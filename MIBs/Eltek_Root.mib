-- Eltek Toplevel MIB for Digital Power plant designs


-- Eltek MIB for ELTEK Distributed Control System Power plant designs
-- $Revision:   1.0  $
-- $Author:   hajo  $
-- $Archive:   V:/PVCS_DB1/archives/WebPower Distributed R210eclipse/Rev 4.2 Std/Nburn/mibs/Eltek_Root.mib-arc  $    
-- $Date:   Jun 24 2008 09:55:14  $  

ELTEK_COMMON-MIB DEFINITIONS ::= BEGIN

IMPORTS
	NOTIFICATION-TYPE, OBJECT-TYPE, MODULE-IDENTITY, 
	mib-2, enterprises, Counter32, Integer32
		FROM SNMPv2-SMI
	NOTIFICATION-GROUP
		FROM SNMPv2-CONF
	DisplayString
		FROM SNMPv2-TC;

eltek MODULE-IDENTITY
	LAST-UPDATED "200509071546Z"
	ORGANIZATION 
		"ELTEK dcSystem MIB Working Group"
	CONTACT-INFO 
		"Harald Johnsen
		      Postal: Eltek Energy AS
		      P.O. Box 1500
		      N-3007 Drammen
		      Norway
		      Tel: +47-32 20 32 00
		      Fax: +47-32 20 31 20
		      E-mail: harald.johnsen@eltekenergy.com
		      web:  www.eltekenergy.com
		            "
	DESCRIPTION 
		"An ongoing effort toward a generic MIB for all ELTEK products.
		The origin of this MIB comes from Nextel spec as of May 2005 and is meant to
		 be a common basic mib for smartpack, aeon gold and mcu control units.
		This iteration is based on the distributed systems smartpack mib, and contains basically 
		changes in the trap format."

	REVISION "200506281130Z"
	DESCRIPTION 
		"First revision"

	REVISION "200507091238Z"
	DESCRIPTION 
		"added battery test and boost start/stop and ac voltages"

	REVISION "200706221127Z"
	DESCRIPTION 
		"Branch 9, contains mainly changes in the Traps format. The traps now meets SNMP v2c specification."
::= { enterprises 12148 }


-- Aeongold branch will be 1
-- AL175    branch will be 2
-- AL6000      branch will be 3
-- Webpower proto branch will be 4
-- Smartpack      branch will be 5
-- Nextel Smartpack  branch will be 6
-- ELTEK Common     branch will be 7
-- ELTEK Distributed  branch will be 8
-- ELTEK Distributed V2 branch will be 9

END
