--  Title:    FALCON32.MIB
--  Version:  v6.6
--  Date:     11/04/02 13:00pm
--
--  Copyright @ 2002 RLE Technologies.  All rights reserved worldwide.
--
--  This MIB defines objects for the RLE falcon SNMP Agent.
--

RLE-FALCON-MIB DEFINITIONS ::= BEGIN

IMPORTS
        TruthValue
                FROM RFC1253-MIB
        DisplayString
                FROM RFC1213-MIB
        OBJECT-TYPE, Gauge
                FROM RFC1155-SMI
        TRAP-TYPE
                FROM RFC-1215
        Counter, enterprises
                FROM RFC1155-SMI;
   PositiveInteger ::= INTEGER (1..2147483647)

rle OBJECT IDENTIFIER ::= { enterprises  3184 }

products   OBJECT IDENTIFIER ::= { rle  1 }

falcon   OBJECT IDENTIFIER ::= { products  1 }

falconMIB OBJECT IDENTIFIER ::= { falcon 1 }

falconIdent OBJECT IDENTIFIER ::= { falconMIB 1 }

falconIdentManufacturer OBJECT-TYPE
    SYNTAX  DisplayString
    ACCESS  read-only
    STATUS  mandatory
    DESCRIPTION
           "The Monitor Control Unit manufacturer."
    ::= { falconIdent  1 }

falconIdentModel OBJECT-TYPE
    SYNTAX  DisplayString
    ACCESS  read-only
    STATUS  mandatory
    DESCRIPTION
           "The Monitor Control Unit Model designation."
    ::= { falconIdent  2 }

falconIdentSoftwareVersion OBJECT-TYPE
    SYNTAX  DisplayString
    ACCESS  read-only
    STATUS  mandatory
    DESCRIPTION
           "The falcon SNMP Agent software version."
    ::= { falconIdent  3 }

falconIdentSpecific OBJECT-TYPE
    SYNTAX  OBJECT IDENTIFIER
    ACCESS  read-only
    STATUS  mandatory
    DESCRIPTION
           "A reference to MIB definitions specific to the
            particular Monitor Unit being managed. This
            object is used to locate the product-specific MIB
            for this device.

            If this information is not present, its value
            should be the OBJECT IDENTIFIER { 0 0 },
            which is a syntactically valid object identifier,
            and any conformant implementation of ASN.1 and BER
            must be able to generate and recognize this value."
    ::= { falconIdent  4 }

falconSystem OBJECT IDENTIFIER ::= { falconMIB 2 }

falconClock OBJECT-TYPE
    SYNTAX  DisplayString
    ACCESS  read-write
    STATUS  mandatory
    DESCRIPTION
           "The falcon internal clock settings.
            Displayed as MM/DD/YY HH:MM:SS"
    ::= { falconSystem  1 }

falconDoorAlarmBypass OBJECT-TYPE
    SYNTAX  INTEGER (-2147483648..2147483647)
    ACCESS  read-write
    STATUS  mandatory
    DESCRIPTION
           "The falcon door alarm bypass switch.
            This allows the alarm to be bypassed upon valid keypad access.
            Zero disables this, or use 1 thru 8 for the corresponding
            falcon input."
    ::= { falconSystem  2 }

falconKeypad OBJECT IDENTIFIER ::= { falconSystem 3 }

falconKeypadCode1 OBJECT-TYPE
    SYNTAX  DisplayString
    ACCESS  read-write
    STATUS  mandatory
    DESCRIPTION
           "The falcon keypad access code for user #1.
            This can be up to six numberic characters."
    ::= { falconKeypad  1 }

falconKeypadName1 OBJECT-TYPE
    SYNTAX  DisplayString
    ACCESS  read-write
    STATUS  mandatory
    DESCRIPTION
           "The falcon keypad access name for user #1.
            This can be up to 20 characters."
    ::= { falconKeypad  2 }

falconKeypadCode2 OBJECT-TYPE
    SYNTAX  DisplayString
    ACCESS  read-write
    STATUS  mandatory
    DESCRIPTION
           "The falcon keypad access code for user #2.
            This can be up to six numberic characters."
    ::= { falconKeypad  3 }

falconKeypadName2 OBJECT-TYPE
    SYNTAX  DisplayString
    ACCESS  read-write
    STATUS  mandatory
    DESCRIPTION
           "The falcon keypad access name for user #2.
            This can be up to 20 characters."
    ::= { falconKeypad  4 }

falconKeypadCode3 OBJECT-TYPE
    SYNTAX  DisplayString
    ACCESS  read-write
    STATUS  mandatory
    DESCRIPTION
           "The falcon keypad access code for user #3.
            This can be up to six numberic characters."
    ::= { falconKeypad  5 }

falconKeypadName3 OBJECT-TYPE
    SYNTAX  DisplayString
    ACCESS  read-write
    STATUS  mandatory
    DESCRIPTION
           "The falcon keypad access name for user #3.
            This can be up to 20 characters."
    ::= { falconKeypad  6 }

falconKeypadCode4 OBJECT-TYPE
    SYNTAX  DisplayString
    ACCESS  read-write
    STATUS  mandatory
    DESCRIPTION
           "The falcon keypad access code for user #4.
            This can be up to six numberic characters."
    ::= { falconKeypad  7 }

falconKeypadName4 OBJECT-TYPE
    SYNTAX  DisplayString
    ACCESS  read-write
    STATUS  mandatory
    DESCRIPTION
           "The falcon keypad access name for user #4.
            This can be up to 20 characters."
    ::= { falconKeypad  8 }

falconKeypadCode5 OBJECT-TYPE
    SYNTAX  DisplayString
    ACCESS  read-write
    STATUS  mandatory
    DESCRIPTION
           "The falcon keypad access code for user #5.
            This can be up to six numberic characters."
    ::= { falconKeypad  9 }

falconKeypadName5 OBJECT-TYPE
    SYNTAX  DisplayString
    ACCESS  read-write
    STATUS  mandatory
    DESCRIPTION
           "The falcon keypad access name for user #5.
            This can be up to 20 characters."
    ::= { falconKeypad  10 }

falconKeypadCode6 OBJECT-TYPE
    SYNTAX  DisplayString
    ACCESS  read-write
    STATUS  mandatory
    DESCRIPTION
           "The falcon keypad access code for user #6.
            This can be up to six numberic characters."
    ::= { falconKeypad  11 }

falconKeypadName6 OBJECT-TYPE
    SYNTAX  DisplayString
    ACCESS  read-write
    STATUS  mandatory
    DESCRIPTION
           "The falcon keypad access name for user #6.
            This can be up to 20 characters."
    ::= { falconKeypad  12 }

falconKeypadCode7 OBJECT-TYPE
    SYNTAX  DisplayString
    ACCESS  read-write
    STATUS  mandatory
    DESCRIPTION
           "The falcon keypad access code for user #7.
            This can be up to six numberic characters."
    ::= { falconKeypad  13 }

falconKeypadName7 OBJECT-TYPE
    SYNTAX  DisplayString
    ACCESS  read-write
    STATUS  mandatory
    DESCRIPTION
           "The falcon keypad access name for user #7.
            This can be up to 20 characters."
    ::= { falconKeypad  14 }

falconKeypadCode8 OBJECT-TYPE
    SYNTAX  DisplayString
    ACCESS  read-write
    STATUS  mandatory
    DESCRIPTION
           "The falcon keypad access code for user #8.
            This can be up to six numberic characters."
    ::= { falconKeypad  15 }

falconKeypadName8 OBJECT-TYPE
    SYNTAX  DisplayString
    ACCESS  read-write
    STATUS  mandatory
    DESCRIPTION
           "The falcon keypad access name for user #8.
            This can be up to 20 characters."
    ::= { falconKeypad  16 }

falconKeypadCode9 OBJECT-TYPE
    SYNTAX  DisplayString
    ACCESS  read-write
    STATUS  mandatory
    DESCRIPTION
           "The falcon keypad access code for user #9.
            This can be up to six numberic characters."
    ::= { falconKeypad  17 }

falconKeypadName9 OBJECT-TYPE
    SYNTAX  DisplayString
    ACCESS  read-write
    STATUS  mandatory
    DESCRIPTION
           "The falcon keypad access name for user #9.
            This can be up to 20 characters."
    ::= { falconKeypad  18 }

falconKeypadCode10 OBJECT-TYPE
    SYNTAX  DisplayString
    ACCESS  read-write
    STATUS  mandatory
    DESCRIPTION
           "The falcon keypad access code for user #10.
            This can be up to six numberic characters."
    ::= { falconKeypad  19 }

falconKeypadName10 OBJECT-TYPE
    SYNTAX  DisplayString
    ACCESS  read-write
    STATUS  mandatory
    DESCRIPTION
           "The falcon keypad access name for user #10.
            This can be up to 20 characters."
    ::= { falconKeypad  20 }

falconKeypadCode11 OBJECT-TYPE
    SYNTAX  DisplayString
    ACCESS  read-write
    STATUS  mandatory
    DESCRIPTION
           "The falcon keypad access code for user #11.
            This can be up to six numberic characters."
    ::= { falconKeypad  21 }

falconKeypadName11 OBJECT-TYPE
    SYNTAX  DisplayString
    ACCESS  read-write
    STATUS  mandatory
    DESCRIPTION
           "The falcon keypad access name for user #11.
            This can be up to 20 characters."
    ::= { falconKeypad  22 }

falconKeypadCode12 OBJECT-TYPE
    SYNTAX  DisplayString
    ACCESS  read-write
    STATUS  mandatory
    DESCRIPTION
           "The falcon keypad access code for user #12.
            This can be up to six numberic characters."
    ::= { falconKeypad  23 }

falconKeypadName12 OBJECT-TYPE
    SYNTAX  DisplayString
    ACCESS  read-write
    STATUS  mandatory
    DESCRIPTION
           "The falcon keypad access name for user #12.
            This can be up to 20 characters."
    ::= { falconKeypad  24 }

falconKeypadCode13 OBJECT-TYPE
    SYNTAX  DisplayString
    ACCESS  read-write
    STATUS  mandatory
    DESCRIPTION
           "The falcon keypad access code for user #13.
            This can be up to six numberic characters."
    ::= { falconKeypad  25 }

falconKeypadName13 OBJECT-TYPE
    SYNTAX  DisplayString
    ACCESS  read-write
    STATUS  mandatory
    DESCRIPTION
           "The falcon keypad access name for user #13.
            This can be up to 20 characters."
    ::= { falconKeypad  26 }

falconKeypadCode14 OBJECT-TYPE
    SYNTAX  DisplayString
    ACCESS  read-write
    STATUS  mandatory
    DESCRIPTION
           "The falcon keypad access code for user #14.
            This can be up to six numberic characters."
    ::= { falconKeypad  27 }

falconKeypadName14 OBJECT-TYPE
    SYNTAX  DisplayString
    ACCESS  read-write
    STATUS  mandatory
    DESCRIPTION
           "The falcon keypad access name for user #14.
            This can be up to 20 characters."
    ::= { falconKeypad  28 }

falconKeypadCode15 OBJECT-TYPE
    SYNTAX  DisplayString
    ACCESS  read-write
    STATUS  mandatory
    DESCRIPTION
           "The falcon keypad access code for user #15.
            This can be up to six numberic characters."
    ::= { falconKeypad  29 }

falconKeypadName15 OBJECT-TYPE
    SYNTAX  DisplayString
    ACCESS  read-write
    STATUS  mandatory
    DESCRIPTION
           "The falcon keypad access name for user #15.
            This can be up to 20 characters."
    ::= { falconKeypad  30 }

falconKeypadCode16 OBJECT-TYPE
    SYNTAX  DisplayString
    ACCESS  read-write
    STATUS  mandatory
    DESCRIPTION
           "The falcon keypad access code for user #16.
            This can be up to six numberic characters."
    ::= { falconKeypad  31 }

falconKeypadName16 OBJECT-TYPE
    SYNTAX  DisplayString
    ACCESS  read-write
    STATUS  mandatory
    DESCRIPTION
           "The falcon keypad access name for user #16.
            This can be up to 20 characters."
    ::= { falconKeypad  32 }

falconKeypadCode17 OBJECT-TYPE
    SYNTAX  DisplayString
    ACCESS  read-write
    STATUS  mandatory
    DESCRIPTION
           "The falcon keypad access code for user #17.
            This can be up to six numberic characters."
    ::= { falconKeypad  33 }

falconKeypadName17 OBJECT-TYPE
    SYNTAX  DisplayString
    ACCESS  read-write
    STATUS  mandatory
    DESCRIPTION
           "The falcon keypad access name for user #17.
            This can be up to 20 characters."
    ::= { falconKeypad  34 }

falconKeypadCode18 OBJECT-TYPE
    SYNTAX  DisplayString
    ACCESS  read-write
    STATUS  mandatory
    DESCRIPTION
           "The falcon keypad access code for user #18.
            This can be up to six numberic characters."
    ::= { falconKeypad  35 }

falconKeypadName18 OBJECT-TYPE
    SYNTAX  DisplayString
    ACCESS  read-write
    STATUS  mandatory
    DESCRIPTION
           "The falcon keypad access name for user #18.
            This can be up to 20 characters."
    ::= { falconKeypad  36 }

falconKeypadCode19 OBJECT-TYPE
    SYNTAX  DisplayString
    ACCESS  read-write
    STATUS  mandatory
    DESCRIPTION
           "The falcon keypad access code for user #19.
            This can be up to six numberic characters."
    ::= { falconKeypad  37 }

falconKeypadName19 OBJECT-TYPE
    SYNTAX  DisplayString
    ACCESS  read-write
    STATUS  mandatory
    DESCRIPTION
           "The falcon keypad access name for user #19.
            This can be up to 20 characters."
    ::= { falconKeypad  38 }

falconKeypadCode20 OBJECT-TYPE
    SYNTAX  DisplayString
    ACCESS  read-write
    STATUS  mandatory
    DESCRIPTION
           "The falcon keypad access code for user #20.
            This can be up to six numberic characters."
    ::= { falconKeypad  39 }

falconKeypadName20 OBJECT-TYPE
    SYNTAX  DisplayString
    ACCESS  read-write
    STATUS  mandatory
    DESCRIPTION
           "The falcon keypad access name for user #20.
            This can be up to 20 characters."
    ::= { falconKeypad  40 }

falconInputVoltage OBJECT-TYPE
    SYNTAX  INTEGER (-2147483648..2147483647)
    ACCESS  read-only
    STATUS  mandatory
    DESCRIPTION
           "The falcon input voltage (DC Power)."
    ::= { falconSystem  4 }

falconOnBattery OBJECT-TYPE
    SYNTAX  INTEGER {
    notInstalled(0),
    installed(1)
}
    ACCESS  read-write
    STATUS  mandatory
    DESCRIPTION
           "The state of use of the On Battery Alarm. When
            the State is set to installed(1), the On Battery and
            Low Battery alarms are enabled.
            This variable is stored in non-volatile memory."
    ::= { falconSystem  5 }

falconLowBatteryThreshold OBJECT-TYPE
    SYNTAX  INTEGER (-2147483648..2147483647)
    ACCESS  read-write
    STATUS  mandatory
    DESCRIPTION
           "The low voltage trip point for the low battery alarm.
            When the input voltage goes below this voltage, the
            Low Battery alarm is set.
            This variable is stored in non-volatile memory."
    ::= { falconSystem  6 }

falconAnalogAverage OBJECT-TYPE
    SYNTAX  INTEGER (0..60)
    ACCESS  read-write
    STATUS  mandatory
    DESCRIPTION
           "This is the analog averaging duration in seconds.
            The analog input readings are averaged for this time
            period before updating. This value must be set to
            1,2,3,4,5,6,10,15,20,30 or 60 seconds.
            This variable is stored in non-volatile memory."
    ::= { falconSystem  7 }

falconPagerStatusString OBJECT-TYPE
    SYNTAX  DisplayString
    ACCESS  read-only
    STATUS  mandatory
    DESCRIPTION
           "The falcon last page status char string."
    ::= { falconSystem  8 }

falconInputs OBJECT IDENTIFIER ::= { falconMIB  3 }

falconInput1 OBJECT IDENTIFIER ::= { falconInputs 1 }

falconInput1State OBJECT-TYPE
    SYNTAX  INTEGER {
    notInstalled(1),
    analog4to20Installed(2),
    digitalNOInstalled(3),
    digitalNCInstalled(4),
    digitalSTInstalled(5)
}
    ACCESS  read-write
    STATUS  mandatory
    DESCRIPTION
           "The state of use of Input Number 1. When a sensor is
            connected to Input 1 set State to installed(2) to
            indicate that the value of falconReading1 is valid.
            When no sensor is connected to Input 1 set
            State to notInstalled(1) to indicate that the value of
            falconReading1 may not be valid.
            This variable is stored in non-volatile memory."
    ::= { falconInput1  1 }

falconInput1Reading OBJECT-TYPE
    SYNTAX  INTEGER (-2147483648..2147483647)
    ACCESS  read-only
    STATUS  mandatory
    DESCRIPTION
           "The reading for sensor 1.
            If the input is digital, the reading will be 1 (active) or
            0 (inactive)"
    ::= { falconInput1  2 }

falconInput1Gain OBJECT-TYPE
    SYNTAX  INTEGER (-2147483648..2147483647)
    ACCESS  read-write
    STATUS  mandatory
    DESCRIPTION
           "A correction gain associated with the sensor variable.
            The value of gain is multiplied by the value from
            Input Sensor Number 1 to obtain the value of
            the Input1 variable. The gain variable is stored in
            non-volatile memory."
    ::= { falconInput1  3 }

falconInput1Offset OBJECT-TYPE
    SYNTAX  INTEGER (-2147483648..2147483647)
    ACCESS  read-write
    STATUS  mandatory
    DESCRIPTION
           "A correction Offset associated with the sensor variable.
            The value of Offset is added to the value from
            Input Sensor Number 1 to obtain the value of
            the Input1 variable. The Offset variable is stored in
            non-volatile memory."
    ::= { falconInput1  4 }

falconInput1Label OBJECT-TYPE
    SYNTAX  DisplayString
    ACCESS  read-write
    STATUS  mandatory
    DESCRIPTION
           "A user-defined text string associated with Input Number 1.
            The text string is stored in non-volatile memory."
    ::= { falconInput1  5 }

falconInput1UOM OBJECT-TYPE
    SYNTAX  DisplayString
    ACCESS  read-write
    STATUS  mandatory
    DESCRIPTION
           "A user-defined text string associated with Input Number 1.
            The text string is stored in non-volatile memory."
    ::= { falconInput1  6 }

falconInput1HighLimit2 OBJECT-TYPE
    SYNTAX  INTEGER (-2147483648..2147483647)
    ACCESS  read-write
    STATUS  mandatory
    DESCRIPTION
           "When input 1 reaches or exceeds this value a trap will
            be generated signifying a high alarm condition at
            sensor 1.
            The HighLimit2 variable is stored in non-volatile memory."
    ::= { falconInput1  7 }

falconInput1HighLimit OBJECT-TYPE
    SYNTAX  INTEGER (-2147483648..2147483647)
    ACCESS  read-write
    STATUS  mandatory
    DESCRIPTION
           "When input 1 reaches or exceeds this value a trap will
            be generated signifying a high alarm condition at
            sensor 1.
            The HighLimit variable is stored in non-volatile memory."
    ::= { falconInput1  8 }

falconInput1LowLimit OBJECT-TYPE
    SYNTAX  INTEGER (-2147483648..2147483647)
    ACCESS  read-write
    STATUS  mandatory
    DESCRIPTION
           "When input 1 reaches or goes below this value a trap will
            be generated signifying a low alarm condition at sensor 1.
            The LowLimit variable is stored in non-volatile memory."
    ::= { falconInput1  9 }

falconInput1LowLimit2 OBJECT-TYPE
    SYNTAX  INTEGER (-2147483648..2147483647)
    ACCESS  read-write
    STATUS  mandatory
    DESCRIPTION
           "When input 1 reaches or goes below this value a trap will
            be generated signifying a low alarm condition at sensor 1.
            The LowLimit variable is stored in non-volatile memory."
    ::= { falconInput1  10 }

falconInput1RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput1  11 }

falconInput1Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput1  12 }

falconInput1Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput1  13 }

falconInput1Schedule OBJECT-TYPE
    SYNTAX  INTEGER {
    none(0),
    a(1),
    b(2)
}
    ACCESS  read-only
    STATUS  mandatory
    DESCRIPTION
           "The current alarm disable schedule for input 1."
    ::= { falconInput1  14 }

falconInput1DigOffLabel OBJECT-TYPE
    SYNTAX  DisplayString
    ACCESS  read-write
    STATUS  mandatory
    DESCRIPTION
           "A user-defined text string associated with Input Number 1.
           This string is used for digital off text.
           The text string is stored in non-volatile memory."
    ::= { falconInput1  15 }

falconInput2 OBJECT IDENTIFIER ::= { falconInputs 2 }

falconInput2State OBJECT-TYPE
    SYNTAX  INTEGER {
    notInstalled(1),
    analog4to20Installed(2),
    digitalNOInstalled(3),
    digitalNCInstalled(4),
         digitalSTInstalled(5)
}
    ACCESS  read-write
    STATUS  mandatory
    DESCRIPTION
           "The state of use of Input Number 2. When a sensor is
            connected to Input 2 set State to installed(2) to
            indicate that the value of falconReading2 is valid.
            When no sensor is connected to Input 2 set
            State to notInstalled(1) to indicate that the value of
            falconReading2 may not be valid.
            This variable is stored in non-volatile memory."
    ::= { falconInput2  1 }

falconInput2Reading OBJECT-TYPE
    SYNTAX  INTEGER (-2147483648..2147483647)
    ACCESS  read-only
    STATUS  mandatory
    DESCRIPTION
           "The reading for sensor 2.
            If the input is digital, the reading will be 1 (active) or
            0 (inactive)"
    ::= { falconInput2  2 }

falconInput2Gain OBJECT-TYPE
    SYNTAX  INTEGER (-2147483648..2147483647)
    ACCESS  read-write
    STATUS  mandatory
    DESCRIPTION
           "A correction gain associated with the sensor variable.
            The value of gain is multiplied by the value from
            Input Sensor Number 2 to obtain the value of
            the Input2 variable. The gain variable is stored in
            non-volatile memory."
    ::= { falconInput2  3 }

falconInput2Offset OBJECT-TYPE
    SYNTAX  INTEGER (-2147483648..2147483647)
    ACCESS  read-write
    STATUS  mandatory
    DESCRIPTION
           "A correction Offset associated with the sensor variable.
            The value of Offset is added to the value from
            Input Sensor Number 2 to obtain the value of
            the Input2 variable. The Offset variable is stored in
            non-volatile memory."
    ::= { falconInput2  4 }

falconInput2Label OBJECT-TYPE
    SYNTAX  DisplayString
    ACCESS  read-write
    STATUS  mandatory
    DESCRIPTION
           "A user-defined text string associated with Input Number 2.
            The text string is stored in non-volatile memory."
    ::= { falconInput2  5 }

falconInput2UOM OBJECT-TYPE
    SYNTAX  DisplayString
    ACCESS  read-write
    STATUS  mandatory
    DESCRIPTION
           "A user-defined text string associated with Input Number 2.
            The text string is stored in non-volatile memory."
    ::= { falconInput2  6 }

falconInput2HighLimit2 OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { falconInput2  7 }

falconInput2HighLimit OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { falconInput2  8 }

falconInput2LowLimit OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { falconInput2  9 }

falconInput2LowLimit2 OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { falconInput2  10 }

falconInput2RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput2  11 }

falconInput2Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput2  12 }

falconInput2Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput2  13 }

falconInput2Schedule OBJECT-TYPE
    SYNTAX  INTEGER {
    none(0),
    a(1),
    b(2)
}
    ACCESS  read-only
    STATUS  mandatory
    DESCRIPTION
           "The current alarm disable schedule for input 2."
    ::= { falconInput2  14 }

falconInput2DigOffLabel OBJECT-TYPE
    SYNTAX  DisplayString
    ACCESS  read-write
    STATUS  mandatory
    DESCRIPTION
           "A user-defined text string associated with Input Number 2.
           This string is used for digital off text.
           The text string is stored in non-volatile memory."
    ::= { falconInput2  15 }

falconInput3 OBJECT IDENTIFIER ::= { falconInputs 3 }

falconInput3State OBJECT-TYPE
    SYNTAX  INTEGER {
    notInstalled(1),
    analog4to20Installed(2),
    digitalNOInstalled(3),
    digitalNCInstalled(4),
         digitalSTInstalled(5)
}
    ACCESS  read-write
    STATUS  mandatory
    DESCRIPTION
           "The state of use of Input Number 3. When a sensor is
            connected to Input 3 set State to installed(2) to
            indicate that the value of falconReading3 is valid.
            When no sensor is connected to Input 3 set
            State to notInstalled(1) to indicate that the value of
            falconReading3 may not be valid.
            This variable is stored in non-volatile memory."
    ::= { falconInput3  1 }

falconInput3Reading OBJECT-TYPE
    SYNTAX  INTEGER (-2147483648..2147483647)
    ACCESS  read-only
    STATUS  mandatory
    DESCRIPTION
           "The reading for sensor 3.
            If the input is digital, the reading will be 1 (active) or
            0 (inactive)"
    ::= { falconInput3  2 }

falconInput3Gain OBJECT-TYPE
    SYNTAX  INTEGER (-2147483648..2147483647)
    ACCESS  read-write
    STATUS  mandatory
    DESCRIPTION
           "A correction gain associated with the sensor variable.
            The value of gain is multiplied by the value from
            Input Sensor Number 3 to obtain the value of
            the Input3 variable. The gain variable is stored in
            non-volatile memory."
    ::= { falconInput3  3 }

falconInput3Offset OBJECT-TYPE
    SYNTAX  INTEGER (-2147483648..2147483647)
    ACCESS  read-write
    STATUS  mandatory
    DESCRIPTION
           "A correction Offset associated with the sensor variable.
            The value of Offset is added to the value from
            Input Sensor Number 3 to obtain the value of
            the Input3 variable. The Offset variable is stored in
            non-volatile memory."
    ::= { falconInput3  4 }

falconInput3Label OBJECT-TYPE
    SYNTAX  DisplayString
    ACCESS  read-write
    STATUS  mandatory
    DESCRIPTION
           "A user-defined text string associated with Input Number 3.
            The text string is stored in non-volatile memory."
    ::= { falconInput3  5 }

falconInput3UOM OBJECT-TYPE
    SYNTAX  DisplayString
    ACCESS  read-write
    STATUS  mandatory
    DESCRIPTION
           "A user-defined text string associated with Input Number 3.
            The text string is stored in non-volatile memory."
    ::= { falconInput3  6 }

falconInput3HighLimit2 OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { falconInput3  7 }

falconInput3HighLimit OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { falconInput3  8 }

falconInput3LowLimit OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { falconInput3  9 }

falconInput3LowLimit2 OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { falconInput3  10 }

falconInput3RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput3  11 }

falconInput3Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput3  12 }

falconInput3Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput3  13 }

falconInput3Schedule OBJECT-TYPE
    SYNTAX  INTEGER {
    none(0),
    a(1),
    b(2)
}
    ACCESS  read-only
    STATUS  mandatory
    DESCRIPTION
           "The current alarm disable schedule for input 3."
    ::= { falconInput3  14 }

falconInput3DigOffLabel OBJECT-TYPE
    SYNTAX  DisplayString
    ACCESS  read-write
    STATUS  mandatory
    DESCRIPTION
           "A user-defined text string associated with Input Number 3.
           This string is used for digital off text.
           The text string is stored in non-volatile memory."
    ::= { falconInput3  15 }

falconInput4 OBJECT IDENTIFIER ::= { falconInputs 4 }

falconInput4State OBJECT-TYPE
    SYNTAX  INTEGER {
    notInstalled(1),
    analog4to20Installed(2),
    digitalNOInstalled(3),
    digitalNCInstalled(4),
         digitalSTInstalled(5)
}
    ACCESS  read-write
    STATUS  mandatory
    DESCRIPTION
           "The state of use of Input Number 4. When a sensor is
            connected to Input 4 set State to installed(2) to
            indicate that the value of falconReading4 is valid.
            When no sensor is connected to Input 4 set
            State to notInstalled(1) to indicate that the value of
            falconReading4 may not be valid.
            This variable is stored in non-volatile memory."
    ::= { falconInput4  1 }

falconInput4Reading OBJECT-TYPE
    SYNTAX  INTEGER (-2147483648..2147483647)
    ACCESS  read-only
    STATUS  mandatory
    DESCRIPTION
           "The reading for sensor 4.
            If the input is digital, the reading will be 1 (active) or
            0 (inactive)"
    ::= { falconInput4  2 }

falconInput4Gain OBJECT-TYPE
    SYNTAX  INTEGER (-2147483648..2147483647)
    ACCESS  read-write
    STATUS  mandatory
    DESCRIPTION
           "A correction gain associated with the sensor variable.
            The value of gain is multiplied by the value from
            Input Sensor Number 4 to obtain the value of
            the Input4 variable. The gain variable is stored in
            non-volatile memory."
    ::= { falconInput4  3 }

falconInput4Offset OBJECT-TYPE
    SYNTAX  INTEGER (-2147483648..2147483647)
    ACCESS  read-write
    STATUS  mandatory
    DESCRIPTION
           "A correction Offset associated with the sensor variable.
            The value of Offset is added to the value from
            Input Sensor Number 4 to obtain the value of
            the Input4 variable. The Offset variable is stored in
            non-volatile memory."
    ::= { falconInput4  4 }

falconInput4Label OBJECT-TYPE
    SYNTAX  DisplayString
    ACCESS  read-write
    STATUS  mandatory
    DESCRIPTION
           "A user-defined text string associated with Input Number 4.
            The text string is stored in non-volatile memory."
    ::= { falconInput4  5 }

falconInput4UOM OBJECT-TYPE
    SYNTAX  DisplayString
    ACCESS  read-write
    STATUS  mandatory
    DESCRIPTION
           "A user-defined text string associated with Input Number 4.
            The text string is stored in non-volatile memory."
    ::= { falconInput4  6 }

falconInput4HighLimit2 OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { falconInput4  7 }

falconInput4HighLimit OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { falconInput4  8 }

falconInput4LowLimit OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { falconInput4  9 }

falconInput4LowLimit2 OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { falconInput4  10 }

falconInput4RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput4  11 }

falconInput4Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput4  12 }

falconInput4Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput4  13 }

falconInput4Schedule OBJECT-TYPE
    SYNTAX  INTEGER {
    none(0),
    a(1),
    b(2)
}
    ACCESS  read-only
    STATUS  mandatory
    DESCRIPTION
           "The current alarm disable schedule for input 4."
    ::= { falconInput4  14 }

falconInput4DigOffLabel OBJECT-TYPE
    SYNTAX  DisplayString
    ACCESS  read-write
    STATUS  mandatory
    DESCRIPTION
           "A user-defined text string associated with Input Number 4.
           This string is used for digital off text.
           The text string is stored in non-volatile memory."
    ::= { falconInput4  15 }

falconInput5 OBJECT IDENTIFIER ::= { falconInputs 5 }

falconInput5State OBJECT-TYPE
    SYNTAX  INTEGER {
    notInstalled(1),
    analog4to20Installed(2),
    digitalNOInstalled(3),
    digitalNCInstalled(4),
         digitalSTInstalled(5)
}
    ACCESS  read-write
    STATUS  mandatory
    DESCRIPTION
           "The state of use of Input Number 5. When a sensor is
            connected to Input 5 set State to installed(2) to
            indicate that the value of falconReading4 is valid.
            When no sensor is connected to Input 5 set
            State to notInstalled(1) to indicate that the value of
            falconReading5 may not be valid.
            This variable is stored in non-volatile memory."
    ::= { falconInput5  1 }

falconInput5Reading OBJECT-TYPE
    SYNTAX  INTEGER (-2147483648..2147483647)
    ACCESS  read-only
    STATUS  mandatory
    DESCRIPTION
           "The reading for sensor 5.
            If the input is digital, the reading will be 1 (active) or
            0 (inactive)"
    ::= { falconInput5  2 }

falconInput5Gain OBJECT-TYPE
    SYNTAX  INTEGER (-2147483648..2147483647)
    ACCESS  read-write
    STATUS  mandatory
    DESCRIPTION
           "A correction gain associated with the sensor variable.
            The value of gain is multiplied by the value from
            Input Sensor Number 5 to obtain the value of
            the Input5 variable. The gain variable is stored in
            non-volatile memory."
    ::= { falconInput5  3 }

falconInput5Offset OBJECT-TYPE
    SYNTAX  INTEGER (-2147483648..2147483647)
    ACCESS  read-write
    STATUS  mandatory
    DESCRIPTION
           "A correction Offset associated with the sensor variable.
            The value of Offset is added to the value from
            Input Sensor Number 5 to obtain the value of
            the Input5 variable. The Offset variable is stored in
            non-volatile memory."
    ::= { falconInput5  4 }

falconInput5Label OBJECT-TYPE
    SYNTAX  DisplayString
    ACCESS  read-write
    STATUS  mandatory
    DESCRIPTION
           "A user-defined text string associated with Input Number 5.
            The text string is stored in non-volatile memory."
    ::= { falconInput5  5 }

falconInput5UOM OBJECT-TYPE
    SYNTAX  DisplayString
    ACCESS  read-write
    STATUS  mandatory
    DESCRIPTION
           "A user-defined text string associated with Input Number 5.
            The text string is stored in non-volatile memory."
    ::= { falconInput5  6 }

falconInput5HighLimit2 OBJECT-TYPE
    SYNTAX  INTEGER (-2147483648..2147483647)
    ACCESS  read-write
    STATUS  mandatory
    DESCRIPTION
           "When input 5 reaches or exceeds this value a trap will
            be generated signifying a high alarm condition at
            sensor 5.
            The HighLimit variable is stored in non-volatile memory."
    ::= { falconInput5  7 }

falconInput5HighLimit OBJECT-TYPE
    SYNTAX  INTEGER (-2147483648..2147483647)
    ACCESS  read-write
    STATUS  mandatory
    DESCRIPTION
           "When input 5 reaches or exceeds this value a trap will
            be generated signifying a high alarm condition at
            sensor 5.
            The HighLimit variable is stored in non-volatile memory."
    ::= { falconInput5  8 }

falconInput5LowLimit OBJECT-TYPE
    SYNTAX  INTEGER (-2147483648..2147483647)
    ACCESS  read-write
    STATUS  mandatory
    DESCRIPTION
           "When input 5 reaches or goes below this value a trap will
            be generated signifying a low alarm condition at sensor 5.
            The LowLimit variable is stored in non-volatile memory."
    ::= { falconInput5  9 }

falconInput5LowLimit2 OBJECT-TYPE
    SYNTAX  INTEGER (-2147483648..2147483647)
    ACCESS  read-write
    STATUS  mandatory
    DESCRIPTION
           "When input 5 reaches or goes below this value a trap will
            be generated signifying a low alarm condition at sensor 5.
            The LowLimit variable is stored in non-volatile memory."
    ::= { falconInput5  10 }

falconInput5RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput5  11 }

falconInput5Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput5  12 }

falconInput5Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput5  13 }

falconInput5Schedule OBJECT-TYPE
    SYNTAX  INTEGER {
    none(0),
    a(1),
    b(2)
}
    ACCESS  read-only
    STATUS  mandatory
    DESCRIPTION
           "The current alarm disable schedule for input 5."
    ::= { falconInput5  14 }

falconInput5DigOffLabel OBJECT-TYPE
    SYNTAX  DisplayString
    ACCESS  read-write
    STATUS  mandatory
    DESCRIPTION
           "A user-defined text string associated with Input Number 5.
           This string is used for digital off text.
           The text string is stored in non-volatile memory."
    ::= { falconInput5  15 }

falconInput6 OBJECT IDENTIFIER ::= { falconInputs 6 }

falconInput6State OBJECT-TYPE
    SYNTAX  INTEGER {
    notInstalled(1),
    analog4to20Installed(2),
    digitalNOInstalled(3),
    digitalNCInstalled(4),
         digitalSTInstalled(5)
}
    ACCESS  read-write
    STATUS  mandatory
    DESCRIPTION
           "The state of use of Input Number 6. When a sensor is
            connected to Input 6 set State to installed(2) to
            indicate that the value of falconReading6 is valid.
            When no sensor is connected to Input 6 set
            State to notInstalled(1) to indicate that the value of
            falconReading6 may not be valid.
            This variable is stored in non-volatile memory."
    ::= { falconInput6  1 }

falconInput6Reading OBJECT-TYPE
    SYNTAX  INTEGER (-2147483648..2147483647)
    ACCESS  read-only
    STATUS  mandatory
    DESCRIPTION
           "The reading for sensor 6.
            If the input is digital, the reading will be 1 (active) or
            0 (inactive)"
    ::= { falconInput6  2 }

falconInput6Gain OBJECT-TYPE
    SYNTAX  INTEGER (-2147483648..2147483647)
    ACCESS  read-write
    STATUS  mandatory
    DESCRIPTION
           "A correction gain associated with the sensor variable.
            The value of gain is multiplied by the value from
            Input Sensor Number 6 to obtain the value of
            the Input6 variable. The gain variable is stored in
            non-volatile memory."
    ::= { falconInput6  3 }

falconInput6Offset OBJECT-TYPE
    SYNTAX  INTEGER (-2147483648..2147483647)
    ACCESS  read-write
    STATUS  mandatory
    DESCRIPTION
           "A correction Offset associated with the sensor variable.
            The value of Offset is added to the value from
            Input Sensor Number 6 to obtain the value of
            the Input6 variable. The Offset variable is stored in
            non-volatile memory."
    ::= { falconInput6  4 }

falconInput6Label OBJECT-TYPE
    SYNTAX  DisplayString
    ACCESS  read-write
    STATUS  mandatory
    DESCRIPTION
           "A user-defined text string associated with Input Number 6.
            The text string is stored in non-volatile memory."
    ::= { falconInput6  5 }

falconInput6UOM OBJECT-TYPE
    SYNTAX  DisplayString
    ACCESS  read-write
    STATUS  mandatory
    DESCRIPTION
           "A user-defined text string associated with Input Number 6.
            The text string is stored in non-volatile memory."
    ::= { falconInput6  6 }

falconInput6HighLimit2 OBJECT-TYPE
    SYNTAX  INTEGER (-2147483648..2147483647)
    ACCESS  read-write
    STATUS  mandatory
    DESCRIPTION
           "When input 6 reaches or exceeds this value a trap will
            be generated signifying a high alarm condition at
            sensor 6.
            The HighLimit variable is stored in non-volatile memory."
    ::= { falconInput6  7 }

falconInput6HighLimit OBJECT-TYPE
    SYNTAX  INTEGER (-2147483648..2147483647)
    ACCESS  read-write
    STATUS  mandatory
    DESCRIPTION
           "When input 6 reaches or exceeds this value a trap will
            be generated signifying a high alarm condition at
            sensor 6.
            The HighLimit variable is stored in non-volatile memory."
    ::= { falconInput6  8 }

falconInput6LowLimit OBJECT-TYPE
    SYNTAX  INTEGER (-2147483648..2147483647)
    ACCESS  read-write
    STATUS  mandatory
    DESCRIPTION
           "When input 6 reaches or goes below this value a trap will
            be generated signifying a low alarm condition at sensor 6.
            The LowLimit variable is stored in non-volatile memory."
    ::= { falconInput6  9 }

falconInput6LowLimit2 OBJECT-TYPE
    SYNTAX  INTEGER (-2147483648..2147483647)
    ACCESS  read-write
    STATUS  mandatory
    DESCRIPTION
           "When input 6 reaches or goes below this value a trap will
            be generated signifying a low alarm condition at sensor 6.
            The LowLimit variable is stored in non-volatile memory."
    ::= { falconInput6  10 }

falconInput6RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput6  11 }

falconInput6Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput6  12 }

falconInput6Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput6  13 }

falconInput6Schedule OBJECT-TYPE
    SYNTAX  INTEGER {
    none(0),
    a(1),
    b(2)
}
    ACCESS  read-only
    STATUS  mandatory
    DESCRIPTION
           "The current alarm disable schedule for input 6."
    ::= { falconInput6  14 }

falconInput6DigOffLabel OBJECT-TYPE
    SYNTAX  DisplayString
    ACCESS  read-write
    STATUS  mandatory
    DESCRIPTION
           "A user-defined text string associated with Input Number 6.
           This string is used for digital off text.
           The text string is stored in non-volatile memory."
    ::= { falconInput6  15 }

falconInput7 OBJECT IDENTIFIER ::= { falconInputs 7 }

falconInput7State OBJECT-TYPE
    SYNTAX  INTEGER {
    notInstalled(1),
    analog4to20Installed(2),
    digitalNOInstalled(3),
    digitalNCInstalled(4),
         digitalSTInstalled(5)
}
    ACCESS  read-write
    STATUS  mandatory
    DESCRIPTION
           "The state of use of Input Number 7. When a sensor is
            connected to Input 7 set State to installed(2) to
            indicate that the value of falconReading4 is valid.
            When no sensor is connected to Input 7 set
            State to notInstalled(1) to indicate that the value of
            falconReading7 may not be valid.
            This variable is stored in non-volatile memory."
    ::= { falconInput7  1 }

falconInput7Reading OBJECT-TYPE
    SYNTAX  INTEGER (-2147483648..2147483647)
    ACCESS  read-only
    STATUS  mandatory
    DESCRIPTION
           "The reading for sensor 7.
            If the input is digital, the reading will be 1 (active) or
            0 (inactive)"
    ::= { falconInput7  2 }

falconInput7Gain OBJECT-TYPE
    SYNTAX  INTEGER (-2147483648..2147483647)
    ACCESS  read-write
    STATUS  mandatory
    DESCRIPTION
           "A correction gain associated with the sensor variable.
            The value of gain is multiplied by the value from
            Input Sensor Number 7 to obtain the value of
            the Input7 variable. The gain variable is stored in
            non-volatile memory."
    ::= { falconInput7  3 }

falconInput7Offset OBJECT-TYPE
    SYNTAX  INTEGER (-2147483648..2147483647)
    ACCESS  read-write
    STATUS  mandatory
    DESCRIPTION
           "A correction Offset associated with the sensor variable.
            The value of Offset is added to the value from
            Input Sensor Number 7 to obtain the value of
            the Input7 variable. The Offset variable is stored in
            non-volatile memory."
    ::= { falconInput7  4 }

falconInput7Label OBJECT-TYPE
    SYNTAX  DisplayString
    ACCESS  read-write
    STATUS  mandatory
    DESCRIPTION
           "A user-defined text string associated with Input Number 7.
            The text string is stored in non-volatile memory."
    ::= { falconInput7  5 }

falconInput7UOM OBJECT-TYPE
    SYNTAX  DisplayString
    ACCESS  read-write
    STATUS  mandatory
    DESCRIPTION
           "A user-defined text string associated with Input Number 7.
            The text string is stored in non-volatile memory."
    ::= { falconInput7  6 }

falconInput7HighLimit2 OBJECT-TYPE
    SYNTAX  INTEGER (-2147483648..2147483647)
    ACCESS  read-write
    STATUS  mandatory
    DESCRIPTION
           "When input 7 reaches or exceeds this value a trap will
            be generated signifying a high alarm condition at
            sensor 7.
            The HighLimit variable is stored in non-volatile memory."
    ::= { falconInput7  7 }

falconInput7HighLimit OBJECT-TYPE
    SYNTAX  INTEGER (-2147483648..2147483647)
    ACCESS  read-write
    STATUS  mandatory
    DESCRIPTION
           "When input 7 reaches or exceeds this value a trap will
            be generated signifying a high alarm condition at
            sensor 7.
            The HighLimit variable is stored in non-volatile memory."
    ::= { falconInput7  8 }

falconInput7LowLimit OBJECT-TYPE
    SYNTAX  INTEGER (-2147483648..2147483647)
    ACCESS  read-write
    STATUS  mandatory
    DESCRIPTION
           "When input 7 reaches or goes below this value a trap will
            be generated signifying a low alarm condition at sensor 7.
            The LowLimit variable is stored in non-volatile memory."
    ::= { falconInput7  9 }

falconInput7LowLimit2 OBJECT-TYPE
    SYNTAX  INTEGER (-2147483648..2147483647)
    ACCESS  read-write
    STATUS  mandatory
    DESCRIPTION
           "When input 7 reaches or goes below this value a trap will
            be generated signifying a low alarm condition at sensor 7.
            The LowLimit variable is stored in non-volatile memory."
    ::= { falconInput7  10 }

falconInput7RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput7  11 }

falconInput7Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput7  12 }

falconInput7Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput7  13 }

falconInput7Schedule OBJECT-TYPE
    SYNTAX  INTEGER {
    none(0),
    a(1),
    b(2)
}
    ACCESS  read-only
    STATUS  mandatory
    DESCRIPTION
           "The current alarm disable schedule for input 7."
    ::= { falconInput7  14 }

falconInput7DigOffLabel OBJECT-TYPE
    SYNTAX  DisplayString
    ACCESS  read-write
    STATUS  mandatory
    DESCRIPTION
           "A user-defined text string associated with Input Number 7.
           This string is used for digital off text.
           The text string is stored in non-volatile memory."
    ::= { falconInput7  15 }

falconInput8 OBJECT IDENTIFIER ::= { falconInputs 8 }

falconInput8State OBJECT-TYPE
    SYNTAX  INTEGER {
    notInstalled(1),
    analog4to20Installed(2),
    digitalNOInstalled(3),
    digitalNCInstalled(4),
         digitalSTInstalled(5)
}
    ACCESS  read-write
    STATUS  mandatory
    DESCRIPTION
           "The state of use of Input Number 8. When a sensor is
            connected to Input 8 set State to installed(2) to
            indicate that the value of falconReading8 is valid.
            When no sensor is connected to Input 8 set
            State to notInstalled(1) to indicate that the value of
            falconReading8 may not be valid.
            This variable is stored in non-volatile memory."
    ::= { falconInput8  1 }

falconInput8Reading OBJECT-TYPE
    SYNTAX  INTEGER (-2147483648..2147483647)
    ACCESS  read-only
    STATUS  mandatory
    DESCRIPTION
           "The reading for sensor 8.
            If the input is digital, the reading will be 1 (active) or
            0 (inactive)"
    ::= { falconInput8  2 }

falconInput8Gain OBJECT-TYPE
    SYNTAX  INTEGER (-2147483648..2147483647)
    ACCESS  read-write
    STATUS  mandatory
    DESCRIPTION
           "A correction gain associated with the sensor variable.
            The value of gain is multiplied by the value from
            Input Sensor Number 8 to obtain the value of
            the Input8 variable. The gain variable is stored in
            non-volatile memory."
    ::= { falconInput8  3 }

falconInput8Offset OBJECT-TYPE
    SYNTAX  INTEGER (-2147483648..2147483647)
    ACCESS  read-write
    STATUS  mandatory
    DESCRIPTION
           "A correction Offset associated with the sensor variable.
            The value of Offset is added to the value from
            Input Sensor Number 8 to obtain the value of
            the Input8 variable. The Offset variable is stored in
            non-volatile memory."
    ::= { falconInput8  4 }

falconInput8Label OBJECT-TYPE
    SYNTAX  DisplayString
    ACCESS  read-write
    STATUS  mandatory
    DESCRIPTION
           "A user-defined text string associated with Input Number 8.
            The text string is stored in non-volatile memory."
    ::= { falconInput8  5 }

falconInput8UOM OBJECT-TYPE
    SYNTAX  DisplayString
    ACCESS  read-write
    STATUS  mandatory
    DESCRIPTION
           "A user-defined text string associated with Input Number 8.
            The text string is stored in non-volatile memory."
    ::= { falconInput8  6 }

falconInput8HighLimit2 OBJECT-TYPE
    SYNTAX  INTEGER (-2147483648..2147483647)
    ACCESS  read-write
    STATUS  mandatory
    DESCRIPTION
           "When input 8 reaches or exceeds this value a trap will
            be generated signifying a high alarm condition at
            sensor 8.
            The HighLimit variable is stored in non-volatile memory."
    ::= { falconInput8  7 }

falconInput8HighLimit OBJECT-TYPE
    SYNTAX  INTEGER (-2147483648..2147483647)
    ACCESS  read-write
    STATUS  mandatory
    DESCRIPTION
           "When input 8 reaches or exceeds this value a trap will
            be generated signifying a high alarm condition at
            sensor 8.
            The HighLimit variable is stored in non-volatile memory."
    ::= { falconInput8  8 }

falconInput8LowLimit OBJECT-TYPE
    SYNTAX  INTEGER (-2147483648..2147483647)
    ACCESS  read-write
    STATUS  mandatory
    DESCRIPTION
           "When input 8 reaches or goes below this value a trap will
            be generated signifying a low alarm condition at sensor 8.
            The LowLimit variable is stored in non-volatile memory."
    ::= { falconInput8  9 }

falconInput8LowLimit2 OBJECT-TYPE
    SYNTAX  INTEGER (-2147483648..2147483647)
    ACCESS  read-write
    STATUS  mandatory
    DESCRIPTION
           "When input 8 reaches or goes below this value a trap will
            be generated signifying a low alarm condition at sensor 8.
            The LowLimit variable is stored in non-volatile memory."
    ::= { falconInput8  10 }

falconInput8RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput8  11 }

falconInput8Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput8  12 }

falconInput8Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput8  13 }

falconInput8Schedule OBJECT-TYPE
    SYNTAX  INTEGER {
    none(0),
    a(1),
    b(2)
}
    ACCESS  read-only
    STATUS  mandatory
    DESCRIPTION
           "The current alarm disable schedule for input 8."
    ::= { falconInput8  14 }

falconInput8DigOffLabel OBJECT-TYPE
    SYNTAX  DisplayString
    ACCESS  read-write
    STATUS  mandatory
    DESCRIPTION
           "A user-defined text string associated with Input Number 8.
           This string is used for digital off text.
           The text string is stored in non-volatile memory."
    ::= { falconInput8  15 }

falconInput9 OBJECT IDENTIFIER ::= { falconInputs 25 }

falconInput9State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 9.
            This variable is stored in non-volatile memory."
    ::= { falconInput9  1 }

falconInput9Reading OBJECT-TYPE
    SYNTAX  INTEGER (0..1)
    ACCESS  read-only
    STATUS  mandatory
    DESCRIPTION
           "The reading for input 9.
            The reading will be 1 (active) or 0 (inactive)"
    ::= { falconInput9  2 }

falconInput9Label OBJECT-TYPE
    SYNTAX  DisplayString
    ACCESS  read-write
    STATUS  mandatory
    DESCRIPTION
           "A user-defined text string associated with Input Number 9.
            The text string is stored in non-volatile memory."
    ::= { falconInput9  3 }

falconInput9RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput9  4 }

falconInput9Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput9  5 }

falconInput9Schedule OBJECT-TYPE
    SYNTAX  INTEGER {
    none(0),
    a(1),
    b(2)
}
    ACCESS  read-only
    STATUS  mandatory
    DESCRIPTION
           "The current alarm disable schedule for input 9."
    ::= { falconInput9  6 }

falconInput9DigOffLabel OBJECT-TYPE
    SYNTAX  DisplayString
    ACCESS  read-write
    STATUS  mandatory
    DESCRIPTION
           "A user-defined text string associated with Input Number 9.
           This string is used for digital off text.
           The text string is stored in non-volatile memory."
    ::= { falconInput9  7 }

falconInput10 OBJECT IDENTIFIER ::= { falconInputs 26 }

falconInput10State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 10.
            This variable is stored in non-volatile memory."
    ::= { falconInput10  1 }

falconInput10Reading OBJECT-TYPE
    SYNTAX  INTEGER (0..1)
    ACCESS  read-only
    STATUS  mandatory
    DESCRIPTION
           "The reading for input 10.
            The reading will be 1 (active) or 0 (inactive)"
    ::= { falconInput10  2 }

falconInput10Label OBJECT-TYPE
    SYNTAX  DisplayString
    ACCESS  read-write
    STATUS  mandatory
    DESCRIPTION
           "A user-defined text string associated with Input Number 10.
            The text string is stored in non-volatile memory."
    ::= { falconInput10  3 }

falconInput10RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput10  4 }

falconInput10Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput10  5 }

falconInput10Schedule OBJECT-TYPE
    SYNTAX  INTEGER {
    none(0),
    a(1),
    b(2)
}
    ACCESS  read-only
    STATUS  mandatory
    DESCRIPTION
           "The current alarm disable schedule for input 10."
    ::= { falconInput10  6 }

falconInput10DigOffLabel OBJECT-TYPE
    SYNTAX  DisplayString
    ACCESS  read-write
    STATUS  mandatory
    DESCRIPTION
           "A user-defined text string associated with Input Number 10.
           This string is used for digital off text.
           The text string is stored in non-volatile memory."
    ::= { falconInput10  7 }

falconInput11 OBJECT IDENTIFIER ::= { falconInputs 27 }

falconInput11State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 11.
            This variable is stored in non-volatile memory."
    ::= { falconInput11  1 }

falconInput11Reading OBJECT-TYPE
    SYNTAX  INTEGER (0..1)
    ACCESS  read-only
    STATUS  mandatory
    DESCRIPTION
           "The reading for input 11.
            The reading will be 1 (active) or 0 (inactive)"
    ::= { falconInput11  2 }

falconInput11Label OBJECT-TYPE
    SYNTAX  DisplayString
    ACCESS  read-write
    STATUS  mandatory
    DESCRIPTION
           "A user-defined text string associated with Input Number 11.
            The text string is stored in non-volatile memory."
    ::= { falconInput11  3 }

falconInput11RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput11  4 }

falconInput11Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput11  5 }

falconInput11Schedule OBJECT-TYPE
    SYNTAX  INTEGER {
    none(0),
    a(1),
    b(2)
}
    ACCESS  read-only
    STATUS  mandatory
    DESCRIPTION
           "The current alarm disable schedule for input 11."
    ::= { falconInput11  6 }

falconInput11DigOffLabel OBJECT-TYPE
    SYNTAX  DisplayString
    ACCESS  read-write
    STATUS  mandatory
    DESCRIPTION
           "A user-defined text string associated with Input Number 11.
           This string is used for digital off text.
           The text string is stored in non-volatile memory."
    ::= { falconInput11  7 }

falconInput12 OBJECT IDENTIFIER ::= { falconInputs 28 }

falconInput12State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 12.
            This variable is stored in non-volatile memory."
    ::= { falconInput12  1 }

falconInput12Reading OBJECT-TYPE
    SYNTAX  INTEGER (0..1)
    ACCESS  read-only
    STATUS  mandatory
    DESCRIPTION
           "The reading for input 12.
            The reading will be 1 (active) or 0 (inactive)"
    ::= { falconInput12  2 }

falconInput12Label OBJECT-TYPE
    SYNTAX  DisplayString
    ACCESS  read-write
    STATUS  mandatory
    DESCRIPTION
           "A user-defined text string associated with Input Number 12.
            The text string is stored in non-volatile memory."
    ::= { falconInput12  3 }

falconInput12RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput12  4 }

falconInput12Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput12  5 }

falconInput12Schedule OBJECT-TYPE
    SYNTAX  INTEGER {
    none(0),
    a(1),
    b(2)
}
    ACCESS  read-only
    STATUS  mandatory
    DESCRIPTION
           "The current alarm disable schedule for input 12."
    ::= { falconInput12  6 }

falconInput12DigOffLabel OBJECT-TYPE
    SYNTAX  DisplayString
    ACCESS  read-write
    STATUS  mandatory
    DESCRIPTION
           "A user-defined text string associated with Input Number 12.
           This string is used for digital off text.
           The text string is stored in non-volatile memory."
    ::= { falconInput12  7 }

falconInput13 OBJECT IDENTIFIER ::= { falconInputs 29 }

falconInput13State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 13.
            This variable is stored in non-volatile memory."
    ::= { falconInput13  1 }

falconInput13Reading OBJECT-TYPE
    SYNTAX  INTEGER (0..1)
    ACCESS  read-only
    STATUS  mandatory
    DESCRIPTION
           "The reading for input 13.
            The reading will be 1 (active) or 0 (inactive)"
    ::= { falconInput13  2 }

falconInput13Label OBJECT-TYPE
    SYNTAX  DisplayString
    ACCESS  read-write
    STATUS  mandatory
    DESCRIPTION
           "A user-defined text string associated with Input Number 13.
            The text string is stored in non-volatile memory."
    ::= { falconInput13  3 }

falconInput13RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput13  4 }

falconInput13Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput13  5 }

falconInput13Schedule OBJECT-TYPE
    SYNTAX  INTEGER {
    none(0),
    a(1),
    b(2)
}
    ACCESS  read-only
    STATUS  mandatory
    DESCRIPTION
           "The current alarm disable schedule for input 13."
    ::= { falconInput13  6 }

falconInput13DigOffLabel OBJECT-TYPE
    SYNTAX  DisplayString
    ACCESS  read-write
    STATUS  mandatory
    DESCRIPTION
           "A user-defined text string associated with Input Number 13.
           This string is used for digital off text.
           The text string is stored in non-volatile memory."
    ::= { falconInput13  7 }

falconInput14 OBJECT IDENTIFIER ::= { falconInputs 30 }

falconInput14State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 14.
            This variable is stored in non-volatile memory."
    ::= { falconInput14  1 }

falconInput14Reading OBJECT-TYPE
    SYNTAX  INTEGER (0..1)
    ACCESS  read-only
    STATUS  mandatory
    DESCRIPTION
           "The reading for input 14.
            The reading will be 1 (active) or 0 (inactive)"
    ::= { falconInput14  2 }

falconInput14Label OBJECT-TYPE
    SYNTAX  DisplayString
    ACCESS  read-write
    STATUS  mandatory
    DESCRIPTION
           "A user-defined text string associated with Input Number 14.
            The text string is stored in non-volatile memory."
    ::= { falconInput14  3 }

falconInput14RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput14  4 }

falconInput14Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput14  5 }

falconInput14Schedule OBJECT-TYPE
    SYNTAX  INTEGER {
    none(0),
    a(1),
    b(2)
}
    ACCESS  read-only
    STATUS  mandatory
    DESCRIPTION
           "The current alarm disable schedule for input 14."
    ::= { falconInput14  6 }

falconInput14DigOffLabel OBJECT-TYPE
    SYNTAX  DisplayString
    ACCESS  read-write
    STATUS  mandatory
    DESCRIPTION
           "A user-defined text string associated with Input Number 14.
           This string is used for digital off text.
           The text string is stored in non-volatile memory."
    ::= { falconInput14  7 }

falconInput15 OBJECT IDENTIFIER ::= { falconInputs 31 }

falconInput15State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 15.
            This variable is stored in non-volatile memory."
    ::= { falconInput15  1 }

falconInput15Reading OBJECT-TYPE
    SYNTAX  INTEGER (0..1)
    ACCESS  read-only
    STATUS  mandatory
    DESCRIPTION
           "The reading for input 15.
            The reading will be 1 (active) or 0 (inactive)"
    ::= { falconInput15  2 }

falconInput15Label OBJECT-TYPE
    SYNTAX  DisplayString
    ACCESS  read-write
    STATUS  mandatory
    DESCRIPTION
           "A user-defined text string associated with Input Number 15.
            The text string is stored in non-volatile memory."
    ::= { falconInput15  3 }

falconInput15RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput15  4 }

falconInput15Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput15  5 }

falconInput15Schedule OBJECT-TYPE
    SYNTAX  INTEGER {
    none(0),
    a(1),
    b(2)
}
    ACCESS  read-only
    STATUS  mandatory
    DESCRIPTION
           "The current alarm disable schedule for input 15."
    ::= { falconInput15  6 }

falconInput15DigOffLabel OBJECT-TYPE
    SYNTAX  DisplayString
    ACCESS  read-write
    STATUS  mandatory
    DESCRIPTION
           "A user-defined text string associated with Input Number 15.
           This string is used for digital off text.
           The text string is stored in non-volatile memory."
    ::= { falconInput15  7 }

falconInput16 OBJECT IDENTIFIER ::= { falconInputs 32 }

falconInput16State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 16.
            This variable is stored in non-volatile memory."
    ::= { falconInput16  1 }

falconInput16Reading OBJECT-TYPE
    SYNTAX  INTEGER (0..1)
    ACCESS  read-only
    STATUS  mandatory
    DESCRIPTION
           "The reading for input 16.
            The reading will be 1 (active) or 0 (inactive)"
    ::= { falconInput16  2 }

falconInput16Label OBJECT-TYPE
    SYNTAX  DisplayString
    ACCESS  read-write
    STATUS  mandatory
    DESCRIPTION
           "A user-defined text string associated with Input Number 16.
            The text string is stored in non-volatile memory."
    ::= { falconInput16  3 }

falconInput16RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput16  4 }

falconInput16Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput16  5 }

falconInput16Schedule OBJECT-TYPE
    SYNTAX  INTEGER {
    none(0),
    a(1),
    b(2)
}
    ACCESS  read-only
    STATUS  mandatory
    DESCRIPTION
           "The current alarm disable schedule for input 16."
    ::= { falconInput16  6 }

falconInput16DigOffLabel OBJECT-TYPE
    SYNTAX  DisplayString
    ACCESS  read-write
    STATUS  mandatory
    DESCRIPTION
           "A user-defined text string associated with Input Number 16.
           This string is used for digital off text.
           The text string is stored in non-volatile memory."
    ::= { falconInput16  7 }

falconInput17 OBJECT IDENTIFIER ::= { falconInputs 33 }

falconInput17State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 17.
            This variable is stored in non-volatile memory."
    ::= { falconInput17  1 }

falconInput17Reading OBJECT-TYPE
    SYNTAX  INTEGER (0..1)
    ACCESS  read-only
    STATUS  mandatory
    DESCRIPTION
           "The reading for input 17.
            The reading will be 1 (active) or 0 (inactive)"
    ::= { falconInput17  2 }

falconInput17Label OBJECT-TYPE
    SYNTAX  DisplayString
    ACCESS  read-write
    STATUS  mandatory
    DESCRIPTION
           "A user-defined text string associated with Input Number 17.
            The text string is stored in non-volatile memory."
    ::= { falconInput17  3 }

falconInput17RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput17  4 }

falconInput17Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput17  5 }

falconInput17Schedule OBJECT-TYPE
    SYNTAX  INTEGER {
    none(0),
    a(1),
    b(2)
}
    ACCESS  read-only
    STATUS  mandatory
    DESCRIPTION
           "The current alarm disable schedule for input 17."
    ::= { falconInput17  6 }

falconInput17DigOffLabel OBJECT-TYPE
    SYNTAX  DisplayString
    ACCESS  read-write
    STATUS  mandatory
    DESCRIPTION
           "A user-defined text string associated with Input Number 17.
           This string is used for digital off text.
           The text string is stored in non-volatile memory."
    ::= { falconInput17  7 }

falconInput18 OBJECT IDENTIFIER ::= { falconInputs 34 }

falconInput18State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 18.
            This variable is stored in non-volatile memory."
    ::= { falconInput18  1 }

falconInput18Reading OBJECT-TYPE
    SYNTAX  INTEGER (0..1)
    ACCESS  read-only
    STATUS  mandatory
    DESCRIPTION
           "The reading for input 18.
            The reading will be 1 (active) or 0 (inactive)"
    ::= { falconInput18  2 }

falconInput18Label OBJECT-TYPE
    SYNTAX  DisplayString
    ACCESS  read-write
    STATUS  mandatory
    DESCRIPTION
           "A user-defined text string associated with Input Number 18.
            The text string is stored in non-volatile memory."
    ::= { falconInput18  3 }

falconInput18RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput18  4 }

falconInput18Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput18  5 }

falconInput18Schedule OBJECT-TYPE
    SYNTAX  INTEGER {
    none(0),
    a(1),
    b(2)
}
    ACCESS  read-only
    STATUS  mandatory
    DESCRIPTION
           "The current alarm disable schedule for input 18."
    ::= { falconInput18  6 }

falconInput18DigOffLabel OBJECT-TYPE
    SYNTAX  DisplayString
    ACCESS  read-write
    STATUS  mandatory
    DESCRIPTION
           "A user-defined text string associated with Input Number 18.
           This string is used for digital off text.
           The text string is stored in non-volatile memory."
    ::= { falconInput18  7 }

falconInput19 OBJECT IDENTIFIER ::= { falconInputs 35 }

falconInput19State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 19.
            This variable is stored in non-volatile memory."
    ::= { falconInput19  1 }

falconInput19Reading OBJECT-TYPE
    SYNTAX  INTEGER (0..1)
    ACCESS  read-only
    STATUS  mandatory
    DESCRIPTION
           "The reading for input 19.
            The reading will be 1 (active) or 0 (inactive)"
    ::= { falconInput19  2 }

falconInput19Label OBJECT-TYPE
    SYNTAX  DisplayString
    ACCESS  read-write
    STATUS  mandatory
    DESCRIPTION
           "A user-defined text string associated with Input Number 19.
            The text string is stored in non-volatile memory."
    ::= { falconInput19  3 }

falconInput19RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput19  4 }

falconInput19Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput19  5 }

falconInput19Schedule OBJECT-TYPE
    SYNTAX  INTEGER {
    none(0),
    a(1),
    b(2)
}
    ACCESS  read-only
    STATUS  mandatory
    DESCRIPTION
           "The current alarm disable schedule for input 19."
    ::= { falconInput19  6 }

falconInput19DigOffLabel OBJECT-TYPE
    SYNTAX  DisplayString
    ACCESS  read-write
    STATUS  mandatory
    DESCRIPTION
           "A user-defined text string associated with Input Number 19.
           This string is used for digital off text.
           The text string is stored in non-volatile memory."
    ::= { falconInput19  7 }

falconInput20 OBJECT IDENTIFIER ::= { falconInputs 36 }

falconInput20State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 20.
            This variable is stored in non-volatile memory."
    ::= { falconInput20  1 }

falconInput20Reading OBJECT-TYPE
    SYNTAX  INTEGER (0..1)
    ACCESS  read-only
    STATUS  mandatory
    DESCRIPTION
           "The reading for input 20.
            The reading will be 1 (active) or 0 (inactive)"
    ::= { falconInput20  2 }

falconInput20Label OBJECT-TYPE
    SYNTAX  DisplayString
    ACCESS  read-write
    STATUS  mandatory
    DESCRIPTION
           "A user-defined text string associated with Input Number 20.
            The text string is stored in non-volatile memory."
    ::= { falconInput20  3 }

falconInput20RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput20  4 }

falconInput20Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput20  5 }

falconInput20Schedule OBJECT-TYPE
    SYNTAX  INTEGER {
    none(0),
    a(1),
    b(2)
}
    ACCESS  read-only
    STATUS  mandatory
    DESCRIPTION
           "The current alarm disable schedule for input 20."
    ::= { falconInput20  6 }

falconInput20DigOffLabel OBJECT-TYPE
    SYNTAX  DisplayString
    ACCESS  read-write
    STATUS  mandatory
    DESCRIPTION
           "A user-defined text string associated with Input Number 20.
           This string is used for digital off text.
           The text string is stored in non-volatile memory."
    ::= { falconInput20  7 }

falconInput21 OBJECT IDENTIFIER ::= { falconInputs 37 }

falconInput21State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 21.
            This variable is stored in non-volatile memory."
    ::= { falconInput21  1 }

falconInput21Reading OBJECT-TYPE
    SYNTAX  INTEGER (0..1)
    ACCESS  read-only
    STATUS  mandatory
    DESCRIPTION
           "The reading for input 21.
            The reading will be 1 (active) or 0 (inactive)"
    ::= { falconInput21  2 }

falconInput21Label OBJECT-TYPE
    SYNTAX  DisplayString
    ACCESS  read-write
    STATUS  mandatory
    DESCRIPTION
           "A user-defined text string associated with Input Number 21.
            The text string is stored in non-volatile memory."
    ::= { falconInput21  3 }

falconInput21RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput21  4 }

falconInput21Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput21  5 }

falconInput21Schedule OBJECT-TYPE
    SYNTAX  INTEGER {
    none(0),
    a(1),
    b(2)
}
    ACCESS  read-only
    STATUS  mandatory
    DESCRIPTION
           "The current alarm disable schedule for input 21."
    ::= { falconInput21  6 }

falconInput21DigOffLabel OBJECT-TYPE
    SYNTAX  DisplayString
    ACCESS  read-write
    STATUS  mandatory
    DESCRIPTION
           "A user-defined text string associated with Input Number 21.
           This string is used for digital off text.
           The text string is stored in non-volatile memory."
    ::= { falconInput21  7 }

falconInput22 OBJECT IDENTIFIER ::= { falconInputs 38 }

falconInput22State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 22.
            This variable is stored in non-volatile memory."
    ::= { falconInput22  1 }

falconInput22Reading OBJECT-TYPE
    SYNTAX  INTEGER (0..1)
    ACCESS  read-only
    STATUS  mandatory
    DESCRIPTION
           "The reading for input 22.
            The reading will be 1 (active) or 0 (inactive)"
    ::= { falconInput22  2 }

falconInput22Label OBJECT-TYPE
    SYNTAX  DisplayString
    ACCESS  read-write
    STATUS  mandatory
    DESCRIPTION
           "A user-defined text string associated with Input Number 22.
            The text string is stored in non-volatile memory."
    ::= { falconInput22  3 }

falconInput22RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput22  4 }

falconInput22Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput22  5 }

falconInput22Schedule OBJECT-TYPE
    SYNTAX  INTEGER {
    none(0),
    a(1),
    b(2)
}
    ACCESS  read-only
    STATUS  mandatory
    DESCRIPTION
           "The current alarm disable schedule for input 22."
    ::= { falconInput22  6 }

falconInput22DigOffLabel OBJECT-TYPE
    SYNTAX  DisplayString
    ACCESS  read-write
    STATUS  mandatory
    DESCRIPTION
           "A user-defined text string associated with Input Number 22.
           This string is used for digital off text.
           The text string is stored in non-volatile memory."
    ::= { falconInput22  7 }

falconInput23 OBJECT IDENTIFIER ::= { falconInputs 39 }

falconInput23State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 23.
            This variable is stored in non-volatile memory."
    ::= { falconInput23  1 }

falconInput23Reading OBJECT-TYPE
    SYNTAX  INTEGER (0..1)
    ACCESS  read-only
    STATUS  mandatory
    DESCRIPTION
           "The reading for input 23.
            The reading will be 1 (active) or 0 (inactive)"
    ::= { falconInput23  2 }

falconInput23Label OBJECT-TYPE
    SYNTAX  DisplayString
    ACCESS  read-write
    STATUS  mandatory
    DESCRIPTION
           "A user-defined text string associated with Input Number 23.
            The text string is stored in non-volatile memory."
    ::= { falconInput23  3 }

falconInput23RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput23  4 }

falconInput23Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput23  5 }

falconInput23Schedule OBJECT-TYPE
    SYNTAX  INTEGER {
    none(0),
    a(1),
    b(2)
}
    ACCESS  read-only
    STATUS  mandatory
    DESCRIPTION
           "The current alarm disable schedule for input 23."
    ::= { falconInput23  6 }

falconInput23DigOffLabel OBJECT-TYPE
    SYNTAX  DisplayString
    ACCESS  read-write
    STATUS  mandatory
    DESCRIPTION
           "A user-defined text string associated with Input Number 23.
           This string is used for digital off text.
           The text string is stored in non-volatile memory."
    ::= { falconInput23  7 }

falconInput24 OBJECT IDENTIFIER ::= { falconInputs 40 }

falconInput24State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 24.
            This variable is stored in non-volatile memory."
    ::= { falconInput24  1 }

falconInput24Reading OBJECT-TYPE
    SYNTAX  INTEGER (0..1)
    ACCESS  read-only
    STATUS  mandatory
    DESCRIPTION
           "The reading for input 24.
            The reading will be 1 (active) or 0 (inactive)"
    ::= { falconInput24  2 }

falconInput24Label OBJECT-TYPE
    SYNTAX  DisplayString
    ACCESS  read-write
    STATUS  mandatory
    DESCRIPTION
           "A user-defined text string associated with Input Number 24.
            The text string is stored in non-volatile memory."
    ::= { falconInput24  3 }

falconInput24RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput24  4 }

falconInput24Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput24  5 }

falconInput24Schedule OBJECT-TYPE
    SYNTAX  INTEGER {
    none(0),
    a(1),
    b(2)
}
    ACCESS  read-only
    STATUS  mandatory
    DESCRIPTION
           "The current alarm disable schedule for input 24."
    ::= { falconInput24  6 }

falconInput24DigOffLabel OBJECT-TYPE
    SYNTAX  DisplayString
    ACCESS  read-write
    STATUS  mandatory
    DESCRIPTION
           "A user-defined text string associated with Input Number 24.
           This string is used for digital off text.
           The text string is stored in non-volatile memory."
    ::= { falconInput24  7 }

falconInput25 OBJECT IDENTIFIER ::= { falconInputs 41 }

falconInput25State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 25.
            This variable is stored in non-volatile memory."
    ::= { falconInput25  1 }

falconInput25Reading OBJECT-TYPE
    SYNTAX  INTEGER (0..1)
    ACCESS  read-only
    STATUS  mandatory
    DESCRIPTION
           "The reading for input 25.
            The reading will be 1 (active) or 0 (inactive)"
    ::= { falconInput25  2 }

falconInput25Label OBJECT-TYPE
    SYNTAX  DisplayString
    ACCESS  read-write
    STATUS  mandatory
    DESCRIPTION
           "A user-defined text string associated with Input Number 25.
            The text string is stored in non-volatile memory."
    ::= { falconInput25  3 }

falconInput25RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput25  4 }

falconInput25Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput25  5 }

falconInput25Schedule OBJECT-TYPE
    SYNTAX  INTEGER {
    none(0),
    a(1),
    b(2)
}
    ACCESS  read-only
    STATUS  mandatory
    DESCRIPTION
           "The current alarm disable schedule for input 25."
    ::= { falconInput25  6 }

falconInput25DigOffLabel OBJECT-TYPE
    SYNTAX  DisplayString
    ACCESS  read-write
    STATUS  mandatory
    DESCRIPTION
           "A user-defined text string associated with Input Number 25.
           This string is used for digital off text.
           The text string is stored in non-volatile memory."
    ::= { falconInput25  7 }

falconInput26 OBJECT IDENTIFIER ::= { falconInputs 42 }

falconInput26State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 26.
            This variable is stored in non-volatile memory."
    ::= { falconInput26  1 }

falconInput26Reading OBJECT-TYPE
    SYNTAX  INTEGER (0..1)
    ACCESS  read-only
    STATUS  mandatory
    DESCRIPTION
           "The reading for input 26.
            The reading will be 1 (active) or 0 (inactive)"
    ::= { falconInput26  2 }

falconInput26Label OBJECT-TYPE
    SYNTAX  DisplayString
    ACCESS  read-write
    STATUS  mandatory
    DESCRIPTION
           "A user-defined text string associated with Input Number 26.
            The text string is stored in non-volatile memory."
    ::= { falconInput26  3 }

falconInput26RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput26  4 }

falconInput26Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput26  5 }

falconInput26Schedule OBJECT-TYPE
    SYNTAX  INTEGER {
    none(0),
    a(1),
    b(2)
}
    ACCESS  read-only
    STATUS  mandatory
    DESCRIPTION
           "The current alarm disable schedule for input 26."
    ::= { falconInput26  6 }

falconInput26DigOffLabel OBJECT-TYPE
    SYNTAX  DisplayString
    ACCESS  read-write
    STATUS  mandatory
    DESCRIPTION
           "A user-defined text string associated with Input Number 26.
           This string is used for digital off text.
           The text string is stored in non-volatile memory."
    ::= { falconInput26  7 }

falconInput27 OBJECT IDENTIFIER ::= { falconInputs 43 }

falconInput27State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 27.
            This variable is stored in non-volatile memory."
    ::= { falconInput27  1 }

falconInput27Reading OBJECT-TYPE
    SYNTAX  INTEGER (0..1)
    ACCESS  read-only
    STATUS  mandatory
    DESCRIPTION
           "The reading for input 27.
            The reading will be 1 (active) or 0 (inactive)"
    ::= { falconInput27  2 }

falconInput27Label OBJECT-TYPE
    SYNTAX  DisplayString
    ACCESS  read-write
    STATUS  mandatory
    DESCRIPTION
           "A user-defined text string associated with Input Number 27.
            The text string is stored in non-volatile memory."
    ::= { falconInput27  3 }

falconInput27RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput27  4 }

falconInput27Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput27  5 }

falconInput27Schedule OBJECT-TYPE
    SYNTAX  INTEGER {
    none(0),
    a(1),
    b(2)
}
    ACCESS  read-only
    STATUS  mandatory
    DESCRIPTION
           "The current alarm disable schedule for input 27."
    ::= { falconInput27  6 }

falconInput27DigOffLabel OBJECT-TYPE
    SYNTAX  DisplayString
    ACCESS  read-write
    STATUS  mandatory
    DESCRIPTION
           "A user-defined text string associated with Input Number 27.
           This string is used for digital off text.
           The text string is stored in non-volatile memory."
    ::= { falconInput27  7 }

falconInput28 OBJECT IDENTIFIER ::= { falconInputs 44 }

falconInput28State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 28.
            This variable is stored in non-volatile memory."
    ::= { falconInput28  1 }

falconInput28Reading OBJECT-TYPE
    SYNTAX  INTEGER (0..1)
    ACCESS  read-only
    STATUS  mandatory
    DESCRIPTION
           "The reading for input 28.
            The reading will be 1 (active) or 0 (inactive)"
    ::= { falconInput28  2 }

falconInput28Label OBJECT-TYPE
    SYNTAX  DisplayString
    ACCESS  read-write
    STATUS  mandatory
    DESCRIPTION
           "A user-defined text string associated with Input Number 28.
            The text string is stored in non-volatile memory."
    ::= { falconInput28  3 }

falconInput28RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput28  4 }

falconInput28Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput28  5 }

falconInput28Schedule OBJECT-TYPE
    SYNTAX  INTEGER {
    none(0),
    a(1),
    b(2)
}
    ACCESS  read-only
    STATUS  mandatory
    DESCRIPTION
           "The current alarm disable schedule for input 28."
    ::= { falconInput28  6 }

falconInput28DigOffLabel OBJECT-TYPE
    SYNTAX  DisplayString
    ACCESS  read-write
    STATUS  mandatory
    DESCRIPTION
           "A user-defined text string associated with Input Number 28.
           This string is used for digital off text.
           The text string is stored in non-volatile memory."
    ::= { falconInput28  7 }

falconInput29 OBJECT IDENTIFIER ::= { falconInputs 45 }

falconInput29State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 29.
            This variable is stored in non-volatile memory."
    ::= { falconInput29  1 }

falconInput29Reading OBJECT-TYPE
    SYNTAX  INTEGER (0..1)
    ACCESS  read-only
    STATUS  mandatory
    DESCRIPTION
           "The reading for input 29.
            The reading will be 1 (active) or 0 (inactive)"
    ::= { falconInput29  2 }

falconInput29Label OBJECT-TYPE
    SYNTAX  DisplayString
    ACCESS  read-write
    STATUS  mandatory
    DESCRIPTION
           "A user-defined text string associated with Input Number 29.
            The text string is stored in non-volatile memory."
    ::= { falconInput29  3 }

falconInput29RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput29  4 }

falconInput29Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput29  5 }

falconInput29Schedule OBJECT-TYPE
    SYNTAX  INTEGER {
    none(0),
    a(1),
    b(2)
}
    ACCESS  read-only
    STATUS  mandatory
    DESCRIPTION
           "The current alarm disable schedule for input 29."
    ::= { falconInput29  6 }

falconInput29DigOffLabel OBJECT-TYPE
    SYNTAX  DisplayString
    ACCESS  read-write
    STATUS  mandatory
    DESCRIPTION
           "A user-defined text string associated with Input Number 29.
           This string is used for digital off text.
           The text string is stored in non-volatile memory."
    ::= { falconInput29  7 }

falconInput30 OBJECT IDENTIFIER ::= { falconInputs 46 }

falconInput30State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 30.
            This variable is stored in non-volatile memory."
    ::= { falconInput30  1 }

falconInput30Reading OBJECT-TYPE
    SYNTAX  INTEGER (0..1)
    ACCESS  read-only
    STATUS  mandatory
    DESCRIPTION
           "The reading for input 30.
            The reading will be 1 (active) or 0 (inactive)"
    ::= { falconInput30  2 }

falconInput30Label OBJECT-TYPE
    SYNTAX  DisplayString
    ACCESS  read-write
    STATUS  mandatory
    DESCRIPTION
           "A user-defined text string associated with Input Number 30.
            The text string is stored in non-volatile memory."
    ::= { falconInput30  3 }

falconInput30RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput30  4 }

falconInput30Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput30  5 }

falconInput30Schedule OBJECT-TYPE
    SYNTAX  INTEGER {
    none(0),
    a(1),
    b(2)
}
    ACCESS  read-only
    STATUS  mandatory
    DESCRIPTION
           "The current alarm disable schedule for input 30."
    ::= { falconInput30  6 }

falconInput30DigOffLabel OBJECT-TYPE
    SYNTAX  DisplayString
    ACCESS  read-write
    STATUS  mandatory
    DESCRIPTION
           "A user-defined text string associated with Input Number 30.
           This string is used for digital off text.
           The text string is stored in non-volatile memory."
    ::= { falconInput30  7 }

falconInput31 OBJECT IDENTIFIER ::= { falconInputs 47 }

falconInput31State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 31.
            This variable is stored in non-volatile memory."
    ::= { falconInput31  1 }

falconInput31Reading OBJECT-TYPE
    SYNTAX  INTEGER (0..1)
    ACCESS  read-only
    STATUS  mandatory
    DESCRIPTION
           "The reading for input 31.
            The reading will be 1 (active) or 0 (inactive)"
    ::= { falconInput31  2 }

falconInput31Label OBJECT-TYPE
    SYNTAX  DisplayString
    ACCESS  read-write
    STATUS  mandatory
    DESCRIPTION
           "A user-defined text string associated with Input Number 31.
            The text string is stored in non-volatile memory."
    ::= { falconInput31  3 }

falconInput31RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput31  4 }

falconInput31Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput31  5 }

falconInput31Schedule OBJECT-TYPE
    SYNTAX  INTEGER {
    none(0),
    a(1),
    b(2)
}
    ACCESS  read-only
    STATUS  mandatory
    DESCRIPTION
           "The current alarm disable schedule for input 31."
    ::= { falconInput31  6 }

falconInput31DigOffLabel OBJECT-TYPE
    SYNTAX  DisplayString
    ACCESS  read-write
    STATUS  mandatory
    DESCRIPTION
           "A user-defined text string associated with Input Number 31.
           This string is used for digital off text.
           The text string is stored in non-volatile memory."
    ::= { falconInput31  7 }

falconInput32 OBJECT IDENTIFIER ::= { falconInputs 48 }

falconInput32State OBJECT-TYPE
    SYNTAX  INTEGER {
    notInstalled(1),
    digitalNOInstalled(3),
    digitalNCInstalled(4),
         digitalSTInstalled(5)
}
    ACCESS  read-write
    STATUS  mandatory
    DESCRIPTION
           "The state of use of Input Number 32.
            This variable is stored in non-volatile memory."
    ::= { falconInput32  1 }

falconInput32Reading OBJECT-TYPE
    SYNTAX  INTEGER (0..1)
    ACCESS  read-only
    STATUS  mandatory
    DESCRIPTION
           "The reading for input 32.
            The reading will be 1 (active) or 0 (inactive)"
    ::= { falconInput32  2 }

falconInput32Label OBJECT-TYPE
    SYNTAX  DisplayString
    ACCESS  read-write
    STATUS  mandatory
    DESCRIPTION
           "A user-defined text string associated with Input Number 32.
            The text string is stored in non-volatile memory."
    ::= { falconInput32  3 }

falconInput32RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput32  4 }

falconInput32Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput32  5 }

falconInput32Schedule OBJECT-TYPE
    SYNTAX  INTEGER {
    none(0),
    a(1),
    b(2)
}
    ACCESS  read-only
    STATUS  mandatory
    DESCRIPTION
           "The current alarm disable schedule for input 32."
    ::= { falconInput32  6 }

falconInput32DigOffLabel OBJECT-TYPE
    SYNTAX  DisplayString
    ACCESS  read-write
    STATUS  mandatory
    DESCRIPTION
           "A user-defined text string associated with Input Number 32.
           This string is used for digital off text.
           The text string is stored in non-volatile memory."
    ::= { falconInput32  7 }

falconOutputs OBJECT IDENTIFIER ::= { falconMIB  4 }

falconRelay1 OBJECT IDENTIFIER ::= { falconOutputs 1 }

falconRelay1State OBJECT-TYPE
    SYNTAX  INTEGER {
    normallyOff(1),
    normallyOn(2),
    forceOn(3),
    forceOff(4),
    keypadControlled(5)
}
    ACCESS  read-write
    STATUS  mandatory
    DESCRIPTION
           "The state of use of Relay Number 1. The relay can be
            set for normally open or closed. The relay can be forced
            to an on or off condition, or controlled by the keypad.
            This variable is stored in non-volatile memory."
    ::= { falconRelay1  1 }

falconRelay1Status OBJECT-TYPE
    SYNTAX  INTEGER {
    normalOff(1),
    normalOn(2),
    forcedOn(3),
    forcedOff(4),
    keycodeActive(5),
    alarmedActive(6),
    scheduledActive(7)
}
    ACCESS  read-only
    STATUS  mandatory
    DESCRIPTION
           "The current status for relay 1."
    ::= { falconRelay1  2 }

falconRelay1Label OBJECT-TYPE
    SYNTAX  DisplayString
    ACCESS  read-write
    STATUS  mandatory
    DESCRIPTION
           "A user-defined text string associated with Relay Number 1.
            The text string is stored in non-volatile memory."
    ::= { falconRelay1  3 }

falconRelay1Time OBJECT-TYPE
    SYNTAX  INTEGER (-2147483648..2147483647)
    ACCESS read-write
    STATUS     mandatory
    DESCRIPTION
        "The number of seconds the relay will be activated.
         Set this to -1 for indefinitely."
    ::= { falconRelay1  4 }

falconRelay1Schedule OBJECT-TYPE
    SYNTAX  INTEGER {
    none(0),
    a(1),
    b(2)
}
    ACCESS  read-only
    STATUS  mandatory
    DESCRIPTION
           "The current schedule for relay 1."
    ::= { falconRelay1  5 }

falconRelay2 OBJECT IDENTIFIER ::= { falconOutputs 2 }

falconRelay2State OBJECT-TYPE
    SYNTAX  INTEGER {
    normallyOff(1),
    normallyOn(2),
    forceOn(3),
    forceOff(4),
    keypadControlled(5)
}
    ACCESS  read-write
    STATUS  mandatory
    DESCRIPTION
           "The state of use of Relay Number 2. The relay can be
            set for normally open or closed. The relay can be forced
            to an on or off condition, or controlled by the keypad.
            This variable is stored in non-volatile memory."
    ::= { falconRelay2  1 }

falconRelay2Status OBJECT-TYPE
    SYNTAX  INTEGER {
    normalOff(1),
    normalOn(2),
    forcedOn(3),
    forcedOff(4),
    keycodeActive(5),
    alarmedActive(6),
    scheduledActive(7)
}
    ACCESS  read-only
    STATUS  mandatory
    DESCRIPTION
           "The current status for relay 2."
    ::= { falconRelay2  2 }

falconRelay2Label OBJECT-TYPE
    SYNTAX  DisplayString
    ACCESS  read-write
    STATUS  mandatory
    DESCRIPTION
           "A user-defined text string associated with Relay Number 2.
            The text string is stored in non-volatile memory."
    ::= { falconRelay2  3 }

falconRelay2Time OBJECT-TYPE
    SYNTAX  INTEGER (-2147483648..2147483647)
    ACCESS read-write
    STATUS     mandatory
    DESCRIPTION
        "The number of seconds the relay will be activated.
         Set this to -1 for indefinitely."
    ::= { falconRelay2  4 }

falconRelay2Schedule OBJECT-TYPE
    SYNTAX  INTEGER {
    none(0),
    a(1),
    b(2)
}
    ACCESS  read-only
    STATUS  mandatory
    DESCRIPTION
           "The current schedule for relay 2."
    ::= { falconRelay2  5 }

falconAlarms OBJECT IDENTIFIER ::= { falconMIB  5 }

falconAlarmsPresent OBJECT-TYPE
    SYNTAX     Gauge
    ACCESS     read-only
    STATUS     mandatory
    DESCRIPTION
        "The present number of active alarm conditions."
    ::= { falconAlarms 1 }

falconAlarmTable OBJECT-TYPE
    SYNTAX     SEQUENCE OF FalconAlarmEntry
    ACCESS     not-accessible
    STATUS     mandatory
    DESCRIPTION
       "A list of alarm table entries.  The table contains
        zero, one, or many rows at any moment, depending upon
        the number of alarm conditions in effect.  The table
        is initially empty at agent startup.  The agent
        creates a row in the table each time a condition is
        detected and deletes that row when that condition no
        longer pertains.  The agent creates the first row with
        falconAlarmId equal to 1, and increments the value of
        falconAlarmId each time a new row is created, wrapping to
        the first free value greater than or equal to 1 when
        the maximum value of falconAlarmId would otherwise be
        exceeded.  Consequently, after multiple operations,
        the table may become sparse, e.g., containing entries
        for rows 95, 100, 101, and 203 and the entries should
        not be assumed to be in chronological order because
        falconAlarmId might have wrapped.

        Alarms are named by an AutonomousType (OBJECT
        IDENTIFIER), falconAlarmDescr, to allow a single table to
        reflect well known alarms plus alarms defined by a
        particular implementation, i.e., as documented in the
        private enterprise MIB definition for the device.  No
        two rows will have the same value of falconAlarmDescr,
        since alarms define conditions.  In order to meet this
        requirement, care should be taken in the definition of
        alarm conditions to insure that a system cannot enter
        the same condition multiple times simultaneously.

        The number of rows in the table at any given time is
        reflected by the value of falconAlarmsPresent."
    ::= { falconAlarms 2 }

falconAlarmEntry OBJECT-TYPE
    SYNTAX     FalconAlarmEntry
    ACCESS     not-accessible
    STATUS     mandatory
    DESCRIPTION
         "An entry containing information applicable to a
         particular alarm."
   INDEX { falconAlarmId }
   ::= { falconAlarmTable 1 }

FalconAlarmEntry ::= SEQUENCE {
    falconAlarmId          PositiveInteger,
    falconAlarmDescr       OBJECT IDENTIFIER
}

falconAlarmId OBJECT-TYPE
    SYNTAX     PositiveInteger
    ACCESS     not-accessible
    STATUS     mandatory
    DESCRIPTION
         "A unique identifier for an alarm condition.  This
          value must remain constant."
    ::= { falconAlarmEntry 1 }

falconAlarmDescr OBJECT-TYPE
    SYNTAX     OBJECT IDENTIFIER
    ACCESS     read-only
    STATUS     mandatory
    DESCRIPTION
        "A reference to an alarm description object.  The
         object referenced should not be accessible, but rather
         be used to provide a unique description of the alarm
         condition."
    ::= { falconAlarmEntry 2 }

--
-- Well known alarm conditions.
--

falconWellKnownAlarms    OBJECT IDENTIFIER ::= { falconAlarms 3 }

falconInput1HighAlarm OBJECT-TYPE
    SYNTAX  OBJECT IDENTIFIER
    ACCESS  read-only
    STATUS  mandatory
    DESCRIPTION
        "The reading for sensor 1 has reached the high limit
        value."
    ::= { falconWellKnownAlarms  1 }

falconInput1LowAlarm OBJECT-TYPE
    SYNTAX  OBJECT IDENTIFIER
    ACCESS  read-only
    STATUS  mandatory
    DESCRIPTION
        "The reading for sensor 1 has reached the low limit
        value."
    ::= { falconWellKnownAlarms  2 }

falconInput1High2Alarm OBJECT-TYPE
    SYNTAX  OBJECT IDENTIFIER
    ACCESS  read-only
    STATUS  mandatory
    DESCRIPTION
        "The reading for sensor 1 has reached the high limit
        value."
    ::= { falconWellKnownAlarms  3 }

falconInput1Low2Alarm OBJECT-TYPE
    SYNTAX  OBJECT IDENTIFIER
    ACCESS  read-only
    STATUS  mandatory
    DESCRIPTION
        "The reading for sensor 1 has reached the low limit
        value."
    ::= { falconWellKnownAlarms  4 }

falconInput2HighAlarm OBJECT-TYPE
    SYNTAX  OBJECT IDENTIFIER
    ACCESS  read-only
    STATUS  mandatory
    DESCRIPTION
        "The reading for sensor 2 has reached the high limit
        value."
    ::= { falconWellKnownAlarms  5 }

falconInput2LowAlarm OBJECT-TYPE
    SYNTAX  OBJECT IDENTIFIER
    ACCESS  read-only
    STATUS  mandatory
    DESCRIPTION
        "The reading for sensor 2 has reached the low limit
        value."
    ::= { falconWellKnownAlarms  6 }

falconInput2High2Alarm OBJECT-TYPE
    SYNTAX  OBJECT IDENTIFIER
    ACCESS  read-only
    STATUS  mandatory
    DESCRIPTION
        "The reading for sensor 2 has reached the high limit
        value."
    ::= { falconWellKnownAlarms  7 }

falconInput2Low2Alarm OBJECT-TYPE
    SYNTAX  OBJECT IDENTIFIER
    ACCESS  read-only
    STATUS  mandatory
    DESCRIPTION
        "The reading for sensor 2 has reached the low limit
        value."
    ::= { falconWellKnownAlarms  8 }

falconInput3HighAlarm OBJECT-TYPE
    SYNTAX  OBJECT IDENTIFIER
    ACCESS  read-only
    STATUS  mandatory
    DESCRIPTION
        "The reading for sensor 3 has reached the high limit
        value."
    ::= { falconWellKnownAlarms  9 }

falconInput3LowAlarm OBJECT-TYPE
    SYNTAX  OBJECT IDENTIFIER
    ACCESS  read-only
    STATUS  mandatory
    DESCRIPTION
        "The reading for sensor 3 has reached the low limit
        value."
    ::= { falconWellKnownAlarms  10 }

falconInput3High2Alarm OBJECT-TYPE
    SYNTAX  OBJECT IDENTIFIER
    ACCESS  read-only
    STATUS  mandatory
    DESCRIPTION
        "The reading for sensor 3 has reached the high limit
        value."
    ::= { falconWellKnownAlarms  11 }

falconInput3Low2Alarm OBJECT-TYPE
    SYNTAX  OBJECT IDENTIFIER
    ACCESS  read-only
    STATUS  mandatory
    DESCRIPTION
        "The reading for sensor 3 has reached the low limit
        value."
    ::= { falconWellKnownAlarms  12 }

falconInput4HighAlarm OBJECT-TYPE
    SYNTAX  OBJECT IDENTIFIER
    ACCESS  read-only
    STATUS  mandatory
    DESCRIPTION
        "The reading for sensor 4 has reached the high limit
        value."
    ::= { falconWellKnownAlarms  13 }

falconInput4LowAlarm OBJECT-TYPE
    SYNTAX  OBJECT IDENTIFIER
    ACCESS  read-only
    STATUS  mandatory
    DESCRIPTION
        "The reading for sensor 4 has reached the low limit
        value."
    ::= { falconWellKnownAlarms  14 }

falconInput4High2Alarm OBJECT-TYPE
    SYNTAX  OBJECT IDENTIFIER
    ACCESS  read-only
    STATUS  mandatory
    DESCRIPTION
        "The reading for sensor 4 has reached the high limit
        value."
    ::= { falconWellKnownAlarms  15 }

falconInput4Low2Alarm OBJECT-TYPE
    SYNTAX  OBJECT IDENTIFIER
    ACCESS  read-only
    STATUS  mandatory
    DESCRIPTION
        "The reading for sensor 4 has reached the low limit
        value."
    ::= { falconWellKnownAlarms  16 }

falconInput5HighAlarm OBJECT-TYPE
    SYNTAX  OBJECT IDENTIFIER
    ACCESS  read-only
    STATUS  mandatory
    DESCRIPTION
        "The reading for sensor 5 has reached the high limit
        value."
    ::= { falconWellKnownAlarms  17 }

falconInput5LowAlarm OBJECT-TYPE
    SYNTAX  OBJECT IDENTIFIER
    ACCESS  read-only
    STATUS  mandatory
    DESCRIPTION
        "The reading for sensor 5 has reached the low limit
        value."
    ::= { falconWellKnownAlarms  18 }

falconInput5High2Alarm OBJECT-TYPE
    SYNTAX  OBJECT IDENTIFIER
    ACCESS  read-only
    STATUS  mandatory
    DESCRIPTION
        "The reading for sensor 5 has reached the high limit
        value."
    ::= { falconWellKnownAlarms  19 }

falconInput5Low2Alarm OBJECT-TYPE
    SYNTAX  OBJECT IDENTIFIER
    ACCESS  read-only
    STATUS  mandatory
    DESCRIPTION
        "The reading for sensor 5 has reached the low limit
        value."
    ::= { falconWellKnownAlarms  20 }

falconInput6HighAlarm OBJECT-TYPE
    SYNTAX  OBJECT IDENTIFIER
    ACCESS  read-only
    STATUS  mandatory
    DESCRIPTION
        "The reading for sensor 6 has reached the high limit
        value."
    ::= { falconWellKnownAlarms  21 }

falconInput6LowAlarm OBJECT-TYPE
    SYNTAX  OBJECT IDENTIFIER
    ACCESS  read-only
    STATUS  mandatory
    DESCRIPTION
        "The reading for sensor 6 has reached the low limit
        value."
    ::= { falconWellKnownAlarms  22 }

falconInput6High2Alarm OBJECT-TYPE
    SYNTAX  OBJECT IDENTIFIER
    ACCESS  read-only
    STATUS  mandatory
    DESCRIPTION
        "The reading for sensor 6 has reached the high limit
        value."
    ::= { falconWellKnownAlarms  23 }

falconInput6Low2Alarm OBJECT-TYPE
    SYNTAX  OBJECT IDENTIFIER
    ACCESS  read-only
    STATUS  mandatory
    DESCRIPTION
        "The reading for sensor 6 has reached the low limit
        value."
    ::= { falconWellKnownAlarms  24 }

falconInput7HighAlarm OBJECT-TYPE
    SYNTAX  OBJECT IDENTIFIER
    ACCESS  read-only
    STATUS  mandatory
    DESCRIPTION
        "The reading for sensor 7 has reached the high limit
        value."
    ::= { falconWellKnownAlarms  25 }

falconInput7LowAlarm OBJECT-TYPE
    SYNTAX  OBJECT IDENTIFIER
    ACCESS  read-only
    STATUS  mandatory
    DESCRIPTION
        "The reading for sensor 7 has reached the low limit
        value."
    ::= { falconWellKnownAlarms  26 }

falconInput7High2Alarm OBJECT-TYPE
    SYNTAX  OBJECT IDENTIFIER
    ACCESS  read-only
    STATUS  mandatory
    DESCRIPTION
        "The reading for sensor 7 has reached the high limit
        value."
    ::= { falconWellKnownAlarms  27 }

falconInput7Low2Alarm OBJECT-TYPE
    SYNTAX  OBJECT IDENTIFIER
    ACCESS  read-only
    STATUS  mandatory
    DESCRIPTION
        "The reading for sensor 7 has reached the low limit
        value."
    ::= { falconWellKnownAlarms  28 }

falconInput8HighAlarm OBJECT-TYPE
    SYNTAX  OBJECT IDENTIFIER
    ACCESS  read-only
    STATUS  mandatory
    DESCRIPTION
        "The reading for sensor 8 has reached the high limit
        value."
    ::= { falconWellKnownAlarms  29 }

falconInput8LowAlarm OBJECT-TYPE
    SYNTAX  OBJECT IDENTIFIER
    ACCESS  read-only
    STATUS  mandatory
    DESCRIPTION
        "The reading for sensor 8 has reached the low limit
        value."
    ::= { falconWellKnownAlarms  30 }

falconInput8High2Alarm OBJECT-TYPE
    SYNTAX  OBJECT IDENTIFIER
    ACCESS  read-only
    STATUS  mandatory
    DESCRIPTION
        "The reading for sensor 8 has reached the high limit
        value."
    ::= { falconWellKnownAlarms  31 }

falconInput8Low2Alarm OBJECT-TYPE
    SYNTAX  OBJECT IDENTIFIER
    ACCESS  read-only
    STATUS  mandatory
    DESCRIPTION
        "The reading for sensor 8 has reached the low limit
        value."
    ::= { falconWellKnownAlarms  32 }

falconInput1DigAlarm OBJECT-TYPE
    SYNTAX  OBJECT IDENTIFIER
    ACCESS  read-only
    STATUS  mandatory
    DESCRIPTION
        "The digital input 1 has been activated."
    ::= { falconWellKnownAlarms  81 }

falconInput2DigAlarm OBJECT-TYPE
    SYNTAX  OBJECT IDENTIFIER
    ACCESS  read-only
    STATUS  mandatory
    DESCRIPTION
        "The digital input 2 has been activated."
    ::= { falconWellKnownAlarms  82 }

falconInput3DigAlarm OBJECT-TYPE
    SYNTAX  OBJECT IDENTIFIER
    ACCESS  read-only
    STATUS  mandatory
    DESCRIPTION
        "The digital input 3 has been activated."
    ::= { falconWellKnownAlarms  83 }

falconInput4DigAlarm OBJECT-TYPE
    SYNTAX  OBJECT IDENTIFIER
    ACCESS  read-only
    STATUS  mandatory
    DESCRIPTION
        "The digital input 4 has been activated."
    ::= { falconWellKnownAlarms  84 }

falconInput5DigAlarm OBJECT-TYPE
    SYNTAX  OBJECT IDENTIFIER
    ACCESS  read-only
    STATUS  mandatory
    DESCRIPTION
        "The digital input 5 has been activated."
    ::= { falconWellKnownAlarms  85 }

falconInput6DigAlarm OBJECT-TYPE
    SYNTAX  OBJECT IDENTIFIER
    ACCESS  read-only
    STATUS  mandatory
    DESCRIPTION
        "The digital input 6 has been activated."
    ::= { falconWellKnownAlarms  86 }

falconInput7DigAlarm OBJECT-TYPE
    SYNTAX  OBJECT IDENTIFIER
    ACCESS  read-only
    STATUS  mandatory
    DESCRIPTION
        "The digital input 7 has been activated."
    ::= { falconWellKnownAlarms  87 }

falconInput8DigAlarm OBJECT-TYPE
    SYNTAX  OBJECT IDENTIFIER
    ACCESS  read-only
    STATUS  mandatory
    DESCRIPTION
        "The digital input 8 has been activated."
    ::= { falconWellKnownAlarms  88 }

falconInput9DigAlarm OBJECT-TYPE
    SYNTAX  OBJECT IDENTIFIER
    ACCESS  read-only
    STATUS  mandatory
    DESCRIPTION
        "The digital input 9 has been activated."
    ::= { falconWellKnownAlarms  89 }

falconInput10DigAlarm OBJECT-TYPE
    SYNTAX  OBJECT IDENTIFIER
    ACCESS  read-only
    STATUS  mandatory
    DESCRIPTION
        "The digital input 10 has been activated."
    ::= { falconWellKnownAlarms  90 }

falconInput11DigAlarm OBJECT-TYPE
    SYNTAX  OBJECT IDENTIFIER
    ACCESS  read-only
    STATUS  mandatory
    DESCRIPTION
        "The digital input 11 has been activated."
    ::= { falconWellKnownAlarms  91 }

falconInput12DigAlarm OBJECT-TYPE
    SYNTAX  OBJECT IDENTIFIER
    ACCESS  read-only
    STATUS  mandatory
    DESCRIPTION
        "The digital input 12 has been activated."
    ::= { falconWellKnownAlarms  92 }

falconInput13DigAlarm OBJECT-TYPE
    SYNTAX  OBJECT IDENTIFIER
    ACCESS  read-only
    STATUS  mandatory
    DESCRIPTION
        "The digital input 13 has been activated."
    ::= { falconWellKnownAlarms  93 }

falconInput14DigAlarm OBJECT-TYPE
    SYNTAX  OBJECT IDENTIFIER
    ACCESS  read-only
    STATUS  mandatory
    DESCRIPTION
        "The digital input 14 has been activated."
    ::= { falconWellKnownAlarms  94 }

falconInput15DigAlarm OBJECT-TYPE
    SYNTAX  OBJECT IDENTIFIER
    ACCESS  read-only
    STATUS  mandatory
    DESCRIPTION
        "The digital input 15 has been activated."
    ::= { falconWellKnownAlarms  95 }

falconInput16DigAlarm OBJECT-TYPE
    SYNTAX  OBJECT IDENTIFIER
    ACCESS  read-only
    STATUS  mandatory
    DESCRIPTION
        "The digital input 16 has been activated."
    ::= { falconWellKnownAlarms  96 }

falconInput17DigAlarm OBJECT-TYPE
    SYNTAX  OBJECT IDENTIFIER
    ACCESS  read-only
    STATUS  mandatory
    DESCRIPTION
        "The digital input 17 has been activated."
    ::= { falconWellKnownAlarms  97 }

falconInput18DigAlarm OBJECT-TYPE
    SYNTAX  OBJECT IDENTIFIER
    ACCESS  read-only
    STATUS  mandatory
    DESCRIPTION
        "The digital input 18 has been activated."
    ::= { falconWellKnownAlarms  98 }

falconInput19DigAlarm OBJECT-TYPE
    SYNTAX  OBJECT IDENTIFIER
    ACCESS  read-only
    STATUS  mandatory
    DESCRIPTION
        "The digital input 19 has been activated."
    ::= { falconWellKnownAlarms  99 }

falconInput20DigAlarm OBJECT-TYPE
    SYNTAX  OBJECT IDENTIFIER
    ACCESS  read-only
    STATUS  mandatory
    DESCRIPTION
        "The digital input 20 has been activated."
    ::= { falconWellKnownAlarms  100 }

falconInput21DigAlarm OBJECT-TYPE
    SYNTAX  OBJECT IDENTIFIER
    ACCESS  read-only
    STATUS  mandatory
    DESCRIPTION
        "The digital input 21 has been activated."
    ::= { falconWellKnownAlarms  101 }

falconInput22DigAlarm OBJECT-TYPE
    SYNTAX  OBJECT IDENTIFIER
    ACCESS  read-only
    STATUS  mandatory
    DESCRIPTION
        "The digital input 22 has been activated."
    ::= { falconWellKnownAlarms  102 }

falconInput23DigAlarm OBJECT-TYPE
    SYNTAX  OBJECT IDENTIFIER
    ACCESS  read-only
    STATUS  mandatory
    DESCRIPTION
        "The digital input 23 has been activated."
    ::= { falconWellKnownAlarms  103 }

falconInput24DigAlarm OBJECT-TYPE
    SYNTAX  OBJECT IDENTIFIER
    ACCESS  read-only
    STATUS  mandatory
    DESCRIPTION
        "The digital input 24 has been activated."
    ::= { falconWellKnownAlarms  104 }

falconInput25DigAlarm OBJECT-TYPE
    SYNTAX  OBJECT IDENTIFIER
    ACCESS  read-only
    STATUS  mandatory
    DESCRIPTION
        "The digital input 25 has been activated."
    ::= { falconWellKnownAlarms  105 }

falconInput26DigAlarm OBJECT-TYPE
    SYNTAX  OBJECT IDENTIFIER
    ACCESS  read-only
    STATUS  mandatory
    DESCRIPTION
        "The digital input 26 has been activated."
    ::= { falconWellKnownAlarms  106 }

falconInput27DigAlarm OBJECT-TYPE
    SYNTAX  OBJECT IDENTIFIER
    ACCESS  read-only
    STATUS  mandatory
    DESCRIPTION
        "The digital input 27 has been activated."
    ::= { falconWellKnownAlarms  107 }

falconInput28DigAlarm OBJECT-TYPE
    SYNTAX  OBJECT IDENTIFIER
    ACCESS  read-only
    STATUS  mandatory
    DESCRIPTION
        "The digital input 28 has been activated."
    ::= { falconWellKnownAlarms  108 }

falconInput29DigAlarm OBJECT-TYPE
    SYNTAX  OBJECT IDENTIFIER
    ACCESS  read-only
    STATUS  mandatory
    DESCRIPTION
        "The digital input 29 has been activated."
    ::= { falconWellKnownAlarms  109 }

falconInput30DigAlarm OBJECT-TYPE
    SYNTAX  OBJECT IDENTIFIER
    ACCESS  read-only
    STATUS  mandatory
    DESCRIPTION
        "The digital input 30 has been activated."
    ::= { falconWellKnownAlarms  110 }

falconInput31DigAlarm OBJECT-TYPE
    SYNTAX  OBJECT IDENTIFIER
    ACCESS  read-only
    STATUS  mandatory
    DESCRIPTION
        "The digital input 31 has been activated."
    ::= { falconWellKnownAlarms  111 }

falconInput32DigAlarm OBJECT-TYPE
    SYNTAX  OBJECT IDENTIFIER
    ACCESS  read-only
    STATUS  mandatory
    DESCRIPTION
        "The digital input 32 has been activated."
    ::= { falconWellKnownAlarms  112 }

falconOnBatteryAlarm OBJECT-TYPE
    SYNTAX  OBJECT IDENTIFIER
    ACCESS  read-only
    STATUS  mandatory
    DESCRIPTION
        "The On Battery input has been activated."
    ::= { falconWellKnownAlarms  114 }

falconLowBatteryAlarm OBJECT-TYPE
    SYNTAX  OBJECT IDENTIFIER
    ACCESS  read-only
    STATUS  mandatory
    DESCRIPTION
        "The Faclon has detected a low battery condition."
    ::= { falconWellKnownAlarms  115 }

falconTraps OBJECT IDENTIFIER ::= { falconMIB  6 }

falconAlarmEntryAdded TRAP-TYPE
    ENTERPRISE   falconTraps 
    DESCRIPTION
           "An AlarmEntryAdded Trap signifies that the a sensor
            reading has reached a high or low limit value."
    ::= 1

falconAlarmEntryRemoved TRAP-TYPE
    ENTERPRISE   falconTraps 
    DESCRIPTION
           "An AlarmEntryAdded Trap signifies that the a sensor
            reading has gone below the high limit value or above
            the low limit value."
    ::= 2

falconAccessGranted TRAP-TYPE
    ENTERPRISE   falconTraps 
    DESCRIPTION
           "An falconAccessGranted Trap signifies that a valid
            key code sequence was processed by the falcon."
    ::= 3

falconAccessDenied TRAP-TYPE
    ENTERPRISE   falconTraps 
    DESCRIPTION
           "An falconAccessedDenied Trap signifies that an invalid
            key code sequence was processed by the falcon."
    ::= 4

falconPageUnsuccessful TRAP-TYPE
    ENTERPRISE   falconTraps 
    DESCRIPTION
           "An falconPageUnsuccessful Trap signifies that an alpha
            numeric page could not be sent to the service."
    ::= 5

falconAlarmHistory OBJECT IDENTIFIER ::= { falconMIB  7 }

falconAlarmHistoryEntries OBJECT-TYPE
    SYNTAX     Gauge
    ACCESS read-only
    STATUS     mandatory
    DESCRIPTION
        "The present number of entries in the alarm history."
    ::= { falconAlarmHistory 1 }

falconAlarmHistoryClear OBJECT-TYPE
    SYNTAX  INTEGER {
    clearBuffer(1)
}
    ACCESS  read-write
    STATUS  mandatory
    DESCRIPTION
           "Setting this value to ClearBuffer(1) will clear the
            alarm history buffer. "
    ::= { falconAlarmHistory 2 }

falconAlarmHistoryTable OBJECT-TYPE
    SYNTAX     SEQUENCE OF FalconAlarmHistoryEntry
    ACCESS not-accessible
    STATUS     mandatory
    DESCRIPTION
       "A list of alarm history table entries stored in the
        in the non-volatile memory.  The table contains zero,
        one, or many rows at any moment, depending upon the
        number of alarm conditions in effect. The falcon creates
        a row in the table each time a new alarm is detected.
        The falcon creates the first row with falconAlarmHistoryId
        equal to 1, and increments the value of falconAlarmHistoryId
        each time a new row is created, up to a maximum of 100.
        After 100 entries are created, the falcon will overwrite
        the earliest entry with the latest alarm.
        The number of rows in the table at any given time is
        reflected by the value of falconAlarmHistoryEntries."
    ::= { falconAlarmHistory 3 }

falconAlarmHistoryEntry OBJECT-TYPE
    SYNTAX     FalconAlarmHistoryEntry
    ACCESS     not-accessible
    STATUS     mandatory
    DESCRIPTION
         "An entry containing information applicable to a
         particular alarm history entry."
   INDEX { falconAlarmHistoryId }
   ::= { falconAlarmHistoryTable 1 }

FalconAlarmHistoryEntry ::= SEQUENCE {
    falconAlarmHistoryId     PositiveInteger,
    falconAlarmHistoryText   DisplayString
}

falconAlarmHistoryId OBJECT-TYPE
    SYNTAX     PositiveInteger
    ACCESS not-accessible
    STATUS     mandatory
    DESCRIPTION
         "A unique identifier for an alarm condition.  This
          value must remain constant."
    ::= { falconAlarmHistoryEntry 1 }

falconAlarmHistoryText OBJECT-TYPE
    SYNTAX     DisplayString
    ACCESS read-only
    STATUS     mandatory
    DESCRIPTION
        "A text desciption of the alarm history entry.
         Each of the strings will have the following format,
         AHxxx-id-type-timestamp label
         xxx  = number entry in the table
         id   = Alarm ID
         type = HIGH, LOW, ALM or RTN
         timestamp = MM/DD/YY HH:MM:SS
         Label = The label associated with the input channel
         These alarms are stored in non-volatile memory."
    ::= { falconAlarmHistoryEntry 2 }

falconTrapSettings OBJECT IDENTIFIER ::= { falconMIB  8 }

falconPersistantTraps OBJECT-TYPE
    SYNTAX  INTEGER (0..2147483647)
    ACCESS read-write
    STATUS     mandatory
    DESCRIPTION
        "The number of minutes between persistant traps.
         Set this to 0 to turn off persistant traps.
         This value is stored in non-volatile memory."
    ::= { falconTrapSettings 1 }

falconAlarmAcknowledge OBJECT-TYPE
    SYNTAX  INTEGER {
    acknowledgeAlarms(1)
}
    ACCESS  read-write
    STATUS  mandatory
    DESCRIPTION
           "Setting this value to AcknowledgeAlarms(1) will
            stop the falcon from sending persistant traps
            and dial out sequences."
    ::= { falconTrapSettings 2 }

falconSchedules OBJECT IDENTIFIER ::= { falconMIB  9 }

falconScheduleABeginDOW OBJECT-TYPE
    SYNTAX  INTEGER {
    sunday(1),
    monday(2),
    tuesday(3),
    wednesday(4),
    thursday(5),
    friday(6),
    saturday(7)
}
    ACCESS  read-write
    STATUS  mandatory
    DESCRIPTION
           "The beginning day of the week for schedule A.
            This variable is stored in non-volatile memory."
    ::= { falconSchedules  1 }

falconScheduleAEndDOW OBJECT-TYPE
    SYNTAX  INTEGER {
    sunday(1),
    monday(2),
    tuesday(3),
    wednesday(4),
    thursday(5),
    friday(6),
    saturday(7)
}
    ACCESS  read-write
    STATUS  mandatory
    DESCRIPTION
           "The ending day of the week for schedule A.
            This variable is stored in non-volatile memory."
    ::= { falconSchedules  2 }

falconScheduleABeginTime OBJECT-TYPE
    SYNTAX  DisplayString
    ACCESS  read-write
    STATUS  mandatory
    DESCRIPTION
           "The schedule A beginning time of day.
            Displayed as HH:MM"
    ::= { falconSchedules  3 }

falconScheduleAEndTime OBJECT-TYPE
    SYNTAX  DisplayString
    ACCESS  read-write
    STATUS  mandatory
    DESCRIPTION
           "The schedule A ending time of day.
            Displayed as HH:MM"
    ::= { falconSchedules  4 }

falconScheduleBBeginDOW OBJECT-TYPE
    SYNTAX  INTEGER {
    sunday(1),
    monday(2),
    tuesday(3),
    wednesday(4),
    thursday(5),
    friday(6),
    saturday(7)
}
    ACCESS  read-write
    STATUS  mandatory
    DESCRIPTION
           "The beginning day of the week for schedule B.
            This variable is stored in non-volatile memory."
    ::= { falconSchedules  5 }

falconScheduleBEndDOW OBJECT-TYPE
    SYNTAX  INTEGER {
    sunday(1),
    monday(2),
    tuesday(3),
    wednesday(4),
    thursday(5),
    friday(6),
    saturday(7)
}
    ACCESS  read-write
    STATUS  mandatory
    DESCRIPTION
           "The ending day of the week for schedule B.
            This variable is stored in non-volatile memory."
    ::= { falconSchedules  6 }

falconScheduleBBeginTime OBJECT-TYPE
    SYNTAX  DisplayString
    ACCESS  read-write
    STATUS  mandatory
    DESCRIPTION
           "The schedule B beginning time of day.
            Displayed as HH:MM"
    ::= { falconSchedules  7 }

falconScheduleBEndTime OBJECT-TYPE
    SYNTAX  DisplayString
    ACCESS  read-write
    STATUS  mandatory
    DESCRIPTION
           "The schedule B ending time of day.
            Displayed as HH:MM"
    ::= { falconSchedules  8 }

--
-- The falcon Extension
--
        falcon8 OBJECT IDENTIFIER ::= { falcon 2 }
        falcon8124 OBJECT IDENTIFIER ::= { falcon 3 }
        falcon812A4 OBJECT IDENTIFIER ::= { falcon 4 }
        falcon32 OBJECT IDENTIFIER ::= { falcon 5 }

END
