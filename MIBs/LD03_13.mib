--
-- LD03_13.MIB
-- MIB generated by Climaveneta SpA
-- Wednesday, 13 November 2013
--

    CAREL-LD03_13-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        LD03_13MIB MODULE-IDENTITY
      		LAST-UPDATED  "201311131045Z"		-- November 13, 2013 at 09:00 GMT
      		ORGANIZATION  "Climaveneta SpA"
      		CONTACT-INFO
                "
                        Climaveneta SpA
                        Via Sarson , 57C
                        36061 Bassano del Grappa (VI) Italy
                        Tel: +39 0424 509500
                        E-mail:
                "

      		DESCRIPTION
                "This is the MIB module for the LD03_13 device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { LD03_13MIB 1 }

        -- 1.3.6.1.4.1.9839.2.1.1.1
        startup-fan OBJECT-TYPE
                    SYNTAX Integer32 (0..1)
                    UNITS "N/A"
                    MAX-ACCESS read-only
                    STATUS current
                    DESCRIPTION "Unit status"
                    DEFVAL { 0 }
                    ::= { digitalObjects 1 }

        -- 1.3.6.1.4.1.9839.2.1.1.2
        compressore1 OBJECT-TYPE
                    SYNTAX Integer32 (0..1)
                    UNITS "N/A"
                    MAX-ACCESS read-only
                    STATUS current
                    DESCRIPTION "Compressor 1 status"
                    DEFVAL { 0 }
                    ::= { digitalObjects 2 }

        -- 1.3.6.1.4.1.9839.2.1.1.3
        compressore2 OBJECT-TYPE
                    SYNTAX Integer32 (0..1)
                    UNITS "N/A"
                    MAX-ACCESS read-only
                    STATUS current
                    DESCRIPTION "Compressor 2 status"
                    DEFVAL { 0 }
                    ::= { digitalObjects 3 }

        -- 1.3.6.1.4.1.9839.2.1.1.4
        resistenze1 OBJECT-TYPE
                    SYNTAX Integer32 (0..1)
                    UNITS "N/A"
                    MAX-ACCESS read-only
                    STATUS current
                    DESCRIPTION "Step 1 Heater status"
                    DEFVAL { 0 }
                    ::= { digitalObjects 4 }

        -- 1.3.6.1.4.1.9839.2.1.1.5
        resistenze2 OBJECT-TYPE
                    SYNTAX Integer32 (0..1)
                    UNITS "N/A"
                    MAX-ACCESS read-only
                    STATUS current
                    DESCRIPTION "Step 2 Heater status"
                    DEFVAL { 0 }
                    ::= { digitalObjects 5 }

        -- 1.3.6.1.4.1.9839.2.1.1.6
        ok-deumidifica OBJECT-TYPE
                    SYNTAX Integer32 (0..1)
                    UNITS "N/A"
                    MAX-ACCESS read-only
                    STATUS current
                    DESCRIPTION "Dehumidification active"
                    DEFVAL { 0 }
                    ::= { digitalObjects 6 }

        -- 1.3.6.1.4.1.9839.2.1.1.7
        gas-caldo-ok OBJECT-TYPE
                    SYNTAX Integer32 (0..1)
                    UNITS "N/A"
                    MAX-ACCESS read-only
                    STATUS current
                    DESCRIPTION "Hot gas active"
                    DEFVAL { 0 }
                    ::= { digitalObjects 7 }

        -- 1.3.6.1.4.1.9839.2.1.1.8
        power OBJECT-TYPE
                    SYNTAX Integer32 (0..1)
                    UNITS "N/A"
                    MAX-ACCESS read-only
                    STATUS current
                    DESCRIPTION "Humidifier status"
                    DEFVAL { 0 }
                    ::= { digitalObjects 8 }

        -- 1.3.6.1.4.1.9839.2.1.1.9
        emerg-mode OBJECT-TYPE
                    SYNTAX Integer32 (0..1)
                    UNITS "N/A"
                    MAX-ACCESS read-only
                    STATUS current
                    DESCRIPTION "Emergency mode status"
                    DEFVAL { 0 }
                    ::= { digitalObjects 9 }

        -- 1.3.6.1.4.1.9839.2.1.1.10
        ok-apri-fcdir OBJECT-TYPE
                    SYNTAX Integer32 (0..1)
                    UNITS "N/A"
                    MAX-ACCESS read-only
                    STATUS current
                    DESCRIPTION "Direct Freecooling enabled"
                    DEFVAL { 0 }
                    ::= { digitalObjects 10 }

        -- 1.3.6.1.4.1.9839.2.1.1.20
        mal-sequenza-fasi OBJECT-TYPE
                    SYNTAX Integer32 (0..1)
                    UNITS "N/A"
                    MAX-ACCESS read-only
                    STATUS current
                    DESCRIPTION "Phase sequence alarm"
                    DEFVAL { 0 }
                    ::= { digitalObjects 20 }

        -- 1.3.6.1.4.1.9839.2.1.1.21
        mal-fuoco-or-allag OBJECT-TYPE
                    SYNTAX Integer32 (0..1)
                    UNITS "N/A"
                    MAX-ACCESS read-only
                    STATUS current
                    DESCRIPTION "Fire or flood alarm"
                    DEFVAL { 0 }
                    ::= { digitalObjects 21 }

        -- 1.3.6.1.4.1.9839.2.1.1.22
        mal-fuoco-fumo OBJECT-TYPE
                    SYNTAX Integer32 (0..1)
                    UNITS "N/A"
                    MAX-ACCESS read-only
                    STATUS current
                    DESCRIPTION "Fire smoke alarm"
                    DEFVAL { 0 }
                    ::= { digitalObjects 22 }

        -- 1.3.6.1.4.1.9839.2.1.1.23
        mal-allagamento OBJECT-TYPE
                    SYNTAX Integer32 (0..1)
                    UNITS "N/A"
                    MAX-ACCESS read-only
                    STATUS current
                    DESCRIPTION "Flooding alarm"
                    DEFVAL { 0 }
                    ::= { digitalObjects 23 }

        -- 1.3.6.1.4.1.9839.2.1.1.24
        mal-flusso-aria OBJECT-TYPE
                    SYNTAX Integer32 (0..1)
                    UNITS "N/A"
                    MAX-ACCESS read-only
                    STATUS current
                    DESCRIPTION "Air flow alarm"
                    DEFVAL { 0 }
                    ::= { digitalObjects 24 }

        -- 1.3.6.1.4.1.9839.2.1.1.25
        mal-alta-press-1 OBJECT-TYPE
                    SYNTAX Integer32 (0..1)
                    UNITS "N/A"
                    MAX-ACCESS read-only
                    STATUS current
                    DESCRIPTION "High press Compr1 alarm"
                    DEFVAL { 0 }
                    ::= { digitalObjects 25 }

        -- 1.3.6.1.4.1.9839.2.1.1.26
        mal-alta-press-2 OBJECT-TYPE
                    SYNTAX Integer32 (0..1)
                    UNITS "N/A"
                    MAX-ACCESS read-only
                    STATUS current
                    DESCRIPTION "High press Compr2 alarm"
                    DEFVAL { 0 }
                    ::= { digitalObjects 26 }

        -- 1.3.6.1.4.1.9839.2.1.1.27
        mal-bassa-press-1 OBJECT-TYPE
                    SYNTAX Integer32 (0..1)
                    UNITS "N/A"
                    MAX-ACCESS read-only
                    STATUS current
                    DESCRIPTION "Low press Compr1"
                    DEFVAL { 0 }
                    ::= { digitalObjects 27 }

        -- 1.3.6.1.4.1.9839.2.1.1.28
        mal-bassa-press-2 OBJECT-TYPE
                    SYNTAX Integer32 (0..1)
                    UNITS "N/A"
                    MAX-ACCESS read-only
                    STATUS current
                    DESCRIPTION "Low press Compr2"
                    DEFVAL { 0 }
                    ::= { digitalObjects 28 }

        -- 1.3.6.1.4.1.9839.2.1.1.29
        mal-eev-1 OBJECT-TYPE
                    SYNTAX Integer32 (0..1)
                    UNITS "N/A"
                    MAX-ACCESS read-only
                    STATUS current
                    DESCRIPTION "EEV 1 alarm"
                    DEFVAL { 0 }
                    ::= { digitalObjects 29 }

        -- 1.3.6.1.4.1.9839.2.1.1.30
        mal-eev-2 OBJECT-TYPE
                    SYNTAX Integer32 (0..1)
                    UNITS "N/A"
                    MAX-ACCESS read-only
                    STATUS current
                    DESCRIPTION "EEV 2 alarm"
                    DEFVAL { 0 }
                    ::= { digitalObjects 30 }

        -- 1.3.6.1.4.1.9839.2.1.1.31
        mal-resistenze OBJECT-TYPE
                    SYNTAX Integer32 (0..1)
                    UNITS "N/A"
                    MAX-ACCESS read-only
                    STATUS current
                    DESCRIPTION "Electric heater alarm"
                    DEFVAL { 0 }
                    ::= { digitalObjects 31 }

        -- 1.3.6.1.4.1.9839.2.1.1.32
        mal-filtri-intasati OBJECT-TYPE
                    SYNTAX Integer32 (0..1)
                    UNITS "N/A"
                    MAX-ACCESS read-only
                    STATUS current
                    DESCRIPTION "Dirty filter alarm"
                    DEFVAL { 0 }
                    ::= { digitalObjects 32 }

        -- 1.3.6.1.4.1.9839.2.1.1.33
        mal-alta-corrente OBJECT-TYPE
                    SYNTAX Integer32 (0..1)
                    UNITS "N/A"
                    MAX-ACCESS read-only
                    STATUS current
                    DESCRIPTION "High current humidif alarm"
                    DEFVAL { 0 }
                    ::= { digitalObjects 33 }

        -- 1.3.6.1.4.1.9839.2.1.1.34
        mal-no-acqua OBJECT-TYPE
                    SYNTAX Integer32 (0..1)
                    UNITS "N/A"
                    MAX-ACCESS read-only
                    STATUS current
                    DESCRIPTION "No water humidif alarm"
                    DEFVAL { 0 }
                    ::= { digitalObjects 34 }

        -- 1.3.6.1.4.1.9839.2.1.1.35
        mal-bassa-corrente OBJECT-TYPE
                    SYNTAX Integer32 (0..1)
                    UNITS "N/A"
                    MAX-ACCESS read-only
                    STATUS current
                    DESCRIPTION "Low current humidif alarm"
                    DEFVAL { 0 }
                    ::= { digitalObjects 35 }

        -- 1.3.6.1.4.1.9839.2.1.1.36
        mepromnook OBJECT-TYPE
                    SYNTAX Integer32 (0..1)
                    UNITS "N/A"
                    MAX-ACCESS read-only
                    STATUS current
                    DESCRIPTION "EEPROM alarm"
                    DEFVAL { 0 }
                    ::= { digitalObjects 36 }

        -- 1.3.6.1.4.1.9839.2.1.1.37
        mal-flusso-acqua OBJECT-TYPE
                    SYNTAX Integer32 (0..1)
                    UNITS "N/A"
                    MAX-ACCESS read-only
                    STATUS current
                    DESCRIPTION "Water flow alarm"
                    DEFVAL { 0 }
                    ::= { digitalObjects 37 }

        -- 1.3.6.1.4.1.9839.2.1.1.38
        mal-probe-troom OBJECT-TYPE
                    SYNTAX Integer32 (0..1)
                    UNITS "N/A"
                    MAX-ACCESS read-only
                    STATUS current
                    DESCRIPTION "Room temp probe alarm"
                    DEFVAL { 0 }
                    ::= { digitalObjects 38 }

        -- 1.3.6.1.4.1.9839.2.1.1.39
        mal-probe-umid OBJECT-TYPE
                    SYNTAX Integer32 (0..1)
                    UNITS "N/A"
                    MAX-ACCESS read-only
                    STATUS current
                    DESCRIPTION "Room humid alarm"
                    DEFVAL { 0 }
                    ::= { digitalObjects 39 }

        -- 1.3.6.1.4.1.9839.2.1.1.40
        mal-probe-tsupply OBJECT-TYPE
                    SYNTAX Integer32 (0..1)
                    UNITS "N/A"
                    MAX-ACCESS read-only
                    STATUS current
                    DESCRIPTION "TSupply probe alarm"
                    DEFVAL { 0 }
                    ::= { digitalObjects 40 }

        -- 1.3.6.1.4.1.9839.2.1.1.41
        mal-probe-coldw OBJECT-TYPE
                    SYNTAX Integer32 (0..1)
                    UNITS "N/A"
                    MAX-ACCESS read-only
                    STATUS current
                    DESCRIPTION "Cold water probe alarm"
                    DEFVAL { 0 }
                    ::= { digitalObjects 41 }

        -- 1.3.6.1.4.1.9839.2.1.1.42
        mal-probe-hotw OBJECT-TYPE
                    SYNTAX Integer32 (0..1)
                    UNITS "N/A"
                    MAX-ACCESS read-only
                    STATUS current
                    DESCRIPTION "Hot water probe alarm"
                    DEFVAL { 0 }
                    ::= { digitalObjects 42 }

        -- 1.3.6.1.4.1.9839.2.1.1.43
        mal-probe-tout OBJECT-TYPE
                    SYNTAX Integer32 (0..1)
                    UNITS "N/A"
                    MAX-ACCESS read-only
                    STATUS current
                    DESCRIPTION "TExt probe alarm"
                    DEFVAL { 0 }
                    ::= { digitalObjects 43 }

        -- 1.3.6.1.4.1.9839.2.1.1.44
        mal-lan OBJECT-TYPE
                    SYNTAX Integer32 (0..1)
                    UNITS "N/A"
                    MAX-ACCESS read-only
                    STATUS current
                    DESCRIPTION "LAN Alarm"
                    DEFVAL { 0 }
                    ::= { digitalObjects 44 }

        -- 1.3.6.1.4.1.9839.2.1.1.45
        mal-alta-temp OBJECT-TYPE
                    SYNTAX Integer32 (0..1)
                    UNITS "N/A"
                    MAX-ACCESS read-only
                    STATUS current
                    DESCRIPTION "High room temperature"
                    DEFVAL { 0 }
                    ::= { digitalObjects 45 }

        -- 1.3.6.1.4.1.9839.2.1.1.46
        mal-bassa-temp OBJECT-TYPE
                    SYNTAX Integer32 (0..1)
                    UNITS "N/A"
                    MAX-ACCESS read-only
                    STATUS current
                    DESCRIPTION "Low Room temperature"
                    DEFVAL { 0 }
                    ::= { digitalObjects 46 }

        -- 1.3.6.1.4.1.9839.2.1.1.47
        mal-alta-umid OBJECT-TYPE
                    SYNTAX Integer32 (0..1)
                    UNITS "N/A"
                    MAX-ACCESS read-only
                    STATUS current
                    DESCRIPTION "High room humidity"
                    DEFVAL { 0 }
                    ::= { digitalObjects 47 }

        -- 1.3.6.1.4.1.9839.2.1.1.48
        mal-bassa-umid OBJECT-TYPE
                    SYNTAX Integer32 (0..1)
                    UNITS "N/A"
                    MAX-ACCESS read-only
                    STATUS current
                    DESCRIPTION "Low room humidity"
                    DEFVAL { 0 }
                    ::= { digitalObjects 48 }

        -- 1.3.6.1.4.1.9839.2.1.1.49
        mal-alta-t-acqua OBJECT-TYPE
                    SYNTAX Integer32 (0..1)
                    UNITS "N/A"
                    MAX-ACCESS read-only
                    STATUS current
                    DESCRIPTION "High water temperature"
                    DEFVAL { 0 }
                    ::= { digitalObjects 49 }

        -- 1.3.6.1.4.1.9839.2.1.1.50
        mal-password OBJECT-TYPE
                    SYNTAX Integer32 (0..1)
                    UNITS "N/A"
                    MAX-ACCESS read-only
                    STATUS current
                    DESCRIPTION "Password Alarm"
                    DEFVAL { 0 }
                    ::= { digitalObjects 50 }

        -- 1.3.6.1.4.1.9839.2.1.1.51
        global-alarm OBJECT-TYPE
                    SYNTAX Integer32 (0..1)
                    UNITS "N/A"
                    MAX-ACCESS read-only
                    STATUS current
                    DESCRIPTION "Global (general) alarm"
                    DEFVAL { 0 }
                    ::= { digitalObjects 51 }

        -- 1.3.6.1.4.1.9839.2.1.1.52
        al-manutenzione OBJECT-TYPE
                    SYNTAX Integer32 (0..1)
                    UNITS "N/A"
                    MAX-ACCESS read-only
                    STATUS current
                    DESCRIPTION "Maintenance Status"
                    DEFVAL { 0 }
                    ::= { digitalObjects 52 }

        -- 1.3.6.1.4.1.9839.2.1.1.53
        mal-probe-pdiff OBJECT-TYPE
                    SYNTAX Integer32 (0..1)
                    UNITS "N/A"
                    MAX-ACCESS read-only
                    STATUS current
                    DESCRIPTION "Differential pressure alarm"
                    DEFVAL { 0 }
                    ::= { digitalObjects 53 }

        -- 1.3.6.1.4.1.9839.2.1.1.54
        all-tlan-exp OBJECT-TYPE
                    SYNTAX Integer32 (0..1)
                    UNITS "N/A"
                    MAX-ACCESS read-only
                    STATUS current
                    DESCRIPTION "Expansion Alarm"
                    DEFVAL { 0 }
                    ::= { digitalObjects 54 }

        -- 1.3.6.1.4.1.9839.2.1.1.55
        mal-inverter OBJECT-TYPE
                    SYNTAX Integer32 (0..1)
                    UNITS "N/A"
                    MAX-ACCESS read-only
                    STATUS current
                    DESCRIPTION "Inverter Alarm"
                    DEFVAL { 0 }
                    ::= { digitalObjects 55 }

        -- 1.3.6.1.4.1.9839.2.1.1.56
        mal-envelop OBJECT-TYPE
                    SYNTAX Integer32 (0..1)
                    UNITS "N/A"
                    MAX-ACCESS read-only
                    STATUS current
                    DESCRIPTION "Envelop Alarm"
                    DEFVAL { 0 }
                    ::= { digitalObjects 56 }

        -- 1.3.6.1.4.1.9839.2.1.1.58
        mal-delta-p OBJECT-TYPE
                    SYNTAX Integer32 (0..1)
                    UNITS "N/A"
                    MAX-ACCESS read-only
                    STATUS current
                    DESCRIPTION "Delta pressure Alarm for inverter compressor"
                    DEFVAL { 0 }
                    ::= { digitalObjects 58 }

        -- 1.3.6.1.4.1.9839.2.1.1.80
        on-seriale OBJECT-TYPE
                    SYNTAX Integer32 (0..1)
                    UNITS "N/A"
                    MAX-ACCESS read-write
                    STATUS current
                    DESCRIPTION "Serial ON OFF"
                    DEFVAL { 0 }
                    ::= { digitalObjects 80 }

        -- 1.3.6.1.4.1.9839.2.1.1.81
        res-al-da-spv OBJECT-TYPE
                    SYNTAX Integer32 (0..1)
                    UNITS "N/A"
                    MAX-ACCESS read-write
                    STATUS current
                    DESCRIPTION "Spv reset alarm"
                    DEFVAL { 0 }
                    ::= { digitalObjects 81 }

 

        -- 1.3.6.1.4.1.9839.2.1.2
        analogObjects OBJECT IDENTIFIER ::= { LD03_13MIB 2 }

        -- 1.3.6.1.4.1.9839.2.1.2.1
        room-temp OBJECT-TYPE
                    SYNTAX Integer32 (-999..999)
                    UNITS "N/A"
                    MAX-ACCESS read-only
                    STATUS current
                    DESCRIPTION "Room Temperature"
                    DEFVAL { 0 }
                    ::= { analogObjects 1 }

        -- 1.3.6.1.4.1.9839.2.1.2.2
        room-umid OBJECT-TYPE
                    SYNTAX Integer32 (0..999)
                    UNITS "N/A"
                    MAX-ACCESS read-only
                    STATUS current
                    DESCRIPTION "Room Umidity"
                    DEFVAL { 0 }
                    ::= { analogObjects 2 }

        -- 1.3.6.1.4.1.9839.2.1.2.3
        supply-temp OBJECT-TYPE
                    SYNTAX Integer32 (-999..999)
                    UNITS "N/A"
                    MAX-ACCESS read-only
                    STATUS current
                    DESCRIPTION "Supply temperature"
                    DEFVAL { 0 }
                    ::= { analogObjects 3 }

        -- 1.3.6.1.4.1.9839.2.1.2.4
        cold-water-temp OBJECT-TYPE
                    SYNTAX Integer32 (-999..999)
                    UNITS "N/A"
                    MAX-ACCESS read-only
                    STATUS current
                    DESCRIPTION "Cold Water Temp"
                    DEFVAL { 0 }
                    ::= { analogObjects 4 }

        -- 1.3.6.1.4.1.9839.2.1.2.5
        hot-water-temp OBJECT-TYPE
                    SYNTAX Integer32 (-999..999)
                    UNITS "N/A"
                    MAX-ACCESS read-only
                    STATUS current
                    DESCRIPTION "Hot Water Temp"
                    DEFVAL { 0 }
                    ::= { analogObjects 5 }

        -- 1.3.6.1.4.1.9839.2.1.2.6
        outdoor-temp OBJECT-TYPE
                    SYNTAX Integer32 (-999..999)
                    UNITS "N/A"
                    MAX-ACCESS read-only
                    STATUS current
                    DESCRIPTION "Outdoor Temp"
                    DEFVAL { 0 }
                    ::= { analogObjects 6 }

        -- 1.3.6.1.4.1.9839.2.1.2.7
        rampa-valv-af1 OBJECT-TYPE
                    SYNTAX Integer32 (0..1000)
                    UNITS "N/A"
                    MAX-ACCESS read-only
                    STATUS current
                    DESCRIPTION "Position Cold Water Valve"
                    DEFVAL { 0 }
                    ::= { analogObjects 7 }

        -- 1.3.6.1.4.1.9839.2.1.2.8
        rampa-valv-ac OBJECT-TYPE
                    SYNTAX Integer32 (0..1000)
                    UNITS "N/A"
                    MAX-ACCESS read-only
                    STATUS current
                    DESCRIPTION "Position Hot Water Valve"
                    DEFVAL { 0 }
                    ::= { analogObjects 8 }

        -- 1.3.6.1.4.1.9839.2.1.2.9
        vent-speed OBJECT-TYPE
                    SYNTAX Integer32 (-32768..32767)
                    UNITS "N/A"
                    MAX-ACCESS read-only
                    STATUS current
                    DESCRIPTION "Fan Speed"
                    DEFVAL { 0 }
                    ::= { analogObjects 9 }

        -- 1.3.6.1.4.1.9839.2.1.2.10
        rampa-valv-af2 OBJECT-TYPE
                    SYNTAX Integer32 (0..1000)
                    UNITS "N/A"
                    MAX-ACCESS read-only
                    STATUS current
                    DESCRIPTION "Position Cold Water Valve2"
                    DEFVAL { 0 }
                    ::= { analogObjects 10 }

        -- 1.3.6.1.4.1.9839.2.1.2.11
        cold-water-temp2 OBJECT-TYPE
                    SYNTAX Integer32 (-999..999)
                    UNITS "N/A"
                    MAX-ACCESS read-only
                    STATUS current
                    DESCRIPTION "Cold Water Temp2"
                    DEFVAL { 0 }
                    ::= { analogObjects 11 }

        -- 1.3.6.1.4.1.9839.2.1.2.12
        rampa-fcdir OBJECT-TYPE
                    SYNTAX Integer32 (0..1000)
                    UNITS "N/A"
                    MAX-ACCESS read-only
                    STATUS current
                    DESCRIPTION "Position freecooling damper"
                    DEFVAL { 0 }
                    ::= { analogObjects 12 }

        -- 1.3.6.1.4.1.9839.2.1.2.14
        out-inverter OBJECT-TYPE
                    SYNTAX Integer32 (0..1000)
                    UNITS "N/A"
                    MAX-ACCESS read-only
                    STATUS current
                    DESCRIPTION "Out inverter"
                    DEFVAL { 0 }
                    ::= { analogObjects 14 }

       
        -- 1.3.6.1.4.1.9839.2.1.2.20
        set-freddo OBJECT-TYPE
                    SYNTAX Integer32 (0..999)
                    UNITS "N/A"
                    MAX-ACCESS read-write
                    STATUS current
                    DESCRIPTION "Setpoint Cooling"
                    DEFVAL { 240 }
                    ::= { analogObjects 20 }

        -- 1.3.6.1.4.1.9839.2.1.2.21
        set-caldo OBJECT-TYPE
                    SYNTAX Integer32 (120..400)
                    UNITS "N/A"
                    MAX-ACCESS read-write
                    STATUS current
                    DESCRIPTION "Setpoint Heating"
                    DEFVAL { 240 }
                    ::= { analogObjects 21 }

        -- 1.3.6.1.4.1.9839.2.1.3
        integerObjects OBJECT IDENTIFIER ::= { LD03_13MIB 3 }

         -- 1.3.6.1.4.1.9839.2.1.3.8
        current-day OBJECT-TYPE
                    SYNTAX Integer32 (1..31)
                    UNITS "N/A"
                    MAX-ACCESS read-only
                    STATUS current
                    DESCRIPTION "Current day"
                    DEFVAL { 1 }
                    ::= { integerObjects 8 }

        -- 1.3.6.1.4.1.9839.2.1.3.9
        current-month OBJECT-TYPE
                    SYNTAX Integer32 (1..12)
                    UNITS "N/A"
                    MAX-ACCESS read-only
                    STATUS current
                    DESCRIPTION "Current month"
                    DEFVAL { 1 }
                    ::= { integerObjects 9 }

        -- 1.3.6.1.4.1.9839.2.1.3.10
        current-year OBJECT-TYPE
                    SYNTAX Integer32 (0..99)
                    UNITS "N/A"
                    MAX-ACCESS read-only
                    STATUS current
                    DESCRIPTION "Current year"
                    DEFVAL { 0 }
                    ::= { integerObjects 10 }

          -- 1.3.6.1.4.1.9839.2.1.3.15
        out-din-setp OBJECT-TYPE
                    SYNTAX Integer32 (0..1000)
                    UNITS "N/A"
                    MAX-ACCESS read-only
                    STATUS current
                    DESCRIPTION "Out chiller dinamic setpoint"
                    DEFVAL { 0 }
                    ::= { integerObjects 15 }

        -- 1.3.6.1.4.1.9839.2.1.3.20
        set-deumid OBJECT-TYPE
                    SYNTAX Integer32 (0..99)
                    UNITS "N/A"
                    MAX-ACCESS read-write
                    STATUS current
                    DESCRIPTION "Set Dehumidif"
                    DEFVAL { 55 }
                    ::= { integerObjects 20 }

        -- 1.3.6.1.4.1.9839.2.1.3.21
        set-umidif OBJECT-TYPE
                    SYNTAX Integer32 (10..99)
                    UNITS "N/A"
                    MAX-ACCESS read-write
                    STATUS current
                    DESCRIPTION "Set Humidif"
                    DEFVAL { 45 }
                    ::= { integerObjects 21 }

         -- 1.3.6.1.4.1.9839.2.1.3.32
        type-alarm-spv OBJECT-TYPE
                    SYNTAX Integer32 (0..32767)
                    UNITS "N/A"
                    MAX-ACCESS read-only
                    STATUS current
                    DESCRIPTION "SPV Type Alarm"
                    DEFVAL { 0 }
                    ::= { integerObjects 32 }

   
  
  
	
	END

--
-- CAREL-LD03_13.MIB
--
