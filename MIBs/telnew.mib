--
-- CAREL-telnew.MIB
-- MIB generated by UNIFLAIR
-- Monday, 17 September 2012
--

    CAREL-telnew-MIB DEFINITIONS ::= BEGIN

		IMPORTS
			OBJECT-GROUP		FROM SNMPv2-CONF			
			sysContact, sysName,
			sysLocation		FROM SNMPv2-MIB
			enterprises, MODULE-IDENTITY,
			OBJECT-TYPE, Integer32	FROM SNMPv2-SMI
			DisplayString		FROM RFC1213-MIB;		

        telnewMIB MODULE-IDENTITY
      		LAST-UPDATED  "200604191625Z"		-- April 19, 2006 at 16:25 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the mP20II Telefonic units device."
      		REVISION  "200604191625Z"		-- April 19, 2006 at 16:25 GMT
      		DESCRIPTION
                "This is the update version of the MIB."
			::= { instruments 1 }


--
-- Node definitions
--

		-- 1.3.6.1.4.1.9839
		carel OBJECT IDENTIFIER ::= { enterprises 9839 }

		-- 1.3.6.1.4.1.9839.1
		systm OBJECT IDENTIFIER ::= { carel 1 }

		-- 1.3.6.1.4.1.9839.1.1
		agentRelease OBJECT-TYPE
			SYNTAX Integer32
			UNITS "N/A"
			MAX-ACCESS read-only
			STATUS current
			DESCRIPTION "Release of the Agent."
		::= { systm 1 }

		-- 1.3.6.1.4.1.9839.1.2
		agentCode OBJECT-TYPE
			SYNTAX Integer32
			UNITS "N/A"
			MAX-ACCESS read-only
			STATUS current
			DESCRIPTION "Code of the Agent. 2=pCOWeb."
		::= { systm 2 }

		-- 1.3.6.1.4.1.9839.2
		instruments OBJECT IDENTIFIER ::= { carel 2 }

		-- 1.3.6.1.4.1.9839.2.0
 		pCOWebInfo OBJECT IDENTIFIER ::= { instruments 0 }

		-- 1.3.6.1.4.1.9839.2.0.10
		pCOStatusgroup OBJECT IDENTIFIER ::= { pCOWebInfo 10 }

		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

        -- 1.3.6.1.4.1.9839.2.1.1
        digitalObjects OBJECT IDENTIFIER ::= { telnewMIB 1 }

        -- 1.3.6.1.4.1.9839.2.1.1.1
        system-on   OBJECT-TYPE
                    SYNTAX Integer32 (0..1)
                    UNITS "N/A"
                    MAX-ACCESS read-only
                    STATUS current
                    DESCRIPTION "System On (Fan)"
                    ::= { digitalObjects 1 }

        -- 1.3.6.1.4.1.9839.2.1.1.2
        compressor OBJECT-TYPE
                    SYNTAX Integer32 (0..1)
                    UNITS "N/A"
                    MAX-ACCESS read-only
                    STATUS current
                    DESCRIPTION "Compressor"
                    ::= { digitalObjects 2 }

        -- 1.3.6.1.4.1.9839.2.1.1.3
        heater OBJECT-TYPE
                    SYNTAX Integer32 (0..1)
                    UNITS "N/A"
                    MAX-ACCESS read-only
                    STATUS current
                    DESCRIPTION "Heater"
                    ::= { digitalObjects 3 }

        -- 1.3.6.1.4.1.9839.2.1.1.4
        free-cooling-condition OBJECT-TYPE
                    SYNTAX Integer32 (0..1)
                    UNITS "N/A"
                    MAX-ACCESS read-only
                    STATUS current
                    DESCRIPTION "Free-cooling condition"
                    ::= { digitalObjects 4 }

        -- 1.3.6.1.4.1.9839.2.1.1.5
        high-pressure-alarm OBJECT-TYPE
                    SYNTAX Integer32 (0..1)
                    UNITS "N/A"
                    MAX-ACCESS read-only
                    STATUS current
                    DESCRIPTION "High Pressure Alarm"
                    ::= { digitalObjects 5 }

        -- 1.3.6.1.4.1.9839.2.1.1.6
         low-pressure-alarm OBJECT-TYPE
                    SYNTAX Integer32 (0..1)
                    UNITS "N/A"
                    MAX-ACCESS read-only
                    STATUS current
                    DESCRIPTION "Low Pressure Alarm"
                    ::= { digitalObjects 6 }

        -- 1.3.6.1.4.1.9839.2.1.1.8
        wrong-phase-sequence-alarm OBJECT-TYPE
                    SYNTAX Integer32 (0..1)
                    UNITS "N/A"
                    MAX-ACCESS read-only
                    STATUS current
                    DESCRIPTION "Wrong phase sequence alarm"
                    ::= { digitalObjects 8 }

        -- 1.3.6.1.4.1.9839.2.1.1.9
        fan-thermal-protection-alarm OBJECT-TYPE
                    SYNTAX Integer32 (0..1)
                    UNITS "N/A"
                    MAX-ACCESS read-only
                    STATUS current
                    DESCRIPTION "Fan thermal protection Alarm (Klixon)"
                    ::= { digitalObjects 9 }

        -- 1.3.6.1.4.1.9839.2.1.1.10
        loss-of-air-flow-alarm OBJECT-TYPE
                    SYNTAX Integer32 (0..1)
                    UNITS "N/A"
                    MAX-ACCESS read-only
                    STATUS current
                    DESCRIPTION "Loss of Air Flow Alarm"
                    ::= { digitalObjects 10 }

        -- 1.3.6.1.4.1.9839.2.1.1.11
        heater-overheating-alarm OBJECT-TYPE
                    SYNTAX Integer32 (0..1)
                    UNITS "N/A"
                    MAX-ACCESS read-only
                    STATUS current
                    DESCRIPTION "Heater Overheating Alarm"
                    ::= { digitalObjects 11 }

        -- 1.3.6.1.4.1.9839.2.1.1.12
        clogged-filter-alarm OBJECT-TYPE
                    SYNTAX Integer32 (0..1)
                    UNITS "N/A"
                    MAX-ACCESS read-only
                    STATUS current
                    DESCRIPTION "Clogged Filter Alarm"
                    ::= { digitalObjects 12 }

        -- 1.3.6.1.4.1.9839.2.1.1.13
        room-high-temp-alarm-1st-level OBJECT-TYPE
                    SYNTAX Integer32 (0..1)
                    UNITS "N/A"
                    MAX-ACCESS read-only
                    STATUS current
                    DESCRIPTION "Room High Temp. Alarm (1st Level Alarm)"
                    ::= { digitalObjects 13 }

        -- 1.3.6.1.4.1.9839.2.1.1.14
        room-low-temp-alarm OBJECT-TYPE
                    SYNTAX Integer32 (0..1)
                    UNITS "N/A"
                    MAX-ACCESS read-only
                    STATUS current
                    DESCRIPTION "Room Low Temp. Alarm"
                    ::= { digitalObjects 14 }

        -- 1.3.6.1.4.1.9839.2.1.1.15
        main-sensor-failure-disconnected OBJECT-TYPE
                    SYNTAX Integer32 (0..1)
                    UNITS "N/A"
                    MAX-ACCESS read-only
                    STATUS current
                    DESCRIPTION "Main Sensors Failure/Disconnected"
                    ::= { digitalObjects 15 }

        -- 1.3.6.1.4.1.9839.2.1.1.16
        auxiliary-sensor-failure-disconnected OBJECT-TYPE
                    SYNTAX Integer32 (0..1)
                    UNITS "N/A"
                    MAX-ACCESS read-only
                    STATUS current
                    DESCRIPTION "Auxiliary Sensor Failure/Disconnected"
                    ::= { digitalObjects 16 }

        -- 1.3.6.1.4.1.9839.2.1.1.17
        lan-connection-failure OBJECT-TYPE
                    SYNTAX Integer32 (0..1)
                    UNITS "N/A"
                    MAX-ACCESS read-only
                    STATUS current
                    DESCRIPTION "LAN connection Failure"
                    ::= { digitalObjects 17 }

        -- 1.3.6.1.4.1.9839.2.1.1.18
        room-high-temp-alarm-2nd-level OBJECT-TYPE
                    SYNTAX Integer32 (0..1)
                    UNITS "N/A"
                    MAX-ACCESS read-only
                    STATUS current
                    DESCRIPTION "Room High Temp. Alarm (2nd Level Alarm)"
                    ::= { digitalObjects 18 }

        -- 1.3.6.1.4.1.9839.2.1.1.19
        air-filter-hour-counter-threshold-alarm OBJECT-TYPE
                    SYNTAX Integer32 (0..1)
                    UNITS "N/A"
                    MAX-ACCESS read-only
                    STATUS current
                    DESCRIPTION "Air filter: hour counter threshold Alarm"
                    ::= { digitalObjects 19 }

        -- 1.3.6.1.4.1.9839.2.1.1.20
        air-conditioning-unit-hour-counter-threshold-alarm OBJECT-TYPE
                    SYNTAX Integer32 (0..1)
                    UNITS "N/A"
                    MAX-ACCESS read-only
                    STATUS current
                    DESCRIPTION "Air conditioning unit: hour counter threshold Alarm"
                    ::= { digitalObjects 20 }

        -- 1.3.6.1.4.1.9839.2.1.1.21
        compressor-hour-counter-threshold-alarm OBJECT-TYPE
                    SYNTAX Integer32 (0..1)
                    UNITS "N/A"
                    MAX-ACCESS read-only
                    STATUS current
                    DESCRIPTION "Compressor: hour counter threshold Alarm"
                    ::= { digitalObjects 21 }

        -- 1.3.6.1.4.1.9839.2.1.1.22
        heater-hour-counter-threshold-alarm OBJECT-TYPE
                    SYNTAX Integer32 (0..1)
                    UNITS "N/A"
                    MAX-ACCESS read-only
                    STATUS current
                    DESCRIPTION "Heater: hour counter threshold Alarm"
                    ::= { digitalObjects 22 }

        -- 1.3.6.1.4.1.9839.2.1.1.23
        general-alarm OBJECT-TYPE
                    SYNTAX Integer32 (0..1)
                    UNITS "N/A"
                    MAX-ACCESS read-only
                    STATUS current
                    DESCRIPTION "General Alarm"
                    ::= { digitalObjects 23 }

        -- 1.3.6.1.4.1.9839.2.1.1.25
        resetAlarm OBJECT-TYPE
                    SYNTAX Integer32 (0..1)
                    UNITS "N/A"
                    MAX-ACCESS read-write
                    STATUS current
                    DESCRIPTION "Alarms Reset"
                    ::= { digitalObjects 25 }

        -- 1.3.6.1.4.1.9839.2.1.1.26
        unit-remote-switch-on-off-control OBJECT-TYPE
                    SYNTAX Integer32 (0..1)
                    UNITS "N/A"
                    MAX-ACCESS read-write
                    STATUS current
                    DESCRIPTION "Unit Remote Switch-On/Off Control"
                    ::= { digitalObjects 26 }

        -- 1.3.6.1.4.1.9839.2.1.1.27
        compressor-remote-control OBJECT-TYPE
                    SYNTAX Integer32 (0..1)
                    UNITS "N/A"
                    MAX-ACCESS read-write
                    STATUS current
                    DESCRIPTION "Compressor Remote Control (CDC)"
                    ::= { digitalObjects 27 }

        -- 1.3.6.1.4.1.9839.2.1.1.28
        heater-remote-control OBJECT-TYPE
                    SYNTAX Integer32 (0..1)
                    UNITS "N/A"
                    MAX-ACCESS read-write
                    STATUS current
                    DESCRIPTION "Heater Remote Control (CDC)"
                    ::= { digitalObjects 28 }

        -- 1.3.6.1.4.1.9839.2.1.1.29
        fc-damper-remote-control OBJECT-TYPE
                    SYNTAX Integer32 (0..1)
                    UNITS "N/A"
                    MAX-ACCESS read-write
                    STATUS current
                    DESCRIPTION "FC Damper Remote Control (CDC)"
                    ::= { digitalObjects 29 }

        -- 1.3.6.1.4.1.9839.2.1.1.30
        local-area-network-running OBJECT-TYPE
                    SYNTAX Integer32 (0..1)
                    UNITS "N/A"
                    MAX-ACCESS read-only
                    STATUS current
                    DESCRIPTION "Local Area Network running"
                    ::= { digitalObjects 30 }

        -- 1.3.6.1.4.1.9839.2.1.1.31
        no-LAN-present OBJECT-TYPE
                    SYNTAX Integer32 (0..1)
                    UNITS "N/A"
                    MAX-ACCESS read-only
                    STATUS current
                    DESCRIPTION "No LAN present"
                    ::= { digitalObjects 31 }

        -- 1.3.6.1.4.1.9839.2.1.1.32
        cooling-mode OBJECT-TYPE
                    SYNTAX Integer32 (0..1)
                    UNITS "N/A"
                    MAX-ACCESS read-only
                    STATUS current
                    DESCRIPTION "Cooling mode"
                    ::= { digitalObjects 32 }

        -- 1.3.6.1.4.1.9839.2.1.1.33
        heating-mode OBJECT-TYPE
                    SYNTAX Integer32 (0..1)
                    UNITS "N/A"
                    MAX-ACCESS read-only
                    STATUS current
                    DESCRIPTION "Heating mode"
                    ::= { digitalObjects 33 }

        -- 1.3.6.1.4.1.9839.2.1.1.34
        re-heating-mode OBJECT-TYPE
                    SYNTAX Integer32 (0..1)
                    UNITS "N/A"
                    MAX-ACCESS read-only
                    STATUS current
                    DESCRIPTION "Re-heating mode"
                    ::= { digitalObjects 34 }

        -- 1.3.6.1.4.1.9839.2.1.1.35
        dehumidification-mode OBJECT-TYPE
                    SYNTAX Integer32 (0..1)
                    UNITS "N/A"
                    MAX-ACCESS read-only
                    STATUS current
                    DESCRIPTION "Dehumidification mode"
                    ::= { digitalObjects 35 }

        -- 1.3.6.1.4.1.9839.2.1.1.36
        addressable-alarm-state OBJECT-TYPE
                    SYNTAX Integer32 (0..1)
                    UNITS "N/A"
                    MAX-ACCESS read-only
                    STATUS current
                    DESCRIPTION "Addressable Alarm State"
                    ::= { digitalObjects 36 }

        -- 1.3.6.1.4.1.9839.2.1.1.37
        unit-in-manual-or-forced-mode OBJECT-TYPE
                    SYNTAX Integer32 (0..1)
                    UNITS "N/A"
                    MAX-ACCESS read-only
                    STATUS current
                    DESCRIPTION "Unit in Manual or Forced mode"
                    ::= { digitalObjects 37 }

        -- 1.3.6.1.4.1.9839.2.1.1.38
        fan-alarm OBJECT-TYPE
                    SYNTAX Integer32 (0..1)
                    UNITS "N/A"
                    MAX-ACCESS read-only
                    STATUS current
                    DESCRIPTION "Fan Alarm"
                    ::= { digitalObjects 38 }

        -- 1.3.6.1.4.1.9839.2.1.1.41
        alarmEXV OBJECT-TYPE
                    SYNTAX Integer32 (0..1)
                    UNITS "N/A"
                    MAX-ACCESS read-only
                    STATUS current
                    DESCRIPTION "Alarm: Electronic Valve Failure"
                    ::= { digitalObjects 41 }

        -- 1.3.6.1.4.1.9839.2.1.1.42
        alarmRoomHH OBJECT-TYPE
                    SYNTAX Integer32 (0..1)
                    UNITS "N/A"
                    MAX-ACCESS read-only
                    STATUS current
                    DESCRIPTION "Alarm: Room High Humidity"
                    ::= { digitalObjects 42 }

        -- 1.3.6.1.4.1.9839.2.1.1.43
        alarmEPROM OBJECT-TYPE
                    SYNTAX Integer32 (0..1)
                    UNITS "N/A"
                    MAX-ACCESS read-only
                    STATUS current
                    DESCRIPTION "Alarm: EEPROM Failed"
                    ::= { digitalObjects 43 }

        -- 1.3.6.1.4.1.9839.2.1.1.44
        alarmFlood OBJECT-TYPE
                    SYNTAX Integer32 (0..1)
                    UNITS "N/A"
                    MAX-ACCESS read-only
                    STATUS current
                    DESCRIPTION "Alarm: Water Leakage Detected"
                    ::= { digitalObjects 44 }

        -- 1.3.6.1.4.1.9839.2.1.1.45
        alarmAccess OBJECT-TYPE
                    SYNTAX Integer32 (0..1)
                    UNITS "N/A"
                    MAX-ACCESS read-only
                    STATUS current
                    DESCRIPTION "Tampering Alarm"
                    ::= { digitalObjects 45 }

        -- 1.3.6.1.4.1.9839.2.1.1.46
        alarmClock OBJECT-TYPE
                    SYNTAX Integer32 (0..1)
                    UNITS "N/A"
                    MAX-ACCESS read-only
                    STATUS current
                    DESCRIPTION "Alarm: Clock Board Failed"
                    ::= { digitalObjects 46 }

        -- 1.3.6.1.4.1.9839.2.1.2
        analogObjects OBJECT IDENTIFIER ::= { telnewMIB 2 }

        -- 1.3.6.1.4.1.9839.2.1.2.1
        room-temperature OBJECT-TYPE
                    SYNTAX Integer32
                    UNITS "degrees C x10"
                    MAX-ACCESS read-only
                    STATUS current
                    DESCRIPTION "Room Temperature"
                    ::= { analogObjects 1 }

        -- 1.3.6.1.4.1.9839.2.1.2.2
        outdoor-temperature OBJECT-TYPE
                    SYNTAX Integer32
                    UNITS "degrees C x10"
                    MAX-ACCESS read-only
                    STATUS current
                    DESCRIPTION "Outdoor Temperature"
                    ::= { analogObjects 2 }

        -- 1.3.6.1.4.1.9839.2.1.2.3
        delivery-air-temperature OBJECT-TYPE
                    SYNTAX Integer32
                    UNITS "degrees C x10"
                    MAX-ACCESS read-only
                    STATUS current
                    DESCRIPTION "Delivery Air Temperature"
                    ::= { analogObjects 3 }

        -- 1.3.6.1.4.1.9839.2.1.2.4
        condensing-temperature OBJECT-TYPE
                    SYNTAX Integer32
                    UNITS "degrees C x10"
                    MAX-ACCESS read-only
                    STATUS current
                    DESCRIPTION "Condensing Temperature (if present)"
                    ::= { analogObjects 4 }

        -- 1.3.6.1.4.1.9839.2.1.2.5
        condensing-pressure OBJECT-TYPE
                    SYNTAX Integer32
                    UNITS "bar x 10"
                    MAX-ACCESS read-only
                    STATUS current
                    DESCRIPTION "Condensing Pressure (if present)"
                    ::= { analogObjects 5 }

        -- 1.3.6.1.4.1.9839.2.1.2.6
        cooling-set-point OBJECT-TYPE
                    SYNTAX Integer32
                    UNITS "degrees C x10"
                    MAX-ACCESS read-write
                    STATUS current
                    DESCRIPTION "Cooling Set Point"
                    ::= { analogObjects 6 }

        -- 1.3.6.1.4.1.9839.2.1.2.7
        cooling-sensitivity OBJECT-TYPE
                    SYNTAX Integer32
                    UNITS "degrees C x10"
                    MAX-ACCESS read-write
                    STATUS current
                    DESCRIPTION "Cooling Sensitivity"
                    ::= { analogObjects 7 }

        -- 1.3.6.1.4.1.9839.2.1.2.8
        heating-set-point OBJECT-TYPE
                    SYNTAX Integer32
                    UNITS "degrees C x10"
                    MAX-ACCESS read-write
                    STATUS current
                    DESCRIPTION "Heating Set point"
                    ::= { analogObjects 8 }

        -- 1.3.6.1.4.1.9839.2.1.2.9
        heating-sensitivity OBJECT-TYPE
                    SYNTAX Integer32
                    UNITS "degrees C x10"
                    MAX-ACCESS read-write
                    STATUS current
                    DESCRIPTION "Heating Sensitivity"
                    ::= { analogObjects 9 }

        -- 1.3.6.1.4.1.9839.2.1.2.10
        room-high-temp-alarm-threshold-1st-level OBJECT-TYPE
                    SYNTAX Integer32
                    UNITS "degrees C x10"
                    MAX-ACCESS read-write
                    STATUS current
                    DESCRIPTION "Room High Temp. Alarm Threshold (1st level)"
                    ::= { analogObjects 10 }

        -- 1.3.6.1.4.1.9839.2.1.2.11
        room-low-temp-alarm-threshold OBJECT-TYPE
                    SYNTAX Integer32
                    UNITS "degrees C x10"
                    MAX-ACCESS read-write
                    STATUS current
                    DESCRIPTION "Room Low Temp. Alarm Threshold"
                    ::= { analogObjects 11 }

        -- 1.3.6.1.4.1.9839.2.1.2.12
        fc-fixed-point-mode-set-point OBJECT-TYPE
                    SYNTAX Integer32
                    UNITS "degrees C x10"
                    MAX-ACCESS read-write
                    STATUS current
                    DESCRIPTION "FC fixed point mode Set Point"
                    ::= { analogObjects 12 }

        -- 1.3.6.1.4.1.9839.2.1.2.15
        damper-limit-ext-max-temperature OBJECT-TYPE
                    SYNTAX Integer32
                    UNITS "degrees C x10"
                    MAX-ACCESS read-write
                    STATUS current
                    DESCRIPTION "Damper limit: Ext. Max. temperature"
                    ::= { analogObjects 15 }

        -- 1.3.6.1.4.1.9839.2.1.2.16
        damper-limit-ext-min-temperature OBJECT-TYPE
                    SYNTAX Integer32
                    UNITS "degrees C x10"
                    MAX-ACCESS read-write
                    STATUS current
                    DESCRIPTION "Damper limit: Ext. Min. temperature"
                     ::= { analogObjects 16 }

        -- 1.3.6.1.4.1.9839.2.1.2.17
        room-relative-humidity OBJECT-TYPE
                    SYNTAX Integer32
                    UNITS "rH% x10"
                    MAX-ACCESS read-only
                    STATUS current
                    DESCRIPTION "Room relative Humidity (if present)"
                    ::= { analogObjects 17 }

        -- 1.3.6.1.4.1.9839.2.1.2.19
        room-high-temp-alarm-threshold-2nd-level OBJECT-TYPE
                    SYNTAX Integer32
                    UNITS "degrees C x10"
                    MAX-ACCESS read-write
                    STATUS current
                    DESCRIPTION "Room High Temp. Alarm Threshold (2nd level)"
                    ::= { analogObjects 19 }

        -- 1.3.6.1.4.1.9839.2.1.2.20
        evaporating-pressure OBJECT-TYPE
                    SYNTAX Integer32
                    UNITS "bar x10"
                    MAX-ACCESS read-only
                    STATUS current
                    DESCRIPTION "Evaporating Pressure (if present)"
                    ::= { analogObjects 20 }

        -- 1.3.6.1.4.1.9839.2.1.2.21
        evaporating-temperature OBJECT-TYPE
                    SYNTAX Integer32
                    UNITS "degrees C x10"
                    MAX-ACCESS read-only
                    STATUS current
                    DESCRIPTION "Evaporating Temperature (if Mechanical Valve present)"
                    ::= { analogObjects 21 }

        -- 1.3.6.1.4.1.9839.2.1.2.22
        suction-temperature OBJECT-TYPE
                    SYNTAX Integer32
                    UNITS "degrees C x10"
                    MAX-ACCESS read-only
                    STATUS current
                    DESCRIPTION "Suction Temperature (if EEV present)"
                    ::= { analogObjects 22 }

        -- 1.3.6.1.4.1.9839.2.1.2.23
        saturation-temperature OBJECT-TYPE
                    SYNTAX Integer32
                    UNITS "degrees C x10"
                    MAX-ACCESS read-only
                    STATUS current
                    DESCRIPTION "Saturation Temperature (if EEV present)"
                    ::= { analogObjects 23 }

        -- 1.3.6.1.4.1.9839.2.1.2.24
        actual-superheat OBJECT-TYPE
                    SYNTAX Integer32
                    UNITS "degrees C x10"
                    MAX-ACCESS read-only
                    STATUS current
                    DESCRIPTION "Actual Superheat (if EEV present)"
                    ::= { analogObjects 24 }

        -- 1.3.6.1.4.1.9839.2.1.3
        integerObjects OBJECT IDENTIFIER ::= { telnewMIB 3 }

        -- 1.3.6.1.4.1.9839.2.1.3.1
        evap-ramp     OBJECT-TYPE
                    SYNTAX Integer32
                    UNITS "N/A"
                    MAX-ACCESS read-only
                    STATUS current
                    DESCRIPTION "Evaporating ramp (fan speed 0-1000)"
                    ::= { integerObjects 1 }

        -- 1.3.6.1.4.1.9839.2.1.3.2
        cond-ramp OBJECT-TYPE
                    SYNTAX Integer32
                    UNITS "N/A"
                    MAX-ACCESS read-only
                    STATUS current
                    DESCRIPTION "Condensanting ramp (fan speed 0-1000)"
                    ::= { integerObjects 2 }

        -- 1.3.6.1.4.1.9839.2.1.3.3
        air-filter-hour-counter OBJECT-TYPE
                    SYNTAX Integer32
                    UNITS "h"
                    MAX-ACCESS read-only
                    STATUS current
                    DESCRIPTION "Air filter hour counter"
                    ::= { integerObjects 3 }

        -- 1.3.6.1.4.1.9839.2.1.3.4
        unit-hour-counter OBJECT-TYPE
                    SYNTAX Integer32
                    UNITS "h"
                    MAX-ACCESS read-only
                    STATUS current
                    DESCRIPTION "Unit hour counter"
                    ::= { integerObjects 4 }

        -- 1.3.6.1.4.1.9839.2.1.3.5
       compressor-hour-counter OBJECT-TYPE
                    SYNTAX Integer32
                    UNITS "h"
                    MAX-ACCESS read-only
                    STATUS current
                    DESCRIPTION "Compressor hour counter"
                    ::= { integerObjects 5 }

        -- 1.3.6.1.4.1.9839.2.1.3.6
        heater-hour-counter OBJECT-TYPE
                    SYNTAX Integer32
                    UNITS "h"
                    MAX-ACCESS read-only
                    STATUS current
                    DESCRIPTION "Heater hour counter"
                    ::= { integerObjects 6 }

        -- 1.3.6.1.4.1.9839.2.1.3.7
        air-filter-hour-counter-threshold OBJECT-TYPE
                    SYNTAX Integer32
                    UNITS "h x100"
                    MAX-ACCESS read-write
                    STATUS current
                    DESCRIPTION "Air filter hour counter Threshold (x100)"
                    ::= { integerObjects 7 }

        -- 1.3.6.1.4.1.9839.2.1.3.8
        unit-hour-counter-threshold OBJECT-TYPE
                    SYNTAX Integer32
                    UNITS "h x100"
                    MAX-ACCESS read-write
                    STATUS current
                    DESCRIPTION "Unit hour counter Threshold (x100)"
                    ::= { integerObjects 8 }

        -- 1.3.6.1.4.1.9839.2.1.3.9
        compressor-hour-counter-threshold OBJECT-TYPE
                    SYNTAX Integer32
                    UNITS "h x100"
                    MAX-ACCESS read-write
                    STATUS current
                    DESCRIPTION "Compressor hour counter Threshold (x100)"
                    ::= { integerObjects 9 }

        -- 1.3.6.1.4.1.9839.2.1.3.10
        heater-hour-counter-threshold OBJECT-TYPE
                    SYNTAX Integer32
                    UNITS "h x100"
                    MAX-ACCESS read-write
                    STATUS current
                    DESCRIPTION "Heater hour counter Threshold (x100)"
                    ::= { integerObjects 10 }

        -- 1.3.6.1.4.1.9839.2.1.3.11
        damper-stroke-time OBJECT-TYPE
                    SYNTAX Integer32
                    UNITS "s"
                    MAX-ACCESS read-write
                    STATUS current
                    DESCRIPTION "Damper stroke time"
                    ::= { integerObjects 11 }

        -- 1.3.6.1.4.1.9839.2.1.3.12
        damper-minimum-opening OBJECT-TYPE
                    SYNTAX Integer32
                    UNITS "%"
                    MAX-ACCESS read-write
                    STATUS current
                    DESCRIPTION "Damper minimum opening %"
                    ::= { integerObjects 12 }

        -- 1.3.6.1.4.1.9839.2.1.3.13
        restart-delay OBJECT-TYPE
                    SYNTAX Integer32
                    UNITS "s"
                    MAX-ACCESS read-write
                    STATUS current
                    DESCRIPTION "Restart delay"
                    ::= { integerObjects 13 }

        -- 1.3.6.1.4.1.9839.2.1.3.14
        start-transient OBJECT-TYPE
                    SYNTAX Integer32
                    UNITS "s"
                    MAX-ACCESS read-write
                    STATUS current
                    DESCRIPTION "Start transient"
                    ::= { integerObjects 14 }

        -- 1.3.6.1.4.1.9839.2.1.3.15
        low-pressure-delay OBJECT-TYPE
                    SYNTAX Integer32
                    UNITS "s"
                    MAX-ACCESS read-write
                    STATUS current
                    DESCRIPTION "Low pressure delay"
                    ::= { integerObjects 15 }

        -- 1.3.6.1.4.1.9839.2.1.3.16
        t-h-alarm-delay OBJECT-TYPE
                    SYNTAX Integer32
                    UNITS "min"
                    MAX-ACCESS read-write
                    STATUS current
                    DESCRIPTION "T+H alarm delay"
                    ::= { integerObjects 16 }

        -- 1.3.6.1.4.1.9839.2.1.3.17
        anti-hunting-regul-constant-time OBJECT-TYPE
                    SYNTAX Integer32
                    UNITS "min"
                    MAX-ACCESS read-write
                    STATUS current
                    DESCRIPTION "Anti hunting regul. constant time"
                    ::= { integerObjects 17 }

        -- 1.3.6.1.4.1.9839.2.1.3.19
        free-cooling-hour-counter OBJECT-TYPE
                    SYNTAX Integer32
                    UNITS "h"
                    MAX-ACCESS read-only
                    STATUS current
                    DESCRIPTION "Free-cooling hour counter"
                    ::= { integerObjects 19 }

        -- 1.3.6.1.4.1.9839.2.1.3.20
        eev-position OBJECT-TYPE
                    SYNTAX Integer32
                    UNITS "steps"
                    MAX-ACCESS read-only
                    STATUS current
                    DESCRIPTION "EEV position (if EEV present)"
                    ::= { integerObjects 20 }

        -- 1.3.6.1.4.1.9839.2.1.3.21
        damper-ramp OBJECT-TYPE
                    SYNTAX Integer32
                    UNITS "N/A"
                    MAX-ACCESS read-only
                    STATUS current
                    DESCRIPTION "Damper ramp (0-1000)"
                    ::= { integerObjects 21 }

	END

--
-- CAREL-telnew.MIB
--
