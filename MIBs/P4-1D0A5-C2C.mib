--
-- Chatsworth Products Inc.
-- Copyright (c) Chatsworth Products Inc., 1998-2012.
-- Version : 1.0.3
-- ************************************************************************

CPI-PDU-P4-1D0A5-C2C-MIB DEFINITIONS ::= BEGIN

IMPORTS
    MODULE-IDENTITY,
    OBJECT-TYPE,
    NOTIFICATION-TYPE,
    IpAddress,
    Integer32,
    Counter64,
    enterprises
        FROM SNMPv2-SMI
    DisplayString
        FROM SNMPv2-TC
    MODULE-COMPLIANCE,
    OBJECT-GROUP,
    NOTIFICATION-GROUP
        FROM SNMPv2-CONF;

cpiProducts MODULE-IDENTITY
    LAST-UPDATED "201211121418Z" -- 12 November 2012
    ORGANIZATION "Chatsworth Products Inc."
    CONTACT-INFO
        "Chatsworth Products, Inc.
        3004 South Austin Avenue
        Georgetown, TX 78626
        Tel: (800) 834-4969
        Email: techsupport@chatsworth.com"
    DESCRIPTION
        "No known updates to the initial released version of the MIB."
    REVISION "201211121418Z"
    DESCRIPTION
        "Initial released version of the MIB."
    ::= { cpi 1 }

cpi OBJECT IDENTIFIER ::= { enterprises 30932 }

cpiPDU OBJECT IDENTIFIER ::= { cpiProducts 1 }

systemInfo OBJECT IDENTIFIER ::= { cpiPDU 1 }

version OBJECT-TYPE
    SYNTAX DisplayString (SIZE (0..14))
    MAX-ACCESS read-only
    STATUS current
    DESCRIPTION
        "Software Version."
    ::= { systemInfo 1 }

modelCode OBJECT-TYPE
    SYNTAX DisplayString (SIZE (0..14))
    MAX-ACCESS read-only
    STATUS current
    DESCRIPTION
        "Model code for the PDU."
    ::= { systemInfo 2 }

hwAddress OBJECT-TYPE
    SYNTAX DisplayString (SIZE (17))
    MAX-ACCESS read-only
    STATUS current
    DESCRIPTION
        "PDU hardware MAC address."
    ::= { systemInfo 3 }

configuration OBJECT IDENTIFIER ::= { cpiPDU 2 }

logInterval OBJECT-TYPE
    SYNTAX Integer32 (0..65535)
    MAX-ACCESS read-write
    STATUS current
    DESCRIPTION
        "The time interval in seconds for logging metrics (disabled if < 10)."
    ::= { configuration 1 }

alarmInterval OBJECT-TYPE
    SYNTAX Integer32 (0..65535)
    MAX-ACCESS read-write
    STATUS current
    DESCRIPTION
        "The time interval in seconds for alarm cycle (disabled if < 10)."
    ::= { configuration 2 }

logDifference OBJECT-TYPE
    SYNTAX Integer32 (0..2000)
    MAX-ACCESS read-write
    STATUS current
    DESCRIPTION
        "The current difference in 1/100 Amps that triggers logging metrics."
    ::= { configuration 3 }

pduIP OBJECT-TYPE
    SYNTAX IpAddress
    MAX-ACCESS read-write
    STATUS current
    DESCRIPTION
        "PDU IP address."
    ::= { configuration 4 }

netOptions OBJECT IDENTIFIER ::= { configuration 5 }

autoIP OBJECT-TYPE
    SYNTAX Integer32 (0..1)
    MAX-ACCESS read-write
    STATUS current
    DESCRIPTION
        "Select dynamic (Auto) or static IP, 0=static and 1=dynamic."
    ::= { netOptions 1 }

autoDNS OBJECT-TYPE
    SYNTAX Integer32 (0..1)
    MAX-ACCESS read-write
    STATUS current
    DESCRIPTION
        "Select dynamic (Auto) or static DNS, 0=static and 1=dynamic."
    ::= { netOptions 2 }

ipV4Enable OBJECT-TYPE
    SYNTAX Integer32 (0..1)
    MAX-ACCESS read-write
    STATUS current
    DESCRIPTION
        "Enable IPV4 Network, 0=disable and 1=enable."
    ::= { netOptions 3 }

snmpEnable OBJECT-TYPE
    SYNTAX Integer32 (0..1)
    MAX-ACCESS read-write
    STATUS current
    DESCRIPTION
        "Enable SNMP network service, 0=disable and 1=enable."
    ::= { netOptions 4 }

telnetEnable OBJECT-TYPE
    SYNTAX Integer32 (0..1)
    MAX-ACCESS read-write
    STATUS current
    DESCRIPTION
        "Enable Telnet service, 0=disable and 1=enable."
    ::= { netOptions 5 }

sshEnable OBJECT-TYPE
    SYNTAX Integer32 (0..1)
    MAX-ACCESS read-write
    STATUS current
    DESCRIPTION
        "Enable SSH Service, 0=disable and 1=enable."
    ::= { netOptions 6 }

httpEnable OBJECT-TYPE
    SYNTAX Integer32 (0..1)
    MAX-ACCESS read-write
    STATUS current
    DESCRIPTION
        "Enable HTTP Service, 0=disable and 1=enable."
    ::= { netOptions 7 }

httpsEnable OBJECT-TYPE
    SYNTAX Integer32 (0..1)
    MAX-ACCESS read-write
    STATUS current
    DESCRIPTION
        "Enable HTTPS Service, 0=disable and 1=enable."
    ::= { netOptions 8 }

subnetMask OBJECT-TYPE
    SYNTAX IpAddress
    MAX-ACCESS read-write
    STATUS current
    DESCRIPTION
        "PDU Subnet Mask."
    ::= { configuration 6 }

gateway OBJECT-TYPE
    SYNTAX IpAddress
    MAX-ACCESS read-write
    STATUS current
    DESCRIPTION
        "PDU Gateway Address."
    ::= { configuration 7 }

dnsHosts OBJECT IDENTIFIER ::= { configuration 8 }

dns1 OBJECT-TYPE
    SYNTAX IpAddress
    MAX-ACCESS read-write
    STATUS current
    DESCRIPTION
        "PDU DNS 1 IP."
    ::= { dnsHosts 1 }

dns2 OBJECT-TYPE
    SYNTAX IpAddress
    MAX-ACCESS read-write
    STATUS current
    DESCRIPTION
        "PDU DNS 2 IP."
    ::= { dnsHosts 2 }

dns3 OBJECT-TYPE
    SYNTAX IpAddress
    MAX-ACCESS read-write
    STATUS current
    DESCRIPTION
        "PDU DNS 3 IP."
    ::= { dnsHosts 3 }

snmpHosts OBJECT IDENTIFIER ::= { configuration 9 }

snmpHost1 OBJECT-TYPE
    SYNTAX IpAddress
    MAX-ACCESS read-write
    STATUS current
    DESCRIPTION
        "SNMP Host 1 IP address."
    ::= { snmpHosts 1 }

snmpHost2 OBJECT-TYPE
    SYNTAX IpAddress
    MAX-ACCESS read-write
    STATUS current
    DESCRIPTION
        "SNMP Host 2 IP address."
    ::= { snmpHosts 2 }

snmpHost3 OBJECT-TYPE
    SYNTAX IpAddress
    MAX-ACCESS read-write
    STATUS current
    DESCRIPTION
        "SNMP Host 3 IP address."
    ::= { snmpHosts 3 }

pduIPv6 OBJECT-TYPE
    SYNTAX DisplayString (SIZE (0..64))
    MAX-ACCESS read-write
    STATUS current
    DESCRIPTION
        "PDU IPV6 address."
    ::= { configuration 10 }

netOptionsIPv6 OBJECT IDENTIFIER ::= { configuration 11 }

autoIPv6 OBJECT-TYPE
    SYNTAX Integer32 (0..1)
    MAX-ACCESS read-write
    STATUS current
    DESCRIPTION
        "Select IPV6 dynamic (Auto) or static IP, 0=static and 1=dynamic."
    ::= { netOptionsIPv6 1 }

autoDNSIPv6 OBJECT-TYPE
    SYNTAX Integer32 (0..1)
    MAX-ACCESS read-write
    STATUS current
    DESCRIPTION
        "Select IPV6 dynamic (Auto) or static DNS, 0=static and 1=dynamic."
    ::= { netOptionsIPv6 2 }

ipv6Enable OBJECT-TYPE
    SYNTAX Integer32 (0..1)
    MAX-ACCESS read-write
    STATUS current
    DESCRIPTION
        "Enable IPV6 Network, 0=disable and 1=enable."
    ::= { netOptionsIPv6 3 }

linkLocalEnable OBJECT-TYPE
    SYNTAX Integer32 (0..1)
    MAX-ACCESS read-write
    STATUS current
    DESCRIPTION
        "Enable IPV6 Link-Local, 0=disable and 1=enable."
    ::= { netOptionsIPv6 4 }

globalAddrEnable OBJECT-TYPE
    SYNTAX Integer32 (0..1)
    MAX-ACCESS read-write
    STATUS current
    DESCRIPTION
        "Enable IPV6 Global Address, 0=disable and 1=enable."
    ::= { netOptionsIPv6 5 }

subnetMaskIPv6 OBJECT-TYPE
    SYNTAX Integer32 (0..127)
    MAX-ACCESS read-write
    STATUS current
    DESCRIPTION
        "PDU IPV6 Subnet Mask."
    ::= { configuration 12 }

gatewayIPv6 OBJECT-TYPE
    SYNTAX DisplayString (SIZE (0..64))
    MAX-ACCESS read-write
    STATUS current
    DESCRIPTION
        "PDU IPV6 Gateway Address."
    ::= { configuration 13 }

dnsHostIPv6 OBJECT IDENTIFIER ::= { configuration 14 }

dns1IPv6 OBJECT-TYPE
    SYNTAX DisplayString (SIZE (0..64))
    MAX-ACCESS read-write
    STATUS current
    DESCRIPTION
        "PDU DNS 2 for IPV6."
    ::= { dnsHostIPv6 1 }

dns2IPv6 OBJECT-TYPE
    SYNTAX DisplayString (SIZE (0..64))
    MAX-ACCESS read-write
    STATUS current
    DESCRIPTION
        "PDU DNS 3 for IPV6."
    ::= { dnsHostIPv6 2 }

dns3IPv6 OBJECT-TYPE
    SYNTAX DisplayString (SIZE (0..64))
    MAX-ACCESS read-write
    STATUS current
    DESCRIPTION
        "PDU DNS 4 for IPV6."
    ::= { dnsHostIPv6 3 }

snmpHostsIPv6 OBJECT IDENTIFIER ::= { configuration 15 }

snmpHost1IPv6 OBJECT-TYPE
    SYNTAX DisplayString (SIZE (0..64))
    MAX-ACCESS read-write
    STATUS current
    DESCRIPTION
        "PDU HOST 1 IPV6."
    ::= { snmpHostsIPv6 1 }

snmpHost2IPv6 OBJECT-TYPE
    SYNTAX DisplayString (SIZE (0..64))
    MAX-ACCESS read-write
    STATUS current
    DESCRIPTION
        "PDU HOST 2 IPV6."
    ::= { snmpHostsIPv6 2 }

snmpHost3IPv6 OBJECT-TYPE
    SYNTAX DisplayString (SIZE (0..64))
    MAX-ACCESS read-write
    STATUS current
    DESCRIPTION
        "PDU HOST 3 IPV6."
    ::= { snmpHostsIPv6 3 }

maxCurrentLimits OBJECT IDENTIFIER ::= { configuration 19 }

branchaMaxCurr OBJECT-TYPE
    SYNTAX Integer32 (0..2000)
    MAX-ACCESS read-write
    STATUS current
    DESCRIPTION
        "Maximum current that BranchA can draw in 1/100 Amps, 0=ignore."
    ::= { maxCurrentLimits 1 }

branchbMaxCurr OBJECT-TYPE
    SYNTAX Integer32 (0..2000)
    MAX-ACCESS read-write
    STATUS current
    DESCRIPTION
        "Maximum current that BranchB can draw in 1/100 Amps, 0=ignore."
    ::= { maxCurrentLimits 2 }

minCurrentLimits OBJECT IDENTIFIER ::= { configuration 20 }

branchaMinCurr OBJECT-TYPE
    SYNTAX Integer32 (0..2000)
    MAX-ACCESS read-write
    STATUS current
    DESCRIPTION
        "Minimum current that BranchA should draw in 1/100 Amps, 0=ignore."
    ::= { minCurrentLimits 1 }

branchbMinCurr OBJECT-TYPE
    SYNTAX Integer32 (0..2000)
    MAX-ACCESS read-write
    STATUS current
    DESCRIPTION
        "Minimum current that BranchB should draw in 1/100 Amps, 0=ignore."
    ::= { minCurrentLimits 2 }

warnHiCurrentLimits OBJECT IDENTIFIER ::= { configuration 21 }

branchaWarnHiCurr OBJECT-TYPE
    SYNTAX Integer32 (0..2000)
    MAX-ACCESS read-write
    STATUS current
    DESCRIPTION
        "Warning upper current limit that BranchA can draw in 1/100 Amps, 0=ignore."
    ::= { warnHiCurrentLimits 1 }

branchbWarnHiCurr OBJECT-TYPE
    SYNTAX Integer32 (0..2000)
    MAX-ACCESS read-write
    STATUS current
    DESCRIPTION
        "Warning upper current limit that BranchB can draw in 1/100 Amps, 0=ignore."
    ::= { warnHiCurrentLimits 2 }

warnLoCurrentLimits OBJECT IDENTIFIER ::= { configuration 22 }

branchaWarnLoCurr OBJECT-TYPE
    SYNTAX Integer32 (0..2000)
    MAX-ACCESS read-write
    STATUS current
    DESCRIPTION
        "Warning lower current limit that BranchA can draw in 1/100 Amps, 0=ignore."
    ::= { warnLoCurrentLimits 1 }

branchbWarnLoCurr OBJECT-TYPE
    SYNTAX Integer32 (0..2000)
    MAX-ACCESS read-write
    STATUS current
    DESCRIPTION
        "Warning lower current limit that BranchB can draw in 1/100 Amps, 0=ignore."
    ::= { warnLoCurrentLimits 2 }

maxVoltageLimits OBJECT IDENTIFIER ::= { configuration 24 }

branchaMaxVolt OBJECT-TYPE
    SYNTAX Integer32 (0..1800)
    MAX-ACCESS read-write
    STATUS current
    DESCRIPTION
        "Maximum voltage that BranchA can reach up to in volts, 0=ignore."
    ::= { maxVoltageLimits 1 }

branchbMaxVolt OBJECT-TYPE
    SYNTAX Integer32 (0..1800)
    MAX-ACCESS read-write
    STATUS current
    DESCRIPTION
        "Maximum voltage that BranchB can reach up to in volts, 0=ignore."
    ::= { maxVoltageLimits 2 }

minVoltageLimits OBJECT IDENTIFIER ::= { configuration 25 }

branchaMinVolt OBJECT-TYPE
    SYNTAX Integer32 (0..1800)
    MAX-ACCESS read-write
    STATUS current
    DESCRIPTION
        "Minimum voltage that BranchA can sag in volts, 0=ignore."
    ::= { minVoltageLimits 1 }

branchbMinVolt OBJECT-TYPE
    SYNTAX Integer32 (0..1800)
    MAX-ACCESS read-write
    STATUS current
    DESCRIPTION
        "Minimum voltage that BranchB can sag in volts, 0=ignore."
    ::= { minVoltageLimits 2 }

warnHiVoltageLimits OBJECT IDENTIFIER ::= { configuration 26 }

branchaWarnHiVolt OBJECT-TYPE
    SYNTAX Integer32 (0..1800)
    MAX-ACCESS read-write
    STATUS current
    DESCRIPTION
        "Warning High voltage in volts that BranchA can reach before triggering warning notifications, 0=ignore."
    ::= { warnHiVoltageLimits 1 }

branchbWarnHiVolt OBJECT-TYPE
    SYNTAX Integer32 (0..1800)
    MAX-ACCESS read-write
    STATUS current
    DESCRIPTION
        "Warning High voltage in volts that BranchB can reach before triggering warning notifications, 0=ignore."
    ::= { warnHiVoltageLimits 2 }

warnLoVoltageLimits OBJECT IDENTIFIER ::= { configuration 27 }

branchaWarnLoVolt OBJECT-TYPE
    SYNTAX Integer32 (0..1800)
    MAX-ACCESS read-write
    STATUS current
    DESCRIPTION
        "Warning Low voltage in volts that BranchA can sag before triggering notifications, 0=ignore."
    ::= { warnLoVoltageLimits 1 }

branchbWarnLoVolt OBJECT-TYPE
    SYNTAX Integer32 (0..1800)
    MAX-ACCESS read-write
    STATUS current
    DESCRIPTION
        "Warning Low voltage in volts that BranchB can sag before triggering notifications, 0=ignore."
    ::= { warnLoVoltageLimits 2 }

receptacleMaxCurrent OBJECT IDENTIFIER ::= { configuration 28 }

port1MaxCurr OBJECT-TYPE
    SYNTAX Integer32 (0..2000)
    MAX-ACCESS read-write
    STATUS current
    DESCRIPTION
        "Port1 maximum current in 1/100 Amps."
    ::= { receptacleMaxCurrent 1 }

port2MaxCurr OBJECT-TYPE
    SYNTAX Integer32 (0..2000)
    MAX-ACCESS read-write
    STATUS current
    DESCRIPTION
        "Port2 maximum current in 1/100 Amps."
    ::= { receptacleMaxCurrent 2 }

port3MaxCurr OBJECT-TYPE
    SYNTAX Integer32 (0..2000)
    MAX-ACCESS read-write
    STATUS current
    DESCRIPTION
        "Port3 maximum current in 1/100 Amps."
    ::= { receptacleMaxCurrent 3 }

port4MaxCurr OBJECT-TYPE
    SYNTAX Integer32 (0..2000)
    MAX-ACCESS read-write
    STATUS current
    DESCRIPTION
        "Port4 maximum current in 1/100 Amps."
    ::= { receptacleMaxCurrent 4 }

port5MaxCurr OBJECT-TYPE
    SYNTAX Integer32 (0..2000)
    MAX-ACCESS read-write
    STATUS current
    DESCRIPTION
        "Port5 maximum current in 1/100 Amps."
    ::= { receptacleMaxCurrent 5 }

port6MaxCurr OBJECT-TYPE
    SYNTAX Integer32 (0..2000)
    MAX-ACCESS read-write
    STATUS current
    DESCRIPTION
        "Port6 maximum current in 1/100 Amps."
    ::= { receptacleMaxCurrent 6 }

port7MaxCurr OBJECT-TYPE
    SYNTAX Integer32 (0..2000)
    MAX-ACCESS read-write
    STATUS current
    DESCRIPTION
        "Port7 maximum current in 1/100 Amps."
    ::= { receptacleMaxCurrent 7 }

port8MaxCurr OBJECT-TYPE
    SYNTAX Integer32 (0..2000)
    MAX-ACCESS read-write
    STATUS current
    DESCRIPTION
        "Port8 maximum current in 1/100 Amps."
    ::= { receptacleMaxCurrent 8 }

port9MaxCurr OBJECT-TYPE
    SYNTAX Integer32 (0..2000)
    MAX-ACCESS read-write
    STATUS current
    DESCRIPTION
        "Port9 maximum current in 1/100 Amps."
    ::= { receptacleMaxCurrent 9 }

port10MaxCurr OBJECT-TYPE
    SYNTAX Integer32 (0..2000)
    MAX-ACCESS read-write
    STATUS current
    DESCRIPTION
        "Port10 maximum current in 1/100 Amps."
    ::= { receptacleMaxCurrent 10 }

port11MaxCurr OBJECT-TYPE
    SYNTAX Integer32 (0..2000)
    MAX-ACCESS read-write
    STATUS current
    DESCRIPTION
        "Port11 maximum current in 1/100 Amps."
    ::= { receptacleMaxCurrent 11 }

port12MaxCurr OBJECT-TYPE
    SYNTAX Integer32 (0..2000)
    MAX-ACCESS read-write
    STATUS current
    DESCRIPTION
        "Port12 maximum current in 1/100 Amps."
    ::= { receptacleMaxCurrent 12 }

port13MaxCurr OBJECT-TYPE
    SYNTAX Integer32 (0..2000)
    MAX-ACCESS read-write
    STATUS current
    DESCRIPTION
        "Port13 maximum current in 1/100 Amps."
    ::= { receptacleMaxCurrent 13 }

port14MaxCurr OBJECT-TYPE
    SYNTAX Integer32 (0..2000)
    MAX-ACCESS read-write
    STATUS current
    DESCRIPTION
        "Port14 maximum current in 1/100 Amps."
    ::= { receptacleMaxCurrent 14 }

port15MaxCurr OBJECT-TYPE
    SYNTAX Integer32 (0..2000)
    MAX-ACCESS read-write
    STATUS current
    DESCRIPTION
        "Port15 maximum current in 1/100 Amps."
    ::= { receptacleMaxCurrent 15 }

port16MaxCurr OBJECT-TYPE
    SYNTAX Integer32 (0..2000)
    MAX-ACCESS read-write
    STATUS current
    DESCRIPTION
        "Port16 maximum current in 1/100 Amps."
    ::= { receptacleMaxCurrent 16 }

port17MaxCurr OBJECT-TYPE
    SYNTAX Integer32 (0..2000)
    MAX-ACCESS read-write
    STATUS current
    DESCRIPTION
        "Port17 maximum current in 1/100 Amps."
    ::= { receptacleMaxCurrent 17 }

port18MaxCurr OBJECT-TYPE
    SYNTAX Integer32 (0..2000)
    MAX-ACCESS read-write
    STATUS current
    DESCRIPTION
        "Port18 maximum current in 1/100 Amps."
    ::= { receptacleMaxCurrent 18 }

port19MaxCurr OBJECT-TYPE
    SYNTAX Integer32 (0..2000)
    MAX-ACCESS read-write
    STATUS current
    DESCRIPTION
        "Port19 maximum current in 1/100 Amps."
    ::= { receptacleMaxCurrent 19 }

port20MaxCurr OBJECT-TYPE
    SYNTAX Integer32 (0..2000)
    MAX-ACCESS read-write
    STATUS current
    DESCRIPTION
        "Port20 maximum current in 1/100 Amps."
    ::= { receptacleMaxCurrent 20 }

port21MaxCurr OBJECT-TYPE
    SYNTAX Integer32 (0..2000)
    MAX-ACCESS read-write
    STATUS current
    DESCRIPTION
        "Port21 maximum current in 1/100 Amps."
    ::= { receptacleMaxCurrent 21 }

port22MaxCurr OBJECT-TYPE
    SYNTAX Integer32 (0..2000)
    MAX-ACCESS read-write
    STATUS current
    DESCRIPTION
        "Port22 maximum current in 1/100 Amps."
    ::= { receptacleMaxCurrent 22 }

port23MaxCurr OBJECT-TYPE
    SYNTAX Integer32 (0..2000)
    MAX-ACCESS read-write
    STATUS current
    DESCRIPTION
        "Port23 maximum current in 1/100 Amps."
    ::= { receptacleMaxCurrent 23 }

port24MaxCurr OBJECT-TYPE
    SYNTAX Integer32 (0..2000)
    MAX-ACCESS read-write
    STATUS current
    DESCRIPTION
        "Port24 maximum current in 1/100 Amps."
    ::= { receptacleMaxCurrent 24 }

receptacleMinCurrent OBJECT IDENTIFIER ::= { configuration 29 }

port1MinCurr OBJECT-TYPE
    SYNTAX Integer32 (0..2000)
    MAX-ACCESS read-write
    STATUS current
    DESCRIPTION
        "Port1 minimum current in 1/100 Amps."
    ::= { receptacleMinCurrent 1 }

port2MinCurr OBJECT-TYPE
    SYNTAX Integer32 (0..2000)
    MAX-ACCESS read-write
    STATUS current
    DESCRIPTION
        "Port2 minimum current in 1/100 Amps."
    ::= { receptacleMinCurrent 2 }

port3MinCurr OBJECT-TYPE
    SYNTAX Integer32 (0..2000)
    MAX-ACCESS read-write
    STATUS current
    DESCRIPTION
        "Port3 minimum current in 1/100 Amps."
    ::= { receptacleMinCurrent 3 }

port4MinCurr OBJECT-TYPE
    SYNTAX Integer32 (0..2000)
    MAX-ACCESS read-write
    STATUS current
    DESCRIPTION
        "Port4 minimum current in 1/100 Amps."
    ::= { receptacleMinCurrent 4 }

port5MinCurr OBJECT-TYPE
    SYNTAX Integer32 (0..2000)
    MAX-ACCESS read-write
    STATUS current
    DESCRIPTION
        "Port5 minimum current in 1/100 Amps."
    ::= { receptacleMinCurrent 5 }

port6MinCurr OBJECT-TYPE
    SYNTAX Integer32 (0..2000)
    MAX-ACCESS read-write
    STATUS current
    DESCRIPTION
        "Port6 minimum current in 1/100 Amps."
    ::= { receptacleMinCurrent 6 }

port7MinCurr OBJECT-TYPE
    SYNTAX Integer32 (0..2000)
    MAX-ACCESS read-write
    STATUS current
    DESCRIPTION
        "Port7 minimum current in 1/100 Amps."
    ::= { receptacleMinCurrent 7 }

port8MinCurr OBJECT-TYPE
    SYNTAX Integer32 (0..2000)
    MAX-ACCESS read-write
    STATUS current
    DESCRIPTION
        "Port8 minimum current in 1/100 Amps."
    ::= { receptacleMinCurrent 8 }

port9MinCurr OBJECT-TYPE
    SYNTAX Integer32 (0..2000)
    MAX-ACCESS read-write
    STATUS current
    DESCRIPTION
        "Port9 minimum current in 1/100 Amps."
    ::= { receptacleMinCurrent 9 }

port10MinCurr OBJECT-TYPE
    SYNTAX Integer32 (0..2000)
    MAX-ACCESS read-write
    STATUS current
    DESCRIPTION
        "Port10 minimum current in 1/100 Amps."
    ::= { receptacleMinCurrent 10 }

port11MinCurr OBJECT-TYPE
    SYNTAX Integer32 (0..2000)
    MAX-ACCESS read-write
    STATUS current
    DESCRIPTION
        "Port11 minimum current in 1/100 Amps."
    ::= { receptacleMinCurrent 11 }

port12MinCurr OBJECT-TYPE
    SYNTAX Integer32 (0..2000)
    MAX-ACCESS read-write
    STATUS current
    DESCRIPTION
        "Port12 minimum current in 1/100 Amps."
    ::= { receptacleMinCurrent 12 }

port13MinCurr OBJECT-TYPE
    SYNTAX Integer32 (0..2000)
    MAX-ACCESS read-write
    STATUS current
    DESCRIPTION
        "Port13 minimum current in 1/100 Amps."
    ::= { receptacleMinCurrent 13 }

port14MinCurr OBJECT-TYPE
    SYNTAX Integer32 (0..2000)
    MAX-ACCESS read-write
    STATUS current
    DESCRIPTION
        "Port14 minimum current in 1/100 Amps."
    ::= { receptacleMinCurrent 14 }

port15MinCurr OBJECT-TYPE
    SYNTAX Integer32 (0..2000)
    MAX-ACCESS read-write
    STATUS current
    DESCRIPTION
        "Port15 minimum current in 1/100 Amps."
    ::= { receptacleMinCurrent 15 }

port16MinCurr OBJECT-TYPE
    SYNTAX Integer32 (0..2000)
    MAX-ACCESS read-write
    STATUS current
    DESCRIPTION
        "Port16 minimum current in 1/100 Amps."
    ::= { receptacleMinCurrent 16 }

port17MinCurr OBJECT-TYPE
    SYNTAX Integer32 (0..2000)
    MAX-ACCESS read-write
    STATUS current
    DESCRIPTION
        "Port17 minimum current in 1/100 Amps."
    ::= { receptacleMinCurrent 17 }

port18MinCurr OBJECT-TYPE
    SYNTAX Integer32 (0..2000)
    MAX-ACCESS read-write
    STATUS current
    DESCRIPTION
        "Port18 minimum current in 1/100 Amps."
    ::= { receptacleMinCurrent 18 }

port19MinCurr OBJECT-TYPE
    SYNTAX Integer32 (0..2000)
    MAX-ACCESS read-write
    STATUS current
    DESCRIPTION
        "Port19 minimum current in 1/100 Amps."
    ::= { receptacleMinCurrent 19 }

port20MinCurr OBJECT-TYPE
    SYNTAX Integer32 (0..2000)
    MAX-ACCESS read-write
    STATUS current
    DESCRIPTION
        "Port20 minimum current in 1/100 Amps."
    ::= { receptacleMinCurrent 20 }

port21MinCurr OBJECT-TYPE
    SYNTAX Integer32 (0..2000)
    MAX-ACCESS read-write
    STATUS current
    DESCRIPTION
        "Port21 minimum current in 1/100 Amps."
    ::= { receptacleMinCurrent 21 }

port22MinCurr OBJECT-TYPE
    SYNTAX Integer32 (0..2000)
    MAX-ACCESS read-write
    STATUS current
    DESCRIPTION
        "Port22 minimum current in 1/100 Amps."
    ::= { receptacleMinCurrent 22 }

port23MinCurr OBJECT-TYPE
    SYNTAX Integer32 (0..2000)
    MAX-ACCESS read-write
    STATUS current
    DESCRIPTION
        "Port23 minimum current in 1/100 Amps."
    ::= { receptacleMinCurrent 23 }

port24MinCurr OBJECT-TYPE
    SYNTAX Integer32 (0..2000)
    MAX-ACCESS read-write
    STATUS current
    DESCRIPTION
        "Port24 minimum current in 1/100 Amps."
    ::= { receptacleMinCurrent 24 }

receptacleWarnHiCurrent OBJECT IDENTIFIER ::= { configuration 30 }

port1WarnHiCurr OBJECT-TYPE
    SYNTAX Integer32 (0..2000)
    MAX-ACCESS read-write
    STATUS current
    DESCRIPTION
        "Port1 warning high current in 1/100 Amps."
    ::= { receptacleWarnHiCurrent 1 }

port2WarnHiCurr OBJECT-TYPE
    SYNTAX Integer32 (0..2000)
    MAX-ACCESS read-write
    STATUS current
    DESCRIPTION
        "Port2 warning high current in 1/100 Amps."
    ::= { receptacleWarnHiCurrent 2 }

port3WarnHiCurr OBJECT-TYPE
    SYNTAX Integer32 (0..2000)
    MAX-ACCESS read-write
    STATUS current
    DESCRIPTION
        "Port3 warning high current in 1/100 Amps."
    ::= { receptacleWarnHiCurrent 3 }

port4WarnHiCurr OBJECT-TYPE
    SYNTAX Integer32 (0..2000)
    MAX-ACCESS read-write
    STATUS current
    DESCRIPTION
        "Port4 warning high current in 1/100 Amps."
    ::= { receptacleWarnHiCurrent 4 }

port5WarnHiCurr OBJECT-TYPE
    SYNTAX Integer32 (0..2000)
    MAX-ACCESS read-write
    STATUS current
    DESCRIPTION
        "Port5 warning high current in 1/100 Amps."
    ::= { receptacleWarnHiCurrent 5 }

port6WarnHiCurr OBJECT-TYPE
    SYNTAX Integer32 (0..2000)
    MAX-ACCESS read-write
    STATUS current
    DESCRIPTION
        "Port6 warning high current in 1/100 Amps."
    ::= { receptacleWarnHiCurrent 6 }

port7WarnHiCurr OBJECT-TYPE
    SYNTAX Integer32 (0..2000)
    MAX-ACCESS read-write
    STATUS current
    DESCRIPTION
        "Port7 warning high current in 1/100 Amps."
    ::= { receptacleWarnHiCurrent 7 }

port8WarnHiCurr OBJECT-TYPE
    SYNTAX Integer32 (0..2000)
    MAX-ACCESS read-write
    STATUS current
    DESCRIPTION
        "Port8 warning high current in 1/100 Amps."
    ::= { receptacleWarnHiCurrent 8 }

port9WarnHiCurr OBJECT-TYPE
    SYNTAX Integer32 (0..2000)
    MAX-ACCESS read-write
    STATUS current
    DESCRIPTION
        "Port9 warning high current in 1/100 Amps."
    ::= { receptacleWarnHiCurrent 9 }

port10WarnHiCurr OBJECT-TYPE
    SYNTAX Integer32 (0..2000)
    MAX-ACCESS read-write
    STATUS current
    DESCRIPTION
        "Port10 warning high current in 1/100 Amps."
    ::= { receptacleWarnHiCurrent 10 }

port11WarnHiCurr OBJECT-TYPE
    SYNTAX Integer32 (0..2000)
    MAX-ACCESS read-write
    STATUS current
    DESCRIPTION
        "Port11 warning high current in 1/100 Amps."
    ::= { receptacleWarnHiCurrent 11 }

port12WarnHiCurr OBJECT-TYPE
    SYNTAX Integer32 (0..2000)
    MAX-ACCESS read-write
    STATUS current
    DESCRIPTION
        "Port12 warning high current in 1/100 Amps."
    ::= { receptacleWarnHiCurrent 12 }

port13WarnHiCurr OBJECT-TYPE
    SYNTAX Integer32 (0..2000)
    MAX-ACCESS read-write
    STATUS current
    DESCRIPTION
        "Port13 warning high current in 1/100 Amps."
    ::= { receptacleWarnHiCurrent 13 }

port14WarnHiCurr OBJECT-TYPE
    SYNTAX Integer32 (0..2000)
    MAX-ACCESS read-write
    STATUS current
    DESCRIPTION
        "Port14 warning high current in 1/100 Amps."
    ::= { receptacleWarnHiCurrent 14 }

port15WarnHiCurr OBJECT-TYPE
    SYNTAX Integer32 (0..2000)
    MAX-ACCESS read-write
    STATUS current
    DESCRIPTION
        "Port15 warning high current in 1/100 Amps."
    ::= { receptacleWarnHiCurrent 15 }

port16WarnHiCurr OBJECT-TYPE
    SYNTAX Integer32 (0..2000)
    MAX-ACCESS read-write
    STATUS current
    DESCRIPTION
        "Port16 warning high current in 1/100 Amps."
    ::= { receptacleWarnHiCurrent 16 }

port17WarnHiCurr OBJECT-TYPE
    SYNTAX Integer32 (0..2000)
    MAX-ACCESS read-write
    STATUS current
    DESCRIPTION
        "Port17 warning high current in 1/100 Amps."
    ::= { receptacleWarnHiCurrent 17 }

port18WarnHiCurr OBJECT-TYPE
    SYNTAX Integer32 (0..2000)
    MAX-ACCESS read-write
    STATUS current
    DESCRIPTION
        "Port18 warning high current in 1/100 Amps."
    ::= { receptacleWarnHiCurrent 18 }

port19WarnHiCurr OBJECT-TYPE
    SYNTAX Integer32 (0..2000)
    MAX-ACCESS read-write
    STATUS current
    DESCRIPTION
        "Port19 warning high current in 1/100 Amps."
    ::= { receptacleWarnHiCurrent 19 }

port20WarnHiCurr OBJECT-TYPE
    SYNTAX Integer32 (0..2000)
    MAX-ACCESS read-write
    STATUS current
    DESCRIPTION
        "Port20 warning high current in 1/100 Amps."
    ::= { receptacleWarnHiCurrent 20 }

port21WarnHiCurr OBJECT-TYPE
    SYNTAX Integer32 (0..2000)
    MAX-ACCESS read-write
    STATUS current
    DESCRIPTION
        "Port21 warning high current in 1/100 Amps."
    ::= { receptacleWarnHiCurrent 21 }

port22WarnHiCurr OBJECT-TYPE
    SYNTAX Integer32 (0..2000)
    MAX-ACCESS read-write
    STATUS current
    DESCRIPTION
        "Port22 warning high current in 1/100 Amps."
    ::= { receptacleWarnHiCurrent 22 }

port23WarnHiCurr OBJECT-TYPE
    SYNTAX Integer32 (0..2000)
    MAX-ACCESS read-write
    STATUS current
    DESCRIPTION
        "Port23 warning high current in 1/100 Amps."
    ::= { receptacleWarnHiCurrent 23 }

port24WarnHiCurr OBJECT-TYPE
    SYNTAX Integer32 (0..2000)
    MAX-ACCESS read-write
    STATUS current
    DESCRIPTION
        "Port24 warning high current in 1/100 Amps."
    ::= { receptacleWarnHiCurrent 24 }

receptacleWarnLoCurrent OBJECT IDENTIFIER ::= { configuration 31 }

port1WarnLoCurr OBJECT-TYPE
    SYNTAX Integer32 (0..2000)
    MAX-ACCESS read-write
    STATUS current
    DESCRIPTION
        "Port1 warning low current in 1/100 Amps."
    ::= { receptacleWarnLoCurrent 1 }

port2WarnLoCurr OBJECT-TYPE
    SYNTAX Integer32 (0..2000)
    MAX-ACCESS read-write
    STATUS current
    DESCRIPTION
        "Port2 warning low current in 1/100 Amps."
    ::= { receptacleWarnLoCurrent 2 }

port3WarnLoCurr OBJECT-TYPE
    SYNTAX Integer32 (0..2000)
    MAX-ACCESS read-write
    STATUS current
    DESCRIPTION
        "Port3 warning low current in 1/100 Amps."
    ::= { receptacleWarnLoCurrent 3 }

port4WarnLoCurr OBJECT-TYPE
    SYNTAX Integer32 (0..2000)
    MAX-ACCESS read-write
    STATUS current
    DESCRIPTION
        "Port4 warning low current in 1/100 Amps."
    ::= { receptacleWarnLoCurrent 4 }

port5WarnLoCurr OBJECT-TYPE
    SYNTAX Integer32 (0..2000)
    MAX-ACCESS read-write
    STATUS current
    DESCRIPTION
        "Port5 warning low current in 1/100 Amps."
    ::= { receptacleWarnLoCurrent 5 }

port6WarnLoCurr OBJECT-TYPE
    SYNTAX Integer32 (0..2000)
    MAX-ACCESS read-write
    STATUS current
    DESCRIPTION
        "Port6 warning low current in 1/100 Amps."
    ::= { receptacleWarnLoCurrent 6 }

port7WarnLoCurr OBJECT-TYPE
    SYNTAX Integer32 (0..2000)
    MAX-ACCESS read-write
    STATUS current
    DESCRIPTION
        "Port7 warning low current in 1/100 Amps."
    ::= { receptacleWarnLoCurrent 7 }

port8WarnLoCurr OBJECT-TYPE
    SYNTAX Integer32 (0..2000)
    MAX-ACCESS read-write
    STATUS current
    DESCRIPTION
        "Port8 warning low current in 1/100 Amps."
    ::= { receptacleWarnLoCurrent 8 }

port9WarnLoCurr OBJECT-TYPE
    SYNTAX Integer32 (0..2000)
    MAX-ACCESS read-write
    STATUS current
    DESCRIPTION
        "Port9 warning low current in 1/100 Amps."
    ::= { receptacleWarnLoCurrent 9 }

port10WarnLoCurr OBJECT-TYPE
    SYNTAX Integer32 (0..2000)
    MAX-ACCESS read-write
    STATUS current
    DESCRIPTION
        "Port10 warning low current in 1/100 Amps."
    ::= { receptacleWarnLoCurrent 10 }

port11WarnLoCurr OBJECT-TYPE
    SYNTAX Integer32 (0..2000)
    MAX-ACCESS read-write
    STATUS current
    DESCRIPTION
        "Port11 warning low current in 1/100 Amps."
    ::= { receptacleWarnLoCurrent 11 }

port12WarnLoCurr OBJECT-TYPE
    SYNTAX Integer32 (0..2000)
    MAX-ACCESS read-write
    STATUS current
    DESCRIPTION
        "Port12 warning low current in 1/100 Amps."
    ::= { receptacleWarnLoCurrent 12 }

port13WarnLoCurr OBJECT-TYPE
    SYNTAX Integer32 (0..2000)
    MAX-ACCESS read-write
    STATUS current
    DESCRIPTION
        "Port13 warning low current in 1/100 Amps."
    ::= { receptacleWarnLoCurrent 13 }

port14WarnLoCurr OBJECT-TYPE
    SYNTAX Integer32 (0..2000)
    MAX-ACCESS read-write
    STATUS current
    DESCRIPTION
        "Port14 warning low current in 1/100 Amps."
    ::= { receptacleWarnLoCurrent 14 }

port15WarnLoCurr OBJECT-TYPE
    SYNTAX Integer32 (0..2000)
    MAX-ACCESS read-write
    STATUS current
    DESCRIPTION
        "Port15 warning low current in 1/100 Amps."
    ::= { receptacleWarnLoCurrent 15 }

port16WarnLoCurr OBJECT-TYPE
    SYNTAX Integer32 (0..2000)
    MAX-ACCESS read-write
    STATUS current
    DESCRIPTION
        "Port16 warning low current in 1/100 Amps."
    ::= { receptacleWarnLoCurrent 16 }

port17WarnLoCurr OBJECT-TYPE
    SYNTAX Integer32 (0..2000)
    MAX-ACCESS read-write
    STATUS current
    DESCRIPTION
        "Port17 warning low current in 1/100 Amps."
    ::= { receptacleWarnLoCurrent 17 }

port18WarnLoCurr OBJECT-TYPE
    SYNTAX Integer32 (0..2000)
    MAX-ACCESS read-write
    STATUS current
    DESCRIPTION
        "Port18 warning low current in 1/100 Amps."
    ::= { receptacleWarnLoCurrent 18 }

port19WarnLoCurr OBJECT-TYPE
    SYNTAX Integer32 (0..2000)
    MAX-ACCESS read-write
    STATUS current
    DESCRIPTION
        "Port19 warning low current in 1/100 Amps."
    ::= { receptacleWarnLoCurrent 19 }

port20WarnLoCurr OBJECT-TYPE
    SYNTAX Integer32 (0..2000)
    MAX-ACCESS read-write
    STATUS current
    DESCRIPTION
        "Port20 warning low current in 1/100 Amps."
    ::= { receptacleWarnLoCurrent 20 }

port21WarnLoCurr OBJECT-TYPE
    SYNTAX Integer32 (0..2000)
    MAX-ACCESS read-write
    STATUS current
    DESCRIPTION
        "Port21 warning low current in 1/100 Amps."
    ::= { receptacleWarnLoCurrent 21 }

port22WarnLoCurr OBJECT-TYPE
    SYNTAX Integer32 (0..2000)
    MAX-ACCESS read-write
    STATUS current
    DESCRIPTION
        "Port22 warning low current in 1/100 Amps."
    ::= { receptacleWarnLoCurrent 22 }

port23WarnLoCurr OBJECT-TYPE
    SYNTAX Integer32 (0..2000)
    MAX-ACCESS read-write
    STATUS current
    DESCRIPTION
        "Port23 warning low current in 1/100 Amps."
    ::= { receptacleWarnLoCurrent 23 }

port24WarnLoCurr OBJECT-TYPE
    SYNTAX Integer32 (0..2000)
    MAX-ACCESS read-write
    STATUS current
    DESCRIPTION
        "Port24 warning low current in 1/100 Amps."
    ::= { receptacleWarnLoCurrent 24 }

maxTempLimits OBJECT IDENTIFIER ::= { configuration 32 }

maxTempProbe1 OBJECT-TYPE
    SYNTAX Integer32 (0..20000)
    MAX-ACCESS read-write
    STATUS current
    DESCRIPTION
        "Maximum temperature for Probe 1 in 1/100 of degrees Fahrenheit, 0=ignore."
    ::= { maxTempLimits 1 }

maxTempProbe2 OBJECT-TYPE
    SYNTAX Integer32 (0..20000)
    MAX-ACCESS read-write
    STATUS current
    DESCRIPTION
        "Maximum temperature for Probe 2 in 1/100 of degrees Fahrenheit, 0=ignore."
    ::= { maxTempLimits 2 }

minTempLimits OBJECT IDENTIFIER ::= { configuration 33 }

minTempProbe1 OBJECT-TYPE
    SYNTAX Integer32 (0..20000)
    MAX-ACCESS read-write
    STATUS current
    DESCRIPTION
        "Minimum temperature for Probe 1 in 1/100 of degrees Fahrenheit, 0=ignore."
    ::= { minTempLimits 1 }

minTempProbe2 OBJECT-TYPE
    SYNTAX Integer32 (0..20000)
    MAX-ACCESS read-write
    STATUS current
    DESCRIPTION
        "Minimum temperature for Probe 2 in 1/100 of degrees Fahrenheit, 0=ignore."
    ::= { minTempLimits 2 }

warnHiTempLimits OBJECT IDENTIFIER ::= { configuration 34 }

warnHiTempProbe1 OBJECT-TYPE
    SYNTAX Integer32 (0..20000)
    MAX-ACCESS read-write
    STATUS current
    DESCRIPTION
        "Warning High temperature for Probe 1 in 1/100 of degrees Fahrenheit, 0=ignore."
    ::= { warnHiTempLimits 1 }

warnHiTempProbe2 OBJECT-TYPE
    SYNTAX Integer32 (0..20000)
    MAX-ACCESS read-write
    STATUS current
    DESCRIPTION
        "Warning High temperature for Probe 2 in 1/100 of degrees Fahrenheit, 0=ignore."
    ::= { warnHiTempLimits 2 }

warnLoTempLimits OBJECT IDENTIFIER ::= { configuration 35 }

warnLoTempProbe1 OBJECT-TYPE
    SYNTAX Integer32 (0..20000)
    MAX-ACCESS read-write
    STATUS current
    DESCRIPTION
        "Warning Low temperature for Probe 1 in 1/100 of degrees Fahrenheit, 0=ignore."
    ::= { warnLoTempLimits 1 }

warnLoTempProbe2 OBJECT-TYPE
    SYNTAX Integer32 (0..20000)
    MAX-ACCESS read-write
    STATUS current
    DESCRIPTION
        "Warning Low temperature for Probe 2 in 1/100 of degrees Fahrenheit, 0=ignore."
    ::= { warnLoTempLimits 2 }

maxHumidityLimits OBJECT IDENTIFIER ::= { configuration 36 }

maxHumidProbe1 OBJECT-TYPE
    SYNTAX Integer32 (0..10000)
    MAX-ACCESS read-write
    STATUS current
    DESCRIPTION
        "Maximum humidity for Probe 1 in 1/100  of %, 0=ignore."
    ::= { maxHumidityLimits 1 }

maxHumidProbe2 OBJECT-TYPE
    SYNTAX Integer32 (0..10000)
    MAX-ACCESS read-write
    STATUS current
    DESCRIPTION
        "Maximum humidity for Probe 2 in 1/100  of %, 0=ignore."
    ::= { maxHumidityLimits 2 }

minHumidityLimits OBJECT IDENTIFIER ::= { configuration 37 }

minHumidProbe1 OBJECT-TYPE
    SYNTAX Integer32 (0..10000)
    MAX-ACCESS read-write
    STATUS current
    DESCRIPTION
        "Minimum humidity for Probe 1 in 1/100  of %, 0=ignore."
    ::= { minHumidityLimits 1 }

minHumidProbe2 OBJECT-TYPE
    SYNTAX Integer32 (0..10000)
    MAX-ACCESS read-write
    STATUS current
    DESCRIPTION
        "Minimum humidity for Probe 2 in 1/100  of %, 0=ignore."
    ::= { minHumidityLimits 2 }

warnHiHumidityLimits OBJECT IDENTIFIER ::= { configuration 38 }

warnHiHumidProbe1 OBJECT-TYPE
    SYNTAX Integer32 (0..10000)
    MAX-ACCESS read-write
    STATUS current
    DESCRIPTION
        "Warning High humidity for Probe 1 in 1/100  of %, 0=ignore."
    ::= { warnHiHumidityLimits 1 }

warnHiHumidProbe2 OBJECT-TYPE
    SYNTAX Integer32 (0..10000)
    MAX-ACCESS read-write
    STATUS current
    DESCRIPTION
        "Warning High humidity for Probe 2 in 1/100  of %, 0=ignore."
    ::= { warnHiHumidityLimits 2 }

warnLoHumidityLimits OBJECT IDENTIFIER ::= { configuration 39 }

warnLoHumidProbe1 OBJECT-TYPE
    SYNTAX Integer32 (0..10000)
    MAX-ACCESS read-write
    STATUS current
    DESCRIPTION
        "Warning Low humidity for Probe 1 in 1/100  of %, 0=ignore."
    ::= { warnLoHumidityLimits 1 }

warnLoHumidProbe2 OBJECT-TYPE
    SYNTAX Integer32 (0..10000)
    MAX-ACCESS read-write
    STATUS current
    DESCRIPTION
        "Warning Low humidity for Probe 2 in 1/100  of %, 0=ignore."
    ::= { warnLoHumidityLimits 2 }

pduName OBJECT-TYPE
    SYNTAX DisplayString (SIZE (0..64))
    MAX-ACCESS read-write
    STATUS current
    DESCRIPTION
        "PDU Name."
    ::= { configuration 40 }

pduDescrip OBJECT-TYPE
    SYNTAX DisplayString (SIZE (0..64))
    MAX-ACCESS read-write
    STATUS current
    DESCRIPTION
        "PDU Description."
    ::= { configuration 41 }

receptacleNames OBJECT IDENTIFIER ::= { configuration 42 }

port1Name OBJECT-TYPE
    SYNTAX DisplayString (SIZE (0..64))
    MAX-ACCESS read-write
    STATUS current
    DESCRIPTION
        "Port1 Name."
    ::= { receptacleNames 1 }

port2Name OBJECT-TYPE
    SYNTAX DisplayString (SIZE (0..64))
    MAX-ACCESS read-write
    STATUS current
    DESCRIPTION
        "Port2 Name."
    ::= { receptacleNames 2 }

port3Name OBJECT-TYPE
    SYNTAX DisplayString (SIZE (0..64))
    MAX-ACCESS read-write
    STATUS current
    DESCRIPTION
        "Port3 Name."
    ::= { receptacleNames 3 }

port4Name OBJECT-TYPE
    SYNTAX DisplayString (SIZE (0..64))
    MAX-ACCESS read-write
    STATUS current
    DESCRIPTION
        "Port4 Name."
    ::= { receptacleNames 4 }

port5Name OBJECT-TYPE
    SYNTAX DisplayString (SIZE (0..64))
    MAX-ACCESS read-write
    STATUS current
    DESCRIPTION
        "Port5 Name."
    ::= { receptacleNames 5 }

port6Name OBJECT-TYPE
    SYNTAX DisplayString (SIZE (0..64))
    MAX-ACCESS read-write
    STATUS current
    DESCRIPTION
        "Port6 Name."
    ::= { receptacleNames 6 }

port7Name OBJECT-TYPE
    SYNTAX DisplayString (SIZE (0..64))
    MAX-ACCESS read-write
    STATUS current
    DESCRIPTION
        "Port7 Name."
    ::= { receptacleNames 7 }

port8Name OBJECT-TYPE
    SYNTAX DisplayString (SIZE (0..64))
    MAX-ACCESS read-write
    STATUS current
    DESCRIPTION
        "Port8 Name."
    ::= { receptacleNames 8 }

port9Name OBJECT-TYPE
    SYNTAX DisplayString (SIZE (0..64))
    MAX-ACCESS read-write
    STATUS current
    DESCRIPTION
        "Port9 Name."
    ::= { receptacleNames 9 }

port10Name OBJECT-TYPE
    SYNTAX DisplayString (SIZE (0..64))
    MAX-ACCESS read-write
    STATUS current
    DESCRIPTION
        "Port10 Name."
    ::= { receptacleNames 10 }

port11Name OBJECT-TYPE
    SYNTAX DisplayString (SIZE (0..64))
    MAX-ACCESS read-write
    STATUS current
    DESCRIPTION
        "Port11 Name."
    ::= { receptacleNames 11 }

port12Name OBJECT-TYPE
    SYNTAX DisplayString (SIZE (0..64))
    MAX-ACCESS read-write
    STATUS current
    DESCRIPTION
        "Port12 Name."
    ::= { receptacleNames 12 }

port13Name OBJECT-TYPE
    SYNTAX DisplayString (SIZE (0..64))
    MAX-ACCESS read-write
    STATUS current
    DESCRIPTION
        "Port13 Name."
    ::= { receptacleNames 13 }

port14Name OBJECT-TYPE
    SYNTAX DisplayString (SIZE (0..64))
    MAX-ACCESS read-write
    STATUS current
    DESCRIPTION
        "Port14 Name."
    ::= { receptacleNames 14 }

port15Name OBJECT-TYPE
    SYNTAX DisplayString (SIZE (0..64))
    MAX-ACCESS read-write
    STATUS current
    DESCRIPTION
        "Port15 Name."
    ::= { receptacleNames 15 }

port16Name OBJECT-TYPE
    SYNTAX DisplayString (SIZE (0..64))
    MAX-ACCESS read-write
    STATUS current
    DESCRIPTION
        "Port16 Name."
    ::= { receptacleNames 16 }

port17Name OBJECT-TYPE
    SYNTAX DisplayString (SIZE (0..64))
    MAX-ACCESS read-write
    STATUS current
    DESCRIPTION
        "Port17 Name."
    ::= { receptacleNames 17 }

port18Name OBJECT-TYPE
    SYNTAX DisplayString (SIZE (0..64))
    MAX-ACCESS read-write
    STATUS current
    DESCRIPTION
        "Port18 Name."
    ::= { receptacleNames 18 }

port19Name OBJECT-TYPE
    SYNTAX DisplayString (SIZE (0..64))
    MAX-ACCESS read-write
    STATUS current
    DESCRIPTION
        "Port19 Name."
    ::= { receptacleNames 19 }

port20Name OBJECT-TYPE
    SYNTAX DisplayString (SIZE (0..64))
    MAX-ACCESS read-write
    STATUS current
    DESCRIPTION
        "Port20 Name."
    ::= { receptacleNames 20 }

port21Name OBJECT-TYPE
    SYNTAX DisplayString (SIZE (0..64))
    MAX-ACCESS read-write
    STATUS current
    DESCRIPTION
        "Port21 Name."
    ::= { receptacleNames 21 }

port22Name OBJECT-TYPE
    SYNTAX DisplayString (SIZE (0..64))
    MAX-ACCESS read-write
    STATUS current
    DESCRIPTION
        "Port22 Name."
    ::= { receptacleNames 22 }

port23Name OBJECT-TYPE
    SYNTAX DisplayString (SIZE (0..64))
    MAX-ACCESS read-write
    STATUS current
    DESCRIPTION
        "Port23 Name."
    ::= { receptacleNames 23 }

port24Name OBJECT-TYPE
    SYNTAX DisplayString (SIZE (0..64))
    MAX-ACCESS read-write
    STATUS current
    DESCRIPTION
        "Port24 Name."
    ::= { receptacleNames 24 }

receptacleDescrips OBJECT IDENTIFIER ::= { configuration 43 }

port1Descrip OBJECT-TYPE
    SYNTAX DisplayString (SIZE (0..64))
    MAX-ACCESS read-write
    STATUS current
    DESCRIPTION
        "Port1 Description."
    ::= { receptacleDescrips 1 }

port2Descrip OBJECT-TYPE
    SYNTAX DisplayString (SIZE (0..64))
    MAX-ACCESS read-write
    STATUS current
    DESCRIPTION
        "Port2 Description."
    ::= { receptacleDescrips 2 }

port3Descrip OBJECT-TYPE
    SYNTAX DisplayString (SIZE (0..64))
    MAX-ACCESS read-write
    STATUS current
    DESCRIPTION
        "Port3 Description."
    ::= { receptacleDescrips 3 }

port4Descrip OBJECT-TYPE
    SYNTAX DisplayString (SIZE (0..64))
    MAX-ACCESS read-write
    STATUS current
    DESCRIPTION
        "Port4 Description."
    ::= { receptacleDescrips 4 }

port5Descrip OBJECT-TYPE
    SYNTAX DisplayString (SIZE (0..64))
    MAX-ACCESS read-write
    STATUS current
    DESCRIPTION
        "Port5 Description."
    ::= { receptacleDescrips 5 }

port6Descrip OBJECT-TYPE
    SYNTAX DisplayString (SIZE (0..64))
    MAX-ACCESS read-write
    STATUS current
    DESCRIPTION
        "Port6 Description."
    ::= { receptacleDescrips 6 }

port7Descrip OBJECT-TYPE
    SYNTAX DisplayString (SIZE (0..64))
    MAX-ACCESS read-write
    STATUS current
    DESCRIPTION
        "Port7 Description."
    ::= { receptacleDescrips 7 }

port8Descrip OBJECT-TYPE
    SYNTAX DisplayString (SIZE (0..64))
    MAX-ACCESS read-write
    STATUS current
    DESCRIPTION
        "Port8 Description."
    ::= { receptacleDescrips 8 }

port9Descrip OBJECT-TYPE
    SYNTAX DisplayString (SIZE (0..64))
    MAX-ACCESS read-write
    STATUS current
    DESCRIPTION
        "Port9 Description."
    ::= { receptacleDescrips 9 }

port10Descrip OBJECT-TYPE
    SYNTAX DisplayString (SIZE (0..64))
    MAX-ACCESS read-write
    STATUS current
    DESCRIPTION
        "Port10 Description."
    ::= { receptacleDescrips 10 }

port11Descrip OBJECT-TYPE
    SYNTAX DisplayString (SIZE (0..64))
    MAX-ACCESS read-write
    STATUS current
    DESCRIPTION
        "Port11 Description."
    ::= { receptacleDescrips 11 }

port12Descrip OBJECT-TYPE
    SYNTAX DisplayString (SIZE (0..64))
    MAX-ACCESS read-write
    STATUS current
    DESCRIPTION
        "Port12 Description."
    ::= { receptacleDescrips 12 }

port13Descrip OBJECT-TYPE
    SYNTAX DisplayString (SIZE (0..64))
    MAX-ACCESS read-write
    STATUS current
    DESCRIPTION
        "Port13 Description."
    ::= { receptacleDescrips 13 }

port14Descrip OBJECT-TYPE
    SYNTAX DisplayString (SIZE (0..64))
    MAX-ACCESS read-write
    STATUS current
    DESCRIPTION
        "Port14 Description."
    ::= { receptacleDescrips 14 }

port15Descrip OBJECT-TYPE
    SYNTAX DisplayString (SIZE (0..64))
    MAX-ACCESS read-write
    STATUS current
    DESCRIPTION
        "Port15 Description."
    ::= { receptacleDescrips 15 }

port16Descrip OBJECT-TYPE
    SYNTAX DisplayString (SIZE (0..64))
    MAX-ACCESS read-write
    STATUS current
    DESCRIPTION
        "Port16 Description."
    ::= { receptacleDescrips 16 }

port17Descrip OBJECT-TYPE
    SYNTAX DisplayString (SIZE (0..64))
    MAX-ACCESS read-write
    STATUS current
    DESCRIPTION
        "Port17 Description."
    ::= { receptacleDescrips 17 }

port18Descrip OBJECT-TYPE
    SYNTAX DisplayString (SIZE (0..64))
    MAX-ACCESS read-write
    STATUS current
    DESCRIPTION
        "Port18 Description."
    ::= { receptacleDescrips 18 }

port19Descrip OBJECT-TYPE
    SYNTAX DisplayString (SIZE (0..64))
    MAX-ACCESS read-write
    STATUS current
    DESCRIPTION
        "Port19 Description."
    ::= { receptacleDescrips 19 }

port20Descrip OBJECT-TYPE
    SYNTAX DisplayString (SIZE (0..64))
    MAX-ACCESS read-write
    STATUS current
    DESCRIPTION
        "Port20 Description."
    ::= { receptacleDescrips 20 }

port21Descrip OBJECT-TYPE
    SYNTAX DisplayString (SIZE (0..64))
    MAX-ACCESS read-write
    STATUS current
    DESCRIPTION
        "Port21 Description."
    ::= { receptacleDescrips 21 }

port22Descrip OBJECT-TYPE
    SYNTAX DisplayString (SIZE (0..64))
    MAX-ACCESS read-write
    STATUS current
    DESCRIPTION
        "Port22 Description."
    ::= { receptacleDescrips 22 }

port23Descrip OBJECT-TYPE
    SYNTAX DisplayString (SIZE (0..64))
    MAX-ACCESS read-write
    STATUS current
    DESCRIPTION
        "Port23 Description."
    ::= { receptacleDescrips 23 }

port24Descrip OBJECT-TYPE
    SYNTAX DisplayString (SIZE (0..64))
    MAX-ACCESS read-write
    STATUS current
    DESCRIPTION
        "Port24 Description."
    ::= { receptacleDescrips 24 }

groupNames OBJECT IDENTIFIER ::= { configuration 50 }

group1Name OBJECT-TYPE
    SYNTAX DisplayString (SIZE (0..64))
    MAX-ACCESS read-write
    STATUS current
    DESCRIPTION
        "Name for GROUP 1 of receptacles."
    ::= { groupNames 1 }

group2Name OBJECT-TYPE
    SYNTAX DisplayString (SIZE (0..64))
    MAX-ACCESS read-write
    STATUS current
    DESCRIPTION
        "Name for GROUP 2 of receptacles."
    ::= { groupNames 2 }

group3Name OBJECT-TYPE
    SYNTAX DisplayString (SIZE (0..64))
    MAX-ACCESS read-write
    STATUS current
    DESCRIPTION
        "Name for GROUP 3 of receptacles."
    ::= { groupNames 3 }

group4Name OBJECT-TYPE
    SYNTAX DisplayString (SIZE (0..64))
    MAX-ACCESS read-write
    STATUS current
    DESCRIPTION
        "Name for GROUP 4 of receptacles."
    ::= { groupNames 4 }

group5Name OBJECT-TYPE
    SYNTAX DisplayString (SIZE (0..64))
    MAX-ACCESS read-write
    STATUS current
    DESCRIPTION
        "Name for GROUP 5 of receptacles."
    ::= { groupNames 5 }

group6Name OBJECT-TYPE
    SYNTAX DisplayString (SIZE (0..64))
    MAX-ACCESS read-write
    STATUS current
    DESCRIPTION
        "Name for GROUP 6 of receptacles."
    ::= { groupNames 6 }

group7Name OBJECT-TYPE
    SYNTAX DisplayString (SIZE (0..64))
    MAX-ACCESS read-write
    STATUS current
    DESCRIPTION
        "Name for GROUP 7 of receptacles."
    ::= { groupNames 7 }

group8Name OBJECT-TYPE
    SYNTAX DisplayString (SIZE (0..64))
    MAX-ACCESS read-write
    STATUS current
    DESCRIPTION
        "Name for GROUP 8 of receptacles."
    ::= { groupNames 8 }

group9Name OBJECT-TYPE
    SYNTAX DisplayString (SIZE (0..64))
    MAX-ACCESS read-write
    STATUS current
    DESCRIPTION
        "Name for GROUP 9 of receptacles."
    ::= { groupNames 9 }

group10Name OBJECT-TYPE
    SYNTAX DisplayString (SIZE (0..64))
    MAX-ACCESS read-write
    STATUS current
    DESCRIPTION
        "Name for GROUP 10 of receptacles."
    ::= { groupNames 10 }

group11Name OBJECT-TYPE
    SYNTAX DisplayString (SIZE (0..64))
    MAX-ACCESS read-write
    STATUS current
    DESCRIPTION
        "Name for GROUP 11 of receptacles."
    ::= { groupNames 11 }

group12Name OBJECT-TYPE
    SYNTAX DisplayString (SIZE (0..64))
    MAX-ACCESS read-write
    STATUS current
    DESCRIPTION
        "Name for GROUP 12 of receptacles."
    ::= { groupNames 12 }

group13Name OBJECT-TYPE
    SYNTAX DisplayString (SIZE (0..64))
    MAX-ACCESS read-write
    STATUS current
    DESCRIPTION
        "Name for GROUP 13 of receptacles."
    ::= { groupNames 13 }

group14Name OBJECT-TYPE
    SYNTAX DisplayString (SIZE (0..64))
    MAX-ACCESS read-write
    STATUS current
    DESCRIPTION
        "Name for GROUP 14 of receptacles."
    ::= { groupNames 14 }

group15Name OBJECT-TYPE
    SYNTAX DisplayString (SIZE (0..64))
    MAX-ACCESS read-write
    STATUS current
    DESCRIPTION
        "Name for GROUP 15 of receptacles."
    ::= { groupNames 15 }

group16Name OBJECT-TYPE
    SYNTAX DisplayString (SIZE (0..64))
    MAX-ACCESS read-write
    STATUS current
    DESCRIPTION
        "Name for GROUP 16 of receptacles."
    ::= { groupNames 16 }

groupMaps OBJECT IDENTIFIER ::= { configuration 51 }

group1Map OBJECT-TYPE
    SYNTAX OCTET STRING (SIZE (0..256))
    MAX-ACCESS read-write
    STATUS current
    DESCRIPTION
        "Map for Group 1 of receptacels."
    ::= { groupMaps 1 }

group2Map OBJECT-TYPE
    SYNTAX OCTET STRING (SIZE (0..256))
    MAX-ACCESS read-write
    STATUS current
    DESCRIPTION
        "Map for Group 2 of receptacels."
    ::= { groupMaps 2 }

group3Map OBJECT-TYPE
    SYNTAX OCTET STRING (SIZE (0..256))
    MAX-ACCESS read-write
    STATUS current
    DESCRIPTION
        "Map for Group 3 of receptacels."
    ::= { groupMaps 3 }

group4Map OBJECT-TYPE
    SYNTAX OCTET STRING (SIZE (0..256))
    MAX-ACCESS read-write
    STATUS current
    DESCRIPTION
        "Map for Group 4 of receptacels."
    ::= { groupMaps 4 }

group5Map OBJECT-TYPE
    SYNTAX OCTET STRING (SIZE (0..256))
    MAX-ACCESS read-write
    STATUS current
    DESCRIPTION
        "Map for Group 5 of receptacels."
    ::= { groupMaps 5 }

group6Map OBJECT-TYPE
    SYNTAX OCTET STRING (SIZE (0..256))
    MAX-ACCESS read-write
    STATUS current
    DESCRIPTION
        "Map for Group 6 of receptacels."
    ::= { groupMaps 6 }

group7Map OBJECT-TYPE
    SYNTAX OCTET STRING (SIZE (0..256))
    MAX-ACCESS read-write
    STATUS current
    DESCRIPTION
        "Map for Group 7 of receptacels."
    ::= { groupMaps 7 }

group8Map OBJECT-TYPE
    SYNTAX OCTET STRING (SIZE (0..256))
    MAX-ACCESS read-write
    STATUS current
    DESCRIPTION
        "Map for Group 8 of receptacels."
    ::= { groupMaps 8 }

group9Map OBJECT-TYPE
    SYNTAX OCTET STRING (SIZE (0..256))
    MAX-ACCESS read-write
    STATUS current
    DESCRIPTION
        "Map for Group 9 of receptacels."
    ::= { groupMaps 9 }

group10Map OBJECT-TYPE
    SYNTAX OCTET STRING (SIZE (0..256))
    MAX-ACCESS read-write
    STATUS current
    DESCRIPTION
        "Map for Group 10 of receptacels."
    ::= { groupMaps 10 }

group11Map OBJECT-TYPE
    SYNTAX OCTET STRING (SIZE (0..256))
    MAX-ACCESS read-write
    STATUS current
    DESCRIPTION
        "Map for Group 11 of receptacels."
    ::= { groupMaps 11 }

group12Map OBJECT-TYPE
    SYNTAX OCTET STRING (SIZE (0..256))
    MAX-ACCESS read-write
    STATUS current
    DESCRIPTION
        "Map for Group 12 of receptacels."
    ::= { groupMaps 12 }

group13Map OBJECT-TYPE
    SYNTAX OCTET STRING (SIZE (0..256))
    MAX-ACCESS read-write
    STATUS current
    DESCRIPTION
        "Map for Group 13 of receptacels."
    ::= { groupMaps 13 }

group14Map OBJECT-TYPE
    SYNTAX OCTET STRING (SIZE (0..256))
    MAX-ACCESS read-write
    STATUS current
    DESCRIPTION
        "Map for Group 14 of receptacels."
    ::= { groupMaps 14 }

group15Map OBJECT-TYPE
    SYNTAX OCTET STRING (SIZE (0..256))
    MAX-ACCESS read-write
    STATUS current
    DESCRIPTION
        "Map for Group 15 of receptacels."
    ::= { groupMaps 15 }

group16Map OBJECT-TYPE
    SYNTAX OCTET STRING (SIZE (0..256))
    MAX-ACCESS read-write
    STATUS current
    DESCRIPTION
        "Map for Group 16 of receptacels."
    ::= { groupMaps 16 }

dispTimeout OBJECT-TYPE
    SYNTAX Integer32 (0..65535)
    MAX-ACCESS read-write
    STATUS current
    DESCRIPTION
        "Inactivity timeout in seconds to blank the local display (disabled if 0)."
    ::= { configuration 55 }

loginTimeout OBJECT-TYPE
    SYNTAX Integer32 (0..65535)
    MAX-ACCESS read-write
    STATUS current
    DESCRIPTION
        "Inactivity timeout in seconds to terminate a logged in session (disabled if 0)."
    ::= { configuration 56 }

dispBrightness OBJECT-TYPE
    SYNTAX Integer32 (0..9)
    MAX-ACCESS read-write
    STATUS current
    DESCRIPTION
        "The relative brightness of the local display (0 in min, 9 is max)."
    ::= { configuration 57 }

pduOptions OBJECT IDENTIFIER ::= { configuration 58 }

inputTop OBJECT-TYPE
    SYNTAX Integer32 (0..1)
    MAX-ACCESS read-write
    STATUS current
    DESCRIPTION
        "Input cord entry orientation, 1 = top, 0 = bottom."
    ::= { pduOptions 1 }

pduRole OBJECT-TYPE
    SYNTAX Integer32 (0..1)
    MAX-ACCESS read-write
    STATUS current
    DESCRIPTION
        "PDU Role, 1 = primary, 0 = secondary."
    ::= { pduOptions 2 }

celsiusTemp OBJECT-TYPE
    SYNTAX Integer32 (0..1)
    MAX-ACCESS read-write
    STATUS current
    DESCRIPTION
        "Temperature units, 1=Celsius, 0=Fahrenheit."
    ::= { pduOptions 3 }

enableWeb OBJECT-TYPE
    SYNTAX Integer32 (0..1)
    MAX-ACCESS read-write
    STATUS current
    DESCRIPTION
        "Enable Web Access, 1 = enable, 0 = disable."
    ::= { pduOptions 4 }

snmpHostOnly OBJECT-TYPE
    SYNTAX Integer32 (0..1)
    MAX-ACCESS read-write
    STATUS current
    DESCRIPTION
        "Restrict access to SNMP via listed Hosts only, 1 = listed SNMP hosts only, 0 = any host."
    ::= { pduOptions 5 }

disLocalAuth OBJECT-TYPE
    SYNTAX Integer32 (0..1)
    MAX-ACCESS read-write
    STATUS current
    DESCRIPTION
        "Disable local authentication, 1 = disable, 0 = enable."
    ::= { pduOptions 6 }

enaRadiusAuth OBJECT-TYPE
    SYNTAX Integer32 (0..1)
    MAX-ACCESS read-write
    STATUS current
    DESCRIPTION
        "Enable Radius authentication, 1 = disable, 0 = enable."
    ::= { pduOptions 7 }

enaADAuth OBJECT-TYPE
    SYNTAX Integer32 (0..1)
    MAX-ACCESS read-write
    STATUS current
    DESCRIPTION
        "Enable Active Directory authentication, 1 = disable, 0 = enable."
    ::= { pduOptions 8 }

enaSMTP OBJECT-TYPE
    SYNTAX Integer32 (0..1)
    MAX-ACCESS read-write
    STATUS current
    DESCRIPTION
        "Enable Mail Notification, 1 = disable, 0 = enable."
    ::= { pduOptions 9 }

httpPorts OBJECT IDENTIFIER ::= { configuration 59 }

httpPort OBJECT-TYPE
    SYNTAX Integer32 (0..65535)
    MAX-ACCESS read-write
    STATUS current
    DESCRIPTION
        "Port for unsecure HTTP access."
    ::= { httpPorts 1 }

httpsPort OBJECT-TYPE
    SYNTAX Integer32 (0..65535)
    MAX-ACCESS read-write
    STATUS current
    DESCRIPTION
        "Port for secure HTTPS access."
    ::= { httpPorts 2 }

sshPorts OBJECT IDENTIFIER ::= { configuration 60 }

sshPort OBJECT-TYPE
    SYNTAX Integer32 (0..65535)
    MAX-ACCESS read-write
    STATUS current
    DESCRIPTION
        "Port for secure SSH access."
    ::= { sshPorts 1 }

telnetPort OBJECT-TYPE
    SYNTAX Integer32 (0..65535)
    MAX-ACCESS read-write
    STATUS current
    DESCRIPTION
        "Port for non secure Telnet access."
    ::= { sshPorts 2 }

snmpPorts OBJECT IDENTIFIER ::= { configuration 61 }

snmpQueryPort OBJECT-TYPE
    SYNTAX Integer32 (0..65535)
    MAX-ACCESS read-write
    STATUS current
    DESCRIPTION
        "Port for SNMP query access."
    ::= { snmpPorts 1 }

snmpTrapPort OBJECT-TYPE
    SYNTAX Integer32 (0..65535)
    MAX-ACCESS read-write
    STATUS current
    DESCRIPTION
        "Port for SNMP trap."
    ::= { snmpPorts 2 }

smtpPorts OBJECT IDENTIFIER ::= { configuration 62 }

smtpSendPort OBJECT-TYPE
    SYNTAX Integer32 (0..65535)
    MAX-ACCESS read-write
    STATUS current
    DESCRIPTION
        "Port for SMTP send."
    ::= { smtpPorts 1 }

smtpReceivePort OBJECT-TYPE
    SYNTAX Integer32 (0..65535)
    MAX-ACCESS read-write
    STATUS current
    DESCRIPTION
        "Port for SMTP Receive."
    ::= { smtpPorts 2 }

rfcTimeServer OBJECT-TYPE
    SYNTAX DisplayString (SIZE (0..64))
    MAX-ACCESS read-write
    STATUS current
    DESCRIPTION
        "RFC Time Server Address."
    ::= { configuration 63 }

ntpTimeServer OBJECT-TYPE
    SYNTAX DisplayString (SIZE (0..64))
    MAX-ACCESS read-write
    STATUS current
    DESCRIPTION
        "NTP Time Server Address."
    ::= { configuration 64 }

smtpServer OBJECT-TYPE
    SYNTAX DisplayString (SIZE (0..64))
    MAX-ACCESS read-write
    STATUS current
    DESCRIPTION
        "Email Server Address."
    ::= { configuration 65 }

snmpReadComm OBJECT-TYPE
    SYNTAX DisplayString (SIZE (0..64))
    MAX-ACCESS read-write
    STATUS current
    DESCRIPTION
        "SNMP Read Community."
    ::= { configuration 66 }

snmpWriteComm OBJECT-TYPE
    SYNTAX DisplayString (SIZE (0..64))
    MAX-ACCESS read-write
    STATUS current
    DESCRIPTION
        "SNMP Write Community."
    ::= { configuration 67 }

snmpUSMuserName OBJECT-TYPE
    SYNTAX DisplayString (SIZE (0..64))
    MAX-ACCESS read-write
    STATUS current
    DESCRIPTION
        "SNMP USM User Name."
    ::= { configuration 68 }

snmpSecurityLevelAlgorithm OBJECT IDENTIFIER ::= { configuration 69 }

snmpSecurityLevel OBJECT-TYPE
    SYNTAX Integer32 (0..4)
    MAX-ACCESS read-write
    STATUS current
    DESCRIPTION
        "Security Level for SNMP: 0 = v1, 1 = v2c, 2 = v3 no authentication,
        3 = v3 with authentication only, 4 = v3 with authentication and privacy"
    ::= { snmpSecurityLevelAlgorithm 1 }

snmpAuthAlgo OBJECT-TYPE
    SYNTAX Integer32 (0..1)
    MAX-ACCESS read-write
    STATUS current
    DESCRIPTION
        "Authentication Algorithm for SNMP: 0 = SHA, 1 = MD5."
    ::= { snmpSecurityLevelAlgorithm 2 }

snmpPrivAlgo OBJECT-TYPE
    SYNTAX Integer32 (0..1)
    MAX-ACCESS read-write
    STATUS current
    DESCRIPTION
        "Privacy Algorithm for SNMP: 0 = DES, 1 = AES."
    ::= { snmpSecurityLevelAlgorithm 3 }

snmpAuthPasswd OBJECT-TYPE
    SYNTAX DisplayString (SIZE (0..64))
    MAX-ACCESS read-write
    STATUS current
    DESCRIPTION
        "SNMP Authentication Password."
    ::= { configuration 70 }

snmpPrivPasswd OBJECT-TYPE
    SYNTAX DisplayString (SIZE (0..64))
    MAX-ACCESS read-write
    STATUS current
    DESCRIPTION
        "SNMP Privacy Password."
    ::= { configuration 71 }

snmpContextName OBJECT-TYPE
    SYNTAX DisplayString (SIZE (0..64))
    MAX-ACCESS read-write
    STATUS current
    DESCRIPTION
        "SNMP Context Name."
    ::= { configuration 72 }

snmpEngineID OBJECT-TYPE
    SYNTAX DisplayString (SIZE (0..64))
    MAX-ACCESS read-write
    STATUS current
    DESCRIPTION
        "SNMP Engine ID."
    ::= { configuration 73 }

snmpLocAuthKey OBJECT-TYPE
    SYNTAX DisplayString (SIZE (0..64))
    MAX-ACCESS read-write
    STATUS current
    DESCRIPTION
        "SNMP Local Authentication Key."
    ::= { configuration 74 }

snmpLocPrivKey OBJECT-TYPE
    SYNTAX DisplayString (SIZE (0..64))
    MAX-ACCESS read-write
    STATUS current
    DESCRIPTION
        "SNMP Local Privacy Key."
    ::= { configuration 75 }

smtpUserName OBJECT-TYPE
    SYNTAX DisplayString (SIZE (0..64))
    MAX-ACCESS read-write
    STATUS current
    DESCRIPTION
        "PDU Email User Login Name."
    ::= { configuration 76 }

smtpUserPasswd OBJECT-TYPE
    SYNTAX DisplayString (SIZE (0..64))
    MAX-ACCESS read-write
    STATUS current
    DESCRIPTION
        "PDU Email User Login Password."
    ::= { configuration 77 }

smtpEmailAddr OBJECT-TYPE
    SYNTAX DisplayString (SIZE (0..64))
    MAX-ACCESS read-write
    STATUS current
    DESCRIPTION
        "PDU Email address."
    ::= { configuration 78 }

smtpEmailDestinations OBJECT IDENTIFIER ::= { configuration 79 }

smtpEmailDestination1 OBJECT-TYPE
    SYNTAX DisplayString (SIZE (0..64))
    MAX-ACCESS read-write
    STATUS current
    DESCRIPTION
        "Email destination for recipient 0."
    ::= { smtpEmailDestinations 1 }

smtpEmailDestination2 OBJECT-TYPE
    SYNTAX DisplayString (SIZE (0..64))
    MAX-ACCESS read-write
    STATUS current
    DESCRIPTION
        "Email destination for recipient 1."
    ::= { smtpEmailDestinations 2 }

smtpEmailDestination3 OBJECT-TYPE
    SYNTAX DisplayString (SIZE (0..64))
    MAX-ACCESS read-write
    STATUS current
    DESCRIPTION
        "Email destination for recipient 2."
    ::= { smtpEmailDestinations 3 }

smtpServOptions OBJECT-TYPE
    SYNTAX Integer32 (0..2)
    MAX-ACCESS read-write
    STATUS current
    DESCRIPTION
        "SMTP Server Options."
    ::= { configuration 80 }

radiusServer OBJECT-TYPE
    SYNTAX DisplayString (SIZE (0..64))
    MAX-ACCESS read-write
    STATUS current
    DESCRIPTION
        "Radius Authentication Server."
    ::= { configuration 81 }

radiusSHSecret OBJECT-TYPE
    SYNTAX DisplayString (SIZE (0..64))
    MAX-ACCESS read-write
    STATUS current
    DESCRIPTION
        "Radius Shared Secret."
    ::= { configuration 82 }

radiusNASServer OBJECT-TYPE
    SYNTAX DisplayString (SIZE (0..64))
    MAX-ACCESS read-write
    STATUS current
    DESCRIPTION
        "Radius Network Access Service."
    ::= { configuration 83 }

radiusNASPorts OBJECT IDENTIFIER ::= { configuration 84 }

radiusPort OBJECT-TYPE
    SYNTAX Integer32 (0..65535)
    MAX-ACCESS read-write
    STATUS current
    DESCRIPTION
        "Port for radius authentication."
    ::= { radiusNASPorts 1 }

nasPort OBJECT-TYPE
    SYNTAX Integer32 (0..65535)
    MAX-ACCESS read-write
    STATUS current
    DESCRIPTION
        "Port for Radius Network Access Service."
    ::= { radiusNASPorts 2 }

adServer OBJECT-TYPE
    SYNTAX DisplayString (SIZE (0..64))
    MAX-ACCESS read-write
    STATUS current
    DESCRIPTION
        "Active Directory Server."
    ::= { configuration 85 }

adDomain OBJECT-TYPE
    SYNTAX DisplayString (SIZE (0..64))
    MAX-ACCESS read-write
    STATUS current
    DESCRIPTION
        "Active Directory Domain."
    ::= { configuration 86 }

adAllPorts OBJECT IDENTIFIER ::= { configuration 87 }

adPort OBJECT-TYPE
    SYNTAX Integer32 (0..65535)
    MAX-ACCESS read-write
    STATUS current
    DESCRIPTION
        "Port for Active Directory authentication."
    ::= { adAllPorts 1 }

adResvPort OBJECT-TYPE
    SYNTAX Integer32 (0..65535)
    MAX-ACCESS read-write
    STATUS current
    DESCRIPTION
        "Alternate or reserved port for Active Directory Authentication."
    ::= { adAllPorts 2 }

envProbeNames OBJECT IDENTIFIER ::= { configuration 88 }

probe1Name OBJECT-TYPE
    SYNTAX DisplayString (SIZE (0..64))
    MAX-ACCESS read-write
    STATUS current
    DESCRIPTION
        "Name for Environmental Probe 1."
    ::= { envProbeNames 1 }

probe2Name OBJECT-TYPE
    SYNTAX DisplayString (SIZE (0..64))
    MAX-ACCESS read-write
    STATUS current
    DESCRIPTION
        "Name for Environmental Probe 2."
    ::= { envProbeNames 2 }

dLogOptions OBJECT IDENTIFIER ::= { configuration 89 }

dLogEnable OBJECT-TYPE
    SYNTAX Integer32 (0..1)
    MAX-ACCESS read-write
    STATUS current
    DESCRIPTION
        "Enable data logging feature, 0=disable and 1=enable."
    ::= { dLogOptions 1 }

netservdLog OBJECT-TYPE
    SYNTAX Integer32 (0..1)
    MAX-ACCESS read-write
    STATUS current
    DESCRIPTION
        "Enable data logging to log server over network, 0=disable and 1=enable."
    ::= { dLogOptions 11 }

autonetLog OBJECT-TYPE
    SYNTAX Integer32 (0..1)
    MAX-ACCESS read-write
    STATUS current
    DESCRIPTION
        "Enable automatic transfer to log server every 6 hours, 0=disable and 1=enable."
    ::= { dLogOptions 12 }

stdmeterdLog OBJECT-TYPE
    SYNTAX Integer32 (0..1)
    MAX-ACCESS read-write
    STATUS current
    DESCRIPTION
        "Enable logging of branch, receptacle and environmental metrics, 0=disable and 1=enable."
    ::= { dLogOptions 2 }

groupmeterdLog OBJECT-TYPE
    SYNTAX Integer32 (0..1)
    MAX-ACCESS read-write
    STATUS current
    DESCRIPTION
        "Enable logging of grouped receptacle metrics, 0=disable and 1=enable."
    ::= { dLogOptions 3 }

alarmdLog OBJECT-TYPE
    SYNTAX Integer32 (0..1)
    MAX-ACCESS read-write
    STATUS current
    DESCRIPTION
        "Enable logging of alarm events, 0=disable and 1=enable."
    ::= { dLogOptions 4 }

userlogindLog OBJECT-TYPE
    SYNTAX Integer32 (0..1)
    MAX-ACCESS read-write
    STATUS current
    DESCRIPTION
        "Enable logging of user login events, 0=disable and 1=enable."
    ::= { dLogOptions 5 }

usersetupdLog OBJECT-TYPE
    SYNTAX Integer32 (0..1)
    MAX-ACCESS read-write
    STATUS current
    DESCRIPTION
        "Enable logging of user setup change events, 0=disable and 1=enable."
    ::= { dLogOptions 6 }

fwupdatedLog OBJECT-TYPE
    SYNTAX Integer32 (0..1)
    MAX-ACCESS read-write
    STATUS current
    DESCRIPTION
        "Enable data logging feature, 0=disable and 1=enable."
    ::= { dLogOptions 7 }

setupchangedLog OBJECT-TYPE
    SYNTAX Integer32 (0..1)
    MAX-ACCESS read-write
    STATUS current
    DESCRIPTION
        "Enable logging of setup change events, 0=disable and 1=enable."
    ::= { dLogOptions 8 }

recepchangedLog OBJECT-TYPE
    SYNTAX Integer32 (0..1)
    MAX-ACCESS read-write
    STATUS current
    DESCRIPTION
        "Enable logging of receptacle state changes, 0=disable and 1=enable."
    ::= { dLogOptions 9 }

pduopchangedLog OBJECT-TYPE
    SYNTAX Integer32 (0..1)
    MAX-ACCESS read-write
    STATUS current
    DESCRIPTION
        "Enable logging of PDU operation and state changes, 0=disable and 1=enable."
    ::= { dLogOptions 10 }

dLogCycle OBJECT-TYPE
    SYNTAX Integer32 (0..65535)
    MAX-ACCESS read-write
    STATUS current
    DESCRIPTION
        "The time interval in minutes for internal data logging to occur."
    ::= { configuration 90 }

dLogFullWarnLevel OBJECT-TYPE
    SYNTAX Integer32 (50..100)
    MAX-ACCESS read-write
    STATUS current
    DESCRIPTION
        "The warning threshold for percentage of storage full (min=50, max=100)."
    ::= { configuration 91 }

netdLogServer OBJECT-TYPE
    SYNTAX DisplayString (SIZE (0..64))
    MAX-ACCESS read-write
    STATUS current
    DESCRIPTION
        "The network address for the data log server."
    ::= { configuration 92 }

netdLogPort OBJECT-TYPE
    SYNTAX Integer32 (0..65535)
    MAX-ACCESS read-write
    STATUS current
    DESCRIPTION
        "The port used by the data log server."
    ::= { configuration 93 }

netdLogUser OBJECT-TYPE
    SYNTAX DisplayString (SIZE (0..64))
    MAX-ACCESS read-write
    STATUS current
    DESCRIPTION
        "The user name to access the data log server."
    ::= { configuration 94 }

netdLogPasswd OBJECT-TYPE
    SYNTAX DisplayString (SIZE (0..64))
    MAX-ACCESS read-write
    STATUS current
    DESCRIPTION
        "The user password to access the data log server."
    ::= { configuration 95 }

netdLogDestdir OBJECT-TYPE
    SYNTAX DisplayString (SIZE (0..64))
    MAX-ACCESS read-write
    STATUS current
    DESCRIPTION
        "The destination directory in the data log server."
    ::= { configuration 96 }

netdLogOptions OBJECT-TYPE
    SYNTAX DisplayString (SIZE (0..64))
    MAX-ACCESS read-write
    STATUS current
    DESCRIPTION
        "The options string when accessing the data log server."
    ::= { configuration 97 }

metrics OBJECT IDENTIFIER ::= { cpiPDU 3 }

mcurrent OBJECT IDENTIFIER ::= { metrics 1 }

currentbrancha OBJECT-TYPE
    SYNTAX Integer32 (0..2000)
    MAX-ACCESS read-only
    STATUS current
    DESCRIPTION
        "BranchA current draw in 1/100 Amps."
    ::= { mcurrent 1 }

currentbranchb OBJECT-TYPE
    SYNTAX Integer32 (0..2000)
    MAX-ACCESS read-only
    STATUS current
    DESCRIPTION
        "BranchB current draw in 1/100 Amps."
    ::= { mcurrent 2 }

mvoltage OBJECT IDENTIFIER ::= { metrics 2 }

voltagebrancha OBJECT-TYPE
    SYNTAX Integer32 (0..1800)
    MAX-ACCESS read-only
    STATUS current
    DESCRIPTION
        "BranchA voltage in 1/10 volts."
    ::= { mvoltage 1 }

voltagebranchb OBJECT-TYPE
    SYNTAX Integer32 (0..1800)
    MAX-ACCESS read-only
    STATUS current
    DESCRIPTION
        "BranchB voltage in 1/10 volts."
    ::= { mvoltage 2 }

mpower OBJECT IDENTIFIER ::= { metrics 3 }

powerbrancha OBJECT-TYPE
    SYNTAX Integer32 (0..3600)
    MAX-ACCESS read-only
    STATUS current
    DESCRIPTION
        "BranchA power consumption in Watts."
    ::= { mpower 1 }

powerbranchb OBJECT-TYPE
    SYNTAX Integer32 (0..3600)
    MAX-ACCESS read-only
    STATUS current
    DESCRIPTION
        "BranchB power consumption in Watts."
    ::= { mpower 2 }

mpowerFactor OBJECT IDENTIFIER ::= { metrics 4 }

powerFactbrancha OBJECT-TYPE
    SYNTAX Integer32 (0..10000)
    MAX-ACCESS read-only
    STATUS current
    DESCRIPTION
        "BranchA power factor x 100."
    ::= { mpowerFactor 1 }

powerFactbranchb OBJECT-TYPE
    SYNTAX Integer32 (0..10000)
    MAX-ACCESS read-only
    STATUS current
    DESCRIPTION
        "BranchB power factor x 100."
    ::= { mpowerFactor 2 }

receptacleCurrent OBJECT IDENTIFIER ::= { metrics 5 }

port1Current OBJECT-TYPE
    SYNTAX Integer32 (0..2000)
    MAX-ACCESS read-only
    STATUS current
    DESCRIPTION
        "Port1 current draw in 1/100 Amps."
    ::= { receptacleCurrent 1 }

port2Current OBJECT-TYPE
    SYNTAX Integer32 (0..2000)
    MAX-ACCESS read-only
    STATUS current
    DESCRIPTION
        "Port2 current draw in 1/100 Amps."
    ::= { receptacleCurrent 2 }

port3Current OBJECT-TYPE
    SYNTAX Integer32 (0..2000)
    MAX-ACCESS read-only
    STATUS current
    DESCRIPTION
        "Port3 current draw in 1/100 Amps."
    ::= { receptacleCurrent 3 }

port4Current OBJECT-TYPE
    SYNTAX Integer32 (0..2000)
    MAX-ACCESS read-only
    STATUS current
    DESCRIPTION
        "Port4 current draw in 1/100 Amps."
    ::= { receptacleCurrent 4 }

port5Current OBJECT-TYPE
    SYNTAX Integer32 (0..2000)
    MAX-ACCESS read-only
    STATUS current
    DESCRIPTION
        "Port5 current draw in 1/100 Amps."
    ::= { receptacleCurrent 5 }

port6Current OBJECT-TYPE
    SYNTAX Integer32 (0..2000)
    MAX-ACCESS read-only
    STATUS current
    DESCRIPTION
        "Port6 current draw in 1/100 Amps."
    ::= { receptacleCurrent 6 }

port7Current OBJECT-TYPE
    SYNTAX Integer32 (0..2000)
    MAX-ACCESS read-only
    STATUS current
    DESCRIPTION
        "Port7 current draw in 1/100 Amps."
    ::= { receptacleCurrent 7 }

port8Current OBJECT-TYPE
    SYNTAX Integer32 (0..2000)
    MAX-ACCESS read-only
    STATUS current
    DESCRIPTION
        "Port8 current draw in 1/100 Amps."
    ::= { receptacleCurrent 8 }

port9Current OBJECT-TYPE
    SYNTAX Integer32 (0..2000)
    MAX-ACCESS read-only
    STATUS current
    DESCRIPTION
        "Port9 current draw in 1/100 Amps."
    ::= { receptacleCurrent 9 }

port10Current OBJECT-TYPE
    SYNTAX Integer32 (0..2000)
    MAX-ACCESS read-only
    STATUS current
    DESCRIPTION
        "Port10 current draw in 1/100 Amps."
    ::= { receptacleCurrent 10 }

port11Current OBJECT-TYPE
    SYNTAX Integer32 (0..2000)
    MAX-ACCESS read-only
    STATUS current
    DESCRIPTION
        "Port11 current draw in 1/100 Amps."
    ::= { receptacleCurrent 11 }

port12Current OBJECT-TYPE
    SYNTAX Integer32 (0..2000)
    MAX-ACCESS read-only
    STATUS current
    DESCRIPTION
        "Port12 current draw in 1/100 Amps."
    ::= { receptacleCurrent 12 }

port13Current OBJECT-TYPE
    SYNTAX Integer32 (0..2000)
    MAX-ACCESS read-only
    STATUS current
    DESCRIPTION
        "Port13 current draw in 1/100 Amps."
    ::= { receptacleCurrent 13 }

port14Current OBJECT-TYPE
    SYNTAX Integer32 (0..2000)
    MAX-ACCESS read-only
    STATUS current
    DESCRIPTION
        "Port14 current draw in 1/100 Amps."
    ::= { receptacleCurrent 14 }

port15Current OBJECT-TYPE
    SYNTAX Integer32 (0..2000)
    MAX-ACCESS read-only
    STATUS current
    DESCRIPTION
        "Port15 current draw in 1/100 Amps."
    ::= { receptacleCurrent 15 }

port16Current OBJECT-TYPE
    SYNTAX Integer32 (0..2000)
    MAX-ACCESS read-only
    STATUS current
    DESCRIPTION
        "Port16 current draw in 1/100 Amps."
    ::= { receptacleCurrent 16 }

port17Current OBJECT-TYPE
    SYNTAX Integer32 (0..2000)
    MAX-ACCESS read-only
    STATUS current
    DESCRIPTION
        "Port17 current draw in 1/100 Amps."
    ::= { receptacleCurrent 17 }

port18Current OBJECT-TYPE
    SYNTAX Integer32 (0..2000)
    MAX-ACCESS read-only
    STATUS current
    DESCRIPTION
        "Port18 current draw in 1/100 Amps."
    ::= { receptacleCurrent 18 }

port19Current OBJECT-TYPE
    SYNTAX Integer32 (0..2000)
    MAX-ACCESS read-only
    STATUS current
    DESCRIPTION
        "Port19 current draw in 1/100 Amps."
    ::= { receptacleCurrent 19 }

port20Current OBJECT-TYPE
    SYNTAX Integer32 (0..2000)
    MAX-ACCESS read-only
    STATUS current
    DESCRIPTION
        "Port20 current draw in 1/100 Amps."
    ::= { receptacleCurrent 20 }

port21Current OBJECT-TYPE
    SYNTAX Integer32 (0..2000)
    MAX-ACCESS read-only
    STATUS current
    DESCRIPTION
        "Port21 current draw in 1/100 Amps."
    ::= { receptacleCurrent 21 }

port22Current OBJECT-TYPE
    SYNTAX Integer32 (0..2000)
    MAX-ACCESS read-only
    STATUS current
    DESCRIPTION
        "Port22 current draw in 1/100 Amps."
    ::= { receptacleCurrent 22 }

port23Current OBJECT-TYPE
    SYNTAX Integer32 (0..2000)
    MAX-ACCESS read-only
    STATUS current
    DESCRIPTION
        "Port23 current draw in 1/100 Amps."
    ::= { receptacleCurrent 23 }

port24Current OBJECT-TYPE
    SYNTAX Integer32 (0..2000)
    MAX-ACCESS read-only
    STATUS current
    DESCRIPTION
        "Port24 current draw in 1/100 Amps."
    ::= { receptacleCurrent 24 }

receptacleCurrentMap OBJECT-TYPE
    SYNTAX DisplayString (SIZE (0..120))
    MAX-ACCESS read-only
    STATUS current
    DESCRIPTION
        "Map of receptacle currents in ascending order and delimited by space."
    ::= { metrics 6 }

temperature OBJECT IDENTIFIER ::= { metrics 8 }

temperatureProbe1 OBJECT-TYPE
    SYNTAX Integer32 (0..20000)
    MAX-ACCESS read-only
    STATUS current
    DESCRIPTION
        "Probe 1 temperature in 1/100 degree Fahrenheit."
    ::= { temperature 1 }

temperatureProbe2 OBJECT-TYPE
    SYNTAX Integer32 (0..20000)
    MAX-ACCESS read-only
    STATUS current
    DESCRIPTION
        "Probe 2 temperature in 1/100 degree Fahrenheit."
    ::= { temperature 2 }

humidity OBJECT IDENTIFIER ::= { metrics 9 }

humidityProbe1 OBJECT-TYPE
    SYNTAX Integer32 (0..10000)
    MAX-ACCESS read-only
    STATUS current
    DESCRIPTION
        "Probe 1 humidity in 1/100 %."
    ::= { humidity 1 }

humidityProbe2 OBJECT-TYPE
    SYNTAX Integer32 (0..10000)
    MAX-ACCESS read-only
    STATUS current
    DESCRIPTION
        "Probe 2 humidity in 1/100 %."
    ::= { humidity 2 }

alarms OBJECT IDENTIFIER ::= { metrics 10 }

alarmsMaxMap OBJECT-TYPE
    SYNTAX Integer32
    MAX-ACCESS read-only
    STATUS current
    DESCRIPTION
        "Max threshold alarmed state bitmap: bit0=currA, bit1=currB, bit2=currC ...
        bit6=voltA, bit7=voltB, bit8=voltC ...
        bit12=temperature1, bit13=temperature2, bit14=humidity1, bit15=humidity2"
    ::= { alarms 1 }

alarmsMinMap OBJECT-TYPE
    SYNTAX Integer32
    MAX-ACCESS read-only
    STATUS current
    DESCRIPTION
        "Min threshold alarmed state bitmap: bit0=currA, bit1=currB, bit2=currC ...
        bit6=voltA, bit7=voltB, bit8=voltC ...
        bit12=temperature1, bit13=temperature2, bit14=humidity1, bit15=humidity2"
    ::= { alarms 2 }

alarmsWarnHiMap OBJECT-TYPE
    SYNTAX Integer32
    MAX-ACCESS read-only
    STATUS current
    DESCRIPTION
        "High threshold warning state bitmap: bit0=currA, bit1=currB, bit2=currC ...
        bit6=voltA, bit7=voltB, bit8=voltC ...
        bit12=temperature1, bit13=temperature2, bit14=humidity1, bit15=humidity2"
    ::= { alarms 3 }

alarmsWarnLoMap OBJECT-TYPE
    SYNTAX Integer32
    MAX-ACCESS read-only
    STATUS current
    DESCRIPTION
        "Low threshold warning state bitmap: bit0=currA, bit1=currB, bit2=currC ...
        bit6=voltA, bit7=voltB, bit8=voltC ...
        bit12=temperature1, bit13=temperature2, bit14=humidity1, bit15=humidity2"
    ::= { alarms 4 }

recep1To32AlarmsMaxMap OBJECT-TYPE
    SYNTAX Integer32
    MAX-ACCESS read-only
    STATUS current
    DESCRIPTION
        "Max threshold alarmed receptacle state bitmap: bit0=recep1, bit1=recep2, ... bit31=recep32"
    ::= { alarms 5 }

recep1To32AlarmsMinMap OBJECT-TYPE
    SYNTAX Integer32
    MAX-ACCESS read-only
    STATUS current
    DESCRIPTION
        "Min threshold alarmed receptacle state bitmap: bit0=recep1, bit1=recep2, ... bit31=recep32"
    ::= { alarms 7 }

recep1To32WarnHiMap OBJECT-TYPE
    SYNTAX Integer32
    MAX-ACCESS read-only
    STATUS current
    DESCRIPTION
        "High threshold warning receptacle state bitmap: bit0=recep1, bit1=recep2, ... bit31=recep32"
    ::= { alarms 9 }

recep1To32WarnLoMap OBJECT-TYPE
    SYNTAX Integer32
    MAX-ACCESS read-only
    STATUS current
    DESCRIPTION
        "Low threshold warning receptacle state bitmap: bit0=recep1, bit1=recep2, ... bit31=recep32"
    ::= { alarms 11 }

menergy OBJECT IDENTIFIER ::= { metrics 11 }

energybranchas OBJECT-TYPE
    SYNTAX Counter64
    MAX-ACCESS read-only
    STATUS current
    DESCRIPTION
        "BranchA branch energy accumulated in decaWatt-secs, divide by 360 to obtain Watt-hr."
    ::= { menergy 1 }

energybranchbs OBJECT-TYPE
    SYNTAX Counter64
    MAX-ACCESS read-only
    STATUS current
    DESCRIPTION
        "BranchB branch energy accumulated in decaWatt-secs, divide by 360 to obtain Watt-hr."
    ::= { menergy 2 }

receptacleEnergy OBJECT IDENTIFIER ::= { metrics 12 }

receptacleEnergyport1s OBJECT-TYPE
    SYNTAX Counter64
    MAX-ACCESS read-only
    STATUS current
    DESCRIPTION
        "Port1 receptacle energy accumulated in decaWatt-secs, divide by 360 to obtain Watt-hr."
    ::= { receptacleEnergy 1 }

receptacleEnergyport2s OBJECT-TYPE
    SYNTAX Counter64
    MAX-ACCESS read-only
    STATUS current
    DESCRIPTION
        "Port2 receptacle energy accumulated in decaWatt-secs, divide by 360 to obtain Watt-hr."
    ::= { receptacleEnergy 2 }

receptacleEnergyport3s OBJECT-TYPE
    SYNTAX Counter64
    MAX-ACCESS read-only
    STATUS current
    DESCRIPTION
        "Port3 receptacle energy accumulated in decaWatt-secs, divide by 360 to obtain Watt-hr."
    ::= { receptacleEnergy 3 }

receptacleEnergyport4s OBJECT-TYPE
    SYNTAX Counter64
    MAX-ACCESS read-only
    STATUS current
    DESCRIPTION
        "Port4 receptacle energy accumulated in decaWatt-secs, divide by 360 to obtain Watt-hr."
    ::= { receptacleEnergy 4 }

receptacleEnergyport5s OBJECT-TYPE
    SYNTAX Counter64
    MAX-ACCESS read-only
    STATUS current
    DESCRIPTION
        "Port5 receptacle energy accumulated in decaWatt-secs, divide by 360 to obtain Watt-hr."
    ::= { receptacleEnergy 5 }

receptacleEnergyport6s OBJECT-TYPE
    SYNTAX Counter64
    MAX-ACCESS read-only
    STATUS current
    DESCRIPTION
        "Port6 receptacle energy accumulated in decaWatt-secs, divide by 360 to obtain Watt-hr."
    ::= { receptacleEnergy 6 }

receptacleEnergyport7s OBJECT-TYPE
    SYNTAX Counter64
    MAX-ACCESS read-only
    STATUS current
    DESCRIPTION
        "Port7 receptacle energy accumulated in decaWatt-secs, divide by 360 to obtain Watt-hr."
    ::= { receptacleEnergy 7 }

receptacleEnergyport8s OBJECT-TYPE
    SYNTAX Counter64
    MAX-ACCESS read-only
    STATUS current
    DESCRIPTION
        "Port8 receptacle energy accumulated in decaWatt-secs, divide by 360 to obtain Watt-hr."
    ::= { receptacleEnergy 8 }

receptacleEnergyport9s OBJECT-TYPE
    SYNTAX Counter64
    MAX-ACCESS read-only
    STATUS current
    DESCRIPTION
        "Port9 receptacle energy accumulated in decaWatt-secs, divide by 360 to obtain Watt-hr."
    ::= { receptacleEnergy 9 }

receptacleEnergyport10s OBJECT-TYPE
    SYNTAX Counter64
    MAX-ACCESS read-only
    STATUS current
    DESCRIPTION
        "Port10 receptacle energy accumulated in decaWatt-secs, divide by 360 to obtain Watt-hr."
    ::= { receptacleEnergy 10 }

receptacleEnergyport11s OBJECT-TYPE
    SYNTAX Counter64
    MAX-ACCESS read-only
    STATUS current
    DESCRIPTION
        "Port11 receptacle energy accumulated in decaWatt-secs, divide by 360 to obtain Watt-hr."
    ::= { receptacleEnergy 11 }

receptacleEnergyport12s OBJECT-TYPE
    SYNTAX Counter64
    MAX-ACCESS read-only
    STATUS current
    DESCRIPTION
        "Port12 receptacle energy accumulated in decaWatt-secs, divide by 360 to obtain Watt-hr."
    ::= { receptacleEnergy 12 }

receptacleEnergyport13s OBJECT-TYPE
    SYNTAX Counter64
    MAX-ACCESS read-only
    STATUS current
    DESCRIPTION
        "Port13 receptacle energy accumulated in decaWatt-secs, divide by 360 to obtain Watt-hr."
    ::= { receptacleEnergy 13 }

receptacleEnergyport14s OBJECT-TYPE
    SYNTAX Counter64
    MAX-ACCESS read-only
    STATUS current
    DESCRIPTION
        "Port14 receptacle energy accumulated in decaWatt-secs, divide by 360 to obtain Watt-hr."
    ::= { receptacleEnergy 14 }

receptacleEnergyport15s OBJECT-TYPE
    SYNTAX Counter64
    MAX-ACCESS read-only
    STATUS current
    DESCRIPTION
        "Port15 receptacle energy accumulated in decaWatt-secs, divide by 360 to obtain Watt-hr."
    ::= { receptacleEnergy 15 }

receptacleEnergyport16s OBJECT-TYPE
    SYNTAX Counter64
    MAX-ACCESS read-only
    STATUS current
    DESCRIPTION
        "Port16 receptacle energy accumulated in decaWatt-secs, divide by 360 to obtain Watt-hr."
    ::= { receptacleEnergy 16 }

receptacleEnergyport17s OBJECT-TYPE
    SYNTAX Counter64
    MAX-ACCESS read-only
    STATUS current
    DESCRIPTION
        "Port17 receptacle energy accumulated in decaWatt-secs, divide by 360 to obtain Watt-hr."
    ::= { receptacleEnergy 17 }

receptacleEnergyport18s OBJECT-TYPE
    SYNTAX Counter64
    MAX-ACCESS read-only
    STATUS current
    DESCRIPTION
        "Port18 receptacle energy accumulated in decaWatt-secs, divide by 360 to obtain Watt-hr."
    ::= { receptacleEnergy 18 }

receptacleEnergyport19s OBJECT-TYPE
    SYNTAX Counter64
    MAX-ACCESS read-only
    STATUS current
    DESCRIPTION
        "Port19 receptacle energy accumulated in decaWatt-secs, divide by 360 to obtain Watt-hr."
    ::= { receptacleEnergy 19 }

receptacleEnergyport20s OBJECT-TYPE
    SYNTAX Counter64
    MAX-ACCESS read-only
    STATUS current
    DESCRIPTION
        "Port20 receptacle energy accumulated in decaWatt-secs, divide by 360 to obtain Watt-hr."
    ::= { receptacleEnergy 20 }

receptacleEnergyport21s OBJECT-TYPE
    SYNTAX Counter64
    MAX-ACCESS read-only
    STATUS current
    DESCRIPTION
        "Port21 receptacle energy accumulated in decaWatt-secs, divide by 360 to obtain Watt-hr."
    ::= { receptacleEnergy 21 }

receptacleEnergyport22s OBJECT-TYPE
    SYNTAX Counter64
    MAX-ACCESS read-only
    STATUS current
    DESCRIPTION
        "Port22 receptacle energy accumulated in decaWatt-secs, divide by 360 to obtain Watt-hr."
    ::= { receptacleEnergy 22 }

receptacleEnergyport23s OBJECT-TYPE
    SYNTAX Counter64
    MAX-ACCESS read-only
    STATUS current
    DESCRIPTION
        "Port23 receptacle energy accumulated in decaWatt-secs, divide by 360 to obtain Watt-hr."
    ::= { receptacleEnergy 23 }

receptacleEnergyport24s OBJECT-TYPE
    SYNTAX Counter64
    MAX-ACCESS read-only
    STATUS current
    DESCRIPTION
        "Port24 receptacle energy accumulated in decaWatt-secs, divide by 360 to obtain Watt-hr."
    ::= { receptacleEnergy 24 }

chained OBJECT IDENTIFIER ::= { cpiPDU 5 }

pduCount OBJECT-TYPE
    SYNTAX Integer32 (0..32)
    MAX-ACCESS read-only
    STATUS current
    DESCRIPTION
        "Count of number of PDUs in the chain."
    ::= { chained 1 }

pduMap OBJECT-TYPE
    SYNTAX DisplayString (SIZE (0..255))
    MAX-ACCESS read-only
    STATUS current
    DESCRIPTION
        "Table map of PDU IDs in the chain, each ID consists of 4 bytes."
    ::= { chained 2 }

pduSelect OBJECT-TYPE
    SYNTAX Integer32 (0..16777215)
    MAX-ACCESS read-write
    STATUS current
    DESCRIPTION
        "Selects the PDUs in the chain for access."
    ::= { chained 3 }

cpiTraps OBJECT IDENTIFIER ::= { cpiPDU 6 }

cpiSpecific OBJECT IDENTIFIER ::= { cpiTraps 0 }

maxCurrentbrancha NOTIFICATION-TYPE
    OBJECTS { pduSelect, currentbrancha }
    STATUS  current
    DESCRIPTION
        "Trap is sent when current in BranchA exceeds set limit."
    ::= { cpiSpecific 1 }

maxCurrentbranchb NOTIFICATION-TYPE
    OBJECTS { pduSelect, currentbranchb }
    STATUS  current
    DESCRIPTION
        "Trap is sent when current in BranchB exceeds set limit."
    ::= { cpiSpecific 2 }

minCurrentbrancha NOTIFICATION-TYPE
    OBJECTS { pduSelect, currentbrancha }
    STATUS  current
    DESCRIPTION
        "Trap is sent when current in BranchA drops below set limit."
    ::= { cpiSpecific 7 }

minCurrentbranchb NOTIFICATION-TYPE
    OBJECTS { pduSelect, currentbranchb }
    STATUS  current
    DESCRIPTION
        "Trap is sent when current in BranchB drops below set limit."
    ::= { cpiSpecific 8 }

maxVoltbrancha NOTIFICATION-TYPE
    OBJECTS { pduSelect, voltagebrancha }
    STATUS  current
    DESCRIPTION
        "Trap is sent when voltage in BranchA exceeds high limit."
    ::= { cpiSpecific 13 }

maxVoltbranchb NOTIFICATION-TYPE
    OBJECTS { pduSelect, voltagebranchb }
    STATUS  current
    DESCRIPTION
        "Trap is sent when voltage in BranchB exceeds high limit."
    ::= { cpiSpecific 14 }

minVoltbrancha NOTIFICATION-TYPE
    OBJECTS { pduSelect, voltagebrancha }
    STATUS  current
    DESCRIPTION
        "Trap is sent when voltage in BranchA drops below low limit."
    ::= { cpiSpecific 19 }

minVoltbranchb NOTIFICATION-TYPE
    OBJECTS { pduSelect, voltagebranchb }
    STATUS  current
    DESCRIPTION
        "Trap is sent when voltage in BranchB drops below low limit."
    ::= { cpiSpecific 20 }

maxTemperature1 NOTIFICATION-TYPE
    OBJECTS { pduSelect, temperatureProbe1 }
    STATUS  current
    DESCRIPTION
        "Trap is sent when temperature exceeds high limit."
    ::= { cpiSpecific 25 }

maxTemperature2 NOTIFICATION-TYPE
    OBJECTS { pduSelect, temperatureProbe2 }
    STATUS  current
    DESCRIPTION
        "Trap is sent when temperature exceeds high limit."
    ::= { cpiSpecific 26 }

minTemperature1 NOTIFICATION-TYPE
    OBJECTS { pduSelect, temperatureProbe1 }
    STATUS  current
    DESCRIPTION
        "Trap is sent when temperature drops below low limit."
    ::= { cpiSpecific 27 }

minTemperature2 NOTIFICATION-TYPE
    OBJECTS { pduSelect, temperatureProbe2 }
    STATUS  current
    DESCRIPTION
        "Trap is sent when temperature drops below low limit."
    ::= { cpiSpecific 28 }

maxHumidity1 NOTIFICATION-TYPE
    OBJECTS { pduSelect, humidityProbe1 }
    STATUS  current
    DESCRIPTION
        "Trap is sent when humidity exceeds high limit."
    ::= { cpiSpecific 29 }

maxHumidity2 NOTIFICATION-TYPE
    OBJECTS { pduSelect, humidityProbe2 }
    STATUS  current
    DESCRIPTION
        "Trap is sent when humidity exceeds high limit."
    ::= { cpiSpecific 30 }

minHumidity1 NOTIFICATION-TYPE
    OBJECTS { pduSelect, humidityProbe1 }
    STATUS  current
    DESCRIPTION
        "Trap is sent when humidity drops below low limit."
    ::= { cpiSpecific 31 }

minHumidity2 NOTIFICATION-TYPE
    OBJECTS { pduSelect, humidityProbe2 }
    STATUS  current
    DESCRIPTION
        "Trap is sent when humidity drops below low limit."
    ::= { cpiSpecific 32 }

changeLog NOTIFICATION-TYPE
    OBJECTS { pduSelect, 
        voltagebrancha,
        voltagebranchb,
        currentbrancha,
        currentbranchb,
        receptacleCurrentMap,
        temperatureProbe1,
        humidityProbe1,
        temperatureProbe2,
        humidityProbe2,
        alarmsMaxMap, 
        alarmsMinMap, 
        alarmsWarnHiMap, 
        alarmsWarnLoMap, 
        recep1To32AlarmsMaxMap, 
        recep1To32AlarmsMinMap, 
        recep1To32WarnHiMap, 
        recep1To32WarnLoMap 
    }
    STATUS  current
    DESCRIPTION
        "Trap is sent when changes in current exceed the amount set in LOGDIFFERENCE."
    ::= { cpiSpecific 33 }

dataLog NOTIFICATION-TYPE
    OBJECTS { pduSelect, 
        voltagebrancha,
        voltagebranchb,
        currentbrancha,
        currentbranchb,
        receptacleCurrentMap,
        temperatureProbe1,
        humidityProbe1,
        temperatureProbe2,
        humidityProbe2,
        alarmsMaxMap, 
        alarmsMinMap, 
        alarmsWarnHiMap, 
        alarmsWarnLoMap, 
        recep1To32AlarmsMaxMap, 
        recep1To32AlarmsMinMap, 
        recep1To32WarnHiMap, 
        recep1To32WarnLoMap 
    }
    STATUS  current
    DESCRIPTION
        "Trap is sent when the data logging interval time is reached"
    ::= { cpiSpecific 34 }

endAlarm NOTIFICATION-TYPE
    OBJECTS { pduSelect, 
        alarmsMaxMap, 
        alarmsMinMap, 
        alarmsWarnHiMap, 
        alarmsWarnLoMap, 
        recep1To32AlarmsMaxMap, 
        recep1To32AlarmsMinMap, 
        recep1To32WarnHiMap, 
        recep1To32WarnLoMap 
    }
    STATUS  current
    DESCRIPTION
        "Trap is sent when all alarms have been resolved/cleared"
    ::= { cpiSpecific 35 }

-- conformance information

cpiMIBConformance OBJECT IDENTIFIER ::= { cpiProducts 2 }

cpiMIBCompliances OBJECT IDENTIFIER ::= { cpiMIBConformance 1 }

cpiMIBGroups OBJECT IDENTIFIER ::= { cpiMIBConformance 2 }

cpiMIBComplianceRev1 MODULE-COMPLIANCE
    STATUS current
    DESCRIPTION
        "The compliance statement for this MIB."
    MODULE  -- this module
        MANDATORY-GROUPS {
            cpiMIBGroupsObjects,
            cpiMIBGroupNotifications
            }
    ::= { cpiMIBCompliances 1 }

-- units of conformance

cpiMIBGroupsObjects OBJECT-GROUP
    OBJECTS {
        version,
        modelCode,
        hwAddress,
        logInterval,
        alarmInterval,
        logDifference,
        pduIP,
        autoIP,
        autoDNS,
        ipV4Enable,
        snmpEnable,
        telnetEnable,
        sshEnable,
        httpEnable,
        httpsEnable,
        subnetMask,
        gateway,
        dns1,
        dns2,
        dns3,
        snmpHost1,
        snmpHost2,
        snmpHost3,
        pduIPv6,
        autoIPv6,
        autoDNSIPv6,
        ipv6Enable,
        linkLocalEnable,
        globalAddrEnable,
        subnetMaskIPv6,
        gatewayIPv6,
        dns1IPv6,
        dns2IPv6,
        dns3IPv6,
        snmpHost1IPv6,
        snmpHost2IPv6,
        snmpHost3IPv6,
        branchaMaxCurr,
        branchbMaxCurr,
        branchaMinCurr,
        branchbMinCurr,
        branchaWarnHiCurr,
        branchbWarnHiCurr,
        branchaWarnLoCurr,
        branchbWarnLoCurr,
        branchaMaxVolt,
        branchbMaxVolt,
        branchaMinVolt,
        branchbMinVolt,
        branchaWarnHiVolt,
        branchbWarnHiVolt,
        branchaWarnLoVolt,
        branchbWarnLoVolt,
        port1MaxCurr,
        port2MaxCurr,
        port3MaxCurr,
        port4MaxCurr,
        port5MaxCurr,
        port6MaxCurr,
        port7MaxCurr,
        port8MaxCurr,
        port9MaxCurr,
        port10MaxCurr,
        port11MaxCurr,
        port12MaxCurr,
        port13MaxCurr,
        port14MaxCurr,
        port15MaxCurr,
        port16MaxCurr,
        port17MaxCurr,
        port18MaxCurr,
        port19MaxCurr,
        port20MaxCurr,
        port21MaxCurr,
        port22MaxCurr,
        port23MaxCurr,
        port24MaxCurr,
        port1MinCurr,
        port2MinCurr,
        port3MinCurr,
        port4MinCurr,
        port5MinCurr,
        port6MinCurr,
        port7MinCurr,
        port8MinCurr,
        port9MinCurr,
        port10MinCurr,
        port11MinCurr,
        port12MinCurr,
        port13MinCurr,
        port14MinCurr,
        port15MinCurr,
        port16MinCurr,
        port17MinCurr,
        port18MinCurr,
        port19MinCurr,
        port20MinCurr,
        port21MinCurr,
        port22MinCurr,
        port23MinCurr,
        port24MinCurr,
        port1WarnHiCurr,
        port2WarnHiCurr,
        port3WarnHiCurr,
        port4WarnHiCurr,
        port5WarnHiCurr,
        port6WarnHiCurr,
        port7WarnHiCurr,
        port8WarnHiCurr,
        port9WarnHiCurr,
        port10WarnHiCurr,
        port11WarnHiCurr,
        port12WarnHiCurr,
        port13WarnHiCurr,
        port14WarnHiCurr,
        port15WarnHiCurr,
        port16WarnHiCurr,
        port17WarnHiCurr,
        port18WarnHiCurr,
        port19WarnHiCurr,
        port20WarnHiCurr,
        port21WarnHiCurr,
        port22WarnHiCurr,
        port23WarnHiCurr,
        port24WarnHiCurr,
        port1WarnLoCurr,
        port2WarnLoCurr,
        port3WarnLoCurr,
        port4WarnLoCurr,
        port5WarnLoCurr,
        port6WarnLoCurr,
        port7WarnLoCurr,
        port8WarnLoCurr,
        port9WarnLoCurr,
        port10WarnLoCurr,
        port11WarnLoCurr,
        port12WarnLoCurr,
        port13WarnLoCurr,
        port14WarnLoCurr,
        port15WarnLoCurr,
        port16WarnLoCurr,
        port17WarnLoCurr,
        port18WarnLoCurr,
        port19WarnLoCurr,
        port20WarnLoCurr,
        port21WarnLoCurr,
        port22WarnLoCurr,
        port23WarnLoCurr,
        port24WarnLoCurr,
        maxTempProbe1,
        maxTempProbe2,
        minTempProbe1,
        minTempProbe2,
        warnHiTempProbe1,
        warnHiTempProbe2,
        warnLoTempProbe1,
        warnLoTempProbe2,
        maxHumidProbe1,
        maxHumidProbe2,
        minHumidProbe1,
        minHumidProbe2,
        warnHiHumidProbe1,
        warnHiHumidProbe2,
        warnLoHumidProbe1,
        warnLoHumidProbe2,
        pduName,
        pduDescrip,
        port1Name,
        port2Name,
        port3Name,
        port4Name,
        port5Name,
        port6Name,
        port7Name,
        port8Name,
        port9Name,
        port10Name,
        port11Name,
        port12Name,
        port13Name,
        port14Name,
        port15Name,
        port16Name,
        port17Name,
        port18Name,
        port19Name,
        port20Name,
        port21Name,
        port22Name,
        port23Name,
        port24Name,
        port1Descrip,
        port2Descrip,
        port3Descrip,
        port4Descrip,
        port5Descrip,
        port6Descrip,
        port7Descrip,
        port8Descrip,
        port9Descrip,
        port10Descrip,
        port11Descrip,
        port12Descrip,
        port13Descrip,
        port14Descrip,
        port15Descrip,
        port16Descrip,
        port17Descrip,
        port18Descrip,
        port19Descrip,
        port20Descrip,
        port21Descrip,
        port22Descrip,
        port23Descrip,
        port24Descrip,
        group1Name,
        group2Name,
        group3Name,
        group4Name,
        group5Name,
        group6Name,
        group7Name,
        group8Name,
        group9Name,
        group10Name,
        group11Name,
        group12Name,
        group13Name,
        group14Name,
        group15Name,
        group16Name,
        group1Map,
        group2Map,
        group3Map,
        group4Map,
        group5Map,
        group6Map,
        group7Map,
        group8Map,
        group9Map,
        group10Map,
        group11Map,
        group12Map,
        group13Map,
        group14Map,
        group15Map,
        group16Map,
        dispTimeout,
        loginTimeout,
        dispBrightness,
        inputTop,
        pduRole,
        celsiusTemp,
        enableWeb,
        snmpHostOnly,
        disLocalAuth,
        enaRadiusAuth,
        enaADAuth,
        enaSMTP,
        httpPort,
        httpsPort,
        sshPort,
        telnetPort,
        snmpQueryPort,
        snmpTrapPort,
        smtpSendPort,
        smtpReceivePort,
        rfcTimeServer,
        ntpTimeServer,
        smtpServer,
        snmpReadComm,
        snmpWriteComm,
        snmpUSMuserName,
        snmpSecurityLevel,
        snmpAuthAlgo,
        snmpPrivAlgo,
        snmpAuthPasswd,
        snmpPrivPasswd,
        snmpContextName,
        snmpEngineID,
        snmpLocAuthKey,
        snmpLocPrivKey,
        smtpUserName,
        smtpUserPasswd,
        smtpEmailAddr,
        smtpEmailDestination1,
        smtpEmailDestination2,
        smtpEmailDestination3,
        smtpServOptions,
        radiusServer,
        radiusSHSecret,
        radiusNASServer,
        radiusPort,
        nasPort,
        adServer,
        adDomain,
        adPort,
        adResvPort,
        probe1Name,
        probe2Name,
        dLogEnable,
        netservdLog,
        autonetLog,
        stdmeterdLog,
        groupmeterdLog,
        alarmdLog,
        userlogindLog,
        usersetupdLog,
        fwupdatedLog,
        setupchangedLog,
        recepchangedLog,
        pduopchangedLog,
        dLogCycle,
        dLogFullWarnLevel,
        netdLogServer,
        netdLogPort,
        netdLogUser,
        netdLogPasswd,
        netdLogDestdir,
        netdLogOptions,
        currentbrancha,
        currentbranchb,
        voltagebrancha,
        voltagebranchb,
        powerbrancha,
        powerbranchb,
        powerFactbrancha,
        powerFactbranchb,
        port1Current,
        port2Current,
        port3Current,
        port4Current,
        port5Current,
        port6Current,
        port7Current,
        port8Current,
        port9Current,
        port10Current,
        port11Current,
        port12Current,
        port13Current,
        port14Current,
        port15Current,
        port16Current,
        port17Current,
        port18Current,
        port19Current,
        port20Current,
        port21Current,
        port22Current,
        port23Current,
        port24Current,
        receptacleCurrentMap,
        temperatureProbe1,
        temperatureProbe2,
        humidityProbe1,
        humidityProbe2,
        alarmsMaxMap,
        alarmsMinMap,
        alarmsWarnHiMap,
        alarmsWarnLoMap,
        recep1To32AlarmsMaxMap,
        recep1To32AlarmsMinMap,
        recep1To32WarnHiMap,
        recep1To32WarnLoMap,
        energybranchas,
        energybranchbs,
        receptacleEnergyport1s,
        receptacleEnergyport2s,
        receptacleEnergyport3s,
        receptacleEnergyport4s,
        receptacleEnergyport5s,
        receptacleEnergyport6s,
        receptacleEnergyport7s,
        receptacleEnergyport8s,
        receptacleEnergyport9s,
        receptacleEnergyport10s,
        receptacleEnergyport11s,
        receptacleEnergyport12s,
        receptacleEnergyport13s,
        receptacleEnergyport14s,
        receptacleEnergyport15s,
        receptacleEnergyport16s,
        receptacleEnergyport17s,
        receptacleEnergyport18s,
        receptacleEnergyport19s,
        receptacleEnergyport20s,
        receptacleEnergyport21s,
        receptacleEnergyport22s,
        receptacleEnergyport23s,
        receptacleEnergyport24s,
        pduCount,
        pduMap,
        pduSelect
    }
    STATUS  current
    DESCRIPTION
        "A collection of objects for managing the PDU."
    ::= { cpiMIBGroups 1 }

cpiMIBGroupNotifications NOTIFICATION-GROUP
    NOTIFICATIONS {
        maxCurrentbrancha,
        maxCurrentbranchb,
        minCurrentbrancha,
        minCurrentbranchb,
        maxVoltbrancha,
        maxVoltbranchb,
        minVoltbrancha,
        minVoltbranchb,
        maxTemperature1,
        maxTemperature2,
        minTemperature1,
        minTemperature2,
        maxHumidity1,
        maxHumidity2,
        minHumidity1,
        minHumidity2,
        changeLog,
        dataLog,
        endAlarm
    }
    STATUS  current
    DESCRIPTION
        "A collection of notifications supported by PDU."
    ::= { cpiMIBGroups 2 }

END
