--------------------------------------------------------------------------------
-- PDI MODBUS/SNMP MIB
--
-- Revision 1.00
-- July 11, 2003
--------------------------------------------------------------------------------

M4V155 DEFINITIONS ::= BEGIN

IMPORTS
    OBJECT-TYPE
        FROM RFC-1212
    enterprises
        FROM RFC1155-SMI;

--------------------------------------------------------------------------------
-- Cusromer OID hierarchy
--------------------------------------------------------------------------------

pdi		OBJECT IDENTIFIER ::= { enterprises 11273 }
m4		OBJECT IDENTIFIER ::= { pdi 1 }
config	OBJECT IDENTIFIER ::= { m4 2 }
variation	OBJECT IDENTIFIER ::= { config 1 }
vars		OBJECT IDENTIFIER ::= { variation 1 }
traps		OBJECT IDENTIFIER ::= { variation 9 }
traps1	OBJECT IDENTIFIER ::= { traps 1 }
traps2	OBJECT IDENTIFIER ::= { traps 2 }
traps3	OBJECT IDENTIFIER ::= { traps 3 }
system	OBJECT IDENTIFIER ::= { traps 4 }

--------------------------------------------------------------------------------
-- Traps
--------------------------------------------------------------------------------

ioFail  TRAP-TYPE
	  ENTERPRISE	system
	  VARIABLES		{ ioFailCount }
	  DESCRIPTION	"I/O failure count exceeds threshold"
	  ::= 0

trap176 TRAP-TYPE
	  ENTERPRISE	traps1
	  DESCRIPTION	"Building input #1 alarm"  
	  ::= 0

trap177 TRAP-TYPE
	  ENTERPRISE	traps1
	  DESCRIPTION	"Building input #2 alarm"  
	  ::= 1

trap178 TRAP-TYPE
	  ENTERPRISE	traps1
	  DESCRIPTION	"Building input #3 alarm"  
	  ::= 2

trap179 TRAP-TYPE
	  ENTERPRISE	traps1
	  DESCRIPTION	"Building input #4 alarm"  
	  ::= 3

trap180 TRAP-TYPE
	  ENTERPRISE	traps1
	  DESCRIPTION	"Building input #5 alarm"  
	  ::= 4

trap181 TRAP-TYPE
	  ENTERPRISE	traps1
	  DESCRIPTION	"Building input #6 alarm"  
	  ::= 5

trap182 TRAP-TYPE
	  ENTERPRISE	traps1
	  DESCRIPTION	"Building input #7 alarm"  
	  ::= 6

trap183 TRAP-TYPE
	  ENTERPRISE	traps1
	  DESCRIPTION	"Building input #8 alarm"  
	  ::= 7

--
-- trap184 - trap207 undefined
--

trap208 TRAP-TYPE
	  ENTERPRISE	traps1
	  DESCRIPTION	"System input #1 alarm"  
	  ::= 32

trap209 TRAP-TYPE
	  ENTERPRISE	traps1
	  DESCRIPTION	"System input #2 alarm"  
	  ::= 33

trap210 TRAP-TYPE
	  ENTERPRISE	traps1
	  DESCRIPTION	"System input #3 alarm"  
	  ::= 34

trap211 TRAP-TYPE
	  ENTERPRISE	traps1
	  DESCRIPTION	"System input #4 alarm"  
	  ::= 35

trap212 TRAP-TYPE
	  ENTERPRISE	traps1
	  DESCRIPTION	"System input #5 alarm"  
	  ::= 36

trap213 TRAP-TYPE
	  ENTERPRISE	traps1
	  DESCRIPTION	"Ground fault warning"  
	  ::= 37

trap214 TRAP-TYPE
	  ENTERPRISE	traps1
	  DESCRIPTION	"Ground integrity"  
	  ::= 38

trap215 TRAP-TYPE
	  ENTERPRISE	traps1
	  DESCRIPTION	"Transformer hi temp"  
	  ::= 39

trap216 TRAP-TYPE
	  ENTERPRISE	traps1
	  DESCRIPTION	"Phase rotation error"  
	  ::= 40

trap217 TRAP-TYPE
	  ENTERPRISE	traps1
	  DESCRIPTION	"Preventive maint due"  
	  ::= 41

trap218 TRAP-TYPE
	  ENTERPRISE	traps1
	  DESCRIPTION	"System shutdown"  
	  ::= 42

--
-- trap219 - trap223 undefined
--

trap224 TRAP-TYPE
	  ENTERPRISE	traps2
	  VARIABLES		{ reg00 }
	  DESCRIPTION	"Input voltage A-B high"  
	  ::= 0

trap225 TRAP-TYPE
	  ENTERPRISE	traps2
	  VARIABLES		{ reg01 }
	  DESCRIPTION	"Input voltage B-C high"  
	  ::= 1

trap226 TRAP-TYPE
	  ENTERPRISE	traps2
	  VARIABLES		{ reg02 }
	  DESCRIPTION	"Input voltage C-A high"  
	  ::= 2

trap227 TRAP-TYPE
	  ENTERPRISE	traps2
	  VARIABLES		{ reg03 }
	  DESCRIPTION	"Output 1 voltage A-N high"  
	  ::= 3

trap228 TRAP-TYPE
	  ENTERPRISE	traps2
	  VARIABLES		{ reg04 }
	  DESCRIPTION	"Output 1 voltage B-N high"  
	  ::= 4

trap229 TRAP-TYPE
	  ENTERPRISE	traps2
	  VARIABLES		{ reg05 }
	  DESCRIPTION	"Output 1 voltage C-N high"  
	  ::= 5

trap230 TRAP-TYPE
	  ENTERPRISE	traps2
	  VARIABLES		{ reg06 }
	  DESCRIPTION	"Output 2 voltage A-N high"  
	  ::= 6

trap231 TRAP-TYPE
	  ENTERPRISE	traps2
	  VARIABLES		{ reg07 }
	  DESCRIPTION	"Output 2 voltage B-N high"  
	  ::= 7

trap232 TRAP-TYPE
	  ENTERPRISE	traps2
	  VARIABLES		{ reg08 }
	  DESCRIPTION	"Output 2 voltage C-N high"  
	  ::= 8

trap233 TRAP-TYPE
	  ENTERPRISE	traps2
	  VARIABLES		{ reg09 }
	  DESCRIPTION	"Output 1 amps A high"  
	  ::= 9

trap234 TRAP-TYPE
	  ENTERPRISE	traps2
	  VARIABLES		{ reg10 }
	  DESCRIPTION	"Output 1 amps B high"  
	  ::= 10

trap235 TRAP-TYPE
	  ENTERPRISE	traps2
	  VARIABLES		{ reg11 }
	  DESCRIPTION	"Output 1 amps C high"  
	  ::= 11

trap236 TRAP-TYPE
	  ENTERPRISE	traps2
	  VARIABLES		{ reg12 }
	  DESCRIPTION	"Output 2 amps A high"  
	  ::= 12

trap237 TRAP-TYPE
	  ENTERPRISE	traps2
	  VARIABLES		{ reg13 }
	  DESCRIPTION	"Output 2 amps B high"  
	  ::= 13

--
-- trap238 - trap239 undefined
--

trap240 TRAP-TYPE
	  ENTERPRISE	traps2
	  VARIABLES		{ reg16 }
	  DESCRIPTION	"Output 1 voltage A-B high"  
	  ::= 16

trap241 TRAP-TYPE
	  ENTERPRISE	traps2
	  VARIABLES		{ reg17 }
	  DESCRIPTION	"Output 1 voltage B-C high"  
	  ::= 17

trap242 TRAP-TYPE
	  ENTERPRISE	traps2
	  VARIABLES		{ reg18 }
	  DESCRIPTION	"Output 1 voltage C-A high"  
	  ::= 18

trap243 TRAP-TYPE
	  ENTERPRISE	traps2
	  VARIABLES		{ reg19 }
	  DESCRIPTION	"Output 2 voltage A-B high"  
	  ::= 19

trap244 TRAP-TYPE
	  ENTERPRISE	traps2
	  VARIABLES		{ reg20 }
	  DESCRIPTION	"Output 2 voltage B-C high"  
	  ::= 20

trap245 TRAP-TYPE
	  ENTERPRISE	traps2
	  VARIABLES		{ reg21 }
	  DESCRIPTION	"Output 2 voltage C-A high"  
	  ::= 21

trap246 TRAP-TYPE
	  ENTERPRISE	traps2
	  VARIABLES		{ reg22 }
	  DESCRIPTION	"Input THD A-B high"  
	  ::= 22

trap247 TRAP-TYPE
	  ENTERPRISE	traps2
	  VARIABLES		{ reg23 }
	  DESCRIPTION	"Input THD B-C high"  
	  ::= 23

trap248 TRAP-TYPE
	  ENTERPRISE	traps2
	  VARIABLES		{ reg24 }
	  DESCRIPTION	"Input THD C-A high"  
	  ::= 24

trap249 TRAP-TYPE
	  ENTERPRISE	traps2
	  VARIABLES		{ reg25 }
	  DESCRIPTION	"Output 1 THD A-N high"  
	  ::= 25

trap250 TRAP-TYPE
	  ENTERPRISE	traps2
	  VARIABLES		{ reg26 }
	  DESCRIPTION	"Output 1 THD B-N high"  
	  ::= 26

trap251 TRAP-TYPE
	  ENTERPRISE	traps2
	  VARIABLES		{ reg27 }
	  DESCRIPTION	"Output 1 THD C-N high"  
	  ::= 27

trap252 TRAP-TYPE
	  ENTERPRISE	traps2
	  VARIABLES		{ reg28 }
	  DESCRIPTION	"Output 2 THD A-N high"  
	  ::= 28

trap253 TRAP-TYPE
	  ENTERPRISE	traps2
	  VARIABLES		{ reg29 }
	  DESCRIPTION	"Output 2 THD B-N high"  
	  ::= 29

--
-- trap254 - trap287 undefined
--

trap288 TRAP-TYPE
	  ENTERPRISE	traps3
	  VARIABLES		{ reg00 }
	  DESCRIPTION	"Input voltage A-B low"  
	  ::= 0

trap289 TRAP-TYPE
	  ENTERPRISE	traps3
	  VARIABLES		{ reg01 }
	  DESCRIPTION	"Input voltage B-C low"  
	  ::= 1

trap290 TRAP-TYPE
	  ENTERPRISE	traps3
	  VARIABLES		{ reg02 }
	  DESCRIPTION	"Input voltage C-A low"  
	  ::= 2

trap291 TRAP-TYPE
	  ENTERPRISE	traps3
	  VARIABLES		{ reg03 }
	  DESCRIPTION	"Output 1 voltage A-N low"  
	  ::= 3

trap292 TRAP-TYPE
	  ENTERPRISE	traps3
	  VARIABLES		{ reg04 }
	  DESCRIPTION	"Output 1 voltage B-N low"  
	  ::= 4

trap293 TRAP-TYPE
	  ENTERPRISE	traps3
	  VARIABLES		{ reg05 }
	  DESCRIPTION	"Output 1 voltage C-N low"  
	  ::= 5

trap294 TRAP-TYPE
	  ENTERPRISE	traps3
	  VARIABLES		{ reg06 }
	  DESCRIPTION	"Output 2 voltage A-N low"  
	  ::= 6

trap295 TRAP-TYPE
	  ENTERPRISE	traps3
	  VARIABLES		{ reg07 }
	  DESCRIPTION	"Output 2 voltage B-N low"  
	  ::= 7

trap296 TRAP-TYPE
	  ENTERPRISE	traps3
	  VARIABLES		{ reg08 }
	  DESCRIPTION	"Output 2 voltage C-N low"  
	  ::= 8

trap297 TRAP-TYPE
	  ENTERPRISE	traps3
	  VARIABLES		{ reg09 }
	  DESCRIPTION	"Output 1 amps A low"  
	  ::= 9

trap298 TRAP-TYPE
	  ENTERPRISE	traps3
	  VARIABLES		{ reg10 }
	  DESCRIPTION	"Output 1 amps B low"  
	  ::= 10

trap299 TRAP-TYPE
	  ENTERPRISE	traps3
	  VARIABLES		{ reg11 }
	  DESCRIPTION	"Output 1 amps C low"  
	  ::= 11

trap300 TRAP-TYPE
	  ENTERPRISE	traps3
	  VARIABLES		{ reg12 }
	  DESCRIPTION	"Output 2 amps A low"  
	  ::= 12

trap301 TRAP-TYPE
	  ENTERPRISE	traps3
	  VARIABLES		{ reg13 }
	  DESCRIPTION	"Output 2 amps B low"  
	  ::= 13

trap302 TRAP-TYPE
	  ENTERPRISE	traps3
	  VARIABLES		{ reg14 }
	  DESCRIPTION	"Output 2 amps C low"  
	  ::= 14

trap303 TRAP-TYPE
	  ENTERPRISE	traps3
	  VARIABLES		{ reg15 }
	  DESCRIPTION	"Ground amps low"  
	  ::= 15

trap304 TRAP-TYPE
	  ENTERPRISE	traps3
	  VARIABLES		{ reg16 }
	  DESCRIPTION	"Output 1 voltage A-B low"  
	  ::= 16

trap305 TRAP-TYPE
	  ENTERPRISE	traps3
	  VARIABLES		{ reg17 }
	  DESCRIPTION	"Output 1 voltage B-C low"  
	  ::= 17

trap306 TRAP-TYPE
	  ENTERPRISE	traps3
	  VARIABLES		{ reg18 }
	  DESCRIPTION	"Output 1 voltage C-A low"  
	  ::= 18

trap307 TRAP-TYPE
	  ENTERPRISE	traps3
	  VARIABLES		{ reg19 }
	  DESCRIPTION	"Output 2 voltage A-B low"  
	  ::= 19

trap308 TRAP-TYPE
	  ENTERPRISE	traps3
	  VARIABLES		{ reg20 }
	  DESCRIPTION	"Output 2 voltage B-C low"  
	  ::= 20

trap309 TRAP-TYPE
	  ENTERPRISE	traps3
	  VARIABLES		{ reg21 }
	  DESCRIPTION	"Output 2 voltage C-A low"  
	  ::= 21

trap310 TRAP-TYPE
	  ENTERPRISE	traps3
	  VARIABLES		{ reg22 }
	  DESCRIPTION	"Input THD A-B low"  
	  ::= 22

trap311 TRAP-TYPE
	  ENTERPRISE	traps3
	  VARIABLES		{ reg23 }
	  DESCRIPTION	"Input THD B-C low"  
	  ::= 23

trap312 TRAP-TYPE
	  ENTERPRISE	traps3
	  VARIABLES		{ reg24 }
	  DESCRIPTION	"Input THD C-A low"  
	  ::= 24

trap313 TRAP-TYPE
	  ENTERPRISE	traps3
	  VARIABLES		{ reg25 }
	  DESCRIPTION	"Output 1 THD A-N low"  
	  ::= 25

trap314 TRAP-TYPE
	  ENTERPRISE	traps3
	  VARIABLES		{ reg26 }
	  DESCRIPTION	"Output 1 THD B-N low"  
	  ::= 26

trap315 TRAP-TYPE
	  ENTERPRISE	traps3
	  VARIABLES		{ reg27 }
	  DESCRIPTION	"Output 1 THD C-N low"  
	  ::= 27

trap316 TRAP-TYPE
	  ENTERPRISE	traps3
	  VARIABLES		{ reg28 }
	  DESCRIPTION	"Output 2 THD A-N low"  
	  ::= 28

trap317 TRAP-TYPE
	  ENTERPRISE	traps3
	  VARIABLES		{ reg29 }
	  DESCRIPTION	"Output 2 THD B-N low"  
	  ::= 29


--
-- trap318 - trap351 undefined
--


--------------------------------------------------------------------------------
-- M4 system values and commands
--------------------------------------------------------------------------------

ioFailCount OBJECT-TYPE
	SYNTAX  INTEGER
	ACCESS  read-only
	STATUS  mandatory
	DESCRIPTION "Consectutive I/O failure count"
		::= { vars 100 }

ioFailThreshold OBJECT-TYPE
	SYNTAX  INTEGER
	ACCESS  read-write
	STATUS  mandatory
	DESCRIPTION "Number of consecutive I/O failures before trap"
		::= { vars 101 }

cmdSilence OBJECT-TYPE
	SYNTAX  INTEGER { execute(1) }
	ACCESS  read-write
	STATUS  mandatory
	DESCRIPTION "Silence command"
		::= { vars 102 }

cmdClear OBJECT-TYPE
	SYNTAX  INTEGER { execute(1) }
	ACCESS  read-write
	STATUS  mandatory
	DESCRIPTION "Clear command"
		::= { vars 103 }

--------------------------------------------------------------------------------
-- M4 v1.55 register values
--------------------------------------------------------------------------------

reg00 OBJECT-TYPE
	SYNTAX  INTEGER
	ACCESS  read-only
	STATUS  mandatory
	DESCRIPTION "Input voltage A-B"
		::= { vars 1 }

reg01 OBJECT-TYPE
	SYNTAX  INTEGER
	ACCESS  read-only
	STATUS  mandatory
	DESCRIPTION "Input voltage B-C"
		::= { vars 2 }

reg02 OBJECT-TYPE
	SYNTAX  INTEGER
	ACCESS  read-only
	STATUS  mandatory
	DESCRIPTION "Input voltage C-A"
		::= { vars 3 }

reg03 OBJECT-TYPE
	SYNTAX  INTEGER
	ACCESS  read-only
	STATUS  mandatory
	DESCRIPTION "Output voltage A-B"
		::= { vars 4 }

reg04 OBJECT-TYPE
	SYNTAX  INTEGER
	ACCESS  read-only
	STATUS  mandatory
	DESCRIPTION "Output voltage B-C"
		::= { vars 5 }

reg05 OBJECT-TYPE
	SYNTAX  INTEGER
	ACCESS  read-only
	STATUS  mandatory
	DESCRIPTION "Output voltage C-A"
		::= { vars 6 }

reg06 OBJECT-TYPE
	SYNTAX  INTEGER
	ACCESS  read-only
	STATUS  mandatory
	DESCRIPTION "Output voltage A-N"
		::= { vars 7 }

reg07 OBJECT-TYPE
	SYNTAX  INTEGER
	ACCESS  read-only
	STATUS  mandatory
	DESCRIPTION "Output voltage B-N"
		::= { vars 8 }

reg08 OBJECT-TYPE
	SYNTAX  INTEGER
	ACCESS  read-only
	STATUS  mandatory
	DESCRIPTION "Output voltage C-N"
		::= { vars 9 }

reg09 OBJECT-TYPE
	SYNTAX  INTEGER
	ACCESS  read-only
	STATUS  mandatory
	DESCRIPTION "Output amps A"
		::= { vars 10 }

reg10 OBJECT-TYPE
	SYNTAX  INTEGER
	ACCESS  read-only
	STATUS  mandatory
	DESCRIPTION "Output amps B"
		::= { vars 11 }

reg11 OBJECT-TYPE
	SYNTAX  INTEGER
	ACCESS  read-only
	STATUS  mandatory
	DESCRIPTION "Output amps C"
		::= { vars 12 }

reg12 OBJECT-TYPE
	SYNTAX  INTEGER
	ACCESS  read-only
	STATUS  mandatory
	DESCRIPTION "Neutral amps"
		::= { vars 13 }

reg13 OBJECT-TYPE
	SYNTAX  INTEGER
	ACCESS  read-only
	STATUS  mandatory
	DESCRIPTION "Ground amps"
		::= { vars 14 }
		
reg14 OBJECT-TYPE
	SYNTAX  INTEGER
	ACCESS  read-only
	STATUS  mandatory
	DESCRIPTION "Ground amps fake"
		::= { vars 15 }
		
reg15 OBJECT-TYPE
	SYNTAX  INTEGER
	ACCESS  read-only
	STATUS  mandatory
	DESCRIPTION "Ground amps fake2"
		::= { vars 16 }

reg16 OBJECT-TYPE
	SYNTAX  INTEGER
	ACCESS  read-only
	STATUS  mandatory
	DESCRIPTION "Kilowatts A"
		::= { vars 17 }

reg17 OBJECT-TYPE
	SYNTAX  INTEGER
	ACCESS  read-only
	STATUS  mandatory
	DESCRIPTION "Power factor A"
		::= { vars 18 }

reg18 OBJECT-TYPE
	SYNTAX  INTEGER
	ACCESS  read-only
	STATUS  mandatory
	DESCRIPTION "Kilowatts B"
		::= { vars 19 }

reg19 OBJECT-TYPE
	SYNTAX  INTEGER
	ACCESS  read-only
	STATUS  mandatory
	DESCRIPTION "Power factor B"
		::= { vars 20 }

reg20 OBJECT-TYPE
	SYNTAX  INTEGER
	ACCESS  read-only
	STATUS  mandatory
	DESCRIPTION "Kilowatts C"
		::= { vars 21 }

reg21 OBJECT-TYPE
	SYNTAX  INTEGER
	ACCESS  read-only
	STATUS  mandatory
	DESCRIPTION "Power factor C"
		::= { vars 22 }

reg22 OBJECT-TYPE
	SYNTAX  INTEGER
	ACCESS  read-only
	STATUS  mandatory
	DESCRIPTION "Kilo volt amp A"
		::= { vars 23 }

reg23 OBJECT-TYPE
	SYNTAX  INTEGER
	ACCESS  read-only
	STATUS  mandatory
	DESCRIPTION "Harmonic dist A"
		::= { vars 24 }

reg24 OBJECT-TYPE
	SYNTAX  INTEGER
	ACCESS  read-only
	STATUS  mandatory
	DESCRIPTION "Kilo volt amp B"
		::= { vars 25 }

reg25 OBJECT-TYPE
	SYNTAX  INTEGER
	ACCESS  read-only
	STATUS  mandatory
	DESCRIPTION "Harmonic dist B"
		::= { vars 26 }

reg26 OBJECT-TYPE
	SYNTAX  INTEGER
	ACCESS  read-only
	STATUS  mandatory
	DESCRIPTION "Kilo volt amp C"
		::= { vars 27 }

reg27 OBJECT-TYPE
	SYNTAX  INTEGER
	ACCESS  read-only
	STATUS  mandatory
	DESCRIPTION "Harmonic dist C"
		::= { vars 28 }

reg28 OBJECT-TYPE
	SYNTAX  INTEGER
	ACCESS  read-only
	STATUS  mandatory
	DESCRIPTION "Total KVA"
		::= { vars 29 }

reg29 OBJECT-TYPE
	SYNTAX  INTEGER
	ACCESS  read-only
	STATUS  mandatory
	DESCRIPTION "Frequency"
		::= { vars 30 }

reg32 OBJECT-TYPE
	SYNTAX  INTEGER
	ACCESS  read-only
	STATUS  mandatory
	DESCRIPTION "Percent KVA A"
		::= { vars 33 }

reg33 OBJECT-TYPE
	SYNTAX  INTEGER
	ACCESS  read-only
	STATUS  mandatory
	DESCRIPTION "Percent KVA B"
		::= { vars 34 }

reg34 OBJECT-TYPE
	SYNTAX  INTEGER
	ACCESS  read-only
	STATUS  mandatory
	DESCRIPTION "Percent KVA C"
		::= { vars 35 }

reg35 OBJECT-TYPE
	SYNTAX  INTEGER
	ACCESS  read-only
	STATUS  mandatory
	DESCRIPTION "KWH"
		::= { vars 36 }

END
