--
-- CAREL-std-air-cond.MIB
-- MIB generated by CAREL
-- Wednesday, 19 May 2010
--

    CAREL-std-air-cond-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        std-air-condMIB MODULE-IDENTITY
      		LAST-UPDATED  "201005190920Z"		-- May 19, 2010 at 09:20 GMT
      		ORGANIZATION  "CAREL Industries S.r.l"
      		CONTACT-INFO
                "
                        Carel Industries S.r.l
                        Via dell'Industria, 11
                        35020 Brugine (PD) Italy
                        Tel: +39 049 9716611
                        E-mail: carel@carel.com
                "
      		DESCRIPTION
                "This is the MIB module for the std-air-cond device."
			REVISION "201005190920Z"
			DESCRIPTION
                "version 1.0"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { std-air-condMIB 1 }

        -- 1.3.6.1.4.1.9839.2.1.1.17
        ST-D1 OBJECT-TYPE
                    SYNTAX Integer32 (0..1)
                    UNITS "N/A"
                    MAX-ACCESS read-only
                    STATUS current
                    DESCRIPTION "Alarm Kaltwassersatz 1"
                    ::= { digitalObjects 1 }

        -- 1.3.6.1.4.1.9839.2.1.1.18
        ST-D2 OBJECT-TYPE
                    SYNTAX Integer32 (0..1)
                    UNITS "N/A"
                    MAX-ACCESS read-only
                    STATUS current
                    DESCRIPTION "Alarm Kaltwassersatz 2"
                    ::= { digitalObjects 2 }

        -- 1.3.6.1.4.1.9839.2.1.1.19
        ST-D3 OBJECT-TYPE
                    SYNTAX Integer32 (0..1)
                    UNITS "N/A"
                    MAX-ACCESS read-only
                    STATUS current
                    DESCRIPTION "Alarm Kaltwassersatz 3"
                    ::= { digitalObjects 3 }

        -- 1.3.6.1.4.1.9839.2.1.1.20
        ST-D4 OBJECT-TYPE
                    SYNTAX Integer32 (0..1)
                    UNITS "N/A"
                    MAX-ACCESS read-only
                    STATUS current
                    DESCRIPTION "Alarm Kaltwassersatz 4"
                    ::= { digitalObjects 4 }

        -- 1.3.6.1.4.1.9839.2.1.1.23
        ST-D5 OBJECT-TYPE
                    SYNTAX Integer32 (0..1)
                    UNITS "N/A"
                    MAX-ACCESS read-only
                    STATUS current
                    DESCRIPTION "Alarm Glykolpumpe 1"
                    ::= { digitalObjects 5 }

        -- 1.3.6.1.4.1.9839.2.1.1.24
        ST-D6 OBJECT-TYPE
                    SYNTAX Integer32 (0..1)
                    UNITS "N/A"
                    MAX-ACCESS read-only
                    STATUS current
                    DESCRIPTION "Alarm Glykolpumpe 2"
                    ::= { digitalObjects 6 }

        -- 1.3.6.1.4.1.9839.2.1.1.25
        ST-D7 OBJECT-TYPE
                    SYNTAX Integer32 (0..1)
                    UNITS "N/A"
                    MAX-ACCESS read-only
                    STATUS current
                    DESCRIPTION "Alarm Stroemungswaechter"
                    ::= { digitalObjects 7 }

        -- 1.3.6.1.4.1.9839.2.1.1.26
        ST-D8 OBJECT-TYPE
                    SYNTAX Integer32 (0..1)
                    UNITS "N/A"
                    MAX-ACCESS read-only
                    STATUS current
                    DESCRIPTION "Alarm Sekundaerpumpe 1"
                    ::= { digitalObjects 8 }

        -- 1.3.6.1.4.1.9839.2.1.1.27
        ST-D9 OBJECT-TYPE
                    SYNTAX Integer32 (0..1)
                    UNITS "N/A"
                    MAX-ACCESS read-only
                    STATUS current
                    DESCRIPTION "Alarm Sekundaerpumpe 2"
                    ::= { digitalObjects 9 }

        -- 1.3.6.1.4.1.9839.2.1.1.28
        ST-D10 OBJECT-TYPE
                    SYNTAX Integer32 (0..1)
                    UNITS "N/A"
                    MAX-ACCESS read-only
                    STATUS current
                    DESCRIPTION "Stroemungswaechter Sekundaerpumpen"
                    ::= { digitalObjects 10 }

        -- 1.3.6.1.4.1.9839.2.1.1.29
        ST-D11 OBJECT-TYPE
                    SYNTAX Integer32 (0..1)
                    UNITS "N/A"
                    MAX-ACCESS read-only
                    STATUS current
                    DESCRIPTION "Alarm Rueckkuehler 1"
                    ::= { digitalObjects 11 }
       
	 -- 1.3.6.1.4.1.9839.2.1.1.30
        ST-D12 OBJECT-TYPE
                    SYNTAX Integer32 (0..1)
                    UNITS "N/A"
                    MAX-ACCESS read-only
                    STATUS current
                    DESCRIPTION "Alarm Rueckkuehler 2"
                    ::= { digitalObjects 12 }
       
	 -- 1.3.6.1.4.1.9839.2.1.1.31
        ST-D13 OBJECT-TYPE
                    SYNTAX Integer32 (0..1)
                    UNITS "N/A"
                    MAX-ACCESS read-only
                    STATUS current
                    DESCRIPTION "Alarm Rueckkuehler 3"
                    ::= { digitalObjects 13 }

       
	 -- 1.3.6.1.4.1.9839.2.1.1.32
        ST-D14 OBJECT-TYPE
                    SYNTAX Integer32 (0..1)
                    UNITS "N/A"
                    MAX-ACCESS read-only
                    STATUS current
                    DESCRIPTION "Alarm Rueckkuehler 4"
                    ::= { digitalObjects 14 }


        -- 1.3.6.1.4.1.9839.2.1.2
        analogObjects OBJECT IDENTIFIER ::= { std-air-condMIB 2 }

        -- 1.3.6.1.4.1.9839.2.1.2.2
        KWS-P-Vor OBJECT-TYPE
                    SYNTAX Integer32 (-32767..32767)
                    UNITS "C/F x10"
                    MAX-ACCESS read-only
                    STATUS current
                    DESCRIPTION "Kaltwasser Primaer Vorlauf Temperatur"
                    ::= { analogObjects 1 }

        -- 1.3.6.1.4.1.9839.2.1.2.3
        KWS-P-Rue OBJECT-TYPE
                    SYNTAX Integer32 (-32767..32767)
                    UNITS "C/F x10"
                    MAX-ACCESS read-only
                    STATUS current
                    DESCRIPTION "Kaltwasser Primaer Ruecklauf Temperatur"
                    ::= { analogObjects 2 }

        -- 1.3.6.1.4.1.9839.2.1.2.4
        DR-P-KW OBJECT-TYPE
                    SYNTAX Integer32 (-32767..32767)
                    UNITS "bar x10"
                    MAX-ACCESS read-only
                    STATUS current
                    DESCRIPTION "Drucktransmitter Kaltwasser Primaer"
                    ::= { analogObjects 3 }

        -- 1.3.6.1.4.1.9839.2.1.2.5
        Temp-Pl-Oben OBJECT-TYPE
                    SYNTAX Integer32 (-32767..32767)
                    UNITS "C/F x10"
                    MAX-ACCESS read-only
                    STATUS current
                    DESCRIPTION "Temperatur Pufferspeicher Oben"
                    ::= { analogObjects 4 }

        -- 1.3.6.1.4.1.9839.2.1.2.6
        Temp-Pl-Vor OBJECT-TYPE
                    SYNTAX Integer32 (-32767..32767)
                    UNITS "C/F x10"
                    MAX-ACCESS read-only
                    STATUS current
                    DESCRIPTION "Temperatur Plattentauscher Vorlauf"
                    ::= { analogObjects 5 }

        -- 1.3.6.1.4.1.9839.2.1.2.7
        Temp-KW-Sek-Vor OBJECT-TYPE
                    SYNTAX Integer32 (-32767..32767)
                    UNITS "C/F x10"
                    MAX-ACCESS read-only
                    STATUS current
                    DESCRIPTION "Temperatur Kaltwasser Sekundaer Vorlauf"
                    ::= { analogObjects 6 }

        -- 1.3.6.1.4.1.9839.2.1.2.8
        Temp-KW-Sek-Rue OBJECT-TYPE
                    SYNTAX Integer32 (-32767..32767)
                    UNITS "Ohm x10"
                    MAX-ACCESS read-only
                    STATUS current
                    DESCRIPTION "Temperatur Kaltwasser Sekundaer Ruecklauf"
                    ::= { analogObjects 7 }

        -- 1.3.6.1.4.1.9839.2.1.2.9
        DR-KW-Sek OBJECT-TYPE
                    SYNTAX Integer32 (-32767..32767)
                    UNITS "bar x10"
                    MAX-ACCESS read-only
                    STATUS current
                    DESCRIPTION "Drucktransmitter Kaltwasser Sekundaer"
                    ::= { analogObjects 8 }

        -- 1.3.6.1.4.1.9839.2.1.2.10
        Temp-Pl-Rue OBJECT-TYPE
                    SYNTAX Integer32 (-32767..32767)
                    UNITS "Ohm x10"
                    MAX-ACCESS read-only
                    STATUS current
                    DESCRIPTION "Temperatur Plattentauscher Ruecklauf"
                    ::= { analogObjects 9 }

        -- 1.3.6.1.4.1.9839.2.1.2.11
        Aussentemp OBJECT-TYPE
                    SYNTAX Integer32 (-32767..32767)
                    UNITS "Ohm x10"
                    MAX-ACCESS read-only
                    STATUS current
                    DESCRIPTION "Aussentemperatur"
                    ::= { analogObjects 10 }

        -- 1.3.6.1.4.1.9839.2.1.3
        integerObjects OBJECT IDENTIFIER ::= { std-air-condMIB 3 }

 
        -- 1.3.6.1.4.1.9839.2.1.3.3
        FK OBJECT-TYPE
                    SYNTAX Integer32 (0..7)
                    UNITS "N/A"
                    MAX-ACCESS read-only
                    STATUS current
                    DESCRIPTION "Freikuehler Y ANzeige 0-100%"
                    ::= { integerObjects 3 }


	END

--
-- CAREL-std-air-cond.MIB
--
