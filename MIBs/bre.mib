--
-- bre.MIB
-- MIB generated by Uniflair
-- Thursday 26 April 2012
--

    BRE-MIB DEFINITIONS ::= BEGIN

		IMPORTS
			OBJECT-GROUP		FROM SNMPv2-CONF			
			sysContact, sysName,
			sysLocation		FROM SNMPv2-MIB
			enterprises, MODULE-IDENTITY,
			OBJECT-TYPE, Integer32	FROM SNMPv2-SMI
			DisplayString		FROM RFC1213-MIB;		
		
        bre-MIB MODULE-IDENTITY
      		LAST-UPDATED  "200712101120Z"		-- December 10, 2007 at 11:20 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the bre device."
      		REVISION  "200712101120Z"		-- December 10, 2007 at 11:20 GMT
      		DESCRIPTION
                "This is the original version of the MIB."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
 		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.
		
		
        -- 1.3.6.1.4.1.9839.2.1.1
        digitalObjects OBJECT IDENTIFIER ::= { bre-MIB 1 }

        -- 1.3.6.1.4.1.9839.2.1.1.1
        system-on OBJECT-TYPE
                    SYNTAX Integer32 (0..1)
                    UNITS "N/A"
                    MAX-ACCESS read-only
                    STATUS current
                    DESCRIPTION "System On"
                    ::= { digitalObjects 1 }

        -- 1.3.6.1.4.1.9839.2.1.1.2
        compressor-1-25-step OBJECT-TYPE
                    SYNTAX Integer32 (0..1)
                    UNITS "N/A"
                    MAX-ACCESS read-only
                    STATUS current
                    DESCRIPTION "Compressor 1 ON- 25% step"
                    ::= { digitalObjects 2 }

        -- 1.3.6.1.4.1.9839.2.1.1.3
        compressor-1-50-step OBJECT-TYPE
                    SYNTAX Integer32 (0..1)
                    UNITS "N/A"
                    MAX-ACCESS read-only
                    STATUS current
                    DESCRIPTION "Compressor 1-50% step"
                    ::= { digitalObjects 3 }

        -- 1.3.6.1.4.1.9839.2.1.1.4
        compressor-1-75-step OBJECT-TYPE
                    SYNTAX Integer32 (0..1)
                    UNITS "N/A"
                    MAX-ACCESS read-only
                    STATUS current
                    DESCRIPTION "Compressor 1- 75% step"
                    ::= { digitalObjects 4 }

        -- 1.3.6.1.4.1.9839.2.1.1.5
        compressor-1-100-step OBJECT-TYPE
                    SYNTAX Integer32 (0..1)
                    UNITS "N/A"
                    MAX-ACCESS read-only
                    STATUS current
                    DESCRIPTION "Compressor 1-100% step"
                    ::= { digitalObjects 5 }

        -- 1.3.6.1.4.1.9839.2.1.1.6
        compressor-2-25-step OBJECT-TYPE
                    SYNTAX Integer32 (0..1)
                    UNITS "N/A"
                    MAX-ACCESS read-only
                    STATUS current
                    DESCRIPTION "Compressor 2 ON-25% step"
                    ::= { digitalObjects 6 }

        -- 1.3.6.1.4.1.9839.2.1.1.7
       compressor-2-50-step OBJECT-TYPE
                    SYNTAX Integer32 (0..1)
                    UNITS "N/A"
                    MAX-ACCESS read-only
                    STATUS current
                    DESCRIPTION "Compressor 2-50% step"
                    ::= { digitalObjects 7 }

        -- 1.3.6.1.4.1.9839.2.1.1.8
        compressor-2-75-step OBJECT-TYPE
                    SYNTAX Integer32 (0..1)
                    UNITS "N/A"
                    MAX-ACCESS read-only
                    STATUS current
                    DESCRIPTION "Compressor 2-75% step"
                    ::= { digitalObjects 8 }

        -- 1.3.6.1.4.1.9839.2.1.1.9
        compressor-2-100-step OBJECT-TYPE
                    SYNTAX Integer32 (0..1)
                    UNITS "N/A"
                    MAX-ACCESS read-only
                    STATUS current
                    DESCRIPTION "Compressor 2-100% step"
                    ::= { digitalObjects 9 }

        -- 1.3.6.1.4.1.9839.2.1.1.10
        circ1-liquid-solenoid OBJECT-TYPE
                    SYNTAX Integer32 (0..1)
                    UNITS "N/A"
                    MAX-ACCESS read-only
                    STATUS current
                    DESCRIPTION "Liquid solenoid valve circuit 1"
                    ::= { digitalObjects 10 }

        -- 1.3.6.1.4.1.9839.2.1.1.11
        circ2-liquid-solenoid OBJECT-TYPE
                    SYNTAX Integer32 (0..1)
                    UNITS "N/A"
                    MAX-ACCESS read-only
                    STATUS current
                    DESCRIPTION "Liquid solenoid valve circuit 2"
                    ::= { digitalObjects 11 }

        -- 1.3.6.1.4.1.9839.2.1.1.12
        pump-1-on OBJECT-TYPE
                    SYNTAX Integer32 (0..1)
                    UNITS "N/A"
                    MAX-ACCESS read-only
                    STATUS current
                    DESCRIPTION "Pump 1 on"
                    ::= { digitalObjects 12 }

        -- 1.3.6.1.4.1.9839.2.1.1.13
        pump-2-on OBJECT-TYPE
                    SYNTAX Integer32 (0..1)
                    UNITS "N/A"
                    MAX-ACCESS read-only
                    STATUS current
                    DESCRIPTION "Pump 2 on"
                    ::= { digitalObjects 13 }

        -- 1.3.6.1.4.1.9839.2.1.1.14
        freecooling-pump-on OBJECT-TYPE
                    SYNTAX Integer32 (0..1)
                    UNITS "N/A"
                    MAX-ACCESS read-only
                    STATUS current
                    DESCRIPTION "Freecooling pump on"
                    ::= { digitalObjects 14 }

        -- 1.3.6.1.4.1.9839.2.1.1.15
        antifreeze-heaters OBJECT-TYPE
                    SYNTAX Integer32 (0..1)
                    UNITS "N/A"
                    MAX-ACCESS read-only
                    STATUS current
                    DESCRIPTION "Antifreeze heaters (option)"
                    ::= { digitalObjects 15 }

        -- 1.3.6.1.4.1.9839.2.1.1.16
        heat-recovery-100 OBJECT-TYPE
                    SYNTAX Integer32 (0..1)
                    UNITS "N/A"
                    MAX-ACCESS read-only
                    STATUS current
                    DESCRIPTION "100% Heat recovery (option)"
                    ::= { digitalObjects 16 }

        -- 1.3.6.1.4.1.9839.2.1.1.17
        regulated-condensing OBJECT-TYPE
                    SYNTAX Integer32 (0..1)
                    UNITS "N/A"
                    MAX-ACCESS read-only
                    STATUS current
                    DESCRIPTION "Regulated condensing Fans"
                    ::= { digitalObjects 17 }

        -- 1.3.6.1.4.1.9839.2.1.1.18
        dcf OBJECT-TYPE
                    SYNTAX Integer32 (0..1)
                    UNITS "N/A"
                    MAX-ACCESS read-only
                    STATUS current
                    DESCRIPTION "Direct condensing Fans"
                    ::= { digitalObjects 18 }

        -- 1.3.6.1.4.1.9839.2.1.1.19
        rcf2 OBJECT-TYPE
                    SYNTAX Integer32 (0..1)
                    UNITS "N/A"
                    MAX-ACCESS read-only
                    STATUS current
                    DESCRIPTION "Regulated condensing Fans 2"
                    ::= { digitalObjects 19 }

        -- 1.3.6.1.4.1.9839.2.1.1.20
        dcf2 OBJECT-TYPE
                    SYNTAX Integer32 (0..1)
                    UNITS "N/A"
                    MAX-ACCESS read-only
                    STATUS current
                    DESCRIPTION "Direct condensing Fans 2"
                    ::= { digitalObjects 20 }

        -- 1.3.6.1.4.1.9839.2.1.1.21
        circ1d OBJECT-TYPE
                    SYNTAX Integer32 (0..1)
                    UNITS "N/A"
                    MAX-ACCESS read-only
                    STATUS current
                    DESCRIPTION "Circuit 1 Defrost (Heat pump only)"
                    ::= { digitalObjects 21 }

        -- 1.3.6.1.4.1.9839.2.1.1.22
        circ2d OBJECT-TYPE
                    SYNTAX Integer32 (0..1)
                    UNITS "N/A"
                    MAX-ACCESS read-only
                    STATUS current
                    DESCRIPTION "Circuit 2 Defrost (Heat pump only)"
                    ::= { digitalObjects 22 }

        -- 1.3.6.1.4.1.9839.2.1.1.23
        lpc OBJECT-TYPE
                    SYNTAX Integer32 (0..1)
                    UNITS "N/A"
                    MAX-ACCESS read-only
                    STATUS current
                    DESCRIPTION "Low power consumption mode"
                    ::= { digitalObjects 23 }

        -- 1.3.6.1.4.1.9839.2.1.1.24
        wmode OBJECT-TYPE
                    SYNTAX Integer32 (0..1)
                    UNITS "N/A"
                    MAX-ACCESS read-only
                    STATUS current
                    DESCRIPTION "Winter mode (Heat pump only)"
                    ::= { digitalObjects 24 }

        -- 1.3.6.1.4.1.9839.2.1.1.25
        wpassal OBJECT-TYPE
                    SYNTAX Integer32 (0..1)
                    UNITS "N/A"
                    MAX-ACCESS read-only
                    STATUS current
                    DESCRIPTION "Wrong password Alarm"
                    ::= { digitalObjects 25 }

        -- 1.3.6.1.4.1.9839.2.1.1.26
        wintempal OBJECT-TYPE
                    SYNTAX Integer32 (0..1)
                    UNITS "N/A"
                    MAX-ACCESS read-only
                    STATUS current
                    DESCRIPTION "Water inlet High Temperature Alarm"
                    ::= { digitalObjects 26 }

        -- 1.3.6.1.4.1.9839.2.1.1.27
        wintlowtemp-al OBJECT-TYPE
                    SYNTAX Integer32 (0..1)
                    UNITS "N/A"
                    MAX-ACCESS read-only
                    STATUS current
                    DESCRIPTION "Water inlet Low Temperature Alarm"
                    ::= { digitalObjects 27 }

        -- 1.3.6.1.4.1.9839.2.1.1.28
        loss-wat-fl-al OBJECT-TYPE
                    SYNTAX Integer32 (0..1)
                    UNITS "N/A"
                    MAX-ACCESS read-only
                    STATUS current
                    DESCRIPTION "Loss of water flow Alarm"
                    ::= { digitalObjects 28 }

        -- 1.3.6.1.4.1.9839.2.1.1.29
        low-press-1-pre OBJECT-TYPE
                    SYNTAX Integer32 (0..1)
                    UNITS "N/A"
                    MAX-ACCESS read-only
                    STATUS current
                    DESCRIPTION "Low Pressure 1 PreAlarm (Autom.Reset)"
                    ::= { digitalObjects 29 }

        -- 1.3.6.1.4.1.9839.2.1.1.30
        low-press-2-pre OBJECT-TYPE
                    SYNTAX Integer32 (0..1)
                    UNITS "N/A"
                    MAX-ACCESS read-only
                    STATUS current
                    DESCRIPTION "Low Pressure 2 PreAlarm (Autom.Reset)"
                    ::= { digitalObjects 30 }

        -- 1.3.6.1.4.1.9839.2.1.1.31
        low-press-1 OBJECT-TYPE
                    SYNTAX Integer32 (0..1)
                    UNITS "N/A"
                    MAX-ACCESS read-only
                    STATUS current
                    DESCRIPTION "Low Pressure 1 Alarm"
                    ::= { digitalObjects 31 }

        -- 1.3.6.1.4.1.9839.2.1.1.32
        low-press-2 OBJECT-TYPE
                    SYNTAX Integer32 (0..1)
                    UNITS "N/A"
                    MAX-ACCESS read-only
                    STATUS current
                    DESCRIPTION "Low Pressure 2 Alarm"
                    ::= { digitalObjects 32 }

        -- 1.3.6.1.4.1.9839.2.1.1.33
        hp1-al OBJECT-TYPE
                    SYNTAX Integer32 (0..1)
                    UNITS "N/A"
                    MAX-ACCESS read-only
                    STATUS current
                    DESCRIPTION "High Pressure 1 Alarm"
                    ::= { digitalObjects 33 }

        -- 1.3.6.1.4.1.9839.2.1.1.34
        hp2-al OBJECT-TYPE
                    SYNTAX Integer32 (0..1)
                    UNITS "N/A"
                    MAX-ACCESS read-only
                    STATUS current
                    DESCRIPTION "High Pressure 2 Alarm"
                    ::= { digitalObjects 34 }

        -- 1.3.6.1.4.1.9839.2.1.1.35
        disch-fail-Comp1 OBJECT-TYPE
                    SYNTAX Integer32 (0..1)
                    UNITS "N/A"
                    MAX-ACCESS read-only
                    STATUS current
                    DESCRIPTION "Compressor 1 Overload Alarm"
                    ::= { digitalObjects 35 }

 	-- 1.3.6.1.4.1.9839.2.1.1.36
        disch-fail-Comp2 OBJECT-TYPE
                    SYNTAX Integer32 (0..1)
                    UNITS "N/A"
                    MAX-ACCESS read-only
                    STATUS current
                    DESCRIPTION "Compressor 2 Overload Alarm"
                    ::= { digitalObjects 36 }

	-- 1.3.6.1.4.1.9839.2.1.1.37
        comp1-overload OBJECT-TYPE
                    SYNTAX Integer32 (0..1)
                    UNITS "N/A"
                    MAX-ACCESS read-only
                    STATUS current
                    DESCRIPTION "Compressor 1 Integral protection Alarm"
                    ::= { digitalObjects 37 }

        -- 1.3.6.1.4.1.9839.2.1.1.38
        comp2-overload OBJECT-TYPE
                    SYNTAX Integer32 (0..1)
                    UNITS "N/A"
                    MAX-ACCESS read-only
                    STATUS current
                    DESCRIPTION "Compressor 2 Integral protection Alarm"
                    ::= { digitalObjects 38 }

        -- 1.3.6.1.4.1.9839.2.1.1.39
        oil-diff-press1-al OBJECT-TYPE
                    SYNTAX Integer32 (0..1)
                    UNITS "N/A"
                    MAX-ACCESS read-only
                    STATUS current
                    DESCRIPTION "Oil differential pressure 1 Alarm"
                    ::= { digitalObjects 39 }

        -- 1.3.6.1.4.1.9839.2.1.1.40
        oil-diff-press2-al OBJECT-TYPE
                    SYNTAX Integer32 (0..1)
                    UNITS "N/A"
                    MAX-ACCESS read-only
                    STATUS current
                    DESCRIPTION "Oil differential pressure 2 Alarm"
                    ::= { digitalObjects 40 }

        -- 1.3.6.1.4.1.9839.2.1.1.41
        antifreeze1-prealarm OBJECT-TYPE
                    SYNTAX Integer32 (0..1)
                    UNITS "N/A"
                    MAX-ACCESS read-only
                    STATUS current
                    DESCRIPTION "Antifreeze 1 Prealarm (Automatic Reset)"
                    ::= { digitalObjects 41 }

        -- 1.3.6.1.4.1.9839.2.1.1.42
        antifreeze2-prealarm OBJECT-TYPE
                    SYNTAX Integer32 (0..1)
                    UNITS "N/A"
                    MAX-ACCESS read-only
                    STATUS current
                    DESCRIPTION "Antifreeze 2 Prealarm (Automatic Reset)"
                    ::= { digitalObjects 42 }

        -- 1.3.6.1.4.1.9839.2.1.1.43
        antifreeze-1-alarm OBJECT-TYPE
                    SYNTAX Integer32 (0..1)
                    UNITS "N/A"
                    MAX-ACCESS read-only
                    STATUS current
                    DESCRIPTION "Antifreeze 1 Alarm"
                    ::= { digitalObjects 43 }

        -- 1.3.6.1.4.1.9839.2.1.1.44
        antifreeze-2-alarm OBJECT-TYPE
                    SYNTAX Integer32 (0..1)
                    UNITS "N/A"
                    MAX-ACCESS read-only
                    STATUS current
                    DESCRIPTION "Antifreeze 2 Alarm"
                    ::= { digitalObjects 44 }

        -- 1.3.6.1.4.1.9839.2.1.1.45
        hrec-lim-al OBJECT-TYPE
                    SYNTAX Integer32 (0..1)
                    UNITS "N/A"
                    MAX-ACCESS read-only
                    STATUS current
                    DESCRIPTION "Heat recovery limit Alarm"
                    ::= { digitalObjects 45 }

        -- 1.3.6.1.4.1.9839.2.1.1.46
        hrec-lim-aut-reset-al OBJECT-TYPE
                    SYNTAX Integer32 (0..1)
                    UNITS "N/A"
                    MAX-ACCESS read-only
                    STATUS current
                    DESCRIPTION "Heat recovery limit PreAlarm (Autom.Reset)"
                    ::= { digitalObjects 46 }

        -- 1.3.6.1.4.1.9839.2.1.1.47
        pump1-overload-alarm OBJECT-TYPE
                    SYNTAX Integer32 (0..1)
                    UNITS "N/A"
                    MAX-ACCESS read-only
                    STATUS current
                    DESCRIPTION "Circulating Pump 1 Overload Alarm"
                    ::= { digitalObjects 47 }

        -- 1.3.6.1.4.1.9839.2.1.1.48
        pump2-overload-alarm OBJECT-TYPE
                    SYNTAX Integer32 (0..1)
                    UNITS "N/A"
                    MAX-ACCESS read-only
                    STATUS current
                    DESCRIPTION "Circulating Pump 2 Overload Alarm"
                    ::= { digitalObjects 48 }

        -- 1.3.6.1.4.1.9839.2.1.1.49
        freecooling-pump-overload-alarm OBJECT-TYPE
                    SYNTAX Integer32 (0..1)
                    UNITS "N/A"
                    MAX-ACCESS read-only
                    STATUS current
                    DESCRIPTION "Freecooling Pump Overload Alarm"
                    ::= { digitalObjects 49 }

        -- 1.3.6.1.4.1.9839.2.1.1.50
        iint-lan-al OBJECT-TYPE
                    SYNTAX Integer32 (0..1)
                    UNITS "N/A"
                    MAX-ACCESS read-only
                    STATUS current
                    DESCRIPTION "Interrupted LAN Alarm"
                    ::= { digitalObjects 50 }

        -- 1.3.6.1.4.1.9839.2.1.1.51
        win-tempsens OBJECT-TYPE
                    SYNTAX Integer32 (0..1)
                    UNITS "N/A"
                    MAX-ACCESS read-only
                    STATUS current
                    DESCRIPTION "Water Inlet Temp. Sensor Failure/Disconnected"
                    ::= { digitalObjects 51 }

        -- 1.3.6.1.4.1.9839.2.1.1.52
        wou-tempsens OBJECT-TYPE
                    SYNTAX Integer32 (0..1)
                    UNITS "N/A"
                    MAX-ACCESS read-only
                    STATUS current
                    DESCRIPTION "Water Outlet Temp. Sensor Failure/Disconnected"
                    ::= { digitalObjects 52 }

        -- 1.3.6.1.4.1.9839.2.1.1.53
        wat-tank-temp-fail OBJECT-TYPE
                    SYNTAX Integer32 (0..1)
                    UNITS "N/A"
                    MAX-ACCESS read-only
                    STATUS current
                    DESCRIPTION "Water Tank Temp. Sensor Failure/Disconnected"
                    ::= { digitalObjects 53 }

        -- 1.3.6.1.4.1.9839.2.1.1.54
        out-air-temp-fail OBJECT-TYPE
                    SYNTAX Integer32 (0..1)
                    UNITS "N/A"
                    MAX-ACCESS read-only
                    STATUS current
                    DESCRIPTION "Outdoor air Temp. Sensor Failure/Disconnected"
                    ::= { digitalObjects 54 }

        -- 1.3.6.1.4.1.9839.2.1.1.55
        cond1-temp-sens OBJECT-TYPE
                    SYNTAX Integer32 (0..1)
                    UNITS "N/A"
                    MAX-ACCESS read-only
                    STATUS current
                    DESCRIPTION "Condensing 1 Temp. Sensor Failure/Disconnected"
                    ::= { digitalObjects 55 }

        -- 1.3.6.1.4.1.9839.2.1.1.56
        cond2-temp-sens OBJECT-TYPE
                    SYNTAX Integer32 (0..1)
                    UNITS "N/A"
                    MAX-ACCESS read-only
                    STATUS current
                    DESCRIPTION "Condensing 2 Temp. Sensor Failure/Disconnected"
                    ::= { digitalObjects 56 }

        -- 1.3.6.1.4.1.9839.2.1.1.57
        evap1-press-fail OBJECT-TYPE
                    SYNTAX Integer32 (0..1)
                    UNITS "N/A"
                    MAX-ACCESS read-only
                    STATUS current
                    DESCRIPTION "Evaporating 1 Press. Sensor Failure/Disconnected"
                    ::= { digitalObjects 57 }

        -- 1.3.6.1.4.1.9839.2.1.1.58
        evap2-press-fail OBJECT-TYPE
                    SYNTAX Integer32 (0..1)
                    UNITS "N/A"
                    MAX-ACCESS read-only
                    STATUS current
                    DESCRIPTION "Evaporating 2 Press. Sensor Failure/Disconnected"
                    ::= { digitalObjects 58 }

        -- 1.3.6.1.4.1.9839.2.1.1.59
        sum-win-control OBJECT-TYPE
                    SYNTAX Integer32 (0..1)
                    UNITS "N/A"
                    MAX-ACCESS read-write
                    STATUS current
                    DESCRIPTION "Summer/Winter mode remote control"
                    ::= { digitalObjects 59 }

        -- 1.3.6.1.4.1.9839.2.1.1.60
        switch-On-Off OBJECT-TYPE
                    SYNTAX Integer32 (0..1)
                    UNITS "N/A"
                    MAX-ACCESS read-write
                    STATUS current
                    DESCRIPTION "Unit Remote Switch-On/Off Control"
                    ::= { digitalObjects 60 }

        -- 1.3.6.1.4.1.9839.2.1.1.61
        buzzer-alarm OBJECT-TYPE
                    SYNTAX Integer32 (0..1)
                    UNITS "N/A"
                    MAX-ACCESS read-write
                    STATUS current
                    DESCRIPTION "Buzzer and Alarm Remote Reset Control"
                    ::= { digitalObjects 61 }

        -- 1.3.6.1.4.1.9839.2.1.1.62
        pump1-2-control OBJECT-TYPE
                    SYNTAX Integer32 (0..1)
                    UNITS "N/A"
                    MAX-ACCESS read-write
                    STATUS current
                    DESCRIPTION "Pump 1-2 Switch-over remote control"
                    ::= { digitalObjects 62 }

        -- 1.3.6.1.4.1.9839.2.1.1.63
        setb-mode OBJECT-TYPE
                    SYNTAX Integer32 (0..1)
                    UNITS "N/A"
                    MAX-ACCESS read-write
                    STATUS current
                    DESCRIPTION "Set Back Mode (Sleep Mode)"
                    ::= { digitalObjects 63 }


        -- 1.3.6.1.4.1.9839.2.1.1.65
        usage-temp OBJECT-TYPE
                    SYNTAX Integer32 (0..1)
                    UNITS "N/A"
                    MAX-ACCESS read-write
                    STATUS current
                    DESCRIPTION "Usage of Temp. Values: Local (0) / Mean (1)"
                    ::= { digitalObjects 65 }

        -- 1.3.6.1.4.1.9839.2.1.1.66
        st-by-Units OBJECT-TYPE
                    SYNTAX Integer32 (0..1)
                    UNITS "N/A"
                    MAX-ACCESS read-only
                    STATUS current
                    DESCRIPTION "No. Of Stand-by Units: one (0) / two (1)"
                    ::= { digitalObjects 66 }

        -- 1.3.6.1.4.1.9839.2.1.1.67
        w-tank-range OBJECT-TYPE
                    SYNTAX Integer32 (0..1)
                    UNITS "N/A"
                    MAX-ACCESS read-only
                    STATUS current
                    DESCRIPTION "Water tank range"
                    ::= { digitalObjects 67 }

        -- 1.3.6.1.4.1.9839.2.1.1.68
        pump1-2-remote-control OBJECT-TYPE
                    SYNTAX Integer32 (0..1)
                    UNITS "N/A"
                    MAX-ACCESS read-only
                    STATUS current
                    DESCRIPTION "Pump 1-2 Switch-over remote control"
                    ::= { digitalObjects 68 }

        -- 1.3.6.1.4.1.9839.2.1.1.69
        general-alarm OBJECT-TYPE
                    SYNTAX Integer32 (0..1)
                    UNITS "N/A"
                    MAX-ACCESS read-only
                    STATUS current
                    DESCRIPTION "General Alarm State"
                    ::= { digitalObjects 69 }

        -- 1.3.6.1.4.1.9839.2.1.1.70
        second-level-alarm OBJECT-TYPE
                    SYNTAX Integer32 (0..1)
                    UNITS "N/A"
                    MAX-ACCESS read-only
                    STATUS current
                    DESCRIPTION "2nd Level Alarm State"
                    ::= { digitalObjects 70 }

        -- 1.3.6.1.4.1.9839.2.1.1.71
        circ1-pump-fail OBJECT-TYPE
                    SYNTAX Integer32 (0..1)
                    UNITS "N/A"
                    MAX-ACCESS read-only
                    STATUS current
                    DESCRIPTION "Circuit 1 Pump-down Failed"
                    ::= { digitalObjects 71 }

        -- 1.3.6.1.4.1.9839.2.1.1.72
        circ2-pump-fail OBJECT-TYPE
                    SYNTAX Integer32 (0..1)
                    UNITS "N/A"
                    MAX-ACCESS read-only
                    STATUS current
                    DESCRIPTION "Circuit 2 Pump-down Failed"
                    ::= { digitalObjects 72 }

        -- 1.3.6.1.4.1.9839.2.1.1.73
        circ1-comp-malf OBJECT-TYPE
                    SYNTAX Integer32 (0..1)
                    UNITS "N/A"
                    MAX-ACCESS read-only
                    STATUS current
                    DESCRIPTION "Circuit 1 Compressor malfunction"
                    ::= { digitalObjects 73 }

        -- 1.3.6.1.4.1.9839.2.1.1.74
        circ2-comp-malf OBJECT-TYPE
                    SYNTAX Integer32 (0..1)
                    UNITS "N/A"
                    MAX-ACCESS read-only
                    STATUS current
                    DESCRIPTION "Circuit 2 Compressor malfunction"
                    ::= { digitalObjects 74 }

        -- 1.3.6.1.4.1.9839.2.1.1.75
        hc-cond1 OBJECT-TYPE
                    SYNTAX Integer32 (0..1)
                    UNITS "N/A"
                    MAX-ACCESS read-only
                    STATUS current
                    DESCRIPTION "High condensing temperature 1"
                    ::= { digitalObjects 75 }

        -- 1.3.6.1.4.1.9839.2.1.1.76
        hc-cond2 OBJECT-TYPE
                    SYNTAX Integer32 (0..1)
                    UNITS "N/A"
                    MAX-ACCESS read-only
                    STATUS current
                    DESCRIPTION "High condensing temperature 2"
                    ::= { digitalObjects 76 }

        -- 1.3.6.1.4.1.9839.2.1.1.77
        circ1-comp-op-limit OBJECT-TYPE
                    SYNTAX Integer32 (0..1)
                    UNITS "N/A"
                    MAX-ACCESS read-only
                    STATUS current
                    DESCRIPTION "Circuit 1 Compressor Operative Limits"
                    ::= { digitalObjects 77 }

        -- 1.3.6.1.4.1.9839.2.1.1.78
        circ2-comp-op-limit OBJECT-TYPE
                    SYNTAX Integer32 (0..1)
                    UNITS "N/A"
                    MAX-ACCESS read-only
                    STATUS current
                    DESCRIPTION "Circuit 2 Compressor Operative Limits"
                    ::= { digitalObjects 78 }


        -- 1.3.6.1.4.1.9839.2.1.1.79
        non-perf-def-lim OBJECT-TYPE
                    SYNTAX Integer32 (0..1)
                    UNITS "N/A"
                    MAX-ACCESS read-only
                    STATUS current
                    DESCRIPTION "Defrost Limits non performing"
                    ::= { digitalObjects 79 }

        -- 1.3.6.1.4.1.9839.2.1.1.80
        comp1-hc OBJECT-TYPE
                    SYNTAX Integer32 (0..1)
                    UNITS "N/A"
                    MAX-ACCESS read-only
                    STATUS current
                    DESCRIPTION "Compressor 1 hour counter"
                    ::= { digitalObjects 80 }

        -- 1.3.6.1.4.1.9839.2.1.1.81
        comp2-hc OBJECT-TYPE
                    SYNTAX Integer32 (0..1)
                    UNITS "N/A"
                    MAX-ACCESS read-only
                    STATUS current
                    DESCRIPTION "Compressor 2 hour counter"
                    ::= { digitalObjects 81 }

        -- 1.3.6.1.4.1.9839.2.1.1.82
        pump1-calc-hc OBJECT-TYPE
                    SYNTAX Integer32 (0..1)
                    UNITS "N/A"
                    MAX-ACCESS read-only
                    STATUS current
                    DESCRIPTION "Circulating Pump 1 hour counter"
                    ::= { digitalObjects 82 }

        -- 1.3.6.1.4.1.9839.2.1.1.83
        pump2-calc-hc OBJECT-TYPE
                    SYNTAX Integer32 (0..1)
                    UNITS "N/A"
                    MAX-ACCESS read-only
                    STATUS current
                    DESCRIPTION "Circulating Pump 2 hour counter"
                    ::= { digitalObjects 83 }

        -- 1.3.6.1.4.1.9839.2.1.1.84
        fp-hc OBJECT-TYPE
                    SYNTAX Integer32 (0..1)
                    UNITS "N/A"
                    MAX-ACCESS read-only
                    STATUS current
                    DESCRIPTION "Freecooling Pump hour counter"
                    ::= { digitalObjects 84 }

        -- 1.3.6.1.4.1.9839.2.1.1.85
        lpower-r OBJECT-TYPE
                    SYNTAX Integer32 (0..1)
                    UNITS "N/A"
                    MAX-ACCESS read-write
                    STATUS current
                    DESCRIPTION "Low power request"
                    ::= { digitalObjects 85 }

        -- 1.3.6.1.4.1.9839.2.1.1.86
        comp1-not-running OBJECT-TYPE
                    SYNTAX Integer32 (0..1)
                    UNITS "N/A"
                    MAX-ACCESS read-only
                    STATUS current
                    DESCRIPTION "Compressor 1 not running"
                    ::= { digitalObjects 86 }

        -- 1.3.6.1.4.1.9839.2.1.1.87
        comp2-not-running OBJECT-TYPE
                    SYNTAX Integer32 (0..1)
                    UNITS "N/A"
                    MAX-ACCESS read-only
                    STATUS current
                    DESCRIPTION "Compressor 2 not running"
                    ::= { digitalObjects 87 }

        -- 1.3.6.1.4.1.9839.2.1.1.88
        comp1-force-off OBJECT-TYPE
                    SYNTAX Integer32 (0..1)
                    UNITS "N/A"
                    MAX-ACCESS read-only
                    STATUS current
                    DESCRIPTION "Compressor 1 Force Off"
                    ::= { digitalObjects 88 }

        -- 1.3.6.1.4.1.9839.2.1.1.89
        comp2-force-off OBJECT-TYPE
                    SYNTAX Integer32 (0..1)
                    UNITS "N/A"
                    MAX-ACCESS read-only
                    STATUS current
                    DESCRIPTION "Compressor 2 Force Off"
                    ::= { digitalObjects 89 }

        -- 1.3.6.1.4.1.9839.2.1.1.90
        fans-thermal1-alarm OBJECT-TYPE
                    SYNTAX Integer32 (0..1)
                    UNITS "N/A"
                    MAX-ACCESS read-only
                    STATUS current
                    DESCRIPTION "Fans thermal 1 alarm"
                    ::= { digitalObjects 90 }

        -- 1.3.6.1.4.1.9839.2.1.1.91
        fans-thermal2-alarm OBJECT-TYPE
                    SYNTAX Integer32 (0..1)
                    UNITS "N/A"
                    MAX-ACCESS read-only
                    STATUS current
                    DESCRIPTION "Fans thermal 2 alarm"
                    ::= { digitalObjects 91 }

        -- 1.3.6.1.4.1.9839.2.1.1.92
        board2-discon OBJECT-TYPE
                    SYNTAX Integer32 (0..1)
                    UNITS "N/A"
                    MAX-ACCESS read-only
                    STATUS current
                    DESCRIPTION "Board 2 disconnected"
                    ::= { digitalObjects 92 }

        -- 1.3.6.1.4.1.9839.2.1.1.93
        fase-sequence-alarm OBJECT-TYPE
                    SYNTAX Integer32 (0..1)
                    UNITS "N/A"
                    MAX-ACCESS read-only
                    STATUS current
                    DESCRIPTION "Phase sequence alarm"
                    ::= { digitalObjects 93 }

        -- 1.3.6.1.4.1.9839.2.1.1.94
        expansion-valve1-alarm OBJECT-TYPE
                    SYNTAX Integer32 (0..1)
                    UNITS "N/A"
                    MAX-ACCESS read-only
                    STATUS current
                    DESCRIPTION "Expansion valve 1 alarm"
                    ::= { digitalObjects 94 }

        -- 1.3.6.1.4.1.9839.2.1.1.95
        expansion-valve2-alarm OBJECT-TYPE
                    SYNTAX Integer32 (0..1)
                    UNITS "N/A"
                    MAX-ACCESS read-only
                    STATUS current
                    DESCRIPTION "Expansion valve 2 alarm"
                    ::= { digitalObjects 95 }

        -- 1.3.6.1.4.1.9839.2.1.1.96
        reset-IG OBJECT-TYPE
                    SYNTAX Integer32 (0..1)
                    UNITS "N/A"
                    MAX-ACCESS read-write
                    STATUS current
                    DESCRIPTION "Reset IG Socomec (Optional Power supply motorized main switch)"
                    ::= { digitalObjects 96 }

        -- 1.3.6.1.4.1.9839.2.1.1.97
        line1-active OBJECT-TYPE
                    SYNTAX Integer32 (0..1)
                    UNITS "N/A"
                    MAX-ACCESS read-only
                    STATUS current
                    DESCRIPTION "Line 1 Active (Optional Power Supply motorized main switch)"
                    ::= { digitalObjects 97 }


        -- 1.3.6.1.4.1.9839.2.1.1.98
        line2-active OBJECT-TYPE
                    SYNTAX Integer32 (0..1)
                    UNITS "N/A"
                    MAX-ACCESS read-only
                    STATUS current
                    DESCRIPTION "Line 2 Active (Optional Power Supply motorized main switch)"
                    ::= { digitalObjects 98 }

        -- 1.3.6.1.4.1.9839.2.1.1.101
        u-type OBJECT-TYPE
                    SYNTAX Integer32 (0..1)
                    UNITS "N/A"
                    MAX-ACCESS read-only
                    STATUS current
                    DESCRIPTION "Unit type (0=BRA; 1=BRE)"
                    ::= { digitalObjects 101 }

        -- 1.3.6.1.4.1.9839.2.1.1.102
        fans-type OBJECT-TYPE
                    SYNTAX Integer32 (0..1)
                    UNITS "N/A"
                    MAX-ACCESS read-only
                    STATUS current
                    DESCRIPTION "Fans type (0=Phase-control; 1=EC)"
                    ::= { digitalObjects 102 }

        -- 1.3.6.1.4.1.9839.2.1.1.108
        disch-temp-comp1 OBJECT-TYPE
                    SYNTAX Integer32 (0..1)
                    UNITS "N/A"
                    MAX-ACCESS read-only
                    STATUS current
                    DESCRIPTION "DischargeTemp. Sensor Failure/Disconnected Comp.1"
                    ::= { digitalObjects 108 }


        -- 1.3.6.1.4.1.9839.2.1.1.109
        disch-temp-comp2 OBJECT-TYPE
                    SYNTAX Integer32 (0..1)
                    UNITS "N/A"
                    MAX-ACCESS read-only
                    STATUS current
                    DESCRIPTION "DischargeTemp. Sensor Failure/Disconnected Comp.2"
                    ::= { digitalObjects 109 }

        -- 1.3.6.1.4.1.9839.2.1.1.111
        disch-temp-comp2 OBJECT-TYPE
                    SYNTAX Integer32 (0..1)
                    UNITS "N/A"
                    MAX-ACCESS read-only
                    STATUS current
                    DESCRIPTION "Electric Heaters Fuse F1 Fault"
                    ::= { digitalObjects 111 }

        -- 1.3.6.1.4.1.9839.2.1.1.112
        disch-temp-comp2 OBJECT-TYPE
                    SYNTAX Integer32 (0..1)
                    UNITS "N/A"
                    MAX-ACCESS read-only
                    STATUS current
                    DESCRIPTION "Inverter Circulation Pump Failed"
                    ::= { digitalObjects 112 }

        -- 1.3.6.1.4.1.9839.2.1.2
        analogObjects OBJECT IDENTIFIER ::= { bre-MIB 2 }

        -- 1.3.6.1.4.1.9839.2.1.2.1
        t-wout OBJECT-TYPE
                    SYNTAX Integer32 (-32767..32767)
                    UNITS "degrees C"
                    MAX-ACCESS read-only
                    STATUS current
                    DESCRIPTION "Water Outlet Temperature"
                    ::= { analogObjects 1 }

        -- 1.3.6.1.4.1.9839.2.1.2.2
        t-wout-regul OBJECT-TYPE
                    SYNTAX Integer32 (-32767..32767)
                    UNITS "degrees C"
                    MAX-ACCESS read-only
                    STATUS current
                    DESCRIPTION "Water Outlet Temp. used by regulator"
                    ::= { analogObjects 2 }

        -- 1.3.6.1.4.1.9839.2.1.2.3
        temp-win OBJECT-TYPE
                    SYNTAX Integer32 (-32767..32767)
                    UNITS "degrees C"
                    MAX-ACCESS read-only
                    STATUS current
                    DESCRIPTION "Water Inlet Temperature"
                    ::= { analogObjects 3 }

        -- 1.3.6.1.4.1.9839.2.1.2.4
        temp-waccu OBJECT-TYPE
                    SYNTAX Integer32 (-32767..32767)
                    UNITS "degrees C"
                    MAX-ACCESS read-only
                    STATUS current
                    DESCRIPTION "Water Tank Temperature"
                    ::= { analogObjects 4 }

        -- 1.3.6.1.4.1.9839.2.1.2.5
        temp-ext OBJECT-TYPE
                    SYNTAX Integer32 (-32767..32767)
                    UNITS "degrees C"
                    MAX-ACCESS read-only
                    STATUS current
                    DESCRIPTION "Outdoor Air Temperature"
                    ::= { analogObjects 5 }

        -- 1.3.6.1.4.1.9839.2.1.2.6
        temp-cond1 OBJECT-TYPE
                    SYNTAX Integer32 (-32767..32767)
                    UNITS "degrees C"
                    MAX-ACCESS read-only
                    STATUS current
                    DESCRIPTION "CIRCUIT 1 CONDENSING TEMPERATURE"
                    ::= { analogObjects 6 }

        -- 1.3.6.1.4.1.9839.2.1.2.7
        temp-cond2 OBJECT-TYPE
                    SYNTAX Integer32 (-32767..32767)
                    UNITS "degrees C"
                    MAX-ACCESS read-only
                    STATUS current
                    DESCRIPTION "CIRCUIT 2 CONDENSING TEMPERATURE"
                    ::= { analogObjects 7 }

        -- 1.3.6.1.4.1.9839.2.1.2.8
        temp-evap1 OBJECT-TYPE
                    SYNTAX Integer32 (-32767..32767)
                    UNITS "degrees C"
                    MAX-ACCESS read-only
                    STATUS current
                    DESCRIPTION "CIRCUIT 1 EVAPORATING TEMPERATURE"
                    ::= { analogObjects 8 }

        -- 1.3.6.1.4.1.9839.2.1.2.9
        temp-evap2 OBJECT-TYPE
                    SYNTAX Integer32 (-32767..32767)
                    UNITS "degrees C"
                    MAX-ACCESS read-only
                    STATUS current
                    DESCRIPTION "CIRCUIT 2 EVAPORATING TEMPERATURE"
                    ::= { analogObjects 9 }

        -- 1.3.6.1.4.1.9839.2.1.2.10
        xv-press-cond1 OBJECT-TYPE
                    SYNTAX Integer32 (-32767..32767)
                    UNITS "bar"
                    MAX-ACCESS read-only
                    STATUS current
                    DESCRIPTION "CIRCUIT 1 CONDENSING PRESSURE"
                    ::= { analogObjects 10 }

        -- 1.3.6.1.4.1.9839.2.1.2.11
        xv-press-cond2 OBJECT-TYPE
                    SYNTAX Integer32 (-32767..32767)
                    UNITS "bar"
                    MAX-ACCESS read-only
                    STATUS current
                    DESCRIPTION "CIRCUIT 2 CONDENSING PRESSURE"
                    ::= { analogObjects 11 }

        -- 1.3.6.1.4.1.9839.2.1.2.12
        xv-press-evap1 OBJECT-TYPE
                    SYNTAX Integer32 (-32767..32767)
                    UNITS "bar"
                    MAX-ACCESS read-only
                    STATUS current
                    DESCRIPTION "CIRCUIT 1 EVAPORATING PRESSURE"
                    ::= { analogObjects 12 }

        -- 1.3.6.1.4.1.9839.2.1.2.13
        xv-press-evap2 OBJECT-TYPE
                    SYNTAX Integer32 (-32767..32767)
                    UNITS "bar"
                    MAX-ACCESS read-only
                    STATUS current
                    DESCRIPTION "CIRCUIT 2 EVAPORATING PRESSURE"
                    ::= { analogObjects 13 }

        -- 1.3.6.1.4.1.9839.2.1.2.14
        comp1-dis-temp OBJECT-TYPE
                    SYNTAX Integer32 (-32767..32767)
                    UNITS "degrees C"
                    MAX-ACCESS read-only
                    STATUS current
                    DESCRIPTION "Discharge temperature compressor 1"
                    ::= { analogObjects 14 }

        -- 1.3.6.1.4.1.9839.2.1.2.15
        comp2-dis-temp OBJECT-TYPE
                    SYNTAX Integer32 (-32767..32767)
                    UNITS "degrees C"
                    MAX-ACCESS read-only
                    STATUS current
                    DESCRIPTION "Discharge temperature compressor 2"
                    ::= { analogObjects 15 }

        -- 1.3.6.1.4.1.9839.2.1.2.16
        circ1-fan-speed-mramp OBJECT-TYPE
                    SYNTAX Integer32 (-32767..32767)
                    UNITS "%"
                    MAX-ACCESS read-only
                    STATUS current
                    DESCRIPTION "Fan Speed Modul.Ramp (circuit 1) (0-100,0%)"
                    ::= { analogObjects 16 }

        -- 1.3.6.1.4.1.9839.2.1.2.17
        circ2-fan-speed-mramp OBJECT-TYPE
                    SYNTAX Integer32 (-32767..32767)
                    UNITS "%"
                    MAX-ACCESS read-only
                    STATUS current
                    DESCRIPTION "Fan Speed Modul.Ramp (circuit 2) (0-100,0%)"
                    ::= { analogObjects 17 }

        -- 1.3.6.1.4.1.9839.2.1.2.18
        t-set-dwtemp OBJECT-TYPE
                    SYNTAX Integer32 (-32767..32767)
                    UNITS "degrees C"
                    MAX-ACCESS read-only
                    STATUS current
                    DESCRIPTION "Delivery Water Temp. Actual Set Point"
                    ::= { analogObjects 18 }

        -- 1.3.6.1.4.1.9839.2.1.2.19
        t-set-hysteresi OBJECT-TYPE
                    SYNTAX Integer32 (-32767..32767)
                    UNITS "degrees C"
                    MAX-ACCESS read-only
                    STATUS current
                    DESCRIPTION "Delivery Water Temp. Max. Hysteresi"
                    ::= { analogObjects 19 }


        -- 1.3.6.1.4.1.9839.2.1.2.20
        offset-sup OBJECT-TYPE
                    SYNTAX Integer32 (-32767..32767)
                    UNITS "degrees C"
                    MAX-ACCESS read-write
                    STATUS current
                    DESCRIPTION "Offset Supervisor"
                    ::= { analogObjects 20 }

        -- 1.3.6.1.4.1.9839.2.1.2.21
        t-sumstd-dw-set OBJECT-TYPE
                    SYNTAX Integer32 (-32767..32767)
                    UNITS "degrees C"
                    MAX-ACCESS read-write
                    STATUS current
                    DESCRIPTION "Delivery Water Temp. Summer STD Set Point"
                    ::= { analogObjects 21 }

        -- 1.3.6.1.4.1.9839.2.1.2.22
        t-sumopt-dw-set OBJECT-TYPE
                    SYNTAX Integer32 (-32767..32767)
                    UNITS "degrees C"
                    MAX-ACCESS read-write
                    STATUS current
                    DESCRIPTION "Delivery Water Temp. Summer OPT Set Point"
                    ::= { analogObjects 22 }

        -- 1.3.6.1.4.1.9839.2.1.2.23
        t-sumsetBack-set OBJECT-TYPE
                    SYNTAX Integer32 (-32767..32767)
                    UNITS "degrees C"
                    MAX-ACCESS read-write
                    STATUS current
                    DESCRIPTION "Del.Water T. Summer SetBack mode SetP."
                    ::= { analogObjects 23 }

        -- 1.3.6.1.4.1.9839.2.1.2.24
        t-win-set OBJECT-TYPE
                    SYNTAX Integer32 (-32767..32767)
                    UNITS "degrees C"
                    MAX-ACCESS read-write
                    STATUS current
                    DESCRIPTION "Delivery Water Temp. Winter Set Point"
                    ::= { analogObjects 24 }

        -- 1.3.6.1.4.1.9839.2.1.2.25
        t-win-setback OBJECT-TYPE
                    SYNTAX Integer32 (-32767..32767)
                    UNITS "degrees C"
                    MAX-ACCESS read-write
                    STATUS current
                    DESCRIPTION "Del.Water T. Winter SetBack mode SetP"
                    ::= { analogObjects 25 }

        -- 1.3.6.1.4.1.9839.2.1.2.26
        in-hi-temp-summ OBJECT-TYPE
                    SYNTAX Integer32 (-32767..32767)
                    UNITS "degrees C"
                    MAX-ACCESS read-write
                    STATUS current
                    DESCRIPTION "CW inlet High Temp.Summer Alarm Threshold"
                    ::= { analogObjects 26 }

        -- 1.3.6.1.4.1.9839.2.1.2.27
        in-low-temp-summ OBJECT-TYPE
                    SYNTAX Integer32 (-32767..32767)
                    UNITS "degrees C"
                    MAX-ACCESS read-write
                    STATUS current
                    DESCRIPTION "CW inlet Low Temp.Summer Alarm Threshold"
                    ::= { analogObjects 27 }

        -- 1.3.6.1.4.1.9839.2.1.2.28
        in-hi-temp-win OBJECT-TYPE
                    SYNTAX Integer32 (-32767..32767)
                    UNITS "degrees C"
                    MAX-ACCESS read-write
                    STATUS current
                    DESCRIPTION "CW inlet High Temp. Alarm Winter Threshold"
                    ::= { analogObjects 28 }

        -- 1.3.6.1.4.1.9839.2.1.2.29
        in-low-temp-win OBJECT-TYPE
                    SYNTAX Integer32 (-32767..32767)
                    UNITS "degrees C"
                    MAX-ACCESS read-write
                    STATUS current
                    DESCRIPTION "CW inlet Low Temp. Alarm Winter Threshold"
                    ::= { analogObjects 29}

        -- 1.3.6.1.4.1.9839.2.1.2.30
        tsum-ext-p1-setp OBJECT-TYPE
                    SYNTAX Integer32 (-32767..32767)
                    UNITS "degrees C"
                    MAX-ACCESS read-write
                    STATUS current
                    DESCRIPTION "Summer T.ext Compens.: P1 T.ext SetP."
                    ::= { analogObjects 30}

        -- 1.3.6.1.4.1.9839.2.1.2.31
        tsum-wout-p2-setp OBJECT-TYPE
                    SYNTAX Integer32 (-32767..32767)
                    UNITS "degrees C"
                    MAX-ACCESS read-write
                    STATUS current
                    DESCRIPTION "Summer T.ext Compens.: P2 T.wout SetP."
                    ::= { analogObjects 31}

        -- 1.3.6.1.4.1.9839.2.1.2.32
        tsum-ext-p2-setp OBJECT-TYPE
                    SYNTAX Integer32 (-32767..32767)
                    UNITS "degrees C"
                    MAX-ACCESS read-write
                    STATUS current
                    DESCRIPTION "Summer T.ext Compens.: P2 T.ext SetP."
                    ::= { analogObjects 32}


        -- 1.3.6.1.4.1.9839.2.1.2.33
        twin-ext-p1-setp OBJECT-TYPE
                    SYNTAX Integer32 (-32767..32767)
                    UNITS "degrees C"
                    MAX-ACCESS read-write
                    STATUS current
                    DESCRIPTION "Winter T.ext Compens.: P1 T.ext SetP."
                    ::= { analogObjects 33 }

        -- 1.3.6.1.4.1.9839.2.1.2.34
        twin-wout-p2-setp OBJECT-TYPE
                    SYNTAX Integer32 (-32767..32767)
                    UNITS "degrees C"
                    MAX-ACCESS read-write
                    STATUS current
                    DESCRIPTION "Winter T.ext Compens.: P2 T.wout SetP."
                    ::= { analogObjects 34 }

        -- 1.3.6.1.4.1.9839.2.1.2.35
        twin-ext-p2-setp OBJECT-TYPE
                    SYNTAX Integer32 (-32767..32767)
                    UNITS "degrees C"
                    MAX-ACCESS read-write
                    STATUS current
                    DESCRIPTION "Winter T.ext Compens.: P2 T.ext SetP."
                    ::= { analogObjects 35 }

        -- 1.3.6.1.4.1.9839.2.1.2.36
        freec-act-setp OBJECT-TYPE
                    SYNTAX Integer32 (-32767..32767)
                    UNITS "degrees C"
                    MAX-ACCESS read-write
                    STATUS current
                    DESCRIPTION "Free-Cooling Activation Set Point"
                    ::= { analogObjects 36 }

        -- 1.3.6.1.4.1.9839.2.1.2.37
        circ1-sup OBJECT-TYPE
                    SYNTAX Integer32 (-32767..32767)
                    UNITS "degrees C"
                    MAX-ACCESS read-only
                    STATUS current
                    DESCRIPTION "Circuit 1 Superheating"
                    ::= { analogObjects 37 }

        -- 1.3.6.1.4.1.9839.2.1.2.38
        circ2-sup OBJECT-TYPE
                    SYNTAX Integer32 (-32767..32767)
                    UNITS "degrees C"
                    MAX-ACCESS read-only
                    STATUS current
                    DESCRIPTION "Circuit 2 Superheating"
                    ::= { analogObjects 38 }

        -- 1.3.6.1.4.1.9839.2.1.2.39
        circ1-suc-p OBJECT-TYPE
                    SYNTAX Integer32 (-32767..32767)
                    UNITS "degrees C"
                    MAX-ACCESS read-only
                    STATUS current
                    DESCRIPTION "Circuit 1 Suction Pressure"
                    ::= { analogObjects 39 }

        -- 1.3.6.1.4.1.9839.2.1.2.40
        circ2-suc-p OBJECT-TYPE
                    SYNTAX Integer32 (-32767..32767)
                    UNITS "degrees C"
                    MAX-ACCESS read-only
                    STATUS current
                    DESCRIPTION "Circuit 2 Suction Pressure"
                    ::= { analogObjects 40 }

        -- 1.3.6.1.4.1.9839.2.1.2.41
        circ1-suc-t OBJECT-TYPE
                    SYNTAX Integer32 (-32767..32767)
                    UNITS "degrees C"
                    MAX-ACCESS read-only
                    STATUS current
                    DESCRIPTION "Circuit 1 Suction Temperature"
                    ::= { analogObjects 41 }

        -- 1.3.6.1.4.1.9839.2.1.2.42
        circ2-suc-t OBJECT-TYPE
                    SYNTAX Integer32 (-32767..32767)
                    UNITS "degrees C"
                    MAX-ACCESS read-only
                    STATUS current
                    DESCRIPTION "Circuit 2 Suction Temperature"
                    ::= { analogObjects 42 }

        -- 1.3.6.1.4.1.9839.2.1.2.43
        circ1-liq-temp OBJECT-TYPE
                    SYNTAX Integer32 (-32767..32767)
                    UNITS "degrees C"
                    MAX-ACCESS read-only
                    STATUS current
                    DESCRIPTION "Circuit 1 Liquid Temperature"
                    ::= { analogObjects 43 }

        -- 1.3.6.1.4.1.9839.2.1.2.44
        circ2-liq-temp OBJECT-TYPE
                    SYNTAX Integer32 (-32767..32767)
                    UNITS "degrees C"
                    MAX-ACCESS read-only
                    STATUS current
                    DESCRIPTION "Circuit 2 Liquid Temperature"
                    ::= { analogObjects 44 }

        -- 1.3.6.1.4.1.9839.2.1.2.45
        pump-inv-req OBJECT-TYPE
                    SYNTAX Integer32 (-32767..32767)
                    UNITS "%"
                    MAX-ACCESS read-write
                    STATUS current
                    DESCRIPTION "Pump inverter request (Optional)"
                    ::= { analogObjects 45 }


        -- 1.3.6.1.4.1.9839.2.1.2.46
        pump-perc-work OBJECT-TYPE
                    SYNTAX Integer32 (-32767..32767)
                    UNITS "%"
                    MAX-ACCESS read-only
                    STATUS current
                    DESCRIPTION "Pump % Working (Optional with inverter)"
                    ::= { analogObjects 46 }


        -- 1.3.6.1.4.1.9839.2.1.2.47
        exv-sup-setP OBJECT-TYPE
                    SYNTAX Integer32 (-32767..32767)
                    UNITS "degrees C"
                    MAX-ACCESS read-only
                    STATUS current
                    DESCRIPTION "EXV PID Superheat SetPoint"
                    ::= { analogObjects 47 }

        -- 1.3.6.1.4.1.9839.2.1.2.48
        exv-sup-prop OBJECT-TYPE
                    SYNTAX Integer32 (-32767..32767)
                    UNITS "N/A"
                    MAX-ACCESS read-only
                    STATUS current
                    DESCRIPTION "EXV PID Superheat Proportional Gain"
                    ::= { analogObjects 48 }

        -- 1.3.6.1.4.1.9839.2.1.2.49
        exv-sup-deriv OBJECT-TYPE
                    SYNTAX Integer32 (-32767..32767)
                    UNITS "sec"
                    MAX-ACCESS read-only
                    STATUS current
                    DESCRIPTION "EXV PID Superheat Derivative time"
                    ::= { analogObjects 49 }


        -- 1.3.6.1.4.1.9839.2.1.2.50
        exv-sup-dead OBJECT-TYPE
                    SYNTAX Integer32 (-32767..32767)
                    UNITS "degrees C"
                    MAX-ACCESS read-only
                    STATUS current
                    DESCRIPTION "EXV PID Superheat Dead Zone"
                    ::= { analogObjects 50 }


        -- 1.3.6.1.4.1.9839.2.1.2.51
        exv-low-sup OBJECT-TYPE
                    SYNTAX Integer32 (-32767..32767)
                    UNITS "degrees C"
                    MAX-ACCESS read-only
                    STATUS current
                    DESCRIPTION "EXV Low superheat threshold"
                    ::= { analogObjects 51 }

        -- 1.3.6.1.4.1.9839.2.1.2.52
        exv-cost-sup OBJECT-TYPE
                    SYNTAX Integer32 (-32767..32767)
                    UNITS "sec"
                    MAX-ACCESS read-only
                    STATUS current
                    DESCRIPTION "EXV Costant time low superheat"
                    ::= { analogObjects 52 }

        -- 1.3.6.1.4.1.9839.2.1.2.53
        exv-mop-thr OBJECT-TYPE
                    SYNTAX Integer32 (-32767..32767)
                    UNITS "degrees C"
                    MAX-ACCESS read-only
                    STATUS current
                    DESCRIPTION "EXV MOP threshold"
                    ::= { analogObjects 53 }

        -- 1.3.6.1.4.1.9839.2.1.2.54
        exv-lop-thr OBJECT-TYPE
                    SYNTAX Integer32 (-32767..32767)
                    UNITS "degrees C"
                    MAX-ACCESS read-only
                    STATUS current
                    DESCRIPTION "EXV LOP threshold"
                    ::= { analogObjects 54 }

        -- 1.3.6.1.4.1.9839.2.1.2.55
        exv-cost-thr1 OBJECT-TYPE
                    SYNTAX Integer32 (-32767..32767)
                    UNITS "sec"
                    MAX-ACCESS read-only
                    STATUS current
                    DESCRIPTION "EXV Costant time threshold"
                    ::= { analogObjects 55 }

        -- 1.3.6.1.4.1.9839.2.1.2.56
        exv-cost-thr2 OBJECT-TYPE
                    SYNTAX Integer32 (-32767..32767)
                    UNITS "sec"
                    MAX-ACCESS read-only
                    STATUS current
                    DESCRIPTION "EXV Costant time threshold 2"
                    ::= { analogObjects 56 }

        -- 1.3.6.1.4.1.9839.2.1.2.58
        fans-st-condon OBJECT-TYPE
                    SYNTAX Integer32 (-32767..32767)
                    UNITS "degrees C"
                    MAX-ACCESS read-only
                    STATUS current
                    DESCRIPTION "Fans speed Temperature cond. ON"
                    ::= { analogObjects 58 }

        -- 1.3.6.1.4.1.9839.2.1.2.59
        fans-st-condoff OBJECT-TYPE
                    SYNTAX Integer32 (-32767..32767)
                    UNITS "degrees C"
                    MAX-ACCESS read-only
                    STATUS current
                    DESCRIPTION "Fans speed Temperature cond. OFF"
                    ::= { analogObjects 59 }

        -- 1.3.6.1.4.1.9839.2.1.2.60
        fans-st-condbeg OBJECT-TYPE
                    SYNTAX Integer32 (-32767..32767)
                    UNITS "degrees C"
                    MAX-ACCESS read-only
                    STATUS current
                    DESCRIPTION "Fans speed Temperature cond. Begin"
                    ::= { analogObjects 60 }

        -- 1.3.6.1.4.1.9839.2.1.2.61
        fans-st-condend OBJECT-TYPE
                    SYNTAX Integer32 (-32767..32767)
                    UNITS "degrees C"
                    MAX-ACCESS read-only
                    STATUS current
                    DESCRIPTION "Fans speed Temperature cond. End"
                    ::= { analogObjects 61 }

        -- 1.3.6.1.4.1.9839.2.1.2.62
        fans-st-condbeg2 OBJECT-TYPE
                    SYNTAX Integer32 (-32767..32767)
                    UNITS "degrees C"
                    MAX-ACCESS read-only
                    STATUS current
                    DESCRIPTION "Fans speed Temperature cond. Begin 2 (Optional)"
                    ::= { analogObjects 62 }

        -- 1.3.6.1.4.1.9839.2.1.2.63
        fans-st-condend2 OBJECT-TYPE
                    SYNTAX Integer32 (-32767..32767)
                    UNITS "degrees C"
                    MAX-ACCESS read-only
                    STATUS current
                    DESCRIPTION "Fans speed Temperature cond. End 2 (Optional)"
                    ::= { analogObjects 63 }

        -- 1.3.6.1.4.1.9839.2.1.3
        integerObjects OBJECT IDENTIFIER ::= { bre-MIB 3 }

        -- 1.3.6.1.4.1.9839.2.1.3.1
        ore-compr1 OBJECT-TYPE
                    SYNTAX Integer32 (-32767..32767)
                    UNITS "h"
                    MAX-ACCESS read-only
                    STATUS current
                    DESCRIPTION "Compressor 1 hour counter"
                    ::= { integerObjects 1 }

        -- 1.3.6.1.4.1.9839.2.1.3.2
        ore-compr2 OBJECT-TYPE
                    SYNTAX Integer32 (-32767..32767)
                    UNITS "h"
                    MAX-ACCESS read-only
                    STATUS current
                    DESCRIPTION "Compressor 2 hour counter"
                    ::= { integerObjects 2 }

        -- 1.3.6.1.4.1.9839.2.1.3.3
        circ-pump1-hc OBJECT-TYPE
                    SYNTAX Integer32 (-32767..32767)
                    UNITS "h"
                    MAX-ACCESS read-only
                    STATUS current
                    DESCRIPTION "Circulating Pump 1 hour counter"
                    ::= { integerObjects 3 }

        -- 1.3.6.1.4.1.9839.2.1.3.4
        circ-pump2-hc OBJECT-TYPE
                    SYNTAX Integer32 (-32767..32767)
                    UNITS "h"
                    MAX-ACCESS read-only
                    STATUS current
                    DESCRIPTION "Circulating Pump 2 hour counter"
                    ::= { integerObjects 4 }

        -- 1.3.6.1.4.1.9839.2.1.3.5
        fc-pump-hc OBJECT-TYPE
                    SYNTAX Integer32 (-32767..32767)
                    UNITS "h"
                    MAX-ACCESS read-only
                    STATUS current
                    DESCRIPTION "Free-cooling Pump hour counter"
                    ::= { integerObjects 5 }

        -- 1.3.6.1.4.1.9839.2.1.3.6
        comp1-sc OBJECT-TYPE
                    SYNTAX Integer32 (-32767..32767)
                    UNITS "h"
                    MAX-ACCESS read-only
                    STATUS current
                    DESCRIPTION "Compressor 1 Starting counter"
                    ::= { integerObjects 6 }

        -- 1.3.6.1.4.1.9839.2.1.3.7
        comp1-sc-X10000 OBJECT-TYPE
                    SYNTAX Integer32 (-32767..32767)
                    UNITS "h"
                    MAX-ACCESS read-only
                    STATUS current
                    DESCRIPTION "Compressor 1 Starting counter x10.000"
                    ::= { integerObjects 7 }

        -- 1.3.6.1.4.1.9839.2.1.3.8
        comp2-sc OBJECT-TYPE
                    SYNTAX Integer32 (-32767..32767)
                    UNITS "n"
                    MAX-ACCESS read-only
                    STATUS current
                    DESCRIPTION "Compressor 2 Starting counter"
                    ::= { integerObjects 8 }

        -- 1.3.6.1.4.1.9839.2.1.3.9
        comp2-sc-X10000 OBJECT-TYPE
                    SYNTAX Integer32 (-32767..32767)
                    UNITS "nx10000"
                    MAX-ACCESS read-only
                    STATUS current
                    DESCRIPTION "Compressor 2 Starting counter x10.000"
                    ::= { integerObjects 9 }

        -- 1.3.6.1.4.1.9839.2.1.3.10
        circ1-dc OBJECT-TYPE
                    SYNTAX Integer32 (-32767..32767)
                    UNITS "n"
                    MAX-ACCESS read-only
                    STATUS current
                    DESCRIPTION "Circuit 1 Defrost counter"
                    ::= { integerObjects 10 }

        -- 1.3.6.1.4.1.9839.2.1.3.11
        circ1-dc-X10-4  OBJECT-TYPE
                    SYNTAX Integer32 (-32767..32767)
                    UNITS "nx10000"
                    MAX-ACCESS read-only
                    STATUS current
                    DESCRIPTION "Circuit 1 Defrost counter x10.000"
                    ::= { integerObjects 11 }

        -- 1.3.6.1.4.1.9839.2.1.3.12
        circ2-dc OBJECT-TYPE
                    SYNTAX Integer32 (-32767..32767)
                    UNITS "n"
                    MAX-ACCESS read-only
                    STATUS current
                    DESCRIPTION "Circuit 2 Defrost counter"
                    ::= { integerObjects 12 }

        -- 1.3.6.1.4.1.9839.2.1.3.13
        circ2-dc-X10-4 OBJECT-TYPE
                    SYNTAX Integer32 (-32767..32767)
                    UNITS "nx10000"
                    MAX-ACCESS read-only
                    STATUS current
                    DESCRIPTION "Circuit 2 Defrost counter x10.000"
                    ::= { integerObjects 13 }

        -- 1.3.6.1.4.1.9839.2.1.3.14
        both-circ-dc OBJECT-TYPE
                    SYNTAX Integer32 (-32767..32767)
                    UNITS "n"
                    MAX-ACCESS read-only
                    STATUS current
                    DESCRIPTION "Both Circuit Defrost counter"
                    ::= { integerObjects 14 }

        -- 1.3.6.1.4.1.9839.2.1.3.15
        both-circ-dc-X10000 OBJECT-TYPE
                    SYNTAX Integer32 (-32767..32767)
                    UNITS "nx10000"
                    MAX-ACCESS read-only
                    STATUS current
                    DESCRIPTION "Both Circuit Defrost counter x10.000"
                    ::= { integerObjects 15 }

        -- 1.3.6.1.4.1.9839.2.1.3.16
        nperf-dc OBJECT-TYPE
                    SYNTAX Integer32 (-32767..32767)
                    UNITS "n"
                    MAX-ACCESS read-only
                    STATUS current
                    DESCRIPTION "Non Performing Defrost counter"
                    ::= { integerObjects 16 }

        -- 1.3.6.1.4.1.9839.2.1.3.17
        nperf-dc-X10000 OBJECT-TYPE
                    SYNTAX Integer32 (-32767..32767)
                    UNITS "nx10000"
                    MAX-ACCESS read-only
                    STATUS current
                    DESCRIPTION "Non Performing Defrost counter x10.000"
                    ::= { integerObjects 17 }

        -- 1.3.6.1.4.1.9839.2.1.3.18
        unit-type OBJECT-TYPE
                    SYNTAX Integer32 (-32767..32767)
                    UNITS "n"
                    MAX-ACCESS read-only
                    STATUS current
                    DESCRIPTION "Unit Type (0= STD Chiller, 1=Low Temp.
                    Ch., 2=Ch.+Heat Rec.; 3=Heat Pump,
                    4=HP+Heat Rec. 5=Ch.+Energy Saving)"
                    ::= { integerObjects 18 }

        -- 1.3.6.1.4.1.9839.2.1.3.19
        pump-config-circ OBJECT-TYPE
                    SYNTAX Integer32 (-32767..32767)
                    UNITS "n"
                    MAX-ACCESS read-only
                    STATUS current
                    DESCRIPTION "Circulating Pump Config. (0,1 or 2 Pumps)"
                    ::= { integerObjects 19 }

        -- 1.3.6.1.4.1.9839.2.1.3.20
        conn-lan OBJECT-TYPE
                    SYNTAX Integer32 (-32767..32767)
                    UNITS "n"
                    MAX-ACCESS read-only
                    STATUS current
                    DESCRIPTION "Total of units connected in LAN"
                    ::= { integerObjects 20 }

        -- 1.3.6.1.4.1.9839.2.1.3.21
        comp1-status OBJECT-TYPE
                    SYNTAX Integer32 (-32767..32767)
                    UNITS "n"
                    MAX-ACCESS read-only
                    STATUS current
                    DESCRIPTION "Comp.1 Status (0=Off,1=On,2=AL,3=Pump.Down)"
                    ::= { integerObjects 21 }

        -- 1.3.6.1.4.1.9839.2.1.3.22
        comp2-status OBJECT-TYPE
                    SYNTAX Integer32 (-32767..32767)
                    UNITS "n"
                    MAX-ACCESS read-only
                    STATUS current
                    DESCRIPTION "Comp.2 Status"
                    ::= { integerObjects 22 }

        -- 1.3.6.1.4.1.9839.2.1.3.23
        comp1-step-status OBJECT-TYPE
                    SYNTAX Integer32 (-32767..32767)
                    UNITS "n"
                    MAX-ACCESS read-only
                    STATUS current
                    DESCRIPTION "Comp.1 Step Status"
                    ::= { integerObjects 23 }

        -- 1.3.6.1.4.1.9839.2.1.3.24
        comp2-step-status OBJECT-TYPE
                    SYNTAX Integer32 (-32767..32767)
                    UNITS "n"
                    MAX-ACCESS read-only
                    STATUS current
                    DESCRIPTION "Comp.2 Step Status"
                    ::= { integerObjects 24 }

        -- 1.3.6.1.4.1.9839.2.1.3.25
        pump1-status OBJECT-TYPE
                    SYNTAX Integer32 (-32767..32767)
                    UNITS "n"
                    MAX-ACCESS read-only
                    STATUS current
                    DESCRIPTION "Pump 1 Status"
                    ::= { integerObjects 25 }

        -- 1.3.6.1.4.1.9839.2.1.3.26
        pump2-status OBJECT-TYPE
                    SYNTAX Integer32 (-32767..32767)
                    UNITS "n"
                    MAX-ACCESS read-only
                    STATUS current
                    DESCRIPTION "Pump 2 Status"
                    ::= { integerObjects 26 }

        -- 1.3.6.1.4.1.9839.2.1.3.27
        fcpump-status OBJECT-TYPE
                    SYNTAX Integer32 (-32767..32767)
                    UNITS "n"
                    MAX-ACCESS read-only
                    STATUS current
                    DESCRIPTION "FC Pump Status"
                    ::= { integerObjects 27 }

        -- 1.3.6.1.4.1.9839.2.1.3.28
        act-setP OBJECT-TYPE
                    SYNTAX Integer32 (-32767..32767)
                    UNITS "n"
                    MAX-ACCESS read-only
                    STATUS current
                    DESCRIPTION "Actual set Point mode (0=std,1= T.ext
Compens., 2=OPT SetP., 3=Setback SetP.,
4=Remote Offsets"
                    ::= { integerObjects 28 }

        -- 1.3.6.1.4.1.9839.2.1.3.31
        last-defrost-length OBJECT-TYPE
                    SYNTAX Integer32 (-32767..32767)
                    UNITS "s"
                    MAX-ACCESS read-write
                    STATUS current
                    DESCRIPTION "Last Defrost Length"
                    ::= { integerObjects 31 }


        -- 1.3.6.1.4.1.9839.2.1.3.32
        rest-delay OBJECT-TYPE
                    SYNTAX Integer32 (-32767..32767)
                    UNITS "s"
                    MAX-ACCESS read-write
                    STATUS current
                    DESCRIPTION "Restart Delay"
                    ::= { integerObjects 32 }

        -- 1.3.6.1.4.1.9839.2.1.3.33
        reg-st-trans OBJECT-TYPE
                    SYNTAX Integer32 (-32767..32767)
                    UNITS "s"
                    MAX-ACCESS read-write
                    STATUS current
                    DESCRIPTION "Regulation Start Transitory"
                    ::= { integerObjects 33 }

        -- 1.3.6.1.4.1.9839.2.1.3.34
        lp-delay OBJECT-TYPE
                    SYNTAX Integer32 (-32767..32767)
                    UNITS "s"
                    MAX-ACCESS read-write
                    STATUS current
                    DESCRIPTION "Low Pressure Delay"
                    ::= { integerObjects 34 }


        -- 1.3.6.1.4.1.9839.2.1.3.35
        alarm-wat-hl-t OBJECT-TYPE
                    SYNTAX Integer32 (-32767..32767)
                    UNITS "min"
                    MAX-ACCESS read-write
                    STATUS current
                    DESCRIPTION "Water High/Low Temp. Alarm Delay"
                    ::= { integerObjects 35 }


        -- 1.3.6.1.4.1.9839.2.1.3.36
       exc-time OBJECT-TYPE
                    SYNTAX Integer32 (-32767..32767)
                    UNITS "s"
                    MAX-ACCESS read-write
                    STATUS current
                    DESCRIPTION "Excursion time"
                    ::= { integerObjects 36 }

        -- 1.3.6.1.4.1.9839.2.1.3.37
        st-by-switch OBJECT-TYPE
                    SYNTAX Integer32 (-32767..32767)
                    UNITS "h"
                    MAX-ACCESS read-write
                    STATUS current
                    DESCRIPTION "Stand-by Unit Switch-over time"
                    ::= { integerObjects 37 }

        -- 1.3.6.1.4.1.9839.2.1.3.38
        run-st-bypump OBJECT-TYPE
                    SYNTAX Integer32 (-32767..32767)
                    UNITS "h"
                    MAX-ACCESS read-write
                    STATUS current
                    DESCRIPTION "Run-Stand-by pump switch-over time"
                    ::= { integerObjects 38 }

        -- 1.3.6.1.4.1.9839.2.1.3.39
        set-mode-cyc-st OBJECT-TYPE
                    SYNTAX Integer32 (-32767..32767)
                    UNITS "min"
                    MAX-ACCESS read-write
                    STATUS current
                    DESCRIPTION "Setback Mode Cyclical start"
                    ::= { integerObjects 39 }

        -- 1.3.6.1.4.1.9839.2.1.3.40
        comp1-work-ht OBJECT-TYPE
                    SYNTAX Integer32 (-32767..32767)
                    UNITS "h*100"
                    MAX-ACCESS read-write
                    STATUS current
                    DESCRIPTION "Compr.1 working hours threshold"
                    ::= { integerObjects 40 }

        -- 1.3.6.1.4.1.9839.2.1.3.41
        comp2-work-ht OBJECT-TYPE
                    SYNTAX Integer32 (-32767..32767)
                    UNITS "h*100"
                    MAX-ACCESS read-write
                    STATUS current
                    DESCRIPTION "Compr.2 working hours threshold"
                    ::= { integerObjects 41 }

        -- 1.3.6.1.4.1.9839.2.1.3.42
        pump1-work-ht OBJECT-TYPE
                    SYNTAX Integer32 (-32767..32767)
                    UNITS "h*100"
                    MAX-ACCESS read-write
                    STATUS current
                    DESCRIPTION "Pump 1 working hours threshold"
                    ::= { integerObjects 42 }

        -- 1.3.6.1.4.1.9839.2.1.3.43
        pump2-work-ht OBJECT-TYPE
                    SYNTAX Integer32 (-32767..32767)
                    UNITS "h*100"
                    MAX-ACCESS read-write
                    STATUS current
                    DESCRIPTION "Pump 2 working hours threshold"
                    ::= { integerObjects 43 }

        -- 1.3.6.1.4.1.9839.2.1.3.44
        fcpump-work-ht OBJECT-TYPE
                    SYNTAX Integer32 (-32767..32767)
                    UNITS "h*100"
                    MAX-ACCESS read-write
                    STATUS current
                    DESCRIPTION "FC Pump working hours threshold"
                    ::= { integerObjects 44 }


        -- 1.3.6.1.4.1.9839.2.1.3.47
        comp1-curr-abs OBJECT-TYPE
                    SYNTAX Integer32 (-32767..32767)
                    UNITS "A"
                    MAX-ACCESS read-only
                    STATUS current
                    DESCRIPTION "Compressor 1 Current Absorbed"
                    ::= { integerObjects 47 }

        -- 1.3.6.1.4.1.9839.2.1.3.48
        comp2-curr-abs OBJECT-TYPE
                    SYNTAX Integer32 (-32767..32767)
                    UNITS "A"
                    MAX-ACCESS read-only
                    STATUS current
                    DESCRIPTION "Compressor 2 Current Absorbed"
                    ::= { integerObjects 48 }

        -- 1.3.6.1.4.1.9839.2.1.3.79
        circ1-exv OBJECT-TYPE
                    SYNTAX Integer32 (-32767..32767)
                    UNITS "step"
                    MAX-ACCESS read-only
                    STATUS current
                    DESCRIPTION "Circuit 1 EXV Position"
                    ::= { integerObjects 79 }

        -- 1.3.6.1.4.1.9839.2.1.3.80
        circ2-exv OBJECT-TYPE
                    SYNTAX Integer32 (-32767..32767)
                    UNITS "step"
                    MAX-ACCESS read-only
                    STATUS current
                    DESCRIPTION "Circuit 2 EXV Position"
                    ::= { integerObjects 80 }

        -- 1.3.6.1.4.1.9839.2.1.3.81
        hour OBJECT-TYPE
                    SYNTAX Integer32 (-32767..32767)
                    UNITS "h"
                    MAX-ACCESS read-only
                    STATUS current
                    DESCRIPTION "Hour"
                    ::= { integerObjects 81 }

        -- 1.3.6.1.4.1.9839.2.1.3.82
        min OBJECT-TYPE
                    SYNTAX Integer32 (-32767..32767)
                    UNITS "Min"
                    MAX-ACCESS read-only
                    STATUS current
                    DESCRIPTION "Minute"
                    ::= { integerObjects 82 }

        -- 1.3.6.1.4.1.9839.2.1.3.83
        day OBJECT-TYPE
                    SYNTAX Integer32 (-32767..32767)
                    UNITS "D"
                    MAX-ACCESS read-only
                    STATUS current
                    DESCRIPTION "Day"
                    ::= { integerObjects 83 }

        -- 1.3.6.1.4.1.9839.2.1.3.84
        month OBJECT-TYPE
                    SYNTAX Integer32 (-32767..32767)
                    UNITS "M"
                    MAX-ACCESS read-only
                    STATUS current
                    DESCRIPTION "Month"
                    ::= { integerObjects 84 }

        -- 1.3.6.1.4.1.9839.2.1.3.85
        year OBJECT-TYPE
                    SYNTAX Integer32 (-32767..32767)
                    UNITS "Y"
                    MAX-ACCESS read-only
                    STATUS current
                    DESCRIPTION "Year"
                    ::= { integerObjects 85 }

      -- 1.3.6.1.4.1.9839.2.1.3.86
        bios-release OBJECT-TYPE
                    SYNTAX Integer32 (-32767..32767)
                    UNITS "N/A"
                    MAX-ACCESS read-only
                    STATUS current
                    DESCRIPTION "Bios release"
                    ::= { integerObjects 86 }

      -- 1.3.6.1.4.1.9839.2.1.3.87
        boot-release OBJECT-TYPE
                    SYNTAX Integer32 (-32767..32767)
                    UNITS "N/A"
                    MAX-ACCESS read-only
                    STATUS current
                    DESCRIPTION "Boot release"
                    ::= { integerObjects 87 }

      -- 1.3.6.1.4.1.9839.2.1.3.88
        sw-release OBJECT-TYPE
                    SYNTAX Integer32 (-32767..32767)
                    UNITS "N/A"
                    MAX-ACCESS read-only
                    STATUS current
                    DESCRIPTION "Software release"
                    ::= { integerObjects 88 }

      -- 1.3.6.1.4.1.9839.2.1.3.89
        head-press-setPoint OBJECT-TYPE
                    SYNTAX Integer32 (-32767..32767)
                    UNITS "N/A"
                    MAX-ACCESS read-only
                    STATUS current
                    DESCRIPTION "Head pressure setPoint"
                    ::= { integerObjects 89 }
	
	END

--
-- CAREL-bre.MIB
--
