-- 892 MIB file

DSE-892 DEFINITIONS ::= BEGIN

IMPORTS
    OBJECT-TYPE, NOTIFICATION-TYPE, MODULE-IDENTITY,
    Integer32, Unsigned32, Opaque, enterprises, Counter32
        FROM SNMPv2-SMI
	DisplayString
		FROM SNMPv2-TC
    TRAP-TYPE
        FROM RFC-1215;

dseVendor MODULE-IDENTITY
    LAST-UPDATED "201501291131Z"
    ORGANIZATION "DSE Development"
    CONTACT-INFO ""
    DESCRIPTION  ""
    REVISION     "201501291131Z"
    DESCRIPTION  "First draft"
	::= { enterprises 41385 }		
		
		
		
		
--Product
dseProduct                OBJECT IDENTIFIER ::= { dseVendor 1 }

--Event Section
dseEventSection           OBJECT IDENTIFIER ::= { dseProduct 1 }

--Instrumentation Section
dseInstrumentsSection           OBJECT IDENTIFIER ::= { dseProduct 3 }



--Events
eventEntry OBJECT-TYPE
    SYNTAX  SEQUENCE OF EventEntry
    MAX-ACCESS  not-accessible
    STATUS  current
    DESCRIPTION
     ""
    ::= { dseEventSection  1 }

dseEventEntry OBJECT-TYPE
    SYNTAX  EventEntry
    MAX-ACCESS  not-accessible
    STATUS  current
    DESCRIPTION
     ""
    INDEX { eventType }
    ::= { eventEntry  1 }

EventEntry ::= SEQUENCE {
  eventType          INTEGER,
  eventSubtype       INTEGER,
  eventParameters    INTEGER, 
  eventTimestamp     INTEGER,
  eventHoursRun      INTEGER,
  eventDescription   DisplayString,
  moduleID           INTEGER,
  moduleDescription  DisplayString
  }

eventType OBJECT-TYPE
  SYNTAX  INTEGER (1..2147483647)
  MAX-ACCESS  read-only
  STATUS  current
  DESCRIPTION "The Event Type"
  ::= { dseEventEntry 1 }

eventSubtype OBJECT-TYPE
  SYNTAX  INTEGER
  MAX-ACCESS  read-only
  STATUS  current
  DESCRIPTION "The Event Subtype"
  ::= { dseEventEntry 2 }

eventParameters OBJECT-TYPE
  SYNTAX  INTEGER
  MAX-ACCESS  read-only
  STATUS  current
  DESCRIPTION "Parameters of the event"
  ::= { dseEventEntry 3 }

eventTimestamp OBJECT-TYPE
  SYNTAX  INTEGER
  MAX-ACCESS  read-only
  STATUS  current
  DESCRIPTION "Timestamp in UNIX time"
  ::= { dseEventEntry 4 }

eventHoursRun OBJECT-TYPE
  SYNTAX  INTEGER
  MAX-ACCESS  read-only
  STATUS  current
  DESCRIPTION "Hours run in seconds"
  ::= { dseEventEntry 5 }

eventDescription OBJECT-TYPE
  SYNTAX  DisplayString
  MAX-ACCESS  read-only
  STATUS  current
  DESCRIPTION "Brief description of the event"
  ::= { dseEventEntry 6 }

moduleID OBJECT-TYPE
  SYNTAX  INTEGER
  MAX-ACCESS  read-only
  STATUS  current
  DESCRIPTION "Index of the module that caused the trap"
  ::= { dseEventEntry 7 }

moduleDescription OBJECT-TYPE
  SYNTAX  DisplayString
  MAX-ACCESS  read-only
  STATUS  current
  DESCRIPTION "Description of the module that caused the trap"
  ::= { dseEventEntry 8 }


--TRAPS
dseTraps OBJECT IDENTIFIER ::= { dseEventSection  2 }

dseEventTrap  NOTIFICATION-TYPE
  OBJECTS   { eventType,       eventSubtype, 
                eventParameters, eventTimestamp,
                eventHoursRun,   eventDescription,
                moduleID,        moduleDescription }
  STATUS current
  DESCRIPTION "Variables of the dseEventTrap"
  ::= { dseTraps 1 }


--Instruments
instrumentTable OBJECT-TYPE
    SYNTAX  SEQUENCE OF DseInstrumentEntry
    MAX-ACCESS  not-accessible
    STATUS  current
    DESCRIPTION
     ""
    ::= { dseInstrumentsSection 1 }

dseInstrumentEntry OBJECT-TYPE
    SYNTAX  DseInstrumentEntry
    MAX-ACCESS  not-accessible
    STATUS  current
    DESCRIPTION
     ""
    INDEX { gencomTask }
    ::= { instrumentTable  1 }

DseInstrumentEntry ::= SEQUENCE {
  gencomTask          INTEGER,
  oilPressure         Unsigned32,
  coolantTemp         Integer32, 
  fuelLevel           Unsigned32,
  batteryVolts        Unsigned32,
  engineSpeed         Unsigned32,
  genL1Volts          Unsigned32,
  genL2Volts          Unsigned32,
  genL3Volts          Unsigned32,
  genL1Current        Unsigned32,
  genL2Current        Unsigned32,
  genL3Current        Unsigned32,
  genL1Watts          Integer32,
  genL2Watts          Integer32,
  genL3Watts          Integer32,
  
  oilTemp             Integer32,
  altVolts            Unsigned32,
  genFreq             Unsigned32,
  genL1L2Volts        Unsigned32,
  genL2L3Volts        Unsigned32,
  genL3L1Volts        Unsigned32,
  genECurrent         Unsigned32,
  mainsFreq           Unsigned32,
  mainsL1Volts        Unsigned32,
  mainsL2Volts        Unsigned32,
  mainsL3Volts        Unsigned32,
  mainsL1L2Volts      Unsigned32,
  mainsL2L3Volts      Unsigned32,
  mainsL3L1Volts      Unsigned32,
  mainsL1Current      Unsigned32,
  mainsL2Current      Unsigned32,
  mainsL3Current      Unsigned32,
  mainsECurrent       Unsigned32,
  mainsL1Watts        Integer32,
  mainsL2Watts        Integer32,
  mainsL3Watts        Integer32,
  busFreq             Unsigned32,
  busL1Volts          Unsigned32,
  busL2Volts          Unsigned32,
  busL3Volts          Unsigned32,
  busL1L2Volts        Unsigned32,
  busL2L3Volts        Unsigned32,
  busL3L1Volts        Unsigned32,
  busL1Current        Unsigned32,
  busL2Current        Unsigned32,
  busL3Current        Unsigned32,
  busECurrent         Unsigned32,
  busL1Watts          Integer32,
  busL2Watts          Integer32,
  busL3Watts          Integer32,
  canLink             Unsigned32,
  genWattsTotal       Integer32,
  genL1VA             Unsigned32,
  genL2VA             Unsigned32,
  genL3VA             Unsigned32,
  genTotalVA          Unsigned32,
  genL1VAr            Integer32,
  genL2VAr            Integer32,
  genL3VAr            Integer32,
  genTotalVAr         Integer32,
  genPowerFactorL1    Integer32,
  genPowerFactorL2    Integer32,
  genPowerFactorL3    Integer32,
  genAvgPowerFactor   Integer32,
  mainsTotalWatts     Integer32,
  mainsL1VA           Unsigned32,
  mainsL2VA           Unsigned32,
  mainsL3VA           Unsigned32,
  mainsTotalVA        Unsigned32,
  mainsL1VAr          Integer32,
  mainsL2VAr          Integer32,
  mainsL3VAr          Integer32,
  mainsTotalVAr       Integer32,
  mainsPowerFactorL1  Integer32,
  mainsPowerFactorL2  Integer32,
  mainsPowerFactorL3  Integer32,
  mainsAvgPowerFactor Integer32,
  busTotalWatts       Integer32,
  busL1VA             Unsigned32,
  busL2VA             Unsigned32,
  busL3VA             Unsigned32,
  busTotalVA          Unsigned32,
  busL1VAr            Integer32,
  busL2VAr            Integer32,
  busL3VAr            Integer32,
  busTotalVAr         Integer32,
  busPowerFactorL1    Integer32,
  busPowerFactorL2    Integer32,
  busPowerFactorL3    Integer32,
  busAvgPowerFactor   Integer32,
  engHours            Unsigned32,
  genAccKW            Unsigned32,
  genAccKVA           Unsigned32,
  genAccKVAr          Unsigned32,
  startAttempts       Unsigned32,
  mainsAccKW          Unsigned32,
  mainsAccKVA         Unsigned32,
  mainsAccKVAr        Unsigned32,
  busAccKW            Unsigned32,
  busAccKVA           Unsigned32,
  busAccKVAr          Unsigned32
  }
  
gencomTask OBJECT-TYPE
  SYNTAX  INTEGER (1..2147483647)
  MAX-ACCESS  read-only
  STATUS  current
  DESCRIPTION "Gencom Task"
  ::= { dseInstrumentEntry 1 }
  
  
oilPressure OBJECT-TYPE
  SYNTAX  Unsigned32
  MAX-ACCESS  read-only
  STATUS  current
  DESCRIPTION "Oil pressure"
  ::= { dseInstrumentEntry 2 }
  
coolantTemp OBJECT-TYPE
  SYNTAX  Integer32
  MAX-ACCESS  read-only
  STATUS  current
  DESCRIPTION "Coolant temperature"
  ::= { dseInstrumentEntry 3 }
  
fuelLevel OBJECT-TYPE
  SYNTAX  Unsigned32
  MAX-ACCESS  read-only
  STATUS  current
  DESCRIPTION "Fuel Level"
  ::= { dseInstrumentEntry 4 }
  
batteryVolts OBJECT-TYPE
  SYNTAX  Unsigned32
  MAX-ACCESS  read-only
  STATUS  current
  DESCRIPTION "Battery voltage"
  ::= { dseInstrumentEntry 5 }
  
engineSpeed OBJECT-TYPE
  SYNTAX  Unsigned32
  MAX-ACCESS  read-only
  STATUS  current
  DESCRIPTION "Engine speed"
  ::= { dseInstrumentEntry 6 }
  
genL1Volts OBJECT-TYPE
  SYNTAX  Unsigned32
  MAX-ACCESS  read-only
  STATUS  current
  DESCRIPTION "Generator L1-N voltage"
  ::= { dseInstrumentEntry 7 }
  
genL2Volts OBJECT-TYPE
  SYNTAX  Unsigned32
  MAX-ACCESS  read-only
  STATUS  current
  DESCRIPTION "Generator L2-N voltage"
  ::= { dseInstrumentEntry 8 }
  
genL3Volts OBJECT-TYPE
  SYNTAX  Unsigned32
  MAX-ACCESS  read-only
  STATUS  current
  DESCRIPTION "Generator L3-N voltage"
  ::= { dseInstrumentEntry 9 }
  
genL1Current OBJECT-TYPE
  SYNTAX  Unsigned32
  MAX-ACCESS  read-only
  STATUS  current
  DESCRIPTION "Generator L1 current"
  ::= { dseInstrumentEntry 10 }
  
genL2Current OBJECT-TYPE
  SYNTAX  Unsigned32
  MAX-ACCESS  read-only
  STATUS  current
  DESCRIPTION "Generator L2 current"
  ::= { dseInstrumentEntry 11 }
  
genL3Current OBJECT-TYPE
  SYNTAX  Unsigned32
  MAX-ACCESS  read-only
  STATUS  current
  DESCRIPTION "Generator L3 current"
  ::= { dseInstrumentEntry 12 }
  
genL1Watts OBJECT-TYPE
  SYNTAX  Integer32
  MAX-ACCESS  read-only
  STATUS  current
  DESCRIPTION "Generator L1 watts"
  ::= { dseInstrumentEntry 13 }
  
genL2Watts OBJECT-TYPE
  SYNTAX  Integer32
  MAX-ACCESS  read-only
  STATUS  current
  DESCRIPTION "Generator L2 watts"
  ::= { dseInstrumentEntry 14 }
  
genL3Watts OBJECT-TYPE
  SYNTAX  Integer32
  MAX-ACCESS  read-only
  STATUS  current
  DESCRIPTION "Generator L3 watts"
  ::= { dseInstrumentEntry 15 }
  
  
  
  
  
oilTemp OBJECT-TYPE
  SYNTAX  Integer32
  MAX-ACCESS  read-only
  STATUS  current
  DESCRIPTION "Oil temperature"
  ::= { dseInstrumentEntry 16 }
  
altVolts OBJECT-TYPE
  SYNTAX  Unsigned32
  MAX-ACCESS  read-only
  STATUS  current
  DESCRIPTION "Charge alternator voltage"
  ::= { dseInstrumentEntry 17 }
  
genFreq OBJECT-TYPE
  SYNTAX  Unsigned32
  MAX-ACCESS  read-only
  STATUS  current
  DESCRIPTION "Generator frequency"
  ::= { dseInstrumentEntry 18 }
  
genL1L2Volts OBJECT-TYPE
  SYNTAX  Unsigned32
  MAX-ACCESS  read-only
  STATUS  current
  DESCRIPTION "Generator L1-L2 voltage"
  ::= { dseInstrumentEntry 19 }
  
genL2L3Volts OBJECT-TYPE
  SYNTAX  Unsigned32
  MAX-ACCESS  read-only
  STATUS  current
  DESCRIPTION "Generator L2-L3 voltage"
  ::= { dseInstrumentEntry 20 }
  
genL3L1Volts OBJECT-TYPE
  SYNTAX  Unsigned32
  MAX-ACCESS  read-only
  STATUS  current
  DESCRIPTION "Generator L3-L1 voltage"
  ::= { dseInstrumentEntry 21 }
  
genECurrent OBJECT-TYPE
  SYNTAX  Unsigned32
  MAX-ACCESS  read-only
  STATUS  current
  DESCRIPTION "Generator earth current"
  ::= { dseInstrumentEntry 22 }
  
mainsFreq OBJECT-TYPE
  SYNTAX  Unsigned32
  MAX-ACCESS  read-only
  STATUS  current
  DESCRIPTION "Mains frequency"
  ::= { dseInstrumentEntry 23 }
  
mainsL1Volts OBJECT-TYPE
  SYNTAX  Unsigned32
  MAX-ACCESS  read-only
  STATUS  current
  DESCRIPTION "Mains L1-N voltage"
  ::= { dseInstrumentEntry 24 }
  
mainsL2Volts OBJECT-TYPE
  SYNTAX  Unsigned32
  MAX-ACCESS  read-only
  STATUS  current
  DESCRIPTION "Mains L2-N voltage"
  ::= { dseInstrumentEntry 25 }
  
mainsL3Volts OBJECT-TYPE
  SYNTAX  Unsigned32
  MAX-ACCESS  read-only
  STATUS  current
  DESCRIPTION "Mains L3-N voltage"
  ::= { dseInstrumentEntry 26 }
  
mainsL1L2Volts OBJECT-TYPE
  SYNTAX  Unsigned32
  MAX-ACCESS  read-only
  STATUS  current
  DESCRIPTION "Mains L1-L2 voltage"
  ::= { dseInstrumentEntry 27 }
  
mainsL2L3Volts OBJECT-TYPE
  SYNTAX  Unsigned32
  MAX-ACCESS  read-only
  STATUS  current
  DESCRIPTION "Mains L2-L3 voltage"
  ::= { dseInstrumentEntry 28 }
  
mainsL3L1Volts OBJECT-TYPE
  SYNTAX  Unsigned32
  MAX-ACCESS  read-only
  STATUS  current
  DESCRIPTION "Mains L3-L1 voltage"
  ::= { dseInstrumentEntry 29 }
  
mainsL1Current OBJECT-TYPE
  SYNTAX  Unsigned32
  MAX-ACCESS  read-only
  STATUS  current
  DESCRIPTION "Mains L1 Current"
  ::= { dseInstrumentEntry 30 }
  
mainsL2Current OBJECT-TYPE
  SYNTAX  Unsigned32
  MAX-ACCESS  read-only
  STATUS  current
  DESCRIPTION "Mains L2 Current"
  ::= { dseInstrumentEntry 31 }
  
mainsL3Current OBJECT-TYPE
  SYNTAX  Unsigned32
  MAX-ACCESS  read-only
  STATUS  current
  DESCRIPTION "Mains L3 Current"
  ::= { dseInstrumentEntry 32 }
  
mainsECurrent OBJECT-TYPE
  SYNTAX  Unsigned32
  MAX-ACCESS  read-only
  STATUS  current
  DESCRIPTION "Mains earth current"
  ::= { dseInstrumentEntry 33 }
  
mainsL1Watts OBJECT-TYPE
  SYNTAX  Integer32
  MAX-ACCESS  read-only
  STATUS  current
  DESCRIPTION "Mains L1 watts"
  ::= { dseInstrumentEntry 34 }
  
mainsL2Watts OBJECT-TYPE
  SYNTAX  Integer32
  MAX-ACCESS  read-only
  STATUS  current
  DESCRIPTION "Mains L2 watts"
  ::= { dseInstrumentEntry 35 }
  
mainsL3Watts OBJECT-TYPE
  SYNTAX  Integer32
  MAX-ACCESS  read-only
  STATUS  current
  DESCRIPTION "Mains L3 watts"
  ::= { dseInstrumentEntry 36 }
  
busFreq OBJECT-TYPE
  SYNTAX  Unsigned32
  MAX-ACCESS  read-only
  STATUS  current
  DESCRIPTION "Bus frequency"
  ::= { dseInstrumentEntry 37 }
  
busL1Volts OBJECT-TYPE
  SYNTAX  Unsigned32
  MAX-ACCESS  read-only
  STATUS  current
  DESCRIPTION "Bus L1-N voltage"
  ::= { dseInstrumentEntry 38 }
  
busL2Volts OBJECT-TYPE
  SYNTAX  Unsigned32
  MAX-ACCESS  read-only
  STATUS  current
  DESCRIPTION "Bus L2-N voltage"
  ::= { dseInstrumentEntry 39 }
  
busL3Volts OBJECT-TYPE
  SYNTAX  Unsigned32
  MAX-ACCESS  read-only
  STATUS  current
  DESCRIPTION "Bus L3-N voltage"
  ::= { dseInstrumentEntry 40 }
  
busL1L2Volts OBJECT-TYPE
  SYNTAX  Unsigned32
  MAX-ACCESS  read-only
  STATUS  current
  DESCRIPTION "Bus L1-L2 voltage"
  ::= { dseInstrumentEntry 41 }
  
busL2L3Volts OBJECT-TYPE
  SYNTAX  Unsigned32
  MAX-ACCESS  read-only
  STATUS  current
  DESCRIPTION "Bus L2-L3 voltage"
  ::= { dseInstrumentEntry 42 }
  
busL3L1Volts OBJECT-TYPE
  SYNTAX  Unsigned32
  MAX-ACCESS  read-only
  STATUS  current
  DESCRIPTION "Bus L3-L1 voltage"
  ::= { dseInstrumentEntry 43 }
  
busL1Current OBJECT-TYPE
  SYNTAX  Unsigned32
  MAX-ACCESS  read-only
  STATUS  current
  DESCRIPTION "Bus L1 Current"
  ::= { dseInstrumentEntry 44 }
  
busL2Current OBJECT-TYPE
  SYNTAX  Unsigned32
  MAX-ACCESS  read-only
  STATUS  current
  DESCRIPTION "Bus L2 Current"
  ::= { dseInstrumentEntry 45 }
  
busL3Current OBJECT-TYPE
  SYNTAX  Unsigned32
  MAX-ACCESS  read-only
  STATUS  current
  DESCRIPTION "Bus L3 Current"
  ::= { dseInstrumentEntry 46 }
  
busECurrent OBJECT-TYPE
  SYNTAX  Unsigned32
  MAX-ACCESS  read-only
  STATUS  current
  DESCRIPTION "Bus earth current"
  ::= { dseInstrumentEntry 47 }
  
busL1Watts OBJECT-TYPE
  SYNTAX  Integer32
  MAX-ACCESS  read-only
  STATUS  current
  DESCRIPTION "Bus L1 watts"
  ::= { dseInstrumentEntry 48 }
  
busL2Watts OBJECT-TYPE
  SYNTAX  Integer32
  MAX-ACCESS  read-only
  STATUS  current
  DESCRIPTION "Bus L2 watts"
  ::= { dseInstrumentEntry 49 }
  
busL3Watts OBJECT-TYPE
  SYNTAX  Integer32
  MAX-ACCESS  read-only
  STATUS  current
  DESCRIPTION "Bus L3 watts"
  ::= { dseInstrumentEntry 50 }
  
canLink OBJECT-TYPE
  SYNTAX  Unsigned32
  MAX-ACCESS  read-only
  STATUS  current
  DESCRIPTION "CAN link status"
  ::= { dseInstrumentEntry 51 }
  
genWattsTotal OBJECT-TYPE
  SYNTAX  Integer32
  MAX-ACCESS  read-only
  STATUS  current
  DESCRIPTION "Generator total watts"
  ::= { dseInstrumentEntry 52 }
  
genL1VA OBJECT-TYPE
  SYNTAX  Unsigned32
  MAX-ACCESS  read-only
  STATUS  current
  DESCRIPTION "Generator L1 VA"
  ::= { dseInstrumentEntry 53 }
  
genL2VA OBJECT-TYPE
  SYNTAX  Unsigned32
  MAX-ACCESS  read-only
  STATUS  current
  DESCRIPTION "Generator L2 VA"
  ::= { dseInstrumentEntry 54 }
  
genL3VA OBJECT-TYPE
  SYNTAX  Unsigned32
  MAX-ACCESS  read-only
  STATUS  current
  DESCRIPTION "Generator L3 VA"
  ::= { dseInstrumentEntry 55 }
  
genTotalVA OBJECT-TYPE
  SYNTAX  Unsigned32
  MAX-ACCESS  read-only
  STATUS  current
  DESCRIPTION "Generator total VA"
  ::= { dseInstrumentEntry 56 }
  
genL1VAr OBJECT-TYPE
  SYNTAX  Integer32
  MAX-ACCESS  read-only
  STATUS  current
  DESCRIPTION "Generator L1 VAr"
  ::= { dseInstrumentEntry 57 }
  
genL2VAr OBJECT-TYPE
  SYNTAX  Integer32
  MAX-ACCESS  read-only
  STATUS  current
  DESCRIPTION "Generator L2 VAr"
  ::= { dseInstrumentEntry 58 }
  
genL3VAr OBJECT-TYPE
  SYNTAX  Integer32
  MAX-ACCESS  read-only
  STATUS  current
  DESCRIPTION "Generator L3 VAr"
  ::= { dseInstrumentEntry 59 }
  
genTotalVAr OBJECT-TYPE
  SYNTAX  Integer32
  MAX-ACCESS  read-only
  STATUS  current
  DESCRIPTION "Generator total VAr"
  ::= { dseInstrumentEntry 60 }
  
genPowerFactorL1 OBJECT-TYPE
  SYNTAX  Integer32
  MAX-ACCESS  read-only
  STATUS  current
  DESCRIPTION "Generator power factor L1"
  ::= { dseInstrumentEntry 61 }
  
genPowerFactorL2 OBJECT-TYPE
  SYNTAX  Integer32
  MAX-ACCESS  read-only
  STATUS  current
  DESCRIPTION "Generator power factor L2"
  ::= { dseInstrumentEntry 62 }
  
genPowerFactorL3 OBJECT-TYPE
  SYNTAX  Integer32
  MAX-ACCESS  read-only
  STATUS  current
  DESCRIPTION "Generator power factor L3"
  ::= { dseInstrumentEntry 63 }
  
genAvgPowerFactor OBJECT-TYPE
  SYNTAX  Integer32
  MAX-ACCESS  read-only
  STATUS  current
  DESCRIPTION "Generator average power factor"
  ::= { dseInstrumentEntry 64 }
  
mainsTotalWatts OBJECT-TYPE
  SYNTAX  Integer32
  MAX-ACCESS  read-only
  STATUS  current
  DESCRIPTION "Mains total watts"
  ::= { dseInstrumentEntry 65 }
  
mainsL1VA OBJECT-TYPE
  SYNTAX  Unsigned32
  MAX-ACCESS  read-only
  STATUS  current
  DESCRIPTION "Mains L1 VA"
  ::= { dseInstrumentEntry 66 }
  
mainsL2VA OBJECT-TYPE
  SYNTAX  Unsigned32
  MAX-ACCESS  read-only
  STATUS  current
  DESCRIPTION "Mains L2 VA"
  ::= { dseInstrumentEntry 67 }
  
mainsL3VA OBJECT-TYPE
  SYNTAX  Unsigned32
  MAX-ACCESS  read-only
  STATUS  current
  DESCRIPTION "Mains L3 VA"
  ::= { dseInstrumentEntry 68 }
  
mainsTotalVA OBJECT-TYPE
  SYNTAX  Unsigned32
  MAX-ACCESS  read-only
  STATUS  current
  DESCRIPTION "Mains total VA"
  ::= { dseInstrumentEntry 69 }
  
mainsL1VAr OBJECT-TYPE
  SYNTAX  Integer32
  MAX-ACCESS  read-only
  STATUS  current
  DESCRIPTION "Mains L1 VAr"
  ::= { dseInstrumentEntry 70 }
  
mainsL2VAr OBJECT-TYPE
  SYNTAX  Integer32
  MAX-ACCESS  read-only
  STATUS  current
  DESCRIPTION "Mains L2 VAr"
  ::= { dseInstrumentEntry 71 }
  
mainsL3VAr OBJECT-TYPE
  SYNTAX  Integer32
  MAX-ACCESS  read-only
  STATUS  current
  DESCRIPTION "Mains L3 VAr"
  ::= { dseInstrumentEntry 72 }
  
mainsTotalVAr OBJECT-TYPE
  SYNTAX  Integer32
  MAX-ACCESS  read-only
  STATUS  current
  DESCRIPTION "Mains total VAr"
  ::= { dseInstrumentEntry 73 }
  
mainsPowerFactorL1 OBJECT-TYPE
  SYNTAX  Integer32
  MAX-ACCESS  read-only
  STATUS  current
  DESCRIPTION "Mains power factor L1"
  ::= { dseInstrumentEntry 74 }
  
mainsPowerFactorL2 OBJECT-TYPE
  SYNTAX  Integer32
  MAX-ACCESS  read-only
  STATUS  current
  DESCRIPTION "Mains power factor L2"
  ::= { dseInstrumentEntry 75 }
  
mainsPowerFactorL3 OBJECT-TYPE
  SYNTAX  Integer32
  MAX-ACCESS  read-only
  STATUS  current
  DESCRIPTION "Mains power factor L3"
  ::= { dseInstrumentEntry 76 }
  
mainsAvgPowerFactor OBJECT-TYPE
  SYNTAX  Integer32
  MAX-ACCESS  read-only
  STATUS  current
  DESCRIPTION "Mains average power factor"
  ::= { dseInstrumentEntry 77 }
  
busTotalWatts OBJECT-TYPE
  SYNTAX  Integer32
  MAX-ACCESS  read-only
  STATUS  current
  DESCRIPTION "Bus total watts"
  ::= { dseInstrumentEntry 78 }
  
busL1VA OBJECT-TYPE
  SYNTAX  Unsigned32
  MAX-ACCESS  read-only
  STATUS  current
  DESCRIPTION "Bus L1 VA"
  ::= { dseInstrumentEntry 79 }
  
busL2VA OBJECT-TYPE
  SYNTAX  Unsigned32
  MAX-ACCESS  read-only
  STATUS  current
  DESCRIPTION "Bus L2 VA"
  ::= { dseInstrumentEntry 80 }
  
busL3VA OBJECT-TYPE
  SYNTAX  Unsigned32
  MAX-ACCESS  read-only
  STATUS  current
  DESCRIPTION "Bus L3 VA"
  ::= { dseInstrumentEntry 81 }
  
busTotalVA OBJECT-TYPE
  SYNTAX  Unsigned32
  MAX-ACCESS  read-only
  STATUS  current
  DESCRIPTION "Bus total VA"
  ::= { dseInstrumentEntry 82 }
  
busL1VAr OBJECT-TYPE
  SYNTAX  Integer32
  MAX-ACCESS  read-only
  STATUS  current
  DESCRIPTION "Bus L1 VAr"
  ::= { dseInstrumentEntry 83 }
  
busL2VAr OBJECT-TYPE
  SYNTAX  Integer32
  MAX-ACCESS  read-only
  STATUS  current
  DESCRIPTION "Bus L2 VAr"
  ::= { dseInstrumentEntry 84 }
  
busL3VAr OBJECT-TYPE
  SYNTAX  Integer32
  MAX-ACCESS  read-only
  STATUS  current
  DESCRIPTION "Bus L3 VAr"
  ::= { dseInstrumentEntry 85 }
  
busTotalVAr OBJECT-TYPE
  SYNTAX  Integer32
  MAX-ACCESS  read-only
  STATUS  current
  DESCRIPTION "Bus total VAr"
  ::= { dseInstrumentEntry 86 }
  
busPowerFactorL1 OBJECT-TYPE
  SYNTAX  Integer32
  MAX-ACCESS  read-only
  STATUS  current
  DESCRIPTION "Bus power factor L1"
  ::= { dseInstrumentEntry 87 }
  
busPowerFactorL2 OBJECT-TYPE
  SYNTAX  Integer32
  MAX-ACCESS  read-only
  STATUS  current
  DESCRIPTION "Bus power factor L2"
  ::= { dseInstrumentEntry 88 }
  
busPowerFactorL3 OBJECT-TYPE
  SYNTAX  Integer32
  MAX-ACCESS  read-only
  STATUS  current
  DESCRIPTION "Bus power factor L3"
  ::= { dseInstrumentEntry 89 }
  
busAvgPowerFactor OBJECT-TYPE
  SYNTAX  Integer32
  MAX-ACCESS  read-only
  STATUS  current
  DESCRIPTION "Bus average power factor"
  ::= { dseInstrumentEntry 90 }
  
engHours OBJECT-TYPE
  SYNTAX  Unsigned32
  MAX-ACCESS  read-only
  STATUS  current
  DESCRIPTION "Engine Hours"
  ::= { dseInstrumentEntry 91 }
  
genAccKW OBJECT-TYPE
  SYNTAX  Unsigned32
  MAX-ACCESS  read-only
  STATUS  current
  DESCRIPTION "Gen accumulated kW"
  ::= { dseInstrumentEntry 92 }
  
genAccKVA OBJECT-TYPE
  SYNTAX  Unsigned32
  MAX-ACCESS  read-only
  STATUS  current
  DESCRIPTION "Gen accumulated kVA"
  ::= { dseInstrumentEntry 93 }
  
genAccKVAr OBJECT-TYPE
  SYNTAX  Unsigned32
  MAX-ACCESS  read-only
  STATUS  current
  DESCRIPTION "Gen accumulated kVAr"
  ::= { dseInstrumentEntry 94 }
  
startAttempts OBJECT-TYPE
  SYNTAX  Unsigned32
  MAX-ACCESS  read-only
  STATUS  current
  DESCRIPTION "Start attempts"
  ::= { dseInstrumentEntry 95 }
  
mainsAccKW OBJECT-TYPE
  SYNTAX  Unsigned32
  MAX-ACCESS  read-only
  STATUS  current
  DESCRIPTION "Mains accumulated kW"
  ::= { dseInstrumentEntry 96 }
  
mainsAccKVA OBJECT-TYPE
  SYNTAX  Unsigned32
  MAX-ACCESS  read-only
  STATUS  current
  DESCRIPTION "Mains accumulated kVA"
  ::= { dseInstrumentEntry 97 }
  
mainsAccKVAr OBJECT-TYPE
  SYNTAX  Unsigned32
  MAX-ACCESS  read-only
  STATUS  current
  DESCRIPTION "Mains accumulated kVAr"
  ::= { dseInstrumentEntry 98 }
  
busAccKW OBJECT-TYPE
  SYNTAX  Unsigned32
  MAX-ACCESS  read-only
  STATUS  current
  DESCRIPTION "Bus accumulated kW"
  ::= { dseInstrumentEntry 99 }
  
busAccKVA OBJECT-TYPE
  SYNTAX  Unsigned32
  MAX-ACCESS  read-only
  STATUS  current
  DESCRIPTION "Bus accumulated kVA"
  ::= { dseInstrumentEntry 100 }
  
busAccKVAr OBJECT-TYPE
  SYNTAX  Unsigned32
  MAX-ACCESS  read-only
  STATUS  current
  DESCRIPTION "Bus accumulated kVAr"
  ::= { dseInstrumentEntry 101 }
  
  
  
  
  
  
--Custom Instruments
customInstrumentTable OBJECT-TYPE
    SYNTAX  SEQUENCE OF DseCustomInstrumentEntry
    MAX-ACCESS  not-accessible
    STATUS  current
    DESCRIPTION
     ""
    ::= { dseInstrumentsSection 2 }

dseCustomInstrumentEntry OBJECT-TYPE
    SYNTAX  DseCustomInstrumentEntry
    MAX-ACCESS  not-accessible
    STATUS  current
    DESCRIPTION
     ""
    INDEX { gencomTaskCustom }
    ::= { customInstrumentTable  1 }

DseCustomInstrumentEntry ::= SEQUENCE {
  gencomTaskCustom   INTEGER,
  slot1Value	     Unsigned32,
  slot1Description   OCTET STRING,
  slot2Value	     Unsigned32,
  slot2Description   OCTET STRING,
  slot3Value	     Unsigned32,
  slot3Description   OCTET STRING,
  slot4Value	     Unsigned32,
  slot4Description   OCTET STRING,
  slot5Value	     Unsigned32,
  slot5Description   OCTET STRING,
  slot6Value	     Unsigned32,
  slot6Description   OCTET STRING,
  slot7Value	     Unsigned32,
  slot7Description   OCTET STRING,
  slot8Value	     Unsigned32,
  slot8Description   OCTET STRING,
  slot9Value	     Unsigned32,
  slot9Description   OCTET STRING,
  slot10Value	     Unsigned32,
  slot10Description   OCTET STRING,
  slot11Value	     Unsigned32,
  slot11Description   OCTET STRING,
  slot12Value	     Unsigned32,
  slot12Description   OCTET STRING,
  slot13Value	     Unsigned32,
  slot13Description   OCTET STRING,
  slot14Value	     Unsigned32,
  slot14Description   OCTET STRING,
  slot15Value	     Unsigned32,
  slot15Description   OCTET STRING,
  slot16Value	     Unsigned32,
  slot16Description   OCTET STRING,
  slot17Value	     Unsigned32,
  slot17Description   OCTET STRING,
  slot18Value	     Unsigned32,
  slot18Description   OCTET STRING,
  slot19Value	     Unsigned32,
  slot19Description   OCTET STRING,
  slot20Value	     Unsigned32,
  slot20Description   OCTET STRING
  }
  
gencomTaskCustom OBJECT-TYPE
  SYNTAX  INTEGER (1..2147483647)
  MAX-ACCESS  read-only
  STATUS  current
  DESCRIPTION "Gencom Task"
  ::= { dseCustomInstrumentEntry 1 }
  
slot1Value OBJECT-TYPE
  SYNTAX  Unsigned32
  MAX-ACCESS  read-only
  STATUS  current
  DESCRIPTION "Custom instrument 1"
  ::= { dseCustomInstrumentEntry 2 }
  
slot1Description OBJECT-TYPE
  SYNTAX  OCTET STRING
  MAX-ACCESS  read-only
  STATUS  current
  DESCRIPTION "Custom instrument 1"
  ::= { dseCustomInstrumentEntry 3 }
  
slot2Value OBJECT-TYPE
  SYNTAX  Unsigned32
  MAX-ACCESS  read-only
  STATUS  current
  DESCRIPTION "Custom instrument 2"
  ::= { dseCustomInstrumentEntry 4 }
  
slot2Description OBJECT-TYPE
  SYNTAX  OCTET STRING
  MAX-ACCESS  read-only
  STATUS  current
  DESCRIPTION "Custom instrument 2"
  ::= { dseCustomInstrumentEntry 5 }
  
slot3Value OBJECT-TYPE
  SYNTAX  Unsigned32
  MAX-ACCESS  read-only
  STATUS  current
  DESCRIPTION "Custom instrument 3"
  ::= { dseCustomInstrumentEntry 6 }
  
slot3Description OBJECT-TYPE
  SYNTAX  OCTET STRING
  MAX-ACCESS  read-only
  STATUS  current
  DESCRIPTION "Custom instrument 3"
  ::= { dseCustomInstrumentEntry 7 }
  
slot4Value OBJECT-TYPE
  SYNTAX  Unsigned32
  MAX-ACCESS  read-only
  STATUS  current
  DESCRIPTION "Custom instrument 4"
  ::= { dseCustomInstrumentEntry 8 }
  
slot4Description OBJECT-TYPE
  SYNTAX  OCTET STRING
  MAX-ACCESS  read-only
  STATUS  current
  DESCRIPTION "Custom instrument 4"
  ::= { dseCustomInstrumentEntry 9 }
  
slot5Value OBJECT-TYPE
  SYNTAX  Unsigned32
  MAX-ACCESS  read-only
  STATUS  current
  DESCRIPTION "Custom instrument 5"
  ::= { dseCustomInstrumentEntry 10 }
  
slot5Description OBJECT-TYPE
  SYNTAX  OCTET STRING
  MAX-ACCESS  read-only
  STATUS  current
  DESCRIPTION "Custom instrument 5"
  ::= { dseCustomInstrumentEntry 11 }
  
slot6Value OBJECT-TYPE
  SYNTAX  Unsigned32
  MAX-ACCESS  read-only
  STATUS  current
  DESCRIPTION "Custom instrument 6"
  ::= { dseCustomInstrumentEntry 12 }
  
slot6Description OBJECT-TYPE
  SYNTAX  OCTET STRING
  MAX-ACCESS  read-only
  STATUS  current
  DESCRIPTION "Custom instrument 6"
  ::= { dseCustomInstrumentEntry 13 }
  
slot7Value OBJECT-TYPE
  SYNTAX  Unsigned32
  MAX-ACCESS  read-only
  STATUS  current
  DESCRIPTION "Custom instrument 7"
  ::= { dseCustomInstrumentEntry 14 }
  
slot7Description OBJECT-TYPE
  SYNTAX  OCTET STRING
  MAX-ACCESS  read-only
  STATUS  current
  DESCRIPTION "Custom instrument 7"
  ::= { dseCustomInstrumentEntry 15 }
  
slot8Value OBJECT-TYPE
  SYNTAX  Unsigned32
  MAX-ACCESS  read-only
  STATUS  current
  DESCRIPTION "Custom instrument 8"
  ::= { dseCustomInstrumentEntry 16 }
  
slot8Description OBJECT-TYPE
  SYNTAX  OCTET STRING
  MAX-ACCESS  read-only
  STATUS  current
  DESCRIPTION "Custom instrument 8"
  ::= { dseCustomInstrumentEntry 17 }
  
slot9Value OBJECT-TYPE
  SYNTAX  Unsigned32
  MAX-ACCESS  read-only
  STATUS  current
  DESCRIPTION "Custom instrument 9"
  ::= { dseCustomInstrumentEntry 18 }
  
slot9Description OBJECT-TYPE
  SYNTAX  OCTET STRING
  MAX-ACCESS  read-only
  STATUS  current
  DESCRIPTION "Custom instrument 9"
  ::= { dseCustomInstrumentEntry 19 }
  
slot10Value OBJECT-TYPE
  SYNTAX  Unsigned32
  MAX-ACCESS  read-only
  STATUS  current
  DESCRIPTION "Custom instrument 10"
  ::= { dseCustomInstrumentEntry 20 }
  
slot10Description OBJECT-TYPE
  SYNTAX  OCTET STRING
  MAX-ACCESS  read-only
  STATUS  current
  DESCRIPTION "Custom instrument 10"
  ::= { dseCustomInstrumentEntry 21 }
  
slot11Value OBJECT-TYPE
  SYNTAX  Unsigned32
  MAX-ACCESS  read-only
  STATUS  current
  DESCRIPTION "Custom instrument 11"
  ::= { dseCustomInstrumentEntry 22 }
  
slot11Description OBJECT-TYPE
  SYNTAX  OCTET STRING
  MAX-ACCESS  read-only
  STATUS  current
  DESCRIPTION "Custom instrument 11"
  ::= { dseCustomInstrumentEntry 23 }
  
slot12Value OBJECT-TYPE
  SYNTAX  Unsigned32
  MAX-ACCESS  read-only
  STATUS  current
  DESCRIPTION "Custom instrument 12"
  ::= { dseCustomInstrumentEntry 24 }
  
slot12Description OBJECT-TYPE
  SYNTAX  OCTET STRING
  MAX-ACCESS  read-only
  STATUS  current
  DESCRIPTION "Custom instrument 12"
  ::= { dseCustomInstrumentEntry 25 }
  
slot13Value OBJECT-TYPE
  SYNTAX  Unsigned32
  MAX-ACCESS  read-only
  STATUS  current
  DESCRIPTION "Custom instrument 13"
  ::= { dseCustomInstrumentEntry 26 }
  
slot13Description OBJECT-TYPE
  SYNTAX  OCTET STRING
  MAX-ACCESS  read-only
  STATUS  current
  DESCRIPTION "Custom instrument 13"
  ::= { dseCustomInstrumentEntry 27 }
  
slot14Value OBJECT-TYPE
  SYNTAX  Unsigned32
  MAX-ACCESS  read-only
  STATUS  current
  DESCRIPTION "Custom instrument 14"
  ::= { dseCustomInstrumentEntry 28 }
  
slot14Description OBJECT-TYPE
  SYNTAX  OCTET STRING
  MAX-ACCESS  read-only
  STATUS  current
  DESCRIPTION "Custom instrument 14"
  ::= { dseCustomInstrumentEntry 29 }
  
slot15Value OBJECT-TYPE
  SYNTAX  Unsigned32
  MAX-ACCESS  read-only
  STATUS  current
  DESCRIPTION "Custom instrument 15"
  ::= { dseCustomInstrumentEntry 30 }
  
slot15Description OBJECT-TYPE
  SYNTAX  OCTET STRING
  MAX-ACCESS  read-only
  STATUS  current
  DESCRIPTION "Custom instrument 15"
  ::= { dseCustomInstrumentEntry 31 }
  
slot16Value OBJECT-TYPE
  SYNTAX  Unsigned32
  MAX-ACCESS  read-only
  STATUS  current
  DESCRIPTION "Custom instrument 16"
  ::= { dseCustomInstrumentEntry 32 }
  
slot16Description OBJECT-TYPE
  SYNTAX  OCTET STRING
  MAX-ACCESS  read-only
  STATUS  current
  DESCRIPTION "Custom instrument 16"
  ::= { dseCustomInstrumentEntry 33 }
  
slot17Value OBJECT-TYPE
  SYNTAX  Unsigned32
  MAX-ACCESS  read-only
  STATUS  current
  DESCRIPTION "Custom instrument 17"
  ::= { dseCustomInstrumentEntry 34 }
  
slot17Description OBJECT-TYPE
  SYNTAX  OCTET STRING
  MAX-ACCESS  read-only
  STATUS  current
  DESCRIPTION "Custom instrument 17"
  ::= { dseCustomInstrumentEntry 35 }
  
slot18Value OBJECT-TYPE
  SYNTAX  Unsigned32
  MAX-ACCESS  read-only
  STATUS  current
  DESCRIPTION "Custom instrument 18"
  ::= { dseCustomInstrumentEntry 36 }
  
slot18Description OBJECT-TYPE
  SYNTAX  OCTET STRING
  MAX-ACCESS  read-only
  STATUS  current
  DESCRIPTION "Custom instrument 18"
  ::= { dseCustomInstrumentEntry 37 }
  
slot19Value OBJECT-TYPE
  SYNTAX  Unsigned32
  MAX-ACCESS  read-only
  STATUS  current
  DESCRIPTION "Custom instrument 19"
  ::= { dseCustomInstrumentEntry 38 }
  
slot19Description OBJECT-TYPE
  SYNTAX  OCTET STRING
  MAX-ACCESS  read-only
  STATUS  current
  DESCRIPTION "Custom instrument 19"
  ::= { dseCustomInstrumentEntry 39 }
  
slot20Value OBJECT-TYPE
  SYNTAX  Unsigned32
  MAX-ACCESS  read-only
  STATUS  current
  DESCRIPTION "Custom instrument 20"
  ::= { dseCustomInstrumentEntry 40 }
  
slot20Description OBJECT-TYPE
  SYNTAX  OCTET STRING
  MAX-ACCESS  read-only
  STATUS  current
  DESCRIPTION "Custom instrument 20"
  ::= { dseCustomInstrumentEntry 41 }
  
  
  
--Control Mode
controlTable OBJECT-TYPE
    SYNTAX  SEQUENCE OF DseControlEntry
    MAX-ACCESS  not-accessible
    STATUS  current
    DESCRIPTION
     ""
    ::= { dseInstrumentsSection 3 }

dseControlEntry OBJECT-TYPE
    SYNTAX  DseControlEntry
    MAX-ACCESS  not-accessible
    STATUS  current
    DESCRIPTION
     ""
    INDEX { gencomTaskControl }
    ::= { controlTable  1 }

DseControlEntry ::= SEQUENCE {
  gencomTaskControl INTEGER,
  mode              Unsigned32,
  modeText         OCTET STRING
  }
  
gencomTaskControl OBJECT-TYPE
  SYNTAX  INTEGER  (1..2147483647)
  MAX-ACCESS  read-only
  STATUS  current
  DESCRIPTION "Gencom Task"
  ::= { dseControlEntry 1 }
  
  
mode OBJECT-TYPE
  SYNTAX  Unsigned32 (0..6)
  MAX-ACCESS  read-only
  STATUS  current
  DESCRIPTION "tbd"
  ::= { dseControlEntry 2 }
  
modeText OBJECT-TYPE
  SYNTAX  OCTET STRING
  MAX-ACCESS  read-only
  STATUS  current
  DESCRIPTION "tbd"
  ::= { dseControlEntry 3 }
  

--keypress action
keypressTable OBJECT-TYPE
    SYNTAX  SEQUENCE OF DseKeypressEntry
    MAX-ACCESS  not-accessible
    STATUS  current
    DESCRIPTION
     ""
    ::= { dseInstrumentsSection 4 }

dseKeypressEntry OBJECT-TYPE
    SYNTAX  DseKeypressEntry
    MAX-ACCESS  not-accessible
    STATUS  current
    DESCRIPTION
     ""
    INDEX { gencomTaskKeypress }
    ::= { keypressTable  1 }

DseKeypressEntry ::= SEQUENCE {
  gencomTaskKeypress         INTEGER,
  keypress           OCTET STRING
  }
  
gencomTaskKeypress OBJECT-TYPE
  SYNTAX  INTEGER  (1..2147483647)
  MAX-ACCESS  read-only
  STATUS  current
  DESCRIPTION "Gencom Task"
  ::= { dseKeypressEntry 1 }
  
  
keypress OBJECT-TYPE
  SYNTAX  OCTET STRING
  MAX-ACCESS  read-write
  STATUS  current
  DESCRIPTION "Valid values: ACT_ON, ACT_MAN, ACT_TEST, ACT_AUTO, ACT_OFF, ACT_GEN, ACT_MAINS, ACT_BUZZ, NO_ACT"
  ::= { dseKeypressEntry 2 }
  

  
  
END
