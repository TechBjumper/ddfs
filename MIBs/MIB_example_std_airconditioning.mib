--
-- CAREL-std-air-cond.MIB
-- MIB generated by CAREL
-- Wednesday, 19 May 2010
--

    CAREL-std-air-cond-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        std-air-condMIB MODULE-IDENTITY
      		LAST-UPDATED  "201005190920Z"		-- May 19, 2010 at 09:20 GMT
      		ORGANIZATION  "CAREL Industries S.r.l"
      		CONTACT-INFO
                "
                        Carel Industries S.r.l
                        Via dell'Industria, 11
                        35020 Brugine (PD) Italy
                        Tel: +39 049 9716611
                        E-mail: carel@carel.com
                "
      		DESCRIPTION
                "This is the MIB module for the std-air-cond device."
			REVISION "201005190920Z"
			DESCRIPTION
                "version 1.0"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { std-air-condMIB 1 }

        -- 1.3.6.1.4.1.9839.2.1.1.1
        digital-input-1 OBJECT-TYPE
                    SYNTAX Integer32 (0..1)
                    UNITS "N/A"
                    MAX-ACCESS read-only
                    STATUS current
                    DESCRIPTION "Digital input 1"
                    ::= { digitalObjects 1 }

        -- 1.3.6.1.4.1.9839.2.1.1.2
        digital-input-2 OBJECT-TYPE
                    SYNTAX Integer32 (0..1)
                    UNITS "N/A"
                    MAX-ACCESS read-only
                    STATUS current
                    DESCRIPTION "Digital input 2"
                    ::= { digitalObjects 2 }

        -- 1.3.6.1.4.1.9839.2.1.1.3
        digital-input-3 OBJECT-TYPE
                    SYNTAX Integer32 (0..1)
                    UNITS "N/A"
                    MAX-ACCESS read-only
                    STATUS current
                    DESCRIPTION "Digital input 3"
                    ::= { digitalObjects 3 }

        -- 1.3.6.1.4.1.9839.2.1.1.4
        digital-input-4 OBJECT-TYPE
                    SYNTAX Integer32 (0..1)
                    UNITS "N/A"
                    MAX-ACCESS read-only
                    STATUS current
                    DESCRIPTION "Digital input 4"
                    ::= { digitalObjects 4 }

        -- 1.3.6.1.4.1.9839.2.1.1.5
        digital-input-5 OBJECT-TYPE
                    SYNTAX Integer32 (0..1)
                    UNITS "N/A"
                    MAX-ACCESS read-only
                    STATUS current
                    DESCRIPTION "Digital input 5"
                    ::= { digitalObjects 5 }

        -- 1.3.6.1.4.1.9839.2.1.1.6
        digital-input-6 OBJECT-TYPE
                    SYNTAX Integer32 (0..1)
                    UNITS "N/A"
                    MAX-ACCESS read-only
                    STATUS current
                    DESCRIPTION "Digital input 6"
                    ::= { digitalObjects 6 }

        -- 1.3.6.1.4.1.9839.2.1.1.7
        digital-input-7 OBJECT-TYPE
                    SYNTAX Integer32 (0..1)
                    UNITS "N/A"
                    MAX-ACCESS read-only
                    STATUS current
                    DESCRIPTION "Digital input 7"
                    ::= { digitalObjects 7 }

        -- 1.3.6.1.4.1.9839.2.1.1.8
        digital-input-8 OBJECT-TYPE
                    SYNTAX Integer32 (0..1)
                    UNITS "N/A"
                    MAX-ACCESS read-only
                    STATUS current
                    DESCRIPTION "Digital input 8"
                    ::= { digitalObjects 8 }

        -- 1.3.6.1.4.1.9839.2.1.1.9
        digital-input-9 OBJECT-TYPE
                    SYNTAX Integer32 (0..1)
                    UNITS "N/A"
                    MAX-ACCESS read-only
                    STATUS current
                    DESCRIPTION "Digital input 9"
                    ::= { digitalObjects 9 }

        -- 1.3.6.1.4.1.9839.2.1.1.10
        digital-input-10 OBJECT-TYPE
                    SYNTAX Integer32 (0..1)
                    UNITS "N/A"
                    MAX-ACCESS read-only
                    STATUS current
                    DESCRIPTION "Digital input 10"
                    ::= { digitalObjects 10 }

        -- 1.3.6.1.4.1.9839.2.1.1.11
        level-hum1 OBJECT-TYPE
                    SYNTAX Integer32 (0..1)
                    UNITS "N/A"
                    MAX-ACCESS read-only
                    STATUS current
                    DESCRIPTION "Humidifier water level contact"
                    ::= { digitalObjects 11 }

        -- 1.3.6.1.4.1.9839.2.1.1.12
        digital-input-12 OBJECT-TYPE
                    SYNTAX Integer32 (0..1)
                    UNITS "N/A"
                    MAX-ACCESS read-only
                    STATUS current
                    DESCRIPTION "Digital input 12"
                    ::= { digitalObjects 12 }

        -- 1.3.6.1.4.1.9839.2.1.1.13
        digital-input-13 OBJECT-TYPE
                    SYNTAX Integer32 (0..1)
                    UNITS "N/A"
                    MAX-ACCESS read-only
                    STATUS current
                    DESCRIPTION "Digital input 13"
                    ::= { digitalObjects 13 }

        -- 1.3.6.1.4.1.9839.2.1.1.14
        digital-input-14 OBJECT-TYPE
                    SYNTAX Integer32 (0..1)
                    UNITS "N/A"
                    MAX-ACCESS read-only
                    STATUS current
                    DESCRIPTION "Digital input 14"
                    ::= { digitalObjects 14 }

        -- 1.3.6.1.4.1.9839.2.1.1.15
        pco2-dout-1 OBJECT-TYPE
                    SYNTAX Integer32 (0..1)
                    UNITS "N/A"
                    MAX-ACCESS read-only
                    STATUS current
                    DESCRIPTION "Digital output 1"
                    ::= { digitalObjects 15 }

        -- 1.3.6.1.4.1.9839.2.1.1.16
        pco2-dout-2 OBJECT-TYPE
                    SYNTAX Integer32 (0..1)
                    UNITS "N/A"
                    MAX-ACCESS read-only
                    STATUS current
                    DESCRIPTION "Digital output 2"
                    ::= { digitalObjects 16 }

        -- 1.3.6.1.4.1.9839.2.1.1.17
        pco2-dout-3 OBJECT-TYPE
                    SYNTAX Integer32 (0..1)
                    UNITS "N/A"
                    MAX-ACCESS read-only
                    STATUS current
                    DESCRIPTION "Digital output 3"
                    ::= { digitalObjects 17 }

        -- 1.3.6.1.4.1.9839.2.1.1.18
        pco2-dout-4 OBJECT-TYPE
                    SYNTAX Integer32 (0..1)
                    UNITS "N/A"
                    MAX-ACCESS read-only
                    STATUS current
                    DESCRIPTION "Digital output 4"
                    ::= { digitalObjects 18 }

        -- 1.3.6.1.4.1.9839.2.1.1.19
        pco2-dout-5 OBJECT-TYPE
                    SYNTAX Integer32 (0..1)
                    UNITS "N/A"
                    MAX-ACCESS read-only
                    STATUS current
                    DESCRIPTION "Digital output 5"
                    ::= { digitalObjects 19 }

        -- 1.3.6.1.4.1.9839.2.1.1.20
        pco2-dout-6 OBJECT-TYPE
                    SYNTAX Integer32 (0..1)
                    UNITS "N/A"
                    MAX-ACCESS read-only
                    STATUS current
                    DESCRIPTION "Digital output 6"
                    ::= { digitalObjects 20 }

        -- 1.3.6.1.4.1.9839.2.1.1.21
        pco2-dout-7 OBJECT-TYPE
                    SYNTAX Integer32 (0..1)
                    UNITS "N/A"
                    MAX-ACCESS read-only
                    STATUS current
                    DESCRIPTION "Digital output 7"
                    ::= { digitalObjects 21 }

        -- 1.3.6.1.4.1.9839.2.1.1.22
        pco2-dout-8 OBJECT-TYPE
                    SYNTAX Integer32 (0..1)
                    UNITS "N/A"
                    MAX-ACCESS read-only
                    STATUS current
                    DESCRIPTION "Digital output 8"
                    ::= { digitalObjects 22 }

        -- 1.3.6.1.4.1.9839.2.1.1.23
        pco2-dout-9 OBJECT-TYPE
                    SYNTAX Integer32 (0..1)
                    UNITS "N/A"
                    MAX-ACCESS read-only
                    STATUS current
                    DESCRIPTION "Digital output 9"
                    ::= { digitalObjects 23 }

        -- 1.3.6.1.4.1.9839.2.1.1.24
        pco2-dout-10 OBJECT-TYPE
                    SYNTAX Integer32 (0..1)
                    UNITS "N/A"
                    MAX-ACCESS read-only
                    STATUS current
                    DESCRIPTION "Digital output 10"
                    ::= { digitalObjects 24 }

        -- 1.3.6.1.4.1.9839.2.1.1.25
        pco2-dout-11 OBJECT-TYPE
                    SYNTAX Integer32 (0..1)
                    UNITS "N/A"
                    MAX-ACCESS read-only
                    STATUS current
                    DESCRIPTION "Digital output 11"
                    ::= { digitalObjects 25 }

        -- 1.3.6.1.4.1.9839.2.1.1.26
        pco2-dout-12 OBJECT-TYPE
                    SYNTAX Integer32 (0..1)
                    UNITS "N/A"
                    MAX-ACCESS read-only
                    STATUS current
                    DESCRIPTION "Digital output 12"
                    ::= { digitalObjects 26 }

        -- 1.3.6.1.4.1.9839.2.1.1.27
        pco2-dout-13 OBJECT-TYPE
                    SYNTAX Integer32 (0..1)
                    UNITS "N/A"
                    MAX-ACCESS read-only
                    STATUS current
                    DESCRIPTION "Digital output 13"
                    ::= { digitalObjects 27 }

        -- 1.3.6.1.4.1.9839.2.1.1.28
        mal-alarm-comp1 OBJECT-TYPE
                    SYNTAX Integer32 (0..1)
                    UNITS "N/A"
                    MAX-ACCESS read-only
                    STATUS current
                    DESCRIPTION "Generic alarm compressor 1"
                    ::= { digitalObjects 28 }

        -- 1.3.6.1.4.1.9839.2.1.1.29
        mal-alarm-comp2 OBJECT-TYPE
                    SYNTAX Integer32 (0..1)
                    UNITS "N/A"
                    MAX-ACCESS read-only
                    STATUS current
                    DESCRIPTION "Generic alarm compressor 2"
                    ::= { digitalObjects 29 }

        -- 1.3.6.1.4.1.9839.2.1.1.30
        mal-low-pres-c1 OBJECT-TYPE
                    SYNTAX Integer32 (0..1)
                    UNITS "N/A"
                    MAX-ACCESS read-only
                    STATUS current
                    DESCRIPTION "Low pressure alarm compressor 1"
                    ::= { digitalObjects 30 }

        -- 1.3.6.1.4.1.9839.2.1.1.31
        mal-low-pres-c2 OBJECT-TYPE
                    SYNTAX Integer32 (0..1)
                    UNITS "N/A"
                    MAX-ACCESS read-only
                    STATUS current
                    DESCRIPTION "Low pressure alarm compressor 2"
                    ::= { digitalObjects 31 }

        -- 1.3.6.1.4.1.9839.2.1.1.32
        mal-air-flow OBJECT-TYPE
                    SYNTAX Integer32 (0..1)
                    UNITS "N/A"
                    MAX-ACCESS read-only
                    STATUS current
                    DESCRIPTION "Air flow alarm"
                    ::= { digitalObjects 32 }

        -- 1.3.6.1.4.1.9839.2.1.1.33
        mal-fan-overl OBJECT-TYPE
                    SYNTAX Integer32 (0..1)
                    UNITS "N/A"
                    MAX-ACCESS read-only
                    STATUS current
                    DESCRIPTION "Fan overload alarm"
                    ::= { digitalObjects 33 }

        -- 1.3.6.1.4.1.9839.2.1.1.34
        mal-heat-overl1 OBJECT-TYPE
                    SYNTAX Integer32 (0..1)
                    UNITS "N/A"
                    MAX-ACCESS read-only
                    STATUS current
                    DESCRIPTION "Heater 1 overload alarm"
                    ::= { digitalObjects 34 }

        -- 1.3.6.1.4.1.9839.2.1.1.35
        mal-heat-overl2 OBJECT-TYPE
                    SYNTAX Integer32 (0..1)
                    UNITS "N/A"
                    MAX-ACCESS read-only
                    STATUS current
                    DESCRIPTION "Heater 2 overload alarm"
                    ::= { digitalObjects 35 }

        -- 1.3.6.1.4.1.9839.2.1.1.36
        mal-fire-smoke OBJECT-TYPE
                    SYNTAX Integer32 (0..1)
                    UNITS "N/A"
                    MAX-ACCESS read-only
                    STATUS current
                    DESCRIPTION "Fire/Smoke alarm"
                    ::= { digitalObjects 36 }

        -- 1.3.6.1.4.1.9839.2.1.1.37
        mal-air-filter OBJECT-TYPE
                    SYNTAX Integer32 (0..1)
                    UNITS "N/A"
                    MAX-ACCESS read-only
                    STATUS current
                    DESCRIPTION "Dirty filter alarm"
                    ::= { digitalObjects 37 }

        -- 1.3.6.1.4.1.9839.2.1.1.38
        mal-h-room-temp OBJECT-TYPE
                    SYNTAX Integer32 (0..1)
                    UNITS "N/A"
                    MAX-ACCESS read-only
                    STATUS current
                    DESCRIPTION "High ambient temperature alarm"
                    ::= { digitalObjects 38 }

        -- 1.3.6.1.4.1.9839.2.1.1.39
        mal-l-room-temp OBJECT-TYPE
                    SYNTAX Integer32 (0..1)
                    UNITS "N/A"
                    MAX-ACCESS read-only
                    STATUS current
                    DESCRIPTION "Low ambient temperature alarm"
                    ::= { digitalObjects 39 }

        -- 1.3.6.1.4.1.9839.2.1.1.40
        mal-high-humid OBJECT-TYPE
                    SYNTAX Integer32 (0..1)
                    UNITS "N/A"
                    MAX-ACCESS read-only
                    STATUS current
                    DESCRIPTION "High ambient humidity alarm"
                    ::= { digitalObjects 40 }

        -- 1.3.6.1.4.1.9839.2.1.1.41
        mal-low-humid OBJECT-TYPE
                    SYNTAX Integer32 (0..1)
                    UNITS "N/A"
                    MAX-ACCESS read-only
                    STATUS current
                    DESCRIPTION "Low ambient humidity alarm"
                    ::= { digitalObjects 41 }

        -- 1.3.6.1.4.1.9839.2.1.1.42
        mal-h-valve-c1 OBJECT-TYPE
                    SYNTAX Integer32 (0..1)
                    UNITS "N/A"
                    MAX-ACCESS read-only
                    STATUS current
                    DESCRIPTION "Op. hour threshold alarm, compressor 1"
                    ::= { digitalObjects 42 }

        -- 1.3.6.1.4.1.9839.2.1.1.43
        mal-h-valve-c2 OBJECT-TYPE
                    SYNTAX Integer32 (0..1)
                    UNITS "N/A"
                    MAX-ACCESS read-only
                    STATUS current
                    DESCRIPTION "Op. hour threshold alarm, compressor 2"
                    ::= { digitalObjects 43 }

        -- 1.3.6.1.4.1.9839.2.1.1.44
        mal-h-main-fan OBJECT-TYPE
                    SYNTAX Integer32 (0..1)
                    UNITS "N/A"
                    MAX-ACCESS read-only
                    STATUS current
                    DESCRIPTION "Op. hour threshold alarm, fan"
                    ::= { digitalObjects 44 }

        -- 1.3.6.1.4.1.9839.2.1.1.45
        mal-room-temp OBJECT-TYPE
                    SYNTAX Integer32 (0..1)
                    UNITS "N/A"
                    MAX-ACCESS read-only
                    STATUS current
                    DESCRIPTION "Room temperature probe faulty alarm"
                    ::= { digitalObjects 45 }

        -- 1.3.6.1.4.1.9839.2.1.1.46
        mal-temp-recovery OBJECT-TYPE
                    SYNTAX Integer32 (0..1)
                    UNITS "N/A"
                    MAX-ACCESS read-only
                    STATUS current
                    DESCRIPTION "Recovery temperature probe faulty alarm"
                    ::= { digitalObjects 46 }

        -- 1.3.6.1.4.1.9839.2.1.1.47
        mal-ext-temp OBJECT-TYPE
                    SYNTAX Integer32 (0..1)
                    UNITS "N/A"
                    MAX-ACCESS read-only
                    STATUS current
                    DESCRIPTION "Outside temperature probe faulty alarm"
                    ::= { digitalObjects 47 }

        -- 1.3.6.1.4.1.9839.2.1.1.48
        mal-supply-temp OBJECT-TYPE
                    SYNTAX Integer32 (0..1)
                    UNITS "N/A"
                    MAX-ACCESS read-only
                    STATUS current
                    DESCRIPTION "Outlet temperature probe faulty alarm"
                    ::= { digitalObjects 48 }

        -- 1.3.6.1.4.1.9839.2.1.1.49
        mal-room-humid OBJECT-TYPE
                    SYNTAX Integer32 (0..1)
                    UNITS "N/A"
                    MAX-ACCESS read-only
                    STATUS current
                    DESCRIPTION "Room humidity probe faulty alarm"
                    ::= { digitalObjects 49 }

        -- 1.3.6.1.4.1.9839.2.1.1.50
        mal-pressure1 OBJECT-TYPE
                    SYNTAX Integer32 (0..1)
                    UNITS "N/A"
                    MAX-ACCESS read-only
                    STATUS current
                    DESCRIPTION "Pressure probe 1 faulty alarm"
                    ::= { digitalObjects 50 }

        -- 1.3.6.1.4.1.9839.2.1.1.51
        mal-pressure2 OBJECT-TYPE
                    SYNTAX Integer32 (0..1)
                    UNITS "N/A"
                    MAX-ACCESS read-only
                    STATUS current
                    DESCRIPTION "Pressure probe 2 faulty alarm"
                    ::= { digitalObjects 51 }

        -- 1.3.6.1.4.1.9839.2.1.1.52
        mal-temp-cond1 OBJECT-TYPE
                    SYNTAX Integer32 (0..1)
                    UNITS "N/A"
                    MAX-ACCESS read-only
                    STATUS current
                    DESCRIPTION "Cond. temp. probe 1 faulty alarm"
                    ::= { digitalObjects 52 }

        -- 1.3.6.1.4.1.9839.2.1.1.53
        mal-temp-cond2 OBJECT-TYPE
                    SYNTAX Integer32 (0..1)
                    UNITS "N/A"
                    MAX-ACCESS read-only
                    STATUS current
                    DESCRIPTION "Cond. temp. probe 2 faulty alarm"
                    ::= { digitalObjects 53 }

        -- 1.3.6.1.4.1.9839.2.1.1.54
        malarm1-1 OBJECT-TYPE
                    SYNTAX Integer32 (0..1)
                    UNITS "N/A"
                    MAX-ACCESS read-only
                    STATUS current
                    DESCRIPTION "High current in humidifier alarm"
                    ::= { digitalObjects 54 }

        -- 1.3.6.1.4.1.9839.2.1.1.55
        malarm1-3 OBJECT-TYPE
                    SYNTAX Integer32 (0..1)
                    UNITS "N/A"
                    MAX-ACCESS read-only
                    STATUS current
                    DESCRIPTION "No water in humidifier alarm"
                    ::= { digitalObjects 55 }

        -- 1.3.6.1.4.1.9839.2.1.1.56
        malarm1-2 OBJECT-TYPE
                    SYNTAX Integer32 (0..1)
                    UNITS "N/A"
                    MAX-ACCESS read-only
                    STATUS current
                    DESCRIPTION "No current in humidifier alarm"
                    ::= { digitalObjects 56 }

        -- 1.3.6.1.4.1.9839.2.1.1.57
        mal-clock OBJECT-TYPE
                    SYNTAX Integer32 (0..1)
                    UNITS "N/A"
                    MAX-ACCESS read-only
                    STATUS current
                    DESCRIPTION "Clock card fault alarm"
                    ::= { digitalObjects 57 }

        -- 1.3.6.1.4.1.9839.2.1.1.58
        mal-high-press1 OBJECT-TYPE
                    SYNTAX Integer32 (0..1)
                    UNITS "N/A"
                    MAX-ACCESS read-only
                    STATUS current
                    DESCRIPTION "High pressure alarm circuit 1"
                    ::= { digitalObjects 58 }

        -- 1.3.6.1.4.1.9839.2.1.1.59
        mal-high-press2 OBJECT-TYPE
                    SYNTAX Integer32 (0..1)
                    UNITS "N/A"
                    MAX-ACCESS read-only
                    STATUS current
                    DESCRIPTION "High pressure alarm circuit 2"
                    ::= { digitalObjects 59 }

        -- 1.3.6.1.4.1.9839.2.1.1.60
        mal-water OBJECT-TYPE
                    SYNTAX Integer32 (0..1)
                    UNITS "N/A"
                    MAX-ACCESS read-only
                    STATUS current
                    DESCRIPTION "Flood alarm"
                    ::= { digitalObjects 60 }

        -- 1.3.6.1.4.1.9839.2.1.1.61
        mal-aux OBJECT-TYPE
                    SYNTAX Integer32 (0..1)
                    UNITS "N/A"
                    MAX-ACCESS read-only
                    STATUS current
                    DESCRIPTION "Auxiliary alarm"
                    ::= { digitalObjects 61 }

        -- 1.3.6.1.4.1.9839.2.1.1.62
        mal-overl-hp-c1 OBJECT-TYPE
                    SYNTAX Integer32 (0..1)
                    UNITS "N/A"
                    MAX-ACCESS read-only
                    STATUS current
                    DESCRIPTION "Thermal cut-out and high pressure alarm, comp. 1"
                    ::= { digitalObjects 62 }

        -- 1.3.6.1.4.1.9839.2.1.1.63
        mal-h-humid OBJECT-TYPE
                    SYNTAX Integer32 (0..1)
                    UNITS "N/A"
                    MAX-ACCESS read-only
                    STATUS current
                    DESCRIPTION "Humid. operating hour threshold alarm"
                    ::= { digitalObjects 63 }

        -- 1.3.6.1.4.1.9839.2.1.1.64
        mal-overl-hp-c2 OBJECT-TYPE
                    SYNTAX Integer32 (0..1)
                    UNITS "N/A"
                    MAX-ACCESS read-only
                    STATUS current
                    DESCRIPTION "Thermal cut-out and high pressure alarm, comp. 2"
                    ::= { digitalObjects 64 }

        -- 1.3.6.1.4.1.9839.2.1.1.65
        mal-cond-fan1 OBJECT-TYPE
                    SYNTAX Integer32 (0..1)
                    UNITS "N/A"
                    MAX-ACCESS read-only
                    STATUS current
                    DESCRIPTION "Condens. 1 fan thermal cut-out alarm"
                    ::= { digitalObjects 65 }

        -- 1.3.6.1.4.1.9839.2.1.1.66
        mal-cond-fan2 OBJECT-TYPE
                    SYNTAX Integer32 (0..1)
                    UNITS "N/A"
                    MAX-ACCESS read-only
                    STATUS current
                    DESCRIPTION "Condens. 2 fan thermal cut-out alarm"
                    ::= { digitalObjects 66 }

        -- 1.3.6.1.4.1.9839.2.1.1.67
        mal-water-flow OBJECT-TYPE
                    SYNTAX Integer32 (0..1)
                    UNITS "N/A"
                    MAX-ACCESS read-only
                    STATUS current
                    DESCRIPTION "Water flow alarm"
                    ::= { digitalObjects 67 }

        -- 1.3.6.1.4.1.9839.2.1.1.69
        comp-and-damper OBJECT-TYPE
                    SYNTAX Integer32 (0..1)
                    UNITS "N/A"
                    MAX-ACCESS read-only
                    STATUS current
                    DESCRIPTION "Enable compressors/cooling coil together with recovery coil"
                    ::= { digitalObjects 69 }

        -- 1.3.6.1.4.1.9839.2.1.1.70
        en-ext-probe OBJECT-TYPE
                    SYNTAX Integer32 (0..1)
                    UNITS "N/A"
                    MAX-ACCESS read-write
                    STATUS current
                    DESCRIPTION "Outside temperature probe enabling"
                    ::= { digitalObjects 70 }

        -- 1.3.6.1.4.1.9839.2.1.1.71
        en-pressure1-probe OBJECT-TYPE
                    SYNTAX Integer32 (0..1)
                    UNITS "N/A"
                    MAX-ACCESS read-write
                    STATUS current
                    DESCRIPTION "Pressure probe 1 enabling"
                    ::= { digitalObjects 71 }

        -- 1.3.6.1.4.1.9839.2.1.1.72
        en-pressure2-probe OBJECT-TYPE
                    SYNTAX Integer32 (0..1)
                    UNITS "N/A"
                    MAX-ACCESS read-write
                    STATUS current
                    DESCRIPTION "Pressure probe 2 enabling"
                    ::= { digitalObjects 72 }

        -- 1.3.6.1.4.1.9839.2.1.1.73
        en-room-humid OBJECT-TYPE
                    SYNTAX Integer32 (0..1)
                    UNITS "N/A"
                    MAX-ACCESS read-write
                    STATUS current
                    DESCRIPTION "Humidity probe enabling"
                    ::= { digitalObjects 73 }

        -- 1.3.6.1.4.1.9839.2.1.1.74
        en-supply-probe OBJECT-TYPE
                    SYNTAX Integer32 (0..1)
                    UNITS "N/A"
                    MAX-ACCESS read-write
                    STATUS current
                    DESCRIPTION "Outlet probe enabling"
                    ::= { digitalObjects 74 }

        -- 1.3.6.1.4.1.9839.2.1.1.75
        en-temp-cond1 OBJECT-TYPE
                    SYNTAX Integer32 (0..1)
                    UNITS "N/A"
                    MAX-ACCESS read-write
                    STATUS current
                    DESCRIPTION "Condenser 1 temp. probe enabling"
                    ::= { digitalObjects 75 }

        -- 1.3.6.1.4.1.9839.2.1.1.76
        en-temp-cond2 OBJECT-TYPE
                    SYNTAX Integer32 (0..1)
                    UNITS "N/A"
                    MAX-ACCESS read-write
                    STATUS current
                    DESCRIPTION "Condenser 2 temp. probe enabling"
                    ::= { digitalObjects 76 }

        -- 1.3.6.1.4.1.9839.2.1.1.77
        en-temp-recovery OBJECT-TYPE
                    SYNTAX Integer32 (0..1)
                    UNITS "N/A"
                    MAX-ACCESS read-write
                    STATUS current
                    DESCRIPTION "Recovery probe enabling"
                    ::= { digitalObjects 77 }

        -- 1.3.6.1.4.1.9839.2.1.1.78
        aout1-ed-conf OBJECT-TYPE
                    SYNTAX Integer32 (0..1)
                    UNITS "N/A"
                    MAX-ACCESS read-write
                    STATUS current
                    DESCRIPTION "Modulating output 1 configuration"
                    ::= { digitalObjects 78 }

        -- 1.3.6.1.4.1.9839.2.1.1.80
        aout2-cw-conf OBJECT-TYPE
                    SYNTAX Integer32 (0..1)
                    UNITS "N/A"
                    MAX-ACCESS read-write
                    STATUS current
                    DESCRIPTION "Modulating output 2 configuration"
                    ::= { digitalObjects 80 }

        -- 1.3.6.1.4.1.9839.2.1.1.81
        dig-inp-1-conf OBJECT-TYPE
                    SYNTAX Integer32 (0..1)
                    UNITS "N/A"
                    MAX-ACCESS read-write
                    STATUS current
                    DESCRIPTION "Digital input 1 configuration"
                    ::= { digitalObjects 81 }

        -- 1.3.6.1.4.1.9839.2.1.1.82
        dig-inp-12-conf OBJECT-TYPE
                    SYNTAX Integer32 (0..1)
                    UNITS "N/A"
                    MAX-ACCESS read-write
                    STATUS current
                    DESCRIPTION "Digital input 12 configuration"
                    ::= { digitalObjects 82 }

        -- 1.3.6.1.4.1.9839.2.1.1.83
        cw-an-main-fan OBJECT-TYPE
                    SYNTAX Integer32 (0..1)
                    UNITS "N/A"
                    MAX-ACCESS read-write
                    STATUS current
                    DESCRIPTION "Modulating outlet fan enabling"
                    ::= { digitalObjects 83 }

        -- 1.3.6.1.4.1.9839.2.1.1.84
        heating-mode OBJECT-TYPE
                    SYNTAX Integer32 (0..1)
                    UNITS "N/A"
                    MAX-ACCESS read-write
                    STATUS current
                    DESCRIPTION "Heating mode"
                    ::= { digitalObjects 84 }

        -- 1.3.6.1.4.1.9839.2.1.1.85
        valve-type OBJECT-TYPE
                    SYNTAX Integer32 (0..1)
                    UNITS "N/A"
                    MAX-ACCESS read-write
                    STATUS current
                    DESCRIPTION "Type of valve on cooling coil"
                    ::= { digitalObjects 85 }

        -- 1.3.6.1.4.1.9839.2.1.1.86
        valve-heat-type OBJECT-TYPE
                    SYNTAX Integer32 (0..1)
                    UNITS "N/A"
                    MAX-ACCESS read-write
                    STATUS current
                    DESCRIPTION "Type of valve on heating coil"
                    ::= { digitalObjects 86 }

        -- 1.3.6.1.4.1.9839.2.1.1.87
        damper-humid OBJECT-TYPE
                    SYNTAX Integer32 (0..1)
                    UNITS "N/A"
                    MAX-ACCESS read-write
                    STATUS current
                    DESCRIPTION "Modulating 0 to 10 V humidifier enabling"
                    ::= { digitalObjects 87 }

        -- 1.3.6.1.4.1.9839.2.1.1.88
        battery-number OBJECT-TYPE
                    SYNTAX Integer32 (0..1)
                    UNITS "N/A"
                    MAX-ACCESS read-write
                    STATUS current
                    DESCRIPTION "Type of coil on main unit CW"
                    ::= { digitalObjects 88 }

        -- 1.3.6.1.4.1.9839.2.1.1.89
        cond-config OBJECT-TYPE
                    SYNTAX Integer32 (0..1)
                    UNITS "N/A"
                    MAX-ACCESS read-write
                    STATUS current
                    DESCRIPTION "Type of condenser"
                    ::= { digitalObjects 89 }

        -- 1.3.6.1.4.1.9839.2.1.1.90
        cond-outp-mode OBJECT-TYPE
                    SYNTAX Integer32 (0..1)
                    UNITS "N/A"
                    MAX-ACCESS read-write
                    STATUS current
                    DESCRIPTION "Select type of fans"
                    ::= { digitalObjects 90 }

        -- 1.3.6.1.4.1.9839.2.1.1.91
        enable-cond OBJECT-TYPE
                    SYNTAX Integer32 (0..1)
                    UNITS "N/A"
                    MAX-ACCESS read-write
                    STATUS current
                    DESCRIPTION "Condenser function enabling"
                    ::= { digitalObjects 91 }

        -- 1.3.6.1.4.1.9839.2.1.1.92
        enable-prevent OBJECT-TYPE
                    SYNTAX Integer32 (0..1)
                    UNITS "N/A"
                    MAX-ACCESS read-write
                    STATUS current
                    DESCRIPTION "High press. prevent function enabling"
                    ::= { digitalObjects 92 }

        -- 1.3.6.1.4.1.9839.2.1.1.93
        abil-supply-limit OBJECT-TYPE
                    SYNTAX Integer32 (0..1)
                    UNITS "N/A"
                    MAX-ACCESS read-write
                    STATUS current
                    DESCRIPTION "Outlet limit function enabling"
                    ::= { digitalObjects 93 }

        -- 1.3.6.1.4.1.9839.2.1.1.94
        en-compensation OBJECT-TYPE
                    SYNTAX Integer32 (0..1)
                    UNITS "N/A"
                    MAX-ACCESS read-write
                    STATUS current
                    DESCRIPTION "Compensation function enabling"
                    ::= { digitalObjects 94 }

        -- 1.3.6.1.4.1.9839.2.1.1.95
        en-dehum-valve OBJECT-TYPE
                    SYNTAX Integer32 (0..1)
                    UNITS "N/A"
                    MAX-ACCESS read-write
                    STATUS current
                    DESCRIPTION "Cooling coil for dehumidify enabling"
                    ::= { digitalObjects 95 }

        -- 1.3.6.1.4.1.9839.2.1.1.96
        en-rec-valve OBJECT-TYPE
                    SYNTAX Integer32 (0..1)
                    UNITS "N/A"
                    MAX-ACCESS read-write
                    STATUS current
                    DESCRIPTION "Recovery coil enabling"
                    ::= { digitalObjects 96 }

        -- 1.3.6.1.4.1.9839.2.1.1.97
        logic-dehumid OBJECT-TYPE
                    SYNTAX Integer32 (0..1)
                    UNITS "N/A"
                    MAX-ACCESS read-write
                    STATUS current
                    DESCRIPTION "Dehumidify contact logic"
                    ::= { digitalObjects 97 }

        -- 1.3.6.1.4.1.9839.2.1.1.98
        en-rotation OBJECT-TYPE
                    SYNTAX Integer32 (0..1)
                    UNITS "N/A"
                    MAX-ACCESS read-write
                    STATUS current
                    DESCRIPTION "FIFO compressor rotation enabling"
                    ::= { digitalObjects 98 }

        -- 1.3.6.1.4.1.9839.2.1.1.99
        en-unloader OBJECT-TYPE
                    SYNTAX Integer32 (0..1)
                    UNITS "N/A"
                    MAX-ACCESS read-write
                    STATUS current
                    DESCRIPTION "Compressor capacity-control steps enabling"
                    ::= { digitalObjects 99 }

        -- 1.3.6.1.4.1.9839.2.1.1.100
        logic-unloader OBJECT-TYPE
                    SYNTAX Integer32 (0..1)
                    UNITS "N/A"
                    MAX-ACCESS read-write
                    STATUS current
                    DESCRIPTION "Cap. control contact logic"
                    ::= { digitalObjects 100 }

        -- 1.3.6.1.4.1.9839.2.1.1.101
        reg-type-temp OBJECT-TYPE
                    SYNTAX Integer32 (0..1)
                    UNITS "N/A"
                    MAX-ACCESS read-write
                    STATUS current
                    DESCRIPTION "Type of temperature control"
                    ::= { digitalObjects 101 }

        -- 1.3.6.1.4.1.9839.2.1.1.102
        en-integr-humid OBJECT-TYPE
                    SYNTAX Integer32 (0..1)
                    UNITS "N/A"
                    MAX-ACCESS read-write
                    STATUS current
                    DESCRIPTION "Built-in humidifier enabling"
                    ::= { digitalObjects 102 }

        -- 1.3.6.1.4.1.9839.2.1.1.105
        mst-cntrl-en OBJECT-TYPE
                    SYNTAX Integer32 (0..1)
                    UNITS "N/A"
                    MAX-ACCESS read-write
                    STATUS current
                    DESCRIPTION "CAREL master control enabling"
                    ::= { digitalObjects 105 }

        -- 1.3.6.1.4.1.9839.2.1.1.106
        abil-force-sleep OBJECT-TYPE
                    SYNTAX Integer32 (0..1)
                    UNITS "N/A"
                    MAX-ACCESS read-write
                    STATUS current
                    DESCRIPTION "Units in pLAN forcing enabling"
                    ::= { digitalObjects 106 }

        -- 1.3.6.1.4.1.9839.2.1.1.107
        on-off-timezones OBJECT-TYPE
                    SYNTAX Integer32 (0..1)
                    UNITS "N/A"
                    MAX-ACCESS read-write
                    STATUS current
                    DESCRIPTION "ON/OFF time bands enabling"
                    ::= { digitalObjects 107 }

        -- 1.3.6.1.4.1.9839.2.1.1.108
        en-time-zones-t OBJECT-TYPE
                    SYNTAX Integer32 (0..1)
                    UNITS "N/A"
                    MAX-ACCESS read-write
                    STATUS current
                    DESCRIPTION "Temperature time bands enabling"
                    ::= { digitalObjects 108 }

        -- 1.3.6.1.4.1.9839.2.1.1.109
        en-time-zones-h OBJECT-TYPE
                    SYNTAX Integer32 (0..1)
                    UNITS "N/A"
                    MAX-ACCESS read-write
                    STATUS current
                    DESCRIPTION "Humidity time bands enabling"
                    ::= { digitalObjects 109 }

        -- 1.3.6.1.4.1.9839.2.1.1.110
        en-off-unit OBJECT-TYPE
                    SYNTAX Integer32 (0..1)
                    UNITS "N/A"
                    MAX-ACCESS read-write
                    STATUS current
                    DESCRIPTION "Unit OFF from button enabling"
                    ::= { digitalObjects 110 }

        -- 1.3.6.1.4.1.9839.2.1.1.111
        en-rem-on-off OBJECT-TYPE
                    SYNTAX Integer32 (0..1)
                    UNITS "N/A"
                    MAX-ACCESS read-write
                    STATUS current
                    DESCRIPTION "Remote ON/OFF digital input enabling"
                    ::= { digitalObjects 111 }

        -- 1.3.6.1.4.1.9839.2.1.1.112
        on-off-boss OBJECT-TYPE
                    SYNTAX Integer32 (0..1)
                    UNITS "N/A"
                    MAX-ACCESS read-write
                    STATUS current
                    DESCRIPTION "Unit ON/OFF from supervisor"
                    ::= { digitalObjects 112 }

        -- 1.3.6.1.4.1.9839.2.1.1.113
        double-alarms OBJECT-TYPE
                    SYNTAX Integer32 (0..1)
                    UNITS "N/A"
                    MAX-ACCESS read-write
                    STATUS current
                    DESCRIPTION "Digital output 7 configuration"
                    ::= { digitalObjects 113 }

        -- 1.3.6.1.4.1.9839.2.1.1.114
        celsius-fahr OBJECT-TYPE
                    SYNTAX Integer32 (0..1)
                    UNITS "N/A"
                    MAX-ACCESS read-write
                    STATUS current
                    DESCRIPTION "Select type of unit measure"
                    ::= { digitalObjects 114 }

        -- 1.3.6.1.4.1.9839.2.1.1.115
        en-clock OBJECT-TYPE
                    SYNTAX Integer32 (0..1)
                    UNITS "N/A"
                    MAX-ACCESS read-write
                    STATUS current
                    DESCRIPTION "Clock card (pCO1) enabling"
                    ::= { digitalObjects 115 }

        -- 1.3.6.1.4.1.9839.2.1.1.116
        en-printer OBJECT-TYPE
                    SYNTAX Integer32 (0..1)
                    UNITS "N/A"
                    MAX-ACCESS read-write
                    STATUS current
                    DESCRIPTION "Printer enabling"
                    ::= { digitalObjects 116 }

        -- 1.3.6.1.4.1.9839.2.1.1.117
        ch-hour OBJECT-TYPE
                    SYNTAX Integer32 (0..1)
                    UNITS "N/A"
                    MAX-ACCESS read-write
                    STATUS current
                    DESCRIPTION "Confirm hour setting"
                    ::= { digitalObjects 117 }

        -- 1.3.6.1.4.1.9839.2.1.1.118
        ch-minute OBJECT-TYPE
                    SYNTAX Integer32 (0..1)
                    UNITS "N/A"
                    MAX-ACCESS read-write
                    STATUS current
                    DESCRIPTION "Confirm minute setting"
                    ::= { digitalObjects 118 }

        -- 1.3.6.1.4.1.9839.2.1.1.119
        ch-day OBJECT-TYPE
                    SYNTAX Integer32 (0..1)
                    UNITS "N/A"
                    MAX-ACCESS read-write
                    STATUS current
                    DESCRIPTION "Confirm day setting"
                    ::= { digitalObjects 119 }

        -- 1.3.6.1.4.1.9839.2.1.1.120
        ch-month OBJECT-TYPE
                    SYNTAX Integer32 (0..1)
                    UNITS "N/A"
                    MAX-ACCESS read-write
                    STATUS current
                    DESCRIPTION "Confirm month setting"
                    ::= { digitalObjects 120 }

        -- 1.3.6.1.4.1.9839.2.1.1.121
        ch-year OBJECT-TYPE
                    SYNTAX Integer32 (0..1)
                    UNITS "N/A"
                    MAX-ACCESS read-write
                    STATUS current
                    DESCRIPTION "Confirm year setting"
                    ::= { digitalObjects 121 }

        -- 1.3.6.1.4.1.9839.2.1.1.123
        res-al-by-bms OBJECT-TYPE
                    SYNTAX Integer32 (0..1)
                    UNITS "N/A"
                    MAX-ACCESS read-write
                    STATUS current
                    DESCRIPTION "Reset alarms from supervisor"
                    ::= { digitalObjects 123 }



        -- 1.3.6.1.4.1.9839.2.1.2
        analogObjects OBJECT IDENTIFIER ::= { std-air-condMIB 2 }

        -- 1.3.6.1.4.1.9839.2.1.2.1
        room-humid OBJECT-TYPE
                    SYNTAX Integer32 (-32767..32767)
                    UNITS "% x10"
                    MAX-ACCESS read-only
                    STATUS current
                    DESCRIPTION "Room humidity probe reading"
                    ::= { analogObjects 1 }

        -- 1.3.6.1.4.1.9839.2.1.2.2
        pressure1 OBJECT-TYPE
                    SYNTAX Integer32 (-32767..32767)
                    UNITS "bar x10"
                    MAX-ACCESS read-only
                    STATUS current
                    DESCRIPTION "Pressure probe 1 reading"
                    ::= { analogObjects 2 }

        -- 1.3.6.1.4.1.9839.2.1.2.3
        pressure2 OBJECT-TYPE
                    SYNTAX Integer32 (-32767..32767)
                    UNITS "bar x10"
                    MAX-ACCESS read-only
                    STATUS current
                    DESCRIPTION "Pressure probe 2 reading"
                    ::= { analogObjects 3 }

        -- 1.3.6.1.4.1.9839.2.1.2.4
        room-temp OBJECT-TYPE
                    SYNTAX Integer32 (-32767..32767)
                    UNITS "C/F x10"
                    MAX-ACCESS read-only
                    STATUS current
                    DESCRIPTION "Room temperature probe reading"
                    ::= { analogObjects 4 }

        -- 1.3.6.1.4.1.9839.2.1.2.5
        supply-air-temp OBJECT-TYPE
                    SYNTAX Integer32 (-32767..32767)
                    UNITS "C/F x10"
                    MAX-ACCESS read-only
                    STATUS current
                    DESCRIPTION "Air outlet temperature probe reading"
                    ::= { analogObjects 5 }

        -- 1.3.6.1.4.1.9839.2.1.2.6
        ext-air-temp OBJECT-TYPE
                    SYNTAX Integer32 (-32767..32767)
                    UNITS "C/F x10"
                    MAX-ACCESS read-only
                    STATUS current
                    DESCRIPTION "Outside temperature probe reading"
                    ::= { analogObjects 6 }

        -- 1.3.6.1.4.1.9839.2.1.2.7
        temp-cond1 OBJECT-TYPE
                    SYNTAX Integer32 (-32767..32767)
                    UNITS "C/F x10"
                    MAX-ACCESS read-only
                    STATUS current
                    DESCRIPTION "Cond. 1 temperature probe reading"
                    ::= { analogObjects 7 }

        -- 1.3.6.1.4.1.9839.2.1.2.8
        temp-cond2 OBJECT-TYPE
                    SYNTAX Integer32 (-32767..32767)
                    UNITS "C/F x10"
                    MAX-ACCESS read-only
                    STATUS current
                    DESCRIPTION "Cond. 2 temperature probe reading"
                    ::= { analogObjects 8 }

        -- 1.3.6.1.4.1.9839.2.1.2.9
        recovery-temp OBJECT-TYPE
                    SYNTAX Integer32 (-32767..32767)
                    UNITS "C/F x10"
                    MAX-ACCESS read-only
                    STATUS current
                    DESCRIPTION "Water recovery temperature reading"
                    ::= { analogObjects 9 }

        -- 1.3.6.1.4.1.9839.2.1.2.10
        sel-set-temp OBJECT-TYPE
                    SYNTAX Integer32 (-32767..32767)
                    UNITS "C/F x10"
                    MAX-ACCESS read-write
                    STATUS current
                    DESCRIPTION "Temperature set point"
                    DEFVAL { 230 }
                    ::= { analogObjects 10 }

        -- 1.3.6.1.4.1.9839.2.1.2.11
        lim-min-set-t OBJECT-TYPE
                    SYNTAX Integer32 (-9999..9999)
                    UNITS "C/F x10"
                    MAX-ACCESS read-write
                    STATUS current
                    DESCRIPTION "Minimum temperature set point limit"
                    DEFVAL { -999 }
                    ::= { analogObjects 11 }

        -- 1.3.6.1.4.1.9839.2.1.2.12
        lim-max-set-t OBJECT-TYPE
                    SYNTAX Integer32 (-9999..9999)
                    UNITS "C/F x10"
                    MAX-ACCESS read-write
                    STATUS current
                    DESCRIPTION "Maximum temperature set point limit"
                    DEFVAL { 999 }
                    ::= { analogObjects 12 }

        -- 1.3.6.1.4.1.9839.2.1.2.13
        sel-set-humid OBJECT-TYPE
                    SYNTAX Integer32 (-32767..32767)
                    UNITS "% x10"
                    MAX-ACCESS read-write
                    STATUS current
                    DESCRIPTION "Humidity set point"
                    DEFVAL { 500 }
                    ::= { analogObjects 13 }

        -- 1.3.6.1.4.1.9839.2.1.2.14
        lim-min-set-h OBJECT-TYPE
                    SYNTAX Integer32 (-9999..9999)
                    UNITS "% x10"
                    MAX-ACCESS read-write
                    STATUS current
                    DESCRIPTION "Minimum humidity set point limit"
                    DEFVAL { -999 }
                    ::= { analogObjects 14 }

        -- 1.3.6.1.4.1.9839.2.1.2.15
        lim-max-set-h OBJECT-TYPE
                    SYNTAX Integer32 (0..9999)
                    UNITS "% x10"
                    MAX-ACCESS read-write
                    STATUS current
                    DESCRIPTION "Maximum humidity set point limit"
                    DEFVAL { 999 }
                    ::= { analogObjects 15 }

        -- 1.3.6.1.4.1.9839.2.1.2.16
        set-temp1 OBJECT-TYPE
                    SYNTAX Integer32 (-32767..32767)
                    UNITS "C/F x10"
                    MAX-ACCESS read-write
                    STATUS current
                    DESCRIPTION "Temperature time band set point Z1"
                    ::= { analogObjects 16 }

        -- 1.3.6.1.4.1.9839.2.1.2.17
        set-temp2 OBJECT-TYPE
                    SYNTAX Integer32 (-32767..32767)
                    UNITS "C/F x10"
                    MAX-ACCESS read-write
                    STATUS current
                    DESCRIPTION "Temperature time band set point Z2"
                    ::= { analogObjects 17 }

        -- 1.3.6.1.4.1.9839.2.1.2.18
        set-temp3 OBJECT-TYPE
                    SYNTAX Integer32 (-32767..32767)
                    UNITS "C/F x10"
                    MAX-ACCESS read-write
                    STATUS current
                    DESCRIPTION "Temperature time band set point Z3"
                    ::= { analogObjects 18 }

        -- 1.3.6.1.4.1.9839.2.1.2.19
        set-temp4 OBJECT-TYPE
                    SYNTAX Integer32 (-32767..32767)
                    UNITS "C/F x10"
                    MAX-ACCESS read-write
                    STATUS current
                    DESCRIPTION "Temperature time band set point Z4"
                    ::= { analogObjects 19 }

        -- 1.3.6.1.4.1.9839.2.1.2.20
        set-humid1 OBJECT-TYPE
                    SYNTAX Integer32 (-32767..32767)
                    UNITS "% x10"
                    MAX-ACCESS read-write
                    STATUS current
                    DESCRIPTION "Humidity time band set point Z1"
                    ::= { analogObjects 20 }

        -- 1.3.6.1.4.1.9839.2.1.2.21
        set-humid2 OBJECT-TYPE
                    SYNTAX Integer32 (-32767..32767)
                    UNITS "% x10"
                    MAX-ACCESS read-write
                    STATUS current
                    DESCRIPTION "Humidity time band set point Z2"
                    ::= { analogObjects 21 }

        -- 1.3.6.1.4.1.9839.2.1.2.22
        set-humid3 OBJECT-TYPE
                    SYNTAX Integer32 (-32767..32767)
                    UNITS "% x10"
                    MAX-ACCESS read-write
                    STATUS current
                    DESCRIPTION "Humidity time band set point Z3"
                    ::= { analogObjects 22 }

        -- 1.3.6.1.4.1.9839.2.1.2.23
        set-humid4 OBJECT-TYPE
                    SYNTAX Integer32 (-32767..32767)
                    UNITS "% x10"
                    MAX-ACCESS read-write
                    STATUS current
                    DESCRIPTION "Humidity time band set point Z4"
                    ::= { analogObjects 23 }

        -- 1.3.6.1.4.1.9839.2.1.2.24
        dead-zone-temp OBJECT-TYPE
                    SYNTAX Integer32 (0..999)
                    UNITS "C/F x10"
                    MAX-ACCESS read-write
                    STATUS current
                    DESCRIPTION "Temperature dead zone"
                    DEFVAL { 5 }
                    ::= { analogObjects 24 }

        -- 1.3.6.1.4.1.9839.2.1.2.25
        diff-temp-cold OBJECT-TYPE
                    SYNTAX Integer32 (0..1000)
                    UNITS "C/F x10"
                    MAX-ACCESS read-write
                    STATUS current
                    DESCRIPTION "Proportional band in cooling"
                    DEFVAL { 30 }
                    ::= { analogObjects 25 }

        -- 1.3.6.1.4.1.9839.2.1.2.26
        diff-temp-hot OBJECT-TYPE
                    SYNTAX Integer32 (0..1000)
                    UNITS "C/F x10"
                    MAX-ACCESS read-write
                    STATUS current
                    DESCRIPTION "Proportional band in heating"
                    DEFVAL { 30 }
                    ::= { analogObjects 26 }

        -- 1.3.6.1.4.1.9839.2.1.2.27
        diff-humid OBJECT-TYPE
                    SYNTAX Integer32 (0..999)
                    UNITS "% x10"
                    MAX-ACCESS read-write
                    STATUS current
                    DESCRIPTION "Proportional band in humidification"
                    DEFVAL { 20 }
                    ::= { analogObjects 27 }

        -- 1.3.6.1.4.1.9839.2.1.2.28
        diff-dehumid OBJECT-TYPE
                    SYNTAX Integer32 (0..999)
                    UNITS "% x10"
                    MAX-ACCESS read-write
                    STATUS current
                    DESCRIPTION "Proportional band in dehumidification"
                    DEFVAL { 20 }
                    ::= { analogObjects 28 }

        -- 1.3.6.1.4.1.9839.2.1.2.29
        delta-setpoint OBJECT-TYPE
                    SYNTAX Integer32 (-9999..9999)
                    UNITS "C/F x10"
                    MAX-ACCESS read-write
                    STATUS current
                    DESCRIPTION "Maximum compensation set temp. offset"
                    DEFVAL { 20 }
                    ::= { analogObjects 29 }

        -- 1.3.6.1.4.1.9839.2.1.2.30
        ext-air-cal OBJECT-TYPE
                    SYNTAX Integer32 (-999..999)
                    UNITS "C/F x10"
                    MAX-ACCESS read-write
                    STATUS current
                    DESCRIPTION "Outside temperature probe calibration"
                    DEFVAL { 0 }
                    ::= { analogObjects 30 }

        -- 1.3.6.1.4.1.9839.2.1.2.31
        pressure1-cal OBJECT-TYPE
                    SYNTAX Integer32 (-99..99)
                    UNITS "bar x10"
                    MAX-ACCESS read-write
                    STATUS current
                    DESCRIPTION "Condens. 1 pressure probe calibration"
                    DEFVAL { 0 }
                    ::= { analogObjects 31 }

        -- 1.3.6.1.4.1.9839.2.1.2.32
        pressure2-cal OBJECT-TYPE
                    SYNTAX Integer32 (-99..99)
                    UNITS "bar x10"
                    MAX-ACCESS read-write
                    STATUS current
                    DESCRIPTION "Condens. 2 pressure probe calibration"
                    DEFVAL { 0 }
                    ::= { analogObjects 32 }

        -- 1.3.6.1.4.1.9839.2.1.2.33
        room-humid-cal OBJECT-TYPE
                    SYNTAX Integer32 (-99..99)
                    UNITS "% x10"
                    MAX-ACCESS read-write
                    STATUS current
                    DESCRIPTION "Humidity probe calibration"
                    DEFVAL { 0 }
                    ::= { analogObjects 33 }

        -- 1.3.6.1.4.1.9839.2.1.2.34
        room-temp-cal OBJECT-TYPE
                    SYNTAX Integer32 (-999..999)
                    UNITS "C/F x10"
                    MAX-ACCESS read-write
                    STATUS current
                    DESCRIPTION "Room temperature probe calibration"
                    DEFVAL { 0 }
                    ::= { analogObjects 34 }

        -- 1.3.6.1.4.1.9839.2.1.2.35
        supply-air-cal OBJECT-TYPE
                    SYNTAX Integer32 (-999..999)
                    UNITS "C/F x10"
                    MAX-ACCESS read-write
                    STATUS current
                    DESCRIPTION "Outlet temperature probe calibration"
                    DEFVAL { 0 }
                    ::= { analogObjects 35 }

        -- 1.3.6.1.4.1.9839.2.1.2.36
        temp-cond1-cal OBJECT-TYPE
                    SYNTAX Integer32 (-999..999)
                    UNITS "C/F x10"
                    MAX-ACCESS read-write
                    STATUS current
                    DESCRIPTION "Condens. 1 temperature probe calibration"
                    DEFVAL { 0 }
                    ::= { analogObjects 36 }

        -- 1.3.6.1.4.1.9839.2.1.2.37
        temp-cond2-cal OBJECT-TYPE
                    SYNTAX Integer32 (-999..999)
                    UNITS "C/F x10"
                    MAX-ACCESS read-write
                    STATUS current
                    DESCRIPTION "Condens. 2 temperature probe calibration"
                    DEFVAL { 0 }
                    ::= { analogObjects 37 }

        -- 1.3.6.1.4.1.9839.2.1.2.38
        temp-rec-cal OBJECT-TYPE
                    SYNTAX Integer32 (-999..999)
                    UNITS "C/F x10"
                    MAX-ACCESS read-write
                    STATUS current
                    DESCRIPTION "Recovery temperature probe calibration"
                    DEFVAL { 0 }
                    ::= { analogObjects 38 }

        -- 1.3.6.1.4.1.9839.2.1.2.39
        diff-low-limit OBJECT-TYPE
                    SYNTAX Integer32 (0..9999)
                    UNITS "C/F x10"
                    MAX-ACCESS read-write
                    STATUS current
                    DESCRIPTION "Stop dehumidification temperature differential"
                    DEFVAL { 50 }
                    ::= { analogObjects 39 }

        -- 1.3.6.1.4.1.9839.2.1.2.40
        diff-supply-lim OBJECT-TYPE
                    SYNTAX Integer32 (0..9999)
                    UNITS "C/F x10"
                    MAX-ACCESS read-write
                    STATUS current
                    DESCRIPTION "Air outlet differential"
                    DEFVAL { 50 }
                    ::= { analogObjects 40 }

        -- 1.3.6.1.4.1.9839.2.1.2.41
        differ-ext OBJECT-TYPE
                    SYNTAX Integer32 (-9999..9999)
                    UNITS "C/F x10"
                    MAX-ACCESS read-write
                    STATUS current
                    DESCRIPTION "Outside air differential for compensation"
                    DEFVAL { 30 }
                    ::= { analogObjects 41 }

        -- 1.3.6.1.4.1.9839.2.1.2.42
        diff-hp-cond OBJECT-TYPE
                    SYNTAX Integer32 (-999..999)
                    UNITS "bar x10"
                    MAX-ACCESS read-write
                    STATUS current
                    DESCRIPTION "High pressure alarm differential"
                    DEFVAL { 10 }
                    ::= { analogObjects 42 }

        -- 1.3.6.1.4.1.9839.2.1.2.43
        fans-differ OBJECT-TYPE
                    SYNTAX Integer32 (-999..999)
                    UNITS "bar x10"
                    MAX-ACCESS read-write
                    STATUS current
                    DESCRIPTION "Condensing (pressure) differential"
                    DEFVAL { 20 }
                    ::= { analogObjects 43 }

        -- 1.3.6.1.4.1.9839.2.1.2.44
        fans-differ-t OBJECT-TYPE
                    SYNTAX Integer32 (-9999..9999)
                    UNITS "C/F x10"
                    MAX-ACCESS read-write
                    STATUS current
                    DESCRIPTION "Condensing (temperature) differential"
                    DEFVAL { 10 }
                    ::= { analogObjects 44 }

        -- 1.3.6.1.4.1.9839.2.1.2.45
        fans-max-speed OBJECT-TYPE
                    SYNTAX Integer32 (0..100)
                    UNITS "V x10"
                    MAX-ACCESS read-write
                    STATUS current
                    DESCRIPTION "Max condenser fan speed"
                    DEFVAL { 100 }
                    ::= { analogObjects 45 }

        -- 1.3.6.1.4.1.9839.2.1.2.46
        fans-min-speed OBJECT-TYPE
                    SYNTAX Integer32 (0..100)
                    UNITS "V x10"
                    MAX-ACCESS read-write
                    STATUS current
                    DESCRIPTION "Min condenser fan speed"
                    DEFVAL { 0 }
                    ::= { analogObjects 46 }

        -- 1.3.6.1.4.1.9839.2.1.2.47
        fans-setpoint OBJECT-TYPE
                    SYNTAX Integer32 (-9999..9999)
                    UNITS "bar x10"
                    MAX-ACCESS read-write
                    STATUS current
                    DESCRIPTION "Condensing (pressure) set point"
                    DEFVAL { 40 }
                    ::= { analogObjects 47 }

        -- 1.3.6.1.4.1.9839.2.1.2.48
        fans-setpoint-t OBJECT-TYPE
                    SYNTAX Integer32 (-9999..9999)
                    UNITS "C/F x10"
                    MAX-ACCESS read-write
                    STATUS current
                    DESCRIPTION "Condensing (temperature) set point"
                    DEFVAL { 550 }
                    ::= { analogObjects 48 }

        -- 1.3.6.1.4.1.9839.2.1.2.49
        force-diff-high OBJECT-TYPE
                    SYNTAX Integer32 (0..999)
                    UNITS "C/F x10"
                    MAX-ACCESS read-write
                    STATUS current
                    DESCRIPTION "Force unit by high temperature differential"
                    DEFVAL { 40 }
                    ::= { analogObjects 49 }

        -- 1.3.6.1.4.1.9839.2.1.2.50
        force-diff-low OBJECT-TYPE
                    SYNTAX Integer32 (0..999)
                    UNITS "C/F x10"
                    MAX-ACCESS read-write
                    STATUS current
                    DESCRIPTION "Force unit by low temperature differential"
                    DEFVAL { 40 }
                    ::= { analogObjects 50 }

        -- 1.3.6.1.4.1.9839.2.1.2.51
        force-offset-high OBJECT-TYPE
                    SYNTAX Integer32 (0..999)
                    UNITS "C/F x10"
                    MAX-ACCESS read-write
                    STATUS current
                    DESCRIPTION "High temperature set point to force unit"
                    DEFVAL { 80 }
                    ::= { analogObjects 51 }

        -- 1.3.6.1.4.1.9839.2.1.2.52
        force-offset-low OBJECT-TYPE
                    SYNTAX Integer32 (0..999)
                    UNITS "C/F x10"
                    MAX-ACCESS read-write
                    STATUS current
                    DESCRIPTION "Low temperature set point to force unit"
                    DEFVAL { 80 }
                    ::= { analogObjects 52 }

        -- 1.3.6.1.4.1.9839.2.1.2.53
        high-room-temp OBJECT-TYPE
                    SYNTAX Integer32 (-9999..9999)
                    UNITS "C/F x10"
                    MAX-ACCESS read-write
                    STATUS current
                    DESCRIPTION "High ambient temperature alarm offset"
                    DEFVAL { 100 }
                    ::= { analogObjects 53 }

        -- 1.3.6.1.4.1.9839.2.1.2.54
        low-room-temp OBJECT-TYPE
                    SYNTAX Integer32 (-9999..9999)
                    UNITS "C/F x10"
                    MAX-ACCESS read-write
                    STATUS current
                    DESCRIPTION "Low ambient temperature alarm offset"
                    DEFVAL { 100 }
                    ::= { analogObjects 54 }

        -- 1.3.6.1.4.1.9839.2.1.2.55
        high-room-humid OBJECT-TYPE
                    SYNTAX Integer32 (0..1000)
                    UNITS "% x10"
                    MAX-ACCESS read-write
                    STATUS current
                    DESCRIPTION "High ambient humidity alarm offset"
                    DEFVAL { 300 }
                    ::= { analogObjects 55 }

        -- 1.3.6.1.4.1.9839.2.1.2.56
        low-room-humid OBJECT-TYPE
                    SYNTAX Integer32 (0..1000)
                    UNITS "% x10"
                    MAX-ACCESS read-write
                    STATUS current
                    DESCRIPTION "Low ambient humidity alarm offset"
                    DEFVAL { 200 }
                    ::= { analogObjects 56 }

        -- 1.3.6.1.4.1.9839.2.1.2.57
        lim-max-mainfan OBJECT-TYPE
                    SYNTAX Integer32 (0..100)
                    UNITS "V x10"
                    MAX-ACCESS read-write
                    STATUS current
                    DESCRIPTION "Analog humidifier max. voltage"
                    DEFVAL { 100 }
                    ::= { analogObjects 57 }

        -- 1.3.6.1.4.1.9839.2.1.2.58
        lim-min-mainfan OBJECT-TYPE
                    SYNTAX Integer32 (0..100)
                    UNITS "V x10"
                    MAX-ACCESS read-write
                    STATUS current
                    DESCRIPTION "Analog humidifier min. voltage"
                    DEFVAL { 50 }
                    ::= { analogObjects 58 }

        -- 1.3.6.1.4.1.9839.2.1.2.59
        max-prod OBJECT-TYPE
                    SYNTAX Integer32 (0..1000)
                    UNITS "% x10"
                    MAX-ACCESS read-write
                    STATUS current
                    DESCRIPTION "Maximum humidifier production"
                    DEFVAL { 700 }
                    ::= { analogObjects 59 }

        -- 1.3.6.1.4.1.9839.2.1.2.60
        max-speed-hum OBJECT-TYPE
                    SYNTAX Integer32 (0..100)
                    UNITS "V x10"
                    MAX-ACCESS read-write
                    STATUS current
                    DESCRIPTION "Maximum outlet fan speed"
                    DEFVAL { 100 }
                    ::= { analogObjects 60 }

        -- 1.3.6.1.4.1.9839.2.1.2.61
        min-speed-hum OBJECT-TYPE
                    SYNTAX Integer32 (0..100)
                    UNITS "V x10"
                    MAX-ACCESS read-write
                    STATUS current
                    DESCRIPTION "Minimum outlet fan speed"
                    DEFVAL { 0 }
                    ::= { analogObjects 61 }

        -- 1.3.6.1.4.1.9839.2.1.2.62
        max-value-humid OBJECT-TYPE
                    SYNTAX Integer32 (0..1000)
                    UNITS "% x10"
                    MAX-ACCESS read-write
                    STATUS current
                    DESCRIPTION "Maximum value humidity probe"
                    DEFVAL { 1000 }
                    ::= { analogObjects 62 }

        -- 1.3.6.1.4.1.9839.2.1.2.63
        min-value-humid OBJECT-TYPE
                    SYNTAX Integer32 (0..1000)
                    UNITS "% x10"
                    MAX-ACCESS read-write
                    STATUS current
                    DESCRIPTION "Minimum value humidity probe"
                    DEFVAL { 0 }
                    ::= { analogObjects 63 }

        -- 1.3.6.1.4.1.9839.2.1.2.64
        max-value-pressure1 OBJECT-TYPE
                    SYNTAX Integer32 (-200..500)
                    UNITS "bar x10"
                    MAX-ACCESS read-write
                    STATUS current
                    DESCRIPTION "Maximum value pressure probe 1"
                    DEFVAL { 300 }
                    ::= { analogObjects 64 }

        -- 1.3.6.1.4.1.9839.2.1.2.65
        min-value-pressure1 OBJECT-TYPE
                    SYNTAX Integer32 (-200..500)
                    UNITS "bar x10"
                    MAX-ACCESS read-write
                    STATUS current
                    DESCRIPTION "Minimum value pressure probe 1"
                    DEFVAL { 0 }
                    ::= { analogObjects 65 }

        -- 1.3.6.1.4.1.9839.2.1.2.66
        max-value-pressure2 OBJECT-TYPE
                    SYNTAX Integer32 (-200..500)
                    UNITS "bar x10"
                    MAX-ACCESS read-write
                    STATUS current
                    DESCRIPTION "Maximum value pressure probe 2"
                    DEFVAL { 300 }
                    ::= { analogObjects 66 }

        -- 1.3.6.1.4.1.9839.2.1.2.67
        min-value-pressure2 OBJECT-TYPE
                    SYNTAX Integer32 (-200..500)
                    UNITS "bar x10"
                    MAX-ACCESS read-write
                    STATUS current
                    DESCRIPTION "Minimum value pressure probe 2"
                    DEFVAL { 0 }
                    ::= { analogObjects 67 }

        -- 1.3.6.1.4.1.9839.2.1.2.68
        offs-low-limit OBJECT-TYPE
                    SYNTAX Integer32 (0..999)
                    UNITS "C/F x10"
                    MAX-ACCESS read-write
                    STATUS current
                    DESCRIPTION "Restart dehumidification temperature set point"
                    DEFVAL { 40 }
                    ::= { analogObjects 68 }

        -- 1.3.6.1.4.1.9839.2.1.2.69
        prevent-diff OBJECT-TYPE
                    SYNTAX Integer32 (-999..999)
                    UNITS "bar x10"
                    MAX-ACCESS read-write
                    STATUS current
                    DESCRIPTION "Prevent differential - pressure"
                    DEFVAL { 20 }
                    ::= { analogObjects 69 }

        -- 1.3.6.1.4.1.9839.2.1.2.70
        prevent-diff-t OBJECT-TYPE
                    SYNTAX Integer32 (-999..999)
                    UNITS "C/F x10"
                    MAX-ACCESS read-write
                    STATUS current
                    DESCRIPTION "Prevent differential - temperature"
                    DEFVAL { 10 }
                    ::= { analogObjects 70 }

        -- 1.3.6.1.4.1.9839.2.1.2.71
        prevent-set OBJECT-TYPE
                    SYNTAX Integer32 (-999..999)
                    UNITS "bar x10"
                    MAX-ACCESS read-write
                    STATUS current
                    DESCRIPTION "Prevent setpoint - pressure"
                    DEFVAL { 200 }
                    ::= { analogObjects 71 }

        -- 1.3.6.1.4.1.9839.2.1.2.72
        prevent-set-t OBJECT-TYPE
                    SYNTAX Integer32 (-999..999)
                    UNITS "C/F x10"
                    MAX-ACCESS read-write
                    STATUS current
                    DESCRIPTION "Prevent set point - temperature"
                    DEFVAL { 700 }
                    ::= { analogObjects 72 }

        -- 1.3.6.1.4.1.9839.2.1.2.73
        rec-setpoint OBJECT-TYPE
                    SYNTAX Integer32 (0..680)
                    UNITS "C/F x10"
                    MAX-ACCESS read-write
                    STATUS current
                    DESCRIPTION "Water recovery set point temperature"
                    DEFVAL { 120 }
                    ::= { analogObjects 73 }

        -- 1.3.6.1.4.1.9839.2.1.2.75
        set-supply-lim OBJECT-TYPE
                    SYNTAX Integer32 (-9999..9999)
                    UNITS "C/F x10"
                    MAX-ACCESS read-write
                    STATUS current
                    DESCRIPTION "Air outlet set point"
                    DEFVAL { 150 }
                    ::= { analogObjects 75 }

        -- 1.3.6.1.4.1.9839.2.1.2.76
        setpoint-ext OBJECT-TYPE
                    SYNTAX Integer32 (-9999..9999)
                    UNITS "C/F x10"
                    MAX-ACCESS read-write
                    STATUS current
                    DESCRIPTION "Outside air set point for compensation"
                    DEFVAL { 250 }
                    ::= { analogObjects 76 }

        -- 1.3.6.1.4.1.9839.2.1.2.77
        speed-dehumid OBJECT-TYPE
                    SYNTAX Integer32 (0..100)
                    UNITS "V x10"
                    MAX-ACCESS read-write
                    STATUS current
                    DESCRIPTION "Outlet fan speed in dehumidification"
                    DEFVAL { 50 }
                    ::= { analogObjects 77 }

        -- 1.3.6.1.4.1.9839.2.1.2.78
        actual-sheat-d1 OBJECT-TYPE
                    SYNTAX Integer32 (-999..999)
                    UNITS "C x10"
                    MAX-ACCESS read-only
                    STATUS current
                    DESCRIPTION "Driver 1 current superheating value"
                    ::= { analogObjects 78 }

        -- 1.3.6.1.4.1.9839.2.1.2.79
        saturation-temp-d1 OBJECT-TYPE
                    SYNTAX Integer32 (-999..999)
                    UNITS "C x10"
                    MAX-ACCESS read-only
                    STATUS current
                    DESCRIPTION "Driver 1 evaporation temperature "
                    ::= { analogObjects 79 }

        -- 1.3.6.1.4.1.9839.2.1.2.80
        suction-temp-d1 OBJECT-TYPE
                    SYNTAX Integer32 (-999..999)
                    UNITS "C x10"
                    MAX-ACCESS read-only
                    STATUS current
                    DESCRIPTION "Driver 1 suction temperature"
                    ::= { analogObjects 80 }

        -- 1.3.6.1.4.1.9839.2.1.2.81
        suction-press-d1 OBJECT-TYPE
                    SYNTAX Integer32 (-999..999)
                    UNITS "bar x10"
                    MAX-ACCESS read-only
                    STATUS current
                    DESCRIPTION "Driver 1 evaporation pressure"
                    ::= { analogObjects 81 }

        -- 1.3.6.1.4.1.9839.2.1.2.82
        cond-temperature-d1 OBJECT-TYPE
                    SYNTAX Integer32 (-999..999)
                    UNITS "C x10"
                    MAX-ACCESS read-only
                    STATUS current
                    DESCRIPTION "Driver 1 condensing temperature"
                    ::= { analogObjects 82 }

        -- 1.3.6.1.4.1.9839.2.1.2.83
        actual-sheat-d2 OBJECT-TYPE
                    SYNTAX Integer32 (-999..999)
                    UNITS "C x10"
                    MAX-ACCESS read-only
                    STATUS current
                    DESCRIPTION "Driver 2 current superheating value"
                    ::= { analogObjects 83 }

        -- 1.3.6.1.4.1.9839.2.1.2.84
        saturation-temp-d2 OBJECT-TYPE
                    SYNTAX Integer32 (-999..999)
                    UNITS "C x10"
                    MAX-ACCESS read-only
                    STATUS current
                    DESCRIPTION "Driver 2 evaporation temperature"
                    ::= { analogObjects 84 }

        -- 1.3.6.1.4.1.9839.2.1.2.85
        suction-temp-d2 OBJECT-TYPE
                    SYNTAX Integer32 (-999..999)
                    UNITS "C x10"
                    MAX-ACCESS read-only
                    STATUS current
                    DESCRIPTION "Driver 2 suction temperature"
                    ::= { analogObjects 85 }

        -- 1.3.6.1.4.1.9839.2.1.2.86
        suction-press-d2 OBJECT-TYPE
                    SYNTAX Integer32 (-999..999)
                    UNITS "bar x10"
                    MAX-ACCESS read-only
                    STATUS current
                    DESCRIPTION "Driver 2 evaporation pressure"
                    ::= { analogObjects 86 }

        -- 1.3.6.1.4.1.9839.2.1.2.87
        cond-temperature-d2 OBJECT-TYPE
                    SYNTAX Integer32 (-999..999)
                    UNITS "C x10"
                    MAX-ACCESS read-only
                    STATUS current
                    DESCRIPTION "Driver 2 condensing temperature"
                    ::= { analogObjects 87 }



        -- 1.3.6.1.4.1.9839.2.1.3
        integerObjects OBJECT IDENTIFIER ::= { std-air-condMIB 3 }

        -- 1.3.6.1.4.1.9839.2.1.3.1
        pco2-aout-1 OBJECT-TYPE
                    SYNTAX Integer32 (-32767..32767)
                    UNITS "%"
                    MAX-ACCESS read-only
                    STATUS current
                    DESCRIPTION "Analog output 1"
                    ::= { integerObjects 1 }

        -- 1.3.6.1.4.1.9839.2.1.3.2
        pco2-aout-2 OBJECT-TYPE
                    SYNTAX Integer32 (-32767..32767)
                    UNITS "%"
                    MAX-ACCESS read-only
                    STATUS current
                    DESCRIPTION "Analog output 2"
                    ::= { integerObjects 2 }

        -- 1.3.6.1.4.1.9839.2.1.3.3
        pco2-aout-3 OBJECT-TYPE
                    SYNTAX Integer32 (-32767..32767)
                    UNITS "%"
                    MAX-ACCESS read-only
                    STATUS current
                    DESCRIPTION "Analog output 3"
                    ::= { integerObjects 3 }

        -- 1.3.6.1.4.1.9839.2.1.3.4
        pco2-aout-4 OBJECT-TYPE
                    SYNTAX Integer32 (-32767..32767)
                    UNITS "%"
                    MAX-ACCESS read-only
                    STATUS current
                    DESCRIPTION "Analog output 4"
                    ::= { integerObjects 4 }

        -- 1.3.6.1.4.1.9839.2.1.3.5
        hour OBJECT-TYPE
                    SYNTAX Integer32 (0..23)
                    UNITS "h"
                    MAX-ACCESS read-only
                    STATUS current
                    DESCRIPTION "Current hour"
                    ::= { integerObjects 5 }

        -- 1.3.6.1.4.1.9839.2.1.3.6
        minute OBJECT-TYPE
                    SYNTAX Integer32 (0..59)
                    UNITS "m"
                    MAX-ACCESS read-only
                    STATUS current
                    DESCRIPTION "Current minutes"
                    ::= { integerObjects 6 }

        -- 1.3.6.1.4.1.9839.2.1.3.7
        day OBJECT-TYPE
                    SYNTAX Integer32 (1..31)
                    UNITS "d"
                    MAX-ACCESS read-only
                    STATUS current
                    DESCRIPTION "Day"
                    ::= { integerObjects 7 }

        -- 1.3.6.1.4.1.9839.2.1.3.8
        month OBJECT-TYPE
                    SYNTAX Integer32 (1..12)
                    UNITS "mh"
                    MAX-ACCESS read-only
                    STATUS current
                    DESCRIPTION "Month"
                    ::= { integerObjects 8 }

        -- 1.3.6.1.4.1.9839.2.1.3.9
        pyear OBJECT-TYPE
                    SYNTAX Integer32 (0..99)
                    UNITS "N/A"
                    MAX-ACCESS read-only
                    STATUS current
                    DESCRIPTION "Year"
                    ::= { integerObjects 9 }

        -- 1.3.6.1.4.1.9839.2.1.3.10
        day-week OBJECT-TYPE
                    SYNTAX Integer32 (0..7)
                    UNITS "N/A"
                    MAX-ACCESS read-only
                    STATUS current
                    DESCRIPTION "Weekday"
                    ::= { integerObjects 10 }

        -- 1.3.6.1.4.1.9839.2.1.3.14
        lhour OBJECT-TYPE
                    SYNTAX Integer32 (0..23)
                    UNITS "h"
                    MAX-ACCESS read-write
                    STATUS current
                    DESCRIPTION "Hour setting"
                    ::= { integerObjects 14 }

        -- 1.3.6.1.4.1.9839.2.1.3.15
        lminute OBJECT-TYPE
                    SYNTAX Integer32 (0..59)
                    UNITS "m"
                    MAX-ACCESS read-write
                    STATUS current
                    DESCRIPTION "Minute setting"
                    ::= { integerObjects 15 }

        -- 1.3.6.1.4.1.9839.2.1.3.16
        lday OBJECT-TYPE
                    SYNTAX Integer32 (1..31)
                    UNITS "d"
                    MAX-ACCESS read-write
                    STATUS current
                    DESCRIPTION "Day setting"
                    ::= { integerObjects 16 }

        -- 1.3.6.1.4.1.9839.2.1.3.17
        lmonth OBJECT-TYPE
                    SYNTAX Integer32 (1..12)
                    UNITS "mh"
                    MAX-ACCESS read-write
                    STATUS current
                    DESCRIPTION "Month setting"
                    ::= { integerObjects 17 }

        -- 1.3.6.1.4.1.9839.2.1.3.18
        lyear OBJECT-TYPE
                    SYNTAX Integer32 (0..99)
                    UNITS "year"
                    MAX-ACCESS read-write
                    STATUS current
                    DESCRIPTION "Year setting"
                    ::= { integerObjects 18 }

        -- 1.3.6.1.4.1.9839.2.1.3.20
        n-comps OBJECT-TYPE
                    SYNTAX Integer32 (1..2)
                    UNITS "N/A"
                    MAX-ACCESS read-write
                    STATUS current
                    DESCRIPTION "Number of compressors"
                    DEFVAL { 2 }
                    ::= { integerObjects 20 }

        -- 1.3.6.1.4.1.9839.2.1.3.21
        n-comps-dehumid OBJECT-TYPE
                    SYNTAX Integer32 (0..2)
                    UNITS "N/A"
                    MAX-ACCESS read-write
                    STATUS current
                    DESCRIPTION "Number of compressor for dehumidify"
                    ::= { integerObjects 21 }

        -- 1.3.6.1.4.1.9839.2.1.3.22
        n-fans OBJECT-TYPE
                    SYNTAX Integer32 (1..2)
                    UNITS "N/A"
                    MAX-ACCESS read-write
                    STATUS current
                    DESCRIPTION "Select number of ON/OFF fans"
                    DEFVAL { 1 }
                    ::= { integerObjects 22 }

        -- 1.3.6.1.4.1.9839.2.1.3.23
        n-heaters OBJECT-TYPE
                    SYNTAX Integer32 (0..3)
                    UNITS "N/A"
                    MAX-ACCESS read-write
                    STATUS current
                    DESCRIPTION "Number of heaters"
                    DEFVAL { 2 }
                    ::= { integerObjects 23 }

        -- 1.3.6.1.4.1.9839.2.1.3.26
        dig-inp-5-conf OBJECT-TYPE
                    SYNTAX Integer32 (0..2)
                    UNITS "N/A"
                    MAX-ACCESS read-write
                    STATUS current
                    DESCRIPTION "Digital input 5 configuration"
                    DEFVAL { 1 }
                    ::= { integerObjects 26 }

        -- 1.3.6.1.4.1.9839.2.1.3.27
        type-ain-humid OBJECT-TYPE
                    SYNTAX Integer32 (2..4)
                    UNITS "N/A"
                    MAX-ACCESS read-write
                    STATUS current
                    DESCRIPTION "Type of signal from humidity probe"
                    DEFVAL { 2 }
                    ::= { integerObjects 27 }

        -- 1.3.6.1.4.1.9839.2.1.3.28
        type-ain-pressure1 OBJECT-TYPE
                    SYNTAX Integer32 (2..4)
                    UNITS "N/A"
                    MAX-ACCESS read-write
                    STATUS current
                    DESCRIPTION "Type of signal from pressure 1 probe"
                    DEFVAL { 4 }
                    ::= { integerObjects 28 }

        -- 1.3.6.1.4.1.9839.2.1.3.29
        type-ain-pressure2 OBJECT-TYPE
                    SYNTAX Integer32 (2..4)
                    UNITS "N/A"
                    MAX-ACCESS read-write
                    STATUS current
                    DESCRIPTION "Type of signal from pressure 2 probe"
                    DEFVAL { 4 }
                    ::= { integerObjects 29 }

        -- 1.3.6.1.4.1.9839.2.1.3.30
        type-cond1-temp OBJECT-TYPE
                    SYNTAX Integer32 (0..4)
                    UNITS "N/A"
                    MAX-ACCESS read-write
                    STATUS current
                    DESCRIPTION "Type of signal from condens. 1 T probe"
                    ::= { integerObjects 30 }

        -- 1.3.6.1.4.1.9839.2.1.3.31
        type-cond2-temp OBJECT-TYPE
                    SYNTAX Integer32 (0..4)
                    UNITS "N/A"
                    MAX-ACCESS read-write
                    STATUS current
                    DESCRIPTION "Type of signal from condens. 2 T probe"
                    ::= { integerObjects 31 }

        -- 1.3.6.1.4.1.9839.2.1.3.32
        type-ext-temp OBJECT-TYPE
                    SYNTAX Integer32 (0..1)
                    UNITS "N/A"
                    MAX-ACCESS read-write
                    STATUS current
                    DESCRIPTION "Type of signal from external temperature probe"
                    DEFVAL { 0 }
                    ::= { integerObjects 32 }

        -- 1.3.6.1.4.1.9839.2.1.3.33
        type-recovery-temp OBJECT-TYPE
                    SYNTAX Integer32 (0..1)
                    UNITS "N/A"
                    MAX-ACCESS read-write
                    STATUS current
                    DESCRIPTION "Type of signal from recovery temperature probe"
                    ::= { integerObjects 33 }

        -- 1.3.6.1.4.1.9839.2.1.3.34
        type-room-temp OBJECT-TYPE
                    SYNTAX Integer32 (0..1)
                    UNITS "N/A"
                    MAX-ACCESS read-write
                    STATUS current
                    DESCRIPTION "Type of signal from room temperature probe"
                    ::= { integerObjects 34 }

        -- 1.3.6.1.4.1.9839.2.1.3.35
        type-supply-temp OBJECT-TYPE
                    SYNTAX Integer32 (0..1)
                    UNITS "N/A"
                    MAX-ACCESS read-write
                    STATUS current
                    DESCRIPTION "Type of signal from outlet temperature probe"
                    ::= { integerObjects 35 }

        -- 1.3.6.1.4.1.9839.2.1.3.36
        type-freon OBJECT-TYPE
                    SYNTAX Integer32 (0..5)
                    UNITS "N/A"
                    MAX-ACCESS read-write
                    STATUS current
                    DESCRIPTION "Select refrigerant"
                    DEFVAL { 2 }
                    ::= { integerObjects 36 }

        -- 1.3.6.1.4.1.9839.2.1.3.37
        delay-air-flow OBJECT-TYPE
                    SYNTAX Integer32 (0..9999)
                    UNITS "sec"
                    MAX-ACCESS read-write
                    STATUS current
                    DESCRIPTION "Air flow switch alarm delay"
                    DEFVAL { 10 }
                    ::= { integerObjects 37 }

        -- 1.3.6.1.4.1.9839.2.1.3.38
        delay-off-fan OBJECT-TYPE
                    SYNTAX Integer32 (0..999)
                    UNITS "sec"
                    MAX-ACCESS read-write
                    STATUS current
                    DESCRIPTION "Outlet fan off delay"
                    DEFVAL { 20 }
                    ::= { integerObjects 38 }

        -- 1.3.6.1.4.1.9839.2.1.3.39
        delay-on-fan OBJECT-TYPE
                    SYNTAX Integer32 (0..999)
                    UNITS "sec"
                    MAX-ACCESS read-write
                    STATUS current
                    DESCRIPTION "Outlet fan start delay"
                    DEFVAL { 10 }
                    ::= { integerObjects 39 }

        -- 1.3.6.1.4.1.9839.2.1.3.40
        delay-relay7 OBJECT-TYPE
                    SYNTAX Integer32 (0..999)
                    UNITS "sec"
                    MAX-ACCESS read-write
                    STATUS current
                    DESCRIPTION "Delay in activating minor alarm relay no.7"
                    ::= { integerObjects 40 }

        -- 1.3.6.1.4.1.9839.2.1.3.41
        delay-relay8 OBJECT-TYPE
                    SYNTAX Integer32 (0..999)
                    UNITS "sec"
                    MAX-ACCESS read-write
                    STATUS current
                    DESCRIPTION "Delay in activating serious alarm relay no.8"
                    ::= { integerObjects 41 }

        -- 1.3.6.1.4.1.9839.2.1.3.42
        delay-water-flow OBJECT-TYPE
                    SYNTAX Integer32 (0..9999)
                    UNITS "sec"
                    MAX-ACCESS read-write
                    STATUS current
                    DESCRIPTION "Water flow switch alarm delay"
                    DEFVAL { 10 }
                    ::= { integerObjects 42 }

        -- 1.3.6.1.4.1.9839.2.1.3.43
        time-betw-comp OBJECT-TYPE
                    SYNTAX Integer32 (0..9999)
                    UNITS "sec"
                    MAX-ACCESS read-write
                    STATUS current
                    DESCRIPTION "Delay between starts of different compressors"
                    DEFVAL { 10 }
                    ::= { integerObjects 43 }

        -- 1.3.6.1.4.1.9839.2.1.3.44
        time-betw-heat OBJECT-TYPE
                    SYNTAX Integer32 (0..9999)
                    UNITS "sec"
                    MAX-ACCESS read-write
                    STATUS current
                    DESCRIPTION "Heater start delay"
                    DEFVAL { 3 }
                    ::= { integerObjects 44 }

        -- 1.3.6.1.4.1.9839.2.1.3.45
        time-low-pres OBJECT-TYPE
                    SYNTAX Integer32 (0..9999)
                    UNITS "sec"
                    MAX-ACCESS read-write
                    STATUS current
                    DESCRIPTION "Low pressure alarm delay"
                    DEFVAL { 180 }
                    ::= { integerObjects 45 }

        -- 1.3.6.1.4.1.9839.2.1.3.46
        time-integr OBJECT-TYPE
                    SYNTAX Integer32 (0..9999)
                    UNITS "sec"
                    MAX-ACCESS read-write
                    STATUS current
                    DESCRIPTION "Integration time for P+I control"
                    DEFVAL { 600 }
                    ::= { integerObjects 46 }

        -- 1.3.6.1.4.1.9839.2.1.3.47
        time-min-off OBJECT-TYPE
                    SYNTAX Integer32 (0..9999)
                    UNITS "sec"
                    MAX-ACCESS read-write
                    STATUS current
                    DESCRIPTION "Minimum compressor OFF time"
                    DEFVAL { 180 }
                    ::= { integerObjects 47 }

        -- 1.3.6.1.4.1.9839.2.1.3.48
        time-min-on OBJECT-TYPE
                    SYNTAX Integer32 (0..9999)
                    UNITS "sec"
                    MAX-ACCESS read-write
                    STATUS current
                    DESCRIPTION "Minimum compressor ON time"
                    DEFVAL { 60 }
                    ::= { integerObjects 48 }

        -- 1.3.6.1.4.1.9839.2.1.3.49
        time-same-comp OBJECT-TYPE
                    SYNTAX Integer32 (0..9999)
                    UNITS "sec"
                    MAX-ACCESS read-write
                    STATUS current
                    DESCRIPTION "Delay between compressor starts"
                    DEFVAL { 360 }
                    ::= { integerObjects 49 }

        -- 1.3.6.1.4.1.9839.2.1.3.50
        time-unloader OBJECT-TYPE
                    SYNTAX Integer32 (0..9999)
                    UNITS "sec"
                    MAX-ACCESS read-write
                    STATUS current
                    DESCRIPTION "Cap. control activation delay"
                    DEFVAL { 10 }
                    ::= { integerObjects 50 }

        -- 1.3.6.1.4.1.9839.2.1.3.51
        time-runn-d3p OBJECT-TYPE
                    SYNTAX Integer32 (0..9999)
                    UNITS "sec"
                    MAX-ACCESS read-write
                    STATUS current
                    DESCRIPTION "3 position valve travel time"
                    DEFVAL { 180 }
                    ::= { integerObjects 51 }

        -- 1.3.6.1.4.1.9839.2.1.3.52
        time-thr-alarm OBJECT-TYPE
                    SYNTAX Integer32 (0..9999)
                    UNITS "sec"
                    MAX-ACCESS read-write
                    STATUS current
                    DESCRIPTION "High-low temperature-humidity alarm delay"
                    DEFVAL { 600 }
                    ::= { integerObjects 52 }

        -- 1.3.6.1.4.1.9839.2.1.3.53
        b5 OBJECT-TYPE
                    SYNTAX Integer32 (0..2000)
                    UNITS "uS/cm"
                    MAX-ACCESS read-write
                    STATUS current
                    DESCRIPTION "High conductivity pre-alarm threshold"
                    DEFVAL { 1500 }
                    ::= { integerObjects 53 }

        -- 1.3.6.1.4.1.9839.2.1.3.54
        b6 OBJECT-TYPE
                    SYNTAX Integer32 (0..2000)
                    UNITS "uS/cm"
                    MAX-ACCESS read-write
                    STATUS current
                    DESCRIPTION "High conductivity alarm delay"
                    DEFVAL { 2000 }
                    ::= { integerObjects 54 }

        -- 1.3.6.1.4.1.9839.2.1.3.55
        humidifier-type OBJECT-TYPE
                    SYNTAX Integer32 (1..37)
                    UNITS "N/A"
                    MAX-ACCESS read-write
                    STATUS current
                    DESCRIPTION "Type of humidifier"
                    DEFVAL { 8 }
                    ::= { integerObjects 55 }

        -- 1.3.6.1.4.1.9839.2.1.3.58
        fascia1-ore-on1 OBJECT-TYPE
                    SYNTAX Integer32 (0..23)
                    UNITS "h"
                    MAX-ACCESS read-write
                    STATUS current
                    DESCRIPTION "Start hour ON/OFF time band F1-1"
                    DEFVAL { 9 }
                    ::= { integerObjects 58 }

        -- 1.3.6.1.4.1.9839.2.1.3.59
        fascia1-min-on1 OBJECT-TYPE
                    SYNTAX Integer32 (0..59)
                    UNITS "m"
                    MAX-ACCESS read-write
                    STATUS current
                    DESCRIPTION "Start minutes ON/OFF time band F1-1"
                    ::= { integerObjects 59 }

        -- 1.3.6.1.4.1.9839.2.1.3.60
        fascia1-ore-off1 OBJECT-TYPE
                    SYNTAX Integer32 (0..23)
                    UNITS "h"
                    MAX-ACCESS read-write
                    STATUS current
                    DESCRIPTION "End hour ON/OFF time band F1-1"
                    DEFVAL { 13 }
                    ::= { integerObjects 60 }

        -- 1.3.6.1.4.1.9839.2.1.3.61
        fascia1-min-off1 OBJECT-TYPE
                    SYNTAX Integer32 (0..59)
                    UNITS "m"
                    MAX-ACCESS read-write
                    STATUS current
                    DESCRIPTION "End minutes ON/OFF time band F1-1"
                    ::= { integerObjects 61 }

        -- 1.3.6.1.4.1.9839.2.1.3.62
        fascia1-ore-on2 OBJECT-TYPE
                    SYNTAX Integer32 (0..23)
                    UNITS "h"
                    MAX-ACCESS read-write
                    STATUS current
                    DESCRIPTION "Start hour ON/OFF time band F1-2"
                    DEFVAL { 14 }
                    ::= { integerObjects 62 }

        -- 1.3.6.1.4.1.9839.2.1.3.63
        fascia1-min-on2 OBJECT-TYPE
                    SYNTAX Integer32 (0..59)
                    UNITS "m"
                    MAX-ACCESS read-write
                    STATUS current
                    DESCRIPTION "Start minutes ON/OFF time band F1-2"
                    ::= { integerObjects 63 }

        -- 1.3.6.1.4.1.9839.2.1.3.64
        fascia1-ore-off2 OBJECT-TYPE
                    SYNTAX Integer32 (0..23)
                    UNITS "h"
                    MAX-ACCESS read-write
                    STATUS current
                    DESCRIPTION "End hour ON/OFF time band F1-2"
                    DEFVAL { 21 }
                    ::= { integerObjects 64 }

        -- 1.3.6.1.4.1.9839.2.1.3.65
        fascia1-min-off2 OBJECT-TYPE
                    SYNTAX Integer32 (0..59)
                    UNITS "m"
                    MAX-ACCESS read-write
                    STATUS current
                    DESCRIPTION "End minutes ON/OFF time band F1-2"
                    ::= { integerObjects 65 }

        -- 1.3.6.1.4.1.9839.2.1.3.66
        fascia2-ore-on OBJECT-TYPE
                    SYNTAX Integer32 (0..23)
                    UNITS "h"
                    MAX-ACCESS read-write
                    STATUS current
                    DESCRIPTION "Start hour ON/OFF time band F2"
                    DEFVAL { 14 }
                    ::= { integerObjects 66 }

        -- 1.3.6.1.4.1.9839.2.1.3.67
        fascia2-min-on OBJECT-TYPE
                    SYNTAX Integer32 (0..59)
                    UNITS "m"
                    MAX-ACCESS read-write
                    STATUS current
                    DESCRIPTION "Start minutes ON/OFF time band F2"
                    ::= { integerObjects 67 }

        -- 1.3.6.1.4.1.9839.2.1.3.68
        fascia2-ore-off OBJECT-TYPE
                    SYNTAX Integer32 (0..23)
                    UNITS "h"
                    MAX-ACCESS read-write
                    STATUS current
                    DESCRIPTION "End hour ON/OFF time band F2"
                    DEFVAL { 21 }
                    ::= { integerObjects 68 }

        -- 1.3.6.1.4.1.9839.2.1.3.69
        fascia2-min-off OBJECT-TYPE
                    SYNTAX Integer32 (0..59)
                    UNITS "m"
                    MAX-ACCESS read-write
                    STATUS current
                    DESCRIPTION "End minutes ON/OFF time band F2"
                    ::= { integerObjects 69 }

        -- 1.3.6.1.4.1.9839.2.1.3.70
        temp-hour1 OBJECT-TYPE
                    SYNTAX Integer32 (0..23)
                    UNITS "h"
                    MAX-ACCESS read-write
                    STATUS current
                    DESCRIPTION "Start hour temperature time band Z1"
                    ::= { integerObjects 70 }

        -- 1.3.6.1.4.1.9839.2.1.3.71
        temp-minute1 OBJECT-TYPE
                    SYNTAX Integer32 (0..59)
                    UNITS "m"
                    MAX-ACCESS read-write
                    STATUS current
                    DESCRIPTION "Start minutes temperature time band Z1"
                    ::= { integerObjects 71 }

        -- 1.3.6.1.4.1.9839.2.1.3.72
        temp-hour2 OBJECT-TYPE
                    SYNTAX Integer32 (0..23)
                    UNITS "h"
                    MAX-ACCESS read-write
                    STATUS current
                    DESCRIPTION "Start hour temperature time band Z2"
                    ::= { integerObjects 72 }

        -- 1.3.6.1.4.1.9839.2.1.3.73
        temp-minute2 OBJECT-TYPE
                    SYNTAX Integer32 (0..59)
                    UNITS "m"
                    MAX-ACCESS read-write
                    STATUS current
                    DESCRIPTION "Start minutes temperature time band Z2"
                    ::= { integerObjects 73 }

        -- 1.3.6.1.4.1.9839.2.1.3.74
        temp-hour3 OBJECT-TYPE
                    SYNTAX Integer32 (0..23)
                    UNITS "h"
                    MAX-ACCESS read-write
                    STATUS current
                    DESCRIPTION "Start hour temperature time band Z3"
                    ::= { integerObjects 74 }

        -- 1.3.6.1.4.1.9839.2.1.3.75
        temp-minute3 OBJECT-TYPE
                    SYNTAX Integer32 (0..59)
                    UNITS "m"
                    MAX-ACCESS read-write
                    STATUS current
                    DESCRIPTION "Start minutes temperature time band Z3"
                    ::= { integerObjects 75 }

        -- 1.3.6.1.4.1.9839.2.1.3.76
        temp-hour4 OBJECT-TYPE
                    SYNTAX Integer32 (0..23)
                    UNITS "h"
                    MAX-ACCESS read-write
                    STATUS current
                    DESCRIPTION "Start hour temperature time band Z4"
                    ::= { integerObjects 76 }

        -- 1.3.6.1.4.1.9839.2.1.3.77
        temp-minute4 OBJECT-TYPE
                    SYNTAX Integer32 (0..59)
                    UNITS "m"
                    MAX-ACCESS read-write
                    STATUS current
                    DESCRIPTION "Start minutes temperature time band Z4"
                    ::= { integerObjects 77 }

        -- 1.3.6.1.4.1.9839.2.1.3.78
        humid-hour1 OBJECT-TYPE
                    SYNTAX Integer32 (0..23)
                    UNITS "h"
                    MAX-ACCESS read-write
                    STATUS current
                    DESCRIPTION "Start hour humidity time band Z1"
                    ::= { integerObjects 78 }

        -- 1.3.6.1.4.1.9839.2.1.3.79
        humid-minute1 OBJECT-TYPE
                    SYNTAX Integer32 (0..59)
                    UNITS "m"
                    MAX-ACCESS read-write
                    STATUS current
                    DESCRIPTION "Start minutes humidity time band Z1"
                    ::= { integerObjects 79 }

        -- 1.3.6.1.4.1.9839.2.1.3.80
        humid-hour2 OBJECT-TYPE
                    SYNTAX Integer32 (0..23)
                    UNITS "h"
                    MAX-ACCESS read-write
                    STATUS current
                    DESCRIPTION "Start hour humidity time band Z2"
                    ::= { integerObjects 80 }

        -- 1.3.6.1.4.1.9839.2.1.3.81
        humid-minute2 OBJECT-TYPE
                    SYNTAX Integer32 (0..59)
                    UNITS "m"
                    MAX-ACCESS read-write
                    STATUS current
                    DESCRIPTION "Start minutes humidity time band Z2"
                    ::= { integerObjects 81 }

        -- 1.3.6.1.4.1.9839.2.1.3.82
        humid-hour3 OBJECT-TYPE
                    SYNTAX Integer32 (0..23)
                    UNITS "h"
                    MAX-ACCESS read-write
                    STATUS current
                    DESCRIPTION "Start hour humidity time band Z3"
                    ::= { integerObjects 82 }

        -- 1.3.6.1.4.1.9839.2.1.3.83
        humid-minute3 OBJECT-TYPE
                    SYNTAX Integer32 (0..59)
                    UNITS "m"
                    MAX-ACCESS read-write
                    STATUS current
                    DESCRIPTION "Start minutes humidity time band Z3"
                    ::= { integerObjects 83 }

        -- 1.3.6.1.4.1.9839.2.1.3.84
        humid-hour4 OBJECT-TYPE
                    SYNTAX Integer32 (0..23)
                    UNITS "h"
                    MAX-ACCESS read-write
                    STATUS current
                    DESCRIPTION "Start hour humidity time band Z4"
                    ::= { integerObjects 84 }

        -- 1.3.6.1.4.1.9839.2.1.3.85
        humid-minute4 OBJECT-TYPE
                    SYNTAX Integer32 (0..59)
                    UNITS "m"
                    MAX-ACCESS read-write
                    STATUS current
                    DESCRIPTION "Start minutes humidity time band Z4"
                    ::= { integerObjects 85 }

        -- 1.3.6.1.4.1.9839.2.1.3.86
        monday-type OBJECT-TYPE
                    SYNTAX Integer32 (0..3)
                    UNITS "N/A"
                    MAX-ACCESS read-write
                    STATUS current
                    DESCRIPTION "Select ON/OFF time bands Monday"
                    DEFVAL { 2 }
                    ::= { integerObjects 86 }

        -- 1.3.6.1.4.1.9839.2.1.3.87
        tuesday-type OBJECT-TYPE
                    SYNTAX Integer32 (0..3)
                    UNITS "N/A"
                    MAX-ACCESS read-write
                    STATUS current
                    DESCRIPTION "Select ON/OFF time bands Tuesday"
                    DEFVAL { 2 }
                    ::= { integerObjects 87 }

        -- 1.3.6.1.4.1.9839.2.1.3.88
        wednesday-type OBJECT-TYPE
                    SYNTAX Integer32 (0..3)
                    UNITS "N/A"
                    MAX-ACCESS read-write
                    STATUS current
                    DESCRIPTION "Select ON/OFF time bands Wednesday"
                    DEFVAL { 2 }
                    ::= { integerObjects 88 }

        -- 1.3.6.1.4.1.9839.2.1.3.89
        thursday-type OBJECT-TYPE
                    SYNTAX Integer32 (0..3)
                    UNITS "N/A"
                    MAX-ACCESS read-write
                    STATUS current
                    DESCRIPTION "Select ON/OFF time bands Thursday"
                    DEFVAL { 2 }
                    ::= { integerObjects 89 }

        -- 1.3.6.1.4.1.9839.2.1.3.90
        friday-type OBJECT-TYPE
                    SYNTAX Integer32 (0..3)
                    UNITS "N/A"
                    MAX-ACCESS read-write
                    STATUS current
                    DESCRIPTION "Select ON/OFF time bands Friday"
                    DEFVAL { 2 }
                    ::= { integerObjects 90 }

        -- 1.3.6.1.4.1.9839.2.1.3.91
        saturday-type OBJECT-TYPE
                    SYNTAX Integer32 (0..3)
                    UNITS "N/A"
                    MAX-ACCESS read-write
                    STATUS current
                    DESCRIPTION "Select ON/OFF time bands Saturday"
                    DEFVAL { 2 }
                    ::= { integerObjects 91 }

        -- 1.3.6.1.4.1.9839.2.1.3.92
        sunday-type OBJECT-TYPE
                    SYNTAX Integer32 (0..3)
                    UNITS "N/A"
                    MAX-ACCESS read-write
                    STATUS current
                    DESCRIPTION "Select ON/OFF time bands Sunday"
                    DEFVAL { 2 }
                    ::= { integerObjects 92 }

        -- 1.3.6.1.4.1.9839.2.1.3.93
        speed-up-time OBJECT-TYPE
                    SYNTAX Integer32 (0..999)
                    UNITS "sec"
                    MAX-ACCESS read-write
                    STATUS current
                    DESCRIPTION "Cond. fan speed-up time"
                    DEFVAL { 2 }
                    ::= { integerObjects 93 }

        -- 1.3.6.1.4.1.9839.2.1.3.94
        thr-h-hour-c1 OBJECT-TYPE
                    SYNTAX Integer32 (0..99)
                    UNITS "h (x1000)"
                    MAX-ACCESS read-write
                    STATUS current
                    DESCRIPTION "Compressor 1 operating hours threshold"
                    DEFVAL { 99 }
                    ::= { integerObjects 94 }

        -- 1.3.6.1.4.1.9839.2.1.3.95
        thr-h-hour-c2 OBJECT-TYPE
                    SYNTAX Integer32 (0..99)
                    UNITS "h (x1000)"
                    MAX-ACCESS read-write
                    STATUS current
                    DESCRIPTION "Compressor 2 operating hours threshold"
                    DEFVAL { 99 }
                    ::= { integerObjects 95 }

        -- 1.3.6.1.4.1.9839.2.1.3.96
        thr-h-humid OBJECT-TYPE
                    SYNTAX Integer32 (0..99)
                    UNITS "h (x1000)"
                    MAX-ACCESS read-write
                    STATUS current
                    DESCRIPTION "Humidifier operating hour threshold"
                    DEFVAL { 99 }
                    ::= { integerObjects 96 }

        -- 1.3.6.1.4.1.9839.2.1.3.97
        thr-h-main-fan OBJECT-TYPE
                    SYNTAX Integer32 (0..99)
                    UNITS "h (x1000)"
                    MAX-ACCESS read-write
                    STATUS current
                    DESCRIPTION "Fan operating hour threshold"
                    DEFVAL { 99 }
                    ::= { integerObjects 97 }

        -- 1.3.6.1.4.1.9839.2.1.3.98
        net-mode OBJECT-TYPE
                    SYNTAX Integer32 (0..2)
                    UNITS "N/A"
                    MAX-ACCESS read-write
                    STATUS current
                    DESCRIPTION "Rotation mode for units in pLAN network"
                    ::= { integerObjects 98 }

        -- 1.3.6.1.4.1.9839.2.1.3.99
        force-time-high OBJECT-TYPE
                    SYNTAX Integer32 (0..999)
                    UNITS "min"
                    MAX-ACCESS read-write
                    STATUS current
                    DESCRIPTION "Forcing delay for high ambient temperature"
                    DEFVAL { 3 }
                    ::= { integerObjects 99 }

        -- 1.3.6.1.4.1.9839.2.1.3.100
        force-time-low OBJECT-TYPE
                    SYNTAX Integer32 (0..999)
                    UNITS "min"
                    MAX-ACCESS read-write
                    STATUS current
                    DESCRIPTION "Forcing delay for low ambient temperature"
                    DEFVAL { 3 }
                    ::= { integerObjects 100 }

        -- 1.3.6.1.4.1.9839.2.1.3.101
        day-rotation OBJECT-TYPE
                    SYNTAX Integer32 (1..7)
                    UNITS "d"
                    MAX-ACCESS read-write
                    STATUS current
                    DESCRIPTION "Interval in days for automatic rotation"
                    DEFVAL { 3 }
                    ::= { integerObjects 101 }

        -- 1.3.6.1.4.1.9839.2.1.3.102
        hour-change OBJECT-TYPE
                    SYNTAX Integer32 (0..23)
                    UNITS "h"
                    MAX-ACCESS read-write
                    STATUS current
                    DESCRIPTION "Hour automatic rotation"
                    DEFVAL { 22 }
                    ::= { integerObjects 102 }

        -- 1.3.6.1.4.1.9839.2.1.3.103
        minute-change OBJECT-TYPE
                    SYNTAX Integer32 (0..59)
                    UNITS "m"
                    MAX-ACCESS read-write
                    STATUS current
                    DESCRIPTION "Minutes automatic rotation"
                    ::= { integerObjects 103 }

        -- 1.3.6.1.4.1.9839.2.1.3.106
        rotation-time OBJECT-TYPE
                    SYNTAX Integer32 (0..240)
                    UNITS "h"
                    MAX-ACCESS read-write
                    STATUS current
                    DESCRIPTION "Automatic rotation interval for units in pLAN"
                    DEFVAL { 24 }
                    ::= { integerObjects 106 }

        -- 1.3.6.1.4.1.9839.2.1.3.107
        unit1-mode OBJECT-TYPE
                    SYNTAX Integer32 (0..1)
                    UNITS "N/A"
                    MAX-ACCESS read-write
                    STATUS current
                    DESCRIPTION "pLAN connection class board 1"
                    DEFVAL { 1 }
                    ::= { integerObjects 107 }

        -- 1.3.6.1.4.1.9839.2.1.3.108
        unit2-mode OBJECT-TYPE
                    SYNTAX Integer32 (0..2)
                    UNITS "N/A"
                    MAX-ACCESS read-write
                    STATUS current
                    DESCRIPTION "pLAN connection class board 2"
                    DEFVAL { 2 }
                    ::= { integerObjects 108 }

        -- 1.3.6.1.4.1.9839.2.1.3.109
        unit3-mode OBJECT-TYPE
                    SYNTAX Integer32 (0..2)
                    UNITS "N/A"
                    MAX-ACCESS read-write
                    STATUS current
                    DESCRIPTION "pLAN connection class board 3"
                    DEFVAL { 2 }
                    ::= { integerObjects 109 }

        -- 1.3.6.1.4.1.9839.2.1.3.110
        unit4-mode OBJECT-TYPE
                    SYNTAX Integer32 (0..2)
                    UNITS "N/A"
                    MAX-ACCESS read-write
                    STATUS current
                    DESCRIPTION "pLAN connection class board 4"
                    DEFVAL { 2 }
                    ::= { integerObjects 110 }

        -- 1.3.6.1.4.1.9839.2.1.3.111
        unit5-mode OBJECT-TYPE
                    SYNTAX Integer32 (0..2)
                    UNITS "N/A"
                    MAX-ACCESS read-write
                    STATUS current
                    DESCRIPTION "pLAN connection class board 5"
                    DEFVAL { 2 }
                    ::= { integerObjects 111 }

        -- 1.3.6.1.4.1.9839.2.1.3.112
        unit6-mode OBJECT-TYPE
                    SYNTAX Integer32 (0..2)
                    UNITS "N/A"
                    MAX-ACCESS read-write
                    STATUS current
                    DESCRIPTION "pLAN connection class board 6"
                    DEFVAL { 2 }
                    ::= { integerObjects 112 }

        -- 1.3.6.1.4.1.9839.2.1.3.113
        unit7-mode OBJECT-TYPE
                    SYNTAX Integer32 (0..2)
                    UNITS "N/A"
                    MAX-ACCESS read-write
                    STATUS current
                    DESCRIPTION "pLAN connection class board 7"
                    DEFVAL { 2 }
                    ::= { integerObjects 113 }

        -- 1.3.6.1.4.1.9839.2.1.3.114
        unit8-mode OBJECT-TYPE
                    SYNTAX Integer32 (0..2)
                    UNITS "N/A"
                    MAX-ACCESS read-write
                    STATUS current
                    DESCRIPTION "pLAN connection class board 8"
                    DEFVAL { 2 }
                    ::= { integerObjects 114 }

        -- 1.3.6.1.4.1.9839.2.1.3.115
        position-valve-d1 OBJECT-TYPE
                    SYNTAX Integer32 (0..9999)
                    UNITS "N/A"
                    MAX-ACCESS read-only
                    STATUS current
                    DESCRIPTION "Valve position driver 1"
                    ::= { integerObjects 115 }

        -- 1.3.6.1.4.1.9839.2.1.3.116
        position-valve-d2 OBJECT-TYPE
                    SYNTAX Integer32 (0..9999)
                    UNITS "N/A"
                    MAX-ACCESS read-only
                    STATUS current
                    DESCRIPTION "Valve position driver 2"
                    ::= { integerObjects 116 }


	
	END

--
-- CAREL-std-air-cond.MIB
--
