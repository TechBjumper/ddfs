--
-- ASCO-QEM-72EE2-BETA-03.mib
-- MIB generated by MG-SOFT Visual MIB Builder Version 7.0  Build 240
-- Tuesday, September 22, 2015 at 14:42:27
--

--   *********************************************************************
-- **
-- ** Confidential and proprietary Information
-- **
-- ** Copyright © ASCO Power Technologies. All rights reserved.
-- ** 
-- ** Beta-03 09/22/2015 LHidalgo, added additional traps for
-- ** ts locked out, ctts extended parallele alarm, ctts failure to 
-- ** synchronize, normal breaker tripped, emergency breaker tripped, 
-- ** y-y primary fail is active.
-- **
-- ** Beta-02 06/25/2015 LHidalgo, added additional DPM OIDs
-- ** to dpmEmergency, dpmNormal, dpmLoad & dpmOthers 
-- ** folders.
-- **
-- ** Beta-01 06/24/2015 LHidalgo, derived from 72EE MIB with
-- ** additional registers from Group 5 & DPM
-- *********************************************************************
-- ** Filename:   ASCO_QEM-72EE2-BETA-03.mib
-- *********************************************************************

	ASCO-QEM-72EE2-BETA-03 DEFINITIONS ::= BEGIN
 
		IMPORTS
			OBJECT-GROUP, MODULE-COMPLIANCE, NOTIFICATION-GROUP			
				FROM SNMPv2-CONF			
			enterprises, Integer32, OBJECT-TYPE, MODULE-IDENTITY, OBJECT-IDENTITY, 
			NOTIFICATION-TYPE			
				FROM SNMPv2-SMI			
			DisplayString			
				FROM SNMPv2-TC;
	
	
--    A MIB with definitions for ASCO Version 2.0
-- 1.3.6.1.4.1.7777
-- 1.3.6.1.4.1.7777
-- June 26, 2015 at 13:29 GMT
-- 1.3.6.1.4.1.7777
-- June 26, 2015 at 13:29 GMT
		-- 1.3.6.1.4.1.7777
		asco MODULE-IDENTITY 
			LAST-UPDATED "201506261329Z"		-- June 26, 2015 at 13:29 GMT
			ORGANIZATION 
				"ASCO Power Technologies"
			CONTACT-INFO 
				"Brendan Kirby 973-966-2000"
			DESCRIPTION 
				"This MIB applies to SNMP Agent implemented in ASCO QEM 72EE2 devices."
			::= { enterprises 7777 }

		
	
	
--
-- Node definitions
--
	
--  Node definitions
-- 
-- Node definitions
-- 
-- 1.3.6.1.4.1.7777.1
-- 1.3.6.1.4.1.7777.1
-- 1.3.6.1.4.1.7777.1
		-- 1.3.6.1.4.1.7777.1
		device OBJECT IDENTIFIER ::= { asco 1 }

		
--    1.3.6.1.4.1.7777.1.2.1
-- 1.3.6.1.4.1.7777.1.1
-- 1.3.6.1.4.1.7777.1.1
		-- 1.3.6.1.4.1.7777.1.1
		transferswitch OBJECT IDENTIFIER ::= { device 1 }

		
--    1.3.6.1.4.1.7777.1.2.1.1
-- 1.3.6.1.4.1.7777.1.1.1
-- 1.3.6.1.4.1.7777.1.1.1
		-- 1.3.6.1.4.1.7777.1.1.1
		phase_shift_between_normal_and_emergency OBJECT-TYPE
			SYNTAX Integer32
			MAX-ACCESS read-only
			STATUS current
			DESCRIPTION
				"Phase shift between normal & emergency"
			::= { transferswitch 1 }

		
--    1.3.6.1.4.1.7777.1.2.1.2
-- 1.3.6.1.4.1.7777.1.1.2
-- 1.3.6.1.4.1.7777.1.1.2
		-- 1.3.6.1.4.1.7777.1.1.2
		normal_frequency OBJECT-TYPE
			SYNTAX Integer32
			MAX-ACCESS read-only
			STATUS current
			DESCRIPTION
				"Normal frequency"
			::= { transferswitch 2 }

		
--    1.3.6.1.4.1.7777.1.2.1.3
-- 1.3.6.1.4.1.7777.1.1.3
-- 1.3.6.1.4.1.7777.1.1.3
		-- 1.3.6.1.4.1.7777.1.1.3
		emergency_frequency OBJECT-TYPE
			SYNTAX Integer32
			MAX-ACCESS read-only
			STATUS current
			DESCRIPTION
				"Emergency frequency"
			::= { transferswitch 3 }

		
--    1.3.6.1.4.1.7777.1.2.1.4
-- 1.3.6.1.4.1.7777.1.1.4
-- 1.3.6.1.4.1.7777.1.1.4
		-- 1.3.6.1.4.1.7777.1.1.4
		main_on_normal OBJECT-TYPE
			SYNTAX Integer32
			MAX-ACCESS read-only
			STATUS current
			DESCRIPTION
				"Main on normal"
			::= { transferswitch 4 }

		
--    1.3.6.1.4.1.7777.1.2.1.5
-- 1.3.6.1.4.1.7777.1.1.5
-- 1.3.6.1.4.1.7777.1.1.5
		-- 1.3.6.1.4.1.7777.1.1.5
		main_on_emergency OBJECT-TYPE
			SYNTAX Integer32
			MAX-ACCESS read-only
			STATUS current
			DESCRIPTION
				"Main on emergency"
			::= { transferswitch 5 }

		
--    1.3.6.1.4.1.7777.1.2.1.6
-- 1.3.6.1.4.1.7777.1.1.6
-- 1.3.6.1.4.1.7777.1.1.6
		-- 1.3.6.1.4.1.7777.1.1.6
		auxiliary_on_normal OBJECT-TYPE
			SYNTAX Integer32
			MAX-ACCESS read-only
			STATUS current
			DESCRIPTION
				"Auxiliary on normal"
			::= { transferswitch 6 }

		
--    1.3.6.1.4.1.7777.1.2.1.7
-- 1.3.6.1.4.1.7777.1.1.7
-- 1.3.6.1.4.1.7777.1.1.7
		-- 1.3.6.1.4.1.7777.1.1.7
		auxiliary_on_emergency OBJECT-TYPE
			SYNTAX Integer32
			MAX-ACCESS read-only
			STATUS current
			DESCRIPTION
				"Auxiliary on emergency"
			::= { transferswitch 7 }

		
--    1.3.6.1.4.1.7777.1.2.1.8
-- 1.3.6.1.4.1.7777.1.1.8
-- 1.3.6.1.4.1.7777.1.1.8
		-- 1.3.6.1.4.1.7777.1.1.8
		normal_source_available OBJECT-TYPE
			SYNTAX Integer32
			MAX-ACCESS read-only
			STATUS current
			DESCRIPTION
				"Normal source available"
			::= { transferswitch 8 }

		
--    1.3.6.1.4.1.7777.1.2.1.9
-- 1.3.6.1.4.1.7777.1.1.9
-- 1.3.6.1.4.1.7777.1.1.9
		-- 1.3.6.1.4.1.7777.1.1.9
		emergency_source_available OBJECT-TYPE
			SYNTAX Integer32
			MAX-ACCESS read-only
			STATUS current
			DESCRIPTION
				"Emergency source available"
			::= { transferswitch 9 }

		
--    1.3.6.1.4.1.7777.1.2.1.10
-- 1.3.6.1.4.1.7777.1.1.10
-- 1.3.6.1.4.1.7777.1.1.10
		-- 1.3.6.1.4.1.7777.1.1.10
		engine_exerciser_with_load_active OBJECT-TYPE
			SYNTAX Integer32
			MAX-ACCESS read-only
			STATUS current
			DESCRIPTION
				"Engine exerciser with load active"
			::= { transferswitch 10 }

		
--    1.3.6.1.4.1.7777.1.2.1.11
-- 1.3.6.1.4.1.7777.1.1.11
-- 1.3.6.1.4.1.7777.1.1.11
		-- 1.3.6.1.4.1.7777.1.1.11
		external_f17_is_active OBJECT-TYPE
			SYNTAX Integer32
			MAX-ACCESS read-only
			STATUS current
			DESCRIPTION
				"External F17 is active"
			::= { transferswitch 11 }

		
--    1.3.6.1.4.1.7777.1.2.1.12
-- 1.3.6.1.4.1.7777.1.1.12
-- 1.3.6.1.4.1.7777.1.1.12
		-- 1.3.6.1.4.1.7777.1.1.12
		normal_voltage_phase_AB OBJECT-TYPE
			SYNTAX Integer32
			MAX-ACCESS read-only
			STATUS current
			DESCRIPTION
				"Normal voltage phase AB"
			::= { transferswitch 12 }

		
--    1.3.6.1.4.1.7777.1.2.1.13
-- 1.3.6.1.4.1.7777.1.1.13
-- 1.3.6.1.4.1.7777.1.1.13
		-- 1.3.6.1.4.1.7777.1.1.13
		normal_voltage_phase_BC OBJECT-TYPE
			SYNTAX Integer32
			MAX-ACCESS read-only
			STATUS current
			DESCRIPTION
				"Normal voltage phase BC"
			::= { transferswitch 13 }

		
--    1.3.6.1.4.1.7777.1.2.1.14
-- 1.3.6.1.4.1.7777.1.1.14
-- 1.3.6.1.4.1.7777.1.1.14
		-- 1.3.6.1.4.1.7777.1.1.14
		normal_voltage_phase_CA OBJECT-TYPE
			SYNTAX Integer32
			MAX-ACCESS read-only
			STATUS current
			DESCRIPTION
				"Normal voltage phase CA"
			::= { transferswitch 14 }

		
--    1.3.6.1.4.1.7777.1.2.1.15
-- 1.3.6.1.4.1.7777.1.1.15
-- 1.3.6.1.4.1.7777.1.1.15
		-- 1.3.6.1.4.1.7777.1.1.15
		normal_voltage_unbalance OBJECT-TYPE
			SYNTAX Integer32
			MAX-ACCESS read-only
			STATUS current
			DESCRIPTION
				"Normal voltage unbalance"
			::= { transferswitch 15 }

		
--    1.3.6.1.4.1.7777.1.2.1.18
-- 1.3.6.1.4.1.7777.1.1.18
-- 1.3.6.1.4.1.7777.1.1.18
		-- 1.3.6.1.4.1.7777.1.1.18
		emergency_voltage_phase_CA OBJECT-TYPE
			SYNTAX Integer32
			MAX-ACCESS read-only
			STATUS current
			DESCRIPTION
				"Emergency voltage phase CA"
			::= { transferswitch 18 }

		
--    1.3.6.1.4.1.7777.1.2.1.19
-- 1.3.6.1.4.1.7777.1.1.19
-- 1.3.6.1.4.1.7777.1.1.19
		-- 1.3.6.1.4.1.7777.1.1.19
		nominal_voltage OBJECT-TYPE
			SYNTAX Integer32
			MAX-ACCESS read-only
			STATUS current
			DESCRIPTION
				"Nominal voltage"
			::= { transferswitch 19 }

		
--    1.3.6.1.4.1.7777.1.2.1.20
-- 1.3.6.1.4.1.7777.1.1.20
-- 1.3.6.1.4.1.7777.1.1.20
		-- 1.3.6.1.4.1.7777.1.1.20
		nominal_frequency OBJECT-TYPE
			SYNTAX Integer32
			MAX-ACCESS read-only
			STATUS current
			DESCRIPTION
				"Nominal frequency"
			::= { transferswitch 20 }

		
--    1.3.6.1.4.1.7777.1.2.1.21
-- 1.3.6.1.4.1.7777.1.1.21
-- 1.3.6.1.4.1.7777.1.1.21
		-- 1.3.6.1.4.1.7777.1.1.21
		normal_source_3phase_sensing OBJECT-TYPE
			SYNTAX Integer32
			MAX-ACCESS read-only
			STATUS current
			DESCRIPTION
				"Normal source 3 phase sensing"
			::= { transferswitch 21 }

		
--    1.3.6.1.4.1.7777.1.2.1.22
-- 1.3.6.1.4.1.7777.1.1.22
-- 1.3.6.1.4.1.7777.1.1.22
		-- 1.3.6.1.4.1.7777.1.1.22
		transfer_switch_type OBJECT-TYPE
			SYNTAX Integer32
			MAX-ACCESS read-only
			STATUS current
			DESCRIPTION
				"Transfer switch type (OTTS,DTTS)"
			::= { transferswitch 22 }

		
--    1.3.6.1.4.1.7777.1.2.1.23
-- 1.3.6.1.4.1.7777.1.1.23
-- 1.3.6.1.4.1.7777.1.1.23
		-- 1.3.6.1.4.1.7777.1.1.23
		transfer_switch_ampere_rating OBJECT-TYPE
			SYNTAX Integer32
			MAX-ACCESS read-only
			STATUS current
			DESCRIPTION
				"Transfer switch ampere rating"
			::= { transferswitch 23 }

		
--    1.3.6.1.4.1.7777.1.2.1.24
-- 1.3.6.1.4.1.7777.1.1.24
-- 1.3.6.1.4.1.7777.1.1.24
		-- 1.3.6.1.4.1.7777.1.1.24
		controller_software_version OBJECT-TYPE
			SYNTAX DisplayString (SIZE (0..11))
			MAX-ACCESS read-only
			STATUS current
			DESCRIPTION
				"Controller software version"
			::= { transferswitch 24 }

		
--    1.3.6.1.4.1.7777.1.2.1.25
-- 1.3.6.1.4.1.7777.1.1.25
-- 1.3.6.1.4.1.7777.1.1.25
		-- 1.3.6.1.4.1.7777.1.1.25
		controller_software_date OBJECT-TYPE
			SYNTAX DisplayString (SIZE (0..11))
			MAX-ACCESS read-only
			STATUS current
			DESCRIPTION
				"Controller software date"
			::= { transferswitch 25 }

		
--    1.3.6.1.4.1.7777.1.2.1.26
-- 1.3.6.1.4.1.7777.1.1.26
-- 1.3.6.1.4.1.7777.1.1.26
		-- 1.3.6.1.4.1.7777.1.1.26
		external_parameter_lock_is_active OBJECT-TYPE
			SYNTAX Integer32
			MAX-ACCESS read-only
			STATUS current
			DESCRIPTION
				"External parameter lock is active"
			::= { transferswitch 26 }

		
--    1.3.6.1.4.1.7777.1.2.1.27
-- 1.3.6.1.4.1.7777.1.1.27
-- 1.3.6.1.4.1.7777.1.1.27
		-- 1.3.6.1.4.1.7777.1.1.27
		engine_running OBJECT-TYPE
			SYNTAX Integer32
			MAX-ACCESS read-only
			STATUS current
			DESCRIPTION
				"Engine running"
			::= { transferswitch 27 }

		
--    1.3.6.1.4.1.7777.1.2.1.28
-- 1.3.6.1.4.1.7777.1.1.28
-- 1.3.6.1.4.1.7777.1.1.28
		-- 1.3.6.1.4.1.7777.1.1.28
		controller_state OBJECT-TYPE
			SYNTAX Integer32
			MAX-ACCESS read-only
			STATUS current
			DESCRIPTION
				"Controller state"
			::= { transferswitch 28 }

		
--    1.3.6.1.4.1.7777.1.2.1.29
-- 1.3.6.1.4.1.7777.1.1.29
-- 1.3.6.1.4.1.7777.1.1.29
		-- 1.3.6.1.4.1.7777.1.1.29
		controller_status_state_data OBJECT-TYPE
			SYNTAX Integer32
			MAX-ACCESS read-only
			STATUS current
			DESCRIPTION
				"Controller status state data"
			::= { transferswitch 29 }

		
--    1.3.6.1.4.1.7777.1.2.1.30
-- 1.3.6.1.4.1.7777.1.1.30
-- 1.3.6.1.4.1.7777.1.1.30
		-- 1.3.6.1.4.1.7777.1.1.30
		timer_bypass_feature_6B_status OBJECT-TYPE
			SYNTAX Integer32
			MAX-ACCESS read-only
			STATUS current
			DESCRIPTION
				"Timer bypass (Feature 6B) status"
			::= { transferswitch 30 }

		
--    1.3.6.1.4.1.7777.1.2.1.31
-- 1.3.6.1.4.1.7777.1.1.31
-- 1.3.6.1.4.1.7777.1.1.31
		-- 1.3.6.1.4.1.7777.1.1.31
		remote_transfer_feature_17_status OBJECT-TYPE
			SYNTAX Integer32
			MAX-ACCESS read-only
			STATUS current
			DESCRIPTION
				"Remote transfer (Feature 17) status"
			::= { transferswitch 31 }

		
--    1.3.6.1.4.1.7777.1.2.1.32
-- 1.3.6.1.4.1.7777.1.1.32
-- 1.3.6.1.4.1.7777.1.1.32
		-- 1.3.6.1.4.1.7777.1.1.32
		load_shed_feature_30_status OBJECT-TYPE
			SYNTAX Integer32
			MAX-ACCESS read-only
			STATUS current
			DESCRIPTION
				"Load shed (Feature 30) status"
			::= { transferswitch 32 }

		
--    1.3.6.1.4.1.7777.1.2.1.33
-- 1.3.6.1.4.1.7777.1.1.33
-- 1.3.6.1.4.1.7777.1.1.33
		-- 1.3.6.1.4.1.7777.1.1.33
		transfer_inhibit_to_emergency_feature_34B_status OBJECT-TYPE
			SYNTAX Integer32
			MAX-ACCESS read-only
			STATUS current
			DESCRIPTION
				"Transfer inhibit to emergency (Feature 34B) status"
			::= { transferswitch 33 }

		
--    1.3.6.1.4.1.7777.1.2.1.34
-- 1.3.6.1.4.1.7777.1.1.34
-- 1.3.6.1.4.1.7777.1.1.34
		-- 1.3.6.1.4.1.7777.1.1.34
		local_test_feature_5_status OBJECT-TYPE
			SYNTAX Integer32
			MAX-ACCESS read-only
			STATUS current
			DESCRIPTION
				"Local test (Feature 5) status"
			::= { transferswitch 34 }

		
--    1.3.6.1.4.1.7777.1.2.1.35
-- 1.3.6.1.4.1.7777.1.1.35
-- 1.3.6.1.4.1.7777.1.1.35
		-- 1.3.6.1.4.1.7777.1.1.35
		manual_transfer_to_emergency_feature_6ZE_status OBJECT-TYPE
			SYNTAX Integer32
			MAX-ACCESS read-only
			STATUS current
			DESCRIPTION
				"Manual transfer to emergency (Feature 6ZE) status"
			::= { transferswitch 35 }

		
--    1.3.6.1.4.1.7777.1.2.1.36
-- 1.3.6.1.4.1.7777.1.1.36
-- 1.3.6.1.4.1.7777.1.1.36
		-- 1.3.6.1.4.1.7777.1.1.36
		current_sensing OBJECT-TYPE
			SYNTAX Integer32
			MAX-ACCESS read-only
			STATUS current
			DESCRIPTION
				"Current sensing"
			::= { transferswitch 36 }

		
--    1.3.6.1.4.1.7777.1.2.1.37
-- 1.3.6.1.4.1.7777.1.1.37
-- 1.3.6.1.4.1.7777.1.1.37
		-- 1.3.6.1.4.1.7777.1.1.37
		phase_A_current OBJECT-TYPE
			SYNTAX Integer32
			MAX-ACCESS read-only
			STATUS current
			DESCRIPTION
				"Phase A current (A).
				With 1 or 2 CT selected this is labeled as I1"
			::= { transferswitch 37 }

		
--    1.3.6.1.4.1.7777.1.2.1.38
-- 1.3.6.1.4.1.7777.1.1.38
-- 1.3.6.1.4.1.7777.1.1.38
		-- 1.3.6.1.4.1.7777.1.1.38
		phase_B_current OBJECT-TYPE
			SYNTAX Integer32
			MAX-ACCESS read-only
			STATUS current
			DESCRIPTION
				"Phase B current (A)"
			::= { transferswitch 38 }

		
--    1.3.6.1.4.1.7777.1.2.1.39
-- 1.3.6.1.4.1.7777.1.1.39
-- 1.3.6.1.4.1.7777.1.1.39
		-- 1.3.6.1.4.1.7777.1.1.39
		phase_C_current OBJECT-TYPE
			SYNTAX Integer32
			MAX-ACCESS read-only
			STATUS current
			DESCRIPTION
				"Phase C current (A).
				With 2 CT selected this is labeled as I2"
			::= { transferswitch 39 }

		
--    1.3.6.1.4.1.7777.1.2.1.40
-- 1.3.6.1.4.1.7777.1.1.40
-- 1.3.6.1.4.1.7777.1.1.40
		-- 1.3.6.1.4.1.7777.1.1.40
		failure_to_accept_timer OBJECT-TYPE
			SYNTAX Integer32
			MAX-ACCESS read-only
			STATUS current
			DESCRIPTION
				"Failure to accept timer"
			::= { transferswitch 40 }

		
--    1.3.6.1.4.1.7777.1.2.1.41
-- 1.3.6.1.4.1.7777.1.1.41
-- 1.3.6.1.4.1.7777.1.1.41
		-- 1.3.6.1.4.1.7777.1.1.41
		normal_to_emergency_pretransfer_time_delay_feature_31_bypass_enabled OBJECT-TYPE
			SYNTAX Integer32
			MAX-ACCESS read-only
			STATUS current
			DESCRIPTION
				"Normal to emergency pretransfer time delay (Feature 31) bypass enabled"
			::= { transferswitch 41 }

		
--    1.3.6.1.4.1.7777.1.2.1.42
-- 1.3.6.1.4.1.7777.1.1.42
-- 1.3.6.1.4.1.7777.1.1.42
		-- 1.3.6.1.4.1.7777.1.1.42
		emergency_to_normal_pretransfer_time_delay_feature_31_bypass_enabled OBJECT-TYPE
			SYNTAX Integer32
			MAX-ACCESS read-only
			STATUS current
			DESCRIPTION
				"Emergency to normal pretransfer time delay (Feature 31) bypass enabled"
			::= { transferswitch 42 }

		
--    1.3.6.1.4.1.7777.1.2.1.43
-- 1.3.6.1.4.1.7777.1.1.43
-- 1.3.6.1.4.1.7777.1.1.43
		-- 1.3.6.1.4.1.7777.1.1.43
		commit_to_transfer_enabled OBJECT-TYPE
			SYNTAX Integer32
			MAX-ACCESS read-only
			STATUS current
			DESCRIPTION
				"Commit to transfer enabled"
			::= { transferswitch 43 }

		
--    1.3.6.1.4.1.7777.1.2.1.44
-- 1.3.6.1.4.1.7777.1.1.44
-- 1.3.6.1.4.1.7777.1.1.44
		-- 1.3.6.1.4.1.7777.1.1.44
		bypass_DTTS_source_failure_enabled OBJECT-TYPE
			SYNTAX Integer32
			MAX-ACCESS read-only
			STATUS current
			DESCRIPTION
				"Bypass DTTS source failure enabled - data for DTTS and Group1 emulation is NOT enabled"
			::= { transferswitch 44 }

		
--    1.3.6.1.4.1.7777.1.2.1.45
-- 1.3.6.1.4.1.7777.1.1.45
-- 1.3.6.1.4.1.7777.1.1.45
		-- 1.3.6.1.4.1.7777.1.1.45
		inphase_transfer_enabled OBJECT-TYPE
			SYNTAX Integer32
			MAX-ACCESS read-only
			STATUS current
			DESCRIPTION
				"Inphase transfer enabled - only for OTTS"
			::= { transferswitch 45 }

		
--    1.3.6.1.4.1.7777.1.2.1.46
-- 1.3.6.1.4.1.7777.1.1.46
-- 1.3.6.1.4.1.7777.1.1.46
		-- 1.3.6.1.4.1.7777.1.1.46
		inphase_monitor_for_load_shed_feature_30_enabled OBJECT-TYPE
			SYNTAX Integer32
			MAX-ACCESS read-only
			STATUS current
			DESCRIPTION
				"Inphase monitor for load shed (Feature 30) enabled"
			::= { transferswitch 46 }

		
--    1.3.6.1.4.1.7777.1.2.1.47
-- 1.3.6.1.4.1.7777.1.1.47
-- 1.3.6.1.4.1.7777.1.1.47
		-- 1.3.6.1.4.1.7777.1.1.47
		fail_accept_timer_enabled OBJECT-TYPE
			SYNTAX Integer32
			MAX-ACCESS read-only
			STATUS current
			DESCRIPTION
				"Fail accept timer enabled"
			::= { transferswitch 47 }

		
--    1.3.6.1.4.1.7777.1.2.1.48
-- 1.3.6.1.4.1.7777.1.1.48
-- 1.3.6.1.4.1.7777.1.1.48
		-- 1.3.6.1.4.1.7777.1.1.48
		transfer_retransfer_time_delay_bypass_feature_6B_input_enabled OBJECT-TYPE
			SYNTAX Integer32
			MAX-ACCESS read-only
			STATUS current
			DESCRIPTION
				"Transfer/retransfer time delay bypass (Feature 6B) input enabled"
			::= { transferswitch 48 }

		
--    1.3.6.1.4.1.7777.1.2.1.49
-- 1.3.6.1.4.1.7777.1.1.49
-- 1.3.6.1.4.1.7777.1.1.49
		-- 1.3.6.1.4.1.7777.1.1.49
		remote_transfer_feature_17_input_enabled OBJECT-TYPE
			SYNTAX Integer32
			MAX-ACCESS read-only
			STATUS current
			DESCRIPTION
				"Remote transfer (Feature 17) input enabled - data for transfer switch in auto mode only"
			::= { transferswitch 49 }

		
--    1.3.6.1.4.1.7777.1.2.1.50
-- 1.3.6.1.4.1.7777.1.1.50
-- 1.3.6.1.4.1.7777.1.1.50
		-- 1.3.6.1.4.1.7777.1.1.50
		retransfer_to_normal_mode_selector_feature_6DL_input_enabled OBJECT-TYPE
			SYNTAX Integer32
			MAX-ACCESS read-only
			STATUS current
			DESCRIPTION
				"Retransfer to normal mode selector (Feature 6DL) enabled"
			::= { transferswitch 50 }

		
--    1.3.6.1.4.1.7777.1.2.1.51
-- 1.3.6.1.4.1.7777.1.1.51
-- 1.3.6.1.4.1.7777.1.1.51
		-- 1.3.6.1.4.1.7777.1.1.51
		serial_remote_transfer_feature_17_enabled OBJECT-TYPE
			SYNTAX Integer32
			MAX-ACCESS read-only
			STATUS current
			DESCRIPTION
				"Serial remote transfer (Feature 17) enabled"
			::= { transferswitch 51 }

		
--    1.3.6.1.4.1.7777.1.2.1.52
-- 1.3.6.1.4.1.7777.1.1.52
-- 1.3.6.1.4.1.7777.1.1.52
		-- 1.3.6.1.4.1.7777.1.1.52
		voltage_unbalance_enabled OBJECT-TYPE
			SYNTAX Integer32
			MAX-ACCESS read-only
			STATUS current
			DESCRIPTION
				"Voltage unbalance enabled"
			::= { transferswitch 52 }

		
--    1.3.6.1.4.1.7777.1.2.1.53
-- 1.3.6.1.4.1.7777.1.1.53
-- 1.3.6.1.4.1.7777.1.1.53
		-- 1.3.6.1.4.1.7777.1.1.53
		current_sensing_module_present OBJECT-TYPE
			SYNTAX Integer32
			MAX-ACCESS read-only
			STATUS current
			DESCRIPTION
				"Current sensing module present"
			::= { transferswitch 53 }

		
--    1.3.6.1.4.1.7777.1.2.1.54
-- 1.3.6.1.4.1.7777.1.1.54
-- 1.3.6.1.4.1.7777.1.1.54
		-- 1.3.6.1.4.1.7777.1.1.54
		alert_LED_active OBJECT-TYPE
			SYNTAX Integer32
			MAX-ACCESS read-only
			STATUS current
			DESCRIPTION
				"Alert LED active"
			::= { transferswitch 54 }

		
--    1.3.6.1.4.1.7777.1.2.1.55
-- 1.3.6.1.4.1.7777.1.1.55
-- 1.3.6.1.4.1.7777.1.1.55
		-- 1.3.6.1.4.1.7777.1.1.55
		not_in_auto_LED_active OBJECT-TYPE
			SYNTAX Integer32
			MAX-ACCESS read-only
			STATUS current
			DESCRIPTION
				"Not in Auto LED active"
			::= { transferswitch 55 }

		
--    1.3.6.1.4.1.7777.1.2.1.58
-- 1.3.6.1.4.1.7777.1.1.58
-- 1.3.6.1.4.1.7777.1.1.58
		-- 1.3.6.1.4.1.7777.1.1.58
		daylight_savings OBJECT-TYPE
			SYNTAX Integer32
			MAX-ACCESS read-only
			STATUS current
			DESCRIPTION
				"Daylight savings"
			::= { transferswitch 58 }

		
--    1.3.6.1.4.1.7777.1.2.1.59
-- 1.3.6.1.4.1.7777.1.1.59
-- 1.3.6.1.4.1.7777.1.1.59
		-- 1.3.6.1.4.1.7777.1.1.59
		loss_of_emergency_when_connected_to_emergency_alarm_enabled OBJECT-TYPE
			SYNTAX Integer32
			MAX-ACCESS read-only
			STATUS current
			DESCRIPTION
				"Loss of emergency when connected to emergency alarm enabled"
			::= { transferswitch 59 }

		
--    1.3.6.1.4.1.7777.1.2.1.60
-- 1.3.6.1.4.1.7777.1.1.60
-- 1.3.6.1.4.1.7777.1.1.60
		-- 1.3.6.1.4.1.7777.1.1.60
		expiration_of_failure_to_accept_timer_alarm_enabled OBJECT-TYPE
			SYNTAX Integer32
			MAX-ACCESS read-only
			STATUS current
			DESCRIPTION
				"Expiration of failure to accept timer alarm enabled"
			::= { transferswitch 60 }

		
--    1.3.6.1.4.1.7777.1.2.1.61
-- 1.3.6.1.4.1.7777.1.1.61
-- 1.3.6.1.4.1.7777.1.1.61
		-- 1.3.6.1.4.1.7777.1.1.61
		load_disconnect_enabled_DTTS_only OBJECT-TYPE
			SYNTAX Integer32
			MAX-ACCESS read-only
			STATUS current
			DESCRIPTION
				"Load disconnect enabled (DTTS only)"
			::= { transferswitch 61 }

		
--    1.3.6.1.4.1.7777.1.2.1.62
-- 1.3.6.1.4.1.7777.1.1.62
-- 1.3.6.1.4.1.7777.1.1.62
		-- 1.3.6.1.4.1.7777.1.1.62
		op1_is_feature_31 OBJECT-TYPE
			SYNTAX Integer32
			MAX-ACCESS read-only
			STATUS current
			DESCRIPTION
				"OP1 is Feature 31"
			::= { transferswitch 62 }

		
--    1.3.6.1.4.1.7777.1.2.1.63
-- 1.3.6.1.4.1.7777.1.1.63
-- 1.3.6.1.4.1.7777.1.1.63
		-- 1.3.6.1.4.1.7777.1.1.63
		op1_is_common_alarm OBJECT-TYPE
			SYNTAX Integer32
			MAX-ACCESS read-only
			STATUS current
			DESCRIPTION
				"OP1 is common alarm"
			::= { transferswitch 63 }

		
--    1.3.6.1.4.1.7777.1.2.1.64
-- 1.3.6.1.4.1.7777.1.1.64
-- 1.3.6.1.4.1.7777.1.1.64
		-- 1.3.6.1.4.1.7777.1.1.64
		op1_is_NR2 OBJECT-TYPE
			SYNTAX Integer32
			MAX-ACCESS read-only
			STATUS current
			DESCRIPTION
				"OP1 is NR2"
			::= { transferswitch 64 }

		
--    1.3.6.1.4.1.7777.1.2.1.65
-- 1.3.6.1.4.1.7777.1.1.65
-- 1.3.6.1.4.1.7777.1.1.65
		-- 1.3.6.1.4.1.7777.1.1.65
		op1_is_not_in_auto OBJECT-TYPE
			SYNTAX Integer32
			MAX-ACCESS read-only
			STATUS current
			DESCRIPTION
				"OP1 is not in auto"
			::= { transferswitch 65 }

		
--    1.3.6.1.4.1.7777.1.2.1.66
-- 1.3.6.1.4.1.7777.1.1.66
-- 1.3.6.1.4.1.7777.1.1.66
		-- 1.3.6.1.4.1.7777.1.1.66
		op2_is_feature_31 OBJECT-TYPE
			SYNTAX Integer32
			MAX-ACCESS read-only
			STATUS current
			DESCRIPTION
				"OP2 is Feature 31"
			::= { transferswitch 66 }

		
--    1.3.6.1.4.1.7777.1.2.1.67
-- 1.3.6.1.4.1.7777.1.1.67
-- 1.3.6.1.4.1.7777.1.1.67
		-- 1.3.6.1.4.1.7777.1.1.67
		op2_is_common_alarm OBJECT-TYPE
			SYNTAX Integer32
			MAX-ACCESS read-only
			STATUS current
			DESCRIPTION
				"OP2 is common alarm"
			::= { transferswitch 67 }

		
--    1.3.6.1.4.1.7777.1.2.1.68
-- 1.3.6.1.4.1.7777.1.1.68
-- 1.3.6.1.4.1.7777.1.1.68
		-- 1.3.6.1.4.1.7777.1.1.68
		op2_is_NR2 OBJECT-TYPE
			SYNTAX Integer32
			MAX-ACCESS read-only
			STATUS current
			DESCRIPTION
				"OP2 is NR2"
			::= { transferswitch 68 }

		
--    1.3.6.1.4.1.7777.1.2.1.69
-- 1.3.6.1.4.1.7777.1.1.69
-- 1.3.6.1.4.1.7777.1.1.69
		-- 1.3.6.1.4.1.7777.1.1.69
		op2_is_not_in_auto OBJECT-TYPE
			SYNTAX Integer32
			MAX-ACCESS read-only
			STATUS current
			DESCRIPTION
				"OP2 is not in auto"
			::= { transferswitch 69 }

		
--    1.3.6.1.4.1.7777.1.2.1.70
-- 1.3.6.1.4.1.7777.1.1.70
-- 1.3.6.1.4.1.7777.1.1.70
		-- 1.3.6.1.4.1.7777.1.1.70
		op2_1G_enabled OBJECT-TYPE
			SYNTAX Integer32
			MAX-ACCESS read-only
			STATUS current
			DESCRIPTION
				"OP2 1G enabled"
			::= { transferswitch 70 }

		
--    1.3.6.1.4.1.7777.1.2.1.71
-- 1.3.6.1.4.1.7777.1.1.71
-- 1.3.6.1.4.1.7777.1.1.71
		-- 1.3.6.1.4.1.7777.1.1.71
		op3_is_feature_31 OBJECT-TYPE
			SYNTAX Integer32
			MAX-ACCESS read-only
			STATUS current
			DESCRIPTION
				"OP3 is Feature 31"
			::= { transferswitch 71 }

		
--    1.3.6.1.4.1.7777.1.2.1.72
-- 1.3.6.1.4.1.7777.1.1.72
-- 1.3.6.1.4.1.7777.1.1.72
		-- 1.3.6.1.4.1.7777.1.1.72
		op3_is_common_alarm OBJECT-TYPE
			SYNTAX Integer32
			MAX-ACCESS read-only
			STATUS current
			DESCRIPTION
				"OP3 is common alarm"
			::= { transferswitch 72 }

		
--    1.3.6.1.4.1.7777.1.2.1.73
-- 1.3.6.1.4.1.7777.1.1.73
-- 1.3.6.1.4.1.7777.1.1.73
		-- 1.3.6.1.4.1.7777.1.1.73
		op3_is_NR2 OBJECT-TYPE
			SYNTAX Integer32
			MAX-ACCESS read-only
			STATUS current
			DESCRIPTION
				"OP2 is NR2"
			::= { transferswitch 73 }

		
--    1.3.6.1.4.1.7777.1.2.1.74
-- 1.3.6.1.4.1.7777.1.1.74
-- 1.3.6.1.4.1.7777.1.1.74
		-- 1.3.6.1.4.1.7777.1.1.74
		op3_is_not_in_auto OBJECT-TYPE
			SYNTAX Integer32
			MAX-ACCESS read-only
			STATUS current
			DESCRIPTION
				"OP3 is not in auto"
			::= { transferswitch 74 }

		
--    1.3.6.1.4.1.7777.1.2.1.75
-- 1.3.6.1.4.1.7777.1.1.75
-- 1.3.6.1.4.1.7777.1.1.75
		-- 1.3.6.1.4.1.7777.1.1.75
		controller_serial_number OBJECT-TYPE
			SYNTAX DisplayString (SIZE (0..13))
			MAX-ACCESS read-only
			STATUS current
			DESCRIPTION
				"Controller serial number"
			::= { transferswitch 75 }

		
--    1.3.6.1.4.1.7777.1.2.1.76
-- 1.3.6.1.4.1.7777.1.1.76
-- 1.3.6.1.4.1.7777.1.1.76
		-- 1.3.6.1.4.1.7777.1.1.76
		engine_exerciser_F11C_advanced_program_number OBJECT-TYPE
			SYNTAX Integer32
			MAX-ACCESS read-only
			STATUS current
			DESCRIPTION
				"Engine exerciser (F11C) advanced program number"
			::= { transferswitch 76 }

		
--    1.3.6.1.4.1.7777.1.2.1.77
-- 1.3.6.1.4.1.7777.1.1.77
-- 1.3.6.1.4.1.7777.1.1.77
		-- 1.3.6.1.4.1.7777.1.1.77
		engine_exerciser_F11C_enabled OBJECT-TYPE
			SYNTAX Integer32
			MAX-ACCESS read-only
			STATUS current
			DESCRIPTION
				"Engine exerciser (F11C) enabled"
			::= { transferswitch 77 }

		
--    1.3.6.1.4.1.7777.1.2.1.78
-- 1.3.6.1.4.1.7777.1.1.78
-- 1.3.6.1.4.1.7777.1.1.78
		-- 1.3.6.1.4.1.7777.1.1.78
		engine_exerciser_F11C_test_with_load_transfer_enabled OBJECT-TYPE
			SYNTAX Integer32
			MAX-ACCESS read-only
			STATUS current
			DESCRIPTION
				"Engine exerciser (F11C) test with load transfer enabled"
			::= { transferswitch 78 }

		
--    1.3.6.1.4.1.7777.1.2.1.79
-- 1.3.6.1.4.1.7777.1.1.79
-- 1.3.6.1.4.1.7777.1.1.79
		-- 1.3.6.1.4.1.7777.1.1.79
		engine_exerciser_F11C_start_week OBJECT-TYPE
			SYNTAX Integer32
			MAX-ACCESS read-only
			STATUS current
			DESCRIPTION
				"Engine exerciser (F11C) start week"
			::= { transferswitch 79 }

		
--    1.3.6.1.4.1.7777.1.2.1.80
-- 1.3.6.1.4.1.7777.1.1.80
-- 1.3.6.1.4.1.7777.1.1.80
		-- 1.3.6.1.4.1.7777.1.1.80
		engine_exerciser_F11C_day_of_week OBJECT-TYPE
			SYNTAX Integer32
			MAX-ACCESS read-only
			STATUS current
			DESCRIPTION
				"Engine exerciser (F11C) day of week"
			::= { transferswitch 80 }

		
--    1.3.6.1.4.1.7777.1.2.1.82
-- 1.3.6.1.4.1.7777.1.1.82
-- 1.3.6.1.4.1.7777.1.1.82
		-- 1.3.6.1.4.1.7777.1.1.82
		engine_exerciser_F11C_start_time_hours OBJECT-TYPE
			SYNTAX Integer32
			MAX-ACCESS read-only
			STATUS current
			DESCRIPTION
				"Engine exerciser (F11C) start time hours"
			::= { transferswitch 82 }

		
--    1.3.6.1.4.1.7777.1.2.1.83
-- 1.3.6.1.4.1.7777.1.1.83
-- 1.3.6.1.4.1.7777.1.1.83
		-- 1.3.6.1.4.1.7777.1.1.83
		engine_exerciser_F11C_start_time_minutes OBJECT-TYPE
			SYNTAX Integer32
			MAX-ACCESS read-only
			STATUS current
			DESCRIPTION
				"Engine exerciser (F11C) start time minutes"
			::= { transferswitch 83 }

		
--    1.3.6.1.4.1.7777.1.2.1.84
-- 1.3.6.1.4.1.7777.1.1.84
-- 1.3.6.1.4.1.7777.1.1.84
		-- 1.3.6.1.4.1.7777.1.1.84
		engine_exerciser_F11C_run_time_hours OBJECT-TYPE
			SYNTAX Integer32
			MAX-ACCESS read-only
			STATUS current
			DESCRIPTION
				"Engine exerciser (F11C) run time hours"
			::= { transferswitch 84 }

		
--    1.3.6.1.4.1.7777.1.2.1.85
-- 1.3.6.1.4.1.7777.1.1.85
-- 1.3.6.1.4.1.7777.1.1.85
		-- 1.3.6.1.4.1.7777.1.1.85
		engine_exerciser_F11C_run_time_minutes OBJECT-TYPE
			SYNTAX Integer32
			MAX-ACCESS read-only
			STATUS current
			DESCRIPTION
				"Engine exerciser (F11C) schedule run time minutes"
			::= { transferswitch 85 }

		
--    1.3.6.1.4.1.7777.1.2.1.86
-- 1.3.6.1.4.1.7777.1.1.86
-- 1.3.6.1.4.1.7777.1.1.86
		-- 1.3.6.1.4.1.7777.1.1.86
		normal_voltage_dropout OBJECT-TYPE
			SYNTAX Integer32
			MAX-ACCESS read-only
			STATUS current
			DESCRIPTION
				"Normal voltage dropout"
			::= { transferswitch 86 }

		
--    1.3.6.1.4.1.7777.1.2.1.87
-- 1.3.6.1.4.1.7777.1.1.87
-- 1.3.6.1.4.1.7777.1.1.87
		-- 1.3.6.1.4.1.7777.1.1.87
		normal_voltage_pickup OBJECT-TYPE
			SYNTAX Integer32
			MAX-ACCESS read-only
			STATUS current
			DESCRIPTION
				"Normal voltage pickup"
			::= { transferswitch 87 }

		
--    1.3.6.1.4.1.7777.1.2.1.88
-- 1.3.6.1.4.1.7777.1.1.88
-- 1.3.6.1.4.1.7777.1.1.88
		-- 1.3.6.1.4.1.7777.1.1.88
		normal_over_voltage_trip OBJECT-TYPE
			SYNTAX Integer32
			MAX-ACCESS read-only
			STATUS current
			DESCRIPTION
				"Normal over voltage trip"
			::= { transferswitch 88 }

		
--    1.3.6.1.4.1.7777.1.2.1.89
-- 1.3.6.1.4.1.7777.1.1.89
-- 1.3.6.1.4.1.7777.1.1.89
		-- 1.3.6.1.4.1.7777.1.1.89
		normal_frequency_dropout OBJECT-TYPE
			SYNTAX Integer32
			MAX-ACCESS read-only
			STATUS current
			DESCRIPTION
				"Normal frequency dropout"
			::= { transferswitch 89 }

		
--    1.3.6.1.4.1.7777.1.2.1.90
-- 1.3.6.1.4.1.7777.1.1.90
-- 1.3.6.1.4.1.7777.1.1.90
		-- 1.3.6.1.4.1.7777.1.1.90
		normal_frequency_pickup OBJECT-TYPE
			SYNTAX Integer32
			MAX-ACCESS read-only
			STATUS current
			DESCRIPTION
				"Normal frequency pickup"
			::= { transferswitch 90 }

		
--    1.3.6.1.4.1.7777.1.2.1.91
-- 1.3.6.1.4.1.7777.1.1.91
-- 1.3.6.1.4.1.7777.1.1.91
		-- 1.3.6.1.4.1.7777.1.1.91
		normal_over_frequency_trip OBJECT-TYPE
			SYNTAX Integer32
			MAX-ACCESS read-only
			STATUS current
			DESCRIPTION
				"Normal over frequency trip"
			::= { transferswitch 91 }

		
--    1.3.6.1.4.1.7777.1.2.1.92
-- 1.3.6.1.4.1.7777.1.1.92
-- 1.3.6.1.4.1.7777.1.1.92
		-- 1.3.6.1.4.1.7777.1.1.92
		emergency_voltage_dropout OBJECT-TYPE
			SYNTAX Integer32
			MAX-ACCESS read-only
			STATUS current
			DESCRIPTION
				"Emergency voltage dropout"
			::= { transferswitch 92 }

		
--    1.3.6.1.4.1.7777.1.2.1.93
-- 1.3.6.1.4.1.7777.1.1.93
-- 1.3.6.1.4.1.7777.1.1.93
		-- 1.3.6.1.4.1.7777.1.1.93
		emergency_voltage_pickup OBJECT-TYPE
			SYNTAX Integer32
			MAX-ACCESS read-only
			STATUS current
			DESCRIPTION
				"Emergency voltage pickup"
			::= { transferswitch 93 }

		
--    1.3.6.1.4.1.7777.1.2.1.94
-- 1.3.6.1.4.1.7777.1.1.94
-- 1.3.6.1.4.1.7777.1.1.94
		-- 1.3.6.1.4.1.7777.1.1.94
		emergency_over_voltage_trip OBJECT-TYPE
			SYNTAX Integer32
			MAX-ACCESS read-only
			STATUS current
			DESCRIPTION
				"Emergency over voltage trip"
			::= { transferswitch 94 }

		
--    1.3.6.1.4.1.7777.1.2.1.95
-- 1.3.6.1.4.1.7777.1.1.95
-- 1.3.6.1.4.1.7777.1.1.95
		-- 1.3.6.1.4.1.7777.1.1.95
		emergency_frequency_dropout OBJECT-TYPE
			SYNTAX Integer32
			MAX-ACCESS read-only
			STATUS current
			DESCRIPTION
				"Emergency frequency dropout"
			::= { transferswitch 95 }

		
--    1.3.6.1.4.1.7777.1.2.1.96
-- 1.3.6.1.4.1.7777.1.1.96
-- 1.3.6.1.4.1.7777.1.1.96
		-- 1.3.6.1.4.1.7777.1.1.96
		emergency_frequency_pickup OBJECT-TYPE
			SYNTAX Integer32
			MAX-ACCESS read-only
			STATUS current
			DESCRIPTION
				"Emergency frequency pickup"
			::= { transferswitch 96 }

		
--    1.3.6.1.4.1.7777.1.2.1.97
-- 1.3.6.1.4.1.7777.1.1.97
-- 1.3.6.1.4.1.7777.1.1.97
		-- 1.3.6.1.4.1.7777.1.1.97
		emergency_over_frequency_trip OBJECT-TYPE
			SYNTAX Integer32
			MAX-ACCESS read-only
			STATUS current
			DESCRIPTION
				"Emergency over frequency trip"
			::= { transferswitch 97 }

		
--    1.3.6.1.4.1.7777.1.2.1.98
-- 1.3.6.1.4.1.7777.1.1.98
-- 1.3.6.1.4.1.7777.1.1.98
		-- 1.3.6.1.4.1.7777.1.1.98
		timer_1C_engine_start_time_delay OBJECT-TYPE
			SYNTAX Integer32
			MAX-ACCESS read-only
			STATUS current
			DESCRIPTION
				"Timer 1C engine start time delay"
			::= { transferswitch 98 }

		
--    1.3.6.1.4.1.7777.1.2.1.99
-- 1.3.6.1.4.1.7777.1.1.99
-- 1.3.6.1.4.1.7777.1.1.99
		-- 1.3.6.1.4.1.7777.1.1.99
		timer_1F_engine_fail_time_delay OBJECT-TYPE
			SYNTAX Integer32
			MAX-ACCESS read-only
			STATUS current
			DESCRIPTION
				"Timer 1F engine fail time delay"
			::= { transferswitch 99 }

		
--    1.3.6.1.4.1.7777.1.2.1.100
-- 1.3.6.1.4.1.7777.1.1.100
-- 1.3.6.1.4.1.7777.1.1.100
		-- 1.3.6.1.4.1.7777.1.1.100
		timer_2B_transfer_N_to_E_time_delay OBJECT-TYPE
			SYNTAX Integer32
			MAX-ACCESS read-only
			STATUS current
			DESCRIPTION
				"Timer 2B transfer N to E time delay"
			::= { transferswitch 100 }

		
--    1.3.6.1.4.1.7777.1.2.1.101
-- 1.3.6.1.4.1.7777.1.1.101
-- 1.3.6.1.4.1.7777.1.1.101
		-- 1.3.6.1.4.1.7777.1.1.101
		timer_2E_engine_cool_down_time_delay OBJECT-TYPE
			SYNTAX Integer32
			MAX-ACCESS read-only
			STATUS current
			DESCRIPTION
				"Timer 2E engine cool down time delay"
			::= { transferswitch 101 }

		
--    1.3.6.1.4.1.7777.1.2.1.102
-- 1.3.6.1.4.1.7777.1.1.102
-- 1.3.6.1.4.1.7777.1.1.102
		-- 1.3.6.1.4.1.7777.1.1.102
		timer_3AF_transfer_E_to_N_on_source_fail_time_delay OBJECT-TYPE
			SYNTAX Integer32
			MAX-ACCESS read-only
			STATUS current
			DESCRIPTION
				"Timer 3AF transfer E to N on source fail time delay"
			::= { transferswitch 102 }

		
--    1.3.6.1.4.1.7777.1.2.1.103
-- 1.3.6.1.4.1.7777.1.1.103
-- 1.3.6.1.4.1.7777.1.1.103
		-- 1.3.6.1.4.1.7777.1.1.103
		timer_3A_T_transfer_E_to_N_on_test_time_delay OBJECT-TYPE
			SYNTAX Integer32
			MAX-ACCESS read-only
			STATUS current
			DESCRIPTION
				"Timer 3A T transfer E to N on test time delay"
			::= { transferswitch 103 }

		
--    1.3.6.1.4.1.7777.1.2.1.104
-- 1.3.6.1.4.1.7777.1.1.104
-- 1.3.6.1.4.1.7777.1.1.104
		-- 1.3.6.1.4.1.7777.1.1.104
		timer_31F_N_to_E_pre_transfer_signal_time_delay OBJECT-TYPE
			SYNTAX Integer32
			MAX-ACCESS read-only
			STATUS current
			DESCRIPTION
				"Timer 31F N to E pre transfer signal time delay"
			::= { transferswitch 104 }

		
--    1.3.6.1.4.1.7777.1.2.1.105
-- 1.3.6.1.4.1.7777.1.1.105
-- 1.3.6.1.4.1.7777.1.1.105
		-- 1.3.6.1.4.1.7777.1.1.105
		timer_31M_N_to_E_post_transfer_signal_time_delay OBJECT-TYPE
			SYNTAX Integer32
			MAX-ACCESS read-only
			STATUS current
			DESCRIPTION
				"Timer 31M N to E post transfer signal time delay"
			::= { transferswitch 105 }

		
--    1.3.6.1.4.1.7777.1.2.1.106
-- 1.3.6.1.4.1.7777.1.1.106
-- 1.3.6.1.4.1.7777.1.1.106
		-- 1.3.6.1.4.1.7777.1.1.106
		timer_31G_E_to_N_pre_transfer_signal_time_delay OBJECT-TYPE
			SYNTAX Integer32
			MAX-ACCESS read-only
			STATUS current
			DESCRIPTION
				"Timer 31G E to N pre transfer signal time delay"
			::= { transferswitch 106 }

		
--    1.3.6.1.4.1.7777.1.2.1.107
-- 1.3.6.1.4.1.7777.1.1.107
-- 1.3.6.1.4.1.7777.1.1.107
		-- 1.3.6.1.4.1.7777.1.1.107
		timer_31N_E_to_N_post_transfer_signal_time_delay OBJECT-TYPE
			SYNTAX Integer32
			MAX-ACCESS read-only
			STATUS current
			DESCRIPTION
				"Timer 31N  E to N post transfer signal time delay"
			::= { transferswitch 107 }

		
--    1.3.6.1.4.1.7777.1.2.1.108
-- 1.3.6.1.4.1.7777.1.1.108
-- 1.3.6.1.4.1.7777.1.1.108
		-- 1.3.6.1.4.1.7777.1.1.108
		dtts_load_disconnect_time_delay OBJECT-TYPE
			SYNTAX Integer32
			MAX-ACCESS read-only
			STATUS current
			DESCRIPTION
				"DTTS load disconnect time delay"
			::= { transferswitch 108 }

		
--    1.3.6.1.4.1.7777.1.2.1.109
-- 1.3.6.1.4.1.7777.1.1.109
-- 1.3.6.1.4.1.7777.1.1.109
		-- 1.3.6.1.4.1.7777.1.1.109
		commit_to_transfer_after_engine_start OBJECT-TYPE
			SYNTAX Integer32
			MAX-ACCESS read-only
			STATUS current
			DESCRIPTION
				"Commit to transfer after engine start"
			::= { transferswitch 109 }

		
--    1.3.6.1.4.1.7777.1.2.1.110
-- 1.3.6.1.4.1.7777.1.1.110
-- 1.3.6.1.4.1.7777.1.1.110
		-- 1.3.6.1.4.1.7777.1.1.110
		real_time_hour OBJECT-TYPE
			SYNTAX Integer32
			MAX-ACCESS read-only
			STATUS current
			DESCRIPTION
				"Real time hour"
			::= { transferswitch 110 }

		
--    1.3.6.1.4.1.7777.1.2.1.111
-- 1.3.6.1.4.1.7777.1.1.111
-- 1.3.6.1.4.1.7777.1.1.111
		-- 1.3.6.1.4.1.7777.1.1.111
		real_time_minute OBJECT-TYPE
			SYNTAX Integer32
			MAX-ACCESS read-only
			STATUS current
			DESCRIPTION
				"Real time minute"
			::= { transferswitch 111 }

		
--    1.3.6.1.4.1.7777.1.2.1.112
-- 1.3.6.1.4.1.7777.1.1.112
-- 1.3.6.1.4.1.7777.1.1.112
		-- 1.3.6.1.4.1.7777.1.1.112
		real_time_second OBJECT-TYPE
			SYNTAX Integer32
			MAX-ACCESS read-only
			STATUS current
			DESCRIPTION
				"Real time second"
			::= { transferswitch 112 }

		
--    1.3.6.1.4.1.7777.1.2.1.113
-- 1.3.6.1.4.1.7777.1.1.113
-- 1.3.6.1.4.1.7777.1.1.113
		-- 1.3.6.1.4.1.7777.1.1.113
		calendar_year OBJECT-TYPE
			SYNTAX Integer32
			MAX-ACCESS read-only
			STATUS current
			DESCRIPTION
				"Calendar year"
			::= { transferswitch 113 }

		
--    1.3.6.1.4.1.7777.1.2.1.114
-- 1.3.6.1.4.1.7777.1.1.114
-- 1.3.6.1.4.1.7777.1.1.114
		-- 1.3.6.1.4.1.7777.1.1.114
		calendar_month OBJECT-TYPE
			SYNTAX Integer32
			MAX-ACCESS read-only
			STATUS current
			DESCRIPTION
				"Calendar month"
			::= { transferswitch 114 }

		
--    1.3.6.1.4.1.7777.1.2.1.115
-- 1.3.6.1.4.1.7777.1.1.115
-- 1.3.6.1.4.1.7777.1.1.115
		-- 1.3.6.1.4.1.7777.1.1.115
		calendar_day_of_month OBJECT-TYPE
			SYNTAX Integer32
			MAX-ACCESS read-only
			STATUS current
			DESCRIPTION
				"Calendar day of month"
			::= { transferswitch 115 }

		
--    1.3.6.1.4.1.7777.1.2.1.116
-- 1.3.6.1.4.1.7777.1.1.116
-- 1.3.6.1.4.1.7777.1.1.116
		-- 1.3.6.1.4.1.7777.1.1.116
		calendar_day_of_week OBJECT-TYPE
			SYNTAX Integer32
			MAX-ACCESS read-only
			STATUS current
			DESCRIPTION
				"Calendar day of week"
			::= { transferswitch 116 }

		
--    1.3.6.1.4.1.7777.1.2.1.117
-- 1.3.6.1.4.1.7777.1.1.117
-- 1.3.6.1.4.1.7777.1.1.117
		-- 1.3.6.1.4.1.7777.1.1.117
		total_time_E_has_been_acceptable_high_word OBJECT-TYPE
			SYNTAX Integer32
			MAX-ACCESS read-only
			STATUS current
			DESCRIPTION
				"Total time E has been acceptable(high word)"
			::= { transferswitch 117 }

		
--    1.3.6.1.4.1.7777.1.2.1.118
-- 1.3.6.1.4.1.7777.1.1.118
-- 1.3.6.1.4.1.7777.1.1.118
		-- 1.3.6.1.4.1.7777.1.1.118
		total_time_E_has_been_acceptable_low_word OBJECT-TYPE
			SYNTAX Integer32
			MAX-ACCESS read-only
			STATUS current
			DESCRIPTION
				"Total time E has been acceptable(low word)"
			::= { transferswitch 118 }

		
--    1.3.6.1.4.1.7777.1.2.1.119
-- 1.3.6.1.4.1.7777.1.1.119
-- 1.3.6.1.4.1.7777.1.1.119
		-- 1.3.6.1.4.1.7777.1.1.119
		total_time_N_has_been_acceptable_high_word OBJECT-TYPE
			SYNTAX Integer32
			MAX-ACCESS read-only
			STATUS current
			DESCRIPTION
				"Total time N has been acceptable(high word)"
			::= { transferswitch 119 }

		
--    1.3.6.1.4.1.7777.1.2.1.120
-- 1.3.6.1.4.1.7777.1.1.120
-- 1.3.6.1.4.1.7777.1.1.120
		-- 1.3.6.1.4.1.7777.1.1.120
		total_time_N_has_been_acceptable_low_word OBJECT-TYPE
			SYNTAX Integer32
			MAX-ACCESS read-only
			STATUS current
			DESCRIPTION
				"Total time N has been acceptable(low word)"
			::= { transferswitch 120 }

		
--    1.3.6.1.4.1.7777.1.2.1.121
-- 1.3.6.1.4.1.7777.1.1.121
-- 1.3.6.1.4.1.7777.1.1.121
		-- 1.3.6.1.4.1.7777.1.1.121
		total_number_of_days_CP_has_been_energized OBJECT-TYPE
			SYNTAX Integer32
			MAX-ACCESS read-only
			STATUS current
			DESCRIPTION
				"Total number of days CP has been energized"
			::= { transferswitch 121 }

		
--    1.3.6.1.4.1.7777.1.2.1.122
-- 1.3.6.1.4.1.7777.1.1.122
-- 1.3.6.1.4.1.7777.1.1.122
		-- 1.3.6.1.4.1.7777.1.1.122
		total_number_of_TS_transfers OBJECT-TYPE
			SYNTAX Integer32
			MAX-ACCESS read-only
			STATUS current
			DESCRIPTION
				"Total number of TS transfers"
			::= { transferswitch 122 }

		
--    1.3.6.1.4.1.7777.1.2.1.123
-- 1.3.6.1.4.1.7777.1.1.123
-- 1.3.6.1.4.1.7777.1.1.123
		-- 1.3.6.1.4.1.7777.1.1.123
		total_number_of_TS_transfers_due_to_source_failures OBJECT-TYPE
			SYNTAX Integer32
			MAX-ACCESS read-only
			STATUS current
			DESCRIPTION
				"Total number of TS transfers due to source failures"
			::= { transferswitch 123 }

		
--    1.3.6.1.4.1.7777.1.2.1.124
-- 1.3.6.1.4.1.7777.1.1.124
-- 1.3.6.1.4.1.7777.1.1.124
		-- 1.3.6.1.4.1.7777.1.1.124
		controller_location OBJECT-TYPE
			SYNTAX DisplayString (SIZE (0..21))
			MAX-ACCESS read-only
			STATUS current
			DESCRIPTION
				"Controller location"
			::= { transferswitch 124 }

		
--    1.3.6.1.4.1.7777.1.2.1.125
-- 1.3.6.1.4.1.7777.1.1.125
-- 1.3.6.1.4.1.7777.1.1.125
		-- 1.3.6.1.4.1.7777.1.1.125
		external_feature_5_enabled OBJECT-TYPE
			SYNTAX Integer32
			MAX-ACCESS read-only
			STATUS current
			DESCRIPTION
				"External Feature 5 enabled"
			::= { transferswitch 125 }

		
--    1.3.6.1.4.1.7777.1.2.1.126
-- 1.3.6.1.4.1.7777.1.1.126
-- 1.3.6.1.4.1.7777.1.1.126
		-- 1.3.6.1.4.1.7777.1.1.126
		external_feature_34_enabled OBJECT-TYPE
			SYNTAX Integer32
			MAX-ACCESS read-only
			STATUS current
			DESCRIPTION
				"External Feature 34 enabled"
			::= { transferswitch 126 }

		
--    1.3.6.1.4.1.7777.1.2.1.127
-- 1.3.6.1.4.1.7777.1.1.127
-- 1.3.6.1.4.1.7777.1.1.127
		-- 1.3.6.1.4.1.7777.1.1.127
		inphase_filter_enabled OBJECT-TYPE
			SYNTAX Integer32
			MAX-ACCESS read-only
			STATUS current
			DESCRIPTION
				"In-phase filter enabled"
			::= { transferswitch 127 }

		
--    1.3.6.1.4.1.7777.1.2.1.128
-- 1.3.6.1.4.1.7777.1.1.128
-- 1.3.6.1.4.1.7777.1.1.128
		-- 1.3.6.1.4.1.7777.1.1.128
		current_sensing_option_installed OBJECT-TYPE
			SYNTAX Integer32
			MAX-ACCESS read-only
			STATUS current
			DESCRIPTION
				"Current sensing option installed"
			::= { transferswitch 128 }

		
--    1.3.6.1.4.1.7777.1.2.1.129
-- 1.3.6.1.4.1.7777.1.1.129
-- 1.3.6.1.4.1.7777.1.1.129
		-- 1.3.6.1.4.1.7777.1.1.129
		advanced_11C_option_installed OBJECT-TYPE
			SYNTAX Integer32
			MAX-ACCESS read-only
			STATUS current
			DESCRIPTION
				"Advanced 11C option Installed"
			::= { transferswitch 129 }

		
--    1.3.6.1.4.1.7777.1.2.1.130
-- 1.3.6.1.4.1.7777.1.1.130
-- 1.3.6.1.4.1.7777.1.1.130
		-- 1.3.6.1.4.1.7777.1.1.130
		event_log_option_installed OBJECT-TYPE
			SYNTAX Integer32
			MAX-ACCESS read-only
			STATUS current
			DESCRIPTION
				"Event log option Installed"
			::= { transferswitch 130 }

		
--    1.3.6.1.4.1.7777.1.2.1.131
-- 1.3.6.1.4.1.7777.1.1.131
-- 1.3.6.1.4.1.7777.1.1.131
		-- 1.3.6.1.4.1.7777.1.1.131
		rs485_communication_option_installed OBJECT-TYPE
			SYNTAX Integer32
			MAX-ACCESS read-only
			STATUS current
			DESCRIPTION
				"RS485 communication option Installed"
			::= { transferswitch 131 }

		
--    1.3.6.1.4.1.7777.1.2.1.132
-- 1.3.6.1.4.1.7777.1.1.132
-- 1.3.6.1.4.1.7777.1.1.132
		-- 1.3.6.1.4.1.7777.1.1.132
		op1_common_alarm_option_installed OBJECT-TYPE
			SYNTAX Integer32
			MAX-ACCESS read-only
			STATUS current
			DESCRIPTION
				"OP1 common alarm option Installed"
			::= { transferswitch 132 }

		
--    1.3.6.1.4.1.7777.1.2.1.133
-- 1.3.6.1.4.1.7777.1.1.133
-- 1.3.6.1.4.1.7777.1.1.133
		-- 1.3.6.1.4.1.7777.1.1.133
		total_time_load_connected_to_normal_high_word OBJECT-TYPE
			SYNTAX Integer32
			MAX-ACCESS read-only
			STATUS current
			DESCRIPTION
				"Total time load connected to normal (high word)"
			::= { transferswitch 133 }

		
--    1.3.6.1.4.1.7777.1.2.1.134
-- 1.3.6.1.4.1.7777.1.1.134
-- 1.3.6.1.4.1.7777.1.1.134
		-- 1.3.6.1.4.1.7777.1.1.134
		total_time_load_connected_to_normal_low_word OBJECT-TYPE
			SYNTAX Integer32
			MAX-ACCESS read-only
			STATUS current
			DESCRIPTION
				"Total time load connected to normal (low word)"
			::= { transferswitch 134 }

		
--    1.3.6.1.4.1.7777.1.2.1.135
-- 1.3.6.1.4.1.7777.1.1.135
-- 1.3.6.1.4.1.7777.1.1.135
		-- 1.3.6.1.4.1.7777.1.1.135
		total_time_load_connected_to_emergency_high_word OBJECT-TYPE
			SYNTAX Integer32
			MAX-ACCESS read-only
			STATUS current
			DESCRIPTION
				"Total time load connected to emergency (high word)"
			::= { transferswitch 135 }

		
--    1.3.6.1.4.1.7777.1.2.1.136
-- 1.3.6.1.4.1.7777.1.1.136
-- 1.3.6.1.4.1.7777.1.1.136
		-- 1.3.6.1.4.1.7777.1.1.136
		total_time_load_connected_to_emergency_low_word OBJECT-TYPE
			SYNTAX Integer32
			MAX-ACCESS read-only
			STATUS current
			DESCRIPTION
				"Total time load connected to emergency (low word)"
			::= { transferswitch 136 }

		
--    1.3.6.1.4.1.7777.1.2.1.137
-- 1.3.6.1.4.1.7777.1.1.137
-- 1.3.6.1.4.1.7777.1.1.137
		-- 1.3.6.1.4.1.7777.1.1.137
		rs485_port_address OBJECT-TYPE
			SYNTAX Integer32
			MAX-ACCESS read-only
			STATUS current
			DESCRIPTION
				"RS-485 port address"
			::= { transferswitch 137 }

		
--    1.3.6.1.4.1.7777.1.2.1.138
-- 1.3.6.1.4.1.7777.1.1.138
-- 1.3.6.1.4.1.7777.1.1.138
		-- 1.3.6.1.4.1.7777.1.1.138
		rs485_port_baud_rate OBJECT-TYPE
			SYNTAX Integer32
			MAX-ACCESS read-only
			STATUS current
			DESCRIPTION
				"RS-485 port baud rate"
			::= { transferswitch 138 }

		
--    1.3.6.1.4.1.7777.1.2.1.139
-- 1.3.6.1.4.1.7777.1.1.139
-- 1.3.6.1.4.1.7777.1.1.139
		-- 1.3.6.1.4.1.7777.1.1.139
		rs485_port_protocol OBJECT-TYPE
			SYNTAX Integer32
			MAX-ACCESS read-only
			STATUS current
			DESCRIPTION
				"RS-485 port protocol"
			::= { transferswitch 139 }

		
--    1.3.6.1.4.1.7777.1.2.1.140
-- 1.3.6.1.4.1.7777.1.1.140
-- 1.3.6.1.4.1.7777.1.1.140
		-- 1.3.6.1.4.1.7777.1.1.140
		emulate_group_1 OBJECT-TYPE
			SYNTAX Integer32
			MAX-ACCESS read-only
			STATUS current
			DESCRIPTION
				"Emulate Group 1"
			::= { transferswitch 140 }

		
--    1.3.6.1.4.1.7777.1.2.1.141
-- 1.3.6.1.4.1.7777.1.1.141
-- 1.3.6.1.4.1.7777.1.1.141
		-- 1.3.6.1.4.1.7777.1.1.141
		dtts_load_disconnect_recovery_mode_manual_or_auto OBJECT-TYPE
			SYNTAX Integer32
			MAX-ACCESS read-only
			STATUS current
			DESCRIPTION
				"DTTS load disconnect recovery mode - manual or auto"
			::= { transferswitch 141 }

		
--    1.3.6.1.4.1.7777.1.2.1.142
-- 1.3.6.1.4.1.7777.1.1.142
-- 1.3.6.1.4.1.7777.1.1.142
		-- 1.3.6.1.4.1.7777.1.1.142
		timer_2B_transfer_N_to_E_on_test_time_delay OBJECT-TYPE
			SYNTAX Integer32
			MAX-ACCESS read-only
			STATUS current
			DESCRIPTION
				"Timer 2B transfer N to E on test time delay"
			::= { transferswitch 142 }

		
--    1.3.6.1.4.1.7777.1.2.1.143
-- 1.3.6.1.4.1.7777.1.1.143
-- 1.3.6.1.4.1.7777.1.1.143
		-- 1.3.6.1.4.1.7777.1.1.143
		inphase_monitor_time_delay OBJECT-TYPE
			SYNTAX Integer32
			MAX-ACCESS read-only
			STATUS current
			DESCRIPTION
				"Inphase monitor time delay"
			::= { transferswitch 143 }

		
--    1.3.6.1.4.1.7777.1.2.1.144
-- 1.3.6.1.4.1.7777.1.1.144
-- 1.3.6.1.4.1.7777.1.1.144
		-- 1.3.6.1.4.1.7777.1.1.144
		ats_total_transfer_time_in_10th_seconds OBJECT-TYPE
			SYNTAX Integer32
			MAX-ACCESS read-only
			STATUS current
			DESCRIPTION
				"ATS total transfer time in 10th seconds (real value in seconds requires division by 10)"
			::= { transferswitch 144 }

		
--    1.3.6.1.4.1.7777.1.2.1.145
-- 1.3.6.1.4.1.7777.1.1.145
-- 1.3.6.1.4.1.7777.1.1.145
		-- 1.3.6.1.4.1.7777.1.1.145
		dongle_installed OBJECT-TYPE
			SYNTAX Integer32
			MAX-ACCESS read-only
			STATUS current
			DESCRIPTION
				"Dongle installed"
			::= { transferswitch 145 }

		
--    1.3.6.1.4.1.7777.1.2.1.146
-- 1.3.6.1.4.1.7777.1.1.146
-- 1.3.6.1.4.1.7777.1.1.146
		-- 1.3.6.1.4.1.7777.1.1.146
		language_selection_setting OBJECT-TYPE
			SYNTAX Integer32
			MAX-ACCESS read-only
			STATUS current
			DESCRIPTION
				"Language selection setting"
			::= { transferswitch 146 }

		
--    1.3.6.1.4.1.7777.1.2.1.147
-- 1.3.6.1.4.1.7777.1.1.147
-- 1.3.6.1.4.1.7777.1.1.147
		-- 1.3.6.1.4.1.7777.1.1.147
		lcd_contrast_setting OBJECT-TYPE
			SYNTAX Integer32
			MAX-ACCESS read-only
			STATUS current
			DESCRIPTION
				"LCD contrast setting"
			::= { transferswitch 147 }

		
--    1.3.6.1.4.1.7777.1.2.1.148
-- 1.3.6.1.4.1.7777.1.1.148
-- 1.3.6.1.4.1.7777.1.1.148
		-- 1.3.6.1.4.1.7777.1.1.148
		controller_name OBJECT-TYPE
			SYNTAX DisplayString (SIZE (0..21))
			MAX-ACCESS read-only
			STATUS current
			DESCRIPTION
				"Controller name"
			::= { transferswitch 148 }

		
--    1.3.6.1.4.1.7777.1.2.1.149
-- 1.3.6.1.4.1.7777.1.1.149
-- 1.3.6.1.4.1.7777.1.1.149
		-- 1.3.6.1.4.1.7777.1.1.149
		boot_loader_version OBJECT-TYPE
			SYNTAX DisplayString (SIZE (0..11))
			MAX-ACCESS read-only
			STATUS current
			DESCRIPTION
				"Boot loader version"
			::= { transferswitch 149 }

		
--    1.3.6.1.4.1.7777.1.2.1.150
-- 1.3.6.1.4.1.7777.1.1.150
-- 1.3.6.1.4.1.7777.1.1.150
		-- 1.3.6.1.4.1.7777.1.1.150
		voltage_display_phase_label_selection OBJECT-TYPE
			SYNTAX Integer32
			MAX-ACCESS read-only
			STATUS current
			DESCRIPTION
				"Voltage display phase label selection"
			::= { transferswitch 150 }

		
--    1.3.6.1.4.1.7777.1.2.1.151
-- 1.3.6.1.4.1.7777.1.1.151
-- 1.3.6.1.4.1.7777.1.1.151
		-- 1.3.6.1.4.1.7777.1.1.151
		source_1_or_source_2_selection_for_different_english_format OBJECT-TYPE
			SYNTAX Integer32
			MAX-ACCESS read-only
			STATUS current
			DESCRIPTION
				"Source 1 or source 2 selection for different English format"
			::= { transferswitch 151 }

		
--    1.3.6.1.4.1.7777.1.2.1.152
-- 1.3.6.1.4.1.7777.1.1.152
-- 1.3.6.1.4.1.7777.1.1.152
		-- 1.3.6.1.4.1.7777.1.1.152
		external_battery_enabled OBJECT-TYPE
			SYNTAX Integer32
			MAX-ACCESS read-only
			STATUS current
			DESCRIPTION
				"External battery enabled"
			::= { transferswitch 152 }

		
--    1.3.6.1.4.1.7777.1.2.1.153
-- 1.3.6.1.4.1.7777.1.1.153
-- 1.3.6.1.4.1.7777.1.1.153
		-- 1.3.6.1.4.1.7777.1.1.153
		ts_data_gen_start_date OBJECT-TYPE
			SYNTAX Integer32
			MAX-ACCESS read-only
			STATUS current
			DESCRIPTION
				"TS data gen start date"
			::= { transferswitch 153 }

		
--    1.3.6.1.4.1.7777.1.2.1.154
-- 1.3.6.1.4.1.7777.1.1.154
-- 1.3.6.1.4.1.7777.1.1.154
		-- 1.3.6.1.4.1.7777.1.1.154
		ts_data_gen_start_month OBJECT-TYPE
			SYNTAX Integer32
			MAX-ACCESS read-only
			STATUS current
			DESCRIPTION
				"TS data gen start month"
			::= { transferswitch 154 }

		
--    1.3.6.1.4.1.7777.1.2.1.155
-- 1.3.6.1.4.1.7777.1.1.155
-- 1.3.6.1.4.1.7777.1.1.155
		-- 1.3.6.1.4.1.7777.1.1.155
		ts_data_gen_start_year OBJECT-TYPE
			SYNTAX Integer32
			MAX-ACCESS read-only
			STATUS current
			DESCRIPTION
				"TS data gen start year"
			::= { transferswitch 155 }

		
--    1.3.6.1.4.1.7777.1.2.1.156
-- 1.3.6.1.4.1.7777.1.1.156
-- 1.3.6.1.4.1.7777.1.1.156
		-- 1.3.6.1.4.1.7777.1.1.156
		ts_data_gen_start_hour OBJECT-TYPE
			SYNTAX Integer32
			MAX-ACCESS read-only
			STATUS current
			DESCRIPTION
				"TS data gen start hour"
			::= { transferswitch 156 }

		
--    1.3.6.1.4.1.7777.1.2.1.157
-- 1.3.6.1.4.1.7777.1.1.157
-- 1.3.6.1.4.1.7777.1.1.157
		-- 1.3.6.1.4.1.7777.1.1.157
		ts_data_gen_start_minutes OBJECT-TYPE
			SYNTAX Integer32
			MAX-ACCESS read-only
			STATUS current
			DESCRIPTION
				"TS data gen start minutes"
			::= { transferswitch 157 }

		
--    1.3.6.1.4.1.7777.1.2.1.158
-- 1.3.6.1.4.1.7777.1.1.158
-- 1.3.6.1.4.1.7777.1.1.158
		-- 1.3.6.1.4.1.7777.1.1.158
		ts_data_gen_start_seconds OBJECT-TYPE
			SYNTAX Integer32
			MAX-ACCESS read-only
			STATUS current
			DESCRIPTION
				"TS data gen start seconds"
			::= { transferswitch 158 }

		
--    1.3.6.1.4.1.7777.1.2.1.159
-- 1.3.6.1.4.1.7777.1.1.159
-- 1.3.6.1.4.1.7777.1.1.159
		-- 1.3.6.1.4.1.7777.1.1.159
		ts_data_gen_start_10th_of_seconds OBJECT-TYPE
			SYNTAX Integer32
			MAX-ACCESS read-only
			STATUS current
			DESCRIPTION
				"TS data gen start 10th of seconds"
			::= { transferswitch 159 }

		
--    1.3.6.1.4.1.7777.1.2.1.160
-- 1.3.6.1.4.1.7777.1.1.160
-- 1.3.6.1.4.1.7777.1.1.160
		-- 1.3.6.1.4.1.7777.1.1.160
		ts_data_gen_start_elapsed_time_in_seconds OBJECT-TYPE
			SYNTAX Integer32
			MAX-ACCESS read-only
			STATUS current
			DESCRIPTION
				"TS data gen start elapsed time in seconds"
			::= { transferswitch 160 }

		
--    1.3.6.1.4.1.7777.1.2.1.161
-- 1.3.6.1.4.1.7777.1.1.161
-- 1.3.6.1.4.1.7777.1.1.161
		-- 1.3.6.1.4.1.7777.1.1.161
		total_active_alarm_number OBJECT-TYPE
			SYNTAX Integer32
			MAX-ACCESS read-only
			STATUS current
			DESCRIPTION
				"Total active alarm number"
			::= { transferswitch 161 }

		
--    1.3.6.1.4.1.7777.1.2.1.162
-- 1.3.6.1.4.1.7777.1.1.162
-- 1.3.6.1.4.1.7777.1.1.162
		-- 1.3.6.1.4.1.7777.1.1.162
		load_shed_direction OBJECT-TYPE
			SYNTAX Integer32
			MAX-ACCESS read-only
			STATUS current
			DESCRIPTION
				"Load shed direction"
			::= { transferswitch 162 }

		
--    1.3.6.1.4.1.7777.1.2.1.163
-- 1.3.6.1.4.1.7777.1.1.163
-- 1.3.6.1.4.1.7777.1.1.163
		-- 1.3.6.1.4.1.7777.1.1.163
		dtts_only_load_shed_on_source_failure OBJECT-TYPE
			SYNTAX Integer32
			MAX-ACCESS read-only
			STATUS current
			DESCRIPTION
				"DTTS only - load shed on source failure"
			::= { transferswitch 163 }

		
--    1.3.6.1.4.1.7777.1.2.1.164
-- 1.3.6.1.4.1.7777.1.1.164
-- 1.3.6.1.4.1.7777.1.1.164
		-- 1.3.6.1.4.1.7777.1.1.164
		dtts_only_load_shed_on_request_f17 OBJECT-TYPE
			SYNTAX Integer32
			MAX-ACCESS read-only
			STATUS current
			DESCRIPTION
				"DTTS only - load shed on request F17"
			::= { transferswitch 164 }

		
--    1.3.6.1.4.1.7777.1.2.1.165
-- 1.3.6.1.4.1.7777.1.1.165
-- 1.3.6.1.4.1.7777.1.1.165
		-- 1.3.6.1.4.1.7777.1.1.165
		normal_voltage_unbalance_dropout OBJECT-TYPE
			SYNTAX Integer32
			MAX-ACCESS read-only
			STATUS current
			DESCRIPTION
				"Normal voltage unbalance dropout.
				Parameter settings display for 3 phase only"
			::= { transferswitch 165 }

		
--    1.3.6.1.4.1.7777.1.2.1.166
-- 1.3.6.1.4.1.7777.1.1.166
-- 1.3.6.1.4.1.7777.1.1.166
		-- 1.3.6.1.4.1.7777.1.1.166
		normal_voltage_unbalance_pickup OBJECT-TYPE
			SYNTAX Integer32
			MAX-ACCESS read-only
			STATUS current
			DESCRIPTION
				"Normal voltage unbalance pickup.
				Parameter settings display for 3 phase only"
			::= { transferswitch 166 }

		
--    1.3.6.1.4.1.7777.1.2.1.167
-- 1.3.6.1.4.1.7777.1.1.167
-- 1.3.6.1.4.1.7777.1.1.167
		-- 1.3.6.1.4.1.7777.1.1.167
		emergency_voltage_unbalance_dropout OBJECT-TYPE
			SYNTAX Integer32
			MAX-ACCESS read-only
			STATUS current
			DESCRIPTION
				"Emergency voltage unbalance dropout.
				Parameter settings display for 3 phase only"
			::= { transferswitch 167 }

		
--    1.3.6.1.4.1.7777.1.2.1.168
-- 1.3.6.1.4.1.7777.1.1.168
-- 1.3.6.1.4.1.7777.1.1.168
		-- 1.3.6.1.4.1.7777.1.1.168
		emergency_voltage_unbalance_pickup OBJECT-TYPE
			SYNTAX Integer32
			MAX-ACCESS read-only
			STATUS current
			DESCRIPTION
				"Emergency voltage unbalance pickup.
				Parameter settings display for 3 phase only"
			::= { transferswitch 168 }

		
--    1.3.6.1.4.1.7777.1.2.1.169
-- 1.3.6.1.4.1.7777.1.1.169
-- 1.3.6.1.4.1.7777.1.1.169
		-- 1.3.6.1.4.1.7777.1.1.169
		emergency_voltage_phase_ab OBJECT-TYPE
			SYNTAX Integer32
			MAX-ACCESS read-only
			STATUS current
			DESCRIPTION
				"Emergency voltage phase AB"
			::= { transferswitch 169 }

		
--    1.3.6.1.4.1.7777.1.2.1.170
-- 1.3.6.1.4.1.7777.1.1.170
-- 1.3.6.1.4.1.7777.1.1.170
		-- 1.3.6.1.4.1.7777.1.1.170
		emergency_voltage_phase_bc OBJECT-TYPE
			SYNTAX Integer32
			MAX-ACCESS read-only
			STATUS current
			DESCRIPTION
				"Emergency voltage phase BC"
			::= { transferswitch 170 }

		
--    1.3.6.1.4.1.7777.1.2.1.171
-- 1.3.6.1.4.1.7777.1.1.171
-- 1.3.6.1.4.1.7777.1.1.171
		-- 1.3.6.1.4.1.7777.1.1.171
		emergency_voltage_unbalance OBJECT-TYPE
			SYNTAX Integer32
			MAX-ACCESS read-only
			STATUS current
			DESCRIPTION
				"Emergency voltage unbalance"
			::= { transferswitch 171 }

		
--    1.3.6.1.4.1.7777.1.2.1.172
-- 1.3.6.1.4.1.7777.1.1.172
-- 1.3.6.1.4.1.7777.1.1.172
		-- 1.3.6.1.4.1.7777.1.1.172
		emergency_source_3phase_sensing OBJECT-TYPE
			SYNTAX Integer32
			MAX-ACCESS read-only
			STATUS current
			DESCRIPTION
				"Emergency source 3 phase sensing"
			::= { transferswitch 172 }

		
--    1.3.6.1.4.1.7777.1.2.1.173
-- 1.3.6.1.4.1.7777.1.1.173
-- 1.3.6.1.4.1.7777.1.1.173
		-- 1.3.6.1.4.1.7777.1.1.173
		transfer_switch_bypass_or_not OBJECT-TYPE
			SYNTAX Integer32
			MAX-ACCESS read-only
			STATUS current
			DESCRIPTION
				"Transfer Switch Bypass Setting"
			::= { transferswitch 173 }

		
--    1.3.6.1.4.1.7777.1.2.1.174
-- 1.3.6.1.4.1.7777.1.1.174
-- 1.3.6.1.4.1.7777.1.1.174
		-- 1.3.6.1.4.1.7777.1.1.174
		transfer_switch_or_dual_breaker OBJECT-TYPE
			SYNTAX Integer32
			MAX-ACCESS read-only
			STATUS current
			DESCRIPTION
				"Transfer Switch or Dual Breaker Setting"
			::= { transferswitch 174 }

		
--    1.3.6.1.4.1.7777.1.2.1.175
-- 1.3.6.1.4.1.7777.1.1.175
-- 1.3.6.1.4.1.7777.1.1.175
		-- 1.3.6.1.4.1.7777.1.1.175
		transfer_switch_locked_out OBJECT-TYPE
			SYNTAX Integer32
			MAX-ACCESS read-only
			STATUS current
			DESCRIPTION
				"Transfer Switch Locked out"
			::= { transferswitch 175 }

		
--    1.3.6.1.4.1.7777.1.2.1.176
-- 1.3.6.1.4.1.7777.1.1.176
-- 1.3.6.1.4.1.7777.1.1.176
		-- 1.3.6.1.4.1.7777.1.1.176
		ctts_extended_parallel_alarm OBJECT-TYPE
			SYNTAX Integer32
			MAX-ACCESS read-only
			STATUS current
			DESCRIPTION
				"CTTS Extended Parallel Alarm"
			::= { transferswitch 176 }

		
--    1.3.6.1.4.1.7777.1.2.1.177
-- 1.3.6.1.4.1.7777.1.1.177
-- 1.3.6.1.4.1.7777.1.1.177
		-- 1.3.6.1.4.1.7777.1.1.177
		ctts_failure_to_synch_alarm OBJECT-TYPE
			SYNTAX Integer32
			MAX-ACCESS read-only
			STATUS current
			DESCRIPTION
				"CTTS Failure To Synch Alarm"
			::= { transferswitch 177 }

		
--    1.3.6.1.4.1.7777.1.2.1.178
-- 1.3.6.1.4.1.7777.1.1.178
-- 1.3.6.1.4.1.7777.1.1.178
		-- 1.3.6.1.4.1.7777.1.1.178
		dtts_load_disconnect OBJECT-TYPE
			SYNTAX Integer32
			MAX-ACCESS read-only
			STATUS current
			DESCRIPTION
				"DTTS Load Disconnect"
			::= { transferswitch 178 }

		
--    1.3.6.1.4.1.7777.1.2.1.179
-- 1.3.6.1.4.1.7777.1.1.179
-- 1.3.6.1.4.1.7777.1.1.179
		-- 1.3.6.1.4.1.7777.1.1.179
		normal_breaker_tripped OBJECT-TYPE
			SYNTAX Integer32
			MAX-ACCESS read-only
			STATUS current
			DESCRIPTION
				"Normal Breaker Tripped"
			::= { transferswitch 179 }

		
--    1.3.6.1.4.1.7777.1.2.1.180
-- 1.3.6.1.4.1.7777.1.1.180
-- 1.3.6.1.4.1.7777.1.1.180
		-- 1.3.6.1.4.1.7777.1.1.180
		emergency_breaker_tripped OBJECT-TYPE
			SYNTAX Integer32
			MAX-ACCESS read-only
			STATUS current
			DESCRIPTION
				"Emergency Breaker Tripped"
			::= { transferswitch 180 }

		
--    1.3.6.1.4.1.7777.1.2.1.181
-- 1.3.6.1.4.1.7777.1.1.181
-- 1.3.6.1.4.1.7777.1.1.181
		-- 1.3.6.1.4.1.7777.1.1.181
		feature_6b OBJECT-TYPE
			SYNTAX Integer32
			MAX-ACCESS read-only
			STATUS current
			DESCRIPTION
				"Feature 6B Status"
			::= { transferswitch 181 }

		
--    1.3.6.1.4.1.7777.1.2.1.182
-- 1.3.6.1.4.1.7777.1.1.182
-- 1.3.6.1.4.1.7777.1.1.182
		-- 1.3.6.1.4.1.7777.1.1.182
		feature_6c OBJECT-TYPE
			SYNTAX Integer32
			MAX-ACCESS read-only
			STATUS current
			DESCRIPTION
				"Feature 6C Status"
			::= { transferswitch 182 }

		
--    1.3.6.1.4.1.7777.1.2.1.183
-- 1.3.6.1.4.1.7777.1.1.183
-- 1.3.6.1.4.1.7777.1.1.183
		-- 1.3.6.1.4.1.7777.1.1.183
		feature_17_serial OBJECT-TYPE
			SYNTAX Integer32
			MAX-ACCESS read-only
			STATUS current
			DESCRIPTION
				"Feature 17 Serial Status"
			::= { transferswitch 183 }

		
--    1.3.6.1.4.1.7777.1.2.1.184
-- 1.3.6.1.4.1.7777.1.1.184
-- 1.3.6.1.4.1.7777.1.1.184
		-- 1.3.6.1.4.1.7777.1.1.184
		feature_29 OBJECT-TYPE
			SYNTAX Integer32
			MAX-ACCESS read-only
			STATUS current
			DESCRIPTION
				"Feature 29 Status"
			::= { transferswitch 184 }

		
--    1.3.6.1.4.1.7777.1.2.1.185
-- 1.3.6.1.4.1.7777.1.1.185
-- 1.3.6.1.4.1.7777.1.1.185
		-- 1.3.6.1.4.1.7777.1.1.185
		feature_34a OBJECT-TYPE
			SYNTAX Integer32
			MAX-ACCESS read-only
			STATUS current
			DESCRIPTION
				"Feature 34A Status"
			::= { transferswitch 185 }

		
--    1.3.6.1.4.1.7777.1.2.1.186
-- 1.3.6.1.4.1.7777.1.1.186
-- 1.3.6.1.4.1.7777.1.1.186
		-- 1.3.6.1.4.1.7777.1.1.186
		feature_89 OBJECT-TYPE
			SYNTAX Integer32
			MAX-ACCESS read-only
			STATUS current
			DESCRIPTION
				"Feature 89 Status"
			::= { transferswitch 186 }

		
--    1.3.6.1.4.1.7777.1.2.1.187
-- 1.3.6.1.4.1.7777.1.1.187
-- 1.3.6.1.4.1.7777.1.1.187
		-- 1.3.6.1.4.1.7777.1.1.187
		feature_ct_bypass OBJECT-TYPE
			SYNTAX Integer32
			MAX-ACCESS read-only
			STATUS current
			DESCRIPTION
				"Feature CT Bypass Status"
			::= { transferswitch 187 }

		
--    1.3.6.1.4.1.7777.1.2.1.188
-- 1.3.6.1.4.1.7777.1.1.188
-- 1.3.6.1.4.1.7777.1.1.188
		-- 1.3.6.1.4.1.7777.1.1.188
		feature_alarm_reset OBJECT-TYPE
			SYNTAX Integer32
			MAX-ACCESS read-only
			STATUS current
			DESCRIPTION
				"Feature Alarm Reset Status"
			::= { transferswitch 188 }

		
--    1.3.6.1.4.1.7777.1.2.1.189
-- 1.3.6.1.4.1.7777.1.1.189
-- 1.3.6.1.4.1.7777.1.1.189
		-- 1.3.6.1.4.1.7777.1.1.189
		feature_6d OBJECT-TYPE
			SYNTAX Integer32
			MAX-ACCESS read-only
			STATUS current
			DESCRIPTION
				"Feature 6D Status"
			::= { transferswitch 189 }

		
--    1.3.6.1.4.1.7777.1.2.1.190
-- 1.3.6.1.4.1.7777.1.1.190
-- 1.3.6.1.4.1.7777.1.1.190
		-- 1.3.6.1.4.1.7777.1.1.190
		feature_34t OBJECT-TYPE
			SYNTAX Integer32
			MAX-ACCESS read-only
			STATUS current
			DESCRIPTION
				"Feature 34T Status"
			::= { transferswitch 190 }

		
--    1.3.6.1.4.1.7777.1.2.1.191
-- 1.3.6.1.4.1.7777.1.1.191
-- 1.3.6.1.4.1.7777.1.1.191
		-- 1.3.6.1.4.1.7777.1.1.191
		control_panel_eventlog_enabled OBJECT-TYPE
			SYNTAX Integer32
			MAX-ACCESS read-only
			STATUS current
			DESCRIPTION
				"Control Panel Event Log Enabled"
			::= { transferswitch 191 }

		
--    1.3.6.1.4.1.7777.1.2.1.192
-- 1.3.6.1.4.1.7777.1.1.192
-- 1.3.6.1.4.1.7777.1.1.192
		-- 1.3.6.1.4.1.7777.1.1.192
		pt_ratio_numerator OBJECT-TYPE
			SYNTAX Integer32
			MAX-ACCESS read-only
			STATUS current
			DESCRIPTION
				"PT Ratio Numerator"
			::= { transferswitch 192 }

		
--    1.3.6.1.4.1.7777.1.2.1.193
-- 1.3.6.1.4.1.7777.1.1.193
-- 1.3.6.1.4.1.7777.1.1.193
		-- 1.3.6.1.4.1.7777.1.1.193
		pt_ratio_denominator OBJECT-TYPE
			SYNTAX Integer32
			MAX-ACCESS read-only
			STATUS current
			DESCRIPTION
				"PT Ratio Denominator"
			::= { transferswitch 193 }

		
--    1.3.6.1.4.1.7777.1.2.1.194
-- 1.3.6.1.4.1.7777.1.1.194
-- 1.3.6.1.4.1.7777.1.1.194
		-- 1.3.6.1.4.1.7777.1.1.194
		control_panel_name OBJECT-TYPE
			SYNTAX Integer32
			MAX-ACCESS read-only
			STATUS current
			DESCRIPTION
				"Control Panel Name"
			::= { transferswitch 194 }

		
--    1.3.6.1.4.1.7777.1.2.1.195
-- 1.3.6.1.4.1.7777.1.1.195
-- 1.3.6.1.4.1.7777.1.1.195
		-- 1.3.6.1.4.1.7777.1.1.195
		normal_voltage_unbalance_enabled OBJECT-TYPE
			SYNTAX Integer32
			MAX-ACCESS read-only
			STATUS current
			DESCRIPTION
				"Normal Voltage Unbalance Enabled"
			::= { transferswitch 195 }

		
--    1.3.6.1.4.1.7777.1.2.1.196
-- 1.3.6.1.4.1.7777.1.1.196
-- 1.3.6.1.4.1.7777.1.1.196
		-- 1.3.6.1.4.1.7777.1.1.196
		emergency_voltage_unbalance_enabled OBJECT-TYPE
			SYNTAX Integer32
			MAX-ACCESS read-only
			STATUS current
			DESCRIPTION
				"Emergency Voltage Unbalance Enabled"
			::= { transferswitch 196 }

		
--    1.3.6.1.4.1.7777.1.2.1.197
-- 1.3.6.1.4.1.7777.1.1.197
-- 1.3.6.1.4.1.7777.1.1.197
		-- 1.3.6.1.4.1.7777.1.1.197
		bypass_31F_and_31M_on_N_source_failure OBJECT-TYPE
			SYNTAX Integer32
			MAX-ACCESS read-only
			STATUS current
			DESCRIPTION
				"Bypass 31F and 31M on N source failure"
			::= { transferswitch 197 }

		
--    1.3.6.1.4.1.7777.1.2.1.198
-- 1.3.6.1.4.1.7777.1.1.198
-- 1.3.6.1.4.1.7777.1.1.198
		-- 1.3.6.1.4.1.7777.1.1.198
		bypass_31G_and_31N_on_E_source_failure OBJECT-TYPE
			SYNTAX Integer32
			MAX-ACCESS read-only
			STATUS current
			DESCRIPTION
				"Bypass 31G and 31N on E source failure"
			::= { transferswitch 198 }

		
--    1.3.6.1.4.1.7777.1.2.1.199
-- 1.3.6.1.4.1.7777.1.1.199
-- 1.3.6.1.4.1.7777.1.1.199
		-- 1.3.6.1.4.1.7777.1.1.199
		external_battery_present OBJECT-TYPE
			SYNTAX Integer32
			MAX-ACCESS read-only
			STATUS current
			DESCRIPTION
				"External Battery Present"
			::= { transferswitch 199 }

		
--    1.3.6.1.4.1.7777.1.2.1.200
-- 1.3.6.1.4.1.7777.1.1.200
-- 1.3.6.1.4.1.7777.1.1.200
		-- 1.3.6.1.4.1.7777.1.1.200
		ctts_in_synch_monitor_time_delay OBJECT-TYPE
			SYNTAX Integer32
			MAX-ACCESS read-only
			STATUS current
			DESCRIPTION
				"CTTS In Synch Monitor Time Delay"
			::= { transferswitch 200 }

		
--    1.3.6.1.4.1.7777.1.2.1.201
-- 1.3.6.1.4.1.7777.1.1.201
-- 1.3.6.1.4.1.7777.1.1.201
		-- 1.3.6.1.4.1.7777.1.1.201
		synch_time_delay OBJECT-TYPE
			SYNTAX Integer32
			MAX-ACCESS read-only
			STATUS current
			DESCRIPTION
				"CTTS Fail To Synch Time Delay"
			::= { transferswitch 201 }

		
--    1.3.6.1.4.1.7777.1.2.1.202
-- 1.3.6.1.4.1.7777.1.1.202
-- 1.3.6.1.4.1.7777.1.1.202
		-- 1.3.6.1.4.1.7777.1.1.202
		ctts_extended_parallel_time_delay OBJECT-TYPE
			SYNTAX Integer32
			MAX-ACCESS read-only
			STATUS current
			DESCRIPTION
				"CTTS Extaneded Parallel Time Delay"
			::= { transferswitch 202 }

		
--    1.3.6.1.4.1.7777.1.2.1.203
-- 1.3.6.1.4.1.7777.1.1.203
-- 1.3.6.1.4.1.7777.1.1.203
		-- 1.3.6.1.4.1.7777.1.1.203
		shed_load_in_phase OBJECT-TYPE
			SYNTAX Integer32
			MAX-ACCESS read-only
			STATUS current
			DESCRIPTION
				"Shed Load In Phase"
			::= { transferswitch 203 }

		
--    1.3.6.1.4.1.7777.1.2.1.204
-- 1.3.6.1.4.1.7777.1.1.204
-- 1.3.6.1.4.1.7777.1.1.204
		-- 1.3.6.1.4.1.7777.1.1.204
		isolate_load_on_source_failure OBJECT-TYPE
			SYNTAX Integer32
			MAX-ACCESS read-only
			STATUS current
			DESCRIPTION
				"Isolate Load On Source Failure"
			::= { transferswitch 204 }

		
--    1.3.6.1.4.1.7777.1.2.1.205
-- 1.3.6.1.4.1.7777.1.1.205
-- 1.3.6.1.4.1.7777.1.1.205
		-- 1.3.6.1.4.1.7777.1.1.205
		isolate_load_on_F17 OBJECT-TYPE
			SYNTAX Integer32
			MAX-ACCESS read-only
			STATUS current
			DESCRIPTION
				"Isolate Load On F17"
			::= { transferswitch 205 }

		
--    1.3.6.1.4.1.7777.1.2.1.206
-- 1.3.6.1.4.1.7777.1.1.206
-- 1.3.6.1.4.1.7777.1.1.206
		-- 1.3.6.1.4.1.7777.1.1.206
		fail_to_sync_auto_ct_bypass OBJECT-TYPE
			SYNTAX Integer32
			MAX-ACCESS read-only
			STATUS current
			DESCRIPTION
				"Fail To Sync Auto CT Bypass"
			::= { transferswitch 206 }

		
--    1.3.6.1.4.1.7777.1.2.1.207
-- 1.3.6.1.4.1.7777.1.1.207
-- 1.3.6.1.4.1.7777.1.1.207
		-- 1.3.6.1.4.1.7777.1.1.207
		transfer_in_phase_on_ct_bypass_if_load_disconnect OBJECT-TYPE
			SYNTAX Integer32
			MAX-ACCESS read-only
			STATUS current
			DESCRIPTION
				"Transfer In phase On CT Bypass If load
				is disconnected"
			::= { transferswitch 207 }

		
--    1.3.6.1.4.1.7777.1.2.1.208
-- 1.3.6.1.4.1.7777.1.1.208
-- 1.3.6.1.4.1.7777.1.1.208
		-- 1.3.6.1.4.1.7777.1.1.208
		network_configuration OBJECT-TYPE
			SYNTAX DisplayString (SIZE (0..128))
			MAX-ACCESS read-only
			STATUS current
			DESCRIPTION
				"Control Panel Network configuration"
			::= { transferswitch 208 }

		
--   1.3.6.1.4.1.7777.1.2
-- 1.3.6.1.4.1.7777.1.2
		-- 1.3.6.1.4.1.7777.1.2
		dpmNormal OBJECT IDENTIFIER ::= { device 2 }

		
--    transfer switch end
-- 1.3.6.1.4.1.7777.1.2.2.1
-- 1.3.6.1.4.1.7777.1.2.1
-- 1.3.6.1.4.1.7777.1.2.1
		-- 1.3.6.1.4.1.7777.1.2.1
		dpmNormalDPMName OBJECT-TYPE
			SYNTAX DisplayString (SIZE (0..128))
			MAX-ACCESS read-only
			STATUS current
			DESCRIPTION
				"Normal DPM name."
			::= { dpmNormal 1 }

		
--    1.3.6.1.4.1.7777.1.2.2.2
-- 1.3.6.1.4.1.7777.1.2.2
-- 1.3.6.1.4.1.7777.1.2.2
		-- 1.3.6.1.4.1.7777.1.2.2
		dpmNormalDPMLoca OBJECT-TYPE
			SYNTAX DisplayString (SIZE (0..128))
			MAX-ACCESS read-only
			STATUS current
			DESCRIPTION
				"Normal DPM Location."
			::= { dpmNormal 2 }

		
--    1.3.6.1.4.1.7777.1.2.2.3
-- 1.3.6.1.4.1.7777.1.2.3
-- 1.3.6.1.4.1.7777.1.2.3
		-- 1.3.6.1.4.1.7777.1.2.3
		dpmNormalNominalVoltage OBJECT-TYPE
			SYNTAX Integer32
			MAX-ACCESS read-only
			STATUS current
			DESCRIPTION
				"Normal Nominal Voltage."
			::= { dpmNormal 3 }

		
--    1.3.6.1.4.1.7777.1.2.2.4
-- 1.3.6.1.4.1.7777.1.2.4
-- 1.3.6.1.4.1.7777.1.2.4
		-- 1.3.6.1.4.1.7777.1.2.4
		dpmNormalNominalCurrent OBJECT-TYPE
			SYNTAX Integer32
			MAX-ACCESS read-only
			STATUS current
			DESCRIPTION
				"Normal Nominal Current."
			::= { dpmNormal 4 }

		
--    1.3.6.1.4.1.7777.1.2.2.5
-- 1.3.6.1.4.1.7777.1.2.5
-- 1.3.6.1.4.1.7777.1.2.5
		-- 1.3.6.1.4.1.7777.1.2.5
		dpmNormalInstantaneousDemandKwMW OBJECT-TYPE
			SYNTAX Integer32
			MAX-ACCESS read-only
			STATUS current
			DESCRIPTION
				"Normal Instantaneous Demand kW MW"
			::= { dpmNormal 5 }

		
--    1.3.6.1.4.1.7777.1.2.2.6
-- 1.3.6.1.4.1.7777.1.2.6
-- 1.3.6.1.4.1.7777.1.2.6
		-- 1.3.6.1.4.1.7777.1.2.6
		dpmNormalInstantaneousDemandDate OBJECT-TYPE
			SYNTAX DisplayString (SIZE (0..128))
			MAX-ACCESS read-only
			STATUS current
			DESCRIPTION
				"Normal Demand Date."
			::= { dpmNormal 6 }

		
--    1.3.6.1.4.1.7777.1.2.2.7
-- 1.3.6.1.4.1.7777.1.2.7
-- 1.3.6.1.4.1.7777.1.2.7
		-- 1.3.6.1.4.1.7777.1.2.7
		dpmNormalInstantaneousDemandTime OBJECT-TYPE
			SYNTAX DisplayString (SIZE (0..128))
			MAX-ACCESS read-only
			STATUS current
			DESCRIPTION
				"Normal Demand Time."
			::= { dpmNormal 7 }

		
--    1.3.6.1.4.1.7777.1.2.2.8
-- 1.3.6.1.4.1.7777.1.2.8
-- 1.3.6.1.4.1.7777.1.2.8
		-- 1.3.6.1.4.1.7777.1.2.8
		dpmNormalBlockDemandforFullHouInkW OBJECT-TYPE
			SYNTAX Integer32
			MAX-ACCESS read-only
			STATUS current
			DESCRIPTION
				"Normal Block Demand for Full Hou In kW."
			::= { dpmNormal 8 }

		
--    1.3.6.1.4.1.7777.1.2.2.9
-- 1.3.6.1.4.1.7777.1.2.9
-- 1.3.6.1.4.1.7777.1.2.9
		-- 1.3.6.1.4.1.7777.1.2.9
		dpmNormalBlockDemandforFullDayInkW OBJECT-TYPE
			SYNTAX Integer32
			MAX-ACCESS read-only
			STATUS current
			DESCRIPTION
				"Normal Block Demand for Full Day In kW."
			::= { dpmNormal 9 }

		
--    1.3.6.1.4.1.7777.1.2.2.10
-- 1.3.6.1.4.1.7777.1.2.10
-- 1.3.6.1.4.1.7777.1.2.10
		-- 1.3.6.1.4.1.7777.1.2.10
		dpmNormalBlockDemandforFullMonthInKW OBJECT-TYPE
			SYNTAX Integer32
			MAX-ACCESS read-only
			STATUS current
			DESCRIPTION
				"Normal Block Demand for Full Month In kW."
			::= { dpmNormal 10 }

		
--    1.3.6.1.4.1.7777.1.2.2.11
-- 1.3.6.1.4.1.7777.1.2.11
-- 1.3.6.1.4.1.7777.1.2.11
		-- 1.3.6.1.4.1.7777.1.2.11
		dpmNormalBlockDemandforFullYear OBJECT-TYPE
			SYNTAX Integer32
			MAX-ACCESS read-only
			STATUS current
			DESCRIPTION
				"Normal Block Demand for Full Year In kW."
			::= { dpmNormal 11 }

		
--    1.3.6.1.4.1.7777.1.2.2.12
-- 1.3.6.1.4.1.7777.1.2.12
-- 1.3.6.1.4.1.7777.1.2.12
		-- 1.3.6.1.4.1.7777.1.2.12
		dpmNormalCurrentThdA OBJECT-TYPE
			SYNTAX Integer32
			MAX-ACCESS read-only
			STATUS current
			DESCRIPTION
				"Normal Phase A THD Current.In percentage "
			::= { dpmNormal 12 }

		
--    1.3.6.1.4.1.7777.1.2.2.13
-- 1.3.6.1.4.1.7777.1.2.13
-- 1.3.6.1.4.1.7777.1.2.13
		-- 1.3.6.1.4.1.7777.1.2.13
		dpmNormalCurrentThdB OBJECT-TYPE
			SYNTAX Integer32
			MAX-ACCESS read-only
			STATUS current
			DESCRIPTION
				"Normal Phase B THD Current.In percentage"
			::= { dpmNormal 13 }

		
--    1.3.6.1.4.1.7777.1.2.2.14
-- 1.3.6.1.4.1.7777.1.2.14
-- 1.3.6.1.4.1.7777.1.2.14
		-- 1.3.6.1.4.1.7777.1.2.14
		dpmNormalCurrentThdC OBJECT-TYPE
			SYNTAX Integer32
			MAX-ACCESS read-only
			STATUS current
			DESCRIPTION
				"Normal Phase C THD Current.In percentage"
			::= { dpmNormal 14 }

		
--    1.3.6.1.4.1.7777.1.2.2.15
-- 1.3.6.1.4.1.7777.1.2.15
-- 1.3.6.1.4.1.7777.1.2.15
		-- 1.3.6.1.4.1.7777.1.2.15
		dpmNormalVoltageThdA OBJECT-TYPE
			SYNTAX Integer32
			MAX-ACCESS read-only
			STATUS current
			DESCRIPTION
				"Normal Phase A THD Voltage.In percentage"
			::= { dpmNormal 15 }

		
--    1.3.6.1.4.1.7777.1.2.2.16
-- 1.3.6.1.4.1.7777.1.2.16
-- 1.3.6.1.4.1.7777.1.2.16
		-- 1.3.6.1.4.1.7777.1.2.16
		dpmNormalVoltageThdB OBJECT-TYPE
			SYNTAX Integer32
			MAX-ACCESS read-only
			STATUS current
			DESCRIPTION
				"Normal Phase B THD Voltage.In percentage"
			::= { dpmNormal 16 }

		
--    1.3.6.1.4.1.7777.1.2.2.17
-- 1.3.6.1.4.1.7777.1.2.17
-- 1.3.6.1.4.1.7777.1.2.17
		-- 1.3.6.1.4.1.7777.1.2.17
		dpmNormalVoltageThdC OBJECT-TYPE
			SYNTAX Integer32
			MAX-ACCESS read-only
			STATUS current
			DESCRIPTION
				"Normal Phase C THD Voltage.In percentage"
			::= { dpmNormal 17 }

		
--    1.3.6.1.4.1.7777.1.2.2.18
-- 1.3.6.1.4.1.7777.1.2.18
-- 1.3.6.1.4.1.7777.1.2.18
		-- 1.3.6.1.4.1.7777.1.2.18
		dpmNormalVab OBJECT-TYPE
			SYNTAX Integer32
			MAX-ACCESS read-only
			STATUS current
			DESCRIPTION
				"Normal Vab Voltage."
			::= { dpmNormal 18 }

		
--    1.3.6.1.4.1.7777.1.2.2.19
-- 1.3.6.1.4.1.7777.1.2.19
-- 1.3.6.1.4.1.7777.1.2.19
		-- 1.3.6.1.4.1.7777.1.2.19
		dpmNormalVbc OBJECT-TYPE
			SYNTAX Integer32
			MAX-ACCESS read-only
			STATUS current
			DESCRIPTION
				"Normal Vbc Voltage."
			::= { dpmNormal 19 }

		
--    1.3.6.1.4.1.7777.1.2.2.20
-- 1.3.6.1.4.1.7777.1.2.20
-- 1.3.6.1.4.1.7777.1.2.20
		-- 1.3.6.1.4.1.7777.1.2.20
		dpmNormalVca OBJECT-TYPE
			SYNTAX Integer32
			MAX-ACCESS read-only
			STATUS current
			DESCRIPTION
				"Normal Vca Voltage."
			::= { dpmNormal 20 }

		
--    1.3.6.1.4.1.7777.1.2.2.21
-- 1.3.6.1.4.1.7777.1.2.21
-- 1.3.6.1.4.1.7777.1.2.21
		-- 1.3.6.1.4.1.7777.1.2.21
		dpmNormalVolAverage OBJECT-TYPE
			SYNTAX Integer32
			MAX-ACCESS read-only
			STATUS current
			DESCRIPTION
				"Normal Vol Average."
			::= { dpmNormal 21 }

		
--    1.3.6.1.4.1.7777.1.2.2.22
-- 1.3.6.1.4.1.7777.1.2.22
-- 1.3.6.1.4.1.7777.1.2.22
		-- 1.3.6.1.4.1.7777.1.2.22
		dpmNormalVolUnbal OBJECT-TYPE
			SYNTAX Integer32
			MAX-ACCESS read-only
			STATUS current
			DESCRIPTION
				"Normal Vol Unbal."
			::= { dpmNormal 22 }

		
--    1.3.6.1.4.1.7777.1.2.2.23
-- 1.3.6.1.4.1.7777.1.2.23
-- 1.3.6.1.4.1.7777.1.2.23
		-- 1.3.6.1.4.1.7777.1.2.23
		dpmNormalVan OBJECT-TYPE
			SYNTAX Integer32
			MAX-ACCESS read-only
			STATUS current
			DESCRIPTION
				"Normal Vol Van."
			::= { dpmNormal 23 }

		
--    1.3.6.1.4.1.7777.1.2.2.24
-- 1.3.6.1.4.1.7777.1.2.24
-- 1.3.6.1.4.1.7777.1.2.24
		-- 1.3.6.1.4.1.7777.1.2.24
		dpmNormalVbn OBJECT-TYPE
			SYNTAX Integer32
			MAX-ACCESS read-only
			STATUS current
			DESCRIPTION
				"Normal Vbn.."
			::= { dpmNormal 24 }

		
--    1.3.6.1.4.1.7777.1.2.2.25
-- 1.3.6.1.4.1.7777.1.2.25
-- 1.3.6.1.4.1.7777.1.2.25
		-- 1.3.6.1.4.1.7777.1.2.25
		dpmNormalVcn OBJECT-TYPE
			SYNTAX Integer32
			MAX-ACCESS read-only
			STATUS current
			DESCRIPTION
				"Normal Vcn. "
			::= { dpmNormal 25 }

		
--    1.3.6.1.4.1.7777.1.2.2.26
-- 1.3.6.1.4.1.7777.1.2.26
-- 1.3.6.1.4.1.7777.1.2.26
		-- 1.3.6.1.4.1.7777.1.2.26
		dpmNormalVavgneutral OBJECT-TYPE
			SYNTAX Integer32
			MAX-ACCESS read-only
			STATUS current
			DESCRIPTION
				"Normal Avg neutral Volatagae."
			::= { dpmNormal 26 }

		
--    1.3.6.1.4.1.7777.1.2.2.27
-- 1.3.6.1.4.1.7777.1.2.27
-- 1.3.6.1.4.1.7777.1.2.27
		-- 1.3.6.1.4.1.7777.1.2.27
		dpmNormalFrequency OBJECT-TYPE
			SYNTAX Integer32
			MAX-ACCESS read-only
			STATUS current
			DESCRIPTION
				"Normal Frequency."
			::= { dpmNormal 27 }

		
--    1.3.6.1.4.1.7777.1.2.2.28
-- 1.3.6.1.4.1.7777.1.2.28
-- 1.3.6.1.4.1.7777.1.2.28
		-- 1.3.6.1.4.1.7777.1.2.28
		dpmNormalPowerFactor OBJECT-TYPE
			SYNTAX Integer32
			MAX-ACCESS read-only
			STATUS current
			DESCRIPTION
				"Normal Power factor."
			::= { dpmNormal 28 }

		
--    1.3.6.1.4.1.7777.1.2.2.29
-- 1.3.6.1.4.1.7777.1.2.29
-- 1.3.6.1.4.1.7777.1.2.29
		-- 1.3.6.1.4.1.7777.1.2.29
		dpmNormalCurPhaseA OBJECT-TYPE
			SYNTAX Integer32
			MAX-ACCESS read-only
			STATUS current
			DESCRIPTION
				"Normal Phase A Current."
			::= { dpmNormal 29 }

		
--    1.3.6.1.4.1.7777.1.2.2.30
-- 1.3.6.1.4.1.7777.1.2.30
-- 1.3.6.1.4.1.7777.1.2.30
		-- 1.3.6.1.4.1.7777.1.2.30
		dpmNormalCurPhaseB OBJECT-TYPE
			SYNTAX Integer32
			MAX-ACCESS read-only
			STATUS current
			DESCRIPTION
				"Normal Phase B Current."
			::= { dpmNormal 30 }

		
--    1.3.6.1.4.1.7777.1.2.2.31
-- 1.3.6.1.4.1.7777.1.2.31
-- 1.3.6.1.4.1.7777.1.2.31
		-- 1.3.6.1.4.1.7777.1.2.31
		dpmNormalCurPhaseC OBJECT-TYPE
			SYNTAX Integer32
			MAX-ACCESS read-only
			STATUS current
			DESCRIPTION
				"Normal Phase C Current."
			::= { dpmNormal 31 }

		
--    1.3.6.1.4.1.7777.1.2.2.32
-- 1.3.6.1.4.1.7777.1.2.32
-- 1.3.6.1.4.1.7777.1.2.32
		-- 1.3.6.1.4.1.7777.1.2.32
		dpmNormalPhaseCurAvg OBJECT-TYPE
			SYNTAX Integer32
			MAX-ACCESS read-only
			STATUS current
			DESCRIPTION
				"Normal Phase Current aVG."
			::= { dpmNormal 32 }

		
--    1.3.6.1.4.1.7777.1.2.2.33
-- 1.3.6.1.4.1.7777.1.2.33
-- 1.3.6.1.4.1.7777.1.2.33
		-- 1.3.6.1.4.1.7777.1.2.33
		dpmNormalPhaseCurUnbalancecePercentage OBJECT-TYPE
			SYNTAX Integer32
			MAX-ACCESS read-only
			STATUS current
			DESCRIPTION
				"Normal Phase Cur Unbalancece Percentage."
			::= { dpmNormal 33 }

		
--    1.3.6.1.4.1.7777.1.2.2.34
-- 1.3.6.1.4.1.7777.1.2.34
-- 1.3.6.1.4.1.7777.1.2.34
		-- 1.3.6.1.4.1.7777.1.2.34
		dpmNormalRealTotalPower OBJECT-TYPE
			SYNTAX Integer32
			MAX-ACCESS read-only
			STATUS current
			DESCRIPTION
				"Normal Real Total power factor."
			::= { dpmNormal 34 }

		
--    1.3.6.1.4.1.7777.1.2.2.35
-- 1.3.6.1.4.1.7777.1.2.35
-- 1.3.6.1.4.1.7777.1.2.35
		-- 1.3.6.1.4.1.7777.1.2.35
		dpmNormalReactiveTotalPower OBJECT-TYPE
			SYNTAX Integer32
			MAX-ACCESS read-only
			STATUS current
			DESCRIPTION
				"Normal Reactive Total power."
			::= { dpmNormal 35 }

		
--    1.3.6.1.4.1.7777.1.2.2.36
-- 1.3.6.1.4.1.7777.1.2.36
-- 1.3.6.1.4.1.7777.1.2.36
		-- 1.3.6.1.4.1.7777.1.2.36
		dpmNormalApparentTotalPower OBJECT-TYPE
			SYNTAX Integer32
			MAX-ACCESS read-only
			STATUS current
			DESCRIPTION
				"Normal AApparent Total power."
			::= { dpmNormal 36 }

		
--    1.3.6.1.4.1.7777.1.2.2.37
-- 1.3.6.1.4.1.7777.1.2.37
-- 1.3.6.1.4.1.7777.1.2.37
		-- 1.3.6.1.4.1.7777.1.2.37
		dpmNormalNetActiveEnergy OBJECT-TYPE
			SYNTAX Integer32
			MAX-ACCESS read-only
			STATUS current
			DESCRIPTION
				"Normal Net Active Energy."
			::= { dpmNormal 37 }

		
--    1.3.6.1.4.1.7777.1.2.2.39
-- 1.3.6.1.4.1.7777.1.2.38
-- 1.3.6.1.4.1.7777.1.2.38
		-- 1.3.6.1.4.1.7777.1.2.38
		dpmNormalFirmwareVersion OBJECT-TYPE
			SYNTAX DisplayString (SIZE (0..128))
			MAX-ACCESS read-only
			STATUS current
			DESCRIPTION
				"Normal DPM Firmware ."
			::= { dpmNormal 38 }

		
--   1.3.6.1.4.1.7777.1.2.39
-- 1.3.6.1.4.1.7777.1.2.39
		-- 1.3.6.1.4.1.7777.1.2.39
		dpmNormalActivePowerA OBJECT-TYPE
			SYNTAX Integer32
			MAX-ACCESS read-only
			STATUS current
			DESCRIPTION
				"Normal Active Power Phase A."
			::= { dpmNormal 39 }

		
--   1.3.6.1.4.1.7777.1.2.40
-- 1.3.6.1.4.1.7777.1.2.40
		-- 1.3.6.1.4.1.7777.1.2.40
		dpmNormalActivePowerB OBJECT-TYPE
			SYNTAX Integer32
			MAX-ACCESS read-only
			STATUS current
			DESCRIPTION
				"Normal Active Power Phase B."
			::= { dpmNormal 40 }

		
--   1.3.6.1.4.1.7777.1.2.41
-- 1.3.6.1.4.1.7777.1.2.41
		-- 1.3.6.1.4.1.7777.1.2.41
		dpmNormalActivePowerC OBJECT-TYPE
			SYNTAX Integer32
			MAX-ACCESS read-only
			STATUS current
			DESCRIPTION
				"Normal Active Power Phase C."
			::= { dpmNormal 41 }

		
--   1.3.6.1.4.1.7777.1.2.42
-- 1.3.6.1.4.1.7777.1.2.42
		-- 1.3.6.1.4.1.7777.1.2.42
		dpmNormalActivePowerTotal OBJECT-TYPE
			SYNTAX Integer32
			MAX-ACCESS read-only
			STATUS current
			DESCRIPTION
				"Normal Active Power Total."
			::= { dpmNormal 42 }

		
--   1.3.6.1.4.1.7777.1.2.43
-- 1.3.6.1.4.1.7777.1.2.43
		-- 1.3.6.1.4.1.7777.1.2.43
		dpmNormalReactivePowerA OBJECT-TYPE
			SYNTAX Integer32
			MAX-ACCESS read-only
			STATUS current
			DESCRIPTION
				"Normal Reactive Power Phase A."
			::= { dpmNormal 43 }

		
--   1.3.6.1.4.1.7777.1.2.44
-- 1.3.6.1.4.1.7777.1.2.44
		-- 1.3.6.1.4.1.7777.1.2.44
		dpmNormalReactivePowerB OBJECT-TYPE
			SYNTAX Integer32
			MAX-ACCESS read-only
			STATUS current
			DESCRIPTION
				"Normal Reactive Power Phase B."
			::= { dpmNormal 44 }

		
--   1.3.6.1.4.1.7777.1.2.45
-- 1.3.6.1.4.1.7777.1.2.45
		-- 1.3.6.1.4.1.7777.1.2.45
		dpmNormalReactivePowerC OBJECT-TYPE
			SYNTAX Integer32
			MAX-ACCESS read-only
			STATUS current
			DESCRIPTION
				"Normal Reactive Power Phase C."
			::= { dpmNormal 45 }

		
--   1.3.6.1.4.1.7777.1.2.46
-- 1.3.6.1.4.1.7777.1.2.46
		-- 1.3.6.1.4.1.7777.1.2.46
		dpmNormalReactivePowerTotal OBJECT-TYPE
			SYNTAX Integer32
			MAX-ACCESS read-only
			STATUS current
			DESCRIPTION
				"Normal Reactive Power Total."
			::= { dpmNormal 46 }

		
--   1.3.6.1.4.1.7777.1.2.47
-- 1.3.6.1.4.1.7777.1.2.47
		-- 1.3.6.1.4.1.7777.1.2.47
		dpmNormalPowerFactorA OBJECT-TYPE
			SYNTAX Integer32
			MAX-ACCESS read-only
			STATUS current
			DESCRIPTION
				"Normal Power factor Phase A."
			::= { dpmNormal 47 }

		
--   1.3.6.1.4.1.7777.1.2.48
-- 1.3.6.1.4.1.7777.1.2.48
		-- 1.3.6.1.4.1.7777.1.2.48
		dpmNormalPowerFactorB OBJECT-TYPE
			SYNTAX Integer32
			MAX-ACCESS read-only
			STATUS current
			DESCRIPTION
				"Normal Power factor Phase B."
			::= { dpmNormal 48 }

		
--   1.3.6.1.4.1.7777.1.2.49
-- 1.3.6.1.4.1.7777.1.2.49
		-- 1.3.6.1.4.1.7777.1.2.49
		dpmNormalPowerFactorC OBJECT-TYPE
			SYNTAX Integer32
			MAX-ACCESS read-only
			STATUS current
			DESCRIPTION
				"Normal Power factor Phase C."
			::= { dpmNormal 49 }

		
--   1.3.6.1.4.1.7777.1.2.50
-- 1.3.6.1.4.1.7777.1.2.50
		-- 1.3.6.1.4.1.7777.1.2.50
		dpmNormalPowerFactorTotal OBJECT-TYPE
			SYNTAX Integer32
			MAX-ACCESS read-only
			STATUS current
			DESCRIPTION
				"Normal Power factor Total."
			::= { dpmNormal 50 }

		
--   1.3.6.1.4.1.7777.1.2.51
-- 1.3.6.1.4.1.7777.1.2.51
		-- 1.3.6.1.4.1.7777.1.2.51
		dpmNormalVoltAmperePowerA OBJECT-TYPE
			SYNTAX Integer32
			MAX-ACCESS read-only
			STATUS current
			DESCRIPTION
				"Normal Volt-Ampere Power Phase A."
			::= { dpmNormal 51 }

		
--   1.3.6.1.4.1.7777.1.2.52
-- 1.3.6.1.4.1.7777.1.2.52
		-- 1.3.6.1.4.1.7777.1.2.52
		dpmNormalVoltAmperePowerB OBJECT-TYPE
			SYNTAX Integer32
			MAX-ACCESS read-only
			STATUS current
			DESCRIPTION
				"Normal Volt-Ampere Power Phase B."
			::= { dpmNormal 52 }

		
--   1.3.6.1.4.1.7777.1.2.53
-- 1.3.6.1.4.1.7777.1.2.53
		-- 1.3.6.1.4.1.7777.1.2.53
		dpmNormalVoltAmperePowerC OBJECT-TYPE
			SYNTAX Integer32
			MAX-ACCESS read-only
			STATUS current
			DESCRIPTION
				"Normal Volt-Ampere Power Phase C."
			::= { dpmNormal 53 }

		
--   1.3.6.1.4.1.7777.1.2.54
-- 1.3.6.1.4.1.7777.1.2.54
		-- 1.3.6.1.4.1.7777.1.2.54
		dpmNormalVoltAmperePowerTotal OBJECT-TYPE
			SYNTAX Integer32
			MAX-ACCESS read-only
			STATUS current
			DESCRIPTION
				"Normal Volt-Ampere Power Total."
			::= { dpmNormal 54 }

		
--   1.3.6.1.4.1.7777.1.2.55
-- 1.3.6.1.4.1.7777.1.2.55
		-- 1.3.6.1.4.1.7777.1.2.55
		dpmNormalMaxWattDemand OBJECT-TYPE
			SYNTAX Integer32
			MAX-ACCESS read-only
			STATUS current
			DESCRIPTION
				"Normal Maximum Watt Demand."
			::= { dpmNormal 55 }

		
--   1.3.6.1.4.1.7777.1.2.56
-- 1.3.6.1.4.1.7777.1.2.56
		-- 1.3.6.1.4.1.7777.1.2.56
		dpmNormalNORMALKWHNet OBJECT-TYPE
			SYNTAX Integer32
			MAX-ACCESS read-only
			STATUS current
			DESCRIPTION
				"Normal NORMAL KWH Net."
			::= { dpmNormal 56 }

		
--   1.3.6.1.4.1.7777.1.2.57
-- 1.3.6.1.4.1.7777.1.2.57
		-- 1.3.6.1.4.1.7777.1.2.57
		dpmNormalNORMALKVARHNet OBJECT-TYPE
			SYNTAX Integer32
			MAX-ACCESS read-only
			STATUS current
			DESCRIPTION
				"Normal NORMAL KVARH Net."
			::= { dpmNormal 57 }

		
--   1.3.6.1.4.1.7777.1.2.58
-- 1.3.6.1.4.1.7777.1.2.58
		-- 1.3.6.1.4.1.7777.1.2.58
		dpmNormalNORMALKVAHNet OBJECT-TYPE
			SYNTAX Integer32
			MAX-ACCESS read-only
			STATUS current
			DESCRIPTION
				"Normal NORMAL KVAH Net."
			::= { dpmNormal 58 }

		
--   1.3.6.1.4.1.7777.1.2.59
-- 1.3.6.1.4.1.7777.1.2.59
		-- 1.3.6.1.4.1.7777.1.2.59
		dpmNormalEMERGKWHNet OBJECT-TYPE
			SYNTAX Integer32
			MAX-ACCESS read-only
			STATUS current
			DESCRIPTION
				"Normal EMERGENCY KWH Net."
			::= { dpmNormal 59 }

		
--   1.3.6.1.4.1.7777.1.2.60
-- 1.3.6.1.4.1.7777.1.2.60
		-- 1.3.6.1.4.1.7777.1.2.60
		dpmNormalEMERGKVARHNet OBJECT-TYPE
			SYNTAX Integer32
			MAX-ACCESS read-only
			STATUS current
			DESCRIPTION
				"Normal EMERGENCY KVARH Net."
			::= { dpmNormal 60 }

		
--   1.3.6.1.4.1.7777.1.2.61
-- 1.3.6.1.4.1.7777.1.2.61
		-- 1.3.6.1.4.1.7777.1.2.61
		dpmNormalEMERGKVAHNet OBJECT-TYPE
			SYNTAX Integer32
			MAX-ACCESS read-only
			STATUS current
			DESCRIPTION
				"Normal EMERGENCY KVAH Net."
			::= { dpmNormal 61 }

		
--   1.3.6.1.4.1.7777.1.2.62
-- 1.3.6.1.4.1.7777.1.2.62
		-- 1.3.6.1.4.1.7777.1.2.62
		dpmNormalNORMALMinTotalActivePower OBJECT-TYPE
			SYNTAX Integer32
			MAX-ACCESS read-only
			STATUS current
			DESCRIPTION
				"Normal NORMAL Min. Total Active Power."
			::= { dpmNormal 62 }

		
--   1.3.6.1.4.1.7777.1.2.63
-- 1.3.6.1.4.1.7777.1.2.63
		-- 1.3.6.1.4.1.7777.1.2.63
		dpmNormalNORMALMaxTotalActivePower OBJECT-TYPE
			SYNTAX Integer32
			MAX-ACCESS read-only
			STATUS current
			DESCRIPTION
				"Normal NORMAL Max. Total Active Power."
			::= { dpmNormal 63 }

		
--   1.3.6.1.4.1.7777.1.2.64
-- 1.3.6.1.4.1.7777.1.2.64
		-- 1.3.6.1.4.1.7777.1.2.64
		dpmNormalNORMALMinTotalReactivePower OBJECT-TYPE
			SYNTAX Integer32
			MAX-ACCESS read-only
			STATUS current
			DESCRIPTION
				"Normal NORMAL Min. Total reactive Power."
			::= { dpmNormal 64 }

		
--   1.3.6.1.4.1.7777.1.2.65
-- 1.3.6.1.4.1.7777.1.2.65
		-- 1.3.6.1.4.1.7777.1.2.65
		dpmNormalNORMALMaxTotalReactivePower OBJECT-TYPE
			SYNTAX Integer32
			MAX-ACCESS read-only
			STATUS current
			DESCRIPTION
				"Normal NORMAL Max. Total Reactive Power."
			::= { dpmNormal 65 }

		
--   1.3.6.1.4.1.7777.1.2.66
-- 1.3.6.1.4.1.7777.1.2.66
		-- 1.3.6.1.4.1.7777.1.2.66
		dpmNormalNORMALMinTotalApparentPower OBJECT-TYPE
			SYNTAX Integer32
			MAX-ACCESS read-only
			STATUS current
			DESCRIPTION
				"Normal NORMAL Min. Total Apparent Power."
			::= { dpmNormal 66 }

		
--   1.3.6.1.4.1.7777.1.2.67
-- 1.3.6.1.4.1.7777.1.2.67
		-- 1.3.6.1.4.1.7777.1.2.67
		dpmNormalNORMALMaxTotalApparentPower OBJECT-TYPE
			SYNTAX Integer32
			MAX-ACCESS read-only
			STATUS current
			DESCRIPTION
				"Normal NORMAL Max. Total Apparent Power."
			::= { dpmNormal 67 }

		
--   1.3.6.1.4.1.7777.1.2.68
-- 1.3.6.1.4.1.7777.1.2.68
		-- 1.3.6.1.4.1.7777.1.2.68
		dpmNormalEMERGMinTotalActivePower OBJECT-TYPE
			SYNTAX Integer32
			MAX-ACCESS read-only
			STATUS current
			DESCRIPTION
				"Normal EMERGENCY Min. Total Active Power."
			::= { dpmNormal 68 }

		
--   1.3.6.1.4.1.7777.1.2.69
-- 1.3.6.1.4.1.7777.1.2.69
		-- 1.3.6.1.4.1.7777.1.2.69
		dpmNormalEMERGMaxTotalActivePower OBJECT-TYPE
			SYNTAX Integer32
			MAX-ACCESS read-only
			STATUS current
			DESCRIPTION
				"Normal EMERGENCY Max. Total Active Power."
			::= { dpmNormal 69 }

		
--   1.3.6.1.4.1.7777.1.2.70
-- 1.3.6.1.4.1.7777.1.2.70
		-- 1.3.6.1.4.1.7777.1.2.70
		dpmNormalEMERGMinTotalReactivePower OBJECT-TYPE
			SYNTAX Integer32
			MAX-ACCESS read-only
			STATUS current
			DESCRIPTION
				"Normal EMERGENCY Min. Total Reactive Power."
			::= { dpmNormal 70 }

		
--   1.3.6.1.4.1.7777.1.2.71
-- 1.3.6.1.4.1.7777.1.2.71
		-- 1.3.6.1.4.1.7777.1.2.71
		dpmNormalEMERGMaxTotalReactivePower OBJECT-TYPE
			SYNTAX Integer32
			MAX-ACCESS read-only
			STATUS current
			DESCRIPTION
				"Normal EMERGENCY Max. Total Reactive Power."
			::= { dpmNormal 71 }

		
--   1.3.6.1.4.1.7777.1.2.72
-- 1.3.6.1.4.1.7777.1.2.72
		-- 1.3.6.1.4.1.7777.1.2.72
		dpmNormalEMERGMinTotalApparentPower OBJECT-TYPE
			SYNTAX Integer32
			MAX-ACCESS read-only
			STATUS current
			DESCRIPTION
				"Normal EMERGENCY Min. Total Apparent Power."
			::= { dpmNormal 72 }

		
--   1.3.6.1.4.1.7777.1.2.73
-- 1.3.6.1.4.1.7777.1.2.73
		-- 1.3.6.1.4.1.7777.1.2.73
		dpmNormalEMERGMaxTotalApparentPower OBJECT-TYPE
			SYNTAX Integer32
			MAX-ACCESS read-only
			STATUS current
			DESCRIPTION
				"Normal EMERGENCY Max. Total Apparent Power."
			::= { dpmNormal 73 }

		
--   1.3.6.1.4.1.7777.1.2.74
-- 1.3.6.1.4.1.7777.1.2.74
		-- 1.3.6.1.4.1.7777.1.2.74
		dpmNormalCurrentMonthMaxDemand OBJECT-TYPE
			SYNTAX Integer32
			MAX-ACCESS read-only
			STATUS current
			DESCRIPTION
				"Normal Current Month Maximum Demand."
			::= { dpmNormal 74 }

		
--   1.3.6.1.4.1.7777.1.2.75
-- 1.3.6.1.4.1.7777.1.2.75
		-- 1.3.6.1.4.1.7777.1.2.75
		dpmNormalMostRecentMonthMaxDemand OBJECT-TYPE
			SYNTAX Integer32
			MAX-ACCESS read-write
			STATUS current
			DESCRIPTION
				"Description."
			::= { dpmNormal 75 }

		
--   1.3.6.1.4.1.7777.1.2.76
-- 1.3.6.1.4.1.7777.1.2.76
		-- 1.3.6.1.4.1.7777.1.2.76
		dpmNormal2ndRecentMonthMaxDemand OBJECT-TYPE
			SYNTAX Integer32
			MAX-ACCESS read-only
			STATUS current
			DESCRIPTION
				"Normal 2nd Recent Month Maximum Demand."
			::= { dpmNormal 76 }

		
--   1.3.6.1.4.1.7777.1.2.77
-- 1.3.6.1.4.1.7777.1.2.77
		-- 1.3.6.1.4.1.7777.1.2.77
		dpmNormal3rdRecentMonthMaxDemand OBJECT-TYPE
			SYNTAX Integer32
			MAX-ACCESS read-only
			STATUS current
			DESCRIPTION
				"Normal 3rd Recent Month Maximum Demand."
			::= { dpmNormal 77 }

		
--   1.3.6.1.4.1.7777.1.2.78
-- 1.3.6.1.4.1.7777.1.2.78
		-- 1.3.6.1.4.1.7777.1.2.78
		dpmNormal4thRecentMonthMaxDemand OBJECT-TYPE
			SYNTAX Integer32
			MAX-ACCESS read-only
			STATUS current
			DESCRIPTION
				"Normal 4th Recent Month Maximum Demand."
			::= { dpmNormal 78 }

		
--   1.3.6.1.4.1.7777.1.2.79
-- 1.3.6.1.4.1.7777.1.2.79
		-- 1.3.6.1.4.1.7777.1.2.79
		dpmNormal5thRecentMonthMaxDemand OBJECT-TYPE
			SYNTAX Integer32
			MAX-ACCESS read-only
			STATUS current
			DESCRIPTION
				"Normal 5th Recent Month Maximum Demand."
			::= { dpmNormal 79 }

		
--   1.3.6.1.4.1.7777.1.2.80
-- 1.3.6.1.4.1.7777.1.2.80
		-- 1.3.6.1.4.1.7777.1.2.80
		dpmNormal6thRecentMonthMaxDemand OBJECT-TYPE
			SYNTAX Integer32
			MAX-ACCESS read-only
			STATUS current
			DESCRIPTION
				"Normal 6th Recent Month Maximum Demand."
			::= { dpmNormal 80 }

		
--   1.3.6.1.4.1.7777.1.2.81
-- 1.3.6.1.4.1.7777.1.2.81
		-- 1.3.6.1.4.1.7777.1.2.81
		dpmNormal7thRecentMonthMaxDemand OBJECT-TYPE
			SYNTAX Integer32
			MAX-ACCESS read-only
			STATUS current
			DESCRIPTION
				"Normal 7th Recent Month Maximum Demand."
			::= { dpmNormal 81 }

		
--   1.3.6.1.4.1.7777.1.2.82
-- 1.3.6.1.4.1.7777.1.2.82
		-- 1.3.6.1.4.1.7777.1.2.82
		dpmNormal8thRecentMonthMaxDemand OBJECT-TYPE
			SYNTAX Integer32
			MAX-ACCESS read-only
			STATUS current
			DESCRIPTION
				"Normal 8th Recent Month Maximum Demand."
			::= { dpmNormal 82 }

		
--   1.3.6.1.4.1.7777.1.2.83
-- 1.3.6.1.4.1.7777.1.2.83
		-- 1.3.6.1.4.1.7777.1.2.83
		dpmNormal9thRecentMonthMaxDemand OBJECT-TYPE
			SYNTAX Integer32
			MAX-ACCESS read-only
			STATUS current
			DESCRIPTION
				"Normal 9th Recent Month Maximum Demand."
			::= { dpmNormal 83 }

		
--   1.3.6.1.4.1.7777.1.2.84
-- 1.3.6.1.4.1.7777.1.2.84
		-- 1.3.6.1.4.1.7777.1.2.84
		dpmNormal10thRecentMonthMaxDemand OBJECT-TYPE
			SYNTAX Integer32
			MAX-ACCESS read-only
			STATUS current
			DESCRIPTION
				"Normal 10th Recent Month Maximum Demand."
			::= { dpmNormal 84 }

		
--   1.3.6.1.4.1.7777.1.2.85
-- 1.3.6.1.4.1.7777.1.2.85
		-- 1.3.6.1.4.1.7777.1.2.85
		dpmNormal11thRecentMonthMaxDemand OBJECT-TYPE
			SYNTAX Integer32
			MAX-ACCESS read-only
			STATUS current
			DESCRIPTION
				"Normal 11th Recent Month Maximum Demand."
			::= { dpmNormal 85 }

		
--   1.3.6.1.4.1.7777.1.2.86
-- 1.3.6.1.4.1.7777.1.2.86
		-- 1.3.6.1.4.1.7777.1.2.86
		dpmNormal12thRecentMonthMaxDemand OBJECT-TYPE
			SYNTAX Integer32
			MAX-ACCESS read-only
			STATUS current
			DESCRIPTION
				"Normal 12th Recent Month Maximum Demand."
			::= { dpmNormal 86 }

		
--   1.3.6.1.4.1.7777.1.2.87
-- 1.3.6.1.4.1.7777.1.2.87
		-- 1.3.6.1.4.1.7777.1.2.87
		dpmNormal13thRecentMonthMaxDemand OBJECT-TYPE
			SYNTAX Integer32
			MAX-ACCESS read-only
			STATUS current
			DESCRIPTION
				"Normal 13th Recent Month Maximum Demand.."
			::= { dpmNormal 87 }

		
--   1.3.6.1.4.1.7777.1.2.88
-- 1.3.6.1.4.1.7777.1.2.88
		-- 1.3.6.1.4.1.7777.1.2.88
		dpmNormal14thRecentMonthMaxDemand OBJECT-TYPE
			SYNTAX Integer32
			MAX-ACCESS read-only
			STATUS current
			DESCRIPTION
				"Normal 14th Recent Month Maximum Demand."
			::= { dpmNormal 88 }

		
--   1.3.6.1.4.1.7777.1.2.89
-- 1.3.6.1.4.1.7777.1.2.89
		-- 1.3.6.1.4.1.7777.1.2.89
		dpmNormal15thRecentMonthMaxDemand OBJECT-TYPE
			SYNTAX Integer32
			MAX-ACCESS read-only
			STATUS current
			DESCRIPTION
				"Normal 15th Recent Month Maximum Demand."
			::= { dpmNormal 89 }

		
--   1.3.6.1.4.1.7777.1.2.90
-- 1.3.6.1.4.1.7777.1.2.90
		-- 1.3.6.1.4.1.7777.1.2.90
		dpmNormal16thRecentMonthMaxDemand OBJECT-TYPE
			SYNTAX Integer32
			MAX-ACCESS read-only
			STATUS current
			DESCRIPTION
				"Normal 16th Recent Month Maximum Demand."
			::= { dpmNormal 90 }

		
--   1.3.6.1.4.1.7777.1.2.91
-- 1.3.6.1.4.1.7777.1.2.91
		-- 1.3.6.1.4.1.7777.1.2.91
		dpmNormal17thRecentMonthMaxDemand OBJECT-TYPE
			SYNTAX Integer32
			MAX-ACCESS read-only
			STATUS current
			DESCRIPTION
				"Normal 17th Recent Month Maximum Demand."
			::= { dpmNormal 91 }

		
--   1.3.6.1.4.1.7777.1.2.92
-- 1.3.6.1.4.1.7777.1.2.92
		-- 1.3.6.1.4.1.7777.1.2.92
		dpmNormal18thRecentMonthMaxDemand OBJECT-TYPE
			SYNTAX Integer32
			MAX-ACCESS read-only
			STATUS current
			DESCRIPTION
				"Normal 18th Recent Month Maximum Demand."
			::= { dpmNormal 92 }

		
--   1.3.6.1.4.1.7777.1.2.93
-- 1.3.6.1.4.1.7777.1.2.93
		-- 1.3.6.1.4.1.7777.1.2.93
		dpmNormal19thRecentMonthMaxDemand OBJECT-TYPE
			SYNTAX Integer32
			MAX-ACCESS read-only
			STATUS current
			DESCRIPTION
				"Normal 19th Recent Month Maximum Demand."
			::= { dpmNormal 93 }

		
--   1.3.6.1.4.1.7777.1.2.94
-- 1.3.6.1.4.1.7777.1.2.94
		-- 1.3.6.1.4.1.7777.1.2.94
		dpmNormal20thRecentMonthMaxDemand OBJECT-TYPE
			SYNTAX Integer32
			MAX-ACCESS read-only
			STATUS current
			DESCRIPTION
				"Normal 20th Recent Month Maximum Demand."
			::= { dpmNormal 94 }

		
--   1.3.6.1.4.1.7777.1.2.95
-- 1.3.6.1.4.1.7777.1.2.95
		-- 1.3.6.1.4.1.7777.1.2.95
		dpmNormal21stRecentMonthMaxDemand OBJECT-TYPE
			SYNTAX Integer32
			MAX-ACCESS read-only
			STATUS current
			DESCRIPTION
				"Normal 21st Recent Month Maximum Demand."
			::= { dpmNormal 95 }

		
--   1.3.6.1.4.1.7777.1.2.96
-- 1.3.6.1.4.1.7777.1.2.96
		-- 1.3.6.1.4.1.7777.1.2.96
		dpmNormal22ndRecentMonthMaxDemand OBJECT-TYPE
			SYNTAX Integer32
			MAX-ACCESS read-only
			STATUS current
			DESCRIPTION
				"Normal 22nd Recent Month Maximum Demand."
			::= { dpmNormal 96 }

		
--   1.3.6.1.4.1.7777.1.2.97
-- 1.3.6.1.4.1.7777.1.2.97
		-- 1.3.6.1.4.1.7777.1.2.97
		dpmNormal23rdRecentMonthMaxDemand OBJECT-TYPE
			SYNTAX Integer32
			MAX-ACCESS read-only
			STATUS current
			DESCRIPTION
				"Normal 23rd Recent Month Maximum Demand."
			::= { dpmNormal 97 }

		
--   1.3.6.1.4.1.7777.1.2.98
-- 1.3.6.1.4.1.7777.1.2.98
		-- 1.3.6.1.4.1.7777.1.2.98
		dpmNormal24thRecentMonthMaxDemand OBJECT-TYPE
			SYNTAX Integer32
			MAX-ACCESS read-only
			STATUS current
			DESCRIPTION
				"Normal 24th Recent Month Maximum Demand."
			::= { dpmNormal 98 }

		
--   1.3.6.1.4.1.7777.1.2.99
-- 1.3.6.1.4.1.7777.1.2.99
		-- 1.3.6.1.4.1.7777.1.2.99
		dpmNormalMainAndAuxilliaryPositions OBJECT-TYPE
			SYNTAX Integer32
			MAX-ACCESS read-only
			STATUS current
			DESCRIPTION
				"Normal Main & Auxiliary Switch positions."
			::= { dpmNormal 99 }

		
--   1.3.6.1.4.1.7777.1.2.100
-- 1.3.6.1.4.1.7777.1.2.100
		-- 1.3.6.1.4.1.7777.1.2.100
		dpmNormalResettableEngineRunCounter OBJECT-TYPE
			SYNTAX Integer32
			MAX-ACCESS read-only
			STATUS current
			DESCRIPTION
				"Normal Resettable Engine Counter."
			::= { dpmNormal 100 }

		
--   1.3.6.1.4.1.7777.1.2.101
-- 1.3.6.1.4.1.7777.1.2.101
		-- 1.3.6.1.4.1.7777.1.2.101
		dpmNormalCumulativeEngineRunCounter OBJECT-TYPE
			SYNTAX Integer32
			MAX-ACCESS read-only
			STATUS current
			DESCRIPTION
				"Normal Cumulative Engine Run Counter."
			::= { dpmNormal 101 }

		
--   1.3.6.1.4.1.7777.1.3
-- 1.3.6.1.4.1.7777.1.3
		-- 1.3.6.1.4.1.7777.1.3
		dpmEmergency OBJECT IDENTIFIER ::= { device 3 }

		
--    transfer switch end
-- 1.3.6.1.4.1.7777.1.2.2.1
-- 1.3.6.1.4.1.7777.1.3.1
-- 1.3.6.1.4.1.7777.1.3.1
		-- 1.3.6.1.4.1.7777.1.3.1
		dpmEmergencyDPMName OBJECT-TYPE
			SYNTAX DisplayString (SIZE (0..128))
			MAX-ACCESS read-only
			STATUS current
			DESCRIPTION
				"Emergency DPM name."
			::= { dpmEmergency 1 }

		
--    1.3.6.1.4.1.7777.1.2.2.2
-- 1.3.6.1.4.1.7777.1.3.2
-- 1.3.6.1.4.1.7777.1.3.2
		-- 1.3.6.1.4.1.7777.1.3.2
		dpmEmergencyDPMLoca OBJECT-TYPE
			SYNTAX DisplayString (SIZE (0..128))
			MAX-ACCESS read-only
			STATUS current
			DESCRIPTION
				"Emergency DPM Location."
			::= { dpmEmergency 2 }

		
--    1.3.6.1.4.1.7777.1.2.2.3
-- 1.3.6.1.4.1.7777.1.3.3
-- 1.3.6.1.4.1.7777.1.3.3
		-- 1.3.6.1.4.1.7777.1.3.3
		dpmEmergencyNominalVoltage OBJECT-TYPE
			SYNTAX Integer32
			MAX-ACCESS read-only
			STATUS current
			DESCRIPTION
				"Emergency Nominal Voltage."
			::= { dpmEmergency 3 }

		
--    1.3.6.1.4.1.7777.1.2.2.4
-- 1.3.6.1.4.1.7777.1.3.4
-- 1.3.6.1.4.1.7777.1.3.4
		-- 1.3.6.1.4.1.7777.1.3.4
		dpmEmergencyNominalCurrent OBJECT-TYPE
			SYNTAX Integer32
			MAX-ACCESS read-only
			STATUS current
			DESCRIPTION
				"Emergency Nominal Current."
			::= { dpmEmergency 4 }

		
--    1.3.6.1.4.1.7777.1.2.2.5
-- 1.3.6.1.4.1.7777.1.3.5
-- 1.3.6.1.4.1.7777.1.3.5
		-- 1.3.6.1.4.1.7777.1.3.5
		dpmEmergencyInstantaneousDemandKwMW OBJECT-TYPE
			SYNTAX Integer32
			MAX-ACCESS read-only
			STATUS current
			DESCRIPTION
				"Emergency Instantaneous Demand kW MW"
			::= { dpmEmergency 5 }

		
--    1.3.6.1.4.1.7777.1.2.2.6
-- 1.3.6.1.4.1.7777.1.3.6
-- 1.3.6.1.4.1.7777.1.3.6
		-- 1.3.6.1.4.1.7777.1.3.6
		dpmEmergencyInstantaneousDemandDate OBJECT-TYPE
			SYNTAX DisplayString (SIZE (0..128))
			MAX-ACCESS read-only
			STATUS current
			DESCRIPTION
				"Emergency Demand Date."
			::= { dpmEmergency 6 }

		
--    1.3.6.1.4.1.7777.1.2.2.7
-- 1.3.6.1.4.1.7777.1.3.7
-- 1.3.6.1.4.1.7777.1.3.7
		-- 1.3.6.1.4.1.7777.1.3.7
		dpmEmergencyInstantaneousDemandTime OBJECT-TYPE
			SYNTAX DisplayString (SIZE (0..128))
			MAX-ACCESS read-only
			STATUS current
			DESCRIPTION
				"Emergency Demand Time."
			::= { dpmEmergency 7 }

		
--    1.3.6.1.4.1.7777.1.2.2.8
-- 1.3.6.1.4.1.7777.1.3.8
-- 1.3.6.1.4.1.7777.1.3.8
		-- 1.3.6.1.4.1.7777.1.3.8
		dpmEmergencyBlockDemandforFullHouInkW OBJECT-TYPE
			SYNTAX Integer32
			MAX-ACCESS read-only
			STATUS current
			DESCRIPTION
				"Emergency Block Demand for Full Hou In kW."
			::= { dpmEmergency 8 }

		
--    1.3.6.1.4.1.7777.1.2.2.9
-- 1.3.6.1.4.1.7777.1.3.9
-- 1.3.6.1.4.1.7777.1.3.9
		-- 1.3.6.1.4.1.7777.1.3.9
		dpmEmergencyBlockDemandforFullDayInkW OBJECT-TYPE
			SYNTAX Integer32
			MAX-ACCESS read-only
			STATUS current
			DESCRIPTION
				"Emergency Block Demand for Full Day In kW."
			::= { dpmEmergency 9 }

		
--    1.3.6.1.4.1.7777.1.2.2.10
-- 1.3.6.1.4.1.7777.1.3.10
-- 1.3.6.1.4.1.7777.1.3.10
		-- 1.3.6.1.4.1.7777.1.3.10
		dpmEmergencyBlockDemandforFullMonthInKW OBJECT-TYPE
			SYNTAX Integer32
			MAX-ACCESS read-only
			STATUS current
			DESCRIPTION
				"Emergency Block Demand for Full Month In kW."
			::= { dpmEmergency 10 }

		
--    1.3.6.1.4.1.7777.1.2.2.11
-- 1.3.6.1.4.1.7777.1.3.11
-- 1.3.6.1.4.1.7777.1.3.11
		-- 1.3.6.1.4.1.7777.1.3.11
		dpmEmergencyBlockDemandforFullYear OBJECT-TYPE
			SYNTAX Integer32
			MAX-ACCESS read-only
			STATUS current
			DESCRIPTION
				"Emergency Block Demand for Full Year In kW."
			::= { dpmEmergency 11 }

		
--    1.3.6.1.4.1.7777.1.2.2.12
-- 1.3.6.1.4.1.7777.1.3.12
-- 1.3.6.1.4.1.7777.1.3.12
		-- 1.3.6.1.4.1.7777.1.3.12
		dpmEmergencyCurrentThdA OBJECT-TYPE
			SYNTAX Integer32
			MAX-ACCESS read-only
			STATUS current
			DESCRIPTION
				"Emergency Phase A THD Current.In percentage "
			::= { dpmEmergency 12 }

		
--    1.3.6.1.4.1.7777.1.2.2.13
-- 1.3.6.1.4.1.7777.1.3.13
-- 1.3.6.1.4.1.7777.1.3.13
		-- 1.3.6.1.4.1.7777.1.3.13
		dpmEmergencyCurrentThdB OBJECT-TYPE
			SYNTAX Integer32
			MAX-ACCESS read-only
			STATUS current
			DESCRIPTION
				"Emergency Phase B THD Current.In percentage"
			::= { dpmEmergency 13 }

		
--    1.3.6.1.4.1.7777.1.2.2.14
-- 1.3.6.1.4.1.7777.1.3.14
-- 1.3.6.1.4.1.7777.1.3.14
		-- 1.3.6.1.4.1.7777.1.3.14
		dpmEmergencyCurrentThdC OBJECT-TYPE
			SYNTAX Integer32
			MAX-ACCESS read-only
			STATUS current
			DESCRIPTION
				"Emergency Phase C THD Current.In percentage"
			::= { dpmEmergency 14 }

		
--    1.3.6.1.4.1.7777.1.2.2.15
-- 1.3.6.1.4.1.7777.1.3.15
-- 1.3.6.1.4.1.7777.1.3.15
		-- 1.3.6.1.4.1.7777.1.3.15
		dpmEmergencyVoltageThdA OBJECT-TYPE
			SYNTAX Integer32
			MAX-ACCESS read-only
			STATUS current
			DESCRIPTION
				"Emergency Phase A THD Voltage.In percentage"
			::= { dpmEmergency 15 }

		
--    1.3.6.1.4.1.7777.1.2.2.16
-- 1.3.6.1.4.1.7777.1.3.16
-- 1.3.6.1.4.1.7777.1.3.16
		-- 1.3.6.1.4.1.7777.1.3.16
		dpmEmergencyVoltageThdB OBJECT-TYPE
			SYNTAX Integer32
			MAX-ACCESS read-only
			STATUS current
			DESCRIPTION
				"Emergency Phase B THD Voltage.In percentage"
			::= { dpmEmergency 16 }

		
--    1.3.6.1.4.1.7777.1.2.2.17
-- 1.3.6.1.4.1.7777.1.3.17
-- 1.3.6.1.4.1.7777.1.3.17
		-- 1.3.6.1.4.1.7777.1.3.17
		dpmEmergencyVoltageThdC OBJECT-TYPE
			SYNTAX Integer32
			MAX-ACCESS read-only
			STATUS current
			DESCRIPTION
				"Emergency Phase C THD Voltage.In percentage"
			::= { dpmEmergency 17 }

		
--    1.3.6.1.4.1.7777.1.2.2.18
-- 1.3.6.1.4.1.7777.1.3.18
-- 1.3.6.1.4.1.7777.1.3.18
		-- 1.3.6.1.4.1.7777.1.3.18
		dpmEmergencyVab OBJECT-TYPE
			SYNTAX Integer32
			MAX-ACCESS read-only
			STATUS current
			DESCRIPTION
				"Emergency Vab Voltage."
			::= { dpmEmergency 18 }

		
--    1.3.6.1.4.1.7777.1.2.2.19
-- 1.3.6.1.4.1.7777.1.3.19
-- 1.3.6.1.4.1.7777.1.3.19
		-- 1.3.6.1.4.1.7777.1.3.19
		dpmEmergencyVbc OBJECT-TYPE
			SYNTAX Integer32
			MAX-ACCESS read-only
			STATUS current
			DESCRIPTION
				"Emergency Vbc Voltage."
			::= { dpmEmergency 19 }

		
--    1.3.6.1.4.1.7777.1.2.2.20
-- 1.3.6.1.4.1.7777.1.3.20
-- 1.3.6.1.4.1.7777.1.3.20
		-- 1.3.6.1.4.1.7777.1.3.20
		dpmEmergencyVca OBJECT-TYPE
			SYNTAX Integer32
			MAX-ACCESS read-only
			STATUS current
			DESCRIPTION
				"Emergency Vca Voltage."
			::= { dpmEmergency 20 }

		
--    1.3.6.1.4.1.7777.1.2.2.21
-- 1.3.6.1.4.1.7777.1.3.21
-- 1.3.6.1.4.1.7777.1.3.21
		-- 1.3.6.1.4.1.7777.1.3.21
		dpmEmergencyVolAverage OBJECT-TYPE
			SYNTAX Integer32
			MAX-ACCESS read-only
			STATUS current
			DESCRIPTION
				"Emergency Vol Average."
			::= { dpmEmergency 21 }

		
--    1.3.6.1.4.1.7777.1.2.2.22
-- 1.3.6.1.4.1.7777.1.3.22
-- 1.3.6.1.4.1.7777.1.3.22
		-- 1.3.6.1.4.1.7777.1.3.22
		dpmEmergencyVolUnbal OBJECT-TYPE
			SYNTAX Integer32
			MAX-ACCESS read-only
			STATUS current
			DESCRIPTION
				"Emergency Vol Unbal."
			::= { dpmEmergency 22 }

		
--    1.3.6.1.4.1.7777.1.2.2.23
-- 1.3.6.1.4.1.7777.1.3.23
-- 1.3.6.1.4.1.7777.1.3.23
		-- 1.3.6.1.4.1.7777.1.3.23
		dpmEmergencyVan OBJECT-TYPE
			SYNTAX Integer32
			MAX-ACCESS read-only
			STATUS current
			DESCRIPTION
				"Emergency Vol Van."
			::= { dpmEmergency 23 }

		
--    1.3.6.1.4.1.7777.1.2.2.24
-- 1.3.6.1.4.1.7777.1.3.24
-- 1.3.6.1.4.1.7777.1.3.24
		-- 1.3.6.1.4.1.7777.1.3.24
		dpmEmergencyVbn OBJECT-TYPE
			SYNTAX Integer32
			MAX-ACCESS read-only
			STATUS current
			DESCRIPTION
				"Emergency Vbn.."
			::= { dpmEmergency 24 }

		
--    1.3.6.1.4.1.7777.1.2.2.25
-- 1.3.6.1.4.1.7777.1.3.25
-- 1.3.6.1.4.1.7777.1.3.25
		-- 1.3.6.1.4.1.7777.1.3.25
		dpmEmergencyVcn OBJECT-TYPE
			SYNTAX Integer32
			MAX-ACCESS read-only
			STATUS current
			DESCRIPTION
				"Emergency Vcn. "
			::= { dpmEmergency 25 }

		
--    1.3.6.1.4.1.7777.1.2.2.26
-- 1.3.6.1.4.1.7777.1.3.26
-- 1.3.6.1.4.1.7777.1.3.26
		-- 1.3.6.1.4.1.7777.1.3.26
		dpmEmergencyVavgneutral OBJECT-TYPE
			SYNTAX Integer32
			MAX-ACCESS read-only
			STATUS current
			DESCRIPTION
				"Emergency Avg neutral Volatagae."
			::= { dpmEmergency 26 }

		
--    1.3.6.1.4.1.7777.1.2.2.27
-- 1.3.6.1.4.1.7777.1.3.27
-- 1.3.6.1.4.1.7777.1.3.27
		-- 1.3.6.1.4.1.7777.1.3.27
		dpmEmergencyFrequency OBJECT-TYPE
			SYNTAX Integer32
			MAX-ACCESS read-only
			STATUS current
			DESCRIPTION
				"Emergency Frequency."
			::= { dpmEmergency 27 }

		
--    1.3.6.1.4.1.7777.1.2.2.28
-- 1.3.6.1.4.1.7777.1.3.28
-- 1.3.6.1.4.1.7777.1.3.28
		-- 1.3.6.1.4.1.7777.1.3.28
		dpmEmergencyPowerFactor OBJECT-TYPE
			SYNTAX Integer32
			MAX-ACCESS read-only
			STATUS current
			DESCRIPTION
				"Emergency Power factor."
			::= { dpmEmergency 28 }

		
--    1.3.6.1.4.1.7777.1.2.2.29
-- 1.3.6.1.4.1.7777.1.3.29
-- 1.3.6.1.4.1.7777.1.3.29
		-- 1.3.6.1.4.1.7777.1.3.29
		dpmEmergencyCurPhaseA OBJECT-TYPE
			SYNTAX Integer32
			MAX-ACCESS read-only
			STATUS current
			DESCRIPTION
				"Emergency Phase A Current."
			::= { dpmEmergency 29 }

		
--    1.3.6.1.4.1.7777.1.2.2.30
-- 1.3.6.1.4.1.7777.1.3.30
-- 1.3.6.1.4.1.7777.1.3.30
		-- 1.3.6.1.4.1.7777.1.3.30
		dpmEmergencyCurPhaseB OBJECT-TYPE
			SYNTAX Integer32
			MAX-ACCESS read-only
			STATUS current
			DESCRIPTION
				"Emergency Phase B Current."
			::= { dpmEmergency 30 }

		
--    1.3.6.1.4.1.7777.1.2.2.31
-- 1.3.6.1.4.1.7777.1.3.31
-- 1.3.6.1.4.1.7777.1.3.31
		-- 1.3.6.1.4.1.7777.1.3.31
		dpmEmergencyCurPhaseC OBJECT-TYPE
			SYNTAX Integer32
			MAX-ACCESS read-only
			STATUS current
			DESCRIPTION
				"Emergency Phase C Current."
			::= { dpmEmergency 31 }

		
--    1.3.6.1.4.1.7777.1.2.2.32
-- 1.3.6.1.4.1.7777.1.3.32
-- 1.3.6.1.4.1.7777.1.3.32
		-- 1.3.6.1.4.1.7777.1.3.32
		dpmEmergencyPhaseCurAvg OBJECT-TYPE
			SYNTAX Integer32
			MAX-ACCESS read-only
			STATUS current
			DESCRIPTION
				"Emergency Phase Current aVG."
			::= { dpmEmergency 32 }

		
--    1.3.6.1.4.1.7777.1.2.2.33
-- 1.3.6.1.4.1.7777.1.3.33
-- 1.3.6.1.4.1.7777.1.3.33
		-- 1.3.6.1.4.1.7777.1.3.33
		dpmEmergencyPhaseCurUnbalancecePercentage OBJECT-TYPE
			SYNTAX Integer32
			MAX-ACCESS read-only
			STATUS current
			DESCRIPTION
				"Emergency Phase Cur Unbalancece Percentage."
			::= { dpmEmergency 33 }

		
--    1.3.6.1.4.1.7777.1.2.2.34
-- 1.3.6.1.4.1.7777.1.3.34
-- 1.3.6.1.4.1.7777.1.3.34
		-- 1.3.6.1.4.1.7777.1.3.34
		dpmEmergencyRealTotalPower OBJECT-TYPE
			SYNTAX Integer32
			MAX-ACCESS read-only
			STATUS current
			DESCRIPTION
				"Emergency Real Total power factor."
			::= { dpmEmergency 34 }

		
--    1.3.6.1.4.1.7777.1.2.2.35
-- 1.3.6.1.4.1.7777.1.3.35
-- 1.3.6.1.4.1.7777.1.3.35
		-- 1.3.6.1.4.1.7777.1.3.35
		dpmEmergencyReactiveTotalPower OBJECT-TYPE
			SYNTAX Integer32
			MAX-ACCESS read-only
			STATUS current
			DESCRIPTION
				"Emergency Reactive Total power."
			::= { dpmEmergency 35 }

		
--    1.3.6.1.4.1.7777.1.2.2.36
-- 1.3.6.1.4.1.7777.1.3.36
-- 1.3.6.1.4.1.7777.1.3.36
		-- 1.3.6.1.4.1.7777.1.3.36
		dpmEmergencyApparentTotalPower OBJECT-TYPE
			SYNTAX Integer32
			MAX-ACCESS read-only
			STATUS current
			DESCRIPTION
				"Emergency Apparent Total power."
			::= { dpmEmergency 36 }

		
--    1.3.6.1.4.1.7777.1.2.2.37
-- 1.3.6.1.4.1.7777.1.3.37
-- 1.3.6.1.4.1.7777.1.3.37
		-- 1.3.6.1.4.1.7777.1.3.37
		dpmEmergencyNetActiveEnergy OBJECT-TYPE
			SYNTAX Integer32
			MAX-ACCESS read-only
			STATUS current
			DESCRIPTION
				"Emergency Net Active Energy."
			::= { dpmEmergency 37 }

		
--    1.3.6.1.4.1.7777.1.2.2.39
-- 1.3.6.1.4.1.7777.1.3.38
-- 1.3.6.1.4.1.7777.1.3.38
		-- 1.3.6.1.4.1.7777.1.3.38
		dpmEmergencyFirmwareVersion OBJECT-TYPE
			SYNTAX DisplayString (SIZE (0..128))
			MAX-ACCESS read-only
			STATUS current
			DESCRIPTION
				"Emergency DPM Firmware ."
			::= { dpmEmergency 38 }

		
--   1.3.6.1.4.1.7777.1.3.39
-- 1.3.6.1.4.1.7777.1.3.39
		-- 1.3.6.1.4.1.7777.1.3.39
		dpmEmergencyActivePowerA OBJECT-TYPE
			SYNTAX Integer32
			MAX-ACCESS read-only
			STATUS current
			DESCRIPTION
				"Emergency Active Power phase A."
			::= { dpmEmergency 39 }

		
--   1.3.6.1.4.1.7777.1.3.40
-- 1.3.6.1.4.1.7777.1.3.40
		-- 1.3.6.1.4.1.7777.1.3.40
		dpmEmergencyActivePowerB OBJECT-TYPE
			SYNTAX Integer32
			MAX-ACCESS read-only
			STATUS current
			DESCRIPTION
				"Emergency Active Power phase B."
			::= { dpmEmergency 40 }

		
--   1.3.6.1.4.1.7777.1.3.41
-- 1.3.6.1.4.1.7777.1.3.41
		-- 1.3.6.1.4.1.7777.1.3.41
		dpmEmergencyActivePowerC OBJECT-TYPE
			SYNTAX Integer32
			MAX-ACCESS read-only
			STATUS current
			DESCRIPTION
				"Emergency Active Power phase C."
			::= { dpmEmergency 41 }

		
--   1.3.6.1.4.1.7777.1.3.42
-- 1.3.6.1.4.1.7777.1.3.42
		-- 1.3.6.1.4.1.7777.1.3.42
		dpmEmergencyActivePowerTotal OBJECT-TYPE
			SYNTAX Integer32
			MAX-ACCESS read-only
			STATUS current
			DESCRIPTION
				"Emergency Active Power total."
			::= { dpmEmergency 42 }

		
--   1.3.6.1.4.1.7777.1.3.43
-- 1.3.6.1.4.1.7777.1.3.43
		-- 1.3.6.1.4.1.7777.1.3.43
		dpmEmergencyReactivePowerA OBJECT-TYPE
			SYNTAX Integer32
			MAX-ACCESS read-only
			STATUS current
			DESCRIPTION
				"Emergency Reactive Power phase A."
			::= { dpmEmergency 43 }

		
--   1.3.6.1.4.1.7777.1.3.44
-- 1.3.6.1.4.1.7777.1.3.44
		-- 1.3.6.1.4.1.7777.1.3.44
		dpmEmergencyReactivePowerB OBJECT-TYPE
			SYNTAX Integer32
			MAX-ACCESS read-only
			STATUS current
			DESCRIPTION
				"Emergency Reactive Power phase B."
			::= { dpmEmergency 44 }

		
--   1.3.6.1.4.1.7777.1.3.45
-- 1.3.6.1.4.1.7777.1.3.45
		-- 1.3.6.1.4.1.7777.1.3.45
		dpmEmergencyReactivePowerC OBJECT-TYPE
			SYNTAX Integer32
			MAX-ACCESS read-only
			STATUS current
			DESCRIPTION
				"Emergency Reactive Power phase C."
			::= { dpmEmergency 45 }

		
--   1.3.6.1.4.1.7777.1.3.46
-- 1.3.6.1.4.1.7777.1.3.46
		-- 1.3.6.1.4.1.7777.1.3.46
		dpmEmergencyReactivePowerTotal OBJECT-TYPE
			SYNTAX Integer32
			MAX-ACCESS read-only
			STATUS current
			DESCRIPTION
				"Emergency Reactive Power Total."
			::= { dpmEmergency 46 }

		
--   1.3.6.1.4.1.7777.1.3.47
-- 1.3.6.1.4.1.7777.1.3.47
		-- 1.3.6.1.4.1.7777.1.3.47
		dpmEmergencyPowerFactorA OBJECT-TYPE
			SYNTAX Integer32
			MAX-ACCESS read-only
			STATUS current
			DESCRIPTION
				"Emergency Power Factor phase A."
			::= { dpmEmergency 47 }

		
--   1.3.6.1.4.1.7777.1.3.48
-- 1.3.6.1.4.1.7777.1.3.48
		-- 1.3.6.1.4.1.7777.1.3.48
		dpmEmergencyPowerFactorB OBJECT-TYPE
			SYNTAX Integer32
			MAX-ACCESS read-only
			STATUS current
			DESCRIPTION
				"Emergency Power Factor phase B."
			::= { dpmEmergency 48 }

		
--   1.3.6.1.4.1.7777.1.3.49
-- 1.3.6.1.4.1.7777.1.3.49
		-- 1.3.6.1.4.1.7777.1.3.49
		dpmEmergencyPowerFactorC OBJECT-TYPE
			SYNTAX Integer32
			MAX-ACCESS read-only
			STATUS current
			DESCRIPTION
				"Emergency Power Factor phase C."
			::= { dpmEmergency 49 }

		
--   1.3.6.1.4.1.7777.1.3.50
-- 1.3.6.1.4.1.7777.1.3.50
		-- 1.3.6.1.4.1.7777.1.3.50
		dpmEmergencyPowerFactorTotal OBJECT-TYPE
			SYNTAX Integer32
			MAX-ACCESS read-only
			STATUS current
			DESCRIPTION
				"Emergency Power Factor Total."
			::= { dpmEmergency 50 }

		
--   1.3.6.1.4.1.7777.1.3.51
-- 1.3.6.1.4.1.7777.1.3.51
		-- 1.3.6.1.4.1.7777.1.3.51
		dpmEmergencyVoltAmperePowerA OBJECT-TYPE
			SYNTAX Integer32
			MAX-ACCESS read-only
			STATUS current
			DESCRIPTION
				"Emergency volt-ampere Power phase A."
			::= { dpmEmergency 51 }

		
--   1.3.6.1.4.1.7777.1.3.52
-- 1.3.6.1.4.1.7777.1.3.52
		-- 1.3.6.1.4.1.7777.1.3.52
		dpmEmergencyVoltAmperePowerB OBJECT-TYPE
			SYNTAX Integer32
			MAX-ACCESS read-only
			STATUS current
			DESCRIPTION
				"Emergency volt-ampere Power phase B."
			::= { dpmEmergency 52 }

		
--   1.3.6.1.4.1.7777.1.3.53
-- 1.3.6.1.4.1.7777.1.3.53
		-- 1.3.6.1.4.1.7777.1.3.53
		dpmEmergencyVoltAmperePowerC OBJECT-TYPE
			SYNTAX Integer32
			MAX-ACCESS read-only
			STATUS current
			DESCRIPTION
				"Emergency volt-ampere Power phase C."
			::= { dpmEmergency 53 }

		
--   1.3.6.1.4.1.7777.1.3.54
-- 1.3.6.1.4.1.7777.1.3.54
		-- 1.3.6.1.4.1.7777.1.3.54
		dpmEmergencyVoltAmperePowerTotal OBJECT-TYPE
			SYNTAX Integer32
			MAX-ACCESS read-only
			STATUS current
			DESCRIPTION
				"Emergency volt-ampere Power Total."
			::= { dpmEmergency 54 }

		
--   1.3.6.1.4.1.7777.1.3.55
-- 1.3.6.1.4.1.7777.1.3.55
		-- 1.3.6.1.4.1.7777.1.3.55
		dpmEmergencyMaxWattDemand OBJECT-TYPE
			SYNTAX Integer32
			MAX-ACCESS read-only
			STATUS current
			DESCRIPTION
				"Emergency Maximum Watt Demand."
			::= { dpmEmergency 55 }

		
--   1.3.6.1.4.1.7777.1.3.56
-- 1.3.6.1.4.1.7777.1.3.56
		-- 1.3.6.1.4.1.7777.1.3.56
		dpmEmergencyNORMALKWHNet OBJECT-TYPE
			SYNTAX Integer32
			MAX-ACCESS read-only
			STATUS current
			DESCRIPTION
				"Emergency NORMAL kWH Net."
			::= { dpmEmergency 56 }

		
--   1.3.6.1.4.1.7777.1.3.57
-- 1.3.6.1.4.1.7777.1.3.57
		-- 1.3.6.1.4.1.7777.1.3.57
		dpmEmergencyNORMALKVARHNet OBJECT-TYPE
			SYNTAX Integer32
			MAX-ACCESS read-only
			STATUS current
			DESCRIPTION
				"Emergency NORMAL kVarH Net."
			::= { dpmEmergency 57 }

		
--   1.3.6.1.4.1.7777.1.3.58
-- 1.3.6.1.4.1.7777.1.3.58
		-- 1.3.6.1.4.1.7777.1.3.58
		dpmEmergencyNORMALKVAHNet OBJECT-TYPE
			SYNTAX Integer32
			MAX-ACCESS read-only
			STATUS current
			DESCRIPTION
				"Emergency NORMAL kVAH Net."
			::= { dpmEmergency 58 }

		
--   1.3.6.1.4.1.7777.1.3.59
-- 1.3.6.1.4.1.7777.1.3.59
		-- 1.3.6.1.4.1.7777.1.3.59
		dpmEmergencyEMERGKWHNet OBJECT-TYPE
			SYNTAX Integer32
			MAX-ACCESS read-only
			STATUS current
			DESCRIPTION
				"Emergency EMERGENCY kWH Net."
			::= { dpmEmergency 59 }

		
--   1.3.6.1.4.1.7777.1.3.60
-- 1.3.6.1.4.1.7777.1.3.60
		-- 1.3.6.1.4.1.7777.1.3.60
		dpmEmergencyEMERGKVARHNet OBJECT-TYPE
			SYNTAX Integer32
			MAX-ACCESS read-only
			STATUS current
			DESCRIPTION
				"Emergency EMERGENCY kVarH Net."
			::= { dpmEmergency 60 }

		
--   1.3.6.1.4.1.7777.1.3.61
-- 1.3.6.1.4.1.7777.1.3.61
		-- 1.3.6.1.4.1.7777.1.3.61
		dpmEmergencyEMERGKVAHNet OBJECT-TYPE
			SYNTAX Integer32
			MAX-ACCESS read-only
			STATUS current
			DESCRIPTION
				"Emergency EMERGENCY kVAH Net."
			::= { dpmEmergency 61 }

		
--   1.3.6.1.4.1.7777.1.3.62
-- 1.3.6.1.4.1.7777.1.3.62
		-- 1.3.6.1.4.1.7777.1.3.62
		dpmEmergencyNORMALMinTotalActivePower OBJECT-TYPE
			SYNTAX Integer32
			MAX-ACCESS read-only
			STATUS current
			DESCRIPTION
				"Emergency NORMAL Minimum Total Active Power."
			::= { dpmEmergency 62 }

		
--   1.3.6.1.4.1.7777.1.3.63
-- 1.3.6.1.4.1.7777.1.3.63
		-- 1.3.6.1.4.1.7777.1.3.63
		dpmEmergencyNORMALMaxTotalActivePower OBJECT-TYPE
			SYNTAX Integer32
			MAX-ACCESS read-only
			STATUS current
			DESCRIPTION
				"Emergency NORMAL Maximum Total Active Power."
			::= { dpmEmergency 63 }

		
--   1.3.6.1.4.1.7777.1.3.64
-- 1.3.6.1.4.1.7777.1.3.64
		-- 1.3.6.1.4.1.7777.1.3.64
		dpmEmergencyNORMALMinTotalReactivePower OBJECT-TYPE
			SYNTAX Integer32
			MAX-ACCESS read-only
			STATUS current
			DESCRIPTION
				"Emergency NORMAL Minimum Total Reactive  Power."
			::= { dpmEmergency 64 }

		
--   1.3.6.1.4.1.7777.1.3.65
-- 1.3.6.1.4.1.7777.1.3.65
		-- 1.3.6.1.4.1.7777.1.3.65
		dpmEmergencyNORMALMaxTotalReactivePower OBJECT-TYPE
			SYNTAX Integer32
			MAX-ACCESS read-only
			STATUS current
			DESCRIPTION
				"Emergency NORMAL Maximum Total Reactive Power."
			::= { dpmEmergency 65 }

		
--   1.3.6.1.4.1.7777.1.3.66
-- 1.3.6.1.4.1.7777.1.3.66
		-- 1.3.6.1.4.1.7777.1.3.66
		dpmEmergencyNORMALMinTotalApparentPower OBJECT-TYPE
			SYNTAX Integer32
			MAX-ACCESS read-only
			STATUS current
			DESCRIPTION
				"Emergency NORMAL Minimum Total Apparent Power."
			::= { dpmEmergency 66 }

		
--   1.3.6.1.4.1.7777.1.3.67
-- 1.3.6.1.4.1.7777.1.3.67
		-- 1.3.6.1.4.1.7777.1.3.67
		dpmEmergencyNORMALMaxTotalApparentPower OBJECT-TYPE
			SYNTAX Integer32
			MAX-ACCESS read-only
			STATUS current
			DESCRIPTION
				"Emergency NORMAL Maximum Total Apparent Power."
			::= { dpmEmergency 67 }

		
--   1.3.6.1.4.1.7777.1.3.68
-- 1.3.6.1.4.1.7777.1.3.68
		-- 1.3.6.1.4.1.7777.1.3.68
		dpmEmergencyEMERGMinTotalActivePower OBJECT-TYPE
			SYNTAX Integer32
			MAX-ACCESS read-only
			STATUS current
			DESCRIPTION
				"Emergency EMERGENCY Minimum Total Active Power."
			::= { dpmEmergency 68 }

		
--   1.3.6.1.4.1.7777.1.3.69
-- 1.3.6.1.4.1.7777.1.3.69
		-- 1.3.6.1.4.1.7777.1.3.69
		dpmEmergencyEMERGMaxTotalActivePower OBJECT-TYPE
			SYNTAX Integer32
			MAX-ACCESS read-only
			STATUS current
			DESCRIPTION
				"Emergency EMERGENCY Maximum Total Active Power."
			::= { dpmEmergency 69 }

		
--   1.3.6.1.4.1.7777.1.3.70
-- 1.3.6.1.4.1.7777.1.3.70
		-- 1.3.6.1.4.1.7777.1.3.70
		dpmEmergencyEMERGMinTotalReactivePower OBJECT-TYPE
			SYNTAX Integer32
			MAX-ACCESS read-only
			STATUS current
			DESCRIPTION
				"Emergency EMERGENCY Minimum Total Reactive  Power."
			::= { dpmEmergency 70 }

		
--   1.3.6.1.4.1.7777.1.3.71
-- 1.3.6.1.4.1.7777.1.3.71
		-- 1.3.6.1.4.1.7777.1.3.71
		dpmEmergencyEMERGMaxTotalReactivePower OBJECT-TYPE
			SYNTAX Integer32
			MAX-ACCESS read-only
			STATUS current
			DESCRIPTION
				"Emergency EMERGENCY Maximum Total Reactive Power."
			::= { dpmEmergency 71 }

		
--   1.3.6.1.4.1.7777.1.3.72
-- 1.3.6.1.4.1.7777.1.3.72
		-- 1.3.6.1.4.1.7777.1.3.72
		dpmEmergencyEMERGMinTotalApparentPower OBJECT-TYPE
			SYNTAX Integer32
			MAX-ACCESS read-only
			STATUS current
			DESCRIPTION
				"Emergency EMERGENCY Minimum Total Apparent Power."
			::= { dpmEmergency 72 }

		
--   1.3.6.1.4.1.7777.1.3.73
-- 1.3.6.1.4.1.7777.1.3.73
		-- 1.3.6.1.4.1.7777.1.3.73
		dpmEmergencyEMERGMaxTotalApparentPower OBJECT-TYPE
			SYNTAX Integer32
			MAX-ACCESS read-only
			STATUS current
			DESCRIPTION
				"Emergency EMERGENCY Maximum Total Apparent Power."
			::= { dpmEmergency 73 }

		
--   1.3.6.1.4.1.7777.1.3.74
-- 1.3.6.1.4.1.7777.1.3.74
		-- 1.3.6.1.4.1.7777.1.3.74
		dpmEmergencyCurrentMonthMaxDemand OBJECT-TYPE
			SYNTAX Integer32
			MAX-ACCESS read-only
			STATUS current
			DESCRIPTION
				"Emergency Current Month Maximum Demand."
			::= { dpmEmergency 74 }

		
--   1.3.6.1.4.1.7777.1.3.75
-- 1.3.6.1.4.1.7777.1.3.75
		-- 1.3.6.1.4.1.7777.1.3.75
		dpmEmergencyMostRecentMonthMaxDemand OBJECT-TYPE
			SYNTAX Integer32
			MAX-ACCESS read-write
			STATUS current
			DESCRIPTION
				"Emergency Most Recent Month Max Demand."
			::= { dpmEmergency 75 }

		
--   1.3.6.1.4.1.7777.1.3.76
-- 1.3.6.1.4.1.7777.1.3.76
		-- 1.3.6.1.4.1.7777.1.3.76
		dpmEmergency2ndRecentMonthMaxDemand OBJECT-TYPE
			SYNTAX Integer32
			MAX-ACCESS read-only
			STATUS current
			DESCRIPTION
				"Emergency 2nd Most Recent Month Max Demand."
			::= { dpmEmergency 76 }

		
--   1.3.6.1.4.1.7777.1.3.77
-- 1.3.6.1.4.1.7777.1.3.77
		-- 1.3.6.1.4.1.7777.1.3.77
		dpmEmergency3rdRecentMonthMaxDemand OBJECT-TYPE
			SYNTAX Integer32
			MAX-ACCESS read-only
			STATUS current
			DESCRIPTION
				"Emergency 3rd Most Recent Month Max Demand."
			::= { dpmEmergency 77 }

		
--   1.3.6.1.4.1.7777.1.3.78
-- 1.3.6.1.4.1.7777.1.3.78
		-- 1.3.6.1.4.1.7777.1.3.78
		dpmEmergency4thRecentMonthMaxDemand OBJECT-TYPE
			SYNTAX Integer32
			MAX-ACCESS read-only
			STATUS current
			DESCRIPTION
				"Emergency 4th Most Recent Month Max Demand."
			::= { dpmEmergency 78 }

		
--   1.3.6.1.4.1.7777.1.3.79
-- 1.3.6.1.4.1.7777.1.3.79
		-- 1.3.6.1.4.1.7777.1.3.79
		dpmEmergency5thRecentMonthMaxDemand OBJECT-TYPE
			SYNTAX Integer32
			MAX-ACCESS read-only
			STATUS current
			DESCRIPTION
				"Emergency 5th Most Recent Month Max Demand."
			::= { dpmEmergency 79 }

		
--   1.3.6.1.4.1.7777.1.3.80
-- 1.3.6.1.4.1.7777.1.3.80
		-- 1.3.6.1.4.1.7777.1.3.80
		dpmEmergency6thRecentMonthMaxDemand OBJECT-TYPE
			SYNTAX Integer32
			MAX-ACCESS read-only
			STATUS current
			DESCRIPTION
				"Emergency 6th Most Recent Month Max Demand."
			::= { dpmEmergency 80 }

		
--   1.3.6.1.4.1.7777.1.3.81
-- 1.3.6.1.4.1.7777.1.3.81
		-- 1.3.6.1.4.1.7777.1.3.81
		dpmEmergency7thRecentMonthMaxDemand OBJECT-TYPE
			SYNTAX Integer32
			MAX-ACCESS read-only
			STATUS current
			DESCRIPTION
				"Emergency 7th Most Recent Month Max Demand."
			::= { dpmEmergency 81 }

		
--   1.3.6.1.4.1.7777.1.3.82
-- 1.3.6.1.4.1.7777.1.3.82
		-- 1.3.6.1.4.1.7777.1.3.82
		dpmEmergency8thRecentMonthMaxDemand OBJECT-TYPE
			SYNTAX Integer32
			MAX-ACCESS read-only
			STATUS current
			DESCRIPTION
				"Emergency 8th Most Recent Month Max Demand."
			::= { dpmEmergency 82 }

		
--   1.3.6.1.4.1.7777.1.3.83
-- 1.3.6.1.4.1.7777.1.3.83
		-- 1.3.6.1.4.1.7777.1.3.83
		dpmEmergency9thRecentMonthMaxDemand OBJECT-TYPE
			SYNTAX Integer32
			MAX-ACCESS read-only
			STATUS current
			DESCRIPTION
				"Emergency 9th Most Recent Month Max Demand."
			::= { dpmEmergency 83 }

		
--   1.3.6.1.4.1.7777.1.3.84
-- 1.3.6.1.4.1.7777.1.3.84
		-- 1.3.6.1.4.1.7777.1.3.84
		dpmEmergency10thRecentMonthMaxDemand OBJECT-TYPE
			SYNTAX Integer32
			MAX-ACCESS read-only
			STATUS current
			DESCRIPTION
				"Emergency 10th Most Recent Month Max Demand."
			::= { dpmEmergency 84 }

		
--   1.3.6.1.4.1.7777.1.3.85
-- 1.3.6.1.4.1.7777.1.3.85
		-- 1.3.6.1.4.1.7777.1.3.85
		dpmEmergency11thRecentMonthMaxDemand OBJECT-TYPE
			SYNTAX Integer32
			MAX-ACCESS read-only
			STATUS current
			DESCRIPTION
				"Emergency 11th Most Recent Month Max Demand."
			::= { dpmEmergency 85 }

		
--   1.3.6.1.4.1.7777.1.3.86
-- 1.3.6.1.4.1.7777.1.3.86
		-- 1.3.6.1.4.1.7777.1.3.86
		dpmEmergency12thRecentMonthMaxDemand OBJECT-TYPE
			SYNTAX Integer32
			MAX-ACCESS read-only
			STATUS current
			DESCRIPTION
				"Emergency 12th Most Recent Month Max Demand."
			::= { dpmEmergency 86 }

		
--   1.3.6.1.4.1.7777.1.3.87
-- 1.3.6.1.4.1.7777.1.3.87
		-- 1.3.6.1.4.1.7777.1.3.87
		dpmEmergency13thRecentMonthMaxDemand OBJECT-TYPE
			SYNTAX Integer32
			MAX-ACCESS read-only
			STATUS current
			DESCRIPTION
				"Emergency 13th Most Recent Month Max Demand."
			::= { dpmEmergency 87 }

		
--   1.3.6.1.4.1.7777.1.3.88
-- 1.3.6.1.4.1.7777.1.3.88
		-- 1.3.6.1.4.1.7777.1.3.88
		dpmEmergency14thRecentMonthMaxDemand OBJECT-TYPE
			SYNTAX Integer32
			MAX-ACCESS read-only
			STATUS current
			DESCRIPTION
				"Emergency 14th Most Recent Month Max Demand."
			::= { dpmEmergency 88 }

		
--   1.3.6.1.4.1.7777.1.3.89
-- 1.3.6.1.4.1.7777.1.3.89
		-- 1.3.6.1.4.1.7777.1.3.89
		dpmEmergency15thRecentMonthMaxDemand OBJECT-TYPE
			SYNTAX Integer32
			MAX-ACCESS read-only
			STATUS current
			DESCRIPTION
				"Emergency 15th Most Recent Month Max Demand."
			::= { dpmEmergency 89 }

		
--   1.3.6.1.4.1.7777.1.3.90
-- 1.3.6.1.4.1.7777.1.3.90
		-- 1.3.6.1.4.1.7777.1.3.90
		dpmEmergency16thRecentMonthMaxDemand OBJECT-TYPE
			SYNTAX Integer32
			MAX-ACCESS read-only
			STATUS current
			DESCRIPTION
				"Emergency 16th Most Recent Month Max Demand."
			::= { dpmEmergency 90 }

		
--   1.3.6.1.4.1.7777.1.3.91
-- 1.3.6.1.4.1.7777.1.3.91
		-- 1.3.6.1.4.1.7777.1.3.91
		dpmEmergency17thRecentMonthMaxDemand OBJECT-TYPE
			SYNTAX Integer32
			MAX-ACCESS read-only
			STATUS current
			DESCRIPTION
				"Emergency 17th Most Recent Month Max Demand."
			::= { dpmEmergency 91 }

		
--   1.3.6.1.4.1.7777.1.3.92
-- 1.3.6.1.4.1.7777.1.3.92
		-- 1.3.6.1.4.1.7777.1.3.92
		dpmEmergency18thRecentMonthMaxDemand OBJECT-TYPE
			SYNTAX Integer32
			MAX-ACCESS read-only
			STATUS current
			DESCRIPTION
				"Emergency 18th Most Recent Month Max Demand."
			::= { dpmEmergency 92 }

		
--   1.3.6.1.4.1.7777.1.3.93
-- 1.3.6.1.4.1.7777.1.3.93
		-- 1.3.6.1.4.1.7777.1.3.93
		dpmEmergency19thRecentMonthMaxDemand OBJECT-TYPE
			SYNTAX Integer32
			MAX-ACCESS read-only
			STATUS current
			DESCRIPTION
				"Emergency 19th Most Recent Month Max Demand."
			::= { dpmEmergency 93 }

		
--   1.3.6.1.4.1.7777.1.3.94
-- 1.3.6.1.4.1.7777.1.3.94
		-- 1.3.6.1.4.1.7777.1.3.94
		dpmEmergency20thRecentMonthMaxDemand OBJECT-TYPE
			SYNTAX Integer32
			MAX-ACCESS read-only
			STATUS current
			DESCRIPTION
				"Emergency 20th Most Recent Month Max Demand."
			::= { dpmEmergency 94 }

		
--   1.3.6.1.4.1.7777.1.3.95
-- 1.3.6.1.4.1.7777.1.3.95
		-- 1.3.6.1.4.1.7777.1.3.95
		dpmEmergency21stRecentMonthMaxDemand OBJECT-TYPE
			SYNTAX Integer32
			MAX-ACCESS read-only
			STATUS current
			DESCRIPTION
				"Emergency 21st Most Recent Month Max Demand."
			::= { dpmEmergency 95 }

		
--   1.3.6.1.4.1.7777.1.3.96
-- 1.3.6.1.4.1.7777.1.3.96
		-- 1.3.6.1.4.1.7777.1.3.96
		dpmEmergency22ndRecentMonthMaxDemand OBJECT-TYPE
			SYNTAX Integer32
			MAX-ACCESS read-only
			STATUS current
			DESCRIPTION
				"Emergency 22nd Most Recent Month Max Demand."
			::= { dpmEmergency 96 }

		
--   1.3.6.1.4.1.7777.1.3.97
-- 1.3.6.1.4.1.7777.1.3.97
		-- 1.3.6.1.4.1.7777.1.3.97
		dpmEmergency23rdRecentMonthMaxDemand OBJECT-TYPE
			SYNTAX Integer32
			MAX-ACCESS read-only
			STATUS current
			DESCRIPTION
				"Emergency 23rd Most Recent Month Max Demand."
			::= { dpmEmergency 97 }

		
--   1.3.6.1.4.1.7777.1.3.98
-- 1.3.6.1.4.1.7777.1.3.98
		-- 1.3.6.1.4.1.7777.1.3.98
		dpmEmergency24thRecentMonthMaxDemand OBJECT-TYPE
			SYNTAX Integer32
			MAX-ACCESS read-only
			STATUS current
			DESCRIPTION
				"Emergency 24th Most Recent Month Max Demand."
			::= { dpmEmergency 98 }

		
--   1.3.6.1.4.1.7777.1.3.99
-- 1.3.6.1.4.1.7777.1.3.99
		-- 1.3.6.1.4.1.7777.1.3.99
		dpmEmergencyMainAndAuxilliaryPositions OBJECT-TYPE
			SYNTAX Integer32
			MAX-ACCESS read-only
			STATUS current
			DESCRIPTION
				"Emergency Main & Auxiliary Switch positions."
			::= { dpmEmergency 99 }

		
--   1.3.6.1.4.1.7777.1.3.100
-- 1.3.6.1.4.1.7777.1.3.100
		-- 1.3.6.1.4.1.7777.1.3.100
		dpmEmergencyResettableEngineRunCounter OBJECT-TYPE
			SYNTAX Integer32
			MAX-ACCESS read-only
			STATUS current
			DESCRIPTION
				"Emergency Resettable Engine Runtime counter in Hours."
			::= { dpmEmergency 100 }

		
--   1.3.6.1.4.1.7777.1.3.101
-- 1.3.6.1.4.1.7777.1.3.101
		-- 1.3.6.1.4.1.7777.1.3.101
		dpmEmergencyCumulativeEngineRunCounter OBJECT-TYPE
			SYNTAX Integer32
			MAX-ACCESS read-only
			STATUS current
			DESCRIPTION
				"Emergency Cumulative Engine Runtime counter in Hours."
			::= { dpmEmergency 101 }

		
--   1.3.6.1.4.1.7777.1.4
-- 1.3.6.1.4.1.7777.1.4
		-- 1.3.6.1.4.1.7777.1.4
		dpmLoad OBJECT IDENTIFIER ::= { device 4 }

		
--    transfer switch end
-- 1.3.6.1.4.1.7777.1.2.2.1
-- 1.3.6.1.4.1.7777.1.4.1
-- 1.3.6.1.4.1.7777.1.4.1
		-- 1.3.6.1.4.1.7777.1.4.1
		dpmLoadDPMName OBJECT-TYPE
			SYNTAX DisplayString (SIZE (0..128))
			MAX-ACCESS read-only
			STATUS current
			DESCRIPTION
				"Load DPM name."
			::= { dpmLoad 1 }

		
--    1.3.6.1.4.1.7777.1.2.2.2
-- 1.3.6.1.4.1.7777.1.4.2
-- 1.3.6.1.4.1.7777.1.4.2
		-- 1.3.6.1.4.1.7777.1.4.2
		dpmLoadDPMLoca OBJECT-TYPE
			SYNTAX DisplayString (SIZE (0..128))
			MAX-ACCESS read-only
			STATUS current
			DESCRIPTION
				"Load DPM Location."
			::= { dpmLoad 2 }

		
--    1.3.6.1.4.1.7777.1.2.2.3
-- 1.3.6.1.4.1.7777.1.4.3
-- 1.3.6.1.4.1.7777.1.4.3
		-- 1.3.6.1.4.1.7777.1.4.3
		dpmLoadNominalVoltage OBJECT-TYPE
			SYNTAX Integer32
			MAX-ACCESS read-only
			STATUS current
			DESCRIPTION
				"Load Nominal Voltage."
			::= { dpmLoad 3 }

		
--    1.3.6.1.4.1.7777.1.2.2.4
-- 1.3.6.1.4.1.7777.1.4.4
-- 1.3.6.1.4.1.7777.1.4.4
		-- 1.3.6.1.4.1.7777.1.4.4
		dpmLoadNominalCurrent OBJECT-TYPE
			SYNTAX Integer32
			MAX-ACCESS read-only
			STATUS current
			DESCRIPTION
				"Load Nominal Current."
			::= { dpmLoad 4 }

		
--    1.3.6.1.4.1.7777.1.2.2.5
-- 1.3.6.1.4.1.7777.1.4.5
-- 1.3.6.1.4.1.7777.1.4.5
		-- 1.3.6.1.4.1.7777.1.4.5
		dpmLoadInstantaneousDemandKwMW OBJECT-TYPE
			SYNTAX Integer32
			MAX-ACCESS read-only
			STATUS current
			DESCRIPTION
				"Load Instantaneous Demand kW MW"
			::= { dpmLoad 5 }

		
--    1.3.6.1.4.1.7777.1.2.2.6
-- 1.3.6.1.4.1.7777.1.4.6
-- 1.3.6.1.4.1.7777.1.4.6
		-- 1.3.6.1.4.1.7777.1.4.6
		dpmLoadInstantaneousDemandDate OBJECT-TYPE
			SYNTAX DisplayString (SIZE (0..128))
			MAX-ACCESS read-only
			STATUS current
			DESCRIPTION
				"Load Demand Date."
			::= { dpmLoad 6 }

		
--    1.3.6.1.4.1.7777.1.2.2.7
-- 1.3.6.1.4.1.7777.1.4.7
-- 1.3.6.1.4.1.7777.1.4.7
		-- 1.3.6.1.4.1.7777.1.4.7
		dpmLoadInstantaneousDemandTime OBJECT-TYPE
			SYNTAX DisplayString (SIZE (0..128))
			MAX-ACCESS read-only
			STATUS current
			DESCRIPTION
				"Load Demand Time."
			::= { dpmLoad 7 }

		
--    1.3.6.1.4.1.7777.1.2.2.8
-- 1.3.6.1.4.1.7777.1.4.8
-- 1.3.6.1.4.1.7777.1.4.8
		-- 1.3.6.1.4.1.7777.1.4.8
		dpmLoadBlockDemandforFullHouInkW OBJECT-TYPE
			SYNTAX Integer32
			MAX-ACCESS read-only
			STATUS current
			DESCRIPTION
				"Load Block Demand for Full Hou In kW."
			::= { dpmLoad 8 }

		
--    1.3.6.1.4.1.7777.1.2.2.9
-- 1.3.6.1.4.1.7777.1.4.9
-- 1.3.6.1.4.1.7777.1.4.9
		-- 1.3.6.1.4.1.7777.1.4.9
		dpmLoadBlockDemandforFullDayInkW OBJECT-TYPE
			SYNTAX Integer32
			MAX-ACCESS read-only
			STATUS current
			DESCRIPTION
				"Load Block Demand for Full Day In kW."
			::= { dpmLoad 9 }

		
--    1.3.6.1.4.1.7777.1.2.2.10
-- 1.3.6.1.4.1.7777.1.4.10
-- 1.3.6.1.4.1.7777.1.4.10
		-- 1.3.6.1.4.1.7777.1.4.10
		dpmLoadBlockDemandforFullMonthInKW OBJECT-TYPE
			SYNTAX Integer32
			MAX-ACCESS read-only
			STATUS current
			DESCRIPTION
				"Load Block Demand for Full Month In kW."
			::= { dpmLoad 10 }

		
--    1.3.6.1.4.1.7777.1.2.2.11
-- 1.3.6.1.4.1.7777.1.4.11
-- 1.3.6.1.4.1.7777.1.4.11
		-- 1.3.6.1.4.1.7777.1.4.11
		dpmLoadBlockDemandforFullYear OBJECT-TYPE
			SYNTAX Integer32
			MAX-ACCESS read-only
			STATUS current
			DESCRIPTION
				"Load Block Demand for Full Year In kW."
			::= { dpmLoad 11 }

		
--    1.3.6.1.4.1.7777.1.2.2.12
-- 1.3.6.1.4.1.7777.1.4.12
-- 1.3.6.1.4.1.7777.1.4.12
		-- 1.3.6.1.4.1.7777.1.4.12
		dpmLoadCurrentThdA OBJECT-TYPE
			SYNTAX Integer32
			MAX-ACCESS read-only
			STATUS current
			DESCRIPTION
				"Load Phase A THD Current.In percentage "
			::= { dpmLoad 12 }

		
--    1.3.6.1.4.1.7777.1.2.2.13
-- 1.3.6.1.4.1.7777.1.4.13
-- 1.3.6.1.4.1.7777.1.4.13
		-- 1.3.6.1.4.1.7777.1.4.13
		dpmLoadCurrentThdB OBJECT-TYPE
			SYNTAX Integer32
			MAX-ACCESS read-only
			STATUS current
			DESCRIPTION
				"Load Phase B THD Current.In percentage"
			::= { dpmLoad 13 }

		
--    1.3.6.1.4.1.7777.1.2.2.14
-- 1.3.6.1.4.1.7777.1.4.14
-- 1.3.6.1.4.1.7777.1.4.14
		-- 1.3.6.1.4.1.7777.1.4.14
		dpmLoadCurrentThdC OBJECT-TYPE
			SYNTAX Integer32
			MAX-ACCESS read-only
			STATUS current
			DESCRIPTION
				"Load Phase C THD Current.In percentage"
			::= { dpmLoad 14 }

		
--    1.3.6.1.4.1.7777.1.2.2.15
-- 1.3.6.1.4.1.7777.1.4.15
-- 1.3.6.1.4.1.7777.1.4.15
		-- 1.3.6.1.4.1.7777.1.4.15
		dpmLoadVoltageThdA OBJECT-TYPE
			SYNTAX Integer32
			MAX-ACCESS read-only
			STATUS current
			DESCRIPTION
				"Load Phase A THD Voltage.In percentage"
			::= { dpmLoad 15 }

		
--    1.3.6.1.4.1.7777.1.2.2.16
-- 1.3.6.1.4.1.7777.1.4.16
-- 1.3.6.1.4.1.7777.1.4.16
		-- 1.3.6.1.4.1.7777.1.4.16
		dpmLoadVoltageThdB OBJECT-TYPE
			SYNTAX Integer32
			MAX-ACCESS read-only
			STATUS current
			DESCRIPTION
				"Load Phase B THD Voltage.In percentage"
			::= { dpmLoad 16 }

		
--    1.3.6.1.4.1.7777.1.2.2.17
-- 1.3.6.1.4.1.7777.1.4.17
-- 1.3.6.1.4.1.7777.1.4.17
		-- 1.3.6.1.4.1.7777.1.4.17
		dpmLoadVoltageThdC OBJECT-TYPE
			SYNTAX Integer32
			MAX-ACCESS read-only
			STATUS current
			DESCRIPTION
				"Load Phase C THD Voltage.In percentage"
			::= { dpmLoad 17 }

		
--    1.3.6.1.4.1.7777.1.2.2.18
-- 1.3.6.1.4.1.7777.1.4.18
-- 1.3.6.1.4.1.7777.1.4.18
		-- 1.3.6.1.4.1.7777.1.4.18
		dpmLoadVab OBJECT-TYPE
			SYNTAX Integer32
			MAX-ACCESS read-only
			STATUS current
			DESCRIPTION
				"Load Vab Volatage."
			::= { dpmLoad 18 }

		
--    1.3.6.1.4.1.7777.1.2.2.19
-- 1.3.6.1.4.1.7777.1.4.19
-- 1.3.6.1.4.1.7777.1.4.19
		-- 1.3.6.1.4.1.7777.1.4.19
		dpmLoadVbc OBJECT-TYPE
			SYNTAX Integer32
			MAX-ACCESS read-only
			STATUS current
			DESCRIPTION
				"Load Vbc Volatage."
			::= { dpmLoad 19 }

		
--    1.3.6.1.4.1.7777.1.2.2.20
-- 1.3.6.1.4.1.7777.1.4.20
-- 1.3.6.1.4.1.7777.1.4.20
		-- 1.3.6.1.4.1.7777.1.4.20
		dpmLoadVca OBJECT-TYPE
			SYNTAX Integer32
			MAX-ACCESS read-only
			STATUS current
			DESCRIPTION
				"Load Vca Volatage."
			::= { dpmLoad 20 }

		
--    1.3.6.1.4.1.7777.1.2.2.21
-- 1.3.6.1.4.1.7777.1.4.21
-- 1.3.6.1.4.1.7777.1.4.21
		-- 1.3.6.1.4.1.7777.1.4.21
		dpmLoadVolAverage OBJECT-TYPE
			SYNTAX Integer32
			MAX-ACCESS read-only
			STATUS current
			DESCRIPTION
				"Load Vol Average."
			::= { dpmLoad 21 }

		
--    1.3.6.1.4.1.7777.1.2.2.22
-- 1.3.6.1.4.1.7777.1.4.22
-- 1.3.6.1.4.1.7777.1.4.22
		-- 1.3.6.1.4.1.7777.1.4.22
		dpmLoadVolUnbal OBJECT-TYPE
			SYNTAX Integer32
			MAX-ACCESS read-only
			STATUS current
			DESCRIPTION
				"Load Vol Unbal."
			::= { dpmLoad 22 }

		
--    1.3.6.1.4.1.7777.1.2.2.23
-- 1.3.6.1.4.1.7777.1.4.23
-- 1.3.6.1.4.1.7777.1.4.23
		-- 1.3.6.1.4.1.7777.1.4.23
		dpmLoadVan OBJECT-TYPE
			SYNTAX Integer32
			MAX-ACCESS read-only
			STATUS current
			DESCRIPTION
				"Load Vol Van."
			::= { dpmLoad 23 }

		
--    1.3.6.1.4.1.7777.1.2.2.24
-- 1.3.6.1.4.1.7777.1.4.24
-- 1.3.6.1.4.1.7777.1.4.24
		-- 1.3.6.1.4.1.7777.1.4.24
		dpmLoadVbn OBJECT-TYPE
			SYNTAX Integer32
			MAX-ACCESS read-only
			STATUS current
			DESCRIPTION
				"Load Vbn.."
			::= { dpmLoad 24 }

		
--    1.3.6.1.4.1.7777.1.2.2.25
-- 1.3.6.1.4.1.7777.1.4.25
-- 1.3.6.1.4.1.7777.1.4.25
		-- 1.3.6.1.4.1.7777.1.4.25
		dpmLoadVcn OBJECT-TYPE
			SYNTAX Integer32
			MAX-ACCESS read-only
			STATUS current
			DESCRIPTION
				"Load Vcn. "
			::= { dpmLoad 25 }

		
--    1.3.6.1.4.1.7777.1.2.2.26
-- 1.3.6.1.4.1.7777.1.4.26
-- 1.3.6.1.4.1.7777.1.4.26
		-- 1.3.6.1.4.1.7777.1.4.26
		dpmLoadVavgneutral OBJECT-TYPE
			SYNTAX Integer32
			MAX-ACCESS read-only
			STATUS current
			DESCRIPTION
				"Load Avg neutral Volatagae."
			::= { dpmLoad 26 }

		
--    1.3.6.1.4.1.7777.1.2.2.27
-- 1.3.6.1.4.1.7777.1.4.27
-- 1.3.6.1.4.1.7777.1.4.27
		-- 1.3.6.1.4.1.7777.1.4.27
		dpmLoadFrequency OBJECT-TYPE
			SYNTAX Integer32
			MAX-ACCESS read-only
			STATUS current
			DESCRIPTION
				"Load Frequency."
			::= { dpmLoad 27 }

		
--    1.3.6.1.4.1.7777.1.2.2.28
-- 1.3.6.1.4.1.7777.1.4.28
-- 1.3.6.1.4.1.7777.1.4.28
		-- 1.3.6.1.4.1.7777.1.4.28
		dpmLoadPowerFactor OBJECT-TYPE
			SYNTAX Integer32
			MAX-ACCESS read-only
			STATUS current
			DESCRIPTION
				"Load Power factor."
			::= { dpmLoad 28 }

		
--    1.3.6.1.4.1.7777.1.2.2.29
-- 1.3.6.1.4.1.7777.1.4.29
-- 1.3.6.1.4.1.7777.1.4.29
		-- 1.3.6.1.4.1.7777.1.4.29
		dpmLoadCurPhaseA OBJECT-TYPE
			SYNTAX Integer32
			MAX-ACCESS read-only
			STATUS current
			DESCRIPTION
				"Load Phase A Current."
			::= { dpmLoad 29 }

		
--    1.3.6.1.4.1.7777.1.2.2.30
-- 1.3.6.1.4.1.7777.1.4.30
-- 1.3.6.1.4.1.7777.1.4.30
		-- 1.3.6.1.4.1.7777.1.4.30
		dpmLoadCurPhaseB OBJECT-TYPE
			SYNTAX Integer32
			MAX-ACCESS read-only
			STATUS current
			DESCRIPTION
				"Load Phase B Current."
			::= { dpmLoad 30 }

		
--    1.3.6.1.4.1.7777.1.2.2.31
-- 1.3.6.1.4.1.7777.1.4.31
-- 1.3.6.1.4.1.7777.1.4.31
		-- 1.3.6.1.4.1.7777.1.4.31
		dpmLoadCurPhaseC OBJECT-TYPE
			SYNTAX Integer32
			MAX-ACCESS read-only
			STATUS current
			DESCRIPTION
				"Load Phase C Current."
			::= { dpmLoad 31 }

		
--    1.3.6.1.4.1.7777.1.2.2.32
-- 1.3.6.1.4.1.7777.1.4.32
-- 1.3.6.1.4.1.7777.1.4.32
		-- 1.3.6.1.4.1.7777.1.4.32
		dpmLoadPhaseCurAvg OBJECT-TYPE
			SYNTAX Integer32
			MAX-ACCESS read-only
			STATUS current
			DESCRIPTION
				"Load Phase Current aVG."
			::= { dpmLoad 32 }

		
--    1.3.6.1.4.1.7777.1.2.2.33
-- 1.3.6.1.4.1.7777.1.4.33
-- 1.3.6.1.4.1.7777.1.4.33
		-- 1.3.6.1.4.1.7777.1.4.33
		dpmLoadPhaseCurUnbalancecePercentage OBJECT-TYPE
			SYNTAX Integer32
			MAX-ACCESS read-only
			STATUS current
			DESCRIPTION
				"Load Phase Cur Unbalancece Percentage."
			::= { dpmLoad 33 }

		
--    1.3.6.1.4.1.7777.1.2.2.34
-- 1.3.6.1.4.1.7777.1.4.34
-- 1.3.6.1.4.1.7777.1.4.34
		-- 1.3.6.1.4.1.7777.1.4.34
		dpmLoadRealTotalPower OBJECT-TYPE
			SYNTAX Integer32
			MAX-ACCESS read-only
			STATUS current
			DESCRIPTION
				"Load Real Total power factor."
			::= { dpmLoad 34 }

		
--    1.3.6.1.4.1.7777.1.2.2.35
-- 1.3.6.1.4.1.7777.1.4.35
-- 1.3.6.1.4.1.7777.1.4.35
		-- 1.3.6.1.4.1.7777.1.4.35
		dpmLoadReactiveTotalPower OBJECT-TYPE
			SYNTAX Integer32
			MAX-ACCESS read-only
			STATUS current
			DESCRIPTION
				"Load Reactive Total power."
			::= { dpmLoad 35 }

		
--    1.3.6.1.4.1.7777.1.2.2.36
-- 1.3.6.1.4.1.7777.1.4.36
-- 1.3.6.1.4.1.7777.1.4.36
		-- 1.3.6.1.4.1.7777.1.4.36
		dpmLoadApparentTotalPower OBJECT-TYPE
			SYNTAX Integer32
			MAX-ACCESS read-only
			STATUS current
			DESCRIPTION
				"Load Apparent Total power."
			::= { dpmLoad 36 }

		
--    1.3.6.1.4.1.7777.1.2.2.37
-- 1.3.6.1.4.1.7777.1.4.37
-- 1.3.6.1.4.1.7777.1.4.37
		-- 1.3.6.1.4.1.7777.1.4.37
		dpmLoadNetActiveEnergy OBJECT-TYPE
			SYNTAX Integer32
			MAX-ACCESS read-only
			STATUS current
			DESCRIPTION
				"Load Net Active Energy."
			::= { dpmLoad 37 }

		
--    1.3.6.1.4.1.7777.1.2.2.39
-- 1.3.6.1.4.1.7777.1.4.38
-- 1.3.6.1.4.1.7777.1.4.38
		-- 1.3.6.1.4.1.7777.1.4.38
		dpmLoadFirmwareVersion OBJECT-TYPE
			SYNTAX DisplayString (SIZE (0..128))
			MAX-ACCESS read-only
			STATUS current
			DESCRIPTION
				"Load DPM Firmware ."
			::= { dpmLoad 38 }

		
--   1.3.6.1.4.1.7777.1.4.39
-- 1.3.6.1.4.1.7777.1.4.39
		-- 1.3.6.1.4.1.7777.1.4.39
		dpmLoadActivePowerA OBJECT-TYPE
			SYNTAX Integer32
			MAX-ACCESS read-only
			STATUS current
			DESCRIPTION
				"Load Active Power phase A."
			::= { dpmLoad 39 }

		
--   1.3.6.1.4.1.7777.1.4.40
-- 1.3.6.1.4.1.7777.1.4.40
		-- 1.3.6.1.4.1.7777.1.4.40
		dpmLoadActivePowerB OBJECT-TYPE
			SYNTAX Integer32
			MAX-ACCESS read-only
			STATUS current
			DESCRIPTION
				"Load Active Power phase B."
			::= { dpmLoad 40 }

		
--   1.3.6.1.4.1.7777.1.4.41
-- 1.3.6.1.4.1.7777.1.4.41
		-- 1.3.6.1.4.1.7777.1.4.41
		dpmLoadActivePowerC OBJECT-TYPE
			SYNTAX Integer32
			MAX-ACCESS read-only
			STATUS current
			DESCRIPTION
				"Load Active Power phase C."
			::= { dpmLoad 41 }

		
--   1.3.6.1.4.1.7777.1.4.42
-- 1.3.6.1.4.1.7777.1.4.42
		-- 1.3.6.1.4.1.7777.1.4.42
		dpmLoadActivePowerTotal OBJECT-TYPE
			SYNTAX Integer32
			MAX-ACCESS read-only
			STATUS current
			DESCRIPTION
				"Load Active Power Total."
			::= { dpmLoad 42 }

		
--   1.3.6.1.4.1.7777.1.4.43
-- 1.3.6.1.4.1.7777.1.4.43
		-- 1.3.6.1.4.1.7777.1.4.43
		dpmLoadReactivePowerA OBJECT-TYPE
			SYNTAX Integer32
			MAX-ACCESS read-only
			STATUS current
			DESCRIPTION
				"Load Reactive Power phase A."
			::= { dpmLoad 43 }

		
--   1.3.6.1.4.1.7777.1.4.44
-- 1.3.6.1.4.1.7777.1.4.44
		-- 1.3.6.1.4.1.7777.1.4.44
		dpmLoadReactivePowerB OBJECT-TYPE
			SYNTAX Integer32
			MAX-ACCESS read-only
			STATUS current
			DESCRIPTION
				"Load Reactive Power phase B."
			::= { dpmLoad 44 }

		
--   1.3.6.1.4.1.7777.1.4.45
-- 1.3.6.1.4.1.7777.1.4.45
		-- 1.3.6.1.4.1.7777.1.4.45
		dpmLoadReactivePowerC OBJECT-TYPE
			SYNTAX Integer32
			MAX-ACCESS read-only
			STATUS current
			DESCRIPTION
				"Load Reactive Power phase C."
			::= { dpmLoad 45 }

		
--   1.3.6.1.4.1.7777.1.4.46
-- 1.3.6.1.4.1.7777.1.4.46
		-- 1.3.6.1.4.1.7777.1.4.46
		dpmLoadReactivePowerTotal OBJECT-TYPE
			SYNTAX Integer32
			MAX-ACCESS read-only
			STATUS current
			DESCRIPTION
				"Load Reactive Power Total."
			::= { dpmLoad 46 }

		
--   1.3.6.1.4.1.7777.1.4.47
-- 1.3.6.1.4.1.7777.1.4.47
		-- 1.3.6.1.4.1.7777.1.4.47
		dpmLoadPowerFactorA OBJECT-TYPE
			SYNTAX Integer32
			MAX-ACCESS read-only
			STATUS current
			DESCRIPTION
				"Load Reactive Power phase A."
			::= { dpmLoad 47 }

		
--   1.3.6.1.4.1.7777.1.4.48
-- 1.3.6.1.4.1.7777.1.4.48
		-- 1.3.6.1.4.1.7777.1.4.48
		dpmLoadPowerFactorB OBJECT-TYPE
			SYNTAX Integer32
			MAX-ACCESS read-only
			STATUS current
			DESCRIPTION
				"Load Reactive Power phase B."
			::= { dpmLoad 48 }

		
--   1.3.6.1.4.1.7777.1.4.49
-- 1.3.6.1.4.1.7777.1.4.49
		-- 1.3.6.1.4.1.7777.1.4.49
		dpmLoadPowerFactorC OBJECT-TYPE
			SYNTAX Integer32
			MAX-ACCESS read-only
			STATUS current
			DESCRIPTION
				"Load Reactive Power phase B."
			::= { dpmLoad 49 }

		
--   1.3.6.1.4.1.7777.1.4.50
-- 1.3.6.1.4.1.7777.1.4.50
		-- 1.3.6.1.4.1.7777.1.4.50
		dpmLoadPowerFactorTotal OBJECT-TYPE
			SYNTAX Integer32
			MAX-ACCESS read-only
			STATUS current
			DESCRIPTION
				"Load Reactive Power Total."
			::= { dpmLoad 50 }

		
--   1.3.6.1.4.1.7777.1.4.51
-- 1.3.6.1.4.1.7777.1.4.51
		-- 1.3.6.1.4.1.7777.1.4.51
		dpmLoadVoltAmperePowerA OBJECT-TYPE
			SYNTAX Integer32
			MAX-ACCESS read-only
			STATUS current
			DESCRIPTION
				"Load volt-ampere Power phase A."
			::= { dpmLoad 51 }

		
--   1.3.6.1.4.1.7777.1.4.52
-- 1.3.6.1.4.1.7777.1.4.52
		-- 1.3.6.1.4.1.7777.1.4.52
		dpmLoadVoltAmperePowerB OBJECT-TYPE
			SYNTAX Integer32
			MAX-ACCESS read-only
			STATUS current
			DESCRIPTION
				"Load volt-ampere Power phase B."
			::= { dpmLoad 52 }

		
--   1.3.6.1.4.1.7777.1.4.53
-- 1.3.6.1.4.1.7777.1.4.53
		-- 1.3.6.1.4.1.7777.1.4.53
		dpmLoadVoltAmperePowerC OBJECT-TYPE
			SYNTAX Integer32
			MAX-ACCESS read-only
			STATUS current
			DESCRIPTION
				"Load volt-ampere Power phase C."
			::= { dpmLoad 53 }

		
--   1.3.6.1.4.1.7777.1.4.54
-- 1.3.6.1.4.1.7777.1.4.54
		-- 1.3.6.1.4.1.7777.1.4.54
		dpmLoadVoltAmperePowerTotal OBJECT-TYPE
			SYNTAX Integer32
			MAX-ACCESS read-only
			STATUS current
			DESCRIPTION
				"Load volt-ampere Power Total."
			::= { dpmLoad 54 }

		
--   1.3.6.1.4.1.7777.1.4.55
-- 1.3.6.1.4.1.7777.1.4.55
		-- 1.3.6.1.4.1.7777.1.4.55
		dpmLoadMaxWattDemand OBJECT-TYPE
			SYNTAX Integer32
			MAX-ACCESS read-only
			STATUS current
			DESCRIPTION
				"Load Maximum Watt Demand."
			::= { dpmLoad 55 }

		
--   1.3.6.1.4.1.7777.1.4.56
-- 1.3.6.1.4.1.7777.1.4.56
		-- 1.3.6.1.4.1.7777.1.4.56
		dpmLoadNORMALKWHNet OBJECT-TYPE
			SYNTAX Integer32
			MAX-ACCESS read-only
			STATUS current
			DESCRIPTION
				"Load NORMAL kWH Net."
			::= { dpmLoad 56 }

		
--   1.3.6.1.4.1.7777.1.4.57
-- 1.3.6.1.4.1.7777.1.4.57
		-- 1.3.6.1.4.1.7777.1.4.57
		dpmLoadNORMALKVARHNet OBJECT-TYPE
			SYNTAX Integer32
			MAX-ACCESS read-only
			STATUS current
			DESCRIPTION
				"Load NORMAL kVarH Net."
			::= { dpmLoad 57 }

		
--   1.3.6.1.4.1.7777.1.4.58
-- 1.3.6.1.4.1.7777.1.4.58
		-- 1.3.6.1.4.1.7777.1.4.58
		dpmLoadNORMALKVAHNet OBJECT-TYPE
			SYNTAX Integer32
			MAX-ACCESS read-only
			STATUS current
			DESCRIPTION
				"Load NORMAL kVaH Net."
			::= { dpmLoad 58 }

		
--   1.3.6.1.4.1.7777.1.4.59
-- 1.3.6.1.4.1.7777.1.4.59
		-- 1.3.6.1.4.1.7777.1.4.59
		dpmLoadEMERGKWHNet OBJECT-TYPE
			SYNTAX Integer32
			MAX-ACCESS read-only
			STATUS current
			DESCRIPTION
				"Load EMERGENCY kWH Net."
			::= { dpmLoad 59 }

		
--   1.3.6.1.4.1.7777.1.4.60
-- 1.3.6.1.4.1.7777.1.4.60
		-- 1.3.6.1.4.1.7777.1.4.60
		dpmLoadEMERGKVARHNet OBJECT-TYPE
			SYNTAX Integer32
			MAX-ACCESS read-only
			STATUS current
			DESCRIPTION
				"Load EMERGENCY kVarH Net."
			::= { dpmLoad 60 }

		
--   1.3.6.1.4.1.7777.1.4.61
-- 1.3.6.1.4.1.7777.1.4.61
		-- 1.3.6.1.4.1.7777.1.4.61
		dpmLoadEMERGKVAHNet OBJECT-TYPE
			SYNTAX Integer32
			MAX-ACCESS read-only
			STATUS current
			DESCRIPTION
				"Load EMERGENCY kVaH Net."
			::= { dpmLoad 61 }

		
--   1.3.6.1.4.1.7777.1.4.62
-- 1.3.6.1.4.1.7777.1.4.62
		-- 1.3.6.1.4.1.7777.1.4.62
		dpmLoadNORMALMinTotalActivePower OBJECT-TYPE
			SYNTAX Integer32
			MAX-ACCESS read-only
			STATUS current
			DESCRIPTION
				"Load NORMAL Minimum Total Active Power."
			::= { dpmLoad 62 }

		
--   1.3.6.1.4.1.7777.1.4.63
-- 1.3.6.1.4.1.7777.1.4.63
		-- 1.3.6.1.4.1.7777.1.4.63
		dpmLoadNORMALMaxTotalActivePower OBJECT-TYPE
			SYNTAX Integer32
			MAX-ACCESS read-only
			STATUS current
			DESCRIPTION
				"Load NORMAL Maximum Total Active Power."
			::= { dpmLoad 63 }

		
--   1.3.6.1.4.1.7777.1.4.64
-- 1.3.6.1.4.1.7777.1.4.64
		-- 1.3.6.1.4.1.7777.1.4.64
		dpmLoadNORMALMinTotalReactivePower OBJECT-TYPE
			SYNTAX Integer32
			MAX-ACCESS read-only
			STATUS current
			DESCRIPTION
				"Load NORMAL Minimum Total Reactive  Power."
			::= { dpmLoad 64 }

		
--   1.3.6.1.4.1.7777.1.4.65
-- 1.3.6.1.4.1.7777.1.4.65
		-- 1.3.6.1.4.1.7777.1.4.65
		dpmLoadNORMALMaxTotalReactivePower OBJECT-TYPE
			SYNTAX Integer32
			MAX-ACCESS read-only
			STATUS current
			DESCRIPTION
				"Load NORMAL Maximum Total Reactive Power."
			::= { dpmLoad 65 }

		
--   1.3.6.1.4.1.7777.1.4.66
-- 1.3.6.1.4.1.7777.1.4.66
		-- 1.3.6.1.4.1.7777.1.4.66
		dpmLoadNORMALMinTotalApparentPower OBJECT-TYPE
			SYNTAX Integer32
			MAX-ACCESS read-only
			STATUS current
			DESCRIPTION
				"Load NORMAL Minimum Total Apparent Power."
			::= { dpmLoad 66 }

		
--   1.3.6.1.4.1.7777.1.4.67
-- 1.3.6.1.4.1.7777.1.4.67
		-- 1.3.6.1.4.1.7777.1.4.67
		dpmLoadNORMALMaxTotalApparentPower OBJECT-TYPE
			SYNTAX Integer32
			MAX-ACCESS read-only
			STATUS current
			DESCRIPTION
				"Load NORMAL Maximum Total Apparent Power."
			::= { dpmLoad 67 }

		
--   1.3.6.1.4.1.7777.1.4.68
-- 1.3.6.1.4.1.7777.1.4.68
		-- 1.3.6.1.4.1.7777.1.4.68
		dpmLoadEMERGMinTotalActivePower OBJECT-TYPE
			SYNTAX Integer32
			MAX-ACCESS read-only
			STATUS current
			DESCRIPTION
				"Load EMERGENCY Minimum Total Active Power."
			::= { dpmLoad 68 }

		
--   1.3.6.1.4.1.7777.1.4.69
-- 1.3.6.1.4.1.7777.1.4.69
		-- 1.3.6.1.4.1.7777.1.4.69
		dpmLoadEMERGMaxTotalActivePower OBJECT-TYPE
			SYNTAX Integer32
			MAX-ACCESS read-only
			STATUS current
			DESCRIPTION
				"Load EMERGENCY Maximum Total Active Power."
			::= { dpmLoad 69 }

		
--   1.3.6.1.4.1.7777.1.4.70
-- 1.3.6.1.4.1.7777.1.4.70
		-- 1.3.6.1.4.1.7777.1.4.70
		dpmLoadEMERGMinTotalReactivePower OBJECT-TYPE
			SYNTAX Integer32
			MAX-ACCESS read-only
			STATUS current
			DESCRIPTION
				"Load EMERGENCY Minimum Total Reactive  Power."
			::= { dpmLoad 70 }

		
--   1.3.6.1.4.1.7777.1.4.71
-- 1.3.6.1.4.1.7777.1.4.71
		-- 1.3.6.1.4.1.7777.1.4.71
		dpmLoadEMERGMaxTotalReactivePower OBJECT-TYPE
			SYNTAX Integer32
			MAX-ACCESS read-only
			STATUS current
			DESCRIPTION
				"Load EMERGENCY Maximum Total Reactive Power."
			::= { dpmLoad 71 }

		
--   1.3.6.1.4.1.7777.1.4.72
-- 1.3.6.1.4.1.7777.1.4.72
		-- 1.3.6.1.4.1.7777.1.4.72
		dpmLoadEMERGMinTotalApparentPower OBJECT-TYPE
			SYNTAX Integer32
			MAX-ACCESS read-only
			STATUS current
			DESCRIPTION
				"Load EMERGENCY Minimum Total Apparent Power."
			::= { dpmLoad 72 }

		
--   1.3.6.1.4.1.7777.1.4.73
-- 1.3.6.1.4.1.7777.1.4.73
		-- 1.3.6.1.4.1.7777.1.4.73
		dpmLoadEMERGMaxTotalApparentPower OBJECT-TYPE
			SYNTAX Integer32
			MAX-ACCESS read-only
			STATUS current
			DESCRIPTION
				"Load EMERGENCY Maximum Total Apparent Power."
			::= { dpmLoad 73 }

		
--   1.3.6.1.4.1.7777.1.4.74
-- 1.3.6.1.4.1.7777.1.4.74
		-- 1.3.6.1.4.1.7777.1.4.74
		dpmLoadCurrentMonthMaxDemand OBJECT-TYPE
			SYNTAX Integer32
			MAX-ACCESS read-only
			STATUS current
			DESCRIPTION
				"Load Current Month Maximum Demand."
			::= { dpmLoad 74 }

		
--   1.3.6.1.4.1.7777.1.4.75
-- 1.3.6.1.4.1.7777.1.4.75
		-- 1.3.6.1.4.1.7777.1.4.75
		dpmLoadMostRecentMonthMaxDemand OBJECT-TYPE
			SYNTAX Integer32
			MAX-ACCESS read-write
			STATUS current
			DESCRIPTION
				"Load Most Recent Month Max Demand."
			::= { dpmLoad 75 }

		
--   1.3.6.1.4.1.7777.1.4.76
-- 1.3.6.1.4.1.7777.1.4.76
		-- 1.3.6.1.4.1.7777.1.4.76
		dpmLoad2ndRecentMonthMaxDemand OBJECT-TYPE
			SYNTAX Integer32
			MAX-ACCESS read-only
			STATUS current
			DESCRIPTION
				"Load 2nd Most Recent Month Max Demand."
			::= { dpmLoad 76 }

		
--   1.3.6.1.4.1.7777.1.4.77
-- 1.3.6.1.4.1.7777.1.4.77
		-- 1.3.6.1.4.1.7777.1.4.77
		dpmLoad3rdRecentMonthMaxDemand OBJECT-TYPE
			SYNTAX Integer32
			MAX-ACCESS read-only
			STATUS current
			DESCRIPTION
				"Load 3rd Most Recent Month Max Demand."
			::= { dpmLoad 77 }

		
--   1.3.6.1.4.1.7777.1.4.78
-- 1.3.6.1.4.1.7777.1.4.78
		-- 1.3.6.1.4.1.7777.1.4.78
		dpmLoad4thRecentMonthMaxDemand OBJECT-TYPE
			SYNTAX Integer32
			MAX-ACCESS read-only
			STATUS current
			DESCRIPTION
				"Load 4th Most Recent Month Max Demand."
			::= { dpmLoad 78 }

		
--   1.3.6.1.4.1.7777.1.4.79
-- 1.3.6.1.4.1.7777.1.4.79
		-- 1.3.6.1.4.1.7777.1.4.79
		dpmLoad5thRecentMonthMaxDemand OBJECT-TYPE
			SYNTAX Integer32
			MAX-ACCESS read-only
			STATUS current
			DESCRIPTION
				"Load 5th Most Recent Month Max Demand."
			::= { dpmLoad 79 }

		
--   1.3.6.1.4.1.7777.1.4.80
-- 1.3.6.1.4.1.7777.1.4.80
		-- 1.3.6.1.4.1.7777.1.4.80
		dpmLoad6thRecentMonthMaxDemand OBJECT-TYPE
			SYNTAX Integer32
			MAX-ACCESS read-only
			STATUS current
			DESCRIPTION
				"Load 6th Most Recent Month Max Demand."
			::= { dpmLoad 80 }

		
--   1.3.6.1.4.1.7777.1.4.81
-- 1.3.6.1.4.1.7777.1.4.81
		-- 1.3.6.1.4.1.7777.1.4.81
		dpmLoad7thRecentMonthMaxDemand OBJECT-TYPE
			SYNTAX Integer32
			MAX-ACCESS read-only
			STATUS current
			DESCRIPTION
				"Load 7th Most Recent Month Max Demand."
			::= { dpmLoad 81 }

		
--   1.3.6.1.4.1.7777.1.4.82
-- 1.3.6.1.4.1.7777.1.4.82
		-- 1.3.6.1.4.1.7777.1.4.82
		dpmLoad8thRecentMonthMaxDemand OBJECT-TYPE
			SYNTAX Integer32
			MAX-ACCESS read-only
			STATUS current
			DESCRIPTION
				"Load 8th Most Recent Month Max Demand."
			::= { dpmLoad 82 }

		
--   1.3.6.1.4.1.7777.1.4.83
-- 1.3.6.1.4.1.7777.1.4.83
		-- 1.3.6.1.4.1.7777.1.4.83
		dpmLoad9thRecentMonthMaxDemand OBJECT-TYPE
			SYNTAX Integer32
			MAX-ACCESS read-only
			STATUS current
			DESCRIPTION
				"Load 9th Most Recent Month Max Demand."
			::= { dpmLoad 83 }

		
--   1.3.6.1.4.1.7777.1.4.84
-- 1.3.6.1.4.1.7777.1.4.84
		-- 1.3.6.1.4.1.7777.1.4.84
		dpmLoad10thRecentMonthMaxDemand OBJECT-TYPE
			SYNTAX Integer32
			MAX-ACCESS read-only
			STATUS current
			DESCRIPTION
				"Load 10th Most Recent Month Max Demand."
			::= { dpmLoad 84 }

		
--   1.3.6.1.4.1.7777.1.4.85
-- 1.3.6.1.4.1.7777.1.4.85
		-- 1.3.6.1.4.1.7777.1.4.85
		dpmLoad11thRecentMonthMaxDemand OBJECT-TYPE
			SYNTAX Integer32
			MAX-ACCESS read-only
			STATUS current
			DESCRIPTION
				"Load 11th Most Recent Month Max Demand."
			::= { dpmLoad 85 }

		
--   1.3.6.1.4.1.7777.1.4.86
-- 1.3.6.1.4.1.7777.1.4.86
		-- 1.3.6.1.4.1.7777.1.4.86
		dpmLoad12thRecentMonthMaxDemand OBJECT-TYPE
			SYNTAX Integer32
			MAX-ACCESS read-only
			STATUS current
			DESCRIPTION
				"Load 12th Most Recent Month Max Demand."
			::= { dpmLoad 86 }

		
--   1.3.6.1.4.1.7777.1.4.87
-- 1.3.6.1.4.1.7777.1.4.87
		-- 1.3.6.1.4.1.7777.1.4.87
		dpmLoad13thRecentMonthMaxDemand OBJECT-TYPE
			SYNTAX Integer32
			MAX-ACCESS read-only
			STATUS current
			DESCRIPTION
				"Load 13th Most Recent Month Max Demand."
			::= { dpmLoad 87 }

		
--   1.3.6.1.4.1.7777.1.4.88
-- 1.3.6.1.4.1.7777.1.4.88
		-- 1.3.6.1.4.1.7777.1.4.88
		dpmLoad14thRecentMonthMaxDemand OBJECT-TYPE
			SYNTAX Integer32
			MAX-ACCESS read-only
			STATUS current
			DESCRIPTION
				"Load 14th Most Recent Month Max Demand."
			::= { dpmLoad 88 }

		
--   1.3.6.1.4.1.7777.1.4.89
-- 1.3.6.1.4.1.7777.1.4.89
		-- 1.3.6.1.4.1.7777.1.4.89
		dpmLoad15thRecentMonthMaxDemand OBJECT-TYPE
			SYNTAX Integer32
			MAX-ACCESS read-only
			STATUS current
			DESCRIPTION
				"Load 15th Most Recent Month Max Demand."
			::= { dpmLoad 89 }

		
--   1.3.6.1.4.1.7777.1.4.90
-- 1.3.6.1.4.1.7777.1.4.90
		-- 1.3.6.1.4.1.7777.1.4.90
		dpmLoad16thRecentMonthMaxDemand OBJECT-TYPE
			SYNTAX Integer32
			MAX-ACCESS read-only
			STATUS current
			DESCRIPTION
				"Load 16th Most Recent Month Max Demand."
			::= { dpmLoad 90 }

		
--   1.3.6.1.4.1.7777.1.4.91
-- 1.3.6.1.4.1.7777.1.4.91
		-- 1.3.6.1.4.1.7777.1.4.91
		dpmLoad17thRecentMonthMaxDemand OBJECT-TYPE
			SYNTAX Integer32
			MAX-ACCESS read-only
			STATUS current
			DESCRIPTION
				"Load 17th Most Recent Month Max Demand."
			::= { dpmLoad 91 }

		
--   1.3.6.1.4.1.7777.1.4.92
-- 1.3.6.1.4.1.7777.1.4.92
		-- 1.3.6.1.4.1.7777.1.4.92
		dpmLoad18thRecentMonthMaxDemand OBJECT-TYPE
			SYNTAX Integer32
			MAX-ACCESS read-only
			STATUS current
			DESCRIPTION
				"Load 18th Most Recent Month Max Demand."
			::= { dpmLoad 92 }

		
--   1.3.6.1.4.1.7777.1.4.93
-- 1.3.6.1.4.1.7777.1.4.93
		-- 1.3.6.1.4.1.7777.1.4.93
		dpmLoad19thRecentMonthMaxDemand OBJECT-TYPE
			SYNTAX Integer32
			MAX-ACCESS read-only
			STATUS current
			DESCRIPTION
				"Load 19th Most Recent Month Max Demand."
			::= { dpmLoad 93 }

		
--   1.3.6.1.4.1.7777.1.4.94
-- 1.3.6.1.4.1.7777.1.4.94
		-- 1.3.6.1.4.1.7777.1.4.94
		dpmLoad20thRecentMonthMaxDemand OBJECT-TYPE
			SYNTAX Integer32
			MAX-ACCESS read-only
			STATUS current
			DESCRIPTION
				"Load 20th Most Recent Month Max Demand."
			::= { dpmLoad 94 }

		
--   1.3.6.1.4.1.7777.1.4.95
-- 1.3.6.1.4.1.7777.1.4.95
		-- 1.3.6.1.4.1.7777.1.4.95
		dpmLoad21stRecentMonthMaxDemand OBJECT-TYPE
			SYNTAX Integer32
			MAX-ACCESS read-only
			STATUS current
			DESCRIPTION
				"Load 21st Most Recent Month Max Demand."
			::= { dpmLoad 95 }

		
--   1.3.6.1.4.1.7777.1.4.96
-- 1.3.6.1.4.1.7777.1.4.96
		-- 1.3.6.1.4.1.7777.1.4.96
		dpmLoad22ndRecentMonthMaxDemand OBJECT-TYPE
			SYNTAX Integer32
			MAX-ACCESS read-only
			STATUS current
			DESCRIPTION
				"Load 22nd Most Recent Month Max Demand."
			::= { dpmLoad 96 }

		
--   1.3.6.1.4.1.7777.1.4.97
-- 1.3.6.1.4.1.7777.1.4.97
		-- 1.3.6.1.4.1.7777.1.4.97
		dpmLoad23rdRecentMonthMaxDemand OBJECT-TYPE
			SYNTAX Integer32
			MAX-ACCESS read-only
			STATUS current
			DESCRIPTION
				"Load 23rd Most Recent Month Max Demand."
			::= { dpmLoad 97 }

		
--   1.3.6.1.4.1.7777.1.4.98
-- 1.3.6.1.4.1.7777.1.4.98
		-- 1.3.6.1.4.1.7777.1.4.98
		dpmLoad24thRecentMonthMaxDemand OBJECT-TYPE
			SYNTAX Integer32
			MAX-ACCESS read-only
			STATUS current
			DESCRIPTION
				"Load 24th Most Recent Month Max Demand."
			::= { dpmLoad 98 }

		
--   1.3.6.1.4.1.7777.1.4.99
-- 1.3.6.1.4.1.7777.1.4.99
		-- 1.3.6.1.4.1.7777.1.4.99
		dpmLoadMainAndAuxilliaryPositions OBJECT-TYPE
			SYNTAX Integer32
			MAX-ACCESS read-only
			STATUS current
			DESCRIPTION
				"Load Main & Auxiliary Switch positions."
			::= { dpmLoad 99 }

		
--   1.3.6.1.4.1.7777.1.4.100
-- 1.3.6.1.4.1.7777.1.4.100
		-- 1.3.6.1.4.1.7777.1.4.100
		dpmLoadResettableEngineRunCounter OBJECT-TYPE
			SYNTAX Integer32
			MAX-ACCESS read-only
			STATUS current
			DESCRIPTION
				"Load Resettable Engine Runtime counter in Hours."
			::= { dpmLoad 100 }

		
--   1.3.6.1.4.1.7777.1.4.101
-- 1.3.6.1.4.1.7777.1.4.101
		-- 1.3.6.1.4.1.7777.1.4.101
		dpmLoadCumulativeEngineRunCounter OBJECT-TYPE
			SYNTAX Integer32
			MAX-ACCESS read-only
			STATUS current
			DESCRIPTION
				"Load Cumulative Engine Runtime counter in Hours."
			::= { dpmLoad 101 }

		
--   1.3.6.1.4.1.7777.1.5
-- 1.3.6.1.4.1.7777.1.5
		-- 1.3.6.1.4.1.7777.1.5
		dpmOther OBJECT IDENTIFIER ::= { device 5 }

		
--    transfer switch end
-- 1.3.6.1.4.1.7777.1.2.2.1
-- 1.3.6.1.4.1.7777.1.5.1
-- 1.3.6.1.4.1.7777.1.5.1
		-- 1.3.6.1.4.1.7777.1.5.1
		dpmOtherDPMName OBJECT-TYPE
			SYNTAX DisplayString (SIZE (0..128))
			MAX-ACCESS read-only
			STATUS current
			DESCRIPTION
				"Other DPM name."
			::= { dpmOther 1 }

		
--    1.3.6.1.4.1.7777.1.2.2.2
-- 1.3.6.1.4.1.7777.1.5.2
-- 1.3.6.1.4.1.7777.1.5.2
		-- 1.3.6.1.4.1.7777.1.5.2
		dpmOtherDPMLoca OBJECT-TYPE
			SYNTAX DisplayString (SIZE (0..128))
			MAX-ACCESS read-only
			STATUS current
			DESCRIPTION
				"Other DPM Location."
			::= { dpmOther 2 }

		
--    1.3.6.1.4.1.7777.1.2.2.3
-- 1.3.6.1.4.1.7777.1.5.3
-- 1.3.6.1.4.1.7777.1.5.3
		-- 1.3.6.1.4.1.7777.1.5.3
		dpmOtherNominalVoltage OBJECT-TYPE
			SYNTAX Integer32
			MAX-ACCESS read-only
			STATUS current
			DESCRIPTION
				"Other Nominal Voltage."
			::= { dpmOther 3 }

		
--    1.3.6.1.4.1.7777.1.2.2.4
-- 1.3.6.1.4.1.7777.1.5.4
-- 1.3.6.1.4.1.7777.1.5.4
		-- 1.3.6.1.4.1.7777.1.5.4
		dpmOtherNominalCurrent OBJECT-TYPE
			SYNTAX Integer32
			MAX-ACCESS read-only
			STATUS current
			DESCRIPTION
				"Other Nominal Current."
			::= { dpmOther 4 }

		
--    1.3.6.1.4.1.7777.1.2.2.5
-- 1.3.6.1.4.1.7777.1.5.5
-- 1.3.6.1.4.1.7777.1.5.5
		-- 1.3.6.1.4.1.7777.1.5.5
		dpmOtherInstantaneousDemandKwMW OBJECT-TYPE
			SYNTAX Integer32
			MAX-ACCESS read-only
			STATUS current
			DESCRIPTION
				"Other Instantaneous Demand kW MW"
			::= { dpmOther 5 }

		
--    1.3.6.1.4.1.7777.1.2.2.6
-- 1.3.6.1.4.1.7777.1.5.6
-- 1.3.6.1.4.1.7777.1.5.6
		-- 1.3.6.1.4.1.7777.1.5.6
		dpmOtherInstantaneousDemandDate OBJECT-TYPE
			SYNTAX DisplayString (SIZE (0..128))
			MAX-ACCESS read-only
			STATUS current
			DESCRIPTION
				"Other Demand Date."
			::= { dpmOther 6 }

		
--    1.3.6.1.4.1.7777.1.2.2.7
-- 1.3.6.1.4.1.7777.1.5.7
-- 1.3.6.1.4.1.7777.1.5.7
		-- 1.3.6.1.4.1.7777.1.5.7
		dpmOtherInstantaneousDemandTime OBJECT-TYPE
			SYNTAX DisplayString (SIZE (0..128))
			MAX-ACCESS read-only
			STATUS current
			DESCRIPTION
				"Other Demand Time."
			::= { dpmOther 7 }

		
--    1.3.6.1.4.1.7777.1.2.2.8
-- 1.3.6.1.4.1.7777.1.5.8
-- 1.3.6.1.4.1.7777.1.5.8
		-- 1.3.6.1.4.1.7777.1.5.8
		dpmOtherBlockDemandforFullHouInkW OBJECT-TYPE
			SYNTAX Integer32
			MAX-ACCESS read-only
			STATUS current
			DESCRIPTION
				"Other Block Demand for Full Hou In kW."
			::= { dpmOther 8 }

		
--    1.3.6.1.4.1.7777.1.2.2.9
-- 1.3.6.1.4.1.7777.1.5.9
-- 1.3.6.1.4.1.7777.1.5.9
		-- 1.3.6.1.4.1.7777.1.5.9
		dpmOtherBlockDemandforFullDayInkW OBJECT-TYPE
			SYNTAX Integer32
			MAX-ACCESS read-only
			STATUS current
			DESCRIPTION
				"Other Block Demand for Full Day In kW."
			::= { dpmOther 9 }

		
--    1.3.6.1.4.1.7777.1.2.2.10
-- 1.3.6.1.4.1.7777.1.5.10
-- 1.3.6.1.4.1.7777.1.5.10
		-- 1.3.6.1.4.1.7777.1.5.10
		dpmOtherBlockDemandforFullMonthInKW OBJECT-TYPE
			SYNTAX Integer32
			MAX-ACCESS read-only
			STATUS current
			DESCRIPTION
				"Other Block Demand for Full Month In kW."
			::= { dpmOther 10 }

		
--    1.3.6.1.4.1.7777.1.2.2.11
-- 1.3.6.1.4.1.7777.1.5.11
-- 1.3.6.1.4.1.7777.1.5.11
		-- 1.3.6.1.4.1.7777.1.5.11
		dpmOtherBlockDemandforFullYear OBJECT-TYPE
			SYNTAX Integer32
			MAX-ACCESS read-only
			STATUS current
			DESCRIPTION
				"Other Block Demand for Full Year In kW."
			::= { dpmOther 11 }

		
--    1.3.6.1.4.1.7777.1.2.2.12
-- 1.3.6.1.4.1.7777.1.5.12
-- 1.3.6.1.4.1.7777.1.5.12
		-- 1.3.6.1.4.1.7777.1.5.12
		dpmOtherCurrentThdA OBJECT-TYPE
			SYNTAX Integer32
			MAX-ACCESS read-only
			STATUS current
			DESCRIPTION
				"Other Phase A THD Current.In percentage "
			::= { dpmOther 12 }

		
--    1.3.6.1.4.1.7777.1.2.2.13
-- 1.3.6.1.4.1.7777.1.5.13
-- 1.3.6.1.4.1.7777.1.5.13
		-- 1.3.6.1.4.1.7777.1.5.13
		dpmOtherCurrentThdB OBJECT-TYPE
			SYNTAX Integer32
			MAX-ACCESS read-only
			STATUS current
			DESCRIPTION
				"Other Phase B THD Current.In percentage"
			::= { dpmOther 13 }

		
--    1.3.6.1.4.1.7777.1.2.2.14
-- 1.3.6.1.4.1.7777.1.5.14
-- 1.3.6.1.4.1.7777.1.5.14
		-- 1.3.6.1.4.1.7777.1.5.14
		dpmOtherCurrentThdC OBJECT-TYPE
			SYNTAX Integer32
			MAX-ACCESS read-only
			STATUS current
			DESCRIPTION
				"Other Phase C THD Current.In percentage"
			::= { dpmOther 14 }

		
--    1.3.6.1.4.1.7777.1.2.2.15
-- 1.3.6.1.4.1.7777.1.5.15
-- 1.3.6.1.4.1.7777.1.5.15
		-- 1.3.6.1.4.1.7777.1.5.15
		dpmOtherVoltageThdA OBJECT-TYPE
			SYNTAX Integer32
			MAX-ACCESS read-only
			STATUS current
			DESCRIPTION
				"Other Phase A THD Voltage.In percentage"
			::= { dpmOther 15 }

		
--    1.3.6.1.4.1.7777.1.2.2.16
-- 1.3.6.1.4.1.7777.1.5.16
-- 1.3.6.1.4.1.7777.1.5.16
		-- 1.3.6.1.4.1.7777.1.5.16
		dpmOtherVoltageThdB OBJECT-TYPE
			SYNTAX Integer32
			MAX-ACCESS read-only
			STATUS current
			DESCRIPTION
				"Other Phase B THD Voltage.In percentage"
			::= { dpmOther 16 }

		
--    1.3.6.1.4.1.7777.1.2.2.17
-- 1.3.6.1.4.1.7777.1.5.17
-- 1.3.6.1.4.1.7777.1.5.17
		-- 1.3.6.1.4.1.7777.1.5.17
		dpmOtherVoltageThdC OBJECT-TYPE
			SYNTAX Integer32
			MAX-ACCESS read-only
			STATUS current
			DESCRIPTION
				"Other Phase C THD Voltage.In percentage"
			::= { dpmOther 17 }

		
--    1.3.6.1.4.1.7777.1.2.2.18
-- 1.3.6.1.4.1.7777.1.5.18
-- 1.3.6.1.4.1.7777.1.5.18
		-- 1.3.6.1.4.1.7777.1.5.18
		dpmOtherVab OBJECT-TYPE
			SYNTAX Integer32
			MAX-ACCESS read-only
			STATUS current
			DESCRIPTION
				"Other Vab Voltage."
			::= { dpmOther 18 }

		
--    1.3.6.1.4.1.7777.1.2.2.19
-- 1.3.6.1.4.1.7777.1.5.19
-- 1.3.6.1.4.1.7777.1.5.19
		-- 1.3.6.1.4.1.7777.1.5.19
		dpmOtherVbc OBJECT-TYPE
			SYNTAX Integer32
			MAX-ACCESS read-only
			STATUS current
			DESCRIPTION
				"Other Vbc Voltage."
			::= { dpmOther 19 }

		
--    1.3.6.1.4.1.7777.1.2.2.20
-- 1.3.6.1.4.1.7777.1.5.20
-- 1.3.6.1.4.1.7777.1.5.20
		-- 1.3.6.1.4.1.7777.1.5.20
		dpmOtherVca OBJECT-TYPE
			SYNTAX Integer32
			MAX-ACCESS read-only
			STATUS current
			DESCRIPTION
				"Other Vca Voltage."
			::= { dpmOther 20 }

		
--    1.3.6.1.4.1.7777.1.2.2.21
-- 1.3.6.1.4.1.7777.1.5.21
-- 1.3.6.1.4.1.7777.1.5.21
		-- 1.3.6.1.4.1.7777.1.5.21
		dpmOtherVolAverage OBJECT-TYPE
			SYNTAX Integer32
			MAX-ACCESS read-only
			STATUS current
			DESCRIPTION
				"Other Vol Average."
			::= { dpmOther 21 }

		
--    1.3.6.1.4.1.7777.1.2.2.22
-- 1.3.6.1.4.1.7777.1.5.22
-- 1.3.6.1.4.1.7777.1.5.22
		-- 1.3.6.1.4.1.7777.1.5.22
		dpmOtherVolUnbal OBJECT-TYPE
			SYNTAX Integer32
			MAX-ACCESS read-only
			STATUS current
			DESCRIPTION
				"Other Vol Unbal."
			::= { dpmOther 22 }

		
--    1.3.6.1.4.1.7777.1.2.2.23
-- 1.3.6.1.4.1.7777.1.5.23
-- 1.3.6.1.4.1.7777.1.5.23
		-- 1.3.6.1.4.1.7777.1.5.23
		dpmOtherVan OBJECT-TYPE
			SYNTAX Integer32
			MAX-ACCESS read-only
			STATUS current
			DESCRIPTION
				"Other Vol Van."
			::= { dpmOther 23 }

		
--    1.3.6.1.4.1.7777.1.2.2.24
-- 1.3.6.1.4.1.7777.1.5.24
-- 1.3.6.1.4.1.7777.1.5.24
		-- 1.3.6.1.4.1.7777.1.5.24
		dpmOtherVbn OBJECT-TYPE
			SYNTAX Integer32
			MAX-ACCESS read-only
			STATUS current
			DESCRIPTION
				"Other Vbn."
			::= { dpmOther 24 }

		
--    1.3.6.1.4.1.7777.1.2.2.25
-- 1.3.6.1.4.1.7777.1.5.25
-- 1.3.6.1.4.1.7777.1.5.25
		-- 1.3.6.1.4.1.7777.1.5.25
		dpmOtherVcn OBJECT-TYPE
			SYNTAX Integer32
			MAX-ACCESS read-only
			STATUS current
			DESCRIPTION
				"Other Vcn. "
			::= { dpmOther 25 }

		
--    1.3.6.1.4.1.7777.1.2.2.26
-- 1.3.6.1.4.1.7777.1.5.26
-- 1.3.6.1.4.1.7777.1.5.26
		-- 1.3.6.1.4.1.7777.1.5.26
		dpmOtherVavgneutral OBJECT-TYPE
			SYNTAX Integer32
			MAX-ACCESS read-only
			STATUS current
			DESCRIPTION
				"Other Avg neutral Voltage."
			::= { dpmOther 26 }

		
--    1.3.6.1.4.1.7777.1.2.2.27
-- 1.3.6.1.4.1.7777.1.5.27
-- 1.3.6.1.4.1.7777.1.5.27
		-- 1.3.6.1.4.1.7777.1.5.27
		dpmOtherFrequency OBJECT-TYPE
			SYNTAX Integer32
			MAX-ACCESS read-only
			STATUS current
			DESCRIPTION
				"Other Frequency."
			::= { dpmOther 27 }

		
--    1.3.6.1.4.1.7777.1.2.2.28
-- 1.3.6.1.4.1.7777.1.5.28
-- 1.3.6.1.4.1.7777.1.5.28
		-- 1.3.6.1.4.1.7777.1.5.28
		dpmOtherPowerFactor OBJECT-TYPE
			SYNTAX Integer32
			MAX-ACCESS read-only
			STATUS current
			DESCRIPTION
				"Other Power factor."
			::= { dpmOther 28 }

		
--    1.3.6.1.4.1.7777.1.2.2.29
-- 1.3.6.1.4.1.7777.1.5.29
-- 1.3.6.1.4.1.7777.1.5.29
		-- 1.3.6.1.4.1.7777.1.5.29
		dpmOtherCurPhaseA OBJECT-TYPE
			SYNTAX Integer32
			MAX-ACCESS read-only
			STATUS current
			DESCRIPTION
				"Other Phase A Current."
			::= { dpmOther 29 }

		
--    1.3.6.1.4.1.7777.1.2.2.30
-- 1.3.6.1.4.1.7777.1.5.30
-- 1.3.6.1.4.1.7777.1.5.30
		-- 1.3.6.1.4.1.7777.1.5.30
		dpmOtherCurPhaseB OBJECT-TYPE
			SYNTAX Integer32
			MAX-ACCESS read-only
			STATUS current
			DESCRIPTION
				"Other Phase B Current."
			::= { dpmOther 30 }

		
--    1.3.6.1.4.1.7777.1.2.2.31
-- 1.3.6.1.4.1.7777.1.5.31
-- 1.3.6.1.4.1.7777.1.5.31
		-- 1.3.6.1.4.1.7777.1.5.31
		dpmOtherCurPhaseC OBJECT-TYPE
			SYNTAX Integer32
			MAX-ACCESS read-only
			STATUS current
			DESCRIPTION
				"Other Phase C Current."
			::= { dpmOther 31 }

		
--    1.3.6.1.4.1.7777.1.2.2.32
-- 1.3.6.1.4.1.7777.1.5.32
-- 1.3.6.1.4.1.7777.1.5.32
		-- 1.3.6.1.4.1.7777.1.5.32
		dpmOtherPhaseCurAvg OBJECT-TYPE
			SYNTAX Integer32
			MAX-ACCESS read-only
			STATUS current
			DESCRIPTION
				"Other Phase Current aVG."
			::= { dpmOther 32 }

		
--    1.3.6.1.4.1.7777.1.2.2.33
-- 1.3.6.1.4.1.7777.1.5.33
-- 1.3.6.1.4.1.7777.1.5.33
		-- 1.3.6.1.4.1.7777.1.5.33
		dpmOtherPhaseCurUnbalancecePercentage OBJECT-TYPE
			SYNTAX Integer32
			MAX-ACCESS read-only
			STATUS current
			DESCRIPTION
				"Other Phase Cur Unbalancece Percentage."
			::= { dpmOther 33 }

		
--    1.3.6.1.4.1.7777.1.2.2.34
-- 1.3.6.1.4.1.7777.1.5.34
-- 1.3.6.1.4.1.7777.1.5.34
		-- 1.3.6.1.4.1.7777.1.5.34
		dpmOtherRealTotalPower OBJECT-TYPE
			SYNTAX Integer32
			MAX-ACCESS read-only
			STATUS current
			DESCRIPTION
				"Other Real Total power factor."
			::= { dpmOther 34 }

		
--    1.3.6.1.4.1.7777.1.2.2.35
-- 1.3.6.1.4.1.7777.1.5.35
-- 1.3.6.1.4.1.7777.1.5.35
		-- 1.3.6.1.4.1.7777.1.5.35
		dpmOtherReactiveTotalPower OBJECT-TYPE
			SYNTAX Integer32
			MAX-ACCESS read-only
			STATUS current
			DESCRIPTION
				"Other Reactive Total power."
			::= { dpmOther 35 }

		
--    1.3.6.1.4.1.7777.1.2.2.36
-- 1.3.6.1.4.1.7777.1.5.36
-- 1.3.6.1.4.1.7777.1.5.36
		-- 1.3.6.1.4.1.7777.1.5.36
		dpmOtherApparentTotalPower OBJECT-TYPE
			SYNTAX Integer32
			MAX-ACCESS read-only
			STATUS current
			DESCRIPTION
				"Other AApparent Total power."
			::= { dpmOther 36 }

		
--    1.3.6.1.4.1.7777.1.2.2.37
-- 1.3.6.1.4.1.7777.1.5.37
-- 1.3.6.1.4.1.7777.1.5.37
		-- 1.3.6.1.4.1.7777.1.5.37
		dpmOtherNetActiveEnergy OBJECT-TYPE
			SYNTAX Integer32
			MAX-ACCESS read-only
			STATUS current
			DESCRIPTION
				"Other Net Active Energy."
			::= { dpmOther 37 }

		
--    1.3.6.1.4.1.7777.1.2.2.39
-- 1.3.6.1.4.1.7777.1.5.38
-- 1.3.6.1.4.1.7777.1.5.38
		-- 1.3.6.1.4.1.7777.1.5.38
		dpmOtherFirmwareVersion OBJECT-TYPE
			SYNTAX DisplayString (SIZE (0..128))
			MAX-ACCESS read-only
			STATUS current
			DESCRIPTION
				"Other DPM Firmware ."
			::= { dpmOther 38 }

		
--   1.3.6.1.4.1.7777.1.5.39
-- 1.3.6.1.4.1.7777.1.5.39
		-- 1.3.6.1.4.1.7777.1.5.39
		dpmOtherActivePowerA OBJECT-TYPE
			SYNTAX Integer32
			MAX-ACCESS read-only
			STATUS current
			DESCRIPTION
				"Other Active Power phase A."
			::= { dpmOther 39 }

		
--   1.3.6.1.4.1.7777.1.5.40
-- 1.3.6.1.4.1.7777.1.5.40
		-- 1.3.6.1.4.1.7777.1.5.40
		dpmOtherActivePowerB OBJECT-TYPE
			SYNTAX Integer32
			MAX-ACCESS read-only
			STATUS current
			DESCRIPTION
				"Other Active Power phase B."
			::= { dpmOther 40 }

		
--   1.3.6.1.4.1.7777.1.5.41
-- 1.3.6.1.4.1.7777.1.5.41
		-- 1.3.6.1.4.1.7777.1.5.41
		dpmOtherActivePowerC OBJECT-TYPE
			SYNTAX Integer32
			MAX-ACCESS read-only
			STATUS current
			DESCRIPTION
				"Other Active Power phase C."
			::= { dpmOther 41 }

		
--   1.3.6.1.4.1.7777.1.5.42
-- 1.3.6.1.4.1.7777.1.5.42
		-- 1.3.6.1.4.1.7777.1.5.42
		dpmOtherActivePowerTotal OBJECT-TYPE
			SYNTAX Integer32
			MAX-ACCESS read-only
			STATUS current
			DESCRIPTION
				"Other Active Power Total."
			::= { dpmOther 42 }

		
--   1.3.6.1.4.1.7777.1.5.43
-- 1.3.6.1.4.1.7777.1.5.43
		-- 1.3.6.1.4.1.7777.1.5.43
		dpmOtherReactivePowerA OBJECT-TYPE
			SYNTAX Integer32
			MAX-ACCESS read-only
			STATUS current
			DESCRIPTION
				"Other Reactive Power phase A."
			::= { dpmOther 43 }

		
--   1.3.6.1.4.1.7777.1.5.44
-- 1.3.6.1.4.1.7777.1.5.44
		-- 1.3.6.1.4.1.7777.1.5.44
		dpmOtherReactivePowerB OBJECT-TYPE
			SYNTAX Integer32
			MAX-ACCESS read-only
			STATUS current
			DESCRIPTION
				"Other Reactive Power phase B."
			::= { dpmOther 44 }

		
--   1.3.6.1.4.1.7777.1.5.45
-- 1.3.6.1.4.1.7777.1.5.45
		-- 1.3.6.1.4.1.7777.1.5.45
		dpmOtherReactivePowerC OBJECT-TYPE
			SYNTAX Integer32
			MAX-ACCESS read-only
			STATUS current
			DESCRIPTION
				"Other Reactive Power phase A."
			::= { dpmOther 45 }

		
--   1.3.6.1.4.1.7777.1.5.46
-- 1.3.6.1.4.1.7777.1.5.46
		-- 1.3.6.1.4.1.7777.1.5.46
		dpmOtherReactivePowerTotal OBJECT-TYPE
			SYNTAX Integer32
			MAX-ACCESS read-only
			STATUS current
			DESCRIPTION
				"Other Reactive Power Total."
			::= { dpmOther 46 }

		
--   1.3.6.1.4.1.7777.1.5.47
-- 1.3.6.1.4.1.7777.1.5.47
		-- 1.3.6.1.4.1.7777.1.5.47
		dpmOtherPowerFactorA OBJECT-TYPE
			SYNTAX Integer32
			MAX-ACCESS read-only
			STATUS current
			DESCRIPTION
				"Other Reactive Power phase A."
			::= { dpmOther 47 }

		
--   1.3.6.1.4.1.7777.1.5.48
-- 1.3.6.1.4.1.7777.1.5.48
		-- 1.3.6.1.4.1.7777.1.5.48
		dpmOtherPowerFactorB OBJECT-TYPE
			SYNTAX Integer32
			MAX-ACCESS read-only
			STATUS current
			DESCRIPTION
				"Other Reactive Power phase B."
			::= { dpmOther 48 }

		
--   1.3.6.1.4.1.7777.1.5.49
-- 1.3.6.1.4.1.7777.1.5.49
		-- 1.3.6.1.4.1.7777.1.5.49
		dpmOtherPowerFactorC OBJECT-TYPE
			SYNTAX Integer32
			MAX-ACCESS read-only
			STATUS current
			DESCRIPTION
				"Other Reactive Power phase C."
			::= { dpmOther 49 }

		
--   1.3.6.1.4.1.7777.1.5.50
-- 1.3.6.1.4.1.7777.1.5.50
		-- 1.3.6.1.4.1.7777.1.5.50
		dpmOtherPowerFactorTotal OBJECT-TYPE
			SYNTAX Integer32
			MAX-ACCESS read-only
			STATUS current
			DESCRIPTION
				"Other Reactive Power Total."
			::= { dpmOther 50 }

		
--   1.3.6.1.4.1.7777.1.5.51
-- 1.3.6.1.4.1.7777.1.5.51
		-- 1.3.6.1.4.1.7777.1.5.51
		dpmOtherVoltAmperePowerA OBJECT-TYPE
			SYNTAX Integer32
			MAX-ACCESS read-only
			STATUS current
			DESCRIPTION
				"Other volt-ampere Power phase A."
			::= { dpmOther 51 }

		
--   1.3.6.1.4.1.7777.1.5.52
-- 1.3.6.1.4.1.7777.1.5.52
		-- 1.3.6.1.4.1.7777.1.5.52
		dpmOtherVoltAmperePowerB OBJECT-TYPE
			SYNTAX Integer32
			MAX-ACCESS read-only
			STATUS current
			DESCRIPTION
				"Other volt-ampere Power phase B."
			::= { dpmOther 52 }

		
--   1.3.6.1.4.1.7777.1.5.53
-- 1.3.6.1.4.1.7777.1.5.53
		-- 1.3.6.1.4.1.7777.1.5.53
		dpmOtherVoltAmperePowerC OBJECT-TYPE
			SYNTAX Integer32
			MAX-ACCESS read-only
			STATUS current
			DESCRIPTION
				"Other volt-ampere Power phase C."
			::= { dpmOther 53 }

		
--   1.3.6.1.4.1.7777.1.5.54
-- 1.3.6.1.4.1.7777.1.5.54
		-- 1.3.6.1.4.1.7777.1.5.54
		dpmOtherVoltAmperePowerTotal OBJECT-TYPE
			SYNTAX Integer32
			MAX-ACCESS read-only
			STATUS current
			DESCRIPTION
				"Other volt-ampere Power Total."
			::= { dpmOther 54 }

		
--   1.3.6.1.4.1.7777.1.5.55
-- 1.3.6.1.4.1.7777.1.5.55
		-- 1.3.6.1.4.1.7777.1.5.55
		dpmOtherMaxWattDemand OBJECT-TYPE
			SYNTAX Integer32
			MAX-ACCESS read-only
			STATUS current
			DESCRIPTION
				"Other Maximum Watt Demand."
			::= { dpmOther 55 }

		
--   1.3.6.1.4.1.7777.1.5.56
-- 1.3.6.1.4.1.7777.1.5.56
		-- 1.3.6.1.4.1.7777.1.5.56
		dpmOtherNORMALKWHNet OBJECT-TYPE
			SYNTAX Integer32
			MAX-ACCESS read-only
			STATUS current
			DESCRIPTION
				"Other NORMAL kWH Net."
			::= { dpmOther 56 }

		
--   1.3.6.1.4.1.7777.1.5.57
-- 1.3.6.1.4.1.7777.1.5.57
		-- 1.3.6.1.4.1.7777.1.5.57
		dpmOtherNORMALKVARHNet OBJECT-TYPE
			SYNTAX Integer32
			MAX-ACCESS read-only
			STATUS current
			DESCRIPTION
				"Other NORMAL kVarH Net."
			::= { dpmOther 57 }

		
--   1.3.6.1.4.1.7777.1.5.58
-- 1.3.6.1.4.1.7777.1.5.58
		-- 1.3.6.1.4.1.7777.1.5.58
		dpmOtherNORMALKVAHNet OBJECT-TYPE
			SYNTAX Integer32
			MAX-ACCESS read-only
			STATUS current
			DESCRIPTION
				"Other NORMAL kVaH Net."
			::= { dpmOther 58 }

		
--   1.3.6.1.4.1.7777.1.5.59
-- 1.3.6.1.4.1.7777.1.5.59
		-- 1.3.6.1.4.1.7777.1.5.59
		dpmOtherEMERGKWHNet OBJECT-TYPE
			SYNTAX Integer32
			MAX-ACCESS read-only
			STATUS current
			DESCRIPTION
				"Other EMERGENCY kWH Net."
			::= { dpmOther 59 }

		
--   1.3.6.1.4.1.7777.1.5.60
-- 1.3.6.1.4.1.7777.1.5.60
		-- 1.3.6.1.4.1.7777.1.5.60
		dpmOtherEMERGKVARHNet OBJECT-TYPE
			SYNTAX Integer32
			MAX-ACCESS read-only
			STATUS current
			DESCRIPTION
				"Other EMERGENCY kVarH Net."
			::= { dpmOther 60 }

		
--   1.3.6.1.4.1.7777.1.5.61
-- 1.3.6.1.4.1.7777.1.5.61
		-- 1.3.6.1.4.1.7777.1.5.61
		dpmOtherEMERGKVAHNet OBJECT-TYPE
			SYNTAX Integer32
			MAX-ACCESS read-only
			STATUS current
			DESCRIPTION
				"Other EMERGENCY kVaH Net."
			::= { dpmOther 61 }

		
--   1.3.6.1.4.1.7777.1.5.62
-- 1.3.6.1.4.1.7777.1.5.62
		-- 1.3.6.1.4.1.7777.1.5.62
		dpmOtherNORMALMinTotalActivePower OBJECT-TYPE
			SYNTAX Integer32
			MAX-ACCESS read-only
			STATUS current
			DESCRIPTION
				"Other NORMAL Minimum Total Active Power."
			::= { dpmOther 62 }

		
--   1.3.6.1.4.1.7777.1.5.63
-- 1.3.6.1.4.1.7777.1.5.63
		-- 1.3.6.1.4.1.7777.1.5.63
		dpmOtherNORMALMaxTotalActivePower OBJECT-TYPE
			SYNTAX Integer32
			MAX-ACCESS read-only
			STATUS current
			DESCRIPTION
				"Other NORMAL Maximum Total Active Power."
			::= { dpmOther 63 }

		
--   1.3.6.1.4.1.7777.1.5.64
-- 1.3.6.1.4.1.7777.1.5.64
		-- 1.3.6.1.4.1.7777.1.5.64
		dpmOtherNORMALMinTotalReactivePower OBJECT-TYPE
			SYNTAX Integer32
			MAX-ACCESS read-only
			STATUS current
			DESCRIPTION
				"Other NORMAL Minimum Total Reactive  Power."
			::= { dpmOther 64 }

		
--   1.3.6.1.4.1.7777.1.5.65
-- 1.3.6.1.4.1.7777.1.5.65
		-- 1.3.6.1.4.1.7777.1.5.65
		dpmOtherNORMALMaxTotalReactivePower OBJECT-TYPE
			SYNTAX Integer32
			MAX-ACCESS read-only
			STATUS current
			DESCRIPTION
				"Other NORMAL Maximum Total Reactive Power."
			::= { dpmOther 65 }

		
--   1.3.6.1.4.1.7777.1.5.66
-- 1.3.6.1.4.1.7777.1.5.66
		-- 1.3.6.1.4.1.7777.1.5.66
		dpmOtherNORMALMinTotalApparentPower OBJECT-TYPE
			SYNTAX Integer32
			MAX-ACCESS read-only
			STATUS current
			DESCRIPTION
				"Other NORMAL Minimum Total Apparent Power."
			::= { dpmOther 66 }

		
--   1.3.6.1.4.1.7777.1.5.67
-- 1.3.6.1.4.1.7777.1.5.67
		-- 1.3.6.1.4.1.7777.1.5.67
		dpmOtherNORMALMaxTotalApparentPower OBJECT-TYPE
			SYNTAX Integer32
			MAX-ACCESS read-only
			STATUS current
			DESCRIPTION
				"Other NORMAL Maximum Total Apparent Power."
			::= { dpmOther 67 }

		
--   1.3.6.1.4.1.7777.1.5.68
-- 1.3.6.1.4.1.7777.1.5.68
		-- 1.3.6.1.4.1.7777.1.5.68
		dpmOtherEMERGMinTotalActivePower OBJECT-TYPE
			SYNTAX Integer32
			MAX-ACCESS read-only
			STATUS current
			DESCRIPTION
				"Other EMERGENCY Minimum Total Active Power."
			::= { dpmOther 68 }

		
--   1.3.6.1.4.1.7777.1.5.69
-- 1.3.6.1.4.1.7777.1.5.69
		-- 1.3.6.1.4.1.7777.1.5.69
		dpmOtherEMERGMaxTotalActivePower OBJECT-TYPE
			SYNTAX Integer32
			MAX-ACCESS read-only
			STATUS current
			DESCRIPTION
				"Other EMERGENCY Maximum Total Active Power."
			::= { dpmOther 69 }

		
--   1.3.6.1.4.1.7777.1.5.70
-- 1.3.6.1.4.1.7777.1.5.70
		-- 1.3.6.1.4.1.7777.1.5.70
		dpmOtherEMERGMinTotalReactivePower OBJECT-TYPE
			SYNTAX Integer32
			MAX-ACCESS read-only
			STATUS current
			DESCRIPTION
				"Other EMERGENCY Minimum Total Reactive  Power."
			::= { dpmOther 70 }

		
--   1.3.6.1.4.1.7777.1.5.71
-- 1.3.6.1.4.1.7777.1.5.71
		-- 1.3.6.1.4.1.7777.1.5.71
		dpmOtherEMERGMaxTotalReactivePower OBJECT-TYPE
			SYNTAX Integer32
			MAX-ACCESS read-only
			STATUS current
			DESCRIPTION
				"Other EMERGENCY Maximum Total Reactive Power."
			::= { dpmOther 71 }

		
--   1.3.6.1.4.1.7777.1.5.72
-- 1.3.6.1.4.1.7777.1.5.72
		-- 1.3.6.1.4.1.7777.1.5.72
		dpmOtherEMERGMinTotalApparentPower OBJECT-TYPE
			SYNTAX Integer32
			MAX-ACCESS read-only
			STATUS current
			DESCRIPTION
				"Other EMERGENCY Minimum Total Apparent Power."
			::= { dpmOther 72 }

		
--   1.3.6.1.4.1.7777.1.5.73
-- 1.3.6.1.4.1.7777.1.5.73
		-- 1.3.6.1.4.1.7777.1.5.73
		dpmOtherEMERGMaxTotalApparentPower OBJECT-TYPE
			SYNTAX Integer32
			MAX-ACCESS read-only
			STATUS current
			DESCRIPTION
				"Other EMERGENCY Maximum Total Apparent Power."
			::= { dpmOther 73 }

		
--   1.3.6.1.4.1.7777.1.5.74
-- 1.3.6.1.4.1.7777.1.5.74
		-- 1.3.6.1.4.1.7777.1.5.74
		dpmOtherCurrentMonthMaxDemand OBJECT-TYPE
			SYNTAX Integer32
			MAX-ACCESS read-only
			STATUS current
			DESCRIPTION
				"Other Current Month Maximum Demand."
			::= { dpmOther 74 }

		
--   1.3.6.1.4.1.7777.1.5.75
-- 1.3.6.1.4.1.7777.1.5.75
		-- 1.3.6.1.4.1.7777.1.5.75
		dpmOtherMostRecentMonthMaxDemand OBJECT-TYPE
			SYNTAX Integer32
			MAX-ACCESS read-write
			STATUS current
			DESCRIPTION
				"Other Most Recent Month Max Demand."
			::= { dpmOther 75 }

		
--   1.3.6.1.4.1.7777.1.5.76
-- 1.3.6.1.4.1.7777.1.5.76
		-- 1.3.6.1.4.1.7777.1.5.76
		dpmOther2ndRecentMonthMaxDemand OBJECT-TYPE
			SYNTAX Integer32
			MAX-ACCESS read-only
			STATUS current
			DESCRIPTION
				"Other 2nd Most Recent Month Max Demand."
			::= { dpmOther 76 }

		
--   1.3.6.1.4.1.7777.1.5.77
-- 1.3.6.1.4.1.7777.1.5.77
		-- 1.3.6.1.4.1.7777.1.5.77
		dpmOther3rdRecentMonthMaxDemand OBJECT-TYPE
			SYNTAX Integer32
			MAX-ACCESS read-only
			STATUS current
			DESCRIPTION
				"Other 3rd Most Recent Month Max Demand."
			::= { dpmOther 77 }

		
--   1.3.6.1.4.1.7777.1.5.78
-- 1.3.6.1.4.1.7777.1.5.78
		-- 1.3.6.1.4.1.7777.1.5.78
		dpmOther4thRecentMonthMaxDemand OBJECT-TYPE
			SYNTAX Integer32
			MAX-ACCESS read-only
			STATUS current
			DESCRIPTION
				"Other 4th Most Recent Month Max Demand."
			::= { dpmOther 78 }

		
--   1.3.6.1.4.1.7777.1.5.79
-- 1.3.6.1.4.1.7777.1.5.79
		-- 1.3.6.1.4.1.7777.1.5.79
		dpmOther5thRecentMonthMaxDemand OBJECT-TYPE
			SYNTAX Integer32
			MAX-ACCESS read-only
			STATUS current
			DESCRIPTION
				"Other 5th Most Recent Month Max Demand."
			::= { dpmOther 79 }

		
--   1.3.6.1.4.1.7777.1.5.80
-- 1.3.6.1.4.1.7777.1.5.80
		-- 1.3.6.1.4.1.7777.1.5.80
		dpmOther6thRecentMonthMaxDemand OBJECT-TYPE
			SYNTAX Integer32
			MAX-ACCESS read-only
			STATUS current
			DESCRIPTION
				"Other 6th Most Recent Month Max Demand."
			::= { dpmOther 80 }

		
--   1.3.6.1.4.1.7777.1.5.81
-- 1.3.6.1.4.1.7777.1.5.81
		-- 1.3.6.1.4.1.7777.1.5.81
		dpmOther7thRecentMonthMaxDemand OBJECT-TYPE
			SYNTAX Integer32
			MAX-ACCESS read-only
			STATUS current
			DESCRIPTION
				"Other 7th Most Recent Month Max Demand."
			::= { dpmOther 81 }

		
--   1.3.6.1.4.1.7777.1.5.82
-- 1.3.6.1.4.1.7777.1.5.82
		-- 1.3.6.1.4.1.7777.1.5.82
		dpmOther8thRecentMonthMaxDemand OBJECT-TYPE
			SYNTAX Integer32
			MAX-ACCESS read-only
			STATUS current
			DESCRIPTION
				"Other 8th Most Recent Month Max Demand."
			::= { dpmOther 82 }

		
--   1.3.6.1.4.1.7777.1.5.83
-- 1.3.6.1.4.1.7777.1.5.83
		-- 1.3.6.1.4.1.7777.1.5.83
		dpmOther9thRecentMonthMaxDemand OBJECT-TYPE
			SYNTAX Integer32
			MAX-ACCESS read-only
			STATUS current
			DESCRIPTION
				"Other 9th Most Recent Month Max Demand."
			::= { dpmOther 83 }

		
--   1.3.6.1.4.1.7777.1.5.84
-- 1.3.6.1.4.1.7777.1.5.84
		-- 1.3.6.1.4.1.7777.1.5.84
		dpmOther10thRecentMonthMaxDemand OBJECT-TYPE
			SYNTAX Integer32
			MAX-ACCESS read-only
			STATUS current
			DESCRIPTION
				"Other 10th Most Recent Month Max Demand."
			::= { dpmOther 84 }

		
--   1.3.6.1.4.1.7777.1.5.85
-- 1.3.6.1.4.1.7777.1.5.85
		-- 1.3.6.1.4.1.7777.1.5.85
		dpmOther11thRecentMonthMaxDemand OBJECT-TYPE
			SYNTAX Integer32
			MAX-ACCESS read-only
			STATUS current
			DESCRIPTION
				"Other 11th Most Recent Month Max Demand."
			::= { dpmOther 85 }

		
--   1.3.6.1.4.1.7777.1.5.86
-- 1.3.6.1.4.1.7777.1.5.86
		-- 1.3.6.1.4.1.7777.1.5.86
		dpmOther12thRecentMonthMaxDemand OBJECT-TYPE
			SYNTAX Integer32
			MAX-ACCESS read-only
			STATUS current
			DESCRIPTION
				"Other 12th Most Recent Month Max Demand."
			::= { dpmOther 86 }

		
--   1.3.6.1.4.1.7777.1.5.87
-- 1.3.6.1.4.1.7777.1.5.87
		-- 1.3.6.1.4.1.7777.1.5.87
		dpmOther13thRecentMonthMaxDemand OBJECT-TYPE
			SYNTAX Integer32
			MAX-ACCESS read-only
			STATUS current
			DESCRIPTION
				"Other 13th Most Recent Month Max Demand."
			::= { dpmOther 87 }

		
--   1.3.6.1.4.1.7777.1.5.88
-- 1.3.6.1.4.1.7777.1.5.88
		-- 1.3.6.1.4.1.7777.1.5.88
		dpmOther14thRecentMonthMaxDemand OBJECT-TYPE
			SYNTAX Integer32
			MAX-ACCESS read-only
			STATUS current
			DESCRIPTION
				"Other 14th Most Recent Month Max Demand."
			::= { dpmOther 88 }

		
--   1.3.6.1.4.1.7777.1.5.89
-- 1.3.6.1.4.1.7777.1.5.89
		-- 1.3.6.1.4.1.7777.1.5.89
		dpmOther15thRecentMonthMaxDemand OBJECT-TYPE
			SYNTAX Integer32
			MAX-ACCESS read-only
			STATUS current
			DESCRIPTION
				"Other 15th Most Recent Month Max Demand."
			::= { dpmOther 89 }

		
--   1.3.6.1.4.1.7777.1.5.90
-- 1.3.6.1.4.1.7777.1.5.90
		-- 1.3.6.1.4.1.7777.1.5.90
		dpmOther16thRecentMonthMaxDemand OBJECT-TYPE
			SYNTAX Integer32
			MAX-ACCESS read-only
			STATUS current
			DESCRIPTION
				"Other 16th Most Recent Month Max Demand."
			::= { dpmOther 90 }

		
--   1.3.6.1.4.1.7777.1.5.91
-- 1.3.6.1.4.1.7777.1.5.91
		-- 1.3.6.1.4.1.7777.1.5.91
		dpmOther17thRecentMonthMaxDemand OBJECT-TYPE
			SYNTAX Integer32
			MAX-ACCESS read-only
			STATUS current
			DESCRIPTION
				"Other 17th Most Recent Month Max Demand."
			::= { dpmOther 91 }

		
--   1.3.6.1.4.1.7777.1.5.92
-- 1.3.6.1.4.1.7777.1.5.92
		-- 1.3.6.1.4.1.7777.1.5.92
		dpmOther18thRecentMonthMaxDemand OBJECT-TYPE
			SYNTAX Integer32
			MAX-ACCESS read-only
			STATUS current
			DESCRIPTION
				"Other 18th Most Recent Month Max Demand."
			::= { dpmOther 92 }

		
--   1.3.6.1.4.1.7777.1.5.93
-- 1.3.6.1.4.1.7777.1.5.93
		-- 1.3.6.1.4.1.7777.1.5.93
		dpmOther19thRecentMonthMaxDemand OBJECT-TYPE
			SYNTAX Integer32
			MAX-ACCESS read-only
			STATUS current
			DESCRIPTION
				"Other 19th Most Recent Month Max Demand."
			::= { dpmOther 93 }

		
--   1.3.6.1.4.1.7777.1.5.94
-- 1.3.6.1.4.1.7777.1.5.94
		-- 1.3.6.1.4.1.7777.1.5.94
		dpmOther20thRecentMonthMaxDemand OBJECT-TYPE
			SYNTAX Integer32
			MAX-ACCESS read-only
			STATUS current
			DESCRIPTION
				"Other 20th Most Recent Month Max Demand."
			::= { dpmOther 94 }

		
--   1.3.6.1.4.1.7777.1.5.95
-- 1.3.6.1.4.1.7777.1.5.95
		-- 1.3.6.1.4.1.7777.1.5.95
		dpmOther21stRecentMonthMaxDemand OBJECT-TYPE
			SYNTAX Integer32
			MAX-ACCESS read-only
			STATUS current
			DESCRIPTION
				"Other 21st Most Recent Month Max Demand."
			::= { dpmOther 95 }

		
--   1.3.6.1.4.1.7777.1.5.96
-- 1.3.6.1.4.1.7777.1.5.96
		-- 1.3.6.1.4.1.7777.1.5.96
		dpmOther22ndRecentMonthMaxDemand OBJECT-TYPE
			SYNTAX Integer32
			MAX-ACCESS read-only
			STATUS current
			DESCRIPTION
				"Other 22nd Most Recent Month Max Demand."
			::= { dpmOther 96 }

		
--   1.3.6.1.4.1.7777.1.5.97
-- 1.3.6.1.4.1.7777.1.5.97
		-- 1.3.6.1.4.1.7777.1.5.97
		dpmOther23rdRecentMonthMaxDemand OBJECT-TYPE
			SYNTAX Integer32
			MAX-ACCESS read-only
			STATUS current
			DESCRIPTION
				"Other 23rd Most Recent Month Max Demand."
			::= { dpmOther 97 }

		
--   1.3.6.1.4.1.7777.1.5.98
-- 1.3.6.1.4.1.7777.1.5.98
		-- 1.3.6.1.4.1.7777.1.5.98
		dpmOther24thRecentMonthMaxDemand OBJECT-TYPE
			SYNTAX Integer32
			MAX-ACCESS read-only
			STATUS current
			DESCRIPTION
				"Other 24th Most Recent Month Max Demand."
			::= { dpmOther 98 }

		
--   1.3.6.1.4.1.7777.1.5.99
-- 1.3.6.1.4.1.7777.1.5.99
		-- 1.3.6.1.4.1.7777.1.5.99
		dpmOtherMainAndAuxilliaryPositions OBJECT-TYPE
			SYNTAX Integer32
			MAX-ACCESS read-only
			STATUS current
			DESCRIPTION
				"Other Main & Auxiliary Switch positions."
			::= { dpmOther 99 }

		
--   1.3.6.1.4.1.7777.1.5.100
-- 1.3.6.1.4.1.7777.1.5.100
		-- 1.3.6.1.4.1.7777.1.5.100
		dpmOtherResettableEngineRunCounter OBJECT-TYPE
			SYNTAX Integer32
			MAX-ACCESS read-only
			STATUS current
			DESCRIPTION
				"Other Resettable Engine Runtime counter in Hours."
			::= { dpmOther 100 }

		
--   1.3.6.1.4.1.7777.1.5.101
-- 1.3.6.1.4.1.7777.1.5.101
		-- 1.3.6.1.4.1.7777.1.5.101
		dpmOtherCumulativeEngineRunCounter OBJECT-TYPE
			SYNTAX Integer32
			MAX-ACCESS read-only
			STATUS current
			DESCRIPTION
				"Other Cumulative Engine Runtime counter in Hours."
			::= { dpmOther 101 }

		
--   1.3.6.1.4.1.7777.1.6
-- 1.3.6.1.4.1.7777.1.6
		-- 1.3.6.1.4.1.7777.1.6
		traps OBJECT IDENTIFIER ::= { device 6 }

		
--   1.3.6.1.4.1.7777.1.6.0
-- 1.3.6.1.4.1.7777.1.6.0
		-- 1.3.6.1.4.1.7777.1.6.0
		trapsV2 OBJECT-IDENTITY
			STATUS current
			DESCRIPTION 
				"Root node for the converted TRAP-TYPEs."
			::= { traps 0 }

		
--   1.3.6.1.4.1.7777.1.6.0.2
-- 1.3.6.1.4.1.7777.1.6.0.2
		-- 1.3.6.1.4.1.7777.1.6.0.2
		generator_start_signal_activated_SNMPSend NOTIFICATION-TYPE
			OBJECTS { psAlarmVariable }
			STATUS current
			DESCRIPTION 
				"Generator Start Signal Activated."
			::= { trapsV2 2 }

		
--   1.3.6.1.4.1.7777.1.6.0.3
-- 1.3.6.1.4.1.7777.1.6.0.3
		-- 1.3.6.1.4.1.7777.1.6.0.3
		generator_start_signal_removed_SNMPSend NOTIFICATION-TYPE
			OBJECTS { psAlarmVariable }
			STATUS current
			DESCRIPTION 
				"Generator Start Signal Removed."
			::= { trapsV2 3 }

		
--   1.3.6.1.4.1.7777.1.6.0.4
-- 1.3.6.1.4.1.7777.1.6.0.4
		-- 1.3.6.1.4.1.7777.1.6.0.4
		transferred_from_normal_to_emergency_SNMPSend NOTIFICATION-TYPE
			OBJECTS { psAlarmVariable }
			STATUS current
			DESCRIPTION 
				"Transferred from Normal to Emergency."
			::= { trapsV2 4 }

		
--   1.3.6.1.4.1.7777.1.6.0.5
-- 1.3.6.1.4.1.7777.1.6.0.5
		-- 1.3.6.1.4.1.7777.1.6.0.5
		transferred_from_emergency_to_normal_SNMPSend NOTIFICATION-TYPE
			OBJECTS { psAlarmVariable }
			STATUS current
			DESCRIPTION 
				"Transferred from Emergency to Normal."
			::= { trapsV2 5 }

		
--   1.3.6.1.4.1.7777.1.6.0.6
-- 1.3.6.1.4.1.7777.1.6.0.6
		-- 1.3.6.1.4.1.7777.1.6.0.6
		emergency_accepted_SNMPSend NOTIFICATION-TYPE
			OBJECTS { psAlarmVariable }
			STATUS current
			DESCRIPTION 
				"Emergency Accepted."
			::= { trapsV2 6 }

		
--   1.3.6.1.4.1.7777.1.6.0.7
-- 1.3.6.1.4.1.7777.1.6.0.7
		-- 1.3.6.1.4.1.7777.1.6.0.7
		emergency_not_accepted_SNMPSend NOTIFICATION-TYPE
			OBJECTS { psAlarmVariable }
			STATUS current
			DESCRIPTION 
				"Emergency Not Accepted."
			::= { trapsV2 7 }

		
--   1.3.6.1.4.1.7777.1.6.0.8
-- 1.3.6.1.4.1.7777.1.6.0.8
		-- 1.3.6.1.4.1.7777.1.6.0.8
		normal_accepted_SNMPSend NOTIFICATION-TYPE
			OBJECTS { psAlarmVariable }
			STATUS current
			DESCRIPTION 
				"Normal Accepted."
			::= { trapsV2 8 }

		
--   1.3.6.1.4.1.7777.1.6.0.9
-- 1.3.6.1.4.1.7777.1.6.0.9
		-- 1.3.6.1.4.1.7777.1.6.0.9
		normal_not_accepted_SNMPSend NOTIFICATION-TYPE
			OBJECTS { psAlarmVariable }
			STATUS current
			DESCRIPTION 
				"Normal Not Accepted."
			::= { trapsV2 9 }

		
--   1.3.6.1.4.1.7777.1.6.0.10
-- 1.3.6.1.4.1.7777.1.6.0.10
		-- 1.3.6.1.4.1.7777.1.6.0.10
		loss_of_emergency_when_on_emergency_SNMPSend NOTIFICATION-TYPE
			OBJECTS { psAlarmVariable }
			STATUS current
			DESCRIPTION 
				"Loss of Emergency when on Emergency."
			::= { trapsV2 10 }

		
--   1.3.6.1.4.1.7777.1.6.0.11
-- 1.3.6.1.4.1.7777.1.6.0.11
		-- 1.3.6.1.4.1.7777.1.6.0.11
		load_disconnected_SNMPSend NOTIFICATION-TYPE
			OBJECTS { psAlarmVariable }
			STATUS current
			DESCRIPTION 
				"Load Disconnected."
			::= { trapsV2 11 }

		
--   1.3.6.1.4.1.7777.1.6.0.12
-- 1.3.6.1.4.1.7777.1.6.0.12
		-- 1.3.6.1.4.1.7777.1.6.0.12
		transfer_switch_changed_to_non_automatic_mode_SNMPSend NOTIFICATION-TYPE
			OBJECTS { psAlarmVariable }
			STATUS current
			DESCRIPTION 
				"Transfer Switch Changed to Non-Automatic Mode."
			::= { trapsV2 12 }

		
--   1.3.6.1.4.1.7777.1.6.0.13
-- 1.3.6.1.4.1.7777.1.6.0.13
		-- 1.3.6.1.4.1.7777.1.6.0.13
		transfer_switch_changed_to_automatic_mode_SNMPSend NOTIFICATION-TYPE
			OBJECTS { psAlarmVariable }
			STATUS current
			DESCRIPTION 
				"Transfer Switch Changed to Automatic Mode."
			::= { trapsV2 13 }

		
--   1.3.6.1.4.1.7777.1.6.0.14
-- 1.3.6.1.4.1.7777.1.6.0.14
		-- 1.3.6.1.4.1.7777.1.6.0.14
		emergency_not_accepted_in_time_SNMPSend NOTIFICATION-TYPE
			OBJECTS { psAlarmVariable }
			STATUS current
			DESCRIPTION 
				"Emergency Not Accepted in Time."
			::= { trapsV2 14 }

		
--   1.3.6.1.4.1.7777.1.6.0.15
-- 1.3.6.1.4.1.7777.1.6.0.15
		-- 1.3.6.1.4.1.7777.1.6.0.15
		transfer_not_successful_SNMPSend NOTIFICATION-TYPE
			OBJECTS { psAlarmVariable }
			STATUS current
			DESCRIPTION 
				"Transfer Not Successful."
			::= { trapsV2 15 }

		
--   1.3.6.1.4.1.7777.1.6.0.16
-- 1.3.6.1.4.1.7777.1.6.0.16
		-- 1.3.6.1.4.1.7777.1.6.0.16
		transfer_switch_position_not_determined_SNMPSend NOTIFICATION-TYPE
			OBJECTS { psAlarmVariable }
			STATUS current
			DESCRIPTION 
				"Transfer Switch Position Not Determined."
			::= { trapsV2 16 }

		
--   1.3.6.1.4.1.7777.1.6.0.17
-- 1.3.6.1.4.1.7777.1.6.0.17
		-- 1.3.6.1.4.1.7777.1.6.0.17
		transfer_switch_locked_out_SNMPSend NOTIFICATION-TYPE
			OBJECTS { psAlarmVariable }
			STATUS current
			DESCRIPTION 
				"Transfer Switch Locked Out."
			::= { trapsV2 17 }

		
--   1.3.6.1.4.1.7777.1.6.0.18
-- 1.3.6.1.4.1.7777.1.6.0.18
		-- 1.3.6.1.4.1.7777.1.6.0.18
		ctts_extended_parallel_alarm_SNMPSend NOTIFICATION-TYPE
			OBJECTS { psAlarmVariable }
			STATUS current
			DESCRIPTION 
				"CTTS Extended Parallel Alarm."
			::= { trapsV2 18 }

		
--   1.3.6.1.4.1.7777.1.6.0.19
-- 1.3.6.1.4.1.7777.1.6.0.19
		-- 1.3.6.1.4.1.7777.1.6.0.19
		ctts_failure_to_synchronize_SNMPSend NOTIFICATION-TYPE
			OBJECTS { psAlarmVariable }
			STATUS current
			DESCRIPTION 
				"CTTS Failure to Synchronize."
			::= { trapsV2 19 }

		
--   1.3.6.1.4.1.7777.1.6.0.20
-- 1.3.6.1.4.1.7777.1.6.0.20
		-- 1.3.6.1.4.1.7777.1.6.0.20
		normal_breaker_tripped_SNMPSend NOTIFICATION-TYPE
			OBJECTS { psAlarmVariable }
			STATUS current
			DESCRIPTION 
				"Normal Breaker Tripped."
			::= { trapsV2 20 }

		
--   1.3.6.1.4.1.7777.1.6.0.21
-- 1.3.6.1.4.1.7777.1.6.0.21
		-- 1.3.6.1.4.1.7777.1.6.0.21
		emergency_breaker_tripped_SNMPSend NOTIFICATION-TYPE
			OBJECTS { psAlarmVariable }
			STATUS current
			DESCRIPTION 
				"Emergency Breaker Tripped."
			::= { trapsV2 21 }

		
--   1.3.6.1.4.1.7777.1.6.0.22
-- 1.3.6.1.4.1.7777.1.6.0.22
		-- 1.3.6.1.4.1.7777.1.6.0.22
		y_y_primary_fail_active_SNMPSend NOTIFICATION-TYPE
			OBJECTS { psAlarmVariable }
			STATUS current
			DESCRIPTION 
				"Y-Y Primary Fail is Active."
			::= { trapsV2 22 }

		
--    1.3.6.1.4.1.7777.1.2.6.1
-- 1.3.6.1.4.1.7777.1.6.1
-- 1.3.6.1.4.1.7777.1.6.1
		-- 1.3.6.1.4.1.7777.1.6.1
		psAlarmVariable OBJECT-TYPE
			SYNTAX DisplayString (SIZE (0..128))
			MAX-ACCESS read-only
			STATUS current
			DESCRIPTION
				"Traps notification."
			::= { traps 1 }

		
--   1.3.6.1.4.1.7777.2
-- 1.3.6.1.4.1.7777.2
		-- 1.3.6.1.4.1.7777.2
		ascoConformance OBJECT IDENTIFIER ::= { asco 2 }

		
--   1.3.6.1.4.1.7777.2.1
-- 1.3.6.1.4.1.7777.2.1
		-- 1.3.6.1.4.1.7777.2.1
		ascoGroups OBJECT IDENTIFIER ::= { ascoConformance 1 }

		
--   1.3.6.1.4.1.7777.2.1.1
-- 1.3.6.1.4.1.7777.2.1.1
		-- 1.3.6.1.4.1.7777.2.1.1
		currentObjectGroup OBJECT-GROUP
			OBJECTS { phase_shift_between_normal_and_emergency, normal_frequency, emergency_frequency, main_on_normal, main_on_emergency, 
				auxiliary_on_normal, auxiliary_on_emergency, normal_source_available, emergency_source_available, engine_exerciser_with_load_active, 
				external_f17_is_active, normal_voltage_phase_AB, normal_voltage_phase_BC, normal_voltage_phase_CA, normal_voltage_unbalance, 
				emergency_voltage_phase_CA, nominal_voltage, nominal_frequency, normal_source_3phase_sensing, transfer_switch_type, 
				transfer_switch_ampere_rating, controller_software_version, controller_software_date, external_parameter_lock_is_active, engine_running, 
				controller_state, controller_status_state_data, timer_bypass_feature_6B_status, remote_transfer_feature_17_status, load_shed_feature_30_status, 
				transfer_inhibit_to_emergency_feature_34B_status, local_test_feature_5_status, manual_transfer_to_emergency_feature_6ZE_status, current_sensing, phase_A_current, 
				phase_B_current, phase_C_current, failure_to_accept_timer, normal_to_emergency_pretransfer_time_delay_feature_31_bypass_enabled, emergency_to_normal_pretransfer_time_delay_feature_31_bypass_enabled, 
				commit_to_transfer_enabled, bypass_DTTS_source_failure_enabled, inphase_transfer_enabled, inphase_monitor_for_load_shed_feature_30_enabled, fail_accept_timer_enabled, 
				transfer_retransfer_time_delay_bypass_feature_6B_input_enabled, remote_transfer_feature_17_input_enabled, retransfer_to_normal_mode_selector_feature_6DL_input_enabled, serial_remote_transfer_feature_17_enabled, voltage_unbalance_enabled, 
				current_sensing_module_present, alert_LED_active, not_in_auto_LED_active, daylight_savings, loss_of_emergency_when_connected_to_emergency_alarm_enabled, 
				expiration_of_failure_to_accept_timer_alarm_enabled, load_disconnect_enabled_DTTS_only, op1_is_feature_31, op1_is_common_alarm, op1_is_NR2, 
				op1_is_not_in_auto, op2_is_feature_31, op2_is_common_alarm, op2_is_NR2, op2_is_not_in_auto, 
				op2_1G_enabled, op3_is_feature_31, op3_is_common_alarm, op3_is_NR2, op3_is_not_in_auto, 
				controller_serial_number, engine_exerciser_F11C_advanced_program_number, engine_exerciser_F11C_enabled, engine_exerciser_F11C_test_with_load_transfer_enabled, engine_exerciser_F11C_start_week, 
				engine_exerciser_F11C_day_of_week, engine_exerciser_F11C_start_time_hours, engine_exerciser_F11C_start_time_minutes, engine_exerciser_F11C_run_time_hours, engine_exerciser_F11C_run_time_minutes, 
				normal_voltage_dropout, normal_voltage_pickup, normal_over_voltage_trip, normal_frequency_dropout, normal_frequency_pickup, 
				normal_over_frequency_trip, emergency_voltage_dropout, emergency_voltage_pickup, emergency_over_voltage_trip, emergency_frequency_dropout, 
				emergency_frequency_pickup, emergency_over_frequency_trip, timer_1C_engine_start_time_delay, timer_1F_engine_fail_time_delay, timer_2B_transfer_N_to_E_time_delay, 
				timer_2E_engine_cool_down_time_delay, timer_3AF_transfer_E_to_N_on_source_fail_time_delay, timer_3A_T_transfer_E_to_N_on_test_time_delay, timer_31F_N_to_E_pre_transfer_signal_time_delay, timer_31M_N_to_E_post_transfer_signal_time_delay, 
				timer_31G_E_to_N_pre_transfer_signal_time_delay, timer_31N_E_to_N_post_transfer_signal_time_delay, dtts_load_disconnect_time_delay, commit_to_transfer_after_engine_start, real_time_hour, 
				real_time_minute, real_time_second, calendar_year, calendar_month, calendar_day_of_month, 
				calendar_day_of_week, total_time_E_has_been_acceptable_high_word, total_time_E_has_been_acceptable_low_word, total_time_N_has_been_acceptable_high_word, total_time_N_has_been_acceptable_low_word, 
				total_number_of_days_CP_has_been_energized, total_number_of_TS_transfers, total_number_of_TS_transfers_due_to_source_failures, controller_location, external_feature_5_enabled, 
				external_feature_34_enabled, inphase_filter_enabled, current_sensing_option_installed, advanced_11C_option_installed, event_log_option_installed, 
				rs485_communication_option_installed, op1_common_alarm_option_installed, total_time_load_connected_to_normal_high_word, total_time_load_connected_to_normal_low_word, total_time_load_connected_to_emergency_high_word, 
				total_time_load_connected_to_emergency_low_word, rs485_port_address, rs485_port_baud_rate, rs485_port_protocol, emulate_group_1, 
				dtts_load_disconnect_recovery_mode_manual_or_auto, timer_2B_transfer_N_to_E_on_test_time_delay, inphase_monitor_time_delay, ats_total_transfer_time_in_10th_seconds, dongle_installed, 
				language_selection_setting, lcd_contrast_setting, controller_name, boot_loader_version, voltage_display_phase_label_selection, 
				source_1_or_source_2_selection_for_different_english_format, external_battery_enabled, ts_data_gen_start_date, ts_data_gen_start_month, ts_data_gen_start_year, 
				ts_data_gen_start_hour, ts_data_gen_start_minutes, ts_data_gen_start_seconds, ts_data_gen_start_10th_of_seconds, ts_data_gen_start_elapsed_time_in_seconds, 
				total_active_alarm_number, load_shed_direction, dtts_only_load_shed_on_source_failure, dtts_only_load_shed_on_request_f17, normal_voltage_unbalance_dropout, 
				normal_voltage_unbalance_pickup, emergency_voltage_unbalance_dropout, emergency_voltage_unbalance_pickup, emergency_voltage_phase_ab, emergency_voltage_phase_bc, 
				emergency_voltage_unbalance, emergency_source_3phase_sensing, transfer_switch_bypass_or_not, transfer_switch_or_dual_breaker, transfer_switch_locked_out, 
				ctts_extended_parallel_alarm, ctts_failure_to_synch_alarm, dtts_load_disconnect, normal_breaker_tripped, emergency_breaker_tripped, 
				feature_6b, feature_6c, feature_17_serial, feature_29, feature_34a, 
				feature_89, feature_ct_bypass, feature_alarm_reset, feature_6d, feature_34t, 
				control_panel_eventlog_enabled, pt_ratio_numerator, pt_ratio_denominator, control_panel_name, normal_voltage_unbalance_enabled, 
				emergency_voltage_unbalance_enabled, bypass_31F_and_31M_on_N_source_failure, bypass_31G_and_31N_on_E_source_failure, external_battery_present, ctts_in_synch_monitor_time_delay, 
				synch_time_delay, ctts_extended_parallel_time_delay, shed_load_in_phase, isolate_load_on_source_failure, isolate_load_on_F17, 
				fail_to_sync_auto_ct_bypass, transfer_in_phase_on_ct_bypass_if_load_disconnect, network_configuration, dpmNormalDPMName, dpmNormalDPMLoca, 
				dpmNormalNominalVoltage, dpmNormalNominalCurrent, dpmNormalInstantaneousDemandKwMW, dpmNormalInstantaneousDemandDate, dpmNormalInstantaneousDemandTime, 
				dpmNormalBlockDemandforFullHouInkW, dpmNormalBlockDemandforFullDayInkW, dpmNormalBlockDemandforFullMonthInKW, dpmNormalBlockDemandforFullYear, dpmNormalCurrentThdA, 
				dpmNormalCurrentThdB, dpmNormalCurrentThdC, dpmNormalVoltageThdA, dpmNormalVoltageThdB, dpmNormalVoltageThdC, 
				dpmNormalVab, dpmNormalVbc, dpmNormalVca, dpmNormalVolAverage, dpmNormalVolUnbal, 
				dpmNormalVan, dpmNormalVbn, dpmNormalVcn, dpmNormalVavgneutral, dpmNormalFrequency, 
				dpmNormalPowerFactor, dpmNormalCurPhaseA, dpmNormalCurPhaseB, dpmNormalCurPhaseC, dpmNormalPhaseCurAvg, 
				dpmNormalPhaseCurUnbalancecePercentage, dpmNormalRealTotalPower, dpmNormalReactiveTotalPower, dpmNormalApparentTotalPower, dpmNormalNetActiveEnergy, 
				dpmNormalFirmwareVersion, dpmNormalActivePowerA, dpmNormalActivePowerB, dpmNormalActivePowerC, dpmNormalActivePowerTotal, 
				dpmNormalReactivePowerA, dpmNormalReactivePowerB, dpmNormalReactivePowerC, dpmNormalReactivePowerTotal, dpmNormalPowerFactorA, 
				dpmNormalPowerFactorB, dpmNormalPowerFactorC, dpmNormalPowerFactorTotal, dpmNormalVoltAmperePowerA, dpmNormalVoltAmperePowerB, 
				dpmNormalVoltAmperePowerC, dpmNormalVoltAmperePowerTotal, dpmNormalKWHNetLO, dpmNormalKWHNetHI, dpmNormalKVARHNetLO, 
				dpmNormalKVARHNetHI, dpmNormalKVAHNetLO, dpmNormalKVAHNetHI, dpmNormalCurrentMonthMaxDemand, dpmNormalMainAndAuxilliaryPositions, 
				dpmEmergencyDPMName, dpmEmergencyDPMLoca, dpmEmergencyNominalVoltage, dpmEmergencyNominalCurrent, dpmEmergencyInstantaneousDemandKwMW, 
				dpmEmergencyInstantaneousDemandDate, dpmEmergencyInstantaneousDemandTime, dpmEmergencyBlockDemandforFullHouInkW, dpmEmergencyBlockDemandforFullDayInkW, dpmEmergencyBlockDemandforFullMonthInKW, 
				dpmEmergencyBlockDemandforFullYear, dpmEmergencyCurrentThdA, dpmEmergencyCurrentThdB, dpmEmergencyCurrentThdC, dpmEmergencyVoltageThdA, 
				dpmEmergencyVoltageThdB, dpmEmergencyVoltageThdC, dpmEmergencyVab, dpmEmergencyVbc, dpmEmergencyVca, 
				dpmEmergencyVolAverage, dpmEmergencyVolUnbal, dpmEmergencyVan, dpmEmergencyVbn, dpmEmergencyVcn, 
				dpmEmergencyVavgneutral, dpmEmergencyFrequency, dpmEmergencyPowerFactor, dpmEmergencyCurPhaseA, dpmEmergencyCurPhaseB, 
				dpmEmergencyCurPhaseC, dpmEmergencyPhaseCurAvg, dpmEmergencyPhaseCurUnbalancecePercentage, dpmEmergencyRealTotalPower, dpmEmergencyReactiveTotalPower, 
				dpmEmergencyApparentTotalPower, dpmEmergencyNetActiveEnergy, dpmEmergencyFirmwareVersion, dpmEmergencyActivePowerA, dpmEmergencyActivePowerB, 
				dpmEmergencyActivePowerC, dpmEmergencyActivePowerTotal, dpmEmergencyReactivePowerA, dpmEmergencyReactivePowerB, dpmEmergencyReactivePowerC, 
				dpmEmergencyReactivePowerTotal, dpmEmergencyPowerFactorA, dpmEmergencyPowerFactorB, dpmEmergencyPowerFactorC, dpmEmergencyPowerFactorTotal, 
				dpmEmergencyVoltAmperePowerA, dpmEmergencyVoltAmperePowerB, dpmEmergencyVoltAmperePowerC, dpmEmergencyVoltAmperePowerTotal, dpmEmergencyKWHNetLO, 
				dpmEmergencyKWHNetHI, dpmEmergencyKVARHNetLO, dpmEmergencyKVARHNetHI, dpmEmergencyKVAHNetLO, dpmEmergencyKVAHNetHI, 
				dpmEmergencyCurrentMonthMaxDemand, dpmEmergencyMainAndAuxilliaryPositions, dpmLoadDPMName, dpmLoadDPMLoca, dpmLoadNominalVoltage, 
				dpmLoadNominalCurrent, dpmLoadInstantaneousDemandKwMW, dpmLoadInstantaneousDemandDate, dpmLoadInstantaneousDemandTime, dpmLoadBlockDemandforFullHouInkW, 
				dpmLoadBlockDemandforFullDayInkW, dpmLoadBlockDemandforFullMonthInKW, dpmLoadBlockDemandforFullYear, dpmLoadCurrentThdA, dpmLoadCurrentThdB, 
				dpmLoadCurrentThdC, dpmLoadVoltageThdA, dpmLoadVoltageThdB, dpmLoadVoltageThdC, dpmLoadVab, 
				dpmLoadVbc, dpmLoadVca, dpmLoadVolAverage, dpmLoadVolUnbal, dpmLoadVan, 
				dpmLoadVbn, dpmLoadVcn, dpmLoadVavgneutral, dpmLoadFrequency, dpmLoadPowerFactor, 
				dpmLoadCurPhaseA, dpmLoadCurPhaseB, dpmLoadCurPhaseC, dpmLoadPhaseCurAvg, dpmLoadPhaseCurUnbalancecePercentage, 
				dpmLoadRealTotalPower, dpmLoadReactiveTotalPower, dpmLoadApparentTotalPower, dpmLoadNetActiveEnergy, dpmLoadFirmwareVersion, 
				dpmLoadActivePowerA, dpmLoadActivePowerB, dpmLoadActivePowerC, dpmLoadActivePowerTotal, dpmLoadReactivePowerA, 
				dpmLoadReactivePowerB, dpmLoadReactivePowerC, dpmLoadReactivePowerTotal, dpmLoadPowerFactorA, dpmLoadPowerFactorB, 
				dpmLoadPowerFactorC, dpmLoadPowerFactorTotal, dpmLoadVoltAmperePowerA, dpmLoadVoltAmperePowerB, dpmLoadVoltAmperePowerC, 
				dpmLoadVoltAmperePowerTotal, dpmLoadKWHNetLO, dpmLoadKWHNetHI, dpmLoadKVARHNetLO, dpmLoadKVARHNetHI, 
				dpmLoadKVAHNetLO, dpmLoadKVAHNetHI, dpmLoadCurrentMonthMaxDemand, dpmLoadMainAndAuxilliaryPositions, dpmOtherDPMName, 
				dpmOtherDPMLoca, dpmOtherNominalVoltage, dpmOtherNominalCurrent, dpmOtherInstantaneousDemandKwMW, dpmOtherInstantaneousDemandDate, 
				dpmOtherInstantaneousDemandTime, dpmOtherBlockDemandforFullHouInkW, dpmOtherBlockDemandforFullDayInkW, dpmOtherBlockDemandforFullMonthInKW, dpmOtherBlockDemandforFullYear, 
				dpmOtherCurrentThdA, dpmOtherCurrentThdB, dpmOtherCurrentThdC, dpmOtherVoltageThdA, dpmOtherVoltageThdB, 
				dpmOtherVoltageThdC, dpmOtherVab, dpmOtherVbc, dpmOtherVca, dpmOtherVolAverage, 
				dpmOtherVolUnbal, dpmOtherVan, dpmOtherVbn, dpmOtherVcn, dpmOtherVavgneutral, 
				dpmOtherFrequency, dpmOtherPowerFactor, dpmOtherCurPhaseA, dpmOtherCurPhaseB, dpmOtherCurPhaseC, 
				dpmOtherPhaseCurAvg, dpmOtherPhaseCurUnbalancecePercentage, dpmOtherRealTotalPower, dpmOtherReactiveTotalPower, dpmOtherApparentTotalPower, 
				dpmOtherNetActiveEnergy, dpmOtherFirmwareVersion, dpmOtherActivePowerA, dpmOtherActivePowerB, dpmOtherActivePowerC, 
				dpmOtherActivePowerTotal, dpmOtherReactivePowerA, dpmOtherReactivePowerB, dpmOtherReactivePowerC, dpmOtherReactivePowerTotal, 
				dpmOtherPowerFactorA, dpmOtherPowerFactorB, dpmOtherPowerFactorC, dpmOtherPowerFactorTotal, dpmOtherVoltAmperePowerA, 
				dpmOtherVoltAmperePowerB, dpmOtherVoltAmperePowerC, dpmOtherVoltAmperePowerTotal, dpmOtherKWHNetLO, dpmOtherKWHNetHI, 
				dpmOtherKVARHNetLO, dpmOtherKVARHNetHI, dpmOtherKVAHNetLO, dpmOtherKVAHNetHI, dpmOtherCurrentMonthMaxDemand, 
				dpmOtherMainAndAuxilliaryPositions, psAlarmVariable }
			STATUS current
			DESCRIPTION 
				"Enter the description of the created OBJECT-GROUP."
			::= { ascoGroups 1 }

		
--   1.3.6.1.4.1.7777.2.1.2
-- 1.3.6.1.4.1.7777.2.1.2
		-- 1.3.6.1.4.1.7777.2.1.2
		currentNotificationGroup NOTIFICATION-GROUP
			NOTIFICATIONS { generator_start_signal_activated_SNMPSend, generator_start_signal_removed_SNMPSend, transferred_from_normal_to_emergency_SNMPSend, transferred_from_emergency_to_normal_SNMPSend, emergency_accepted_SNMPSend, 
				emergency_not_accepted_SNMPSend, normal_accepted_SNMPSend, normal_not_accepted_SNMPSend, loss_of_emergency_when_on_emergency_SNMPSend, load_disconnected_SNMPSend, 
				transfer_switch_changed_to_non_automatic_mode_SNMPSend, transfer_switch_changed_to_automatic_mode_SNMPSend, emergency_not_accepted_in_time_SNMPSend, transfer_not_successful_SNMPSend, transfer_switch_position_not_determined_SNMPSend
				 }
			STATUS current
			DESCRIPTION 
				"Enter the description of the created NOTIFICATION-GROUP."
			::= { ascoGroups 2 }

		
--   1.3.6.1.4.1.7777.2.2
-- 1.3.6.1.4.1.7777.2.2
		-- 1.3.6.1.4.1.7777.2.2
		ascoCompliances OBJECT IDENTIFIER ::= { ascoConformance 2 }

		
--   1.3.6.1.4.1.7777.2.2.1
-- this module
-- 1.3.6.1.4.1.7777.2.2.1
		-- 1.3.6.1.4.1.7777.2.2.1
		basicCompliance MODULE-COMPLIANCE
			STATUS current
			DESCRIPTION 
				"Enter the description of the created MODULE-COMPLIANCE."
			MODULE ASCO-QEM-72EE2-BETA-02
				MANDATORY-GROUPS { currentObjectGroup, currentNotificationGroup }
			::= { ascoCompliances 1 }

		
	
	END

--
-- ASCO-QEM-72EE2-BETA-03.mib
--
