--
-- CAREL-mstaf.MIB
-- MIB generated by CAREL
-- Thursday, 12 September 2013
--

    CAREL-mstaf-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        mstafMIB MODULE-IDENTITY
      		LAST-UPDATED  "201309121047Z"		-- September 12, 2013 at 10:47 GMT
      		ORGANIZATION  "CAREL SpA"
      		CONTACT-INFO
                "
                        Carel SpA
                        Via dell'Industria, 11
                        35020 Brugine (PD) Italy
                        Tel: +39 049 9716611
                        E-mail: carel@carel.com
                "
      		DESCRIPTION

                "This is the MIB module for the TRA Uniflair device."
		REVISION   "201309121047Z"		-- September 12, 2013 at 10:47 GMT
		DESCRIPTION


                "This is the MIB module for the mstaf device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { mstafMIB 1 }

        -- 1.3.6.1.4.1.9839.2.1.1.1
        abil-un1 OBJECT-TYPE
                    SYNTAX Integer32 (0..1)
                    UNITS "N/A"
                    MAX-ACCESS read-only
                    STATUS current
                    DESCRIPTION "ENABLE AFM1"
                    ::= { digitalObjects 1 }

        -- 1.3.6.1.4.1.9839.2.1.1.2
        alcu1 OBJECT-TYPE
                    SYNTAX Integer32 (0..1)
                    UNITS "N/A"
                    MAX-ACCESS read-only
                    STATUS current
                    DESCRIPTION "LAN CONNECTION FAILED AFM1"
                    ::= { digitalObjects 2 }

        -- 1.3.6.1.4.1.9839.2.1.1.3
        regol-1 OBJECT-TYPE
                    SYNTAX Integer32 (0..1)
                    UNITS "N/A"
                    MAX-ACCESS read-only
                    STATUS current
                    DESCRIPTION "REGULATION ACTIVE AFM1"
                    ::= { digitalObjects 3 }

        -- 1.3.6.1.4.1.9839.2.1.1.4
        buz-1 OBJECT-TYPE
                    SYNTAX Integer32 (0..1)
                    UNITS "N/A"
                    MAX-ACCESS read-only
                    STATUS current
                    DESCRIPTION "ALARM AFM1"
                    ::= { digitalObjects 4 }

        -- 1.3.6.1.4.1.9839.2.1.1.5
        abil-un2 OBJECT-TYPE
                    SYNTAX Integer32 (0..1)
                    UNITS "N/A"
                    MAX-ACCESS read-only
                    STATUS current
                    DESCRIPTION "ENABLE AFM2"
                    ::= { digitalObjects 5 }

        -- 1.3.6.1.4.1.9839.2.1.1.6
        alcu2 OBJECT-TYPE
                    SYNTAX Integer32 (0..1)
                    UNITS "N/A"
                    MAX-ACCESS read-only
                    STATUS current
                    DESCRIPTION "LAN CONNECTION FAILED AFM2"
                    ::= { digitalObjects 6 }

        -- 1.3.6.1.4.1.9839.2.1.1.7
        regol-2 OBJECT-TYPE
                    SYNTAX Integer32 (0..1)
                    UNITS "N/A"
                    MAX-ACCESS read-only
                    STATUS current
                    DESCRIPTION "REGULATION ACTIVE AFM2"
                    ::= { digitalObjects 7 }

        -- 1.3.6.1.4.1.9839.2.1.1.8
        buz-2 OBJECT-TYPE
                    SYNTAX Integer32 (0..1)
                    UNITS "N/A"
                    MAX-ACCESS read-only
                    STATUS current
                    DESCRIPTION "ALARM AFM2"
                    ::= { digitalObjects 8 }

        -- 1.3.6.1.4.1.9839.2.1.1.9
        abil-un3 OBJECT-TYPE
                    SYNTAX Integer32 (0..1)
                    UNITS "N/A"
                    MAX-ACCESS read-only
                    STATUS current
                    DESCRIPTION "ENABLE AFM3"
                    ::= { digitalObjects 9 }

        -- 1.3.6.1.4.1.9839.2.1.1.10
        alcu3 OBJECT-TYPE
                    SYNTAX Integer32 (0..1)
                    UNITS "N/A"
                    MAX-ACCESS read-only
                    STATUS current
                    DESCRIPTION "LAN CONNECTION FAILED AFM3"
                    ::= { digitalObjects 10 }

        -- 1.3.6.1.4.1.9839.2.1.1.11
        regol-3 OBJECT-TYPE
                    SYNTAX Integer32 (0..1)
                    UNITS "N/A"
                    MAX-ACCESS read-only
                    STATUS current
                    DESCRIPTION "REGULATION ACTIVE AFM3"
                    ::= { digitalObjects 11 }

        -- 1.3.6.1.4.1.9839.2.1.1.12
        buz-3 OBJECT-TYPE
                    SYNTAX Integer32 (0..1)
                    UNITS "N/A"
                    MAX-ACCESS read-only
                    STATUS current
                    DESCRIPTION "ALARM AFM3"
                    ::= { digitalObjects 12 }

        -- 1.3.6.1.4.1.9839.2.1.1.13
        abil-un4 OBJECT-TYPE
                    SYNTAX Integer32 (0..1)
                    UNITS "N/A"
                    MAX-ACCESS read-only
                    STATUS current
                    DESCRIPTION "ENABLE AFM4"
                    ::= { digitalObjects 13 }

        -- 1.3.6.1.4.1.9839.2.1.1.14
        alcu4 OBJECT-TYPE
                    SYNTAX Integer32 (0..1)
                    UNITS "N/A"
                    MAX-ACCESS read-only
                    STATUS current
                    DESCRIPTION "LAN CONNECTION FAILED AFM4"
                    ::= { digitalObjects 14 }

        -- 1.3.6.1.4.1.9839.2.1.1.15
        regol-4 OBJECT-TYPE
                    SYNTAX Integer32 (0..1)
                    UNITS "N/A"
                    MAX-ACCESS read-only
                    STATUS current
                    DESCRIPTION "REGULATION ACTIVE AFM4"
                    ::= { digitalObjects 15 }

        -- 1.3.6.1.4.1.9839.2.1.1.16
        buz-4 OBJECT-TYPE
                    SYNTAX Integer32 (0..1)
                    UNITS "N/A"
                    MAX-ACCESS read-only
                    STATUS current
                    DESCRIPTION "ALARM AFM4"
                    ::= { digitalObjects 16 }

        -- 1.3.6.1.4.1.9839.2.1.1.17
        abil-un5 OBJECT-TYPE
                    SYNTAX Integer32 (0..1)
                    UNITS "N/A"
                    MAX-ACCESS read-only
                    STATUS current
                    DESCRIPTION "ENABLE AFM5"
                    ::= { digitalObjects 17 }

        -- 1.3.6.1.4.1.9839.2.1.1.18
        alcu5 OBJECT-TYPE
                    SYNTAX Integer32 (0..1)
                    UNITS "N/A"
                    MAX-ACCESS read-only
                    STATUS current
                    DESCRIPTION "LAN CONNECTION FAILED AFM5"
                    ::= { digitalObjects 18 }

        -- 1.3.6.1.4.1.9839.2.1.1.19
        regol-5 OBJECT-TYPE
                    SYNTAX Integer32 (0..1)
                    UNITS "N/A"
                    MAX-ACCESS read-only
                    STATUS current
                    DESCRIPTION "REGULATION ACTIVE AFM5"
                    ::= { digitalObjects 19 }

        -- 1.3.6.1.4.1.9839.2.1.1.20
        buz-5 OBJECT-TYPE
                    SYNTAX Integer32 (0..1)
                    UNITS "N/A"
                    MAX-ACCESS read-only
                    STATUS current
                    DESCRIPTION "ALARM AFM5"
                    ::= { digitalObjects 20 }

        -- 1.3.6.1.4.1.9839.2.1.1.21
        abil-un6 OBJECT-TYPE
                    SYNTAX Integer32 (0..1)
                    UNITS "N/A"
                    MAX-ACCESS read-only
                    STATUS current
                    DESCRIPTION "ENABLE AFM6"
                    ::= { digitalObjects 21 }

        -- 1.3.6.1.4.1.9839.2.1.1.22
        alcu6 OBJECT-TYPE
                    SYNTAX Integer32 (0..1)
                    UNITS "N/A"
                    MAX-ACCESS read-only
                    STATUS current
                    DESCRIPTION "LAN CONNECTION FAILED AFM6"
                    ::= { digitalObjects 22 }

        -- 1.3.6.1.4.1.9839.2.1.1.23
        regol-6 OBJECT-TYPE
                    SYNTAX Integer32 (0..1)
                    UNITS "N/A"
                    MAX-ACCESS read-only
                    STATUS current
                    DESCRIPTION "REGULATION ACTIVE AFM6"
                    ::= { digitalObjects 23 }

        -- 1.3.6.1.4.1.9839.2.1.1.24
        buz-6 OBJECT-TYPE
                    SYNTAX Integer32 (0..1)
                    UNITS "N/A"
                    MAX-ACCESS read-only
                    STATUS current
                    DESCRIPTION "ALARM AFM6"
                    ::= { digitalObjects 24 }

        -- 1.3.6.1.4.1.9839.2.1.1.25
        abil-un7 OBJECT-TYPE
                    SYNTAX Integer32 (0..1)
                    UNITS "N/A"
                    MAX-ACCESS read-only
                    STATUS current
                    DESCRIPTION "ENABLE AFM7"
                    ::= { digitalObjects 25 }

        -- 1.3.6.1.4.1.9839.2.1.1.26
        alcu7 OBJECT-TYPE
                    SYNTAX Integer32 (0..1)
                    UNITS "N/A"
                    MAX-ACCESS read-only
                    STATUS current
                    DESCRIPTION "LAN CONNECTION FAILED AFM7"
                    ::= { digitalObjects 26 }

        -- 1.3.6.1.4.1.9839.2.1.1.27
        regol-7 OBJECT-TYPE
                    SYNTAX Integer32 (0..1)
                    UNITS "N/A"
                    MAX-ACCESS read-only
                    STATUS current
                    DESCRIPTION "REGULATION ACTIVE AFM7"
                    ::= { digitalObjects 27 }

        -- 1.3.6.1.4.1.9839.2.1.1.28
        buz-7 OBJECT-TYPE
                    SYNTAX Integer32 (0..1)
                    UNITS "N/A"
                    MAX-ACCESS read-only
                    STATUS current
                    DESCRIPTION "ALARM AFM7"
                    ::= { digitalObjects 28 }

        -- 1.3.6.1.4.1.9839.2.1.1.29
        abil-un8 OBJECT-TYPE
                    SYNTAX Integer32 (0..1)
                    UNITS "N/A"
                    MAX-ACCESS read-only
                    STATUS current
                    DESCRIPTION "ENABLE AFM8"
                    ::= { digitalObjects 29 }

        -- 1.3.6.1.4.1.9839.2.1.1.30
        alcu8 OBJECT-TYPE
                    SYNTAX Integer32 (0..1)
                    UNITS "N/A"
                    MAX-ACCESS read-only
                    STATUS current
                    DESCRIPTION "LAN CONNECTION FAILED AFM8"
                    ::= { digitalObjects 30 }

        -- 1.3.6.1.4.1.9839.2.1.1.31
        regol-8 OBJECT-TYPE
                    SYNTAX Integer32 (0..1)
                    UNITS "N/A"
                    MAX-ACCESS read-only
                    STATUS current
                    DESCRIPTION "REGULATION ACTIVE AFM8"
                    ::= { digitalObjects 31 }

        -- 1.3.6.1.4.1.9839.2.1.1.32
        buz-8 OBJECT-TYPE
                    SYNTAX Integer32 (0..1)
                    UNITS "N/A"
                    MAX-ACCESS read-only
                    STATUS current
                    DESCRIPTION "ALARM AFM8"
                    ::= { digitalObjects 32 }

        -- 1.3.6.1.4.1.9839.2.1.1.33
        abil-un9 OBJECT-TYPE
                    SYNTAX Integer32 (0..1)
                    UNITS "N/A"
                    MAX-ACCESS read-only
                    STATUS current
                    DESCRIPTION "ENABLE AFM9"
                    ::= { digitalObjects 33 }

        -- 1.3.6.1.4.1.9839.2.1.1.34
        alcu9 OBJECT-TYPE
                    SYNTAX Integer32 (0..1)
                    UNITS "N/A"
                    MAX-ACCESS read-only
                    STATUS current
                    DESCRIPTION "LAN CONNECTION FAILED AFM9"
                    ::= { digitalObjects 34 }

        -- 1.3.6.1.4.1.9839.2.1.1.35
        regol-9 OBJECT-TYPE
                    SYNTAX Integer32 (0..1)
                    UNITS "N/A"
                    MAX-ACCESS read-only
                    STATUS current
                    DESCRIPTION "REGULATION ACTIVE AFM9"
                    ::= { digitalObjects 35 }

        -- 1.3.6.1.4.1.9839.2.1.1.36
        buz-9 OBJECT-TYPE
                    SYNTAX Integer32 (0..1)
                    UNITS "N/A"
                    MAX-ACCESS read-only
                    STATUS current
                    DESCRIPTION "ALARM AFM9"
                    ::= { digitalObjects 36 }

        -- 1.3.6.1.4.1.9839.2.1.1.37
        abil-un10 OBJECT-TYPE
                    SYNTAX Integer32 (0..1)
                    UNITS "N/A"
                    MAX-ACCESS read-only
                    STATUS current
                    DESCRIPTION "ENABLE AFM10"
                    ::= { digitalObjects 37 }

        -- 1.3.6.1.4.1.9839.2.1.1.38
        alcu10 OBJECT-TYPE
                    SYNTAX Integer32 (0..1)
                    UNITS "N/A"
                    MAX-ACCESS read-only
                    STATUS current
                    DESCRIPTION "LAN CONNECTION FAILED AFM10"
                    ::= { digitalObjects 38 }

        -- 1.3.6.1.4.1.9839.2.1.1.39
        regol-10 OBJECT-TYPE
                    SYNTAX Integer32 (0..1)
                    UNITS "N/A"
                    MAX-ACCESS read-only
                    STATUS current
                    DESCRIPTION "REGULATION ACTIVE AFM10"
                    ::= { digitalObjects 39 }

        -- 1.3.6.1.4.1.9839.2.1.1.40
        buz-10 OBJECT-TYPE
                    SYNTAX Integer32 (0..1)
                    UNITS "N/A"
                    MAX-ACCESS read-only
                    STATUS current
                    DESCRIPTION "ALARM AFM10"
                    ::= { digitalObjects 40 }

        -- 1.3.6.1.4.1.9839.2.1.1.41
        abil-un11 OBJECT-TYPE
                    SYNTAX Integer32 (0..1)
                    UNITS "N/A"
                    MAX-ACCESS read-only
                    STATUS current
                    DESCRIPTION "ENABLE AFM11"
                    ::= { digitalObjects 41 }

        -- 1.3.6.1.4.1.9839.2.1.1.42
        alcu11 OBJECT-TYPE
                    SYNTAX Integer32 (0..1)
                    UNITS "N/A"
                    MAX-ACCESS read-only
                    STATUS current
                    DESCRIPTION "LAN CONNECTION FAILED AFM11"
                    ::= { digitalObjects 42 }

        -- 1.3.6.1.4.1.9839.2.1.1.43
        regol-11 OBJECT-TYPE
                    SYNTAX Integer32 (0..1)
                    UNITS "N/A"
                    MAX-ACCESS read-only
                    STATUS current
                    DESCRIPTION "REGULATION ACTIVE AFM11"
                    ::= { digitalObjects 43 }

        -- 1.3.6.1.4.1.9839.2.1.1.44
        buz-11 OBJECT-TYPE
                    SYNTAX Integer32 (0..1)
                    UNITS "N/A"
                    MAX-ACCESS read-only
                    STATUS current
                    DESCRIPTION "ALARM AFM11"
                    ::= { digitalObjects 44 }

        -- 1.3.6.1.4.1.9839.2.1.1.45
        abil-un12 OBJECT-TYPE
                    SYNTAX Integer32 (0..1)
                    UNITS "N/A"
                    MAX-ACCESS read-only
                    STATUS current
                    DESCRIPTION "ENABLE AFM12"
                    ::= { digitalObjects 45 }

        -- 1.3.6.1.4.1.9839.2.1.1.46
        alcu12 OBJECT-TYPE
                    SYNTAX Integer32 (0..1)
                    UNITS "N/A"
                    MAX-ACCESS read-only
                    STATUS current
                    DESCRIPTION "LAN CONNECTION FAILED AFM12"
                    ::= { digitalObjects 46 }

        -- 1.3.6.1.4.1.9839.2.1.1.47
        regol-12 OBJECT-TYPE
                    SYNTAX Integer32 (0..1)
                    UNITS "N/A"
                    MAX-ACCESS read-only
                    STATUS current
                    DESCRIPTION "REGULATION ACTIVE AFM12"
                    ::= { digitalObjects 47 }

        -- 1.3.6.1.4.1.9839.2.1.1.48
        buz-12 OBJECT-TYPE
                    SYNTAX Integer32 (0..1)
                    UNITS "N/A"
                    MAX-ACCESS read-only
                    STATUS current
                    DESCRIPTION "ALARM AFM12"
                    ::= { digitalObjects 48 }

        -- 1.3.6.1.4.1.9839.2.1.1.49
        abil-un13 OBJECT-TYPE
                    SYNTAX Integer32 (0..1)
                    UNITS "N/A"
                    MAX-ACCESS read-only
                    STATUS current
                    DESCRIPTION "ENABLE AFM13"
                    ::= { digitalObjects 49 }

        -- 1.3.6.1.4.1.9839.2.1.1.50
        alcu13 OBJECT-TYPE
                    SYNTAX Integer32 (0..1)
                    UNITS "N/A"
                    MAX-ACCESS read-only
                    STATUS current
                    DESCRIPTION "LAN CONNECTION FAILED AFM13"
                    ::= { digitalObjects 50 }

        -- 1.3.6.1.4.1.9839.2.1.1.51
        regol-13 OBJECT-TYPE
                    SYNTAX Integer32 (0..1)
                    UNITS "N/A"
                    MAX-ACCESS read-only
                    STATUS current
                    DESCRIPTION "REGULATION ACTIVE AFM13"
                    ::= { digitalObjects 51 }

        -- 1.3.6.1.4.1.9839.2.1.1.52
        buz-13 OBJECT-TYPE
                    SYNTAX Integer32 (0..1)
                    UNITS "N/A"
                    MAX-ACCESS read-only
                    STATUS current
                    DESCRIPTION "ALARM AFM13"
                    ::= { digitalObjects 52 }

        -- 1.3.6.1.4.1.9839.2.1.1.53
        abil-un14 OBJECT-TYPE
                    SYNTAX Integer32 (0..1)
                    UNITS "N/A"
                    MAX-ACCESS read-only
                    STATUS current
                    DESCRIPTION "ENABLE AFM14"
                    ::= { digitalObjects 53 }

        -- 1.3.6.1.4.1.9839.2.1.1.54
        alcu14 OBJECT-TYPE
                    SYNTAX Integer32 (0..1)
                    UNITS "N/A"
                    MAX-ACCESS read-only
                    STATUS current
                    DESCRIPTION "LAN CONNECTION FAILED AFM14"
                    ::= { digitalObjects 54 }

        -- 1.3.6.1.4.1.9839.2.1.1.55
        regol-14 OBJECT-TYPE
                    SYNTAX Integer32 (0..1)
                    UNITS "N/A"
                    MAX-ACCESS read-only
                    STATUS current
                    DESCRIPTION "REGULATION ACTIVE AFM14"
                    ::= { digitalObjects 55 }

        -- 1.3.6.1.4.1.9839.2.1.1.56
        buz-14 OBJECT-TYPE
                    SYNTAX Integer32 (0..1)
                    UNITS "N/A"
                    MAX-ACCESS read-only
                    STATUS current
                    DESCRIPTION "ALARM AFM14"
                    ::= { digitalObjects 56 }

        -- 1.3.6.1.4.1.9839.2.1.1.57
        abil-un15 OBJECT-TYPE
                    SYNTAX Integer32 (0..1)
                    UNITS "N/A"
                    MAX-ACCESS read-only
                    STATUS current
                    DESCRIPTION "ENABLE AFM15"
                    ::= { digitalObjects 57 }

        -- 1.3.6.1.4.1.9839.2.1.1.58
        alcu15 OBJECT-TYPE
                    SYNTAX Integer32 (0..1)
                    UNITS "N/A"
                    MAX-ACCESS read-only
                    STATUS current
                    DESCRIPTION "LAN CONNECTION FAILED AFM15"
                    ::= { digitalObjects 58 }

        -- 1.3.6.1.4.1.9839.2.1.1.59
        regol-15 OBJECT-TYPE
                    SYNTAX Integer32 (0..1)
                    UNITS "N/A"
                    MAX-ACCESS read-only
                    STATUS current
                    DESCRIPTION "REGULATION ACTIVE AFM15"
                    ::= { digitalObjects 59 }

        -- 1.3.6.1.4.1.9839.2.1.1.60
        buz-15 OBJECT-TYPE
                    SYNTAX Integer32 (0..1)
                    UNITS "N/A"
                    MAX-ACCESS read-only
                    STATUS current
                    DESCRIPTION "ALARM AFM15"
                    ::= { digitalObjects 60 }

        -- 1.3.6.1.4.1.9839.2.1.1.61
        abil-un16 OBJECT-TYPE
                    SYNTAX Integer32 (0..1)
                    UNITS "N/A"
                    MAX-ACCESS read-only
                    STATUS current
                    DESCRIPTION "ENABLE AFM16"
                    ::= { digitalObjects 61 }

        -- 1.3.6.1.4.1.9839.2.1.1.62
        alcu16 OBJECT-TYPE
                    SYNTAX Integer32 (0..1)
                    UNITS "N/A"
                    MAX-ACCESS read-only
                    STATUS current
                    DESCRIPTION "LAN CONNECTION FAILED AFM16"
                    ::= { digitalObjects 62 }

        -- 1.3.6.1.4.1.9839.2.1.1.63
        regol-16 OBJECT-TYPE
                    SYNTAX Integer32 (0..1)
                    UNITS "N/A"
                    MAX-ACCESS read-only
                    STATUS current
                    DESCRIPTION "REGULATION ACTIVE AFM16"
                    ::= { digitalObjects 63 }

        -- 1.3.6.1.4.1.9839.2.1.1.64
        buz-16 OBJECT-TYPE
                    SYNTAX Integer32 (0..1)
                    UNITS "N/A"
                    MAX-ACCESS read-only
                    STATUS current
                    DESCRIPTION "ALARM AFM16"
                    ::= { digitalObjects 64 }

        -- 1.3.6.1.4.1.9839.2.1.1.65
        abil-un17 OBJECT-TYPE
                    SYNTAX Integer32 (0..1)
                    UNITS "N/A"
                    MAX-ACCESS read-only
                    STATUS current
                    DESCRIPTION "ENABLE AFM17"
                    ::= { digitalObjects 65 }

        -- 1.3.6.1.4.1.9839.2.1.1.66
        alcu17 OBJECT-TYPE
                    SYNTAX Integer32 (0..1)
                    UNITS "N/A"
                    MAX-ACCESS read-only
                    STATUS current
                    DESCRIPTION "LAN CONNECTION FAILED AFM17"
                    ::= { digitalObjects 66 }

        -- 1.3.6.1.4.1.9839.2.1.1.67
        regol-17 OBJECT-TYPE
                    SYNTAX Integer32 (0..1)
                    UNITS "N/A"
                    MAX-ACCESS read-only
                    STATUS current
                    DESCRIPTION "REGULATION ACTIVE AFM17"
                    ::= { digitalObjects 67 }

        -- 1.3.6.1.4.1.9839.2.1.1.68
        buz-17 OBJECT-TYPE
                    SYNTAX Integer32 (0..1)
                    UNITS "N/A"
                    MAX-ACCESS read-only
                    STATUS current
                    DESCRIPTION "ALARM AFM17"
                    ::= { digitalObjects 68 }

        -- 1.3.6.1.4.1.9839.2.1.1.69
        abil-un18 OBJECT-TYPE
                    SYNTAX Integer32 (0..1)
                    UNITS "N/A"
                    MAX-ACCESS read-only
                    STATUS current
                    DESCRIPTION "ENABLE AFM18"
                    ::= { digitalObjects 69 }

        -- 1.3.6.1.4.1.9839.2.1.1.70
        alcu18 OBJECT-TYPE
                    SYNTAX Integer32 (0..1)
                    UNITS "N/A"
                    MAX-ACCESS read-only
                    STATUS current
                    DESCRIPTION "LAN CONNECTION FAILED AFM18"
                    ::= { digitalObjects 70 }

        -- 1.3.6.1.4.1.9839.2.1.1.71
        regol-18 OBJECT-TYPE
                    SYNTAX Integer32 (0..1)
                    UNITS "N/A"
                    MAX-ACCESS read-only
                    STATUS current
                    DESCRIPTION "REGULATION ACTIVE AFM18"
                    ::= { digitalObjects 71 }

        -- 1.3.6.1.4.1.9839.2.1.1.72
        buz-18 OBJECT-TYPE
                    SYNTAX Integer32 (0..1)
                    UNITS "N/A"
                    MAX-ACCESS read-only
                    STATUS current
                    DESCRIPTION "ALARM AFM18"
                    ::= { digitalObjects 72 }

        -- 1.3.6.1.4.1.9839.2.1.1.73
        abil-un19 OBJECT-TYPE
                    SYNTAX Integer32 (0..1)
                    UNITS "N/A"
                    MAX-ACCESS read-only
                    STATUS current
                    DESCRIPTION "ENABLE AFM19"
                    ::= { digitalObjects 73 }

        -- 1.3.6.1.4.1.9839.2.1.1.74
        alcu19 OBJECT-TYPE
                    SYNTAX Integer32 (0..1)
                    UNITS "N/A"
                    MAX-ACCESS read-only
                    STATUS current
                    DESCRIPTION "LAN CONNECTION FAILED AFM19"
                    ::= { digitalObjects 74 }

        -- 1.3.6.1.4.1.9839.2.1.1.75
        regol-19 OBJECT-TYPE
                    SYNTAX Integer32 (0..1)
                    UNITS "N/A"
                    MAX-ACCESS read-only
                    STATUS current
                    DESCRIPTION "REGULATION ACTIVE AFM19"
                    ::= { digitalObjects 75 }

        -- 1.3.6.1.4.1.9839.2.1.1.76
        buz-19 OBJECT-TYPE
                    SYNTAX Integer32 (0..1)
                    UNITS "N/A"
                    MAX-ACCESS read-only
                    STATUS current
                    DESCRIPTION "ALARM AFM19"
                    ::= { digitalObjects 76 }

        -- 1.3.6.1.4.1.9839.2.1.1.77
        abil-un20 OBJECT-TYPE
                    SYNTAX Integer32 (0..1)
                    UNITS "N/A"
                    MAX-ACCESS read-only
                    STATUS current
                    DESCRIPTION "ENABLE AFM20"
                    ::= { digitalObjects 77 }

        -- 1.3.6.1.4.1.9839.2.1.1.78
        alcu20 OBJECT-TYPE
                    SYNTAX Integer32 (0..1)
                    UNITS "N/A"
                    MAX-ACCESS read-only
                    STATUS current
                    DESCRIPTION "LAN CONNECTION FAILED AFM20"
                    ::= { digitalObjects 78 }

        -- 1.3.6.1.4.1.9839.2.1.1.79
        regol-20 OBJECT-TYPE
                    SYNTAX Integer32 (0..1)
                    UNITS "N/A"
                    MAX-ACCESS read-only
                    STATUS current
                    DESCRIPTION "REGULATION ACTIVE AFM20"
                    ::= { digitalObjects 79 }

        -- 1.3.6.1.4.1.9839.2.1.1.80
        buz-20 OBJECT-TYPE
                    SYNTAX Integer32 (0..1)
                    UNITS "N/A"
                    MAX-ACCESS read-only
                    STATUS current
                    DESCRIPTION "ALARM AFM20"
                    ::= { digitalObjects 80 }

        -- 1.3.6.1.4.1.9839.2.1.1.81
        abil-un21 OBJECT-TYPE
                    SYNTAX Integer32 (0..1)
                    UNITS "N/A"
                    MAX-ACCESS read-only
                    STATUS current
                    DESCRIPTION "ENABLE AFM21"
                    ::= { digitalObjects 81 }

        -- 1.3.6.1.4.1.9839.2.1.1.82
        alcu21 OBJECT-TYPE
                    SYNTAX Integer32 (0..1)
                    UNITS "N/A"
                    MAX-ACCESS read-only
                    STATUS current
                    DESCRIPTION "LAN CONNECTION FAILED AFM21"
                    ::= { digitalObjects 82 }

        -- 1.3.6.1.4.1.9839.2.1.1.83
        regol-21 OBJECT-TYPE
                    SYNTAX Integer32 (0..1)
                    UNITS "N/A"
                    MAX-ACCESS read-only
                    STATUS current
                    DESCRIPTION "REGULATION ACTIVE AFM21"
                    ::= { digitalObjects 83 }

        -- 1.3.6.1.4.1.9839.2.1.1.84
        buz-21 OBJECT-TYPE
                    SYNTAX Integer32 (0..1)
                    UNITS "N/A"
                    MAX-ACCESS read-only
                    STATUS current
                    DESCRIPTION "ALARM AFM21"
                    ::= { digitalObjects 84 }

        -- 1.3.6.1.4.1.9839.2.1.1.85
        abil-un22 OBJECT-TYPE
                    SYNTAX Integer32 (0..1)
                    UNITS "N/A"
                    MAX-ACCESS read-only
                    STATUS current
                    DESCRIPTION "ENABLE AFM22"
                    ::= { digitalObjects 85 }

        -- 1.3.6.1.4.1.9839.2.1.1.86
        alcu22 OBJECT-TYPE
                    SYNTAX Integer32 (0..1)
                    UNITS "N/A"
                    MAX-ACCESS read-only
                    STATUS current
                    DESCRIPTION "LAN CONNECTION FAILED AFM22"
                    ::= { digitalObjects 86 }

        -- 1.3.6.1.4.1.9839.2.1.1.87
        regol-22 OBJECT-TYPE
                    SYNTAX Integer32 (0..1)
                    UNITS "N/A"
                    MAX-ACCESS read-only
                    STATUS current
                    DESCRIPTION "REGULATION ACTIVE AFM22"
                    ::= { digitalObjects 87 }

        -- 1.3.6.1.4.1.9839.2.1.1.88
        buz-22 OBJECT-TYPE
                    SYNTAX Integer32 (0..1)
                    UNITS "N/A"
                    MAX-ACCESS read-only
                    STATUS current
                    DESCRIPTION "ALARM AFM22"
                    ::= { digitalObjects 88 }

        -- 1.3.6.1.4.1.9839.2.1.1.89
        abil-un23 OBJECT-TYPE
                    SYNTAX Integer32 (0..1)
                    UNITS "N/A"
                    MAX-ACCESS read-only
                    STATUS current
                    DESCRIPTION "ENABLE AFM23"
                    ::= { digitalObjects 89 }

        -- 1.3.6.1.4.1.9839.2.1.1.90
        alcu23 OBJECT-TYPE
                    SYNTAX Integer32 (0..1)
                    UNITS "N/A"
                    MAX-ACCESS read-only
                    STATUS current
                    DESCRIPTION "LAN CONNECTION FAILED AFM23"
                    ::= { digitalObjects 90 }

        -- 1.3.6.1.4.1.9839.2.1.1.91
        regol-23 OBJECT-TYPE
                    SYNTAX Integer32 (0..1)
                    UNITS "N/A"
                    MAX-ACCESS read-only
                    STATUS current
                    DESCRIPTION "REGULATION ACTIVE AFM23"
                    ::= { digitalObjects 91 }

        -- 1.3.6.1.4.1.9839.2.1.1.92
        buz-23 OBJECT-TYPE
                    SYNTAX Integer32 (0..1)
                    UNITS "N/A"
                    MAX-ACCESS read-only
                    STATUS current
                    DESCRIPTION "ALARM AFM23"
                    ::= { digitalObjects 92 }

        -- 1.3.6.1.4.1.9839.2.1.1.93
        abil-un24 OBJECT-TYPE
                    SYNTAX Integer32 (0..1)
                    UNITS "N/A"
                    MAX-ACCESS read-only
                    STATUS current
                    DESCRIPTION "ENABLE AFM24"
                    ::= { digitalObjects 93 }

        -- 1.3.6.1.4.1.9839.2.1.1.94
        alcu24 OBJECT-TYPE
                    SYNTAX Integer32 (0..1)
                    UNITS "N/A"
                    MAX-ACCESS read-only
                    STATUS current
                    DESCRIPTION "LAN CONNECTION FAILED AFM24"
                    ::= { digitalObjects 94 }

        -- 1.3.6.1.4.1.9839.2.1.1.95
        regol-24 OBJECT-TYPE
                    SYNTAX Integer32 (0..1)
                    UNITS "N/A"
                    MAX-ACCESS read-only
                    STATUS current
                    DESCRIPTION "REGULATION ACTIVE AFM24"
                    ::= { digitalObjects 95 }

        -- 1.3.6.1.4.1.9839.2.1.1.96
        buz-24 OBJECT-TYPE
                    SYNTAX Integer32 (0..1)
                    UNITS "N/A"
                    MAX-ACCESS read-only
                    STATUS current
                    DESCRIPTION "ALARM AFM24"
                    ::= { digitalObjects 96 }

        -- 1.3.6.1.4.1.9839.2.1.1.97
        abil-un25 OBJECT-TYPE
                    SYNTAX Integer32 (0..1)
                    UNITS "N/A"
                    MAX-ACCESS read-only
                    STATUS current
                    DESCRIPTION "ENABLE AFM25"
                    ::= { digitalObjects 97 }

        -- 1.3.6.1.4.1.9839.2.1.1.98
        alcu25 OBJECT-TYPE
                    SYNTAX Integer32 (0..1)
                    UNITS "N/A"
                    MAX-ACCESS read-only
                    STATUS current
                    DESCRIPTION "LAN CONNECTION FAILED AFM25"
                    ::= { digitalObjects 98 }

        -- 1.3.6.1.4.1.9839.2.1.1.99
        regol-25 OBJECT-TYPE
                    SYNTAX Integer32 (0..1)
                    UNITS "N/A"
                    MAX-ACCESS read-only
                    STATUS current
                    DESCRIPTION "REGULATION ACTIVE AFM25"
                    ::= { digitalObjects 99 }

        -- 1.3.6.1.4.1.9839.2.1.1.100
        buz-25 OBJECT-TYPE
                    SYNTAX Integer32 (0..1)
                    UNITS "N/A"
                    MAX-ACCESS read-only
                    STATUS current
                    DESCRIPTION "ALARM AFM25"
                    ::= { digitalObjects 100 }

        -- 1.3.6.1.4.1.9839.2.1.1.101
        abil-un26 OBJECT-TYPE
                    SYNTAX Integer32 (0..1)
                    UNITS "N/A"
                    MAX-ACCESS read-only
                    STATUS current
                    DESCRIPTION "ENABLE AFM26"
                    ::= { digitalObjects 101 }

        -- 1.3.6.1.4.1.9839.2.1.1.102
        alcu26 OBJECT-TYPE
                    SYNTAX Integer32 (0..1)
                    UNITS "N/A"
                    MAX-ACCESS read-only
                    STATUS current
                    DESCRIPTION "LAN CONNECTION FAILED AFM26"
                    ::= { digitalObjects 102 }

        -- 1.3.6.1.4.1.9839.2.1.1.103
        regol-26 OBJECT-TYPE
                    SYNTAX Integer32 (0..1)
                    UNITS "N/A"
                    MAX-ACCESS read-only
                    STATUS current
                    DESCRIPTION "REGULATION ACTIVE AFM26"
                    ::= { digitalObjects 103 }

        -- 1.3.6.1.4.1.9839.2.1.1.104
        buz-26 OBJECT-TYPE
                    SYNTAX Integer32 (0..1)
                    UNITS "N/A"
                    MAX-ACCESS read-only
                    STATUS current
                    DESCRIPTION "ALARM AFM26"
                    ::= { digitalObjects 104 }

        -- 1.3.6.1.4.1.9839.2.1.1.105
        abil-un27 OBJECT-TYPE
                    SYNTAX Integer32 (0..1)
                    UNITS "N/A"
                    MAX-ACCESS read-only
                    STATUS current
                    DESCRIPTION "ENABLE AFM27"
                    ::= { digitalObjects 105 }

        -- 1.3.6.1.4.1.9839.2.1.1.106
        alcu27 OBJECT-TYPE
                    SYNTAX Integer32 (0..1)
                    UNITS "N/A"
                    MAX-ACCESS read-only
                    STATUS current
                    DESCRIPTION "LAN CONNECTION FAILED AFM27"
                    ::= { digitalObjects 106 }

        -- 1.3.6.1.4.1.9839.2.1.1.107
        regol-27 OBJECT-TYPE
                    SYNTAX Integer32 (0..1)
                    UNITS "N/A"
                    MAX-ACCESS read-only
                    STATUS current
                    DESCRIPTION "REGULATION ACTIVE AFM27"
                    ::= { digitalObjects 107 }

        -- 1.3.6.1.4.1.9839.2.1.1.108
        buz-27 OBJECT-TYPE
                    SYNTAX Integer32 (0..1)
                    UNITS "N/A"
                    MAX-ACCESS read-only
                    STATUS current
                    DESCRIPTION "ALARM AFM27"
                    ::= { digitalObjects 108 }

        -- 1.3.6.1.4.1.9839.2.1.1.109
        abil-un28 OBJECT-TYPE
                    SYNTAX Integer32 (0..1)
                    UNITS "N/A"
                    MAX-ACCESS read-only
                    STATUS current
                    DESCRIPTION "ENABLE AFM28"
                    ::= { digitalObjects 109 }

        -- 1.3.6.1.4.1.9839.2.1.1.110
        alcu28 OBJECT-TYPE
                    SYNTAX Integer32 (0..1)
                    UNITS "N/A"
                    MAX-ACCESS read-only
                    STATUS current
                    DESCRIPTION "LAN CONNECTION FAILED AFM28"
                    ::= { digitalObjects 110 }

        -- 1.3.6.1.4.1.9839.2.1.1.111
        regol-28 OBJECT-TYPE
                    SYNTAX Integer32 (0..1)
                    UNITS "N/A"
                    MAX-ACCESS read-only
                    STATUS current
                    DESCRIPTION "REGULATION ACTIVE AFM28"
                    ::= { digitalObjects 111 }

        -- 1.3.6.1.4.1.9839.2.1.1.112
        buz-28 OBJECT-TYPE
                    SYNTAX Integer32 (0..1)
                    UNITS "N/A"
                    MAX-ACCESS read-only
                    STATUS current
                    DESCRIPTION "ALARM AFM28"
                    ::= { digitalObjects 112 }

        -- 1.3.6.1.4.1.9839.2.1.1.113
        abil-un29 OBJECT-TYPE
                    SYNTAX Integer32 (0..1)
                    UNITS "N/A"
                    MAX-ACCESS read-only
                    STATUS current
                    DESCRIPTION "ENABLE AFM29"
                    ::= { digitalObjects 113 }

        -- 1.3.6.1.4.1.9839.2.1.1.114
        alcu29 OBJECT-TYPE
                    SYNTAX Integer32 (0..1)
                    UNITS "N/A"
                    MAX-ACCESS read-only
                    STATUS current
                    DESCRIPTION "LAN CONNECTION FAILED AFM29"
                    ::= { digitalObjects 114 }

        -- 1.3.6.1.4.1.9839.2.1.1.115
        regol-29 OBJECT-TYPE
                    SYNTAX Integer32 (0..1)
                    UNITS "N/A"
                    MAX-ACCESS read-only
                    STATUS current
                    DESCRIPTION "REGULATION ACTIVE AFM29"
                    ::= { digitalObjects 115 }

        -- 1.3.6.1.4.1.9839.2.1.1.116
        buz-29 OBJECT-TYPE
                    SYNTAX Integer32 (0..1)
                    UNITS "N/A"
                    MAX-ACCESS read-only
                    STATUS current
                    DESCRIPTION "ALARM AFM29"
                    ::= { digitalObjects 116 }

        -- 1.3.6.1.4.1.9839.2.1.1.117
        abil-un30 OBJECT-TYPE
                    SYNTAX Integer32 (0..1)
                    UNITS "N/A"
                    MAX-ACCESS read-only
                    STATUS current
                    DESCRIPTION "ENABLE AFM30"
                    ::= { digitalObjects 117 }

        -- 1.3.6.1.4.1.9839.2.1.1.118
        alcu30 OBJECT-TYPE
                    SYNTAX Integer32 (0..1)
                    UNITS "N/A"
                    MAX-ACCESS read-only
                    STATUS current
                    DESCRIPTION "LAN CONNECTION FAILED AFM30"
                    ::= { digitalObjects 118 }

        -- 1.3.6.1.4.1.9839.2.1.1.119
        regol-30 OBJECT-TYPE
                    SYNTAX Integer32 (0..1)
                    UNITS "N/A"
                    MAX-ACCESS read-only
                    STATUS current
                    DESCRIPTION "REGULATION ACTIVE AFM30"
                    ::= { digitalObjects 119 }

        -- 1.3.6.1.4.1.9839.2.1.1.120
        buz-30 OBJECT-TYPE
                    SYNTAX Integer32 (0..1)
                    UNITS "N/A"
                    MAX-ACCESS read-only
                    STATUS current
                    DESCRIPTION "ALARM AFM30"
                    ::= { digitalObjects 120 }

        -- 1.3.6.1.4.1.9839.2.1.1.121
        res-al OBJECT-TYPE
                    SYNTAX Integer32 (0..1)
                    UNITS "N/A"
                    MAX-ACCESS read-write
                    STATUS current
                    DESCRIPTION "Buzzer and Alarm Unit Reset"
                    ::= { digitalObjects 121 }

        -- 1.3.6.1.4.1.9839.2.1.1.122
        syson-cdz1 OBJECT-TYPE
                    SYNTAX Integer32 (0..1)
                    UNITS "N/A"
                    MAX-ACCESS read-only
                    STATUS current
                    DESCRIPTION "System On (Fan) CDZ 1"
                    ::= { digitalObjects 122 }

        -- 1.3.6.1.4.1.9839.2.1.1.123
        syson-cdz2 OBJECT-TYPE
                    SYNTAX Integer32 (0..1)
                    UNITS "N/A"
                    MAX-ACCESS read-only
                    STATUS current
                    DESCRIPTION "System On (Fan) CDZ 2"
                    ::= { digitalObjects 123 }

        -- 1.3.6.1.4.1.9839.2.1.1.124
        syson-cdz3 OBJECT-TYPE
                    SYNTAX Integer32 (0..1)
                    UNITS "N/A"
                    MAX-ACCESS read-only
                    STATUS current
                    DESCRIPTION "System On (Fan) CDZ 3"
                    ::= { digitalObjects 124 }

        -- 1.3.6.1.4.1.9839.2.1.1.125
        syson-cdz4 OBJECT-TYPE
                    SYNTAX Integer32 (0..1)
                    UNITS "N/A"
                    MAX-ACCESS read-only
                    STATUS current
                    DESCRIPTION "System On (Fan) CDZ 4"
                    ::= { digitalObjects 125 }

        -- 1.3.6.1.4.1.9839.2.1.1.126
        syson-cdz5 OBJECT-TYPE
                    SYNTAX Integer32 (0..1)
                    UNITS "N/A"
                    MAX-ACCESS read-only
                    STATUS current
                    DESCRIPTION "System On (Fan) CDZ 5"
                    ::= { digitalObjects 126 }

        -- 1.3.6.1.4.1.9839.2.1.1.127
        syson-cdz6 OBJECT-TYPE
                    SYNTAX Integer32 (0..1)
                    UNITS "N/A"
                    MAX-ACCESS read-only
                    STATUS current
                    DESCRIPTION "System On (Fan) CDZ 6"
                    ::= { digitalObjects 127 }

        -- 1.3.6.1.4.1.9839.2.1.1.128
        syson-cdz7 OBJECT-TYPE
                    SYNTAX Integer32 (0..1)
                    UNITS "N/A"
                    MAX-ACCESS read-only
                    STATUS current
                    DESCRIPTION "System On (Fan) CDZ 7"
                    ::= { digitalObjects 128 }

        -- 1.3.6.1.4.1.9839.2.1.1.129
        syson-cdz8 OBJECT-TYPE
                    SYNTAX Integer32 (0..1)
                    UNITS "N/A"
                    MAX-ACCESS read-only
                    STATUS current
                    DESCRIPTION "System On (Fan) CDZ 8"
                    ::= { digitalObjects 129 }

        -- 1.3.6.1.4.1.9839.2.1.1.130
        syson-cdz9 OBJECT-TYPE
                    SYNTAX Integer32 (0..1)
                    UNITS "N/A"
                    MAX-ACCESS read-only
                    STATUS current
                    DESCRIPTION "System On (Fan) CDZ 9"
                    ::= { digitalObjects 130 }

        -- 1.3.6.1.4.1.9839.2.1.1.131
        syson-cdz10 OBJECT-TYPE
                    SYNTAX Integer32 (0..1)
                    UNITS "N/A"
                    MAX-ACCESS read-only
                    STATUS current
                    DESCRIPTION "System On (Fan) CDZ 10"
                    ::= { digitalObjects 131 }

        -- 1.3.6.1.4.1.9839.2.1.1.132
        gen-al-cdz1 OBJECT-TYPE
                    SYNTAX Integer32 (0..1)
                    UNITS "N/A"
                    MAX-ACCESS read-only
                    STATUS current
                    DESCRIPTION "General Alarm CDZ1"
                    ::= { digitalObjects 132 }

        -- 1.3.6.1.4.1.9839.2.1.1.133
        gen-al-cdz2 OBJECT-TYPE
                    SYNTAX Integer32 (0..1)
                    UNITS "N/A"
                    MAX-ACCESS read-only
                    STATUS current
                    DESCRIPTION "General Alarm CDZ2"
                    ::= { digitalObjects 133 }

        -- 1.3.6.1.4.1.9839.2.1.1.134
        gen-al-cdz3 OBJECT-TYPE
                    SYNTAX Integer32 (0..1)
                    UNITS "N/A"
                    MAX-ACCESS read-only
                    STATUS current
                    DESCRIPTION "General Alarm CDZ3"
                    ::= { digitalObjects 134 }

        -- 1.3.6.1.4.1.9839.2.1.1.135
        gen-al-cdz4 OBJECT-TYPE
                    SYNTAX Integer32 (0..1)
                    UNITS "N/A"
                    MAX-ACCESS read-only
                    STATUS current
                    DESCRIPTION "General Alarm CDZ4"
                    ::= { digitalObjects 135 }

        -- 1.3.6.1.4.1.9839.2.1.1.136
        gen-al-cdz5 OBJECT-TYPE
                    SYNTAX Integer32 (0..1)
                    UNITS "N/A"
                    MAX-ACCESS read-only
                    STATUS current
                    DESCRIPTION "General Alarm CDZ5"
                    ::= { digitalObjects 136 }

        -- 1.3.6.1.4.1.9839.2.1.1.137
        gen-al-cdz6 OBJECT-TYPE
                    SYNTAX Integer32 (0..1)
                    UNITS "N/A"
                    MAX-ACCESS read-only
                    STATUS current
                    DESCRIPTION "General Alarm CDZ6"
                    ::= { digitalObjects 137 }

        -- 1.3.6.1.4.1.9839.2.1.1.138
        gen-al-cdz7 OBJECT-TYPE
                    SYNTAX Integer32 (0..1)
                    UNITS "N/A"
                    MAX-ACCESS read-only
                    STATUS current
                    DESCRIPTION "General Alarm CDZ7"
                    ::= { digitalObjects 138 }

        -- 1.3.6.1.4.1.9839.2.1.1.139
        gen-al-cdz8 OBJECT-TYPE
                    SYNTAX Integer32 (0..1)
                    UNITS "N/A"
                    MAX-ACCESS read-only
                    STATUS current
                    DESCRIPTION "General Alarm CDZ8"
                    ::= { digitalObjects 139 }

        -- 1.3.6.1.4.1.9839.2.1.1.140
        gen-al-cdz9 OBJECT-TYPE
                    SYNTAX Integer32 (0..1)
                    UNITS "N/A"
                    MAX-ACCESS read-only
                    STATUS current
                    DESCRIPTION "General Alarm CDZ9"
                    ::= { digitalObjects 140 }

        -- 1.3.6.1.4.1.9839.2.1.1.141
        gen-al-cdz10 OBJECT-TYPE
                    SYNTAX Integer32 (0..1)
                    UNITS "N/A"
                    MAX-ACCESS read-only
                    STATUS current
                    DESCRIPTION "General Alarm CDZ10"
                    ::= { digitalObjects 141 }



        -- 1.3.6.1.4.1.9839.2.1.2
        analogObjects OBJECT IDENTIFIER ::= { mstafMIB 2 }

        -- 1.3.6.1.4.1.9839.2.1.2.1
        t1-1 OBJECT-TYPE
                    SYNTAX Integer32 (12345..12345)
                    UNITS "C x10"
                    MAX-ACCESS read-only
                    STATUS current
                    DESCRIPTION "TEMPERATURE 1 AFM1"
                    ::= { analogObjects 1 }

        -- 1.3.6.1.4.1.9839.2.1.2.2
        t1-2 OBJECT-TYPE
                    SYNTAX Integer32 (12345..12345)
                    UNITS "C x10"
                    MAX-ACCESS read-only
                    STATUS current
                    DESCRIPTION "TEMPERATURE 1 AFM2"
                    ::= { analogObjects 2 }

        -- 1.3.6.1.4.1.9839.2.1.2.3
        t1-3 OBJECT-TYPE
                    SYNTAX Integer32 (12345..12345)
                    UNITS "C x10"
                    MAX-ACCESS read-only
                    STATUS current
                    DESCRIPTION "TEMPERATURE 1 AFM3"
                    ::= { analogObjects 3 }

        -- 1.3.6.1.4.1.9839.2.1.2.4
        t1-4 OBJECT-TYPE
                    SYNTAX Integer32 (12345..12345)
                    UNITS "C x10"
                    MAX-ACCESS read-only
                    STATUS current
                    DESCRIPTION "TEMPERATURE 1 AFM4"
                    ::= { analogObjects 4 }

        -- 1.3.6.1.4.1.9839.2.1.2.5
        t1-5 OBJECT-TYPE
                    SYNTAX Integer32 (12345..12345)
                    UNITS "C x10"
                    MAX-ACCESS read-only
                    STATUS current
                    DESCRIPTION "TEMPERATURE 1 AFM5"
                    ::= { analogObjects 5 }

        -- 1.3.6.1.4.1.9839.2.1.2.6
        t1-6 OBJECT-TYPE
                    SYNTAX Integer32 (12345..12345)
                    UNITS "C x10"
                    MAX-ACCESS read-only
                    STATUS current
                    DESCRIPTION "TEMPERATURE 1 AFM6"
                    ::= { analogObjects 6 }

        -- 1.3.6.1.4.1.9839.2.1.2.7
        t1-7 OBJECT-TYPE
                    SYNTAX Integer32 (12345..12345)
                    UNITS "C x10"
                    MAX-ACCESS read-only
                    STATUS current
                    DESCRIPTION "TEMPERATURE 1 AFM7"
                    ::= { analogObjects 7 }

        -- 1.3.6.1.4.1.9839.2.1.2.8
        t1-8 OBJECT-TYPE
                    SYNTAX Integer32 (12345..12345)
                    UNITS "C x10"
                    MAX-ACCESS read-only
                    STATUS current
                    DESCRIPTION "TEMPERATURE 1 AFM8"
                    ::= { analogObjects 8 }

        -- 1.3.6.1.4.1.9839.2.1.2.9
        t1-9 OBJECT-TYPE
                    SYNTAX Integer32 (12345..12345)
                    UNITS "C x10"
                    MAX-ACCESS read-only
                    STATUS current
                    DESCRIPTION "TEMPERATURE 1 AFM9"
                    ::= { analogObjects 9 }

        -- 1.3.6.1.4.1.9839.2.1.2.10
        t1-10 OBJECT-TYPE
                    SYNTAX Integer32 (12345..12345)
                    UNITS "C x10"
                    MAX-ACCESS read-only
                    STATUS current
                    DESCRIPTION "TEMPERATURE 1 AFM10"
                    ::= { analogObjects 10 }

        -- 1.3.6.1.4.1.9839.2.1.2.11
        t1-11 OBJECT-TYPE
                    SYNTAX Integer32 (12345..12345)
                    UNITS "C x10"
                    MAX-ACCESS read-only
                    STATUS current
                    DESCRIPTION "TEMPERATURE 1 AFM11"
                    ::= { analogObjects 11 }

        -- 1.3.6.1.4.1.9839.2.1.2.12
        t1-12 OBJECT-TYPE
                    SYNTAX Integer32 (12345..12345)
                    UNITS "C x10"
                    MAX-ACCESS read-only
                    STATUS current
                    DESCRIPTION "TEMPERATURE 1 AFM12"
                    ::= { analogObjects 12 }

        -- 1.3.6.1.4.1.9839.2.1.2.13
        t1-13 OBJECT-TYPE
                    SYNTAX Integer32 (12345..12345)
                    UNITS "C x10"
                    MAX-ACCESS read-only
                    STATUS current
                    DESCRIPTION "TEMPERATURE 1 AFM13"
                    ::= { analogObjects 13 }

        -- 1.3.6.1.4.1.9839.2.1.2.14
        t1-14 OBJECT-TYPE
                    SYNTAX Integer32 (12345..12345)
                    UNITS "C x10"
                    MAX-ACCESS read-only
                    STATUS current
                    DESCRIPTION "TEMPERATURE 1 AFM14"
                    ::= { analogObjects 14 }

        -- 1.3.6.1.4.1.9839.2.1.2.15
        t1-15 OBJECT-TYPE
                    SYNTAX Integer32 (12345..12345)
                    UNITS "C x10"
                    MAX-ACCESS read-only
                    STATUS current
                    DESCRIPTION "TEMPERATURE 1 AFM15"
                    ::= { analogObjects 15 }

        -- 1.3.6.1.4.1.9839.2.1.2.16
        t1-16 OBJECT-TYPE
                    SYNTAX Integer32 (12345..12345)
                    UNITS "C x10"
                    MAX-ACCESS read-only
                    STATUS current
                    DESCRIPTION "TEMPERATURE 1 AFM16"
                    ::= { analogObjects 16 }

        -- 1.3.6.1.4.1.9839.2.1.2.17
        t1-17 OBJECT-TYPE
                    SYNTAX Integer32 (12345..12345)
                    UNITS "C x10"
                    MAX-ACCESS read-only
                    STATUS current
                    DESCRIPTION "TEMPERATURE 1 AFM17"
                    ::= { analogObjects 17 }

        -- 1.3.6.1.4.1.9839.2.1.2.18
        t1-18 OBJECT-TYPE
                    SYNTAX Integer32 (12345..12345)
                    UNITS "C x10"
                    MAX-ACCESS read-only
                    STATUS current
                    DESCRIPTION "TEMPERATURE 1 AFM18"
                    ::= { analogObjects 18 }

        -- 1.3.6.1.4.1.9839.2.1.2.19
        t1-19 OBJECT-TYPE
                    SYNTAX Integer32 (12345..12345)
                    UNITS "C x10"
                    MAX-ACCESS read-only
                    STATUS current
                    DESCRIPTION "TEMPERATURE 1 AFM19"
                    ::= { analogObjects 19 }

        -- 1.3.6.1.4.1.9839.2.1.2.20
        t1-20 OBJECT-TYPE
                    SYNTAX Integer32 (12345..12345)
                    UNITS "C x10"
                    MAX-ACCESS read-only
                    STATUS current
                    DESCRIPTION "TEMPERATURE 1 AFM20"
                    ::= { analogObjects 20 }

        -- 1.3.6.1.4.1.9839.2.1.2.21
        t1-21 OBJECT-TYPE
                    SYNTAX Integer32 (12345..12345)
                    UNITS "C x10"
                    MAX-ACCESS read-only
                    STATUS current
                    DESCRIPTION "TEMPERATURE 1 AFM21"
                    ::= { analogObjects 21 }

        -- 1.3.6.1.4.1.9839.2.1.2.22
        t1-22 OBJECT-TYPE
                    SYNTAX Integer32 (12345..12345)
                    UNITS "C x10"
                    MAX-ACCESS read-only
                    STATUS current
                    DESCRIPTION "TEMPERATURE 1 AFM22"
                    ::= { analogObjects 22 }

        -- 1.3.6.1.4.1.9839.2.1.2.23
        t1-23 OBJECT-TYPE
                    SYNTAX Integer32 (12345..12345)
                    UNITS "C x10"
                    MAX-ACCESS read-only
                    STATUS current
                    DESCRIPTION "TEMPERATURE 1 AFM23"
                    ::= { analogObjects 23 }

        -- 1.3.6.1.4.1.9839.2.1.2.24
        t1-24 OBJECT-TYPE
                    SYNTAX Integer32 (12345..12345)
                    UNITS "C x10"
                    MAX-ACCESS read-only
                    STATUS current
                    DESCRIPTION "TEMPERATURE 1 AFM24"
                    ::= { analogObjects 24 }

        -- 1.3.6.1.4.1.9839.2.1.2.25
        t1-25 OBJECT-TYPE
                    SYNTAX Integer32 (12345..12345)
                    UNITS "C x10"
                    MAX-ACCESS read-only
                    STATUS current
                    DESCRIPTION "TEMPERATURE 1 AFM25"
                    ::= { analogObjects 25 }

        -- 1.3.6.1.4.1.9839.2.1.2.26
        t1-26 OBJECT-TYPE
                    SYNTAX Integer32 (12345..12345)
                    UNITS "C x10"
                    MAX-ACCESS read-only
                    STATUS current
                    DESCRIPTION "TEMPERATURE 1 AFM26"
                    ::= { analogObjects 26 }

        -- 1.3.6.1.4.1.9839.2.1.2.27
        t1-27 OBJECT-TYPE
                    SYNTAX Integer32 (12345..12345)
                    UNITS "C x10"
                    MAX-ACCESS read-only
                    STATUS current
                    DESCRIPTION "TEMPERATURE 1 AFM27"
                    ::= { analogObjects 27 }

        -- 1.3.6.1.4.1.9839.2.1.2.28
        t1-28 OBJECT-TYPE
                    SYNTAX Integer32 (12345..12345)
                    UNITS "C x10"
                    MAX-ACCESS read-only
                    STATUS current
                    DESCRIPTION "TEMPERATURE 1 AFM28"
                    ::= { analogObjects 28 }

        -- 1.3.6.1.4.1.9839.2.1.2.29
        t1-29 OBJECT-TYPE
                    SYNTAX Integer32 (12345..12345)
                    UNITS "C x10"
                    MAX-ACCESS read-only
                    STATUS current
                    DESCRIPTION "TEMPERATURE 1 AFM29"
                    ::= { analogObjects 29 }

        -- 1.3.6.1.4.1.9839.2.1.2.30
        t1-30 OBJECT-TYPE
                    SYNTAX Integer32 (12345..12345)
                    UNITS "C x10"
                    MAX-ACCESS read-only
                    STATUS current
                    DESCRIPTION "TEMPERATURE 1 AFM30"
                    ::= { analogObjects 30 }

        -- 1.3.6.1.4.1.9839.2.1.2.31
        t2-1 OBJECT-TYPE
                    SYNTAX Integer32 (12345..12345)
                    UNITS "C x10"
                    MAX-ACCESS read-only
                    STATUS current
                    DESCRIPTION "TEMPERATURE 2 AFM1"
                    ::= { analogObjects 31 }

        -- 1.3.6.1.4.1.9839.2.1.2.32
        t2-2 OBJECT-TYPE
                    SYNTAX Integer32 (12345..12345)
                    UNITS "C x10"
                    MAX-ACCESS read-only
                    STATUS current
                    DESCRIPTION "TEMPERATURE 2 AFM2"
                    ::= { analogObjects 32 }

        -- 1.3.6.1.4.1.9839.2.1.2.33
        t2-3 OBJECT-TYPE
                    SYNTAX Integer32 (12345..12345)
                    UNITS "C x10"
                    MAX-ACCESS read-only
                    STATUS current
                    DESCRIPTION "TEMPERATURE 2 AFM3"
                    ::= { analogObjects 33 }

        -- 1.3.6.1.4.1.9839.2.1.2.34
        t2-4 OBJECT-TYPE
                    SYNTAX Integer32 (12345..12345)
                    UNITS "C x10"
                    MAX-ACCESS read-only
                    STATUS current
                    DESCRIPTION "TEMPERATURE 2 AFM4"
                    ::= { analogObjects 34 }

        -- 1.3.6.1.4.1.9839.2.1.2.35
        t2-5 OBJECT-TYPE
                    SYNTAX Integer32 (12345..12345)
                    UNITS "C x10"
                    MAX-ACCESS read-only
                    STATUS current
                    DESCRIPTION "TEMPERATURE 2 AFM5"
                    ::= { analogObjects 35 }

        -- 1.3.6.1.4.1.9839.2.1.2.36
        t2-6 OBJECT-TYPE
                    SYNTAX Integer32 (12345..12345)
                    UNITS "C x10"
                    MAX-ACCESS read-only
                    STATUS current
                    DESCRIPTION "TEMPERATURE 2 AFM6"
                    ::= { analogObjects 36 }

        -- 1.3.6.1.4.1.9839.2.1.2.37
        t2-7 OBJECT-TYPE
                    SYNTAX Integer32 (12345..12345)
                    UNITS "C x10"
                    MAX-ACCESS read-only
                    STATUS current
                    DESCRIPTION "TEMPERATURE 2 AFM7"
                    ::= { analogObjects 37 }

        -- 1.3.6.1.4.1.9839.2.1.2.38
        t2-8 OBJECT-TYPE
                    SYNTAX Integer32 (12345..12345)
                    UNITS "C x10"
                    MAX-ACCESS read-only
                    STATUS current
                    DESCRIPTION "TEMPERATURE 2 AFM8"
                    ::= { analogObjects 38 }

        -- 1.3.6.1.4.1.9839.2.1.2.39
        t2-9 OBJECT-TYPE
                    SYNTAX Integer32 (12345..12345)
                    UNITS "C x10"
                    MAX-ACCESS read-only
                    STATUS current
                    DESCRIPTION "TEMPERATURE 2 AFM9"
                    ::= { analogObjects 39 }

        -- 1.3.6.1.4.1.9839.2.1.2.40
        t2-10 OBJECT-TYPE
                    SYNTAX Integer32 (12345..12345)
                    UNITS "C x10"
                    MAX-ACCESS read-only
                    STATUS current
                    DESCRIPTION "TEMPERATURE 2 AFM10"
                    ::= { analogObjects 40 }

        -- 1.3.6.1.4.1.9839.2.1.2.41
        t2-11 OBJECT-TYPE
                    SYNTAX Integer32 (12345..12345)
                    UNITS "C x10"
                    MAX-ACCESS read-only
                    STATUS current
                    DESCRIPTION "TEMPERATURE 2 AFM11"
                    ::= { analogObjects 41 }

        -- 1.3.6.1.4.1.9839.2.1.2.42
        t2-12 OBJECT-TYPE
                    SYNTAX Integer32 (12345..12345)
                    UNITS "C x10"
                    MAX-ACCESS read-only
                    STATUS current
                    DESCRIPTION "TEMPERATURE 2 AFM12"
                    ::= { analogObjects 42 }

        -- 1.3.6.1.4.1.9839.2.1.2.43
        t2-13 OBJECT-TYPE
                    SYNTAX Integer32 (12345..12345)
                    UNITS "C x10"
                    MAX-ACCESS read-only
                    STATUS current
                    DESCRIPTION "TEMPERATURE 2 AFM13"
                    ::= { analogObjects 43 }

        -- 1.3.6.1.4.1.9839.2.1.2.44
        t2-14 OBJECT-TYPE
                    SYNTAX Integer32 (12345..12345)
                    UNITS "C x10"
                    MAX-ACCESS read-only
                    STATUS current
                    DESCRIPTION "TEMPERATURE 2 AFM14"
                    ::= { analogObjects 44 }

        -- 1.3.6.1.4.1.9839.2.1.2.45
        t2-15 OBJECT-TYPE
                    SYNTAX Integer32 (12345..12345)
                    UNITS "C x10"
                    MAX-ACCESS read-only
                    STATUS current
                    DESCRIPTION "TEMPERATURE 2 AFM15"
                    ::= { analogObjects 45 }

        -- 1.3.6.1.4.1.9839.2.1.2.46
        t2-16 OBJECT-TYPE
                    SYNTAX Integer32 (12345..12345)
                    UNITS "C x10"
                    MAX-ACCESS read-only
                    STATUS current
                    DESCRIPTION "TEMPERATURE 2 AFM16"
                    ::= { analogObjects 46 }

        -- 1.3.6.1.4.1.9839.2.1.2.47
        t2-17 OBJECT-TYPE
                    SYNTAX Integer32 (12345..12345)
                    UNITS "C x10"
                    MAX-ACCESS read-only
                    STATUS current
                    DESCRIPTION "TEMPERATURE 2 AFM17"
                    ::= { analogObjects 47 }

        -- 1.3.6.1.4.1.9839.2.1.2.48
        t2-18 OBJECT-TYPE
                    SYNTAX Integer32 (12345..12345)
                    UNITS "C x10"
                    MAX-ACCESS read-only
                    STATUS current
                    DESCRIPTION "TEMPERATURE 2 AFM18"
                    ::= { analogObjects 48 }

        -- 1.3.6.1.4.1.9839.2.1.2.49
        t2-19 OBJECT-TYPE
                    SYNTAX Integer32 (12345..12345)
                    UNITS "C x10"
                    MAX-ACCESS read-only
                    STATUS current
                    DESCRIPTION "TEMPERATURE 2 AFM19"
                    ::= { analogObjects 49 }

        -- 1.3.6.1.4.1.9839.2.1.2.50
        t2-20 OBJECT-TYPE
                    SYNTAX Integer32 (12345..12345)
                    UNITS "C x10"
                    MAX-ACCESS read-only
                    STATUS current
                    DESCRIPTION "TEMPERATURE 2 AFM20"
                    ::= { analogObjects 50 }

        -- 1.3.6.1.4.1.9839.2.1.2.51
        t2-21 OBJECT-TYPE
                    SYNTAX Integer32 (12345..12345)
                    UNITS "C x10"
                    MAX-ACCESS read-only
                    STATUS current
                    DESCRIPTION "TEMPERATURE 2 AFM21"
                    ::= { analogObjects 51 }

        -- 1.3.6.1.4.1.9839.2.1.2.52
        t2-22 OBJECT-TYPE
                    SYNTAX Integer32 (12345..12345)
                    UNITS "C x10"
                    MAX-ACCESS read-only
                    STATUS current
                    DESCRIPTION "TEMPERATURE 2 AFM22"
                    ::= { analogObjects 52 }

        -- 1.3.6.1.4.1.9839.2.1.2.53
        t2-23 OBJECT-TYPE
                    SYNTAX Integer32 (12345..12345)
                    UNITS "C x10"
                    MAX-ACCESS read-only
                    STATUS current
                    DESCRIPTION "TEMPERATURE 2 AFM23"
                    ::= { analogObjects 53 }

        -- 1.3.6.1.4.1.9839.2.1.2.54
        t2-24 OBJECT-TYPE
                    SYNTAX Integer32 (12345..12345)
                    UNITS "C x10"
                    MAX-ACCESS read-only
                    STATUS current
                    DESCRIPTION "TEMPERATURE 2 AFM24"
                    ::= { analogObjects 54 }

        -- 1.3.6.1.4.1.9839.2.1.2.55
        t2-25 OBJECT-TYPE
                    SYNTAX Integer32 (12345..12345)
                    UNITS "C x10"
                    MAX-ACCESS read-only
                    STATUS current
                    DESCRIPTION "TEMPERATURE 2 AFM25"
                    ::= { analogObjects 55 }

        -- 1.3.6.1.4.1.9839.2.1.2.56
        t2-26 OBJECT-TYPE
                    SYNTAX Integer32 (12345..12345)
                    UNITS "C x10"
                    MAX-ACCESS read-only
                    STATUS current
                    DESCRIPTION "TEMPERATURE 2 AFM26"
                    ::= { analogObjects 56 }

        -- 1.3.6.1.4.1.9839.2.1.2.57
        t2-27 OBJECT-TYPE
                    SYNTAX Integer32 (12345..12345)
                    UNITS "C x10"
                    MAX-ACCESS read-only
                    STATUS current
                    DESCRIPTION "TEMPERATURE 2 AFM27"
                    ::= { analogObjects 57 }

        -- 1.3.6.1.4.1.9839.2.1.2.58
        t2-28 OBJECT-TYPE
                    SYNTAX Integer32 (12345..12345)
                    UNITS "C x10"
                    MAX-ACCESS read-only
                    STATUS current
                    DESCRIPTION "TEMPERATURE 2 AFM28"
                    ::= { analogObjects 58 }

        -- 1.3.6.1.4.1.9839.2.1.2.59
        t2-29 OBJECT-TYPE
                    SYNTAX Integer32 (12345..12345)
                    UNITS "C x10"
                    MAX-ACCESS read-only
                    STATUS current
                    DESCRIPTION "TEMPERATURE 2 AFM29"
                    ::= { analogObjects 59 }

        -- 1.3.6.1.4.1.9839.2.1.2.60
        t2-30 OBJECT-TYPE
                    SYNTAX Integer32 (12345..12345)
                    UNITS "C x10"
                    MAX-ACCESS read-only
                    STATUS current
                    DESCRIPTION "TEMPERATURE 2 AFM30"
                    ::= { analogObjects 60 }

        -- 1.3.6.1.4.1.9839.2.1.2.61
        sp-1 OBJECT-TYPE
                    SYNTAX Integer32 (200..500)
                    UNITS "C x10"
                    MAX-ACCESS read-write
                    STATUS current
                    DESCRIPTION "SETPOINT AFM1"
                    ::= { analogObjects 61 }

        -- 1.3.6.1.4.1.9839.2.1.2.62
        sp-2 OBJECT-TYPE
                    SYNTAX Integer32 (200..500)
                    UNITS "C x10"
                    MAX-ACCESS read-write
                    STATUS current
                    DESCRIPTION "SETPOINT AFM2"
                    ::= { analogObjects 62 }

        -- 1.3.6.1.4.1.9839.2.1.2.63
        sp-3 OBJECT-TYPE
                    SYNTAX Integer32 (200..500)
                    UNITS "C x10"
                    MAX-ACCESS read-write
                    STATUS current
                    DESCRIPTION "SETPOINT AFM3"
                    ::= { analogObjects 63 }

        -- 1.3.6.1.4.1.9839.2.1.2.64
        sp-4 OBJECT-TYPE
                    SYNTAX Integer32 (200..500)
                    UNITS "C x10"
                    MAX-ACCESS read-write
                    STATUS current
                    DESCRIPTION "SETPOINT AFM4"
                    ::= { analogObjects 64 }

        -- 1.3.6.1.4.1.9839.2.1.2.65
        sp-5 OBJECT-TYPE
                    SYNTAX Integer32 (200..500)
                    UNITS "C x10"
                    MAX-ACCESS read-write
                    STATUS current
                    DESCRIPTION "SETPOINT AFM5"
                    ::= { analogObjects 65 }

        -- 1.3.6.1.4.1.9839.2.1.2.66
        sp-6 OBJECT-TYPE
                    SYNTAX Integer32 (200..500)
                    UNITS "C x10"
                    MAX-ACCESS read-write
                    STATUS current
                    DESCRIPTION "SETPOINT AFM6"
                    ::= { analogObjects 66 }

        -- 1.3.6.1.4.1.9839.2.1.2.67
        sp-7 OBJECT-TYPE
                    SYNTAX Integer32 (200..500)
                    UNITS "C x10"
                    MAX-ACCESS read-write
                    STATUS current
                    DESCRIPTION "SETPOINT AFM7"
                    ::= { analogObjects 67 }

        -- 1.3.6.1.4.1.9839.2.1.2.68
        sp-8 OBJECT-TYPE
                    SYNTAX Integer32 (200..500)
                    UNITS "C x10"
                    MAX-ACCESS read-write
                    STATUS current
                    DESCRIPTION "SETPOINT AFM8"
                    ::= { analogObjects 68 }

        -- 1.3.6.1.4.1.9839.2.1.2.69
        sp-9 OBJECT-TYPE
                    SYNTAX Integer32 (200..500)
                    UNITS "C x10"
                    MAX-ACCESS read-write
                    STATUS current
                    DESCRIPTION "SETPOINT AFM9"
                    ::= { analogObjects 69 }

        -- 1.3.6.1.4.1.9839.2.1.2.70
        sp-10 OBJECT-TYPE
                    SYNTAX Integer32 (200..500)
                    UNITS "C x10"
                    MAX-ACCESS read-write
                    STATUS current
                    DESCRIPTION "SETPOINT AFM10"
                    ::= { analogObjects 70 }

        -- 1.3.6.1.4.1.9839.2.1.2.71
        sp-11 OBJECT-TYPE
                    SYNTAX Integer32 (200..500)
                    UNITS "C x10"
                    MAX-ACCESS read-write
                    STATUS current
                    DESCRIPTION "SETPOINT AFM11"
                    ::= { analogObjects 71 }

        -- 1.3.6.1.4.1.9839.2.1.2.72
        sp-12 OBJECT-TYPE
                    SYNTAX Integer32 (200..500)
                    UNITS "C x10"
                    MAX-ACCESS read-write
                    STATUS current
                    DESCRIPTION "SETPOINT AFM12"
                    ::= { analogObjects 72 }

        -- 1.3.6.1.4.1.9839.2.1.2.73
        sp-13 OBJECT-TYPE
                    SYNTAX Integer32 (200..500)
                    UNITS "C x10"
                    MAX-ACCESS read-write
                    STATUS current
                    DESCRIPTION "SETPOINT AFM13"
                    ::= { analogObjects 73 }

        -- 1.3.6.1.4.1.9839.2.1.2.74
        sp-14 OBJECT-TYPE
                    SYNTAX Integer32 (200..500)
                    UNITS "C x10"
                    MAX-ACCESS read-write
                    STATUS current
                    DESCRIPTION "SETPOINT AFM14"
                    ::= { analogObjects 74 }

        -- 1.3.6.1.4.1.9839.2.1.2.75
        sp-15 OBJECT-TYPE
                    SYNTAX Integer32 (200..500)
                    UNITS "C x10"
                    MAX-ACCESS read-write
                    STATUS current
                    DESCRIPTION "SETPOINT AFM15"
                    ::= { analogObjects 75 }

        -- 1.3.6.1.4.1.9839.2.1.2.76
        sp-16 OBJECT-TYPE
                    SYNTAX Integer32 (200..500)
                    UNITS "C x10"
                    MAX-ACCESS read-write
                    STATUS current
                    DESCRIPTION "SETPOINT AFM16"
                    ::= { analogObjects 76 }

        -- 1.3.6.1.4.1.9839.2.1.2.77
        sp-17 OBJECT-TYPE
                    SYNTAX Integer32 (200..500)
                    UNITS "C x10"
                    MAX-ACCESS read-write
                    STATUS current
                    DESCRIPTION "SETPOINT AFM17"
                    ::= { analogObjects 77 }

        -- 1.3.6.1.4.1.9839.2.1.2.78
        sp-18 OBJECT-TYPE
                    SYNTAX Integer32 (200..500)
                    UNITS "C x10"
                    MAX-ACCESS read-write
                    STATUS current
                    DESCRIPTION "SETPOINT AFM18"
                    ::= { analogObjects 78 }

        -- 1.3.6.1.4.1.9839.2.1.2.79
        sp-19 OBJECT-TYPE
                    SYNTAX Integer32 (200..500)
                    UNITS "C x10"
                    MAX-ACCESS read-write
                    STATUS current
                    DESCRIPTION "SETPOINT AFM19"
                    ::= { analogObjects 79 }

        -- 1.3.6.1.4.1.9839.2.1.2.80
        sp-20 OBJECT-TYPE
                    SYNTAX Integer32 (200..500)
                    UNITS "C x10"
                    MAX-ACCESS read-write
                    STATUS current
                    DESCRIPTION "SETPOINT AFM20"
                    ::= { analogObjects 80 }

        -- 1.3.6.1.4.1.9839.2.1.2.81
        sp-21 OBJECT-TYPE
                    SYNTAX Integer32 (200..500)
                    UNITS "C x10"
                    MAX-ACCESS read-write
                    STATUS current
                    DESCRIPTION "SETPOINT AFM21"
                    ::= { analogObjects 81 }

        -- 1.3.6.1.4.1.9839.2.1.2.82
        sp-22 OBJECT-TYPE
                    SYNTAX Integer32 (200..500)
                    UNITS "C x10"
                    MAX-ACCESS read-write
                    STATUS current
                    DESCRIPTION "SETPOINT AFM22"
                    ::= { analogObjects 82 }

        -- 1.3.6.1.4.1.9839.2.1.2.83
        sp-23 OBJECT-TYPE
                    SYNTAX Integer32 (200..500)
                    UNITS "C x10"
                    MAX-ACCESS read-write
                    STATUS current
                    DESCRIPTION "SETPOINT AFM23"
                    ::= { analogObjects 83 }

        -- 1.3.6.1.4.1.9839.2.1.2.84
        sp-24 OBJECT-TYPE
                    SYNTAX Integer32 (200..500)
                    UNITS "C x10"
                    MAX-ACCESS read-write
                    STATUS current
                    DESCRIPTION "SETPOINT AFM24"
                    ::= { analogObjects 84 }

        -- 1.3.6.1.4.1.9839.2.1.2.85
        sp-25 OBJECT-TYPE
                    SYNTAX Integer32 (200..500)
                    UNITS "C x10"
                    MAX-ACCESS read-write
                    STATUS current
                    DESCRIPTION "SETPOINT AFM25"
                    ::= { analogObjects 85 }

        -- 1.3.6.1.4.1.9839.2.1.2.86
        sp-26 OBJECT-TYPE
                    SYNTAX Integer32 (200..500)
                    UNITS "C x10"
                    MAX-ACCESS read-write
                    STATUS current
                    DESCRIPTION "SETPOINT AFM26"
                    ::= { analogObjects 86 }

        -- 1.3.6.1.4.1.9839.2.1.2.87
        sp-27 OBJECT-TYPE
                    SYNTAX Integer32 (200..500)
                    UNITS "C x10"
                    MAX-ACCESS read-write
                    STATUS current
                    DESCRIPTION "SETPOINT AFM27"
                    ::= { analogObjects 87 }

        -- 1.3.6.1.4.1.9839.2.1.2.88
        sp-28 OBJECT-TYPE
                    SYNTAX Integer32 (200..500)
                    UNITS "C x10"
                    MAX-ACCESS read-write
                    STATUS current
                    DESCRIPTION "SETPOINT AFM28"
                    ::= { analogObjects 88 }

        -- 1.3.6.1.4.1.9839.2.1.2.89
        sp-29 OBJECT-TYPE
                    SYNTAX Integer32 (200..500)
                    UNITS "C x10"
                    MAX-ACCESS read-write
                    STATUS current
                    DESCRIPTION "SETPOINT AFM29"
                    ::= { analogObjects 89 }

        -- 1.3.6.1.4.1.9839.2.1.2.90
        sp-30 OBJECT-TYPE
                    SYNTAX Integer32 (200..500)
                    UNITS "C x10"
                    MAX-ACCESS read-write
                    STATUS current
                    DESCRIPTION "SETPOINT AFM30"
                    ::= { analogObjects 90 }

        -- 1.3.6.1.4.1.9839.2.1.2.91
        bp-1 OBJECT-TYPE
                    SYNTAX Integer32 (10..300)
                    UNITS "C x10"
                    MAX-ACCESS read-write
                    STATUS current
                    DESCRIPTION "DIFFERENTIAL AFM1"
                    ::= { analogObjects 91 }

        -- 1.3.6.1.4.1.9839.2.1.2.92
        bp-2 OBJECT-TYPE
                    SYNTAX Integer32 (10..300)
                    UNITS "C x10"
                    MAX-ACCESS read-write
                    STATUS current
                    DESCRIPTION "DIFFERENTIAL AFM2"
                    ::= { analogObjects 92 }

        -- 1.3.6.1.4.1.9839.2.1.2.93
        bp-3 OBJECT-TYPE
                    SYNTAX Integer32 (10..300)
                    UNITS "C x10"
                    MAX-ACCESS read-write
                    STATUS current
                    DESCRIPTION "DIFFERENTIAL AFM3"
                    ::= { analogObjects 93 }

        -- 1.3.6.1.4.1.9839.2.1.2.94
        bp-4 OBJECT-TYPE
                    SYNTAX Integer32 (10..300)
                    UNITS "C x10"
                    MAX-ACCESS read-write
                    STATUS current
                    DESCRIPTION "DIFFERENTIAL AFM4"
                    ::= { analogObjects 94 }

        -- 1.3.6.1.4.1.9839.2.1.2.95
        bp-5 OBJECT-TYPE
                    SYNTAX Integer32 (10..300)
                    UNITS "C x10"
                    MAX-ACCESS read-write
                    STATUS current
                    DESCRIPTION "DIFFERENTIAL AFM5"
                    ::= { analogObjects 95 }

        -- 1.3.6.1.4.1.9839.2.1.2.96
        bp-6 OBJECT-TYPE
                    SYNTAX Integer32 (10..300)
                    UNITS "C x10"
                    MAX-ACCESS read-write
                    STATUS current
                    DESCRIPTION "DIFFERENTIAL AFM6"
                    ::= { analogObjects 96 }

        -- 1.3.6.1.4.1.9839.2.1.2.97
        bp-7 OBJECT-TYPE
                    SYNTAX Integer32 (10..300)
                    UNITS "C x10"
                    MAX-ACCESS read-write
                    STATUS current
                    DESCRIPTION "DIFFERENTIAL AFM7"
                    ::= { analogObjects 97 }

        -- 1.3.6.1.4.1.9839.2.1.2.98
        bp-8 OBJECT-TYPE
                    SYNTAX Integer32 (10..300)
                    UNITS "C x10"
                    MAX-ACCESS read-write
                    STATUS current
                    DESCRIPTION "DIFFERENTIAL AFM8"
                    ::= { analogObjects 98 }

        -- 1.3.6.1.4.1.9839.2.1.2.99
        bp-9 OBJECT-TYPE
                    SYNTAX Integer32 (10..300)
                    UNITS "C x10"
                    MAX-ACCESS read-write
                    STATUS current
                    DESCRIPTION "DIFFERENTIAL AFM9"
                    ::= { analogObjects 99 }

        -- 1.3.6.1.4.1.9839.2.1.2.100
        bp-10 OBJECT-TYPE
                    SYNTAX Integer32 (10..300)
                    UNITS "C x10"
                    MAX-ACCESS read-write
                    STATUS current
                    DESCRIPTION "DIFFERENTIAL AFM10"
                    ::= { analogObjects 100 }

        -- 1.3.6.1.4.1.9839.2.1.2.101
        bp-11 OBJECT-TYPE
                    SYNTAX Integer32 (10..300)
                    UNITS "C x10"
                    MAX-ACCESS read-write
                    STATUS current
                    DESCRIPTION "DIFFERENTIAL AFM11"
                    ::= { analogObjects 101 }

        -- 1.3.6.1.4.1.9839.2.1.2.102
        bp-12 OBJECT-TYPE
                    SYNTAX Integer32 (10..300)
                    UNITS "C x10"
                    MAX-ACCESS read-write
                    STATUS current
                    DESCRIPTION "DIFFERENTIAL AFM12"
                    ::= { analogObjects 102 }

        -- 1.3.6.1.4.1.9839.2.1.2.103
        bp-13 OBJECT-TYPE
                    SYNTAX Integer32 (10..300)
                    UNITS "C x10"
                    MAX-ACCESS read-write
                    STATUS current
                    DESCRIPTION "DIFFERENTIAL AFM13"
                    ::= { analogObjects 103 }

        -- 1.3.6.1.4.1.9839.2.1.2.104
        bp-14 OBJECT-TYPE
                    SYNTAX Integer32 (10..300)
                    UNITS "C x10"
                    MAX-ACCESS read-write
                    STATUS current
                    DESCRIPTION "DIFFERENTIAL AFM14"
                    ::= { analogObjects 104 }

        -- 1.3.6.1.4.1.9839.2.1.2.105
        bp-15 OBJECT-TYPE
                    SYNTAX Integer32 (10..300)
                    UNITS "C x10"
                    MAX-ACCESS read-write
                    STATUS current
                    DESCRIPTION "DIFFERENTIAL AFM15"
                    ::= { analogObjects 105 }

        -- 1.3.6.1.4.1.9839.2.1.2.106
        bp-16 OBJECT-TYPE
                    SYNTAX Integer32 (10..300)
                    UNITS "C x10"
                    MAX-ACCESS read-write
                    STATUS current
                    DESCRIPTION "DIFFERENTIAL AFM16"
                    ::= { analogObjects 106 }

        -- 1.3.6.1.4.1.9839.2.1.2.107
        bp-17 OBJECT-TYPE
                    SYNTAX Integer32 (10..300)
                    UNITS "C x10"
                    MAX-ACCESS read-write
                    STATUS current
                    DESCRIPTION "DIFFERENTIAL AFM17"
                    ::= { analogObjects 107 }

        -- 1.3.6.1.4.1.9839.2.1.2.108
        bp-18 OBJECT-TYPE
                    SYNTAX Integer32 (10..300)
                    UNITS "C x10"
                    MAX-ACCESS read-write
                    STATUS current
                    DESCRIPTION "DIFFERENTIAL AFM18"
                    ::= { analogObjects 108 }

        -- 1.3.6.1.4.1.9839.2.1.2.109
        bp-19 OBJECT-TYPE
                    SYNTAX Integer32 (10..300)
                    UNITS "C x10"
                    MAX-ACCESS read-write
                    STATUS current
                    DESCRIPTION "DIFFERENTIAL AFM19"
                    ::= { analogObjects 109 }

        -- 1.3.6.1.4.1.9839.2.1.2.110
        bp-20 OBJECT-TYPE
                    SYNTAX Integer32 (10..300)
                    UNITS "C x10"
                    MAX-ACCESS read-write
                    STATUS current
                    DESCRIPTION "DIFFERENTIAL AFM20"
                    ::= { analogObjects 110 }

        -- 1.3.6.1.4.1.9839.2.1.2.111
        bp-21 OBJECT-TYPE
                    SYNTAX Integer32 (10..300)
                    UNITS "C x10"
                    MAX-ACCESS read-write
                    STATUS current
                    DESCRIPTION "DIFFERENTIAL AFM21"
                    ::= { analogObjects 111 }

        -- 1.3.6.1.4.1.9839.2.1.2.112
        bp-22 OBJECT-TYPE
                    SYNTAX Integer32 (10..300)
                    UNITS "C x10"
                    MAX-ACCESS read-write
                    STATUS current
                    DESCRIPTION "DIFFERENTIAL AFM22"
                    ::= { analogObjects 112 }

        -- 1.3.6.1.4.1.9839.2.1.2.113
        bp-23 OBJECT-TYPE
                    SYNTAX Integer32 (10..300)
                    UNITS "C x10"
                    MAX-ACCESS read-write
                    STATUS current
                    DESCRIPTION "DIFFERENTIAL AFM23"
                    ::= { analogObjects 113 }

        -- 1.3.6.1.4.1.9839.2.1.2.114
        bp-24 OBJECT-TYPE
                    SYNTAX Integer32 (10..300)
                    UNITS "C x10"
                    MAX-ACCESS read-write
                    STATUS current
                    DESCRIPTION "DIFFERENTIAL AFM24"
                    ::= { analogObjects 114 }

        -- 1.3.6.1.4.1.9839.2.1.2.115
        bp-25 OBJECT-TYPE
                    SYNTAX Integer32 (10..300)
                    UNITS "C x10"
                    MAX-ACCESS read-write
                    STATUS current
                    DESCRIPTION "DIFFERENTIAL AFM25"
                    ::= { analogObjects 115 }

        -- 1.3.6.1.4.1.9839.2.1.2.116
        bp-26 OBJECT-TYPE
                    SYNTAX Integer32 (10..300)
                    UNITS "C x10"
                    MAX-ACCESS read-write
                    STATUS current
                    DESCRIPTION "DIFFERENTIAL AFM26"
                    ::= { analogObjects 116 }

        -- 1.3.6.1.4.1.9839.2.1.2.117
        bp-27 OBJECT-TYPE
                    SYNTAX Integer32 (10..300)
                    UNITS "C x10"
                    MAX-ACCESS read-write
                    STATUS current
                    DESCRIPTION "DIFFERENTIAL AFM27"
                    ::= { analogObjects 117 }

        -- 1.3.6.1.4.1.9839.2.1.2.118
        bp-28 OBJECT-TYPE
                    SYNTAX Integer32 (10..300)
                    UNITS "C x10"
                    MAX-ACCESS read-write
                    STATUS current
                    DESCRIPTION "DIFFERENTIAL AFM28"
                    ::= { analogObjects 118 }

        -- 1.3.6.1.4.1.9839.2.1.2.119
        bp-29 OBJECT-TYPE
                    SYNTAX Integer32 (10..300)
                    UNITS "C x10"
                    MAX-ACCESS read-write
                    STATUS current
                    DESCRIPTION "DIFFERENTIAL AFM29"
                    ::= { analogObjects 119 }

        -- 1.3.6.1.4.1.9839.2.1.2.120
        bp-30 OBJECT-TYPE
                    SYNTAX Integer32 (10..300)
                    UNITS "C x10"
                    MAX-ACCESS read-write
                    STATUS current
                    DESCRIPTION "DIFFERENTIAL AFM30"
                    ::= { analogObjects 120 }

        -- 1.3.6.1.4.1.9839.2.1.2.121
        offs-spv OBJECT-TYPE
                    SYNTAX Integer32 (12345..12345)
                    UNITS "N/A"
                    MAX-ACCESS read-write
                    STATUS current
                    DESCRIPTION "SERIAL TRANSMISSION OFFSET"
                    ::= { analogObjects 121 }

        -- 1.3.6.1.4.1.9839.2.1.2.131
        room-t-cdz1 OBJECT-TYPE
                    SYNTAX Integer32 (12345..12345)
                    UNITS "C x10"
                    MAX-ACCESS read-only
                    STATUS current
                    DESCRIPTION "ROOM TEMPERATURE CDZ1"
                    ::= { analogObjects 131 }

        -- 1.3.6.1.4.1.9839.2.1.2.132
        room-t-cdz2 OBJECT-TYPE
                    SYNTAX Integer32 (12345..12345)
                    UNITS "C x10"
                    MAX-ACCESS read-only
                    STATUS current
                    DESCRIPTION "ROOM TEMPERATURE CDZ2"
                    ::= { analogObjects 132 }

        -- 1.3.6.1.4.1.9839.2.1.2.133
        room-t-cdz3 OBJECT-TYPE
                    SYNTAX Integer32 (12345..12345)
                    UNITS "C x10"
                    MAX-ACCESS read-only
                    STATUS current
                    DESCRIPTION "ROOM TEMPERATURE CDZ3"
                    ::= { analogObjects 133 }

        -- 1.3.6.1.4.1.9839.2.1.2.134
        room-t-cdz4 OBJECT-TYPE
                    SYNTAX Integer32 (12345..12345)
                    UNITS "C x10"
                    MAX-ACCESS read-only
                    STATUS current
                    DESCRIPTION "ROOM TEMPERATURE CDZ4"
                    ::= { analogObjects 134 }

        -- 1.3.6.1.4.1.9839.2.1.2.135
        room-t-cdz5 OBJECT-TYPE
                    SYNTAX Integer32 (12345..12345)
                    UNITS "C x10"
                    MAX-ACCESS read-only
                    STATUS current
                    DESCRIPTION "ROOM TEMPERATURE CDZ5"
                    ::= { analogObjects 135 }

        -- 1.3.6.1.4.1.9839.2.1.2.136
        room-t-cdz6 OBJECT-TYPE
                    SYNTAX Integer32 (12345..12345)
                    UNITS "C x10"
                    MAX-ACCESS read-only
                    STATUS current
                    DESCRIPTION "ROOM TEMPERATURE CDZ6"
                    ::= { analogObjects 136 }

        -- 1.3.6.1.4.1.9839.2.1.2.137
        room-t-cdz7 OBJECT-TYPE
                    SYNTAX Integer32 (12345..12345)
                    UNITS "C x10"
                    MAX-ACCESS read-only
                    STATUS current
                    DESCRIPTION "ROOM TEMPERATURE CDZ7"
                    ::= { analogObjects 137 }

        -- 1.3.6.1.4.1.9839.2.1.2.138
        room-t-cdz8 OBJECT-TYPE
                    SYNTAX Integer32 (12345..12345)
                    UNITS "C x10"
                    MAX-ACCESS read-only
                    STATUS current
                    DESCRIPTION "ROOM TEMPERATURE CDZ8"
                    ::= { analogObjects 138 }

        -- 1.3.6.1.4.1.9839.2.1.2.139
        room-t-cdz9 OBJECT-TYPE
                    SYNTAX Integer32 (12345..12345)
                    UNITS "C x10"
                    MAX-ACCESS read-only
                    STATUS current
                    DESCRIPTION "ROOM TEMPERATURE CDZ9"
                    ::= { analogObjects 139 }

        -- 1.3.6.1.4.1.9839.2.1.2.140
        room-t-cdz10 OBJECT-TYPE
                    SYNTAX Integer32 (12345..12345)
                    UNITS "C x10"
                    MAX-ACCESS read-only
                    STATUS current
                    DESCRIPTION "ROOM TEMPERATURE CDZ10"
                    ::= { analogObjects 140 }

        -- 1.3.6.1.4.1.9839.2.1.2.141
        deliver-airt-cdz1 OBJECT-TYPE
                    SYNTAX Integer32 (12345..12345)
                    UNITS "C x10"
                    MAX-ACCESS read-only
                    STATUS current
                    DESCRIPTION "DELIVERY AIR TEMPERATURE CDZ1"
                    ::= { analogObjects 141 }

        -- 1.3.6.1.4.1.9839.2.1.2.142
        deliver-airt-cdz2 OBJECT-TYPE
                    SYNTAX Integer32 (12345..12345)
                    UNITS "C x10"
                    MAX-ACCESS read-only
                    STATUS current
                    DESCRIPTION "DELIVERY AIR TEMPERATURE CDZ2"
                    ::= { analogObjects 142 }

        -- 1.3.6.1.4.1.9839.2.1.2.143
        deliver-airt-cdz3 OBJECT-TYPE
                    SYNTAX Integer32 (12345..12345)
                    UNITS "C x10"
                    MAX-ACCESS read-only
                    STATUS current
                    DESCRIPTION "DELIVERY AIR TEMPERATURE CDZ3"
                    ::= { analogObjects 143 }

        -- 1.3.6.1.4.1.9839.2.1.2.144
        deliver-airt-cdz4 OBJECT-TYPE
                    SYNTAX Integer32 (12345..12345)
                    UNITS "C x10"
                    MAX-ACCESS read-only
                    STATUS current
                    DESCRIPTION "DELIVERY AIR TEMPERATURE CDZ4"
                    ::= { analogObjects 144 }

        -- 1.3.6.1.4.1.9839.2.1.2.145
        deliver-airt-cdz5 OBJECT-TYPE
                    SYNTAX Integer32 (12345..12345)
                    UNITS "C x10"
                    MAX-ACCESS read-only
                    STATUS current
                    DESCRIPTION "DELIVERY AIR TEMPERATURE CDZ5"
                    ::= { analogObjects 145 }

        -- 1.3.6.1.4.1.9839.2.1.2.146
        deliver-airt-cdz6 OBJECT-TYPE
                    SYNTAX Integer32 (12345..12345)
                    UNITS "C x10"
                    MAX-ACCESS read-only
                    STATUS current
                    DESCRIPTION "DELIVERY AIR TEMPERATURE CDZ6"
                    ::= { analogObjects 146 }

        -- 1.3.6.1.4.1.9839.2.1.2.147
        deliver-airt-cdz7 OBJECT-TYPE
                    SYNTAX Integer32 (12345..12345)
                    UNITS "C x10"
                    MAX-ACCESS read-only
                    STATUS current
                    DESCRIPTION "DELIVERY AIR TEMPERATURE CDZ7"
                    ::= { analogObjects 147 }

        -- 1.3.6.1.4.1.9839.2.1.2.148
        deliver-airt-cdz8 OBJECT-TYPE
                    SYNTAX Integer32 (12345..12345)
                    UNITS "C x10"
                    MAX-ACCESS read-only
                    STATUS current
                    DESCRIPTION "DELIVERY AIR TEMPERATURE CDZ8"
                    ::= { analogObjects 148 }

        -- 1.3.6.1.4.1.9839.2.1.2.149
        deliver-airt-cdz9 OBJECT-TYPE
                    SYNTAX Integer32 (12345..12345)
                    UNITS "C x10"
                    MAX-ACCESS read-only
                    STATUS current
                    DESCRIPTION "DELIVERY AIR TEMPERATURE CDZ9"
                    ::= { analogObjects 149 }

        -- 1.3.6.1.4.1.9839.2.1.2.150
        deliver-airt-cdz10 OBJECT-TYPE
                    SYNTAX Integer32 (12345..12345)
                    UNITS "C x10"
                    MAX-ACCESS read-only
                    STATUS current
                    DESCRIPTION "DELIVERY AIR TEMPERATURE CDZ10"
                    ::= { analogObjects 150 }

        -- 1.3.6.1.4.1.9839.2.1.2.151
        room-rh-cdz1 OBJECT-TYPE
                    SYNTAX Integer32 (12345..12345)
                    UNITS "% x10"
                    MAX-ACCESS read-only
                    STATUS current
                    DESCRIPTION "ROOM RELATIVE HUMIDITY CDZ1"
                    ::= { analogObjects 151 }

        -- 1.3.6.1.4.1.9839.2.1.2.152
        room-rh-cdz2 OBJECT-TYPE
                    SYNTAX Integer32 (12345..12345)
                    UNITS "% x10"
                    MAX-ACCESS read-only
                    STATUS current
                    DESCRIPTION "ROOM RELATIVE HUMIDITY CDZ2"
                    ::= { analogObjects 152 }

        -- 1.3.6.1.4.1.9839.2.1.2.153
        room-rh-cdz3 OBJECT-TYPE
                    SYNTAX Integer32 (12345..12345)
                    UNITS "% x10"
                    MAX-ACCESS read-only
                    STATUS current
                    DESCRIPTION "ROOM RELATIVE HUMIDITY CDZ3"
                    ::= { analogObjects 153 }

        -- 1.3.6.1.4.1.9839.2.1.2.154
        room-rh-cdz4 OBJECT-TYPE
                    SYNTAX Integer32 (12345..12345)
                    UNITS "% x10"
                    MAX-ACCESS read-only
                    STATUS current
                    DESCRIPTION "ROOM RELATIVE HUMIDITY CDZ4"
                    ::= { analogObjects 154 }

        -- 1.3.6.1.4.1.9839.2.1.2.155
        room-rh-cdz5 OBJECT-TYPE
                    SYNTAX Integer32 (12345..12345)
                    UNITS "% x10"
                    MAX-ACCESS read-only
                    STATUS current
                    DESCRIPTION "ROOM RELATIVE HUMIDITY CDZ5"
                    ::= { analogObjects 155 }

        -- 1.3.6.1.4.1.9839.2.1.2.156
        room-rh-cdz6 OBJECT-TYPE
                    SYNTAX Integer32 (12345..12345)
                    UNITS "% x10"
                    MAX-ACCESS read-only
                    STATUS current
                    DESCRIPTION "ROOM RELATIVE HUMIDITY CDZ6"
                    ::= { analogObjects 156 }

        -- 1.3.6.1.4.1.9839.2.1.2.157
        room-rh-cdz7 OBJECT-TYPE
                    SYNTAX Integer32 (12345..12345)
                    UNITS "% x10"
                    MAX-ACCESS read-only
                    STATUS current
                    DESCRIPTION "ROOM RELATIVE HUMIDITY CDZ7"
                    ::= { analogObjects 157 }

        -- 1.3.6.1.4.1.9839.2.1.2.158
        room-rh-cdz8 OBJECT-TYPE
                    SYNTAX Integer32 (12345..12345)
                    UNITS "% x10"
                    MAX-ACCESS read-only
                    STATUS current
                    DESCRIPTION "ROOM RELATIVE HUMIDITY CDZ8"
                    ::= { analogObjects 158 }

        -- 1.3.6.1.4.1.9839.2.1.2.159
        room-rh-cdz9 OBJECT-TYPE
                    SYNTAX Integer32 (12345..12345)
                    UNITS "% x10"
                    MAX-ACCESS read-only
                    STATUS current
                    DESCRIPTION "ROOM RELATIVE HUMIDITY CDZ9"
                    ::= { analogObjects 159 }

        -- 1.3.6.1.4.1.9839.2.1.2.160
        room-rh-cdz10 OBJECT-TYPE
                    SYNTAX Integer32 (12345..12345)
                    UNITS "% x10"
                    MAX-ACCESS read-only
                    STATUS current
                    DESCRIPTION "ROOM RELATIVE HUMIDITY CDZ10"
                    ::= { analogObjects 160 }

        -- 1.3.6.1.4.1.9839.2.1.2.161
        cw-t-cdz1 OBJECT-TYPE
                    SYNTAX Integer32 (12345..12345)
                    UNITS "C x10"
                    MAX-ACCESS read-only
                    STATUS current
                    DESCRIPTION "CHILLED WATER TEMPERATURE CDZ1"
                    ::= { analogObjects 161 }

        -- 1.3.6.1.4.1.9839.2.1.2.162
        cw-t-cdz2 OBJECT-TYPE
                    SYNTAX Integer32 (12345..12345)
                    UNITS "C x10"
                    MAX-ACCESS read-only
                    STATUS current
                    DESCRIPTION "CHILLED WATER TEMPERATURE CDZ2"
                    ::= { analogObjects 162 }

        -- 1.3.6.1.4.1.9839.2.1.2.163
        cw-t-cdz3 OBJECT-TYPE
                    SYNTAX Integer32 (12345..12345)
                    UNITS "C x10"
                    MAX-ACCESS read-only
                    STATUS current
                    DESCRIPTION "CHILLED WATER TEMPERATURE CDZ3"
                    ::= { analogObjects 163 }

        -- 1.3.6.1.4.1.9839.2.1.2.164
        cw-t-cdz4 OBJECT-TYPE
                    SYNTAX Integer32 (12345..12345)
                    UNITS "C x10"
                    MAX-ACCESS read-only
                    STATUS current
                    DESCRIPTION "CHILLED WATER TEMPERATURE CDZ4"
                    ::= { analogObjects 164 }

        -- 1.3.6.1.4.1.9839.2.1.2.165
        cw-t-cdz5 OBJECT-TYPE
                    SYNTAX Integer32 (12345..12345)
                    UNITS "C x10"
                    MAX-ACCESS read-only
                    STATUS current
                    DESCRIPTION "CHILLED WATER TEMPERATURE CDZ5"
                    ::= { analogObjects 165 }

        -- 1.3.6.1.4.1.9839.2.1.2.166
        cw-t-cdz6 OBJECT-TYPE
                    SYNTAX Integer32 (12345..12345)
                    UNITS "C x10"
                    MAX-ACCESS read-only
                    STATUS current
                    DESCRIPTION "CHILLED WATER TEMPERATURE CDZ6"
                    ::= { analogObjects 166 }

        -- 1.3.6.1.4.1.9839.2.1.2.167
        cw-t-cdz7 OBJECT-TYPE
                    SYNTAX Integer32 (12345..12345)
                    UNITS "C x10"
                    MAX-ACCESS read-only
                    STATUS current
                    DESCRIPTION "CHILLED WATER TEMPERATURE CDZ7"
                    ::= { analogObjects 167 }

        -- 1.3.6.1.4.1.9839.2.1.2.168
        cw-t-cdz8 OBJECT-TYPE
                    SYNTAX Integer32 (12345..12345)
                    UNITS "C x10"
                    MAX-ACCESS read-only
                    STATUS current
                    DESCRIPTION "CHILLED WATER TEMPERATURE CDZ8"
                    ::= { analogObjects 168 }

        -- 1.3.6.1.4.1.9839.2.1.2.169
        cw-t-cdz9 OBJECT-TYPE
                    SYNTAX Integer32 (12345..12345)
                    UNITS "C x10"
                    MAX-ACCESS read-only
                    STATUS current
                    DESCRIPTION "CHILLED WATER TEMPERATURE CDZ9"
                    ::= { analogObjects 169 }

        -- 1.3.6.1.4.1.9839.2.1.2.170
        cw-t-cdz10 OBJECT-TYPE
                    SYNTAX Integer32 (12345..12345)
                    UNITS "C x10"
                    MAX-ACCESS read-only
                    STATUS current
                    DESCRIPTION "CHILLED WATER TEMPERATURE CDZ10"
                    ::= { analogObjects 170 }

        -- 1.3.6.1.4.1.9839.2.1.2.171
        fan-speed-cdz1 OBJECT-TYPE
                    SYNTAX Integer32 (12345..12345)
                    UNITS "% x10"
                    MAX-ACCESS read-only
                    STATUS current
                    DESCRIPTION "EVAPORATING FAN SPEED CDZ1"
                    ::= { analogObjects 171 }

        -- 1.3.6.1.4.1.9839.2.1.2.172
        fan-speed-cdz2 OBJECT-TYPE
                    SYNTAX Integer32 (12345..12345)
                    UNITS "% x10"
                    MAX-ACCESS read-only
                    STATUS current
                    DESCRIPTION "EVAPORATING FAN SPEED CDZ2"
                    ::= { analogObjects 172 }

        -- 1.3.6.1.4.1.9839.2.1.2.173
        fan-speed-cdz3 OBJECT-TYPE
                    SYNTAX Integer32 (12345..12345)
                    UNITS "% x10"
                    MAX-ACCESS read-only
                    STATUS current
                    DESCRIPTION "EVAPORATING FAN SPEED CDZ3"
                    ::= { analogObjects 173 }

        -- 1.3.6.1.4.1.9839.2.1.2.174
        fan-speed-cdz4 OBJECT-TYPE
                    SYNTAX Integer32 (12345..12345)
                    UNITS "% x10"
                    MAX-ACCESS read-only
                    STATUS current
                    DESCRIPTION "EVAPORATING FAN SPEED CDZ4"
                    ::= { analogObjects 174 }

        -- 1.3.6.1.4.1.9839.2.1.2.175
        fan-speed-cdz5 OBJECT-TYPE
                    SYNTAX Integer32 (12345..12345)
                    UNITS "% x10"
                    MAX-ACCESS read-only
                    STATUS current
                    DESCRIPTION "EVAPORATING FAN SPEED CDZ5"
                    ::= { analogObjects 175 }

        -- 1.3.6.1.4.1.9839.2.1.2.176
        fan-speed-cdz6 OBJECT-TYPE
                    SYNTAX Integer32 (12345..12345)
                    UNITS "% x10"
                    MAX-ACCESS read-only
                    STATUS current
                    DESCRIPTION "EVAPORATING FAN SPEED CDZ6"
                    ::= { analogObjects 176 }

        -- 1.3.6.1.4.1.9839.2.1.2.177
        fan-speed-cdz7 OBJECT-TYPE
                    SYNTAX Integer32 (12345..12345)
                    UNITS "% x10"
                    MAX-ACCESS read-only
                    STATUS current
                    DESCRIPTION "EVAPORATING FAN SPEED CDZ7"
                    ::= { analogObjects 177 }

        -- 1.3.6.1.4.1.9839.2.1.2.178
        fan-speed-cdz8 OBJECT-TYPE
                    SYNTAX Integer32 (12345..12345)
                    UNITS "% x10"
                    MAX-ACCESS read-only
                    STATUS current
                    DESCRIPTION "EVAPORATING FAN SPEED CDZ8"
                    ::= { analogObjects 178 }

        -- 1.3.6.1.4.1.9839.2.1.2.179
        fan-speed-cdz9 OBJECT-TYPE
                    SYNTAX Integer32 (12345..12345)
                    UNITS "% x10"
                    MAX-ACCESS read-only
                    STATUS current
                    DESCRIPTION "EVAPORATING FAN SPEED CDZ9"
                    ::= { analogObjects 179 }

        -- 1.3.6.1.4.1.9839.2.1.2.180
        fan-speed-cdz10 OBJECT-TYPE
                    SYNTAX Integer32 (12345..12345)
                    UNITS "% x10"
                    MAX-ACCESS read-only
                    STATUS current
                    DESCRIPTION "EVAPORATING FAN SPEED CDZ10"
                    ::= { analogObjects 180 }



        -- 1.3.6.1.4.1.9839.2.1.3
        integerObjects OBJECT IDENTIFIER ::= { mstafMIB 3 }

        -- 1.3.6.1.4.1.9839.2.1.3.1
        al-af1 OBJECT-TYPE
                    SYNTAX Integer32 (12345..12345)
                    UNITS "N/A"
                    MAX-ACCESS read-only
                    STATUS current
                    DESCRIPTION "ALARM CODE AFM1"
                    ::= { integerObjects 1 }

        -- 1.3.6.1.4.1.9839.2.1.3.2
        al-af2 OBJECT-TYPE
                    SYNTAX Integer32 (12345..12345)
                    UNITS "N/A"
                    MAX-ACCESS read-only
                    STATUS current
                    DESCRIPTION "ALARM CODE AFM2"
                    ::= { integerObjects 2 }

        -- 1.3.6.1.4.1.9839.2.1.3.3
        al-af3 OBJECT-TYPE
                    SYNTAX Integer32 (12345..12345)
                    UNITS "N/A"
                    MAX-ACCESS read-only
                    STATUS current
                    DESCRIPTION "ALARM CODE AFM3"
                    ::= { integerObjects 3 }

        -- 1.3.6.1.4.1.9839.2.1.3.4
        al-af4 OBJECT-TYPE
                    SYNTAX Integer32 (12345..12345)
                    UNITS "N/A"
                    MAX-ACCESS read-only
                    STATUS current
                    DESCRIPTION "ALARM CODE AFM4"
                    ::= { integerObjects 4 }

        -- 1.3.6.1.4.1.9839.2.1.3.5
        al-af5 OBJECT-TYPE
                    SYNTAX Integer32 (12345..12345)
                    UNITS "N/A"
                    MAX-ACCESS read-only
                    STATUS current
                    DESCRIPTION "ALARM CODE AFM5"
                    ::= { integerObjects 5 }

        -- 1.3.6.1.4.1.9839.2.1.3.6
        al-af6 OBJECT-TYPE
                    SYNTAX Integer32 (12345..12345)
                    UNITS "N/A"
                    MAX-ACCESS read-only
                    STATUS current
                    DESCRIPTION "ALARM CODE AFM6"
                    ::= { integerObjects 6 }

        -- 1.3.6.1.4.1.9839.2.1.3.7
        al-af7 OBJECT-TYPE
                    SYNTAX Integer32 (12345..12345)
                    UNITS "N/A"
                    MAX-ACCESS read-only
                    STATUS current
                    DESCRIPTION "ALARM CODE AFM7"
                    ::= { integerObjects 7 }

        -- 1.3.6.1.4.1.9839.2.1.3.8
        al-af8 OBJECT-TYPE
                    SYNTAX Integer32 (12345..12345)
                    UNITS "N/A"
                    MAX-ACCESS read-only
                    STATUS current
                    DESCRIPTION "ALARM CODE AFM8"
                    ::= { integerObjects 8 }

        -- 1.3.6.1.4.1.9839.2.1.3.9
        al-af9 OBJECT-TYPE
                    SYNTAX Integer32 (12345..12345)
                    UNITS "N/A"
                    MAX-ACCESS read-only
                    STATUS current
                    DESCRIPTION "ALARM CODE AFM9"
                    ::= { integerObjects 9 }

        -- 1.3.6.1.4.1.9839.2.1.3.10
        al-af10 OBJECT-TYPE
                    SYNTAX Integer32 (12345..12345)
                    UNITS "N/A"
                    MAX-ACCESS read-only
                    STATUS current
                    DESCRIPTION "ALARM CODE AFM10"
                    ::= { integerObjects 10 }

        -- 1.3.6.1.4.1.9839.2.1.3.11
        al-af11 OBJECT-TYPE
                    SYNTAX Integer32 (12345..12345)
                    UNITS "N/A"
                    MAX-ACCESS read-only
                    STATUS current
                    DESCRIPTION "ALARM CODE AFM11"
                    ::= { integerObjects 11 }

        -- 1.3.6.1.4.1.9839.2.1.3.12
        al-af12 OBJECT-TYPE
                    SYNTAX Integer32 (12345..12345)
                    UNITS "N/A"
                    MAX-ACCESS read-only
                    STATUS current
                    DESCRIPTION "ALARM CODE AFM12"
                    ::= { integerObjects 12 }

        -- 1.3.6.1.4.1.9839.2.1.3.13
        al-af13 OBJECT-TYPE
                    SYNTAX Integer32 (12345..12345)
                    UNITS "N/A"
                    MAX-ACCESS read-only
                    STATUS current
                    DESCRIPTION "ALARM CODE AFM13"
                    ::= { integerObjects 13 }

        -- 1.3.6.1.4.1.9839.2.1.3.14
        al-af14 OBJECT-TYPE
                    SYNTAX Integer32 (12345..12345)
                    UNITS "N/A"
                    MAX-ACCESS read-only
                    STATUS current
                    DESCRIPTION "ALARM CODE AFM14"
                    ::= { integerObjects 14 }

        -- 1.3.6.1.4.1.9839.2.1.3.15
        al-af15 OBJECT-TYPE
                    SYNTAX Integer32 (12345..12345)
                    UNITS "N/A"
                    MAX-ACCESS read-only
                    STATUS current
                    DESCRIPTION "ALARM CODE AFM15"
                    ::= { integerObjects 15 }

        -- 1.3.6.1.4.1.9839.2.1.3.16
        al-af16 OBJECT-TYPE
                    SYNTAX Integer32 (12345..12345)
                    UNITS "N/A"
                    MAX-ACCESS read-only
                    STATUS current
                    DESCRIPTION "ALARM CODE AFM16"
                    ::= { integerObjects 16 }

        -- 1.3.6.1.4.1.9839.2.1.3.17
        al-af17 OBJECT-TYPE
                    SYNTAX Integer32 (12345..12345)
                    UNITS "N/A"
                    MAX-ACCESS read-only
                    STATUS current
                    DESCRIPTION "ALARM CODE AFM17"
                    ::= { integerObjects 17 }

        -- 1.3.6.1.4.1.9839.2.1.3.18
        al-af18 OBJECT-TYPE
                    SYNTAX Integer32 (12345..12345)
                    UNITS "N/A"
                    MAX-ACCESS read-only
                    STATUS current
                    DESCRIPTION "ALARM CODE AFM18"
                    ::= { integerObjects 18 }

        -- 1.3.6.1.4.1.9839.2.1.3.19
        al-af19 OBJECT-TYPE
                    SYNTAX Integer32 (12345..12345)
                    UNITS "N/A"
                    MAX-ACCESS read-only
                    STATUS current
                    DESCRIPTION "ALARM CODE AFM19"
                    ::= { integerObjects 19 }

        -- 1.3.6.1.4.1.9839.2.1.3.20
        al-af20 OBJECT-TYPE
                    SYNTAX Integer32 (12345..12345)
                    UNITS "N/A"
                    MAX-ACCESS read-only
                    STATUS current
                    DESCRIPTION "ALARM CODE AFM20"
                    ::= { integerObjects 20 }

        -- 1.3.6.1.4.1.9839.2.1.3.21
        al-af21 OBJECT-TYPE
                    SYNTAX Integer32 (12345..12345)
                    UNITS "N/A"
                    MAX-ACCESS read-only
                    STATUS current
                    DESCRIPTION "ALARM CODE AFM21"
                    ::= { integerObjects 21 }

        -- 1.3.6.1.4.1.9839.2.1.3.22
        al-af22 OBJECT-TYPE
                    SYNTAX Integer32 (12345..12345)
                    UNITS "N/A"
                    MAX-ACCESS read-only
                    STATUS current
                    DESCRIPTION "ALARM CODE AFM22"
                    ::= { integerObjects 22 }

        -- 1.3.6.1.4.1.9839.2.1.3.23
        al-af23 OBJECT-TYPE
                    SYNTAX Integer32 (12345..12345)
                    UNITS "N/A"
                    MAX-ACCESS read-only
                    STATUS current
                    DESCRIPTION "ALARM CODE AFM23"
                    ::= { integerObjects 23 }

        -- 1.3.6.1.4.1.9839.2.1.3.24
        al-af24 OBJECT-TYPE
                    SYNTAX Integer32 (12345..12345)
                    UNITS "N/A"
                    MAX-ACCESS read-only
                    STATUS current
                    DESCRIPTION "ALARM CODE AFM24"
                    ::= { integerObjects 24 }

        -- 1.3.6.1.4.1.9839.2.1.3.25
        al-af25 OBJECT-TYPE
                    SYNTAX Integer32 (12345..12345)
                    UNITS "N/A"
                    MAX-ACCESS read-only
                    STATUS current
                    DESCRIPTION "ALARM CODE AFM25"
                    ::= { integerObjects 25 }

        -- 1.3.6.1.4.1.9839.2.1.3.26
        al-af26 OBJECT-TYPE
                    SYNTAX Integer32 (12345..12345)
                    UNITS "N/A"
                    MAX-ACCESS read-only
                    STATUS current
                    DESCRIPTION "ALARM CODE AFM26"
                    ::= { integerObjects 26 }

        -- 1.3.6.1.4.1.9839.2.1.3.27
        al-af27 OBJECT-TYPE
                    SYNTAX Integer32 (12345..12345)
                    UNITS "N/A"
                    MAX-ACCESS read-only
                    STATUS current
                    DESCRIPTION "ALARM CODE AFM27"
                    ::= { integerObjects 27 }

        -- 1.3.6.1.4.1.9839.2.1.3.28
        al-af28 OBJECT-TYPE
                    SYNTAX Integer32 (12345..12345)
                    UNITS "N/A"
                    MAX-ACCESS read-only
                    STATUS current
                    DESCRIPTION "ALARM CODE AFM28"
                    ::= { integerObjects 28 }

        -- 1.3.6.1.4.1.9839.2.1.3.29
        al-af29 OBJECT-TYPE
                    SYNTAX Integer32 (12345..12345)
                    UNITS "N/A"
                    MAX-ACCESS read-only
                    STATUS current
                    DESCRIPTION "ALARM CODE AFM29"
                    ::= { integerObjects 29 }

        -- 1.3.6.1.4.1.9839.2.1.3.30
        al-af30 OBJECT-TYPE
                    SYNTAX Integer32 (12345..12345)
                    UNITS "N/A"
                    MAX-ACCESS read-only
                    STATUS current
                    DESCRIPTION "ALARM CODE AFM30"
                    ::= { integerObjects 30 }

        -- 1.3.6.1.4.1.9839.2.1.3.31
        outv-1 OBJECT-TYPE
                    SYNTAX Integer32 (12345..12345)
                    UNITS "%"
                    MAX-ACCESS read-only
                    STATUS current
                    DESCRIPTION "FAN SPEED AFM1"
                    ::= { integerObjects 31 }

        -- 1.3.6.1.4.1.9839.2.1.3.32
        outv-2 OBJECT-TYPE
                    SYNTAX Integer32 (12345..12345)
                    UNITS "%"
                    MAX-ACCESS read-only
                    STATUS current
                    DESCRIPTION "FAN SPEED AFM2"
                    ::= { integerObjects 32 }

        -- 1.3.6.1.4.1.9839.2.1.3.33
        outv-3 OBJECT-TYPE
                    SYNTAX Integer32 (12345..12345)
                    UNITS "%"
                    MAX-ACCESS read-only
                    STATUS current
                    DESCRIPTION "FAN SPEED AFM3"
                    ::= { integerObjects 33 }

        -- 1.3.6.1.4.1.9839.2.1.3.34
        outv-4 OBJECT-TYPE
                    SYNTAX Integer32 (12345..12345)
                    UNITS "%"
                    MAX-ACCESS read-only
                    STATUS current
                    DESCRIPTION "FAN SPEED AFM4"
                    ::= { integerObjects 34 }

        -- 1.3.6.1.4.1.9839.2.1.3.35
        outv-5 OBJECT-TYPE
                    SYNTAX Integer32 (12345..12345)
                    UNITS "%"
                    MAX-ACCESS read-only
                    STATUS current
                    DESCRIPTION "FAN SPEED AFM5"
                    ::= { integerObjects 35 }

        -- 1.3.6.1.4.1.9839.2.1.3.36
        outv-6 OBJECT-TYPE
                    SYNTAX Integer32 (12345..12345)
                    UNITS "%"
                    MAX-ACCESS read-only
                    STATUS current
                    DESCRIPTION "FAN SPEED AFM6"
                    ::= { integerObjects 36 }

        -- 1.3.6.1.4.1.9839.2.1.3.37
        outv-7 OBJECT-TYPE
                    SYNTAX Integer32 (12345..12345)
                    UNITS "%"
                    MAX-ACCESS read-only
                    STATUS current
                    DESCRIPTION "FAN SPEED AFM7"
                    ::= { integerObjects 37 }

        -- 1.3.6.1.4.1.9839.2.1.3.38
        outv-8 OBJECT-TYPE
                    SYNTAX Integer32 (12345..12345)
                    UNITS "%"
                    MAX-ACCESS read-only
                    STATUS current
                    DESCRIPTION "FAN SPEED AFM8"
                    ::= { integerObjects 38 }

        -- 1.3.6.1.4.1.9839.2.1.3.39
        outv-9 OBJECT-TYPE
                    SYNTAX Integer32 (12345..12345)
                    UNITS "%"
                    MAX-ACCESS read-only
                    STATUS current
                    DESCRIPTION "FAN SPEED AFM9"
                    ::= { integerObjects 39 }

        -- 1.3.6.1.4.1.9839.2.1.3.40
        outv-10 OBJECT-TYPE
                    SYNTAX Integer32 (12345..12345)
                    UNITS "%"
                    MAX-ACCESS read-only
                    STATUS current
                    DESCRIPTION "FAN SPEED AFM10"
                    ::= { integerObjects 40 }

        -- 1.3.6.1.4.1.9839.2.1.3.41
        outv-11 OBJECT-TYPE
                    SYNTAX Integer32 (12345..12345)
                    UNITS "%"
                    MAX-ACCESS read-only
                    STATUS current
                    DESCRIPTION "FAN SPEED AFM11"
                    ::= { integerObjects 41 }

        -- 1.3.6.1.4.1.9839.2.1.3.42
        outv-12 OBJECT-TYPE
                    SYNTAX Integer32 (12345..12345)
                    UNITS "%"
                    MAX-ACCESS read-only
                    STATUS current
                    DESCRIPTION "FAN SPEED AFM12"
                    ::= { integerObjects 42 }

        -- 1.3.6.1.4.1.9839.2.1.3.43
        outv-13 OBJECT-TYPE
                    SYNTAX Integer32 (12345..12345)
                    UNITS "%"
                    MAX-ACCESS read-only
                    STATUS current
                    DESCRIPTION "FAN SPEED AFM13"
                    ::= { integerObjects 43 }

        -- 1.3.6.1.4.1.9839.2.1.3.44
        outv-14 OBJECT-TYPE
                    SYNTAX Integer32 (12345..12345)
                    UNITS "%"
                    MAX-ACCESS read-only
                    STATUS current
                    DESCRIPTION "FAN SPEED AFM14"
                    ::= { integerObjects 44 }

        -- 1.3.6.1.4.1.9839.2.1.3.45
        outv-15 OBJECT-TYPE
                    SYNTAX Integer32 (12345..12345)
                    UNITS "%"
                    MAX-ACCESS read-only
                    STATUS current
                    DESCRIPTION "FAN SPEED AFM15"
                    ::= { integerObjects 45 }

        -- 1.3.6.1.4.1.9839.2.1.3.46
        outv-16 OBJECT-TYPE
                    SYNTAX Integer32 (12345..12345)
                    UNITS "%"
                    MAX-ACCESS read-only
                    STATUS current
                    DESCRIPTION "FAN SPEED AFM16"
                    ::= { integerObjects 46 }

        -- 1.3.6.1.4.1.9839.2.1.3.47
        outv-17 OBJECT-TYPE
                    SYNTAX Integer32 (12345..12345)
                    UNITS "%"
                    MAX-ACCESS read-only
                    STATUS current
                    DESCRIPTION "FAN SPEED AFM17"
                    ::= { integerObjects 47 }

        -- 1.3.6.1.4.1.9839.2.1.3.48
        outv-18 OBJECT-TYPE
                    SYNTAX Integer32 (12345..12345)
                    UNITS "%"
                    MAX-ACCESS read-only
                    STATUS current
                    DESCRIPTION "FAN SPEED AFM18"
                    ::= { integerObjects 48 }

        -- 1.3.6.1.4.1.9839.2.1.3.49
        outv-19 OBJECT-TYPE
                    SYNTAX Integer32 (12345..12345)
                    UNITS "%"
                    MAX-ACCESS read-only
                    STATUS current
                    DESCRIPTION "FAN SPEED AFM19"
                    ::= { integerObjects 49 }

        -- 1.3.6.1.4.1.9839.2.1.3.50
        outv-20 OBJECT-TYPE
                    SYNTAX Integer32 (12345..12345)
                    UNITS "%"
                    MAX-ACCESS read-only
                    STATUS current
                    DESCRIPTION "FAN SPEED AFM20"
                    ::= { integerObjects 50 }

        -- 1.3.6.1.4.1.9839.2.1.3.51
        outv-21 OBJECT-TYPE
                    SYNTAX Integer32 (12345..12345)
                    UNITS "%"
                    MAX-ACCESS read-only
                    STATUS current
                    DESCRIPTION "FAN SPEED AFM21"
                    ::= { integerObjects 51 }

        -- 1.3.6.1.4.1.9839.2.1.3.52
        outv-22 OBJECT-TYPE
                    SYNTAX Integer32 (12345..12345)
                    UNITS "%"
                    MAX-ACCESS read-only
                    STATUS current
                    DESCRIPTION "FAN SPEED AFM22"
                    ::= { integerObjects 52 }

        -- 1.3.6.1.4.1.9839.2.1.3.53
        outv-23 OBJECT-TYPE
                    SYNTAX Integer32 (12345..12345)
                    UNITS "%"
                    MAX-ACCESS read-only
                    STATUS current
                    DESCRIPTION "FAN SPEED AFM23"
                    ::= { integerObjects 53 }

        -- 1.3.6.1.4.1.9839.2.1.3.54
        outv-24 OBJECT-TYPE
                    SYNTAX Integer32 (12345..12345)
                    UNITS "%"
                    MAX-ACCESS read-only
                    STATUS current
                    DESCRIPTION "FAN SPEED AFM24"
                    ::= { integerObjects 54 }

        -- 1.3.6.1.4.1.9839.2.1.3.55
        outv-25 OBJECT-TYPE
                    SYNTAX Integer32 (12345..12345)
                    UNITS "%"
                    MAX-ACCESS read-only
                    STATUS current
                    DESCRIPTION "FAN SPEED AFM25"
                    ::= { integerObjects 55 }

        -- 1.3.6.1.4.1.9839.2.1.3.56
        outv-26 OBJECT-TYPE
                    SYNTAX Integer32 (12345..12345)
                    UNITS "%"
                    MAX-ACCESS read-only
                    STATUS current
                    DESCRIPTION "FAN SPEED AFM26"
                    ::= { integerObjects 56 }

        -- 1.3.6.1.4.1.9839.2.1.3.57
        outv-27 OBJECT-TYPE
                    SYNTAX Integer32 (12345..12345)
                    UNITS "%"
                    MAX-ACCESS read-only
                    STATUS current
                    DESCRIPTION "FAN SPEED AFM27"
                    ::= { integerObjects 57 }

        -- 1.3.6.1.4.1.9839.2.1.3.58
        outv-28 OBJECT-TYPE
                    SYNTAX Integer32 (12345..12345)
                    UNITS "%"
                    MAX-ACCESS read-only
                    STATUS current
                    DESCRIPTION "FAN SPEED AFM28"
                    ::= { integerObjects 58 }

        -- 1.3.6.1.4.1.9839.2.1.3.59
        outv-29 OBJECT-TYPE
                    SYNTAX Integer32 (12345..12345)
                    UNITS "%"
                    MAX-ACCESS read-only
                    STATUS current
                    DESCRIPTION "FAN SPEED AFM29"
                    ::= { integerObjects 59 }

        -- 1.3.6.1.4.1.9839.2.1.3.60
        outv-30 OBJECT-TYPE
                    SYNTAX Integer32 (12345..12345)
                    UNITS "%"
                    MAX-ACCESS read-only
                    STATUS current
                    DESCRIPTION "FAN SPEED AFM30"
                    ::= { integerObjects 60 }

        -- 1.3.6.1.4.1.9839.2.1.3.61
        it-1 OBJECT-TYPE
                    SYNTAX Integer32 (0..9999)
                    UNITS "N/A"
                    MAX-ACCESS read-write
                    STATUS current
                    DESCRIPTION "INTEGRAL TIME AFM1"
                    DEFVAL { 0 }
                    ::= { integerObjects 61 }

        -- 1.3.6.1.4.1.9839.2.1.3.62
        it-2 OBJECT-TYPE
                    SYNTAX Integer32 (0..9999)
                    UNITS "N/A"
                    MAX-ACCESS read-write
                    STATUS current
                    DESCRIPTION "INTEGRAL TIME AFM2"
                    DEFVAL { 0 }
                    ::= { integerObjects 62 }

        -- 1.3.6.1.4.1.9839.2.1.3.63
        it-3 OBJECT-TYPE
                    SYNTAX Integer32 (0..9999)
                    UNITS "N/A"
                    MAX-ACCESS read-write
                    STATUS current
                    DESCRIPTION "INTEGRAL TIME AFM3"
                    DEFVAL { 0 }
                    ::= { integerObjects 63 }

        -- 1.3.6.1.4.1.9839.2.1.3.64
        it-4 OBJECT-TYPE
                    SYNTAX Integer32 (0..9999)
                    UNITS "N/A"
                    MAX-ACCESS read-write
                    STATUS current
                    DESCRIPTION "INTEGRAL TIME AFM4"
                    DEFVAL { 0 }
                    ::= { integerObjects 64 }

        -- 1.3.6.1.4.1.9839.2.1.3.65
        it-5 OBJECT-TYPE
                    SYNTAX Integer32 (0..9999)
                    UNITS "N/A"
                    MAX-ACCESS read-write
                    STATUS current
                    DESCRIPTION "INTEGRAL TIME AFM5"
                    DEFVAL { 0 }
                    ::= { integerObjects 65 }

        -- 1.3.6.1.4.1.9839.2.1.3.66
        it-6 OBJECT-TYPE
                    SYNTAX Integer32 (0..9999)
                    UNITS "N/A"
                    MAX-ACCESS read-write
                    STATUS current
                    DESCRIPTION "INTEGRAL TIME AFM6"
                    DEFVAL { 0 }
                    ::= { integerObjects 66 }

        -- 1.3.6.1.4.1.9839.2.1.3.67
        it-7 OBJECT-TYPE
                    SYNTAX Integer32 (0..9999)
                    UNITS "N/A"
                    MAX-ACCESS read-write
                    STATUS current
                    DESCRIPTION "INTEGRAL TIME AFM7"
                    DEFVAL { 0 }
                    ::= { integerObjects 67 }

        -- 1.3.6.1.4.1.9839.2.1.3.68
        it-8 OBJECT-TYPE
                    SYNTAX Integer32 (0..9999)
                    UNITS "N/A"
                    MAX-ACCESS read-write
                    STATUS current
                    DESCRIPTION "INTEGRAL TIME AFM8"
                    DEFVAL { 0 }
                    ::= { integerObjects 68 }

        -- 1.3.6.1.4.1.9839.2.1.3.69
        it-9 OBJECT-TYPE
                    SYNTAX Integer32 (0..9999)
                    UNITS "N/A"
                    MAX-ACCESS read-write
                    STATUS current
                    DESCRIPTION "INTEGRAL TIME AFM9"
                    DEFVAL { 0 }
                    ::= { integerObjects 69 }

        -- 1.3.6.1.4.1.9839.2.1.3.70
        it-10 OBJECT-TYPE
                    SYNTAX Integer32 (0..9999)
                    UNITS "N/A"
                    MAX-ACCESS read-write
                    STATUS current
                    DESCRIPTION "INTEGRAL TIME AFM10"
                    DEFVAL { 0 }
                    ::= { integerObjects 70 }

        -- 1.3.6.1.4.1.9839.2.1.3.71
        it-11 OBJECT-TYPE
                    SYNTAX Integer32 (0..9999)
                    UNITS "N/A"
                    MAX-ACCESS read-write
                    STATUS current
                    DESCRIPTION "INTEGRAL TIME AFM11"
                    DEFVAL { 0 }
                    ::= { integerObjects 71 }

        -- 1.3.6.1.4.1.9839.2.1.3.72
        it-12 OBJECT-TYPE
                    SYNTAX Integer32 (0..9999)
                    UNITS "N/A"
                    MAX-ACCESS read-write
                    STATUS current
                    DESCRIPTION "INTEGRAL TIME AFM12"
                    DEFVAL { 0 }
                    ::= { integerObjects 72 }

        -- 1.3.6.1.4.1.9839.2.1.3.73
        it-13 OBJECT-TYPE
                    SYNTAX Integer32 (0..9999)
                    UNITS "N/A"
                    MAX-ACCESS read-write
                    STATUS current
                    DESCRIPTION "INTEGRAL TIME AFM13"
                    DEFVAL { 0 }
                    ::= { integerObjects 73 }

        -- 1.3.6.1.4.1.9839.2.1.3.74
        it-14 OBJECT-TYPE
                    SYNTAX Integer32 (0..9999)
                    UNITS "N/A"
                    MAX-ACCESS read-write
                    STATUS current
                    DESCRIPTION "INTEGRAL TIME AFM14"
                    DEFVAL { 0 }
                    ::= { integerObjects 74 }

        -- 1.3.6.1.4.1.9839.2.1.3.75
        it-15 OBJECT-TYPE
                    SYNTAX Integer32 (0..9999)
                    UNITS "N/A"
                    MAX-ACCESS read-write
                    STATUS current
                    DESCRIPTION "INTEGRAL TIME AFM15"
                    DEFVAL { 0 }
                    ::= { integerObjects 75 }

        -- 1.3.6.1.4.1.9839.2.1.3.76
        it-16 OBJECT-TYPE
                    SYNTAX Integer32 (0..9999)
                    UNITS "N/A"
                    MAX-ACCESS read-write
                    STATUS current
                    DESCRIPTION "INTEGRAL TIME AFM16"
                    DEFVAL { 0 }
                    ::= { integerObjects 76 }

        -- 1.3.6.1.4.1.9839.2.1.3.77
        it-17 OBJECT-TYPE
                    SYNTAX Integer32 (0..9999)
                    UNITS "N/A"
                    MAX-ACCESS read-write
                    STATUS current
                    DESCRIPTION "INTEGRAL TIME AFM17"
                    DEFVAL { 0 }
                    ::= { integerObjects 77 }

        -- 1.3.6.1.4.1.9839.2.1.3.78
        it-18 OBJECT-TYPE
                    SYNTAX Integer32 (0..9999)
                    UNITS "N/A"
                    MAX-ACCESS read-write
                    STATUS current
                    DESCRIPTION "INTEGRAL TIME AFM18"
                    DEFVAL { 0 }
                    ::= { integerObjects 78 }

        -- 1.3.6.1.4.1.9839.2.1.3.79
        it-19 OBJECT-TYPE
                    SYNTAX Integer32 (0..9999)
                    UNITS "N/A"
                    MAX-ACCESS read-write
                    STATUS current
                    DESCRIPTION "INTEGRAL TIME AFM19"
                    DEFVAL { 0 }
                    ::= { integerObjects 79 }

        -- 1.3.6.1.4.1.9839.2.1.3.80
        it-20 OBJECT-TYPE
                    SYNTAX Integer32 (0..9999)
                    UNITS "N/A"
                    MAX-ACCESS read-write
                    STATUS current
                    DESCRIPTION "INTEGRAL TIME AFM20"
                    DEFVAL { 0 }
                    ::= { integerObjects 80 }

        -- 1.3.6.1.4.1.9839.2.1.3.81
        it-21 OBJECT-TYPE
                    SYNTAX Integer32 (0..9999)
                    UNITS "N/A"
                    MAX-ACCESS read-write
                    STATUS current
                    DESCRIPTION "INTEGRAL TIME AFM21"
                    DEFVAL { 0 }
                    ::= { integerObjects 81 }

        -- 1.3.6.1.4.1.9839.2.1.3.82
        it-22 OBJECT-TYPE
                    SYNTAX Integer32 (0..9999)
                    UNITS "N/A"
                    MAX-ACCESS read-write
                    STATUS current
                    DESCRIPTION "INTEGRAL TIME AFM22"
                    DEFVAL { 0 }
                    ::= { integerObjects 82 }

        -- 1.3.6.1.4.1.9839.2.1.3.83
        it-23 OBJECT-TYPE
                    SYNTAX Integer32 (0..9999)
                    UNITS "N/A"
                    MAX-ACCESS read-write
                    STATUS current
                    DESCRIPTION "INTEGRAL TIME AFM23"
                    DEFVAL { 0 }
                    ::= { integerObjects 83 }

        -- 1.3.6.1.4.1.9839.2.1.3.84
        it-24 OBJECT-TYPE
                    SYNTAX Integer32 (0..9999)
                    UNITS "N/A"
                    MAX-ACCESS read-write
                    STATUS current
                    DESCRIPTION "INTEGRAL TIME AFM24"
                    DEFVAL { 0 }
                    ::= { integerObjects 84 }

        -- 1.3.6.1.4.1.9839.2.1.3.85
        it-25 OBJECT-TYPE
                    SYNTAX Integer32 (0..9999)
                    UNITS "N/A"
                    MAX-ACCESS read-write
                    STATUS current
                    DESCRIPTION "INTEGRAL TIME AFM25"
                    DEFVAL { 0 }
                    ::= { integerObjects 85 }

        -- 1.3.6.1.4.1.9839.2.1.3.86
        it-26 OBJECT-TYPE
                    SYNTAX Integer32 (0..9999)
                    UNITS "N/A"
                    MAX-ACCESS read-write
                    STATUS current
                    DESCRIPTION "INTEGRAL TIME AFM26"
                    DEFVAL { 0 }
                    ::= { integerObjects 86 }

        -- 1.3.6.1.4.1.9839.2.1.3.87
        it-27 OBJECT-TYPE
                    SYNTAX Integer32 (0..9999)
                    UNITS "N/A"
                    MAX-ACCESS read-write
                    STATUS current
                    DESCRIPTION "INTEGRAL TIME AFM27"
                    DEFVAL { 0 }
                    ::= { integerObjects 87 }

        -- 1.3.6.1.4.1.9839.2.1.3.88
        it-28 OBJECT-TYPE
                    SYNTAX Integer32 (0..9999)
                    UNITS "N/A"
                    MAX-ACCESS read-write
                    STATUS current
                    DESCRIPTION "INTEGRAL TIME AFM28"
                    DEFVAL { 0 }
                    ::= { integerObjects 88 }

        -- 1.3.6.1.4.1.9839.2.1.3.89
        it-29 OBJECT-TYPE
                    SYNTAX Integer32 (0..9999)
                    UNITS "N/A"
                    MAX-ACCESS read-write
                    STATUS current
                    DESCRIPTION "INTEGRAL TIME AFM29"
                    DEFVAL { 0 }
                    ::= { integerObjects 89 }

        -- 1.3.6.1.4.1.9839.2.1.3.90
        it-30 OBJECT-TYPE
                    SYNTAX Integer32 (0..9999)
                    UNITS "N/A"
                    MAX-ACCESS read-write
                    STATUS current
                    DESCRIPTION "INTEGRAL TIME AFM30"
                    DEFVAL { 0 }
                    ::= { integerObjects 90 }

        -- 1.3.6.1.4.1.9839.2.1.3.91
        dips-ramp-cdz1 OBJECT-TYPE
                    SYNTAX Integer32 (12345..12345)
                    UNITS "%"
                    MAX-ACCESS read-only
                    STATUS current
                    DESCRIPTION "COLD WATER VALVE RAMP CDZ1"
                    ::= { integerObjects 91 }

        -- 1.3.6.1.4.1.9839.2.1.3.92
        dips-ramp-cdz2 OBJECT-TYPE
                    SYNTAX Integer32 (12345..12345)
                    UNITS "%"
                    MAX-ACCESS read-only
                    STATUS current
                    DESCRIPTION "COLD WATER VALVE RAMP CDZ2"
                    ::= { integerObjects 92 }

        -- 1.3.6.1.4.1.9839.2.1.3.93
        dips-ramp-cdz3 OBJECT-TYPE
                    SYNTAX Integer32 (12345..12345)
                    UNITS "%"
                    MAX-ACCESS read-only
                    STATUS current
                    DESCRIPTION "COLD WATER VALVE RAMP CDZ3"
                    ::= { integerObjects 93 }

        -- 1.3.6.1.4.1.9839.2.1.3.94
        dips-ramp-cdz4 OBJECT-TYPE
                    SYNTAX Integer32 (12345..12345)
                    UNITS "%"
                    MAX-ACCESS read-only
                    STATUS current
                    DESCRIPTION "COLD WATER VALVE RAMP CDZ4"
                    ::= { integerObjects 94 }

        -- 1.3.6.1.4.1.9839.2.1.3.95
        dips-ramp-cdz5 OBJECT-TYPE
                    SYNTAX Integer32 (12345..12345)
                    UNITS "%"
                    MAX-ACCESS read-only
                    STATUS current
                    DESCRIPTION "COLD WATER VALVE RAMP CDZ5"
                    ::= { integerObjects 95 }

        -- 1.3.6.1.4.1.9839.2.1.3.96
        dips-ramp-cdz6 OBJECT-TYPE
                    SYNTAX Integer32 (12345..12345)
                    UNITS "%"
                    MAX-ACCESS read-only
                    STATUS current
                    DESCRIPTION "COLD WATER VALVE RAMP CDZ6"
                    ::= { integerObjects 96 }

        -- 1.3.6.1.4.1.9839.2.1.3.97
        dips-ramp-cdz7 OBJECT-TYPE
                    SYNTAX Integer32 (12345..12345)
                    UNITS "%"
                    MAX-ACCESS read-only
                    STATUS current
                    DESCRIPTION "COLD WATER VALVE RAMP CDZ7"
                    ::= { integerObjects 97 }

        -- 1.3.6.1.4.1.9839.2.1.3.98
        dips-ramp-cdz8 OBJECT-TYPE
                    SYNTAX Integer32 (12345..12345)
                    UNITS "%"
                    MAX-ACCESS read-only
                    STATUS current
                    DESCRIPTION "COLD WATER VALVE RAMP CDZ8"
                    ::= { integerObjects 98 }

        -- 1.3.6.1.4.1.9839.2.1.3.99
        dips-ramp-cdz9 OBJECT-TYPE
                    SYNTAX Integer32 (12345..12345)
                    UNITS "%"
                    MAX-ACCESS read-only
                    STATUS current
                    DESCRIPTION "COLD WATER VALVE RAMP CDZ9"
                    ::= { integerObjects 99 }

        -- 1.3.6.1.4.1.9839.2.1.3.100
        dips-ramp-cdz10 OBJECT-TYPE
                    SYNTAX Integer32 (12345..12345)
                    UNITS "%"
                    MAX-ACCESS read-only
                    STATUS current
                    DESCRIPTION "COLD WATER VALVE RAMP CDZ10"
                    ::= { integerObjects 100 }

        -- 1.3.6.1.4.1.9839.2.1.3.101
        status-cdz1 OBJECT-TYPE
                    SYNTAX Integer32 (12345..12345)
                    UNITS "N/A"
                    MAX-ACCESS read-only
                    STATUS current
                    DESCRIPTION "STATUS CDZ1"
                    ::= { integerObjects 101 }

        -- 1.3.6.1.4.1.9839.2.1.3.102
        status-cdz2 OBJECT-TYPE
                    SYNTAX Integer32 (12345..12345)
                    UNITS "N/A"
                    MAX-ACCESS read-only
                    STATUS current
                    DESCRIPTION "STATUS CDZ2"
                    ::= { integerObjects 102 }

        -- 1.3.6.1.4.1.9839.2.1.3.103
        status-cdz3 OBJECT-TYPE
                    SYNTAX Integer32 (12345..12345)
                    UNITS "N/A"
                    MAX-ACCESS read-only
                    STATUS current
                    DESCRIPTION "STATUS CDZ3"
                    ::= { integerObjects 103 }

        -- 1.3.6.1.4.1.9839.2.1.3.104
        status-cdz4 OBJECT-TYPE
                    SYNTAX Integer32 (12345..12345)
                    UNITS "N/A"
                    MAX-ACCESS read-only
                    STATUS current
                    DESCRIPTION "STATUS CDZ4"
                    ::= { integerObjects 104 }

        -- 1.3.6.1.4.1.9839.2.1.3.105
        status-cdz5 OBJECT-TYPE
                    SYNTAX Integer32 (12345..12345)
                    UNITS "N/A"
                    MAX-ACCESS read-only
                    STATUS current
                    DESCRIPTION "STATUS CDZ5"
                    ::= { integerObjects 105 }

        -- 1.3.6.1.4.1.9839.2.1.3.106
        status-cdz6 OBJECT-TYPE
                    SYNTAX Integer32 (12345..12345)
                    UNITS "N/A"
                    MAX-ACCESS read-only
                    STATUS current
                    DESCRIPTION "STATUS CDZ6"
                    ::= { integerObjects 106 }

        -- 1.3.6.1.4.1.9839.2.1.3.107
        status-cdz7 OBJECT-TYPE
                    SYNTAX Integer32 (12345..12345)
                    UNITS "N/A"
                    MAX-ACCESS read-only
                    STATUS current
                    DESCRIPTION "STATUS CDZ7"
                    ::= { integerObjects 107 }

        -- 1.3.6.1.4.1.9839.2.1.3.108
        status-cdz8 OBJECT-TYPE
                    SYNTAX Integer32 (12345..12345)
                    UNITS "N/A"
                    MAX-ACCESS read-only
                    STATUS current
                    DESCRIPTION "STATUS CDZ8"
                    ::= { integerObjects 108 }

        -- 1.3.6.1.4.1.9839.2.1.3.109
        status-cdz9 OBJECT-TYPE
                    SYNTAX Integer32 (12345..12345)
                    UNITS "N/A"
                    MAX-ACCESS read-only
                    STATUS current
                    DESCRIPTION "STATUS CDZ9"
                    ::= { integerObjects 109 }

        -- 1.3.6.1.4.1.9839.2.1.3.110
        status-cdz10 OBJECT-TYPE
                    SYNTAX Integer32 (12345..12345)
                    UNITS "N/A"
                    MAX-ACCESS read-only
                    STATUS current
                    DESCRIPTION "STATUS CDZ10"
                    ::= { integerObjects 110 }

        -- 1.3.6.1.4.1.9839.2.1.3.111
        allarmi1-cdz1 OBJECT-TYPE
                    SYNTAX Integer32 (12345..12345)
                    UNITS "N/A"
                    MAX-ACCESS read-only
                    STATUS current
                    DESCRIPTION "ALARM CODE A CDZ1"
                    ::= { integerObjects 111 }

        -- 1.3.6.1.4.1.9839.2.1.3.112
        allarmi1-cdz2 OBJECT-TYPE
                    SYNTAX Integer32 (12345..12345)
                    UNITS "N/A"
                    MAX-ACCESS read-only
                    STATUS current
                    DESCRIPTION "ALARM CODE A CDZ2"
                    ::= { integerObjects 112 }

        -- 1.3.6.1.4.1.9839.2.1.3.113
        allarmi1-cdz3 OBJECT-TYPE
                    SYNTAX Integer32 (12345..12345)
                    UNITS "N/A"
                    MAX-ACCESS read-only
                    STATUS current
                    DESCRIPTION "ALARM CODE A CDZ3"
                    ::= { integerObjects 113 }

        -- 1.3.6.1.4.1.9839.2.1.3.114
        allarmi1-cdz4 OBJECT-TYPE
                    SYNTAX Integer32 (12345..12345)
                    UNITS "N/A"
                    MAX-ACCESS read-only
                    STATUS current
                    DESCRIPTION "ALARM CODE A CDZ4"
                    ::= { integerObjects 114 }

        -- 1.3.6.1.4.1.9839.2.1.3.115
        allarmi1-cdz5 OBJECT-TYPE
                    SYNTAX Integer32 (12345..12345)
                    UNITS "N/A"
                    MAX-ACCESS read-only
                    STATUS current
                    DESCRIPTION "ALARM CODE A CDZ5"
                    ::= { integerObjects 115 }

        -- 1.3.6.1.4.1.9839.2.1.3.116
        allarmi1-cdz6 OBJECT-TYPE
                    SYNTAX Integer32 (12345..12345)
                    UNITS "N/A"
                    MAX-ACCESS read-only
                    STATUS current
                    DESCRIPTION "ALARM CODE A CDZ6"
                    ::= { integerObjects 116 }

        -- 1.3.6.1.4.1.9839.2.1.3.117
        allarmi1-cdz7 OBJECT-TYPE
                    SYNTAX Integer32 (12345..12345)
                    UNITS "N/A"
                    MAX-ACCESS read-only
                    STATUS current
                    DESCRIPTION "ALARM CODE A CDZ7"
                    ::= { integerObjects 117 }

        -- 1.3.6.1.4.1.9839.2.1.3.118
        allarmi1-cdz8 OBJECT-TYPE
                    SYNTAX Integer32 (12345..12345)
                    UNITS "N/A"
                    MAX-ACCESS read-only
                    STATUS current
                    DESCRIPTION "ALARM CODE A CDZ8"
                    ::= { integerObjects 118 }

        -- 1.3.6.1.4.1.9839.2.1.3.119
        allarmi1-cdz9 OBJECT-TYPE
                    SYNTAX Integer32 (12345..12345)
                    UNITS "N/A"
                    MAX-ACCESS read-only
                    STATUS current
                    DESCRIPTION "ALARM CODE A CDZ9"
                    ::= { integerObjects 119 }

        -- 1.3.6.1.4.1.9839.2.1.3.120
        allarmi1-cdz10 OBJECT-TYPE
                    SYNTAX Integer32 (12345..12345)
                    UNITS "N/A"
                    MAX-ACCESS read-only
                    STATUS current
                    DESCRIPTION "ALARM CODE A CDZ10"
                    ::= { integerObjects 120 }

        -- 1.3.6.1.4.1.9839.2.1.3.121
        allarmi2-cdz1 OBJECT-TYPE
                    SYNTAX Integer32 (12345..12345)
                    UNITS "N/A"
                    MAX-ACCESS read-only
                    STATUS current
                    DESCRIPTION "ALARM CODE B CDZ1"
                    ::= { integerObjects 121 }

        -- 1.3.6.1.4.1.9839.2.1.3.122
        allarmi2-cdz2 OBJECT-TYPE
                    SYNTAX Integer32 (12345..12345)
                    UNITS "N/A"
                    MAX-ACCESS read-only
                    STATUS current
                    DESCRIPTION "ALARM CODE B CDZ2"
                    ::= { integerObjects 122 }

        -- 1.3.6.1.4.1.9839.2.1.3.123
        allarmi2-cdz3 OBJECT-TYPE
                    SYNTAX Integer32 (12345..12345)
                    UNITS "N/A"
                    MAX-ACCESS read-only
                    STATUS current
                    DESCRIPTION "ALARM CODE B CDZ3"
                    ::= { integerObjects 123 }

        -- 1.3.6.1.4.1.9839.2.1.3.124
        allarmi2-cdz4 OBJECT-TYPE
                    SYNTAX Integer32 (12345..12345)
                    UNITS "N/A"
                    MAX-ACCESS read-only
                    STATUS current
                    DESCRIPTION "ALARM CODE B CDZ4"
                    ::= { integerObjects 124 }

        -- 1.3.6.1.4.1.9839.2.1.3.125
        allarmi2-cdz5 OBJECT-TYPE
                    SYNTAX Integer32 (12345..12345)
                    UNITS "N/A"
                    MAX-ACCESS read-only
                    STATUS current
                    DESCRIPTION "ALARM CODE B CDZ5"
                    ::= { integerObjects 125 }

        -- 1.3.6.1.4.1.9839.2.1.3.126
        allarmi2-cdz6 OBJECT-TYPE
                    SYNTAX Integer32 (12345..12345)
                    UNITS "N/A"
                    MAX-ACCESS read-only
                    STATUS current
                    DESCRIPTION "ALARM CODE B CDZ6"
                    ::= { integerObjects 126 }

        -- 1.3.6.1.4.1.9839.2.1.3.127
        allarmi2-cdz7 OBJECT-TYPE
                    SYNTAX Integer32 (12345..12345)
                    UNITS "N/A"
                    MAX-ACCESS read-only
                    STATUS current
                    DESCRIPTION "ALARM CODE B CDZ7"
                    ::= { integerObjects 127 }

        -- 1.3.6.1.4.1.9839.2.1.3.128
        allarmi2-cdz8 OBJECT-TYPE
                    SYNTAX Integer32 (12345..12345)
                    UNITS "N/A"
                    MAX-ACCESS read-only
                    STATUS current
                    DESCRIPTION "ALARM CODE B CDZ8"
                    ::= { integerObjects 128 }

        -- 1.3.6.1.4.1.9839.2.1.3.129
        allarmi2-cdz9 OBJECT-TYPE
                    SYNTAX Integer32 (12345..12345)
                    UNITS "N/A"
                    MAX-ACCESS read-only
                    STATUS current
                    DESCRIPTION "ALARM CODE B CDZ9"
                    ::= { integerObjects 129 }

        -- 1.3.6.1.4.1.9839.2.1.3.130
        allarmi2-cdz10 OBJECT-TYPE
                    SYNTAX Integer32 (12345..12345)
                    UNITS "N/A"
                    MAX-ACCESS read-only
                    STATUS current
                    DESCRIPTION "ALARM CODE B CDZ10"
                    ::= { integerObjects 130 }


	
	END

--
-- CAREL-mstaf.MIB
--
