--
-- ug40cdzDE.MIB
-- MIB generated by UNIFLAIR
-- Tuesday, 12 January 2009
--

    UNIFLAIR-ug40cdzDE-MIB DEFINITIONS ::= BEGIN
 
		IMPORTS
			OBJECT-GROUP		FROM SNMPv2-CONF			
			sysContact, sysName,
			sysLocation		FROM SNMPv2-MIB
			enterprises, MODULE-IDENTITY,
			OBJECT-TYPE, Integer32	FROM SNMPv2-SMI
			DisplayString		FROM RFC1213-MIB;		
		
        ug40cdzDEMIB MODULE-IDENTITY
      		LAST-UPDATED  "200604111645Z"		-- April 11, 2006 at 16:45 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the UG40 Close Control Uniflair device."
		REVISION   "200604111645Z"		-- April 11, 2006 at 16:45 GMT
		DESCRIPTION
		"This is the original version of this MIB"
			::= { instruments 1 }
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { ug40cdzDEMIB 1 }

        -- 1.3.6.1.4.1.9839.2.1.1.1
        systemOn OBJECT-TYPE
                    SYNTAX Integer32 (0..1)
                    UNITS "N/A"
                    MAX-ACCESS read-only
                    STATUS current
                    DESCRIPTION "GERAET"
                    ::= { digitalObjects 1 }

        -- 1.3.6.1.4.1.9839.2.1.1.2
        compressore1 OBJECT-TYPE
                    SYNTAX Integer32 (0..1)
                    UNITS "N/A"
                    MAX-ACCESS read-only
                    STATUS current
                    DESCRIPTION "VERDICHTER 1"
                    ::= { digitalObjects 2 }

        -- 1.3.6.1.4.1.9839.2.1.1.3
        compressore2 OBJECT-TYPE
                    SYNTAX Integer32 (0..1)
                    UNITS "N/A"
                    MAX-ACCESS read-only
                    STATUS current
                    DESCRIPTION "VERDICHTER 2"
                    ::= { digitalObjects 3 }

        -- 1.3.6.1.4.1.9839.2.1.1.4
        compressore3 OBJECT-TYPE
                    SYNTAX Integer32 (0..1)
                    UNITS "N/A"
                    MAX-ACCESS read-only
                    STATUS current
                    DESCRIPTION "VERDICHTER 3"
                    ::= { digitalObjects 4 }

        -- 1.3.6.1.4.1.9839.2.1.1.5
        compressore4 OBJECT-TYPE
                    SYNTAX Integer32 (0..1)
                    UNITS "N/A"
                    MAX-ACCESS read-only
                    STATUS current
                    DESCRIPTION "VERDICHTER 4"
                    ::= { digitalObjects 5 }

        -- 1.3.6.1.4.1.9839.2.1.1.6
        heating1 OBJECT-TYPE
                    SYNTAX Integer32 (0..1)
                    UNITS "N/A"
                    MAX-ACCESS read-only
                    STATUS current
                    DESCRIPTION "ELEKTROHEIZUNG 1"
                    ::= { digitalObjects 6 }

        -- 1.3.6.1.4.1.9839.2.1.1.7
        heating2 OBJECT-TYPE
                    SYNTAX Integer32 (0..1)
                    UNITS "N/A"
                    MAX-ACCESS read-only
                    STATUS current
                    DESCRIPTION "ELEKTROHEIZUNG 2"
                    ::= { digitalObjects 7 }

        -- 1.3.6.1.4.1.9839.2.1.1.9
        hotGasCoil OBJECT-TYPE
                    SYNTAX Integer32 (0..1)
                    UNITS "N/A"
                    MAX-ACCESS read-only
                    STATUS current
                    DESCRIPTION "HEISSGASHEIZUNG"
                    ::= { digitalObjects 9 }

        -- 1.3.6.1.4.1.9839.2.1.1.10
        dehumidification OBJECT-TYPE
                    SYNTAX Integer32 (0..1)
                    UNITS "N/A"
                    MAX-ACCESS read-only
                    STATUS current
                    DESCRIPTION "Entfeuchtung"
                    ::= { digitalObjects 10 }

        -- 1.3.6.1.4.1.9839.2.1.1.11
        humidification OBJECT-TYPE
                    SYNTAX Integer32 (0..1)
                    UNITS "N/A"
                    MAX-ACCESS read-only
                    STATUS current
                    DESCRIPTION "Befeuchtung"
                    ::= { digitalObjects 11 }

        -- 1.3.6.1.4.1.9839.2.1.1.12
        emerg OBJECT-TYPE
                    SYNTAX Integer32 (0..1)
                    UNITS "N/A"
                    MAX-ACCESS read-only
                    STATUS current
                    DESCRIPTION "Stromausfall"
                    ::= { digitalObjects 12 }
  
        -- 1.3.6.1.4.1.9839.2.1.1.20
        alarmAccess OBJECT-TYPE
                    SYNTAX Integer32 (0..1)
                    UNITS "N/A"
                    MAX-ACCESS read-only
                    STATUS current
                    DESCRIPTION "Dreimal ein Falsches Passwort Benutzt"
                    ::= { digitalObjects 20 }

        -- 1.3.6.1.4.1.9839.2.1.1.21
        alarmRoomHT OBJECT-TYPE
                    SYNTAX Integer32 (0..1)
                    UNITS "N/A"
                    MAX-ACCESS read-only
                    STATUS current
                    DESCRIPTION "Alarm: Raumtemperatur ueber Maximalwert"
                    ::= { digitalObjects 21 }

        -- 1.3.6.1.4.1.9839.2.1.1.22
        alarmRoomLT OBJECT-TYPE
                    SYNTAX Integer32 (0..1)
                    UNITS "N/A"
                    MAX-ACCESS read-only
                    STATUS current
                    DESCRIPTION "Alarm: Raumtemperatur unter Minimalwert"
                    ::= { digitalObjects 22 }

        -- 1.3.6.1.4.1.9839.2.1.1.23
        alarmRoomHH OBJECT-TYPE
                    SYNTAX Integer32 (0..1)
                    UNITS "N/A"
                    MAX-ACCESS read-only
                    STATUS current
                    DESCRIPTION "Alarm: relative Feuchte ueber Maximalwert"
                    ::= { digitalObjects 23 }

        -- 1.3.6.1.4.1.9839.2.1.1.24
        alarmRoomLH OBJECT-TYPE
                    SYNTAX Integer32 (0..1)
                    UNITS "N/A"
                    MAX-ACCESS read-only
                    STATUS current
                    DESCRIPTION "Alarm: relative Feuchte unter Minimalwert"
                    ::= { digitalObjects 24 }

        -- 1.3.6.1.4.1.9839.2.1.1.25
        alarmRoomEAP OBJECT-TYPE
                    SYNTAX Integer32 (0..1)
                    UNITS "N/A"
                    MAX-ACCESS read-only
                    STATUS current
                    DESCRIPTION "Alarm: Raumgrenzwert ueberschritten (externe Fuehler)"
                    ::= { digitalObjects 25 }

        -- 1.3.6.1.4.1.9839.2.1.1.26
        alarmFilter OBJECT-TYPE
                    SYNTAX Integer32 (0..1)
                    UNITS "N/A"
                    MAX-ACCESS read-only
                    STATUS current
                    DESCRIPTION "Alarm: Filter verschmutzt: Filter reinigen bzw. wechseln"
                    ::= { digitalObjects 26 }

        -- 1.3.6.1.4.1.9839.2.1.1.27
        alarmFlood OBJECT-TYPE
                    SYNTAX Integer32 (0..1)
                    UNITS "N/A"
                    MAX-ACCESS read-only
                    STATUS current
                    DESCRIPTION "Alarm: Wasserverlust"
                    ::= { digitalObjects 27 }

        -- 1.3.6.1.4.1.9839.2.1.1.28
        alarmAirFlow OBJECT-TYPE
                    SYNTAX Integer32 (0..1)
                    UNITS "N/A"
                    MAX-ACCESS read-only
                    STATUS current
                    DESCRIPTION "Alarm: keine Luftstroemung Ventilatoren bzw. Waechter pruefen"
                    ::= { digitalObjects 28 }

        -- 1.3.6.1.4.1.9839.2.1.1.29
        alarmHeater OBJECT-TYPE
                    SYNTAX Integer32 (0..1)
                    UNITS "N/A"
                    MAX-ACCESS read-only
                    STATUS current
                    DESCRIPTION "Alarm: Erhitzer ueberhitzt"
                    ::= { digitalObjects 29 }

        -- 1.3.6.1.4.1.9839.2.1.1.30
        alarmHP1 OBJECT-TYPE
                    SYNTAX Integer32 (0..1)
                    UNITS "N/A"
                    MAX-ACCESS read-only
                    STATUS current
                    DESCRIPTION "Alarm: Kreis 1 Hochdruck bzw. Fehler der Verdichter Schuetz"
                    ::= { digitalObjects 30 }

        -- 1.3.6.1.4.1.9839.2.1.1.31
        alarmHP2 OBJECT-TYPE
                    SYNTAX Integer32 (0..1)
                    UNITS "N/A"
                    MAX-ACCESS read-only
                    STATUS current
                    DESCRIPTION "Alarm: Kreis 2 Hochdruck bzw. Fehler der Verdichter Schuetz"
                    ::= { digitalObjects 31 }

        -- 1.3.6.1.4.1.9839.2.1.1.32
        alarmLP1 OBJECT-TYPE
                    SYNTAX Integer32 (0..1)
                    UNITS "N/A"
                    MAX-ACCESS read-only
                    STATUS current
                    DESCRIPTION "Alarm: Kreis 1 Niederdruck"
                    ::= { digitalObjects 32 }

        -- 1.3.6.1.4.1.9839.2.1.1.33
        alarmLP2 OBJECT-TYPE
                    SYNTAX Integer32 (0..1)
                    UNITS "N/A"
                    MAX-ACCESS read-only
                    STATUS current
                    DESCRIPTION "Alarm: Alarm: Kreis 2 Niederdruck"
                    ::= { digitalObjects 33 }

        -- 1.3.6.1.4.1.9839.2.1.1.34
        alarmEXV1 OBJECT-TYPE
                    SYNTAX Integer32 (0..1)
                    UNITS "N/A"
                    MAX-ACCESS read-only
                    STATUS current
                    DESCRIPTION "Alarm: Stoerung Elektroventil C1"
                    ::= { digitalObjects 34 }

        -- 1.3.6.1.4.1.9839.2.1.1.35
        alarmEXV2 OBJECT-TYPE
                    SYNTAX Integer32 (0..1)
                    UNITS "N/A"
                    MAX-ACCESS read-only
                    STATUS current
                    DESCRIPTION "Alarm: Stoerung Elektroventil C2"
                    ::= { digitalObjects 35 }

        -- 1.3.6.1.4.1.9839.2.1.1.36
        alarmPSE OBJECT-TYPE
                    SYNTAX Integer32 (0..1)
                    UNITS "N/A"
                    MAX-ACCESS read-only
                    STATUS current
                    DESCRIPTION "Alarm: Stoerung falsche Phasenfolge"
                    ::= { digitalObjects 36 }

        -- 1.3.6.1.4.1.9839.2.1.1.37
        alarmSmokeFire OBJECT-TYPE
                    SYNTAX Integer32 (0..1)
                    UNITS "N/A"
                    MAX-ACCESS read-only
                    STATUS current
                    DESCRIPTION "Alarm: RAUCH bzw. FEUER gemeldet"
                    ::= { digitalObjects 37 }

        -- 1.3.6.1.4.1.9839.2.1.1.38
        alarmLAN OBJECT-TYPE
                    SYNTAX Integer32 (0..1)
                    UNITS "N/A"
                    MAX-ACCESS read-only
                    STATUS current
                    DESCRIPTION "Alarm: LAN unterbrochen"
                    ::= { digitalObjects 38 }

        -- 1.3.6.1.4.1.9839.2.1.1.39
        alarmHUHC OBJECT-TYPE
                    SYNTAX Integer32 (0..1)
                    UNITS "N/A"
                    MAX-ACCESS read-only
                    STATUS current
                    DESCRIPTION "Alarm: Befeuchter: Hochstrom"
                    ::= { digitalObjects 39 }

        -- 1.3.6.1.4.1.9839.2.1.1.40
        alarmHUPL OBJECT-TYPE
                    SYNTAX Integer32 (0..1)
                    UNITS "N/A"
                    MAX-ACCESS read-only
                    STATUS current
                    DESCRIPTION "Alarm: Befeuchter: keine elekt.Stromspeise Anschlusse pruefen"
                    ::= { digitalObjects 40 }

        -- 1.3.6.1.4.1.9839.2.1.1.41
        alarmHUWL OBJECT-TYPE
                    SYNTAX Integer32 (0..1)
                    UNITS "N/A"
                    MAX-ACCESS read-only
                    STATUS current
                    DESCRIPTION "Alarm: Befeuchter: Wasser unverfuegbar"
                    ::= { digitalObjects 41 }

        -- 1.3.6.1.4.1.9839.2.1.1.42
        alarmCWDHT OBJECT-TYPE
                    SYNTAX Integer32 (0..1)
                    UNITS "N/A"
                    MAX-ACCESS read-only
                    STATUS current
                    DESCRIPTION "Alarm: Wasser zu warm zum Entfeuchten Kaltwassersatz pruefen"
                    ::= { digitalObjects 42 }

        -- 1.3.6.1.4.1.9839.2.1.1.43
        alarmCWF OBJECT-TYPE
                    SYNTAX Integer32 (0..1)
                    UNITS "N/A"
                    MAX-ACCESS read-only
                    STATUS current
                    DESCRIPTION "Alarm: Kaltwasserventil defekt bzw. keine Wasserstroemung"
                    ::= { digitalObjects 43 }

        -- 1.3.6.1.4.1.9839.2.1.1.44
        alarmCWFF OBJECT-TYPE
                    SYNTAX Integer32 (0..1)
                    UNITS "N/A"
                    MAX-ACCESS read-only
                    STATUS current
                    DESCRIPTION "Alarm: keine Kaltwasserstroemung: Wasserkreis kontrollieren"
                    ::= { digitalObjects 44 }

        -- 1.3.6.1.4.1.9839.2.1.1.45
        alarmCWHT OBJECT-TYPE
                    SYNTAX Integer32 (0..1)
                    UNITS "N/A"
                    MAX-ACCESS read-only
                    STATUS current
                    DESCRIPTION "Alarm: Hohe Kaltwassertemperat. Kaltwassersatz pruefen"
                    ::= { digitalObjects 45 }

        -- 1.3.6.1.4.1.9839.2.1.1.46
        alarmRTS OBJECT-TYPE
                    SYNTAX Integer32 (0..1)
                    UNITS "N/A"
                    MAX-ACCESS read-only
                    STATUS current
                    DESCRIPTION "Alarm: Raumtemperatur Fuehler defekt/abgeklemmt"
                    ::= { digitalObjects 46 }

        -- 1.3.6.1.4.1.9839.2.1.1.47
        alarmHWS OBJECT-TYPE
                    SYNTAX Integer32 (0..1)
                    UNITS "N/A"
                    MAX-ACCESS read-only
                    STATUS current
                    DESCRIPTION "Alarm: Warmwassertemperatur Fuehler defekt/abgeklemmt"
                    ::= { digitalObjects 47 }

        -- 1.3.6.1.4.1.9839.2.1.1.48
        alarmCWS OBJECT-TYPE
                    SYNTAX Integer32 (0..1)
                    UNITS "N/A"
                    MAX-ACCESS read-only
                    STATUS current
                    DESCRIPTION "Alarm: Wassereingangtemper. Fuehler defekt/abgeklemmt"
                    ::= { digitalObjects 48 }

        -- 1.3.6.1.4.1.9839.2.1.1.49
        alarmOTS OBJECT-TYPE
                    SYNTAX Integer32 (0..1)
                    UNITS "N/A"
                    MAX-ACCESS read-only
                    STATUS current
                    DESCRIPTION "Alarm: Aussentemperatur Fuehler defekt/abgeklemmt"
                    ::= { digitalObjects 49 }

        -- 1.3.6.1.4.1.9839.2.1.1.50
        alarmDTS OBJECT-TYPE
                    SYNTAX Integer32 (0..1)
                    UNITS "N/A"
                    MAX-ACCESS read-only
                    STATUS current
                    DESCRIPTION "Alarm: Zulufttemperatur Fuehler defekt/abgeklemmt"
                    ::= { digitalObjects 50 }

        -- 1.3.6.1.4.1.9839.2.1.1.51
        alarmRHS OBJECT-TYPE
                    SYNTAX Integer32 (0..1)
                    UNITS "N/A"
                    MAX-ACCESS read-only
                    STATUS current
                    DESCRIPTION "Alarm: Raumfeuchtefuehler defekt/abgeklemmt"
                    ::= { digitalObjects 51 }

        -- 1.3.6.1.4.1.9839.2.1.1.52
        alarmCWOTS OBJECT-TYPE
                    SYNTAX Integer32 (0..1)
                    UNITS "N/A"
                    MAX-ACCESS read-only
                    STATUS current
                    DESCRIPTION "Alarm: Wasserausgangtemper. Fuehler defekt/abgeklemmt"
                    ::= { digitalObjects 52 }

        -- 1.3.6.1.4.1.9839.2.1.1.53
        alarmC1Hours OBJECT-TYPE
                    SYNTAX Integer32 (0..1)
                    UNITS "N/A"
                    MAX-ACCESS read-only
                    STATUS current
                    DESCRIPTION "Dienstmitteil.: Verdichter 1 hat Betriebstunden ueberschritten"
                    ::= { digitalObjects 53 }

        -- 1.3.6.1.4.1.9839.2.1.1.54
        alarmC2Hours OBJECT-TYPE
                    SYNTAX Integer32 (0..1)
                    UNITS "N/A"
                    MAX-ACCESS read-only
                    STATUS current
                    DESCRIPTION "Dienstmitteil.: Verdichter 2 hat Betriebstunden ueberschritten"
                    ::= { digitalObjects 54 }

        -- 1.3.6.1.4.1.9839.2.1.1.55
        alarmC3Hours OBJECT-TYPE
                    SYNTAX Integer32 (0..1)
                    UNITS "N/A"
                    MAX-ACCESS read-only
                    STATUS current
                    DESCRIPTION "Dienstmitteil.: Verdichter 3 hat Betriebstunden ueberschritten"
                    ::= { digitalObjects 55 }

        -- 1.3.6.1.4.1.9839.2.1.1.56
        alarmC4Hours OBJECT-TYPE
                    SYNTAX Integer32 (0..1)
                    UNITS "N/A"
                    MAX-ACCESS read-only
                    STATUS current
                    DESCRIPTION "Dienstmitteil.: Verdichter 4 hat Betriebstunden ueberschritten"
                    ::= { digitalObjects 56 }

        -- 1.3.6.1.4.1.9839.2.1.1.57
        alarmFilterHours OBJECT-TYPE
                    SYNTAX Integer32 (0..1)
                    UNITS "N/A"
                    MAX-ACCESS read-only
                    STATUS current
                    DESCRIPTION "Dienstmitteil.: Luftfilter haben Betriebsstdn. ueberschritten"
                    ::= { digitalObjects 57 }

        -- 1.3.6.1.4.1.9839.2.1.1.58
        alarmHeat1Hours OBJECT-TYPE
                    SYNTAX Integer32 (0..1)
                    UNITS "N/A"
                    MAX-ACCESS read-only
                    STATUS current
                    DESCRIPTION "Dienstmitteil.: El.Erhitzer 1 hat Betriebstunden ueberschritten"
                    ::= { digitalObjects 58 }

        -- 1.3.6.1.4.1.9839.2.1.1.59
        alarmHeat2Hours OBJECT-TYPE
                    SYNTAX Integer32 (0..1)
                    UNITS "N/A"
                    MAX-ACCESS read-only
                    STATUS current
                    DESCRIPTION "Dienstmitteil.: El.Erhitzer 2 hat Betriebstunden ueberschritten"
                    ::= { digitalObjects 59 }

        -- 1.3.6.1.4.1.9839.2.1.1.60
        alarmHumHours OBJECT-TYPE
                    SYNTAX Integer32 (0..1)
                    UNITS "N/A"
                    MAX-ACCESS read-only
                    STATUS current
                    DESCRIPTION "Dienstmitteil.: Befeuchter hat Betriebstunden ueberschritten"
                    ::= { digitalObjects 60 }

        -- 1.3.6.1.4.1.9839.2.1.1.61
        alarmUnitHours OBJECT-TYPE
                    SYNTAX Integer32 (0..1)
                    UNITS "N/A"
                    MAX-ACCESS read-only
                    STATUS current
                    DESCRIPTION "Dienstmitteil.: das Geraet hat Unit hour counter threshold"
                    ::= { digitalObjects 61 }

        -- 1.3.6.1.4.1.9839.2.1.1.62
        alarmDI2 OBJECT-TYPE
                    SYNTAX Integer32 (0..1)
                    UNITS "N/A"
                    MAX-ACCESS read-only
                    STATUS current
                    DESCRIPTION "Alarmkontakt ID2"
                    ::= { digitalObjects 62 }

        -- 1.3.6.1.4.1.9839.2.1.1.63
        alarmDI4 OBJECT-TYPE
                    SYNTAX Integer32 (0..1)
                    UNITS "N/A"
                    MAX-ACCESS read-only
                    STATUS current
                    DESCRIPTION "Alarmkontakt ID4"
                    ::= { digitalObjects 63 }

        -- 1.3.6.1.4.1.9839.2.1.1.64
        alarmDI6 OBJECT-TYPE
                    SYNTAX Integer32 (0..1)
                    UNITS "N/A"
                    MAX-ACCESS read-only
                    STATUS current
                    DESCRIPTION "Alarmkontakt ID6"
                    ::= { digitalObjects 64 }

        -- 1.3.6.1.4.1.9839.2.1.1.65
        alarmHum OBJECT-TYPE
                    SYNTAX Integer32 (0..1)
                    UNITS "N/A"
                    MAX-ACCESS read-only
                    STATUS current
                    DESCRIPTION "Stoerung Befeuchter"
                    ::= { digitalObjects 65 }

        -- 1.3.6.1.4.1.9839.2.1.1.66
        alarmGeneral OBJECT-TYPE
                    SYNTAX Integer32 (0..1)
                    UNITS "N/A"
                    MAX-ACCESS read-only
                    STATUS current
                    DESCRIPTION "Sammelalarm"
                    ::= { digitalObjects 66 }

        -- 1.3.6.1.4.1.9839.2.1.1.67
        alarm2ndLevel OBJECT-TYPE
                    SYNTAX Integer32 (0..1)
                    UNITS "N/A"
                    MAX-ACCESS read-only
                    STATUS current
                    DESCRIPTION "GEZWUNGENER BETRIEBSWECHSEL ALARM"
                    ::= { digitalObjects 67 }

        -- 1.3.6.1.4.1.9839.2.1.1.68
        alarmA OBJECT-TYPE
                    SYNTAX Integer32 (0..1)
                    UNITS "N/A"
                    MAX-ACCESS read-only
                    STATUS current
                    DESCRIPTION "Alarmtyp A"
                    ::= { digitalObjects 68 }

        -- 1.3.6.1.4.1.9839.2.1.1.69
        alarmB OBJECT-TYPE
                    SYNTAX Integer32 (0..1)
                    UNITS "N/A"
                    MAX-ACCESS read-only
                    STATUS current
                    DESCRIPTION "Alarmtyp B"
                    ::= { digitalObjects 69 }

        -- 1.3.6.1.4.1.9839.2.1.1.70
        alarmC OBJECT-TYPE
                    SYNTAX Integer32 (0..1)
                    UNITS "N/A"
                    MAX-ACCESS read-only
                    STATUS current
                    DESCRIPTION "Alarmtyp C"
                    ::= { digitalObjects 70 }

        -- 1.3.6.1.4.1.9839.2.1.1.71
        selDXCW OBJECT-TYPE
                    SYNTAX Integer32 (0..1)
                    UNITS "N/A"
                    MAX-ACCESS read-write
                    STATUS current
                    DESCRIPTION "Schalter Direktverdampfung/Kaltwasser (TC Geraete)"
                    ::= { digitalObjects 71 }

        -- 1.3.6.1.4.1.9839.2.1.1.72
        selSW OBJECT-TYPE
                    SYNTAX Integer32 (0..1)
                    UNITS "N/A"
                    MAX-ACCESS read-write
                    STATUS current
                    DESCRIPTION "Sommer/Winter Waehlschalter"
                    ::= { digitalObjects 72 }

        -- 1.3.6.1.4.1.9839.2.1.1.75
        systemOnOff OBJECT-TYPE
                    SYNTAX Integer32 (0..1)
                    UNITS "N/A"
                    MAX-ACCESS read-write
                    STATUS current
                    DESCRIPTION "Geraet AUS/EIN"
                    ::= { digitalObjects 75 }

        -- 1.3.6.1.4.1.9839.2.1.1.76
        resetAlarm OBJECT-TYPE
                    SYNTAX Integer32 (0..1)
                    UNITS "N/A"
                    MAX-ACCESS read-write
                    STATUS current
                    DESCRIPTION "Alarm Reset"
                    ::= { digitalObjects 76 }

        -- 1.3.6.1.4.1.9839.2.1.1.77
        resetHrsFilt OBJECT-TYPE
                    SYNTAX Integer32 (0..1)
                    UNITS "N/A"
                    MAX-ACCESS read-write
                    STATUS current
                    DESCRIPTION "Luftfilter Betriebsstd. Reset"
                    ::= { digitalObjects 77 }

        -- 1.3.6.1.4.1.9839.2.1.1.78
        resetHrC1 OBJECT-TYPE
                    SYNTAX Integer32 (0..1)
                    UNITS "N/A"
                    MAX-ACCESS read-write
                    STATUS current
                    DESCRIPTION "Verdichter 1 Betriebsstd. Reset"
                    ::= { digitalObjects 78 }

        -- 1.3.6.1.4.1.9839.2.1.1.79
        resetHrC2 OBJECT-TYPE
                    SYNTAX Integer32 (0..1)
                    UNITS "N/A"
                    MAX-ACCESS read-write
                    STATUS current
                    DESCRIPTION "Verdichter 2 Betriebsstd. Reset"
                    ::= { digitalObjects 79 }

        -- 1.3.6.1.4.1.9839.2.1.1.80
        resetHrC3 OBJECT-TYPE
                    SYNTAX Integer32 (0..1)
                    UNITS "N/A"
                    MAX-ACCESS read-write
                    STATUS current
                    DESCRIPTION "Verdichter 3 Betriebsstd. Reset"
                    ::= { digitalObjects 80 }

        -- 1.3.6.1.4.1.9839.2.1.1.81
        resetHrC4 OBJECT-TYPE
                    SYNTAX Integer32 (0..1)
                    UNITS "N/A"
                    MAX-ACCESS read-write
                    STATUS current
                    DESCRIPTION "Verdichter 4 Betriebsstd. Reset"
                    ::= { digitalObjects 81 }

        -- 1.3.6.1.4.1.9839.2.1.1.82
        resetStC1 OBJECT-TYPE
                    SYNTAX Integer32 (0..1)
                    UNITS "N/A"
                    MAX-ACCESS read-write
                    STATUS current
                    DESCRIPTION "Verdichter 1 Startnummer Reset"
                    ::= { digitalObjects 82 }

        -- 1.3.6.1.4.1.9839.2.1.1.83
        resetStC2 OBJECT-TYPE
                    SYNTAX Integer32 (0..1)
                    UNITS "N/A"
                    MAX-ACCESS read-write
                    STATUS current
                    DESCRIPTION "Verdichter 2 Startnummer Reset"
                    ::= { digitalObjects 83 }

        -- 1.3.6.1.4.1.9839.2.1.1.84
        resetStC3 OBJECT-TYPE
                    SYNTAX Integer32 (0..1)
                    UNITS "N/A"
                    MAX-ACCESS read-write
                    STATUS current
                    DESCRIPTION "Verdichter 3 Startnummer Reset"
                    ::= { digitalObjects 84 }

        -- 1.3.6.1.4.1.9839.2.1.1.85
        resetStC4 OBJECT-TYPE
                    SYNTAX Integer32 (0..1)
                    UNITS "N/A"
                    MAX-ACCESS read-write
                    STATUS current
                    DESCRIPTION "Verdichter 4 Startnummer Reset"
                    ::= { digitalObjects 85 }

        -- 1.3.6.1.4.1.9839.2.1.1.86
        resetHrH1 OBJECT-TYPE
                    SYNTAX Integer32 (0..1)
                    UNITS "N/A"
                    MAX-ACCESS read-write
                    STATUS current
                    DESCRIPTION "El.Erhitzer 1 Betriebsstd. Reset"
                    ::= { digitalObjects 86 }


        -- 1.3.6.1.4.1.9839.2.1.1.87
        resetHrH2 OBJECT-TYPE
                    SYNTAX Integer32 (0..1)
                    UNITS "N/A"
                    MAX-ACCESS read-write
                    STATUS current
                    DESCRIPTION "El.Erhitzer 2 Betriebsstd. Reset"
                    ::= { digitalObjects 87 }

        -- 1.3.6.1.4.1.9839.2.1.1.88
        resetStH1 OBJECT-TYPE
                    SYNTAX Integer32 (0..1)
                    UNITS "N/A"
                    MAX-ACCESS read-write
                    STATUS current
                    DESCRIPTION "El.Erhitzer 1 Startnummer Reset"
                    ::= { digitalObjects 88 }

        -- 1.3.6.1.4.1.9839.2.1.1.89
        resetStH2 OBJECT-TYPE
                    SYNTAX Integer32 (0..1)
                    UNITS "N/A"
                    MAX-ACCESS read-write
                    STATUS current
                    DESCRIPTION "El.Erhitzer 2 Startnummer Reset"
                    ::= { digitalObjects 89 }

        -- 1.3.6.1.4.1.9839.2.1.1.90
        resetHrHU OBJECT-TYPE
                    SYNTAX Integer32 (0..1)
                    UNITS "N/A"
                    MAX-ACCESS read-write
                    STATUS current
                    DESCRIPTION "Befeuchter Betriebsstd. Reset"
                    ::= { digitalObjects 90 }

        -- 1.3.6.1.4.1.9839.2.1.1.91
        resetStHU OBJECT-TYPE
                    SYNTAX Integer32 (0..1)
                    UNITS "N/A"
                    MAX-ACCESS read-write
                    STATUS current
                    DESCRIPTION "Befeuchter Startnummer Reset"
                    ::= { digitalObjects 91 }

        -- 1.3.6.1.4.1.9839.2.1.1.92
        resetHrACU OBJECT-TYPE
                    SYNTAX Integer32 (0..1)
                    UNITS "N/A"
                    MAX-ACCESS read-write
                    STATUS current
                    DESCRIPTION "Geraet Betriebsstd. Reset"
                    ::= { digitalObjects 92 }

        -- 1.3.6.1.4.1.9839.2.1.1.95
        sleepmode OBJECT-TYPE
                    SYNTAX Integer32 (0..1)
                    UNITS "N/A"
                    MAX-ACCESS read-write
                    STATUS current
                    DESCRIPTION "BEREITSCHAFTSMODUS"
                    ::= { digitalObjects 95 }

        -- 1.3.6.1.4.1.9839.2.1.1.96
        smtest OBJECT-TYPE
                    SYNTAX Integer32 (0..1)
                    UNITS "N/A"
                    MAX-ACCESS read-write
                    STATUS current
                    DESCRIPTION "Zyklischer Anlauf"
                    ::= { digitalObjects 96 }

        -- 1.3.6.1.4.1.9839.2.1.1.97
        enablemeanT OBJECT-TYPE
                    SYNTAX Integer32 (0..1)
                    UNITS "N/A"
                    MAX-ACCESS read-write
                    STATUS current
                    DESCRIPTION "Lokalwerte/Mittelwert"
                    ::= { digitalObjects 97 }

 
        -- 1.3.6.1.4.1.9839.2.1.2
        analogObjects OBJECT IDENTIFIER ::= { ug40cdzDEMIB 2 }

        -- 1.3.6.1.4.1.9839.2.1.2.1
        roomTemp OBJECT-TYPE
                    SYNTAX Integer32 (-32767..32767)
                    UNITS "degrees C"
                    MAX-ACCESS read-only
                    STATUS current
                    DESCRIPTION "Raumtemperatur"
                    ::= { analogObjects 1 }

        -- 1.3.6.1.4.1.9839.2.1.2.2
        outdoorTemp OBJECT-TYPE
                    SYNTAX Integer32 (-32767..32767)
                    UNITS "degrees C"
                    MAX-ACCESS read-only
                    STATUS current
                    DESCRIPTION "Aussentemperatur"
                    ::= { analogObjects 2 }

        -- 1.3.6.1.4.1.9839.2.1.2.3
        deliveryTemp OBJECT-TYPE
                    SYNTAX Integer32 (-32767..32767)
                    UNITS "degrees C"
                    MAX-ACCESS read-write
                    STATUS current
                    DESCRIPTION "Zulufttemperatur"
                    ::= { analogObjects 3 }

        -- 1.3.6.1.4.1.9839.2.1.2.4
        cwTemp OBJECT-TYPE
                    SYNTAX Integer32 (-32767..32767)
                    UNITS "degrees C"
                    MAX-ACCESS read-only
                    STATUS current
                    DESCRIPTION "Wassertemp.ein"
                    ::= { analogObjects 4 }

        -- 1.3.6.1.4.1.9839.2.1.2.5
        hwTemp OBJECT-TYPE
                    SYNTAX Integer32 (-32767..32767)
                    UNITS "degrees C"
                    MAX-ACCESS read-only
                    STATUS current
                    DESCRIPTION "Warmwasser temperatur"
                    ::= { analogObjects 5 }

        -- 1.3.6.1.4.1.9839.2.1.2.6
        roomRH OBJECT-TYPE
                    SYNTAX Integer32 (-32767..32767)
                    UNITS "rH%"
                    MAX-ACCESS read-only
                    STATUS current
                    DESCRIPTION "Raumfeuchte"
                    ::= { analogObjects 6 }

        -- 1.3.6.1.4.1.9839.2.1.2.7
        cwoTemp OBJECT-TYPE
                    SYNTAX Integer32 (-32767..32767)
                    UNITS "degrees C"
                    MAX-ACCESS read-only
                    STATUS current
                    DESCRIPTION "Kaltwasser aus temperatur"
                    ::= { analogObjects 7 }

        -- 1.3.6.1.4.1.9839.2.1.2.8
        evapPress1 OBJECT-TYPE
                    SYNTAX Integer32 (-32767..32767)
                    UNITS "bar"
                    MAX-ACCESS read-write
                    STATUS current
                    DESCRIPTION "Kreis 1 Verd.Druck"
                    ::= { analogObjects 8 }

        -- 1.3.6.1.4.1.9839.2.1.2.9
        evapPress2 OBJECT-TYPE
                    SYNTAX Integer32 (-32767..32767)
                    UNITS "bar"
                    MAX-ACCESS read-write
                    STATUS current
                    DESCRIPTION "Kreis 2 Verd.Druck"
                    ::= { analogObjects 9 }

        -- 1.3.6.1.4.1.9839.2.1.2.10
        suctTemp1 OBJECT-TYPE
                    SYNTAX Integer32 (-32767..32767)
                    UNITS "degrees C"
                    MAX-ACCESS read-only
                    STATUS current
                    DESCRIPTION "Kreis 1 Ansaug Temp."
                    ::= { analogObjects 10 }

        -- 1.3.6.1.4.1.9839.2.1.2.11
        suctTemp2 OBJECT-TYPE
                    SYNTAX Integer32 (-32767..32767)
                    UNITS "degrees C"
                    MAX-ACCESS read-only
                    STATUS current
                    DESCRIPTION "Kreis 2 Ansaug Temp."
                    ::= { analogObjects 11 }

        -- 1.3.6.1.4.1.9839.2.1.2.12
        evapTemp1 OBJECT-TYPE
                    SYNTAX Integer32 (-32767..32767)
                    UNITS "degrees C"
                    MAX-ACCESS read-only
                    STATUS current
                    DESCRIPTION "Kreis 1 Verd.Temp."
                    ::= { analogObjects 12 }

        -- 1.3.6.1.4.1.9839.2.1.2.13
        evapTemp2 OBJECT-TYPE
                    SYNTAX Integer32 (-32767..32767)
                    UNITS "degrees C"
                    MAX-ACCESS read-only
                    STATUS current
                    DESCRIPTION "Kreis 2 Verd.Temp."
                    ::= { analogObjects 13 }

        -- 1.3.6.1.4.1.9839.2.1.2.14
        ssh1 OBJECT-TYPE
                    SYNTAX Integer32 (-32767..32767)
                    UNITS "degrees C"
                    MAX-ACCESS read-only
                    STATUS current
                    DESCRIPTION "Kreis 1 Uberhitzung"
                    ::= { analogObjects 14 }

        -- 1.3.6.1.4.1.9839.2.1.2.15
        ssh2 OBJECT-TYPE
                    SYNTAX Integer32 (-32767..32767)
                    UNITS "degrees C"
                    MAX-ACCESS read-only
                    STATUS current
                    DESCRIPTION "Kreis 2 Uberhitzung"
                    ::= { analogObjects 15 }

        -- 1.3.6.1.4.1.9839.2.1.2.16
        coolRamp OBJECT-TYPE
                    SYNTAX Integer32 (-32767..32767)
                    UNITS "%"
                    MAX-ACCESS read-only
                    STATUS current
                    DESCRIPTION "Wasserventil"
                    ::= { analogObjects 16 }

        -- 1.3.6.1.4.1.9839.2.1.2.17
        heatRamp OBJECT-TYPE
                    SYNTAX Integer32 (-32767..32767)
                    UNITS "%"
                    MAX-ACCESS read-only
                    STATUS current
                    DESCRIPTION "Warmwasserventil"
                    ::= { analogObjects 17 }

        -- 1.3.6.1.4.1.9839.2.1.2.18
        fanSpeed OBJECT-TYPE
                    SYNTAX Integer32 (-32767..32767)
                    UNITS "%"
                    MAX-ACCESS read-only
                    STATUS current
                    DESCRIPTION "Vent.Geschwind"
                    ::= { analogObjects 18 }

        -- 1.3.6.1.4.1.9839.2.1.2.20
        coolSetP OBJECT-TYPE
                    SYNTAX Integer32 (-32767..32767)
                    UNITS "degrees C"
                    MAX-ACCESS read-write
                    STATUS current
                    DESCRIPTION "Kuehlsollwert"
                    ::= { analogObjects 20 }

        -- 1.3.6.1.4.1.9839.2.1.2.21
        coolDiff OBJECT-TYPE
                    SYNTAX Integer32 (-32767..32767)
                    UNITS "degrees C"
                    MAX-ACCESS read-write
                    STATUS current
                    DESCRIPTION "Kuehl. Proport.Bereich"
                    ::= { analogObjects 21 }

        -- 1.3.6.1.4.1.9839.2.1.2.22
        cool2SetP OBJECT-TYPE
                    SYNTAX Integer32 (-32767..32767)
                    UNITS "degrees C"
                    MAX-ACCESS read-write
                    STATUS current
                    DESCRIPTION "2 Kuehlsollwert"
                    ::= { analogObjects 22 }

        -- 1.3.6.1.4.1.9839.2.1.2.23
        heatSetP OBJECT-TYPE
                    SYNTAX Integer32 (-32767..32767)
                    UNITS "degrees C"
                    MAX-ACCESS read-write
                    STATUS current
                    DESCRIPTION "Heizsollwert"
                    ::= { analogObjects 23 }

        -- 1.3.6.1.4.1.9839.2.1.2.24
        heat2SetP OBJECT-TYPE
                    SYNTAX Integer32 (-32767..32767)
                    UNITS "degrees C"
                    MAX-ACCESS read-write
                    STATUS current
                    DESCRIPTION "2 Heizsollwert"
                    ::= { analogObjects 24 }

        -- 1.3.6.1.4.1.9839.2.1.2.25
        heatDiff OBJECT-TYPE
                    SYNTAX Integer32 (-32767..32767)
                    UNITS "degrees C"
                    MAX-ACCESS read-write
                    STATUS current
                    DESCRIPTION "Heiz. Proport.Bereich"
                    ::= { analogObjects 25 }

        -- 1.3.6.1.4.1.9839.2.1.2.26
        thrsHT OBJECT-TYPE
                    SYNTAX Integer32 (-32767..32767)
                    UNITS "degrees C x10"
                    MAX-ACCESS read-write
                    STATUS current
                    DESCRIPTION "Max.Raumtemper."
                    ::= { analogObjects 26 }

        -- 1.3.6.1.4.1.9839.2.1.2.27
        thrsLT OBJECT-TYPE
                    SYNTAX Integer32 (-32767..32767)
                    UNITS "degrees C x10"
                    MAX-ACCESS read-write
                    STATUS current
                    DESCRIPTION "Min.Raumtemper."
                    ::= { analogObjects 27 }

        -- 1.3.6.1.4.1.9839.2.1.2.28
        smCoolSetp OBJECT-TYPE
                    SYNTAX Integer32 (-32767..32767)
                    UNITS "degrees C"
                    MAX-ACCESS read-write
                    STATUS current
                    DESCRIPTION "BEREITSCHAFTSMODUS: Max.Temp."
                    ::= { analogObjects 28 }

        -- 1.3.6.1.4.1.9839.2.1.2.29
        smHeatSetp OBJECT-TYPE
                    SYNTAX Integer32 (-32767..32767)
                    UNITS "degrees C"
                    MAX-ACCESS read-write
                    STATUS current
                    DESCRIPTION "BEREITSCHAFTSMODUS: Min.Temp."
                    ::= { analogObjects 29 }

        -- 1.3.6.1.4.1.9839.2.1.2.30
        cwDehumSetp OBJECT-TYPE
                    SYNTAX Integer32 (-32767..32767)
                    UNITS "degrees C"
                    MAX-ACCESS read-write
                    STATUS current
                    DESCRIPTION "Kaltwassersollwert zum Entfeuchten"
                    ::= { analogObjects 30 }

        -- 1.3.6.1.4.1.9839.2.1.2.31
        cwHtThrsh OBJECT-TYPE
                    SYNTAX Integer32 (-32767..32767)
                    UNITS "degrees C"
                    MAX-ACCESS read-write
                    STATUS current
                    DESCRIPTION "Hochtemperaturalarmgrenze Kaltwasser"
                    ::= { analogObjects 31 }

        -- 1.3.6.1.4.1.9839.2.1.2.32
        cwModeSetp OBJECT-TYPE
                    SYNTAX Integer32 (-32767..32767)
                    UNITS "degrees C"
                    MAX-ACCESS read-write
                    STATUS current
                    DESCRIPTION "Kaltwassersollwert um das Kaltwassermodus einzuschalten (TC Geraete)"
                    ::= { analogObjects 32 }

        -- 1.3.6.1.4.1.9839.2.1.2.33
        radcoolSpES OBJECT-TYPE
                    SYNTAX Integer32 (-32767..32767)
                    UNITS "degrees C"
                    MAX-ACCESS read-write
                    STATUS current
                    DESCRIPTION "Trockenkuehlersollwert bei Energiesparmodus"
                    ::= { analogObjects 33 }

        -- 1.3.6.1.4.1.9839.2.1.2.34
        radcoolSpDX OBJECT-TYPE
                    SYNTAX Integer32 (-32767..32767)
                    UNITS "degrees C"
                    MAX-ACCESS read-write
                    STATUS current
                    DESCRIPTION "Trockenkuehlersollwert bei Direktverdampfungsmodus"
                    ::= { analogObjects 34 }

        -- 1.3.6.1.4.1.9839.2.1.2.35
        delTempLimit OBJECT-TYPE
                    SYNTAX Integer32 (-32767..32767)
                    UNITS "degrees C x10"
                    MAX-ACCESS read-write
                    STATUS current
                    DESCRIPTION "Zulufttemperaturminimalsollwert"
                    ::= { analogObjects 35 }

        -- 1.3.6.1.4.1.9839.2.1.2.36
        dtAutChgMLT OBJECT-TYPE
                    SYNTAX Integer32 (-32767..32767)
                    UNITS "degrees C"
                    MAX-ACCESS read-write
                    STATUS current
                    DESCRIPTION "Aut.Abschwechselndiff Mittelw/Lokal"
                    ::= { analogObjects 36 }


        -- 1.3.6.1.4.1.9839.2.1.3
        integerObjects OBJECT IDENTIFIER ::= { ug40cdzDEMIB 3 }

        -- 1.3.6.1.4.1.9839.2.1.3.1
        filterWorkH OBJECT-TYPE
                    SYNTAX Integer32 (-32767..32767)
                    UNITS "h"
                    MAX-ACCESS read-only
                    STATUS current
                    DESCRIPTION "Luftfilter Betriebsstd."
                    ::= { integerObjects 1 }

        -- 1.3.6.1.4.1.9839.2.1.3.2
        unitWorkH OBJECT-TYPE
                    SYNTAX Integer32 (-32767..32767)
                    UNITS "h"
                    MAX-ACCESS read-only
                    STATUS current
                    DESCRIPTION "Geraet Run Hours"
                    ::= { integerObjects 2 }

        -- 1.3.6.1.4.1.9839.2.1.3.3
        compr1WorkH OBJECT-TYPE
                    SYNTAX Integer32 (-32767..32767)
                    UNITS "h"
                    MAX-ACCESS read-only
                    STATUS current
                    DESCRIPTION "Verdichter 1 Betriebsstd."
                    ::= { integerObjects 3 }

        -- 1.3.6.1.4.1.9839.2.1.3.4
        compr2WorkH OBJECT-TYPE
                    SYNTAX Integer32 (-32767..32767)
                    UNITS "h"
                    MAX-ACCESS read-only
                    STATUS current
                    DESCRIPTION "Verdichter 2 Betriebsstd."
                    ::= { integerObjects 4 }

        -- 1.3.6.1.4.1.9839.2.1.3.5
        compr3WorkH OBJECT-TYPE
                    SYNTAX Integer32 (-32767..32767)
                    UNITS "h"
                    MAX-ACCESS read-only
                    STATUS current
                    DESCRIPTION "Verdichter 3 Betriebsstd."
                    ::= { integerObjects 5 }

        -- 1.3.6.1.4.1.9839.2.1.3.6
        compr4WorkH OBJECT-TYPE
                    SYNTAX Integer32 (-32767..32767)
                    UNITS "h"
                    MAX-ACCESS read-only
                    STATUS current
                    DESCRIPTION "Verdichter 4 Betriebsstd."
                    ::= { integerObjects 6 }

        -- 1.3.6.1.4.1.9839.2.1.3.7
        heat1WorkH OBJECT-TYPE
                    SYNTAX Integer32 (-32767..32767)
                    UNITS "h"
                    MAX-ACCESS read-only
                    STATUS current
                    DESCRIPTION "El.Erhitzer 1 Betriebsstd."
                    ::= { integerObjects 7 }

        -- 1.3.6.1.4.1.9839.2.1.3.8
        heat2WorkH OBJECT-TYPE
                    SYNTAX Integer32 (-32767..32767)
                    UNITS "h"
                    MAX-ACCESS read-only
                    STATUS current
                    DESCRIPTION "El.Erhitzer 1 Betriebsstd. "
                    ::= { integerObjects 8 }

        -- 1.3.6.1.4.1.9839.2.1.3.9
        humiWorkH OBJECT-TYPE
                    SYNTAX Integer32 (-32767..32767)
                    UNITS "h"
                    MAX-ACCESS read-only
                    STATUS current
                    DESCRIPTION "Befeuchter Betriebsstd."
                    ::= { integerObjects 9 }

        -- 1.3.6.1.4.1.9839.2.1.3.12
        dehumPband OBJECT-TYPE
                    SYNTAX Integer32 (-32767..32767)
                    UNITS "rH%"
                    MAX-ACCESS read-write
                    STATUS current
                    DESCRIPTION "Proport.Bereich (Entfeuchte)"
                    ::= { integerObjects 12 }

        -- 1.3.6.1.4.1.9839.2.1.3.13
        humidPband OBJECT-TYPE
                    SYNTAX Integer32 (-32767..32767)
                    UNITS "rH%"
                    MAX-ACCESS read-write
                    STATUS current
                    DESCRIPTION "Proport.Bereich (Befeuchte)"
                    ::= { integerObjects 13 }

        -- 1.3.6.1.4.1.9839.2.1.3.14
        hhAlarmThrsh OBJECT-TYPE
                    SYNTAX Integer32 (-32767..32767)
                    UNITS "rH%"
                    MAX-ACCESS read-write
                    STATUS current
                    DESCRIPTION "Max.Raumfeuchte"
                    ::= { integerObjects 14 }

        -- 1.3.6.1.4.1.9839.2.1.3.15
        lhAlarmThrsh OBJECT-TYPE
                    SYNTAX Integer32 (-32767..32767)
                    UNITS "rH%"
                    MAX-ACCESS read-write
                    STATUS current
                    DESCRIPTION "Min.Raumfeuchte"
                    ::= { integerObjects 15 }

        -- 1.3.6.1.4.1.9839.2.1.3.16
        dehumSetp OBJECT-TYPE
                    SYNTAX Integer32 (-32767..32767)
                    UNITS "rH%"
                    MAX-ACCESS read-write
                    STATUS current
                    DESCRIPTION "Entfeuchtesollw."
                    ::= { integerObjects 16 }

        -- 1.3.6.1.4.1.9839.2.1.3.17
        smDehumSetp OBJECT-TYPE
                    SYNTAX Integer32 (-32767..32767)
                    UNITS "rH%"
                    MAX-ACCESS read-write
                    STATUS current
                    DESCRIPTION "BEREITSCHAFTSMODUS: Max.Feuchte"
                    ::= { integerObjects 17 }

        -- 1.3.6.1.4.1.9839.2.1.3.18
        humidSetp OBJECT-TYPE
                    SYNTAX Integer32 (-32767..32767)
                    UNITS "rH%"
                    MAX-ACCESS read-write
                    STATUS current
                    DESCRIPTION "Befeuchtesollw."
                    ::= { integerObjects 18 }

        -- 1.3.6.1.4.1.9839.2.1.3.19
        smHumidSetp OBJECT-TYPE
                    SYNTAX Integer32 (-32767..32767)
                    UNITS "rH%"
                    MAX-ACCESS read-write
                    STATUS current
                    DESCRIPTION "BEREITSCHAFTSMODUS: Min.Feuchte"
                    ::= { integerObjects 19 }

        -- 1.3.6.1.4.1.9839.2.1.3.20
        pwOnDelay OBJECT-TYPE
                    SYNTAX Integer32 (-32767..32767)
                    UNITS "s"
                    MAX-ACCESS read-write
                    STATUS current
                    DESCRIPTION "Wiederanlaufverzoegerung"
                    ::= { integerObjects 20 }

        -- 1.3.6.1.4.1.9839.2.1.3.21
        regulDelay OBJECT-TYPE
                    SYNTAX Integer32 (-32767..32767)
                    UNITS "s"
                    MAX-ACCESS read-write
                    STATUS current
                    DESCRIPTION "Einschaltuebergangzustand"
                    ::= { integerObjects 21 }

        -- 1.3.6.1.4.1.9839.2.1.3.22
        lowPdelay OBJECT-TYPE
                    SYNTAX Integer32 (-32767..32767)
                    UNITS "s"
                    MAX-ACCESS read-write
                    STATUS current
                    DESCRIPTION "Alarmverzoegerung bei Niederdruck"
                    ::= { integerObjects 22 }

        -- 1.3.6.1.4.1.9839.2.1.3.23
        thAlarmdelay OBJECT-TYPE
                    SYNTAX Integer32 (-32767..32767)
                    UNITS "min"
                    MAX-ACCESS read-write
                    STATUS current
                    DESCRIPTION "Alarmverzoegerung bei Temperatur- bzw. Feuchtegrenzeueberschreitung"
                    ::= { integerObjects 23 }

        -- 1.3.6.1.4.1.9839.2.1.3.24
        regExcTime OBJECT-TYPE
                    SYNTAX Integer32 (-32767..32767)
                    UNITS "min"
                    MAX-ACCESS read-write
                    STATUS current
                    DESCRIPTION "Pendelsperrekonstante"
                    ::= { integerObjects 24 }

        -- 1.3.6.1.4.1.9839.2.1.3.25
        stdbyTime OBJECT-TYPE
                    SYNTAX Integer32 (-32767..32767)
                    UNITS "h"
                    MAX-ACCESS read-write
                    STATUS current
                    DESCRIPTION "Verlaufszeit"
                    ::= { integerObjects 25 }

        -- 1.3.6.1.4.1.9839.2.1.3.27
        lanUnit OBJECT-TYPE
                    SYNTAX Integer32 (-32767..32767)
                    UNITS "n"
                    MAX-ACCESS read-write
                    STATUS current
                    DESCRIPTION "LAN Num.Geraet"
                    ::= { integerObjects 27 }

        -- 1.3.6.1.4.1.9839.2.1.3.28
        smCycleTime OBJECT-TYPE
                    SYNTAX Integer32 (-32767..32767)
                    UNITS "min"
                    MAX-ACCESS read-write
                    STATUS current
                    DESCRIPTION "Zeitabst"
                    ::= { integerObjects 28 }

        -- 1.3.6.1.4.1.9839.2.1.3.29
        exv1steps OBJECT-TYPE
                    SYNTAX Integer32 (-32767..32767)
                    UNITS "n"
                    MAX-ACCESS read-only
                    STATUS current
                    DESCRIPTION "Kreis 1 EXV Position"
                    ::= { integerObjects 29 }

        -- 1.3.6.1.4.1.9839.2.1.3.30
        exv2steps OBJECT-TYPE
                    SYNTAX Integer32 (-32767..32767)
                    UNITS "n"
                    MAX-ACCESS read-only
                    STATUS current
                    DESCRIPTION "Kreis 2 EXV Position"
                    ::= { integerObjects 30 }


	
	END

--
-- ug40cdzDE.MIB
--
