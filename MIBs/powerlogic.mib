NIOBRARA-POWERLOGIC-MIB-OLD DEFINITIONS ::= BEGIN

--  Title:    NRDPOWERLOGIC.MIB
--  Version:  v1.3
--  Date:     05/30/07
--
--  Copyright @ 2001-2007 Niobrara R&D Corporation.  All rights reserved worldwide.
--
--  This MIB defines objects for all SQUARE D POWERLOGIC QUCM SNMP Agents.
--

          IMPORTS
	      enterprises, Counter,
	      TimeTicks, Gauge, IpAddress     FROM RFC1155-SMI
          OBJECT-TYPE                     FROM RFC-1212
          sysUpTime, DisplayString        FROM RFC1213-MIB
	      TRAP-TYPE                       FROM RFC-1215;

	  niobrara OBJECT IDENTIFIER ::= { enterprises 6532 }




--
-- Niobrara Automation
--

    niobraraAutomation OBJECT IDENTIFIER ::= { niobrara 1 }

--
-- NRD Automation
--
	nrdExtensions OBJECT IDENTIFIER ::= { niobraraAutomation 1 }

	nrdExperimental OBJECT IDENTIFIER ::= { niobraraAutomation 2 }

	nrdPrivate OBJECT IDENTIFIER ::= { niobraraAutomation 3 }


--
-- NRD Extensions
--


	  ntrapargs                      OBJECT IDENTIFIER ::=  { nrdExtensions 10 }

-- the ntrapargs group
ntrapargsInteger OBJECT-TYPE
   SYNTAX INTEGER    
   ACCESS read-only
   STATUS mandatory
   DESCRIPTION
      "This OID allows Niobrara traps to be sent with an integer argument
       that my not be defined in the POWERLOGIC MIB.
      
       A get of this OID will return 0."
   ::= { ntrapargs 1 }
  
ntrapargsIpAddress OBJECT-TYPE
   SYNTAX IpAddress   
   ACCESS read-only
   STATUS mandatory
   DESCRIPTION
      "This OID allows Niobrara traps to be sent with an IP address argument
       that my not be defined in the POWERLOGIC MIB.
      
       A get of this OID will return 0.0.0.0."
   ::= { ntrapargs 2 }
   
ntrapargsString OBJECT-TYPE
   SYNTAX  DisplayString 
   ACCESS read-only
   STATUS mandatory
   DESCRIPTION
      "This OID allows Niobrara traps to be sent with an octet string argument
       that my not be defined in the POWERLOGIC MIB.
      
       A get of this OID will return a NULL string."
   ::= { ntrapargs 3 }

ntrapargsGauge OBJECT-TYPE
   SYNTAX  Gauge 
   ACCESS read-only
   STATUS mandatory
   DESCRIPTION
      "This OID allows Niobrara traps to be sent with a Gauge argument
       that my not be defined in the POWERLOGIC MIB.
      
       A get of this OID will return 0."
   ::= { ntrapargs 4 }

ntrapargsTimeTicks OBJECT-TYPE
   SYNTAX TimeTicks  
   ACCESS read-only
   STATUS mandatory
   DESCRIPTION
      "This OID allows Niobrara traps to be sent with a TimeTicks argument
       that my not be defined in the POWERLOGIC MIB.
      
       A get of this OID will return 0."
   ::= { ntrapargs 5 }



--
-- NRD Private
--

	nrdPowerlogic OBJECT IDENTIFIER ::= { nrdPrivate 1 }

          --
          --      The Device Identification group.
          --      All objects in this group are determined at device
	  	  --      initialization and remain static.
          --


          nrdcmIden        OBJECT IDENTIFIER ::= { nrdPowerlogic 1 }

          nrdcmSoftwareVersion OBJECT-TYPE
              SYNTAX DisplayString (SIZE (255))
              ACCESS read-only
              STATUS mandatory
              DESCRIPTION
                      "The QUCM SNMP Agent software version."
              ::= { nrdcmIden 1 }

          nrdcmFirmwareVersion OBJECT-TYPE
              SYNTAX DisplayString (SIZE (255))
              ACCESS read-only
              STATUS mandatory
              DESCRIPTION
                      "The QUCM firmware version."
              ::= { nrdcmIden 2 }

--
-- Circuit Monitor, Power Meters, Enercept, MCM Data
--

          nrdcmData     OBJECT IDENTIFIER ::= { nrdPowerlogic 2 }
          
          nrdcmNumMeters OBJECT-TYPE
              SYNTAX INTEGER (1..60)
              ACCESS read-only
              STATUS mandatory
              DESCRIPTION
                      "The number of meters configured in this
                      device. This entry indicates the number of rows in
                      the Data table."
              ::= { nrdcmData 1 }

          nrdcmDataTable OBJECT-TYPE
              SYNTAX SEQUENCE OF NrdcmDataEntry
              ACCESS not-accessible
              STATUS mandatory
              ::= { nrdcmData 2 }

          nrdcmDataEntry OBJECT-TYPE
              SYNTAX NrdcmDataEntry
              ACCESS not-accessible
              STATUS mandatory
              INDEX { nrdcmMeter }
              ::= { nrdcmDataTable 1 }

          NrdcmDataEntry ::= SEQUENCE {
              nrdcmMeter                        INTEGER,
              nrdcmModel                        DisplayString,
              nrdcmLabel                        DisplayString, 
              nrdcmNameplate					DisplayString,
              nrdcmMeterName					DisplayString,
              nrdcmNetworkName					DisplayString,
              nrdcmNetworkIP                    IpAddress,
              nrdcmMeterSlaveAddress            INTEGER,
              nrdcmBuildingName					DisplayString,
              nrdcmFrequency                    INTEGER,
              nrdcmTruePowerFactor              INTEGER,
              nrdcmDisplacementPowerFactor      INTEGER,
              nrdcmCurrentA                     INTEGER,
              nrdcmCurrentB                     INTEGER,
              nrdcmCurrentC                     INTEGER,
              nrdcmCurrentN                     INTEGER,
              nrdcmCurrentG                     INTEGER,
              nrdcmCurrentAVG                   INTEGER,
              nrdcmCurrentApparent              INTEGER,
              nrdcmVoltageAN                    INTEGER,
              nrdcmVoltageBN                    INTEGER,
              nrdcmVoltageCN                    INTEGER,
              nrdcmVoltageLNAvg                 INTEGER,
              nrdcmVoltageAB                    INTEGER,
              nrdcmVoltageBC                    INTEGER,
              nrdcmVoltageCA                    INTEGER,
              nrdcmVoltageLLAvg                 INTEGER,
              nrdcmRealPowerA                   INTEGER,
              nrdcmRealPowerB                   INTEGER,
              nrdcmRealPowerC                   INTEGER,
              nrdcmRealPowerTotal               INTEGER,
              nrdcmReactivePowerA               INTEGER,
              nrdcmReactivePowerB               INTEGER,
              nrdcmReactivePowerC               INTEGER,
              nrdcmReactivePowerTotal           INTEGER,
              nrdcmApparentPowerA               INTEGER,
              nrdcmApparentPowerB               INTEGER,
              nrdcmApparentPowerC               INTEGER,
              nrdcmApparentPowerTotal           INTEGER,
              nrdcmRealEnergyIn                 INTEGER,
              nrdcmReactiveEnergyIn             INTEGER,
              nrdcmRealEnergyOut		        INTEGER,
              nrdcmReactiveEnergyOut	        INTEGER,
              nrdcmApparentEnergy		        INTEGER,
              nrdcmRealEnergySignedTotal        INTEGER,
              nrdcmReactiveEnergySignedTotal    INTEGER,
          	  nrdcmIncrementalRealEnergyIn      INTEGER,
              nrdcmIncrementalReactiveEnergyIn  INTEGER,
              nrdcmIncrementalRealEnergyOut     INTEGER,
              nrdcmIncrementalReactiveEnergyOut INTEGER,
              nrdcmIncrementalApparentEnergy    INTEGER,
              nrdcmDemandPresentCurrentAvg      INTEGER,
              nrdcmDemandPresentCurrentA        INTEGER,
              nrdcmDemandPresentCurrentB        INTEGER,
              nrdcmDemandPresentCurrentC        INTEGER,
              nrdcmDemandPresentCurrentN        INTEGER,
              nrdcmDemandPeakCurrentAvg         INTEGER,
              nrdcmDemandPeakCurrentA           INTEGER,
              nrdcmDemandPeakCurrentB           INTEGER,
              nrdcmDemandPeakCurrentC           INTEGER,
              nrdcmDemandPeakCurrentN           INTEGER,
              nrdcmDemandPresentRealPower       INTEGER,
              nrdcmDemandPresentReactivePower   INTEGER,
              nrdcmDemandPresentApparentPower   INTEGER,
              nrdcmDemandPeakRealPower		    INTEGER,
              nrdcmDemandPeakReactivePower 	    INTEGER,
              nrdcmDemandPeakApparentPower 	    INTEGER
          }

          nrdcmMeter OBJECT-TYPE
              SYNTAX INTEGER (1..60)
              ACCESS read-only
              STATUS mandatory
              DESCRIPTION
                      "The meter number."
              ::= { nrdcmDataEntry 1 }
          
          nrdcmModel OBJECT-TYPE
              SYNTAX DisplayString (SIZE (255))
              ACCESS read-write
              STATUS mandatory
              DESCRIPTION
                      "The CM Model designation."
              ::= { nrdcmDataEntry 2 }

          nrdcmLabel OBJECT-TYPE
              SYNTAX DisplayString (SIZE (255))
              ACCESS read-only
              STATUS mandatory
              DESCRIPTION
                      "The CM Label."
              ::= { nrdcmDataEntry 3 }

          nrdcmNameplate OBJECT-TYPE
              SYNTAX DisplayString (SIZE (255))
              ACCESS read-only
              STATUS mandatory
              DESCRIPTION
                      "The CM Nameplate."
              ::= { nrdcmDataEntry 4 }

         nrdcmMeterName OBJECT-TYPE
              SYNTAX DisplayString (SIZE (255))
              ACCESS read-only
              STATUS mandatory
              DESCRIPTION
                      "The CM's Meter Name."
              ::= { nrdcmDataEntry 5 }

         nrdcmNetworkName OBJECT-TYPE
              SYNTAX DisplayString (SIZE (255))
              ACCESS read-only
              STATUS mandatory
              DESCRIPTION
                      "The CM's Network Device Name."
              ::= { nrdcmDataEntry 6 }
         
         nrdcmNetworkIP	OBJECT-TYPE
              SYNTAX	IpAddress
              ACCESS	read-only
	          STATUS	mandatory
	          DESCRIPTION
		            "The IP address of the meter's server"
		      ::= { nrdcmDataEntry 7 }

         nrdcmMeterSlaveAddress OBJECT-TYPE
              SYNTAX INTEGER (1..255)
              ACCESS read-only
              STATUS mandatory
              DESCRIPTION
                      "The meter's drop number."
              ::= { nrdcmDataEntry 8 }
          
         nrdcmBuildingName OBJECT-TYPE
              SYNTAX DisplayString (SIZE (255))
              ACCESS read-only
              STATUS mandatory
              DESCRIPTION
                      "The CM's Building Name."
              ::= { nrdcmDataEntry 9 }

          nrdcmFrequency OBJECT-TYPE
              SYNTAX INTEGER (0..32767)
              ACCESS read-only
              STATUS mandatory
              DESCRIPTION
                      "The line frequency.
                      (Unit of measure: .01 Hz)"
              ::= { nrdcmDataEntry 10 }
              
          nrdcmTruePowerFactor OBJECT-TYPE
              SYNTAX INTEGER (-32768..32767)
              ACCESS read-only
              STATUS mandatory
              DESCRIPTION
                      "The True Power Factor.
                      (Unit of measure: .001%)"
              ::= { nrdcmDataEntry 11 }

          nrdcmDisplacementPowerFactor OBJECT-TYPE
              SYNTAX INTEGER (-32768..32767)
              ACCESS read-only
              STATUS mandatory
              DESCRIPTION
                      "The Displacement Power Factor.
                      (Unit of measure: .001%)"
              ::= { nrdcmDataEntry 12 }
              
          nrdcmCurrentA OBJECT-TYPE
              SYNTAX INTEGER (0..2147483647)
              ACCESS read-only
              STATUS mandatory
              DESCRIPTION
                      "The Current, Phase A.
                      (Unit of measure: Amp)"
              ::= { nrdcmDataEntry 13 }
              
          nrdcmCurrentB OBJECT-TYPE
              SYNTAX INTEGER (0..2147483647)
              ACCESS read-only
              STATUS mandatory
              DESCRIPTION
                      "The Current, Phase B.
                      (Unit of measure: Amp)"
              ::= { nrdcmDataEntry 14 }

          nrdcmCurrentC OBJECT-TYPE
              SYNTAX INTEGER (0..21474783647)
              ACCESS read-only
              STATUS mandatory
              DESCRIPTION
                      "The Current, Phase C.
                      (Unit of measure: Amp)"
              ::= { nrdcmDataEntry 15 }

          nrdcmCurrentN OBJECT-TYPE
              SYNTAX INTEGER (0..2147483647)
              ACCESS read-only
              STATUS mandatory
              DESCRIPTION
                      "The Current, Neutral.
                      (Unit of measure: Amp)"
              ::= { nrdcmDataEntry 16 }
          
          nrdcmCurrentG OBJECT-TYPE
              SYNTAX INTEGER (0..21474783647)
              ACCESS read-only
              STATUS mandatory
              DESCRIPTION
                      "The Current, Phase G.
                      (Unit of measure: Amp)"
              ::= { nrdcmDataEntry 17 }
          
          nrdcmCurrentAVG OBJECT-TYPE
              SYNTAX INTEGER (0..21474783647)
              ACCESS read-only
              STATUS mandatory
              DESCRIPTION
                      "The Current, 3-Phase Avg.
                      (Unit of measure: Amp)"
              ::= { nrdcmDataEntry 18 }
              
          nrdcmCurrentApparent OBJECT-TYPE
              SYNTAX INTEGER (0..21474783647)
              ACCESS read-only
              STATUS mandatory
              DESCRIPTION
                      "The Apparent RMS Current.
                      (Unit of measure: Amp)"
              ::= { nrdcmDataEntry 19 }

          nrdcmVoltageAN OBJECT-TYPE
              SYNTAX INTEGER (0..21474783647)
              ACCESS read-only
              STATUS mandatory
              DESCRIPTION
                      "The Voltage, Phase A-N.
                      (Unit of measure: Volt)"
              ::= { nrdcmDataEntry 20 }

          nrdcmVoltageBN OBJECT-TYPE
              SYNTAX INTEGER (0..21474783647)
              ACCESS read-only
              STATUS mandatory
              DESCRIPTION
                      "The Voltage, Phase B-N.
                      (Unit of measure: Volt)"
              ::= { nrdcmDataEntry 21 }

          nrdcmVoltageCN OBJECT-TYPE
              SYNTAX INTEGER (0..21474783647)
              ACCESS read-only
              STATUS mandatory
              DESCRIPTION
                      "The Voltage, Phase C-N.
                      (Unit of measure: Volt)"
              ::= { nrdcmDataEntry 22 }

          nrdcmVoltageLNAvg OBJECT-TYPE
              SYNTAX INTEGER (0..21474783647)
              ACCESS read-only
              STATUS mandatory
              DESCRIPTION
                      "The Voltage, L-N Average.
                      (Unit of measure: Volt)"
              ::= { nrdcmDataEntry 23 }

          nrdcmVoltageAB OBJECT-TYPE
              SYNTAX INTEGER (0..21474783647)
              ACCESS read-only
              STATUS mandatory
              DESCRIPTION
                      "The Voltage, Phase A-B.
                      (Unit of measure: Volt)"
              ::= { nrdcmDataEntry 24 }

          nrdcmVoltageBC OBJECT-TYPE
              SYNTAX INTEGER (0..21474783647)
              ACCESS read-only
              STATUS mandatory
              DESCRIPTION
                      "The Voltage, Phase B-C.
                      (Unit of measure: Volt)"
              ::= { nrdcmDataEntry 25 }

          nrdcmVoltageCA OBJECT-TYPE
              SYNTAX INTEGER (0..21474783647)
              ACCESS read-only
              STATUS mandatory
              DESCRIPTION
                      "The Voltage, Phase C-A.
                      (Unit of measure: Volt)"
              ::= { nrdcmDataEntry 26 }

          nrdcmVoltageLLAvg OBJECT-TYPE
              SYNTAX INTEGER (0..21474783647)
              ACCESS read-only
              STATUS mandatory
              DESCRIPTION
                      "The Voltage, L-L Average.
                      (Unit of measure: Volt)"
              ::= { nrdcmDataEntry 27 }

          nrdcmRealPowerA OBJECT-TYPE
              SYNTAX INTEGER (-214747783648..21474783647)
              ACCESS read-only
              STATUS mandatory
              DESCRIPTION
                      "The Real Power, Phase A.
                      (Unit of measure: KW)"
              ::= { nrdcmDataEntry 28 }

          nrdcmRealPowerB OBJECT-TYPE
              SYNTAX INTEGER (-214747783648..21474783647)
              ACCESS read-only
              STATUS mandatory
              DESCRIPTION
                      "The Real Power, Phase B.
                      (Unit of measure: KW)"
              ::= { nrdcmDataEntry 29 }

          nrdcmRealPowerC OBJECT-TYPE
              SYNTAX INTEGER (-214747783648..21474783647)
              ACCESS read-only
              STATUS mandatory
              DESCRIPTION
                      "The Real Power, Phase C.
                      (Unit of measure: KW)"
              ::= { nrdcmDataEntry 30 }

          nrdcmRealPowerTotal OBJECT-TYPE
              SYNTAX INTEGER (-214747783648..21474783647)
              ACCESS read-only
              STATUS mandatory
              DESCRIPTION
                      "The Total Real Power.
                      (Unit of measure: KW)"
              ::= { nrdcmDataEntry 31 }

          nrdcmReactivePowerA OBJECT-TYPE
              SYNTAX INTEGER (-214747783648..21474783647)
              ACCESS read-only
              STATUS mandatory
              DESCRIPTION
                      "The Reactive Power, Phase A.
                      (Unit of measure: KVAr)"
              ::= { nrdcmDataEntry 32 }

          nrdcmReactivePowerB OBJECT-TYPE
              SYNTAX INTEGER (-214747783648..21474783647)
              ACCESS read-only
              STATUS mandatory
              DESCRIPTION
                      "The Reactive Power, Phase B.
                      (Unit of measure: KVAr)"
              ::= { nrdcmDataEntry 33 }

          nrdcmReactivePowerC OBJECT-TYPE
              SYNTAX INTEGER (-214747783648..21474783647)
              ACCESS read-only
              STATUS mandatory
              DESCRIPTION
                      "The Reactive Power, Phase C.
                      (Unit of measure: KVAr)"
              ::= { nrdcmDataEntry 34 }

          nrdcmReactivePowerTotal OBJECT-TYPE
              SYNTAX INTEGER (-214747783648..21474783647)
              ACCESS read-only
              STATUS mandatory
              DESCRIPTION
                      "The Total Reactive Power.
                      (Unit of measure: KVAr)"
              ::= { nrdcmDataEntry 35 }

          nrdcmApparentPowerA OBJECT-TYPE
              SYNTAX INTEGER (0..21474783647)
              ACCESS read-only
              STATUS mandatory
              DESCRIPTION
                      "The Apparent Power, Phase A.
                      (Unit of measure: KVA)"
              ::= { nrdcmDataEntry 36 }

          nrdcmApparentPowerB OBJECT-TYPE
              SYNTAX INTEGER (0..21474783647)
              ACCESS read-only
              STATUS mandatory
              DESCRIPTION
                      "The Apparent Power, Phase B.
                      (Unit of measure: KVA)"
              ::= { nrdcmDataEntry 37 }

          nrdcmApparentPowerC OBJECT-TYPE
              SYNTAX INTEGER (0..21474783647)
              ACCESS read-only
              STATUS mandatory
              DESCRIPTION
                      "The Apparent Power, Phase C.
                      (Unit of measure: KVA)"
              ::= { nrdcmDataEntry 38 }

          nrdcmApparentPowerTotal OBJECT-TYPE
              SYNTAX INTEGER (0..21474783647)
              ACCESS read-only
              STATUS mandatory
              DESCRIPTION
                      "The Total Apparent Power.
                      (Unit of measure: KVA)"
              ::= { nrdcmDataEntry 39 }

          nrdcmRealEnergyIn OBJECT-TYPE
              SYNTAX INTEGER (0..21474783647)
              ACCESS read-only
              STATUS mandatory
              DESCRIPTION
                      "The Real Energy In.
                      (Unit of measure: KWH)"
              ::= { nrdcmDataEntry 40 }

          nrdcmReactiveEnergyIn OBJECT-TYPE
              SYNTAX INTEGER (0..21474783647)
              ACCESS read-only
              STATUS mandatory
              DESCRIPTION
                      "The Reactive Energy In.
                      (Unit of measure: KVArH)"
              ::= { nrdcmDataEntry 41 }

          nrdcmRealEnergyOut OBJECT-TYPE
              SYNTAX INTEGER (0..21474783647)
              ACCESS read-only
              STATUS mandatory
              DESCRIPTION
                      "The Real Energy Out.
                      (Unit of measure: KWH)"
              ::= { nrdcmDataEntry 42 }

          nrdcmReactiveEnergyOut OBJECT-TYPE
              SYNTAX INTEGER (0..21474783647)
              ACCESS read-only
              STATUS mandatory
              DESCRIPTION
                      "The Reactive Energy Out.
                      (Unit of measure: KVArH)"
              ::= { nrdcmDataEntry 43 }

          nrdcmApparentEnergy OBJECT-TYPE
              SYNTAX INTEGER (0..21474783647)
              ACCESS read-only
              STATUS mandatory
              DESCRIPTION
                      "The Apparent Energy.
                      (Unit of measure: KVAH)"
              ::= { nrdcmDataEntry 44 }

          nrdcmRealEnergySignedTotal OBJECT-TYPE
              SYNTAX INTEGER (-214747783648..21474783647)
              ACCESS read-only
              STATUS mandatory
              DESCRIPTION
                      "The Signed, Total Real Energy.
                      (Unit of measure: KWH)"
              ::= { nrdcmDataEntry 45 }

          nrdcmReactiveEnergySignedTotal OBJECT-TYPE
              SYNTAX INTEGER (-214747783648..21474783647)
              ACCESS read-only
              STATUS mandatory
              DESCRIPTION
                      "The Signed, Total Reactive Energy.
                      (Unit of measure: KVArH)"
              ::= { nrdcmDataEntry 46 }

          nrdcmIncrementalRealEnergyIn OBJECT-TYPE
              SYNTAX INTEGER (0..21474783647)
              ACCESS read-only
              STATUS mandatory
              DESCRIPTION
                      "The Incremental Real Energy In.
                      (Unit of measure: KWH)"
              ::= { nrdcmDataEntry 47 }

          nrdcmIncrementalReactiveEnergyIn OBJECT-TYPE
              SYNTAX INTEGER (0..21474783647)
              ACCESS read-only
              STATUS mandatory
              DESCRIPTION
                      "The Incremental Reactive Energy In.
                      (Unit of measure: KVArH)"
              ::= { nrdcmDataEntry 48 }

          nrdcmIncrementalRealEnergyOut OBJECT-TYPE
              SYNTAX INTEGER (0..21474783647)
              ACCESS read-only
              STATUS mandatory
              DESCRIPTION
                      "The Incremental Real Energy Out.
                      (Unit of measure: KWH)"
              ::= { nrdcmDataEntry 49 }

          nrdcmIncrementalReactiveEnergyOut OBJECT-TYPE
              SYNTAX INTEGER (0..21474783647)
              ACCESS read-only
              STATUS mandatory
              DESCRIPTION
                      "The Incremental Reactive Energy Out.
                      (Unit of measure: KVArH)"
              ::= { nrdcmDataEntry 50 }

          nrdcmIncrementalApparentEnergy OBJECT-TYPE
              SYNTAX INTEGER (0..21474783647)
              ACCESS read-only
              STATUS mandatory
              DESCRIPTION
                      "The Incremental Apparent Energy.
                      (Unit of measure: KVAH)"
              ::= { nrdcmDataEntry 51 }

          nrdcmDemandPresentCurrentAvg OBJECT-TYPE
              SYNTAX INTEGER (0..21474783647)
              ACCESS read-only
              STATUS mandatory
              DESCRIPTION
                      "The Present Current Demand 3-Phase Average.
                      (Unit of measure: Amps)"
              ::= { nrdcmDataEntry 52 }

          nrdcmDemandPresentCurrentA OBJECT-TYPE
              SYNTAX INTEGER (0..21474783647)
              ACCESS read-only
              STATUS mandatory
              DESCRIPTION
                      "The Present Current Demand Phase A.
                      (Unit of measure: Amps)"
              ::= { nrdcmDataEntry 53 }

          nrdcmDemandPresentCurrentB OBJECT-TYPE
              SYNTAX INTEGER (0..21474783647)
              ACCESS read-only
              STATUS mandatory
              DESCRIPTION
                      "The Present Current Demand Phase B.
                      (Unit of measure: Amps)"
              ::= { nrdcmDataEntry 54 }
	                             
          nrdcmDemandPresentCurrentC OBJECT-TYPE
              SYNTAX INTEGER (0..21474783647)
              ACCESS read-only
              STATUS mandatory
              DESCRIPTION
                      "The Present Current Demand Phase C.
                      (Unit of measure: Amps)"
              ::= { nrdcmDataEntry 55 }

          nrdcmDemandPresentCurrentN OBJECT-TYPE
              SYNTAX INTEGER (0..21474783647)
              ACCESS read-only
              STATUS mandatory
              DESCRIPTION
                      "The Present Current Demand Phase N.
                      (Unit of measure: Amps)"
              ::= { nrdcmDataEntry 56 }
	                             
          nrdcmDemandPeakCurrentAvg OBJECT-TYPE
              SYNTAX INTEGER (0..21474783647)
              ACCESS read-only
              STATUS mandatory
              DESCRIPTION
                      "The Preak Current Demand 3-Phase Average.
                      (Unit of measure: Amps)"
              ::= { nrdcmDataEntry 57 }

          nrdcmDemandPeakCurrentA OBJECT-TYPE
              SYNTAX INTEGER (0..21474783647)
              ACCESS read-only
              STATUS mandatory
              DESCRIPTION
                      "The Preak Current Demand Phase A.
                      (Unit of measure: Amps)"
              ::= { nrdcmDataEntry 58 }

          nrdcmDemandPeakCurrentB OBJECT-TYPE
              SYNTAX INTEGER (0..21474783647)
              ACCESS read-only
              STATUS mandatory
              DESCRIPTION
                      "The Peak Current Demand Phase B.
                      (Unit of measure: Amps)"
              ::= { nrdcmDataEntry 59 }
	                             
          nrdcmDemandPeakCurrentC OBJECT-TYPE
              SYNTAX INTEGER (0..21474783647)
              ACCESS read-only
              STATUS mandatory
              DESCRIPTION
                      "The Peak Current Demand Phase C.
                      (Unit of measure: Amps)"
              ::= { nrdcmDataEntry 60 }

          nrdcmDemandPeakCurrentN OBJECT-TYPE
              SYNTAX INTEGER (0..21474783647)
              ACCESS read-only
              STATUS mandatory
              DESCRIPTION
                      "The Peak Current Demand Phase N.
                      (Unit of measure: Amps)"
              ::= { nrdcmDataEntry 61 }
	                             
          nrdcmDemandPresentRealPower OBJECT-TYPE
              SYNTAX INTEGER (-214747783648..21474783647)
              ACCESS read-only
              STATUS mandatory
              DESCRIPTION
                      "The Present Demand Real Power.
                      (Unit of measure: KVW)"
              ::= { nrdcmDataEntry 62 }

          nrdcmDemandPresentReactivePower OBJECT-TYPE
              SYNTAX INTEGER (-214747783648..21474783647)
              ACCESS read-only
              STATUS mandatory
              DESCRIPTION
                      "The Present Demand Reactive Power.
                      (Unit of measure: KVAr)"
              ::= { nrdcmDataEntry 63 }

          nrdcmDemandPresentApparentPower OBJECT-TYPE
              SYNTAX INTEGER (-214747783648..21474783647)
              ACCESS read-only
              STATUS mandatory
              DESCRIPTION
                      "The Present Demand Apparent Power.
                      (Unit of measure: KVA)"
              ::= { nrdcmDataEntry 64 }


          nrdcmDemandPeakRealPower OBJECT-TYPE
              SYNTAX INTEGER (-214747783648..21474783647)
              ACCESS read-only
              STATUS mandatory
              DESCRIPTION
                      "The Peak Demand Real Power.
                      (Unit of measure: KVW)"
              ::= { nrdcmDataEntry 65 }

          nrdcmDemandPeakReactivePower OBJECT-TYPE
              SYNTAX INTEGER (-214747783648..21474783647)
              ACCESS read-only
              STATUS mandatory
              DESCRIPTION
                      "The Peak Demand Reactive Power.
                      (Unit of measure: KVAr)"
              ::= { nrdcmDataEntry 66 }

          nrdcmDemandPeakApparentPower OBJECT-TYPE
              SYNTAX INTEGER (-214747783648..21474783647)
              ACCESS read-only
              STATUS mandatory
              DESCRIPTION
                      "The Peak Demand Apparent Power.
                      (Unit of measure: KVA)"
              ::= { nrdcmDataEntry 67 }



          --
          -- The Alarm group.
          --

          nrdcmAlarm     OBJECT IDENTIFIER ::= { nrdPowerlogic 3 }
          
          nrdcmAlarms OBJECT-TYPE
              SYNTAX Gauge
              ACCESS read-only
              STATUS optional
              DESCRIPTION
                      "The current number of alarm conditions."
              ::= { nrdcmAlarm 1 }

          nrdcmAlarmTable OBJECT-TYPE
              SYNTAX SEQUENCE OF NrdcmAlarmEntry
              ACCESS not-accessible
              STATUS optional
              ::= { nrdcmAlarm 2 }

          nrdcmAlarmEntry OBJECT-TYPE
              SYNTAX NrdcmAlarmEntry
              ACCESS not-accessible
              STATUS optional
              INDEX { nrdcmAlarmId }
              ::= { nrdcmAlarmTable 1 }

          NrdcmAlarmEntry ::= SEQUENCE {
              nrdcmAlarmId              INTEGER,
              nrdcmAlarmMeter           INTEGER,
              nrdcmAlarmMeterName		DisplayString,
              nrdcmAlarmNetworkName		DisplayString,
              nrdcmAlarmBuildingName	DisplayString,
              nrdcmAlarmDescr           INTEGER,
              nrdcmAlarmTime            DisplayString
          }

          nrdcmAlarmId OBJECT-TYPE
              SYNTAX INTEGER (0..2147483647)
              ACCESS read-only
              STATUS optional
              DESCRIPTION
                      "A unique identifier for an alarm condition. This
                      value must remain constant between agent
		              initializations."
              ::= { nrdcmAlarmEntry 1 }

          nrdcmAlarmMeter OBJECT-TYPE
              SYNTAX INTEGER
              ACCESS read-only
              STATUS optional
              DESCRIPTION
                      "The Meter number reporting the alarm."
              ::= { nrdcmAlarmEntry 2 }

         nrdcmAlarmMeterName OBJECT-TYPE
              SYNTAX DisplayString (SIZE (255))
              ACCESS read-only
              STATUS mandatory
              DESCRIPTION
                      "The CM's Meter Name."
              ::= { nrdcmAlarmEntry 3 }

         nrdcmAlarmNetworkName OBJECT-TYPE
              SYNTAX DisplayString (SIZE (255))
              ACCESS read-only
              STATUS mandatory
              DESCRIPTION
                      "The CM's Network Device Name."
              ::= { nrdcmAlarmEntry 4 }

         nrdcmAlarmBuildingName OBJECT-TYPE
              SYNTAX DisplayString (SIZE (255))
              ACCESS read-only
              STATUS mandatory
              DESCRIPTION
                      "The CM's Building Name."
              ::= { nrdcmAlarmEntry 5 }


          nrdcmAlarmDescr OBJECT-TYPE
              SYNTAX INTEGER {
              	online(1)
              	offline(2)
                   sts_Phase_Source_12_Fault(501)
                   sts_Load_Supplying_Fault(502)
                   sts_EPO_Supplying_Fault(503)                   
                   sts_EPO_Activated_Fault(504)                    
                   sts_Thermal_Overload_Fault(505)
                   sts_Phase_S1S2_Rotation_Fault(506)
                   sts_Overload_Fault(507)
                   sts_Internal_Fault(508)
                   sts_General_Alarm_Fault(509)
                   sts_Static_Switch1_Fault(510)
                   sts_KM1_Fault(511)
                   sts_Source1_Out_Of_Tolerance(512)
                   sts_Source1_Frequency_Out_Of_Tolerance_Fault(513)
                   sts_Source1_Voltage_Fault(514)
                   sts_Static_Switch2_Fault(515)
                   sts_KM2_Fault(516)
                   sts_Source2_Out_Of_Tolerance(517)
                   sts_Source2_Frequency_Out_Of_Tolerance_Fault(518)
                   sts_Source2_Voltage_Fault(519)
			     pwups_Control_Off(601)
			     pwups_On_Battery(602)
			     pwups_Low_Battery(603)
			     pwups_Output_Overload(604)
			     pwups_Internal_Failure(605)
			     pwups_Battery_Discharged(606)
			     pwups_Inverter_Failure(607)
			     pwups_On_Bypass(608)
			     pwups_Bypass_Not_Available(609)
			     pwups_Output_Off(610)
			     pwups_Input_Failure(611)
			     pwups_Building_Alarm(612)
			     pwups_Shutdown_Imminent(613)
			     pwups_Breaker_Open(614)
			     pwups_Battery_Bad(615)
			     pwups_Diagnostic_Test_Failed(616)
			     pwups_Shutdown_Pending(617)
			     pwups_Ambient_Temp_Bad(618)
			     pwups_Contact_Active(619)
			     pwups_Temperature_Bad(620)
			     pwups_Charger_Failed(621)
			     pwups_Fan_Failure(622)
			     pwups_Fuse_Failure(623)
			     pwups_Power_Switch_Bad(624)
			     pwups_Module_Failure(625)
			     pwups_Output_Bad(626)
			     pwups_Awaiting_Power(627)
			     pwups_On_Maintenance_Bypass(628)
                   mgeups_Battery_Discharging(701)
                   mgeups_Minimum_Battery_Voltage_Alarm(702)
                   mgeups_Low_Battery_Shutdown_Alarm(703)
                   mgeups_Battery_Temperature_Alarm(704)
                   mgeups_Input_Voltage_Alarm(705)
                   mgeups_Battery_Ventilation_Alarm(706)
                   mgeups_Major_Charger_Alarm(707)
                   mgeups_Emergency_Off_Switch(708)
                   mgeups_Charger_Input_Voltage_Alarm(709)	
                   mgeups_Charger_Input_Frequency_Alarm(710)
                   mgeups_Charger_Gradual_Shutdown_Alarm(711)
                   mgeups_Inverter_Stack_Overload_Alarm(712)
                   mgeups_Major_Inverter_Alarm(713)
                   mgeups_Inverter_Thermal_Overload_Alarm(714)
                   mgeups_Emergency_Off_Switch_Inverter(715)
                   mgeups_Forced_Inverter_Shutdown(716)
                   mgeups_Conditional_Inverter_Shutdown(717)
                   mgeups_Inverter_Overload_Alarm(718)
                   mgeups_Battery_Cabinet_Ventilation_Alarm(719)
                   mgeups_Transfer_Fault_Alarm(720)
                   mgeups_Bypass_Voltage_Alarm(721)
                   mgeups_Emergency_Off_Switch_Bypass(722)
                   mgeups_Maintenance_Bypass_Switch(723)
                   mgeups_Bypass_Frequency_Alarm(724)
                   mgeups_Bypass_Phase_Voltage_Alarm(725)
                   mgeups_Static_Bypass_Overload_Alarm(726)
                   mgeups_Static_Bypass_Thermal_Overload_Alarm(727)
                   mgeups_Inverter_Thermal_Overload_Alarm_2(728)
                   mgeups_Auxiliary_Cubicle_Alarm(729)
                   mgeups_Acquisition_Alarm(730)	
                   mgeups_Battery_Backup_Time_Alarm(731)
                   mgeups_Battery_End_of_Life_Alarm(732)
                   mgeups_ups_Minor_Alarm(733)
                   mgeups_ups_Major_Alarm(734)
                   mgeups_On_Battery(735)
                   mgeups_Cubicle_Ventilation_Alarm(736)
                   mgeups_Communication_Error_Alarm(737)
                   mgeups_Remote_Setting_Alarm(738)
                   mgeups_Invalid_Measurements_Alarm(739)			
                   mgeups_Change_in_Status_Alarm(740)			
                   mgeups_Invalid_Phone_Main_Site_Alarm(741)	
                   mgeups_Invalid_Phone_Secondary_Site_Alarm(742)
              	cm2_over_current_A(1001)
              	cm2_over_current_B(1002)
              	cm2_over_current_C(1003)
              	cm2_over_current_N(1004)
              	cm2_over_current_G(1005)
              	cm2_under_current_A(1006)
              	cm2_under_current_B(1007)
              	cm2_under_current_C(1008)
              	cm2_current_unbalance_A(1009)
              	cm2_current_unbalance_B(1010)
              	cm2_current_unbalance_C(1011)
              	cm2_phase_loss_current(1012)
              	cm2_over_voltage_AN(1013)
              	cm2_over_voltage_BN(1014)
              	cm2_over_voltage_CN(1015)
              	cm2_over_voltage_AB(1016)
              	cm2_over_voltage_BC(1017)
              	cm2_over_voltage_CA(1018)
              	cm2_under_voltage_AN(1019)
              	cm2_under_voltage_BN(1020)
              	cm2_under_voltage_CN(1021)
              	cm2_under_voltage_AB(1022)
              	cm2_under_voltage_BC(1023)
              	cm2_under_voltage_CA(1024)
              	cm2_voltage_unbalance_AN(1025)
              	cm2_voltage_unbalance_BN(1026)
              	cm2_voltage_unbalance_CN(1027)
              	cm2_voltage_unbalance_AB(1028)
              	cm2_voltage_unbalance_BC(1029)
              	cm2_voltage_unbalance_CA(1030)
              	cm2_phase_voltage_loss(1031)
              	cm2_over_kVA_3phase_total(1032)
              	cm2_over_KW_into_load_3phase_total(1033)
              	cm2_over_KW_out_of_load_3phase_total(1034)
              	cm2_over_kVAR_into_load_3phase_total(1035)
              	cm2_over_kVAR_out_of_load_3phase_total(1036)
              	cm2_over_current_demand_A(1037)
              	cm2_over_current_demand_B(1038)
              	cm2_over_current_demand_C(1039)
              	cm2_over_current_demand_total(1040)
              	cm2_over_frequency(1041)
              	cm2_under_frequency(1042)
              	cm2_lagging_true_power_factor(1043)
              	cm2_leading_true_power_factor(1044)
              	cm2_lagging_displacement_power_factor(1045)
              	cm2_leading_displacement_power_factor(1046)
              	cm2_swell_sag_alarm_inhibit(1047)
              	cm2_reserved_1048(1048)
              	cm2_over_value_THD_current_A(1049)
              	cm2_over_value_THD_current_B(1050)
              	cm2_over_value_THD_current_C(1051)
              	cm2_over_value_THD_voltage_AN(1052)
              	cm2_over_value_THD_voltage_BN(1053)
              	cm2_over_value_THD_voltage_CN(1054)
              	cm2_over_value_THD_voltage_AB(1055)
              	cm2_over_value_THD_voltage_BC(1056)
              	cm2_over_value_THD_voltage_CA(1057)
              	cm2_over_k-factor_A(1058)
              	cm2_over_k-factor_B(1059)
              	cm2_over_k-factor_C(1060)
              	cm2_over_predicted_kVA_demand(1061)
              	cm2_over_predicted_KW_demand(1062)
              	cm2_over_predicted_kVAR_demand(1063)
              	cm2_over_kVA_demand_level_1(1064)
              	cm2_over_kVA_demand_level_2(1065)
              	cm2_over_kVA_demand_level_3(1066)
              	cm2_over_kW_demand_level_1(1067)
              	cm2_over_kW_demand_level_2(1068)
              	cm2_over_kW_demand_level_3(1069)
              	cm2_over_kVAR_demand(1070)
              	cm2_over_lagging_3phase_avg_power_factor(1071)
              	cm2_under_3phase_total_real_power(1072)
              	cm2_over_reverse_3phase_power(1073)
              	cm2_phase_reversal(1074)
              	cm2_status_input_1_transition_from_Off_to_On(1075)
              	cm2_status_input_2_transition_from_Off_to_On(1076)
              	cm2_status_input_3_transition_from_Off_to_On(1077)
              	cm2_status_input_4_transition_from_Off_to_On(1078)
              	cm2_status_input_5_transition_from_Off_to_On(1079)
              	cm2_status_input_6_transition_from_Off_to_On(1080)
              	cm2_status_input_7_transition_from_Off_to_On(1081)
              	cm2_status_input_8_transition_from_Off_to_On(1082)
              	cm2_status_input_1_transition_from_On_to_Off(1083)
              	cm2_status_input_2_transition_from_On_to_Off(1084)
              	cm2_status_input_3_transition_from_On_to_Off(1085)
              	cm2_status_input_4_transition_from_On_to_Off(1086)
              	cm2_status_input_5_transition_from_On_to_Off(1087)
              	cm2_status_input_6_transition_from_On_to_Off(1088)
              	cm2_status_input_7_transition_from_On_to_Off(1089)
              	cm2_status_input_8_transition_from_On_to_Off(1090)
              	cm2_reserved_1091(1091)
				cm2_reserved_1092(1092)
				cm2_reserved_1093(1093)
				cm2_reserved_1094(1094)
				cm2_reserved_1095(1095)
				cm2_reserved_1096(1096)
				cm2_reserved_1097(1097)
				cm2_reserved_1098(1098)
				cm2_end_of_incremental_energy_interval(1099)
				cm2_power_up_reset(1100)
              	cm2_end_of_demand_interval(1101)
				cm2_end_of_update_cycle(1102)
				cm2_over_analog_input_1(1103)
				cm2_over_analog_input_2(1104)
				cm2_over_analog_input_3(1105)
				cm2_over_analog_input_4(1106)
				cm2_under_analog_input_1(1107)
				cm2_under_analog_input_2(1108)
				cm2_under_analog_input_3(1109)
				cm2_under_analog_input_4(1110)
              	cm2_reserved_1111(1111)
				cm2_reserved_1112(1112)
				cm2_reserved_1113(1113)
				cm2_reserved_1114(1114)
				cm2_reserved_1115(1115)
				cm2_reserved_1116(1116)
				cm2_reserved_1117(1117)
				cm2_reserved_1118(1118)
				cm2_reserved_1119(1119)
				cm2_reserved_1120(1120)
              	cm2_voltage_swell_AN_AB(1201)
				cm2_voltage_swell_BN(1202)
				cm2_voltage_swell_CN_CB(1203)
				cm2_current_swell_A(1204)
				cm2_current_swell_B(1205)
				cm2_current_swell_C(1206)
				cm2_current_swell_N(1207)
				cm2_voltage_sag_AN_AB(1208)
				cm2_voltage_sag_BN(1209)
				cm2_voltage_sag_CN_BC(1210)
				cm2_current_sag_A(1211)
				cm2_current_sag_B(1212)
				cm2_current_sag_C(1213)
				cm2_current_sag_N(1214)
				cm2_reserved_1215(1215)
				cm2_reserved_1216(1216)
              	cm4_over_current_A(4001)
              	cm4_over_current_B(4002)
              	cm4_over_current_C(4003)
              	cm4_over_current_N(4004)
              	cm4_over_current_G(4005)
              	cm4_under_current_A(4006)
              	cm4_under_current_B(4007)
              	cm4_under_current_C(4008)
              	cm4_current_unbalance_MAX(4009)
				cm4_current_loss(4010)
              	cm4_over_voltage_AN(4011)
              	cm4_over_voltage_BN(4012)
              	cm4_over_voltage_CN(4013)
              	cm4_over_voltage_AB(4014)
              	cm4_over_voltage_BC(4015)
              	cm4_over_voltage_CA(4016)
              	cm4_under_voltage_AN(4017)
              	cm4_under_voltage_BN(4018)
              	cm4_under_voltage_CN(4019)
              	cm4_under_voltage_AB(4020)
              	cm4_under_voltage_BC(4021)
              	cm4_under_voltage_CA(4022)
              	cm4_voltage_unbalance_LN_MAX(4023)
              	cm4_voltage_unbalance_LL_MAX(4024)
              	cm4_phase_voltage_loss(4025)
				cm4_phase_reversal(4026)
              	cm4_over_kVA_demand(4027)
              	cm4_over_KW_demand(4028)
              	cm4_over_KVAR_demand(4029)
              	cm4_over_frequency(4030)
              	cm4_under_frequency(4031)
              	cm4_lagging_true_power_factor(4032)
              	cm4_leading_true_power_factor(4033)
              	cm4_lagging_displacement_power_factor(4034)
              	cm4_leading_displacement_power_factor(4035)
				cm4_over_current_demand_A(4036)
				cm4_over_current_demand_B(4037)
				cm4_over_current_demand_C(4038)
              	cm4_over_THD_voltage_AN(4039)
              	cm4_over_THD_voltage_BN(4040)
              	cm4_over_THD_voltage_CN(4041)
              	cm4_over_THD_voltage_AB(4042)
              	cm4_over_THD_voltage_BC(4043)
              	cm4_over_THD_voltage_CA(4044)
				cm4_standard_speed_custom_alarm_45(4045)
				cm4_standard_speed_custom_alarm_46(4046)
				cm4_standard_speed_custom_alarm_47(4047)
				cm4_standard_speed_custom_alarm_48(4048)
				cm4_standard_speed_custom_alarm_49(4049)
				cm4_standard_speed_custom_alarm_50(4050)
				cm4_standard_speed_custom_alarm_51(4051)
				cm4_standard_speed_custom_alarm_52(4052)
				cm4_standard_speed_custom_alarm_53(4053)
				cm4_standard_speed_custom_alarm_54(4054)
				cm4_standard_speed_custom_alarm_55(4055)
				cm4_standard_speed_custom_alarm_56(4056)
				cm4_standard_speed_custom_alarm_57(4057)
				cm4_standard_speed_custom_alarm_58(4058)
				cm4_standard_speed_custom_alarm_59(4059)
				cm4_standard_speed_custom_alarm_60(4060)
				cm4_standard_speed_custom_alarm_61(4061)
				cm4_standard_speed_custom_alarm_62(4062)
				cm4_standard_speed_custom_alarm_63(4063)
				cm4_standard_speed_custom_alarm_64(4064)
				cm4_hs_over_current_A(4065)
				cm4_hs_over_current_B(4066)
				cm4_hs_over_current_C(4067)
				cm4_hs_over_current_N(4068)
				cm4_hs_over_current_G(4069)
				cm4_hs_over_voltage_AN(4070)
				cm4_hs_over_voltage_BN(4071)
				cm4_hs_over_voltage_CN(4072)
				cm4_hs_over_voltage_AB(4073)
				cm4_hs_over_voltage_BC(4074)
				cm4_hs_over_voltage_CA(4075)
				cm4_hs_over_voltage_NG(4076)
				cm4_hs_under_voltage_AN(4077)
				cm4_hs_under_voltage_BN(4078)
				cm4_hs_under_voltage_CN(4079)
				cm4_hs_under_voltage_AB(4080)
				cm4_hs_under_voltage_BC(4081)
				cm4_hs_under_voltage_CA(4082)
				cm4_high_speed_custom_alarm_19(4083)
				cm4_high_speed_custom_alarm_20(4084)
				cm4_voltage_swell_AN(4085)
				cm4_voltage_swell_BN(4086)
				cm4_voltage_swell_CN(4087)
				cm4_voltage_swell_NG(4088)
				cm4_voltage_swell_AB(4089)
				cm4_voltage_swell_BC(4090)
				cm4_voltage_swell_CA(4091)
				cm4_voltage_sag_AN(4092)
				cm4_voltage_sag_BN(4093)
				cm4_voltage_sag_CN(409)
				cm4_voltage_sag_AB(4095)
				cm4_voltage_sag_BC(4096)
				cm4_voltage_sag_CA(4097)
				cm4_current_swell_A(4098)
				cm4_current_swell_B(4099)
				cm4_current_swell_C(4100)
				cm4_current_swell_N(4101)
				cm4_current_sag_A(4102)
				cm4_current_sag_B(4103)
				cm4_current_sag_C(4104)
				cm4_end_of_incremental_energy_interval(4105)
				cm4_end_of_power_demand_interval(4106)
				cm4_end_of_1_second_update_cycle(4107)
				cm4_end_of_100_ms_update_cycle(4108)
				cm4_power_up_reset(4109)
				cm4_digital_custom_alarm_06(4110)
				cm4_digital_custom_alarm_07(4111)
				cm4_digital_custom_alarm_08(4112)
				cm4_digital_custom_alarm_09(4113)
				cm4_digital_custom_alarm_10(4114)
				cm4_digital_custom_alarm_11(4115)
				cm4_digital_custom_alarm_12(4116)
				cm4_digital_custom_alarm_13(4117)
				cm4_digital_custom_alarm_14(4118)
				cm4_digital_custom_alarm_15(4119)
				cm4_digital_custom_alarm_16(4120)

              }	  
              ACCESS read-only
              STATUS optional
              DESCRIPTION
                      "A reference to an alarm."
                      
              ::= { nrdcmAlarmEntry 6 }

         nrdcmAlarmTime OBJECT-TYPE
              SYNTAX DisplayString (SIZE (255))
              ACCESS read-only
              STATUS mandatory
              DESCRIPTION
                      "Time/Date when the alarm occurred."
              ::= { nrdcmAlarmEntry 7 }

--
--  The POWERLOGIC Meter traps
--
          nrdcmtraps        OBJECT IDENTIFIER ::= { nrdPowerlogic 4 }

nrdcmDeviceOnline TRAP-TYPE
			ENTERPRISE	niobrara
			VARIABLES  	{ ntrapargsString }
			DESCRIPTION
			"The QUCM has established communication with the meter."

			::= 1
	
nrdcmDeviceOffline TRAP-TYPE
			ENTERPRISE	niobrara
			VARIABLES  	{ ntrapargsString }
			DESCRIPTION
			"The QUCM has lost communication with the meter."

			::= 2


nrdcmAlarmCondition TRAP-TYPE
   			ENTERPRISE niobrara
   			VARIABLES { ntrapargsInteger, ntrapargsString }
   			DESCRIPTION
      			"INFORMATION: An alarm condition has been detected.
       			The first variable is the fault condition."
   			::= 3

nrdcmAlarmConditionCleared TRAP-TYPE
   			ENTERPRISE niobrara
   			VARIABLES { ntrapargsInteger, ntrapargsString }
   			DESCRIPTION
      			"INFORMATION: An alarm condition has been cleared.
      			The first variable is the fault condition."
   			::= 4




--
-- Branch Circuit Monitor
--

          nrdbcmData     OBJECT IDENTIFIER ::= { nrdPowerlogic 5 }
          
          nrdbcmNumMeters OBJECT-TYPE
              SYNTAX INTEGER (1..60)
              ACCESS read-only
              STATUS mandatory
              DESCRIPTION
                      "The number of Veris Branch Circuit Monitors configured 
                      in this device. This entry indicates the number of rows in
                      the Data table."
              ::= { nrdbcmData 1 }

          nrdbcmDataTable OBJECT-TYPE
              SYNTAX SEQUENCE OF NrdbcmDataEntry
              ACCESS not-accessible
              STATUS mandatory
              ::= { nrdbcmData 2 }

          nrdbcmDataEntry OBJECT-TYPE
              SYNTAX NrdbcmDataEntry
              ACCESS not-accessible
              STATUS mandatory
              INDEX { nrdbcmMeter }
              ::= { nrdbcmDataTable 1 }

          NrdbcmDataEntry ::= SEQUENCE {
              nrdbcmMeter                       INTEGER,
              nrdbcmModel                       DisplayString,
              nrdbcmLabel                       DisplayString, 
              nrdbcmNameplate					DisplayString,
              nrdbcmMeterName					DisplayString,
              nrdbcmNetworkName					DisplayString,
              nrdbcmNetworkIP                   IpAddress,
              nrdbcmMeterSlaveAddress           INTEGER,
              nrdbcmBuildingName				DisplayString,
			  nrdbcmBreaker1A01Current          INTEGER,
			  nrdbcmBreaker1B02Current          INTEGER,
			  nrdbcmBreaker1A03Current          INTEGER,
			  nrdbcmBreaker1B04Current          INTEGER,
			  nrdbcmBreaker1A05Current          INTEGER,
			  nrdbcmBreaker1B06Current          INTEGER,
			  nrdbcmBreaker1A07Current          INTEGER,
			  nrdbcmBreaker1B08Current          INTEGER,
			  nrdbcmBreaker1A09Current          INTEGER,
			  nrdbcmBreaker1B10Current          INTEGER,
			  nrdbcmBreaker1A11Current          INTEGER,
			  nrdbcmBreaker1B12Current          INTEGER,
			  nrdbcmBreaker1A13Current          INTEGER,
			  nrdbcmBreaker1B14Current          INTEGER,
			  nrdbcmBreaker1A15Current          INTEGER,
			  nrdbcmBreaker1B16Current          INTEGER,
			  nrdbcmBreaker1A17Current          INTEGER,
			  nrdbcmBreaker1B18Current          INTEGER,
			  nrdbcmBreaker1A19Current          INTEGER,
			  nrdbcmBreaker1B20Current          INTEGER,
			  nrdbcmBreaker1A21Current          INTEGER,
			  nrdbcmBreaker1B22Current          INTEGER,
			  nrdbcmBreaker1A23Current          INTEGER,
			  nrdbcmBreaker1B24Current          INTEGER,
			  nrdbcmBreaker1A25Current          INTEGER,
			  nrdbcmBreaker1B26Current          INTEGER,
			  nrdbcmBreaker1A27Current          INTEGER,
			  nrdbcmBreaker1B28Current          INTEGER,
			  nrdbcmBreaker1A29Current          INTEGER,
			  nrdbcmBreaker1B30Current          INTEGER,
			  nrdbcmBreaker1A31Current          INTEGER,
			  nrdbcmBreaker1B32Current          INTEGER,
			  nrdbcmBreaker1A33Current          INTEGER,
			  nrdbcmBreaker1B34Current          INTEGER,
			  nrdbcmBreaker1A35Current          INTEGER,
			  nrdbcmBreaker1B36Current          INTEGER,
			  nrdbcmBreaker1A37Current          INTEGER,
			  nrdbcmBreaker1B38Current          INTEGER,
			  nrdbcmBreaker1A39Current          INTEGER,
			  nrdbcmBreaker1B40Current          INTEGER,
			  nrdbcmBreaker1A41Current          INTEGER,
			  nrdbcmBreaker1B42Current          INTEGER
          }

          nrdbcmMeter OBJECT-TYPE
              SYNTAX INTEGER (1..60)
              ACCESS read-only
              STATUS mandatory
              DESCRIPTION
                      "The meter number."
              ::= { nrdbcmDataEntry 1 }
          
          nrdbcmModel OBJECT-TYPE
              SYNTAX DisplayString (SIZE (255))
              ACCESS read-write
              STATUS mandatory
              DESCRIPTION
                      "The CM Model designation."
              ::= { nrdbcmDataEntry 2 }

          nrdbcmLabel OBJECT-TYPE
              SYNTAX DisplayString (SIZE (255))
              ACCESS read-only
              STATUS mandatory
              DESCRIPTION
                      "The CM Label."
              ::= { nrdbcmDataEntry 3 }

          nrdbcmNameplate OBJECT-TYPE
              SYNTAX DisplayString (SIZE (255))
              ACCESS read-only
              STATUS mandatory
              DESCRIPTION
                      "The CM Nameplate."
              ::= { nrdbcmDataEntry 4 }

         nrdbcmMeterName OBJECT-TYPE
              SYNTAX DisplayString (SIZE (255))
              ACCESS read-only
              STATUS mandatory
              DESCRIPTION
                      "The CM's Meter Name."
              ::= { nrdbcmDataEntry 5 }

         nrdbcmNetworkName OBJECT-TYPE
              SYNTAX DisplayString (SIZE (255))
              ACCESS read-only
              STATUS mandatory
              DESCRIPTION
                      "The CM's Network Device Name."
              ::= { nrdbcmDataEntry 6 }
         
         nrdbcmNetworkIP	OBJECT-TYPE
              SYNTAX	IpAddress
              ACCESS	read-only
	          STATUS	mandatory
	          DESCRIPTION
		            "The IP address of the meter's server"
		      ::= { nrdbcmDataEntry 7 }

         nrdbcmMeterSlaveAddress OBJECT-TYPE
              SYNTAX INTEGER (1..255)
              ACCESS read-only
              STATUS mandatory
              DESCRIPTION
                      "The meter's drop number."
              ::= { nrdbcmDataEntry 8 }
          
         nrdbcmBuildingName OBJECT-TYPE
              SYNTAX DisplayString (SIZE (255))
              ACCESS read-only
              STATUS mandatory
              DESCRIPTION
                      "The CM's Building Name."
              ::= { nrdbcmDataEntry 9 }

          nrdbcmBreaker1A01Current OBJECT-TYPE
              SYNTAX INTEGER (0..65535)
              ACCESS read-only
              STATUS mandatory
              DESCRIPTION
                      "The Current for Breaker 1A01.
                      (Unit of measure: .001 Amp)"
              ::= { nrdbcmDataEntry 10 }

          nrdbcmBreaker1B02Current OBJECT-TYPE
              SYNTAX INTEGER (0..65535)
              ACCESS read-only
              STATUS mandatory
              DESCRIPTION
                      "The Current for Breaker 1B02.
                      (Unit of measure: .001 Amp)"
              ::= { nrdbcmDataEntry 11 }

          nrdbcmBreaker1A03Current OBJECT-TYPE
              SYNTAX INTEGER (0..65535)
              ACCESS read-only
              STATUS mandatory
              DESCRIPTION
                      "The Current for Breaker 1A03.
                      (Unit of measure: .001 Amp)"
              ::= { nrdbcmDataEntry 12 }

          nrdbcmBreaker1B04Current OBJECT-TYPE
              SYNTAX INTEGER (0..65535)
              ACCESS read-only
              STATUS mandatory
              DESCRIPTION
                      "The Current for Breaker 1B04.
                      (Unit of measure: .001 Amp)"
              ::= { nrdbcmDataEntry 13 }

          nrdbcmBreaker1A05Current OBJECT-TYPE
              SYNTAX INTEGER (0..65535)
              ACCESS read-only
              STATUS mandatory
              DESCRIPTION
                      "The Current for Breaker 1A05.
                      (Unit of measure: .001 Amp)"
              ::= { nrdbcmDataEntry 14 }

          nrdbcmBreaker1B06Current OBJECT-TYPE
              SYNTAX INTEGER (0..65535)
              ACCESS read-only
              STATUS mandatory
              DESCRIPTION
                      "The Current for Breaker 1B06.
                      (Unit of measure: .001 Amp)"
              ::= { nrdbcmDataEntry 15 }

          nrdbcmBreaker1A07Current OBJECT-TYPE
              SYNTAX INTEGER (0..65535)
              ACCESS read-only
              STATUS mandatory
              DESCRIPTION
                      "The Current for Breaker 1A07.
                      (Unit of measure: .001 Amp)"
              ::= { nrdbcmDataEntry 16 }

          nrdbcmBreaker1B08Current OBJECT-TYPE
              SYNTAX INTEGER (0..65535)
              ACCESS read-only
              STATUS mandatory
              DESCRIPTION
                      "The Current for Breaker 1B08.
                      (Unit of measure: .001 Amp)"
              ::= { nrdbcmDataEntry 17 }

          nrdbcmBreaker1A09Current OBJECT-TYPE
              SYNTAX INTEGER (0..65535)
              ACCESS read-only
              STATUS mandatory
              DESCRIPTION
                      "The Current for Breaker 1A09.
                      (Unit of measure: .001 Amp)"
              ::= { nrdbcmDataEntry 18 }

          nrdbcmBreaker1B10Current OBJECT-TYPE
              SYNTAX INTEGER (0..65535)
              ACCESS read-only
              STATUS mandatory
              DESCRIPTION
                      "The Current for Breaker 1B10.
                      (Unit of measure: .001 Amp)"
              ::= { nrdbcmDataEntry 19 }

          nrdbcmBreaker1A11Current OBJECT-TYPE
              SYNTAX INTEGER (0..65535)
              ACCESS read-only
              STATUS mandatory
              DESCRIPTION
                      "The Current for Breaker 1A11.
                      (Unit of measure: .001 Amp)"
              ::= { nrdbcmDataEntry 20 }

          nrdbcmBreaker1B12Current OBJECT-TYPE
              SYNTAX INTEGER (0..65535)
              ACCESS read-only
              STATUS mandatory
              DESCRIPTION
                      "The Current for Breaker 1B12.
                      (Unit of measure: .001 Amp)"
              ::= { nrdbcmDataEntry 21 }

          nrdbcmBreaker1A13Current OBJECT-TYPE
              SYNTAX INTEGER (0..65535)
              ACCESS read-only
              STATUS mandatory
              DESCRIPTION
                      "The Current for Breaker 1A13.
                      (Unit of measure: .001 Amp)"
              ::= { nrdbcmDataEntry 22 }

          nrdbcmBreaker1B14Current OBJECT-TYPE
              SYNTAX INTEGER (0..65535)
              ACCESS read-only
              STATUS mandatory
              DESCRIPTION
                      "The Current for Breaker 1B14.
                      (Unit of measure: .001 Amp)"
              ::= { nrdbcmDataEntry 23 }

          nrdbcmBreaker1A15Current OBJECT-TYPE
              SYNTAX INTEGER (0..65535)
              ACCESS read-only
              STATUS mandatory
              DESCRIPTION
                      "The Current for Breaker 1A15.
                      (Unit of measure: .001 Amp)"
              ::= { nrdbcmDataEntry 24 }

          nrdbcmBreaker1B16Current OBJECT-TYPE
              SYNTAX INTEGER (0..65535)
              ACCESS read-only
              STATUS mandatory
              DESCRIPTION
                      "The Current for Breaker 1B16.
                      (Unit of measure: .001 Amp)"
              ::= { nrdbcmDataEntry 25 }

          nrdbcmBreaker1A17Current OBJECT-TYPE
              SYNTAX INTEGER (0..65535)
              ACCESS read-only
              STATUS mandatory
              DESCRIPTION
                      "The Current for Breaker 1A17.
                      (Unit of measure: .001 Amp)"
              ::= { nrdbcmDataEntry 26 }

          nrdbcmBreaker1B18Current OBJECT-TYPE
              SYNTAX INTEGER (0..65535)
              ACCESS read-only
              STATUS mandatory
              DESCRIPTION
                      "The Current for Breaker 1B18.
                      (Unit of measure: .001 Amp)"
              ::= { nrdbcmDataEntry 27 }

          nrdbcmBreaker1A19Current OBJECT-TYPE
              SYNTAX INTEGER (0..65535)
              ACCESS read-only
              STATUS mandatory
              DESCRIPTION
                      "The Current for Breaker 1A19.
                      (Unit of measure: .001 Amp)"
              ::= { nrdbcmDataEntry 28 }

          nrdbcmBreaker1B20Current OBJECT-TYPE
              SYNTAX INTEGER (0..65535)
              ACCESS read-only
              STATUS mandatory
              DESCRIPTION
                      "The Current for Breaker 1B20.
                      (Unit of measure: .001 Amp)"
              ::= { nrdbcmDataEntry 29 }

          nrdbcmBreaker1A21Current OBJECT-TYPE
              SYNTAX INTEGER (0..65535)
              ACCESS read-only
              STATUS mandatory
              DESCRIPTION
                      "The Current for Breaker 1A21.
                      (Unit of measure: .001 Amp)"
              ::= { nrdbcmDataEntry 30 }

          nrdbcmBreaker1B22Current OBJECT-TYPE
              SYNTAX INTEGER (0..65535)
              ACCESS read-only
              STATUS mandatory
              DESCRIPTION
                      "The Current for Breaker 1B22.
                      (Unit of measure: .001 Amp)"
              ::= { nrdbcmDataEntry 31 }

          nrdbcmBreaker1A23Current OBJECT-TYPE
              SYNTAX INTEGER (0..65535)
              ACCESS read-only
              STATUS mandatory
              DESCRIPTION
                      "The Current for Breaker 1A23.
                      (Unit of measure: .001 Amp)"
              ::= { nrdbcmDataEntry 32 }

          nrdbcmBreaker1B24Current OBJECT-TYPE
              SYNTAX INTEGER (0..65535)
              ACCESS read-only
              STATUS mandatory
              DESCRIPTION
                      "The Current for Breaker 1B24.
                      (Unit of measure: .001 Amp)"
              ::= { nrdbcmDataEntry 33 }

          nrdbcmBreaker1A25Current OBJECT-TYPE
              SYNTAX INTEGER (0..65535)
              ACCESS read-only
              STATUS mandatory
              DESCRIPTION
                      "The Current for Breaker 1A25.
                      (Unit of measure: .001 Amp)"
              ::= { nrdbcmDataEntry 34 }

          nrdbcmBreaker1B26Current OBJECT-TYPE
              SYNTAX INTEGER (0..65535)
              ACCESS read-only
              STATUS mandatory
              DESCRIPTION
                      "The Current for Breaker 1B26.
                      (Unit of measure: .001 Amp)"
              ::= { nrdbcmDataEntry 35 }

          nrdbcmBreaker1A27Current OBJECT-TYPE
              SYNTAX INTEGER (0..65535)
              ACCESS read-only
              STATUS mandatory
              DESCRIPTION
                      "The Current for Breaker 1A27.
                      (Unit of measure: .001 Amp)"
              ::= { nrdbcmDataEntry 36 }

          nrdbcmBreaker1B28Current OBJECT-TYPE
              SYNTAX INTEGER (0..65535)
              ACCESS read-only
              STATUS mandatory
              DESCRIPTION
                      "The Current for Breaker 1B28.
                      (Unit of measure: .001 Amp)"
              ::= { nrdbcmDataEntry 37 }

          nrdbcmBreaker1A29Current OBJECT-TYPE
              SYNTAX INTEGER (0..65535)
              ACCESS read-only
              STATUS mandatory
              DESCRIPTION
                      "The Current for Breaker 1A29.
                      (Unit of measure: .001 Amp)"
              ::= { nrdbcmDataEntry 38 }

          nrdbcmBreaker1B30Current OBJECT-TYPE
              SYNTAX INTEGER (0..65535)
              ACCESS read-only
              STATUS mandatory
              DESCRIPTION
                      "The Current for Breaker 1B30.
                      (Unit of measure: .001 Amp)"
              ::= { nrdbcmDataEntry 39 }

          nrdbcmBreaker1A31Current OBJECT-TYPE
              SYNTAX INTEGER (0..65535)
              ACCESS read-only
              STATUS mandatory
              DESCRIPTION
                      "The Current for Breaker 1A31.
                      (Unit of measure: .001 Amp)"
              ::= { nrdbcmDataEntry 40 }

          nrdbcmBreaker1B32Current OBJECT-TYPE
              SYNTAX INTEGER (0..65535)
              ACCESS read-only
              STATUS mandatory
              DESCRIPTION
                      "The Current for Breaker 1B32.
                      (Unit of measure: .001 Amp)"
              ::= { nrdbcmDataEntry 41 }

          nrdbcmBreaker1A33Current OBJECT-TYPE
              SYNTAX INTEGER (0..65535)
              ACCESS read-only
              STATUS mandatory
              DESCRIPTION
                      "The Current for Breaker 1A33.
                      (Unit of measure: .001 Amp)"
              ::= { nrdbcmDataEntry 42 }
	
          nrdbcmBreaker1B34Current OBJECT-TYPE
              SYNTAX INTEGER (0..65535)
              ACCESS read-only
              STATUS mandatory
              DESCRIPTION
                      "The Current for Breaker 1B34.
                      (Unit of measure: .001 Amp)"
              ::= { nrdbcmDataEntry 43 }
	
          nrdbcmBreaker1A35Current OBJECT-TYPE
              SYNTAX INTEGER (0..65535)
              ACCESS read-only
              STATUS mandatory
              DESCRIPTION
                      "The Current for Breaker 1A35.
                      (Unit of measure: .001 Amp)"
              ::= { nrdbcmDataEntry 44 }
	
          nrdbcmBreaker1B36Current OBJECT-TYPE
              SYNTAX INTEGER (0..65535)
              ACCESS read-only
              STATUS mandatory
              DESCRIPTION
                      "The Current for Breaker 1B36.
                      (Unit of measure: .001 Amp)"
              ::= { nrdbcmDataEntry 45 }
	
          nrdbcmBreaker1A37Current OBJECT-TYPE
              SYNTAX INTEGER (0..65535)
              ACCESS read-only
              STATUS mandatory
              DESCRIPTION
                      "The Current for Breaker 1A37.
                      (Unit of measure: .001 Amp)"
              ::= { nrdbcmDataEntry 46 }
	
          nrdbcmBreaker1B38Current OBJECT-TYPE
              SYNTAX INTEGER (0..65535)
              ACCESS read-only
              STATUS mandatory
              DESCRIPTION
                      "The Current for Breaker 1B38.
                      (Unit of measure: .001 Amp)"
              ::= { nrdbcmDataEntry 47 }
	
          nrdbcmBreaker1A39Current OBJECT-TYPE
              SYNTAX INTEGER (0..65535)
              ACCESS read-only
              STATUS mandatory
              DESCRIPTION
                      "The Current for Breaker 1A39.
                      (Unit of measure: .001 Amp)"
              ::= { nrdbcmDataEntry 48 }
	
          nrdbcmBreaker1B40Current OBJECT-TYPE
              SYNTAX INTEGER (0..65535)
              ACCESS read-only
              STATUS mandatory
              DESCRIPTION
                      "The Current for Breaker 1B40.
                      (Unit of measure: .001 Amp)"
              ::= { nrdbcmDataEntry 49 }
	
          nrdbcmBreaker1A41Current OBJECT-TYPE
              SYNTAX INTEGER (0..65535)
              ACCESS read-only
              STATUS mandatory
              DESCRIPTION
                      "The Current for Breaker 1A41.
                      (Unit of measure: .001 Amp)"
              ::= { nrdbcmDataEntry 50 }
	
          nrdbcmBreaker1B42Current OBJECT-TYPE
              SYNTAX INTEGER (0..65535)
              ACCESS read-only
              STATUS mandatory
              DESCRIPTION
                      "The Current for Breaker 1B42.
                      (Unit of measure: .001 Amp)"
              ::= { nrdbcmDataEntry 51 }
	
--
-- MGE Upsilon STS
--

          nrdstsData     OBJECT IDENTIFIER ::= { nrdPowerlogic 6 }
          
          nrdstsNumMeters OBJECT-TYPE
              SYNTAX INTEGER (1..60)
              ACCESS read-only
              STATUS mandatory
              DESCRIPTION
                      "The number of MGE Upsilon STS units configured 
                      in this device. This entry indicates the number of rows in
                      the Data table."
              ::= { nrdstsData 1 }

          nrdstsDataTable OBJECT-TYPE
              SYNTAX SEQUENCE OF NrdstsDataEntry
              ACCESS not-accessible
              STATUS mandatory
              ::= { nrdstsData 2 }

          nrdstsDataEntry OBJECT-TYPE
              SYNTAX NrdstsDataEntry
              ACCESS not-accessible
              STATUS mandatory
              INDEX { nrdstsMeter }
              ::= { nrdstsDataTable 1 }

          NrdstsDataEntry ::= SEQUENCE {
              nrdstsMeter                                INTEGER,
              nrdstsModel                                DisplayString,
              nrdstsLabel                                DisplayString, 
              nrdstsNameplate					         DisplayString,
              nrdstsMeterName					         DisplayString,
              nrdstsNetworkName					         DisplayString,
              nrdstsNetworkIP                            IpAddress,
              nrdstsMeterSlaveAddress                    INTEGER,
              nrdstsBuildingName				         DisplayString,

			  nrdstsOutputSwitch                         INTEGER,
			  nrdstsLoadSupplied                         INTEGER,
			  nrdstsTransferValid                        INTEGER,
			  nrdstsProhibitedTransfer                   INTEGER,
			  nrdstsPhaseSource12Fault                   INTEGER,
			  nrdstsLoadSupplyingFault                   INTEGER,
			  nrdstsEPOSupplyingFault                    INTEGER,
			  nrdstsEPOActivatedFault                    INTEGER,
			  nrdstsThermalOverloadFault                 INTEGER,
			  nrdstsPhaseS1S2RotationFault               INTEGER,
			  nrdstsOverloadFault                        INTEGER,
			  nrdstsInternalFault                        INTEGER,
			  nrdstsGeneralAlarmFault                    INTEGER,

			  nrdstsPhaseSource1Source2                  INTEGER,
			  nrdstsTotalRealPower                       INTEGER,
			  nrdstsTotalApparentPower                   INTEGER,
			  nrdstsTotalReactivePower                   INTEGER,
			  nrdstsPercentLoadLevel                     INTEGER,
			  nrdstsPowerFactor                          INTEGER,
			  nrdstsPeakFactor                           INTEGER,
			  nrdstsNominalVoltage                       INTEGER,
			  nrdstsNominalFrequency                     INTEGER,
			  nrdstsNominalCurrent                       INTEGER,

			  nrdstsStaticSwitch1Fault                   INTEGER,
			  nrdstsKM1Fault                             INTEGER,
			  nrdstsSource1InputSwitch                   INTEGER,
			  nrdstsSource1BypassSwitch                  INTEGER,
			  nrdstsSource1Active                        INTEGER,
			  nrdstsSource1Preferred                     INTEGER,
			  nrdstsSource1OutOfTolerance                INTEGER,
			  nrdstsSource1FrequencyOutOfToleranceFault  INTEGER,
			  nrdstsSource1Frequency                     INTEGER,
			  nrdstsSource1PhasesInversion               INTEGER,
			  nrdstsSource1VoltageFault                  INTEGER,
			  nrdstsSource1VoltageAB                     INTEGER,
			  nrdstsSource1VoltageBC                     INTEGER,
			  nrdstsSource1VoltageCA                     INTEGER,
			  nrdstsSource1VoltageAN                     INTEGER,
			  nrdstsSource1VoltageBN                     INTEGER,
			  nrdstsSource1VoltageCN                     INTEGER,
			  nrdstsSource1CurrentA                      INTEGER,
			  nrdstsSource1CurrentB                      INTEGER,
			  nrdstsSource1CurrentC                      INTEGER,
			  nrdstsSource1CurrentN                      INTEGER,
			  nrdstsSource1RealPowerA                    INTEGER,
			  nrdstsSource1RealPowerB                    INTEGER,
			  nrdstsSource1RealPowerC                    INTEGER,
			  nrdstsSource1ApparentPowerA                INTEGER,
			  nrdstsSource1ApparentPowerB                INTEGER,
			  nrdstsSource1ApparentPowerC                INTEGER,
		
			  nrdstsStaticSwitch2Fault                   INTEGER,
			  nrdstsKM2Fault                             INTEGER,
			  nrdstsSource2InputSwitch                   INTEGER,
			  nrdstsSource2BypassSwitch                  INTEGER,
			  nrdstsSource2Active                        INTEGER,
			  nrdstsSource2Preferred                     INTEGER,
			  nrdstsSource2OutOfTolerance                INTEGER,
			  nrdstsSource2FrequencyOutOfToleranceFault  INTEGER,
			  nrdstsSource2VoltageFault                  INTEGER,
			  nrdstsSource2Frequency                     INTEGER,
			  nrdstsSource2PhasesInversion               INTEGER,
			  nrdstsSource2VoltageFault                  INTEGER,
			  nrdstsSource2VoltageAB                     INTEGER,
			  nrdstsSource2VoltageBC                     INTEGER,
			  nrdstsSource2VoltageCA                     INTEGER,
			  nrdstsSource2VoltageAN                     INTEGER,
			  nrdstsSource2VoltageBN                     INTEGER,
			  nrdstsSource2VoltageCN                     INTEGER,
			  nrdstsSource2CurrentA                      INTEGER,
			  nrdstsSource2CurrentB                      INTEGER,
			  nrdstsSource2CurrentC                      INTEGER,
			  nrdstsSource2CurrentN                      INTEGER,
			  nrdstsSource2RealPowerA                    INTEGER,
			  nrdstsSource2RealPowerB                    INTEGER,
			  nrdstsSource2RealPowerC                    INTEGER,
			  nrdstsSource2ApparentPowerA                INTEGER,
			  nrdstsSource2ApparentPowerB                INTEGER,
			  nrdstsSource2ApparentPowerC                INTEGER
          
          }


          nrdstsMeter OBJECT-TYPE
              SYNTAX INTEGER (1..60)
              ACCESS read-only
              STATUS mandatory
              DESCRIPTION
                      "The meter number."
              ::= { nrdstsDataEntry 1 }
          
          nrdstsModel OBJECT-TYPE
              SYNTAX DisplayString (SIZE (255))
              ACCESS read-write
              STATUS mandatory
              DESCRIPTION
                      "The CM Model designation."
              ::= { nrdstsDataEntry 2 }

          nrdstsLabel OBJECT-TYPE
              SYNTAX DisplayString (SIZE (255))
              ACCESS read-only
              STATUS mandatory
              DESCRIPTION
                      "The CM Label."
              ::= { nrdstsDataEntry 3 }

          nrdstsNameplate OBJECT-TYPE
              SYNTAX DisplayString (SIZE (255))
              ACCESS read-only
              STATUS mandatory
              DESCRIPTION
                      "The CM Nameplate."
              ::= { nrdstsDataEntry 4 }

         nrdstsMeterName OBJECT-TYPE
              SYNTAX DisplayString (SIZE (255))
              ACCESS read-only
              STATUS mandatory
              DESCRIPTION
                      "The CM's Meter Name."
              ::= { nrdstsDataEntry 5 }

         nrdstsNetworkName OBJECT-TYPE
              SYNTAX DisplayString (SIZE (255))
              ACCESS read-only
              STATUS mandatory
              DESCRIPTION			  
                      "The CM's Network Device Name."
              ::= { nrdstsDataEntry 6 }
         
         nrdstsNetworkIP	OBJECT-TYPE
              SYNTAX	IpAddress
              ACCESS	read-only
	          STATUS	mandatory
	          DESCRIPTION
		            "The IP address of the meter's server"
		      ::= { nrdstsDataEntry 7 }

         nrdstsMeterSlaveAddress OBJECT-TYPE
              SYNTAX INTEGER (1..255)
              ACCESS read-only
              STATUS mandatory
              DESCRIPTION
                      "The meter's drop number."
              ::= { nrdstsDataEntry 8 }
          
         nrdstsBuildingName OBJECT-TYPE
              SYNTAX DisplayString (SIZE (255))
              ACCESS read-only
              STATUS mandatory
              DESCRIPTION
                      "The CM's Building Name."
              ::= { nrdstsDataEntry 9 }

          nrdstsOutputSwitch OBJECT-TYPE
              SYNTAX INTEGER {
				open(0)
				closed(1)
			  }
              ACCESS read-only
              STATUS mandatory
              DESCRIPTION
                      "The Status of the Q3 Output Switch"
              ::= { nrdstsDataEntry 10 }
              
          nrdstsLoadSupplied OBJECT-TYPE
              SYNTAX INTEGER {
				no(0)
				yes(1)
			  }
              ACCESS read-only
              STATUS mandatory
              DESCRIPTION
                      "The Status of the Load Supplied"
              ::= { nrdstsDataEntry 11 }
              
          nrdstsTransferValid OBJECT-TYPE
              SYNTAX INTEGER {
				no(0)
				yes(1)
			  }
              ACCESS read-only
              STATUS mandatory
              DESCRIPTION
                      "The Status of the Validy of the Transfer"
              ::= { nrdstsDataEntry 12 }
              
          nrdstsProhibitedTransfer OBJECT-TYPE
              SYNTAX INTEGER {
				no(0)
				yes(1)
			  }
              ACCESS read-only
              STATUS mandatory
              DESCRIPTION
                      "The State of Transfer Prohibited"
              ::= { nrdstsDataEntry 13 }
              
          nrdstsPhaseSource12Fault OBJECT-TYPE
              SYNTAX INTEGER {
				no(0)
				yes(1)
			  }
              ACCESS read-only
              STATUS mandatory
              DESCRIPTION
                      "The State of the detection of a phase
                      fault between Source 1 and Source 2."
              ::= { nrdstsDataEntry 14 }
              
          nrdstsLoadSupplyingFault OBJECT-TYPE
              SYNTAX INTEGER {
				no(0)
				yes(1)
			  }
              ACCESS read-only
              STATUS mandatory
              DESCRIPTION
                      "The State of the Load Supplying Fault"
              ::= { nrdstsDataEntry 15 }
              
          nrdstsEPOSupplyingFault OBJECT-TYPE
              SYNTAX INTEGER {
				no(0)
				yes(1)
			  }
              ACCESS read-only
              STATUS mandatory
              DESCRIPTION
                      "The State of the EPO Supplying Fault"
              ::= { nrdstsDataEntry 16 }
              
          nrdstsEPOActivatedFault OBJECT-TYPE
              SYNTAX INTEGER {
				no(0)
				yes(1)
			  }
              ACCESS read-only
              STATUS mandatory
              DESCRIPTION
                      "The State of the EPO Activiated Fault"
              ::= { nrdstsDataEntry 17 }
              
          nrdstsThermalOverloadFault OBJECT-TYPE
              SYNTAX INTEGER {
				no(0)
				yes(1)
			  }
              ACCESS read-only
              STATUS mandatory
              DESCRIPTION
                      "The State of the Thermal Overload Fault"
              ::= { nrdstsDataEntry 18 }
              
          nrdstsPhaseS1S2RotationFault OBJECT-TYPE
              SYNTAX INTEGER {
				no(0)
				yes(1)
			  }
              ACCESS read-only
              STATUS mandatory
              DESCRIPTION
                      "The State of the Phase S1/S2 Rotation Fault"
              ::= { nrdstsDataEntry 19 }
              
          nrdstsOverloadFault OBJECT-TYPE
              SYNTAX INTEGER {
				no(0)
				yes(1)
			  }
              ACCESS read-only
              STATUS mandatory
              DESCRIPTION
                      "The State of the Overload Fault"
              ::= { nrdstsDataEntry 20 }
              
          nrdstsInternalFault OBJECT-TYPE
              SYNTAX INTEGER {
				no(0)
				yes(1)
			  }
              ACCESS read-only
              STATUS mandatory
              DESCRIPTION
                      "The State of the Internal Fault"
              ::= { nrdstsDataEntry 21 }
              
          nrdstsGeneralAlarmFault OBJECT-TYPE
              SYNTAX INTEGER {
				no(0)
				yes(1)
			  }
              ACCESS read-only
              STATUS mandatory
              DESCRIPTION
                      "The State of the General Alarm Fault"
              ::= { nrdstsDataEntry 22 }

          nrdstsPhaseSource1Source2 OBJECT-TYPE
              SYNTAX INTEGER (0..32767)
              ACCESS read-only
              STATUS mandatory
              DESCRIPTION
                      "The angle of separation between phases
					  of Source 1 and Source 2.
                      (Unit of measure: Degrees)"
              ::= { nrdstsDataEntry 23 }
              
          nrdstsTotalRealPower OBJECT-TYPE
              SYNTAX INTEGER (0..32767)
              ACCESS read-only
              STATUS mandatory
              DESCRIPTION
                      "The Metered Total Real Power.
                      (Unit of measure: kW)"
              ::= { nrdstsDataEntry 24 }
              
          nrdstsTotalApparentPower OBJECT-TYPE
              SYNTAX INTEGER (0..32767)
              ACCESS read-only
              STATUS mandatory
              DESCRIPTION
                      "The Metered Total Apparent Power.
                      (Unit of measure: kVA)"
              ::= { nrdstsDataEntry 25 }
              
          nrdstsTotalReactivePower OBJECT-TYPE
              SYNTAX INTEGER (-32767..32767)
              ACCESS read-only
              STATUS mandatory
              DESCRIPTION
                      "The Metered Total Reactive Power.
                      (Unit of measure: kVAR)"
              ::= { nrdstsDataEntry 26 }
              
          nrdstsPercentLoadLevel OBJECT-TYPE
              SYNTAX INTEGER (0..100)
              ACCESS read-only
              STATUS mandatory
              DESCRIPTION
                      "The % of maximum load level.
                      (Unit of measure: %)"
              ::= { nrdstsDataEntry 27 }
              
          nrdstsPowerFactor OBJECT-TYPE
              SYNTAX INTEGER (0..100)
              ACCESS read-only
              STATUS mandatory
              DESCRIPTION
                      "The Total Metered Power Factor.
                      (Unit of measure: .01%)"
              ::= { nrdstsDataEntry 28 }
              
          nrdstsPeakFactor OBJECT-TYPE
              SYNTAX INTEGER (0..400)
              ACCESS read-only
              STATUS mandatory
              DESCRIPTION
                      "The Peak Factor.
                      (Unit of measure: .01%)"
              ::= { nrdstsDataEntry 29 }
              
          nrdstsNominalVoltage OBJECT-TYPE
              SYNTAX INTEGER (0..32767)
              ACCESS read-only
              STATUS mandatory
              DESCRIPTION
                      "The Nominal Voltage of the STS.
                      (Unit of measure: Volts)"
              ::= { nrdstsDataEntry 30 }
              
          nrdstsNominalFrequency OBJECT-TYPE
              SYNTAX INTEGER (0..32767)
              ACCESS read-only
              STATUS mandatory
              DESCRIPTION
                      "The Nominal Frequency of the STS.
                      (Unit of measure: Hz)"
              ::= { nrdstsDataEntry 31 }
              
          nrdstsNominalCurrent OBJECT-TYPE
              SYNTAX INTEGER (0..32767)
              ACCESS read-only
              STATUS mandatory
              DESCRIPTION
                      "The Nominal Current of the STS.
                      (Unit of measure: Amps"
              ::= { nrdstsDataEntry 32 }
              




          nrdstsStaticSwitch1Fault OBJECT-TYPE
              SYNTAX INTEGER {
				no(0)
				yes(1)
			  }
              ACCESS read-only
              STATUS mandatory
              DESCRIPTION
                      "The State of the Static Switch 1 Fault."
              ::= { nrdstsDataEntry 33 }

          nrdstsKM1Fault OBJECT-TYPE
              SYNTAX INTEGER {
				no(0)
				yes(1)
			  }
              ACCESS read-only
              STATUS mandatory
              DESCRIPTION
                      "The State of the KM1 Fault."
              ::= { nrdstsDataEntry 34 }

          nrdstsSource1InputSwitch OBJECT-TYPE
              SYNTAX INTEGER {
				open(0)
				closed(1)
			  }
              ACCESS read-only
              STATUS mandatory
              DESCRIPTION
                      "The Status of the Source 1 Input Switch."
              ::= { nrdstsDataEntry 35 }
              
          nrdstsSource1BypassSwitch OBJECT-TYPE
              SYNTAX INTEGER {
				open(0)
				closed(1)
			  }
              ACCESS read-only
              STATUS mandatory
              DESCRIPTION
                      "The Status of the Source 1 Bypass Switch."
              ::= { nrdstsDataEntry 36 }
              
          nrdstsSource1Active OBJECT-TYPE
              SYNTAX INTEGER {
				no(0)
				yes(1)
			  }
              ACCESS read-only
              STATUS mandatory
              DESCRIPTION
                      "The State of Source 1 Active."
              ::= { nrdstsDataEntry 37 }

          nrdstsSource1Preferred OBJECT-TYPE
              SYNTAX INTEGER {
				no(0)
				yes(1)
			  }
              ACCESS read-only
              STATUS mandatory
              DESCRIPTION
                      "The State of Source 1 Preferred."
              ::= { nrdstsDataEntry 38 }

          nrdstsSource1OutOfTolerance OBJECT-TYPE
              SYNTAX INTEGER {
				no(0)
				yes(1)
			  }
              ACCESS read-only
              STATUS mandatory
              DESCRIPTION
                      "The State of Source 1 Out of Tolerance."
              ::= { nrdstsDataEntry 39 }

          nrdstsSource1FrequencyOutOfToleranceFault OBJECT-TYPE
              SYNTAX INTEGER {
				no(0)
				yes(1)
			  }
              ACCESS read-only
              STATUS mandatory
              DESCRIPTION
                      "The State of Source 1 Frequency Out of Tolerance."
              ::= { nrdstsDataEntry 40 }

          nrdstsSource1Frequency OBJECT-TYPE
              SYNTAX INTEGER (0..32767)
              ACCESS read-only
              STATUS mandatory
              DESCRIPTION
                      "The Phase A line frequency.
                      (Unit of measure: Hz)"
              ::= { nrdstsDataEntry 41 }
              
          nrdstsSource1PhasesInversion OBJECT-TYPE
              SYNTAX INTEGER {
				no(0)
				yes(1)
			  }
              ACCESS read-only
              STATUS mandatory
              DESCRIPTION
                      "The State of Source 1 Phases Inversion."
              ::= { nrdstsDataEntry 42 }

          nrdstsSource1VoltageFault OBJECT-TYPE
              SYNTAX INTEGER {
				no(0)
				yes(1)
			  }
              ACCESS read-only
              STATUS mandatory
              DESCRIPTION
                      "The State of Source 1 Voltage Fault"
              ::= { nrdstsDataEntry 43 }
              
          nrdstsSource1VoltageAB OBJECT-TYPE
              SYNTAX INTEGER (0..32767)
              ACCESS read-only
              STATUS mandatory
              DESCRIPTION
                      "The Voltage between Phase A and Phase B of Source 1.
                      (Unit of measure: Volt)"
              ::= { nrdstsDataEntry 44 }

          nrdstsSource1VoltageBC OBJECT-TYPE
              SYNTAX INTEGER (0..32767)
              ACCESS read-only
              STATUS mandatory
              DESCRIPTION
                      "The Voltage between Phase B and Phase C of Source 1.
                      (Unit of measure: Volt)"
              ::= { nrdstsDataEntry 45 }

          nrdstsSource1VoltageCA OBJECT-TYPE
              SYNTAX INTEGER (0..32767)
              ACCESS read-only
              STATUS mandatory
              DESCRIPTION
                      "The Voltage between Phase C and Phase A of Source 1.
                      (Unit of measure: Volt)"
              ::= { nrdstsDataEntry 46 }

          nrdstsSource1VoltageAN OBJECT-TYPE
              SYNTAX INTEGER (0..32767)
              ACCESS read-only
              STATUS mandatory
              DESCRIPTION
                      "The Voltage between Phase A and Neutral of Source 1.
                      (Unit of measure: Volt)"
              ::= { nrdstsDataEntry 47 }

          nrdstsSource1VoltageBN OBJECT-TYPE
              SYNTAX INTEGER (0..32767)
              ACCESS read-only
              STATUS mandatory
              DESCRIPTION
                      "The Voltage between Phase B and Neutral of Source 1.
                      (Unit of measure: Volt)"
              ::= { nrdstsDataEntry 48 }

          nrdstsSource1VoltageCN OBJECT-TYPE
              SYNTAX INTEGER (0..32767)
              ACCESS read-only
              STATUS mandatory
              DESCRIPTION
                      "The Voltage between Phase C and Neutral of Source 1.
                      (Unit of measure: Volt)"
              ::= { nrdstsDataEntry 49 }

          nrdstsSource1CurrentA OBJECT-TYPE
              SYNTAX INTEGER (0..32767)
              ACCESS read-only
              STATUS mandatory
              DESCRIPTION
                      "The Current, Phase A of Source 1.
                      (Unit of measure: Amp)"
              ::= { nrdstsDataEntry 50 }

          nrdstsSource1CurrentB OBJECT-TYPE
              SYNTAX INTEGER (0..32767)
              ACCESS read-only
              STATUS mandatory
              DESCRIPTION
                      "The Current, Phase B of Source 1.
                      (Unit of measure: Amp)"
              ::= { nrdstsDataEntry 51 }

          nrdstsSource1CurrentC OBJECT-TYPE
              SYNTAX INTEGER (0..32767)
              ACCESS read-only
              STATUS mandatory
              DESCRIPTION
                      "The Current, Phase C of Source 1.
                      (Unit of measure: Amp)"
              ::= { nrdstsDataEntry 52 }

          nrdstsSource1CurrentN OBJECT-TYPE
              SYNTAX INTEGER (0..32767)
              ACCESS read-only
              STATUS mandatory
              DESCRIPTION
                      "The Current, Phase Neutral of Source 1.
                      (Unit of measure: Amp)"
              ::= { nrdstsDataEntry 53 }

          nrdstsSource1RealPowerA OBJECT-TYPE
              SYNTAX INTEGER (0..32767)
              ACCESS read-only
              STATUS mandatory
              DESCRIPTION
                      "The Real Power, Phase A of Source 1.
                      (Unit of measure: kW)"
              ::= { nrdstsDataEntry 54 }

          nrdstsSource1RealPowerB OBJECT-TYPE
              SYNTAX INTEGER (0..32767)
              ACCESS read-only
              STATUS mandatory
              DESCRIPTION
                      "The Real Power, Phase B of Source 1.
                      (Unit of measure: kW)"
              ::= { nrdstsDataEntry 55 }

          nrdstsSource1RealPowerC OBJECT-TYPE
              SYNTAX INTEGER (0..32767)
              ACCESS read-only
              STATUS mandatory
              DESCRIPTION
                      "The Real Power, Phase C of Source 1.
                      (Unit of measure: kW)"
              ::= { nrdstsDataEntry 56 }

          nrdstsSource1ApparentPowerA OBJECT-TYPE
              SYNTAX INTEGER (0..32767)
              ACCESS read-only
              STATUS mandatory
              DESCRIPTION
                      "The Apparent Power, Phase A of Source 1.
                      (Unit of measure: kVA)"
              ::= { nrdstsDataEntry 57 }

          nrdstsSource1ApparentPowerB OBJECT-TYPE
              SYNTAX INTEGER (0..32767)
              ACCESS read-only
              STATUS mandatory
              DESCRIPTION
                      "The Apparent Power, Phase B of Source 1.
                      (Unit of measure: kVA)"
              ::= { nrdstsDataEntry 58 }

          nrdstsSource1ApparentPowerC OBJECT-TYPE
              SYNTAX INTEGER (0..32767)
              ACCESS read-only
              STATUS mandatory
              DESCRIPTION
                      "The Apparent Power, Phase C of Source 1.
                      (Unit of measure: kVA)"
              ::= { nrdstsDataEntry 59 }

          nrdstsStaticSwitch2Fault OBJECT-TYPE
              SYNTAX INTEGER {
				no(0)
				yes(1)
			  }
              ACCESS read-only
              STATUS mandatory
              DESCRIPTION
                      "The State of the Static Switch 2 Fault."
              ::= { nrdstsDataEntry 60 }

          nrdstsKM2Fault OBJECT-TYPE
              SYNTAX INTEGER {
				no(0)
				yes(1)
			  }
              ACCESS read-only
              STATUS mandatory
              DESCRIPTION
                      "The State of the KM2 Fault."
              ::= { nrdstsDataEntry 61 }

          nrdstsSource2InputSwitch OBJECT-TYPE
              SYNTAX INTEGER {
				open(0)
				closed(1)
			  }
              ACCESS read-only
              STATUS mandatory
              DESCRIPTION
                      "The Status of the Source 2 Input Switch."
              ::= { nrdstsDataEntry 62 }
              
          nrdstsSource2BypassSwitch OBJECT-TYPE
              SYNTAX INTEGER {
				open(0)
				closed(1)
			  }
              ACCESS read-only
              STATUS mandatory
              DESCRIPTION
                      "The Status of the Source 2 Bypass Switch."
              ::= { nrdstsDataEntry 63 }
              
          nrdstsSource2Active OBJECT-TYPE
              SYNTAX INTEGER {
				no(0)
				yes(1)
			  }
              ACCESS read-only
              STATUS mandatory
              DESCRIPTION
                      "The State of Source 2 Active."
              ::= { nrdstsDataEntry 64 }

          nrdstsSource2Preferred OBJECT-TYPE
              SYNTAX INTEGER {
				no(0)
				yes(1)
			  }
              ACCESS read-only
              STATUS mandatory
              DESCRIPTION
                      "The State of Source 2 Preferred."
              ::= { nrdstsDataEntry 65 }

          nrdstsSource2OutOfTolerance OBJECT-TYPE
              SYNTAX INTEGER {
				no(0)
				yes(1)
			  }
              ACCESS read-only
              STATUS mandatory
              DESCRIPTION
                      "The State of Source 2 Out of Tolerance."
              ::= { nrdstsDataEntry 66 }

          nrdstsSource2FrequencyOutOfToleranceFault OBJECT-TYPE
              SYNTAX INTEGER {
				no(0)
				yes(1)
			  }
              ACCESS read-only
              STATUS mandatory
              DESCRIPTION
                      "The State of Source 2 Frequency Out of Tolerance."
              ::= { nrdstsDataEntry 67 }

          nrdstsSource2Frequency OBJECT-TYPE
              SYNTAX INTEGER (0..32767)
              ACCESS read-only
              STATUS mandatory
              DESCRIPTION
                      "The Phase A line frequency.
                      (Unit of measure: Hz)"
              ::= { nrdstsDataEntry 68 }
              
          nrdstsSource2PhasesInversion OBJECT-TYPE
              SYNTAX INTEGER {
				no(0)
				yes(1)
			  }
              ACCESS read-only
              STATUS mandatory
              DESCRIPTION
                      "The State of Source 2 Phases Inversion."
              ::= { nrdstsDataEntry 69 }

          nrdstsSource2VoltageFault OBJECT-TYPE
              SYNTAX INTEGER {
				no(0)
				yes(1)
			  }
              ACCESS read-only
              STATUS mandatory
              DESCRIPTION
                      "The State of Source 2 Voltage Fault"
              ::= { nrdstsDataEntry 70 }
              
          nrdstsSource2VoltageAB OBJECT-TYPE
              SYNTAX INTEGER (0..32767)
              ACCESS read-only
              STATUS mandatory
              DESCRIPTION
                      "The Voltage between Phase A and Phase B of Source 2.
                      (Unit of measure: Volt)"
              ::= { nrdstsDataEntry 71 }

          nrdstsSource2VoltageBC OBJECT-TYPE
              SYNTAX INTEGER (0..32767)
              ACCESS read-only
              STATUS mandatory
              DESCRIPTION
                      "The Voltage between Phase B and Phase C of Source 2.
                      (Unit of measure: Volt)"
              ::= { nrdstsDataEntry 72 }

          nrdstsSource2VoltageCA OBJECT-TYPE
              SYNTAX INTEGER (0..32767)
              ACCESS read-only
              STATUS mandatory
              DESCRIPTION
                      "The Voltage between Phase C and Phase A of Source 2.
                      (Unit of measure: Volt)"
              ::= { nrdstsDataEntry 73 }

          nrdstsSource2VoltageAN OBJECT-TYPE
              SYNTAX INTEGER (0..32767)
              ACCESS read-only
              STATUS mandatory
              DESCRIPTION
                      "The Voltage between Phase A and Neutral of Source 2.
                      (Unit of measure: Volt)"
              ::= { nrdstsDataEntry 74 }

          nrdstsSource2VoltageBN OBJECT-TYPE
              SYNTAX INTEGER (0..32767)
              ACCESS read-only
              STATUS mandatory
              DESCRIPTION
                      "The Voltage between Phase B and Neutral of Source 2.
                      (Unit of measure: Volt)"
              ::= { nrdstsDataEntry 75 }

          nrdstsSource2VoltageCN OBJECT-TYPE
              SYNTAX INTEGER (0..32767)
              ACCESS read-only
              STATUS mandatory
              DESCRIPTION
                      "The Voltage between Phase C and Neutral of Source 2.
                      (Unit of measure: Volt)"
              ::= { nrdstsDataEntry 76 }

          nrdstsSource2CurrentA OBJECT-TYPE
              SYNTAX INTEGER (0..32767)
              ACCESS read-only
              STATUS mandatory
              DESCRIPTION
                      "The Current, Phase A of Source 2.
                      (Unit of measure: Amp)"
              ::= { nrdstsDataEntry 77 }

          nrdstsSource2CurrentB OBJECT-TYPE
              SYNTAX INTEGER (0..32767)
              ACCESS read-only
              STATUS mandatory
              DESCRIPTION
                      "The Current, Phase B of Source 2.
                      (Unit of measure: Amp)"
              ::= { nrdstsDataEntry 78 }

          nrdstsSource2CurrentC OBJECT-TYPE
              SYNTAX INTEGER (0..32767)
              ACCESS read-only
              STATUS mandatory
              DESCRIPTION
                      "The Current, Phase C of Source 2.
                      (Unit of measure: Amp)"
              ::= { nrdstsDataEntry 79 }

          nrdstsSource2CurrentN OBJECT-TYPE
              SYNTAX INTEGER (0..32767)
              ACCESS read-only
              STATUS mandatory
              DESCRIPTION
                      "The Current, Phase Neutral of Source 2.
                      (Unit of measure: Amp)"
              ::= { nrdstsDataEntry 80 }

          nrdstsSource2RealPowerA OBJECT-TYPE
              SYNTAX INTEGER (0..32767)
              ACCESS read-only
              STATUS mandatory
              DESCRIPTION
                      "The Real Power, Phase A of Source 2.
                      (Unit of measure: kW)"
              ::= { nrdstsDataEntry 81 }

          nrdstsSource2RealPowerB OBJECT-TYPE
              SYNTAX INTEGER (0..32767)
              ACCESS read-only
              STATUS mandatory
              DESCRIPTION
                      "The Real Power, Phase B of Source 2.
                      (Unit of measure: kW)"
              ::= { nrdstsDataEntry 82 }

          nrdstsSource2RealPowerC OBJECT-TYPE
              SYNTAX INTEGER (0..32767)
              ACCESS read-only
              STATUS mandatory
              DESCRIPTION
                      "The Real Power, Phase C of Source 2.
                      (Unit of measure: kW)"
              ::= { nrdstsDataEntry 83 }

          nrdstsSource2ApparentPowerA OBJECT-TYPE
              SYNTAX INTEGER (0..32767)
              ACCESS read-only
              STATUS mandatory
              DESCRIPTION
                      "The Apparent Power, Phase A of Source 2.
                      (Unit of measure: kVA)"
              ::= { nrdstsDataEntry 84 }

          nrdstsSource2ApparentPowerB OBJECT-TYPE
              SYNTAX INTEGER (0..32767)
              ACCESS read-only
              STATUS mandatory
              DESCRIPTION
                      "The Apparent Power, Phase B of Source 2.
                      (Unit of measure: kVA)"
              ::= { nrdstsDataEntry 85 }

          nrdstsSource2ApparentPowerC OBJECT-TYPE
              SYNTAX INTEGER (0..32767)
              ACCESS read-only
              STATUS mandatory
              DESCRIPTION
                      "The Apparent Power, Phase C of Source 2.
                      (Unit of measure: kVA)"
              ::= { nrdstsDataEntry 86 }




--
-- PowerWare UPS
--

          nrdpwupsData     OBJECT IDENTIFIER ::= { nrdPowerlogic 7 }
          
          nrdpwupsNumMeters OBJECT-TYPE
              SYNTAX INTEGER (1..60)
              ACCESS read-only
              STATUS mandatory
              DESCRIPTION
                      "The number of PowerWare UPSs configured 
                      in this device. This entry indicates the number of rows in
                      the Data table."
              ::= { nrdpwupsData 1 }

          nrdpwupsDataTable OBJECT-TYPE
              SYNTAX SEQUENCE OF NrdpwupsDataEntry
              ACCESS not-accessible
              STATUS mandatory
              ::= { nrdpwupsData 2 }

          nrdpwupsDataEntry OBJECT-TYPE
              SYNTAX NrdpwupsDataEntry
              ACCESS not-accessible
              STATUS mandatory
              INDEX { nrdpwupsMeter }
              ::= { nrdpwupsDataTable 1 }

          NrdpwupsDataEntry ::= SEQUENCE {
               nrdpwupsMeter                              INTEGER,
               nrdpwupsModel                              DisplayString,
               nrdpwupsLabel                              DisplayString, 
               nrdpwupsNameplate				        DisplayString,
               nrdpwupsMeterName				        DisplayString,
               nrdpwupsNetworkName				        DisplayString,
               nrdpwupsNetworkIP                          IpAddress,
               nrdpwupsMeterSlaveAddress                  INTEGER,
               nrdpwupsBuildingName			        DisplayString,
		      nrdpwupsOutputVoltsAB                      INTEGER,
		      nrdpwupsOutputVoltsBC                      INTEGER,
		      nrdpwupsOutputVoltsCA                      INTEGER,
		      nrdpwupsInputVoltsAB                       INTEGER,
		      nrdpwupsInputVoltsBC                       INTEGER,
		      nrdpwupsInputVoltsCA                       INTEGER,
		      nrdpwupsInverterVoltsAB                    INTEGER,
		      nrdpwupsInverterVoltsBC                    INTEGER,
		      nrdpwupsInverterVoltsCA                    INTEGER,
		      nrdpwupsBypassVoltsAB                      INTEGER,
		      nrdpwupsBypassVoltsBC                      INTEGER,
		      nrdpwupsBypassVoltsCA                      INTEGER,
		      nrdpwupsMainLogicPower                     INTEGER,
		      nrdpwupsSecondaryVpPower                   INTEGER,
		      nrdpwupsSecondaryVnPower                   INTEGER,
		      nrdpwupsInverterCurrentA                   INTEGER,
		      nrdpwupsInverterCurrentB                   INTEGER,
		      nrdpwupsInverterCurrentC                   INTEGER,
		      nrdpwupsInputCurrentA                      INTEGER,
		      nrdpwupsInputCurrentB                      INTEGER,
		      nrdpwupsInputCurrentC                      INTEGER,
		      nrdpwupsOutputKw                           INTEGER,
		      nrdpwupsInputKw                            INTEGER,
		      nrdpwupsOutputKva                          INTEGER,
		      nrdpwupsInputKva                           INTEGER,
		      nrdpwupsOutputPowerFactor                  INTEGER,
		      nrdpwupsInputPowerFactor                   INTEGER,
		      nrdpwupsOutputFrequency                    INTEGER,
		      nrdpwupsInputFrequency                     INTEGER,
		      nrdpwupsInverterFrequency                  INTEGER,
		      nrdpwupsBypassFrequency                    INTEGER,
		      nrdpwupsDcLinkVolts                        INTEGER,
		      nrdpwupsBatteryCurrent                     INTEGER,
		      nrdpwupsBatteryVoltage                     INTEGER,
		      nrdpwupsPercentBatteryLeft                 INTEGER,
		      nrdpwupsBatteryTimeRemaining               INTEGER,
		      nrdpwupsBatteryChargeTime                  INTEGER,
		      nrdpwupsPeakInverterCurrentA               INTEGER,
		      nrdpwupsPeakInverterCurrentB               INTEGER,
		      nrdpwupsPeakInverterCurrentC               INTEGER,
		      nrdpwupsAvgInputCurrent3PhaseSum           INTEGER,
		      nrdpwupsInputCurrentBarChart               INTEGER,
		      nrdpwupsDcVoltsBarChart                    INTEGER,
		      nrdpwupsBatteryCurrentBarChart             INTEGER,
		      nrdpwupsBypassVoltsAN                      INTEGER,
		      nrdpwupsBypassVoltsBN                      INTEGER,
		      nrdpwupsBypassVoltsCN                      INTEGER,
		      nrdpwupsInputVoltsAN                       INTEGER,
		      nrdpwupsInputVoltsBN                       INTEGER,
		      nrdpwupsInputVoltsCN                       INTEGER,
		      nrdpwupsInverterVoltsAN                    INTEGER,
		      nrdpwupsInverterVoltsBN                    INTEGER,
		      nrdpwupsInverterVoltsCN                    INTEGER,
		      nrdpwupsAmbientTemperature                 INTEGER,
		      nrdpwupsHeatsinkTemperature                INTEGER,
		      nrdpwupsPowerSupplyTemperature             INTEGER,
		      nrdpwupsLoadCurrentA                       INTEGER,
		      nrdpwupsLoadCurrentB                       INTEGER,
		      nrdpwupsLoadCurrentC                       INTEGER,
		      nrdpwupsLoadCurrentBarChartA               INTEGER,
		      nrdpwupsLoadCurrentBarChartB               INTEGER,
		      nrdpwupsLoadCurrentBarChartC               INTEGER,
		      nrdpwupsOutputVABarChart                   INTEGER,
		      nrdpwupsPositiveDcRailVolts                INTEGER,
		      nrdpwupsNegativeDcRailVolts                INTEGER,
		      nrdpwupsAutoBalanceVolts                   INTEGER,
		      nrdpwupsBatteryTemperature                 INTEGER,
		      nrdpwupsOutputVoltsAN                      INTEGER,
		      nrdpwupsOutputVoltsBN                      INTEGER,
		      nrdpwupsOutputVoltsCN                      INTEGER,
		      nrdpwupsNeutralCurrent                     INTEGER,
		      nrdpwupsOutputKwA                          INTEGER,
		      nrdpwupsOutputKwB                          INTEGER,
		      nrdpwupsOutputKwC                          INTEGER,
		      nrdpwupsOutputKwABC                        INTEGER,
		      nrdpwupsRectifierDcCurrent                 INTEGER,
		      nrdpwupsPositiveBatteryVolts               INTEGER,
		      nrdpwupsNegativeBatteryVolts               INTEGER,
		      nrdpwupsPositiveBatteryCurrent             INTEGER,
		      nrdpwupsNegativeBatteryCurrent             INTEGER,
               nrdpwupsOnBattery                          INTEGER,
		      nrdpwupsOnBypass                           INTEGER,
		      nrdpwupsSystemNormal                       INTEGER,
		      nrdpwupsUpsOff                             INTEGER,
		      nrdpwupsStaticPositionSwitch               INTEGER,
		      nrdpwupsCriticalBussBreaker                INTEGER,
		      nrdpwupsByassBreaker                       INTEGER,
		      nrdpwupsBackfeedBreaker                    INTEGER,
		      nrdpwupsBypassInputPower                   INTEGER,
		      nrdpwupsMIB                                INTEGER,
		      nrdpwupsMBB                                INTEGER,
		      nrdpwupsMBP                                INTEGER,
		      nrdpwupsSbmNormal                          INTEGER,
		      nrdpwupsSbmOnBattery                       INTEGER,
		      nrdpwupsSbmOnBypass                        INTEGER,
		      nrdpwupsSbmNotice                          INTEGER,
		      nrdpwupsSbmAlarm                           INTEGER,
		      nrdpwupsSbmOnStandby                       INTEGER,
		      nrdpwupsUpmNormalLed1                      INTEGER,
		      nrdpwupsUpmBatteryLed1                     INTEGER,
		      nrdpwupsUpmBypassLed1                      INTEGER,
		      nrdpwupsupmNoticeLed1                      INTEGER,
		      nrdpwupsUpmAlarmLed1                       INTEGER,
		      nrdpwupsUpmStandbyLed1                     INTEGER,
		      nrdpwupsUpmPresent1                        INTEGER,
		      nrdpwupsUpmNormalLed2                      INTEGER,
		      nrdpwupsUpmBatteryLed2                     INTEGER,
		      nrdpwupsUpmBypassLed2                      INTEGER,
		      nrdpwupsupmNoticeLed2                      INTEGER,
		      nrdpwupsUpmAlarmLed2                       INTEGER,
		      nrdpwupsUpmStandbyLed2                     INTEGER,
		      nrdpwupsUpmPresent2                        INTEGER,
		      nrdpwupsUpmNormalLed3                      INTEGER,
		      nrdpwupsUpmBatteryLed3                     INTEGER,
		      nrdpwupsUpmBypassLed3                      INTEGER,
		      nrdpwupsupmNoticeLed3                      INTEGER,
		      nrdpwupsUpmAlarmLed3                       INTEGER,
		      nrdpwupsUpmStandbyLed3                     INTEGER,
		      nrdpwupsUpmPresent3                        INTEGER,
		      nrdpwupsUpmNormalLed4                      INTEGER,
		      nrdpwupsUpmBatteryLed4                     INTEGER,
		      nrdpwupsUpmBypassLed4                      INTEGER,
		      nrdpwupsupmNoticeLed4                      INTEGER,
		      nrdpwupsUpmAlarmLed4                       INTEGER,
		      nrdpwupsUpmStandbyLed4                     INTEGER,
		      nrdpwupsUpmPresent4                        INTEGER,
		      nrdpwupsUpmNormalLed5                      INTEGER,
		      nrdpwupsUpmBatteryLed5                     INTEGER,
		      nrdpwupsUpmBypassLed55                     INTEGER,
		      nrdpwupsupmNoticeLed5                      INTEGER,
		      nrdpwupsUpmAlarmLed5                       INTEGER,
		      nrdpwupsUpmStandbyLed5                     INTEGER,
		      nrdpwupsUpmPresent5                        INTEGER,
		      nrdpwupsUpmNormalLed6                      INTEGER,
		      nrdpwupsUpmBatteryLed6                     INTEGER,
		      nrdpwupsUpmBypassLed6                      INTEGER,
		      nrdpwupsupmNoticeLed6                      INTEGER,
		      nrdpwupsUpmAlarmLed6                       INTEGER,
		      nrdpwupsUpmStandbyLed6                     INTEGER,
		      nrdpwupsUpmPresent6                        INTEGER,
		      nrdpwupsUpmNormalLed7                      INTEGER,
		      nrdpwupsUpmBatteryLed7                     INTEGER,
		      nrdpwupsUpmBypassLed7                      INTEGER,
		      nrdpwupsupmNoticeLed7                      INTEGER,
		      nrdpwupsUpmAlarmLed7                       INTEGER,
		      nrdpwupsUpmStandbyLed7                     INTEGER,
		      nrdpwupsUpmPresent7                        INTEGER,
		      nrdpwupsUpmNormalLed8                      INTEGER,
		      nrdpwupsUpmBatteryLed8                     INTEGER,
		      nrdpwupsUpmBypassLed8                      INTEGER,
		      nrdpwupsupmNoticeLed8                      INTEGER,
		      nrdpwupsUpmAlarmLed8                       INTEGER,
		      nrdpwupsUpmStandbyLed8                     INTEGER,
		      nrdpwupsUpmPresent8                        INTEGER,
		      nrdpwupsRectifierStatus                    INTEGER,
		      nrdpwupsRectifierInputStatus               INTEGER,
		      nrdpwupsBypassStatus                       INTEGER,
		      nrdpwupsBypassInputStatus                  INTEGER,
		      nrdpwupsInputCircuitBreakerStatus          INTEGER,
		      nrdpwupsBatteryDisconnectSTatus            INTEGER,
		      nrdpwupsInverterDisconnectStatus           INTEGER,
		      nrdpwupsInverterStatus                     INTEGER,
		      nrdpwupsUpmNormal                          INTEGER,
		      nrdpwupsUpnOnBattery                       INTEGER,
		      nrdpwupsUpnBypass                          INTEGER,
		      nrdpwupsUpnNotice                          INTEGER,
		      nrdpwupsUpnAlarm                           INTEGER,
		      nrdpwupsUpnStandby                         INTEGER,
		      nrdpwupsMobClosed                          INTEGER,
		      nrdpwupsSystemRedundant                    INTEGER,
		      nrdpwupsInveterAcOverVoltage               INTEGER,
		      nrdpwupsInveterAcUnderVoltage              INTEGER,
		      nrdpwupsInverterOverUnderFrequency         INTEGER,
		      nrdpwupsBypassAcOverVoltage                INTEGER,
		      nrdpwupsBypassAcUnderVoltage               INTEGER,
		      nrdpwupsBypassOverUnderFrequency           INTEGER,
		      nrdpwupsInputAcOverVoltage                 INTEGER,
		      nrdpwupsInputAcUnderVoltage                INTEGER,
		      nrdpwupsInputAcOverUnderFrequency          INTEGER,
		      nrdpwupsOutputAcOverVoltage                INTEGER,
		      nrdpwupsOutputAcUnderVoltage               INTEGER,
		      nrdpwupsOutputAcOverUnderFrequency         INTEGER,
		      nrdpwupsRemoteEmergencyPowerOff            INTEGER,
		      nrdpwupsRemoteGoToBypass                   INTEGER,
		      nrdpwupsBuildingAlarm6                     INTEGER,
		      nrdpwupsBuildingAlarm5                     INTEGER,
		      nrdpwupsBuildingAlarm4                     INTEGER,
		      nrdpwupsBuildingAlarm3                     INTEGER,
		      nrdpwupsBuildingAlarm2                     INTEGER,
		      nrdpwupsBuildingAlarm1                     INTEGER,
		      nrdpwupsStaticSwitchOverTemerature         INTEGER,
		      nrdpwupsChargerOverTemperature             INTEGER,
		      nrdpwupsChargerLogicPowerFail              INTEGER,
		      nrdpwupsChargerOverVoltageCurrent          INTEGER,
		      nrdpwupsInverterOverTemperature            INTEGER,
		      nrdpwupsOutputOverload                     INTEGER,
		      nrdpwupsRectifierInputOverCurrent          INTEGER,
		      nrdpwupsInverterOutputOverCurrent          INTEGER,
		      nrdpwupsDcLinkOverVoltage                  INTEGER,
		      nrdpwupsDcLinkUnderVoltage                 INTEGER,
		      nrdpwupsRectifierFailed                    INTEGER,
		      nrdpwupsInverterFault                      INTEGER,
		      nrdpwupsBatteryContactorFail               INTEGER,
		      nrdpwupsBypassBreakerFail                  INTEGER,
		      nrdpwupsChargerFailure                     INTEGER,
		      nrdpwupsStaticSwitchFailure                INTEGER,
		      nrdpwupsBatteryCurrentLimit                INTEGER,
		      nrdpwupsOutputCurrentover100Percent        INTEGER,
		      nrdpwupsBatteryGroundFault                 INTEGER,
		      nrdpwupsShutdownImminent                   INTEGER,
		      nrdpwupsBatteryLow                         INTEGER,
		      nrdpwupsUtilityFail                        INTEGER,
		      nrdpwupsOutputShortCircuit                 INTEGER,
		      nrdpwupsUtilityNotPresent                  INTEGER,
		      nrdpwupsFullTimeCharging                   INTEGER,
		      nrdpwupsInputLIneVoltageLoss               INTEGER,
               nrdpwupsBatteryDcOverVoltage               INTEGER,
               nrdpwupsPowerSupplyFailure                 INTEGER,
               nrdpwupsRectifierCurrentOver125Percent     INTEGER,
               nrdpwupsNetwrokNotResponding               INTEGER,
               nrdpwupsOutputDcOverVoltage                INTEGER,
               nrdpwupsEmergencyShutdownCommand           INTEGER,
               nrdpwupsBypassNotAvailable                 INTEGER,
               nrdpwupsRectifierBreakerOpen               INTEGER,
               nrdpwupsBatteryContactorOpen               INTEGER,
		      nrdpwupsInverterContactOpen                INTEGER,
		      nrdpwupsBypassBreakerOpen                  INTEGER,
		      nrdpwupsBatteryTotallyDischarged           INTEGER,
		      nrdpwupsLossOfRedundancy                   INTEGER,
		      nrdpwupsLossOfSyncBus                      INTEGER,
		      nrdpwupsRectifierBreakerShuntTripped       INTEGER,
		      nrdpwupsLossOfChargerSync                  INTEGER,
		      nrdpwupsOutputBreakerOpen                  INTEGER,
		      nrdpwupsControlPowerOn                     INTEGER,
		      nrdpwupsInverterOn                         INTEGER,
		      nrdpwupsChargerOn                          INTEGER,
		      nrdpwupsBypassOn                           INTEGER,
		      nrdpwupsBypassPowerLoss                    INTEGER,
		      nrdpwupsCheckBatteryFlag                   INTEGER,
		      nrdpwupsBatteryCharging                    INTEGER,
		      nrdpwupsBatteryNotCharged                  INTEGER,
		      nrdpwupsOtherUpsOn                         INTEGER,
		      nrdpwupsParallelInverter                   INTEGER,
		      nrdpwupsUpsInParallel                      INTEGER,
		      nrdpwupsOutputBreakerRelayFailure          INTEGER,
		      nrdpwupsControlPowerOff                    INTEGER,
		      nrdpwups106PercentOverloadA                INTEGER,
		      nrdpwups106PercentOverloadB                INTEGER,
		      nrdpwups106PercentOverloadC                INTEGER,
		      nrdpwups125PercentOverloadA                INTEGER,
		      nrdpwups125PercentOverloadB                INTEGER,
		      nrdpwups125PercentOverloadC                INTEGER,
		      nrdpwups150PercentOverloadA                INTEGER,
		      nrdpwups150PercentOverloadB                INTEGER,
		      nrdpwups150PercentOverloadC                INTEGER,
		      nrdpwupsUpsOnBattery                       INTEGER,
		      nrdpwupsUpsOnBypass                        INTEGER,
		      nrdpwupsLoadDumped                         INTEGER,
		      nrdpwupsLoadOnInverter                     INTEGER,
		      nrdpwupsLowBatteryShutdown                 INTEGER,
		      nrdpwupsInParallelOperation                INTEGER,
		      nrdpwupsSyncingToBypass                    INTEGER,
		      nrdpwupsBypassFailure                      INTEGER,
		      nrdpwupsBatteryTestFailed                  INTEGER,
		      nrdpwupsFuseFailure                        INTEGER,
		      nrdpwupsFanFailure                         INTEGER,
		      nrdpwupsSiteWiringFault                    INTEGER,
		      nrdpwupsBackfeedContactorFailure           INTEGER,
		      nrdpwupsBatteriesDisconnected              INTEGER,
		      nrdpwupsUpsCabinetOverTemperature          INTEGER,
		      nrdpwupsTransformerOverTemperature         INTEGER,
		      nrdpwupsAmbientUnderTemperature            INTEGER,
		      nrdpwupsAmbientOverTemperature             INTEGER,
		      nrdpwupsUnableToChargeBatteries            INTEGER,
		      nrdpwupsInputBreakerFailed                 INTEGER

          }

          nrdpwupsMeter OBJECT-TYPE
              SYNTAX INTEGER (1..60)
              ACCESS read-only
              STATUS mandatory
              DESCRIPTION
                      "The meter number."
              ::= { nrdpwupsDataEntry 1 }
          
          nrdpwupsModel OBJECT-TYPE
              SYNTAX DisplayString (SIZE (255))
              ACCESS read-write
              STATUS mandatory
              DESCRIPTION
                      "The CM Model designation."
              ::= { nrdpwupsDataEntry 2 }

          nrdpwupsLabel OBJECT-TYPE
              SYNTAX DisplayString (SIZE (255))
              ACCESS read-only
              STATUS mandatory
              DESCRIPTION
                      "The CM Label."
              ::= { nrdpwupsDataEntry 3 }

          nrdpwupsNameplate OBJECT-TYPE
              SYNTAX DisplayString (SIZE (255))
              ACCESS read-only
              STATUS mandatory
              DESCRIPTION
                      "The CM Nameplate."
              ::= { nrdpwupsDataEntry 4 }

         nrdpwupsMeterName OBJECT-TYPE
              SYNTAX DisplayString (SIZE (255))
              ACCESS read-only
              STATUS mandatory
              DESCRIPTION
                      "The CM's Meter Name."
              ::= { nrdpwupsDataEntry 5 }

         nrdpwupsNetworkName OBJECT-TYPE
              SYNTAX DisplayString (SIZE (255))
              ACCESS read-only
              STATUS mandatory
              DESCRIPTION
                      "The CM's Network Device Name."
              ::= { nrdpwupsDataEntry 6 }
         
         nrdpwupsNetworkIP	OBJECT-TYPE
              SYNTAX	IpAddress
              ACCESS	read-only
	          STATUS	mandatory
	          DESCRIPTION
		            "The IP address of the meter's server"
		      ::= { nrdpwupsDataEntry 7 }

         nrdpwupsMeterSlaveAddress OBJECT-TYPE
              SYNTAX INTEGER (1..255)
              ACCESS read-only
              STATUS mandatory
              DESCRIPTION
                      "The meter's drop number."
              ::= { nrdpwupsDataEntry 8 }
          
         nrdpwupsBuildingName OBJECT-TYPE
              SYNTAX DisplayString (SIZE (255))
              ACCESS read-only
              STATUS mandatory
              DESCRIPTION
                      "The CM's Building Name."
              ::= { nrdpwupsDataEntry 9 }

         nrdpwupsOutputVoltsAB OBJECT-TYPE
              SYNTAX INTEGER (0..65535)
              ACCESS read-only
              STATUS mandatory
              DESCRIPTION
                      "The Output RMS Voltage for Phase A to B.
                      (Unit of measure: .1 Volt)"
              ::= { nrdpwupsDataEntry 10 }
			
         nrdpwupsOutputVoltsBC OBJECT-TYPE
              SYNTAX INTEGER (0..65535)
              ACCESS read-only
              STATUS mandatory
              DESCRIPTION
                      "The Output RMS Voltage for Phase B to C.
                      (Unit of measure: .1 Volt)"
              ::= { nrdpwupsDataEntry 11 }
			
         nrdpwupsOutputVoltsCA OBJECT-TYPE
              SYNTAX INTEGER (0..65535)
              ACCESS read-only
              STATUS mandatory
              DESCRIPTION
                      "The Output RMS Voltage for Phase C to A.
                      (Unit of measure: .1 Volt)"
              ::= { nrdpwupsDataEntry 12 }
			
         nrdpwupsInputVoltsAB OBJECT-TYPE
              SYNTAX INTEGER (0..65535)
              ACCESS read-only
              STATUS mandatory
              DESCRIPTION
                      "The Input RMS Voltage for Phase A to B.
                      (Unit of measure: .1 Volt)"
              ::= { nrdpwupsDataEntry 13 }
			
         nrdpwupsInputVoltsBC OBJECT-TYPE
              SYNTAX INTEGER (0..65535)
              ACCESS read-only
              STATUS mandatory
              DESCRIPTION
                      "The Input RMS Voltage for Phase B to C.
                      (Unit of measure: .1 Volt)"
              ::= { nrdpwupsDataEntry 14 }
			
         nrdpwupsInputVoltsCA OBJECT-TYPE
              SYNTAX INTEGER (0..65535)
              ACCESS read-only
              STATUS mandatory
              DESCRIPTION
                      "The Input RMS Voltage for Phase C to A.
                      (Unit of measure: .1 Volt)"
              ::= { nrdpwupsDataEntry 15 }
			
         nrdpwupsInverterVoltsAB OBJECT-TYPE
              SYNTAX INTEGER (0..65535)
              ACCESS read-only
              STATUS mandatory
              DESCRIPTION
                      "The Inverter RMS Voltage for Phase A to B.
                      (Unit of measure: .1 Volt)"
              ::= { nrdpwupsDataEntry 16 }
			
         nrdpwupsInverterVoltsBC OBJECT-TYPE
              SYNTAX INTEGER (0..65535)
              ACCESS read-only
              STATUS mandatory
              DESCRIPTION
                      "The Inverter RMS Voltage for Phase B to C.
                      (Unit of measure: .1 Volt)"
              ::= { nrdpwupsDataEntry 17 }
			
         nrdpwupsInverterVoltsCA OBJECT-TYPE
              SYNTAX INTEGER (0..65535)
              ACCESS read-only
              STATUS mandatory
              DESCRIPTION
                      "The Inverter RMS Voltage for Phase C to A.
                      (Unit of measure: .1 Volt)"
              ::= { nrdpwupsDataEntry 18 }
			
         nrdpwupsBypassVoltsAB OBJECT-TYPE
              SYNTAX INTEGER (0..65535)
              ACCESS read-only
              STATUS mandatory
              DESCRIPTION
                      "The Bypass RMS Voltage for Phase A to B.
                      (Unit of measure: .1 Volt)"
              ::= { nrdpwupsDataEntry 19 }
			
         nrdpwupsBypassVoltsBC OBJECT-TYPE
              SYNTAX INTEGER (0..65535)
              ACCESS read-only
              STATUS mandatory
              DESCRIPTION
                      "The Bypass RMS Voltage for Phase B to C.
                      (Unit of measure: .1 Volt)"
              ::= { nrdpwupsDataEntry 20 }
			
         nrdpwupsBypassVoltsCA OBJECT-TYPE
              SYNTAX INTEGER (0..65535)
              ACCESS read-only
              STATUS mandatory
              DESCRIPTION
                      "The Bypass RMS Voltage for Phase C to A.
                      (Unit of measure: .1 Volt)"
              ::= { nrdpwupsDataEntry 21 }
			
         nrdpwupsMainLogicPower OBJECT-TYPE
              SYNTAX INTEGER (0..65535)
              ACCESS read-only
              STATUS mandatory
              DESCRIPTION
                      "The Power Supply Voltage for UPS logic board.
                      (Unit of measure: .1 Volt)"
              ::= { nrdpwupsDataEntry 22 }
			
         nrdpwupsSecondaryVpPower OBJECT-TYPE
              SYNTAX INTEGER (0..65535)
              ACCESS read-only
              STATUS mandatory
              DESCRIPTION
                      "The Positive Power Supply Voltage for UPS control.
                      (Unit of measure: .1 Volt)"
              ::= { nrdpwupsDataEntry 23 }
			
         nrdpwupsSecondaryVnPower OBJECT-TYPE
              SYNTAX INTEGER (-32768..32767)
              ACCESS read-only
              STATUS mandatory
              DESCRIPTION
                      "The Negative Power Supply Voltage for UPS control.
                      (Unit of measure: .1 Volt)"
              ::= { nrdpwupsDataEntry 24 }
			
         nrdpwupsInverterCurrentA OBJECT-TYPE
              SYNTAX INTEGER (0..65535)
              ACCESS read-only
              STATUS mandatory
              DESCRIPTION
                      "The Inverter Output Current for Phase A.
                      (Unit of measure: .1 Amp)"
              ::= { nrdpwupsDataEntry 25 }
			
         nrdpwupsInverterCurrentB OBJECT-TYPE
              SYNTAX INTEGER (0..65535)
              ACCESS read-only
              STATUS mandatory
              DESCRIPTION
                      "The Inverter Output Current for Phase B.
                      (Unit of measure: .1 Amp)"
              ::= { nrdpwupsDataEntry 26 }
			
         nrdpwupsInverterCurrentC OBJECT-TYPE
              SYNTAX INTEGER (0..65535)
              ACCESS read-only
              STATUS mandatory
              DESCRIPTION
                      "The Inverter Output Current for Phase C.
                      (Unit of measure: .1 Amp)"
              ::= { nrdpwupsDataEntry 27 }
			
         nrdpwupsInputCurrentA OBJECT-TYPE
              SYNTAX INTEGER (0..65535)
              ACCESS read-only
              STATUS mandatory
              DESCRIPTION
                      "The Input Current for Phase A.
                      (Unit of measure: .1 Amp)"
              ::= { nrdpwupsDataEntry 28 }
			
         nrdpwupsInputCurrentB OBJECT-TYPE
              SYNTAX INTEGER (0..65535)
              ACCESS read-only
              STATUS mandatory
              DESCRIPTION
                      "The Input Current for Phase B.
                      (Unit of measure: .1 Amp)"
              ::= { nrdpwupsDataEntry 29 }
			
         nrdpwupsInputCurrentC OBJECT-TYPE
              SYNTAX INTEGER (0..65535)
              ACCESS read-only
              STATUS mandatory
              DESCRIPTION
                      "The Input Current for Phase C.
                      (Unit of measure: .1 Amp)"
              ::= { nrdpwupsDataEntry 30 }
			
         nrdpwupsOutputKw OBJECT-TYPE
              SYNTAX INTEGER (0..65535)
              ACCESS read-only
              STATUS mandatory
              DESCRIPTION
                      "The Output True Power.
                      (Unit of measure: .1 kW)"
              ::= { nrdpwupsDataEntry 31 }
			
         nrdpwupsInputKw OBJECT-TYPE
              SYNTAX INTEGER (0..65535)
              ACCESS read-only
              STATUS mandatory
              DESCRIPTION
                      "The Input True Power.
                      (Unit of measure: .1 kW)"
              ::= { nrdpwupsDataEntry 32 }
			
         nrdpwupsOutputKva OBJECT-TYPE
              SYNTAX INTEGER (0..65535)
              ACCESS read-only
              STATUS mandatory
              DESCRIPTION
                      "The Output Apparent Power.
                      (Unit of measure: .1 kVA)"
              ::= { nrdpwupsDataEntry 33 }
			
         nrdpwupsInputKva OBJECT-TYPE
              SYNTAX INTEGER (0..65535)
              ACCESS read-only
              STATUS mandatory
              DESCRIPTION
                      "The Input Apparent Power.
                      (Unit of measure: .1 kVA)"
              ::= { nrdpwupsDataEntry 34 }
			
         nrdpwupsOutputPowerFactor OBJECT-TYPE
              SYNTAX INTEGER (0..100)
              ACCESS read-only
              STATUS mandatory
              DESCRIPTION
                      "The Output Power Factor.
                      (Unit of measure: .01 %)"
              ::= { nrdpwupsDataEntry 35 }
			
         nrdpwupsInputPowerFactor OBJECT-TYPE
              SYNTAX INTEGER (0..100)
              ACCESS read-only
              STATUS mandatory
              DESCRIPTION
                      "The Input Power Factor.
                      (Unit of measure: .01 %)"
              ::= { nrdpwupsDataEntry 36 }
			
         nrdpwupsOutputFrequency OBJECT-TYPE
              SYNTAX INTEGER (0..65535)
              ACCESS read-only
              STATUS mandatory
              DESCRIPTION
                      "The Output Frequency.
                      (Unit of measure: .1 Hz)"
              ::= { nrdpwupsDataEntry 37 }
			
         nrdpwupsInputFrequency OBJECT-TYPE
              SYNTAX INTEGER (0..65535)
              ACCESS read-only
              STATUS mandatory
              DESCRIPTION
                      "The Input Frequency.
                      (Unit of measure: .1 Hz)"
              ::= { nrdpwupsDataEntry 38 }
			
         nrdpwupsInverterFrequency OBJECT-TYPE
              SYNTAX INTEGER (0..65535)
              ACCESS read-only
              STATUS mandatory
              DESCRIPTION
                      "The Inverter Frequency.
                      (Unit of measure: .1 Hz)"
              ::= { nrdpwupsDataEntry 39 }
			
         nrdpwupsBypassFrequency OBJECT-TYPE
              SYNTAX INTEGER (0..65535)
              ACCESS read-only
              STATUS mandatory
              DESCRIPTION
                      "The Bypass Frequency.
                      (Unit of measure: .1 Hz)"
              ::= { nrdpwupsDataEntry 40 }
			
         nrdpwupsDcLinkVolts OBJECT-TYPE
              SYNTAX INTEGER (0..65535)
              ACCESS read-only
              STATUS mandatory
              DESCRIPTION
                      "The DC Voltage Rectifier to Inverter.
                      (Unit of measure: .1 Volt)"
              ::= { nrdpwupsDataEntry 41 }
			
         nrdpwupsBatteryCurrent OBJECT-TYPE
              SYNTAX INTEGER (-32768..32767)
              ACCESS read-only
              STATUS mandatory
              DESCRIPTION
                      "The Battery Current. Discharge is negative current.
                      (Unit of measure: .1 Amp)"
              ::= { nrdpwupsDataEntry 42 }
			
         nrdpwupsBatteryVoltage OBJECT-TYPE
              SYNTAX INTEGER (0..65535)
              ACCESS read-only
              STATUS mandatory
              DESCRIPTION
                      "The Battery Voltage.
                      (Unit of measure: .1 Volt)"
              ::= { nrdpwupsDataEntry 43 }
			
         nrdpwupsPercentBatteryLeft OBJECT-TYPE
              SYNTAX INTEGER (0..65535)
              ACCESS read-only
              STATUS mandatory
              DESCRIPTION
                      "The Percentage of Useful Stored Energy Remaining.
                      (Unit of measure: .1 %)"
              ::= { nrdpwupsDataEntry 44 }
			
         nrdpwupsBatteryTimeRemaining OBJECT-TYPE
              SYNTAX INTEGER (0..65535)
              ACCESS read-only
              STATUS mandatory
              DESCRIPTION
                      "The estimated minutes until DCUV for current load.
                      (Unit of measure: .1 Min)"
              ::= { nrdpwupsDataEntry 45 }
			
         nrdpwupsBatteryChargeTime OBJECT-TYPE
              SYNTAX INTEGER (0..65535)
              ACCESS read-only
              STATUS mandatory
              DESCRIPTION
                      "The estimated minutes required to fully charge the battery.
                      (Unit of measure: .1 Min)"
              ::= { nrdpwupsDataEntry 46 }
			
         nrdpwupsPeakInverterCurrentA OBJECT-TYPE
              SYNTAX INTEGER (0..65535)
              ACCESS read-only
              STATUS mandatory
              DESCRIPTION
                      "The Peak Inverter Current for Phase A.
                      (Unit of measure: .1 Amp)"
              ::= { nrdpwupsDataEntry 47 }
			
         nrdpwupsPeakInverterCurrentB OBJECT-TYPE
              SYNTAX INTEGER (0..65535)
              ACCESS read-only
              STATUS mandatory
              DESCRIPTION
                      "The Peak Inverter Current for Phase B.
                      (Unit of measure: .1 Amp)"
              ::= { nrdpwupsDataEntry 48 }
			
         nrdpwupsPeakInverterCurrentC OBJECT-TYPE
              SYNTAX INTEGER (0..65535)
              ACCESS read-only
              STATUS mandatory
              DESCRIPTION
                      "The Peak Inverter Current for Phase C.
                      (Unit of measure: .1 Amp)"
              ::= { nrdpwupsDataEntry 49 }
			
         nrdpwupsAvgInputCurrent3PhaseSum OBJECT-TYPE
              SYNTAX INTEGER (0..65535)
              ACCESS read-only
              STATUS mandatory
              DESCRIPTION
                      "The Average Sum of the 3 phase Input Currents.
                      (Unit of measure: .1 Amp)"
              ::= { nrdpwupsDataEntry 50 }
			
         nrdpwupsInputCurrentBarChart OBJECT-TYPE
              SYNTAX INTEGER (0..65535)
              ACCESS read-only
              STATUS mandatory
              DESCRIPTION
                      "To compare against input phase curents.
                      (Unit of measure: .1 Amp)"
              ::= { nrdpwupsDataEntry 52 }
			
         nrdpwupsDcVoltsBarChart OBJECT-TYPE
              SYNTAX INTEGER (0..65535)
              ACCESS read-only
              STATUS mandatory
              DESCRIPTION
                      "To compare against DC link volts.
                      (Unit of measure: .1 Volt)"
              ::= { nrdpwupsDataEntry 54 }
			
         nrdpwupsBatteryCurrentBarChart OBJECT-TYPE
              SYNTAX INTEGER (0..65535)
              ACCESS read-only
              STATUS mandatory
              DESCRIPTION
                      "Value is 100% rated battery discharge current.
                      (Unit of measure: .1 Amp)"
              ::= { nrdpwupsDataEntry 56 }
			
         nrdpwupsBypassVoltsAN OBJECT-TYPE
              SYNTAX INTEGER (0..65535)
              ACCESS read-only
              STATUS mandatory
              DESCRIPTION
                      "The Bypass RMS Voltage for Phase A to N.
                      (Unit of measure: .1 Volt)"
              ::= { nrdpwupsDataEntry 63 }
			
         nrdpwupsBypassVoltsBN OBJECT-TYPE
              SYNTAX INTEGER (0..65535)
              ACCESS read-only
              STATUS mandatory
              DESCRIPTION
                      "The Bypass RMS Voltage for Phase B to N.
                      (Unit of measure: .1 Volt)"
              ::= { nrdpwupsDataEntry 64 }
			
         nrdpwupsBypassVoltsCN OBJECT-TYPE
              SYNTAX INTEGER (0..65535)
              ACCESS read-only
              STATUS mandatory
              DESCRIPTION
                      "The Bypass RMS Voltage for Phase C to N.
                      (Unit of measure: .1 Volt)"
              ::= { nrdpwupsDataEntry 65 }
			
         nrdpwupsInputVoltsAN OBJECT-TYPE
              SYNTAX INTEGER (0..65535)
              ACCESS read-only
              STATUS mandatory
              DESCRIPTION
                      "The Input RMS Voltage for Phase A to N.
                      (Unit of measure: .1 Volt)"
              ::= { nrdpwupsDataEntry 66 }
			
         nrdpwupsInputVoltsBN OBJECT-TYPE
              SYNTAX INTEGER (0..65535)
              ACCESS read-only
              STATUS mandatory
              DESCRIPTION
                      "The Input RMS Voltage for Phase B to N.
                      (Unit of measure: .1 Volt)"
              ::= { nrdpwupsDataEntry 67 }
			
         nrdpwupsInputVoltsCN OBJECT-TYPE
              SYNTAX INTEGER (0..65535)
              ACCESS read-only
              STATUS mandatory
              DESCRIPTION
                      "The Input RMS Voltage for Phase C to N.
                      (Unit of measure: .1 Volt)"
              ::= { nrdpwupsDataEntry 68 }
			
         nrdpwupsInverterVoltsAN OBJECT-TYPE
              SYNTAX INTEGER (0..65535)
              ACCESS read-only
              STATUS mandatory
              DESCRIPTION
                      "The Inverter RMS Voltage for Phase A to N.
                      (Unit of measure: .1 Volt)"
              ::= { nrdpwupsDataEntry 69 }
			
         nrdpwupsInverterVoltsBN OBJECT-TYPE
              SYNTAX INTEGER (0..65535)
              ACCESS read-only
              STATUS mandatory
              DESCRIPTION
                      "The Inverter RMS Voltage for Phase B to N.
                      (Unit of measure: .1 Volt)"
              ::= { nrdpwupsDataEntry 70 }
			
         nrdpwupsInverterVoltsCN OBJECT-TYPE
              SYNTAX INTEGER (0..65535)
              ACCESS read-only
              STATUS mandatory
              DESCRIPTION
                      "The Inverter RMS Voltage for Phase C to N.
                      (Unit of measure: .1 Volt)"
              ::= { nrdpwupsDataEntry 71 }
			
         nrdpwupsAmbientTemperature OBJECT-TYPE
              SYNTAX INTEGER (-32768..32767)
              ACCESS read-only
              STATUS mandatory
              DESCRIPTION
                      "The ambient temperature.
                      (Unit of measure: .1 C)"
              ::= { nrdpwupsDataEntry 72 }
			
         nrdpwupsHeatsinkTemperature OBJECT-TYPE
              SYNTAX INTEGER (-32768..32767)
              ACCESS read-only
              STATUS mandatory
              DESCRIPTION
                      "The heatsink temperature.
                      (Unit of measure: .1 C)"
              ::= { nrdpwupsDataEntry 73 }
			
         nrdpwupsPowerSupplyTemperature OBJECT-TYPE
              SYNTAX INTEGER (-32768..32767)
              ACCESS read-only
              STATUS mandatory
              DESCRIPTION
                      "The power supply temperature.
                      (Unit of measure: .1 C)"
              ::= { nrdpwupsDataEntry 74 }
			
         nrdpwupsLoadCurrentA OBJECT-TYPE
              SYNTAX INTEGER (0..65535)
              ACCESS read-only
              STATUS mandatory
              DESCRIPTION
                      "The Output Load Current for Phase A.
                      (Unit of measure: .1 Amp)"
              ::= { nrdpwupsDataEntry 75 }
			
         nrdpwupsLoadCurrentB OBJECT-TYPE
              SYNTAX INTEGER (0..65535)
              ACCESS read-only
              STATUS mandatory
              DESCRIPTION
                      "The Output Load Current for Phase B.
                      (Unit of measure: .1 Amp)"
              ::= { nrdpwupsDataEntry 76 }
			
         nrdpwupsLoadCurrentC OBJECT-TYPE
              SYNTAX INTEGER (0..65535)
              ACCESS read-only
              STATUS mandatory
              DESCRIPTION
                      "The Output Load Current for Phase C.
                      (Unit of measure: .1 Amp)"
              ::= { nrdpwupsDataEntry 77 }
			
         nrdpwupsLoadCurrentBarChartA OBJECT-TYPE
              SYNTAX INTEGER (0..65535)
              ACCESS read-only
              STATUS mandatory
              DESCRIPTION
                      "100% rated values for the output phase A currents bar charts.
                      (Unit of measure: .1 Amp)"
              ::= { nrdpwupsDataEntry 78 }
			
         nrdpwupsLoadCurrentBarChartB OBJECT-TYPE
              SYNTAX INTEGER (0..65535)
              ACCESS read-only
              STATUS mandatory
              DESCRIPTION
                      "100% rated values for the output phase B currents bar charts.
                      (Unit of measure: .1 Amp)"
              ::= { nrdpwupsDataEntry 79 }
			
         nrdpwupsLoadCurrentBarChartC OBJECT-TYPE
              SYNTAX INTEGER (0..65535)
              ACCESS read-only
              STATUS mandatory
              DESCRIPTION
                      "100% rated values for the output phase C currents bar charts.
                      (Unit of measure: .1 Amp)"
              ::= { nrdpwupsDataEntry 80 }
			
         nrdpwupsOutputVABarChart OBJECT-TYPE
              SYNTAX INTEGER (0..65535)
              ACCESS read-only
              STATUS mandatory
              DESCRIPTION
                      "Rated KVA of the UPS.
                      (Unit of measure: .1 kVA)"
              ::= { nrdpwupsDataEntry 81 }
			
         nrdpwupsPositiveDcRailVolts OBJECT-TYPE
              SYNTAX INTEGER (0..65535)
              ACCESS read-only
              STATUS mandatory
              DESCRIPTION
                      "The Postive DC Link Voltage.
                      (Unit of measure: .1 Volt)"
              ::= { nrdpwupsDataEntry 84 }
			
         nrdpwupsNegativeDcRailVolts OBJECT-TYPE
              SYNTAX INTEGER (-32768..32767)
              ACCESS read-only
              STATUS mandatory
              DESCRIPTION
                      "The Negative DC Link Voltage.
                      (Unit of measure: .1 Volt)"
              ::= { nrdpwupsDataEntry 85 }
			
         nrdpwupsAutoBalanceVolts OBJECT-TYPE
              SYNTAX INTEGER (-32768..32767)
              ACCESS read-only
              STATUS mandatory
              DESCRIPTION
                      "The DC voltage content of output.
                      (Unit of measure: .1 Volt)"
              ::= { nrdpwupsDataEntry 86 }
			
         nrdpwupsBatteryTemperature OBJECT-TYPE
              SYNTAX INTEGER (-32768..32767)
              ACCESS read-only
              STATUS mandatory
              DESCRIPTION
                      "The battery temperature.
                      (Unit of measure: .1 C)"
              ::= { nrdpwupsDataEntry 87 }
			
         nrdpwupsOutputVoltsAN OBJECT-TYPE
              SYNTAX INTEGER (0..65535)
              ACCESS read-only
              STATUS mandatory
              DESCRIPTION
                      "The Output Voltage for Phase A to N.
                      (Unit of measure: .1 Volt)"
              ::= { nrdpwupsDataEntry 88 }
			
         nrdpwupsOutputVoltsBN OBJECT-TYPE
              SYNTAX INTEGER (0..65535)
              ACCESS read-only
              STATUS mandatory
              DESCRIPTION
                      "The Output Voltage for Phase B to N.
                      (Unit of measure: .1 Volt)"
              ::= { nrdpwupsDataEntry 89 }
			
         nrdpwupsOutputVoltsCN OBJECT-TYPE
              SYNTAX INTEGER (0..65535)
              ACCESS read-only
              STATUS mandatory
              DESCRIPTION
                      "The Output Voltage for Phase C to N.
                      (Unit of measure: .1 Volt)"
              ::= { nrdpwupsDataEntry 90 }
			
         nrdpwupsNeutralCurrent OBJECT-TYPE
              SYNTAX INTEGER (0..65535)
              ACCESS read-only
              STATUS mandatory
              DESCRIPTION
                      "The Output Neutral RMS Current.
                      (Unit of measure: .1 Amp)"
              ::= { nrdpwupsDataEntry 91 }
			
         nrdpwupsOutputKwA OBJECT-TYPE
              SYNTAX INTEGER (0..65535)
              ACCESS read-only
              STATUS mandatory
              DESCRIPTION
                      "The Output True Power for Phase A.
                      (Unit of measure: .1 kW)"
              ::= { nrdpwupsDataEntry 92 }
			
         nrdpwupsOutputKwB OBJECT-TYPE
              SYNTAX INTEGER (0..65535)
              ACCESS read-only
              STATUS mandatory
              DESCRIPTION
                      "The Output True Power for Phase B.
                      (Unit of measure: .1 kW)"
              ::= { nrdpwupsDataEntry 93 }
			
         nrdpwupsOutputKwC OBJECT-TYPE
              SYNTAX INTEGER (0..65535)
              ACCESS read-only
              STATUS mandatory
              DESCRIPTION
                      "The Output True Power for Phase C.
                      (Unit of measure: .1 kW)"
              ::= { nrdpwupsDataEntry 94 }
			
         nrdpwupsOutputKwABC OBJECT-TYPE
              SYNTAX INTEGER (0..65535)
              ACCESS read-only
              STATUS mandatory
              DESCRIPTION
                      "The 100% rated value for the output watts pwer phase bar charts.
                      (Unit of measure: .1 kW)"
              ::= { nrdpwupsDataEntry 95 }
			
         nrdpwupsRectifierDcCurrent OBJECT-TYPE
              SYNTAX INTEGER (0..65535)
              ACCESS read-only
              STATUS mandatory
              DESCRIPTION
                      "The DC Current rectifier to DC link.
                      (Unit of measure: .1 Amp)"
              ::= { nrdpwupsDataEntry 96 }
			
         nrdpwupsPositiveBatteryVolts OBJECT-TYPE
              SYNTAX INTEGER (0..65535)
              ACCESS read-only
              STATUS mandatory
              DESCRIPTION
                      "The Postive Battery Voltage.
                      (Unit of measure: .1 Volt)"
              ::= { nrdpwupsDataEntry 97 }
			
         nrdpwupsNegativeBatteryVolts OBJECT-TYPE
              SYNTAX INTEGER (-32768..32767)
              ACCESS read-only
              STATUS mandatory
              DESCRIPTION
                      "The Negative Battery Voltage.
                      (Unit of measure: .1 Volt)"
              ::= { nrdpwupsDataEntry 98 }
			
         nrdpwupsPositiveBatteryCurrent OBJECT-TYPE
              SYNTAX INTEGER (-32768..32767)
              ACCESS read-only
              STATUS mandatory
              DESCRIPTION
                      "The Postive Battery Current.
                      (Unit of measure: .1 Amp)"
              ::= { nrdpwupsDataEntry 99 }
			
         nrdpwupsNegativeBatteryCurrent OBJECT-TYPE
              SYNTAX INTEGER (-32768..32767)
              ACCESS read-only
              STATUS mandatory
              DESCRIPTION
                      "The Negative Battery Current.
                      (Unit of measure: .1 Amp)"
              ::= { nrdpwupsDataEntry 100 }
			
      nrdpwupsOnBattery OBJECT-TYPE                     
           SYNTAX INTEGER {
				no(0)
				yes(1)
			  }
           ACCESS read-only
           STATUS mandatory
           DESCRIPTION
                   "The UPS is on Battery."
           ::= { nrdpwupsDataEntry 101 }
							    
		  nrdpwupsOnBypass OBJECT-TYPE                      
           SYNTAX INTEGER {
				no(0)
				yes(1)		    
			  }				    
           ACCESS read-only		    
           STATUS mandatory		    
           DESCRIPTION			    
                   "The UPS is on Bypass."
           ::= { nrdpwupsDataEntry 110 }
							    
 	nrdpwupsSystemNormal OBJECT-TYPE                  
           SYNTAX INTEGER {
				no(0)
				yes(1)		    
			  }				    
           ACCESS read-only		    
           STATUS mandatory		    
           DESCRIPTION			    
                   "The UPS is operating normally."
           ::= { nrdpwupsDataEntry 111 }
							    
		 	nrdpwupsUpsOff OBJECT-TYPE                        
           SYNTAX INTEGER {
				no(0)
				yes(1)		    
			  }				    
           ACCESS read-only	    
           STATUS mandatory	    
           DESCRIPTION		    
                   "The UPS is no longer supplying power to the load."
           ::= { nrdpwupsDataEntry 116 }
							    
 	nrdpwupsStaticPositionSwitch OBJECT-TYPE          
           SYNTAX INTEGER {
				no(0)
				yes(1)		    
			  }				    
           ACCESS read-only		    
           STATUS mandatory		    
           DESCRIPTION			    
                   "The static switch is on."
           ::= { nrdpwupsDataEntry 132 }
							    
 	nrdpwupsCriticalBussBreaker OBJECT-TYPE           
           SYNTAX INTEGER {
				no(0)
				yes(1)		    
			  }				    
           ACCESS read-only		    
           STATUS mandatory		    
           DESCRIPTION			    
                   "The critical bus breaker is closed."
           ::= { nrdpwupsDataEntry 133 }
							    
 	nrdpwupsByassBreaker OBJECT-TYPE                  
           SYNTAX INTEGER {
				no(0)
				yes(1)		    
			  }				    
           ACCESS read-only		    
           STATUS mandatory		    
           DESCRIPTION			    
                   "The bypass breaker is closed."
           ::= { nrdpwupsDataEntry 134 }
							    
 	nrdpwupsBackfeedBreaker OBJECT-TYPE               
           SYNTAX INTEGER {
				no(0)
				yes(1)		    
			  }				    
           ACCESS read-only		    
           STATUS mandatory		    
           DESCRIPTION			    
                   "The backfeed breaker is closed."
           ::= { nrdpwupsDataEntry 135 }
							    
 	nrdpwupsBypassInputPower OBJECT-TYPE              
           SYNTAX INTEGER {
				no(0)
				yes(1)		    
			  }				    
           ACCESS read-only		    
           STATUS mandatory		    
           DESCRIPTION			    
                   "The bypass input power is available."
           ::= { nrdpwupsDataEntry 136 }
							    
 	nrdpwupsMIB OBJECT-TYPE                           
           SYNTAX INTEGER {
				no(0)
				yes(1)		    
			  }				    
           ACCESS read-only		    
           STATUS mandatory		    
           DESCRIPTION			    
                   "The Maintenance Isolation Breaker (MIB) is closed."
           ::= { nrdpwupsDataEntry 137 }
							    
 	nrdpwupsMBB OBJECT-TYPE                           
           SYNTAX INTEGER {
				no(0)
				yes(1)		    
			  }				    
           ACCESS read-only		    
           STATUS mandatory		    
           DESCRIPTION			    
                   "The Maintenance Bypass Breaker (MBB) is closed."
           ::= { nrdpwupsDataEntry 138 }
							    
 	nrdpwupsMBP OBJECT-TYPE                           
           SYNTAX INTEGER {
				no(0)
				yes(1)		    
			  }				    
           ACCESS read-only		    
           STATUS mandatory		    
           DESCRIPTION			    
                   "The Maintenance Bypass Input (MBP) is closed."
           ::= { nrdpwupsDataEntry 139 }
							    
 	nrdpwupsSbmNormal OBJECT-TYPE                     
           SYNTAX INTEGER {
				no(0)
				yes(1)		    
			  }				    
           ACCESS read-only		    
           STATUS mandatory		    
           DESCRIPTION			    
                   "The system is normal."
           ::= { nrdpwupsDataEntry 140 }
							    
 	nrdpwupsSbmOnBattery OBJECT-TYPE                  
           SYNTAX INTEGER {
				no(0)
				yes(1)		    
			  }				    
           ACCESS read-only		    
           STATUS mandatory		    
           DESCRIPTION			    
                   "The modules are on battery."
           ::= { nrdpwupsDataEntry 141 }
							    
 	nrdpwupsSbmOnBypass OBJECT-TYPE                   
           SYNTAX INTEGER {
				no(0)
				yes(1)		    
			  }				    
           ACCESS read-only		    
           STATUS mandatory		    
           DESCRIPTION			    
                   "The critical load is on bypass."
           ::= { nrdpwupsDataEntry 142 }
							    
 	nrdpwupsSbmNotice OBJECT-TYPE                     
           SYNTAX INTEGER {
				no(0)
				yes(1)		    
			  }				    
           ACCESS read-only		    
           STATUS mandatory		    
           DESCRIPTION			    
                   "The minor alarm advisory."
           ::= { nrdpwupsDataEntry 143 }
							    
 	nrdpwupsSbmAlarm OBJECT-TYPE                      
           SYNTAX INTEGER {
				no(0)
				yes(1)		    
			  }				    
           ACCESS read-only		    
           STATUS mandatory		    
           DESCRIPTION			    
                   "The major alarm, shutdown imminent."
           ::= { nrdpwupsDataEntry 144 }
							    
 	nrdpwupsSbmOnStandby OBJECT-TYPE                  
           SYNTAX INTEGER {
				no(0)
				yes(1)		    
			  }				    
           ACCESS read-only		    
           STATUS mandatory		    
           DESCRIPTION			    
                   "The on standby."
           ::= { nrdpwupsDataEntry 145 }
							    
 	nrdpwupsUpmNormalLed1 OBJECT-TYPE                 
           SYNTAX INTEGER {
				no(0)
				yes(1)		    
			  }				    
           ACCESS read-only		    
           STATUS mandatory		    
           DESCRIPTION			    
                   "The UPM #1 system normal and inverter on line."
           ::= { nrdpwupsDataEntry 148 }
							    
 	nrdpwupsUpmBatteryLed1 OBJECT-TYPE                
           SYNTAX INTEGER {
				no(0)
				yes(1)		    
			  }				    
           ACCESS read-only		    
           STATUS mandatory		    
           DESCRIPTION			    
                   "The UPM #1 modules are on battery in single mode."
           ::= { nrdpwupsDataEntry 149 }
							    
 	nrdpwupsUpmBypassLed1 OBJECT-TYPE                 
           SYNTAX INTEGER {
				no(0)
				yes(1)		    
			  }				    
           ACCESS read-only		    
           STATUS mandatory		    
           DESCRIPTION			    
                   "The UPM #1 critical load is on bypass (single)."
           ::= { nrdpwupsDataEntry 150 }
							    
 	nrdpwupsupmNoticeLed1 OBJECT-TYPE                 
           SYNTAX INTEGER {
				no(0)
				yes(1)		    
			  }				    
           ACCESS read-only		    
           STATUS mandatory		    
           DESCRIPTION			    
                   "The UPM #1 has Minor alarm (single mode)."
           ::= { nrdpwupsDataEntry 151 }
							    
 	nrdpwupsUpmAlarmLed1 OBJECT-TYPE                  
           SYNTAX INTEGER {
				no(0)
				yes(1)		    
			  }				    
           ACCESS read-only		    
           STATUS mandatory		    
           DESCRIPTION			    
                   "The UPM #1 has Major alarm, shutdown imminent."
           ::= { nrdpwupsDataEntry 152 }
							    
 	nrdpwupsUpmStandbyLed1 OBJECT-TYPE                
           SYNTAX INTEGER {
				no(0)
				yes(1)		    
			  }				    
           ACCESS read-only		    
           STATUS mandatory		    
           DESCRIPTION			    
                   "The UPM #1 is on standby."
           ::= { nrdpwupsDataEntry 153 }
							    
 	nrdpwupsUpmPresent1 OBJECT-TYPE                   
           SYNTAX INTEGER {
				no(0)
				yes(1)		    
			  }				    
           ACCESS read-only		    
           STATUS mandatory		    
           DESCRIPTION			    
                   "The UPM #1 is present."
           ::= { nrdpwupsDataEntry 154 }
							    
 	nrdpwupsUpmNormalLed2 OBJECT-TYPE                 
           SYNTAX INTEGER {
				no(0)
				yes(1)		    
			  }				    
           ACCESS read-only		    
           STATUS mandatory		    
           DESCRIPTION			    
                   "The UPM #2 system normal and inverter on line."
           ::= { nrdpwupsDataEntry 156 }
							    
 	nrdpwupsUpmBatteryLed2 OBJECT-TYPE                
           SYNTAX INTEGER {
				no(0)
				yes(1)		    
			  }				    
           ACCESS read-only		    
           STATUS mandatory		    
           DESCRIPTION			    
                   "The UPM #2 modules are on battery in single mode."
           ::= { nrdpwupsDataEntry 157 }
							    
 	nrdpwupsUpmBypassLed2 OBJECT-TYPE                 
           SYNTAX INTEGER {
				no(0)
				yes(1)		    
			  }				    
           ACCESS read-only		    
           STATUS mandatory		    
           DESCRIPTION			    
                   "The UPM #2 critical load is on bypass (single)."
           ::= { nrdpwupsDataEntry 158 }
							    
 	nrdpwupsupmNoticeLed2 OBJECT-TYPE                 
           SYNTAX INTEGER {
				no(0)
				yes(1)		    
			  }				    
           ACCESS read-only		    
           STATUS mandatory		    
           DESCRIPTION			    
                   "The UPM #2 has Minor alarm (single mode)."
           ::= { nrdpwupsDataEntry 159 }
							    
 	nrdpwupsUpmAlarmLed2 OBJECT-TYPE                  
           SYNTAX INTEGER {
				no(0)
				yes(1)		    
			  }				    
           ACCESS read-only		    
           STATUS mandatory		    
           DESCRIPTION			    
                   "The UPM #2 has Major alarm, shutdown imminent."
           ::= { nrdpwupsDataEntry 160 }
							    
 	nrdpwupsUpmStandbyLed2 OBJECT-TYPE                
           SYNTAX INTEGER {
				no(0)
				yes(1)		    
			  }				    
           ACCESS read-only		    
           STATUS mandatory		    
           DESCRIPTION			    
                   "The UPM #2 is on standby."
           ::= { nrdpwupsDataEntry 161 }
							    
 	nrdpwupsUpmPresent2 OBJECT-TYPE                   
           SYNTAX INTEGER {
				no(0)
				yes(1)		    
			  }				    
           ACCESS read-only		    
           STATUS mandatory		    
           DESCRIPTION			    
                   "The UPM #2 is present."
           ::= { nrdpwupsDataEntry 162 }
							    
 	nrdpwupsUpmNormalLed3 OBJECT-TYPE                 
           SYNTAX INTEGER {
				no(0)
				yes(1)		    
			  }				    
           ACCESS read-only		    
           STATUS mandatory		    
           DESCRIPTION			    
                   "The UPM #3 system normal and inverter on line."
           ::= { nrdpwupsDataEntry 164 }
							    
 	nrdpwupsUpmBatteryLed3 OBJECT-TYPE                
           SYNTAX INTEGER {
				no(0)
				yes(1)		    
			  }				    
           ACCESS read-only		    
           STATUS mandatory		    
           DESCRIPTION			    
                   "The UPM #3 modules are on battery in single mode."
           ::= { nrdpwupsDataEntry 165 }
							    
 	nrdpwupsUpmBypassLed3 OBJECT-TYPE                 
           SYNTAX INTEGER {
				no(0)
				yes(1)		    
			  }				    
           ACCESS read-only		    
           STATUS mandatory		    
           DESCRIPTION			    
                   "The UPM #3 critical load is on bypass (single)."
           ::= { nrdpwupsDataEntry 166 }
							    
 	nrdpwupsupmNoticeLed3 OBJECT-TYPE                 
           SYNTAX INTEGER {
				no(0)
				yes(1)		    
			  }				    
           ACCESS read-only		    
           STATUS mandatory		    
           DESCRIPTION			    
                   "The UPM #3 has Minor alarm (single mode)."
           ::= { nrdpwupsDataEntry 167 }
							    
 	nrdpwupsUpmAlarmLed3 OBJECT-TYPE                  
           SYNTAX INTEGER {
				no(0)
				yes(1)		    
			  }				    
           ACCESS read-only		    
           STATUS mandatory		    
           DESCRIPTION			    
                   "The UPM #3 has Major alarm, shutdown imminent."
           ::= { nrdpwupsDataEntry 168 }
							    
 	nrdpwupsUpmStandbyLed3 OBJECT-TYPE                
           SYNTAX INTEGER {
				no(0)
				yes(1)		    
			  }				    
           ACCESS read-only		    
           STATUS mandatory		    
           DESCRIPTION			    
                   "The UPM #3 is on standby."
           ::= { nrdpwupsDataEntry 169 }
							    
 	nrdpwupsUpmPresent3 OBJECT-TYPE                   
           SYNTAX INTEGER {
				no(0)
				yes(1)		    
			  }				    
           ACCESS read-only		    
           STATUS mandatory		    
           DESCRIPTION			    
                   "The UPM #3 is present."
           ::= { nrdpwupsDataEntry 170 }
							    
 	nrdpwupsUpmNormalLed4 OBJECT-TYPE                 
           SYNTAX INTEGER {
				no(0)
				yes(1)		    
			  }				    
           ACCESS read-only		    
           STATUS mandatory		    
           DESCRIPTION			    
                   "The UPM #4 system normal and inverter on line."
           ::= { nrdpwupsDataEntry 172 }
							    
 	nrdpwupsUpmBatteryLed4 OBJECT-TYPE                
           SYNTAX INTEGER {
				no(0)
				yes(1)		    
			  }				    
           ACCESS read-only		    
           STATUS mandatory		    
           DESCRIPTION			    
                   "The UPM #4 modules are on battery in single mode."
           ::= { nrdpwupsDataEntry 173 }
							    
 	nrdpwupsUpmBypassLed4 OBJECT-TYPE                 
           SYNTAX INTEGER {
				no(0)
				yes(1)		    
			  }				    
           ACCESS read-only		    
           STATUS mandatory		    
           DESCRIPTION			    
                   "The UPM #4 critical load is on bypass (single)."
           ::= { nrdpwupsDataEntry 174 }
							    
 	nrdpwupsupmNoticeLed4 OBJECT-TYPE                 
           SYNTAX INTEGER {
				no(0)
				yes(1)		    
			  }				    
           ACCESS read-only		    
           STATUS mandatory		    
           DESCRIPTION			    
                   "The UPM #4 has Minor alarm (single mode)."
           ::= { nrdpwupsDataEntry 175 }
							    
 	nrdpwupsUpmAlarmLed4 OBJECT-TYPE                  
           SYNTAX INTEGER {
				no(0)
				yes(1)		    
			  }				    
           ACCESS read-only		    
           STATUS mandatory		    
           DESCRIPTION			    
                   "The UPM #4 has Major alarm, shutdown imminent."
           ::= { nrdpwupsDataEntry 176 }
							    
 	nrdpwupsUpmStandbyLed4 OBJECT-TYPE                
           SYNTAX INTEGER {
				no(0)
				yes(1)		    
			  }				    
           ACCESS read-only		    
           STATUS mandatory		    
           DESCRIPTION			    
                   "The UPM #4 is on standby."
           ::= { nrdpwupsDataEntry 177 }
							    
 	nrdpwupsUpmPresent4 OBJECT-TYPE                   
           SYNTAX INTEGER {
				no(0)
				yes(1)		    
			  }				    
           ACCESS read-only		    
           STATUS mandatory		    
           DESCRIPTION			    
                   "The UPM #4 is present."
           ::= { nrdpwupsDataEntry 178 }
							    
 	nrdpwupsUpmNormalLed5 OBJECT-TYPE                 
           SYNTAX INTEGER {
				no(0)
				yes(1)		    
			  }				    
           ACCESS read-only		    
           STATUS mandatory		    
           DESCRIPTION			    
                   "The UPM #5 system normal and inverter on line."
           ::= { nrdpwupsDataEntry 180 }
							    
 	nrdpwupsUpmBatteryLed5 OBJECT-TYPE                
           SYNTAX INTEGER {
				no(0)
				yes(1)		    
			  }				    
           ACCESS read-only		    
           STATUS mandatory		    
           DESCRIPTION			    
                   "The UPM #5 modules are on battery in single mode."
           ::= { nrdpwupsDataEntry 181 }
							    
 	nrdpwupsUpmBypassLed55 OBJECT-TYPE                
           SYNTAX INTEGER {
				no(0)
				yes(1)		    
			  }				    
           ACCESS read-only		    
           STATUS mandatory		    
           DESCRIPTION			    
                   "The UPM #5 critical load is on bypass (single)."
           ::= { nrdpwupsDataEntry 182 }
							    
 	nrdpwupsupmNoticeLed5 OBJECT-TYPE                 
           SYNTAX INTEGER {
				no(0)
				yes(1)		    
			  }				    
           ACCESS read-only		    
           STATUS mandatory		    
           DESCRIPTION			    
                   "The UPM #5 has Minor alarm (single mode)."
           ::= { nrdpwupsDataEntry 183 }
							    
 	nrdpwupsUpmAlarmLed5 OBJECT-TYPE                  
           SYNTAX INTEGER {
				no(0)
				yes(1)		    
			  }				    
           ACCESS read-only		    
           STATUS mandatory		    
           DESCRIPTION			    
                   "The UPM #5 has Major alarm, shutdown imminent."
           ::= { nrdpwupsDataEntry 184 }
							    
 	nrdpwupsUpmStandbyLed5 OBJECT-TYPE                
           SYNTAX INTEGER {
				no(0)
				yes(1)		    
			  }				    
           ACCESS read-only		    
           STATUS mandatory		    
           DESCRIPTION			    
                   "The UPM #5 is on standby."
           ::= { nrdpwupsDataEntry 185 }
							    
 	nrdpwupsUpmPresent5 OBJECT-TYPE                   
           SYNTAX INTEGER {
				no(0)
				yes(1)		    
			  }				    
           ACCESS read-only		    
           STATUS mandatory		    
           DESCRIPTION			    
                   "The UPM #5 is present."
           ::= { nrdpwupsDataEntry 186 }
							    
 	nrdpwupsUpmNormalLed6 OBJECT-TYPE                 
           SYNTAX INTEGER {
				no(0)
				yes(1)		    
			  }				    
           ACCESS read-only		    
           STATUS mandatory		    
           DESCRIPTION			    
                   "The UPM #6 system normal and inverter on line."
           ::= { nrdpwupsDataEntry 188 }
							    
 	nrdpwupsUpmBatteryLed6 OBJECT-TYPE                
           SYNTAX INTEGER {
				no(0)
				yes(1)		    
			  }				    
           ACCESS read-only		    
           STATUS mandatory		    
           DESCRIPTION			    
                   "The UPM #6 modules are on battery in single mode."
           ::= { nrdpwupsDataEntry 189 }
							    
 	nrdpwupsUpmBypassLed6 OBJECT-TYPE                 
           SYNTAX INTEGER {
				no(0)
				yes(1)		    
			  }				    
           ACCESS read-only		    
           STATUS mandatory		    
           DESCRIPTION			    
                   "The UPM #6 critical load is on bypass (single)."
           ::= { nrdpwupsDataEntry 190 }
							    
 	nrdpwupsupmNoticeLed6 OBJECT-TYPE                 
           SYNTAX INTEGER {
				no(0)
				yes(1)		    
			  }				    
           ACCESS read-only		    
           STATUS mandatory		    
           DESCRIPTION			    
                   "The UPM #6 has Minor alarm (single mode)."
           ::= { nrdpwupsDataEntry 191 }
							    
 	nrdpwupsUpmAlarmLed6 OBJECT-TYPE                  
           SYNTAX INTEGER {
				no(0)
				yes(1)		    
			  }				    
           ACCESS read-only		    
           STATUS mandatory		    
           DESCRIPTION			    
                   "The UPM #6 has Major alarm, shutdown imminent."
           ::= { nrdpwupsDataEntry 192 }
							    
 	nrdpwupsUpmStandbyLed6 OBJECT-TYPE                
           SYNTAX INTEGER {
				no(0)
				yes(1)		    
			  }				    
           ACCESS read-only		    
           STATUS mandatory		    
           DESCRIPTION			    
                   "The UPM #6 is on standby."
           ::= { nrdpwupsDataEntry 193 }
							    
 	nrdpwupsUpmPresent6 OBJECT-TYPE                   
           SYNTAX INTEGER {
				no(0)
				yes(1)		    
			  }				    
           ACCESS read-only		    
           STATUS mandatory		    
           DESCRIPTION			    
                   "The UPM #6 is present."
           ::= { nrdpwupsDataEntry 194 }
							    
 	nrdpwupsUpmNormalLed7 OBJECT-TYPE                 
           SYNTAX INTEGER {
				no(0)
				yes(1)		    
			  }				    
           ACCESS read-only		    
           STATUS mandatory		    
           DESCRIPTION			    
                   "The UPM #7 system normal and inverter on line."
           ::= { nrdpwupsDataEntry 196 }
							    
 	nrdpwupsUpmBatteryLed7 OBJECT-TYPE                
           SYNTAX INTEGER {
				no(0)
				yes(1)		    
			  }				    
           ACCESS read-only		    
           STATUS mandatory		    
           DESCRIPTION			    
                   "The UPM #7 modules are on battery in single mode."
           ::= { nrdpwupsDataEntry 197 }
							    
 	nrdpwupsUpmBypassLed7 OBJECT-TYPE                 
           SYNTAX INTEGER {
				no(0)
				yes(1)		    
			  }				    
           ACCESS read-only		    
           STATUS mandatory		    
           DESCRIPTION			    
                   "The UPM #7 critical load is on bypass (single)."
           ::= { nrdpwupsDataEntry 198 }
							    
 	nrdpwupsupmNoticeLed7 OBJECT-TYPE                 
           SYNTAX INTEGER {
				no(0)
				yes(1)		    
			  }				    
           ACCESS read-only		    
           STATUS mandatory		    
           DESCRIPTION			    
                   "The UPM #7 has Minor alarm (single mode)."
           ::= { nrdpwupsDataEntry 199 }
							    
 	nrdpwupsUpmAlarmLed7 OBJECT-TYPE                  
           SYNTAX INTEGER {
				no(0)
				yes(1)		    
			  }				    
           ACCESS read-only		    
           STATUS mandatory		    
           DESCRIPTION			    
                   "The UPM #7 has Major alarm, shutdown imminent."
           ::= { nrdpwupsDataEntry 200 }
							    
 	nrdpwupsUpmStandbyLed7 OBJECT-TYPE                
           SYNTAX INTEGER {
				no(0)
				yes(1)		    
			  }				    
           ACCESS read-only		    
           STATUS mandatory		    
           DESCRIPTION			    
                   "The UPM #7 is on standby."
           ::= { nrdpwupsDataEntry 201 }
							    
 	nrdpwupsUpmPresent7 OBJECT-TYPE                   
           SYNTAX INTEGER {
				no(0)
				yes(1)		    
			  }				    
           ACCESS read-only		    
           STATUS mandatory		    
           DESCRIPTION			    
                   "The UPM #7 is present."
           ::= { nrdpwupsDataEntry 202 }
							    
 	nrdpwupsUpmNormalLed8 OBJECT-TYPE                 
           SYNTAX INTEGER {
				no(0)
				yes(1)		    
			  }				    
           ACCESS read-only		    
           STATUS mandatory		    
           DESCRIPTION			    
                   "The UPM #8 system normal and inverter on line."
           ::= { nrdpwupsDataEntry 204 }
							    
 	nrdpwupsUpmBatteryLed8 OBJECT-TYPE                
           SYNTAX INTEGER {
				no(0)
				yes(1)		    
			  }				    
           ACCESS read-only		    
           STATUS mandatory		    
           DESCRIPTION			    
                   "The UPM #8 modules are on battery in single mode."
           ::= { nrdpwupsDataEntry 205 }
							    
 	nrdpwupsUpmBypassLed8 OBJECT-TYPE                 
           SYNTAX INTEGER {
				no(0)
				yes(1)		    
			  }				    
           ACCESS read-only		    
           STATUS mandatory		    
           DESCRIPTION			    
                   "The UPM #8 critical load is on bypass (single)."
           ::= { nrdpwupsDataEntry 206 }
							    
 	nrdpwupsupmNoticeLed8 OBJECT-TYPE                 
           SYNTAX INTEGER {
				no(0)
				yes(1)		    
			  }				    
           ACCESS read-only		    
           STATUS mandatory		    
           DESCRIPTION			    
                   "The UPM #8 has Minor alarm (single mode)."
           ::= { nrdpwupsDataEntry 207 }
							    
 	nrdpwupsUpmAlarmLed8 OBJECT-TYPE                  
           SYNTAX INTEGER {
				no(0)
				yes(1)		    
			  }				    
           ACCESS read-only		    
           STATUS mandatory		    
           DESCRIPTION			    
                   "The UPM #8 has Major alarm, shutdown imminent."
           ::= { nrdpwupsDataEntry 208 }
							    
 	nrdpwupsUpmStandbyLed8 OBJECT-TYPE                
           SYNTAX INTEGER {
				no(0)
				yes(1)		    
			  }				    
           ACCESS read-only		    
           STATUS mandatory		    
           DESCRIPTION			    
                   "The UPM #8 is on standby."
           ::= { nrdpwupsDataEntry 209 }
							    
 	nrdpwupsUpmPresent8 OBJECT-TYPE                   
           SYNTAX INTEGER {
				no(0)
				yes(1)		    
			  }				    
           ACCESS read-only		    
           STATUS mandatory		    
           DESCRIPTION			    
                   "The UPM #8 is present."
           ::= { nrdpwupsDataEntry 210 }
							    
 	nrdpwupsRectifierStatus OBJECT-TYPE               
           SYNTAX INTEGER {
				no(0)
				yes(1)		    
			  }				    
           ACCESS read-only		    
           STATUS mandatory		    
           DESCRIPTION			    
                   "The rectifier is on."
           ::= { nrdpwupsDataEntry 212 }
							    
 	nrdpwupsRectifierInputStatus OBJECT-TYPE          
           SYNTAX INTEGER {
				no(0)
				yes(1)		    
			  }				    
           ACCESS read-only		    
           STATUS mandatory		    
           DESCRIPTION			    
                   "The rectifier input is present."
           ::= { nrdpwupsDataEntry 213 }
							    
 	nrdpwupsBypassStatus OBJECT-TYPE                  
           SYNTAX INTEGER {
				no(0)
				yes(1)		    
			  }				    
           ACCESS read-only		    
           STATUS mandatory		    
           DESCRIPTION			    
                   "The bypas is on."
           ::= { nrdpwupsDataEntry 214 }
							    
 	nrdpwupsBypassInputStatus OBJECT-TYPE             
           SYNTAX INTEGER {
				no(0)
				yes(1)		    
			  }				    
           ACCESS read-only		    
           STATUS mandatory		    
           DESCRIPTION			    
                   "The bypass voltage is present."
           ::= { nrdpwupsDataEntry 215 }
							    
 	nrdpwupsInputCircuitBreakerStatus OBJECT-TYPE     
           SYNTAX INTEGER {
				no(0)
				yes(1)		    
			  }				    
           ACCESS read-only		    
           STATUS mandatory		    
           DESCRIPTION			    
                   "The Input Circuit Breaker Status (CB1) is closed."
           ::= { nrdpwupsDataEntry 216 }
							    
 	nrdpwupsBatteryDisconnectSTatus OBJECT-TYPE       
           SYNTAX INTEGER {
				no(0)
				yes(1)		    
			  }				    
           ACCESS read-only		    
           STATUS mandatory		    
           DESCRIPTION			    
                   "The battery disconnect is closed."
           ::= { nrdpwupsDataEntry 217 }
							    
 	nrdpwupsInverterDisconnectStatus OBJECT-TYPE      
           SYNTAX INTEGER {
				no(0)
				yes(1)		    
			  }				    
           ACCESS read-only		    
           STATUS mandatory		    
           DESCRIPTION			    
                   "The UPS is on line and inverter is supplying power."
           ::= { nrdpwupsDataEntry 218 }
							    
 	nrdpwupsInverterStatus OBJECT-TYPE                
           SYNTAX INTEGER {
				no(0)
				yes(1)		    
			  }				    
           ACCESS read-only		    
           STATUS mandatory		    
           DESCRIPTION			    
                   "The inverter has failure."
           ::= { nrdpwupsDataEntry 219 }
							    
 	nrdpwupsUpmNormal OBJECT-TYPE                     
           SYNTAX INTEGER {
				no(0)
				yes(1)		    
			  }				    
           ACCESS read-only		    
           STATUS mandatory		    
           DESCRIPTION			    
                   "The UPM is normal"
           ::= { nrdpwupsDataEntry 220 }
							    
 	nrdpwupsUpnOnBattery OBJECT-TYPE                  
           SYNTAX INTEGER {
				no(0)
				yes(1)		    
			  }				    
           ACCESS read-only		    
           STATUS mandatory		    
           DESCRIPTION			    
                   "The UPM is on battery."
           ::= { nrdpwupsDataEntry 221 }
							    
 	nrdpwupsUpnBypass OBJECT-TYPE                     
           SYNTAX INTEGER {
				no(0)
				yes(1)		    
			  }				    
           ACCESS read-only		    
           STATUS mandatory		    
           DESCRIPTION			    
                   "The UPM is on bypass."
           ::= { nrdpwupsDataEntry 222 }
							    
 	nrdpwupsUpnNotice OBJECT-TYPE                     
           SYNTAX INTEGER {
				no(0)
				yes(1)		    
			  }				    
           ACCESS read-only		    
           STATUS mandatory		    
           DESCRIPTION			    
                   "The "
           ::= { nrdpwupsDataEntry 223 }
							    
 	nrdpwupsUpnAlarm OBJECT-TYPE                      
           SYNTAX INTEGER {
				no(0)
				yes(1)		    
			  }				    
           ACCESS read-only		    
           STATUS mandatory		    
           DESCRIPTION			    
                   "The UPM has major alarm."
           ::= { nrdpwupsDataEntry 224 }
							    
	nrdpwupsUpnStandby OBJECT-TYPE                    
           SYNTAX INTEGER {
				no(0)
				yes(1)		    
			  }				    
           ACCESS read-only		    
           STATUS mandatory		    
           DESCRIPTION			    
                   "The UPM in on standby."
           ::= { nrdpwupsDataEntry 225 }
							    
 	nrdpwupsMobClosed OBJECT-TYPE                     
           SYNTAX INTEGER {
				no(0)
				yes(1)		    
			  }				    
           ACCESS read-only		    
           STATUS mandatory		    
           DESCRIPTION			    
                   "The MOB is closed."
           ::= { nrdpwupsDataEntry 228 }
							    
 	nrdpwupsSystemRedundant OBJECT-TYPE               
           SYNTAX INTEGER {
				no(0)
				yes(1)		    
			  }				    
           ACCESS read-only		    
           STATUS mandatory		    
           DESCRIPTION			    
                   "The system is redundant."
           ::= { nrdpwupsDataEntry 229 }
							    
 	nrdpwupsInveterAcOverVoltage OBJECT-TYPE          
           SYNTAX INTEGER {
				no(0)
				yes(1)		    
			  }				    
           ACCESS read-only		    
           STATUS mandatory		    
           DESCRIPTION			    
                   "The inverter output voltage has exceeded the upper voltage limit."
           ::= { nrdpwupsDataEntry 244 }
							    
 	nrdpwupsInveterAcUnderVoltage OBJECT-TYPE         
           SYNTAX INTEGER {
				no(0)
				yes(1)		    
			  }				    
           ACCESS read-only		    
           STATUS mandatory		    
           DESCRIPTION			    
                   "The inverter output voltage is less than the lower voltage limit."
           ::= { nrdpwupsDataEntry 245 }
							    
 	nrdpwupsInverterOverUnderFrequency OBJECT-TYPE    
           SYNTAX INTEGER {
				no(0)
				yes(1)		    
			  }				    
           ACCESS read-only		    
           STATUS mandatory		    
           DESCRIPTION			    
                   "The inverter output frequency is outside the upper or lower frequency limit."
           ::= { nrdpwupsDataEntry 246 }
							    
 	nrdpwupsBypassAcOverVoltage OBJECT-TYPE           
           SYNTAX INTEGER {
				no(0)
				yes(1)		    
			  }				    
           ACCESS read-only		    
           STATUS mandatory		    
           DESCRIPTION			    
                   "The bypass input voltage has exceeded the upper voltage limit."
           ::= { nrdpwupsDataEntry 247 }
							    
 	nrdpwupsBypassAcUnderVoltage OBJECT-TYPE          
           SYNTAX INTEGER {
				no(0)
				yes(1)		    
			  }				    
           ACCESS read-only		    
           STATUS mandatory		    
           DESCRIPTION			    
                   "The bypass input voltage is less than the lower voltage limit."
           ::= { nrdpwupsDataEntry 248 }
							    
 	nrdpwupsBypassOverUnderFrequency OBJECT-TYPE      
           SYNTAX INTEGER {
				no(0)
				yes(1)		    
			  }				    
           ACCESS read-only		    
           STATUS mandatory		    
           DESCRIPTION			    
                   "The bypass input frequency is outside the upper or lower frequency limit."
           ::= { nrdpwupsDataEntry 249 }
							    
 	nrdpwupsInputAcOverVoltage OBJECT-TYPE            
           SYNTAX INTEGER {
				no(0)
				yes(1)		    
			  }				    
           ACCESS read-only		    
           STATUS mandatory		    
           DESCRIPTION			    
                   "The input (Utility) voltage has exceeded the upper voltage limit."
           ::= { nrdpwupsDataEntry 250 }
							    
 	nrdpwupsInputAcUnderVoltage OBJECT-TYPE           
           SYNTAX INTEGER {
				no(0)
				yes(1)		    
			  }				    
           ACCESS read-only		    
           STATUS mandatory		    
           DESCRIPTION			    
                   "The input (Utility) voltage is less than the lower voltage limit."
           ::= { nrdpwupsDataEntry 251 }
							    
 	nrdpwupsInputAcOverUnderFrequency OBJECT-TYPE     
           SYNTAX INTEGER {
				no(0)
				yes(1)		    
			  }				    
           ACCESS read-only		    
           STATUS mandatory		    
           DESCRIPTION			    
                   "The input (Utility) frequency is outside the upper or lower frequency limit."
           ::= { nrdpwupsDataEntry 252 }
							    
 	nrdpwupsOutputAcOverVoltage OBJECT-TYPE           
           SYNTAX INTEGER {
				no(0)
				yes(1)		    
			  }				    
           ACCESS read-only		    
           STATUS mandatory		    
           DESCRIPTION			    
                   "The output voltage has exceeded the upper voltage limit."
           ::= { nrdpwupsDataEntry 253 }
							    
 	nrdpwupsOutputAcUnderVoltage OBJECT-TYPE          
           SYNTAX INTEGER {
				no(0)
				yes(1)		    
			  }				    
           ACCESS read-only		    
           STATUS mandatory		    
           DESCRIPTION			    
                   "The output voltage is less than the lower voltage limit."
           ::= { nrdpwupsDataEntry 254 }
							    
 	nrdpwupsOutputAcOverUnderFrequency OBJECT-TYPE    
           SYNTAX INTEGER {
				no(0)
				yes(1)		    
			  }				    
           ACCESS read-only		    
           STATUS mandatory		    
           DESCRIPTION			    
                   "The output frequency is outside the upper or lower frequency limit."
           ::= { nrdpwupsDataEntry 255 }
							    
 	nrdpwupsRemoteEmergencyPowerOff OBJECT-TYPE       
           SYNTAX INTEGER {
				no(0)
				yes(1)		    
			  }				    
           ACCESS read-only		    
           STATUS mandatory		    
           DESCRIPTION			    
                   "The UPS has shut down due to the activation of the remote EPO signal"
           ::= { nrdpwupsDataEntry 256 }
							    
 	nrdpwupsRemoteGoToBypass OBJECT-TYPE              
           SYNTAX INTEGER {
				no(0)
				yes(1)		    
			  }				    
           ACCESS read-only		    
           STATUS mandatory		    
           DESCRIPTION			    
                   "The UPS has transferred to bypass."
           ::= { nrdpwupsDataEntry 257 }
							    
 	nrdpwupsBuildingAlarm6 OBJECT-TYPE                
           SYNTAX INTEGER {
				no(0)
				yes(1)		    
			  }				    
           ACCESS read-only		    
           STATUS mandatory		    
           DESCRIPTION			    
                   "The dry contact closure has been detected on the building alarm 6 input."
           ::= { nrdpwupsDataEntry 258 }
							    
 	nrdpwupsBuildingAlarm5 OBJECT-TYPE                
           SYNTAX INTEGER {
				no(0)
				yes(1)		    
			  }				    
           ACCESS read-only		    
           STATUS mandatory		    
           DESCRIPTION			    
                   "The dry contact closure has been detected on the building alarm 5 input."
           ::= { nrdpwupsDataEntry 259 }
							    
 	nrdpwupsBuildingAlarm4 OBJECT-TYPE                
           SYNTAX INTEGER {
				no(0)
				yes(1)		    
			  }				    
           ACCESS read-only		    
           STATUS mandatory		    
           DESCRIPTION			    
                   "The dry contact closure has been detected on the building alarm 4 input."
           ::= { nrdpwupsDataEntry 260 }
							    
 	nrdpwupsBuildingAlarm3 OBJECT-TYPE                
           SYNTAX INTEGER {
				no(0)
				yes(1)		    
			  }				    
           ACCESS read-only		    
           STATUS mandatory		    
           DESCRIPTION			    
                   "The dry contact closure has been detected on the building alarm 3 input."
           ::= { nrdpwupsDataEntry 261 }
							    
 	nrdpwupsBuildingAlarm2 OBJECT-TYPE                
           SYNTAX INTEGER {
				no(0)
				yes(1)		    
			  }				    
           ACCESS read-only		    
           STATUS mandatory		    
           DESCRIPTION			    
                   "The dry contact closure has been detected on the building alarm 2 input."
           ::= { nrdpwupsDataEntry 262 }
							    
 	nrdpwupsBuildingAlarm1 OBJECT-TYPE                
           SYNTAX INTEGER {
				no(0)
				yes(1)		    
			  }				    
           ACCESS read-only		    
           STATUS mandatory		    
           DESCRIPTION			    
                   "The dry contact closure has been detected on the building alarm 1 input."
           ::= { nrdpwupsDataEntry 263 }
							    
 	nrdpwupsStaticSwitchOverTemerature OBJECT-TYPE    
           SYNTAX INTEGER {
				no(0)
				yes(1)		    
			  }				    
           ACCESS read-only		    
           STATUS mandatory		    
           DESCRIPTION			    
                   "The static switch operating temperature has been exceeded."
           ::= { nrdpwupsDataEntry 264 }
							    
 	nrdpwupsChargerOverTemperature OBJECT-TYPE        
           SYNTAX INTEGER {
				no(0)
				yes(1)		    
			  }				    
           ACCESS read-only		    
           STATUS mandatory		    
           DESCRIPTION			    
                   "The battery charger operating temperature has been exceeded."
           ::= { nrdpwupsDataEntry 265 }
							    
 	nrdpwupsChargerLogicPowerFail OBJECT-TYPE         
           SYNTAX INTEGER {
				no(0)
				yes(1)		    
			  }				    
           ACCESS read-only		    
           STATUS mandatory		    
           DESCRIPTION			    
                   "The battery charger power supply to its digital logic circuitry has failed."
           ::= { nrdpwupsDataEntry 266 }
							    
 	nrdpwupsChargerOverVoltageCurrent OBJECT-TYPE     
           SYNTAX INTEGER {
				no(0)
				yes(1)		    
			  }				    
           ACCESS read-only		    
           STATUS mandatory		    
           DESCRIPTION			    
                   "The battery charger output has exceeded its voltage or current limit."
           ::= { nrdpwupsDataEntry 267 }
							    
 	nrdpwupsInverterOverTemperature OBJECT-TYPE       
           SYNTAX INTEGER {
				no(0)
				yes(1)		    
			  }				    
           ACCESS read-only		    
           STATUS mandatory		    
           DESCRIPTION			    
                   "The inverter temperature has exceeded the upper temperature limit."
           ::= { nrdpwupsDataEntry 268 }
							    
 	nrdpwupsOutputOverload OBJECT-TYPE                
           SYNTAX INTEGER {
				no(0)
				yes(1)		    
			  }				    
           ACCESS read-only		    
           STATUS mandatory		    
           DESCRIPTION			    
                   "The output current limit has been exceeded."
           ::= { nrdpwupsDataEntry 269 }
							    
 	nrdpwupsRectifierInputOverCurrent OBJECT-TYPE     
           SYNTAX INTEGER {
				no(0)
				yes(1)		    
			  }				    
           ACCESS read-only		    
           STATUS mandatory		    
           DESCRIPTION			    
                   "The rectifier input current has exceeded the upper current limit."
           ::= { nrdpwupsDataEntry 270 }
							    
 	nrdpwupsInverterOutputOverCurrent OBJECT-TYPE     
           SYNTAX INTEGER {
				no(0)
				yes(1)		    
			  }				    
           ACCESS read-only		    
           STATUS mandatory		    
           DESCRIPTION			    
                   "The inverter output current has exceeded the upper current limit."
           ::= { nrdpwupsDataEntry 271 }
							    
 	nrdpwupsDcLinkOverVoltage OBJECT-TYPE             
           SYNTAX INTEGER {
				no(0)
				yes(1)		    
			  }				    
           ACCESS read-only		    
           STATUS mandatory		    
           DESCRIPTION			    
                   "The DC link voltage has exceeded the upper voltage limit."
           ::= { nrdpwupsDataEntry 272 }
							    
 	nrdpwupsDcLinkUnderVoltage OBJECT-TYPE            
           SYNTAX INTEGER {
				no(0)
				yes(1)		    
			  }				    
           ACCESS read-only		    
           STATUS mandatory		    
           DESCRIPTION			    
                   "The DC link voltage is less than the lower voltage limit."
           ::= { nrdpwupsDataEntry 273 }
							    
 	nrdpwupsRectifierFailed OBJECT-TYPE               
           SYNTAX INTEGER {
				no(0)
				yes(1)		    
			  }				    
           ACCESS read-only		    
           STATUS mandatory		    
           DESCRIPTION			    
                   "The rectifier has failed."
           ::= { nrdpwupsDataEntry 274 }
							    
 	nrdpwupsInverterFault OBJECT-TYPE                 
           SYNTAX INTEGER {
				no(0)
				yes(1)		    
			  }				    
           ACCESS read-only		    
           STATUS mandatory		    
           DESCRIPTION			    
                   "The inverter has failed."
           ::= { nrdpwupsDataEntry 275 }
							    
 	nrdpwupsBatteryContactorFail OBJECT-TYPE          
           SYNTAX INTEGER {
				no(0)
				yes(1)		    
			  }				    
           ACCESS read-only		    
           STATUS mandatory		    
           DESCRIPTION			    
                   "The battery contactor has failed."
           ::= { nrdpwupsDataEntry 276 }
							    
 	nrdpwupsBypassBreakerFail OBJECT-TYPE             
           SYNTAX INTEGER {
				no(0)
				yes(1)		    
			  }				    
           ACCESS read-only		    
           STATUS mandatory		    
           DESCRIPTION			    
                   "The bypass breaker has failed."
           ::= { nrdpwupsDataEntry 277 }
							    
 	nrdpwupsChargerFailure OBJECT-TYPE                
           SYNTAX INTEGER {
				no(0)
				yes(1)		    
			  }				    
           ACCESS read-only		    
           STATUS mandatory		    
           DESCRIPTION			    
                   "The battery charger has failed."
           ::= { nrdpwupsDataEntry 278 }
							    
 	nrdpwupsStaticSwitchFailure OBJECT-TYPE           
           SYNTAX INTEGER {
				no(0)
				yes(1)		    
			  }				    
           ACCESS read-only		    
           STATUS mandatory		    
           DESCRIPTION			    
                   "The static switch has failed."
           ::= { nrdpwupsDataEntry 280 }
							    
 	nrdpwupsBatteryCurrentLimit OBJECT-TYPE           
           SYNTAX INTEGER {
				no(0)
				yes(1)		    
			  }				    
           ACCESS read-only		    
           STATUS mandatory		    
           DESCRIPTION			    
                   "The battery is operating at maximum current capability."
           ::= { nrdpwupsDataEntry 291 }
							    
 	nrdpwupsOutputCurrentover100Percent OBJECT-TYPE   
           SYNTAX INTEGER {
				no(0)
				yes(1)		    
			  }				    
           ACCESS read-only		    
           STATUS mandatory		    
           DESCRIPTION			    
                   "The system critical bus has exceeded 100% of its current output rating."
           ::= { nrdpwupsDataEntry 294 }
							    
 	nrdpwupsBatteryGroundFault OBJECT-TYPE            
           SYNTAX INTEGER {
				no(0)
				yes(1)		    
			  }				    
           ACCESS read-only		    
           STATUS mandatory		    
           DESCRIPTION			    
                   "The leakage path exists between a battery connection and ground."
           ::= { nrdpwupsDataEntry 295 }
							    
 	nrdpwupsShutdownImminent OBJECT-TYPE              
           SYNTAX INTEGER {
				no(0)
				yes(1)		    
			  }				    
           ACCESS read-only		    
           STATUS mandatory		    
           DESCRIPTION			    
                   "The UPS has entered a state where it may abruptly stop operating without further notice."
           ::= { nrdpwupsDataEntry 299 }
							    
 	nrdpwupsBatteryLow OBJECT-TYPE                    
           SYNTAX INTEGER {
				no(0)
				yes(1)		    
			  }				    
           ACCESS read-only		    
           STATUS mandatory		    
           DESCRIPTION			    
                   "The battery voltage is low."
           ::= { nrdpwupsDataEntry 300 }
							    
 	nrdpwupsUtilityFail OBJECT-TYPE                   
           SYNTAX INTEGER {
				no(0)
				yes(1)		    
			  }				    
           ACCESS read-only		    
           STATUS mandatory		    
           DESCRIPTION			    
                   "The utility input power is not within predetermined limits."
           ::= { nrdpwupsDataEntry 301 }
							    
 	nrdpwupsOutputShortCircuit OBJECT-TYPE            
           SYNTAX INTEGER {
				no(0)
				yes(1)		    
			  }				    
           ACCESS read-only		    
           STATUS mandatory		    
           DESCRIPTION			    
                   "The UPS has detected an abnormally low impedance on its output."
           ::= { nrdpwupsDataEntry 302 }
							    
 	nrdpwupsUtilityNotPresent OBJECT-TYPE             
           SYNTAX INTEGER {
				no(0)
				yes(1)		    
			  }				    
           ACCESS read-only		    
           STATUS mandatory		    
           DESCRIPTION			    
                   "The utility input is not present."
           ::= { nrdpwupsDataEntry 303 }
							    
 	nrdpwupsFullTimeCharging OBJECT-TYPE              
           SYNTAX INTEGER {
				no(0)
				yes(1)		    
			  }				    
           ACCESS read-only		    
           STATUS mandatory		    
           DESCRIPTION			    
                   "The battery charger is on."
           ::= { nrdpwupsDataEntry 304 }
							    
 	nrdpwupsInputLIneVoltageLoss OBJECT-TYPE          
           SYNTAX INTEGER {
				no(0)
				yes(1)		    
			  }				    
           ACCESS read-only		    
           STATUS mandatory		    
           DESCRIPTION			    
                   "The input voltage is out of range."
           ::= { nrdpwupsDataEntry 311 }
							    
    nrdpwupsBatteryDcOverVoltage OBJECT-TYPE          
           SYNTAX INTEGER {
				no(0)
				yes(1)		    
			  }				    
           ACCESS read-only		    
           STATUS mandatory		    
           DESCRIPTION			    
                   "The battery voltage has exceeded a predetermined limit."
           ::= { nrdpwupsDataEntry 312 }
							    
      nrdpwupsPowerSupplyFailure OBJECT-TYPE            
           SYNTAX INTEGER {
				no(0)
				yes(1)		    
			  }				    
           ACCESS read-only		    
           STATUS mandatory		    
           DESCRIPTION			    
                   "The logic power supply has failed."
           ::= { nrdpwupsDataEntry 314 }
							    
      nrdpwupsRectifierCurrentOver125Percent OBJECT-TYPE
           SYNTAX INTEGER {
				no(0)
				yes(1)		    
			  }				    
           ACCESS read-only		    
           STATUS mandatory		    
           DESCRIPTION			    
                   "The rectifier/charger has exceeded 125% of its rating."
           ::= { nrdpwupsDataEntry 319 }
							    
      nrdpwupsNetwrokNotResponding OBJECT-TYPE         
           SYNTAX INTEGER {
				no(0)
				yes(1)		    
			  }				    
           ACCESS read-only		    
           STATUS mandatory		    
           DESCRIPTION			    
                   "The network communications has failed."
           ::= { nrdpwupsDataEntry 329 }
							    
      nrdpwupsOutputDcOverVoltage OBJECT-TYPE          
           SYNTAX INTEGER {
				no(0)
				yes(1)		    
			  }				    
           ACCESS read-only		    
           STATUS mandatory		    
           DESCRIPTION			    
                   "The output DC has exceeded the over voltage limit."
           ::= { nrdpwupsDataEntry 333 }
							    
      nrdpwupsEmergencyShutdownCommand OBJECT-TYPE     
           SYNTAX INTEGER {
				no(0)
				yes(1)		    
			  }				    
           ACCESS read-only		    
           STATUS mandatory		    
           DESCRIPTION			    
                   "The emergency power-off (EPO) command was issued."
           ::= { nrdpwupsDataEntry 341 }
							    
      nrdpwupsBypassNotAvailable OBJECT-TYPE           
           SYNTAX INTEGER {
				no(0)
				yes(1)		    
			  }				    
           ACCESS read-only		    
           STATUS mandatory		    
           DESCRIPTION			    
                   "The bypass input voltage is not available for transfer."
           ::= { nrdpwupsDataEntry 349 }
							    
      nrdpwupsRectifierBreakerOpen OBJECT-TYPE         
           SYNTAX INTEGER {
				no(0)
				yes(1)		    
			  }				    
           ACCESS read-only		    
           STATUS mandatory		    
           DESCRIPTION			    
                   "The rectifier/charger breaker is open."
           ::= { nrdpwupsDataEntry 350 }
							    
      nrdpwupsBatteryContactorOpen OBJECT-TYPE         
           SYNTAX INTEGER {
				no(0)
				yes(1)		    
			  }				    
           ACCESS read-only		    
           STATUS mandatory		    
           DESCRIPTION			    
                   "The battery contactor/breaker is open."
           ::= { nrdpwupsDataEntry 351 }
							    
	nrdpwupsInverterContactOpen OBJECT-TYPE          
           SYNTAX INTEGER {
				no(0)
				yes(1)		    
			  }				    
           ACCESS read-only		    
           STATUS mandatory		    
           DESCRIPTION			    
                   "The inverter output contactor/breaker is open."
           ::= { nrdpwupsDataEntry 352 }
							    
	nrdpwupsBypassBreakerOpen OBJECT-TYPE            
           SYNTAX INTEGER {
				no(0)
				yes(1)		    
			  }				    
           ACCESS read-only		    
           STATUS mandatory		    
           DESCRIPTION			    
                   "The bypass breaker is open."
           ::= { nrdpwupsDataEntry 353 }
							    
	nrdpwupsBatteryTotallyDischarged OBJECT-TYPE     
           SYNTAX INTEGER {
				no(0)
				yes(1)		    
			  }				    
           ACCESS read-only		    
           STATUS mandatory		    
           DESCRIPTION			    
                   "The battery has been discharged to its maximum discharged state."
           ::= { nrdpwupsDataEntry 370 }
							    
	nrdpwupsLossOfRedundancy OBJECT-TYPE             
           SYNTAX INTEGER {
				no(0)
				yes(1)		    
			  }				    
           ACCESS read-only		    
           STATUS mandatory		    
           DESCRIPTION			    
                   "A power module has failed."
           ::= { nrdpwupsDataEntry 376 }
							    
	nrdpwupsLossOfSyncBus OBJECT-TYPE                
           SYNTAX INTEGER {
				no(0)
				yes(1)		    
			  }				    
           ACCESS read-only		    
           STATUS mandatory		    
           DESCRIPTION			    
                   "The sync bus not active is detected."
           ::= { nrdpwupsDataEntry 377 }
							    
	nrdpwupsRectifierBreakerShuntTripped OBJECT-TYPE 
           SYNTAX INTEGER {
				no(0)
				yes(1)		    
			  }				    
           ACCESS read-only		    
           STATUS mandatory		    
           DESCRIPTION			    
                   "The rectifier breaker has been tripped."
           ::= { nrdpwupsDataEntry 378 }
							    
	nrdpwupsLossOfChargerSync OBJECT-TYPE            
           SYNTAX INTEGER {
				no(0)
				yes(1)		    
			  }				    
           ACCESS read-only		    
           STATUS mandatory		    
           DESCRIPTION			    
                   "The charger is not synchronized to its input voltage."
           ::= { nrdpwupsDataEntry 379 }
							    
	nrdpwupsOutputBreakerOpen OBJECT-TYPE            
           SYNTAX INTEGER {
				no(0)
				yes(1)		    
			  }				    
           ACCESS read-only		    
           STATUS mandatory		    
           DESCRIPTION			    
                   "The UPS output breaker is open."
           ::= { nrdpwupsDataEntry 381 }
							    
	nrdpwupsControlPowerOn OBJECT-TYPE               
           SYNTAX INTEGER {
				no(0)
				yes(1)		    
			  }				    
           ACCESS read-only		    
           STATUS mandatory		    
           DESCRIPTION			    
                   "The control power has been applied."
           ::= { nrdpwupsDataEntry 382 }
							    
	nrdpwupsInverterOn OBJECT-TYPE                   
           SYNTAX INTEGER {
				no(0)
				yes(1)		    
			  }				    
           ACCESS read-only		    
           STATUS mandatory		    
           DESCRIPTION			    
                   "The inverter is on."
           ::= { nrdpwupsDataEntry 383 }
							    
	nrdpwupsChargerOn OBJECT-TYPE                    
           SYNTAX INTEGER {
				no(0)
				yes(1)		    
			  }				    
           ACCESS read-only		    
           STATUS mandatory		    
           DESCRIPTION			    
                   "The charger is on."
           ::= { nrdpwupsDataEntry 384 }
							    
	nrdpwupsBypassOn OBJECT-TYPE                     
           SYNTAX INTEGER {
				no(0)
				yes(1)		    
			  }				    
           ACCESS read-only		    
           STATUS mandatory		    
           DESCRIPTION			    
                   "The bypass is available."
           ::= { nrdpwupsDataEntry 385 }
							    
	nrdpwupsBypassPowerLoss OBJECT-TYPE              
           SYNTAX INTEGER {
				no(0)
				yes(1)		    
			  }				    
           ACCESS read-only		    
           STATUS mandatory		    
           DESCRIPTION			    
                   "The bypass input has insufficient power available to supply the current load."
           ::= { nrdpwupsDataEntry 386 }
							    
	nrdpwupsCheckBatteryFlag OBJECT-TYPE             
           SYNTAX INTEGER {
				no(0)
				yes(1)		    
			  }				    
           ACCESS read-only		    
           STATUS mandatory		    
           DESCRIPTION			    
                   "The battery has failed."
           ::= { nrdpwupsDataEntry 393 }
							    
	nrdpwupsBatteryCharging OBJECT-TYPE              
           SYNTAX INTEGER {
				no(0)
				yes(1)		    
			  }				    
           ACCESS read-only		    
           STATUS mandatory		    
           DESCRIPTION			    
                   "The battery is being charged."
           ::= { nrdpwupsDataEntry 394 }
							    
	nrdpwupsBatteryNotCharged OBJECT-TYPE            
           SYNTAX INTEGER {
				no(0)
				yes(1)		    
			  }				    
           ACCESS read-only		    
           STATUS mandatory		    
           DESCRIPTION			    
                   "The battery is not fully charged."
           ::= { nrdpwupsDataEntry 395 }
							    
	nrdpwupsOtherUpsOn OBJECT-TYPE                   
           SYNTAX INTEGER {
				no(0)
				yes(1)		    
			  }				    
           ACCESS read-only		    
           STATUS mandatory		    
           DESCRIPTION			    
                   "One of the other UPSs is currently on (parallel system)."
           ::= { nrdpwupsDataEntry 398 }
							    
	nrdpwupsParallelInverter OBJECT-TYPE             
           SYNTAX INTEGER {
				no(0)
				yes(1)		    
			  }				    
           ACCESS read-only		    
           STATUS mandatory		    
           DESCRIPTION			    
                   "Two or more inverters are currently operating in parallel."
           ::= { nrdpwupsDataEntry 399 }
							    
	nrdpwupsUpsInParallel OBJECT-TYPE                
           SYNTAX INTEGER {
				no(0)
				yes(1)		    
			  }				    
           ACCESS read-only		    
           STATUS mandatory		    
           DESCRIPTION			    
                   "Parallel operation with at least one other UPS."
           ::= { nrdpwupsDataEntry 400 }
							    
	nrdpwupsOutputBreakerRelayFailure OBJECT-TYPE    
           SYNTAX INTEGER {
				no(0)
				yes(1)		    
			  }				    
           ACCESS read-only		    
           STATUS mandatory		    
           DESCRIPTION			    
                   "The output breaker or relay has failed."
           ::= { nrdpwupsDataEntry 401 }
							    
	nrdpwupsControlPowerOff OBJECT-TYPE              
           SYNTAX INTEGER {
				no(0)
				yes(1)		    
			  }				    
           ACCESS read-only		    
           STATUS mandatory		    
           DESCRIPTION			    
                   "The control power has been removed."
           ::= { nrdpwupsDataEntry 402 }
							    
	nrdpwups106PercentOverloadA OBJECT-TYPE          
           SYNTAX INTEGER {
				no(0)
				yes(1)		    
			  }				    
           ACCESS read-only		    
           STATUS mandatory		    
           DESCRIPTION			    
                   "The output phase A has exceeded 106% of its rated current or power."
           ::= { nrdpwupsDataEntry 403 }
							    
	nrdpwups106PercentOverloadB OBJECT-TYPE          
           SYNTAX INTEGER {
				no(0)
				yes(1)		    
			  }				    
           ACCESS read-only		    
           STATUS mandatory		    
           DESCRIPTION			    
                   "The output phase B has exceeded 106% of its rated current or power."
           ::= { nrdpwupsDataEntry 404 }
							    
	nrdpwups106PercentOverloadC OBJECT-TYPE          
           SYNTAX INTEGER {
				no(0)
				yes(1)		    
			  }				    
           ACCESS read-only		    
           STATUS mandatory		    
           DESCRIPTION			    
                   "The output phase C has exceeded 106% of its rated current or power."
           ::= { nrdpwupsDataEntry 405 }
							    
	nrdpwups125PercentOverloadA OBJECT-TYPE          
           SYNTAX INTEGER {
				no(0)
				yes(1)		    
			  }				    
           ACCESS read-only		    
           STATUS mandatory		    
           DESCRIPTION			    
                   "The output phase A has exceeded 125% of its rated current or power."
           ::= { nrdpwupsDataEntry 406 }
							    
	nrdpwups125PercentOverloadB OBJECT-TYPE          
           SYNTAX INTEGER {
				no(0)
				yes(1)		    
			  }				    
           ACCESS read-only		    
           STATUS mandatory		    
           DESCRIPTION			    
                   "The output phase B has exceeded 125% of its rated current or power."
           ::= { nrdpwupsDataEntry 407 }
							    
	nrdpwups125PercentOverloadC OBJECT-TYPE          
           SYNTAX INTEGER {
				no(0)
				yes(1)		    
			  }				    
           ACCESS read-only		    
           STATUS mandatory		    
           DESCRIPTION			    
                   "The output phase C has exceeded 125% of its rated current or power."
           ::= { nrdpwupsDataEntry 408 }
							    
	nrdpwups150PercentOverloadA OBJECT-TYPE          
           SYNTAX INTEGER {
				no(0)
				yes(1)		    
			  }				    
           ACCESS read-only		    
           STATUS mandatory		    
           DESCRIPTION			    
                   "The output phase A has exceeded 150% of its rated current or power."
           ::= { nrdpwupsDataEntry 409 }
							    
	nrdpwups150PercentOverloadB OBJECT-TYPE          
           SYNTAX INTEGER {
				no(0)
				yes(1)		    
			  }				    
           ACCESS read-only		    
           STATUS mandatory		    
           DESCRIPTION			    
                   "The output phase B has exceeded 150% of its rated current or power."
           ::= { nrdpwupsDataEntry 410 }
							    
	nrdpwups150PercentOverloadC OBJECT-TYPE          
           SYNTAX INTEGER {
				no(0)
				yes(1)		    
			  }				    
           ACCESS read-only		    
           STATUS mandatory		    
           DESCRIPTION			    
                   "The output phase C has exceeded 150% of its rated current or power."
           ::= { nrdpwupsDataEntry 411 }
							    
	nrdpwupsUpsOnBattery OBJECT-TYPE                 
           SYNTAX INTEGER {
				no(0)
				yes(1)		    
			  }				    
           ACCESS read-only		    
           STATUS mandatory		    
           DESCRIPTION			    
                   "The UPS is on battery."
           ::= { nrdpwupsDataEntry 412 }
							    
	nrdpwupsUpsOnBypass OBJECT-TYPE                  
           SYNTAX INTEGER {
				no(0)
				yes(1)		    
			  }				    
           ACCESS read-only		    
           STATUS mandatory		    
           DESCRIPTION			    
                   "The UPS is on bypass."
           ::= { nrdpwupsDataEntry 413 }
							    
	nrdpwupsLoadDumped OBJECT-TYPE                   
           SYNTAX INTEGER {
				no(0)
				yes(1)		    
			  }				    
           ACCESS read-only		    
           STATUS mandatory		    
           DESCRIPTION			    
                   "The load power is off."
           ::= { nrdpwupsDataEntry 414 }
							    
	nrdpwupsLoadOnInverter OBJECT-TYPE               
           SYNTAX INTEGER {
				no(0)
				yes(1)		    
			  }				    
           ACCESS read-only		    
           STATUS mandatory		    
           DESCRIPTION			    
                   "The inverter is supplying power to the load."
           ::= { nrdpwupsDataEntry 415 }
							    
	nrdpwupsLowBatteryShutdown OBJECT-TYPE           
           SYNTAX INTEGER {
				no(0)
				yes(1)		    
			  }				    
           ACCESS read-only		    
           STATUS mandatory		    
           DESCRIPTION			    
                   "The battery low limit is reached."
           ::= { nrdpwupsDataEntry 418 }
							    
	nrdpwupsInParallelOperation OBJECT-TYPE          
           SYNTAX INTEGER {
				no(0)
				yes(1)		    
			  }				    
           ACCESS read-only		    
           STATUS mandatory		    
           DESCRIPTION			    
                   "The UPS is operating in normal parallel mode."
           ::= { nrdpwupsDataEntry 423 }
							    
	nrdpwupsSyncingToBypass OBJECT-TYPE              
           SYNTAX INTEGER {
				no(0)
				yes(1)		    
			  }				    
           ACCESS read-only		    
           STATUS mandatory		    
           DESCRIPTION			    
                   "The inverter output is synchronized to the bypass source."
           ::= { nrdpwupsDataEntry 424 }
							    
	nrdpwupsBypassFailure OBJECT-TYPE                
           SYNTAX INTEGER {
				no(0)
				yes(1)		    
			  }				    
           ACCESS read-only		    
           STATUS mandatory		    
           DESCRIPTION			    
                   "The bypass breaker failure."
           ::= { nrdpwupsDataEntry 432 }
							    
	nrdpwupsBatteryTestFailed OBJECT-TYPE            
           SYNTAX INTEGER {
				no(0)
				yes(1)		    
			  }				    
           ACCESS read-only		    
           STATUS mandatory		    
           DESCRIPTION			    
                   "The battery has failed and needs to be replaced."
           ::= { nrdpwupsDataEntry 435 }
							    
	nrdpwupsFuseFailure OBJECT-TYPE                  
           SYNTAX INTEGER {
				no(0)
				yes(1)		    
			  }				    
           ACCESS read-only		    
           STATUS mandatory		    
           DESCRIPTION			    
                   "At least one fuse in the UPS has failed and needs to be replaced."
           ::= { nrdpwupsDataEntry 436 }
							    
	nrdpwupsFanFailure OBJECT-TYPE                   
           SYNTAX INTEGER {
				no(0)
				yes(1)		    
			  }				    
           ACCESS read-only		    
           STATUS mandatory		    
           DESCRIPTION			    
                   "At least one fan in the UPS has failed."
           ::= { nrdpwupsDataEntry 437 }
							    
	nrdpwupsSiteWiringFault OBJECT-TYPE              
           SYNTAX INTEGER {
				no(0)
				yes(1)		    
			  }				    
           ACCESS read-only		    
           STATUS mandatory		    
           DESCRIPTION			    
                   "A fault in the input wiring, other than Phase Rotation; e.g., Ground/Neutral reversed."
           ::= { nrdpwupsDataEntry 438 }
							    
	nrdpwupsBackfeedContactorFailure OBJECT-TYPE     
           SYNTAX INTEGER {
				no(0)
				yes(1)		    
			  }				    
           ACCESS read-only		    
           STATUS mandatory		    
           DESCRIPTION			    
                   "The Backfeed contactor has failed."
           ::= { nrdpwupsDataEntry 439 }
							    
	nrdpwupsBatteriesDisconnected OBJECT-TYPE        
           SYNTAX INTEGER {
				no(0)
				yes(1)		    
			  }				    
           ACCESS read-only		    
           STATUS mandatory		    
           DESCRIPTION			    
                   "The batteries are not connected."
           ::= { nrdpwupsDataEntry 443 }
							    
	nrdpwupsUpsCabinetOverTemperature OBJECT-TYPE    
           SYNTAX INTEGER {
				no(0)
				yes(1)		    
			  }				    
           ACCESS read-only		    
           STATUS mandatory		    
           DESCRIPTION			    
                   "The temperature inside the UPS has exceeded its upper limit."
           ::= { nrdpwupsDataEntry 444 }
							    
	nrdpwupsTransformerOverTemperature OBJECT-TYPE   
           SYNTAX INTEGER {
				no(0)
				yes(1)		    
			  }				    
           ACCESS read-only		    
           STATUS mandatory		    
           DESCRIPTION			    
                   "The output transformer has exceeded its upper temperature limit."
           ::= { nrdpwupsDataEntry 445 }
							    
	nrdpwupsAmbientUnderTemperature OBJECT-TYPE      
           SYNTAX INTEGER {
				no(0)
				yes(1)		    
			  }				    
           ACCESS read-only		    
           STATUS mandatory		    
           DESCRIPTION			    
                   "The ambient temperature is below its lower limit."
           ::= { nrdpwupsDataEntry 446 }
							    
	nrdpwupsAmbientOverTemperature OBJECT-TYPE       
           SYNTAX INTEGER {
				no(0)
				yes(1)		    
			  }				    
           ACCESS read-only		    
           STATUS mandatory		    
           DESCRIPTION			    
                   "The ambient temperature is above its upper limit."
           ::= { nrdpwupsDataEntry 447 }
							    
	nrdpwupsUnableToChargeBatteries OBJECT-TYPE      
           SYNTAX INTEGER {
				no(0)
				yes(1)		    
			  }				    
           ACCESS read-only		    
           STATUS mandatory		    
           DESCRIPTION			    
                   "The charger circuit has determined bad batteries or an open circuit in the connections to the batteries."
           ::= { nrdpwupsDataEntry 452 }
							    
	nrdpwupsInputBreakerFailed OBJECT-TYPE           
           SYNTAX INTEGER {
				no(0)
				yes(1)		    
			  }				    
           ACCESS read-only		    
           STATUS mandatory		    
           DESCRIPTION			    
                   "The input or utility breaker has failed."
           ::= { nrdpwupsDataEntry 461 }
							    


--
-- MGE UPS-EPS
--

          nrdmgeupsData     OBJECT IDENTIFIER ::= { nrdPowerlogic 8 }
          
          nrdmgeupsNumMeters OBJECT-TYPE
              SYNTAX INTEGER (1..60)
              ACCESS read-only
              STATUS mandatory
              DESCRIPTION
                      "The number of MGE UPSs configured 
                      in this device. This entry indicates the number of rows in
                      the Data table."
              ::= { nrdmgeupsData 1 }

          nrdmgeupsDataTable OBJECT-TYPE
              SYNTAX SEQUENCE OF NrdmgeupsDataEntry
              ACCESS not-accessible
              STATUS mandatory
              ::= { nrdmgeupsData 2 }

          nrdmgeupsDataEntry OBJECT-TYPE
              SYNTAX NrdmgeupsDataEntry
              ACCESS not-accessible
              STATUS mandatory
              INDEX { nrdmgeupsMeter }
              ::= { nrdmgeupsDataTable 1 }

          NrdmgeupsDataEntry ::= SEQUENCE {
              nrdmgeupsMeter                            INTEGER,
              nrdmgeupsModel                            DisplayString,
              nrdmgeupsLabel                            DisplayString, 
              nrdmgeupsNameplate                        DisplayString,
              nrdmgeupsMeterName                        DisplayString,
              nrdmgeupsNetworkName                      DisplayString,
              nrdmgeupsNetworkIP                        IpAddress,
              nrdmgeupsMeterSlaveAddress                INTEGER,
              nrdmgeupsBuildingName                     DisplayString,
		     nrdmgeupsInputCurrentA                    INTEGER,
		     nrdmgeupsInputCurrentB                    INTEGER,
		     nrdmgeupsInputCurrentC                    INTEGER,
		     nrdmgeupsInverterCurrentA                 INTEGER,
		     nrdmgeupsInverterCurrentB                 INTEGER,
		     nrdmgeupsInverterCurrentC                 INTEGER,
		     nrdmgeupsBypassCurrentA                   INTEGER,
		     nrdmgeupsBypassCurrentB                   INTEGER,
		     nrdmgeupsBypassCurrentC                   INTEGER,
		     nrdmgeupsLoadCurrentA                     INTEGER,
		     nrdmgeupsLoadCurrentB                     INTEGER,
		     nrdmgeupsLoadCurrentC                     INTEGER,
		     nrdmgeupsLoadPercentLoadCurrent           INTEGER,
		     nrdmgeupsPercentPeakLoadA                 INTEGER,
		     nrdmgeupsPercentPeakLoadB                 INTEGER,
		     nrdmgeupsPercentPeakLoadC                 INTEGER,
		     nrdmgeupsInputVoltageAB                   INTEGER,
		     nrdmgeupsInputVoltageBC                   INTEGER,
		     nrdmgeupsInputVoltageCA                   INTEGER,
		     nrdmgeupsInverterVoltageAN                INTEGER,
		     nrdmgeupsInverterVoltageBN                INTEGER,
		     nrdmgeupsInverterVoltageCN                INTEGER,
		     nrdmgeupsInverterVoltageA                 INTEGER,
		     nrdmgeupsInverterVoltageB                 INTEGER,
		     nrdmgeupsInverterVoltageC                 INTEGER,
		     nrdmgeupsBypassVoltageAN                  INTEGER,
		     nrdmgeupsBypassVoltageBN                  INTEGER,
		     nrdmgeupsBypassVoltageCN                  INTEGER,
		     nrdmgeupsBypassVoltageAB                  INTEGER,
		     nrdmgeupsBypassVoltageBC                  INTEGER,
		     nrdmgeupsBypassVoltageCA                  INTEGER,
		     nrdmgeupsLoadVoltageAN                    INTEGER,
		     nrdmgeupsLoadVoltageBN                    INTEGER,
		     nrdmgeupsLoadVoltageCN                    INTEGER,
		     nrdmgeupsLoadVoltageAB                    INTEGER,
		     nrdmgeupsLoadVoltageBC                    INTEGER,
		     nrdmgeupsLoadVoltageCA                    INTEGER,
		     nrdmgeupsPowerRealLoadA                   INTEGER,
		     nrdmgeupsPowerRealLoadB                   INTEGER,
		     nrdmgeupsPowerRealLoadC                   INTEGER,
		     nrdmgeupsPowerApparentLoadA               INTEGER,
		     nrdmgeupsPowerApparentLoadB               INTEGER,
		     nrdmgeupsPowerApparentLoadC               INTEGER,
		     nrdmgeupsUPSRealPower                     INTEGER,
		     nrdmgeupsUPSApparentPower                 INTEGER,
		     nrdmgeupsPercentInverterLoad              INTEGER,
		     nrdmgeupsPowerFactor		            INTEGER,
		     nrdmgeupsUPSInputFrequency	            INTEGER,
		     nrdmgeupsUPSInverterFrequency             INTEGER,
		     nrdmgeupsUPSBypassFrequency	            INTEGER,
		     nrdmgeupsUPSLoadFrequency 	            INTEGER,
		     nrdmgeupsUPSBatteryVoltage	            INTEGER,
		     nrdmgeupsUPSBatteryCurrent 	            INTEGER,
		     nrdmgeupsUPSBatteryBackupTime             INTEGER,
		     nrdmgeupsUPSBatteryTemperature            INTEGER,
		     nrdmgeupsInverterType                     INTEGER,
		     nrdmgeupsCurrentRatedLoad                 INTEGER,
		     nrdmgeupsPowerRatedLoad                   INTEGER,
		     nrdmgeupsBatteryCircuitBreaker            INTEGER,
		     nrdmgeupsUPSBatteryDischarging            INTEGER,
		     nrdmgeupsMinimumBatteryVoltageAlarm       INTEGER,
		     nrdmgeupsLowBatteryShutdownAlarm          INTEGER,
		     nrdmgeupsBatteryTemperatureAlarm          INTEGER,
		     nrdmgeupsInputVoltageAlarm                INTEGER,
		     nrdmgeupsBatteryVentilationAlarm          INTEGER,
		     nrdmgeupsBatteryCharging                  INTEGER,
		     nrdmgeupsChargerStatus                    INTEGER,
		     nrdmgeupsMajorChargerAlarm                INTEGER,
		     nrdmgeupsInputSwitchQ1                    INTEGER,
		     nrdmgeupsEmergencyOffSwitch               INTEGER,
		     nrdmgeupsChargerInputVoltageAlarm         INTEGER,
		     nrdmgeupsChargerInputFrequencyAlarm       INTEGER,
		     nrdmgeupsChargerGradualShutdownAlarm      INTEGER,
		     nrdmgeupsCurrentLimitingEngine            INTEGER,
		     nrdmgeupsCurrentLimitingBattery           INTEGER,
		     nrdmgeupsBatteryEqualization              INTEGER,
		     nrdmgeupsEngineGeneratorSet               INTEGER,
		     nrdmgeupsInverterStackOverloadAlarm       INTEGER,
              nrdmgeupsMajorInverterAlarm               INTEGER,
		     nrdmgeupsCurrentLimitingInverterOutput    INTEGER,
		     nrdmgeupsInverterThermalOverloadAlarm     INTEGER,
		     nrdmgeupsOutsideContact                   INTEGER,
		     nrdmgeupsEmergencyOffSwitchInverter       INTEGER,
		     nrdmgeupsForcedInverterShutdown           INTEGER,
		     nrdmgeupsFrequencyConversion              INTEGER,
		     nrdmgeupsConditionalInverterShutdown      INTEGER,
		     nrdmgeupsInverterOverloadAlarm            INTEGER,
		     nrdmgeupsBatteryCabinetVentilationAlarm   INTEGER,
		     nrdmgeupsInverterConnected                INTEGER,
		     nrdmgeupsInverterOffDisabled              INTEGER,
		     nrdmgeupsSynchwithBypass                  INTEGER,
		     nrdmgeupsTransferFaultAlarm               INTEGER,
		     nrdmgeupsBypassVoltageAlarm               INTEGER,
		     nrdmgeupsEmergencyOffSwitchBypass         INTEGER,
		     nrdmgeupsK2SContactor                     INTEGER,
		     nrdmgeupsBypassInputSwitch                INTEGER,
		     nrdmgeupsMaintenanceBypassSwitch          INTEGER,
		     nrdmgeupsInverterOutputSwitch             INTEGER,
		     nrdmgeupsStaticSwitch                     INTEGER,
		     nrdmgeupsBypassFrequencyAlarm             INTEGER,
		     nrdmgeupsBypassPhaseVoltageAlarm          INTEGER,
		     nrdmgeupsDesynchwithBypass                INTEGER,
		     nrdmgeupsStaticBypassOverloadAlarm        INTEGER,
		     nrdmgeupsStaticBypassThermalOverloadAlarm INTEGER,
		     nrdmgeupsInverterThermalOverloadAlarm2    INTEGER,
		     nrdmgeupsAuxiliaryCubicleAlarm            INTEGER,
		     nrdmgeupsInhibitTransfertoBypass          INTEGER,
		     nrdmgeupsTransferLockout                  INTEGER,
		     nrdmgeupsSufficientInverters              INTEGER,
		     nrdmgeupsAcquisitionAlarm                 INTEGER,
		     nrdmgeupsBatteryBackupTimeAlarm           INTEGER,
		     nrdmgeupsBatteryEndofLifeAlarm            INTEGER,
		     nrdmgeupsSystemNormal                     INTEGER,
		     nrdmgeupsUPSMinorAlarm                    INTEGER,
		     nrdmgeupsUPSMajorAlarm                    INTEGER,
		     nrdmgeupsOnBattery                        INTEGER,
		     nrdmgeupsStaticSwitchorK2SStatus          INTEGER,
		     nrdmgeupsCubicleVentilationAlarm          INTEGER,
		     nrdmgeupsCommunicationErrorAlarm          INTEGER,
		     nrdmgeupsInConfigurationMode              INTEGER,
		     nrdmgeupsRemoteSettingAlarm               INTEGER,
		     nrdmgeupsInvalidMeasurementsAlarm         INTEGER,
		     nrdmgeupsChangeinStatusAlarm              INTEGER,
		     nrdmgeupsInvalidPhoneMainSiteAlarm        INTEGER,
		     nrdmgeupsInvalidPhoneSecondarySiteAlarm   INTEGER,
		     nrdmgeupsCallReset                        INTEGER,
		     nrdmgeupsReturnCall                       INTEGER,
		     nrdmgeupsStatusChangeReset                INTEGER,
		     nrdmgeupsBatteryInstalled                 INTEGER,
		     nrdmgeupsBatterySensorInstalled           INTEGER,
		  
          }

          nrdmgeupsMeter OBJECT-TYPE
              SYNTAX INTEGER (1..60)
              ACCESS read-only
              STATUS mandatory
              DESCRIPTION
                      "The meter number."
              ::= { nrdmgeupsDataEntry 1 }
          
          nrdmgeupsModel OBJECT-TYPE
              SYNTAX DisplayString (SIZE (255))
              ACCESS read-write
              STATUS mandatory
              DESCRIPTION
                      "The CM Model designation."
              ::= { nrdmgeupsDataEntry 2 }

          nrdmgeupsLabel OBJECT-TYPE
              SYNTAX DisplayString (SIZE (255))
              ACCESS read-only
              STATUS mandatory
              DESCRIPTION
                      "The CM Label."
              ::= { nrdmgeupsDataEntry 3 }

          nrdmgeupsNameplate OBJECT-TYPE
              SYNTAX DisplayString (SIZE (255))
              ACCESS read-only
              STATUS mandatory
              DESCRIPTION
                      "The CM Nameplate."
              ::= { nrdmgeupsDataEntry 4 }

         nrdmgeupsMeterName OBJECT-TYPE
              SYNTAX DisplayString (SIZE (255))
              ACCESS read-only
              STATUS mandatory
              DESCRIPTION
                      "The CM's Meter Name."
              ::= { nrdmgeupsDataEntry 5 }

         nrdmgeupsNetworkName OBJECT-TYPE
              SYNTAX DisplayString (SIZE (255))
              ACCESS read-only
              STATUS mandatory
              DESCRIPTION
                      "The CM's Network Device Name."
              ::= { nrdmgeupsDataEntry 6 }
         
         nrdmgeupsNetworkIP	OBJECT-TYPE
              SYNTAX	IpAddress
              ACCESS	read-only
	          STATUS	mandatory
	          DESCRIPTION
		            "The IP address of the meter's server"
		      ::= { nrdmgeupsDataEntry 7 }

         nrdmgeupsMeterSlaveAddress OBJECT-TYPE
              SYNTAX INTEGER (1..255)
              ACCESS read-only
              STATUS mandatory
              DESCRIPTION
                      "The meter's drop number."
              ::= { nrdmgeupsDataEntry 8 }
          
         nrdmgeupsBuildingName OBJECT-TYPE
              SYNTAX DisplayString (SIZE (255))
              ACCESS read-only
              STATUS mandatory
              DESCRIPTION
                      "The CM's Building Name."
              ::= { nrdmgeupsDataEntry 9 }


         nrdmgeupsInputCurrentA OBJECT-TYPE
              SYNTAX INTEGER (0..65535)
              ACCESS read-only
              STATUS mandatory
              DESCRIPTION
                      "The Input Current for Phase A.
                      (Unit of measure: 1 Amp)"
              ::= { nrdmgeupsDataEntry 10 }
   		
         nrdmgeupsInputCurrentB OBJECT-TYPE                    
              SYNTAX INTEGER (0..65535)
              ACCESS read-only
              STATUS mandatory
              DESCRIPTION
                      "The Input Current for Phase B.
                      (Unit of measure: 1 Amp)"
              ::= { nrdmgeupsDataEntry 11 }
   		
         nrdmgeupsInputCurrentC OBJECT-TYPE                    
              SYNTAX INTEGER (0..65535)
              ACCESS read-only
              STATUS mandatory
              DESCRIPTION
                      "The Input Current for Phase C.
                      (Unit of measure: 1 Amp)"
              ::= { nrdmgeupsDataEntry 12 }
   		
         nrdmgeupsInverterCurrentA OBJECT-TYPE                 
              SYNTAX INTEGER (0..65535)
              ACCESS read-only
              STATUS mandatory
              DESCRIPTION
                      "The Inverter Current for Phase A.
                      (Unit of measure: 1 Amp)"
              ::= { nrdmgeupsDataEntry 13 }
   		
         nrdmgeupsInverterCurrentB OBJECT-TYPE                 
              SYNTAX INTEGER (0..65535)
              ACCESS read-only
              STATUS mandatory
              DESCRIPTION
                      "The Inverter Current for Phase B.
                      (Unit of measure: 1 Amp)"
              ::= { nrdmgeupsDataEntry 14 }
   		
         nrdmgeupsInverterCurrentC OBJECT-TYPE                 
              SYNTAX INTEGER (0..65535)
              ACCESS read-only
              STATUS mandatory
              DESCRIPTION
                      "The Inverter Current for Phase C.
                      (Unit of measure: 1 Amp)"
              ::= { nrdmgeupsDataEntry 15 }
   		
         nrdmgeupsBypassCurrentA OBJECT-TYPE                   
              SYNTAX INTEGER (0..65535)
              ACCESS read-only
              STATUS mandatory
              DESCRIPTION
                      "The Bypass Current for Phase A.
                      (Unit of measure: 1 Amp)"
              ::= { nrdmgeupsDataEntry 16 }
   		
         nrdmgeupsBypassCurrentB OBJECT-TYPE                   
              SYNTAX INTEGER (0..65535)
              ACCESS read-only
              STATUS mandatory
              DESCRIPTION
                      "The Bypass Current for Phase B.
                      (Unit of measure: 1 Amp)"
              ::= { nrdmgeupsDataEntry 17 }
   		
         nrdmgeupsBypassCurrentC OBJECT-TYPE                   
              SYNTAX INTEGER (0..65535)
              ACCESS read-only
              STATUS mandatory
              DESCRIPTION
                      "The Bypass Current for Phase C.
                      (Unit of measure: 1 Amp)"
              ::= { nrdmgeupsDataEntry 18 }
   		
         nrdmgeupsLoadCurrentA OBJECT-TYPE                     
              SYNTAX INTEGER (0..65535)
              ACCESS read-only
              STATUS mandatory
              DESCRIPTION
                      "The Output Current for Phase A.
                      (Unit of measure: 1 Amp)"
              ::= { nrdmgeupsDataEntry 19 }
   		
         nrdmgeupsLoadCurrentB OBJECT-TYPE                     
              SYNTAX INTEGER (0..65535)
              ACCESS read-only
              STATUS mandatory
              DESCRIPTION
                      "The Output Current for Phase B.
                      (Unit of measure: 1 Amp)"
              ::= { nrdmgeupsDataEntry 20 }
   		
         nrdmgeupsLoadCurrentC OBJECT-TYPE                     
              SYNTAX INTEGER (0..65535)
              ACCESS read-only
              STATUS mandatory
              DESCRIPTION
                      "The Output Current for Phase C.
                      (Unit of measure: 1 Amp)"
              ::= { nrdmgeupsDataEntry 21 }
   		
         nrdmgeupsLoadPercentLoadCurrent OBJECT-TYPE           
              SYNTAX INTEGER (0..65535)
              ACCESS read-only
              STATUS mandatory
              DESCRIPTION
                      "The Output Percent Load.
                      (Unit of measure: 1 %)"
              ::= { nrdmgeupsDataEntry 22 }
   		
         nrdmgeupsPercentPeakLoadA OBJECT-TYPE                 
              SYNTAX INTEGER (0..65535)
              ACCESS read-only
              STATUS mandatory
              DESCRIPTION
                      "The Peak Output Percent Load for Phase A.
                      (Unit of measure: .01 %)"
              ::= { nrdmgeupsDataEntry 23 }
   		
         nrdmgeupsPercentPeakLoadB OBJECT-TYPE                 
              SYNTAX INTEGER (-32768..32767)
              ACCESS read-only
              STATUS mandatory
              DESCRIPTION
                      "The Peak Output Percent Load for Phase B.
                      (Unit of measure: .01 %)"
              ::= { nrdmgeupsDataEntry 24 }
   		
         nrdmgeupsPercentPeakLoadC OBJECT-TYPE                 
              SYNTAX INTEGER (0..65535)
              ACCESS read-only
              STATUS mandatory
              DESCRIPTION
                      "The Peak Output Percent Load for Phase C.
                      (Unit of measure: .01 %)"
              ::= { nrdmgeupsDataEntry 25 }
   		
         nrdmgeupsInputVoltageAB OBJECT-TYPE                   
              SYNTAX INTEGER (0..65535)
              ACCESS read-only
              STATUS mandatory
              DESCRIPTION
                      "The Input Voltage Phase A to B.
                      (Unit of measure: 1 Volt)"
              ::= { nrdmgeupsDataEntry 26 }
   		
         nrdmgeupsInputVoltageBC OBJECT-TYPE                   
              SYNTAX INTEGER (0..65535)
              ACCESS read-only
              STATUS mandatory
              DESCRIPTION
                      "The Input Voltage Phase B to C.
                      (Unit of measure: 1 Volt)"
              ::= { nrdmgeupsDataEntry 27 }
   		
         nrdmgeupsInputVoltageCA OBJECT-TYPE                   
              SYNTAX INTEGER (0..65535)
              ACCESS read-only
              STATUS mandatory
              DESCRIPTION
                      "The Input Voltage Phase C to A.
                      (Unit of measure: 1 Volt)"
              ::= { nrdmgeupsDataEntry 28 }
   		
         nrdmgeupsInverterVoltageAN OBJECT-TYPE                
              SYNTAX INTEGER (0..65535)
              ACCESS read-only
              STATUS mandatory
              DESCRIPTION
                      "The Inverter Voltage Phase A to N.
                      (Unit of measure: 1 Volt)"
              ::= { nrdmgeupsDataEntry 29 }
   		
         nrdmgeupsInverterVoltageBN OBJECT-TYPE                
              SYNTAX INTEGER (0..65535)
              ACCESS read-only
              STATUS mandatory
              DESCRIPTION
                      "The Inverter Voltage Phase B to N.
                      (Unit of measure: 1 Volt)"
              ::= { nrdmgeupsDataEntry 30 }
   		
         nrdmgeupsInverterVoltageCN OBJECT-TYPE                
              SYNTAX INTEGER (0..65535)
              ACCESS read-only
              STATUS mandatory
              DESCRIPTION
                      "The Inverter Voltage Phase C to N.
                      (Unit of measure: 1 Volt)"
              ::= { nrdmgeupsDataEntry 31 }
   		
         nrdmgeupsInverterVoltageA OBJECT-TYPE                 
              SYNTAX INTEGER (0..65535)
              ACCESS read-only
              STATUS mandatory
              DESCRIPTION
                      "The Inverter Voltage Phase A to B.
                      (Unit of measure: 1 Volt)"
              ::= { nrdmgeupsDataEntry 32 }
   		
         nrdmgeupsInverterVoltageB OBJECT-TYPE                 
              SYNTAX INTEGER (0..65535)
              ACCESS read-only
              STATUS mandatory
              DESCRIPTION
                      "The Inverter Voltage Phase B to C.
                      (Unit of measure: 1 Volt)"
              ::= { nrdmgeupsDataEntry 33 }
   		
         nrdmgeupsInverterVoltageC OBJECT-TYPE                 
              SYNTAX INTEGER (0..65535)
              ACCESS read-only
              STATUS mandatory
              DESCRIPTION
                      "The Inverter Voltage Phase C to A.
                      (Unit of measure: 1 Volt)"
              ::= { nrdmgeupsDataEntry 34 }
   		
         nrdmgeupsBypassVoltageAN OBJECT-TYPE                  
              SYNTAX INTEGER (0..100)
              ACCESS read-only
              STATUS mandatory
              DESCRIPTION
                      "The Bypass Voltage Phase A to N.
                      (Unit of measure: 1 Volt)"
              ::= { nrdmgeupsDataEntry 35 }
   		
         nrdmgeupsBypassVoltageBN OBJECT-TYPE                  
              SYNTAX INTEGER (0..100)
              ACCESS read-only
              STATUS mandatory
              DESCRIPTION
                      "The Bypass Voltage Phase B to N.
                      (Unit of measure: 1 Volt)"
              ::= { nrdmgeupsDataEntry 36 }
   		
         nrdmgeupsBypassVoltageCN OBJECT-TYPE                  
              SYNTAX INTEGER (0..65535)
              ACCESS read-only
              STATUS mandatory
              DESCRIPTION
                      "The Bypass Voltage Phase C to N.
                      (Unit of measure: 1 Volt)"
              ::= { nrdmgeupsDataEntry 37 }
   		
         nrdmgeupsBypassVoltageAB OBJECT-TYPE                  
              SYNTAX INTEGER (0..65535)
              ACCESS read-only
              STATUS mandatory
              DESCRIPTION
                      "The Bypass Voltage Phase A to B.
                      (Unit of measure: 1 Volt)"
              ::= { nrdmgeupsDataEntry 38 }
   		
         nrdmgeupsBypassVoltageBC OBJECT-TYPE                  
              SYNTAX INTEGER (0..65535)
              ACCESS read-only
              STATUS mandatory
              DESCRIPTION
                      "The Bypass Voltage Phase B to C.
                      (Unit of measure: 1 Volt)"
              ::= { nrdmgeupsDataEntry 39 }
   		
         nrdmgeupsBypassVoltageCA OBJECT-TYPE                  
              SYNTAX INTEGER (0..65535)
              ACCESS read-only
              STATUS mandatory
              DESCRIPTION
                      "The Bypass Voltage Phase C to A.
                      (Unit of measure: 1 Volt)"
              ::= { nrdmgeupsDataEntry 40 }
   		
         nrdmgeupsLoadVoltageAN OBJECT-TYPE                    
              SYNTAX INTEGER (0..65535)
              ACCESS read-only
              STATUS mandatory
              DESCRIPTION
                      "The Output Voltage Phase A to N.
                      (Unit of measure: 1 Volt)"
              ::= { nrdmgeupsDataEntry 41 }
   		
         nrdmgeupsLoadVoltageBN OBJECT-TYPE                    
              SYNTAX INTEGER (-32768..32767)
              ACCESS read-only
              STATUS mandatory
              DESCRIPTION
                      "The Output Voltage Phase B to N.
                      (Unit of measure: 1 Volt)"
              ::= { nrdmgeupsDataEntry 42 }
   		
         nrdmgeupsLoadVoltageCN OBJECT-TYPE                    
              SYNTAX INTEGER (0..65535)
              ACCESS read-only
              STATUS mandatory
              DESCRIPTION
                      "The Output Voltage Phase C to N.
                      (Unit of measure: 1 Volt)"
              ::= { nrdmgeupsDataEntry 43 }
   		
         nrdmgeupsLoadVoltageAB OBJECT-TYPE                    
              SYNTAX INTEGER (0..65535)
              ACCESS read-only
              STATUS mandatory
              DESCRIPTION
                      "The Output Voltage Phase A to B.
                      (Unit of measure: 1 Volt)"
              ::= { nrdmgeupsDataEntry 44 }
   		
         nrdmgeupsLoadVoltageBC OBJECT-TYPE                    
              SYNTAX INTEGER (0..65535)
              ACCESS read-only
              STATUS mandatory
              DESCRIPTION
                      "The Output Voltage Phase B to C.
                      (Unit of measure: 1 Volt)"
              ::= { nrdmgeupsDataEntry 45 }
   		
         nrdmgeupsLoadVoltageCA OBJECT-TYPE                    
              SYNTAX INTEGER (0..65535)
              ACCESS read-only
              STATUS mandatory
              DESCRIPTION
                      "The Output Voltage Phase C to A.
                      (Unit of measure: 1 Volt)"
              ::= { nrdmgeupsDataEntry 46 }
   		
         nrdmgeupsPowerRealLoadA OBJECT-TYPE                   
              SYNTAX INTEGER (0..65535)
              ACCESS read-only
              STATUS mandatory
              DESCRIPTION
                      "The Output Real Power for Phase A.
                      (Unit of measure: 1 KW)"
              ::= { nrdmgeupsDataEntry 47 }
   		
         nrdmgeupsPowerRealLoadB OBJECT-TYPE                   
              SYNTAX INTEGER (0..65535)
              ACCESS read-only
              STATUS mandatory
              DESCRIPTION
                      "The Output Real Power for Phase B.
                      (Unit of measure: 1 KW)"
              ::= { nrdmgeupsDataEntry 48 }
   		
         nrdmgeupsPowerRealLoadC OBJECT-TYPE                   
              SYNTAX INTEGER (0..65535)
              ACCESS read-only
              STATUS mandatory
              DESCRIPTION
                      "The Output Real Power for Phase C.
                      (Unit of measure: 1 KW)"
              ::= { nrdmgeupsDataEntry 49 }
   		
         nrdmgeupsPowerApparentLoadA OBJECT-TYPE               
              SYNTAX INTEGER (0..65535)
              ACCESS read-only
              STATUS mandatory
              DESCRIPTION
                      "The Output Apparent Power for Phase A.
                      (Unit of measure: 1 KVA)"
              ::= { nrdmgeupsDataEntry 50 }
   		
         nrdmgeupsPowerApparentLoadB OBJECT-TYPE               
              SYNTAX INTEGER (0..65535)
              ACCESS read-only
              STATUS mandatory
              DESCRIPTION
                      "The Output Apparent Power for Phase B.
                      (Unit of measure: 1 KVA)"
              ::= { nrdmgeupsDataEntry 51 }
   		
         nrdmgeupsPowerApparentLoadC OBJECT-TYPE               
              SYNTAX INTEGER (0..65535)
              ACCESS read-only
              STATUS mandatory
              DESCRIPTION
                      "The Output Apparent Power for Phase C.
                      (Unit of measure: 1 KVA)"
              ::= { nrdmgeupsDataEntry 52 }
   		
         nrdmgeupsUPSRealPower OBJECT-TYPE                     
              SYNTAX INTEGER (0..65535)
              ACCESS read-only
              STATUS mandatory
              DESCRIPTION
                      "The Total Output Real Power.
                      (Unit of measure: 1 KW)"
              ::= { nrdmgeupsDataEntry 53 }
   		
         nrdmgeupsUPSApparentPower OBJECT-TYPE
              SYNTAX INTEGER (0..65535)
              ACCESS read-only
              STATUS mandatory
              DESCRIPTION
                      "The Total Output Apparent Power.
                      (Unit of measure: 1 KVA)"
              ::= { nrdmgeupsDataEntry 54 }
   		
         nrdmgeupsPercentInverterLoad OBJECT-TYPE              
              SYNTAX INTEGER (0..65535)
              ACCESS read-only
              STATUS mandatory
              DESCRIPTION
                      "The Total Inverter Percent Output.
                      (Unit of measure: 1 %)"
              ::= { nrdmgeupsDataEntry 55 }
   		
         nrdmgeupsPowerFactor OBJECT-TYPE		              
              SYNTAX INTEGER (0..65535)
              ACCESS read-only
              STATUS mandatory
              DESCRIPTION
                      "The Output Power Factor.
                      (Unit of measure: .01 %)"
              ::= { nrdmgeupsDataEntry 56 }
   		
         nrdmgeupsUPSInputFrequency OBJECT-TYPE	              
              SYNTAX INTEGER (0..65535)
              ACCESS read-only
              STATUS mandatory
              DESCRIPTION
                      "The Input Frequency.
                      (Unit of measure: .1 Hz)"
              ::= { nrdmgeupsDataEntry 57 }
   		
         nrdmgeupsUPSInverterFrequency OBJECT-TYPE             
              SYNTAX INTEGER (0..65535)
              ACCESS read-only
              STATUS mandatory
              DESCRIPTION
                      "The Inverter Frequency.
                      (Unit of measure: .1 Hz)"
              ::= { nrdmgeupsDataEntry 58 }
   		
         nrdmgeupsUPSBypassFrequency OBJECT-TYPE	              
              SYNTAX INTEGER (0..65535)
              ACCESS read-only
              STATUS mandatory
              DESCRIPTION
                      "The Bypass Frequency.
                      (Unit of measure: .1 Hz)"
              ::= { nrdmgeupsDataEntry 59 }
   		
         nrdmgeupsUPSLoadFrequency OBJECT-TYPE 	              
              SYNTAX INTEGER (0..65535)
              ACCESS read-only
              STATUS mandatory
              DESCRIPTION
                      "The Output Frequency.
                      (Unit of measure: .1 Hz)"
              ::= { nrdmgeupsDataEntry 60 }
   		
         nrdmgeupsUPSBatteryVoltage OBJECT-TYPE	              
              SYNTAX INTEGER (0..65535)
              ACCESS read-only
              STATUS mandatory
              DESCRIPTION
                      "The Battery Voltage.
                      (Unit of measure: 1 Volt)"
              ::= { nrdmgeupsDataEntry 61 }
   		
         nrdmgeupsUPSBatteryCurrent OBJECT-TYPE 	              
              SYNTAX INTEGER (0..65535)
              ACCESS read-only
              STATUS mandatory
              DESCRIPTION
                      "The Battery Current.
                      (Unit of measure: 1 Amp)"
              ::= { nrdmgeupsDataEntry 62 }
   		
         nrdmgeupsUPSBatteryBackupTime OBJECT-TYPE            
              SYNTAX INTEGER (-32768..32767)
              ACCESS read-only
              STATUS mandatory
              DESCRIPTION
                      "The Battery Backup Time Remaining.
                      (Unit of measure: 1 Minute)"
              ::= { nrdmgeupsDataEntry 63 }
   		
         nrdmgeupsUPSBatteryTemperature OBJECT-TYPE            
              SYNTAX INTEGER (-32768..32767)
              ACCESS read-only
              STATUS mandatory
              DESCRIPTION
                      "The Battery Temperature.
                      (Unit of measure: 1 C)"
              ::= { nrdmgeupsDataEntry 64 }
   		
         nrdmgeupsInverterType OBJECT-TYPE                     
           SYNTAX INTEGER {
   			unitary(0)
   			parallel_wo_SS(1)
   			parallel_w_SS(2)
   			ss_cubical(3)
   		  }
              ACCESS read-only
              STATUS mandatory
              DESCRIPTION
                      "The type of inverter."
              ::= { nrdmgeupsDataEntry 65 }
   		
         nrdmgeupsCurrentRatedLoad OBJECT-TYPE                 
              SYNTAX INTEGER (0..65535)
              ACCESS read-only
              STATUS mandatory
              DESCRIPTION
                      "The Maximum Rated Current.
                      (Unit of measure: 1 Amp)"
              ::= { nrdmgeupsDataEntry 66 }
   		
         nrdmgeupsPowerRatedLoad OBJECT-TYPE                   
              SYNTAX INTEGER (0..65535)
              ACCESS read-only
              STATUS mandatory
              DESCRIPTION
                      "The Maximum Rated Power.
                      (Unit of measure: 1 KW)"
              ::= { nrdmgeupsDataEntry 67 }

   		
         nrdmgeupsBatteryCircuitBreaker OBJECT-TYPE                   
           SYNTAX INTEGER {
   			no(0)
   			yes(1)
   		  }
           ACCESS read-only
           STATUS mandatory
           DESCRIPTION
                   "The Battery Circuit Breaker is Closed."
           ::= { nrdmgeupsDataEntry 68 }

         nrdmgeupsUPSBatteryDischarging  OBJECT-TYPE                               
           SYNTAX INTEGER {
   			no(0)
   			yes(1)
   		  }
           ACCESS read-only
           STATUS mandatory
           DESCRIPTION
                   "The Battery is Discharging."
           ::= { nrdmgeupsDataEntry 69 }

         nrdmgeupsMinimumBatteryVoltageAlarm  OBJECT-TYPE                         
           SYNTAX INTEGER {
   			no(0)
   			yes(1)
   		  }
           ACCESS read-only
           STATUS mandatory
           DESCRIPTION
                   "The Battery is below minimum voltage."
           ::= { nrdmgeupsDataEntry 70 }

         nrdmgeupsLowBatteryShutdownAlarm  OBJECT-TYPE                            
           SYNTAX INTEGER {
   			no(0)
   			yes(1)
   		  }
           ACCESS read-only
           STATUS mandatory
           DESCRIPTION
                   "The battery is below shutdown voltage."
           ::= { nrdmgeupsDataEntry 71 }

         nrdmgeupsBatteryTemperatureAlarm  OBJECT-TYPE                            
           SYNTAX INTEGER {
   			no(0)
   			yes(1)
   		  }
           ACCESS read-only
           STATUS mandatory
           DESCRIPTION
                   "The battery temperature is out of range."
           ::= { nrdmgeupsDataEntry 72 }

         nrdmgeupsInputVoltageAlarm   OBJECT-TYPE                                 
           SYNTAX INTEGER {
   			no(0)
   			yes(1)
   		  }
           ACCESS read-only
           STATUS mandatory
           DESCRIPTION
                   "The Input voltage is out of range."
           ::= { nrdmgeupsDataEntry 73 }

         nrdmgeupsBatteryVentilationAlarm   OBJECT-TYPE                           
           SYNTAX INTEGER {
   			no(0)
   			yes(1)
   		  }
           ACCESS read-only
           STATUS mandatory
           DESCRIPTION
                   "The battery ventilation is in alarm."
           ::= { nrdmgeupsDataEntry 74 }

         nrdmgeupsBatteryCharging   OBJECT-TYPE                                   
           SYNTAX INTEGER {
   			no(0)
   			yes(1)
   		  }
           ACCESS read-only
           STATUS mandatory
           DESCRIPTION
                   "The Battery is charging."
           ::= { nrdmgeupsDataEntry 75 }

         nrdmgeupsChargerStatus  OBJECT-TYPE                                      
           SYNTAX INTEGER {
   			no(0)
   			yes(1)
   		  }
           ACCESS read-only
           STATUS mandatory
           DESCRIPTION
                   "The charger is operating."
           ::= { nrdmgeupsDataEntry 76 }

         nrdmgeupsMajorChargerAlarm  OBJECT-TYPE                                  
           SYNTAX INTEGER {
   			no(0)
   			yes(1)
   		  }
           ACCESS read-only
           STATUS mandatory
           DESCRIPTION
                   "There is a major charger alarm."
           ::= { nrdmgeupsDataEntry 77 }

         nrdmgeupsInputSwitchQ1   OBJECT-TYPE                                     
           SYNTAX INTEGER {
   			no(0)
   			yes(1)
   		  }
           ACCESS read-only
           STATUS mandatory
           DESCRIPTION
                   "The Input Switch Q1 is closed."
           ::= { nrdmgeupsDataEntry 78 }

         nrdmgeupsEmergencyOffSwitch   OBJECT-TYPE                                
           SYNTAX INTEGER {
   			no(0)
   			yes(1)
   		  }
           ACCESS read-only
           STATUS mandatory
           DESCRIPTION
                   "The Emergency Off Switch is Closed."
           ::= { nrdmgeupsDataEntry 79 }

         nrdmgeupsChargerInputVoltageAlarm   OBJECT-TYPE                          
           SYNTAX INTEGER {
   			no(0)
   			yes(1)
   		  }
           ACCESS read-only
           STATUS mandatory
           DESCRIPTION
                   "There is a charger input voltage alarm."
           ::= { nrdmgeupsDataEntry 80 }

         nrdmgeupsChargerInputFrequencyAlarm  OBJECT-TYPE                         
           SYNTAX INTEGER {
   			no(0)
   			yes(1)
   		  }
           ACCESS read-only
           STATUS mandatory
           DESCRIPTION
                   "There is a charger input frequency alarm."
           ::= { nrdmgeupsDataEntry 81 }

         nrdmgeupsChargerGradualShutdownAlarm  OBJECT-TYPE                        
           SYNTAX INTEGER {
   			no(0)
   			yes(1)
   		  }
           ACCESS read-only
           STATUS mandatory
           DESCRIPTION
                   "There is a charger gradual shutdown alarm."
           ::= { nrdmgeupsDataEntry 82 }

         nrdmgeupsCurrentLimitingEngine  OBJECT-TYPE                              
           SYNTAX INTEGER {
   			no(0)
   			yes(1)
   		  }
           ACCESS read-only
           STATUS mandatory
           DESCRIPTION
                   "The current limiting engine is active."
           ::= { nrdmgeupsDataEntry 83 }

         nrdmgeupsCurrentLimitingBattery   OBJECT-TYPE                            
           SYNTAX INTEGER {
   			no(0)
   			yes(1)
   		  }
           ACCESS read-only
           STATUS mandatory
           DESCRIPTION
                   "The battery current limiting is active."
           ::= { nrdmgeupsDataEntry 84 }

         nrdmgeupsBatteryEqualization   OBJECT-TYPE                               
           SYNTAX INTEGER {
   			no(0)
   			yes(1)
   		  }
           ACCESS read-only
           STATUS mandatory
           DESCRIPTION
                   "The battery equalizaiton is active."
           ::= { nrdmgeupsDataEntry 85 }

         nrdmgeupsEngineGeneratorSet  OBJECT-TYPE                                 
           SYNTAX INTEGER {
   			no(0)
   			yes(1)
   		  }
           ACCESS read-only
           STATUS mandatory
           DESCRIPTION
                   "The engine generator set is active."
           ::= { nrdmgeupsDataEntry 86 }

         nrdmgeupsInverterStackOverloadAlarm   OBJECT-TYPE                        
           SYNTAX INTEGER {
   			no(0)
   			yes(1)
   		  }
           ACCESS read-only
           STATUS mandatory
           DESCRIPTION
                   "The inverter stack overload alarm is active."
           ::= { nrdmgeupsDataEntry 87 }

         nrdmgeupsMajorInverterAlarm   OBJECT-TYPE                                
           SYNTAX INTEGER {
   			no(0)
   			yes(1)
   		  }
           ACCESS read-only
           STATUS mandatory
           DESCRIPTION
                   "The major inverter alarm is active."
           ::= { nrdmgeupsDataEntry 88 }

         nrdmgeupsCurrentLimitingInverterOutput   OBJECT-TYPE                     
           SYNTAX INTEGER {
   			no(0)
   			yes(1)
   		  }
           ACCESS read-only
           STATUS mandatory
           DESCRIPTION
                   "The current limiting inverter output is active."
           ::= { nrdmgeupsDataEntry 89 }

         nrdmgeupsInverterThermalOverloadAlarm      OBJECT-TYPE                   
           SYNTAX INTEGER {
   			no(0)
   			yes(1)
   		  }
           ACCESS read-only
           STATUS mandatory
           DESCRIPTION
                   "The inverter thermal overload alarm is active."
           ::= { nrdmgeupsDataEntry 90 }

         nrdmgeupsOutsideContact                    OBJECT-TYPE                   
           SYNTAX INTEGER {
   			no(0)
   			yes(1)
   		  }
           ACCESS read-only
           STATUS mandatory
           DESCRIPTION
                   "The outside contact is closed."
           ::= { nrdmgeupsDataEntry 91 }

         nrdmgeupsEmergencyOffSwitchInverter        OBJECT-TYPE                   
           SYNTAX INTEGER {
   			no(0)
   			yes(1)
   		  }
           ACCESS read-only
           STATUS mandatory
           DESCRIPTION
                   "The inverter emergency off switch is closed."
           ::= { nrdmgeupsDataEntry 92 }

         nrdmgeupsForcedInverterShutdown             OBJECT-TYPE                   
           SYNTAX INTEGER {
   			no(0)
   			yes(1)
   		  }
           ACCESS read-only
           STATUS mandatory
           DESCRIPTION
                   "The inverter is in forced shutdown."
           ::= { nrdmgeupsDataEntry 93 }

         nrdmgeupsFrequencyConversion         OBJECT-TYPE                         
           SYNTAX INTEGER {
   			no(0)
   			yes(1)
   		  }
           ACCESS read-only
           STATUS mandatory
           DESCRIPTION
                   "The frequency conversion is active."
           ::= { nrdmgeupsDataEntry 94 }

         nrdmgeupsConditionalInverterShutdown   OBJECT-TYPE                      
           SYNTAX INTEGER {
   			no(0)
   			yes(1)
   		  }
           ACCESS read-only
           STATUS mandatory
           DESCRIPTION
                   "The conditional inverter is active."
           ::= { nrdmgeupsDataEntry 95 }

         nrdmgeupsInverterOverloadAlarm     OBJECT-TYPE                          
           SYNTAX INTEGER {
   			no(0)
   			yes(1)
   		  }
           ACCESS read-only
           STATUS mandatory
           DESCRIPTION
                   "The inverter overload alarm is active."
           ::= { nrdmgeupsDataEntry 96 }

         nrdmgeupsBatteryCabinetVentilationAlarm    OBJECT-TYPE                   
           SYNTAX INTEGER {
   			no(0)
   			yes(1)
   		  }
           ACCESS read-only
           STATUS mandatory
           DESCRIPTION
                   "The battery cabinent ventilation alarm is active."
           ::= { nrdmgeupsDataEntry 97 }

         nrdmgeupsInverterConnected                 OBJECT-TYPE                   
           SYNTAX INTEGER {
   			no(0)
   			yes(1)
   		  }
           ACCESS read-only
           STATUS mandatory
           DESCRIPTION
                   "The inverter is connected."
           ::= { nrdmgeupsDataEntry 98 }

         nrdmgeupsInverterOffDisabled               OBJECT-TYPE                   
           SYNTAX INTEGER {
   			no(0)
   			yes(1)
   		  }
           ACCESS read-only
           STATUS mandatory
           DESCRIPTION
                   "The inverter off is disabled."
           ::= { nrdmgeupsDataEntry 99 }

          nrdmgeupsSynchwithBypass                  OBJECT-TYPE                    
           SYNTAX INTEGER {
   			no(0)
   			yes(1)
   		  }
           ACCESS read-only
           STATUS mandatory
           DESCRIPTION
                   "The ups is in sync with bypass."
           ::= { nrdmgeupsDataEntry  100 }
   						      
          nrdmgeupsTransferFaultAlarm	             OBJECT-TYPE                      
           SYNTAX INTEGER {			
   			no(0)			
   			yes(1)		      
   		  }				      
           ACCESS read-only		      
           STATUS mandatory		      
           DESCRIPTION			      
                   "The transfer fault alarm is active."
           ::= { nrdmgeupsDataEntry  101}
   						      
          nrdmgeupsBypassVoltageAlarm	             OBJECT-TYPE                      
           SYNTAX INTEGER {			
   			no(0)			
   			yes(1)		      
   		  }				      
           ACCESS read-only		      
           STATUS mandatory		      
           DESCRIPTION			      
                   "The bypass voltage alarm is active."
           ::= { nrdmgeupsDataEntry  102}
   						      
          nrdmgeupsEmergencyOffSwitchBypass         OBJECT-TYPE                    
           SYNTAX INTEGER {			
   			no(0)			
   			yes(1)		      
   		  }				      
           ACCESS read-only		      
           STATUS mandatory		      
           DESCRIPTION			      
                   "The bypass emergency off switch is closed."
           ::= { nrdmgeupsDataEntry  103}
   						      
          nrdmgeupsK2SContactor      	             OBJECT-TYPE                      
           SYNTAX INTEGER {			
   			no(0)			
   			yes(1)		      
   		  }				      
           ACCESS read-only		      
           STATUS mandatory		      
           DESCRIPTION			      
                   "The K2S contactor is closed."
           ::= { nrdmgeupsDataEntry  104}
   						      
          nrdmgeupsBypassInputSwitch 	             OBJECT-TYPE                      
           SYNTAX INTEGER {			
   			no(0)			
   			yes(1)		      
   		  }				      
           ACCESS read-only		      
           STATUS mandatory		      
           DESCRIPTION			      
                   "The bypass input switch is closed."
           ::= { nrdmgeupsDataEntry  105}
   						      
          nrdmgeupsMaintenanceBypassSwitch          OBJECT-TYPE                    
            SYNTAX INTEGER {			
   				no(0)		
   				yes(1)	      
   			  }			      
            ACCESS read-only		      
            STATUS mandatory		      
            DESCRIPTION			      
                    "The maintenance bypass switch is closed."
            ::= { nrdmgeupsDataEntry 106 }
   						      
          nrdmgeupsInverterOutputSwitch             OBJECT-TYPE                    
            SYNTAX INTEGER {			
   				no(0)		
   				yes(1)	      
   			  }			      
            ACCESS read-only		      
            STATUS mandatory		      
            DESCRIPTION			      
                    "The inverter output switch is closed."
            ::= { nrdmgeupsDataEntry 107 }
   						      
          nrdmgeupsStaticSwitch      	             OBJECT-TYPE                      
            SYNTAX INTEGER {			
   				no(0)		
   				yes(1)	      
   			  }			      
            ACCESS read-only		      
            STATUS mandatory		      
            DESCRIPTION			      
                    "The static switch is closed."
            ::= { nrdmgeupsDataEntry 108 }
   						      
          nrdmgeupsBypassFrequencyAlarm             OBJECT-TYPE                    
           SYNTAX INTEGER {			
   			no(0)			
   			yes(1)		      
   		  }				      
           ACCESS read-only		      
           STATUS mandatory		      
           DESCRIPTION			      
                   "The bypass frequency alarm is active."
           ::= { nrdmgeupsDataEntry  109}
   						      
          nrdmgeupsBypassPhaseVoltageAlarm          OBJECT-TYPE                    
            SYNTAX INTEGER {			
   				no(0)		
   				yes(1)	      
   			  }			      
            ACCESS read-only		      
            STATUS mandatory		      
            DESCRIPTION			      
                    "The bypass voltage alarm is active."
            ::= { nrdmgeupsDataEntry 110 }
   						      
          nrdmgeupsDesynchwithBypass 	             OBJECT-TYPE                      
            SYNTAX INTEGER {			
   				no(0)		
   				yes(1)	      
   			  }			      
            ACCESS read-only		      
            STATUS mandatory		      
            DESCRIPTION			      
                    "The ups is desynch with bypass."
            ::= { nrdmgeupsDataEntry 111 }
   						      
          nrdmgeupsStaticBypassOverloadAlarm        OBJECT-TYPE                    
            SYNTAX INTEGER {			
   				no(0)		
   				yes(1)	      
   			  }			      
            ACCESS read-only		      
            STATUS mandatory		      
            DESCRIPTION			      
                    "The statice bypass overload alarm is active."
            ::= { nrdmgeupsDataEntry 112 }
   						      
          nrdmgeupsStaticBypassThermalOverloadAlarm  OBJECT-TYPE                   
           SYNTAX INTEGER {			
   			no(0)			
   			yes(1)		      
   		  }				      
           ACCESS read-only		      
           STATUS mandatory		      
           DESCRIPTION			      
                   "The static bypass thermal overload alarm is active."
           ::= { nrdmgeupsDataEntry  113}
   						      
          nrdmgeupsInverterThermalOverloadAlarm2     OBJECT-TYPE                   
            SYNTAX INTEGER {			
   				no(0)		
   				yes(1)	      
   			  }			      
            ACCESS read-only		      
            STATUS mandatory		      
            DESCRIPTION			      
                    "The second inverter thermal overload alarm is active."
            ::= { nrdmgeupsDataEntry 114 }
   						      
          nrdmgeupsAuxiliaryCubicleAlarm             OBJECT-TYPE                   
            SYNTAX INTEGER {			
   				no(0)		
   				yes(1)	      
   			  }			      
            ACCESS read-only		      
            STATUS mandatory		      
            DESCRIPTION			      
                    "The auxiliary cubicle alarm is active."
            ::= { nrdmgeupsDataEntry 115 }
   						      
          nrdmgeupsInhibitTransfertoBypass           OBJECT-TYPE                   
            SYNTAX INTEGER {			
   				no(0)		
   				yes(1)	      
   			  }			      
            ACCESS read-only		      
            STATUS mandatory		      
            DESCRIPTION			      
                    "The inhibit transfer to bypass is active."
            ::= { nrdmgeupsDataEntry 116 }
   						      
          nrdmgeupsTransferLockout   	              OBJECT-TYPE                     
           SYNTAX INTEGER {			
   			no(0)			
   			yes(1)		      
   		  }				      
           ACCESS read-only		      
           STATUS mandatory		      
           DESCRIPTION			      
                   "The transfer lockout is active."
           ::= { nrdmgeupsDataEntry  117}
   						      
          nrdmgeupsSufficientInverters               OBJECT-TYPE                   
            SYNTAX INTEGER {			
   				no(0)		
   				yes(1)	      
   			  }			      
            ACCESS read-only		      
            STATUS mandatory		      
            DESCRIPTION			      
                    "The ups has sufficient inverters."
            ::= { nrdmgeupsDataEntry 118 }
   						      
          nrdmgeupsAcquisitionAlarm  	              OBJECT-TYPE                     
            SYNTAX INTEGER {			
   				no(0)		
   				yes(1)	      
   			  }			      
            ACCESS read-only		      
            STATUS mandatory		      
            DESCRIPTION			      
                    "The acquisition alarm is active."
            ::= { nrdmgeupsDataEntry 119 }
   						      
          nrdmgeupsBatteryBackupTimeAlarm            OBJECT-TYPE                   
            SYNTAX INTEGER {			
   				no(0)		
   				yes(1)	      
   			  }			      
            ACCESS read-only		      
            STATUS mandatory		      
            DESCRIPTION			      
                    "The battery backup time alarm is active."
            ::= { nrdmgeupsDataEntry 120 }
   						      
          nrdmgeupsBatteryEndofLifeAlarm             OBJECT-TYPE                   
           SYNTAX INTEGER {			
   			no(0)			
   			yes(1)		      
   		  }				      
           ACCESS read-only		      
           STATUS mandatory		      
           DESCRIPTION			      
                   "The battery end of life alarm is active."
           ::= { nrdmgeupsDataEntry  121}
   						      
          nrdmgeupsSystemNormal      	               OBJECT-TYPE                   
            SYNTAX INTEGER {			
   				no(0)		
   				yes(1)	      
   			  }			      
            ACCESS read-only		      
            STATUS mandatory		      
            DESCRIPTION			      
                    "The system is operating normally."
            ::= { nrdmgeupsDataEntry 122 }
   						      
          nrdmgeupsUPSMinorAlarm     	                OBJECT-TYPE                   
            SYNTAX INTEGER {			
   				no(0)		
   				yes(1)	      
   			  }			      
            ACCESS read-only		      
            STATUS mandatory		      
            DESCRIPTION			      
                    "There is a minor alarm."
            ::= { nrdmgeupsDataEntry 123 }
   						      
          nrdmgeupsUPSMajorAlarm     	                OBJECT-TYPE                   
            SYNTAX INTEGER {			
   				no(0)		
   				yes(1)	      
   			  }			      
            ACCESS read-only		      
            STATUS mandatory		      
            DESCRIPTION			      
                    "There is a major alarm."
            ::= { nrdmgeupsDataEntry 124 }
   						      
          nrdmgeupsOnBattery         	                OBJECT-TYPE                   
           SYNTAX INTEGER {			
   			no(0)			
   			yes(1)		      
   		  }				      
           ACCESS read-only		      
           STATUS mandatory		      
           DESCRIPTION			      
                   "The ups is on battery."
           ::= { nrdmgeupsDataEntry  125}
   						      
          nrdmgeupsStaticSwitchorK2SStatus          	 OBJECT-TYPE                   
            SYNTAX INTEGER {			
   				no(0)		
   				yes(1)	      
   			  }			      
            ACCESS read-only		      
            STATUS mandatory		      
            DESCRIPTION			      
                    "The static switch or K2S is closed."
            ::= { nrdmgeupsDataEntry 126 }
   						      
          nrdmgeupsCubicleVentilationAlarm           OBJECT-TYPE                   
            SYNTAX INTEGER {			
   				no(0)		
   				yes(1)	      
   			  }			      
            ACCESS read-only		      
            STATUS mandatory		      
            DESCRIPTION			      
                    "The cubicle ventilation alarm is active."
            ::= { nrdmgeupsDataEntry 127 }
   						      
          nrdmgeupsCommunicationErrorAlarm           OBJECT-TYPE                   
            SYNTAX INTEGER {			
   				no(0)		
   				yes(1)	      
   			  }			      
            ACCESS read-only		      
            STATUS mandatory		      
            DESCRIPTION			      
                    "The communication error alarm is active."
            ::= { nrdmgeupsDataEntry 128 }
   						      
          nrdmgeupsInConfigurationMode               OBJECT-TYPE                   
           SYNTAX INTEGER {			
   			no(0)			
   			yes(1)		      
   		  }				      
           ACCESS read-only		      
           STATUS mandatory		      
           DESCRIPTION			      
                   "The ups is in configuration mode."
           ::= { nrdmgeupsDataEntry  129}
   						      
          nrdmgeupsRemoteSettingAlarm	                OBJECT-TYPE                   
            SYNTAX INTEGER {			
   				no(0)		
   				yes(1)	      
   			  }			      
            ACCESS read-only		      
            STATUS mandatory		      
            DESCRIPTION			      
                    "The remote setting alarm is active."
            ::= { nrdmgeupsDataEntry 130 }
   						      
          nrdmgeupsInvalidMeasurementsAlarm          OBJECT-TYPE                   
            SYNTAX INTEGER {			
   				no(0)		
   				yes(1)	      
   			  }			      
            ACCESS read-only		      
            STATUS mandatory		      
            DESCRIPTION			      
                    "The invalid measurement alarm is active."
            ::= { nrdmgeupsDataEntry 131 }
   						      
          nrdmgeupsChangeinStatusAlarm               OBJECT-TYPE                   
            SYNTAX INTEGER {			
   				no(0)		
   				yes(1)	      
   			  }			      
            ACCESS read-only		      
            STATUS mandatory		      
            DESCRIPTION			      
                    "The change in status alarm is active."
            ::= { nrdmgeupsDataEntry 132 }
   						      
          nrdmgeupsInvalidPhoneMainSiteAlarm         OBJECT-TYPE                   
           SYNTAX INTEGER {			
   			no(0)			
   			yes(1)		      
   		  }				      
           ACCESS read-only		      
           STATUS mandatory		      
           DESCRIPTION			      
                   "The invalid phone main site alarm is active."
           ::= { nrdmgeupsDataEntry  133}
   						      
          nrdmgeupsInvalidPhoneSecondarySiteAlarm    OBJECT-TYPE                   
            SYNTAX INTEGER {			
   				no(0)		
   				yes(1)	      
   			  }			      
            ACCESS read-only		      
            STATUS mandatory		      
            DESCRIPTION			      
                    "The invalid phone secondary site alarm is active."
            ::= { nrdmgeupsDataEntry 134 }
   						      
          nrdmgeupsCallReset         	                OBJECT-TYPE                   
            SYNTAX INTEGER {			
   				no(0)		
   				yes(1)	      
   			  }			      
            ACCESS read-only		      
            STATUS mandatory		      
            DESCRIPTION			      
                    "The call reset is active."
            ::= { nrdmgeupsDataEntry 135 }
   						      
          nrdmgeupsReturnCall        	                OBJECT-TYPE                   
            SYNTAX INTEGER {			
   				no(0)		
   				yes(1)	      
   			  }			      
            ACCESS read-only		      
            STATUS mandatory		      
            DESCRIPTION			      
                    "The return call is active."
            ::= { nrdmgeupsDataEntry 136 }
   						      
          nrdmgeupsStatusChangeReset 	                OBJECT-TYPE                   
           SYNTAX INTEGER {			
   			no(0)			
   			yes(1)		      
   		  }				      
           ACCESS read-only		      
           STATUS mandatory		      
           DESCRIPTION			      
                   "The status change reset is active."
           ::= { nrdmgeupsDataEntry  137}
   						      
          nrdmgeupsBatteryInstalled  	                OBJECT-TYPE                   
            SYNTAX INTEGER {			
   				no(0)		
   				yes(1)	      
   			  }			      
            ACCESS read-only		      
            STATUS mandatory		      
            DESCRIPTION			      
                    "The battery is installed."
            ::= { nrdmgeupsDataEntry 138 }
   						      
          nrdmgeupsBatterySensorInstalled           	 OBJECT-TYPE                   
            SYNTAX INTEGER {			
   				no(0)		
   				yes(1)	      
   			  }			      
            ACCESS read-only		      
            STATUS mandatory		      
            DESCRIPTION			      
                    "The battery sensor is installed."
            ::= { nrdmgeupsDataEntry 139 }


	END
