SNMPSERVER-MIB DEFINITIONS ::= BEGIN


IMPORTS
MODULE-IDENTITY, OBJECT-TYPE, NOTIFICATION-TYPE, TimeTicks, Counter32, Counter64, Unsigned32, dod, mib-2
FROM SNMPv2-SMI
DisplayString
FROM SNMPv2-TC;

internet OBJECT IDENTIFIER  ::= { dod 1 }

mgmt OBJECT IDENTIFIER  ::= { internet 2 }

mib-2 OBJECT IDENTIFIER  ::= { mgmt 1 }

system OBJECT IDENTIFIER  ::= { mib-2 1 }

	sysDescr OBJECT-TYPE
	SYNTAX DisplayString
	MAX-ACCESS read-only
	STATUS current
	DESCRIPTION ""
	::= { system 1 }

	sysObjectID OBJECT-TYPE
	SYNTAX OBJECT IDENTIFIER
	MAX-ACCESS read-only
	STATUS current
	DESCRIPTION ""
	::= { system 2 }

	sysUpTime OBJECT-TYPE
	SYNTAX TimeTicks
	MAX-ACCESS read-only
	STATUS current
	DESCRIPTION ""
	::= { system 3 }

	sysContact OBJECT-TYPE
	SYNTAX DisplayString
	MAX-ACCESS read-write
	STATUS current
	DESCRIPTION ""
	::= { system 4 }

	sysName OBJECT-TYPE
	SYNTAX DisplayString
	MAX-ACCESS read-write
	STATUS current
	DESCRIPTION ""
	::= { system 5 }

	sysLocation OBJECT-TYPE
	SYNTAX DisplayString
	MAX-ACCESS read-write
	STATUS current
	DESCRIPTION ""
	::= { system 6 }

private OBJECT IDENTIFIER  ::= { internet 4 }

enterprises OBJECT IDENTIFIER  ::= { private 1 }

fieldServertechnologies OBJECT-TYPE
    SYNTAX 32Bit_Reg
MAX-ACCESS read-only
STATUS current
DESCRIPTION ""
::= { enterprises 6347 }

	node1 OBJECT IDENTIFIER  ::= { fieldServertechnologies 1 }

		traps1 OBJECT IDENTIFIER  ::= { node1 0 }

			retHumProbAlTrap_1  NOTIFICATION-TYPE
			OBJECTS
			{
			retHumProbAl_1
			}
			STATUS   current
			DESCRIPTION "Broken return humidity probe alarm"
			::= { traps1 1 }

			retTempProbAlTrap_1  NOTIFICATION-TYPE
			OBJECTS
			{
			retTempProbAl_1
			}
			STATUS   current
			DESCRIPTION "Broken return temperature probe alarm"
			::= { traps1 2 }

			airPrSensorALTrap_1  NOTIFICATION-TYPE
			OBJECTS
			{
			airPrSensorAL_1
			}
			STATUS   current
			DESCRIPTION "Broken differential air pressure sensor alarm"
			::= { traps1 3 }

			supTempProbAlTrap_1  NOTIFICATION-TYPE
			OBJECTS
			{
			supTempProbAl_1
			}
			STATUS   current
			DESCRIPTION "Broken supply temperature probe alarm"
			::= { traps1 4 }

			watIN1ProbAlTrap_1  NOTIFICATION-TYPE
			OBJECTS
			{
			watIN1ProbAl_1
			}
			STATUS   current
			DESCRIPTION "Broken water IN 1 / Free cooling temperature probe alarmarm"
			::= { traps1 5 }

			watOUT1ProbAlTrap_1  NOTIFICATION-TYPE
			OBJECTS
			{
			watOUT1ProbAl_1
			}
			STATUS   current
			DESCRIPTION "Broken water OUT 1 temperature probe alarm"
			::= { traps1 6 }

			watFlw1ProbAlTrap_1  NOTIFICATION-TYPE
			OBJECTS
			{
			watFlw1ProbAl_1
			}
			STATUS   current
			DESCRIPTION "Broken water flow rate sensor 1 / Liquid temperature probe 1 alarm"
			::= { traps1 7 }

			supHumProbAlTrap_1  NOTIFICATION-TYPE
			OBJECTS
			{
			supHumProbAl_1
			}
			STATUS   current
			DESCRIPTION "Broken supply humidity probe alarm"
			::= { traps1 8 }

			watFlw2ProbAlTrap_1  NOTIFICATION-TYPE
			OBJECTS
			{
			watFlw2ProbAl_1
			}
			STATUS   current
			DESCRIPTION "Broken water flow rate sensor 2 / Liquid temperature probe 2 alarm"
			::= { traps1 9 }

			watPresAlTrap_1  NOTIFICATION-TYPE
			OBJECTS
			{
			watPresAl_1
			}
			STATUS   current
			DESCRIPTION "Water presence / Condensate drain pump alarm"
			::= { traps1 10 }

			elHeatAlTrap_1  NOTIFICATION-TYPE
			OBJECTS
			{
			elHeatAl_1
			}
			STATUS   current
			DESCRIPTION "Electric heater safety thermostat alarm"
			::= { traps1 11 }

			damperAlTrap_1  NOTIFICATION-TYPE
			OBJECTS
			{
			damperAl_1
			}
			STATUS   current
			DESCRIPTION "Damper status alarm"
			::= { traps1 12 }

			filterAlTrap_1  NOTIFICATION-TYPE
			OBJECTS
			{
			filterAl_1
			}
			STATUS   current
			DESCRIPTION "Clogged air filter alarm"
			::= { traps1 13 }

			c1ThermAlTrap_1  NOTIFICATION-TYPE
			OBJECTS
			{
			c1ThermAl_1
			}
			STATUS   current
			DESCRIPTION "Compressor 1 thermal protection alarm"
			::= { traps1 14 }

			c2ThermAlTrap_1  NOTIFICATION-TYPE
			OBJECTS
			{
			c2ThermAl_1
			}
			STATUS   current
			DESCRIPTION "Compressor 2 thermal protection alarm"
			::= { traps1 15 }

			c1HighPresAlTrap_1  NOTIFICATION-TYPE
			OBJECTS
			{
			c1HighPresAl_1
			}
			STATUS   current
			DESCRIPTION "Compressor 1 high pressure alarm"
			::= { traps1 16 }

			c2HighPresAlTrap_1  NOTIFICATION-TYPE
			OBJECTS
			{
			c2HighPresAl_1
			}
			STATUS   current
			DESCRIPTION "Compressor 2 high pressure alarm"
			::= { traps1 17 }

			c1LowPresAlTrap_1  NOTIFICATION-TYPE
			OBJECTS
			{
			c1LowPresAl_1
			}
			STATUS   current
			DESCRIPTION "Compressor 1 low pressure alarm"
			::= { traps1 18 }

			c2LowPresAlTrap_1  NOTIFICATION-TYPE
			OBJECTS
			{
			c2LowPresAl_1
			}
			STATUS   current
			DESCRIPTION "Compressor 2 low pressure alarm"
			::= { traps1 19 }

			c1HighDischAlTrap_1  NOTIFICATION-TYPE
			OBJECTS
			{
			c1HighDischAl_1
			}
			STATUS   current
			DESCRIPTION "Compressor 1 high discharge temperature alarm"
			::= { traps1 20 }

			c2HighDischAlTrap_1  NOTIFICATION-TYPE
			OBJECTS
			{
			c2HighDischAl_1
			}
			STATUS   current
			DESCRIPTION "Compressor 2 high discharge temperature alarm"
			::= { traps1 21 }

			eEV1AlTrap_1  NOTIFICATION-TYPE
			OBJECTS
			{
			eEV1Al_1
			}
			STATUS   current
			DESCRIPTION "EEV 1 alarm"
			::= { traps1 22 }

			eEV2AlTrap_1  NOTIFICATION-TYPE
			OBJECTS
			{
			eEV2Al_1
			}
			STATUS   current
			DESCRIPTION "EEV 2 alarm"
			::= { traps1 23 }

			inverterCompAlTrap_1  NOTIFICATION-TYPE
			OBJECTS
			{
			inverterCompAl_1
			}
			STATUS   current
			DESCRIPTION "DC compressor inverter alarm"
			::= { traps1 24 }

			fan1InverterAlTrap_1  NOTIFICATION-TYPE
			OBJECTS
			{
			fan1InverterAl_1
			}
			STATUS   current
			DESCRIPTION "Fan 1 inverter alarm"
			::= { traps1 25 }

			fan2InverterAlTrap_1  NOTIFICATION-TYPE
			OBJECTS
			{
			fan2InverterAl_1
			}
			STATUS   current
			DESCRIPTION "Fan 2 inverter alarm"
			::= { traps1 26 }

			fan3InverterAlTrap_1  NOTIFICATION-TYPE
			OBJECTS
			{
			fan3InverterAl_1
			}
			STATUS   current
			DESCRIPTION "Fan 3 inverter alarm"
			::= { traps1 27 }

			fan4InverterAlTrap_1  NOTIFICATION-TYPE
			OBJECTS
			{
			fan4InverterAl_1
			}
			STATUS   current
			DESCRIPTION "Fan 4 inverter alarm"
			::= { traps1 28 }

			fan5InverterAlTrap_1  NOTIFICATION-TYPE
			OBJECTS
			{
			fan5InverterAl_1
			}
			STATUS   current
			DESCRIPTION "Fan 5 inverter alarm"
			::= { traps1 29 }

			internalHumidifAlTrap_1  NOTIFICATION-TYPE
			OBJECTS
			{
			internalHumidifAl_1
			}
			STATUS   current
			DESCRIPTION "Internal humidifier alarm"
			::= { traps1 30 }

			localNetworkAlTrap_1  NOTIFICATION-TYPE
			OBJECTS
			{
			localNetworkAl_1
			}
			STATUS   current
			DESCRIPTION "Local network communication alarm"
			::= { traps1 31 }

			regHighTempAlTrap_1  NOTIFICATION-TYPE
			OBJECTS
			{
			regHighTempAl_1
			}
			STATUS   current
			DESCRIPTION "High regulation temperature alarm"
			::= { traps1 32 }

			regLowTempAlTrap_1  NOTIFICATION-TYPE
			OBJECTS
			{
			regLowTempAl_1
			}
			STATUS   current
			DESCRIPTION "Low regulation temperature alarm"
			::= { traps1 33 }

			retHighHumiAlTrap_1  NOTIFICATION-TYPE
			OBJECTS
			{
			retHighHumiAl_1
			}
			STATUS   current
			DESCRIPTION "High return humidity alarm"
			::= { traps1 34 }

			retLowHumiAlTrap_1  NOTIFICATION-TYPE
			OBJECTS
			{
			retLowHumiAl_1
			}
			STATUS   current
			DESCRIPTION "Low return humidity alarm"
			::= { traps1 35 }

			supHighHumiAlTrap_1  NOTIFICATION-TYPE
			OBJECTS
			{
			supHighHumiAl_1
			}
			STATUS   current
			DESCRIPTION "High supply humidity alarm"
			::= { traps1 36 }

			supLowHumiAlTrap_1  NOTIFICATION-TYPE
			OBJECTS
			{
			supLowHumiAl_1
			}
			STATUS   current
			DESCRIPTION "Low supply humidity alarm"
			::= { traps1 37 }

			highLimTempAlTrap_1  NOTIFICATION-TYPE
			OBJECTS
			{
			highLimTempAl_1
			}
			STATUS   current
			DESCRIPTION "High limit temperature alarm"
			::= { traps1 38 }

			lowLimTempAlTrap_1  NOTIFICATION-TYPE
			OBJECTS
			{
			lowLimTempAl_1
			}
			STATUS   current
			DESCRIPTION "Low limit temperature alarm"
			::= { traps1 39 }

			dryCoolerAlTrap_1  NOTIFICATION-TYPE
			OBJECTS
			{
			dryCoolerAl_1
			}
			STATUS   current
			DESCRIPTION "Dry cooler general alarm"
			::= { traps1 40 }

			externalHumidifAlTrap_1  NOTIFICATION-TYPE
			OBJECTS
			{
			externalHumidifAl_1
			}
			STATUS   current
			DESCRIPTION "External humidifier general alarm"
			::= { traps1 41 }

			waterPumpAlTrap_1  NOTIFICATION-TYPE
			OBJECTS
			{
			waterPumpAl_1
			}
			STATUS   current
			DESCRIPTION "General water pump alarm"
			::= { traps1 42 }

			condenser1AlTrap_1  NOTIFICATION-TYPE
			OBJECTS
			{
			condenser1Al_1
			}
			STATUS   current
			DESCRIPTION "Condenser 1 general alarm"
			::= { traps1 43 }

			condenser2AlTrap_1  NOTIFICATION-TYPE
			OBJECTS
			{
			condenser2Al_1
			}
			STATUS   current
			DESCRIPTION "Condenser 2 general alarm"
			::= { traps1 44 }

			gasLeakAlTrap_1  NOTIFICATION-TYPE
			OBJECTS
			{
			gasLeakAl_1
			}
			STATUS   current
			DESCRIPTION "Refrigerant gas leak detector alarm"
			::= { traps1 45 }

			fansGenAlTrap_1  NOTIFICATION-TYPE
			OBJECTS
			{
			fansGenAl_1
			}
			STATUS   current
			DESCRIPTION "General supply fans alarm"
			::= { traps1 46 }

			fireSmokeAlTrap_1  NOTIFICATION-TYPE
			OBJECTS
			{
			fireSmokeAl_1
			}
			STATUS   current
			DESCRIPTION "Fire/Smoke presence alarm"
			::= { traps1 47 }

			genericSoftAlTrap_1  NOTIFICATION-TYPE
			OBJECTS
			{
			genericSoftAl_1
			}
			STATUS   current
			DESCRIPTION "Non-critical generic alarm"
			::= { traps1 48 }

			genericSeriousAlTrap_1  NOTIFICATION-TYPE
			OBJECTS
			{
			genericSeriousAl_1
			}
			STATUS   current
			DESCRIPTION "Critical generic alarm"
			::= { traps1 49 }

			condUnitGeneralAlTrap_1  NOTIFICATION-TYPE
			OBJECTS
			{
			condUnitGeneralAl_1
			}
			STATUS   current
			DESCRIPTION "Condensing unit general alarm"
			::= { traps1 50 }

			powerSupplyAlTrap_1  NOTIFICATION-TYPE
			OBJECTS
			{
			powerSupplyAl_1
			}
			STATUS   current
			DESCRIPTION "Power supply failure alarm"
			::= { traps1 51 }

			c1LowComprRatioAlTrap_1  NOTIFICATION-TYPE
			OBJECTS
			{
			c1LowComprRatioAl_1
			}
			STATUS   current
			DESCRIPTION "Compressor 1 low compression ratio alarm"
			::= { traps1 52 }

			c2LowComprRatioAlTrap_1  NOTIFICATION-TYPE
			OBJECTS
			{
			c2LowComprRatioAl_1
			}
			STATUS   current
			DESCRIPTION "Compressor 2 low compression ratio alarm"
			::= { traps1 53 }

			watIN2ProbAlTrap_1  NOTIFICATION-TYPE
			OBJECTS
			{
			watIN2ProbAl_1
			}
			STATUS   current
			DESCRIPTION "Broken water IN 2 temperature probe alarm"
			::= { traps1 54 }

			watOUT2ProbAlTrap_1  NOTIFICATION-TYPE
			OBJECTS
			{
			watOUT2ProbAl_1
			}
			STATUS   current
			DESCRIPTION "Broken water OUT 2 temperature probe alarm"
			::= { traps1 55 }

			dirtyFiltPresSensAlTrap_1  NOTIFICATION-TYPE
			OBJECTS
			{
			dirtyFiltPresSensAl_1
			}
			STATUS   current
			DESCRIPTION "Dirty filter pressure sensor alarm"
			::= { traps1 56 }

			eEV1CommAlTrap_1  NOTIFICATION-TYPE
			OBJECTS
			{
			eEV1CommAl_1
			}
			STATUS   current
			DESCRIPTION "EEV 1 communication alarm"
			::= { traps1 57 }

			eEV1SuctProbAlTrap_1  NOTIFICATION-TYPE
			OBJECTS
			{
			eEV1SuctProbAl_1
			}
			STATUS   current
			DESCRIPTION "EEV 1 Suction temperature probe alarm"
			::= { traps1 58 }

			eEV1EvapProbAlTrap_1  NOTIFICATION-TYPE
			OBJECTS
			{
			eEV1EvapProbAl_1
			}
			STATUS   current
			DESCRIPTION "EEV 1 Evaporation pressure probe alarm"
			::= { traps1 59 }

			eEV1CondProbAlTrap_1  NOTIFICATION-TYPE
			OBJECTS
			{
			eEV1CondProbAl_1
			}
			STATUS   current
			DESCRIPTION "EEV 1 Condensation pressure probe alarm"
			::= { traps1 60 }

			eEV1DischProbAlTrap_1  NOTIFICATION-TYPE
			OBJECTS
			{
			eEV1DischProbAl_1
			}
			STATUS   current
			DESCRIPTION "EEV 1 Discharge temperature probe alarm"
			::= { traps1 61 }

			eEV2CommAlTrap_1  NOTIFICATION-TYPE
			OBJECTS
			{
			eEV2CommAl_1
			}
			STATUS   current
			DESCRIPTION "EEV 2 Communication down alarm"
			::= { traps1 62 }

			eEV2SuctProbAlTrap_1  NOTIFICATION-TYPE
			OBJECTS
			{
			eEV2SuctProbAl_1
			}
			STATUS   current
			DESCRIPTION "EEV 2 Suction temperature probe alarm"
			::= { traps1 63 }

			eEV2EvapProbAlTrap_1  NOTIFICATION-TYPE
			OBJECTS
			{
			eEV2EvapProbAl_1
			}
			STATUS   current
			DESCRIPTION "EEV 2 Evaporation pressure probe alarm"
			::= { traps1 64 }

			eEV2CondProbAlTrap_1  NOTIFICATION-TYPE
			OBJECTS
			{
			eEV2CondProbAl_1
			}
			STATUS   current
			DESCRIPTION "EEV 2 Condensation pressure probe alarm"
			::= { traps1 65 }

			eEV2DischProbAlTrap_1  NOTIFICATION-TYPE
			OBJECTS
			{
			eEV2DischProbAl_1
			}
			STATUS   current
			DESCRIPTION "EEV 2 Discharge temperature probe alarm"
			::= { traps1 66 }

			cPYCommAlTrap_1  NOTIFICATION-TYPE
			OBJECTS
			{
			cPYCommAl_1
			}
			STATUS   current
			DESCRIPTION "CPY communication alarm"
			::= { traps1 67 }

			cPYMemoryAlTrap_1  NOTIFICATION-TYPE
			OBJECTS
			{
			cPYMemoryAl_1
			}
			STATUS   current
			DESCRIPTION "CPY Internal memory error"
			::= { traps1 68 }

			cPYParameterAlTrap_1  NOTIFICATION-TYPE
			OBJECTS
			{
			cPYParameterAl_1
			}
			STATUS   current
			DESCRIPTION "CPY Parameter error"
			::= { traps1 69 }

			cPYHighCurrentAlTrap_1  NOTIFICATION-TYPE
			OBJECTS
			{
			cPYHighCurrentAl_1
			}
			STATUS   current
			DESCRIPTION "CPY Electrode high current"
			::= { traps1 70 }

			cPYLowSteamAlTrap_1  NOTIFICATION-TYPE
			OBJECTS
			{
			cPYLowSteamAl_1
			}
			STATUS   current
			DESCRIPTION "CPY Low steam production"
			::= { traps1 71 }

			cPYDrainAlTrap_1  NOTIFICATION-TYPE
			OBJECTS
			{
			cPYDrainAl_1
			}
			STATUS   current
			DESCRIPTION "CPY No drain"
			::= { traps1 72 }

			cPYMaintAlTrap_1  NOTIFICATION-TYPE
			OBJECTS
			{
			cPYMaintAl_1
			}
			STATUS   current
			DESCRIPTION "CPY Maintenance time expired"
			::= { traps1 73 }

			cPYNoWaterAlTrap_1  NOTIFICATION-TYPE
			OBJECTS
			{
			cPYNoWaterAl_1
			}
			STATUS   current
			DESCRIPTION "CPY No water"
			::= { traps1 74 }

			cPYCylMaintAlTrap_1  NOTIFICATION-TYPE
			OBJECTS
			{
			cPYCylMaintAl_1
			}
			STATUS   current
			DESCRIPTION "CPY Cylinder maintenance"
			::= { traps1 75 }

			cPYDirtyCylAlTrap_1  NOTIFICATION-TYPE
			OBJECTS
			{
			cPYDirtyCylAl_1
			}
			STATUS   current
			DESCRIPTION "CPY Dirty cylinder"
			::= { traps1 76 }

			cPYFoamAlTrap_1  NOTIFICATION-TYPE
			OBJECTS
			{
			cPYFoamAl_1
			}
			STATUS   current
			DESCRIPTION "CPY Foam presence"
			::= { traps1 77 }

			cPYLifeTimeAlTrap_1  NOTIFICATION-TYPE
			OBJECTS
			{
			cPYLifeTimeAl_1
			}
			STATUS   current
			DESCRIPTION "CPY Life time expired"
			::= { traps1 78 }

			cPYHighWatLevAlTrap_1  NOTIFICATION-TYPE
			OBJECTS
			{
			cPYHighWatLevAl_1
			}
			STATUS   current
			DESCRIPTION "CPY High water level"
			::= { traps1 79 }

			cPYHighWatConductAlTrap_1  NOTIFICATION-TYPE
			OBJECTS
			{
			cPYHighWatConductAl_1
			}
			STATUS   current
			DESCRIPTION "CPY High water conductivity"
			::= { traps1 80 }

			cPYConnectionAlTrap_1  NOTIFICATION-TYPE
			OBJECTS
			{
			cPYConnectionAl_1
			}
			STATUS   current
			DESCRIPTION "CPY Connection error"
			::= { traps1 81 }

			fan1PowerAlTrap_1  NOTIFICATION-TYPE
			OBJECTS
			{
			fan1PowerAl_1
			}
			STATUS   current
			DESCRIPTION "Fan 1 phase/power supply down alarm"
			::= { traps1 82 }

			fan1CommAlTrap_1  NOTIFICATION-TYPE
			OBJECTS
			{
			fan1CommAl_1
			}
			STATUS   current
			DESCRIPTION "Fan 1 communication down"
			::= { traps1 83 }

			fan1HighTempAlTrap_1  NOTIFICATION-TYPE
			OBJECTS
			{
			fan1HighTempAl_1
			}
			STATUS   current
			DESCRIPTION "Fan 1 High regulation module temperature"
			::= { traps1 84 }

			fan1NetComAlTrap_1  NOTIFICATION-TYPE
			OBJECTS
			{
			fan1NetComAl_1
			}
			STATUS   current
			DESCRIPTION "Fan 1 master-slave communication failure"
			::= { traps1 85 }

			fan1InvRegAlTrap_1  NOTIFICATION-TYPE
			OBJECTS
			{
			fan1InverterAl_1
			}
			STATUS   current
			DESCRIPTION "Fan 1 regulation module malfunction"
			::= { traps1 86 }

			fan1HighMotTempAlTrap_1  NOTIFICATION-TYPE
			OBJECTS
			{
			fan1HighMotTempAl_1
			}
			STATUS   current
			DESCRIPTION "Fan 1 High motor temperature"
			::= { traps1 87 }

			fan1HallSensAlTrap_1  NOTIFICATION-TYPE
			OBJECTS
			{
			fan1HallSensAl_1
			}
			STATUS   current
			DESCRIPTION "Fan 1 Hall sensor error"
			::= { traps1 88 }

			fan1OverloadAlTrap_1  NOTIFICATION-TYPE
			OBJECTS
			{
			fan1OverloadAl_1
			}
			STATUS   current
			DESCRIPTION "Fan 1 overload motor"
			::= { traps1 89 }

			fan1LowDCAlTrap_1  NOTIFICATION-TYPE
			OBJECTS
			{
			fan1LowDCAl_1
			}
			STATUS   current
			DESCRIPTION "Fan 1 low DC power supply"
			::= { traps1 94 }

			fan2PowerAlTrap_1  NOTIFICATION-TYPE
			OBJECTS
			{
			fan2PowerAl_1
			}
			STATUS   current
			DESCRIPTION "Fan 2 phase/power supply down alarm"
			::= { traps1 95 }

			fan2CommAlTrap_1  NOTIFICATION-TYPE
			OBJECTS
			{
			fan2CommAl_1
			}
			STATUS   current
			DESCRIPTION "Fan 2 communication down"
			::= { traps1 96 }

			fan2HighTempAlTrap_1  NOTIFICATION-TYPE
			OBJECTS
			{
			fan2HighTempAl_1
			}
			STATUS   current
			DESCRIPTION "Fan 2 High regulation module temperature"
			::= { traps1 97 }

			fan2NetComAlTrap_1  NOTIFICATION-TYPE
			OBJECTS
			{
			fan2NetComAl_1
			}
			STATUS   current
			DESCRIPTION "Fan 2 master-slave communication failure"
			::= { traps1 98 }

			fan2InvRegAlTrap_1  NOTIFICATION-TYPE
			OBJECTS
			{
			fan2InverterAl_1
			}
			STATUS   current
			DESCRIPTION "Fan 2 regulation module malfunction"
			::= { traps1 99 }

			fan2HighMotTempAlTrap_1  NOTIFICATION-TYPE
			OBJECTS
			{
			fan2HighMotTempAl_1
			}
			STATUS   current
			DESCRIPTION "Fan 2 High motor temperature"
			::= { traps1 100 }

			fan2HallSensAlTrap_1  NOTIFICATION-TYPE
			OBJECTS
			{
			fan2HallSensAl_1
			}
			STATUS   current
			DESCRIPTION "Fan 2 Hall sensor error"
			::= { traps1 101 }

			fan2OverloadAlTrap_1  NOTIFICATION-TYPE
			OBJECTS
			{
			fan2OverloadAl_1
			}
			STATUS   current
			DESCRIPTION "Fan 2 overload motor"
			::= { traps1 102 }

			fan2LowDCAlTrap_1  NOTIFICATION-TYPE
			OBJECTS
			{
			fan2LowDCAl_1
			}
			STATUS   current
			DESCRIPTION "Fan 2 low DC power supply"
			::= { traps1 107 }

			fan3PowerAlTrap_1  NOTIFICATION-TYPE
			OBJECTS
			{
			fan3PowerAl_1
			}
			STATUS   current
			DESCRIPTION "Fan 3 phase/power supply down alarm"
			::= { traps1 108 }

			fan3CommAlTrap_1  NOTIFICATION-TYPE
			OBJECTS
			{
			fan3CommAl_1
			}
			STATUS   current
			DESCRIPTION "Fan 3 communication down"
			::= { traps1 109 }

			fan3HighTempAlTrap_1  NOTIFICATION-TYPE
			OBJECTS
			{
			fan3HighTempAl_1
			}
			STATUS   current
			DESCRIPTION "Fan 3 High regulation module temperature"
			::= { traps1 110 }

			fan3NetComAlTrap_1  NOTIFICATION-TYPE
			OBJECTS
			{
			fan3NetComAl_1
			}
			STATUS   current
			DESCRIPTION "Fan 3 master-slave communication failure"
			::= { traps1 111 }

			fan3InvRegAlTrap_1  NOTIFICATION-TYPE
			OBJECTS
			{
			fan3InverterAl_1
			}
			STATUS   current
			DESCRIPTION "Fan 3 regulation module malfunction"
			::= { traps1 112 }

			fan3HighMotTempAlTrap_1  NOTIFICATION-TYPE
			OBJECTS
			{
			fan3HighMotTempAl_1
			}
			STATUS   current
			DESCRIPTION "Fan 3 High motor temperature"
			::= { traps1 113 }

			fan3HallSensAlTrap_1  NOTIFICATION-TYPE
			OBJECTS
			{
			fan3HallSensAl_1
			}
			STATUS   current
			DESCRIPTION "Fan 3 Hall sensor error"
			::= { traps1 114 }

			fan3OverloadAlTrap_1  NOTIFICATION-TYPE
			OBJECTS
			{
			fan3OverloadAl_1
			}
			STATUS   current
			DESCRIPTION "Fan 3 overload motor"
			::= { traps1 115 }

			fan3LowDCAlTrap_1  NOTIFICATION-TYPE
			OBJECTS
			{
			fan3LowDCAl_1
			}
			STATUS   current
			DESCRIPTION "Fan 3 low DC power supply"
			::= { traps1 120 }

			fan4PowerAlTrap_1  NOTIFICATION-TYPE
			OBJECTS
			{
			fan4PowerAl_1
			}
			STATUS   current
			DESCRIPTION "Fan 4 phase/power supply down alarm"
			::= { traps1 121 }

			fan4CommAlTrap_1  NOTIFICATION-TYPE
			OBJECTS
			{
			fan4CommAl_1
			}
			STATUS   current
			DESCRIPTION "Fan 4 communication down"
			::= { traps1 122 }

			fan4HighTempAlTrap_1  NOTIFICATION-TYPE
			OBJECTS
			{
			fan4HighTempAl_1
			}
			STATUS   current
			DESCRIPTION "Fan 4 High regulation module temperature"
			::= { traps1 123 }

			fan4NetComAlTrap_1  NOTIFICATION-TYPE
			OBJECTS
			{
			fan4NetComAl_1
			}
			STATUS   current
			DESCRIPTION "Fan 4 master-slave communication failure"
			::= { traps1 124 }

			fan4InvRegAlTrap_1  NOTIFICATION-TYPE
			OBJECTS
			{
			fan4InverterAl_1
			}
			STATUS   current
			DESCRIPTION "Fan 4 regulation module malfunction"
			::= { traps1 125 }

			fan4HighMotTempAlTrap_1  NOTIFICATION-TYPE
			OBJECTS
			{
			fan4HighMotTempAl_1
			}
			STATUS   current
			DESCRIPTION "Fan 4 High motor temperature"
			::= { traps1 126 }

			fan4HallSensAlTrap_1  NOTIFICATION-TYPE
			OBJECTS
			{
			fan4HallSensAl_1
			}
			STATUS   current
			DESCRIPTION "Fan 4 Hall sensor error"
			::= { traps1 127 }

			fan4OverloadAlTrap_1  NOTIFICATION-TYPE
			OBJECTS
			{
			fan4OverloadAl_1
			}
			STATUS   current
			DESCRIPTION "Fan 4 overload motor"
			::= { traps1 128 }

			fan4LowDCAlTrap_1  NOTIFICATION-TYPE
			OBJECTS
			{
			fan4LowDCAl_1
			}
			STATUS   current
			DESCRIPTION "Fan 4 low DC power supply"
			::= { traps1 133 }

			fan5PowerAlTrap_1  NOTIFICATION-TYPE
			OBJECTS
			{
			fan5PowerAl_1
			}
			STATUS   current
			DESCRIPTION "Fan 5 phase/power supply down alarm"
			::= { traps1 134 }

			fan5CommAlTrap_1  NOTIFICATION-TYPE
			OBJECTS
			{
			fan5CommAl_1
			}
			STATUS   current
			DESCRIPTION "Fan 5 communication down"
			::= { traps1 135 }

			fan5HighTempAlTrap_1  NOTIFICATION-TYPE
			OBJECTS
			{
			fan5HighTempAl_1
			}
			STATUS   current
			DESCRIPTION "Fan 5 High regulation module temperature"
			::= { traps1 136 }

			fan5NetComAlTrap_1  NOTIFICATION-TYPE
			OBJECTS
			{
			fan5NetComAl_1
			}
			STATUS   current
			DESCRIPTION "Fan 5 master-slave communication failure"
			::= { traps1 137 }

			fan5InvRegAlTrap_1  NOTIFICATION-TYPE
			OBJECTS
			{
			fan5InverterAl_1
			}
			STATUS   current
			DESCRIPTION "Fan 5 regulation module malfunction"
			::= { traps1 138 }

			fan5HighMotTempAlTrap_1  NOTIFICATION-TYPE
			OBJECTS
			{
			fan5HighMotTempAl_1
			}
			STATUS   current
			DESCRIPTION "Fan 5 High motor temperature"
			::= { traps1 139 }

			fan5HallSensAlTrap_1  NOTIFICATION-TYPE
			OBJECTS
			{
			fan5HallSensAl_1
			}
			STATUS   current
			DESCRIPTION "Fan 5 Hall sensor error"
			::= { traps1 140 }

			fan5OverloadAlTrap_1  NOTIFICATION-TYPE
			OBJECTS
			{
			fan5OverloadAl_1
			}
			STATUS   current
			DESCRIPTION "Fan 5 overload motor"
			::= { traps1 141 }

			fan5LowDCAlTrap_1  NOTIFICATION-TYPE
			OBJECTS
			{
			fan5LowDCAl_1
			}
			STATUS   current
			DESCRIPTION "Fan 5 low DC power supply"
			::= { traps1 146 }

			dFPSBrokenAlTrap_1  NOTIFICATION-TYPE
			OBJECTS
			{
			dFPSBrokenAl_1
			}
			STATUS   current
			DESCRIPTION "Dirty filter pressure sensor broken alarm"
			::= { traps1 147 }

			dFPSCablingAlTrap_1  NOTIFICATION-TYPE
			OBJECTS
			{
			dFPSCablingAl_1
			}
			STATUS   current
			DESCRIPTION "Dirty filter pressure sensor cabling alarm"
			::= { traps1 148 }

			dFPSRangeAlTrap_1  NOTIFICATION-TYPE
			OBJECTS
			{
			dFPSRangeAl_1
			}
			STATUS   current
			DESCRIPTION "Dirty filter pressure sensor range alarm"
			::= { traps1 149 }

			dFPSADCAlTrap_1  NOTIFICATION-TYPE
			OBJECTS
			{
			dFPSADCAl_1
			}
			STATUS   current
			DESCRIPTION "Dirty filter pressure sensor ADC alarm"
			::= { traps1 150 }

			dFPSSettingAlTrap_1  NOTIFICATION-TYPE
			OBJECTS
			{
			dFPSSettingAl_1
			}
			STATUS   current
			DESCRIPTION "Dirty filter pressure sensor setting alarm"
			::= { traps1 151 }

			dFPSDCOAlTrap_1  NOTIFICATION-TYPE
			OBJECTS
			{
			dFPSDCOAl_1
			}
			STATUS   current
			DESCRIPTION "Dirty filter pressure sensor DCO alarm"
			::= { traps1 152 }

			dFPSWatchdogAlTrap_1  NOTIFICATION-TYPE
			OBJECTS
			{
			dFPSWatchdogAl_1
			}
			STATUS   current
			DESCRIPTION "Dirty filter pressure sensor watchdog alarm"
			::= { traps1 153 }

			dFPSCommAlTrap_1  NOTIFICATION-TYPE
			OBJECTS
			{
			dFPSCommAl_1
			}
			STATUS   current
			DESCRIPTION "Dirty filter pressure sensor communication alarm"
			::= { traps1 154 }

			invCompCommAlarmTrap_1  NOTIFICATION-TYPE
			OBJECTS
			{
			invCompCommAlarm_1
			}
			STATUS   current
			DESCRIPTION "DC compressor inverter communication alarm"
			::= { traps1 155 }

		binaryObjects1 OBJECT IDENTIFIER  ::= { node1 1 }

			damperStatusDI_1 OBJECT-TYPE
			SYNTAX INTEGER
			MAX-ACCESS read-only
			STATUS current
			DESCRIPTION "Motorized dampers status"
			::= { binaryObjects1 1 }

			dirtyFilterDI_1 OBJECT-TYPE
			SYNTAX INTEGER
			MAX-ACCESS read-only
			STATUS current
			DESCRIPTION "Dirty filter alarm"
			::= { binaryObjects1 2 }

			remoteOffDI_1 OBJECT-TYPE
			SYNTAX INTEGER
			MAX-ACCESS read-only
			STATUS current
			DESCRIPTION "Remote OFF"
			::= { binaryObjects1 3 }

			elecHeaterAlarmDI_1 OBJECT-TYPE
			SYNTAX INTEGER
			MAX-ACCESS read-only
			STATUS current
			DESCRIPTION "Electric heater safety thermostat"
			::= { binaryObjects1 4 }

			waterAlarmDI_1 OBJECT-TYPE
			SYNTAX INTEGER
			MAX-ACCESS read-only
			STATUS current
			DESCRIPTION "Flooding / Condensate drain alarm"
			::= { binaryObjects1 5 }

			configurableDI1_1 OBJECT-TYPE
			SYNTAX INTEGER
			MAX-ACCESS read-only
			STATUS current
			DESCRIPTION "Configurable input 1"
			::= { binaryObjects1 6 }

			configurableDI2_1 OBJECT-TYPE
			SYNTAX INTEGER
			MAX-ACCESS read-only
			STATUS current
			DESCRIPTION "Configurable input 2"
			::= { binaryObjects1 7 }

			configurableDI3_1 OBJECT-TYPE
			SYNTAX INTEGER
			MAX-ACCESS read-only
			STATUS current
			DESCRIPTION "Configurable input 3"
			::= { binaryObjects1 8 }

			configurableDI4_1 OBJECT-TYPE
			SYNTAX INTEGER
			MAX-ACCESS read-only
			STATUS current
			DESCRIPTION "Configurable input 4"
			::= { binaryObjects1 9 }

			comp1ThermAlarmDI_1 OBJECT-TYPE
			SYNTAX INTEGER
			MAX-ACCESS read-only
			STATUS current
			DESCRIPTION "Compressor 1 thermal alarm"
			::= { binaryObjects1 10 }

			comp1HPAlarmDI_1 OBJECT-TYPE
			SYNTAX INTEGER
			MAX-ACCESS read-only
			STATUS current
			DESCRIPTION "Compressor 1 high pressure alarm"
			::= { binaryObjects1 11 }

			comp1LPAlarmDI_1 OBJECT-TYPE
			SYNTAX INTEGER
			MAX-ACCESS read-only
			STATUS current
			DESCRIPTION "Compressor 1 low pressure alarm"
			::= { binaryObjects1 12 }

			comp2ThermAlarmDI_1 OBJECT-TYPE
			SYNTAX INTEGER
			MAX-ACCESS read-only
			STATUS current
			DESCRIPTION "Compressor 2 thermal alarm"
			::= { binaryObjects1 13 }

			comp2HPAlarmDI_1 OBJECT-TYPE
			SYNTAX INTEGER
			MAX-ACCESS read-only
			STATUS current
			DESCRIPTION "Compressor 2 high pressure alarm"
			::= { binaryObjects1 14 }

			comp2LowPresAlarmDI_1 OBJECT-TYPE
			SYNTAX INTEGER
			MAX-ACCESS read-only
			STATUS current
			DESCRIPTION "Compressor 2 low pressure alarm"
			::= { binaryObjects1 15 }

			fansDO_1 OBJECT-TYPE
			SYNTAX INTEGER
			MAX-ACCESS read-only
			STATUS current
			DESCRIPTION "Fans Control"
			::= { binaryObjects1 16 }

			damperDO_1 OBJECT-TYPE
			SYNTAX INTEGER
			MAX-ACCESS read-only
			STATUS current
			DESCRIPTION "Dampers control"
			::= { binaryObjects1 17 }

			elecHeaterStage1DO_1 OBJECT-TYPE
			SYNTAX INTEGER
			MAX-ACCESS read-only
			STATUS current
			DESCRIPTION "Electrical heater stage 1"
			::= { binaryObjects1 18 }

			elecHeaterStage2DO_1 OBJECT-TYPE
			SYNTAX INTEGER
			MAX-ACCESS read-only
			STATUS current
			DESCRIPTION "Electrical heater stage 2"
			::= { binaryObjects1 19 }

			configurableDO1_1 OBJECT-TYPE
			SYNTAX INTEGER
			MAX-ACCESS read-only
			STATUS current
			DESCRIPTION "Configurable digital output 1"
			::= { binaryObjects1 20 }

			configurableDO2_1 OBJECT-TYPE
			SYNTAX INTEGER
			MAX-ACCESS read-only
			STATUS current
			DESCRIPTION "Configurable digital output 2"
			::= { binaryObjects1 21 }

			configurableDO3_1 OBJECT-TYPE
			SYNTAX INTEGER
			MAX-ACCESS read-only
			STATUS current
			DESCRIPTION "Configurable digital output 3"
			::= { binaryObjects1 22 }

			configurableDO4_1 OBJECT-TYPE
			SYNTAX INTEGER
			MAX-ACCESS read-only
			STATUS current
			DESCRIPTION "Configurable digital output 4"
			::= { binaryObjects1 23 }

			compressor1DO_1 OBJECT-TYPE
			SYNTAX INTEGER
			MAX-ACCESS read-only
			STATUS current
			DESCRIPTION "Compressor 1 control"
			::= { binaryObjects1 24 }

			compressor2DO_1 OBJECT-TYPE
			SYNTAX INTEGER
			MAX-ACCESS read-only
			STATUS current
			DESCRIPTION "Compressor 2 control"
			::= { binaryObjects1 25 }

			humidifierPowerDO_1 OBJECT-TYPE
			SYNTAX INTEGER
			MAX-ACCESS read-only
			STATUS current
			DESCRIPTION "Humidifier control"
			::= { binaryObjects1 26 }

			humidifDrainValveDO_1 OBJECT-TYPE
			SYNTAX INTEGER
			MAX-ACCESS read-only
			STATUS current
			DESCRIPTION "Drain valve"
			::= { binaryObjects1 27 }

			humidifFillValveDO_1 OBJECT-TYPE
			SYNTAX INTEGER
			MAX-ACCESS read-only
			STATUS current
			DESCRIPTION "Filling valve"
			::= { binaryObjects1 28 }

			humidifWaterLevel_1 OBJECT-TYPE
			SYNTAX INTEGER
			MAX-ACCESS read-only
			STATUS current
			DESCRIPTION "High water level"
			::= { binaryObjects1 29 }

			supervOFF_1 OBJECT-TYPE
			SYNTAX INTEGER
			MAX-ACCESS read-write
			STATUS current
			DESCRIPTION "Supervisor OFF"
			::= { binaryObjects1 30 }

			enableHumidifier_1 OBJECT-TYPE
			SYNTAX INTEGER
			MAX-ACCESS read-write
			STATUS current
			DESCRIPTION "Humidification enabling"
			::= { binaryObjects1 31 }

			humidifManualDrain_1 OBJECT-TYPE
			SYNTAX INTEGER
			MAX-ACCESS read-write
			STATUS current
			DESCRIPTION "Humidifier manual discharge"
			::= { binaryObjects1 32 }

			humidifCylWashing_1 OBJECT-TYPE
			SYNTAX INTEGER
			MAX-ACCESS read-write
			STATUS current
			DESCRIPTION "Humidifier cylinder pre-wash"
			::= { binaryObjects1 33 }

			tSEchange_1 OBJECT-TYPE
			SYNTAX INTEGER
			MAX-ACCESS read-write
			STATUS current
			DESCRIPTION "Two sources source exchange"
			::= { binaryObjects1 34 }

			watPresAlRes_1 OBJECT-TYPE
			SYNTAX INTEGER
			MAX-ACCESS read-write
			STATUS current
			DESCRIPTION "Water presence sensor / Condensate drain pump alarm reset"
			::= { binaryObjects1 35 }

			elHeatAlRes_1 OBJECT-TYPE
			SYNTAX INTEGER
			MAX-ACCESS read-write
			STATUS current
			DESCRIPTION "Electric heater safety thermostat alarm reset"
			::= { binaryObjects1 36 }

			damperAlRes_1 OBJECT-TYPE
			SYNTAX INTEGER
			MAX-ACCESS read-write
			STATUS current
			DESCRIPTION "Damper status alarm reset"
			::= { binaryObjects1 37 }

			filterAlRes_1 OBJECT-TYPE
			SYNTAX INTEGER
			MAX-ACCESS read-write
			STATUS current
			DESCRIPTION "Clogged air filter alarm reset"
			::= { binaryObjects1 38 }

			c1ThermAlRes_1 OBJECT-TYPE
			SYNTAX INTEGER
			MAX-ACCESS read-write
			STATUS current
			DESCRIPTION "Compressor 1 magnetic thermal protection alarm reset"
			::= { binaryObjects1 39 }

			c2ThermAlRes_1 OBJECT-TYPE
			SYNTAX INTEGER
			MAX-ACCESS read-write
			STATUS current
			DESCRIPTION "Compressor 2 magnetic thermal protection alarm reset"
			::= { binaryObjects1 40 }

			c1HighPresAlRes_1 OBJECT-TYPE
			SYNTAX INTEGER
			MAX-ACCESS read-write
			STATUS current
			DESCRIPTION "Compressor 1 high pressure alarm reset"
			::= { binaryObjects1 41 }

			c2HighPresAlRes_1 OBJECT-TYPE
			SYNTAX INTEGER
			MAX-ACCESS read-write
			STATUS current
			DESCRIPTION "Compressor 2 high pressure alarm reset"
			::= { binaryObjects1 42 }

			c1HighDischAlRes_1 OBJECT-TYPE
			SYNTAX INTEGER
			MAX-ACCESS read-write
			STATUS current
			DESCRIPTION "Compressor 1 high discharge temperature alarm reset"
			::= { binaryObjects1 43 }

			c2HighDischAlRes_1 OBJECT-TYPE
			SYNTAX INTEGER
			MAX-ACCESS read-write
			STATUS current
			DESCRIPTION "Compressor 2 high discharge temperature alarm reset"
			::= { binaryObjects1 44 }

			eEV1AlRes_1 OBJECT-TYPE
			SYNTAX INTEGER
			MAX-ACCESS read-write
			STATUS current
			DESCRIPTION "EEV 1 alarm reset"
			::= { binaryObjects1 45 }

			eEV2AlRes_1 OBJECT-TYPE
			SYNTAX INTEGER
			MAX-ACCESS read-write
			STATUS current
			DESCRIPTION "EEV 2 alarm reset"
			::= { binaryObjects1 46 }

			inverterCompAlRes_1 OBJECT-TYPE
			SYNTAX INTEGER
			MAX-ACCESS read-write
			STATUS current
			DESCRIPTION "DC compressor inverter alarm reset"
			::= { binaryObjects1 47 }

			c1LoComprRatioAlRes_1 OBJECT-TYPE
			SYNTAX INTEGER
			MAX-ACCESS read-write
			STATUS current
			DESCRIPTION "Compressor 1 low compression ratio alarm reset"
			::= { binaryObjects1 48 }

			c2LoComprRatioAlRes_1 OBJECT-TYPE
			SYNTAX INTEGER
			MAX-ACCESS read-write
			STATUS current
			DESCRIPTION "Compressor 2 low compression ratio alarm reset"
			::= { binaryObjects1 49 }

			fan1InverterAlRes_1 OBJECT-TYPE
			SYNTAX INTEGER
			MAX-ACCESS read-write
			STATUS current
			DESCRIPTION "Fan 1 inverter alarm reset"
			::= { binaryObjects1 50 }

			fan2InverterAlRes_1 OBJECT-TYPE
			SYNTAX INTEGER
			MAX-ACCESS read-write
			STATUS current
			DESCRIPTION "Fan 2 inverter alarm reset"
			::= { binaryObjects1 51 }

			fan3InverterAlRes_1 OBJECT-TYPE
			SYNTAX INTEGER
			MAX-ACCESS read-write
			STATUS current
			DESCRIPTION "Fan 3 inverter alarm reset"
			::= { binaryObjects1 52 }

			fan4InverterAlRes_1 OBJECT-TYPE
			SYNTAX INTEGER
			MAX-ACCESS read-write
			STATUS current
			DESCRIPTION "Fan 4 inverter alarm reset"
			::= { binaryObjects1 53 }

			fan5InverterAlRes_1 OBJECT-TYPE
			SYNTAX INTEGER
			MAX-ACCESS read-write
			STATUS current
			DESCRIPTION "Fan 5 inverter alarm reset"
			::= { binaryObjects1 54 }

			intHumidifAlRes_1 OBJECT-TYPE
			SYNTAX INTEGER
			MAX-ACCESS read-write
			STATUS current
			DESCRIPTION "Internal humidifier alarm reset"
			::= { binaryObjects1 55 }

			dryCoolerAlRes_1 OBJECT-TYPE
			SYNTAX INTEGER
			MAX-ACCESS read-write
			STATUS current
			DESCRIPTION "Dry cooler general alarm reset"
			::= { binaryObjects1 56 }

			extHumidifAlRes_1 OBJECT-TYPE
			SYNTAX INTEGER
			MAX-ACCESS read-write
			STATUS current
			DESCRIPTION "External humidifier general alarm reset"
			::= { binaryObjects1 57 }

			waterPumpAlRes_1 OBJECT-TYPE
			SYNTAX INTEGER
			MAX-ACCESS read-write
			STATUS current
			DESCRIPTION "General water pump alarm reset"
			::= { binaryObjects1 58 }

			condenser1AlRes_1 OBJECT-TYPE
			SYNTAX INTEGER
			MAX-ACCESS read-write
			STATUS current
			DESCRIPTION "Condenser 1 general alarm reset"
			::= { binaryObjects1 59 }

			condenser2AlRes_1 OBJECT-TYPE
			SYNTAX INTEGER
			MAX-ACCESS read-write
			STATUS current
			DESCRIPTION "Condenser 2 general alarm reset"
			::= { binaryObjects1 60 }

			gasLeakAResl_1 OBJECT-TYPE
			SYNTAX INTEGER
			MAX-ACCESS read-write
			STATUS current
			DESCRIPTION "Refrigerant gas leak detector alarm reset"
			::= { binaryObjects1 61 }

			fansGenAResl_1 OBJECT-TYPE
			SYNTAX INTEGER
			MAX-ACCESS read-write
			STATUS current
			DESCRIPTION "General supply fans alarm reset"
			::= { binaryObjects1 62 }

			fireSmokeAlRes_1 OBJECT-TYPE
			SYNTAX INTEGER
			MAX-ACCESS read-write
			STATUS current
			DESCRIPTION "Fire/Smoke presence alarm reset"
			::= { binaryObjects1 63 }

			genericSoftAlRes_1 OBJECT-TYPE
			SYNTAX INTEGER
			MAX-ACCESS read-write
			STATUS current
			DESCRIPTION "Non-critical generic alarm reset"
			::= { binaryObjects1 64 }

			genericSeriousAlRes_1 OBJECT-TYPE
			SYNTAX INTEGER
			MAX-ACCESS read-write
			STATUS current
			DESCRIPTION "Critical generic alarm reset"
			::= { binaryObjects1 65 }

			condUnitGenAlRes_1 OBJECT-TYPE
			SYNTAX INTEGER
			MAX-ACCESS read-write
			STATUS current
			DESCRIPTION "Condensing unit generic alarm reset"
			::= { binaryObjects1 66 }

			powerSupplyAlRes_1 OBJECT-TYPE
			SYNTAX INTEGER
			MAX-ACCESS read-write
			STATUS current
			DESCRIPTION "Power supply failure alarm reset"
			::= { binaryObjects1 67 }

			c1LowPresAlRes_1 OBJECT-TYPE
			SYNTAX INTEGER
			MAX-ACCESS read-write
			STATUS current
			DESCRIPTION "Compressor 1 low pressure alarm reset"
			::= { binaryObjects1 68 }

			c2LowPresAlRes_1 OBJECT-TYPE
			SYNTAX INTEGER
			MAX-ACCESS read-write
			STATUS current
			DESCRIPTION "Compressor 2 low pressure alarm reset"
			::= { binaryObjects1 69 }

		scalarsObjects1 OBJECT IDENTIFIER  ::= { node1 2 }

			returnHumidity_1 OBJECT-TYPE
			SYNTAX Integer32
			MAX-ACCESS read-only
			STATUS current
			DESCRIPTION "Return humidity"
			::= { scalarsObjects1 1 }

			returnTemperature_1 OBJECT-TYPE
			SYNTAX Integer32
			MAX-ACCESS read-only
			STATUS current
			DESCRIPTION "Return temperature"
			::= { scalarsObjects1 2 }

			supplyHumidity_1 OBJECT-TYPE
			SYNTAX Integer32
			MAX-ACCESS read-only
			STATUS current
			DESCRIPTION "Supply humidity"
			::= { scalarsObjects1 3 }

			supplyTemperature_1 OBJECT-TYPE
			SYNTAX Integer32
			MAX-ACCESS read-only
			STATUS current
			DESCRIPTION "Supply temperature"
			::= { scalarsObjects1 4 }

			airPressure_1 OBJECT-TYPE
			SYNTAX Integer32
			MAX-ACCESS read-only
			STATUS current
			DESCRIPTION "Air pressure"
			::= { scalarsObjects1 5 }

			waterINTemperature_1 OBJECT-TYPE
			SYNTAX Integer32
			MAX-ACCESS read-only
			STATUS current
			DESCRIPTION "Water inlet temperature 1 / free cooling"
			::= { scalarsObjects1 6 }

			waterOUTTemperature_1 OBJECT-TYPE
			SYNTAX Integer32
			MAX-ACCESS read-only
			STATUS current
			DESCRIPTION "Water outlet temperature 1"
			::= { scalarsObjects1 7 }

			comp1CondPress_1 OBJECT-TYPE
			SYNTAX Integer32
			MAX-ACCESS read-only
			STATUS current
			DESCRIPTION "Compressor 1 condensation pressure"
			::= { scalarsObjects1 8 }

			compr2CondPress_1 OBJECT-TYPE
			SYNTAX Integer32
			MAX-ACCESS read-only
			STATUS current
			DESCRIPTION "Compressor 2 condensation pressure"
			::= { scalarsObjects1 9 }

			compr1CondTemp_1 OBJECT-TYPE
			SYNTAX Integer32
			MAX-ACCESS read-only
			STATUS current
			DESCRIPTION "Compressor 1 condensation temperature"
			::= { scalarsObjects1 10 }

			comp2CondTemp_1 OBJECT-TYPE
			SYNTAX Integer32
			MAX-ACCESS read-only
			STATUS current
			DESCRIPTION "Compressor 2 condensation temperature"
			::= { scalarsObjects1 11 }

			comp1DischTemp_1 OBJECT-TYPE
			SYNTAX Integer32
			MAX-ACCESS read-only
			STATUS current
			DESCRIPTION "Compressor 1 discharge temperature"
			::= { scalarsObjects1 12 }

			comp2DischTemp_1 OBJECT-TYPE
			SYNTAX Integer32
			MAX-ACCESS read-only
			STATUS current
			DESCRIPTION "Compressor 2 discharge temperature"
			::= { scalarsObjects1 13 }

			comp1SuctionTemp_1 OBJECT-TYPE
			SYNTAX Integer32
			MAX-ACCESS read-only
			STATUS current
			DESCRIPTION "Compressor 1 suction temperature"
			::= { scalarsObjects1 14 }

			comp2SuctionTemp_1 OBJECT-TYPE
			SYNTAX Integer32
			MAX-ACCESS read-only
			STATUS current
			DESCRIPTION "Compressor 2 suction temperature"
			::= { scalarsObjects1 15 }

			comp1EvapPres_1 OBJECT-TYPE
			SYNTAX Integer32
			MAX-ACCESS read-only
			STATUS current
			DESCRIPTION "Compressor 1 evaporation pressure"
			::= { scalarsObjects1 16 }

			comp2EvapPres_1 OBJECT-TYPE
			SYNTAX Integer32
			MAX-ACCESS read-only
			STATUS current
			DESCRIPTION "Compressor 2 evaporation pressure"
			::= { scalarsObjects1 17 }

			comp1EvapTemp_1 OBJECT-TYPE
			SYNTAX Integer32
			MAX-ACCESS read-only
			STATUS current
			DESCRIPTION "Compressor 1 evaporation temperature"
			::= { scalarsObjects1 18 }

			comp2EvapTemp_1 OBJECT-TYPE
			SYNTAX Integer32
			MAX-ACCESS read-only
			STATUS current
			DESCRIPTION "Compressor 2 evaporation temperature"
			::= { scalarsObjects1 19 }

			comp1LiquidTemp_1 OBJECT-TYPE
			SYNTAX Integer32
			MAX-ACCESS read-only
			STATUS current
			DESCRIPTION "Compressor 1 liquid temperature"
			::= { scalarsObjects1 20 }

			compr2LiquidTemp_1 OBJECT-TYPE
			SYNTAX Integer32
			MAX-ACCESS read-only
			STATUS current
			DESCRIPTION "Compressor 2 liquid temperature"
			::= { scalarsObjects1 21 }

			waterFlow1_1 OBJECT-TYPE
			SYNTAX Integer32
			MAX-ACCESS read-only
			STATUS current
			DESCRIPTION "Water flow rate 1"
			::= { scalarsObjects1 22 }

			waterFlow2_1 OBJECT-TYPE
			SYNTAX Integer32
			MAX-ACCESS read-only
			STATUS current
			DESCRIPTION "Water flow rate 2"
			::= { scalarsObjects1 23 }

			totalWaterFlow_1 OBJECT-TYPE
			SYNTAX Integer32
			MAX-ACCESS read-only
			STATUS current
			DESCRIPTION "Total water flow rate"
			::= { scalarsObjects1 24 }

			returnHumidityAvg_1 OBJECT-TYPE
			SYNTAX Integer32
			MAX-ACCESS read-only
			STATUS current
			DESCRIPTION "Return humidity (average local network)"
			::= { scalarsObjects1 25 }

			returnTempAvg_1 OBJECT-TYPE
			SYNTAX Integer32
			MAX-ACCESS read-only
			STATUS current
			DESCRIPTION "Return temperature (average local network)"
			::= { scalarsObjects1 26 }

			supplyHumidityAvg_1 OBJECT-TYPE
			SYNTAX Integer32
			MAX-ACCESS read-only
			STATUS current
			DESCRIPTION "Supply humidity (average local network)"
			::= { scalarsObjects1 27 }

			supplyTempAvg_1 OBJECT-TYPE
			SYNTAX Integer32
			MAX-ACCESS read-only
			STATUS current
			DESCRIPTION "Supply temperature (average local network)"
			::= { scalarsObjects1 28 }

			airPressureAvg_1 OBJECT-TYPE
			SYNTAX Integer32
			MAX-ACCESS read-only
			STATUS current
			DESCRIPTION "Air pressure (local network average)"
			::= { scalarsObjects1 29 }

			waterINTemperature2_1 OBJECT-TYPE
			SYNTAX Integer32
			MAX-ACCESS read-only
			STATUS current
			DESCRIPTION "Water inlet temperature 2"
			::= { scalarsObjects1 30 }

			waterOUTemperature2_1 OBJECT-TYPE
			SYNTAX Integer32
			MAX-ACCESS read-only
			STATUS current
			DESCRIPTION "Water outlet temperature 2"
			::= { scalarsObjects1 31 }

			diffFilterPressure_1 OBJECT-TYPE
			SYNTAX Integer32
			MAX-ACCESS read-only
			STATUS current
			DESCRIPTION "Dirty filter differential pressure"
			::= { scalarsObjects1 32 }

			unitFansDryCoolerAO_1 OBJECT-TYPE
			SYNTAX Integer32
			MAX-ACCESS read-only
			STATUS current
			DESCRIPTION "Supply fans / Dry cooler"
			::= { scalarsObjects1 33 }

			coolingAO_1 OBJECT-TYPE
			SYNTAX Integer32
			MAX-ACCESS read-only
			STATUS current
			DESCRIPTION "Cooling valve / Free cooling / External inverter"
			::= { scalarsObjects1 34 }

			heatingAO_1 OBJECT-TYPE
			SYNTAX Integer32
			MAX-ACCESS read-only
			STATUS current
			DESCRIPTION "Heating Valve / Modulating electric heater"
			::= { scalarsObjects1 35 }

			twoSourcesAO_1 OBJECT-TYPE
			SYNTAX Integer32
			MAX-ACCESS read-only
			STATUS current
			DESCRIPTION "Two sources water valve"
			::= { scalarsObjects1 36 }

			condenser1AO_1 OBJECT-TYPE
			SYNTAX Integer32
			MAX-ACCESS read-only
			STATUS current
			DESCRIPTION "Condenser 1"
			::= { scalarsObjects1 37 }

			condenser2HumidifAO_1 OBJECT-TYPE
			SYNTAX Integer32
			MAX-ACCESS read-only
			STATUS current
			DESCRIPTION "Humidifier / Condenser 2"
			::= { scalarsObjects1 38 }

			unitStatus_1 OBJECT-TYPE
			SYNTAX Integer32
			MAX-ACCESS read-only
			STATUS current
			DESCRIPTION "Unit status"
			::= { scalarsObjects1 39 }

			airFlow_1 OBJECT-TYPE
			SYNTAX Integer32
			MAX-ACCESS read-only
			STATUS current
			DESCRIPTION "Air flow rate"
			::= { scalarsObjects1 40 }

			unitWorkingHours_1 OBJECT-TYPE
			SYNTAX Integer32
			MAX-ACCESS read-only
			STATUS current
			DESCRIPTION "Unit working hours"
			::= { scalarsObjects1 41 }

			comp1WorkingHours_1 OBJECT-TYPE
			SYNTAX Integer32
			MAX-ACCESS read-only
			STATUS current
			DESCRIPTION "Compressor 1 working hours"
			::= { scalarsObjects1 42 }

			compr2WorkingHours_1 OBJECT-TYPE
			SYNTAX Integer32
			MAX-ACCESS read-only
			STATUS current
			DESCRIPTION "Compressor 2 working hours"
			::= { scalarsObjects1 43 }

			heaterWorkingHours_1 OBJECT-TYPE
			SYNTAX Integer32
			MAX-ACCESS read-only
			STATUS current
			DESCRIPTION "Heating working hours"
			::= { scalarsObjects1 44 }

			dryCoolerWorkHours_1 OBJECT-TYPE
			SYNTAX Integer32
			MAX-ACCESS read-only
			STATUS current
			DESCRIPTION "Dry cooler working hours"
			::= { scalarsObjects1 45 }

			humidifWorkingHours_1 OBJECT-TYPE
			SYNTAX Integer32
			MAX-ACCESS read-only
			STATUS current
			DESCRIPTION "Humidifier working hours"
			::= { scalarsObjects1 46 }

			coolValveWorkHours_1 OBJECT-TYPE
			SYNTAX Integer32
			MAX-ACCESS read-only
			STATUS current
			DESCRIPTION "Cooling valve working hours"
			::= { scalarsObjects1 47 }

			cond1WorkingHours_1 OBJECT-TYPE
			SYNTAX Integer32
			MAX-ACCESS read-only
			STATUS current
			DESCRIPTION "Condenser 1 working hours"
			::= { scalarsObjects1 48 }

			cond2WorkingHours_1 OBJECT-TYPE
			SYNTAX Integer32
			MAX-ACCESS read-only
			STATUS current
			DESCRIPTION "Condenser 2 working hours"
			::= { scalarsObjects1 49 }

			freeCoolWorkHours_1 OBJECT-TYPE
			SYNTAX Integer32
			MAX-ACCESS read-only
			STATUS current
			DESCRIPTION "Free cooling working hours"
			::= { scalarsObjects1 50 }

			eEV1SuperheatSet_1 OBJECT-TYPE
			SYNTAX Integer32
			MAX-ACCESS read-only
			STATUS current
			DESCRIPTION "Current EEV1 superheating set-point"
			::= { scalarsObjects1 51 }

			eEV2SuperheatSet_1 OBJECT-TYPE
			SYNTAX Integer32
			MAX-ACCESS read-only
			STATUS current
			DESCRIPTION "Current EEV2 superheating set-point"
			::= { scalarsObjects1 52 }

			eEV1Superheat_1 OBJECT-TYPE
			SYNTAX Integer32
			MAX-ACCESS read-only
			STATUS current
			DESCRIPTION "Current EEV1 superheating"
			::= { scalarsObjects1 53 }

			eEV2Superheat_1 OBJECT-TYPE
			SYNTAX Integer32
			MAX-ACCESS read-only
			STATUS current
			DESCRIPTION "Current EEV2 superheating"
			::= { scalarsObjects1 54 }

			eEV1Position_1 OBJECT-TYPE
			SYNTAX Integer32
			MAX-ACCESS read-only
			STATUS current
			DESCRIPTION "Current EEV1 position"
			::= { scalarsObjects1 55 }

			eEV2Position_1 OBJECT-TYPE
			SYNTAX Integer32
			MAX-ACCESS read-only
			STATUS current
			DESCRIPTION "Current EEV2 position"
			::= { scalarsObjects1 56 }

			eEV1PDesuperheat_1 OBJECT-TYPE
			SYNTAX Integer32
			MAX-ACCESS read-only
			STATUS current
			DESCRIPTION "Current EEV1 de-superheating"
			::= { scalarsObjects1 57 }

			eEV2Desuperheat_1 OBJECT-TYPE
			SYNTAX Integer32
			MAX-ACCESS read-only
			STATUS current
			DESCRIPTION "Current EEV2 de-superheating"
			::= { scalarsObjects1 58 }

			eEV1PSubcooling_1 OBJECT-TYPE
			SYNTAX Integer32
			MAX-ACCESS read-only
			STATUS current
			DESCRIPTION "Current EEV1 sub-cooling"
			::= { scalarsObjects1 59 }

			eEV2Subcooling_1 OBJECT-TYPE
			SYNTAX Integer32
			MAX-ACCESS read-only
			STATUS current
			DESCRIPTION "Current EEV2 sub-cooling"
			::= { scalarsObjects1 60 }

			humidifSteamProd_1 OBJECT-TYPE
			SYNTAX Integer32
			MAX-ACCESS read-only
			STATUS current
			DESCRIPTION "Actual humidifier production"
			::= { scalarsObjects1 61 }

			humidifWaterConduct_1 OBJECT-TYPE
			SYNTAX Integer32
			MAX-ACCESS read-only
			STATUS current
			DESCRIPTION "Supply water conductivity"
			::= { scalarsObjects1 62 }

			humidifierCurrent_1 OBJECT-TYPE
			SYNTAX Integer32
			MAX-ACCESS read-only
			STATUS current
			DESCRIPTION "Absorbed humidifier current"
			::= { scalarsObjects1 63 }

			humidifWorkingMode_1 OBJECT-TYPE
			SYNTAX Integer32
			MAX-ACCESS read-only
			STATUS current
			DESCRIPTION "Humidifier operation mode"
			::= { scalarsObjects1 64 }

			humidifWorkStatus_1 OBJECT-TYPE
			SYNTAX Integer32
			MAX-ACCESS read-only
			STATUS current
			DESCRIPTION "Humidifier operation status"
			::= { scalarsObjects1 65 }

			fan1SpeedRPM_1 OBJECT-TYPE
			SYNTAX Integer32
			MAX-ACCESS read-only
			STATUS current
			DESCRIPTION "Fan speed 1"
			::= { scalarsObjects1 66 }

			fan2SpeedRPM_1 OBJECT-TYPE
			SYNTAX Integer32
			MAX-ACCESS read-only
			STATUS current
			DESCRIPTION "Fan speed 2"
			::= { scalarsObjects1 67 }

			fan3SpeedRPM_1 OBJECT-TYPE
			SYNTAX Integer32
			MAX-ACCESS read-only
			STATUS current
			DESCRIPTION "Fan speed 3"
			::= { scalarsObjects1 68 }

			fan4SpeedRPM_1 OBJECT-TYPE
			SYNTAX Integer32
			MAX-ACCESS read-only
			STATUS current
			DESCRIPTION "Fan speed 4"
			::= { scalarsObjects1 69 }

			fan5SpeedRPM_1 OBJECT-TYPE
			SYNTAX Integer32
			MAX-ACCESS read-only
			STATUS current
			DESCRIPTION "Fan speed 5"
			::= { scalarsObjects1 70 }

			fan1Speed_1 OBJECT-TYPE
			SYNTAX Integer32
			MAX-ACCESS read-only
			STATUS current
			DESCRIPTION "Fan speed 1"
			::= { scalarsObjects1 71 }

			fan2Speed_1 OBJECT-TYPE
			SYNTAX Integer32
			MAX-ACCESS read-only
			STATUS current
			DESCRIPTION "Fan speed 2"
			::= { scalarsObjects1 72 }

			fan3Speed_1 OBJECT-TYPE
			SYNTAX Integer32
			MAX-ACCESS read-only
			STATUS current
			DESCRIPTION "Fan speed 3"
			::= { scalarsObjects1 73 }

			fan4Speed_1 OBJECT-TYPE
			SYNTAX Integer32
			MAX-ACCESS read-only
			STATUS current
			DESCRIPTION "Fan speed 4"
			::= { scalarsObjects1 74 }

			fan5Speed_1 OBJECT-TYPE
			SYNTAX Integer32
			MAX-ACCESS read-only
			STATUS current
			DESCRIPTION "Fan speed 5"
			::= { scalarsObjects1 75 }

			fan1Current_1 OBJECT-TYPE
			SYNTAX Integer32
			MAX-ACCESS read-only
			STATUS current
			DESCRIPTION "Fan 1 absorbed current"
			::= { scalarsObjects1 76 }

			fan1Power_1 OBJECT-TYPE
			SYNTAX Integer32
			MAX-ACCESS read-only
			STATUS current
			DESCRIPTION "Fan 1 absorbed electrical power"
			::= { scalarsObjects1 77 }

			fan2Current_1 OBJECT-TYPE
			SYNTAX Integer32
			MAX-ACCESS read-only
			STATUS current
			DESCRIPTION "Fan 2 absorbed current"
			::= { scalarsObjects1 78 }

			fan2Power_1 OBJECT-TYPE
			SYNTAX Integer32
			MAX-ACCESS read-only
			STATUS current
			DESCRIPTION "Fan 2 absorbed electrical power"
			::= { scalarsObjects1 79 }

			fan3Current_1 OBJECT-TYPE
			SYNTAX Integer32
			MAX-ACCESS read-only
			STATUS current
			DESCRIPTION "Fan 3 absorbed current"
			::= { scalarsObjects1 80 }

			fan3Power_1 OBJECT-TYPE
			SYNTAX Integer32
			MAX-ACCESS read-only
			STATUS current
			DESCRIPTION "Fan 3 absorbed electrical power"
			::= { scalarsObjects1 81 }

			fan4Current_1 OBJECT-TYPE
			SYNTAX Integer32
			MAX-ACCESS read-only
			STATUS current
			DESCRIPTION "Fan 4 absorbed current"
			::= { scalarsObjects1 82 }

			fan4Power_1 OBJECT-TYPE
			SYNTAX Integer32
			MAX-ACCESS read-only
			STATUS current
			DESCRIPTION "Fan 4 absorbed electrical power"
			::= { scalarsObjects1 83 }

			fan5Current_1 OBJECT-TYPE
			SYNTAX Integer32
			MAX-ACCESS read-only
			STATUS current
			DESCRIPTION "Fan 5 absorbed current"
			::= { scalarsObjects1 84 }

			fan5Power_1 OBJECT-TYPE
			SYNTAX Integer32
			MAX-ACCESS read-only
			STATUS current
			DESCRIPTION "Fan 5 absorbed electrical power"
			::= { scalarsObjects1 85 }

			inverterCompSpeed_1 OBJECT-TYPE
			SYNTAX Integer32
			MAX-ACCESS read-only
			STATUS current
			DESCRIPTION "Current compressor speed"
			::= { scalarsObjects1 86 }

			inverterCompPower_1 OBJECT-TYPE
			SYNTAX Integer32
			MAX-ACCESS read-only
			STATUS current
			DESCRIPTION "Current compressor electrical power"
			::= { scalarsObjects1 87 }

			inverterCompCurrent_1 OBJECT-TYPE
			SYNTAX Integer32
			MAX-ACCESS read-only
			STATUS current
			DESCRIPTION "Current compressor absorbed current"
			::= { scalarsObjects1 88 }

			waterCoolingCap1_1 OBJECT-TYPE
			SYNTAX Integer32
			MAX-ACCESS read-only
			STATUS current
			DESCRIPTION "Chilled water cooling power 1"
			::= { scalarsObjects1 89 }

			eER1_1 OBJECT-TYPE
			SYNTAX Integer32
			MAX-ACCESS read-only
			STATUS current
			DESCRIPTION "EER 1"
			::= { scalarsObjects1 90 }

			heaterActiveStages_1 OBJECT-TYPE
			SYNTAX Integer32
			MAX-ACCESS read-only
			STATUS current
			DESCRIPTION "Number of active stages"
			::= { scalarsObjects1 91 }

			elecHeaterPower_1 OBJECT-TYPE
			SYNTAX Integer32
			MAX-ACCESS read-only
			STATUS current
			DESCRIPTION "Electric heater power requirement"
			::= { scalarsObjects1 92 }

			temperatureSetpoint_1 OBJECT-TYPE
			SYNTAX Integer32
			MAX-ACCESS read-write
			STATUS current
			DESCRIPTION "Temperature set-point"
			::= { scalarsObjects1 93 }

			humiditySetpoint_1 OBJECT-TYPE
			SYNTAX Integer32
			MAX-ACCESS read-write
			STATUS current
			DESCRIPTION "Humidity set-point"
			::= { scalarsObjects1 94 }

			airFlowSetpoint_1 OBJECT-TYPE
			SYNTAX Integer32
			MAX-ACCESS read-write
			STATUS current
			DESCRIPTION "Supply air flow set-point"
			::= { scalarsObjects1 95 }

			airPressureSetpoint_1 OBJECT-TYPE
			SYNTAX Integer32
			MAX-ACCESS read-write
			STATUS current
			DESCRIPTION "Air pressure set-point"
			::= { scalarsObjects1 96 }

			tempControlSel_1 OBJECT-TYPE
			SYNTAX Integer32
			MAX-ACCESS read-write
			STATUS current
			DESCRIPTION "Temperature regulation sensor"
			::= { scalarsObjects1 97 }

			tempControlType_1 OBJECT-TYPE
			SYNTAX Integer32
			MAX-ACCESS read-write
			STATUS current
			DESCRIPTION "Temperature regulation type"
			::= { scalarsObjects1 98 }

			proportionalBand_1 OBJECT-TYPE
			SYNTAX Integer32
			MAX-ACCESS read-write
			STATUS current
			DESCRIPTION "Temperature Proportional Band"
			::= { scalarsObjects1 99 }

			intagrativeTime_1 OBJECT-TYPE
			SYNTAX Integer32
			MAX-ACCESS read-write
			STATUS current
			DESCRIPTION "Temperature Integration time"
			::= { scalarsObjects1 100 }

			derivativeTime_1 OBJECT-TYPE
			SYNTAX Integer32
			MAX-ACCESS read-write
			STATUS current
			DESCRIPTION "Temperature Derivation time"
			::= { scalarsObjects1 101 }

			highTempAlarmOffset_1 OBJECT-TYPE
			SYNTAX Integer32
			MAX-ACCESS read-write
			STATUS current
			DESCRIPTION "High temperature alarm offset"
			::= { scalarsObjects1 102 }

			lowTempAlarmOffset_1 OBJECT-TYPE
			SYNTAX Integer32
			MAX-ACCESS read-write
			STATUS current
			DESCRIPTION "Low temperature alarm offset"
			::= { scalarsObjects1 103 }

			highLimitTempThr_1 OBJECT-TYPE
			SYNTAX Integer32
			MAX-ACCESS read-write
			STATUS current
			DESCRIPTION "Temperature upper limit"
			::= { scalarsObjects1 104 }

			highLimitTempMng_1 OBJECT-TYPE
			SYNTAX Integer32
			MAX-ACCESS read-write
			STATUS current
			DESCRIPTION "High limit temperature management"
			::= { scalarsObjects1 105 }

			lowLimitTempThr_1 OBJECT-TYPE
			SYNTAX Integer32
			MAX-ACCESS read-write
			STATUS current
			DESCRIPTION "Temperature lower limit"
			::= { scalarsObjects1 106 }

			lowLimitTempMng_1 OBJECT-TYPE
			SYNTAX Integer32
			MAX-ACCESS read-write
			STATUS current
			DESCRIPTION "Low limit temperature management"
			::= { scalarsObjects1 107 }

			dehumidifPropBand_1 OBJECT-TYPE
			SYNTAX Integer32
			MAX-ACCESS read-write
			STATUS current
			DESCRIPTION "Dehumidification proportional band"
			::= { scalarsObjects1 108 }

			humidifPropBand_1 OBJECT-TYPE
			SYNTAX Integer32
			MAX-ACCESS read-write
			STATUS current
			DESCRIPTION "Humidification proportional band"
			::= { scalarsObjects1 109 }

			highRetHumAlOffset_1 OBJECT-TYPE
			SYNTAX Integer32
			MAX-ACCESS read-write
			STATUS current
			DESCRIPTION "High return humidity alarm offset"
			::= { scalarsObjects1 110 }

			lowRetHumAlOffset_1 OBJECT-TYPE
			SYNTAX Integer32
			MAX-ACCESS read-write
			STATUS current
			DESCRIPTION "Low return humidity alarm offset"
			::= { scalarsObjects1 111 }

			highSupHumThr_1 OBJECT-TYPE
			SYNTAX Integer32
			MAX-ACCESS read-write
			STATUS current
			DESCRIPTION "Higher supply humidity limit"
			::= { scalarsObjects1 112 }

			lowSupHumThr_1 OBJECT-TYPE
			SYNTAX Integer32
			MAX-ACCESS read-write
			STATUS current
			DESCRIPTION "Lower supply humidity limit"
			::= { scalarsObjects1 113 }

			freeCoolingDelta_1 OBJECT-TYPE
			SYNTAX Integer32
			MAX-ACCESS read-write
			STATUS current
			DESCRIPTION "Free cooling delta"
			::= { scalarsObjects1 114 }

			tSWaterSetpoint_1 OBJECT-TYPE
			SYNTAX Integer32
			MAX-ACCESS read-write
			STATUS current
			DESCRIPTION "Two sources water set-point"
			::= { scalarsObjects1 115 }

			tSWaterPropBand_1 OBJECT-TYPE
			SYNTAX Integer32
			MAX-ACCESS read-write
			STATUS current
			DESCRIPTION "Two sources water band"
			::= { scalarsObjects1 116 }

			cond1ActualSet_1 OBJECT-TYPE
			SYNTAX Integer32
			MAX-ACCESS read-only
			STATUS current
			DESCRIPTION "Current condenser 1 set-point"
			::= { scalarsObjects1 117 }

			cond2ActualSet_1 OBJECT-TYPE
			SYNTAX Integer32
			MAX-ACCESS read-only
			STATUS current
			DESCRIPTION "Current condenser 2 set-point"
			::= { scalarsObjects1 118 }

			condSetpoint_1 OBJECT-TYPE
			SYNTAX Integer32
			MAX-ACCESS read-write
			STATUS current
			DESCRIPTION "Condensation set-point"
			::= { scalarsObjects1 119 }

			condPropoBand_1 OBJECT-TYPE
			SYNTAX Integer32
			MAX-ACCESS read-write
			STATUS current
			DESCRIPTION "Condensation proportional band"
			::= { scalarsObjects1 120 }

			condSetIncrease_1 OBJECT-TYPE
			SYNTAX Integer32
			MAX-ACCESS read-write
			STATUS current
			DESCRIPTION "Condensation set-point increase"
			::= { scalarsObjects1 121 }

			maxCondSetpoint_1 OBJECT-TYPE
			SYNTAX Integer32
			MAX-ACCESS read-write
			STATUS current
			DESCRIPTION "Maximum condensation set-point"
			::= { scalarsObjects1 122 }

			dryCoolerActualSet_1 OBJECT-TYPE
			SYNTAX Integer32
			MAX-ACCESS read-only
			STATUS current
			DESCRIPTION "Current dry cooler set-point"
			::= { scalarsObjects1 123 }

			dryCoolerSetpoint_1 OBJECT-TYPE
			SYNTAX Integer32
			MAX-ACCESS read-write
			STATUS current
			DESCRIPTION "Dry cooler set-point"
			::= { scalarsObjects1 124 }

			dryCoolerPropBand_1 OBJECT-TYPE
			SYNTAX Integer32
			MAX-ACCESS read-write
			STATUS current
			DESCRIPTION "Dry cooler proportional band"
			::= { scalarsObjects1 125 }

			dryCoolerSetIncr_1 OBJECT-TYPE
			SYNTAX Integer32
			MAX-ACCESS read-write
			STATUS current
			DESCRIPTION "Dry Cooler set-point increase"
			::= { scalarsObjects1 126 }

			maxDryCoolerSet_1 OBJECT-TYPE
			SYNTAX Integer32
			MAX-ACCESS read-write
			STATUS current
			DESCRIPTION "Maximum dry Cooler set-point"
			::= { scalarsObjects1 127 }

			dirtyFiltersSet_1 OBJECT-TYPE
			SYNTAX Integer32
			MAX-ACCESS read-write
			STATUS current
			DESCRIPTION "Dirty filter set-point"
			::= { scalarsObjects1 128 }

			dirtyFiltersDiff_1 OBJECT-TYPE
			SYNTAX Integer32
			MAX-ACCESS read-write
			STATUS current
			DESCRIPTION "Dirty filter differential"
			::= { scalarsObjects1 129 }

			invCompAlCode1_1 OBJECT-TYPE
			SYNTAX 32Bit_Reg
			MAX-ACCESS read-only
			STATUS current
			DESCRIPTION "DC compressor inverter alarm code [0]"
			::= { scalarsObjects1 130 }

			invCompAlCode2_1 OBJECT-TYPE
			SYNTAX 32Bit_Reg
			MAX-ACCESS read-only
			STATUS current
			DESCRIPTION "DC compressor inverter alarm code [1]"
			::= { scalarsObjects1 131 }

			invCompAlCode3_1 OBJECT-TYPE
			SYNTAX 32Bit_Reg
			MAX-ACCESS read-only
			STATUS current
			DESCRIPTION "DC compressor inverter alarm code [2]"
			::= { scalarsObjects1 132 }

			invCompAlCode4_1 OBJECT-TYPE
			SYNTAX 32Bit_Reg
			MAX-ACCESS read-only
			STATUS current
			DESCRIPTION "DC compressor inverter alarm code [3]"
			::= { scalarsObjects1 133 }

			invCompAlCode5_1 OBJECT-TYPE
			SYNTAX 32Bit_Reg
			MAX-ACCESS read-only
			STATUS current
			DESCRIPTION "DC compressor inverter alarm code [4]"
			::= { scalarsObjects1 134 }

			compRatio1_1 OBJECT-TYPE
			SYNTAX Integer32
			MAX-ACCESS read-only
			STATUS current
			DESCRIPTION "Current compression ratio 1"
			::= { scalarsObjects1 135 }

			compRatio2_1 OBJECT-TYPE
			SYNTAX Integer32
			MAX-ACCESS read-only
			STATUS current
			DESCRIPTION "Current compression ratio 2"
			::= { scalarsObjects1 136 }

			waterCoolingCap2_1 OBJECT-TYPE
			SYNTAX Integer32
			MAX-ACCESS read-only
			STATUS current
			DESCRIPTION "Chilled water cooling power 2"
			::= { scalarsObjects1 137 }

			eER2_1 OBJECT-TYPE
			SYNTAX Integer32
			MAX-ACCESS read-only
			STATUS current
			DESCRIPTION "EER 2"
			::= { scalarsObjects1 138 }

		alarms1 OBJECT IDENTIFIER  ::= { node1 3 }

			retHumProbAl_1 OBJECT-TYPE
			SYNTAX INTEGER
			MAX-ACCESS read-only
			STATUS current
			DESCRIPTION "Broken return humidity probe alarm"
			::= { alarms1 1 }

			retTempProbAl_1 OBJECT-TYPE
			SYNTAX INTEGER
			MAX-ACCESS read-only
			STATUS current
			DESCRIPTION "Broken return temperature probe alarm"
			::= { alarms1 2 }

			airPrSensorAL_1 OBJECT-TYPE
			SYNTAX INTEGER
			MAX-ACCESS read-only
			STATUS current
			DESCRIPTION "Broken differential air pressure sensor alarm"
			::= { alarms1 3 }

			supTempProbAl_1 OBJECT-TYPE
			SYNTAX INTEGER
			MAX-ACCESS read-only
			STATUS current
			DESCRIPTION "Broken supply temperature probe alarm"
			::= { alarms1 4 }

			watIN1ProbAl_1 OBJECT-TYPE
			SYNTAX INTEGER
			MAX-ACCESS read-only
			STATUS current
			DESCRIPTION "Broken water IN 1 / Free cooling temperature probe alarm"
			::= { alarms1 5 }

			watOUT1ProbAl_1 OBJECT-TYPE
			SYNTAX INTEGER
			MAX-ACCESS read-only
			STATUS current
			DESCRIPTION "Broken water OUT 1 temperature probe alarm"
			::= { alarms1 6 }

			watFlw1ProbAl_1 OBJECT-TYPE
			SYNTAX INTEGER
			MAX-ACCESS read-only
			STATUS current
			DESCRIPTION "Broken water flow rate sensor 1 / Liquid temperature probe 1 alarm"
			::= { alarms1 7 }

			supHumProbAl_1 OBJECT-TYPE
			SYNTAX INTEGER
			MAX-ACCESS read-only
			STATUS current
			DESCRIPTION "Broken supply humidity probe alarm"
			::= { alarms1 8 }

			watFlw2ProbAl_1 OBJECT-TYPE
			SYNTAX INTEGER
			MAX-ACCESS read-only
			STATUS current
			DESCRIPTION "Broken water flow rate sensor 2 / Liquid temperature probe 2 alarm"
			::= { alarms1 9 }

			watPresAl_1 OBJECT-TYPE
			SYNTAX INTEGER
			MAX-ACCESS read-only
			STATUS current
			DESCRIPTION "Water presence / Condensate drain pump alarm"
			::= { alarms1 10 }

			elHeatAl_1 OBJECT-TYPE
			SYNTAX INTEGER
			MAX-ACCESS read-only
			STATUS current
			DESCRIPTION "Electric heater safety thermostat alarm"
			::= { alarms1 11 }

			damperAl_1 OBJECT-TYPE
			SYNTAX INTEGER
			MAX-ACCESS read-only
			STATUS current
			DESCRIPTION "Damper status alarm"
			::= { alarms1 12 }

			filterAl_1 OBJECT-TYPE
			SYNTAX INTEGER
			MAX-ACCESS read-only
			STATUS current
			DESCRIPTION "Clogged air filter alarm"
			::= { alarms1 13 }

			c1ThermAl_1 OBJECT-TYPE
			SYNTAX INTEGER
			MAX-ACCESS read-only
			STATUS current
			DESCRIPTION "Compressor 1 thermal protection alarm"
			::= { alarms1 14 }

			c2ThermAl_1 OBJECT-TYPE
			SYNTAX INTEGER
			MAX-ACCESS read-only
			STATUS current
			DESCRIPTION "Compressor 2 thermal protection alarm"
			::= { alarms1 15 }

			c1HighPresAl_1 OBJECT-TYPE
			SYNTAX INTEGER
			MAX-ACCESS read-only
			STATUS current
			DESCRIPTION "Compressor 1 high pressure alarm"
			::= { alarms1 16 }

			c2HighPresAl_1 OBJECT-TYPE
			SYNTAX INTEGER
			MAX-ACCESS read-only
			STATUS current
			DESCRIPTION "Compressor 2 high pressure alarm"
			::= { alarms1 17 }

			c1LowPresAl_1 OBJECT-TYPE
			SYNTAX INTEGER
			MAX-ACCESS read-only
			STATUS current
			DESCRIPTION "Compressor 1 low pressure alarm"
			::= { alarms1 18 }

			c2LowPresAl_1 OBJECT-TYPE
			SYNTAX INTEGER
			MAX-ACCESS read-only
			STATUS current
			DESCRIPTION "Compressor 2 low pressure alarm"
			::= { alarms1 19 }

			c1HighDischAl_1 OBJECT-TYPE
			SYNTAX INTEGER
			MAX-ACCESS read-only
			STATUS current
			DESCRIPTION "Compressor 1 high discharge temperature alarm"
			::= { alarms1 20 }

			c2HighDischAl_1 OBJECT-TYPE
			SYNTAX INTEGER
			MAX-ACCESS read-only
			STATUS current
			DESCRIPTION "Compressor 2 high discharge temperature alarm"
			::= { alarms1 21 }

			eEV1Al_1 OBJECT-TYPE
			SYNTAX INTEGER
			MAX-ACCESS read-only
			STATUS current
			DESCRIPTION "EEV 1 alarm"
			::= { alarms1 22 }

			eEV2Al_1 OBJECT-TYPE
			SYNTAX INTEGER
			MAX-ACCESS read-only
			STATUS current
			DESCRIPTION "EEV 2 alarm"
			::= { alarms1 23 }

			inverterCompAl_1 OBJECT-TYPE
			SYNTAX INTEGER
			MAX-ACCESS read-only
			STATUS current
			DESCRIPTION "DC compressor inverter alarm"
			::= { alarms1 24 }

			fan1InverterAl_1 OBJECT-TYPE
			SYNTAX INTEGER
			MAX-ACCESS read-only
			STATUS current
			DESCRIPTION "Fan 1 inverter alarm"
			::= { alarms1 25 }

			fan2InverterAl_1 OBJECT-TYPE
			SYNTAX INTEGER
			MAX-ACCESS read-only
			STATUS current
			DESCRIPTION "Fan 2 inverter alarm"
			::= { alarms1 26 }

			fan3InverterAl_1 OBJECT-TYPE
			SYNTAX INTEGER
			MAX-ACCESS read-only
			STATUS current
			DESCRIPTION "Fan 3 inverter alarm"
			::= { alarms1 27 }

			fan4InverterAl_1 OBJECT-TYPE
			SYNTAX INTEGER
			MAX-ACCESS read-only
			STATUS current
			DESCRIPTION "Fan 4 inverter alarm"
			::= { alarms1 28 }

			fan5InverterAl_1 OBJECT-TYPE
			SYNTAX INTEGER
			MAX-ACCESS read-only
			STATUS current
			DESCRIPTION "Fan 5 inverter alarm"
			::= { alarms1 29 }

			internalHumidifAl_1 OBJECT-TYPE
			SYNTAX INTEGER
			MAX-ACCESS read-only
			STATUS current
			DESCRIPTION "Internal humidifier alarm"
			::= { alarms1 30 }

			localNetworkAl_1 OBJECT-TYPE
			SYNTAX INTEGER
			MAX-ACCESS read-only
			STATUS current
			DESCRIPTION "Local network communication alarm"
			::= { alarms1 31 }

			regHighTempAl_1 OBJECT-TYPE
			SYNTAX INTEGER
			MAX-ACCESS read-only
			STATUS current
			DESCRIPTION "High regulation temperature alarm"
			::= { alarms1 32 }

			regLowTempAl_1 OBJECT-TYPE
			SYNTAX INTEGER
			MAX-ACCESS read-only
			STATUS current
			DESCRIPTION "Low regulation temperature alarm"
			::= { alarms1 33 }

			retHighHumiAl_1 OBJECT-TYPE
			SYNTAX INTEGER
			MAX-ACCESS read-only
			STATUS current
			DESCRIPTION "High return humidity alarm"
			::= { alarms1 34 }

			retLowHumiAl_1 OBJECT-TYPE
			SYNTAX INTEGER
			MAX-ACCESS read-only
			STATUS current
			DESCRIPTION "Low return humidity alarm"
			::= { alarms1 35 }

			supHighHumiAl_1 OBJECT-TYPE
			SYNTAX INTEGER
			MAX-ACCESS read-only
			STATUS current
			DESCRIPTION "High supply humidity alarm"
			::= { alarms1 36 }

			supLowHumiAl_1 OBJECT-TYPE
			SYNTAX INTEGER
			MAX-ACCESS read-only
			STATUS current
			DESCRIPTION "Low supply humidity alarm"
			::= { alarms1 37 }

			highLimTempAl_1 OBJECT-TYPE
			SYNTAX INTEGER
			MAX-ACCESS read-only
			STATUS current
			DESCRIPTION "High limit temperature alarm"
			::= { alarms1 38 }

			lowLimTempAl_1 OBJECT-TYPE
			SYNTAX INTEGER
			MAX-ACCESS read-only
			STATUS current
			DESCRIPTION "Low limit temperature alarm"
			::= { alarms1 39 }

			dryCoolerAl_1 OBJECT-TYPE
			SYNTAX INTEGER
			MAX-ACCESS read-only
			STATUS current
			DESCRIPTION "Dry cooler general alarm"
			::= { alarms1 40 }

			externalHumidifAl_1 OBJECT-TYPE
			SYNTAX INTEGER
			MAX-ACCESS read-only
			STATUS current
			DESCRIPTION "External humidifier general alarm"
			::= { alarms1 41 }

			waterPumpAl_1 OBJECT-TYPE
			SYNTAX INTEGER
			MAX-ACCESS read-only
			STATUS current
			DESCRIPTION "General water pump alarm"
			::= { alarms1 42 }

			condenser1Al_1 OBJECT-TYPE
			SYNTAX INTEGER
			MAX-ACCESS read-only
			STATUS current
			DESCRIPTION "Condenser 1 general alarm"
			::= { alarms1 43 }

			condenser2Al_1 OBJECT-TYPE
			SYNTAX INTEGER
			MAX-ACCESS read-only
			STATUS current
			DESCRIPTION "Condenser 2 general alarm"
			::= { alarms1 44 }

			gasLeakAl_1 OBJECT-TYPE
			SYNTAX INTEGER
			MAX-ACCESS read-only
			STATUS current
			DESCRIPTION "Refrigerant gas leak detector alarm"
			::= { alarms1 45 }

			fansGenAl_1 OBJECT-TYPE
			SYNTAX INTEGER
			MAX-ACCESS read-only
			STATUS current
			DESCRIPTION "General supply fans alarm"
			::= { alarms1 46 }

			fireSmokeAl_1 OBJECT-TYPE
			SYNTAX INTEGER
			MAX-ACCESS read-only
			STATUS current
			DESCRIPTION "Fire/Smoke presence alarm"
			::= { alarms1 47 }

			genericSoftAl_1 OBJECT-TYPE
			SYNTAX INTEGER
			MAX-ACCESS read-only
			STATUS current
			DESCRIPTION "Non-critical generic alarm"
			::= { alarms1 48 }

			genericSeriousAl_1 OBJECT-TYPE
			SYNTAX INTEGER
			MAX-ACCESS read-only
			STATUS current
			DESCRIPTION "Critical generic alarm"
			::= { alarms1 49 }

			condUnitGeneralAl_1 OBJECT-TYPE
			SYNTAX INTEGER
			MAX-ACCESS read-only
			STATUS current
			DESCRIPTION "Condensing unit general alarm"
			::= { alarms1 50 }

			powerSupplyAl_1 OBJECT-TYPE
			SYNTAX INTEGER
			MAX-ACCESS read-only
			STATUS current
			DESCRIPTION "Power supply failure alarm"
			::= { alarms1 51 }

			c1LowComprRatioAl_1 OBJECT-TYPE
			SYNTAX INTEGER
			MAX-ACCESS read-only
			STATUS current
			DESCRIPTION "Compressor 1 low compression ratio alarm"
			::= { alarms1 52 }

			c2LowComprRatioAl_1 OBJECT-TYPE
			SYNTAX INTEGER
			MAX-ACCESS read-only
			STATUS current
			DESCRIPTION "Compressor 2 low compression ratio alarm"
			::= { alarms1 53 }

			watIN2ProbAl_1 OBJECT-TYPE
			SYNTAX INTEGER
			MAX-ACCESS read-only
			STATUS current
			DESCRIPTION "Broken water IN 2 temperature probe alarm"
			::= { alarms1 54 }

			watOUT2ProbAl_1 OBJECT-TYPE
			SYNTAX INTEGER
			MAX-ACCESS read-only
			STATUS current
			DESCRIPTION "Broken water OUT 2 temperature probe alarm"
			::= { alarms1 55 }

			dirtyFiltPresSensAl_1 OBJECT-TYPE
			SYNTAX INTEGER
			MAX-ACCESS read-only
			STATUS current
			DESCRIPTION "Dirty filter pressure sensor alarm"
			::= { alarms1 56 }

			eEV1CommAl_1 OBJECT-TYPE
			SYNTAX INTEGER
			MAX-ACCESS read-only
			STATUS current
			DESCRIPTION "EEV 1 communication alarm"
			::= { alarms1 57 }

			eEV1SuctProbAl_1 OBJECT-TYPE
			SYNTAX INTEGER
			MAX-ACCESS read-only
			STATUS current
			DESCRIPTION "EEV 1 Suction temperature probe alarm"
			::= { alarms1 58 }

			eEV1EvapProbAl_1 OBJECT-TYPE
			SYNTAX INTEGER
			MAX-ACCESS read-only
			STATUS current
			DESCRIPTION "EEV 1 Evaporation pressure probe alarm"
			::= { alarms1 59 }

			eEV1CondProbAl_1 OBJECT-TYPE
			SYNTAX INTEGER
			MAX-ACCESS read-only
			STATUS current
			DESCRIPTION "EEV 1 Condensation pressure probe alarm"
			::= { alarms1 60 }

			eEV1DischProbAl_1 OBJECT-TYPE
			SYNTAX INTEGER
			MAX-ACCESS read-only
			STATUS current
			DESCRIPTION "EEV 1 Discharge temperature probe alarm"
			::= { alarms1 61 }

			eEV2CommAl_1 OBJECT-TYPE
			SYNTAX INTEGER
			MAX-ACCESS read-only
			STATUS current
			DESCRIPTION "EEV 2 Communication down alarm"
			::= { alarms1 62 }

			eEV2SuctProbAl_1 OBJECT-TYPE
			SYNTAX INTEGER
			MAX-ACCESS read-only
			STATUS current
			DESCRIPTION "EEV 2 Suction temperature probe alarm"
			::= { alarms1 63 }

			eEV2EvapProbAl_1 OBJECT-TYPE
			SYNTAX INTEGER
			MAX-ACCESS read-only
			STATUS current
			DESCRIPTION "EEV 2 Evaporation pressure probe alarm"
			::= { alarms1 64 }

			eEV2CondProbAl_1 OBJECT-TYPE
			SYNTAX INTEGER
			MAX-ACCESS read-only
			STATUS current
			DESCRIPTION "EEV 2 Condensation pressure probe alarm"
			::= { alarms1 65 }

			eEV2DischProbAl_1 OBJECT-TYPE
			SYNTAX INTEGER
			MAX-ACCESS read-only
			STATUS current
			DESCRIPTION "EEV 2 Discharge temperature probe alarm"
			::= { alarms1 66 }

			cPYCommAl_1 OBJECT-TYPE
			SYNTAX INTEGER
			MAX-ACCESS read-only
			STATUS current
			DESCRIPTION "CPY communication alarm"
			::= { alarms1 67 }

			cPYMemoryAl_1 OBJECT-TYPE
			SYNTAX INTEGER
			MAX-ACCESS read-only
			STATUS current
			DESCRIPTION "CPY Internal memory error"
			::= { alarms1 68 }

			cPYParameterAl_1 OBJECT-TYPE
			SYNTAX INTEGER
			MAX-ACCESS read-only
			STATUS current
			DESCRIPTION "CPY Parameter error"
			::= { alarms1 69 }

			cPYHighCurrentAl_1 OBJECT-TYPE
			SYNTAX INTEGER
			MAX-ACCESS read-only
			STATUS current
			DESCRIPTION "CPY Electrode high current"
			::= { alarms1 70 }

			cPYLowSteamAl_1 OBJECT-TYPE
			SYNTAX INTEGER
			MAX-ACCESS read-only
			STATUS current
			DESCRIPTION "CPY Low steam production"
			::= { alarms1 71 }

			cPYDrainAl_1 OBJECT-TYPE
			SYNTAX INTEGER
			MAX-ACCESS read-only
			STATUS current
			DESCRIPTION "CPY No drain"
			::= { alarms1 72 }

			cPYMaintAl_1 OBJECT-TYPE
			SYNTAX INTEGER
			MAX-ACCESS read-only
			STATUS current
			DESCRIPTION "CPY Maintenance time expired"
			::= { alarms1 73 }

			cPYNoWaterAl_1 OBJECT-TYPE
			SYNTAX INTEGER
			MAX-ACCESS read-only
			STATUS current
			DESCRIPTION "CPY No water"
			::= { alarms1 74 }

			cPYCylMaintAl_1 OBJECT-TYPE
			SYNTAX INTEGER
			MAX-ACCESS read-only
			STATUS current
			DESCRIPTION "CPY Cylinder maintenance"
			::= { alarms1 75 }

			cPYDirtyCylAl_1 OBJECT-TYPE
			SYNTAX INTEGER
			MAX-ACCESS read-only
			STATUS current
			DESCRIPTION "CPY Dirty cylinder"
			::= { alarms1 76 }

			cPYFoamAl_1 OBJECT-TYPE
			SYNTAX INTEGER
			MAX-ACCESS read-only
			STATUS current
			DESCRIPTION "CPY Foam presence"
			::= { alarms1 77 }

			cPYLifeTimeAl_1 OBJECT-TYPE
			SYNTAX INTEGER
			MAX-ACCESS read-only
			STATUS current
			DESCRIPTION "CPY Life time expired"
			::= { alarms1 78 }

			cPYHighWatLevAl_1 OBJECT-TYPE
			SYNTAX INTEGER
			MAX-ACCESS read-only
			STATUS current
			DESCRIPTION "CPY High water level"
			::= { alarms1 79 }

			cPYHighWatConductAl_1 OBJECT-TYPE
			SYNTAX INTEGER
			MAX-ACCESS read-only
			STATUS current
			DESCRIPTION "CPY High water conductivity"
			::= { alarms1 80 }

			cPYConnectionAl_1 OBJECT-TYPE
			SYNTAX INTEGER
			MAX-ACCESS read-only
			STATUS current
			DESCRIPTION "CPY Connection error"
			::= { alarms1 81 }

			fan1PowerAl_1 OBJECT-TYPE
			SYNTAX INTEGER
			MAX-ACCESS read-only
			STATUS current
			DESCRIPTION "Fan 1 phase/power supply down alarm"
			::= { alarms1 82 }

			fan1CommAl_1 OBJECT-TYPE
			SYNTAX INTEGER
			MAX-ACCESS read-only
			STATUS current
			DESCRIPTION "Fan 1 communication down"
			::= { alarms1 83 }

			fan1HighTempAl_1 OBJECT-TYPE
			SYNTAX INTEGER
			MAX-ACCESS read-only
			STATUS current
			DESCRIPTION "Fan 1 High regulation module temperature"
			::= { alarms1 84 }

			fan1NetComAl_1 OBJECT-TYPE
			SYNTAX INTEGER
			MAX-ACCESS read-only
			STATUS current
			DESCRIPTION "Fan 1 master-slave communication failure"
			::= { alarms1 85 }

			fan1InvRegAl_1 OBJECT-TYPE
			SYNTAX INTEGER
			MAX-ACCESS read-only
			STATUS current
			DESCRIPTION "Fan 1 regulation module malfunction"
			::= { alarms1 86 }

			fan1HighMotTempAl_1 OBJECT-TYPE
			SYNTAX INTEGER
			MAX-ACCESS read-only
			STATUS current
			DESCRIPTION "Fan 1 High motor temperature"
			::= { alarms1 87 }

			fan1HallSensAl_1 OBJECT-TYPE
			SYNTAX INTEGER
			MAX-ACCESS read-only
			STATUS current
			DESCRIPTION "Fan 1 Hall sensor error"
			::= { alarms1 88 }

			fan1OverloadAl_1 OBJECT-TYPE
			SYNTAX INTEGER
			MAX-ACCESS read-only
			STATUS current
			DESCRIPTION "Fan 1 overload motor"
			::= { alarms1 89 }

			fan1LowDCAl_1 OBJECT-TYPE
			SYNTAX INTEGER
			MAX-ACCESS read-only
			STATUS current
			DESCRIPTION "Fan 1 low DC power supply"
			::= { alarms1 94 }

			fan2PowerAl_1 OBJECT-TYPE
			SYNTAX INTEGER
			MAX-ACCESS read-only
			STATUS current
			DESCRIPTION "Fan 2 phase/power supply down alarm"
			::= { alarms1 95 }

			fan2CommAl_1 OBJECT-TYPE
			SYNTAX INTEGER
			MAX-ACCESS read-only
			STATUS current
			DESCRIPTION "Fan 2 communication down"
			::= { alarms1 96 }

			fan2HighTempAl_1 OBJECT-TYPE
			SYNTAX INTEGER
			MAX-ACCESS read-only
			STATUS current
			DESCRIPTION "Fan 2 High regulation module temperature"
			::= { alarms1 97 }

			fan2NetComAl_1 OBJECT-TYPE
			SYNTAX INTEGER
			MAX-ACCESS read-only
			STATUS current
			DESCRIPTION "Fan 2 master-slave communication failure"
			::= { alarms1 98 }

			fan2InvRegAl_1 OBJECT-TYPE
			SYNTAX INTEGER
			MAX-ACCESS read-only
			STATUS current
			DESCRIPTION "Fan 2 regulation module malfunction"
			::= { alarms1 99 }

			fan2HighMotTempAl_1 OBJECT-TYPE
			SYNTAX INTEGER
			MAX-ACCESS read-only
			STATUS current
			DESCRIPTION "Fan 2 High motor temperature"
			::= { alarms1 100 }

			fan2HallSensAl_1 OBJECT-TYPE
			SYNTAX INTEGER
			MAX-ACCESS read-only
			STATUS current
			DESCRIPTION "Fan 2 Hall sensor error"
			::= { alarms1 101 }

			fan2OverloadAl_1 OBJECT-TYPE
			SYNTAX INTEGER
			MAX-ACCESS read-only
			STATUS current
			DESCRIPTION "Fan 2 overload motor"
			::= { alarms1 102 }

			fan2LowDCAl_1 OBJECT-TYPE
			SYNTAX INTEGER
			MAX-ACCESS read-only
			STATUS current
			DESCRIPTION "Fan 2 low DC power supply"
			::= { alarms1 107 }

			fan3PowerAl_1 OBJECT-TYPE
			SYNTAX INTEGER
			MAX-ACCESS read-only
			STATUS current
			DESCRIPTION "Fan 3 phase/power supply down alarm"
			::= { alarms1 108 }

			fan3CommAl_1 OBJECT-TYPE
			SYNTAX INTEGER
			MAX-ACCESS read-only
			STATUS current
			DESCRIPTION "Fan 3 communication down"
			::= { alarms1 109 }

			fan3HighTempAl_1 OBJECT-TYPE
			SYNTAX INTEGER
			MAX-ACCESS read-only
			STATUS current
			DESCRIPTION "Fan 3 High regulation module temperature"
			::= { alarms1 110 }

			fan3NetComAl_1 OBJECT-TYPE
			SYNTAX INTEGER
			MAX-ACCESS read-only
			STATUS current
			DESCRIPTION "Fan 3 master-slave communication failure"
			::= { alarms1 111 }

			fan3InvReg_1 OBJECT-TYPE
			SYNTAX INTEGER
			MAX-ACCESS read-only
			STATUS current
			DESCRIPTION "Fan 3 regulation module malfunction"
			::= { alarms1 112 }

			fan3HighMotTempAl_1 OBJECT-TYPE
			SYNTAX INTEGER
			MAX-ACCESS read-only
			STATUS current
			DESCRIPTION "Fan 3 High motor temperature"
			::= { alarms1 113 }

			fan3HallSensAl_1 OBJECT-TYPE
			SYNTAX INTEGER
			MAX-ACCESS read-only
			STATUS current
			DESCRIPTION "Fan 3 Hall sensor error"
			::= { alarms1 114 }

			fan3OverloadAl_1 OBJECT-TYPE
			SYNTAX INTEGER
			MAX-ACCESS read-only
			STATUS current
			DESCRIPTION "Fan 3 overload motor"
			::= { alarms1 115 }

			fan3LowDCAl_1 OBJECT-TYPE
			SYNTAX INTEGER
			MAX-ACCESS read-only
			STATUS current
			DESCRIPTION "Fan 3 low DC power supply"
			::= { alarms1 120 }

			fan4PowerAl_1 OBJECT-TYPE
			SYNTAX INTEGER
			MAX-ACCESS read-only
			STATUS current
			DESCRIPTION "Fan 4 phase/power supply down alarm"
			::= { alarms1 121 }

			fan4CommAl_1 OBJECT-TYPE
			SYNTAX INTEGER
			MAX-ACCESS read-only
			STATUS current
			DESCRIPTION "Fan 4 communication down"
			::= { alarms1 122 }

			fan4HighTempAl_1 OBJECT-TYPE
			SYNTAX INTEGER
			MAX-ACCESS read-only
			STATUS current
			DESCRIPTION "Fan 4 High regulation module temperature"
			::= { alarms1 123 }

			fan4NetComAl_1 OBJECT-TYPE
			SYNTAX INTEGER
			MAX-ACCESS read-only
			STATUS current
			DESCRIPTION "Fan 4 master-slave communication failure"
			::= { alarms1 124 }

			fan4InvReg_1 OBJECT-TYPE
			SYNTAX INTEGER
			MAX-ACCESS read-only
			STATUS current
			DESCRIPTION "Fan 4 regulation module malfunction"
			::= { alarms1 125 }

			fan4HighMotTempAl_1 OBJECT-TYPE
			SYNTAX INTEGER
			MAX-ACCESS read-only
			STATUS current
			DESCRIPTION "Fan 4 High motor temperature"
			::= { alarms1 126 }

			fan4HallSensAl_1 OBJECT-TYPE
			SYNTAX INTEGER
			MAX-ACCESS read-only
			STATUS current
			DESCRIPTION "Fan 4 Hall sensor error"
			::= { alarms1 127 }

			fan4OverloadAl_1 OBJECT-TYPE
			SYNTAX INTEGER
			MAX-ACCESS read-only
			STATUS current
			DESCRIPTION "Fan 4 overload motor"
			::= { alarms1 128 }

			fan4LowDCAl_1 OBJECT-TYPE
			SYNTAX INTEGER
			MAX-ACCESS read-only
			STATUS current
			DESCRIPTION "Fan 4 low DC power supply"
			::= { alarms1 133 }

			fan5PowerAl_1 OBJECT-TYPE
			SYNTAX INTEGER
			MAX-ACCESS read-only
			STATUS current
			DESCRIPTION "Fan 5 phase/power supply down alarm"
			::= { alarms1 134 }

			fan5CommAl_1 OBJECT-TYPE
			SYNTAX INTEGER
			MAX-ACCESS read-only
			STATUS current
			DESCRIPTION "Fan 5 communication down"
			::= { alarms1 135 }

			fan5HighTempAl_1 OBJECT-TYPE
			SYNTAX INTEGER
			MAX-ACCESS read-only
			STATUS current
			DESCRIPTION "Fan 5 High regulation module temperature"
			::= { alarms1 136 }

			fan5NetComAl_1 OBJECT-TYPE
			SYNTAX INTEGER
			MAX-ACCESS read-only
			STATUS current
			DESCRIPTION "Fan 5 master-slave communication failure"
			::= { alarms1 137 }

			fan5InvReg_1 OBJECT-TYPE
			SYNTAX INTEGER
			MAX-ACCESS read-only
			STATUS current
			DESCRIPTION "Fan 5 regulation module malfunction"
			::= { alarms1 138 }

			fan5HighMotTempAl_1 OBJECT-TYPE
			SYNTAX INTEGER
			MAX-ACCESS read-only
			STATUS current
			DESCRIPTION "Fan 5 High motor temperature"
			::= { alarms1 139 }

			fan5HallSensAl_1 OBJECT-TYPE
			SYNTAX INTEGER
			MAX-ACCESS read-only
			STATUS current
			DESCRIPTION "Fan 5 Hall sensor error"
			::= { alarms1 140 }

			fan5OverloadAl_1 OBJECT-TYPE
			SYNTAX INTEGER
			MAX-ACCESS read-only
			STATUS current
			DESCRIPTION "Fan 5 overload motor"
			::= { alarms1 141 }

			fan5LowDCAl_1 OBJECT-TYPE
			SYNTAX INTEGER
			MAX-ACCESS read-only
			STATUS current
			DESCRIPTION "Fan 5 low DC power supply"
			::= { alarms1 146 }

			dFPSBrokenAl_1 OBJECT-TYPE
			SYNTAX INTEGER
			MAX-ACCESS read-only
			STATUS current
			DESCRIPTION "Dirty filter pressure sensor broken alarm"
			::= { alarms1 147 }

			dFPSCablingAl_1 OBJECT-TYPE
			SYNTAX INTEGER
			MAX-ACCESS read-only
			STATUS current
			DESCRIPTION "Dirty filter pressure sensor cabling alarm"
			::= { alarms1 148 }

			dFPSRangeAl_1 OBJECT-TYPE
			SYNTAX INTEGER
			MAX-ACCESS read-only
			STATUS current
			DESCRIPTION "Dirty filter pressure sensor range alarm"
			::= { alarms1 149 }

			dFPSADCAl_1 OBJECT-TYPE
			SYNTAX INTEGER
			MAX-ACCESS read-only
			STATUS current
			DESCRIPTION "Dirty filter pressure sensor ADC alarm"
			::= { alarms1 150 }

			dFPSSettingAl_1 OBJECT-TYPE
			SYNTAX INTEGER
			MAX-ACCESS read-only
			STATUS current
			DESCRIPTION "Dirty filter pressure sensor setting alarm"
			::= { alarms1 151 }

			dFPSDCOAl_1 OBJECT-TYPE
			SYNTAX INTEGER
			MAX-ACCESS read-only
			STATUS current
			DESCRIPTION "Dirty filter pressure sensor DCO alarm"
			::= { alarms1 152 }

			dFPSWatchdogAl_1 OBJECT-TYPE
			SYNTAX INTEGER
			MAX-ACCESS read-only
			STATUS current
			DESCRIPTION "Dirty filter pressure sensor watchdog alarm"
			::= { alarms1 153 }

			dFPSCommAl_1 OBJECT-TYPE
			SYNTAX INTEGER
			MAX-ACCESS read-only
			STATUS current
			DESCRIPTION "Dirty filter pressure sensor communication alarm"
			::= { alarms1 154 }

			invCompCommAlarm_1 OBJECT-TYPE
			SYNTAX INTEGER
			MAX-ACCESS read-only
			STATUS current
			DESCRIPTION "DC compressor inverter communication alarm"
			::= { alarms1 155 }
END
