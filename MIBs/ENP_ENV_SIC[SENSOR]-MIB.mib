------------------------------------------------------------
-- EMERSON NETWORK POWER
-- RDU-SIC G2 Device MIB. 
-- Using Generate Template V1.0
-- Copyright 2008-2015 Emerson Corporation.
-- All rights reserved.
------------------------------------------------------------

ENP_ENV_SIC-MIB DEFINITIONS ::= BEGIN

IMPORTS
	MODULE-IDENTITY, OBJECT-TYPE, NOTIFICATION-TYPE,Integer32, Counter32, enterprises	
		FROM SNMPv2-SMI
	TEXTUAL-CONVENTION, DisplayString, DateAndTime
		FROM SNMPv2-TC;
	
------------------------------------------------------------
-- Node definitions
------------------------------------------------------------
enp OBJECT IDENTIFIER ::= { enterprises 13400 }
	
products OBJECT IDENTIFIER ::= { enp 2 }

ENP_ENV_SIC MODULE-IDENTITY
	LAST-UPDATED "201309020955Z"
	ORGANIZATION "EMERSON NETWORK POWER (ENPC)"
	CONTACT-INFO "EMERSON NETWORK POWER"
	REVISION     "200"
	DESCRIPTION  "EMERSON NETWORK POWER (ENPC) For RDU-SIC G2 MIB."
	::= { products 503 }

------------------------------------------------------------
-- Textual conventions
------------------------------------------------------------

AlarmSeverity ::= TEXTUAL-CONVENTION
	STATUS current
	DESCRIPTION "
		The severity of the alarm. One of
		(1) informational
		(2) warning
		(3) critical"
	SYNTAX INTEGER {
		informational(1),
		warning(2),
		critical(3) }
		
AlarmStatusChange ::= TEXTUAL-CONVENTION
	STATUS current
	DESCRIPTION "
		Indicates 'activated' (0) or 'deactivated' (1) alarm events."
	SYNTAX INTEGER {
		activated(0),
		deactivated(1) }

------------------------------------------------------------
-- 1.1 Identification of the device { ENP_ENV_SIC 1 }
------------------------------------------------------------

ident OBJECT IDENTIFIER ::= { ENP_ENV_SIC 1 }
															
identManufacturer OBJECT-TYPE
	SYNTAX DisplayString
	MAX-ACCESS read-only
	STATUS current
	DESCRIPTION "
		The name of the device manufacturer."
	::= { ident 1 }

identModel OBJECT-TYPE
	SYNTAX DisplayString
	MAX-ACCESS read-only
	STATUS current
	DESCRIPTION "
		The manufacturers model designation of the device."
	::= { ident 2 }
	
identIndex OBJECT-TYPE
	SYNTAX Integer32
	MAX-ACCESS read-write
	STATUS current
	DESCRIPTION "
		The sequence number of the device."
	::= { ident 3 }

------------------------------------------------------------
-- 1.2 system values { ENP_ENV_SIC 2 }
------------------------------------------------------------
system OBJECT IDENTIFIER ::= { ENP_ENV_SIC 2 }
	
		
		

------------------------------------------------------------
--gourp2
------------------------------------------------------------
group2 OBJECT IDENTIFIER ::= { system 2 }
sensor0 OBJECT-TYPE
		SYNTAX INTEGER {
			temphumsensor(0),
			tempsensor(1),
			4digitalinputsensor(2),
			invalidequip(3)
 }
		MAX-ACCESS read-only
		STATUS current
		DESCRIPTION
		"sensor0, status."
		::= { group2 1}
temp0 OBJECT-TYPE
		SYNTAX Integer32
		
		MAX-ACCESS read-only
		STATUS current
		DESCRIPTION
		"temp0, stored as 0.1℃."
		::= { group2 2}
hum0 OBJECT-TYPE
		SYNTAX Integer32
		
		MAX-ACCESS read-only
		STATUS current
		DESCRIPTION
		"hum0, stored as 0.1."
		::= { group2 3}
temp0alarmstatus OBJECT-TYPE
		SYNTAX INTEGER {
			normal(0),
			hightemp(1),
			lowtemp(2),
			invalid(3)
 }
		MAX-ACCESS read-only
		STATUS current
		DESCRIPTION
		"temp0alarmstatus, status."
		::= { group2 4}
hum0alarmstatus OBJECT-TYPE
		SYNTAX INTEGER {
			normal(0),
			highhum(1),
			lowhum(2),
			invalid(3)
 }
		MAX-ACCESS read-only
		STATUS current
		DESCRIPTION
		"hum0alarmstatus, status."
		::= { group2 5}
sensor1 OBJECT-TYPE
		SYNTAX INTEGER {
			temphumsensor(0),
			tempsensor(1),
			4digitalinputsensor(2),
			invalidequip(3)
 }
		MAX-ACCESS read-only
		STATUS current
		DESCRIPTION
		"sensor1, status."
		::= { group2 6}
temp1 OBJECT-TYPE
		SYNTAX Integer32
		
		MAX-ACCESS read-only
		STATUS current
		DESCRIPTION
		"temp1, stored as 0.1℃."
		::= { group2 7}
hum1 OBJECT-TYPE
		SYNTAX Integer32
		
		MAX-ACCESS read-only
		STATUS current
		DESCRIPTION
		"hum1, stored as 0.1."
		::= { group2 8}
temp1alarmstatus OBJECT-TYPE
		SYNTAX INTEGER {
			normal(0),
			hightemp(1),
			lowtemp(2),
			invalid(3)
 }
		MAX-ACCESS read-only
		STATUS current
		DESCRIPTION
		"temp1alarmstatus, status."
		::= { group2 9}
hum1alarmstatus OBJECT-TYPE
		SYNTAX INTEGER {
			normal(0),
			highhum(1),
			lowhum(2),
			invalid(3)
 }
		MAX-ACCESS read-only
		STATUS current
		DESCRIPTION
		"hum1alarmstatus, status."
		::= { group2 10}
sensor2 OBJECT-TYPE
		SYNTAX INTEGER {
			temphumsensor(0),
			tempsensor(1),
			4digitalinputsensor(2),
			invalidequip(3)
 }
		MAX-ACCESS read-only
		STATUS current
		DESCRIPTION
		"sensor2, status."
		::= { group2 11}
temp2 OBJECT-TYPE
		SYNTAX Integer32
		
		MAX-ACCESS read-only
		STATUS current
		DESCRIPTION
		"temp2, stored as 0.1℃."
		::= { group2 12}
hum2 OBJECT-TYPE
		SYNTAX Integer32
		
		MAX-ACCESS read-only
		STATUS current
		DESCRIPTION
		"hum2, stored as 0.1."
		::= { group2 13}
temp2alarmstatus OBJECT-TYPE
		SYNTAX INTEGER {
			normal(0),
			hightemp(1),
			lowtemp(2),
			invalid(3)
 }
		MAX-ACCESS read-only
		STATUS current
		DESCRIPTION
		"temp2alarmstatus, status."
		::= { group2 14}
hum2alarmstatus OBJECT-TYPE
		SYNTAX INTEGER {
			normal(0),
			highhum(1),
			lowhum(2),
			invalid(3)
 }
		MAX-ACCESS read-only
		STATUS current
		DESCRIPTION
		"hum2alarmstatus, status."
		::= { group2 15}
sensor3 OBJECT-TYPE
		SYNTAX INTEGER {
			temphumsensor(0),
			tempsensor(1),
			4digitalinputsensor(2),
			invalidequip(3)
 }
		MAX-ACCESS read-only
		STATUS current
		DESCRIPTION
		"sensor3, status."
		::= { group2 16}
temp3 OBJECT-TYPE
		SYNTAX Integer32
		
		MAX-ACCESS read-only
		STATUS current
		DESCRIPTION
		"temp3, stored as 0.1℃."
		::= { group2 17}
hum3 OBJECT-TYPE
		SYNTAX Integer32
		
		MAX-ACCESS read-only
		STATUS current
		DESCRIPTION
		"hum3, stored as 0.1."
		::= { group2 18}
temp3alarmstatus OBJECT-TYPE
		SYNTAX INTEGER {
			normal(0),
			hightemp(1),
			lowtemp(2),
			invalid(3)
 }
		MAX-ACCESS read-only
		STATUS current
		DESCRIPTION
		"temp3alarmstatus, status."
		::= { group2 19}
hum3alarmstatus OBJECT-TYPE
		SYNTAX INTEGER {
			normal(0),
			highhum(1),
			lowhum(2),
			invalid(3)
 }
		MAX-ACCESS read-only
		STATUS current
		DESCRIPTION
		"hum3alarmstatus, status."
		::= { group2 20}
sensor0 OBJECT-TYPE
		SYNTAX INTEGER {
			temphumsensor(0),
			tempsensor(1),
			4digitalinputsensor(2),
			invalidequip(3)
 }
		MAX-ACCESS read-only
		STATUS current
		DESCRIPTION
		"sensor0, status."
		::= { group2 21}
door01 OBJECT-TYPE
		SYNTAX INTEGER {
			normal(0),
			alarm(1),
			uninstall(2),
			leave(3)
 }
		MAX-ACCESS read-only
		STATUS current
		DESCRIPTION
		"door01, status."
		::= { group2 22}
door02 OBJECT-TYPE
		SYNTAX INTEGER {
			normal(0),
			alarm(1),
			uninstall(2),
			leave(3)
 }
		MAX-ACCESS read-only
		STATUS current
		DESCRIPTION
		"door02, status."
		::= { group2 23}
warter0 OBJECT-TYPE
		SYNTAX INTEGER {
			normal(0),
			alarm(1),
			uninstall(2),
			leave(3)
 }
		MAX-ACCESS read-only
		STATUS current
		DESCRIPTION
		"warter0, status."
		::= { group2 24}
smoke0 OBJECT-TYPE
		SYNTAX INTEGER {
			normal(0),
			alarm(1),
			uninstall(2),
			leave(3)
 }
		MAX-ACCESS read-only
		STATUS current
		DESCRIPTION
		"smoke0, status."
		::= { group2 25}
sensor1 OBJECT-TYPE
		SYNTAX INTEGER {
			temphumsensor(0),
			tempsensor(1),
			4digitalinputsensor(2),
			invalidequip(3)
 }
		MAX-ACCESS read-only
		STATUS current
		DESCRIPTION
		"sensor1, status."
		::= { group2 26}
door11 OBJECT-TYPE
		SYNTAX INTEGER {
			normal(0),
			alarm(1),
			uninstall(2),
			leave(3)
 }
		MAX-ACCESS read-only
		STATUS current
		DESCRIPTION
		"door11, status."
		::= { group2 27}
door12 OBJECT-TYPE
		SYNTAX INTEGER {
			normal(0),
			alarm(1),
			uninstall(2),
			leave(3)
 }
		MAX-ACCESS read-only
		STATUS current
		DESCRIPTION
		"door12, status."
		::= { group2 28}
warter1 OBJECT-TYPE
		SYNTAX INTEGER {
			normal(0),
			alarm(1),
			uninstall(2),
			leave(3)
 }
		MAX-ACCESS read-only
		STATUS current
		DESCRIPTION
		"warter1, status."
		::= { group2 29}
smoke1 OBJECT-TYPE
		SYNTAX INTEGER {
			normal(0),
			alarm(1),
			uninstall(2),
			leave(3)
 }
		MAX-ACCESS read-only
		STATUS current
		DESCRIPTION
		"smoke1, status."
		::= { group2 30}
communicationstatus OBJECT-TYPE
		SYNTAX INTEGER {
			normal(0),
			failure(1)
 }
		MAX-ACCESS read-only
		STATUS current
		DESCRIPTION
		"communicationstatus, status."
		::= { group2 31}

------------------------------------------------------------
--gourp3
------------------------------------------------------------
group3 OBJECT IDENTIFIER ::= { system 3 }
uninstalldi0 OBJECT-TYPE
		SYNTAX INTEGER {
			door1di1(0),
			door2di2(1),
			waterdi3(2),
			smokedi4(3),
			alldi(4)
 }
		MAX-ACCESS read-write
		STATUS current
		DESCRIPTION
		"uninstalldi0, status."
		::= { group3 1}
uninstalldi1 OBJECT-TYPE
		SYNTAX INTEGER {
			door1di1(0),
			door2di2(1),
			waterdi3(2),
			smokedi4(3),
			alldi(4)
 }
		MAX-ACCESS read-write
		STATUS current
		DESCRIPTION
		"uninstalldi1, status."
		::= { group3 2}

------------------------------------------------------------
--gourp4
------------------------------------------------------------
group4 OBJECT IDENTIFIER ::= { system 4 }
hightemp0alarmlimit OBJECT-TYPE
		SYNTAX Integer32
		
		MAX-ACCESS read-write
		STATUS current
		DESCRIPTION
		"hightemp0alarmlimit, stored as 0.1℃."
		::= { group4 1}
lowtemp0alarmlimit OBJECT-TYPE
		SYNTAX Integer32
		
		MAX-ACCESS read-write
		STATUS current
		DESCRIPTION
		"lowtemp0alarmlimit, stored as 0.1℃."
		::= { group4 2}
highhum0alarmlimit OBJECT-TYPE
		SYNTAX Integer32
		
		MAX-ACCESS read-write
		STATUS current
		DESCRIPTION
		"highhum0alarmlimit, stored as 0.1."
		::= { group4 3}
lowhum0alarmlimit OBJECT-TYPE
		SYNTAX Integer32
		
		MAX-ACCESS read-write
		STATUS current
		DESCRIPTION
		"lowhum0alarmlimit, stored as 0.1."
		::= { group4 4}
hightemp1alarmlimit OBJECT-TYPE
		SYNTAX Integer32
		
		MAX-ACCESS read-write
		STATUS current
		DESCRIPTION
		"hightemp1alarmlimit, stored as 0.1℃."
		::= { group4 5}
lowtemp1alarmlimit OBJECT-TYPE
		SYNTAX Integer32
		
		MAX-ACCESS read-write
		STATUS current
		DESCRIPTION
		"lowtemp1alarmlimit, stored as 0.1℃."
		::= { group4 6}
highhum1alarmlimit OBJECT-TYPE
		SYNTAX Integer32
		
		MAX-ACCESS read-write
		STATUS current
		DESCRIPTION
		"highhum1alarmlimit, stored as 0.1."
		::= { group4 7}
lowhum1alarmlimit OBJECT-TYPE
		SYNTAX Integer32
		
		MAX-ACCESS read-write
		STATUS current
		DESCRIPTION
		"lowhum1alarmlimit, stored as 0.1."
		::= { group4 8}
hightemp2alarmlimit OBJECT-TYPE
		SYNTAX Integer32
		
		MAX-ACCESS read-write
		STATUS current
		DESCRIPTION
		"hightemp2alarmlimit, stored as 0.1℃."
		::= { group4 9}
lowtemp2alarmlimit OBJECT-TYPE
		SYNTAX Integer32
		
		MAX-ACCESS read-write
		STATUS current
		DESCRIPTION
		"lowtemp2alarmlimit, stored as 0.1℃."
		::= { group4 10}
highhum2alarmlimit OBJECT-TYPE
		SYNTAX Integer32
		
		MAX-ACCESS read-write
		STATUS current
		DESCRIPTION
		"highhum2alarmlimit, stored as 0.1."
		::= { group4 11}
lowhum2alarmlimit OBJECT-TYPE
		SYNTAX Integer32
		
		MAX-ACCESS read-write
		STATUS current
		DESCRIPTION
		"lowhum2alarmlimit, stored as 0.1."
		::= { group4 12}
hightemp3alarmlimit OBJECT-TYPE
		SYNTAX Integer32
		
		MAX-ACCESS read-write
		STATUS current
		DESCRIPTION
		"hightemp3alarmlimit, stored as 0.1℃."
		::= { group4 13}
lowtemp3alarmlimit OBJECT-TYPE
		SYNTAX Integer32
		
		MAX-ACCESS read-write
		STATUS current
		DESCRIPTION
		"lowtemp3alarmlimit, stored as 0.1℃."
		::= { group4 14}
highhum3alarmlimit OBJECT-TYPE
		SYNTAX Integer32
		
		MAX-ACCESS read-write
		STATUS current
		DESCRIPTION
		"highhum3alarmlimit, stored as 0.1."
		::= { group4 15}
lowhum3alarmlimit OBJECT-TYPE
		SYNTAX Integer32
		
		MAX-ACCESS read-write
		STATUS current
		DESCRIPTION
		"lowhum3alarmlimit, stored as 0.1."
		::= { group4 16}
door01criterion OBJECT-TYPE
		SYNTAX INTEGER {
			openalarm(0),
			closedalarm(1)
 }
		MAX-ACCESS read-write
		STATUS current
		DESCRIPTION
		"door01criterion, status."
		::= { group4 17}
door02criterion OBJECT-TYPE
		SYNTAX INTEGER {
			openalarm(0),
			closedalarm(1)
 }
		MAX-ACCESS read-write
		STATUS current
		DESCRIPTION
		"door02criterion, status."
		::= { group4 18}
warter0criterion OBJECT-TYPE
		SYNTAX INTEGER {
			openalarm(0),
			closedalarm(1)
 }
		MAX-ACCESS read-write
		STATUS current
		DESCRIPTION
		"warter0criterion, status."
		::= { group4 19}
smoke0criterion OBJECT-TYPE
		SYNTAX INTEGER {
			openalarm(0),
			closedalarm(1)
 }
		MAX-ACCESS read-write
		STATUS current
		DESCRIPTION
		"smoke0criterion, status."
		::= { group4 20}
door11criterion OBJECT-TYPE
		SYNTAX INTEGER {
			openalarm(0),
			closedalarm(1)
 }
		MAX-ACCESS read-write
		STATUS current
		DESCRIPTION
		"door11criterion, status."
		::= { group4 21}
door12criterion OBJECT-TYPE
		SYNTAX INTEGER {
			openalarm(0),
			closedalarm(1)
 }
		MAX-ACCESS read-write
		STATUS current
		DESCRIPTION
		"door12criterion, status."
		::= { group4 22}
warter1criterion OBJECT-TYPE
		SYNTAX INTEGER {
			openalarm(0),
			closedalarm(1)
 }
		MAX-ACCESS read-write
		STATUS current
		DESCRIPTION
		"warter1criterion, status."
		::= { group4 23}
smoke1criterion OBJECT-TYPE
		SYNTAX INTEGER {
			openalarm(0),
			closedalarm(1)
 }
		MAX-ACCESS read-write
		STATUS current
		DESCRIPTION
		"smoke1criterion, status."
		::= { group4 24}
------------------------------------------------------------
-- 3 Alarm trap table 
-- If you want to know the equipment trap list detail,
-- Please find a Excel file named "RDU-SIC G2 trap table";
------------------------------------------------------------

alarmTrapTable OBJECT-TYPE
	SYNTAX SEQUENCE OF AlarmTrapEntry
	MAX-ACCESS not-accessible
	STATUS current
	DESCRIPTION "
		Table holding information about the submitted alarm traps."
	::= { ENP_ENV_SIC  3 }

alarmTrapEntry OBJECT-TYPE
	SYNTAX AlarmTrapEntry
	MAX-ACCESS not-accessible
	STATUS current
	DESCRIPTION "
		An entry (conceptual row) in the alarmTrapTable."
	INDEX { alarmIndex }
	::= { alarmTrapTable 1 }

AlarmTrapEntry ::= SEQUENCE {
	alarmIndex Counter32,
	alarmTime DisplayString,
	alarmStatusChange StatusChange,
	alarmSeverity Status,
	alarmDescription DisplayString,
	alarmId Integer32 }

alarmIndex OBJECT-TYPE
	SYNTAX Counter32
	MAX-ACCESS read-only
	STATUS current
	DESCRIPTION "
		The unique sequence number of this alarm trap."
	::= { alarmTrapEntry 1 }

alarmTime OBJECT-TYPE
	SYNTAX DisplayString
	MAX-ACCESS read-only
	STATUS current
	DESCRIPTION "
		Date and time when event occured."
	::= { alarmTrapEntry 2 }

alarmStatusChange OBJECT-TYPE
	SYNTAX StatusChange
	MAX-ACCESS read-only
	STATUS current
	DESCRIPTION "
		Indicates 'activated' (0) or 'deactivated' (1) alarm events."
	::= { alarmTrapEntry 3 }

alarmSeverity OBJECT-TYPE
	SYNTAX Status
	MAX-ACCESS read-only
	STATUS current
	DESCRIPTION "
		The severity of the alarm. One of
		(0) informational
		(1) warning
		(2) critical"
	::= { alarmTrapEntry 4 }
	
alarmDescription OBJECT-TYPE
	SYNTAX DisplayString
	MAX-ACCESS read-only
	STATUS current
	DESCRIPTION "
		Free-text description of alarm."
	::= { alarmTrapEntry 5 }
	
alarmId OBJECT-TYPE
	SYNTAX Integer32
	MAX-ACCESS read-only
	STATUS current
	DESCRIPTION "
		Alarm Index in system."
	::= { alarmTrapEntry 6 }

	
	
------------------------------------------------------------
-- System Alarm Trap Define
------------------------------------------------------------

systemAlarmTrap OBJECT IDENTIFIER ::= { ENP_ENV_SIC 4 }

systemAlarmTrapFormatDefine NOTIFICATION-TYPE
	OBJECTS {
		systemAlarmIndex,
		systemAlarmTime,
		systemAlarmStatusChange,
		systemAlarmSeverity,
		systemAlarmDescription,
		systemAlarmId,
		systemAlarmEquipId,
		systemAlarmEquipTypeId }
	STATUS current
	DESCRIPTION "
		An alarm trap is sent when an alarm occurs (activated) or
		returns to normal state (deactivated). Alarm traps are logged
		in alarmTrapTable. Variables in this trap:
		* systemAlarmIndex - The unique sequence number of this alarm trap.
		* systemAlarmTime - Date and time when event occured (local time).
		* systemAlarmStatusChange - (0) activated or (1) deactivated.
		* systemAlarmSeverity - The severity of the alarm..
		* systemAlarmId - Alarm id.
		* systemAlarmEquipId - Alarm equipment id.
		* systemAlarmEquipTypeId - Alarm equipment type id."
	::= { systemAlarmTrap 1 }
	
	
------------------------------------------------------------
-- End of MIB definitions
------------------------------------------------------------
END
