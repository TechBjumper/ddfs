GEISTMFG-EM8GM214-MIB DEFINITIONS ::= BEGIN

IMPORTS
	MODULE-IDENTITY, OBJECT-TYPE, enterprises, Unsigned32 FROM SNMPv2-SMI;

geistmfg MODULE-IDENTITY
	LAST-UPDATED "200612140000Z"
	ORGANIZATION "Geist Manufacturing"
	CONTACT-INFO "support@geistmfg.com/800.432.3219"
	DESCRIPTION "The MIB for EM8/GM2-14"
	::= { enterprises 21239 }
	

em8gm214 OBJECT IDENTIFIER
	::=  { geistmfg 13 }


productInfo OBJECT IDENTIFIER
	::= { em8gm214 1 }

totalDeciAmps OBJECT IDENTIFIER
	::= { em8gm214 2 }




productTitle    OBJECT-TYPE
   SYNTAX DisplayString
   ACCESS read-only
   STATUS mandatory
   DESCRIPTION
      "Name of product"
   ::= { productInfo 1 }
   
productVersion    OBJECT-TYPE
   SYNTAX DisplayString
   ACCESS read-only
   STATUS mandatory
   DESCRIPTION
      "Firmware version"
   ::= { productInfo 2 }

productName    OBJECT-TYPE
   SYNTAX DisplayString
   ACCESS read-only
   STATUS mandatory
   DESCRIPTION
      "Unit friendly name"
   ::= { productInfo 3 }

productMAC    OBJECT-TYPE
   SYNTAX DisplayString
   ACCESS read-only
   STATUS mandatory
   DESCRIPTION
      "Unit MAC address"
   ::= { productInfo 4 }

productIP    OBJECT-TYPE
   SYNTAX DisplayString
   ACCESS read-only
   STATUS mandatory
   DESCRIPTION
      "IP address of the unit"
   ::= { productInfo 5 }




totalDeciAmpsCircuit1   OBJECT-TYPE
   SYNTAX INTEGER(0..300)
   UNITS "0.1 Amps"
   ACCESS read-only
   STATUS mandatory
   DESCRIPTION
   "Total Amps consumed by Circuit1, in units of 0.1 amps"
   ::= { totalDeciAmps 1 }

totalDeciAmpsCircuit2   OBJECT-TYPE
   SYNTAX INTEGER(0..300)
   UNITS "0.1 Amps"
   ACCESS read-only
   STATUS mandatory
   DESCRIPTION
   "Total Amps consumed by Circuit2, in units of 0.1 amps"
   ::= { totalDeciAmps 2 }



totalDeciAmpsCircuit1TRAP TRAP-TYPE
ENTERPRISE geistmfg
VARIABLES { totalDeciAmpsCircuit1 }
DESCRIPTION "Amps Circuit1 Trap"
::= 1

totalDeciAmpsCircuit2TRAP TRAP-TYPE
ENTERPRISE geistmfg
VARIABLES { totalDeciAmpsCircuit2 }
DESCRIPTION "Amps Circuit2 Trap"
::= 2





END
