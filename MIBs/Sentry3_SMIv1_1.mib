Sentry3-MIB DEFINITIONS ::= BEGIN

IMPORTS
    TRAP-TYPE
        FROM RFC-1215
    DisplayString
        FROM RFC1213-MIB
    OBJECT-TYPE
        FROM RFC-1212
    enterprises
        FROM RFC1155-SMI;

serverTech OBJECT IDENTIFIER ::= { enterprises  1718 }

-- created from sentry3 (200707091445Z)

sentry3 OBJECT IDENTIFIER ::= { serverTech  3 }

systemGroup OBJECT IDENTIFIER ::= { sentry3  1 }

systemTables OBJECT IDENTIFIER ::= { sentry3  2 }

systemVersion OBJECT-TYPE
    SYNTAX  DisplayString
    ACCESS  read-only
    STATUS  mandatory
    DESCRIPTION
           "The firmware version of the system."
    ::= { systemGroup  1 }

systemNICSerialNumber OBJECT-TYPE
    SYNTAX  DisplayString
    ACCESS  read-only
    STATUS  mandatory
    DESCRIPTION
           "The serial number of the network interface card in the
             system."
    ::= { systemGroup  2 }

systemLocation OBJECT-TYPE
    SYNTAX  DisplayString
    ACCESS  read-write
    STATUS  mandatory
    DESCRIPTION
           "The location of the system."
    ::= { systemGroup  3 }

systemTowerCount OBJECT-TYPE
    SYNTAX  INTEGER
    ACCESS  read-only
    STATUS  mandatory
    DESCRIPTION
           "The number of towers in the system."
    ::= { systemGroup  4 }

systemEnvMonCount OBJECT-TYPE
    SYNTAX  INTEGER
    ACCESS  read-only
    STATUS  mandatory
    DESCRIPTION
           "The number of environmental monitors in the system."
    ::= { systemGroup  5 }

systemTotalPower OBJECT-TYPE
    SYNTAX  INTEGER
    ACCESS  read-only
    STATUS  mandatory
    DESCRIPTION
           "The total power comsumption of all of the input feeds in the
             system.  A non-negative value indicates the total power
             compsumption in Watts.  A negative value indicates that the
             total power comsumption was not available."
    ::= { systemGroup  6 }

systemArea OBJECT-TYPE
    SYNTAX  INTEGER
    ACCESS  read-only
    STATUS  mandatory
    DESCRIPTION
           "The area that the footprint of the system occupies.  A
             non-zero non-negative value indicates the area in tenths of
             square feet.  A zero or negative value indicates that the
             area was not available."
    ::= { systemGroup  7 }

systemWattsPerUnitArea OBJECT-TYPE
    SYNTAX  INTEGER
    ACCESS  read-only
    STATUS  mandatory
    DESCRIPTION
           "The system Watts per square foot of area.  A non-negative
             value indicates the power consumption per unit area in Watts
             per square foot.  A negative value indicates that the power
             consumption per unit area was not available."
    ::= { systemGroup  8 }

towerTable OBJECT-TYPE
    SYNTAX  SEQUENCE OF TowerEntry
    ACCESS  not-accessible
    STATUS  mandatory
    DESCRIPTION
           "A table of towers."
    ::= { systemTables  1 }

towerEntry OBJECT-TYPE
    SYNTAX  TowerEntry
    ACCESS  not-accessible
    STATUS  mandatory
    DESCRIPTION
           "Row definition for the tower table."
    INDEX   { towerIndex }
    ::= { towerTable  1 }

TowerEntry ::=
    SEQUENCE {
        towerIndex
            INTEGER,

        towerID
            DisplayString,

        towerName
            DisplayString,

        towerStatus
            INTEGER,

        towerInfeedCount
            INTEGER,

        towerProductSN
            DisplayString,

        towerModelNumber
            DisplayString,

        towerCapabilities
            OCTET STRING,
    }

towerIndex OBJECT-TYPE
    SYNTAX  INTEGER(0..4)
    ACCESS  not-accessible
    STATUS  mandatory
    DESCRIPTION
           "Index for the tower table."
    ::= { towerEntry  1 }

towerID OBJECT-TYPE
    SYNTAX  DisplayString
    ACCESS  read-only
    STATUS  mandatory
    DESCRIPTION
           "The ID of the tower."
    ::= { towerEntry  2 }

towerName OBJECT-TYPE
    SYNTAX  DisplayString
    ACCESS  read-write
    STATUS  mandatory
    DESCRIPTION
           "The name of the tower."
    ::= { towerEntry  3 }

towerStatus OBJECT-TYPE
    SYNTAX  INTEGER {
                 normal(0),
                 noComm(1),
                 fanFail(2),
                 overTemp(3)
               }
    ACCESS  read-only
    STATUS  mandatory
    DESCRIPTION
           "The operational status of the tower."
    ::= { towerEntry  4 }

towerInfeedCount OBJECT-TYPE
    SYNTAX  INTEGER
    ACCESS  read-only
    STATUS  mandatory
    DESCRIPTION
           "The number of input feeds on the tower."
    ::= { towerEntry  5 }

towerProductSN OBJECT-TYPE
    SYNTAX  DisplayString
    ACCESS  read-only
    STATUS  mandatory
    DESCRIPTION
           "The product serial number of the tower."
    ::= { towerEntry  6 }

towerModelNumber OBJECT-TYPE
    SYNTAX  DisplayString
    ACCESS  read-only
    STATUS  mandatory
    DESCRIPTION
           "The model number of the tower."
    ::= { towerEntry  7 }

towerCapabilities OBJECT-TYPE
    SYNTAX  OCTET STRING
    ACCESS  read-only
    STATUS  mandatory
    DESCRIPTION
           "The capabilities of the tower.  The value of this object is
             encoded per the BITS pseudotype (draft-perkins-bits-00.txt)
             with these enumerated bit positions: failSafe(0),
             fuseSense(1), directCurrent(2), threePhase(3), fanSense(4),
             and tempSense(5)."
    ::= { towerEntry  8 }

infeedTable OBJECT-TYPE
    SYNTAX  SEQUENCE OF InfeedEntry
    ACCESS  not-accessible
    STATUS  mandatory
    DESCRIPTION
           "A table of input feeds."
    ::= { systemTables  2 }

infeedEntry OBJECT-TYPE
    SYNTAX  InfeedEntry
    ACCESS  not-accessible
    STATUS  mandatory
    DESCRIPTION
           "Row definition for the input feed table."
    INDEX   { towerIndex, infeedIndex }
    ::= { infeedTable  1 }

InfeedEntry ::=
    SEQUENCE {
        infeedIndex
            INTEGER,

        infeedID
            DisplayString,

        infeedName
            DisplayString,

        infeedCapabilities
            OCTET STRING,

        infeedStatus
            INTEGER,

        infeedLoadStatus
            INTEGER,

        infeedLoadValue
            INTEGER,

        infeedLoadHighThresh
            INTEGER,

        infeedOutletCount
            INTEGER,

        infeedCapacity
            INTEGER,

        infeedVoltage
            INTEGER,

        infeedPower
            INTEGER
    }

infeedIndex OBJECT-TYPE
    SYNTAX  INTEGER(0..4)
    ACCESS  not-accessible
    STATUS  mandatory
    DESCRIPTION
           "Index for the input feed table."
    ::= { infeedEntry  1 }

infeedID OBJECT-TYPE
    SYNTAX  DisplayString
    ACCESS  read-only
    STATUS  mandatory
    DESCRIPTION
           "The ID of the input feed."
    ::= { infeedEntry  2 }

infeedName OBJECT-TYPE
    SYNTAX  DisplayString
    ACCESS  read-write
    STATUS  mandatory
    DESCRIPTION
           "The name of the input feed."
    ::= { infeedEntry  3 }

infeedCapabilities OBJECT-TYPE
    SYNTAX  OCTET STRING
    ACCESS  read-only
    STATUS  mandatory
    DESCRIPTION
           "The capabilities of the input feed.  The value of this object
             is encoded per the BITS pseudotype (draft-perkins-bits-00.txt)
             with these enumerated bit positions: onSense(0), loadSense(1),
             powerControl(2), failSafe(3), and defaultOff(4)."
    ::= { infeedEntry  4 }

infeedStatus OBJECT-TYPE
    SYNTAX  INTEGER {
                 off(0),
                 on(1),
                 offWait(2),
                 onWait(3),
                 offError(4),
                 onError(5),
                 noComm(6)
               }
    ACCESS  read-only
    STATUS  mandatory
    DESCRIPTION
           "The status of the input feed.  If the infeedCapabilities
             'onSense' bit is TRUE, then all of the states are supported
             and indicate the sensed state of the input feed.  If the
             infeedCapabilities 'onSense' bit is FALSE, then only the
             'on' and 'noComm' states are supported, and 'on' indicates
             a derived state, not a sensed state."
    ::= { infeedEntry  5 }

infeedLoadStatus OBJECT-TYPE
    SYNTAX  INTEGER {
                 normal(0),
                 notOn(1),
                 reading(2),
                 loadLow(3),
                 loadHigh(4),
                 overLoad(5),
                 readError(6),
                 noComm(7)
               }
    ACCESS  read-only
    STATUS  mandatory
    DESCRIPTION
           "The status of the load measured on the input feed.  If the
             infeedCapabilities 'loadSense' bit is TRUE, then all of the
             states are supported.  If the infeedCapabilities 'loadSense'
             bit is FALSE, then only the 'normal' and 'noComm' states are
             supported."
    ::= { infeedEntry  6 }

infeedLoadValue OBJECT-TYPE
    SYNTAX  INTEGER
    ACCESS  read-only
    STATUS  mandatory
    DESCRIPTION
           "The load measured on the input feed.  A non-negative value
             indicates the measured load in hundredths of Amps.  A
             negative value indicates that a load value was not able to
             be measured."
    ::= { infeedEntry  7 }

infeedLoadHighThresh OBJECT-TYPE
    SYNTAX  INTEGER
    ACCESS  read-write
    STATUS  mandatory
    DESCRIPTION
           "The load high threshold value of the input feed in Amps."
    ::= { infeedEntry  8 }

infeedOutletCount OBJECT-TYPE
    SYNTAX  INTEGER
    ACCESS  read-only
    STATUS  mandatory
    DESCRIPTION
           "The number of outlets on the input feed."
    ::= { infeedEntry  9 }

infeedCapacity OBJECT-TYPE
    SYNTAX  INTEGER
    ACCESS  read-only
    STATUS  mandatory
    DESCRIPTION
           "The voltage of the input feed.  A non-negative value
             indicates the voltage in tenths of Volts.  A negative
             value indicates that the voltage was not available."
    ::= { infeedEntry  10 }

infeedVoltage OBJECT-TYPE
    SYNTAX  INTEGER
    ACCESS  read-only
    STATUS  mandatory
    DESCRIPTION
           "The load capacity of the input feed.  A non-negative
             value indicates the maximum load in Amps.  A negative
             value indicates that the capacity was not available."
    ::= { infeedEntry  11 }

infeedPower OBJECT-TYPE
    SYNTAX  INTEGER
    ACCESS  read-only
    STATUS  mandatory
    DESCRIPTION
           "The power consumption of the input feed.  A non-negative
             value indicates the power consumption in Watts.  A negative
             value indicates that the power consumption was not
             available."
    ::= { infeedEntry  12 }

outletTable OBJECT-TYPE
    SYNTAX  SEQUENCE OF OutletEntry
    ACCESS  not-accessible
    STATUS  mandatory
    DESCRIPTION
           "A table of outlets."
    ::= { systemTables  3 }

outletEntry OBJECT-TYPE
    SYNTAX  OutletEntry
    ACCESS  not-accessible
    STATUS  mandatory
    DESCRIPTION
           "Row definition for the outlet table."
    INDEX   { towerIndex, infeedIndex, outletIndex }
    ::= { outletTable  1 }

OutletEntry ::=
    SEQUENCE {
        outletIndex
            INTEGER,

        outletID
            DisplayString,

        outletName
            DisplayString,

        outletCapabilities
            OCTET STRING,

        outletStatus
            INTEGER,

        outletLoadStatus
            INTEGER,

        outletLoadValue
            INTEGER,

        outletLoadLowThresh
            INTEGER,

        outletLoadHighThresh
            INTEGER,

        outletControlState
            INTEGER,

        outletControlAction
            INTEGER
    }

outletIndex OBJECT-TYPE
    SYNTAX  INTEGER(0..16)
    ACCESS  not-accessible
    STATUS  mandatory
    DESCRIPTION
           "Index for the outlet table."
    ::= { outletEntry  1 }

outletID OBJECT-TYPE
    SYNTAX  DisplayString
    ACCESS  read-only
    STATUS  mandatory
    DESCRIPTION
           "The ID of the outlet."
    ::= { outletEntry  2 }

outletName OBJECT-TYPE
    SYNTAX  DisplayString
    ACCESS  read-write
    STATUS  mandatory
    DESCRIPTION
           "The name of the outlet."
    ::= { outletEntry  3 }

outletCapabilities OBJECT-TYPE
    SYNTAX  OCTET STRING
    ACCESS  read-only
    STATUS  mandatory
    DESCRIPTION
           "The capabilities of the outlet.  The value of this object
             is encoded per the BITS pseudotype (draft-perkins-bits-00.txt)
             with these enumerated bit positions: onSense(0), loadSense(1),
             powerControl(2), shutdown(3), defaultOn(4), ownInfeed(5), and
             fusedBranch(6)."
    ::= { outletEntry  4 }

outletStatus OBJECT-TYPE
    SYNTAX  INTEGER {
                 off(0),
                 on(1),
                 offWait(2),
                 onWait(3),
                 offError(4),
                 onError(5),
                 noComm(6),
                 reading(7),
                 offFuse(8),
                 onFuse(9)
               }
    ACCESS  read-only
    STATUS  mandatory
    DESCRIPTION
           "The status of the outlet.  If the outletCapabilities
             'onSense' bit is TRUE, then the state indicates the sensed
             state of the outlet, not a derived state, and 'offError'
             and 'onError' are supported to indicate a mismatch between
             the control and sensed state.  If the outletCapabilities
             'fusedBranch' bit is TRUE, then the outlet is on a fused
             branch circuit that can detect the fuse state, and 'offFuse'
             and 'onFuse' are supported to indicate a fuse error."
    ::= { outletEntry  5 }

outletLoadStatus OBJECT-TYPE
    SYNTAX  INTEGER {
                 normal(0),
                 notOn(1),
                 reading(2),
                 loadLow(3),
                 loadHigh(4),
                 overLoad(5),
                 readError(6),
                 noComm(7)
               }
    ACCESS  read-only
    STATUS  mandatory
    DESCRIPTION
           "The status of the load measured on the outlet.  If the 
             outletCapabilities 'loadSense' bit is TRUE, then all of the
             states are supported.  If the outletCapabilities 'loadSense'
             bit is FALSE, then only the 'normal' and 'noComm' states are
             supported."
    ::= { outletEntry  6 }

outletLoadValue OBJECT-TYPE
    SYNTAX  INTEGER
    ACCESS  read-only
    STATUS  mandatory
    DESCRIPTION
           "The load measured on the outlet.  A non-negative value
             indicates the measured load in hundredths of Amps.  A
             negative value indicates that a load value was not able to
             be measured."
    ::= { outletEntry  7 }

outletLoadLowThresh OBJECT-TYPE
    SYNTAX  INTEGER
    ACCESS  read-write
    STATUS  mandatory
    DESCRIPTION
           "The load low threshold value of the outlet in Amps."
    ::= { outletEntry  8 }

outletLoadHighThresh OBJECT-TYPE
    SYNTAX  INTEGER
    ACCESS  read-write
    STATUS  mandatory
    DESCRIPTION
           "The load high threshold value of the outlet in Amps."
    ::= { outletEntry  9 }

outletControlState OBJECT-TYPE
    SYNTAX  INTEGER {
                 idleOff(0),
                 idleOn(1),
                 wakeOff(2),
                 wakeOn(3),
                 off(4),
                 on(5),
                 lockedOff(6),
                 lockedOn(7),
                 reboot(8),
                 shutdown(9),
                 pendOn(10),
                 pendOff(11),
                 minimumOff(12),
                 minimumOn(13),
                 eventOff(14),
                 eventOn(15),
                 eventReboot(16),
                 eventShutdown(17)
               }
    ACCESS  read-only
    STATUS  mandatory
    DESCRIPTION
           "The control state of the outlet.  The supported states are
             dependent upon the outletCapabilities 'powerControl' and
             'shutdown' bits, as well as the supported features of the
             firmware version."
    ::= { outletEntry  10 }

outletControlAction OBJECT-TYPE
    SYNTAX  INTEGER {
                 none(0),
                 on(1),
                 off(2),
                 reboot(3)
               }
    ACCESS  read-write
    STATUS  mandatory
    DESCRIPTION
           "An action to change the control state of the outlet.  If
             the outletCapabilities 'powerControl' bit is TRUE, then the
             'on', 'off', and 'reboot' actions can be used to change the
             control state of the outlet.  If the outletCapabilities
             'powerControl' bit is FALSE, then the actions have no
             effect."
    ::= { outletEntry  11 }

envMonTable OBJECT-TYPE
    SYNTAX  SEQUENCE OF EnvMonEntry
    ACCESS  not-accessible
    STATUS  mandatory
    DESCRIPTION
           "A table of environmental monitors."
    ::= { systemTables  4 }

envMonEntry OBJECT-TYPE
    SYNTAX  EnvMonEntry
    ACCESS  not-accessible
    STATUS  mandatory
    DESCRIPTION
           "Row definition for the environmental monitor table."
    INDEX   { envMonIndex }
    ::= { envMonTable  1 }

EnvMonEntry ::=
    SEQUENCE {
        envMonIndex
            INTEGER,

        envMonID
            DisplayString,

        envMonName
            DisplayString,

        envMonStatus
            INTEGER,

        envMonWaterSensorName
            DisplayString,

        envMonWaterSensorStatus
            INTEGER,

        envMonADCName
            DisplayString,

        envMonADCStatus
            INTEGER,

        envMonADCCount
            INTEGER,

        envMonADCLowThresh
            INTEGER,

        envMonADCHighThresh
            INTEGER,

        envMonTempHumidSensorCount
            INTEGER,

        envMonContactClosureCount
            INTEGER
    }

envMonIndex OBJECT-TYPE
    SYNTAX  INTEGER(0..4)
    ACCESS  not-accessible
    STATUS  mandatory
    DESCRIPTION
           "Index for the environmental monitor table."
    ::= { envMonEntry  1 }

envMonID OBJECT-TYPE
    SYNTAX  DisplayString
    ACCESS  read-only
    STATUS  mandatory
    DESCRIPTION
           "The ID of the environmental monitor."
    ::= { envMonEntry  2 }

envMonName OBJECT-TYPE
    SYNTAX  DisplayString
    ACCESS  read-write
    STATUS  mandatory
    DESCRIPTION
           "The name of the environmental monitor."
    ::= { envMonEntry  3 }

envMonStatus OBJECT-TYPE
    SYNTAX  INTEGER {
                 normal(0),
                 noComm(1)
               }
    ACCESS  read-only
    STATUS  mandatory
    DESCRIPTION
           "The operational status of the environmental monitor."
    ::= { envMonEntry  4 }

envMonWaterSensorName OBJECT-TYPE
    SYNTAX  DisplayString
    ACCESS  read-write
    STATUS  mandatory
    DESCRIPTION
           "The name of the water sensor."
    ::= { envMonEntry  5 }

envMonWaterSensorStatus OBJECT-TYPE
    SYNTAX  INTEGER {
                 normal(0),
                 alarm(1),
                 noComm(2)
               }
    ACCESS  read-only
    STATUS  mandatory
    DESCRIPTION
           "The status of the water sensor."
    ::= { envMonEntry  6 }

envMonADCName OBJECT-TYPE
    SYNTAX  DisplayString
    ACCESS  read-write
    STATUS  mandatory
    DESCRIPTION
           "The name of the analog-to-digital converter."
    ::= { envMonEntry  7 }

envMonADCStatus OBJECT-TYPE
    SYNTAX  INTEGER {
                 normal(0),
                 reading(1),
                 countLow(2),
                 countHigh(3),
                 readError(4),
                 noComm(5)
               }
    ACCESS  read-only
    STATUS  mandatory
    DESCRIPTION
           "The status of the analog-to-digital converter."
    ::= { envMonEntry  8 }

envMonADCCount OBJECT-TYPE
    SYNTAX  INTEGER
    ACCESS  read-only
    STATUS  mandatory
    DESCRIPTION
           "The 8-bit count value from the analog-to-digital converter.
             A non-negative value indicates the digital value retrieved
             from the ADC.  A negative value indicates that a digital
             value was not able to be retrieved."
    ::= { envMonEntry  9 }

envMonADCLowThresh OBJECT-TYPE
    SYNTAX  INTEGER
    ACCESS  read-write
    STATUS  mandatory
    DESCRIPTION
           "The 8-bit count low threshold value of the analog-to-digital
             converter."
    ::= { envMonEntry  10 }

envMonADCHighThresh OBJECT-TYPE
    SYNTAX  INTEGER
    ACCESS  read-write
    STATUS  mandatory
    DESCRIPTION
           "The 8-bit count high threshold value of the analog-to-digital
             converter."
    ::= { envMonEntry  11 }

envMonTempHumidSensorCount OBJECT-TYPE
    SYNTAX  INTEGER
    ACCESS  read-only
    STATUS  mandatory
    DESCRIPTION
           "The number of temperature/humidity sensors on the
             environmental monitor."
    ::= { envMonEntry  12 }

envMonContactClosureCount OBJECT-TYPE
    SYNTAX  INTEGER
    ACCESS  read-only
    STATUS  mandatory
    DESCRIPTION
           "The number of contact closures on the environmental
             monitor."
    ::= { envMonEntry  13 }

tempHumidSensorTable OBJECT-TYPE
    SYNTAX  SEQUENCE OF TempHumidSensorEntry
    ACCESS  not-accessible
    STATUS  mandatory
    DESCRIPTION
           "A table of temperature/humidity sensors."
    ::= { systemTables  5 }

tempHumidSensorEntry OBJECT-TYPE
    SYNTAX  TempHumidSensorEntry
    ACCESS  not-accessible
    STATUS  mandatory
    DESCRIPTION
           "Row definition for the temperature/humidity sensor table."
    INDEX   { envMonIndex, tempHumidSensorIndex }
    ::= { tempHumidSensorTable  1 }

TempHumidSensorEntry ::=
    SEQUENCE {
        tempHumidSensorIndex
            INTEGER,

        tempHumidSensorID
            DisplayString,

        tempHumidSensorName
            DisplayString,

        tempHumidSensorStatus
            INTEGER,

        tempHumidSensorTempStatus
            INTEGER,

        tempHumidSensorTempValue
            INTEGER,

        tempHumidSensorTempLowThresh
            INTEGER,

        tempHumidSensorTempHighThresh
            INTEGER,

        tempHumidSensorHumidStatus
            INTEGER,

        tempHumidSensorHumidValue
            INTEGER,

        tempHumidSensorHumidLowThresh
            INTEGER,

        tempHumidSensorHumidHighThresh
            INTEGER,

        tempHumidSensorTempScale
            INTEGER
    }

tempHumidSensorIndex OBJECT-TYPE
    SYNTAX  INTEGER(0..2)
    ACCESS  not-accessible
    STATUS  mandatory
    DESCRIPTION
           "Index for the temperature/humidity sensor table."
    ::= { tempHumidSensorEntry  1 }

tempHumidSensorID OBJECT-TYPE
    SYNTAX  DisplayString
    ACCESS  read-only
    STATUS  mandatory
    DESCRIPTION
           "The ID of the temperature/humidity sensor."
    ::= { tempHumidSensorEntry  2 }

tempHumidSensorName OBJECT-TYPE
    SYNTAX  DisplayString
    ACCESS  read-write
    STATUS  mandatory
    DESCRIPTION
           "The name of the temperature/humidity sensor."
    ::= { tempHumidSensorEntry  3 }

tempHumidSensorStatus OBJECT-TYPE
    SYNTAX  INTEGER {
                 found(0),
                 notFound(1),
                 lost(2),
                 noComm(3)
               }
    ACCESS  read-only
    STATUS  mandatory
    DESCRIPTION
           "The operational status of the temperature/humidity sensor."
    ::= { tempHumidSensorEntry  4 }

tempHumidSensorTempStatus OBJECT-TYPE
    SYNTAX  INTEGER {
                 normal(0),
                 notFound(1),
                 reading(2),
                 tempLow(3),
                 tempHigh(4),
                 readError(5),
                 lost(6),
                 noComm(7)
               }
    ACCESS  read-only
    STATUS  mandatory
    DESCRIPTION
           "The status of the temperature sensor."
    ::= { tempHumidSensorEntry  5 }

tempHumidSensorTempValue OBJECT-TYPE
    SYNTAX  INTEGER
    ACCESS  read-only
    STATUS  mandatory
    DESCRIPTION
            "The temperature measured by the sensor.  A non-negative value
             indicates the measured temperature in tenths of degrees, using
             the scale selected by tempHumidSensorTempScale.  If the agent
             does not support the tempHumidSensorTempScale object, then the
             temperature scale used is Celsius.  A negative value indicates
             that a temperature value was not able to be measured."
    ::= { tempHumidSensorEntry  6 }

tempHumidSensorTempLowThresh OBJECT-TYPE
    SYNTAX  INTEGER
    ACCESS  read-write
    STATUS  mandatory
    DESCRIPTION
            "The temperature low threshold value of the sensor in degrees,
             using the scale selected by tempHumidSensorTempScale.  If the
             agent does not support the tempHumidSensorTempScale object,
             then the temperature scale used is Celsius."
    ::= { tempHumidSensorEntry  7 }

tempHumidSensorTempHighThresh OBJECT-TYPE
    SYNTAX  INTEGER
    ACCESS  read-write
    STATUS  mandatory
    DESCRIPTION
            "The temperature high threshold value of the sensor in degrees,
             using the scale selected by tempHumidSensorTempScale.  If the
             agent does not support the tempHumidSensorTempScale object,
             then the temperature scale used is Celsius."
    ::= { tempHumidSensorEntry  8 }

tempHumidSensorHumidStatus OBJECT-TYPE
    SYNTAX  INTEGER {
                 normal(0),
                 notFound(1),
                 reading(2),
                 humidLow(3),
                 humidHigh(4),
                 readError(5),
                 lost(6),
                 noComm(7)
               }
    ACCESS  read-only
    STATUS  mandatory
    DESCRIPTION
           "The status of the humidity sensor."
    ::= { tempHumidSensorEntry  9 }

tempHumidSensorHumidValue OBJECT-TYPE
    SYNTAX  INTEGER
    ACCESS  read-only
    STATUS  mandatory
    DESCRIPTION
           "The humidity measured by the sensor.  A non-negative value
             indicates the measured humidity in percentage relative
             humidity.  A negative value indicates that a humidity value
             was not able to be measured."
    ::= { tempHumidSensorEntry  10 }

tempHumidSensorHumidLowThresh OBJECT-TYPE
    SYNTAX  INTEGER
    ACCESS  read-write
    STATUS  mandatory
    DESCRIPTION
           "The humidity low threshold value of the sensor in percentage
             relative humidity."
    ::= { tempHumidSensorEntry  11 }

tempHumidSensorHumidHighThresh OBJECT-TYPE
    SYNTAX  INTEGER
    ACCESS  read-write
    STATUS  mandatory
    DESCRIPTION
           "The humidity low threshold value of the sensor in percentage
             relative humidity."
    ::= { tempHumidSensorEntry  12 }

tempHumidSensorTempScale OBJECT-TYPE
    SYNTAX  INTEGER {
                 celsius(0),
                 fahrenheit(1)
               }
    ACCESS  read-only
    STATUS  mandatory
    DESCRIPTION
            "The scale used for temperature values.  This is a global
             setting for all temperature values in the system.  If the
             agent does not support this object, then the temperature
             scale used is Celsius."
        ::= { tempHumidSensorEntry 13 }

contactClosureTable OBJECT-TYPE
    SYNTAX  SEQUENCE OF ContactClosureEntry
    ACCESS  not-accessible
    STATUS  mandatory
    DESCRIPTION
           "A table of contact closures."
    ::= { systemTables  6 }

contactClosureEntry OBJECT-TYPE
    SYNTAX  ContactClosureEntry
    ACCESS  not-accessible
    STATUS  mandatory
    DESCRIPTION
           "Row definition for the contact closure table."
    INDEX   { envMonIndex, contactClosureIndex }
    ::= { contactClosureTable  1 }

ContactClosureEntry ::=
    SEQUENCE {
        contactClosureIndex
            INTEGER,

        contactClosureID
            DisplayString,

        contactClosureName
            DisplayString,

        contactClosureStatus
            INTEGER
    }

contactClosureIndex OBJECT-TYPE
    SYNTAX  INTEGER(0..4)
    ACCESS  not-accessible
    STATUS  mandatory
    DESCRIPTION
           "Index for the contact closure table."
    ::= { contactClosureEntry  1 }

contactClosureID OBJECT-TYPE
    SYNTAX  DisplayString
    ACCESS  read-only
    STATUS  mandatory
    DESCRIPTION
           "The ID of the contact closure."
    ::= { contactClosureEntry  2 }

contactClosureName OBJECT-TYPE
    SYNTAX  DisplayString
    ACCESS  read-write
    STATUS  mandatory
    DESCRIPTION
           "The name of the contact closure."
    ::= { contactClosureEntry  3 }

contactClosureStatus OBJECT-TYPE
    SYNTAX  INTEGER {
                 normal(0),
                 alarm(1),
                 noComm(2)
               }
    ACCESS  read-only
    STATUS  mandatory
    DESCRIPTION
           "The status of the contact closure."
    ::= { contactClosureEntry  4 }

sentry3Traps OBJECT IDENTIFIER ::= { sentry3 100 }

towerStatusEvent TRAP-TYPE
    ENTERPRISE  sentry3Traps
    VARIABLES   {
                 systemLocation,
                 towerID,
                 towerName,
                 towerStatus
               }
    DESCRIPTION
           "Tower status event.  If enabled, this trap is sent when the
             towerStatus indicates an error state ('noComm', 'fanFail',
             or 'overTemp').  This trap is repeated periodically while the
             towerStatus remains in an error state.  If the towerStatus
             returns to a non-error state ('normal'), this trap is sent
             once more with the non-error towerStatus, and then stops
             being repeated.

             While the towerStatus indicates a 'noComm' error state, all
             status and load traps are suppressed for input feeds and
             outlets on the tower."
    ::= 1

infeedStatusEvent TRAP-TYPE
    ENTERPRISE  sentry3Traps
    VARIABLES   {
                 systemLocation,
                 infeedID,
                 infeedName,
                 infeedStatus
               }
    DESCRIPTION
           "Input feed status event.  If enabled, this trap is sent when
             the infeedStatus indicates an error state ('offError',
             'onError', or 'noComm').  This trap is repeated periodically
             while the infeedStatus remains in an error state.  If the
             infeedStatus returns to a non-error state ('off' or 'on'),
             this trap is sent once more with the non-error infeedStatus,
             and then stops being repeated.

             While the infeedStatus indicates an error state, load
             traps are suppressed for the input feed, and, if the
             infeedCapabilities 'failSafe' bit is FALSE, all status and
             load traps are suppressed for outlets on the input feed."
    ::= 2

infeedLoadEvent TRAP-TYPE
    ENTERPRISE  sentry3Traps
    VARIABLES   {
                 systemLocation,
                 infeedID,
                 infeedName,
                 infeedLoadStatus,
                 infeedLoadValue,
                 infeedLoadHighThresh
               }
    DESCRIPTION
           "Input feed load event.  If enabled, this trap is sent when
             the infeedLoadStatus indicates an error state ('loadLow',
             'loadHigh', 'overLoad', 'readError', or 'noComm').  This
             trap is repeated periodically while the infeedLoadStatus
             remains in an error state.  If the infeedLoadStatus returns
             to a non-error state ('normal' or 'notOn'), this trap is
             sent once more with the non-error infeedLoadStatus, and then
             stops being repeated."
    ::= 3

outletStatusEvent TRAP-TYPE
    ENTERPRISE  sentry3Traps
    VARIABLES   {
                 systemLocation,
                 outletID,
                 outletName,
                 outletStatus
               }
    DESCRIPTION
           "Outlet status event.  If enabled, this trap is sent when the
             outletStatus indicates an error state ('offError', 'onError',
             'noComm', 'offFuse', or 'onFuse').  This trap is repeated
             periodically while the outletStatus remains in an error state.
             If the outletStatus returns to a non-error state ('off' or
             'on'), this trap is sent once more with the non-error
             outletStatus, and then stops being repeated.

             While the outletStatus indicates an error state, load traps
             are suppressed for the outlet."
    ::= 4

outletLoadEvent TRAP-TYPE
    ENTERPRISE  sentry3Traps
    VARIABLES   {
                 systemLocation,
                 outletID,
                 outletName,
                 outletLoadStatus,
                 outletLoadValue,
                 outletLoadLowThresh,
                 outletLoadHighThresh
               }
    DESCRIPTION
           "Outlet load event.  If enabled, this trap is sent when the
             outletLoadStatus indicates an error state ('loadLow',
             'loadHigh', 'overLoad', 'readError', or 'noComm').  This
             trap is repeated periodically while the outletLoadStatus
             remains in an error state.  If the outletLoadStatus returns
             to a non-error state ('normal' or 'notOn'), this trap is
             sent once more with the non-error outletLoadStatus, and then
             stops being repeated."
    ::= 5

outletChangeEvent TRAP-TYPE
    ENTERPRISE  sentry3Traps
    VARIABLES   {
                 systemLocation,
                 outletID,
                 outletName,
                 outletStatus,
                 outletControlState
               }
    DESCRIPTION
           "Outlet on/off change event.  If enabled, this trap is sent
             when the outletStatus changes from any 'on' state ('on',
             'onWait', 'onError', or 'onFuse') to any 'off' state ('off',
             'offWait', 'offError', or 'offFuse'), and vice-versa."
    ::= 6

envMonStatusEvent TRAP-TYPE
    ENTERPRISE  sentry3Traps
    VARIABLES   {
                 systemLocation,
                 envMonID,
                 envMonName,
                 envMonStatus
               }
    DESCRIPTION
           "Environmental monitor status event.  If enabled, this trap
             is sent when the envMonStatus indicates an error state
             ('noComm').  This trap is repeated periodically while the
             envMonStatus remains in an error state.  If the envMonStatus
             returns to a non-error state ('normal'), this trap is sent
             once more with the non-error envMonStatus, and then stops
             being repeated.

             While the envMonStatus indicates an error state, all status
             traps are suppressed for the water sensor, ADC, temperature/
             humudity sensors, and contact closures on the environmental
             monitor."
    ::= 7

envMonWaterSensorEvent TRAP-TYPE
    ENTERPRISE  sentry3Traps
    VARIABLES   {
                 systemLocation,
                 envMonID,
                 envMonWaterSensorName,
                 envMonWaterSensorStatus
               }
    DESCRIPTION
           "Environmental monitor water sensor event.  If enabled, this
             trap is sent when the envMonWaterSensorStatus indicates an
             error state ('alarm').  This trap is repeated periodically
             while the envMonWaterSensorStatus remains in an error state.
             If the envMonWaterSensorStatus returns to a non-error state
             ('normal'), this trap is sent once more with the non-error
             envMonWaterSensorStatus, and then stops being repeated."
    ::= 8

envMonADCEvent TRAP-TYPE
    ENTERPRISE  sentry3Traps
    VARIABLES   {
                 systemLocation,
                 envMonID,
                 envMonADCName,
                 envMonADCStatus,
                 envMonADCCount,
                 envMonADCLowThresh,
                 envMonADCHighThresh
               }
    DESCRIPTION
           "Environmental monitor analog-to-digital converter event.
             If enabled, this trap is sent when the envMonADCStatus
             indicates an error state ('countLow' or 'countHigh').  This
             trap is repeated periodically while the envMonADCStatus
             remains in an error state.  If the envMonADCStatus returns
             to a non-error state ('normal'), this trap is sent once more
             with the non-error envMonADCStatus, and then stops being
             repeated."
    ::= 9

tempHumidSensorStatusEvent TRAP-TYPE
    ENTERPRISE  sentry3Traps
    VARIABLES   {
                 systemLocation,
                 tempHumidSensorID,
                 tempHumidSensorName,
                 tempHumidSensorStatus
               }
    DESCRIPTION
           "Temperature/humidity sensor status event.  If enabled, this
             trap is sent when the tempHumidSensorStatus indicates an
             error state ('lost').  This trap is repeated periodically
             while the tempHumidSensorStatus remains in an error state.
             If the tempHumidSensorStatus returns to a non-error state
             ('found'), this trap is sent once more with the non-error
             tempHumidSensorStatus, and then stops being repeated.

             While the tempHumidSensorStatus indicates an error state, all
             temperature and humidity status traps are suppressed for the
             temperature/humudity sensor."
    ::= 10

tempHumidSensorTempEvent TRAP-TYPE
    ENTERPRISE  sentry3Traps
    VARIABLES   {
                 systemLocation,
                 tempHumidSensorID,
                 tempHumidSensorName,
                 tempHumidSensorTempStatus,
                 tempHumidSensorTempValue,
                 tempHumidSensorTempLowThresh,
                 tempHumidSensorTempHighThresh,
                 tempHumidSensorTempScale
               }
    DESCRIPTION
           "Temperature/humidity sensor temperature event.  If enabled,
             this trap is sent when the tempHumidSensorTempStatus
             indicates an error state ('tempLow' or 'tempHigh').
             This trap is repeated periodically while the
             tempHumidSensorTempStatus remains in an error state.  If
             the tempHumidSensorTempStatus returns to a non-error state
             ('normal'), this trap is sent once more with the non-error
             tempHumidSensorTempStatus, and then stops being repeated."
    ::= 11

tempHumidSensorHumidEvent TRAP-TYPE
    ENTERPRISE  sentry3Traps
    VARIABLES   {
                 systemLocation,
                 tempHumidSensorID,
                 tempHumidSensorName,
                 tempHumidSensorHumidStatus,
                 tempHumidSensorHumidValue,
                 tempHumidSensorHumidLowThresh,
                 tempHumidSensorHumidHighThresh
               }
    DESCRIPTION
           "Temperature/humidity sensor humidity event.  If enabled,
             this trap is sent when the tempHumidSensorHumidStatus
             indicates an error state ('humidLow' or 'humidHigh').
             This trap is repeated periodically while the
             tempHumidSensorHumidStatus remains in an error state.  If
             the tempHumidSensorHumidStatus returns to a non-error state
             ('normal'), this trap is sent once more with the non-error
             tempHumidSensorHumidStatus, and then stops being repeated."
    ::= 12

contactClosureEvent TRAP-TYPE
    ENTERPRISE  sentry3Traps
    VARIABLES   {
                 systemLocation,
                 contactClosureID,
                 contactClosureName,
                 contactClosureStatus
               }
    DESCRIPTION
           "Contact closure event.  If enabled, this trap is sent when
             the contactClosureStatus indicates an error state ('alarm').
             This trap is repeated periodically while the
             contactClosureStatus remains in an error state.  If the
             contactClosureStatus returns to a non-error state ('normal'),
             this trap is sent once more with the non-error
             contactClosureStatus, and then stops being repeated."
    ::= 13

END
