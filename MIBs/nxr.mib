------------------------------------------------------------
-- EMERSON NETWORK POWER
-- SIC MIB
------------------------------------------------------------

ENP-nxr-MIB DEFINITIONS ::= BEGIN

IMPORTS
	MODULE-IDENTITY, OBJECT-TYPE, NOTIFICATION-TYPE,
	Integer32, Counter32, enterprises
		FROM SNMPv2-SMI
	TEXTUAL-CONVENTION, DisplayString, DateAndTime
		FROM SNMPv2-TC;
		
		
------------------------------------------------------------
-- Node definitions
------------------------------------------------------------

enp OBJECT IDENTIFIER ::= { enterprises 13400 }

products OBJECT IDENTIFIER ::= { enp 2 }

nxrMIB MODULE-IDENTITY
	LAST-UPDATED "200911231030Z"
	ORGANIZATION "
		EMERSON NETWORK POWER (ENP)"
	CONTACT-INFO "
		EMERSON NETWORK POWER"
	DESCRIPTION "
		EMERSON NETWORK POWER (ENP) SIC MIB."
	::= { products 19 }


------------------------------------------------------------
-- Textual conventions
------------------------------------------------------------

Status ::= TEXTUAL-CONVENTION
	STATUS current
	DESCRIPTION "
		The severity of the alarm. One of
		(0) informational
		(1) warning
		(2) critical"
	SYNTAX INTEGER {
		informational(0),
		warning(1),
		critical(2) }
		
StatusChange ::= TEXTUAL-CONVENTION
	STATUS current
	DESCRIPTION "
		Indicates 'activated' (0) or 'deactivated' (1) alarm events."
	SYNTAX INTEGER {
		activated(0),
		deactivated(1) }


------------------------------------------------------------
-- 1.1 Identification of the plant { nxrMIB 1 }
------------------------------------------------------------

ident OBJECT IDENTIFIER ::= { nxrMIB 1 }

identManufacturer OBJECT-TYPE
	SYNTAX DisplayString
	MAX-ACCESS read-only
	STATUS current
	DESCRIPTION "
		The name of the device manufacturer."
	::= { ident 1 }

identModel OBJECT-TYPE
	SYNTAX DisplayString
	MAX-ACCESS read-only
	STATUS current
	DESCRIPTION "
		The manufacturers model designation of the device."
	::= { ident 2 }

identIndex OBJECT-TYPE
	SYNTAX Integer32
	MAX-ACCESS read-write
	STATUS current
	DESCRIPTION "
		The sequence number of the device."
	::= { ident 3 }
	

------------------------------------------------------------
-- 1.2 system values { nxrMIB 2 }
------------------------------------------------------------

system OBJECT IDENTIFIER ::= { nxrMIB 2 }


-- ------------------------------------------------------------------------ 
-- 1.2.1 the status group
-- ------------------------------------------------------------------------ 

status OBJECT IDENTIFIER ::= { system 1 }

	systemStatus OBJECT-TYPE
		SYNTAX Status
		MAX-ACCESS read-only
		STATUS current
		DESCRIPTION "
			Status of the complete plant (highest alarm). One of
			(0) normal
			(1) warning
			(2) critical"
		::= { status 1 }


-- ------------------------------------------------------------------------ 
-- 1.2.2 the systemdata group
-- ------------------------------------------------------------------------ 

systemdata OBJECT IDENTIFIER ::= { system 2 }

    systemOutputAcitvePowerA OBJECT-TYPE
        SYNTAX Integer32
        MAX-ACCESS read-only
        STATUS current
        DESCRIPTION
            "System Output Acitve Power A, stored as 0.01 kW."
        ::= { systemdata 1 }

    systemOutputAcitvePowerB OBJECT-TYPE
        SYNTAX Integer32
        MAX-ACCESS read-only
        STATUS current
        DESCRIPTION
            "System Output Acitve Power B, stored as 0.01 kW."
        ::= { systemdata 2 }

    systemOutputAcitvePowerC OBJECT-TYPE
        SYNTAX Integer32
        MAX-ACCESS read-only
        STATUS current
        DESCRIPTION
            "System Output Acitve Power C, stored as 0.01 kW."
        ::= { systemdata 3 }
        
    systemOutputAppPowerA OBJECT-TYPE
        SYNTAX Integer32
        MAX-ACCESS read-only
        STATUS current
        DESCRIPTION
            "System Output App Power A, stored as 0.01 kVA."
        ::= { systemdata 4 }

    systemOutputAppPowerB OBJECT-TYPE
        SYNTAX Integer32
        MAX-ACCESS read-only
        STATUS current
        DESCRIPTION
            "System Output App Power B, stored as 0.01 kVA."
        ::= { systemdata 5 }

    systemOutputAppPowerC OBJECT-TYPE
        SYNTAX Integer32
        MAX-ACCESS read-only
        STATUS current
        DESCRIPTION
            "System Output App Power C, stored as 0.01 kVA."
        ::= { systemdata 6 }
        
    systemOutputReactivePowerA OBJECT-TYPE
        SYNTAX Integer32
        MAX-ACCESS read-only
        STATUS current
        DESCRIPTION
            "System Output Reactive Power A, stored as 0.01 KVAR."
        ::= { systemdata 7 }

    systemOutputReactivePowerB OBJECT-TYPE
        SYNTAX Integer32
        MAX-ACCESS read-only
        STATUS current
        DESCRIPTION
            "System Output Reactive Power B, stored as 0.01 KVAR."
        ::= { systemdata 8 }

    systemOutputReactivePowerC OBJECT-TYPE
        SYNTAX Integer32
        MAX-ACCESS read-only
        STATUS current
        DESCRIPTION
            "System Output Reactive Power C, stored as 0.01 KVAR."
        ::= { systemdata 9 }


-- ------------------------------------------------------------------------ 
-- 1.2.3 the unit group
-- ------------------------------------------------------------------------ 

unit OBJECT IDENTIFIER ::= { system 3 }

    unitModules OBJECT-TYPE
    	SYNTAX Integer32
    	MAX-ACCESS read-only
        STATUS current
        DESCRIPTION
            "Unit Modules, stored as 0.01."
        ::= { unit 1 }

    unitCapacity OBJECT-TYPE
        SYNTAX Integer32
        MAX-ACCESS read-only
        STATUS current
        DESCRIPTION
            "Unit Capacity, stored as 0.01 kVA."
        ::= { unit 2 }

    moduleCapacity OBJECT-TYPE
        SYNTAX Integer32
        MAX-ACCESS read-only
        STATUS current
        DESCRIPTION
            "Module Capacity, stored as 0.01 kVA."
        ::= { unit 3 }

-- ------------------------------------------------------------------------ 
-- 1.2.4 the main group
-- ------------------------------------------------------------------------ 

analogdata OBJECT IDENTIFIER ::= { system 4 }

    inputPhaseVoltageA OBJECT-TYPE
        SYNTAX Integer32
        MAX-ACCESS read-only
        STATUS current
        DESCRIPTION
            "Input Phase Voltage A, stored as 0.01 V."
        ::= { analogdata 1 }

    inputPhaseVoltageB OBJECT-TYPE
        SYNTAX Integer32
        MAX-ACCESS read-only
        STATUS current
        DESCRIPTION
            "Input Phase Voltage B, stored as 0.01 V."
        ::= { analogdata 2 }

    inputPhaseVoltageC OBJECT-TYPE
        SYNTAX Integer32
        MAX-ACCESS read-only
        STATUS current
        DESCRIPTION
            "Input Phase Voltage C, stored as 0.01 V."
        ::= { analogdata 3 }

    inputLineVoltageA OBJECT-TYPE
        SYNTAX Integer32
        MAX-ACCESS read-only
        STATUS current
        DESCRIPTION
            "Input Line Voltage A, stored as 0.01 V."
        ::= { analogdata 4 }

    inputLineVoltageB OBJECT-TYPE
        SYNTAX Integer32
        MAX-ACCESS read-only
        STATUS current
        DESCRIPTION
            "Input Line Voltage B, stored as 0.01 V."
        ::= { analogdata 5 }

    inputLineVoltageC OBJECT-TYPE
        SYNTAX Integer32
        MAX-ACCESS read-only
        STATUS current
        DESCRIPTION
            "Input Line Voltage C, stored as 0.01 V."
        ::= { analogdata 6 }

    inputCurrentA OBJECT-TYPE
        SYNTAX Integer32
        MAX-ACCESS read-only
        STATUS current
        DESCRIPTION
            "Input Current A, stored as 0.01 A."
        ::= { analogdata 7 }

    inputCurrentB OBJECT-TYPE
        SYNTAX Integer32
        MAX-ACCESS read-only
        STATUS current
        DESCRIPTION
            "Input Current B, stored as 0.01 A."
        ::= { analogdata 8 }

    inputCurrentC OBJECT-TYPE
        SYNTAX Integer32
        MAX-ACCESS read-only
        STATUS current
        DESCRIPTION
            "Input Current C, stored as 0.01 A."
        ::= { analogdata 9 }

    inputFrequency OBJECT-TYPE
        SYNTAX Integer32
        MAX-ACCESS read-only
        STATUS current
        DESCRIPTION
            "Input Frequency, stored as 0.01 Hz."
        ::= { analogdata 10 }

    inputPowerFactorA OBJECT-TYPE
        SYNTAX Integer32
        MAX-ACCESS read-only
        STATUS current
        DESCRIPTION
            "Input Power Factor A, stored as 0.01."
        ::= { v 11 }

    inputPowerFactorB OBJECT-TYPE
        SYNTAX Integer32
        MAX-ACCESS read-only
        STATUS current
        DESCRIPTION
            "Input Power Factor B, stored as 0.01."
        ::= { analogdata 12 }

    inputPowerFactorC OBJECT-TYPE
        SYNTAX Integer32
        MAX-ACCESS read-only
        STATUS current
        DESCRIPTION
            "Input Power Factor C, stored as 0.01."
        ::= { analogdata 13 }

    dCBus1Voltage OBJECT-TYPE
        SYNTAX Integer32
        MAX-ACCESS read-only
        STATUS current
        DESCRIPTION
            "DCBus1 Voltage, stored as 0.01 V."
        ::= { analogdata 14 }

    dCBus2Voltage OBJECT-TYPE
        SYNTAX Integer32
        MAX-ACCESS read-only
        STATUS current
        DESCRIPTION
            "DCBus2 Voltage, stored as 0.01 V."
        ::= { analogdata 15 }

    outputVoltageA OBJECT-TYPE
    	SYNTAX Integer32
    	MAX-ACCESS read-only
        STATUS current
        DESCRIPTION
            "Output voltage A, stored as 0.01 V."
        ::= { analogdata 16 }

    outputVoltageB OBJECT-TYPE
    	SYNTAX Integer32
    	MAX-ACCESS read-only
        STATUS current
        DESCRIPTION
            "Output voltage B, stored as 0.01 V."
        ::= { analogdata 17 }

    outputVoltageC OBJECT-TYPE
    	SYNTAX Integer32
    	MAX-ACCESS read-only
        STATUS current
        DESCRIPTION
            "Output voltage C, stored as 0.01 V."
        ::= { analogdata 18 }

    outputCurrentA OBJECT-TYPE
        SYNTAX Integer32
        MAX-ACCESS read-only
        STATUS current
        DESCRIPTION
            "Output current A, stored as 0.01 A."
        ::= { analogdata 19 }

    outputCurrentB OBJECT-TYPE
        SYNTAX Integer32
        MAX-ACCESS read-only
        STATUS current
        DESCRIPTION
            "Output current B, stored as 0.01 A."
        ::= { analogdata 20 }

    outputCurrentC OBJECT-TYPE
        SYNTAX Integer32
        MAX-ACCESS read-only
        STATUS current
        DESCRIPTION
            "Output current C, stored as 0.01 A."
        ::= { analogdata 21 }

    outputFrequency OBJECT-TYPE
        SYNTAX Integer32
        MAX-ACCESS read-only
        STATUS current
        DESCRIPTION
            "Output Frequency, stored as 0.01 Hz."
        ::= { analogdata 22 }

    outputPowerFactorA OBJECT-TYPE
        SYNTAX Integer32
        MAX-ACCESS read-only
        STATUS current
        DESCRIPTION
            "Output Power Factor A, stored as 0.01."
        ::= { analogdata 23 }

    outputPowerFactorB OBJECT-TYPE
        SYNTAX Integer32
        MAX-ACCESS read-only
        STATUS current
        DESCRIPTION
            "Output Power Factor B, stored as 0.01."
        ::= { analogdata 24 }

    outputPowerFactorC OBJECT-TYPE
        SYNTAX Integer32
        MAX-ACCESS read-only
        STATUS current
        DESCRIPTION
            "Output Power Factor C, stored as 0.01."
        ::= { analogdata 25 }

    outputAcitvePowerA OBJECT-TYPE
        SYNTAX Integer32
        MAX-ACCESS read-only
        STATUS current
        DESCRIPTION
            "Output Acitve Power A, stored as 0.01 kW."
        ::= { analogdata 26 }

    outputAcitvePowerB OBJECT-TYPE
        SYNTAX Integer32
        MAX-ACCESS read-only
        STATUS current
        DESCRIPTION
            "Output Acitve Power B, stored as 0.01 kW."
        ::= { analogdata 27 }

    outputAcitvePowerC OBJECT-TYPE
        SYNTAX Integer32
        MAX-ACCESS read-only
        STATUS current
        DESCRIPTION
            "Output Acitve Power C, stored as 0.01 kW."
        ::= { analogdata 28 }

    outputReactivePowerA OBJECT-TYPE
        SYNTAX Integer32
        MAX-ACCESS read-only
        STATUS current
        DESCRIPTION
            "Output Reactive Power A, stored as 0.01 KVAR."
        ::= { analogdata 29 }

    outputReactivePowerB OBJECT-TYPE
        SYNTAX Integer32
        MAX-ACCESS read-only
        STATUS current
        DESCRIPTION
            "Output Reactive Power B, stored as 0.01 KVAR."
        ::= { analogdata 30 }

    outputReactivePowerC OBJECT-TYPE
        SYNTAX Integer32
        MAX-ACCESS read-only
        STATUS current
        DESCRIPTION
            "Output Reactive Power C, stored as 0.01 KVAR."
        ::= { analogdata 31 }

    outputAppPowerA OBJECT-TYPE
        SYNTAX Integer32
        MAX-ACCESS read-only
        STATUS current
        DESCRIPTION
            "Output App Power A, stored as 0.01 kVA."
        ::= { analogdata 32 }

    outputAppPowerB OBJECT-TYPE
        SYNTAX Integer32
        MAX-ACCESS read-only
        STATUS current
        DESCRIPTION
            "Output App Power B, stored as 0.01 kVA."
        ::= { analogdata 33 }

    outputAppPowerC OBJECT-TYPE
        SYNTAX Integer32
        MAX-ACCESS read-only
        STATUS current
        DESCRIPTION
            "Output App Power C, stored as 0.01 kVA."
        ::= { analogdata 34 }

    outputLoadA OBJECT-TYPE
        SYNTAX Integer32
        MAX-ACCESS read-only
        STATUS current
        DESCRIPTION
            "Output Load A, stored as 0.01 %."
        ::= { analogdata 35 }

    outputLoadB OBJECT-TYPE
        SYNTAX Integer32
        MAX-ACCESS read-only
        STATUS current
        DESCRIPTION
            "Output Load B, stored as 0.01 %."
        ::= { analogdata 36 }

    outputLoadC OBJECT-TYPE
        SYNTAX Integer32
        MAX-ACCESS read-only
        STATUS current
        DESCRIPTION
            "Output Load C, stored as 0.01 %."
        ::= { analogdata 37 }

    outputCrestFactorA OBJECT-TYPE
        SYNTAX Integer32
        MAX-ACCESS read-only
        STATUS current
        DESCRIPTION
            "Output Crest Factor A, stored as 0.01 ."
        ::= { analogdata 38 }

    outputCrestFactorB OBJECT-TYPE
        SYNTAX Integer32
        MAX-ACCESS read-only
        STATUS current
        DESCRIPTION
            "Output Crest Factor B, stored as 0.01 ."
        ::= { analogdata 39 }

    outputCrestFactorC OBJECT-TYPE
        SYNTAX Integer32
        MAX-ACCESS read-only
        STATUS current
        DESCRIPTION
            "Output Crest Factor C, stored as 0.01 ."
        ::= { analogdata 40 }

    bypassVoltageA OBJECT-TYPE
        SYNTAX Integer32
        MAX-ACCESS read-only
        STATUS current
        DESCRIPTION
            "Bypass Voltage A, stored as 0.01 V."
        ::= { analogdata 41 }

    bypassVoltageB OBJECT-TYPE
        SYNTAX Integer32
        MAX-ACCESS read-only
        STATUS current
        DESCRIPTION
            "Bypass Voltage B, stored as 0.01 V."
        ::= { analogdata 42 }

    bypassVoltageC OBJECT-TYPE
        SYNTAX Integer32
        MAX-ACCESS read-only
        STATUS current
        DESCRIPTION
            "Bypass Voltage C, stored as 0.01 V."
        ::= { analogdata 43 }

    bypassFrequency OBJECT-TYPE
        SYNTAX Integer32
        MAX-ACCESS read-only
        STATUS current
        DESCRIPTION
            "Bypass Frequency, stored as 0.01 Hz."
        ::= { analogdata 44 }

    positiveBatteryVoltage OBJECT-TYPE
        SYNTAX Integer32
        MAX-ACCESS read-only
        STATUS current
        DESCRIPTION
            "positive Battery Voltage, stored as 0.01 V."
        ::= { analogdata 45 }

    positiveBatteryCurrent OBJECT-TYPE
        SYNTAX Integer32
        MAX-ACCESS read-only
        STATUS current
        DESCRIPTION
            "positive Battery Current, stored as 0.01 A."
        ::= { analogdata 46 }

    negativeBatteryVoltage OBJECT-TYPE
        SYNTAX Integer32
        MAX-ACCESS read-only
        STATUS current
        DESCRIPTION
            "negative Battery Voltage, stored as 0.01 V."
        ::= { analogdata 47 }

    negativeBatteryCurrent OBJECT-TYPE
        SYNTAX Integer32
        MAX-ACCESS read-only
        STATUS current
        DESCRIPTION
            "negative Battery Current, stored as 0.01 A."
        ::= { analogdata 48 }

    batteryAgingRate OBJECT-TYPE
        SYNTAX Integer32
        MAX-ACCESS read-only
        STATUS current
        DESCRIPTION
            "Battery Aging Rate, stored as 0.01."
        ::= { analogdata 49 }

    batteryRemainsTime OBJECT-TYPE
        SYNTAX Integer32
        MAX-ACCESS read-only
        STATUS current
        DESCRIPTION
            "Battery Remains Time, stored as 0.01 Hour."
        ::= { analogdata 50 }

    batteryTemperature OBJECT-TYPE
        SYNTAX Integer32
        MAX-ACCESS read-only
        STATUS current
        DESCRIPTION
            "Battery Temperature, stored as 0.01 &deg;C."
        ::= { analogdata 51 }

    batteryEnvironmentTemperature OBJECT-TYPE
        SYNTAX Integer32
        MAX-ACCESS read-only
        STATUS current
        DESCRIPTION
            "Battery Environment Temperature, stored as 0.01 &deg;C."
        ::= { analogdata 52 }

-- ------------------------------------------------------------------------ 
-- 1.2.5 the bypass group
-- ------------------------------------------------------------------------ 

analogdata1 OBJECT IDENTIFIER ::= { system 5 }

    inputPhaseVoltageA1 OBJECT-TYPE
        SYNTAX Integer32
        MAX-ACCESS read-only
        STATUS current
        DESCRIPTION
            "Input Phase Voltage A, stored as 0.01 V."
        ::= { analogdata1 1 }

    inputPhaseVoltageB1 OBJECT-TYPE
        SYNTAX Integer32
        MAX-ACCESS read-only
        STATUS current
        DESCRIPTION
            "Input Phase Voltage B, stored as 0.01 V."
        ::= { analogdata1 2 }

    inputPhaseVoltageC1 OBJECT-TYPE
        SYNTAX Integer32
        MAX-ACCESS read-only
        STATUS current
        DESCRIPTION
            "Input Phase Voltage C, stored as 0.01 V."
        ::= { analogdata1 3 }

    inputLineVoltageA1 OBJECT-TYPE
        SYNTAX Integer32
        MAX-ACCESS read-only
        STATUS current
        DESCRIPTION
            "Input Line Voltage A, stored as 0.01 V."
        ::= { analogdata1 4 }

    inputLineVoltageB1 OBJECT-TYPE
        SYNTAX Integer32
        MAX-ACCESS read-only
        STATUS current
        DESCRIPTION
            "Input Line Voltage B, stored as 0.01 V."
        ::= { analogdata1 5 }

    inputLineVoltageC1 OBJECT-TYPE
        SYNTAX Integer32
        MAX-ACCESS read-only
        STATUS current
        DESCRIPTION
            "Input Line Voltage C, stored as 0.01 V."
        ::= { analogdata1 6 }

    inputCurrentA1 OBJECT-TYPE
        SYNTAX Integer32
        MAX-ACCESS read-only
        STATUS current
        DESCRIPTION
            "Input Current A, stored as 0.01 A."
        ::= { analogdata1 7 }

    inputCurrentB1 OBJECT-TYPE
        SYNTAX Integer32
        MAX-ACCESS read-only
        STATUS current
        DESCRIPTION
            "Input Current B, stored as 0.01 A."
        ::= { analogdata1 8 }

    inputCurrentC1 OBJECT-TYPE
        SYNTAX Integer32
        MAX-ACCESS read-only
        STATUS current
        DESCRIPTION
            "Input Current C, stored as 0.01 A."
        ::= { analogdata1 9 }

    inputFrequency1 OBJECT-TYPE
        SYNTAX Integer32
        MAX-ACCESS read-only
        STATUS current
        DESCRIPTION
            "Input Frequency, stored as 0.01 Hz."
        ::= { analogdata1 10 }

    inputPowerFactorA1 OBJECT-TYPE
        SYNTAX Integer32
        MAX-ACCESS read-only
        STATUS current
        DESCRIPTION
            "Input Power Factor A, stored as 0.01."
        ::= { analogdata1 11 }

    inputPowerFactorB1 OBJECT-TYPE
        SYNTAX Integer32
        MAX-ACCESS read-only
        STATUS current
        DESCRIPTION
            "Input Power Factor B, stored as 0.01."
        ::= { analogdata1 12 }

    inputPowerFactorC1 OBJECT-TYPE
        SYNTAX Integer32
        MAX-ACCESS read-only
        STATUS current
        DESCRIPTION
            "Input Power Factor C, stored as 0.01."
        ::= { analogdata1 13 }

    dCBus1Voltage1 OBJECT-TYPE
        SYNTAX Integer32
        MAX-ACCESS read-only
        STATUS current
        DESCRIPTION
            "DCBus1 Voltage, stored as 0.01 V."
        ::= { analogdata1 14 }

    dCBus2Voltage1 OBJECT-TYPE
        SYNTAX Integer32
        MAX-ACCESS read-only
        STATUS current
        DESCRIPTION
            "DCBus2 Voltage, stored as 0.01 V."
        ::= { analogdata1 15 }

    outputVoltageA1 OBJECT-TYPE
    	SYNTAX Integer32
    	MAX-ACCESS read-only
        STATUS current
        DESCRIPTION
            "Output voltage A, stored as 0.01 V."
        ::= { analogdata1 16 }

    outputVoltageB1 OBJECT-TYPE
    	SYNTAX Integer32
    	MAX-ACCESS read-only
        STATUS current
        DESCRIPTION
            "Output voltage B, stored as 0.01 V."
        ::= { analogdata1 17 }

    outputVoltageC1 OBJECT-TYPE
    	SYNTAX Integer32
    	MAX-ACCESS read-only
        STATUS current
        DESCRIPTION
            "Output voltage C, stored as 0.01 V."
        ::= { analogdata1 18 }

    outputCurrentA1 OBJECT-TYPE
        SYNTAX Integer32
        MAX-ACCESS read-only
        STATUS current
        DESCRIPTION
            "Output current A, stored as 0.01 A."
        ::= { analogdata1 19 }

    outputCurrentB1 OBJECT-TYPE
        SYNTAX Integer32
        MAX-ACCESS read-only
        STATUS current
        DESCRIPTION
            "Output current B, stored as 0.01 A."
        ::= { analogdata1 20 }

    outputCurrentC1 OBJECT-TYPE
        SYNTAX Integer32
        MAX-ACCESS read-only
        STATUS current
        DESCRIPTION
            "Output current C, stored as 0.01 A."
        ::= { analogdata1 21 }

    outputFrequency1 OBJECT-TYPE
        SYNTAX Integer32
        MAX-ACCESS read-only
        STATUS current
        DESCRIPTION
            "Output Frequency, stored as 0.01 Hz."
        ::= { analogdata1 22 }

    outputPowerFactorA1 OBJECT-TYPE
        SYNTAX Integer32
        MAX-ACCESS read-only
        STATUS current
        DESCRIPTION
            "Output Power Factor A, stored as 0.01."
        ::= { analogdata1 23 }

    outputPowerFactorB1 OBJECT-TYPE
        SYNTAX Integer32
        MAX-ACCESS read-only
        STATUS current
        DESCRIPTION
            "Output Power Factor B, stored as 0.01."
        ::= { analogdata1 24 }

    outputPowerFactorC1 OBJECT-TYPE
        SYNTAX Integer32
        MAX-ACCESS read-only
        STATUS current
        DESCRIPTION
            "Output Power Factor C, stored as 0.01."
        ::= { analogdata1 25 }

    outputAcitvePowerA1 OBJECT-TYPE
        SYNTAX Integer32
        MAX-ACCESS read-only
        STATUS current
        DESCRIPTION
            "Output Acitve Power A, stored as 0.01 kW."
        ::= { analogdata1 26 }

    outputAcitvePowerB1 OBJECT-TYPE
        SYNTAX Integer32
        MAX-ACCESS read-only
        STATUS current
        DESCRIPTION
            "Output Acitve Power B, stored as 0.01 kW."
        ::= { analogdata1 27 }

    outputAcitvePowerC1 OBJECT-TYPE
        SYNTAX Integer32
        MAX-ACCESS read-only
        STATUS current
        DESCRIPTION
            "Output Acitve Power C, stored as 0.01 kW."
        ::= { analogdata1 28 }

    outputReactivePowerA1 OBJECT-TYPE
        SYNTAX Integer32
        MAX-ACCESS read-only
        STATUS current
        DESCRIPTION
            "Output Reactive Power A, stored as 0.01 KVAR."
        ::= { analogdata1 29 }

    outputReactivePowerB1 OBJECT-TYPE
        SYNTAX Integer32
        MAX-ACCESS read-only
        STATUS current
        DESCRIPTION
            "Output Reactive Power B, stored as 0.01 KVAR."
        ::= { analogdata1 30 }

    outputReactivePowerC1 OBJECT-TYPE
        SYNTAX Integer32
        MAX-ACCESS read-only
        STATUS current
        DESCRIPTION
            "Output Reactive Power C, stored as 0.01 KVAR."
        ::= { analogdata1 31 }

    outputAppPowerA1 OBJECT-TYPE
        SYNTAX Integer32
        MAX-ACCESS read-only
        STATUS current
        DESCRIPTION
            "Output App Power A, stored as 0.01 kVA."
        ::= { analogdata1 32 }

    outputAppPowerB1 OBJECT-TYPE
        SYNTAX Integer32
        MAX-ACCESS read-only
        STATUS current
        DESCRIPTION
            "Output App Power B, stored as 0.01 kVA."
        ::= { analogdata1 33 }

    outputAppPowerC1 OBJECT-TYPE
        SYNTAX Integer32
        MAX-ACCESS read-only
        STATUS current
        DESCRIPTION
            "Output App Power C, stored as 0.01 kVA."
        ::= { analogdata1 34 }

    outputLoadA1 OBJECT-TYPE
        SYNTAX Integer32
        MAX-ACCESS read-only
        STATUS current
        DESCRIPTION
            "Output Load A, stored as 0.01 %."
        ::= { analogdata1 35 }

    outputLoadB1 OBJECT-TYPE
        SYNTAX Integer32
        MAX-ACCESS read-only
        STATUS current
        DESCRIPTION
            "Output Load B, stored as 0.01 %."
        ::= { analogdata1 36 }

    outputLoadC1 OBJECT-TYPE
        SYNTAX Integer32
        MAX-ACCESS read-only
        STATUS current
        DESCRIPTION
            "Output Load C, stored as 0.01 %."
        ::= { analogdata1 37 }

    outputCrestFactorA1 OBJECT-TYPE
        SYNTAX Integer32
        MAX-ACCESS read-only
        STATUS current
        DESCRIPTION
            "Output Crest Factor A, stored as 0.01 ."
        ::= { analogdata1 38 }

    outputCrestFactorB1 OBJECT-TYPE
        SYNTAX Integer32
        MAX-ACCESS read-only
        STATUS current
        DESCRIPTION
            "Output Crest Factor B, stored as 0.01 ."
        ::= { analogdata1 39 }

    outputCrestFactorC1 OBJECT-TYPE
        SYNTAX Integer32
        MAX-ACCESS read-only
        STATUS current
        DESCRIPTION
            "Output Crest Factor C, stored as 0.01 ."
        ::= { analogdata1 40 }

    bypassVoltageA1 OBJECT-TYPE
        SYNTAX Integer32
        MAX-ACCESS read-only
        STATUS current
        DESCRIPTION
            "Bypass Voltage A, stored as 0.01 V."
        ::= { analogdata1 41 }

    bypassVoltageB1 OBJECT-TYPE
        SYNTAX Integer32
        MAX-ACCESS read-only
        STATUS current
        DESCRIPTION
            "Bypass Voltage B, stored as 0.01 V."
        ::= { analogdata1 42 }

    bypassVoltageC1 OBJECT-TYPE
        SYNTAX Integer32
        MAX-ACCESS read-only
        STATUS current
        DESCRIPTION
            "Bypass Voltage C, stored as 0.01 V."
        ::= { analogdata1 43 }

    bypassFrequency1 OBJECT-TYPE
        SYNTAX Integer32
        MAX-ACCESS read-only
        STATUS current
        DESCRIPTION
            "Bypass Frequency, stored as 0.01 Hz."
        ::= { analogdata1 44 }

    positiveBatteryVoltage1 OBJECT-TYPE
        SYNTAX Integer32
        MAX-ACCESS read-only
        STATUS current
        DESCRIPTION
            "positive Battery Voltage, stored as 0.01 V."
        ::= { analogdata1 45 }

    positiveBatteryCurrent1 OBJECT-TYPE
        SYNTAX Integer32
        MAX-ACCESS read-only
        STATUS current
        DESCRIPTION
            "positive Battery Current, stored as 0.01 A."
        ::= { analogdata1 46 }

    negativeBatteryVoltage1 OBJECT-TYPE
        SYNTAX Integer32
        MAX-ACCESS read-only
        STATUS current
        DESCRIPTION
            "negative Battery Voltage, stored as 0.01 V."
        ::= { analogdata1 47 }

    negativeBatteryCurrent1 OBJECT-TYPE
        SYNTAX Integer32
        MAX-ACCESS read-only
        STATUS current
        DESCRIPTION
            "negative Battery Current, stored as 0.01 A."
        ::= { analogdata1 48 }

    batteryAgingRate1 OBJECT-TYPE
        SYNTAX Integer32
        MAX-ACCESS read-only
        STATUS current
        DESCRIPTION
            "Battery Aging Rate, stored as 0.01."
        ::= { analogdata1 49 }

    batteryRemainsTime1 OBJECT-TYPE
        SYNTAX Integer32
        MAX-ACCESS read-only
        STATUS current
        DESCRIPTION
            "Battery Remains Time, stored as 0.01 Hour."
        ::= { analogdata1 50 }

    batteryTemperature1 OBJECT-TYPE
        SYNTAX Integer32
        MAX-ACCESS read-only
        STATUS current
        DESCRIPTION
            "Battery Temperature, stored as 0.01 &deg;C."
        ::= { analogdata1 51 }

    batteryEnvironmentTemperature1 OBJECT-TYPE
        SYNTAX Integer32
        MAX-ACCESS read-only
        STATUS current
        DESCRIPTION
            "Battery Environment Temperature, stored as 0.01 &deg;C."
        ::= { analogdata1 52 }
        
analogdata2 OBJECT IDENTIFIER ::= { system 6 }

    inputPhaseVoltageA2 OBJECT-TYPE
        SYNTAX Integer32
        MAX-ACCESS read-only
        STATUS current
        DESCRIPTION
            "Input Phase Voltage A, stored as 0.01 V."
        ::= { analogdata2 1 }

    inputPhaseVoltageB2 OBJECT-TYPE
        SYNTAX Integer32
        MAX-ACCESS read-only
        STATUS current
        DESCRIPTION
            "Input Phase Voltage B, stored as 0.01 V."
        ::= { analogdata2 2 }

    inputPhaseVoltageC2 OBJECT-TYPE
        SYNTAX Integer32
        MAX-ACCESS read-only
        STATUS current
        DESCRIPTION
            "Input Phase Voltage C, stored as 0.01 V."
        ::= { analogdata2 3 }

    inputLineVoltageA2 OBJECT-TYPE
        SYNTAX Integer32
        MAX-ACCESS read-only
        STATUS current
        DESCRIPTION
            "Input Line Voltage A, stored as 0.01 V."
        ::= { analogdata2 4 }

    inputLineVoltageB2 OBJECT-TYPE
        SYNTAX Integer32
        MAX-ACCESS read-only
        STATUS current
        DESCRIPTION
            "Input Line Voltage B, stored as 0.01 V."
        ::= { analogdata2 5 }

    inputLineVoltageC2 OBJECT-TYPE
        SYNTAX Integer32
        MAX-ACCESS read-only
        STATUS current
        DESCRIPTION
            "Input Line Voltage C, stored as 0.01 V."
        ::= { analogdata2 6 }

    inputCurrentA2 OBJECT-TYPE
        SYNTAX Integer32
        MAX-ACCESS read-only
        STATUS current
        DESCRIPTION
            "Input Current A, stored as 0.01 A."
        ::= { analogdata2 7 }

    inputCurrentB2 OBJECT-TYPE
        SYNTAX Integer32
        MAX-ACCESS read-only
        STATUS current
        DESCRIPTION
            "Input Current B, stored as 0.01 A."
        ::= { analogdata2 8 }

    inputCurrentC2 OBJECT-TYPE
        SYNTAX Integer32
        MAX-ACCESS read-only
        STATUS current
        DESCRIPTION
            "Input Current C, stored as 0.01 A."
        ::= { analogdata2 9 }

    inputFrequency2 OBJECT-TYPE
        SYNTAX Integer32
        MAX-ACCESS read-only
        STATUS current
        DESCRIPTION
            "Input Frequency, stored as 0.01 Hz."
        ::= { analogdata2 10 }

    inputPowerFactorA2 OBJECT-TYPE
        SYNTAX Integer32
        MAX-ACCESS read-only
        STATUS current
        DESCRIPTION
            "Input Power Factor A, stored as 0.01."
        ::= { analogdata2 11 }

    inputPowerFactorB2 OBJECT-TYPE
        SYNTAX Integer32
        MAX-ACCESS read-only
        STATUS current
        DESCRIPTION
            "Input Power Factor B, stored as 0.01."
        ::= { analogdata2 12 }

    inputPowerFactorC2 OBJECT-TYPE
        SYNTAX Integer32
        MAX-ACCESS read-only
        STATUS current
        DESCRIPTION
            "Input Power Factor C, stored as 0.01."
        ::= { analogdata2 13 }

    dCBus1Voltage2 OBJECT-TYPE
        SYNTAX Integer32
        MAX-ACCESS read-only
        STATUS current
        DESCRIPTION
            "DCBus1 Voltage, stored as 0.01 V."
        ::= { analogdata2 14 }

    dCBus2Voltage2 OBJECT-TYPE
        SYNTAX Integer32
        MAX-ACCESS read-only
        STATUS current
        DESCRIPTION
            "DCBus2 Voltage, stored as 0.01 V."
        ::= { analogdata2 15 }

    outputVoltageA2 OBJECT-TYPE
    	SYNTAX Integer32
    	MAX-ACCESS read-only
        STATUS current
        DESCRIPTION
            "Output voltage A, stored as 0.01 V."
        ::= { analogdata2 16 }

    outputVoltageB2 OBJECT-TYPE
    	SYNTAX Integer32
    	MAX-ACCESS read-only
        STATUS current
        DESCRIPTION
            "Output voltage B, stored as 0.01 V."
        ::= { analogdata2 17 }

    outputVoltageC2 OBJECT-TYPE
    	SYNTAX Integer32
    	MAX-ACCESS read-only
        STATUS current
        DESCRIPTION
            "Output voltage C, stored as 0.01 V."
        ::= { analogdata2 18 }

    outputCurrentA2 OBJECT-TYPE
        SYNTAX Integer32
        MAX-ACCESS read-only
        STATUS current
        DESCRIPTION
            "Output current A, stored as 0.01 A."
        ::= { analogdata2 19 }

    outputCurrentB2 OBJECT-TYPE
        SYNTAX Integer32
        MAX-ACCESS read-only
        STATUS current
        DESCRIPTION
            "Output current B, stored as 0.01 A."
        ::= { analogdata2 20 }

    outputCurrentC2 OBJECT-TYPE
        SYNTAX Integer32
        MAX-ACCESS read-only
        STATUS current
        DESCRIPTION
            "Output current C, stored as 0.01 A."
        ::= { analogdata2 21 }

    outputFrequency2 OBJECT-TYPE
        SYNTAX Integer32
        MAX-ACCESS read-only
        STATUS current
        DESCRIPTION
            "Output Frequency, stored as 0.01 Hz."
        ::= { analogdata2 22 }

    outputPowerFactorA2 OBJECT-TYPE
        SYNTAX Integer32
        MAX-ACCESS read-only
        STATUS current
        DESCRIPTION
            "Output Power Factor A, stored as 0.01."
        ::= { analogdata2 23 }

    outputPowerFactorB2 OBJECT-TYPE
        SYNTAX Integer32
        MAX-ACCESS read-only
        STATUS current
        DESCRIPTION
            "Output Power Factor B, stored as 0.01."
        ::= { analogdata2 24 }

    outputPowerFactorC2 OBJECT-TYPE
        SYNTAX Integer32
        MAX-ACCESS read-only
        STATUS current
        DESCRIPTION
            "Output Power Factor C, stored as 0.01."
        ::= { analogdata2 25 }

    outputAcitvePowerA2 OBJECT-TYPE
        SYNTAX Integer32
        MAX-ACCESS read-only
        STATUS current
        DESCRIPTION
            "Output Acitve Power A, stored as 0.01 kW."
        ::= { analogdata2 26 }

    outputAcitvePowerB2 OBJECT-TYPE
        SYNTAX Integer32
        MAX-ACCESS read-only
        STATUS current
        DESCRIPTION
            "Output Acitve Power B, stored as 0.01 kW."
        ::= { analogdata2 27 }

    outputAcitvePowerC2 OBJECT-TYPE
        SYNTAX Integer32
        MAX-ACCESS read-only
        STATUS current
        DESCRIPTION
            "Output Acitve Power C, stored as 0.01 kW."
        ::= { analogdata2 28 }

    outputReactivePowerA2 OBJECT-TYPE
        SYNTAX Integer32
        MAX-ACCESS read-only
        STATUS current
        DESCRIPTION
            "Output Reactive Power A, stored as 0.01 KVAR."
        ::= { analogdata2 29 }

    outputReactivePowerB2 OBJECT-TYPE
        SYNTAX Integer32
        MAX-ACCESS read-only
        STATUS current
        DESCRIPTION
            "Output Reactive Power B, stored as 0.01 KVAR."
        ::= { analogdata2 30 }

    outputReactivePowerC2 OBJECT-TYPE
        SYNTAX Integer32
        MAX-ACCESS read-only
        STATUS current
        DESCRIPTION
            "Output Reactive Power C, stored as 0.01 KVAR."
        ::= { analogdata2 31 }

    outputAppPowerA2 OBJECT-TYPE
        SYNTAX Integer32
        MAX-ACCESS read-only
        STATUS current
        DESCRIPTION
            "Output App Power A, stored as 0.01 kVA."
        ::= { analogdata2 32 }

    outputAppPowerB2 OBJECT-TYPE
        SYNTAX Integer32
        MAX-ACCESS read-only
        STATUS current
        DESCRIPTION
            "Output App Power B, stored as 0.01 kVA."
        ::= { analogdata2 33 }

    outputAppPowerC2 OBJECT-TYPE
        SYNTAX Integer32
        MAX-ACCESS read-only
        STATUS current
        DESCRIPTION
            "Output App Power C, stored as 0.01 kVA."
        ::= { analogdata2 34 }

    outputLoadA2 OBJECT-TYPE
        SYNTAX Integer32
        MAX-ACCESS read-only
        STATUS current
        DESCRIPTION
            "Output Load A, stored as 0.01 %."
        ::= { analogdata2 35 }

    outputLoadB2 OBJECT-TYPE
        SYNTAX Integer32
        MAX-ACCESS read-only
        STATUS current
        DESCRIPTION
            "Output Load B, stored as 0.01 %."
        ::= { analogdata2 36 }

    outputLoadC2 OBJECT-TYPE
        SYNTAX Integer32
        MAX-ACCESS read-only
        STATUS current
        DESCRIPTION
            "Output Load C, stored as 0.01 %."
        ::= { analogdata2 37 }

    outputCrestFactorA2 OBJECT-TYPE
        SYNTAX Integer32
        MAX-ACCESS read-only
        STATUS current
        DESCRIPTION
            "Output Crest Factor A, stored as 0.01 ."
        ::= { analogdata2 38 }

    outputCrestFactorB2 OBJECT-TYPE
        SYNTAX Integer32
        MAX-ACCESS read-only
        STATUS current
        DESCRIPTION
            "Output Crest Factor B, stored as 0.01 ."
        ::= { analogdata2 39 }

    outputCrestFactorC2 OBJECT-TYPE
        SYNTAX Integer32
        MAX-ACCESS read-only
        STATUS current
        DESCRIPTION
            "Output Crest Factor C, stored as 0.01 ."
        ::= { analogdata2 40 }

    bypassVoltageA2 OBJECT-TYPE
        SYNTAX Integer32
        MAX-ACCESS read-only
        STATUS current
        DESCRIPTION
            "Bypass Voltage A, stored as 0.01 V."
        ::= { analogdata2 41 }

    bypassVoltageB2 OBJECT-TYPE
        SYNTAX Integer32
        MAX-ACCESS read-only
        STATUS current
        DESCRIPTION
            "Bypass Voltage B, stored as 0.01 V."
        ::= { analogdata2 42 }

    bypassVoltageC2 OBJECT-TYPE
        SYNTAX Integer32
        MAX-ACCESS read-only
        STATUS current
        DESCRIPTION
            "Bypass Voltage C, stored as 0.01 V."
        ::= { analogdata2 43 }

    bypassFrequency2 OBJECT-TYPE
        SYNTAX Integer32
        MAX-ACCESS read-only
        STATUS current
        DESCRIPTION
            "Bypass Frequency, stored as 0.01 Hz."
        ::= { analogdata2 44 }

    positiveBatteryVoltage2 OBJECT-TYPE
        SYNTAX Integer32
        MAX-ACCESS read-only
        STATUS current
        DESCRIPTION
            "positive Battery Voltage, stored as 0.01 V."
        ::= { analogdata2 45 }

    positiveBatteryCurrent2 OBJECT-TYPE
        SYNTAX Integer32
        MAX-ACCESS read-only
        STATUS current
        DESCRIPTION
            "positive Battery Current, stored as 0.01 A."
        ::= { analogdata2 46 }

    negativeBatteryVoltage2 OBJECT-TYPE
        SYNTAX Integer32
        MAX-ACCESS read-only
        STATUS current
        DESCRIPTION
            "negative Battery Voltage, stored as 0.01 V."
        ::= { analogdata2 47 }

    negativeBatteryCurrent2 OBJECT-TYPE
        SYNTAX Integer32
        MAX-ACCESS read-only
        STATUS current
        DESCRIPTION
            "negative Battery Current, stored as 0.01 A."
        ::= { analogdata2 48 }

    batteryAgingRate2 OBJECT-TYPE
        SYNTAX Integer32
        MAX-ACCESS read-only
        STATUS current
        DESCRIPTION
            "Battery Aging Rate, stored as 0.01."
        ::= { analogdata2 49 }

    batteryRemainsTime2 OBJECT-TYPE
        SYNTAX Integer32
        MAX-ACCESS read-only
        STATUS current
        DESCRIPTION
            "Battery Remains Time, stored as 0.01 Hour."
        ::= { analogdata2 50 }

    batteryTemperature2 OBJECT-TYPE
        SYNTAX Integer32
        MAX-ACCESS read-only
        STATUS current
        DESCRIPTION
            "Battery Temperature, stored as 0.01 &deg;C."
        ::= { analogdata2 51 }

    batteryEnvironmentTemperature2 OBJECT-TYPE
        SYNTAX Integer32
        MAX-ACCESS read-only
        STATUS current
        DESCRIPTION
            "Battery Environment Temperature, stored as 0.01 &deg;C."
        ::= { analogdata2 52 }

analogdata3 OBJECT IDENTIFIER ::= { system 7 }

    inputPhaseVoltageA3 OBJECT-TYPE
        SYNTAX Integer32
        MAX-ACCESS read-only
        STATUS current
        DESCRIPTION
            "Input Phase Voltage A, stored as 0.01 V."
        ::= { analogdata3 1 }

    inputPhaseVoltageB3 OBJECT-TYPE
        SYNTAX Integer32
        MAX-ACCESS read-only
        STATUS current
        DESCRIPTION
            "Input Phase Voltage B, stored as 0.01 V."
        ::= { analogdata3 2 }

    inputPhaseVoltageC3 OBJECT-TYPE
        SYNTAX Integer32
        MAX-ACCESS read-only
        STATUS current
        DESCRIPTION
            "Input Phase Voltage C, stored as 0.01 V."
        ::= { analogdata3 3 }

    inputLineVoltageA3 OBJECT-TYPE
        SYNTAX Integer32
        MAX-ACCESS read-only
        STATUS current
        DESCRIPTION
            "Input Line Voltage A, stored as 0.01 V."
        ::= { analogdata3 4 }

    inputLineVoltageB3 OBJECT-TYPE
        SYNTAX Integer32
        MAX-ACCESS read-only
        STATUS current
        DESCRIPTION
            "Input Line Voltage B, stored as 0.01 V."
        ::= { analogdata3 5 }

    inputLineVoltageC3 OBJECT-TYPE
        SYNTAX Integer32
        MAX-ACCESS read-only
        STATUS current
        DESCRIPTION
            "Input Line Voltage C, stored as 0.01 V."
        ::= { analogdata3 6 }

    inputCurrentA3 OBJECT-TYPE
        SYNTAX Integer32
        MAX-ACCESS read-only
        STATUS current
        DESCRIPTION
            "Input Current A, stored as 0.01 A."
        ::= { analogdata3 7 }

    inputCurrentB3 OBJECT-TYPE
        SYNTAX Integer32
        MAX-ACCESS read-only
        STATUS current
        DESCRIPTION
            "Input Current B, stored as 0.01 A."
        ::= { analogdata3 8 }

    inputCurrentC3 OBJECT-TYPE
        SYNTAX Integer32
        MAX-ACCESS read-only
        STATUS current
        DESCRIPTION
            "Input Current C, stored as 0.01 A."
        ::= { analogdata3 9 }

    inputFrequency3 OBJECT-TYPE
        SYNTAX Integer32
        MAX-ACCESS read-only
        STATUS current
        DESCRIPTION
            "Input Frequency, stored as 0.01 Hz."
        ::= { analogdata3 10 }

    inputPowerFactorA3 OBJECT-TYPE
        SYNTAX Integer32
        MAX-ACCESS read-only
        STATUS current
        DESCRIPTION
            "Input Power Factor A, stored as 0.01."
        ::= { analogdata3 11 }

    inputPowerFactorB3 OBJECT-TYPE
        SYNTAX Integer32
        MAX-ACCESS read-only
        STATUS current
        DESCRIPTION
            "Input Power Factor B, stored as 0.01."
        ::= { analogdata3 12 }

    inputPowerFactorC3 OBJECT-TYPE
        SYNTAX Integer32
        MAX-ACCESS read-only
        STATUS current
        DESCRIPTION
            "Input Power Factor C, stored as 0.01."
        ::= { analogdata3 13 }

    dCBus1Voltage3 OBJECT-TYPE
        SYNTAX Integer32
        MAX-ACCESS read-only
        STATUS current
        DESCRIPTION
            "DCBus1 Voltage, stored as 0.01 V."
        ::= { analogdata3 14 }

    dCBus2Voltage3 OBJECT-TYPE
        SYNTAX Integer32
        MAX-ACCESS read-only
        STATUS current
        DESCRIPTION
            "DCBus2 Voltage, stored as 0.01 V."
        ::= { analogdata3 15 }

    outputVoltageA3 OBJECT-TYPE
    	SYNTAX Integer32
    	MAX-ACCESS read-only
        STATUS current
        DESCRIPTION
            "Output voltage A, stored as 0.01 V."
        ::= { analogdata3 16 }

    outputVoltageB3 OBJECT-TYPE
    	SYNTAX Integer32
    	MAX-ACCESS read-only
        STATUS current
        DESCRIPTION
            "Output voltage B, stored as 0.01 V."
        ::= { analogdata3 17 }

    outputVoltageC3 OBJECT-TYPE
    	SYNTAX Integer32
    	MAX-ACCESS read-only
        STATUS current
        DESCRIPTION
            "Output voltage C, stored as 0.01 V."
        ::= { analogdata3 18 }

    outputCurrentA3 OBJECT-TYPE
        SYNTAX Integer32
        MAX-ACCESS read-only
        STATUS current
        DESCRIPTION
            "Output current A, stored as 0.01 A."
        ::= { analogdata3 19 }

    outputCurrentB3 OBJECT-TYPE
        SYNTAX Integer32
        MAX-ACCESS read-only
        STATUS current
        DESCRIPTION
            "Output current B, stored as 0.01 A."
        ::= { analogdata3 20 }

    outputCurrentC3 OBJECT-TYPE
        SYNTAX Integer32
        MAX-ACCESS read-only
        STATUS current
        DESCRIPTION
            "Output current C, stored as 0.01 A."
        ::= { analogdata3 21 }

    outputFrequency3 OBJECT-TYPE
        SYNTAX Integer32
        MAX-ACCESS read-only
        STATUS current
        DESCRIPTION
            "Output Frequency, stored as 0.01 Hz."
        ::= { analogdata3 22 }

    outputPowerFactorA3 OBJECT-TYPE
        SYNTAX Integer32
        MAX-ACCESS read-only
        STATUS current
        DESCRIPTION
            "Output Power Factor A, stored as 0.01."
        ::= { analogdata3 23 }

    outputPowerFactorB3 OBJECT-TYPE
        SYNTAX Integer32
        MAX-ACCESS read-only
        STATUS current
        DESCRIPTION
            "Output Power Factor B, stored as 0.01."
        ::= { analogdata3 24 }

    outputPowerFactorC3 OBJECT-TYPE
        SYNTAX Integer32
        MAX-ACCESS read-only
        STATUS current
        DESCRIPTION
            "Output Power Factor C, stored as 0.01."
        ::= { analogdata3 25 }

    outputAcitvePowerA3 OBJECT-TYPE
        SYNTAX Integer32
        MAX-ACCESS read-only
        STATUS current
        DESCRIPTION
            "Output Acitve Power A, stored as 0.01 kW."
        ::= { analogdata3 26 }

    outputAcitvePowerB3 OBJECT-TYPE
        SYNTAX Integer32
        MAX-ACCESS read-only
        STATUS current
        DESCRIPTION
            "Output Acitve Power B, stored as 0.01 kW."
        ::= { analogdata3 27 }

    outputAcitvePowerC3 OBJECT-TYPE
        SYNTAX Integer32
        MAX-ACCESS read-only
        STATUS current
        DESCRIPTION
            "Output Acitve Power C, stored as 0.01 kW."
        ::= { analogdata3 28 }

    outputReactivePowerA3 OBJECT-TYPE
        SYNTAX Integer32
        MAX-ACCESS read-only
        STATUS current
        DESCRIPTION
            "Output Reactive Power A, stored as 0.01 KVAR."
        ::= { analogdata3 29 }

    outputReactivePowerB3 OBJECT-TYPE
        SYNTAX Integer32
        MAX-ACCESS read-only
        STATUS current
        DESCRIPTION
            "Output Reactive Power B, stored as 0.01 KVAR."
        ::= { analogdata3 30 }

    outputReactivePowerC3 OBJECT-TYPE
        SYNTAX Integer32
        MAX-ACCESS read-only
        STATUS current
        DESCRIPTION
            "Output Reactive Power C, stored as 0.01 KVAR."
        ::= { analogdata3 31 }

    outputAppPowerA3 OBJECT-TYPE
        SYNTAX Integer32
        MAX-ACCESS read-only
        STATUS current
        DESCRIPTION
            "Output App Power A, stored as 0.01 kVA."
        ::= { analogdata3 32 }

    outputAppPowerB3 OBJECT-TYPE
        SYNTAX Integer32
        MAX-ACCESS read-only
        STATUS current
        DESCRIPTION
            "Output App Power B, stored as 0.01 kVA."
        ::= { analogdata3 33 }

    outputAppPowerC3 OBJECT-TYPE
        SYNTAX Integer32
        MAX-ACCESS read-only
        STATUS current
        DESCRIPTION
            "Output App Power C, stored as 0.01 kVA."
        ::= { analogdata3 34 }

    outputLoadA3 OBJECT-TYPE
        SYNTAX Integer32
        MAX-ACCESS read-only
        STATUS current
        DESCRIPTION
            "Output Load A, stored as 0.01 %."
        ::= { analogdata3 35 }

    outputLoadB3 OBJECT-TYPE
        SYNTAX Integer32
        MAX-ACCESS read-only
        STATUS current
        DESCRIPTION
            "Output Load B, stored as 0.01 %."
        ::= { analogdata3 36 }

    outputLoadC3 OBJECT-TYPE
        SYNTAX Integer32
        MAX-ACCESS read-only
        STATUS current
        DESCRIPTION
            "Output Load C, stored as 0.01 %."
        ::= { analogdata3 37 }

    outputCrestFactorA3 OBJECT-TYPE
        SYNTAX Integer32
        MAX-ACCESS read-only
        STATUS current
        DESCRIPTION
            "Output Crest Factor A, stored as 0.01 ."
        ::= { analogdata3 38 }

    outputCrestFactorB3 OBJECT-TYPE
        SYNTAX Integer32
        MAX-ACCESS read-only
        STATUS current
        DESCRIPTION
            "Output Crest Factor B, stored as 0.01 ."
        ::= { analogdata3 39 }

    outputCrestFactorC3 OBJECT-TYPE
        SYNTAX Integer32
        MAX-ACCESS read-only
        STATUS current
        DESCRIPTION
            "Output Crest Factor C, stored as 0.01 ."
        ::= { analogdata3 40 }

    bypassVoltageA3 OBJECT-TYPE
        SYNTAX Integer32
        MAX-ACCESS read-only
        STATUS current
        DESCRIPTION
            "Bypass Voltage A, stored as 0.01 V."
        ::= { analogdata3 41 }

    bypassVoltageB3 OBJECT-TYPE
        SYNTAX Integer32
        MAX-ACCESS read-only
        STATUS current
        DESCRIPTION
            "Bypass Voltage B, stored as 0.01 V."
        ::= { analogdata3 42 }

    bypassVoltageC3 OBJECT-TYPE
        SYNTAX Integer32
        MAX-ACCESS read-only
        STATUS current
        DESCRIPTION
            "Bypass Voltage C, stored as 0.01 V."
        ::= { analogdata3 43 }

    bypassFrequency3 OBJECT-TYPE
        SYNTAX Integer32
        MAX-ACCESS read-only
        STATUS current
        DESCRIPTION
            "Bypass Frequency, stored as 0.01 Hz."
        ::= { analogdata3 44 }

    positiveBatteryVoltage3 OBJECT-TYPE
        SYNTAX Integer32
        MAX-ACCESS read-only
        STATUS current
        DESCRIPTION
            "positive Battery Voltage, stored as 0.01 V."
        ::= { analogdata3 45 }

    positiveBatteryCurrent3 OBJECT-TYPE
        SYNTAX Integer32
        MAX-ACCESS read-only
        STATUS current
        DESCRIPTION
            "positive Battery Current, stored as 0.01 A."
        ::= { analogdata3 46 }

    negativeBatteryVoltage3 OBJECT-TYPE
        SYNTAX Integer32
        MAX-ACCESS read-only
        STATUS current
        DESCRIPTION
            "negative Battery Voltage, stored as 0.01 V."
        ::= { analogdata3 47 }

    negativeBatteryCurrent3 OBJECT-TYPE
        SYNTAX Integer32
        MAX-ACCESS read-only
        STATUS current
        DESCRIPTION
            "negative Battery Current, stored as 0.01 A."
        ::= { analogdata3 48 }

    batteryAgingRate3 OBJECT-TYPE
        SYNTAX Integer32
        MAX-ACCESS read-only
        STATUS current
        DESCRIPTION
            "Battery Aging Rate, stored as 0.01."
        ::= { analogdata3 49 }

    batteryRemainsTime3 OBJECT-TYPE
        SYNTAX Integer32
        MAX-ACCESS read-only
        STATUS current
        DESCRIPTION
            "Battery Remains Time, stored as 0.01 Hour."
        ::= { analogdata3 50 }

    batteryTemperature3 OBJECT-TYPE
        SYNTAX Integer32
        MAX-ACCESS read-only
        STATUS current
        DESCRIPTION
            "Battery Temperature, stored as 0.01 &deg;C."
        ::= { analogdata3 51 }

    batteryEnvironmentTemperature3 OBJECT-TYPE
        SYNTAX Integer32
        MAX-ACCESS read-only
        STATUS current
        DESCRIPTION
            "Battery Environment Temperature, stored as 0.01 &deg;C."
        ::= { analogdata3 52 }
        
analogdata4 OBJECT IDENTIFIER ::= { system 8 }

    inputPhaseVoltageA4 OBJECT-TYPE
        SYNTAX Integer32
        MAX-ACCESS read-only
        STATUS current
        DESCRIPTION
            "Input Phase Voltage A, stored as 0.01 V."
        ::= { analogdata4 1 }

    inputPhaseVoltageB4 OBJECT-TYPE
        SYNTAX Integer32
        MAX-ACCESS read-only
        STATUS current
        DESCRIPTION
            "Input Phase Voltage B, stored as 0.01 V."
        ::= { analogdata4 2 }

    inputPhaseVoltageC4 OBJECT-TYPE
        SYNTAX Integer32
        MAX-ACCESS read-only
        STATUS current
        DESCRIPTION
            "Input Phase Voltage C, stored as 0.01 V."
        ::= { analogdata4 3 }

    inputLineVoltageA4 OBJECT-TYPE
        SYNTAX Integer32
        MAX-ACCESS read-only
        STATUS current
        DESCRIPTION
            "Input Line Voltage A, stored as 0.01 V."
        ::= { analogdata4 4 }

    inputLineVoltageB4 OBJECT-TYPE
        SYNTAX Integer32
        MAX-ACCESS read-only
        STATUS current
        DESCRIPTION
            "Input Line Voltage B, stored as 0.01 V."
        ::= { analogdata4 5 }

    inputLineVoltageC4 OBJECT-TYPE
        SYNTAX Integer32
        MAX-ACCESS read-only
        STATUS current
        DESCRIPTION
            "Input Line Voltage C, stored as 0.01 V."
        ::= { analogdata4 6 }

    inputCurrentA4 OBJECT-TYPE
        SYNTAX Integer32
        MAX-ACCESS read-only
        STATUS current
        DESCRIPTION
            "Input Current A, stored as 0.01 A."
        ::= { analogdata4 7 }

    inputCurrentB4 OBJECT-TYPE
        SYNTAX Integer32
        MAX-ACCESS read-only
        STATUS current
        DESCRIPTION
            "Input Current B, stored as 0.01 A."
        ::= { analogdata4 8 }

    inputCurrentC4 OBJECT-TYPE
        SYNTAX Integer32
        MAX-ACCESS read-only
        STATUS current
        DESCRIPTION
            "Input Current C, stored as 0.01 A."
        ::= { analogdata4 9 }

    inputFrequency4 OBJECT-TYPE
        SYNTAX Integer32
        MAX-ACCESS read-only
        STATUS current
        DESCRIPTION
            "Input Frequency, stored as 0.01 Hz."
        ::= { analogdata4 10 }

    inputPowerFactorA4 OBJECT-TYPE
        SYNTAX Integer32
        MAX-ACCESS read-only
        STATUS current
        DESCRIPTION
            "Input Power Factor A, stored as 0.01."
        ::= { analogdata4 11 }

    inputPowerFactorB4 OBJECT-TYPE
        SYNTAX Integer32
        MAX-ACCESS read-only
        STATUS current
        DESCRIPTION
            "Input Power Factor B, stored as 0.01."
        ::= { analogdata4 12 }

    inputPowerFactorC4 OBJECT-TYPE
        SYNTAX Integer32
        MAX-ACCESS read-only
        STATUS current
        DESCRIPTION
            "Input Power Factor C, stored as 0.01."
        ::= { analogdata4 13 }

    dCBus1Voltage4 OBJECT-TYPE
        SYNTAX Integer32
        MAX-ACCESS read-only
        STATUS current
        DESCRIPTION
            "DCBus1 Voltage, stored as 0.01 V."
        ::= { analogdata4 14 }

    dCBus2Voltage4 OBJECT-TYPE
        SYNTAX Integer32
        MAX-ACCESS read-only
        STATUS current
        DESCRIPTION
            "DCBus2 Voltage, stored as 0.01 V."
        ::= { analogdata4 15 }

    outputVoltageA4 OBJECT-TYPE
    	SYNTAX Integer32
    	MAX-ACCESS read-only
        STATUS current
        DESCRIPTION
            "Output voltage A, stored as 0.01 V."
        ::= { analogdata4 16 }

    outputVoltageB4 OBJECT-TYPE
    	SYNTAX Integer32
    	MAX-ACCESS read-only
        STATUS current
        DESCRIPTION
            "Output voltage B, stored as 0.01 V."
        ::= { analogdata4 17 }

    outputVoltageC4 OBJECT-TYPE
    	SYNTAX Integer32
    	MAX-ACCESS read-only
        STATUS current
        DESCRIPTION
            "Output voltage C, stored as 0.01 V."
        ::= { analogdata4 18 }

    outputCurrentA4 OBJECT-TYPE
        SYNTAX Integer32
        MAX-ACCESS read-only
        STATUS current
        DESCRIPTION
            "Output current A, stored as 0.01 A."
        ::= { analogdata4 19 }

    outputCurrentB4 OBJECT-TYPE
        SYNTAX Integer32
        MAX-ACCESS read-only
        STATUS current
        DESCRIPTION
            "Output current B, stored as 0.01 A."
        ::= { analogdata4 20 }

    outputCurrentC4 OBJECT-TYPE
        SYNTAX Integer32
        MAX-ACCESS read-only
        STATUS current
        DESCRIPTION
            "Output current C, stored as 0.01 A."
        ::= { analogdata4 21 }

    outputFrequency4 OBJECT-TYPE
        SYNTAX Integer32
        MAX-ACCESS read-only
        STATUS current
        DESCRIPTION
            "Output Frequency, stored as 0.01 Hz."
        ::= { analogdata4 22 }

    outputPowerFactorA4 OBJECT-TYPE
        SYNTAX Integer32
        MAX-ACCESS read-only
        STATUS current
        DESCRIPTION
            "Output Power Factor A, stored as 0.01."
        ::= { analogdata4 23 }

    outputPowerFactorB4 OBJECT-TYPE
        SYNTAX Integer32
        MAX-ACCESS read-only
        STATUS current
        DESCRIPTION
            "Output Power Factor B, stored as 0.01."
        ::= { analogdata4 24 }

    outputPowerFactorC4 OBJECT-TYPE
        SYNTAX Integer32
        MAX-ACCESS read-only
        STATUS current
        DESCRIPTION
            "Output Power Factor C, stored as 0.01."
        ::= { analogdata4 25 }

    outputAcitvePowerA4 OBJECT-TYPE
        SYNTAX Integer32
        MAX-ACCESS read-only
        STATUS current
        DESCRIPTION
            "Output Acitve Power A, stored as 0.01 kW."
        ::= { analogdata4 26 }

    outputAcitvePowerB4 OBJECT-TYPE
        SYNTAX Integer32
        MAX-ACCESS read-only
        STATUS current
        DESCRIPTION
            "Output Acitve Power B, stored as 0.01 kW."
        ::= { analogdata4 27 }

    outputAcitvePowerC4 OBJECT-TYPE
        SYNTAX Integer32
        MAX-ACCESS read-only
        STATUS current
        DESCRIPTION
            "Output Acitve Power C, stored as 0.01 kW."
        ::= { analogdata4 28 }

    outputReactivePowerA4 OBJECT-TYPE
        SYNTAX Integer32
        MAX-ACCESS read-only
        STATUS current
        DESCRIPTION
            "Output Reactive Power A, stored as 0.01 KVAR."
        ::= { analogdata4 29 }

    outputReactivePowerB4 OBJECT-TYPE
        SYNTAX Integer32
        MAX-ACCESS read-only
        STATUS current
        DESCRIPTION
            "Output Reactive Power B, stored as 0.01 KVAR."
        ::= { analogdata4 30 }

    outputReactivePowerC4 OBJECT-TYPE
        SYNTAX Integer32
        MAX-ACCESS read-only
        STATUS current
        DESCRIPTION
            "Output Reactive Power C, stored as 0.01 KVAR."
        ::= { analogdata4 31 }

    outputAppPowerA4 OBJECT-TYPE
        SYNTAX Integer32
        MAX-ACCESS read-only
        STATUS current
        DESCRIPTION
            "Output App Power A, stored as 0.01 kVA."
        ::= { analogdata4 32 }

    outputAppPowerB4 OBJECT-TYPE
        SYNTAX Integer32
        MAX-ACCESS read-only
        STATUS current
        DESCRIPTION
            "Output App Power B, stored as 0.01 kVA."
        ::= { analogdata4 33 }

    outputAppPowerC4 OBJECT-TYPE
        SYNTAX Integer32
        MAX-ACCESS read-only
        STATUS current
        DESCRIPTION
            "Output App Power C, stored as 0.01 kVA."
        ::= { analogdata4 34 }

    outputLoadA4 OBJECT-TYPE
        SYNTAX Integer32
        MAX-ACCESS read-only
        STATUS current
        DESCRIPTION
            "Output Load A, stored as 0.01 %."
        ::= { analogdata4 35 }

    outputLoadB4 OBJECT-TYPE
        SYNTAX Integer32
        MAX-ACCESS read-only
        STATUS current
        DESCRIPTION
            "Output Load B, stored as 0.01 %."
        ::= { analogdata4 36 }

    outputLoadC4 OBJECT-TYPE
        SYNTAX Integer32
        MAX-ACCESS read-only
        STATUS current
        DESCRIPTION
            "Output Load C, stored as 0.01 %."
        ::= { analogdata4 37 }

    outputCrestFactorA4 OBJECT-TYPE
        SYNTAX Integer32
        MAX-ACCESS read-only
        STATUS current
        DESCRIPTION
            "Output Crest Factor A, stored as 0.01 ."
        ::= { analogdata4 38 }

    outputCrestFactorB4 OBJECT-TYPE
        SYNTAX Integer32
        MAX-ACCESS read-only
        STATUS current
        DESCRIPTION
            "Output Crest Factor B, stored as 0.01 ."
        ::= { analogdata4 39 }

    outputCrestFactorC4 OBJECT-TYPE
        SYNTAX Integer32
        MAX-ACCESS read-only
        STATUS current
        DESCRIPTION
            "Output Crest Factor C, stored as 0.01 ."
        ::= { analogdata4 40 }

    bypassVoltageA4 OBJECT-TYPE
        SYNTAX Integer32
        MAX-ACCESS read-only
        STATUS current
        DESCRIPTION
            "Bypass Voltage A, stored as 0.01 V."
        ::= { analogdata4 41 }

    bypassVoltageB4 OBJECT-TYPE
        SYNTAX Integer32
        MAX-ACCESS read-only
        STATUS current
        DESCRIPTION
            "Bypass Voltage B, stored as 0.01 V."
        ::= { analogdata4 42 }

    bypassVoltageC4 OBJECT-TYPE
        SYNTAX Integer32
        MAX-ACCESS read-only
        STATUS current
        DESCRIPTION
            "Bypass Voltage C, stored as 0.01 V."
        ::= { analogdata4 43 }

    bypassFrequency4 OBJECT-TYPE
        SYNTAX Integer32
        MAX-ACCESS read-only
        STATUS current
        DESCRIPTION
            "Bypass Frequency, stored as 0.01 Hz."
        ::= { analogdata4 44 }

    positiveBatteryVoltage4 OBJECT-TYPE
        SYNTAX Integer32
        MAX-ACCESS read-only
        STATUS current
        DESCRIPTION
            "positive Battery Voltage, stored as 0.01 V."
        ::= { analogdata4 45 }

    positiveBatteryCurrent4 OBJECT-TYPE
        SYNTAX Integer32
        MAX-ACCESS read-only
        STATUS current
        DESCRIPTION
            "positive Battery Current, stored as 0.01 A."
        ::= { analogdata4 46 }

    negativeBatteryVoltage4 OBJECT-TYPE
        SYNTAX Integer32
        MAX-ACCESS read-only
        STATUS current
        DESCRIPTION
            "negative Battery Voltage, stored as 0.01 V."
        ::= { analogdata4 47 }

    negativeBatteryCurrent4 OBJECT-TYPE
        SYNTAX Integer32
        MAX-ACCESS read-only
        STATUS current
        DESCRIPTION
            "negative Battery Current, stored as 0.01 A."
        ::= { analogdata4 48 }

    batteryAgingRate4 OBJECT-TYPE
        SYNTAX Integer32
        MAX-ACCESS read-only
        STATUS current
        DESCRIPTION
            "Battery Aging Rate, stored as 0.01."
        ::= { analogdata4 49 }

    batteryRemainsTime4 OBJECT-TYPE
        SYNTAX Integer32
        MAX-ACCESS read-only
        STATUS current
        DESCRIPTION
            "Battery Remains Time, stored as 0.01 Hour."
        ::= { analogdata4 50 }

    batteryTemperature4 OBJECT-TYPE
        SYNTAX Integer32
        MAX-ACCESS read-only
        STATUS current
        DESCRIPTION
            "Battery Temperature, stored as 0.01 &deg;C."
        ::= { analogdata4 51 }

    batteryEnvironmentTemperature4 OBJECT-TYPE
        SYNTAX Integer32
        MAX-ACCESS read-only
        STATUS current
        DESCRIPTION
            "Battery Environment Temperature, stored as 0.01 &deg;C."
        ::= { analogdata4 52 }
        
analogdata5 OBJECT IDENTIFIER ::= { system 9 }

    inputPhaseVoltageA5 OBJECT-TYPE
        SYNTAX Integer32
        MAX-ACCESS read-only
        STATUS current
        DESCRIPTION
            "Input Phase Voltage A, stored as 0.01 V."
        ::= { analogdata5 1 }

    inputPhaseVoltageB5 OBJECT-TYPE
        SYNTAX Integer32
        MAX-ACCESS read-only
        STATUS current
        DESCRIPTION
            "Input Phase Voltage B, stored as 0.01 V."
        ::= { analogdata5 2 }

    inputPhaseVoltageC5 OBJECT-TYPE
        SYNTAX Integer32
        MAX-ACCESS read-only
        STATUS current
        DESCRIPTION
            "Input Phase Voltage C, stored as 0.01 V."
        ::= { analogdata5 3 }

    inputLineVoltageA5 OBJECT-TYPE
        SYNTAX Integer32
        MAX-ACCESS read-only
        STATUS current
        DESCRIPTION
            "Input Line Voltage A, stored as 0.01 V."
        ::= { analogdata5 4 }

    inputLineVoltageB5 OBJECT-TYPE
        SYNTAX Integer32
        MAX-ACCESS read-only
        STATUS current
        DESCRIPTION
            "Input Line Voltage B, stored as 0.01 V."
        ::= { analogdata5 5 }

    inputLineVoltageC5 OBJECT-TYPE
        SYNTAX Integer32
        MAX-ACCESS read-only
        STATUS current
        DESCRIPTION
            "Input Line Voltage C, stored as 0.01 V."
        ::= { analogdata5 6 }

    inputCurrentA5 OBJECT-TYPE
        SYNTAX Integer32
        MAX-ACCESS read-only
        STATUS current
        DESCRIPTION
            "Input Current A, stored as 0.01 A."
        ::= { analogdata5 7 }

    inputCurrentB5 OBJECT-TYPE
        SYNTAX Integer32
        MAX-ACCESS read-only
        STATUS current
        DESCRIPTION
            "Input Current B, stored as 0.01 A."
        ::= { analogdata5 8 }

    inputCurrentC5 OBJECT-TYPE
        SYNTAX Integer32
        MAX-ACCESS read-only
        STATUS current
        DESCRIPTION
            "Input Current C, stored as 0.01 A."
        ::= { analogdata5 9 }

    inputFrequency5 OBJECT-TYPE
        SYNTAX Integer32
        MAX-ACCESS read-only
        STATUS current
        DESCRIPTION
            "Input Frequency, stored as 0.01 Hz."
        ::= { analogdata5 10 }

    inputPowerFactorA5 OBJECT-TYPE
        SYNTAX Integer32
        MAX-ACCESS read-only
        STATUS current
        DESCRIPTION
            "Input Power Factor A, stored as 0.01."
        ::= { analogdata5 11 }

    inputPowerFactorB5 OBJECT-TYPE
        SYNTAX Integer32
        MAX-ACCESS read-only
        STATUS current
        DESCRIPTION
            "Input Power Factor B, stored as 0.01."
        ::= { analogdata5 12 }

    inputPowerFactorC5 OBJECT-TYPE
        SYNTAX Integer32
        MAX-ACCESS read-only
        STATUS current
        DESCRIPTION
            "Input Power Factor C, stored as 0.01."
        ::= { analogdata5 13 }

    dCBus1Voltage5 OBJECT-TYPE
        SYNTAX Integer32
        MAX-ACCESS read-only
        STATUS current
        DESCRIPTION
            "DCBus1 Voltage, stored as 0.01 V."
        ::= { analogdata5 14 }

    dCBus2Voltage5 OBJECT-TYPE
        SYNTAX Integer32
        MAX-ACCESS read-only
        STATUS current
        DESCRIPTION
            "DCBus2 Voltage, stored as 0.01 V."
        ::= { analogdata5 15 }

    outputVoltageA5 OBJECT-TYPE
    	SYNTAX Integer32
    	MAX-ACCESS read-only
        STATUS current
        DESCRIPTION
            "Output voltage A, stored as 0.01 V."
        ::= { analogdata5 16 }

    outputVoltageB5 OBJECT-TYPE
    	SYNTAX Integer32
    	MAX-ACCESS read-only
        STATUS current
        DESCRIPTION
            "Output voltage B, stored as 0.01 V."
        ::= { analogdata5 17 }

    outputVoltageC5 OBJECT-TYPE
    	SYNTAX Integer32
    	MAX-ACCESS read-only
        STATUS current
        DESCRIPTION
            "Output voltage C, stored as 0.01 V."
        ::= { analogdata5 18 }

    outputCurrentA5 OBJECT-TYPE
        SYNTAX Integer32
        MAX-ACCESS read-only
        STATUS current
        DESCRIPTION
            "Output current A, stored as 0.01 A."
        ::= { analogdata5 19 }

    outputCurrentB5 OBJECT-TYPE
        SYNTAX Integer32
        MAX-ACCESS read-only
        STATUS current
        DESCRIPTION
            "Output current B, stored as 0.01 A."
        ::= { analogdata5 20 }

    outputCurrentC5 OBJECT-TYPE
        SYNTAX Integer32
        MAX-ACCESS read-only
        STATUS current
        DESCRIPTION
            "Output current C, stored as 0.01 A."
        ::= { analogdata5 21 }

    outputFrequency5 OBJECT-TYPE
        SYNTAX Integer32
        MAX-ACCESS read-only
        STATUS current
        DESCRIPTION
            "Output Frequency, stored as 0.01 Hz."
        ::= { analogdata5 22 }

    outputPowerFactorA5 OBJECT-TYPE
        SYNTAX Integer32
        MAX-ACCESS read-only
        STATUS current
        DESCRIPTION
            "Output Power Factor A, stored as 0.01."
        ::= { analogdata5 23 }

    outputPowerFactorB5 OBJECT-TYPE
        SYNTAX Integer32
        MAX-ACCESS read-only
        STATUS current
        DESCRIPTION
            "Output Power Factor B, stored as 0.01."
        ::= { analogdata5 24 }

    outputPowerFactorC5 OBJECT-TYPE
        SYNTAX Integer32
        MAX-ACCESS read-only
        STATUS current
        DESCRIPTION
            "Output Power Factor C, stored as 0.01."
        ::= { analogdata5 25 }

    outputAcitvePowerA5 OBJECT-TYPE
        SYNTAX Integer32
        MAX-ACCESS read-only
        STATUS current
        DESCRIPTION
            "Output Acitve Power A, stored as 0.01 kW."
        ::= { analogdata5 26 }

    outputAcitvePowerB5 OBJECT-TYPE
        SYNTAX Integer32
        MAX-ACCESS read-only
        STATUS current
        DESCRIPTION
            "Output Acitve Power B, stored as 0.01 kW."
        ::= { analogdata5 27 }

    outputAcitvePowerC5 OBJECT-TYPE
        SYNTAX Integer32
        MAX-ACCESS read-only
        STATUS current
        DESCRIPTION
            "Output Acitve Power C, stored as 0.01 kW."
        ::= { analogdata5 28 }

    outputReactivePowerA5 OBJECT-TYPE
        SYNTAX Integer32
        MAX-ACCESS read-only
        STATUS current
        DESCRIPTION
            "Output Reactive Power A, stored as 0.01 KVAR."
        ::= { analogdata5 29 }

    outputReactivePowerB5 OBJECT-TYPE
        SYNTAX Integer32
        MAX-ACCESS read-only
        STATUS current
        DESCRIPTION
            "Output Reactive Power B, stored as 0.01 KVAR."
        ::= { analogdata5 30 }

    outputReactivePowerC5 OBJECT-TYPE
        SYNTAX Integer32
        MAX-ACCESS read-only
        STATUS current
        DESCRIPTION
            "Output Reactive Power C, stored as 0.01 KVAR."
        ::= { analogdata5 31 }

    outputAppPowerA5 OBJECT-TYPE
        SYNTAX Integer32
        MAX-ACCESS read-only
        STATUS current
        DESCRIPTION
            "Output App Power A, stored as 0.01 kVA."
        ::= { analogdata5 32 }

    outputAppPowerB5 OBJECT-TYPE
        SYNTAX Integer32
        MAX-ACCESS read-only
        STATUS current
        DESCRIPTION
            "Output App Power B, stored as 0.01 kVA."
        ::= { analogdata5 33 }

    outputAppPowerC5 OBJECT-TYPE
        SYNTAX Integer32
        MAX-ACCESS read-only
        STATUS current
        DESCRIPTION
            "Output App Power C, stored as 0.01 kVA."
        ::= { analogdata5 34 }

    outputLoadA5 OBJECT-TYPE
        SYNTAX Integer32
        MAX-ACCESS read-only
        STATUS current
        DESCRIPTION
            "Output Load A, stored as 0.01 %."
        ::= { analogdata5 35 }

    outputLoadB5 OBJECT-TYPE
        SYNTAX Integer32
        MAX-ACCESS read-only
        STATUS current
        DESCRIPTION
            "Output Load B, stored as 0.01 %."
        ::= { analogdata5 36 }

    outputLoadC5 OBJECT-TYPE
        SYNTAX Integer32
        MAX-ACCESS read-only
        STATUS current
        DESCRIPTION
            "Output Load C, stored as 0.01 %."
        ::= { analogdata5 37 }

    outputCrestFactorA5 OBJECT-TYPE
        SYNTAX Integer32
        MAX-ACCESS read-only
        STATUS current
        DESCRIPTION
            "Output Crest Factor A, stored as 0.01 ."
        ::= { analogdata5 38 }

    outputCrestFactorB5 OBJECT-TYPE
        SYNTAX Integer32
        MAX-ACCESS read-only
        STATUS current
        DESCRIPTION
            "Output Crest Factor B, stored as 0.01 ."
        ::= { analogdata5 39 }

    outputCrestFactorC5 OBJECT-TYPE
        SYNTAX Integer32
        MAX-ACCESS read-only
        STATUS current
        DESCRIPTION
            "Output Crest Factor C, stored as 0.01 ."
        ::= { analogdata5 40 }

    bypassVoltageA5 OBJECT-TYPE
        SYNTAX Integer32
        MAX-ACCESS read-only
        STATUS current
        DESCRIPTION
            "Bypass Voltage A, stored as 0.01 V."
        ::= { analogdata5 41 }

    bypassVoltageB5 OBJECT-TYPE
        SYNTAX Integer32
        MAX-ACCESS read-only
        STATUS current
        DESCRIPTION
            "Bypass Voltage B, stored as 0.01 V."
        ::= { analogdata5 42 }

    bypassVoltageC5 OBJECT-TYPE
        SYNTAX Integer32
        MAX-ACCESS read-only
        STATUS current
        DESCRIPTION
            "Bypass Voltage C, stored as 0.01 V."
        ::= { analogdata5 43 }

    bypassFrequency5 OBJECT-TYPE
        SYNTAX Integer32
        MAX-ACCESS read-only
        STATUS current
        DESCRIPTION
            "Bypass Frequency, stored as 0.01 Hz."
        ::= { analogdata5 44 }

    positiveBatteryVoltage5 OBJECT-TYPE
        SYNTAX Integer32
        MAX-ACCESS read-only
        STATUS current
        DESCRIPTION
            "positive Battery Voltage, stored as 0.01 V."
        ::= { analogdata5 45 }

    positiveBatteryCurrent5 OBJECT-TYPE
        SYNTAX Integer32
        MAX-ACCESS read-only
        STATUS current
        DESCRIPTION
            "positive Battery Current, stored as 0.01 A."
        ::= { analogdata5 46 }

    negativeBatteryVoltage5 OBJECT-TYPE
        SYNTAX Integer32
        MAX-ACCESS read-only
        STATUS current
        DESCRIPTION
            "negative Battery Voltage, stored as 0.01 V."
        ::= { analogdata5 47 }

    negativeBatteryCurrent5 OBJECT-TYPE
        SYNTAX Integer32
        MAX-ACCESS read-only
        STATUS current
        DESCRIPTION
            "negative Battery Current, stored as 0.01 A."
        ::= { analogdata5 48 }

    batteryAgingRate5 OBJECT-TYPE
        SYNTAX Integer32
        MAX-ACCESS read-only
        STATUS current
        DESCRIPTION
            "Battery Aging Rate, stored as 0.01."
        ::= { analogdata5 49 }

    batteryRemainsTime5 OBJECT-TYPE
        SYNTAX Integer32
        MAX-ACCESS read-only
        STATUS current
        DESCRIPTION
            "Battery Remains Time, stored as 0.01 Hour."
        ::= { analogdata5 50 }

    batteryTemperature5 OBJECT-TYPE
        SYNTAX Integer32
        MAX-ACCESS read-only
        STATUS current
        DESCRIPTION
            "Battery Temperature, stored as 0.01 &deg;C."
        ::= { analogdata5 51 }

    batteryEnvironmentTemperature5 OBJECT-TYPE
        SYNTAX Integer32
        MAX-ACCESS read-only
        STATUS current
        DESCRIPTION
            "Battery Environment Temperature, stored as 0.01 &deg;C."
        ::= { analogdata5 52 }
        
analogdata6 OBJECT IDENTIFIER ::= { system 10 }

    inputPhaseVoltageA6 OBJECT-TYPE
        SYNTAX Integer32
        MAX-ACCESS read-only
        STATUS current
        DESCRIPTION
            "Input Phase Voltage A, stored as 0.01 V."
        ::= { analogdata6 1 }

    inputPhaseVoltageB6 OBJECT-TYPE
        SYNTAX Integer32
        MAX-ACCESS read-only
        STATUS current
        DESCRIPTION
            "Input Phase Voltage B, stored as 0.01 V."
        ::= { analogdata6 2 }

    inputPhaseVoltageC6 OBJECT-TYPE
        SYNTAX Integer32
        MAX-ACCESS read-only
        STATUS current
        DESCRIPTION
            "Input Phase Voltage C, stored as 0.01 V."
        ::= { analogdata6 3 }

    inputLineVoltageA6 OBJECT-TYPE
        SYNTAX Integer32
        MAX-ACCESS read-only
        STATUS current
        DESCRIPTION
            "Input Line Voltage A, stored as 0.01 V."
        ::= { analogdata6 4 }

    inputLineVoltageB6 OBJECT-TYPE
        SYNTAX Integer32
        MAX-ACCESS read-only
        STATUS current
        DESCRIPTION
            "Input Line Voltage B, stored as 0.01 V."
        ::= { analogdata6 5 }

    inputLineVoltageC6 OBJECT-TYPE
        SYNTAX Integer32
        MAX-ACCESS read-only
        STATUS current
        DESCRIPTION
            "Input Line Voltage C, stored as 0.01 V."
        ::= { analogdata6 6 }

    inputCurrentA6 OBJECT-TYPE
        SYNTAX Integer32
        MAX-ACCESS read-only
        STATUS current
        DESCRIPTION
            "Input Current A, stored as 0.01 A."
        ::= { analogdata6 7 }

    inputCurrentB6 OBJECT-TYPE
        SYNTAX Integer32
        MAX-ACCESS read-only
        STATUS current
        DESCRIPTION
            "Input Current B, stored as 0.01 A."
        ::= { analogdata6 8 }

    inputCurrentC6 OBJECT-TYPE
        SYNTAX Integer32
        MAX-ACCESS read-only
        STATUS current
        DESCRIPTION
            "Input Current C, stored as 0.01 A."
        ::= { analogdata6 9 }

    inputFrequency6 OBJECT-TYPE
        SYNTAX Integer32
        MAX-ACCESS read-only
        STATUS current
        DESCRIPTION
            "Input Frequency, stored as 0.01 Hz."
        ::= { analogdata6 10 }

    inputPowerFactorA6 OBJECT-TYPE
        SYNTAX Integer32
        MAX-ACCESS read-only
        STATUS current
        DESCRIPTION
            "Input Power Factor A, stored as 0.01."
        ::= { analogdata6 11 }

    inputPowerFactorB6 OBJECT-TYPE
        SYNTAX Integer32
        MAX-ACCESS read-only
        STATUS current
        DESCRIPTION
            "Input Power Factor B, stored as 0.01."
        ::= { analogdata6 12 }

    inputPowerFactorC6 OBJECT-TYPE
        SYNTAX Integer32
        MAX-ACCESS read-only
        STATUS current
        DESCRIPTION
            "Input Power Factor C, stored as 0.01."
        ::= { analogdata6 13 }

    dCBus1Voltage6 OBJECT-TYPE
        SYNTAX Integer32
        MAX-ACCESS read-only
        STATUS current
        DESCRIPTION
            "DCBus1 Voltage, stored as 0.01 V."
        ::= { analogdata6 14 }

    dCBus2Voltage6 OBJECT-TYPE
        SYNTAX Integer32
        MAX-ACCESS read-only
        STATUS current
        DESCRIPTION
            "DCBus2 Voltage, stored as 0.01 V."
        ::= { analogdata6 15 }

    outputVoltageA6 OBJECT-TYPE
    	SYNTAX Integer32
    	MAX-ACCESS read-only
        STATUS current
        DESCRIPTION
            "Output voltage A, stored as 0.01 V."
        ::= { analogdata6 16 }

    outputVoltageB6 OBJECT-TYPE
    	SYNTAX Integer32
    	MAX-ACCESS read-only
        STATUS current
        DESCRIPTION
            "Output voltage B, stored as 0.01 V."
        ::= { analogdata6 17 }

    outputVoltageC6 OBJECT-TYPE
    	SYNTAX Integer32
    	MAX-ACCESS read-only
        STATUS current
        DESCRIPTION
            "Output voltage C, stored as 0.01 V."
        ::= { analogdata6 18 }

    outputCurrentA6 OBJECT-TYPE
        SYNTAX Integer32
        MAX-ACCESS read-only
        STATUS current
        DESCRIPTION
            "Output current A, stored as 0.01 A."
        ::= { analogdata6 19 }

    outputCurrentB6 OBJECT-TYPE
        SYNTAX Integer32
        MAX-ACCESS read-only
        STATUS current
        DESCRIPTION
            "Output current B, stored as 0.01 A."
        ::= { analogdata6 20 }

    outputCurrentC6 OBJECT-TYPE
        SYNTAX Integer32
        MAX-ACCESS read-only
        STATUS current
        DESCRIPTION
            "Output current C, stored as 0.01 A."
        ::= { analogdata6 21 }

    outputFrequency6 OBJECT-TYPE
        SYNTAX Integer32
        MAX-ACCESS read-only
        STATUS current
        DESCRIPTION
            "Output Frequency, stored as 0.01 Hz."
        ::= { analogdata6 22 }

    outputPowerFactorA6 OBJECT-TYPE
        SYNTAX Integer32
        MAX-ACCESS read-only
        STATUS current
        DESCRIPTION
            "Output Power Factor A, stored as 0.01."
        ::= { analogdata6 23 }

    outputPowerFactorB6 OBJECT-TYPE
        SYNTAX Integer32
        MAX-ACCESS read-only
        STATUS current
        DESCRIPTION
            "Output Power Factor B, stored as 0.01."
        ::= { analogdata6 24 }

    outputPowerFactorC6 OBJECT-TYPE
        SYNTAX Integer32
        MAX-ACCESS read-only
        STATUS current
        DESCRIPTION
            "Output Power Factor C, stored as 0.01."
        ::= { analogdata6 25 }

    outputAcitvePowerA6 OBJECT-TYPE
        SYNTAX Integer32
        MAX-ACCESS read-only
        STATUS current
        DESCRIPTION
            "Output Acitve Power A, stored as 0.01 kW."
        ::= { analogdata6 26 }

    outputAcitvePowerB6 OBJECT-TYPE
        SYNTAX Integer32
        MAX-ACCESS read-only
        STATUS current
        DESCRIPTION
            "Output Acitve Power B, stored as 0.01 kW."
        ::= { analogdata6 27 }

    outputAcitvePowerC6 OBJECT-TYPE
        SYNTAX Integer32
        MAX-ACCESS read-only
        STATUS current
        DESCRIPTION
            "Output Acitve Power C, stored as 0.01 kW."
        ::= { analogdata6 28 }

    outputReactivePowerA6 OBJECT-TYPE
        SYNTAX Integer32
        MAX-ACCESS read-only
        STATUS current
        DESCRIPTION
            "Output Reactive Power A, stored as 0.01 KVAR."
        ::= { analogdata6 29 }

    outputReactivePowerB6 OBJECT-TYPE
        SYNTAX Integer32
        MAX-ACCESS read-only
        STATUS current
        DESCRIPTION
            "Output Reactive Power B, stored as 0.01 KVAR."
        ::= { analogdata6 30 }

    outputReactivePowerC6 OBJECT-TYPE
        SYNTAX Integer32
        MAX-ACCESS read-only
        STATUS current
        DESCRIPTION
            "Output Reactive Power C, stored as 0.01 KVAR."
        ::= { analogdata6 31 }

    outputAppPowerA6 OBJECT-TYPE
        SYNTAX Integer32
        MAX-ACCESS read-only
        STATUS current
        DESCRIPTION
            "Output App Power A, stored as 0.01 kVA."
        ::= { analogdata6 32 }

    outputAppPowerB6 OBJECT-TYPE
        SYNTAX Integer32
        MAX-ACCESS read-only
        STATUS current
        DESCRIPTION
            "Output App Power B, stored as 0.01 kVA."
        ::= { analogdata6 33 }

    outputAppPowerC6 OBJECT-TYPE
        SYNTAX Integer32
        MAX-ACCESS read-only
        STATUS current
        DESCRIPTION
            "Output App Power C, stored as 0.01 kVA."
        ::= { analogdata6 34 }

    outputLoadA6 OBJECT-TYPE
        SYNTAX Integer32
        MAX-ACCESS read-only
        STATUS current
        DESCRIPTION
            "Output Load A, stored as 0.01 %."
        ::= { analogdata6 35 }

    outputLoadB6 OBJECT-TYPE
        SYNTAX Integer32
        MAX-ACCESS read-only
        STATUS current
        DESCRIPTION
            "Output Load B, stored as 0.01 %."
        ::= { analogdata6 36 }

    outputLoadC6 OBJECT-TYPE
        SYNTAX Integer32
        MAX-ACCESS read-only
        STATUS current
        DESCRIPTION
            "Output Load C, stored as 0.01 %."
        ::= { analogdata6 37 }

    outputCrestFactorA6 OBJECT-TYPE
        SYNTAX Integer32
        MAX-ACCESS read-only
        STATUS current
        DESCRIPTION
            "Output Crest Factor A, stored as 0.01 ."
        ::= { analogdata6 38 }

    outputCrestFactorB6 OBJECT-TYPE
        SYNTAX Integer32
        MAX-ACCESS read-only
        STATUS current
        DESCRIPTION
            "Output Crest Factor B, stored as 0.01 ."
        ::= { analogdata6 39 }

    outputCrestFactorC6 OBJECT-TYPE
        SYNTAX Integer32
        MAX-ACCESS read-only
        STATUS current
        DESCRIPTION
            "Output Crest Factor C, stored as 0.01 ."
        ::= { analogdata6 40 }

    bypassVoltageA6 OBJECT-TYPE
        SYNTAX Integer32
        MAX-ACCESS read-only
        STATUS current
        DESCRIPTION
            "Bypass Voltage A, stored as 0.01 V."
        ::= { analogdata6 41 }

    bypassVoltageB6 OBJECT-TYPE
        SYNTAX Integer32
        MAX-ACCESS read-only
        STATUS current
        DESCRIPTION
            "Bypass Voltage B, stored as 0.01 V."
        ::= { analogdata6 42 }

    bypassVoltageC6 OBJECT-TYPE
        SYNTAX Integer32
        MAX-ACCESS read-only
        STATUS current
        DESCRIPTION
            "Bypass Voltage C, stored as 0.01 V."
        ::= { analogdata6 43 }

    bypassFrequency6 OBJECT-TYPE
        SYNTAX Integer32
        MAX-ACCESS read-only
        STATUS current
        DESCRIPTION
            "Bypass Frequency, stored as 0.01 Hz."
        ::= { analogdata6 44 }

    positiveBatteryVoltage6 OBJECT-TYPE
        SYNTAX Integer32
        MAX-ACCESS read-only
        STATUS current
        DESCRIPTION
            "positive Battery Voltage, stored as 0.01 V."
        ::= { analogdata6 45 }

    positiveBatteryCurrent6 OBJECT-TYPE
        SYNTAX Integer32
        MAX-ACCESS read-only
        STATUS current
        DESCRIPTION
            "positive Battery Current, stored as 0.01 A."
        ::= { analogdata6 46 }

    negativeBatteryVoltage6 OBJECT-TYPE
        SYNTAX Integer32
        MAX-ACCESS read-only
        STATUS current
        DESCRIPTION
            "negative Battery Voltage, stored as 0.01 V."
        ::= { analogdata6 47 }

    negativeBatteryCurrent6 OBJECT-TYPE
        SYNTAX Integer32
        MAX-ACCESS read-only
        STATUS current
        DESCRIPTION
            "negative Battery Current, stored as 0.01 A."
        ::= { analogdata6 48 }

    batteryAgingRate6 OBJECT-TYPE
        SYNTAX Integer32
        MAX-ACCESS read-only
        STATUS current
        DESCRIPTION
            "Battery Aging Rate, stored as 0.01."
        ::= { analogdata6 49 }

    batteryRemainsTime6 OBJECT-TYPE
        SYNTAX Integer32
        MAX-ACCESS read-only
        STATUS current
        DESCRIPTION
            "Battery Remains Time, stored as 0.01 Hour."
        ::= { analogdata6 50 }

    batteryTemperature6 OBJECT-TYPE
        SYNTAX Integer32
        MAX-ACCESS read-only
        STATUS current
        DESCRIPTION
            "Battery Temperature, stored as 0.01 &deg;C."
        ::= { analogdata6 51 }

    batteryEnvironmentTemperature6 OBJECT-TYPE
        SYNTAX Integer32
        MAX-ACCESS read-only
        STATUS current
        DESCRIPTION
            "Battery Environment Temperature, stored as 0.01 &deg;C."
        ::= { analogdata6 52 }
        
analogdata7 OBJECT IDENTIFIER ::= { system 11 }

    inputPhaseVoltageA7 OBJECT-TYPE
        SYNTAX Integer32
        MAX-ACCESS read-only
        STATUS current
        DESCRIPTION
            "Input Phase Voltage A, stored as 0.01 V."
        ::= { analogdata7 1 }

    inputPhaseVoltageB7 OBJECT-TYPE
        SYNTAX Integer32
        MAX-ACCESS read-only
        STATUS current
        DESCRIPTION
            "Input Phase Voltage B, stored as 0.01 V."
        ::= { analogdata7 2 }

    inputPhaseVoltageC7 OBJECT-TYPE
        SYNTAX Integer32
        MAX-ACCESS read-only
        STATUS current
        DESCRIPTION
            "Input Phase Voltage C, stored as 0.01 V."
        ::= { analogdata7 3 }

    inputLineVoltageA7 OBJECT-TYPE
        SYNTAX Integer32
        MAX-ACCESS read-only
        STATUS current
        DESCRIPTION
            "Input Line Voltage A, stored as 0.01 V."
        ::= { analogdata7 4 }

    inputLineVoltageB7 OBJECT-TYPE
        SYNTAX Integer32
        MAX-ACCESS read-only
        STATUS current
        DESCRIPTION
            "Input Line Voltage B, stored as 0.01 V."
        ::= { analogdata7 5 }

    inputLineVoltageC7 OBJECT-TYPE
        SYNTAX Integer32
        MAX-ACCESS read-only
        STATUS current
        DESCRIPTION
            "Input Line Voltage C, stored as 0.01 V."
        ::= { analogdata7 6 }

    inputCurrentA7 OBJECT-TYPE
        SYNTAX Integer32
        MAX-ACCESS read-only
        STATUS current
        DESCRIPTION
            "Input Current A, stored as 0.01 A."
        ::= { analogdata7 7 }

    inputCurrentB7 OBJECT-TYPE
        SYNTAX Integer32
        MAX-ACCESS read-only
        STATUS current
        DESCRIPTION
            "Input Current B, stored as 0.01 A."
        ::= { analogdata7 8 }

    inputCurrentC7 OBJECT-TYPE
        SYNTAX Integer32
        MAX-ACCESS read-only
        STATUS current
        DESCRIPTION
            "Input Current C, stored as 0.01 A."
        ::= { analogdata7 9 }

    inputFrequency7 OBJECT-TYPE
        SYNTAX Integer32
        MAX-ACCESS read-only
        STATUS current
        DESCRIPTION
            "Input Frequency, stored as 0.01 Hz."
        ::= { analogdata7 10 }

    inputPowerFactorA7 OBJECT-TYPE
        SYNTAX Integer32
        MAX-ACCESS read-only
        STATUS current
        DESCRIPTION
            "Input Power Factor A, stored as 0.01."
        ::= { analogdata7 11 }

    inputPowerFactorB7 OBJECT-TYPE
        SYNTAX Integer32
        MAX-ACCESS read-only
        STATUS current
        DESCRIPTION
            "Input Power Factor B, stored as 0.01."
        ::= { analogdata7 12 }

    inputPowerFactorC7 OBJECT-TYPE
        SYNTAX Integer32
        MAX-ACCESS read-only
        STATUS current
        DESCRIPTION
            "Input Power Factor C, stored as 0.01."
        ::= { analogdata7 13 }

    dCBus1Voltage7 OBJECT-TYPE
        SYNTAX Integer32
        MAX-ACCESS read-only
        STATUS current
        DESCRIPTION
            "DCBus1 Voltage, stored as 0.01 V."
        ::= { analogdata7 14 }

    dCBus2Voltage7 OBJECT-TYPE
        SYNTAX Integer32
        MAX-ACCESS read-only
        STATUS current
        DESCRIPTION
            "DCBus2 Voltage, stored as 0.01 V."
        ::= { analogdata7 15 }

    outputVoltageA7 OBJECT-TYPE
    	SYNTAX Integer32
    	MAX-ACCESS read-only
        STATUS current
        DESCRIPTION
            "Output voltage A, stored as 0.01 V."
        ::= { analogdata7 16 }

    outputVoltageB7 OBJECT-TYPE
    	SYNTAX Integer32
    	MAX-ACCESS read-only
        STATUS current
        DESCRIPTION
            "Output voltage B, stored as 0.01 V."
        ::= { analogdata7 17 }

    outputVoltageC7 OBJECT-TYPE
    	SYNTAX Integer32
    	MAX-ACCESS read-only
        STATUS current
        DESCRIPTION
            "Output voltage C, stored as 0.01 V."
        ::= { analogdata7 18 }

    outputCurrentA7 OBJECT-TYPE
        SYNTAX Integer32
        MAX-ACCESS read-only
        STATUS current
        DESCRIPTION
            "Output current A, stored as 0.01 A."
        ::= { analogdata7 19 }

    outputCurrentB7 OBJECT-TYPE
        SYNTAX Integer32
        MAX-ACCESS read-only
        STATUS current
        DESCRIPTION
            "Output current B, stored as 0.01 A."
        ::= { analogdata7 20 }

    outputCurrentC7 OBJECT-TYPE
        SYNTAX Integer32
        MAX-ACCESS read-only
        STATUS current
        DESCRIPTION
            "Output current C, stored as 0.01 A."
        ::= { analogdata7 21 }

    outputFrequency7 OBJECT-TYPE
        SYNTAX Integer32
        MAX-ACCESS read-only
        STATUS current
        DESCRIPTION
            "Output Frequency, stored as 0.01 Hz."
        ::= { analogdata7 22 }

    outputPowerFactorA7 OBJECT-TYPE
        SYNTAX Integer32
        MAX-ACCESS read-only
        STATUS current
        DESCRIPTION
            "Output Power Factor A, stored as 0.01."
        ::= { analogdata7 23 }

    outputPowerFactorB7 OBJECT-TYPE
        SYNTAX Integer32
        MAX-ACCESS read-only
        STATUS current
        DESCRIPTION
            "Output Power Factor B, stored as 0.01."
        ::= { analogdata7 24 }

    outputPowerFactorC7 OBJECT-TYPE
        SYNTAX Integer32
        MAX-ACCESS read-only
        STATUS current
        DESCRIPTION
            "Output Power Factor C, stored as 0.01."
        ::= { analogdata7 25 }

    outputAcitvePowerA7 OBJECT-TYPE
        SYNTAX Integer32
        MAX-ACCESS read-only
        STATUS current
        DESCRIPTION
            "Output Acitve Power A, stored as 0.01 kW."
        ::= { analogdata7 26 }

    outputAcitvePowerB7 OBJECT-TYPE
        SYNTAX Integer32
        MAX-ACCESS read-only
        STATUS current
        DESCRIPTION
            "Output Acitve Power B, stored as 0.01 kW."
        ::= { analogdata7 27 }

    outputAcitvePowerC7 OBJECT-TYPE
        SYNTAX Integer32
        MAX-ACCESS read-only
        STATUS current
        DESCRIPTION
            "Output Acitve Power C, stored as 0.01 kW."
        ::= { analogdata7 28 }

    outputReactivePowerA7 OBJECT-TYPE
        SYNTAX Integer32
        MAX-ACCESS read-only
        STATUS current
        DESCRIPTION
            "Output Reactive Power A, stored as 0.01 KVAR."
        ::= { analogdata7 29 }

    outputReactivePowerB7 OBJECT-TYPE
        SYNTAX Integer32
        MAX-ACCESS read-only
        STATUS current
        DESCRIPTION
            "Output Reactive Power B, stored as 0.01 KVAR."
        ::= { analogdata7 30 }

    outputReactivePowerC7 OBJECT-TYPE
        SYNTAX Integer32
        MAX-ACCESS read-only
        STATUS current
        DESCRIPTION
            "Output Reactive Power C, stored as 0.01 KVAR."
        ::= { analogdata7 31 }

    outputAppPowerA7 OBJECT-TYPE
        SYNTAX Integer32
        MAX-ACCESS read-only
        STATUS current
        DESCRIPTION
            "Output App Power A, stored as 0.01 kVA."
        ::= { analogdata7 32 }

    outputAppPowerB7 OBJECT-TYPE
        SYNTAX Integer32
        MAX-ACCESS read-only
        STATUS current
        DESCRIPTION
            "Output App Power B, stored as 0.01 kVA."
        ::= { analogdata7 33 }

    outputAppPowerC7 OBJECT-TYPE
        SYNTAX Integer32
        MAX-ACCESS read-only
        STATUS current
        DESCRIPTION
            "Output App Power C, stored as 0.01 kVA."
        ::= { analogdata7 34 }

    outputLoadA7 OBJECT-TYPE
        SYNTAX Integer32
        MAX-ACCESS read-only
        STATUS current
        DESCRIPTION
            "Output Load A, stored as 0.01 %."
        ::= { analogdata7 35 }

    outputLoadB7 OBJECT-TYPE
        SYNTAX Integer32
        MAX-ACCESS read-only
        STATUS current
        DESCRIPTION
            "Output Load B, stored as 0.01 %."
        ::= { analogdata7 36 }

    outputLoadC7 OBJECT-TYPE
        SYNTAX Integer32
        MAX-ACCESS read-only
        STATUS current
        DESCRIPTION
            "Output Load C, stored as 0.01 %."
        ::= { analogdata7 37 }

    outputCrestFactorA7 OBJECT-TYPE
        SYNTAX Integer32
        MAX-ACCESS read-only
        STATUS current
        DESCRIPTION
            "Output Crest Factor A, stored as 0.01 ."
        ::= { analogdata7 38 }

    outputCrestFactorB7 OBJECT-TYPE
        SYNTAX Integer32
        MAX-ACCESS read-only
        STATUS current
        DESCRIPTION
            "Output Crest Factor B, stored as 0.01 ."
        ::= { analogdata7 39 }

    outputCrestFactorC7 OBJECT-TYPE
        SYNTAX Integer32
        MAX-ACCESS read-only
        STATUS current
        DESCRIPTION
            "Output Crest Factor C, stored as 0.01 ."
        ::= { analogdata7 40 }

    bypassVoltageA7 OBJECT-TYPE
        SYNTAX Integer32
        MAX-ACCESS read-only
        STATUS current
        DESCRIPTION
            "Bypass Voltage A, stored as 0.01 V."
        ::= { analogdata7 41 }

    bypassVoltageB7 OBJECT-TYPE
        SYNTAX Integer32
        MAX-ACCESS read-only
        STATUS current
        DESCRIPTION
            "Bypass Voltage B, stored as 0.01 V."
        ::= { analogdata7 42 }

    bypassVoltageC7 OBJECT-TYPE
        SYNTAX Integer32
        MAX-ACCESS read-only
        STATUS current
        DESCRIPTION
            "Bypass Voltage C, stored as 0.01 V."
        ::= { analogdata7 43 }

    bypassFrequency7 OBJECT-TYPE
        SYNTAX Integer32
        MAX-ACCESS read-only
        STATUS current
        DESCRIPTION
            "Bypass Frequency, stored as 0.01 Hz."
        ::= { analogdata7 44 }

    positiveBatteryVoltage7 OBJECT-TYPE
        SYNTAX Integer32
        MAX-ACCESS read-only
        STATUS current
        DESCRIPTION
            "positive Battery Voltage, stored as 0.01 V."
        ::= { analogdata7 45 }

    positiveBatteryCurrent7 OBJECT-TYPE
        SYNTAX Integer32
        MAX-ACCESS read-only
        STATUS current
        DESCRIPTION
            "positive Battery Current, stored as 0.01 A."
        ::= { analogdata7 46 }

    negativeBatteryVoltage7 OBJECT-TYPE
        SYNTAX Integer32
        MAX-ACCESS read-only
        STATUS current
        DESCRIPTION
            "negative Battery Voltage, stored as 0.01 V."
        ::= { analogdata7 47 }

    negativeBatteryCurrent7 OBJECT-TYPE
        SYNTAX Integer32
        MAX-ACCESS read-only
        STATUS current
        DESCRIPTION
            "negative Battery Current, stored as 0.01 A."
        ::= { analogdata7 48 }

    batteryAgingRate7 OBJECT-TYPE
        SYNTAX Integer32
        MAX-ACCESS read-only
        STATUS current
        DESCRIPTION
            "Battery Aging Rate, stored as 0.01."
        ::= { analogdata7 49 }

    batteryRemainsTime7 OBJECT-TYPE
        SYNTAX Integer32
        MAX-ACCESS read-only
        STATUS current
        DESCRIPTION
            "Battery Remains Time, stored as 0.01 Hour."
        ::= { analogdata7 50 }

    batteryTemperature7 OBJECT-TYPE
        SYNTAX Integer32
        MAX-ACCESS read-only
        STATUS current
        DESCRIPTION
            "Battery Temperature, stored as 0.01 &deg;C."
        ::= { analogdata7 51 }

    batteryEnvironmentTemperature7 OBJECT-TYPE
        SYNTAX Integer32
        MAX-ACCESS read-only
        STATUS current
        DESCRIPTION
            "Battery Environment Temperature, stored as 0.01 &deg;C."
        ::= { analogdata7 52 }
        
analogdata8 OBJECT IDENTIFIER ::= { system 12 }

    inputPhaseVoltageA8 OBJECT-TYPE
        SYNTAX Integer32
        MAX-ACCESS read-only
        STATUS current
        DESCRIPTION
            "Input Phase Voltage A, stored as 0.01 V."
        ::= { analogdata8 1 }

    inputPhaseVoltageB8 OBJECT-TYPE
        SYNTAX Integer32
        MAX-ACCESS read-only
        STATUS current
        DESCRIPTION
            "Input Phase Voltage B, stored as 0.01 V."
        ::= { analogdata8 2 }

    inputPhaseVoltageC8 OBJECT-TYPE
        SYNTAX Integer32
        MAX-ACCESS read-only
        STATUS current
        DESCRIPTION
            "Input Phase Voltage C, stored as 0.01 V."
        ::= { analogdata8 3 }

    inputLineVoltageA8 OBJECT-TYPE
        SYNTAX Integer32
        MAX-ACCESS read-only
        STATUS current
        DESCRIPTION
            "Input Line Voltage A, stored as 0.01 V."
        ::= { analogdata8 4 }

    inputLineVoltageB8 OBJECT-TYPE
        SYNTAX Integer32
        MAX-ACCESS read-only
        STATUS current
        DESCRIPTION
            "Input Line Voltage B, stored as 0.01 V."
        ::= { analogdata8 5 }

    inputLineVoltageC8 OBJECT-TYPE
        SYNTAX Integer32
        MAX-ACCESS read-only
        STATUS current
        DESCRIPTION
            "Input Line Voltage C, stored as 0.01 V."
        ::= { analogdata8 6 }

    inputCurrentA8 OBJECT-TYPE
        SYNTAX Integer32
        MAX-ACCESS read-only
        STATUS current
        DESCRIPTION
            "Input Current A, stored as 0.01 A."
        ::= { analogdata8 7 }

    inputCurrentB8 OBJECT-TYPE
        SYNTAX Integer32
        MAX-ACCESS read-only
        STATUS current
        DESCRIPTION
            "Input Current B, stored as 0.01 A."
        ::= { analogdata8 8 }

    inputCurrentC8 OBJECT-TYPE
        SYNTAX Integer32
        MAX-ACCESS read-only
        STATUS current
        DESCRIPTION
            "Input Current C, stored as 0.01 A."
        ::= { analogdata8 9 }

    inputFrequency8 OBJECT-TYPE
        SYNTAX Integer32
        MAX-ACCESS read-only
        STATUS current
        DESCRIPTION
            "Input Frequency, stored as 0.01 Hz."
        ::= { analogdata8 10 }

    inputPowerFactorA8 OBJECT-TYPE
        SYNTAX Integer32
        MAX-ACCESS read-only
        STATUS current
        DESCRIPTION
            "Input Power Factor A, stored as 0.01."
        ::= { analogdata8 11 }

    inputPowerFactorB8 OBJECT-TYPE
        SYNTAX Integer32
        MAX-ACCESS read-only
        STATUS current
        DESCRIPTION
            "Input Power Factor B, stored as 0.01."
        ::= { analogdata8 12 }

    inputPowerFactorC8 OBJECT-TYPE
        SYNTAX Integer32
        MAX-ACCESS read-only
        STATUS current
        DESCRIPTION
            "Input Power Factor C, stored as 0.01."
        ::= { analogdata8 13 }

    dCBus1Voltage8 OBJECT-TYPE
        SYNTAX Integer32
        MAX-ACCESS read-only
        STATUS current
        DESCRIPTION
            "DCBus1 Voltage, stored as 0.01 V."
        ::= { analogdata8 14 }

    dCBus2Voltage8 OBJECT-TYPE
        SYNTAX Integer32
        MAX-ACCESS read-only
        STATUS current
        DESCRIPTION
            "DCBus2 Voltage, stored as 0.01 V."
        ::= { analogdata8 15 }

    outputVoltageA8 OBJECT-TYPE
    	SYNTAX Integer32
    	MAX-ACCESS read-only
        STATUS current
        DESCRIPTION
            "Output voltage A, stored as 0.01 V."
        ::= { analogdata8 16 }

    outputVoltageB8 OBJECT-TYPE
    	SYNTAX Integer32
    	MAX-ACCESS read-only
        STATUS current
        DESCRIPTION
            "Output voltage B, stored as 0.01 V."
        ::= { analogdata8 17 }

    outputVoltageC8 OBJECT-TYPE
    	SYNTAX Integer32
    	MAX-ACCESS read-only
        STATUS current
        DESCRIPTION
            "Output voltage C, stored as 0.01 V."
        ::= { analogdata8 18 }

    outputCurrentA8 OBJECT-TYPE
        SYNTAX Integer32
        MAX-ACCESS read-only
        STATUS current
        DESCRIPTION
            "Output current A, stored as 0.01 A."
        ::= { analogdata8 19 }

    outputCurrentB8 OBJECT-TYPE
        SYNTAX Integer32
        MAX-ACCESS read-only
        STATUS current
        DESCRIPTION
            "Output current B, stored as 0.01 A."
        ::= { analogdata8 20 }

    outputCurrentC8 OBJECT-TYPE
        SYNTAX Integer32
        MAX-ACCESS read-only
        STATUS current
        DESCRIPTION
            "Output current C, stored as 0.01 A."
        ::= { analogdata8 21 }

    outputFrequency8 OBJECT-TYPE
        SYNTAX Integer32
        MAX-ACCESS read-only
        STATUS current
        DESCRIPTION
            "Output Frequency, stored as 0.01 Hz."
        ::= { analogdata8 22 }

    outputPowerFactorA8 OBJECT-TYPE
        SYNTAX Integer32
        MAX-ACCESS read-only
        STATUS current
        DESCRIPTION
            "Output Power Factor A, stored as 0.01."
        ::= { analogdata8 23 }

    outputPowerFactorB8 OBJECT-TYPE
        SYNTAX Integer32
        MAX-ACCESS read-only
        STATUS current
        DESCRIPTION
            "Output Power Factor B, stored as 0.01."
        ::= { analogdata8 24 }

    outputPowerFactorC8 OBJECT-TYPE
        SYNTAX Integer32
        MAX-ACCESS read-only
        STATUS current
        DESCRIPTION
            "Output Power Factor C, stored as 0.01."
        ::= { analogdata8 25 }

    outputAcitvePowerA8 OBJECT-TYPE
        SYNTAX Integer32
        MAX-ACCESS read-only
        STATUS current
        DESCRIPTION
            "Output Acitve Power A, stored as 0.01 kW."
        ::= { analogdata8 26 }

    outputAcitvePowerB8 OBJECT-TYPE
        SYNTAX Integer32
        MAX-ACCESS read-only
        STATUS current
        DESCRIPTION
            "Output Acitve Power B, stored as 0.01 kW."
        ::= { analogdata8 27 }

    outputAcitvePowerC8 OBJECT-TYPE
        SYNTAX Integer32
        MAX-ACCESS read-only
        STATUS current
        DESCRIPTION
            "Output Acitve Power C, stored as 0.01 kW."
        ::= { analogdata8 28 }

    outputReactivePowerA8 OBJECT-TYPE
        SYNTAX Integer32
        MAX-ACCESS read-only
        STATUS current
        DESCRIPTION
            "Output Reactive Power A, stored as 0.01 KVAR."
        ::= { analogdata8 29 }

    outputReactivePowerB8 OBJECT-TYPE
        SYNTAX Integer32
        MAX-ACCESS read-only
        STATUS current
        DESCRIPTION
            "Output Reactive Power B, stored as 0.01 KVAR."
        ::= { analogdata8 30 }

    outputReactivePowerC8 OBJECT-TYPE
        SYNTAX Integer32
        MAX-ACCESS read-only
        STATUS current
        DESCRIPTION
            "Output Reactive Power C, stored as 0.01 KVAR."
        ::= { analogdata8 31 }

    outputAppPowerA8 OBJECT-TYPE
        SYNTAX Integer32
        MAX-ACCESS read-only
        STATUS current
        DESCRIPTION
            "Output App Power A, stored as 0.01 kVA."
        ::= { analogdata8 32 }

    outputAppPowerB8 OBJECT-TYPE
        SYNTAX Integer32
        MAX-ACCESS read-only
        STATUS current
        DESCRIPTION
            "Output App Power B, stored as 0.01 kVA."
        ::= { analogdata8 33 }

    outputAppPowerC8 OBJECT-TYPE
        SYNTAX Integer32
        MAX-ACCESS read-only
        STATUS current
        DESCRIPTION
            "Output App Power C, stored as 0.01 kVA."
        ::= { analogdata8 34 }

    outputLoadA8 OBJECT-TYPE
        SYNTAX Integer32
        MAX-ACCESS read-only
        STATUS current
        DESCRIPTION
            "Output Load A, stored as 0.01 %."
        ::= { analogdata8 35 }

    outputLoadB8 OBJECT-TYPE
        SYNTAX Integer32
        MAX-ACCESS read-only
        STATUS current
        DESCRIPTION
            "Output Load B, stored as 0.01 %."
        ::= { analogdata8 36 }

    outputLoadC8 OBJECT-TYPE
        SYNTAX Integer32
        MAX-ACCESS read-only
        STATUS current
        DESCRIPTION
            "Output Load C, stored as 0.01 %."
        ::= { analogdata8 37 }

    outputCrestFactorA8 OBJECT-TYPE
        SYNTAX Integer32
        MAX-ACCESS read-only
        STATUS current
        DESCRIPTION
            "Output Crest Factor A, stored as 0.01 ."
        ::= { analogdata8 38 }

    outputCrestFactorB8 OBJECT-TYPE
        SYNTAX Integer32
        MAX-ACCESS read-only
        STATUS current
        DESCRIPTION
            "Output Crest Factor B, stored as 0.01 ."
        ::= { analogdata8 39 }

    outputCrestFactorC8 OBJECT-TYPE
        SYNTAX Integer32
        MAX-ACCESS read-only
        STATUS current
        DESCRIPTION
            "Output Crest Factor C, stored as 0.01 ."
        ::= { analogdata8 40 }

    bypassVoltageA8 OBJECT-TYPE
        SYNTAX Integer32
        MAX-ACCESS read-only
        STATUS current
        DESCRIPTION
            "Bypass Voltage A, stored as 0.01 V."
        ::= { analogdata8 41 }

    bypassVoltageB8 OBJECT-TYPE
        SYNTAX Integer32
        MAX-ACCESS read-only
        STATUS current
        DESCRIPTION
            "Bypass Voltage B, stored as 0.01 V."
        ::= { analogdata8 42 }

    bypassVoltageC8 OBJECT-TYPE
        SYNTAX Integer32
        MAX-ACCESS read-only
        STATUS current
        DESCRIPTION
            "Bypass Voltage C, stored as 0.01 V."
        ::= { analogdata8 43 }

    bypassFrequency8 OBJECT-TYPE
        SYNTAX Integer32
        MAX-ACCESS read-only
        STATUS current
        DESCRIPTION
            "Bypass Frequency, stored as 0.01 Hz."
        ::= { analogdata8 44 }

    positiveBatteryVoltage8 OBJECT-TYPE
        SYNTAX Integer32
        MAX-ACCESS read-only
        STATUS current
        DESCRIPTION
            "positive Battery Voltage, stored as 0.01 V."
        ::= { analogdata8 45 }

    positiveBatteryCurrent8 OBJECT-TYPE
        SYNTAX Integer32
        MAX-ACCESS read-only
        STATUS current
        DESCRIPTION
            "positive Battery Current, stored as 0.01 A."
        ::= { analogdata8 46 }

    negativeBatteryVoltage8 OBJECT-TYPE
        SYNTAX Integer32
        MAX-ACCESS read-only
        STATUS current
        DESCRIPTION
            "negative Battery Voltage, stored as 0.01 V."
        ::= { analogdata8 47 }

    negativeBatteryCurrent8 OBJECT-TYPE
        SYNTAX Integer32
        MAX-ACCESS read-only
        STATUS current
        DESCRIPTION
            "negative Battery Current, stored as 0.01 A."
        ::= { analogdata8 48 }

    batteryAgingRate8 OBJECT-TYPE
        SYNTAX Integer32
        MAX-ACCESS read-only
        STATUS current
        DESCRIPTION
            "Battery Aging Rate, stored as 0.01."
        ::= { analogdata8 49 }

    batteryRemainsTime8 OBJECT-TYPE
        SYNTAX Integer32
        MAX-ACCESS read-only
        STATUS current
        DESCRIPTION
            "Battery Remains Time, stored as 0.01 Hour."
        ::= { analogdata8 50 }

    batteryTemperature8 OBJECT-TYPE
        SYNTAX Integer32
        MAX-ACCESS read-only
        STATUS current
        DESCRIPTION
            "Battery Temperature, stored as 0.01 &deg;C."
        ::= { analogdata8 51 }

    batteryEnvironmentTemperature8 OBJECT-TYPE
        SYNTAX Integer32
        MAX-ACCESS read-only
        STATUS current
        DESCRIPTION
            "Battery Environment Temperature, stored as 0.01 &deg;C."
        ::= { analogdata8 52 }
        
analogdata9 OBJECT IDENTIFIER ::= { system 13 }

    inputPhaseVoltageA9 OBJECT-TYPE
        SYNTAX Integer32
        MAX-ACCESS read-only
        STATUS current
        DESCRIPTION
            "Input Phase Voltage A, stored as 0.01 V."
        ::= { analogdata9 1 }

    inputPhaseVoltageB9 OBJECT-TYPE
        SYNTAX Integer32
        MAX-ACCESS read-only
        STATUS current
        DESCRIPTION
            "Input Phase Voltage B, stored as 0.01 V."
        ::= { analogdata9 2 }

    inputPhaseVoltageC9 OBJECT-TYPE
        SYNTAX Integer32
        MAX-ACCESS read-only
        STATUS current
        DESCRIPTION
            "Input Phase Voltage C, stored as 0.01 V."
        ::= { analogdata9 3 }

    inputLineVoltageA9 OBJECT-TYPE
        SYNTAX Integer32
        MAX-ACCESS read-only
        STATUS current
        DESCRIPTION
            "Input Line Voltage A, stored as 0.01 V."
        ::= { analogdata9 4 }

    inputLineVoltageB9 OBJECT-TYPE
        SYNTAX Integer32
        MAX-ACCESS read-only
        STATUS current
        DESCRIPTION
            "Input Line Voltage B, stored as 0.01 V."
        ::= { analogdata9 5 }

    inputLineVoltageC9 OBJECT-TYPE
        SYNTAX Integer32
        MAX-ACCESS read-only
        STATUS current
        DESCRIPTION
            "Input Line Voltage C, stored as 0.01 V."
        ::= { analogdata9 6 }

    inputCurrentA9 OBJECT-TYPE
        SYNTAX Integer32
        MAX-ACCESS read-only
        STATUS current
        DESCRIPTION
            "Input Current A, stored as 0.01 A."
        ::= { analogdata9 7 }

    inputCurrentB9 OBJECT-TYPE
        SYNTAX Integer32
        MAX-ACCESS read-only
        STATUS current
        DESCRIPTION
            "Input Current B, stored as 0.01 A."
        ::= { analogdata9 8 }

    inputCurrentC9 OBJECT-TYPE
        SYNTAX Integer32
        MAX-ACCESS read-only
        STATUS current
        DESCRIPTION
            "Input Current C, stored as 0.01 A."
        ::= { analogdata9 9 }

    inputFrequency9 OBJECT-TYPE
        SYNTAX Integer32
        MAX-ACCESS read-only
        STATUS current
        DESCRIPTION
            "Input Frequency, stored as 0.01 Hz."
        ::= { analogdata9 10 }

    inputPowerFactorA9 OBJECT-TYPE
        SYNTAX Integer32
        MAX-ACCESS read-only
        STATUS current
        DESCRIPTION
            "Input Power Factor A, stored as 0.01."
        ::= { analogdata9 11 }

    inputPowerFactorB9 OBJECT-TYPE
        SYNTAX Integer32
        MAX-ACCESS read-only
        STATUS current
        DESCRIPTION
            "Input Power Factor B, stored as 0.01."
        ::= { analogdata9 12 }

    inputPowerFactorC9 OBJECT-TYPE
        SYNTAX Integer32
        MAX-ACCESS read-only
        STATUS current
        DESCRIPTION
            "Input Power Factor C, stored as 0.01."
        ::= { analogdata9 13 }

    dCBus1Voltage9 OBJECT-TYPE
        SYNTAX Integer32
        MAX-ACCESS read-only
        STATUS current
        DESCRIPTION
            "DCBus1 Voltage, stored as 0.01 V."
        ::= { analogdata9 14 }

    dCBus2Voltage9 OBJECT-TYPE
        SYNTAX Integer32
        MAX-ACCESS read-only
        STATUS current
        DESCRIPTION
            "DCBus2 Voltage, stored as 0.01 V."
        ::= { analogdata9 15 }

    outputVoltageA9 OBJECT-TYPE
    	SYNTAX Integer32
    	MAX-ACCESS read-only
        STATUS current
        DESCRIPTION
            "Output voltage A, stored as 0.01 V."
        ::= { analogdata9 16 }

    outputVoltageB9 OBJECT-TYPE
    	SYNTAX Integer32
    	MAX-ACCESS read-only
        STATUS current
        DESCRIPTION
            "Output voltage B, stored as 0.01 V."
        ::= { analogdata9 17 }

    outputVoltageC9 OBJECT-TYPE
    	SYNTAX Integer32
    	MAX-ACCESS read-only
        STATUS current
        DESCRIPTION
            "Output voltage C, stored as 0.01 V."
        ::= { analogdata9 18 }

    outputCurrentA9 OBJECT-TYPE
        SYNTAX Integer32
        MAX-ACCESS read-only
        STATUS current
        DESCRIPTION
            "Output current A, stored as 0.01 A."
        ::= { analogdata9 19 }

    outputCurrentB9 OBJECT-TYPE
        SYNTAX Integer32
        MAX-ACCESS read-only
        STATUS current
        DESCRIPTION
            "Output current B, stored as 0.01 A."
        ::= { analogdata9 20 }

    outputCurrentC9 OBJECT-TYPE
        SYNTAX Integer32
        MAX-ACCESS read-only
        STATUS current
        DESCRIPTION
            "Output current C, stored as 0.01 A."
        ::= { analogdata9 21 }

    outputFrequency9 OBJECT-TYPE
        SYNTAX Integer32
        MAX-ACCESS read-only
        STATUS current
        DESCRIPTION
            "Output Frequency, stored as 0.01 Hz."
        ::= { analogdata9 22 }

    outputPowerFactorA9 OBJECT-TYPE
        SYNTAX Integer32
        MAX-ACCESS read-only
        STATUS current
        DESCRIPTION
            "Output Power Factor A, stored as 0.01."
        ::= { analogdata9 23 }

    outputPowerFactorB9 OBJECT-TYPE
        SYNTAX Integer32
        MAX-ACCESS read-only
        STATUS current
        DESCRIPTION
            "Output Power Factor B, stored as 0.01."
        ::= { analogdata9 24 }

    outputPowerFactorC9 OBJECT-TYPE
        SYNTAX Integer32
        MAX-ACCESS read-only
        STATUS current
        DESCRIPTION
            "Output Power Factor C, stored as 0.01."
        ::= { analogdata9 25 }

    outputAcitvePowerA9 OBJECT-TYPE
        SYNTAX Integer32
        MAX-ACCESS read-only
        STATUS current
        DESCRIPTION
            "Output Acitve Power A, stored as 0.01 kW."
        ::= { analogdata9 26 }

    outputAcitvePowerB9 OBJECT-TYPE
        SYNTAX Integer32
        MAX-ACCESS read-only
        STATUS current
        DESCRIPTION
            "Output Acitve Power B, stored as 0.01 kW."
        ::= { analogdata9 27 }

    outputAcitvePowerC9 OBJECT-TYPE
        SYNTAX Integer32
        MAX-ACCESS read-only
        STATUS current
        DESCRIPTION
            "Output Acitve Power C, stored as 0.01 kW."
        ::= { analogdata9 28 }

    outputReactivePowerA9 OBJECT-TYPE
        SYNTAX Integer32
        MAX-ACCESS read-only
        STATUS current
        DESCRIPTION
            "Output Reactive Power A, stored as 0.01 KVAR."
        ::= { analogdata9 29 }

    outputReactivePowerB9 OBJECT-TYPE
        SYNTAX Integer32
        MAX-ACCESS read-only
        STATUS current
        DESCRIPTION
            "Output Reactive Power B, stored as 0.01 KVAR."
        ::= { analogdata9 30 }

    outputReactivePowerC9 OBJECT-TYPE
        SYNTAX Integer32
        MAX-ACCESS read-only
        STATUS current
        DESCRIPTION
            "Output Reactive Power C, stored as 0.01 KVAR."
        ::= { analogdata9 31 }

    outputAppPowerA9 OBJECT-TYPE
        SYNTAX Integer32
        MAX-ACCESS read-only
        STATUS current
        DESCRIPTION
            "Output App Power A, stored as 0.01 kVA."
        ::= { analogdata9 32 }

    outputAppPowerB9 OBJECT-TYPE
        SYNTAX Integer32
        MAX-ACCESS read-only
        STATUS current
        DESCRIPTION
            "Output App Power B, stored as 0.01 kVA."
        ::= { analogdata9 33 }

    outputAppPowerC9 OBJECT-TYPE
        SYNTAX Integer32
        MAX-ACCESS read-only
        STATUS current
        DESCRIPTION
            "Output App Power C, stored as 0.01 kVA."
        ::= { analogdata9 34 }

    outputLoadA9 OBJECT-TYPE
        SYNTAX Integer32
        MAX-ACCESS read-only
        STATUS current
        DESCRIPTION
            "Output Load A, stored as 0.01 %."
        ::= { analogdata9 35 }

    outputLoadB9 OBJECT-TYPE
        SYNTAX Integer32
        MAX-ACCESS read-only
        STATUS current
        DESCRIPTION
            "Output Load B, stored as 0.01 %."
        ::= { analogdata9 36 }

    outputLoadC9 OBJECT-TYPE
        SYNTAX Integer32
        MAX-ACCESS read-only
        STATUS current
        DESCRIPTION
            "Output Load C, stored as 0.01 %."
        ::= { analogdata9 37 }

    outputCrestFactorA9 OBJECT-TYPE
        SYNTAX Integer32
        MAX-ACCESS read-only
        STATUS current
        DESCRIPTION
            "Output Crest Factor A, stored as 0.01 ."
        ::= { analogdata9 38 }

    outputCrestFactorB9 OBJECT-TYPE
        SYNTAX Integer32
        MAX-ACCESS read-only
        STATUS current
        DESCRIPTION
            "Output Crest Factor B, stored as 0.01 ."
        ::= { analogdata9 39 }

    outputCrestFactorC9 OBJECT-TYPE
        SYNTAX Integer32
        MAX-ACCESS read-only
        STATUS current
        DESCRIPTION
            "Output Crest Factor C, stored as 0.01 ."
        ::= { analogdata9 40 }

    bypassVoltageA9 OBJECT-TYPE
        SYNTAX Integer32
        MAX-ACCESS read-only
        STATUS current
        DESCRIPTION
            "Bypass Voltage A, stored as 0.01 V."
        ::= { analogdata9 41 }

    bypassVoltageB9 OBJECT-TYPE
        SYNTAX Integer32
        MAX-ACCESS read-only
        STATUS current
        DESCRIPTION
            "Bypass Voltage B, stored as 0.01 V."
        ::= { analogdata9 42 }

    bypassVoltageC9 OBJECT-TYPE
        SYNTAX Integer32
        MAX-ACCESS read-only
        STATUS current
        DESCRIPTION
            "Bypass Voltage C, stored as 0.01 V."
        ::= { analogdata9 43 }

    bypassFrequency9 OBJECT-TYPE
        SYNTAX Integer32
        MAX-ACCESS read-only
        STATUS current
        DESCRIPTION
            "Bypass Frequency, stored as 0.01 Hz."
        ::= { analogdata9 44 }

    positiveBatteryVoltage9 OBJECT-TYPE
        SYNTAX Integer32
        MAX-ACCESS read-only
        STATUS current
        DESCRIPTION
            "positive Battery Voltage, stored as 0.01 V."
        ::= { analogdata9 45 }

    positiveBatteryCurrent9 OBJECT-TYPE
        SYNTAX Integer32
        MAX-ACCESS read-only
        STATUS current
        DESCRIPTION
            "positive Battery Current, stored as 0.01 A."
        ::= { analogdata9 46 }

    negativeBatteryVoltage9 OBJECT-TYPE
        SYNTAX Integer32
        MAX-ACCESS read-only
        STATUS current
        DESCRIPTION
            "negative Battery Voltage, stored as 0.01 V."
        ::= { analogdata9 47 }

    negativeBatteryCurrent9 OBJECT-TYPE
        SYNTAX Integer32
        MAX-ACCESS read-only
        STATUS current
        DESCRIPTION
            "negative Battery Current, stored as 0.01 A."
        ::= { analogdata9 48 }

    batteryAgingRate9 OBJECT-TYPE
        SYNTAX Integer32
        MAX-ACCESS read-only
        STATUS current
        DESCRIPTION
            "Battery Aging Rate, stored as 0.01."
        ::= { analogdata9 49 }

    batteryRemainsTime9 OBJECT-TYPE
        SYNTAX Integer32
        MAX-ACCESS read-only
        STATUS current
        DESCRIPTION
            "Battery Remains Time, stored as 0.01 Hour."
        ::= { analogdata9 50 }

    batteryTemperature9 OBJECT-TYPE
        SYNTAX Integer32
        MAX-ACCESS read-only
        STATUS current
        DESCRIPTION
            "Battery Temperature, stored as 0.01 &deg;C."
        ::= { analogdata9 51 }

    batteryEnvironmentTemperature9 OBJECT-TYPE
        SYNTAX Integer32
        MAX-ACCESS read-only
        STATUS current
        DESCRIPTION
            "Battery Environment Temperature, stored as 0.01 &deg;C."
        ::= { analogdata9 52 }
        
analogdata10 OBJECT IDENTIFIER ::= { system 14 }

    inputPhaseVoltageA10 OBJECT-TYPE
        SYNTAX Integer32
        MAX-ACCESS read-only
        STATUS current
        DESCRIPTION
            "Input Phase Voltage A, stored as 0.01 V."
        ::= { analogdata10 1 }

    inputPhaseVoltageB10 OBJECT-TYPE
        SYNTAX Integer32
        MAX-ACCESS read-only
        STATUS current
        DESCRIPTION
            "Input Phase Voltage B, stored as 0.01 V."
        ::= { analogdata10 2 }

    inputPhaseVoltageC10 OBJECT-TYPE
        SYNTAX Integer32
        MAX-ACCESS read-only
        STATUS current
        DESCRIPTION
            "Input Phase Voltage C, stored as 0.01 V."
        ::= { analogdata10 3 }

    inputLineVoltageA10 OBJECT-TYPE
        SYNTAX Integer32
        MAX-ACCESS read-only
        STATUS current
        DESCRIPTION
            "Input Line Voltage A, stored as 0.01 V."
        ::= { analogdata10 4 }

    inputLineVoltageB10 OBJECT-TYPE
        SYNTAX Integer32
        MAX-ACCESS read-only
        STATUS current
        DESCRIPTION
            "Input Line Voltage B, stored as 0.01 V."
        ::= { analogdata10 5 }

    inputLineVoltageC10 OBJECT-TYPE
        SYNTAX Integer32
        MAX-ACCESS read-only
        STATUS current
        DESCRIPTION
            "Input Line Voltage C, stored as 0.01 V."
        ::= { analogdata10 6 }

    inputCurrentA10 OBJECT-TYPE
        SYNTAX Integer32
        MAX-ACCESS read-only
        STATUS current
        DESCRIPTION
            "Input Current A, stored as 0.01 A."
        ::= { analogdata10 7 }

    inputCurrentB10 OBJECT-TYPE
        SYNTAX Integer32
        MAX-ACCESS read-only
        STATUS current
        DESCRIPTION
            "Input Current B, stored as 0.01 A."
        ::= { analogdata10 8 }

    inputCurrentC10 OBJECT-TYPE
        SYNTAX Integer32
        MAX-ACCESS read-only
        STATUS current
        DESCRIPTION
            "Input Current C, stored as 0.01 A."
        ::= { analogdata10 9 }

    inputFrequency10 OBJECT-TYPE
        SYNTAX Integer32
        MAX-ACCESS read-only
        STATUS current
        DESCRIPTION
            "Input Frequency, stored as 0.01 Hz."
        ::= { analogdata10 10 }

    inputPowerFactorA10 OBJECT-TYPE
        SYNTAX Integer32
        MAX-ACCESS read-only
        STATUS current
        DESCRIPTION
            "Input Power Factor A, stored as 0.01."
        ::= { analogdata10 11 }

    inputPowerFactorB10 OBJECT-TYPE
        SYNTAX Integer32
        MAX-ACCESS read-only
        STATUS current
        DESCRIPTION
            "Input Power Factor B, stored as 0.01."
        ::= { analogdata10 12 }

    inputPowerFactorC10 OBJECT-TYPE
        SYNTAX Integer32
        MAX-ACCESS read-only
        STATUS current
        DESCRIPTION
            "Input Power Factor C, stored as 0.01."
        ::= { analogdata10 13 }

    dCBus1Voltage10 OBJECT-TYPE
        SYNTAX Integer32
        MAX-ACCESS read-only
        STATUS current
        DESCRIPTION
            "DCBus1 Voltage, stored as 0.01 V."
        ::= { analogdata10 14 }

    dCBus2Voltage10 OBJECT-TYPE
        SYNTAX Integer32
        MAX-ACCESS read-only
        STATUS current
        DESCRIPTION
            "DCBus2 Voltage, stored as 0.01 V."
        ::= { analogdata10 15 }

    outputVoltageA10 OBJECT-TYPE
    	SYNTAX Integer32
    	MAX-ACCESS read-only
        STATUS current
        DESCRIPTION
            "Output voltage A, stored as 0.01 V."
        ::= { analogdata10 16 }

    outputVoltageB10 OBJECT-TYPE
    	SYNTAX Integer32
    	MAX-ACCESS read-only
        STATUS current
        DESCRIPTION
            "Output voltage B, stored as 0.01 V."
        ::= { analogdata10 17 }

    outputVoltageC10 OBJECT-TYPE
    	SYNTAX Integer32
    	MAX-ACCESS read-only
        STATUS current
        DESCRIPTION
            "Output voltage C, stored as 0.01 V."
        ::= { analogdata10 18 }

    outputCurrentA10 OBJECT-TYPE
        SYNTAX Integer32
        MAX-ACCESS read-only
        STATUS current
        DESCRIPTION
            "Output current A, stored as 0.01 A."
        ::= { analogdata10 19 }

    outputCurrentB10 OBJECT-TYPE
        SYNTAX Integer32
        MAX-ACCESS read-only
        STATUS current
        DESCRIPTION
            "Output current B, stored as 0.01 A."
        ::= { analogdata10 20 }

    outputCurrentC10 OBJECT-TYPE
        SYNTAX Integer32
        MAX-ACCESS read-only
        STATUS current
        DESCRIPTION
            "Output current C, stored as 0.01 A."
        ::= { analogdata10 21 }

    outputFrequency10 OBJECT-TYPE
        SYNTAX Integer32
        MAX-ACCESS read-only
        STATUS current
        DESCRIPTION
            "Output Frequency, stored as 0.01 Hz."
        ::= { analogdata10 22 }

    outputPowerFactorA10 OBJECT-TYPE
        SYNTAX Integer32
        MAX-ACCESS read-only
        STATUS current
        DESCRIPTION
            "Output Power Factor A, stored as 0.01."
        ::= { analogdata10 23 }

    outputPowerFactorB10 OBJECT-TYPE
        SYNTAX Integer32
        MAX-ACCESS read-only
        STATUS current
        DESCRIPTION
            "Output Power Factor B, stored as 0.01."
        ::= { analogdata10 24 }

    outputPowerFactorC10 OBJECT-TYPE
        SYNTAX Integer32
        MAX-ACCESS read-only
        STATUS current
        DESCRIPTION
            "Output Power Factor C, stored as 0.01."
        ::= { analogdata10 25 }

    outputAcitvePowerA10 OBJECT-TYPE
        SYNTAX Integer32
        MAX-ACCESS read-only
        STATUS current
        DESCRIPTION
            "Output Acitve Power A, stored as 0.01 kW."
        ::= { analogdata10 26 }

    outputAcitvePowerB10 OBJECT-TYPE
        SYNTAX Integer32
        MAX-ACCESS read-only
        STATUS current
        DESCRIPTION
            "Output Acitve Power B, stored as 0.01 kW."
        ::= { analogdata10 27 }

    outputAcitvePowerC10 OBJECT-TYPE
        SYNTAX Integer32
        MAX-ACCESS read-only
        STATUS current
        DESCRIPTION
            "Output Acitve Power C, stored as 0.01 kW."
        ::= { analogdata10 28 }

    outputReactivePowerA10 OBJECT-TYPE
        SYNTAX Integer32
        MAX-ACCESS read-only
        STATUS current
        DESCRIPTION
            "Output Reactive Power A, stored as 0.01 KVAR."
        ::= { analogdata10 29 }

    outputReactivePowerB10 OBJECT-TYPE
        SYNTAX Integer32
        MAX-ACCESS read-only
        STATUS current
        DESCRIPTION
            "Output Reactive Power B, stored as 0.01 KVAR."
        ::= { analogdata10 30 }

    outputReactivePowerC10 OBJECT-TYPE
        SYNTAX Integer32
        MAX-ACCESS read-only
        STATUS current
        DESCRIPTION
            "Output Reactive Power C, stored as 0.01 KVAR."
        ::= { analogdata10 31 }

    outputAppPowerA10 OBJECT-TYPE
        SYNTAX Integer32
        MAX-ACCESS read-only
        STATUS current
        DESCRIPTION
            "Output App Power A, stored as 0.01 kVA."
        ::= { analogdata10 32 }

    outputAppPowerB10 OBJECT-TYPE
        SYNTAX Integer32
        MAX-ACCESS read-only
        STATUS current
        DESCRIPTION
            "Output App Power B, stored as 0.01 kVA."
        ::= { analogdata10 33 }

    outputAppPowerC10 OBJECT-TYPE
        SYNTAX Integer32
        MAX-ACCESS read-only
        STATUS current
        DESCRIPTION
            "Output App Power C, stored as 0.01 kVA."
        ::= { analogdata10 34 }

    outputLoadA10 OBJECT-TYPE
        SYNTAX Integer32
        MAX-ACCESS read-only
        STATUS current
        DESCRIPTION
            "Output Load A, stored as 0.01 %."
        ::= { analogdata10 35 }

    outputLoadB10 OBJECT-TYPE
        SYNTAX Integer32
        MAX-ACCESS read-only
        STATUS current
        DESCRIPTION
            "Output Load B, stored as 0.01 %."
        ::= { analogdata10 36 }

    outputLoadC10 OBJECT-TYPE
        SYNTAX Integer32
        MAX-ACCESS read-only
        STATUS current
        DESCRIPTION
            "Output Load C, stored as 0.01 %."
        ::= { analogdata10 37 }

    outputCrestFactorA10 OBJECT-TYPE
        SYNTAX Integer32
        MAX-ACCESS read-only
        STATUS current
        DESCRIPTION
            "Output Crest Factor A, stored as 0.01 ."
        ::= { analogdata10 38 }

    outputCrestFactorB10 OBJECT-TYPE
        SYNTAX Integer32
        MAX-ACCESS read-only
        STATUS current
        DESCRIPTION
            "Output Crest Factor B, stored as 0.01 ."
        ::= { analogdata10 39 }

    outputCrestFactorC10 OBJECT-TYPE
        SYNTAX Integer32
        MAX-ACCESS read-only
        STATUS current
        DESCRIPTION
            "Output Crest Factor C, stored as 0.01 ."
        ::= { analogdata10 40 }

    bypassVoltageA10 OBJECT-TYPE
        SYNTAX Integer32
        MAX-ACCESS read-only
        STATUS current
        DESCRIPTION
            "Bypass Voltage A, stored as 0.01 V."
        ::= { analogdata10 41 }

    bypassVoltageB10 OBJECT-TYPE
        SYNTAX Integer32
        MAX-ACCESS read-only
        STATUS current
        DESCRIPTION
            "Bypass Voltage B, stored as 0.01 V."
        ::= { analogdata10 42 }

    bypassVoltageC10 OBJECT-TYPE
        SYNTAX Integer32
        MAX-ACCESS read-only
        STATUS current
        DESCRIPTION
            "Bypass Voltage C, stored as 0.01 V."
        ::= { analogdata10 43 }

    bypassFrequency10 OBJECT-TYPE
        SYNTAX Integer32
        MAX-ACCESS read-only
        STATUS current
        DESCRIPTION
            "Bypass Frequency, stored as 0.01 Hz."
        ::= { analogdata10 44 }

    positiveBatteryVoltage10 OBJECT-TYPE
        SYNTAX Integer32
        MAX-ACCESS read-only
        STATUS current
        DESCRIPTION
            "positive Battery Voltage, stored as 0.01 V."
        ::= { analogdata10 45 }

    positiveBatteryCurrent10 OBJECT-TYPE
        SYNTAX Integer32
        MAX-ACCESS read-only
        STATUS current
        DESCRIPTION
            "positive Battery Current, stored as 0.01 A."
        ::= { analogdata10 46 }

    negativeBatteryVoltage10 OBJECT-TYPE
        SYNTAX Integer32
        MAX-ACCESS read-only
        STATUS current
        DESCRIPTION
            "negative Battery Voltage, stored as 0.01 V."
        ::= { analogdata10 47 }

    negativeBatteryCurrent10 OBJECT-TYPE
        SYNTAX Integer32
        MAX-ACCESS read-only
        STATUS current
        DESCRIPTION
            "negative Battery Current, stored as 0.01 A."
        ::= { analogdata10 48 }

    batteryAgingRate10 OBJECT-TYPE
        SYNTAX Integer32
        MAX-ACCESS read-only
        STATUS current
        DESCRIPTION
            "Battery Aging Rate, stored as 0.01."
        ::= { analogdata10 49 }

    batteryRemainsTime10 OBJECT-TYPE
        SYNTAX Integer32
        MAX-ACCESS read-only
        STATUS current
        DESCRIPTION
            "Battery Remains Time, stored as 0.01 Hour."
        ::= { analogdata10 50 }

    batteryTemperature10 OBJECT-TYPE
        SYNTAX Integer32
        MAX-ACCESS read-only
        STATUS current
        DESCRIPTION
            "Battery Temperature, stored as 0.01 &deg;C."
        ::= { analogdata10 51 }

    batteryEnvironmentTemperature10 OBJECT-TYPE
        SYNTAX Integer32
        MAX-ACCESS read-only
        STATUS current
        DESCRIPTION
            "Battery Environment Temperature, stored as 0.01 &deg;C."
        ::= { analogdata10 52 }


-- ------------------------------------------------------------------------ 
-- 1.2.6 the control group
-- ------------------------------------------------------------------------ 



-- ------------------------------------------------------------------------ 
-- 1.2.7 the config group
-- ------------------------------------------------------------------------ 



------------------------------------------------------------
-- 1.3 Alarm trap table { nxrMIB 3 }
------------------------------------------------------------

alarmTrapTable OBJECT-TYPE
	SYNTAX SEQUENCE OF AlarmTrapEntry
	MAX-ACCESS not-accessible
	STATUS current
	DESCRIPTION "
		Table holding information about the submitted alarm traps."
	::= { nxrMIB 3 }

alarmTrapEntry OBJECT-TYPE
	SYNTAX AlarmTrapEntry
	MAX-ACCESS not-accessible
	STATUS current
	DESCRIPTION "
		An entry (conceptual row) in the alarmTrapTable."
	INDEX { alarmIndex }
	::= { alarmTrapTable 1 }

AlarmTrapEntry ::= SEQUENCE {
	alarmIndex Counter32,
	alarmTime DisplayString,
	alarmStatusChange StatusChange,
	alarmSeverity Status,
	alarmDescription DisplayString,
	alarmId Integer32 }

alarmIndex OBJECT-TYPE
	SYNTAX Counter32
	MAX-ACCESS read-only
	STATUS current
	DESCRIPTION "
		The unique sequence number of this alarm trap."
	::= { alarmTrapEntry 1 }

alarmTime OBJECT-TYPE
	SYNTAX DisplayString
	MAX-ACCESS read-only
	STATUS current
	DESCRIPTION "
		Date and time when event occured."
	::= { alarmTrapEntry 2 }

alarmStatusChange OBJECT-TYPE
	SYNTAX StatusChange
	MAX-ACCESS read-only
	STATUS current
	DESCRIPTION "
		Indicates 'activated' (0) or 'deactivated' (1) alarm events."
	::= { alarmTrapEntry 3 }

alarmSeverity OBJECT-TYPE
	SYNTAX Status
	MAX-ACCESS read-only
	STATUS current
	DESCRIPTION "
		The severity of the alarm. One of
		(0) informational
		(1) warning
		(2) critical"
	::= { alarmTrapEntry 4 }
	
alarmDescription OBJECT-TYPE
	SYNTAX DisplayString
	MAX-ACCESS read-only
	STATUS current
	DESCRIPTION "
		Free-text description of alarm."
	::= { alarmTrapEntry 5 }
	
alarmId OBJECT-TYPE
	SYNTAX Integer32
	MAX-ACCESS read-only
	STATUS current
	DESCRIPTION "
		Alarm id."
	::= { alarmTrapEntry 6 }


------------------------------------------------------------
-- End of MIB definitions
------------------------------------------------------------

END
