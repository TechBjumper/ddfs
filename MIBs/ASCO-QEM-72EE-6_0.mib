-- *********************************************************************
-- **
-- ** Confidential and proprietary Information
-- **
-- ** Copyright © ASCO Power Technologies. All rights reserved.
-- ** 
-- ** Modified 4/7/2015 bKirby	Filename change
-- ** Modified 6/30/2015 aVerma	major addition of Group G registers
-- *********************************************************************
-- ** Filename:   ASCO_QEM-72EE-6_0.mib
-- *********************************************************************

ASCO-QEM-72EE-6-0-MIB DEFINITIONS ::= BEGIN

IMPORTS

    MODULE-COMPLIANCE, OBJECT-GROUP
        FROM SNMPv2-CONF

    MODULE-IDENTITY, OBJECT-TYPE,NOTIFICATION-TYPE, enterprises, Counter32, Integer32
        FROM SNMPv2-SMI

    DisplayString
        FROM SNMPv2-TC;



-- A MIB with definitions for ASCO Version 2.0

		-- 1.3.6.1.4.1.7777
		asco OBJECT IDENTIFIER ::= { enterprises 7777 }


		-- 1.3.6.1.4.1.7777.1
		device OBJECT IDENTIFIER ::= { asco 1 }


		-- 1.3.6.1.4.1.7777.1.2.1
		transferswitch   OBJECT IDENTIFIER ::= { device 1 }
		dpmNormal        OBJECT IDENTIFIER ::= { device 2 }
		dpmEmergency     OBJECT IDENTIFIER ::= { device 3 }
		dpmLoad          OBJECT IDENTIFIER ::= { device 4 }
		dpmOther         OBJECT IDENTIFIER ::= { device 5 }
		traps            OBJECT IDENTIFIER ::= { device 6 }

        -- 1.3.6.1.4.1.7777.1.2.1.1
		phase_shift_between_normal_and_emergency OBJECT-TYPE
			SYNTAX Integer32
			MAX-ACCESS read-only
			STATUS current
			DESCRIPTION
				"Phase shift between normal & emergency"
			::= { transferswitch 1 }
                        
                        
        -- 1.3.6.1.4.1.7777.1.2.1.2
		normal_frequency OBJECT-TYPE
			SYNTAX Integer32
			MAX-ACCESS read-only
			STATUS current
			DESCRIPTION
				"Normal frequency"
			::= { transferswitch 2 }
                        
                        
         -- 1.3.6.1.4.1.7777.1.2.1.3
	       emergency_frequency OBJECT-TYPE
			SYNTAX Integer32
			MAX-ACCESS read-only
			STATUS current
			DESCRIPTION
				"Emergency frequency"
			::= { transferswitch 3 }
                        
                        
        -- 1.3.6.1.4.1.7777.1.2.1.4
	       main_on_normal OBJECT-TYPE
			SYNTAX Integer32
			MAX-ACCESS read-only
			STATUS current
			DESCRIPTION
				"Main on normal"
			::= { transferswitch 4 }         
               
        -- 1.3.6.1.4.1.7777.1.2.1.5
	       main_on_emergency OBJECT-TYPE
			SYNTAX Integer32
			MAX-ACCESS read-only
			STATUS current
			DESCRIPTION
				"Main on emergency"
			::= { transferswitch 5 }     
                                  
                        
         -- 1.3.6.1.4.1.7777.1.2.1.6
	       auxiliary_on_normal OBJECT-TYPE
			SYNTAX Integer32
			MAX-ACCESS read-only
			STATUS current
			DESCRIPTION
				"Auxiliary on normal"
			::= { transferswitch 6 }   
              
              -- 1.3.6.1.4.1.7777.1.2.1.7
	      auxiliary_on_emergency OBJECT-TYPE
			SYNTAX Integer32
			MAX-ACCESS read-only
			STATUS current
			DESCRIPTION
				"Auxiliary on emergency"
			::= { transferswitch 7 } 
                        
                        
              -- 1.3.6.1.4.1.7777.1.2.1.8
	      normal_source_available OBJECT-TYPE
			SYNTAX Integer32
			MAX-ACCESS read-only
			STATUS current
			DESCRIPTION
				"Normal source available"
			::= { transferswitch 8 } 
             
             -- 1.3.6.1.4.1.7777.1.2.1.9
	     emergency_source_available OBJECT-TYPE
			SYNTAX Integer32
			MAX-ACCESS read-only
			STATUS current
			DESCRIPTION
				"Emergency source available"
			::= { transferswitch 9 } 
             
              -- 1.3.6.1.4.1.7777.1.2.1.10
	        engine_exerciser_with_load_active OBJECT-TYPE
			SYNTAX Integer32
			MAX-ACCESS read-only
			STATUS current
			  DESCRIPTION
				"Engine exerciser with load active"
			::= { transferswitch 10 } 
                        
              -- 1.3.6.1.4.1.7777.1.2.1.11
	        external_f17_is_active OBJECT-TYPE
			SYNTAX Integer32
			MAX-ACCESS read-only
			STATUS current
			  DESCRIPTION
				"External F17 is active"
			::= { transferswitch 11 } 
                        
                        
             -- 1.3.6.1.4.1.7777.1.2.1.12
	        normal_voltage_phase_AB OBJECT-TYPE
			SYNTAX Integer32
			MAX-ACCESS read-only
			STATUS current
			  DESCRIPTION
				"Normal voltage phase AB"
			::= { transferswitch 12 } 
                        
             -- 1.3.6.1.4.1.7777.1.2.1.13
	        normal_voltage_phase_BC OBJECT-TYPE
			SYNTAX Integer32
			MAX-ACCESS read-only
			STATUS current
			  DESCRIPTION
				"Normal voltage phase BC"
			::= { transferswitch 13 } 
                                   
              -- 1.3.6.1.4.1.7777.1.2.1.14
	      normal_voltage_phase_CA OBJECT-TYPE
			SYNTAX Integer32
			MAX-ACCESS read-only
			STATUS current
			  DESCRIPTION
				"Normal voltage phase CA"
			::= { transferswitch 14 } 
             
             -- 1.3.6.1.4.1.7777.1.2.1.15
	     normal_voltage_unbalance OBJECT-TYPE
			SYNTAX Integer32
			MAX-ACCESS read-only
			STATUS current
			  DESCRIPTION
				"Normal voltage unbalance"
			::= { transferswitch 15 } 
              
            
                        
        -- 1.3.6.1.4.1.7777.1.2.1.18
	    emergency_voltage_phase_CA OBJECT-TYPE
			SYNTAX Integer32
			MAX-ACCESS read-only
			STATUS current
			  DESCRIPTION
				"Emergency voltage phase CA"
			::= { transferswitch 18 }  
                        
        -- 1.3.6.1.4.1.7777.1.2.1.19
	    nominal_voltage OBJECT-TYPE
			SYNTAX Integer32
			MAX-ACCESS read-only
			STATUS current
			  DESCRIPTION
				"Nominal voltage"
			::= { transferswitch 19 }  
			
        -- 1.3.6.1.4.1.7777.1.2.1.20
	    nominal_frequency OBJECT-TYPE
			SYNTAX Integer32
			MAX-ACCESS read-only
			STATUS current
			  DESCRIPTION
				"Nominal frequency"
			::= { transferswitch 20 }  

	    -- 1.3.6.1.4.1.7777.1.2.1.21
            normal_source_3phase_sensing OBJECT-TYPE
			SYNTAX Integer32
			MAX-ACCESS read-only
			STATUS current
			  DESCRIPTION
				"Normal source 3 phase sensing"
			::= { transferswitch 21 }  
                        
         
            -- 1.3.6.1.4.1.7777.1.2.1.22
            transfer_switch_type OBJECT-TYPE
			SYNTAX Integer32
			MAX-ACCESS read-only
			STATUS current
			  DESCRIPTION
				"Transfer switch type (OTTS,DTTS)"
			::= { transferswitch 22 }  


            -- 1.3.6.1.4.1.7777.1.2.1.23
            transfer_switch_ampere_rating OBJECT-TYPE
			SYNTAX Integer32
			MAX-ACCESS read-only
			STATUS current
			  DESCRIPTION
				"Transfer switch ampere rating"
			::= { transferswitch 23 } 
                        
            -- 1.3.6.1.4.1.7777.1.2.1.24
            controller_software_version OBJECT-TYPE
			SYNTAX DisplayString (SIZE (0..11))
			MAX-ACCESS read-only
			STATUS current
			  DESCRIPTION
				"Controller software version"
			::= { transferswitch 24 } 
           
            -- 1.3.6.1.4.1.7777.1.2.1.25
            controller_software_date OBJECT-TYPE
			SYNTAX DisplayString (SIZE (0..11))
			MAX-ACCESS read-only
			STATUS current
			  DESCRIPTION
				"Controller software date"
			::= { transferswitch 25 } 
                        
            -- 1.3.6.1.4.1.7777.1.2.1.26
            external_parameter_lock_is_active OBJECT-TYPE
			SYNTAX Integer32
			MAX-ACCESS read-only
			STATUS current
			  DESCRIPTION
				"External parameter lock is active"
			::= { transferswitch 26 } 
                        
            -- 1.3.6.1.4.1.7777.1.2.1.27
            engine_running OBJECT-TYPE
			SYNTAX Integer32
			MAX-ACCESS read-only
			STATUS current
			  DESCRIPTION
				"Engine running"
			::= { transferswitch 27 } 
                        
            -- 1.3.6.1.4.1.7777.1.2.1.28
            controller_state OBJECT-TYPE
			SYNTAX Integer32
			MAX-ACCESS read-only
			STATUS current
			  DESCRIPTION
				"Controller state"
			::= { transferswitch 28 } 
                        
            -- 1.3.6.1.4.1.7777.1.2.1.29
            controller_status_state_data OBJECT-TYPE
			SYNTAX Integer32
			MAX-ACCESS read-only
			STATUS current
			  DESCRIPTION
				"Controller status state data"
			::= { transferswitch 29 } 
                        
            -- 1.3.6.1.4.1.7777.1.2.1.30
            timer_bypass_feature_6B_status OBJECT-TYPE
			SYNTAX Integer32
			MAX-ACCESS read-only
			STATUS current
			  DESCRIPTION
				"Timer bypass (Feature 6B) status"
			::= { transferswitch 30 } 
         
         -- 1.3.6.1.4.1.7777.1.2.1.31
           remote_transfer_feature_17_status OBJECT-TYPE
			SYNTAX Integer32
			MAX-ACCESS read-only
			STATUS current
			  DESCRIPTION
				"Remote transfer (Feature 17) status"
			::= { transferswitch 31 } 
     
           -- 1.3.6.1.4.1.7777.1.2.1.32
           load_shed_feature_30_status OBJECT-TYPE
			SYNTAX Integer32
			MAX-ACCESS read-only
			STATUS current
			  DESCRIPTION
				"Load shed (Feature 30) status"
			::= { transferswitch 32 } 
                        
           -- 1.3.6.1.4.1.7777.1.2.1.33
           transfer_inhibit_to_emergency_feature_34B_status OBJECT-TYPE
			SYNTAX Integer32
			MAX-ACCESS read-only
			STATUS current
			  DESCRIPTION
				"Transfer inhibit to emergency (Feature 34B) status"
			::= { transferswitch 33 } 
                                             
           -- 1.3.6.1.4.1.7777.1.2.1.34
           local_test_feature_5_status OBJECT-TYPE
			SYNTAX Integer32
			MAX-ACCESS read-only
			STATUS current
			  DESCRIPTION
				"Local test (Feature 5) status"
			::= { transferswitch 34 } 
                        
          -- 1.3.6.1.4.1.7777.1.2.1.35
          manual_transfer_to_emergency_feature_6ZE_status OBJECT-TYPE
			SYNTAX Integer32
			MAX-ACCESS read-only
			STATUS current
			  DESCRIPTION
				"Manual transfer to emergency (Feature 6ZE) status"
			::= { transferswitch 35 } 
         
        -- 1.3.6.1.4.1.7777.1.2.1.36
        current_sensing OBJECT-TYPE
			SYNTAX Integer32
			MAX-ACCESS read-only
			STATUS current
			  DESCRIPTION
				"Current sensing"
			::= { transferswitch 36 } 
                        
         -- 1.3.6.1.4.1.7777.1.2.1.37
         phase_A_current OBJECT-TYPE
			SYNTAX Integer32
			MAX-ACCESS read-only
			STATUS current
			  DESCRIPTION
				"Phase A current (A).
				With 1 or 2 CT selected this is labeled as I1"
			::= { transferswitch 37 } 
         
        -- 1.3.6.1.4.1.7777.1.2.1.38
        phase_B_current OBJECT-TYPE
			SYNTAX Integer32
			MAX-ACCESS read-only
			STATUS current
			  DESCRIPTION
				"Phase B current (A)"
			::= { transferswitch 38 } 
       
        -- 1.3.6.1.4.1.7777.1.2.1.39
        phase_C_current OBJECT-TYPE
			SYNTAX Integer32
			MAX-ACCESS read-only
			STATUS current
			  DESCRIPTION
				"Phase C current (A).
				With 2 CT selected this is labeled as I2"
			::= { transferswitch 39 } 
        
        -- 1.3.6.1.4.1.7777.1.2.1.40
        failure_to_accept_timer OBJECT-TYPE
			SYNTAX Integer32
			MAX-ACCESS read-only
			STATUS current
			  DESCRIPTION
				"Failure to accept timer"
			::= { transferswitch 40 } 
       
        -- 1.3.6.1.4.1.7777.1.2.1.41
        normal_to_emergency_pretransfer_time_delay_feature_31_bypass_enabled OBJECT-TYPE
			SYNTAX Integer32
			MAX-ACCESS read-only
			STATUS current
			  DESCRIPTION
				"Normal to emergency pretransfer time delay (Feature 31) bypass enabled"
			::= { transferswitch 41 } 
                        
        -- 1.3.6.1.4.1.7777.1.2.1.42
        emergency_to_normal_pretransfer_time_delay_feature_31_bypass_enabled OBJECT-TYPE
			SYNTAX Integer32
			MAX-ACCESS read-only
			STATUS current
			  DESCRIPTION
				"Emergency to normal pretransfer time delay (Feature 31) bypass enabled"
			::= { transferswitch 42 } 


        -- 1.3.6.1.4.1.7777.1.2.1.43
        commit_to_transfer_enabled OBJECT-TYPE
			SYNTAX Integer32
			MAX-ACCESS read-only
			STATUS current
			  DESCRIPTION
				"Commit to transfer enabled"
			::= { transferswitch 43 } 

       -- 1.3.6.1.4.1.7777.1.2.1.44
        bypass_DTTS_source_failure_enabled OBJECT-TYPE
			SYNTAX Integer32
			MAX-ACCESS read-only
			STATUS current
			  DESCRIPTION
				"Bypass DTTS source failure enabled - data for DTTS and Group1 emulation is NOT enabled"
			::= { transferswitch 44 } 
                        
        -- 1.3.6.1.4.1.7777.1.2.1.45
        inphase_transfer_enabled OBJECT-TYPE
			SYNTAX Integer32
			MAX-ACCESS read-only
			STATUS current
			  DESCRIPTION
				"Inphase transfer enabled - only for OTTS"
			::= { transferswitch 45 } 

        
        -- 1.3.6.1.4.1.7777.1.2.1.46
        inphase_monitor_for_load_shed_feature_30_enabled OBJECT-TYPE
			SYNTAX Integer32
			MAX-ACCESS read-only
			STATUS current
			  DESCRIPTION
				"Inphase monitor for load shed (Feature 30) enabled"
			::= { transferswitch 46 } 
        
        
        -- 1.3.6.1.4.1.7777.1.2.1.47
        fail_accept_timer_enabled OBJECT-TYPE
			SYNTAX Integer32
			MAX-ACCESS read-only
			STATUS current
			  DESCRIPTION
				"Fail accept timer enabled"
			::= { transferswitch 47 } 
        
        -- 1.3.6.1.4.1.7777.1.2.1.48
        transfer_retransfer_time_delay_bypass_feature_6B_input_enabled OBJECT-TYPE
			SYNTAX Integer32
			MAX-ACCESS read-only
			STATUS current
			  DESCRIPTION
				"Transfer/retransfer time delay bypass (Feature 6B) input enabled"
			::= { transferswitch 48 } 
        
        -- 1.3.6.1.4.1.7777.1.2.1.49
        remote_transfer_feature_17_input_enabled OBJECT-TYPE
			SYNTAX Integer32
			MAX-ACCESS read-only
			STATUS current
			  DESCRIPTION
				"Remote transfer (Feature 17) input enabled - data for transfer switch in auto mode only"
			::= { transferswitch 49 } 
        
        -- 1.3.6.1.4.1.7777.1.2.1.50
        retransfer_to_normal_mode_selector_feature_6DL_input_enabled OBJECT-TYPE
			SYNTAX Integer32
			MAX-ACCESS read-only
			STATUS current
			  DESCRIPTION
				"Retransfer to normal mode selector (Feature 6DL) enabled"
			::= { transferswitch 50 } 
        
        -- 1.3.6.1.4.1.7777.1.2.1.51
        serial_remote_transfer_feature_17_enabled OBJECT-TYPE
			SYNTAX Integer32
			MAX-ACCESS read-only
			STATUS current
			  DESCRIPTION
				"Serial remote transfer (Feature 17) enabled"
			::= { transferswitch 51 } 
                        
        -- 1.3.6.1.4.1.7777.1.2.1.52
        voltage_unbalance_enabled OBJECT-TYPE
			SYNTAX Integer32
			MAX-ACCESS read-only
			STATUS current
			  DESCRIPTION
				"Voltage unbalance enabled"
			::= { transferswitch 52 } 
                        
        -- 1.3.6.1.4.1.7777.1.2.1.53
        current_sensing_module_present OBJECT-TYPE
			SYNTAX Integer32
			MAX-ACCESS read-only
			STATUS current
			  DESCRIPTION
				"Current sensing module present"
			::= { transferswitch 53 } 
                        
       -- 1.3.6.1.4.1.7777.1.2.1.54
        alert_LED_active OBJECT-TYPE
			SYNTAX Integer32
			MAX-ACCESS read-only
			STATUS current
			  DESCRIPTION
				"Alert LED active"
			::= { transferswitch 54 } 
        
        
        -- 1.3.6.1.4.1.7777.1.2.1.55
        not_in_auto_LED_active OBJECT-TYPE
			SYNTAX Integer32
			MAX-ACCESS read-only
			STATUS current
			  DESCRIPTION
				"Not in Auto LED active"
			::= { transferswitch 55 } 
        
                      
      -- 1.3.6.1.4.1.7777.1.2.1.58
      daylight_savings OBJECT-TYPE
			SYNTAX Integer32
			MAX-ACCESS read-only
			STATUS current
			  DESCRIPTION
				"Daylight savings"
			::= { transferswitch 58 } 
        
      -- 1.3.6.1.4.1.7777.1.2.1.59
      loss_of_emergency_when_connected_to_emergency_alarm_enabled OBJECT-TYPE
			SYNTAX Integer32
			MAX-ACCESS read-only
			STATUS current
			  DESCRIPTION
				"Loss of emergency when connected to emergency alarm enabled"
			::= { transferswitch 59 } 
                        
                        
      -- 1.3.6.1.4.1.7777.1.2.1.60
      expiration_of_failure_to_accept_timer_alarm_enabled  OBJECT-TYPE
			SYNTAX Integer32
			MAX-ACCESS read-only
			STATUS current
			  DESCRIPTION
				"Expiration of failure to accept timer alarm enabled"
			::= { transferswitch 60 } 
                                       
        -- 1.3.6.1.4.1.7777.1.2.1.61
        load_disconnect_enabled_DTTS_only  OBJECT-TYPE
			SYNTAX Integer32
			MAX-ACCESS read-only
			STATUS current
			  DESCRIPTION
				"Load disconnect enabled (DTTS only)"
			::= { transferswitch 61 }                  
                        
        -- 1.3.6.1.4.1.7777.1.2.1.62
        op1_is_feature_31  OBJECT-TYPE
			SYNTAX Integer32
			MAX-ACCESS read-only
			STATUS current
			  DESCRIPTION
				"OP1 is Feature 31"
			::= { transferswitch 62 }   

        -- 1.3.6.1.4.1.7777.1.2.1.63
        op1_is_common_alarm  OBJECT-TYPE
			SYNTAX Integer32
			MAX-ACCESS read-only
			STATUS current
			  DESCRIPTION
				"OP1 is common alarm"
			::= { transferswitch 63 } 
     
        -- 1.3.6.1.4.1.7777.1.2.1.64
        op1_is_NR2  OBJECT-TYPE
			SYNTAX Integer32
			MAX-ACCESS read-only
			STATUS current
			  DESCRIPTION
				"OP1 is NR2"
			::= { transferswitch 64 } 	 

        -- 1.3.6.1.4.1.7777.1.2.1.65
        op1_is_not_in_auto  OBJECT-TYPE
			SYNTAX Integer32
			MAX-ACCESS read-only
			STATUS current
			  DESCRIPTION
				"OP1 is not in auto"
			::= { transferswitch 65 } 	


        -- 1.3.6.1.4.1.7777.1.2.1.66
        op2_is_feature_31  OBJECT-TYPE
			SYNTAX Integer32
			MAX-ACCESS read-only
			STATUS current
			  DESCRIPTION
				"OP2 is Feature 31"
			::= { transferswitch 66 }   

        -- 1.3.6.1.4.1.7777.1.2.1.67
        op2_is_common_alarm  OBJECT-TYPE
			SYNTAX Integer32
			MAX-ACCESS read-only
			STATUS current
			  DESCRIPTION
				"OP2 is common alarm"
			::= { transferswitch 67 } 
     
    -- 1.3.6.1.4.1.7777.1.2.1.68
        op2_is_NR2  OBJECT-TYPE
			SYNTAX Integer32
			MAX-ACCESS read-only
			STATUS current
			  DESCRIPTION
				"OP2 is NR2"
			::= { transferswitch 68 } 	 

    -- 1.3.6.1.4.1.7777.1.2.1.69
        op2_is_not_in_auto  OBJECT-TYPE
			SYNTAX Integer32
			MAX-ACCESS read-only
			STATUS current
			  DESCRIPTION
				"OP2 is not in auto"
			::= { transferswitch 69 } 


    -- 1.3.6.1.4.1.7777.1.2.1.70
    op2_1G_enabled  OBJECT-TYPE
			SYNTAX Integer32
			MAX-ACCESS read-only
			STATUS current
			  DESCRIPTION
				"OP2 1G enabled"
			::= { transferswitch 70 }


	-- 1.3.6.1.4.1.7777.1.2.1.71
    op3_is_feature_31  OBJECT-TYPE
			SYNTAX Integer32
			MAX-ACCESS read-only
			STATUS current
			  DESCRIPTION
				"OP3 is Feature 31"
			::= { transferswitch 71 }   

    -- 1.3.6.1.4.1.7777.1.2.1.72
    op3_is_common_alarm  OBJECT-TYPE
			SYNTAX Integer32
			MAX-ACCESS read-only
			STATUS current
			  DESCRIPTION
				"OP3 is common alarm"
			::= { transferswitch 72 } 
     
    -- 1.3.6.1.4.1.7777.1.2.1.73
    op3_is_NR2  OBJECT-TYPE
			SYNTAX Integer32
			MAX-ACCESS read-only
			STATUS current
			  DESCRIPTION
				"OP2 is NR2"
			::= { transferswitch 73 } 	 

    -- 1.3.6.1.4.1.7777.1.2.1.74
    op3_is_not_in_auto  OBJECT-TYPE
			SYNTAX Integer32
			MAX-ACCESS read-only
			STATUS current
			  DESCRIPTION
				"OP3 is not in auto"
			::= { transferswitch 74 } 
	
    -- 1.3.6.1.4.1.7777.1.2.1.75
    controller_serial_number  OBJECT-TYPE
			SYNTAX DisplayString (SIZE (0..13))
			MAX-ACCESS read-only
			STATUS current
			  DESCRIPTION
				"Controller serial number"
			::= { transferswitch 75 } 

	-- 1.3.6.1.4.1.7777.1.2.1.76
    engine_exerciser_F11C_advanced_program_number  OBJECT-TYPE
			SYNTAX Integer32
			MAX-ACCESS read-only
			STATUS current
			  DESCRIPTION
				"Engine exerciser (F11C) advanced program number"
			::= { transferswitch 76 } 		

	-- 1.3.6.1.4.1.7777.1.2.1.77
    engine_exerciser_F11C_enabled  OBJECT-TYPE
			SYNTAX Integer32
			MAX-ACCESS read-only
			STATUS current
			  DESCRIPTION
				"Engine exerciser (F11C) enabled"
			::= { transferswitch 77 } 			
			
	-- 1.3.6.1.4.1.7777.1.2.1.78
    engine_exerciser_F11C_test_with_load_transfer_enabled  OBJECT-TYPE
			SYNTAX Integer32
			MAX-ACCESS read-only
			STATUS current
			  DESCRIPTION
				"Engine exerciser (F11C) test with load transfer enabled"
			::= { transferswitch 78 } 			
			
	-- 1.3.6.1.4.1.7777.1.2.1.79
    engine_exerciser_F11C_start_week  OBJECT-TYPE
			SYNTAX Integer32
			MAX-ACCESS read-only
			STATUS current
			  DESCRIPTION
				"Engine exerciser (F11C) start week"
			::= { transferswitch 79 } 			
			

	-- 1.3.6.1.4.1.7777.1.2.1.80
    engine_exerciser_F11C_day_of_week  OBJECT-TYPE
			SYNTAX Integer32
			MAX-ACCESS read-only
			STATUS current
			  DESCRIPTION
				"Engine exerciser (F11C) day of week"
			::= { transferswitch 80 } 					
			
			
			
	-- 1.3.6.1.4.1.7777.1.2.1.82
    engine_exerciser_F11C_start_time_hours  OBJECT-TYPE
			SYNTAX Integer32
			MAX-ACCESS read-only
			STATUS current
			  DESCRIPTION
				"Engine exerciser (F11C) start time hours"
			::= { transferswitch 82 } 	
    
    -- 1.3.6.1.4.1.7777.1.2.1.83
    engine_exerciser_F11C_start_time_minutes  OBJECT-TYPE
			SYNTAX Integer32
			MAX-ACCESS read-only
			STATUS current
			  DESCRIPTION
			 	"Engine exerciser (F11C) start time minutes"
			::= { transferswitch 83 } 	


    -- 1.3.6.1.4.1.7777.1.2.1.84
    engine_exerciser_F11C_run_time_hours  OBJECT-TYPE
			SYNTAX Integer32
			MAX-ACCESS read-only
			STATUS current
			  DESCRIPTION
				"Engine exerciser (F11C) run time hours"
			::= { transferswitch 84 } 	

    -- 1.3.6.1.4.1.7777.1.2.1.85
    engine_exerciser_F11C_run_time_minutes  OBJECT-TYPE
			SYNTAX Integer32
			MAX-ACCESS read-only
			STATUS current
			  DESCRIPTION
				"Engine exerciser (F11C) schedule run time minutes"
			::= { transferswitch 85 } 	
			
			
	-- 1.3.6.1.4.1.7777.1.2.1.86
    normal_voltage_dropout  OBJECT-TYPE
			SYNTAX Integer32
			MAX-ACCESS read-only
			STATUS current
			  DESCRIPTION
				"Normal voltage dropout"
			::= { transferswitch 86 } 			

	-- 1.3.6.1.4.1.7777.1.2.1.87
    normal_voltage_pickup  OBJECT-TYPE
			SYNTAX Integer32
			MAX-ACCESS read-only
			STATUS current
			  DESCRIPTION
				"Normal voltage pickup"
			::= { transferswitch 87 } 	

    -- 1.3.6.1.4.1.7777.1.2.1.88
    normal_over_voltage_trip  OBJECT-TYPE
			SYNTAX Integer32
			MAX-ACCESS read-only
			STATUS current
			  DESCRIPTION
				"Normal over voltage trip"
			::= { transferswitch 88 } 	

    -- 1.3.6.1.4.1.7777.1.2.1.89
    normal_frequency_dropout  OBJECT-TYPE
			SYNTAX Integer32
			MAX-ACCESS read-only
			STATUS current
			  DESCRIPTION
				"Normal frequency dropout"
			::= { transferswitch 89 } 	


    			
	-- 1.3.6.1.4.1.7777.1.2.1.90
    normal_frequency_pickup  OBJECT-TYPE
			SYNTAX Integer32
			MAX-ACCESS read-only
			STATUS current
			  DESCRIPTION
				"Normal frequency pickup"
			::= { transferswitch 90 } 	

    -- 1.3.6.1.4.1.7777.1.2.1.91
    normal_over_frequency_trip  OBJECT-TYPE
			SYNTAX Integer32
			MAX-ACCESS read-only
			STATUS current
			  DESCRIPTION
				"Normal over frequency trip"
			::= { transferswitch 91 } 				
	
    -- 1.3.6.1.4.1.7777.1.2.1.92
    emergency_voltage_dropout  OBJECT-TYPE
			SYNTAX Integer32
			MAX-ACCESS read-only
			STATUS current
			  DESCRIPTION
				"Emergency voltage dropout"
			::= { transferswitch 92 } 			

	-- 1.3.6.1.4.1.7777.1.2.1.93
    emergency_voltage_pickup  OBJECT-TYPE
			SYNTAX Integer32
			MAX-ACCESS read-only
			STATUS current
			  DESCRIPTION
				"Emergency voltage pickup"
			::= { transferswitch 93 } 	

    -- 1.3.6.1.4.1.7777.1.2.1.94
    emergency_over_voltage_trip  OBJECT-TYPE
			SYNTAX Integer32
			MAX-ACCESS read-only
			STATUS current
			  DESCRIPTION
				"Emergency over voltage trip"
			::= { transferswitch 94 } 	

    -- 1.3.6.1.4.1.7777.1.2.1.95
    emergency_frequency_dropout  OBJECT-TYPE
			SYNTAX Integer32
			MAX-ACCESS read-only
			STATUS current
			  DESCRIPTION
				"Emergency frequency dropout"
			::= { transferswitch 95 } 	


    			
	-- 1.3.6.1.4.1.7777.1.2.1.96
    emergency_frequency_pickup  OBJECT-TYPE
			SYNTAX Integer32
			MAX-ACCESS read-only
			STATUS current
			  DESCRIPTION
				"Emergency frequency pickup"
			::= { transferswitch 96 } 	

    -- 1.3.6.1.4.1.7777.1.2.1.97
    emergency_over_frequency_trip  OBJECT-TYPE
			SYNTAX Integer32
			MAX-ACCESS read-only
			STATUS current
			  DESCRIPTION
				"Emergency over frequency trip"
			::= { transferswitch 97 } 				
		
	-- 1.3.6.1.4.1.7777.1.2.1.98
    timer_1C_engine_start_time_delay  OBJECT-TYPE
			SYNTAX Integer32
			MAX-ACCESS read-only
			STATUS current
			  DESCRIPTION
				"Timer 1C engine start time delay"
			::= { transferswitch 98 } 	

    -- 1.3.6.1.4.1.7777.1.2.1.99
    timer_1F_engine_fail_time_delay  OBJECT-TYPE
			SYNTAX Integer32
			MAX-ACCESS read-only
			STATUS current
			  DESCRIPTION
				"Timer 1F engine fail time delay"
			::= { transferswitch 99 } 		
			
	-- 1.3.6.1.4.1.7777.1.2.1.100
    timer_2B_transfer_N_to_E_time_delay  OBJECT-TYPE
			SYNTAX Integer32
			MAX-ACCESS read-only
			STATUS current
			  DESCRIPTION
				"Timer 2B transfer N to E time delay"
			::= { transferswitch 100 } 	

    -- 1.3.6.1.4.1.7777.1.2.1.101
    timer_2E_engine_cool_down_time_delay  OBJECT-TYPE
			SYNTAX Integer32
			MAX-ACCESS read-only
			STATUS current
			  DESCRIPTION
				"Timer 2E engine cool down time delay"
			::= { transferswitch 101 } 		
	
	-- 1.3.6.1.4.1.7777.1.2.1.102
    timer_3AF_transfer_E_to_N_on_source_fail_time_delay  OBJECT-TYPE
			SYNTAX Integer32
			MAX-ACCESS read-only
			STATUS current
			  DESCRIPTION
				"Timer 3AF transfer E to N on source fail time delay"
			::= { transferswitch 102 } 	

    -- 1.3.6.1.4.1.7777.1.2.1.103
    timer_3A_T_transfer_E_to_N_on_test_time_delay  OBJECT-TYPE
			SYNTAX Integer32
			MAX-ACCESS read-only
			STATUS current
			  DESCRIPTION
				"Timer 3A T transfer E to N on test time delay"
			::= { transferswitch 103 } 
	
	-- 1.3.6.1.4.1.7777.1.2.1.104
    timer_31F_N_to_E_pre_transfer_signal_time_delay  OBJECT-TYPE
			SYNTAX Integer32
			MAX-ACCESS read-only
			STATUS current
			  DESCRIPTION
				"Timer 31F N to E pre transfer signal time delay"
			::= { transferswitch 104 } 	

    -- 1.3.6.1.4.1.7777.1.2.1.105
    timer_31M_N_to_E_post_transfer_signal_time_delay  OBJECT-TYPE
			SYNTAX Integer32
			MAX-ACCESS read-only
			STATUS current
			  DESCRIPTION
				"Timer 31M N to E post transfer signal time delay"
			::= { transferswitch 105 } 
	
	
	-- 1.3.6.1.4.1.7777.1.2.1.106
    timer_31G_E_to_N_pre_transfer_signal_time_delay  OBJECT-TYPE
			SYNTAX Integer32
			MAX-ACCESS read-only
			STATUS current
			  DESCRIPTION
				"Timer 31G E to N pre transfer signal time delay"
			::= { transferswitch 106 } 	

    -- 1.3.6.1.4.1.7777.1.2.1.107
    timer_31N_E_to_N_post_transfer_signal_time_delay  OBJECT-TYPE
			SYNTAX Integer32
			MAX-ACCESS read-only
			STATUS current
			  DESCRIPTION
				"Timer 31N  E to N post transfer signal time delay"
			::= { transferswitch 107 } 
			
	
	-- 1.3.6.1.4.1.7777.1.2.1.108
    dtts_load_disconnect_time_delay  OBJECT-TYPE
			SYNTAX Integer32
			MAX-ACCESS read-only
			STATUS current
			  DESCRIPTION
				"DTTS load disconnect time delay"
			::= { transferswitch 108 } 	

    -- 1.3.6.1.4.1.7777.1.2.1.109
    commit_to_transfer_after_engine_start  OBJECT-TYPE
			SYNTAX Integer32
			MAX-ACCESS read-only
			STATUS current
			  DESCRIPTION
				"Commit to transfer after engine start"
			::= { transferswitch 109 } 
	
	
	-- 1.3.6.1.4.1.7777.1.2.1.110
    real_time_hour  OBJECT-TYPE
			SYNTAX Integer32
			MAX-ACCESS read-only
			STATUS current
			  DESCRIPTION
				"Real time hour"
			::= { transferswitch 110 } 	

    
	
	-- 1.3.6.1.4.1.7777.1.2.1.111
    real_time_minute  OBJECT-TYPE
			SYNTAX Integer32
			MAX-ACCESS read-only
			STATUS current
			  DESCRIPTION
				"Real time minute"
			::= { transferswitch 111 } 		
	
	-- 1.3.6.1.4.1.7777.1.2.1.112
    real_time_second  OBJECT-TYPE
			SYNTAX Integer32
			MAX-ACCESS read-only
			STATUS current
			  DESCRIPTION
				"Real time second"
			::= { transferswitch 112 } 	

    -- 1.3.6.1.4.1.7777.1.2.1.113
    calendar_year  OBJECT-TYPE
			SYNTAX Integer32
			MAX-ACCESS read-only
			STATUS current
			  DESCRIPTION
				"Calendar year"
			::= { transferswitch 113 } 
	
	-- 1.3.6.1.4.1.7777.1.2.1.114
    calendar_month  OBJECT-TYPE
			SYNTAX Integer32
			MAX-ACCESS read-only
			STATUS current
			  DESCRIPTION
				"Calendar month"
			::= { transferswitch 114 } 	

    -- 1.3.6.1.4.1.7777.1.2.1.115
    calendar_day_of_month  OBJECT-TYPE
			SYNTAX Integer32
			MAX-ACCESS read-only
			STATUS current
			  DESCRIPTION
				"Calendar day of month"
			::= { transferswitch 115 } 
	
	
	-- 1.3.6.1.4.1.7777.1.2.1.116
    calendar_day_of_week  OBJECT-TYPE
			SYNTAX Integer32
			MAX-ACCESS read-only
			STATUS current
			  DESCRIPTION
				"Calendar day of week"
			::= { transferswitch 116 } 	

    -- 1.3.6.1.4.1.7777.1.2.1.117
    total_time_E_has_been_acceptable_high_word   OBJECT-TYPE
			SYNTAX Integer32  
			MAX-ACCESS read-only
			STATUS current
			  DESCRIPTION
				"Total time E has been acceptable(high word)"
			::= { transferswitch 117 } 
			
	-- 1.3.6.1.4.1.7777.1.2.1.118
    total_time_E_has_been_acceptable_low_word  OBJECT-TYPE
			SYNTAX Integer32  
			MAX-ACCESS read-only
			STATUS current
			  DESCRIPTION
				"Total time E has been acceptable(low word)"
			::= { transferswitch 118 } 
			
	-- 1.3.6.1.4.1.7777.1.2.1.119
    total_time_N_has_been_acceptable_high_word  OBJECT-TYPE
			SYNTAX Integer32  
			MAX-ACCESS read-only
			STATUS current
			  DESCRIPTION
				"Total time N has been acceptable(high word)"
			::= { transferswitch 119 } 	
	
	-- 1.3.6.1.4.1.7777.1.2.1.120
    total_time_N_has_been_acceptable_low_word  OBJECT-TYPE
			SYNTAX Integer32  
			MAX-ACCESS read-only
			STATUS current
			  DESCRIPTION
				"Total time N has been acceptable(low word)"
			::= { transferswitch 120 } 	

    -- 1.3.6.1.4.1.7777.1.2.1.121
    total_number_of_days_CP_has_been_energized  OBJECT-TYPE
			SYNTAX Integer32
			MAX-ACCESS read-only
			STATUS current
			  DESCRIPTION
				"Total number of days CP has been energized"
			::= { transferswitch 121 } 
	
	
	-- 1.3.6.1.4.1.7777.1.2.1.122
    total_number_of_TS_transfers  OBJECT-TYPE
			SYNTAX Integer32
			MAX-ACCESS read-only
			STATUS current
			  DESCRIPTION
				"Total number of TS transfers"
			::= { transferswitch 122 } 	

	-- 1.3.6.1.4.1.7777.1.2.1.123
    total_number_of_TS_transfers_due_to_source_failures  OBJECT-TYPE
			SYNTAX Integer32
			MAX-ACCESS read-only
			STATUS current
			  DESCRIPTION
				"Total number of TS transfers due to source failures"
			::= { transferswitch 123 } 
			
	
    -- 1.3.6.1.4.1.7777.1.2.1.124
    controller_location OBJECT-TYPE
			SYNTAX DisplayString (SIZE (0..21))
			MAX-ACCESS read-only
			STATUS current
			  DESCRIPTION
				"Controller location"
			::= { transferswitch 124 } 


    -- 1.3.6.1.4.1.7777.1.2.1.125
    external_feature_5_enabled  OBJECT-TYPE
			SYNTAX Integer32
			MAX-ACCESS read-only
			STATUS current
			  DESCRIPTION
				"External Feature 5 enabled"
			::= { transferswitch 125 } 
			
	-- 1.3.6.1.4.1.7777.1.2.1.126
    external_feature_34_enabled  OBJECT-TYPE
			SYNTAX Integer32
			MAX-ACCESS read-only
			STATUS current
			  DESCRIPTION
				"External Feature 34 enabled"
			::= { transferswitch 126 } 
			
	-- 1.3.6.1.4.1.7777.1.2.1.127
    inphase_filter_enabled  OBJECT-TYPE
			SYNTAX Integer32
			MAX-ACCESS read-only
			STATUS current
			  DESCRIPTION
				"In-phase filter enabled"
			::= { transferswitch 127 }		
	
	-- 1.3.6.1.4.1.7777.1.2.1.128
    current_sensing_option_installed  OBJECT-TYPE
			SYNTAX Integer32
			MAX-ACCESS read-only
			STATUS current
			  DESCRIPTION
				"Current sensing option installed"
			::= { transferswitch 128 }		
	

    -- 1.3.6.1.4.1.7777.1.2.1.129
    advanced_11C_option_installed  OBJECT-TYPE
			SYNTAX Integer32
			MAX-ACCESS read-only
			STATUS current
			  DESCRIPTION
				"Advanced 11C option Installed"
			::= { transferswitch 129 }		


    -- 1.3.6.1.4.1.7777.1.2.1.130
    event_log_option_installed  OBJECT-TYPE
			SYNTAX Integer32
			MAX-ACCESS read-only
			STATUS current
			  DESCRIPTION
				"Event log option Installed"
			::= { transferswitch 130 }	

    -- 1.3.6.1.4.1.7777.1.2.1.131
    rs485_communication_option_installed  OBJECT-TYPE
			SYNTAX Integer32
			MAX-ACCESS read-only
			STATUS current
			  DESCRIPTION
				"RS485 communication option Installed"
			::= { transferswitch 131 }	
    
	
	
	-- 1.3.6.1.4.1.7777.1.2.1.132
    op1_common_alarm_option_installed  OBJECT-TYPE
			SYNTAX Integer32
			MAX-ACCESS read-only
			STATUS current
			  DESCRIPTION
				"OP1 common alarm option Installed"
			::= { transferswitch 132 }	
	
	
	-- 1.3.6.1.4.1.7777.1.2.1.133
    total_time_load_connected_to_normal_high_word  OBJECT-TYPE
			SYNTAX Integer32
			MAX-ACCESS read-only
			STATUS current
			  DESCRIPTION
				"Total time load connected to normal (high word)"
			::= { transferswitch 133 }	
	
	-- 1.3.6.1.4.1.7777.1.2.1.134
    total_time_load_connected_to_normal_low_word  OBJECT-TYPE
			SYNTAX Integer32
			MAX-ACCESS read-only
			STATUS current
			  DESCRIPTION
				"Total time load connected to normal (low word)"
			::= { transferswitch 134 }	
	
	
	-- 1.3.6.1.4.1.7777.1.2.1.135
    total_time_load_connected_to_emergency_high_word  OBJECT-TYPE
			SYNTAX Integer32
			MAX-ACCESS read-only
			STATUS current
			  DESCRIPTION
				"Total time load connected to emergency (high word)"
			::= { transferswitch 135 }	
	
	
	-- 1.3.6.1.4.1.7777.1.2.1.136
    total_time_load_connected_to_emergency_low_word  OBJECT-TYPE
			SYNTAX Integer32
			MAX-ACCESS read-only
			STATUS current
			  DESCRIPTION
				"Total time load connected to emergency (low word)"
			::= { transferswitch 136 }	
	
	-- 1.3.6.1.4.1.7777.1.2.1.137
    rs485_port_address  OBJECT-TYPE
			SYNTAX Integer32
			MAX-ACCESS read-only
			STATUS current
			  DESCRIPTION
				"RS-485 port address"
			::= { transferswitch 137 }	
	
	-- 1.3.6.1.4.1.7777.1.2.1.138
    rs485_port_baud_rate  OBJECT-TYPE
			SYNTAX Integer32
			MAX-ACCESS read-only
			STATUS current
			  DESCRIPTION
				"RS-485 port baud rate"
			::= { transferswitch 138 }	
	
	
	-- 1.3.6.1.4.1.7777.1.2.1.139
    rs485_port_protocol  OBJECT-TYPE
			SYNTAX Integer32
			MAX-ACCESS read-only
			STATUS current
			  DESCRIPTION
				"RS-485 port protocol"
			::= { transferswitch 139 }	
			
			
	-- 1.3.6.1.4.1.7777.1.2.1.140
    emulate_group_1  OBJECT-TYPE
			SYNTAX Integer32
			MAX-ACCESS read-only
			STATUS current
			  DESCRIPTION
				"Emulate Group 1"
			::= { transferswitch 140 }			
			
			
	-- 1.3.6.1.4.1.7777.1.2.1.141
    dtts_load_disconnect_recovery_mode_manual_or_auto  OBJECT-TYPE
			SYNTAX Integer32
			MAX-ACCESS read-only
			STATUS current
			  DESCRIPTION
				"DTTS load disconnect recovery mode - manual or auto"
			::= { transferswitch 141 }			
			
			
	-- 1.3.6.1.4.1.7777.1.2.1.142
    timer_2B_transfer_N_to_E_on_test_time_delay  OBJECT-TYPE
			SYNTAX Integer32
			MAX-ACCESS read-only
			STATUS current
			  DESCRIPTION
				"Timer 2B transfer N to E on test time delay"
			::= { transferswitch 142 }			
			
			
	-- 1.3.6.1.4.1.7777.1.2.1.143
    inphase_monitor_time_delay  OBJECT-TYPE
			SYNTAX Integer32
			MAX-ACCESS read-only
			STATUS current
			  DESCRIPTION
				"Inphase monitor time delay"
			::= { transferswitch 143 }			
			
	-- 1.3.6.1.4.1.7777.1.2.1.144
    ats_total_transfer_time_in_10th_seconds  OBJECT-TYPE
			SYNTAX Integer32
			MAX-ACCESS read-only
			STATUS current
			  DESCRIPTION
				"ATS total transfer time in 10th seconds (real value in seconds requires division by 10)"
			::= { transferswitch 144 }					
		


    -- 1.3.6.1.4.1.7777.1.2.1.145
    dongle_installed  OBJECT-TYPE
			SYNTAX Integer32
			MAX-ACCESS read-only
			STATUS current
			  DESCRIPTION
				"Dongle installed"
			::= { transferswitch 145 }					
			


    -- 1.3.6.1.4.1.7777.1.2.1.146
    language_selection_setting  OBJECT-TYPE
			SYNTAX Integer32
			MAX-ACCESS read-only
			STATUS current
			  DESCRIPTION
				"Language selection setting"
			::= { transferswitch 146 }					
			


    -- 1.3.6.1.4.1.7777.1.2.1.147
    lcd_contrast_setting  OBJECT-TYPE
			SYNTAX Integer32
			MAX-ACCESS read-only
			STATUS current
			  DESCRIPTION
				"LCD contrast setting"
			::= { transferswitch 147 }					
			


    -- 1.3.6.1.4.1.7777.1.2.1.148
    controller_name  OBJECT-TYPE
			SYNTAX DisplayString (SIZE (0..21))
			MAX-ACCESS read-only
			STATUS current
			  DESCRIPTION
				"Controller name"
			::= { transferswitch 148 }					
			

    -- 1.3.6.1.4.1.7777.1.2.1.149
    boot_loader_version  OBJECT-TYPE
			SYNTAX DisplayString (SIZE (0..11))
			MAX-ACCESS read-only
			STATUS current
			  DESCRIPTION
				"Boot loader version"
			::= { transferswitch 149 }					
			

    -- 1.3.6.1.4.1.7777.1.2.1.150
    voltage_display_phase_label_selection  OBJECT-TYPE
			SYNTAX Integer32
			MAX-ACCESS read-only
			STATUS current
			  DESCRIPTION
				"Voltage display phase label selection"
			::= { transferswitch 150 }					
			


     -- 1.3.6.1.4.1.7777.1.2.1.151
    source_1_or_source_2_selection_for_different_english_format  OBJECT-TYPE
			SYNTAX Integer32
			MAX-ACCESS read-only
			STATUS current
			  DESCRIPTION
				"Source 1 or source 2 selection for different English format"
			::= { transferswitch 151 }		


     -- 1.3.6.1.4.1.7777.1.2.1.152
    external_battery_enabled  OBJECT-TYPE
			SYNTAX Integer32
			MAX-ACCESS read-only
			STATUS current
			  DESCRIPTION
				"External battery enabled"
			::= { transferswitch 152 }	



    -- 1.3.6.1.4.1.7777.1.2.1.153
    ts_data_gen_start_date  OBJECT-TYPE
			SYNTAX Integer32
			MAX-ACCESS read-only
			STATUS current
			  DESCRIPTION
				"TS data gen start date"
			::= { transferswitch 153 }	

    
	-- 1.3.6.1.4.1.7777.1.2.1.154
    ts_data_gen_start_month  OBJECT-TYPE
			SYNTAX Integer32
			MAX-ACCESS read-only
			STATUS current
			  DESCRIPTION
				"TS data gen start month"
			::= { transferswitch 154 }	
	
	-- 1.3.6.1.4.1.7777.1.2.1.155
    ts_data_gen_start_year  OBJECT-TYPE
			SYNTAX Integer32
			MAX-ACCESS read-only
			STATUS current
			  DESCRIPTION
				"TS data gen start year"
			::= { transferswitch 155 }	
	
	-- 1.3.6.1.4.1.7777.1.2.1.156
    ts_data_gen_start_hour  OBJECT-TYPE
			SYNTAX Integer32
			MAX-ACCESS read-only
			STATUS current
			  DESCRIPTION
				"TS data gen start hour"
			::= { transferswitch 156 }	
	
	-- 1.3.6.1.4.1.7777.1.2.1.157
    ts_data_gen_start_minutes  OBJECT-TYPE
			SYNTAX Integer32
			MAX-ACCESS read-only
			STATUS current
			  DESCRIPTION
				"TS data gen start minutes"
			::= { transferswitch 157 }	
			
	-- 1.3.6.1.4.1.7777.1.2.1.158
    ts_data_gen_start_seconds  OBJECT-TYPE
			SYNTAX Integer32
			MAX-ACCESS read-only
			STATUS current
			  DESCRIPTION
				"TS data gen start seconds"
			::= { transferswitch 158 }	
	
	-- 1.3.6.1.4.1.7777.1.2.1.159
    ts_data_gen_start_10th_of_seconds  OBJECT-TYPE
			SYNTAX Integer32
			MAX-ACCESS read-only
			STATUS current
			  DESCRIPTION
				"TS data gen start 10th of seconds"
			::= { transferswitch 159 }	
	
	-- 1.3.6.1.4.1.7777.1.2.1.160
    ts_data_gen_start_elapsed_time_in_seconds  OBJECT-TYPE
			SYNTAX Integer32
			MAX-ACCESS read-only
			STATUS current
			  DESCRIPTION
				"TS data gen start elapsed time in seconds"
			::= { transferswitch 160 }	

    -- 1.3.6.1.4.1.7777.1.2.1.161
    total_active_alarm_number  OBJECT-TYPE
			SYNTAX Integer32
			MAX-ACCESS read-only
			STATUS current
			  DESCRIPTION
				"Total active alarm number"
			::= { transferswitch 161 }	
    
	-- 1.3.6.1.4.1.7777.1.2.1.162
    load_shed_direction  OBJECT-TYPE
			SYNTAX Integer32
			MAX-ACCESS read-only
			STATUS current
			  DESCRIPTION
				"Load shed direction"
			::= { transferswitch 162 }	

			
    -- 1.3.6.1.4.1.7777.1.2.1.163
    dtts_only_load_shed_on_source_failure  OBJECT-TYPE
			SYNTAX Integer32
			MAX-ACCESS read-only
			STATUS current
			  DESCRIPTION
				"DTTS only - load shed on source failure"
			::= { transferswitch 163 }	

			
			
	-- 1.3.6.1.4.1.7777.1.2.1.164
    dtts_only_load_shed_on_request_f17  OBJECT-TYPE
			SYNTAX Integer32
			MAX-ACCESS read-only
			STATUS current
			  DESCRIPTION
				"DTTS only - load shed on request F17"
			::= { transferswitch 164 }	

	

    -- 1.3.6.1.4.1.7777.1.2.1.165
    normal_voltage_unbalance_dropout  OBJECT-TYPE
			SYNTAX Integer32
			MAX-ACCESS read-only
			STATUS current
			  DESCRIPTION
				"Normal voltage unbalance dropout.
				 Parameter settings display for 3 phase only"
			::= { transferswitch 165 }	
	
	-- 1.3.6.1.4.1.7777.1.2.1.166
    normal_voltage_unbalance_pickup  OBJECT-TYPE
			SYNTAX Integer32
			MAX-ACCESS read-only
			STATUS current
			  DESCRIPTION
				"Normal voltage unbalance pickup.
				 Parameter settings display for 3 phase only"
			::= { transferswitch 166 }	
	
	-- 1.3.6.1.4.1.7777.1.2.1.167
    emergency_voltage_unbalance_dropout  OBJECT-TYPE
			SYNTAX Integer32
			MAX-ACCESS read-only
			STATUS current
			  DESCRIPTION
				"Emergency voltage unbalance dropout.
				Parameter settings display for 3 phase only"
			::= { transferswitch 167 }	
			
			
	-- 1.3.6.1.4.1.7777.1.2.1.168
    emergency_voltage_unbalance_pickup  OBJECT-TYPE
			SYNTAX Integer32
			MAX-ACCESS read-only
			STATUS current
			  DESCRIPTION
				"Emergency voltage unbalance pickup.
				 Parameter settings display for 3 phase only"
			::= { transferswitch 168 }	


	
-- transfer switch end

        -- 1.3.6.1.4.1.7777.1.2.2.1
		dpmNormalDPMName OBJECT-TYPE
			SYNTAX DisplayString (SIZE (0..128))
			MAX-ACCESS read-only
			STATUS current
			DESCRIPTION
				"Normal DPM name."
			::= { dpmNormal 1 }


		-- 1.3.6.1.4.1.7777.1.2.2.2
		dpmNormalDPMLoca OBJECT-TYPE
			SYNTAX DisplayString (SIZE (0..128))
			MAX-ACCESS read-only
			STATUS current
			DESCRIPTION
				"Normal DPM Location."
			::= { dpmNormal 2 }


		-- 1.3.6.1.4.1.7777.1.2.2.3
		dpmNormalNominalVoltage OBJECT-TYPE
			SYNTAX Integer32
			MAX-ACCESS read-only
			STATUS current
			DESCRIPTION
				"Normal Nominal Voltage."
			::= { dpmNormal 3 }


		-- 1.3.6.1.4.1.7777.1.2.2.4
		dpmNormalNominalCurrent OBJECT-TYPE
			SYNTAX Integer32
			MAX-ACCESS read-only
			STATUS current
			DESCRIPTION
				"Normal Nominal Current."
			::= { dpmNormal 4 }


		-- 1.3.6.1.4.1.7777.1.2.2.5
		dpmNormalInstantaneousDemandKwMW OBJECT-TYPE
			SYNTAX Integer32
			MAX-ACCESS read-only
			STATUS current
			DESCRIPTION
				"Normal Instantaneous Demand kW MW"
			::= { dpmNormal 5 }


		-- 1.3.6.1.4.1.7777.1.2.2.6
		dpmNormalInstantaneousDemandDate OBJECT-TYPE
			SYNTAX DisplayString (SIZE (0..128))
			MAX-ACCESS read-only
			STATUS current
			DESCRIPTION
				"Demand Date."
			::= { dpmNormal 6 }


		-- 1.3.6.1.4.1.7777.1.2.2.7
		dpmNormalInstantaneousDemandTime OBJECT-TYPE
			SYNTAX DisplayString (SIZE (0..128))
			MAX-ACCESS read-only
			STATUS current
			DESCRIPTION
				"Demand Time."
			::= { dpmNormal 7 }


		-- 1.3.6.1.4.1.7777.1.2.2.8
		dpmNormalBlockDemandforFullHouInkW OBJECT-TYPE
			SYNTAX Integer32
			MAX-ACCESS read-only
			STATUS current
			DESCRIPTION
				"Block Demand for Full Hou In kW."
			::= { dpmNormal 8 }


		-- 1.3.6.1.4.1.7777.1.2.2.9
		dpmNormalBlockDemandforFullDayInkW OBJECT-TYPE
			SYNTAX Integer32
			MAX-ACCESS read-only
			STATUS current
			DESCRIPTION
				"Block Demand for Full Day In kW."
			::= { dpmNormal 9 }

		-- 1.3.6.1.4.1.7777.1.2.2.10
		dpmNormalBlockDemandforFullMonthInKW OBJECT-TYPE
			SYNTAX Integer32
			MAX-ACCESS read-only
			STATUS current
			DESCRIPTION
				"Block Demand for Full Month In kW."
			::= { dpmNormal 10 }

		-- 1.3.6.1.4.1.7777.1.2.2.11
		dpmNormalBlockDemandforFullYear OBJECT-TYPE
			SYNTAX Integer32
			MAX-ACCESS read-only
			STATUS current
			DESCRIPTION
				"Block Demand for Full Year In kW."
			::= { dpmNormal 11 }

		-- 1.3.6.1.4.1.7777.1.2.2.12
		dpmNormalCurrentThdA OBJECT-TYPE
			SYNTAX Integer32
			MAX-ACCESS read-only
			STATUS current
			DESCRIPTION
				"Phase A THD Current.In percentage "
			::= { dpmNormal 12 }

		-- 1.3.6.1.4.1.7777.1.2.2.13
		dpmNormalCurrentThdB OBJECT-TYPE
			SYNTAX Integer32
			MAX-ACCESS read-only
			STATUS current
			DESCRIPTION
				"Phase B THD Current.In percentage"
			::= { dpmNormal 13 }

		-- 1.3.6.1.4.1.7777.1.2.2.14
  		dpmNormalCurrentThdC OBJECT-TYPE
			SYNTAX Integer32
			MAX-ACCESS read-only
			STATUS current
			DESCRIPTION
				"Phase C THD Current.In percentage"
			::= { dpmNormal 14 }

		-- 1.3.6.1.4.1.7777.1.2.2.15
  		dpmNormalVoltageThdA OBJECT-TYPE
			SYNTAX Integer32
			MAX-ACCESS read-only
			STATUS current
			DESCRIPTION
				"Phase A THD Voltage.In percentage"
			::= { dpmNormal 15 }

		-- 1.3.6.1.4.1.7777.1.2.2.16
		dpmNormalVoltageThdB OBJECT-TYPE
			SYNTAX Integer32
			MAX-ACCESS read-only
			STATUS current
			DESCRIPTION
				"Phase B THD Voltage.In percentage"
			::= { dpmNormal 16 }


		-- 1.3.6.1.4.1.7777.1.2.2.17
		dpmNormalVoltageThdC OBJECT-TYPE
			SYNTAX Integer32
			MAX-ACCESS read-only
			STATUS current
			DESCRIPTION
				"Phase C THD Voltage.In percentage"
			::= { dpmNormal 17 }


		-- 1.3.6.1.4.1.7777.1.2.2.18
		dpmNormalVab OBJECT-TYPE
			SYNTAX Integer32
			MAX-ACCESS read-only
			STATUS current
			DESCRIPTION
				"Normal Vab Volatage."
			::= { dpmNormal 18 }

		-- 1.3.6.1.4.1.7777.1.2.2.19
		dpmNormalVbc OBJECT-TYPE
			SYNTAX Integer32
			MAX-ACCESS read-only
			STATUS current
			DESCRIPTION
				"Normal Vbc Volatage."
			::= { dpmNormal 19 }


		-- 1.3.6.1.4.1.7777.1.2.2.20
		dpmNormalVca OBJECT-TYPE
			SYNTAX Integer32
			MAX-ACCESS read-only
			STATUS current
			DESCRIPTION
				"Normal Vca Volatage."
			::= { dpmNormal 20 }

		-- 1.3.6.1.4.1.7777.1.2.2.21
		dpmNormalVolAverage OBJECT-TYPE
			SYNTAX Integer32
			MAX-ACCESS read-only
			STATUS current
			DESCRIPTION
				"Normal Vol Average."
			::= { dpmNormal 21 }

		-- 1.3.6.1.4.1.7777.1.2.2.22
		dpmNormalVolUnbal OBJECT-TYPE
			SYNTAX Integer32
			MAX-ACCESS read-only
			STATUS current
			DESCRIPTION
				"Normal Vol Unbal."
			::= { dpmNormal 22 }

		-- 1.3.6.1.4.1.7777.1.2.2.23
		dpmNormalVan OBJECT-TYPE
			SYNTAX Integer32
			MAX-ACCESS read-only
			STATUS current
			DESCRIPTION
				"Normal Vol Van."
			::= { dpmNormal 23 }


		-- 1.3.6.1.4.1.7777.1.2.2.24
		dpmNormalVbn OBJECT-TYPE
			SYNTAX Integer32
			MAX-ACCESS read-only
			STATUS current
			DESCRIPTION
				"Normal Vbn.."
			::= { dpmNormal 24 }


		-- 1.3.6.1.4.1.7777.1.2.2.25
		dpmNormalVcn OBJECT-TYPE
			SYNTAX Integer32
			MAX-ACCESS read-only
			STATUS current
			DESCRIPTION
				"Normal Vcn. "
			::= { dpmNormal 25 }


		-- 1.3.6.1.4.1.7777.1.2.2.26
		dpmNormalVavgneutral OBJECT-TYPE
			SYNTAX Integer32
			MAX-ACCESS read-only
			STATUS current
			DESCRIPTION
				"Normal Avg neutral Volatagae."
			::= { dpmNormal 26 }

		-- 1.3.6.1.4.1.7777.1.2.2.27
		dpmNormalFrequency OBJECT-TYPE
			SYNTAX Integer32
			MAX-ACCESS read-only
			STATUS current
			DESCRIPTION
				"Normal Frequency."
			::= { dpmNormal 27 }

		-- 1.3.6.1.4.1.7777.1.2.2.28
		dpmNormalPowerFactor OBJECT-TYPE
			SYNTAX Integer32
			MAX-ACCESS read-only
			STATUS current
			DESCRIPTION
				"Normal Power factor."
			::= { dpmNormal 28 }

		-- 1.3.6.1.4.1.7777.1.2.2.29
		dpmNormalCurPhaseA OBJECT-TYPE
			SYNTAX Integer32
			MAX-ACCESS read-only
			STATUS current
			DESCRIPTION
				"Normal Phase A Current."
			::= { dpmNormal 29 }

		-- 1.3.6.1.4.1.7777.1.2.2.30
		dpmNormalCurPhaseB OBJECT-TYPE
			SYNTAX Integer32
			MAX-ACCESS read-only
			STATUS current
			DESCRIPTION
				"Normal Phase B Current."
			::= { dpmNormal 30 }


		-- 1.3.6.1.4.1.7777.1.2.2.31
		dpmNormalCurPhaseC OBJECT-TYPE
			SYNTAX Integer32
			MAX-ACCESS read-only
			STATUS current
			DESCRIPTION
				"Normal Phase C Current."
			::= { dpmNormal 31 }

		-- 1.3.6.1.4.1.7777.1.2.2.32
		dpmNormalPhaseCurAvg OBJECT-TYPE
			SYNTAX Integer32
			MAX-ACCESS read-only
			STATUS current
			DESCRIPTION
				"Normal Phase Current aVG."
			::= { dpmNormal 32 }

		-- 1.3.6.1.4.1.7777.1.2.2.33
		dpmNormalPhaseCurUnbalancecePercentage OBJECT-TYPE
			SYNTAX Integer32
			MAX-ACCESS read-only
			STATUS current
			DESCRIPTION
				"Normal Phase Cur Unbalancece Percentage."
			::= { dpmNormal 33 }

		-- 1.3.6.1.4.1.7777.1.2.2.34
		dpmNormalRealTotalPower OBJECT-TYPE
			SYNTAX Integer32
			MAX-ACCESS read-only
			STATUS current
			DESCRIPTION
				"Normal Real Total power factor."
			::= { dpmNormal 34 }

		-- 1.3.6.1.4.1.7777.1.2.2.35
		dpmNormalReactiveTotalPower OBJECT-TYPE
			SYNTAX Integer32
			MAX-ACCESS read-only
			STATUS current
			DESCRIPTION
				"Normal Reactive Total power."
			::= { dpmNormal 35 }

		-- 1.3.6.1.4.1.7777.1.2.2.36
  		dpmNormalApparentTotalPower OBJECT-TYPE
			SYNTAX Integer32
			MAX-ACCESS read-only
			STATUS current
			DESCRIPTION
				"Normal AApparent Total power."
			::= { dpmNormal 36 }

		-- 1.3.6.1.4.1.7777.1.2.2.37
  		dpmNormalNetActiveEnergy OBJECT-TYPE
			SYNTAX Integer32
			MAX-ACCESS read-only
			STATUS current
			DESCRIPTION
				"Normal Net Active Energy."
			::= { dpmNormal 37 }


		-- 1.3.6.1.4.1.7777.1.2.2.39
		dpmNormalFirmwareVersion OBJECT-TYPE
			SYNTAX DisplayString (SIZE (0..128))
			MAX-ACCESS read-only
			STATUS current
			DESCRIPTION
				"Normal DPM Firmware ."
			::= { dpmNormal 38 }

--Emergency
        -- 1.3.6.1.4.1.7777.1.2.3.1
		dpmEmergencyDPMName OBJECT-TYPE
			SYNTAX DisplayString (SIZE (0..128))
			MAX-ACCESS read-only
			STATUS current
			DESCRIPTION
				"Emergency DPM name."
			::= { dpmEmergency 1 }


		-- 1.3.6.1.4.1.7777.1.2.3.2
		dpmEmergencyDPMLoca OBJECT-TYPE
			SYNTAX DisplayString (SIZE (0..128))
			MAX-ACCESS read-only
			STATUS current
			DESCRIPTION
				"Emergency DPM Location."
			::= { dpmEmergency 2 }


		-- 1.3.6.1.4.1.7777.1.2.3.3
		dpmEmergencyNominalVoltage OBJECT-TYPE
			SYNTAX Integer32
			MAX-ACCESS read-only
			STATUS current
			DESCRIPTION
				"Emergency Nominal Voltage."
			::= { dpmEmergency 3 }


		-- 1.3.6.1.4.1.7777.1.2.3.4
		dpmEmergencyNominalCurrent OBJECT-TYPE
			SYNTAX Integer32
			MAX-ACCESS read-only
			STATUS current
			DESCRIPTION
				"Emergency Nominal Current."
			::= { dpmEmergency 4 }


		-- 1.3.6.1.4.1.7777.1.2.3.5
		dpmEmergencyInstantaneousDemandKwMW OBJECT-TYPE
			SYNTAX Integer32
			MAX-ACCESS read-only
			STATUS current
			DESCRIPTION
				"Emergency Instantaneous Demand Kw MW"
			::= { dpmEmergency 5 }


		-- 1.3.6.1.4.1.7777.1.2.3.6
		dpmEmergencyInstantaneousDemandDate OBJECT-TYPE
			SYNTAX DisplayString (SIZE (0..128))
			MAX-ACCESS read-only
			STATUS current
			DESCRIPTION
				"Demand Date."
			::= { dpmEmergency 6 }


		-- 1.3.6.1.4.1.7777.1.2.3.7
		dpmEmergencyInstantaneousDemandTime OBJECT-TYPE
			SYNTAX DisplayString (SIZE (0..128))
			MAX-ACCESS read-only
			STATUS current
			DESCRIPTION
				"Demand Time."
			::= { dpmEmergency 7 }


		-- 1.3.6.1.4.1.7777.1.2.3.8
		dpmEmergencyBlockDemandforFullHouInkW OBJECT-TYPE
			SYNTAX Integer32
			MAX-ACCESS read-only
			STATUS current
			DESCRIPTION
				"Block Demand for Full Hou In kW."
			::= { dpmEmergency 8 }


		-- 1.3.6.1.4.1.7777.1.2.3.9
		dpmEmergencyBlockDemandforFullDayInkW OBJECT-TYPE
			SYNTAX Integer32
			MAX-ACCESS read-only
			STATUS current
			DESCRIPTION
				"Block Demand for Full Day In kW."
			::= { dpmEmergency 9 }

		-- 1.3.6.1.4.1.7777.1.2.3.10
		dpmEmergencyBlockDemandforFullMonthInKW OBJECT-TYPE
			SYNTAX Integer32
			MAX-ACCESS read-only
			STATUS current
			DESCRIPTION
				"Block Demand for Full Month In kW."
			::= { dpmEmergency 10 }

		-- 1.3.6.1.4.1.7777.1.2.3.11
		dpmEmergencyBlockDemandforFullYear OBJECT-TYPE
			SYNTAX Integer32
			MAX-ACCESS read-only
			STATUS current
			DESCRIPTION
				"Block Demand for Full Yearin kW"
			::= { dpmEmergency 11 }

		-- 1.3.6.1.4.1.7777.1.2.3.12
		dpmEmergencyCurrentThdA OBJECT-TYPE
			SYNTAX Integer32
			MAX-ACCESS read-only
			STATUS current
			DESCRIPTION
				"Phase A THD Current.In percentage"
			::= { dpmEmergency 12 }

		-- 1.3.6.1.4.1.7777.1.2.3.13
		dpmEmergencyCurrentThdB OBJECT-TYPE
			SYNTAX Integer32
			MAX-ACCESS read-only
			STATUS current
			DESCRIPTION
				"Phase B THD Current.In percentage"
			::= { dpmEmergency 13 }

		-- 1.3.6.1.4.1.7777.1.2.3.14
  		dpmEmergencyCurrentThdC OBJECT-TYPE
			SYNTAX Integer32
			MAX-ACCESS read-only
			STATUS current
			DESCRIPTION
				"Phase C THD Current.In percentage"
			::= { dpmEmergency 14 }

		-- 1.3.6.1.4.1.7777.1.2.3.15
  		dpmEmergencyVoltageThdA OBJECT-TYPE
			SYNTAX Integer32
			MAX-ACCESS read-only
			STATUS current
			DESCRIPTION
				"Phase A THD Voltage.In percentage"
			::= { dpmEmergency 15 }

		-- 1.3.6.1.4.1.7777.1.2.3.16
		dpmEmergencyVoltageThdB OBJECT-TYPE
			SYNTAX Integer32
			MAX-ACCESS read-only
			STATUS current
			DESCRIPTION
				"Phase B THD Voltage.In percentage"
			::= { dpmEmergency 16 }


		-- 1.3.6.1.4.1.7777.1.2.3.17
		dpmEmergencyVoltageThdC OBJECT-TYPE
			SYNTAX Integer32
			MAX-ACCESS read-only
			STATUS current
			DESCRIPTION
				"Phase C THD Voltage.In percentage"
			::= { dpmEmergency 17 }


		-- 1.3.6.1.4.1.7777.1.2.3.18
		dpmEmergencyVab OBJECT-TYPE
			SYNTAX Integer32
			MAX-ACCESS read-only
			STATUS current
			DESCRIPTION
				"Emergency Vab Volatage."
			::= { dpmEmergency 18 }

		-- 1.3.6.1.4.1.7777.1.2.3.19
		dpmEmergencyVbc OBJECT-TYPE
			SYNTAX Integer32
			MAX-ACCESS read-only
			STATUS current
			DESCRIPTION
				"Emergency Vbc Volatage."
			::= { dpmEmergency 19 }


		-- 1.3.6.1.4.1.7777.1.2.3.20
		dpmEmergencyVca OBJECT-TYPE
			SYNTAX Integer32
			MAX-ACCESS read-only
			STATUS current
			DESCRIPTION
				"Emergency Vca Volatage."
			::= { dpmEmergency 20 }

		-- 1.3.6.1.4.1.7777.1.2.3.21
		dpmEmergencyVolAverage OBJECT-TYPE
			SYNTAX Integer32
			MAX-ACCESS read-only
			STATUS current
			DESCRIPTION
				"Emergency Vol Average."
			::= { dpmEmergency 21 }

		-- 1.3.6.1.4.1.7777.1.2.3.22
		dpmEmergencyVolUnbal OBJECT-TYPE
			SYNTAX Integer32
			MAX-ACCESS read-only
			STATUS current
			DESCRIPTION
				"Emergency Vol Unbal."
			::= { dpmEmergency 22 }

		-- 1.3.6.1.4.1.7777.1.2.3.23
		dpmEmergencyVan OBJECT-TYPE
			SYNTAX Integer32
			MAX-ACCESS read-only
			STATUS current
			DESCRIPTION
				"Emergency Vol Van."
			::= { dpmEmergency 23 }


		-- 1.3.6.1.4.1.7777.1.2.3.24
		dpmEmergencyVbn OBJECT-TYPE
			SYNTAX Integer32
			MAX-ACCESS read-only
			STATUS current
			DESCRIPTION
				"Emergency Vbn.."
			::= { dpmEmergency 24 }


		-- 1.3.6.1.4.1.7777.1.2.3.25
		dpmEmergencyVcn OBJECT-TYPE
			SYNTAX Integer32
			MAX-ACCESS read-only
			STATUS current
			DESCRIPTION
				"Emergency Vcn. "
			::= { dpmEmergency 25 }


		-- 1.3.6.1.4.1.7777.1.2.3.26
		dpmEmergencyVavgneutral OBJECT-TYPE
			SYNTAX Integer32
			MAX-ACCESS read-only
			STATUS current
			DESCRIPTION
				"Emergency Avg neutral Volatagae."
			::= { dpmEmergency 26 }

		-- 1.3.6.1.4.1.7777.1.2.3.27
		dpmEmergencyFrequency OBJECT-TYPE
			SYNTAX Integer32
			MAX-ACCESS read-only
			STATUS current
			DESCRIPTION
				"Emergency Frequency."
			::= { dpmEmergency 27 }

		-- 1.3.6.1.4.1.7777.1.2.3.28
		dpmEmergencyPowerFactor OBJECT-TYPE
			SYNTAX Integer32
			MAX-ACCESS read-only
			STATUS current
			DESCRIPTION
				"Emergency Power factor."
			::= { dpmEmergency 28 }

		-- 1.3.6.1.4.1.7777.1.2.3.29
		dpmEmergencyCurPhaseA OBJECT-TYPE
			SYNTAX Integer32
			MAX-ACCESS read-only
			STATUS current
			DESCRIPTION
				"Emergency Phase A Current."
			::= { dpmEmergency 29 }

		-- 1.3.6.1.4.1.7777.1.2.3.30
		dpmEmergencyCurPhaseB OBJECT-TYPE
			SYNTAX Integer32
			MAX-ACCESS read-only
			STATUS current
			DESCRIPTION
				"Emergency Phase B Current."
			::= { dpmEmergency 30 }


		-- 1.3.6.1.4.1.7777.1.2.3.31
		dpmEmergencyCurPhaseC OBJECT-TYPE
			SYNTAX Integer32
			MAX-ACCESS read-only
			STATUS current
			DESCRIPTION
				"Emergency Phase C Current."
			::= { dpmEmergency 31 }

		-- 1.3.6.1.4.1.7777.1.2.3.32
		dpmEmergencyPhaseCurAvg OBJECT-TYPE
			SYNTAX Integer32
			MAX-ACCESS read-only
			STATUS current
			DESCRIPTION
				"Emergency Phase Current aVG."
			::= { dpmEmergency 32 }

		-- 1.3.6.1.4.1.7777.1.2.3.33
		dpmEmergencyPhaseCurUnbalancecePercentage OBJECT-TYPE
			SYNTAX Integer32
			MAX-ACCESS read-only
			STATUS current
			DESCRIPTION
				"Emergency Phase Cur Unbalancece Percentage."
			::= { dpmEmergency 33 }

		-- 1.3.6.1.4.1.7777.1.2.3.34
		dpmEmergencyRealTotalPower OBJECT-TYPE
			SYNTAX Integer32
			MAX-ACCESS read-only
			STATUS current
			DESCRIPTION
				"Emergency Real Total power factor."
			::= { dpmEmergency 34 }

		-- 1.3.6.1.4.1.7777.1.2.3.35
		dpmEmergencyReactiveTotalPower OBJECT-TYPE
			SYNTAX Integer32
			MAX-ACCESS read-only
			STATUS current
			DESCRIPTION
				"Emergency Reactive Total power."
			::= { dpmEmergency 35 }

		-- 1.3.6.1.4.1.7777.1.2.3.36
  		dpmEmergencyApparentTotalPower OBJECT-TYPE
			SYNTAX Integer32
			MAX-ACCESS read-only
			STATUS current
			DESCRIPTION
				"Emergency AApparent Total power."
			::= { dpmEmergency 36 }

		-- 1.3.6.1.4.1.7777.1.2.3.37
  		dpmEmergencyNetActiveEnergy OBJECT-TYPE
			SYNTAX Integer32
			MAX-ACCESS read-only
			STATUS current
			DESCRIPTION
				"Emergency Net Active Energy."
			::= { dpmEmergency 37 }


		-- 1.3.6.1.4.1.7777.1.2.3.39
		dpmEmergencyFirmwareVersion OBJECT-TYPE
			SYNTAX DisplayString (SIZE (0..128))
			MAX-ACCESS read-only
			STATUS current
			DESCRIPTION
				"Emergency DPM Firmware ."
			::= { dpmEmergency 38 }

--Load

        -- 1.3.6.1.4.1.7777.1.2.4.1
		dpmLoadDPMName OBJECT-TYPE
			SYNTAX DisplayString (SIZE (0..128))
			MAX-ACCESS read-only
			STATUS current
			DESCRIPTION
				"Load DPM name."
			::= { dpmLoad 1 }


		-- 1.3.6.1.4.1.7777.1.2.4.2
		dpmLoadDPMLoca OBJECT-TYPE
			SYNTAX DisplayString (SIZE (0..128))
			MAX-ACCESS read-only
			STATUS current
			DESCRIPTION
				"Load DPM Location."
			::= { dpmLoad 2 }


		-- 1.3.6.1.4.1.7777.1.2.4.3
		dpmLoadNominalVoltage OBJECT-TYPE
			SYNTAX Integer32
			MAX-ACCESS read-only
			STATUS current
			DESCRIPTION
				"Load Nominal Voltage."
			::= { dpmLoad 3 }


		-- 1.3.6.1.4.1.7777.1.2.4.4
		dpmLoadNominalCurrent OBJECT-TYPE
			SYNTAX Integer32
			MAX-ACCESS read-only
			STATUS current
			DESCRIPTION
				"Load Nominal Current."
			::= { dpmLoad 4 }


		-- 1.3.6.1.4.1.7777.1.2.4.5
		dpmLoadInstantaneousDemandKwMW OBJECT-TYPE
			SYNTAX Integer32
			MAX-ACCESS read-only
			STATUS current
			DESCRIPTION
				"Load Instantaneous Demand Kw MW"
			::= { dpmLoad 5 }


		-- 1.3.6.1.4.1.7777.1.2.4.6
		dpmLoadInstantaneousDemandDate OBJECT-TYPE
			SYNTAX DisplayString (SIZE (0..128))
			MAX-ACCESS read-only
			STATUS current
			DESCRIPTION
				"Demand Date."
			::= { dpmLoad 6 }


		-- 1.3.6.1.4.1.7777.1.2.4.7
		dpmLoadInstantaneousDemandTime OBJECT-TYPE
			SYNTAX DisplayString (SIZE (0..128))
			MAX-ACCESS read-only
			STATUS current
			DESCRIPTION
				"Demand Time."
			::= { dpmLoad 7 }


		-- 1.3.6.1.4.1.7777.1.2.4.8
		dpmLoadBlockDemandforFullHouInkW OBJECT-TYPE
			SYNTAX Integer32
			MAX-ACCESS read-only
			STATUS current
			DESCRIPTION
				"Block Demand for Full Hou In kW."
			::= { dpmLoad 8 }


		-- 1.3.6.1.4.1.7777.1.2.4.9
		dpmLoadBlockDemandforFullDayInkW OBJECT-TYPE
			SYNTAX Integer32
			MAX-ACCESS read-only
			STATUS current
			DESCRIPTION
				"Block Demand for Full Day In kW."
			::= { dpmLoad 9 }

		-- 1.3.6.1.4.1.7777.1.2.4.10
		dpmLoadBlockDemandforFullMonthInKW OBJECT-TYPE
			SYNTAX Integer32
			MAX-ACCESS read-only
			STATUS current
			DESCRIPTION
				"Block Demand for Full Month In kW."
			::= { dpmLoad 10 }

		-- 1.3.6.1.4.1.7777.1.2.4.11
		dpmLoadBlockDemandforFullYear OBJECT-TYPE
			SYNTAX Integer32
			MAX-ACCESS read-only
			STATUS current
			DESCRIPTION
				"Block Demand for Full Yearin kW"
			::= { dpmLoad 11 }

		-- 1.3.6.1.4.1.7777.1.2.4.12
		dpmLoadCurrentThdA OBJECT-TYPE
			SYNTAX Integer32
			MAX-ACCESS read-only
			STATUS current
			DESCRIPTION
				"Phase A THD Current.In percentage"
			::= { dpmLoad 12 }

		-- 1.3.6.1.4.1.7777.1.2.4.13
		dpmLoadCurrentThdB OBJECT-TYPE
			SYNTAX Integer32
			MAX-ACCESS read-only
			STATUS current
			DESCRIPTION
				"Phase B THD Current.In percentage"
			::= { dpmLoad 13 }

		-- 1.3.6.1.4.1.7777.1.2.4.14
  		dpmLoadCurrentThdC OBJECT-TYPE
			SYNTAX Integer32
			MAX-ACCESS read-only
			STATUS current
			DESCRIPTION
				"Phase C THD Current.In percentage"
			::= { dpmLoad 14 }

		-- 1.3.6.1.4.1.7777.1.2.4.15
  		dpmLoadVoltageThdA OBJECT-TYPE
			SYNTAX Integer32
			MAX-ACCESS read-only
			STATUS current
			DESCRIPTION
				"Phase A THD Voltage.In percentage"
			::= { dpmLoad 15 }

		-- 1.3.6.1.4.1.7777.1.2.4.16
		dpmLoadVoltageThdB OBJECT-TYPE
			SYNTAX Integer32
			MAX-ACCESS read-only
			STATUS current
			DESCRIPTION
				"Phase B THD Voltage.In percentage"
			::= { dpmLoad 16 }


		-- 1.3.6.1.4.1.7777.1.2.4.17
		dpmLoadVoltageThdC OBJECT-TYPE
			SYNTAX Integer32
			MAX-ACCESS read-only
			STATUS current
			DESCRIPTION
				"Phase C THD Voltage.In percentage"
			::= { dpmLoad 17 }


		-- 1.3.6.1.4.1.7777.1.2.4.18
		dpmLoadVab OBJECT-TYPE
			SYNTAX Integer32
			MAX-ACCESS read-only
			STATUS current
			DESCRIPTION
				"Load Vab Volatage."
			::= { dpmLoad 18 }

		-- 1.3.6.1.4.1.7777.1.2.4.19
		dpmLoadVbc OBJECT-TYPE
			SYNTAX Integer32
			MAX-ACCESS read-only
			STATUS current
			DESCRIPTION
				"Load Vbc Volatage."
			::= { dpmLoad 19 }


		-- 1.3.6.1.4.1.7777.1.2.4.20
		dpmLoadVca OBJECT-TYPE
			SYNTAX Integer32
			MAX-ACCESS read-only
			STATUS current
			DESCRIPTION
				"Load Vca Volatage."
			::= { dpmLoad 20 }

		-- 1.3.6.1.4.1.7777.1.2.4.21
		dpmLoadVolAverage OBJECT-TYPE
			SYNTAX Integer32
			MAX-ACCESS read-only
			STATUS current
			DESCRIPTION
				"Load Vol Average."
			::= { dpmLoad 21 }

		-- 1.3.6.1.4.1.7777.1.2.4.22
		dpmLoadVolUnbal OBJECT-TYPE
			SYNTAX Integer32
			MAX-ACCESS read-only
			STATUS current
			DESCRIPTION
				"Load Vol Unbal."
			::= { dpmLoad 22 }

		-- 1.3.6.1.4.1.7777.1.2.4.23
		dpmLoadVan OBJECT-TYPE
			SYNTAX Integer32
			MAX-ACCESS read-only
			STATUS current
			DESCRIPTION
				"Load Vol Van."
			::= { dpmLoad 23 }


		-- 1.3.6.1.4.1.7777.1.2.4.24
		dpmLoadVbn OBJECT-TYPE
			SYNTAX Integer32
			MAX-ACCESS read-only
			STATUS current
			DESCRIPTION
				"Load Vbn.."
			::= { dpmLoad 24 }


		-- 1.3.6.1.4.1.7777.1.2.4.25
		dpmLoadVcn OBJECT-TYPE
			SYNTAX Integer32
			MAX-ACCESS read-only
			STATUS current
			DESCRIPTION
				"Load Vcn. "
			::= { dpmLoad 25 }


		-- 1.3.6.1.4.1.7777.1.2.4.26
		dpmLoadVavgneutral OBJECT-TYPE
			SYNTAX Integer32
			MAX-ACCESS read-only
			STATUS current
			DESCRIPTION
				"Load Avg neutral Volatagae."
			::= { dpmLoad 26 }

		-- 1.3.6.1.4.1.7777.1.2.4.27
		dpmLoadFrequency OBJECT-TYPE
			SYNTAX Integer32
			MAX-ACCESS read-only
			STATUS current
			DESCRIPTION
				"Load Frequency."
			::= { dpmLoad 27 }

		-- 1.3.6.1.4.1.7777.1.2.4.28
		dpmLoadPowerFactor OBJECT-TYPE
			SYNTAX Integer32
			MAX-ACCESS read-only
			STATUS current
			DESCRIPTION
				"Load Power factor."
			::= { dpmLoad 28 }

		-- 1.3.6.1.4.1.7777.1.2.4.29
		dpmLoadCurPhaseA OBJECT-TYPE
			SYNTAX Integer32
			MAX-ACCESS read-only
			STATUS current
			DESCRIPTION
				"Load Phase A Current."
			::= { dpmLoad 29 }

		-- 1.3.6.1.4.1.7777.1.2.4.30
		dpmLoadCurPhaseB OBJECT-TYPE
			SYNTAX Integer32
			MAX-ACCESS read-only
			STATUS current
			DESCRIPTION
				"Load Phase B Current."
			::= { dpmLoad 30 }


		-- 1.3.6.1.4.1.7777.1.2.4.31
		dpmLoadCurPhaseC OBJECT-TYPE
			SYNTAX Integer32
			MAX-ACCESS read-only
			STATUS current
			DESCRIPTION
				"Load Phase C Current."
			::= { dpmLoad 31 }

		-- 1.3.6.1.4.1.7777.1.2.4.32
		dpmLoadPhaseCurAvg OBJECT-TYPE
			SYNTAX Integer32
			MAX-ACCESS read-only
			STATUS current
			DESCRIPTION
				"Load Phase Current aVG."
			::= { dpmLoad 32 }

		-- 1.3.6.1.4.1.7777.1.2.4.33
		dpmLoadPhaseCurUnbalancecePercentage OBJECT-TYPE
			SYNTAX Integer32
			MAX-ACCESS read-only
			STATUS current
			DESCRIPTION
				"Load Phase Cur Unbalancece Percentage."
			::= { dpmLoad 33 }

		-- 1.3.6.1.4.1.7777.1.2.4.34
		dpmLoadRealTotalPower OBJECT-TYPE
			SYNTAX Integer32
			MAX-ACCESS read-only
			STATUS current
			DESCRIPTION
				"Load Real Total power factor."
			::= { dpmLoad 34 }

		-- 1.3.6.1.4.1.7777.1.2.4.35
		dpmLoadReactiveTotalPower OBJECT-TYPE
			SYNTAX Integer32
			MAX-ACCESS read-only
			STATUS current
			DESCRIPTION
				"Load Reactive Total power."
			::= { dpmLoad 35 }

		-- 1.3.6.1.4.1.7777.1.2.4.36
  		dpmLoadApparentTotalPower OBJECT-TYPE
			SYNTAX Integer32
			MAX-ACCESS read-only
			STATUS current
			DESCRIPTION
				"Load AApparent Total power."
			::= { dpmLoad 36 }

		-- 1.3.6.1.4.1.7777.1.2.4.37
  		dpmLoadNetActiveEnergy OBJECT-TYPE
			SYNTAX Integer32
			MAX-ACCESS read-only
			STATUS current
			DESCRIPTION
				"Load Net Active Energy."
			::= { dpmLoad 37 }


		-- 1.3.6.1.4.1.7777.1.2.4.39
		dpmLoadFirmwareVersion OBJECT-TYPE
			SYNTAX DisplayString (SIZE (0..128))
			MAX-ACCESS read-only
			STATUS current
			DESCRIPTION
				"Load DPM Firmware."
			::= { dpmLoad 38 }


--Other

        -- 1.3.6.1.4.1.7777.1.2.5.1
		dpmOtherDPMName OBJECT-TYPE
			SYNTAX DisplayString (SIZE (0..128))
			MAX-ACCESS read-only
			STATUS current
			DESCRIPTION
				"Other DPM name."
			::= { dpmOther 1 }


		-- 1.3.6.1.4.1.7777.1.2.5.2
		dpmOtherDPMLoca OBJECT-TYPE
			SYNTAX DisplayString (SIZE (0..128))
			MAX-ACCESS read-only
			STATUS current
			DESCRIPTION
				"Other DPM Location."
			::= { dpmOther 2 }


		-- 1.3.6.1.4.1.7777.1.2.5.3
		dpmOtherNominalVoltage OBJECT-TYPE
			SYNTAX Integer32
			MAX-ACCESS read-only
			STATUS current
			DESCRIPTION
				"Other Nominal Voltage."
			::= { dpmOther 3 }


		-- 1.3.6.1.4.1.7777.1.2.5.4
		dpmOtherNominalCurrent OBJECT-TYPE
			SYNTAX Integer32
			MAX-ACCESS read-only
			STATUS current
			DESCRIPTION
				"Other Nominal Current."
			::= { dpmOther 4 }


		-- 1.3.6.1.4.1.7777.1.2.5.5
		dpmOtherInstantaneousDemandKwMW OBJECT-TYPE
			SYNTAX Integer32
			MAX-ACCESS read-only
			STATUS current
			DESCRIPTION
				"Other Instantaneous Demand kw MW"
			::= { dpmOther 5 }


		-- 1.3.6.1.4.1.7777.1.2.5.6
		dpmOtherInstantaneousDemandDate OBJECT-TYPE
			SYNTAX DisplayString (SIZE (0..128))
			MAX-ACCESS read-only
			STATUS current
			DESCRIPTION
				"Demand Date."
			::= { dpmOther 6 }


		-- 1.3.6.1.4.1.7777.1.2.5.7
		dpmOtherInstantaneousDemandTime OBJECT-TYPE
			SYNTAX DisplayString (SIZE (0..128))
			MAX-ACCESS read-only
			STATUS current
			DESCRIPTION
				"Demand Time."
			::= { dpmOther 7 }


		-- 1.3.6.1.4.1.7777.1.2.5.8
		dpmOtherBlockDemandforFullHouInkW OBJECT-TYPE
			SYNTAX Integer32
			MAX-ACCESS read-only
			STATUS current
			DESCRIPTION
				"Block Demand for Full Hou In kW."
			::= { dpmOther 8 }


		-- 1.3.6.1.4.1.7777.1.2.5.9
		dpmOtherBlockDemandforFullDayInkW OBJECT-TYPE
			SYNTAX Integer32
			MAX-ACCESS read-only
			STATUS current
			DESCRIPTION
				"Block Demand for Full Day In kW."
			::= { dpmOther 9 }

		-- 1.3.6.1.4.1.7777.1.2.5.10
		dpmOtherBlockDemandforFullMonthInKW OBJECT-TYPE
			SYNTAX Integer32
			MAX-ACCESS read-only
			STATUS current
			DESCRIPTION
				"Block Demand for Full Month In kW."
			::= { dpmOther 10 }

		-- 1.3.6.1.4.1.7777.1.2.5.11
		dpmOtherBlockDemandforFullYear OBJECT-TYPE
			SYNTAX Integer32
			MAX-ACCESS read-only
			STATUS current
			DESCRIPTION
				"Block Demand for Full Year."
			::= { dpmOther 11 }

		-- 1.3.6.1.4.1.7777.1.2.5.12
		dpmOtherCurrentThdA OBJECT-TYPE
			SYNTAX Integer32
			MAX-ACCESS read-only
			STATUS current
			DESCRIPTION
				"Phase A THD Current.In percentage"
			::= { dpmOther 12 }

		-- 1.3.6.1.4.1.7777.1.2.5.13
		dpmOtherCurrentThdB OBJECT-TYPE
			SYNTAX Integer32
			MAX-ACCESS read-only
			STATUS current
			DESCRIPTION
				"Phase B THD Current.In percentage"
			::= { dpmOther 13 }

		-- 1.3.6.1.4.1.7777.1.2.5.14
  		dpmOtherCurrentThdC OBJECT-TYPE
			SYNTAX Integer32
			MAX-ACCESS read-only
			STATUS current
			DESCRIPTION
				"Phase C THD Current.In percentage"
			::= { dpmOther 14 }

		-- 1.3.6.1.4.1.7777.1.2.5.15
  		dpmOtherVoltageThdA OBJECT-TYPE
			SYNTAX Integer32
			MAX-ACCESS read-only
			STATUS current
			DESCRIPTION
				"Phase A THD Voltage.In percentage"
			::= { dpmOther 15 }

		-- 1.3.6.1.4.1.7777.1.2.5.16
		dpmOtherVoltageThdB OBJECT-TYPE
			SYNTAX Integer32
			MAX-ACCESS read-only
			STATUS current
			DESCRIPTION
				"Phase B THD Voltage.In percentage"
			::= { dpmOther 16 }


		-- 1.3.6.1.4.1.7777.1.2.5.17
		dpmOtherVoltageThdC OBJECT-TYPE
			SYNTAX Integer32
			MAX-ACCESS read-only
			STATUS current
			DESCRIPTION
				"Phase C THD Voltage.In percentage"
			::= { dpmOther 17 }


		-- 1.3.6.1.4.1.7777.1.2.5.18
		dpmOtherVab OBJECT-TYPE
			SYNTAX Integer32
			MAX-ACCESS read-only
			STATUS current
			DESCRIPTION
				"Other Vab Volatage."
			::= { dpmOther 18 }

		-- 1.3.6.1.4.1.7777.1.2.5.19
		dpmOtherVbc OBJECT-TYPE
			SYNTAX Integer32
			MAX-ACCESS read-only
			STATUS current
			DESCRIPTION
				"Other Vbc Volatage."
			::= { dpmOther 19 }


		-- 1.3.6.1.4.1.7777.1.2.5.20
		dpmOtherVca OBJECT-TYPE
			SYNTAX Integer32
			MAX-ACCESS read-only
			STATUS current
			DESCRIPTION
				"Other Vca Volatage."
			::= { dpmOther 20 }

		-- 1.3.6.1.4.1.7777.1.2.5.21
		dpmOtherVolAverage OBJECT-TYPE
			SYNTAX Integer32
			MAX-ACCESS read-only
			STATUS current
			DESCRIPTION
				"Other Vol Average."
			::= { dpmOther 21 }

		-- 1.3.6.1.4.1.7777.1.2.5.22
		dpmOtherVolUnbal OBJECT-TYPE
			SYNTAX Integer32
			MAX-ACCESS read-only
			STATUS current
			DESCRIPTION
				"Other Vol Unbal."
			::= { dpmOther 22 }

		-- 1.3.6.1.4.1.7777.1.2.5.23
		dpmOtherVan OBJECT-TYPE
			SYNTAX Integer32
			MAX-ACCESS read-only
			STATUS current
			DESCRIPTION
				"Other Vol Van."
			::= { dpmOther 23 }


		-- 1.3.6.1.4.1.7777.1.2.5.24
		dpmOtherVbn OBJECT-TYPE
			SYNTAX Integer32
			MAX-ACCESS read-only
			STATUS current
			DESCRIPTION
				"Other Vbn.."
			::= { dpmOther 24 }


		-- 1.3.6.1.4.1.7777.1.2.5.25
		dpmOtherVcn OBJECT-TYPE
			SYNTAX Integer32
			MAX-ACCESS read-only
			STATUS current
			DESCRIPTION
				"Other Vcn. "
			::= { dpmOther 25 }


		-- 1.3.6.1.4.1.7777.1.2.5.26
		dpmOtherVavgneutral OBJECT-TYPE
			SYNTAX Integer32
			MAX-ACCESS read-only
			STATUS current
			DESCRIPTION
				"Other Avg neutral Volatagae."
			::= { dpmOther 26 }

		-- 1.3.6.1.4.1.7777.1.2.5.27
		dpmOtherFrequency OBJECT-TYPE
			SYNTAX Integer32
			MAX-ACCESS read-only
			STATUS current
			DESCRIPTION
				"Other Frequency."
			::= { dpmOther 27 }

		-- 1.3.6.1.4.1.7777.1.2.5.28
		dpmOtherPowerFactor OBJECT-TYPE
			SYNTAX Integer32
			MAX-ACCESS read-only
			STATUS current
			DESCRIPTION
				"Other Power factor."
			::= { dpmOther 28 }

		-- 1.3.6.1.4.1.7777.1.2.5.29
		dpmOtherCurPhaseA OBJECT-TYPE
			SYNTAX Integer32
			MAX-ACCESS read-only
			STATUS current
			DESCRIPTION
				"Other Phase A Current."
			::= { dpmOther 29 }

		-- 1.3.6.1.4.1.7777.1.2.5.30
		dpmOtherCurPhaseB OBJECT-TYPE
			SYNTAX Integer32
			MAX-ACCESS read-only
			STATUS current
			DESCRIPTION
				"Other Phase B Current."
			::= { dpmOther 30 }


		-- 1.3.6.1.4.1.7777.1.2.5.31
		dpmOtherCurPhaseC OBJECT-TYPE
			SYNTAX Integer32
			MAX-ACCESS read-only
			STATUS current
			DESCRIPTION
				"Other Phase C Current."
			::= { dpmOther 31 }

		-- 1.3.6.1.4.1.7777.1.2.5.32
		dpmOtherPhaseCurAvg OBJECT-TYPE
			SYNTAX Integer32
			MAX-ACCESS read-only
			STATUS current
			DESCRIPTION
				"Other Phase Current aVG."
			::= { dpmOther 32 }

		-- 1.3.6.1.4.1.7777.1.2.5.33
		dpmOtherPhaseCurUnbalancecePercentage OBJECT-TYPE
			SYNTAX Integer32
			MAX-ACCESS read-only
			STATUS current
			DESCRIPTION
				"Other Phase Cur Unbalancece Percentage."
			::= { dpmOther 33 }

		-- 1.3.6.1.4.1.7777.1.2.5.34
		dpmOtherRealTotalPower OBJECT-TYPE
			SYNTAX Integer32
			MAX-ACCESS read-only
			STATUS current
			DESCRIPTION
				"Other Real Total power factor."
			::= { dpmOther 34 }

		-- 1.3.6.1.4.1.7777.1.2.5.35
		dpmOtherReactiveTotalPower OBJECT-TYPE
			SYNTAX Integer32
			MAX-ACCESS read-only
			STATUS current
			DESCRIPTION
				"Other Reactive Total power."
			::= { dpmOther 35 }

		-- 1.3.6.1.4.1.7777.1.2.5.36
  		dpmOtherApparentTotalPower OBJECT-TYPE
			SYNTAX Integer32
			MAX-ACCESS read-only
			STATUS current
			DESCRIPTION
				"Other AApparent Total power."
			::= { dpmOther 36 }

		-- 1.3.6.1.4.1.7777.1.2.5.37
  		dpmOtherNetActiveEnergy OBJECT-TYPE
			SYNTAX Integer32
			MAX-ACCESS read-only
			STATUS current
			DESCRIPTION
				"Other Net Active Energy."
			::= { dpmOther 37 }


		-- 1.3.6.1.4.1.7777.1.2.5.39
		dpmOtherFirmwareVersion OBJECT-TYPE
			SYNTAX DisplayString (SIZE (0..128))
			MAX-ACCESS read-only
			STATUS current
			DESCRIPTION
				"Other DPM Firmware."
			::= { dpmOther 38 }


		-- 1.3.6.1.4.1.7777.1.2.6.1
		psAlarmVariable OBJECT-TYPE
			SYNTAX DisplayString (SIZE (0..128))
			MAX-ACCESS read-only
			STATUS current
			DESCRIPTION
				"Traps notification."
			::= { traps 1 }



generator_start_signal_activated_SNMPSend NOTIFICATION-TYPE
        OBJECTS { psAlarmVariable }
        STATUS  current
        DESCRIPTION
            "Generator Start Signal Activated."
    ::= { traps 2 }

generator_start_signal_removed_SNMPSend NOTIFICATION-TYPE
        OBJECTS { psAlarmVariable }
        STATUS  current
        DESCRIPTION
            "Generator Start Signal Removed."
    ::= { traps 3 }

transferred_from_normal_to_emergency_SNMPSend NOTIFICATION-TYPE
        OBJECTS { psAlarmVariable }
        STATUS  current
        DESCRIPTION
            "Transferred from Normal to Emergency."
    ::= { traps 4 }

transferred_from_emergency_to_normal_SNMPSend NOTIFICATION-TYPE
        OBJECTS { psAlarmVariable }
        STATUS  current
        DESCRIPTION
            "Transferred from Emergency to Normal."
    ::= { traps 5 }

emergency_accepted_SNMPSend NOTIFICATION-TYPE
        OBJECTS { psAlarmVariable }
        STATUS  current
        DESCRIPTION
            "Emergency Accepted."
    ::= { traps 6 }

emergency_not_accepted_SNMPSend NOTIFICATION-TYPE
        OBJECTS { psAlarmVariable }
        STATUS  current
        DESCRIPTION
            "Emergency Not Accepted."
    ::= { traps 7 }

normal_accepted_SNMPSend NOTIFICATION-TYPE
        OBJECTS { psAlarmVariable }
        STATUS  current
        DESCRIPTION
            "Normal Accepted."
    ::= { traps 8 }

normal_not_accepted_SNMPSend NOTIFICATION-TYPE
        OBJECTS { psAlarmVariable }
        STATUS  current
        DESCRIPTION
            "Normal Not Accepted."
    ::= { traps 9 }

loss_of_emergency_when_on_emergency_SNMPSend NOTIFICATION-TYPE
        OBJECTS { psAlarmVariable }
        STATUS  current
        DESCRIPTION
            "Loss of Emergency when on Emergency."
    ::= { traps 10 }

load_disconnected_SNMPSend NOTIFICATION-TYPE
        OBJECTS { psAlarmVariable }
        STATUS  current
        DESCRIPTION
            "Load Disconnected."
    ::= { traps 11 }

transfer_switch_changed_to_non_automatic_mode_SNMPSend NOTIFICATION-TYPE
        OBJECTS { psAlarmVariable }
        STATUS  current
        DESCRIPTION
            "Transfer Switch Changed to Non-Automatic Mode."
    ::= { traps 12 }

transfer_switch_changed_to_automatic_mode_SNMPSend NOTIFICATION-TYPE
        OBJECTS { psAlarmVariable }
        STATUS  current
        DESCRIPTION
            "Transfer Switch Changed to Automatic Mode."
    ::= { traps 13 }


emergency_not_accepted_in_time_SNMPSend NOTIFICATION-TYPE
        OBJECTS { psAlarmVariable }
        STATUS  current
        DESCRIPTION
            "Emergency Not Accepted in Time."
    ::= { traps 14 }


transfer_not_successful_SNMPSend NOTIFICATION-TYPE
        OBJECTS { psAlarmVariable }
        STATUS  current
        DESCRIPTION
            "Transfer Not Successful."
    ::= { traps 15 }

transfer_switch_position_not_determined_SNMPSend NOTIFICATION-TYPE
        OBJECTS { psAlarmVariable }
        STATUS  current
        DESCRIPTION
            "Transfer Switch Position Not Determined."
    ::= { traps 16 }

auxiliary_engine_input_SNMPSend NOTIFICATION-TYPE
        OBJECTS { psAlarmVariable }
        STATUS  current
        DESCRIPTION
            "Auxiliary/Engine Input."
    ::= { traps 17 }
END
