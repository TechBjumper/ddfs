--				
-- CAREL-aarc_norm.MIB			
-- MIB generated by CAREL				
-- Monday, 14 February 2005				
--				
				
    CAREL-aarc_norm-MIB DEFINITIONS ::= BEGIN				
 				
		IMPORTS		
			OBJECT-GROUP	
				FROM SNMPv2-CONF
			sysContact, sysName, sysLocation	
				FROM SNMPv2-MIB
			enterprises, MODULE-IDENTITY	
				FROM SNMPv2-SMI;
				
        aarc_normMIB MODULE-IDENTITY				
      		LAST-UPDATED  "200502141118Z"		-- February 14, 2005 at 11:18 GMT
      		ORGANIZATION  "CAREL SpA"		
      		CONTACT-INFO		
                "				
                        Carel SpA				
                        Via dell'Industria, 11				
                        35020 Brugine (PD) Italy				
                        Tel: +39 049 9716611				
                        E-mail: carel@carel.com				
                "				
      		DESCRIPTION		
                "This is the MIB module for the aarc_norm device."				
			::= { instruments 1 }	
				
				
--				
-- Node definitions		
--				
				
		-- 1.3.6.1.4.1.9839		
		carel OBJECT IDENTIFIER ::= { enterprises 9839 }		
				
		-- 1.3.6.1.4.1.9839.1		
		systm OBJECT IDENTIFIER ::= { carel 1 }		
				
		-- 1.3.6.1.4.1.9839.1.1		
		agentRelease OBJECT-TYPE		
			SYNTAX Integer32	
			UNITS "N/A"	
			MAX-ACCESS read-only	
			STATUS current	
			DESCRIPTION "Release of the Agent."	
		::= { systm 1 }		
				
		-- 1.3.6.1.4.1.9839.1.2		
		agentCode OBJECT-TYPE		
			SYNTAX Integer32	
			UNITS "N/A"	
			MAX-ACCESS read-only	
			STATUS current	
			DESCRIPTION "Code of the Agent. 1=WebGate"	
		::= { systm 2 }		
				
		-- 1.3.6.1.4.1.9839.2		
		instruments OBJECT IDENTIFIER ::= { carel 2 }		
				
		-- 1.3.6.1.4.1.9839.2.0		
		webGateInfo OBJECT IDENTIFIER ::= { instruments 0 }		
				
		-- 1.3.6.1.4.1.9839.2.0.1		
		agentParameters OBJECT IDENTIFIER ::= { webGateInfo 1 }		
				
		-- 1.3.6.1.4.1.9839.2.0.1.1		
		netSize OBJECT-TYPE		
			SYNTAX Integer32 (1..16)	
			UNITS "N/A"	
			MAX-ACCESS read-write	
			STATUS current	
			DESCRIPTION "Network size. It corresponds to the number of units connected to the WebGate. "	
		::= { agentParameters 1 }		
				
		-- 1.3.6.1.4.1.9839.2.0.1.2		
		baudRate OBJECT-TYPE		
			SYNTAX Integer32 (1200 | 2400 |4800 |9600 | 19200)	
			UNITS "N/A"	
			MAX-ACCESS read-write	
			STATUS current	
			DESCRIPTION "Baudrate of the Carel network. "	
		::= { agentParameters 2 }		
				
		-- 1.3.6.1.4.1.9839.2.0.2		
		unitTypeGroup OBJECT IDENTIFIER ::= { webGateInfo 2 }		
		 		
		-- 1.3.6.1.4.1.9839.2.0.2.1 		
		unit1-Type OBJECT-TYPE		
			SYNTAX DisplayString	
			UNITS "N/A"	
			MAX-ACCESS read-only	
			STATUS current	
			DESCRIPTION "Type of the unit having serial address 1. "	
			::= { unitTypeGroup 1 }	
				
		-- ... You will have how many unitX-Type objects as the value of netSize is		
				
		-- 1.3.6.1.4.1.9839.2.0.3		
		unitCodeGroup OBJECT IDENTIFIER ::= { webGateInfo 3 }		
				
		-- 1.3.6.1.4.1.9839.2.0.3.1		
		unit1-Code OBJECT-TYPE		
			SYNTAX Integer32	
			UNITS "N/A"	
			MAX-ACCESS read-only	
			STATUS current	
			DESCRIPTION "Code of the unit having serial address 1. "	
			::= { unitCodeGroup 1 }	
				
		-- ... You will have how many unitX-Code objects as the value of netSize is		
				
		-- 1.3.6.1.4.1.9839.2.0.4		
		unitSoftwareReleaseGroup OBJECT IDENTIFIER ::= { webGateInfo 4 }		
				
		-- 1.3.6.1.4.1.9839.2.0.3.1		
		unit1-SoftwareRelease OBJECT-TYPE		
			SYNTAX Integer32	
			UNITS "N/A"	
			MAX-ACCESS read-only	
			STATUS current	
			DESCRIPTION "Software release of the unit having serial address 1. "	
			::= { unitSoftwareReleaseGroup 1 }	
				
		-- ... You will have how many unitX-SoftwareRelease objects as the value of netSize is		
				
		-- 1.3.6.1.4.1.9839.2.0.5		
		unitMinSoftwareReleaseGroup OBJECT IDENTIFIER ::= { webGateInfo 5 }		
				
		-- 1.3.6.1.4.1.9839.2.0.5.1		
		unit1-MinSoftwareRelease OBJECT-TYPE		
			SYNTAX Integer32	
			UNITS "N/A"	
			MAX-ACCESS read-only	
			STATUS current	
			DESCRIPTION "Minimum software release of the unit having serial address 1. "	
			::= { unitMinSoftwareReleaseGroup 1 }	
				
		-- ... You will have how many unitX-MinSoftwareRelease objects as the value of netSize is		
				
		-- 1.3.6.1.4.1.9839.2.0.6		
		unitMaxSoftwareReleaseGroup OBJECT IDENTIFIER ::= { webGateInfo 6 }		
				
		-- 1.3.6.1.4.1.9839.2.0.6.1		
		unit1-MaxSoftwareRelease OBJECT-TYPE		
			SYNTAX Integer32	
			UNITS "N/A"	
			MAX-ACCESS read-only	
			STATUS current	
			DESCRIPTION "Maximum software release of the unit having serial address 1. "	
			::= { unitMaxSoftwareReleaseGroup 1 }	
				
		-- ... You will have how many unitX-MaxSoftwareRelease objects as the value of netSize is		
				
		-- 1.3.6.1.4.1.9839.2.0.7		
		unitNoAnswerCounterGroup OBJECT IDENTIFIER ::= { webGateInfo 7 }		
				
		-- 1.3.6.1.4.1.9839.2.0.7.1		
		unit1-NoAnswerCounter OBJECT-TYPE		
			SYNTAX Integer32	
			UNITS "N/A"	
			MAX-ACCESS read-only	
			STATUS current	
			DESCRIPTION "No answer counter of the unit having serial address 1. "	
			::= { unitNoAnswerCounterGroup 1 }	
				
		-- ... You will have how many unitX-NoAnswerCounter objects as the value of netSize is		
				
		-- 1.3.6.1.4.1.9839.2.0.8		
		unitErrorChecksumCounterGroup OBJECT IDENTIFIER ::= { webGateInfo 8 }		
				
		-- 1.3.6.1.4.1.9839.2.0.8.1		
		unit1-ErrorChecksumCounter OBJECT-TYPE		
			SYNTAX Integer32	
			UNITS "N/A"	
			MAX-ACCESS read-only	
			STATUS current	
			DESCRIPTION "Error checksum counter of the unit having serial address 1. "	
			::= { unitErrorChecksumCounterGroup 1 }	
				
		-- ... You will have how many unitX-ErrorChecksumCounter objects as the value of netSize is		
				
		-- 1.3.6.1.4.1.9839.2.0.9		
		unitTimeoutCounterGroup OBJECT IDENTIFIER ::= { webGateInfo 9 }		
				
		-- 1.3.6.1.4.1.9839.2.0.9.1		
		unit1-TimeoutCounter OBJECT-TYPE		
			SYNTAX Integer32	
			UNITS "N/A"	
			MAX-ACCESS read-only	
			STATUS current	
			DESCRIPTION "Timeout counter of the unit having serial address 1. "	
			::= { unitTimeoutCounterGroup 1 }	
				
		-- ... You will have how many unitX-TimeoutCounter objects as the value of netSize is		
				
		-- 1.3.6.1.4.1.9839.2.1		
        -- aarc_normMIB OBJECT IDENTIFIER ::= { instruments 1 }				
				
        -- 1.3.6.1.4.1.9839.2.1.1				
        digitalObjects OBJECT IDENTIFIER ::= { aarc_normMIB 1 }				
				
        -- 1.3.6.1.4.1.9839.2.1.1.1				
        v_digit1 OBJECT-TYPE				
                    SYNTAX Integer32 (0..1)				
                    UNITS "N/A"				
                    MAX-ACCESS read-only				
                    STATUS current				
                    DESCRIPTION "Heat enable input (hp)"				
                    ::= { digitalObjects 1 }				
				
        -- 1.3.6.1.4.1.9839.2.1.1.2				
        en_cooling OBJECT-TYPE				
                    SYNTAX Integer32 (0..1)				
                    UNITS "N/A"				
                    MAX-ACCESS read-only				
                    STATUS current				
                    DESCRIPTION "Cool enable input"				
                    ::= { digitalObjects 2 }				
				
        -- 1.3.6.1.4.1.9839.2.1.1.3				
        v_digit3 OBJECT-TYPE				
                    SYNTAX Integer32 (0..1)				
                    UNITS "N/A"				
                    MAX-ACCESS read-only				
                    STATUS current				
                    DESCRIPTION "Condens. Fan 1 (hp)"				
                    ::= { digitalObjects 3 }				
				
        -- 1.3.6.1.4.1.9839.2.1.1.4				
        v_digit4 OBJECT-TYPE				
                    SYNTAX Integer32 (0..1)				
                    UNITS "N/A"				
                    MAX-ACCESS read-only				
                    STATUS current				
                    DESCRIPTION "Reverse cycle valve 1 (hp)"				
                    ::= { digitalObjects 4 }				
				
        -- 1.3.6.1.4.1.9839.2.1.1.5				
        main_fan_al OBJECT-TYPE				
                    SYNTAX Integer32 (0..1)				
                    UNITS "N/A"				
                    MAX-ACCESS read-only				
                    STATUS current				
                    DESCRIPTION "Main fan"				
                    ::= { digitalObjects 5 }				
				
        -- 1.3.6.1.4.1.9839.2.1.1.6				
        req_dehumid OBJECT-TYPE				
                    SYNTAX Integer32 (0..1)				
                    UNITS "N/A"				
                    MAX-ACCESS read-only				
                    STATUS current				
                    DESCRIPTION "Dehumidification valve"				
                    ::= { digitalObjects 6 }				
				
        -- 1.3.6.1.4.1.9839.2.1.1.7				
        output3 OBJECT-TYPE				
                    SYNTAX Integer32 (0..1)				
                    UNITS "N/A"				
                    MAX-ACCESS read-only				
                    STATUS current				
                    DESCRIPTION "Humidifier"				
                    ::= { digitalObjects 7 }				
				
        -- 1.3.6.1.4.1.9839.2.1.1.8				
        fill_humid OBJECT-TYPE				
                    SYNTAX Integer32 (0..1)				
                    UNITS "N/A"				
                    MAX-ACCESS read-only				
                    STATUS current				
                    DESCRIPTION "Water inlet humidifier"				
                    ::= { digitalObjects 8 }				
				
        -- 1.3.6.1.4.1.9839.2.1.1.9				
        drain_humid OBJECT-TYPE				
                    SYNTAX Integer32 (0..1)				
                    UNITS "N/A"				
                    MAX-ACCESS read-only				
                    STATUS current				
                    DESCRIPTION "Water humidif.discharge"				
                    ::= { digitalObjects 9 }				
				
        -- 1.3.6.1.4.1.9839.2.1.1.10				
        general_alarm1 OBJECT-TYPE				
                    SYNTAX Integer32 (0..1)				
                    UNITS "N/A"				
                    MAX-ACCESS read-only				
                    STATUS current				
                    DESCRIPTION "General alarm 1"				
                    ::= { digitalObjects 10 }				
				
        -- 1.3.6.1.4.1.9839.2.1.1.11				
        general_alarm2 OBJECT-TYPE				
                    SYNTAX Integer32 (0..1)				
                    UNITS "N/A"				
                    MAX-ACCESS read-only				
                    STATUS current				
                    DESCRIPTION "General alarm 2"				
                    ::= { digitalObjects 11 }				
				
        -- 1.3.6.1.4.1.9839.2.1.1.12				
        v_digit12 OBJECT-TYPE				
                    SYNTAX Integer32 (0..1)				
                    UNITS "N/A"				
                    MAX-ACCESS read-only				
                    STATUS current				
                    DESCRIPTION "Valve 0-10v cooling enable"				
                    ::= { digitalObjects 12 }				
				
        -- 1.3.6.1.4.1.9839.2.1.1.13				
        v_digit13 OBJECT-TYPE				
                    SYNTAX Integer32 (0..1)				
                    UNITS "N/A"				
                    MAX-ACCESS read-only				
                    STATUS current				
                    DESCRIPTION "Valve 0-10v heating enable"				
                    ::= { digitalObjects 13 }				
				
        -- 1.3.6.1.4.1.9839.2.1.1.14				
        v_digit14 OBJECT-TYPE				
                    SYNTAX Integer32 (0..1)				
                    UNITS "N/A"				
                    MAX-ACCESS read-only				
                    STATUS current				
                    DESCRIPTION "Hi press. circuit 2 enable (hp)"				
                    ::= { digitalObjects 14 }				
				
        -- 1.3.6.1.4.1.9839.2.1.1.15				
        compressor1 OBJECT-TYPE				
                    SYNTAX Integer32 (0..1)				
                    UNITS "N/A"				
                    MAX-ACCESS read-only				
                    STATUS current				
                    DESCRIPTION "Compressor 1"				
                    ::= { digitalObjects 15 }				
				
        -- 1.3.6.1.4.1.9839.2.1.1.16				
        compressor2 OBJECT-TYPE				
                    SYNTAX Integer32 (0..1)				
                    UNITS "N/A"				
                    MAX-ACCESS read-only				
                    STATUS current				
                    DESCRIPTION "Compressor 2"				
                    ::= { digitalObjects 16 }				
				
        -- 1.3.6.1.4.1.9839.2.1.1.17				
        unload1_c1 OBJECT-TYPE				
                    SYNTAX Integer32 (0..1)				
                    UNITS "N/A"				
                    MAX-ACCESS read-only				
                    STATUS current				
                    DESCRIPTION "Unloader compr. 1"				
                    ::= { digitalObjects 17 }				
				
        -- 1.3.6.1.4.1.9839.2.1.1.18				
        unload1_c2 OBJECT-TYPE				
                    SYNTAX Integer32 (0..1)				
                    UNITS "N/A"				
                    MAX-ACCESS read-only				
                    STATUS current				
                    DESCRIPTION "Unloader compr. 2"				
                    ::= { digitalObjects 18 }				
				
        -- 1.3.6.1.4.1.9839.2.1.1.19				
        heater1 OBJECT-TYPE				
                    SYNTAX Integer32 (0..1)				
                    UNITS "N/A"				
                    MAX-ACCESS read-only				
                    STATUS current				
                    DESCRIPTION "Heater 1"				
                    ::= { digitalObjects 19 }				
				
        -- 1.3.6.1.4.1.9839.2.1.1.20				
        heater2 OBJECT-TYPE				
                    SYNTAX Integer32 (0..1)				
                    UNITS "N/A"				
                    MAX-ACCESS read-only				
                    STATUS current				
                    DESCRIPTION "Heater 2 (no for hp)"				
                    ::= { digitalObjects 20 }				
				
        -- 1.3.6.1.4.1.9839.2.1.1.21				
        open_cool_d3p OBJECT-TYPE				
                    SYNTAX Integer32 (0..1)				
                    UNITS "N/A"				
                    MAX-ACCESS read-only				
                    STATUS current				
                    DESCRIPTION "Open cool float.valve"				
                    ::= { digitalObjects 21 }				
				
        -- 1.3.6.1.4.1.9839.2.1.1.22				
        close_cool_d3p OBJECT-TYPE				
                    SYNTAX Integer32 (0..1)				
                    UNITS "N/A"				
                    MAX-ACCESS read-only				
                    STATUS current				
                    DESCRIPTION "Close cool float.valve"				
                    ::= { digitalObjects 22 }				
				
        -- 1.3.6.1.4.1.9839.2.1.1.23				
        open_heat_d3p OBJECT-TYPE				
                    SYNTAX Integer32 (0..1)				
                    UNITS "N/A"				
                    MAX-ACCESS read-only				
                    STATUS current				
                    DESCRIPTION "Open heat float.valve"				
                    ::= { digitalObjects 23 }				
				
        -- 1.3.6.1.4.1.9839.2.1.1.24				
        close_heat_d3p OBJECT-TYPE				
                    SYNTAX Integer32 (0..1)				
                    UNITS "N/A"				
                    MAX-ACCESS read-only				
                    STATUS current				
                    DESCRIPTION "Close heat float.valve"				
                    ::= { digitalObjects 24 }				
				
        -- 1.3.6.1.4.1.9839.2.1.1.31				
        xal_fan_overl OBJECT-TYPE				
                    SYNTAX Integer32 (0..1)				
                    UNITS "N/A"				
                    MAX-ACCESS read-only				
                    STATUS current				
                    DESCRIPTION "Al01 – Main fan overload"				
                    ::= { digitalObjects 31 }				
				
        -- 1.3.6.1.4.1.9839.2.1.1.32				
        al_air_flow OBJECT-TYPE				
                    SYNTAX Integer32 (0..1)				
                    UNITS "N/A"				
                    MAX-ACCESS read-only				
                    STATUS current				
                    DESCRIPTION "Al02 – Air flow switch alarm"				
                    ::= { digitalObjects 32 }				
				
        -- 1.3.6.1.4.1.9839.2.1.1.33				
        al_air_filter OBJECT-TYPE				
                    SYNTAX Integer32 (0..1)				
                    UNITS "N/A"				
                    MAX-ACCESS read-only				
                    STATUS current				
                    DESCRIPTION "Al03 – Air filter alarm"				
                    ::= { digitalObjects 33 }				
				
        -- 1.3.6.1.4.1.9839.2.1.1.34				
        xal_comp_overl1 OBJECT-TYPE				
                    SYNTAX Integer32 (0..1)				
                    UNITS "N/A"				
                    MAX-ACCESS read-only				
                    STATUS current				
                    DESCRIPTION "Al04 – Compressor 1 overload"				
                    ::= { digitalObjects 34 }				
				
        -- 1.3.6.1.4.1.9839.2.1.1.35				
        mal_h_pressure1 OBJECT-TYPE				
                    SYNTAX Integer32 (0..1)				
                    UNITS "N/A"				
                    MAX-ACCESS read-only				
                    STATUS current				
                    DESCRIPTION "Al05 – Hi pressure compr. 1 (probe)"				
                    ::= { digitalObjects 35 }				
				
        -- 1.3.6.1.4.1.9839.2.1.1.36				
        mal_high_pres1 OBJECT-TYPE				
                    SYNTAX Integer32 (0..1)				
                    UNITS "N/A"				
                    MAX-ACCESS read-only				
                    STATUS current				
                    DESCRIPTION "Al05 – Hi safety compr. 1 (switch)"				
                    ::= { digitalObjects 36 }				
				
        -- 1.3.6.1.4.1.9839.2.1.1.37				
        mal_low_pres1 OBJECT-TYPE				
                    SYNTAX Integer32 (0..1)				
                    UNITS "N/A"				
                    MAX-ACCESS read-only				
                    STATUS current				
                    DESCRIPTION "Al07 – Low pressure compr. 1"				
                    ::= { digitalObjects 37 }				
				
        -- 1.3.6.1.4.1.9839.2.1.1.38				
        al_heat_overl OBJECT-TYPE				
                    SYNTAX Integer32 (0..1)				
                    UNITS "N/A"				
                    MAX-ACCESS read-only				
                    STATUS current				
                    DESCRIPTION "Al08 – Heaters thermostat"				
                    ::= { digitalObjects 38 }				
				
        -- 1.3.6.1.4.1.9839.2.1.1.39				
        al_overflow OBJECT-TYPE				
                    SYNTAX Integer32 (0..1)				
                    UNITS "N/A"				
                    MAX-ACCESS read-only				
                    STATUS current				
                    DESCRIPTION "Al09 – Presence of water alarm"				
                    ::= { digitalObjects 39 }				
				
        -- 1.3.6.1.4.1.9839.2.1.1.40				
        al_h_pre_room OBJECT-TYPE				
                    SYNTAX Integer32 (0..1)				
                    UNITS "N/A"				
                    MAX-ACCESS read-only				
                    STATUS current				
                    DESCRIPTION "Al10 – Hi room temp. prealarm"				
                    ::= { digitalObjects 40 }				
				
        -- 1.3.6.1.4.1.9839.2.1.1.41				
        al_h_room_temp OBJECT-TYPE				
                    SYNTAX Integer32 (0..1)				
                    UNITS "N/A"				
                    MAX-ACCESS read-only				
                    STATUS current				
                    DESCRIPTION "Al11 – Hi room temp.alarm"				
                    ::= { digitalObjects 41 }				
				
        -- 1.3.6.1.4.1.9839.2.1.1.42				
        al_l_room_temp OBJECT-TYPE				
                    SYNTAX Integer32 (0..1)				
                    UNITS "N/A"				
                    MAX-ACCESS read-only				
                    STATUS current				
                    DESCRIPTION "Al12 – Low room temp. alarm"				
                    ::= { digitalObjects 42 }				
				
        -- 1.3.6.1.4.1.9839.2.1.1.43				
        al_high_humid OBJECT-TYPE				
                    SYNTAX Integer32 (0..1)				
                    UNITS "N/A"				
                    MAX-ACCESS read-only				
                    STATUS current				
                    DESCRIPTION "Al13 – High room humidity alarm"				
                    ::= { digitalObjects 43 }				
				
        -- 1.3.6.1.4.1.9839.2.1.1.44				
        al_low_humid OBJECT-TYPE				
                    SYNTAX Integer32 (0..1)				
                    UNITS "N/A"				
                    MAX-ACCESS read-only				
                    STATUS current				
                    DESCRIPTION "Al14 – Low room humidity alarm"				
                    ::= { digitalObjects 44 }				
				
        -- 1.3.6.1.4.1.9839.2.1.1.45				
        al_external1 OBJECT-TYPE				
                    SYNTAX Integer32 (0..1)				
                    UNITS "N/A"				
                    MAX-ACCESS read-only				
                    STATUS current				
                    DESCRIPTION "Al15 – External alarm 1"				
                    ::= { digitalObjects 45 }				
				
        -- 1.3.6.1.4.1.9839.2.1.1.46				
        al_external2 OBJECT-TYPE				
                    SYNTAX Integer32 (0..1)				
                    UNITS "N/A"				
                    MAX-ACCESS read-only				
                    STATUS current				
                    DESCRIPTION "Al16 – external alarm 2"				
                    ::= { digitalObjects 46 }				
				
        -- 1.3.6.1.4.1.9839.2.1.1.47				
        xal_comp_overl2 OBJECT-TYPE				
                    SYNTAX Integer32 (0..1)				
                    UNITS "N/A"				
                    MAX-ACCESS read-only				
                    STATUS current				
                    DESCRIPTION "Al17 – Compressor 2 overload"				
                    ::= { digitalObjects 47 }				
				
        -- 1.3.6.1.4.1.9839.2.1.1.48				
        mal_h_pressure2 OBJECT-TYPE				
                    SYNTAX Integer32 (0..1)				
                    UNITS "N/A"				
                    MAX-ACCESS read-only				
                    STATUS current				
                    DESCRIPTION "Al18 – Hi pressure compr. 2 (probe)"				
                    ::= { digitalObjects 48 }				
				
        -- 1.3.6.1.4.1.9839.2.1.1.49				
        mal_high_pres2 OBJECT-TYPE				
                    SYNTAX Integer32 (0..1)				
                    UNITS "N/A"				
                    MAX-ACCESS read-only				
                    STATUS current				
                    DESCRIPTION "Al19 – Hi safety compr. 2 (switch)"				
                    ::= { digitalObjects 49 }				
				
        -- 1.3.6.1.4.1.9839.2.1.1.50				
        mal_low_pres2 OBJECT-TYPE				
                    SYNTAX Integer32 (0..1)				
                    UNITS "N/A"				
                    MAX-ACCESS read-only				
                    STATUS current				
                    DESCRIPTION "Al20 – Low pressure compr. 2"				
                    ::= { digitalObjects 50 }				
				
        -- 1.3.6.1.4.1.9839.2.1.1.51				
        al_room_humid OBJECT-TYPE				
                    SYNTAX Integer32 (0..1)				
                    UNITS "N/A"				
                    MAX-ACCESS read-only				
                    STATUS current				
                    DESCRIPTION "Al21 – Probe fail humidity"				
                    ::= { digitalObjects 51 }				
				
        -- 1.3.6.1.4.1.9839.2.1.1.52				
        al_probe_temp OBJECT-TYPE				
                    SYNTAX Integer32 (0..1)				
                    UNITS "N/A"				
                    MAX-ACCESS read-only				
                    STATUS current				
                    DESCRIPTION "Al22 – Probe fail temp."				
                    ::= { digitalObjects 52 }				
				
        -- 1.3.6.1.4.1.9839.2.1.1.53				
        al_pressure OBJECT-TYPE				
                    SYNTAX Integer32 (0..1)				
                    UNITS "N/A"				
                    MAX-ACCESS read-only				
                    STATUS current				
                    DESCRIPTION "Al23 – Probe fail pressure"				
                    ::= { digitalObjects 53 }				
				
        -- 1.3.6.1.4.1.9839.2.1.1.54				
        mal_e06 OBJECT-TYPE				
                    SYNTAX Integer32 (0..1)				
                    UNITS "N/A"				
                    MAX-ACCESS read-only				
                    STATUS current				
                    DESCRIPTION "Al24 – High current humidifier"				
                    ::= { digitalObjects 54 }				
				
        -- 1.3.6.1.4.1.9839.2.1.1.55				
        al_e09 OBJECT-TYPE				
                    SYNTAX Integer32 (0..1)				
                    UNITS "N/A"				
                    MAX-ACCESS read-only				
                    STATUS current				
                    DESCRIPTION "Al25 – Lack of water humidifier"				
                    ::= { digitalObjects 55 }				
				
        -- 1.3.6.1.4.1.9839.2.1.1.56				
        mal_e10 OBJECT-TYPE				
                    SYNTAX Integer32 (0..1)				
                    UNITS "N/A"				
                    MAX-ACCESS read-only				
                    STATUS current				
                    DESCRIPTION "Al26 – Lack of current humidif."				
                    ::= { digitalObjects 56 }				
				
        -- 1.3.6.1.4.1.9839.2.1.1.58				
        al_maintenance OBJECT-TYPE				
                    SYNTAX Integer32 (0..1)				
                    UNITS "N/A"				
                    MAX-ACCESS read-only				
                    STATUS current				
                    DESCRIPTION "Al28 – Maintenance alarm"				
                    ::= { digitalObjects 58 }				
				
        -- 1.3.6.1.4.1.9839.2.1.1.59				
        mal_oil_diff1 OBJECT-TYPE				
                    SYNTAX Integer32 (0..1)				
                    UNITS "N/A"				
                    MAX-ACCESS read-only				
                    STATUS current				
                    DESCRIPTION "Al29 – Compressor 1 oil diff."				
                    ::= { digitalObjects 59 }				
				
        -- 1.3.6.1.4.1.9839.2.1.1.60				
        mal_oil_diff2 OBJECT-TYPE				
                    SYNTAX Integer32 (0..1)				
                    UNITS "N/A"				
                    MAX-ACCESS read-only				
                    STATUS current				
                    DESCRIPTION "Al30 – Compressor 2 oil diff."				
                    ::= { digitalObjects 60 }				
				
        -- 1.3.6.1.4.1.9839.2.1.1.61				
        mal_smoke_fire OBJECT-TYPE				
                    SYNTAX Integer32 (0..1)				
                    UNITS "N/A"				
                    MAX-ACCESS read-only				
                    STATUS current				
                    DESCRIPTION "Al31 – Smoke - fire alarm"				
                    ::= { digitalObjects 61 }				
				
        -- 1.3.6.1.4.1.9839.2.1.1.62				
        al_plan OBJECT-TYPE				
                    SYNTAX Integer32 (0..1)				
                    UNITS "N/A"				
                    MAX-ACCESS read-only				
                    STATUS current				
                    DESCRIPTION "Al32 – LAN disconnected"				
                    ::= { digitalObjects 62 }				
				
        -- 1.3.6.1.4.1.9839.2.1.1.63				
        al_overload OBJECT-TYPE				
                    SYNTAX Integer32 (0..1)				
                    UNITS "N/A"				
                    MAX-ACCESS read-only				
                    STATUS current				
                    DESCRIPTION "Al33 – Overload alarms"				
                    ::= { digitalObjects 63 }				
				
        -- 1.3.6.1.4.1.9839.2.1.1.64				
        al_clock OBJECT-TYPE				
                    SYNTAX Integer32 (0..1)				
                    UNITS "N/A"				
                    MAX-ACCESS read-only				
                    STATUS current				
                    DESCRIPTION "Al34 – Clock board faulty"				
                    ::= { digitalObjects 64 }				
				
        -- 1.3.6.1.4.1.9839.2.1.1.65				
        mepromnook OBJECT-TYPE				
                    SYNTAX Integer32 (0..1)				
                    UNITS "N/A"				
                    MAX-ACCESS read-only				
                    STATUS current				
                    DESCRIPTION "Al35 – Eeprom write fail"				
                    ::= { digitalObjects 65 }				
				
        -- 1.3.6.1.4.1.9839.2.1.1.66				
        mal_limit_therm OBJECT-TYPE				
                    SYNTAX Integer32 (0..1)				
                    UNITS "N/A"				
                    MAX-ACCESS read-only				
                    STATUS current				
                    DESCRIPTION "Al36 – Limit thermostat alarm"				
                    ::= { digitalObjects 66 }				
				
        -- 1.3.6.1.4.1.9839.2.1.1.79				
        v_digit79 OBJECT-TYPE				
                    SYNTAX Integer32 (0..1)				
                    UNITS "N/A"				
                    MAX-ACCESS read-only				
                    STATUS current				
                    DESCRIPTION "Condens. Fan 2 (hp)"				
                    ::= { digitalObjects 79 }				
				
        -- 1.3.6.1.4.1.9839.2.1.1.80				
        v_digit80 OBJECT-TYPE				
                    SYNTAX Integer32 (0..1)				
                    UNITS "N/A"				
                    MAX-ACCESS read-only				
                    STATUS current				
                    DESCRIPTION "Reverse cycle valve 2 (hp)"				
                    ::= { digitalObjects 80 }				
				
        -- 1.3.6.1.4.1.9839.2.1.1.81				
        v_digit81 OBJECT-TYPE				
                    SYNTAX Integer32 (0..1)				
                    UNITS "N/A"				
                    MAX-ACCESS read-only				
                    STATUS current				
                    DESCRIPTION "Compressor 1 alarm (hp)"				
                    ::= { digitalObjects 81 }				
				
        -- 1.3.6.1.4.1.9839.2.1.1.82				
        v_digit82 OBJECT-TYPE				
                    SYNTAX Integer32 (0..1)				
                    UNITS "N/A"				
                    MAX-ACCESS read-only				
                    STATUS current				
                    DESCRIPTION "Compressor 2 alarm (hp)"				
                    ::= { digitalObjects 82 }				
				
        -- 1.3.6.1.4.1.9839.2.1.1.83				
        v_digit83 OBJECT-TYPE				
                    SYNTAX Integer32 (0..1)				
                    UNITS "N/A"				
                    MAX-ACCESS read-only				
                    STATUS current				
                    DESCRIPTION "Temperature alarm (hp)"				
                    ::= { digitalObjects 83 }				
				
        -- 1.3.6.1.4.1.9839.2.1.1.84				
        v_digit84 OBJECT-TYPE				
                    SYNTAX Integer32 (0..1)				
                    UNITS "N/A"				
                    MAX-ACCESS read-only				
                    STATUS current				
                    DESCRIPTION "Humidity alarm (hp)"				
                    ::= { digitalObjects 84 }				
				
        -- 1.3.6.1.4.1.9839.2.1.1.85				
        v_digit85 OBJECT-TYPE				
                    SYNTAX Integer32 (0..1)				
                    UNITS "N/A"				
                    MAX-ACCESS read-only				
                    STATUS current				
                    DESCRIPTION "Air flow loss/main fan (hp)"				
                    ::= { digitalObjects 85 }				
				
        -- 1.3.6.1.4.1.9839.2.1.1.86				
        v_digit86 OBJECT-TYPE				
                    SYNTAX Integer32 (0..1)				
                    UNITS "N/A"				
                    MAX-ACCESS read-only				
                    STATUS current				
                    DESCRIPTION "Air filters or maint.alarm"				
                    ::= { digitalObjects 86 }				
				
        -- 1.3.6.1.4.1.9839.2.1.1.101				
        req_res_alarm OBJECT-TYPE				
                    SYNTAX Integer32 (0..1)				
                    UNITS "N/A"				
                    MAX-ACCESS read-write				
                    STATUS current				
                    DESCRIPTION "Alarm reset command"				
                    ::= { digitalObjects 101 }				
				
        -- 1.3.6.1.4.1.9839.2.1.1.110				
        en_buzzer OBJECT-TYPE				
                    SYNTAX Integer32 (0..1)				
                    UNITS "N/A"				
                    MAX-ACCESS read-only				
                    STATUS current				
                    DESCRIPTION "Buzzer enable"				
                    ::= { digitalObjects 110 }				
				
        -- 1.3.6.1.4.1.9839.2.1.1.112				
        disable_humid OBJECT-TYPE				
                    SYNTAX Integer32 (0..1)				
                    UNITS "N/A"				
                    MAX-ACCESS read-only				
                    STATUS current				
                    DESCRIPTION "Integrated humidifier disable"				
                    ::= { digitalObjects 112 }				
				
        -- 1.3.6.1.4.1.9839.2.1.1.113				
        type_drain OBJECT-TYPE				
                    SYNTAX Integer32 (0..1)				
                    UNITS "N/A"				
                    MAX-ACCESS read-only				
                    STATUS current				
                    DESCRIPTION "Discharge type"				
                    ::= { digitalObjects 113 }				
				
        -- 1.3.6.1.4.1.9839.2.1.1.114				
        en_clock OBJECT-TYPE				
                    SYNTAX Integer32 (0..1)				
                    UNITS "N/A"				
                    MAX-ACCESS read-only				
                    STATUS current				
                    DESCRIPTION "Watch enable"				
                    ::= { digitalObjects 114 }				
				
        -- 1.3.6.1.4.1.9839.2.1.1.115				
        logic_alarm1 OBJECT-TYPE				
                    SYNTAX Integer32 (0..1)				
                    UNITS "N/A"				
                    MAX-ACCESS read-only				
                    STATUS current				
                    DESCRIPTION "General alarm 1 relay logic"				
                    ::= { digitalObjects 115 }				
				
        -- 1.3.6.1.4.1.9839.2.1.1.116				
        logic_alarm2 OBJECT-TYPE				
                    SYNTAX Integer32 (0..1)				
                    UNITS "N/A"				
                    MAX-ACCESS read-only				
                    STATUS current				
                    DESCRIPTION "General alarm 2 relay logic"				
                    ::= { digitalObjects 116 }				
				
        -- 1.3.6.1.4.1.9839.2.1.1.117				
        valve_logic OBJECT-TYPE				
                    SYNTAX Integer32 (0..1)				
                    UNITS "N/A"				
                    MAX-ACCESS read-only				
                    STATUS current				
                    DESCRIPTION "Hot-cold valve logic (0-10 or 10-0v)"				
                    ::= { digitalObjects 117 }				
				
        -- 1.3.6.1.4.1.9839.2.1.1.118				
        en_time_zones OBJECT-TYPE				
                    SYNTAX Integer32 (0..1)				
                    UNITS "N/A"				
                    MAX-ACCESS read-only				
                    STATUS current				
                    DESCRIPTION "Daily timezone enable"				
                    ::= { digitalObjects 118 }				
				
        -- 1.3.6.1.4.1.9839.2.1.1.119				
        on_off_boss OBJECT-TYPE				
                    SYNTAX Integer32 (0..1)				
                    UNITS "N/A"				
                    MAX-ACCESS read-write				
                    STATUS current				
                    DESCRIPTION "Unit active on-off"				
                    ::= { digitalObjects 119 }				
				
        -- 1.3.6.1.4.1.9839.2.1.1.120				
        en_ext_air OBJECT-TYPE				
                    SYNTAX Integer32 (0..1)				
                    UNITS "N/A"				
                    MAX-ACCESS read-only				
                    STATUS current				
                    DESCRIPTION "External air probe enable"				
                    ::= { digitalObjects 120 }				
				
        -- 1.3.6.1.4.1.9839.2.1.1.121				
        en_unloader OBJECT-TYPE				
                    SYNTAX Integer32 (0..1)				
                    UNITS "N/A"				
                    MAX-ACCESS read-only				
                    STATUS current				
                    DESCRIPTION "Capacity control enable"				
                    ::= { digitalObjects 121 }				
				
        -- 1.3.6.1.4.1.9839.2.1.1.123				
        en_out_water OBJECT-TYPE				
                    SYNTAX Integer32 (0..1)				
                    UNITS "N/A"				
                    MAX-ACCESS read-only				
                    STATUS current				
                    DESCRIPTION "Outlet water temp. enable"				
                    ::= { digitalObjects 123 }				
				
        -- 1.3.6.1.4.1.9839.2.1.1.124				
        en_supply_air OBJECT-TYPE				
                    SYNTAX Integer32 (0..1)				
                    UNITS "N/A"				
                    MAX-ACCESS read-only				
                    STATUS current				
                    DESCRIPTION "Supply air probe enable"				
                    ::= { digitalObjects 124 }				
				
        -- 1.3.6.1.4.1.9839.2.1.1.125				
        en_in_water OBJECT-TYPE				
                    SYNTAX Integer32 (0..1)				
                    UNITS "N/A"				
                    MAX-ACCESS read-only				
                    STATUS current				
                    DESCRIPTION "Inlet water temp. enable"				
                    ::= { digitalObjects 125 }				
				
        -- 1.3.6.1.4.1.9839.2.1.1.126				
        en_cool_d3p OBJECT-TYPE				
                    SYNTAX Integer32 (0..1)				
                    UNITS "N/A"				
                    MAX-ACCESS read-only				
                    STATUS current				
                    DESCRIPTION "Float cool.valve enable"				
                    ::= { digitalObjects 126 }				
				
        -- 1.3.6.1.4.1.9839.2.1.1.127				
        en_heat_d3p OBJECT-TYPE				
                    SYNTAX Integer32 (0..1)				
                    UNITS "N/A"				
                    MAX-ACCESS read-only				
                    STATUS current				
                    DESCRIPTION "Float heat. valve enable"				
                    ::= { digitalObjects 127 }				
				
        -- 1.3.6.1.4.1.9839.2.1.1.128				
        en_off_keyboard OBJECT-TYPE				
                    SYNTAX Integer32 (0..1)				
                    UNITS "N/A"				
                    MAX-ACCESS read-only				
                    STATUS current				
                    DESCRIPTION "On/Off from keyboard enable"				
                    ::= { digitalObjects 128 }				
				
        -- 1.3.6.1.4.1.9839.2.1.1.130				
        en_room_humid OBJECT-TYPE				
                    SYNTAX Integer32 (0..1)				
                    UNITS "N/A"				
                    MAX-ACCESS read-only				
                    STATUS current				
                    DESCRIPTION "Humidity probe enable"				
                    ::= { digitalObjects 130 }				
				
        -- 1.3.6.1.4.1.9839.2.1.1.131				
        stand_alone OBJECT-TYPE				
                    SYNTAX Integer32 (0..1)				
                    UNITS "N/A"				
                    MAX-ACCESS read-only				
                    STATUS current				
                    DESCRIPTION "Master rotation enable (LAN)"				
                    ::= { digitalObjects 131 }				
				
        -- 1.3.6.1.4.1.9839.2.1.1.132				
        reset_sequence OBJECT-TYPE				
                    SYNTAX Integer32 (0..1)				
                    UNITS "N/A"				
                    MAX-ACCESS read-only				
                    STATUS current				
                    DESCRIPTION "Master rotation restart (LAN)"				
                    ::= { digitalObjects 132 }				
				
        -- 1.3.6.1.4.1.9839.2.1.1.133				
        en_integr_humid OBJECT-TYPE				
                    SYNTAX Integer32 (0..1)				
                    UNITS "N/A"				
                    MAX-ACCESS read-only				
                    STATUS current				
                    DESCRIPTION "Integrated humidifier enable"				
                    ::= { digitalObjects 133 }				
				
        -- 1.3.6.1.4.1.9839.2.1.1.134				
        logic_unloader OBJECT-TYPE				
                    SYNTAX Integer32 (0..1)				
                    UNITS "N/A"				
                    MAX-ACCESS read-only				
                    STATUS current				
                    DESCRIPTION "Capacity control logic"				
                    ::= { digitalObjects 134 }				
				
        -- 1.3.6.1.4.1.9839.2.1.1.136				
        reverse_cool OBJECT-TYPE				
                    SYNTAX Integer32 (0..1)				
                    UNITS "N/A"				
                    MAX-ACCESS read-only				
                    STATUS current				
                    DESCRIPTION "Float cool. valve logic"				
                    ::= { digitalObjects 136 }				
				
        -- 1.3.6.1.4.1.9839.2.1.1.137				
        en_inp8_board2 OBJECT-TYPE				
                    SYNTAX Integer32 (0..1)				
                    UNITS "N/A"				
                    MAX-ACCESS read-only				
                    STATUS current				
                    DESCRIPTION "Input B8 board 2 enable (no hp)"				
                    ::= { digitalObjects 137 }				
				
        -- 1.3.6.1.4.1.9839.2.1.1.138				
        v_digit138 OBJECT-TYPE				
                    SYNTAX Integer32 (0..1)				
                    UNITS "N/A"				
                    MAX-ACCESS read-only				
                    STATUS current				
                    DESCRIPTION "Main fan status during defrost."				
                    ::= { digitalObjects 138 }				
				
        -- 1.3.6.1.4.1.9839.2.1.1.139				
        v_digit139 OBJECT-TYPE				
                    SYNTAX Integer32 (0..1)				
                    UNITS "N/A"				
                    MAX-ACCESS read-only				
                    STATUS current				
                    DESCRIPTION "Condensation fan enable (hp)"				
                    ::= { digitalObjects 139 }				
				
        -- 1.3.6.1.4.1.9839.2.1.1.140				
        phases_n OBJECT-TYPE				
                    SYNTAX Integer32 (0..1)				
                    UNITS "N/A"				
                    MAX-ACCESS read-only				
                    STATUS current				
                    DESCRIPTION "Number of phases of integrated humidifier"				
                    ::= { digitalObjects 140 }				
				
        -- 1.3.6.1.4.1.9839.2.1.1.141				
        v_digit141 OBJECT-TYPE				
                    SYNTAX Integer32 (0..1)				
                    UNITS "N/A"				
                    MAX-ACCESS read-only				
                    STATUS current				
                    DESCRIPTION "Type of freon (hp)"				
                    ::= { digitalObjects 141 }				
				
        -- 1.3.6.1.4.1.9839.2.1.1.142				
        en_inp7_board2 OBJECT-TYPE				
                    SYNTAX Integer32 (0..1)				
                    UNITS "N/A"				
                    MAX-ACCESS read-only				
                    STATUS current				
                    DESCRIPTION "Input B7 board 2 enable (no for hp)"				
                    ::= { digitalObjects 142 }				
				
        -- 1.3.6.1.4.1.9839.2.1.1.145				
        open_cool_fl OBJECT-TYPE				
                    SYNTAX Integer32 (0..1)				
                    UNITS "N/A"				
                    MAX-ACCESS read-write				
                    STATUS current				
                    DESCRIPTION "Enable cooling valve manual opening of 3-point (no for hp)"				
                    ::= { digitalObjects 145 }				
				
        -- 1.3.6.1.4.1.9839.2.1.1.146				
        close_cool_fl OBJECT-TYPE				
                    SYNTAX Integer32 (0..1)				
                    UNITS "N/A"				
                    MAX-ACCESS read-write				
                    STATUS current				
                    DESCRIPTION "Enable cooling valve manual closing of 3-point (no for hp)"				
                    ::= { digitalObjects 146 }				
				
        -- 1.3.6.1.4.1.9839.2.1.1.147				
        open_heat_fl OBJECT-TYPE				
                    SYNTAX Integer32 (0..1)				
                    UNITS "N/A"				
                    MAX-ACCESS read-write				
                    STATUS current				
                    DESCRIPTION "Enable heating valve manual opening of 3-point (no for hp)"				
                    ::= { digitalObjects 147 }				
				
        -- 1.3.6.1.4.1.9839.2.1.1.148				
        close_heat_fl OBJECT-TYPE				
                    SYNTAX Integer32 (0..1)				
                    UNITS "N/A"				
                    MAX-ACCESS read-write				
                    STATUS current				
                    DESCRIPTION "Enable heating valve manual closing of 3-point  (no for hp)"				
                    ::= { digitalObjects 148 }				
				
        -- 1.3.6.1.4.1.9839.2.1.1.150				
        stop_humid OBJECT-TYPE				
                    SYNTAX Integer32 (0..1)				
                    UNITS "N/A"				
                    MAX-ACCESS read-only				
                    STATUS current				
                    DESCRIPTION "Reduce humidif.in cool position"				
                    ::= { digitalObjects 150 }				
				
        -- 1.3.6.1.4.1.9839.2.1.1.151				
        stop_in_alarm OBJECT-TYPE				
                    SYNTAX Integer32 (0..1)				
                    UNITS "N/A"				
                    MAX-ACCESS read-only				
                    STATUS current				
                    DESCRIPTION "Stop unit in alarm"				
                    ::= { digitalObjects 151 }				
				
        -- 1.3.6.1.4.1.9839.2.1.1.152				
        manual_drain OBJECT-TYPE				
                    SYNTAX Integer32 (0..1)				
                    UNITS "N/A"				
                    MAX-ACCESS read-only				
                    STATUS current				
                    DESCRIPTION "Manual discharge enable"				
                    ::= { digitalObjects 152 }				
				
        -- 1.3.6.1.4.1.9839.2.1.1.153				
        en_valve OBJECT-TYPE				
                    SYNTAX Integer32 (0..1)				
                    UNITS "N/A"				
                    MAX-ACCESS read-only				
                    STATUS current				
                    DESCRIPTION "Hot / cold 0-10 volt valve board 1 present "				
                    ::= { digitalObjects 153 }				
				
        -- 1.3.6.1.4.1.9839.2.1.1.154				
        v_digit154 OBJECT-TYPE				
                    SYNTAX Integer32 (0..1)				
                    UNITS "N/A"				
                    MAX-ACCESS read-only				
                    STATUS current				
                    DESCRIPTION "Air delivery temp. probe on circuit 2"				
                    ::= { digitalObjects 154 }				
				
        -- 1.3.6.1.4.1.9839.2.1.1.155				
        en_pressure OBJECT-TYPE				
                    SYNTAX Integer32 (0..1)				
                    UNITS "N/A"				
                    MAX-ACCESS read-only				
                    STATUS current				
                    DESCRIPTION "Pressure probe enable"				
                    ::= { digitalObjects 155 }				
				
        -- 1.3.6.1.4.1.9839.2.1.1.158				
        en_limit_therm OBJECT-TYPE				
                    SYNTAX Integer32 (0..1)				
                    UNITS "N/A"				
                    MAX-ACCESS read-only				
                    STATUS current				
                    DESCRIPTION "Limit thermostat enable"				
                    ::= { digitalObjects 158 }				
				
        -- 1.3.6.1.4.1.9839.2.1.1.167				
        v_digit167 OBJECT-TYPE				
                    SYNTAX Integer32 (0..1)				
                    UNITS "N/A"				
                    MAX-ACCESS read-only				
                    STATUS current				
                    DESCRIPTION "Enable line voltage / Enable line voltage on input B7 board 1, hp"				
                    ::= { digitalObjects 167 }				
				
        -- 1.3.6.1.4.1.9839.2.1.1.168				
        v_digit168 OBJECT-TYPE				
                    SYNTAX Integer32 (0..1)				
                    UNITS "N/A"				
                    MAX-ACCESS read-only				
                    STATUS current				
                    DESCRIPTION "Analogue input B7 board 1 present"				
                    ::= { digitalObjects 168 }				
				
        -- 1.3.6.1.4.1.9839.2.1.1.171				
        syson OBJECT-TYPE				
                    SYNTAX Integer32 (0..1)				
                    UNITS "N/A"				
                    MAX-ACCESS read-only				
                    STATUS current				
                    DESCRIPTION "Machine status on/off (no with lock unit)"				
                    ::= { digitalObjects 171 }				
				
        -- 1.3.6.1.4.1.9839.2.1.1.173				
        v_digit173 OBJECT-TYPE				
                    SYNTAX Integer32 (0..1)				
                    UNITS "N/A"				
                    MAX-ACCESS read-only				
                    STATUS current				
                    DESCRIPTION "Compressor 1 enable"				
                    ::= { digitalObjects 173 }				
				
        -- 1.3.6.1.4.1.9839.2.1.1.174				
        en_comp2 OBJECT-TYPE				
                    SYNTAX Integer32 (0..1)				
                    UNITS "N/A"				
                    MAX-ACCESS read-only				
                    STATUS current				
                    DESCRIPTION "Compressor 2 enable"				
                    ::= { digitalObjects 174 }				
				
        -- 1.3.6.1.4.1.9839.2.1.1.175				
        en_heater1 OBJECT-TYPE				
                    SYNTAX Integer32 (0..1)				
                    UNITS "N/A"				
                    MAX-ACCESS read-only				
                    STATUS current				
                    DESCRIPTION "Heater 1 enable (hp)"				
                    ::= { digitalObjects 175 }				
				
        -- 1.3.6.1.4.1.9839.2.1.1.176				
        en_heater2 OBJECT-TYPE				
                    SYNTAX Integer32 (0..1)				
                    UNITS "N/A"				
                    MAX-ACCESS read-only				
                    STATUS current				
                    DESCRIPTION "Heater 2 enable (no for hp)"				
                    ::= { digitalObjects 176 }				
				
        -- 1.3.6.1.4.1.9839.2.1.1.177				
        en_heater_bin OBJECT-TYPE				
                    SYNTAX Integer32 (0..1)				
                    UNITS "N/A"				
                    MAX-ACCESS read-only				
                    STATUS current				
                    DESCRIPTION "Enable signal to Heaters with binary activation mode (no for hp)"				
                    ::= { digitalObjects 177 }				
				
        -- 1.3.6.1.4.1.9839.2.1.1.180				
        two_circuits OBJECT-TYPE				
                    SYNTAX Integer32 (0..1)				
                    UNITS "N/A"				
                    MAX-ACCESS read-only				
                    STATUS current				
                    DESCRIPTION "Enable two refrigeration circuits"				
                    ::= { digitalObjects 180 }				
				
				
				
        -- 1.3.6.1.4.1.9839.2.1.2				
        analogObjects OBJECT IDENTIFIER ::= { aarc_normMIB 2 }				
				
        -- 1.3.6.1.4.1.9839.2.1.2.1				
        unit_type OBJECT-TYPE				
                    SYNTAX Integer32 (0..270)				
                    UNITS "N/A"				
                    MAX-ACCESS read-only				
                    STATUS current				
                    DESCRIPTION "Unit type (7=Enertel; 8=Pegasus; etc.)"				
                    ::= { analogObjects 1 }				
				
        -- 1.3.6.1.4.1.9839.2.1.2.2				
        room_temp OBJECT-TYPE				
                    SYNTAX Integer32 (-450..900)				
                    UNITS "°C x10"				
                    MAX-ACCESS read-only				
                    STATUS current				
                    DESCRIPTION "Ambient air temperature"				
                    ::= { analogObjects 2 }				
				
        -- 1.3.6.1.4.1.9839.2.1.2.3				
        supply_air_temp OBJECT-TYPE				
                    SYNTAX Integer32 (-450..900)				
                    UNITS "°C x10"				
                    MAX-ACCESS read-only				
                    STATUS current				
                    DESCRIPTION "Supply air temp. circuit 1"				
                    ::= { analogObjects 3 }				
				
        -- 1.3.6.1.4.1.9839.2.1.2.4				
        out_water_temp OBJECT-TYPE				
                    SYNTAX Integer32 (-450..900)				
                    UNITS "°C x10"				
                    MAX-ACCESS read-only				
                    STATUS current				
                    DESCRIPTION "Supply air temp.circuit 2 / Outlet water temp.circuit 1 (hp)"				
                    ::= { analogObjects 4 }				
				
        -- 1.3.6.1.4.1.9839.2.1.2.5				
        ext_air_temp OBJECT-TYPE				
                    SYNTAX Integer32 (-450..900)				
                    UNITS "°C x10"				
                    MAX-ACCESS read-only				
                    STATUS current				
                    DESCRIPTION "External air temp. / Inlet water temp."				
                    ::= { analogObjects 5 }				
				
        -- 1.3.6.1.4.1.9839.2.1.2.6				
        v_analog6 OBJECT-TYPE				
                    SYNTAX Integer32 (-450..900)				
                    UNITS "°C x10"				
                    MAX-ACCESS read-only				
                    STATUS current				
                    DESCRIPTION "Supply air temp.circuit 2 (hp)"				
                    ::= { analogObjects 6 }				
				
        -- 1.3.6.1.4.1.9839.2.1.2.7				
        pressure1 OBJECT-TYPE				
                    SYNTAX Integer32 (0..34000)				
                    UNITS "kPa x10"				
                    MAX-ACCESS read-only				
                    STATUS current				
                    DESCRIPTION "High pressure circuit 1 (data * 10)"				
                    ::= { analogObjects 7 }				
				
        -- 1.3.6.1.4.1.9839.2.1.2.8				
        pressure2 OBJECT-TYPE				
                    SYNTAX Integer32 (0..34000)				
                    UNITS "kPa x10"				
                    MAX-ACCESS read-only				
                    STATUS current				
                    DESCRIPTION "High pressure circuit 2 (data * 10)"				
                    ::= { analogObjects 8 }				
				
        -- 1.3.6.1.4.1.9839.2.1.2.9				
        increase_perc OBJECT-TYPE				
                    SYNTAX Integer32 (0..100)				
                    UNITS "°C x10"				
                    MAX-ACCESS read-only				
                    STATUS current				
                    DESCRIPTION "Set-point compensation"				
                    ::= { analogObjects 9 }				
				
        -- 1.3.6.1.4.1.9839.2.1.2.10				
        line_voltage OBJECT-TYPE				
                    SYNTAX Integer32 (0..15000)				
                    UNITS "kPa x10"				
                    MAX-ACCESS read-only				
                    STATUS current				
                    DESCRIPTION "Suction pressure circuit 2 hp (data * 10)"				
                    ::= { analogObjects 10 }				
				
        -- 1.3.6.1.4.1.9839.2.1.2.11				
        v_analog11 OBJECT-TYPE				
                    SYNTAX Integer32 (-450..900)				
                    UNITS "°C x10"				
                    MAX-ACCESS read-only				
                    STATUS current				
                    DESCRIPTION "Outlet water circuit 2"				
                    ::= { analogObjects 11 }				
				
        -- 1.3.6.1.4.1.9839.2.1.2.12				
        v_analog12 OBJECT-TYPE				
                    SYNTAX Integer32 (0..15000)				
                    UNITS "kPa x10"				
                    MAX-ACCESS read-only				
                    STATUS current				
                    DESCRIPTION "Suction pressure circuit 1 hp (data * 10)"				
                    ::= { analogObjects 12 }				
				
        -- 1.3.6.1.4.1.9839.2.1.2.13				
        v_analog13 OBJECT-TYPE				
                    SYNTAX Integer32 (-450..900)				
                    UNITS "°C x10"				
                    MAX-ACCESS read-only				
                    STATUS current				
                    DESCRIPTION "Saturated gas temp.circuit 1 (hp)"				
                    ::= { analogObjects 13 }				
				
        -- 1.3.6.1.4.1.9839.2.1.2.14				
        v_analog14 OBJECT-TYPE				
                    SYNTAX Integer32 (-450..900)				
                    UNITS "°C x10"				
                    MAX-ACCESS read-only				
                    STATUS current				
                    DESCRIPTION "Saturated gas temp.circuit 2 (hp)"				
                    ::= { analogObjects 14 }				
				
        -- 1.3.6.1.4.1.9839.2.1.2.15				
        set_temp OBJECT-TYPE				
                    SYNTAX Integer32 (0..500)				
                    UNITS "°C x10"				
                    MAX-ACCESS read-only				
                    STATUS current				
                    DESCRIPTION "Effective air temp. Set-point"				
                    ::= { analogObjects 15 }				
				
        -- 1.3.6.1.4.1.9839.2.1.2.16				
        sel_set_temp OBJECT-TYPE				
                    SYNTAX Integer32 (50..350)				
                    UNITS "°C x10"				
                    MAX-ACCESS read-write				
                    STATUS current				
                    DESCRIPTION "Air temperature Set-point"				
                    ::= { analogObjects 16 }				
				
        -- 1.3.6.1.4.1.9839.2.1.2.17				
        line_current7_2 OBJECT-TYPE				
                    SYNTAX Integer32 (0..5000)				
                    UNITS "A x10"				
                    MAX-ACCESS read-only				
                    STATUS current				
                    DESCRIPTION "Value of input B7 board 2"				
                    ::= { analogObjects 17 }				
				
        -- 1.3.6.1.4.1.9839.2.1.2.18				
        man_cooling OBJECT-TYPE				
                    SYNTAX Integer32 (0..100)				
                    UNITS "Vdc x10"				
                    MAX-ACCESS read-write				
                    STATUS current				
                    DESCRIPTION "Man Opening cool.valve 0-10v"				
                    ::= { analogObjects 18 }				
				
        -- 1.3.6.1.4.1.9839.2.1.2.19				
        man_heating OBJECT-TYPE				
                    SYNTAX Integer32 (0..100)				
                    UNITS "Vdc x10"				
                    MAX-ACCESS read-write				
                    STATUS current				
                    DESCRIPTION "Man Opening heat.valve 0-10v"				
                    ::= { analogObjects 19 }				
				
        -- 1.3.6.1.4.1.9839.2.1.2.20				
        v_analog20 OBJECT-TYPE				
                    SYNTAX Integer32 (-450..900)				
                    UNITS "°C x10"				
                    MAX-ACCESS read-only				
                    STATUS current				
                    DESCRIPTION "Memo.gas temp.circuit 1 (hp)"				
                    ::= { analogObjects 20 }				
				
        -- 1.3.6.1.4.1.9839.2.1.2.21				
        v_analog21 OBJECT-TYPE				
                    SYNTAX Integer32 (-450..900)				
                    UNITS "°C x10"				
                    MAX-ACCESS read-only				
                    STATUS current				
                    DESCRIPTION "Memo.gas temp.circuit 2 (hp)"				
                    ::= { analogObjects 21 }				
				
        -- 1.3.6.1.4.1.9839.2.1.2.32				
        v_analog32 OBJECT-TYPE				
                    SYNTAX Integer32 (-32767..32767)				
                    UNITS "°C x10"				
                    MAX-ACCESS read-only				
                    STATUS current				
                    DESCRIPTION "Water limit therm.threshold (hp)"				
                    ::= { analogObjects 32 }				
				
        -- 1.3.6.1.4.1.9839.2.1.2.33				
        h_pre_room_temp OBJECT-TYPE				
                    SYNTAX Integer32 (-32767..32767)				
                    UNITS "°C x10"				
                    MAX-ACCESS read-only				
                    STATUS current				
                    DESCRIPTION "High air temp.pre-alarm"				
                    ::= { analogObjects 33 }				
				
        -- 1.3.6.1.4.1.9839.2.1.2.34				
        thr_limit_therm OBJECT-TYPE				
                    SYNTAX Integer32 (-32767..32767)				
                    UNITS "°C x10"				
                    MAX-ACCESS read-only				
                    STATUS current				
                    DESCRIPTION "Air Limit therm.threshold"				
                    ::= { analogObjects 34 }				
				
        -- 1.3.6.1.4.1.9839.2.1.2.35				
        min_inverter OBJECT-TYPE				
                    SYNTAX Integer32 (-32767..32767)				
                    UNITS "v x10"				
                    MAX-ACCESS read-only				
                    STATUS current				
                    DESCRIPTION "Condens.out. Min value"				
                    ::= { analogObjects 35 }				
				
        -- 1.3.6.1.4.1.9839.2.1.2.36				
        max_inverter OBJECT-TYPE				
                    SYNTAX Integer32 (-32767..32767)				
                    UNITS "v x10"				
                    MAX-ACCESS read-only				
                    STATUS current				
                    DESCRIPTION "Condens.out. Max value"				
                    ::= { analogObjects 36 }				
				
        -- 1.3.6.1.4.1.9839.2.1.2.37				
        delta_setpoint OBJECT-TYPE				
                    SYNTAX Integer32 (-32767..32767)				
                    UNITS "°C x10"				
                    MAX-ACCESS read-only				
                    STATUS current				
                    DESCRIPTION "Compensation set-point"				
                    ::= { analogObjects 37 }				
				
        -- 1.3.6.1.4.1.9839.2.1.2.38				
        low_room_temp OBJECT-TYPE				
                    SYNTAX Integer32 (-32767..32767)				
                    UNITS "°C x10"				
                    MAX-ACCESS read-only				
                    STATUS current				
                    DESCRIPTION "Low air temp. alarm"				
                    ::= { analogObjects 38 }				
				
        -- 1.3.6.1.4.1.9839.2.1.2.39				
        high_room_temp OBJECT-TYPE				
                    SYNTAX Integer32 (-32767..32767)				
                    UNITS "°C x10"				
                    MAX-ACCESS read-only				
                    STATUS current				
                    DESCRIPTION "High air temp. alarm"				
                    ::= { analogObjects 39 }				
				
        -- 1.3.6.1.4.1.9839.2.1.2.40				
        low_room_humid OBJECT-TYPE				
                    SYNTAX Integer32 (-32767..32767)				
                    UNITS "%rH x10"				
                    MAX-ACCESS read-only				
                    STATUS current				
                    DESCRIPTION "Low humidity alarm"				
                    ::= { analogObjects 40 }				
				
        -- 1.3.6.1.4.1.9839.2.1.2.41				
        high_room_humid OBJECT-TYPE				
                    SYNTAX Integer32 (-32767..32767)				
                    UNITS "%rH x10"				
                    MAX-ACCESS read-only				
                    STATUS current				
                    DESCRIPTION "High humidity alarm"				
                    ::= { analogObjects 41 }				
				
        -- 1.3.6.1.4.1.9839.2.1.2.42				
        lim_min_set_t OBJECT-TYPE				
                    SYNTAX Integer32 (-32767..32767)				
                    UNITS "°C x10"				
                    MAX-ACCESS read-only				
                    STATUS current				
                    DESCRIPTION "Temp.setpoint min limit"				
                    ::= { analogObjects 42 }				
				
        -- 1.3.6.1.4.1.9839.2.1.2.43				
        lim_max_set_t OBJECT-TYPE				
                    SYNTAX Integer32 (-32767..32767)				
                    UNITS "°C x10"				
                    MAX-ACCESS read-only				
                    STATUS current				
                    DESCRIPTION "Temp.setpoint max limit"				
                    ::= { analogObjects 43 }				
				
        -- 1.3.6.1.4.1.9839.2.1.2.44				
        thr_heater3 OBJECT-TYPE				
                    SYNTAX Integer32 (-32767..32767)				
                    UNITS "°C x10"				
                    MAX-ACCESS read-only				
                    STATUS current				
                    DESCRIPTION "Step heater 3 stage On"				
                    ::= { analogObjects 44 }				
				
        -- 1.3.6.1.4.1.9839.2.1.2.45				
        hys_heater3 OBJECT-TYPE				
                    SYNTAX Integer32 (-32767..32767)				
                    UNITS "°C x10"				
                    MAX-ACCESS read-only				
                    STATUS current				
                    DESCRIPTION "Step heater 3 differential"				
                    ::= { analogObjects 45 }				
				
        -- 1.3.6.1.4.1.9839.2.1.2.46				
        thr_unload1 OBJECT-TYPE				
                    SYNTAX Integer32 (-32767..32767)				
                    UNITS "°C x10"				
                    MAX-ACCESS read-only				
                    STATUS current				
                    DESCRIPTION "Step unload.compr.1 stage On"				
                    ::= { analogObjects 46 }				
				
        -- 1.3.6.1.4.1.9839.2.1.2.47				
        hys_unload1 OBJECT-TYPE				
                    SYNTAX Integer32 (-32767..32767)				
                    UNITS "°C x10"				
                    MAX-ACCESS read-only				
                    STATUS current				
                    DESCRIPTION "Step unloader compr. 1 diff."				
                    ::= { analogObjects 47 }				
				
        -- 1.3.6.1.4.1.9839.2.1.2.48				
        thr_unload2 OBJECT-TYPE				
                    SYNTAX Integer32 (-32767..32767)				
                    UNITS "°C x10"				
                    MAX-ACCESS read-only				
                    STATUS current				
                    DESCRIPTION "Step unload.compr.2 stage On"				
                    ::= { analogObjects 48 }				
				
        -- 1.3.6.1.4.1.9839.2.1.2.49				
        hys_unload2 OBJECT-TYPE				
                    SYNTAX Integer32 (-32767..32767)				
                    UNITS "°C x10"				
                    MAX-ACCESS read-only				
                    STATUS current				
                    DESCRIPTION "Step unloader compr. 2 diff."				
                    ::= { analogObjects 49 }				
				
        -- 1.3.6.1.4.1.9839.2.1.2.60				
        hys_comp1 OBJECT-TYPE				
                    SYNTAX Integer32 (-32767..32767)				
                    UNITS "°C x10"				
                    MAX-ACCESS read-only				
                    STATUS current				
                    DESCRIPTION "Step compr.1 differential"				
                    ::= { analogObjects 60 }				
				
        -- 1.3.6.1.4.1.9839.2.1.2.61				
        hys_comp2 OBJECT-TYPE				
                    SYNTAX Integer32 (-32767..32767)				
                    UNITS "°C x10"				
                    MAX-ACCESS read-only				
                    STATUS current				
                    DESCRIPTION "Step compr.2 differential"				
                    ::= { analogObjects 61 }				
				
        -- 1.3.6.1.4.1.9839.2.1.2.62				
        thr_heater1 OBJECT-TYPE				
                    SYNTAX Integer32 (-32767..32767)				
                    UNITS "°C x10"				
                    MAX-ACCESS read-only				
                    STATUS current				
                    DESCRIPTION "Step heater 1 stage On"				
                    ::= { analogObjects 62 }				
				
        -- 1.3.6.1.4.1.9839.2.1.2.92				
        supervisor_code OBJECT-TYPE				
                    SYNTAX Integer32 (-32767..32767)				
                    UNITS "N/A"				
                    MAX-ACCESS read-only				
                    STATUS current				
                    DESCRIPTION "Parameters code"				
                    ::= { analogObjects 92 }				
				
				
				
        -- 1.3.6.1.4.1.9839.2.1.3				
        integerObjects OBJECT IDENTIFIER ::= { aarc_normMIB 3 }				
				
        -- 1.3.6.1.4.1.9839.2.1.3.1				
        room_humid OBJECT-TYPE				
                    SYNTAX Integer32 (0..100)				
                    UNITS "%rH"				
                    MAX-ACCESS read-only				
                    STATUS current				
                    DESCRIPTION "Ambient air humidity"				
                    ::= { integerObjects 1 }				
				
        -- 1.3.6.1.4.1.9839.2.1.3.3				
        in_b8_board1 OBJECT-TYPE				
                    SYNTAX Integer32 (0..600)				
                    UNITS "N/A"				
                    MAX-ACCESS read-only				
                    STATUS current				
                    DESCRIPTION "Value of input B8 board 1; current or voltage line"				
                    ::= { integerObjects 3 }				
				
        -- 1.3.6.1.4.1.9839.2.1.3.4				
        out_condens1 OBJECT-TYPE				
                    SYNTAX Integer32 (0..100)				
                    UNITS "%"				
                    MAX-ACCESS read-only				
                    STATUS current				
                    DESCRIPTION "Value output 0-100% for condensation control circuit 1"				
                    ::= { integerObjects 4 }				
				
        -- 1.3.6.1.4.1.9839.2.1.3.5				
        out_condens2 OBJECT-TYPE				
                    SYNTAX Integer32 (0..100)				
                    UNITS "%"				
                    MAX-ACCESS read-only				
                    STATUS current				
                    DESCRIPTION "Value output 0-100% for condensation control circuit 2"				
                    ::= { integerObjects 5 }				
				
        -- 1.3.6.1.4.1.9839.2.1.3.6				
        out_cooling OBJECT-TYPE				
                    SYNTAX Integer32 (0..100)				
                    UNITS "%"				
                    MAX-ACCESS read-only				
                    STATUS current				
                    DESCRIPTION "Value output 0-100% for cooling valve control (not for hp)"				
                    ::= { integerObjects 6 }				
				
        -- 1.3.6.1.4.1.9839.2.1.3.7				
        out_heating OBJECT-TYPE				
                    SYNTAX Integer32 (0..100)				
                    UNITS "%"				
                    MAX-ACCESS read-only				
                    STATUS current				
                    DESCRIPTION "Value output 0-100% for heating valve control (not for hp)"				
                    ::= { integerObjects 7 }				
				
        -- 1.3.6.1.4.1.9839.2.1.3.8				
        out_cool_heat OBJECT-TYPE				
                    SYNTAX Integer32 (0..100)				
                    UNITS "%"				
                    MAX-ACCESS read-only				
                    STATUS current				
                    DESCRIPTION "Heating/cooling valve"				
                    ::= { integerObjects 8 }				
				
        -- 1.3.6.1.4.1.9839.2.1.3.9				
        in_b7_board1 OBJECT-TYPE				
                    SYNTAX Integer32 (0..600)				
                    UNITS "N/A"				
                    MAX-ACCESS read-only				
                    STATUS current				
                    DESCRIPTION "Value of input B7 board 1;  line current, line voltage"				
                    ::= { integerObjects 9 }				
				
        -- 1.3.6.1.4.1.9839.2.1.3.10				
        mem_code_al1 OBJECT-TYPE				
                    SYNTAX Integer32 (0..36)				
                    UNITS "N/A"				
                    MAX-ACCESS read-only				
                    STATUS current				
                    DESCRIPTION "Last but 9 alarm memorized, 10° in the status list"				
                    ::= { integerObjects 10 }				
				
        -- 1.3.6.1.4.1.9839.2.1.3.11				
        mem_code_al2 OBJECT-TYPE				
                    SYNTAX Integer32 (0..36)				
                    UNITS "N/A"				
                    MAX-ACCESS read-only				
                    STATUS current				
                    DESCRIPTION "Last but 8 alarm memorized, 9° in the status list"				
                    ::= { integerObjects 11 }				
				
        -- 1.3.6.1.4.1.9839.2.1.3.12				
        mem_code_al3 OBJECT-TYPE				
                    SYNTAX Integer32 (0..36)				
                    UNITS "N/A"				
                    MAX-ACCESS read-only				
                    STATUS current				
                    DESCRIPTION "Last but 7 alarm memorized, 8° in the status list"				
                    ::= { integerObjects 12 }				
				
        -- 1.3.6.1.4.1.9839.2.1.3.13				
        mem_code_al4 OBJECT-TYPE				
                    SYNTAX Integer32 (0..36)				
                    UNITS "N/A"				
                    MAX-ACCESS read-only				
                    STATUS current				
                    DESCRIPTION "Last but 6 alarm memorized, 7° in the status list"				
                    ::= { integerObjects 13 }				
				
        -- 1.3.6.1.4.1.9839.2.1.3.14				
        mem_code_al5 OBJECT-TYPE				
                    SYNTAX Integer32 (0..36)				
                    UNITS "N/A"				
                    MAX-ACCESS read-only				
                    STATUS current				
                    DESCRIPTION "Last but 5 alarm memorized, 6° in the status list"				
                    ::= { integerObjects 14 }				
				
        -- 1.3.6.1.4.1.9839.2.1.3.15				
        mem_code_al6 OBJECT-TYPE				
                    SYNTAX Integer32 (0..36)				
                    UNITS "N/A"				
                    MAX-ACCESS read-only				
                    STATUS current				
                    DESCRIPTION "Last but 4 alarm memorized, 5° in the status list"				
                    ::= { integerObjects 15 }				
				
        -- 1.3.6.1.4.1.9839.2.1.3.16				
        mem_code_al7 OBJECT-TYPE				
                    SYNTAX Integer32 (0..36)				
                    UNITS "N/A"				
                    MAX-ACCESS read-only				
                    STATUS current				
                    DESCRIPTION "Last but 3 alarm memorized, 4° in the status list"				
                    ::= { integerObjects 16 }				
				
        -- 1.3.6.1.4.1.9839.2.1.3.17				
        mem_code_al8 OBJECT-TYPE				
                    SYNTAX Integer32 (0..36)				
                    UNITS "N/A"				
                    MAX-ACCESS read-only				
                    STATUS current				
                    DESCRIPTION "Last but 2 alarm memorized, 3° in the status list"				
                    ::= { integerObjects 17 }				
				
        -- 1.3.6.1.4.1.9839.2.1.3.18				
        mem_code_al9 OBJECT-TYPE				
                    SYNTAX Integer32 (0..36)				
                    UNITS "N/A"				
                    MAX-ACCESS read-only				
                    STATUS current				
                    DESCRIPTION "Last but 1 alarm memorized, second in the status list"				
                    ::= { integerObjects 18 }				
				
        -- 1.3.6.1.4.1.9839.2.1.3.19				
        mem_code_al10 OBJECT-TYPE				
                    SYNTAX Integer32 (0..36)				
                    UNITS "N/A"				
                    MAX-ACCESS read-only				
                    STATUS current				
                    DESCRIPTION "Last alarm memorized, fist in the status list"				
                    ::= { integerObjects 19 }				
				
        -- 1.3.6.1.4.1.9839.2.1.3.20				
        unit_status OBJECT-TYPE				
                    SYNTAX Integer32 (-32767..32767)				
                    UNITS "N/A"				
                    MAX-ACCESS read-only				
                    STATUS current				
                    DESCRIPTION "Unit status: 1=on; 7=off (ext.disable); 8=off (keyboard); etc."				
                    ::= { integerObjects 20 }				
				
        -- 1.3.6.1.4.1.9839.2.1.3.21				
        comp1_status OBJECT-TYPE				
                    SYNTAX Integer32 (0..2)				
                    UNITS "N/A"				
                    MAX-ACCESS read-write				
                    STATUS current				
                    DESCRIPTION "Compressor 1 or cooling 1 for heat pump hp"				
                    ::= { integerObjects 21 }				
				
        -- 1.3.6.1.4.1.9839.2.1.3.22				
        comp2_status OBJECT-TYPE				
                    SYNTAX Integer32 (0..2)				
                    UNITS "N/A"				
                    MAX-ACCESS read-write				
                    STATUS current				
                    DESCRIPTION "Compressor 2 or cooling 2 for heat pump hp"				
                    ::= { integerObjects 22 }				
				
        -- 1.3.6.1.4.1.9839.2.1.3.23				
        heater1_status OBJECT-TYPE				
                    SYNTAX Integer32 (0..2)				
                    UNITS "N/A"				
                    MAX-ACCESS read-write				
                    STATUS current				
                    DESCRIPTION "Heater 1"				
                    ::= { integerObjects 23 }				
				
        -- 1.3.6.1.4.1.9839.2.1.3.24				
        heater2_status OBJECT-TYPE				
                    SYNTAX Integer32 (0..2)				
                    UNITS "N/A"				
                    MAX-ACCESS read-write				
                    STATUS current				
                    DESCRIPTION "Heater 2"				
                    ::= { integerObjects 24 }				
				
        -- 1.3.6.1.4.1.9839.2.1.3.25				
        humid_status OBJECT-TYPE				
                    SYNTAX Integer32 (0..2)				
                    UNITS "N/A"				
                    MAX-ACCESS read-write				
                    STATUS current				
                    DESCRIPTION "Humidifier"				
                    ::= { integerObjects 25 }				
				
        -- 1.3.6.1.4.1.9839.2.1.3.26				
        dehumid_status OBJECT-TYPE				
                    SYNTAX Integer32 (0..2)				
                    UNITS "N/A"				
                    MAX-ACCESS read-write				
                    STATUS current				
                    DESCRIPTION "Dehumidifier"				
                    ::= { integerObjects 26 }				
				
        -- 1.3.6.1.4.1.9839.2.1.3.27				
        cool_status OBJECT-TYPE				
                    SYNTAX Integer32 (0..2)				
                    UNITS "N/A"				
                    MAX-ACCESS read-write				
                    STATUS current				
                    DESCRIPTION "Cooling valve status"				
                    ::= { integerObjects 27 }				
				
        -- 1.3.6.1.4.1.9839.2.1.3.28				
        heat_status OBJECT-TYPE				
                    SYNTAX Integer32 (0..2)				
                    UNITS "N/A"				
                    MAX-ACCESS read-write				
                    STATUS current				
                    DESCRIPTION "Heating valve status"				
                    ::= { integerObjects 28 }				
				
        -- 1.3.6.1.4.1.9839.2.1.3.29				
        cool_fl_status OBJECT-TYPE				
                    SYNTAX Integer32 (0..2)				
                    UNITS "N/A"				
                    MAX-ACCESS read-write				
                    STATUS current				
                    DESCRIPTION "3-point Cooling valve status (no for hp)"				
                    ::= { integerObjects 29 }				
				
        -- 1.3.6.1.4.1.9839.2.1.3.30				
        heat_fl_status OBJECT-TYPE				
                    SYNTAX Integer32 (0..2)				
                    UNITS "N/A"				
                    MAX-ACCESS read-write				
                    STATUS current				
                    DESCRIPTION "3-point Heating valve status (no for hp)"				
                    ::= { integerObjects 30 }				
				
        -- 1.3.6.1.4.1.9839.2.1.3.31				
        open_time_cool OBJECT-TYPE				
                    SYNTAX Integer32 (1..300)				
                    UNITS "s"				
                    MAX-ACCESS read-write				
                    STATUS current				
                    DESCRIPTION "3-point cooling valve for opening time or Heating 1 for hp"				
                    ::= { integerObjects 31 }				
				
        -- 1.3.6.1.4.1.9839.2.1.3.32				
        close_time_cool OBJECT-TYPE				
                    SYNTAX Integer32 (1..300)				
                    UNITS "s"				
                    MAX-ACCESS read-write				
                    STATUS current				
                    DESCRIPTION "3-point cooling valve for closing time or Heating 2 for hp"				
                    ::= { integerObjects 32 }				
				
        -- 1.3.6.1.4.1.9839.2.1.3.33				
        open_time_heat OBJECT-TYPE				
                    SYNTAX Integer32 (1..300)				
                    UNITS "s"				
                    MAX-ACCESS read-write				
                    STATUS current				
                    DESCRIPTION "3-point heating valve for opening time"				
                    ::= { integerObjects 33 }				
				
        -- 1.3.6.1.4.1.9839.2.1.3.34				
        close_time_heat OBJECT-TYPE				
                    SYNTAX Integer32 (1..300)				
                    UNITS "s"				
                    MAX-ACCESS read-write				
                    STATUS current				
                    DESCRIPTION "3-point heating valve for closing time"				
                    ::= { integerObjects 34 }				
				
        -- 1.3.6.1.4.1.9839.2.1.3.35				
        impuls_comp1 OBJECT-TYPE				
                    SYNTAX Integer32 (-32767..32767)				
                    UNITS "p"				
                    MAX-ACCESS read-only				
                    STATUS current				
                    DESCRIPTION "Number of start compressor 1"				
                    ::= { integerObjects 35 }				
				
        -- 1.3.6.1.4.1.9839.2.1.3.36				
        impuls_comp2 OBJECT-TYPE				
                    SYNTAX Integer32 (-32767..32767)				
                    UNITS "p"				
                    MAX-ACCESS read-only				
                    STATUS current				
                    DESCRIPTION "Number of start compressor 2"				
                    ::= { integerObjects 36 }				
				
        -- 1.3.6.1.4.1.9839.2.1.3.37				
        x_heater1 OBJECT-TYPE				
                    SYNTAX Integer32 (-32767..32767)				
                    UNITS "h"				
                    MAX-ACCESS read-only				
                    STATUS current				
                    DESCRIPTION "Working hours Heater 1"				
                    ::= { integerObjects 37 }				
				
        -- 1.3.6.1.4.1.9839.2.1.3.38				
        max_value2_inp7 OBJECT-TYPE				
                    SYNTAX Integer32 (-32767..32767)				
                    UNITS "N/A"				
                    MAX-ACCESS read-only				
                    STATUS current				
                    DESCRIPTION "Max scale of input B7 board 2 (no for hp)"				
                    ::= { integerObjects 38 }				
				
        -- 1.3.6.1.4.1.9839.2.1.3.39				
        x_heater2 OBJECT-TYPE				
                    SYNTAX Integer32 (-32767..32767)				
                    UNITS "h"				
                    MAX-ACCESS read-only				
                    STATUS current				
                    DESCRIPTION "Working hours Heater 2 (no for hp)"				
                    ::= { integerObjects 39 }				
				
        -- 1.3.6.1.4.1.9839.2.1.3.40				
        thr_comp1 OBJECT-TYPE				
                    SYNTAX Integer32 (-32767..32767)				
                    UNITS "°C"				
                    MAX-ACCESS read-only				
                    STATUS current				
                    DESCRIPTION "Step compr.1 stage On (value : 10)"				
                    ::= { integerObjects 40 }				
				
        -- 1.3.6.1.4.1.9839.2.1.3.41				
        x_humid OBJECT-TYPE				
                    SYNTAX Integer32 (-32767..32767)				
                    UNITS "h"				
                    MAX-ACCESS read-only				
                    STATUS current				
                    DESCRIPTION "Working hours humidifier"				
                    ::= { integerObjects 41 }				
				
        -- 1.3.6.1.4.1.9839.2.1.3.42				
        v_integ.42 OBJECT-TYPE				
                    SYNTAX Integer32 (0..100)				
                    UNITS "%"				
                    MAX-ACCESS read-only				
                    STATUS current				
                    DESCRIPTION "Value output 0-100% for heating/cooling valve circuit 2 (hp)"				
                    ::= { integerObjects 42 }				
				
        -- 1.3.6.1.4.1.9839.2.1.3.43				
        x_dehumid OBJECT-TYPE				
                    SYNTAX Integer32 (-32767..32767)				
                    UNITS "h"				
                    MAX-ACCESS read-only				
                    STATUS current				
                    DESCRIPTION "Working hours dehumidifier (no for hp)"				
                    ::= { integerObjects 43 }				
				
        -- 1.3.6.1.4.1.9839.2.1.3.44				
        max_prod OBJECT-TYPE				
                    SYNTAX Integer32 (-32767..32767)				
                    UNITS "Kg/h"				
                    MAX-ACCESS read-only				
                    STATUS current				
                    DESCRIPTION "Rated capacity humidifier (value : 10)"				
                    ::= { integerObjects 44 }				
				
        -- 1.3.6.1.4.1.9839.2.1.3.45				
        x_main_fan OBJECT-TYPE				
                    SYNTAX Integer32 (-32767..32767)				
                    UNITS "h"				
                    MAX-ACCESS read-only				
                    STATUS current				
                    DESCRIPTION "Working hours main fan"				
                    ::= { integerObjects 45 }				
				
        -- 1.3.6.1.4.1.9839.2.1.3.46				
        thr_comp2 OBJECT-TYPE				
                    SYNTAX Integer32 (-32767..32767)				
                    UNITS "°C"				
                    MAX-ACCESS read-only				
                    STATUS current				
                    DESCRIPTION "Step compr.2 stage On (value : 10)"				
                    ::= { integerObjects 46 }				
				
        -- 1.3.6.1.4.1.9839.2.1.3.47				
        x_valve_comp1 OBJECT-TYPE				
                    SYNTAX Integer32 (-32767..32767)				
                    UNITS "h"				
                    MAX-ACCESS read-only				
                    STATUS current				
                    DESCRIPTION "Working hours compressor 1"				
                    ::= { integerObjects 47 }				
				
        -- 1.3.6.1.4.1.9839.2.1.3.48				
        v_integ.48 OBJECT-TYPE				
                    SYNTAX Integer32 (-32767..32767)				
                    UNITS "h"				
                    MAX-ACCESS read-only				
                    STATUS current				
                    DESCRIPTION "Working hours heating 1 (hp)"				
                    ::= { integerObjects 48 }				
				
        -- 1.3.6.1.4.1.9839.2.1.3.49				
        x_valve_comp2 OBJECT-TYPE				
                    SYNTAX Integer32 (-32767..32767)				
                    UNITS "h"				
                    MAX-ACCESS read-only				
                    STATUS current				
                    DESCRIPTION "Working hours compressor 2"				
                    ::= { integerObjects 49 }				
				
        -- 1.3.6.1.4.1.9839.2.1.3.50				
        v_integ.50 OBJECT-TYPE				
                    SYNTAX Integer32 (-32767..32767)				
                    UNITS "h"				
                    MAX-ACCESS read-only				
                    STATUS current				
                    DESCRIPTION "Working hours heating 2 (hp)"				
                    ::= { integerObjects 50 }				
				
        -- 1.3.6.1.4.1.9839.2.1.3.51				
        max_value2_inp8 OBJECT-TYPE				
                    SYNTAX Integer32 (-32767..32767)				
                    UNITS "N/A"				
                    MAX-ACCESS read-only				
                    STATUS current				
                    DESCRIPTION "Max scale of input B8 board 2 (no for hp)"				
                    ::= { integerObjects 51 }				
				
        -- 1.3.6.1.4.1.9839.2.1.3.52				
        nominal_prod OBJECT-TYPE				
                    SYNTAX Integer32 (-32767..32767)				
                    UNITS "Kg/h"				
                    MAX-ACCESS read-only				
                    STATUS current				
                    DESCRIPTION "Nominal capacity of humidifier (value : 10)"				
                    ::= { integerObjects 52 }				
				
        -- 1.3.6.1.4.1.9839.2.1.3.53				
        voltage OBJECT-TYPE				
                    SYNTAX Integer32 (-32767..32767)				
                    UNITS "Vac"				
                    MAX-ACCESS read-only				
                    STATUS current				
                    DESCRIPTION "Operating voltage of integrated humidifier"				
                    ::= { integerObjects 53 }				
				
        -- 1.3.6.1.4.1.9839.2.1.3.54				
        tam_model OBJECT-TYPE				
                    SYNTAX Integer32 (-32767..32767)				
                    UNITS "N/A"				
                    MAX-ACCESS read-only				
                    STATUS current				
                    DESCRIPTION "Transformer model for humidifier"				
                    ::= { integerObjects 54 }				
				
        -- 1.3.6.1.4.1.9839.2.1.3.55				
        start_cool_damp OBJECT-TYPE				
                    SYNTAX Integer32 (-32767..32767)				
                    UNITS "°C"				
                    MAX-ACCESS read-only				
                    STATUS current				
                    DESCRIPTION "Cold valve start opening, 0 Volt (value : 10)"				
                    ::= { integerObjects 55 }				
				
        -- 1.3.6.1.4.1.9839.2.1.3.56				
        end_cool_damp OBJECT-TYPE				
                    SYNTAX Integer32 (-32767..32767)				
                    UNITS "°C"				
                    MAX-ACCESS read-only				
                    STATUS current				
                    DESCRIPTION "Cold valve end opening, 10 Volt (value : 10)"				
                    ::= { integerObjects 56 }				
				
        -- 1.3.6.1.4.1.9839.2.1.3.57				
        start_heat_damp OBJECT-TYPE				
                    SYNTAX Integer32 (-32767..32767)				
                    UNITS "°C"				
                    MAX-ACCESS read-only				
                    STATUS current				
                    DESCRIPTION "Heat valve start opening, 0 Volt (value : 10)"				
                    ::= { integerObjects 57 }				
				
        -- 1.3.6.1.4.1.9839.2.1.3.58				
        end_heat_damp OBJECT-TYPE				
                    SYNTAX Integer32 (-32767..32767)				
                    UNITS "°C"				
                    MAX-ACCESS read-only				
                    STATUS current				
                    DESCRIPTION "Heat valve end opening, 10 Volt (value : 10)"				
                    ::= { integerObjects 58 }				
				
        -- 1.3.6.1.4.1.9839.2.1.3.59				
        time_same_comp OBJECT-TYPE				
                    SYNTAX Integer32 (-32767..32767)				
                    UNITS "s"				
                    MAX-ACCESS read-only				
                    STATUS current				
                    DESCRIPTION "Time between starts of same compressor"				
                    ::= { integerObjects 59 }				
				
        -- 1.3.6.1.4.1.9839.2.1.3.60				
        time_min_on OBJECT-TYPE				
                    SYNTAX Integer32 (-32767..32767)				
                    UNITS "s"				
                    MAX-ACCESS read-only				
                    STATUS current				
                    DESCRIPTION "Minimum compressor ON time"				
                    ::= { integerObjects 60 }				
				
        -- 1.3.6.1.4.1.9839.2.1.3.61				
        time_min_off OBJECT-TYPE				
                    SYNTAX Integer32 (-32767..32767)				
                    UNITS "s"				
                    MAX-ACCESS read-only				
                    STATUS current				
                    DESCRIPTION "Minimum compressor OFF time"				
                    ::= { integerObjects 61 }				
				
        -- 1.3.6.1.4.1.9839.2.1.3.62				
        time_betw_comp OBJECT-TYPE				
                    SYNTAX Integer32 (-32767..32767)				
                    UNITS "s"				
                    MAX-ACCESS read-only				
                    STATUS current				
                    DESCRIPTION "Time between starts of different compressors"				
                    ::= { integerObjects 62 }				
				
        -- 1.3.6.1.4.1.9839.2.1.3.63				
        n_heaters OBJECT-TYPE				
                    SYNTAX Integer32 (-32767..32767)				
                    UNITS "N/A"				
                    MAX-ACCESS read-only				
                    STATUS current				
                    DESCRIPTION "Number of Heaters / defrosting time (hp)"				
                    ::= { integerObjects 63 }				
				
        -- 1.3.6.1.4.1.9839.2.1.3.64				
        configuration OBJECT-TYPE				
                    SYNTAX Integer32 (-32767..32767)				
                    UNITS "N/A"				
                    MAX-ACCESS read-only				
                    STATUS current				
                    DESCRIPTION "Config. Unit, number of compressor and board"				
                    ::= { integerObjects 64 }				
				
        -- 1.3.6.1.4.1.9839.2.1.3.65				
        delay_temper OBJECT-TYPE				
                    SYNTAX Integer32 (-32767..32767)				
                    UNITS "s"				
                    MAX-ACCESS read-only				
                    STATUS current				
                    DESCRIPTION "Temperature alarm delay"				
                    ::= { integerObjects 65 }				
				
        -- 1.3.6.1.4.1.9839.2.1.3.66				
        time_betw_heat OBJECT-TYPE				
                    SYNTAX Integer32 (-32767..32767)				
                    UNITS "s"				
                    MAX-ACCESS read-only				
                    STATUS current				
                    DESCRIPTION "Time between start of two Heaters (no hp)"				
                    ::= { integerObjects 66 }				
				
        -- 1.3.6.1.4.1.9839.2.1.3.67				
        hys_heater1 OBJECT-TYPE				
                    SYNTAX Integer32 (-32767..32767)				
                    UNITS "°C"				
                    MAX-ACCESS read-only				
                    STATUS current				
                    DESCRIPTION "Step heater 1 differential (value : 10)"				
                    ::= { integerObjects 67 }				
				
        -- 1.3.6.1.4.1.9839.2.1.3.68				
        thr_h_main_fan OBJECT-TYPE				
                    SYNTAX Integer32 (-32767..32767)				
                    UNITS "h"				
                    MAX-ACCESS read-only				
                    STATUS current				
                    DESCRIPTION "Main fan excessive operating time alarm threshold"				
                    ::= { integerObjects 68 }				
				
        -- 1.3.6.1.4.1.9839.2.1.3.69				
        thr_hour_c1 OBJECT-TYPE				
                    SYNTAX Integer32 (-32767..32767)				
                    UNITS "h"				
                    MAX-ACCESS read-only				
                    STATUS current				
                    DESCRIPTION "Compressor 1 excessive operating time alarm threshold"				
                    ::= { integerObjects 69 }				
				
        -- 1.3.6.1.4.1.9839.2.1.3.70				
        thr_hour_c2 OBJECT-TYPE				
                    SYNTAX Integer32 (-32767..32767)				
                    UNITS "h"				
                    MAX-ACCESS read-only				
                    STATUS current				
                    DESCRIPTION "Compressor 2 excessive operating time alarm threshold"				
                    ::= { integerObjects 70 }				
				
        -- 1.3.6.1.4.1.9839.2.1.3.71				
        start_cool_d3p OBJECT-TYPE				
                    SYNTAX Integer32 (-32767..32767)				
                    UNITS "°C"				
                    MAX-ACCESS read-only				
                    STATUS current				
                    DESCRIPTION "3-point cold valve start opening / max. defrosting time (hp)"				
                    ::= { integerObjects 71 }				
				
        -- 1.3.6.1.4.1.9839.2.1.3.72				
        end_cool_d3p OBJECT-TYPE				
                    SYNTAX Integer32 (-32767..32767)				
                    UNITS "°C"				
                    MAX-ACCESS read-only				
                    STATUS current				
                    DESCRIPTION "3-point cold valve end opening (no hp)"				
                    ::= { integerObjects 72 }				
				
        -- 1.3.6.1.4.1.9839.2.1.3.73				
        start_heat_d3p OBJECT-TYPE				
                    SYNTAX Integer32 (-32767..32767)				
                    UNITS "°C"				
                    MAX-ACCESS read-only				
                    STATUS current				
                    DESCRIPTION "3-point heat valve start opening (no hp)"				
                    ::= { integerObjects 73 }				
				
        -- 1.3.6.1.4.1.9839.2.1.3.74				
        end_heat_d3p OBJECT-TYPE				
                    SYNTAX Integer32 (-32767..32767)				
                    UNITS "°C"				
                    MAX-ACCESS read-only				
                    STATUS current				
                    DESCRIPTION "3-point heat valve end opening / meaning of input B7 board 2 (hp)"				
                    ::= { integerObjects 74 }				
				
        -- 1.3.6.1.4.1.9839.2.1.3.75				
        mean_anal_out1 OBJECT-TYPE				
                    SYNTAX Integer32 (-32767..32767)				
                    UNITS "N/A"				
                    MAX-ACCESS read-only				
                    STATUS current				
                    DESCRIPTION "Meaning of analogue output 1"				
                    ::= { integerObjects 75 }				
				
        -- 1.3.6.1.4.1.9839.2.1.3.76				
        time_runn_d3p OBJECT-TYPE				
                    SYNTAX Integer32 (-32767..32767)				
                    UNITS "s"				
                    MAX-ACCESS read-only				
                    STATUS current				
                    DESCRIPTION "Float valve running time / meaning of input B8 board 2 (hp)"				
                    ::= { integerObjects 76 }				
				
        -- 1.3.6.1.4.1.9839.2.1.3.77				
        input_b7 OBJECT-TYPE				
                    SYNTAX Integer32 (-32767..32767)				
                    UNITS "N/A"				
                    MAX-ACCESS read-only				
                    STATUS current				
                    DESCRIPTION "Meaning of analogue output B7 board 1"				
                    ::= { integerObjects 77 }				
				
        -- 1.3.6.1.4.1.9839.2.1.3.78				
        delay_on_fan OBJECT-TYPE				
                    SYNTAX Integer32 (-32767..32767)				
                    UNITS "s"				
                    MAX-ACCESS read-only				
                    STATUS current				
                    DESCRIPTION "Main fan start delay"				
                    ::= { integerObjects 78 }				
				
        -- 1.3.6.1.4.1.9839.2.1.3.79				
        delay_off_fan OBJECT-TYPE				
                    SYNTAX Integer32 (-32767..32767)				
                    UNITS "s"				
                    MAX-ACCESS read-only				
                    STATUS current				
                    DESCRIPTION "Main fan stop delay"				
                    ::= { integerObjects 79 }				
				
        -- 1.3.6.1.4.1.9839.2.1.3.80				
        compens_time OBJECT-TYPE				
                    SYNTAX Integer32 (-32767..32767)				
                    UNITS "min"				
                    MAX-ACCESS read-only				
                    STATUS current				
                    DESCRIPTION "Set-point compensation time"				
                    ::= { integerObjects 80 }				
				
        -- 1.3.6.1.4.1.9839.2.1.3.81				
        mean_anal_inp8 OBJECT-TYPE				
                    SYNTAX Integer32 (-32767..32767)				
                    UNITS "N/A"				
                    MAX-ACCESS read-only				
                    STATUS current				
                    DESCRIPTION "Meaning of analog.input B8 board 1 or analog.output P1 board 2 (hp)"				
                    ::= { integerObjects 81 }				
				
        -- 1.3.6.1.4.1.9839.2.1.3.82				
        time_unloader OBJECT-TYPE				
                    SYNTAX Integer32 (-32767..32767)				
                    UNITS "s"				
                    MAX-ACCESS read-only				
                    STATUS current				
                    DESCRIPTION "Delay between compressor and capacity control"				
                    ::= { integerObjects 82 }				
				
        -- 1.3.6.1.4.1.9839.2.1.3.83				
        inverter_setp OBJECT-TYPE				
                    SYNTAX Integer32 (-32767..32767)				
                    UNITS "kPa"				
                    MAX-ACCESS read-only				
                    STATUS current				
                    DESCRIPTION "Condensation control set-point (value * 10)"				
                    ::= { integerObjects 83 }				
				
        -- 1.3.6.1.4.1.9839.2.1.3.84				
        inverter_diff OBJECT-TYPE				
                    SYNTAX Integer32 (-32767..32767)				
                    UNITS "kPa"				
                    MAX-ACCESS read-only				
                    STATUS current				
                    DESCRIPTION "Condensation control set-point diff. (value * 10)"				
                    ::= { integerObjects 84 }				
				
        -- 1.3.6.1.4.1.9839.2.1.3.85				
        on_max_inv OBJECT-TYPE				
                    SYNTAX Integer32 (-32767..32767)				
                    UNITS "kPa"				
                    MAX-ACCESS read-only				
                    STATUS current				
                    DESCRIPTION "Value to turn on the condens.with compr.off (value * 10)"				
                    ::= { integerObjects 85 }				
				
        -- 1.3.6.1.4.1.9839.2.1.3.86				
        off_max_inv OBJECT-TYPE				
                    SYNTAX Integer32 (-32767..32767)				
                    UNITS "kPa"				
                    MAX-ACCESS read-only				
                    STATUS current				
                    DESCRIPTION "Value to turn off the condens.with compr.off (value * 10)"				
                    ::= { integerObjects 86 }				
				
        -- 1.3.6.1.4.1.9839.2.1.3.87				
        thr_high_limit OBJECT-TYPE				
                    SYNTAX Integer32 (-32767..32767)				
                    UNITS "°C"				
                    MAX-ACCESS read-only				
                    STATUS current				
                    DESCRIPTION "Hi limit thresh. stop dehumif. (value:10) / Min suction pressure (hp)"				
                    ::= { integerObjects 87 }				
				
        -- 1.3.6.1.4.1.9839.2.1.3.88				
        hys_high_limit OBJECT-TYPE				
                    SYNTAX Integer32 (-32767..32767)				
                    UNITS "°C"				
                    MAX-ACCESS read-only				
                    STATUS current				
                    DESCRIPTION "Hi limit diff. stop dehum.(value:10)/ Max. top suction pressure (hp)"				
                    ::= { integerObjects 88 }				
				
        -- 1.3.6.1.4.1.9839.2.1.3.89				
        thr_low_limit OBJECT-TYPE				
                    SYNTAX Integer32 (-32767..32767)				
                    UNITS "°C"				
                    MAX-ACCESS read-only				
                    STATUS current				
                    DESCRIPTION "Lo limit thresh.stop dehumif.(value:10) / press. end gas defrosting (hp)"				
                    ::= { integerObjects 89 }				
				
        -- 1.3.6.1.4.1.9839.2.1.3.90				
        hys_low_limit OBJECT-TYPE				
                    SYNTAX Integer32 (-32767..32767)				
                    UNITS "°C"				
                    MAX-ACCESS read-only				
                    STATUS current				
                    DESCRIPTION "Lo limit diff.stop dehum.(value:10)/ Low pressure threshold (hp)"				
                    ::= { integerObjects 90 }				
				
        -- 1.3.6.1.4.1.9839.2.1.3.91				
        thr_dehumid OBJECT-TYPE				
                    SYNTAX Integer32 (-32767..32767)				
                    UNITS "%rH"				
                    MAX-ACCESS read-only				
                    STATUS current				
                    DESCRIPTION "Deumidification threshold"				
                    ::= { integerObjects 91 }				
				
        -- 1.3.6.1.4.1.9839.2.1.3.92				
        hys_dehumid OBJECT-TYPE				
                    SYNTAX Integer32 (-32767..32767)				
                    UNITS "%rH"				
                    MAX-ACCESS read-only				
                    STATUS current				
                    DESCRIPTION "Deumidification differential"				
                    ::= { integerObjects 92 }				
				
        -- 1.3.6.1.4.1.9839.2.1.3.93				
        thr_humid OBJECT-TYPE				
                    SYNTAX Integer32 (-32767..32767)				
                    UNITS "%rH"				
                    MAX-ACCESS read-only				
                    STATUS current				
                    DESCRIPTION "Humidity threshold"				
                    ::= { integerObjects 93 }				
				
        -- 1.3.6.1.4.1.9839.2.1.3.94				
        hys_humid OBJECT-TYPE				
                    SYNTAX Integer32 (-32767..32767)				
                    UNITS "%rH"				
                    MAX-ACCESS read-only				
                    STATUS current				
                    DESCRIPTION "Humidity differential"				
                    ::= { integerObjects 94 }				
				
        -- 1.3.6.1.4.1.9839.2.1.3.95				
        min_press_value OBJECT-TYPE				
                    SYNTAX Integer32 (-32767..32767)				
                    UNITS "kPa"				
                    MAX-ACCESS read-only				
                    STATUS current				
                    DESCRIPTION "Min scale of delivery pressure sensor (value * 10)"				
                    ::= { integerObjects 95 }				
				
        -- 1.3.6.1.4.1.9839.2.1.3.96				
        max_press_value OBJECT-TYPE				
                    SYNTAX Integer32 (-32767..32767)				
                    UNITS "kPa"				
                    MAX-ACCESS read-only				
                    STATUS current				
                    DESCRIPTION "Max scale of delivery pressure sensor (value * 10)"				
                    ::= { integerObjects 96 }				
				
        -- 1.3.6.1.4.1.9839.2.1.3.97				
        thr_heater2 OBJECT-TYPE				
                    SYNTAX Integer32 (-32767..32767)				
                    UNITS "°C"				
                    MAX-ACCESS read-only				
                    STATUS current				
                    DESCRIPTION "Step heater 2 stage On (value : 10)"				
                    ::= { integerObjects 97 }				
				
        -- 1.3.6.1.4.1.9839.2.1.3.98				
        max_value_inp7 OBJECT-TYPE				
                    SYNTAX Integer32 (-32767..32767)				
                    UNITS "N/A"				
                    MAX-ACCESS read-only				
                    STATUS current				
                    DESCRIPTION "Top of the range value of input B7 board 1"				
                    ::= { integerObjects 98 }				
				
        -- 1.3.6.1.4.1.9839.2.1.3.99				
        lim_min_set_h OBJECT-TYPE				
                    SYNTAX Integer32 (-32767..32767)				
                    UNITS "%rH"				
                    MAX-ACCESS read-only				
                    STATUS current				
                    DESCRIPTION "Minimum limit of humidity setpoint"				
                    ::= { integerObjects 99 }				
				
        -- 1.3.6.1.4.1.9839.2.1.3.100				
        max_value_inp8 OBJECT-TYPE				
                    SYNTAX Integer32 (-32767..32767)				
                    UNITS "N/A"				
                    MAX-ACCESS read-only				
                    STATUS current				
                    DESCRIPTION "Top range value input B8 board 1 (B7 board 2 for hp)"				
                    ::= { integerObjects 100 }				
				
        -- 1.3.6.1.4.1.9839.2.1.3.101				
        hys_heater2 OBJECT-TYPE				
                    SYNTAX Integer32 (-32767..32767)				
                    UNITS "°C"				
                    MAX-ACCESS read-only				
                    STATUS current				
                    DESCRIPTION "Step heater 2 differential (value : 10)"				
                    ::= { integerObjects 101 }				
				
        -- 1.3.6.1.4.1.9839.2.1.3.102				
        sel_set_humid OBJECT-TYPE				
                    SYNTAX Integer32 (20..80)				
                    UNITS "%rH"				
                    MAX-ACCESS read-write				
                    STATUS current				
                    DESCRIPTION "Air humidity Set-point"				
                    ::= { integerObjects 102 }				
				
        -- 1.3.6.1.4.1.9839.2.1.3.103				
        diff_humid OBJECT-TYPE				
                    SYNTAX Integer32 (-32767..32767)				
                    UNITS "%rH"				
                    MAX-ACCESS read-only				
                    STATUS current				
                    DESCRIPTION "Humidity differential (umidif. Externo)"				
                    ::= { integerObjects 103 }				
				
        -- 1.3.6.1.4.1.9839.2.1.3.104				
        units_number OBJECT-TYPE				
                    SYNTAX Integer32 (-32767..32767)				
                    UNITS "N/A"				
                    MAX-ACCESS read-only				
                    STATUS current				
                    DESCRIPTION "Number of masters connected via LAN"				
                    ::= { integerObjects 104 }				
				
        -- 1.3.6.1.4.1.9839.2.1.3.105				
        rotation_time OBJECT-TYPE				
                    SYNTAX Integer32 (-32767..32767)				
                    UNITS "h"				
                    MAX-ACCESS read-only				
                    STATUS current				
                    DESCRIPTION "Rotation time between networked masters (no for hp)"				
                    ::= { integerObjects 105 }				
				
        -- 1.3.6.1.4.1.9839.2.1.3.106				
        thr_h_heater1 OBJECT-TYPE				
                    SYNTAX Integer32 (-32767..32767)				
                    UNITS "h"				
                    MAX-ACCESS read-only				
                    STATUS current				
                    DESCRIPTION "Heater 1  excessive operating time alarm threshold "				
                    ::= { integerObjects 106 }				
				
        -- 1.3.6.1.4.1.9839.2.1.3.107				
        thr_h_heater2 OBJECT-TYPE				
                    SYNTAX Integer32 (-32767..32767)				
                    UNITS "h"				
                    MAX-ACCESS read-only				
                    STATUS current				
                    DESCRIPTION "Heater 2  exc.operating time alarm threshold (no for hp)"				
                    ::= { integerObjects 107 }				
				
        -- 1.3.6.1.4.1.9839.2.1.3.108				
        thr_h_humid OBJECT-TYPE				
                    SYNTAX Integer32 (-32767..32767)				
                    UNITS "h"				
                    MAX-ACCESS read-only				
                    STATUS current				
                    DESCRIPTION "Humidifier excessive operating time alarm"				
                    ::= { integerObjects 108 }				
				
        -- 1.3.6.1.4.1.9839.2.1.3.109				
        delay_humid OBJECT-TYPE				
                    SYNTAX Integer32 (-32767..32767)				
                    UNITS "s"				
                    MAX-ACCESS read-only				
                    STATUS current				
                    DESCRIPTION "High / low humidity alarm delay"				
                    ::= { integerObjects 109 }				
				
        -- 1.3.6.1.4.1.9839.2.1.3.110				
        max_pressure OBJECT-TYPE				
                    SYNTAX Integer32 (-32767..32767)				
                    UNITS "kPa"				
                    MAX-ACCESS read-only				
                    STATUS current				
                    DESCRIPTION "High pressure alarm threshold (value * 10)"				
                    ::= { integerObjects 110 }				
				
        -- 1.3.6.1.4.1.9839.2.1.3.111				
        delay_low_pres OBJECT-TYPE				
                    SYNTAX Integer32 (-32767..32767)				
                    UNITS "kPa"				
                    MAX-ACCESS read-only				
                    STATUS current				
                    DESCRIPTION "Low pressure alarm threshold (value * 10)"				
                    ::= { integerObjects 111 }				
				
        -- 1.3.6.1.4.1.9839.2.1.3.112				
        delay_air_flow OBJECT-TYPE				
                    SYNTAX Integer32 (-32767..32767)				
                    UNITS "s"				
                    MAX-ACCESS read-only				
                    STATUS current				
                    DESCRIPTION "Air flow rate switch alarm delay"				
                    ::= { integerObjects 112 }				
				
        -- 1.3.6.1.4.1.9839.2.1.3.113				
        delay_gen_al1 OBJECT-TYPE				
                    SYNTAX Integer32 (-32767..32767)				
                    UNITS "s"				
                    MAX-ACCESS read-only				
                    STATUS current				
                    DESCRIPTION "General alarm 1 delay"				
                    ::= { integerObjects 113 }				
				
        -- 1.3.6.1.4.1.9839.2.1.3.114				
        delay_gen_al2 OBJECT-TYPE				
                    SYNTAX Integer32 (-32767..32767)				
                    UNITS "s"				
                    MAX-ACCESS read-only				
                    STATUS current				
                    DESCRIPTION "General alarm 2 delay"				
                    ::= { integerObjects 114 }				
				
        -- 1.3.6.1.4.1.9839.2.1.3.115				
        delay_oil_diff OBJECT-TYPE				
                    SYNTAX Integer32 (-32767..32767)				
                    UNITS "s"				
                    MAX-ACCESS read-only				
                    STATUS current				
                    DESCRIPTION "Oil differential alarm delay (board 2)"				
                    ::= { integerObjects 115 }				
				
        -- 1.3.6.1.4.1.9839.2.1.3.116				
        logic_dehumid OBJECT-TYPE				
                    SYNTAX Integer32 (-32767..32767)				
                    UNITS "N/A"				
                    MAX-ACCESS read-only				
                    STATUS current				
                    DESCRIPTION "Dehumidification logic (no for hp)"				
                    ::= { integerObjects 116 }				
				
        -- 1.3.6.1.4.1.9839.2.1.3.117				
        lim_max_set_h OBJECT-TYPE				
                    SYNTAX Integer32 (-32767..32767)				
                    UNITS "%rH"				
                    MAX-ACCESS read-only				
                    STATUS current				
                    DESCRIPTION "Max humidity setpoint limit"				
                    ::= { integerObjects 117 }				
				
				
				
	END			
				
--				
-- CAREL-aarc_norm.MIB			
--
