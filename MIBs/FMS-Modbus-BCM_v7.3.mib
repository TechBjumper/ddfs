--  Title:    FMS-Modbus-BCM.MIB
--  Version:  v7.3
--  Date:     12/15/04 11:18am
--  Copyright @ 2004 RLE Technologies.  All rights reserved worldwide.
--  This MIB defines objects for the RLE falcon SNMP Agent.
--

RLE-FALCON-EM-MIB DEFINITIONS ::= BEGIN

IMPORTS
        TruthValue           FROM RFC1253-MIB
        DisplayString        FROM RFC1213-MIB
        OBJECT-TYPE, Gauge   FROM RFC1155-SMI
        TRAP-TYPE            FROM RFC-1215
        Counter, enterprises FROM RFC1155-SMI;
        PositiveInteger ::= INTEGER (1..2147483647)

rle          OBJECT IDENTIFIER ::= { enterprises  3184 }
products     OBJECT IDENTIFIER ::= { rle  1 }
falcon-em    OBJECT IDENTIFIER ::= { products  5 }
falcon-emMIB OBJECT IDENTIFIER ::= { falcon-em 1 }
falconModbus OBJECT IDENTIFIER ::= { falcon-emMIB 12 }
falconBCMs   OBJECT IDENTIFIER ::= { falconModbus 1 }

falconBCM01  OBJECT IDENTIFIER ::= { falconBCMs  1 }

falconBCM01Label OBJECT-TYPE
    SYNTAX  DisplayString
    ACCESS  read-only
    STATUS  mandatory
    DESCRIPTION
           "A user-defined text string associated with the BCM."
    ::= { falconBCM01  1 }

falconBCM01CBTable OBJECT-TYPE
    SYNTAX  SEQUENCE OF FalconBCM01CBEntry
    ACCESS  not-accessible
    STATUS  mandatory
    DESCRIPTION
           "A table of the falcon modbus BCM CB port status."
    ::= { falconBCM01 2 }

falconBCM01CBEntry OBJECT-TYPE
     SYNTAX  FalconBCM01Entry
     ACCESS  not-accessible
     STATUS  mandatory
     DESCRIPTION
            "An entry containing objects for the Falcon
             modbus BCM CB port."
     INDEX   { falconBCM01CBIndex }
     ::= { falconBCM01CBTable 1 }

          
FalconBCM01CBEntry ::= SEQUENCE {
     falconBCM01CBIndex       INTEGER,
     falconBCM01CBStatus      INTEGER, 
     falconBCM01CBReading     INTEGER,
     falconBCM01CBLabel       DisplayString
}     

falconBCM01CBIndex OBJECT-TYPE
    SYNTAX  INTEGER
    ACCESS  read-only
    STATUS  mandatory
    DESCRIPTION
           "A unique value for each BCM CB port.  Its value
            ranges between 1 and 42."
     ::= { falconBCM01CBEntry 1 }

falconBCM01CBStatus OBJECT-TYPE
    SYNTAX  INTEGER {
    notConfigured(0),
    offline(1),
    normal(2),
    zeroAmpAlarm(3),
    warning(4),
    alarm(5)
}
    ACCESS  read-only
    STATUS  mandatory
    DESCRIPTION
           "The current status for this circuit breaker."
    ::= { falconBCM01CBEntry  2 }

falconBCM01CBReading OBJECT-TYPE
    SYNTAX  INTEGER (-2147483648..2147483647)
    ACCESS  read-only
    STATUS  mandatory
    DESCRIPTION
           "The current reading (AMPS) for circuit breaker."
    ::= { falconBCM01CBEntry  3 }

falconBCM01CBLabel OBJECT-TYPE
    SYNTAX  DisplayString
    ACCESS  read-only
    STATUS  mandatory
    DESCRIPTION
           "A user-defined text string associated with the circuit breaker."
    ::= { falconBCM01CBEntry  4 }

falconBCM02  OBJECT IDENTIFIER ::= { falconBCMs  2 }

falconBCM02Label OBJECT-TYPE
    SYNTAX  DisplayString
    ACCESS  read-only
    STATUS  mandatory
    DESCRIPTION
           "A user-defined text string associated with the BCM."
    ::= { falconBCM02  1 }

falconBCM02CBTable OBJECT-TYPE
    SYNTAX  SEQUENCE OF FalconBCM02CBEntry
    ACCESS  not-accessible
    STATUS  mandatory
    DESCRIPTION
           "A table of the falcon modbus BCM CB port status."
    ::= { falconBCM02 2 }

falconBCM02CBEntry OBJECT-TYPE
     SYNTAX  FalconBCM02Entry
     ACCESS  not-accessible
     STATUS  mandatory
     DESCRIPTION
            "An entry containing objects for the Falcon
             modbus BCM CB port."
     INDEX   { falconBCM02CBIndex }
     ::= { falconBCM02CBTable 1 }

          
FalconBCM02CBEntry ::= SEQUENCE {
     falconBCM02CBIndex       INTEGER,
     falconBCM02CBStatus      INTEGER, 
     falconBCM02CBReading     INTEGER,
     falconBCM02CBLabel       DisplayString
}     

falconBCM02CBIndex OBJECT-TYPE
    SYNTAX  INTEGER
    ACCESS  read-only
    STATUS  mandatory
    DESCRIPTION
           "A unique value for each BCM CB port.  Its value
            ranges between 1 and 42."
     ::= { falconBCM02CBEntry 1 }

falconBCM02CBStatus OBJECT-TYPE
    SYNTAX  INTEGER {
    notConfigured(0),
    offline(1),
    normal(2),
    zeroAmpAlarm(3),
    warning(4),
    alarm(5)
}
    ACCESS  read-only
    STATUS  mandatory
    DESCRIPTION
           "The current status for this circuit breaker."
    ::= { falconBCM02CBEntry  2 }

falconBCM02CBReading OBJECT-TYPE
    SYNTAX  INTEGER (-2147483648..2147483647)
    ACCESS  read-only
    STATUS  mandatory
    DESCRIPTION
           "The current reading (AMPS) for circuit breaker."
    ::= { falconBCM02CBEntry  3 }

falconBCM02CBLabel OBJECT-TYPE
    SYNTAX  DisplayString
    ACCESS  read-only
    STATUS  mandatory
    DESCRIPTION
           "A user-defined text string associated with the circuit breaker."
    ::= { falconBCM02CBEntry  4 }

falconBCM03  OBJECT IDENTIFIER ::= { falconBCMs  3 }

falconBCM03Label OBJECT-TYPE
    SYNTAX  DisplayString
    ACCESS  read-only
    STATUS  mandatory
    DESCRIPTION
           "A user-defined text string associated with the BCM."
    ::= { falconBCM03  1 }

falconBCM03CBTable OBJECT-TYPE
    SYNTAX  SEQUENCE OF FalconBCM03CBEntry
    ACCESS  not-accessible
    STATUS  mandatory
    DESCRIPTION
           "A table of the falcon modbus BCM CB port status."
    ::= { falconBCM03 2 }

falconBCM03CBEntry OBJECT-TYPE
     SYNTAX  FalconBCM03Entry
     ACCESS  not-accessible
     STATUS  mandatory
     DESCRIPTION
            "An entry containing objects for the Falcon
             modbus BCM CB port."
     INDEX   { falconBCM03CBIndex }
     ::= { falconBCM03CBTable 1 }

          
FalconBCM03CBEntry ::= SEQUENCE {
     falconBCM03CBIndex       INTEGER,
     falconBCM03CBStatus      INTEGER, 
     falconBCM03CBReading     INTEGER,
     falconBCM03CBLabel       DisplayString
}     

falconBCM03CBIndex OBJECT-TYPE
    SYNTAX  INTEGER
    ACCESS  read-only
    STATUS  mandatory
    DESCRIPTION
           "A unique value for each BCM CB port.  Its value
            ranges between 1 and 42."
     ::= { falconBCM03CBEntry 1 }

falconBCM03CBStatus OBJECT-TYPE
    SYNTAX  INTEGER {
    notConfigured(0),
    offline(1),
    normal(2),
    zeroAmpAlarm(3),
    warning(4),
    alarm(5)
}
    ACCESS  read-only
    STATUS  mandatory
    DESCRIPTION
           "The current status for this circuit breaker."
    ::= { falconBCM03CBEntry  2 }

falconBCM03CBReading OBJECT-TYPE
    SYNTAX  INTEGER (-2147483648..2147483647)
    ACCESS  read-only
    STATUS  mandatory
    DESCRIPTION
           "The current reading (AMPS) for circuit breaker."
    ::= { falconBCM03CBEntry  3 }

falconBCM03CBLabel OBJECT-TYPE
    SYNTAX  DisplayString
    ACCESS  read-only
    STATUS  mandatory
    DESCRIPTION
           "A user-defined text string associated with the circuit breaker."
    ::= { falconBCM03CBEntry  4 }

falconBCM04  OBJECT IDENTIFIER ::= { falconBCMs  4 }

falconBCM04Label OBJECT-TYPE
    SYNTAX  DisplayString
    ACCESS  read-only
    STATUS  mandatory
    DESCRIPTION
           "A user-defined text string associated with the BCM."
    ::= { falconBCM04  1 }

falconBCM04CBTable OBJECT-TYPE
    SYNTAX  SEQUENCE OF FalconBCM04CBEntry
    ACCESS  not-accessible
    STATUS  mandatory
    DESCRIPTION
           "A table of the falcon modbus BCM CB port status."
    ::= { falconBCM04 2 }

falconBCM04CBEntry OBJECT-TYPE
     SYNTAX  FalconBCM04Entry
     ACCESS  not-accessible
     STATUS  mandatory
     DESCRIPTION
            "An entry containing objects for the Falcon
             modbus BCM CB port."
     INDEX   { falconBCM04CBIndex }
     ::= { falconBCM04CBTable 1 }

          
FalconBCM04CBEntry ::= SEQUENCE {
     falconBCM04CBIndex       INTEGER,
     falconBCM04CBStatus      INTEGER, 
     falconBCM04CBReading     INTEGER,
     falconBCM04CBLabel       DisplayString
}     

falconBCM04CBIndex OBJECT-TYPE
    SYNTAX  INTEGER
    ACCESS  read-only
    STATUS  mandatory
    DESCRIPTION
           "A unique value for each BCM CB port.  Its value
            ranges between 1 and 42."
     ::= { falconBCM04CBEntry 1 }

falconBCM04CBStatus OBJECT-TYPE
    SYNTAX  INTEGER {
    notConfigured(0),
    offline(1),
    normal(2),
    zeroAmpAlarm(3),
    warning(4),
    alarm(5)
}
    ACCESS  read-only
    STATUS  mandatory
    DESCRIPTION
           "The current status for this circuit breaker."
    ::= { falconBCM04CBEntry  2 }

falconBCM04CBReading OBJECT-TYPE
    SYNTAX  INTEGER (-2147483648..2147483647)
    ACCESS  read-only
    STATUS  mandatory
    DESCRIPTION
           "The current reading (AMPS) for circuit breaker."
    ::= { falconBCM04CBEntry  3 }

falconBCM04CBLabel OBJECT-TYPE
    SYNTAX  DisplayString
    ACCESS  read-only
    STATUS  mandatory
    DESCRIPTION
           "A user-defined text string associated with the circuit breaker."
    ::= { falconBCM04CBEntry  4 }


falconBCMTrap OBJECT IDENTIFIER ::= { falconModbus  2 }

falconBCM01Trap TRAP-TYPE
    ENTERPRISE   falconBCMTrap 
    VARIABLES {
        falconAlarmId,
        falconBCM01CBIndex,
        falconBCM01CBStatus,
        falconBCM01CBLabel,
        falconBCM01CBReading
    }
    DESCRIPTION
        "The current on a BCM #01 circuit breaker has 
         reached an alarm state."
    ::= 1

falconBCM02Trap TRAP-TYPE
    ENTERPRISE   falconBCMTrap 
    VARIABLES {
        falconAlarmId,
        falconBCM02CBIndex,
        falconBCM02CBStatus,
        falconBCM02CBLabel,
        falconBCM02CBReading
    }
    DESCRIPTION
        "The current on a BCM #02 circuit breaker has 
         reached an alarm state."
    ::= 2

falconBCM03Trap TRAP-TYPE
    ENTERPRISE   falconBCMTrap 
    VARIABLES {
        falconAlarmId,
        falconBCM03CBIndex,
        falconBCM03CBStatus,
        falconBCM03CBLabel,
        falconBCM03CBReading
    }
    DESCRIPTION
        "The current on a BCM #03 circuit breaker has 
         reached an alarm state."
    ::= 3

falconBCM04Trap TRAP-TYPE
    ENTERPRISE   falconBCMTrap 
    VARIABLES {
        falconAlarmId,
        falconBCM04CBIndex,
        falconBCM04CBStatus,
        falconBCM04CBLabel,
        falconBCM04CBReading
    }
    DESCRIPTION
        "The current on a BCM #04 circuit breaker has 
         reached an alarm state."
    ::= 4

falconBCMTrapClear OBJECT IDENTIFIER ::= { falconModbus  3 }

falconBCM01TrapClear TRAP-TYPE
    ENTERPRISE   falconBCMTrapClear 
    VARIABLES {
        falconAlarmId,
        falconBCM01CBIndex,
        falconBCM01CBStatus,
        falconBCM01CBLabel,
        falconBCM01CBReading
    }
    DESCRIPTION
        "The current on a BCM #01 circuit breaker has 
         returned to normal."
    ::= 1

falconBCM02TrapClear TRAP-TYPE
    ENTERPRISE   falconBCMTrapClear 
    VARIABLES {
        falconAlarmId,
        falconBCM02CBIndex,
        falconBCM02CBStatus,
        falconBCM02CBLabel,
        falconBCM02CBReading
    }
    DESCRIPTION
        "The current on a BCM #02 circuit breaker has 
         returned to normal."
    ::= 2

falconBCM03TrapClear TRAP-TYPE
    ENTERPRISE   falconBCMTrapClear 
    VARIABLES {
        falconAlarmId,
        falconBCM03CBIndex,
        falconBCM03CBStatus,
        falconBCM03CBLabel,
        falconBCM03CBReading
    }
    DESCRIPTION
        "The current on a BCM #03 circuit breaker has 
         returned to normal."
    ::= 3

falconBCM04TrapClear TRAP-TYPE
    ENTERPRISE   falconBCMTrapClear 
    VARIABLES {
        falconAlarmId,
        falconBCM04CBIndex,
        falconBCM04CBStatus,
        falconBCM04CBLabel,
        falconBCM04CBReading
    }
    DESCRIPTION
        "The current on a BCM #04 circuit breaker has 
         returned to normal."
    ::= 4
        
falconMbG628 OBJECT IDENTIFIER ::= { falconModbus 4 }

falconMbUnits  OBJECT IDENTIFIER ::= { falconMbG628  1 }

falconMbUnitsTable OBJECT-TYPE
    SYNTAX  SEQUENCE OF FalconMbUnitsEntry
    ACCESS  not-accessible
    STATUS  mandatory
    DESCRIPTION
           "A table of the falcon modbus unit status."
    ::= { falconMbUnits 1 }

falconMbUnitsEntry OBJECT-TYPE
     SYNTAX  FalconMbUnitsEntry
     ACCESS  not-accessible
     STATUS  mandatory
     DESCRIPTION
            "An entry containing objects for the Falcon
             modbus unit status."
     INDEX   { falconMbUnitsIndex }
     ::= { falconMbUnitsTable 1 }

          
FalconMbUnitsEntry ::= SEQUENCE {
     falconMbUnitsIndex       INTEGER,
     falconMbUnitsStatus      INTEGER, 
     falconMbUnitsLabel       DisplayString
}     

falconMbUnitsIndex OBJECT-TYPE
    SYNTAX  INTEGER
    ACCESS  read-only
    STATUS  mandatory
    DESCRIPTION
           "A unique value for each Modbus unit.  Its value
            ranges between 1 and 16."
     ::= { falconMbUnitsEntry 1 }

falconMbUnitsStatus OBJECT-TYPE
    SYNTAX  INTEGER {
    notConfigured(0),
    offline(1),
    normal(2),
    alarm(3)
}
    ACCESS  read-only
    STATUS  mandatory
    DESCRIPTION
           "The current status for this Modbus unit."
    ::= { falconMbUnitsEntry  2 }

falconMbUnitsLabel OBJECT-TYPE
    SYNTAX  DisplayString
    ACCESS  read-only
    STATUS  mandatory
    DESCRIPTION
           "A user-defined text string associated with the Modbus unit."
    ::= { falconMbUnitsEntry  3 }

falconModbusTrapData OBJECT IDENTIFIER ::= { falconMbG628  2 }

falconModbusTrapRegisterNumber OBJECT-TYPE
    SYNTAX  PositiveInteger
    ACCESS  not-accessible
    STATUS  mandatory
    DESCRIPTION
           "A Modbus register number (e.g. 40001)."
    ::= { falconModbusTrapData  1 }

falconModbusTrapRegisterLabel OBJECT-TYPE
    SYNTAX  DisplayString
    ACCESS  not-accessible
    STATUS  mandatory
    DESCRIPTION
           "A user-defined text string associated with the Modbus register"
    ::= { falconModbusTrapData  2 }

falconModbusTraps OBJECT IDENTIFIER ::= { falconModbus  5 }

falconModbusTrap TRAP-TYPE
    ENTERPRISE   falconModbusTraps 
    VARIABLES {
        falconAlarmId,
        falconMbUnitsIndex,
		falconMbUnitsStatus,
		falconMbUnitsLabel,
        falconModbusTrapRegisterNumber,
        falconModbusTrapRegisterLabel
    }
    DESCRIPTION
        "A Modbus device has register has reached an alarm state."
    ::= 1

falconModbusTrapsClear OBJECT IDENTIFIER ::= { falconModbus  6 }

falconModbusTrapClear TRAP-TYPE
    ENTERPRISE   falconModbusTrapsClear 
    VARIABLES {
        falconAlarmId,
        falconMbUnitsIndex,
		falconMbUnitsStatus,
		falconMbUnitsLabel,
        falconModbusTrapRegisterNumber,
        falconModbusTrapRegisterLabel
    }
    DESCRIPTION
        "A Modbus device register has returned to normal."
    ::= 1
        
END
