-- Toshiba MIB
-- RemotEye 4 System MIB
--
--{iso(1) org(3) dod(6) internet(1) private(4) enterprises(1)
-- toshiba(186) equ(1) equups(19) ticups(2) rmti4 (5) system(254)}
--=============================================================================

TIC-RMTI4-SYS-MIB DEFINITIONS ::= BEGIN

--=============================================================================
-- Update : January 30, 2015
-- By     : Edwin Rubio, Toshiba International Corp.
-- Revised: Added upsAgentClearFaultWarningHistory 
--		  : Modified Description for upsAgentClearUPSEventLog
--		  : Syntax Change for upsSNMPTrapsReceiversIPAddress 
--		  : Syntax Change for upsSNMPTrapReceiversTrapType 
--		  : Renamed upsTrapRE4UPSCommError to upsTrapRe4UPSCommError
--		  : Renamed upsTrapRE4UPSCommErrorClear to upsTrapRe4UPSCommErrorClear
--=============================================================================
-- Update : May 1, 2014
-- By     : Edwin Rubio, Toshiba International Corp.
-- Revised: Added upsTrapTestTrap/upsTrapTestTrapClear
--		  : Renamed upsEmailClientsDailyStatusRemotEye4SetLog to upsEmailClientsDailyStatusSystemSettingLog
--		  : Renamed upsEmailClientsEventStatusRemotEye4SetLog to upsEmailClientsEventStatusSystemSettingLog
--=============================================================================
-- Update : April 15, 2014
-- By     : Edwin Rubio, Toshiba International Corp.
-- Revised: Removed upsAgentGeneralRecordLogFrequency
--		  : Changed upsAgentHistoryLogFrequency to upsAgentGeneralRecordsLogFrequency
--		  : Changed upsAgentExtHistoryLogFrequency to upsAgentExtGeneralRecordsLogFrequency
--		  : Removed upsAgentClearGeneralHistory
--		  : Changed upsConnectedClientsConnectionTimeout to upsConnectedClientsConnectedTime
--		  : Changed upsEmailClientsDailyStatusHistoryLog to upsEmailClientsDailyStatusGeneralRecordsLog
--		  : Changed upsEmailClientsDailyStatusExtendedHistoryLog to upsEmailClientsDailyStatusExtGeneralRecordsLog
--		  : Removed upsEmailClientsDailyStatusGeneralLog
--		  : Changed upsEmailClientsEventStatusHistoryLog to upsEmailClientsEventStatusGeneralRecordsLog
--		  : Changed upsEmailClientsEventStatusExtendedHistoryLog to upsEmailClientsEventStatusExtGeneralRecordsLog
--		  : Removed upsEmailClientsEventStatusGeneralLog
--		  : Changed upsEMDType to upsEMDName
--		  : Changed upsAlarmLogInError to upsAlarmHTTPLogInError
--		  : Added upsTrapRE4UPSCommError
--=============================================================================
-- Update : January 13, 2014
-- By     : Edwin Rubio, Toshiba International Corp.
-- Revised: Modified upsEMDTemperatureHysteresis
--		  : Modified upsEMDHumidityHysteresis
--		  : Modified upsEMDAlarmR1Hysteresis
--		  : Modified upsEMDAlarmR2Hysteresis
--=============================================================================
-- Update : January 8, 2014
-- By     : Edwin Rubio, Toshiba International Corp.
-- Revised: Modified upsEMDTemperatureHysteresis OID
--		  : Modified upsEMDTemperatureCalibrationOffset OID
--		  : Modified upsEMDHumidityHysteresis OID
--		  : Modified upsEMDHumidityCalibrationOffset OID
--		  : Modified upsEMDAlarmR1Hysteresis OID
--		  : Modified upsEMDAlarmR2Hysteresis OID
--		  : Changed upsTraps ENTERPRISE from RMTI4System to system
--=============================================================================
-- Update : December 22, 2013
-- By     : Tiffany Tye, Toshiba International Corp.
-- Revised: RemotEye 4 System First Draft MIB for RemotEye 4
--==============================================================================

IMPORTS
 DisplayString, TimeStamp, TimeInterval, TestAndIncr, AutonomousType
 FROM SNMPv2-TC
 enterprises
 FROM RFC1155-SMI
 OBJECT-TYPE
 FROM RFC-1212
 TRAP-TYPE
 FROM RFC-1215;
       
 PositiveInteger    ::= INTEGER (0..2147483647)
 NonNegativeInteger ::= INTEGER (0..2147483647)


toshiba     OBJECT IDENTIFIER ::= { enterprises 186 }
equ         OBJECT IDENTIFIER ::= { toshiba 1 }
equUPS      OBJECT IDENTIFIER ::= { equ 19 }
ticUPS      OBJECT IDENTIFIER ::= { equUPS 2 }
rmti4       OBJECT IDENTIFIER ::= { ticUPS 5 }
system       	OBJECT IDENTIFIER ::= { rmti4 254 }

upsAgent    OBJECT IDENTIFIER ::= { system 1 }
upsConnectedClients  OBJECT IDENTIFIER ::= { system 2 }
upsEmail    OBJECT IDENTIFIER ::= { system 3 }
upsSNMP     OBJECT IDENTIFIER ::= { system 4 }
upsEMD      OBJECT IDENTIFIER ::= { system 5 }
upsAgentAlarm OBJECT IDENTIFIER ::= { system 6 }
upsTrap     OBJECT IDENTIFIER ::= { system 7 }

-- ===========================================================================
--
-- upsAgent – Group 1
--
-- ===========================================================================
upsAgentFirmwareVersion OBJECT-TYPE
      SYNTAX DisplayString (SIZE(0..63))
      ACCESS read-only
      STATUS mandatory
      DESCRIPTION
          "The UPS RemotEye 4 firmware version."
      ::= { upsAgent 1 }

upsAgentMACAddress OBJECT-TYPE
    SYNTAX DisplayString (SIZE(20))
    ACCESS read-only
    STATUS mandatory
    DESCRIPTION
        "The RemotEye 4 MAC address that NMS can identify the managed device."
    ::= { upsAgent 2 }


upsAgentIPAddress OBJECT-TYPE
        SYNTAX IpAddress
        ACCESS read-write
        STATUS mandatory
        DESCRIPTION
                "The RemotEye 4 IP address."
        ::= { upsAgent 3}

upsAgentGatewayAddress OBJECT-TYPE
        SYNTAX IpAddress
        ACCESS read-write
        STATUS mandatory
        DESCRIPTION
                "The gateway IP address that allow RemotEye 4
                 through routers."
        ::= { upsAgent 4}

upsAgentSubnetMask OBJECT-TYPE
        SYNTAX IpAddress
        ACCESS read-write
        STATUS mandatory
        DESCRIPTION
                "Internet address subnet mask."
        ::= { upsAgent 5}

upsAgentIPv6LinkLocalAddress OBJECT-TYPE
        SYNTAX IpAddress
        ACCESS read-write
        STATUS mandatory
        DESCRIPTION	
                "The RemotEye 4 IPv6 Link Local Address. "
        ::= { upsAgent 6}

upsAgentIPv6GlobalAddress OBJECT-TYPE
        SYNTAX IpAddress
        ACCESS read-write
        STATUS mandatory
        DESCRIPTION
                "The RemotEye 4 IPv6 Global Address."
        ::= { upsAgent 7}

upsAgentIPv6PrefixLength OBJECT-TYPE
        SYNTAX DisplayString (SIZE (0..63))
        ACCESS read-write
        STATUS mandatory
        DESCRIPTION
                "The RemotEye 4 IPv6 Prefix length."
        ::= { upsAgent 8}

upsIPv6RouterAddress OBJECT-TYPE
        SYNTAX IpAddress
        ACCESS read-write
        STATUS mandatory
        DESCRIPTION
                "The RemotEye 4 IPv6 Router Address."
        ::= { upsAgent 9}

upsAgentDate OBJECT-TYPE
        SYNTAX DisplayString (SIZE (10..10))
        UNITS "MM/DD/YYYY"
        ACCESS read-write
        STATUS mandatory
        DESCRIPTION
                "The date in RemotEye 4, format is (MM/DD/YYYY)."
        ::= { upsAgent 10}

upsAgentTime OBJECT-TYPE
        SYNTAX DisplayString (SIZE (8..8))
        UNITS "HH:MM:SS"
        ACCESS read-write
        STATUS mandatory
        DESCRIPTION
                "The time in RemotEye 4, 24 hour format is (hh:mm:ss)."
        ::= { upsAgent 11}

upsAgentNTPTimeServer       OBJECT-TYPE
        SYNTAX DisplayString (SIZE(0..63))
        ACCESS  read-write
        STATUS  mandatory
        DESCRIPTION
                "The IP address of the NTP server to synchronize RemotEye 4 Time and Date."
        ::= { upsAgent 12 }

upsAgentHistoryLogFrequency OBJECT-TYPE
        SYNTAX INTEGER (5..28800) -- in seconds
        UNITS "Seconds"
        ACCESS read-write
        STATUS mandatory
        DESCRIPTION
                "The frequency of updating the history log. The value
                 is in seconds."
        ::= { upsAgent 13 }

upsAgentExtHistoryLogFrequency 
	OBJECT-TYPE
        SYNTAX INTEGER (1..10080) -- in minutes
        UNITS "Minutes"
        ACCESS read-write
        STATUS mandatory
        DESCRIPTION
                 "The frequency of updating the extended history log. The value is in minutes."
        ::= { upsAgent 14 }

upsAgentEMDHistoryLogFrequency OBJECT-TYPE
        SYNTAX INTEGER (5..28800) -- in seconds
        UNITS "Seconds"
        ACCESS read-write
        STATUS mandatory
        DESCRIPTION
                "The frequency of updating the EMD history log. The value
                 is in seconds."
  ::= { upsAgent 15 }

upsAgentEMDExtHistoryLogFrequency OBJECT-TYPE
        SYNTAX INTEGER (1..10080) -- in minutes
        UNITS "Minutes"
        ACCESS read-write
        STATUS mandatory
        DESCRIPTION
                 "The frequency of updating the EMD extended history log. The value is in minutes."
        ::= { upsAgent 16 }

upsAgentPollRate OBJECT-TYPE
    SYNTAX INTEGER (1..999) 
    UNITS  "Second"
    ACCESS read-write
    STATUS mandatory
    DESCRIPTION
        "The frequency that RemotEye 4 polls the connected
         UPS in seconds."
    ::= { upsAgent 17 }

upsAgentBaudRate OBJECT-TYPE
        SYNTAX INTEGER
        ACCESS read-only
        STATUS mandatory
        DESCRIPTION
            "The serial port communication speed."
        ::= { upsAgent 18}

upsAgentDHCPControl OBJECT-TYPE
        SYNTAX  INTEGER {
                enabled(1),
                disabled(2)
                }
        ACCESS read-write
        STATUS mandatory
        DESCRIPTION
                "Enable or disable DHCP/BootP capability."
        ::= { upsAgent 19 }

upsAgentTelnetControl OBJECT-TYPE
        SYNTAX  INTEGER {
                enabled(1),
                disabled(2)
                }
        ACCESS read-write
        STATUS mandatory
        DESCRIPTION
                "Enable or disable telnet access."
        ::= { upsAgent 20 }

upsAgentTFTPControl OBJECT-TYPE
        SYNTAX  INTEGER {
                enabled(1),
                disabled(2)
                }
        ACCESS read-write
        STATUS mandatory
        DESCRIPTION
                "Enable or disable network upgrade capability."
        ::= { upsAgent 21 }

upsAgentSSHv2Control OBJECT-TYPE
        SYNTAX  INTEGER {
                enabled(1),
                disabled(2)
                }
        ACCESS read-write
        STATUS mandatory
        DESCRIPTION
                "Enable or disable SSHv2 protocol."
        ::= { upsAgent 22 }

upsAgentResetToDefault OBJECT-TYPE
        SYNTAX  INTEGER {
                reset(1),
                nothing(2)
                }
        ACCESS read-write
        STATUS mandatory
        DESCRIPTION
                "Reset all parameters of RemotEye 4 to default values."
        ::= { upsAgent 23 }

upsAgentRestart OBJECT-TYPE
        SYNTAX  INTEGER {
                restart(1),
                nothing(2)
                }
        ACCESS read-write
        STATUS mandatory
        DESCRIPTION
                "Restart RemotEye 4."
        ::= { upsAgent 24 }

upsAgentSystemName OBJECT-TYPE
    SYNTAX DisplayString (SIZE(0..31))
    ACCESS read-write
    STATUS mandatory
    DESCRIPTION
        "The Agent System name."
    ::= { upsAgent 25 }

upsAgentSystemContact OBJECT-TYPE
    SYNTAX DisplayString (SIZE(0..31))
    ACCESS read-write
    STATUS mandatory
    DESCRIPTION
        "Contact Information."
    ::= { upsAgent 26 }

upsAgentSystemLocation OBJECT-TYPE
    SYNTAX DisplayString (SIZE(0..31))
    ACCESS read-write
    STATUS mandatory
    DESCRIPTION
        "Agent Location."
    ::= { upsAgent 27 }

upsAgentClearGeneralRecordsLog OBJECT-TYPE
        SYNTAX  INTEGER {
                clear(1),
                nothing(2)
                }
        ACCESS read-write
        STATUS mandatory
        DESCRIPTION
                "Clear general records log data."
        ::= { upsAgent 28 }

upsAgentClearExtGeneralRecordsLog OBJECT-TYPE
        SYNTAX  INTEGER {
                clear(1),
                nothing(2)
                }
        ACCESS read-write
        STATUS mandatory
        DESCRIPTION
                "Clear extended general records log data."
        ::= { upsAgent 29 }

upsAgentClearTestHistory OBJECT-TYPE
        SYNTAX  INTEGER {
                clear(1),
                nothing(2)
                }
        ACCESS read-write
        STATUS mandatory
        DESCRIPTION
                "Clear test history log data."
        ::= { upsAgent 30 }

upsAgentClearBackupHistory OBJECT-TYPE
        SYNTAX  INTEGER {
                clear(1),
                nothing(2)
                }
        ACCESS read-write
        STATUS mandatory
        DESCRIPTION
                "Clear backup history log data."
        ::= { upsAgent 31 }

upsAgentClearFaultHistory OBJECT-TYPE
        SYNTAX  INTEGER {
                clear(1),
                nothing(2)
                }
        ACCESS read-write
        STATUS mandatory
        DESCRIPTION
                "Clear fault history log data."
        ::= { upsAgent 32 }

upsAgentClearOperationModeHistory OBJECT-TYPE
        SYNTAX  INTEGER {
                clear(1),
                nothing(2)
                }
        ACCESS read-write
        STATUS mandatory
        DESCRIPTION
                "Clear operation history log data."
        ::= { upsAgent 33 }

upsAgentClearWarningHistory OBJECT-TYPE
        SYNTAX  INTEGER {
                clear(1),
                nothing(2)
                }
        ACCESS read-write
        STATUS mandatory
        DESCRIPTION
                "Clear warning history log data."
        ::= { upsAgent 34 }


upsAgentClearSystemSettingChangeHistory OBJECT-TYPE
        SYNTAX  INTEGER {
                clear(1),
                nothing(2)
                }
        ACCESS read-write
        STATUS mandatory
        DESCRIPTION
                "Clear system settings change history log data."
        ::= { upsAgent 35 }

upsAgentClearFaultWarningHistory OBJECT-TYPE
        SYNTAX  INTEGER {
                clear(1),
                nothing(2)
                }
        ACCESS read-write
        STATUS mandatory
        DESCRIPTION
                "Clear Fault/Warning History log data."
        ::= { upsAgent 36 }
		
upsAgentClearUPSEventLog OBJECT-TYPE
        SYNTAX  INTEGER {
                clear(1),
                nothing(2)
                }
        ACCESS read-write
        STATUS mandatory
        DESCRIPTION
                "Clear UPS Event log data."
        ::= { upsAgent 37 }

upsAgentClearRMTI4EventLog OBJECT-TYPE
        SYNTAX  INTEGER {
                clear(1),
                nothing(2)
                }
        ACCESS read-write
        STATUS mandatory
        DESCRIPTION
                "Clear RMTI4 event log data."
        ::= { upsAgent 38 }

upsAgentClearEMDHistoryLog OBJECT-TYPE
        SYNTAX  INTEGER {
                clear(1),
                nothing(2)
                }
        ACCESS read-write
        STATUS mandatory
        DESCRIPTION
                "Clear EMD history log data."
        ::= { upsAgent 39 }

upsAgentClearEMDExtHistoryLog OBJECT-TYPE
        SYNTAX  INTEGER {
                clear(1),
                nothing(2)
                }
        ACCESS read-write
        STATUS mandatory
        DESCRIPTION
                "Clear EMD ext. history log data."
        ::= { upsAgent 40 }
--=========================================================================
--
-- upsConnectedClients – Group 2
--
-- ===========================================================================
upsConnectedClientsNumber OBJECT-TYPE
    SYNTAX NonNegativeInteger
    ACCESS read-only
    STATUS mandatory
    DESCRIPTION
        "The count of clients which have registered for UPS
         Shutdown control."
    ::= { upsConnectedClients 1 }

upsConnectedClientsTable OBJECT-TYPE
    SYNTAX SEQUENCE OF UpsConnectedClientsEntry
    ACCESS not-accessible
    STATUS mandatory
    DESCRIPTION
        "The devices powered by UPS and registered to RemotEye 4."
    ::= { upsConnectedClients 2 }

upsConnectedClientsEntry OBJECT-TYPE
    SYNTAX UpsConnectedClientsEntry
    ACCESS not-accessible
    STATUS mandatory
    DESCRIPTION
        "The devices protected by RemotEye 4."
    INDEX  { upsConnectedClientsIndex }
    ::= { upsConnectedClientsTable 1 }

UpsConnectedClientsEntry ::=
    SEQUENCE {
        upsConnectedClientsIndex               PositiveInteger,
        upsConnectedClientsIPAddress           IpAddress,
        upsConnectedClientsName                DisplayString,
        upsConnectedClientsTimeAtConnection    DisplayString,
        upsConnectedClientsShutdownDelay       DisplayString,
        upsConnectedClientsConnectedTime	   INTEGER,
        upsConnectedClientsShutdownTest        INTEGER
    }

-- ===========================================================================
-- upsConnectedClientsTable/upsConnectedClientsEntry/upsConnectedClientsIndex
-- ===========================================================================

upsConnectedClientsIndex OBJECT-TYPE
    SYNTAX PositiveInteger
    ACCESS read-only
    STATUS mandatory
    DESCRIPTION
        "The index number of the device that is registered to RemotEye     4."
    ::= { upsConnectedClientsEntry 1 }

upsConnectedClientsIPAddress OBJECT-TYPE
    SYNTAX IpAddress
    ACCESS read-only
    STATUS mandatory
    DESCRIPTION
        "The IP address of the device."
    ::= { upsConnectedClientsEntry 2 }

upsConnectedClientsName OBJECT-TYPE
    SYNTAX DisplayString (SIZE(0..31))
    ACCESS read-only
    STATUS mandatory
    DESCRIPTION
        "The name/description of the device plugged into the UPS."
    ::= { upsConnectedClientsEntry 3 }

upsConnectedClientsTimeAtConnection OBJECT-TYPE
    SYNTAX DisplayString (SIZE(0..31))
    ACCESS read-only
    STATUS mandatory
    DESCRIPTION
        "The time that the device registered to RemotEye 4."
    ::= { upsConnectedClientsEntry 4 }

upsConnectedClientsShutdownDelay OBJECT-TYPE
    SYNTAX DisplayString (SIZE(0..2))
    ACCESS read-only
    STATUS mandatory
    DESCRIPTION
        "The delay time that client will shut down after receive
         shut down request from RemotEye 4."
    ::= { upsConnectedClientsEntry 5 }
    
upsConnectedClientsConnectedTime OBJECT-TYPE
    SYNTAX INTEGER
    ACCESS read-only
    STATUS mandatory
    DESCRIPTION
            "The time at which the client registered with the RemotEye 4."
    ::= { upsConnectedClientsEntry 6 }
    
upsConnectedClientsShutdownTest OBJECT-TYPE
    SYNTAX INTEGER
    ACCESS read-write
    STATUS mandatory
    DESCRIPTION
            "The client will shut down test after receive
             shut down request from RemotEye 4."
    ::= { upsConnectedClientsEntry 7 }

--===========================================================================
--
-- upsEmail - Group 3
-- 
-- ===========================================================================

upsEmailMailServer OBJECT-TYPE
    SYNTAX DisplayString (SIZE (0..31))
    ACCESS read-write
    STATUS mandatory
    DESCRIPTION
        "The Email mail server for RemotEye 4."
    ::= { upsEmail 1 }

upsEmailUserAccount OBJECT-TYPE
    SYNTAX DisplayString (SIZE (0..15))
    ACCESS read-write
    STATUS mandatory
    DESCRIPTION
        "The email mail server login name."
    ::= { upsEmail 2 }

upsEmailUserPassword OBJECT-TYPE
    SYNTAX DisplayString (SIZE (0..15))
    ACCESS read-write
    STATUS mandatory
    DESCRIPTION
        "The Email mail server password."
    ::= { upsEmail 3 }

upsEmailDomainName OBJECT-TYPE
    SYNTAX DisplayString (SIZE (0..31))
    ACCESS read-write
    STATUS mandatory
    DESCRIPTION
        "The Email mail server domain name."
    ::= { upsEmail 4 }

upsEmailDNSServer OBJECT-TYPE
    SYNTAX IpAddress
    ACCESS read-write
    STATUS mandatory
    DESCRIPTION
        "The Email DNS server name."
    ::= { upsEmail 5 }

upsEmailStatusReportSendTime OBJECT-TYPE
    SYNTAX DisplayString (SIZE(8))
    ACCESS read-write
    STATUS mandatory
    DESCRIPTION
        "The Email Status Report Send Time."
    ::= { upsEmail 6 }

upsEmailClientsTable OBJECT-TYPE
    SYNTAX SEQUENCE OF UpsEmailClientsEntry
    ACCESS not-accessible
    STATUS mandatory
    DESCRIPTION
        "The email addresses that RemotEye 4 will send logs and status reports to."
    ::= { upsEmail 7 }

upsEmailClientsEntry OBJECT-TYPE
    SYNTAX UpsEmailClientsEntry
    ACCESS not-accessible
    STATUS mandatory
    DESCRIPTION
        "The email addresses that RemotEye 4 will send logs and status    
         reports to."
    INDEX  { upsEmailClientsIndex }
    ::= { upsEmailClientsTable 1 }

UpsEmailClientsEntry ::=
    SEQUENCE {
        upsEmailClientsIndex        		PositiveInteger,
        upsEmailClientsEmailAddress 		DisplayString,
        upsEmailClientsDescription  		DisplayString,
        upsEmailClientsType             	INTEGER,
        upsEmailClientsInfoLevel    		INTEGER
    }

-- ===========================================================================
-- upsEmailClientsTable/upsEmailClientsEntry/upsEmailClientsIndex
-- ===========================================================================

upsEmailClientsIndex OBJECT-TYPE
    SYNTAX PositiveInteger
    ACCESS read-only
    STATUS mandatory
    DESCRIPTION
        "The index of the email clients."
    ::= { upsEmailClientsEntry 1 }

upsEmailClientsEmailAddress OBJECT-TYPE
    SYNTAX DisplayString (SIZE(0..128))
    ACCESS read-write
    STATUS mandatory
    DESCRIPTION
        "The email address of the clients."
    ::= { upsEmailClientsEntry 2 }

upsEmailClientsDescription OBJECT-TYPE
    SYNTAX DisplayString (SIZE(0..31))
    ACCESS read-write
    STATUS mandatory
    DESCRIPTION
        "The name/description of the clients."
    ::= { upsEmailClientsEntry 3 }
    
upsEmailClientsType OBJECT-TYPE
    SYNTAX INTEGER {
    none(1),
    event(2),
    status(3),
    eventStatus(4)
    }
    ACCESS read-write
    STATUS mandatory
    DESCRIPTION
        "The type of receive."
    ::= { upsEmailClientsEntry 4 }

upsEmailClientsInfoLevel OBJECT-TYPE
    SYNTAX INTEGER {
        fault(1),
        warning(2),
        informational(3)
    }
    ACCESS read-write
    STATUS mandatory
    DESCRIPTION
        "The type of information that clients would like to receive."
    ::= { upsEmailClientsEntry 5 }

upsEmailClientsDailyStatusGeneralRecordsLog OBJECT-TYPE
    SYNTAX INTEGER {
    enabled (1),
    disabled(2)
    }
    ACCESS read-write
    STATUS mandatory
    DESCRIPTION
        "The Status general records log received."
    ::= { upsEmail 8 }

upsEmailClientsDailyStatusExtGeneralRecordsLog  OBJECT-TYPE
    SYNTAX INTEGER {
    enabled (1),
    disabled(2)
    }
    ACCESS read-write
    STATUS mandatory
    DESCRIPTION
        "The Daily Status extended general Log receive."
    ::= { upsEmail 9 }

upsEmailClientsDailyStatusUPSEventsLog  OBJECT-TYPE
    SYNTAX INTEGER {
    enabled (1),
    disabled(2)
    }
    ACCESS read-write
    STATUS mandatory
    DESCRIPTION
        "The type of receive."
    ::= { upsEmail 10 }

upsEmailClientsDailyStatusTestLog  OBJECT-TYPE
    SYNTAX INTEGER {
    enabled (1),
    disabled(2)
    }
    ACCESS read-write
    STATUS mandatory
    DESCRIPTION
        "The Daily Status Test Log receive."
    ::= { upsEmail 11 }

upsEmailClientsDailyStatusBackupLog  OBJECT-TYPE
    SYNTAX INTEGER {
    enabled (1),
    disabled(2)
    }
    ACCESS read-write
    STATUS mandatory
    DESCRIPTION
        "The Daily Status Backup Log receive."
    ::= { upsEmail 12 }


upsEmailClientsDailyStatusFaultLog  OBJECT-TYPE
    SYNTAX INTEGER {
    enabled (1),
    disabled(2)
    }
    ACCESS read-write
    STATUS mandatory
    DESCRIPTION
        "The Daily Status Fault Log receive."
    ::= { upsEmail 13 }

upsEmailClientsDailyStatusOperationLog  OBJECT-TYPE
    SYNTAX INTEGER {
    enabled (1),
    disabled(2)
    }
    ACCESS read-write
    STATUS mandatory
    DESCRIPTION
        "The Daily Status Operation Log receive."
    ::= { upsEmail 14 }

upsEmailClientsDailyStatusWarningLog  OBJECT-TYPE
    SYNTAX INTEGER {
    enabled (1),
    disabled(2)
    }
    ACCESS read-write
    STATUS mandatory
    DESCRIPTION
        "The Daily Status Warning Log receive."
    ::= { upsEmail 15 }

upsEmailClientsDailyStatusSystemSettingLog  OBJECT-TYPE
    SYNTAX INTEGER {
    enabled (1),
    disabled(2)
    }
    ACCESS read-write
    STATUS mandatory
    DESCRIPTION
        "The Daily Status RemotEye 4 Sets Log receive."
    ::= { upsEmail 16 }

upsEmailClientsDailyStatusRemotEye4EventsLog  OBJECT-TYPE
    SYNTAX INTEGER {
    enabled (1),
    disabled(2)
    }
    ACCESS read-write
    STATUS mandatory
    DESCRIPTION
        "The Daily Status RemotEye 4 Events Log receive."
    ::= { upsEmail 17 }

upsEmailClientsDailyStatusEMDHistoryLog OBJECT-TYPE
    SYNTAX INTEGER {
    enabled (1),
    disabled(2)
    }
    ACCESS read-write
    STATUS mandatory
    DESCRIPTION
        "The Daily Status EMD History Log receive."
    ::= { upsEmail 18 }

upsEmailClientsDailyStatusEMDExtendedHistoryLog  OBJECT-TYPE
    SYNTAX INTEGER {
    enabled (1),
    disabled(2)
    }
    ACCESS read-write
    STATUS mandatory
    DESCRIPTION
        "The Daily Status EMD Extended History Log receive."
    ::= { upsEmail 19 }


upsEmailClientsEventStatusGeneralRecordsLog OBJECT-TYPE
    SYNTAX INTEGER {
    enabled (1),
    disabled(2)
    }
    ACCESS read-write
    STATUS mandatory
    DESCRIPTION
        "The Event Status general records log receive."
    ::= { upsEmail 20 }

upsEmailClientsEventStatusExtGeneralRecordsLog  OBJECT-TYPE
    SYNTAX INTEGER {
    enabled (1),
    disabled(2)
    }
    ACCESS read-write
    STATUS mandatory
    DESCRIPTION
        "The Event Status extended general log receive."
    ::= { upsEmail 21 }

upsEmailClientsEventStatusUPSEventsLog  OBJECT-TYPE
    SYNTAX INTEGER {
    enabled (1),
    disabled(2)
    }
    ACCESS read-write
    STATUS mandatory
    DESCRIPTION
        "The Event Status UPS Event receive."
    ::= { upsEmail 22 }

upsEmailClientsEventStatusTestLog  OBJECT-TYPE
    SYNTAX INTEGER {
    enabled (1),
    disabled(2)
    }
    ACCESS read-write
    STATUS mandatory
    DESCRIPTION
        "The Event Status Test Log receive."
    ::= { upsEmail 23 }

upsEmailClientsEventStatusBackupLog  OBJECT-TYPE
    SYNTAX INTEGER {
    enabled (1),
    disabled(2)
    }
    ACCESS read-write
    STATUS mandatory
    DESCRIPTION
        "The Event Status Backup Log receive."
    ::= { upsEmail 24 }

upsEmailClientsEventStatusFaultLog  OBJECT-TYPE
    SYNTAX INTEGER {
    enabled (1),
    disabled(2)
    }
    ACCESS read-write
    STATUS mandatory
    DESCRIPTION
        "The Event Status Fault Log receive."
    ::= { upsEmail 25 }

upsEmailClientsEventStatusOperationLog  OBJECT-TYPE
    SYNTAX INTEGER {
    enabled (1),
    disabled(2)
    }
    ACCESS read-write
    STATUS mandatory
    DESCRIPTION
        "The Event Status Operation Log receive."
    ::= { upsEmail 26 }

upsEmailClientsEventStatusWarningLog  OBJECT-TYPE
    SYNTAX INTEGER {
    enabled (1),
    disabled(2)
    }
    ACCESS read-write
    STATUS mandatory
    DESCRIPTION
        "The Event Status Warning Log receive."
    ::= { upsEmail 27 }

upsEmailClientsEventStatusSystemSettingLog  OBJECT-TYPE
    SYNTAX INTEGER {
    enabled (1),
    disabled(2)
    }
    ACCESS read-write
    STATUS mandatory
    DESCRIPTION
        "The event Status System Setting change received."
    ::= { upsEmail 28 }

upsEmailClientsEventStatusRemotEye4EventsLog  OBJECT-TYPE
    SYNTAX INTEGER {
    enabled (1),
    disabled(2)
    }
    ACCESS read-write
    STATUS mandatory
    DESCRIPTION
        "The Event Status RemotEye 4 Events Log receive."
    ::= { upsEmail 29 }

upsEmailClientsEventStatusEMDHistoryLog OBJECT-TYPE
    SYNTAX INTEGER {
    enabled (1),
    disabled(2)
    }
    ACCESS read-write
    STATUS mandatory
    DESCRIPTION
        "The Event Status EMD History Log receive."
    ::= { upsEmail 30 }

upsEmailClientsEventStatusEMDExtendedHistoryLog  OBJECT-TYPE
    SYNTAX INTEGER {
    enabled (1),
    disabled(2)
    }
    ACCESS read-write
    STATUS mandatory
    DESCRIPTION
        "The Event Status EMD Extended History Log receive."
    ::= { upsEmail 31 }

-- ===========================================================================
--
-- upsSNMP - Group 4
-- 
-- ===========================================================================

upsSNMPTrapsReceiversTable OBJECT-TYPE
    SYNTAX SEQUENCE OF UpsSNMPTrapsReceiversEntry
    ACCESS not-accessible
    STATUS mandatory
    DESCRIPTION
        "A list of managers to send traps. The number of
         entries is given by the value of upsSNMPNumTrapReceivers."
    ::= { upsSNMP 1 }

upsSNMPTrapsReceiversEntry OBJECT-TYPE
    SYNTAX UpsSNMPTrapsReceiversEntry
    ACCESS not-accessible
    STATUS mandatory
    DESCRIPTION
        "The managers to send traps."
    INDEX  { upsSNMPTrapsReceiversIndex }
    ::= { upsSNMPTrapsReceiversTable 1 }

UpsSNMPTrapsReceiversEntry ::=
    SEQUENCE {
        upsSNMPTrapsReceiversIndex                     PositiveInteger,
        upsSNMPTrapsReceiversIPAddress                 DisplayString,
        upsSNMPTrapReceiversCommunityString            DisplayString,
        upsSNMPTrapReceiversTrapType                   INTEGER,
        upsSNMPTrapReceiversInfoReceivingSeverityLevel INTEGER,
        upsSNMPTrapReceiversDescription                DisplayString
    }

-- ===========================================================================
-- upsSNMPTrapsReceiversTable/upsSNMPTrapsReceiversEntry/upsSNMPTrapsReceiversIndex
-- ===========================================================================
upsSNMPTrapsReceiversIndex OBJECT-TYPE
    SYNTAX PositiveInteger
    ACCESS read-only
    STATUS mandatory
    DESCRIPTION
        "The index to a trap receiver entry."
    ::= { upsSNMPTrapsReceiversEntry 1 }

upsSNMPTrapsReceiversIPAddress OBJECT-TYPE
    SYNTAX DisplayString
    ACCESS read-write
    STATUS mandatory
    DESCRIPTION
        "The IP address of the manager to send a trap."
    ::= { upsSNMPTrapsReceiversEntry 2 }

upsSNMPTrapReceiversCommunityString OBJECT-TYPE
    SYNTAX DisplayString (SIZE(0..19))
    ACCESS read-write
    STATUS mandatory
    DESCRIPTION
        "The community name to use in the trap when
         sent to the manager."
    ::= { upsSNMPTrapsReceiversEntry 3 }

upsSNMPTrapReceiversTrapType OBJECT-TYPE
    SYNTAX INTEGER {
        none(1),
        toshiba-trap(2),
        rfc1628-trap(3)
    }
    ACCESS read-write
    STATUS mandatory
    DESCRIPTION
        "The trap type selected."
    ::= { upsSNMPTrapsReceiversEntry 4 }

upsSNMPTrapReceiversInfoReceivingSeverityLevel OBJECT-TYPE
    SYNTAX INTEGER {
        informational(1),
        warning(2),
        fault(3)
    }
    ACCESS read-write
    STATUS mandatory
    DESCRIPTION
        "The severity level of traps to be received by this manager."
    ::= { upsSNMPTrapsReceiversEntry 5 }

upsSNMPTrapReceiversDescription OBJECT-TYPE
    SYNTAX DisplayString (SIZE(0..31))
    ACCESS read-write
    STATUS mandatory
    DESCRIPTION
        "Description of trap receivers."
    ::= { upsSNMPTrapsReceiversEntry 6 }
    
upsSNMPSecurityUserTable OBJECT-TYPE
    SYNTAX SEQUENCE OF UpsSNMPSecurityUserEntry
    ACCESS not-accessible
    STATUS mandatory
    DESCRIPTION
        "A list of managers which can access RemotEye 4 with private
         community string."
    ::= { upsSNMP 2 }

upsSNMPSecurityUserEntry OBJECT-TYPE
    SYNTAX UpsSNMPSecurityUserEntry
    ACCESS not-accessible
    STATUS mandatory
    DESCRIPTION
        "The managers."
    INDEX  { upsSNMPSecurityUserIndex}
    ::= { upsSNMPSecurityUserTable 1 }

UpsSNMPSecurityUserEntry ::=
    SEQUENCE {
        upsSNMPSecurityUserIndex             PositiveInteger,
        upsSNMPSecurityUserName              DisplayString,
        upsSNMPSecurityUserAuthPassword      DisplayString,
        upsSNMPSecurityUserAuthProtocol      INTEGER,
        upsSNMPSecurityUserPrivPassword      DisplayString,
        upsSNMPSecurityUserPrivProtocol      INTEGER,
        upsSNMPSecurityUserLevel             INTEGER
    }

-- ===========================================================================
-- upsSNMPCommunitiesTable/upsSNMPCommunitiesEntry/upsSNMPCommunitiesIndex
-- ===========================================================================

upsSNMPSecurityUserIndex OBJECT-TYPE
    SYNTAX PositiveInteger
    ACCESS read-only
    STATUS mandatory
    DESCRIPTION
        "The index to access control entry."
    ::= { upsSNMPSecurityUserEntry 1 }

upsSNMPSecurityUserName OBJECT-TYPE
    SYNTAX DisplayString (SIZE(0..31))
    ACCESS read-write
    STATUS mandatory
    DESCRIPTION
        "The User Name for snmpv3 to access RemotEye 4."
    ::= { upsSNMPSecurityUserEntry 2 }

upsSNMPSecurityUserAuthPassword OBJECT-TYPE
    SYNTAX DisplayString (SIZE(0..31))
    ACCESS read-write
    STATUS mandatory
    DESCRIPTION
        "The Authentication key password for snmpv3 to access RemotEye 4."
    ::= { upsSNMPSecurityUserEntry 3 }


upsSNMPSecurityUserAuthProtocol OBJECT-TYPE
    SYNTAX INTEGER {
        md5(1),
        sha(2)
    }
    ACCESS read-write
    STATUS mandatory
    DESCRIPTION
        "The Authentication key create method for snmpv3 to access RemotEye 4."
    ::= { upsSNMPSecurityUserEntry 4 }
   
upsSNMPSecurityUserPrivPassword OBJECT-TYPE
    SYNTAX DisplayString (SIZE(0..31))
    ACCESS read-write
    STATUS mandatory
    DESCRIPTION
        "The privacy key password to access RemotEye 4."
    ::= { upsSNMPSecurityUserEntry 5 }


upsSNMPSecurityUserPrivProtocol OBJECT-TYPE
    SYNTAX INTEGER {
        des(1),
        aes(2)
    }
    ACCESS read-write
    STATUS mandatory
    DESCRIPTION
        "The privacy key create method for snmpv3 to access RemotEye 4."
    ::= { upsSNMPSecurityUserEntry 6 }

upsSNMPSecurityUserLevel OBJECT-TYPE
    SYNTAX INTEGER {
        noAuthNoPriv(1),
        authNoPriv(2),
        authPriv(3)
    }
    ACCESS read-write
    STATUS mandatory
    DESCRIPTION
        "The Security method for snmpv3 to access RemotEye 4."
    ::= { upsSNMPSecurityUserEntry 7 }

upsSNMPReadCommunicate OBJECT-TYPE
    SYNTAX DisplayString (SIZE(0..31))
    ACCESS read-write
    STATUS mandatory
    DESCRIPTION
        "For snmpv1 or v2c to read RemotEye 4."
    ::= { upsSNMP 3 }
   
upsSNMPWriteCommunicate OBJECT-TYPE
    SYNTAX DisplayString (SIZE(0..31))
    ACCESS read-write
    STATUS mandatory
    DESCRIPTION
        "For snmpv1 or v2c to read/write RemotEye 4."
    ::= { upsSNMP 4 }

upsSNMPTrapRetryCount OBJECT-TYPE
        SYNTAX  INTEGER
        ACCESS read-write
        STATUS mandatory
        DESCRIPTION
                "The count of repeat traps to send to NMS before trap
                 acknowledge received."
        ::= { upsSNMP 5}

upsSNMPTrapRetryTime OBJECT-TYPE
        SYNTAX  INTEGER
        ACCESS read-write
        STATUS mandatory
        DESCRIPTION
                "The time between retry traps sned to NMS."
        ::= { upsSNMP 6}

upsSNMPTrapAckSignature OBJECT-TYPE
        SYNTAX  INTEGER
        ACCESS read-write
        STATUS mandatory
        DESCRIPTION
                "The signature of trap acknowledge."
        ::= { upsSNMP 7}

upsSNMPMibVersion OBJECT-TYPE
        SYNTAX INTEGER
        ACCESS read-only
        STATUS mandatory
        DESCRIPTION
                "The version of MIB spec."
        ::= { upsSNMP 8 }

-- ===========================================================================
--
-- upsEMD - Group 5
-- 
-- ===========================================================================
upsEMDName OBJECT-TYPE
    SYNTAX DisplayString (SIZE(0..31))
    ACCESS read-write
    STATUS mandatory
    DESCRIPTION
        "The name assign to specific EMD."
    ::= { upsEMD 1 }

upsEMDTemperature OBJECT-TYPE
    SYNTAX INTEGER
    UNITS "C/F"
    ACCESS read-only
    STATUS mandatory
    DESCRIPTION
        "The EMD temperature."
    ::= { upsEMD 2 }

upsEMDTemperatureLowWarningSetPoint OBJECT-TYPE
    SYNTAX INTEGER
    UNITS "C/F"
    ACCESS read-write
    STATUS mandatory
    DESCRIPTION
        "The EMD temperature low warning set point."
    ::= { upsEMD 3 }

upsEMDTemperatureLowCriticalSetPoint OBJECT-TYPE
    SYNTAX INTEGER
    UNITS "C/F"
    ACCESS read-write
    STATUS mandatory
    DESCRIPTION
        "The EMD temperature low critical set point."
    ::= { upsEMD 4 }

upsEMDTemperatureHighWarningSetPoint OBJECT-TYPE
    SYNTAX INTEGER
    UNITS "C/F"
    ACCESS read-write
    STATUS mandatory
    DESCRIPTION
        "The EMD temperature high warning set point."
    ::= { upsEMD 5 }

upsEMDTemperatureHighCriticalSetPoint OBJECT-TYPE
    SYNTAX INTEGER
    UNITS "C/F"
    ACCESS read-write
    STATUS mandatory
    DESCRIPTION
        "The EMD temperature high critical set point."
    ::= { upsEMD 6 }

upsEMDTemperatureHysteresis OBJECT-TYPE
    SYNTAX INTEGER 
    UNITS "0 ~ 10 Seconds"
    ACCESS read-write
    STATUS mandatory
    DESCRIPTION
        "The EMD temperature hysteresis."
    ::= { upsEMD 7 }

upsEMDTemperatureCalibrationOffset OBJECT-TYPE
    SYNTAX  INTEGER {
                plus0(1),
               	plus5(2),
               	plus10(3),
               	plus15(4),
               	plus20(5),
               	plus25(6),
               	plus30(7),
               	minus5(8),
               	minus10(9),
               	minus15(10),
               	minus20(11),
               	minus25(12),
               	minus30(13)
    }
    UNITS "0.1"
    ACCESS read-write
    STATUS mandatory
    DESCRIPTION
        "The EMD temperature calibration offset unit 0.1 "
    ::= { upsEMD 8 }

upsEMDHumidity OBJECT-TYPE
    SYNTAX INTEGER
    UNITS "%"
    ACCESS read-only
    STATUS mandatory
    DESCRIPTION
        "The EMD Humidity."
    ::= { upsEMD 9 }

upsEMDHumidityLowWarningSetPoint OBJECT-TYPE
    SYNTAX INTEGER
    UNITS "%"
    ACCESS read-write
    STATUS mandatory
    DESCRIPTION
        "The EMD Humidity low warning set point."
    ::= { upsEMD 10 }

upsEMDHumidityLowCriticalSetPoint OBJECT-TYPE
    SYNTAX INTEGER
    UNITS "%"
    ACCESS read-write
    STATUS mandatory
    DESCRIPTION
        "The EMD Humidity low critical set point."
    ::= { upsEMD 11 }

upsEMDHumidityHighWarningSetPoint OBJECT-TYPE
    SYNTAX INTEGER
    UNITS "%"
    ACCESS read-write
    STATUS mandatory
    DESCRIPTION
        "The EMD Humidity high warning set point."
    ::= { upsEMD 12 }

upsEMDHumidityHighCriticalSetPoint OBJECT-TYPE
    SYNTAX INTEGER
    UNITS "%"
    ACCESS read-write
    STATUS mandatory
    DESCRIPTION
        "The EMD Humidity high critical set point."
    ::= { upsEMD 13 }

upsEMDHumidityHysteresis OBJECT-TYPE
    SYNTAX INTEGER
    UNITS "0 ~ 10 Seconds"
    ACCESS read-write
    STATUS mandatory
    DESCRIPTION
        "The EMD Humidity hysteresis."
    ::= { upsEMD 14 }

upsEMDHumidityCalibrationOffset OBJECT-TYPE
    SYNTAX  INTEGER {
                plus0(1),
               	plus1(2),
               	plus2(3),
               	plus3(4),
               	plus4(5),
               	plus5(6),
               	plus6(7),
               	minus1(8),
               	minus2(9),
               	minus3(10),
               	minus4(11),
               	minus5(12),
               	minus6(13)
    }
    UNITS "1 %"
    ACCESS read-write
    STATUS mandatory
    DESCRIPTION
        "The EMD Humidity calibration offset "
    ::= { upsEMD 15 }

upsEMDR1Name OBJECT-TYPE
    SYNTAX DisplayString
    ACCESS read-write
    STATUS mandatory
    DESCRIPTION
        "The name assign to dry contact 1."
    ::= { upsEMD 16 }

upsEMDR1Status OBJECT-TYPE
    SYNTAX INTEGER {
        unknown(1),
        disabled(2),
        active(3),
        inactive(4)
    }
    ACCESS read-only
    STATUS mandatory
    DESCRIPTION
        "The EMD dry contact 1 status."
    ::= { upsEMD 17 }

upsEMDAlarmR1Enable OBJECT-TYPE
    SYNTAX INTEGER {
        disable(1),
        normalClose(2),
        normalOpen(3)
    }
    ACCESS read-write
    STATUS mandatory
    DESCRIPTION
        "The EMD contact R1 alarm enable setting."
    ::= { upsEMD 18 }

upsEMDAlarmR1Hysteresis OBJECT-TYPE
	SYNTAX INTEGER
    UNITS "0 ~ 10 Seconds"
    ACCESS read-write
    STATUS mandatory
    DESCRIPTION
        "The EMD Contact R1 alarm hysteresis."
    ::= { upsEMD 19 }

upsEMDR2Name OBJECT-TYPE
    SYNTAX DisplayString
    ACCESS read-write
    STATUS mandatory
    DESCRIPTION
        "The name assign to dry contact 2."
    ::= { upsEMD 20 }

upsEMDR2Status OBJECT-TYPE
    SYNTAX INTEGER {
        unknown(1),
        disabled(2),
        active(3),
        inactive(4)        
    }
    ACCESS read-only
    STATUS mandatory
    DESCRIPTION
        "The EMD dry contact 2 status."
    ::= { upsEMD 21 }

upsEMDAlarmR2Enable OBJECT-TYPE
    SYNTAX INTEGER {
        disable(1),
        normalClose(2),
        normalOpen(3)
    }
    ACCESS read-write
    STATUS mandatory
    DESCRIPTION
        "The EMD contact R2 alarm enable setting."
    ::= { upsEMD 22 }

upsEMDAlarmR2Hysteresis OBJECT-TYPE
	SYNTAX INTEGER
    UNITS "0 ~ 10 Seconds"
    ACCESS read-write
    STATUS mandatory
    DESCRIPTION
        "The EMD Contact R2 alarm hysteresis."
    ::= { upsEMD 23 }

upsEMDSetup OBJECT-TYPE
    SYNTAX INTEGER {
        disabled(1),
        auto(2)
    }
    ACCESS read-write
    STATUS mandatory
    DESCRIPTION
        "The EMD enable setting."
    ::= { upsEMD 24 }

upsEMDUnit OBJECT-TYPE
    SYNTAX INTEGER {
        celsius(1),
        fahrenheit(2)
    }
    ACCESS read-write
    STATUS mandatory
    DESCRIPTION
        "The EMD unit setting."
    ::= { upsEMD 25 }
    
--=======================================================================
-- upsAgentAlarm – Group 6
--
-- Traps group
-- 
--=======================================================================

upsWellKnownAlarms OBJECT IDENTIFIER ::= { upsAgentAlarm  1 }


upsAlarmEMDSensor1AlarmTriggered OBJECT-TYPE
    SYNTAX INTEGER
    ACCESS read-only
    STATUS mandatory
    DESCRIPTION
        "Info: EMD sensor 1 alarm is triggered."
    ::= { upsWellKnownAlarms 1 }
    
upsAlarmEMDSensor2AlarmTriggered OBJECT-TYPE
    SYNTAX INTEGER
    ACCESS read-only
    STATUS mandatory
    DESCRIPTION
        "Info: EMD sensor 2 alarm is triggered."
    ::= { upsWellKnownAlarms 2 }
       
upsAlarmEMDHumidityAtLowCriticalPoint OBJECT-TYPE
    SYNTAX INTEGER
    ACCESS read-only
    STATUS mandatory
    DESCRIPTION
        "Info: EMD humidity is at low critical point."
    ::= { upsWellKnownAlarms 3 }

upsAlarmEMDHumidityAtHighCriticalPoint OBJECT-TYPE
    SYNTAX INTEGER
    ACCESS read-only
    STATUS mandatory
    DESCRIPTION
        "Info: EMD humidity is at high critical point."
    ::= { upsWellKnownAlarms 4 }

upsAlarmEMDHumidityAtLowWarningPoint OBJECT-TYPE
    SYNTAX INTEGER
    ACCESS read-only
    STATUS mandatory
    DESCRIPTION
        "Info: EMD humidity is at low warning point."
    ::= { upsWellKnownAlarms 5 }  

upsAlarmEMDHumidityAtHighWarningPoint OBJECT-TYPE
    SYNTAX INTEGER
    ACCESS read-only
    STATUS mandatory
    DESCRIPTION
        "Info: EMD humidity is at high warning point."
    ::= { upsWellKnownAlarms 6 }
    
upsAlarmEMDTemperatureAtLowCriticalPoint OBJECT-TYPE
    SYNTAX INTEGER
    ACCESS read-only
    STATUS mandatory
    DESCRIPTION
        "Info: EMD Temperature is at low critical point."
    ::= { upsWellKnownAlarms 7 }

upsAlarmEMDTemperatureAtHighCriticalPoint OBJECT-TYPE
    SYNTAX INTEGER
    ACCESS read-only
    STATUS mandatory
    DESCRIPTION
        "Info: EMD Temperature is at high critical point."
    ::= { upsWellKnownAlarms 8 }

upsAlarmEMDTemperatureAtLowWarningPoint OBJECT-TYPE
    SYNTAX INTEGER
    ACCESS read-only
    STATUS mandatory
    DESCRIPTION
        "Info: EMD Temperature is at low warning point."
    ::= { upsWellKnownAlarms 9 }

upsAlarmEMDTemperatureAtHighWarningPoint OBJECT-TYPE
    SYNTAX INTEGER
    ACCESS read-only
    STATUS mandatory
    DESCRIPTION
        "Info: EMD Temperature is at high warning point."
    ::= { upsWellKnownAlarms 10 }

upsAlarmHTTPLogInError OBJECT-TYPE
    SYNTAX INTEGER
    ACCESS read-only
    STATUS mandatory
    DESCRIPTION
        "Error with log in information"
    ::= { upsWellKnownAlarms 11 }
	
upsTrapRE4UPSCommError OBJECT-TYPE
    SYNTAX INTEGER
    ACCESS read-only
    STATUS mandatory
    DESCRIPTION
        "RemotEye 4 and UPS communication error."
    ::= { upsWellKnownAlarms 12 }
--
--=======================================================================
-- upsTraps – Group 7
--
-- Traps group
-- 
--=======================================================================

upsTrapEMDSensor1AlarmTriggered TRAP-TYPE 
    ENTERPRISE system
    DESCRIPTION
        "Warning: EMD sensor 1 alarm is triggered."
    ::= 1

upsTrapEMDSensor1AlarmTriggeredClear TRAP-TYPE 
    ENTERPRISE system
    DESCRIPTION
        "Warning Clear: EMD sensor 1 alarm is triggered."
    ::= 2

upsTrapEMDSensor2AlarmTriggered TRAP-TYPE 
    ENTERPRISE system
    DESCRIPTION
        "Warning: EMD sensor 2 alarm is triggered."
    ::= 3

upsTrapEMDSensor2AlarmTriggeredClear TRAP-TYPE 
    ENTERPRISE system
    DESCRIPTION
        "Warning Clear: EMD sensor 2 alarm is triggered."
    ::= 4

upsTrapEMDHumidityAtLowCriticalPoint TRAP-TYPE 
    ENTERPRISE system
    DESCRIPTION
        "Warning: EMD humidity is at low critical point."
    ::= 5

upsTrapEMDHumidityAtLowCriticalPointClear TRAP-TYPE 
    ENTERPRISE system
    DESCRIPTION
        "Warning Clear: EMD humidity is at low critical point."
    ::= 6

upsTrapEMDHumidityAtHighCriticalPoint TRAP-TYPE 
    ENTERPRISE system
    DESCRIPTION
        "Warning: EMD humidity is at high critical point."
    ::= 7

upsTrapEMDHumidityAtHighCriticalPointClear TRAP-TYPE 
    ENTERPRISE system
    DESCRIPTION
        "Warning Clear: EMD humidity is at high critical point."
    ::= 8

upsTrapEMDHumidityAtLowWarningPoint TRAP-TYPE 
    ENTERPRISE system
    DESCRIPTION
        "Warning: EMD humidity is at low warning point."
    ::= 9

upsTrapEMDHumidityAtLowWarningPointClear TRAP-TYPE 
    ENTERPRISE system
    DESCRIPTION
        "Warning Clear: EMD humidity is at low warning point."
    ::= 10

upsTrapEMDHumidityAtHighWarningPoint TRAP-TYPE
    ENTERPRISE system
    DESCRIPTION
        "Warning: EMD humidity is at high warning point."
    ::= 11

upsTrapEMDHumidityAtHighWarningPointClear TRAP-TYPE 
    ENTERPRISE system
    DESCRIPTION
        "Warning Clear: EMD humidity is at high warning point."
    ::= 12

upsTrapEMDTemperatureAtLowCriticalPoint TRAP-TYPE 
    ENTERPRISE system
    DESCRIPTION
        "Warning: EMD Temperature is at low critical point."
    ::= 13

upsTrapEMDTemperatureAtLowCriticalPointClear TRAP-TYPE 
    ENTERPRISE system
    DESCRIPTION
        "Warning Clear: EMD Temperature is at low critical point."
    ::= 14

upsTrapEMDTemperatureAtHighCriticalPoint TRAP-TYPE 
    ENTERPRISE system
    DESCRIPTION
        "Warning: EMD Temperature is at high critical point."
    ::= 15

upsTrapEMDTemperatureAtHighCriticalPointClear TRAP-TYPE 
    ENTERPRISE system
    DESCRIPTION
        "Warning Clear: EMD Temperature is at high critical point."
    ::= 16

upsTrapEMDTemperatureAtLowWarningPoint TRAP-TYPE 
    ENTERPRISE system
    DESCRIPTION
        "Warning: EMD Temperature is at low warning point."
    ::= 17

upsTrapEMDTemperatureAtLowWarningPointClear TRAP-TYPE 
    ENTERPRISE system
    DESCRIPTION
        "Warning Clear: EMD Temperature is at low warning point."
    ::= 18

upsTrapEMDTemperatureAtHighWarningPoint TRAP-TYPE 
    ENTERPRISE system
    DESCRIPTION
        "Warning: EMD Temperature is at high warning point."
    ::= 19

upsTrapEMDTemperatureAtHighWarningPointClear TRAP-TYPE 
     ENTERPRISE system
    DESCRIPTION
        "Warning Clear: EMD Temperature is at high warning point."
    ::= 20

upsTrapHTTPLogInError TRAP-TYPE 
    ENTERPRISE system
    DESCRIPTION
        "Info: Username/Password information is incorrect."
    ::= 21

upsTrapHTTPLogInErrorClear TRAP-TYPE 
    ENTERPRISE system
    DESCRIPTION
        "Info Clear: Username/Password information is incorrect."
    ::= 22

upsTrapRe4UPSCommError TRAP-TYPE
	ENTERPRISE system
	DESCRIPTION
		"Info: RemotEye 4 and UPS communication error."
	::=23

upsTrapRe4UPSCommErrorClear TRAP-TYPE 
    ENTERPRISE system
    DESCRIPTION
        "Info Clear: RemotEye 4 and UPS communication error."
    ::= 24
	
upsTrapTestTrap TRAP-TYPE 
	ENTERPRISE system
    DESCRIPTION
        "Info: This is a Trap Test."
    ::= 25
	
upsTrapTestTrapClear TRAP-TYPE 
	ENTERPRISE system
    DESCRIPTION
        "Info Clear: This is a Trap Test."
    ::= 26

END
