Pulizzi DEFINITIONS ::= BEGIN

IMPORTS
	OBJECT-TYPE, MODULE-IDENTITY, enterprises, 
	IpAddress, Integer32
		FROM SNMPv2-SMI
	DisplayString
		FROM SNMPv2-TC;

pulizzi MODULE-IDENTITY
	LAST-UPDATED "200410081703Z"
	ORGANIZATION 
		""
	CONTACT-INFO 
		""
	DESCRIPTION 
		""
::= { enterprises 20677 }

ipv3600              OBJECT IDENTIFIER ::= { pulizzi 2 }
unitConfig           OBJECT IDENTIFIER ::= { ipv3600 1 }
networkSettings      OBJECT IDENTIFIER ::= { ipv3600 2 }
logManagerConfig     OBJECT IDENTIFIER ::= { ipv3600 3 }
serialSettings       OBJECT IDENTIFIER ::= { ipv3600 4 }
telnetSettings       OBJECT IDENTIFIER ::= { ipv3600 5 }
outletMngt           OBJECT IDENTIFIER ::= { ipv3600 6 }
outletConfig         OBJECT IDENTIFIER ::= { outletMngt 1 }
outlet1              OBJECT IDENTIFIER ::= { outletConfig 1 }
outlet2              OBJECT IDENTIFIER ::= { outletConfig 2 }
outlet3              OBJECT IDENTIFIER ::= { outletConfig 3 }
outlet4              OBJECT IDENTIFIER ::= { outletConfig 4 }
outlet5              OBJECT IDENTIFIER ::= { outletConfig 5 }
outlet6              OBJECT IDENTIFIER ::= { outletConfig 6 }
outlet7              OBJECT IDENTIFIER ::= { outletConfig 7 }
outlet8              OBJECT IDENTIFIER ::= { outletConfig 8 }
outlet9              OBJECT IDENTIFIER ::= { outletConfig 9 }
outlet10             OBJECT IDENTIFIER ::= { outletConfig 10 }
outlet11             OBJECT IDENTIFIER ::= { outletConfig 11 }
outlet12             OBJECT IDENTIFIER ::= { outletConfig 12 }
outlet13             OBJECT IDENTIFIER ::= { outletConfig 13 }
outlet14             OBJECT IDENTIFIER ::= { outletConfig 14 }
outlet15             OBJECT IDENTIFIER ::= { outletConfig 15 }
outlet16             OBJECT IDENTIFIER ::= { outletConfig 16 }
outlet17             OBJECT IDENTIFIER ::= { outletConfig 17 }
outlet18             OBJECT IDENTIFIER ::= { outletConfig 18 }
outlet19             OBJECT IDENTIFIER ::= { outletConfig 19 }
outlet20             OBJECT IDENTIFIER ::= { outletConfig 20 }
outlet21             OBJECT IDENTIFIER ::= { outletConfig 21 }
outlet22             OBJECT IDENTIFIER ::= { outletConfig 22 }
outlet23             OBJECT IDENTIFIER ::= { outletConfig 23 }
outlet24             OBJECT IDENTIFIER ::= { outletConfig 24 }
outletControl        OBJECT IDENTIFIER ::= { outletMngt 2 }
outletStatus         OBJECT IDENTIFIER ::= { outletMngt 3 }

-- Configure SNMP settings for the IPV3600 module.

snmpSettings         OBJECT IDENTIFIER ::= { ipv3600 7 }
snmpTraps            OBJECT IDENTIFIER ::= { snmpSettings 8 }
environmentalSettings  OBJECT IDENTIFIER ::= { ipv3600 8 }
temperatureSensorConfig  OBJECT IDENTIFIER ::= { environmentalSettings 1 }
tempSensor1          OBJECT IDENTIFIER ::= { temperatureSensorConfig 1 }
tempSensor2          OBJECT IDENTIFIER ::= { temperatureSensorConfig 2 }
humiditySensorConfig  OBJECT IDENTIFIER ::= { environmentalSettings 2 }
humSensor1           OBJECT IDENTIFIER ::= { humiditySensorConfig 1 }
contactClosureConfig  OBJECT IDENTIFIER ::= { environmentalSettings 3 }
contactClosure1      OBJECT IDENTIFIER ::= { contactClosureConfig 1 }
contactClosure2      OBJECT IDENTIFIER ::= { contactClosureConfig 2 }
contactClosure3      OBJECT IDENTIFIER ::= { contactClosureConfig 3 }
outletSectionConfig  OBJECT IDENTIFIER ::= { environmentalSettings 4 }
outletSection1Config  OBJECT IDENTIFIER ::= { outletSectionConfig 1 }
outletSection2Config  OBJECT IDENTIFIER ::= { outletSectionConfig 2 }
outletSection3Config  OBJECT IDENTIFIER ::= { outletSectionConfig 3 }
currentSensorValues  OBJECT IDENTIFIER ::= { environmentalSettings 5 }
currentOutletSectionValues  OBJECT IDENTIFIER ::= { environmentalSettings 6 }
outletSection1       OBJECT IDENTIFIER ::= { currentOutletSectionValues 1 }
outletSection2       OBJECT IDENTIFIER ::= { currentOutletSectionValues 2 }
outletSection3       OBJECT IDENTIFIER ::= { currentOutletSectionValues 3 }
total                OBJECT IDENTIFIER ::= { currentOutletSectionValues 4 }

unitName  OBJECT-TYPE
	SYNTAX     OCTET STRING
	MAX-ACCESS read-write
	STATUS     current
	DESCRIPTION 
		""
	::= { unitConfig 1 }

strappingId  OBJECT-TYPE
	SYNTAX     Integer32 (0..25)
	MAX-ACCESS read-write
	STATUS     current
	DESCRIPTION 
		""
	::= { unitConfig 2 }

unitTime  OBJECT-TYPE
	SYNTAX     OCTET STRING
	MAX-ACCESS read-write
	STATUS     current
	DESCRIPTION 
		""
	::= { unitConfig 3 }

unitDate  OBJECT-TYPE
	SYNTAX     OCTET STRING
	MAX-ACCESS read-write
	STATUS     current
	DESCRIPTION 
		""
	::= { unitConfig 4 }

unitDayOfWeek  OBJECT-TYPE
	SYNTAX     INTEGER {
		sunday (1),
		monday (2),
		tuesday (3),
		wednesday (4),
		thursday (5),
		friday (6),
		saturday (7)
	}
	MAX-ACCESS read-write
	STATUS     current
	DESCRIPTION 
		""
	::= { unitConfig 5 }

vaLoggingInterval  OBJECT-TYPE
	SYNTAX     INTEGER {
		disabled (0),
		fiveminutes (1),
		fifteenminutes (2),
		hourly (3)
	}
	MAX-ACCESS read-write
	STATUS     current
	DESCRIPTION 
		""
	::= { unitConfig 6 }

keyBoardTime  OBJECT-TYPE
	SYNTAX     Integer32
	MAX-ACCESS read-write
	STATUS     current
	DESCRIPTION 
		""
	::= { unitConfig 7 }

invertDisplay  OBJECT-TYPE
	SYNTAX     INTEGER {
		normal (0),
		inverted (1)
	}
	MAX-ACCESS read-write
	STATUS     current
	DESCRIPTION 
		""
	::= { unitConfig 8 }

fahrenheitOrCelsius  OBJECT-TYPE
	SYNTAX     INTEGER {
		fahrenheit (0),
		celsius (1)
	}
	MAX-ACCESS read-write
	STATUS     current
	DESCRIPTION 
		""
	::= { unitConfig 9 }

unitIPAddress  OBJECT-TYPE
	SYNTAX     IpAddress
	MAX-ACCESS read-write
	STATUS     current
	DESCRIPTION 
		""
	::= { networkSettings 1 }

subnetMask  OBJECT-TYPE
	SYNTAX     IpAddress
	MAX-ACCESS read-write
	STATUS     current
	DESCRIPTION 
		""
	::= { networkSettings 2 }

defaultGateway  OBJECT-TYPE
	SYNTAX     IpAddress
	MAX-ACCESS read-write
	STATUS     current
	DESCRIPTION 
		""
	::= { networkSettings 3 }

webPort  OBJECT-TYPE
	SYNTAX     Integer32
	MAX-ACCESS read-write
	STATUS     current
	DESCRIPTION 
		""
	::= { networkSettings 4 }

webEnabled  OBJECT-TYPE
	SYNTAX     INTEGER {
		enabled (1),
		disabled (2)
	}
	MAX-ACCESS read-write
	STATUS     current
	DESCRIPTION 
		""
	::= { networkSettings 5 }

macAddress  OBJECT-TYPE
	SYNTAX     OCTET STRING
	MAX-ACCESS read-only
	STATUS     current
	DESCRIPTION 
		""
	::= { networkSettings 6 }

enablePing  OBJECT-TYPE
	SYNTAX     INTEGER {
		disabled (0),
		enabled (1)
	}
	MAX-ACCESS read-write
	STATUS     current
	DESCRIPTION 
		""
	::= { networkSettings 7 }

pingInterval  OBJECT-TYPE
	SYNTAX     INTEGER {
		fiveminutes (0),
		fifteenminutes (1),
		onehour (2),
		disabled (3)
	}
	MAX-ACCESS read-write
	STATUS     current
	DESCRIPTION 
		""
	::= { networkSettings 8 }

mailServerIPAddress  OBJECT-TYPE
	SYNTAX     IpAddress
	MAX-ACCESS read-write
	STATUS     current
	DESCRIPTION 
		""
	::= { logManagerConfig 1 }

sendLogFrom  OBJECT-TYPE
	SYNTAX     OCTET STRING
	MAX-ACCESS read-write
	STATUS     current
	DESCRIPTION 
		""
	::= { logManagerConfig 2 }

sendLogToUser1Address  OBJECT-TYPE
	SYNTAX     OCTET STRING
	MAX-ACCESS read-write
	STATUS     current
	DESCRIPTION 
		""
	::= { logManagerConfig 3 }

sendLogToUser2Address  OBJECT-TYPE
	SYNTAX     OCTET STRING
	MAX-ACCESS read-write
	STATUS     current
	DESCRIPTION 
		""
	::= { logManagerConfig 4 }

sendAllertsToUser1Address  OBJECT-TYPE
	SYNTAX     OCTET STRING
	MAX-ACCESS read-write
	STATUS     current
	DESCRIPTION 
		""
	::= { logManagerConfig 5 }

sendAllertsToUser2Address  OBJECT-TYPE
	SYNTAX     OCTET STRING
	MAX-ACCESS read-write
	STATUS     current
	DESCRIPTION 
		""
	::= { logManagerConfig 6 }

sendLogFrequency  OBJECT-TYPE
	SYNTAX     INTEGER {
		weekly-on-Sunday (1),
		weekly-on-Monday (2),
		weekly-on-Tuesday (3),
		weekly-on-Wednesday (4),
		weekly-on-Thursday (5),
		weekly-on-Friday (6),
		weekly-on-Saturday (7),
		daily (8),
		when-full (9),
		never (10)
	}
	MAX-ACCESS read-write
	STATUS     current
	DESCRIPTION 
		""
	::= { logManagerConfig 7 }

sendLogTime  OBJECT-TYPE
	SYNTAX     OCTET STRING
	MAX-ACCESS read-write
	STATUS     current
	DESCRIPTION 
		""
	::= { logManagerConfig 8 }

userLogInLogOut  OBJECT-TYPE
	SYNTAX     INTEGER {
		disabled (1),
		sendToLog (2),
		sendAllert (3),
		sendtoLogAndAllert (4)
	}
	MAX-ACCESS read-write
	STATUS     current
	DESCRIPTION 
		""
	::= { logManagerConfig 9 }

userLogInLogOutFailed  OBJECT-TYPE
	SYNTAX     INTEGER {
		disabled (1),
		sendToLog (2),
		sendAllert (3),
		sendtoLogAndAllert (4)
	}
	MAX-ACCESS read-write
	STATUS     current
	DESCRIPTION 
		""
	::= { logManagerConfig 10 }

outletActivity  OBJECT-TYPE
	SYNTAX     INTEGER {
		disabled (1),
		sendToLog (2),
		sendAllert (3),
		sendtoLogAndAllert (4)
	}
	MAX-ACCESS read-write
	STATUS     current
	DESCRIPTION 
		""
	::= { logManagerConfig 11 }

systemOnOff  OBJECT-TYPE
	SYNTAX     INTEGER {
		disabled (1),
		sendToLog (2),
		sendAllert (3),
		sendtoLogAndAllert (4)
	}
	MAX-ACCESS read-write
	STATUS     current
	DESCRIPTION 
		""
	::= { logManagerConfig 12 }

outletSection1Log  OBJECT-TYPE
	SYNTAX     INTEGER {
		disabled (0),
		sendAlert (1)
	}
	MAX-ACCESS read-write
	STATUS     current
	DESCRIPTION 
		""
	::= { logManagerConfig 13 }

outletSection2Log  OBJECT-TYPE
	SYNTAX     INTEGER {
		disabled (0),
		sendAlert (1)
	}
	MAX-ACCESS read-write
	STATUS     current
	DESCRIPTION 
		""
	::= { logManagerConfig 14 }

outletSection3Log  OBJECT-TYPE
	SYNTAX     INTEGER {
		disabled (0),
		sendAlert (1)
	}
	MAX-ACCESS read-write
	STATUS     current
	DESCRIPTION 
		""
	::= { logManagerConfig 15 }

tempSensor1Log  OBJECT-TYPE
	SYNTAX     INTEGER {
		disabled (0),
		sendAlert (1)
	}
	MAX-ACCESS read-write
	STATUS     current
	DESCRIPTION 
		""
	::= { logManagerConfig 16 }

tempSensor2Log  OBJECT-TYPE
	SYNTAX     INTEGER {
		disabled (0),
		sendAlert (1)
	}
	MAX-ACCESS read-write
	STATUS     current
	DESCRIPTION 
		""
	::= { logManagerConfig 17 }

humSensor1Log  OBJECT-TYPE
	SYNTAX     INTEGER {
		disabled (0),
		sendAlert (1)
	}
	MAX-ACCESS read-write
	STATUS     current
	DESCRIPTION 
		""
	::= { logManagerConfig 18 }

contactClosure1Log  OBJECT-TYPE
	SYNTAX     INTEGER {
		disabled (0),
		sendAlert (1)
	}
	MAX-ACCESS read-write
	STATUS     current
	DESCRIPTION 
		""
	::= { logManagerConfig 19 }

contactClosure2Log  OBJECT-TYPE
	SYNTAX     INTEGER {
		disabled (0),
		sendAlert (1)
	}
	MAX-ACCESS read-write
	STATUS     current
	DESCRIPTION 
		""
	::= { logManagerConfig 20 }

contactClosure3Log  OBJECT-TYPE
	SYNTAX     INTEGER {
		disabled (0),
		sendAlert (1)
	}
	MAX-ACCESS read-write
	STATUS     current
	DESCRIPTION 
		""
	::= { logManagerConfig 21 }

baudRate  OBJECT-TYPE
	SYNTAX     INTEGER {
		baud9600 (0),
		baud19200 (1),
		baud38400 (2)
	}
	MAX-ACCESS read-write
	STATUS     current
	DESCRIPTION 
		""
	::= { serialSettings 1 }

telnetPort  OBJECT-TYPE
	SYNTAX     Integer32
	MAX-ACCESS read-write
	STATUS     current
	DESCRIPTION 
		""
	::= { telnetSettings 1 }

telnetEnabled  OBJECT-TYPE
	SYNTAX     INTEGER {
		enabled (1),
		disabled (2)
	}
	MAX-ACCESS read-write
	STATUS     current
	DESCRIPTION 
		""
	::= { telnetSettings 2 }

outlet1Name  OBJECT-TYPE
	SYNTAX     OCTET STRING
	MAX-ACCESS read-write
	STATUS     current
	DESCRIPTION 
		"Name of Outlet #1"
	::= { outlet1 1 }

outlet1PingIpAddress  OBJECT-TYPE
	SYNTAX     IpAddress
	MAX-ACCESS read-write
	STATUS     current
	DESCRIPTION 
		""
	::= { outlet1 2 }

outlet1Link  OBJECT-TYPE
	SYNTAX     OCTET STRING
	MAX-ACCESS read-write
	STATUS     current
	DESCRIPTION 
		""
	::= { outlet1 3 }

outlet1SequenceTime  OBJECT-TYPE
	SYNTAX     Integer32
	MAX-ACCESS read-write
	STATUS     current
	DESCRIPTION 
		""
	::= { outlet1 4 }

outlet1RebootTime  OBJECT-TYPE
	SYNTAX     Integer32
	MAX-ACCESS read-write
	STATUS     current
	DESCRIPTION 
		""
	::= { outlet1 5 }

outlet2Name  OBJECT-TYPE
	SYNTAX     OCTET STRING
	MAX-ACCESS read-write
	STATUS     current
	DESCRIPTION 
		""
	::= { outlet2 1 }

outlet2PingIpAddress  OBJECT-TYPE
	SYNTAX     IpAddress
	MAX-ACCESS read-write
	STATUS     current
	DESCRIPTION 
		""
	::= { outlet2 2 }

outlet2Link  OBJECT-TYPE
	SYNTAX     OCTET STRING
	MAX-ACCESS read-write
	STATUS     current
	DESCRIPTION 
		""
	::= { outlet2 3 }

outlet2SequenceTime  OBJECT-TYPE
	SYNTAX     Integer32
	MAX-ACCESS read-write
	STATUS     current
	DESCRIPTION 
		""
	::= { outlet2 4 }

outlet2RebootTime  OBJECT-TYPE
	SYNTAX     Integer32
	MAX-ACCESS read-write
	STATUS     current
	DESCRIPTION 
		""
	::= { outlet2 5 }

outlet3Name  OBJECT-TYPE
	SYNTAX     OCTET STRING
	MAX-ACCESS read-write
	STATUS     current
	DESCRIPTION 
		""
	::= { outlet3 1 }

outlet3PingIpAddress  OBJECT-TYPE
	SYNTAX     IpAddress
	MAX-ACCESS read-write
	STATUS     current
	DESCRIPTION 
		""
	::= { outlet3 2 }

outlet3Link  OBJECT-TYPE
	SYNTAX     OCTET STRING
	MAX-ACCESS read-write
	STATUS     current
	DESCRIPTION 
		""
	::= { outlet3 3 }

outlet3SequenceTime  OBJECT-TYPE
	SYNTAX     Integer32
	MAX-ACCESS read-write
	STATUS     current
	DESCRIPTION 
		""
	::= { outlet3 4 }

outlet3RebootTime  OBJECT-TYPE
	SYNTAX     Integer32
	MAX-ACCESS read-write
	STATUS     current
	DESCRIPTION 
		""
	::= { outlet3 5 }

outlet4Name  OBJECT-TYPE
	SYNTAX     OCTET STRING
	MAX-ACCESS read-write
	STATUS     current
	DESCRIPTION 
		""
	::= { outlet4 1 }

outlet4PingIpAddress  OBJECT-TYPE
	SYNTAX     IpAddress
	MAX-ACCESS read-write
	STATUS     current
	DESCRIPTION 
		""
	::= { outlet4 2 }

outlet4Link  OBJECT-TYPE
	SYNTAX     OCTET STRING
	MAX-ACCESS read-write
	STATUS     current
	DESCRIPTION 
		""
	::= { outlet4 3 }

outlet4SequenceTime  OBJECT-TYPE
	SYNTAX     Integer32
	MAX-ACCESS read-write
	STATUS     current
	DESCRIPTION 
		""
	::= { outlet4 4 }

outlet4RebootTime  OBJECT-TYPE
	SYNTAX     Integer32
	MAX-ACCESS read-write
	STATUS     current
	DESCRIPTION 
		""
	::= { outlet4 5 }

outlet5Name  OBJECT-TYPE
	SYNTAX     OCTET STRING
	MAX-ACCESS read-write
	STATUS     current
	DESCRIPTION 
		""
	::= { outlet5 1 }

outlet5PingIpAddress  OBJECT-TYPE
	SYNTAX     IpAddress
	MAX-ACCESS read-write
	STATUS     current
	DESCRIPTION 
		""
	::= { outlet5 2 }

outlet5Link  OBJECT-TYPE
	SYNTAX     OCTET STRING
	MAX-ACCESS read-write
	STATUS     current
	DESCRIPTION 
		""
	::= { outlet5 3 }

outlet5SequenceTime  OBJECT-TYPE
	SYNTAX     Integer32
	MAX-ACCESS read-write
	STATUS     current
	DESCRIPTION 
		""
	::= { outlet5 4 }

outlet5RebootTime  OBJECT-TYPE
	SYNTAX     Integer32
	MAX-ACCESS read-write
	STATUS     current
	DESCRIPTION 
		""
	::= { outlet5 5 }

outlet6Name  OBJECT-TYPE
	SYNTAX     OCTET STRING
	MAX-ACCESS read-write
	STATUS     current
	DESCRIPTION 
		""
	::= { outlet6 1 }

outlet6PingIpAddress  OBJECT-TYPE
	SYNTAX     IpAddress
	MAX-ACCESS read-write
	STATUS     current
	DESCRIPTION 
		""
	::= { outlet6 2 }

outlet6Link  OBJECT-TYPE
	SYNTAX     OCTET STRING
	MAX-ACCESS read-write
	STATUS     current
	DESCRIPTION 
		""
	::= { outlet6 3 }

outlet6SequenceTime  OBJECT-TYPE
	SYNTAX     Integer32
	MAX-ACCESS read-write
	STATUS     current
	DESCRIPTION 
		""
	::= { outlet6 4 }

outlet6RebootTime  OBJECT-TYPE
	SYNTAX     Integer32
	MAX-ACCESS read-write
	STATUS     current
	DESCRIPTION 
		""
	::= { outlet6 5 }

outlet7Name  OBJECT-TYPE
	SYNTAX     OCTET STRING
	MAX-ACCESS read-write
	STATUS     current
	DESCRIPTION 
		""
	::= { outlet7 1 }

outlet7PingIpAddress  OBJECT-TYPE
	SYNTAX     IpAddress
	MAX-ACCESS read-write
	STATUS     current
	DESCRIPTION 
		""
	::= { outlet7 2 }

outlet7Link  OBJECT-TYPE
	SYNTAX     OCTET STRING
	MAX-ACCESS read-write
	STATUS     current
	DESCRIPTION 
		""
	::= { outlet7 3 }

outlet7SequenceTime  OBJECT-TYPE
	SYNTAX     Integer32
	MAX-ACCESS read-write
	STATUS     current
	DESCRIPTION 
		""
	::= { outlet7 4 }

outlet7RebootTime  OBJECT-TYPE
	SYNTAX     Integer32
	MAX-ACCESS read-write
	STATUS     current
	DESCRIPTION 
		""
	::= { outlet7 5 }

outlet8Name  OBJECT-TYPE
	SYNTAX     OCTET STRING
	MAX-ACCESS read-write
	STATUS     current
	DESCRIPTION 
		""
	::= { outlet8 1 }

outlet8PingIpAddress  OBJECT-TYPE
	SYNTAX     IpAddress
	MAX-ACCESS read-write
	STATUS     current
	DESCRIPTION 
		""
	::= { outlet8 2 }

outlet8Link  OBJECT-TYPE
	SYNTAX     OCTET STRING
	MAX-ACCESS read-write
	STATUS     current
	DESCRIPTION 
		""
	::= { outlet8 3 }

outlet8SequenceTime  OBJECT-TYPE
	SYNTAX     Integer32
	MAX-ACCESS read-write
	STATUS     current
	DESCRIPTION 
		""
	::= { outlet8 4 }

outlet8RebootTime  OBJECT-TYPE
	SYNTAX     Integer32
	MAX-ACCESS read-write
	STATUS     current
	DESCRIPTION 
		""
	::= { outlet8 5 }

outlet9Name  OBJECT-TYPE
	SYNTAX     OCTET STRING
	MAX-ACCESS read-write
	STATUS     current
	DESCRIPTION 
		""
	::= { outlet9 1 }

outlet9PingIpAddress  OBJECT-TYPE
	SYNTAX     IpAddress
	MAX-ACCESS read-write
	STATUS     current
	DESCRIPTION 
		""
	::= { outlet9 2 }

outlet9Link  OBJECT-TYPE
	SYNTAX     OCTET STRING
	MAX-ACCESS read-write
	STATUS     current
	DESCRIPTION 
		""
	::= { outlet9 3 }

outlet9SequenceTime  OBJECT-TYPE
	SYNTAX     Integer32
	MAX-ACCESS read-write
	STATUS     current
	DESCRIPTION 
		""
	::= { outlet9 4 }

outlet9RebootTime  OBJECT-TYPE
	SYNTAX     Integer32
	MAX-ACCESS read-write
	STATUS     current
	DESCRIPTION 
		""
	::= { outlet9 5 }

outlet10Name  OBJECT-TYPE
	SYNTAX     OCTET STRING
	MAX-ACCESS read-write
	STATUS     current
	DESCRIPTION 
		""
	::= { outlet10 1 }

outlet10PingIpAddress  OBJECT-TYPE
	SYNTAX     IpAddress
	MAX-ACCESS read-write
	STATUS     current
	DESCRIPTION 
		""
	::= { outlet10 2 }

outlet10Link  OBJECT-TYPE
	SYNTAX     OCTET STRING
	MAX-ACCESS read-write
	STATUS     current
	DESCRIPTION 
		""
	::= { outlet10 3 }

outlet10SequenceTime  OBJECT-TYPE
	SYNTAX     Integer32
	MAX-ACCESS read-write
	STATUS     current
	DESCRIPTION 
		""
	::= { outlet10 4 }

outlet10RebootTime  OBJECT-TYPE
	SYNTAX     Integer32
	MAX-ACCESS read-write
	STATUS     current
	DESCRIPTION 
		""
	::= { outlet10 5 }

outlet11Name  OBJECT-TYPE
	SYNTAX     OCTET STRING
	MAX-ACCESS read-write
	STATUS     current
	DESCRIPTION 
		""
	::= { outlet11 1 }

outlet11PingIpAddress  OBJECT-TYPE
	SYNTAX     IpAddress
	MAX-ACCESS read-write
	STATUS     current
	DESCRIPTION 
		""
	::= { outlet11 2 }

outlet11Link  OBJECT-TYPE
	SYNTAX     OCTET STRING
	MAX-ACCESS read-write
	STATUS     current
	DESCRIPTION 
		""
	::= { outlet11 3 }

outlet11SequenceTime  OBJECT-TYPE
	SYNTAX     Integer32
	MAX-ACCESS read-write
	STATUS     current
	DESCRIPTION 
		""
	::= { outlet11 4 }

outlet11RebootTime  OBJECT-TYPE
	SYNTAX     Integer32
	MAX-ACCESS read-write
	STATUS     current
	DESCRIPTION 
		""
	::= { outlet11 5 }

outlet12Name  OBJECT-TYPE
	SYNTAX     OCTET STRING
	MAX-ACCESS read-write
	STATUS     current
	DESCRIPTION 
		""
	::= { outlet12 1 }

outlet12PingIpAddress  OBJECT-TYPE
	SYNTAX     IpAddress
	MAX-ACCESS read-write
	STATUS     current
	DESCRIPTION 
		""
	::= { outlet12 2 }

outlet12Link  OBJECT-TYPE
	SYNTAX     OCTET STRING
	MAX-ACCESS read-write
	STATUS     current
	DESCRIPTION 
		""
	::= { outlet12 3 }

outlet12SequenceTime  OBJECT-TYPE
	SYNTAX     Integer32
	MAX-ACCESS read-write
	STATUS     current
	DESCRIPTION 
		""
	::= { outlet12 4 }

outlet12RebootTime  OBJECT-TYPE
	SYNTAX     Integer32
	MAX-ACCESS read-write
	STATUS     current
	DESCRIPTION 
		""
	::= { outlet12 5 }

outlet13Name  OBJECT-TYPE
	SYNTAX     OCTET STRING
	MAX-ACCESS read-write
	STATUS     current
	DESCRIPTION 
		""
	::= { outlet13 1 }

outlet13PingIpAddress  OBJECT-TYPE
	SYNTAX     IpAddress
	MAX-ACCESS read-write
	STATUS     current
	DESCRIPTION 
		""
	::= { outlet13 2 }

outlet13Link  OBJECT-TYPE
	SYNTAX     OCTET STRING
	MAX-ACCESS read-write
	STATUS     current
	DESCRIPTION 
		""
	::= { outlet13 3 }

outlet13SequenceTime  OBJECT-TYPE
	SYNTAX     Integer32
	MAX-ACCESS read-write
	STATUS     current
	DESCRIPTION 
		""
	::= { outlet13 4 }

outlet13RebootTime  OBJECT-TYPE
	SYNTAX     Integer32
	MAX-ACCESS read-write
	STATUS     current
	DESCRIPTION 
		""
	::= { outlet13 5 }

outlet14Name  OBJECT-TYPE
	SYNTAX     OCTET STRING
	MAX-ACCESS read-write
	STATUS     current
	DESCRIPTION 
		""
	::= { outlet14 1 }

outlet14PingIpAddress  OBJECT-TYPE
	SYNTAX     IpAddress
	MAX-ACCESS read-write
	STATUS     current
	DESCRIPTION 
		""
	::= { outlet14 2 }

outlet14Link  OBJECT-TYPE
	SYNTAX     OCTET STRING
	MAX-ACCESS read-write
	STATUS     current
	DESCRIPTION 
		""
	::= { outlet14 3 }

outlet14SequenceTime  OBJECT-TYPE
	SYNTAX     Integer32
	MAX-ACCESS read-write
	STATUS     current
	DESCRIPTION 
		""
	::= { outlet14 4 }

outlet14RebootTime  OBJECT-TYPE
	SYNTAX     Integer32
	MAX-ACCESS read-write
	STATUS     current
	DESCRIPTION 
		""
	::= { outlet14 5 }

outlet15Name  OBJECT-TYPE
	SYNTAX     OCTET STRING
	MAX-ACCESS read-write
	STATUS     current
	DESCRIPTION 
		""
	::= { outlet15 1 }

outlet15PingIpAddress  OBJECT-TYPE
	SYNTAX     IpAddress
	MAX-ACCESS read-write
	STATUS     current
	DESCRIPTION 
		""
	::= { outlet15 2 }

outlet15Link  OBJECT-TYPE
	SYNTAX     OCTET STRING
	MAX-ACCESS read-write
	STATUS     current
	DESCRIPTION 
		""
	::= { outlet15 3 }

outlet15SequenceTime  OBJECT-TYPE
	SYNTAX     Integer32
	MAX-ACCESS read-write
	STATUS     current
	DESCRIPTION 
		""
	::= { outlet15 4 }

outlet15RebootTime  OBJECT-TYPE
	SYNTAX     Integer32
	MAX-ACCESS read-write
	STATUS     current
	DESCRIPTION 
		""
	::= { outlet15 5 }

outlet16Name  OBJECT-TYPE
	SYNTAX     OCTET STRING
	MAX-ACCESS read-write
	STATUS     current
	DESCRIPTION 
		""
	::= { outlet16 1 }

outlet16PingIpAddress  OBJECT-TYPE
	SYNTAX     IpAddress
	MAX-ACCESS read-write
	STATUS     current
	DESCRIPTION 
		""
	::= { outlet16 2 }

outlet16Link  OBJECT-TYPE
	SYNTAX     OCTET STRING
	MAX-ACCESS read-write
	STATUS     current
	DESCRIPTION 
		""
	::= { outlet16 3 }

outlet16SequenceTime  OBJECT-TYPE
	SYNTAX     Integer32
	MAX-ACCESS read-write
	STATUS     current
	DESCRIPTION 
		""
	::= { outlet16 4 }

outlet16RebootTime  OBJECT-TYPE
	SYNTAX     Integer32
	MAX-ACCESS read-write
	STATUS     current
	DESCRIPTION 
		""
	::= { outlet16 5 }

outlet17Name  OBJECT-TYPE
	SYNTAX     OCTET STRING
	MAX-ACCESS read-write
	STATUS     current
	DESCRIPTION 
		""
	::= { outlet17 1 }

outlet17PingIpAddress  OBJECT-TYPE
	SYNTAX     IpAddress
	MAX-ACCESS read-write
	STATUS     current
	DESCRIPTION 
		""
	::= { outlet17 2 }

outlet17Link  OBJECT-TYPE
	SYNTAX     OCTET STRING
	MAX-ACCESS read-write
	STATUS     current
	DESCRIPTION 
		""
	::= { outlet17 3 }

outlet17SequenceTime  OBJECT-TYPE
	SYNTAX     Integer32
	MAX-ACCESS read-write
	STATUS     current
	DESCRIPTION 
		""
	::= { outlet17 4 }

outlet17RebootTime  OBJECT-TYPE
	SYNTAX     Integer32
	MAX-ACCESS read-write
	STATUS     current
	DESCRIPTION 
		""
	::= { outlet17 5 }

outlet18Name  OBJECT-TYPE
	SYNTAX     OCTET STRING
	MAX-ACCESS read-write
	STATUS     current
	DESCRIPTION 
		""
	::= { outlet18 1 }

outlet18PingIpAddress  OBJECT-TYPE
	SYNTAX     IpAddress
	MAX-ACCESS read-write
	STATUS     current
	DESCRIPTION 
		""
	::= { outlet18 2 }

outlet18Link  OBJECT-TYPE
	SYNTAX     OCTET STRING
	MAX-ACCESS read-write
	STATUS     current
	DESCRIPTION 
		""
	::= { outlet18 3 }

outlet18SequenceTime  OBJECT-TYPE
	SYNTAX     Integer32
	MAX-ACCESS read-write
	STATUS     current
	DESCRIPTION 
		""
	::= { outlet18 4 }

outlet18RebootTime  OBJECT-TYPE
	SYNTAX     Integer32
	MAX-ACCESS read-write
	STATUS     current
	DESCRIPTION 
		""
	::= { outlet18 5 }

outlet19Name  OBJECT-TYPE
	SYNTAX     OCTET STRING
	MAX-ACCESS read-write
	STATUS     current
	DESCRIPTION 
		""
	::= { outlet19 1 }

outlet19PingIpAddress  OBJECT-TYPE
	SYNTAX     IpAddress
	MAX-ACCESS read-write
	STATUS     current
	DESCRIPTION 
		""
	::= { outlet19 2 }

outlet19Link  OBJECT-TYPE
	SYNTAX     OCTET STRING
	MAX-ACCESS read-write
	STATUS     current
	DESCRIPTION 
		""
	::= { outlet19 3 }

outlet19SequenceTime  OBJECT-TYPE
	SYNTAX     Integer32
	MAX-ACCESS read-write
	STATUS     current
	DESCRIPTION 
		""
	::= { outlet19 4 }

outlet19RebootTime  OBJECT-TYPE
	SYNTAX     Integer32
	MAX-ACCESS read-write
	STATUS     current
	DESCRIPTION 
		""
	::= { outlet19 5 }

outlet20Name  OBJECT-TYPE
	SYNTAX     OCTET STRING
	MAX-ACCESS read-write
	STATUS     current
	DESCRIPTION 
		""
	::= { outlet20 1 }

outlet20PingIpAddress  OBJECT-TYPE
	SYNTAX     IpAddress
	MAX-ACCESS read-write
	STATUS     current
	DESCRIPTION 
		""
	::= { outlet20 2 }

outlet20Link  OBJECT-TYPE
	SYNTAX     OCTET STRING
	MAX-ACCESS read-write
	STATUS     current
	DESCRIPTION 
		""
	::= { outlet20 3 }

outlet20SequenceTime  OBJECT-TYPE
	SYNTAX     Integer32
	MAX-ACCESS read-write
	STATUS     current
	DESCRIPTION 
		""
	::= { outlet20 4 }

outlet20RebootTime  OBJECT-TYPE
	SYNTAX     Integer32
	MAX-ACCESS read-write
	STATUS     current
	DESCRIPTION 
		""
	::= { outlet20 5 }

outlet21Name  OBJECT-TYPE
	SYNTAX     OCTET STRING
	MAX-ACCESS read-write
	STATUS     current
	DESCRIPTION 
		""
	::= { outlet21 1 }

outlet21PingIpAddress  OBJECT-TYPE
	SYNTAX     IpAddress
	MAX-ACCESS read-write
	STATUS     current
	DESCRIPTION 
		""
	::= { outlet21 2 }

outlet21Link  OBJECT-TYPE
	SYNTAX     OCTET STRING
	MAX-ACCESS read-write
	STATUS     current
	DESCRIPTION 
		""
	::= { outlet21 3 }

outlet21SequenceTime  OBJECT-TYPE
	SYNTAX     Integer32
	MAX-ACCESS read-write
	STATUS     current
	DESCRIPTION 
		""
	::= { outlet21 4 }

outlet21RebootTime  OBJECT-TYPE
	SYNTAX     Integer32
	MAX-ACCESS read-write
	STATUS     current
	DESCRIPTION 
		""
	::= { outlet21 5 }

outlet22Name  OBJECT-TYPE
	SYNTAX     OCTET STRING
	MAX-ACCESS read-write
	STATUS     current
	DESCRIPTION 
		""
	::= { outlet22 1 }

outlet22PingIpAddress  OBJECT-TYPE
	SYNTAX     IpAddress
	MAX-ACCESS read-write
	STATUS     current
	DESCRIPTION 
		""
	::= { outlet22 2 }

outlet22Link  OBJECT-TYPE
	SYNTAX     OCTET STRING
	MAX-ACCESS read-write
	STATUS     current
	DESCRIPTION 
		""
	::= { outlet22 3 }

outlet22SequenceTime  OBJECT-TYPE
	SYNTAX     Integer32
	MAX-ACCESS read-write
	STATUS     current
	DESCRIPTION 
		""
	::= { outlet22 4 }

outlet22RebootTime  OBJECT-TYPE
	SYNTAX     Integer32
	MAX-ACCESS read-write
	STATUS     current
	DESCRIPTION 
		""
	::= { outlet22 5 }

outlet23Name  OBJECT-TYPE
	SYNTAX     OCTET STRING
	MAX-ACCESS read-write
	STATUS     current
	DESCRIPTION 
		""
	::= { outlet23 1 }

outlet23PingIpAddress  OBJECT-TYPE
	SYNTAX     IpAddress
	MAX-ACCESS read-write
	STATUS     current
	DESCRIPTION 
		""
	::= { outlet23 2 }

outlet23Link  OBJECT-TYPE
	SYNTAX     OCTET STRING
	MAX-ACCESS read-write
	STATUS     current
	DESCRIPTION 
		""
	::= { outlet23 3 }

outlet23SequenceTime  OBJECT-TYPE
	SYNTAX     Integer32
	MAX-ACCESS read-write
	STATUS     current
	DESCRIPTION 
		""
	::= { outlet23 4 }

outlet23RebootTime  OBJECT-TYPE
	SYNTAX     Integer32
	MAX-ACCESS read-write
	STATUS     current
	DESCRIPTION 
		""
	::= { outlet23 5 }

outlet24Name  OBJECT-TYPE
	SYNTAX     OCTET STRING
	MAX-ACCESS read-write
	STATUS     current
	DESCRIPTION 
		""
	::= { outlet24 1 }

outlet24PingIpAddress  OBJECT-TYPE
	SYNTAX     IpAddress
	MAX-ACCESS read-write
	STATUS     current
	DESCRIPTION 
		""
	::= { outlet24 2 }

outlet24Link  OBJECT-TYPE
	SYNTAX     OCTET STRING
	MAX-ACCESS read-write
	STATUS     current
	DESCRIPTION 
		""
	::= { outlet24 3 }

outlet24SequenceTime  OBJECT-TYPE
	SYNTAX     Integer32
	MAX-ACCESS read-write
	STATUS     current
	DESCRIPTION 
		""
	::= { outlet24 4 }

outlet24RebootTime  OBJECT-TYPE
	SYNTAX     Integer32
	MAX-ACCESS read-write
	STATUS     current
	DESCRIPTION 
		""
	::= { outlet24 5 }

globalCommand  OBJECT-TYPE
	SYNTAX     INTEGER {
		nochange (0),
		globalOn (1),
		globalOff (2),
		sequenceOn (3),
		sequenceOff (4)
	}
	MAX-ACCESS read-write
	STATUS     current
	DESCRIPTION 
		""
	::= { outletControl 1 }

outlet1Command  OBJECT-TYPE
	SYNTAX     INTEGER {
		immediateOn (1),
		immediateOff (2),
		reboot (3),
		nochange (4)
	}
	MAX-ACCESS read-write
	STATUS     current
	DESCRIPTION 
		""
	::= { outletControl 2 }

outlet2Command  OBJECT-TYPE
	SYNTAX     INTEGER {
		immediateOn (1),
		immediateOff (2),
		reboot (3),
		nochange (4)
	}
	MAX-ACCESS read-write
	STATUS     current
	DESCRIPTION 
		""
	::= { outletControl 3 }

outlet3Command  OBJECT-TYPE
	SYNTAX     INTEGER {
		immediateOn (1),
		immediateOff (2),
		reboot (3),
		nochange (4)
	}
	MAX-ACCESS read-write
	STATUS     current
	DESCRIPTION 
		""
	::= { outletControl 4 }

outlet4Command  OBJECT-TYPE
	SYNTAX     INTEGER {
		immediateOn (1),
		immediateOff (2),
		reboot (3),
		nochange (4)
	}
	MAX-ACCESS read-write
	STATUS     current
	DESCRIPTION 
		""
	::= { outletControl 5 }

outlet5Command  OBJECT-TYPE
	SYNTAX     INTEGER {
		immediateOn (1),
		immediateOff (2),
		reboot (3),
		nochange (4)
	}
	MAX-ACCESS read-write
	STATUS     current
	DESCRIPTION 
		""
	::= { outletControl 6 }

outlet6Command  OBJECT-TYPE
	SYNTAX     INTEGER {
		immediateOn (1),
		immediateOff (2),
		reboot (3),
		nochange (4)
	}
	MAX-ACCESS read-write
	STATUS     current
	DESCRIPTION 
		""
	::= { outletControl 7 }

outlet7Command  OBJECT-TYPE
	SYNTAX     INTEGER {
		immediateOn (1),
		immediateOff (2),
		reboot (3),
		nochange (4)
	}
	MAX-ACCESS read-write
	STATUS     current
	DESCRIPTION 
		""
	::= { outletControl 8 }

outlet8Command  OBJECT-TYPE
	SYNTAX     INTEGER {
		immediateOn (1),
		immediateOff (2),
		reboot (3),
		nochange (4)
	}
	MAX-ACCESS read-write
	STATUS     current
	DESCRIPTION 
		""
	::= { outletControl 9 }

outlet9Command  OBJECT-TYPE
	SYNTAX     INTEGER {
		immediateOn (1),
		immediateOff (2),
		reboot (3),
		nochange (4)
	}
	MAX-ACCESS read-write
	STATUS     current
	DESCRIPTION 
		""
	::= { outletControl 10 }

outlet10Command  OBJECT-TYPE
	SYNTAX     INTEGER {
		immediateOn (1),
		immediateOff (2),
		reboot (3),
		nochange (4)
	}
	MAX-ACCESS read-write
	STATUS     current
	DESCRIPTION 
		""
	::= { outletControl 11 }

outlet11Command  OBJECT-TYPE
	SYNTAX     INTEGER {
		immediateOn (1),
		immediateOff (2),
		reboot (3),
		nochange (4)
	}
	MAX-ACCESS read-write
	STATUS     current
	DESCRIPTION 
		""
	::= { outletControl 12 }

outlet12Command  OBJECT-TYPE
	SYNTAX     INTEGER {
		immediateOn (1),
		immediateOff (2),
		reboot (3),
		noChange (4)
	}
	MAX-ACCESS read-write
	STATUS     current
	DESCRIPTION 
		""
	::= { outletControl 13 }

outlet13Command  OBJECT-TYPE
	SYNTAX     INTEGER {
		immediateOn (1),
		immediateOff (2),
		reboot (3),
		nochange (4)
	}
	MAX-ACCESS read-write
	STATUS     current
	DESCRIPTION 
		""
	::= { outletControl 14 }

outlet14Command  OBJECT-TYPE
	SYNTAX     INTEGER {
		immediateOn (1),
		immediateOff (2),
		reboot (3),
		nochange (4)
	}
	MAX-ACCESS read-write
	STATUS     current
	DESCRIPTION 
		""
	::= { outletControl 15 }

outlet15Command  OBJECT-TYPE
	SYNTAX     INTEGER {
		immediateOn (1),
		immediateOff (2),
		reboot (3),
		nochange (4)
	}
	MAX-ACCESS read-write
	STATUS     current
	DESCRIPTION 
		""
	::= { outletControl 16 }

outlet16Command  OBJECT-TYPE
	SYNTAX     INTEGER {
		immediateOn (1),
		immediateOff (2),
		reboot (3),
		nochange (4)
	}
	MAX-ACCESS read-write
	STATUS     current
	DESCRIPTION 
		""
	::= { outletControl 17 }

outlet17Command  OBJECT-TYPE
	SYNTAX     INTEGER {
		immediateOn (1),
		immediateOff (2),
		reboot (3),
		nochange (4)
	}
	MAX-ACCESS read-write
	STATUS     current
	DESCRIPTION 
		""
	::= { outletControl 18 }

outlet18Command  OBJECT-TYPE
	SYNTAX     INTEGER {
		immediateOn (1),
		immediateOff (2),
		reboot (3),
		nochange (4)
	}
	MAX-ACCESS read-write
	STATUS     current
	DESCRIPTION 
		""
	::= { outletControl 19 }

outlet19Command  OBJECT-TYPE
	SYNTAX     INTEGER {
		immediateOn (1),
		immediateOff (2),
		reboot (3),
		nochange (4)
	}
	MAX-ACCESS read-write
	STATUS     current
	DESCRIPTION 
		""
	::= { outletControl 20 }

outlet20Command  OBJECT-TYPE
	SYNTAX     INTEGER {
		immediateOn (1),
		immediateOff (2),
		reboot (3),
		nochange (4)
	}
	MAX-ACCESS read-write
	STATUS     current
	DESCRIPTION 
		""
	::= { outletControl 21 }

outlet21Command  OBJECT-TYPE
	SYNTAX     INTEGER {
		immediateOn (1),
		immediateOff (2),
		reboot (3),
		nochange (4)
	}
	MAX-ACCESS read-write
	STATUS     current
	DESCRIPTION 
		""
	::= { outletControl 22 }

outlet22Command  OBJECT-TYPE
	SYNTAX     INTEGER {
		immediateOn (1),
		immediateOff (2),
		reboot (3),
		nochange (4)
	}
	MAX-ACCESS read-write
	STATUS     current
	DESCRIPTION 
		""
	::= { outletControl 23 }

outlet23Command  OBJECT-TYPE
	SYNTAX     INTEGER {
		immediateOn (1),
		immediateOff (2),
		reboot (3),
		nochange (4)
	}
	MAX-ACCESS read-write
	STATUS     current
	DESCRIPTION 
		""
	::= { outletControl 24 }

outlet24Command  OBJECT-TYPE
	SYNTAX     INTEGER {
		immediateOn (1),
		immediateOff (2),
		reboot (3),
		nochange (4)
	}
	MAX-ACCESS read-write
	STATUS     current
	DESCRIPTION 
		""
	::= { outletControl 25 }

outlet1Status  OBJECT-TYPE
	SYNTAX     INTEGER {
		on (1),
		off (2)
	}
	MAX-ACCESS read-only
	STATUS     current
	DESCRIPTION 
		""
	::= { outletStatus 1 }

outlet2Status  OBJECT-TYPE
	SYNTAX     INTEGER {
		on (1),
		off (2)
	}
	MAX-ACCESS read-only
	STATUS     current
	DESCRIPTION 
		""
	::= { outletStatus 2 }

outlet3Status  OBJECT-TYPE
	SYNTAX     INTEGER {
		on (1),
		off (2)
	}
	MAX-ACCESS read-only
	STATUS     current
	DESCRIPTION 
		""
	::= { outletStatus 3 }

outlet4Status  OBJECT-TYPE
	SYNTAX     INTEGER {
		on (1),
		off (2)
	}
	MAX-ACCESS read-only
	STATUS     current
	DESCRIPTION 
		""
	::= { outletStatus 4 }

outlet5Status  OBJECT-TYPE
	SYNTAX     INTEGER {
		on (1),
		off (2)
	}
	MAX-ACCESS read-only
	STATUS     current
	DESCRIPTION 
		""
	::= { outletStatus 5 }

outlet6Status  OBJECT-TYPE
	SYNTAX     INTEGER {
		on (1),
		off (2)
	}
	MAX-ACCESS read-only
	STATUS     current
	DESCRIPTION 
		""
	::= { outletStatus 6 }

outlet7Status  OBJECT-TYPE
	SYNTAX     INTEGER {
		on (1),
		off (2)
	}
	MAX-ACCESS read-only
	STATUS     current
	DESCRIPTION 
		""
	::= { outletStatus 7 }

outlet8Status  OBJECT-TYPE
	SYNTAX     INTEGER {
		on (1),
		off (2)
	}
	MAX-ACCESS read-only
	STATUS     current
	DESCRIPTION 
		""
	::= { outletStatus 8 }

outlet9Status  OBJECT-TYPE
	SYNTAX     INTEGER {
		on (1),
		off (2)
	}
	MAX-ACCESS read-only
	STATUS     current
	DESCRIPTION 
		""
	::= { outletStatus 9 }

outlet10Status  OBJECT-TYPE
	SYNTAX     INTEGER {
		on (1),
		off (2)
	}
	MAX-ACCESS read-only
	STATUS     current
	DESCRIPTION 
		""
	::= { outletStatus 10 }

outlet11Status  OBJECT-TYPE
	SYNTAX     INTEGER {
		on (1),
		off (2)
	}
	MAX-ACCESS read-only
	STATUS     current
	DESCRIPTION 
		""
	::= { outletStatus 11 }

outlet12Status  OBJECT-TYPE
	SYNTAX     INTEGER {
		on (1),
		off (2)
	}
	MAX-ACCESS read-only
	STATUS     current
	DESCRIPTION 
		""
	::= { outletStatus 12 }

outlet13Status  OBJECT-TYPE
	SYNTAX     INTEGER {
		on (1),
		off (2)
	}
	MAX-ACCESS read-only
	STATUS     current
	DESCRIPTION 
		""
	::= { outletStatus 13 }

outlet14Status  OBJECT-TYPE
	SYNTAX     INTEGER {
		on (1),
		off (2)
	}
	MAX-ACCESS read-only
	STATUS     current
	DESCRIPTION 
		""
	::= { outletStatus 14 }

outlet15Status  OBJECT-TYPE
	SYNTAX     INTEGER {
		on (1),
		off (2)
	}
	MAX-ACCESS read-only
	STATUS     current
	DESCRIPTION 
		""
	::= { outletStatus 15 }

outlet16Status  OBJECT-TYPE
	SYNTAX     INTEGER {
		on (1),
		off (2)
	}
	MAX-ACCESS read-only
	STATUS     current
	DESCRIPTION 
		""
	::= { outletStatus 16 }

outlet17Status  OBJECT-TYPE
	SYNTAX     INTEGER {
		on (1),
		off (2)
	}
	MAX-ACCESS read-only
	STATUS     current
	DESCRIPTION 
		""
	::= { outletStatus 17 }

outlet18Status  OBJECT-TYPE
	SYNTAX     INTEGER {
		on (1),
		off (2)
	}
	MAX-ACCESS read-only
	STATUS     current
	DESCRIPTION 
		""
	::= { outletStatus 18 }

outlet19Status  OBJECT-TYPE
	SYNTAX     INTEGER {
		on (1),
		off (2)
	}
	MAX-ACCESS read-only
	STATUS     current
	DESCRIPTION 
		""
	::= { outletStatus 19 }

outlet20Status  OBJECT-TYPE
	SYNTAX     INTEGER {
		on (1),
		off (2)
	}
	MAX-ACCESS read-only
	STATUS     current
	DESCRIPTION 
		""
	::= { outletStatus 20 }

outlet21Status  OBJECT-TYPE
	SYNTAX     INTEGER {
		on (1),
		off (2)
	}
	MAX-ACCESS read-only
	STATUS     current
	DESCRIPTION 
		""
	::= { outletStatus 21 }

outlet22Status  OBJECT-TYPE
	SYNTAX     INTEGER {
		on (1),
		off (2)
	}
	MAX-ACCESS read-only
	STATUS     current
	DESCRIPTION 
		""
	::= { outletStatus 22 }

outlet23Status  OBJECT-TYPE
	SYNTAX     INTEGER {
		on (1),
		off (2)
	}
	MAX-ACCESS read-only
	STATUS     current
	DESCRIPTION 
		""
	::= { outletStatus 23 }

outlet24Status  OBJECT-TYPE
	SYNTAX     INTEGER {
		on (1),
		off (2)
	}
	MAX-ACCESS read-only
	STATUS     current
	DESCRIPTION 
		""
	::= { outletStatus 24 }

publicCommunityName  OBJECT-TYPE
	SYNTAX     DisplayString (SIZE(21))
	MAX-ACCESS read-write
	STATUS     current
	DESCRIPTION 
		"Enter the Public Community Name.  Default public"
	::= { snmpSettings 1 }

privateCommunityName  OBJECT-TYPE
	SYNTAX     DisplayString (SIZE(21))
	MAX-ACCESS read-write
	STATUS     current
	DESCRIPTION 
		"Enter the Private Community Name.  Default private"
	::= { snmpSettings 2 }

trapCommunityName  OBJECT-TYPE
	SYNTAX     DisplayString (SIZE(21))
	MAX-ACCESS read-write
	STATUS     current
	DESCRIPTION 
		""
	::= { snmpSettings 3 }

publicCommunityPassword  OBJECT-TYPE
	SYNTAX     DisplayString (SIZE(21))
	MAX-ACCESS read-write
	STATUS     current
	DESCRIPTION 
		""
	::= { snmpSettings 4 }

privateCommunityPassword  OBJECT-TYPE
	SYNTAX     DisplayString (SIZE(21))
	MAX-ACCESS read-write
	STATUS     current
	DESCRIPTION 
		""
	::= { snmpSettings 5 }

trapIpAddress  OBJECT-TYPE
	SYNTAX     IpAddress
	MAX-ACCESS read-write
	STATUS     current
	DESCRIPTION 
		""
	::= { snmpSettings 6 }

snmpEnabled  OBJECT-TYPE
	SYNTAX     INTEGER {
		enabled (0),
		disabled (1)
	}
	MAX-ACCESS read-write
	STATUS     current
	DESCRIPTION 
		""
	::= { snmpSettings 7 }

trapUserLoginLogout  OBJECT-TYPE
	SYNTAX     INTEGER {
		disabled (0),
		enabled (1)
	}
	MAX-ACCESS read-write
	STATUS     current
	DESCRIPTION 
		""
	::= { snmpTraps 1 }

trapFailedLogin  OBJECT-TYPE
	SYNTAX     INTEGER {
		disabled (0),
		enabled (1)
	}
	MAX-ACCESS read-write
	STATUS     current
	DESCRIPTION 
		""
	::= { snmpTraps 2 }

trapOutletActivity  OBJECT-TYPE
	SYNTAX     INTEGER {
		disabled (0),
		enabled (1)
	}
	MAX-ACCESS read-write
	STATUS     current
	DESCRIPTION 
		""
	::= { snmpTraps 3 }

trapSystemOnOff  OBJECT-TYPE
	SYNTAX     INTEGER {
		disabled (0),
		enabled (1)
	}
	MAX-ACCESS read-write
	STATUS     current
	DESCRIPTION 
		""
	::= { snmpTraps 4 }

trapOutletSection1Threshold  OBJECT-TYPE
	SYNTAX     INTEGER {
		disabled (0),
		enabled (1)
	}
	MAX-ACCESS read-write
	STATUS     current
	DESCRIPTION 
		""
	::= { snmpTraps 5 }

trapOutletSection2Threshold  OBJECT-TYPE
	SYNTAX     INTEGER {
		disabled (0),
		enabled (1)
	}
	MAX-ACCESS read-write
	STATUS     current
	DESCRIPTION 
		""
	::= { snmpTraps 6 }

trapOutletSection3Threshold  OBJECT-TYPE
	SYNTAX     INTEGER {
		disabled (0),
		enabled (1)
	}
	MAX-ACCESS read-write
	STATUS     current
	DESCRIPTION 
		""
	::= { snmpTraps 7 }

trapTemperatureSensor1Threshold  OBJECT-TYPE
	SYNTAX     INTEGER {
		disabled (0),
		enabled (1)
	}
	MAX-ACCESS read-write
	STATUS     current
	DESCRIPTION 
		""
	::= { snmpTraps 8 }

trapTemperatureSensor2Threshold  OBJECT-TYPE
	SYNTAX     INTEGER {
		disabled (0),
		enabled (1)
	}
	MAX-ACCESS read-write
	STATUS     current
	DESCRIPTION 
		""
	::= { snmpTraps 9 }

trapHumiditySensorThreshold  OBJECT-TYPE
	SYNTAX     INTEGER {
		disabled (0),
		enabled (1)
	}
	MAX-ACCESS read-write
	STATUS     current
	DESCRIPTION 
		""
	::= { snmpTraps 10 }

trapContactClosure1Threshold  OBJECT-TYPE
	SYNTAX     INTEGER {
		disabled (0),
		enabled (1)
	}
	MAX-ACCESS read-write
	STATUS     current
	DESCRIPTION 
		""
	::= { snmpTraps 11 }

trapContactClosure2Threshold  OBJECT-TYPE
	SYNTAX     INTEGER {
		disabled (0),
		enabled (1)
	}
	MAX-ACCESS read-write
	STATUS     current
	DESCRIPTION 
		""
	::= { snmpTraps 12 }

trapContactClosure3Threshold  OBJECT-TYPE
	SYNTAX     INTEGER {
		disabled (0),
		enabled (1)
	}
	MAX-ACCESS read-write
	STATUS     current
	DESCRIPTION 
		""
	::= { snmpTraps 13 }

tempSensor1Name  OBJECT-TYPE
	SYNTAX     DisplayString (SIZE(21))
	MAX-ACCESS read-write
	STATUS     current
	DESCRIPTION 
		""
	::= { tempSensor1 1 }

tempSensor1Enable  OBJECT-TYPE
	SYNTAX     INTEGER {
		disabled (0),
		enabled (1)
	}
	MAX-ACCESS read-write
	STATUS     current
	DESCRIPTION 
		""
	::= { tempSensor1 2 }

tempSensor1HighThresh  OBJECT-TYPE
	SYNTAX     Integer32 (-100..300)
	MAX-ACCESS read-write
	STATUS     current
	DESCRIPTION 
		""
	::= { tempSensor1 3 }

tempSensor1LowThresh  OBJECT-TYPE
	SYNTAX     Integer32 (-100..300)
	MAX-ACCESS read-write
	STATUS     current
	DESCRIPTION 
		""
	::= { tempSensor1 4 }

tempSensor1ControlOutlet  OBJECT-TYPE
	SYNTAX     INTEGER {
		disabled (0),
		enabled (1)
	}
	MAX-ACCESS read-write
	STATUS     current
	DESCRIPTION 
		""
	::= { tempSensor1 5 }

tempSensor1OutletName  OBJECT-TYPE
	SYNTAX     DisplayString (SIZE(21))
	MAX-ACCESS read-write
	STATUS     current
	DESCRIPTION 
		""
	::= { tempSensor1 6 }

tempSensor1OutletState  OBJECT-TYPE
	SYNTAX     INTEGER {
		turnOutletOn (0),
		turnOutletOff (1)
	}
	MAX-ACCESS read-write
	STATUS     current
	DESCRIPTION 
		""
	::= { tempSensor1 7 }

tempSensor2Name  OBJECT-TYPE
	SYNTAX     DisplayString (SIZE(21))
	MAX-ACCESS read-write
	STATUS     current
	DESCRIPTION 
		""
	::= { tempSensor2 1 }

tempSensor2Enable  OBJECT-TYPE
	SYNTAX     INTEGER {
		disabled (0),
		enabled (1)
	}
	MAX-ACCESS read-write
	STATUS     current
	DESCRIPTION 
		""
	::= { tempSensor2 2 }

tempSensor2HighThresh  OBJECT-TYPE
	SYNTAX     Integer32 (-100..300)
	MAX-ACCESS read-write
	STATUS     current
	DESCRIPTION 
		""
	::= { tempSensor2 3 }

tempSensor2LowThresh  OBJECT-TYPE
	SYNTAX     Integer32 (-100..300)
	MAX-ACCESS read-write
	STATUS     current
	DESCRIPTION 
		""
	::= { tempSensor2 4 }

tempSensor2ControlOutlet  OBJECT-TYPE
	SYNTAX     INTEGER {
		disabled (0),
		enabled (1)
	}
	MAX-ACCESS read-write
	STATUS     current
	DESCRIPTION 
		""
	::= { tempSensor2 5 }

tempSensor2OutletName  OBJECT-TYPE
	SYNTAX     DisplayString (SIZE(21))
	MAX-ACCESS read-write
	STATUS     current
	DESCRIPTION 
		""
	::= { tempSensor2 6 }

tempSensor2OutletState  OBJECT-TYPE
	SYNTAX     INTEGER {
		turnOutletOn (0),
		turnOutletOff (1)
	}
	MAX-ACCESS read-write
	STATUS     current
	DESCRIPTION 
		""
	::= { tempSensor2 7 }

humSensor1Name  OBJECT-TYPE
	SYNTAX     DisplayString (SIZE(21))
	MAX-ACCESS read-write
	STATUS     current
	DESCRIPTION 
		""
	::= { humSensor1 1 }

humSensor1Enable  OBJECT-TYPE
	SYNTAX     INTEGER {
		disabled (0),
		enabled (1)
	}
	MAX-ACCESS read-write
	STATUS     current
	DESCRIPTION 
		""
	::= { humSensor1 2 }

humSensor1HighThresh  OBJECT-TYPE
	SYNTAX     Integer32 (0..100)
	MAX-ACCESS read-write
	STATUS     current
	DESCRIPTION 
		""
	::= { humSensor1 3 }

humSensor1LowThresh  OBJECT-TYPE
	SYNTAX     Integer32 (0..100)
	MAX-ACCESS read-write
	STATUS     current
	DESCRIPTION 
		""
	::= { humSensor1 4 }

humSensor1ControlOutlet  OBJECT-TYPE
	SYNTAX     INTEGER {
		disabled (0),
		enabled (1)
	}
	MAX-ACCESS read-write
	STATUS     current
	DESCRIPTION 
		""
	::= { humSensor1 5 }

humSensor1OutletName  OBJECT-TYPE
	SYNTAX     DisplayString (SIZE(21))
	MAX-ACCESS read-write
	STATUS     current
	DESCRIPTION 
		""
	::= { humSensor1 6 }

humSensor1OutletState  OBJECT-TYPE
	SYNTAX     INTEGER {
		turnOutletOn (0),
		turnOutletOff (1)
	}
	MAX-ACCESS read-write
	STATUS     current
	DESCRIPTION 
		""
	::= { humSensor1 7 }

contactClosure1Name  OBJECT-TYPE
	SYNTAX     DisplayString (SIZE(21))
	MAX-ACCESS read-write
	STATUS     current
	DESCRIPTION 
		""
	::= { contactClosure1 1 }

contactClosure1Enable  OBJECT-TYPE
	SYNTAX     INTEGER {
		disabled (0),
		enabled (1)
	}
	MAX-ACCESS read-write
	STATUS     current
	DESCRIPTION 
		""
	::= { contactClosure1 2 }

contactClosure1ControlOutlet  OBJECT-TYPE
	SYNTAX     INTEGER {
		disabled (0),
		enabled (1)
	}
	MAX-ACCESS read-write
	STATUS     current
	DESCRIPTION 
		""
	::= { contactClosure1 3 }

contactClosure1OutletName  OBJECT-TYPE
	SYNTAX     DisplayString (SIZE(21))
	MAX-ACCESS read-write
	STATUS     current
	DESCRIPTION 
		""
	::= { contactClosure1 4 }

contactClosure1OutletState  OBJECT-TYPE
	SYNTAX     INTEGER {
		turnOutletOn (0),
		turnOutletOff (1)
	}
	MAX-ACCESS read-write
	STATUS     current
	DESCRIPTION 
		""
	::= { contactClosure1 5 }

contactClosure2Name  OBJECT-TYPE
	SYNTAX     DisplayString (SIZE(21))
	MAX-ACCESS read-write
	STATUS     current
	DESCRIPTION 
		""
	::= { contactClosure2 1 }

contactClosure2Enable  OBJECT-TYPE
	SYNTAX     INTEGER {
		disabled (0),
		enabled (1)
	}
	MAX-ACCESS read-write
	STATUS     current
	DESCRIPTION 
		""
	::= { contactClosure2 2 }

contactClosure2ControlOutlet  OBJECT-TYPE
	SYNTAX     INTEGER {
		disabled (0),
		enabled (1)
	}
	MAX-ACCESS read-write
	STATUS     current
	DESCRIPTION 
		""
	::= { contactClosure2 3 }

contactClosure2OutletName  OBJECT-TYPE
	SYNTAX     DisplayString (SIZE(21))
	MAX-ACCESS read-write
	STATUS     current
	DESCRIPTION 
		""
	::= { contactClosure2 4 }

contactClosure2OutletState  OBJECT-TYPE
	SYNTAX     INTEGER {
		turnOutletOn (0),
		turnOutletOff (1)
	}
	MAX-ACCESS read-write
	STATUS     current
	DESCRIPTION 
		""
	::= { contactClosure2 5 }

contactClosure3Name  OBJECT-TYPE
	SYNTAX     DisplayString (SIZE(21))
	MAX-ACCESS read-write
	STATUS     current
	DESCRIPTION 
		""
	::= { contactClosure3 1 }

contactClosure3Enable  OBJECT-TYPE
	SYNTAX     INTEGER {
		disabled (0),
		enabled (1)
	}
	MAX-ACCESS read-write
	STATUS     current
	DESCRIPTION 
		""
	::= { contactClosure3 2 }

contactClosure3ControlOutlet  OBJECT-TYPE
	SYNTAX     INTEGER {
		disabled (0),
		enabled (1)
	}
	MAX-ACCESS read-write
	STATUS     current
	DESCRIPTION 
		""
	::= { contactClosure3 3 }

contactClosure3OutletName  OBJECT-TYPE
	SYNTAX     DisplayString (SIZE(21))
	MAX-ACCESS read-write
	STATUS     current
	DESCRIPTION 
		""
	::= { contactClosure3 4 }

contactClosure3OutletState  OBJECT-TYPE
	SYNTAX     INTEGER {
		turnOutletOn (0),
		turnOutletOff (1)
	}
	MAX-ACCESS read-write
	STATUS     current
	DESCRIPTION 
		""
	::= { contactClosure3 5 }

outletSection1VoltageHighThreshold  OBJECT-TYPE
	SYNTAX     Integer32
	MAX-ACCESS read-write
	STATUS     current
	DESCRIPTION 
		""
	::= { outletSection1Config 1 }

outletSection1VoltageLowThreshold  OBJECT-TYPE
	SYNTAX     Integer32
	MAX-ACCESS read-write
	STATUS     current
	DESCRIPTION 
		""
	::= { outletSection1Config 2 }

outletSection1CurrentHighThreshold  OBJECT-TYPE
	SYNTAX     Integer32 (0..20)
	MAX-ACCESS read-write
	STATUS     current
	DESCRIPTION 
		""
	::= { outletSection1Config 3 }

outletSection1CurrentLowThreshold  OBJECT-TYPE
	SYNTAX     Integer32 (0..20)
	MAX-ACCESS read-write
	STATUS     current
	DESCRIPTION 
		""
	::= { outletSection1Config 4 }

outletSection1ControlOutlet  OBJECT-TYPE
	SYNTAX     INTEGER {
		disabled (0),
		enabled (1)
	}
	MAX-ACCESS read-write
	STATUS     current
	DESCRIPTION 
		""
	::= { outletSection1Config 5 }

outletSection1OutletName  OBJECT-TYPE
	SYNTAX     DisplayString (SIZE(21))
	MAX-ACCESS read-write
	STATUS     current
	DESCRIPTION 
		""
	::= { outletSection1Config 6 }

outletSection2VoltageHighThreshold  OBJECT-TYPE
	SYNTAX     Integer32
	MAX-ACCESS read-write
	STATUS     current
	DESCRIPTION 
		""
	::= { outletSection2Config 1 }

outletSection2VoltageLowThreshold  OBJECT-TYPE
	SYNTAX     Integer32
	MAX-ACCESS read-write
	STATUS     current
	DESCRIPTION 
		""
	::= { outletSection2Config 2 }

outletSection2CurrentHighThreshold  OBJECT-TYPE
	SYNTAX     Integer32 (0..20)
	MAX-ACCESS read-write
	STATUS     current
	DESCRIPTION 
		""
	::= { outletSection2Config 3 }

outletSection2CurrentLowThreshold  OBJECT-TYPE
	SYNTAX     Integer32 (0..20)
	MAX-ACCESS read-write
	STATUS     current
	DESCRIPTION 
		""
	::= { outletSection2Config 4 }

outletSection2ControlOutlet  OBJECT-TYPE
	SYNTAX     INTEGER {
		disabled (0),
		enabled (1)
	}
	MAX-ACCESS read-write
	STATUS     current
	DESCRIPTION 
		""
	::= { outletSection2Config 5 }

outletSection2OutletName  OBJECT-TYPE
	SYNTAX     DisplayString (SIZE(21))
	MAX-ACCESS read-write
	STATUS     current
	DESCRIPTION 
		""
	::= { outletSection2Config 6 }

outletSection3VoltageHighThreshold  OBJECT-TYPE
	SYNTAX     Integer32
	MAX-ACCESS read-write
	STATUS     current
	DESCRIPTION 
		""
	::= { outletSection3Config 1 }

outletSection3VoltageLowThreshold  OBJECT-TYPE
	SYNTAX     Integer32
	MAX-ACCESS read-write
	STATUS     current
	DESCRIPTION 
		""
	::= { outletSection3Config 2 }

outletSection3CurrentHighThreshold  OBJECT-TYPE
	SYNTAX     Integer32 (0..20)
	MAX-ACCESS read-write
	STATUS     current
	DESCRIPTION 
		""
	::= { outletSection3Config 3 }

outletSection3CurrentLowThreshold  OBJECT-TYPE
	SYNTAX     Integer32 (0..20)
	MAX-ACCESS read-write
	STATUS     current
	DESCRIPTION 
		""
	::= { outletSection3Config 4 }

outletSection3ControlOutlet  OBJECT-TYPE
	SYNTAX     INTEGER {
		disabled (0),
		enabled (1)
	}
	MAX-ACCESS read-write
	STATUS     current
	DESCRIPTION 
		""
	::= { outletSection3Config 5 }

outletSection3OutletName  OBJECT-TYPE
	SYNTAX     DisplayString (SIZE(21))
	MAX-ACCESS read-write
	STATUS     current
	DESCRIPTION 
		""
	::= { outletSection3Config 6 }

tempSensor1Temp  OBJECT-TYPE
	SYNTAX     Integer32 (-100..300)
	MAX-ACCESS read-only
	STATUS     current
	DESCRIPTION 
		""
	::= { currentSensorValues 1 }

tempSensor2Temp  OBJECT-TYPE
	SYNTAX     Integer32 (-100..300)
	MAX-ACCESS read-only
	STATUS     current
	DESCRIPTION 
		""
	::= { currentSensorValues 2 }

humSensor1Humidity  OBJECT-TYPE
	SYNTAX     Integer32 (0..100)
	MAX-ACCESS read-only
	STATUS     current
	DESCRIPTION 
		""
	::= { currentSensorValues 3 }

contactClosure1State  OBJECT-TYPE
	SYNTAX     INTEGER {
		contactOpen (0),
		contactClosed (1)
	}
	MAX-ACCESS read-only
	STATUS     current
	DESCRIPTION 
		""
	::= { currentSensorValues 4 }

contactClosure2State  OBJECT-TYPE
	SYNTAX     INTEGER {
		contactOpen (0),
		contactClosed (1)
	}
	MAX-ACCESS read-only
	STATUS     current
	DESCRIPTION 
		""
	::= { currentSensorValues 5 }

contactClosure3State  OBJECT-TYPE
	SYNTAX     INTEGER {
		contactOpen (0),
		contactClosed (1)
	}
	MAX-ACCESS read-only
	STATUS     current
	DESCRIPTION 
		""
	::= { currentSensorValues 6 }

outletSection1Voltage  OBJECT-TYPE
	SYNTAX     Integer32
	MAX-ACCESS read-only
	STATUS     current
	DESCRIPTION 
		""
	::= { outletSection1 1 }

outletSection1Current  OBJECT-TYPE
	SYNTAX     Integer32
	MAX-ACCESS read-only
	STATUS     current
	DESCRIPTION 
		""
	::= { outletSection1 2 }

outletSection1Va  OBJECT-TYPE
	SYNTAX     Integer32
	MAX-ACCESS read-only
	STATUS     current
	DESCRIPTION 
		""
	::= { outletSection1 3 }

outletSection2Voltage  OBJECT-TYPE
	SYNTAX     Integer32
	MAX-ACCESS read-only
	STATUS     current
	DESCRIPTION 
		""
	::= { outletSection2 1 }

outletSection2Current  OBJECT-TYPE
	SYNTAX     Integer32
	MAX-ACCESS read-only
	STATUS     current
	DESCRIPTION 
		""
	::= { outletSection2 2 }

outletSection2Va  OBJECT-TYPE
	SYNTAX     Integer32
	MAX-ACCESS read-only
	STATUS     current
	DESCRIPTION 
		""
	::= { outletSection2 3 }

outletSection3Voltage  OBJECT-TYPE
	SYNTAX     Integer32
	MAX-ACCESS read-only
	STATUS     current
	DESCRIPTION 
		""
	::= { outletSection3 1 }

outletSection3Current  OBJECT-TYPE
	SYNTAX     Integer32
	MAX-ACCESS read-only
	STATUS     current
	DESCRIPTION 
		""
	::= { outletSection3 2 }

outletSection3Va  OBJECT-TYPE
	SYNTAX     Integer32
	MAX-ACCESS read-only
	STATUS     current
	DESCRIPTION 
		""
	::= { outletSection3 3 }

totalVoltage  OBJECT-TYPE
	SYNTAX     Integer32
	MAX-ACCESS read-only
	STATUS     current
	DESCRIPTION 
		""
	::= { total 1 }

totalCurrent  OBJECT-TYPE
	SYNTAX     Integer32
	MAX-ACCESS read-only
	STATUS     current
	DESCRIPTION 
		""
	::= { total 2 }

totalVa  OBJECT-TYPE
	SYNTAX     Integer32
	MAX-ACCESS read-only
	STATUS     current
	DESCRIPTION 
		""
	::= { total 3 }
END


-- This MIB was created using NuDesign Team's Visual MIBuilder (Ver 4.6).
