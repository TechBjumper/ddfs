-- ***********************************************************************************************************************
-- *                                                                                                                     *
-- *                                                                                Document Number: TBD                 *
-- *                                                                                Document Version: 01.00              *
-- *            SCHNEIDER ELECTRIC:                                                                                      *
-- *                                                                                                                     *
-- *                                                                                                                     *
-- *            DESCRIPTION:  This is the Schneider SNMP MIB for PM5xxx SNMP supported Products                          *
-- *                                                                                                                     *
-- *            FILE:         SchneiderPM55xx_V1_13                                   *
-- *                                                                                                                     *
-- *            MAIN REVISIONS:                                                                                          *
-- * *********************************************************************************************************************
-- *          REVISION                        *  DATE                    *  DESCRIPTION                                  *
-- * *********************************************************************************************************************
-- *          V01.13                          *  Monday, September 08, 2014           *  Creation                                     *
-- * *********************************************************************************************************************
SCHNEIDER-PM5XXX-MIB DEFINITIONS ::= BEGIN
    IMPORTS
    enterprises, private
    FROM RFC1155-SMI
    OBJECT-TYPE, NOTIFICATION-TYPE
    FROM SNMPv2-SMI
    DisplayString
    FROM SNMPv2-TC;
 
        schneiderElectric OBJECT IDENTIFIER ::= { enterprises 3833 }
 
        transparentFactoryEthernet OBJECT IDENTIFIER ::= { schneiderElectric 1 }
 
        products OBJECT IDENTIFIER ::= { transparentFactoryEthernet 100 }
 
        singleProducts OBJECT IDENTIFIER ::= { products 1 }
 
        pm5000 OBJECT IDENTIFIER ::= { singleProducts 3 }
 
        pm556x OBJECT IDENTIFIER ::= { pm5000 1 }
 
        meterSystem OBJECT IDENTIFIER ::= { pm556x 1 }
 
            midSerialNumber OBJECT-TYPE
                SYNTAX DisplayString (SIZE (0..255))
                MAX-ACCESS read-only
                STATUS mandatory
                DESCRIPTION 
                    "PM556x - Unit Serial Number"
                ::= { meterSystem 1 }
 
            midOsFirmwareVersion OBJECT-TYPE
                SYNTAX DisplayString (SIZE (0..255))
                MAX-ACCESS read-only
                STATUS mandatory
                DESCRIPTION 
                    "PM556x - OS Firmware Revision"
                ::= { meterSystem 2 }
 
            midRsFirmwareVersion OBJECT-TYPE
                SYNTAX DisplayString (SIZE (0..255))
                MAX-ACCESS read-only
                STATUS mandatory
                DESCRIPTION 
                    "PM556x - RS Firmware Revision"
                ::= { meterSystem 3 }
 
            midLanguageVersion OBJECT-TYPE
                SYNTAX DisplayString (SIZE (0..255))
                MAX-ACCESS read-only
                STATUS mandatory
                DESCRIPTION 
                    "PM556x - Language File Revision"
                ::= { meterSystem 4 }
 
            midCommsFirmwareVersion OBJECT-TYPE
                SYNTAX DisplayString (SIZE (0..255))
                MAX-ACCESS read-only
                STATUS mandatory
                DESCRIPTION 
                    "PM556x - Communications Firmware Revision"
                ::= { meterSystem 5 }
 
            midModelNumber OBJECT-TYPE
                SYNTAX DisplayString (SIZE (0..255))
                MAX-ACCESS read-only
                STATUS mandatory
                DESCRIPTION 
                    "PM556x - Model Number"
                ::= { meterSystem 6 }
 
            midMeterName OBJECT-TYPE
                SYNTAX DisplayString (SIZE (0..255))
                MAX-ACCESS read-only
                STATUS mandatory
                DESCRIPTION 
                    "PM556x - Meter Name"
                ::= { meterSystem 7 }
 
            midHardwareRevision OBJECT-TYPE
                SYNTAX DisplayString (SIZE (0..255))
                MAX-ACCESS read-only
                STATUS mandatory
                DESCRIPTION 
                    "PM556x - Hardware Series Revision"
                ::= { meterSystem 8 }
 
            midModelIDNumber OBJECT-TYPE
                SYNTAX DisplayString (SIZE (0..255))
                MAX-ACCESS read-only
                STATUS mandatory
                DESCRIPTION 
                    "PM556x - Model ID Code"
                ::= { meterSystem 9 }
 
            midManufacturer OBJECT-TYPE
                SYNTAX DisplayString (SIZE (0..255))
                MAX-ACCESS read-only
                STATUS mandatory
                DESCRIPTION 
                    "PM556x - Manufuacturer Name"
                ::= { meterSystem 10 }
 
            midManufactureDate OBJECT-TYPE
                SYNTAX DisplayString (SIZE (0..255))
                MAX-ACCESS read-only
                STATUS mandatory
                DESCRIPTION 
                    "PM556x - Date of Manufacture"
                ::= { meterSystem 11 }
 
 
        realTimeClock OBJECT IDENTIFIER ::= { pm556x 2 }
 
            rtcYear OBJECT-TYPE
                SYNTAX DisplayString (SIZE (0..255))
                MAX-ACCESS read-only
                STATUS mandatory
                DESCRIPTION 
                    "PM556x - Real Time Clock (Year)"
                ::= { realTimeClock 1 }
 
            rtcMonth OBJECT-TYPE
                SYNTAX DisplayString (SIZE (0..255))
                MAX-ACCESS read-only
                STATUS mandatory
                DESCRIPTION 
                    "PM556x - Real Time Clock (Month)"
                ::= { realTimeClock 2 }
 
            rtcDay OBJECT-TYPE
                SYNTAX DisplayString (SIZE (0..255))
                MAX-ACCESS read-only
                STATUS mandatory
                DESCRIPTION 
                    "PM556x - Real Time Clock (Day)"
                ::= { realTimeClock 3 }
 
            rtcHour OBJECT-TYPE
                SYNTAX DisplayString (SIZE (0..255))
                MAX-ACCESS read-only
                STATUS mandatory
                DESCRIPTION 
                    "PM556x - Real Time Clock (Hour)"
                ::= { realTimeClock 4 }
 
            rtcMinutes OBJECT-TYPE
                SYNTAX DisplayString (SIZE (0..255))
                MAX-ACCESS read-only
                STATUS mandatory
                DESCRIPTION 
                    "PM556x - Real Time Clock (Minutes)"
                ::= { realTimeClock 5 }
 
            rtcSeconds OBJECT-TYPE
                SYNTAX DisplayString (SIZE (0..255))
                MAX-ACCESS read-only
                STATUS mandatory
                DESCRIPTION 
                    "PM556x - Real Time Clock (Seconds)"
                ::= { realTimeClock 6 }
 
 
        metering OBJECT IDENTIFIER ::= { pm556x 3 }
 
        wiringType OBJECT IDENTIFIER ::= { metering 1 }
 
            swtWiringType OBJECT-TYPE
                SYNTAX DisplayString (SIZE (0..255))
                MAX-ACCESS read-only
                STATUS mandatory
                DESCRIPTION 
                    "Power System Configuration Options:
1ph, 2w, LN
1ph, 2w, LL
1ph, 3w, LL with N
3ph, 3w, Delta, Ungrounded
3ph, 3w, Delta, Corner Grounded
3ph, 3w, Wye, Ungrounded
3ph, 3w, Wye Grounded
3ph, 3w, Wye, Resistance Grounded
3ph, 4w, Open Delta, Center-Tapped
3ph, 4w, Delta, Center-Tapped
3ph, 4w, Wye, Ungrounded
3ph, 4w, Wye Grounded
3ph, 4w, Wye, Resistance Grounded "
                ::= { wiringType 1 }
 
 
        frequency OBJECT IDENTIFIER ::= { metering 2 }
 
            fFrequency OBJECT-TYPE
                SYNTAX DisplayString (SIZE (0..255))
                MAX-ACCESS read-only
                STATUS mandatory
                DESCRIPTION 
                    "Measured System Frequency (Hz)"
                ::= { frequency 1 }
 
 
        loadCurrent OBJECT IDENTIFIER ::= { metering 3 }
 
            lcIa OBJECT-TYPE
                SYNTAX DisplayString (SIZE (0..255))
                MAX-ACCESS read-only
                STATUS mandatory
                DESCRIPTION 
                    "Measured Load Current - Phase A - (Amps)"
                ::= { loadCurrent 1 }
 
            lcIb OBJECT-TYPE
                SYNTAX DisplayString (SIZE (0..255))
                MAX-ACCESS read-only
                STATUS mandatory
                DESCRIPTION 
                    "Measured Load Current - Phase B - (Amps)"
                ::= { loadCurrent 2 }
 
            lcIC OBJECT-TYPE
                SYNTAX DisplayString (SIZE (0..255))
                MAX-ACCESS read-only
                STATUS mandatory
                DESCRIPTION 
                    "Measured Load Current - Phase C - (Amps)"
                ::= { loadCurrent 3 }
 
            lcIn OBJECT-TYPE
                SYNTAX DisplayString (SIZE (0..255))
                MAX-ACCESS read-only
                STATUS mandatory
                DESCRIPTION 
                    "Measured Neutral Current - (Amps)"
                ::= { loadCurrent 4 }
 
            lcIg OBJECT-TYPE
                SYNTAX DisplayString (SIZE (0..255))
                MAX-ACCESS read-only
                STATUS mandatory
                DESCRIPTION 
                    "Calculated Ground Current - (Amps)"
                ::= { loadCurrent 5 }
 
            lcIavg OBJECT-TYPE
                SYNTAX DisplayString (SIZE (0..255))
                MAX-ACCESS read-only
                STATUS mandatory
                DESCRIPTION 
                    "Total Average Load Current - Phase (A,B,C) - (Amps)"
                ::= { loadCurrent 6 }
 
 
        currentUnbalance OBJECT IDENTIFIER ::= { metering 4 }
 
            cuIA OBJECT-TYPE
                SYNTAX DisplayString (SIZE (0..255))
                MAX-ACCESS read-only
                STATUS mandatory
                DESCRIPTION 
                    "Percent Current Unbalance - Phase A"
                ::= { currentUnbalance 1 }
 
            cuIB OBJECT-TYPE
                SYNTAX DisplayString (SIZE (0..255))
                MAX-ACCESS read-only
                STATUS mandatory
                DESCRIPTION 
                    "Percent Current Unbalance - Phase B"
                ::= { currentUnbalance 2 }
 
            cuIC OBJECT-TYPE
                SYNTAX DisplayString (SIZE (0..255))
                MAX-ACCESS read-only
                STATUS mandatory
                DESCRIPTION 
                    "Percent Current Unbalance - Phase C"
                ::= { currentUnbalance 3 }
 
            cuIWorst OBJECT-TYPE
                SYNTAX DisplayString (SIZE (0..255))
                MAX-ACCESS read-only
                STATUS mandatory
                DESCRIPTION 
                    "Percent Current Unbalance - Worst Detected "
                ::= { currentUnbalance 4 }
 
 
        voltage OBJECT IDENTIFIER ::= { metering 5 }
 
            vVan OBJECT-TYPE
                SYNTAX DisplayString (SIZE (0..255))
                MAX-ACCESS read-only
                STATUS mandatory
                DESCRIPTION 
                    "Measured Line Voltage - Van - (Volts)"
                ::= { voltage 1 }
 
            vVbn OBJECT-TYPE
                SYNTAX DisplayString (SIZE (0..255))
                MAX-ACCESS read-only
                STATUS mandatory
                DESCRIPTION 
                    "Measured Line Voltage - Vbn - (Volts)"
                ::= { voltage 2 }
 
            vVcn OBJECT-TYPE
                SYNTAX DisplayString (SIZE (0..255))
                MAX-ACCESS read-only
                STATUS mandatory
                DESCRIPTION 
                    "Measured Line Voltage - Vcn - (Volts)"
                ::= { voltage 3 }
 
            vVlnAverage OBJECT-TYPE
                SYNTAX DisplayString (SIZE (0..255))
                MAX-ACCESS read-only
                STATUS mandatory
                DESCRIPTION 
                    "Average Measured Line Voltage - (Van,Vbn,Vcn) - (Volts)"
                ::= { voltage 4 }
 
            vVab OBJECT-TYPE
                SYNTAX DisplayString (SIZE (0..255))
                MAX-ACCESS read-only
                STATUS mandatory
                DESCRIPTION 
                    "Measured Line Voltage - Vab - (Volts)"
                ::= { voltage 5 }
 
            vVbc OBJECT-TYPE
                SYNTAX DisplayString (SIZE (0..255))
                MAX-ACCESS read-only
                STATUS mandatory
                DESCRIPTION 
                    "Measured Line Voltage - Vbc - (Volts)"
                ::= { voltage 6 }
 
            vVca OBJECT-TYPE
                SYNTAX DisplayString (SIZE (0..255))
                MAX-ACCESS read-only
                STATUS mandatory
                DESCRIPTION 
                    "Measured Line Voltage - Vca - (Volts)"
                ::= { voltage 7 }
 
            vVng OBJECT-TYPE
                SYNTAX DisplayString (SIZE (0..255))
                MAX-ACCESS read-only
                STATUS mandatory
                DESCRIPTION 
                    "Measured Line Voltage - Vng - (Volts)"
                ::= { voltage 8 }
 
            vVllAverage OBJECT-TYPE
                SYNTAX DisplayString (SIZE (0..255))
                MAX-ACCESS read-only
                STATUS mandatory
                DESCRIPTION 
                    "Average Measured Line Voltage - (Vab,Vbc,Vca) - (Volts)"
                ::= { voltage 9 }
 
 
        voltageUnbalance OBJECT IDENTIFIER ::= { metering 6 }
 
            vuVab OBJECT-TYPE
                SYNTAX DisplayString (SIZE (0..255))
                MAX-ACCESS read-only
                STATUS mandatory
                DESCRIPTION 
                    "Percent Voltage Unbalance - Vab"
                ::= { voltageUnbalance 1 }
 
            vuVbc OBJECT-TYPE
                SYNTAX DisplayString (SIZE (0..255))
                MAX-ACCESS read-only
                STATUS mandatory
                DESCRIPTION 
                    "Percent Voltage Unbalance - Vbc"
                ::= { voltageUnbalance 2 }
 
            vuVca OBJECT-TYPE
                SYNTAX DisplayString (SIZE (0..255))
                MAX-ACCESS read-only
                STATUS mandatory
                DESCRIPTION 
                    "Percent Voltage Unbalance - Vca"
                ::= { voltageUnbalance 3 }
 
            vuVllWorst OBJECT-TYPE
                SYNTAX DisplayString (SIZE (0..255))
                MAX-ACCESS read-only
                STATUS mandatory
                DESCRIPTION 
                    "Percent Voltage Unbalance - Worst Detected (VL-L)"
                ::= { voltageUnbalance 4 }
 
            vuVan OBJECT-TYPE
                SYNTAX DisplayString (SIZE (0..255))
                MAX-ACCESS read-only
                STATUS mandatory
                DESCRIPTION 
                    "Percent Voltage Unbalance - Van"
                ::= { voltageUnbalance 5 }
 
            vuVbn OBJECT-TYPE
                SYNTAX DisplayString (SIZE (0..255))
                MAX-ACCESS read-only
                STATUS mandatory
                DESCRIPTION 
                    "Percent Voltage Unbalance - Vbn"
                ::= { voltageUnbalance 6 }
 
            vuVcn OBJECT-TYPE
                SYNTAX DisplayString (SIZE (0..255))
                MAX-ACCESS read-only
                STATUS mandatory
                DESCRIPTION 
                    "Percent Voltage Unbalance - Vcn"
                ::= { voltageUnbalance 7 }
 
            vuVlnWorst OBJECT-TYPE
                SYNTAX DisplayString (SIZE (0..255))
                MAX-ACCESS read-only
                STATUS mandatory
                DESCRIPTION 
                    "Percent Voltage Unbalance - Worst Detected (VL-N)"
                ::= { voltageUnbalance 8 }
 
 
        power OBJECT IDENTIFIER ::= { metering 7 }
 
            pActivePa OBJECT-TYPE
                SYNTAX DisplayString (SIZE (0..255))
                MAX-ACCESS read-only
                STATUS mandatory
                DESCRIPTION 
                    "Active Power - Phase A - (kW)"
                ::= { power 1 }
 
            pActivePb OBJECT-TYPE
                SYNTAX DisplayString (SIZE (0..255))
                MAX-ACCESS read-only
                STATUS mandatory
                DESCRIPTION 
                    "Active Power - Phase B - (kW)"
                ::= { power 2 }
 
            pActivePc OBJECT-TYPE
                SYNTAX DisplayString (SIZE (0..255))
                MAX-ACCESS read-only
                STATUS mandatory
                DESCRIPTION 
                    "Active Power - Phase C - (kW)"
                ::= { power 3 }
 
            pActivePtot OBJECT-TYPE
                SYNTAX DisplayString (SIZE (0..255))
                MAX-ACCESS read-only
                STATUS mandatory
                DESCRIPTION 
                    "Total Active Power - Phase (A,B,C) - (kW)"
                ::= { power 4 }
 
            pReactivePa OBJECT-TYPE
                SYNTAX DisplayString (SIZE (0..255))
                MAX-ACCESS read-only
                STATUS mandatory
                DESCRIPTION 
                    "Reactive Power - Phase A - (kVar)"
                ::= { power 5 }
 
            pReactivePb OBJECT-TYPE
                SYNTAX DisplayString (SIZE (0..255))
                MAX-ACCESS read-only
                STATUS mandatory
                DESCRIPTION 
                    "Reactive Power - Phase B - (kVar)"
                ::= { power 6 }
 
            pReactivePc OBJECT-TYPE
                SYNTAX DisplayString (SIZE (0..255))
                MAX-ACCESS read-only
                STATUS mandatory
                DESCRIPTION 
                    "Reactive Power - Phase C - (kVar)"
                ::= { power 7 }
 
            pReactivePtot OBJECT-TYPE
                SYNTAX DisplayString (SIZE (0..255))
                MAX-ACCESS read-only
                STATUS mandatory
                DESCRIPTION 
                    "Total Reactive Power - Phase (A,B,C) - (kVar)"
                ::= { power 8 }
 
            pApparentPa OBJECT-TYPE
                SYNTAX DisplayString (SIZE (0..255))
                MAX-ACCESS read-only
                STATUS mandatory
                DESCRIPTION 
                    "Apparent Power - Phase A - (kVA)"
                ::= { power 9 }
 
            pApparentPb OBJECT-TYPE
                SYNTAX DisplayString (SIZE (0..255))
                MAX-ACCESS read-only
                STATUS mandatory
                DESCRIPTION 
                    "Apparent Power - Phase B - (kVA)"
                ::= { power 10 }
 
            pApparentPc OBJECT-TYPE
                SYNTAX DisplayString (SIZE (0..255))
                MAX-ACCESS read-only
                STATUS mandatory
                DESCRIPTION 
                    "Apparent Power - Phase C - (kVA)"
                ::= { power 11 }
 
            pApparentPtot OBJECT-TYPE
                SYNTAX DisplayString (SIZE (0..255))
                MAX-ACCESS read-only
                STATUS mandatory
                DESCRIPTION 
                    "Total Apparent Power - Phase (A,B,C) - (kVA)"
                ::= { power 12 }
 
 
        powerFactor OBJECT IDENTIFIER ::= { metering 8 }
 
            pfPfa OBJECT-TYPE
                SYNTAX DisplayString (SIZE (0..255))
                MAX-ACCESS read-only
                STATUS mandatory
                DESCRIPTION 
                    "Power Factor - Phase A"
                ::= { powerFactor 1 }
 
            pfPfb OBJECT-TYPE
                SYNTAX DisplayString (SIZE (0..255))
                MAX-ACCESS read-only
                STATUS mandatory
                DESCRIPTION 
                    "Power Factor - Phase B"
                ::= { powerFactor 2 }
 
            pfPfc OBJECT-TYPE
                SYNTAX DisplayString (SIZE (0..255))
                MAX-ACCESS read-only
                STATUS mandatory
                DESCRIPTION 
                    "Power Factor - Phase C"
                ::= { powerFactor 3 }
 
            pfPftot OBJECT-TYPE
                SYNTAX DisplayString (SIZE (0..255))
                MAX-ACCESS read-only
                STATUS mandatory
                DESCRIPTION 
                    "Total Power Factor - Phase (A, B, C)"
                ::= { powerFactor 4 }
 
            pfPfDisplacementA OBJECT-TYPE
                SYNTAX DisplayString (SIZE (0..255))
                MAX-ACCESS read-only
                STATUS mandatory
                DESCRIPTION 
                    "Displacement Power Factor - Phase A"
                ::= { powerFactor 5 }
 
            pfPfDisplacementB OBJECT-TYPE
                SYNTAX DisplayString (SIZE (0..255))
                MAX-ACCESS read-only
                STATUS mandatory
                DESCRIPTION 
                    "Displacement Power Factor - Phase B"
                ::= { powerFactor 6 }
 
            pfPfDisplacementC OBJECT-TYPE
                SYNTAX DisplayString (SIZE (0..255))
                MAX-ACCESS read-only
                STATUS mandatory
                DESCRIPTION 
                    "Displacement Power Factor - Phase C"
                ::= { powerFactor 7 }
 
            pfPfDisplacementTotal OBJECT-TYPE
                SYNTAX DisplayString (SIZE (0..255))
                MAX-ACCESS read-only
                STATUS mandatory
                DESCRIPTION 
                    "Total Displacement Power Factor - Phase (A, B, C)"
                ::= { powerFactor 8 }
 
 
        phaseRotation OBJECT IDENTIFIER ::= { metering 9 }
 
            prPhaseRotation OBJECT-TYPE
                SYNTAX DisplayString (SIZE (0..255))
                MAX-ACCESS read-only
                STATUS mandatory
                DESCRIPTION 
                    "Phase Rotation (0 = ABC, 1 = CBA)"
                ::= { phaseRotation 1 }
 
 
        accumulatedEnergy  OBJECT IDENTIFIER ::= { metering 10 }
 
            aeResetDateTime OBJECT-TYPE
                SYNTAX DisplayString (SIZE (0..255))
                MAX-ACCESS read-only
                STATUS mandatory
                DESCRIPTION 
                    "Accumulated Energy - Date /Time of Last Reset"
                ::= { accumulatedEnergy 1 }
 
            aeActiveEDelivered OBJECT-TYPE
                SYNTAX DisplayString (SIZE (0..255))
                MAX-ACCESS read-only
                STATUS mandatory
                DESCRIPTION 
                    "Accumulated Energy - Active Energy Delivered - (Wh)"
                ::= { accumulatedEnergy 2 }
 
            aeActiveEReceived OBJECT-TYPE
                SYNTAX DisplayString (SIZE (0..255))
                MAX-ACCESS read-only
                STATUS mandatory
                DESCRIPTION 
                    "Accumulated Energy - Active Energy Received - (Wh)"
                ::= { accumulatedEnergy 3 }
 
            aeActiveEDeliveredPlusReceived OBJECT-TYPE
                SYNTAX DisplayString (SIZE (0..255))
                MAX-ACCESS read-only
                STATUS mandatory
                DESCRIPTION 
                    "Accumulated Energy - Active Energy (Delivered + Received) - (Wh)"
                ::= { accumulatedEnergy 4 }
 
            aeActiveEDeliveredMinusReceived OBJECT-TYPE
                SYNTAX DisplayString (SIZE (0..255))
                MAX-ACCESS read-only
                STATUS mandatory
                DESCRIPTION 
                    "Accumulated Energy - Active Energy (Delivered - Received) - (Wh)"
                ::= { accumulatedEnergy 5 }
 
            aeReactiveEDelivered OBJECT-TYPE
                SYNTAX DisplayString (SIZE (0..255))
                MAX-ACCESS read-only
                STATUS mandatory
                DESCRIPTION 
                    "Accumulated Energy - Reactive Energy Delivered - (VARh)"
                ::= { accumulatedEnergy 6 }
 
            aeReactiveEReceived OBJECT-TYPE
                SYNTAX DisplayString (SIZE (0..255))
                MAX-ACCESS read-only
                STATUS mandatory
                DESCRIPTION 
                    "Accumulated Energy - Reactive Energy Received - (VARh)"
                ::= { accumulatedEnergy 7 }
 
            aeReactiveEDeliveredPlusReceived OBJECT-TYPE
                SYNTAX DisplayString (SIZE (0..255))
                MAX-ACCESS read-only
                STATUS mandatory
                DESCRIPTION 
                    "Accumulated Energy - Reactive Energy (Delivered + Received) - (VARh)"
                ::= { accumulatedEnergy 8 }
 
            aeReactiveEDeliveredMinusReceived OBJECT-TYPE
                SYNTAX DisplayString (SIZE (0..255))
                MAX-ACCESS read-only
                STATUS mandatory
                DESCRIPTION 
                    "Accumulated Energy - Reactive Energy (Delivered - Received) - (VARh)"
                ::= { accumulatedEnergy 9 }
 
            aeApparentEDelivered OBJECT-TYPE
                SYNTAX DisplayString (SIZE (0..255))
                MAX-ACCESS read-only
                STATUS mandatory
                DESCRIPTION 
                    "Accumulated Energy - Apparent Energy Delivered - (VAh)"
                ::= { accumulatedEnergy 10 }
 
            aeApparentEReceived OBJECT-TYPE
                SYNTAX DisplayString (SIZE (0..255))
                MAX-ACCESS read-only
                STATUS mandatory
                DESCRIPTION 
                    "Accumulated Energy - Apparent Energy Received - (VAh)"
                ::= { accumulatedEnergy 11 }
 
            aeApparentEDeliveredPlusReceived OBJECT-TYPE
                SYNTAX DisplayString (SIZE (0..255))
                MAX-ACCESS read-only
                STATUS mandatory
                DESCRIPTION 
                    "Accumulated Energy - Apparent Energy (Delivered + Received) - (VAh)"
                ::= { accumulatedEnergy 12 }
 
            aeApparentEDeliveredMinusReceived OBJECT-TYPE
                SYNTAX DisplayString (SIZE (0..255))
                MAX-ACCESS read-only
                STATUS mandatory
                DESCRIPTION 
                    "Accumulated Energy - Apparent Energy (Delivered - Received) - (VAh)"
                ::= { accumulatedEnergy 13 }
 
 
        inputMetering OBJECT IDENTIFIER ::= { metering 11 }
 
            imInpMtrCh1Accum OBJECT-TYPE
                SYNTAX DisplayString (SIZE (0..255))
                MAX-ACCESS read-only
                STATUS mandatory
                DESCRIPTION 
                    "Input Metering - Channel 1 - Accumulated Value"
                ::= { inputMetering 1 }
 
            imInpMtrCh1AccumRstDtTime OBJECT-TYPE
                SYNTAX DisplayString (SIZE (0..255))
                MAX-ACCESS read-only
                STATUS mandatory
                DESCRIPTION 
                    "Input Metering - Channel 1 - Date / Time of Last Reset"
                ::= { inputMetering 2 }
 
            imInpMtrCh1UnitsCode OBJECT-TYPE
                SYNTAX DisplayString (SIZE (0..255))
                MAX-ACCESS read-only
                STATUS mandatory
                DESCRIPTION 
                    "Input Metering - Channel 1 - Units Code"
                ::= { inputMetering 3 }
 
            imInpMtrCh2Accum OBJECT-TYPE
                SYNTAX DisplayString (SIZE (0..255))
                MAX-ACCESS read-only
                STATUS mandatory
                DESCRIPTION 
                    "Input Metering - Channel 2 - Accumulated Value"
                ::= { inputMetering 4 }
 
            imInpMtrCh2AccumRstDtTime OBJECT-TYPE
                SYNTAX DisplayString (SIZE (0..255))
                MAX-ACCESS read-only
                STATUS mandatory
                DESCRIPTION 
                    "Input Metering - Channel 2 - Date / Time of Last Reset"
                ::= { inputMetering 5 }
 
            imInpMtrCh2UnitsCode OBJECT-TYPE
                SYNTAX DisplayString (SIZE (0..255))
                MAX-ACCESS read-only
                STATUS mandatory
                DESCRIPTION 
                    "Input Metering - Channel 2 - Units Code"
                ::= { inputMetering 6 }
 
            imInpMtrCh3Accum OBJECT-TYPE
                SYNTAX DisplayString (SIZE (0..255))
                MAX-ACCESS read-only
                STATUS mandatory
                DESCRIPTION 
                    "Input Metering - Channel 3 - Accumulated Value"
                ::= { inputMetering 7 }
 
            imInpMtrCh3AccumRstDtTime OBJECT-TYPE
                SYNTAX DisplayString (SIZE (0..255))
                MAX-ACCESS read-only
                STATUS mandatory
                DESCRIPTION 
                    "Input Metering - Channel 3 - Date / Time of Last Reset"
                ::= { inputMetering 8 }
 
            imInpMtrCh3UnitsCode OBJECT-TYPE
                SYNTAX DisplayString (SIZE (0..255))
                MAX-ACCESS read-only
                STATUS mandatory
                DESCRIPTION 
                    "Input Metering - Channel 3 - Units Code"
                ::= { inputMetering 9 }
 
            imInpMtrCh4Accum OBJECT-TYPE
                SYNTAX DisplayString (SIZE (0..255))
                MAX-ACCESS read-only
                STATUS mandatory
                DESCRIPTION 
                    "Input Metering - Channel 4 - Accumulated Value"
                ::= { inputMetering 10 }
 
            imInpMtrCh4AccumRstDtTime OBJECT-TYPE
                SYNTAX DisplayString (SIZE (0..255))
                MAX-ACCESS read-only
                STATUS mandatory
                DESCRIPTION 
                    "Input Metering - Channel 4 - Date / Time of Last Reset"
                ::= { inputMetering 11 }
 
            imInpMtrCh4UnitsCode OBJECT-TYPE
                SYNTAX DisplayString (SIZE (0..255))
                MAX-ACCESS read-only
                STATUS mandatory
                DESCRIPTION 
                    "Input Metering - Channel 4 - Units Code"
                ::= { inputMetering 12 }
 
 
        currentDemand OBJECT IDENTIFIER ::= { metering 12 }
 
            cdIaLastDemand OBJECT-TYPE
                SYNTAX DisplayString (SIZE (0..255))
                MAX-ACCESS read-only
                STATUS mandatory
                DESCRIPTION 
                    "Last Current Demand - Phase A - (Amps)"
                ::= { currentDemand 1 }
 
            cdIaPresentDemand OBJECT-TYPE
                SYNTAX DisplayString (SIZE (0..255))
                MAX-ACCESS read-only
                STATUS mandatory
                DESCRIPTION 
                    "Present Current Demand - Phase A - (Amps)"
                ::= { currentDemand 2 }
 
            cdIaPredictedDemand OBJECT-TYPE
                SYNTAX DisplayString (SIZE (0..255))
                MAX-ACCESS read-only
                STATUS mandatory
                DESCRIPTION 
                    "Predicted Current Demand - Phase A - (Amps)"
                ::= { currentDemand 3 }
 
            cdIaPeakDemand OBJECT-TYPE
                SYNTAX DisplayString (SIZE (0..255))
                MAX-ACCESS read-only
                STATUS mandatory
                DESCRIPTION 
                    "Peak Current Demand - Phase A - (Amps)"
                ::= { currentDemand 4 }
 
            cdIaPeakDemandDateTime OBJECT-TYPE
                SYNTAX DisplayString (SIZE (0..255))
                MAX-ACCESS read-only
                STATUS mandatory
                DESCRIPTION 
                    "Peak Current Demand - Phase A - Date / Time of Peak Value"
                ::= { currentDemand 5 }
 
            cdIbLastDemand OBJECT-TYPE
                SYNTAX DisplayString (SIZE (0..255))
                MAX-ACCESS read-only
                STATUS mandatory
                DESCRIPTION 
                    "Last Current Demand - Phase B - (Amps)"
                ::= { currentDemand 6 }
 
            cdIbPresentDemand OBJECT-TYPE
                SYNTAX DisplayString (SIZE (0..255))
                MAX-ACCESS read-only
                STATUS mandatory
                DESCRIPTION 
                    "Present Current Demand - Phase B - (Amps)"
                ::= { currentDemand 7 }
 
            cdIbPredictedDemand OBJECT-TYPE
                SYNTAX DisplayString (SIZE (0..255))
                MAX-ACCESS read-only
                STATUS mandatory
                DESCRIPTION 
                    "Predicted Current Demand - Phase B - (Amps)"
                ::= { currentDemand 8 }
 
            cdIbPeakDemand OBJECT-TYPE
                SYNTAX DisplayString (SIZE (0..255))
                MAX-ACCESS read-only
                STATUS mandatory
                DESCRIPTION 
                    "Peak Current Demand - Phase B - (Amps)"
                ::= { currentDemand 9 }
 
            cdIbPeakDemandDateTime OBJECT-TYPE
                SYNTAX DisplayString (SIZE (0..255))
                MAX-ACCESS read-only
                STATUS mandatory
                DESCRIPTION 
                    "Peak Current Demand - Phase B - Date / Time of Peak Value"
                ::= { currentDemand 10 }
 
            cdIcLastDemand OBJECT-TYPE
                SYNTAX DisplayString (SIZE (0..255))
                MAX-ACCESS read-only
                STATUS mandatory
                DESCRIPTION 
                    "Last Current Demand - Phase C - (Amps)"
                ::= { currentDemand 11 }
 
            cdIcPresentDemand OBJECT-TYPE
                SYNTAX DisplayString (SIZE (0..255))
                MAX-ACCESS read-only
                STATUS mandatory
                DESCRIPTION 
                    "Present Current Demand - Phase C - (Amps)"
                ::= { currentDemand 12 }
 
            cdIcPredictedDemand OBJECT-TYPE
                SYNTAX DisplayString (SIZE (0..255))
                MAX-ACCESS read-only
                STATUS mandatory
                DESCRIPTION 
                    "Predicted Current Demand - Phase C - (Amps)"
                ::= { currentDemand 13 }
 
            cdIcPeakDemand OBJECT-TYPE
                SYNTAX DisplayString (SIZE (0..255))
                MAX-ACCESS read-only
                STATUS mandatory
                DESCRIPTION 
                    "Peak Current Demand - Phase C - (Amps)"
                ::= { currentDemand 14 }
 
            cdIcPeakDemandDateTime OBJECT-TYPE
                SYNTAX DisplayString (SIZE (0..255))
                MAX-ACCESS read-only
                STATUS mandatory
                DESCRIPTION 
                    "Peak Current Demand - Phase C - Date / Time of Peak Value"
                ::= { currentDemand 15 }
 
            cdPeakDemandResetDateTime OBJECT-TYPE
                SYNTAX DisplayString (SIZE (0..255))
                MAX-ACCESS read-only
                STATUS mandatory
                DESCRIPTION 
                    "Peak Current Demand - Date / Time of Last Reset"
                ::= { currentDemand 16 }
 
 
        powerDemand OBJECT IDENTIFIER ::= { metering 13 }
 
            pdLastActivePowerDemand OBJECT-TYPE
                SYNTAX DisplayString (SIZE (0..255))
                MAX-ACCESS read-only
                STATUS mandatory
                DESCRIPTION 
                    "Last Active Power Demand - (kW)"
                ::= { powerDemand 1 }
 
            pdPresentActivePowerDemand OBJECT-TYPE
                SYNTAX DisplayString (SIZE (0..255))
                MAX-ACCESS read-only
                STATUS mandatory
                DESCRIPTION 
                    "Present Active Power Demand - (kW)"
                ::= { powerDemand 2 }
 
            pdPredictedActivePowerDemand OBJECT-TYPE
                SYNTAX DisplayString (SIZE (0..255))
                MAX-ACCESS read-only
                STATUS mandatory
                DESCRIPTION 
                    "Predicted Active Power Demand - (kW)"
                ::= { powerDemand 3 }
 
            pdPeakActivePowerDemand OBJECT-TYPE
                SYNTAX DisplayString (SIZE (0..255))
                MAX-ACCESS read-only
                STATUS mandatory
                DESCRIPTION 
                    "Peak Active Power Demand - (kW)"
                ::= { powerDemand 4 }
 
            pdLastReactivePowerDemand OBJECT-TYPE
                SYNTAX DisplayString (SIZE (0..255))
                MAX-ACCESS read-only
                STATUS mandatory
                DESCRIPTION 
                    "Last Reactive Power Demand - (kVAR)"
                ::= { powerDemand 5 }
 
            pdPresentReactivePowerDemand OBJECT-TYPE
                SYNTAX DisplayString (SIZE (0..255))
                MAX-ACCESS read-only
                STATUS mandatory
                DESCRIPTION 
                    "Present Reactive Power Demand - (kVAR)"
                ::= { powerDemand 6 }
 
            pdPredictedReactivePowerDemand OBJECT-TYPE
                SYNTAX DisplayString (SIZE (0..255))
                MAX-ACCESS read-only
                STATUS mandatory
                DESCRIPTION 
                    "Predicted Reactive Power Demand - (kVAR)"
                ::= { powerDemand 7 }
 
            pdPeakReactivePowerDemand OBJECT-TYPE
                SYNTAX DisplayString (SIZE (0..255))
                MAX-ACCESS read-only
                STATUS mandatory
                DESCRIPTION 
                    "Peak Reactive Power Demand - (kVAR)"
                ::= { powerDemand 8 }
 
            pdLastApparentPowerDemand OBJECT-TYPE
                SYNTAX DisplayString (SIZE (0..255))
                MAX-ACCESS read-only
                STATUS mandatory
                DESCRIPTION 
                    "Last Apparent Power Demand - (kVA)"
                ::= { powerDemand 9 }
 
            pdPresentApparentPowerDemand OBJECT-TYPE
                SYNTAX DisplayString (SIZE (0..255))
                MAX-ACCESS read-only
                STATUS mandatory
                DESCRIPTION 
                    "Present Apparent Power Demand - (kVA)"
                ::= { powerDemand 10 }
 
            pdPredictedApparentPowerDemand OBJECT-TYPE
                SYNTAX DisplayString (SIZE (0..255))
                MAX-ACCESS read-only
                STATUS mandatory
                DESCRIPTION 
                    "Predicted Apparent Power Demand - (kVA)"
                ::= { powerDemand 11 }
 
            pdPeakApparentPowerDemand OBJECT-TYPE
                SYNTAX DisplayString (SIZE (0..255))
                MAX-ACCESS read-only
                STATUS mandatory
                DESCRIPTION 
                    "Peak Apparent Power Demand - (kVA)"
                ::= { powerDemand 12 }
 
            pdPeakPowerResetDateTime OBJECT-TYPE
                SYNTAX DisplayString (SIZE (0..255))
                MAX-ACCESS read-only
                STATUS mandatory
                DESCRIPTION 
                    "Peak Power Demand - Date / Time of Last Reset"
                ::= { powerDemand 13 }
 
 
        inputMeteringDemand OBJECT IDENTIFIER ::= { metering 14 }
 
            imLastInpMtrCh1Dmd OBJECT-TYPE
                SYNTAX DisplayString (SIZE (0..255))
                MAX-ACCESS read-only
                STATUS mandatory
                DESCRIPTION 
                    "Last Demand - Input Metering - Channel 1"
                ::= { inputMeteringDemand 1 }
 
            imPresInpMtrCh1Dmd OBJECT-TYPE
                SYNTAX DisplayString (SIZE (0..255))
                MAX-ACCESS read-only
                STATUS mandatory
                DESCRIPTION 
                    "Present Demand - Input Metering - Channel 1"
                ::= { inputMeteringDemand 2 }
 
            imPredInpMtrCh1Dmd OBJECT-TYPE
                SYNTAX DisplayString (SIZE (0..255))
                MAX-ACCESS read-only
                STATUS mandatory
                DESCRIPTION 
                    "Predicted Demand - Input Metering - Channel 1"
                ::= { inputMeteringDemand 3 }
 
            imPeakInpMtrCh1Dmd OBJECT-TYPE
                SYNTAX DisplayString (SIZE (0..255))
                MAX-ACCESS read-only
                STATUS mandatory
                DESCRIPTION 
                    "Peak Demand - Input Metering - Channel 1"
                ::= { inputMeteringDemand 4 }
 
            imPeakInpMtrCh1DmdDtTime OBJECT-TYPE
                SYNTAX DisplayString (SIZE (0..255))
                MAX-ACCESS read-only
                STATUS mandatory
                DESCRIPTION 
                    "Peak Demand - Input Metering - Channel 1 - Date / Time"
                ::= { inputMeteringDemand 5 }
 
            imLastInpMtrCh2Dmd OBJECT-TYPE
                SYNTAX DisplayString (SIZE (0..255))
                MAX-ACCESS read-only
                STATUS mandatory
                DESCRIPTION 
                    "Last Demand - Input Metering - Channel 2"
                ::= { inputMeteringDemand 6 }
 
            imPresInpMtrCh2Dmd OBJECT-TYPE
                SYNTAX DisplayString (SIZE (0..255))
                MAX-ACCESS read-only
                STATUS mandatory
                DESCRIPTION 
                    "Present Demand - Input Metering - Channel 2"
                ::= { inputMeteringDemand 7 }
 
            imPredInpMtrCh2Dmd OBJECT-TYPE
                SYNTAX DisplayString (SIZE (0..255))
                MAX-ACCESS read-only
                STATUS mandatory
                DESCRIPTION 
                    "Predicted Demand - Input Metering - Channel 2"
                ::= { inputMeteringDemand 8 }
 
            imPeakInpMtrCh2Dmd OBJECT-TYPE
                SYNTAX DisplayString (SIZE (0..255))
                MAX-ACCESS read-only
                STATUS mandatory
                DESCRIPTION 
                    "Peak Demand - Input Metering - Channel 2"
                ::= { inputMeteringDemand 9 }
 
            imPeakInpMtrCh2DmdDtTime OBJECT-TYPE
                SYNTAX DisplayString (SIZE (0..255))
                MAX-ACCESS read-only
                STATUS mandatory
                DESCRIPTION 
                    "Peak Demand - Input Metering - Channel 2 - Date / Time"
                ::= { inputMeteringDemand 10 }
 
            imLastInpMtrCh3Dmd OBJECT-TYPE
                SYNTAX DisplayString (SIZE (0..255))
                MAX-ACCESS read-only
                STATUS mandatory
                DESCRIPTION 
                    "Last Demand - Input Metering - Channel 3"
                ::= { inputMeteringDemand 11 }
 
            imPresInpMtrCh3Dmd OBJECT-TYPE
                SYNTAX DisplayString (SIZE (0..255))
                MAX-ACCESS read-only
                STATUS mandatory
                DESCRIPTION 
                    "Present Demand - Input Metering - Channel 3"
                ::= { inputMeteringDemand 12 }
 
            imPredInpMtrCh3Dmd OBJECT-TYPE
                SYNTAX DisplayString (SIZE (0..255))
                MAX-ACCESS read-only
                STATUS mandatory
                DESCRIPTION 
                    "Predicted Demand - Input Metering - Channel 3"
                ::= { inputMeteringDemand 13 }
 
            imPeakInpMtrCh3Dmd OBJECT-TYPE
                SYNTAX DisplayString (SIZE (0..255))
                MAX-ACCESS read-only
                STATUS mandatory
                DESCRIPTION 
                    "Peak Demand - Input Metering - Channel 3"
                ::= { inputMeteringDemand 14 }
 
            imPeakInpMtrCh3DmdDtTime OBJECT-TYPE
                SYNTAX DisplayString (SIZE (0..255))
                MAX-ACCESS read-only
                STATUS mandatory
                DESCRIPTION 
                    "Peak Demand - Input Metering - Channel 3 - Date / Time"
                ::= { inputMeteringDemand 15 }
 
            imLastInpMtrCh4Dmd OBJECT-TYPE
                SYNTAX DisplayString (SIZE (0..255))
                MAX-ACCESS read-only
                STATUS mandatory
                DESCRIPTION 
                    "Last Demand - Input Metering - Channel 4"
                ::= { inputMeteringDemand 16 }
 
            imPresInpMtrCh4Dmd OBJECT-TYPE
                SYNTAX DisplayString (SIZE (0..255))
                MAX-ACCESS read-only
                STATUS mandatory
                DESCRIPTION 
                    "Present Demand - Input Metering - Channel 4"
                ::= { inputMeteringDemand 17 }
 
            imPredInpMtrCh4Dmd OBJECT-TYPE
                SYNTAX DisplayString (SIZE (0..255))
                MAX-ACCESS read-only
                STATUS mandatory
                DESCRIPTION 
                    "Predicted Demand - Input Metering - Channel 4"
                ::= { inputMeteringDemand 18 }
 
            imPeakInpMtrCh4Dmd OBJECT-TYPE
                SYNTAX DisplayString (SIZE (0..255))
                MAX-ACCESS read-only
                STATUS mandatory
                DESCRIPTION 
                    "Peak Demand - Input Metering - Channel 4"
                ::= { inputMeteringDemand 19 }
 
            imPeakInpMtrCh4DmdDtTime OBJECT-TYPE
                SYNTAX DisplayString (SIZE (0..255))
                MAX-ACCESS read-only
                STATUS mandatory
                DESCRIPTION 
                    "Peak Demand - Input Metering - Channel 4 - Date / Time"
                ::= { inputMeteringDemand 20 }
 
            imInpMtrPeakDmdRstDtTime OBJECT-TYPE
                SYNTAX DisplayString (SIZE (0..255))
                MAX-ACCESS read-only
                STATUS mandatory
                DESCRIPTION 
                    "Peak Demand - Input Metering - Date / Time of Last Reset"
                ::= { inputMeteringDemand 21 }
 
 
 
        io OBJECT IDENTIFIER ::= { pm556x 4 }
 
        inputs OBJECT IDENTIFIER ::= { io 1 }
 
        ioInput1 OBJECT IDENTIFIER ::= { inputs 1 }
 
            ioInput1OnOffStatus OBJECT-TYPE
                SYNTAX DisplayString (SIZE (0..255))
                MAX-ACCESS read-only
                STATUS mandatory
                DESCRIPTION 
                    "Input 1 - On / Off Status"
                ::= { ioInput1 1 }
 
            ioInput1Label OBJECT-TYPE
                SYNTAX DisplayString (SIZE (0..255))
                MAX-ACCESS read-only
                STATUS mandatory
                DESCRIPTION 
                    "Input 1 - Label"
                ::= { ioInput1 2 }
 
            ioInput1Type OBJECT-TYPE
                SYNTAX DisplayString (SIZE (0..255))
                MAX-ACCESS read-only
                STATUS mandatory
                DESCRIPTION 
                    "Input 1 - Type - First digit (1) indicates point is digital input
Second digit indicates the digital input module type
Second digit can be used to identify specific hardware options.
   0 = Generic digital input
Third digit indicates input type
   1 = AC
   2 = DC"
                ::= { ioInput1 3 }
 
            ioInput1ControlMode OBJECT-TYPE
                SYNTAX DisplayString (SIZE (0..255))
                MAX-ACCESS read-only
                STATUS mandatory
                DESCRIPTION 
                    "Input 1 - ControlMode
0 = Normal (Alarm)
1 = Demand Interval Sync Pulse
2 = Multi-tariff Control
3 = Input Metering
4 = Conditional Energy Control
5 = Incremental Energy Reset"
                ::= { ioInput1 4 }
 
            ioInput1DebounceTime OBJECT-TYPE
                SYNTAX DisplayString (SIZE (0..255))
                MAX-ACCESS read-only
                STATUS mandatory
                DESCRIPTION 
                    "Input 1 - Debounce Time (10mS increments)"
                ::= { ioInput1 5 }
 
            ioInput1Counter OBJECT-TYPE
                SYNTAX DisplayString (SIZE (0..255))
                MAX-ACCESS read-only
                STATUS mandatory
                DESCRIPTION 
                    "Input 1 - Counter"
                ::= { ioInput1 6 }
 
            ioInput1OnTime OBJECT-TYPE
                SYNTAX DisplayString (SIZE (0..255))
                MAX-ACCESS read-only
                STATUS mandatory
                DESCRIPTION 
                    "Input 1 - On Time (Seconds)"
                ::= { ioInput1 7 }
 
 
        ioInput2 OBJECT IDENTIFIER ::= { inputs 2 }
 
            ioInput2OnOffStatus OBJECT-TYPE
                SYNTAX DisplayString (SIZE (0..255))
                MAX-ACCESS read-only
                STATUS mandatory
                DESCRIPTION 
                    "Input 2 - On / Off Status"
                ::= { ioInput2 1 }
 
            ioInput2Label OBJECT-TYPE
                SYNTAX DisplayString (SIZE (0..255))
                MAX-ACCESS read-only
                STATUS mandatory
                DESCRIPTION 
                    "Input 2 - Label"
                ::= { ioInput2 2 }
 
            ioInput2Type OBJECT-TYPE
                SYNTAX DisplayString (SIZE (0..255))
                MAX-ACCESS read-only
                STATUS mandatory
                DESCRIPTION 
                    "Input 2 - Type - First digit (1) indicates point is digital input
Second digit indicates the digital input module type
Second digit can be used to identify specific hardware options.
   0 = Generic digital input
Third digit indicates input type
   1 = AC
   2 = DC"
                ::= { ioInput2 3 }
 
            ioInput2ControlMode OBJECT-TYPE
                SYNTAX DisplayString (SIZE (0..255))
                MAX-ACCESS read-only
                STATUS mandatory
                DESCRIPTION 
                    "Input 2 - ControlMode
0 = Normal (Alarm)
1 = Demand Interval Sync Pulse
2 = Multi-tariff Control
3 = Input Metering
4 = Conditional Energy Control
5 = Incremental Energy Reset"
                ::= { ioInput2 4 }
 
            ioInput2DebounceTime OBJECT-TYPE
                SYNTAX DisplayString (SIZE (0..255))
                MAX-ACCESS read-only
                STATUS mandatory
                DESCRIPTION 
                    "Input 2 - Debounce Time (10mS increments)"
                ::= { ioInput2 5 }
 
            ioInput2Counter OBJECT-TYPE
                SYNTAX DisplayString (SIZE (0..255))
                MAX-ACCESS read-only
                STATUS mandatory
                DESCRIPTION 
                    "Input 2 - Counter"
                ::= { ioInput2 6 }
 
            ioInput2OnTime OBJECT-TYPE
                SYNTAX DisplayString (SIZE (0..255))
                MAX-ACCESS read-only
                STATUS mandatory
                DESCRIPTION 
                    "Input 2 - On Time (Seconds)"
                ::= { ioInput2 7 }
 
 
        ioInput3 OBJECT IDENTIFIER ::= { inputs 3 }
 
            ioInput3OnOffStatus OBJECT-TYPE
                SYNTAX DisplayString (SIZE (0..255))
                MAX-ACCESS read-only
                STATUS mandatory
                DESCRIPTION 
                    "Input 3 - On / Off Status"
                ::= { ioInput3 1 }
 
            ioInput3Label OBJECT-TYPE
                SYNTAX DisplayString (SIZE (0..255))
                MAX-ACCESS read-only
                STATUS mandatory
                DESCRIPTION 
                    "Input 3 - Label"
                ::= { ioInput3 2 }
 
            ioInput3Type OBJECT-TYPE
                SYNTAX DisplayString (SIZE (0..255))
                MAX-ACCESS read-only
                STATUS mandatory
                DESCRIPTION 
                    "Input 3 - Type - First digit (1) indicates point is digital input
Second digit indicates the digital input module type
Second digit can be used to identify specific hardware options.
   0 = Generic digital input
Third digit indicates input type
   1 = AC
   2 = DC"
                ::= { ioInput3 3 }
 
            ioInput3ControlMode OBJECT-TYPE
                SYNTAX DisplayString (SIZE (0..255))
                MAX-ACCESS read-only
                STATUS mandatory
                DESCRIPTION 
                    "Input 3 - ControlMode
0 = Normal (Alarm)
1 = Demand Interval Sync Pulse
2 = Multi-tariff Control
3 = Input Metering
4 = Conditional Energy Control
5 = Incremental Energy Reset"
                ::= { ioInput3 4 }
 
            ioInput3DebounceTime OBJECT-TYPE
                SYNTAX DisplayString (SIZE (0..255))
                MAX-ACCESS read-only
                STATUS mandatory
                DESCRIPTION 
                    "Input 3 - Debounce Time (10mS increments)"
                ::= { ioInput3 5 }
 
            ioInput3Counter OBJECT-TYPE
                SYNTAX DisplayString (SIZE (0..255))
                MAX-ACCESS read-only
                STATUS mandatory
                DESCRIPTION 
                    "Input 3 - Counter"
                ::= { ioInput3 6 }
 
            ioInput3OnTime OBJECT-TYPE
                SYNTAX DisplayString (SIZE (0..255))
                MAX-ACCESS read-only
                STATUS mandatory
                DESCRIPTION 
                    "Input 3 - On Time (Seconds)"
                ::= { ioInput3 7 }
 
 
        ioInput4 OBJECT IDENTIFIER ::= { inputs 4 }
 
            ioInput4OnOffStatus OBJECT-TYPE
                SYNTAX DisplayString (SIZE (0..255))
                MAX-ACCESS read-only
                STATUS mandatory
                DESCRIPTION 
                    "Input 4 - On / Off Status"
                ::= { ioInput4 1 }
 
            ioInput4Label OBJECT-TYPE
                SYNTAX DisplayString (SIZE (0..255))
                MAX-ACCESS read-only
                STATUS mandatory
                DESCRIPTION 
                    "Input 4 - Label"
                ::= { ioInput4 2 }
 
            ioInput4Type OBJECT-TYPE
                SYNTAX DisplayString (SIZE (0..255))
                MAX-ACCESS read-only
                STATUS mandatory
                DESCRIPTION 
                    "Input 4 - Type - First digit (1) indicates point is digital input
Second digit indicates the digital input module type
Second digit can be used to identify specific hardware options.
   0 = Generic digital input
Third digit indicates input type
   1 = AC
   2 = DC"
                ::= { ioInput4 3 }
 
            ioInput4ControlMode OBJECT-TYPE
                SYNTAX DisplayString (SIZE (0..255))
                MAX-ACCESS read-only
                STATUS mandatory
                DESCRIPTION 
                    "Input 4 - ControlMode
0 = Normal (Alarm)
1 = Demand Interval Sync Pulse
2 = Multi-tariff Control
3 = Input Metering
4 = Conditional Energy Control
5 = Incremental Energy Reset"
                ::= { ioInput4 4 }
 
            ioInput4DebounceTime OBJECT-TYPE
                SYNTAX DisplayString (SIZE (0..255))
                MAX-ACCESS read-only
                STATUS mandatory
                DESCRIPTION 
                    "Input 4 - Debounce Time (10mS increments)"
                ::= { ioInput4 5 }
 
            ioInput4Counter OBJECT-TYPE
                SYNTAX DisplayString (SIZE (0..255))
                MAX-ACCESS read-only
                STATUS mandatory
                DESCRIPTION 
                    "Input 4 - Counter"
                ::= { ioInput4 6 }
 
            ioInput4OnTime OBJECT-TYPE
                SYNTAX DisplayString (SIZE (0..255))
                MAX-ACCESS read-only
                STATUS mandatory
                DESCRIPTION 
                    "Input 4 - On Time (Seconds)"
                ::= { ioInput4 7 }
 
 
        outputs OBJECT IDENTIFIER ::= { io 2 }
 
        ioOutput1 OBJECT IDENTIFIER ::= { outputs 1 }
 
            ioOutput1OnOffStatus OBJECT-TYPE
                SYNTAX DisplayString (SIZE (0..255))
                MAX-ACCESS read-only
                STATUS mandatory
                DESCRIPTION 
                    "Output 1 - On / Off Status"
                ::= { ioOutput1 1 }
 
            ioOutput1Label OBJECT-TYPE
                SYNTAX DisplayString (SIZE (0..255))
                MAX-ACCESS read-only
                STATUS mandatory
                DESCRIPTION 
                    "Output 1 - Label"
                ::= { ioOutput1 2 }
 
            ioOutput1Type OBJECT-TYPE
                SYNTAX DisplayString (SIZE (0..255))
                MAX-ACCESS read-only
                STATUS mandatory
                DESCRIPTION 
                    "Output 1 - Type - First digit (2) indicates point is digital output 
Second digit indicates module type    
    0 = Generic Digital output
Third digit indicates output type    
    1 = solid state relay    
    2 = electromechanical relay
"
                ::= { ioOutput1 3 }
 
            ioOutput1EnabledDisabledState OBJECT-TYPE
                SYNTAX DisplayString (SIZE (0..255))
                MAX-ACCESS read-only
                STATUS mandatory
                DESCRIPTION 
                    "Output 1 - Enabled / Disabled Status - (0 = Disabled, 1= Enabled)"
                ::= { ioOutput1 4 }
 
            ioOutput1Behavior OBJECT-TYPE
                SYNTAX DisplayString (SIZE (0..255))
                MAX-ACCESS read-only
                STATUS mandatory
                DESCRIPTION 
                    "Output 1 - Behavior - (0 = Normal, 1 = Timed, 2 = Coil Hold)"
                ::= { ioOutput1 5 }
 
            ioOutput1OnTimerTime OBJECT-TYPE
                SYNTAX DisplayString (SIZE (0..255))
                MAX-ACCESS read-only
                STATUS mandatory
                DESCRIPTION 
                    "Output 1 - On Timer Time (Seconds)"
                ::= { ioOutput1 6 }
 
 
        ioOutput2 OBJECT IDENTIFIER ::= { outputs 2 }
 
            ioOutput2OnOffStatus OBJECT-TYPE
                SYNTAX DisplayString (SIZE (0..255))
                MAX-ACCESS read-only
                STATUS mandatory
                DESCRIPTION 
                    "Output 2 - On / Off Status"
                ::= { ioOutput2 1 }
 
            ioOutput2Label OBJECT-TYPE
                SYNTAX DisplayString (SIZE (0..255))
                MAX-ACCESS read-only
                STATUS mandatory
                DESCRIPTION 
                    "Output 2 - Label"
                ::= { ioOutput2 2 }
 
            ioOutput2Type OBJECT-TYPE
                SYNTAX DisplayString (SIZE (0..255))
                MAX-ACCESS read-only
                STATUS mandatory
                DESCRIPTION 
                    "Output 2 - Type - First digit (2) indicates point is digital output 
Second digit indicates module type    
    0 = Generic Digital output
Third digit indicates output type    
    1 = solid state relay    
    2 = electromechanical relay
"
                ::= { ioOutput2 3 }
 
            ioOutput2EnabledDisabledState OBJECT-TYPE
                SYNTAX DisplayString (SIZE (0..255))
                MAX-ACCESS read-only
                STATUS mandatory
                DESCRIPTION 
                    "Output 2 - Enabled / Disabled Status - (0 = Disabled, 1= Enabled)"
                ::= { ioOutput2 4 }
 
            ioOutput2Behavior OBJECT-TYPE
                SYNTAX DisplayString (SIZE (0..255))
                MAX-ACCESS read-only
                STATUS mandatory
                DESCRIPTION 
                    "Output 2 - Behavior - (0 = Normal, 1 = Timed, 2 = Coil Hold)"
                ::= { ioOutput2 5 }
 
            ioOutput2OnTimerTime OBJECT-TYPE
                SYNTAX DisplayString (SIZE (0..255))
                MAX-ACCESS read-only
                STATUS mandatory
                DESCRIPTION 
                    "Output 2 - On Timer Time (Seconds)"
                ::= { ioOutput2 6 }
 
 
 
        alarms OBJECT IDENTIFIER ::= { pm556x 5 }
 
        alarmsConfiguration OBJECT IDENTIFIER ::= { alarms 1 }
 
        oneSecStdAlarmConfiguration OBJECT IDENTIFIER ::= { alarmsConfiguration 1 }
 
        almCfgOverCurrPh OBJECT IDENTIFIER ::= { oneSecStdAlarmConfiguration 1 }
 
            almCfgOverCurrPhEnableDisable OBJECT-TYPE
                SYNTAX DisplayString (SIZE (0..255))
                MAX-ACCESS read-only
                STATUS mandatory
                DESCRIPTION 
                    "Alarm Configuration - Over Current Phase - Enable / Disable"
                ::= { almCfgOverCurrPh 1 }
 
            almCfgOverCurrPhPriority OBJECT-TYPE
                SYNTAX DisplayString (SIZE (0..255))
                MAX-ACCESS read-only
                STATUS mandatory
                DESCRIPTION 
                    "Alarm Configuration - Over Current Phase - Priority"
                ::= { almCfgOverCurrPh 2 }
 
            almCfgOverCurrPhPkupStPnt OBJECT-TYPE
                SYNTAX DisplayString (SIZE (0..255))
                MAX-ACCESS read-only
                STATUS mandatory
                DESCRIPTION 
                    "Alarm Configuration - Over Current Phase - Pickup Setpoint (Amps)"
                ::= { almCfgOverCurrPh 3 }
 
            almCfgOverCurrPhPkupDly OBJECT-TYPE
                SYNTAX DisplayString (SIZE (0..255))
                MAX-ACCESS read-only
                STATUS mandatory
                DESCRIPTION 
                    "Alarm Configuration - Over Current Phase - Pickup Delay (Seconds)"
                ::= { almCfgOverCurrPh 4 }
 
            almCfgOverCurrPhDrpStPnt OBJECT-TYPE
                SYNTAX DisplayString (SIZE (0..255))
                MAX-ACCESS read-only
                STATUS mandatory
                DESCRIPTION 
                    "Alarm Configuration - Over Current Phase - Drop Out Setpoint (Amps)"
                ::= { almCfgOverCurrPh 5 }
 
            almCfgOverCurrPhDrpDly OBJECT-TYPE
                SYNTAX DisplayString (SIZE (0..255))
                MAX-ACCESS read-only
                STATUS mandatory
                DESCRIPTION 
                    "Alarm Configuration - Over Current Phase - Drop Out Delay (Seconds)"
                ::= { almCfgOverCurrPh 6 }
 
            almCfgOverCurrPhDOs   OBJECT-TYPE
                SYNTAX DisplayString (SIZE (0..255))
                MAX-ACCESS read-only
                STATUS mandatory
                DESCRIPTION 
                    "Alarm Configuration - Over Current Phase - Associated Digital Outputs. Bitmap of digital outputs to associate with this alarm.
Bitmap is right-justified with the least significant bit associated with digital output ID of 1."
                ::= { almCfgOverCurrPh 7 }
 
 
        almCfgUnderCurrPh OBJECT IDENTIFIER ::= { oneSecStdAlarmConfiguration 2 }
 
            almCfgUnderCurrPhEnableDisable OBJECT-TYPE
                SYNTAX DisplayString (SIZE (0..255))
                MAX-ACCESS read-only
                STATUS mandatory
                DESCRIPTION 
                    "Alarm Configuration - Under Current Phase - Enable / Disable"
                ::= { almCfgUnderCurrPh 1 }
 
            almCfgUnderCurrPhPriority OBJECT-TYPE
                SYNTAX DisplayString (SIZE (0..255))
                MAX-ACCESS read-only
                STATUS mandatory
                DESCRIPTION 
                    "Alarm Configuration - Under Current Phase - Priority"
                ::= { almCfgUnderCurrPh 2 }
 
            almCfgUnderCurrPhPkupStPnt OBJECT-TYPE
                SYNTAX DisplayString (SIZE (0..255))
                MAX-ACCESS read-only
                STATUS mandatory
                DESCRIPTION 
                    "Alarm Configuration - Under Current Phase - Pickup Setpoint (Amps)"
                ::= { almCfgUnderCurrPh 3 }
 
            almCfgUnderCurrPhPkupDly OBJECT-TYPE
                SYNTAX DisplayString (SIZE (0..255))
                MAX-ACCESS read-only
                STATUS mandatory
                DESCRIPTION 
                    "Alarm Configuration - Under Current Phase - Pickup Delay (Seconds)"
                ::= { almCfgUnderCurrPh 4 }
 
            almCfgUnderCurrPhDrpStPnt OBJECT-TYPE
                SYNTAX DisplayString (SIZE (0..255))
                MAX-ACCESS read-only
                STATUS mandatory
                DESCRIPTION 
                    "Alarm Configuration - Under Current Phase - Drop Out Setpoint (Amps)"
                ::= { almCfgUnderCurrPh 5 }
 
            almCfgUnderCurrPhDrpDly OBJECT-TYPE
                SYNTAX DisplayString (SIZE (0..255))
                MAX-ACCESS read-only
                STATUS mandatory
                DESCRIPTION 
                    "Alarm Configuration - Under Current Phase - Drop Out Delay (Seconds)"
                ::= { almCfgUnderCurrPh 6 }
 
            almCfgUnderCurrPhDOs   OBJECT-TYPE
                SYNTAX DisplayString (SIZE (0..255))
                MAX-ACCESS read-only
                STATUS mandatory
                DESCRIPTION 
                    "Alarm Configuration - Under Current Phase - Associated Digital Outputs. Bitmap of digital outputs to associate with this alarm.
Bitmap is right-justified with the least significant bit associated with digital output ID of 1."
                ::= { almCfgUnderCurrPh 7 }
 
 
        almCfgOverCurrNtrl OBJECT IDENTIFIER ::= { oneSecStdAlarmConfiguration 3 }
 
            almCfgOverCurrNtrlEnableDisable OBJECT-TYPE
                SYNTAX DisplayString (SIZE (0..255))
                MAX-ACCESS read-only
                STATUS mandatory
                DESCRIPTION 
                    "Alarm Configuration - Over Current Neutral - Enable / Disable"
                ::= { almCfgOverCurrNtrl 1 }
 
            almCfgOverCurrNtrlPriority OBJECT-TYPE
                SYNTAX DisplayString (SIZE (0..255))
                MAX-ACCESS read-only
                STATUS mandatory
                DESCRIPTION 
                    "Alarm Configuration - Over Current Neutral - Priority"
                ::= { almCfgOverCurrNtrl 2 }
 
            almCfgOverCurrNtrlPkupStPnt OBJECT-TYPE
                SYNTAX DisplayString (SIZE (0..255))
                MAX-ACCESS read-only
                STATUS mandatory
                DESCRIPTION 
                    "Alarm Configuration - Over Current Neutral - Pickup Setpoint (Amps)"
                ::= { almCfgOverCurrNtrl 3 }
 
            almCfgOverCurrNtrlPkupDly OBJECT-TYPE
                SYNTAX DisplayString (SIZE (0..255))
                MAX-ACCESS read-only
                STATUS mandatory
                DESCRIPTION 
                    "Alarm Configuration - Over Current Neutral - Pickup Delay (Seconds)"
                ::= { almCfgOverCurrNtrl 4 }
 
            almCfgOverCurrNtrlDrpStPnt OBJECT-TYPE
                SYNTAX DisplayString (SIZE (0..255))
                MAX-ACCESS read-only
                STATUS mandatory
                DESCRIPTION 
                    "Alarm Configuration - Over Current Neutral - Drop Out Setpoint (Amps)"
                ::= { almCfgOverCurrNtrl 5 }
 
            almCfgOverCurrNtrlDrpDly OBJECT-TYPE
                SYNTAX DisplayString (SIZE (0..255))
                MAX-ACCESS read-only
                STATUS mandatory
                DESCRIPTION 
                    "Alarm Configuration - Over Current Neutral - Drop Out Delay (Seconds)"
                ::= { almCfgOverCurrNtrl 6 }
 
            almCfgOverCurrNtrlDOs   OBJECT-TYPE
                SYNTAX DisplayString (SIZE (0..255))
                MAX-ACCESS read-only
                STATUS mandatory
                DESCRIPTION 
                    "Alarm Configuration - Over Current Neutral - Associated Digital Outputs. Bitmap of digital outputs to associate with this alarm.
Bitmap is right-justified with the least significant bit associated with digital output ID of 1."
                ::= { almCfgOverCurrNtrl 7 }
 
 
        almCfgOverCurrGnd OBJECT IDENTIFIER ::= { oneSecStdAlarmConfiguration 4 }
 
            almCfgOverCurrGndEnableDisable OBJECT-TYPE
                SYNTAX DisplayString (SIZE (0..255))
                MAX-ACCESS read-only
                STATUS mandatory
                DESCRIPTION 
                    "Alarm Configuration - Over Current Ground - Enable / Disable"
                ::= { almCfgOverCurrGnd 1 }
 
            almCfgOverCurrGndPriority OBJECT-TYPE
                SYNTAX DisplayString (SIZE (0..255))
                MAX-ACCESS read-only
                STATUS mandatory
                DESCRIPTION 
                    "Alarm Configuration - Over Current Ground - Priority"
                ::= { almCfgOverCurrGnd 2 }
 
            almCfgOverCurrGndPkupStPnt OBJECT-TYPE
                SYNTAX DisplayString (SIZE (0..255))
                MAX-ACCESS read-only
                STATUS mandatory
                DESCRIPTION 
                    "Alarm Configuration - Over Current Ground - Pickup Setpoint (Amps)"
                ::= { almCfgOverCurrGnd 3 }
 
            almCfgOverCurrGndPkupDly OBJECT-TYPE
                SYNTAX DisplayString (SIZE (0..255))
                MAX-ACCESS read-only
                STATUS mandatory
                DESCRIPTION 
                    "Alarm Configuration - Over Current Ground - Pickup Delay (Seconds)"
                ::= { almCfgOverCurrGnd 4 }
 
            almCfgOverCurrGndDrpStPnt OBJECT-TYPE
                SYNTAX DisplayString (SIZE (0..255))
                MAX-ACCESS read-only
                STATUS mandatory
                DESCRIPTION 
                    "Alarm Configuration - Over Current Ground - Drop Out Setpoint (Amps)"
                ::= { almCfgOverCurrGnd 5 }
 
            almCfgOverCurrGndDrpDly OBJECT-TYPE
                SYNTAX DisplayString (SIZE (0..255))
                MAX-ACCESS read-only
                STATUS mandatory
                DESCRIPTION 
                    "Alarm Configuration - Over Current Ground - Drop Out Delay (Seconds)"
                ::= { almCfgOverCurrGnd 6 }
 
            almCfgOverCurrGndDOs   OBJECT-TYPE
                SYNTAX DisplayString (SIZE (0..255))
                MAX-ACCESS read-only
                STATUS mandatory
                DESCRIPTION 
                    "Alarm Configuration - Over Current Ground - Associated Digital Outputs. Bitmap of digital outputs to associate with this alarm.
Bitmap is right-justified with the least significant bit associated with digital output ID of 1."
                ::= { almCfgOverCurrGnd 7 }
 
 
        almCfgOverVoltLL OBJECT IDENTIFIER ::= { oneSecStdAlarmConfiguration 5 }
 
            almCfgOverVoltLLEnableDisable OBJECT-TYPE
                SYNTAX DisplayString (SIZE (0..255))
                MAX-ACCESS read-only
                STATUS mandatory
                DESCRIPTION 
                    "Alarm Configuration - Over Voltage L-L - Enable / Disable"
                ::= { almCfgOverVoltLL 1 }
 
            almCfgOverVoltLLPriority OBJECT-TYPE
                SYNTAX DisplayString (SIZE (0..255))
                MAX-ACCESS read-only
                STATUS mandatory
                DESCRIPTION 
                    "Alarm Configuration - Over Voltage L-L - Priority"
                ::= { almCfgOverVoltLL 2 }
 
            almCfgOverVoltLLPkupStPnt OBJECT-TYPE
                SYNTAX DisplayString (SIZE (0..255))
                MAX-ACCESS read-only
                STATUS mandatory
                DESCRIPTION 
                    "Alarm Configuration - Over Voltage L-L - Pickup Setpoint (Volts)"
                ::= { almCfgOverVoltLL 3 }
 
            almCfgOverVoltLLPkupDly OBJECT-TYPE
                SYNTAX DisplayString (SIZE (0..255))
                MAX-ACCESS read-only
                STATUS mandatory
                DESCRIPTION 
                    "Alarm Configuration - Over Voltage L-L - Pickup Delay (Seconds)"
                ::= { almCfgOverVoltLL 4 }
 
            almCfgOverVoltLLDrpStPnt OBJECT-TYPE
                SYNTAX DisplayString (SIZE (0..255))
                MAX-ACCESS read-only
                STATUS mandatory
                DESCRIPTION 
                    "Alarm Configuration - Over Voltage L-L - Drop Out Setpoint (Volts)"
                ::= { almCfgOverVoltLL 5 }
 
            almCfgOverVoltLLDrpDly OBJECT-TYPE
                SYNTAX DisplayString (SIZE (0..255))
                MAX-ACCESS read-only
                STATUS mandatory
                DESCRIPTION 
                    "Alarm Configuration - Over Voltage L-L - Drop Out Delay (Seconds)"
                ::= { almCfgOverVoltLL 6 }
 
            almCfgOverVoltLLDOs   OBJECT-TYPE
                SYNTAX DisplayString (SIZE (0..255))
                MAX-ACCESS read-only
                STATUS mandatory
                DESCRIPTION 
                    "Alarm Configuration - Over Voltage L-L - Associated Digital Outputs. Bitmap of digital outputs to associate with this alarm.
Bitmap is right-justified with the least significant bit associated with digital output ID of 1."
                ::= { almCfgOverVoltLL 7 }
 
 
        almCfgUnderVoltLL OBJECT IDENTIFIER ::= { oneSecStdAlarmConfiguration 6 }
 
            almCfgUnderVoltLLEnableDisable OBJECT-TYPE
                SYNTAX DisplayString (SIZE (0..255))
                MAX-ACCESS read-only
                STATUS mandatory
                DESCRIPTION 
                    "Alarm Configuration - Under Voltage L-L - Enable / Disable"
                ::= { almCfgUnderVoltLL 1 }
 
            almCfgUnderVoltLLPriority OBJECT-TYPE
                SYNTAX DisplayString (SIZE (0..255))
                MAX-ACCESS read-only
                STATUS mandatory
                DESCRIPTION 
                    "Alarm Configuration - Under Voltage L-L - Priority"
                ::= { almCfgUnderVoltLL 2 }
 
            almCfgUnderVoltLLPkupStPnt OBJECT-TYPE
                SYNTAX DisplayString (SIZE (0..255))
                MAX-ACCESS read-only
                STATUS mandatory
                DESCRIPTION 
                    "Alarm Configuration - Under Voltage L-L - Pickup Setpoint (Volts)"
                ::= { almCfgUnderVoltLL 3 }
 
            almCfgUnderVoltLLPkupDly OBJECT-TYPE
                SYNTAX DisplayString (SIZE (0..255))
                MAX-ACCESS read-only
                STATUS mandatory
                DESCRIPTION 
                    "Alarm Configuration - Under Voltage L-L - Pickup Delay (Seconds)"
                ::= { almCfgUnderVoltLL 4 }
 
            almCfgUnderVoltLLDrpStPnt OBJECT-TYPE
                SYNTAX DisplayString (SIZE (0..255))
                MAX-ACCESS read-only
                STATUS mandatory
                DESCRIPTION 
                    "Alarm Configuration - Under Voltage L-L - Drop Out Setpoint (Volts)"
                ::= { almCfgUnderVoltLL 5 }
 
            almCfgUnderVoltLLDrpDly OBJECT-TYPE
                SYNTAX DisplayString (SIZE (0..255))
                MAX-ACCESS read-only
                STATUS mandatory
                DESCRIPTION 
                    "Alarm Configuration - Under Voltage L-L - Drop Out Delay (Seconds)"
                ::= { almCfgUnderVoltLL 6 }
 
            almCfgUnderVoltLLDOs   OBJECT-TYPE
                SYNTAX DisplayString (SIZE (0..255))
                MAX-ACCESS read-only
                STATUS mandatory
                DESCRIPTION 
                    "Alarm Configuration - Under Voltage L-L - Associated Digital Outputs. Bitmap of digital outputs to associate with this alarm.
Bitmap is right-justified with the least significant bit associated with digital output ID of 1."
                ::= { almCfgUnderVoltLL 7 }
 
 
        almCfgOverVoltLN OBJECT IDENTIFIER ::= { oneSecStdAlarmConfiguration 7 }
 
            almCfgOverVoltLNEnableDisable OBJECT-TYPE
                SYNTAX DisplayString (SIZE (0..255))
                MAX-ACCESS read-only
                STATUS mandatory
                DESCRIPTION 
                    "Alarm Configuration - Over Voltage L-N - Enable / Disable"
                ::= { almCfgOverVoltLN 1 }
 
            almCfgOverVoltLNPriority OBJECT-TYPE
                SYNTAX DisplayString (SIZE (0..255))
                MAX-ACCESS read-only
                STATUS mandatory
                DESCRIPTION 
                    "Alarm Configuration - Over Voltage L-N - Priority"
                ::= { almCfgOverVoltLN 2 }
 
            almCfgOverVoltLNPkupStPnt OBJECT-TYPE
                SYNTAX DisplayString (SIZE (0..255))
                MAX-ACCESS read-only
                STATUS mandatory
                DESCRIPTION 
                    "Alarm Configuration - Over Voltage L-N - Pickup Setpoint (Volts)"
                ::= { almCfgOverVoltLN 3 }
 
            almCfgOverVoltLNPkupDly OBJECT-TYPE
                SYNTAX DisplayString (SIZE (0..255))
                MAX-ACCESS read-only
                STATUS mandatory
                DESCRIPTION 
                    "Alarm Configuration - Over Voltage L-N - Pickup Delay (Seconds)"
                ::= { almCfgOverVoltLN 4 }
 
            almCfgOverVoltLNDrpStPnt OBJECT-TYPE
                SYNTAX DisplayString (SIZE (0..255))
                MAX-ACCESS read-only
                STATUS mandatory
                DESCRIPTION 
                    "Alarm Configuration - Over Voltage L-N - Drop Out Setpoint (Volts)"
                ::= { almCfgOverVoltLN 5 }
 
            almCfgOverVoltLNDrpDly OBJECT-TYPE
                SYNTAX DisplayString (SIZE (0..255))
                MAX-ACCESS read-only
                STATUS mandatory
                DESCRIPTION 
                    "Alarm Configuration - Over Voltage L-N - Drop Out Delay (Seconds)"
                ::= { almCfgOverVoltLN 6 }
 
            almCfgOverVoltLNDOs   OBJECT-TYPE
                SYNTAX DisplayString (SIZE (0..255))
                MAX-ACCESS read-only
                STATUS mandatory
                DESCRIPTION 
                    "Alarm Configuration - Over Voltage L-N - Associated Digital Outputs. Bitmap of digital outputs to associate with this alarm.
Bitmap is right-justified with the least significant bit associated with digital output ID of 1."
                ::= { almCfgOverVoltLN 7 }
 
 
        almCfgUnderVoltLN OBJECT IDENTIFIER ::= { oneSecStdAlarmConfiguration 8 }
 
            almCfgUnderVoltLNEnableDisable OBJECT-TYPE
                SYNTAX DisplayString (SIZE (0..255))
                MAX-ACCESS read-only
                STATUS mandatory
                DESCRIPTION 
                    "Alarm Configuration - Under Voltage L-N - Enable / Disable"
                ::= { almCfgUnderVoltLN 1 }
 
            almCfgUnderVoltLNPriority OBJECT-TYPE
                SYNTAX DisplayString (SIZE (0..255))
                MAX-ACCESS read-only
                STATUS mandatory
                DESCRIPTION 
                    "Alarm Configuration - Under Voltage L-N - Priority"
                ::= { almCfgUnderVoltLN 2 }
 
            almCfgUnderVoltLNPkupStPnt OBJECT-TYPE
                SYNTAX DisplayString (SIZE (0..255))
                MAX-ACCESS read-only
                STATUS mandatory
                DESCRIPTION 
                    "Alarm Configuration - Under Voltage L-N - Pickup Setpoint (Volts)"
                ::= { almCfgUnderVoltLN 3 }
 
            almCfgUnderVoltLNPkupDly OBJECT-TYPE
                SYNTAX DisplayString (SIZE (0..255))
                MAX-ACCESS read-only
                STATUS mandatory
                DESCRIPTION 
                    "Alarm Configuration - Under Voltage L-N - Pickup Delay (Seconds)"
                ::= { almCfgUnderVoltLN 4 }
 
            almCfgUnderVoltLNDrpStPnt OBJECT-TYPE
                SYNTAX DisplayString (SIZE (0..255))
                MAX-ACCESS read-only
                STATUS mandatory
                DESCRIPTION 
                    "Alarm Configuration - Under Voltage L-N - Drop Out Setpoint (Volts)"
                ::= { almCfgUnderVoltLN 5 }
 
            almCfgUnderVoltLNDrpDly OBJECT-TYPE
                SYNTAX DisplayString (SIZE (0..255))
                MAX-ACCESS read-only
                STATUS mandatory
                DESCRIPTION 
                    "Alarm Configuration - Under Voltage L-N - Drop Out Delay (Seconds)"
                ::= { almCfgUnderVoltLN 6 }
 
            almCfgUnderVoltLNDOs   OBJECT-TYPE
                SYNTAX DisplayString (SIZE (0..255))
                MAX-ACCESS read-only
                STATUS mandatory
                DESCRIPTION 
                    "Alarm Configuration - Under Voltage L-N - Associated Digital Outputs. Bitmap of digital outputs to associate with this alarm.
Bitmap is right-justified with the least significant bit associated with digital output ID of 1."
                ::= { almCfgUnderVoltLN 7 }
 
 
        almCfgOverPwrAct OBJECT IDENTIFIER ::= { oneSecStdAlarmConfiguration 9 }
 
            almCfgOverPwrActEnableDisable OBJECT-TYPE
                SYNTAX DisplayString (SIZE (0..255))
                MAX-ACCESS read-only
                STATUS mandatory
                DESCRIPTION 
                    "Alarm Configuration - Over Power Active - Enable / Disable"
                ::= { almCfgOverPwrAct 1 }
 
            almCfgOverPwrActPriority OBJECT-TYPE
                SYNTAX DisplayString (SIZE (0..255))
                MAX-ACCESS read-only
                STATUS mandatory
                DESCRIPTION 
                    "Alarm Configuration - Over Power Active - Priority"
                ::= { almCfgOverPwrAct 2 }
 
            almCfgOverPwrActPkupStPnt OBJECT-TYPE
                SYNTAX DisplayString (SIZE (0..255))
                MAX-ACCESS read-only
                STATUS mandatory
                DESCRIPTION 
                    "Alarm Configuration - Over Power Active - Pickup Setpoint (kW)"
                ::= { almCfgOverPwrAct 3 }
 
            almCfgOverPwrActPkupDly OBJECT-TYPE
                SYNTAX DisplayString (SIZE (0..255))
                MAX-ACCESS read-only
                STATUS mandatory
                DESCRIPTION 
                    "Alarm Configuration - Over Power Active - Pickup Delay (Seconds)"
                ::= { almCfgOverPwrAct 4 }
 
            almCfgOverPwrActDrpStPnt OBJECT-TYPE
                SYNTAX DisplayString (SIZE (0..255))
                MAX-ACCESS read-only
                STATUS mandatory
                DESCRIPTION 
                    "Alarm Configuration - Over Power Active - Drop Out Setpoint (kW)"
                ::= { almCfgOverPwrAct 5 }
 
            almCfgOverPwrActDrpDly OBJECT-TYPE
                SYNTAX DisplayString (SIZE (0..255))
                MAX-ACCESS read-only
                STATUS mandatory
                DESCRIPTION 
                    "Alarm Configuration - Over Power Active - Drop Out Delay (Seconds)"
                ::= { almCfgOverPwrAct 6 }
 
            almCfgOverPwrActDOs   OBJECT-TYPE
                SYNTAX DisplayString (SIZE (0..255))
                MAX-ACCESS read-only
                STATUS mandatory
                DESCRIPTION 
                    "Alarm Configuration - Over Power Active - Associated Digital Outputs. Bitmap of digital outputs to associate with this alarm.
Bitmap is right-justified with the least significant bit associated with digital output ID of 1."
                ::= { almCfgOverPwrAct 7 }
 
 
        almCfgOverPwrReact OBJECT IDENTIFIER ::= { oneSecStdAlarmConfiguration 10 }
 
            almCfgOverPwrReactEnableDisable OBJECT-TYPE
                SYNTAX DisplayString (SIZE (0..255))
                MAX-ACCESS read-only
                STATUS mandatory
                DESCRIPTION 
                    "Alarm Configuration - Over Power Reactive - Enable / Disable"
                ::= { almCfgOverPwrReact 1 }
 
            almCfgOverPwrReactPriority OBJECT-TYPE
                SYNTAX DisplayString (SIZE (0..255))
                MAX-ACCESS read-only
                STATUS mandatory
                DESCRIPTION 
                    "Alarm Configuration - Over Power Reactive - Priority"
                ::= { almCfgOverPwrReact 2 }
 
            almCfgOverPwrReactPkupStPnt OBJECT-TYPE
                SYNTAX DisplayString (SIZE (0..255))
                MAX-ACCESS read-only
                STATUS mandatory
                DESCRIPTION 
                    "Alarm Configuration - Over Power Reactive - Pickup Setpoint (kVAR)"
                ::= { almCfgOverPwrReact 3 }
 
            almCfgOverPwrReactPkupDly OBJECT-TYPE
                SYNTAX DisplayString (SIZE (0..255))
                MAX-ACCESS read-only
                STATUS mandatory
                DESCRIPTION 
                    "Alarm Configuration - Over Power Reactive - Pickup Delay (Seconds)"
                ::= { almCfgOverPwrReact 4 }
 
            almCfgOverPwrReactDrpStPnt OBJECT-TYPE
                SYNTAX DisplayString (SIZE (0..255))
                MAX-ACCESS read-only
                STATUS mandatory
                DESCRIPTION 
                    "Alarm Configuration - Over Power Reactive - Drop Out Setpoint (kVAR)"
                ::= { almCfgOverPwrReact 5 }
 
            almCfgOverPwrReactDrpDly OBJECT-TYPE
                SYNTAX DisplayString (SIZE (0..255))
                MAX-ACCESS read-only
                STATUS mandatory
                DESCRIPTION 
                    "Alarm Configuration - Over Power Reactive - Drop Out Delay (Seconds)"
                ::= { almCfgOverPwrReact 6 }
 
            almCfgOverPwrReactDOs   OBJECT-TYPE
                SYNTAX DisplayString (SIZE (0..255))
                MAX-ACCESS read-only
                STATUS mandatory
                DESCRIPTION 
                    "Alarm Configuration - Over Power Reactive - Associated Digital Outputs. Bitmap of digital outputs to associate with this alarm.
Bitmap is right-justified with the least significant bit associated with digital output ID of 1."
                ::= { almCfgOverPwrReact 7 }
 
 
        almCfgOverPwrApprnt OBJECT IDENTIFIER ::= { oneSecStdAlarmConfiguration 11 }
 
            almCfgOverPwrApprntEnableDisable OBJECT-TYPE
                SYNTAX DisplayString (SIZE (0..255))
                MAX-ACCESS read-only
                STATUS mandatory
                DESCRIPTION 
                    "Alarm Configuration - Over Power Apparent - Enable / Disable"
                ::= { almCfgOverPwrApprnt 1 }
 
            almCfgOverPwrApprntPriority OBJECT-TYPE
                SYNTAX DisplayString (SIZE (0..255))
                MAX-ACCESS read-only
                STATUS mandatory
                DESCRIPTION 
                    "Alarm Configuration - Over Power Apparent - Priority"
                ::= { almCfgOverPwrApprnt 2 }
 
            almCfgOverPwrApprntPkupStPnt OBJECT-TYPE
                SYNTAX DisplayString (SIZE (0..255))
                MAX-ACCESS read-only
                STATUS mandatory
                DESCRIPTION 
                    "Alarm Configuration - Over Power Apparent - Pickup Setpoint (kVA)"
                ::= { almCfgOverPwrApprnt 3 }
 
            almCfgOverPwrApprntPkupDly OBJECT-TYPE
                SYNTAX DisplayString (SIZE (0..255))
                MAX-ACCESS read-only
                STATUS mandatory
                DESCRIPTION 
                    "Alarm Configuration - Over Power Apparent - Pickup Delay (Seconds)"
                ::= { almCfgOverPwrApprnt 4 }
 
            almCfgOverPwrApprntDrpStPnt OBJECT-TYPE
                SYNTAX DisplayString (SIZE (0..255))
                MAX-ACCESS read-only
                STATUS mandatory
                DESCRIPTION 
                    "Alarm Configuration - Over Power Apparent - Drop Out Setpoint (kVA)"
                ::= { almCfgOverPwrApprnt 5 }
 
            almCfgOverPwrApprntDrpDly OBJECT-TYPE
                SYNTAX DisplayString (SIZE (0..255))
                MAX-ACCESS read-only
                STATUS mandatory
                DESCRIPTION 
                    "Alarm Configuration - Over Power Apparent - Drop Out Delay (Seconds)"
                ::= { almCfgOverPwrApprnt 6 }
 
            almCfgOverPwrApprntDOs   OBJECT-TYPE
                SYNTAX DisplayString (SIZE (0..255))
                MAX-ACCESS read-only
                STATUS mandatory
                DESCRIPTION 
                    "Alarm Configuration - Over Power Apparent - Associated Digital Outputs. Bitmap of digital outputs to associate with this alarm.
Bitmap is right-justified with the least significant bit associated with digital output ID of 1."
                ::= { almCfgOverPwrApprnt 7 }
 
 
        almCfgLeadPFTrue OBJECT IDENTIFIER ::= { oneSecStdAlarmConfiguration 12 }
 
            almCfgLeadPFTrueEnableDisable OBJECT-TYPE
                SYNTAX DisplayString (SIZE (0..255))
                MAX-ACCESS read-only
                STATUS mandatory
                DESCRIPTION 
                    "Alarm Configuration - Leading Power Factor True - Enable / Disable"
                ::= { almCfgLeadPFTrue 1 }
 
            almCfgLeadPFTruePriority OBJECT-TYPE
                SYNTAX DisplayString (SIZE (0..255))
                MAX-ACCESS read-only
                STATUS mandatory
                DESCRIPTION 
                    "Alarm Configuration - Leading Power Factor True - Priority"
                ::= { almCfgLeadPFTrue 2 }
 
            almCfgLeadPFTruePkupStPnt OBJECT-TYPE
                SYNTAX DisplayString (SIZE (0..255))
                MAX-ACCESS read-only
                STATUS mandatory
                DESCRIPTION 
                    "Alarm Configuration - Leading Power Factor True - Pickup Setpoint"
                ::= { almCfgLeadPFTrue 3 }
 
            almCfgLeadPFTruePkupStPntLeadOrLag OBJECT-TYPE
                SYNTAX DisplayString (SIZE (0..255))
                MAX-ACCESS read-only
                STATUS mandatory
                DESCRIPTION 
                    "Alarm Configuration - Leading Power Factor True - Pickup Setpoint (Lead or Lag)"
                ::= { almCfgLeadPFTrue 4 }
 
            almCfgLeadPFTruePkupDly OBJECT-TYPE
                SYNTAX DisplayString (SIZE (0..255))
                MAX-ACCESS read-only
                STATUS mandatory
                DESCRIPTION 
                    "Alarm Configuration - Leading Power Factor True - Pickup Delay (Seconds)"
                ::= { almCfgLeadPFTrue 5 }
 
            almCfgLeadPFTrueDrpStPnt OBJECT-TYPE
                SYNTAX DisplayString (SIZE (0..255))
                MAX-ACCESS read-only
                STATUS mandatory
                DESCRIPTION 
                    "Alarm Configuration - Leading Power Factor True - Drop Out Setpoint"
                ::= { almCfgLeadPFTrue 6 }
 
            almCfgLeadPFTrueDrpDly OBJECT-TYPE
                SYNTAX DisplayString (SIZE (0..255))
                MAX-ACCESS read-only
                STATUS mandatory
                DESCRIPTION 
                    "Alarm Configuration - Leading Power Factor True - Drop Out Delay (Seconds)"
                ::= { almCfgLeadPFTrue 7 }
 
            almCfgLeadPFTrueDOs   OBJECT-TYPE
                SYNTAX DisplayString (SIZE (0..255))
                MAX-ACCESS read-only
                STATUS mandatory
                DESCRIPTION 
                    "Alarm Configuration - Leading Power Factor True - Associated Digital Outputs. Bitmap of digital outputs to associate with this alarm.
Bitmap is right-justified with the least significant bit associated with digital output ID of 1."
                ::= { almCfgLeadPFTrue 8 }
 
 
        almCfgLagPFTrue OBJECT IDENTIFIER ::= { oneSecStdAlarmConfiguration 13 }
 
            almCfgLagPFTrueEnableDisable OBJECT-TYPE
                SYNTAX DisplayString (SIZE (0..255))
                MAX-ACCESS read-only
                STATUS mandatory
                DESCRIPTION 
                    "Alarm Configuration - Lagging Power Factor True - Enable / Disable"
                ::= { almCfgLagPFTrue 1 }
 
            almCfgLagPFTruePriority OBJECT-TYPE
                SYNTAX DisplayString (SIZE (0..255))
                MAX-ACCESS read-only
                STATUS mandatory
                DESCRIPTION 
                    "Alarm Configuration - Lagging Power Factor True - Priority"
                ::= { almCfgLagPFTrue 2 }
 
            almCfgLagPFTruePkupStPnt OBJECT-TYPE
                SYNTAX DisplayString (SIZE (0..255))
                MAX-ACCESS read-only
                STATUS mandatory
                DESCRIPTION 
                    "Alarm Configuration - Lagging Power Factor True - Pickup Setpoint"
                ::= { almCfgLagPFTrue 3 }
 
            almCfgLagPFTruePkupStPntLeadOrLag OBJECT-TYPE
                SYNTAX DisplayString (SIZE (0..255))
                MAX-ACCESS read-only
                STATUS mandatory
                DESCRIPTION 
                    "Alarm Configuration - Lagging Power Factor True - Pickup Setpoint (Lead or Lag)"
                ::= { almCfgLagPFTrue 4 }
 
            almCfgLagPFTruePkupDly OBJECT-TYPE
                SYNTAX DisplayString (SIZE (0..255))
                MAX-ACCESS read-only
                STATUS mandatory
                DESCRIPTION 
                    "Alarm Configuration - Lagging Power Factor True - Pickup Delay (Seconds)"
                ::= { almCfgLagPFTrue 5 }
 
            almCfgLagPFTrueDrpStPnt OBJECT-TYPE
                SYNTAX DisplayString (SIZE (0..255))
                MAX-ACCESS read-only
                STATUS mandatory
                DESCRIPTION 
                    "Alarm Configuration - Lagging Power Factor True - Drop Out Setpoint"
                ::= { almCfgLagPFTrue 6 }
 
            almCfgLagPFTrueDrpDly OBJECT-TYPE
                SYNTAX DisplayString (SIZE (0..255))
                MAX-ACCESS read-only
                STATUS mandatory
                DESCRIPTION 
                    "Alarm Configuration - Lagging Power Factor True - Drop Out Delay (Seconds)"
                ::= { almCfgLagPFTrue 7 }
 
            almCfgLagPFTrueDOs   OBJECT-TYPE
                SYNTAX DisplayString (SIZE (0..255))
                MAX-ACCESS read-only
                STATUS mandatory
                DESCRIPTION 
                    "Alarm Configuration - Lagging Power Factor True - Associated Digital Outputs. Bitmap of digital outputs to associate with this alarm.
Bitmap is right-justified with the least significant bit associated with digital output ID of 1."
                ::= { almCfgLagPFTrue 8 }
 
 
        almCfgLeadPFDisp OBJECT IDENTIFIER ::= { oneSecStdAlarmConfiguration 14 }
 
            almCfgLeadPFDispEnableDisable OBJECT-TYPE
                SYNTAX DisplayString (SIZE (0..255))
                MAX-ACCESS read-only
                STATUS mandatory
                DESCRIPTION 
                    "Alarm Configuration - Leading Power Factor Disp - Enable / Disable"
                ::= { almCfgLeadPFDisp 1 }
 
            almCfgLeadPFDispPriority OBJECT-TYPE
                SYNTAX DisplayString (SIZE (0..255))
                MAX-ACCESS read-only
                STATUS mandatory
                DESCRIPTION 
                    "Alarm Configuration - Leading Power Factor Disp - Priority"
                ::= { almCfgLeadPFDisp 2 }
 
            almCfgLeadPFDispPkupStPnt OBJECT-TYPE
                SYNTAX DisplayString (SIZE (0..255))
                MAX-ACCESS read-only
                STATUS mandatory
                DESCRIPTION 
                    "Alarm Configuration - Leading Power Factor Disp - Pickup Setpoint"
                ::= { almCfgLeadPFDisp 3 }
 
            almCfgLeadPFDispPkupStPntLeadOrLag OBJECT-TYPE
                SYNTAX DisplayString (SIZE (0..255))
                MAX-ACCESS read-only
                STATUS mandatory
                DESCRIPTION 
                    "Alarm Configuration - Leading Power Factor Disp - Pickup Setpoint (Lead or Lag)"
                ::= { almCfgLeadPFDisp 4 }
 
            almCfgLeadPFDispPkupDly OBJECT-TYPE
                SYNTAX DisplayString (SIZE (0..255))
                MAX-ACCESS read-only
                STATUS mandatory
                DESCRIPTION 
                    "Alarm Configuration - Leading Power Factor Disp - Pickup Delay (Seconds)"
                ::= { almCfgLeadPFDisp 5 }
 
            almCfgLeadPFDispDrpStPnt OBJECT-TYPE
                SYNTAX DisplayString (SIZE (0..255))
                MAX-ACCESS read-only
                STATUS mandatory
                DESCRIPTION 
                    "Alarm Configuration - Leading Power Factor Disp - Drop Out Setpoint"
                ::= { almCfgLeadPFDisp 6 }
 
            almCfgLeadPFDispDrpDly OBJECT-TYPE
                SYNTAX DisplayString (SIZE (0..255))
                MAX-ACCESS read-only
                STATUS mandatory
                DESCRIPTION 
                    "Alarm Configuration - Leading Power Factor Disp - Drop Out Delay (Seconds)"
                ::= { almCfgLeadPFDisp 7 }
 
            almCfgLeadPFDispDOs   OBJECT-TYPE
                SYNTAX DisplayString (SIZE (0..255))
                MAX-ACCESS read-only
                STATUS mandatory
                DESCRIPTION 
                    "Alarm Configuration - Leading Power Factor Disp - Associated Digital Outputs. Bitmap of digital outputs to associate with this alarm.
Bitmap is right-justified with the least significant bit associated with digital output ID of 1."
                ::= { almCfgLeadPFDisp 8 }
 
 
        almCfgLagPFDisp OBJECT IDENTIFIER ::= { oneSecStdAlarmConfiguration 15 }
 
            almCfgLagPFDispEnableDisable OBJECT-TYPE
                SYNTAX DisplayString (SIZE (0..255))
                MAX-ACCESS read-only
                STATUS mandatory
                DESCRIPTION 
                    "Alarm Configuration - Lagging Power Factor Disp - Enable / Disable"
                ::= { almCfgLagPFDisp 1 }
 
            almCfgLagPFDispPriority OBJECT-TYPE
                SYNTAX DisplayString (SIZE (0..255))
                MAX-ACCESS read-only
                STATUS mandatory
                DESCRIPTION 
                    "Alarm Configuration - Lagging Power Factor Disp - Priority"
                ::= { almCfgLagPFDisp 2 }
 
            almCfgLagPFDispPkupStPnt OBJECT-TYPE
                SYNTAX DisplayString (SIZE (0..255))
                MAX-ACCESS read-only
                STATUS mandatory
                DESCRIPTION 
                    "Alarm Configuration - Lagging Power Factor Disp - Pickup Setpoint"
                ::= { almCfgLagPFDisp 3 }
 
            almCfgLagPFDispPkupStPntLeadOrLag OBJECT-TYPE
                SYNTAX DisplayString (SIZE (0..255))
                MAX-ACCESS read-only
                STATUS mandatory
                DESCRIPTION 
                    "Alarm Configuration - Lagging Power Factor Disp - Pickup Setpoint (Lead or Lag)"
                ::= { almCfgLagPFDisp 4 }
 
            almCfgLagPFDispPkupDly OBJECT-TYPE
                SYNTAX DisplayString (SIZE (0..255))
                MAX-ACCESS read-only
                STATUS mandatory
                DESCRIPTION 
                    "Alarm Configuration - Lagging Power Factor Disp - Pickup Delay (Seconds)"
                ::= { almCfgLagPFDisp 5 }
 
            almCfgLagPFDispDrpStPnt OBJECT-TYPE
                SYNTAX DisplayString (SIZE (0..255))
                MAX-ACCESS read-only
                STATUS mandatory
                DESCRIPTION 
                    "Alarm Configuration - Lagging Power Factor Disp - Drop Out Setpoint"
                ::= { almCfgLagPFDisp 6 }
 
            almCfgLagPFDispDrpDly OBJECT-TYPE
                SYNTAX DisplayString (SIZE (0..255))
                MAX-ACCESS read-only
                STATUS mandatory
                DESCRIPTION 
                    "Alarm Configuration - Lagging Power Factor Disp - Drop Out Delay (Seconds)"
                ::= { almCfgLagPFDisp 7 }
 
            almCfgLagPFDispDOs   OBJECT-TYPE
                SYNTAX DisplayString (SIZE (0..255))
                MAX-ACCESS read-only
                STATUS mandatory
                DESCRIPTION 
                    "Alarm Configuration - Lagging Power Factor Disp - Associated Digital Outputs. Bitmap of digital outputs to associate with this alarm.
Bitmap is right-justified with the least significant bit associated with digital output ID of 1."
                ::= { almCfgLagPFDisp 8 }
 
 
        almCfgOverDmdActPwrPres OBJECT IDENTIFIER ::= { oneSecStdAlarmConfiguration 16 }
 
            almCfgOverDmdActPwrPresEnableDisable OBJECT-TYPE
                SYNTAX DisplayString (SIZE (0..255))
                MAX-ACCESS read-only
                STATUS mandatory
                DESCRIPTION 
                    "Alarm Configuration - Over Demand Active Power Present - Enable / Disable"
                ::= { almCfgOverDmdActPwrPres 1 }
 
            almCfgOverDmdActPwrPresPriority OBJECT-TYPE
                SYNTAX DisplayString (SIZE (0..255))
                MAX-ACCESS read-only
                STATUS mandatory
                DESCRIPTION 
                    "Alarm Configuration - Over Demand Active Power Present - Priority"
                ::= { almCfgOverDmdActPwrPres 2 }
 
            almCfgOverDmdActPwrPresPkupStPnt OBJECT-TYPE
                SYNTAX DisplayString (SIZE (0..255))
                MAX-ACCESS read-only
                STATUS mandatory
                DESCRIPTION 
                    "Alarm Configuration - Over Demand Active Power Present - Pickup Setpoint (kW)"
                ::= { almCfgOverDmdActPwrPres 3 }
 
            almCfgOverDmdActPwrPresPkupDly OBJECT-TYPE
                SYNTAX DisplayString (SIZE (0..255))
                MAX-ACCESS read-only
                STATUS mandatory
                DESCRIPTION 
                    "Alarm Configuration - Over Demand Active Power Present - Pickup Delay (Seconds)"
                ::= { almCfgOverDmdActPwrPres 4 }
 
            almCfgOverDmdActPwrPresDrpStPnt OBJECT-TYPE
                SYNTAX DisplayString (SIZE (0..255))
                MAX-ACCESS read-only
                STATUS mandatory
                DESCRIPTION 
                    "Alarm Configuration - Over Demand Active Power Present - Drop Out Setpoint (kW)"
                ::= { almCfgOverDmdActPwrPres 5 }
 
            almCfgOverDmdActPwrPresDrpDly OBJECT-TYPE
                SYNTAX DisplayString (SIZE (0..255))
                MAX-ACCESS read-only
                STATUS mandatory
                DESCRIPTION 
                    "Alarm Configuration - Over Demand Active Power Present - Drop Out Delay (Seconds)"
                ::= { almCfgOverDmdActPwrPres 6 }
 
            almCfgOverDmdActPwrPresDOs   OBJECT-TYPE
                SYNTAX DisplayString (SIZE (0..255))
                MAX-ACCESS read-only
                STATUS mandatory
                DESCRIPTION 
                    "Alarm Configuration - Over Demand Active Power Present - Associated Digital Outputs. Bitmap of digital outputs to associate with this alarm.
Bitmap is right-justified with the least significant bit associated with digital output ID of 1."
                ::= { almCfgOverDmdActPwrPres 7 }
 
 
        almCfgOverDmdActPwrLast OBJECT IDENTIFIER ::= { oneSecStdAlarmConfiguration 17 }
 
            almCfgOverDmdActPwrLastEnableDisable OBJECT-TYPE
                SYNTAX DisplayString (SIZE (0..255))
                MAX-ACCESS read-only
                STATUS mandatory
                DESCRIPTION 
                    "Alarm Configuration - Over Demand Active Power Last - Enable / Disable"
                ::= { almCfgOverDmdActPwrLast 1 }
 
            almCfgOverDmdActPwrLastPriority OBJECT-TYPE
                SYNTAX DisplayString (SIZE (0..255))
                MAX-ACCESS read-only
                STATUS mandatory
                DESCRIPTION 
                    "Alarm Configuration - Over Demand Active Power Last - Priority"
                ::= { almCfgOverDmdActPwrLast 2 }
 
            almCfgOverDmdActPwrLastPkupStPnt OBJECT-TYPE
                SYNTAX DisplayString (SIZE (0..255))
                MAX-ACCESS read-only
                STATUS mandatory
                DESCRIPTION 
                    "Alarm Configuration - Over Demand Active Power Last - Pickup Setpoint (kW)"
                ::= { almCfgOverDmdActPwrLast 3 }
 
            almCfgOverDmdActPwrLastPkupDly OBJECT-TYPE
                SYNTAX DisplayString (SIZE (0..255))
                MAX-ACCESS read-only
                STATUS mandatory
                DESCRIPTION 
                    "Alarm Configuration - Over Demand Active Power Last - Pickup Delay (Seconds)"
                ::= { almCfgOverDmdActPwrLast 4 }
 
            almCfgOverDmdActPwrLastDrpStPnt OBJECT-TYPE
                SYNTAX DisplayString (SIZE (0..255))
                MAX-ACCESS read-only
                STATUS mandatory
                DESCRIPTION 
                    "Alarm Configuration - Over Demand Active Power Last - Drop Out Setpoint (kW)"
                ::= { almCfgOverDmdActPwrLast 5 }
 
            almCfgOverDmdActPwrLastDrpDly OBJECT-TYPE
                SYNTAX DisplayString (SIZE (0..255))
                MAX-ACCESS read-only
                STATUS mandatory
                DESCRIPTION 
                    "Alarm Configuration - Over Demand Active Power Last - Drop Out Delay (Seconds)"
                ::= { almCfgOverDmdActPwrLast 6 }
 
            almCfgOverDmdActPwrLastDOs   OBJECT-TYPE
                SYNTAX DisplayString (SIZE (0..255))
                MAX-ACCESS read-only
                STATUS mandatory
                DESCRIPTION 
                    "Alarm Configuration - Over Demand Active Power Last - Associated Digital Outputs. Bitmap of digital outputs to associate with this alarm.
Bitmap is right-justified with the least significant bit associated with digital output ID of 1."
                ::= { almCfgOverDmdActPwrLast 7 }
 
 
        almCfgOverDmdActPwrPred OBJECT IDENTIFIER ::= { oneSecStdAlarmConfiguration 18 }
 
            almCfgOverDmdActPwrPredEnableDisable OBJECT-TYPE
                SYNTAX DisplayString (SIZE (0..255))
                MAX-ACCESS read-only
                STATUS mandatory
                DESCRIPTION 
                    "Alarm Configuration - Over Demand Active Power Predicted - Enable / Disable"
                ::= { almCfgOverDmdActPwrPred 1 }
 
            almCfgOverDmdActPwrPredPriority OBJECT-TYPE
                SYNTAX DisplayString (SIZE (0..255))
                MAX-ACCESS read-only
                STATUS mandatory
                DESCRIPTION 
                    "Alarm Configuration - Over Demand Active Power Predicted - Priority"
                ::= { almCfgOverDmdActPwrPred 2 }
 
            almCfgOverDmdActPwrPredPkupStPnt OBJECT-TYPE
                SYNTAX DisplayString (SIZE (0..255))
                MAX-ACCESS read-only
                STATUS mandatory
                DESCRIPTION 
                    "Alarm Configuration - Over Demand Active Power Predicted - Pickup Setpoint (kW)"
                ::= { almCfgOverDmdActPwrPred 3 }
 
            almCfgOverDmdActPwrPredPkupDly OBJECT-TYPE
                SYNTAX DisplayString (SIZE (0..255))
                MAX-ACCESS read-only
                STATUS mandatory
                DESCRIPTION 
                    "Alarm Configuration - Over Demand Active Power Predicted - Pickup Delay (Seconds)"
                ::= { almCfgOverDmdActPwrPred 4 }
 
            almCfgOverDmdActPwrPredDrpStPnt OBJECT-TYPE
                SYNTAX DisplayString (SIZE (0..255))
                MAX-ACCESS read-only
                STATUS mandatory
                DESCRIPTION 
                    "Alarm Configuration - Over Demand Active Power Predicted - Drop Out Setpoint (kW)"
                ::= { almCfgOverDmdActPwrPred 5 }
 
            almCfgOverDmdActPwrPredDrpDly OBJECT-TYPE
                SYNTAX DisplayString (SIZE (0..255))
                MAX-ACCESS read-only
                STATUS mandatory
                DESCRIPTION 
                    "Alarm Configuration - Over Demand Active Power Predicted - Drop Out Delay (Seconds)"
                ::= { almCfgOverDmdActPwrPred 6 }
 
            almCfgOverDmdActPwrPredDOs   OBJECT-TYPE
                SYNTAX DisplayString (SIZE (0..255))
                MAX-ACCESS read-only
                STATUS mandatory
                DESCRIPTION 
                    "Alarm Configuration - Over Demand Active Power Predicted - Associated Digital Outputs. Bitmap of digital outputs to associate with this alarm.
Bitmap is right-justified with the least significant bit associated with digital output ID of 1."
                ::= { almCfgOverDmdActPwrPred 7 }
 
 
        almCfgOverDmdReactPwrPres OBJECT IDENTIFIER ::= { oneSecStdAlarmConfiguration 19 }
 
            almCfgOverDmdReactPwrPresEnableDisable OBJECT-TYPE
                SYNTAX DisplayString (SIZE (0..255))
                MAX-ACCESS read-only
                STATUS mandatory
                DESCRIPTION 
                    "Alarm Configuration - Over Demand Reactive Power Present - Enable / Disable"
                ::= { almCfgOverDmdReactPwrPres 1 }
 
            almCfgOverDmdReactPwrPresPriority OBJECT-TYPE
                SYNTAX DisplayString (SIZE (0..255))
                MAX-ACCESS read-only
                STATUS mandatory
                DESCRIPTION 
                    "Alarm Configuration - Over Demand Reactive Power Present - Priority"
                ::= { almCfgOverDmdReactPwrPres 2 }
 
            almCfgOverDmdReactPwrPresPkupStPnt OBJECT-TYPE
                SYNTAX DisplayString (SIZE (0..255))
                MAX-ACCESS read-only
                STATUS mandatory
                DESCRIPTION 
                    "Alarm Configuration - Over Demand Reactive Power Present - Pickup Setpoint (kVAR)"
                ::= { almCfgOverDmdReactPwrPres 3 }
 
            almCfgOverDmdReactPwrPresPkupDly OBJECT-TYPE
                SYNTAX DisplayString (SIZE (0..255))
                MAX-ACCESS read-only
                STATUS mandatory
                DESCRIPTION 
                    "Alarm Configuration - Over Demand Reactive Power Present - Pickup Delay (Seconds)"
                ::= { almCfgOverDmdReactPwrPres 4 }
 
            almCfgOverDmdReactPwrPresDrpStPnt OBJECT-TYPE
                SYNTAX DisplayString (SIZE (0..255))
                MAX-ACCESS read-only
                STATUS mandatory
                DESCRIPTION 
                    "Alarm Configuration - Over Demand Reactive Power Present - Drop Out Setpoint (kVAR)"
                ::= { almCfgOverDmdReactPwrPres 5 }
 
            almCfgOverDmdReactPwrPresDrpDly OBJECT-TYPE
                SYNTAX DisplayString (SIZE (0..255))
                MAX-ACCESS read-only
                STATUS mandatory
                DESCRIPTION 
                    "Alarm Configuration - Over Demand Reactive Power Present - Drop Out Delay (Seconds)"
                ::= { almCfgOverDmdReactPwrPres 6 }
 
            almCfgOverDmdReactPwrPresDOs   OBJECT-TYPE
                SYNTAX DisplayString (SIZE (0..255))
                MAX-ACCESS read-only
                STATUS mandatory
                DESCRIPTION 
                    "Alarm Configuration - Over Demand Reactive Power Present - Associated Digital Outputs. Bitmap of digital outputs to associate with this alarm.
Bitmap is right-justified with the least significant bit associated with digital output ID of 1."
                ::= { almCfgOverDmdReactPwrPres 7 }
 
 
        almCfgOverDmdReactPwrLast OBJECT IDENTIFIER ::= { oneSecStdAlarmConfiguration 20 }
 
            almCfgOverDmdReactPwrLastEnableDisable OBJECT-TYPE
                SYNTAX DisplayString (SIZE (0..255))
                MAX-ACCESS read-only
                STATUS mandatory
                DESCRIPTION 
                    "Alarm Configuration - Over Demand Reactive Power Last - Enable / Disable"
                ::= { almCfgOverDmdReactPwrLast 1 }
 
            almCfgOverDmdReactPwrLastPriority OBJECT-TYPE
                SYNTAX DisplayString (SIZE (0..255))
                MAX-ACCESS read-only
                STATUS mandatory
                DESCRIPTION 
                    "Alarm Configuration - Over Demand Reactive Power Last - Priority"
                ::= { almCfgOverDmdReactPwrLast 2 }
 
            almCfgOverDmdReactPwrLastPkupStPnt OBJECT-TYPE
                SYNTAX DisplayString (SIZE (0..255))
                MAX-ACCESS read-only
                STATUS mandatory
                DESCRIPTION 
                    "Alarm Configuration - Over Demand Reactive Power Last - Pickup Setpoint (kVAR)"
                ::= { almCfgOverDmdReactPwrLast 3 }
 
            almCfgOverDmdReactPwrLastPkupDly OBJECT-TYPE
                SYNTAX DisplayString (SIZE (0..255))
                MAX-ACCESS read-only
                STATUS mandatory
                DESCRIPTION 
                    "Alarm Configuration - Over Demand Reactive Power Last - Pickup Delay (Seconds)"
                ::= { almCfgOverDmdReactPwrLast 4 }
 
            almCfgOverDmdReactPwrLastDrpStPnt OBJECT-TYPE
                SYNTAX DisplayString (SIZE (0..255))
                MAX-ACCESS read-only
                STATUS mandatory
                DESCRIPTION 
                    "Alarm Configuration - Over Demand Reactive Power Last - Drop Out Setpoint (kVAR)"
                ::= { almCfgOverDmdReactPwrLast 5 }
 
            almCfgOverDmdReactPwrLastDrpDly OBJECT-TYPE
                SYNTAX DisplayString (SIZE (0..255))
                MAX-ACCESS read-only
                STATUS mandatory
                DESCRIPTION 
                    "Alarm Configuration - Over Demand Reactive Power Last - Drop Out Delay (Seconds)"
                ::= { almCfgOverDmdReactPwrLast 6 }
 
            almCfgOverDmdReactPwrLastDOs   OBJECT-TYPE
                SYNTAX DisplayString (SIZE (0..255))
                MAX-ACCESS read-only
                STATUS mandatory
                DESCRIPTION 
                    "Alarm Configuration - Over Demand Reactive Power Last - Associated Digital Outputs. Bitmap of digital outputs to associate with this alarm.
Bitmap is right-justified with the least significant bit associated with digital output ID of 1."
                ::= { almCfgOverDmdReactPwrLast 7 }
 
 
        almCfgOverDmdReactPwrPred OBJECT IDENTIFIER ::= { oneSecStdAlarmConfiguration 21 }
 
            almCfgOverDmdReactPwrPredEnableDisable OBJECT-TYPE
                SYNTAX DisplayString (SIZE (0..255))
                MAX-ACCESS read-only
                STATUS mandatory
                DESCRIPTION 
                    "Alarm Configuration - Over Demand Reactive Power Predicted - Enable / Disable"
                ::= { almCfgOverDmdReactPwrPred 1 }
 
            almCfgOverDmdReactPwrPredPriority OBJECT-TYPE
                SYNTAX DisplayString (SIZE (0..255))
                MAX-ACCESS read-only
                STATUS mandatory
                DESCRIPTION 
                    "Alarm Configuration - Over Demand Reactive Power Predicted - Priority"
                ::= { almCfgOverDmdReactPwrPred 2 }
 
            almCfgOverDmdReactPwrPredPkupStPnt OBJECT-TYPE
                SYNTAX DisplayString (SIZE (0..255))
                MAX-ACCESS read-only
                STATUS mandatory
                DESCRIPTION 
                    "Alarm Configuration - Over Demand Reactive Power Predicted - Pickup Setpoint (kVAR)"
                ::= { almCfgOverDmdReactPwrPred 3 }
 
            almCfgOverDmdReactPwrPredPkupDly OBJECT-TYPE
                SYNTAX DisplayString (SIZE (0..255))
                MAX-ACCESS read-only
                STATUS mandatory
                DESCRIPTION 
                    "Alarm Configuration - Over Demand Reactive Power Predicted - Pickup Delay (Seconds)"
                ::= { almCfgOverDmdReactPwrPred 4 }
 
            almCfgOverDmdReactPwrPredDrpStPnt OBJECT-TYPE
                SYNTAX DisplayString (SIZE (0..255))
                MAX-ACCESS read-only
                STATUS mandatory
                DESCRIPTION 
                    "Alarm Configuration - Over Demand Reactive Power Predicted - Drop Out Setpoint (kVAR)"
                ::= { almCfgOverDmdReactPwrPred 5 }
 
            almCfgOverDmdReactPwrPredDrpDly OBJECT-TYPE
                SYNTAX DisplayString (SIZE (0..255))
                MAX-ACCESS read-only
                STATUS mandatory
                DESCRIPTION 
                    "Alarm Configuration - Over Demand Reactive Power Predicted - Drop Out Delay (Seconds)"
                ::= { almCfgOverDmdReactPwrPred 6 }
 
            almCfgOverDmdReactPwrPredDOs   OBJECT-TYPE
                SYNTAX DisplayString (SIZE (0..255))
                MAX-ACCESS read-only
                STATUS mandatory
                DESCRIPTION 
                    "Alarm Configuration - Over Demand Reactive Power Predicted - Associated Digital Outputs. Bitmap of digital outputs to associate with this alarm.
Bitmap is right-justified with the least significant bit associated with digital output ID of 1."
                ::= { almCfgOverDmdReactPwrPred 7 }
 
 
        almCfgOverDmdApprntPwrPres OBJECT IDENTIFIER ::= { oneSecStdAlarmConfiguration 22 }
 
            almCfgOverDmdApprntPwrPresEnableDisable OBJECT-TYPE
                SYNTAX DisplayString (SIZE (0..255))
                MAX-ACCESS read-only
                STATUS mandatory
                DESCRIPTION 
                    "Alarm Configuration - Over Demand Apparent Power Present - Enable / Disable"
                ::= { almCfgOverDmdApprntPwrPres 1 }
 
            almCfgOverDmdApprntPwrPresPriority OBJECT-TYPE
                SYNTAX DisplayString (SIZE (0..255))
                MAX-ACCESS read-only
                STATUS mandatory
                DESCRIPTION 
                    "Alarm Configuration - Over Demand Apparent Power Present - Priority"
                ::= { almCfgOverDmdApprntPwrPres 2 }
 
            almCfgOverDmdApprntPwrPresPkupStPnt OBJECT-TYPE
                SYNTAX DisplayString (SIZE (0..255))
                MAX-ACCESS read-only
                STATUS mandatory
                DESCRIPTION 
                    "Alarm Configuration - Over Demand Apparent Power Present - Pickup Setpoint (kVA)"
                ::= { almCfgOverDmdApprntPwrPres 3 }
 
            almCfgOverDmdApprntPwrPresPkupDly OBJECT-TYPE
                SYNTAX DisplayString (SIZE (0..255))
                MAX-ACCESS read-only
                STATUS mandatory
                DESCRIPTION 
                    "Alarm Configuration - Over Demand Apparent Power Present - Pickup Delay (Seconds)"
                ::= { almCfgOverDmdApprntPwrPres 4 }
 
            almCfgOverDmdApprntPwrPresDrpStPnt OBJECT-TYPE
                SYNTAX DisplayString (SIZE (0..255))
                MAX-ACCESS read-only
                STATUS mandatory
                DESCRIPTION 
                    "Alarm Configuration - Over Demand Apparent Power Present - Drop Out Setpoint (kVA)"
                ::= { almCfgOverDmdApprntPwrPres 5 }
 
            almCfgOverDmdApprntPwrPresDrpDly OBJECT-TYPE
                SYNTAX DisplayString (SIZE (0..255))
                MAX-ACCESS read-only
                STATUS mandatory
                DESCRIPTION 
                    "Alarm Configuration - Over Demand Apparent Power Present - Drop Out Delay (Seconds)"
                ::= { almCfgOverDmdApprntPwrPres 6 }
 
            almCfgOverDmdApprntPwrPresDOs   OBJECT-TYPE
                SYNTAX DisplayString (SIZE (0..255))
                MAX-ACCESS read-only
                STATUS mandatory
                DESCRIPTION 
                    "Alarm Configuration - Over Demand Apparent Power Present - Associated Digital Outputs. Bitmap of digital outputs to associate with this alarm.
Bitmap is right-justified with the least significant bit associated with digital output ID of 1."
                ::= { almCfgOverDmdApprntPwrPres 7 }
 
 
        almCfgOverDmdApprntPwrLast OBJECT IDENTIFIER ::= { oneSecStdAlarmConfiguration 23 }
 
            almCfgOverDmdApprntPwrLastEnableDisable OBJECT-TYPE
                SYNTAX DisplayString (SIZE (0..255))
                MAX-ACCESS read-only
                STATUS mandatory
                DESCRIPTION 
                    "Alarm Configuration - Over Demand Apparent Power Last - Enable / Disable"
                ::= { almCfgOverDmdApprntPwrLast 1 }
 
            almCfgOverDmdApprntPwrLastPriority OBJECT-TYPE
                SYNTAX DisplayString (SIZE (0..255))
                MAX-ACCESS read-only
                STATUS mandatory
                DESCRIPTION 
                    "Alarm Configuration - Over Demand Apparent Power Last - Priority"
                ::= { almCfgOverDmdApprntPwrLast 2 }
 
            almCfgOverDmdApprntPwrLastPkupStPnt OBJECT-TYPE
                SYNTAX DisplayString (SIZE (0..255))
                MAX-ACCESS read-only
                STATUS mandatory
                DESCRIPTION 
                    "Alarm Configuration - Over Demand Apparent Power Last - Pickup Setpoint (kVA)"
                ::= { almCfgOverDmdApprntPwrLast 3 }
 
            almCfgOverDmdApprntPwrLastPkupDly OBJECT-TYPE
                SYNTAX DisplayString (SIZE (0..255))
                MAX-ACCESS read-only
                STATUS mandatory
                DESCRIPTION 
                    "Alarm Configuration - Over Demand Apparent Power Last - Pickup Delay (Seconds)"
                ::= { almCfgOverDmdApprntPwrLast 4 }
 
            almCfgOverDmdApprntPwrLastDrpStPnt OBJECT-TYPE
                SYNTAX DisplayString (SIZE (0..255))
                MAX-ACCESS read-only
                STATUS mandatory
                DESCRIPTION 
                    "Alarm Configuration - Over Demand Apparent Power Last - Drop Out Setpoint (kVA)"
                ::= { almCfgOverDmdApprntPwrLast 5 }
 
            almCfgOverDmdApprntPwrLastDrpDly OBJECT-TYPE
                SYNTAX DisplayString (SIZE (0..255))
                MAX-ACCESS read-only
                STATUS mandatory
                DESCRIPTION 
                    "Alarm Configuration - Over Demand Apparent Power Last - Drop Out Delay (Seconds)"
                ::= { almCfgOverDmdApprntPwrLast 6 }
 
            almCfgOverDmdApprntPwrLastDOs   OBJECT-TYPE
                SYNTAX DisplayString (SIZE (0..255))
                MAX-ACCESS read-only
                STATUS mandatory
                DESCRIPTION 
                    "Alarm Configuration - Over Demand Apparent Power Last - Associated Digital Outputs. Bitmap of digital outputs to associate with this alarm.
Bitmap is right-justified with the least significant bit associated with digital output ID of 1."
                ::= { almCfgOverDmdApprntPwrLast 7 }
 
 
        almCfgOverDmdApprntPwrPred OBJECT IDENTIFIER ::= { oneSecStdAlarmConfiguration 24 }
 
            almCfgOverDmdApprntPwrPredEnableDisable OBJECT-TYPE
                SYNTAX DisplayString (SIZE (0..255))
                MAX-ACCESS read-only
                STATUS mandatory
                DESCRIPTION 
                    "Alarm Configuration - Over Demand Apparent Power Predicted - Enable / Disable"
                ::= { almCfgOverDmdApprntPwrPred 1 }
 
            almCfgOverDmdApprntPwrPredPriority OBJECT-TYPE
                SYNTAX DisplayString (SIZE (0..255))
                MAX-ACCESS read-only
                STATUS mandatory
                DESCRIPTION 
                    "Alarm Configuration - Over Demand Apparent Power Predicted - Priority"
                ::= { almCfgOverDmdApprntPwrPred 2 }
 
            almCfgOverDmdApprntPwrPredPkupStPnt OBJECT-TYPE
                SYNTAX DisplayString (SIZE (0..255))
                MAX-ACCESS read-only
                STATUS mandatory
                DESCRIPTION 
                    "Alarm Configuration - Over Demand Apparent Power Predicted - Pickup Setpoint (kVA)"
                ::= { almCfgOverDmdApprntPwrPred 3 }
 
            almCfgOverDmdApprntPwrPredPkupDly OBJECT-TYPE
                SYNTAX DisplayString (SIZE (0..255))
                MAX-ACCESS read-only
                STATUS mandatory
                DESCRIPTION 
                    "Alarm Configuration - Over Demand Apparent Power Predicted - Pickup Delay (Seconds)"
                ::= { almCfgOverDmdApprntPwrPred 4 }
 
            almCfgOverDmdApprntPwrPredDrpStPnt OBJECT-TYPE
                SYNTAX DisplayString (SIZE (0..255))
                MAX-ACCESS read-only
                STATUS mandatory
                DESCRIPTION 
                    "Alarm Configuration - Over Demand Apparent Power Predicted - Drop Out Setpoint (kVA)"
                ::= { almCfgOverDmdApprntPwrPred 5 }
 
            almCfgOverDmdApprntPwrPredDrpDly OBJECT-TYPE
                SYNTAX DisplayString (SIZE (0..255))
                MAX-ACCESS read-only
                STATUS mandatory
                DESCRIPTION 
                    "Alarm Configuration - Over Demand Apparent Power Predicted - Drop Out Delay (Seconds)"
                ::= { almCfgOverDmdApprntPwrPred 6 }
 
            almCfgOverDmdApprntPwrPredDOs   OBJECT-TYPE
                SYNTAX DisplayString (SIZE (0..255))
                MAX-ACCESS read-only
                STATUS mandatory
                DESCRIPTION 
                    "Alarm Configuration - Over Demand Apparent Power Predicted - Associated Digital Outputs. Bitmap of digital outputs to associate with this alarm.
Bitmap is right-justified with the least significant bit associated with digital output ID of 1."
                ::= { almCfgOverDmdApprntPwrPred 7 }
 
 
        almCfgOverFreq OBJECT IDENTIFIER ::= { oneSecStdAlarmConfiguration 25 }
 
            almCfgOverFreqEnableDisable OBJECT-TYPE
                SYNTAX DisplayString (SIZE (0..255))
                MAX-ACCESS read-only
                STATUS mandatory
                DESCRIPTION 
                    "Alarm Configuration - Over Frequency - Enable / Disable"
                ::= { almCfgOverFreq 1 }
 
            almCfgOverFreqPriority OBJECT-TYPE
                SYNTAX DisplayString (SIZE (0..255))
                MAX-ACCESS read-only
                STATUS mandatory
                DESCRIPTION 
                    "Alarm Configuration - Over Frequency - Priority"
                ::= { almCfgOverFreq 2 }
 
            almCfgOverFreqPkupStPnt OBJECT-TYPE
                SYNTAX DisplayString (SIZE (0..255))
                MAX-ACCESS read-only
                STATUS mandatory
                DESCRIPTION 
                    "Alarm Configuration - Over Frequency - Pickup Setpoint (Hz)"
                ::= { almCfgOverFreq 3 }
 
            almCfgOverFreqPkupDly OBJECT-TYPE
                SYNTAX DisplayString (SIZE (0..255))
                MAX-ACCESS read-only
                STATUS mandatory
                DESCRIPTION 
                    "Alarm Configuration - Over Frequency - Pickup Delay (Seconds)"
                ::= { almCfgOverFreq 4 }
 
            almCfgOverFreqDrpStPnt OBJECT-TYPE
                SYNTAX DisplayString (SIZE (0..255))
                MAX-ACCESS read-only
                STATUS mandatory
                DESCRIPTION 
                    "Alarm Configuration - Over Frequency - Drop Out Setpoint (Hz)"
                ::= { almCfgOverFreq 5 }
 
            almCfgOverFreqDrpDly OBJECT-TYPE
                SYNTAX DisplayString (SIZE (0..255))
                MAX-ACCESS read-only
                STATUS mandatory
                DESCRIPTION 
                    "Alarm Configuration - Over Frequency - Drop Out Delay (Seconds)"
                ::= { almCfgOverFreq 6 }
 
            almCfgOverFreqDOs   OBJECT-TYPE
                SYNTAX DisplayString (SIZE (0..255))
                MAX-ACCESS read-only
                STATUS mandatory
                DESCRIPTION 
                    "Alarm Configuration - Over Frequency - Associated Digital Outputs. Bitmap of digital outputs to associate with this alarm.
Bitmap is right-justified with the least significant bit associated with digital output ID of 1."
                ::= { almCfgOverFreq 7 }
 
 
        almCfgUnderFreq OBJECT IDENTIFIER ::= { oneSecStdAlarmConfiguration 26 }
 
            almCfgUnderFreqEnableDisable OBJECT-TYPE
                SYNTAX DisplayString (SIZE (0..255))
                MAX-ACCESS read-only
                STATUS mandatory
                DESCRIPTION 
                    "Alarm Configuration - Under Frequency - Enable / Disable"
                ::= { almCfgUnderFreq 1 }
 
            almCfgUnderFreqPriority OBJECT-TYPE
                SYNTAX DisplayString (SIZE (0..255))
                MAX-ACCESS read-only
                STATUS mandatory
                DESCRIPTION 
                    "Alarm Configuration - Under Frequency - Priority"
                ::= { almCfgUnderFreq 2 }
 
            almCfgUnderFreqPkupStPnt OBJECT-TYPE
                SYNTAX DisplayString (SIZE (0..255))
                MAX-ACCESS read-only
                STATUS mandatory
                DESCRIPTION 
                    "Alarm Configuration - Under Frequency - Pickup Setpoint (Hz)"
                ::= { almCfgUnderFreq 3 }
 
            almCfgUnderFreqPkupDly OBJECT-TYPE
                SYNTAX DisplayString (SIZE (0..255))
                MAX-ACCESS read-only
                STATUS mandatory
                DESCRIPTION 
                    "Alarm Configuration - Under Frequency - Pickup Delay (Seconds)"
                ::= { almCfgUnderFreq 4 }
 
            almCfgUnderFreqDrpStPnt OBJECT-TYPE
                SYNTAX DisplayString (SIZE (0..255))
                MAX-ACCESS read-only
                STATUS mandatory
                DESCRIPTION 
                    "Alarm Configuration - Under Frequency - Drop Out Setpoint (Hz)"
                ::= { almCfgUnderFreq 5 }
 
            almCfgUnderFreqDrpDly OBJECT-TYPE
                SYNTAX DisplayString (SIZE (0..255))
                MAX-ACCESS read-only
                STATUS mandatory
                DESCRIPTION 
                    "Alarm Configuration - Under Frequency - Drop Out Delay (Seconds)"
                ::= { almCfgUnderFreq 6 }
 
            almCfgUnderFreqDOs   OBJECT-TYPE
                SYNTAX DisplayString (SIZE (0..255))
                MAX-ACCESS read-only
                STATUS mandatory
                DESCRIPTION 
                    "Alarm Configuration - Under Frequency - Associated Digital Outputs. Bitmap of digital outputs to associate with this alarm.
Bitmap is right-justified with the least significant bit associated with digital output ID of 1."
                ::= { almCfgUnderFreq 7 }
 
 
        almCfgOverVoltUnb OBJECT IDENTIFIER ::= { oneSecStdAlarmConfiguration 27 }
 
            almCfgOverVoltUnbEnableDisable OBJECT-TYPE
                SYNTAX DisplayString (SIZE (0..255))
                MAX-ACCESS read-only
                STATUS mandatory
                DESCRIPTION 
                    "Alarm Configuration - Over Voltage Unbalance - Enable / Disable"
                ::= { almCfgOverVoltUnb 1 }
 
            almCfgOverVoltUnbPriority OBJECT-TYPE
                SYNTAX DisplayString (SIZE (0..255))
                MAX-ACCESS read-only
                STATUS mandatory
                DESCRIPTION 
                    "Alarm Configuration - Over Voltage Unbalance - Priority"
                ::= { almCfgOverVoltUnb 2 }
 
            almCfgOverVoltUnbPkupStPnt OBJECT-TYPE
                SYNTAX DisplayString (SIZE (0..255))
                MAX-ACCESS read-only
                STATUS mandatory
                DESCRIPTION 
                    "Alarm Configuration - Over Voltage Unbalance - Pickup Setpoint (Volts)"
                ::= { almCfgOverVoltUnb 3 }
 
            almCfgOverVoltUnbPkupDly OBJECT-TYPE
                SYNTAX DisplayString (SIZE (0..255))
                MAX-ACCESS read-only
                STATUS mandatory
                DESCRIPTION 
                    "Alarm Configuration - Over Voltage Unbalance - Pickup Delay (Seconds)"
                ::= { almCfgOverVoltUnb 4 }
 
            almCfgOverVoltUnbDrpStPnt OBJECT-TYPE
                SYNTAX DisplayString (SIZE (0..255))
                MAX-ACCESS read-only
                STATUS mandatory
                DESCRIPTION 
                    "Alarm Configuration - Over Voltage Unbalance - Drop Out Setpoint (Volts)"
                ::= { almCfgOverVoltUnb 5 }
 
            almCfgOverVoltUnbDrpDly OBJECT-TYPE
                SYNTAX DisplayString (SIZE (0..255))
                MAX-ACCESS read-only
                STATUS mandatory
                DESCRIPTION 
                    "Alarm Configuration - Over Voltage Unbalance - Drop Out Delay (Seconds)"
                ::= { almCfgOverVoltUnb 6 }
 
            almCfgOverVoltUnbDOs   OBJECT-TYPE
                SYNTAX DisplayString (SIZE (0..255))
                MAX-ACCESS read-only
                STATUS mandatory
                DESCRIPTION 
                    "Alarm Configuration - Over Voltage Unbalance - Associated Digital Outputs. Bitmap of digital outputs to associate with this alarm.
Bitmap is right-justified with the least significant bit associated with digital output ID of 1."
                ::= { almCfgOverVoltUnb 7 }
 
 
        almCfgOverVoltTotHarmDist OBJECT IDENTIFIER ::= { oneSecStdAlarmConfiguration 28 }
 
            almCfgOverVoltTotHarmDistEnableDisable OBJECT-TYPE
                SYNTAX DisplayString (SIZE (0..255))
                MAX-ACCESS read-only
                STATUS mandatory
                DESCRIPTION 
                    "Alarm Configuration - Over Voltage Total Harmonic Distortion - Enable / Disable"
                ::= { almCfgOverVoltTotHarmDist 1 }
 
            almCfgOverVoltTotHarmDistPriority OBJECT-TYPE
                SYNTAX DisplayString (SIZE (0..255))
                MAX-ACCESS read-only
                STATUS mandatory
                DESCRIPTION 
                    "Alarm Configuration - Over Voltage Total Harmonic Distortion - Priority"
                ::= { almCfgOverVoltTotHarmDist 2 }
 
            almCfgOverVoltTotHarmDistPkupStPnt OBJECT-TYPE
                SYNTAX DisplayString (SIZE (0..255))
                MAX-ACCESS read-only
                STATUS mandatory
                DESCRIPTION 
                    "Alarm Configuration - Over Voltage Total Harmonic Distortion - Pickup Setpoint (%)"
                ::= { almCfgOverVoltTotHarmDist 3 }
 
            almCfgOverVoltTotHarmDistPkupDly OBJECT-TYPE
                SYNTAX DisplayString (SIZE (0..255))
                MAX-ACCESS read-only
                STATUS mandatory
                DESCRIPTION 
                    "Alarm Configuration - Over Voltage Total Harmonic Distortion - Pickup Delay (Seconds)"
                ::= { almCfgOverVoltTotHarmDist 4 }
 
            almCfgOverVoltTotHarmDistDrpStPnt OBJECT-TYPE
                SYNTAX DisplayString (SIZE (0..255))
                MAX-ACCESS read-only
                STATUS mandatory
                DESCRIPTION 
                    "Alarm Configuration - Over Voltage Total Harmonic Distortion - Drop Out Setpoint (%)"
                ::= { almCfgOverVoltTotHarmDist 5 }
 
            almCfgOverVoltTotHarmDistDrpDly OBJECT-TYPE
                SYNTAX DisplayString (SIZE (0..255))
                MAX-ACCESS read-only
                STATUS mandatory
                DESCRIPTION 
                    "Alarm Configuration - Over Voltage Total Harmonic Distortion - Drop Out Delay (Seconds)"
                ::= { almCfgOverVoltTotHarmDist 6 }
 
            almCfgOverVoltTotHarmDistDOs   OBJECT-TYPE
                SYNTAX DisplayString (SIZE (0..255))
                MAX-ACCESS read-only
                STATUS mandatory
                DESCRIPTION 
                    "Alarm Configuration - Over Voltage Total Harmonic Distortion - Associated Digital Outputs. Bitmap of digital outputs to associate with this alarm.
Bitmap is right-justified with the least significant bit associated with digital output ID of 1."
                ::= { almCfgOverVoltTotHarmDist 7 }
 
 
        almCfgPhaseLoss OBJECT IDENTIFIER ::= { oneSecStdAlarmConfiguration 29 }
 
            almCfgPhaseLossEnableDisable OBJECT-TYPE
                SYNTAX DisplayString (SIZE (0..255))
                MAX-ACCESS read-only
                STATUS mandatory
                DESCRIPTION 
                    "Alarm Configuration - Phase Loss - Enable / Disable"
                ::= { almCfgPhaseLoss 1 }
 
            almCfgPhaseLossPriority OBJECT-TYPE
                SYNTAX DisplayString (SIZE (0..255))
                MAX-ACCESS read-only
                STATUS mandatory
                DESCRIPTION 
                    "Alarm Configuration - Phase Loss - Priority"
                ::= { almCfgPhaseLoss 2 }
 
            almCfgPhaseLossPkupStPnt OBJECT-TYPE
                SYNTAX DisplayString (SIZE (0..255))
                MAX-ACCESS read-only
                STATUS mandatory
                DESCRIPTION 
                    "Alarm Configuration - Phase Loss - Pickup Setpoint"
                ::= { almCfgPhaseLoss 3 }
 
            almCfgPhaseLossPkupDly OBJECT-TYPE
                SYNTAX DisplayString (SIZE (0..255))
                MAX-ACCESS read-only
                STATUS mandatory
                DESCRIPTION 
                    "Alarm Configuration - Phase Loss - Pickup Delay (Seconds)"
                ::= { almCfgPhaseLoss 4 }
 
            almCfgPhaseLossDrpStPnt OBJECT-TYPE
                SYNTAX DisplayString (SIZE (0..255))
                MAX-ACCESS read-only
                STATUS mandatory
                DESCRIPTION 
                    "Alarm Configuration - Phase Loss - Drop Out Setpoint"
                ::= { almCfgPhaseLoss 5 }
 
            almCfgPhaseLossDrpDly OBJECT-TYPE
                SYNTAX DisplayString (SIZE (0..255))
                MAX-ACCESS read-only
                STATUS mandatory
                DESCRIPTION 
                    "Alarm Configuration - Phase Loss - Drop Out Delay (Seconds)"
                ::= { almCfgPhaseLoss 6 }
 
            almCfgPhaseLossDOs   OBJECT-TYPE
                SYNTAX DisplayString (SIZE (0..255))
                MAX-ACCESS read-only
                STATUS mandatory
                DESCRIPTION 
                    "Alarm Configuration - Phase Loss - Associated Digital Outputs. Bitmap of digital outputs to associate with this alarm.
Bitmap is right-justified with the least significant bit associated with digital output ID of 1."
                ::= { almCfgPhaseLoss 7 }
 
 
 
        oneSecCustAlarmConfiguration OBJECT IDENTIFIER ::= { alarmsConfiguration 2 }
 
        almCfgCustom1 OBJECT IDENTIFIER ::= { oneSecCustAlarmConfiguration 1 }
 
            almCfgCustom1Label OBJECT-TYPE
                SYNTAX DisplayString (SIZE (0..255))
                MAX-ACCESS read-only
                STATUS mandatory
                DESCRIPTION 
                    "Alarm Configuration - Custom 1 - Label"
                ::= { almCfgCustom1 1 }
 
            almCfgCustom1EnableDisable OBJECT-TYPE
                SYNTAX DisplayString (SIZE (0..255))
                MAX-ACCESS read-only
                STATUS mandatory
                DESCRIPTION 
                    "Alarm Configuration - Custom 1 - Enable / Disable"
                ::= { almCfgCustom1 2 }
 
            almCfgCustom1Priority OBJECT-TYPE
                SYNTAX DisplayString (SIZE (0..255))
                MAX-ACCESS read-only
                STATUS mandatory
                DESCRIPTION 
                    "Alarm Configuration - Custom 1 - Priority"
                ::= { almCfgCustom1 3 }
 
            almCfgCustom1SrcRegister OBJECT-TYPE
                SYNTAX DisplayString (SIZE (0..255))
                MAX-ACCESS read-only
                STATUS mandatory
                DESCRIPTION 
                    "Alarm Configuration - Custom 1 - Source Register"
                ::= { almCfgCustom1 4 }
 
            almCfgCustom1PkupStPnt OBJECT-TYPE
                SYNTAX DisplayString (SIZE (0..255))
                MAX-ACCESS read-only
                STATUS mandatory
                DESCRIPTION 
                    "Alarm Configuration - Custom 1 - Pickup Setpoint - (Units depend on selected Parameter)"
                ::= { almCfgCustom1 5 }
 
            almCfgCustom1PkupDly OBJECT-TYPE
                SYNTAX DisplayString (SIZE (0..255))
                MAX-ACCESS read-only
                STATUS mandatory
                DESCRIPTION 
                    "Alarm Configuration - Custom 1 - Pickup Delay (Seconds)"
                ::= { almCfgCustom1 6 }
 
            almCfgCustom1DrpStPnt OBJECT-TYPE
                SYNTAX DisplayString (SIZE (0..255))
                MAX-ACCESS read-only
                STATUS mandatory
                DESCRIPTION 
                    "Alarm Configuration - Custom 1 - Dropout Setpoint - (Units depend on selected Parameter)"
                ::= { almCfgCustom1 7 }
 
            almCfgCustom1DrpDly OBJECT-TYPE
                SYNTAX DisplayString (SIZE (0..255))
                MAX-ACCESS read-only
                STATUS mandatory
                DESCRIPTION 
                    "Alarm Configuration - Custom 1 - Dropout Delay (Seconds)"
                ::= { almCfgCustom1 8 }
 
            almCfgCustom1DOs   OBJECT-TYPE
                SYNTAX DisplayString (SIZE (0..255))
                MAX-ACCESS read-only
                STATUS mandatory
                DESCRIPTION 
                    "Alarm Configuration - Custom 1 - Associated Digital Outputs. Bitmap of digital outputs to associate with this alarm.
Bitmap is right-justified with the least significant bit associated with digital output ID of 1."
                ::= { almCfgCustom1 9 }
 
 
        almCfgCustom2 OBJECT IDENTIFIER ::= { oneSecCustAlarmConfiguration 2 }
 
            almCfgCustom2Label OBJECT-TYPE
                SYNTAX DisplayString (SIZE (0..255))
                MAX-ACCESS read-only
                STATUS mandatory
                DESCRIPTION 
                    "Alarm Configuration - Custom 2 - Label"
                ::= { almCfgCustom2 1 }
 
            almCfgCustom2EnableDisable OBJECT-TYPE
                SYNTAX DisplayString (SIZE (0..255))
                MAX-ACCESS read-only
                STATUS mandatory
                DESCRIPTION 
                    "Alarm Configuration - Custom 2 - Enable / Disable"
                ::= { almCfgCustom2 2 }
 
            almCfgCustom2Priority OBJECT-TYPE
                SYNTAX DisplayString (SIZE (0..255))
                MAX-ACCESS read-only
                STATUS mandatory
                DESCRIPTION 
                    "Alarm Configuration - Custom 2 - Priority"
                ::= { almCfgCustom2 3 }
 
            almCfgCustom2SrcRegister OBJECT-TYPE
                SYNTAX DisplayString (SIZE (0..255))
                MAX-ACCESS read-only
                STATUS mandatory
                DESCRIPTION 
                    "Alarm Configuration - Custom 2 - Source Register"
                ::= { almCfgCustom2 4 }
 
            almCfgCustom2PkupStPnt OBJECT-TYPE
                SYNTAX DisplayString (SIZE (0..255))
                MAX-ACCESS read-only
                STATUS mandatory
                DESCRIPTION 
                    "Alarm Configuration - Custom 2 - Pickup Setpoint - (Units depend on selected Parameter)"
                ::= { almCfgCustom2 5 }
 
            almCfgCustom2PkupDly OBJECT-TYPE
                SYNTAX DisplayString (SIZE (0..255))
                MAX-ACCESS read-only
                STATUS mandatory
                DESCRIPTION 
                    "Alarm Configuration - Custom 2 - Pickup Delay (Seconds)"
                ::= { almCfgCustom2 6 }
 
            almCfgCustom2DrpStPnt OBJECT-TYPE
                SYNTAX DisplayString (SIZE (0..255))
                MAX-ACCESS read-only
                STATUS mandatory
                DESCRIPTION 
                    "Alarm Configuration - Custom 2 - Dropout Setpoint - (Units depend on selected Parameter)"
                ::= { almCfgCustom2 7 }
 
            almCfgCustom2DrpDly OBJECT-TYPE
                SYNTAX DisplayString (SIZE (0..255))
                MAX-ACCESS read-only
                STATUS mandatory
                DESCRIPTION 
                    "Alarm Configuration - Custom 2 - Dropout Delay (Seconds)"
                ::= { almCfgCustom2 8 }
 
            almCfgCustom2DOs   OBJECT-TYPE
                SYNTAX DisplayString (SIZE (0..255))
                MAX-ACCESS read-only
                STATUS mandatory
                DESCRIPTION 
                    "Alarm Configuration - Custom 2 - Associated Digital Outputs. Bitmap of digital outputs to associate with this alarm.
Bitmap is right-justified with the least significant bit associated with digital output ID of 1."
                ::= { almCfgCustom2 9 }
 
 
        almCfgCustom3 OBJECT IDENTIFIER ::= { oneSecCustAlarmConfiguration 3 }
 
            almCfgCustom3Label OBJECT-TYPE
                SYNTAX DisplayString (SIZE (0..255))
                MAX-ACCESS read-only
                STATUS mandatory
                DESCRIPTION 
                    "Alarm Configuration - Custom 3 - Label"
                ::= { almCfgCustom3 1 }
 
            almCfgCustom3EnableDisable OBJECT-TYPE
                SYNTAX DisplayString (SIZE (0..255))
                MAX-ACCESS read-only
                STATUS mandatory
                DESCRIPTION 
                    "Alarm Configuration - Custom 3 - Enable / Disable"
                ::= { almCfgCustom3 2 }
 
            almCfgCustom3Priority OBJECT-TYPE
                SYNTAX DisplayString (SIZE (0..255))
                MAX-ACCESS read-only
                STATUS mandatory
                DESCRIPTION 
                    "Alarm Configuration - Custom 3 - Priority"
                ::= { almCfgCustom3 3 }
 
            almCfgCustom3SrcRegister OBJECT-TYPE
                SYNTAX DisplayString (SIZE (0..255))
                MAX-ACCESS read-only
                STATUS mandatory
                DESCRIPTION 
                    "Alarm Configuration - Custom 3 - Source Register"
                ::= { almCfgCustom3 4 }
 
            almCfgCustom3PkupStPnt OBJECT-TYPE
                SYNTAX DisplayString (SIZE (0..255))
                MAX-ACCESS read-only
                STATUS mandatory
                DESCRIPTION 
                    "Alarm Configuration - Custom 3 - Pickup Setpoint - (Units depend on selected Parameter)"
                ::= { almCfgCustom3 5 }
 
            almCfgCustom3PkupDly OBJECT-TYPE
                SYNTAX DisplayString (SIZE (0..255))
                MAX-ACCESS read-only
                STATUS mandatory
                DESCRIPTION 
                    "Alarm Configuration - Custom 3 - Pickup Delay (Seconds)"
                ::= { almCfgCustom3 6 }
 
            almCfgCustom3DrpStPnt OBJECT-TYPE
                SYNTAX DisplayString (SIZE (0..255))
                MAX-ACCESS read-only
                STATUS mandatory
                DESCRIPTION 
                    "Alarm Configuration - Custom 3 - Dropout Setpoint - (Units depend on selected Parameter)"
                ::= { almCfgCustom3 7 }
 
            almCfgCustom3DrpDly OBJECT-TYPE
                SYNTAX DisplayString (SIZE (0..255))
                MAX-ACCESS read-only
                STATUS mandatory
                DESCRIPTION 
                    "Alarm Configuration - Custom 3 - Dropout Delay (Seconds)"
                ::= { almCfgCustom3 8 }
 
            almCfgCustom3DOs   OBJECT-TYPE
                SYNTAX DisplayString (SIZE (0..255))
                MAX-ACCESS read-only
                STATUS mandatory
                DESCRIPTION 
                    "Alarm Configuration - Custom 3 - Associated Digital Outputs. Bitmap of digital outputs to associate with this alarm.
Bitmap is right-justified with the least significant bit associated with digital output ID of 1."
                ::= { almCfgCustom3 9 }
 
 
        almCfgCustom4 OBJECT IDENTIFIER ::= { oneSecCustAlarmConfiguration 4 }
 
            almCfgCustom4Label OBJECT-TYPE
                SYNTAX DisplayString (SIZE (0..255))
                MAX-ACCESS read-only
                STATUS mandatory
                DESCRIPTION 
                    "Alarm Configuration - Custom 4 - Label"
                ::= { almCfgCustom4 1 }
 
            almCfgCustom4EnableDisable OBJECT-TYPE
                SYNTAX DisplayString (SIZE (0..255))
                MAX-ACCESS read-only
                STATUS mandatory
                DESCRIPTION 
                    "Alarm Configuration - Custom 4 - Enable / Disable"
                ::= { almCfgCustom4 2 }
 
            almCfgCustom4Priority OBJECT-TYPE
                SYNTAX DisplayString (SIZE (0..255))
                MAX-ACCESS read-only
                STATUS mandatory
                DESCRIPTION 
                    "Alarm Configuration - Custom 4 - Priority"
                ::= { almCfgCustom4 3 }
 
            almCfgCustom4SrcRegister OBJECT-TYPE
                SYNTAX DisplayString (SIZE (0..255))
                MAX-ACCESS read-only
                STATUS mandatory
                DESCRIPTION 
                    "Alarm Configuration - Custom 4 - Source Register"
                ::= { almCfgCustom4 4 }
 
            almCfgCustom4PkupStPnt OBJECT-TYPE
                SYNTAX DisplayString (SIZE (0..255))
                MAX-ACCESS read-only
                STATUS mandatory
                DESCRIPTION 
                    "Alarm Configuration - Custom 4 - Pickup Setpoint - (Units depend on selected Parameter)"
                ::= { almCfgCustom4 5 }
 
            almCfgCustom4PkupDly OBJECT-TYPE
                SYNTAX DisplayString (SIZE (0..255))
                MAX-ACCESS read-only
                STATUS mandatory
                DESCRIPTION 
                    "Alarm Configuration - Custom 4 - Pickup Delay (Seconds)"
                ::= { almCfgCustom4 6 }
 
            almCfgCustom4DrpStPnt OBJECT-TYPE
                SYNTAX DisplayString (SIZE (0..255))
                MAX-ACCESS read-only
                STATUS mandatory
                DESCRIPTION 
                    "Alarm Configuration - Custom 4 - Dropout Setpoint - (Units depend on selected Parameter)"
                ::= { almCfgCustom4 7 }
 
            almCfgCustom4DrpDly OBJECT-TYPE
                SYNTAX DisplayString (SIZE (0..255))
                MAX-ACCESS read-only
                STATUS mandatory
                DESCRIPTION 
                    "Alarm Configuration - Custom 4 - Dropout Delay (Seconds)"
                ::= { almCfgCustom4 8 }
 
            almCfgCustom4DOs   OBJECT-TYPE
                SYNTAX DisplayString (SIZE (0..255))
                MAX-ACCESS read-only
                STATUS mandatory
                DESCRIPTION 
                    "Alarm Configuration - Custom 4 - Associated Digital Outputs. Bitmap of digital outputs to associate with this alarm.
Bitmap is right-justified with the least significant bit associated with digital output ID of 1."
                ::= { almCfgCustom4 9 }
 
 
        almCfgCustom5 OBJECT IDENTIFIER ::= { oneSecCustAlarmConfiguration 5 }
 
            almCfgCustom5Label OBJECT-TYPE
                SYNTAX DisplayString (SIZE (0..255))
                MAX-ACCESS read-only
                STATUS mandatory
                DESCRIPTION 
                    "Alarm Configuration - Custom 5 - Label"
                ::= { almCfgCustom5 1 }
 
            almCfgCustom5EnableDisable OBJECT-TYPE
                SYNTAX DisplayString (SIZE (0..255))
                MAX-ACCESS read-only
                STATUS mandatory
                DESCRIPTION 
                    "Alarm Configuration - Custom 5 - Enable / Disable"
                ::= { almCfgCustom5 2 }
 
            almCfgCustom5Priority OBJECT-TYPE
                SYNTAX DisplayString (SIZE (0..255))
                MAX-ACCESS read-only
                STATUS mandatory
                DESCRIPTION 
                    "Alarm Configuration - Custom 5 - Priority"
                ::= { almCfgCustom5 3 }
 
            almCfgCustom5SrcRegister OBJECT-TYPE
                SYNTAX DisplayString (SIZE (0..255))
                MAX-ACCESS read-only
                STATUS mandatory
                DESCRIPTION 
                    "Alarm Configuration - Custom 5 - Source Register"
                ::= { almCfgCustom5 4 }
 
            almCfgCustom5PkupStPnt OBJECT-TYPE
                SYNTAX DisplayString (SIZE (0..255))
                MAX-ACCESS read-only
                STATUS mandatory
                DESCRIPTION 
                    "Alarm Configuration - Custom 5 - Pickup Setpoint - (Units depend on selected Parameter)"
                ::= { almCfgCustom5 5 }
 
            almCfgCustom5PkupDly OBJECT-TYPE
                SYNTAX DisplayString (SIZE (0..255))
                MAX-ACCESS read-only
                STATUS mandatory
                DESCRIPTION 
                    "Alarm Configuration - Custom 5 - Pickup Delay (Seconds)"
                ::= { almCfgCustom5 6 }
 
            almCfgCustom5DrpStPnt OBJECT-TYPE
                SYNTAX DisplayString (SIZE (0..255))
                MAX-ACCESS read-only
                STATUS mandatory
                DESCRIPTION 
                    "Alarm Configuration - Custom 5 - Dropout Setpoint - (Units depend on selected Parameter)"
                ::= { almCfgCustom5 7 }
 
            almCfgCustom5DrpDly OBJECT-TYPE
                SYNTAX DisplayString (SIZE (0..255))
                MAX-ACCESS read-only
                STATUS mandatory
                DESCRIPTION 
                    "Alarm Configuration - Custom 5 - Dropout Delay (Seconds)"
                ::= { almCfgCustom5 8 }
 
            almCfgCustom5DOs   OBJECT-TYPE
                SYNTAX DisplayString (SIZE (0..255))
                MAX-ACCESS read-only
                STATUS mandatory
                DESCRIPTION 
                    "Alarm Configuration - Custom 5 - Associated Digital Outputs. Bitmap of digital outputs to associate with this alarm.
Bitmap is right-justified with the least significant bit associated with digital output ID of 1."
                ::= { almCfgCustom5 9 }
 
 
 
        digitalAlarmConfiguration OBJECT IDENTIFIER ::= { alarmsConfiguration 3 }
 
        almCfgDigitalS1 OBJECT IDENTIFIER ::= { digitalAlarmConfiguration 1 }
 
            almCfgDigitalS1EnableDisable OBJECT-TYPE
                SYNTAX DisplayString (SIZE (0..255))
                MAX-ACCESS read-only
                STATUS mandatory
                DESCRIPTION 
                    "Alarm Configuration - Digital S1 - Enable / Disable"
                ::= { almCfgDigitalS1 1 }
 
            almCfgDigitalS1Priority OBJECT-TYPE
                SYNTAX DisplayString (SIZE (0..255))
                MAX-ACCESS read-only
                STATUS mandatory
                DESCRIPTION 
                    "Alarm Configuration - Digital S1 - Priority"
                ::= { almCfgDigitalS1 2 }
 
            almCfgDigitalS1PkupType OBJECT-TYPE
                SYNTAX DisplayString (SIZE (0..255))
                MAX-ACCESS read-only
                STATUS mandatory
                DESCRIPTION 
                    "Alarm Configuration - Digital S1 - Pickup Type"
                ::= { almCfgDigitalS1 3 }
 
            almCfgDigitalS1PkupDly OBJECT-TYPE
                SYNTAX DisplayString (SIZE (0..255))
                MAX-ACCESS read-only
                STATUS mandatory
                DESCRIPTION 
                    "Alarm Configuration - Digital S1 - Pickup Delay (Seconds)"
                ::= { almCfgDigitalS1 4 }
 
            almCfgDigitalS1DrpDly OBJECT-TYPE
                SYNTAX DisplayString (SIZE (0..255))
                MAX-ACCESS read-only
                STATUS mandatory
                DESCRIPTION 
                    "Alarm Configuration - Digital S1 - Dropout Delay (Seconds)"
                ::= { almCfgDigitalS1 5 }
 
            almCfgDigitalS1DOs  OBJECT-TYPE
                SYNTAX DisplayString (SIZE (0..255))
                MAX-ACCESS read-only
                STATUS mandatory
                DESCRIPTION 
                    "Alarm Configuration - Digital S1 - Associated Digital Outputs. Bitmap of digital outputs to associate with this alarm.
Bitmap is right-justified with the least significant bit associated with digital output ID of 1."
                ::= { almCfgDigitalS1 6 }
 
 
        almCfgDigitalS2 OBJECT IDENTIFIER ::= { digitalAlarmConfiguration 2 }
 
            almCfgDigitalS2EnableDisable OBJECT-TYPE
                SYNTAX DisplayString (SIZE (0..255))
                MAX-ACCESS read-only
                STATUS mandatory
                DESCRIPTION 
                    "Alarm Configuration - Digital S2 - Enable / Disable"
                ::= { almCfgDigitalS2 1 }
 
            almCfgDigitalS2Priority OBJECT-TYPE
                SYNTAX DisplayString (SIZE (0..255))
                MAX-ACCESS read-only
                STATUS mandatory
                DESCRIPTION 
                    "Alarm Configuration - Digital S2 - Priority"
                ::= { almCfgDigitalS2 2 }
 
            almCfgDigitalS2PkupType OBJECT-TYPE
                SYNTAX DisplayString (SIZE (0..255))
                MAX-ACCESS read-only
                STATUS mandatory
                DESCRIPTION 
                    "Alarm Configuration - Digital S2 - Pickup Type"
                ::= { almCfgDigitalS2 3 }
 
            almCfgDigitalS2PkupDly OBJECT-TYPE
                SYNTAX DisplayString (SIZE (0..255))
                MAX-ACCESS read-only
                STATUS mandatory
                DESCRIPTION 
                    "Alarm Configuration - Digital S2 - Pickup Delay (Seconds)"
                ::= { almCfgDigitalS2 4 }
 
            almCfgDigitalS2DrpDly OBJECT-TYPE
                SYNTAX DisplayString (SIZE (0..255))
                MAX-ACCESS read-only
                STATUS mandatory
                DESCRIPTION 
                    "Alarm Configuration - Digital S2 - Dropout Delay (Seconds)"
                ::= { almCfgDigitalS2 5 }
 
            almCfgDigitalS2DOs  OBJECT-TYPE
                SYNTAX DisplayString (SIZE (0..255))
                MAX-ACCESS read-only
                STATUS mandatory
                DESCRIPTION 
                    "Alarm Configuration - Digital S2 - Associated Digital Outputs. Bitmap of digital outputs to associate with this alarm.
Bitmap is right-justified with the least significant bit associated with digital output ID of 1."
                ::= { almCfgDigitalS2 6 }
 
 
        almCfgDigitalS3 OBJECT IDENTIFIER ::= { digitalAlarmConfiguration 3 }
 
            almCfgDigitalS3EnableDisable OBJECT-TYPE
                SYNTAX DisplayString (SIZE (0..255))
                MAX-ACCESS read-only
                STATUS mandatory
                DESCRIPTION 
                    "Alarm Configuration - Digital S3 - Enable / Disable"
                ::= { almCfgDigitalS3 1 }
 
            almCfgDigitalS3Priority OBJECT-TYPE
                SYNTAX DisplayString (SIZE (0..255))
                MAX-ACCESS read-only
                STATUS mandatory
                DESCRIPTION 
                    "Alarm Configuration - Digital S3 - Priority"
                ::= { almCfgDigitalS3 2 }
 
            almCfgDigitalS3PkupType OBJECT-TYPE
                SYNTAX DisplayString (SIZE (0..255))
                MAX-ACCESS read-only
                STATUS mandatory
                DESCRIPTION 
                    "Alarm Configuration - Digital S3 - Pickup Type"
                ::= { almCfgDigitalS3 3 }
 
            almCfgDigitalS3PkupDly OBJECT-TYPE
                SYNTAX DisplayString (SIZE (0..255))
                MAX-ACCESS read-only
                STATUS mandatory
                DESCRIPTION 
                    "Alarm Configuration - Digital S3 - Pickup Delay (Seconds)"
                ::= { almCfgDigitalS3 4 }
 
            almCfgDigitalS3DrpDly OBJECT-TYPE
                SYNTAX DisplayString (SIZE (0..255))
                MAX-ACCESS read-only
                STATUS mandatory
                DESCRIPTION 
                    "Alarm Configuration - Digital S3 - Dropout Delay (Seconds)"
                ::= { almCfgDigitalS3 5 }
 
            almCfgDigitalS3DOs  OBJECT-TYPE
                SYNTAX DisplayString (SIZE (0..255))
                MAX-ACCESS read-only
                STATUS mandatory
                DESCRIPTION 
                    "Alarm Configuration - Digital S3 - Associated Digital Outputs. Bitmap of digital outputs to associate with this alarm.
Bitmap is right-justified with the least significant bit associated with digital output ID of 1."
                ::= { almCfgDigitalS3 6 }
 
 
        almCfgDigitalS4 OBJECT IDENTIFIER ::= { digitalAlarmConfiguration 4 }
 
            almCfgDigitalS4EnableDisable OBJECT-TYPE
                SYNTAX DisplayString (SIZE (0..255))
                MAX-ACCESS read-only
                STATUS mandatory
                DESCRIPTION 
                    "Alarm Configuration - Digital S4 - Enable / Disable"
                ::= { almCfgDigitalS4 1 }
 
            almCfgDigitalS4Priority OBJECT-TYPE
                SYNTAX DisplayString (SIZE (0..255))
                MAX-ACCESS read-only
                STATUS mandatory
                DESCRIPTION 
                    "Alarm Configuration - Digital S4 - Priority"
                ::= { almCfgDigitalS4 2 }
 
            almCfgDigitalS4PkupType OBJECT-TYPE
                SYNTAX DisplayString (SIZE (0..255))
                MAX-ACCESS read-only
                STATUS mandatory
                DESCRIPTION 
                    "Alarm Configuration - Digital S4 - Pickup Type"
                ::= { almCfgDigitalS4 3 }
 
            almCfgDigitalS4PkupDly OBJECT-TYPE
                SYNTAX DisplayString (SIZE (0..255))
                MAX-ACCESS read-only
                STATUS mandatory
                DESCRIPTION 
                    "Alarm Configuration - Digital S4 - Pickup Delay (Seconds)"
                ::= { almCfgDigitalS4 4 }
 
            almCfgDigitalS4DrpDly OBJECT-TYPE
                SYNTAX DisplayString (SIZE (0..255))
                MAX-ACCESS read-only
                STATUS mandatory
                DESCRIPTION 
                    "Alarm Configuration - Digital S4 - Dropout Delay (Seconds)"
                ::= { almCfgDigitalS4 5 }
 
            almCfgDigitalS4DOs  OBJECT-TYPE
                SYNTAX DisplayString (SIZE (0..255))
                MAX-ACCESS read-only
                STATUS mandatory
                DESCRIPTION 
                    "Alarm Configuration - Digital S4 - Associated Digital Outputs. Bitmap of digital outputs to associate with this alarm.
Bitmap is right-justified with the least significant bit associated with digital output ID of 1."
                ::= { almCfgDigitalS4 6 }
 
 
 
        unaryAlarmConfiguration OBJECT IDENTIFIER ::= { alarmsConfiguration 4 }
 
        almCfgMtrPwrUp OBJECT IDENTIFIER ::= { unaryAlarmConfiguration 1 }
 
            almCfgMtrPwrUpEnableDisable OBJECT-TYPE
                SYNTAX DisplayString (SIZE (0..255))
                MAX-ACCESS read-only
                STATUS mandatory
                DESCRIPTION 
                    "Alarm Configuration - Unary Meter Power Up - Enabled / Disabled"
                ::= { almCfgMtrPwrUp 1 }
 
            almCfgMtrPwrUpPriority OBJECT-TYPE
                SYNTAX DisplayString (SIZE (0..255))
                MAX-ACCESS read-only
                STATUS mandatory
                DESCRIPTION 
                    "Alarm Configuration - Unary Meter Power Up - Priority"
                ::= { almCfgMtrPwrUp 2 }
 
            almCfgMtrPwrUpDOs  OBJECT-TYPE
                SYNTAX DisplayString (SIZE (0..255))
                MAX-ACCESS read-only
                STATUS mandatory
                DESCRIPTION 
                    "Alarm Configuration - Unary Meter Power Up -  Associated Digital Outputs. Bitmap of digital outputs to associate with this alarm.
Bitmap is right-justified with the least significant bit associated with digital output ID of 1."
                ::= { almCfgMtrPwrUp 3 }
 
 
        almCfgMtrReset OBJECT IDENTIFIER ::= { unaryAlarmConfiguration 2 }
 
            almCfgMtrResetEnableDisable OBJECT-TYPE
                SYNTAX DisplayString (SIZE (0..255))
                MAX-ACCESS read-only
                STATUS mandatory
                DESCRIPTION 
                    "Alarm Configuration - Unary Meter Reset - Enabled / Disabled"
                ::= { almCfgMtrReset 1 }
 
            almCfgMtrResetPriority OBJECT-TYPE
                SYNTAX DisplayString (SIZE (0..255))
                MAX-ACCESS read-only
                STATUS mandatory
                DESCRIPTION 
                    "Alarm Configuration - Unary Meter Reset - Priority"
                ::= { almCfgMtrReset 2 }
 
            almCfgMtrResetDOs  OBJECT-TYPE
                SYNTAX DisplayString (SIZE (0..255))
                MAX-ACCESS read-only
                STATUS mandatory
                DESCRIPTION 
                    "Alarm Configuration - Unary Meter Reset -  Associated Digital Outputs. Bitmap of digital outputs to associate with this alarm.
Bitmap is right-justified with the least significant bit associated with digital output ID of 1."
                ::= { almCfgMtrReset 3 }
 
 
        almCfgMtrDiag OBJECT IDENTIFIER ::= { unaryAlarmConfiguration 3 }
 
            almCfgMtrDiagEnableDisable OBJECT-TYPE
                SYNTAX DisplayString (SIZE (0..255))
                MAX-ACCESS read-only
                STATUS mandatory
                DESCRIPTION 
                    "Alarm Configuration - Unary Meter Diagnostic - Enabled / Disabled"
                ::= { almCfgMtrDiag 1 }
 
            almCfgMtrDiagPriority OBJECT-TYPE
                SYNTAX DisplayString (SIZE (0..255))
                MAX-ACCESS read-only
                STATUS mandatory
                DESCRIPTION 
                    "Alarm Configuration - Unary Meter Diagnostic - Priority"
                ::= { almCfgMtrDiag 2 }
 
            almCfgMtrDiagDOs  OBJECT-TYPE
                SYNTAX DisplayString (SIZE (0..255))
                MAX-ACCESS read-only
                STATUS mandatory
                DESCRIPTION 
                    "Alarm Configuration - Unary Meter Diagnostic -  Associated Digital Outputs. Bitmap of digital outputs to associate with this alarm.
Bitmap is right-justified with the least significant bit associated with digital output ID of 1."
                ::= { almCfgMtrDiag 3 }
 
 
        almCfgMtrReversal OBJECT IDENTIFIER ::= { unaryAlarmConfiguration 4 }
 
            almCfgMtrReversalEnableDisable OBJECT-TYPE
                SYNTAX DisplayString (SIZE (0..255))
                MAX-ACCESS read-only
                STATUS mandatory
                DESCRIPTION 
                    "Alarm Configuration - Unary Meter Phase Reversal - Enabled / Disabled"
                ::= { almCfgMtrReversal 1 }
 
            almCfgMtrReversalPriority OBJECT-TYPE
                SYNTAX DisplayString (SIZE (0..255))
                MAX-ACCESS read-only
                STATUS mandatory
                DESCRIPTION 
                    "Alarm Configuration - Unary Meter Phase Reversal - Priority"
                ::= { almCfgMtrReversal 2 }
 
            almCfgMtrReversalDOs  OBJECT-TYPE
                SYNTAX DisplayString (SIZE (0..255))
                MAX-ACCESS read-only
                STATUS mandatory
                DESCRIPTION 
                    "Alarm Configuration - Unary Meter Phase Reversal -  Associated Digital Outputs. Bitmap of digital outputs to associate with this alarm.
Bitmap is right-justified with the least significant bit associated with digital output ID of 1."
                ::= { almCfgMtrReversal 3 }
 
 
 
        logicAlarmConfiguration OBJECT IDENTIFIER ::= { alarmsConfiguration 5 }
 
        almCfgLogic1 OBJECT IDENTIFIER ::= { logicAlarmConfiguration 1 }
 
            almCfgLogic1Label OBJECT-TYPE
                SYNTAX DisplayString (SIZE (0..255))
                MAX-ACCESS read-only
                STATUS mandatory
                DESCRIPTION 
                    "Alarm Configuration - Logic 1 - Label"
                ::= { almCfgLogic1 1 }
 
            almCfgLogic1EnableDisable OBJECT-TYPE
                SYNTAX DisplayString (SIZE (0..255))
                MAX-ACCESS read-only
                STATUS mandatory
                DESCRIPTION 
                    "Alarm Configuration - Logic 1 - Enabled / Disabled"
                ::= { almCfgLogic1 2 }
 
            almCfgLogic1Priority OBJECT-TYPE
                SYNTAX DisplayString (SIZE (0..255))
                MAX-ACCESS read-only
                STATUS mandatory
                DESCRIPTION 
                    "Alarm Configuration - Logic 1 - Priority"
                ::= { almCfgLogic1 3 }
 
            almCfgLogic1Type OBJECT-TYPE
                SYNTAX DisplayString (SIZE (0..255))
                MAX-ACCESS read-only
                STATUS mandatory
                DESCRIPTION 
                    "Alarm Configuration - Logic 1 - Type"
                ::= { almCfgLogic1 4 }
 
            almCfgLogic1Input1 OBJECT-TYPE
                SYNTAX DisplayString (SIZE (0..255))
                MAX-ACCESS read-only
                STATUS mandatory
                DESCRIPTION 
                    "Alarm Configuration - Logic 1 - Input 1"
                ::= { almCfgLogic1 5 }
 
            almCfgLogic1Input2 OBJECT-TYPE
                SYNTAX DisplayString (SIZE (0..255))
                MAX-ACCESS read-only
                STATUS mandatory
                DESCRIPTION 
                    "Alarm Configuration - Logic 1 - Input 2"
                ::= { almCfgLogic1 6 }
 
            almCfgLogic1Input3 OBJECT-TYPE
                SYNTAX DisplayString (SIZE (0..255))
                MAX-ACCESS read-only
                STATUS mandatory
                DESCRIPTION 
                    "Alarm Configuration - Logic 1 - Input 3"
                ::= { almCfgLogic1 7 }
 
            almCfgLogic1Input4 OBJECT-TYPE
                SYNTAX DisplayString (SIZE (0..255))
                MAX-ACCESS read-only
                STATUS mandatory
                DESCRIPTION 
                    "Alarm Configuration - Logic 1 - Input 4"
                ::= { almCfgLogic1 8 }
 
            almCfgLogic1DOs   OBJECT-TYPE
                SYNTAX DisplayString (SIZE (0..255))
                MAX-ACCESS read-only
                STATUS mandatory
                DESCRIPTION 
                    "Alarm Configuration - Logic 1 - Associated Digital Outputs. Bitmap of digital outputs to associate with this alarm.
Bitmap is right-justified with the least significant bit associated with digital output ID of 1."
                ::= { almCfgLogic1 9 }
 
 
        almCfgLogic2 OBJECT IDENTIFIER ::= { logicAlarmConfiguration 2 }
 
            almCfgLogic2Label OBJECT-TYPE
                SYNTAX DisplayString (SIZE (0..255))
                MAX-ACCESS read-only
                STATUS mandatory
                DESCRIPTION 
                    "Alarm Configuration - Logic 2 - Label"
                ::= { almCfgLogic2 1 }
 
            almCfgLogic2EnableDisable OBJECT-TYPE
                SYNTAX DisplayString (SIZE (0..255))
                MAX-ACCESS read-only
                STATUS mandatory
                DESCRIPTION 
                    "Alarm Configuration - Logic 2 - Enabled / Disabled"
                ::= { almCfgLogic2 2 }
 
            almCfgLogic2Priority OBJECT-TYPE
                SYNTAX DisplayString (SIZE (0..255))
                MAX-ACCESS read-only
                STATUS mandatory
                DESCRIPTION 
                    "Alarm Configuration - Logic 2 - Priority"
                ::= { almCfgLogic2 3 }
 
            almCfgLogic2Type OBJECT-TYPE
                SYNTAX DisplayString (SIZE (0..255))
                MAX-ACCESS read-only
                STATUS mandatory
                DESCRIPTION 
                    "Alarm Configuration - Logic 2 - Type"
                ::= { almCfgLogic2 4 }
 
            almCfgLogic2Input1 OBJECT-TYPE
                SYNTAX DisplayString (SIZE (0..255))
                MAX-ACCESS read-only
                STATUS mandatory
                DESCRIPTION 
                    "Alarm Configuration - Logic 2 - Input 1"
                ::= { almCfgLogic2 5 }
 
            almCfgLogic2Input2 OBJECT-TYPE
                SYNTAX DisplayString (SIZE (0..255))
                MAX-ACCESS read-only
                STATUS mandatory
                DESCRIPTION 
                    "Alarm Configuration - Logic 2 - Input 2"
                ::= { almCfgLogic2 6 }
 
            almCfgLogic2Input3 OBJECT-TYPE
                SYNTAX DisplayString (SIZE (0..255))
                MAX-ACCESS read-only
                STATUS mandatory
                DESCRIPTION 
                    "Alarm Configuration - Logic 2 - Input 3"
                ::= { almCfgLogic2 7 }
 
            almCfgLogic2Input4 OBJECT-TYPE
                SYNTAX DisplayString (SIZE (0..255))
                MAX-ACCESS read-only
                STATUS mandatory
                DESCRIPTION 
                    "Alarm Configuration - Logic 2 - Input 4"
                ::= { almCfgLogic2 8 }
 
            almCfgLogic2DOs   OBJECT-TYPE
                SYNTAX DisplayString (SIZE (0..255))
                MAX-ACCESS read-only
                STATUS mandatory
                DESCRIPTION 
                    "Alarm Configuration - Logic 2 - Associated Digital Outputs. Bitmap of digital outputs to associate with this alarm.
Bitmap is right-justified with the least significant bit associated with digital output ID of 1."
                ::= { almCfgLogic2 9 }
 
 
        almCfgLogic3 OBJECT IDENTIFIER ::= { logicAlarmConfiguration 3 }
 
            almCfgLogic3Label OBJECT-TYPE
                SYNTAX DisplayString (SIZE (0..255))
                MAX-ACCESS read-only
                STATUS mandatory
                DESCRIPTION 
                    "Alarm Configuration - Logic 3 - Label"
                ::= { almCfgLogic3 1 }
 
            almCfgLogic3EnableDisable OBJECT-TYPE
                SYNTAX DisplayString (SIZE (0..255))
                MAX-ACCESS read-only
                STATUS mandatory
                DESCRIPTION 
                    "Alarm Configuration - Logic 3 - Enabled / Disabled"
                ::= { almCfgLogic3 2 }
 
            almCfgLogic3Priority OBJECT-TYPE
                SYNTAX DisplayString (SIZE (0..255))
                MAX-ACCESS read-only
                STATUS mandatory
                DESCRIPTION 
                    "Alarm Configuration - Logic 3 - Priority"
                ::= { almCfgLogic3 3 }
 
            almCfgLogic3Type OBJECT-TYPE
                SYNTAX DisplayString (SIZE (0..255))
                MAX-ACCESS read-only
                STATUS mandatory
                DESCRIPTION 
                    "Alarm Configuration - Logic 3 - Type"
                ::= { almCfgLogic3 4 }
 
            almCfgLogic3Input1 OBJECT-TYPE
                SYNTAX DisplayString (SIZE (0..255))
                MAX-ACCESS read-only
                STATUS mandatory
                DESCRIPTION 
                    "Alarm Configuration - Logic 3 - Input 1"
                ::= { almCfgLogic3 5 }
 
            almCfgLogic3Input2 OBJECT-TYPE
                SYNTAX DisplayString (SIZE (0..255))
                MAX-ACCESS read-only
                STATUS mandatory
                DESCRIPTION 
                    "Alarm Configuration - Logic 3 - Input 2"
                ::= { almCfgLogic3 6 }
 
            almCfgLogic3Input3 OBJECT-TYPE
                SYNTAX DisplayString (SIZE (0..255))
                MAX-ACCESS read-only
                STATUS mandatory
                DESCRIPTION 
                    "Alarm Configuration - Logic 3 - Input 3"
                ::= { almCfgLogic3 7 }
 
            almCfgLogic3Input4 OBJECT-TYPE
                SYNTAX DisplayString (SIZE (0..255))
                MAX-ACCESS read-only
                STATUS mandatory
                DESCRIPTION 
                    "Alarm Configuration - Logic 3 - Input 4"
                ::= { almCfgLogic3 8 }
 
            almCfgLogic3DOs   OBJECT-TYPE
                SYNTAX DisplayString (SIZE (0..255))
                MAX-ACCESS read-only
                STATUS mandatory
                DESCRIPTION 
                    "Alarm Configuration - Logic 3 - Associated Digital Outputs. Bitmap of digital outputs to associate with this alarm.
Bitmap is right-justified with the least significant bit associated with digital output ID of 1."
                ::= { almCfgLogic3 9 }
 
 
        almCfgLogic4 OBJECT IDENTIFIER ::= { logicAlarmConfiguration 4 }
 
            almCfgLogic4Label OBJECT-TYPE
                SYNTAX DisplayString (SIZE (0..255))
                MAX-ACCESS read-only
                STATUS mandatory
                DESCRIPTION 
                    "Alarm Configuration - Logic 4 - Label"
                ::= { almCfgLogic4 1 }
 
            almCfgLogic4EnableDisable OBJECT-TYPE
                SYNTAX DisplayString (SIZE (0..255))
                MAX-ACCESS read-only
                STATUS mandatory
                DESCRIPTION 
                    "Alarm Configuration - Logic 4 - Enabled / Disabled"
                ::= { almCfgLogic4 2 }
 
            almCfgLogic4Priority OBJECT-TYPE
                SYNTAX DisplayString (SIZE (0..255))
                MAX-ACCESS read-only
                STATUS mandatory
                DESCRIPTION 
                    "Alarm Configuration - Logic 4 - Priority"
                ::= { almCfgLogic4 3 }
 
            almCfgLogic4Type OBJECT-TYPE
                SYNTAX DisplayString (SIZE (0..255))
                MAX-ACCESS read-only
                STATUS mandatory
                DESCRIPTION 
                    "Alarm Configuration - Logic 4 - Type"
                ::= { almCfgLogic4 4 }
 
            almCfgLogic4Input1 OBJECT-TYPE
                SYNTAX DisplayString (SIZE (0..255))
                MAX-ACCESS read-only
                STATUS mandatory
                DESCRIPTION 
                    "Alarm Configuration - Logic 4 - Input 1"
                ::= { almCfgLogic4 5 }
 
            almCfgLogic4Input2 OBJECT-TYPE
                SYNTAX DisplayString (SIZE (0..255))
                MAX-ACCESS read-only
                STATUS mandatory
                DESCRIPTION 
                    "Alarm Configuration - Logic 4 - Input 2"
                ::= { almCfgLogic4 6 }
 
            almCfgLogic4Input3 OBJECT-TYPE
                SYNTAX DisplayString (SIZE (0..255))
                MAX-ACCESS read-only
                STATUS mandatory
                DESCRIPTION 
                    "Alarm Configuration - Logic 4 - Input 3"
                ::= { almCfgLogic4 7 }
 
            almCfgLogic4Input4 OBJECT-TYPE
                SYNTAX DisplayString (SIZE (0..255))
                MAX-ACCESS read-only
                STATUS mandatory
                DESCRIPTION 
                    "Alarm Configuration - Logic 4 - Input 4"
                ::= { almCfgLogic4 8 }
 
            almCfgLogic4DOs   OBJECT-TYPE
                SYNTAX DisplayString (SIZE (0..255))
                MAX-ACCESS read-only
                STATUS mandatory
                DESCRIPTION 
                    "Alarm Configuration - Logic 4 - Associated Digital Outputs. Bitmap of digital outputs to associate with this alarm.
Bitmap is right-justified with the least significant bit associated with digital output ID of 1."
                ::= { almCfgLogic4 9 }
 
 
        almCfgLogic5 OBJECT IDENTIFIER ::= { logicAlarmConfiguration 5 }
 
            almCfgLogic5Label OBJECT-TYPE
                SYNTAX DisplayString (SIZE (0..255))
                MAX-ACCESS read-only
                STATUS mandatory
                DESCRIPTION 
                    "Alarm Configuration - Logic 5 - Label"
                ::= { almCfgLogic5 1 }
 
            almCfgLogic5EnableDisable OBJECT-TYPE
                SYNTAX DisplayString (SIZE (0..255))
                MAX-ACCESS read-only
                STATUS mandatory
                DESCRIPTION 
                    "Alarm Configuration - Logic 5 - Enabled / Disabled"
                ::= { almCfgLogic5 2 }
 
            almCfgLogic5Priority OBJECT-TYPE
                SYNTAX DisplayString (SIZE (0..255))
                MAX-ACCESS read-only
                STATUS mandatory
                DESCRIPTION 
                    "Alarm Configuration - Logic 5 - Priority"
                ::= { almCfgLogic5 3 }
 
            almCfgLogic5Type OBJECT-TYPE
                SYNTAX DisplayString (SIZE (0..255))
                MAX-ACCESS read-only
                STATUS mandatory
                DESCRIPTION 
                    "Alarm Configuration - Logic 5 - Type"
                ::= { almCfgLogic5 4 }
 
            almCfgLogic5Input1 OBJECT-TYPE
                SYNTAX DisplayString (SIZE (0..255))
                MAX-ACCESS read-only
                STATUS mandatory
                DESCRIPTION 
                    "Alarm Configuration - Logic 5 - Input 1"
                ::= { almCfgLogic5 5 }
 
            almCfgLogic5Input2 OBJECT-TYPE
                SYNTAX DisplayString (SIZE (0..255))
                MAX-ACCESS read-only
                STATUS mandatory
                DESCRIPTION 
                    "Alarm Configuration - Logic 5 - Input 2"
                ::= { almCfgLogic5 6 }
 
            almCfgLogic5Input3 OBJECT-TYPE
                SYNTAX DisplayString (SIZE (0..255))
                MAX-ACCESS read-only
                STATUS mandatory
                DESCRIPTION 
                    "Alarm Configuration - Logic 5 - Input 3"
                ::= { almCfgLogic5 7 }
 
            almCfgLogic5Input4 OBJECT-TYPE
                SYNTAX DisplayString (SIZE (0..255))
                MAX-ACCESS read-only
                STATUS mandatory
                DESCRIPTION 
                    "Alarm Configuration - Logic 5 - Input 4"
                ::= { almCfgLogic5 8 }
 
            almCfgLogic5DOs   OBJECT-TYPE
                SYNTAX DisplayString (SIZE (0..255))
                MAX-ACCESS read-only
                STATUS mandatory
                DESCRIPTION 
                    "Alarm Configuration - Logic 5 - Associated Digital Outputs. Bitmap of digital outputs to associate with this alarm.
Bitmap is right-justified with the least significant bit associated with digital output ID of 1."
                ::= { almCfgLogic5 9 }
 
 
        almCfgLogic6 OBJECT IDENTIFIER ::= { logicAlarmConfiguration 6 }
 
            almCfgLogic6Label OBJECT-TYPE
                SYNTAX DisplayString (SIZE (0..255))
                MAX-ACCESS read-only
                STATUS mandatory
                DESCRIPTION 
                    "Alarm Configuration - Logic 6 - Label"
                ::= { almCfgLogic6 1 }
 
            almCfgLogic6EnableDisable OBJECT-TYPE
                SYNTAX DisplayString (SIZE (0..255))
                MAX-ACCESS read-only
                STATUS mandatory
                DESCRIPTION 
                    "Alarm Configuration - Logic 6 - Enabled / Disabled"
                ::= { almCfgLogic6 2 }
 
            almCfgLogic6Priority OBJECT-TYPE
                SYNTAX DisplayString (SIZE (0..255))
                MAX-ACCESS read-only
                STATUS mandatory
                DESCRIPTION 
                    "Alarm Configuration - Logic 6 - Priority"
                ::= { almCfgLogic6 3 }
 
            almCfgLogic6Type OBJECT-TYPE
                SYNTAX DisplayString (SIZE (0..255))
                MAX-ACCESS read-only
                STATUS mandatory
                DESCRIPTION 
                    "Alarm Configuration - Logic 6 - Type"
                ::= { almCfgLogic6 4 }
 
            almCfgLogic6Input1 OBJECT-TYPE
                SYNTAX DisplayString (SIZE (0..255))
                MAX-ACCESS read-only
                STATUS mandatory
                DESCRIPTION 
                    "Alarm Configuration - Logic 6 - Input 1"
                ::= { almCfgLogic6 5 }
 
            almCfgLogic6Input2 OBJECT-TYPE
                SYNTAX DisplayString (SIZE (0..255))
                MAX-ACCESS read-only
                STATUS mandatory
                DESCRIPTION 
                    "Alarm Configuration - Logic 6 - Input 2"
                ::= { almCfgLogic6 6 }
 
            almCfgLogic6Input3 OBJECT-TYPE
                SYNTAX DisplayString (SIZE (0..255))
                MAX-ACCESS read-only
                STATUS mandatory
                DESCRIPTION 
                    "Alarm Configuration - Logic 6 - Input 3"
                ::= { almCfgLogic6 7 }
 
            almCfgLogic6Input4 OBJECT-TYPE
                SYNTAX DisplayString (SIZE (0..255))
                MAX-ACCESS read-only
                STATUS mandatory
                DESCRIPTION 
                    "Alarm Configuration - Logic 6 - Input 4"
                ::= { almCfgLogic6 8 }
 
            almCfgLogic6DOs   OBJECT-TYPE
                SYNTAX DisplayString (SIZE (0..255))
                MAX-ACCESS read-only
                STATUS mandatory
                DESCRIPTION 
                    "Alarm Configuration - Logic 6 - Associated Digital Outputs. Bitmap of digital outputs to associate with this alarm.
Bitmap is right-justified with the least significant bit associated with digital output ID of 1."
                ::= { almCfgLogic6 9 }
 
 
        almCfgLogic7 OBJECT IDENTIFIER ::= { logicAlarmConfiguration 7 }
 
            almCfgLogic7Label OBJECT-TYPE
                SYNTAX DisplayString (SIZE (0..255))
                MAX-ACCESS read-only
                STATUS mandatory
                DESCRIPTION 
                    "Alarm Configuration - Logic 7 - Label"
                ::= { almCfgLogic7 1 }
 
            almCfgLogic7EnableDisable OBJECT-TYPE
                SYNTAX DisplayString (SIZE (0..255))
                MAX-ACCESS read-only
                STATUS mandatory
                DESCRIPTION 
                    "Alarm Configuration - Logic 7 - Enabled / Disabled"
                ::= { almCfgLogic7 2 }
 
            almCfgLogic7Priority OBJECT-TYPE
                SYNTAX DisplayString (SIZE (0..255))
                MAX-ACCESS read-only
                STATUS mandatory
                DESCRIPTION 
                    "Alarm Configuration - Logic 7 - Priority"
                ::= { almCfgLogic7 3 }
 
            almCfgLogic7Type OBJECT-TYPE
                SYNTAX DisplayString (SIZE (0..255))
                MAX-ACCESS read-only
                STATUS mandatory
                DESCRIPTION 
                    "Alarm Configuration - Logic 7 - Type"
                ::= { almCfgLogic7 4 }
 
            almCfgLogic7Input1 OBJECT-TYPE
                SYNTAX DisplayString (SIZE (0..255))
                MAX-ACCESS read-only
                STATUS mandatory
                DESCRIPTION 
                    "Alarm Configuration - Logic 7 - Input 1"
                ::= { almCfgLogic7 5 }
 
            almCfgLogic7Input2 OBJECT-TYPE
                SYNTAX DisplayString (SIZE (0..255))
                MAX-ACCESS read-only
                STATUS mandatory
                DESCRIPTION 
                    "Alarm Configuration - Logic 7 - Input 2"
                ::= { almCfgLogic7 6 }
 
            almCfgLogic7Input3 OBJECT-TYPE
                SYNTAX DisplayString (SIZE (0..255))
                MAX-ACCESS read-only
                STATUS mandatory
                DESCRIPTION 
                    "Alarm Configuration - Logic 7 - Input 3"
                ::= { almCfgLogic7 7 }
 
            almCfgLogic7Input4 OBJECT-TYPE
                SYNTAX DisplayString (SIZE (0..255))
                MAX-ACCESS read-only
                STATUS mandatory
                DESCRIPTION 
                    "Alarm Configuration - Logic 7 - Input 4"
                ::= { almCfgLogic7 8 }
 
            almCfgLogic7DOs   OBJECT-TYPE
                SYNTAX DisplayString (SIZE (0..255))
                MAX-ACCESS read-only
                STATUS mandatory
                DESCRIPTION 
                    "Alarm Configuration - Logic 7 - Associated Digital Outputs. Bitmap of digital outputs to associate with this alarm.
Bitmap is right-justified with the least significant bit associated with digital output ID of 1."
                ::= { almCfgLogic7 9 }
 
 
        almCfgLogic8 OBJECT IDENTIFIER ::= { logicAlarmConfiguration 8 }
 
            almCfgLogic8Label OBJECT-TYPE
                SYNTAX DisplayString (SIZE (0..255))
                MAX-ACCESS read-only
                STATUS mandatory
                DESCRIPTION 
                    "Alarm Configuration - Logic 8 - Label"
                ::= { almCfgLogic8 1 }
 
            almCfgLogic8EnableDisable OBJECT-TYPE
                SYNTAX DisplayString (SIZE (0..255))
                MAX-ACCESS read-only
                STATUS mandatory
                DESCRIPTION 
                    "Alarm Configuration - Logic 8 - Enabled / Disabled"
                ::= { almCfgLogic8 2 }
 
            almCfgLogic8Priority OBJECT-TYPE
                SYNTAX DisplayString (SIZE (0..255))
                MAX-ACCESS read-only
                STATUS mandatory
                DESCRIPTION 
                    "Alarm Configuration - Logic 8 - Priority"
                ::= { almCfgLogic8 3 }
 
            almCfgLogic8Type OBJECT-TYPE
                SYNTAX DisplayString (SIZE (0..255))
                MAX-ACCESS read-only
                STATUS mandatory
                DESCRIPTION 
                    "Alarm Configuration - Logic 8 - Type"
                ::= { almCfgLogic8 4 }
 
            almCfgLogic8Input1 OBJECT-TYPE
                SYNTAX DisplayString (SIZE (0..255))
                MAX-ACCESS read-only
                STATUS mandatory
                DESCRIPTION 
                    "Alarm Configuration - Logic 8 - Input 1"
                ::= { almCfgLogic8 5 }
 
            almCfgLogic8Input2 OBJECT-TYPE
                SYNTAX DisplayString (SIZE (0..255))
                MAX-ACCESS read-only
                STATUS mandatory
                DESCRIPTION 
                    "Alarm Configuration - Logic 8 - Input 2"
                ::= { almCfgLogic8 6 }
 
            almCfgLogic8Input3 OBJECT-TYPE
                SYNTAX DisplayString (SIZE (0..255))
                MAX-ACCESS read-only
                STATUS mandatory
                DESCRIPTION 
                    "Alarm Configuration - Logic 8 - Input 3"
                ::= { almCfgLogic8 7 }
 
            almCfgLogic8Input4 OBJECT-TYPE
                SYNTAX DisplayString (SIZE (0..255))
                MAX-ACCESS read-only
                STATUS mandatory
                DESCRIPTION 
                    "Alarm Configuration - Logic 8 - Input 4"
                ::= { almCfgLogic8 8 }
 
            almCfgLogic8DOs   OBJECT-TYPE
                SYNTAX DisplayString (SIZE (0..255))
                MAX-ACCESS read-only
                STATUS mandatory
                DESCRIPTION 
                    "Alarm Configuration - Logic 8 - Associated Digital Outputs. Bitmap of digital outputs to associate with this alarm.
Bitmap is right-justified with the least significant bit associated with digital output ID of 1."
                ::= { almCfgLogic8 9 }
 
 
        almCfgLogic9 OBJECT IDENTIFIER ::= { logicAlarmConfiguration 9 }
 
            almCfgLogic9Label OBJECT-TYPE
                SYNTAX DisplayString (SIZE (0..255))
                MAX-ACCESS read-only
                STATUS mandatory
                DESCRIPTION 
                    "Alarm Configuration - Logic 9 - Label"
                ::= { almCfgLogic9 1 }
 
            almCfgLogic9EnableDisable OBJECT-TYPE
                SYNTAX DisplayString (SIZE (0..255))
                MAX-ACCESS read-only
                STATUS mandatory
                DESCRIPTION 
                    "Alarm Configuration - Logic 9 - Enabled / Disabled"
                ::= { almCfgLogic9 2 }
 
            almCfgLogic9Priority OBJECT-TYPE
                SYNTAX DisplayString (SIZE (0..255))
                MAX-ACCESS read-only
                STATUS mandatory
                DESCRIPTION 
                    "Alarm Configuration - Logic 9 - Priority"
                ::= { almCfgLogic9 3 }
 
            almCfgLogic9Type OBJECT-TYPE
                SYNTAX DisplayString (SIZE (0..255))
                MAX-ACCESS read-only
                STATUS mandatory
                DESCRIPTION 
                    "Alarm Configuration - Logic 9 - Type"
                ::= { almCfgLogic9 4 }
 
            almCfgLogic9Input1 OBJECT-TYPE
                SYNTAX DisplayString (SIZE (0..255))
                MAX-ACCESS read-only
                STATUS mandatory
                DESCRIPTION 
                    "Alarm Configuration - Logic 9 - Input 1"
                ::= { almCfgLogic9 5 }
 
            almCfgLogic9Input2 OBJECT-TYPE
                SYNTAX DisplayString (SIZE (0..255))
                MAX-ACCESS read-only
                STATUS mandatory
                DESCRIPTION 
                    "Alarm Configuration - Logic 9 - Input 2"
                ::= { almCfgLogic9 6 }
 
            almCfgLogic9Input3 OBJECT-TYPE
                SYNTAX DisplayString (SIZE (0..255))
                MAX-ACCESS read-only
                STATUS mandatory
                DESCRIPTION 
                    "Alarm Configuration - Logic 9 - Input 3"
                ::= { almCfgLogic9 7 }
 
            almCfgLogic9Input4 OBJECT-TYPE
                SYNTAX DisplayString (SIZE (0..255))
                MAX-ACCESS read-only
                STATUS mandatory
                DESCRIPTION 
                    "Alarm Configuration - Logic 9 - Input 4"
                ::= { almCfgLogic9 8 }
 
            almCfgLogic9DOs   OBJECT-TYPE
                SYNTAX DisplayString (SIZE (0..255))
                MAX-ACCESS read-only
                STATUS mandatory
                DESCRIPTION 
                    "Alarm Configuration - Logic 9 - Associated Digital Outputs. Bitmap of digital outputs to associate with this alarm.
Bitmap is right-justified with the least significant bit associated with digital output ID of 1."
                ::= { almCfgLogic9 9 }
 
 
        almCfgLogic10 OBJECT IDENTIFIER ::= { logicAlarmConfiguration 10 }
 
            almCfgLogic10Label OBJECT-TYPE
                SYNTAX DisplayString (SIZE (0..255))
                MAX-ACCESS read-only
                STATUS mandatory
                DESCRIPTION 
                    "Alarm Configuration - Logic 10 - Label"
                ::= { almCfgLogic10 1 }
 
            almCfgLogic10EnableDisable OBJECT-TYPE
                SYNTAX DisplayString (SIZE (0..255))
                MAX-ACCESS read-only
                STATUS mandatory
                DESCRIPTION 
                    "Alarm Configuration - Logic 10 - Enabled / Disabled"
                ::= { almCfgLogic10 2 }
 
            almCfgLogic10Priority OBJECT-TYPE
                SYNTAX DisplayString (SIZE (0..255))
                MAX-ACCESS read-only
                STATUS mandatory
                DESCRIPTION 
                    "Alarm Configuration - Logic 10 - Priority"
                ::= { almCfgLogic10 3 }
 
            almCfgLogic10Type OBJECT-TYPE
                SYNTAX DisplayString (SIZE (0..255))
                MAX-ACCESS read-only
                STATUS mandatory
                DESCRIPTION 
                    "Alarm Configuration - Logic 10 - Type"
                ::= { almCfgLogic10 4 }
 
            almCfgLogic10Input1 OBJECT-TYPE
                SYNTAX DisplayString (SIZE (0..255))
                MAX-ACCESS read-only
                STATUS mandatory
                DESCRIPTION 
                    "Alarm Configuration - Logic 10 - Input 1"
                ::= { almCfgLogic10 5 }
 
            almCfgLogic10Input2 OBJECT-TYPE
                SYNTAX DisplayString (SIZE (0..255))
                MAX-ACCESS read-only
                STATUS mandatory
                DESCRIPTION 
                    "Alarm Configuration - Logic 10 - Input 2"
                ::= { almCfgLogic10 6 }
 
            almCfgLogic10Input3 OBJECT-TYPE
                SYNTAX DisplayString (SIZE (0..255))
                MAX-ACCESS read-only
                STATUS mandatory
                DESCRIPTION 
                    "Alarm Configuration - Logic 10 - Input 3"
                ::= { almCfgLogic10 7 }
 
            almCfgLogic10Input4 OBJECT-TYPE
                SYNTAX DisplayString (SIZE (0..255))
                MAX-ACCESS read-only
                STATUS mandatory
                DESCRIPTION 
                    "Alarm Configuration - Logic 10 - Input 4"
                ::= { almCfgLogic10 8 }
 
            almCfgLogic10DOs   OBJECT-TYPE
                SYNTAX DisplayString (SIZE (0..255))
                MAX-ACCESS read-only
                STATUS mandatory
                DESCRIPTION 
                    "Alarm Configuration - Logic 10 - Associated Digital Outputs. Bitmap of digital outputs to associate with this alarm.
Bitmap is right-justified with the least significant bit associated with digital output ID of 1."
                ::= { almCfgLogic10 9 }
 
 
 
 
        alarmBitmapsActivated OBJECT IDENTIFIER ::= { alarms 2 }
 
            almBitmapsActivatedStd_1to16 OBJECT-TYPE
                SYNTAX DisplayString (SIZE (0..255))
                MAX-ACCESS read-only
                STATUS mandatory
                DESCRIPTION 
                    "Activated Alarms Bitmap - Standard 1 Second Alarms (1-16)"
                ::= { alarmBitmapsActivated 1 }
 
            almBitmapsActivatedStd_17to29 OBJECT-TYPE
                SYNTAX DisplayString (SIZE (0..255))
                MAX-ACCESS read-only
                STATUS mandatory
                DESCRIPTION 
                    "Activated Alarms Bitmap - Standard 1 Second Alarms (17-29)"
                ::= { alarmBitmapsActivated 2 }
 
            almBitmapsActivatedCustom_1to5 OBJECT-TYPE
                SYNTAX DisplayString (SIZE (0..255))
                MAX-ACCESS read-only
                STATUS mandatory
                DESCRIPTION 
                    "Activated Alarms Bitmap - Custom Alarms (1-5)"
                ::= { alarmBitmapsActivated 3 }
 
            almBitmapsActivatedDigital_S1toS4 OBJECT-TYPE
                SYNTAX DisplayString (SIZE (0..255))
                MAX-ACCESS read-only
                STATUS mandatory
                DESCRIPTION 
                    "Activated Alarms Bitmap - Digital Alarms (S1-S4)"
                ::= { alarmBitmapsActivated 4 }
 
            almBitmapsActivatedUnary_1to4 OBJECT-TYPE
                SYNTAX DisplayString (SIZE (0..255))
                MAX-ACCESS read-only
                STATUS mandatory
                DESCRIPTION 
                    "Activated Alarms Bitmap - Unary Alarms (1-4)"
                ::= { alarmBitmapsActivated 5 }
 
            almBitmapsActivatedLogical_1to10 OBJECT-TYPE
                SYNTAX DisplayString (SIZE (0..255))
                MAX-ACCESS read-only
                STATUS mandatory
                DESCRIPTION 
                    "Activated Alarms Bitmap - Logic Alarms (1-10)"
                ::= { alarmBitmapsActivated 6 }
 
 
        alarmCounters OBJECT IDENTIFIER ::= { alarms 3 }
 
        almCounterStd OBJECT IDENTIFIER ::= { alarmCounters 1 }
 
            almCounterOverCurrPh OBJECT-TYPE
                SYNTAX INTEGER (0..65535)
                MAX-ACCESS read-only
                STATUS mandatory
                DESCRIPTION 
                    "Alarm Counter - Over Current (Phase)"
                ::= { almCounterStd 1 }
 
            almCounterUnderCurrPh OBJECT-TYPE
                SYNTAX INTEGER (0..65535)
                MAX-ACCESS read-only
                STATUS mandatory
                DESCRIPTION 
                    "Alarm Counter - Under Current (Phase)"
                ::= { almCounterStd 2 }
 
            almCounterOverCurrNtrl OBJECT-TYPE
                SYNTAX INTEGER (0..65535)
                MAX-ACCESS read-only
                STATUS mandatory
                DESCRIPTION 
                    "Alarm Counter - Over Current Neutral"
                ::= { almCounterStd 3 }
 
            almCounterOverCurrGnd OBJECT-TYPE
                SYNTAX INTEGER (0..65535)
                MAX-ACCESS read-only
                STATUS mandatory
                DESCRIPTION 
                    "Alarm Counter - Over Current Ground"
                ::= { almCounterStd 4 }
 
            almCounterOverVoltLL OBJECT-TYPE
                SYNTAX INTEGER (0..65535)
                MAX-ACCESS read-only
                STATUS mandatory
                DESCRIPTION 
                    "Alarm Counter - Over Voltage L-L"
                ::= { almCounterStd 5 }
 
            almCounterUnderVoltLL OBJECT-TYPE
                SYNTAX INTEGER (0..65535)
                MAX-ACCESS read-only
                STATUS mandatory
                DESCRIPTION 
                    "Alarm Counter - Under Voltage L-L"
                ::= { almCounterStd 6 }
 
            almCounterOverVoltLN OBJECT-TYPE
                SYNTAX INTEGER (0..65535)
                MAX-ACCESS read-only
                STATUS mandatory
                DESCRIPTION 
                    "Alarm Counter - Over Voltage L-N"
                ::= { almCounterStd 7 }
 
            almCounterUnderVoltLN OBJECT-TYPE
                SYNTAX INTEGER (0..65535)
                MAX-ACCESS read-only
                STATUS mandatory
                DESCRIPTION 
                    "Alarm Counter - Under Voltage L-N"
                ::= { almCounterStd 8 }
 
            almCounterOverPwrAct OBJECT-TYPE
                SYNTAX INTEGER (0..65535)
                MAX-ACCESS read-only
                STATUS mandatory
                DESCRIPTION 
                    "Alarm Counter - Over Active Power"
                ::= { almCounterStd 9 }
 
            almCounterOverPwrReact OBJECT-TYPE
                SYNTAX INTEGER (0..65535)
                MAX-ACCESS read-only
                STATUS mandatory
                DESCRIPTION 
                    "Alarm Counter - Over Reactive Power"
                ::= { almCounterStd 10 }
 
            almCounterOverPwrApprnt OBJECT-TYPE
                SYNTAX INTEGER (0..65535)
                MAX-ACCESS read-only
                STATUS mandatory
                DESCRIPTION 
                    "Alarm Counter - Over Apparent Power"
                ::= { almCounterStd 11 }
 
            almCounterLeadPFTrue OBJECT-TYPE
                SYNTAX INTEGER (0..65535)
                MAX-ACCESS read-only
                STATUS mandatory
                DESCRIPTION 
                    "Alarm Counter - Leading Power Factor True"
                ::= { almCounterStd 12 }
 
            almCounterLagPFTrue OBJECT-TYPE
                SYNTAX INTEGER (0..65535)
                MAX-ACCESS read-only
                STATUS mandatory
                DESCRIPTION 
                    "Alarm Counter - Lagging Power Factor True"
                ::= { almCounterStd 13 }
 
            almCounterLeadPFDisp OBJECT-TYPE
                SYNTAX INTEGER (0..65535)
                MAX-ACCESS read-only
                STATUS mandatory
                DESCRIPTION 
                    "Alarm Counter - Leading Power Factor Displacement"
                ::= { almCounterStd 14 }
 
            almCounterLagPFDisp OBJECT-TYPE
                SYNTAX INTEGER (0..65535)
                MAX-ACCESS read-only
                STATUS mandatory
                DESCRIPTION 
                    "Alarm Counter - Lagging Power Factor Displacement"
                ::= { almCounterStd 15 }
 
            almCounterOverDmdActPwrPres OBJECT-TYPE
                SYNTAX INTEGER (0..65535)
                MAX-ACCESS read-only
                STATUS mandatory
                DESCRIPTION 
                    "Alarm Counter - Over Demand Active Power Present"
                ::= { almCounterStd 16 }
 
            almCounterOverDmdActPwrLast OBJECT-TYPE
                SYNTAX INTEGER (0..65535)
                MAX-ACCESS read-only
                STATUS mandatory
                DESCRIPTION 
                    "Alarm Counter - Over Demand Active Power Last"
                ::= { almCounterStd 17 }
 
            almCounterOverDmdActPwrPred OBJECT-TYPE
                SYNTAX INTEGER (0..65535)
                MAX-ACCESS read-only
                STATUS mandatory
                DESCRIPTION 
                    "Alarm Counter - Over Demand Active Power Predicted"
                ::= { almCounterStd 18 }
 
            almCounterOverDmdReactPwrPres OBJECT-TYPE
                SYNTAX INTEGER (0..65535)
                MAX-ACCESS read-only
                STATUS mandatory
                DESCRIPTION 
                    "Alarm Counter - Over Demand Reactive Power Present"
                ::= { almCounterStd 19 }
 
            almCounterOverDmdReactPwrLast OBJECT-TYPE
                SYNTAX INTEGER (0..65535)
                MAX-ACCESS read-only
                STATUS mandatory
                DESCRIPTION 
                    "Alarm Counter - Over Demand Reactive Power Last"
                ::= { almCounterStd 20 }
 
            almCounterOverDmdReactPwrPred OBJECT-TYPE
                SYNTAX INTEGER (0..65535)
                MAX-ACCESS read-only
                STATUS mandatory
                DESCRIPTION 
                    "Alarm Counter - Over Demand Reactive Power Predicted"
                ::= { almCounterStd 21 }
 
            almCounterOverDmdApprntPwrPres OBJECT-TYPE
                SYNTAX INTEGER (0..65535)
                MAX-ACCESS read-only
                STATUS mandatory
                DESCRIPTION 
                    "Alarm Counter - Over Demand Apparent Power Present"
                ::= { almCounterStd 22 }
 
            almCounterOverDmdApprntPwrLast OBJECT-TYPE
                SYNTAX INTEGER (0..65535)
                MAX-ACCESS read-only
                STATUS mandatory
                DESCRIPTION 
                    "Alarm Counter - Over Demand Apparent Power Last"
                ::= { almCounterStd 23 }
 
            almCounterOverDmdApprntPwrPred OBJECT-TYPE
                SYNTAX INTEGER (0..65535)
                MAX-ACCESS read-only
                STATUS mandatory
                DESCRIPTION 
                    "Alarm Counter - Over Demand Apparent Power Predicted"
                ::= { almCounterStd 24 }
 
            almCounterOverFreq OBJECT-TYPE
                SYNTAX INTEGER (0..65535)
                MAX-ACCESS read-only
                STATUS mandatory
                DESCRIPTION 
                    "Alarm Counter - Over Frequency"
                ::= { almCounterStd 25 }
 
            almCounterUnderFreq OBJECT-TYPE
                SYNTAX INTEGER (0..65535)
                MAX-ACCESS read-only
                STATUS mandatory
                DESCRIPTION 
                    "Alarm Counter - Under Frequency"
                ::= { almCounterStd 26 }
 
            almCounterOverVoltUnb OBJECT-TYPE
                SYNTAX INTEGER (0..65535)
                MAX-ACCESS read-only
                STATUS mandatory
                DESCRIPTION 
                    "Alarm Counter - Over Voltage Unbalance"
                ::= { almCounterStd 27 }
 
            almCounterOverVoltTotHarmDist OBJECT-TYPE
                SYNTAX INTEGER (0..65535)
                MAX-ACCESS read-only
                STATUS mandatory
                DESCRIPTION 
                    "Alarm Counter - Over Voltage Total Harmonic Distortion"
                ::= { almCounterStd 28 }
 
            almCounterPhaseLoss OBJECT-TYPE
                SYNTAX INTEGER (0..65535)
                MAX-ACCESS read-only
                STATUS mandatory
                DESCRIPTION 
                    "Alarm Counter - Phase Loss"
                ::= { almCounterStd 29 }
 
 
        almCounterCust OBJECT IDENTIFIER ::= { alarmCounters 2 }
 
            almCounterCustom1 OBJECT-TYPE
                SYNTAX INTEGER (0..65535)
                MAX-ACCESS read-only
                STATUS mandatory
                DESCRIPTION 
                    "Alarm Counter - Custom Alarm 1"
                ::= { almCounterCust 1 }
 
            almCounterCustom2 OBJECT-TYPE
                SYNTAX INTEGER (0..65535)
                MAX-ACCESS read-only
                STATUS mandatory
                DESCRIPTION 
                    "Alarm Counter - Custom Alarm 2"
                ::= { almCounterCust 2 }
 
            almCounterCustom3 OBJECT-TYPE
                SYNTAX INTEGER (0..65535)
                MAX-ACCESS read-only
                STATUS mandatory
                DESCRIPTION 
                    "Alarm Counter - Custom Alarm 3"
                ::= { almCounterCust 3 }
 
            almCounterCustom4 OBJECT-TYPE
                SYNTAX INTEGER (0..65535)
                MAX-ACCESS read-only
                STATUS mandatory
                DESCRIPTION 
                    "Alarm Counter - Custom Alarm 4"
                ::= { almCounterCust 4 }
 
            almCounterCustom5 OBJECT-TYPE
                SYNTAX INTEGER (0..65535)
                MAX-ACCESS read-only
                STATUS mandatory
                DESCRIPTION 
                    "Alarm Counter - Custom Alarm 5"
                ::= { almCounterCust 5 }
 
 
        almCounterDigital OBJECT IDENTIFIER ::= { alarmCounters 3 }
 
            almCounterDigitalS1 OBJECT-TYPE
                SYNTAX INTEGER (0..65535)
                MAX-ACCESS read-only
                STATUS mandatory
                DESCRIPTION 
                    "Alarm Counter - Digital Input S1"
                ::= { almCounterDigital 1 }
 
            almCounterDigitalS2 OBJECT-TYPE
                SYNTAX INTEGER (0..65535)
                MAX-ACCESS read-only
                STATUS mandatory
                DESCRIPTION 
                    "Alarm Counter - Digital Input S2"
                ::= { almCounterDigital 2 }
 
            almCounterDigitalS3 OBJECT-TYPE
                SYNTAX INTEGER (0..65535)
                MAX-ACCESS read-only
                STATUS mandatory
                DESCRIPTION 
                    "Alarm Counter - Digital Input S3"
                ::= { almCounterDigital 3 }
 
            almCounterDigitalS4 OBJECT-TYPE
                SYNTAX INTEGER (0..65535)
                MAX-ACCESS read-only
                STATUS mandatory
                DESCRIPTION 
                    "Alarm Counter - Digital Input S4"
                ::= { almCounterDigital 4 }
 
 
 
        almCounterUnary OBJECT IDENTIFIER ::= { alarmCounters 4 }
 
            almCounterMtrPwrUp OBJECT-TYPE
                SYNTAX INTEGER (0..65535)
                MAX-ACCESS read-only
                STATUS mandatory
                DESCRIPTION 
                    "Alarm Counter - Meter Power Up"
                ::= { almCounterUnary 1 }
 
            almCounterMtrReset OBJECT-TYPE
                SYNTAX INTEGER (0..65535)
                MAX-ACCESS read-only
                STATUS mandatory
                DESCRIPTION 
                    "Alarm Counter - Meter Reset"
                ::= { almCounterUnary 2 }
 
            almCounterMtrDiag OBJECT-TYPE
                SYNTAX INTEGER (0..65535)
                MAX-ACCESS read-only
                STATUS mandatory
                DESCRIPTION 
                    "Alarm Counter - Meter Diagnostic"
                ::= { almCounterUnary 3 }
 
            almCounterMtrReversal OBJECT-TYPE
                SYNTAX INTEGER (0..65535)
                MAX-ACCESS read-only
                STATUS mandatory
                DESCRIPTION 
                    "Alarm Counter - Meter Phase Reversal"
                ::= { almCounterUnary 4 }
 
 
        almCounterLogic OBJECT IDENTIFIER ::= { alarmCounters 5 }
 
            almCounterLogic1 OBJECT-TYPE
                SYNTAX INTEGER (0..65535)
                MAX-ACCESS read-only
                STATUS mandatory
                DESCRIPTION 
                    "Alarm Counter - Logic Alarm 1"
                ::= { almCounterLogic 1 }
 
            almCounterLogic2 OBJECT-TYPE
                SYNTAX INTEGER (0..65535)
                MAX-ACCESS read-only
                STATUS mandatory
                DESCRIPTION 
                    "Alarm Counter - Logic Alarm 2"
                ::= { almCounterLogic 2 }
 
            almCounterLogic3 OBJECT-TYPE
                SYNTAX INTEGER (0..65535)
                MAX-ACCESS read-only
                STATUS mandatory
                DESCRIPTION 
                    "Alarm Counter - Logic Alarm 3"
                ::= { almCounterLogic 3 }
 
            almCounterLogic4 OBJECT-TYPE
                SYNTAX INTEGER (0..65535)
                MAX-ACCESS read-only
                STATUS mandatory
                DESCRIPTION 
                    "Alarm Counter - Logic Alarm 4"
                ::= { almCounterLogic 4 }
 
            almCounterLogic5 OBJECT-TYPE
                SYNTAX INTEGER (0..65535)
                MAX-ACCESS read-only
                STATUS mandatory
                DESCRIPTION 
                    "Alarm Counter - Logic Alarm 5"
                ::= { almCounterLogic 5 }
 
            almCounterLogic6 OBJECT-TYPE
                SYNTAX INTEGER (0..65535)
                MAX-ACCESS read-only
                STATUS mandatory
                DESCRIPTION 
                    "Alarm Counter - Logic Alarm 6"
                ::= { almCounterLogic 6 }
 
            almCounterLogic7 OBJECT-TYPE
                SYNTAX INTEGER (0..65535)
                MAX-ACCESS read-only
                STATUS mandatory
                DESCRIPTION 
                    "Alarm Counter - Logic Alarm 7"
                ::= { almCounterLogic 7 }
 
            almCounterLogic8 OBJECT-TYPE
                SYNTAX INTEGER (0..65535)
                MAX-ACCESS read-only
                STATUS mandatory
                DESCRIPTION 
                    "Alarm Counter - Logic Alarm 8"
                ::= { almCounterLogic 8 }
 
            almCounterLogic9 OBJECT-TYPE
                SYNTAX INTEGER (0..65535)
                MAX-ACCESS read-only
                STATUS mandatory
                DESCRIPTION 
                    "Alarm Counter - Logic Alarm 9"
                ::= { almCounterLogic 9 }
 
            almCounterLogic10 OBJECT-TYPE
                SYNTAX INTEGER (0..65535)
                MAX-ACCESS read-only
                STATUS mandatory
                DESCRIPTION 
                    "Alarm Counter - Logic Alarm 10"
                ::= { almCounterLogic 10 }
 
 
 
 
        mibVersion OBJECT IDENTIFIER ::= { pm556x 6 }
 
            mibVersionInfo OBJECT-TYPE
                SYNTAX DisplayString (SIZE (0..255))
                MAX-ACCESS read-only
                STATUS mandatory
                DESCRIPTION 
                    "This object displays the correct version of MIB file to be used in conjunction with this PM556x device. Other MIB file versions may or may not correctly describe the objects shown. USERS MUST ENSURE THEY HAVE THE CORRECT VERSION OF MIB FILE THAT MATCHES THE FIRMWARE VERSION OF THIS DEVICE."
                ::= { mibVersion 1 }
 
 
trapVariables OBJECT IDENTIFIER ::= { pm556x 7 }

    alarmDateAndTime OBJECT-TYPE
        SYNTAX              DisplayString (SIZE (0..255))
        ACCESS              read-only
        STATUS              mandatory
        DESCRIPTION          "The Date and Time of the alarm state change."
        ::= { trapVariables 1 }

    alarmLabel OBJECT-TYPE
        SYNTAX              DisplayString (SIZE (0..255))
        ACCESS              read-only
        STATUS              mandatory
        DESCRIPTION         "The Descriptive Label given to the alarm"
        ::= { trapVariables 2 }

    alarmType OBJECT-TYPE
        SYNTAX              DisplayString (SIZE (0..255))
        ACCESS              read-only
        STATUS              mandatory
        DESCRIPTION         "The state of the Alarm - pickup, dropout, unary,
                            diagnostic"
        ::= { trapVariables 3 }

    alarmValue OBJECT-TYPE
        SYNTAX              DisplayString (SIZE (0..255))
        ACCESS              read-only
        STATUS              mandatory
        DESCRIPTION         "The value of the alarm when it changed state."
        ::= { trapVariables 4 }

    alarmPriority OBJECT-TYPE
        SYNTAX              DisplayString (SIZE (0..255))
        ACCESS              read-only
        STATUS              mandatory
        DESCRIPTION         "The priority defined for the alarm."
        ::= { trapVariables 5 }
pm556xOnBoardAlarmP1 TRAP-TYPE
        ENTERPRISE          pm556x
        VARIABLES           {
                                alarmDateAndTime,
                                alarmLabel,
                                alarmType,
                                alarmValue,
                                alarmPriority
                            }
        DESCRIPTION         "Indicates the Host Meter On-Board Alarm system has detected a state change of an enabled alarm with a priority of 1"
        ::= 1

    pm556xOnBoardAlarmP2 TRAP-TYPE
        ENTERPRISE          pm556x
        VARIABLES           {
                                alarmDateAndTime,
                                alarmLabel,
                                alarmType,
                                alarmValue,
                                alarmPriority
                            }
        DESCRIPTION         "Indicates the Host Meter On-Board Alarm system has detected a state change of an enabled alarm with a priority of 2"
        ::= 2

    pm556xOnBoardAlarmP3 TRAP-TYPE
        ENTERPRISE          pm556x
        VARIABLES           {
                                alarmDateAndTime,
                                alarmLabel,
                                alarmType,
                                alarmValue,
                                alarmPriority
                            }
        DESCRIPTION         "Indicates the Host Meter On-Board Alarm system has detected a state change of an enabled alarm with a priority of 3"
        ::= 3
END
