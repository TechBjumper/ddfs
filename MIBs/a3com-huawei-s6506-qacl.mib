-- ==================================================================
-- Copyright (C) 2002 by  HUAWEI TECHNOLOGIES. All rights reserved.
-- 
-- Description: HUAWEI Lan Switch s6506QACL MIB
-- Reference:
-- Version: V1.0
-- History:
--(1) Created by Sunlingge, 2001.06.29
-- ==================================================================

A3COM-HUAWEI-S6506-Qacl-MIB DEFINITIONS ::= BEGIN

IMPORTS

    RowStatus, TruthValue, MacAddress
        FROM SNMPv2-TC    

    MODULE-IDENTITY,OBJECT-TYPE,Counter32, Counter64, IpAddress
        FROM SNMPv2-SMI    

    InterfaceIndex
    	FROM IF-MIB
   
    lanSw
        FROM A3COM-HUAWEI-OID-MIB;

	 hws6506qAclMib MODULE-IDENTITY
	        LAST-UPDATED "200106290000Z"
	        ORGANIZATION ""
	        CONTACT-INFO
	        ""
	        DESCRIPTION
	        ""
	        REVISION "200106290000Z"
	        DESCRIPTION
	        ""
	        ::= { s6506  6 }

    s6506		 OBJECT IDENTIFIER ::= { lanSw 19 }

    hws6506qAclMibObject OBJECT IDENTIFIER ::= {   hws6506qAclMib 1  }

  -- TABLE: hwqAclMeterCarTable
  hwqAclMeterCarTable OBJECT-TYPE
    SYNTAX      SEQUENCE OF HwqAclMeterCarTableEntry
    MAX-ACCESS  not-accessible
    STATUS      current
    DESCRIPTION
      " CAR traffic description table "
    ::= { hws6506qAclMibObject 1 }

  hwqAclMeterCarTableEntry OBJECT-TYPE
    SYNTAX      HwqAclMeterCarTableEntry
    MAX-ACCESS  not-accessible
    STATUS      current
    DESCRIPTION
      ""
    INDEX {  
              hwqACLMeterCarName
             }
    ::= { hwqAclMeterCarTable 1 }

  HwqAclMeterCarTableEntry ::=
    SEQUENCE
    {
      hwqACLMeterCarName	OCTET STRING,
      hwqACLMeterCarValue	INTEGER,
      hwqACLMeterCarRowStatus	RowStatus
    }

  hwqACLMeterCarName OBJECT-TYPE
    SYNTAX      OCTET STRING(SIZE (1..32))
    MAX-ACCESS  read-write
    STATUS      current
    DESCRIPTION
        " Name of CAR traffic "
    ::={ hwqAclMeterCarTableEntry 1 }

  hwqACLMeterCarValue OBJECT-TYPE
    SYNTAX      INTEGER(0..131072)
    MAX-ACCESS  read-write
    STATUS      current
    DESCRIPTION
        "Max. bandwidth"
    ::={ hwqAclMeterCarTableEntry 2 }

  hwqACLMeterCarRowStatus OBJECT-TYPE
    SYNTAX      RowStatus
    MAX-ACCESS  read-create
    STATUS      current
    DESCRIPTION
        "Row operation status"
    ::={ hwqAclMeterCarTableEntry 3 }

  -- TABLE: hwqAclMeterRedTable
  hwqAclMeterRedTable OBJECT-TYPE
    SYNTAX      SEQUENCE OF HwqAclMeterRedTableEntry
    MAX-ACCESS  not-accessible
    STATUS      current
    DESCRIPTION
      " Traffic description table"
    ::= { hws6506qAclMibObject 2 }

  hwqAclMeterRedTableEntry OBJECT-TYPE
    SYNTAX      HwqAclMeterRedTableEntry
    MAX-ACCESS  not-accessible
    STATUS      current
    DESCRIPTION
      ""
    INDEX {  
              hwqACLMeterRedName
             }
    ::= { hwqAclMeterRedTable 1 }

  HwqAclMeterRedTableEntry ::=
    SEQUENCE
    {
      hwqACLMeterRedName	OCTET STRING,
      hwqACLMeterStartQueue	INTEGER,
      hwqACLMeterStopQueue	INTEGER,
      hwqACLMeterProbability	INTEGER,
      hwqACLMeterRedRowStatus	RowStatus
    }

  hwqACLMeterRedName OBJECT-TYPE
    SYNTAX      OCTET STRING(SIZE (1..32))
    MAX-ACCESS  read-write
    STATUS      current
    DESCRIPTION
        " Traffic name"
    ::={ hwqAclMeterRedTableEntry 1 }

  hwqACLMeterStartQueue OBJECT-TYPE
    SYNTAX      INTEGER(0..16383)
    MAX-ACCESS  read-write
    STATUS      current
    DESCRIPTION
        "Start of queue length"
    ::={ hwqAclMeterRedTableEntry 2 }

  hwqACLMeterStopQueue OBJECT-TYPE
    SYNTAX      INTEGER(0..16383)
    MAX-ACCESS  read-write
    STATUS      current
    DESCRIPTION
        "End of queue length"
    ::={ hwqAclMeterRedTableEntry 3 }

  hwqACLMeterProbability OBJECT-TYPE
    SYNTAX      INTEGER(0..100)
    MAX-ACCESS  read-write
    STATUS      current
    DESCRIPTION
        "Drop probability"
    ::={ hwqAclMeterRedTableEntry 4 }

  hwqACLMeterRedRowStatus OBJECT-TYPE
    SYNTAX      RowStatus
    MAX-ACCESS  read-create
    STATUS      current
    DESCRIPTION
        "Row operation status"
    ::={ hwqAclMeterRedTableEntry 5 }

  -- TABLE: hwqAclMeterBandWidthTable
  hwqAclMeterBandWidthTable OBJECT-TYPE
    SYNTAX      SEQUENCE OF HwqAclMeterBandWidthTableEntry
    MAX-ACCESS  not-accessible
    STATUS      current
    DESCRIPTION
      " Traffic description table"
    ::= { hws6506qAclMibObject 3 }

  hwqAclMeterBandWidthTableEntry OBJECT-TYPE
    SYNTAX      HwqAclMeterBandWidthTableEntry
    MAX-ACCESS  not-accessible
    STATUS      current
    DESCRIPTION
      ""
    INDEX {  
              hwqACLMeterBandWidthName
             }
    ::= { hwqAclMeterBandWidthTable 1 }

  HwqAclMeterBandWidthTableEntry ::=
    SEQUENCE
    {
      hwqACLMeterBandWidthName	OCTET STRING,
      hwqACLMeterMaxBandWidth	INTEGER,
      hwqACLMeterMinBandWidth	INTEGER,
      hwqACLMeterWeight	INTEGER,
      hwqACLMeterBandWidthRowStatus	RowStatus
    }

  hwqACLMeterBandWidthName OBJECT-TYPE
    SYNTAX      OCTET STRING(SIZE (1..32))
    MAX-ACCESS  read-write
    STATUS      current
    DESCRIPTION
        " Traffic name"
    ::={ hwqAclMeterBandWidthTableEntry 1 }

  hwqACLMeterMaxBandWidth OBJECT-TYPE
    SYNTAX      INTEGER(0..131072)
    MAX-ACCESS  read-write
    STATUS      current
    DESCRIPTION
        "Max. bandwidth"
    ::={ hwqAclMeterBandWidthTableEntry 2 }

  hwqACLMeterMinBandWidth OBJECT-TYPE
    SYNTAX      INTEGER(0..131072)
    MAX-ACCESS  read-write
    STATUS      current
    DESCRIPTION
        "Min. bandwidth"
    ::={ hwqAclMeterBandWidthTableEntry 3 }

  hwqACLMeterWeight OBJECT-TYPE
    SYNTAX      INTEGER(1..100)
    MAX-ACCESS  read-write
    STATUS      current
    DESCRIPTION
        "Weight"
    ::={ hwqAclMeterBandWidthTableEntry 4 }

  hwqACLMeterBandWidthRowStatus OBJECT-TYPE
    SYNTAX      RowStatus
    MAX-ACCESS  read-create
    STATUS      current
    DESCRIPTION
        "Row operation status"
    ::={ hwqAclMeterBandWidthTableEntry 5 }

  -- TABLE: hwqAclActionTable
  hwqAclActionTable OBJECT-TYPE
    SYNTAX      SEQUENCE OF HwqAclActionTableEntry
    MAX-ACCESS  not-accessible
    STATUS      current
    DESCRIPTION
      " Action description table  "
    ::= { hws6506qAclMibObject 4 }

  hwqAclActionTableEntry OBJECT-TYPE
    SYNTAX      HwqAclActionTableEntry
    MAX-ACCESS  not-accessible
    STATUS      current
    DESCRIPTION
      ""
    INDEX {  
              hwqACLActionName
             }
    ::= { hwqAclActionTable 1 }

  HwqAclActionTableEntry ::=
    SEQUENCE
    {
      hwqACLActionName	OCTET STRING,
      hwqACLActionDSCP	INTEGER,
      hwqACLActionPriQueue	INTEGER,
      hwqACLActionGatherFlag	INTEGER,
      hwqACLActionCarName	OCTET STRING,
      hwqACLActionRedName	OCTET STRING,
      hwqACLActionBandWidthName	OCTET STRING,
      hwqACLActionRowStatus	RowStatus
    }

  hwqACLActionName OBJECT-TYPE
    SYNTAX      OCTET STRING(SIZE (1..32))
    MAX-ACCESS  read-write
    STATUS      current
    DESCRIPTION
        "Action name"
    ::={ hwqAclActionTableEntry 1 }

  hwqACLActionDSCP OBJECT-TYPE
    SYNTAX      INTEGER(0..63 | 65535)
    MAX-ACCESS  read-write
    STATUS      current
    DESCRIPTION
        " DSCP value: EF: Expedited Fowarding  (0), AF1: Assured Forwarding 1  (10), AF2: Assured Forwarding 2  (18), AF3: Assured Forwarding 3  (26), AF4: Assured Forwarding 4  (34), BE: Best Effort (46) and other values are available. When it is 65535, it indicates that no setting is made. "
    ::={ hwqAclActionTableEntry 2 }

  hwqACLActionPriQueue OBJECT-TYPE
    SYNTAX      INTEGER(0..7 | 65535)
    MAX-ACCESS  read-write
    STATUS      current
    DESCRIPTION
        "Queue priority. When it takes 65535, it indicates that no priority is configured."
    ::={ hwqAclActionTableEntry 3 }

  hwqACLActionGatherFlag OBJECT-TYPE
    SYNTAX      INTEGER{notgather    (0),gather    (1)}
    MAX-ACCESS  read-write
    STATUS      current
    DESCRIPTION
        "Gather flags"
    ::={ hwqAclActionTableEntry 4 }

  hwqACLActionCarName OBJECT-TYPE
    SYNTAX      OCTET STRING(SIZE(0..32))
    MAX-ACCESS  read-write
    STATUS      current
    DESCRIPTION
        "CAR name "
    ::={ hwqAclActionTableEntry 5 }

  hwqACLActionRedName OBJECT-TYPE
    SYNTAX      OCTET STRING(SIZE(0..32))
    MAX-ACCESS  read-write
    STATUS      current
    DESCRIPTION
        "RED name "
    ::={ hwqAclActionTableEntry 6 }

  hwqACLActionBandWidthName OBJECT-TYPE
    SYNTAX      OCTET STRING(SIZE(0..32))
    MAX-ACCESS  read-write
    STATUS      current
    DESCRIPTION
        "Bandwidth name "
    ::={ hwqAclActionTableEntry 7 }

  hwqACLActionRowStatus OBJECT-TYPE
    SYNTAX      RowStatus
    MAX-ACCESS  read-create
    STATUS      current
    DESCRIPTION
        "Row operation status"
    ::={ hwqAclActionTableEntry 8 }

  -- TABLE: hwqAclPortAttrSchedulTable
  hwqAclPortAttrSchedulTable OBJECT-TYPE
    SYNTAX      SEQUENCE OF HwqAclPortAttrSchedulTableEntry
    MAX-ACCESS  not-accessible
    STATUS      current
    DESCRIPTION
      "Port attributes table"
    ::= { hws6506qAclMibObject 5 }

  hwqAclPortAttrSchedulTableEntry OBJECT-TYPE
    SYNTAX      HwqAclPortAttrSchedulTableEntry
    MAX-ACCESS  not-accessible
    STATUS      current
    DESCRIPTION
      ""
    INDEX {  
              hwqACLPortAttrSchedulPort
             }
    ::= { hwqAclPortAttrSchedulTable 1 }

  HwqAclPortAttrSchedulTableEntry ::=
    SEQUENCE
    {
      hwqACLPortAttrSchedulPort	OCTET STRING,
      hwqACLPortAttrSchedulMode	INTEGER,
      hwqACLPortAttrSchedulRowStatus	RowStatus
    }

  hwqACLPortAttrSchedulPort OBJECT-TYPE
    SYNTAX      OCTET STRING(SIZE(1..32))
    MAX-ACCESS  read-write
    STATUS      current
    DESCRIPTION
        "Port name"
    ::={ hwqAclPortAttrSchedulTableEntry 1 }

  hwqACLPortAttrSchedulMode OBJECT-TYPE
    SYNTAX      INTEGER{zero    (0),one    (1),two    (2)}
    MAX-ACCESS  read-write
    STATUS      current
    DESCRIPTION
        "Scheduling mode"
    ::={ hwqAclPortAttrSchedulTableEntry 2 }

  hwqACLPortAttrSchedulRowStatus OBJECT-TYPE
    SYNTAX      RowStatus
    MAX-ACCESS  read-create
    STATUS      current
    DESCRIPTION
        "Row operation status"
    ::={ hwqAclPortAttrSchedulTableEntry 3 }

  -- TABLE: hwqAclPortMirrorTable
  hwqAclPortMirrorTable OBJECT-TYPE
    SYNTAX      SEQUENCE OF HwqAclPortMirrorTableEntry
    MAX-ACCESS  not-accessible
    STATUS      current
    DESCRIPTION
      "Port mirroring table"
    ::= { hws6506qAclMibObject 6 }

  hwqAclPortMirrorTableEntry OBJECT-TYPE
    SYNTAX      HwqAclPortMirrorTableEntry
    MAX-ACCESS  not-accessible
    STATUS      current
    DESCRIPTION
      ""
    INDEX {  
              hwqACLPortMirrorName
             }
    ::= { hwqAclPortMirrorTable 1 }

  HwqAclPortMirrorTableEntry ::=
    SEQUENCE
    {
      hwqACLPortMirrorName	OCTET STRING,
      hwqACLPortMirrorPortMask1	INTEGER,
      hwqACLPortMirrorPortMask2	INTEGER,
      hwqACLPortMirrorMirrorDirection	INTEGER,
      hwqACLPortMirrorMirrorPort	OCTET STRING,
      hwqACLPortMirrorRowStatus	RowStatus
    }

  hwqACLPortMirrorName OBJECT-TYPE
    SYNTAX      OCTET STRING(SIZE(1..32))
    MAX-ACCESS  read-write
    STATUS      current
    DESCRIPTION
        "Port mirror name"
    ::={ hwqAclPortMirrorTableEntry 1 }

  hwqACLPortMirrorPortMask1 OBJECT-TYPE
    SYNTAX      INTEGER
    MAX-ACCESS  read-write
    STATUS      current
    DESCRIPTION
        "Port mask"
    ::={ hwqAclPortMirrorTableEntry 2 }

  hwqACLPortMirrorPortMask2 OBJECT-TYPE
    SYNTAX      INTEGER
    MAX-ACCESS  read-write
    STATUS      current
    DESCRIPTION
        "Port mask"
    ::={ hwqAclPortMirrorTableEntry 3 }

  hwqACLPortMirrorMirrorDirection OBJECT-TYPE
    SYNTAX      INTEGER{input    (1),output    (2)}
    MAX-ACCESS  read-write
    STATUS      current
    DESCRIPTION
        "Mirroring direction"
    ::={ hwqAclPortMirrorTableEntry 4 }

  hwqACLPortMirrorMirrorPort OBJECT-TYPE
    SYNTAX      OCTET STRING
    MAX-ACCESS  read-write
    STATUS      current
    DESCRIPTION
        "Mirror port"
    ::={ hwqAclPortMirrorTableEntry 5 }

  hwqACLPortMirrorRowStatus OBJECT-TYPE
    SYNTAX      RowStatus
    MAX-ACCESS  read-create
    STATUS      current
    DESCRIPTION
        "Row operation status"
    ::={ hwqAclPortMirrorTableEntry 6 }

  -- TABLE: hwqAclGlobalQaclModeTable
  hwqAclGlobalQaclModeTable OBJECT-TYPE
    SYNTAX      SEQUENCE OF HwqAclGlobalQaclModeTableEntry
    MAX-ACCESS  not-accessible
    STATUS      current
    DESCRIPTION
      "Global table"
    ::= { hws6506qAclMibObject 7 }

  hwqAclGlobalQaclModeTableEntry OBJECT-TYPE
    SYNTAX      HwqAclGlobalQaclModeTableEntry
    MAX-ACCESS  not-accessible
    STATUS      current
    DESCRIPTION
      ""
    INDEX {  
              hwqACLGlobalMode
             }
    ::= { hwqAclGlobalQaclModeTable 1 }

  HwqAclGlobalQaclModeTableEntry ::=
    SEQUENCE
    {
      hwqACLGlobalMode	INTEGER,
      hwqACLGlobalModeRowStatus	RowStatus
    }

  hwqACLGlobalMode OBJECT-TYPE
    SYNTAX      INTEGER{l2    (1),l3    (2)}
    MAX-ACCESS  read-write
    STATUS      current
    DESCRIPTION
        "L2/L3 filtering"
    ::={ hwqAclGlobalQaclModeTableEntry 1 }

  hwqACLGlobalModeRowStatus OBJECT-TYPE
    SYNTAX      RowStatus
    MAX-ACCESS  read-create
    STATUS      current
    DESCRIPTION
        "Row operation status"
    ::={ hwqAclGlobalQaclModeTableEntry 2 }

  -- TABLE: hwqAclGlobalPriTrustTable
  hwqAclGlobalPriTrustTable OBJECT-TYPE
    SYNTAX      SEQUENCE OF HwqAclGlobalPriTrustTableEntry
    MAX-ACCESS  not-accessible
    STATUS      current
    DESCRIPTION
      ""
    ::= { hws6506qAclMibObject 8 }

  hwqAclGlobalPriTrustTableEntry OBJECT-TYPE
    SYNTAX      HwqAclGlobalPriTrustTableEntry
    MAX-ACCESS  not-accessible
    STATUS      current
    DESCRIPTION
      ""
    INDEX {  
              hwqACLGlobalTrustPri
             }
    ::= { hwqAclGlobalPriTrustTable 1 }

  HwqAclGlobalPriTrustTableEntry ::=
    SEQUENCE
    {
      hwqACLGlobalTrustPri	INTEGER,
      hwqACLGlobalTrustPriRowStatus	RowStatus
    }

  hwqACLGlobalTrustPri OBJECT-TYPE
    SYNTAX      INTEGER{local    (0),cos    (1),dscp    (2)}
    MAX-ACCESS  read-write
    STATUS      current
    DESCRIPTION
      ""
    ::={ hwqAclGlobalPriTrustTableEntry 1 }

  hwqACLGlobalTrustPriRowStatus OBJECT-TYPE
    SYNTAX      RowStatus
    MAX-ACCESS  read-create
    STATUS      current
    DESCRIPTION
        "Row operation status"
    ::={ hwqAclGlobalPriTrustTableEntry 2 }

  -- TABLE: hwQAclRuleTable
  hwQAclRuleTable OBJECT-TYPE
    SYNTAX      SEQUENCE OF HwQAclRuleTableEntry
    MAX-ACCESS  not-accessible
    STATUS      current
    DESCRIPTION
      "Traffic rule description table  "
    ::= { hws6506qAclMibObject 9 }

  hwQAclRuleTableEntry OBJECT-TYPE
    SYNTAX      HwQAclRuleTableEntry
    MAX-ACCESS  not-accessible
    STATUS      current
    DESCRIPTION
      ""
    INDEX {  
              hwqACLRuleAclName
             }
    ::= { hwQAclRuleTable 1 }

  HwQAclRuleTableEntry ::=
    SEQUENCE
    {
      hwqACLRuleAclName	OCTET STRING,
      hwqACLRuleAclCmdType	INTEGER,
      hwqACLRuleMatchOrder	INTEGER,
      hwqACLRulePermitDeny	INTEGER,
      hwqACLRuleL3Protocol	INTEGER,
      hwqACLRuleTcpFlag	INTEGER,
      hwqACLRuleSourceIp	IpAddress,
      hwqACLRuleSourceIpWildcard	IpAddress,
      hwqACLRuleSourceIpAny	INTEGER,
      hwqACLRuleSourceL4PortOp	INTEGER,
      hwqACLRuleSourceL4Port	INTEGER,
      hwqACLRuleDestIp	IpAddress,
      hwqACLRuleDestIpWildcard	IpAddress,
      hwqACLRuleDestIpAny	INTEGER,
      hwqACLRuleDestL4PortOp	INTEGER,
      hwqACLRuleDestL4Port	INTEGER,
      hwqACLRulePrecedence	INTEGER,
      hwqACLRuleTos	INTEGER,
      hwqACLRuleEthType	INTEGER,
      hwqACLRuleL2Protocol	INTEGER,
      hwqACLRuleVlan	INTEGER,
      hwqACLRuleSourceMac	MacAddress,
      hwqACLRuleSourceMacAny	INTEGER,
      hwqACLRuleDestMac	MacAddress,
      hwqACLRuleDestMacAny	INTEGER,
      hwqACLRuleLog	INTEGER,
      hwqACLRuleTrName	OCTET STRING,
      hwqACLRuleRowStatus	RowStatus
    }

  hwqACLRuleAclName OBJECT-TYPE
    SYNTAX      OCTET STRING(SIZE (1..32))
    MAX-ACCESS  read-write
    STATUS      current
    DESCRIPTION
        "Name of traffic rule (1-199, string)<1-32>"
    ::={ hwQAclRuleTableEntry 1 }

  hwqACLRuleAclCmdType OBJECT-TYPE
    SYNTAX      INTEGER{
    				acl-name-link(3),
    				acl-name-standard(4),
    				acl-name-extended(5),
    				qos-link(6),
    				qos-ip(7),
    				invalid(65535)
    				}
    MAX-ACCESS  read-write
    STATUS      current
    DESCRIPTION
        "Command type (ACL-NAME-LINK 3, ACL-NAME-STANDARD 4, ACL-NAME-EXTENDED 5, QOS-LINK 6 and QOS-IP 7)"
    ::={ hwQAclRuleTableEntry 2 }

  hwqACLRuleMatchOrder OBJECT-TYPE
    SYNTAX      INTEGER{config(0),auto(1)}
    MAX-ACCESS  read-write
    STATUS      current
    DESCRIPTION
        "Order of issuing priorities (config 0; auto 1)"
    ::={ hwQAclRuleTableEntry 3 }

  hwqACLRulePermitDeny OBJECT-TYPE
    SYNTAX      INTEGER{permit(0),deny(1)}
    MAX-ACCESS  read-write
    STATUS      current
    DESCRIPTION
        "Permit/Deny (permit 0; deny 1)"
    ::={ hwQAclRuleTableEntry 4 }

  hwqACLRuleL3Protocol OBJECT-TYPE
    SYNTAX      INTEGER(1..255|65535)
    MAX-ACCESS  read-write
    STATUS      current
    DESCRIPTION
        "L3 protocol <0-255>"
    ::={ hwQAclRuleTableEntry 5 }

  hwqACLRuleTcpFlag OBJECT-TYPE
    SYNTAX      INTEGER(0..31|65535)
    MAX-ACCESS  read-write
    STATUS      current
    DESCRIPTION
        "TcpFlag<0-31>"
    ::={ hwQAclRuleTableEntry 6 }

  hwqACLRuleSourceIp OBJECT-TYPE
    SYNTAX      IpAddress
    MAX-ACCESS  read-write
    STATUS      current
    DESCRIPTION
        "Source IP address"
    ::={ hwQAclRuleTableEntry 7 }

  hwqACLRuleSourceIpWildcard OBJECT-TYPE
    SYNTAX      IpAddress
    MAX-ACCESS  read-write
    STATUS      current
    DESCRIPTION
        "Wildcards of source IP address"
    ::={ hwQAclRuleTableEntry 8 }

  hwqACLRuleSourceIpAny OBJECT-TYPE
    SYNTAX      INTEGER{invalid(0),valid(1)}
    MAX-ACCESS  read-write
    STATUS      current
    DESCRIPTION
        "Any source IP address (valid 1)"
    ::={ hwQAclRuleTableEntry 9 }

  hwqACLRuleSourceL4PortOp OBJECT-TYPE
    SYNTAX      INTEGER{eq(0),invalid(65535)}
    MAX-ACCESS  read-write
    STATUS      current
    DESCRIPTION
        "Source L4 port operator"
    ::={ hwQAclRuleTableEntry 10 }

  hwqACLRuleSourceL4Port OBJECT-TYPE
    SYNTAX      INTEGER(0..65535)
    MAX-ACCESS  read-write
    STATUS      current
    DESCRIPTION
        "Number of source L4 port <0-65535>"
    ::={ hwQAclRuleTableEntry 11 }

  hwqACLRuleDestIp OBJECT-TYPE
    SYNTAX      IpAddress
    MAX-ACCESS  read-write
    STATUS      current
    DESCRIPTION
        "Destination IP address"
    ::={ hwQAclRuleTableEntry 12 }

  hwqACLRuleDestIpWildcard OBJECT-TYPE
    SYNTAX      IpAddress
    MAX-ACCESS  read-write
    STATUS      current
    DESCRIPTION
        "Wildcards of destination IP address"
    ::={ hwQAclRuleTableEntry 13 }

  hwqACLRuleDestIpAny OBJECT-TYPE
    SYNTAX      INTEGER{invalid(0),valid(1)}
    MAX-ACCESS  read-write
    STATUS      current
    DESCRIPTION
        "Any destination IP address (valid 1)"
    ::={ hwQAclRuleTableEntry 14 }

  hwqACLRuleDestL4PortOp OBJECT-TYPE
    SYNTAX      INTEGER{eq(0),invalid(65535)}
    MAX-ACCESS  read-write
    STATUS      current
    DESCRIPTION
        "Destination L4 port operator"
    ::={ hwQAclRuleTableEntry 15 }

  hwqACLRuleDestL4Port OBJECT-TYPE
    SYNTAX      INTEGER(0..65535)
    MAX-ACCESS  read-write
    STATUS      current
    DESCRIPTION
        "Number of destination L4 port <0-65535>"
    ::={ hwQAclRuleTableEntry 16 }

  hwqACLRulePrecedence OBJECT-TYPE
    SYNTAX      INTEGER{
    				routine(0),
    				priority(1),
    				immediate(2),
    				flash(3),
    				flash-override(4),
    				critical(5),
    				internet(6),
    				network(7),
    				invalid(65535)
    				}
    MAX-ACCESS  read-write
    STATUS      current
    DESCRIPTION
        "Precedence"
    ::={ hwQAclRuleTableEntry 17 }

  hwqACLRuleTos OBJECT-TYPE
    SYNTAX      INTEGER(0..7|65535)
    MAX-ACCESS  read-write
    STATUS      current
    DESCRIPTION
        "TOS value <0-7>"
    ::={ hwQAclRuleTableEntry 18 }

  hwqACLRuleEthType OBJECT-TYPE
    SYNTAX      INTEGER{dix(0),snap(1),sap(3),invalid(65535)}
    MAX-ACCESS  read-write
    STATUS      current
    DESCRIPTION
        "Ethernet encapsulation (dix 0, snap 1 and sap 3)"
    ::={ hwQAclRuleTableEntry 19 }

  hwqACLRuleL2Protocol OBJECT-TYPE
    SYNTAX      INTEGER{ip(2048),arp(2054),rarp(32821),invalid(65535)}
    MAX-ACCESS  read-write
    STATUS      current
    DESCRIPTION
        "Protocols carried at L2 (ip 0x0800; arp 0x0806; rarp 0x8035)"
    ::={ hwQAclRuleTableEntry 20 }

  hwqACLRuleVlan OBJECT-TYPE
    SYNTAX      INTEGER(1..4000|65535)
    MAX-ACCESS  read-write
    STATUS      current
    DESCRIPTION
        "VLAN ID <1-4000>"
    ::={ hwQAclRuleTableEntry 21 }

  hwqACLRuleSourceMac OBJECT-TYPE
    SYNTAX      MacAddress
    MAX-ACCESS  read-write
    STATUS      current
    DESCRIPTION
        "Source MAC address"
    ::={ hwQAclRuleTableEntry 22 }

  hwqACLRuleSourceMacAny OBJECT-TYPE
    SYNTAX      INTEGER{invalid(0),valid(1)}
    MAX-ACCESS  read-write
    STATUS      current
    DESCRIPTION
        "Any source MAC address (valid 1)"
    ::={ hwQAclRuleTableEntry 23 }

  hwqACLRuleDestMac OBJECT-TYPE
    SYNTAX      MacAddress
    MAX-ACCESS  read-write
    STATUS      current
    DESCRIPTION
        "Destination MAC address"
    ::={ hwQAclRuleTableEntry 24 }

  hwqACLRuleDestMacAny OBJECT-TYPE
    SYNTAX      INTEGER{invalid(0),valid(1)}
    MAX-ACCESS  read-write
    STATUS      current
    DESCRIPTION
        " Any destination MAC address (valid 1)"
    ::={ hwQAclRuleTableEntry 25 }

  hwqACLRuleLog OBJECT-TYPE
    SYNTAX      INTEGER{invalid(0),valid(1)}
    MAX-ACCESS  read-write
    STATUS      current
    DESCRIPTION
        "Log (valid 1)"
    ::={ hwQAclRuleTableEntry 26 }

  hwqACLRuleTrName OBJECT-TYPE
    SYNTAX      OCTET STRING(SIZE (0..32))
    MAX-ACCESS  read-write
    STATUS      current
    DESCRIPTION
        "Name of time range <1-32>"
    ::={ hwQAclRuleTableEntry 27 }

  hwqACLRuleRowStatus OBJECT-TYPE
    SYNTAX      RowStatus
    MAX-ACCESS  read-create
    STATUS      current
    DESCRIPTION
        "Row operation status"
    ::={ hwQAclRuleTableEntry 28 }

  -- TABLE: hwqAclMapTable
  hwqAclMapTable OBJECT-TYPE
    SYNTAX      SEQUENCE OF HwqAclMapTableEntry
    MAX-ACCESS  not-accessible
    STATUS      current
    DESCRIPTION
      ""
    ::= { hws6506qAclMibObject 10 }

  hwqAclMapTableEntry OBJECT-TYPE
    SYNTAX      HwqAclMapTableEntry
    MAX-ACCESS  not-accessible
    STATUS      current
    DESCRIPTION
      ""
    INDEX {  
              hwqACLMapName
             }
    ::= { hwqAclMapTable 1 }

  HwqAclMapTableEntry ::=
    SEQUENCE
    {
      hwqACLMapName	OCTET STRING,
      hwqACLMapRuleName	OCTET STRING,
      hwqACLMapActionName	OCTET STRING,
      hwqACLMapRowStatus	RowStatus
    }

  hwqACLMapName OBJECT-TYPE
    SYNTAX      OCTET STRING(SIZE (1..32))
    MAX-ACCESS  read-write
    STATUS      current
    DESCRIPTION
        "Map name"
    ::={ hwqAclMapTableEntry 1 }

  hwqACLMapRuleName OBJECT-TYPE
    SYNTAX      OCTET STRING(SIZE (0..32))
    MAX-ACCESS  read-write
    STATUS      current
    DESCRIPTION
        "Name of the rule in the map"
    ::={ hwqAclMapTableEntry 2 }

  hwqACLMapActionName OBJECT-TYPE
    SYNTAX      OCTET STRING(SIZE (0..32))
    MAX-ACCESS  read-write
    STATUS      current
    DESCRIPTION
        "Name of the action in the map"
    ::={ hwqAclMapTableEntry 3 }

  hwqACLMapRowStatus OBJECT-TYPE
    SYNTAX      RowStatus
    MAX-ACCESS  read-create
    STATUS      current
    DESCRIPTION
        "Row operation status"
    ::={ hwqAclMapTableEntry 4 }

  -- TABLE: hwqAclAccessGroupTable
  hwqAclAccessGroupTable OBJECT-TYPE
    SYNTAX      SEQUENCE OF HwqAclAccessGroupTableEntry
    MAX-ACCESS  not-accessible
    STATUS      current
    DESCRIPTION
      ""
    ::= { hws6506qAclMibObject 11 }

  hwqAclAccessGroupTableEntry OBJECT-TYPE
    SYNTAX      HwqAclAccessGroupTableEntry
    MAX-ACCESS  not-accessible
    STATUS      current
    DESCRIPTION
      ""
    INDEX {  
              hwqACLAccessGroupCommitName
             }
    ::= { hwqAclAccessGroupTable 1 }

  HwqAclAccessGroupTableEntry ::=
    SEQUENCE
    {
      hwqACLAccessGroupCommitName	OCTET STRING,
      hwqACLAccessGroupRowStatus	RowStatus
    }

  hwqACLAccessGroupCommitName OBJECT-TYPE
    SYNTAX      OCTET STRING(SIZE (1..64))
    MAX-ACCESS  read-write
    STATUS      current
    DESCRIPTION
        "Issued map name"
    ::={ hwqAclAccessGroupTableEntry 1 }

  hwqACLAccessGroupRowStatus OBJECT-TYPE
    SYNTAX      RowStatus
    MAX-ACCESS  read-create
    STATUS      current
    DESCRIPTION
        "Row operation status"
    ::={ hwqAclAccessGroupTableEntry 2 }

  -- TABLE: hwqAclSetQosMapTable
  hwqAclSetQosMapTable OBJECT-TYPE
    SYNTAX      SEQUENCE OF HwqAclSetQosMapTableEntry
    MAX-ACCESS  not-accessible
    STATUS      current
    DESCRIPTION
      ""
    ::= { hws6506qAclMibObject 12 }

  hwqAclSetQosMapTableEntry OBJECT-TYPE
    SYNTAX      HwqAclSetQosMapTableEntry
    MAX-ACCESS  not-accessible
    STATUS      current
    DESCRIPTION
      ""
    INDEX {  
              hwqACLSetQosMapCommitName
             }
    ::= { hwqAclSetQosMapTable 1 }

  HwqAclSetQosMapTableEntry ::=
    SEQUENCE
    {
      hwqACLSetQosMapCommitName	OCTET STRING,
      hwqACLSetQosMapRowStatus	RowStatus
    }

  hwqACLSetQosMapCommitName OBJECT-TYPE
    SYNTAX      OCTET STRING(SIZE (1..64))
    MAX-ACCESS  read-write
    STATUS      current
    DESCRIPTION
        "Issued map name"
    ::={ hwqAclSetQosMapTableEntry 1 }

  hwqACLSetQosMapRowStatus OBJECT-TYPE
    SYNTAX      RowStatus
    MAX-ACCESS  read-create
    STATUS      current
    DESCRIPTION
        "Issued map name"
    ::={ hwqAclSetQosMapTableEntry 2 }

  -- TABLE: hwqAclSetTimeRangeTable
  hwqAclSetTimeRangeTable OBJECT-TYPE
    SYNTAX      SEQUENCE OF HwqAclSetTimeRangeTableEntry
    MAX-ACCESS  not-accessible
    STATUS      current
    DESCRIPTION
      ""
    ::= { hws6506qAclMibObject 13 }

  hwqAclSetTimeRangeTableEntry OBJECT-TYPE
    SYNTAX      HwqAclSetTimeRangeTableEntry
    MAX-ACCESS  not-accessible
    STATUS      current
    DESCRIPTION
      ""
    INDEX {  
              hwqACLSetTimeRangeName
             }
    ::= { hwqAclSetTimeRangeTable 1 }

  HwqAclSetTimeRangeTableEntry ::=
    SEQUENCE
    {
      hwqACLSetTimeRangeName	OCTET STRING,
      hwqACLSetTimeRangeAbsolute	INTEGER,
      hwqACLSetTimeRangeAStartTime	OCTET STRING,
      hwqACLSetTimeRangeAStartDate	OCTET STRING,
      hwqACLSetTimeRangeAEndTime	OCTET STRING,
      hwqACLSetTimeRangeAEndDate	OCTET STRING,
      hwqACLSetTimeRangePeriodic	INTEGER,
      hwqACLSetTimeRangePDaysOfWeek	INTEGER,
      hwqACLSetTimeRangePStartDayOfWeek	INTEGER,
      hwqACLSetTimeRangePEndDayOfWeek	INTEGER,
      hwqACLSetTimeRangePStartTime	OCTET STRING,
      hwqACLSetTimeRangePEndTime	OCTET STRING,
      hwqACLSetTimeRangeRowStatus	RowStatus
    }

  hwqACLSetTimeRangeName OBJECT-TYPE
    SYNTAX      OCTET STRING(SIZE (1..32))
    MAX-ACCESS  read-write
    STATUS      current
    DESCRIPTION
        "Name of the time range"
    ::={ hwqAclSetTimeRangeTableEntry 1 }

  hwqACLSetTimeRangeAbsolute OBJECT-TYPE
    SYNTAX      INTEGER{invalid(0),valid(1)}
    MAX-ACCESS  read-write
    STATUS      current
    DESCRIPTION
        "Whether the absolute time range is valid"
    ::={ hwqAclSetTimeRangeTableEntry 2 }

  hwqACLSetTimeRangeAStartTime OBJECT-TYPE
    SYNTAX      OCTET STRING(SIZE (0..5))
    MAX-ACCESS  read-write
    STATUS      current
    DESCRIPTION
        "Absolute starting time <HH:MM>"
    ::={ hwqAclSetTimeRangeTableEntry 3 }

  hwqACLSetTimeRangeAStartDate OBJECT-TYPE
    SYNTAX      OCTET STRING(SIZE (0..10))
    MAX-ACCESS  read-write
    STATUS      current
    DESCRIPTION
        "Absolute starting date <MM-DD-YYYY>"
    ::={ hwqAclSetTimeRangeTableEntry 4 }

  hwqACLSetTimeRangeAEndTime OBJECT-TYPE
    SYNTAX      OCTET STRING(SIZE (0..5))
    MAX-ACCESS  read-write
    STATUS      current
    DESCRIPTION
        " Absolute end time <HH:MM>"
    ::={ hwqAclSetTimeRangeTableEntry 5 }

  hwqACLSetTimeRangeAEndDate OBJECT-TYPE
    SYNTAX      OCTET STRING(SIZE (0..10))
    MAX-ACCESS  read-write
    STATUS      current
    DESCRIPTION
        " Absolute end date <MM-DD-YYYY>"
    ::={ hwqAclSetTimeRangeTableEntry 6 }

  hwqACLSetTimeRangePeriodic OBJECT-TYPE
    SYNTAX      INTEGER{invalid(0),valid(1)}
    MAX-ACCESS  read-write
    STATUS      current
    DESCRIPTION
        "Whether the periodic time range is valid"
    ::={ hwqAclSetTimeRangeTableEntry 7 }

  hwqACLSetTimeRangePDaysOfWeek OBJECT-TYPE
    SYNTAX      INTEGER
    MAX-ACCESS  read-write
    STATUS      current
    DESCRIPTION
        " The week masks for the periodic time to take effect. From low bit to high bit, they are sun(0),mon(1),tue(2),wed(3),thu(4),fri(5) and sat(6). "
    ::={ hwqAclSetTimeRangeTableEntry 8 }

  hwqACLSetTimeRangePStartDayOfWeek OBJECT-TYPE
    SYNTAX      INTEGER{sun(0),mon(1),tue(2),wed(3),thu(4),fri(5),sat(6)}
    MAX-ACCESS  read-write
    STATUS      current
    DESCRIPTION
        "Starting day of week when the periodic time range takes effect"
    ::={ hwqAclSetTimeRangeTableEntry 9 }

  hwqACLSetTimeRangePEndDayOfWeek OBJECT-TYPE
    SYNTAX      INTEGER{sun(0),mon(1),yue(2),wed(3),thu(4),fri(5),sat(6)}
    MAX-ACCESS  read-write
    STATUS      current
    DESCRIPTION
        "End day of week before which the periodic time range takes effect"
    ::={ hwqAclSetTimeRangeTableEntry 10 }

  hwqACLSetTimeRangePStartTime OBJECT-TYPE
    SYNTAX      OCTET STRING(SIZE (0..5))
    MAX-ACCESS  read-write
    STATUS      current
    DESCRIPTION
        "Starting time of periodic time range <HH:MM>"
    ::={ hwqAclSetTimeRangeTableEntry 11 }

  hwqACLSetTimeRangePEndTime OBJECT-TYPE
    SYNTAX      OCTET STRING(SIZE (0..5))
    MAX-ACCESS  read-write
    STATUS      current
    DESCRIPTION
        "End time of the periodic time range <HH:MM>"
    ::={ hwqAclSetTimeRangeTableEntry 12 }

  hwqACLSetTimeRangeRowStatus OBJECT-TYPE
    SYNTAX      RowStatus
    MAX-ACCESS  read-create
    STATUS      current
    DESCRIPTION
        " "
    ::={ hwqAclSetTimeRangeTableEntry 13 }
END
