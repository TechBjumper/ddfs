-- ----------------------------------------------------------------------------
--                    CM CONDITION MIB
--                    CM-CONDITION-MIB
--
--      Copyright (c) 1999-2000 HUAWEI ELECTRIC TECH. CO., LTD, SHENZHEN.
--      Copyright (c) 2000-2001 AVANSYS POWER CO., LTD., SHENZHEN.
--      Copyright (c) 2001-2007 EMERSON NETWORK POWER CO., LTD.
--      All rights reserved.
--
--      Created    by: Zheng Chunhua
--      Created  date: 2007-06-07
--      Modified Date: 
--
-- ----------------------------------------------------------------------------

CM-CONDITION-MIB DEFINITIONS ::= BEGIN

IMPORTS
    OBJECT-TYPE
        FROM RFC-1212

    TRAP-TYPE
        FROM RFC-1215

    enterprises, IpAddress
        FROM RFC1155-SMI;

    DisplayString ::= OCTET STRING


    -- ------------------------------------------------------------------------
    -- the location of CONDITION group in ENP enterprise.
    -- ------------------------------------------------------------------------ 
    emersonNetworkPower     OBJECT IDENTIFIER ::= { enterprises 13400 }
    products                OBJECT IDENTIFIER ::= { emersonNetworkPower 2 }    
    emersonUps              OBJECT IDENTIFIER ::= { products 1 }
    CMCondition             OBJECT IDENTIFIER ::= { products 9 }
    
    -- ------------------------------------------------------------------------
    -- the main objects about CONDITION
    -- ------------------------------------------------------------------------ 
    upsAgent        OBJECT IDENTIFIER ::= { emersonUps 1 }
    upsCommon       OBJECT IDENTIFIER ::= { emersonUps 2 }
    conditionSpecial      OBJECT IDENTIFIER ::= { CMCondition 1 }
    upsAlarm        OBJECT IDENTIFIER ::= { emersonUps 4 }

    upsIdent        OBJECT IDENTIFIER ::= { upsCommon 1 }
    
    -- ------------------------------------------------------------------------
    -- the common objects about a  CONDITION
    -- ------------------------------------------------------------------------ 
    upsBaseIdent    OBJECT IDENTIFIER ::=  { upsIdent 1 }
    upsSmartIdent   OBJECT IDENTIFIER ::=  { upsIdent 2 }

    upsBaseAlaram   OBJECT IDENTIFIER ::=  { upsAlarm 1 }
    upsSmartAlarm   OBJECT IDENTIFIER ::=  { upsAlarm 2 }

    -- ------------------------------------------------------------------------
    -- the detail objects about a special CONDITION
    -- ------------------------------------------------------------------------ 
    conditionInput        OBJECT IDENTIFIER ::=  { conditionSpecial 1 }
    conditionOutput       OBJECT IDENTIFIER ::=  { conditionSpecial 2 }
    conditionStatus       OBJECT IDENTIFIER ::=  { conditionSpecial 3 }
    conditionTest         OBJECT IDENTIFIER ::=  { conditionSpecial 4 }
    conditionControl      OBJECT IDENTIFIER ::=  { conditionSpecial 5 }
    conditionConfig       OBJECT IDENTIFIER ::=  { conditionSpecial 6 }
   
    conditionBaseInput    OBJECT IDENTIFIER ::=  { conditionInput 1 }
    conditionSmartInput   OBJECT IDENTIFIER ::=  { conditionInput 2 }
    
    conditionBaseOutput   OBJECT IDENTIFIER ::=  { conditionOutput 1 }
    conditionSmartOutput  OBJECT IDENTIFIER ::=  { conditionOutput 2 }

    conditionBaseStatus   OBJECT IDENTIFIER ::=  { conditionStatus 1 }
    conditionSmartStatus  OBJECT IDENTIFIER ::=  { conditionStatus 2 }
    
    conditionBaseControl  OBJECT IDENTIFIER ::=  { conditionControl 1 }
    conditionSmartControl OBJECT IDENTIFIER ::=  { conditionControl 2 }
    
    conditionBaseTest     OBJECT IDENTIFIER ::=  { conditionTest 1 }
    conditionSmartTest    OBJECT IDENTIFIER ::=  { conditionTest 2 }
    
    conditionBaseConfig   OBJECT IDENTIFIER ::=  { conditionConfig 1 }
    conditionSmartConfig  OBJECT IDENTIFIER ::=  { conditionConfig 2 }

    -- ------------------------------------------------------------------------
    -- 1. upsAgent group
    -- ------------------------------------------------------------------------ 
   
    agentRevision OBJECT-TYPE
        SYNTAX INTEGER
        ACCESS read-only
        STATUS mandatory
        DESCRIPTION
            "The software version of the agent."
        ::= { upsAgent 1 }

    agentManagersNum OBJECT-TYPE
        SYNTAX INTEGER
        ACCESS read-only
        STATUS mandatory
        DESCRIPTION
           "The number of managers that can manage the agent. "
        ::= { upsAgent 2 }
 
    agentManagersTable OBJECT-TYPE
        SYNTAX SEQUENCE OF AgentManagersEntry
        ACCESS not-accessible
        STATUS mandatory
        DESCRIPTION
            "A list of managers of the agent.  The number of
            entries is given by the value of agentManagersNum."
        ::= { upsAgent 3 }
 
    agentManagersEntry OBJECT-TYPE
        SYNTAX AgentManagersEntry
        ACCESS not-accessible
        STATUS mandatory
        DESCRIPTION
            "The managers of the agent."
        INDEX  { managerIndex}
        ::= { agentManagersTable 1 }
 
    AgentManagersEntry ::=
        SEQUENCE {
            managerIndex
                INTEGER,
            managerAddr
                IpAddress,
            publicCommunityString
                 DisplayString,
            privateCommunityString
                 DisplayString,
            managerPrivilege
                INTEGER,
            acceptTrapLevel
                INTEGER,
            managerAccept
                INTEGER
        }
 
    managerIndex OBJECT-TYPE
        SYNTAX INTEGER
        ACCESS read-only
        STATUS mandatory
        DESCRIPTION
            "The index of the managers entry."
        ::= { agentManagersEntry 1 }
    
    managerAddr OBJECT-TYPE
        SYNTAX IpAddress
        ACCESS read-write
        STATUS mandatory
        DESCRIPTION
            "The IP address of the manager."
        ::= { agentManagersEntry 2 }

    publicCommunityString OBJECT-TYPE
        SYNTAX DisplayString
        ACCESS read-write
        STATUS mandatory
        DESCRIPTION
           "The public community name to use in the query request."
        ::= { agentManagersEntry 3 }
 
    privateCommunityString OBJECT-TYPE
        SYNTAX DisplayString
        ACCESS read-write
        STATUS mandatory
        DESCRIPTION
           "The private community name to use int the control request."
        ::= { agentManagersEntry 4 }
 
    managerPrivilege OBJECT-TYPE
        SYNTAX INTEGER {
            forbidden(0),
            query(1),
            control(2),
            administrator(3)
       }
        ACCESS read-write
        STATUS mandatory
        DESCRIPTION
            "The privilege of the manager to access the agent.
            setting forbidden(0) indicates the manager have no any privilege to access the agent,
            setting query(1) indicates the manager can GET information from agent only,
            setting control(2) indicates the manager can GET information from agent and 
            send control command to the agent.
            setting administrator(3) indicates the manager has all management privilege
            including set or modify this managers table."
       ::= { agentManagersEntry 5 }

    acceptTrapLevel OBJECT-TYPE
         SYNTAX INTEGER {
            information(1),
            warning(2),
            severe(3),
            noTraps(4)
        }
        ACCESS read-write
        STATUS mandatory
        DESCRIPTION
            "The severity threshold of traps to send to the manager.
            traps are labeled in severity as informational(1), warning(2),
            severe(3).  Only traps of equal or greater severity than
            this value are sent to the manager. setting noTraps(4) indicates
            agent do not send any traps to the manager."
       ::= { agentManagersEntry 6 }

    managerAccept OBJECT-TYPE
        SYNTAX INTEGER   {
            view(0),
            new(1),
            modify(2),
            delete(3)
        }
        ACCESS read-write
        STATUS mandatory
        DESCRIPTION
           "An entry will be added if new(1), will be modified if modify(2), 
           and will be removed if delete(3)."
        ::= { agentManagersEntry 7 }

    -- ------------------------------------------------------------------------
    -- 2. upsCommon group
    -- ------------------------------------------------------------------------ 

    -- ------------------------------------------------------------------------
    -- 2.1 upsIdent group
    -- ------------------------------------------------------------------------ 

    -- ------------------------------------------------------------------------ 
    -- 2.1.1 the upsBaseIdent group
    -- ------------------------------------------------------------------------ 

    upsBaseIdentModel OBJECT-TYPE
        SYNTAX DisplayString
        ACCESS read-only
        STATUS mandatory
        DESCRIPTION
            "The CONDITION model name (e.g. 'CM CONDITION')."
        ::= { upsBaseIdent 1 }

    upsBaseIdentName OBJECT-TYPE
        SYNTAX DisplayString
        ACCESS read-write
        STATUS mandatory
        DESCRIPTION
            "An 8 byte ID string identifying the CONDITION.  This object
             can be set by the administrator."
        ::= { upsBaseIdent 2 }
                
    
    -- ------------------------------------------------------------------------ 
    -- 2.1.2 the upsSmartIdent group
    -- ------------------------------------------------------------------------ 
            
    upsSmartIdentFirmwareRevision OBJECT-TYPE
        SYNTAX DisplayString
        ACCESS read-only
        STATUS mandatory
        DESCRIPTION
            "The firmware revision of the CONDITION system."
        ::= { upsSmartIdent 1 }
        
    -- !!!!!!!!!!!!!!!!!!!!!!!!!!!!!!!!!!!!!!!!!!!!!!!!
    -- IMPORTANT: CM CONDITION does NOT support manu-date and product-serial
    --            to read these variables will get 'reserved'
    upsSmartIdentDateOfManufacture OBJECT-TYPE
        SYNTAX DisplayString
       ACCESS read-only
        STATUS mandatory
        DESCRIPTION
           "The date when the CONDITION was manufactured in yyyy/mm/dd format."
        ::= { upsSmartIdent 2 }

    upsSmartIdentSerialNumber OBJECT-TYPE
         SYNTAX DisplayString
        ACCESS read-only
         STATUS mandatory
         DESCRIPTION
            "An 8-character string identifying the serial number of
              the CONDITION internal microprocessor.  This number is set at
              the factory.  NOTE: This number does NOT correspond to
             the serial number on the rear of the CONDITION."
        ::= { upsSmartIdent 3 }
    
    upsSmartIdentFactory OBJECT-TYPE
        SYNTAX DisplayString
        ACCESS read-only
        STATUS mandatory
        DESCRIPTION
            "The name of the factory that manufactured this CONDITION."
        ::= { upsSmartIdent 4 }
    
    -- ------------------------------------------------------------------------
    -- 3. conditionSpecial group
    -- ------------------------------------------------------------------------ 

    -- ------------------------------------------------------------------------
    -- 3.3. the conditionInput group
    -- ------------------------------------------------------------------------

    -- ------------------------------------------------------------------------
    -- 3.3.1 the conditionBaseInput group
    -- ------------------------------------------------------------------------

    -- ------------------------------------------------------------------------
    -- 3.3.2 the conditionSmartInput group
    -- ------------------------------------------------------------------------

    -- ------------------------------------------------------------------------
    -- 3.4. the conditionOutput group
    -- ------------------------------------------------------------------------

    -- ------------------------------------------------------------------------
    -- 3.4.1 the conditionBaseOutput group
    -- ------------------------------------------------------------------------
    
    -- ------------------------------------------------------------------------
    -- 3.4.2 the conditionSmartOutput group
    ------------------------------------------------------------------------
    conditionSmartTemperature OBJECT-TYPE
        SYNTAX INTEGER
        ACCESS read-only
        STATUS mandatory
        DESCRIPTION
            "Temperature of the CONDITION system expressed in 1/10 °C."
        ::= { conditionSmartOutput 1 }

    conditionSmartHumidity OBJECT-TYPE
        SYNTAX INTEGER
        ACCESS read-only
        STATUS mandatory
        DESCRIPTION
            "Humidity of the CONDITION system expressed in %RH."
        ::= { conditionSmartOutput 2 }

    
    -- ---------------------------------------------------------------------
    -- 3.5. the conditionStatus group
    ------------------------------------------------------------------------
    -- ---------------------------------------------------------------------
    -- 3.5.1 the conditionBaseStatus group
    ------------------------------------------------------------------------
    conditionBaseStatusCommunication OBJECT-TYPE
        SYNTAX INTEGER {
            unknown(1),
            ok(2),
            lostCommunication(3),
            notEstablished(4)
        }
        ACCESS read-only
        STATUS mandatory
        DESCRIPTION
            "The status of communication to CONDITION. lostCommunication(3) indicates
            some errors occurred between CONDITION and agent. notEstablished(4) indicates
            agent can not connect to CONDITION, maybe error on communication port or port
            settings error."
        ::= { conditionBaseStatus 1 }

    -- ---------------------------------------------------------------------
    -- 3.5.2 the conditionSmartStatus group
    ------------------------------------------------------------------------
    
    conditionSmartStatusUnitOnOff OBJECT-TYPE
        SYNTAX INTEGER  {
            unknown(1),
            on(2),
            off(3)
        }
        ACCESS read-only
        STATUS mandatory
        DESCRIPTION
            "Unit OnOff"
        ::= { conditionSmartStatus 1 }

    conditionSmartStatusRemoteShutdownEnabled OBJECT-TYPE
        SYNTAX INTEGER  {
            unknown(1),
            enabled(2),
            disabled(3)
        }
        ACCESS read-only
        STATUS mandatory
        DESCRIPTION
            "Remote Shutdown Enabled"
        ::= { conditionSmartStatus 2 }

    conditionSmartStatusCompressor1OnOff OBJECT-TYPE
        SYNTAX INTEGER  {
            unknown(1),
            on(2),
            off(3)
        }
        ACCESS read-only
        STATUS mandatory
        DESCRIPTION
            "Compressor 1 On Off"
        ::= { conditionSmartStatus 3 }
        
    conditionSmartStatusCompressor2OnOff OBJECT-TYPE
        SYNTAX INTEGER  {
            unknown(1),
            on(2),
            off(3)
        }
        ACCESS read-only
        STATUS mandatory
        DESCRIPTION
            "Compressor 2 On Off"
        ::= { conditionSmartStatus 4 }

    conditionSmartStatusHeater1OnOff OBJECT-TYPE
        SYNTAX INTEGER  {
            unknown(1),
            on(2),
            off(3)
        }
        ACCESS read-only
        STATUS mandatory
        DESCRIPTION
            "Heater 1 On Off"
        ::= { conditionSmartStatus 5 }
        
    conditionSmartStatusHeater2OnOff OBJECT-TYPE
        SYNTAX INTEGER  {
            unknown(1),
            on(2),
            off(3)
        }
        ACCESS read-only
        STATUS mandatory
        DESCRIPTION
            "Heater 2 On Off"
        ::= { conditionSmartStatus 6 }

    conditionSmartStatusHotGasBypass OBJECT-TYPE
        SYNTAX INTEGER  {
            unknown(1),
            on(2),
            off(3)
        }
        ACCESS read-only
        STATUS mandatory
        DESCRIPTION
            "Hot Gas Bypass"
        ::= { conditionSmartStatus 7 }

    conditionSmartStatusFlushValve OBJECT-TYPE
        SYNTAX INTEGER  {
            unknown(1),
            on(2),
            off(3)
        }
        ACCESS read-only
        STATUS mandatory
        DESCRIPTION
            "Flush Valve"
        ::= { conditionSmartStatus 8 }

    conditionSmartStatusHumidifier OBJECT-TYPE
        SYNTAX INTEGER  {
            unknown(1),
            on(2),
            off(3)
        }
        ACCESS read-only
        STATUS mandatory
        DESCRIPTION
            "Humidifier"
        ::= { conditionSmartStatus 9 }

    conditionSmartStatusDehumidifyFanMode OBJECT-TYPE
        SYNTAX INTEGER  {
            unknown(1),
            on(2),
            off(3)
        }
        ACCESS read-only
        STATUS mandatory
        DESCRIPTION
            "Dehumidify Fan Mode"
        ::= { conditionSmartStatus 10 }

    conditionSmartStatusMainFan OBJECT-TYPE
        SYNTAX INTEGER  {
            unknown(1),
            on(2),
            off(3)
        }
        ACCESS read-only
        STATUS mandatory
        DESCRIPTION
            "Main Fan"
        ::= { conditionSmartStatus 11 }


    conditionSmartStatusSecondUnitEnabled OBJECT-TYPE
        SYNTAX INTEGER  {
            unknown(1),
            enabled(2),
            disabled(3)
        }
        ACCESS read-only
        STATUS mandatory
        DESCRIPTION
            "Second Unit Enabled"
        ::= { conditionSmartStatus 12 }

    conditionSmartStatusFlushTime OBJECT-TYPE
        SYNTAX INTEGER  {
            unknown(1),
            five(2),
            ten(3),
            twenty(4)
        }
        ACCESS read-only
        STATUS mandatory
        DESCRIPTION
            "Flush Time"
        ::= { conditionSmartStatus 13 }

    conditionSmartStatusHighTemperature OBJECT-TYPE
        SYNTAX INTEGER  {
            unknown(1),
            no(2),
            yes(3)
        }
        ACCESS read-only
        STATUS mandatory
        DESCRIPTION
            "High Temperature"
        ::= { conditionSmartStatus 14 }

    conditionSmartStatusLowTemperature OBJECT-TYPE
        SYNTAX INTEGER  {
            unknown(1),
            no(2),
            yes(3)
        }
        ACCESS read-only
        STATUS mandatory
        DESCRIPTION
            "Low Temperature"
        ::= { conditionSmartStatus 15 }

    conditionSmartStatusHighHumidify OBJECT-TYPE
        SYNTAX INTEGER  {
            unknown(1),
            no(2),
            yes(3)
        }
        ACCESS read-only
        STATUS mandatory
        DESCRIPTION
            "High Humidify"
        ::= { conditionSmartStatus 16 }

    conditionSmartStatusLowHumidify OBJECT-TYPE
        SYNTAX INTEGER  {
            unknown(1),
            no(2),
            yes(3)
        }
        ACCESS read-only
        STATUS mandatory
        DESCRIPTION
            "Low Humidify"
        ::= { conditionSmartStatus 17 }

    conditionSmartStatusSensorBoardFailure OBJECT-TYPE
        SYNTAX INTEGER  {
            unknown(1),
            no(2),
            yes(3)
        }
        ACCESS read-only
        STATUS mandatory
        DESCRIPTION
            "Sensor Board Failure"
        ::= { conditionSmartStatus 18 }

    conditionSmartStatusAirLoss OBJECT-TYPE
        SYNTAX INTEGER  {
            unknown(1),
            no(2),
            yes(3)
        }
        ACCESS read-only
        STATUS mandatory
        DESCRIPTION
            "Air Loss"
        ::= { conditionSmartStatus 19 }

    conditionSmartStatusWaterUnderfloor OBJECT-TYPE
        SYNTAX INTEGER  {
            unknown(1),
            no(2),
            yes(3)
        }
        ACCESS read-only
        STATUS mandatory
        DESCRIPTION
            "Water Underfloor"
        ::= { conditionSmartStatus 20 }

    conditionSmartStatusCompressor1HighPressure OBJECT-TYPE
        SYNTAX INTEGER  {
            unknown(1),
            no(2),
            yes(3)
        }
        ACCESS read-only
        STATUS mandatory
        DESCRIPTION
            "Compressor 1 High Pressure"
        ::= { conditionSmartStatus 21 }

    conditionSmartStatusCompressor2HighPressure OBJECT-TYPE
        SYNTAX INTEGER  {
            unknown(1),
            no(2),
            yes(3)
        }
        ACCESS read-only
        STATUS mandatory
        DESCRIPTION
            "Compressor 2 High Pressure"
        ::= { conditionSmartStatus 22 }

    conditionSmartStatusCompressor1LowPressure OBJECT-TYPE
        SYNTAX INTEGER  {
            unknown(1),
            no(2),
            yes(3)
        }
        ACCESS read-only
        STATUS mandatory
        DESCRIPTION
            "Compressor 1 Low Pressure"
        ::= { conditionSmartStatus 23 }

    conditionSmartStatusCompressor2LowPressure OBJECT-TYPE
        SYNTAX INTEGER  {
            unknown(1),
            no(2),
            yes(3)
        }
        ACCESS read-only
        STATUS mandatory
        DESCRIPTION
            "Compressor 2 Low Pressure"
        ::= { conditionSmartStatus 24 }

    conditionSmartStatusCoolMode OBJECT-TYPE
        SYNTAX INTEGER  {
            unknown(1),
            on(2),
            off(3)
        }
        ACCESS read-only
        STATUS mandatory
        DESCRIPTION
            "Cool Mode"
        ::= { conditionSmartStatus 25 }

    conditionSmartStatusHeatMode OBJECT-TYPE
        SYNTAX INTEGER  {
            unknown(1),
            on(2),
            off(3)
        }
        ACCESS read-only
        STATUS mandatory
        DESCRIPTION
            "Heat Mode"
        ::= { conditionSmartStatus 26 }

    conditionSmartStatusHumidifyMode OBJECT-TYPE
        SYNTAX INTEGER  {
            unknown(1),
            on(2),
            off(3)
        }
        ACCESS read-only
        STATUS mandatory
        DESCRIPTION
            "Humidify Mode"
        ::= { conditionSmartStatus 27 }

    conditionSmartStatusDehumidifyMode OBJECT-TYPE
        SYNTAX INTEGER  {
            unknown(1),
            on(2),
            off(3)
        }
        ACCESS read-only
        STATUS mandatory
        DESCRIPTION
            "Dehumidify Mode"
        ::= { conditionSmartStatus 28 }

    conditionSmartStatusCoolingSystemServiceRequired OBJECT-TYPE
        SYNTAX INTEGER  {
            unknown(1),
            no(2),
            yes(3)
        }
        ACCESS read-only
        STATUS mandatory
        DESCRIPTION
            "Cooling System Service Required"
        ::= { conditionSmartStatus 29 }

    conditionSmartStatusHumidifySystemServiceRequired OBJECT-TYPE
        SYNTAX INTEGER  {
            unknown(1),
            no(2),
            yes(3)
        }
        ACCESS read-only
        STATUS mandatory
        DESCRIPTION
            "Humidify System Service Required"
        ::= { conditionSmartStatus 30 }

    conditionSmartStatusAirSystemServiceRequired OBJECT-TYPE
        SYNTAX INTEGER  {
            unknown(1),
            no(2),
            yes(3)
        }
        ACCESS read-only
        STATUS mandatory
        DESCRIPTION
            "Air System Service Required"
        ::= { conditionSmartStatus 31 }

    conditionSmartStatusHumidifierWaterLevelLow OBJECT-TYPE
        SYNTAX INTEGER  {
            unknown(1),
            no(2),
            yes(3)
        }
        ACCESS read-only
        STATUS mandatory
        DESCRIPTION
            "Humidifier Water Level Low"
        ::= { conditionSmartStatus 32 }

    conditionSmartStatusSpareAlarm1 OBJECT-TYPE
        SYNTAX INTEGER  {
            unknown(1),
            no(2),
            yes(3)
        }
        ACCESS read-only
        STATUS mandatory
        DESCRIPTION
            "Spare Alarm 1"
        ::= { conditionSmartStatus 33 }

    conditionSmartStatusSpareAlarm2 OBJECT-TYPE
        SYNTAX INTEGER  {
            unknown(1),
            no(2),
            yes(3)
        }
        ACCESS read-only
        STATUS mandatory
        DESCRIPTION
            "Spare Alarm 2"
        ::= { conditionSmartStatus 34 }

    conditionSmartStatusSpareAlarm3 OBJECT-TYPE
        SYNTAX INTEGER  {
            unknown(1),
            no(2),
            yes(3)
        }
        ACCESS read-only
        STATUS mandatory
        DESCRIPTION
            "Spare Alarm 3"
        ::= { conditionSmartStatus 35 }


    conditionSmartStatusPowerLost OBJECT-TYPE
        SYNTAX INTEGER  {
            unknown(1),
            no(2),
            yes(3)
        }
        ACCESS read-only
        STATUS mandatory
        DESCRIPTION
            "Power Lost"
        ::= { conditionSmartStatus 36 }

    -- ------------------------------------------------------------------------ 
    -- 3.6. the conditionTest group
    -- ------------------------------------------------------------------------ 

    -- ------------------------------------------------------------------------ 
    -- 3.6.1 the conditionBaseTest group
    -- ------------------------------------------------------------------------ 
    
    -- no conditionBaseTest variables

    -- ------------------------------------------------------------------------ 
    -- 3.6.2 the conditionSmartTest group
    -- ------------------------------------------------------------------------ 

    -- no conditionSmartTest variables


    -- ------------------------------------------------------------------------ 
    -- 3.7. the conditionControl group
    -- ------------------------------------------------------------------------ 
    -- 
    -- ------------------------------------------------------------------------ 
    -- 3.7.1 the conditionBaseControl group
    -- ------------------------------------------------------------------------ 
    
    -- no variables

    -- ------------------------------------------------------------------------ 
    -- 3.7.2 the conditionSmartControl group
    -- ------------------------------------------------------------------------ 

    conditionSmartControlRemoteOn OBJECT-TYPE
        SYNTAX INTEGER  {
            noTurnOnCondition(1),
            turnOnCondition(2)
        }
        ACCESS read-write
        STATUS mandatory
        DESCRIPTION
            "Setting this variable to turnOnCondition(2) to turn on condition.
             Setting this value to noTurnOnCondition(1) has no effect.

             The value noTurnOnCondition(1) will always be returned 
             when the variable is read."
        ::= { conditionSmartControl 1 }
         
    conditionSmartControlRemoteOff OBJECT-TYPE
        SYNTAX INTEGER  {
            noTurnOffCondition(1),
            turnOffCondition(2)
        }
        ACCESS read-write
        STATUS mandatory
        DESCRIPTION
            "Setting this variable to turnOffCondition(2) to turn off condition.
             Setting this value to noTurnOffCondition(1) has no effect.

             The value noTurnOffCondition(1) will always be returned 
             when the variable is read."
        ::= { conditionSmartControl 2 }

         
    conditionSmartControlAlarmMute OBJECT-TYPE
        SYNTAX INTEGER  {
            noAlarmMute(1),
            alarmMute(2)
        }
        ACCESS read-write
        STATUS mandatory
        DESCRIPTION
            "Setting this variable to alarmMute(2) to Alarm Mute condition.
             Setting this value to noAlarm Mute(1) has no effect.

             The value noAlarmMute(1) will always be returned 
             when the variable is read."
        ::= { conditionSmartControl 3 }

    -- ------------------------------------------------------------------------
    -- 3.8. the conditionConfig group
    -- ------------------------------------------------------------------------
        -- ------------------------------------------------------------------------ 
    -- 3.8.1 the conditionBaseConfig group
    -- ------------------------------------------------------------------------ 
    
 
    -- ------------------------------------------------------------------------ 
    -- 3.8.2 the conditionSmartConfig group
    -- ------------------------------------------------------------------------ 

    conditionSmartConfigTemperatureSetpoint OBJECT-TYPE
        SYNTAX INTEGER
        ACCESS read-write
        STATUS mandatory
        DESCRIPTION
            "The Temperature Setpoint in °C.  Allowed values are from 
             17 to 26 °C.
    
             If a value other than a supported value is provided in a
             set request, the condition interprets it as a the next higher
             acceptable value.  If the provided value is higher than
             the highest acceptable value, the highest acceptable
             value is used."
        ::= { conditionSmartConfig 1 }
    
    conditionSmartConfigHumidifySetpoint OBJECT-TYPE
        SYNTAX INTEGER
        ACCESS read-write
        STATUS mandatory
        DESCRIPTION
            "The Humidify Setpoint in %RH.  Allowed values are from 
             42 to 60 %RH.
    
             If a value other than a supported value is provided in a
             set request, the condition interprets it as a the next higher
             acceptable value.  If the provided value is higher than
             the highest acceptable value, the highest acceptable
             value is used."
        ::= { conditionSmartConfig 2 }
    

    -- ------------------------------------------------------------------------
    -- 4. the upsAlarm group
    -- ------------------------------------------------------------------------

    -- ------------------------------------------------------------------------
    -- 4.1. the upsBaseAlaram group
    -- ------------------------------------------------------------------------

    -- no upsBaseAlaram variables

    -- ------------------------------------------------------------------------
    -- 4.2. the upsSmartAlarm group
    -- ------------------------------------------------------------------------
    upsSmartAlarmPresentNum OBJECT-TYPE
        SYNTAX INTEGER
        ACCESS read-only
        STATUS mandatory
        DESCRIPTION
           "The present number of active alarams."
        ::= { upsSmartAlarm 1 }

    upsSmartAlarmPresentTable OBJECT-TYPE
        SYNTAX SEQUENCE OF UpsSmartAlarmPresentEntry
        ACCESS not-accessible
        STATUS mandatory
        DESCRIPTION
            "A list of current CONDITION alarms, The number of entries is given
            by the value of conditionSmartAlarmPresentNum."
        ::= { upsSmartAlarm 2 }

    upsSmartAlarmPresentEntry OBJECT-TYPE
        SYNTAX UpsSmartAlarmPresentEntry
        ACCESS not-accessible
        STATUS mandatory
        DESCRIPTION
            "The present alarms list."
        INDEX  { presentAlarmIndex}
        ::= { upsSmartAlarmPresentTable 1 }

    UpsSmartAlarmPresentEntry ::=
        SEQUENCE {
            presentAlarmIndex
                INTEGER,
            presentAlarmTime
                DisplayString,
            presentAlarmId
                INTEGER,
            presentAlarmName
                DisplayString,
            presentAlaramLevel
                INTEGER
        }

    presentAlarmIndex OBJECT-TYPE
        SYNTAX INTEGER
        ACCESS read-only
        STATUS mandatory
        DESCRIPTION
            "The index of the present alaram entry."
        ::= { upsSmartAlarmPresentEntry 1 }

    presentAlarmTime OBJECT-TYPE
        SYNTAX DisplayString
        ACCESS read-only
        STATUS mandatory
        DESCRIPTION
           "The time of the alarm generated, format as yyyy/mm/dd hh:mm:ss."
        ::= { upsSmartAlarmPresentEntry 2 }

    presentAlarmId OBJECT-TYPE
        SYNTAX INTEGER
        ACCESS read-only
        STATUS mandatory
        DESCRIPTION
            "The alarm ID."
       ::= { upsSmartAlarmPresentEntry 3 }

    presentAlarmName OBJECT-TYPE
        SYNTAX DisplayString
        ACCESS read-only
        STATUS mandatory
        DESCRIPTION
           "The name of the alarm."
        ::= { upsSmartAlarmPresentEntry 4 }

    presentAlaramLevel OBJECT-TYPE
        SYNTAX INTEGER {
            information(1),
            warning(2),
            severe(3)
        }
        ACCESS read-only
        STATUS mandatory
        DESCRIPTION
            "The alarm level."
       ::= { upsSmartAlarmPresentEntry 5 }

    -- historical alarms
    upsSmartAlarmHistoryNum OBJECT-TYPE
        SYNTAX INTEGER
        ACCESS read-only
        STATUS mandatory
        DESCRIPTION
           "The number of historical alarms."
        ::= { upsSmartAlarm 3 }

    upsSmartAlarmHistoryTable OBJECT-TYPE
        SYNTAX SEQUENCE OF UpsSmartAlarmHistoryEntry
        ACCESS not-accessible
        STATUS mandatory
        DESCRIPTION
            "A list of historical CONDITION alarms, The number of entries is given
            by the value of conditionSmartAlarmHistoryNum."
        ::= { upsSmartAlarm 4 }

    upsSmartAlarmHistoryEntry OBJECT-TYPE
        SYNTAX UpsSmartAlarmHistoryEntry
        ACCESS not-accessible
        STATUS mandatory
        DESCRIPTION
            "The historical alarms list."
        INDEX  { historyAlarmIndex}
        ::= { upsSmartAlarmHistoryTable 1 }

    UpsSmartAlarmHistoryEntry ::=
        SEQUENCE {
            historyAlarmIndex
                INTEGER,
            historyAlarmTime
                DisplayString,
            historyAlarmId
                INTEGER,
            historyAlarmName
                DisplayString,
            historyAlaramLevel
                INTEGER
        }

    historyAlarmIndex OBJECT-TYPE
        SYNTAX INTEGER
        ACCESS read-only
        STATUS mandatory
        DESCRIPTION
            "The index of the historical alaram entry."
        ::= { upsSmartAlarmHistoryEntry 1 }

    historyAlarmTime OBJECT-TYPE
        SYNTAX DisplayString
        ACCESS read-only
        STATUS mandatory
        DESCRIPTION
           "The time of the alarm generated, format as yyyy/mm/dd hh:mm:ss."
        ::= { upsSmartAlarmHistoryEntry 2 }

    historyAlarmId OBJECT-TYPE
        SYNTAX INTEGER
        ACCESS read-only
        STATUS mandatory
        DESCRIPTION
            "The alarm ID."
       ::= { upsSmartAlarmHistoryEntry 3 }

    historyAlarmName OBJECT-TYPE
        SYNTAX DisplayString
        ACCESS read-only
        STATUS mandatory
        DESCRIPTION
           "The name of the alarm."
        ::= { upsSmartAlarmHistoryEntry 4 }

    historyAlaramLevel OBJECT-TYPE
        SYNTAX INTEGER {
            information(1),
            warning(2),
            severe(3)
        }
        ACCESS read-only
        STATUS mandatory
        DESCRIPTION
            "The alarm level."
       ::= { upsSmartAlarmHistoryEntry 5 }



    -- ------------------------------------------------------------------------
    -- Traps
    -- ------------------------------------------------------------------------

    --
    -- trap args
    --
    trapArgsString OBJECT-TYPE
        SYNTAX  DisplayString
        ACCESS read-only
        STATUS mandatory
        DESCRIPTION
            "This OID allows CM CONDITION traps to be sent with an octet string argument
             that may not be defined in the CM CONDITION MIB.

             A get of this OID will return a NULL string."
        ::= { upsAlarm 2002 }


    communicationInterrupt TRAP-TYPE
        ENTERPRISE CMCondition
        VARIABLES { trapArgsString }
        DESCRIPTION
            "SEVERE: Communication Interrupt."
       --#TYPE "CM CONDITION: Communication Interrupt"
       --#SUMMARY "Communication Interrupt."
       --#ARGUMENTS { }
       --#SEVERITY CRITICAL
       --#TIMEINDEX 1
       --#HELP ""
       --#HELPTAG 0
       --#STATE DEGRADED
        ::= 1


    communicationRestored TRAP-TYPE
        ENTERPRISE CMCondition
        VARIABLES { trapArgsString }
        DESCRIPTION
            "INFORMATION: Communication Restored."
       --#TYPE "CM CONDITION: Communication Restored"
       --#SUMMARY "Communication Restored."
       --#ARGUMENTS { }
       --#SEVERITY INFORMATIONAL
       --#TIMEINDEX 1
       --#HELP ""
       --#HELPTAG 0
       --#STATE OPERATIONAL
        ::= 2

    highTemperatureRecovered TRAP-TYPE
        ENTERPRISE CMCondition
        VARIABLES { trapArgsString }
        DESCRIPTION
            "SEVERE: High Temperature Recovered."
       --#TYPE "CM CONDITION: High Temperature Recovered"
       --#SUMMARY "High Temperature Recovered."
       --#ARGUMENTS { }
       --#SEVERITY INFORMATIONAL
       --#TIMEINDEX 1
       --#HELP ""
       --#HELPTAG 0
       --#STATE OPERATIONAL
        ::= 3


    highTemperature TRAP-TYPE
        ENTERPRISE CMCondition
        VARIABLES { trapArgsString }
        DESCRIPTION
            "SEVERE: High Temperature."
       --#TYPE "CM CONDITION: High Temperature"
       --#SUMMARY "High Temperature."
       --#ARGUMENTS { }
       --#SEVERITY CRITICAL
       --#TIMEINDEX 1
       --#HELP ""
       --#HELPTAG 0
       --#STATE DEGRADED
        ::= 4


    lowTemperatureRecovered TRAP-TYPE
        ENTERPRISE CMCondition
        VARIABLES { trapArgsString }
        DESCRIPTION
            "INFORMATION: Low Temperature Recovered."
       --#TYPE "CM CONDITION: Low Temperature Recovered"
       --#SUMMARY "Low Temperature Recovered."
       --#ARGUMENTS { }
       --#SEVERITY INFORMATIONAL
       --#TIMEINDEX 1
       --#HELP ""
       --#HELPTAG 0
       --#STATE OPERATIONAL
        ::= 5

    lowTemperature TRAP-TYPE
        ENTERPRISE CMCondition
        VARIABLES { trapArgsString }
        DESCRIPTION
            "SEVERE: Low Temperature."
       --#TYPE "CM CONDITION: Low Temperature"
       --#SUMMARY "Low Temperature."
       --#ARGUMENTS { }
       --#SEVERITY CRITICAL
       --#TIMEINDEX 1
       --#HELP ""
       --#HELPTAG 0
       --#STATE DEGRADED
        ::= 6

    highHumidifyRecovered TRAP-TYPE
        ENTERPRISE CMCondition
        VARIABLES { trapArgsString }
        DESCRIPTION
            "SEVERE: High Humidify Recovered."
       --#TYPE "CM CONDITION: High Humidify Recovered"
       --#SUMMARY "High Humidify Recovered."
       --#ARGUMENTS { }
       --#SEVERITY INFORMATIONAL
       --#TIMEINDEX 1
       --#HELP ""
       --#HELPTAG 0
       --#STATE OPERATIONAL
        ::= 7


    highHumidify TRAP-TYPE
        ENTERPRISE CMCondition
        VARIABLES { trapArgsString }
        DESCRIPTION
            "SEVERE: High Humidify."
       --#TYPE "CM CONDITION: High Humidify"
       --#SUMMARY "High Humidify."
       --#ARGUMENTS { }
       --#SEVERITY CRITICAL
       --#TIMEINDEX 1
       --#HELP ""
       --#HELPTAG 0
       --#STATE DEGRADED
        ::= 8


    lowHumidifyRecovered TRAP-TYPE
        ENTERPRISE CMCondition
        VARIABLES { trapArgsString }
        DESCRIPTION
            "INFORMATION: Low Humidify Recovered."
       --#TYPE "CM CONDITION: Low Humidify Recovered"
       --#SUMMARY "Low Humidify Recovered."
       --#ARGUMENTS { }
       --#SEVERITY INFORMATIONAL
       --#TIMEINDEX 1
       --#HELP ""
       --#HELPTAG 0
       --#STATE OPERATIONAL
        ::= 9


    lowHumidify TRAP-TYPE
        ENTERPRISE CMCondition
        VARIABLES { trapArgsString }
        DESCRIPTION
            "SEVERE: Low Humidify."
       --#TYPE "CM CONDITION: Low Humidify"
       --#SUMMARY "Low Humidify."
       --#ARGUMENTS { }
       --#SEVERITY CRITICAL
       --#TIMEINDEX 1
       --#HELP ""
       --#HELPTAG 0
       --#STATE DEGRADED
        ::= 10


    sensorBoardFailureRecovered TRAP-TYPE
        ENTERPRISE CMCondition
        VARIABLES { trapArgsString }
        DESCRIPTION
            "INFORMATION: Sensor Board Failure Recovered."
       --#TYPE "CM CONDITION: Sensor Board Failure Recovered"
       --#SUMMARY "Sensor Board Failure Recovered."
       --#ARGUMENTS { }
       --#SEVERITY INFORMATIONAL
       --#TIMEINDEX 1
       --#HELP ""
       --#HELPTAG 0
       --#STATE OPERATIONAL
        ::= 11
        
    sensorBoardFailure TRAP-TYPE
        ENTERPRISE CMCondition
        VARIABLES { trapArgsString }
        DESCRIPTION
            "INFORMATION: Sensor Board Failure."
       --#TYPE "CM CONDITION: Sensor Board Failure"
       --#SUMMARY "Sensor Board Failure."
       --#ARGUMENTS { }
       --#SEVERITY CRITICAL
       --#TIMEINDEX 1
       --#HELP ""
       --#HELPTAG 0
       --#STATE DEGRADED
        ::= 12

    airLossRecovered TRAP-TYPE
        ENTERPRISE CMCondition
        VARIABLES { trapArgsString }
        DESCRIPTION
            "SEVERE: Air Loss Recovered."
       --#TYPE "CM CONDITION: Air Loss Recovered"
       --#SUMMARY "Air Loss Recovered"
       --#ARGUMENTS { }
       --#SEVERITY INFORMATIONAL
       --#TIMEINDEX 1
       --#HELP ""
       --#HELPTAG 0
       --#STATE OPERATIONAL
        ::= 13


    airLoss TRAP-TYPE
        ENTERPRISE CMCondition
        VARIABLES { trapArgsString }
        DESCRIPTION
            "SEVERE: Air Loss."
       --#TYPE "CM CONDITION: Air Loss"
       --#SUMMARY "Air Loss."
       --#ARGUMENTS { }
       --#SEVERITY CRITICAL
       --#TIMEINDEX 1
       --#HELP ""
       --#HELPTAG 0
       --#STATE DEGRADED
        ::= 14

    waterUnderfloorRecovered TRAP-TYPE
        ENTERPRISE CMCondition
        VARIABLES { trapArgsString }
        DESCRIPTION
            "INFORMATION: Water Underfloor Recovered."
       --#TYPE "CM CONDITION: Water Underfloor Recovered"
       --#SUMMARY "Water Underfloor Recovered."
       --#ARGUMENTS { }
       --#SEVERITY INFORMATIONAL
       --#TIMEINDEX 1
       --#HELP ""
       --#HELPTAG 0
       --#STATE OPERATIONAL
        ::= 15

    waterUnderfloor TRAP-TYPE
        ENTERPRISE CMCondition
        VARIABLES { trapArgsString }
        DESCRIPTION
            "SEVERE: Water Underfloor."
       --#TYPE "CM CONDITION: Water Underfloor"
       --#SUMMARY "Water Underfloor."
       --#ARGUMENTS { }
       --#SEVERITY CRITICAL
       --#TIMEINDEX 1
       --#HELP ""
       --#HELPTAG 0
       --#STATE DEGRADED
        ::= 16

    compressor1HighPressureRecovered TRAP-TYPE
        ENTERPRISE CMCondition
        VARIABLES { trapArgsString }
        DESCRIPTION
            "INFORMATION: Compressor 1 High Pressure Recovered."
       --#TYPE "LDS9811 CONDITION: Compressor 1 High Pressure Recovered"
       --#SUMMARY "Compressor 1 High Pressure Recovered."
       --#ARGUMENTS { }
       --#SEVERITY INFORMATIONAL
       --#TIMEINDEX 1
       --#HELP ""
       --#HELPTAG 0
       --#STATE OPERATIONAL
        ::= 17

    compressor1HighPressure TRAP-TYPE
        ENTERPRISE CMCondition
        VARIABLES { trapArgsString }
        DESCRIPTION
            "SEVERE: Compressor 1 High Pressure."
       --#TYPE "LDS9811 CONDITION: Compressor 1 High Pressure"
       --#SUMMARY "Compressor 1 High Pressure."
       --#ARGUMENTS { }
       --#SEVERITY CRITICAL
       --#TIMEINDEX 1
       --#HELP ""
       --#HELPTAG 0
       --#STATE DEGRADED
        ::= 18

    compressor2HighPressureRecovered TRAP-TYPE
        ENTERPRISE CMCondition
        VARIABLES { trapArgsString }
        DESCRIPTION
            "SEVERE: Compressor 2 High Pressure Recovered."
       --#TYPE "LDS9811 CONDITION: Compressor 2 High Pressure Recovered"
       --#SUMMARY "Compressor 2 High Pressure Recovered"
       --#ARGUMENTS { }
       --#SEVERITY INFORMATIONAL
       --#TIMEINDEX 1
       --#HELP ""
       --#HELPTAG 0
       --#STATE OPERATIONAL
        ::= 19


    compressor2HighPressure TRAP-TYPE
        ENTERPRISE CMCondition
        VARIABLES { trapArgsString }
        DESCRIPTION
            "SEVERE: Compressor 2 High Pressure."
       --#TYPE "LDS9811 CONDITION: Compressor 2 High Pressure"
       --#SUMMARY "Compressor 2 High Pressure."
       --#ARGUMENTS { }
       --#SEVERITY CRITICAL
       --#TIMEINDEX 1
       --#HELP ""
       --#HELPTAG 0
       --#STATE DEGRADED
        ::= 20


    compressor1LowPressureRecovered TRAP-TYPE
        ENTERPRISE CMCondition
        VARIABLES { trapArgsString }
        DESCRIPTION
            "INFORMATION: Compressor 1 Low Pressure Recovered."
       --#TYPE "LDS9811 CONDITION: Compressor 1 Low Pressure Recovered"
       --#SUMMARY "Compressor 1 Low Pressure Recovered."
       --#ARGUMENTS { }
       --#SEVERITY INFORMATIONAL
       --#TIMEINDEX 1
       --#HELP ""
       --#HELPTAG 0
       --#STATE OPERATIONAL
        ::= 21

    compressor1LowPressure TRAP-TYPE
        ENTERPRISE CMCondition
        VARIABLES { trapArgsString }
        DESCRIPTION
            "SEVERE: Compressor 1 Low Pressure."
       --#TYPE "LDS9811 CONDITION: Compressor 1 Low Pressure"
       --#SUMMARY "Compressor 1 Low Pressure."
       --#ARGUMENTS { }
       --#SEVERITY CRITICAL
       --#TIMEINDEX 1
       --#HELP ""
       --#HELPTAG 0
       --#STATE DEGRADED
        ::= 22

    compressor2LowPressureRecovered TRAP-TYPE
        ENTERPRISE CMCondition
        VARIABLES { trapArgsString }
        DESCRIPTION
            "SEVERE: Compressor 2 Low Pressure Recovered."
       --#TYPE "LDS9811 CONDITION: Compressor 2 Low Pressure Recovered"
       --#SUMMARY "Compressor 2 Low Pressure Recovered"
       --#ARGUMENTS { }
       --#SEVERITY INFORMATIONAL
       --#TIMEINDEX 1
       --#HELP ""
       --#HELPTAG 0
       --#STATE OPERATIONAL
        ::= 23


    compressor2LowPressure TRAP-TYPE
        ENTERPRISE CMCondition
        VARIABLES { trapArgsString }
        DESCRIPTION
            "SEVERE: Compressor 2 Low Pressure."
       --#TYPE "LDS9811 CONDITION: Compressor 2 Low Pressure"
       --#SUMMARY "Compressor 2 Low Pressure."
       --#ARGUMENTS { }
       --#SEVERITY CRITICAL
       --#TIMEINDEX 1
       --#HELP ""
       --#HELPTAG 0
       --#STATE DEGRADED
        ::= 24

    coolingSystemServiceRequiredRecovered TRAP-TYPE
        ENTERPRISE CMCondition
        VARIABLES { trapArgsString }
        DESCRIPTION
            "INFORMATION: Cooling System Service Required Recovered."
       --#TYPE "CM CONDITION: Cooling System Service Required Recovered"
       --#SUMMARY "Cooling System Service Required Recovered."
       --#ARGUMENTS { }
       --#SEVERITY INFORMATIONAL
       --#TIMEINDEX 1
       --#HELP ""
       --#HELPTAG 0
       --#STATE OPERATIONAL
        ::= 25

    coolingSystemServiceRequired TRAP-TYPE
        ENTERPRISE CMCondition
        VARIABLES { trapArgsString }
        DESCRIPTION
            "INFORMATION: Cooling System Service Required."
       --#TYPE "CM CONDITION: Cooling System Service Required"
       --#SUMMARY "Cooling System Service Required."
       --#ARGUMENTS { }
       --#SEVERITY CRITICAL
       --#TIMEINDEX 1
       --#HELP ""
       --#HELPTAG 0
       --#STATE DEGRADED
        ::= 26

    humidifySystemServiceRequiredRecovered TRAP-TYPE
        ENTERPRISE CMCondition
        VARIABLES { trapArgsString }
        DESCRIPTION
            "INFORMATION: Humidify System Service Required Recovered."
       --#TYPE "CM CONDITION: Humidify System Service Required Recovered"
       --#SUMMARY "Humidify System Service Required Recovered."
       --#ARGUMENTS { }
       --#SEVERITY INFORMATIONAL
       --#TIMEINDEX 1
       --#HELP ""
       --#HELPTAG 0
       --#STATE OPERATIONAL
        ::= 27

    humidifySystemServiceRequired TRAP-TYPE
        ENTERPRISE CMCondition
        VARIABLES { trapArgsString }
        DESCRIPTION
            "SEVERE: Humidify System Service Required."
       --#TYPE "CM CONDITION: Humidify System Service Required"
       --#SUMMARY "Humidify System Service Required."
       --#ARGUMENTS { }
       --#SEVERITY CRITICAL
       --#TIMEINDEX 1
       --#HELP ""
       --#HELPTAG 0
       --#STATE DEGRADED
        ::= 28

    airSystemServiceRequiredRecovered TRAP-TYPE
        ENTERPRISE CMCondition
        VARIABLES { trapArgsString }
        DESCRIPTION
            "SEVERE: Air System Service Required Recovered."
       --#TYPE "CM CONDITION: Air System Service Required Recovered"
       --#SUMMARY "Air System Service Required Recovered."
       --#ARGUMENTS { }
       --#SEVERITY INFORMATIONAL
       --#TIMEINDEX 1
       --#HELP ""
       --#HELPTAG 0
       --#STATE OPERATIONAL
        ::= 29

    airSystemServiceRequired TRAP-TYPE
        ENTERPRISE CMCondition
        VARIABLES { trapArgsString }
        DESCRIPTION
            "SEVERE: Air System Service Required."
       --#TYPE "CM CONDITION: Air System Service Required"
       --#SUMMARY "Air System Service Required."
       --#ARGUMENTS { }
       --#SEVERITY CRITICAL
       --#TIMEINDEX 1
       --#HELP ""
       --#HELPTAG 0
       --#STATE DEGRADED
        ::= 30

    humidifierWaterLevelLowRecovered TRAP-TYPE
        ENTERPRISE CMCondition
        VARIABLES { trapArgsString }
        DESCRIPTION
            "INFORMATION: Humidifier Water Level Low Recovered."
       --#TYPE "CM CONDITION: Humidifier Water Level Low Recovered"
       --#SUMMARY "Humidifier Water Level Low Recovered."
       --#ARGUMENTS { }
       --#SEVERITY INFORMATIONAL
       --#TIMEINDEX 1
       --#HELP ""
       --#HELPTAG 0
       --#STATE OPERATIONAL
        ::= 31

    humidifierWaterLevelLow TRAP-TYPE
        ENTERPRISE CMCondition
        VARIABLES { trapArgsString }
        DESCRIPTION
            "SEVERE: Humidifier Water Level Low."
       --#TYPE "CM CONDITION: Humidifier Water Level Low"
       --#SUMMARY "Humidifier Water Level Low."
       --#ARGUMENTS { }
       --#SEVERITY CRITICAL
       --#TIMEINDEX 1
       --#HELP ""
       --#HELPTAG 0
       --#STATE DEGRADED
        ::= 32


    spareAlarm1Recovered TRAP-TYPE
        ENTERPRISE CMCondition
        VARIABLES { trapArgsString }
        DESCRIPTION
            "SEVERE: Spare Alarm 1 Recovered."
       --#TYPE "CM CONDITION: Spare Alarm 1 Recovered"
       --#SUMMARY "Spare Alarm 1 Recovered."
       --#ARGUMENTS { }
       --#SEVERITY INFORMATIONAL
       --#TIMEINDEX 1
       --#HELP ""
       --#HELPTAG 0
       --#STATE OPERATIONAL
        ::= 33


    spareAlarm1 TRAP-TYPE
        ENTERPRISE CMCondition
        VARIABLES { trapArgsString }
        DESCRIPTION
            "SEVERE: Spare Alarm 1."
       --#TYPE "CM CONDITION: Spare Alarm 1"
       --#SUMMARY "Spare Alarm 1."
       --#ARGUMENTS { }
       --#SEVERITY CRITICAL
       --#TIMEINDEX 1
       --#HELP ""
       --#HELPTAG 0
       --#STATE DEGRADED
        ::= 34

    spareAlarm2Recovered TRAP-TYPE
        ENTERPRISE CMCondition
        VARIABLES { trapArgsString }
        DESCRIPTION
            "SEVERE: Spare Alarm 2 Recovered."
       --#TYPE "CM CONDITION: Spare Alarm 2 Recovered"
       --#SUMMARY "Spare Alarm 2 Recovered."
       --#ARGUMENTS { }
       --#SEVERITY INFORMATIONAL
       --#TIMEINDEX 1
       --#HELP ""
       --#HELPTAG 0
       --#STATE OPERATIONAL
        ::= 35


    spareAlarm2 TRAP-TYPE
        ENTERPRISE CMCondition
        VARIABLES { trapArgsString }
        DESCRIPTION
            "SEVERE: Spare Alarm 2."
       --#TYPE "CM CONDITION: Spare Alarm 2"
       --#SUMMARY "Spare Alarm 2."
       --#ARGUMENTS { }
       --#SEVERITY CRITICAL
       --#TIMEINDEX 1
       --#HELP ""
       --#HELPTAG 0
       --#STATE DEGRADED
        ::= 36

    spareAlarm3Recovered TRAP-TYPE
        ENTERPRISE CMCondition
        VARIABLES { trapArgsString }
        DESCRIPTION
            "SEVERE: Spare Alarm 3 Recovered."
       --#TYPE "CM CONDITION: Spare Alarm 3 Recovered"
       --#SUMMARY "Spare Alarm 3 Recovered."
       --#ARGUMENTS { }
       --#SEVERITY INFORMATIONAL
       --#TIMEINDEX 1
       --#HELP ""
       --#HELPTAG 0
       --#STATE OPERATIONAL
        ::= 37


    spareAlarm3 TRAP-TYPE
        ENTERPRISE CMCondition
        VARIABLES { trapArgsString }
        DESCRIPTION
            "SEVERE: Spare Alarm 3."
       --#TYPE "CM CONDITION: Spare Alarm 3"
       --#SUMMARY "Spare Alarm 3."
       --#ARGUMENTS { }
       --#SEVERITY CRITICAL
       --#TIMEINDEX 1
       --#HELP ""
       --#HELPTAG 0
       --#STATE DEGRADED
        ::= 38


    powerLostRecovered TRAP-TYPE
        ENTERPRISE CMCondition
        VARIABLES { trapArgsString }
        DESCRIPTION
            "SEVERE: Power Lost Recovered."
       --#TYPE "CM CONDITION: Power Lost Recovered"
       --#SUMMARY "Power Lost Recovered."
       --#ARGUMENTS { }
       --#SEVERITY INFORMATIONAL
       --#TIMEINDEX 1
       --#HELP ""
       --#HELPTAG 0
       --#STATE OPERATIONAL
        ::= 39


    powerLost TRAP-TYPE
        ENTERPRISE CMCondition
        VARIABLES { trapArgsString }
        DESCRIPTION
            "SEVERE: Power Lost."
       --#TYPE "CM CONDITION: Power Lost"
       --#SUMMARY "Power Lost."
       --#ARGUMENTS { }
       --#SEVERITY CRITICAL
       --#TIMEINDEX 1
       --#HELP ""
       --#HELPTAG 0
       --#STATE DEGRADED
        ::= 40

END -- end of CM-CONDITION-MIB
