--
-- CAREL-flccu1314gmar.MIB
-- MIB generated by CAREL
-- Friday, 29 January 2016
--

    CAREL-flccu1314gmar-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI
			DisplayString
				FROM SNMPv2-TC;
		
        flccu1314gmarMIB MODULE-IDENTITY
      		LAST-UPDATED  "201601290903Z"		-- January 29, 2016 at 09:03 GMT
      		ORGANIZATION  "CAREL Industries S.r.l."
      		CONTACT-INFO
                "
                        Carel Industries S.r.l.
                        Via dell'Industria, 11
                        35020 Brugine (PD) Italy
                        Tel: +39 049 9716611
                        E-mail: carel@carel.com
                "
      		DESCRIPTION
                "This is the MIB module for the flccu1314gmar device."
			REVISION "201601290903Z"
			DESCRIPTION
				"version4pCOweb"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { flccu1314gmarMIB 1 }

        -- 1.3.6.1.4.1.9839.2.1.1.1
        fan_mode OBJECT-TYPE
                    SYNTAX Integer32 (0..1)
                    UNITS "N/A"
                    MAX-ACCESS read-only
                    STATUS current
                    DESCRIPTION "Fan Mode"
                    DEFVAL { 0 }
                    ::= { digitalObjects 1 }

        -- 1.3.6.1.4.1.9839.2.1.1.2
        cool_mode OBJECT-TYPE
                    SYNTAX Integer32 (0..1)
                    UNITS "N/A"
                    MAX-ACCESS read-only
                    STATUS current
                    DESCRIPTION "Cooling Mode"
                    DEFVAL { 0 }
                    ::= { digitalObjects 2 }

        -- 1.3.6.1.4.1.9839.2.1.1.3
        heat_mode OBJECT-TYPE
                    SYNTAX Integer32 (0..1)
                    UNITS "N/A"
                    MAX-ACCESS read-only
                    STATUS current
                    DESCRIPTION "Heating Mode"
                    DEFVAL { 0 }
                    ::= { digitalObjects 3 }

        -- 1.3.6.1.4.1.9839.2.1.1.4
        dehumid_mode OBJECT-TYPE
                    SYNTAX Integer32 (0..1)
                    UNITS "N/A"
                    MAX-ACCESS read-only
                    STATUS current
                    DESCRIPTION "Dehumidification Mode"
                    DEFVAL { 0 }
                    ::= { digitalObjects 4 }

        -- 1.3.6.1.4.1.9839.2.1.1.5
        humid_mode OBJECT-TYPE
                    SYNTAX Integer32 (0..1)
                    UNITS "N/A"
                    MAX-ACCESS read-only
                    STATUS current
                    DESCRIPTION "Humidification Mode"
                    DEFVAL { 0 }
                    ::= { digitalObjects 5 }

        -- 1.3.6.1.4.1.9839.2.1.1.6
        damper_mode OBJECT-TYPE
                    SYNTAX Integer32 (0..1)
                    UNITS "N/A"
                    MAX-ACCESS read-only
                    STATUS current
                    DESCRIPTION "Damper Mode"
                    DEFVAL { 0 }
                    ::= { digitalObjects 6 }

        -- 1.3.6.1.4.1.9839.2.1.1.7
        manual_proc OBJECT-TYPE
                    SYNTAX Integer32 (0..1)
                    UNITS "N/A"
                    MAX-ACCESS read-only
                    STATUS current
                    DESCRIPTION "Manual Control"
                    DEFVAL { 0 }
                    ::= { digitalObjects 7 }

        -- 1.3.6.1.4.1.9839.2.1.1.8
        act_pumpdown OBJECT-TYPE
                    SYNTAX Integer32 (0..1)
                    UNITS "N/A"
                    MAX-ACCESS read-only
                    STATUS current
                    DESCRIPTION "Pumpdown"
                    DEFVAL { 0 }
                    ::= { digitalObjects 8 }

        -- 1.3.6.1.4.1.9839.2.1.1.9
        pumpdown_c1 OBJECT-TYPE
                    SYNTAX Integer32 (0..1)
                    UNITS "N/A"
                    MAX-ACCESS read-only
                    STATUS current
                    DESCRIPTION "Comp 1 Pumpdown"
                    DEFVAL { 0 }
                    ::= { digitalObjects 9 }

        -- 1.3.6.1.4.1.9839.2.1.1.10
        pumpdown_c2 OBJECT-TYPE
                    SYNTAX Integer32 (0..1)
                    UNITS "N/A"
                    MAX-ACCESS read-only
                    STATUS current
                    DESCRIPTION "Comp 2 Pumpdown"
                    DEFVAL { 0 }
                    ::= { digitalObjects 10 }

        -- 1.3.6.1.4.1.9839.2.1.1.21
        evap_fan_ol1 OBJECT-TYPE
                    SYNTAX Integer32 (0..1)
                    UNITS "N/A"
                    MAX-ACCESS read-only
                    STATUS current
                    DESCRIPTION "Blower Fan 1 Overload Status"
                    DEFVAL { 0 }
                    ::= { digitalObjects 21 }

        -- 1.3.6.1.4.1.9839.2.1.1.22
        evap_fan_ol2 OBJECT-TYPE
                    SYNTAX Integer32 (0..1)
                    UNITS "N/A"
                    MAX-ACCESS read-only
                    STATUS current
                    DESCRIPTION "Blower Fan 2 Overload Status"
                    DEFVAL { 0 }
                    ::= { digitalObjects 22 }

        -- 1.3.6.1.4.1.9839.2.1.1.23
        air_flow OBJECT-TYPE
                    SYNTAX Integer32 (0..1)
                    UNITS "N/A"
                    MAX-ACCESS read-only
                    STATUS current
                    DESCRIPTION "Air Flow Switch Status"
                    DEFVAL { 0 }
                    ::= { digitalObjects 23 }

        -- 1.3.6.1.4.1.9839.2.1.1.24
        air_filter OBJECT-TYPE
                    SYNTAX Integer32 (0..1)
                    UNITS "N/A"
                    MAX-ACCESS read-only
                    STATUS current
                    DESCRIPTION "Filter Diff. Pressure Switch Status"
                    DEFVAL { 0 }
                    ::= { digitalObjects 24 }

        -- 1.3.6.1.4.1.9839.2.1.1.25
        low_press1 OBJECT-TYPE
                    SYNTAX Integer32 (0..1)
                    UNITS "N/A"
                    MAX-ACCESS read-only
                    STATUS current
                    DESCRIPTION "Comp 1 Low Pressure Switch Status"
                    DEFVAL { 0 }
                    ::= { digitalObjects 25 }

        -- 1.3.6.1.4.1.9839.2.1.1.26
        high_press1 OBJECT-TYPE
                    SYNTAX Integer32 (0..1)
                    UNITS "N/A"
                    MAX-ACCESS read-only
                    STATUS current
                    DESCRIPTION "Comp 1 High Pressure Switch Status"
                    DEFVAL { 0 }
                    ::= { digitalObjects 26 }

        -- 1.3.6.1.4.1.9839.2.1.1.27
        low_press2 OBJECT-TYPE
                    SYNTAX Integer32 (0..1)
                    UNITS "N/A"
                    MAX-ACCESS read-only
                    STATUS current
                    DESCRIPTION "Comp 2 Low Pressure Switch Status"
                    DEFVAL { 0 }
                    ::= { digitalObjects 27 }

        -- 1.3.6.1.4.1.9839.2.1.1.28
        high_press2 OBJECT-TYPE
                    SYNTAX Integer32 (0..1)
                    UNITS "N/A"
                    MAX-ACCESS read-only
                    STATUS current
                    DESCRIPTION "Comp 2 High Pressure Switch Status"
                    DEFVAL { 0 }
                    ::= { digitalObjects 28 }

        -- 1.3.6.1.4.1.9839.2.1.1.29
        customer_alarm OBJECT-TYPE
                    SYNTAX Integer32 (0..1)
                    UNITS "N/A"
                    MAX-ACCESS read-only
                    STATUS current
                    DESCRIPTION "Customer Alarm Interlock Status"
                    DEFVAL { 0 }
                    ::= { digitalObjects 29 }

        -- 1.3.6.1.4.1.9839.2.1.1.30
        remote_on_off OBJECT-TYPE
                    SYNTAX Integer32 (0..1)
                    UNITS "N/A"
                    MAX-ACCESS read-only
                    STATUS current
                    DESCRIPTION "Remote Start/Stop Input Status"
                    DEFVAL { 0 }
                    ::= { digitalObjects 30 }

        -- 1.3.6.1.4.1.9839.2.1.1.31
        water_flood OBJECT-TYPE
                    SYNTAX Integer32 (0..1)
                    UNITS "N/A"
                    MAX-ACCESS read-only
                    STATUS current
                    DESCRIPTION "Under Floor Water Detector Status"
                    DEFVAL { 0 }
                    ::= { digitalObjects 31 }

        -- 1.3.6.1.4.1.9839.2.1.1.32
        water_level OBJECT-TYPE
                    SYNTAX Integer32 (0..1)
                    UNITS "N/A"
                    MAX-ACCESS read-only
                    STATUS current
                    DESCRIPTION "Humidifier Water Level"
                    DEFVAL { 0 }
                    ::= { digitalObjects 32 }

        -- 1.3.6.1.4.1.9839.2.1.1.33
        chw_thermostat OBJECT-TYPE
                    SYNTAX Integer32 (0..1)
                    UNITS "N/A"
                    MAX-ACCESS read-only
                    STATUS current
                    DESCRIPTION "CHW Thermostat Status"
                    DEFVAL { 0 }
                    ::= { digitalObjects 33 }

        -- 1.3.6.1.4.1.9839.2.1.1.34
        flow_sw OBJECT-TYPE
                    SYNTAX Integer32 (0..1)
                    UNITS "N/A"
                    MAX-ACCESS read-only
                    STATUS current
                    DESCRIPTION "CHW Flow Switch Status"
                    DEFVAL { 0 }
                    ::= { digitalObjects 34 }

        -- 1.3.6.1.4.1.9839.2.1.1.35
        smoke_detector OBJECT-TYPE
                    SYNTAX Integer32 (0..1)
                    UNITS "N/A"
                    MAX-ACCESS read-only
                    STATUS current
                    DESCRIPTION "Smoke Detector Status"
                    DEFVAL { 0 }
                    ::= { digitalObjects 35 }

        -- 1.3.6.1.4.1.9839.2.1.1.36
        indoor_diff OBJECT-TYPE
                    SYNTAX Integer32 (0..1)
                    UNITS "N/A"
                    MAX-ACCESS read-only
                    STATUS current
                    DESCRIPTION "Indoor Pressure Diff. Switch Status"
                    DEFVAL { 0 }
                    ::= { digitalObjects 36 }

        -- 1.3.6.1.4.1.9839.2.1.1.37
        heater_ol1 OBJECT-TYPE
                    SYNTAX Integer32 (0..1)
                    UNITS "N/A"
                    MAX-ACCESS read-only
                    STATUS current
                    DESCRIPTION "Heater 1 Overload Status"
                    DEFVAL { 0 }
                    ::= { digitalObjects 37 }

        -- 1.3.6.1.4.1.9839.2.1.1.38
        heater_ol2 OBJECT-TYPE
                    SYNTAX Integer32 (0..1)
                    UNITS "N/A"
                    MAX-ACCESS read-only
                    STATUS current
                    DESCRIPTION "Heater 2&3 Overload Status"
                    DEFVAL { 0 }
                    ::= { digitalObjects 38 }

        -- 1.3.6.1.4.1.9839.2.1.1.51
        evap_fan1a OBJECT-TYPE
                    SYNTAX Integer32 (0..1)
                    UNITS "N/A"
                    MAX-ACCESS read-only
                    STATUS current
                    DESCRIPTION "Blower Fan 1 Output"
                    DEFVAL { 0 }
                    ::= { digitalObjects 51 }

        -- 1.3.6.1.4.1.9839.2.1.1.52
        evap_fan2 OBJECT-TYPE
                    SYNTAX Integer32 (0..1)
                    UNITS "N/A"
                    MAX-ACCESS read-only
                    STATUS current
                    DESCRIPTION "Blower Fan 2 Output"
                    DEFVAL { 0 }
                    ::= { digitalObjects 52 }

        -- 1.3.6.1.4.1.9839.2.1.1.53
        compressor1 OBJECT-TYPE
                    SYNTAX Integer32 (0..1)
                    UNITS "N/A"
                    MAX-ACCESS read-only
                    STATUS current
                    DESCRIPTION "Compressor 1 Output"
                    DEFVAL { 0 }
                    ::= { digitalObjects 53 }

        -- 1.3.6.1.4.1.9839.2.1.1.54
        compressor2 OBJECT-TYPE
                    SYNTAX Integer32 (0..1)
                    UNITS "N/A"
                    MAX-ACCESS read-only
                    STATUS current
                    DESCRIPTION "Compressor 2 Output"
                    DEFVAL { 0 }
                    ::= { digitalObjects 54 }

        -- 1.3.6.1.4.1.9839.2.1.1.55
        heater1 OBJECT-TYPE
                    SYNTAX Integer32 (0..1)
                    UNITS "N/A"
                    MAX-ACCESS read-only
                    STATUS current
                    DESCRIPTION "Heater 1 Output"
                    DEFVAL { 0 }
                    ::= { digitalObjects 55 }

        -- 1.3.6.1.4.1.9839.2.1.1.56
        heater2 OBJECT-TYPE
                    SYNTAX Integer32 (0..1)
                    UNITS "N/A"
                    MAX-ACCESS read-only
                    STATUS current
                    DESCRIPTION "Heater 2&3 Output"
                    DEFVAL { 0 }
                    ::= { digitalObjects 56 }

        -- 1.3.6.1.4.1.9839.2.1.1.57
        global_alarm OBJECT-TYPE
                    SYNTAX Integer32 (0..1)
                    UNITS "N/A"
                    MAX-ACCESS read-only
                    STATUS current
                    DESCRIPTION "Global (general) alarm"
                    DEFVAL { 0 }
                    ::= { digitalObjects 57 }

        -- 1.3.6.1.4.1.9839.2.1.1.58
        comp1_liq OBJECT-TYPE
                    SYNTAX Integer32 (0..1)
                    UNITS "N/A"
                    MAX-ACCESS read-only
                    STATUS current
                    DESCRIPTION "Comp 1 Liquid Line Sol Vlv"
                    DEFVAL { 0 }
                    ::= { digitalObjects 58 }

        -- 1.3.6.1.4.1.9839.2.1.1.59
        comp2_liq OBJECT-TYPE
                    SYNTAX Integer32 (0..1)
                    UNITS "N/A"
                    MAX-ACCESS read-only
                    STATUS current
                    DESCRIPTION "Comp 2 Liquid Line Sol Vlv"
                    DEFVAL { 0 }
                    ::= { digitalObjects 59 }

        -- 1.3.6.1.4.1.9839.2.1.1.60
        humidifier_output OBJECT-TYPE
                    SYNTAX Integer32 (0..1)
                    UNITS "N/A"
                    MAX-ACCESS read-only
                    STATUS current
                    DESCRIPTION "Humidifier Output"
                    DEFVAL { 0 }
                    ::= { digitalObjects 60 }

        -- 1.3.6.1.4.1.9839.2.1.1.61
        fill1 OBJECT-TYPE
                    SYNTAX Integer32 (0..1)
                    UNITS "N/A"
                    MAX-ACCESS read-only
                    STATUS current
                    DESCRIPTION "Humdifier Fill Sol Vlv"
                    DEFVAL { 0 }
                    ::= { digitalObjects 61 }

        -- 1.3.6.1.4.1.9839.2.1.1.62
        drain1 OBJECT-TYPE
                    SYNTAX Integer32 (0..1)
                    UNITS "N/A"
                    MAX-ACCESS read-only
                    STATUS current
                    DESCRIPTION "Humidifier Drain Vlv"
                    DEFVAL { 0 }
                    ::= { digitalObjects 62 }

        -- 1.3.6.1.4.1.9839.2.1.1.63
        open_cool_d3p OBJECT-TYPE
                    SYNTAX Integer32 (0..1)
                    UNITS "N/A"
                    MAX-ACCESS read-only
                    STATUS current
                    DESCRIPTION "CHW 3-Point Vlv Open"
                    DEFVAL { 0 }
                    ::= { digitalObjects 63 }

        -- 1.3.6.1.4.1.9839.2.1.1.64
        close_cool_d3p OBJECT-TYPE
                    SYNTAX Integer32 (0..1)
                    UNITS "N/A"
                    MAX-ACCESS read-only
                    STATUS current
                    DESCRIPTION "CHW 3-Point Valve Close"
                    DEFVAL { 0 }
                    ::= { digitalObjects 64 }

        -- 1.3.6.1.4.1.9839.2.1.1.65
        buzzer OBJECT-TYPE
                    SYNTAX Integer32 (0..1)
                    UNITS "N/A"
                    MAX-ACCESS read-only
                    STATUS current
                    DESCRIPTION "Status of the buzzer (0=buzzer OFF, 1=buzzer ON) (only if MANUAL_BUZZER_MNG=0)"
                    DEFVAL { 0 }
                    ::= { digitalObjects 65 }

        -- 1.3.6.1.4.1.9839.2.1.1.81
        mal_high_press1 OBJECT-TYPE
                    SYNTAX Integer32 (0..1)
                    UNITS "N/A"
                    MAX-ACCESS read-only
                    STATUS current
                    DESCRIPTION "Comp1 High Pressure Alarm"
                    DEFVAL { 0 }
                    ::= { digitalObjects 81 }

        -- 1.3.6.1.4.1.9839.2.1.1.82
        mal_press_lp1 OBJECT-TYPE
                    SYNTAX Integer32 (0..1)
                    UNITS "N/A"
                    MAX-ACCESS read-only
                    STATUS current
                    DESCRIPTION "Comp 1 Low Pressure Alarm"
                    DEFVAL { 0 }
                    ::= { digitalObjects 82 }

        -- 1.3.6.1.4.1.9839.2.1.1.83
        mal_high_press2 OBJECT-TYPE
                    SYNTAX Integer32 (0..1)
                    UNITS "N/A"
                    MAX-ACCESS read-only
                    STATUS current
                    DESCRIPTION "Comp 2 High Pressure Alarm"
                    DEFVAL { 0 }
                    ::= { digitalObjects 83 }

        -- 1.3.6.1.4.1.9839.2.1.1.84
        mal_press_lp2 OBJECT-TYPE
                    SYNTAX Integer32 (0..1)
                    UNITS "N/A"
                    MAX-ACCESS read-only
                    STATUS current
                    DESCRIPTION "Comp 2 Low Pressure Alarm"
                    DEFVAL { 0 }
                    ::= { digitalObjects 84 }

        -- 1.3.6.1.4.1.9839.2.1.1.85
        mal_room_humid OBJECT-TYPE
                    SYNTAX Integer32 (0..1)
                    UNITS "N/A"
                    MAX-ACCESS read-only
                    STATUS current
                    DESCRIPTION "Room Humidity Probe Faulty"
                    DEFVAL { 0 }
                    ::= { digitalObjects 85 }

        -- 1.3.6.1.4.1.9839.2.1.1.86
        mal_h_room_temp OBJECT-TYPE
                    SYNTAX Integer32 (0..1)
                    UNITS "N/A"
                    MAX-ACCESS read-only
                    STATUS current
                    DESCRIPTION "High Romm Temp Alarm"
                    DEFVAL { 0 }
                    ::= { digitalObjects 86 }

        -- 1.3.6.1.4.1.9839.2.1.1.87
        mal_l_room_temp OBJECT-TYPE
                    SYNTAX Integer32 (0..1)
                    UNITS "N/A"
                    MAX-ACCESS read-only
                    STATUS current
                    DESCRIPTION "Low Room Temp Alarm"
                    DEFVAL { 0 }
                    ::= { digitalObjects 87 }

        -- 1.3.6.1.4.1.9839.2.1.1.88
        mal_room_temp OBJECT-TYPE
                    SYNTAX Integer32 (0..1)
                    UNITS "N/A"
                    MAX-ACCESS read-only
                    STATUS current
                    DESCRIPTION "Room Temp Probe Faulty"
                    DEFVAL { 0 }
                    ::= { digitalObjects 88 }

        -- 1.3.6.1.4.1.9839.2.1.1.89
        mal_supply_air OBJECT-TYPE
                    SYNTAX Integer32 (0..1)
                    UNITS "N/A"
                    MAX-ACCESS read-only
                    STATUS current
                    DESCRIPTION "Supply Air Probe Faulty"
                    DEFVAL { 0 }
                    ::= { digitalObjects 89 }

        -- 1.3.6.1.4.1.9839.2.1.1.90
        mal_hour_unit OBJECT-TYPE
                    SYNTAX Integer32 (0..1)
                    UNITS "N/A"
                    MAX-ACCESS read-only
                    STATUS current
                    DESCRIPTION "Unit Running Hours Threshold Exceeded"
                    DEFVAL { 0 }
                    ::= { digitalObjects 90 }

        -- 1.3.6.1.4.1.9839.2.1.1.91
        mal_hour_comp1 OBJECT-TYPE
                    SYNTAX Integer32 (0..1)
                    UNITS "N/A"
                    MAX-ACCESS read-only
                    STATUS current
                    DESCRIPTION "Comp 1 Running Hours Threshold Exceeded"
                    DEFVAL { 0 }
                    ::= { digitalObjects 91 }

        -- 1.3.6.1.4.1.9839.2.1.1.92
        mal_hour_comp2 OBJECT-TYPE
                    SYNTAX Integer32 (0..1)
                    UNITS "N/A"
                    MAX-ACCESS read-only
                    STATUS current
                    DESCRIPTION "Comp 2 Running Hours Threshold Exceeded"
                    DEFVAL { 0 }
                    ::= { digitalObjects 92 }

        -- 1.3.6.1.4.1.9839.2.1.1.93
        mal_fan_ol1 OBJECT-TYPE
                    SYNTAX Integer32 (0..1)
                    UNITS "N/A"
                    MAX-ACCESS read-only
                    STATUS current
                    DESCRIPTION "Eavp Fan 1 Overload Alarm"
                    DEFVAL { 0 }
                    ::= { digitalObjects 93 }

        -- 1.3.6.1.4.1.9839.2.1.1.94
        mal_fan_ol2 OBJECT-TYPE
                    SYNTAX Integer32 (0..1)
                    UNITS "N/A"
                    MAX-ACCESS read-only
                    STATUS current
                    DESCRIPTION "Evap Fan 2 Overload Alarm"
                    DEFVAL { 0 }
                    ::= { digitalObjects 94 }

        -- 1.3.6.1.4.1.9839.2.1.1.95
        mal_customer OBJECT-TYPE
                    SYNTAX Integer32 (0..1)
                    UNITS "N/A"
                    MAX-ACCESS read-only
                    STATUS current
                    DESCRIPTION "Customer Interlock Alarm"
                    DEFVAL { 0 }
                    ::= { digitalObjects 95 }

        -- 1.3.6.1.4.1.9839.2.1.1.96
        mepromnook OBJECT-TYPE
                    SYNTAX Integer32 (0..1)
                    UNITS "N/A"
                    MAX-ACCESS read-only
                    STATUS current
                    DESCRIPTION "Eeprom Alarm"
                    DEFVAL { 0 }
                    ::= { digitalObjects 96 }

        -- 1.3.6.1.4.1.9839.2.1.1.97
        mal_h_humid OBJECT-TYPE
                    SYNTAX Integer32 (0..1)
                    UNITS "N/A"
                    MAX-ACCESS read-only
                    STATUS current
                    DESCRIPTION "High Room Humidity Alarm"
                    DEFVAL { 0 }
                    ::= { digitalObjects 97 }

        -- 1.3.6.1.4.1.9839.2.1.1.98
        mal_l_humid OBJECT-TYPE
                    SYNTAX Integer32 (0..1)
                    UNITS "N/A"
                    MAX-ACCESS read-only
                    STATUS current
                    DESCRIPTION "Low Room Humidity Alarm"
                    DEFVAL { 0 }
                    ::= { digitalObjects 98 }

        -- 1.3.6.1.4.1.9839.2.1.1.99
        mal_heater_ol1 OBJECT-TYPE
                    SYNTAX Integer32 (0..1)
                    UNITS "N/A"
                    MAX-ACCESS read-only
                    STATUS current
                    DESCRIPTION "Heater 1 Overload Alarm"
                    DEFVAL { 0 }
                    ::= { digitalObjects 99 }

        -- 1.3.6.1.4.1.9839.2.1.1.100
        mal_heater_ol2 OBJECT-TYPE
                    SYNTAX Integer32 (0..1)
                    UNITS "N/A"
                    MAX-ACCESS read-only
                    STATUS current
                    DESCRIPTION "Heater 2 & 3 Overload Alarm"
                    DEFVAL { 0 }
                    ::= { digitalObjects 100 }

        -- 1.3.6.1.4.1.9839.2.1.1.101
        mal_rm_press OBJECT-TYPE
                    SYNTAX Integer32 (0..1)
                    UNITS "N/A"
                    MAX-ACCESS read-only
                    STATUS current
                    DESCRIPTION "Room Diff. Pressure Probe Faulty"
                    DEFVAL { 0 }
                    ::= { digitalObjects 101 }

        -- 1.3.6.1.4.1.9839.2.1.1.102
        mal_air_flow OBJECT-TYPE
                    SYNTAX Integer32 (0..1)
                    UNITS "N/A"
                    MAX-ACCESS read-only
                    STATUS current
                    DESCRIPTION "No Air Flow Alarm"
                    DEFVAL { 0 }
                    ::= { digitalObjects 102 }

        -- 1.3.6.1.4.1.9839.2.1.1.103
        mal_indoor_diff OBJECT-TYPE
                    SYNTAX Integer32 (0..1)
                    UNITS "N/A"
                    MAX-ACCESS read-only
                    STATUS current
                    DESCRIPTION "Indoor Pressure Diff. Alarm"
                    DEFVAL { 0 }
                    ::= { digitalObjects 103 }

        -- 1.3.6.1.4.1.9839.2.1.1.104
        mal_air_filter OBJECT-TYPE
                    SYNTAX Integer32 (0..1)
                    UNITS "N/A"
                    MAX-ACCESS read-only
                    STATUS current
                    DESCRIPTION "Filter Dirty Alarm"
                    DEFVAL { 0 }
                    ::= { digitalObjects 104 }

        -- 1.3.6.1.4.1.9839.2.1.1.105
        mal_flow_sw OBJECT-TYPE
                    SYNTAX Integer32 (0..1)
                    UNITS "N/A"
                    MAX-ACCESS read-only
                    STATUS current
                    DESCRIPTION "CHW Flow Switch Alarm"
                    DEFVAL { 0 }
                    ::= { digitalObjects 105 }

        -- 1.3.6.1.4.1.9839.2.1.1.106
        mal_overheat OBJECT-TYPE
                    SYNTAX Integer32 (0..1)
                    UNITS "N/A"
                    MAX-ACCESS read-only
                    STATUS current
                    DESCRIPTION "High Supply Air Temp Alarm"
                    DEFVAL { 0 }
                    ::= { digitalObjects 106 }

        -- 1.3.6.1.4.1.9839.2.1.1.107
        mal_flood OBJECT-TYPE
                    SYNTAX Integer32 (0..1)
                    UNITS "N/A"
                    MAX-ACCESS read-only
                    STATUS current
                    DESCRIPTION "Water Detector Alarm"
                    DEFVAL { 0 }
                    ::= { digitalObjects 107 }

        -- 1.3.6.1.4.1.9839.2.1.1.108
        mal_water_level OBJECT-TYPE
                    SYNTAX Integer32 (0..1)
                    UNITS "N/A"
                    MAX-ACCESS read-only
                    STATUS current
                    DESCRIPTION "Humidifier Water Level Alarm"
                    DEFVAL { 0 }
                    ::= { digitalObjects 108 }

        -- 1.3.6.1.4.1.9839.2.1.1.109
        malarm1 OBJECT-TYPE
                    SYNTAX Integer32 (0..1)
                    UNITS "N/A"
                    MAX-ACCESS read-only
                    STATUS current
                    DESCRIPTION "High Conductivity Alarm"
                    DEFVAL { 0 }
                    ::= { digitalObjects 109 }

        -- 1.3.6.1.4.1.9839.2.1.1.110
        malarm1_8 OBJECT-TYPE
                    SYNTAX Integer32 (0..1)
                    UNITS "N/A"
                    MAX-ACCESS read-only
                    STATUS current
                    DESCRIPTION "Foan Cylinder 1 Alarm"
                    DEFVAL { 0 }
                    ::= { digitalObjects 110 }

        -- 1.3.6.1.4.1.9839.2.1.1.111
        malarm1_9 OBJECT-TYPE
                    SYNTAX Integer32 (0..1)
                    UNITS "N/A"
                    MAX-ACCESS read-only
                    STATUS current
                    DESCRIPTION "Exhaustion Cylinder 1"
                    DEFVAL { 0 }
                    ::= { digitalObjects 111 }

        -- 1.3.6.1.4.1.9839.2.1.1.112
        malarm1_11 OBJECT-TYPE
                    SYNTAX Integer32 (0..1)
                    UNITS "N/A"
                    MAX-ACCESS read-only
                    STATUS current
                    DESCRIPTION "Cylinder 1 Maintenance Warning"
                    DEFVAL { 0 }
                    ::= { digitalObjects 112 }

        -- 1.3.6.1.4.1.9839.2.1.1.113
        malarm1_10 OBJECT-TYPE
                    SYNTAX Integer32 (0..1)
                    UNITS "N/A"
                    MAX-ACCESS read-only
                    STATUS current
                    DESCRIPTION "Boiler 1 Maintenance Mandatory"
                    DEFVAL { 0 }
                    ::= { digitalObjects 113 }

        -- 1.3.6.1.4.1.9839.2.1.1.114
        malarm2 OBJECT-TYPE
                    SYNTAX Integer32 (0..1)
                    UNITS "N/A"
                    MAX-ACCESS read-only
                    STATUS current
                    DESCRIPTION "Cylinder 2 High Conductivity Alarm"
                    DEFVAL { 0 }
                    ::= { digitalObjects 114 }

        -- 1.3.6.1.4.1.9839.2.1.1.115
        malarm1_1 OBJECT-TYPE
                    SYNTAX Integer32 (0..1)
                    UNITS "N/A"
                    MAX-ACCESS read-only
                    STATUS current
                    DESCRIPTION "High Current - Cylinder 1"
                    DEFVAL { 0 }
                    ::= { digitalObjects 115 }

        -- 1.3.6.1.4.1.9839.2.1.1.116
        malarm1_2 OBJECT-TYPE
                    SYNTAX Integer32 (0..1)
                    UNITS "N/A"
                    MAX-ACCESS read-only
                    STATUS current
                    DESCRIPTION "Low Current - Cylinder 1"
                    DEFVAL { 0 }
                    ::= { digitalObjects 116 }

        -- 1.3.6.1.4.1.9839.2.1.1.117
        malarm1_3 OBJECT-TYPE
                    SYNTAX Integer32 (0..1)
                    UNITS "N/A"
                    MAX-ACCESS read-only
                    STATUS current
                    DESCRIPTION "Cylinder 1 Lack Of Water"
                    DEFVAL { 0 }
                    ::= { digitalObjects 117 }

        -- 1.3.6.1.4.1.9839.2.1.1.118
        malarm1_4 OBJECT-TYPE
                    SYNTAX Integer32 (0..1)
                    UNITS "N/A"
                    MAX-ACCESS read-only
                    STATUS current
                    DESCRIPTION "Cylinder 1 Low Production"
                    DEFVAL { 0 }
                    ::= { digitalObjects 118 }

        -- 1.3.6.1.4.1.9839.2.1.1.119
        malarm1_5 OBJECT-TYPE
                    SYNTAX Integer32 (0..1)
                    UNITS "N/A"
                    MAX-ACCESS read-only
                    STATUS current
                    DESCRIPTION "Cylinder 1 - Drain Alarm"
                    DEFVAL { 0 }
                    ::= { digitalObjects 119 }

        -- 1.3.6.1.4.1.9839.2.1.1.120
        malarm1_6 OBJECT-TYPE
                    SYNTAX Integer32 (0..1)
                    UNITS "N/A"
                    MAX-ACCESS read-only
                    STATUS current
                    DESCRIPTION "Cylinder 1 - Full Cylinder"
                    DEFVAL { 0 }
                    ::= { digitalObjects 120 }

        -- 1.3.6.1.4.1.9839.2.1.1.121
        malarm1_7 OBJECT-TYPE
                    SYNTAX Integer32 (0..1)
                    UNITS "N/A"
                    MAX-ACCESS read-only
                    STATUS current
                    DESCRIPTION "Pre-Exhaustion - Cylinder 1"
                    DEFVAL { 0 }
                    ::= { digitalObjects 121 }

        -- 1.3.6.1.4.1.9839.2.1.1.122
        mal_smoke_alarm OBJECT-TYPE
                    SYNTAX Integer32 (0..1)
                    UNITS "N/A"
                    MAX-ACCESS read-only
                    STATUS current
                    DESCRIPTION "Smoke Detector Alarm"
                    DEFVAL { 0 }
                    ::= { digitalObjects 122 }

        -- 1.3.6.1.4.1.9839.2.1.1.123
        mal_c1_short_cyc OBJECT-TYPE
                    SYNTAX Integer32 (0..1)
                    UNITS "N/A"
                    MAX-ACCESS read-only
                    STATUS current
                    DESCRIPTION "Comp 1 Short Cycle alarm"
                    DEFVAL { 0 }
                    ::= { digitalObjects 123 }

        -- 1.3.6.1.4.1.9839.2.1.1.124
        mal_c2_short_cyc OBJECT-TYPE
                    SYNTAX Integer32 (0..1)
                    UNITS "N/A"
                    MAX-ACCESS read-only
                    STATUS current
                    DESCRIPTION "Comp 2 Short Cycle Alarm"
                    DEFVAL { 0 }
                    ::= { digitalObjects 124 }

        -- 1.3.6.1.4.1.9839.2.1.1.125
        mal_plan OBJECT-TYPE
                    SYNTAX Integer32 (0..1)
                    UNITS "N/A"
                    MAX-ACCESS read-only
                    STATUS current
                    DESCRIPTION "DB Lan Alarm"
                    DEFVAL { 0 }
                    ::= { digitalObjects 125 }

        -- 1.3.6.1.4.1.9839.2.1.1.171
        superv_onoff OBJECT-TYPE
                    SYNTAX Integer32 (0..1)
                    UNITS "N/A"
                    MAX-ACCESS read-write
                    STATUS current
                    DESCRIPTION "Supervisor ON/OFF"
                    DEFVAL { 0 }
                    ::= { digitalObjects 171 }

        -- 1.3.6.1.4.1.9839.2.1.1.172
        en_time_zones OBJECT-TYPE
                    SYNTAX Integer32 (0..1)
                    UNITS "N/A"
                    MAX-ACCESS read-write
                    STATUS current
                    DESCRIPTION "Enable Daily Time Zone Control"
                    DEFVAL { 0 }
                    ::= { digitalObjects 172 }

        -- 1.3.6.1.4.1.9839.2.1.1.173
        en_sch_onoff OBJECT-TYPE
                    SYNTAX Integer32 (0..1)
                    UNITS "N/A"
                    MAX-ACCESS read-write
                    STATUS current
                    DESCRIPTION "Enable Weekly Time Zone Control"
                    DEFVAL { 0 }
                    ::= { digitalObjects 173 }

        -- 1.3.6.1.4.1.9839.2.1.1.201
        cent_on OBJECT-TYPE
                    SYNTAX Integer32 (0..1)
                    UNITS "N/A"
                    MAX-ACCESS read-only
                    STATUS current
                    DESCRIPTION "Centigrade ON"
                    DEFVAL { 0 }
                    ::= { digitalObjects 201 }

        -- 1.3.6.1.4.1.9839.2.1.1.202
        phases_type OBJECT-TYPE
                    SYNTAX Integer32 (0..1)
                    UNITS "N/A"
                    MAX-ACCESS read-only
                    STATUS current
                    DESCRIPTION "Carel Humidifier Phase Type"
                    DEFVAL { 0 }
                    ::= { digitalObjects 202 }

        -- 1.3.6.1.4.1.9839.2.1.1.203
        level_hum1 OBJECT-TYPE
                    SYNTAX Integer32 (0..1)
                    UNITS "N/A"
                    MAX-ACCESS read-only
                    STATUS current
                    DESCRIPTION "Humidifier Water Level"
                    DEFVAL { 0 }
                    ::= { digitalObjects 203 }

        -- 1.3.6.1.4.1.9839.2.1.1.204
        main_master OBJECT-TYPE
                    SYNTAX Integer32 (0..1)
                    UNITS "N/A"
                    MAX-ACCESS read-only
                    STATUS current
                    DESCRIPTION "Master Unit"
                    DEFVAL { 0 }
                    ::= { digitalObjects 204 }

        -- 1.3.6.1.4.1.9839.2.1.1.205
        reset_alarms OBJECT-TYPE
                    SYNTAX Integer32 (0..1)
                    UNITS "N/A"
                    MAX-ACCESS read-write
                    STATUS current
                    DESCRIPTION "Request to reset/clear alarm memories"
                    DEFVAL { 0 }
                    ::= { digitalObjects 205 }

        -- 1.3.6.1.4.1.9839.2.1.1.206
        reset_buzzer OBJECT-TYPE
                    SYNTAX Integer32 (0..1)
                    UNITS "N/A"
                    MAX-ACCESS read-write
                    STATUS current
                    DESCRIPTION "Request to switch off the buzzer "
                    DEFVAL { 0 }
                    ::= { digitalObjects 206 }

        -- 1.3.6.1.4.1.9839.2.1.1.207
        previous_event OBJECT-TYPE
                    SYNTAX Integer32 (0..1)
                    UNITS "N/A"
                    MAX-ACCESS read-write
                    STATUS current
                    DESCRIPTION "N/A"
                    DEFVAL { 0 }
                    ::= { digitalObjects 207 }

        -- 1.3.6.1.4.1.9839.2.1.1.208
        next_event OBJECT-TYPE
                    SYNTAX Integer32 (0..1)
                    UNITS "N/A"
                    MAX-ACCESS read-write
                    STATUS current
                    DESCRIPTION "N/A"
                    DEFVAL { 0 }
                    ::= { digitalObjects 208 }

        -- 1.3.6.1.4.1.9839.2.1.1.209
        init_event_hist OBJECT-TYPE
                    SYNTAX Integer32 (0..1)
                    UNITS "N/A"
                    MAX-ACCESS read-write
                    STATUS current
                    DESCRIPTION "N/A"
                    DEFVAL { 0 }
                    ::= { digitalObjects 209 }

        -- 1.3.6.1.4.1.9839.2.1.1.210
        en_comp1 OBJECT-TYPE
                    SYNTAX Integer32 (0..1)
                    UNITS "N/A"
                    MAX-ACCESS read-write
                    STATUS current
                    DESCRIPTION "Enable Compressor 1"
                    DEFVAL { 0 }
                    ::= { digitalObjects 210 }

        -- 1.3.6.1.4.1.9839.2.1.1.211
        en_comp2 OBJECT-TYPE
                    SYNTAX Integer32 (0..1)
                    UNITS "N/A"
                    MAX-ACCESS read-write
                    STATUS current
                    DESCRIPTION "Enable Compressor 2"
                    DEFVAL { 0 }
                    ::= { digitalObjects 211 }

        -- 1.3.6.1.4.1.9839.2.1.1.212
        en_heater1 OBJECT-TYPE
                    SYNTAX Integer32 (0..1)
                    UNITS "N/A"
                    MAX-ACCESS read-write
                    STATUS current
                    DESCRIPTION "Enable Heater 1"
                    DEFVAL { 0 }
                    ::= { digitalObjects 212 }

        -- 1.3.6.1.4.1.9839.2.1.1.213
        en_heater2 OBJECT-TYPE
                    SYNTAX Integer32 (0..1)
                    UNITS "N/A"
                    MAX-ACCESS read-write
                    STATUS current
                    DESCRIPTION "Enable Heater 2"
                    DEFVAL { 0 }
                    ::= { digitalObjects 213 }

        -- 1.3.6.1.4.1.9839.2.1.1.214
        en_heater_bin OBJECT-TYPE
                    SYNTAX Integer32 (0..1)
                    UNITS "N/A"
                    MAX-ACCESS read-write
                    STATUS current
                    DESCRIPTION "Enable Heater Binary"
                    DEFVAL { 0 }
                    ::= { digitalObjects 214 }

        -- 1.3.6.1.4.1.9839.2.1.1.215
        en_cool_comp OBJECT-TYPE
                    SYNTAX Integer32 (0..1)
                    UNITS "N/A"
                    MAX-ACCESS read-only
                    STATUS current
                    DESCRIPTION "N/A"
                    DEFVAL { 0 }
                    ::= { digitalObjects 215 }

        -- 1.3.6.1.4.1.9839.2.1.1.216
        en_dual_mode OBJECT-TYPE
                    SYNTAX Integer32 (0..1)
                    UNITS "N/A"
                    MAX-ACCESS read-only
                    STATUS current
                    DESCRIPTION "N/A"
                    DEFVAL { 0 }
                    ::= { digitalObjects 216 }

        -- 1.3.6.1.4.1.9839.2.1.1.217
        en_cool_0to10v OBJECT-TYPE
                    SYNTAX Integer32 (0..1)
                    UNITS "N/A"
                    MAX-ACCESS read-only
                    STATUS current
                    DESCRIPTION "N/A"
                    DEFVAL { 0 }
                    ::= { digitalObjects 217 }

        -- 1.3.6.1.4.1.9839.2.1.1.218
        en_cool_water OBJECT-TYPE
                    SYNTAX Integer32 (0..1)
                    UNITS "N/A"
                    MAX-ACCESS read-only
                    STATUS current
                    DESCRIPTION "N/A"
                    DEFVAL { 0 }
                    ::= { digitalObjects 218 }

        -- 1.3.6.1.4.1.9839.2.1.1.219
        with_air_damper OBJECT-TYPE
                    SYNTAX Integer32 (0..1)
                    UNITS "N/A"
                    MAX-ACCESS read-only
                    STATUS current
                    DESCRIPTION "N/A"
                    DEFVAL { 0 }
                    ::= { digitalObjects 219 }

        -- 1.3.6.1.4.1.9839.2.1.1.220
        humid_onoff OBJECT-TYPE
                    SYNTAX Integer32 (0..1)
                    UNITS "N/A"
                    MAX-ACCESS read-only
                    STATUS current
                    DESCRIPTION "N/A"
                    DEFVAL { 0 }
                    ::= { digitalObjects 220 }

        -- 1.3.6.1.4.1.9839.2.1.1.221
        en_integr_humid OBJECT-TYPE
                    SYNTAX Integer32 (0..1)
                    UNITS "N/A"
                    MAX-ACCESS read-only
                    STATUS current
                    DESCRIPTION "N/A"
                    DEFVAL { 0 }
                    ::= { digitalObjects 221 }

        -- 1.3.6.1.4.1.9839.2.1.1.222
        humid_0to10 OBJECT-TYPE
                    SYNTAX Integer32 (0..1)
                    UNITS "N/A"
                    MAX-ACCESS read-only
                    STATUS current
                    DESCRIPTION "N/A"
                    DEFVAL { 0 }
                    ::= { digitalObjects 222 }

        -- 1.3.6.1.4.1.9839.2.1.1.223
        en_water_level OBJECT-TYPE
                    SYNTAX Integer32 (0..1)
                    UNITS "N/A"
                    MAX-ACCESS read-only
                    STATUS current
                    DESCRIPTION "N/A"
                    DEFVAL { 0 }
                    ::= { digitalObjects 223 }

        -- 1.3.6.1.4.1.9839.2.1.1.224
        vfd_select1 OBJECT-TYPE
                    SYNTAX Integer32 (0..1)
                    UNITS "N/A"
                    MAX-ACCESS read-write
                    STATUS current
                    DESCRIPTION "N/A"
                    DEFVAL { 0 }
                    ::= { digitalObjects 224 }

        -- 1.3.6.1.4.1.9839.2.1.1.225
        vfd_select2 OBJECT-TYPE
                    SYNTAX Integer32 (0..1)
                    UNITS "N/A"
                    MAX-ACCESS read-write
                    STATUS current
                    DESCRIPTION "N/A"
                    DEFVAL { 0 }
                    ::= { digitalObjects 225 }

        -- 1.3.6.1.4.1.9839.2.1.1.226
        en_cool_dx OBJECT-TYPE
                    SYNTAX Integer32 (0..1)
                    UNITS "N/A"
                    MAX-ACCESS read-only
                    STATUS current
                    DESCRIPTION "N/A"
                    DEFVAL { 0 }
                    ::= { digitalObjects 226 }

        -- 1.3.6.1.4.1.9839.2.1.1.227
        show_one_comp OBJECT-TYPE
                    SYNTAX Integer32 (0..1)
                    UNITS "N/A"
                    MAX-ACCESS read-only
                    STATUS current
                    DESCRIPTION "Show One Comp"
                    DEFVAL { 0 }
                    ::= { digitalObjects 227 }

        -- 1.3.6.1.4.1.9839.2.1.1.228
        show_two_comp OBJECT-TYPE
                    SYNTAX Integer32 (0..1)
                    UNITS "N/A"
                    MAX-ACCESS read-only
                    STATUS current
                    DESCRIPTION "Show Two Comp"
                    DEFVAL { 0 }
                    ::= { digitalObjects 228 }

        -- 1.3.6.1.4.1.9839.2.1.1.229
        show_one_lls OBJECT-TYPE
                    SYNTAX Integer32 (0..1)
                    UNITS "N/A"
                    MAX-ACCESS read-only
                    STATUS current
                    DESCRIPTION "Show One LLS"
                    DEFVAL { 0 }
                    ::= { digitalObjects 229 }

        -- 1.3.6.1.4.1.9839.2.1.1.230
        show_two_lls OBJECT-TYPE
                    SYNTAX Integer32 (0..1)
                    UNITS "N/A"
                    MAX-ACCESS read-only
                    STATUS current
                    DESCRIPTION "Show Two LLS"
                    DEFVAL { 0 }
                    ::= { digitalObjects 230 }

        -- 1.3.6.1.4.1.9839.2.1.1.231
        disable_humidifier OBJECT-TYPE
                    SYNTAX Integer32 (0..1)
                    UNITS "N/A"
                    MAX-ACCESS read-only
                    STATUS current
                    DESCRIPTION "humidfier not present"
                    DEFVAL { 0 }
                    ::= { digitalObjects 231 }

        -- 1.3.6.1.4.1.9839.2.1.1.232
        comp_present OBJECT-TYPE
                    SYNTAX Integer32 (0..1)
                    UNITS "N/A"
                    MAX-ACCESS read-only
                    STATUS current
                    DESCRIPTION "Compressor Present in the unit"
                    DEFVAL { 0 }
                    ::= { digitalObjects 232 }

        -- 1.3.6.1.4.1.9839.2.1.1.233
        en_rotation_time OBJECT-TYPE
                    SYNTAX Integer32 (0..1)
                    UNITS "N/A"
                    MAX-ACCESS read-only
                    STATUS current
                    DESCRIPTION "N/A"
                    DEFVAL { 0 }
                    ::= { digitalObjects 233 }

        -- 1.3.6.1.4.1.9839.2.1.1.234
        timezones_rotation OBJECT-TYPE
                    SYNTAX Integer32 (0..1)
                    UNITS "N/A"
                    MAX-ACCESS read-only
                    STATUS current
                    DESCRIPTION "N/A"
                    DEFVAL { 0 }
                    ::= { digitalObjects 234 }

        -- 1.3.6.1.4.1.9839.2.1.1.235
        rotation_enabled OBJECT-TYPE
                    SYNTAX Integer32 (0..1)
                    UNITS "N/A"
                    MAX-ACCESS read-only
                    STATUS current
                    DESCRIPTION "N/A"
                    DEFVAL { 0 }
                    ::= { digitalObjects 235 }

        -- 1.3.6.1.4.1.9839.2.1.1.236
        user_access OBJECT-TYPE
                    SYNTAX Integer32 (0..1)
                    UNITS "N/A"
                    MAX-ACCESS read-only
                    STATUS current
                    DESCRIPTION "N/A"
                    DEFVAL { 0 }
                    ::= { digitalObjects 236 }

        -- 1.3.6.1.4.1.9839.2.1.1.237
        service_access OBJECT-TYPE
                    SYNTAX Integer32 (0..1)
                    UNITS "N/A"
                    MAX-ACCESS read-only
                    STATUS current
                    DESCRIPTION "N/A"
                    DEFVAL { 0 }
                    ::= { digitalObjects 237 }

        -- 1.3.6.1.4.1.9839.2.1.1.238
        factory_access OBJECT-TYPE
                    SYNTAX Integer32 (0..1)
                    UNITS "N/A"
                    MAX-ACCESS read-only
                    STATUS current
                    DESCRIPTION "N/A"
                    DEFVAL { 0 }
                    ::= { digitalObjects 238 }

        -- 1.3.6.1.4.1.9839.2.1.1.239
        all_level OBJECT-TYPE
                    SYNTAX Integer32 (0..1)
                    UNITS "N/A"
                    MAX-ACCESS read-only
                    STATUS current
                    DESCRIPTION "N/A"
                    DEFVAL { 0 }
                    ::= { digitalObjects 239 }

        -- 1.3.6.1.4.1.9839.2.1.1.240
        level2_3 OBJECT-TYPE
                    SYNTAX Integer32 (0..1)
                    UNITS "N/A"
                    MAX-ACCESS read-only
                    STATUS current
                    DESCRIPTION "N/A"
                    DEFVAL { 0 }
                    ::= { digitalObjects 240 }

        -- 1.3.6.1.4.1.9839.2.1.1.241
        admin OBJECT-TYPE
                    SYNTAX Integer32 (0..1)
                    UNITS "N/A"
                    MAX-ACCESS read-only
                    STATUS current
                    DESCRIPTION "N/A"
                    DEFVAL { 0 }
                    ::= { digitalObjects 241 }

        -- 1.3.6.1.4.1.9839.2.1.1.242
        pass_ass_nok OBJECT-TYPE
                    SYNTAX Integer32 (0..1)
                    UNITS "N/A"
                    MAX-ACCESS read-only
                    STATUS current
                    DESCRIPTION "N/A"
                    DEFVAL { 0 }
                    ::= { digitalObjects 242 }

        -- 1.3.6.1.4.1.9839.2.1.1.243
        pass_ut_nok OBJECT-TYPE
                    SYNTAX Integer32 (0..1)
                    UNITS "N/A"
                    MAX-ACCESS read-only
                    STATUS current
                    DESCRIPTION "N/A"
                    DEFVAL { 0 }
                    ::= { digitalObjects 243 }

        -- 1.3.6.1.4.1.9839.2.1.1.244
        pass_cos_nok OBJECT-TYPE
                    SYNTAX Integer32 (0..1)
                    UNITS "N/A"
                    MAX-ACCESS read-only
                    STATUS current
                    DESCRIPTION "N/A"
                    DEFVAL { 0 }
                    ::= { digitalObjects 244 }

        -- 1.3.6.1.4.1.9839.2.1.1.245
        not_admin_access OBJECT-TYPE
                    SYNTAX Integer32 (0..1)
                    UNITS "N/A"
                    MAX-ACCESS read-only
                    STATUS current
                    DESCRIPTION "N/A"
                    DEFVAL { 0 }
                    ::= { digitalObjects 245 }

        -- 1.3.6.1.4.1.9839.2.1.1.246
        not_level2_3 OBJECT-TYPE
                    SYNTAX Integer32 (0..1)
                    UNITS "N/A"
                    MAX-ACCESS read-only
                    STATUS current
                    DESCRIPTION "N/A"
                    DEFVAL { 0 }
                    ::= { digitalObjects 246 }

        -- 1.3.6.1.4.1.9839.2.1.1.247
        right_pass OBJECT-TYPE
                    SYNTAX Integer32 (0..1)
                    UNITS "N/A"
                    MAX-ACCESS read-only
                    STATUS current
                    DESCRIPTION "N/A"
                    DEFVAL { 0 }
                    ::= { digitalObjects 247 }

        -- 1.3.6.1.4.1.9839.2.1.1.248
        no_access OBJECT-TYPE
                    SYNTAX Integer32 (0..1)
                    UNITS "N/A"
                    MAX-ACCESS read-only
                    STATUS current
                    DESCRIPTION "N/A"
                    DEFVAL { 0 }
                    ::= { digitalObjects 248 }

        -- 1.3.6.1.4.1.9839.2.1.1.249
        chw_vlv_present OBJECT-TYPE
                    SYNTAX Integer32 (0..1)
                    UNITS "N/A"
                    MAX-ACCESS read-only
                    STATUS current
                    DESCRIPTION "CHW Valve Present in the unit"
                    DEFVAL { 0 }
                    ::= { digitalObjects 249 }

        -- 1.3.6.1.4.1.9839.2.1.1.250
        not_show_one_comp OBJECT-TYPE
                    SYNTAX Integer32 (0..1)
                    UNITS "N/A"
                    MAX-ACCESS read-only
                    STATUS current
                    DESCRIPTION "NOT Show One Comp"
                    DEFVAL { 0 }
                    ::= { digitalObjects 250 }

        -- 1.3.6.1.4.1.9839.2.1.1.251
        not_show_two_comp OBJECT-TYPE
                    SYNTAX Integer32 (0..1)
                    UNITS "N/A"
                    MAX-ACCESS read-only
                    STATUS current
                    DESCRIPTION "NOT Show Two Comp"
                    DEFVAL { 0 }
                    ::= { digitalObjects 251 }

        -- 1.3.6.1.4.1.9839.2.1.1.252
        presence_unit1 OBJECT-TYPE
                    SYNTAX Integer32 (0..1)
                    UNITS "N/A"
                    MAX-ACCESS read-only
                    STATUS current
                    DESCRIPTION "N/A"
                    DEFVAL { 0 }
                    ::= { digitalObjects 252 }

        -- 1.3.6.1.4.1.9839.2.1.1.253
        presence_unit2 OBJECT-TYPE
                    SYNTAX Integer32 (0..1)
                    UNITS "N/A"
                    MAX-ACCESS read-only
                    STATUS current
                    DESCRIPTION "N/A"
                    DEFVAL { 0 }
                    ::= { digitalObjects 253 }

        -- 1.3.6.1.4.1.9839.2.1.1.254
        presence_unit3 OBJECT-TYPE
                    SYNTAX Integer32 (0..1)
                    UNITS "N/A"
                    MAX-ACCESS read-only
                    STATUS current
                    DESCRIPTION "N/A"
                    DEFVAL { 0 }
                    ::= { digitalObjects 254 }

        -- 1.3.6.1.4.1.9839.2.1.1.255
        presence_unit4 OBJECT-TYPE
                    SYNTAX Integer32 (0..1)
                    UNITS "N/A"
                    MAX-ACCESS read-only
                    STATUS current
                    DESCRIPTION "N/A"
                    DEFVAL { 0 }
                    ::= { digitalObjects 255 }

        -- 1.3.6.1.4.1.9839.2.1.1.256
        presence_unit5 OBJECT-TYPE
                    SYNTAX Integer32 (0..1)
                    UNITS "N/A"
                    MAX-ACCESS read-only
                    STATUS current
                    DESCRIPTION "N/A"
                    DEFVAL { 0 }
                    ::= { digitalObjects 256 }

        -- 1.3.6.1.4.1.9839.2.1.1.257
        presence_unit6 OBJECT-TYPE
                    SYNTAX Integer32 (0..1)
                    UNITS "N/A"
                    MAX-ACCESS read-only
                    STATUS current
                    DESCRIPTION "N/A"
                    DEFVAL { 0 }
                    ::= { digitalObjects 257 }

        -- 1.3.6.1.4.1.9839.2.1.1.258
        presence_unit7 OBJECT-TYPE
                    SYNTAX Integer32 (0..1)
                    UNITS "N/A"
                    MAX-ACCESS read-only
                    STATUS current
                    DESCRIPTION "N/A"
                    DEFVAL { 0 }
                    ::= { digitalObjects 258 }

        -- 1.3.6.1.4.1.9839.2.1.1.259
        presence_unit8 OBJECT-TYPE
                    SYNTAX Integer32 (0..1)
                    UNITS "N/A"
                    MAX-ACCESS read-only
                    STATUS current
                    DESCRIPTION "N/A"
                    DEFVAL { 0 }
                    ::= { digitalObjects 259 }

        -- 1.3.6.1.4.1.9839.2.1.1.260
        not_main_master OBJECT-TYPE
                    SYNTAX Integer32 (0..1)
                    UNITS "N/A"
                    MAX-ACCESS read-only
                    STATUS current
                    DESCRIPTION "NOT Master Unit"
                    DEFVAL { 0 }
                    ::= { digitalObjects 260 }

        -- 1.3.6.1.4.1.9839.2.1.1.401
        set_hour OBJECT-TYPE
                    SYNTAX Integer32 (0..1)
                    UNITS "N/A"
                    MAX-ACCESS read-write
                    STATUS current
                    DESCRIPTION "Request to copy NEW_HOUR into HOUR"
                    DEFVAL { 0 }
                    ::= { digitalObjects 401 }

        -- 1.3.6.1.4.1.9839.2.1.1.402
        set_minute OBJECT-TYPE
                    SYNTAX Integer32 (0..1)
                    UNITS "N/A"
                    MAX-ACCESS read-write
                    STATUS current
                    DESCRIPTION "Request to copy NEW_MINUTE into MINUTE"
                    DEFVAL { 0 }
                    ::= { digitalObjects 402 }

        -- 1.3.6.1.4.1.9839.2.1.1.403
        set_day OBJECT-TYPE
                    SYNTAX Integer32 (0..1)
                    UNITS "N/A"
                    MAX-ACCESS read-write
                    STATUS current
                    DESCRIPTION "Request to copy NEW_DAY into DAY"
                    DEFVAL { 0 }
                    ::= { digitalObjects 403 }

        -- 1.3.6.1.4.1.9839.2.1.1.404
        set_month OBJECT-TYPE
                    SYNTAX Integer32 (0..1)
                    UNITS "N/A"
                    MAX-ACCESS read-write
                    STATUS current
                    DESCRIPTION "Request to copy NEW_MONTH into MONTH"
                    DEFVAL { 0 }
                    ::= { digitalObjects 404 }

        -- 1.3.6.1.4.1.9839.2.1.1.405
        set_year OBJECT-TYPE
                    SYNTAX Integer32 (0..1)
                    UNITS "N/A"
                    MAX-ACCESS read-write
                    STATUS current
                    DESCRIPTION "Request to copy NEW_YEAR into YEAR"
                    DEFVAL { 0 }
                    ::= { digitalObjects 405 }

        -- 1.3.6.1.4.1.9839.2.1.1.406
        set_weekday OBJECT-TYPE
                    SYNTAX Integer32 (0..1)
                    UNITS "N/A"
                    MAX-ACCESS read-write
                    STATUS current
                    DESCRIPTION "Request to copy NEW_WEEKDAY into WEEKDAY"
                    DEFVAL { 0 }
                    ::= { digitalObjects 406 }

        -- 1.3.6.1.4.1.9839.2.1.1.407
        copy_time OBJECT-TYPE
                    SYNTAX Integer32 (0..1)
                    UNITS "N/A"
                    MAX-ACCESS read-write
                    STATUS current
                    DESCRIPTION "Request to copy RTC (real time clock) data (HOUR, etc) into new clock data (LHOUR, etc) "
                    DEFVAL { 0 }
                    ::= { digitalObjects 407 }

        -- 1.3.6.1.4.1.9839.2.1.1.408
        autostart OBJECT-TYPE
                    SYNTAX Integer32 (0..1)
                    UNITS "N/A"
                    MAX-ACCESS read-write
                    STATUS current
                    DESCRIPTION "Enable Auto Restart"
                    DEFVAL { 0 }
                    ::= { digitalObjects 408 }

        -- 1.3.6.1.4.1.9839.2.1.1.409
        en_superv_onoff OBJECT-TYPE
                    SYNTAX Integer32 (0..1)
                    UNITS "N/A"
                    MAX-ACCESS read-write
                    STATUS current
                    DESCRIPTION "Enable Supervisor ON/OFF"
                    DEFVAL { 0 }
                    ::= { digitalObjects 409 }

        -- 1.3.6.1.4.1.9839.2.1.1.410
        en_dig_on_off OBJECT-TYPE
                    SYNTAX Integer32 (0..1)
                    UNITS "N/A"
                    MAX-ACCESS read-write
                    STATUS current
                    DESCRIPTION "Enable Remote On/Off"
                    DEFVAL { 0 }
                    ::= { digitalObjects 410 }

        -- 1.3.6.1.4.1.9839.2.1.1.411
        en_fanoff OBJECT-TYPE
                    SYNTAX Integer32 (0..1)
                    UNITS "N/A"
                    MAX-ACCESS read-write
                    STATUS current
                    DESCRIPTION "Enable Off Fan 2 During Dehumid"
                    DEFVAL { 0 }
                    ::= { digitalObjects 411 }

        -- 1.3.6.1.4.1.9839.2.1.1.412
        en_hi_reset OBJECT-TYPE
                    SYNTAX Integer32 (0..1)
                    UNITS "N/A"
                    MAX-ACCESS read-write
                    STATUS current
                    DESCRIPTION "Enable High Pressure Alarm Manual Reset"
                    DEFVAL { 0 }
                    ::= { digitalObjects 412 }

        -- 1.3.6.1.4.1.9839.2.1.1.413
        en_lo_reset OBJECT-TYPE
                    SYNTAX Integer32 (0..1)
                    UNITS "N/A"
                    MAX-ACCESS read-write
                    STATUS current
                    DESCRIPTION "Enable Low Pressure Alarm Manual Reset"
                    DEFVAL { 0 }
                    ::= { digitalObjects 413 }

        -- 1.3.6.1.4.1.9839.2.1.1.414
        en_humid OBJECT-TYPE
                    SYNTAX Integer32 (0..1)
                    UNITS "N/A"
                    MAX-ACCESS read-write
                    STATUS current
                    DESCRIPTION "Enable Humidifier"
                    DEFVAL { 0 }
                    ::= { digitalObjects 414 }

        -- 1.3.6.1.4.1.9839.2.1.1.415
        en_humid_dehum OBJECT-TYPE
                    SYNTAX Integer32 (0..1)
                    UNITS "N/A"
                    MAX-ACCESS read-write
                    STATUS current
                    DESCRIPTION "Enable Humidity Priority Control"
                    DEFVAL { 0 }
                    ::= { digitalObjects 415 }

        -- 1.3.6.1.4.1.9839.2.1.1.416
        en_pumpdown OBJECT-TYPE
                    SYNTAX Integer32 (0..1)
                    UNITS "N/A"
                    MAX-ACCESS read-write
                    STATUS current
                    DESCRIPTION "Enable Pumpdown"
                    DEFVAL { 0 }
                    ::= { digitalObjects 416 }

        -- 1.3.6.1.4.1.9839.2.1.1.417
        en_room_press OBJECT-TYPE
                    SYNTAX Integer32 (0..1)
                    UNITS "N/A"
                    MAX-ACCESS read-write
                    STATUS current
                    DESCRIPTION "Enable Room Diff. Preesure Probe"
                    DEFVAL { 0 }
                    ::= { digitalObjects 417 }

        -- 1.3.6.1.4.1.9839.2.1.1.418
        en_rotation OBJECT-TYPE
                    SYNTAX Integer32 (0..1)
                    UNITS "N/A"
                    MAX-ACCESS read-write
                    STATUS current
                    DESCRIPTION "Enable Compressor Rotation"
                    DEFVAL { 0 }
                    ::= { digitalObjects 418 }

        -- 1.3.6.1.4.1.9839.2.1.1.419
        en_smoke_detector OBJECT-TYPE
                    SYNTAX Integer32 (0..1)
                    UNITS "N/A"
                    MAX-ACCESS read-write
                    STATUS current
                    DESCRIPTION "Enable Smoke Detector"
                    DEFVAL { 0 }
                    ::= { digitalObjects 419 }

        -- 1.3.6.1.4.1.9839.2.1.1.420
        en_water_detector OBJECT-TYPE
                    SYNTAX Integer32 (0..1)
                    UNITS "N/A"
                    MAX-ACCESS read-write
                    STATUS current
                    DESCRIPTION "Enable Water Detector"
                    DEFVAL { 0 }
                    ::= { digitalObjects 420 }

        -- 1.3.6.1.4.1.9839.2.1.1.421
        en_supervisor OBJECT-TYPE
                    SYNTAX Integer32 (0..1)
                    UNITS "N/A"
                    MAX-ACCESS read-write
                    STATUS current
                    DESCRIPTION "Enable BMS"
                    DEFVAL { 0 }
                    ::= { digitalObjects 421 }

        -- 1.3.6.1.4.1.9839.2.1.1.422
        en_supply_probe OBJECT-TYPE
                    SYNTAX Integer32 (0..1)
                    UNITS "N/A"
                    MAX-ACCESS read-write
                    STATUS current
                    DESCRIPTION "Enable Supply Air Probe"
                    DEFVAL { 0 }
                    ::= { digitalObjects 422 }

        -- 1.3.6.1.4.1.9839.2.1.1.423
        reg_type_temp OBJECT-TYPE
                    SYNTAX Integer32 (0..1)
                    UNITS "N/A"
                    MAX-ACCESS read-write
                    STATUS current
                    DESCRIPTION "Temperature Control Type (P or P+I)"
                    DEFVAL { 1 }
                    ::= { digitalObjects 423 }

        -- 1.3.6.1.4.1.9839.2.1.1.424
        rs_hi_comp1 OBJECT-TYPE
                    SYNTAX Integer32 (0..1)
                    UNITS "N/A"
                    MAX-ACCESS read-write
                    STATUS current
                    DESCRIPTION "Reset Comp 1 High Pressure Alarm"
                    DEFVAL { 0 }
                    ::= { digitalObjects 424 }

        -- 1.3.6.1.4.1.9839.2.1.1.425
        rs_lo_comp1 OBJECT-TYPE
                    SYNTAX Integer32 (0..1)
                    UNITS "N/A"
                    MAX-ACCESS read-write
                    STATUS current
                    DESCRIPTION "Reset Comp 1 Low Pressure Alarm"
                    DEFVAL { 0 }
                    ::= { digitalObjects 425 }

        -- 1.3.6.1.4.1.9839.2.1.1.426
        rs_hi_comp2 OBJECT-TYPE
                    SYNTAX Integer32 (0..1)
                    UNITS "N/A"
                    MAX-ACCESS read-write
                    STATUS current
                    DESCRIPTION "Reset Comp 2 High Pressure Alarm"
                    DEFVAL { 0 }
                    ::= { digitalObjects 426 }

        -- 1.3.6.1.4.1.9839.2.1.1.427
        rs_lo_comp2 OBJECT-TYPE
                    SYNTAX Integer32 (0..1)
                    UNITS "N/A"
                    MAX-ACCESS read-write
                    STATUS current
                    DESCRIPTION "Reset Comp 2 Low Pressure Alarm"
                    DEFVAL { 0 }
                    ::= { digitalObjects 427 }

        -- 1.3.6.1.4.1.9839.2.1.1.428
        hotgas_reheat_en OBJECT-TYPE
                    SYNTAX Integer32 (0..1)
                    UNITS "N/A"
                    MAX-ACCESS read-write
                    STATUS current
                    DESCRIPTION "Enable Hotgas Reheat"
                    DEFVAL { 0 }
                    ::= { digitalObjects 428 }

        -- 1.3.6.1.4.1.9839.2.1.1.429
        en_room_humid OBJECT-TYPE
                    SYNTAX Integer32 (0..1)
                    UNITS "N/A"
                    MAX-ACCESS read-write
                    STATUS current
                    DESCRIPTION "Enable Room Humidity Probe"
                    DEFVAL { 0 }
                    ::= { digitalObjects 429 }

        -- 1.3.6.1.4.1.9839.2.1.1.430
        require_default OBJECT-TYPE
                    SYNTAX Integer32 (0..1)
                    UNITS "N/A"
                    MAX-ACCESS read-write
                    STATUS current
                    DESCRIPTION "Restore The Default Settings"
                    DEFVAL { 0 }
                    ::= { digitalObjects 430 }

        -- 1.3.6.1.4.1.9839.2.1.1.431
        sel_0_4_humid OBJECT-TYPE
                    SYNTAX Integer32 (0..1)
                    UNITS "N/A"
                    MAX-ACCESS read-write
                    STATUS current
                    DESCRIPTION "sel 0 4 humid"
                    DEFVAL { 0 }
                    ::= { digitalObjects 431 }

        -- 1.3.6.1.4.1.9839.2.1.1.432
        en_flow_sw_alarm OBJECT-TYPE
                    SYNTAX Integer32 (0..1)
                    UNITS "N/A"
                    MAX-ACCESS read-write
                    STATUS current
                    DESCRIPTION "Enable Flow Switch Alarm"
                    DEFVAL { 0 }
                    ::= { digitalObjects 432 }

        -- 1.3.6.1.4.1.9839.2.1.1.433
        en_evap_fan_ol OBJECT-TYPE
                    SYNTAX Integer32 (0..1)
                    UNITS "N/A"
                    MAX-ACCESS read-write
                    STATUS current
                    DESCRIPTION "Enable EVAP FAN OL"
                    DEFVAL { 0 }
                    ::= { digitalObjects 433 }

        -- 1.3.6.1.4.1.9839.2.1.1.434
        en_heat_control OBJECT-TYPE
                    SYNTAX Integer32 (0..1)
                    UNITS "N/A"
                    MAX-ACCESS read-write
                    STATUS current
                    DESCRIPTION "Enable HEAT CONTROL"
                    DEFVAL { 1 }
                    ::= { digitalObjects 434 }

        -- 1.3.6.1.4.1.9839.2.1.1.435
        en_heater_ol OBJECT-TYPE
                    SYNTAX Integer32 (0..1)
                    UNITS "N/A"
                    MAX-ACCESS read-write
                    STATUS current
                    DESCRIPTION "Enable HEATER Overload"
                    DEFVAL { 0 }
                    ::= { digitalObjects 435 }

        -- 1.3.6.1.4.1.9839.2.1.1.436
        en_clock OBJECT-TYPE
                    SYNTAX Integer32 (0..1)
                    UNITS "N/A"
                    MAX-ACCESS read-write
                    STATUS current
                    DESCRIPTION "Enable CLOCK"
                    DEFVAL { 0 }
                    ::= { digitalObjects 436 }

        -- 1.3.6.1.4.1.9839.2.1.1.437
        keyb_on_off OBJECT-TYPE
                    SYNTAX Integer32 (0..1)
                    UNITS "N/A"
                    MAX-ACCESS read-write
                    STATUS current
                    DESCRIPTION "Keyboard On/Off"
                    DEFVAL { 0 }
                    ::= { digitalObjects 437 }

        -- 1.3.6.1.4.1.9839.2.1.1.438
        board_type_h OBJECT-TYPE
                    SYNTAX Integer32 (0..1)
                    UNITS "N/A"
                    MAX-ACCESS read-write
                    STATUS current
                    DESCRIPTION "Board Type H"
                    DEFVAL { 0 }
                    ::= { digitalObjects 438 }

        -- 1.3.6.1.4.1.9839.2.1.1.439
        unpower_drain OBJECT-TYPE
                    SYNTAX Integer32 (0..1)
                    UNITS "N/A"
                    MAX-ACCESS read-write
                    STATUS current
                    DESCRIPTION "Unpower Drain"
                    DEFVAL { 0 }
                    ::= { digitalObjects 439 }

        -- 1.3.6.1.4.1.9839.2.1.1.440
        disable_drain_rsetp OBJECT-TYPE
                    SYNTAX Integer32 (0..1)
                    UNITS "N/A"
                    MAX-ACCESS read-write
                    STATUS current
                    DESCRIPTION "Disable Drain RSetp"
                    DEFVAL { 0 }
                    ::= { digitalObjects 440 }

        -- 1.3.6.1.4.1.9839.2.1.1.441
        disable_drain_std_by OBJECT-TYPE
                    SYNTAX Integer32 (0..1)
                    UNITS "N/A"
                    MAX-ACCESS read-write
                    STATUS current
                    DESCRIPTION "Disable Drain Std By"
                    DEFVAL { 0 }
                    ::= { digitalObjects 441 }

        -- 1.3.6.1.4.1.9839.2.1.1.442
        dis_cylinder_warning OBJECT-TYPE
                    SYNTAX Integer32 (0..1)
                    UNITS "N/A"
                    MAX-ACCESS read-write
                    STATUS current
                    DESCRIPTION "Disable Cylinder Warning"
                    DEFVAL { 0 }
                    ::= { digitalObjects 442 }

        -- 1.3.6.1.4.1.9839.2.1.1.443
        periodic_flushing OBJECT-TYPE
                    SYNTAX Integer32 (0..1)
                    UNITS "N/A"
                    MAX-ACCESS read-write
                    STATUS current
                    DESCRIPTION "Periodic Flushing"
                    DEFVAL { 0 }
                    ::= { digitalObjects 443 }

        -- 1.3.6.1.4.1.9839.2.1.1.444
        damper_mode_set OBJECT-TYPE
                    SYNTAX Integer32 (0..1)
                    UNITS "N/A"
                    MAX-ACCESS read-write
                    STATUS current
                    DESCRIPTION "DAMPER MODE SET"
                    DEFVAL { 0 }
                    ::= { digitalObjects 444 }

        -- 1.3.6.1.4.1.9839.2.1.1.445
        type_drain OBJECT-TYPE
                    SYNTAX Integer32 (0..1)
                    UNITS "N/A"
                    MAX-ACCESS read-write
                    STATUS current
                    DESCRIPTION "Drain Type"
                    DEFVAL { 0 }
                    ::= { digitalObjects 445 }

        -- 1.3.6.1.4.1.9839.2.1.1.446
        blower_vfd_en OBJECT-TYPE
                    SYNTAX Integer32 (0..1)
                    UNITS "N/A"
                    MAX-ACCESS read-write
                    STATUS current
                    DESCRIPTION "BLOWER VFD EN"
                    DEFVAL { 0 }
                    ::= { digitalObjects 446 }

        -- 1.3.6.1.4.1.9839.2.1.1.447
        en_dual_mode_auto OBJECT-TYPE
                    SYNTAX Integer32 (0..1)
                    UNITS "N/A"
                    MAX-ACCESS read-write
                    STATUS current
                    DESCRIPTION "Enable Dual Mode"
                    DEFVAL { 0 }
                    ::= { digitalObjects 447 }

        -- 1.3.6.1.4.1.9839.2.1.1.448
        reset_sequence1 OBJECT-TYPE
                    SYNTAX Integer32 (0..1)
                    UNITS "N/A"
                    MAX-ACCESS read-write
                    STATUS current
                    DESCRIPTION "Reset Rotation Sequence"
                    DEFVAL { 0 }
                    ::= { digitalObjects 448 }

        -- 1.3.6.1.4.1.9839.2.1.1.449
        reset_events OBJECT-TYPE
                    SYNTAX Integer32 (0..1)
                    UNITS "N/A"
                    MAX-ACCESS read-write
                    STATUS current
                    DESCRIPTION "Clear Alarm History"
                    DEFVAL { 0 }
                    ::= { digitalObjects 449 }

        -- 1.3.6.1.4.1.9839.2.1.1.450
        rs_hour_unit OBJECT-TYPE
                    SYNTAX Integer32 (0..1)
                    UNITS "N/A"
                    MAX-ACCESS read-write
                    STATUS current
                    DESCRIPTION "Reset Unit Running Hour"
                    DEFVAL { 0 }
                    ::= { digitalObjects 450 }

        -- 1.3.6.1.4.1.9839.2.1.1.451
        rs_hour_comp1 OBJECT-TYPE
                    SYNTAX Integer32 (0..1)
                    UNITS "N/A"
                    MAX-ACCESS read-write
                    STATUS current
                    DESCRIPTION " Reset Compressor 1 Running Hour"
                    DEFVAL { 0 }
                    ::= { digitalObjects 451 }

        -- 1.3.6.1.4.1.9839.2.1.1.452
        rs_hour_comp2 OBJECT-TYPE
                    SYNTAX Integer32 (0..1)
                    UNITS "N/A"
                    MAX-ACCESS read-write
                    STATUS current
                    DESCRIPTION "Reset Compressor 2 Running Hour"
                    DEFVAL { 0 }
                    ::= { digitalObjects 452 }

        -- 1.3.6.1.4.1.9839.2.1.1.453
        res_al1 OBJECT-TYPE
                    SYNTAX Integer32 (0..1)
                    UNITS "N/A"
                    MAX-ACCESS read-write
                    STATUS current
                    DESCRIPTION "N/A"
                    DEFVAL { 0 }
                    ::= { digitalObjects 453 }

        -- 1.3.6.1.4.1.9839.2.1.1.454
        alarm_reset OBJECT-TYPE
                    SYNTAX Integer32 (0..1)
                    UNITS "N/A"
                    MAX-ACCESS read-write
                    STATUS current
                    DESCRIPTION "N/A"
                    DEFVAL { 0 }
                    ::= { digitalObjects 454 }

        -- 1.3.6.1.4.1.9839.2.1.1.455
        do_event_c OBJECT-TYPE
                    SYNTAX Integer32 (0..1)
                    UNITS "N/A"
                    MAX-ACCESS read-write
                    STATUS current
                    DESCRIPTION "N/A"
                    DEFVAL { 0 }
                    ::= { digitalObjects 455 }

        -- 1.3.6.1.4.1.9839.2.1.1.456
        check_password OBJECT-TYPE
                    SYNTAX Integer32 (0..1)
                    UNITS "N/A"
                    MAX-ACCESS read-write
                    STATUS current
                    DESCRIPTION "N/A"
                    DEFVAL { 0 }
                    ::= { digitalObjects 456 }

        -- 1.3.6.1.4.1.9839.2.1.1.457
        clr_password OBJECT-TYPE
                    SYNTAX Integer32 (0..1)
                    UNITS "N/A"
                    MAX-ACCESS read-write
                    STATUS current
                    DESCRIPTION "N/A"
                    DEFVAL { 0 }
                    ::= { digitalObjects 457 }

        -- 1.3.6.1.4.1.9839.2.1.1.458
        res_pass OBJECT-TYPE
                    SYNTAX Integer32 (0..1)
                    UNITS "N/A"
                    MAX-ACCESS read-write
                    STATUS current
                    DESCRIPTION "N/A"
                    DEFVAL { 0 }
                    ::= { digitalObjects 458 }

        -- 1.3.6.1.4.1.9839.2.1.1.459
        man_evap_fan1 OBJECT-TYPE
                    SYNTAX Integer32 (0..1)
                    UNITS "N/A"
                    MAX-ACCESS read-write
                    STATUS current
                    DESCRIPTION "N/A"
                    DEFVAL { 0 }
                    ::= { digitalObjects 459 }

        -- 1.3.6.1.4.1.9839.2.1.1.460
        man_o_d3p_comp1 OBJECT-TYPE
                    SYNTAX Integer32 (0..1)
                    UNITS "N/A"
                    MAX-ACCESS read-write
                    STATUS current
                    DESCRIPTION "N/A"
                    DEFVAL { 0 }
                    ::= { digitalObjects 460 }

        -- 1.3.6.1.4.1.9839.2.1.1.461
        man_liq1 OBJECT-TYPE
                    SYNTAX Integer32 (0..1)
                    UNITS "N/A"
                    MAX-ACCESS read-write
                    STATUS current
                    DESCRIPTION "N/A"
                    DEFVAL { 0 }
                    ::= { digitalObjects 461 }

        -- 1.3.6.1.4.1.9839.2.1.1.462
        man_c_d3p_comp2 OBJECT-TYPE
                    SYNTAX Integer32 (0..1)
                    UNITS "N/A"
                    MAX-ACCESS read-write
                    STATUS current
                    DESCRIPTION "N/A"
                    DEFVAL { 0 }
                    ::= { digitalObjects 462 }

        -- 1.3.6.1.4.1.9839.2.1.1.463
        man_liq2 OBJECT-TYPE
                    SYNTAX Integer32 (0..1)
                    UNITS "N/A"
                    MAX-ACCESS read-write
                    STATUS current
                    DESCRIPTION "N/A"
                    DEFVAL { 0 }
                    ::= { digitalObjects 463 }

        -- 1.3.6.1.4.1.9839.2.1.1.464
        man_heater1 OBJECT-TYPE
                    SYNTAX Integer32 (0..1)
                    UNITS "N/A"
                    MAX-ACCESS read-write
                    STATUS current
                    DESCRIPTION "N/A"
                    DEFVAL { 0 }
                    ::= { digitalObjects 464 }

        -- 1.3.6.1.4.1.9839.2.1.1.465
        man_heater2 OBJECT-TYPE
                    SYNTAX Integer32 (0..1)
                    UNITS "N/A"
                    MAX-ACCESS read-write
                    STATUS current
                    DESCRIPTION "N/A"
                    DEFVAL { 0 }
                    ::= { digitalObjects 465 }

        -- 1.3.6.1.4.1.9839.2.1.1.466
        man_humid OBJECT-TYPE
                    SYNTAX Integer32 (0..1)
                    UNITS "N/A"
                    MAX-ACCESS read-write
                    STATUS current
                    DESCRIPTION "N/A"
                    DEFVAL { 0 }
                    ::= { digitalObjects 466 }

        -- 1.3.6.1.4.1.9839.2.1.1.467
        man_cool_0to10v OBJECT-TYPE
                    SYNTAX Integer32 (0..1)
                    UNITS "N/A"
                    MAX-ACCESS read-write
                    STATUS current
                    DESCRIPTION "N/A"
                    DEFVAL { 0 }
                    ::= { digitalObjects 467 }

        -- 1.3.6.1.4.1.9839.2.1.1.468
        man_blower_vfd_en OBJECT-TYPE
                    SYNTAX Integer32 (0..1)
                    UNITS "N/A"
                    MAX-ACCESS read-write
                    STATUS current
                    DESCRIPTION "N/A"
                    DEFVAL { 0 }
                    ::= { digitalObjects 468 }

        -- 1.3.6.1.4.1.9839.2.1.1.469
        pre_clean1 OBJECT-TYPE
                    SYNTAX Integer32 (0..1)
                    UNITS "N/A"
                    MAX-ACCESS read-write
                    STATUS current
                    DESCRIPTION "N/A"
                    DEFVAL { 0 }
                    ::= { digitalObjects 469 }

        -- 1.3.6.1.4.1.9839.2.1.1.470
        startup_drain1 OBJECT-TYPE
                    SYNTAX Integer32 (0..1)
                    UNITS "N/A"
                    MAX-ACCESS read-write
                    STATUS current
                    DESCRIPTION "N/A"
                    DEFVAL { 0 }
                    ::= { digitalObjects 470 }



        -- 1.3.6.1.4.1.9839.2.1.2
        analogObjects OBJECT IDENTIFIER ::= { flccu1314gmarMIB 2 }

        -- 1.3.6.1.4.1.9839.2.1.2.1
        room_temp OBJECT-TYPE
                    SYNTAX Integer32 (-999..999)
                    UNITS "N/A"
                    MAX-ACCESS read-only
                    STATUS current
                    DESCRIPTION "Room Temperature"
                    DEFVAL { 0 }
                    ::= { analogObjects 1 }

        -- 1.3.6.1.4.1.9839.2.1.2.2
        room_humid OBJECT-TYPE
                    SYNTAX Integer32 (-999..999)
                    UNITS "N/A"
                    MAX-ACCESS read-only
                    STATUS current
                    DESCRIPTION "Room Humidity"
                    DEFVAL { 0 }
                    ::= { analogObjects 2 }

        -- 1.3.6.1.4.1.9839.2.1.2.3
        set_temp OBJECT-TYPE
                    SYNTAX Integer32 (-999..999)
                    UNITS "N/A"
                    MAX-ACCESS read-only
                    STATUS current
                    DESCRIPTION "Current Temperature Setpoint"
                    DEFVAL { 0 }
                    ::= { analogObjects 3 }

        -- 1.3.6.1.4.1.9839.2.1.2.4
        set_humid OBJECT-TYPE
                    SYNTAX Integer32 (0..999)
                    UNITS "N/A"
                    MAX-ACCESS read-only
                    STATUS current
                    DESCRIPTION "Current Humidity Setpoint"
                    DEFVAL { 0 }
                    ::= { analogObjects 4 }

        -- 1.3.6.1.4.1.9839.2.1.2.5
        supply_air_temp OBJECT-TYPE
                    SYNTAX Integer32 (-9999..9999)
                    UNITS "N/A"
                    MAX-ACCESS read-only
                    STATUS current
                    DESCRIPTION "Supply Air Temperature"
                    DEFVAL { 0 }
                    ::= { analogObjects 5 }

        -- 1.3.6.1.4.1.9839.2.1.2.6
        room_press_diff OBJECT-TYPE
                    SYNTAX Integer32 (-32767..32767)
                    UNITS "N/A"
                    MAX-ACCESS read-only
                    STATUS current
                    DESCRIPTION "Room Pressure Differential"
                    DEFVAL { 0 }
                    ::= { analogObjects 6 }

        -- 1.3.6.1.4.1.9839.2.1.2.7
        cool_damper_out OBJECT-TYPE
                    SYNTAX Integer32 (0..9999)
                    UNITS "N/A"
                    MAX-ACCESS read-only
                    STATUS current
                    DESCRIPTION "N/A"
                    DEFVAL { 0 }
                    ::= { analogObjects 7 }

        -- 1.3.6.1.4.1.9839.2.1.2.8
        humid_ao_a OBJECT-TYPE
                    SYNTAX Integer32 (0..999)
                    UNITS "N/A"
                    MAX-ACCESS read-only
                    STATUS current
                    DESCRIPTION "Humidity Output"
                    DEFVAL { 0 }
                    ::= { analogObjects 8 }

        -- 1.3.6.1.4.1.9839.2.1.2.9
        damper_ao_a OBJECT-TYPE
                    SYNTAX Integer32 (0..999)
                    UNITS "N/A"
                    MAX-ACCESS read-only
                    STATUS current
                    DESCRIPTION "Damper Output"
                    DEFVAL { 0 }
                    ::= { analogObjects 9 }

        -- 1.3.6.1.4.1.9839.2.1.2.10
        blower_ao_disp OBJECT-TYPE
                    SYNTAX Integer32 (-999..999)
                    UNITS "N/A"
                    MAX-ACCESS read-only
                    STATUS current
                    DESCRIPTION "Blower VFD Output"
                    DEFVAL { 0 }
                    ::= { analogObjects 10 }

        -- 1.3.6.1.4.1.9839.2.1.2.11
        c1_reheat_vlv_disp OBJECT-TYPE
                    SYNTAX Integer32 (0..9999)
                    UNITS "N/A"
                    MAX-ACCESS read-only
                    STATUS current
                    DESCRIPTION "Comp 1 Reheat Valve Output"
                    DEFVAL { 0 }
                    ::= { analogObjects 11 }

        -- 1.3.6.1.4.1.9839.2.1.2.12
        c2_reheat_vlv_disp OBJECT-TYPE
                    SYNTAX Integer32 (0..9999)
                    UNITS "N/A"
                    MAX-ACCESS read-only
                    STATUS current
                    DESCRIPTION "Comp 2 Reheat Valve Output"
                    DEFVAL { 0 }
                    ::= { analogObjects 12 }

        -- 1.3.6.1.4.1.9839.2.1.2.31
        sel_set_temp OBJECT-TYPE
                    SYNTAX Integer32 (0..999)
                    UNITS "N/A"
                    MAX-ACCESS read-write
                    STATUS current
                    DESCRIPTION "Room Temperature Setpoint"
                    DEFVAL { 0 }
                    ::= { analogObjects 31 }

        -- 1.3.6.1.4.1.9839.2.1.2.32
        sel_set_humid OBJECT-TYPE
                    SYNTAX Integer32 (0..1000)
                    UNITS "N/A"
                    MAX-ACCESS read-write
                    STATUS current
                    DESCRIPTION "Room Humidity Setpoint"
                    DEFVAL { 0 }
                    ::= { analogObjects 32 }

        -- 1.3.6.1.4.1.9839.2.1.2.33
        set_temp1 OBJECT-TYPE
                    SYNTAX Integer32 (-999..999)
                    UNITS "N/A"
                    MAX-ACCESS read-write
                    STATUS current
                    DESCRIPTION "Room Temperature Setpoint (Time Zone 1)"
                    DEFVAL { 0 }
                    ::= { analogObjects 33 }

        -- 1.3.6.1.4.1.9839.2.1.2.34
        set_temp2 OBJECT-TYPE
                    SYNTAX Integer32 (-999..999)
                    UNITS "N/A"
                    MAX-ACCESS read-write
                    STATUS current
                    DESCRIPTION "Room Temperature Setpoint (Time Zone 2)"
                    DEFVAL { 0 }
                    ::= { analogObjects 34 }

        -- 1.3.6.1.4.1.9839.2.1.2.35
        set_temp3 OBJECT-TYPE
                    SYNTAX Integer32 (-999..999)
                    UNITS "N/A"
                    MAX-ACCESS read-write
                    STATUS current
                    DESCRIPTION "Room Temperature Setpoint (Time Zone 3)"
                    DEFVAL { 0 }
                    ::= { analogObjects 35 }

        -- 1.3.6.1.4.1.9839.2.1.2.36
        set_temp4 OBJECT-TYPE
                    SYNTAX Integer32 (-999..999)
                    UNITS "N/A"
                    MAX-ACCESS read-write
                    STATUS current
                    DESCRIPTION "Room Temperature Setpoint (Time Zone 4)"
                    DEFVAL { 0 }
                    ::= { analogObjects 36 }

        -- 1.3.6.1.4.1.9839.2.1.2.37
        set_humid1 OBJECT-TYPE
                    SYNTAX Integer32 (0..999)
                    UNITS "N/A"
                    MAX-ACCESS read-write
                    STATUS current
                    DESCRIPTION "Room Humidity Setpoint (Time Zone 1)"
                    DEFVAL { 0 }
                    ::= { analogObjects 37 }

        -- 1.3.6.1.4.1.9839.2.1.2.38
        set_humid2 OBJECT-TYPE
                    SYNTAX Integer32 (0..999)
                    UNITS "N/A"
                    MAX-ACCESS read-write
                    STATUS current
                    DESCRIPTION "Room Humidity Setpoint (Time Zone 2)"
                    DEFVAL { 0 }
                    ::= { analogObjects 38 }

        -- 1.3.6.1.4.1.9839.2.1.2.39
        set_humid3 OBJECT-TYPE
                    SYNTAX Integer32 (0..999)
                    UNITS "N/A"
                    MAX-ACCESS read-write
                    STATUS current
                    DESCRIPTION "Room Humidity Setpoint (Time Zone 3)"
                    DEFVAL { 0 }
                    ::= { analogObjects 39 }

        -- 1.3.6.1.4.1.9839.2.1.2.40
        set_humid4 OBJECT-TYPE
                    SYNTAX Integer32 (0..999)
                    UNITS "N/A"
                    MAX-ACCESS read-write
                    STATUS current
                    DESCRIPTION "Room Humidity Setpoint (Time Zone 4)"
                    DEFVAL { 0 }
                    ::= { analogObjects 40 }

        -- 1.3.6.1.4.1.9839.2.1.2.41
        max_prod OBJECT-TYPE
                    SYNTAX Integer32 (0..1000)
                    UNITS "N/A"
                    MAX-ACCESS read-write
                    STATUS current
                    DESCRIPTION "Humidifier Max. Steam Production"
                    DEFVAL { 0 }
                    ::= { analogObjects 41 }

        -- 1.3.6.1.4.1.9839.2.1.2.201
        f2 OBJECT-TYPE
                    SYNTAX Integer32 (0..9999)
                    UNITS "N/A"
                    MAX-ACCESS read-only
                    STATUS current
                    DESCRIPTION "Humidifier Nominal Steam Production"
                    DEFVAL { 0 }
                    ::= { analogObjects 201 }

        -- 1.3.6.1.4.1.9839.2.1.2.202
        f5 OBJECT-TYPE
                    SYNTAX Integer32 (0..9999)
                    UNITS "N/A"
                    MAX-ACCESS read-only
                    STATUS current
                    DESCRIPTION "Humidifier Nominal Amps"
                    DEFVAL { 0 }
                    ::= { analogObjects 202 }

        -- 1.3.6.1.4.1.9839.2.1.2.203
        production OBJECT-TYPE
                    SYNTAX Integer32 (0..9999)
                    UNITS "N/A"
                    MAX-ACCESS read-only
                    STATUS current
                    DESCRIPTION "Current Humidifier Steam Flow"
                    DEFVAL { 0 }
                    ::= { analogObjects 203 }

        -- 1.3.6.1.4.1.9839.2.1.2.204
        current1 OBJECT-TYPE
                    SYNTAX Integer32 (0..9999)
                    UNITS "N/A"
                    MAX-ACCESS read-only
                    STATUS current
                    DESCRIPTION "Current Humidifier Amps"
                    DEFVAL { 0 }
                    ::= { analogObjects 204 }

        -- 1.3.6.1.4.1.9839.2.1.2.401
        dead_zone_temp OBJECT-TYPE
                    SYNTAX Integer32 (0..50)
                    UNITS "N/A"
                    MAX-ACCESS read-write
                    STATUS current
                    DESCRIPTION "Temperature Dead Zone Setpoint"
                    DEFVAL { 0 }
                    ::= { analogObjects 401 }

        -- 1.3.6.1.4.1.9839.2.1.2.402
        diff_temp OBJECT-TYPE
                    SYNTAX Integer32 (10..100)
                    UNITS "N/A"
                    MAX-ACCESS read-write
                    STATUS current
                    DESCRIPTION "Temperatue Control Band Setpoint"
                    DEFVAL { 10 }
                    ::= { analogObjects 402 }

        -- 1.3.6.1.4.1.9839.2.1.2.403
        diff_humid OBJECT-TYPE
                    SYNTAX Integer32 (0..200)
                    UNITS "N/A"
                    MAX-ACCESS read-write
                    STATUS current
                    DESCRIPTION "Humidity Control Band Setpoint"
                    DEFVAL { 10 }
                    ::= { analogObjects 403 }

        -- 1.3.6.1.4.1.9839.2.1.2.404
        room_temp_cal OBJECT-TYPE
                    SYNTAX Integer32 (-99..99)
                    UNITS "N/A"
                    MAX-ACCESS read-write
                    STATUS current
                    DESCRIPTION "Room Temp Probe Adjust"
                    DEFVAL { -99 }
                    ::= { analogObjects 404 }

        -- 1.3.6.1.4.1.9839.2.1.2.405
        supply_air_cal OBJECT-TYPE
                    SYNTAX Integer32 (-99..99)
                    UNITS "N/A"
                    MAX-ACCESS read-write
                    STATUS current
                    DESCRIPTION "Supply Air Probe Adjust"
                    DEFVAL { -99 }
                    ::= { analogObjects 405 }

        -- 1.3.6.1.4.1.9839.2.1.2.406
        room_humid_cal OBJECT-TYPE
                    SYNTAX Integer32 (-99..99)
                    UNITS "N/A"
                    MAX-ACCESS read-write
                    STATUS current
                    DESCRIPTION "Room Humidity Probe Adjust"
                    DEFVAL { -99 }
                    ::= { analogObjects 406 }

        -- 1.3.6.1.4.1.9839.2.1.2.407
        room_press_cal OBJECT-TYPE
                    SYNTAX Integer32 (-99..99)
                    UNITS "N/A"
                    MAX-ACCESS read-write
                    STATUS current
                    DESCRIPTION "Room Press. Diff. Probe Adjust"
                    DEFVAL { -99 }
                    ::= { analogObjects 407 }

        -- 1.3.6.1.4.1.9839.2.1.2.408
        changover_sp1 OBJECT-TYPE
                    SYNTAX Integer32 (0..9999)
                    UNITS "N/A"
                    MAX-ACCESS read-write
                    STATUS current
                    DESCRIPTION "Setpoint of auto changeover to DX mode"
                    DEFVAL { 188 }
                    ::= { analogObjects 408 }

        -- 1.3.6.1.4.1.9839.2.1.2.409
        min_value_humid OBJECT-TYPE
                    SYNTAX Integer32 (0..1000)
                    UNITS "N/A"
                    MAX-ACCESS read-write
                    STATUS current
                    DESCRIPTION "Minimum humidity"
                    DEFVAL { 0 }
                    ::= { analogObjects 409 }

        -- 1.3.6.1.4.1.9839.2.1.2.410
        max_value_humid OBJECT-TYPE
                    SYNTAX Integer32 (0..1000)
                    UNITS "N/A"
                    MAX-ACCESS read-write
                    STATUS current
                    DESCRIPTION "Maximum humidity"
                    DEFVAL { 0 }
                    ::= { analogObjects 410 }

        -- 1.3.6.1.4.1.9839.2.1.2.411
        pressure_4ma OBJECT-TYPE
                    SYNTAX Integer32 (-999..999)
                    UNITS "N/A"
                    MAX-ACCESS read-write
                    STATUS current
                    DESCRIPTION "Pressure at 4mA"
                    DEFVAL { 0 }
                    ::= { analogObjects 411 }

        -- 1.3.6.1.4.1.9839.2.1.2.412
        pressure_20ma OBJECT-TYPE
                    SYNTAX Integer32 (-999..999)
                    UNITS "N/A"
                    MAX-ACCESS read-write
                    STATUS current
                    DESCRIPTION "Pressure at 20mA"
                    DEFVAL { 0 }
                    ::= { analogObjects 412 }

        -- 1.3.6.1.4.1.9839.2.1.2.413
        overheat_set OBJECT-TYPE
                    SYNTAX Integer32 (0..999)
                    UNITS "N/A"
                    MAX-ACCESS read-write
                    STATUS current
                    DESCRIPTION "High Supply Air Temp Setpoint"
                    DEFVAL { 300 }
                    ::= { analogObjects 413 }

        -- 1.3.6.1.4.1.9839.2.1.2.414
        humid_h_set OBJECT-TYPE
                    SYNTAX Integer32 (200..800)
                    UNITS "N/A"
                    MAX-ACCESS read-write
                    STATUS current
                    DESCRIPTION "High Humidity Alarm Setpoint"
                    DEFVAL { 20 }
                    ::= { analogObjects 414 }

        -- 1.3.6.1.4.1.9839.2.1.2.415
        humid_l_set OBJECT-TYPE
                    SYNTAX Integer32 (200..800)
                    UNITS "N/A"
                    MAX-ACCESS read-write
                    STATUS current
                    DESCRIPTION "Low Humidity Alarm Setpoint"
                    DEFVAL { 200 }
                    ::= { analogObjects 415 }

        -- 1.3.6.1.4.1.9839.2.1.2.416
        high_room_temp OBJECT-TYPE
                    SYNTAX Integer32 (100..1500)
                    UNITS "N/A"
                    MAX-ACCESS read-write
                    STATUS current
                    DESCRIPTION "High Temperature Alarm Setpoint"
                    DEFVAL { 300 }
                    ::= { analogObjects 416 }

        -- 1.3.6.1.4.1.9839.2.1.2.417
        low_room_temp OBJECT-TYPE
                    SYNTAX Integer32 (100..1000)
                    UNITS "N/A"
                    MAX-ACCESS read-write
                    STATUS current
                    DESCRIPTION "Low Temperature Alarm Setpoint"
                    DEFVAL { 160 }
                    ::= { analogObjects 417 }

        -- 1.3.6.1.4.1.9839.2.1.2.418
        damper_min OBJECT-TYPE
                    SYNTAX Integer32 (0..100)
                    UNITS "N/A"
                    MAX-ACCESS read-write
                    STATUS current
                    DESCRIPTION "Minimum output of air damper"
                    DEFVAL { 0 }
                    ::= { analogObjects 418 }

        -- 1.3.6.1.4.1.9839.2.1.2.419
        damper_20ma OBJECT-TYPE
                    SYNTAX Integer32 (0..100)
                    UNITS "N/A"
                    MAX-ACCESS read-write
                    STATUS current
                    DESCRIPTION "Air Damper Output At Maximum Pressure"
                    DEFVAL { 100 }
                    ::= { analogObjects 419 }

        -- 1.3.6.1.4.1.9839.2.1.2.420
        damper_4ma OBJECT-TYPE
                    SYNTAX Integer32 (0..100)
                    UNITS "N/A"
                    MAX-ACCESS read-write
                    STATUS current
                    DESCRIPTION "Air Damper Output At Miniimum Pressure"
                    DEFVAL { 0 }
                    ::= { analogObjects 420 }

        -- 1.3.6.1.4.1.9839.2.1.2.421
        start_cool_damp OBJECT-TYPE
                    SYNTAX Integer32 (0..1000)
                    UNITS "N/A"
                    MAX-ACCESS read-write
                    STATUS current
                    DESCRIPTION "Open position of 0-10V cool valve"
                    DEFVAL { 0 }
                    ::= { analogObjects 421 }

        -- 1.3.6.1.4.1.9839.2.1.2.422
        end_cool_damp OBJECT-TYPE
                    SYNTAX Integer32 (0..1000)
                    UNITS "N/A"
                    MAX-ACCESS read-write
                    STATUS current
                    DESCRIPTION "Close position of 0-10V cool valve"
                    DEFVAL { 0 }
                    ::= { analogObjects 422 }

        -- 1.3.6.1.4.1.9839.2.1.2.423
        start_cool_d3p OBJECT-TYPE
                    SYNTAX Integer32 (0..1000)
                    UNITS "N/A"
                    MAX-ACCESS read-write
                    STATUS current
                    DESCRIPTION "Open position of 3 points valve"
                    DEFVAL { 0 }
                    ::= { analogObjects 423 }

        -- 1.3.6.1.4.1.9839.2.1.2.424
        end_cool_d3p OBJECT-TYPE
                    SYNTAX Integer32 (0..1000)
                    UNITS "N/A"
                    MAX-ACCESS read-write
                    STATUS current
                    DESCRIPTION "Close position of 3 points valve"
                    DEFVAL { 0 }
                    ::= { analogObjects 424 }

        -- 1.3.6.1.4.1.9839.2.1.2.425
        lim_max_humid OBJECT-TYPE
                    SYNTAX Integer32 (200..800)
                    UNITS "N/A"
                    MAX-ACCESS read-write
                    STATUS current
                    DESCRIPTION "Maximum Humidity Setpoint"
                    DEFVAL { 200 }
                    ::= { analogObjects 425 }

        -- 1.3.6.1.4.1.9839.2.1.2.426
        lim_max_temp OBJECT-TYPE
                    SYNTAX Integer32 (100..1500)
                    UNITS "N/A"
                    MAX-ACCESS read-write
                    STATUS current
                    DESCRIPTION "Maximum Temperature Setpoint"
                    DEFVAL { 1040 }
                    ::= { analogObjects 426 }

        -- 1.3.6.1.4.1.9839.2.1.2.427
        lim_min_humid OBJECT-TYPE
                    SYNTAX Integer32 (200..800)
                    UNITS "N/A"
                    MAX-ACCESS read-write
                    STATUS current
                    DESCRIPTION "Minimum Humidity Setpoint"
                    DEFVAL { 200 }
                    ::= { analogObjects 427 }

        -- 1.3.6.1.4.1.9839.2.1.2.428
        lim_min_temp OBJECT-TYPE
                    SYNTAX Integer32 (100..1500)
                    UNITS "N/A"
                    MAX-ACCESS read-write
                    STATUS current
                    DESCRIPTION "Minimum Temperature Setpoint"
                    DEFVAL { 500 }
                    ::= { analogObjects 428 }

        -- 1.3.6.1.4.1.9839.2.1.2.429
        temp_prop_mul_sp OBJECT-TYPE
                    SYNTAX Integer32 (-999..999)
                    UNITS "N/A"
                    MAX-ACCESS read-write
                    STATUS current
                    DESCRIPTION "Target Move Setpoint for Cooling (Proportional MUL)"
                    DEFVAL { 0 }
                    ::= { analogObjects 429 }

        -- 1.3.6.1.4.1.9839.2.1.2.430
        temp_deriv_mul_sp OBJECT-TYPE
                    SYNTAX Integer32 (-999..999)
                    UNITS "N/A"
                    MAX-ACCESS read-write
                    STATUS current
                    DESCRIPTION "Target Move Setpoint for Cooling (Derivative MUL)"
                    DEFVAL { 0 }
                    ::= { analogObjects 430 }

        -- 1.3.6.1.4.1.9839.2.1.2.431
        temp_deriv_sp OBJECT-TYPE
                    SYNTAX Integer32 (-999..999)
                    UNITS "N/A"
                    MAX-ACCESS read-write
                    STATUS current
                    DESCRIPTION "Target Move Setpoint for Cooling (Derivative)"
                    DEFVAL { 0 }
                    ::= { analogObjects 431 }

        -- 1.3.6.1.4.1.9839.2.1.2.432
        temp_lo_bound OBJECT-TYPE
                    SYNTAX Integer32 (-999..999)
                    UNITS "N/A"
                    MAX-ACCESS read-write
                    STATUS current
                    DESCRIPTION "Target Move Setpoint for Cooling (Lower Bound)"
                    DEFVAL { 0 }
                    ::= { analogObjects 432 }

        -- 1.3.6.1.4.1.9839.2.1.2.433
        temp_up_bound OBJECT-TYPE
                    SYNTAX Integer32 (-999..999)
                    UNITS "N/A"
                    MAX-ACCESS read-write
                    STATUS current
                    DESCRIPTION "Target Move Setpoint for Cooling (Upper Bound)"
                    DEFVAL { 0 }
                    ::= { analogObjects 433 }

        -- 1.3.6.1.4.1.9839.2.1.2.434
        humid_prop_mul_sp OBJECT-TYPE
                    SYNTAX Integer32 (-999..999)
                    UNITS "N/A"
                    MAX-ACCESS read-write
                    STATUS current
                    DESCRIPTION "Target Move Setpoint for Dehumidification (Proportional MUL)"
                    DEFVAL { 0 }
                    ::= { analogObjects 434 }

        -- 1.3.6.1.4.1.9839.2.1.2.435
        humid_deriv_mul_sp OBJECT-TYPE
                    SYNTAX Integer32 (-999..999)
                    UNITS "N/A"
                    MAX-ACCESS read-write
                    STATUS current
                    DESCRIPTION "Target Move Setpoint for Dehumidification (Derivative MUL)"
                    DEFVAL { 0 }
                    ::= { analogObjects 435 }

        -- 1.3.6.1.4.1.9839.2.1.2.436
        humid_lo_bound OBJECT-TYPE
                    SYNTAX Integer32 (-999..999)
                    UNITS "N/A"
                    MAX-ACCESS read-write
                    STATUS current
                    DESCRIPTION "Target Move Setpoint for Dehumidification (Lower Bound)"
                    DEFVAL { 0 }
                    ::= { analogObjects 436 }

        -- 1.3.6.1.4.1.9839.2.1.2.437
        humid_up_bound OBJECT-TYPE
                    SYNTAX Integer32 (-999..999)
                    UNITS "N/A"
                    MAX-ACCESS read-write
                    STATUS current
                    DESCRIPTION "Target Move Setpoint for Dehumidification (Upper Bound)"
                    DEFVAL { 0 }
                    ::= { analogObjects 437 }

        -- 1.3.6.1.4.1.9839.2.1.2.438
        humid_deriv_sp OBJECT-TYPE
                    SYNTAX Integer32 (-999..999)
                    UNITS "N/A"
                    MAX-ACCESS read-write
                    STATUS current
                    DESCRIPTION "Target Move Setpoint for Dehumidification (Derivative)"
                    DEFVAL { 0 }
                    ::= { analogObjects 438 }

        -- 1.3.6.1.4.1.9839.2.1.2.439
        supply_temp_sp OBJECT-TYPE
                    SYNTAX Integer32 (0..9999)
                    UNITS "N/A"
                    MAX-ACCESS read-write
                    STATUS current
                    DESCRIPTION "VFD Run Full Speed"
                    DEFVAL { 188 }
                    ::= { analogObjects 439 }

        -- 1.3.6.1.4.1.9839.2.1.2.440
        vfd_min OBJECT-TYPE
                    SYNTAX Integer32 (300..600)
                    UNITS "N/A"
                    MAX-ACCESS read-write
                    STATUS current
                    DESCRIPTION "VFD Minimum Hz"
                    DEFVAL { 300 }
                    ::= { analogObjects 440 }

        -- 1.3.6.1.4.1.9839.2.1.2.441
        vfd_max OBJECT-TYPE
                    SYNTAX Integer32 (300..600)
                    UNITS "N/A"
                    MAX-ACCESS read-write
                    STATUS current
                    DESCRIPTION "VFD Maximum Hz"
                    DEFVAL { 300 }
                    ::= { analogObjects 441 }

        -- 1.3.6.1.4.1.9839.2.1.2.442
        rt_trend_low OBJECT-TYPE
                    SYNTAX Integer32 (-32768..32767)
                    UNITS "N/A"
                    MAX-ACCESS read-write
                    STATUS current
                    DESCRIPTION "Room Temp Trend Low Bound"
                    DEFVAL { 0 }
                    ::= { analogObjects 442 }

        -- 1.3.6.1.4.1.9839.2.1.2.443
        rt_trend_high OBJECT-TYPE
                    SYNTAX Integer32 (-32768..32767)
                    UNITS "N/A"
                    MAX-ACCESS read-write
                    STATUS current
                    DESCRIPTION "Room Temp Trend High Bound"
                    DEFVAL { 0 }
                    ::= { analogObjects 443 }

        -- 1.3.6.1.4.1.9839.2.1.2.444
        man_humid_value OBJECT-TYPE
                    SYNTAX Integer32 (0..100)
                    UNITS "N/A"
                    MAX-ACCESS read-write
                    STATUS current
                    DESCRIPTION "N/A"
                    DEFVAL { 0 }
                    ::= { analogObjects 444 }

        -- 1.3.6.1.4.1.9839.2.1.2.445
        man_cool_value OBJECT-TYPE
                    SYNTAX Integer32 (0..100)
                    UNITS "N/A"
                    MAX-ACCESS read-write
                    STATUS current
                    DESCRIPTION "N/A"
                    DEFVAL { 0 }
                    ::= { analogObjects 445 }

        -- 1.3.6.1.4.1.9839.2.1.2.446
        man_blower_vfd OBJECT-TYPE
                    SYNTAX Integer32 (60..100)
                    UNITS "N/A"
                    MAX-ACCESS read-write
                    STATUS current
                    DESCRIPTION "N/A"
                    DEFVAL { 0 }
                    ::= { analogObjects 446 }



        -- 1.3.6.1.4.1.9839.2.1.3
        integerObjects OBJECT IDENTIFIER ::= { flccu1314gmarMIB 3 }

        -- 1.3.6.1.4.1.9839.2.1.3.0
        tam_model OBJECT-TYPE
                    SYNTAX Integer32 (-32768..32767)
                    UNITS "N/A"
                    MAX-ACCESS read-only
                    STATUS current
                    DESCRIPTION "N/A"
                    DEFVAL { 0 }
                    ::= { integerObjects 0 }

        -- 1.3.6.1.4.1.9839.2.1.3.1
        unit_status OBJECT-TYPE
                    SYNTAX Integer32 (0..999)
                    UNITS "N/A"
                    MAX-ACCESS read-only
                    STATUS current
                    DESCRIPTION "Unit Status"
                    DEFVAL { 0 }
                    ::= { integerObjects 1 }

        -- 1.3.6.1.4.1.9839.2.1.3.2
        conductivity OBJECT-TYPE
                    SYNTAX Integer32 (-9999..9999)
                    UNITS "N/A"
                    MAX-ACCESS read-only
                    STATUS current
                    DESCRIPTION "Conductivity of Cylinder"
                    DEFVAL { 0 }
                    ::= { integerObjects 2 }

        -- 1.3.6.1.4.1.9839.2.1.3.3
        cylinder1_phase OBJECT-TYPE
                    SYNTAX Integer32 (0..99)
                    UNITS "N/A"
                    MAX-ACCESS read-only
                    STATUS current
                    DESCRIPTION "Cylinder 1 Status"
                    DEFVAL { 0 }
                    ::= { integerObjects 3 }

        -- 1.3.6.1.4.1.9839.2.1.3.4
        cylinder1_status OBJECT-TYPE
                    SYNTAX Integer32 (0..99)
                    UNITS "N/A"
                    MAX-ACCESS read-only
                    STATUS current
                    DESCRIPTION "Cylinder 1 Activity"
                    DEFVAL { 0 }
                    ::= { integerObjects 4 }

        -- 1.3.6.1.4.1.9839.2.1.3.5
        x_hour_unit_h OBJECT-TYPE
                    SYNTAX Integer32 (0..999)
                    UNITS "N/A"
                    MAX-ACCESS read-only
                    STATUS current
                    DESCRIPTION "Unit Running Hour (H)"
                    DEFVAL { 0 }
                    ::= { integerObjects 5 }

        -- 1.3.6.1.4.1.9839.2.1.3.6
        x_hour_unit_l OBJECT-TYPE
                    SYNTAX Integer32 (0..999)
                    UNITS "N/A"
                    MAX-ACCESS read-only
                    STATUS current
                    DESCRIPTION "Unit Running Hour (L)"
                    DEFVAL { 0 }
                    ::= { integerObjects 6 }

        -- 1.3.6.1.4.1.9839.2.1.3.7
        x_hour_comp1_h OBJECT-TYPE
                    SYNTAX Integer32 (0..999)
                    UNITS "N/A"
                    MAX-ACCESS read-only
                    STATUS current
                    DESCRIPTION "Comp 1 Running Hour (H)"
                    DEFVAL { 0 }
                    ::= { integerObjects 7 }

        -- 1.3.6.1.4.1.9839.2.1.3.8
        x_hour_comp1_l OBJECT-TYPE
                    SYNTAX Integer32 (0..999)
                    UNITS "N/A"
                    MAX-ACCESS read-only
                    STATUS current
                    DESCRIPTION "Comp 1 Running Hour (L)"
                    DEFVAL { 0 }
                    ::= { integerObjects 8 }

        -- 1.3.6.1.4.1.9839.2.1.3.9
        x_hour_comp2_h OBJECT-TYPE
                    SYNTAX Integer32 (0..999)
                    UNITS "N/A"
                    MAX-ACCESS read-only
                    STATUS current
                    DESCRIPTION "Comp 2 Running Hour (H)"
                    DEFVAL { 0 }
                    ::= { integerObjects 9 }

        -- 1.3.6.1.4.1.9839.2.1.3.10
        x_hour_comp2_l OBJECT-TYPE
                    SYNTAX Integer32 (0..999)
                    UNITS "N/A"
                    MAX-ACCESS read-only
                    STATUS current
                    DESCRIPTION "Comp 2 Running Hour (L)"
                    DEFVAL { 0 }
                    ::= { integerObjects 10 }

        -- 1.3.6.1.4.1.9839.2.1.3.11
        current_year OBJECT-TYPE
                    SYNTAX Integer32 (0..99)
                    UNITS "N/A"
                    MAX-ACCESS read-only
                    STATUS current
                    DESCRIPTION "Current year"
                    DEFVAL { 0 }
                    ::= { integerObjects 11 }

        -- 1.3.6.1.4.1.9839.2.1.3.12
        current_month OBJECT-TYPE
                    SYNTAX Integer32 (1..12)
                    UNITS "N/A"
                    MAX-ACCESS read-only
                    STATUS current
                    DESCRIPTION "Current month"
                    DEFVAL { 1 }
                    ::= { integerObjects 12 }

        -- 1.3.6.1.4.1.9839.2.1.3.13
        current_day OBJECT-TYPE
                    SYNTAX Integer32 (1..31)
                    UNITS "N/A"
                    MAX-ACCESS read-only
                    STATUS current
                    DESCRIPTION "Current day"
                    DEFVAL { 1 }
                    ::= { integerObjects 13 }

        -- 1.3.6.1.4.1.9839.2.1.3.14
        current_weekday OBJECT-TYPE
                    SYNTAX Integer32 (1..7)
                    UNITS "N/A"
                    MAX-ACCESS read-only
                    STATUS current
                    DESCRIPTION "Current weekday"
                    DEFVAL { 1 }
                    ::= { integerObjects 14 }

        -- 1.3.6.1.4.1.9839.2.1.3.15
        current_hour OBJECT-TYPE
                    SYNTAX Integer32 (0..23)
                    UNITS "hour"
                    MAX-ACCESS read-only
                    STATUS current
                    DESCRIPTION "Current hour"
                    DEFVAL { 0 }
                    ::= { integerObjects 15 }

        -- 1.3.6.1.4.1.9839.2.1.3.16
        current_minute OBJECT-TYPE
                    SYNTAX Integer32 (0..59)
                    UNITS "N/A"
                    MAX-ACCESS read-only
                    STATUS current
                    DESCRIPTION "Current minute"
                    DEFVAL { 0 }
                    ::= { integerObjects 16 }

        -- 1.3.6.1.4.1.9839.2.1.3.17
        current_second OBJECT-TYPE
                    SYNTAX Integer32 (0..59)
                    UNITS "sec"
                    MAX-ACCESS read-only
                    STATUS current
                    DESCRIPTION "Current second"
                    DEFVAL { 0 }
                    ::= { integerObjects 17 }

        -- 1.3.6.1.4.1.9839.2.1.3.51
        cent_on_w OBJECT-TYPE
                    SYNTAX Integer32 (0..1)
                    UNITS "N/A"
                    MAX-ACCESS read-write
                    STATUS current
                    DESCRIPTION "UOM for Temperature"
                    DEFVAL { 0 }
                    ::= { integerObjects 51 }

        -- 1.3.6.1.4.1.9839.2.1.3.52
        temp_hour1 OBJECT-TYPE
                    SYNTAX Integer32 (0..23)
                    UNITS "N/A"
                    MAX-ACCESS read-write
                    STATUS current
                    DESCRIPTION "Temperature Setpoint (Hour-Time Zone 1)"
                    DEFVAL { 0 }
                    ::= { integerObjects 52 }

        -- 1.3.6.1.4.1.9839.2.1.3.53
        temp_minute1 OBJECT-TYPE
                    SYNTAX Integer32 (0..59)
                    UNITS "N/A"
                    MAX-ACCESS read-write
                    STATUS current
                    DESCRIPTION "Temperature Setpoint (Minute-Time Zone 1)"
                    DEFVAL { 0 }
                    ::= { integerObjects 53 }

        -- 1.3.6.1.4.1.9839.2.1.3.54
        temp_hour2 OBJECT-TYPE
                    SYNTAX Integer32 (0..23)
                    UNITS "N/A"
                    MAX-ACCESS read-write
                    STATUS current
                    DESCRIPTION "Temperature Setpoint (Hour-Time Zone 2)"
                    DEFVAL { 0 }
                    ::= { integerObjects 54 }

        -- 1.3.6.1.4.1.9839.2.1.3.55
        temp_minute2 OBJECT-TYPE
                    SYNTAX Integer32 (0..59)
                    UNITS "N/A"
                    MAX-ACCESS read-write
                    STATUS current
                    DESCRIPTION "Temperature Setpoint (Minute-Time Zone 2)"
                    DEFVAL { 0 }
                    ::= { integerObjects 55 }

        -- 1.3.6.1.4.1.9839.2.1.3.56
        temp_hour3 OBJECT-TYPE
                    SYNTAX Integer32 (0..23)
                    UNITS "N/A"
                    MAX-ACCESS read-write
                    STATUS current
                    DESCRIPTION "Temperature Setpoint (Hour-Time Zone 3)"
                    DEFVAL { 0 }
                    ::= { integerObjects 56 }

        -- 1.3.6.1.4.1.9839.2.1.3.57
        temp_minute3 OBJECT-TYPE
                    SYNTAX Integer32 (0..59)
                    UNITS "N/A"
                    MAX-ACCESS read-write
                    STATUS current
                    DESCRIPTION "Temperature Setpoint (Minute-Time Zone 3)"
                    DEFVAL { 0 }
                    ::= { integerObjects 57 }

        -- 1.3.6.1.4.1.9839.2.1.3.58
        temp_hour4 OBJECT-TYPE
                    SYNTAX Integer32 (0..23)
                    UNITS "N/A"
                    MAX-ACCESS read-write
                    STATUS current
                    DESCRIPTION "Temperature Setpoint (Hour-Time Zone 4)"
                    DEFVAL { 0 }
                    ::= { integerObjects 58 }

        -- 1.3.6.1.4.1.9839.2.1.3.59
        temp_minute4 OBJECT-TYPE
                    SYNTAX Integer32 (0..59)
                    UNITS "N/A"
                    MAX-ACCESS read-write
                    STATUS current
                    DESCRIPTION "Temperature Setpoint (Minute-Time Zone 4)"
                    DEFVAL { 0 }
                    ::= { integerObjects 59 }

        -- 1.3.6.1.4.1.9839.2.1.3.60
        humid_hour1 OBJECT-TYPE
                    SYNTAX Integer32 (0..23)
                    UNITS "N/A"
                    MAX-ACCESS read-write
                    STATUS current
                    DESCRIPTION "Humidity Setpoint (Hour-Time Zone 1)"
                    DEFVAL { 0 }
                    ::= { integerObjects 60 }

        -- 1.3.6.1.4.1.9839.2.1.3.61
        humid_minute1 OBJECT-TYPE
                    SYNTAX Integer32 (0..59)
                    UNITS "N/A"
                    MAX-ACCESS read-write
                    STATUS current
                    DESCRIPTION "Humidity Setpoint (Minute-Time Zone 1)"
                    DEFVAL { 0 }
                    ::= { integerObjects 61 }

        -- 1.3.6.1.4.1.9839.2.1.3.62
        humid_hour2 OBJECT-TYPE
                    SYNTAX Integer32 (0..23)
                    UNITS "N/A"
                    MAX-ACCESS read-write
                    STATUS current
                    DESCRIPTION "Humidity Setpoint (Hour-Time Zone 2)"
                    DEFVAL { 0 }
                    ::= { integerObjects 62 }

        -- 1.3.6.1.4.1.9839.2.1.3.63
        humid_minute2 OBJECT-TYPE
                    SYNTAX Integer32 (0..59)
                    UNITS "N/A"
                    MAX-ACCESS read-write
                    STATUS current
                    DESCRIPTION "Humidity Setpoint (Minute-Time Zone 2)"
                    DEFVAL { 0 }
                    ::= { integerObjects 63 }

        -- 1.3.6.1.4.1.9839.2.1.3.64
        humid_hour3 OBJECT-TYPE
                    SYNTAX Integer32 (0..23)
                    UNITS "N/A"
                    MAX-ACCESS read-write
                    STATUS current
                    DESCRIPTION "Humidity Setpoint (Hour-Time Zone 3)"
                    DEFVAL { 0 }
                    ::= { integerObjects 64 }

        -- 1.3.6.1.4.1.9839.2.1.3.65
        humid_minute3 OBJECT-TYPE
                    SYNTAX Integer32 (0..59)
                    UNITS "N/A"
                    MAX-ACCESS read-write
                    STATUS current
                    DESCRIPTION "Humidity Setpoint (Minute-Time Zone 3)"
                    DEFVAL { 0 }
                    ::= { integerObjects 65 }

        -- 1.3.6.1.4.1.9839.2.1.3.66
        humid_hour4 OBJECT-TYPE
                    SYNTAX Integer32 (0..23)
                    UNITS "N/A"
                    MAX-ACCESS read-write
                    STATUS current
                    DESCRIPTION "Humidity Setpoint (Hour-Time Zone 4)"
                    DEFVAL { 0 }
                    ::= { integerObjects 66 }

        -- 1.3.6.1.4.1.9839.2.1.3.67
        humid_minute4 OBJECT-TYPE
                    SYNTAX Integer32 (0..59)
                    UNITS "N/A"
                    MAX-ACCESS read-write
                    STATUS current
                    DESCRIPTION "Humidity Setpoint (Minute-Time Zone 4)"
                    DEFVAL { 0 }
                    ::= { integerObjects 67 }

        -- 1.3.6.1.4.1.9839.2.1.3.68
        on_mon_hour OBJECT-TYPE
                    SYNTAX Integer32 (0..23)
                    UNITS "N/A"
                    MAX-ACCESS read-write
                    STATUS current
                    DESCRIPTION "Monday ON Hour"
                    DEFVAL { 0 }
                    ::= { integerObjects 68 }

        -- 1.3.6.1.4.1.9839.2.1.3.69
        on_mon_min OBJECT-TYPE
                    SYNTAX Integer32 (0..59)
                    UNITS "N/A"
                    MAX-ACCESS read-write
                    STATUS current
                    DESCRIPTION "Monday ON Minute"
                    DEFVAL { 0 }
                    ::= { integerObjects 69 }

        -- 1.3.6.1.4.1.9839.2.1.3.70
        off_mon_hour OBJECT-TYPE
                    SYNTAX Integer32 (0..23)
                    UNITS "N/A"
                    MAX-ACCESS read-write
                    STATUS current
                    DESCRIPTION "Monday OFF Hour"
                    DEFVAL { 0 }
                    ::= { integerObjects 70 }

        -- 1.3.6.1.4.1.9839.2.1.3.71
        off_mon_min OBJECT-TYPE
                    SYNTAX Integer32 (0..59)
                    UNITS "N/A"
                    MAX-ACCESS read-write
                    STATUS current
                    DESCRIPTION "Monday OFF Minute"
                    DEFVAL { 0 }
                    ::= { integerObjects 71 }

        -- 1.3.6.1.4.1.9839.2.1.3.72
        on_tue_hour OBJECT-TYPE
                    SYNTAX Integer32 (0..23)
                    UNITS "N/A"
                    MAX-ACCESS read-write
                    STATUS current
                    DESCRIPTION "Tuesday ON Hour"
                    DEFVAL { 0 }
                    ::= { integerObjects 72 }

        -- 1.3.6.1.4.1.9839.2.1.3.73
        on_tue_min OBJECT-TYPE
                    SYNTAX Integer32 (0..59)
                    UNITS "N/A"
                    MAX-ACCESS read-write
                    STATUS current
                    DESCRIPTION "Tuesday ON Minute"
                    DEFVAL { 0 }
                    ::= { integerObjects 73 }

        -- 1.3.6.1.4.1.9839.2.1.3.74
        off_tue_hour OBJECT-TYPE
                    SYNTAX Integer32 (0..23)
                    UNITS "N/A"
                    MAX-ACCESS read-write
                    STATUS current
                    DESCRIPTION "Tuesday OFF Hour"
                    DEFVAL { 0 }
                    ::= { integerObjects 74 }

        -- 1.3.6.1.4.1.9839.2.1.3.75
        off_tue_min OBJECT-TYPE
                    SYNTAX Integer32 (0..59)
                    UNITS "N/A"
                    MAX-ACCESS read-write
                    STATUS current
                    DESCRIPTION "Tuesday OFF Minute"
                    DEFVAL { 0 }
                    ::= { integerObjects 75 }

        -- 1.3.6.1.4.1.9839.2.1.3.76
        on_wed_hour OBJECT-TYPE
                    SYNTAX Integer32 (0..23)
                    UNITS "N/A"
                    MAX-ACCESS read-write
                    STATUS current
                    DESCRIPTION "Wednesday ON Hour"
                    DEFVAL { 0 }
                    ::= { integerObjects 76 }

        -- 1.3.6.1.4.1.9839.2.1.3.77
        on_wed_min OBJECT-TYPE
                    SYNTAX Integer32 (0..59)
                    UNITS "N/A"
                    MAX-ACCESS read-write
                    STATUS current
                    DESCRIPTION "Wednesday ON Minute"
                    DEFVAL { 0 }
                    ::= { integerObjects 77 }

        -- 1.3.6.1.4.1.9839.2.1.3.78
        off_wed_hour OBJECT-TYPE
                    SYNTAX Integer32 (0..23)
                    UNITS "N/A"
                    MAX-ACCESS read-write
                    STATUS current
                    DESCRIPTION "Wednesday OFF Hour"
                    DEFVAL { 0 }
                    ::= { integerObjects 78 }

        -- 1.3.6.1.4.1.9839.2.1.3.79
        off_wed_min OBJECT-TYPE
                    SYNTAX Integer32 (0..59)
                    UNITS "N/A"
                    MAX-ACCESS read-write
                    STATUS current
                    DESCRIPTION "Wednesday OFF Minute"
                    DEFVAL { 0 }
                    ::= { integerObjects 79 }

        -- 1.3.6.1.4.1.9839.2.1.3.80
        on_thu_hour OBJECT-TYPE
                    SYNTAX Integer32 (0..23)
                    UNITS "N/A"
                    MAX-ACCESS read-write
                    STATUS current
                    DESCRIPTION "Thursday ON Hour"
                    DEFVAL { 0 }
                    ::= { integerObjects 80 }

        -- 1.3.6.1.4.1.9839.2.1.3.81
        on_thu_min OBJECT-TYPE
                    SYNTAX Integer32 (0..59)
                    UNITS "N/A"
                    MAX-ACCESS read-write
                    STATUS current
                    DESCRIPTION "Thursday ON Minute"
                    DEFVAL { 0 }
                    ::= { integerObjects 81 }

        -- 1.3.6.1.4.1.9839.2.1.3.82
        off_thu_hour OBJECT-TYPE
                    SYNTAX Integer32 (0..23)
                    UNITS "N/A"
                    MAX-ACCESS read-write
                    STATUS current
                    DESCRIPTION "Thursday OFF Hour"
                    DEFVAL { 0 }
                    ::= { integerObjects 82 }

        -- 1.3.6.1.4.1.9839.2.1.3.83
        off_thu_min OBJECT-TYPE
                    SYNTAX Integer32 (0..59)
                    UNITS "N/A"
                    MAX-ACCESS read-write
                    STATUS current
                    DESCRIPTION "Thursday OFF Minute"
                    DEFVAL { 0 }
                    ::= { integerObjects 83 }

        -- 1.3.6.1.4.1.9839.2.1.3.84
        on_fri_hour OBJECT-TYPE
                    SYNTAX Integer32 (0..23)
                    UNITS "N/A"
                    MAX-ACCESS read-write
                    STATUS current
                    DESCRIPTION "Friday ON Hour"
                    DEFVAL { 0 }
                    ::= { integerObjects 84 }

        -- 1.3.6.1.4.1.9839.2.1.3.85
        on_fri_min OBJECT-TYPE
                    SYNTAX Integer32 (0..59)
                    UNITS "N/A"
                    MAX-ACCESS read-write
                    STATUS current
                    DESCRIPTION "Friday ON Minute"
                    DEFVAL { 0 }
                    ::= { integerObjects 85 }

        -- 1.3.6.1.4.1.9839.2.1.3.86
        off_fri_hour OBJECT-TYPE
                    SYNTAX Integer32 (0..23)
                    UNITS "N/A"
                    MAX-ACCESS read-write
                    STATUS current
                    DESCRIPTION "Friday OFF Hour"
                    DEFVAL { 0 }
                    ::= { integerObjects 86 }

        -- 1.3.6.1.4.1.9839.2.1.3.87
        off_fri_min OBJECT-TYPE
                    SYNTAX Integer32 (0..59)
                    UNITS "N/A"
                    MAX-ACCESS read-write
                    STATUS current
                    DESCRIPTION "Friday OFF Minute"
                    DEFVAL { 0 }
                    ::= { integerObjects 87 }

        -- 1.3.6.1.4.1.9839.2.1.3.88
        on_sat_hour OBJECT-TYPE
                    SYNTAX Integer32 (0..23)
                    UNITS "N/A"
                    MAX-ACCESS read-write
                    STATUS current
                    DESCRIPTION "Saturday ON Hour"
                    DEFVAL { 0 }
                    ::= { integerObjects 88 }

        -- 1.3.6.1.4.1.9839.2.1.3.89
        on_sat_min OBJECT-TYPE
                    SYNTAX Integer32 (0..59)
                    UNITS "N/A"
                    MAX-ACCESS read-write
                    STATUS current
                    DESCRIPTION "Saturday ON Minute"
                    DEFVAL { 0 }
                    ::= { integerObjects 89 }

        -- 1.3.6.1.4.1.9839.2.1.3.90
        off_sat_hour OBJECT-TYPE
                    SYNTAX Integer32 (0..23)
                    UNITS "N/A"
                    MAX-ACCESS read-write
                    STATUS current
                    DESCRIPTION "Saturday OFF Hour"
                    DEFVAL { 0 }
                    ::= { integerObjects 90 }

        -- 1.3.6.1.4.1.9839.2.1.3.91
        off_sat_min OBJECT-TYPE
                    SYNTAX Integer32 (0..59)
                    UNITS "N/A"
                    MAX-ACCESS read-write
                    STATUS current
                    DESCRIPTION "Saturday OFF Minute"
                    DEFVAL { 0 }
                    ::= { integerObjects 91 }

        -- 1.3.6.1.4.1.9839.2.1.3.92
        on_sun_hour OBJECT-TYPE
                    SYNTAX Integer32 (0..23)
                    UNITS "N/A"
                    MAX-ACCESS read-write
                    STATUS current
                    DESCRIPTION "Sunday ON Hour"
                    DEFVAL { 0 }
                    ::= { integerObjects 92 }

        -- 1.3.6.1.4.1.9839.2.1.3.93
        on_sun_min OBJECT-TYPE
                    SYNTAX Integer32 (0..59)
                    UNITS "N/A"
                    MAX-ACCESS read-write
                    STATUS current
                    DESCRIPTION "Sunday ON Minute"
                    DEFVAL { 0 }
                    ::= { integerObjects 93 }

        -- 1.3.6.1.4.1.9839.2.1.3.94
        off_sun_hour OBJECT-TYPE
                    SYNTAX Integer32 (0..23)
                    UNITS "N/A"
                    MAX-ACCESS read-write
                    STATUS current
                    DESCRIPTION "Sunday OFF Hour"
                    DEFVAL { 0 }
                    ::= { integerObjects 94 }

        -- 1.3.6.1.4.1.9839.2.1.3.95
        off_sun_min OBJECT-TYPE
                    SYNTAX Integer32 (0..59)
                    UNITS "N/A"
                    MAX-ACCESS read-write
                    STATUS current
                    DESCRIPTION "Sunday OFF Minute"
                    DEFVAL { 0 }
                    ::= { integerObjects 95 }

        -- 1.3.6.1.4.1.9839.2.1.3.201
        voltage_type OBJECT-TYPE
                    SYNTAX Integer32 (0..99)
                    UNITS "N/A"
                    MAX-ACCESS read-only
                    STATUS current
                    DESCRIPTION "Humidifier Voltage Type"
                    DEFVAL { 0 }
                    ::= { integerObjects 201 }

        -- 1.3.6.1.4.1.9839.2.1.3.202
        voltage OBJECT-TYPE
                    SYNTAX Integer32 (-32768..32767)
                    UNITS "N/A"
                    MAX-ACCESS read-only
                    STATUS current
                    DESCRIPTION "Humidifier Voltage"
                    DEFVAL { 0 }
                    ::= { integerObjects 202 }

        -- 1.3.6.1.4.1.9839.2.1.3.203
        min_overheat_de OBJECT-TYPE
                    SYNTAX Integer32 (-32768..32767)
                    UNITS "N/A"
                    MAX-ACCESS read-only
                    STATUS current
                    DESCRIPTION "Minimum Delay Time of High Supply Temperature Alarm"
                    DEFVAL { 0 }
                    ::= { integerObjects 203 }

        -- 1.3.6.1.4.1.9839.2.1.3.204
        max_overheat_de OBJECT-TYPE
                    SYNTAX Integer32 (-32768..32767)
                    UNITS "N/A"
                    MAX-ACCESS read-only
                    STATUS current
                    DESCRIPTION "Maximum Delay Time of High Supply Temperature Alarm"
                    DEFVAL { 0 }
                    ::= { integerObjects 204 }

        -- 1.3.6.1.4.1.9839.2.1.3.205
        mask_year OBJECT-TYPE
                    SYNTAX Integer32 (0..32767)
                    UNITS "N/A"
                    MAX-ACCESS read-write
                    STATUS current
                    DESCRIPTION "N/A"
                    DEFVAL { 0 }
                    ::= { integerObjects 205 }

        -- 1.3.6.1.4.1.9839.2.1.3.206
        mask_month OBJECT-TYPE
                    SYNTAX Integer32 (0..32767)
                    UNITS "N/A"
                    MAX-ACCESS read-write
                    STATUS current
                    DESCRIPTION "N/A"
                    DEFVAL { 0 }
                    ::= { integerObjects 206 }

        -- 1.3.6.1.4.1.9839.2.1.3.207
        mask_day OBJECT-TYPE
                    SYNTAX Integer32 (0..32767)
                    UNITS "N/A"
                    MAX-ACCESS read-write
                    STATUS current
                    DESCRIPTION "N/A"
                    DEFVAL { 0 }
                    ::= { integerObjects 207 }

        -- 1.3.6.1.4.1.9839.2.1.3.208
        mask_hour OBJECT-TYPE
                    SYNTAX Integer32 (0..32767)
                    UNITS "N/A"
                    MAX-ACCESS read-write
                    STATUS current
                    DESCRIPTION "N/A"
                    DEFVAL { 0 }
                    ::= { integerObjects 208 }

        -- 1.3.6.1.4.1.9839.2.1.3.209
        mask_minute OBJECT-TYPE
                    SYNTAX Integer32 (0..32767)
                    UNITS "N/A"
                    MAX-ACCESS read-write
                    STATUS current
                    DESCRIPTION "N/A"
                    DEFVAL { 0 }
                    ::= { integerObjects 209 }

        -- 1.3.6.1.4.1.9839.2.1.3.210
        mask_code OBJECT-TYPE
                    SYNTAX Integer32 (0..32767)
                    UNITS "N/A"
                    MAX-ACCESS read-write
                    STATUS current
                    DESCRIPTION "N/A"
                    DEFVAL { 0 }
                    ::= { integerObjects 210 }

        -- 1.3.6.1.4.1.9839.2.1.3.211
        conf_units_rot OBJECT-TYPE
                    SYNTAX Integer32 (0..8)
                    UNITS "N/A"
                    MAX-ACCESS read-write
                    STATUS current
                    DESCRIPTION "Number Of Unit For Rotation"
                    DEFVAL { 0 }
                    ::= { integerObjects 211 }

        -- 1.3.6.1.4.1.9839.2.1.3.212
        ver_year OBJECT-TYPE
                    SYNTAX Integer32 (0..99)
                    UNITS "N/A"
                    MAX-ACCESS read-only
                    STATUS current
                    DESCRIPTION "Version Year"
                    DEFVAL { 0 }
                    ::= { integerObjects 212 }

        -- 1.3.6.1.4.1.9839.2.1.3.213
        ver_mo OBJECT-TYPE
                    SYNTAX Integer32 (0..99)
                    UNITS "N/A"
                    MAX-ACCESS read-only
                    STATUS current
                    DESCRIPTION "Version Month"
                    DEFVAL { 0 }
                    ::= { integerObjects 213 }

        -- 1.3.6.1.4.1.9839.2.1.3.214
        ver_da OBJECT-TYPE
                    SYNTAX Integer32 (0..99)
                    UNITS "N/A"
                    MAX-ACCESS read-only
                    STATUS current
                    DESCRIPTION "Version Date"
                    DEFVAL { 0 }
                    ::= { integerObjects 214 }

        -- 1.3.6.1.4.1.9839.2.1.3.215
        event_number OBJECT-TYPE
                    SYNTAX Integer32 (0..999)
                    UNITS "N/A"
                    MAX-ACCESS read-only
                    STATUS current
                    DESCRIPTION "N/A"
                    DEFVAL { 0 }
                    ::= { integerObjects 215 }

        -- 1.3.6.1.4.1.9839.2.1.3.216
        pos OBJECT-TYPE
                    SYNTAX Integer32 (0..9)
                    UNITS "N/A"
                    MAX-ACCESS read-only
                    STATUS current
                    DESCRIPTION "N/A"
                    DEFVAL { 0 }
                    ::= { integerObjects 216 }

        -- 1.3.6.1.4.1.9839.2.1.3.217
        pass_type OBJECT-TYPE
                    SYNTAX Integer32 (0..9)
                    UNITS "N/A"
                    MAX-ACCESS read-only
                    STATUS current
                    DESCRIPTION "N/A"
                    DEFVAL { 0 }
                    ::= { integerObjects 217 }

        -- 1.3.6.1.4.1.9839.2.1.3.401
        unit_mode OBJECT-TYPE
                    SYNTAX Integer32 (0..2)
                    UNITS "N/A"
                    MAX-ACCESS read-write
                    STATUS current
                    DESCRIPTION "Unit Mode Set"
                    DEFVAL { 0 }
                    ::= { integerObjects 401 }

        -- 1.3.6.1.4.1.9839.2.1.3.402
        n_fan OBJECT-TYPE
                    SYNTAX Integer32 (1..2)
                    UNITS "N/A"
                    MAX-ACCESS read-write
                    STATUS current
                    DESCRIPTION "No. of Evap. Fan"
                    DEFVAL { 1 }
                    ::= { integerObjects 402 }

        -- 1.3.6.1.4.1.9839.2.1.3.403
        n_comp OBJECT-TYPE
                    SYNTAX Integer32 (1..2)
                    UNITS "N/A"
                    MAX-ACCESS read-write
                    STATUS current
                    DESCRIPTION "No. Of Comp."
                    DEFVAL { 1 }
                    ::= { integerObjects 403 }

        -- 1.3.6.1.4.1.9839.2.1.3.404
        n_comp_dehumid OBJECT-TYPE
                    SYNTAX Integer32 (1..2)
                    UNITS "N/A"
                    MAX-ACCESS read-write
                    STATUS current
                    DESCRIPTION "No. of Comp. For Dehumid."
                    DEFVAL { 2 }
                    ::= { integerObjects 404 }

        -- 1.3.6.1.4.1.9839.2.1.3.405
        n_heaters OBJECT-TYPE
                    SYNTAX Integer32 (1..3)
                    UNITS "N/A"
                    MAX-ACCESS read-write
                    STATUS current
                    DESCRIPTION "Heater Setup"
                    DEFVAL { 3 }
                    ::= { integerObjects 405 }

        -- 1.3.6.1.4.1.9839.2.1.3.406
        delay_on_fan OBJECT-TYPE
                    SYNTAX Integer32 (0..999)
                    UNITS "N/A"
                    MAX-ACCESS read-write
                    STATUS current
                    DESCRIPTION "Evap Fan Delay ON Time"
                    DEFVAL { 0 }
                    ::= { integerObjects 406 }

        -- 1.3.6.1.4.1.9839.2.1.3.407
        delay_off_fan OBJECT-TYPE
                    SYNTAX Integer32 (0..999)
                    UNITS "N/A"
                    MAX-ACCESS read-write
                    STATUS current
                    DESCRIPTION "Evap Fan Delay Off Time"
                    DEFVAL { 0 }
                    ::= { integerObjects 407 }

        -- 1.3.6.1.4.1.9839.2.1.3.408
        liq_delay OBJECT-TYPE
                    SYNTAX Integer32 (0..99)
                    UNITS "N/A"
                    MAX-ACCESS read-write
                    STATUS current
                    DESCRIPTION "Liquid Line Sol Vlv On Delay"
                    DEFVAL { 0 }
                    ::= { integerObjects 408 }

        -- 1.3.6.1.4.1.9839.2.1.3.409
        rit_pumpdown OBJECT-TYPE
                    SYNTAX Integer32 (0..300)
                    UNITS "N/A"
                    MAX-ACCESS read-write
                    STATUS current
                    DESCRIPTION "Pumpdown Delay"
                    DEFVAL { 0 }
                    ::= { integerObjects 409 }

        -- 1.3.6.1.4.1.9839.2.1.3.410
        time_betw_heat OBJECT-TYPE
                    SYNTAX Integer32 (3..99)
                    UNITS "N/A"
                    MAX-ACCESS read-write
                    STATUS current
                    DESCRIPTION "Heater Insertion Delay"
                    DEFVAL { 3 }
                    ::= { integerObjects 410 }

        -- 1.3.6.1.4.1.9839.2.1.3.411
        time_integr OBJECT-TYPE
                    SYNTAX Integer32 (0..999)
                    UNITS "N/A"
                    MAX-ACCESS read-write
                    STATUS current
                    DESCRIPTION "Integral Time For P+I Control"
                    DEFVAL { 0 }
                    ::= { integerObjects 411 }

        -- 1.3.6.1.4.1.9839.2.1.3.412
        thr_hour_unit OBJECT-TYPE
                    SYNTAX Integer32 (1..999)
                    UNITS "N/A"
                    MAX-ACCESS read-write
                    STATUS current
                    DESCRIPTION "Unit Maintenance Threshold Hour (x1000)"
                    DEFVAL { 1 }
                    ::= { integerObjects 412 }

        -- 1.3.6.1.4.1.9839.2.1.3.413
        thr_hour_comp OBJECT-TYPE
                    SYNTAX Integer32 (1..999)
                    UNITS "N/A"
                    MAX-ACCESS read-write
                    STATUS current
                    DESCRIPTION "Comp Maintenance Threshold Hour (x1000)"
                    DEFVAL { 1 }
                    ::= { integerObjects 413 }

        -- 1.3.6.1.4.1.9839.2.1.3.414
        type_ain_humid OBJECT-TYPE
                    SYNTAX Integer32 (2..4)
                    UNITS "N/A"
                    MAX-ACCESS read-write
                    STATUS current
                    DESCRIPTION "Humidity Probe Type"
                    DEFVAL { 2 }
                    ::= { integerObjects 414 }

        -- 1.3.6.1.4.1.9839.2.1.3.415
        humid_type OBJECT-TYPE
                    SYNTAX Integer32 (0..2)
                    UNITS "N/A"
                    MAX-ACCESS read-write
                    STATUS current
                    DESCRIPTION "Type Of Humidifier"
                    DEFVAL { 0 }
                    ::= { integerObjects 415 }

        -- 1.3.6.1.4.1.9839.2.1.3.416
        humid_delay OBJECT-TYPE
                    SYNTAX Integer32 (0..600)
                    UNITS "N/A"
                    MAX-ACCESS read-write
                    STATUS current
                    DESCRIPTION "Humidifier Insertion Delay"
                    DEFVAL { 0 }
                    ::= { integerObjects 416 }

        -- 1.3.6.1.4.1.9839.2.1.3.417
        del_air_flow OBJECT-TYPE
                    SYNTAX Integer32 (0..999)
                    UNITS "N/A"
                    MAX-ACCESS read-write
                    STATUS current
                    DESCRIPTION "No Air Flow Alarm Delay"
                    DEFVAL { 30 }
                    ::= { integerObjects 417 }

        -- 1.3.6.1.4.1.9839.2.1.3.418
        del_al_cus OBJECT-TYPE
                    SYNTAX Integer32 (0..180)
                    UNITS "N/A"
                    MAX-ACCESS read-write
                    STATUS current
                    DESCRIPTION "Customer Interlock Alarm Delay"
                    DEFVAL { 0 }
                    ::= { integerObjects 418 }

        -- 1.3.6.1.4.1.9839.2.1.3.419
        del_flood OBJECT-TYPE
                    SYNTAX Integer32 (0..999)
                    UNITS "N/A"
                    MAX-ACCESS read-write
                    STATUS current
                    DESCRIPTION "Water Detector Alarm Delay"
                    DEFVAL { 10 }
                    ::= { integerObjects 419 }

        -- 1.3.6.1.4.1.9839.2.1.3.420
        del_water_level OBJECT-TYPE
                    SYNTAX Integer32 (0..600)
                    UNITS "N/A"
                    MAX-ACCESS read-write
                    STATUS current
                    DESCRIPTION "Humidifier Water Level Alarm Delay"
                    DEFVAL { 5 }
                    ::= { integerObjects 420 }

        -- 1.3.6.1.4.1.9839.2.1.3.421
        high_target_sp OBJECT-TYPE
                    SYNTAX Integer32 (0..99)
                    UNITS "N/A"
                    MAX-ACCESS read-write
                    STATUS current
                    DESCRIPTION "Max. Freq. - Temp. Target"
                    DEFVAL { 0 }
                    ::= { integerObjects 421 }

        -- 1.3.6.1.4.1.9839.2.1.3.422
        high_target_sp_humid OBJECT-TYPE
                    SYNTAX Integer32 (0..99)
                    UNITS "N/A"
                    MAX-ACCESS read-write
                    STATUS current
                    DESCRIPTION "Max. Freq. - Humid Target"
                    DEFVAL { 0 }
                    ::= { integerObjects 422 }

        -- 1.3.6.1.4.1.9839.2.1.3.423
        new_hour OBJECT-TYPE
                    SYNTAX Integer32 (0..23)
                    UNITS "hour"
                    MAX-ACCESS read-write
                    STATUS current
                    DESCRIPTION "New hour"
                    DEFVAL { 0 }
                    ::= { integerObjects 423 }

        -- 1.3.6.1.4.1.9839.2.1.3.424
        new_minute OBJECT-TYPE
                    SYNTAX Integer32 (0..59)
                    UNITS "N/A"
                    MAX-ACCESS read-write
                    STATUS current
                    DESCRIPTION "New minute"
                    DEFVAL { 0 }
                    ::= { integerObjects 424 }

        -- 1.3.6.1.4.1.9839.2.1.3.425
        new_day OBJECT-TYPE
                    SYNTAX Integer32 (1..31)
                    UNITS "N/A"
                    MAX-ACCESS read-write
                    STATUS current
                    DESCRIPTION "New day"
                    DEFVAL { 0 }
                    ::= { integerObjects 425 }

        -- 1.3.6.1.4.1.9839.2.1.3.426
        new_month OBJECT-TYPE
                    SYNTAX Integer32 (1..12)
                    UNITS "N/A"
                    MAX-ACCESS read-write
                    STATUS current
                    DESCRIPTION "New month"
                    DEFVAL { 0 }
                    ::= { integerObjects 426 }

        -- 1.3.6.1.4.1.9839.2.1.3.427
        new_year OBJECT-TYPE
                    SYNTAX Integer32 (0..99)
                    UNITS "N/A"
                    MAX-ACCESS read-write
                    STATUS current
                    DESCRIPTION "New year"
                    DEFVAL { 0 }
                    ::= { integerObjects 427 }

        -- 1.3.6.1.4.1.9839.2.1.3.428
        new_weekday OBJECT-TYPE
                    SYNTAX Integer32 (1..7)
                    UNITS "N/A"
                    MAX-ACCESS read-write
                    STATUS current
                    DESCRIPTION "New weekday"
                    DEFVAL { 1 }
                    ::= { integerObjects 428 }

        -- 1.3.6.1.4.1.9839.2.1.3.429
        overheat_delay OBJECT-TYPE
                    SYNTAX Integer32 (-32768..32767)
                    UNITS "N/A"
                    MAX-ACCESS read-write
                    STATUS current
                    DESCRIPTION "High Supply Air Temp Alarm Delay"
                    DEFVAL { 5 }
                    ::= { integerObjects 429 }

        -- 1.3.6.1.4.1.9839.2.1.3.430
        unit2_mode OBJECT-TYPE
                    SYNTAX Integer32 (0..2)
                    UNITS "N/A"
                    MAX-ACCESS read-write
                    STATUS current
                    DESCRIPTION "Unit 2 Configuration"
                    DEFVAL { 0 }
                    ::= { integerObjects 430 }

        -- 1.3.6.1.4.1.9839.2.1.3.431
        unit3_mode OBJECT-TYPE
                    SYNTAX Integer32 (0..2)
                    UNITS "N/A"
                    MAX-ACCESS read-write
                    STATUS current
                    DESCRIPTION "Unit 3 Configuration"
                    DEFVAL { 0 }
                    ::= { integerObjects 431 }

        -- 1.3.6.1.4.1.9839.2.1.3.432
        unit4_mode OBJECT-TYPE
                    SYNTAX Integer32 (0..2)
                    UNITS "N/A"
                    MAX-ACCESS read-write
                    STATUS current
                    DESCRIPTION "Unit 4 Configuration"
                    DEFVAL { 0 }
                    ::= { integerObjects 432 }

        -- 1.3.6.1.4.1.9839.2.1.3.433
        unit5_mode OBJECT-TYPE
                    SYNTAX Integer32 (0..2)
                    UNITS "N/A"
                    MAX-ACCESS read-write
                    STATUS current
                    DESCRIPTION "Unit 5 Configuration"
                    DEFVAL { 0 }
                    ::= { integerObjects 433 }

        -- 1.3.6.1.4.1.9839.2.1.3.434
        unit6_mode OBJECT-TYPE
                    SYNTAX Integer32 (0..2)
                    UNITS "N/A"
                    MAX-ACCESS read-write
                    STATUS current
                    DESCRIPTION "Unit 6 Configuration"
                    DEFVAL { 0 }
                    ::= { integerObjects 434 }

        -- 1.3.6.1.4.1.9839.2.1.3.435
        unit7_mode OBJECT-TYPE
                    SYNTAX Integer32 (0..2)
                    UNITS "N/A"
                    MAX-ACCESS read-write
                    STATUS current
                    DESCRIPTION "Unit 7 Configuration"
                    DEFVAL { 0 }
                    ::= { integerObjects 435 }

        -- 1.3.6.1.4.1.9839.2.1.3.436
        unit8_mode OBJECT-TYPE
                    SYNTAX Integer32 (0..2)
                    UNITS "N/A"
                    MAX-ACCESS read-write
                    STATUS current
                    DESCRIPTION "Unit 8 Configuration"
                    DEFVAL { 0 }
                    ::= { integerObjects 436 }

        -- 1.3.6.1.4.1.9839.2.1.3.437
        unit1_mode OBJECT-TYPE
                    SYNTAX Integer32 (0..1)
                    UNITS "N/A"
                    MAX-ACCESS read-write
                    STATUS current
                    DESCRIPTION "Unit 1 Configuration"
                    DEFVAL { 0 }
                    ::= { integerObjects 437 }

        -- 1.3.6.1.4.1.9839.2.1.3.438
        net_mode OBJECT-TYPE
                    SYNTAX Integer32 (0..2)
                    UNITS "N/A"
                    MAX-ACCESS read-write
                    STATUS current
                    DESCRIPTION "Unit Rotation type"
                    DEFVAL { 0 }
                    ::= { integerObjects 438 }

        -- 1.3.6.1.4.1.9839.2.1.3.439
        rotation_time OBJECT-TYPE
                    SYNTAX Integer32 (0..240)
                    UNITS "N/A"
                    MAX-ACCESS read-write
                    STATUS current
                    DESCRIPTION "Unit Rotation Time"
                    DEFVAL { 0 }
                    ::= { integerObjects 439 }

        -- 1.3.6.1.4.1.9839.2.1.3.440
        hour_change OBJECT-TYPE
                    SYNTAX Integer32 (0..23)
                    UNITS "N/A"
                    MAX-ACCESS read-write
                    STATUS current
                    DESCRIPTION "Rotation Time (Hour)"
                    DEFVAL { 0 }
                    ::= { integerObjects 440 }

        -- 1.3.6.1.4.1.9839.2.1.3.441
        minute_change OBJECT-TYPE
                    SYNTAX Integer32 (0..59)
                    UNITS "N/A"
                    MAX-ACCESS read-write
                    STATUS current
                    DESCRIPTION "Rotation Time (Minute)"
                    DEFVAL { 0 }
                    ::= { integerObjects 441 }

        -- 1.3.6.1.4.1.9839.2.1.3.442
        day_rotation OBJECT-TYPE
                    SYNTAX Integer32 (1..7)
                    UNITS "N/A"
                    MAX-ACCESS read-write
                    STATUS current
                    DESCRIPTION "Time Interval To Take Rotation"
                    DEFVAL { 1 }
                    ::= { integerObjects 442 }

        -- 1.3.6.1.4.1.9839.2.1.3.443
        units_stand_by OBJECT-TYPE
                    SYNTAX Integer32 (0..7)
                    UNITS "N/A"
                    MAX-ACCESS read-write
                    STATUS current
                    DESCRIPTION "Standby Units"
                    DEFVAL { 0 }
                    ::= { integerObjects 443 }

        -- 1.3.6.1.4.1.9839.2.1.3.444
        humidifier_type OBJECT-TYPE
                    SYNTAX Integer32 (0..73)
                    UNITS "N/A"
                    MAX-ACCESS read-write
                    STATUS current
                    DESCRIPTION "Humidifier Type"
                    DEFVAL { 1 }
                    ::= { integerObjects 444 }

        -- 1.3.6.1.4.1.9839.2.1.3.445
        n_cylinders OBJECT-TYPE
                    SYNTAX Integer32 (0..1)
                    UNITS "N/A"
                    MAX-ACCESS read-write
                    STATUS current
                    DESCRIPTION "Number of Cylinders"
                    DEFVAL { 0 }
                    ::= { integerObjects 445 }

        -- 1.3.6.1.4.1.9839.2.1.3.446
        b2 OBJECT-TYPE
                    SYNTAX Integer32 (0..120)
                    UNITS "N/A"
                    MAX-ACCESS read-write
                    STATUS current
                    DESCRIPTION "Time to off"
                    DEFVAL { 0 }
                    ::= { integerObjects 446 }

        -- 1.3.6.1.4.1.9839.2.1.3.447
        b4 OBJECT-TYPE
                    SYNTAX Integer32 (0..2000)
                    UNITS "N/A"
                    MAX-ACCESS read-write
                    STATUS current
                    DESCRIPTION "Force Conductivity"
                    DEFVAL { 0 }
                    ::= { integerObjects 447 }

        -- 1.3.6.1.4.1.9839.2.1.3.448
        b5 OBJECT-TYPE
                    SYNTAX Integer32 (-32768..32767)
                    UNITS "N/A"
                    MAX-ACCESS read-write
                    STATUS current
                    DESCRIPTION "Conductivity Warning"
                    DEFVAL { 0 }
                    ::= { integerObjects 448 }

        -- 1.3.6.1.4.1.9839.2.1.3.449
        b6 OBJECT-TYPE
                    SYNTAX Integer32 (0..2000)
                    UNITS "N/A"
                    MAX-ACCESS read-write
                    STATUS current
                    DESCRIPTION "Conductivity Alarm"
                    DEFVAL { 0 }
                    ::= { integerObjects 449 }

        -- 1.3.6.1.4.1.9839.2.1.3.450
        b8 OBJECT-TYPE
                    SYNTAX Integer32 (50..200)
                    UNITS "N/A"
                    MAX-ACCESS read-write
                    STATUS current
                    DESCRIPTION "Drain Frequency"
                    DEFVAL { 50 }
                    ::= { integerObjects 450 }

        -- 1.3.6.1.4.1.9839.2.1.3.451
        b9 OBJECT-TYPE
                    SYNTAX Integer32 (50..200)
                    UNITS "N/A"
                    MAX-ACCESS read-write
                    STATUS current
                    DESCRIPTION "Drain Duration"
                    DEFVAL { 50 }
                    ::= { integerObjects 451 }

        -- 1.3.6.1.4.1.9839.2.1.3.452
        hour_maint_warn OBJECT-TYPE
                    SYNTAX Integer32 (0..4000)
                    UNITS "N/A"
                    MAX-ACCESS read-write
                    STATUS current
                    DESCRIPTION "Cylinder Maintenance Warning"
                    DEFVAL { 0 }
                    ::= { integerObjects 452 }

        -- 1.3.6.1.4.1.9839.2.1.3.453
        flush_period OBJECT-TYPE
                    SYNTAX Integer32 (1..120)
                    UNITS "N/A"
                    MAX-ACCESS read-write
                    STATUS current
                    DESCRIPTION "Flush Period"
                    DEFVAL { 1 }
                    ::= { integerObjects 453 }

        -- 1.3.6.1.4.1.9839.2.1.3.454
        inactivity_drain OBJECT-TYPE
                    SYNTAX Integer32 (1..199)
                    UNITS "N/A"
                    MAX-ACCESS read-write
                    STATUS current
                    DESCRIPTION "Inactivity Drain"
                    DEFVAL { 1 }
                    ::= { integerObjects 454 }

        -- 1.3.6.1.4.1.9839.2.1.3.455
        s_thresh1_h OBJECT-TYPE
                    SYNTAX Integer32 (0..999)
                    UNITS "N/A"
                    MAX-ACCESS read-write
                    STATUS current
                    DESCRIPTION "Compressor 1 Position (Dehumidification)"
                    DEFVAL { 0 }
                    ::= { integerObjects 455 }

        -- 1.3.6.1.4.1.9839.2.1.3.456
        s_differ1_h OBJECT-TYPE
                    SYNTAX Integer32 (0..999)
                    UNITS "N/A"
                    MAX-ACCESS read-write
                    STATUS current
                    DESCRIPTION "Compressor 1 Hysteresis (Dehumidification)"
                    DEFVAL { 0 }
                    ::= { integerObjects 456 }

        -- 1.3.6.1.4.1.9839.2.1.3.457
        s_thresh2_h OBJECT-TYPE
                    SYNTAX Integer32 (0..999)
                    UNITS "N/A"
                    MAX-ACCESS read-write
                    STATUS current
                    DESCRIPTION "Compressor 2 Position (Dehumidification)"
                    DEFVAL { 0 }
                    ::= { integerObjects 457 }

        -- 1.3.6.1.4.1.9839.2.1.3.458
        s_differ2_h OBJECT-TYPE
                    SYNTAX Integer32 (0..999)
                    UNITS "N/A"
                    MAX-ACCESS read-write
                    STATUS current
                    DESCRIPTION "Compressor 2 Hysteresis (Dehumidification)"
                    DEFVAL { 0 }
                    ::= { integerObjects 458 }

        -- 1.3.6.1.4.1.9839.2.1.3.459
        t_lon_posit OBJECT-TYPE
                    SYNTAX Integer32 (0..999)
                    UNITS "N/A"
                    MAX-ACCESS read-write
                    STATUS current
                    DESCRIPTION "On Dehumidification Temperature"
                    DEFVAL { 0 }
                    ::= { integerObjects 459 }

        -- 1.3.6.1.4.1.9839.2.1.3.460
        t_loff_posit OBJECT-TYPE
                    SYNTAX Integer32 (0..999)
                    UNITS "N/A"
                    MAX-ACCESS read-write
                    STATUS current
                    DESCRIPTION "Off Dehumidification Temperature"
                    DEFVAL { 0 }
                    ::= { integerObjects 460 }

        -- 1.3.6.1.4.1.9839.2.1.3.461
        s_thresh1 OBJECT-TYPE
                    SYNTAX Integer32 (0..999)
                    UNITS "N/A"
                    MAX-ACCESS read-write
                    STATUS current
                    DESCRIPTION "Compressor 1 Position (Cooling)"
                    DEFVAL { 0 }
                    ::= { integerObjects 461 }

        -- 1.3.6.1.4.1.9839.2.1.3.462
        s_differ1 OBJECT-TYPE
                    SYNTAX Integer32 (0..999)
                    UNITS "N/A"
                    MAX-ACCESS read-write
                    STATUS current
                    DESCRIPTION "Compressor 1 Hysteresis (Cooling)"
                    DEFVAL { 0 }
                    ::= { integerObjects 462 }

        -- 1.3.6.1.4.1.9839.2.1.3.463
        p_res1 OBJECT-TYPE
                    SYNTAX Integer32 (0..9999)
                    UNITS "N/A"
                    MAX-ACCESS read-write
                    STATUS current
                    DESCRIPTION "Heater 1 Position (Heating)"
                    DEFVAL { 0 }
                    ::= { integerObjects 463 }

        -- 1.3.6.1.4.1.9839.2.1.3.464
        s_thresh2 OBJECT-TYPE
                    SYNTAX Integer32 (0..999)
                    UNITS "N/A"
                    MAX-ACCESS read-write
                    STATUS current
                    DESCRIPTION "Compressor 2 Position (Cooling)"
                    DEFVAL { 0 }
                    ::= { integerObjects 464 }

        -- 1.3.6.1.4.1.9839.2.1.3.465
        p_res1_dehum OBJECT-TYPE
                    SYNTAX Integer32 (0..9999)
                    UNITS "N/A"
                    MAX-ACCESS read-write
                    STATUS current
                    DESCRIPTION "Heater 1 Hysteresis (Dehumidification)"
                    DEFVAL { 0 }
                    ::= { integerObjects 465 }

        -- 1.3.6.1.4.1.9839.2.1.3.466
        s_differ2 OBJECT-TYPE
                    SYNTAX Integer32 (0..999)
                    UNITS "N/A"
                    MAX-ACCESS read-write
                    STATUS current
                    DESCRIPTION "Compressor 2 Hysteresis (Cooling)"
                    DEFVAL { 0 }
                    ::= { integerObjects 466 }

        -- 1.3.6.1.4.1.9839.2.1.3.467
        h_res1 OBJECT-TYPE
                    SYNTAX Integer32 (0..9999)
                    UNITS "N/A"
                    MAX-ACCESS read-write
                    STATUS current
                    DESCRIPTION "Heater 1 Position (Heating)"
                    DEFVAL { 0 }
                    ::= { integerObjects 467 }

        -- 1.3.6.1.4.1.9839.2.1.3.468
        h_res1_dehum OBJECT-TYPE
                    SYNTAX Integer32 (0..9999)
                    UNITS "N/A"
                    MAX-ACCESS read-write
                    STATUS current
                    DESCRIPTION "Heater 1 Hysteresis (Dehumidification)"
                    DEFVAL { 0 }
                    ::= { integerObjects 468 }

        -- 1.3.6.1.4.1.9839.2.1.3.469
        p_res2 OBJECT-TYPE
                    SYNTAX Integer32 (0..9999)
                    UNITS "N/A"
                    MAX-ACCESS read-write
                    STATUS current
                    DESCRIPTION "Heater 2 Position (Heating)"
                    DEFVAL { 0 }
                    ::= { integerObjects 469 }

        -- 1.3.6.1.4.1.9839.2.1.3.470
        p_res2_dehum OBJECT-TYPE
                    SYNTAX Integer32 (0..9999)
                    UNITS "N/A"
                    MAX-ACCESS read-write
                    STATUS current
                    DESCRIPTION "Heater 2 Hysteresis (Dehumidification)"
                    DEFVAL { 0 }
                    ::= { integerObjects 470 }

        -- 1.3.6.1.4.1.9839.2.1.3.471
        h_res2 OBJECT-TYPE
                    SYNTAX Integer32 (0..9999)
                    UNITS "N/A"
                    MAX-ACCESS read-write
                    STATUS current
                    DESCRIPTION "Heater 2 Position (Heating)"
                    DEFVAL { 0 }
                    ::= { integerObjects 471 }

        -- 1.3.6.1.4.1.9839.2.1.3.472
        h_res2_dehum OBJECT-TYPE
                    SYNTAX Integer32 (0..9999)
                    UNITS "N/A"
                    MAX-ACCESS read-write
                    STATUS current
                    DESCRIPTION "Heater 2 Hysteresis (Dehumidification)"
                    DEFVAL { 0 }
                    ::= { integerObjects 472 }

        -- 1.3.6.1.4.1.9839.2.1.3.473
        p_res3 OBJECT-TYPE
                    SYNTAX Integer32 (0..9999)
                    UNITS "N/A"
                    MAX-ACCESS read-write
                    STATUS current
                    DESCRIPTION "Heater 3 Position (Heating)"
                    DEFVAL { 0 }
                    ::= { integerObjects 473 }

        -- 1.3.6.1.4.1.9839.2.1.3.474
        p_res3_dehum OBJECT-TYPE
                    SYNTAX Integer32 (0..9999)
                    UNITS "N/A"
                    MAX-ACCESS read-write
                    STATUS current
                    DESCRIPTION "Heater 3 Hysteresis (Dehumidification)"
                    DEFVAL { 0 }
                    ::= { integerObjects 474 }

        -- 1.3.6.1.4.1.9839.2.1.3.475
        h_res3 OBJECT-TYPE
                    SYNTAX Integer32 (0..9999)
                    UNITS "N/A"
                    MAX-ACCESS read-write
                    STATUS current
                    DESCRIPTION "Heater 3 Position (Heating)"
                    DEFVAL { 0 }
                    ::= { integerObjects 475 }

        -- 1.3.6.1.4.1.9839.2.1.3.476
        h_res3_dehum OBJECT-TYPE
                    SYNTAX Integer32 (0..9999)
                    UNITS "N/A"
                    MAX-ACCESS read-write
                    STATUS current
                    DESCRIPTION "Heater 3 Hysteresis (Dehumidification)"
                    DEFVAL { 0 }
                    ::= { integerObjects 476 }

        -- 1.3.6.1.4.1.9839.2.1.3.477
        comp_min_on OBJECT-TYPE
                    SYNTAX Integer32 (1..600)
                    UNITS "N/A"
                    MAX-ACCESS read-write
                    STATUS current
                    DESCRIPTION "Compressor Minimum On Time"
                    DEFVAL { 1 }
                    ::= { integerObjects 477 }

        -- 1.3.6.1.4.1.9839.2.1.3.478
        comp_min_off OBJECT-TYPE
                    SYNTAX Integer32 (1..600)
                    UNITS "N/A"
                    MAX-ACCESS read-write
                    STATUS current
                    DESCRIPTION "Compressor Minimum Off Time"
                    DEFVAL { 1 }
                    ::= { integerObjects 478 }

        -- 1.3.6.1.4.1.9839.2.1.3.479
        comp_min_betw OBJECT-TYPE
                    SYNTAX Integer32 (1..180)
                    UNITS "N/A"
                    MAX-ACCESS read-write
                    STATUS current
                    DESCRIPTION "Time Between Different Compressor"
                    DEFVAL { 1 }
                    ::= { integerObjects 479 }

        -- 1.3.6.1.4.1.9839.2.1.3.480
        comp_min_same OBJECT-TYPE
                    SYNTAX Integer32 (1..900)
                    UNITS "N/A"
                    MAX-ACCESS read-write
                    STATUS current
                    DESCRIPTION "Time Between Same Compressor"
                    DEFVAL { 1 }
                    ::= { integerObjects 480 }

        -- 1.3.6.1.4.1.9839.2.1.3.481
        time_runn_d3p OBJECT-TYPE
                    SYNTAX Integer32 (0..9999)
                    UNITS "N/A"
                    MAX-ACCESS read-write
                    STATUS current
                    DESCRIPTION "3 Points Valve Opening Time"
                    DEFVAL { 0 }
                    ::= { integerObjects 481 }

        -- 1.3.6.1.4.1.9839.2.1.3.482
        sys_delay_on OBJECT-TYPE
                    SYNTAX Integer32 (5..99)
                    UNITS "N/A"
                    MAX-ACCESS read-write
                    STATUS current
                    DESCRIPTION "System Delay On Time"
                    DEFVAL { 5 }
                    ::= { integerObjects 482 }

        -- 1.3.6.1.4.1.9839.2.1.3.483
        vfd_run_del OBJECT-TYPE
                    SYNTAX Integer32 (0..999)
                    UNITS "N/A"
                    MAX-ACCESS read-write
                    STATUS current
                    DESCRIPTION "N/A"
                    DEFVAL { 0 }
                    ::= { integerObjects 483 }

        -- 1.3.6.1.4.1.9839.2.1.3.484
        del_smoke_al OBJECT-TYPE
                    SYNTAX Integer32 (0..999)
                    UNITS "N/A"
                    MAX-ACCESS read-write
                    STATUS current
                    DESCRIPTION "Smoke Detector Alarm Delay Time"
                    DEFVAL { 3 }
                    ::= { integerObjects 484 }

        -- 1.3.6.1.4.1.9839.2.1.3.485
        vfd_control_type OBJECT-TYPE
                    SYNTAX Integer32 (0..2)
                    UNITS "N/A"
                    MAX-ACCESS read-write
                    STATUS current
                    DESCRIPTION "VFD Control Type (0: None, 1: CHW Proportional, 2: Delta Temp)"
                    DEFVAL { 0 }
                    ::= { integerObjects 485 }

        -- 1.3.6.1.4.1.9839.2.1.3.486
        lp_changes OBJECT-TYPE
                    SYNTAX Integer32 (0..50)
                    UNITS "N/A"
                    MAX-ACCESS read-write
                    STATUS current
                    DESCRIPTION "Compressor Short Cycle Alarm (Number of Changes)"
                    DEFVAL { 10 }
                    ::= { integerObjects 486 }

        -- 1.3.6.1.4.1.9839.2.1.3.487
        lp_al_del OBJECT-TYPE
                    SYNTAX Integer32 (0..60)
                    UNITS "N/A"
                    MAX-ACCESS read-write
                    STATUS current
                    DESCRIPTION "Compressor Low Pressure Alarm Delay"
                    DEFVAL { 5 }
                    ::= { integerObjects 487 }

        -- 1.3.6.1.4.1.9839.2.1.3.488
        time_within OBJECT-TYPE
                    SYNTAX Integer32 (0..30)
                    UNITS "N/A"
                    MAX-ACCESS read-write
                    STATUS current
                    DESCRIPTION "Compressor Short Cycle Alarm (Period)"
                    DEFVAL { 10 }
                    ::= { integerObjects 488 }

        -- 1.3.6.1.4.1.9839.2.1.3.489
        auto_dx_del_off OBJECT-TYPE
                    SYNTAX Integer32 (0..999)
                    UNITS "N/A"
                    MAX-ACCESS read-write
                    STATUS current
                    DESCRIPTION "Auto Changeover Delay (DX -> CHW)"
                    DEFVAL { 0 }
                    ::= { integerObjects 489 }

        -- 1.3.6.1.4.1.9839.2.1.3.490
        auto_chw_del_off OBJECT-TYPE
                    SYNTAX Integer32 (0..999)
                    UNITS "N/A"
                    MAX-ACCESS read-write
                    STATUS current
                    DESCRIPTION "Auto Changeover Delay (CHW -> DX)"
                    DEFVAL { 0 }
                    ::= { integerObjects 490 }

        -- 1.3.6.1.4.1.9839.2.1.3.491
        vfd_trip_del OBJECT-TYPE
                    SYNTAX Integer32 (0..999)
                    UNITS "N/A"
                    MAX-ACCESS read-write
                    STATUS current
                    DESCRIPTION "Blower VFD Alarm (Trip)"
                    DEFVAL { 0 }
                    ::= { integerObjects 491 }

        -- 1.3.6.1.4.1.9839.2.1.3.492
        rh_vlv_low_sp OBJECT-TYPE
                    SYNTAX Integer32 (-32768..32767)
                    UNITS "N/A"
                    MAX-ACCESS read-write
                    STATUS current
                    DESCRIPTION "Minimum Hotgas Valve Modulating Setpoint"
                    DEFVAL { 0 }
                    ::= { integerObjects 492 }

        -- 1.3.6.1.4.1.9839.2.1.3.493
        rh_vlv_high_sp OBJECT-TYPE
                    SYNTAX Integer32 (-32768..32767)
                    UNITS "N/A"
                    MAX-ACCESS read-write
                    STATUS current
                    DESCRIPTION "Maximum Hotgas Valve Modulating Setpoint"
                    DEFVAL { 0 }
                    ::= { integerObjects 493 }

        -- 1.3.6.1.4.1.9839.2.1.3.494
        bms_address OBJECT-TYPE
                    SYNTAX Integer32 (1..207)
                    UNITS "N/A"
                    MAX-ACCESS read-write
                    STATUS current
                    DESCRIPTION "Address of the controller in a supervisory system network n.1"
                    DEFVAL { 1 }
                    ::= { integerObjects 494 }

        -- 1.3.6.1.4.1.9839.2.1.3.495
        rit_al_ht_in OBJECT-TYPE
                    SYNTAX Integer32 (1..60)
                    UNITS "N/A"
                    MAX-ACCESS read-write
                    STATUS current
                    DESCRIPTION "Temperature Alarm Delay"
                    DEFVAL { 1 }
                    ::= { integerObjects 495 }

        -- 1.3.6.1.4.1.9839.2.1.3.496
        humid_lh_del OBJECT-TYPE
                    SYNTAX Integer32 (1..60)
                    UNITS "N/A"
                    MAX-ACCESS read-write
                    STATUS current
                    DESCRIPTION "Humidity Alarm Delay"
                    DEFVAL { 1 }
                    ::= { integerObjects 496 }

        -- 1.3.6.1.4.1.9839.2.1.3.497
        prop_temp_neg_max_count OBJECT-TYPE
                    SYNTAX Integer32 (-32768..32767)
                    UNITS "N/A"
                    MAX-ACCESS read-write
                    STATUS current
                    DESCRIPTION "Heater Maximum Counter"
                    DEFVAL { 0 }
                    ::= { integerObjects 497 }

        -- 1.3.6.1.4.1.9839.2.1.3.498
        protocol_type OBJECT-TYPE
                    SYNTAX Integer32 (0..4)
                    UNITS "N/A"
                    MAX-ACCESS read-write
                    STATUS current
                    DESCRIPTION "Protocol"
                    DEFVAL { 0 }
                    ::= { integerObjects 498 }

        -- 1.3.6.1.4.1.9839.2.1.3.499
        baud_rate OBJECT-TYPE
                    SYNTAX Integer32 (0..4)
                    UNITS "N/A"
                    MAX-ACCESS read-write
                    STATUS current
                    DESCRIPTION "Baud Rate"
                    DEFVAL { 0 }
                    ::= { integerObjects 499 }

        -- 1.3.6.1.4.1.9839.2.1.3.500
        is_start_delay OBJECT-TYPE
                    SYNTAX Integer32 (0..999)
                    UNITS "N/A"
                    MAX-ACCESS read-write
                    STATUS current
                    DESCRIPTION "Indoor Pressure Differential Switch Delay (Startup)"
                    DEFVAL { 0 }
                    ::= { integerObjects 500 }

        -- 1.3.6.1.4.1.9839.2.1.3.501
        is_run_delay OBJECT-TYPE
                    SYNTAX Integer32 (0..999)
                    UNITS "N/A"
                    MAX-ACCESS read-write
                    STATUS current
                    DESCRIPTION "Indoor Pressure Differential Switch Delay (Running)"
                    DEFVAL { 0 }
                    ::= { integerObjects 501 }

        -- 1.3.6.1.4.1.9839.2.1.3.502
        fs_start_delay OBJECT-TYPE
                    SYNTAX Integer32 (0..999)
                    UNITS "N/A"
                    MAX-ACCESS read-write
                    STATUS current
                    DESCRIPTION "Water Flow Switch Delay (Startup)"
                    DEFVAL { 0 }
                    ::= { integerObjects 502 }

        -- 1.3.6.1.4.1.9839.2.1.3.503
        fs_run_delay OBJECT-TYPE
                    SYNTAX Integer32 (0..999)
                    UNITS "N/A"
                    MAX-ACCESS read-write
                    STATUS current
                    DESCRIPTION "Water Flow Switch Delay (Running)"
                    DEFVAL { 0 }
                    ::= { integerObjects 503 }

        -- 1.3.6.1.4.1.9839.2.1.3.507
        rm_temp_ch OBJECT-TYPE
                    SYNTAX Integer32 (1..10)
                    UNITS "N/A"
                    MAX-ACCESS read-write
                    STATUS current
                    DESCRIPTION "AI Config - Room Temp"
                    DEFVAL { 1 }
                    ::= { integerObjects 507 }

        -- 1.3.6.1.4.1.9839.2.1.3.508
        rm_humid_ch OBJECT-TYPE
                    SYNTAX Integer32 (1..10)
                    UNITS "N/A"
                    MAX-ACCESS read-write
                    STATUS current
                    DESCRIPTION "AI Config - Room Humid"
                    DEFVAL { 1 }
                    ::= { integerObjects 508 }

        -- 1.3.6.1.4.1.9839.2.1.3.509
        supply_air_ch OBJECT-TYPE
                    SYNTAX Integer32 (1..10)
                    UNITS "N/A"
                    MAX-ACCESS read-write
                    STATUS current
                    DESCRIPTION "Ai Config - Supply Air Temp"
                    DEFVAL { 1 }
                    ::= { integerObjects 509 }

        -- 1.3.6.1.4.1.9839.2.1.3.510
        humid_conduct_ch OBJECT-TYPE
                    SYNTAX Integer32 (1..10)
                    UNITS "N/A"
                    MAX-ACCESS read-write
                    STATUS current
                    DESCRIPTION "AI Config - Humidifier Conductivity"
                    DEFVAL { 1 }
                    ::= { integerObjects 510 }

        -- 1.3.6.1.4.1.9839.2.1.3.511
        humid_current_ch OBJECT-TYPE
                    SYNTAX Integer32 (1..10)
                    UNITS "N/A"
                    MAX-ACCESS read-write
                    STATUS current
                    DESCRIPTION "AI Config - Humidifier Current"
                    DEFVAL { 1 }
                    ::= { integerObjects 511 }

        -- 1.3.6.1.4.1.9839.2.1.3.515
        ch_evap_fan_ol1 OBJECT-TYPE
                    SYNTAX Integer32 (1..14)
                    UNITS "N/A"
                    MAX-ACCESS read-write
                    STATUS current
                    DESCRIPTION "DI Config for Blower Fan 1 Overload Status"
                    DEFVAL { 1 }
                    ::= { integerObjects 515 }

        -- 1.3.6.1.4.1.9839.2.1.3.516
        ch_air_flow OBJECT-TYPE
                    SYNTAX Integer32 (1..14)
                    UNITS "N/A"
                    MAX-ACCESS read-write
                    STATUS current
                    DESCRIPTION "DI Config for Air Flow Switch Status"
                    DEFVAL { 1 }
                    ::= { integerObjects 516 }

        -- 1.3.6.1.4.1.9839.2.1.3.517
        ch_air_filter OBJECT-TYPE
                    SYNTAX Integer32 (1..14)
                    UNITS "N/A"
                    MAX-ACCESS read-write
                    STATUS current
                    DESCRIPTION "DI Config for Filter Diff. Pressure Switch Status"
                    DEFVAL { 1 }
                    ::= { integerObjects 517 }

        -- 1.3.6.1.4.1.9839.2.1.3.518
        ch_low_press1 OBJECT-TYPE
                    SYNTAX Integer32 (1..14)
                    UNITS "N/A"
                    MAX-ACCESS read-write
                    STATUS current
                    DESCRIPTION "AI Config for Comp 1 Low Pressure Switch Status"
                    DEFVAL { 1 }
                    ::= { integerObjects 518 }

        -- 1.3.6.1.4.1.9839.2.1.3.519
        ch_high_press1 OBJECT-TYPE
                    SYNTAX Integer32 (1..14)
                    UNITS "N/A"
                    MAX-ACCESS read-write
                    STATUS current
                    DESCRIPTION "AI Config for Comp 1 High Pressure Switch Status"
                    DEFVAL { 1 }
                    ::= { integerObjects 519 }

        -- 1.3.6.1.4.1.9839.2.1.3.520
        ch_cust_alr OBJECT-TYPE
                    SYNTAX Integer32 (1..14)
                    UNITS "N/A"
                    MAX-ACCESS read-write
                    STATUS current
                    DESCRIPTION "DI Config for Customer Alarm Interlock Status"
                    DEFVAL { 1 }
                    ::= { integerObjects 520 }

        -- 1.3.6.1.4.1.9839.2.1.3.521
        ch_rem_on_off OBJECT-TYPE
                    SYNTAX Integer32 (1..14)
                    UNITS "N/A"
                    MAX-ACCESS read-write
                    STATUS current
                    DESCRIPTION "DI Config for Remote Start/Stop Input Status"
                    DEFVAL { 1 }
                    ::= { integerObjects 521 }

        -- 1.3.6.1.4.1.9839.2.1.3.522
        ch_water_flood OBJECT-TYPE
                    SYNTAX Integer32 (1..14)
                    UNITS "N/A"
                    MAX-ACCESS read-write
                    STATUS current
                    DESCRIPTION "DI Config for Under Floor Water Detector Status"
                    DEFVAL { 1 }
                    ::= { integerObjects 522 }

        -- 1.3.6.1.4.1.9839.2.1.3.523
        ch_low_press2 OBJECT-TYPE
                    SYNTAX Integer32 (1..14)
                    UNITS "N/A"
                    MAX-ACCESS read-write
                    STATUS current
                    DESCRIPTION "DI Config for Comp 2 Low Pressure Switch Status"
                    DEFVAL { 1 }
                    ::= { integerObjects 523 }

        -- 1.3.6.1.4.1.9839.2.1.3.524
        ch_high_press2 OBJECT-TYPE
                    SYNTAX Integer32 (1..14)
                    UNITS "N/A"
                    MAX-ACCESS read-write
                    STATUS current
                    DESCRIPTION "DI Config for Comp 2 High Pressure Switch Status"
                    DEFVAL { 1 }
                    ::= { integerObjects 524 }

        -- 1.3.6.1.4.1.9839.2.1.3.525
        ch_water_level OBJECT-TYPE
                    SYNTAX Integer32 (1..14)
                    UNITS "N/A"
                    MAX-ACCESS read-write
                    STATUS current
                    DESCRIPTION "DI Config for Humidifier Water Level"
                    DEFVAL { 1 }
                    ::= { integerObjects 525 }

        -- 1.3.6.1.4.1.9839.2.1.3.526
        ch_smoke_detector OBJECT-TYPE
                    SYNTAX Integer32 (1..14)
                    UNITS "N/A"
                    MAX-ACCESS read-write
                    STATUS current
                    DESCRIPTION "Di Config for Smoke Detector Status"
                    DEFVAL { 1 }
                    ::= { integerObjects 526 }

        -- 1.3.6.1.4.1.9839.2.1.3.527
        ch_chw_thermostat OBJECT-TYPE
                    SYNTAX Integer32 (1..14)
                    UNITS "N/A"
                    MAX-ACCESS read-write
                    STATUS current
                    DESCRIPTION "DI Config for CHW Thermostat Status"
                    DEFVAL { 1 }
                    ::= { integerObjects 527 }

        -- 1.3.6.1.4.1.9839.2.1.3.528
        ch_flow_sw OBJECT-TYPE
                    SYNTAX Integer32 (1..14)
                    UNITS "N/A"
                    MAX-ACCESS read-write
                    STATUS current
                    DESCRIPTION "DI Config for CHW Flow Switch Status"
                    DEFVAL { 1 }
                    ::= { integerObjects 528 }

        -- 1.3.6.1.4.1.9839.2.1.3.529
        ch_compressor1 OBJECT-TYPE
                    SYNTAX Integer32 (1..13)
                    UNITS "N/A"
                    MAX-ACCESS read-write
                    STATUS current
                    DESCRIPTION "DO Config for Compressor 1 Output"
                    DEFVAL { 1 }
                    ::= { integerObjects 529 }

        -- 1.3.6.1.4.1.9839.2.1.3.530
        ch_comp1_liq OBJECT-TYPE
                    SYNTAX Integer32 (1..13)
                    UNITS "N/A"
                    MAX-ACCESS read-write
                    STATUS current
                    DESCRIPTION "DO Config for Comp 1 Liquid Line Sol Vlv"
                    DEFVAL { 1 }
                    ::= { integerObjects 530 }

        -- 1.3.6.1.4.1.9839.2.1.3.531
        ch_buzzer OBJECT-TYPE
                    SYNTAX Integer32 (1..13)
                    UNITS "N/A"
                    MAX-ACCESS read-write
                    STATUS current
                    DESCRIPTION "DO Config for Buzzer"
                    DEFVAL { 1 }
                    ::= { integerObjects 531 }

        -- 1.3.6.1.4.1.9839.2.1.3.532
        ch_heater1 OBJECT-TYPE
                    SYNTAX Integer32 (1..13)
                    UNITS "N/A"
                    MAX-ACCESS read-write
                    STATUS current
                    DESCRIPTION "DO Config for Heater 1 Output"
                    DEFVAL { 1 }
                    ::= { integerObjects 532 }

        -- 1.3.6.1.4.1.9839.2.1.3.533
        ch_heater2 OBJECT-TYPE
                    SYNTAX Integer32 (1..13)
                    UNITS "N/A"
                    MAX-ACCESS read-write
                    STATUS current
                    DESCRIPTION "DO Config for Heater 2&3 Output"
                    DEFVAL { 1 }
                    ::= { integerObjects 533 }

        -- 1.3.6.1.4.1.9839.2.1.3.534
        ch_humidifier_output OBJECT-TYPE
                    SYNTAX Integer32 (1..13)
                    UNITS "N/A"
                    MAX-ACCESS read-write
                    STATUS current
                    DESCRIPTION "DO Config for Humidifier Output"
                    DEFVAL { 1 }
                    ::= { integerObjects 534 }

        -- 1.3.6.1.4.1.9839.2.1.3.535
        ch_evap_fan1a OBJECT-TYPE
                    SYNTAX Integer32 (1..13)
                    UNITS "N/A"
                    MAX-ACCESS read-write
                    STATUS current
                    DESCRIPTION "DO Config for Blower Fan 1 Output"
                    DEFVAL { 1 }
                    ::= { integerObjects 535 }

        -- 1.3.6.1.4.1.9839.2.1.3.536
        ch_global_alarm OBJECT-TYPE
                    SYNTAX Integer32 (1..13)
                    UNITS "N/A"
                    MAX-ACCESS read-write
                    STATUS current
                    DESCRIPTION "DO Config for Global Alarm"
                    DEFVAL { 1 }
                    ::= { integerObjects 536 }

        -- 1.3.6.1.4.1.9839.2.1.3.537
        ch_compressor2 OBJECT-TYPE
                    SYNTAX Integer32 (1..13)
                    UNITS "N/A"
                    MAX-ACCESS read-write
                    STATUS current
                    DESCRIPTION "DO Config for Compressor 2 Output"
                    DEFVAL { 1 }
                    ::= { integerObjects 537 }

        -- 1.3.6.1.4.1.9839.2.1.3.538
        ch_comp2_liq OBJECT-TYPE
                    SYNTAX Integer32 (1..13)
                    UNITS "N/A"
                    MAX-ACCESS read-write
                    STATUS current
                    DESCRIPTION "DO Config for Comp 2 Liquid Line Sol Vlv"
                    DEFVAL { 1 }
                    ::= { integerObjects 538 }

        -- 1.3.6.1.4.1.9839.2.1.3.539
        ch_fill1 OBJECT-TYPE
                    SYNTAX Integer32 (1..13)
                    UNITS "N/A"
                    MAX-ACCESS read-write
                    STATUS current
                    DESCRIPTION "DO Config for Humdifier Fill Sol Vlv"
                    DEFVAL { 1 }
                    ::= { integerObjects 539 }

        -- 1.3.6.1.4.1.9839.2.1.3.540
        ch_drain1 OBJECT-TYPE
                    SYNTAX Integer32 (1..13)
                    UNITS "N/A"
                    MAX-ACCESS read-write
                    STATUS current
                    DESCRIPTION "DO Config for Humidifier Drain Vlv"
                    DEFVAL { 1 }
                    ::= { integerObjects 540 }

        -- 1.3.6.1.4.1.9839.2.1.3.541
        ch_spare_do OBJECT-TYPE
                    SYNTAX Integer32 (1..13)
                    UNITS "N/A"
                    MAX-ACCESS read-write
                    STATUS current
                    DESCRIPTION "DO Config for Spare DO"
                    DEFVAL { 1 }
                    ::= { integerObjects 541 }

        -- 1.3.6.1.4.1.9839.2.1.3.542
        ch_chw_aout OBJECT-TYPE
                    SYNTAX Integer32 (1..4)
                    UNITS "N/A"
                    MAX-ACCESS read-write
                    STATUS current
                    DESCRIPTION "AO COnfig for Cooling Valve Output"
                    DEFVAL { 1 }
                    ::= { integerObjects 542 }

        -- 1.3.6.1.4.1.9839.2.1.3.543
        ch_blower_ao_out OBJECT-TYPE
                    SYNTAX Integer32 (1..4)
                    UNITS "N/A"
                    MAX-ACCESS read-write
                    STATUS current
                    DESCRIPTION "AO Config for Blower VFD / EC Fan"
                    DEFVAL { 1 }
                    ::= { integerObjects 543 }

        -- 1.3.6.1.4.1.9839.2.1.3.544
        ch_c1_reheat_vlv_out OBJECT-TYPE
                    SYNTAX Integer32 (1..4)
                    UNITS "N/A"
                    MAX-ACCESS read-write
                    STATUS current
                    DESCRIPTION "AO Config for HGRV 1"
                    DEFVAL { 1 }
                    ::= { integerObjects 544 }

        -- 1.3.6.1.4.1.9839.2.1.3.545
        ch_c2_reheat_vlv_out OBJECT-TYPE
                    SYNTAX Integer32 (1..4)
                    UNITS "N/A"
                    MAX-ACCESS read-write
                    STATUS current
                    DESCRIPTION "AO Config for HGRV 2"
                    DEFVAL { 1 }
                    ::= { integerObjects 545 }

        -- 1.3.6.1.4.1.9839.2.1.3.546
        lp_start_delay OBJECT-TYPE
                    SYNTAX Integer32 (0..600)
                    UNITS "N/A"
                    MAX-ACCESS read-write
                    STATUS current
                    DESCRIPTION "N/A"
                    DEFVAL { 0 }
                    ::= { integerObjects 546 }

        -- 1.3.6.1.4.1.9839.2.1.3.547
        lp_run_delay OBJECT-TYPE
                    SYNTAX Integer32 (0..300)
                    UNITS "N/A"
                    MAX-ACCESS read-write
                    STATUS current
                    DESCRIPTION "N/A"
                    DEFVAL { 0 }
                    ::= { integerObjects 547 }

        -- 1.3.6.1.4.1.9839.2.1.3.548
        protocol_type_bms2 OBJECT-TYPE
                    SYNTAX Integer32 (0..1)
                    UNITS "N/A"
                    MAX-ACCESS read-write
                    STATUS current
                    DESCRIPTION "Protocol (BMS 2)"
                    DEFVAL { 0 }
                    ::= { integerObjects 548 }

        -- 1.3.6.1.4.1.9839.2.1.3.549
        baud_rate_bms2 OBJECT-TYPE
                    SYNTAX Integer32 (0..4)
                    UNITS "N/A"
                    MAX-ACCESS read-write
                    STATUS current
                    DESCRIPTION "Baud Rate (BMS 2)"
                    DEFVAL { 0 }
                    ::= { integerObjects 549 }

        -- 1.3.6.1.4.1.9839.2.1.3.550
        bms2_address OBJECT-TYPE
                    SYNTAX Integer32 (1..207)
                    UNITS "N/A"
                    MAX-ACCESS read-write
                    STATUS current
                    DESCRIPTION "Address of the controller in a supervisory system network n.2"
                    DEFVAL { 1 }
                    ::= { integerObjects 550 }

        -- 1.3.6.1.4.1.9839.2.1.3.551
        new_pass_ass OBJECT-TYPE
                    SYNTAX Integer32 (0..9999)
                    UNITS "N/A"
                    MAX-ACCESS read-write
                    STATUS current
                    DESCRIPTION "N/A"
                    DEFVAL { 0 }
                    ::= { integerObjects 551 }

        -- 1.3.6.1.4.1.9839.2.1.3.552
        new_pass_ass_h OBJECT-TYPE
                    SYNTAX Integer32 (0..9999)
                    UNITS "N/A"
                    MAX-ACCESS read-write
                    STATUS current
                    DESCRIPTION "N/A"
                    DEFVAL { 0 }
                    ::= { integerObjects 552 }

        -- 1.3.6.1.4.1.9839.2.1.3.553
        new_pass_ut OBJECT-TYPE
                    SYNTAX Integer32 (0..9999)
                    UNITS "N/A"
                    MAX-ACCESS read-write
                    STATUS current
                    DESCRIPTION "N/A"
                    DEFVAL { 0 }
                    ::= { integerObjects 553 }

        -- 1.3.6.1.4.1.9839.2.1.3.554
        new_pass_ut_h OBJECT-TYPE
                    SYNTAX Integer32 (0..9999)
                    UNITS "N/A"
                    MAX-ACCESS read-write
                    STATUS current
                    DESCRIPTION "N/A"
                    DEFVAL { 0 }
                    ::= { integerObjects 554 }

        -- 1.3.6.1.4.1.9839.2.1.3.555
        new_pass_cos OBJECT-TYPE
                    SYNTAX Integer32 (0..9999)
                    UNITS "N/A"
                    MAX-ACCESS read-write
                    STATUS current
                    DESCRIPTION "N/A"
                    DEFVAL { 0 }
                    ::= { integerObjects 555 }

        -- 1.3.6.1.4.1.9839.2.1.3.556
        new_pass_cos_h OBJECT-TYPE
                    SYNTAX Integer32 (0..9999)
                    UNITS "N/A"
                    MAX-ACCESS read-write
                    STATUS current
                    DESCRIPTION "N/A"
                    DEFVAL { 0 }
                    ::= { integerObjects 556 }

        -- 1.3.6.1.4.1.9839.2.1.3.557
        admin_pass OBJECT-TYPE
                    SYNTAX Integer32 (0..9999)
                    UNITS "N/A"
                    MAX-ACCESS read-write
                    STATUS current
                    DESCRIPTION "N/A"
                    DEFVAL { 0 }
                    ::= { integerObjects 557 }

        -- 1.3.6.1.4.1.9839.2.1.3.558
        admin_pass_h OBJECT-TYPE
                    SYNTAX Integer32 (0..9999)
                    UNITS "N/A"
                    MAX-ACCESS read-write
                    STATUS current
                    DESCRIPTION "N/A"
                    DEFVAL { 0 }
                    ::= { integerObjects 558 }

        -- 1.3.6.1.4.1.9839.2.1.3.559
        number OBJECT-TYPE
                    SYNTAX Integer32 (0..9)
                    UNITS "N/A"
                    MAX-ACCESS read-write
                    STATUS current
                    DESCRIPTION "N/A"
                    DEFVAL { 0 }
                    ::= { integerObjects 559 }

        -- 1.3.6.1.4.1.9839.2.1.3.560
        datalog_time_interval OBJECT-TYPE
                    SYNTAX Integer32 (0..999)
                    UNITS "N/A"
                    MAX-ACCESS read-write
                    STATUS current
                    DESCRIPTION "N/A"
                    DEFVAL { 0 }
                    ::= { integerObjects 560 }


	
	END

--
-- CAREL-flccu1314gmar.MIB
--
