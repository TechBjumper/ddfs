-- *****************************************************************
-- BJUMPER.mib  Nexcon Telecomunicaciones
--                  Estructura de la MIB
--
-- Julio 2014
--
-- Copyright (c) 2013 by Nexcon Telecomunicaciones
-- All rights reserved.
-- 
-- *****************************************************************

NEXCON-BJUMPER-MIB DEFINITIONS ::= BEGIN


	IMPORTS
		MODULE-IDENTITY,
		OBJECT-IDENTITY,
		enterprises
			FROM SNMPv2-SMI;

nexcon MODULE-IDENTITY        
    LAST-UPDATED "9811240100Z"
	ORGANIZATION "Nexcon Telecomunicaciones"
	CONTACT-INFO
		"	Nexcon Telecomunicaciones
			Departamento de I+D
			Postal: Camarena 177 Local 1
			28047 Madrid
			SPAIN
		   	Tel: +34 915098994
			E-mail: mail@nexcon.es"
	DESCRIPTION
		"Estructura de MIB para NEXCON Telecomunicaciones enterprise."
	::= { enterprises 25318 }	-- assigned by IANA


SNMPConverter OBJECT-IDENTITY
	STATUS	current
	DESCRIPTION
		"
		Asociada a los equipos de Nexcon Telecomunicaciones convertidores SNMP
		"
	::= { nexcon 3 }

--
--	Equipo BJUMPER. Convertidor SNMP de MODbus
--

    OCTOPUS OBJECT IDENTIFIER 		::= {SNMPConverter 4}

--	--------------------------
--	LISTADO DE PARAMETROS ----
--	--------------------------

-- ** Parametros sólo lectura ***
	 EntradasDigitales 			OBJECT IDENTIFIER 	::= {OCTOPUS 1} 
     EntradasAnalogicas 		OBJECT IDENTIFIER 	::= {OCTOPUS 2} 
     SalidasDigitales 			OBJECT IDENTIFIER 	::= {OCTOPUS 3}
	 Dev_BACnet 				OBJECT IDENTIFIER  	::=	{OCTOPUS 4}
	 UPS_Chloride				OBJECT IDENTIFIER  	::=	{Dev_BACnet 1}
	 Network_UPS				OBJECT IDENTIFIER  	::=	{UPS_Chloride 1}
	 Object_UPS					OBJECT IDENTIFIER  	::=	{UPS_Chloride 2}
	 Cuadro						OBJECT IDENTIFIER  	::=	{Dev_BACnet 2}
	 Network_Cuadro				OBJECT IDENTIFIER  	::=	{Cuadro 1}
	 Object_Cuadro				OBJECT IDENTIFIER  	::=	{Cuadro 2}	 
	 CRAC_FC					OBJECT IDENTIFIER  	::=	{Dev_BACnet 3}
	 Network_CRAC_FC			OBJECT IDENTIFIER  	::=	{CRAC_FC 1}
	 Object_CRAC_FC				OBJECT IDENTIFIER  	::=	{CRAC_FC 2}	 
	 PASARELA					OBJECT IDENTIFIER  	::=	{Dev_BACnet 4}
	 Network_PASARELA			OBJECT IDENTIFIER  	::=	{PASARELA 1}
     Dev_SNMP 					OBJECT IDENTIFIER 	::= {OCTOPUS 5} 
	 UPS_EATON					OBJECT IDENTIFIER  	::=	{Dev_SNMP 1}
	 Network_UPS_EATON			OBJECT IDENTIFIER  	::=	{UPS_EATON 1}
	 Object_UPS_EATON			OBJECT IDENTIFIER  	::=	{UPS_EATON 2}	 
     
-- ** Parametros de configuración de red ***
     Network OBJECT IDENTIFIER 				::= {OCTOPUS 6}

-- ** Parametros de configuración de red ***
     Information OBJECT IDENTIFIER 			::= {OCTOPUS 7}
	 
--	********************************************
--	******INFORMACION PARAMETROS DE RED ********
--	********************************************
IP_OCTOPUS OBJECT-TYPE
        SYNTAX IpAddress
        MAX-ACCESS  read-write
        STATUS current
        DESCRIPTION  " Direccion IP de Octopus"    
        ::={Network 1}
 
IP_SNMP OBJECT-TYPE
        SYNTAX IpAddress
        MAX-ACCESS  read-write
        STATUS current
        DESCRIPTION   "Direccion IP gestor SNMP"    
        ::={Network 2}

IP_SNMP2 OBJECT-TYPE
        SYNTAX IpAddress
        MAX-ACCESS  read-write
        STATUS current
        DESCRIPTION   "Direccion IP gestor SNMP2"    
        ::={Network 3}       
        

MASK OBJECT-TYPE
        SYNTAX IpAddress
        MAX-ACCESS  read-write
        STATUS current
        DESCRIPTION   "Mascara para IP OCTOPUS"    
        ::={Network 4}

Gateway OBJECT-TYPE
        SYNTAX IpAddress
        MAX-ACCESS  read-write
        STATUS current
        DESCRIPTION   "Puerta de enlace OCTOPUS"    
        ::={Network 5}

HabilitarSNMP2 OBJECT-TYPE
        SYNTAX INTEGER
	   {   No(0),
           Si(1)  }
        MAX-ACCESS  read-write
        STATUS current
        DESCRIPTION  "Habilitacion de segundo administrador SNMP"    
        ::={Network 6}

NTP-Server OBJECT-TYPE
        SYNTAX IpAddress
        MAX-ACCESS  read-write
        STATUS current
        DESCRIPTION   "Servidor NTP"    
        ::={Network 7}
		
NTP-Port OBJECT-TYPE
        SYNTAX INTEGER (0..32767)
        MAX-ACCESS  read-write
        STATUS current
        DESCRIPTION   "Puerto para NTP"    
        ::={Network 8}

NTP-Update OBJECT-TYPE
        SYNTAX INTEGER (0..32767)
        MAX-ACCESS  read-write
        STATUS current
        DESCRIPTION   "Tiempo de actualizacion Servidor NTP"    
        ::={Network 9}        

TFTP-Server OBJECT-TYPE
        SYNTAX IpAddress
        MAX-ACCESS  read-write
        STATUS current
        DESCRIPTION   "Servidor TFTP para actualizaciones firmware"    
        ::={Network 10}
        
TFTP-File OBJECT-TYPE
        SYNTAX  DisplayString
        MAX-ACCESS  read-write
        STATUS current
        DESCRIPTION   "Fichero Actualizacion firmware"    
        ::={Network 11}      

Update OBJECT-TYPE
        SYNTAX INTEGER
	   {   No(0),
           Si(1)  }
        MAX-ACCESS  read-write
        STATUS current
        DESCRIPTION   "Comenzar Update firmware"    
        ::={Network 12}

Status_Update OBJECT-TYPE
        SYNTAX DisplayString
        MAX-ACCESS  read-only
        STATUS current
        DESCRIPTION   "Estado actualizacion"    
        ::={Network 13}     
           
--	********************************************
--	******INFORMACION EQUIPO            ********
--	********************************************
Version OBJECT-TYPE
        SYNTAX DisplayString
        MAX-ACCESS  read-only
        STATUS current
        DESCRIPTION  " Version Equipo"    
        ::={Information 1}
 
Descripcion OBJECT-TYPE
        SYNTAX DisplayString
        MAX-ACCESS  read-only
        STATUS current
        DESCRIPTION   "Informacion de la version"    
        ::={Information 2}

Time OBJECT-TYPE
        SYNTAX DisplayString
        MAX-ACCESS  read-only
        STATUS current
        DESCRIPTION   "Hora del equipo"    
        ::={Information 3}

--	********************************************
--	******INFORMACION OCTOPUS BACNET***********
--	********************************************
--- BACnet Equipo 1 UPS -----
---- Datos Conexion ----
IP_UPS OBJECT-TYPE
        SYNTAX IpAddress
        MAX-ACCESS  read-write
        STATUS current
        DESCRIPTION  " Direccion IP de acceso al equipos BacNet1 (UPS)"    
        ::={Network_UPS 1}
Port_UPS OBJECT-TYPE
        SYNTAX INTEGER (0..32767)
        MAX-ACCESS  read-write
        STATUS current
        DESCRIPTION   "Direccion IP de acceso al equipos BacNet1 (UPS)"    
        ::={Network_UPS 2}	
Estado_UPS OBJECT-TYPE
        SYNTAX INTEGER
		{
			FALLO(1),
			Conectado(0)
		}
        MAX-ACCESS  read-only
        STATUS current
        DESCRIPTION   "Estado de la conexion al equipo BACNet1 (UPS)"    
        ::={Network_UPS 3}		

---- Datos Objetos ----		
Battery_Temperature OBJECT-TYPE
		SYNTAX INTEGER (0..32767)
		MAX-ACCESS read-only
		STATUS current
		DESCRIPTION "Battery Temperature"
		::={Object_UPS 0}
		
Battery_Voltage OBJECT-TYPE
		SYNTAX INTEGER (0..32767)
		MAX-ACCESS read-only
		STATUS current
		DESCRIPTION "Battery Voltaje"
		::={Object_UPS 1}
		
Output_Frequency OBJECT-TYPE
		SYNTAX INTEGER (0..32767)
		MAX-ACCESS read-only
		STATUS current
		DESCRIPTION "Output Frequency"
		::={Object_UPS 2}
		
Output_kW_Line1 OBJECT-TYPE
		SYNTAX INTEGER (0..32767)
		MAX-ACCESS read-only
		STATUS current
		DESCRIPTION "Output kW Line 1"
		::={Object_UPS 3}
		
Output_kW_Line2 OBJECT-TYPE
		SYNTAX INTEGER (0..32767)
		MAX-ACCESS read-only
		STATUS current
		DESCRIPTION "Output kW Line 2"
		::={Object_UPS 4}
		
Output_kW_Line3 OBJECT-TYPE
		SYNTAX INTEGER (0..32767)
		MAX-ACCESS read-only
		STATUS current
		DESCRIPTION "Output kW Line 3"
		::={Object_UPS 5}
		
Output_Voltage_Line1 OBJECT-TYPE
		SYNTAX INTEGER (0..32767)
		MAX-ACCESS read-only
		STATUS current
		DESCRIPTION "Output Voltage Line 1"
		::={Object_UPS 6}
		
Output_Voltage_Line2 OBJECT-TYPE
		SYNTAX INTEGER (0..32767)
		MAX-ACCESS read-only
		STATUS current
		DESCRIPTION "Output Voltage Line 2"
		::={Object_UPS 7}
		
Output_Voltage_Line3 OBJECT-TYPE
		SYNTAX INTEGER (0..32767)
		MAX-ACCESS read-only
		STATUS current
		DESCRIPTION "Output Voltage Line 3"
		::={Object_UPS 8}
		
Maintenance OBJECT-TYPE
		SYNTAX INTEGER
		{
			NO(1),
			SI(0)
		}
		MAX-ACCESS read-only
		STATUS current
		DESCRIPTION "Maintenance"
		::={Object_UPS 9}
		
UPS_Not_Synchronized OBJECT-TYPE
		SYNTAX INTEGER
		{
			NO(1),
			SI(0)
		}
		MAX-ACCESS read-only
		STATUS current
		DESCRIPTION "UPS not Synchronized"
		::={Object_UPS 10}
		
Low_Battery OBJECT-TYPE
		SYNTAX INTEGER
		{
			NO(1),
			SI(0)
		}
		MAX-ACCESS read-only
		STATUS current
		DESCRIPTION "Low Battery"
		::={Object_UPS 11}

--- BACnet Equipo 2 Cuadro FPC -----
---- Datos Conexion ----
IP_Cuadro OBJECT-TYPE
        SYNTAX IpAddress
        MAX-ACCESS  read-write
        STATUS current
        DESCRIPTION  " Direccion IP de acceso al equipos BacNet2 (Cuadro FPC)"    
        ::={Network_Cuadro 1}
Port_Cuadro OBJECT-TYPE
        SYNTAX INTEGER (0..32767)
        MAX-ACCESS  read-write
        STATUS current
        DESCRIPTION   "Direccion IP de acceso al equipos BacNet2 (Cuadro)"    
        ::={Network_Cuadro 2}	

Estado_Cuadro OBJECT-TYPE		
		SYNTAX INTEGER
		{
			FALLO(1),
			Conectado(0)
		}
        MAX-ACCESS  read-only
        STATUS current
        DESCRIPTION   "Estado de la conexion al equipo BACNet2 (Cuadro)"	
		::={Network_Cuadro 3}		

---- Datos Objetos ----				
Current_Ix OBJECT-TYPE
		SYNTAX INTEGER (0..32767)
		MAX-ACCESS read-only
		STATUS current
		DESCRIPTION "Current Ix"
		::={Object_Cuadro 1}
		
Current_Iy OBJECT-TYPE
		SYNTAX INTEGER (0..32767)
		MAX-ACCESS read-only
		STATUS current
		DESCRIPTION "Current Iy"
		::={Object_Cuadro 2}
		
Current_Iz OBJECT-TYPE
		SYNTAX INTEGER (0..32767)
		MAX-ACCESS read-only
		STATUS current
		DESCRIPTION "Current Iz"
		::={Object_Cuadro 3}
		
Voltage_Xn OBJECT-TYPE
		SYNTAX INTEGER (0..32767)
		MAX-ACCESS read-only
		STATUS current
		DESCRIPTION "Voltage Xn"
		::={Object_Cuadro 4}
		
Voltage_Yn OBJECT-TYPE
		SYNTAX INTEGER (0..32767)
		MAX-ACCESS read-only
		STATUS current
		DESCRIPTION "Voltage Yn"
		::={Object_Cuadro 5}
		
Voltage_Zn OBJECT-TYPE
		SYNTAX INTEGER (0..32767)
		MAX-ACCESS read-only
		STATUS current
		DESCRIPTION "Voltage Zn"
		::={Object_Cuadro 6}
		
Maintenance OBJECT-TYPE
		SYNTAX INTEGER
		{
			NO(1),
			SI(0)
		}
		MAX-ACCESS read-only
		STATUS current
		DESCRIPTION "Maintenance"
		::={Object_Cuadro 7}
		
Ground_Overcurrent OBJECT-TYPE
		SYNTAX INTEGER 
		{
			NO(1),
			SI(0)
		}
		MAX-ACCESS read-only
		STATUS current
		DESCRIPTION "Ground Overcurrent"
		::={Object_Cuadro 8}
		
Neutral_Current OBJECT-TYPE
		SYNTAX INTEGER (0..32767)
		MAX-ACCESS read-only
		STATUS current
		DESCRIPTION "Neutral Current"
		::={Object_Cuadro 9}
		
Output_CurrentA OBJECT-TYPE
		SYNTAX INTEGER (0..32767)
		MAX-ACCESS read-only
		STATUS current
		DESCRIPTION "Output Current A"
		::={Object_Cuadro 10}
		
Output_CurrentB OBJECT-TYPE
		SYNTAX INTEGER (0..32767)
		MAX-ACCESS read-only
		STATUS current
		DESCRIPTION "Output Current B"
		::={Object_Cuadro 11}
		
Output_CurrentC OBJECT-TYPE
		SYNTAX INTEGER (0..32767)
		MAX-ACCESS read-only
		STATUS current
		DESCRIPTION "Output Current C"
		::={Object_Cuadro 12}
		
Output_Voltage_A-N OBJECT-TYPE
		SYNTAX INTEGER (0..32767)
		MAX-ACCESS read-only
		STATUS current
		DESCRIPTION "Output Voltage A-N"
		::={Object_Cuadro 13}
		
Output_Voltage_B-N OBJECT-TYPE
		SYNTAX INTEGER (0..32767)
		MAX-ACCESS read-only
		STATUS current
		DESCRIPTION "Output Voltage B-N"
		::={Object_Cuadro 14}
		
Output_Voltage_C-N OBJECT-TYPE
		SYNTAX INTEGER (0..32767)
		MAX-ACCESS read-only
		STATUS current
		DESCRIPTION "Output Voltage C-N"
		::={Object_Cuadro 15}
		
Emergency_Power_OFF OBJECT-TYPE
		SYNTAX INTEGER 
		{
			NO(1),
			SI(0)
		}
		MAX-ACCESS read-only
		STATUS current
		DESCRIPTION "Emergency Power OFF"
		::={Object_Cuadro 16}
		
Frequency_Deviation OBJECT-TYPE
		SYNTAX INTEGER 
		{
			NO(1),
			SI(0)
		}
		MAX-ACCESS read-only
		STATUS current
		DESCRIPTION "Frequency Deviation"
		::={Object_Cuadro 17}
		
Ground_Failure OBJECT-TYPE
		SYNTAX INTEGER 
		{
			NO(1),
			SI(0)
		}
		MAX-ACCESS read-only
		STATUS current
		DESCRIPTION "Ground Failure"
		::={Object_Cuadro 18}
--- BACnet Equipo 3 CARC FC -----
---- Datos Conexion ----
IP_CRAC_FC OBJECT-TYPE
        SYNTAX IpAddress
        MAX-ACCESS  read-write
        STATUS current
        DESCRIPTION  " Direccion IP de acceso al equipos BacNet3 (CRAC FC)"    
        ::={Network_CRAC_FC 1}
Port_CRAC_FC OBJECT-TYPE
        SYNTAX INTEGER (0..32767)
        MAX-ACCESS  read-write
        STATUS current
        DESCRIPTION   "Direccion IP de acceso al equipos BacNet3 (CRAC FC)" 		
        ::={Network_CRAC_FC 2}	
		
Estado_CRAC_FC OBJECT-TYPE		
		SYNTAX INTEGER
		{
			FALLO(1),
			Conectado(0)
		}
        MAX-ACCESS  read-only
        STATUS current
        DESCRIPTION   "Estado de la conexion al equipo BACNet3 (CRAC FC)"	
		::={Network_CRAC_FC 3}
		
Cooling_Ramp OBJECT-TYPE
		SYNTAX INTEGER (0..32767)
		MAX-ACCESS read-only
		STATUS current
		DESCRIPTION "Cooling Ramp%"
		::={Object_CRAC_FC 1}
		
Fan_Ramp OBJECT-TYPE
		SYNTAX INTEGER (0..32767)
		MAX-ACCESS read-only
		STATUS current
		DESCRIPTION "Fan Ramp%"
		::={Object_CRAC_FC 2}
		
Return_Humidity OBJECT-TYPE
		SYNTAX INTEGER (0..32767)
		MAX-ACCESS read-only
		STATUS current
		DESCRIPTION "Return Humidity"
		::={Object_CRAC_FC 3}
		
Return_Temp OBJECT-TYPE
		SYNTAX INTEGER (0..32767)
		MAX-ACCESS read-only
		STATUS current
		DESCRIPTION "Return Temp"
		::={Object_CRAC_FC 4}
		
Supply_Temp OBJECT-TYPE
		SYNTAX INTEGER (0..32767)
		MAX-ACCESS read-only
		STATUS current
		DESCRIPTION "Supply Temp"
		::={Object_CRAC_FC 5}
		
Cooling_State OBJECT-TYPE
		SYNTAX INTEGER 
		{
			NO(1),
			SI(0)
		}
		MAX-ACCESS read-only
		STATUS current
		DESCRIPTION "Cooling State"
		::={Object_CRAC_FC 6}
		
Fan_State OBJECT-TYPE
		SYNTAX INTEGER 
		{
			NO(1),
			SI(0)
		}
		MAX-ACCESS read-only
		STATUS current
		DESCRIPTION "Fan State"
		::={Object_CRAC_FC 7}
		
Unit_ON_OFF OBJECT-TYPE
		SYNTAX INTEGER 
		{
			ON(1),
			OFF(0)
		}
		MAX-ACCESS read-only
		STATUS current
		DESCRIPTION "Unit ON/OFF"
		::={Object_CRAC_FC 8}
		
		
--- BACnet Equipo 4 PASARELA -----
---- Datos Conexion ----
IP_PASARELA OBJECT-TYPE
        SYNTAX IpAddress
        MAX-ACCESS  read-write
        STATUS current
        DESCRIPTION  " Direccion IP de acceso a la pasarela"    
        ::={Network_PASARELA 1}
Port_PASARELA OBJECT-TYPE
        SYNTAX INTEGER (0..32767)
        MAX-ACCESS  read-write
        STATUS current
        DESCRIPTION   "Direccion IP de acceso a la pasarela" 		
        ::={Network_PASARELA 2}	
		
Estado_PASARELA OBJECT-TYPE		
		SYNTAX INTEGER
		{
			FALLO(1),
			Conectado(0)
		}
        MAX-ACCESS  read-only
        STATUS current
        DESCRIPTION   "Estado de la conexion a la pasarela"	
		::={Network_PASARELA 3}
		

--	********************************************
--	******INFORMACION OCTOPUS SNMP***********
--	********************************************
--- SNMP1 Equipo 1 UPS EATON-----
---- Datos Conexion ----
IP_UPS_EATON OBJECT-TYPE
        SYNTAX IpAddress
        MAX-ACCESS  read-write
        STATUS current
        DESCRIPTION  " Direccion IP de acceso al equipos SNMP1 (UPS_EATON)"    
        ::={Network_UPS_EATON 1}
Port_UPS_EATON OBJECT-TYPE
        SYNTAX INTEGER (0..32767)
        MAX-ACCESS  read-write
        STATUS current
        DESCRIPTION   "Direccion IP de acceso al equipos SNMP1 (UPS_EATON)"    
        ::={Network_UPS_EATON 2}
ESTADO_UPS_EATON OBJECT-TYPE
        SYNTAX INTEGER
		{
			FALLO(1),
			Conectado(0)
		}
        MAX-ACCESS  read-only
        STATUS current
        DESCRIPTION   "Estao de conexion SNMP(UPS_EATON)"    
        ::={Network_UPS_EATON 3}		

---- Datos Objetos ----				
--- UPS Eaton----
Battery_Voltage OBJECT-TYPE
		SYNTAX INTEGER (0..32767)
		MAX-ACCESS read-only
		STATUS current
		DESCRIPTION "Voltaje de la bateria"
		::= {Object_UPS_EATON 1}
		
Battery_Time OBJECT-TYPE
		SYNTAX INTEGER (0..32767)
		MAX-ACCESS read-only
		STATUS current
		DESCRIPTION "Tiempo restante de la bateria en segundos"
		::= {Object_UPS_EATON 2}
		
Voltage_Phase1 OBJECT-TYPE
		SYNTAX INTEGER (0..32767)
		MAX-ACCESS read-only
		STATUS current
		DESCRIPTION "Voltaje de entrada fase 1"
		::= {Object_UPS_EATON 3}
		
Voltage_Phase2 OBJECT-TYPE
		SYNTAX INTEGER (0..32767)
		MAX-ACCESS read-only
		STATUS current
		DESCRIPTION "Voltaje de entrada fase 2"
		::= {Object_UPS_EATON 4}

Voltage_Phase3 OBJECT-TYPE
		SYNTAX INTEGER (0..32767)
		MAX-ACCESS read-only
		STATUS current
		DESCRIPTION "Voltaje de entrada fase 3"
		::= {Object_UPS_EATON 5}

Power_Phase1 OBJECT-TYPE
		SYNTAX INTEGER (0..32767)
		MAX-ACCESS read-only
		STATUS current
		DESCRIPTION "Potencia de salida fase 1"
		::= {Object_UPS_EATON 6}

Power_Phase2 OBJECT-TYPE
		SYNTAX INTEGER (0..32767)
		MAX-ACCESS read-only
		STATUS current
		DESCRIPTION "Potencia de salida fase 2"
		::= {Object_UPS_EATON 7}

Power_Phase3 OBJECT-TYPE
		SYNTAX INTEGER (0..32767)
		MAX-ACCESS read-only
		STATUS current
		DESCRIPTION "Potencia de salida fase 3"
		::= {Object_UPS_EATON 8}

Battery_Capacity OBJECT-TYPE
		SYNTAX INTEGER (0..32767)
		MAX-ACCESS read-only
		STATUS current
		DESCRIPTION "Capacidad en % de la bateria"
		::= {Object_UPS_EATON 9}

Input_Frecuency OBJECT-TYPE
		SYNTAX INTEGER (0..32767)
		MAX-ACCESS read-only
		STATUS current
		DESCRIPTION "Frecuencia de entrada"
		::= {Object_UPS_EATON 10}

Num_Alarms OBJECT-TYPE
		SYNTAX INTEGER (0..32767)
		MAX-ACCESS read-only
		STATUS current
		DESCRIPTION "Numero de alarmas actuales"
		::= {Object_UPS_EATON 11}

Output_Voltage OBJECT-TYPE
		SYNTAX INTEGER (0..32767)
		MAX-ACCESS read-only
		STATUS current
		DESCRIPTION "Voltaje de salida"
		::= {Object_UPS_EATON 12}

--	********************************************
--	******ENTRADAS DIGITALES********************
--	********************************************
GruposEntradasDigitales OBJECT-TYPE
        SYNTAX     OCTET STRING (SIZE (10))
        MAX-ACCESS read-write
        STATUS     current
        DESCRIPTION   "Lectura completa de estado binario de entradas digitales"
        ::= {EntradasDigitales 0}
        
Entrada-Digital1 OBJECT-TYPE 
        SYNTAX INTEGER
	   {   No(1),
           Si(0)  }
        MAX-ACCESS read-only
        STATUS current
        DESCRIPTION   "Entrada Digital 1"
        ::= {EntradasDigitales 1} 

Entrada-Digital2 OBJECT-TYPE 
        SYNTAX INTEGER
	   {   No(1),
           Si(0)  }
        MAX-ACCESS read-only
        STATUS current
        DESCRIPTION   "Entrada Digital 2"
        ::= {EntradasDigitales 2} 

Entrada-Digital3 OBJECT-TYPE 
        SYNTAX INTEGER
	   {   No(1),
           Si(0)  }
        MAX-ACCESS read-only
        STATUS current
        DESCRIPTION   "Entrada Digital 3"
        ::= {EntradasDigitales 3} 

Entrada-Digital4 OBJECT-TYPE 
        SYNTAX INTEGER
	   {   No(1),
           Si(0)  }
        MAX-ACCESS read-only
        STATUS current
        DESCRIPTION   "Entrada Digital 4"
        ::= {EntradasDigitales 4} 

Entrada-Digital5 OBJECT-TYPE 
        SYNTAX INTEGER
	   {   No(1),
           Si(0)  }
        MAX-ACCESS read-only
        STATUS current
        DESCRIPTION    "Entrada Digital 5"
        ::= {EntradasDigitales 5} 

Entrada-Digital6 OBJECT-TYPE 
        SYNTAX INTEGER
	   {   No(1),
           Si(0)  }
        MAX-ACCESS read-only
        STATUS current
        DESCRIPTION    "Entrada Digital 6"
        ::= {EntradasDigitales 6} 

Entrada-Digital7 OBJECT-TYPE 
        SYNTAX INTEGER
	   {   No(1),
           Si(0)  }
        MAX-ACCESS read-only
        STATUS current
        DESCRIPTION    "Entrada Digital 7"
        ::= {EntradasDigitales 7}

Entrada-Digital8 OBJECT-TYPE 
        SYNTAX INTEGER
	   {   No(1),
           Si(0)  }
        MAX-ACCESS read-only
        STATUS current
        DESCRIPTION     "Entrada Digital 8"
        ::= {EntradasDigitales 8}
        
Entrada-Digital9 OBJECT-TYPE 
        SYNTAX INTEGER
	   {   No(1),
           Si(0)  }
        MAX-ACCESS read-only
        STATUS current
        DESCRIPTION    "Entrada Digital 9"
        ::= {EntradasDigitales 9}

Entrada-Digital10 OBJECT-TYPE 
        SYNTAX INTEGER
	   {   No(1),
           Si(0)  }
        MAX-ACCESS read-only
        STATUS current
        DESCRIPTION    "Entrada Digital 10"
        ::= {EntradasDigitales 10} 

Entrada-Digital11 OBJECT-TYPE 
        SYNTAX INTEGER
	   {   No(1),
           Si(0)  }
        MAX-ACCESS read-only
        STATUS current
        DESCRIPTION    "Entrada Digital 11"
        ::= {EntradasDigitales 11} 

Entrada-Digital12 OBJECT-TYPE 
        SYNTAX INTEGER
	   {   No(1),
           Si(0)  }
        MAX-ACCESS read-only
        STATUS current
        DESCRIPTION    "Entrada Digital 12"
        ::= {EntradasDigitales 12} 

Entrada-Digital13 OBJECT-TYPE 
        SYNTAX INTEGER
	   {   No(1),
           Si(0)  }
        MAX-ACCESS read-only
        STATUS current
        DESCRIPTION    "Entrada Digital 13"
        ::= {EntradasDigitales 13} 

Entrada-Digital14 OBJECT-TYPE 
        SYNTAX INTEGER
	   {   No(1),
           Si(0)  }
        MAX-ACCESS read-only
        STATUS current
        DESCRIPTION    "Entrada Digital 14"
        ::= {EntradasDigitales 14} 

Entrada-Digital15 OBJECT-TYPE 
        SYNTAX INTEGER
	   {   No(1),
           Si(0)  }
        MAX-ACCESS read-only
        STATUS current
        DESCRIPTION    "Entrada Digital 15"
        ::= {EntradasDigitales 15} 

Entrada-Digital16 OBJECT-TYPE 
        SYNTAX INTEGER
	   {   No(1),
           Si(0)  }
        MAX-ACCESS read-only
        STATUS current
        DESCRIPTION    "Entrada Digital 16"
        ::= {EntradasDigitales 16} 

Entrada-Digital17 OBJECT-TYPE 
        SYNTAX INTEGER
	   {   No(1),
           Si(0)  }
        MAX-ACCESS read-only
        STATUS current
        DESCRIPTION    "Entrada Digital 17"
        ::= {EntradasDigitales 17} 

Entrada-Digital18 OBJECT-TYPE 
        SYNTAX INTEGER
	   {   No(1),
           Si(0)  }
        MAX-ACCESS read-only
        STATUS current
        DESCRIPTION    "Entrada Digital 18"
        ::= {EntradasDigitales 18} 
        
Entrada-Digital19 OBJECT-TYPE 
        SYNTAX INTEGER
	   {   No(1),
           Si(0)  }
        MAX-ACCESS read-only
        STATUS current
        DESCRIPTION    "Entrada Digital 19"
        ::= {EntradasDigitales 19}

Entrada-Digital20 OBJECT-TYPE 
        SYNTAX INTEGER
	   {   No(1),
           Si(0)  }
        MAX-ACCESS read-only
        STATUS current
        DESCRIPTION    "Entrada Digital 20"
        ::= {EntradasDigitales 20} 

Entrada-Digital21 OBJECT-TYPE 
        SYNTAX INTEGER
	   {   No(1),
           Si(0)  }
        MAX-ACCESS read-only
        STATUS current
        DESCRIPTION    "Entrada Digital 21"
        ::= {EntradasDigitales 21} 
        
Entrada-Digital22 OBJECT-TYPE 
        SYNTAX INTEGER
	   {   No(1),
           Si(0)  }
        MAX-ACCESS read-only
        STATUS current
        DESCRIPTION    "Entrada Digital 22"
        ::= {EntradasDigitales 22} 

Entrada-Digital23 OBJECT-TYPE 
        SYNTAX INTEGER
	   {   No(1),
           Si(0)  }
        MAX-ACCESS read-only
        STATUS current
        DESCRIPTION    "Entrada Digital 23"
        ::= {EntradasDigitales 23} 
        
Entrada-Digital24 OBJECT-TYPE 
        SYNTAX INTEGER
	   {   No(1),
           Si(0)  }
        MAX-ACCESS read-only
        STATUS current
        DESCRIPTION    "Entrada Digital 24"
        ::= {EntradasDigitales 24}

--	********************************************
--	******ENTRADAS ANALOGICAS********************
--	********************************************		
GruposEntradasAnalogicas OBJECT-TYPE
        SYNTAX     OCTET STRING (SIZE (7))
        MAX-ACCESS read-write
        STATUS     current
        DESCRIPTION   "Lectura completa de estado de analógicas"
        ::= {EntradasAnalogicas 0}
                                
Entrada-Analogica1 OBJECT-TYPE 
        SYNTAX INTEGER (-32768..32767)
        MAX-ACCESS read-only
        STATUS current
        DESCRIPTION "Entrada Analogica 1"
        ::= {EntradasAnalogicas 76}

Entrada-Analogica2 OBJECT-TYPE 
        SYNTAX INTEGER (-32768..32767)
        MAX-ACCESS read-only
        STATUS current
        DESCRIPTION "Entrada Analogica 2"
        ::= {EntradasAnalogicas 77}
        
Entrada-Analogica3 OBJECT-TYPE 
        SYNTAX INTEGER (-32768..32767)
        MAX-ACCESS read-only
        STATUS current
        DESCRIPTION "Entrada Analogica 3"
        ::= {EntradasAnalogicas 78}

--	********************************************
--	******SALIDAS DIGITALES********************
--	********************************************	
GruposSalidasDigitales OBJECT-TYPE
        SYNTAX     OCTET STRING (SIZE (3))
        MAX-ACCESS read-write
        STATUS     current
        DESCRIPTION   "Lectura completa de estado salidas digitales"
        ::= {SalidasDigitales 0}
                  
Salida-Digital1 OBJECT-TYPE 
        SYNTAX INTEGER
	  {   Desactivado(1),
           Activado(0)   }
        MAX-ACCESS read-write
        STATUS current
        DESCRIPTION "Salida Digital 1"
        ::= {SalidasDigitales 81}
                     
Salida-Digital2 OBJECT-TYPE 
        SYNTAX INTEGER
	  {   Desactivado(1),
           Activado(0)   }
        MAX-ACCESS read-write
        STATUS current
        DESCRIPTION "Salida Digital 2"
        ::= {SalidasDigitales 82}

Salida-Digital3 OBJECT-TYPE 
        SYNTAX INTEGER
	  {   Desactivado(1),
           Activado(0)   }
        MAX-ACCESS read-write
        STATUS current
        DESCRIPTION "Salida Digital 3"
        ::= {SalidasDigitales 83}
                     
Salida-Digital4 OBJECT-TYPE 
        SYNTAX INTEGER
	  {   Desactivado(1),
           Activado(0)   }
        MAX-ACCESS read-write
        STATUS current
        DESCRIPTION "Salida Digital 4"
        ::= {SalidasDigitales 84}

Salida-Digital5 OBJECT-TYPE 
        SYNTAX INTEGER
	  {   Desactivado(1),
           Activado(0)   }
        MAX-ACCESS read-write
        STATUS current
        DESCRIPTION "Salida Digital 5"
        ::= {SalidasDigitales 85}
                     
Salida-Digital6 OBJECT-TYPE 
        SYNTAX INTEGER
	  {   Desactivado(1),
           Activado(0)   }
        MAX-ACCESS read-write
        STATUS current
        DESCRIPTION "Salida Digital 6"
        ::= {SalidasDigitales 86}

Salida-Digital7 OBJECT-TYPE 
        SYNTAX INTEGER
	  {   Desactivado(1),
           Activado(0)   }
        MAX-ACCESS read-write
        STATUS current
        DESCRIPTION "Salida Digital 7"
        ::= {SalidasDigitales 87}
                     
Salida-Digital8 OBJECT-TYPE 
        SYNTAX INTEGER
	  {   Desactivado(1),
           Activado(0)   }
        MAX-ACCESS read-write
        STATUS current
        DESCRIPTION "Salida Digital 8"
        ::= {SalidasDigitales 88}    
                                     
--	--------------------------------------
--	****** 		TRAPS		 *******
--	--------------------------------------
--	****************************************************
--	******INFORMACION PARAMETROS DE Trap_structure *****
--	****************************************************
                   
----------------------------------------------        
Nexcon-OCTOPUS-ColdStart TRAP-TYPE
              ENTERPRISE nexcon
              DESCRIPTION
              " El equipo se acaba de encender."
              ::=  1        
----------------------------------------------        
Nexcon-OCTOPUS-WarmStart TRAP-TYPE
              ENTERPRISE nexcon
              DESCRIPTION
              " El equipo se acaba de reiniciar."
              ::=  2
-------------------------------------------------------
Nexcon-OCTOPUS-Fallo-Analogica1 TRAP-TYPE
        ENTERPRISE nexcon
        DESCRIPTION    "TRAP activacion fallo analogica 1"
        ::= 10
Nexcon-OCTOPUS-Recuperación-Analógica1 TRAP-TYPE
        ENTERPRISE nexcon
        DESCRIPTION    "TRAP desactivacion fallo analogica 1"
        ::= 11
Nexcon-OCTOPUS-Activacion-In-Analogica1_MAX TRAP-TYPE
        ENTERPRISE nexcon
        DESCRIPTION    "TRAP activacion entrada analogica1 por máximo"
        ::= 12
Nexcon-OCTOPUS-Activacion-In-Analogica1_MIN TRAP-TYPE
        ENTERPRISE nexcon
        DESCRIPTION    "TRAP activacion entrada analogica1 por minimo"
        ::= 13
Nexcon-OCTOPUS-Activacion-In-Analogica1_NORMAL TRAP-TYPE
        ENTERPRISE nexcon
        DESCRIPTION    "TRAP activacion entrada analogica1 normal"
        ::= 14

Nexcon-OCTOPUS-Fallo-Analogica2 TRAP-TYPE
        ENTERPRISE nexcon
        DESCRIPTION    "TRAP activacion fallo analogica 2"
        ::= 15
Nexcon-OCTOPUS-Recuperación-Analógica2 TRAP-TYPE
        ENTERPRISE nexcon
        DESCRIPTION    "TRAP desactivacion fallo analogica 2"
        ::= 16
Nexcon-OCTOPUS-Activacion-In-Analogica2_MAX TRAP-TYPE
        ENTERPRISE nexcon
        DESCRIPTION    "TRAP activacion entrada analogica2 por máximo"
        ::= 17
Nexcon-OCTOPUS-Activacion-In-Analogica2_MIN TRAP-TYPE
        ENTERPRISE nexcon
         DESCRIPTION    "TRAP activacion entrada analogica2 por minimo"
        ::= 18
Nexcon-OCTOPUS-Activacion-In-Analogica2_NORMAL TRAP-TYPE
        ENTERPRISE nexcon
        DESCRIPTION    "TRAP activacion entrada analogica2 normal"
        ::= 19

Nexcon-OCTOPUS-Fallo-Analogica3 TRAP-TYPE
        ENTERPRISE nexcon
        DESCRIPTION    "TRAP activacion fallo analogica 3"
        ::= 20
Nexcon-OCTOPUS-Recuperación-Analógica3 TRAP-TYPE
        ENTERPRISE nexcon
        DESCRIPTION    "TRAP desactivacion fallo analogica 3"
        ::= 21
Nexcon-OCTOPUS-Activacion-In-Analogica3_MAX TRAP-TYPE
        ENTERPRISE nexcon
        DESCRIPTION    "TRAP activacion entrada analogica3 por máximo"
        ::= 22
Nexcon-OCTOPUS-Activacion-In-Analogica3_MIN TRAP-TYPE
        ENTERPRISE nexcon
         DESCRIPTION    "TRAP activacion entrada analogica3 por minimo"
        ::= 23
Nexcon-OCTOPUS-Activacion-In-Analogica3_NORMAL TRAP-TYPE
        ENTERPRISE nexcon
        DESCRIPTION    "TRAP activacion entrada analogica3 normal"
        ::= 24
--------------------BACNET1 UPS-----------------------------------
Nexcon-OCTOPUS-UPS_Battery_Temperature_MAX TRAP-TYPE
        ENTERPRISE nexcon
        DESCRIPTION    "TRAP activacion Bateria UPS Bacnet1 por maximo"
        ::= 25
Nexcon-OCTOPUS-UPS_Battery_Temperature_MIN TRAP-TYPE
        ENTERPRISE nexcon
        DESCRIPTION    "TRAP activacion Bateria UPS Bacnet1 por minimo"
        ::= 26
Nexcon-OCTOPUS-UPS_Battery_Temperature_NORMAL TRAP-TYPE
        ENTERPRISE nexcon
        DESCRIPTION    "TRAP activacion Bateria UPS Bacnet1 Normal"
        ::= 27
Nexcon-OCTOPUS-UPS_Battery_Voltage_MAX TRAP-TYPE
        ENTERPRISE nexcon
        DESCRIPTION    "TRAP activacion Bateria UPS Bacnet1 por maximo"
        ::= 28
Nexcon-OCTOPUS-UPS_Battery_Voltage_MIN TRAP-TYPE
        ENTERPRISE nexcon
        DESCRIPTION    "TRAP activacion Bateria UPS Bacnet1 por minimo"
        ::= 29
Nexcon-OCTOPUS-UPS_Battery_Voltage_NORMAL TRAP-TYPE
        ENTERPRISE nexcon
        DESCRIPTION    "TRAP activacion Bateria UPS Bacnet1 Normal"
        ::= 30
Nexcon-OCTOPUS-UPS_Maintenance_ON TRAP-TYPE
        ENTERPRISE nexcon
        DESCRIPTION    "TRAP activacion Mantenimiento UPS BacnNet1"
        ::= 31
Nexcon-OCTOPUS-UPS_Maintenance_OFF TRAP-TYPE
        ENTERPRISE nexcon
        DESCRIPTION    "TRAP desactivacion Mantenimiento UPS BacnNet1"
        ::= 32
		
Nexcon-OCTOPUS-UPS_ESTADO_FAIL TRAP-TYPE
        ENTERPRISE nexcon
        DESCRIPTION    "TRAP comunicacion UPS perdida"
        ::= 89
Nexcon-OCTOPUS-UPS_MESTADO_OK TRAP-TYPE
        ENTERPRISE nexcon
        DESCRIPTION    "TRAP comunicacion UPS restablecida"
        ::= 88		

--------------------BACNET2 CUADRO-----------------------------------
Nexcon-OCTOPUS-CUADRO_Volts_Xn_MAX TRAP-TYPE
        ENTERPRISE nexcon
        DESCRIPTION    "TRAP activacion Volts Xn CUADRO Bacnet2 por maximo"
        ::= 33
Nexcon-OCTOPUS-CUADRO_Volts_Xn_MIN TRAP-TYPE
        ENTERPRISE nexcon
        DESCRIPTION    "TRAP activacion Volts Xn CUADRO Bacnet2 por minimo"
        ::= 34
Nexcon-OCTOPUS-CUADRO_Volts_Xn_NORMAL TRAP-TYPE
        ENTERPRISE nexcon
        DESCRIPTION    "TRAP activacion Volts Xn CUADRO Bacnet2 NORMAL"
        ::= 35
Nexcon-OCTOPUS-CUADRO_Volts_Yn_MAX TRAP-TYPE
        ENTERPRISE nexcon
        DESCRIPTION    "TRAP activacion Volts Yn CUADRO Bacnet2 por maximo"
        ::= 36
Nexcon-OCTOPUS-CUADRO_Volts_Yn_MIN TRAP-TYPE
        ENTERPRISE nexcon
        DESCRIPTION    "TRAP activacion Volts Yn CUADRO Bacnet2 por minimo"
        ::= 37
Nexcon-OCTOPUS-CUADRO_Volts_Yn_NORMAL TRAP-TYPE
        ENTERPRISE nexcon
        DESCRIPTION    "TRAP activacion Volts Yn CUADRO Bacnet2 NORMAL"
        ::= 38
Nexcon-OCTOPUS-CUADRO_Volts_Zn_MAX TRAP-TYPE
        ENTERPRISE nexcon
        DESCRIPTION    "TRAP activacion Volts Zn CUADRO Bacnet2 por maximo"
        ::= 39
Nexcon-OCTOPUS-CUADRO_Volts_Zn_MIN TRAP-TYPE
        ENTERPRISE nexcon
        DESCRIPTION    "TRAP activacion Volts Zn CUADRO Bacnet2 por minimo"
        ::= 40
Nexcon-OCTOPUS-CUADRO_Volts_Zn_NORMAL TRAP-TYPE
        ENTERPRISE nexcon
        DESCRIPTION    "TRAP activacion Volts Zn CUADRO Bacnet2 NORMAL"
        ::= 41		
Nexcon-OCTOPUS-CUADRO_Maintenance_ON TRAP-TYPE
        ENTERPRISE nexcon
        DESCRIPTION    "TRAP activacion Mantenimiento CUADRO BacnNet2"
        ::= 42
Nexcon-OCTOPUS-CUADRO_Maintenance_OFF TRAP-TYPE
        ENTERPRISE nexcon
        DESCRIPTION    "TRAP desactivacion Mantenimiento CUADRO BacnNet2"
        ::= 43		
Nexcon-OCTOPUS-CUADRO_Ground_Overcurrent_ON TRAP-TYPE
        ENTERPRISE nexcon
        DESCRIPTION    "TRAP activacion Ground_Overcurrent CUADRO BacnNet2"
        ::= 44
Nexcon-OCTOPUS-CUADRO_Ground_Overcurrent_OFF TRAP-TYPE
        ENTERPRISE nexcon
        DESCRIPTION    "TRAP desactivacion Ground_Overcurrent CUADRO BacnNet2"
        ::= 45	
Nexcon-OCTOPUS-CUADRO_Emergency_Power_ON TRAP-TYPE
        ENTERPRISE nexcon
        DESCRIPTION    "TRAP activacion Emergency Power Off CUADRO BacnNet2"
        ::= 46
Nexcon-OCTOPUS-CUADRO_Emergency_Power_OFF TRAP-TYPE
        ENTERPRISE nexcon
        DESCRIPTION    "TRAP desactivacion Emergency Power Off CUADRO BacnNet2"
        ::= 47		
Nexcon-OCTOPUS-CUADRO_Frequency_Deviation_ON TRAP-TYPE
        ENTERPRISE nexcon
        DESCRIPTION    "TRAP activacion Frequency Deviation CUADRO BacnNet2"
        ::= 48
Nexcon-OCTOPUS-CUADRO_Frequency_Deviation_OFF TRAP-TYPE
        ENTERPRISE nexcon
        DESCRIPTION    "TRAP desactivacion Frequency Deviation CUADRO BacnNet2"
        ::= 49	
Nexcon-OCTOPUS-CUADRO_Ground_Failure_ON TRAP-TYPE
        ENTERPRISE nexcon
        DESCRIPTION    "TRAP activacion Ground Failure CUADRO BacnNet2"
        ::= 50
Nexcon-OCTOPUS-CUADRO_Ground_Failure_OFF TRAP-TYPE
        ENTERPRISE nexcon
        DESCRIPTION    "TRAP desactivacion Ground Failure CUADRO BacnNet2"
        ::= 51
		
Nexcon-OCTOPUS-CUADRO_ESTADO_FAIL TRAP-TYPE
        ENTERPRISE nexcon
        DESCRIPTION    "TRAP comunicacion CUADROD FPC perdida"
        ::= 91

Nexcon-OCTOPUS-CUADRO_ESTADO_OK TRAP-TYPE
        ENTERPRISE nexcon
        DESCRIPTION    "TRAP comunicacion CUADRO FPC	restablecida"
        ::= 90


--------------------BACNET3 CRAC-----------------------------------
Nexcon-OCTOPUS-CRAC_Return_Humidity_MAX TRAP-TYPE
        ENTERPRISE nexcon
        DESCRIPTION    "TRAP activacion Return Humidity CRAC Bacnet3 por maximo"
        ::= 52
Nexcon-OCTOPUS-CRAC_Return_Humidity_MIN TRAP-TYPE
        ENTERPRISE nexcon
        DESCRIPTION    "TRAP activacion Return Humidity CRAC Bacnet3 por minimo"
        ::= 53
Nexcon-OCTOPUS-CRAC_Return_Humidity_NORMAL TRAP-TYPE
        ENTERPRISE nexcon
        DESCRIPTION    "TRAP activacion Return Humidity CRAC Bacnet3 NORMAL"
        ::= 54
Nexcon-OCTOPUS-CRAC_Return_Temp_MAX TRAP-TYPE
        ENTERPRISE nexcon
        DESCRIPTION    "TRAP activacion Return_Temp CRAC Bacnet3 por maximo"
        ::= 55
Nexcon-OCTOPUS-CRAC_Return_Temp_MIN TRAP-TYPE
        ENTERPRISE nexcon
        DESCRIPTION    "TRAP activacion Return_Temp CRAC Bacnet3 por minimo"
        ::= 56
Nexcon-OCTOPUS-CRAC_Return_Temp_NORMAL TRAP-TYPE
        ENTERPRISE nexcon
        DESCRIPTION    "TRAP activacion Return_Temp CRAC Bacnet3 NORMAL"
        ::= 57
Nexcon-OCTOPUS-CRAC_ON TRAP-TYPE
        ENTERPRISE nexcon
        DESCRIPTION    "TRAP activacion CRAC BacnNet3"
        ::= 58
Nexcon-OCTOPUS-CRAC_OFF TRAP-TYPE
        ENTERPRISE nexcon
        DESCRIPTION    "TRAP desactivacion CRAC BacnNet3"
        ::= 59	

Nexcon-OCTOPUS-CRAC_ESTADO_OK TRAP-TYPE
        ENTERPRISE nexcon
        DESCRIPTION    "TRAP comunicacion CRAC perdida"
        ::= 92
Nexcon-OCTOPUS-CRAC_ESTADO_FAIL TRAP-TYPE
        ENTERPRISE nexcon
        DESCRIPTION    "TRAP comunicacion CRAC perdida"
        ::= 93		

Nexcon-OCTOPUS-PASARELA_FAIL TRAP-TYPE
        ENTERPRISE nexcon
        DESCRIPTION    "TRAP comunicacion con la pasarela perdida"
        ::= 94			

Nexcon-OCTOPUS-PASARELA_OK TRAP-TYPE
        ENTERPRISE nexcon
        DESCRIPTION    "TRAP comunicacion con la pasarela restablecida"
        ::= 95	
		
--------------------SNMP1 UPS-----------------------------------
Nexcon-OCTOPUS-UPS_EATON_Capacity_MIN TRAP-TYPE
        ENTERPRISE nexcon
        DESCRIPTION    "TRAP activacion Capacidad batería por debajo de límites"
        ::= 60
Nexcon-OCTOPUS-UPS_EATON_Capacity_NORMAL TRAP-TYPE
        ENTERPRISE nexcon
        DESCRIPTION    "TRAP activacion Capacidad batería normal"
        ::= 61
Nexcon-OCTOPUS-UPS_EATON_Input_Frecuency_MIN TRAP-TYPE
        ENTERPRISE nexcon
        DESCRIPTION    "TRAP activacion Frecuencia de entrada por debajo de límites"
        ::= 62
Nexcon-OCTOPUS-UPS_EATON_Input_Frecuency_NORMAL TRAP-TYPE
        ENTERPRISE nexcon
        DESCRIPTION    "TRAP activacion Frecuencia de entrada normal"
        ::= 63
Nexcon-OCTOPUS-UPS_EATON_Alarms_ON TRAP-TYPE
        ENTERPRISE nexcon
        DESCRIPTION    "TRAP activacion alarmas"
        ::= 64
Nexcon-OCTOPUS-UPS_EATON_Alarms_OFF TRAP-TYPE
        ENTERPRISE nexcon
        DESCRIPTION    "TRAP desactivacion alarmas"
        ::= 65
Nexcon-OCTOPUS-UPS_EATON_Output_Voltage_MIN TRAP-TYPE
        ENTERPRISE nexcon
        DESCRIPTION    "TRAP activacion Voltaje de entrada por debajo de límites"
        ::= 66
Nexcon-OCTOPUS-UPS_EATON_Output_Voltage_NORMAL TRAP-TYPE
        ENTERPRISE nexcon
        DESCRIPTION    "TRAP activacion Voltaje de entrada normal"
        ::= 67	

Nexcon-OCTOPUS-UPS_EATON_ESTADO_FAIL TRAP-TYPE
        ENTERPRISE nexcon
        DESCRIPTION    "TRAP comunicacion UPS EATON perdida"
        ::= 96	
Nexcon-OCTOPUS-UPS_EATON_ESTADO_OK TRAP-TYPE
        ENTERPRISE nexcon
        DESCRIPTION    "TRAP comunicacion UPS EATON restablecida"
        ::= 97			
---------------ENTRADAS DIGITALES----------------------------------
Nexcon-OCTOPUS-Activacion-In-Digital1 TRAP-TYPE
        ENTERPRISE nexcon
        DESCRIPTION    "TRAP activacion entrada digital1"
        ::= 68
Nexcon-OCTOPUS-Desactivacion-In-Digital1 TRAP-TYPE
        ENTERPRISE nexcon
        DESCRIPTION		"TRAP desactivacion entrada digital1"
        ::= 69
Nexcon-OCTOPUS-Activacion-In-Digital2 TRAP-TYPE
        ENTERPRISE nexcon
        DESCRIPTION    "TRAP activacion entrada digital2"
        ::= 70
Nexcon-OCTOPUS-Desactivacion-In-Digital2 TRAP-TYPE
        ENTERPRISE nexcon
        DESCRIPTION		"TRAP desactivacion entrada digital2"
        ::= 71
Nexcon-OCTOPUS-Activacion-In-Digital3 TRAP-TYPE
        ENTERPRISE nexcon
        DESCRIPTION    "TRAP activacion entrada digital3"
        ::= 72
Nexcon-OCTOPUS-Desactivacion-In-Digital3 TRAP-TYPE
        ENTERPRISE nexcon
        DESCRIPTION		"TRAP desactivacion entrada digital3"
        ::= 73
Nexcon-OCTOPUS-Activacion-In-Digital4 TRAP-TYPE
        ENTERPRISE nexcon
        DESCRIPTION    "TRAP activacion entrada digital4"
        ::= 74
Nexcon-OCTOPUS-Desactivacion-In-Digital4 TRAP-TYPE
        ENTERPRISE nexcon
        DESCRIPTION		"TRAP desactivacion entrada digital4"
        ::= 75
Nexcon-OCTOPUS-Activacion-In-Digital5 TRAP-TYPE
        ENTERPRISE nexcon
        DESCRIPTION    "TRAP activacion entrada digital5"
        ::= 76
Nexcon-OCTOPUS-Desactivacion-In-Digital5 TRAP-TYPE
        ENTERPRISE nexcon
        DESCRIPTION		"TRAP desactivacion entrada digital5"
        ::= 77
Nexcon-OCTOPUS-Activacion-In-Digital6 TRAP-TYPE
        ENTERPRISE nexcon
        DESCRIPTION    "TRAP activacion entrada digital6"
        ::= 78
Nexcon-OCTOPUS-Desactivacion-In-Digital6 TRAP-TYPE
        ENTERPRISE nexcon
        DESCRIPTION		"TRAP desactivacion entrada digital6"
        ::= 79
Nexcon-OCTOPUS-Activacion-In-Digital7 TRAP-TYPE
        ENTERPRISE nexcon
        DESCRIPTION    "TRAP activacion entrada digital7"
        ::= 80
Nexcon-OCTOPUS-Desactivacion-In-Digital7 TRAP-TYPE
        ENTERPRISE nexcon
        DESCRIPTION		"TRAP desactivacion entrada digital7"
        ::= 81
Nexcon-OCTOPUS-Activacion-In-Digital8 TRAP-TYPE
        ENTERPRISE nexcon
        DESCRIPTION    "TRAP activacion entrada digital8"
        ::= 82
Nexcon-OCTOPUS-Desactivacion-In-Digital8 TRAP-TYPE
        ENTERPRISE nexcon
        DESCRIPTION		"TRAP desactivacion entrada digital8"
        ::= 83
-------------------------------------------------------
Nexcon-BJUMPER-Update-Start TRAP-TYPE
        ENTERPRISE nexcon
        DESCRIPTION    "Comienzo Actualización Firmware"
        ::= 84
Nexcon-BJUMPER-Update-End TRAP-TYPE
        ENTERPRISE nexcon
        DESCRIPTION    "Fin Actualización Firmware"
        ::= 85                
-------------------------------------------------------
Nexcon-BJUMPER-Fallo_NTP TRAP-TYPE
        ENTERPRISE nexcon
        DESCRIPTION    "Fallo Actualización NTP"
        ::= 86  
-------------------------------------------------------
Nexcon-BJUMPER-Sincronizacion_NTP TRAP-TYPE
        ENTERPRISE nexcon
        DESCRIPTION    "Sincronizacion NTP"
        ::= 87      
-------------------------------------------------------      
END
