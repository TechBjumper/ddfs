--
-- CAREL-aranew.MIB
-- MIB generated by CAREL
-- Monday, 10 December 2007
--

    CAREL-aranew-MIB DEFINITIONS ::= BEGIN

		IMPORTS
			OBJECT-GROUP		FROM SNMPv2-CONF			
			sysContact, sysName,
			sysLocation		FROM SNMPv2-MIB
			enterprises, MODULE-IDENTITY,
			OBJECT-TYPE, Integer32	FROM SNMPv2-SMI
			DisplayString		FROM RFC1213-MIB;		
		
        aranewMIB MODULE-IDENTITY
      		LAST-UPDATED  "200712101120Z"		-- December 10, 2007 at 11:20 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the ARANEW device."
      		REVISION  "200712101120Z"		-- December 10, 2007 at 11:20 GMT
      		DESCRIPTION
                "This is the original version of the MIB."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
 		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.
		
		
        -- 1.3.6.1.4.1.9839.2.1.1
        digitalObjects OBJECT IDENTIFIER ::= { aranewMIB 1 }

        -- 1.3.6.1.4.1.9839.2.1.1.1
        pump-on OBJECT-TYPE
                    SYNTAX Integer32 (0..1)
                    UNITS "N/A"
                    MAX-ACCESS read-only
                    STATUS current
                    DESCRIPTION "PUMP STATUS"
                    ::= { digitalObjects 1 }

        -- 1.3.6.1.4.1.9839.2.1.1.2
        compress1 OBJECT-TYPE
                    SYNTAX Integer32 (0..1)
                    UNITS "N/A"
                    MAX-ACCESS read-only
                    STATUS current
                    DESCRIPTION "COMPRESSOR 1"
                    ::= { digitalObjects 2 }

        -- 1.3.6.1.4.1.9839.2.1.1.3
        compress2 OBJECT-TYPE
                    SYNTAX Integer32 (0..1)
                    UNITS "N/A"
                    MAX-ACCESS read-only
                    STATUS current
                    DESCRIPTION "COMPRESSOR 2"
                    ::= { digitalObjects 3 }

        -- 1.3.6.1.4.1.9839.2.1.1.4
        compress3 OBJECT-TYPE
                    SYNTAX Integer32 (0..1)
                    UNITS "N/A"
                    MAX-ACCESS read-only
                    STATUS current
                    DESCRIPTION "COMPRESSOR 3"
                    ::= { digitalObjects 4 }

        -- 1.3.6.1.4.1.9839.2.1.1.5
        compress4 OBJECT-TYPE
                    SYNTAX Integer32 (0..1)
                    UNITS "N/A"
                    MAX-ACCESS read-only
                    STATUS current
                    DESCRIPTION "COMPRESSOR 4"
                    ::= { digitalObjects 5 }

        -- 1.3.6.1.4.1.9839.2.1.1.6
        pompa1 OBJECT-TYPE
                    SYNTAX Integer32 (0..1)
                    UNITS "N/A"
                    MAX-ACCESS read-only
                    STATUS current
                    DESCRIPTION "PUMP 1"
                    ::= { digitalObjects 6 }

        -- 1.3.6.1.4.1.9839.2.1.1.7
        pompa2 OBJECT-TYPE
                    SYNTAX Integer32 (0..1)
                    UNITS "N/A"
                    MAX-ACCESS read-only
                    STATUS current
                    DESCRIPTION "PUMP 2"
                    ::= { digitalObjects 7 }

        -- 1.3.6.1.4.1.9839.2.1.1.8
        etvl-circ1 OBJECT-TYPE
                    SYNTAX Integer32 (0..1)
                    UNITS "N/A"
                    MAX-ACCESS read-only
                    STATUS current
                    DESCRIPTION "CIRCUIT 1 REFRIGERANT SHUT-OFF VALVE"
                    ::= { digitalObjects 8 }

        -- 1.3.6.1.4.1.9839.2.1.1.9
        etvl-circ2 OBJECT-TYPE
                    SYNTAX Integer32 (0..1)
                    UNITS "N/A"
                    MAX-ACCESS read-only
                    STATUS current
                    DESCRIPTION "CIRCUIT 2 REFRIGERANT SHUT-OFF VALVE"
                    ::= { digitalObjects 9 }

        -- 1.3.6.1.4.1.9839.2.1.1.10
        heat-rec-on OBJECT-TYPE
                    SYNTAX Integer32 (0..1)
                    UNITS "N/A"
                    MAX-ACCESS read-only
                    STATUS current
                    DESCRIPTION "TOTAL HEAT RECOVERY"
                    ::= { digitalObjects 10 }

        -- 1.3.6.1.4.1.9839.2.1.1.11
        heater OBJECT-TYPE
                    SYNTAX Integer32 (0..1)
                    UNITS "N/A"
                    MAX-ACCESS read-only
                    STATUS current
                    DESCRIPTION "ANTIFREEZE HEATER"
                    ::= { digitalObjects 11 }

        -- 1.3.6.1.4.1.9839.2.1.1.12
        out-cv-y OBJECT-TYPE
                    SYNTAX Integer32 (0..1)
                    UNITS "N/A"
                    MAX-ACCESS read-only
                    STATUS current
                    DESCRIPTION "FAN ON - STAR CONNECTION"
                    ::= { digitalObjects 12 }

        -- 1.3.6.1.4.1.9839.2.1.1.13
        out-cv-d OBJECT-TYPE
                    SYNTAX Integer32 (0..1)
                    UNITS "N/A"
                    MAX-ACCESS read-only
                    STATUS current
                    DESCRIPTION "FAN ON - DELTA CONNECTION"
                    ::= { digitalObjects 13 }

        -- 1.3.6.1.4.1.9839.2.1.1.14
        defrost-circ1 OBJECT-TYPE
                    SYNTAX Integer32 (0..1)
                    UNITS "N/A"
                    MAX-ACCESS read-only
                    STATUS current
                    DESCRIPTION "CIRCUIT 1 DEFROST"
                    ::= { digitalObjects 14 }

        -- 1.3.6.1.4.1.9839.2.1.1.15
        defrost-circ2 OBJECT-TYPE
                    SYNTAX Integer32 (0..1)
                    UNITS "N/A"
                    MAX-ACCESS read-only
                    STATUS current
                    DESCRIPTION "CIRCUIT 2 DEFROST"
                    ::= { digitalObjects 15 }

        -- 1.3.6.1.4.1.9839.2.1.1.16
        low-pw-req OBJECT-TYPE
                    SYNTAX Integer32 (0..1)
                    UNITS "N/A"
                    MAX-ACCESS read-only
                    STATUS current
                    DESCRIPTION "LOW POWER CONSUMPTION MODE"
                    ::= { digitalObjects 16 }

        -- 1.3.6.1.4.1.9839.2.1.1.17
        inverno OBJECT-TYPE
                    SYNTAX Integer32 (0..1)
                    UNITS "N/A"
                    MAX-ACCESS read-only
                    STATUS current
                    DESCRIPTION "HEATING MODE"
                    ::= { digitalObjects 17 }

        -- 1.3.6.1.4.1.9839.2.1.1.18
        pompa-fc OBJECT-TYPE
                    SYNTAX Integer32 (0..1)
                    UNITS "N/A"
                    MAX-ACCESS read-only
                    STATUS current
                    DESCRIPTION "FREE-COOLING PUMP"
                    ::= { digitalObjects 18 }

        -- 1.3.6.1.4.1.9839.2.1.1.19
        mal-access OBJECT-TYPE
                    SYNTAX Integer32 (0..1)
                    UNITS "N/A"
                    MAX-ACCESS read-only
                    STATUS current
                    DESCRIPTION "ATTEMPT TO ACCESS WITH WRONG PASSWORD"
                    ::= { digitalObjects 19 }

        -- 1.3.6.1.4.1.9839.2.1.1.20
        mal-ht-win OBJECT-TYPE
                    SYNTAX Integer32 (0..1)
                    UNITS "N/A"
                    MAX-ACCESS read-only
                    STATUS current
                    DESCRIPTION "WATER IN TEMPERATURE ABOVE MAXIMUM LIMIT"
                    ::= { digitalObjects 20 }

        -- 1.3.6.1.4.1.9839.2.1.1.21
        mal-lt-win OBJECT-TYPE
                    SYNTAX Integer32 (0..1)
                    UNITS "N/A"
                    MAX-ACCESS read-only
                    STATUS current
                    DESCRIPTION "WATER IN TEMPERATURE BELOW LOW LIMIT"
                    ::= { digitalObjects 21 }

        -- 1.3.6.1.4.1.9839.2.1.1.22
        mal-flusso-h2o OBJECT-TYPE
                    SYNTAX Integer32 (0..1)
                    UNITS "N/A"
                    MAX-ACCESS read-only
                    STATUS current
                    DESCRIPTION "WATER FLOW FAILURE"
                    ::= { digitalObjects 22 }

        -- 1.3.6.1.4.1.9839.2.1.1.23
        mpreal-bp1 OBJECT-TYPE
                    SYNTAX Integer32 (0..1)
                    UNITS "N/A"
                    MAX-ACCESS read-only
                    STATUS current
                    DESCRIPTION "CIRCUIT 1 LOW PRESSURE PREALARM"
                    ::= { digitalObjects 23 }

        -- 1.3.6.1.4.1.9839.2.1.1.24
        mpreal-bp2 OBJECT-TYPE
                    SYNTAX Integer32 (0..1)
                    UNITS "N/A"
                    MAX-ACCESS read-only
                    STATUS current
                    DESCRIPTION "CIRCUIT 2 LOW PRESSURE PREALARM"
                    ::= { digitalObjects 24 }

        -- 1.3.6.1.4.1.9839.2.1.1.25
        al-bp1 OBJECT-TYPE
                    SYNTAX Integer32 (0..1)
                    UNITS "N/A"
                    MAX-ACCESS read-only
                    STATUS current
                    DESCRIPTION "CIRCUIT 1 LOW PRESSURE ALARM"
                    ::= { digitalObjects 25 }

        -- 1.3.6.1.4.1.9839.2.1.1.26
        al-bp2 OBJECT-TYPE
                    SYNTAX Integer32 (0..1)
                    UNITS "N/A"
                    MAX-ACCESS read-only
                    STATUS current
                    DESCRIPTION "CIRCUIT 2 LOW PRESSURE ALARM"
                    ::= { digitalObjects 26 }

        -- 1.3.6.1.4.1.9839.2.1.1.27
        mal-ap1 OBJECT-TYPE
                    SYNTAX Integer32 (0..1)
                    UNITS "N/A"
                    MAX-ACCESS read-only
                    STATUS current
                    DESCRIPTION "CIRCUIT 1 HIGH PRESSURE ALARM"
                    ::= { digitalObjects 27 }

        -- 1.3.6.1.4.1.9839.2.1.1.28
        mal-ap2 OBJECT-TYPE
                    SYNTAX Integer32 (0..1)
                    UNITS "N/A"
                    MAX-ACCESS read-only
                    STATUS current
                    DESCRIPTION "CIRCUIT 2 HIGH PRESSURE ALARM"
                    ::= { digitalObjects 28 }

        -- 1.3.6.1.4.1.9839.2.1.1.29
        mal-tpdgt OBJECT-TYPE
                    SYNTAX Integer32 (0..1)
                    UNITS "N/A"
                    MAX-ACCESS read-only
                    STATUS current
                    DESCRIPTION "COMPRESSOR 1 THERMOPROTECTOR ALARM"
                    ::= { digitalObjects 29 }

        -- 1.3.6.1.4.1.9839.2.1.1.30
        mal-tpdgt2 OBJECT-TYPE
                    SYNTAX Integer32 (0..1)
                    UNITS "N/A"
                    MAX-ACCESS read-only
                    STATUS current
                    DESCRIPTION "COMPRESSOR 2 THERMOPROTECTOR ALARM"
                    ::= { digitalObjects 30 }

        -- 1.3.6.1.4.1.9839.2.1.1.31
        mal-tpdgt3 OBJECT-TYPE
                    SYNTAX Integer32 (0..1)
                    UNITS "N/A"
                    MAX-ACCESS read-only
                    STATUS current
                    DESCRIPTION "COMPRESSOR 3 THERMOPROTECTOR ALARM"
                    ::= { digitalObjects 31 }

        -- 1.3.6.1.4.1.9839.2.1.1.32
        mal-tpdgt4 OBJECT-TYPE
                    SYNTAX Integer32 (0..1)
                    UNITS "N/A"
                    MAX-ACCESS read-only
                    STATUS current
                    DESCRIPTION "COMPRESSOR 4 THERMOPROTECTOR ALARM"
                    ::= { digitalObjects 32 }

        -- 1.3.6.1.4.1.9839.2.1.1.33
        mal-pompa1 OBJECT-TYPE
                    SYNTAX Integer32 (0..1)
                    UNITS "N/A"
                    MAX-ACCESS read-only
                    STATUS current
                    DESCRIPTION "PUMP 1 FAILURE"
                    ::= { digitalObjects 33 }

        -- 1.3.6.1.4.1.9839.2.1.1.34
        mal-pompa2 OBJECT-TYPE
                    SYNTAX Integer32 (0..1)
                    UNITS "N/A"
                    MAX-ACCESS read-only
                    STATUS current
                    DESCRIPTION "PUMP 2 FAILURE"
                    ::= { digitalObjects 34 }

        -- 1.3.6.1.4.1.9839.2.1.1.35
        mal-pompafc OBJECT-TYPE
                    SYNTAX Integer32 (0..1)
                    UNITS "N/A"
                    MAX-ACCESS read-only
                    STATUS current
                    DESCRIPTION "FREE-COOLING PUMP FAILURE"
                    ::= { digitalObjects 35 }

        -- 1.3.6.1.4.1.9839.2.1.1.38
        al-hr OBJECT-TYPE
                    SYNTAX Integer32 (0..1)
                    UNITS "N/A"
                    MAX-ACCESS read-only
                    STATUS current
                    DESCRIPTION "HEAT RECOVERY FAILURE"
                    ::= { digitalObjects 38 }

        -- 1.3.6.1.4.1.9839.2.1.1.39
        preal-hr OBJECT-TYPE
                    SYNTAX Integer32 (0..1)
                    UNITS "N/A"
                    MAX-ACCESS read-only
                    STATUS current
                    DESCRIPTION "HEAT RECOVERY FAILURE PREALARM"
                    ::= { digitalObjects 39 }

        -- 1.3.6.1.4.1.9839.2.1.1.40
        mal-lan OBJECT-TYPE
                    SYNTAX Integer32 (0..1)
                    UNITS "N/A"
                    MAX-ACCESS read-only
                    STATUS current
                    DESCRIPTION "LAN FAILURE"
                    ::= { digitalObjects 40 }

        -- 1.3.6.1.4.1.9839.2.1.1.41
        mal-sonda-twin OBJECT-TYPE
                    SYNTAX Integer32 (0..1)
                    UNITS "N/A"
                    MAX-ACCESS read-only
                    STATUS current
                    DESCRIPTION "WATER IN TEMPERATURE SENSOR FAILURE"
                    ::= { digitalObjects 41 }

        -- 1.3.6.1.4.1.9839.2.1.1.42
        mal-sonda-twout OBJECT-TYPE
                    SYNTAX Integer32 (0..1)
                    UNITS "N/A"
                    MAX-ACCESS read-only
                    STATUS current
                    DESCRIPTION "WATER OUT TEMPERATURE SENSOR FAILURE"
                    ::= { digitalObjects 42 }

        -- 1.3.6.1.4.1.9839.2.1.1.43
        mal-sonda-twaccu OBJECT-TYPE
                    SYNTAX Integer32 (0..1)
                    UNITS "N/A"
                    MAX-ACCESS read-only
                    STATUS current
                    DESCRIPTION "WATER TANK TEMPERATURE SENSOR FAILURE"
                    ::= { digitalObjects 43 }

        -- 1.3.6.1.4.1.9839.2.1.1.44
        mal-sonda-te OBJECT-TYPE
                    SYNTAX Integer32 (0..1)
                    UNITS "N/A"
                    MAX-ACCESS read-only
                    STATUS current
                    DESCRIPTION "EXTERNAL AIR TEMPERATURE SENSOR FAILURE"
                    ::= { digitalObjects 44 }

        -- 1.3.6.1.4.1.9839.2.1.1.45
        mal-sonda-tc1 OBJECT-TYPE
                    SYNTAX Integer32 (0..1)
                    UNITS "N/A"
                    MAX-ACCESS read-only
                    STATUS current
                    DESCRIPTION "CIRCUIT 1 CONDENSING TEMPERATURE SENSOR FAILURE"
                    ::= { digitalObjects 45 }

        -- 1.3.6.1.4.1.9839.2.1.1.46
        mal-sonda-tc2 OBJECT-TYPE
                    SYNTAX Integer32 (0..1)
                    UNITS "N/A"
                    MAX-ACCESS read-only
                    STATUS current
                    DESCRIPTION "CIRCUIT 2 CONDENSING TEMPERATURE SENSOR FAILURE"
                    ::= { digitalObjects 46 }

        -- 1.3.6.1.4.1.9839.2.1.1.47
        mal-sonda-pc1 OBJECT-TYPE
                    SYNTAX Integer32 (0..1)
                    UNITS "N/A"
                    MAX-ACCESS read-only
                    STATUS current
                    DESCRIPTION "CIRCUIT 1 CONDENSING PRESSURE SENSOR FAILURE"
                    ::= { digitalObjects 47 }

        -- 1.3.6.1.4.1.9839.2.1.1.48
        mal-sonda-pc2 OBJECT-TYPE
                    SYNTAX Integer32 (0..1)
                    UNITS "N/A"
                    MAX-ACCESS read-only
                    STATUS current
                    DESCRIPTION "CIRCUIT 2 CONDENSING PRESSURE SENSOR FAILURE"
                    ::= { digitalObjects 48 }

        -- 1.3.6.1.4.1.9839.2.1.1.49
        mal-sonda-pev1 OBJECT-TYPE
                    SYNTAX Integer32 (0..1)
                    UNITS "N/A"
                    MAX-ACCESS read-only
                    STATUS current
                    DESCRIPTION "CIRCUIT 1 EVAPORATING PRESSURE SENSOR FAILURE"
                    ::= { digitalObjects 49 }

        -- 1.3.6.1.4.1.9839.2.1.1.50
        mal-sonda-pev2 OBJECT-TYPE
                    SYNTAX Integer32 (0..1)
                    UNITS "N/A"
                    MAX-ACCESS read-only
                    STATUS current
                    DESCRIPTION "CIRCUIT 2 EVAPORATING PRESSURE SENSOR FAILURE"
                    ::= { digitalObjects 50 }

        -- 1.3.6.1.4.1.9839.2.1.1.51
        glb-al OBJECT-TYPE
                    SYNTAX Integer32 (0..1)
                    UNITS "N/A"
                    MAX-ACCESS read-only
                    STATUS current
                    DESCRIPTION "GENERAL ALARM"
                    ::= { digitalObjects 51 }

        -- 1.3.6.1.4.1.9839.2.1.1.52
        or-al-2lev OBJECT-TYPE
                    SYNTAX Integer32 (0..1)
                    UNITS "N/A"
                    MAX-ACCESS read-only
                    STATUS current
                    DESCRIPTION "SECOND LEVEL ALARM"
                    ::= { digitalObjects 52 }

        -- 1.3.6.1.4.1.9839.2.1.1.53
        mal-ore-compr1 OBJECT-TYPE
                    SYNTAX Integer32 (0..1)
                    UNITS "N/A"
                    MAX-ACCESS read-only
                    STATUS current
                    DESCRIPTION "COMPRESSOR 1 EXCEEDED MAXIMUM RUN HOURS"
                    ::= { digitalObjects 53 }

        -- 1.3.6.1.4.1.9839.2.1.1.54
        mal-ore-compr2 OBJECT-TYPE
                    SYNTAX Integer32 (0..1)
                    UNITS "N/A"
                    MAX-ACCESS read-only
                    STATUS current
                    DESCRIPTION "COMPRESSOR 2 EXCEEDED MAXIMUM RUN HOURS"
                    ::= { digitalObjects 54 }

        -- 1.3.6.1.4.1.9839.2.1.1.55
        mal-ore-compr3 OBJECT-TYPE
                    SYNTAX Integer32 (0..1)
                    UNITS "N/A"
                    MAX-ACCESS read-only
                    STATUS current
                    DESCRIPTION "COMPRESSOR 3 EXCEEDED MAXIMUM RUN HOURS"
                    ::= { digitalObjects 55 }

        -- 1.3.6.1.4.1.9839.2.1.1.56
        mal-ore-compr4 OBJECT-TYPE
                    SYNTAX Integer32 (0..1)
                    UNITS "N/A"
                    MAX-ACCESS read-only
                    STATUS current
                    DESCRIPTION "COMPRESSOR 4 EXCEEDED MAXIMUM RUN HOURS"
                    ::= { digitalObjects 56 }

        -- 1.3.6.1.4.1.9839.2.1.1.57
        mal-ore-pump1 OBJECT-TYPE
                    SYNTAX Integer32 (0..1)
                    UNITS "N/A"
                    MAX-ACCESS read-only
                    STATUS current
                    DESCRIPTION "PUMP 1 EXCEEDED MAXIMUM RUN HOURS"
                    ::= { digitalObjects 57 }

        -- 1.3.6.1.4.1.9839.2.1.1.58
        mal-ore-pump2 OBJECT-TYPE
                    SYNTAX Integer32 (0..1)
                    UNITS "N/A"
                    MAX-ACCESS read-only
                    STATUS current
                    DESCRIPTION "PUMP 2 EXCEEDED MAXIMUM RUN HOURS"
                    ::= { digitalObjects 58 }

        -- 1.3.6.1.4.1.9839.2.1.1.59
        k-est-inv OBJECT-TYPE
                    SYNTAX Integer32 (0..1)
                    UNITS "N/A"
                    MAX-ACCESS read-write
                    STATUS current
                    DESCRIPTION "SUMMER-WINTER MODE"
                    ::= { digitalObjects 59 }

        -- 1.3.6.1.4.1.9839.2.1.1.60
        k-syson OBJECT-TYPE
                    SYNTAX Integer32 (0..1)
                    UNITS "N/A"
                    MAX-ACCESS read-write
                    STATUS current
                    DESCRIPTION "UNIT ON/OFF"
                    ::= { digitalObjects 60 }

        -- 1.3.6.1.4.1.9839.2.1.1.61
        xs-res-al OBJECT-TYPE
                    SYNTAX Integer32 (0..1)
                    UNITS "N/A"
                    MAX-ACCESS read-write
                    STATUS current
                    DESCRIPTION "ALARM RESET"
                    ::= { digitalObjects 61 }

        -- 1.3.6.1.4.1.9839.2.1.1.62
        chg-pump OBJECT-TYPE
                    SYNTAX Integer32 (0..1)
                    UNITS "N/A"
                    MAX-ACCESS read-write
                    STATUS current
                    DESCRIPTION "PUMPS CHANGEOVER"
                    ::= { digitalObjects 62 }

        -- 1.3.6.1.4.1.9839.2.1.1.63
        sleep-mode OBJECT-TYPE
                    SYNTAX Integer32 (0..1)
                    UNITS "N/A"
                    MAX-ACCESS read-write
                    STATUS current
                    DESCRIPTION "SETBACK MODE"
                    ::= { digitalObjects 63 }

        -- 1.3.6.1.4.1.9839.2.1.1.65
        ab-mediath OBJECT-TYPE
                    SYNTAX Integer32 (0..1)
                    UNITS "N/A"
                    MAX-ACCESS read-write
                    STATUS current
                    DESCRIPTION "ENABLE MEAN VALUES REGULATION"
                    ::= { digitalObjects 65 }

        -- 1.3.6.1.4.1.9839.2.1.1.67
        range-t-waccu OBJECT-TYPE
                    SYNTAX Integer32 (0..1)
                    UNITS "N/A"
                    MAX-ACCESS read-only
                    STATUS current
                    DESCRIPTION "PRESENCE OF WATER TANK TEMPERATURE SENSOR"
                    ::= { digitalObjects 67 }

        -- 1.3.6.1.4.1.9839.2.1.1.68
        range-p-cond OBJECT-TYPE
                    SYNTAX Integer32 (0..1)
                    UNITS "N/A"
                    MAX-ACCESS read-only
                    STATUS current
                    DESCRIPTION "PRESENCE OF CONDENSING PRESSURE SENSORS"
                    ::= { digitalObjects 68 }

        -- 1.3.6.1.4.1.9839.2.1.1.69
        range-p-evap OBJECT-TYPE
                    SYNTAX Integer32 (0..1)
                    UNITS "N/A"
                    MAX-ACCESS read-only
                    STATUS current
                    DESCRIPTION "PRESENCE OF EVAPORATING PRESSURE SENSORS"
                    ::= { digitalObjects 69 }

        -- 1.3.6.1.4.1.9839.2.1.1.71
        pd-fail-circ1 OBJECT-TYPE
                    SYNTAX Integer32 (0..1)
                    UNITS "N/A"
                    MAX-ACCESS read-only
                    STATUS current
                    DESCRIPTION "CIRCUIT 1 PUMPDOWN FAILURE"
                    ::= { digitalObjects 71 }

        -- 1.3.6.1.4.1.9839.2.1.1.72
        pd-fail-circ2 OBJECT-TYPE
                    SYNTAX Integer32 (0..1)
                    UNITS "N/A"
                    MAX-ACCESS read-only
                    STATUS current
                    DESCRIPTION "CIRCUIT 2 PUMPDOWN FAILURE"
                    ::= { digitalObjects 72 }

        -- 1.3.6.1.4.1.9839.2.1.1.73
        circ1-malfunction OBJECT-TYPE
                    SYNTAX Integer32 (0..1)
                    UNITS "N/A"
                    MAX-ACCESS read-only
                    STATUS current
                    DESCRIPTION "CIRCUIT 1 MALFUNCTION"
                    ::= { digitalObjects 73 }

        -- 1.3.6.1.4.1.9839.2.1.1.74
        circ2-malfunction OBJECT-TYPE
                    SYNTAX Integer32 (0..1)
                    UNITS "N/A"
                    MAX-ACCESS read-only
                    STATUS current
                    DESCRIPTION "CIRCUIT 2 MALFUNCTION"
                    ::= { digitalObjects 74 }

        -- 1.3.6.1.4.1.9839.2.1.1.76
        compr1-limit OBJECT-TYPE
                    SYNTAX Integer32 (0..1)
                    UNITS "N/A"
                    MAX-ACCESS read-only
                    STATUS current
                    DESCRIPTION "COMPRESSOR 1 LIMIT"
                    ::= { digitalObjects 76 }

        -- 1.3.6.1.4.1.9839.2.1.1.77
        compr2-limit OBJECT-TYPE
                    SYNTAX Integer32 (0..1)
                    UNITS "N/A"
                    MAX-ACCESS read-only
                    STATUS current
                    DESCRIPTION "COMPRESSOR 2 LIMIT"
                    ::= { digitalObjects 77 }

        -- 1.3.6.1.4.1.9839.2.1.1.78
        defrost-np OBJECT-TYPE
                    SYNTAX Integer32 (0..1)
                    UNITS "N/A"
                    MAX-ACCESS read-only
                    STATUS current
                    DESCRIPTION "DEFROST NOT POSSIBLE"
                    ::= { digitalObjects 78 }



        -- 1.3.6.1.4.1.9839.2.1.2
        analogObjects OBJECT IDENTIFIER ::= { aranewMIB 2 }

        -- 1.3.6.1.4.1.9839.2.1.2.1
        temp-wout OBJECT-TYPE
                    SYNTAX Integer32 (-32767..32767)
                    UNITS "degrees C"
                    MAX-ACCESS read-only
                    STATUS current
                    DESCRIPTION "WATER OUT TEMPERATURE"
                    ::= { analogObjects 1 }

        -- 1.3.6.1.4.1.9839.2.1.2.2
        t-wout-regol OBJECT-TYPE
                    SYNTAX Integer32 (-32767..32767)
                    UNITS "degrees C"
                    MAX-ACCESS read-only
                    STATUS current
                    DESCRIPTION "REGULATION WATER OUT TEMPERATURE"
                    ::= { analogObjects 2 }

        -- 1.3.6.1.4.1.9839.2.1.2.3
        temp-win OBJECT-TYPE
                    SYNTAX Integer32 (-32767..32767)
                    UNITS "degrees C"
                    MAX-ACCESS read-only
                    STATUS current
                    DESCRIPTION "WATER IN TEMPERATURE"
                    ::= { analogObjects 3 }

        -- 1.3.6.1.4.1.9839.2.1.2.4
        temp-waccu OBJECT-TYPE
                    SYNTAX Integer32 (-32767..32767)
                    UNITS "degrees C"
                    MAX-ACCESS read-only
                    STATUS current
                    DESCRIPTION "WATER TANK TEMPERATURE"
                    ::= { analogObjects 4 }

        -- 1.3.6.1.4.1.9839.2.1.2.5
        temp-ext OBJECT-TYPE
                    SYNTAX Integer32 (-32767..32767)
                    UNITS "degrees C"
                    MAX-ACCESS read-only
                    STATUS current
                    DESCRIPTION "EXTERNAL AIR TEMPERATURE"
                    ::= { analogObjects 5 }

        -- 1.3.6.1.4.1.9839.2.1.2.6
        temp-cond1 OBJECT-TYPE
                    SYNTAX Integer32 (-32767..32767)
                    UNITS "degrees C"
                    MAX-ACCESS read-only
                    STATUS current
                    DESCRIPTION "CIRCUIT 1 CONDENSING TEMPERATURE"
                    ::= { analogObjects 6 }

        -- 1.3.6.1.4.1.9839.2.1.2.7
        temp-cond2 OBJECT-TYPE
                    SYNTAX Integer32 (-32767..32767)
                    UNITS "degrees C"
                    MAX-ACCESS read-only
                    STATUS current
                    DESCRIPTION "CIRCUIT 2 CONDENSING TEMPERATURE"
                    ::= { analogObjects 7 }

        -- 1.3.6.1.4.1.9839.2.1.2.8
        temp-evap1 OBJECT-TYPE
                    SYNTAX Integer32 (-32767..32767)
                    UNITS "degrees C"
                    MAX-ACCESS read-only
                    STATUS current
                    DESCRIPTION "CIRCUIT 1 EVAPORATING TEMPERATURE"
                    ::= { analogObjects 8 }

        -- 1.3.6.1.4.1.9839.2.1.2.9
        temp-evap2 OBJECT-TYPE
                    SYNTAX Integer32 (-32767..32767)
                    UNITS "degrees C"
                    MAX-ACCESS read-only
                    STATUS current
                    DESCRIPTION "CIRCUIT 2 EVAPORATING TEMPERATURE"
                    ::= { analogObjects 9 }

        -- 1.3.6.1.4.1.9839.2.1.2.10
        xv-press-cond1 OBJECT-TYPE
                    SYNTAX Integer32 (-32767..32767)
                    UNITS "bar"
                    MAX-ACCESS read-only
                    STATUS current
                    DESCRIPTION "CIRCUIT 1 CONDENSING PRESSURE"
                    ::= { analogObjects 10 }

        -- 1.3.6.1.4.1.9839.2.1.2.11
        xv-press-cond2 OBJECT-TYPE
                    SYNTAX Integer32 (-32767..32767)
                    UNITS "bar"
                    MAX-ACCESS read-only
                    STATUS current
                    DESCRIPTION "CIRCUIT 2 CONDENSING PRESSURE"
                    ::= { analogObjects 11 }

        -- 1.3.6.1.4.1.9839.2.1.2.12
        xv-press-evap1 OBJECT-TYPE
                    SYNTAX Integer32 (-32767..32767)
                    UNITS "bar"
                    MAX-ACCESS read-only
                    STATUS current
                    DESCRIPTION "CIRCUIT 1 EVAPORATING PRESSURE"
                    ::= { analogObjects 12 }

        -- 1.3.6.1.4.1.9839.2.1.2.13
        xv-press-evap2 OBJECT-TYPE
                    SYNTAX Integer32 (-32767..32767)
                    UNITS "bar"
                    MAX-ACCESS read-only
                    STATUS current
                    DESCRIPTION "CIRCUIT 2 EVAPORATING PRESSURE"
                    ::= { analogObjects 13 }

        -- 1.3.6.1.4.1.9839.2.1.2.14
        x-rampa-vent2 OBJECT-TYPE
                    SYNTAX Integer32 (-32767..32767)
                    UNITS "%"
                    MAX-ACCESS read-only
                    STATUS current
                    DESCRIPTION "FAN MODULATING RAMP"
                    ::= { analogObjects 14 }

        -- 1.3.6.1.4.1.9839.2.1.2.15
        t-set-regol OBJECT-TYPE
                    SYNTAX Integer32 (-32767..32767)
                    UNITS "degrees C"
                    MAX-ACCESS read-only
                    STATUS current
                    DESCRIPTION "LEAVING TEMP.REGULATION SETPOINT"
                    ::= { analogObjects 15 }

        -- 1.3.6.1.4.1.9839.2.1.2.16
        zona-neutra OBJECT-TYPE
                    SYNTAX Integer32 (-32767..32767)
                    UNITS "degrees C"
                    MAX-ACCESS read-only
                    STATUS current
                    DESCRIPTION "MAX HYSTERESI"
                    ::= { analogObjects 16 }

        -- 1.3.6.1.4.1.9839.2.1.2.17
        ofs-spv OBJECT-TYPE
                    SYNTAX Integer32 (-32767..32767)
                    UNITS "N/A"
                    MAX-ACCESS read-write
                    STATUS current
                    DESCRIPTION "OFFSET FOR SERIAL COMMUNICATION"
                    ::= { analogObjects 17 }

        -- 1.3.6.1.4.1.9839.2.1.2.18
        t-set-e OBJECT-TYPE
                    SYNTAX Integer32 (-32767..32767)
                    UNITS "degrees C"
                    MAX-ACCESS read-write
                    STATUS current
                    DESCRIPTION "SUMMER SETPOINT"
                    ::= { analogObjects 18 }

        -- 1.3.6.1.4.1.9839.2.1.2.19
        t-set-d OBJECT-TYPE
                    SYNTAX Integer32 (-32767..32767)
                    UNITS "degrees C"
                    MAX-ACCESS read-write
                    STATUS current
                    DESCRIPTION "SUMMER SECOND SETPOINT"
                    ::= { analogObjects 19 }

        -- 1.3.6.1.4.1.9839.2.1.2.20
        t-set-sm OBJECT-TYPE
                    SYNTAX Integer32 (-32767..32767)
                    UNITS "degrees C"
                    MAX-ACCESS read-write
                    STATUS current
                    DESCRIPTION "SETBACK MODE SUMMER SETPOINT"
                    ::= { analogObjects 20 }

        -- 1.3.6.1.4.1.9839.2.1.2.21
        t-set-i OBJECT-TYPE
                    SYNTAX Integer32 (-32767..32767)
                    UNITS "degrees C"
                    MAX-ACCESS read-write
                    STATUS current
                    DESCRIPTION "WINTER SETPOINT"
                    ::= { analogObjects 21 }

        -- 1.3.6.1.4.1.9839.2.1.2.22
        t-set-c-sm OBJECT-TYPE
                    SYNTAX Integer32 (-32767..32767)
                    UNITS "degrees C"
                    MAX-ACCESS read-write
                    STATUS current
                    DESCRIPTION "SETBACK MODE WINTER SETPOINT"
                    ::= { analogObjects 22 }

        -- 1.3.6.1.4.1.9839.2.1.2.23
        set-ht-win-e OBJECT-TYPE
                    SYNTAX Integer32 (-32767..32767)
                    UNITS "degrees C"
                    MAX-ACCESS read-write
                    STATUS current
                    DESCRIPTION "WATER IN HIGH TEMPERATURE ALARM THRESHOLD-SUMMER"
                    ::= { analogObjects 23 }

        -- 1.3.6.1.4.1.9839.2.1.2.24
        set-lt-win-e OBJECT-TYPE
                    SYNTAX Integer32 (-32767..32767)
                    UNITS "degrees C"
                    MAX-ACCESS read-write
                    STATUS current
                    DESCRIPTION "WATER IN LOW TEMPERATURE ALARM THRESHOLD-SUMMER"
                    ::= { analogObjects 24 }

        -- 1.3.6.1.4.1.9839.2.1.2.25
        set-ht-win-i OBJECT-TYPE
                    SYNTAX Integer32 (-32767..32767)
                    UNITS "degrees C"
                    MAX-ACCESS read-write
                    STATUS current
                    DESCRIPTION "WATER IN HIGH TEMPERATURE ALARM THRESHOLD-WINTER"
                    ::= { analogObjects 25 }

        -- 1.3.6.1.4.1.9839.2.1.2.26
        set-lt-win-i OBJECT-TYPE
                    SYNTAX Integer32 (-32767..32767)
                    UNITS "degrees C"
                    MAX-ACCESS read-write
                    STATUS current
                    DESCRIPTION "WATER IN LOW TEMPERATURE ALARM THRESHOLD-WINTER"
                    ::= { analogObjects 26 }

        -- 1.3.6.1.4.1.9839.2.1.2.33
        set-delta-fc OBJECT-TYPE
                    SYNTAX Integer32 (-32767..32767)
                    UNITS "degrees C"
                    MAX-ACCESS read-write
                    STATUS current
                    DESCRIPTION "FREECOOLING DELTAT SETPOINT"
                    ::= { analogObjects 33 }



        -- 1.3.6.1.4.1.9839.2.1.3
        integerObjects OBJECT IDENTIFIER ::= { aranewMIB 3 }

        -- 1.3.6.1.4.1.9839.2.1.3.1
        ore-compr1 OBJECT-TYPE
                    SYNTAX Integer32 (-32767..32767)
                    UNITS "h"
                    MAX-ACCESS read-only
                    STATUS current
                    DESCRIPTION "COMPRESSOR 1 RUN HOURS"
                    ::= { integerObjects 1 }

        -- 1.3.6.1.4.1.9839.2.1.3.2
        ore-compr2 OBJECT-TYPE
                    SYNTAX Integer32 (-32767..32767)
                    UNITS "h"
                    MAX-ACCESS read-only
                    STATUS current
                    DESCRIPTION "COMPRESSOR 2 RUN HOURS"
                    ::= { integerObjects 2 }

        -- 1.3.6.1.4.1.9839.2.1.3.3
        ore-compr3 OBJECT-TYPE
                    SYNTAX Integer32 (-32767..32767)
                    UNITS "h"
                    MAX-ACCESS read-only
                    STATUS current
                    DESCRIPTION "COMPRESSOR 3 RUN HOURS"
                    ::= { integerObjects 3 }

        -- 1.3.6.1.4.1.9839.2.1.3.4
        ore-compr4 OBJECT-TYPE
                    SYNTAX Integer32 (-32767..32767)
                    UNITS "h"
                    MAX-ACCESS read-only
                    STATUS current
                    DESCRIPTION "COMPRESSOR 4 RUN HOURS"
                    ::= { integerObjects 4 }

        -- 1.3.6.1.4.1.9839.2.1.3.5
        ore-pump1 OBJECT-TYPE
                    SYNTAX Integer32 (-32767..32767)
                    UNITS "h"
                    MAX-ACCESS read-only
                    STATUS current
                    DESCRIPTION "PUMP 1 RUN HOURS"
                    ::= { integerObjects 5 }

        -- 1.3.6.1.4.1.9839.2.1.3.6
        ore-pump2 OBJECT-TYPE
                    SYNTAX Integer32 (-32767..32767)
                    UNITS "h"
                    MAX-ACCESS read-only
                    STATUS current
                    DESCRIPTION "PUMP 2 RUN HOURS"
                    ::= { integerObjects 6 }

        -- 1.3.6.1.4.1.9839.2.1.3.7
        ore-pumpfc OBJECT-TYPE
                    SYNTAX Integer32 (-32767..32767)
                    UNITS "h"
                    MAX-ACCESS read-only
                    STATUS current
                    DESCRIPTION "FREE-COOLING PUMP RUN HOURS"
                    ::= { integerObjects 7 }

        -- 1.3.6.1.4.1.9839.2.1.3.8
        spunti-c1 OBJECT-TYPE
                    SYNTAX Integer32 (-32767..32767)
                    UNITS "n"
                    MAX-ACCESS read-only
                    STATUS current
                    DESCRIPTION "COMPRESSOR 1 STARTING NUMBER"
                    ::= { integerObjects 8 }

        -- 1.3.6.1.4.1.9839.2.1.3.9
        spunti10k-c1 OBJECT-TYPE
                    SYNTAX Integer32 (-32767..32767)
                    UNITS "nx1000"
                    MAX-ACCESS read-only
                    STATUS current
                    DESCRIPTION "COMPRESSOR 1 STARTING NUMBER (x1000)"
                    ::= { integerObjects 9 }

        -- 1.3.6.1.4.1.9839.2.1.3.10
        spunti-c2 OBJECT-TYPE
                    SYNTAX Integer32 (-32767..32767)
                    UNITS "n"
                    MAX-ACCESS read-only
                    STATUS current
                    DESCRIPTION "COMPRESSOR 2 STARTING NUMBER"
                    ::= { integerObjects 10 }

        -- 1.3.6.1.4.1.9839.2.1.3.11
        spunti10k-c2 OBJECT-TYPE
                    SYNTAX Integer32 (-32767..32767)
                    UNITS "nx1000"
                    MAX-ACCESS read-only
                    STATUS current
                    DESCRIPTION "COMPRESSOR 2 STARTING NUMBER (x1000)"
                    ::= { integerObjects 11 }

        -- 1.3.6.1.4.1.9839.2.1.3.12
        spunti-c3 OBJECT-TYPE
                    SYNTAX Integer32 (-32767..32767)
                    UNITS "n"
                    MAX-ACCESS read-only
                    STATUS current
                    DESCRIPTION "COMPRESSOR 3 STARTING NUMBER"
                    ::= { integerObjects 12 }

        -- 1.3.6.1.4.1.9839.2.1.3.13
        spunti10k-c3 OBJECT-TYPE
                    SYNTAX Integer32 (-32767..32767)
                    UNITS "nx1000"
                    MAX-ACCESS read-only
                    STATUS current
                    DESCRIPTION "COMPRESSOR 3 STARTING NUMBER (x1000)"
                    ::= { integerObjects 13 }

        -- 1.3.6.1.4.1.9839.2.1.3.14
        spunti-c4 OBJECT-TYPE
                    SYNTAX Integer32 (-32767..32767)
                    UNITS "n"
                    MAX-ACCESS read-only
                    STATUS current
                    DESCRIPTION "COMPRESSOR 4 STARTING NUMBER"
                    ::= { integerObjects 14 }

        -- 1.3.6.1.4.1.9839.2.1.3.15
        spunti10k-c4 OBJECT-TYPE
                    SYNTAX Integer32 (-32767..32767)
                    UNITS "nx1000"
                    MAX-ACCESS read-only
                    STATUS current
                    DESCRIPTION "COMPRESSOR 4 STARTING NUMBER (x1000)"
                    ::= { integerObjects 15 }

        -- 1.3.6.1.4.1.9839.2.1.3.16
        num-def-c1 OBJECT-TYPE
                    SYNTAX Integer32 (-32767..32767)
                    UNITS "n"
                    MAX-ACCESS read-only
                    STATUS current
                    DESCRIPTION "CIRCUIT 1 DEFROSTING NUMBER"
                    ::= { integerObjects 16 }

        -- 1.3.6.1.4.1.9839.2.1.3.17
        n10k-def-c1 OBJECT-TYPE
                    SYNTAX Integer32 (-32767..32767)
                    UNITS "nx1000"
                    MAX-ACCESS read-only
                    STATUS current
                    DESCRIPTION "CIRCUIT 1 DEFROSTING NUMBER (x1000)"
                    ::= { integerObjects 17 }

        -- 1.3.6.1.4.1.9839.2.1.3.18
        num-def-c2 OBJECT-TYPE
                    SYNTAX Integer32 (-32767..32767)
                    UNITS "n"
                    MAX-ACCESS read-only
                    STATUS current
                    DESCRIPTION "CIRCUIT 2 DEFROSTING NUMBER"
                    ::= { integerObjects 18 }

        -- 1.3.6.1.4.1.9839.2.1.3.19
        n10k-def-c2 OBJECT-TYPE
                    SYNTAX Integer32 (-32767..32767)
                    UNITS "nx1000"
                    MAX-ACCESS read-only
                    STATUS current
                    DESCRIPTION "CIRCUIT 2 DEFROSTING NUMBER (x1000)"
                    ::= { integerObjects 19 }

        -- 1.3.6.1.4.1.9839.2.1.3.20
        num-def-both OBJECT-TYPE
                    SYNTAX Integer32 (-32767..32767)
                    UNITS "n"
                    MAX-ACCESS read-only
                    STATUS current
                    DESCRIPTION "DEFROSTING TOTAL NUMBER"
                    ::= { integerObjects 20 }

        -- 1.3.6.1.4.1.9839.2.1.3.21
        n10k-def-both OBJECT-TYPE
                    SYNTAX Integer32 (-32767..32767)
                    UNITS "nx1000"
                    MAX-ACCESS read-only
                    STATUS current
                    DESCRIPTION "DEFROSTING TOTAL NUMBER (x1000)"
                    ::= { integerObjects 21 }

        -- 1.3.6.1.4.1.9839.2.1.3.22
        num-def-np OBJECT-TYPE
                    SYNTAX Integer32 (-32767..32767)
                    UNITS "n"
                    MAX-ACCESS read-only
                    STATUS current
                    DESCRIPTION "DEFROSTING FAILURE NUMBER"
                    ::= { integerObjects 22 }

        -- 1.3.6.1.4.1.9839.2.1.3.23
        n10k-def-np OBJECT-TYPE
                    SYNTAX Integer32 (-32767..32767)
                    UNITS "nx1000"
                    MAX-ACCESS read-only
                    STATUS current
                    DESCRIPTION "DEFROSTING FAILURE NUMBER (x1000)"
                    ::= { integerObjects 23 }

        -- 1.3.6.1.4.1.9839.2.1.3.35
        xdsp-dresa1 OBJECT-TYPE
                    SYNTAX Integer32 (-32767..32767)
                    UNITS "N/A"
                    MAX-ACCESS read-only
                    STATUS current
                    DESCRIPTION "RESERVED VARIABLE"
                    ::= { integerObjects 35 }

        -- 1.3.6.1.4.1.9839.2.1.3.36
        xdsp-dresa2 OBJECT-TYPE
                    SYNTAX Integer32 (-32767..32767)
                    UNITS "N/A"
                    MAX-ACCESS read-only
                    STATUS current
                    DESCRIPTION "RESERVED VARIABLE"
                    ::= { integerObjects 36 }

        -- 1.3.6.1.4.1.9839.2.1.3.37
        durata-defrost OBJECT-TYPE
                    SYNTAX Integer32 (-32767..32767)
                    UNITS "s"
                    MAX-ACCESS read-only
                    STATUS current
                    DESCRIPTION "LAST DEFROST TIME LENGHT"
                    ::= { integerObjects 37 }

        -- 1.3.6.1.4.1.9839.2.1.3.38
        restart-delay OBJECT-TYPE
                    SYNTAX Integer32 (-32767..32767)
                    UNITS "s"
                    MAX-ACCESS read-only
                    STATUS current
                    DESCRIPTION "RESTART DELAY"
                    ::= { integerObjects 38 }

        -- 1.3.6.1.4.1.9839.2.1.3.39
        regul-delay OBJECT-TYPE
                    SYNTAX Integer32 (-32767..32767)
                    UNITS "s"
                    MAX-ACCESS read-only
                    STATUS current
                    DESCRIPTION "REGULATION START TRANSITORY"
                    ::= { integerObjects 39 }

        -- 1.3.6.1.4.1.9839.2.1.3.40
        time-lowp OBJECT-TYPE
                    SYNTAX Integer32 (-32767..32767)
                    UNITS "s"
                    MAX-ACCESS read-write
                    STATUS current
                    DESCRIPTION "LOW PRESSURE DELAY"
                    ::= { integerObjects 40 }

        -- 1.3.6.1.4.1.9839.2.1.3.41
        alarm-delay OBJECT-TYPE
                    SYNTAX Integer32 (-32767..32767)
                    UNITS "min"
                    MAX-ACCESS read-write
                    STATUS current
                    DESCRIPTION "WATER HIGH-LOW TEMP.ALARM DELAY"
                    ::= { integerObjects 41 }

        -- 1.3.6.1.4.1.9839.2.1.3.43
        t-std-by OBJECT-TYPE
                    SYNTAX Integer32 (-32767..32767)
                    UNITS "h"
                    MAX-ACCESS read-write
                    STATUS current
                    DESCRIPTION "STAND-BY CYCLE TIME"
                    ::= { integerObjects 43 }

        -- 1.3.6.1.4.1.9839.2.1.3.44
        ore-rot-pompe OBJECT-TYPE
                    SYNTAX Integer32 (-32767..32767)
                    UNITS "h"
                    MAX-ACCESS read-write
                    STATUS current
                    DESCRIPTION "RUN STAND-BY PUMP CYCLE TIME"
                    ::= { integerObjects 44 }

        -- 1.3.6.1.4.1.9839.2.1.3.45
        ciclo-sm OBJECT-TYPE
                    SYNTAX Integer32 (-32767..32767)
                    UNITS "min"
                    MAX-ACCESS read-write
                    STATUS current
                    DESCRIPTION "SETBACK MODE CYCLE TIME"
                    ::= { integerObjects 45 }

        -- 1.3.6.1.4.1.9839.2.1.3.46
        set-hm100-c1 OBJECT-TYPE
                    SYNTAX Integer32 (-32767..32767)
                    UNITS "hx100"
                    MAX-ACCESS read-write
                    STATUS current
                    DESCRIPTION "COMPRESSOR 1 RUN HOURS ALARM LIMIT"
                    ::= { integerObjects 46 }

        -- 1.3.6.1.4.1.9839.2.1.3.47
        set-hm100-c2 OBJECT-TYPE
                    SYNTAX Integer32 (-32767..32767)
                    UNITS "hx100"
                    MAX-ACCESS read-write
                    STATUS current
                    DESCRIPTION "COMPRESSOR 2 RUN HOURS ALARM LIMIT"
                    ::= { integerObjects 47 }

        -- 1.3.6.1.4.1.9839.2.1.3.48
        set-hm100-c3 OBJECT-TYPE
                    SYNTAX Integer32 (-32767..32767)
                    UNITS "hx100"
                    MAX-ACCESS read-write
                    STATUS current
                    DESCRIPTION "COMPRESSOR 3 RUN HOURS ALARM LIMIT"
                    ::= { integerObjects 48 }

        -- 1.3.6.1.4.1.9839.2.1.3.49
        set-hm100-c4 OBJECT-TYPE
                    SYNTAX Integer32 (-32767..32767)
                    UNITS "hx100"
                    MAX-ACCESS read-write
                    STATUS current
                    DESCRIPTION "COMPRESSOR 4 RUN HOURS ALARM LIMIT"
                    ::= { integerObjects 49 }

        -- 1.3.6.1.4.1.9839.2.1.3.50
        set-hm100-p1 OBJECT-TYPE
                    SYNTAX Integer32 (-32767..32767)
                    UNITS "hx100"
                    MAX-ACCESS read-write
                    STATUS current
                    DESCRIPTION "PUMP 1 RUN HOURS ALARM LIMIT"
                    ::= { integerObjects 50 }

        -- 1.3.6.1.4.1.9839.2.1.3.51
        set-hm100-p2 OBJECT-TYPE
                    SYNTAX Integer32 (-32767..32767)
                    UNITS "hx100"
                    MAX-ACCESS read-write
                    STATUS current
                    DESCRIPTION "PUMP 2 RUN HOURS ALARM LIMIT"
                    ::= { integerObjects 51 }

        -- 1.3.6.1.4.1.9839.2.1.3.52
        set-hm100-pfc OBJECT-TYPE
                    SYNTAX Integer32 (-32767..32767)
                    UNITS "hx100"
                    MAX-ACCESS read-write
                    STATUS current
                    DESCRIPTION "FREECOOLING PUMP RUN HOURS ALARM LIMIT"
                    ::= { integerObjects 52 }


	
	END

--
-- CAREL-aranew.MIB
--
