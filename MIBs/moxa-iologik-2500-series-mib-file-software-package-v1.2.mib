-- *****************************************************************
-- Moxa Active Ethernet I/O Server MIB
--
-- 11-04-2009
--
-- Copyright (c) 2005 by Moxa Networking Co., Ltd.
-- All rights reserved.
-- *****************************************************************

MOXA-IO-2500-MIB DEFINITIONS ::= BEGIN
    IMPORTS
        enterprises, Unsigned32, Integer32, MODULE-IDENTITY, OBJECT-TYPE, NOTIFICATION-TYPE FROM SNMPv2-SMI;
   
-- 1.3.6.1.4.1.8691.10.2500
    ioLogik2500   MODULE-IDENTITY
    LAST-UPDATED "201705261100Z"
    ORGANIZATION "Moxa Automation,Inc."
    CONTACT-INFO
            "Postal: Moxa Automation,Inc.
             Fl.4, No.135,Lane 235,Pao-Chiao Rd.
             Shing Tien City,Taipei,Taiwan,R.O.C
             Tel: +866-2-89191230 "
    DESCRIPTION "The MIB module for Moxa ioLogik Active Ethernet I/O specific information"
	REVISION "201705261100Z"
    DESCRIPTION "Add counter overflag info" 
	
	REVISION "201705251800Z"
    DESCRIPTION "Add table of remote device from modbus tcp master" 
	
	REVISION "201705251400Z"
    DESCRIPTION "Add table of expansion" 
	
	REVISION "201604150500Z"
    DESCRIPTION "Rename description about burn-out" 
    
	REVISION "201510131700Z"
    DESCRIPTION "Updated version of this MIB (for simple web level3)" 

    REVISION "201406241700Z"
    DESCRIPTION "First version of this MIB"
           ::= { dataAcquisitionAndControl 2500 }    -- 1.3.6.1.4.1.8691.10.2500

-- 1.3.6.1.4.1.8691
    moxa OBJECT IDENTIFIER ::= { enterprises 8691 }

-- 1.3.6.1.4.1.8691.10
    dataAcquisitionAndControl OBJECT IDENTIFIER ::= { moxa 10 }

-- 1.3.6.1.4.1.8691.10.2500.1
    serverModel OBJECT-TYPE
        SYNTAX OCTET STRING
        MAX-ACCESS read-only
        STATUS current
        DESCRIPTION
            "The I/O server model"
        ::= { ioLogik2500 1 }

-- 1.3.6.1.4.1.8691.10.2500.2
    systemTime OBJECT-TYPE
        SYNTAX Integer32
        MAX-ACCESS read-only
        STATUS current
        DESCRIPTION
            "I/O server up time (in seconds)"
        ::= { ioLogik2500 2 }

-- 1.3.6.1.4.1.8691.10.2500.3
    firmwareVersion OBJECT-TYPE
        SYNTAX OCTET STRING
        MAX-ACCESS read-only
        STATUS current
        DESCRIPTION
            "The firmware version"
        ::= { ioLogik2500 3 }

-- 1.3.6.1.4.1.8691.10.2500.9
    messageCollect OBJECT IDENTIFIER ::= { ioLogik2500 9 }	
	
-- 1.3.6.1.4.1.8691.10.2500.9.1
    message1 OBJECT IDENTIFIER ::= { messageCollect 1}	

-- 1.3.6.1.4.1.8691.10.2500.9.1.1
    messageContent OBJECT IDENTIFIER ::= { message1 1}		

-- 1.3.6.1.4.1.8691.10.2500.9.1.1.1
    messageTrap NOTIFICATION-TYPE
	STATUS current
	DESCRIPTION 	"SNMP trap message"
	::= {messageContent 1}

----------------------------------------------------------------
-- 1.3.6.1.4.1.8691.10.2500.4

ioExpansionTable OBJECT-TYPE
		SYNTAX 			SEQUENCE OF ExpansionTableDef
		MAX-ACCESS 		not-accessible
		STATUS 			current
		DESCRIPTION		"I/O Expansion - status table"
		::= { ioLogik2500 4 }
		
ioExpansion OBJECT-TYPE
		SYNTAX 			ExpansionTableDef
		MAX-ACCESS 		not-accessible
		STATUS 			current
		DESCRIPTION		"The ioExpansion item"
		INDEX { ioExpansionIndex }
		::= { ioExpansionTable 1 }

ExpansionTableDef ::= SEQUENCE { 
    	ioExpansionIndex		INTEGER,
		ioExpansionStatus		INTEGER
		}  

ioExpansionIndex OBJECT-TYPE
		SYNTAX 			INTEGER (1..8)
		MAX-ACCESS 		read-only
		STATUS 			current
		DESCRIPTION		"I/O Expansion Index"
		::= { ioExpansion 1 }
		
ioExpansionStatus OBJECT-TYPE
		SYNTAX 			INTEGER (0..1)
		MAX-ACCESS 		read-only
		STATUS 			current
		DESCRIPTION		"I/O Expansion - status, 0=disconnected, 1=good "
		::= { ioExpansion 2 }
----------------------------------------------------------------	

----------------------------------------------------------------
-- 1.3.6.1.4.1.8691.10.2500.5

modbusTcpMasterDeviceTable OBJECT-TYPE
		SYNTAX 			SEQUENCE OF ModbusTCPMaster-DeviceTableDef
		MAX-ACCESS 		not-accessible
		STATUS 			current
		DESCRIPTION		"ModbusTCPMaster Remote Device Table"
		::= { ioLogik2500 5 }
		
modbusTcpMasterDevice OBJECT-TYPE
		SYNTAX 			ModbusTCPMaster-DeviceTableDef
		MAX-ACCESS 		not-accessible
		STATUS 			current
		DESCRIPTION		"ModbusTCPMaster Remote Device"
		INDEX { modbusTCPMaster-DeviceIndex }
		::= { modbusTcpMasterDeviceTable 1 }

ModbusTCPMaster-DeviceTableDef ::= SEQUENCE { 
    	modbusTCPMaster-DeviceIndex		INTEGER,
		modbusTCPMaster-DeviceStatus	INTEGER
		}  

modbusTCPMaster-DeviceIndex OBJECT-TYPE
		SYNTAX 			INTEGER (0..1)
		MAX-ACCESS 		read-only
		STATUS 			current
		DESCRIPTION		"ModbusTCPMaster Remote Device Index"
		::= { modbusTcpMasterDevice 1 }
		
modbusTCPMaster-DeviceStatus OBJECT-TYPE
		SYNTAX 			INTEGER (0..1)
		MAX-ACCESS 		read-only
		STATUS 			current
		DESCRIPTION		"ModbusTCPMaster Remote Device status, 0=disconnected, 1=good "
		::= { modbusTcpMasterDevice 2 }
----------------------------------------------------------------	

	
----------------------------------------------------------------
-- 1.3.6.1.4.1.8691.10.2500.10
    slot0-io OBJECT IDENTIFIER ::= { ioLogik2500 10 }
----------------------------------------------------------------
-- slot 0 DI
slot0-diTable OBJECT-TYPE
		SYNTAX 			SEQUENCE OF Slot0-diDef
		MAX-ACCESS 		not-accessible
		STATUS 			current
		DESCRIPTION		"The di channel table"
		::= { slot0-io 1 }

slot0-di OBJECT-TYPE
		SYNTAX 			Slot0-diDef
		MAX-ACCESS 		not-accessible
		STATUS 			current
		DESCRIPTION		"The di channel item"
		INDEX { slot0-diIndex }
		::= { slot0-diTable 1 }

Slot0-diDef ::= SEQUENCE { 
    	slot0-diIndex		INTEGER,
		slot0-diStatus		Unsigned32,
		slot0-diCounterReset2Init INTEGER
		}  

slot0-diIndex OBJECT-TYPE
		SYNTAX 			INTEGER (0..7)
		MAX-ACCESS 		read-only
		STATUS 			current
		DESCRIPTION		"The channel index"
		::= { slot0-di 1 }
		
slot0-diStatus OBJECT-TYPE
		SYNTAX 			Unsigned32 
		MAX-ACCESS 		read-write
		STATUS 			current
		DESCRIPTION		"The channel di status. 0=off, 1=on in di mode or n=counter value in counter mode"
		::= { slot0-di 2 }
		
slot0-diCounterReset2Init OBJECT-TYPE
		SYNTAX 			INTEGER 
		MAX-ACCESS 		read-write
		STATUS 			current
		DESCRIPTION		"Trigger counter to initial value. 1=Reset counter to initial value"
		::= { slot0-di 3 }

-- slot 0 DICounterStart
slot0-diCounterStartTable OBJECT-TYPE
		SYNTAX 			SEQUENCE OF Slot0-diCounterStartDef
		MAX-ACCESS 		not-accessible
		STATUS 			current
		DESCRIPTION		"The counter table starting for di"
		::= { slot0-io 39 }

slot0-diCounterStart OBJECT-TYPE
		SYNTAX 			Slot0-diCounterStartDef
		MAX-ACCESS 		not-accessible
		STATUS 			current
		DESCRIPTION		"The counter starting of di item"
		INDEX { slot0-diCounterStartIndex }
		::= { slot0-diCounterStartTable 1 }

Slot0-diCounterStartDef ::= SEQUENCE { 
    	slot0-diCounterStartIndex		INTEGER,
		slot0-diCounterStartStatus		INTEGER,
		slot0-diCounterOverflowFlag     INTEGER,
		slot0-diCounterOverflowFlagClear  INTEGER 
		}  

slot0-diCounterStartIndex OBJECT-TYPE
		SYNTAX 			INTEGER (0..7)
		MAX-ACCESS 		read-only
		STATUS 			current
		DESCRIPTION		"The channel index for di counter start"
		::= { slot0-diCounterStart 1 }
		
slot0-diCounterStartStatus OBJECT-TYPE
		SYNTAX 			INTEGER (0..1)
		MAX-ACCESS 		read-write
		STATUS 			current
		DESCRIPTION		"The channel status for di counter start. 0=stop. 1=start"
		::= { slot0-diCounterStart 2 }  

slot0-diCounterOverflowFlag OBJECT-TYPE
		SYNTAX 			INTEGER (0..1)
		MAX-ACCESS 		read-only
		STATUS 			current
		DESCRIPTION		"Counter overflow flag (0: Normal, 1: Overflow)"
		::= { slot0-diCounterStart 3 }

slot0-diCounterOverflowFlagClear OBJECT-TYPE
		SYNTAX 			INTEGER
		MAX-ACCESS 		read-write
		STATUS 			current
		DESCRIPTION		"Counter clear overflow flag (1: Clear)"
		::= { slot0-diCounterStart 4 }  
		
-- slot 0 DO
slot0-doTable OBJECT-TYPE
		SYNTAX 			SEQUENCE OF Slot0-doDef
		MAX-ACCESS 		not-accessible
		STATUS 			current
		DESCRIPTION		"The do channel table"
		::= { slot0-io 2 }

slot0-do OBJECT-TYPE
		SYNTAX 			Slot0-doDef
		MAX-ACCESS 		not-accessible
		STATUS 			current
		DESCRIPTION		"The do channel item"
		INDEX { slot0-doIndex }
		::= { slot0-doTable 1 }

Slot0-doDef ::= SEQUENCE { 
    	slot0-doIndex		INTEGER,
		slot0-doStatus		INTEGER		
		}  

slot0-doIndex OBJECT-TYPE
		SYNTAX 			INTEGER (0..7)
		MAX-ACCESS 		read-only
		STATUS 			current
		DESCRIPTION		"The channel index"
		::= { slot0-do 1 }
		
slot0-doStatus OBJECT-TYPE
		SYNTAX 			INTEGER (0..1)
		MAX-ACCESS 		read-write
		STATUS 			current
		DESCRIPTION		"The channel do status. 0=off, 1=on in do mode or 0=stop, 1=start in pulse mode"
		::= { slot0-do 2 }  

-- slot 0 DIO
slot0-dioTable OBJECT-TYPE
		SYNTAX 			SEQUENCE OF Slot0-dioDef
		MAX-ACCESS 		not-accessible
		STATUS 			current
		DESCRIPTION		"The dio channel table"
		::= { slot0-io 3 }

slot0-dio OBJECT-TYPE
		SYNTAX 			Slot0-dioDef
		MAX-ACCESS 		not-accessible
		STATUS 			current
		DESCRIPTION		"The dio channel item"
		INDEX { slot0-dioIndex }
		::= { slot0-dioTable 1 }

Slot0-dioDef ::= SEQUENCE { 
    	slot0-dioIndex		INTEGER,
		slot0-dioStatus		Unsigned32,
		slot0-dioCounterReset2Init INTEGER		
		}  

slot0-dioIndex OBJECT-TYPE
		SYNTAX 			INTEGER (0..11)
		MAX-ACCESS 		read-only
		STATUS 			current
		DESCRIPTION		"The channel index"
		::= { slot0-dio 1 }
		
slot0-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot0-dio 2 }  
		
slot0-dioCounterReset2Init OBJECT-TYPE
		SYNTAX 			INTEGER 
		MAX-ACCESS 		read-write
		STATUS 			current
		DESCRIPTION		"Trigger counter to initial value. 1=Reset counter to initial value"
		::= { slot0-dio 3 }

-- slot 0 DIOCounterStart
slot0-dioCounterStartTable OBJECT-TYPE
		SYNTAX 			SEQUENCE OF Slot0-dioCounterStartDef
		MAX-ACCESS 		not-accessible
		STATUS 			current
		DESCRIPTION		"The counter table starting for dio"
		::= { slot0-io 46 }

slot0-dioCounterStart OBJECT-TYPE
		SYNTAX 			Slot0-dioCounterStartDef
		MAX-ACCESS 		not-accessible
		STATUS 			current
		DESCRIPTION		"The counter starting of dio item"
		INDEX { slot0-dioCounterStartIndex}
		::= { slot0-dioCounterStartTable 1 }

Slot0-dioCounterStartDef ::= SEQUENCE { 
    	slot0-dioCounterStartIndex		INTEGER,
		slot0-dioCounterStartStatus		INTEGER,
		slot0-dioCounterOverflowFlag		INTEGER,
		slot0-dioCounterOverflowFlagClear	INTEGER
		}  

slot0-dioCounterStartIndex OBJECT-TYPE
		SYNTAX 			INTEGER (0..11)
		MAX-ACCESS 		read-only
		STATUS 			current
		DESCRIPTION		"The channel index for dio counter start"
		::= { slot0-dioCounterStart 1 }
		
slot0-dioCounterStartStatus OBJECT-TYPE
		SYNTAX 			INTEGER (0..1)
		MAX-ACCESS 		read-write
		STATUS 			current
		DESCRIPTION		"The channel status for dio counter start. 0=stop, 1=start"
		::= { slot0-dioCounterStart 2 }

slot0-dioCounterOverflowFlag OBJECT-TYPE
		SYNTAX 			INTEGER (0..1)
		MAX-ACCESS 		read-only
		STATUS 			current
		DESCRIPTION		"Counter overflow flag (0: Normal, 1: Overflow)"
		::= { slot0-dioCounterStart 3 }

slot0-dioCounterOverflowFlagClear OBJECT-TYPE
		SYNTAX 			INTEGER
		MAX-ACCESS 		read-write
		STATUS 			current
		DESCRIPTION		"Counter clear overflow flag (1: Clear)"
		::= { slot0-dioCounterStart 4 }      		
		
-- slot 0 Relay
slot0-relayTable OBJECT-TYPE
		SYNTAX 			SEQUENCE OF Slot0-relayDef
		MAX-ACCESS 		not-accessible
		STATUS 			current
		DESCRIPTION		"The relay channel table"
		::= { slot0-io 4 }

slot0-relay OBJECT-TYPE
		SYNTAX 			Slot0-relayDef
		MAX-ACCESS 		not-accessible
		STATUS 			current
		DESCRIPTION		"The relay channel item"
		INDEX { slot0-relayIndex }
		::= { slot0-relayTable 1 }

Slot0-relayDef ::= SEQUENCE { 
    	slot0-relayIndex		INTEGER,
		slot0-relayStatus		INTEGER		
		}  

slot0-relayIndex OBJECT-TYPE
		SYNTAX 			INTEGER (0..7)
		MAX-ACCESS 		read-only
		STATUS 			current
		DESCRIPTION		"The channel index"
		::= { slot0-relay 1 }
		
slot0-relayStatus OBJECT-TYPE
		SYNTAX 			INTEGER (0..1)
		MAX-ACCESS 		read-write
		STATUS 			current
		DESCRIPTION		"The channel relay status. 0=off, 1=on in do mode or 0=stop, 1=start in pulse mode"
		::= { slot0-relay 2 }  

-- slot 0 AI
slot0-aiTable OBJECT-TYPE
		SYNTAX 			SEQUENCE OF Slot0-aiDef
		MAX-ACCESS 		not-accessible
		STATUS 			current
		DESCRIPTION		"The ai channel table"
		::= { slot0-io 5 }

slot0-ai OBJECT-TYPE
		SYNTAX 			Slot0-aiDef
		MAX-ACCESS 		not-accessible
		STATUS 			current
		DESCRIPTION		"The ai channel item"
		INDEX { slot0-aiIndex }
		::= { slot0-aiTable 1 }

Slot0-aiDef ::= SEQUENCE { 
    	slot0-aiIndex		INTEGER,
		slot0-aiStatus		OCTET STRING,
		slot0-aiBurnoutStatus INTEGER
		}  

slot0-aiIndex OBJECT-TYPE
		SYNTAX 			INTEGER (0..3)
		MAX-ACCESS 		read-only
		STATUS 			current
		DESCRIPTION		"The channel index"
		::= { slot0-ai 1 }
		
slot0-aiStatus OBJECT-TYPE
		SYNTAX 			OCTET STRING
		MAX-ACCESS 		read-only
		STATUS 			current
		DESCRIPTION		"The channel ai scaled value"
		::= { slot0-ai 2 }  
		
slot0-aiBurnoutStatus OBJECT-TYPE
		SYNTAX 			INTEGER (0..3)
		MAX-ACCESS 		read-only
		STATUS 			current
		DESCRIPTION		"The channel of burnout status (0: normal, 1: burnout, 2: overange, 3: underange)"
		::= { slot0-ai 3 }  

-- slot 0 AO
slot0-aoTable OBJECT-TYPE
		SYNTAX 			SEQUENCE OF Slot0-aoDef
		MAX-ACCESS 		not-accessible
		STATUS 			current
		DESCRIPTION		"The ao channel table"
		::= { slot0-io 6 }

slot0-ao OBJECT-TYPE
		SYNTAX 			Slot0-aoDef
		MAX-ACCESS 		not-accessible
		STATUS 			current
		DESCRIPTION		"The ao channel item"
		INDEX { slot0-aoIndex }
		::= { slot0-aoTable 1 }

Slot0-aoDef ::= SEQUENCE { 
    	slot0-aoIndex		INTEGER,
		slot0-aoStatus		OCTET STRING		
		}  

slot0-aoIndex OBJECT-TYPE
		SYNTAX 			INTEGER (0..8)
		MAX-ACCESS 		read-only
		STATUS 			current
		DESCRIPTION		"The channel index"
		::= { slot0-ao 1 }
		
slot0-aoStatus OBJECT-TYPE
		SYNTAX 			OCTET STRING
		MAX-ACCESS 		read-write
		STATUS 			current
		DESCRIPTION		"The channel ao scaled value"
		::= { slot0-ao 2 }  

-- slot 0 RTD
slot0-rtdTable OBJECT-TYPE
		SYNTAX 			SEQUENCE OF Slot0-rtdDef
		MAX-ACCESS 		not-accessible
		STATUS 			current
		DESCRIPTION		"The rtd channel table"
		::= { slot0-io 7 }

slot0-rtd OBJECT-TYPE
		SYNTAX 			Slot0-rtdDef
		MAX-ACCESS 		not-accessible
		STATUS 			current
		DESCRIPTION		"The rtd channel item"
		INDEX { slot0-rtdIndex }
		::= { slot0-rtdTable 1 }

Slot0-rtdDef ::= SEQUENCE { 
    	slot0-rtdIndex		INTEGER,
		slot0-rtdStatus		OCTET STRING		
		}  

slot0-rtdIndex OBJECT-TYPE
		SYNTAX 			INTEGER (0..8)
		MAX-ACCESS 		read-only
		STATUS 			current
		DESCRIPTION		"The channel index"
		::= { slot0-rtd 1 }
		
slot0-rtdStatus OBJECT-TYPE
		SYNTAX 			OCTET STRING
		MAX-ACCESS 		read-only
		STATUS 			current
		DESCRIPTION		"The channel rtd scaled value"
		::= { slot0-rtd 2 }  

-- slot 0 TC
slot0-tcTable OBJECT-TYPE
		SYNTAX 			SEQUENCE OF Slot0-tcDef
		MAX-ACCESS 		not-accessible
		STATUS 			current
		DESCRIPTION		"The tc channel table"
		::= { slot0-io 8 }

slot0-tc OBJECT-TYPE
		SYNTAX 			Slot0-tcDef
		MAX-ACCESS 		not-accessible
		STATUS 			current
		DESCRIPTION		"The tc channel item"
		INDEX { slot0-tcIndex }
		::= { slot0-tcTable 1 }

Slot0-tcDef ::= SEQUENCE { 
    	slot0-tcIndex		INTEGER,
		slot0-tcStatus		OCTET STRING		
		}  

slot0-tcIndex OBJECT-TYPE
		SYNTAX 			INTEGER (0..8)
		MAX-ACCESS 		read-only
		STATUS 			current
		DESCRIPTION		"The channel index"
		::= { slot0-tc 1 }
		
slot0-tcStatus OBJECT-TYPE
		SYNTAX 			OCTET STRING
		MAX-ACCESS 		read-only
		STATUS 			current
		DESCRIPTION		"The channel tc scaled value"
		::= { slot0-tc 2 }  

		
-- ir
slot0-irTable OBJECT-TYPE
		SYNTAX 			SEQUENCE OF Slot0-irDef
		MAX-ACCESS 		not-accessible
		STATUS 			current
		DESCRIPTION		"The ir channel table"
		::= { slot0-io 9 }
		
slot0-ir OBJECT-TYPE
		SYNTAX 			Slot0-irDef
		MAX-ACCESS 		not-accessible
		STATUS 			current
		DESCRIPTION		"The ir channel item"
		INDEX { slot0-irIndex }
		::= { slot0-irTable 1 }

Slot0-irDef ::= SEQUENCE { 
    	slot0-irIndex		INTEGER,
		slot0-irName		OCTET STRING,
		slot0-irValue		OCTET STRING,
		slot0-irDataType	OCTET STRING
		}  

slot0-irIndex OBJECT-TYPE
		SYNTAX 			INTEGER (0..300)
		MAX-ACCESS 		read-only
		STATUS 			current
		DESCRIPTION		"The internal register index"
		::= { slot0-ir 1 }

slot0-irName OBJECT-TYPE
		SYNTAX 			OCTET STRING
		MAX-ACCESS 		read-only
		STATUS 			current
		DESCRIPTION		"The internal register name"
		::= { slot0-ir 2 }  		

slot0-irValue OBJECT-TYPE
		SYNTAX 			OCTET STRING
		MAX-ACCESS 		read-write
		STATUS 			current
		DESCRIPTION		"The internal register value"
		::= { slot0-ir 3 }  		
		
slot0-irDataType OBJECT-TYPE
		SYNTAX 			OCTET STRING
		MAX-ACCESS 		read-only
		STATUS 			current
		DESCRIPTION		"The internal register type (0: wir, 1: fir, 2: bir, 3: dwir)"
		::= { slot0-ir 4 }  
		
-- slot 0 P2PRule
slot0-p2pRuleTable OBJECT-TYPE
		SYNTAX 			SEQUENCE OF Slot0-p2pRuleDef
		MAX-ACCESS 		not-accessible
		STATUS 			current
		DESCRIPTION		"The p2p rule table"
		::= { slot0-io 47 }

slot0-p2pRule OBJECT-TYPE
		SYNTAX 			Slot0-p2pRuleDef
		MAX-ACCESS 		not-accessible
		STATUS 			current
		DESCRIPTION		"The p2p rule item"
		INDEX { slot0-p2pRuleIndex }
		::= { slot0-p2pRuleTable 1 }

Slot0-p2pRuleDef ::= SEQUENCE { 
    	slot0-p2pRuleIndex		INTEGER,
		slot0-p2pRuleStatus		INTEGER	
		}  

slot0-p2pRuleIndex OBJECT-TYPE
		SYNTAX 			INTEGER (0..15)
		MAX-ACCESS 		read-only
		STATUS 			current
		DESCRIPTION		"The index for p2p rule"
		::= { slot0-p2pRule 1 }
		
slot0-p2pRuleStatus OBJECT-TYPE
		SYNTAX 			INTEGER(0..1)
		MAX-ACCESS 		read-only
		STATUS 			current
		DESCRIPTION		"The p2p rule status. 0=idle, 1=running"
		::= { slot0-p2pRule 2 }  	

-- slot 0 VC
slot0-vcTable OBJECT-TYPE
		SYNTAX 			SEQUENCE OF Slot0-vcDef
		MAX-ACCESS 		not-accessible
		STATUS 			current
		DESCRIPTION		"The vc channel table"
		::= { slot0-io 36 }

slot0-vc OBJECT-TYPE
		SYNTAX 			Slot0-vcDef
		MAX-ACCESS 		not-accessible
		STATUS 			current
		DESCRIPTION		"The vc channel item"
		INDEX { slot0-vcIndex }
		::= { slot0-vcTable 1 }

Slot0-vcDef ::= SEQUENCE { 
    	slot0-vcIndex		INTEGER,
		slot0-vcStatus		OCTET STRING		
		}  

slot0-vcIndex OBJECT-TYPE
		SYNTAX 			INTEGER (0..9)
		MAX-ACCESS 		read-only
		STATUS 			current
		DESCRIPTION		"The channel index"
		::= { slot0-vc 1 }
		
slot0-vcStatus OBJECT-TYPE
		SYNTAX 			OCTET STRING
		MAX-ACCESS 		read-only
		STATUS 			current
		DESCRIPTION		"The virtual channel scaled value"
		::= { slot0-vc 2 }  
		
----------------------------------------------------------------
-- 1.3.6.1.4.1.8691.10.2500.11
    slot0-io-Trap OBJECT IDENTIFIER ::= { ioLogik2500 11 }
----------------------------------------------------------------

----------------------------------------------------------------
-- 1.3.6.1.4.1.8691.10.2500.11.1
    slot0-di-Trap OBJECT IDENTIFIER ::= { slot0-io-Trap 1 }
----------------------------------------------------------------

slot0Trap-di-00 NOTIFICATION-TYPE
    STATUS      current
    DESCRIPTION
        "SNMPTrap, di channel-00 in slot 0"
::= { slot0-di-Trap 1 }

slot0Trap-di-01 NOTIFICATION-TYPE
    STATUS      current
    DESCRIPTION
        "SNMPTrap, di channel-01 in slot 0"
::= { slot0-di-Trap 2 }

slot0Trap-di-02 NOTIFICATION-TYPE
    STATUS      current
    DESCRIPTION
        "SNMPTrap, di channel-02 in slot 0"
::= { slot0-di-Trap 3 }

slot0Trap-di-03 NOTIFICATION-TYPE
    STATUS      current
    DESCRIPTION
        "SNMPTrap, di channel-03 in slot 0"
::= { slot0-di-Trap 4 }

slot0Trap-di-04 NOTIFICATION-TYPE
    STATUS      current
    DESCRIPTION
        "SNMPTrap, di channel-04 in slot 0"
::= { slot0-di-Trap 5 }

slot0Trap-di-05 NOTIFICATION-TYPE
    STATUS      current
    DESCRIPTION
        "SNMPTrap, di channel-05 in slot 0"
::= { slot0-di-Trap 6 }

slot0Trap-di-06 NOTIFICATION-TYPE
    STATUS      current
    DESCRIPTION
        "SNMPTrap, di channel-06 in slot 0"
::= { slot0-di-Trap 7 }

slot0Trap-di-07 NOTIFICATION-TYPE
    STATUS      current
    DESCRIPTION
        "SNMPTrap, di channel-07 in slot 0"
::= { slot0-di-Trap 8 }

slot0Trap-di-08 NOTIFICATION-TYPE
    STATUS      current
    DESCRIPTION
        "SNMPTrap, di channel-08 in slot 0"
::= { slot0-di-Trap 9 }

slot0Trap-di-09 NOTIFICATION-TYPE
    STATUS      current
    DESCRIPTION
        "SNMPTrap, di channel-09 in slot 0"
::= { slot0-di-Trap 10 }

slot0Trap-di-10 NOTIFICATION-TYPE
    STATUS      current
    DESCRIPTION
        "SNMPTrap, di channel-10 in slot 0"
::= { slot0-di-Trap 11 }

slot0Trap-di-11 NOTIFICATION-TYPE
    STATUS      current
    DESCRIPTION
        "SNMPTrap, di channel-11 in slot 0"
::= { slot0-di-Trap 12 }

slot0Trap-di-12 NOTIFICATION-TYPE
    STATUS      current
    DESCRIPTION
        "SNMPTrap, di channel-12 in slot 0"
::= { slot0-di-Trap 13 }

slot0Trap-di-13 NOTIFICATION-TYPE
    STATUS      current
    DESCRIPTION
        "SNMPTrap, di channel-13 in slot 0"
::= { slot0-di-Trap 14 }

slot0Trap-di-14 NOTIFICATION-TYPE
    STATUS      current
    DESCRIPTION
        "SNMPTrap, di channel-14 in slot 0"
::= { slot0-di-Trap 15 }

slot0Trap-di-15 NOTIFICATION-TYPE
    STATUS      current
    DESCRIPTION
        "SNMPTrap, di channel-15 in slot 0"
::= { slot0-di-Trap 16 }
----------------------------------------------------------------
-- 1.3.6.1.4.1.8691.10.2500.11.2
    slot0-do-Trap OBJECT IDENTIFIER ::= { slot0-io-Trap 2 }
----------------------------------------------------------------

slot0Trap-do-00 NOTIFICATION-TYPE
    STATUS      current
    DESCRIPTION
        "SNMPTrap, do channel-00 in slot 0"
::= { slot0-do-Trap 1 }

slot0Trap-do-01 NOTIFICATION-TYPE
    STATUS      current
    DESCRIPTION
        "SNMPTrap, do channel-01 in slot 0"
::= { slot0-do-Trap 2 }

slot0Trap-do-02 NOTIFICATION-TYPE
    STATUS      current
    DESCRIPTION
        "SNMPTrap, do channel-02 in slot 0"
::= { slot0-do-Trap 3 }

slot0Trap-do-03 NOTIFICATION-TYPE
    STATUS      current
    DESCRIPTION
        "SNMPTrap, do channel-03 in slot 0"
::= { slot0-do-Trap 4 }

slot0Trap-do-04 NOTIFICATION-TYPE
    STATUS      current
    DESCRIPTION
        "SNMPTrap, do channel-04 in slot 0"
::= { slot0-do-Trap 5 }

slot0Trap-do-05 NOTIFICATION-TYPE
    STATUS      current
    DESCRIPTION
        "SNMPTrap, do channel-05 in slot 0"
::= { slot0-do-Trap 6 }

slot0Trap-do-06 NOTIFICATION-TYPE
    STATUS      current
    DESCRIPTION
        "SNMPTrap, do channel-06 in slot 0"
::= { slot0-do-Trap 7 }

slot0Trap-do-07 NOTIFICATION-TYPE
    STATUS      current
    DESCRIPTION
        "SNMPTrap, do channel-07 in slot 0"
::= { slot0-do-Trap 8 }

slot0Trap-do-08 NOTIFICATION-TYPE
    STATUS      current
    DESCRIPTION
        "SNMPTrap, do channel-08 in slot 0"
::= { slot0-do-Trap 9 }

slot0Trap-do-09 NOTIFICATION-TYPE
    STATUS      current
    DESCRIPTION
        "SNMPTrap, do channel-09 in slot 0"
::= { slot0-do-Trap 10 }

slot0Trap-do-10 NOTIFICATION-TYPE
    STATUS      current
    DESCRIPTION
        "SNMPTrap, do channel-10 in slot 0"
::= { slot0-do-Trap 11 }

slot0Trap-do-11 NOTIFICATION-TYPE
    STATUS      current
    DESCRIPTION
        "SNMPTrap, do channel-11 in slot 0"
::= { slot0-do-Trap 12 }

slot0Trap-do-12 NOTIFICATION-TYPE
    STATUS      current
    DESCRIPTION
        "SNMPTrap, do channel-12 in slot 0"
::= { slot0-do-Trap 13 }

slot0Trap-do-13 NOTIFICATION-TYPE
    STATUS      current
    DESCRIPTION
        "SNMPTrap, do channel-13 in slot 0"
::= { slot0-do-Trap 14 }

slot0Trap-do-14 NOTIFICATION-TYPE
    STATUS      current
    DESCRIPTION
        "SNMPTrap, do channel-14 in slot 0"
::= { slot0-do-Trap 15 }

slot0Trap-do-15 NOTIFICATION-TYPE
    STATUS      current
    DESCRIPTION
        "SNMPTrap, do channel-15 in slot 0"
::= { slot0-do-Trap 16 }

----------------------------------------------------------------
-- 1.3.6.1.4.1.8691.10.2500.11.3
    slot0-dio-Trap OBJECT IDENTIFIER ::= { slot0-io-Trap 3 }
----------------------------------------------------------------

slot0Trap-dio-00 NOTIFICATION-TYPE
    STATUS      current
    DESCRIPTION
        "SNMPTrap, dio channel-00 in slot 0"
::= { slot0-dio-Trap 1 }

slot0Trap-dio-01 NOTIFICATION-TYPE
    STATUS      current
    DESCRIPTION
        "SNMPTrap, dio channel-01 in slot 0"
::= { slot0-dio-Trap 2 }

slot0Trap-dio-02 NOTIFICATION-TYPE
    STATUS      current
    DESCRIPTION
        "SNMPTrap, dio channel-02 in slot 0"
::= { slot0-dio-Trap 3 }

slot0Trap-dio-03 NOTIFICATION-TYPE
    STATUS      current
    DESCRIPTION
        "SNMPTrap, dio channel-03 in slot 0"
::= { slot0-dio-Trap 4 }

slot0Trap-dio-04 NOTIFICATION-TYPE
    STATUS      current
    DESCRIPTION
        "SNMPTrap, dio channel-04 in slot 0"
::= { slot0-dio-Trap 5 }

slot0Trap-dio-05 NOTIFICATION-TYPE
    STATUS      current
    DESCRIPTION
        "SNMPTrap, dio channel-05 in slot 0"
::= { slot0-dio-Trap 6 }

slot0Trap-dio-06 NOTIFICATION-TYPE
    STATUS      current
    DESCRIPTION
        "SNMPTrap, dio channel-06 in slot 0"
::= { slot0-dio-Trap 7 }

slot0Trap-dio-07 NOTIFICATION-TYPE
    STATUS      current
    DESCRIPTION
        "SNMPTrap, dio channel-07 in slot 0"
::= { slot0-dio-Trap 8 }

slot0Trap-dio-08 NOTIFICATION-TYPE
    STATUS      current
    DESCRIPTION
        "SNMPTrap, dio channel-08 in slot 0"
::= { slot0-dio-Trap 9 }

slot0Trap-dio-09 NOTIFICATION-TYPE
    STATUS      current
    DESCRIPTION
        "SNMPTrap, dio channel-09 in slot 0"
::= { slot0-dio-Trap 10 }

slot0Trap-dio-10 NOTIFICATION-TYPE
    STATUS      current
    DESCRIPTION
        "SNMPTrap, dio channel-10 in slot 0"
::= { slot0-dio-Trap 11 }

slot0Trap-dio-11 NOTIFICATION-TYPE
    STATUS      current
    DESCRIPTION
        "SNMPTrap, dio channel-11 in slot 0"
::= { slot0-dio-Trap 12 }

slot0Trap-dio-12 NOTIFICATION-TYPE
    STATUS      current
    DESCRIPTION
        "SNMPTrap, dio channel-12 in slot 0"
::= { slot0-dio-Trap 13 }

slot0Trap-dio-13 NOTIFICATION-TYPE
    STATUS      current
    DESCRIPTION
        "SNMPTrap, dio channel-13 in slot 0"
::= { slot0-dio-Trap 14 }

slot0Trap-dio-14 NOTIFICATION-TYPE
    STATUS      current
    DESCRIPTION
        "SNMPTrap, dio channel-14 in slot 0"
::= { slot0-dio-Trap 15 }

slot0Trap-dio-15 NOTIFICATION-TYPE
    STATUS      current
    DESCRIPTION
        "SNMPTrap, dio channel-15 in slot 0"
::= { slot0-dio-Trap 16 }

----------------------------------------------------------------
-- 1.3.6.1.4.1.8691.10.2500.11.4
    slot0-relay-Trap OBJECT IDENTIFIER ::= { slot0-io-Trap 4 }
----------------------------------------------------------------

slot0Trap-relay-00 NOTIFICATION-TYPE
    STATUS      current
    DESCRIPTION
        "SNMPTrap, relay channel-00 in slot 0"
::= { slot0-relay-Trap 1 }

slot0Trap-relay-01 NOTIFICATION-TYPE
    STATUS      current
    DESCRIPTION
        "SNMPTrap, relay channel-01 in slot 0"
::= { slot0-relay-Trap 2 }

slot0Trap-relay-02 NOTIFICATION-TYPE
    STATUS      current
    DESCRIPTION
        "SNMPTrap, relay channel-02 in slot 0"
::= { slot0-relay-Trap 3 }

slot0Trap-relay-03 NOTIFICATION-TYPE
    STATUS      current
    DESCRIPTION
        "SNMPTrap, relay channel-03 in slot 0"
::= { slot0-relay-Trap 4 }

slot0Trap-relay-04 NOTIFICATION-TYPE
    STATUS      current
    DESCRIPTION
        "SNMPTrap, relay channel-04 in slot 0"
::= { slot0-relay-Trap 5 }

slot0Trap-relay-05 NOTIFICATION-TYPE
    STATUS      current
    DESCRIPTION
        "SNMPTrap, relay channel-05 in slot 0"
::= { slot0-relay-Trap 6 }

slot0Trap-relay-06 NOTIFICATION-TYPE
    STATUS      current
    DESCRIPTION
        "SNMPTrap, relay channel-06 in slot 0"
::= { slot0-relay-Trap 7 }

slot0Trap-relay-07 NOTIFICATION-TYPE
    STATUS      current
    DESCRIPTION
        "SNMPTrap, relay channel-07 in slot 0"
::= { slot0-relay-Trap 8 }

slot0Trap-relay-08 NOTIFICATION-TYPE
    STATUS      current
    DESCRIPTION
        "SNMPTrap, relay channel-08 in slot 0"
::= { slot0-relay-Trap 9 }

slot0Trap-relay-09 NOTIFICATION-TYPE
    STATUS      current
    DESCRIPTION
        "SNMPTrap, relay channel-09 in slot 0"
::= { slot0-relay-Trap 10 }

slot0Trap-relay-10 NOTIFICATION-TYPE
    STATUS      current
    DESCRIPTION
        "SNMPTrap, relay channel-10 in slot 0"
::= { slot0-relay-Trap 11 }

slot0Trap-relay-11 NOTIFICATION-TYPE
    STATUS      current
    DESCRIPTION
        "SNMPTrap, relay channel-11 in slot 0"
::= { slot0-relay-Trap 12 }

slot0Trap-relay-12 NOTIFICATION-TYPE
    STATUS      current
    DESCRIPTION
        "SNMPTrap, relay channel-12 in slot 0"
::= { slot0-relay-Trap 13 }

slot0Trap-relay-13 NOTIFICATION-TYPE
    STATUS      current
    DESCRIPTION
        "SNMPTrap, relay channel-13 in slot 0"
::= { slot0-relay-Trap 14 }

slot0Trap-relay-14 NOTIFICATION-TYPE
    STATUS      current
    DESCRIPTION
        "SNMPTrap, relay channel-14 in slot 0"
::= { slot0-relay-Trap 15 }

slot0Trap-relay-15 NOTIFICATION-TYPE
    STATUS      current
    DESCRIPTION
        "SNMPTrap, relay channel-15 in slot 0"
::= { slot0-relay-Trap 16 }

----------------------------------------------------------------
-- 1.3.6.1.4.1.8691.10.2500.11.5
    slot0-ai-Trap OBJECT IDENTIFIER ::= { slot0-io-Trap 5 }
----------------------------------------------------------------

slot0Trap-ai-00 NOTIFICATION-TYPE
    STATUS      current
    DESCRIPTION
        "SNMPTrap, ai channel-00 in slot 0"
::= { slot0-ai-Trap 1 }

slot0Trap-ai-01 NOTIFICATION-TYPE
    STATUS      current
    DESCRIPTION
        "SNMPTrap, ai channel-01 in slot 0"
::= { slot0-ai-Trap 2 }

slot0Trap-ai-02 NOTIFICATION-TYPE
    STATUS      current
    DESCRIPTION
        "SNMPTrap, ai channel-02 in slot 0"
::= { slot0-ai-Trap 3 }

slot0Trap-ai-03 NOTIFICATION-TYPE
    STATUS      current
    DESCRIPTION
        "SNMPTrap, ai channel-03 in slot 0"
::= { slot0-ai-Trap 4 }

slot0Trap-ai-04 NOTIFICATION-TYPE
    STATUS      current
    DESCRIPTION
        "SNMPTrap, ai channel-04 in slot 0"
::= { slot0-ai-Trap 5 }

slot0Trap-ai-05 NOTIFICATION-TYPE
    STATUS      current
    DESCRIPTION
        "SNMPTrap, ai channel-05 in slot 0"
::= { slot0-ai-Trap 6 }

slot0Trap-ai-06 NOTIFICATION-TYPE
    STATUS      current
    DESCRIPTION
        "SNMPTrap, ai channel-06 in slot 0"
::= { slot0-ai-Trap 7 }

slot0Trap-ai-07 NOTIFICATION-TYPE
    STATUS      current
    DESCRIPTION
        "SNMPTrap, ai channel-07 in slot 0"
::= { slot0-ai-Trap 8 }

slot0Trap-ai-08 NOTIFICATION-TYPE
    STATUS      current
    DESCRIPTION
        "SNMPTrap, ai channel-08 in slot 0"
::= { slot0-ai-Trap 9 }

slot0Trap-ai-09 NOTIFICATION-TYPE
    STATUS      current
    DESCRIPTION
        "SNMPTrap, ai channel-09 in slot 0"
::= { slot0-ai-Trap 10 }

slot0Trap-ai-10 NOTIFICATION-TYPE
    STATUS      current
    DESCRIPTION
        "SNMPTrap, ai channel-10 in slot 0"
::= { slot0-ai-Trap 11 }

slot0Trap-ai-11 NOTIFICATION-TYPE
    STATUS      current
    DESCRIPTION
        "SNMPTrap, ai channel-11 in slot 0"
::= { slot0-ai-Trap 12 }

slot0Trap-ai-12 NOTIFICATION-TYPE
    STATUS      current
    DESCRIPTION
        "SNMPTrap, ai channel-12 in slot 0"
::= { slot0-ai-Trap 13 }

slot0Trap-ai-13 NOTIFICATION-TYPE
    STATUS      current
    DESCRIPTION
        "SNMPTrap, ai channel-13 in slot 0"
::= { slot0-ai-Trap 14 }

slot0Trap-ai-14 NOTIFICATION-TYPE
    STATUS      current
    DESCRIPTION
        "SNMPTrap, ai channel-14 in slot 0"
::= { slot0-ai-Trap 15 }

slot0Trap-ai-15 NOTIFICATION-TYPE
    STATUS      current
    DESCRIPTION
        "SNMPTrap, ai channel-15 in slot 0"
::= { slot0-ai-Trap 16 }

----------------------------------------------------------------
-- 1.3.6.1.4.1.8691.10.2500.11.6
    slot0-ao-Trap OBJECT IDENTIFIER ::= { slot0-io-Trap 6 }
----------------------------------------------------------------

slot0Trap-ao-00 NOTIFICATION-TYPE
    STATUS      current
    DESCRIPTION
        "SNMPTrap, ao channel-00 in slot 0"
::= { slot0-ao-Trap 1 }

slot0Trap-ao-01 NOTIFICATION-TYPE
    STATUS      current
    DESCRIPTION
        "SNMPTrap, ao channel-01 in slot 0"
::= { slot0-ao-Trap 2 }

slot0Trap-ao-02 NOTIFICATION-TYPE
    STATUS      current
    DESCRIPTION
        "SNMPTrap, ao channel-02 in slot 0"
::= { slot0-ao-Trap 3 }

slot0Trap-ao-03 NOTIFICATION-TYPE
    STATUS      current
    DESCRIPTION
        "SNMPTrap, ao channel-03 in slot 0"
::= { slot0-ao-Trap 4 }

slot0Trap-ao-04 NOTIFICATION-TYPE
    STATUS      current
    DESCRIPTION
        "SNMPTrap, ao channel-04 in slot 0"
::= { slot0-ao-Trap 5 }

slot0Trap-ao-05 NOTIFICATION-TYPE
    STATUS      current
    DESCRIPTION
        "SNMPTrap, ao channel-05 in slot 0"
::= { slot0-ao-Trap 6 }

slot0Trap-ao-06 NOTIFICATION-TYPE
    STATUS      current
    DESCRIPTION
        "SNMPTrap, ao channel-06 in slot 0"
::= { slot0-ao-Trap 7 }

slot0Trap-ao-07 NOTIFICATION-TYPE
    STATUS      current
    DESCRIPTION
        "SNMPTrap, ao channel-07 in slot 0"
::= { slot0-ao-Trap 8 }

slot0Trap-ao-08 NOTIFICATION-TYPE
    STATUS      current
    DESCRIPTION
        "SNMPTrap, ao channel-08 in slot 0"
::= { slot0-ao-Trap 9 }

slot0Trap-ao-09 NOTIFICATION-TYPE
    STATUS      current
    DESCRIPTION
        "SNMPTrap, ao channel-09 in slot 0"
::= { slot0-ao-Trap 10 }

slot0Trap-ao-10 NOTIFICATION-TYPE
    STATUS      current
    DESCRIPTION
        "SNMPTrap, ao channel-10 in slot 0"
::= { slot0-ao-Trap 11 }

slot0Trap-ao-11 NOTIFICATION-TYPE
    STATUS      current
    DESCRIPTION
        "SNMPTrap, ao channel-11 in slot 0"
::= { slot0-ao-Trap 12 }

slot0Trap-ao-12 NOTIFICATION-TYPE
    STATUS      current
    DESCRIPTION
        "SNMPTrap, ao channel-12 in slot 0"
::= { slot0-ao-Trap 13 }

slot0Trap-ao-13 NOTIFICATION-TYPE
    STATUS      current
    DESCRIPTION
        "SNMPTrap, ao channel-13 in slot 0"
::= { slot0-ao-Trap 14 }

slot0Trap-ao-14 NOTIFICATION-TYPE
    STATUS      current
    DESCRIPTION
        "SNMPTrap, ao channel-14 in slot 0"
::= { slot0-ao-Trap 15 }

slot0Trap-ao-15 NOTIFICATION-TYPE
    STATUS      current
    DESCRIPTION
        "SNMPTrap, ao channel-15 in slot 0"
::= { slot0-ao-Trap 16 }

----------------------------------------------------------------
-- 1.3.6.1.4.1.8691.10.2500.11.7
    slot0-rtd-Trap OBJECT IDENTIFIER ::= { slot0-io-Trap 7 }
----------------------------------------------------------------

slot0Trap-rtd-00 NOTIFICATION-TYPE
    STATUS      current
    DESCRIPTION
        "SNMPTrap, rtd channel-00 in slot 0"
::= { slot0-rtd-Trap 1 }

slot0Trap-rtd-01 NOTIFICATION-TYPE
    STATUS      current
    DESCRIPTION
        "SNMPTrap, rtd channel-01 in slot 0"
::= { slot0-rtd-Trap 2 }

slot0Trap-rtd-02 NOTIFICATION-TYPE
    STATUS      current
    DESCRIPTION
        "SNMPTrap, rtd channel-02 in slot 0"
::= { slot0-rtd-Trap 3 }

slot0Trap-rtd-03 NOTIFICATION-TYPE
    STATUS      current
    DESCRIPTION
        "SNMPTrap, rtd channel-03 in slot 0"
::= { slot0-rtd-Trap 4 }

slot0Trap-rtd-04 NOTIFICATION-TYPE
    STATUS      current
    DESCRIPTION
        "SNMPTrap, rtd channel-04 in slot 0"
::= { slot0-rtd-Trap 5 }

slot0Trap-rtd-05 NOTIFICATION-TYPE
    STATUS      current
    DESCRIPTION
        "SNMPTrap, rtd channel-05 in slot 0"
::= { slot0-rtd-Trap 6 }

slot0Trap-rtd-06 NOTIFICATION-TYPE
    STATUS      current
    DESCRIPTION
        "SNMPTrap, rtd channel-06 in slot 0"
::= { slot0-rtd-Trap 7 }

slot0Trap-rtd-07 NOTIFICATION-TYPE
    STATUS      current
    DESCRIPTION
        "SNMPTrap, rtd channel-07 in slot 0"
::= { slot0-rtd-Trap 8 }

slot0Trap-rtd-08 NOTIFICATION-TYPE
    STATUS      current
    DESCRIPTION
        "SNMPTrap, rtd channel-08 in slot 0"
::= { slot0-rtd-Trap 9 }

slot0Trap-rtd-09 NOTIFICATION-TYPE
    STATUS      current
    DESCRIPTION
        "SNMPTrap, rtd channel-09 in slot 0"
::= { slot0-rtd-Trap 10 }

slot0Trap-rtd-10 NOTIFICATION-TYPE
    STATUS      current
    DESCRIPTION
        "SNMPTrap, rtd channel-10 in slot 0"
::= { slot0-rtd-Trap 11 }

slot0Trap-rtd-11 NOTIFICATION-TYPE
    STATUS      current
    DESCRIPTION
        "SNMPTrap, rtd channel-11 in slot 0"
::= { slot0-rtd-Trap 12 }

slot0Trap-rtd-12 NOTIFICATION-TYPE
    STATUS      current
    DESCRIPTION
        "SNMPTrap, rtd channel-12 in slot 0"
::= { slot0-rtd-Trap 13 }

slot0Trap-rtd-13 NOTIFICATION-TYPE
    STATUS      current
    DESCRIPTION
        "SNMPTrap, rtd channel-13 in slot 0"
::= { slot0-rtd-Trap 14 }

slot0Trap-rtd-14 NOTIFICATION-TYPE
    STATUS      current
    DESCRIPTION
        "SNMPTrap, rtd channel-14 in slot 0"
::= { slot0-rtd-Trap 15 }

slot0Trap-rtd-15 NOTIFICATION-TYPE
    STATUS      current
    DESCRIPTION
        "SNMPTrap, rtd channel-15 in slot 0"
::= { slot0-rtd-Trap 16 }

----------------------------------------------------------------
-- 1.3.6.1.4.1.8691.10.2500.11.8
    slot0-tc-Trap OBJECT IDENTIFIER ::= { slot0-io-Trap 8 }
----------------------------------------------------------------

slot0Trap-tc-00 NOTIFICATION-TYPE
    STATUS      current
    DESCRIPTION
        "SNMPTrap, tc channel-00 in slot 0"
::= { slot0-tc-Trap 1 }

slot0Trap-tc-01 NOTIFICATION-TYPE
    STATUS      current
    DESCRIPTION
        "SNMPTrap, tc channel-01 in slot 0"
::= { slot0-tc-Trap 2 }

slot0Trap-tc-02 NOTIFICATION-TYPE
    STATUS      current
    DESCRIPTION
        "SNMPTrap, tc channel-02 in slot 0"
::= { slot0-tc-Trap 3 }

slot0Trap-tc-03 NOTIFICATION-TYPE
    STATUS      current
    DESCRIPTION
        "SNMPTrap, tc channel-03 in slot 0"
::= { slot0-tc-Trap 4 }

slot0Trap-tc-04 NOTIFICATION-TYPE
    STATUS      current
    DESCRIPTION
        "SNMPTrap, tc channel-04 in slot 0"
::= { slot0-tc-Trap 5 }

slot0Trap-tc-05 NOTIFICATION-TYPE
    STATUS      current
    DESCRIPTION
        "SNMPTrap, tc channel-05 in slot 0"
::= { slot0-tc-Trap 6 }

slot0Trap-tc-06 NOTIFICATION-TYPE
    STATUS      current
    DESCRIPTION
        "SNMPTrap, tc channel-06 in slot 0"
::= { slot0-tc-Trap 7 }

slot0Trap-tc-07 NOTIFICATION-TYPE
    STATUS      current
    DESCRIPTION
        "SNMPTrap, tc channel-07 in slot 0"
::= { slot0-tc-Trap 8 }

slot0Trap-tc-08 NOTIFICATION-TYPE
    STATUS      current
    DESCRIPTION
        "SNMPTrap, tc channel-08 in slot 0"
::= { slot0-tc-Trap 9 }

slot0Trap-tc-09 NOTIFICATION-TYPE
    STATUS      current
    DESCRIPTION
        "SNMPTrap, tc channel-09 in slot 0"
::= { slot0-tc-Trap 10 }

slot0Trap-tc-10 NOTIFICATION-TYPE
    STATUS      current
    DESCRIPTION
        "SNMPTrap, tc channel-10 in slot 0"
::= { slot0-tc-Trap 11 }

slot0Trap-tc-11 NOTIFICATION-TYPE
    STATUS      current
    DESCRIPTION
        "SNMPTrap, tc channel-11 in slot 0"
::= { slot0-tc-Trap 12 }

slot0Trap-tc-12 NOTIFICATION-TYPE
    STATUS      current
    DESCRIPTION
        "SNMPTrap, tc channel-12 in slot 0"
::= { slot0-tc-Trap 13 }

slot0Trap-tc-13 NOTIFICATION-TYPE
    STATUS      current
    DESCRIPTION
        "SNMPTrap, tc channel-13 in slot 0"
::= { slot0-tc-Trap 14 }

slot0Trap-tc-14 NOTIFICATION-TYPE
    STATUS      current
    DESCRIPTION
        "SNMPTrap, tc channel-14 in slot 0"
::= { slot0-tc-Trap 15 }

slot0Trap-tc-15 NOTIFICATION-TYPE
    STATUS      current
    DESCRIPTION
        "SNMPTrap, tc channel-15 in slot 0"
::= { slot0-tc-Trap 16 }

----------------------------------------------------------------
-- 1.3.6.1.4.1.8691.10.2500.11.9
    slot0-ir-Trap OBJECT IDENTIFIER ::= { slot0-io-Trap 9 }
----------------------------------------------------------------

slot0Trap-ir-00 NOTIFICATION-TYPE
    STATUS      current
    DESCRIPTION
        "SNMPTrap, word ir Channel-00 in slot 0"
::= { slot0-ir-Trap 1 }

slot0Trap-ir-01 NOTIFICATION-TYPE
    STATUS      current
    DESCRIPTION
        "SNMPTrap, word ir Channel-01 in slot 0"
::= { slot0-ir-Trap 2 }

slot0Trap-ir-02 NOTIFICATION-TYPE
    STATUS      current
    DESCRIPTION
        "SNMPTrap, word ir Channel-02 in slot 0"
::= { slot0-ir-Trap 3 }

slot0Trap-ir-03 NOTIFICATION-TYPE
    STATUS      current
    DESCRIPTION
        "SNMPTrap, word ir Channel-03 in slot 0"
::= { slot0-ir-Trap 4 }

slot0Trap-ir-04 NOTIFICATION-TYPE
    STATUS      current
    DESCRIPTION
        "SNMPTrap, word ir Channel-04 in slot 0"
::= { slot0-ir-Trap 5 }

slot0Trap-ir-05 NOTIFICATION-TYPE
    STATUS      current
    DESCRIPTION
        "SNMPTrap, word ir Channel-05 in slot 0"
::= { slot0-ir-Trap 6 }

slot0Trap-ir-06 NOTIFICATION-TYPE
    STATUS      current
    DESCRIPTION
        "SNMPTrap, word ir Channel-06 in slot 0"
::= { slot0-ir-Trap 7 }

slot0Trap-ir-07 NOTIFICATION-TYPE
    STATUS      current
    DESCRIPTION
        "SNMPTrap, word ir Channel-07 in slot 0"
::= { slot0-ir-Trap 8 }

slot0Trap-ir-08 NOTIFICATION-TYPE
    STATUS      current
    DESCRIPTION
        "SNMPTrap, word ir Channel-08 in slot 0"
::= { slot0-ir-Trap 9 }

slot0Trap-ir-09 NOTIFICATION-TYPE
    STATUS      current
    DESCRIPTION
        "SNMPTrap, word ir Channel-09 in slot 0"
::= { slot0-ir-Trap 10 }

slot0Trap-ir-10 NOTIFICATION-TYPE
    STATUS      current
    DESCRIPTION
        "SNMPTrap, word ir Channel-10 in slot 0"
::= { slot0-ir-Trap 11 }

slot0Trap-ir-11 NOTIFICATION-TYPE
    STATUS      current
    DESCRIPTION
        "SNMPTrap, word ir Channel-11 in slot 0"
::= { slot0-ir-Trap 12 }

slot0Trap-ir-12 NOTIFICATION-TYPE
    STATUS      current
    DESCRIPTION
        "SNMPTrap, word ir Channel-12 in slot 0"
::= { slot0-ir-Trap 13 }

slot0Trap-ir-13 NOTIFICATION-TYPE
    STATUS      current
    DESCRIPTION
        "SNMPTrap, word ir Channel-13 in slot 0"
::= { slot0-ir-Trap 14 }

slot0Trap-ir-14 NOTIFICATION-TYPE
    STATUS      current
    DESCRIPTION
        "SNMPTrap, word ir Channel-14 in slot 0"
::= { slot0-ir-Trap 15 }

slot0Trap-ir-15 NOTIFICATION-TYPE
    STATUS      current
    DESCRIPTION
        "SNMPTrap, word ir Channel-15 in slot 0"
::= { slot0-ir-Trap 16 }

slot0Trap-ir-16 NOTIFICATION-TYPE
    STATUS      current
    DESCRIPTION
        "SNMPTrap, word ir Channel-16 in slot 0"
::= { slot0-ir-Trap 17 }

slot0Trap-ir-17 NOTIFICATION-TYPE
    STATUS      current
    DESCRIPTION
        "SNMPTrap, word ir Channel-17 in slot 0"
::= { slot0-ir-Trap 18 }

slot0Trap-ir-18 NOTIFICATION-TYPE
    STATUS      current
    DESCRIPTION
        "SNMPTrap, word ir Channel-18 in slot 0"
::= { slot0-ir-Trap 19 }

slot0Trap-ir-19 NOTIFICATION-TYPE
    STATUS      current
    DESCRIPTION
        "SNMPTrap, word ir Channel-19 in slot 0"
::= { slot0-ir-Trap 20 }

slot0Trap-ir-20 NOTIFICATION-TYPE
    STATUS      current
    DESCRIPTION
        "SNMPTrap, word ir Channel-20 in slot 0"
::= { slot0-ir-Trap 21 }

slot0Trap-ir-21 NOTIFICATION-TYPE
    STATUS      current
    DESCRIPTION
        "SNMPTrap, word ir Channel-21 in slot 0"
::= { slot0-ir-Trap 22 }

slot0Trap-ir-22 NOTIFICATION-TYPE
    STATUS      current
    DESCRIPTION
        "SNMPTrap, word ir Channel-22 in slot 0"
::= { slot0-ir-Trap 23 }

slot0Trap-ir-23 NOTIFICATION-TYPE
    STATUS      current
    DESCRIPTION
        "SNMPTrap, word ir Channel-23 in slot 0"
::= { slot0-ir-Trap 24 }

slot0Trap-ir-24 NOTIFICATION-TYPE
    STATUS      current
    DESCRIPTION
        "SNMPTrap, word ir Channel-24 in slot 0"
::= { slot0-ir-Trap 25 }

slot0Trap-ir-25 NOTIFICATION-TYPE
    STATUS      current
    DESCRIPTION
        "SNMPTrap, word ir Channel-25 in slot 0"
::= { slot0-ir-Trap 26 }

slot0Trap-ir-26 NOTIFICATION-TYPE
    STATUS      current
    DESCRIPTION
        "SNMPTrap, word ir Channel-26 in slot 0"
::= { slot0-ir-Trap 27 }

slot0Trap-ir-27 NOTIFICATION-TYPE
    STATUS      current
    DESCRIPTION
        "SNMPTrap, word ir Channel-27 in slot 0"
::= { slot0-ir-Trap 28 }

slot0Trap-ir-28 NOTIFICATION-TYPE
    STATUS      current
    DESCRIPTION
        "SNMPTrap, word ir Channel-28 in slot 0"
::= { slot0-ir-Trap 29 }

slot0Trap-ir-29 NOTIFICATION-TYPE
    STATUS      current
    DESCRIPTION
        "SNMPTrap, word ir Channel-29 in slot 0"
::= { slot0-ir-Trap 30 }

slot0Trap-ir-30 NOTIFICATION-TYPE
    STATUS      current
    DESCRIPTION
        "SNMPTrap, word ir Channel-30 in slot 0"
::= { slot0-ir-Trap 31 }

slot0Trap-ir-31 NOTIFICATION-TYPE
    STATUS      current
    DESCRIPTION
        "SNMPTrap, word ir Channel-31 in slot 0"
::= { slot0-ir-Trap 32 }

slot0Trap-ir-32 NOTIFICATION-TYPE
    STATUS      current
    DESCRIPTION
        "SNMPTrap, word ir Channel-32 in slot 0"
::= { slot0-ir-Trap 33 }

slot0Trap-ir-33 NOTIFICATION-TYPE
    STATUS      current
    DESCRIPTION
        "SNMPTrap, word ir Channel-33 in slot 0"
::= { slot0-ir-Trap 34 }

slot0Trap-ir-34 NOTIFICATION-TYPE
    STATUS      current
    DESCRIPTION
        "SNMPTrap, word ir Channel-34 in slot 0"
::= { slot0-ir-Trap 35 }

slot0Trap-ir-35 NOTIFICATION-TYPE
    STATUS      current
    DESCRIPTION
        "SNMPTrap, word ir Channel-35 in slot 0"
::= { slot0-ir-Trap 36 }

slot0Trap-ir-36 NOTIFICATION-TYPE
    STATUS      current
    DESCRIPTION
        "SNMPTrap, word ir Channel-36 in slot 0"
::= { slot0-ir-Trap 37 }

slot0Trap-ir-37 NOTIFICATION-TYPE
    STATUS      current
    DESCRIPTION
        "SNMPTrap, word ir Channel-37 in slot 0"
::= { slot0-ir-Trap 38 }

slot0Trap-ir-38 NOTIFICATION-TYPE
    STATUS      current
    DESCRIPTION
        "SNMPTrap, word ir Channel-38 in slot 0"
::= { slot0-ir-Trap 39 }

slot0Trap-ir-39 NOTIFICATION-TYPE
    STATUS      current
    DESCRIPTION
        "SNMPTrap, word ir Channel-39 in slot 0"
::= { slot0-ir-Trap 40 }

slot0Trap-ir-40 NOTIFICATION-TYPE
    STATUS      current
    DESCRIPTION
        "SNMPTrap, word ir Channel-40 in slot 0"
::= { slot0-ir-Trap 41 }

slot0Trap-ir-41 NOTIFICATION-TYPE
    STATUS      current
    DESCRIPTION
        "SNMPTrap, word ir Channel-41 in slot 0"
::= { slot0-ir-Trap 42 }

slot0Trap-ir-42 NOTIFICATION-TYPE
    STATUS      current
    DESCRIPTION
        "SNMPTrap, word ir Channel-42 in slot 0"
::= { slot0-ir-Trap 43 }

slot0Trap-ir-43 NOTIFICATION-TYPE
    STATUS      current
    DESCRIPTION
        "SNMPTrap, word ir Channel-43 in slot 0"
::= { slot0-ir-Trap 44 }

slot0Trap-ir-44 NOTIFICATION-TYPE
    STATUS      current
    DESCRIPTION
        "SNMPTrap, word ir Channel-44 in slot 0"
::= { slot0-ir-Trap 45 }

slot0Trap-ir-45 NOTIFICATION-TYPE
    STATUS      current
    DESCRIPTION
        "SNMPTrap, word ir Channel-45 in slot 0"
::= { slot0-ir-Trap 46 }

slot0Trap-ir-46 NOTIFICATION-TYPE
    STATUS      current
    DESCRIPTION
        "SNMPTrap, word ir Channel-46 in slot 0"
::= { slot0-ir-Trap 47 }

slot0Trap-ir-47 NOTIFICATION-TYPE
    STATUS      current
    DESCRIPTION
        "SNMPTrap, word ir Channel-47 in slot 0"
::= { slot0-ir-Trap 48 }

slot0Trap-ir-48 NOTIFICATION-TYPE
    STATUS      current
    DESCRIPTION
        "SNMPTrap, float ir Channel-00 in slot 0"
::= { slot0-ir-Trap 49 }

slot0Trap-ir-49 NOTIFICATION-TYPE
    STATUS      current
    DESCRIPTION
        "SNMPTrap, float ir Channel-01 in slot 0"
::= { slot0-ir-Trap 50 }

slot0Trap-ir-50 NOTIFICATION-TYPE
    STATUS      current
    DESCRIPTION
        "SNMPTrap, float ir Channel-02 in slot 0"
::= { slot0-ir-Trap 51 }

slot0Trap-ir-51 NOTIFICATION-TYPE
    STATUS      current
    DESCRIPTION
        "SNMPTrap, float ir Channel-03 in slot 0"
::= { slot0-ir-Trap 52 }

slot0Trap-ir-52 NOTIFICATION-TYPE
    STATUS      current
    DESCRIPTION
        "SNMPTrap, float ir Channel-04 in slot 0"
::= { slot0-ir-Trap 53 }

slot0Trap-ir-53 NOTIFICATION-TYPE
    STATUS      current
    DESCRIPTION
        "SNMPTrap, float ir Channel-05 in slot 0"
::= { slot0-ir-Trap 54 }

slot0Trap-ir-54 NOTIFICATION-TYPE
    STATUS      current
    DESCRIPTION
        "SNMPTrap, float ir Channel-06 in slot 0"
::= { slot0-ir-Trap 55 }

slot0Trap-ir-55 NOTIFICATION-TYPE
    STATUS      current
    DESCRIPTION
        "SNMPTrap, float ir Channel-07 in slot 0"
::= { slot0-ir-Trap 56 }

slot0Trap-ir-56 NOTIFICATION-TYPE
    STATUS      current
    DESCRIPTION
        "SNMPTrap, float ir Channel-08 in slot 0"
::= { slot0-ir-Trap 57 }

slot0Trap-ir-57 NOTIFICATION-TYPE
    STATUS      current
    DESCRIPTION
        "SNMPTrap, float ir Channel-09 in slot 0"
::= { slot0-ir-Trap 58 }

slot0Trap-ir-58 NOTIFICATION-TYPE
    STATUS      current
    DESCRIPTION
        "SNMPTrap, float ir Channel-10 in slot 0"
::= { slot0-ir-Trap 59 }

slot0Trap-ir-59 NOTIFICATION-TYPE
    STATUS      current
    DESCRIPTION
        "SNMPTrap, float ir Channel-11 in slot 0"
::= { slot0-ir-Trap 60 }

slot0Trap-ir-60 NOTIFICATION-TYPE
    STATUS      current
    DESCRIPTION
        "SNMPTrap, float ir Channel-12 in slot 0"
::= { slot0-ir-Trap 61 }

slot0Trap-ir-61 NOTIFICATION-TYPE
    STATUS      current
    DESCRIPTION
        "SNMPTrap, float ir Channel-13 in slot 0"
::= { slot0-ir-Trap 62 }

slot0Trap-ir-62 NOTIFICATION-TYPE
    STATUS      current
    DESCRIPTION
        "SNMPTrap, float ir Channel-14 in slot 0"
::= { slot0-ir-Trap 63 }

slot0Trap-ir-63 NOTIFICATION-TYPE
    STATUS      current
    DESCRIPTION
        "SNMPTrap, float ir Channel-15 in slot 0"
::= { slot0-ir-Trap 64 }

slot0Trap-ir-64 NOTIFICATION-TYPE
    STATUS      current
    DESCRIPTION
        "SNMPTrap, float ir Channel-16 in slot 0"
::= { slot0-ir-Trap 65 }

slot0Trap-ir-65 NOTIFICATION-TYPE
    STATUS      current
    DESCRIPTION
        "SNMPTrap, float ir Channel-17 in slot 0"
::= { slot0-ir-Trap 66 }

slot0Trap-ir-66 NOTIFICATION-TYPE
    STATUS      current
    DESCRIPTION
        "SNMPTrap, float ir Channel-18 in slot 0"
::= { slot0-ir-Trap 67 }

slot0Trap-ir-67 NOTIFICATION-TYPE
    STATUS      current
    DESCRIPTION
        "SNMPTrap, float ir Channel-19 in slot 0"
::= { slot0-ir-Trap 68 }

slot0Trap-ir-68 NOTIFICATION-TYPE
    STATUS      current
    DESCRIPTION
        "SNMPTrap, float ir Channel-20 in slot 0"
::= { slot0-ir-Trap 69 }

slot0Trap-ir-69 NOTIFICATION-TYPE
    STATUS      current
    DESCRIPTION
        "SNMPTrap, float ir Channel-21 in slot 0"
::= { slot0-ir-Trap 70 }

slot0Trap-ir-70 NOTIFICATION-TYPE
    STATUS      current
    DESCRIPTION
        "SNMPTrap, float ir Channel-22 in slot 0"
::= { slot0-ir-Trap 71 }

slot0Trap-ir-71 NOTIFICATION-TYPE
    STATUS      current
    DESCRIPTION
        "SNMPTrap, float ir Channel-23 in slot 0"
::= { slot0-ir-Trap 72 }

slot0Trap-ir-72 NOTIFICATION-TYPE
    STATUS      current
    DESCRIPTION
        "SNMPTrap, float ir Channel-24 in slot 0"
::= { slot0-ir-Trap 73 }

slot0Trap-ir-73 NOTIFICATION-TYPE
    STATUS      current
    DESCRIPTION
        "SNMPTrap, float ir Channel-25 in slot 0"
::= { slot0-ir-Trap 74 }

slot0Trap-ir-74 NOTIFICATION-TYPE
    STATUS      current
    DESCRIPTION
        "SNMPTrap, float ir Channel-26 in slot 0"
::= { slot0-ir-Trap 75 }

slot0Trap-ir-75 NOTIFICATION-TYPE
    STATUS      current
    DESCRIPTION
        "SNMPTrap, float ir Channel-27 in slot 0"
::= { slot0-ir-Trap 76 }

slot0Trap-ir-76 NOTIFICATION-TYPE
    STATUS      current
    DESCRIPTION
        "SNMPTrap, float ir Channel-28 in slot 0"
::= { slot0-ir-Trap 77 }

slot0Trap-ir-77 NOTIFICATION-TYPE
    STATUS      current
    DESCRIPTION
        "SNMPTrap, float ir Channel-29 in slot 0"
::= { slot0-ir-Trap 78 }

slot0Trap-ir-78 NOTIFICATION-TYPE
    STATUS      current
    DESCRIPTION
        "SNMPTrap, float ir Channel-30 in slot 0"
::= { slot0-ir-Trap 79 }

slot0Trap-ir-79 NOTIFICATION-TYPE
    STATUS      current
    DESCRIPTION
        "SNMPTrap, float ir Channel-31 in slot 0"
::= { slot0-ir-Trap 80}

slot0Trap-ir-80 NOTIFICATION-TYPE
    STATUS      current
    DESCRIPTION
        "SNMPTrap, float ir Channel-32 in slot 0"
::= { slot0-ir-Trap 81 }

slot0Trap-ir-81 NOTIFICATION-TYPE
    STATUS      current
    DESCRIPTION
        "SNMPTrap, float ir Channel-33 in slot 0"
::= { slot0-ir-Trap 82 }

slot0Trap-ir-82 NOTIFICATION-TYPE
    STATUS      current
    DESCRIPTION
        "SNMPTrap, float ir Channel-34 in slot 0"
::= { slot0-ir-Trap 83 }

slot0Trap-ir-83 NOTIFICATION-TYPE
    STATUS      current
    DESCRIPTION
        "SNMPTrap, float ir Channel-35 in slot 0"
::= { slot0-ir-Trap 84 }

slot0Trap-ir-84 NOTIFICATION-TYPE
    STATUS      current
    DESCRIPTION
        "SNMPTrap, float ir Channel-36 in slot 0"
::= { slot0-ir-Trap 85 }

slot0Trap-ir-85 NOTIFICATION-TYPE
    STATUS      current
    DESCRIPTION
        "SNMPTrap, float ir Channel-37 in slot 0"
::= { slot0-ir-Trap 86 }

slot0Trap-ir-86 NOTIFICATION-TYPE
    STATUS      current
    DESCRIPTION
        "SNMPTrap, float ir Channel-38 in slot 0"
::= { slot0-ir-Trap 87 }

slot0Trap-ir-87 NOTIFICATION-TYPE
    STATUS      current
    DESCRIPTION
        "SNMPTrap, float ir Channel-39 in slot 0"
::= { slot0-ir-Trap 88 }

slot0Trap-ir-88 NOTIFICATION-TYPE
    STATUS      current
    DESCRIPTION
        "SNMPTrap, float ir Channel-40 in slot 0"
::= { slot0-ir-Trap 89 }

slot0Trap-ir-89 NOTIFICATION-TYPE
    STATUS      current
    DESCRIPTION
        "SNMPTrap, float ir Channel-41 in slot 0"
::= { slot0-ir-Trap 90 }

slot0Trap-ir-90 NOTIFICATION-TYPE
    STATUS      current
    DESCRIPTION
        "SNMPTrap, float ir Channel-42 in slot 0"
::= { slot0-ir-Trap 91 }

slot0Trap-ir-91 NOTIFICATION-TYPE
    STATUS      current
    DESCRIPTION
        "SNMPTrap, float ir Channel-43 in slot 0"
::= { slot0-ir-Trap 92 }

slot0Trap-ir-92 NOTIFICATION-TYPE
    STATUS      current
    DESCRIPTION
        "SNMPTrap, float ir Channel-44 in slot 0"
::= { slot0-ir-Trap 93 }

slot0Trap-ir-93 NOTIFICATION-TYPE
    STATUS      current
    DESCRIPTION
        "SNMPTrap, float ir Channel-45 in slot 0"
::= { slot0-ir-Trap 94 }

slot0Trap-ir-94 NOTIFICATION-TYPE
    STATUS      current
    DESCRIPTION
        "SNMPTrap, float ir Channel-46 in slot 0"
::= { slot0-ir-Trap 95 }

slot0Trap-ir-95 NOTIFICATION-TYPE
    STATUS      current
    DESCRIPTION
        "SNMPTrap, float ir Channel-47 in slot 0"
::= { slot0-ir-Trap 96 }

slot0Trap-ir-96 NOTIFICATION-TYPE
    STATUS      current
    DESCRIPTION
        "SNMPTrap, bool ir Channel-00 in slot 0"
::= { slot0-ir-Trap 97 }

slot0Trap-ir-97 NOTIFICATION-TYPE
    STATUS      current
    DESCRIPTION
        "SNMPTrap, bool ir Channel-01 in slot 0"
::= { slot0-ir-Trap 98 }

slot0Trap-ir-98 NOTIFICATION-TYPE
    STATUS      current
    DESCRIPTION
        "SNMPTrap, bool ir Channel-02 in slot 0"
::= { slot0-ir-Trap 99 }

slot0Trap-ir-99 NOTIFICATION-TYPE
    STATUS      current
    DESCRIPTION
        "SNMPTrap, bool ir Channel-03 in slot 0"
::= { slot0-ir-Trap 100 }

slot0Trap-ir-100 NOTIFICATION-TYPE
    STATUS      current
    DESCRIPTION
        "SNMPTrap, bool ir Channel-04 in slot 0"
::= { slot0-ir-Trap 101 }

slot0Trap-ir-101 NOTIFICATION-TYPE
    STATUS      current
    DESCRIPTION
        "SNMPTrap, bool ir Channel-05 in slot 0"
::= { slot0-ir-Trap 102 }

slot0Trap-ir-102 NOTIFICATION-TYPE
    STATUS      current
    DESCRIPTION
        "SNMPTrap, bool ir Channel-06 in slot 0"
::= { slot0-ir-Trap 103 }

slot0Trap-ir-103 NOTIFICATION-TYPE
    STATUS      current
    DESCRIPTION
        "SNMPTrap, bool ir Channel-07 in slot 0"
::= { slot0-ir-Trap 104 }

slot0Trap-ir-104 NOTIFICATION-TYPE
    STATUS      current
    DESCRIPTION
        "SNMPTrap, bool ir Channel-08 in slot 0"
::= { slot0-ir-Trap 105 }

slot0Trap-ir-105 NOTIFICATION-TYPE
    STATUS      current
    DESCRIPTION
        "SNMPTrap, bool ir Channel-09 in slot 0"
::= { slot0-ir-Trap 106 }

slot0Trap-ir-106 NOTIFICATION-TYPE
    STATUS      current
    DESCRIPTION
        "SNMPTrap, bool ir Channel-10 in slot 0"
::= { slot0-ir-Trap 107 }

slot0Trap-ir-107 NOTIFICATION-TYPE
    STATUS      current
    DESCRIPTION
        "SNMPTrap, bool ir Channel-11 in slot 0"
::= { slot0-ir-Trap 108 }

slot0Trap-ir-108 NOTIFICATION-TYPE
    STATUS      current
    DESCRIPTION
        "SNMPTrap, bool ir Channel-12 in slot 0"
::= { slot0-ir-Trap 109 }

slot0Trap-ir-109 NOTIFICATION-TYPE
    STATUS      current
    DESCRIPTION
        "SNMPTrap, bool ir Channel-13 in slot 0"
::= { slot0-ir-Trap 110 }

slot0Trap-ir-110 NOTIFICATION-TYPE
    STATUS      current
    DESCRIPTION
        "SNMPTrap, bool ir Channel-14 in slot 0"
::= { slot0-ir-Trap 111 }

slot0Trap-ir-111 NOTIFICATION-TYPE
    STATUS      current
    DESCRIPTION
        "SNMPTrap, bool ir Channel-15 in slot 0"
::= { slot0-ir-Trap 112 }

slot0Trap-ir-112 NOTIFICATION-TYPE
    STATUS      current
    DESCRIPTION
        "SNMPTrap, bool ir Channel-16 in slot 0"
::= { slot0-ir-Trap 113 }

slot0Trap-ir-113 NOTIFICATION-TYPE
    STATUS      current
    DESCRIPTION
        "SNMPTrap, bool ir Channel-17 in slot 0"
::= { slot0-ir-Trap 114 }

slot0Trap-ir-114 NOTIFICATION-TYPE
    STATUS      current
    DESCRIPTION
        "SNMPTrap, bool ir Channel-18 in slot 0"
::= { slot0-ir-Trap 115 }

slot0Trap-ir-115 NOTIFICATION-TYPE
    STATUS      current
    DESCRIPTION
        "SNMPTrap, bool ir Channel-19 in slot 0"
::= { slot0-ir-Trap 116 }

slot0Trap-ir-116 NOTIFICATION-TYPE
    STATUS      current
    DESCRIPTION
        "SNMPTrap, bool ir Channel-20 in slot 0"
::= { slot0-ir-Trap 117 }

slot0Trap-ir-117 NOTIFICATION-TYPE
    STATUS      current
    DESCRIPTION
        "SNMPTrap, bool ir Channel-21 in slot 0"
::= { slot0-ir-Trap 118 }

slot0Trap-ir-118 NOTIFICATION-TYPE
    STATUS      current
    DESCRIPTION
        "SNMPTrap, bool ir Channel-22 in slot 0"
::= { slot0-ir-Trap 119 }

slot0Trap-ir-119 NOTIFICATION-TYPE
    STATUS      current
    DESCRIPTION
        "SNMPTrap, bool ir Channel-23 in slot 0"
::= { slot0-ir-Trap 120 }

slot0Trap-ir-120 NOTIFICATION-TYPE
    STATUS      current
    DESCRIPTION
        "SNMPTrap, bool ir Channel-24 in slot 0"
::= { slot0-ir-Trap 121 }

slot0Trap-ir-121 NOTIFICATION-TYPE
    STATUS      current
    DESCRIPTION
        "SNMPTrap, bool ir Channel-25 in slot 0"
::= { slot0-ir-Trap 122 }

slot0Trap-ir-122 NOTIFICATION-TYPE
    STATUS      current
    DESCRIPTION
        "SNMPTrap, bool ir Channel-26 in slot 0"
::= { slot0-ir-Trap 123 }

slot0Trap-ir-123 NOTIFICATION-TYPE
    STATUS      current
    DESCRIPTION
        "SNMPTrap, bool ir Channel-27 in slot 0"
::= { slot0-ir-Trap 124 }

slot0Trap-ir-124 NOTIFICATION-TYPE
    STATUS      current
    DESCRIPTION
        "SNMPTrap, bool ir Channel-28 in slot 0"
::= { slot0-ir-Trap 125 }

slot0Trap-ir-125 NOTIFICATION-TYPE
    STATUS      current
    DESCRIPTION
        "SNMPTrap, bool ir Channel-29 in slot 0"
::= { slot0-ir-Trap 126 }

slot0Trap-ir-126 NOTIFICATION-TYPE
    STATUS      current
    DESCRIPTION
        "SNMPTrap, bool ir Channel-30 in slot 0"
::= { slot0-ir-Trap 127 }

slot0Trap-ir-127 NOTIFICATION-TYPE
    STATUS      current
    DESCRIPTION
        "SNMPTrap, bool ir Channel-31 in slot 0"
::= { slot0-ir-Trap 128 }

slot0Trap-ir-128 NOTIFICATION-TYPE
    STATUS      current
    DESCRIPTION
        "SNMPTrap, bool ir Channel-32 in slot 0"
::= { slot0-ir-Trap 129 }

slot0Trap-ir-129 NOTIFICATION-TYPE
    STATUS      current
    DESCRIPTION
        "SNMPTrap, bool ir Channel-33 in slot 0"
::= { slot0-ir-Trap 130 }

slot0Trap-ir-130 NOTIFICATION-TYPE
    STATUS      current
    DESCRIPTION
        "SNMPTrap, bool ir Channel-34 in slot 0"
::= { slot0-ir-Trap 131 }

slot0Trap-ir-131 NOTIFICATION-TYPE
    STATUS      current
    DESCRIPTION
        "SNMPTrap, bool ir Channel-35 in slot 0"
::= { slot0-ir-Trap 132 }

slot0Trap-ir-132 NOTIFICATION-TYPE
    STATUS      current
    DESCRIPTION
        "SNMPTrap, bool ir Channel-36 in slot 0"
::= { slot0-ir-Trap 133 }

slot0Trap-ir-133 NOTIFICATION-TYPE
    STATUS      current
    DESCRIPTION
        "SNMPTrap, bool ir Channel-37 in slot 0"
::= { slot0-ir-Trap 134 }

slot0Trap-ir-134 NOTIFICATION-TYPE
    STATUS      current
    DESCRIPTION
        "SNMPTrap, bool ir Channel-38 in slot 0"
::= { slot0-ir-Trap 135 }

slot0Trap-ir-135 NOTIFICATION-TYPE
    STATUS      current
    DESCRIPTION
        "SNMPTrap, bool ir Channel-39 in slot 0"
::= { slot0-ir-Trap 136 }

slot0Trap-ir-136 NOTIFICATION-TYPE
    STATUS      current
    DESCRIPTION
        "SNMPTrap, bool ir Channel-40 in slot 0"
::= { slot0-ir-Trap 137 }

slot0Trap-ir-137 NOTIFICATION-TYPE
    STATUS      current
    DESCRIPTION
        "SNMPTrap, bool ir Channel-41 in slot 0"
::= { slot0-ir-Trap 138 }

slot0Trap-ir-138 NOTIFICATION-TYPE
    STATUS      current
    DESCRIPTION
        "SNMPTrap, bool ir Channel-42 in slot 0"
::= { slot0-ir-Trap 139 }

slot0Trap-ir-139 NOTIFICATION-TYPE
    STATUS      current
    DESCRIPTION
        "SNMPTrap, bool ir Channel-43 in slot 0"
::= { slot0-ir-Trap 140 }

slot0Trap-ir-140 NOTIFICATION-TYPE
    STATUS      current
    DESCRIPTION
        "SNMPTrap, bool ir Channel-44 in slot 0"
::= { slot0-ir-Trap 141 }

slot0Trap-ir-141 NOTIFICATION-TYPE
    STATUS      current
    DESCRIPTION
        "SNMPTrap, bool ir Channel-45 in slot 0"
::= { slot0-ir-Trap 142 }

slot0Trap-ir-142 NOTIFICATION-TYPE
    STATUS      current
    DESCRIPTION
        "SNMPTrap, bool ir Channel-46 in slot 0"
::= { slot0-ir-Trap 143 }

slot0Trap-ir-143 NOTIFICATION-TYPE
    STATUS      current
    DESCRIPTION
        "SNMPTrap, bool ir Channel-47 in slot 0"
::= { slot0-ir-Trap 144 }

slot0Trap-ir-144 NOTIFICATION-TYPE
    STATUS      current
    DESCRIPTION
        "SNMPTrap, dword ir Channel-00 in slot 0"
::= { slot0-ir-Trap 145 }

slot0Trap-ir-145 NOTIFICATION-TYPE
    STATUS      current
    DESCRIPTION
        "SNMPTrap, dword ir Channel-01 in slot 0"
::= { slot0-ir-Trap 146 }

slot0Trap-ir-146 NOTIFICATION-TYPE
    STATUS      current
    DESCRIPTION
        "SNMPTrap, dword ir Channel-02 in slot 0"
::= { slot0-ir-Trap 147 }

slot0Trap-ir-147 NOTIFICATION-TYPE
    STATUS      current
    DESCRIPTION
        "SNMPTrap, dword ir Channel-03 in slot 0"
::= { slot0-ir-Trap 148 }

slot0Trap-ir-148 NOTIFICATION-TYPE
    STATUS      current
    DESCRIPTION
        "SNMPTrap, dword ir Channel-04 in slot 0"
::= { slot0-ir-Trap 149 }

slot0Trap-ir-149 NOTIFICATION-TYPE
    STATUS      current
    DESCRIPTION
        "SNMPTrap, dword ir Channel-05 in slot 0"
::= { slot0-ir-Trap 150 }

slot0Trap-ir-150 NOTIFICATION-TYPE
    STATUS      current
    DESCRIPTION
        "SNMPTrap, dword ir Channel-06 in slot 0"
::= { slot0-ir-Trap 151 }

slot0Trap-ir-151 NOTIFICATION-TYPE
    STATUS      current
    DESCRIPTION
        "SNMPTrap, dword ir Channel-07 in slot 0"
::= { slot0-ir-Trap 152 }

slot0Trap-ir-152 NOTIFICATION-TYPE
    STATUS      current
    DESCRIPTION
        "SNMPTrap, dword ir Channel-08 in slot 0"
::= { slot0-ir-Trap 153 }

slot0Trap-ir-153 NOTIFICATION-TYPE
    STATUS      current
    DESCRIPTION
        "SNMPTrap, dword ir Channel-09 in slot 0"
::= { slot0-ir-Trap 154 }

slot0Trap-ir-154 NOTIFICATION-TYPE
    STATUS      current
    DESCRIPTION
        "SNMPTrap, dword ir Channel-10 in slot 0"
::= { slot0-ir-Trap 155 }

slot0Trap-ir-155 NOTIFICATION-TYPE
    STATUS      current
    DESCRIPTION
        "SNMPTrap, dword ir Channel-11 in slot 0"
::= { slot0-ir-Trap 156 }

slot0Trap-ir-156 NOTIFICATION-TYPE
    STATUS      current
    DESCRIPTION
        "SNMPTrap, dword ir Channel-12 in slot 0"
::= { slot0-ir-Trap 157 }

slot0Trap-ir-157 NOTIFICATION-TYPE
    STATUS      current
    DESCRIPTION
        "SNMPTrap, dword ir Channel-13 in slot 0"
::= { slot0-ir-Trap 158 }

slot0Trap-ir-158 NOTIFICATION-TYPE
    STATUS      current
    DESCRIPTION
        "SNMPTrap, dword ir Channel-14 in slot 0"
::= { slot0-ir-Trap 159 }

slot0Trap-ir-159 NOTIFICATION-TYPE
    STATUS      current
    DESCRIPTION
        "SNMPTrap, dword ir Channel-15 in slot 0"
::= { slot0-ir-Trap 160 }

slot0Trap-ir-160 NOTIFICATION-TYPE
    STATUS      current
    DESCRIPTION
        "SNMPTrap, dword ir Channel-16 in slot 0"
::= { slot0-ir-Trap 161 }

slot0Trap-ir-161 NOTIFICATION-TYPE
    STATUS      current
    DESCRIPTION
        "SNMPTrap, dword ir Channel-17 in slot 0"
::= { slot0-ir-Trap 162 }

slot0Trap-ir-162 NOTIFICATION-TYPE
    STATUS      current
    DESCRIPTION
        "SNMPTrap, dword ir Channel-18 in slot 0"
::= { slot0-ir-Trap 163 }

slot0Trap-ir-163 NOTIFICATION-TYPE
    STATUS      current
    DESCRIPTION
        "SNMPTrap, dword ir Channel-19 in slot 0"
::= { slot0-ir-Trap 164 }

slot0Trap-ir-164 NOTIFICATION-TYPE
    STATUS      current
    DESCRIPTION
        "SNMPTrap, dword ir Channel-20 in slot 0"
::= { slot0-ir-Trap 165 }

slot0Trap-ir-165 NOTIFICATION-TYPE
    STATUS      current
    DESCRIPTION
        "SNMPTrap, dword ir Channel-21 in slot 0"
::= { slot0-ir-Trap 166 }

slot0Trap-ir-166 NOTIFICATION-TYPE
    STATUS      current
    DESCRIPTION
        "SNMPTrap, dword ir Channel-22 in slot 0"
::= { slot0-ir-Trap 167 }

slot0Trap-ir-167 NOTIFICATION-TYPE
    STATUS      current
    DESCRIPTION
        "SNMPTrap, dword ir Channel-23 in slot 0"
::= { slot0-ir-Trap 168 }

slot0Trap-ir-168 NOTIFICATION-TYPE
    STATUS      current
    DESCRIPTION
        "SNMPTrap, dword ir Channel-24 in slot 0"
::= { slot0-ir-Trap 169 }

slot0Trap-ir-169 NOTIFICATION-TYPE
    STATUS      current
    DESCRIPTION
        "SNMPTrap, dword ir Channel-25 in slot 0"
::= { slot0-ir-Trap 170 }

slot0Trap-ir-170 NOTIFICATION-TYPE
    STATUS      current
    DESCRIPTION
        "SNMPTrap, dword ir Channel-26 in slot 0"
::= { slot0-ir-Trap 171 }

slot0Trap-ir-171 NOTIFICATION-TYPE
    STATUS      current
    DESCRIPTION
        "SNMPTrap, dword ir Channel-27 in slot 0"
::= { slot0-ir-Trap 172 }

slot0Trap-ir-172 NOTIFICATION-TYPE
    STATUS      current
    DESCRIPTION
        "SNMPTrap, dword ir Channel-28 in slot 0"
::= { slot0-ir-Trap 173 }

slot0Trap-ir-173 NOTIFICATION-TYPE
    STATUS      current
    DESCRIPTION
        "SNMPTrap, dword ir Channel-29 in slot 0"
::= { slot0-ir-Trap 174 }

slot0Trap-ir-174 NOTIFICATION-TYPE
    STATUS      current
    DESCRIPTION
        "SNMPTrap, dword ir Channel-30 in slot 0"
::= { slot0-ir-Trap 175 }

slot0Trap-ir-175 NOTIFICATION-TYPE
    STATUS      current
    DESCRIPTION
        "SNMPTrap, dword ir Channel-31 in slot 0"
::= { slot0-ir-Trap 176 }

slot0Trap-ir-176 NOTIFICATION-TYPE
    STATUS      current
    DESCRIPTION
        "SNMPTrap, dword ir Channel-32 in slot 0"
::= { slot0-ir-Trap 177 }

slot0Trap-ir-177 NOTIFICATION-TYPE
    STATUS      current
    DESCRIPTION
        "SNMPTrap, dword ir Channel-33 in slot 0"
::= { slot0-ir-Trap 178 }

slot0Trap-ir-178 NOTIFICATION-TYPE
    STATUS      current
    DESCRIPTION
        "SNMPTrap, dword ir Channel-34 in slot 0"
::= { slot0-ir-Trap 179 }

slot0Trap-ir-179 NOTIFICATION-TYPE
    STATUS      current
    DESCRIPTION
        "SNMPTrap, dword ir Channel-35 in slot 0"
::= { slot0-ir-Trap 180 }

slot0Trap-ir-180 NOTIFICATION-TYPE
    STATUS      current
    DESCRIPTION
        "SNMPTrap, dword ir Channel-36 in slot 0"
::= { slot0-ir-Trap 181 }

slot0Trap-ir-181 NOTIFICATION-TYPE
    STATUS      current
    DESCRIPTION
        "SNMPTrap, dword ir Channel-37 in slot 0"
::= { slot0-ir-Trap 182 }

slot0Trap-ir-182 NOTIFICATION-TYPE
    STATUS      current
    DESCRIPTION
        "SNMPTrap, dword ir Channel-38 in slot 0"
::= { slot0-ir-Trap 183 }

slot0Trap-ir-183 NOTIFICATION-TYPE
    STATUS      current
    DESCRIPTION
        "SNMPTrap, dword ir Channel-39 in slot 0"
::= { slot0-ir-Trap 184 }

slot0Trap-ir-184 NOTIFICATION-TYPE
    STATUS      current
    DESCRIPTION
        "SNMPTrap, dword ir Channel-40 in slot 0"
::= { slot0-ir-Trap 185 }

slot0Trap-ir-185 NOTIFICATION-TYPE
    STATUS      current
    DESCRIPTION
        "SNMPTrap, dword ir Channel-41 in slot 0"
::= { slot0-ir-Trap 186 }

slot0Trap-ir-186 NOTIFICATION-TYPE
    STATUS      current
    DESCRIPTION
        "SNMPTrap, dword ir Channel-42 in slot 0"
::= { slot0-ir-Trap 187 }

slot0Trap-ir-187 NOTIFICATION-TYPE
    STATUS      current
    DESCRIPTION
        "SNMPTrap, dword ir Channel-43 in slot 0"
::= { slot0-ir-Trap 188 }

slot0Trap-ir-188 NOTIFICATION-TYPE
    STATUS      current
    DESCRIPTION
        "SNMPTrap, dword ir Channel-44 in slot 0"
::= { slot0-ir-Trap 189 }

slot0Trap-ir-189 NOTIFICATION-TYPE
    STATUS      current
    DESCRIPTION
        "SNMPTrap, dword ir Channel-45 in slot 0"
::= { slot0-ir-Trap 190 }

slot0Trap-ir-190 NOTIFICATION-TYPE
    STATUS      current
    DESCRIPTION
        "SNMPTrap, dword ir Channel-46 in slot 0"
::= { slot0-ir-Trap 191 }

slot0Trap-ir-191 NOTIFICATION-TYPE
    STATUS      current
    DESCRIPTION
        "SNMPTrap, dword ir Channel-47 in slot 0"
::= { slot0-ir-Trap 192 }

----------------------------------------------------------------
-- 1.3.6.1.4.1.8691.10.2500.11.10
    slot0-vc-Trap OBJECT IDENTIFIER ::= { slot0-io-Trap 10 }
----------------------------------------------------------------

slot0Trap-vc-00 NOTIFICATION-TYPE
    STATUS      current
    DESCRIPTION
        "SNMPTrap, vc channel-00 in slot 0"
::= { slot0-vc-Trap 1 }

slot0Trap-vc-01 NOTIFICATION-TYPE
    STATUS      current
    DESCRIPTION
        "SNMPTrap, vc channel-01 in slot 0"
::= { slot0-vc-Trap 2 }

slot0Trap-vc-02 NOTIFICATION-TYPE
    STATUS      current
    DESCRIPTION
        "SNMPTrap, vc channel-02 in slot 0"
::= { slot0-vc-Trap 3 }

slot0Trap-vc-03 NOTIFICATION-TYPE
    STATUS      current
    DESCRIPTION
        "SNMPTrap, vc channel-03 in slot 0"
::= { slot0-vc-Trap 4 }

slot0Trap-vc-04 NOTIFICATION-TYPE
    STATUS      current
    DESCRIPTION
        "SNMPTrap, vc channel-04 in slot 0"
::= { slot0-vc-Trap 5 }

slot0Trap-vc-05 NOTIFICATION-TYPE
    STATUS      current
    DESCRIPTION
        "SNMPTrap, vc channel-05 in slot 0"
::= { slot0-vc-Trap 6 }

slot0Trap-vc-06 NOTIFICATION-TYPE
    STATUS      current
    DESCRIPTION
        "SNMPTrap, vc channel-06 in slot 0"
::= { slot0-vc-Trap 7 }

slot0Trap-vc-07 NOTIFICATION-TYPE
    STATUS      current
    DESCRIPTION
        "SNMPTrap, vc channel-07 in slot 0"
::= { slot0-vc-Trap 8 }

slot0Trap-vc-08 NOTIFICATION-TYPE
    STATUS      current
    DESCRIPTION
        "SNMPTrap, vc channel-08 in slot 0"
::= { slot0-vc-Trap 9 }

slot0Trap-vc-09 NOTIFICATION-TYPE
    STATUS      current
    DESCRIPTION
        "SNMPTrap, vc channel-09 in slot 0"
::= { slot0-vc-Trap 10 }

slot0Trap-vc-10 NOTIFICATION-TYPE
    STATUS      current
    DESCRIPTION
        "SNMPTrap, vc channel-10 in slot 0"
::= { slot0-vc-Trap 11 }

slot0Trap-vc-11 NOTIFICATION-TYPE
    STATUS      current
    DESCRIPTION
        "SNMPTrap, vc channel-11 in slot 0"
::= { slot0-vc-Trap 12 }

slot0Trap-vc-12 NOTIFICATION-TYPE
    STATUS      current
    DESCRIPTION
        "SNMPTrap, vc channel-12 in slot 0"
::= { slot0-vc-Trap 13 }

slot0Trap-vc-13 NOTIFICATION-TYPE
    STATUS      current
    DESCRIPTION
        "SNMPTrap, vc channel-13 in slot 0"
::= { slot0-vc-Trap 14 }

slot0Trap-vc-14 NOTIFICATION-TYPE
    STATUS      current
    DESCRIPTION
        "SNMPTrap, vc channel-14 in slot 0"
::= { slot0-vc-Trap 15 }

slot0Trap-vc-15 NOTIFICATION-TYPE
    STATUS      current
    DESCRIPTION
        "SNMPTrap, vc channel-15 in slot 0"
::= { slot0-vc-Trap 16 }

----------------------------------------------------------------
-- 1.3.6.1.4.1.8691.10.2500.20
    slot1-io OBJECT IDENTIFIER ::= { ioLogik2500 20 }
----------------------------------------------------------------
-- slot 1 DI
slot1-diTable OBJECT-TYPE
		SYNTAX 			SEQUENCE OF Slot1-diDef
		MAX-ACCESS 		not-accessible
		STATUS 			current
		DESCRIPTION		"The di channel table"
		::= { slot1-io 1 }

slot1-di OBJECT-TYPE
		SYNTAX 			Slot1-diDef
		MAX-ACCESS 		not-accessible
		STATUS 			current
		DESCRIPTION		"The di channel item"
		INDEX { slot1-diIndex }
		::= { slot1-diTable 1 }

Slot1-diDef ::= SEQUENCE { 
    	slot1-diIndex		INTEGER,
		slot1-diStatus		Unsigned32,
		slot1-diCounterReset2Init INTEGER		
		}  

slot1-diIndex OBJECT-TYPE
		SYNTAX 			INTEGER (0..15)
		MAX-ACCESS 		read-only
		STATUS 			current
		DESCRIPTION		"The channel index"
		::= { slot1-di 1 }
		
slot1-diStatus OBJECT-TYPE
		SYNTAX 			Unsigned32
		MAX-ACCESS 		read-write
		STATUS 			current
		DESCRIPTION		"The channel di status. 0=off, 1=on in di mode or n=counter value in counter mode"
		::= { slot1-di 2 }

slot1-diCounterReset2Init OBJECT-TYPE
		SYNTAX 			INTEGER 
		MAX-ACCESS 		read-write
		STATUS 			current
		DESCRIPTION		"Trigger counter to initial value. 1=Reset counter to initial value"
		::= { slot1-di 3 }		
		
-- slot 1 DICounterStart
slot1-diCounterStartTable OBJECT-TYPE
		SYNTAX 			SEQUENCE OF Slot1-diCounterStartDef
		MAX-ACCESS 		not-accessible
		STATUS 			current
		DESCRIPTION		"The counter table starting for di"
		::= { slot1-io 39 }

slot1-diCounterStart OBJECT-TYPE
		SYNTAX 			Slot1-diCounterStartDef
		MAX-ACCESS 		not-accessible
		STATUS 			current
		DESCRIPTION		"The counter starting of di item"
		INDEX { slot1-diCounterStartIndex }
		::= { slot1-diCounterStartTable 1 }

Slot1-diCounterStartDef ::= SEQUENCE { 
    		slot1-diCounterStartIndex		INTEGER,
			slot1-diCounterStartStatus		INTEGER				
		}  

slot1-diCounterStartIndex OBJECT-TYPE
		SYNTAX 			INTEGER (0..15)
		MAX-ACCESS 		read-only
		STATUS 			current
		DESCRIPTION		"The channel index for di counter start"
		::= { slot1-diCounterStart 1 }
		
slot1-diCounterStartStatus OBJECT-TYPE
		SYNTAX 			INTEGER (0..1)
		MAX-ACCESS 		read-write
		STATUS 			current
		DESCRIPTION		"The channel status for di counter start. 0=stop, 1=start"
		::= { slot1-diCounterStart 2 }

		
-- slot 1 DO
slot1-doTable OBJECT-TYPE
		SYNTAX 			SEQUENCE OF Slot1-doDef
		MAX-ACCESS 		not-accessible
		STATUS 			current
		DESCRIPTION		"The do channel table"
		::= { slot1-io 2 }

slot1-do OBJECT-TYPE
		SYNTAX 			Slot1-doDef
		MAX-ACCESS 		not-accessible
		STATUS 			current
		DESCRIPTION		"The do channel item"
		INDEX { slot1-doIndex }
		::= { slot1-doTable 1 }

Slot1-doDef ::= SEQUENCE { 
    	slot1-doIndex		INTEGER,
		slot1-doStatus		INTEGER		
		}  

slot1-doIndex OBJECT-TYPE
		SYNTAX 			INTEGER (0..15)
		MAX-ACCESS 		read-only
		STATUS 			current
		DESCRIPTION		"The channel index"
		::= { slot1-do 1 }
		
slot1-doStatus OBJECT-TYPE
		SYNTAX 			INTEGER (0..1)
		MAX-ACCESS 		read-write
		STATUS 			current
		DESCRIPTION		"The channel do status. 0=off, 1=on in do mode or 0=stop, 1=start in pulse mode"
		::= { slot1-do 2 }  

-- slot 1 DIO
slot1-dioTable OBJECT-TYPE
		SYNTAX 			SEQUENCE OF Slot1-dioDef
		MAX-ACCESS 		not-accessible
		STATUS 			current
		DESCRIPTION		"The dio channel table"
		::= { slot1-io 3 }

slot1-dio OBJECT-TYPE
		SYNTAX 			Slot1-dioDef
		MAX-ACCESS 		not-accessible
		STATUS 			current
		DESCRIPTION		"The dio channel item"
		INDEX { slot1-dioIndex }
		::= { slot1-dioTable 1 }

Slot1-dioDef ::= SEQUENCE { 
    	slot1-dioIndex		INTEGER,
		slot1-dioStatus		Unsigned32,
		slot1-dioCounterReset2Init INTEGER		
		}  

slot1-dioIndex OBJECT-TYPE
		SYNTAX 			INTEGER (0..15)
		MAX-ACCESS 		read-only
		STATUS 			current
		DESCRIPTION		"The channel index"
		::= { slot1-dio 1 }
		
slot1-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot1-dio 2 }
		
slot1-dioCounterReset2Init OBJECT-TYPE
		SYNTAX 			INTEGER 
		MAX-ACCESS 		read-write
		STATUS 			current
		DESCRIPTION		"Trigger counter to initial value. 1=Reset counter to initial value"
		::= { slot1-dio 3 }
		
-- slot 1 DIOCounterStart
slot1-dioCounterStartTable OBJECT-TYPE
		SYNTAX 			SEQUENCE OF Slot1-dioCounterStartDef
		MAX-ACCESS 		not-accessible
		STATUS 			current
		DESCRIPTION		"The counter table starting for dio"
		::= { slot1-io 46 }

slot1-dioCounterStart OBJECT-TYPE
		SYNTAX 			Slot1-dioCounterStartDef
		MAX-ACCESS 		not-accessible
		STATUS 			current
		DESCRIPTION		"The counter starting of dio item"
		INDEX { slot1-dioCounterStartIndex }
		::= { slot1-dioCounterStartTable 1 }

Slot1-dioCounterStartDef ::= SEQUENCE { 
    	slot1-dioCounterStartIndex		INTEGER,
		slot1-dioCounterStartStatus		INTEGER		
		}  

slot1-dioCounterStartIndex OBJECT-TYPE
		SYNTAX 			INTEGER (0..15)
		MAX-ACCESS 		read-only
		STATUS 			current
		DESCRIPTION		"The channel index for dio counter start"
		::= { slot1-dioCounterStart 1 }
		
slot1-dioCounterStartStatus OBJECT-TYPE
		SYNTAX 			INTEGER (0..1)
		MAX-ACCESS 		read-write
		STATUS 			current
		DESCRIPTION		"The channel status for dio counter start. 0=stop, 1=start"
		::= { slot1-dioCounterStart 2 }   		
				
		
-- slot 1 Relay
slot1-relayTable OBJECT-TYPE
		SYNTAX 			SEQUENCE OF Slot1-relayDef
		MAX-ACCESS 		not-accessible
		STATUS 			current
		DESCRIPTION		"The relay channel table"
		::= { slot1-io 4 }

slot1-relay OBJECT-TYPE
		SYNTAX 			Slot1-relayDef
		MAX-ACCESS 		not-accessible
		STATUS 			current
		DESCRIPTION		"The relay channel item"
		INDEX { slot1-relayIndex }
		::= { slot1-relayTable 1 }

Slot1-relayDef ::= SEQUENCE { 
    	slot1-relayIndex		INTEGER,
		slot1-relayStatus		INTEGER		
		}  

slot1-relayIndex OBJECT-TYPE
		SYNTAX 			INTEGER (0..15)
		MAX-ACCESS 		read-only
		STATUS 			current
		DESCRIPTION		"The channel index"
		::= { slot1-relay 1 }
		
slot1-relayStatus OBJECT-TYPE
		SYNTAX 			INTEGER (0..1)
		MAX-ACCESS 		read-write
		STATUS 			current
		DESCRIPTION		"The channel relay status. 0=off, 1=on in do mode or 0=stop, 1=start in pulse mode"
		::= { slot1-relay 2 }  

-- slot 1 AI
slot1-aiTable OBJECT-TYPE
		SYNTAX 			SEQUENCE OF Slot1-aiDef
		MAX-ACCESS 		not-accessible
		STATUS 			current
		DESCRIPTION		"The ai channel table"
		::= { slot1-io 5 }

slot1-ai OBJECT-TYPE
		SYNTAX 			Slot1-aiDef
		MAX-ACCESS 		not-accessible
		STATUS 			current
		DESCRIPTION		"The ai channel item"
		INDEX { slot1-aiIndex }
		::= { slot1-aiTable 1 }

Slot1-aiDef ::= SEQUENCE { 
    	slot1-aiIndex		INTEGER,
		slot1-aiStatus		OCTET STRING,
		slot1-aiBurnoutStatus INTEGER		
		}  

slot1-aiIndex OBJECT-TYPE
		SYNTAX 			INTEGER (0..15)
		MAX-ACCESS 		read-only
		STATUS 			current
		DESCRIPTION		"The channel index"
		::= { slot1-ai 1 }
		
slot1-aiStatus OBJECT-TYPE
		SYNTAX 			OCTET STRING
		MAX-ACCESS 		read-only
		STATUS 			current
		DESCRIPTION		"The channel ai scaled value"
		::= { slot1-ai 2 }  

slot1-aiBurnoutStatus OBJECT-TYPE
		SYNTAX 			INTEGER (0..3)
		MAX-ACCESS 		read-only
		STATUS 			current
		DESCRIPTION		"The channel of burnout status (0: normal, 1: burnout, 2: underange, 3: overange)"
		::= { slot1-ai 3 }  

-- slot 1 AO
slot1-aoTable OBJECT-TYPE
		SYNTAX 			SEQUENCE OF Slot1-aoDef
		MAX-ACCESS 		not-accessible
		STATUS 			current
		DESCRIPTION		"The ao channel table"
		::= { slot1-io 6 }

slot1-ao OBJECT-TYPE
		SYNTAX 			Slot1-aoDef
		MAX-ACCESS 		not-accessible
		STATUS 			current
		DESCRIPTION		"The ao channel item"
		INDEX { slot1-aoIndex }
		::= { slot1-aoTable 1 }

Slot1-aoDef ::= SEQUENCE { 
    	slot1-aoIndex		INTEGER,
		slot1-aoStatus		OCTET STRING		
		}  

slot1-aoIndex OBJECT-TYPE
		SYNTAX 			INTEGER (0..15)
		MAX-ACCESS 		read-only
		STATUS 			current
		DESCRIPTION		"The channel index"
		::= { slot1-ao 1 }
		
slot1-aoStatus OBJECT-TYPE
		SYNTAX 			OCTET STRING
		MAX-ACCESS 		read-write
		STATUS 			current
		DESCRIPTION		"The channel ao scaled value"
		::= { slot1-ao 2 }  

-- slot 1 RTD
slot1-rtdTable OBJECT-TYPE
		SYNTAX 			SEQUENCE OF Slot1-rtdDef
		MAX-ACCESS 		not-accessible
		STATUS 			current
		DESCRIPTION		"The rtd channel table"
		::= { slot1-io 7 }

slot1-rtd OBJECT-TYPE
		SYNTAX 			Slot1-rtdDef
		MAX-ACCESS 		not-accessible
		STATUS 			current
		DESCRIPTION		"The rtd channel item"
		INDEX { slot1-rtdIndex }
		::= { slot1-rtdTable 1 }

Slot1-rtdDef ::= SEQUENCE { 
    	slot1-rtdIndex		INTEGER,
		slot1-rtdStatus		OCTET STRING		
		}  

slot1-rtdIndex OBJECT-TYPE
		SYNTAX 			INTEGER (0..15)
		MAX-ACCESS 		read-only
		STATUS 			current
		DESCRIPTION		"The channel index"
		::= { slot1-rtd 1 }
		
slot1-rtdStatus OBJECT-TYPE
		SYNTAX 			OCTET STRING
		MAX-ACCESS 		read-only
		STATUS 			current
		DESCRIPTION		"The channel rtd scaled value"
		::= { slot1-rtd 2 }  

-- slot 1 TC
slot1-tcTable OBJECT-TYPE
		SYNTAX 			SEQUENCE OF Slot1-tcDef
		MAX-ACCESS 		not-accessible
		STATUS 			current
		DESCRIPTION		"The tc channel table"
		::= { slot1-io 8 }

slot1-tc OBJECT-TYPE
		SYNTAX 			Slot1-tcDef
		MAX-ACCESS 		not-accessible
		STATUS 			current
		DESCRIPTION		"The tc channel item"
		INDEX { slot1-tcIndex }
		::= { slot1-tcTable 1 }

Slot1-tcDef ::= SEQUENCE { 
    	slot1-tcIndex		INTEGER,
		slot1-tcStatus		OCTET STRING		
		}  

slot1-tcIndex OBJECT-TYPE
		SYNTAX 			INTEGER (0..15)
		MAX-ACCESS 		read-only
		STATUS 			current
		DESCRIPTION		"The channel index"
		::= { slot1-tc 1 }
		
slot1-tcStatus OBJECT-TYPE
		SYNTAX 			OCTET STRING
		MAX-ACCESS 		read-only
		STATUS 			current
		DESCRIPTION		"The channel tc scaled value"
		::= { slot1-tc 2 }  


----------------------------------------------------------------
-- 1.3.6.1.4.1.8691.10.2500.21
    slot1-io-Trap OBJECT IDENTIFIER ::= { ioLogik2500 21 }
----------------------------------------------------------------

----------------------------------------------------------------
-- 1.3.6.1.4.1.8691.10.2500.21.1
    slot1-di-Trap OBJECT IDENTIFIER ::= { slot1-io-Trap 1 }
----------------------------------------------------------------

slot1Trap-di-00 NOTIFICATION-TYPE
    STATUS      current
    DESCRIPTION
        "SNMPTrap, di channel-00 in slot 1"
::= { slot1-di-Trap 1 }

slot1Trap-di-01 NOTIFICATION-TYPE
    STATUS      current
    DESCRIPTION
        "SNMPTrap, di channel-01 in slot 1"
::= { slot1-di-Trap 2 }

slot1Trap-di-02 NOTIFICATION-TYPE
    STATUS      current
    DESCRIPTION
        "SNMPTrap, di channel-02 in slot 1"
::= { slot1-di-Trap 3 }

slot1Trap-di-03 NOTIFICATION-TYPE
    STATUS      current
    DESCRIPTION
        "SNMPTrap, di channel-03 in slot 1"
::= { slot1-di-Trap 4 }

slot1Trap-di-04 NOTIFICATION-TYPE
    STATUS      current
    DESCRIPTION
        "SNMPTrap, di channel-04 in slot 1"
::= { slot1-di-Trap 5 }

slot1Trap-di-05 NOTIFICATION-TYPE
    STATUS      current
    DESCRIPTION
        "SNMPTrap, di channel-05 in slot 1"
::= { slot1-di-Trap 6 }

slot1Trap-di-06 NOTIFICATION-TYPE
    STATUS      current
    DESCRIPTION
        "SNMPTrap, di channel-06 in slot 1"
::= { slot1-di-Trap 7 }

slot1Trap-di-07 NOTIFICATION-TYPE
    STATUS      current
    DESCRIPTION
        "SNMPTrap, di channel-07 in slot 1"
::= { slot1-di-Trap 8 }

slot1Trap-di-08 NOTIFICATION-TYPE
    STATUS      current
    DESCRIPTION
        "SNMPTrap, di channel-08 in slot 1"
::= { slot1-di-Trap 9 }

slot1Trap-di-09 NOTIFICATION-TYPE
    STATUS      current
    DESCRIPTION
        "SNMPTrap, di channel-09 in slot 1"
::= { slot1-di-Trap 10 }

slot1Trap-di-10 NOTIFICATION-TYPE
    STATUS      current
    DESCRIPTION
        "SNMPTrap, di channel-10 in slot 1"
::= { slot1-di-Trap 11 }

slot1Trap-di-11 NOTIFICATION-TYPE
    STATUS      current
    DESCRIPTION
        "SNMPTrap, di channel-11 in slot 1"
::= { slot1-di-Trap 12 }

slot1Trap-di-12 NOTIFICATION-TYPE
    STATUS      current
    DESCRIPTION
        "SNMPTrap, di channel-12 in slot 1"
::= { slot1-di-Trap 13 }

slot1Trap-di-13 NOTIFICATION-TYPE
    STATUS      current
    DESCRIPTION
        "SNMPTrap, di channel-13 in slot 1"
::= { slot1-di-Trap 14 }

slot1Trap-di-14 NOTIFICATION-TYPE
    STATUS      current
    DESCRIPTION
        "SNMPTrap, di channel-14 in slot 1"
::= { slot1-di-Trap 15 }

slot1Trap-di-15 NOTIFICATION-TYPE
    STATUS      current
    DESCRIPTION
        "SNMPTrap, di channel-15 in slot 1"
::= { slot1-di-Trap 16 }
----------------------------------------------------------------
-- 1.3.6.1.4.1.8691.10.2500.21.2
    slot1-do-Trap OBJECT IDENTIFIER ::= { slot1-io-Trap 2 }
----------------------------------------------------------------

slot1Trap-do-00 NOTIFICATION-TYPE
    STATUS      current
    DESCRIPTION
        "SNMPTrap, do channel-00 in slot 1"
::= { slot1-do-Trap 1 }

slot1Trap-do-01 NOTIFICATION-TYPE
    STATUS      current
    DESCRIPTION
        "SNMPTrap, do channel-01 in slot 1"
::= { slot1-do-Trap 2 }

slot1Trap-do-02 NOTIFICATION-TYPE
    STATUS      current
    DESCRIPTION
        "SNMPTrap, do channel-02 in slot 1"
::= { slot1-do-Trap 3 }

slot1Trap-do-03 NOTIFICATION-TYPE
    STATUS      current
    DESCRIPTION
        "SNMPTrap, do channel-03 in slot 1"
::= { slot1-do-Trap 4 }

slot1Trap-do-04 NOTIFICATION-TYPE
    STATUS      current
    DESCRIPTION
        "SNMPTrap, do channel-04 in slot 1"
::= { slot1-do-Trap 5 }

slot1Trap-do-05 NOTIFICATION-TYPE
    STATUS      current
    DESCRIPTION
        "SNMPTrap, do channel-05 in slot 1"
::= { slot1-do-Trap 6 }

slot1Trap-do-06 NOTIFICATION-TYPE
    STATUS      current
    DESCRIPTION
        "SNMPTrap, do channel-06 in slot 1"
::= { slot1-do-Trap 7 }

slot1Trap-do-07 NOTIFICATION-TYPE
    STATUS      current
    DESCRIPTION
        "SNMPTrap, do channel-07 in slot 1"
::= { slot1-do-Trap 8 }

slot1Trap-do-08 NOTIFICATION-TYPE
    STATUS      current
    DESCRIPTION
        "SNMPTrap, do channel-08 in slot 1"
::= { slot1-do-Trap 9 }

slot1Trap-do-09 NOTIFICATION-TYPE
    STATUS      current
    DESCRIPTION
        "SNMPTrap, do channel-09 in slot 1"
::= { slot1-do-Trap 10 }

slot1Trap-do-10 NOTIFICATION-TYPE
    STATUS      current
    DESCRIPTION
        "SNMPTrap, do channel-10 in slot 1"
::= { slot1-do-Trap 11 }

slot1Trap-do-11 NOTIFICATION-TYPE
    STATUS      current
    DESCRIPTION
        "SNMPTrap, do channel-11 in slot 1"
::= { slot1-do-Trap 12 }

slot1Trap-do-12 NOTIFICATION-TYPE
    STATUS      current
    DESCRIPTION
        "SNMPTrap, do channel-12 in slot 1"
::= { slot1-do-Trap 13 }

slot1Trap-do-13 NOTIFICATION-TYPE
    STATUS      current
    DESCRIPTION
        "SNMPTrap, do channel-13 in slot 1"
::= { slot1-do-Trap 14 }

slot1Trap-do-14 NOTIFICATION-TYPE
    STATUS      current
    DESCRIPTION
        "SNMPTrap, do channel-14 in slot 1"
::= { slot1-do-Trap 15 }

slot1Trap-do-15 NOTIFICATION-TYPE
    STATUS      current
    DESCRIPTION
        "SNMPTrap, do channel-15 in slot 1"
::= { slot1-do-Trap 16 }

----------------------------------------------------------------
-- 1.3.6.1.4.1.8691.10.2500.21.3
    slot1-dio-Trap OBJECT IDENTIFIER ::= { slot1-io-Trap 3 }
----------------------------------------------------------------

slot1Trap-dio-00 NOTIFICATION-TYPE
    STATUS      current
    DESCRIPTION
        "SNMPTrap, dio channel-00 in slot 1"
::= { slot1-dio-Trap 1 }

slot1Trap-dio-01 NOTIFICATION-TYPE
    STATUS      current
    DESCRIPTION
        "SNMPTrap, dio channel-01 in slot 1"
::= { slot1-dio-Trap 2 }

slot1Trap-dio-02 NOTIFICATION-TYPE
    STATUS      current
    DESCRIPTION
        "SNMPTrap, dio channel-02 in slot 1"
::= { slot1-dio-Trap 3 }

slot1Trap-dio-03 NOTIFICATION-TYPE
    STATUS      current
    DESCRIPTION
        "SNMPTrap, dio channel-03 in slot 1"
::= { slot1-dio-Trap 4 }

slot1Trap-dio-04 NOTIFICATION-TYPE
    STATUS      current
    DESCRIPTION
        "SNMPTrap, dio channel-04 in slot 1"
::= { slot1-dio-Trap 5 }

slot1Trap-dio-05 NOTIFICATION-TYPE
    STATUS      current
    DESCRIPTION
        "SNMPTrap, dio channel-05 in slot 1"
::= { slot1-dio-Trap 6 }

slot1Trap-dio-06 NOTIFICATION-TYPE
    STATUS      current
    DESCRIPTION
        "SNMPTrap, dio channel-06 in slot 1"
::= { slot1-dio-Trap 7 }

slot1Trap-dio-07 NOTIFICATION-TYPE
    STATUS      current
    DESCRIPTION
        "SNMPTrap, dio channel-07 in slot 1"
::= { slot1-dio-Trap 8 }

slot1Trap-dio-08 NOTIFICATION-TYPE
    STATUS      current
    DESCRIPTION
        "SNMPTrap, dio channel-08 in slot 1"
::= { slot1-dio-Trap 9 }

slot1Trap-dio-09 NOTIFICATION-TYPE
    STATUS      current
    DESCRIPTION
        "SNMPTrap, dio channel-09 in slot 1"
::= { slot1-dio-Trap 10 }

slot1Trap-dio-10 NOTIFICATION-TYPE
    STATUS      current
    DESCRIPTION
        "SNMPTrap, dio channel-10 in slot 1"
::= { slot1-dio-Trap 11 }

slot1Trap-dio-11 NOTIFICATION-TYPE
    STATUS      current
    DESCRIPTION
        "SNMPTrap, dio channel-11 in slot 1"
::= { slot1-dio-Trap 12 }

slot1Trap-dio-12 NOTIFICATION-TYPE
    STATUS      current
    DESCRIPTION
        "SNMPTrap, dio channel-12 in slot 1"
::= { slot1-dio-Trap 13 }

slot1Trap-dio-13 NOTIFICATION-TYPE
    STATUS      current
    DESCRIPTION
        "SNMPTrap, dio channel-13 in slot 1"
::= { slot1-dio-Trap 14 }

slot1Trap-dio-14 NOTIFICATION-TYPE
    STATUS      current
    DESCRIPTION
        "SNMPTrap, dio channel-14 in slot 1"
::= { slot1-dio-Trap 15 }

slot1Trap-dio-15 NOTIFICATION-TYPE
    STATUS      current
    DESCRIPTION
        "SNMPTrap, dio channel-15 in slot 1"
::= { slot1-dio-Trap 16 }

----------------------------------------------------------------
-- 1.3.6.1.4.1.8691.10.2500.21.4
    slot1-relay-Trap OBJECT IDENTIFIER ::= { slot1-io-Trap 4 }
----------------------------------------------------------------

slot1Trap-relay-00 NOTIFICATION-TYPE
    STATUS      current
    DESCRIPTION
        "SNMPTrap, relay channel-00 in slot 1"
::= { slot1-relay-Trap 1 }

slot1Trap-relay-01 NOTIFICATION-TYPE
    STATUS      current
    DESCRIPTION
        "SNMPTrap, relay channel-01 in slot 1"
::= { slot1-relay-Trap 2 }

slot1Trap-relay-02 NOTIFICATION-TYPE
    STATUS      current
    DESCRIPTION
        "SNMPTrap, relay channel-02 in slot 1"
::= { slot1-relay-Trap 3 }

slot1Trap-relay-03 NOTIFICATION-TYPE
    STATUS      current
    DESCRIPTION
        "SNMPTrap, relay channel-03 in slot 1"
::= { slot1-relay-Trap 4 }

slot1Trap-relay-04 NOTIFICATION-TYPE
    STATUS      current
    DESCRIPTION
        "SNMPTrap, relay channel-04 in slot 1"
::= { slot1-relay-Trap 5 }

slot1Trap-relay-05 NOTIFICATION-TYPE
    STATUS      current
    DESCRIPTION
        "SNMPTrap, relay channel-05 in slot 1"
::= { slot1-relay-Trap 6 }

slot1Trap-relay-06 NOTIFICATION-TYPE
    STATUS      current
    DESCRIPTION
        "SNMPTrap, relay channel-06 in slot 1"
::= { slot1-relay-Trap 7 }

slot1Trap-relay-07 NOTIFICATION-TYPE
    STATUS      current
    DESCRIPTION
        "SNMPTrap, relay channel-07 in slot 1"
::= { slot1-relay-Trap 8 }

slot1Trap-relay-08 NOTIFICATION-TYPE
    STATUS      current
    DESCRIPTION
        "SNMPTrap, relay channel-08 in slot 1"
::= { slot1-relay-Trap 9 }

slot1Trap-relay-09 NOTIFICATION-TYPE
    STATUS      current
    DESCRIPTION
        "SNMPTrap, relay channel-09 in slot 1"
::= { slot1-relay-Trap 10 }

slot1Trap-relay-10 NOTIFICATION-TYPE
    STATUS      current
    DESCRIPTION
        "SNMPTrap, relay channel-10 in slot 1"
::= { slot1-relay-Trap 11 }

slot1Trap-relay-11 NOTIFICATION-TYPE
    STATUS      current
    DESCRIPTION
        "SNMPTrap, relay channel-11 in slot 1"
::= { slot1-relay-Trap 12 }

slot1Trap-relay-12 NOTIFICATION-TYPE
    STATUS      current
    DESCRIPTION
        "SNMPTrap, relay channel-12 in slot 1"
::= { slot1-relay-Trap 13 }

slot1Trap-relay-13 NOTIFICATION-TYPE
    STATUS      current
    DESCRIPTION
        "SNMPTrap, relay channel-13 in slot 1"
::= { slot1-relay-Trap 14 }

slot1Trap-relay-14 NOTIFICATION-TYPE
    STATUS      current
    DESCRIPTION
        "SNMPTrap, relay channel-14 in slot 1"
::= { slot1-relay-Trap 15 }

slot1Trap-relay-15 NOTIFICATION-TYPE
    STATUS      current
    DESCRIPTION
        "SNMPTrap, relay channel-15 in slot 1"
::= { slot1-relay-Trap 16 }

----------------------------------------------------------------
-- 1.3.6.1.4.1.8691.10.2500.21.5
    slot1-ai-Trap OBJECT IDENTIFIER ::= { slot1-io-Trap 5 }
----------------------------------------------------------------

slot1Trap-ai-00 NOTIFICATION-TYPE
    STATUS      current
    DESCRIPTION
        "SNMPTrap, ai channel-00 in slot 1"
::= { slot1-ai-Trap 1 }

slot1Trap-ai-01 NOTIFICATION-TYPE
    STATUS      current
    DESCRIPTION
        "SNMPTrap, ai channel-01 in slot 1"
::= { slot1-ai-Trap 2 }

slot1Trap-ai-02 NOTIFICATION-TYPE
    STATUS      current
    DESCRIPTION
        "SNMPTrap, ai channel-02 in slot 1"
::= { slot1-ai-Trap 3 }

slot1Trap-ai-03 NOTIFICATION-TYPE
    STATUS      current
    DESCRIPTION
        "SNMPTrap, ai channel-03 in slot 1"
::= { slot1-ai-Trap 4 }

slot1Trap-ai-04 NOTIFICATION-TYPE
    STATUS      current
    DESCRIPTION
        "SNMPTrap, ai channel-04 in slot 1"
::= { slot1-ai-Trap 5 }

slot1Trap-ai-05 NOTIFICATION-TYPE
    STATUS      current
    DESCRIPTION
        "SNMPTrap, ai channel-05 in slot 1"
::= { slot1-ai-Trap 6 }

slot1Trap-ai-06 NOTIFICATION-TYPE
    STATUS      current
    DESCRIPTION
        "SNMPTrap, ai channel-06 in slot 1"
::= { slot1-ai-Trap 7 }

slot1Trap-ai-07 NOTIFICATION-TYPE
    STATUS      current
    DESCRIPTION
        "SNMPTrap, ai channel-07 in slot 1"
::= { slot1-ai-Trap 8 }

slot1Trap-ai-08 NOTIFICATION-TYPE
    STATUS      current
    DESCRIPTION
        "SNMPTrap, ai channel-08 in slot 1"
::= { slot1-ai-Trap 9 }

slot1Trap-ai-09 NOTIFICATION-TYPE
    STATUS      current
    DESCRIPTION
        "SNMPTrap, ai channel-09 in slot 1"
::= { slot1-ai-Trap 10 }

slot1Trap-ai-10 NOTIFICATION-TYPE
    STATUS      current
    DESCRIPTION
        "SNMPTrap, ai channel-10 in slot 1"
::= { slot1-ai-Trap 11 }

slot1Trap-ai-11 NOTIFICATION-TYPE
    STATUS      current
    DESCRIPTION
        "SNMPTrap, ai channel-11 in slot 1"
::= { slot1-ai-Trap 12 }

slot1Trap-ai-12 NOTIFICATION-TYPE
    STATUS      current
    DESCRIPTION
        "SNMPTrap, ai channel-12 in slot 1"
::= { slot1-ai-Trap 13 }

slot1Trap-ai-13 NOTIFICATION-TYPE
    STATUS      current
    DESCRIPTION
        "SNMPTrap, ai channel-13 in slot 1"
::= { slot1-ai-Trap 14 }

slot1Trap-ai-14 NOTIFICATION-TYPE
    STATUS      current
    DESCRIPTION
        "SNMPTrap, ai channel-14 in slot 1"
::= { slot1-ai-Trap 15 }

slot1Trap-ai-15 NOTIFICATION-TYPE
    STATUS      current
    DESCRIPTION
        "SNMPTrap, ai channel-15 in slot 1"
::= { slot1-ai-Trap 16 }

----------------------------------------------------------------
-- 1.3.6.1.4.1.8691.10.2500.21.6
    slot1-ao-Trap OBJECT IDENTIFIER ::= { slot1-io-Trap 6 }
----------------------------------------------------------------

slot1Trap-ao-00 NOTIFICATION-TYPE
    STATUS      current
    DESCRIPTION
        "SNMPTrap, ao channel-00 in slot 1"
::= { slot1-ao-Trap 1 }

slot1Trap-ao-01 NOTIFICATION-TYPE
    STATUS      current
    DESCRIPTION
        "SNMPTrap, ao channel-01 in slot 1"
::= { slot1-ao-Trap 2 }

slot1Trap-ao-02 NOTIFICATION-TYPE
    STATUS      current
    DESCRIPTION
        "SNMPTrap, ao channel-02 in slot 1"
::= { slot1-ao-Trap 3 }

slot1Trap-ao-03 NOTIFICATION-TYPE
    STATUS      current
    DESCRIPTION
        "SNMPTrap, ao channel-03 in slot 1"
::= { slot1-ao-Trap 4 }

slot1Trap-ao-04 NOTIFICATION-TYPE
    STATUS      current
    DESCRIPTION
        "SNMPTrap, ao channel-04 in slot 1"
::= { slot1-ao-Trap 5 }

slot1Trap-ao-05 NOTIFICATION-TYPE
    STATUS      current
    DESCRIPTION
        "SNMPTrap, ao channel-05 in slot 1"
::= { slot1-ao-Trap 6 }

slot1Trap-ao-06 NOTIFICATION-TYPE
    STATUS      current
    DESCRIPTION
        "SNMPTrap, ao channel-06 in slot 1"
::= { slot1-ao-Trap 7 }

slot1Trap-ao-07 NOTIFICATION-TYPE
    STATUS      current
    DESCRIPTION
        "SNMPTrap, ao channel-07 in slot 1"
::= { slot1-ao-Trap 8 }

slot1Trap-ao-08 NOTIFICATION-TYPE
    STATUS      current
    DESCRIPTION
        "SNMPTrap, ao channel-08 in slot 1"
::= { slot1-ao-Trap 9 }

slot1Trap-ao-09 NOTIFICATION-TYPE
    STATUS      current
    DESCRIPTION
        "SNMPTrap, ao channel-09 in slot 1"
::= { slot1-ao-Trap 10 }

slot1Trap-ao-10 NOTIFICATION-TYPE
    STATUS      current
    DESCRIPTION
        "SNMPTrap, ao channel-10 in slot 1"
::= { slot1-ao-Trap 11 }

slot1Trap-ao-11 NOTIFICATION-TYPE
    STATUS      current
    DESCRIPTION
        "SNMPTrap, ao channel-11 in slot 1"
::= { slot1-ao-Trap 12 }

slot1Trap-ao-12 NOTIFICATION-TYPE
    STATUS      current
    DESCRIPTION
        "SNMPTrap, ao channel-12 in slot 1"
::= { slot1-ao-Trap 13 }

slot1Trap-ao-13 NOTIFICATION-TYPE
    STATUS      current
    DESCRIPTION
        "SNMPTrap, ao channel-13 in slot 1"
::= { slot1-ao-Trap 14 }

slot1Trap-ao-14 NOTIFICATION-TYPE
    STATUS      current
    DESCRIPTION
        "SNMPTrap, ao channel-14 in slot 1"
::= { slot1-ao-Trap 15 }

slot1Trap-ao-15 NOTIFICATION-TYPE
    STATUS      current
    DESCRIPTION
        "SNMPTrap, ao channel-15 in slot 1"
::= { slot1-ao-Trap 16 }

----------------------------------------------------------------
-- 1.3.6.1.4.1.8691.10.2500.21.7
    slot1-rtd-Trap OBJECT IDENTIFIER ::= { slot1-io-Trap 7 }
----------------------------------------------------------------

slot1Trap-rtd-00 NOTIFICATION-TYPE
    STATUS      current
    DESCRIPTION
        "SNMPTrap, rtd channel-00 in slot 1"
::= { slot1-rtd-Trap 1 }

slot1Trap-rtd-01 NOTIFICATION-TYPE
    STATUS      current
    DESCRIPTION
        "SNMPTrap, rtd channel-01 in slot 1"
::= { slot1-rtd-Trap 2 }

slot1Trap-rtd-02 NOTIFICATION-TYPE
    STATUS      current
    DESCRIPTION
        "SNMPTrap, rtd channel-02 in slot 1"
::= { slot1-rtd-Trap 3 }

slot1Trap-rtd-03 NOTIFICATION-TYPE
    STATUS      current
    DESCRIPTION
        "SNMPTrap, rtd channel-03 in slot 1"
::= { slot1-rtd-Trap 4 }

slot1Trap-rtd-04 NOTIFICATION-TYPE
    STATUS      current
    DESCRIPTION
        "SNMPTrap, rtd channel-04 in slot 1"
::= { slot1-rtd-Trap 5 }

slot1Trap-rtd-05 NOTIFICATION-TYPE
    STATUS      current
    DESCRIPTION
        "SNMPTrap, rtd channel-05 in slot 1"
::= { slot1-rtd-Trap 6 }

slot1Trap-rtd-06 NOTIFICATION-TYPE
    STATUS      current
    DESCRIPTION
        "SNMPTrap, rtd channel-06 in slot 1"
::= { slot1-rtd-Trap 7 }

slot1Trap-rtd-07 NOTIFICATION-TYPE
    STATUS      current
    DESCRIPTION
        "SNMPTrap, rtd channel-07 in slot 1"
::= { slot1-rtd-Trap 8 }

slot1Trap-rtd-08 NOTIFICATION-TYPE
    STATUS      current
    DESCRIPTION
        "SNMPTrap, rtd channel-08 in slot 1"
::= { slot1-rtd-Trap 9 }

slot1Trap-rtd-09 NOTIFICATION-TYPE
    STATUS      current
    DESCRIPTION
        "SNMPTrap, rtd channel-09 in slot 1"
::= { slot1-rtd-Trap 10 }

slot1Trap-rtd-10 NOTIFICATION-TYPE
    STATUS      current
    DESCRIPTION
        "SNMPTrap, rtd channel-10 in slot 1"
::= { slot1-rtd-Trap 11 }

slot1Trap-rtd-11 NOTIFICATION-TYPE
    STATUS      current
    DESCRIPTION
        "SNMPTrap, rtd channel-11 in slot 1"
::= { slot1-rtd-Trap 12 }

slot1Trap-rtd-12 NOTIFICATION-TYPE
    STATUS      current
    DESCRIPTION
        "SNMPTrap, rtd channel-12 in slot 1"
::= { slot1-rtd-Trap 13 }

slot1Trap-rtd-13 NOTIFICATION-TYPE
    STATUS      current
    DESCRIPTION
        "SNMPTrap, rtd channel-13 in slot 1"
::= { slot1-rtd-Trap 14 }

slot1Trap-rtd-14 NOTIFICATION-TYPE
    STATUS      current
    DESCRIPTION
        "SNMPTrap, rtd channel-14 in slot 1"
::= { slot1-rtd-Trap 15 }

slot1Trap-rtd-15 NOTIFICATION-TYPE
    STATUS      current
    DESCRIPTION
        "SNMPTrap, rtd channel-15 in slot 1"
::= { slot1-rtd-Trap 16 }

----------------------------------------------------------------
-- 1.3.6.1.4.1.8691.10.2500.21.8
    slot1-tc-Trap OBJECT IDENTIFIER ::= { slot1-io-Trap 8 }
----------------------------------------------------------------

slot1Trap-tc-00 NOTIFICATION-TYPE
    STATUS      current
    DESCRIPTION
        "SNMPTrap, tc channel-00 in slot 1"
::= { slot1-tc-Trap 1 }

slot1Trap-tc-01 NOTIFICATION-TYPE
    STATUS      current
    DESCRIPTION
        "SNMPTrap, tc channel-01 in slot 1"
::= { slot1-tc-Trap 2 }

slot1Trap-tc-02 NOTIFICATION-TYPE
    STATUS      current
    DESCRIPTION
        "SNMPTrap, tc channel-02 in slot 1"
::= { slot1-tc-Trap 3 }

slot1Trap-tc-03 NOTIFICATION-TYPE
    STATUS      current
    DESCRIPTION
        "SNMPTrap, tc channel-03 in slot 1"
::= { slot1-tc-Trap 4 }

slot1Trap-tc-04 NOTIFICATION-TYPE
    STATUS      current
    DESCRIPTION
        "SNMPTrap, tc channel-04 in slot 1"
::= { slot1-tc-Trap 5 }

slot1Trap-tc-05 NOTIFICATION-TYPE
    STATUS      current
    DESCRIPTION
        "SNMPTrap, tc channel-05 in slot 1"
::= { slot1-tc-Trap 6 }

slot1Trap-tc-06 NOTIFICATION-TYPE
    STATUS      current
    DESCRIPTION
        "SNMPTrap, tc channel-06 in slot 1"
::= { slot1-tc-Trap 7 }

slot1Trap-tc-07 NOTIFICATION-TYPE
    STATUS      current
    DESCRIPTION
        "SNMPTrap, tc channel-07 in slot 1"
::= { slot1-tc-Trap 8 }

slot1Trap-tc-08 NOTIFICATION-TYPE
    STATUS      current
    DESCRIPTION
        "SNMPTrap, tc channel-08 in slot 1"
::= { slot1-tc-Trap 9 }

slot1Trap-tc-09 NOTIFICATION-TYPE
    STATUS      current
    DESCRIPTION
        "SNMPTrap, tc channel-09 in slot 1"
::= { slot1-tc-Trap 10 }

slot1Trap-tc-10 NOTIFICATION-TYPE
    STATUS      current
    DESCRIPTION
        "SNMPTrap, tc channel-10 in slot 1"
::= { slot1-tc-Trap 11 }

slot1Trap-tc-11 NOTIFICATION-TYPE
    STATUS      current
    DESCRIPTION
        "SNMPTrap, tc channel-11 in slot 1"
::= { slot1-tc-Trap 12 }

slot1Trap-tc-12 NOTIFICATION-TYPE
    STATUS      current
    DESCRIPTION
        "SNMPTrap, tc channel-12 in slot 1"
::= { slot1-tc-Trap 13 }

slot1Trap-tc-13 NOTIFICATION-TYPE
    STATUS      current
    DESCRIPTION
        "SNMPTrap, tc channel-13 in slot 1"
::= { slot1-tc-Trap 14 }

slot1Trap-tc-14 NOTIFICATION-TYPE
    STATUS      current
    DESCRIPTION
        "SNMPTrap, tc channel-14 in slot 1"
::= { slot1-tc-Trap 15 }

slot1Trap-tc-15 NOTIFICATION-TYPE
    STATUS      current
    DESCRIPTION
        "SNMPTrap, tc channel-15 in slot 1"
::= { slot1-tc-Trap 16 }		
		
		
----------------------------------------------------------------
-- 1.3.6.1.4.1.8691.10.2500.30
    slot2-io OBJECT IDENTIFIER ::= { ioLogik2500 30 }
----------------------------------------------------------------
-- slot 2 DI
slot2-diTable OBJECT-TYPE
		SYNTAX 			SEQUENCE OF Slot2-diDef
		MAX-ACCESS 		not-accessible
		STATUS 			current
		DESCRIPTION		"The di channel table"
		::= { slot2-io 1 }

slot2-di OBJECT-TYPE
		SYNTAX 			Slot2-diDef
		MAX-ACCESS 		not-accessible
		STATUS 			current
		DESCRIPTION		"The di channel item"
		INDEX { slot2-diIndex }
		::= { slot2-diTable 1 }

Slot2-diDef ::= SEQUENCE { 
    	slot2-diIndex		INTEGER,
		slot2-diStatus		Unsigned32,
		slot2-diCounterReset2Init INTEGER		
		}  

slot2-diIndex OBJECT-TYPE
		SYNTAX 			INTEGER (0..15)
		MAX-ACCESS 		read-only
		STATUS 			current
		DESCRIPTION		"The channel index"
		::= { slot2-di 1 }
		
slot2-diStatus OBJECT-TYPE
		SYNTAX 			Unsigned32
		MAX-ACCESS 		read-write
		STATUS 			current
		DESCRIPTION		"The channel di status. 0=off, 1=on in di mode or n=counter value in counter mode"
		::= { slot2-di 2 }

slot2-diCounterReset2Init OBJECT-TYPE
		SYNTAX 			INTEGER 
		MAX-ACCESS 		read-write
		STATUS 			current
		DESCRIPTION		"Trigger counter to initial value. 1=Reset counter to initial value"
		::= { slot2-di 3 }
		
-- slot 2 DICounterStart
slot2-diCounterStartTable OBJECT-TYPE
		SYNTAX 			SEQUENCE OF Slot2-diCounterStartDef
		MAX-ACCESS 		not-accessible
		STATUS 			current
		DESCRIPTION		"The counter table starting for di"
		::= { slot2-io 39 }

slot2-diCounterStart OBJECT-TYPE
		SYNTAX 			Slot2-diCounterStartDef
		MAX-ACCESS 		not-accessible
		STATUS 			current
		DESCRIPTION		"The counter starting of di item"
		INDEX { slot2-diCounterStartIndex }
		::= { slot2-diCounterStartTable 1 }

Slot2-diCounterStartDef ::= SEQUENCE { 
    		slot2-diCounterStartIndex		INTEGER,
			slot2-diCounterStartStatus		INTEGER			
		}  

slot2-diCounterStartIndex OBJECT-TYPE
		SYNTAX 			INTEGER (0..15)
		MAX-ACCESS 		read-only
		STATUS 			current
		DESCRIPTION		"The channel index for di counter start"
		::= { slot2-diCounterStart 1 }
		
slot2-diCounterStartStatus OBJECT-TYPE
		SYNTAX 			INTEGER (0..1)
		MAX-ACCESS 		read-write
		STATUS 			current
		DESCRIPTION		"The channel status for di counter start. 0=stop, 1=start"
		::= { slot2-diCounterStart 2 } 	
		
-- slot 2 DO
slot2-doTable OBJECT-TYPE
		SYNTAX 			SEQUENCE OF Slot2-doDef
		MAX-ACCESS 		not-accessible
		STATUS 			current
		DESCRIPTION		"The do channel table"
		::= { slot2-io 2 }

slot2-do OBJECT-TYPE
		SYNTAX 			Slot2-doDef
		MAX-ACCESS 		not-accessible
		STATUS 			current
		DESCRIPTION		"The do channel item"
		INDEX { slot2-doIndex }
		::= { slot2-doTable 1 }

Slot2-doDef ::= SEQUENCE { 
    	slot2-doIndex		INTEGER,
		slot2-doStatus		INTEGER		
		}  

slot2-doIndex OBJECT-TYPE
		SYNTAX 			INTEGER (0..15)
		MAX-ACCESS 		read-only
		STATUS 			current
		DESCRIPTION		"The channel index"
		::= { slot2-do 1 }
		
slot2-doStatus OBJECT-TYPE
		SYNTAX 			INTEGER (0..1)
		MAX-ACCESS 		read-write
		STATUS 			current
		DESCRIPTION		"The channel do status. 0=off, 1=on in do mode or 0=stop, 1=start in pulse mode"
		::= { slot2-do 2 }  

-- slot 2 DIO
slot2-dioTable OBJECT-TYPE
		SYNTAX 			SEQUENCE OF Slot2-dioDef
		MAX-ACCESS 		not-accessible
		STATUS 			current
		DESCRIPTION		"The dio channel table"
		::= { slot2-io 3 }

slot2-dio OBJECT-TYPE
		SYNTAX 			Slot2-dioDef
		MAX-ACCESS 		not-accessible
		STATUS 			current
		DESCRIPTION		"The dio channel item"
		INDEX { slot2-dioIndex }
		::= { slot2-dioTable 1 }

Slot2-dioDef ::= SEQUENCE { 
    	slot2-dioIndex		INTEGER,
		slot2-dioStatus		Unsigned32,
		slot2-dioCounterReset2Init INTEGER				
		}  

slot2-dioIndex OBJECT-TYPE
		SYNTAX 			INTEGER (0..15)
		MAX-ACCESS 		read-only
		STATUS 			current
		DESCRIPTION		"The channel index"
		::= { slot2-dio 1 }
		
slot2-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot2-dio 2 }  
		
slot2-dioCounterReset2Init OBJECT-TYPE
		SYNTAX 			INTEGER 
		MAX-ACCESS 		read-write
		STATUS 			current
		DESCRIPTION		"Trigger counter to initial value. 1=Reset counter to initial value"
		::= { slot2-dio 3 }


-- slot 2 DIOCounterStart
slot2-dioCounterStartTable OBJECT-TYPE
		SYNTAX 			SEQUENCE OF Slot2-dioCounterStartDef
		MAX-ACCESS 		not-accessible
		STATUS 			current
		DESCRIPTION		"The counter table starting for dio"
		::= { slot2-io 46 }

slot2-dioCounterStart OBJECT-TYPE
		SYNTAX 			Slot2-dioCounterStartDef
		MAX-ACCESS 		not-accessible
		STATUS 			current
		DESCRIPTION		"The counter starting of dio item"
		INDEX { slot2-dioCounterStartIndex }
		::= { slot2-dioCounterStartTable 1 }

Slot2-dioCounterStartDef ::= SEQUENCE { 
    		slot2-dioCounterStartIndex		INTEGER,
			slot2-dioCounterStartStatus		INTEGER		
		}  

slot2-dioCounterStartIndex OBJECT-TYPE
		SYNTAX 			INTEGER (0..15)
		MAX-ACCESS 		read-only
		STATUS 			current
		DESCRIPTION		"The channel index for dio counter start"
		::= { slot2-dioCounterStart 1 }
		
slot2-dioCounterStartStatus OBJECT-TYPE
		SYNTAX 			INTEGER (0..1)
		MAX-ACCESS 		read-write
		STATUS 			current
		DESCRIPTION		"The channel status for dio counter start. 0=stop, 1=start"
		::= { slot2-dioCounterStart 2 }  			
		
		
-- slot 2 Relay
slot2-relayTable OBJECT-TYPE
		SYNTAX 			SEQUENCE OF Slot2-relayDef
		MAX-ACCESS 		not-accessible
		STATUS 			current
		DESCRIPTION		"The relay channel table"
		::= { slot2-io 4 }

slot2-relay OBJECT-TYPE
		SYNTAX 			Slot2-relayDef
		MAX-ACCESS 		not-accessible
		STATUS 			current
		DESCRIPTION		"The relay channel item"
		INDEX { slot2-relayIndex }
		::= { slot2-relayTable 1 }

Slot2-relayDef ::= SEQUENCE { 
    	slot2-relayIndex		INTEGER,
		slot2-relayStatus		INTEGER		
		}  

slot2-relayIndex OBJECT-TYPE
		SYNTAX 			INTEGER (0..15)
		MAX-ACCESS 		read-only
		STATUS 			current
		DESCRIPTION		"The channel index"
		::= { slot2-relay 1 }
		
slot2-relayStatus OBJECT-TYPE
		SYNTAX 			INTEGER (0..1)
		MAX-ACCESS 		read-write
		STATUS 			current
		DESCRIPTION		"The channel relay status. 0=off, 1=on in do mode or 0=stop, 1=start in pulse mode"
		::= { slot2-relay 2 }  

-- slot 2 AI
slot2-aiTable OBJECT-TYPE
		SYNTAX 			SEQUENCE OF Slot2-aiDef
		MAX-ACCESS 		not-accessible
		STATUS 			current
		DESCRIPTION		"The ai channel table"
		::= { slot2-io 5 }

slot2-ai OBJECT-TYPE
		SYNTAX 			Slot2-aiDef
		MAX-ACCESS 		not-accessible
		STATUS 			current
		DESCRIPTION		"The ai channel item"
		INDEX { slot2-aiIndex }
		::= { slot2-aiTable 1 }

Slot2-aiDef ::= SEQUENCE { 
    	slot2-aiIndex		INTEGER,
		slot2-aiStatus		OCTET STRING,
		slot2-aiBurnoutStatus INTEGER		
		}  

slot2-aiIndex OBJECT-TYPE
		SYNTAX 			INTEGER (0..15)
		MAX-ACCESS 		read-only
		STATUS 			current
		DESCRIPTION		"The channel index"
		::= { slot2-ai 1 }
		
slot2-aiStatus OBJECT-TYPE
		SYNTAX 			OCTET STRING
		MAX-ACCESS 		read-only
		STATUS 			current
		DESCRIPTION		"The channel ai scaled value"
		::= { slot2-ai 2 }  

slot2-aiBurnoutStatus OBJECT-TYPE
		SYNTAX 			INTEGER (0..3)
		MAX-ACCESS 		read-only
		STATUS 			current
		DESCRIPTION		"The channel of burnout status (0: normal, 1: burnout, 2: underange, 3: overange)"
		::= { slot2-ai 3 }  

-- slot 2 AO
slot2-aoTable OBJECT-TYPE
		SYNTAX 			SEQUENCE OF Slot2-aoDef
		MAX-ACCESS 		not-accessible
		STATUS 			current
		DESCRIPTION		"The ao channel table"
		::= { slot2-io 6 }

slot2-ao OBJECT-TYPE
		SYNTAX 			Slot2-aoDef
		MAX-ACCESS 		not-accessible
		STATUS 			current
		DESCRIPTION		"The ao channel item"
		INDEX { slot2-aoIndex }
		::= { slot2-aoTable 1 }

Slot2-aoDef ::= SEQUENCE { 
    	slot2-aoIndex		INTEGER,
		slot2-aoStatus		OCTET STRING		
		}  

slot2-aoIndex OBJECT-TYPE
		SYNTAX 			INTEGER (0..15)
		MAX-ACCESS 		read-only
		STATUS 			current
		DESCRIPTION		"The channel index"
		::= { slot2-ao 1 }
		
slot2-aoStatus OBJECT-TYPE
		SYNTAX 			OCTET STRING
		MAX-ACCESS 		read-write
		STATUS 			current
		DESCRIPTION		"The channel ao scaled value"
		::= { slot2-ao 2 }  

-- slot 2 RTD
slot2-rtdTable OBJECT-TYPE
		SYNTAX 			SEQUENCE OF Slot2-rtdDef
		MAX-ACCESS 		not-accessible
		STATUS 			current
		DESCRIPTION		"The rtd channel table"
		::= { slot2-io 7 }

slot2-rtd OBJECT-TYPE
		SYNTAX 			Slot2-rtdDef
		MAX-ACCESS 		not-accessible
		STATUS 			current
		DESCRIPTION		"The rtd channel item"
		INDEX { slot2-rtdIndex }
		::= { slot2-rtdTable 1 }

Slot2-rtdDef ::= SEQUENCE { 
    	slot2-rtdIndex		INTEGER,
		slot2-rtdStatus		OCTET STRING		
		}  

slot2-rtdIndex OBJECT-TYPE
		SYNTAX 			INTEGER (0..15)
		MAX-ACCESS 		read-only
		STATUS 			current
		DESCRIPTION		"The channel index"
		::= { slot2-rtd 1 }
		
slot2-rtdStatus OBJECT-TYPE
		SYNTAX 			OCTET STRING
		MAX-ACCESS 		read-only
		STATUS 			current
		DESCRIPTION		"The channel rtd scaled value"
		::= { slot2-rtd 2 }  

-- slot 2 TC
slot2-tcTable OBJECT-TYPE
		SYNTAX 			SEQUENCE OF Slot2-tcDef
		MAX-ACCESS 		not-accessible
		STATUS 			current
		DESCRIPTION		"The tc channel table"
		::= { slot2-io 8 }

slot2-tc OBJECT-TYPE
		SYNTAX 			Slot2-tcDef
		MAX-ACCESS 		not-accessible
		STATUS 			current
		DESCRIPTION		"The tc channel item"
		INDEX { slot2-tcIndex }
		::= { slot2-tcTable 1 }

Slot2-tcDef ::= SEQUENCE { 
    	slot2-tcIndex		INTEGER,
		slot2-tcStatus		OCTET STRING		
		}  

slot2-tcIndex OBJECT-TYPE
		SYNTAX 			INTEGER (0..15)
		MAX-ACCESS 		read-only
		STATUS 			current
		DESCRIPTION		"The channel index"
		::= { slot2-tc 1 }
		
slot2-tcStatus OBJECT-TYPE
		SYNTAX 			OCTET STRING
		MAX-ACCESS 		read-only
		STATUS 			current
		DESCRIPTION		"The channel tc scaled value"
		::= { slot2-tc 2 }  

----------------------------------------------------------------
-- 1.3.6.1.4.1.8691.10.2500.31
    slot2-io-Trap OBJECT IDENTIFIER ::= { ioLogik2500 31 }
----------------------------------------------------------------

----------------------------------------------------------------
-- 1.3.6.1.4.1.8691.10.2500.31.1
    slot2-di-Trap OBJECT IDENTIFIER ::= { slot2-io-Trap 1 }
----------------------------------------------------------------

slot2Trap-di-00 NOTIFICATION-TYPE
    STATUS      current
    DESCRIPTION
        "SNMPTrap, di channel-00 in slot 2"
::= { slot2-di-Trap 1 }

slot2Trap-di-01 NOTIFICATION-TYPE
    STATUS      current
    DESCRIPTION
        "SNMPTrap, di channel-01 in slot 2"
::= { slot2-di-Trap 2 }

slot2Trap-di-02 NOTIFICATION-TYPE
    STATUS      current
    DESCRIPTION
        "SNMPTrap, di channel-02 in slot 2"
::= { slot2-di-Trap 3 }

slot2Trap-di-03 NOTIFICATION-TYPE
    STATUS      current
    DESCRIPTION
        "SNMPTrap, di channel-03 in slot 2"
::= { slot2-di-Trap 4 }

slot2Trap-di-04 NOTIFICATION-TYPE
    STATUS      current
    DESCRIPTION
        "SNMPTrap, di channel-04 in slot 2"
::= { slot2-di-Trap 5 }

slot2Trap-di-05 NOTIFICATION-TYPE
    STATUS      current
    DESCRIPTION
        "SNMPTrap, di channel-05 in slot 2"
::= { slot2-di-Trap 6 }

slot2Trap-di-06 NOTIFICATION-TYPE
    STATUS      current
    DESCRIPTION
        "SNMPTrap, di channel-06 in slot 2"
::= { slot2-di-Trap 7 }

slot2Trap-di-07 NOTIFICATION-TYPE
    STATUS      current
    DESCRIPTION
        "SNMPTrap, di channel-07 in slot 2"
::= { slot2-di-Trap 8 }

slot2Trap-di-08 NOTIFICATION-TYPE
    STATUS      current
    DESCRIPTION
        "SNMPTrap, di channel-08 in slot 2"
::= { slot2-di-Trap 9 }

slot2Trap-di-09 NOTIFICATION-TYPE
    STATUS      current
    DESCRIPTION
        "SNMPTrap, di channel-09 in slot 2"
::= { slot2-di-Trap 10 }

slot2Trap-di-10 NOTIFICATION-TYPE
    STATUS      current
    DESCRIPTION
        "SNMPTrap, di channel-10 in slot 2"
::= { slot2-di-Trap 11 }

slot2Trap-di-11 NOTIFICATION-TYPE
    STATUS      current
    DESCRIPTION
        "SNMPTrap, di channel-11 in slot 2"
::= { slot2-di-Trap 12 }

slot2Trap-di-12 NOTIFICATION-TYPE
    STATUS      current
    DESCRIPTION
        "SNMPTrap, di channel-12 in slot 2"
::= { slot2-di-Trap 13 }

slot2Trap-di-13 NOTIFICATION-TYPE
    STATUS      current
    DESCRIPTION
        "SNMPTrap, di channel-13 in slot 2"
::= { slot2-di-Trap 14 }

slot2Trap-di-14 NOTIFICATION-TYPE
    STATUS      current
    DESCRIPTION
        "SNMPTrap, di channel-14 in slot 2"
::= { slot2-di-Trap 15 }

slot2Trap-di-15 NOTIFICATION-TYPE
    STATUS      current
    DESCRIPTION
        "SNMPTrap, di channel-15 in slot 2"
::= { slot2-di-Trap 16 }
----------------------------------------------------------------
-- 1.3.6.1.4.1.8691.10.2500.31.2
    slot2-do-Trap OBJECT IDENTIFIER ::= { slot2-io-Trap 2 }
----------------------------------------------------------------

slot2Trap-do-00 NOTIFICATION-TYPE
    STATUS      current
    DESCRIPTION
        "SNMPTrap, do channel-00 in slot 2"
::= { slot2-do-Trap 1 }

slot2Trap-do-01 NOTIFICATION-TYPE
    STATUS      current
    DESCRIPTION
        "SNMPTrap, do channel-01 in slot 2"
::= { slot2-do-Trap 2 }

slot2Trap-do-02 NOTIFICATION-TYPE
    STATUS      current
    DESCRIPTION
        "SNMPTrap, do channel-02 in slot 2"
::= { slot2-do-Trap 3 }

slot2Trap-do-03 NOTIFICATION-TYPE
    STATUS      current
    DESCRIPTION
        "SNMPTrap, do channel-03 in slot 2"
::= { slot2-do-Trap 4 }

slot2Trap-do-04 NOTIFICATION-TYPE
    STATUS      current
    DESCRIPTION
        "SNMPTrap, do channel-04 in slot 2"
::= { slot2-do-Trap 5 }

slot2Trap-do-05 NOTIFICATION-TYPE
    STATUS      current
    DESCRIPTION
        "SNMPTrap, do channel-05 in slot 2"
::= { slot2-do-Trap 6 }

slot2Trap-do-06 NOTIFICATION-TYPE
    STATUS      current
    DESCRIPTION
        "SNMPTrap, do channel-06 in slot 2"
::= { slot2-do-Trap 7 }

slot2Trap-do-07 NOTIFICATION-TYPE
    STATUS      current
    DESCRIPTION
        "SNMPTrap, do channel-07 in slot 2"
::= { slot2-do-Trap 8 }

slot2Trap-do-08 NOTIFICATION-TYPE
    STATUS      current
    DESCRIPTION
        "SNMPTrap, do channel-08 in slot 2"
::= { slot2-do-Trap 9 }

slot2Trap-do-09 NOTIFICATION-TYPE
    STATUS      current
    DESCRIPTION
        "SNMPTrap, do channel-09 in slot 2"
::= { slot2-do-Trap 10 }

slot2Trap-do-10 NOTIFICATION-TYPE
    STATUS      current
    DESCRIPTION
        "SNMPTrap, do channel-10 in slot 2"
::= { slot2-do-Trap 11 }

slot2Trap-do-11 NOTIFICATION-TYPE
    STATUS      current
    DESCRIPTION
        "SNMPTrap, do channel-11 in slot 2"
::= { slot2-do-Trap 12 }

slot2Trap-do-12 NOTIFICATION-TYPE
    STATUS      current
    DESCRIPTION
        "SNMPTrap, do channel-12 in slot 2"
::= { slot2-do-Trap 13 }

slot2Trap-do-13 NOTIFICATION-TYPE
    STATUS      current
    DESCRIPTION
        "SNMPTrap, do channel-13 in slot 2"
::= { slot2-do-Trap 14 }

slot2Trap-do-14 NOTIFICATION-TYPE
    STATUS      current
    DESCRIPTION
        "SNMPTrap, do channel-14 in slot 2"
::= { slot2-do-Trap 15 }

slot2Trap-do-15 NOTIFICATION-TYPE
    STATUS      current
    DESCRIPTION
        "SNMPTrap, do channel-15 in slot 2"
::= { slot2-do-Trap 16 }

----------------------------------------------------------------
-- 1.3.6.1.4.1.8691.10.2500.31.3
    slot2-dio-Trap OBJECT IDENTIFIER ::= { slot2-io-Trap 3 }
----------------------------------------------------------------

slot2Trap-dio-00 NOTIFICATION-TYPE
    STATUS      current
    DESCRIPTION
        "SNMPTrap, dio channel-00 in slot 2"
::= { slot2-dio-Trap 1 }

slot2Trap-dio-01 NOTIFICATION-TYPE
    STATUS      current
    DESCRIPTION
        "SNMPTrap, dio channel-01 in slot 2"
::= { slot2-dio-Trap 2 }

slot2Trap-dio-02 NOTIFICATION-TYPE
    STATUS      current
    DESCRIPTION
        "SNMPTrap, dio channel-02 in slot 2"
::= { slot2-dio-Trap 3 }

slot2Trap-dio-03 NOTIFICATION-TYPE
    STATUS      current
    DESCRIPTION
        "SNMPTrap, dio channel-03 in slot 2"
::= { slot2-dio-Trap 4 }

slot2Trap-dio-04 NOTIFICATION-TYPE
    STATUS      current
    DESCRIPTION
        "SNMPTrap, dio channel-04 in slot 2"
::= { slot2-dio-Trap 5 }

slot2Trap-dio-05 NOTIFICATION-TYPE
    STATUS      current
    DESCRIPTION
        "SNMPTrap, dio channel-05 in slot 2"
::= { slot2-dio-Trap 6 }

slot2Trap-dio-06 NOTIFICATION-TYPE
    STATUS      current
    DESCRIPTION
        "SNMPTrap, dio channel-06 in slot 2"
::= { slot2-dio-Trap 7 }

slot2Trap-dio-07 NOTIFICATION-TYPE
    STATUS      current
    DESCRIPTION
        "SNMPTrap, dio channel-07 in slot 2"
::= { slot2-dio-Trap 8 }

slot2Trap-dio-08 NOTIFICATION-TYPE
    STATUS      current
    DESCRIPTION
        "SNMPTrap, dio channel-08 in slot 2"
::= { slot2-dio-Trap 9 }

slot2Trap-dio-09 NOTIFICATION-TYPE
    STATUS      current
    DESCRIPTION
        "SNMPTrap, dio channel-09 in slot 2"
::= { slot2-dio-Trap 10 }

slot2Trap-dio-10 NOTIFICATION-TYPE
    STATUS      current
    DESCRIPTION
        "SNMPTrap, dio channel-10 in slot 2"
::= { slot2-dio-Trap 11 }

slot2Trap-dio-11 NOTIFICATION-TYPE
    STATUS      current
    DESCRIPTION
        "SNMPTrap, dio channel-11 in slot 2"
::= { slot2-dio-Trap 12 }

slot2Trap-dio-12 NOTIFICATION-TYPE
    STATUS      current
    DESCRIPTION
        "SNMPTrap, dio channel-12 in slot 2"
::= { slot2-dio-Trap 13 }

slot2Trap-dio-13 NOTIFICATION-TYPE
    STATUS      current
    DESCRIPTION
        "SNMPTrap, dio channel-13 in slot 2"
::= { slot2-dio-Trap 14 }

slot2Trap-dio-14 NOTIFICATION-TYPE
    STATUS      current
    DESCRIPTION
        "SNMPTrap, dio channel-14 in slot 2"
::= { slot2-dio-Trap 15 }

slot2Trap-dio-15 NOTIFICATION-TYPE
    STATUS      current
    DESCRIPTION
        "SNMPTrap, dio channel-15 in slot 2"
::= { slot2-dio-Trap 16 }

----------------------------------------------------------------
-- 1.3.6.1.4.1.8691.10.2500.31.4
    slot2-relay-Trap OBJECT IDENTIFIER ::= { slot2-io-Trap 4 }
----------------------------------------------------------------

slot2Trap-relay-00 NOTIFICATION-TYPE
    STATUS      current
    DESCRIPTION
        "SNMPTrap, relay channel-00 in slot 2"
::= { slot2-relay-Trap 1 }

slot2Trap-relay-01 NOTIFICATION-TYPE
    STATUS      current
    DESCRIPTION
        "SNMPTrap, relay channel-01 in slot 2"
::= { slot2-relay-Trap 2 }

slot2Trap-relay-02 NOTIFICATION-TYPE
    STATUS      current
    DESCRIPTION
        "SNMPTrap, relay channel-02 in slot 2"
::= { slot2-relay-Trap 3 }

slot2Trap-relay-03 NOTIFICATION-TYPE
    STATUS      current
    DESCRIPTION
        "SNMPTrap, relay channel-03 in slot 2"
::= { slot2-relay-Trap 4 }

slot2Trap-relay-04 NOTIFICATION-TYPE
    STATUS      current
    DESCRIPTION
        "SNMPTrap, relay channel-04 in slot 2"
::= { slot2-relay-Trap 5 }

slot2Trap-relay-05 NOTIFICATION-TYPE
    STATUS      current
    DESCRIPTION
        "SNMPTrap, relay channel-05 in slot 2"
::= { slot2-relay-Trap 6 }

slot2Trap-relay-06 NOTIFICATION-TYPE
    STATUS      current
    DESCRIPTION
        "SNMPTrap, relay channel-06 in slot 2"
::= { slot2-relay-Trap 7 }

slot2Trap-relay-07 NOTIFICATION-TYPE
    STATUS      current
    DESCRIPTION
        "SNMPTrap, relay channel-07 in slot 2"
::= { slot2-relay-Trap 8 }

slot2Trap-relay-08 NOTIFICATION-TYPE
    STATUS      current
    DESCRIPTION
        "SNMPTrap, relay channel-08 in slot 2"
::= { slot2-relay-Trap 9 }

slot2Trap-relay-09 NOTIFICATION-TYPE
    STATUS      current
    DESCRIPTION
        "SNMPTrap, relay channel-09 in slot 2"
::= { slot2-relay-Trap 10 }

slot2Trap-relay-10 NOTIFICATION-TYPE
    STATUS      current
    DESCRIPTION
        "SNMPTrap, relay channel-10 in slot 2"
::= { slot2-relay-Trap 11 }

slot2Trap-relay-11 NOTIFICATION-TYPE
    STATUS      current
    DESCRIPTION
        "SNMPTrap, relay channel-11 in slot 2"
::= { slot2-relay-Trap 12 }

slot2Trap-relay-12 NOTIFICATION-TYPE
    STATUS      current
    DESCRIPTION
        "SNMPTrap, relay channel-12 in slot 2"
::= { slot2-relay-Trap 13 }

slot2Trap-relay-13 NOTIFICATION-TYPE
    STATUS      current
    DESCRIPTION
        "SNMPTrap, relay channel-13 in slot 2"
::= { slot2-relay-Trap 14 }

slot2Trap-relay-14 NOTIFICATION-TYPE
    STATUS      current
    DESCRIPTION
        "SNMPTrap, relay channel-14 in slot 2"
::= { slot2-relay-Trap 15 }

slot2Trap-relay-15 NOTIFICATION-TYPE
    STATUS      current
    DESCRIPTION
        "SNMPTrap, relay channel-15 in slot 2"
::= { slot2-relay-Trap 16 }

----------------------------------------------------------------
-- 1.3.6.1.4.1.8691.10.2500.31.5
    slot2-ai-Trap OBJECT IDENTIFIER ::= { slot2-io-Trap 5 }
----------------------------------------------------------------

slot2Trap-ai-00 NOTIFICATION-TYPE
    STATUS      current
    DESCRIPTION
        "SNMPTrap, ai channel-00 in slot 2"
::= { slot2-ai-Trap 1 }

slot2Trap-ai-01 NOTIFICATION-TYPE
    STATUS      current
    DESCRIPTION
        "SNMPTrap, ai channel-01 in slot 2"
::= { slot2-ai-Trap 2 }

slot2Trap-ai-02 NOTIFICATION-TYPE
    STATUS      current
    DESCRIPTION
        "SNMPTrap, ai channel-02 in slot 2"
::= { slot2-ai-Trap 3 }

slot2Trap-ai-03 NOTIFICATION-TYPE
    STATUS      current
    DESCRIPTION
        "SNMPTrap, ai channel-03 in slot 2"
::= { slot2-ai-Trap 4 }

slot2Trap-ai-04 NOTIFICATION-TYPE
    STATUS      current
    DESCRIPTION
        "SNMPTrap, ai channel-04 in slot 2"
::= { slot2-ai-Trap 5 }

slot2Trap-ai-05 NOTIFICATION-TYPE
    STATUS      current
    DESCRIPTION
        "SNMPTrap, ai channel-05 in slot 2"
::= { slot2-ai-Trap 6 }

slot2Trap-ai-06 NOTIFICATION-TYPE
    STATUS      current
    DESCRIPTION
        "SNMPTrap, ai channel-06 in slot 2"
::= { slot2-ai-Trap 7 }

slot2Trap-ai-07 NOTIFICATION-TYPE
    STATUS      current
    DESCRIPTION
        "SNMPTrap, ai channel-07 in slot 2"
::= { slot2-ai-Trap 8 }

slot2Trap-ai-08 NOTIFICATION-TYPE
    STATUS      current
    DESCRIPTION
        "SNMPTrap, ai channel-08 in slot 2"
::= { slot2-ai-Trap 9 }

slot2Trap-ai-09 NOTIFICATION-TYPE
    STATUS      current
    DESCRIPTION
        "SNMPTrap, ai channel-09 in slot 2"
::= { slot2-ai-Trap 10 }

slot2Trap-ai-10 NOTIFICATION-TYPE
    STATUS      current
    DESCRIPTION
        "SNMPTrap, ai channel-10 in slot 2"
::= { slot2-ai-Trap 11 }

slot2Trap-ai-11 NOTIFICATION-TYPE
    STATUS      current
    DESCRIPTION
        "SNMPTrap, ai channel-11 in slot 2"
::= { slot2-ai-Trap 12 }

slot2Trap-ai-12 NOTIFICATION-TYPE
    STATUS      current
    DESCRIPTION
        "SNMPTrap, ai channel-12 in slot 2"
::= { slot2-ai-Trap 13 }

slot2Trap-ai-13 NOTIFICATION-TYPE
    STATUS      current
    DESCRIPTION
        "SNMPTrap, ai channel-13 in slot 2"
::= { slot2-ai-Trap 14 }

slot2Trap-ai-14 NOTIFICATION-TYPE
    STATUS      current
    DESCRIPTION
        "SNMPTrap, ai channel-14 in slot 2"
::= { slot2-ai-Trap 15 }

slot2Trap-ai-15 NOTIFICATION-TYPE
    STATUS      current
    DESCRIPTION
        "SNMPTrap, ai channel-15 in slot 2"
::= { slot2-ai-Trap 16 }

----------------------------------------------------------------
-- 1.3.6.1.4.1.8691.10.2500.31.6
    slot2-ao-Trap OBJECT IDENTIFIER ::= { slot2-io-Trap 6 }
----------------------------------------------------------------

slot2Trap-ao-00 NOTIFICATION-TYPE
    STATUS      current
    DESCRIPTION
        "SNMPTrap, ao channel-00 in slot 2"
::= { slot2-ao-Trap 1 }

slot2Trap-ao-01 NOTIFICATION-TYPE
    STATUS      current
    DESCRIPTION
        "SNMPTrap, ao channel-01 in slot 2"
::= { slot2-ao-Trap 2 }

slot2Trap-ao-02 NOTIFICATION-TYPE
    STATUS      current
    DESCRIPTION
        "SNMPTrap, ao channel-02 in slot 2"
::= { slot2-ao-Trap 3 }

slot2Trap-ao-03 NOTIFICATION-TYPE
    STATUS      current
    DESCRIPTION
        "SNMPTrap, ao channel-03 in slot 2"
::= { slot2-ao-Trap 4 }

slot2Trap-ao-04 NOTIFICATION-TYPE
    STATUS      current
    DESCRIPTION
        "SNMPTrap, ao channel-04 in slot 2"
::= { slot2-ao-Trap 5 }

slot2Trap-ao-05 NOTIFICATION-TYPE
    STATUS      current
    DESCRIPTION
        "SNMPTrap, ao channel-05 in slot 2"
::= { slot2-ao-Trap 6 }

slot2Trap-ao-06 NOTIFICATION-TYPE
    STATUS      current
    DESCRIPTION
        "SNMPTrap, ao channel-06 in slot 2"
::= { slot2-ao-Trap 7 }

slot2Trap-ao-07 NOTIFICATION-TYPE
    STATUS      current
    DESCRIPTION
        "SNMPTrap, ao channel-07 in slot 2"
::= { slot2-ao-Trap 8 }

slot2Trap-ao-08 NOTIFICATION-TYPE
    STATUS      current
    DESCRIPTION
        "SNMPTrap, ao channel-08 in slot 2"
::= { slot2-ao-Trap 9 }

slot2Trap-ao-09 NOTIFICATION-TYPE
    STATUS      current
    DESCRIPTION
        "SNMPTrap, ao channel-09 in slot 2"
::= { slot2-ao-Trap 10 }

slot2Trap-ao-10 NOTIFICATION-TYPE
    STATUS      current
    DESCRIPTION
        "SNMPTrap, ao channel-10 in slot 2"
::= { slot2-ao-Trap 11 }

slot2Trap-ao-11 NOTIFICATION-TYPE
    STATUS      current
    DESCRIPTION
        "SNMPTrap, ao channel-11 in slot 2"
::= { slot2-ao-Trap 12 }

slot2Trap-ao-12 NOTIFICATION-TYPE
    STATUS      current
    DESCRIPTION
        "SNMPTrap, ao channel-12 in slot 2"
::= { slot2-ao-Trap 13 }

slot2Trap-ao-13 NOTIFICATION-TYPE
    STATUS      current
    DESCRIPTION
        "SNMPTrap, ao channel-13 in slot 2"
::= { slot2-ao-Trap 14 }

slot2Trap-ao-14 NOTIFICATION-TYPE
    STATUS      current
    DESCRIPTION
        "SNMPTrap, ao channel-14 in slot 2"
::= { slot2-ao-Trap 15 }

slot2Trap-ao-15 NOTIFICATION-TYPE
    STATUS      current
    DESCRIPTION
        "SNMPTrap, ao channel-15 in slot 2"
::= { slot2-ao-Trap 16 }

----------------------------------------------------------------
-- 1.3.6.1.4.1.8691.10.2500.31.7
    slot2-rtd-Trap OBJECT IDENTIFIER ::= { slot2-io-Trap 7 }
----------------------------------------------------------------

slot2Trap-rtd-00 NOTIFICATION-TYPE
    STATUS      current
    DESCRIPTION
        "SNMPTrap, rtd channel-00 in slot 2"
::= { slot2-rtd-Trap 1 }

slot2Trap-rtd-01 NOTIFICATION-TYPE
    STATUS      current
    DESCRIPTION
        "SNMPTrap, rtd channel-01 in slot 2"
::= { slot2-rtd-Trap 2 }

slot2Trap-rtd-02 NOTIFICATION-TYPE
    STATUS      current
    DESCRIPTION
        "SNMPTrap, rtd channel-02 in slot 2"
::= { slot2-rtd-Trap 3 }

slot2Trap-rtd-03 NOTIFICATION-TYPE
    STATUS      current
    DESCRIPTION
        "SNMPTrap, rtd channel-03 in slot 2"
::= { slot2-rtd-Trap 4 }

slot2Trap-rtd-04 NOTIFICATION-TYPE
    STATUS      current
    DESCRIPTION
        "SNMPTrap, rtd channel-04 in slot 2"
::= { slot2-rtd-Trap 5 }

slot2Trap-rtd-05 NOTIFICATION-TYPE
    STATUS      current
    DESCRIPTION
        "SNMPTrap, rtd channel-05 in slot 2"
::= { slot2-rtd-Trap 6 }

slot2Trap-rtd-06 NOTIFICATION-TYPE
    STATUS      current
    DESCRIPTION
        "SNMPTrap, rtd channel-06 in slot 2"
::= { slot2-rtd-Trap 7 }

slot2Trap-rtd-07 NOTIFICATION-TYPE
    STATUS      current
    DESCRIPTION
        "SNMPTrap, rtd channel-07 in slot 2"
::= { slot2-rtd-Trap 8 }

slot2Trap-rtd-08 NOTIFICATION-TYPE
    STATUS      current
    DESCRIPTION
        "SNMPTrap, rtd channel-08 in slot 2"
::= { slot2-rtd-Trap 9 }

slot2Trap-rtd-09 NOTIFICATION-TYPE
    STATUS      current
    DESCRIPTION
        "SNMPTrap, rtd channel-09 in slot 2"
::= { slot2-rtd-Trap 10 }

slot2Trap-rtd-10 NOTIFICATION-TYPE
    STATUS      current
    DESCRIPTION
        "SNMPTrap, rtd channel-10 in slot 2"
::= { slot2-rtd-Trap 11 }

slot2Trap-rtd-11 NOTIFICATION-TYPE
    STATUS      current
    DESCRIPTION
        "SNMPTrap, rtd channel-11 in slot 2"
::= { slot2-rtd-Trap 12 }

slot2Trap-rtd-12 NOTIFICATION-TYPE
    STATUS      current
    DESCRIPTION
        "SNMPTrap, rtd channel-12 in slot 2"
::= { slot2-rtd-Trap 13 }

slot2Trap-rtd-13 NOTIFICATION-TYPE
    STATUS      current
    DESCRIPTION
        "SNMPTrap, rtd channel-13 in slot 2"
::= { slot2-rtd-Trap 14 }

slot2Trap-rtd-14 NOTIFICATION-TYPE
    STATUS      current
    DESCRIPTION
        "SNMPTrap, rtd channel-14 in slot 2"
::= { slot2-rtd-Trap 15 }

slot2Trap-rtd-15 NOTIFICATION-TYPE
    STATUS      current
    DESCRIPTION
        "SNMPTrap, rtd channel-15 in slot 2"
::= { slot2-rtd-Trap 16 }

----------------------------------------------------------------
-- 1.3.6.1.4.1.8691.10.2500.31.8
    slot2-tc-Trap OBJECT IDENTIFIER ::= { slot2-io-Trap 8 }
----------------------------------------------------------------

slot2Trap-tc-00 NOTIFICATION-TYPE
    STATUS      current
    DESCRIPTION
        "SNMPTrap, tc channel-00 in slot 2"
::= { slot2-tc-Trap 1 }

slot2Trap-tc-01 NOTIFICATION-TYPE
    STATUS      current
    DESCRIPTION
        "SNMPTrap, tc channel-01 in slot 2"
::= { slot2-tc-Trap 2 }

slot2Trap-tc-02 NOTIFICATION-TYPE
    STATUS      current
    DESCRIPTION
        "SNMPTrap, tc channel-02 in slot 2"
::= { slot2-tc-Trap 3 }

slot2Trap-tc-03 NOTIFICATION-TYPE
    STATUS      current
    DESCRIPTION
        "SNMPTrap, tc channel-03 in slot 2"
::= { slot2-tc-Trap 4 }

slot2Trap-tc-04 NOTIFICATION-TYPE
    STATUS      current
    DESCRIPTION
        "SNMPTrap, tc channel-04 in slot 2"
::= { slot2-tc-Trap 5 }

slot2Trap-tc-05 NOTIFICATION-TYPE
    STATUS      current
    DESCRIPTION
        "SNMPTrap, tc channel-05 in slot 2"
::= { slot2-tc-Trap 6 }

slot2Trap-tc-06 NOTIFICATION-TYPE
    STATUS      current
    DESCRIPTION
        "SNMPTrap, tc channel-06 in slot 2"
::= { slot2-tc-Trap 7 }

slot2Trap-tc-07 NOTIFICATION-TYPE
    STATUS      current
    DESCRIPTION
        "SNMPTrap, tc channel-07 in slot 2"
::= { slot2-tc-Trap 8 }

slot2Trap-tc-08 NOTIFICATION-TYPE
    STATUS      current
    DESCRIPTION
        "SNMPTrap, tc channel-08 in slot 2"
::= { slot2-tc-Trap 9 }

slot2Trap-tc-09 NOTIFICATION-TYPE
    STATUS      current
    DESCRIPTION
        "SNMPTrap, tc channel-09 in slot 2"
::= { slot2-tc-Trap 10 }

slot2Trap-tc-10 NOTIFICATION-TYPE
    STATUS      current
    DESCRIPTION
        "SNMPTrap, tc channel-10 in slot 2"
::= { slot2-tc-Trap 11 }

slot2Trap-tc-11 NOTIFICATION-TYPE
    STATUS      current
    DESCRIPTION
        "SNMPTrap, tc channel-11 in slot 2"
::= { slot2-tc-Trap 12 }

slot2Trap-tc-12 NOTIFICATION-TYPE
    STATUS      current
    DESCRIPTION
        "SNMPTrap, tc channel-12 in slot 2"
::= { slot2-tc-Trap 13 }

slot2Trap-tc-13 NOTIFICATION-TYPE
    STATUS      current
    DESCRIPTION
        "SNMPTrap, tc channel-13 in slot 2"
::= { slot2-tc-Trap 14 }

slot2Trap-tc-14 NOTIFICATION-TYPE
    STATUS      current
    DESCRIPTION
        "SNMPTrap, tc channel-14 in slot 2"
::= { slot2-tc-Trap 15 }

slot2Trap-tc-15 NOTIFICATION-TYPE
    STATUS      current
    DESCRIPTION
        "SNMPTrap, tc channel-15 in slot 2"
::= { slot2-tc-Trap 16 }		
				
		
----------------------------------------------------------------
-- 1.3.6.1.4.1.8691.10.2500.40
    slot3-io OBJECT IDENTIFIER ::= { ioLogik2500 40 }
----------------------------------------------------------------
-- slot 3 DI
slot3-diTable OBJECT-TYPE
		SYNTAX 			SEQUENCE OF Slot3-diDef
		MAX-ACCESS 		not-accessible
		STATUS 			current
		DESCRIPTION		"The di channel table"
		::= { slot3-io 1 }

slot3-di OBJECT-TYPE
		SYNTAX 			Slot3-diDef
		MAX-ACCESS 		not-accessible
		STATUS 			current
		DESCRIPTION		"The di channel item"
		INDEX { slot3-diIndex }
		::= { slot3-diTable 1 }

Slot3-diDef ::= SEQUENCE { 
    	slot3-diIndex		INTEGER,
		slot3-diStatus		Unsigned32,
		slot3-diCounterReset2Init INTEGER		
		}  

slot3-diIndex OBJECT-TYPE
		SYNTAX 			INTEGER (0..15)
		MAX-ACCESS 		read-only
		STATUS 			current
		DESCRIPTION		"The channel index"
		::= { slot3-di 1 }
		
slot3-diStatus OBJECT-TYPE
		SYNTAX 			Unsigned32
		MAX-ACCESS 		read-write
		STATUS 			current
		DESCRIPTION		"The channel di status. 0=off, 1=on in di mode or n=counter value in counter mode"
		::= { slot3-di 2 }

slot3-diCounterReset2Init OBJECT-TYPE
		SYNTAX 			INTEGER 
		MAX-ACCESS 		read-write
		STATUS 			current
		DESCRIPTION		"Trigger counter to initial value. 1=Reset counter to initial value"
		::= { slot3-di 3 }
		
-- slot 3 DICounterStart
slot3-diCounterStartTable OBJECT-TYPE
		SYNTAX 			SEQUENCE OF Slot3-diCounterStartDef
		MAX-ACCESS 		not-accessible
		STATUS 			current
		DESCRIPTION		"The counter table starting for di"
		::= { slot3-io 39 }

slot3-diCounterStart OBJECT-TYPE
		SYNTAX 			Slot3-diCounterStartDef
		MAX-ACCESS 		not-accessible
		STATUS 			current
		DESCRIPTION		"The counter starting of di item"
		INDEX { slot3-diCounterStartIndex }
		::= { slot3-diCounterStartTable 1 }

Slot3-diCounterStartDef ::= SEQUENCE { 
    		slot3-diCounterStartIndex		INTEGER,
			slot3-diCounterStartStatus		INTEGER			
		}  

slot3-diCounterStartIndex OBJECT-TYPE
		SYNTAX 			INTEGER (0..15)
		MAX-ACCESS 		read-only
		STATUS 			current
		DESCRIPTION		"The channel index for di counter start"
		::= { slot3-diCounterStart 1 }
		
slot3-diCounterStartStatus OBJECT-TYPE
		SYNTAX 			INTEGER (0..1)
		MAX-ACCESS 		read-write
		STATUS 			current
		DESCRIPTION		"The channel status for di counter start. 0=stop, 1=start"
		::= { slot3-diCounterStart 2 }  
		
-- slot 3 DO
slot3-doTable OBJECT-TYPE
		SYNTAX 			SEQUENCE OF Slot3-doDef
		MAX-ACCESS 		not-accessible
		STATUS 			current
		DESCRIPTION		"The do channel table"
		::= { slot3-io 2 }

slot3-do OBJECT-TYPE
		SYNTAX 			Slot3-doDef
		MAX-ACCESS 		not-accessible
		STATUS 			current
		DESCRIPTION		"The do channel item"
		INDEX { slot3-doIndex }
		::= { slot3-doTable 1 }

Slot3-doDef ::= SEQUENCE { 
    		slot3-doIndex		INTEGER,
		slot3-doStatus		INTEGER		
		}  

slot3-doIndex OBJECT-TYPE
		SYNTAX 			INTEGER (0..15)
		MAX-ACCESS 		read-only
		STATUS 			current
		DESCRIPTION		"The channel index"
		::= { slot3-do 1 }
		
slot3-doStatus OBJECT-TYPE
		SYNTAX 			INTEGER (0..1)
		MAX-ACCESS 		read-write
		STATUS 			current
		DESCRIPTION		"The channel do status. 0=off, 1=on in do mode or 0=stop, 1=start in pulse mode"
		::= { slot3-do 2 }  

-- slot 3 DIO
slot3-dioTable OBJECT-TYPE
		SYNTAX 			SEQUENCE OF Slot3-dioDef
		MAX-ACCESS 		not-accessible
		STATUS 			current
		DESCRIPTION		"The dio channel table"
		::= { slot3-io 3 }

slot3-dio OBJECT-TYPE
		SYNTAX 			Slot3-dioDef
		MAX-ACCESS 		not-accessible
		STATUS 			current
		DESCRIPTION		"The dio channel item"
		INDEX { slot3-dioIndex }
		::= { slot3-dioTable 1 }

Slot3-dioDef ::= SEQUENCE { 
    	slot3-dioIndex		INTEGER,
		slot3-dioStatus		Unsigned32,
		slot3-dioCounterReset2Init INTEGER				
		}  

slot3-dioIndex OBJECT-TYPE
		SYNTAX 			INTEGER (0..15)
		MAX-ACCESS 		read-only
		STATUS 			current
		DESCRIPTION		"The channel index"
		::= { slot3-dio 1 }
		
slot3-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot3-dio 2 }  

slot3-dioCounterReset2Init OBJECT-TYPE
		SYNTAX 			INTEGER 
		MAX-ACCESS 		read-write
		STATUS 			current
		DESCRIPTION		"Trigger counter to initial value. 1=Reset counter to initial value"
		::= { slot3-dio 3 }		
		
-- slot 3 DIOCounterStart
slot3-dioCounterStartTable OBJECT-TYPE
		SYNTAX 			SEQUENCE OF Slot3-dioCounterStartDef
		MAX-ACCESS 		not-accessible
		STATUS 			current
		DESCRIPTION		"The counter table starting for dio"
		::= { slot3-io 46 }

slot3-dioCounterStart OBJECT-TYPE
		SYNTAX 			Slot3-dioCounterStartDef
		MAX-ACCESS 		not-accessible
		STATUS 			current
		DESCRIPTION		"The counter starting of dio item"
		INDEX { slot3-dioCounterStartIndex }
		::= { slot3-dioCounterStartTable 1 }

Slot3-dioCounterStartDef ::= SEQUENCE { 
    		slot3-dioCounterStartIndex		INTEGER,
			slot3-dioCounterStartStatus		INTEGER			
		}  

slot3-dioCounterStartIndex OBJECT-TYPE
		SYNTAX 			INTEGER (0..15)
		MAX-ACCESS 		read-only
		STATUS 			current
		DESCRIPTION		"The channel index for dio counter start"
		::= { slot3-dioCounterStart 1 }
		
slot3-dioCounterStartStatus OBJECT-TYPE
		SYNTAX 			INTEGER (0..1)
		MAX-ACCESS 		read-write
		STATUS 			current
		DESCRIPTION		"The channel status for dio counter start. 0=stop, 1=start"
		::= { slot3-dioCounterStart 2 } 
		
-- slot 3 Relay
slot3-relayTable OBJECT-TYPE
		SYNTAX 			SEQUENCE OF Slot3-relayDef
		MAX-ACCESS 		not-accessible
		STATUS 			current
		DESCRIPTION		"The relay channel table"
		::= { slot3-io 4 }

slot3-relay OBJECT-TYPE
		SYNTAX 			Slot3-relayDef
		MAX-ACCESS 		not-accessible
		STATUS 			current
		DESCRIPTION		"The relay channel item"
		INDEX { slot3-relayIndex }
		::= { slot3-relayTable 1 }

Slot3-relayDef ::= SEQUENCE { 
    		slot3-relayIndex		INTEGER,
		slot3-relayStatus		INTEGER		
		}  

slot3-relayIndex OBJECT-TYPE
		SYNTAX 			INTEGER (0..15)
		MAX-ACCESS 		read-only
		STATUS 			current
		DESCRIPTION		"The channel index"
		::= { slot3-relay 1 }
		
slot3-relayStatus OBJECT-TYPE
		SYNTAX 			INTEGER (0..1)
		MAX-ACCESS 		read-write
		STATUS 			current
		DESCRIPTION		"The channel relay status. 0=off, 1=on in do mode or 0=stop, 1=start in pulse mode"
		::= { slot3-relay 2 }  

-- slot 3 AI
slot3-aiTable OBJECT-TYPE
		SYNTAX 			SEQUENCE OF Slot3-aiDef
		MAX-ACCESS 		not-accessible
		STATUS 			current
		DESCRIPTION		"The ai channel table"
		::= { slot3-io 5 }

slot3-ai OBJECT-TYPE
		SYNTAX 			Slot3-aiDef
		MAX-ACCESS 		not-accessible
		STATUS 			current
		DESCRIPTION		"The ai channel item"
		INDEX { slot3-aiIndex }
		::= { slot3-aiTable 1 }

Slot3-aiDef ::= SEQUENCE { 
    	slot3-aiIndex		INTEGER,
		slot3-aiStatus		OCTET STRING,
		slot3-aiBurnoutStatus INTEGER		
		}  

slot3-aiIndex OBJECT-TYPE
		SYNTAX 			INTEGER (0..15)
		MAX-ACCESS 		read-only
		STATUS 			current
		DESCRIPTION		"The channel index"
		::= { slot3-ai 1 }
		
slot3-aiStatus OBJECT-TYPE
		SYNTAX 			OCTET STRING
		MAX-ACCESS 		read-only
		STATUS 			current
		DESCRIPTION		"The channel ai scaled value"
		::= { slot3-ai 2 }  

slot3-aiBurnoutStatus OBJECT-TYPE
		SYNTAX 			INTEGER (0..3)
		MAX-ACCESS 		read-only
		STATUS 			current
		DESCRIPTION		"The channel of burnout status (0: normal, 1: burnout, 2: underange, 3: overange)"
		::= { slot3-ai 3 }  		
		
-- slot 3 AO
slot3-aoTable OBJECT-TYPE
		SYNTAX 			SEQUENCE OF Slot3-aoDef
		MAX-ACCESS 		not-accessible
		STATUS 			current
		DESCRIPTION		"The ao channel table"
		::= { slot3-io 6 }

slot3-ao OBJECT-TYPE
		SYNTAX 			Slot3-aoDef
		MAX-ACCESS 		not-accessible
		STATUS 			current
		DESCRIPTION		"The ao channel item"
		INDEX { slot3-aoIndex }
		::= { slot3-aoTable 1 }

Slot3-aoDef ::= SEQUENCE { 
    		slot3-aoIndex		INTEGER,
		slot3-aoStatus		OCTET STRING		
		}  

slot3-aoIndex OBJECT-TYPE
		SYNTAX 			INTEGER (0..15)
		MAX-ACCESS 		read-only
		STATUS 			current
		DESCRIPTION		"The channel index"
		::= { slot3-ao 1 }
		
slot3-aoStatus OBJECT-TYPE
		SYNTAX 			OCTET STRING
		MAX-ACCESS 		read-write
		STATUS 			current
		DESCRIPTION		"The channel ao scaled value"
		::= { slot3-ao 2 }  

-- slot 3 RTD
slot3-rtdTable OBJECT-TYPE
		SYNTAX 			SEQUENCE OF Slot3-rtdDef
		MAX-ACCESS 		not-accessible
		STATUS 			current
		DESCRIPTION		"The rtd channel table"
		::= { slot3-io 7 }

slot3-rtd OBJECT-TYPE
		SYNTAX 			Slot3-rtdDef
		MAX-ACCESS 		not-accessible
		STATUS 			current
		DESCRIPTION		"The rtd channel item"
		INDEX { slot3-rtdIndex }
		::= { slot3-rtdTable 1 }

Slot3-rtdDef ::= SEQUENCE { 
    		slot3-rtdIndex		INTEGER,
		slot3-rtdStatus		OCTET STRING		
		}  

slot3-rtdIndex OBJECT-TYPE
		SYNTAX 			INTEGER (0..15)
		MAX-ACCESS 		read-only
		STATUS 			current
		DESCRIPTION		"The channel index"
		::= { slot3-rtd 1 }
		
slot3-rtdStatus OBJECT-TYPE
		SYNTAX 			OCTET STRING
		MAX-ACCESS 		read-only
		STATUS 			current
		DESCRIPTION		"The channel rtd scaled value"
		::= { slot3-rtd 2 }  

-- slot 3 TC
slot3-tcTable OBJECT-TYPE
		SYNTAX 			SEQUENCE OF Slot3-tcDef
		MAX-ACCESS 		not-accessible
		STATUS 			current
		DESCRIPTION		"The tc channel table"
		::= { slot3-io 8 }

slot3-tc OBJECT-TYPE
		SYNTAX 			Slot3-tcDef
		MAX-ACCESS 		not-accessible
		STATUS 			current
		DESCRIPTION		"The tc channel item"
		INDEX { slot3-tcIndex }
		::= { slot3-tcTable 1 }

Slot3-tcDef ::= SEQUENCE { 
    		slot3-tcIndex		INTEGER,
		slot3-tcStatus		OCTET STRING		
		}  

slot3-tcIndex OBJECT-TYPE
		SYNTAX 			INTEGER (0..15)
		MAX-ACCESS 		read-only
		STATUS 			current
		DESCRIPTION		"The channel index"
		::= { slot3-tc 1 }
		
slot3-tcStatus OBJECT-TYPE
		SYNTAX 			OCTET STRING
		MAX-ACCESS 		read-only
		STATUS 			current
		DESCRIPTION		"The channel tc scaled value"
		::= { slot3-tc 2 }  

----------------------------------------------------------------
-- 1.3.6.1.4.1.8691.10.2500.41
    slot3-io-Trap OBJECT IDENTIFIER ::= { ioLogik2500 41 }
----------------------------------------------------------------

----------------------------------------------------------------
-- 1.3.6.1.4.1.8691.10.2500.41.1
    slot3-di-Trap OBJECT IDENTIFIER ::= { slot3-io-Trap 1 }
----------------------------------------------------------------

slot3Trap-di-00 NOTIFICATION-TYPE
    STATUS      current
    DESCRIPTION
        "SNMPTrap, di channel-00 in slot 3"
::= { slot3-di-Trap 1 }

slot3Trap-di-01 NOTIFICATION-TYPE
    STATUS      current
    DESCRIPTION
        "SNMPTrap, di channel-01 in slot 3"
::= { slot3-di-Trap 2 }

slot3Trap-di-02 NOTIFICATION-TYPE
    STATUS      current
    DESCRIPTION
        "SNMPTrap, di channel-02 in slot 3"
::= { slot3-di-Trap 3 }

slot3Trap-di-03 NOTIFICATION-TYPE
    STATUS      current
    DESCRIPTION
        "SNMPTrap, di channel-03 in slot 3"
::= { slot3-di-Trap 4 }

slot3Trap-di-04 NOTIFICATION-TYPE
    STATUS      current
    DESCRIPTION
        "SNMPTrap, di channel-04 in slot 3"
::= { slot3-di-Trap 5 }

slot3Trap-di-05 NOTIFICATION-TYPE
    STATUS      current
    DESCRIPTION
        "SNMPTrap, di channel-05 in slot 3"
::= { slot3-di-Trap 6 }

slot3Trap-di-06 NOTIFICATION-TYPE
    STATUS      current
    DESCRIPTION
        "SNMPTrap, di channel-06 in slot 3"
::= { slot3-di-Trap 7 }

slot3Trap-di-07 NOTIFICATION-TYPE
    STATUS      current
    DESCRIPTION
        "SNMPTrap, di channel-07 in slot 3"
::= { slot3-di-Trap 8 }

slot3Trap-di-08 NOTIFICATION-TYPE
    STATUS      current
    DESCRIPTION
        "SNMPTrap, di channel-08 in slot 3"
::= { slot3-di-Trap 9 }

slot3Trap-di-09 NOTIFICATION-TYPE
    STATUS      current
    DESCRIPTION
        "SNMPTrap, di channel-09 in slot 3"
::= { slot3-di-Trap 10 }

slot3Trap-di-10 NOTIFICATION-TYPE
    STATUS      current
    DESCRIPTION
        "SNMPTrap, di channel-10 in slot 3"
::= { slot3-di-Trap 11 }

slot3Trap-di-11 NOTIFICATION-TYPE
    STATUS      current
    DESCRIPTION
        "SNMPTrap, di channel-11 in slot 3"
::= { slot3-di-Trap 12 }

slot3Trap-di-12 NOTIFICATION-TYPE
    STATUS      current
    DESCRIPTION
        "SNMPTrap, di channel-12 in slot 3"
::= { slot3-di-Trap 13 }

slot3Trap-di-13 NOTIFICATION-TYPE
    STATUS      current
    DESCRIPTION
        "SNMPTrap, di channel-13 in slot 3"
::= { slot3-di-Trap 14 }

slot3Trap-di-14 NOTIFICATION-TYPE
    STATUS      current
    DESCRIPTION
        "SNMPTrap, di channel-14 in slot 3"
::= { slot3-di-Trap 15 }

slot3Trap-di-15 NOTIFICATION-TYPE
    STATUS      current
    DESCRIPTION
        "SNMPTrap, di channel-15 in slot 3"
::= { slot3-di-Trap 16 }
----------------------------------------------------------------
-- 1.3.6.1.4.1.8691.10.2500.41.2
    slot3-do-Trap OBJECT IDENTIFIER ::= { slot3-io-Trap 2 }
----------------------------------------------------------------

slot3Trap-do-00 NOTIFICATION-TYPE
    STATUS      current
    DESCRIPTION
        "SNMPTrap, do channel-00 in slot 3"
::= { slot3-do-Trap 1 }

slot3Trap-do-01 NOTIFICATION-TYPE
    STATUS      current
    DESCRIPTION
        "SNMPTrap, do channel-01 in slot 3"
::= { slot3-do-Trap 2 }

slot3Trap-do-02 NOTIFICATION-TYPE
    STATUS      current
    DESCRIPTION
        "SNMPTrap, do channel-02 in slot 3"
::= { slot3-do-Trap 3 }

slot3Trap-do-03 NOTIFICATION-TYPE
    STATUS      current
    DESCRIPTION
        "SNMPTrap, do channel-03 in slot 3"
::= { slot3-do-Trap 4 }

slot3Trap-do-04 NOTIFICATION-TYPE
    STATUS      current
    DESCRIPTION
        "SNMPTrap, do channel-04 in slot 3"
::= { slot3-do-Trap 5 }

slot3Trap-do-05 NOTIFICATION-TYPE
    STATUS      current
    DESCRIPTION
        "SNMPTrap, do channel-05 in slot 3"
::= { slot3-do-Trap 6 }

slot3Trap-do-06 NOTIFICATION-TYPE
    STATUS      current
    DESCRIPTION
        "SNMPTrap, do channel-06 in slot 3"
::= { slot3-do-Trap 7 }

slot3Trap-do-07 NOTIFICATION-TYPE
    STATUS      current
    DESCRIPTION
        "SNMPTrap, do channel-07 in slot 3"
::= { slot3-do-Trap 8 }

slot3Trap-do-08 NOTIFICATION-TYPE
    STATUS      current
    DESCRIPTION
        "SNMPTrap, do channel-08 in slot 3"
::= { slot3-do-Trap 9 }

slot3Trap-do-09 NOTIFICATION-TYPE
    STATUS      current
    DESCRIPTION
        "SNMPTrap, do channel-09 in slot 3"
::= { slot3-do-Trap 10 }

slot3Trap-do-10 NOTIFICATION-TYPE
    STATUS      current
    DESCRIPTION
        "SNMPTrap, do channel-10 in slot 3"
::= { slot3-do-Trap 11 }

slot3Trap-do-11 NOTIFICATION-TYPE
    STATUS      current
    DESCRIPTION
        "SNMPTrap, do channel-11 in slot 3"
::= { slot3-do-Trap 12 }

slot3Trap-do-12 NOTIFICATION-TYPE
    STATUS      current
    DESCRIPTION
        "SNMPTrap, do channel-12 in slot 3"
::= { slot3-do-Trap 13 }

slot3Trap-do-13 NOTIFICATION-TYPE
    STATUS      current
    DESCRIPTION
        "SNMPTrap, do channel-13 in slot 3"
::= { slot3-do-Trap 14 }

slot3Trap-do-14 NOTIFICATION-TYPE
    STATUS      current
    DESCRIPTION
        "SNMPTrap, do channel-14 in slot 3"
::= { slot3-do-Trap 15 }

slot3Trap-do-15 NOTIFICATION-TYPE
    STATUS      current
    DESCRIPTION
        "SNMPTrap, do channel-15 in slot 3"
::= { slot3-do-Trap 16 }

----------------------------------------------------------------
-- 1.3.6.1.4.1.8691.10.2500.41.3
    slot3-dio-Trap OBJECT IDENTIFIER ::= { slot3-io-Trap 3 }
----------------------------------------------------------------

slot3Trap-dio-00 NOTIFICATION-TYPE
    STATUS      current
    DESCRIPTION
        "SNMPTrap, dio channel-00 in slot 3"
::= { slot3-dio-Trap 1 }

slot3Trap-dio-01 NOTIFICATION-TYPE
    STATUS      current
    DESCRIPTION
        "SNMPTrap, dio channel-01 in slot 3"
::= { slot3-dio-Trap 2 }

slot3Trap-dio-02 NOTIFICATION-TYPE
    STATUS      current
    DESCRIPTION
        "SNMPTrap, dio channel-02 in slot 3"
::= { slot3-dio-Trap 3 }

slot3Trap-dio-03 NOTIFICATION-TYPE
    STATUS      current
    DESCRIPTION
        "SNMPTrap, dio channel-03 in slot 3"
::= { slot3-dio-Trap 4 }

slot3Trap-dio-04 NOTIFICATION-TYPE
    STATUS      current
    DESCRIPTION
        "SNMPTrap, dio channel-04 in slot 3"
::= { slot3-dio-Trap 5 }

slot3Trap-dio-05 NOTIFICATION-TYPE
    STATUS      current
    DESCRIPTION
        "SNMPTrap, dio channel-05 in slot 3"
::= { slot3-dio-Trap 6 }

slot3Trap-dio-06 NOTIFICATION-TYPE
    STATUS      current
    DESCRIPTION
        "SNMPTrap, dio channel-06 in slot 3"
::= { slot3-dio-Trap 7 }

slot3Trap-dio-07 NOTIFICATION-TYPE
    STATUS      current
    DESCRIPTION
        "SNMPTrap, dio channel-07 in slot 3"
::= { slot3-dio-Trap 8 }

slot3Trap-dio-08 NOTIFICATION-TYPE
    STATUS      current
    DESCRIPTION
        "SNMPTrap, dio channel-08 in slot 3"
::= { slot3-dio-Trap 9 }

slot3Trap-dio-09 NOTIFICATION-TYPE
    STATUS      current
    DESCRIPTION
        "SNMPTrap, dio channel-09 in slot 3"
::= { slot3-dio-Trap 10 }

slot3Trap-dio-10 NOTIFICATION-TYPE
    STATUS      current
    DESCRIPTION
        "SNMPTrap, dio channel-10 in slot 3"
::= { slot3-dio-Trap 11 }

slot3Trap-dio-11 NOTIFICATION-TYPE
    STATUS      current
    DESCRIPTION
        "SNMPTrap, dio channel-11 in slot 3"
::= { slot3-dio-Trap 12 }

slot3Trap-dio-12 NOTIFICATION-TYPE
    STATUS      current
    DESCRIPTION
        "SNMPTrap, dio channel-12 in slot 3"
::= { slot3-dio-Trap 13 }

slot3Trap-dio-13 NOTIFICATION-TYPE
    STATUS      current
    DESCRIPTION
        "SNMPTrap, dio channel-13 in slot 3"
::= { slot3-dio-Trap 14 }

slot3Trap-dio-14 NOTIFICATION-TYPE
    STATUS      current
    DESCRIPTION
        "SNMPTrap, dio channel-14 in slot 3"
::= { slot3-dio-Trap 15 }

slot3Trap-dio-15 NOTIFICATION-TYPE
    STATUS      current
    DESCRIPTION
        "SNMPTrap, dio channel-15 in slot 3"
::= { slot3-dio-Trap 16 }

----------------------------------------------------------------
-- 1.3.6.1.4.1.8691.10.2500.41.4
    slot3-relay-Trap OBJECT IDENTIFIER ::= { slot3-io-Trap 4 }
----------------------------------------------------------------

slot3Trap-relay-00 NOTIFICATION-TYPE
    STATUS      current
    DESCRIPTION
        "SNMPTrap, relay channel-00 in slot 3"
::= { slot3-relay-Trap 1 }

slot3Trap-relay-01 NOTIFICATION-TYPE
    STATUS      current
    DESCRIPTION
        "SNMPTrap, relay channel-01 in slot 3"
::= { slot3-relay-Trap 2 }

slot3Trap-relay-02 NOTIFICATION-TYPE
    STATUS      current
    DESCRIPTION
        "SNMPTrap, relay channel-02 in slot 3"
::= { slot3-relay-Trap 3 }

slot3Trap-relay-03 NOTIFICATION-TYPE
    STATUS      current
    DESCRIPTION
        "SNMPTrap, relay channel-03 in slot 3"
::= { slot3-relay-Trap 4 }

slot3Trap-relay-04 NOTIFICATION-TYPE
    STATUS      current
    DESCRIPTION
        "SNMPTrap, relay channel-04 in slot 3"
::= { slot3-relay-Trap 5 }

slot3Trap-relay-05 NOTIFICATION-TYPE
    STATUS      current
    DESCRIPTION
        "SNMPTrap, relay channel-05 in slot 3"
::= { slot3-relay-Trap 6 }

slot3Trap-relay-06 NOTIFICATION-TYPE
    STATUS      current
    DESCRIPTION
        "SNMPTrap, relay channel-06 in slot 3"
::= { slot3-relay-Trap 7 }

slot3Trap-relay-07 NOTIFICATION-TYPE
    STATUS      current
    DESCRIPTION
        "SNMPTrap, relay channel-07 in slot 3"
::= { slot3-relay-Trap 8 }

slot3Trap-relay-08 NOTIFICATION-TYPE
    STATUS      current
    DESCRIPTION
        "SNMPTrap, relay channel-08 in slot 3"
::= { slot3-relay-Trap 9 }

slot3Trap-relay-09 NOTIFICATION-TYPE
    STATUS      current
    DESCRIPTION
        "SNMPTrap, relay channel-09 in slot 3"
::= { slot3-relay-Trap 10 }

slot3Trap-relay-10 NOTIFICATION-TYPE
    STATUS      current
    DESCRIPTION
        "SNMPTrap, relay channel-10 in slot 3"
::= { slot3-relay-Trap 11 }

slot3Trap-relay-11 NOTIFICATION-TYPE
    STATUS      current
    DESCRIPTION
        "SNMPTrap, relay channel-11 in slot 3"
::= { slot3-relay-Trap 12 }

slot3Trap-relay-12 NOTIFICATION-TYPE
    STATUS      current
    DESCRIPTION
        "SNMPTrap, relay channel-12 in slot 3"
::= { slot3-relay-Trap 13 }

slot3Trap-relay-13 NOTIFICATION-TYPE
    STATUS      current
    DESCRIPTION
        "SNMPTrap, relay channel-13 in slot 3"
::= { slot3-relay-Trap 14 }

slot3Trap-relay-14 NOTIFICATION-TYPE
    STATUS      current
    DESCRIPTION
        "SNMPTrap, relay channel-14 in slot 3"
::= { slot3-relay-Trap 15 }

slot3Trap-relay-15 NOTIFICATION-TYPE
    STATUS      current
    DESCRIPTION
        "SNMPTrap, relay channel-15 in slot 3"
::= { slot3-relay-Trap 16 }

----------------------------------------------------------------
-- 1.3.6.1.4.1.8691.10.2500.41.5
    slot3-ai-Trap OBJECT IDENTIFIER ::= { slot3-io-Trap 5 }
----------------------------------------------------------------

slot3Trap-ai-00 NOTIFICATION-TYPE
    STATUS      current
    DESCRIPTION
        "SNMPTrap, ai channel-00 in slot 3"
::= { slot3-ai-Trap 1 }

slot3Trap-ai-01 NOTIFICATION-TYPE
    STATUS      current
    DESCRIPTION
        "SNMPTrap, ai channel-01 in slot 3"
::= { slot3-ai-Trap 2 }

slot3Trap-ai-02 NOTIFICATION-TYPE
    STATUS      current
    DESCRIPTION
        "SNMPTrap, ai channel-02 in slot 3"
::= { slot3-ai-Trap 3 }

slot3Trap-ai-03 NOTIFICATION-TYPE
    STATUS      current
    DESCRIPTION
        "SNMPTrap, ai channel-03 in slot 3"
::= { slot3-ai-Trap 4 }

slot3Trap-ai-04 NOTIFICATION-TYPE
    STATUS      current
    DESCRIPTION
        "SNMPTrap, ai channel-04 in slot 3"
::= { slot3-ai-Trap 5 }

slot3Trap-ai-05 NOTIFICATION-TYPE
    STATUS      current
    DESCRIPTION
        "SNMPTrap, ai channel-05 in slot 3"
::= { slot3-ai-Trap 6 }

slot3Trap-ai-06 NOTIFICATION-TYPE
    STATUS      current
    DESCRIPTION
        "SNMPTrap, ai channel-06 in slot 3"
::= { slot3-ai-Trap 7 }

slot3Trap-ai-07 NOTIFICATION-TYPE
    STATUS      current
    DESCRIPTION
        "SNMPTrap, ai channel-07 in slot 3"
::= { slot3-ai-Trap 8 }

slot3Trap-ai-08 NOTIFICATION-TYPE
    STATUS      current
    DESCRIPTION
        "SNMPTrap, ai channel-08 in slot 3"
::= { slot3-ai-Trap 9 }

slot3Trap-ai-09 NOTIFICATION-TYPE
    STATUS      current
    DESCRIPTION
        "SNMPTrap, ai channel-09 in slot 3"
::= { slot3-ai-Trap 10 }

slot3Trap-ai-10 NOTIFICATION-TYPE
    STATUS      current
    DESCRIPTION
        "SNMPTrap, ai channel-10 in slot 3"
::= { slot3-ai-Trap 11 }

slot3Trap-ai-11 NOTIFICATION-TYPE
    STATUS      current
    DESCRIPTION
        "SNMPTrap, ai channel-11 in slot 3"
::= { slot3-ai-Trap 12 }

slot3Trap-ai-12 NOTIFICATION-TYPE
    STATUS      current
    DESCRIPTION
        "SNMPTrap, ai channel-12 in slot 3"
::= { slot3-ai-Trap 13 }

slot3Trap-ai-13 NOTIFICATION-TYPE
    STATUS      current
    DESCRIPTION
        "SNMPTrap, ai channel-13 in slot 3"
::= { slot3-ai-Trap 14 }

slot3Trap-ai-14 NOTIFICATION-TYPE
    STATUS      current
    DESCRIPTION
        "SNMPTrap, ai channel-14 in slot 3"
::= { slot3-ai-Trap 15 }

slot3Trap-ai-15 NOTIFICATION-TYPE
    STATUS      current
    DESCRIPTION
        "SNMPTrap, ai channel-15 in slot 3"
::= { slot3-ai-Trap 16 }

----------------------------------------------------------------
-- 1.3.6.1.4.1.8691.10.2500.41.6
    slot3-ao-Trap OBJECT IDENTIFIER ::= { slot3-io-Trap 6 }
----------------------------------------------------------------

slot3Trap-ao-00 NOTIFICATION-TYPE
    STATUS      current
    DESCRIPTION
        "SNMPTrap, ao channel-00 in slot 3"
::= { slot3-ao-Trap 1 }

slot3Trap-ao-01 NOTIFICATION-TYPE
    STATUS      current
    DESCRIPTION
        "SNMPTrap, ao channel-01 in slot 3"
::= { slot3-ao-Trap 2 }

slot3Trap-ao-02 NOTIFICATION-TYPE
    STATUS      current
    DESCRIPTION
        "SNMPTrap, ao channel-02 in slot 3"
::= { slot3-ao-Trap 3 }

slot3Trap-ao-03 NOTIFICATION-TYPE
    STATUS      current
    DESCRIPTION
        "SNMPTrap, ao channel-03 in slot 3"
::= { slot3-ao-Trap 4 }

slot3Trap-ao-04 NOTIFICATION-TYPE
    STATUS      current
    DESCRIPTION
        "SNMPTrap, ao channel-04 in slot 3"
::= { slot3-ao-Trap 5 }

slot3Trap-ao-05 NOTIFICATION-TYPE
    STATUS      current
    DESCRIPTION
        "SNMPTrap, ao channel-05 in slot 3"
::= { slot3-ao-Trap 6 }

slot3Trap-ao-06 NOTIFICATION-TYPE
    STATUS      current
    DESCRIPTION
        "SNMPTrap, ao channel-06 in slot 3"
::= { slot3-ao-Trap 7 }

slot3Trap-ao-07 NOTIFICATION-TYPE
    STATUS      current
    DESCRIPTION
        "SNMPTrap, ao channel-07 in slot 3"
::= { slot3-ao-Trap 8 }

slot3Trap-ao-08 NOTIFICATION-TYPE
    STATUS      current
    DESCRIPTION
        "SNMPTrap, ao channel-08 in slot 3"
::= { slot3-ao-Trap 9 }

slot3Trap-ao-09 NOTIFICATION-TYPE
    STATUS      current
    DESCRIPTION
        "SNMPTrap, ao channel-09 in slot 3"
::= { slot3-ao-Trap 10 }

slot3Trap-ao-10 NOTIFICATION-TYPE
    STATUS      current
    DESCRIPTION
        "SNMPTrap, ao channel-10 in slot 3"
::= { slot3-ao-Trap 11 }

slot3Trap-ao-11 NOTIFICATION-TYPE
    STATUS      current
    DESCRIPTION
        "SNMPTrap, ao channel-11 in slot 3"
::= { slot3-ao-Trap 12 }

slot3Trap-ao-12 NOTIFICATION-TYPE
    STATUS      current
    DESCRIPTION
        "SNMPTrap, ao channel-12 in slot 3"
::= { slot3-ao-Trap 13 }

slot3Trap-ao-13 NOTIFICATION-TYPE
    STATUS      current
    DESCRIPTION
        "SNMPTrap, ao channel-13 in slot 3"
::= { slot3-ao-Trap 14 }

slot3Trap-ao-14 NOTIFICATION-TYPE
    STATUS      current
    DESCRIPTION
        "SNMPTrap, ao channel-14 in slot 3"
::= { slot3-ao-Trap 15 }

slot3Trap-ao-15 NOTIFICATION-TYPE
    STATUS      current
    DESCRIPTION
        "SNMPTrap, ao channel-15 in slot 3"
::= { slot3-ao-Trap 16 }

----------------------------------------------------------------
-- 1.3.6.1.4.1.8691.10.2500.41.7
    slot3-rtd-Trap OBJECT IDENTIFIER ::= { slot3-io-Trap 7 }
----------------------------------------------------------------

slot3Trap-rtd-00 NOTIFICATION-TYPE
    STATUS      current
    DESCRIPTION
        "SNMPTrap, rtd channel-00 in slot 3"
::= { slot3-rtd-Trap 1 }

slot3Trap-rtd-01 NOTIFICATION-TYPE
    STATUS      current
    DESCRIPTION
        "SNMPTrap, rtd channel-01 in slot 3"
::= { slot3-rtd-Trap 2 }

slot3Trap-rtd-02 NOTIFICATION-TYPE
    STATUS      current
    DESCRIPTION
        "SNMPTrap, rtd channel-02 in slot 3"
::= { slot3-rtd-Trap 3 }

slot3Trap-rtd-03 NOTIFICATION-TYPE
    STATUS      current
    DESCRIPTION
        "SNMPTrap, rtd channel-03 in slot 3"
::= { slot3-rtd-Trap 4 }

slot3Trap-rtd-04 NOTIFICATION-TYPE
    STATUS      current
    DESCRIPTION
        "SNMPTrap, rtd channel-04 in slot 3"
::= { slot3-rtd-Trap 5 }

slot3Trap-rtd-05 NOTIFICATION-TYPE
    STATUS      current
    DESCRIPTION
        "SNMPTrap, rtd channel-05 in slot 3"
::= { slot3-rtd-Trap 6 }

slot3Trap-rtd-06 NOTIFICATION-TYPE
    STATUS      current
    DESCRIPTION
        "SNMPTrap, rtd channel-06 in slot 3"
::= { slot3-rtd-Trap 7 }

slot3Trap-rtd-07 NOTIFICATION-TYPE
    STATUS      current
    DESCRIPTION
        "SNMPTrap, rtd channel-07 in slot 3"
::= { slot3-rtd-Trap 8 }

slot3Trap-rtd-08 NOTIFICATION-TYPE
    STATUS      current
    DESCRIPTION
        "SNMPTrap, rtd channel-08 in slot 3"
::= { slot3-rtd-Trap 9 }

slot3Trap-rtd-09 NOTIFICATION-TYPE
    STATUS      current
    DESCRIPTION
        "SNMPTrap, rtd channel-09 in slot 3"
::= { slot3-rtd-Trap 10 }

slot3Trap-rtd-10 NOTIFICATION-TYPE
    STATUS      current
    DESCRIPTION
        "SNMPTrap, rtd channel-10 in slot 3"
::= { slot3-rtd-Trap 11 }

slot3Trap-rtd-11 NOTIFICATION-TYPE
    STATUS      current
    DESCRIPTION
        "SNMPTrap, rtd channel-11 in slot 3"
::= { slot3-rtd-Trap 12 }

slot3Trap-rtd-12 NOTIFICATION-TYPE
    STATUS      current
    DESCRIPTION
        "SNMPTrap, rtd channel-12 in slot 3"
::= { slot3-rtd-Trap 13 }

slot3Trap-rtd-13 NOTIFICATION-TYPE
    STATUS      current
    DESCRIPTION
        "SNMPTrap, rtd channel-13 in slot 3"
::= { slot3-rtd-Trap 14 }

slot3Trap-rtd-14 NOTIFICATION-TYPE
    STATUS      current
    DESCRIPTION
        "SNMPTrap, rtd channel-14 in slot 3"
::= { slot3-rtd-Trap 15 }

slot3Trap-rtd-15 NOTIFICATION-TYPE
    STATUS      current
    DESCRIPTION
        "SNMPTrap, rtd channel-15 in slot 3"
::= { slot3-rtd-Trap 16 }

----------------------------------------------------------------
-- 1.3.6.1.4.1.8691.10.2500.41.8
    slot3-tc-Trap OBJECT IDENTIFIER ::= { slot3-io-Trap 8 }
----------------------------------------------------------------

slot3Trap-tc-00 NOTIFICATION-TYPE
    STATUS      current
    DESCRIPTION
        "SNMPTrap, tc channel-00 in slot 3"
::= { slot3-tc-Trap 1 }

slot3Trap-tc-01 NOTIFICATION-TYPE
    STATUS      current
    DESCRIPTION
        "SNMPTrap, tc channel-01 in slot 3"
::= { slot3-tc-Trap 2 }

slot3Trap-tc-02 NOTIFICATION-TYPE
    STATUS      current
    DESCRIPTION
        "SNMPTrap, tc channel-02 in slot 3"
::= { slot3-tc-Trap 3 }

slot3Trap-tc-03 NOTIFICATION-TYPE
    STATUS      current
    DESCRIPTION
        "SNMPTrap, tc channel-03 in slot 3"
::= { slot3-tc-Trap 4 }

slot3Trap-tc-04 NOTIFICATION-TYPE
    STATUS      current
    DESCRIPTION
        "SNMPTrap, tc channel-04 in slot 3"
::= { slot3-tc-Trap 5 }

slot3Trap-tc-05 NOTIFICATION-TYPE
    STATUS      current
    DESCRIPTION
        "SNMPTrap, tc channel-05 in slot 3"
::= { slot3-tc-Trap 6 }

slot3Trap-tc-06 NOTIFICATION-TYPE
    STATUS      current
    DESCRIPTION
        "SNMPTrap, tc channel-06 in slot 3"
::= { slot3-tc-Trap 7 }

slot3Trap-tc-07 NOTIFICATION-TYPE
    STATUS      current
    DESCRIPTION
        "SNMPTrap, tc channel-07 in slot 3"
::= { slot3-tc-Trap 8 }

slot3Trap-tc-08 NOTIFICATION-TYPE
    STATUS      current
    DESCRIPTION
        "SNMPTrap, tc channel-08 in slot 3"
::= { slot3-tc-Trap 9 }

slot3Trap-tc-09 NOTIFICATION-TYPE
    STATUS      current
    DESCRIPTION
        "SNMPTrap, tc channel-09 in slot 3"
::= { slot3-tc-Trap 10 }

slot3Trap-tc-10 NOTIFICATION-TYPE
    STATUS      current
    DESCRIPTION
        "SNMPTrap, tc channel-10 in slot 3"
::= { slot3-tc-Trap 11 }

slot3Trap-tc-11 NOTIFICATION-TYPE
    STATUS      current
    DESCRIPTION
        "SNMPTrap, tc channel-11 in slot 3"
::= { slot3-tc-Trap 12 }

slot3Trap-tc-12 NOTIFICATION-TYPE
    STATUS      current
    DESCRIPTION
        "SNMPTrap, tc channel-12 in slot 3"
::= { slot3-tc-Trap 13 }

slot3Trap-tc-13 NOTIFICATION-TYPE
    STATUS      current
    DESCRIPTION
        "SNMPTrap, tc channel-13 in slot 3"
::= { slot3-tc-Trap 14 }

slot3Trap-tc-14 NOTIFICATION-TYPE
    STATUS      current
    DESCRIPTION
        "SNMPTrap, tc channel-14 in slot 3"
::= { slot3-tc-Trap 15 }

slot3Trap-tc-15 NOTIFICATION-TYPE
    STATUS      current
    DESCRIPTION
        "SNMPTrap, tc channel-15 in slot 3"
::= { slot3-tc-Trap 16 }				
		
----------------------------------------------------------------
-- 1.3.6.1.4.1.8691.10.2500.50
    slot4-io OBJECT IDENTIFIER ::= { ioLogik2500 50 }
----------------------------------------------------------------
-- slot 4 DI
slot4-diTable OBJECT-TYPE
		SYNTAX 			SEQUENCE OF Slot4-diDef
		MAX-ACCESS 		not-accessible
		STATUS 			current
		DESCRIPTION		"The di channel table"
		::= { slot4-io 1 }

slot4-di OBJECT-TYPE
		SYNTAX 			Slot4-diDef
		MAX-ACCESS 		not-accessible
		STATUS 			current
		DESCRIPTION		"The di channel item"
		INDEX { slot4-diIndex }
		::= { slot4-diTable 1 }

Slot4-diDef ::= SEQUENCE { 
    	slot4-diIndex		INTEGER,
		slot4-diStatus		Unsigned32,
		slot4-diCounterReset2Init INTEGER		
		}  

slot4-diIndex OBJECT-TYPE
		SYNTAX 			INTEGER (0..15)
		MAX-ACCESS 		read-only
		STATUS 			current
		DESCRIPTION		"The channel index"
		::= { slot4-di 1 }
		
slot4-diStatus OBJECT-TYPE
		SYNTAX 			Unsigned32
		MAX-ACCESS 		read-write
		STATUS 			current
		DESCRIPTION		"The channel di status. 0=off, 1=on in di mode or n=counter value in counter mode"
		::= { slot4-di 2 }

slot4-diCounterReset2Init OBJECT-TYPE
		SYNTAX 			INTEGER 
		MAX-ACCESS 		read-write
		STATUS 			current
		DESCRIPTION		"Trigger counter to initial value. 1=Reset counter to initial value"
		::= { slot4-di 3 }		
		
-- slot 4 DICounterStart
slot4-diCounterStartTable OBJECT-TYPE
		SYNTAX 			SEQUENCE OF Slot4-diCounterStartDef
		MAX-ACCESS 		not-accessible
		STATUS 			current
		DESCRIPTION		"The counter table starting for di"
		::= { slot4-io 39 }

slot4-diCounterStart OBJECT-TYPE
		SYNTAX 			Slot4-diCounterStartDef
		MAX-ACCESS 		not-accessible
		STATUS 			current
		DESCRIPTION		"The counter starting of di item"
		INDEX { slot4-diCounterStartIndex }
		::= { slot4-diCounterStartTable 1 }

Slot4-diCounterStartDef ::= SEQUENCE { 
    	slot4-diCounterStartIndex		INTEGER,
		slot4-diCounterStartStatus		INTEGER		
		}  

slot4-diCounterStartIndex OBJECT-TYPE
		SYNTAX 			INTEGER (0..15)
		MAX-ACCESS 		read-only
		STATUS 			current
		DESCRIPTION		"The channel index for di counter start"
		::= { slot4-diCounterStart 1 }
		
slot4-diCounterStartStatus OBJECT-TYPE
		SYNTAX 			INTEGER (0..1)
		MAX-ACCESS 		read-write
		STATUS 			current
		DESCRIPTION		"The channel status for di counter start. 0=stop, 1=start"
		::= { slot4-diCounterStart 2 }  		
		
-- slot 4 DO
slot4-doTable OBJECT-TYPE
		SYNTAX 			SEQUENCE OF Slot4-doDef
		MAX-ACCESS 		not-accessible
		STATUS 			current
		DESCRIPTION		"The do channel table"
		::= { slot4-io 2 }

slot4-do OBJECT-TYPE
		SYNTAX 			Slot4-doDef
		MAX-ACCESS 		not-accessible
		STATUS 			current
		DESCRIPTION		"The do channel item"
		INDEX { slot4-doIndex }
		::= { slot4-doTable 1 }

Slot4-doDef ::= SEQUENCE { 
    		slot4-doIndex		INTEGER,
		slot4-doStatus		INTEGER		
		}  

slot4-doIndex OBJECT-TYPE
		SYNTAX 			INTEGER (0..15)
		MAX-ACCESS 		read-only
		STATUS 			current
		DESCRIPTION		"The channel index"
		::= { slot4-do 1 }
		
slot4-doStatus OBJECT-TYPE
		SYNTAX 			INTEGER (0..1)
		MAX-ACCESS 		read-write
		STATUS 			current
		DESCRIPTION		"The channel do status. 0=off, 1=on in do mode or 0=stop, 1=start in pulse mode"
		::= { slot4-do 2 }  

-- slot 4 DIO
slot4-dioTable OBJECT-TYPE
		SYNTAX 			SEQUENCE OF Slot4-dioDef
		MAX-ACCESS 		not-accessible
		STATUS 			current
		DESCRIPTION		"The dio channel table"
		::= { slot4-io 3 }

slot4-dio OBJECT-TYPE
		SYNTAX 			Slot4-dioDef
		MAX-ACCESS 		not-accessible
		STATUS 			current
		DESCRIPTION		"The dio channel item"
		INDEX { slot4-dioIndex }
		::= { slot4-dioTable 1 }

Slot4-dioDef ::= SEQUENCE { 
    	slot4-dioIndex		INTEGER,
		slot4-dioStatus		Unsigned32,
		slot4-dioCounterReset2Init INTEGER			
		}  

slot4-dioIndex OBJECT-TYPE
		SYNTAX 			INTEGER (0..15)
		MAX-ACCESS 		read-only
		STATUS 			current
		DESCRIPTION		"The channel index"
		::= { slot4-dio 1 }
		
slot4-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot4-dio 2 }  

slot4-dioCounterReset2Init OBJECT-TYPE
		SYNTAX 			INTEGER 
		MAX-ACCESS 		read-write
		STATUS 			current
		DESCRIPTION		"Trigger counter to initial value. 1=Reset counter to initial value"
		::= { slot4-dio 3 }		
		
-- slot 4 DIOCounterStart
slot4-dioCounterStartTable OBJECT-TYPE
		SYNTAX 			SEQUENCE OF Slot4-dioCounterStartDef
		MAX-ACCESS 		not-accessible
		STATUS 			current
		DESCRIPTION		"The counter table starting for dio"
		::= { slot4-io 46 }

slot4-dioCounterStart OBJECT-TYPE
		SYNTAX 			Slot4-dioCounterStartDef
		MAX-ACCESS 		not-accessible
		STATUS 			current
		DESCRIPTION		"The counter starting of dio item"
		INDEX { slot4-dioCounterStartIndex }
		::= { slot4-dioCounterStartTable 1 }

Slot4-dioCounterStartDef ::= SEQUENCE { 
    	slot4-dioCounterStartIndex		INTEGER,
		slot4-dioCounterStartStatus		INTEGER			
		}  

slot4-dioCounterStartIndex OBJECT-TYPE
		SYNTAX 			INTEGER (0..15)
		MAX-ACCESS 		read-only
		STATUS 			current
		DESCRIPTION		"The channel index for dio counter start"
		::= { slot4-dioCounterStart 1 }
		
slot4-dioCounterStartStatus OBJECT-TYPE
		SYNTAX 			INTEGER (0..1)
		MAX-ACCESS 		read-write
		STATUS 			current
		DESCRIPTION		"The channel status for dio counter start. 0=stop, 1=start"
		::= { slot4-dioCounterStart 2 } 	
		
-- slot 4 Relay
slot4-relayTable OBJECT-TYPE
		SYNTAX 			SEQUENCE OF Slot4-relayDef
		MAX-ACCESS 		not-accessible
		STATUS 			current
		DESCRIPTION		"The relay channel table"
		::= { slot4-io 4 }

slot4-relay OBJECT-TYPE
		SYNTAX 			Slot4-relayDef
		MAX-ACCESS 		not-accessible
		STATUS 			current
		DESCRIPTION		"The relay channel item"
		INDEX { slot4-relayIndex }
		::= { slot4-relayTable 1 }

Slot4-relayDef ::= SEQUENCE { 
    		slot4-relayIndex		INTEGER,
		slot4-relayStatus		INTEGER		
		}  

slot4-relayIndex OBJECT-TYPE
		SYNTAX 			INTEGER (0..15)
		MAX-ACCESS 		read-only
		STATUS 			current
		DESCRIPTION		"The channel index"
		::= { slot4-relay 1 }
		
slot4-relayStatus OBJECT-TYPE
		SYNTAX 			INTEGER (0..1)
		MAX-ACCESS 		read-write
		STATUS 			current
		DESCRIPTION		"The channel relay status. 0=off, 1=on in do mode or 0=stop, 1=start in pulse mode"
		::= { slot4-relay 2 }  

-- slot 4 AI
slot4-aiTable OBJECT-TYPE
		SYNTAX 			SEQUENCE OF Slot4-aiDef
		MAX-ACCESS 		not-accessible
		STATUS 			current
		DESCRIPTION		"The ai channel table"
		::= { slot4-io 5 }

slot4-ai OBJECT-TYPE
		SYNTAX 			Slot4-aiDef
		MAX-ACCESS 		not-accessible
		STATUS 			current
		DESCRIPTION		"The ai channel item"
		INDEX { slot4-aiIndex }
		::= { slot4-aiTable 1 }

Slot4-aiDef ::= SEQUENCE { 
    	slot4-aiIndex		INTEGER,
		slot4-aiStatus		OCTET STRING,
		slot4-aiBurnoutStatus INTEGER		
		}  

slot4-aiIndex OBJECT-TYPE
		SYNTAX 			INTEGER (0..15)
		MAX-ACCESS 		read-only
		STATUS 			current
		DESCRIPTION		"The channel index"
		::= { slot4-ai 1 }
		
slot4-aiStatus OBJECT-TYPE
		SYNTAX 			OCTET STRING
		MAX-ACCESS 		read-only
		STATUS 			current
		DESCRIPTION		"The channel ai scaled value"
		::= { slot4-ai 2 } 

slot4-aiBurnoutStatus OBJECT-TYPE
		SYNTAX 			INTEGER (0..3)
		MAX-ACCESS 		read-only
		STATUS 			current
		DESCRIPTION		"The channel of burnout status (0: normal, 1: burnout, 2: underange, 3: overange)"
		::= { slot4-ai 3 }  		

-- slot 4 AO
slot4-aoTable OBJECT-TYPE
		SYNTAX 			SEQUENCE OF Slot4-aoDef
		MAX-ACCESS 		not-accessible
		STATUS 			current
		DESCRIPTION		"The ao channel table"
		::= { slot4-io 6 }

slot4-ao OBJECT-TYPE
		SYNTAX 			Slot4-aoDef
		MAX-ACCESS 		not-accessible
		STATUS 			current
		DESCRIPTION		"The ao channel item"
		INDEX { slot4-aoIndex }
		::= { slot4-aoTable 1 }

Slot4-aoDef ::= SEQUENCE { 
    	slot4-aoIndex		INTEGER,
		slot4-aoStatus		OCTET STRING		
		}  

slot4-aoIndex OBJECT-TYPE
		SYNTAX 			INTEGER (0..15)
		MAX-ACCESS 		read-only
		STATUS 			current
		DESCRIPTION		"The channel index"
		::= { slot4-ao 1 }
		
slot4-aoStatus OBJECT-TYPE
		SYNTAX 			OCTET STRING
		MAX-ACCESS 		read-write
		STATUS 			current
		DESCRIPTION		"The channel ao scaled value"
		::= { slot4-ao 2 }  

-- slot 4 RTD
slot4-rtdTable OBJECT-TYPE
		SYNTAX 			SEQUENCE OF Slot4-rtdDef
		MAX-ACCESS 		not-accessible
		STATUS 			current
		DESCRIPTION		"The rtd channel table"
		::= { slot4-io 7 }

slot4-rtd OBJECT-TYPE
		SYNTAX 			Slot4-rtdDef
		MAX-ACCESS 		not-accessible
		STATUS 			current
		DESCRIPTION		"The rtd channel item"
		INDEX { slot4-rtdIndex }
		::= { slot4-rtdTable 1 }

Slot4-rtdDef ::= SEQUENCE { 
    	slot4-rtdIndex		INTEGER,
		slot4-rtdStatus		OCTET STRING		
		}  

slot4-rtdIndex OBJECT-TYPE
		SYNTAX 			INTEGER (0..15)
		MAX-ACCESS 		read-only
		STATUS 			current
		DESCRIPTION		"The channel index"
		::= { slot4-rtd 1 }
		
slot4-rtdStatus OBJECT-TYPE
		SYNTAX 			OCTET STRING
		MAX-ACCESS 		read-only
		STATUS 			current
		DESCRIPTION		"The channel rtd scaled value"
		::= { slot4-rtd 2 }  

-- slot 4 TC
slot4-tcTable OBJECT-TYPE
		SYNTAX 			SEQUENCE OF Slot4-tcDef
		MAX-ACCESS 		not-accessible
		STATUS 			current
		DESCRIPTION		"The tc channel table"
		::= { slot4-io 8 }

slot4-tc OBJECT-TYPE
		SYNTAX 			Slot4-tcDef
		MAX-ACCESS 		not-accessible
		STATUS 			current
		DESCRIPTION		"The tc channel item"
		INDEX { slot4-tcIndex }
		::= { slot4-tcTable 1 }

Slot4-tcDef ::= SEQUENCE { 
    	slot4-tcIndex		INTEGER,
		slot4-tcStatus		OCTET STRING		
		}  

slot4-tcIndex OBJECT-TYPE
		SYNTAX 			INTEGER (0..15)
		MAX-ACCESS 		read-only
		STATUS 			current
		DESCRIPTION		"The channel index"
		::= { slot4-tc 1 }
		
slot4-tcStatus OBJECT-TYPE
		SYNTAX 			OCTET STRING
		MAX-ACCESS 		read-only
		STATUS 			current
		DESCRIPTION		"The channel tc scaled value"
		::= { slot4-tc 2 }  

----------------------------------------------------------------
-- 1.3.6.1.4.1.8691.10.2500.51
    slot4-io-Trap OBJECT IDENTIFIER ::= { ioLogik2500 51 }
----------------------------------------------------------------

----------------------------------------------------------------
-- 1.3.6.1.4.1.8691.10.2500.51.1
    slot4-di-Trap OBJECT IDENTIFIER ::= { slot4-io-Trap 1 }
----------------------------------------------------------------

slot4Trap-di-00 NOTIFICATION-TYPE
    STATUS      current
    DESCRIPTION
        "SNMPTrap, di channel-00 in slot 4"
::= { slot4-di-Trap 1 }

slot4Trap-di-01 NOTIFICATION-TYPE
    STATUS      current
    DESCRIPTION
        "SNMPTrap, di channel-01 in slot 4"
::= { slot4-di-Trap 2 }

slot4Trap-di-02 NOTIFICATION-TYPE
    STATUS      current
    DESCRIPTION
        "SNMPTrap, di channel-02 in slot 4"
::= { slot4-di-Trap 3 }

slot4Trap-di-03 NOTIFICATION-TYPE
    STATUS      current
    DESCRIPTION
        "SNMPTrap, di channel-03 in slot 4"
::= { slot4-di-Trap 4 }

slot4Trap-di-04 NOTIFICATION-TYPE
    STATUS      current
    DESCRIPTION
        "SNMPTrap, di channel-04 in slot 4"
::= { slot4-di-Trap 5 }

slot4Trap-di-05 NOTIFICATION-TYPE
    STATUS      current
    DESCRIPTION
        "SNMPTrap, di channel-05 in slot 4"
::= { slot4-di-Trap 6 }

slot4Trap-di-06 NOTIFICATION-TYPE
    STATUS      current
    DESCRIPTION
        "SNMPTrap, di channel-06 in slot 4"
::= { slot4-di-Trap 7 }

slot4Trap-di-07 NOTIFICATION-TYPE
    STATUS      current
    DESCRIPTION
        "SNMPTrap, di channel-07 in slot 4"
::= { slot4-di-Trap 8 }

slot4Trap-di-08 NOTIFICATION-TYPE
    STATUS      current
    DESCRIPTION
        "SNMPTrap, di channel-08 in slot 4"
::= { slot4-di-Trap 9 }

slot4Trap-di-09 NOTIFICATION-TYPE
    STATUS      current
    DESCRIPTION
        "SNMPTrap, di channel-09 in slot 4"
::= { slot4-di-Trap 10 }

slot4Trap-di-10 NOTIFICATION-TYPE
    STATUS      current
    DESCRIPTION
        "SNMPTrap, di channel-10 in slot 4"
::= { slot4-di-Trap 11 }

slot4Trap-di-11 NOTIFICATION-TYPE
    STATUS      current
    DESCRIPTION
        "SNMPTrap, di channel-11 in slot 4"
::= { slot4-di-Trap 12 }

slot4Trap-di-12 NOTIFICATION-TYPE
    STATUS      current
    DESCRIPTION
        "SNMPTrap, di channel-12 in slot 4"
::= { slot4-di-Trap 13 }

slot4Trap-di-13 NOTIFICATION-TYPE
    STATUS      current
    DESCRIPTION
        "SNMPTrap, di channel-13 in slot 4"
::= { slot4-di-Trap 14 }

slot4Trap-di-14 NOTIFICATION-TYPE
    STATUS      current
    DESCRIPTION
        "SNMPTrap, di channel-14 in slot 4"
::= { slot4-di-Trap 15 }

slot4Trap-di-15 NOTIFICATION-TYPE
    STATUS      current
    DESCRIPTION
        "SNMPTrap, di channel-15 in slot 4"
::= { slot4-di-Trap 16 }
----------------------------------------------------------------
-- 1.3.6.1.4.1.8691.10.2500.51.2
    slot4-do-Trap OBJECT IDENTIFIER ::= { slot4-io-Trap 2 }
----------------------------------------------------------------

slot4Trap-do-00 NOTIFICATION-TYPE
    STATUS      current
    DESCRIPTION
        "SNMPTrap, do channel-00 in slot 4"
::= { slot4-do-Trap 1 }

slot4Trap-do-01 NOTIFICATION-TYPE
    STATUS      current
    DESCRIPTION
        "SNMPTrap, do channel-01 in slot 4"
::= { slot4-do-Trap 2 }

slot4Trap-do-02 NOTIFICATION-TYPE
    STATUS      current
    DESCRIPTION
        "SNMPTrap, do channel-02 in slot 4"
::= { slot4-do-Trap 3 }

slot4Trap-do-03 NOTIFICATION-TYPE
    STATUS      current
    DESCRIPTION
        "SNMPTrap, do channel-03 in slot 4"
::= { slot4-do-Trap 4 }

slot4Trap-do-04 NOTIFICATION-TYPE
    STATUS      current
    DESCRIPTION
        "SNMPTrap, do channel-04 in slot 4"
::= { slot4-do-Trap 5 }

slot4Trap-do-05 NOTIFICATION-TYPE
    STATUS      current
    DESCRIPTION
        "SNMPTrap, do channel-05 in slot 4"
::= { slot4-do-Trap 6 }

slot4Trap-do-06 NOTIFICATION-TYPE
    STATUS      current
    DESCRIPTION
        "SNMPTrap, do channel-06 in slot 4"
::= { slot4-do-Trap 7 }

slot4Trap-do-07 NOTIFICATION-TYPE
    STATUS      current
    DESCRIPTION
        "SNMPTrap, do channel-07 in slot 4"
::= { slot4-do-Trap 8 }

slot4Trap-do-08 NOTIFICATION-TYPE
    STATUS      current
    DESCRIPTION
        "SNMPTrap, do channel-08 in slot 4"
::= { slot4-do-Trap 9 }

slot4Trap-do-09 NOTIFICATION-TYPE
    STATUS      current
    DESCRIPTION
        "SNMPTrap, do channel-09 in slot 4"
::= { slot4-do-Trap 10 }

slot4Trap-do-10 NOTIFICATION-TYPE
    STATUS      current
    DESCRIPTION
        "SNMPTrap, do channel-10 in slot 4"
::= { slot4-do-Trap 11 }

slot4Trap-do-11 NOTIFICATION-TYPE
    STATUS      current
    DESCRIPTION
        "SNMPTrap, do channel-11 in slot 4"
::= { slot4-do-Trap 12 }

slot4Trap-do-12 NOTIFICATION-TYPE
    STATUS      current
    DESCRIPTION
        "SNMPTrap, do channel-12 in slot 4"
::= { slot4-do-Trap 13 }

slot4Trap-do-13 NOTIFICATION-TYPE
    STATUS      current
    DESCRIPTION
        "SNMPTrap, do channel-13 in slot 4"
::= { slot4-do-Trap 14 }

slot4Trap-do-14 NOTIFICATION-TYPE
    STATUS      current
    DESCRIPTION
        "SNMPTrap, do channel-14 in slot 4"
::= { slot4-do-Trap 15 }

slot4Trap-do-15 NOTIFICATION-TYPE
    STATUS      current
    DESCRIPTION
        "SNMPTrap, do channel-15 in slot 4"
::= { slot4-do-Trap 16 }

----------------------------------------------------------------
-- 1.3.6.1.4.1.8691.10.2500.51.3
    slot4-dio-Trap OBJECT IDENTIFIER ::= { slot4-io-Trap 3 }
----------------------------------------------------------------

slot4Trap-dio-00 NOTIFICATION-TYPE
    STATUS      current
    DESCRIPTION
        "SNMPTrap, dio channel-00 in slot 4"
::= { slot4-dio-Trap 1 }

slot4Trap-dio-01 NOTIFICATION-TYPE
    STATUS      current
    DESCRIPTION
        "SNMPTrap, dio channel-01 in slot 4"
::= { slot4-dio-Trap 2 }

slot4Trap-dio-02 NOTIFICATION-TYPE
    STATUS      current
    DESCRIPTION
        "SNMPTrap, dio channel-02 in slot 4"
::= { slot4-dio-Trap 3 }

slot4Trap-dio-03 NOTIFICATION-TYPE
    STATUS      current
    DESCRIPTION
        "SNMPTrap, dio channel-03 in slot 4"
::= { slot4-dio-Trap 4 }

slot4Trap-dio-04 NOTIFICATION-TYPE
    STATUS      current
    DESCRIPTION
        "SNMPTrap, dio channel-04 in slot 4"
::= { slot4-dio-Trap 5 }

slot4Trap-dio-05 NOTIFICATION-TYPE
    STATUS      current
    DESCRIPTION
        "SNMPTrap, dio channel-05 in slot 4"
::= { slot4-dio-Trap 6 }

slot4Trap-dio-06 NOTIFICATION-TYPE
    STATUS      current
    DESCRIPTION
        "SNMPTrap, dio channel-06 in slot 4"
::= { slot4-dio-Trap 7 }

slot4Trap-dio-07 NOTIFICATION-TYPE
    STATUS      current
    DESCRIPTION
        "SNMPTrap, dio channel-07 in slot 4"
::= { slot4-dio-Trap 8 }

slot4Trap-dio-08 NOTIFICATION-TYPE
    STATUS      current
    DESCRIPTION
        "SNMPTrap, dio channel-08 in slot 4"
::= { slot4-dio-Trap 9 }

slot4Trap-dio-09 NOTIFICATION-TYPE
    STATUS      current
    DESCRIPTION
        "SNMPTrap, dio channel-09 in slot 4"
::= { slot4-dio-Trap 10 }

slot4Trap-dio-10 NOTIFICATION-TYPE
    STATUS      current
    DESCRIPTION
        "SNMPTrap, dio channel-10 in slot 4"
::= { slot4-dio-Trap 11 }

slot4Trap-dio-11 NOTIFICATION-TYPE
    STATUS      current
    DESCRIPTION
        "SNMPTrap, dio channel-11 in slot 4"
::= { slot4-dio-Trap 12 }

slot4Trap-dio-12 NOTIFICATION-TYPE
    STATUS      current
    DESCRIPTION
        "SNMPTrap, dio channel-12 in slot 4"
::= { slot4-dio-Trap 13 }

slot4Trap-dio-13 NOTIFICATION-TYPE
    STATUS      current
    DESCRIPTION
        "SNMPTrap, dio channel-13 in slot 4"
::= { slot4-dio-Trap 14 }

slot4Trap-dio-14 NOTIFICATION-TYPE
    STATUS      current
    DESCRIPTION
        "SNMPTrap, dio channel-14 in slot 4"
::= { slot4-dio-Trap 15 }

slot4Trap-dio-15 NOTIFICATION-TYPE
    STATUS      current
    DESCRIPTION
        "SNMPTrap, dio channel-15 in slot 4"
::= { slot4-dio-Trap 16 }

----------------------------------------------------------------
-- 1.3.6.1.4.1.8691.10.2500.51.4
    slot4-relay-Trap OBJECT IDENTIFIER ::= { slot4-io-Trap 4 }
----------------------------------------------------------------

slot4Trap-relay-00 NOTIFICATION-TYPE
    STATUS      current
    DESCRIPTION
        "SNMPTrap, relay channel-00 in slot 4"
::= { slot4-relay-Trap 1 }

slot4Trap-relay-01 NOTIFICATION-TYPE
    STATUS      current
    DESCRIPTION
        "SNMPTrap, relay channel-01 in slot 4"
::= { slot4-relay-Trap 2 }

slot4Trap-relay-02 NOTIFICATION-TYPE
    STATUS      current
    DESCRIPTION
        "SNMPTrap, relay channel-02 in slot 4"
::= { slot4-relay-Trap 3 }

slot4Trap-relay-03 NOTIFICATION-TYPE
    STATUS      current
    DESCRIPTION
        "SNMPTrap, relay channel-03 in slot 4"
::= { slot4-relay-Trap 4 }

slot4Trap-relay-04 NOTIFICATION-TYPE
    STATUS      current
    DESCRIPTION
        "SNMPTrap, relay channel-04 in slot 4"
::= { slot4-relay-Trap 5 }

slot4Trap-relay-05 NOTIFICATION-TYPE
    STATUS      current
    DESCRIPTION
        "SNMPTrap, relay channel-05 in slot 4"
::= { slot4-relay-Trap 6 }

slot4Trap-relay-06 NOTIFICATION-TYPE
    STATUS      current
    DESCRIPTION
        "SNMPTrap, relay channel-06 in slot 4"
::= { slot4-relay-Trap 7 }

slot4Trap-relay-07 NOTIFICATION-TYPE
    STATUS      current
    DESCRIPTION
        "SNMPTrap, relay channel-07 in slot 4"
::= { slot4-relay-Trap 8 }

slot4Trap-relay-08 NOTIFICATION-TYPE
    STATUS      current
    DESCRIPTION
        "SNMPTrap, relay channel-08 in slot 4"
::= { slot4-relay-Trap 9 }

slot4Trap-relay-09 NOTIFICATION-TYPE
    STATUS      current
    DESCRIPTION
        "SNMPTrap, relay channel-09 in slot 4"
::= { slot4-relay-Trap 10 }

slot4Trap-relay-10 NOTIFICATION-TYPE
    STATUS      current
    DESCRIPTION
        "SNMPTrap, relay channel-10 in slot 4"
::= { slot4-relay-Trap 11 }

slot4Trap-relay-11 NOTIFICATION-TYPE
    STATUS      current
    DESCRIPTION
        "SNMPTrap, relay channel-11 in slot 4"
::= { slot4-relay-Trap 12 }

slot4Trap-relay-12 NOTIFICATION-TYPE
    STATUS      current
    DESCRIPTION
        "SNMPTrap, relay channel-12 in slot 4"
::= { slot4-relay-Trap 13 }

slot4Trap-relay-13 NOTIFICATION-TYPE
    STATUS      current
    DESCRIPTION
        "SNMPTrap, relay channel-13 in slot 4"
::= { slot4-relay-Trap 14 }

slot4Trap-relay-14 NOTIFICATION-TYPE
    STATUS      current
    DESCRIPTION
        "SNMPTrap, relay channel-14 in slot 4"
::= { slot4-relay-Trap 15 }

slot4Trap-relay-15 NOTIFICATION-TYPE
    STATUS      current
    DESCRIPTION
        "SNMPTrap, relay channel-15 in slot 4"
::= { slot4-relay-Trap 16 }

----------------------------------------------------------------
-- 1.3.6.1.4.1.8691.10.2500.51.5
    slot4-ai-Trap OBJECT IDENTIFIER ::= { slot4-io-Trap 5 }
----------------------------------------------------------------

slot4Trap-ai-00 NOTIFICATION-TYPE
    STATUS      current
    DESCRIPTION
        "SNMPTrap, ai channel-00 in slot 4"
::= { slot4-ai-Trap 1 }

slot4Trap-ai-01 NOTIFICATION-TYPE
    STATUS      current
    DESCRIPTION
        "SNMPTrap, ai channel-01 in slot 4"
::= { slot4-ai-Trap 2 }

slot4Trap-ai-02 NOTIFICATION-TYPE
    STATUS      current
    DESCRIPTION
        "SNMPTrap, ai channel-02 in slot 4"
::= { slot4-ai-Trap 3 }

slot4Trap-ai-03 NOTIFICATION-TYPE
    STATUS      current
    DESCRIPTION
        "SNMPTrap, ai channel-03 in slot 4"
::= { slot4-ai-Trap 4 }

slot4Trap-ai-04 NOTIFICATION-TYPE
    STATUS      current
    DESCRIPTION
        "SNMPTrap, ai channel-04 in slot 4"
::= { slot4-ai-Trap 5 }

slot4Trap-ai-05 NOTIFICATION-TYPE
    STATUS      current
    DESCRIPTION
        "SNMPTrap, ai channel-05 in slot 4"
::= { slot4-ai-Trap 6 }

slot4Trap-ai-06 NOTIFICATION-TYPE
    STATUS      current
    DESCRIPTION
        "SNMPTrap, ai channel-06 in slot 4"
::= { slot4-ai-Trap 7 }

slot4Trap-ai-07 NOTIFICATION-TYPE
    STATUS      current
    DESCRIPTION
        "SNMPTrap, ai channel-07 in slot 4"
::= { slot4-ai-Trap 8 }

slot4Trap-ai-08 NOTIFICATION-TYPE
    STATUS      current
    DESCRIPTION
        "SNMPTrap, ai channel-08 in slot 4"
::= { slot4-ai-Trap 9 }

slot4Trap-ai-09 NOTIFICATION-TYPE
    STATUS      current
    DESCRIPTION
        "SNMPTrap, ai channel-09 in slot 4"
::= { slot4-ai-Trap 10 }

slot4Trap-ai-10 NOTIFICATION-TYPE
    STATUS      current
    DESCRIPTION
        "SNMPTrap, ai channel-10 in slot 4"
::= { slot4-ai-Trap 11 }

slot4Trap-ai-11 NOTIFICATION-TYPE
    STATUS      current
    DESCRIPTION
        "SNMPTrap, ai channel-11 in slot 4"
::= { slot4-ai-Trap 12 }

slot4Trap-ai-12 NOTIFICATION-TYPE
    STATUS      current
    DESCRIPTION
        "SNMPTrap, ai channel-12 in slot 4"
::= { slot4-ai-Trap 13 }

slot4Trap-ai-13 NOTIFICATION-TYPE
    STATUS      current
    DESCRIPTION
        "SNMPTrap, ai channel-13 in slot 4"
::= { slot4-ai-Trap 14 }

slot4Trap-ai-14 NOTIFICATION-TYPE
    STATUS      current
    DESCRIPTION
        "SNMPTrap, ai channel-14 in slot 4"
::= { slot4-ai-Trap 15 }

slot4Trap-ai-15 NOTIFICATION-TYPE
    STATUS      current
    DESCRIPTION
        "SNMPTrap, ai channel-15 in slot 4"
::= { slot4-ai-Trap 16 }

----------------------------------------------------------------
-- 1.3.6.1.4.1.8691.10.2500.51.6
    slot4-ao-Trap OBJECT IDENTIFIER ::= { slot4-io-Trap 6 }
----------------------------------------------------------------

slot4Trap-ao-00 NOTIFICATION-TYPE
    STATUS      current
    DESCRIPTION
        "SNMPTrap, ao channel-00 in slot 4"
::= { slot4-ao-Trap 1 }

slot4Trap-ao-01 NOTIFICATION-TYPE
    STATUS      current
    DESCRIPTION
        "SNMPTrap, ao channel-01 in slot 4"
::= { slot4-ao-Trap 2 }

slot4Trap-ao-02 NOTIFICATION-TYPE
    STATUS      current
    DESCRIPTION
        "SNMPTrap, ao channel-02 in slot 4"
::= { slot4-ao-Trap 3 }

slot4Trap-ao-03 NOTIFICATION-TYPE
    STATUS      current
    DESCRIPTION
        "SNMPTrap, ao channel-03 in slot 4"
::= { slot4-ao-Trap 4 }

slot4Trap-ao-04 NOTIFICATION-TYPE
    STATUS      current
    DESCRIPTION
        "SNMPTrap, ao channel-04 in slot 4"
::= { slot4-ao-Trap 5 }

slot4Trap-ao-05 NOTIFICATION-TYPE
    STATUS      current
    DESCRIPTION
        "SNMPTrap, ao channel-05 in slot 4"
::= { slot4-ao-Trap 6 }

slot4Trap-ao-06 NOTIFICATION-TYPE
    STATUS      current
    DESCRIPTION
        "SNMPTrap, ao channel-06 in slot 4"
::= { slot4-ao-Trap 7 }

slot4Trap-ao-07 NOTIFICATION-TYPE
    STATUS      current
    DESCRIPTION
        "SNMPTrap, ao channel-07 in slot 4"
::= { slot4-ao-Trap 8 }

slot4Trap-ao-08 NOTIFICATION-TYPE
    STATUS      current
    DESCRIPTION
        "SNMPTrap, ao channel-08 in slot 4"
::= { slot4-ao-Trap 9 }

slot4Trap-ao-09 NOTIFICATION-TYPE
    STATUS      current
    DESCRIPTION
        "SNMPTrap, ao channel-09 in slot 4"
::= { slot4-ao-Trap 10 }

slot4Trap-ao-10 NOTIFICATION-TYPE
    STATUS      current
    DESCRIPTION
        "SNMPTrap, ao channel-10 in slot 4"
::= { slot4-ao-Trap 11 }

slot4Trap-ao-11 NOTIFICATION-TYPE
    STATUS      current
    DESCRIPTION
        "SNMPTrap, ao channel-11 in slot 4"
::= { slot4-ao-Trap 12 }

slot4Trap-ao-12 NOTIFICATION-TYPE
    STATUS      current
    DESCRIPTION
        "SNMPTrap, ao channel-12 in slot 4"
::= { slot4-ao-Trap 13 }

slot4Trap-ao-13 NOTIFICATION-TYPE
    STATUS      current
    DESCRIPTION
        "SNMPTrap, ao channel-13 in slot 4"
::= { slot4-ao-Trap 14 }

slot4Trap-ao-14 NOTIFICATION-TYPE
    STATUS      current
    DESCRIPTION
        "SNMPTrap, ao channel-14 in slot 4"
::= { slot4-ao-Trap 15 }

slot4Trap-ao-15 NOTIFICATION-TYPE
    STATUS      current
    DESCRIPTION
        "SNMPTrap, ao channel-15 in slot 4"
::= { slot4-ao-Trap 16 }

----------------------------------------------------------------
-- 1.3.6.1.4.1.8691.10.2500.51.7
    slot4-rtd-Trap OBJECT IDENTIFIER ::= { slot4-io-Trap 7 }
----------------------------------------------------------------

slot4Trap-rtd-00 NOTIFICATION-TYPE
    STATUS      current
    DESCRIPTION
        "SNMPTrap, rtd channel-00 in slot 4"
::= { slot4-rtd-Trap 1 }

slot4Trap-rtd-01 NOTIFICATION-TYPE
    STATUS      current
    DESCRIPTION
        "SNMPTrap, rtd channel-01 in slot 4"
::= { slot4-rtd-Trap 2 }

slot4Trap-rtd-02 NOTIFICATION-TYPE
    STATUS      current
    DESCRIPTION
        "SNMPTrap, rtd channel-02 in slot 4"
::= { slot4-rtd-Trap 3 }

slot4Trap-rtd-03 NOTIFICATION-TYPE
    STATUS      current
    DESCRIPTION
        "SNMPTrap, rtd channel-03 in slot 4"
::= { slot4-rtd-Trap 4 }

slot4Trap-rtd-04 NOTIFICATION-TYPE
    STATUS      current
    DESCRIPTION
        "SNMPTrap, rtd channel-04 in slot 4"
::= { slot4-rtd-Trap 5 }

slot4Trap-rtd-05 NOTIFICATION-TYPE
    STATUS      current
    DESCRIPTION
        "SNMPTrap, rtd channel-05 in slot 4"
::= { slot4-rtd-Trap 6 }

slot4Trap-rtd-06 NOTIFICATION-TYPE
    STATUS      current
    DESCRIPTION
        "SNMPTrap, rtd channel-06 in slot 4"
::= { slot4-rtd-Trap 7 }

slot4Trap-rtd-07 NOTIFICATION-TYPE
    STATUS      current
    DESCRIPTION
        "SNMPTrap, rtd channel-07 in slot 4"
::= { slot4-rtd-Trap 8 }

slot4Trap-rtd-08 NOTIFICATION-TYPE
    STATUS      current
    DESCRIPTION
        "SNMPTrap, rtd channel-08 in slot 4"
::= { slot4-rtd-Trap 9 }

slot4Trap-rtd-09 NOTIFICATION-TYPE
    STATUS      current
    DESCRIPTION
        "SNMPTrap, rtd channel-09 in slot 4"
::= { slot4-rtd-Trap 10 }

slot4Trap-rtd-10 NOTIFICATION-TYPE
    STATUS      current
    DESCRIPTION
        "SNMPTrap, rtd channel-10 in slot 4"
::= { slot4-rtd-Trap 11 }

slot4Trap-rtd-11 NOTIFICATION-TYPE
    STATUS      current
    DESCRIPTION
        "SNMPTrap, rtd channel-11 in slot 4"
::= { slot4-rtd-Trap 12 }

slot4Trap-rtd-12 NOTIFICATION-TYPE
    STATUS      current
    DESCRIPTION
        "SNMPTrap, rtd channel-12 in slot 4"
::= { slot4-rtd-Trap 13 }

slot4Trap-rtd-13 NOTIFICATION-TYPE
    STATUS      current
    DESCRIPTION
        "SNMPTrap, rtd channel-13 in slot 4"
::= { slot4-rtd-Trap 14 }

slot4Trap-rtd-14 NOTIFICATION-TYPE
    STATUS      current
    DESCRIPTION
        "SNMPTrap, rtd channel-14 in slot 4"
::= { slot4-rtd-Trap 15 }

slot4Trap-rtd-15 NOTIFICATION-TYPE
    STATUS      current
    DESCRIPTION
        "SNMPTrap, rtd channel-15 in slot 4"
::= { slot4-rtd-Trap 16 }

----------------------------------------------------------------
-- 1.3.6.1.4.1.8691.10.2500.51.8
    slot4-tc-Trap OBJECT IDENTIFIER ::= { slot4-io-Trap 8 }
----------------------------------------------------------------

slot4Trap-tc-00 NOTIFICATION-TYPE
    STATUS      current
    DESCRIPTION
        "SNMPTrap, tc channel-00 in slot 4"
::= { slot4-tc-Trap 1 }

slot4Trap-tc-01 NOTIFICATION-TYPE
    STATUS      current
    DESCRIPTION
        "SNMPTrap, tc channel-01 in slot 4"
::= { slot4-tc-Trap 2 }

slot4Trap-tc-02 NOTIFICATION-TYPE
    STATUS      current
    DESCRIPTION
        "SNMPTrap, tc channel-02 in slot 4"
::= { slot4-tc-Trap 3 }

slot4Trap-tc-03 NOTIFICATION-TYPE
    STATUS      current
    DESCRIPTION
        "SNMPTrap, tc channel-03 in slot 4"
::= { slot4-tc-Trap 4 }

slot4Trap-tc-04 NOTIFICATION-TYPE
    STATUS      current
    DESCRIPTION
        "SNMPTrap, tc channel-04 in slot 4"
::= { slot4-tc-Trap 5 }

slot4Trap-tc-05 NOTIFICATION-TYPE
    STATUS      current
    DESCRIPTION
        "SNMPTrap, tc channel-05 in slot 4"
::= { slot4-tc-Trap 6 }

slot4Trap-tc-06 NOTIFICATION-TYPE
    STATUS      current
    DESCRIPTION
        "SNMPTrap, tc channel-06 in slot 4"
::= { slot4-tc-Trap 7 }

slot4Trap-tc-07 NOTIFICATION-TYPE
    STATUS      current
    DESCRIPTION
        "SNMPTrap, tc channel-07 in slot 4"
::= { slot4-tc-Trap 8 }

slot4Trap-tc-08 NOTIFICATION-TYPE
    STATUS      current
    DESCRIPTION
        "SNMPTrap, tc channel-08 in slot 4"
::= { slot4-tc-Trap 9 }

slot4Trap-tc-09 NOTIFICATION-TYPE
    STATUS      current
    DESCRIPTION
        "SNMPTrap, tc channel-09 in slot 4"
::= { slot4-tc-Trap 10 }

slot4Trap-tc-10 NOTIFICATION-TYPE
    STATUS      current
    DESCRIPTION
        "SNMPTrap, tc channel-10 in slot 4"
::= { slot4-tc-Trap 11 }

slot4Trap-tc-11 NOTIFICATION-TYPE
    STATUS      current
    DESCRIPTION
        "SNMPTrap, tc channel-11 in slot 4"
::= { slot4-tc-Trap 12 }

slot4Trap-tc-12 NOTIFICATION-TYPE
    STATUS      current
    DESCRIPTION
        "SNMPTrap, tc channel-12 in slot 4"
::= { slot4-tc-Trap 13 }

slot4Trap-tc-13 NOTIFICATION-TYPE
    STATUS      current
    DESCRIPTION
        "SNMPTrap, tc channel-13 in slot 4"
::= { slot4-tc-Trap 14 }

slot4Trap-tc-14 NOTIFICATION-TYPE
    STATUS      current
    DESCRIPTION
        "SNMPTrap, tc channel-14 in slot 4"
::= { slot4-tc-Trap 15 }

slot4Trap-tc-15 NOTIFICATION-TYPE
    STATUS      current
    DESCRIPTION
        "SNMPTrap, tc channel-15 in slot 4"
::= { slot4-tc-Trap 16 }				
		
----------------------------------------------------------------
-- 1.3.6.1.4.1.8691.10.2500.60
    slot5-io OBJECT IDENTIFIER ::= { ioLogik2500 60 }
----------------------------------------------------------------
-- slot 5 DI
slot5-diTable OBJECT-TYPE
		SYNTAX 			SEQUENCE OF Slot5-diDef
		MAX-ACCESS 		not-accessible
		STATUS 			current
		DESCRIPTION		"The di channel table"
		::= { slot5-io 1 }

slot5-di OBJECT-TYPE
		SYNTAX 			Slot5-diDef
		MAX-ACCESS 		not-accessible
		STATUS 			current
		DESCRIPTION		"The di channel item"
		INDEX { slot5-diIndex }
		::= { slot5-diTable 1 }

Slot5-diDef ::= SEQUENCE { 
    	slot5-diIndex		INTEGER,
		slot5-diStatus	Unsigned32,
		slot5-diCounterReset2Init INTEGER		
		}  

slot5-diIndex OBJECT-TYPE
		SYNTAX 			INTEGER (0..15)
		MAX-ACCESS 		read-only
		STATUS 			current
		DESCRIPTION		"The channel index"
		::= { slot5-di 1 }
		
slot5-diStatus OBJECT-TYPE
		SYNTAX 			Unsigned32
		MAX-ACCESS 		read-write
		STATUS 			current
		DESCRIPTION		"The channel di status. 0=off, 1=on in di mode or n=counter value in counter mode"
		::= { slot5-di 2 }

slot5-diCounterReset2Init OBJECT-TYPE
		SYNTAX 			INTEGER 
		MAX-ACCESS 		read-write
		STATUS 			current
		DESCRIPTION		"Trigger counter to initial value. 1=Reset counter to initial value"
		::= { slot5-di 3 }
		
-- slot 5 DICounterStart
slot5-diCounterStartTable OBJECT-TYPE
		SYNTAX 			SEQUENCE OF Slot5-diCounterStartDef
		MAX-ACCESS 		not-accessible
		STATUS 			current
		DESCRIPTION		"The counter table starting for di"
		::= { slot5-io 39 }

slot5-diCounterStart OBJECT-TYPE
		SYNTAX 			Slot5-diCounterStartDef
		MAX-ACCESS 		not-accessible
		STATUS 			current
		DESCRIPTION		"The counter starting of di item"
		INDEX { slot5-diCounterStartIndex }
		::= { slot5-diCounterStartTable 1 }

Slot5-diCounterStartDef ::= SEQUENCE { 
    	slot5-diCounterStartIndex		INTEGER,
		slot5-diCounterStartStatus		INTEGER		
		}  

slot5-diCounterStartIndex OBJECT-TYPE
		SYNTAX 			INTEGER (0..15)
		MAX-ACCESS 		read-only
		STATUS 			current
		DESCRIPTION		"The channel index for di counter start"
		::= { slot5-diCounterStart 1 }
		
slot5-diCounterStartStatus OBJECT-TYPE
		SYNTAX 			INTEGER (0..1)
		MAX-ACCESS 		read-write
		STATUS 			current
		DESCRIPTION		"The channel status for di counter start. 0=stop, 1=start"
		::= { slot5-diCounterStart 2 }	
		
						
-- slot 5 DO
slot5-doTable OBJECT-TYPE
		SYNTAX 			SEQUENCE OF Slot5-doDef
		MAX-ACCESS 		not-accessible
		STATUS 			current
		DESCRIPTION		"The do channel table"
		::= { slot5-io 2 }

slot5-do OBJECT-TYPE
		SYNTAX 			Slot5-doDef
		MAX-ACCESS 		not-accessible
		STATUS 			current
		DESCRIPTION		"The do channel item"
		INDEX { slot5-doIndex }
		::= { slot5-doTable 1 }

Slot5-doDef ::= SEQUENCE { 
    	slot5-doIndex		INTEGER,
		slot5-doStatus		INTEGER		
		}  

slot5-doIndex OBJECT-TYPE
		SYNTAX 			INTEGER (0..15)
		MAX-ACCESS 		read-only
		STATUS 			current
		DESCRIPTION		"The channel index"
		::= { slot5-do 1 }
		
slot5-doStatus OBJECT-TYPE
		SYNTAX 			INTEGER (0..1)
		MAX-ACCESS 		read-write
		STATUS 			current
		DESCRIPTION		"The channel do status. 0=off, 1=on in do mode or 0=stop, 1=start in pulse mode"
		::= { slot5-do 2 }  

-- slot 5 DIO
slot5-dioTable OBJECT-TYPE
		SYNTAX 			SEQUENCE OF Slot5-dioDef
		MAX-ACCESS 		not-accessible
		STATUS 			current
		DESCRIPTION		"The dio channel table"
		::= { slot5-io 3 }

slot5-dio OBJECT-TYPE
		SYNTAX 			Slot5-dioDef
		MAX-ACCESS 		not-accessible
		STATUS 			current
		DESCRIPTION		"The dio channel item"
		INDEX { slot5-dioIndex }
		::= { slot5-dioTable 1 }

Slot5-dioDef ::= SEQUENCE { 
    	slot5-dioIndex		INTEGER,
		slot5-dioStatus		Unsigned32,
		slot5-dioCounterReset2Init INTEGER				
		}  

slot5-dioIndex OBJECT-TYPE
		SYNTAX 			INTEGER (0..15)
		MAX-ACCESS 		read-only
		STATUS 			current
		DESCRIPTION		"The channel index"
		::= { slot5-dio 1 }
		
slot5-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot5-dio 2 }  

slot5-dioCounterReset2Init OBJECT-TYPE
		SYNTAX 			INTEGER 
		MAX-ACCESS 		read-write
		STATUS 			current
		DESCRIPTION		"Trigger counter to initial value. 1=Reset counter to initial value"
		::= { slot5-dio 3 }			
		
-- slot 5 DIOCounterStart
slot5-dioCounterStartTable OBJECT-TYPE
		SYNTAX 			SEQUENCE OF Slot5-dioCounterStartDef
		MAX-ACCESS 		not-accessible
		STATUS 			current
		DESCRIPTION		"The counter table starting for dio"
		::= { slot5-io 46 }

slot5-dioCounterStart OBJECT-TYPE
		SYNTAX 			Slot5-dioCounterStartDef
		MAX-ACCESS 		not-accessible
		STATUS 			current
		DESCRIPTION		"The counter starting of dio item"
		INDEX { slot5-dioCounterStartIndex }
		::= { slot5-dioCounterStartTable 1 }

Slot5-dioCounterStartDef ::= SEQUENCE { 
    		slot5-dioCounterStartIndex		INTEGER,
			slot5-dioCounterStartStatus		INTEGER			
		}  

slot5-dioCounterStartIndex OBJECT-TYPE
		SYNTAX 			INTEGER (0..15)
		MAX-ACCESS 		read-only
		STATUS 			current
		DESCRIPTION		"The channel index for dio counter start"
		::= { slot5-dioCounterStart 1 }
		
slot5-dioCounterStartStatus OBJECT-TYPE
		SYNTAX 			INTEGER (0..1)
		MAX-ACCESS 		read-write
		STATUS 			current
		DESCRIPTION		"The channel status for dio counter start. 0=stop, 1=start"
		::= { slot5-dioCounterStart 2 }
		
-- slot 5 Relay
slot5-relayTable OBJECT-TYPE
		SYNTAX 			SEQUENCE OF Slot5-relayDef
		MAX-ACCESS 		not-accessible
		STATUS 			current
		DESCRIPTION		"The relay channel table"
		::= { slot5-io 4 }

slot5-relay OBJECT-TYPE
		SYNTAX 			Slot5-relayDef
		MAX-ACCESS 		not-accessible
		STATUS 			current
		DESCRIPTION		"The relay channel item"
		INDEX { slot5-relayIndex }
		::= { slot5-relayTable 1 }

Slot5-relayDef ::= SEQUENCE { 
    	slot5-relayIndex		INTEGER,
		slot5-relayStatus		INTEGER		
		}  

slot5-relayIndex OBJECT-TYPE
		SYNTAX 			INTEGER (0..15)
		MAX-ACCESS 		read-only
		STATUS 			current
		DESCRIPTION		"The channel index"
		::= { slot5-relay 1 }
		
slot5-relayStatus OBJECT-TYPE
		SYNTAX 			INTEGER (0..1)
		MAX-ACCESS 		read-write
		STATUS 			current
		DESCRIPTION		"The channel relay status. 0=off, 1=on in do mode or 0=stop, 1=start in pulse mode"
		::= { slot5-relay 2 }  

-- slot 5 AI
slot5-aiTable OBJECT-TYPE
		SYNTAX 			SEQUENCE OF Slot5-aiDef
		MAX-ACCESS 		not-accessible
		STATUS 			current
		DESCRIPTION		"The ai channel table"
		::= { slot5-io 5 }

slot5-ai OBJECT-TYPE
		SYNTAX 			Slot5-aiDef
		MAX-ACCESS 		not-accessible
		STATUS 			current
		DESCRIPTION		"The ai channel item"
		INDEX { slot5-aiIndex }
		::= { slot5-aiTable 1 }

Slot5-aiDef ::= SEQUENCE { 
    	slot5-aiIndex		INTEGER,
		slot5-aiStatus		OCTET STRING,
		slot5-aiBurnoutStatus INTEGER		
		}  

slot5-aiIndex OBJECT-TYPE
		SYNTAX 			INTEGER (0..15)
		MAX-ACCESS 		read-only
		STATUS 			current
		DESCRIPTION		"The channel index"
		::= { slot5-ai 1 }
		
slot5-aiStatus OBJECT-TYPE
		SYNTAX 			OCTET STRING
		MAX-ACCESS 		read-only
		STATUS 			current
		DESCRIPTION		"The channel ai scaled value"
		::= { slot5-ai 2 }

slot5-aiBurnoutStatus OBJECT-TYPE
		SYNTAX 			INTEGER (0..3)
		MAX-ACCESS 		read-only
		STATUS 			current
		DESCRIPTION		"The channel of burnout status (0: normal, 1: burnout, 2: underange, 3: overange)"
		::= { slot5-ai 3 }  		

-- slot 5 AO
slot5-aoTable OBJECT-TYPE
		SYNTAX 			SEQUENCE OF Slot5-aoDef
		MAX-ACCESS 		not-accessible
		STATUS 			current
		DESCRIPTION		"The ao channel table"
		::= { slot5-io 6 }

slot5-ao OBJECT-TYPE
		SYNTAX 			Slot5-aoDef
		MAX-ACCESS 		not-accessible
		STATUS 			current
		DESCRIPTION		"The ao channel item"
		INDEX { slot5-aoIndex }
		::= { slot5-aoTable 1 }

Slot5-aoDef ::= SEQUENCE { 
    	slot5-aoIndex		INTEGER,
		slot5-aoStatus		OCTET STRING		
		}  

slot5-aoIndex OBJECT-TYPE
		SYNTAX 			INTEGER (0..15)
		MAX-ACCESS 		read-only
		STATUS 			current
		DESCRIPTION		"The channel index"
		::= { slot5-ao 1 }
		
slot5-aoStatus OBJECT-TYPE
		SYNTAX 			OCTET STRING
		MAX-ACCESS 		read-write
		STATUS 			current
		DESCRIPTION		"The channel ao scaled value"
		::= { slot5-ao 2 }  

-- slot 5 RTD
slot5-rtdTable OBJECT-TYPE
		SYNTAX 			SEQUENCE OF Slot5-rtdDef
		MAX-ACCESS 		not-accessible
		STATUS 			current
		DESCRIPTION		"The rtd channel table"
		::= { slot5-io 7 }

slot5-rtd OBJECT-TYPE
		SYNTAX 			Slot5-rtdDef
		MAX-ACCESS 		not-accessible
		STATUS 			current
		DESCRIPTION		"The rtd channel item"
		INDEX { slot5-rtdIndex }
		::= { slot5-rtdTable 1 }

Slot5-rtdDef ::= SEQUENCE { 
    	slot5-rtdIndex		INTEGER,
		slot5-rtdStatus		OCTET STRING		
		}  

slot5-rtdIndex OBJECT-TYPE
		SYNTAX 			INTEGER (0..15)
		MAX-ACCESS 		read-only
		STATUS 			current
		DESCRIPTION		"The channel index"
		::= { slot5-rtd 1 }
		
slot5-rtdStatus OBJECT-TYPE
		SYNTAX 			OCTET STRING
		MAX-ACCESS 		read-only
		STATUS 			current
		DESCRIPTION		"The channel rtd scaled value"
		::= { slot5-rtd 2 }  

-- slot 5 TC
slot5-tcTable OBJECT-TYPE
		SYNTAX 			SEQUENCE OF Slot5-tcDef
		MAX-ACCESS 		not-accessible
		STATUS 			current
		DESCRIPTION		"The tc channel table"
		::= { slot5-io 8 }

slot5-tc OBJECT-TYPE
		SYNTAX 			Slot5-tcDef
		MAX-ACCESS 		not-accessible
		STATUS 			current
		DESCRIPTION		"The tc channel item"
		INDEX { slot5-tcIndex }
		::= { slot5-tcTable 1 }

Slot5-tcDef ::= SEQUENCE { 
    	slot5-tcIndex		INTEGER,
		slot5-tcStatus		OCTET STRING		
		}  

slot5-tcIndex OBJECT-TYPE
		SYNTAX 			INTEGER (0..15)
		MAX-ACCESS 		read-only
		STATUS 			current
		DESCRIPTION		"The channel index"
		::= { slot5-tc 1 }
		
slot5-tcStatus OBJECT-TYPE
		SYNTAX 			OCTET STRING
		MAX-ACCESS 		read-only
		STATUS 			current
		DESCRIPTION		"The channel tc scaled value"
		::= { slot5-tc 2 }  

----------------------------------------------------------------
-- 1.3.6.1.4.1.8691.10.2500.61
    slot5-io-Trap OBJECT IDENTIFIER ::= { ioLogik2500 61 }
----------------------------------------------------------------

----------------------------------------------------------------
-- 1.3.6.1.4.1.8691.10.2500.61.1
    slot5-di-Trap OBJECT IDENTIFIER ::= { slot5-io-Trap 1 }
----------------------------------------------------------------

slot5Trap-di-00 NOTIFICATION-TYPE
    STATUS      current
    DESCRIPTION
        "SNMPTrap, di channel-00 in slot 5"
::= { slot5-di-Trap 1 }

slot5Trap-di-01 NOTIFICATION-TYPE
    STATUS      current
    DESCRIPTION
        "SNMPTrap, di channel-01 in slot 5"
::= { slot5-di-Trap 2 }

slot5Trap-di-02 NOTIFICATION-TYPE
    STATUS      current
    DESCRIPTION
        "SNMPTrap, di channel-02 in slot 5"
::= { slot5-di-Trap 3 }

slot5Trap-di-03 NOTIFICATION-TYPE
    STATUS      current
    DESCRIPTION
        "SNMPTrap, di channel-03 in slot 5"
::= { slot5-di-Trap 4 }

slot5Trap-di-04 NOTIFICATION-TYPE
    STATUS      current
    DESCRIPTION
        "SNMPTrap, di channel-04 in slot 5"
::= { slot5-di-Trap 5 }

slot5Trap-di-05 NOTIFICATION-TYPE
    STATUS      current
    DESCRIPTION
        "SNMPTrap, di channel-05 in slot 5"
::= { slot5-di-Trap 6 }

slot5Trap-di-06 NOTIFICATION-TYPE
    STATUS      current
    DESCRIPTION
        "SNMPTrap, di channel-06 in slot 5"
::= { slot5-di-Trap 7 }

slot5Trap-di-07 NOTIFICATION-TYPE
    STATUS      current
    DESCRIPTION
        "SNMPTrap, di channel-07 in slot 5"
::= { slot5-di-Trap 8 }

slot5Trap-di-08 NOTIFICATION-TYPE
    STATUS      current
    DESCRIPTION
        "SNMPTrap, di channel-08 in slot 5"
::= { slot5-di-Trap 9 }

slot5Trap-di-09 NOTIFICATION-TYPE
    STATUS      current
    DESCRIPTION
        "SNMPTrap, di channel-09 in slot 5"
::= { slot5-di-Trap 10 }

slot5Trap-di-10 NOTIFICATION-TYPE
    STATUS      current
    DESCRIPTION
        "SNMPTrap, di channel-10 in slot 5"
::= { slot5-di-Trap 11 }

slot5Trap-di-11 NOTIFICATION-TYPE
    STATUS      current
    DESCRIPTION
        "SNMPTrap, di channel-11 in slot 5"
::= { slot5-di-Trap 12 }

slot5Trap-di-12 NOTIFICATION-TYPE
    STATUS      current
    DESCRIPTION
        "SNMPTrap, di channel-12 in slot 5"
::= { slot5-di-Trap 13 }

slot5Trap-di-13 NOTIFICATION-TYPE
    STATUS      current
    DESCRIPTION
        "SNMPTrap, di channel-13 in slot 5"
::= { slot5-di-Trap 14 }

slot5Trap-di-14 NOTIFICATION-TYPE
    STATUS      current
    DESCRIPTION
        "SNMPTrap, di channel-14 in slot 5"
::= { slot5-di-Trap 15 }

slot5Trap-di-15 NOTIFICATION-TYPE
    STATUS      current
    DESCRIPTION
        "SNMPTrap, di channel-15 in slot 5"
::= { slot5-di-Trap 16 }
----------------------------------------------------------------
-- 1.3.6.1.4.1.8691.10.2500.61.2
    slot5-do-Trap OBJECT IDENTIFIER ::= { slot5-io-Trap 2 }
----------------------------------------------------------------

slot5Trap-do-00 NOTIFICATION-TYPE
    STATUS      current
    DESCRIPTION
        "SNMPTrap, do channel-00 in slot 5"
::= { slot5-do-Trap 1 }

slot5Trap-do-01 NOTIFICATION-TYPE
    STATUS      current
    DESCRIPTION
        "SNMPTrap, do channel-01 in slot 5"
::= { slot5-do-Trap 2 }

slot5Trap-do-02 NOTIFICATION-TYPE
    STATUS      current
    DESCRIPTION
        "SNMPTrap, do channel-02 in slot 5"
::= { slot5-do-Trap 3 }

slot5Trap-do-03 NOTIFICATION-TYPE
    STATUS      current
    DESCRIPTION
        "SNMPTrap, do channel-03 in slot 5"
::= { slot5-do-Trap 4 }

slot5Trap-do-04 NOTIFICATION-TYPE
    STATUS      current
    DESCRIPTION
        "SNMPTrap, do channel-04 in slot 5"
::= { slot5-do-Trap 5 }

slot5Trap-do-05 NOTIFICATION-TYPE
    STATUS      current
    DESCRIPTION
        "SNMPTrap, do channel-05 in slot 5"
::= { slot5-do-Trap 6 }

slot5Trap-do-06 NOTIFICATION-TYPE
    STATUS      current
    DESCRIPTION
        "SNMPTrap, do channel-06 in slot 5"
::= { slot5-do-Trap 7 }

slot5Trap-do-07 NOTIFICATION-TYPE
    STATUS      current
    DESCRIPTION
        "SNMPTrap, do channel-07 in slot 5"
::= { slot5-do-Trap 8 }

slot5Trap-do-08 NOTIFICATION-TYPE
    STATUS      current
    DESCRIPTION
        "SNMPTrap, do channel-08 in slot 5"
::= { slot5-do-Trap 9 }

slot5Trap-do-09 NOTIFICATION-TYPE
    STATUS      current
    DESCRIPTION
        "SNMPTrap, do channel-09 in slot 5"
::= { slot5-do-Trap 10 }

slot5Trap-do-10 NOTIFICATION-TYPE
    STATUS      current
    DESCRIPTION
        "SNMPTrap, do channel-10 in slot 5"
::= { slot5-do-Trap 11 }

slot5Trap-do-11 NOTIFICATION-TYPE
    STATUS      current
    DESCRIPTION
        "SNMPTrap, do channel-11 in slot 5"
::= { slot5-do-Trap 12 }

slot5Trap-do-12 NOTIFICATION-TYPE
    STATUS      current
    DESCRIPTION
        "SNMPTrap, do channel-12 in slot 5"
::= { slot5-do-Trap 13 }

slot5Trap-do-13 NOTIFICATION-TYPE
    STATUS      current
    DESCRIPTION
        "SNMPTrap, do channel-13 in slot 5"
::= { slot5-do-Trap 14 }

slot5Trap-do-14 NOTIFICATION-TYPE
    STATUS      current
    DESCRIPTION
        "SNMPTrap, do channel-14 in slot 5"
::= { slot5-do-Trap 15 }

slot5Trap-do-15 NOTIFICATION-TYPE
    STATUS      current
    DESCRIPTION
        "SNMPTrap, do channel-15 in slot 5"
::= { slot5-do-Trap 16 }

----------------------------------------------------------------
-- 1.3.6.1.4.1.8691.10.2500.61.3
    slot5-dio-Trap OBJECT IDENTIFIER ::= { slot5-io-Trap 3 }
----------------------------------------------------------------

slot5Trap-dio-00 NOTIFICATION-TYPE
    STATUS      current
    DESCRIPTION
        "SNMPTrap, dio channel-00 in slot 5"
::= { slot5-dio-Trap 1 }

slot5Trap-dio-01 NOTIFICATION-TYPE
    STATUS      current
    DESCRIPTION
        "SNMPTrap, dio channel-01 in slot 5"
::= { slot5-dio-Trap 2 }

slot5Trap-dio-02 NOTIFICATION-TYPE
    STATUS      current
    DESCRIPTION
        "SNMPTrap, dio channel-02 in slot 5"
::= { slot5-dio-Trap 3 }

slot5Trap-dio-03 NOTIFICATION-TYPE
    STATUS      current
    DESCRIPTION
        "SNMPTrap, dio channel-03 in slot 5"
::= { slot5-dio-Trap 4 }

slot5Trap-dio-04 NOTIFICATION-TYPE
    STATUS      current
    DESCRIPTION
        "SNMPTrap, dio channel-04 in slot 5"
::= { slot5-dio-Trap 5 }

slot5Trap-dio-05 NOTIFICATION-TYPE
    STATUS      current
    DESCRIPTION
        "SNMPTrap, dio channel-05 in slot 5"
::= { slot5-dio-Trap 6 }

slot5Trap-dio-06 NOTIFICATION-TYPE
    STATUS      current
    DESCRIPTION
        "SNMPTrap, dio channel-06 in slot 5"
::= { slot5-dio-Trap 7 }

slot5Trap-dio-07 NOTIFICATION-TYPE
    STATUS      current
    DESCRIPTION
        "SNMPTrap, dio channel-07 in slot 5"
::= { slot5-dio-Trap 8 }

slot5Trap-dio-08 NOTIFICATION-TYPE
    STATUS      current
    DESCRIPTION
        "SNMPTrap, dio channel-08 in slot 5"
::= { slot5-dio-Trap 9 }

slot5Trap-dio-09 NOTIFICATION-TYPE
    STATUS      current
    DESCRIPTION
        "SNMPTrap, dio channel-09 in slot 5"
::= { slot5-dio-Trap 10 }

slot5Trap-dio-10 NOTIFICATION-TYPE
    STATUS      current
    DESCRIPTION
        "SNMPTrap, dio channel-10 in slot 5"
::= { slot5-dio-Trap 11 }

slot5Trap-dio-11 NOTIFICATION-TYPE
    STATUS      current
    DESCRIPTION
        "SNMPTrap, dio channel-11 in slot 5"
::= { slot5-dio-Trap 12 }

slot5Trap-dio-12 NOTIFICATION-TYPE
    STATUS      current
    DESCRIPTION
        "SNMPTrap, dio channel-12 in slot 5"
::= { slot5-dio-Trap 13 }

slot5Trap-dio-13 NOTIFICATION-TYPE
    STATUS      current
    DESCRIPTION
        "SNMPTrap, dio channel-13 in slot 5"
::= { slot5-dio-Trap 14 }

slot5Trap-dio-14 NOTIFICATION-TYPE
    STATUS      current
    DESCRIPTION
        "SNMPTrap, dio channel-14 in slot 5"
::= { slot5-dio-Trap 15 }

slot5Trap-dio-15 NOTIFICATION-TYPE
    STATUS      current
    DESCRIPTION
        "SNMPTrap, dio channel-15 in slot 5"
::= { slot5-dio-Trap 16 }

----------------------------------------------------------------
-- 1.3.6.1.4.1.8691.10.2500.61.4
    slot5-relay-Trap OBJECT IDENTIFIER ::= { slot5-io-Trap 4 }
----------------------------------------------------------------

slot5Trap-relay-00 NOTIFICATION-TYPE
    STATUS      current
    DESCRIPTION
        "SNMPTrap, relay channel-00 in slot 5"
::= { slot5-relay-Trap 1 }

slot5Trap-relay-01 NOTIFICATION-TYPE
    STATUS      current
    DESCRIPTION
        "SNMPTrap, relay channel-01 in slot 5"
::= { slot5-relay-Trap 2 }

slot5Trap-relay-02 NOTIFICATION-TYPE
    STATUS      current
    DESCRIPTION
        "SNMPTrap, relay channel-02 in slot 5"
::= { slot5-relay-Trap 3 }

slot5Trap-relay-03 NOTIFICATION-TYPE
    STATUS      current
    DESCRIPTION
        "SNMPTrap, relay channel-03 in slot 5"
::= { slot5-relay-Trap 4 }

slot5Trap-relay-04 NOTIFICATION-TYPE
    STATUS      current
    DESCRIPTION
        "SNMPTrap, relay channel-04 in slot 5"
::= { slot5-relay-Trap 5 }

slot5Trap-relay-05 NOTIFICATION-TYPE
    STATUS      current
    DESCRIPTION
        "SNMPTrap, relay channel-05 in slot 5"
::= { slot5-relay-Trap 6 }

slot5Trap-relay-06 NOTIFICATION-TYPE
    STATUS      current
    DESCRIPTION
        "SNMPTrap, relay channel-06 in slot 5"
::= { slot5-relay-Trap 7 }

slot5Trap-relay-07 NOTIFICATION-TYPE
    STATUS      current
    DESCRIPTION
        "SNMPTrap, relay channel-07 in slot 5"
::= { slot5-relay-Trap 8 }

slot5Trap-relay-08 NOTIFICATION-TYPE
    STATUS      current
    DESCRIPTION
        "SNMPTrap, relay channel-08 in slot 5"
::= { slot5-relay-Trap 9 }

slot5Trap-relay-09 NOTIFICATION-TYPE
    STATUS      current
    DESCRIPTION
        "SNMPTrap, relay channel-09 in slot 5"
::= { slot5-relay-Trap 10 }

slot5Trap-relay-10 NOTIFICATION-TYPE
    STATUS      current
    DESCRIPTION
        "SNMPTrap, relay channel-10 in slot 5"
::= { slot5-relay-Trap 11 }

slot5Trap-relay-11 NOTIFICATION-TYPE
    STATUS      current
    DESCRIPTION
        "SNMPTrap, relay channel-11 in slot 5"
::= { slot5-relay-Trap 12 }

slot5Trap-relay-12 NOTIFICATION-TYPE
    STATUS      current
    DESCRIPTION
        "SNMPTrap, relay channel-12 in slot 5"
::= { slot5-relay-Trap 13 }

slot5Trap-relay-13 NOTIFICATION-TYPE
    STATUS      current
    DESCRIPTION
        "SNMPTrap, relay channel-13 in slot 5"
::= { slot5-relay-Trap 14 }

slot5Trap-relay-14 NOTIFICATION-TYPE
    STATUS      current
    DESCRIPTION
        "SNMPTrap, relay channel-14 in slot 5"
::= { slot5-relay-Trap 15 }

slot5Trap-relay-15 NOTIFICATION-TYPE
    STATUS      current
    DESCRIPTION
        "SNMPTrap, relay channel-15 in slot 5"
::= { slot5-relay-Trap 16 }

----------------------------------------------------------------
-- 1.3.6.1.4.1.8691.10.2500.61.5
    slot5-ai-Trap OBJECT IDENTIFIER ::= { slot5-io-Trap 5 }
----------------------------------------------------------------

slot5Trap-ai-00 NOTIFICATION-TYPE
    STATUS      current
    DESCRIPTION
        "SNMPTrap, ai channel-00 in slot 5"
::= { slot5-ai-Trap 1 }

slot5Trap-ai-01 NOTIFICATION-TYPE
    STATUS      current
    DESCRIPTION
        "SNMPTrap, ai channel-01 in slot 5"
::= { slot5-ai-Trap 2 }

slot5Trap-ai-02 NOTIFICATION-TYPE
    STATUS      current
    DESCRIPTION
        "SNMPTrap, ai channel-02 in slot 5"
::= { slot5-ai-Trap 3 }

slot5Trap-ai-03 NOTIFICATION-TYPE
    STATUS      current
    DESCRIPTION
        "SNMPTrap, ai channel-03 in slot 5"
::= { slot5-ai-Trap 4 }

slot5Trap-ai-04 NOTIFICATION-TYPE
    STATUS      current
    DESCRIPTION
        "SNMPTrap, ai channel-04 in slot 5"
::= { slot5-ai-Trap 5 }

slot5Trap-ai-05 NOTIFICATION-TYPE
    STATUS      current
    DESCRIPTION
        "SNMPTrap, ai channel-05 in slot 5"
::= { slot5-ai-Trap 6 }

slot5Trap-ai-06 NOTIFICATION-TYPE
    STATUS      current
    DESCRIPTION
        "SNMPTrap, ai channel-06 in slot 5"
::= { slot5-ai-Trap 7 }

slot5Trap-ai-07 NOTIFICATION-TYPE
    STATUS      current
    DESCRIPTION
        "SNMPTrap, ai channel-07 in slot 5"
::= { slot5-ai-Trap 8 }

slot5Trap-ai-08 NOTIFICATION-TYPE
    STATUS      current
    DESCRIPTION
        "SNMPTrap, ai channel-08 in slot 5"
::= { slot5-ai-Trap 9 }

slot5Trap-ai-09 NOTIFICATION-TYPE
    STATUS      current
    DESCRIPTION
        "SNMPTrap, ai channel-09 in slot 5"
::= { slot5-ai-Trap 10 }

slot5Trap-ai-10 NOTIFICATION-TYPE
    STATUS      current
    DESCRIPTION
        "SNMPTrap, ai channel-10 in slot 5"
::= { slot5-ai-Trap 11 }

slot5Trap-ai-11 NOTIFICATION-TYPE
    STATUS      current
    DESCRIPTION
        "SNMPTrap, ai channel-11 in slot 5"
::= { slot5-ai-Trap 12 }

slot5Trap-ai-12 NOTIFICATION-TYPE
    STATUS      current
    DESCRIPTION
        "SNMPTrap, ai channel-12 in slot 5"
::= { slot5-ai-Trap 13 }

slot5Trap-ai-13 NOTIFICATION-TYPE
    STATUS      current
    DESCRIPTION
        "SNMPTrap, ai channel-13 in slot 5"
::= { slot5-ai-Trap 14 }

slot5Trap-ai-14 NOTIFICATION-TYPE
    STATUS      current
    DESCRIPTION
        "SNMPTrap, ai channel-14 in slot 5"
::= { slot5-ai-Trap 15 }

slot5Trap-ai-15 NOTIFICATION-TYPE
    STATUS      current
    DESCRIPTION
        "SNMPTrap, ai channel-15 in slot 5"
::= { slot5-ai-Trap 16 }

----------------------------------------------------------------
-- 1.3.6.1.4.1.8691.10.2500.61.6
    slot5-ao-Trap OBJECT IDENTIFIER ::= { slot5-io-Trap 6 }
----------------------------------------------------------------

slot5Trap-ao-00 NOTIFICATION-TYPE
    STATUS      current
    DESCRIPTION
        "SNMPTrap, ao channel-00 in slot 5"
::= { slot5-ao-Trap 1 }

slot5Trap-ao-01 NOTIFICATION-TYPE
    STATUS      current
    DESCRIPTION
        "SNMPTrap, ao channel-01 in slot 5"
::= { slot5-ao-Trap 2 }

slot5Trap-ao-02 NOTIFICATION-TYPE
    STATUS      current
    DESCRIPTION
        "SNMPTrap, ao channel-02 in slot 5"
::= { slot5-ao-Trap 3 }

slot5Trap-ao-03 NOTIFICATION-TYPE
    STATUS      current
    DESCRIPTION
        "SNMPTrap, ao channel-03 in slot 5"
::= { slot5-ao-Trap 4 }

slot5Trap-ao-04 NOTIFICATION-TYPE
    STATUS      current
    DESCRIPTION
        "SNMPTrap, ao channel-04 in slot 5"
::= { slot5-ao-Trap 5 }

slot5Trap-ao-05 NOTIFICATION-TYPE
    STATUS      current
    DESCRIPTION
        "SNMPTrap, ao channel-05 in slot 5"
::= { slot5-ao-Trap 6 }

slot5Trap-ao-06 NOTIFICATION-TYPE
    STATUS      current
    DESCRIPTION
        "SNMPTrap, ao channel-06 in slot 5"
::= { slot5-ao-Trap 7 }

slot5Trap-ao-07 NOTIFICATION-TYPE
    STATUS      current
    DESCRIPTION
        "SNMPTrap, ao channel-07 in slot 5"
::= { slot5-ao-Trap 8 }

slot5Trap-ao-08 NOTIFICATION-TYPE
    STATUS      current
    DESCRIPTION
        "SNMPTrap, ao channel-08 in slot 5"
::= { slot5-ao-Trap 9 }

slot5Trap-ao-09 NOTIFICATION-TYPE
    STATUS      current
    DESCRIPTION
        "SNMPTrap, ao channel-09 in slot 5"
::= { slot5-ao-Trap 10 }

slot5Trap-ao-10 NOTIFICATION-TYPE
    STATUS      current
    DESCRIPTION
        "SNMPTrap, ao channel-10 in slot 5"
::= { slot5-ao-Trap 11 }

slot5Trap-ao-11 NOTIFICATION-TYPE
    STATUS      current
    DESCRIPTION
        "SNMPTrap, ao channel-11 in slot 5"
::= { slot5-ao-Trap 12 }

slot5Trap-ao-12 NOTIFICATION-TYPE
    STATUS      current
    DESCRIPTION
        "SNMPTrap, ao channel-12 in slot 5"
::= { slot5-ao-Trap 13 }

slot5Trap-ao-13 NOTIFICATION-TYPE
    STATUS      current
    DESCRIPTION
        "SNMPTrap, ao channel-13 in slot 5"
::= { slot5-ao-Trap 14 }

slot5Trap-ao-14 NOTIFICATION-TYPE
    STATUS      current
    DESCRIPTION
        "SNMPTrap, ao channel-14 in slot 5"
::= { slot5-ao-Trap 15 }

slot5Trap-ao-15 NOTIFICATION-TYPE
    STATUS      current
    DESCRIPTION
        "SNMPTrap, ao channel-15 in slot 5"
::= { slot5-ao-Trap 16 }

----------------------------------------------------------------
-- 1.3.6.1.4.1.8691.10.2500.61.7
    slot5-rtd-Trap OBJECT IDENTIFIER ::= { slot5-io-Trap 7 }
----------------------------------------------------------------

slot5Trap-rtd-00 NOTIFICATION-TYPE
    STATUS      current
    DESCRIPTION
        "SNMPTrap, rtd channel-00 in slot 5"
::= { slot5-rtd-Trap 1 }

slot5Trap-rtd-01 NOTIFICATION-TYPE
    STATUS      current
    DESCRIPTION
        "SNMPTrap, rtd channel-01 in slot 5"
::= { slot5-rtd-Trap 2 }

slot5Trap-rtd-02 NOTIFICATION-TYPE
    STATUS      current
    DESCRIPTION
        "SNMPTrap, rtd channel-02 in slot 5"
::= { slot5-rtd-Trap 3 }

slot5Trap-rtd-03 NOTIFICATION-TYPE
    STATUS      current
    DESCRIPTION
        "SNMPTrap, rtd channel-03 in slot 5"
::= { slot5-rtd-Trap 4 }

slot5Trap-rtd-04 NOTIFICATION-TYPE
    STATUS      current
    DESCRIPTION
        "SNMPTrap, rtd channel-04 in slot 5"
::= { slot5-rtd-Trap 5 }

slot5Trap-rtd-05 NOTIFICATION-TYPE
    STATUS      current
    DESCRIPTION
        "SNMPTrap, rtd channel-05 in slot 5"
::= { slot5-rtd-Trap 6 }

slot5Trap-rtd-06 NOTIFICATION-TYPE
    STATUS      current
    DESCRIPTION
        "SNMPTrap, rtd channel-06 in slot 5"
::= { slot5-rtd-Trap 7 }

slot5Trap-rtd-07 NOTIFICATION-TYPE
    STATUS      current
    DESCRIPTION
        "SNMPTrap, rtd channel-07 in slot 5"
::= { slot5-rtd-Trap 8 }

slot5Trap-rtd-08 NOTIFICATION-TYPE
    STATUS      current
    DESCRIPTION
        "SNMPTrap, rtd channel-08 in slot 5"
::= { slot5-rtd-Trap 9 }

slot5Trap-rtd-09 NOTIFICATION-TYPE
    STATUS      current
    DESCRIPTION
        "SNMPTrap, rtd channel-09 in slot 5"
::= { slot5-rtd-Trap 10 }

slot5Trap-rtd-10 NOTIFICATION-TYPE
    STATUS      current
    DESCRIPTION
        "SNMPTrap, rtd channel-10 in slot 5"
::= { slot5-rtd-Trap 11 }

slot5Trap-rtd-11 NOTIFICATION-TYPE
    STATUS      current
    DESCRIPTION
        "SNMPTrap, rtd channel-11 in slot 5"
::= { slot5-rtd-Trap 12 }

slot5Trap-rtd-12 NOTIFICATION-TYPE
    STATUS      current
    DESCRIPTION
        "SNMPTrap, rtd channel-12 in slot 5"
::= { slot5-rtd-Trap 13 }

slot5Trap-rtd-13 NOTIFICATION-TYPE
    STATUS      current
    DESCRIPTION
        "SNMPTrap, rtd channel-13 in slot 5"
::= { slot5-rtd-Trap 14 }

slot5Trap-rtd-14 NOTIFICATION-TYPE
    STATUS      current
    DESCRIPTION
        "SNMPTrap, rtd channel-14 in slot 5"
::= { slot5-rtd-Trap 15 }

slot5Trap-rtd-15 NOTIFICATION-TYPE
    STATUS      current
    DESCRIPTION
        "SNMPTrap, rtd channel-15 in slot 5"
::= { slot5-rtd-Trap 16 }

----------------------------------------------------------------
-- 1.3.6.1.4.1.8691.10.2500.61.8
    slot5-tc-Trap OBJECT IDENTIFIER ::= { slot5-io-Trap 8 }
----------------------------------------------------------------

slot5Trap-tc-00 NOTIFICATION-TYPE
    STATUS      current
    DESCRIPTION
        "SNMPTrap, tc channel-00 in slot 5"
::= { slot5-tc-Trap 1 }

slot5Trap-tc-01 NOTIFICATION-TYPE
    STATUS      current
    DESCRIPTION
        "SNMPTrap, tc channel-01 in slot 5"
::= { slot5-tc-Trap 2 }

slot5Trap-tc-02 NOTIFICATION-TYPE
    STATUS      current
    DESCRIPTION
        "SNMPTrap, tc channel-02 in slot 5"
::= { slot5-tc-Trap 3 }

slot5Trap-tc-03 NOTIFICATION-TYPE
    STATUS      current
    DESCRIPTION
        "SNMPTrap, tc channel-03 in slot 5"
::= { slot5-tc-Trap 4 }

slot5Trap-tc-04 NOTIFICATION-TYPE
    STATUS      current
    DESCRIPTION
        "SNMPTrap, tc channel-04 in slot 5"
::= { slot5-tc-Trap 5 }

slot5Trap-tc-05 NOTIFICATION-TYPE
    STATUS      current
    DESCRIPTION
        "SNMPTrap, tc channel-05 in slot 5"
::= { slot5-tc-Trap 6 }

slot5Trap-tc-06 NOTIFICATION-TYPE
    STATUS      current
    DESCRIPTION
        "SNMPTrap, tc channel-06 in slot 5"
::= { slot5-tc-Trap 7 }

slot5Trap-tc-07 NOTIFICATION-TYPE
    STATUS      current
    DESCRIPTION
        "SNMPTrap, tc channel-07 in slot 5"
::= { slot5-tc-Trap 8 }

slot5Trap-tc-08 NOTIFICATION-TYPE
    STATUS      current
    DESCRIPTION
        "SNMPTrap, tc channel-08 in slot 5"
::= { slot5-tc-Trap 9 }

slot5Trap-tc-09 NOTIFICATION-TYPE
    STATUS      current
    DESCRIPTION
        "SNMPTrap, tc channel-09 in slot 5"
::= { slot5-tc-Trap 10 }

slot5Trap-tc-10 NOTIFICATION-TYPE
    STATUS      current
    DESCRIPTION
        "SNMPTrap, tc channel-10 in slot 5"
::= { slot5-tc-Trap 11 }

slot5Trap-tc-11 NOTIFICATION-TYPE
    STATUS      current
    DESCRIPTION
        "SNMPTrap, tc channel-11 in slot 5"
::= { slot5-tc-Trap 12 }

slot5Trap-tc-12 NOTIFICATION-TYPE
    STATUS      current
    DESCRIPTION
        "SNMPTrap, tc channel-12 in slot 5"
::= { slot5-tc-Trap 13 }

slot5Trap-tc-13 NOTIFICATION-TYPE
    STATUS      current
    DESCRIPTION
        "SNMPTrap, tc channel-13 in slot 5"
::= { slot5-tc-Trap 14 }

slot5Trap-tc-14 NOTIFICATION-TYPE
    STATUS      current
    DESCRIPTION
        "SNMPTrap, tc channel-14 in slot 5"
::= { slot5-tc-Trap 15 }

slot5Trap-tc-15 NOTIFICATION-TYPE
    STATUS      current
    DESCRIPTION
        "SNMPTrap, tc channel-15 in slot 5"
::= { slot5-tc-Trap 16 }					
		
----------------------------------------------------------------
-- 1.3.6.1.4.1.8691.10.2500.70
    slot6-io OBJECT IDENTIFIER ::= { ioLogik2500 70 }
----------------------------------------------------------------
-- slot 6 DI
slot6-diTable OBJECT-TYPE
		SYNTAX 			SEQUENCE OF Slot6-diDef
		MAX-ACCESS 		not-accessible
		STATUS 			current
		DESCRIPTION		"The di channel table"
		::= { slot6-io 1 }

slot6-di OBJECT-TYPE
		SYNTAX 			Slot6-diDef
		MAX-ACCESS 		not-accessible
		STATUS 			current
		DESCRIPTION		"The di channel item"
		INDEX { slot6-diIndex }
		::= { slot6-diTable 1 }

Slot6-diDef ::= SEQUENCE { 
    	slot6-diIndex		INTEGER,
		slot6-diStatus		Unsigned32,
		slot6-diCounterReset2Init INTEGER		
		}  

slot6-diIndex OBJECT-TYPE
		SYNTAX 			INTEGER (0..15)
		MAX-ACCESS 		read-only
		STATUS 			current
		DESCRIPTION		"The channel index"
		::= { slot6-di 1 }
		
slot6-diStatus OBJECT-TYPE
		SYNTAX 			Unsigned32
		MAX-ACCESS 		read-write
		STATUS 			current
		DESCRIPTION		"The channel di status. 0=off, 1=on in di mode or n=counter value in counter mode"
		::= { slot6-di 2 }
		
slot6-diCounterReset2Init OBJECT-TYPE
		SYNTAX 			INTEGER 
		MAX-ACCESS 		read-write
		STATUS 			current
		DESCRIPTION		"Trigger counter to initial value. 1=Reset counter to initial value"
		::= { slot6-di 3 }

-- slot 6 DICounterStart
slot6-diCounterStartTable OBJECT-TYPE
		SYNTAX 			SEQUENCE OF Slot6-diCounterStartDef
		MAX-ACCESS 		not-accessible
		STATUS 			current
		DESCRIPTION		"The counter table starting for di"
		::= { slot6-io 39 }

slot6-diCounterStart OBJECT-TYPE
		SYNTAX 			Slot6-diCounterStartDef
		MAX-ACCESS 		not-accessible
		STATUS 			current
		DESCRIPTION		"The counter starting of di item"
		INDEX { slot6-diCounterStartIndex }
		::= { slot6-diCounterStartTable 1 }

Slot6-diCounterStartDef ::= SEQUENCE { 
    	slot6-diCounterStartIndex		INTEGER,
		slot6-diCounterStartStatus		INTEGER		
		}  

slot6-diCounterStartIndex OBJECT-TYPE
		SYNTAX 			INTEGER (0..15)
		MAX-ACCESS 		read-only
		STATUS 			current
		DESCRIPTION		"The channel index for di counter start"
		::= { slot6-diCounterStart 1 }
		
slot6-diCounterStartStatus OBJECT-TYPE
		SYNTAX 			INTEGER (0..1)
		MAX-ACCESS 		read-write
		STATUS 			current
		DESCRIPTION		"The channel status for di counter start. 0=stop, 1=start"
		::= { slot6-diCounterStart 2 } 	
		
-- slot 6 DO
slot6-doTable OBJECT-TYPE
		SYNTAX 			SEQUENCE OF Slot6-doDef
		MAX-ACCESS 		not-accessible
		STATUS 			current
		DESCRIPTION		"The do channel table"
		::= { slot6-io 2 }

slot6-do OBJECT-TYPE
		SYNTAX 			Slot6-doDef
		MAX-ACCESS 		not-accessible
		STATUS 			current
		DESCRIPTION		"The do channel item"
		INDEX { slot6-doIndex }
		::= { slot6-doTable 1 }

Slot6-doDef ::= SEQUENCE { 
    	slot6-doIndex		INTEGER,
		slot6-doStatus		INTEGER		
		}  

slot6-doIndex OBJECT-TYPE
		SYNTAX 			INTEGER (0..15)
		MAX-ACCESS 		read-only
		STATUS 			current
		DESCRIPTION		"The channel index"
		::= { slot6-do 1 }
		
slot6-doStatus OBJECT-TYPE
		SYNTAX 			INTEGER (0..1)
		MAX-ACCESS 		read-write
		STATUS 			current
		DESCRIPTION		"The channel do status. 0=off, 1=on in do mode or 0=stop, 1=start in pulse mode"
		::= { slot6-do 2 }  

-- slot 6 DIO
slot6-dioTable OBJECT-TYPE
		SYNTAX 			SEQUENCE OF Slot6-dioDef
		MAX-ACCESS 		not-accessible
		STATUS 			current
		DESCRIPTION		"The dio channel table"
		::= { slot6-io 3 }

slot6-dio OBJECT-TYPE
		SYNTAX 			Slot6-dioDef
		MAX-ACCESS 		not-accessible
		STATUS 			current
		DESCRIPTION		"The dio channel item"
		INDEX { slot6-dioIndex }
		::= { slot6-dioTable 1 }

Slot6-dioDef ::= SEQUENCE { 
    	slot6-dioIndex		INTEGER,
		slot6-dioStatus		Unsigned32,
		slot6-dioCounterReset2Init INTEGER			
		}  

slot6-dioIndex OBJECT-TYPE
		SYNTAX 			INTEGER (0..15)
		MAX-ACCESS 		read-only
		STATUS 			current
		DESCRIPTION		"The channel index"
		::= { slot6-dio 1 }
		
slot6-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot6-dio 2 }  
		
slot6-dioCounterReset2Init OBJECT-TYPE
		SYNTAX 			INTEGER 
		MAX-ACCESS 		read-write
		STATUS 			current
		DESCRIPTION		"Trigger counter to initial value. 1=Reset counter to initial value"
		::= { slot6-dio 3 }

-- slot 6 DIOCounterStart
slot6-dioCounterStartTable OBJECT-TYPE
		SYNTAX 			SEQUENCE OF Slot6-dioCounterStartDef
		MAX-ACCESS 		not-accessible
		STATUS 			current
		DESCRIPTION		"The counter table starting for dio"
		::= { slot6-io 46 }

slot6-dioCounterStart OBJECT-TYPE
		SYNTAX 			Slot6-dioCounterStartDef
		MAX-ACCESS 		not-accessible
		STATUS 			current
		DESCRIPTION		"The counter starting of dio item"
		INDEX { slot6-dioCounterStartIndex }
		::= { slot6-dioCounterStartTable 1 }

Slot6-dioCounterStartDef ::= SEQUENCE { 
    	slot6-dioCounterStartIndex		INTEGER,
		slot6-dioCounterStartStatus		INTEGER	
		}  

slot6-dioCounterStartIndex OBJECT-TYPE
		SYNTAX 			INTEGER (0..15)
		MAX-ACCESS 		read-only
		STATUS 			current
		DESCRIPTION		"The channel index for dio counter start"
		::= { slot6-dioCounterStart 1 }
		
slot6-dioCounterStartStatus OBJECT-TYPE
		SYNTAX 			INTEGER (0..1)
		MAX-ACCESS 		read-write
		STATUS 			current
		DESCRIPTION		"The channel status for dio counter start. 0=stop, 1=start"
		::= { slot6-dioCounterStart 2 } 
 		
				
-- slot 6 Relay
slot6-relayTable OBJECT-TYPE
		SYNTAX 			SEQUENCE OF Slot6-relayDef
		MAX-ACCESS 		not-accessible
		STATUS 			current
		DESCRIPTION		"The relay channel table"
		::= { slot6-io 4 }

slot6-relay OBJECT-TYPE
		SYNTAX 			Slot6-relayDef
		MAX-ACCESS 		not-accessible
		STATUS 			current
		DESCRIPTION		"The relay channel item"
		INDEX { slot6-relayIndex }
		::= { slot6-relayTable 1 }

Slot6-relayDef ::= SEQUENCE { 
    		slot6-relayIndex		INTEGER,
		slot6-relayStatus		INTEGER		
		}  

slot6-relayIndex OBJECT-TYPE
		SYNTAX 			INTEGER (0..15)
		MAX-ACCESS 		read-only
		STATUS 			current
		DESCRIPTION		"The channel index"
		::= { slot6-relay 1 }
		
slot6-relayStatus OBJECT-TYPE
		SYNTAX 			INTEGER (0..1)
		MAX-ACCESS 		read-write
		STATUS 			current
		DESCRIPTION		"The channel relay status. 0=off, 1=on in do mode or 0=stop, 1=start in pulse mode"
		::= { slot6-relay 2 }  

-- slot 6 AI
slot6-aiTable OBJECT-TYPE
		SYNTAX 			SEQUENCE OF Slot6-aiDef
		MAX-ACCESS 		not-accessible
		STATUS 			current
		DESCRIPTION		"The ai channel table"
		::= { slot6-io 5 }

slot6-ai OBJECT-TYPE
		SYNTAX 			Slot6-aiDef
		MAX-ACCESS 		not-accessible
		STATUS 			current
		DESCRIPTION		"The ai channel item"
		INDEX { slot6-aiIndex }
		::= { slot6-aiTable 1 }

Slot6-aiDef ::= SEQUENCE { 
    	slot6-aiIndex		INTEGER,
		slot6-aiStatus		OCTET STRING,
		slot6-aiBurnoutStatus INTEGER		
		}  

slot6-aiIndex OBJECT-TYPE
		SYNTAX 			INTEGER (0..15)
		MAX-ACCESS 		read-only
		STATUS 			current
		DESCRIPTION		"The channel index"
		::= { slot6-ai 1 }
		
slot6-aiStatus OBJECT-TYPE
		SYNTAX 			OCTET STRING
		MAX-ACCESS 		read-only
		STATUS 			current
		DESCRIPTION		"The channel ai scaled value"
		::= { slot6-ai 2 }  

slot6-aiBurnoutStatus OBJECT-TYPE
		SYNTAX 			INTEGER (0..3)
		MAX-ACCESS 		read-only
		STATUS 			current
		DESCRIPTION		"The channel of burnout status (0: normal, 1: burnout, 2: underange, 3: overange)"
		::= { slot6-ai 3 }  
		
-- slot 6 AO
slot6-aoTable OBJECT-TYPE
		SYNTAX 			SEQUENCE OF Slot6-aoDef
		MAX-ACCESS 		not-accessible
		STATUS 			current
		DESCRIPTION		"The ao channel table"
		::= { slot6-io 6 }

slot6-ao OBJECT-TYPE
		SYNTAX 			Slot6-aoDef
		MAX-ACCESS 		not-accessible
		STATUS 			current
		DESCRIPTION		"The ao channel item"
		INDEX { slot6-aoIndex }
		::= { slot6-aoTable 1 }

Slot6-aoDef ::= SEQUENCE { 
    	slot6-aoIndex		INTEGER,
		slot6-aoStatus		OCTET STRING		
		}  

slot6-aoIndex OBJECT-TYPE
		SYNTAX 			INTEGER (0..15)
		MAX-ACCESS 		read-only
		STATUS 			current
		DESCRIPTION		"The channel index"
		::= { slot6-ao 1 }
		
slot6-aoStatus OBJECT-TYPE
		SYNTAX 			OCTET STRING
		MAX-ACCESS 		read-write
		STATUS 			current
		DESCRIPTION		"The channel ao scaled value"
		::= { slot6-ao 2 }  

-- slot 6 RTD
slot6-rtdTable OBJECT-TYPE
		SYNTAX 			SEQUENCE OF Slot6-rtdDef
		MAX-ACCESS 		not-accessible
		STATUS 			current
		DESCRIPTION		"The rtd channel table"
		::= { slot6-io 7 }

slot6-rtd OBJECT-TYPE
		SYNTAX 			Slot6-rtdDef
		MAX-ACCESS 		not-accessible
		STATUS 			current
		DESCRIPTION		"The rtd channel item"
		INDEX { slot6-rtdIndex }
		::= { slot6-rtdTable 1 }

Slot6-rtdDef ::= SEQUENCE { 
    	slot6-rtdIndex		INTEGER,
		slot6-rtdStatus		OCTET STRING		
		}  

slot6-rtdIndex OBJECT-TYPE
		SYNTAX 			INTEGER (0..15)
		MAX-ACCESS 		read-only
		STATUS 			current
		DESCRIPTION		"The channel index"
		::= { slot6-rtd 1 }
		
slot6-rtdStatus OBJECT-TYPE
		SYNTAX 			OCTET STRING
		MAX-ACCESS 		read-only
		STATUS 			current
		DESCRIPTION		"The channel rtd scaled value"
		::= { slot6-rtd 2 }  

-- slot 6 TC
slot6-tcTable OBJECT-TYPE
		SYNTAX 			SEQUENCE OF Slot6-tcDef
		MAX-ACCESS 		not-accessible
		STATUS 			current
		DESCRIPTION		"The tc channel table"
		::= { slot6-io 8 }

slot6-tc OBJECT-TYPE
		SYNTAX 			Slot6-tcDef
		MAX-ACCESS 		not-accessible
		STATUS 			current
		DESCRIPTION		"The tc channel item"
		INDEX { slot6-tcIndex }
		::= { slot6-tcTable 1 }

Slot6-tcDef ::= SEQUENCE { 
    	slot6-tcIndex		INTEGER,
		slot6-tcStatus		OCTET STRING		
		}  

slot6-tcIndex OBJECT-TYPE
		SYNTAX 			INTEGER (0..15)
		MAX-ACCESS 		read-only
		STATUS 			current
		DESCRIPTION		"The channel index"
		::= { slot6-tc 1 }
		
slot6-tcStatus OBJECT-TYPE
		SYNTAX 			OCTET STRING
		MAX-ACCESS 		read-only
		STATUS 			current
		DESCRIPTION		"The channel tc scaled value"
		::= { slot6-tc 2 }  

----------------------------------------------------------------
-- 1.3.6.1.4.1.8691.10.2500.71
    slot6-io-Trap OBJECT IDENTIFIER ::= { ioLogik2500 71 }
----------------------------------------------------------------

----------------------------------------------------------------
-- 1.3.6.1.4.1.8691.10.2500.71.1
    slot6-di-Trap OBJECT IDENTIFIER ::= { slot6-io-Trap 1 }
----------------------------------------------------------------

slot6Trap-di-00 NOTIFICATION-TYPE
    STATUS      current
    DESCRIPTION
        "SNMPTrap, di channel-00 in slot 6"
::= { slot6-di-Trap 1 }

slot6Trap-di-01 NOTIFICATION-TYPE
    STATUS      current
    DESCRIPTION
        "SNMPTrap, di channel-01 in slot 6"
::= { slot6-di-Trap 2 }

slot6Trap-di-02 NOTIFICATION-TYPE
    STATUS      current
    DESCRIPTION
        "SNMPTrap, di channel-02 in slot 6"
::= { slot6-di-Trap 3 }

slot6Trap-di-03 NOTIFICATION-TYPE
    STATUS      current
    DESCRIPTION
        "SNMPTrap, di channel-03 in slot 6"
::= { slot6-di-Trap 4 }

slot6Trap-di-04 NOTIFICATION-TYPE
    STATUS      current
    DESCRIPTION
        "SNMPTrap, di channel-04 in slot 6"
::= { slot6-di-Trap 5 }

slot6Trap-di-05 NOTIFICATION-TYPE
    STATUS      current
    DESCRIPTION
        "SNMPTrap, di channel-05 in slot 6"
::= { slot6-di-Trap 6 }

slot6Trap-di-06 NOTIFICATION-TYPE
    STATUS      current
    DESCRIPTION
        "SNMPTrap, di channel-06 in slot 6"
::= { slot6-di-Trap 7 }

slot6Trap-di-07 NOTIFICATION-TYPE
    STATUS      current
    DESCRIPTION
        "SNMPTrap, di channel-07 in slot 6"
::= { slot6-di-Trap 8 }

slot6Trap-di-08 NOTIFICATION-TYPE
    STATUS      current
    DESCRIPTION
        "SNMPTrap, di channel-08 in slot 6"
::= { slot6-di-Trap 9 }

slot6Trap-di-09 NOTIFICATION-TYPE
    STATUS      current
    DESCRIPTION
        "SNMPTrap, di channel-09 in slot 6"
::= { slot6-di-Trap 10 }

slot6Trap-di-10 NOTIFICATION-TYPE
    STATUS      current
    DESCRIPTION
        "SNMPTrap, di channel-10 in slot 6"
::= { slot6-di-Trap 11 }

slot6Trap-di-11 NOTIFICATION-TYPE
    STATUS      current
    DESCRIPTION
        "SNMPTrap, di channel-11 in slot 6"
::= { slot6-di-Trap 12 }

slot6Trap-di-12 NOTIFICATION-TYPE
    STATUS      current
    DESCRIPTION
        "SNMPTrap, di channel-12 in slot 6"
::= { slot6-di-Trap 13 }

slot6Trap-di-13 NOTIFICATION-TYPE
    STATUS      current
    DESCRIPTION
        "SNMPTrap, di channel-13 in slot 6"
::= { slot6-di-Trap 14 }

slot6Trap-di-14 NOTIFICATION-TYPE
    STATUS      current
    DESCRIPTION
        "SNMPTrap, di channel-14 in slot 6"
::= { slot6-di-Trap 15 }

slot6Trap-di-15 NOTIFICATION-TYPE
    STATUS      current
    DESCRIPTION
        "SNMPTrap, di channel-15 in slot 6"
::= { slot6-di-Trap 16 }
----------------------------------------------------------------
-- 1.3.6.1.4.1.8691.10.2500.71.2
    slot6-do-Trap OBJECT IDENTIFIER ::= { slot6-io-Trap 2 }
----------------------------------------------------------------

slot6Trap-do-00 NOTIFICATION-TYPE
    STATUS      current
    DESCRIPTION
        "SNMPTrap, do channel-00 in slot 6"
::= { slot6-do-Trap 1 }

slot6Trap-do-01 NOTIFICATION-TYPE
    STATUS      current
    DESCRIPTION
        "SNMPTrap, do channel-01 in slot 6"
::= { slot6-do-Trap 2 }

slot6Trap-do-02 NOTIFICATION-TYPE
    STATUS      current
    DESCRIPTION
        "SNMPTrap, do channel-02 in slot 6"
::= { slot6-do-Trap 3 }

slot6Trap-do-03 NOTIFICATION-TYPE
    STATUS      current
    DESCRIPTION
        "SNMPTrap, do channel-03 in slot 6"
::= { slot6-do-Trap 4 }

slot6Trap-do-04 NOTIFICATION-TYPE
    STATUS      current
    DESCRIPTION
        "SNMPTrap, do channel-04 in slot 6"
::= { slot6-do-Trap 5 }

slot6Trap-do-05 NOTIFICATION-TYPE
    STATUS      current
    DESCRIPTION
        "SNMPTrap, do channel-05 in slot 6"
::= { slot6-do-Trap 6 }

slot6Trap-do-06 NOTIFICATION-TYPE
    STATUS      current
    DESCRIPTION
        "SNMPTrap, do channel-06 in slot 6"
::= { slot6-do-Trap 7 }

slot6Trap-do-07 NOTIFICATION-TYPE
    STATUS      current
    DESCRIPTION
        "SNMPTrap, do channel-07 in slot 6"
::= { slot6-do-Trap 8 }

slot6Trap-do-08 NOTIFICATION-TYPE
    STATUS      current
    DESCRIPTION
        "SNMPTrap, do channel-08 in slot 6"
::= { slot6-do-Trap 9 }

slot6Trap-do-09 NOTIFICATION-TYPE
    STATUS      current
    DESCRIPTION
        "SNMPTrap, do channel-09 in slot 6"
::= { slot6-do-Trap 10 }

slot6Trap-do-10 NOTIFICATION-TYPE
    STATUS      current
    DESCRIPTION
        "SNMPTrap, do channel-10 in slot 6"
::= { slot6-do-Trap 11 }

slot6Trap-do-11 NOTIFICATION-TYPE
    STATUS      current
    DESCRIPTION
        "SNMPTrap, do channel-11 in slot 6"
::= { slot6-do-Trap 12 }

slot6Trap-do-12 NOTIFICATION-TYPE
    STATUS      current
    DESCRIPTION
        "SNMPTrap, do channel-12 in slot 6"
::= { slot6-do-Trap 13 }

slot6Trap-do-13 NOTIFICATION-TYPE
    STATUS      current
    DESCRIPTION
        "SNMPTrap, do channel-13 in slot 6"
::= { slot6-do-Trap 14 }

slot6Trap-do-14 NOTIFICATION-TYPE
    STATUS      current
    DESCRIPTION
        "SNMPTrap, do channel-14 in slot 6"
::= { slot6-do-Trap 15 }

slot6Trap-do-15 NOTIFICATION-TYPE
    STATUS      current
    DESCRIPTION
        "SNMPTrap, do channel-15 in slot 6"
::= { slot6-do-Trap 16 }

----------------------------------------------------------------
-- 1.3.6.1.4.1.8691.10.2500.71.3
    slot6-dio-Trap OBJECT IDENTIFIER ::= { slot6-io-Trap 3 }
----------------------------------------------------------------

slot6Trap-dio-00 NOTIFICATION-TYPE
    STATUS      current
    DESCRIPTION
        "SNMPTrap, dio channel-00 in slot 6"
::= { slot6-dio-Trap 1 }

slot6Trap-dio-01 NOTIFICATION-TYPE
    STATUS      current
    DESCRIPTION
        "SNMPTrap, dio channel-01 in slot 6"
::= { slot6-dio-Trap 2 }

slot6Trap-dio-02 NOTIFICATION-TYPE
    STATUS      current
    DESCRIPTION
        "SNMPTrap, dio channel-02 in slot 6"
::= { slot6-dio-Trap 3 }

slot6Trap-dio-03 NOTIFICATION-TYPE
    STATUS      current
    DESCRIPTION
        "SNMPTrap, dio channel-03 in slot 6"
::= { slot6-dio-Trap 4 }

slot6Trap-dio-04 NOTIFICATION-TYPE
    STATUS      current
    DESCRIPTION
        "SNMPTrap, dio channel-04 in slot 6"
::= { slot6-dio-Trap 5 }

slot6Trap-dio-05 NOTIFICATION-TYPE
    STATUS      current
    DESCRIPTION
        "SNMPTrap, dio channel-05 in slot 6"
::= { slot6-dio-Trap 6 }

slot6Trap-dio-06 NOTIFICATION-TYPE
    STATUS      current
    DESCRIPTION
        "SNMPTrap, dio channel-06 in slot 6"
::= { slot6-dio-Trap 7 }

slot6Trap-dio-07 NOTIFICATION-TYPE
    STATUS      current
    DESCRIPTION
        "SNMPTrap, dio channel-07 in slot 6"
::= { slot6-dio-Trap 8 }

slot6Trap-dio-08 NOTIFICATION-TYPE
    STATUS      current
    DESCRIPTION
        "SNMPTrap, dio channel-08 in slot 6"
::= { slot6-dio-Trap 9 }

slot6Trap-dio-09 NOTIFICATION-TYPE
    STATUS      current
    DESCRIPTION
        "SNMPTrap, dio channel-09 in slot 6"
::= { slot6-dio-Trap 10 }

slot6Trap-dio-10 NOTIFICATION-TYPE
    STATUS      current
    DESCRIPTION
        "SNMPTrap, dio channel-10 in slot 6"
::= { slot6-dio-Trap 11 }

slot6Trap-dio-11 NOTIFICATION-TYPE
    STATUS      current
    DESCRIPTION
        "SNMPTrap, dio channel-11 in slot 6"
::= { slot6-dio-Trap 12 }

slot6Trap-dio-12 NOTIFICATION-TYPE
    STATUS      current
    DESCRIPTION
        "SNMPTrap, dio channel-12 in slot 6"
::= { slot6-dio-Trap 13 }

slot6Trap-dio-13 NOTIFICATION-TYPE
    STATUS      current
    DESCRIPTION
        "SNMPTrap, dio channel-13 in slot 6"
::= { slot6-dio-Trap 14 }

slot6Trap-dio-14 NOTIFICATION-TYPE
    STATUS      current
    DESCRIPTION
        "SNMPTrap, dio channel-14 in slot 6"
::= { slot6-dio-Trap 15 }

slot6Trap-dio-15 NOTIFICATION-TYPE
    STATUS      current
    DESCRIPTION
        "SNMPTrap, dio channel-15 in slot 6"
::= { slot6-dio-Trap 16 }

----------------------------------------------------------------
-- 1.3.6.1.4.1.8691.10.2500.71.4
    slot6-relay-Trap OBJECT IDENTIFIER ::= { slot6-io-Trap 4 }
----------------------------------------------------------------

slot6Trap-relay-00 NOTIFICATION-TYPE
    STATUS      current
    DESCRIPTION
        "SNMPTrap, relay channel-00 in slot 6"
::= { slot6-relay-Trap 1 }

slot6Trap-relay-01 NOTIFICATION-TYPE
    STATUS      current
    DESCRIPTION
        "SNMPTrap, relay channel-01 in slot 6"
::= { slot6-relay-Trap 2 }

slot6Trap-relay-02 NOTIFICATION-TYPE
    STATUS      current
    DESCRIPTION
        "SNMPTrap, relay channel-02 in slot 6"
::= { slot6-relay-Trap 3 }

slot6Trap-relay-03 NOTIFICATION-TYPE
    STATUS      current
    DESCRIPTION
        "SNMPTrap, relay channel-03 in slot 6"
::= { slot6-relay-Trap 4 }

slot6Trap-relay-04 NOTIFICATION-TYPE
    STATUS      current
    DESCRIPTION
        "SNMPTrap, relay channel-04 in slot 6"
::= { slot6-relay-Trap 5 }

slot6Trap-relay-05 NOTIFICATION-TYPE
    STATUS      current
    DESCRIPTION
        "SNMPTrap, relay channel-05 in slot 6"
::= { slot6-relay-Trap 6 }

slot6Trap-relay-06 NOTIFICATION-TYPE
    STATUS      current
    DESCRIPTION
        "SNMPTrap, relay channel-06 in slot 6"
::= { slot6-relay-Trap 7 }

slot6Trap-relay-07 NOTIFICATION-TYPE
    STATUS      current
    DESCRIPTION
        "SNMPTrap, relay channel-07 in slot 6"
::= { slot6-relay-Trap 8 }

slot6Trap-relay-08 NOTIFICATION-TYPE
    STATUS      current
    DESCRIPTION
        "SNMPTrap, relay channel-08 in slot 6"
::= { slot6-relay-Trap 9 }

slot6Trap-relay-09 NOTIFICATION-TYPE
    STATUS      current
    DESCRIPTION
        "SNMPTrap, relay channel-09 in slot 6"
::= { slot6-relay-Trap 10 }

slot6Trap-relay-10 NOTIFICATION-TYPE
    STATUS      current
    DESCRIPTION
        "SNMPTrap, relay channel-10 in slot 6"
::= { slot6-relay-Trap 11 }

slot6Trap-relay-11 NOTIFICATION-TYPE
    STATUS      current
    DESCRIPTION
        "SNMPTrap, relay channel-11 in slot 6"
::= { slot6-relay-Trap 12 }

slot6Trap-relay-12 NOTIFICATION-TYPE
    STATUS      current
    DESCRIPTION
        "SNMPTrap, relay channel-12 in slot 6"
::= { slot6-relay-Trap 13 }

slot6Trap-relay-13 NOTIFICATION-TYPE
    STATUS      current
    DESCRIPTION
        "SNMPTrap, relay channel-13 in slot 6"
::= { slot6-relay-Trap 14 }

slot6Trap-relay-14 NOTIFICATION-TYPE
    STATUS      current
    DESCRIPTION
        "SNMPTrap, relay channel-14 in slot 6"
::= { slot6-relay-Trap 15 }

slot6Trap-relay-15 NOTIFICATION-TYPE
    STATUS      current
    DESCRIPTION
        "SNMPTrap, relay channel-15 in slot 6"
::= { slot6-relay-Trap 16 }

----------------------------------------------------------------
-- 1.3.6.1.4.1.8691.10.2500.71.5
    slot6-ai-Trap OBJECT IDENTIFIER ::= { slot6-io-Trap 5 }
----------------------------------------------------------------

slot6Trap-ai-00 NOTIFICATION-TYPE
    STATUS      current
    DESCRIPTION
        "SNMPTrap, ai channel-00 in slot 6"
::= { slot6-ai-Trap 1 }

slot6Trap-ai-01 NOTIFICATION-TYPE
    STATUS      current
    DESCRIPTION
        "SNMPTrap, ai channel-01 in slot 6"
::= { slot6-ai-Trap 2 }

slot6Trap-ai-02 NOTIFICATION-TYPE
    STATUS      current
    DESCRIPTION
        "SNMPTrap, ai channel-02 in slot 6"
::= { slot6-ai-Trap 3 }

slot6Trap-ai-03 NOTIFICATION-TYPE
    STATUS      current
    DESCRIPTION
        "SNMPTrap, ai channel-03 in slot 6"
::= { slot6-ai-Trap 4 }

slot6Trap-ai-04 NOTIFICATION-TYPE
    STATUS      current
    DESCRIPTION
        "SNMPTrap, ai channel-04 in slot 6"
::= { slot6-ai-Trap 5 }

slot6Trap-ai-05 NOTIFICATION-TYPE
    STATUS      current
    DESCRIPTION
        "SNMPTrap, ai channel-05 in slot 6"
::= { slot6-ai-Trap 6 }

slot6Trap-ai-06 NOTIFICATION-TYPE
    STATUS      current
    DESCRIPTION
        "SNMPTrap, ai channel-06 in slot 6"
::= { slot6-ai-Trap 7 }

slot6Trap-ai-07 NOTIFICATION-TYPE
    STATUS      current
    DESCRIPTION
        "SNMPTrap, ai channel-07 in slot 6"
::= { slot6-ai-Trap 8 }

slot6Trap-ai-08 NOTIFICATION-TYPE
    STATUS      current
    DESCRIPTION
        "SNMPTrap, ai channel-08 in slot 6"
::= { slot6-ai-Trap 9 }

slot6Trap-ai-09 NOTIFICATION-TYPE
    STATUS      current
    DESCRIPTION
        "SNMPTrap, ai channel-09 in slot 6"
::= { slot6-ai-Trap 10 }

slot6Trap-ai-10 NOTIFICATION-TYPE
    STATUS      current
    DESCRIPTION
        "SNMPTrap, ai channel-10 in slot 6"
::= { slot6-ai-Trap 11 }

slot6Trap-ai-11 NOTIFICATION-TYPE
    STATUS      current
    DESCRIPTION
        "SNMPTrap, ai channel-11 in slot 6"
::= { slot6-ai-Trap 12 }

slot6Trap-ai-12 NOTIFICATION-TYPE
    STATUS      current
    DESCRIPTION
        "SNMPTrap, ai channel-12 in slot 6"
::= { slot6-ai-Trap 13 }

slot6Trap-ai-13 NOTIFICATION-TYPE
    STATUS      current
    DESCRIPTION
        "SNMPTrap, ai channel-13 in slot 6"
::= { slot6-ai-Trap 14 }

slot6Trap-ai-14 NOTIFICATION-TYPE
    STATUS      current
    DESCRIPTION
        "SNMPTrap, ai channel-14 in slot 6"
::= { slot6-ai-Trap 15 }

slot6Trap-ai-15 NOTIFICATION-TYPE
    STATUS      current
    DESCRIPTION
        "SNMPTrap, ai channel-15 in slot 6"
::= { slot6-ai-Trap 16 }

----------------------------------------------------------------
-- 1.3.6.1.4.1.8691.10.2500.71.6
    slot6-ao-Trap OBJECT IDENTIFIER ::= { slot6-io-Trap 6 }
----------------------------------------------------------------

slot6Trap-ao-00 NOTIFICATION-TYPE
    STATUS      current
    DESCRIPTION
        "SNMPTrap, ao channel-00 in slot 6"
::= { slot6-ao-Trap 1 }

slot6Trap-ao-01 NOTIFICATION-TYPE
    STATUS      current
    DESCRIPTION
        "SNMPTrap, ao channel-01 in slot 6"
::= { slot6-ao-Trap 2 }

slot6Trap-ao-02 NOTIFICATION-TYPE
    STATUS      current
    DESCRIPTION
        "SNMPTrap, ao channel-02 in slot 6"
::= { slot6-ao-Trap 3 }

slot6Trap-ao-03 NOTIFICATION-TYPE
    STATUS      current
    DESCRIPTION
        "SNMPTrap, ao channel-03 in slot 6"
::= { slot6-ao-Trap 4 }

slot6Trap-ao-04 NOTIFICATION-TYPE
    STATUS      current
    DESCRIPTION
        "SNMPTrap, ao channel-04 in slot 6"
::= { slot6-ao-Trap 5 }

slot6Trap-ao-05 NOTIFICATION-TYPE
    STATUS      current
    DESCRIPTION
        "SNMPTrap, ao channel-05 in slot 6"
::= { slot6-ao-Trap 6 }

slot6Trap-ao-06 NOTIFICATION-TYPE
    STATUS      current
    DESCRIPTION
        "SNMPTrap, ao channel-06 in slot 6"
::= { slot6-ao-Trap 7 }

slot6Trap-ao-07 NOTIFICATION-TYPE
    STATUS      current
    DESCRIPTION
        "SNMPTrap, ao channel-07 in slot 6"
::= { slot6-ao-Trap 8 }

slot6Trap-ao-08 NOTIFICATION-TYPE
    STATUS      current
    DESCRIPTION
        "SNMPTrap, ao channel-08 in slot 6"
::= { slot6-ao-Trap 9 }

slot6Trap-ao-09 NOTIFICATION-TYPE
    STATUS      current
    DESCRIPTION
        "SNMPTrap, ao channel-09 in slot 6"
::= { slot6-ao-Trap 10 }

slot6Trap-ao-10 NOTIFICATION-TYPE
    STATUS      current
    DESCRIPTION
        "SNMPTrap, ao channel-10 in slot 6"
::= { slot6-ao-Trap 11 }

slot6Trap-ao-11 NOTIFICATION-TYPE
    STATUS      current
    DESCRIPTION
        "SNMPTrap, ao channel-11 in slot 6"
::= { slot6-ao-Trap 12 }

slot6Trap-ao-12 NOTIFICATION-TYPE
    STATUS      current
    DESCRIPTION
        "SNMPTrap, ao channel-12 in slot 6"
::= { slot6-ao-Trap 13 }

slot6Trap-ao-13 NOTIFICATION-TYPE
    STATUS      current
    DESCRIPTION
        "SNMPTrap, ao channel-13 in slot 6"
::= { slot6-ao-Trap 14 }

slot6Trap-ao-14 NOTIFICATION-TYPE
    STATUS      current
    DESCRIPTION
        "SNMPTrap, ao channel-14 in slot 6"
::= { slot6-ao-Trap 15 }

slot6Trap-ao-15 NOTIFICATION-TYPE
    STATUS      current
    DESCRIPTION
        "SNMPTrap, ao channel-15 in slot 6"
::= { slot6-ao-Trap 16 }

----------------------------------------------------------------
-- 1.3.6.1.4.1.8691.10.2500.71.7
    slot6-rtd-Trap OBJECT IDENTIFIER ::= { slot6-io-Trap 7 }
----------------------------------------------------------------

slot6Trap-rtd-00 NOTIFICATION-TYPE
    STATUS      current
    DESCRIPTION
        "SNMPTrap, rtd channel-00 in slot 6"
::= { slot6-rtd-Trap 1 }

slot6Trap-rtd-01 NOTIFICATION-TYPE
    STATUS      current
    DESCRIPTION
        "SNMPTrap, rtd channel-01 in slot 6"
::= { slot6-rtd-Trap 2 }

slot6Trap-rtd-02 NOTIFICATION-TYPE
    STATUS      current
    DESCRIPTION
        "SNMPTrap, rtd channel-02 in slot 6"
::= { slot6-rtd-Trap 3 }

slot6Trap-rtd-03 NOTIFICATION-TYPE
    STATUS      current
    DESCRIPTION
        "SNMPTrap, rtd channel-03 in slot 6"
::= { slot6-rtd-Trap 4 }

slot6Trap-rtd-04 NOTIFICATION-TYPE
    STATUS      current
    DESCRIPTION
        "SNMPTrap, rtd channel-04 in slot 6"
::= { slot6-rtd-Trap 5 }

slot6Trap-rtd-05 NOTIFICATION-TYPE
    STATUS      current
    DESCRIPTION
        "SNMPTrap, rtd channel-05 in slot 6"
::= { slot6-rtd-Trap 6 }

slot6Trap-rtd-06 NOTIFICATION-TYPE
    STATUS      current
    DESCRIPTION
        "SNMPTrap, rtd channel-06 in slot 6"
::= { slot6-rtd-Trap 7 }

slot6Trap-rtd-07 NOTIFICATION-TYPE
    STATUS      current
    DESCRIPTION
        "SNMPTrap, rtd channel-07 in slot 6"
::= { slot6-rtd-Trap 8 }

slot6Trap-rtd-08 NOTIFICATION-TYPE
    STATUS      current
    DESCRIPTION
        "SNMPTrap, rtd channel-08 in slot 6"
::= { slot6-rtd-Trap 9 }

slot6Trap-rtd-09 NOTIFICATION-TYPE
    STATUS      current
    DESCRIPTION
        "SNMPTrap, rtd channel-09 in slot 6"
::= { slot6-rtd-Trap 10 }

slot6Trap-rtd-10 NOTIFICATION-TYPE
    STATUS      current
    DESCRIPTION
        "SNMPTrap, rtd channel-10 in slot 6"
::= { slot6-rtd-Trap 11 }

slot6Trap-rtd-11 NOTIFICATION-TYPE
    STATUS      current
    DESCRIPTION
        "SNMPTrap, rtd channel-11 in slot 6"
::= { slot6-rtd-Trap 12 }

slot6Trap-rtd-12 NOTIFICATION-TYPE
    STATUS      current
    DESCRIPTION
        "SNMPTrap, rtd channel-12 in slot 6"
::= { slot6-rtd-Trap 13 }

slot6Trap-rtd-13 NOTIFICATION-TYPE
    STATUS      current
    DESCRIPTION
        "SNMPTrap, rtd channel-13 in slot 6"
::= { slot6-rtd-Trap 14 }

slot6Trap-rtd-14 NOTIFICATION-TYPE
    STATUS      current
    DESCRIPTION
        "SNMPTrap, rtd channel-14 in slot 6"
::= { slot6-rtd-Trap 15 }

slot6Trap-rtd-15 NOTIFICATION-TYPE
    STATUS      current
    DESCRIPTION
        "SNMPTrap, rtd channel-15 in slot 6"
::= { slot6-rtd-Trap 16 }

----------------------------------------------------------------
-- 1.3.6.1.4.1.8691.10.2500.71.8
    slot6-tc-Trap OBJECT IDENTIFIER ::= { slot6-io-Trap 8 }
----------------------------------------------------------------

slot6Trap-tc-00 NOTIFICATION-TYPE
    STATUS      current
    DESCRIPTION
        "SNMPTrap, tc channel-00 in slot 6"
::= { slot6-tc-Trap 1 }

slot6Trap-tc-01 NOTIFICATION-TYPE
    STATUS      current
    DESCRIPTION
        "SNMPTrap, tc channel-01 in slot 6"
::= { slot6-tc-Trap 2 }

slot6Trap-tc-02 NOTIFICATION-TYPE
    STATUS      current
    DESCRIPTION
        "SNMPTrap, tc channel-02 in slot 6"
::= { slot6-tc-Trap 3 }

slot6Trap-tc-03 NOTIFICATION-TYPE
    STATUS      current
    DESCRIPTION
        "SNMPTrap, tc channel-03 in slot 6"
::= { slot6-tc-Trap 4 }

slot6Trap-tc-04 NOTIFICATION-TYPE
    STATUS      current
    DESCRIPTION
        "SNMPTrap, tc channel-04 in slot 6"
::= { slot6-tc-Trap 5 }

slot6Trap-tc-05 NOTIFICATION-TYPE
    STATUS      current
    DESCRIPTION
        "SNMPTrap, tc channel-05 in slot 6"
::= { slot6-tc-Trap 6 }

slot6Trap-tc-06 NOTIFICATION-TYPE
    STATUS      current
    DESCRIPTION
        "SNMPTrap, tc channel-06 in slot 6"
::= { slot6-tc-Trap 7 }

slot6Trap-tc-07 NOTIFICATION-TYPE
    STATUS      current
    DESCRIPTION
        "SNMPTrap, tc channel-07 in slot 6"
::= { slot6-tc-Trap 8 }

slot6Trap-tc-08 NOTIFICATION-TYPE
    STATUS      current
    DESCRIPTION
        "SNMPTrap, tc channel-08 in slot 6"
::= { slot6-tc-Trap 9 }

slot6Trap-tc-09 NOTIFICATION-TYPE
    STATUS      current
    DESCRIPTION
        "SNMPTrap, tc channel-09 in slot 6"
::= { slot6-tc-Trap 10 }

slot6Trap-tc-10 NOTIFICATION-TYPE
    STATUS      current
    DESCRIPTION
        "SNMPTrap, tc channel-10 in slot 6"
::= { slot6-tc-Trap 11 }

slot6Trap-tc-11 NOTIFICATION-TYPE
    STATUS      current
    DESCRIPTION
        "SNMPTrap, tc channel-11 in slot 6"
::= { slot6-tc-Trap 12 }

slot6Trap-tc-12 NOTIFICATION-TYPE
    STATUS      current
    DESCRIPTION
        "SNMPTrap, tc channel-12 in slot 6"
::= { slot6-tc-Trap 13 }

slot6Trap-tc-13 NOTIFICATION-TYPE
    STATUS      current
    DESCRIPTION
        "SNMPTrap, tc channel-13 in slot 6"
::= { slot6-tc-Trap 14 }

slot6Trap-tc-14 NOTIFICATION-TYPE
    STATUS      current
    DESCRIPTION
        "SNMPTrap, tc channel-14 in slot 6"
::= { slot6-tc-Trap 15 }

slot6Trap-tc-15 NOTIFICATION-TYPE
    STATUS      current
    DESCRIPTION
        "SNMPTrap, tc channel-15 in slot 6"
::= { slot6-tc-Trap 16 }			
		
		
----------------------------------------------------------------
-- 1.3.6.1.4.1.8691.10.2500.80
    slot7-io OBJECT IDENTIFIER ::= { ioLogik2500 80 }
----------------------------------------------------------------
-- slot 7 DI
slot7-diTable OBJECT-TYPE
		SYNTAX 			SEQUENCE OF Slot7-diDef
		MAX-ACCESS 		not-accessible
		STATUS 			current
		DESCRIPTION		"The di channel table"
		::= { slot7-io 1 }

slot7-di OBJECT-TYPE
		SYNTAX 			Slot7-diDef
		MAX-ACCESS 		not-accessible
		STATUS 			current
		DESCRIPTION		"The di channel item"
		INDEX { slot7-diIndex }
		::= { slot7-diTable 1 }

Slot7-diDef ::= SEQUENCE { 
    	slot7-diIndex		INTEGER,
		slot7-diStatus		Unsigned32,
		slot7-diCounterReset2Init INTEGER		
		}  

slot7-diIndex OBJECT-TYPE
		SYNTAX 			INTEGER (0..15)
		MAX-ACCESS 		read-only
		STATUS 			current
		DESCRIPTION		"The channel index"
		::= { slot7-di 1 }
		
slot7-diStatus OBJECT-TYPE
		SYNTAX 			Unsigned32
		MAX-ACCESS 		read-write
		STATUS 			current
		DESCRIPTION		"The channel di status. 0=off, 1=on in di mode or n=counter value in counter mode"
		::= { slot7-di 2 }
		
slot7-diCounterReset2Init OBJECT-TYPE
		SYNTAX 			INTEGER 
		MAX-ACCESS 		read-write
		STATUS 			current
		DESCRIPTION		"Trigger counter to initial value. 1=Reset counter to initial value"
		::= { slot7-di 3 }

-- slot 7 DICounterStart
slot7-diCounterStartTable OBJECT-TYPE
		SYNTAX 			SEQUENCE OF Slot7-diCounterStartDef
		MAX-ACCESS 		not-accessible
		STATUS 			current
		DESCRIPTION		"The counter table starting for di"
		::= { slot7-io 39 }

slot7-diCounterStart OBJECT-TYPE
		SYNTAX 			Slot7-diCounterStartDef
		MAX-ACCESS 		not-accessible
		STATUS 			current
		DESCRIPTION		"The counter starting of di item"
		INDEX { slot7-diCounterStartIndex }
		::= { slot7-diCounterStartTable 1 }

Slot7-diCounterStartDef ::= SEQUENCE { 
    		slot7-diCounterStartIndex		INTEGER,
			slot7-diCounterStartStatus		INTEGER	
		}  

slot7-diCounterStartIndex OBJECT-TYPE
		SYNTAX 			INTEGER (0..15)
		MAX-ACCESS 		read-only
		STATUS 			current
		DESCRIPTION		"The channel index for di counter start"
		::= { slot7-diCounterStart 1 }
		
slot7-diCounterStartStatus OBJECT-TYPE
		SYNTAX 			INTEGER (0..1)
		MAX-ACCESS 		read-write
		STATUS 			current
		DESCRIPTION		"The channel status for di counter start. 0=stop, 1=start"
		::= { slot7-diCounterStart 2 } 
		
				
-- slot 7 DO
slot7-doTable OBJECT-TYPE
		SYNTAX 			SEQUENCE OF Slot7-doDef
		MAX-ACCESS 		not-accessible
		STATUS 			current
		DESCRIPTION		"The do channel table"
		::= { slot7-io 2 }

slot7-do OBJECT-TYPE
		SYNTAX 			Slot7-doDef
		MAX-ACCESS 		not-accessible
		STATUS 			current
		DESCRIPTION		"The do channel item"
		INDEX { slot7-doIndex }
		::= { slot7-doTable 1 }

Slot7-doDef ::= SEQUENCE { 
    	slot7-doIndex		INTEGER,
		slot7-doStatus		INTEGER		
		}  

slot7-doIndex OBJECT-TYPE
		SYNTAX 			INTEGER (0..15)
		MAX-ACCESS 		read-only
		STATUS 			current
		DESCRIPTION		"The channel index"
		::= { slot7-do 1 }
		
slot7-doStatus OBJECT-TYPE
		SYNTAX 			INTEGER (0..1)
		MAX-ACCESS 		read-write
		STATUS 			current
		DESCRIPTION		"The channel do status. 0=off, 1=on in do mode or 0=stop, 1=start in pulse mode"
		::= { slot7-do 2 }  

-- slot 7 DIO
slot7-dioTable OBJECT-TYPE
		SYNTAX 			SEQUENCE OF Slot7-dioDef
		MAX-ACCESS 		not-accessible
		STATUS 			current
		DESCRIPTION		"The dio channel table"
		::= { slot7-io 3 }

slot7-dio OBJECT-TYPE
		SYNTAX 			Slot7-dioDef
		MAX-ACCESS 		not-accessible
		STATUS 			current
		DESCRIPTION		"The dio channel item"
		INDEX { slot7-dioIndex }
		::= { slot7-dioTable 1 }

Slot7-dioDef ::= SEQUENCE { 
    	slot7-dioIndex		INTEGER,
		slot7-dioStatus		Unsigned32,
		slot7-dioCounterReset2Init INTEGER			
		}  

slot7-dioIndex OBJECT-TYPE
		SYNTAX 			INTEGER (0..15)
		MAX-ACCESS 		read-only
		STATUS 			current
		DESCRIPTION		"The channel index"
		::= { slot7-dio 1 }
		
slot7-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot7-dio 2 } 

slot7-dioCounterReset2Init OBJECT-TYPE
		SYNTAX 			INTEGER 
		MAX-ACCESS 		read-write
		STATUS 			current
		DESCRIPTION		"Trigger counter to initial value. 1=Reset counter to initial value"
		::= { slot7-dio 3 }		

-- slot 7 DIOCounterStart
slot7-dioCounterStartTable OBJECT-TYPE
		SYNTAX 			SEQUENCE OF Slot7-dioCounterStartDef
		MAX-ACCESS 		not-accessible
		STATUS 			current
		DESCRIPTION		"The counter table starting for dio"
		::= { slot7-io 46 }

slot7-dioCounterStart OBJECT-TYPE
		SYNTAX 			Slot7-dioCounterStartDef
		MAX-ACCESS 		not-accessible
		STATUS 			current
		DESCRIPTION		"The counter starting of dio item"
		INDEX { slot7-dioCounterStartIndex }
		::= { slot7-dioCounterStartTable 1 }

Slot7-dioCounterStartDef ::= SEQUENCE { 
    	slot7-dioCounterStartIndex		INTEGER,
		slot7-dioCounterStartStatus		INTEGER	
		}  

slot7-dioCounterStartIndex OBJECT-TYPE
		SYNTAX 			INTEGER (0..15)
		MAX-ACCESS 		read-only
		STATUS 			current
		DESCRIPTION		"The channel index for dio counter start"
		::= { slot7-dioCounterStart 1 }
		
slot7-dioCounterStartStatus OBJECT-TYPE
		SYNTAX 			INTEGER (0..1)
		MAX-ACCESS 		read-write
		STATUS 			current
		DESCRIPTION		"The channel status for dio counter start. 0=stop, 1=start"
		::= { slot7-dioCounterStart 2 }  		

		
-- slot 7 Relay
slot7-relayTable OBJECT-TYPE
		SYNTAX 			SEQUENCE OF Slot7-relayDef
		MAX-ACCESS 		not-accessible
		STATUS 			current
		DESCRIPTION		"The relay channel table"
		::= { slot7-io 4 }

slot7-relay OBJECT-TYPE
		SYNTAX 			Slot7-relayDef
		MAX-ACCESS 		not-accessible
		STATUS 			current
		DESCRIPTION		"The relay channel item"
		INDEX { slot7-relayIndex }
		::= { slot7-relayTable 1 }

Slot7-relayDef ::= SEQUENCE { 
    	slot7-relayIndex		INTEGER,
		slot7-relayStatus		INTEGER		
		}  

slot7-relayIndex OBJECT-TYPE
		SYNTAX 			INTEGER (0..15)
		MAX-ACCESS 		read-only
		STATUS 			current
		DESCRIPTION		"The channel index"
		::= { slot7-relay 1 }
		
slot7-relayStatus OBJECT-TYPE
		SYNTAX 			INTEGER (0..1)
		MAX-ACCESS 		read-write
		STATUS 			current
		DESCRIPTION		"The channel relay status. 0=off, 1=on in do mode or 0=stop, 1=start in pulse mode"
		::= { slot7-relay 2 }  

-- slot 7 AI
slot7-aiTable OBJECT-TYPE
		SYNTAX 			SEQUENCE OF Slot7-aiDef
		MAX-ACCESS 		not-accessible
		STATUS 			current
		DESCRIPTION		"The ai channel table"
		::= { slot7-io 5 }

slot7-ai OBJECT-TYPE
		SYNTAX 			Slot7-aiDef
		MAX-ACCESS 		not-accessible
		STATUS 			current
		DESCRIPTION		"The ai channel item"
		INDEX { slot7-aiIndex }
		::= { slot7-aiTable 1 }

Slot7-aiDef ::= SEQUENCE { 
    	slot7-aiIndex		INTEGER,
		slot7-aiStatus		OCTET STRING,
		slot7-aiBurnoutStatus INTEGER		
		}  

slot7-aiIndex OBJECT-TYPE
		SYNTAX 			INTEGER (0..15)
		MAX-ACCESS 		read-only
		STATUS 			current
		DESCRIPTION		"The channel index"
		::= { slot7-ai 1 }
		
slot7-aiStatus OBJECT-TYPE
		SYNTAX 			OCTET STRING
		MAX-ACCESS 		read-only
		STATUS 			current
		DESCRIPTION		"The channel ai scaled value"
		::= { slot7-ai 2 }

slot7-aiBurnoutStatus OBJECT-TYPE
		SYNTAX 			INTEGER (0..3)
		MAX-ACCESS 		read-only
		STATUS 			current
		DESCRIPTION		"The channel of burnout status (0: normal, 1: burnout, 2: underange, 3: overange)"
		::= { slot7-ai 3 }  				

-- slot 7 AO
slot7-aoTable OBJECT-TYPE
		SYNTAX 			SEQUENCE OF Slot7-aoDef
		MAX-ACCESS 		not-accessible
		STATUS 			current
		DESCRIPTION		"The ao channel table"
		::= { slot7-io 6 }

slot7-ao OBJECT-TYPE
		SYNTAX 			Slot7-aoDef
		MAX-ACCESS 		not-accessible
		STATUS 			current
		DESCRIPTION		"The ao channel item"
		INDEX { slot7-aoIndex }
		::= { slot7-aoTable 1 }

Slot7-aoDef ::= SEQUENCE { 
    	slot7-aoIndex		INTEGER,
		slot7-aoStatus		OCTET STRING		
		}  

slot7-aoIndex OBJECT-TYPE
		SYNTAX 			INTEGER (0..15)
		MAX-ACCESS 		read-only
		STATUS 			current
		DESCRIPTION		"The channel index"
		::= { slot7-ao 1 }
		
slot7-aoStatus OBJECT-TYPE
		SYNTAX 			OCTET STRING
		MAX-ACCESS 		read-write
		STATUS 			current
		DESCRIPTION		"The channel ao scaled value"
		::= { slot7-ao 2 }  

-- slot 7 RTD
slot7-rtdTable OBJECT-TYPE
		SYNTAX 			SEQUENCE OF Slot7-rtdDef
		MAX-ACCESS 		not-accessible
		STATUS 			current
		DESCRIPTION		"The rtd channel table"
		::= { slot7-io 7 }

slot7-rtd OBJECT-TYPE
		SYNTAX 			Slot7-rtdDef
		MAX-ACCESS 		not-accessible
		STATUS 			current
		DESCRIPTION		"The rtd channel item"
		INDEX { slot7-rtdIndex }
		::= { slot7-rtdTable 1 }

Slot7-rtdDef ::= SEQUENCE { 
    	slot7-rtdIndex		INTEGER,
		slot7-rtdStatus		OCTET STRING		
		}  

slot7-rtdIndex OBJECT-TYPE
		SYNTAX 			INTEGER (0..15)
		MAX-ACCESS 		read-only
		STATUS 			current
		DESCRIPTION		"The channel index"
		::= { slot7-rtd 1 }
		
slot7-rtdStatus OBJECT-TYPE
		SYNTAX 			OCTET STRING
		MAX-ACCESS 		read-only
		STATUS 			current
		DESCRIPTION		"The channel rtd scaled value"
		::= { slot7-rtd 2 }  

-- slot 7 TC
slot7-tcTable OBJECT-TYPE
		SYNTAX 			SEQUENCE OF Slot7-tcDef
		MAX-ACCESS 		not-accessible
		STATUS 			current
		DESCRIPTION		"The tc channel table"
		::= { slot7-io 8 }

slot7-tc OBJECT-TYPE
		SYNTAX 			Slot7-tcDef
		MAX-ACCESS 		not-accessible
		STATUS 			current
		DESCRIPTION		"The tc channel item"
		INDEX { slot7-tcIndex }
		::= { slot7-tcTable 1 }

Slot7-tcDef ::= SEQUENCE { 
    		slot7-tcIndex		INTEGER,
		slot7-tcStatus		OCTET STRING		
		}  

slot7-tcIndex OBJECT-TYPE
		SYNTAX 			INTEGER (0..15)
		MAX-ACCESS 		read-only
		STATUS 			current
		DESCRIPTION		"The channel index"
		::= { slot7-tc 1 }
		
slot7-tcStatus OBJECT-TYPE
		SYNTAX 			OCTET STRING
		MAX-ACCESS 		read-only
		STATUS 			current
		DESCRIPTION		"The channel tc scaled value"
		::= { slot7-tc 2 }  


----------------------------------------------------------------
-- 1.3.6.1.4.1.8691.10.2500.81
    slot7-io-Trap OBJECT IDENTIFIER ::= { ioLogik2500 81 }
----------------------------------------------------------------

----------------------------------------------------------------
-- 1.3.6.1.4.1.8691.10.2500.81.1
    slot7-di-Trap OBJECT IDENTIFIER ::= { slot7-io-Trap 1 }
----------------------------------------------------------------

slot7Trap-di-00 NOTIFICATION-TYPE
    STATUS      current
    DESCRIPTION
        "SNMPTrap, di channel-00 in slot 7"
::= { slot7-di-Trap 1 }

slot7Trap-di-01 NOTIFICATION-TYPE
    STATUS      current
    DESCRIPTION
        "SNMPTrap, di channel-01 in slot 7"
::= { slot7-di-Trap 2 }

slot7Trap-di-02 NOTIFICATION-TYPE
    STATUS      current
    DESCRIPTION
        "SNMPTrap, di channel-02 in slot 7"
::= { slot7-di-Trap 3 }

slot7Trap-di-03 NOTIFICATION-TYPE
    STATUS      current
    DESCRIPTION
        "SNMPTrap, di channel-03 in slot 7"
::= { slot7-di-Trap 4 }

slot7Trap-di-04 NOTIFICATION-TYPE
    STATUS      current
    DESCRIPTION
        "SNMPTrap, di channel-04 in slot 7"
::= { slot7-di-Trap 5 }

slot7Trap-di-05 NOTIFICATION-TYPE
    STATUS      current
    DESCRIPTION
        "SNMPTrap, di channel-05 in slot 7"
::= { slot7-di-Trap 6 }

slot7Trap-di-06 NOTIFICATION-TYPE
    STATUS      current
    DESCRIPTION
        "SNMPTrap, di channel-06 in slot 7"
::= { slot7-di-Trap 7 }

slot7Trap-di-07 NOTIFICATION-TYPE
    STATUS      current
    DESCRIPTION
        "SNMPTrap, di channel-07 in slot 7"
::= { slot7-di-Trap 8 }

slot7Trap-di-08 NOTIFICATION-TYPE
    STATUS      current
    DESCRIPTION
        "SNMPTrap, di channel-08 in slot 7"
::= { slot7-di-Trap 9 }

slot7Trap-di-09 NOTIFICATION-TYPE
    STATUS      current
    DESCRIPTION
        "SNMPTrap, di channel-09 in slot 7"
::= { slot7-di-Trap 10 }

slot7Trap-di-10 NOTIFICATION-TYPE
    STATUS      current
    DESCRIPTION
        "SNMPTrap, di channel-10 in slot 7"
::= { slot7-di-Trap 11 }

slot7Trap-di-11 NOTIFICATION-TYPE
    STATUS      current
    DESCRIPTION
        "SNMPTrap, di channel-11 in slot 7"
::= { slot7-di-Trap 12 }

slot7Trap-di-12 NOTIFICATION-TYPE
    STATUS      current
    DESCRIPTION
        "SNMPTrap, di channel-12 in slot 7"
::= { slot7-di-Trap 13 }

slot7Trap-di-13 NOTIFICATION-TYPE
    STATUS      current
    DESCRIPTION
        "SNMPTrap, di channel-13 in slot 7"
::= { slot7-di-Trap 14 }

slot7Trap-di-14 NOTIFICATION-TYPE
    STATUS      current
    DESCRIPTION
        "SNMPTrap, di channel-14 in slot 7"
::= { slot7-di-Trap 15 }

slot7Trap-di-15 NOTIFICATION-TYPE
    STATUS      current
    DESCRIPTION
        "SNMPTrap, di channel-15 in slot 7"
::= { slot7-di-Trap 16 }
----------------------------------------------------------------
-- 1.3.6.1.4.1.8691.10.2500.81.2
    slot7-do-Trap OBJECT IDENTIFIER ::= { slot7-io-Trap 2 }
----------------------------------------------------------------

slot7Trap-do-00 NOTIFICATION-TYPE
    STATUS      current
    DESCRIPTION
        "SNMPTrap, do channel-00 in slot 7"
::= { slot7-do-Trap 1 }

slot7Trap-do-01 NOTIFICATION-TYPE
    STATUS      current
    DESCRIPTION
        "SNMPTrap, do channel-01 in slot 7"
::= { slot7-do-Trap 2 }

slot7Trap-do-02 NOTIFICATION-TYPE
    STATUS      current
    DESCRIPTION
        "SNMPTrap, do channel-02 in slot 7"
::= { slot7-do-Trap 3 }

slot7Trap-do-03 NOTIFICATION-TYPE
    STATUS      current
    DESCRIPTION
        "SNMPTrap, do channel-03 in slot 7"
::= { slot7-do-Trap 4 }

slot7Trap-do-04 NOTIFICATION-TYPE
    STATUS      current
    DESCRIPTION
        "SNMPTrap, do channel-04 in slot 7"
::= { slot7-do-Trap 5 }

slot7Trap-do-05 NOTIFICATION-TYPE
    STATUS      current
    DESCRIPTION
        "SNMPTrap, do channel-05 in slot 7"
::= { slot7-do-Trap 6 }

slot7Trap-do-06 NOTIFICATION-TYPE
    STATUS      current
    DESCRIPTION
        "SNMPTrap, do channel-06 in slot 7"
::= { slot7-do-Trap 7 }

slot7Trap-do-07 NOTIFICATION-TYPE
    STATUS      current
    DESCRIPTION
        "SNMPTrap, do channel-07 in slot 7"
::= { slot7-do-Trap 8 }

slot7Trap-do-08 NOTIFICATION-TYPE
    STATUS      current
    DESCRIPTION
        "SNMPTrap, do channel-08 in slot 7"
::= { slot7-do-Trap 9 }

slot7Trap-do-09 NOTIFICATION-TYPE
    STATUS      current
    DESCRIPTION
        "SNMPTrap, do channel-09 in slot 7"
::= { slot7-do-Trap 10 }

slot7Trap-do-10 NOTIFICATION-TYPE
    STATUS      current
    DESCRIPTION
        "SNMPTrap, do channel-10 in slot 7"
::= { slot7-do-Trap 11 }

slot7Trap-do-11 NOTIFICATION-TYPE
    STATUS      current
    DESCRIPTION
        "SNMPTrap, do channel-11 in slot 7"
::= { slot7-do-Trap 12 }

slot7Trap-do-12 NOTIFICATION-TYPE
    STATUS      current
    DESCRIPTION
        "SNMPTrap, do channel-12 in slot 7"
::= { slot7-do-Trap 13 }

slot7Trap-do-13 NOTIFICATION-TYPE
    STATUS      current
    DESCRIPTION
        "SNMPTrap, do channel-13 in slot 7"
::= { slot7-do-Trap 14 }

slot7Trap-do-14 NOTIFICATION-TYPE
    STATUS      current
    DESCRIPTION
        "SNMPTrap, do channel-14 in slot 7"
::= { slot7-do-Trap 15 }

slot7Trap-do-15 NOTIFICATION-TYPE
    STATUS      current
    DESCRIPTION
        "SNMPTrap, do channel-15 in slot 7"
::= { slot7-do-Trap 16 }

----------------------------------------------------------------
-- 1.3.6.1.4.1.8691.10.2500.81.3
    slot7-dio-Trap OBJECT IDENTIFIER ::= { slot7-io-Trap 3 }
----------------------------------------------------------------

slot7Trap-dio-00 NOTIFICATION-TYPE
    STATUS      current
    DESCRIPTION
        "SNMPTrap, dio channel-00 in slot 7"
::= { slot7-dio-Trap 1 }

slot7Trap-dio-01 NOTIFICATION-TYPE
    STATUS      current
    DESCRIPTION
        "SNMPTrap, dio channel-01 in slot 7"
::= { slot7-dio-Trap 2 }

slot7Trap-dio-02 NOTIFICATION-TYPE
    STATUS      current
    DESCRIPTION
        "SNMPTrap, dio channel-02 in slot 7"
::= { slot7-dio-Trap 3 }

slot7Trap-dio-03 NOTIFICATION-TYPE
    STATUS      current
    DESCRIPTION
        "SNMPTrap, dio channel-03 in slot 7"
::= { slot7-dio-Trap 4 }

slot7Trap-dio-04 NOTIFICATION-TYPE
    STATUS      current
    DESCRIPTION
        "SNMPTrap, dio channel-04 in slot 7"
::= { slot7-dio-Trap 5 }

slot7Trap-dio-05 NOTIFICATION-TYPE
    STATUS      current
    DESCRIPTION
        "SNMPTrap, dio channel-05 in slot 7"
::= { slot7-dio-Trap 6 }

slot7Trap-dio-06 NOTIFICATION-TYPE
    STATUS      current
    DESCRIPTION
        "SNMPTrap, dio channel-06 in slot 7"
::= { slot7-dio-Trap 7 }

slot7Trap-dio-07 NOTIFICATION-TYPE
    STATUS      current
    DESCRIPTION
        "SNMPTrap, dio channel-07 in slot 7"
::= { slot7-dio-Trap 8 }

slot7Trap-dio-08 NOTIFICATION-TYPE
    STATUS      current
    DESCRIPTION
        "SNMPTrap, dio channel-08 in slot 7"
::= { slot7-dio-Trap 9 }

slot7Trap-dio-09 NOTIFICATION-TYPE
    STATUS      current
    DESCRIPTION
        "SNMPTrap, dio channel-09 in slot 7"
::= { slot7-dio-Trap 10 }

slot7Trap-dio-10 NOTIFICATION-TYPE
    STATUS      current
    DESCRIPTION
        "SNMPTrap, dio channel-10 in slot 7"
::= { slot7-dio-Trap 11 }

slot7Trap-dio-11 NOTIFICATION-TYPE
    STATUS      current
    DESCRIPTION
        "SNMPTrap, dio channel-11 in slot 7"
::= { slot7-dio-Trap 12 }

slot7Trap-dio-12 NOTIFICATION-TYPE
    STATUS      current
    DESCRIPTION
        "SNMPTrap, dio channel-12 in slot 7"
::= { slot7-dio-Trap 13 }

slot7Trap-dio-13 NOTIFICATION-TYPE
    STATUS      current
    DESCRIPTION
        "SNMPTrap, dio channel-13 in slot 7"
::= { slot7-dio-Trap 14 }

slot7Trap-dio-14 NOTIFICATION-TYPE
    STATUS      current
    DESCRIPTION
        "SNMPTrap, dio channel-14 in slot 7"
::= { slot7-dio-Trap 15 }

slot7Trap-dio-15 NOTIFICATION-TYPE
    STATUS      current
    DESCRIPTION
        "SNMPTrap, dio channel-15 in slot 7"
::= { slot7-dio-Trap 16 }

----------------------------------------------------------------
-- 1.3.6.1.4.1.8691.10.2500.81.4
    slot7-relay-Trap OBJECT IDENTIFIER ::= { slot7-io-Trap 4 }
----------------------------------------------------------------

slot7Trap-relay-00 NOTIFICATION-TYPE
    STATUS      current
    DESCRIPTION
        "SNMPTrap, relay channel-00 in slot 7"
::= { slot7-relay-Trap 1 }

slot7Trap-relay-01 NOTIFICATION-TYPE
    STATUS      current
    DESCRIPTION
        "SNMPTrap, relay channel-01 in slot 7"
::= { slot7-relay-Trap 2 }

slot7Trap-relay-02 NOTIFICATION-TYPE
    STATUS      current
    DESCRIPTION
        "SNMPTrap, relay channel-02 in slot 7"
::= { slot7-relay-Trap 3 }

slot7Trap-relay-03 NOTIFICATION-TYPE
    STATUS      current
    DESCRIPTION
        "SNMPTrap, relay channel-03 in slot 7"
::= { slot7-relay-Trap 4 }

slot7Trap-relay-04 NOTIFICATION-TYPE
    STATUS      current
    DESCRIPTION
        "SNMPTrap, relay channel-04 in slot 7"
::= { slot7-relay-Trap 5 }

slot7Trap-relay-05 NOTIFICATION-TYPE
    STATUS      current
    DESCRIPTION
        "SNMPTrap, relay channel-05 in slot 7"
::= { slot7-relay-Trap 6 }

slot7Trap-relay-06 NOTIFICATION-TYPE
    STATUS      current
    DESCRIPTION
        "SNMPTrap, relay channel-06 in slot 7"
::= { slot7-relay-Trap 7 }

slot7Trap-relay-07 NOTIFICATION-TYPE
    STATUS      current
    DESCRIPTION
        "SNMPTrap, relay channel-07 in slot 7"
::= { slot7-relay-Trap 8 }

slot7Trap-relay-08 NOTIFICATION-TYPE
    STATUS      current
    DESCRIPTION
        "SNMPTrap, relay channel-08 in slot 7"
::= { slot7-relay-Trap 9 }

slot7Trap-relay-09 NOTIFICATION-TYPE
    STATUS      current
    DESCRIPTION
        "SNMPTrap, relay channel-09 in slot 7"
::= { slot7-relay-Trap 10 }

slot7Trap-relay-10 NOTIFICATION-TYPE
    STATUS      current
    DESCRIPTION
        "SNMPTrap, relay channel-10 in slot 7"
::= { slot7-relay-Trap 11 }

slot7Trap-relay-11 NOTIFICATION-TYPE
    STATUS      current
    DESCRIPTION
        "SNMPTrap, relay channel-11 in slot 7"
::= { slot7-relay-Trap 12 }

slot7Trap-relay-12 NOTIFICATION-TYPE
    STATUS      current
    DESCRIPTION
        "SNMPTrap, relay channel-12 in slot 7"
::= { slot7-relay-Trap 13 }

slot7Trap-relay-13 NOTIFICATION-TYPE
    STATUS      current
    DESCRIPTION
        "SNMPTrap, relay channel-13 in slot 7"
::= { slot7-relay-Trap 14 }

slot7Trap-relay-14 NOTIFICATION-TYPE
    STATUS      current
    DESCRIPTION
        "SNMPTrap, relay channel-14 in slot 7"
::= { slot7-relay-Trap 15 }

slot7Trap-relay-15 NOTIFICATION-TYPE
    STATUS      current
    DESCRIPTION
        "SNMPTrap, relay channel-15 in slot 7"
::= { slot7-relay-Trap 16 }

----------------------------------------------------------------
-- 1.3.6.1.4.1.8691.10.2500.81.5
    slot7-ai-Trap OBJECT IDENTIFIER ::= { slot7-io-Trap 5 }
----------------------------------------------------------------

slot7Trap-ai-00 NOTIFICATION-TYPE
    STATUS      current
    DESCRIPTION
        "SNMPTrap, ai channel-00 in slot 7"
::= { slot7-ai-Trap 1 }

slot7Trap-ai-01 NOTIFICATION-TYPE
    STATUS      current
    DESCRIPTION
        "SNMPTrap, ai channel-01 in slot 7"
::= { slot7-ai-Trap 2 }

slot7Trap-ai-02 NOTIFICATION-TYPE
    STATUS      current
    DESCRIPTION
        "SNMPTrap, ai channel-02 in slot 7"
::= { slot7-ai-Trap 3 }

slot7Trap-ai-03 NOTIFICATION-TYPE
    STATUS      current
    DESCRIPTION
        "SNMPTrap, ai channel-03 in slot 7"
::= { slot7-ai-Trap 4 }

slot7Trap-ai-04 NOTIFICATION-TYPE
    STATUS      current
    DESCRIPTION
        "SNMPTrap, ai channel-04 in slot 7"
::= { slot7-ai-Trap 5 }

slot7Trap-ai-05 NOTIFICATION-TYPE
    STATUS      current
    DESCRIPTION
        "SNMPTrap, ai channel-05 in slot 7"
::= { slot7-ai-Trap 6 }

slot7Trap-ai-06 NOTIFICATION-TYPE
    STATUS      current
    DESCRIPTION
        "SNMPTrap, ai channel-06 in slot 7"
::= { slot7-ai-Trap 7 }

slot7Trap-ai-07 NOTIFICATION-TYPE
    STATUS      current
    DESCRIPTION
        "SNMPTrap, ai channel-07 in slot 7"
::= { slot7-ai-Trap 8 }

slot7Trap-ai-08 NOTIFICATION-TYPE
    STATUS      current
    DESCRIPTION
        "SNMPTrap, ai channel-08 in slot 7"
::= { slot7-ai-Trap 9 }

slot7Trap-ai-09 NOTIFICATION-TYPE
    STATUS      current
    DESCRIPTION
        "SNMPTrap, ai channel-09 in slot 7"
::= { slot7-ai-Trap 10 }

slot7Trap-ai-10 NOTIFICATION-TYPE
    STATUS      current
    DESCRIPTION
        "SNMPTrap, ai channel-10 in slot 7"
::= { slot7-ai-Trap 11 }

slot7Trap-ai-11 NOTIFICATION-TYPE
    STATUS      current
    DESCRIPTION
        "SNMPTrap, ai channel-11 in slot 7"
::= { slot7-ai-Trap 12 }

slot7Trap-ai-12 NOTIFICATION-TYPE
    STATUS      current
    DESCRIPTION
        "SNMPTrap, ai channel-12 in slot 7"
::= { slot7-ai-Trap 13 }

slot7Trap-ai-13 NOTIFICATION-TYPE
    STATUS      current
    DESCRIPTION
        "SNMPTrap, ai channel-13 in slot 7"
::= { slot7-ai-Trap 14 }

slot7Trap-ai-14 NOTIFICATION-TYPE
    STATUS      current
    DESCRIPTION
        "SNMPTrap, ai channel-14 in slot 7"
::= { slot7-ai-Trap 15 }

slot7Trap-ai-15 NOTIFICATION-TYPE
    STATUS      current
    DESCRIPTION
        "SNMPTrap, ai channel-15 in slot 7"
::= { slot7-ai-Trap 16 }

----------------------------------------------------------------
-- 1.3.6.1.4.1.8691.10.2500.81.6
    slot7-ao-Trap OBJECT IDENTIFIER ::= { slot7-io-Trap 6 }
----------------------------------------------------------------

slot7Trap-ao-00 NOTIFICATION-TYPE
    STATUS      current
    DESCRIPTION
        "SNMPTrap, ao channel-00 in slot 7"
::= { slot7-ao-Trap 1 }

slot7Trap-ao-01 NOTIFICATION-TYPE
    STATUS      current
    DESCRIPTION
        "SNMPTrap, ao channel-01 in slot 7"
::= { slot7-ao-Trap 2 }

slot7Trap-ao-02 NOTIFICATION-TYPE
    STATUS      current
    DESCRIPTION
        "SNMPTrap, ao channel-02 in slot 7"
::= { slot7-ao-Trap 3 }

slot7Trap-ao-03 NOTIFICATION-TYPE
    STATUS      current
    DESCRIPTION
        "SNMPTrap, ao channel-03 in slot 7"
::= { slot7-ao-Trap 4 }

slot7Trap-ao-04 NOTIFICATION-TYPE
    STATUS      current
    DESCRIPTION
        "SNMPTrap, ao channel-04 in slot 7"
::= { slot7-ao-Trap 5 }

slot7Trap-ao-05 NOTIFICATION-TYPE
    STATUS      current
    DESCRIPTION
        "SNMPTrap, ao channel-05 in slot 7"
::= { slot7-ao-Trap 6 }

slot7Trap-ao-06 NOTIFICATION-TYPE
    STATUS      current
    DESCRIPTION
        "SNMPTrap, ao channel-06 in slot 7"
::= { slot7-ao-Trap 7 }

slot7Trap-ao-07 NOTIFICATION-TYPE
    STATUS      current
    DESCRIPTION
        "SNMPTrap, ao channel-07 in slot 7"
::= { slot7-ao-Trap 8 }

slot7Trap-ao-08 NOTIFICATION-TYPE
    STATUS      current
    DESCRIPTION
        "SNMPTrap, ao channel-08 in slot 7"
::= { slot7-ao-Trap 9 }

slot7Trap-ao-09 NOTIFICATION-TYPE
    STATUS      current
    DESCRIPTION
        "SNMPTrap, ao channel-09 in slot 7"
::= { slot7-ao-Trap 10 }

slot7Trap-ao-10 NOTIFICATION-TYPE
    STATUS      current
    DESCRIPTION
        "SNMPTrap, ao channel-10 in slot 7"
::= { slot7-ao-Trap 11 }

slot7Trap-ao-11 NOTIFICATION-TYPE
    STATUS      current
    DESCRIPTION
        "SNMPTrap, ao channel-11 in slot 7"
::= { slot7-ao-Trap 12 }

slot7Trap-ao-12 NOTIFICATION-TYPE
    STATUS      current
    DESCRIPTION
        "SNMPTrap, ao channel-12 in slot 7"
::= { slot7-ao-Trap 13 }

slot7Trap-ao-13 NOTIFICATION-TYPE
    STATUS      current
    DESCRIPTION
        "SNMPTrap, ao channel-13 in slot 7"
::= { slot7-ao-Trap 14 }

slot7Trap-ao-14 NOTIFICATION-TYPE
    STATUS      current
    DESCRIPTION
        "SNMPTrap, ao channel-14 in slot 7"
::= { slot7-ao-Trap 15 }

slot7Trap-ao-15 NOTIFICATION-TYPE
    STATUS      current
    DESCRIPTION
        "SNMPTrap, ao channel-15 in slot 7"
::= { slot7-ao-Trap 16 }

----------------------------------------------------------------
-- 1.3.6.1.4.1.8691.10.2500.81.7
    slot7-rtd-Trap OBJECT IDENTIFIER ::= { slot7-io-Trap 7 }
----------------------------------------------------------------

slot7Trap-rtd-00 NOTIFICATION-TYPE
    STATUS      current
    DESCRIPTION
        "SNMPTrap, rtd channel-00 in slot 7"
::= { slot7-rtd-Trap 1 }

slot7Trap-rtd-01 NOTIFICATION-TYPE
    STATUS      current
    DESCRIPTION
        "SNMPTrap, rtd channel-01 in slot 7"
::= { slot7-rtd-Trap 2 }

slot7Trap-rtd-02 NOTIFICATION-TYPE
    STATUS      current
    DESCRIPTION
        "SNMPTrap, rtd channel-02 in slot 7"
::= { slot7-rtd-Trap 3 }

slot7Trap-rtd-03 NOTIFICATION-TYPE
    STATUS      current
    DESCRIPTION
        "SNMPTrap, rtd channel-03 in slot 7"
::= { slot7-rtd-Trap 4 }

slot7Trap-rtd-04 NOTIFICATION-TYPE
    STATUS      current
    DESCRIPTION
        "SNMPTrap, rtd channel-04 in slot 7"
::= { slot7-rtd-Trap 5 }

slot7Trap-rtd-05 NOTIFICATION-TYPE
    STATUS      current
    DESCRIPTION
        "SNMPTrap, rtd channel-05 in slot 7"
::= { slot7-rtd-Trap 6 }

slot7Trap-rtd-06 NOTIFICATION-TYPE
    STATUS      current
    DESCRIPTION
        "SNMPTrap, rtd channel-06 in slot 7"
::= { slot7-rtd-Trap 7 }

slot7Trap-rtd-07 NOTIFICATION-TYPE
    STATUS      current
    DESCRIPTION
        "SNMPTrap, rtd channel-07 in slot 7"
::= { slot7-rtd-Trap 8 }

slot7Trap-rtd-08 NOTIFICATION-TYPE
    STATUS      current
    DESCRIPTION
        "SNMPTrap, rtd channel-08 in slot 7"
::= { slot7-rtd-Trap 9 }

slot7Trap-rtd-09 NOTIFICATION-TYPE
    STATUS      current
    DESCRIPTION
        "SNMPTrap, rtd channel-09 in slot 7"
::= { slot7-rtd-Trap 10 }

slot7Trap-rtd-10 NOTIFICATION-TYPE
    STATUS      current
    DESCRIPTION
        "SNMPTrap, rtd channel-10 in slot 7"
::= { slot7-rtd-Trap 11 }

slot7Trap-rtd-11 NOTIFICATION-TYPE
    STATUS      current
    DESCRIPTION
        "SNMPTrap, rtd channel-11 in slot 7"
::= { slot7-rtd-Trap 12 }

slot7Trap-rtd-12 NOTIFICATION-TYPE
    STATUS      current
    DESCRIPTION
        "SNMPTrap, rtd channel-12 in slot 7"
::= { slot7-rtd-Trap 13 }

slot7Trap-rtd-13 NOTIFICATION-TYPE
    STATUS      current
    DESCRIPTION
        "SNMPTrap, rtd channel-13 in slot 7"
::= { slot7-rtd-Trap 14 }

slot7Trap-rtd-14 NOTIFICATION-TYPE
    STATUS      current
    DESCRIPTION
        "SNMPTrap, rtd channel-14 in slot 7"
::= { slot7-rtd-Trap 15 }

slot7Trap-rtd-15 NOTIFICATION-TYPE
    STATUS      current
    DESCRIPTION
        "SNMPTrap, rtd channel-15 in slot 7"
::= { slot7-rtd-Trap 16 }

----------------------------------------------------------------
-- 1.3.6.1.4.1.8691.10.2500.81.8
    slot7-tc-Trap OBJECT IDENTIFIER ::= { slot7-io-Trap 8 }
----------------------------------------------------------------

slot7Trap-tc-00 NOTIFICATION-TYPE
    STATUS      current
    DESCRIPTION
        "SNMPTrap, tc channel-00 in slot 7"
::= { slot7-tc-Trap 1 }

slot7Trap-tc-01 NOTIFICATION-TYPE
    STATUS      current
    DESCRIPTION
        "SNMPTrap, tc channel-01 in slot 7"
::= { slot7-tc-Trap 2 }

slot7Trap-tc-02 NOTIFICATION-TYPE
    STATUS      current
    DESCRIPTION
        "SNMPTrap, tc channel-02 in slot 7"
::= { slot7-tc-Trap 3 }

slot7Trap-tc-03 NOTIFICATION-TYPE
    STATUS      current
    DESCRIPTION
        "SNMPTrap, tc channel-03 in slot 7"
::= { slot7-tc-Trap 4 }

slot7Trap-tc-04 NOTIFICATION-TYPE
    STATUS      current
    DESCRIPTION
        "SNMPTrap, tc channel-04 in slot 7"
::= { slot7-tc-Trap 5 }

slot7Trap-tc-05 NOTIFICATION-TYPE
    STATUS      current
    DESCRIPTION
        "SNMPTrap, tc channel-05 in slot 7"
::= { slot7-tc-Trap 6 }

slot7Trap-tc-06 NOTIFICATION-TYPE
    STATUS      current
    DESCRIPTION
        "SNMPTrap, tc channel-06 in slot 7"
::= { slot7-tc-Trap 7 }

slot7Trap-tc-07 NOTIFICATION-TYPE
    STATUS      current
    DESCRIPTION
        "SNMPTrap, tc channel-07 in slot 7"
::= { slot7-tc-Trap 8 }

slot7Trap-tc-08 NOTIFICATION-TYPE
    STATUS      current
    DESCRIPTION
        "SNMPTrap, tc channel-08 in slot 7"
::= { slot7-tc-Trap 9 }

slot7Trap-tc-09 NOTIFICATION-TYPE
    STATUS      current
    DESCRIPTION
        "SNMPTrap, tc channel-09 in slot 7"
::= { slot7-tc-Trap 10 }

slot7Trap-tc-10 NOTIFICATION-TYPE
    STATUS      current
    DESCRIPTION
        "SNMPTrap, tc channel-10 in slot 7"
::= { slot7-tc-Trap 11 }

slot7Trap-tc-11 NOTIFICATION-TYPE
    STATUS      current
    DESCRIPTION
        "SNMPTrap, tc channel-11 in slot 7"
::= { slot7-tc-Trap 12 }

slot7Trap-tc-12 NOTIFICATION-TYPE
    STATUS      current
    DESCRIPTION
        "SNMPTrap, tc channel-12 in slot 7"
::= { slot7-tc-Trap 13 }

slot7Trap-tc-13 NOTIFICATION-TYPE
    STATUS      current
    DESCRIPTION
        "SNMPTrap, tc channel-13 in slot 7"
::= { slot7-tc-Trap 14 }

slot7Trap-tc-14 NOTIFICATION-TYPE
    STATUS      current
    DESCRIPTION
        "SNMPTrap, tc channel-14 in slot 7"
::= { slot7-tc-Trap 15 }

slot7Trap-tc-15 NOTIFICATION-TYPE
    STATUS      current
    DESCRIPTION
        "SNMPTrap, tc channel-15 in slot 7"
::= { slot7-tc-Trap 16 }					
		
		
----------------------------------------------------------------
-- 1.3.6.1.4.1.8691.10.2500.90
    slot8-io OBJECT IDENTIFIER ::= { ioLogik2500 90 }
----------------------------------------------------------------
-- slot 8 DI
slot8-diTable OBJECT-TYPE
		SYNTAX 			SEQUENCE OF Slot8-diDef
		MAX-ACCESS 		not-accessible
		STATUS 			current
		DESCRIPTION		"The di channel table"
		::= { slot8-io 1 }

slot8-di OBJECT-TYPE
		SYNTAX 			Slot8-diDef
		MAX-ACCESS 		not-accessible
		STATUS 			current
		DESCRIPTION		"The di channel item"
		INDEX { slot8-diIndex }
		::= { slot8-diTable 1 }

Slot8-diDef ::= SEQUENCE { 
    	slot8-diIndex		INTEGER,
		slot8-diStatus		Unsigned32,
		slot8-diCounterReset2Init INTEGER		
		}  

slot8-diIndex OBJECT-TYPE
		SYNTAX 			INTEGER (0..15)
		MAX-ACCESS 		read-only
		STATUS 			current
		DESCRIPTION		"The channel index"
		::= { slot8-di 1 }
		
slot8-diStatus OBJECT-TYPE
		SYNTAX 			Unsigned32
		MAX-ACCESS 		read-write
		STATUS 			current
		DESCRIPTION		"The channel di status. 0=off, 1=on in di mode or n=counter value in counter mode"
		::= { slot8-di 2 }

slot8-diCounterReset2Init OBJECT-TYPE
		SYNTAX 			INTEGER 
		MAX-ACCESS 		read-write
		STATUS 			current
		DESCRIPTION		"Trigger counter to initial value. 1=Reset counter to initial value"
		::= { slot8-di 3 }
		
-- slot 8 DICounterStart
slot8-diCounterStartTable OBJECT-TYPE
		SYNTAX 			SEQUENCE OF Slot8-diCounterStartDef
		MAX-ACCESS 		not-accessible
		STATUS 			current
		DESCRIPTION		"The counter table starting for di"
		::= { slot8-io 39 }

slot8-diCounterStart OBJECT-TYPE
		SYNTAX 			Slot8-diCounterStartDef
		MAX-ACCESS 		not-accessible
		STATUS 			current
		DESCRIPTION		"The counter starting of di item"
		INDEX { slot8-diCounterStartIndex }
		::= { slot8-diCounterStartTable 1 }

Slot8-diCounterStartDef ::= SEQUENCE { 
    	slot8-diCounterStartIndex		INTEGER,
		slot8-diCounterStartStatus		INTEGER	
		}  

slot8-diCounterStartIndex OBJECT-TYPE
		SYNTAX 			INTEGER (0..15)
		MAX-ACCESS 		read-only
		STATUS 			current
		DESCRIPTION		"The channel index for di counter start"
		::= { slot8-diCounterStart 1 }
		
slot8-diCounterStartStatus OBJECT-TYPE
		SYNTAX 			INTEGER (0..1)
		MAX-ACCESS 		read-write
		STATUS 			current
		DESCRIPTION		"The channel status for di counter start. 0=stop, 1=start"
		::= { slot8-diCounterStart 2 }  		
		
-- slot 8 DO
slot8-doTable OBJECT-TYPE
		SYNTAX 			SEQUENCE OF Slot8-doDef
		MAX-ACCESS 		not-accessible
		STATUS 			current
		DESCRIPTION		"The do channel table"
		::= { slot8-io 2 }

slot8-do OBJECT-TYPE
		SYNTAX 			Slot8-doDef
		MAX-ACCESS 		not-accessible
		STATUS 			current
		DESCRIPTION		"The do channel item"
		INDEX { slot8-doIndex }
		::= { slot8-doTable 1 }

Slot8-doDef ::= SEQUENCE { 
    	slot8-doIndex		INTEGER,
		slot8-doStatus		INTEGER		
		}  

slot8-doIndex OBJECT-TYPE
		SYNTAX 			INTEGER (0..15)
		MAX-ACCESS 		read-only
		STATUS 			current
		DESCRIPTION		"The channel index"
		::= { slot8-do 1 }
		
slot8-doStatus OBJECT-TYPE
		SYNTAX 			INTEGER (0..1)
		MAX-ACCESS 		read-write
		STATUS 			current
		DESCRIPTION		"The channel do status. 0=off, 1=on in do mode or 0=stop, 1=start in pulse mode"
		::= { slot8-do 2 }  

-- slot 8 DIO
slot8-dioTable OBJECT-TYPE
		SYNTAX 			SEQUENCE OF Slot8-dioDef
		MAX-ACCESS 		not-accessible
		STATUS 			current
		DESCRIPTION		"The dio channel table"
		::= { slot8-io 3 }

slot8-dio OBJECT-TYPE
		SYNTAX 			Slot8-dioDef
		MAX-ACCESS 		not-accessible
		STATUS 			current
		DESCRIPTION		"The dio channel item"
		INDEX { slot8-dioIndex }
		::= { slot8-dioTable 1 }

Slot8-dioDef ::= SEQUENCE { 
    	slot8-dioIndex		INTEGER,
		slot8-dioStatus		Unsigned32,
		slot8-dioCounterReset2Init INTEGER				
		}  

slot8-dioIndex OBJECT-TYPE
		SYNTAX 			INTEGER (0..15)
		MAX-ACCESS 		read-only
		STATUS 			current
		DESCRIPTION		"The channel index"
		::= { slot8-dio 1 }
		
slot8-dioStatus OBJECT-TYPE
		SYNTAX 			Unsigned32
		MAX-ACCESS 		read-write
		STATUS 			current
		DESCRIPTION		"The channel dio status. 0=off, 1=on in di/do mode or n=counter value in counter mode or 0=stop, 1=start in pulse mode"
		::= { slot8-dio 2 }  

slot8-dioCounterReset2Init OBJECT-TYPE
		SYNTAX 			INTEGER 
		MAX-ACCESS 		read-write
		STATUS 			current
		DESCRIPTION		"Trigger counter to initial value. 1=Reset counter to initial value"
		::= { slot8-dio 3 }		
		
-- slot 8 DIOCounterStart
slot8-dioCounterStartTable OBJECT-TYPE
		SYNTAX 			SEQUENCE OF Slot8-dioCounterStartDef
		MAX-ACCESS 		not-accessible
		STATUS 			current
		DESCRIPTION		"The counter table starting for dio"
		::= { slot8-io 46 }

slot8-dioCounterStart OBJECT-TYPE
		SYNTAX 			Slot8-dioCounterStartDef
		MAX-ACCESS 		not-accessible
		STATUS 			current
		DESCRIPTION		"The counter starting of dio item"
		INDEX { slot8-dioCounterStartIndex }
		::= { slot8-dioCounterStartTable 1 }

Slot8-dioCounterStartDef ::= SEQUENCE { 
    	slot8-dioCounterStartIndex		INTEGER,
		slot8-dioCounterStartStatus		INTEGER	
		}  

slot8-dioCounterStartIndex OBJECT-TYPE
		SYNTAX 			INTEGER (0..15)
		MAX-ACCESS 		read-only
		STATUS 			current
		DESCRIPTION		"The channel index for dio counter start"
		::= { slot8-dioCounterStart 1 }
		
slot8-dioCounterStartStatus OBJECT-TYPE
		SYNTAX 			INTEGER (0..1)
		MAX-ACCESS 		read-write
		STATUS 			current
		DESCRIPTION		"The channel status for dio counter start. 0=stop, 1=start"
		::= { slot8-dioCounterStart 2 } 	
						
-- slot 8 Relay
slot8-relayTable OBJECT-TYPE
		SYNTAX 			SEQUENCE OF Slot8-relayDef
		MAX-ACCESS 		not-accessible
		STATUS 			current
		DESCRIPTION		"The relay channel table"
		::= { slot8-io 4 }

slot8-relay OBJECT-TYPE
		SYNTAX 			Slot8-relayDef
		MAX-ACCESS 		not-accessible
		STATUS 			current
		DESCRIPTION		"The relay channel item"
		INDEX { slot8-relayIndex }
		::= { slot8-relayTable 1 }

Slot8-relayDef ::= SEQUENCE { 
    	slot8-relayIndex		INTEGER,
		slot8-relayStatus		INTEGER		
		}  

slot8-relayIndex OBJECT-TYPE
		SYNTAX 			INTEGER (0..15)
		MAX-ACCESS 		read-only
		STATUS 			current
		DESCRIPTION		"The channel index"
		::= { slot8-relay 1 }
		
slot8-relayStatus OBJECT-TYPE
		SYNTAX 			INTEGER (0..1)
		MAX-ACCESS 		read-write
		STATUS 			current
		DESCRIPTION		"The channel relay status. 0=off, 1=on in do mode or 0=stop, 1=start in pulse mode"
		::= { slot8-relay 2 }  

-- slot 8 AI
slot8-aiTable OBJECT-TYPE
		SYNTAX 			SEQUENCE OF Slot8-aiDef
		MAX-ACCESS 		not-accessible
		STATUS 			current
		DESCRIPTION		"The ai channel table"
		::= { slot8-io 5 }

slot8-ai OBJECT-TYPE
		SYNTAX 			Slot8-aiDef
		MAX-ACCESS 		not-accessible
		STATUS 			current
		DESCRIPTION		"The ai channel item"
		INDEX { slot8-aiIndex }
		::= { slot8-aiTable 1 }

Slot8-aiDef ::= SEQUENCE { 
    	slot8-aiIndex		INTEGER,
		slot8-aiStatus		OCTET STRING,
		slot8-aiBurnoutStatus INTEGER		
		}  

slot8-aiIndex OBJECT-TYPE
		SYNTAX 			INTEGER (0..15)
		MAX-ACCESS 		read-only
		STATUS 			current
		DESCRIPTION		"The channel index"
		::= { slot8-ai 1 }
		
slot8-aiStatus OBJECT-TYPE
		SYNTAX 			OCTET STRING
		MAX-ACCESS 		read-only
		STATUS 			current
		DESCRIPTION		"The channel ai scaled value"
		::= { slot8-ai 2 }  

slot8-aiBurnoutStatus OBJECT-TYPE
		SYNTAX 			INTEGER (0..3)
		MAX-ACCESS 		read-only
		STATUS 			current
		DESCRIPTION		"The channel of burnout status (0: normal, 1: burnout, 2: underange, 3: overange)"
		::= { slot8-ai 3 }  		
		
-- slot 8 AO
slot8-aoTable OBJECT-TYPE
		SYNTAX 			SEQUENCE OF Slot8-aoDef
		MAX-ACCESS 		not-accessible
		STATUS 			current
		DESCRIPTION		"The ao channel table"
		::= { slot8-io 6 }

slot8-ao OBJECT-TYPE
		SYNTAX 			Slot8-aoDef
		MAX-ACCESS 		not-accessible
		STATUS 			current
		DESCRIPTION		"The ao channel item"
		INDEX { slot8-aoIndex }
		::= { slot8-aoTable 1 }

Slot8-aoDef ::= SEQUENCE { 
    	slot8-aoIndex		INTEGER,
		slot8-aoStatus		OCTET STRING		
		}  

slot8-aoIndex OBJECT-TYPE
		SYNTAX 			INTEGER (0..15)
		MAX-ACCESS 		read-only
		STATUS 			current
		DESCRIPTION		"The channel index"
		::= { slot8-ao 1 }
		
slot8-aoStatus OBJECT-TYPE
		SYNTAX 			OCTET STRING
		MAX-ACCESS 		read-write
		STATUS 			current
		DESCRIPTION		"The channel ao scaled value"
		::= { slot8-ao 2 }  

-- slot 8 RTD
slot8-rtdTable OBJECT-TYPE
		SYNTAX 			SEQUENCE OF Slot8-rtdDef
		MAX-ACCESS 		not-accessible
		STATUS 			current
		DESCRIPTION		"The rtd channel table"
		::= { slot8-io 7 }

slot8-rtd OBJECT-TYPE
		SYNTAX 			Slot8-rtdDef
		MAX-ACCESS 		not-accessible
		STATUS 			current
		DESCRIPTION		"The rtd channel item"
		INDEX { slot8-rtdIndex }
		::= { slot8-rtdTable 1 }

Slot8-rtdDef ::= SEQUENCE { 
    		slot8-rtdIndex		INTEGER,
		slot8-rtdStatus		OCTET STRING		
		}  

slot8-rtdIndex OBJECT-TYPE
		SYNTAX 			INTEGER (0..15)
		MAX-ACCESS 		read-only
		STATUS 			current
		DESCRIPTION		"The channel index"
		::= { slot8-rtd 1 }
		
slot8-rtdStatus OBJECT-TYPE
		SYNTAX 			OCTET STRING
		MAX-ACCESS 		read-only
		STATUS 			current
		DESCRIPTION		"The channel rtd scaled value"
		::= { slot8-rtd 2 }  

-- slot 8 TC
slot8-tcTable OBJECT-TYPE
		SYNTAX 			SEQUENCE OF Slot8-tcDef
		MAX-ACCESS 		not-accessible
		STATUS 			current
		DESCRIPTION		"The tc channel table"
		::= { slot8-io 8 }

slot8-tc OBJECT-TYPE
		SYNTAX 			Slot8-tcDef
		MAX-ACCESS 		not-accessible
		STATUS 			current
		DESCRIPTION		"The tc channel item"
		INDEX { slot8-tcIndex }
		::= { slot8-tcTable 1 }

Slot8-tcDef ::= SEQUENCE { 
    		slot8-tcIndex		INTEGER,
		slot8-tcStatus		OCTET STRING		
		}  

slot8-tcIndex OBJECT-TYPE
		SYNTAX 			INTEGER (0..15)
		MAX-ACCESS 		read-only
		STATUS 			current
		DESCRIPTION		"The channel index"
		::= { slot8-tc 1 }
		
slot8-tcStatus OBJECT-TYPE
		SYNTAX 			OCTET STRING
		MAX-ACCESS 		read-only
		STATUS 			current
		DESCRIPTION		"The channel tc scaled value"
		::= { slot8-tc 2 }  

----------------------------------------------------------------
-- 1.3.6.1.4.1.8691.10.2500.91
    slot8-io-Trap OBJECT IDENTIFIER ::= { ioLogik2500 91 }
----------------------------------------------------------------

----------------------------------------------------------------
-- 1.3.6.1.4.1.8691.10.2500.91.1
    slot8-di-Trap OBJECT IDENTIFIER ::= { slot8-io-Trap 1 }
----------------------------------------------------------------

slot8Trap-di-00 NOTIFICATION-TYPE
    STATUS      current
    DESCRIPTION
        "SNMPTrap, di channel-00 in slot 8"
::= { slot8-di-Trap 1 }

slot8Trap-di-01 NOTIFICATION-TYPE
    STATUS      current
    DESCRIPTION
        "SNMPTrap, di channel-01 in slot 8"
::= { slot8-di-Trap 2 }

slot8Trap-di-02 NOTIFICATION-TYPE
    STATUS      current
    DESCRIPTION
        "SNMPTrap, di channel-02 in slot 8"
::= { slot8-di-Trap 3 }

slot8Trap-di-03 NOTIFICATION-TYPE
    STATUS      current
    DESCRIPTION
        "SNMPTrap, di channel-03 in slot 8"
::= { slot8-di-Trap 4 }

slot8Trap-di-04 NOTIFICATION-TYPE
    STATUS      current
    DESCRIPTION
        "SNMPTrap, di channel-04 in slot 8"
::= { slot8-di-Trap 5 }

slot8Trap-di-05 NOTIFICATION-TYPE
    STATUS      current
    DESCRIPTION
        "SNMPTrap, di channel-05 in slot 8"
::= { slot8-di-Trap 6 }

slot8Trap-di-06 NOTIFICATION-TYPE
    STATUS      current
    DESCRIPTION
        "SNMPTrap, di channel-06 in slot 8"
::= { slot8-di-Trap 7 }

slot8Trap-di-07 NOTIFICATION-TYPE
    STATUS      current
    DESCRIPTION
        "SNMPTrap, di channel-07 in slot 8"
::= { slot8-di-Trap 8 }

slot8Trap-di-08 NOTIFICATION-TYPE
    STATUS      current
    DESCRIPTION
        "SNMPTrap, di channel-08 in slot 8"
::= { slot8-di-Trap 9 }

slot8Trap-di-09 NOTIFICATION-TYPE
    STATUS      current
    DESCRIPTION
        "SNMPTrap, di channel-09 in slot 8"
::= { slot8-di-Trap 10 }

slot8Trap-di-10 NOTIFICATION-TYPE
    STATUS      current
    DESCRIPTION
        "SNMPTrap, di channel-10 in slot 8"
::= { slot8-di-Trap 11 }

slot8Trap-di-11 NOTIFICATION-TYPE
    STATUS      current
    DESCRIPTION
        "SNMPTrap, di channel-11 in slot 8"
::= { slot8-di-Trap 12 }

slot8Trap-di-12 NOTIFICATION-TYPE
    STATUS      current
    DESCRIPTION
        "SNMPTrap, di channel-12 in slot 8"
::= { slot8-di-Trap 13 }

slot8Trap-di-13 NOTIFICATION-TYPE
    STATUS      current
    DESCRIPTION
        "SNMPTrap, di channel-13 in slot 8"
::= { slot8-di-Trap 14 }

slot8Trap-di-14 NOTIFICATION-TYPE
    STATUS      current
    DESCRIPTION
        "SNMPTrap, di channel-14 in slot 8"
::= { slot8-di-Trap 15 }

slot8Trap-di-15 NOTIFICATION-TYPE
    STATUS      current
    DESCRIPTION
        "SNMPTrap, di channel-15 in slot 8"
::= { slot8-di-Trap 16 }
----------------------------------------------------------------
-- 1.3.6.1.4.1.8691.10.2500.91.2
    slot8-do-Trap OBJECT IDENTIFIER ::= { slot8-io-Trap 2 }
----------------------------------------------------------------

slot8Trap-do-00 NOTIFICATION-TYPE
    STATUS      current
    DESCRIPTION
        "SNMPTrap, do channel-00 in slot 8"
::= { slot8-do-Trap 1 }

slot8Trap-do-01 NOTIFICATION-TYPE
    STATUS      current
    DESCRIPTION
        "SNMPTrap, do channel-01 in slot 8"
::= { slot8-do-Trap 2 }

slot8Trap-do-02 NOTIFICATION-TYPE
    STATUS      current
    DESCRIPTION
        "SNMPTrap, do channel-02 in slot 8"
::= { slot8-do-Trap 3 }

slot8Trap-do-03 NOTIFICATION-TYPE
    STATUS      current
    DESCRIPTION
        "SNMPTrap, do channel-03 in slot 8"
::= { slot8-do-Trap 4 }

slot8Trap-do-04 NOTIFICATION-TYPE
    STATUS      current
    DESCRIPTION
        "SNMPTrap, do channel-04 in slot 8"
::= { slot8-do-Trap 5 }

slot8Trap-do-05 NOTIFICATION-TYPE
    STATUS      current
    DESCRIPTION
        "SNMPTrap, do channel-05 in slot 8"
::= { slot8-do-Trap 6 }

slot8Trap-do-06 NOTIFICATION-TYPE
    STATUS      current
    DESCRIPTION
        "SNMPTrap, do channel-06 in slot 8"
::= { slot8-do-Trap 7 }

slot8Trap-do-07 NOTIFICATION-TYPE
    STATUS      current
    DESCRIPTION
        "SNMPTrap, do channel-07 in slot 8"
::= { slot8-do-Trap 8 }

slot8Trap-do-08 NOTIFICATION-TYPE
    STATUS      current
    DESCRIPTION
        "SNMPTrap, do channel-08 in slot 8"
::= { slot8-do-Trap 9 }

slot8Trap-do-09 NOTIFICATION-TYPE
    STATUS      current
    DESCRIPTION
        "SNMPTrap, do channel-09 in slot 8"
::= { slot8-do-Trap 10 }

slot8Trap-do-10 NOTIFICATION-TYPE
    STATUS      current
    DESCRIPTION
        "SNMPTrap, do channel-10 in slot 8"
::= { slot8-do-Trap 11 }

slot8Trap-do-11 NOTIFICATION-TYPE
    STATUS      current
    DESCRIPTION
        "SNMPTrap, do channel-11 in slot 8"
::= { slot8-do-Trap 12 }

slot8Trap-do-12 NOTIFICATION-TYPE
    STATUS      current
    DESCRIPTION
        "SNMPTrap, do channel-12 in slot 8"
::= { slot8-do-Trap 13 }

slot8Trap-do-13 NOTIFICATION-TYPE
    STATUS      current
    DESCRIPTION
        "SNMPTrap, do channel-13 in slot 8"
::= { slot8-do-Trap 14 }

slot8Trap-do-14 NOTIFICATION-TYPE
    STATUS      current
    DESCRIPTION
        "SNMPTrap, do channel-14 in slot 8"
::= { slot8-do-Trap 15 }

slot8Trap-do-15 NOTIFICATION-TYPE
    STATUS      current
    DESCRIPTION
        "SNMPTrap, do channel-15 in slot 8"
::= { slot8-do-Trap 16 }

----------------------------------------------------------------
-- 1.3.6.1.4.1.8691.10.2500.91.3
    slot8-dio-Trap OBJECT IDENTIFIER ::= { slot8-io-Trap 3 }
----------------------------------------------------------------

slot8Trap-dio-00 NOTIFICATION-TYPE
    STATUS      current
    DESCRIPTION
        "SNMPTrap, dio channel-00 in slot 8"
::= { slot8-dio-Trap 1 }

slot8Trap-dio-01 NOTIFICATION-TYPE
    STATUS      current
    DESCRIPTION
        "SNMPTrap, dio channel-01 in slot 8"
::= { slot8-dio-Trap 2 }

slot8Trap-dio-02 NOTIFICATION-TYPE
    STATUS      current
    DESCRIPTION
        "SNMPTrap, dio channel-02 in slot 8"
::= { slot8-dio-Trap 3 }

slot8Trap-dio-03 NOTIFICATION-TYPE
    STATUS      current
    DESCRIPTION
        "SNMPTrap, dio channel-03 in slot 8"
::= { slot8-dio-Trap 4 }

slot8Trap-dio-04 NOTIFICATION-TYPE
    STATUS      current
    DESCRIPTION
        "SNMPTrap, dio channel-04 in slot 8"
::= { slot8-dio-Trap 5 }

slot8Trap-dio-05 NOTIFICATION-TYPE
    STATUS      current
    DESCRIPTION
        "SNMPTrap, dio channel-05 in slot 8"
::= { slot8-dio-Trap 6 }

slot8Trap-dio-06 NOTIFICATION-TYPE
    STATUS      current
    DESCRIPTION
        "SNMPTrap, dio channel-06 in slot 8"
::= { slot8-dio-Trap 7 }

slot8Trap-dio-07 NOTIFICATION-TYPE
    STATUS      current
    DESCRIPTION
        "SNMPTrap, dio channel-07 in slot 8"
::= { slot8-dio-Trap 8 }

slot8Trap-dio-08 NOTIFICATION-TYPE
    STATUS      current
    DESCRIPTION
        "SNMPTrap, dio channel-08 in slot 8"
::= { slot8-dio-Trap 9 }

slot8Trap-dio-09 NOTIFICATION-TYPE
    STATUS      current
    DESCRIPTION
        "SNMPTrap, dio channel-09 in slot 8"
::= { slot8-dio-Trap 10 }

slot8Trap-dio-10 NOTIFICATION-TYPE
    STATUS      current
    DESCRIPTION
        "SNMPTrap, dio channel-10 in slot 8"
::= { slot8-dio-Trap 11 }

slot8Trap-dio-11 NOTIFICATION-TYPE
    STATUS      current
    DESCRIPTION
        "SNMPTrap, dio channel-11 in slot 8"
::= { slot8-dio-Trap 12 }

slot8Trap-dio-12 NOTIFICATION-TYPE
    STATUS      current
    DESCRIPTION
        "SNMPTrap, dio channel-12 in slot 8"
::= { slot8-dio-Trap 13 }

slot8Trap-dio-13 NOTIFICATION-TYPE
    STATUS      current
    DESCRIPTION
        "SNMPTrap, dio channel-13 in slot 8"
::= { slot8-dio-Trap 14 }

slot8Trap-dio-14 NOTIFICATION-TYPE
    STATUS      current
    DESCRIPTION
        "SNMPTrap, dio channel-14 in slot 8"
::= { slot8-dio-Trap 15 }

slot8Trap-dio-15 NOTIFICATION-TYPE
    STATUS      current
    DESCRIPTION
        "SNMPTrap, dio channel-15 in slot 8"
::= { slot8-dio-Trap 16 }

----------------------------------------------------------------
-- 1.3.6.1.4.1.8691.10.2500.91.4
    slot8-relay-Trap OBJECT IDENTIFIER ::= { slot8-io-Trap 4 }
----------------------------------------------------------------

slot8Trap-relay-00 NOTIFICATION-TYPE
    STATUS      current
    DESCRIPTION
        "SNMPTrap, relay channel-00 in slot 8"
::= { slot8-relay-Trap 1 }

slot8Trap-relay-01 NOTIFICATION-TYPE
    STATUS      current
    DESCRIPTION
        "SNMPTrap, relay channel-01 in slot 8"
::= { slot8-relay-Trap 2 }

slot8Trap-relay-02 NOTIFICATION-TYPE
    STATUS      current
    DESCRIPTION
        "SNMPTrap, relay channel-02 in slot 8"
::= { slot8-relay-Trap 3 }

slot8Trap-relay-03 NOTIFICATION-TYPE
    STATUS      current
    DESCRIPTION
        "SNMPTrap, relay channel-03 in slot 8"
::= { slot8-relay-Trap 4 }

slot8Trap-relay-04 NOTIFICATION-TYPE
    STATUS      current
    DESCRIPTION
        "SNMPTrap, relay channel-04 in slot 8"
::= { slot8-relay-Trap 5 }

slot8Trap-relay-05 NOTIFICATION-TYPE
    STATUS      current
    DESCRIPTION
        "SNMPTrap, relay channel-05 in slot 8"
::= { slot8-relay-Trap 6 }

slot8Trap-relay-06 NOTIFICATION-TYPE
    STATUS      current
    DESCRIPTION
        "SNMPTrap, relay channel-06 in slot 8"
::= { slot8-relay-Trap 7 }

slot8Trap-relay-07 NOTIFICATION-TYPE
    STATUS      current
    DESCRIPTION
        "SNMPTrap, relay channel-07 in slot 8"
::= { slot8-relay-Trap 8 }

slot8Trap-relay-08 NOTIFICATION-TYPE
    STATUS      current
    DESCRIPTION
        "SNMPTrap, relay channel-08 in slot 8"
::= { slot8-relay-Trap 9 }

slot8Trap-relay-09 NOTIFICATION-TYPE
    STATUS      current
    DESCRIPTION
        "SNMPTrap, relay channel-09 in slot 8"
::= { slot8-relay-Trap 10 }

slot8Trap-relay-10 NOTIFICATION-TYPE
    STATUS      current
    DESCRIPTION
        "SNMPTrap, relay channel-10 in slot 8"
::= { slot8-relay-Trap 11 }

slot8Trap-relay-11 NOTIFICATION-TYPE
    STATUS      current
    DESCRIPTION
        "SNMPTrap, relay channel-11 in slot 8"
::= { slot8-relay-Trap 12 }

slot8Trap-relay-12 NOTIFICATION-TYPE
    STATUS      current
    DESCRIPTION
        "SNMPTrap, relay channel-12 in slot 8"
::= { slot8-relay-Trap 13 }

slot8Trap-relay-13 NOTIFICATION-TYPE
    STATUS      current
    DESCRIPTION
        "SNMPTrap, relay channel-13 in slot 8"
::= { slot8-relay-Trap 14 }

slot8Trap-relay-14 NOTIFICATION-TYPE
    STATUS      current
    DESCRIPTION
        "SNMPTrap, relay channel-14 in slot 8"
::= { slot8-relay-Trap 15 }

slot8Trap-relay-15 NOTIFICATION-TYPE
    STATUS      current
    DESCRIPTION
        "SNMPTrap, relay channel-15 in slot 8"
::= { slot8-relay-Trap 16 }

----------------------------------------------------------------
-- 1.3.6.1.4.1.8691.10.2500.91.5
    slot8-ai-Trap OBJECT IDENTIFIER ::= { slot8-io-Trap 5 }
----------------------------------------------------------------

slot8Trap-ai-00 NOTIFICATION-TYPE
    STATUS      current
    DESCRIPTION
        "SNMPTrap, ai channel-00 in slot 8"
::= { slot8-ai-Trap 1 }

slot8Trap-ai-01 NOTIFICATION-TYPE
    STATUS      current
    DESCRIPTION
        "SNMPTrap, ai channel-01 in slot 8"
::= { slot8-ai-Trap 2 }

slot8Trap-ai-02 NOTIFICATION-TYPE
    STATUS      current
    DESCRIPTION
        "SNMPTrap, ai channel-02 in slot 8"
::= { slot8-ai-Trap 3 }

slot8Trap-ai-03 NOTIFICATION-TYPE
    STATUS      current
    DESCRIPTION
        "SNMPTrap, ai channel-03 in slot 8"
::= { slot8-ai-Trap 4 }

slot8Trap-ai-04 NOTIFICATION-TYPE
    STATUS      current
    DESCRIPTION
        "SNMPTrap, ai channel-04 in slot 8"
::= { slot8-ai-Trap 5 }

slot8Trap-ai-05 NOTIFICATION-TYPE
    STATUS      current
    DESCRIPTION
        "SNMPTrap, ai channel-05 in slot 8"
::= { slot8-ai-Trap 6 }

slot8Trap-ai-06 NOTIFICATION-TYPE
    STATUS      current
    DESCRIPTION
        "SNMPTrap, ai channel-06 in slot 8"
::= { slot8-ai-Trap 7 }

slot8Trap-ai-07 NOTIFICATION-TYPE
    STATUS      current
    DESCRIPTION
        "SNMPTrap, ai channel-07 in slot 8"
::= { slot8-ai-Trap 8 }

slot8Trap-ai-08 NOTIFICATION-TYPE
    STATUS      current
    DESCRIPTION
        "SNMPTrap, ai channel-08 in slot 8"
::= { slot8-ai-Trap 9 }

slot8Trap-ai-09 NOTIFICATION-TYPE
    STATUS      current
    DESCRIPTION
        "SNMPTrap, ai channel-09 in slot 8"
::= { slot8-ai-Trap 10 }

slot8Trap-ai-10 NOTIFICATION-TYPE
    STATUS      current
    DESCRIPTION
        "SNMPTrap, ai channel-10 in slot 8"
::= { slot8-ai-Trap 11 }

slot8Trap-ai-11 NOTIFICATION-TYPE
    STATUS      current
    DESCRIPTION
        "SNMPTrap, ai channel-11 in slot 8"
::= { slot8-ai-Trap 12 }

slot8Trap-ai-12 NOTIFICATION-TYPE
    STATUS      current
    DESCRIPTION
        "SNMPTrap, ai channel-12 in slot 8"
::= { slot8-ai-Trap 13 }

slot8Trap-ai-13 NOTIFICATION-TYPE
    STATUS      current
    DESCRIPTION
        "SNMPTrap, ai channel-13 in slot 8"
::= { slot8-ai-Trap 14 }

slot8Trap-ai-14 NOTIFICATION-TYPE
    STATUS      current
    DESCRIPTION
        "SNMPTrap, ai channel-14 in slot 8"
::= { slot8-ai-Trap 15 }

slot8Trap-ai-15 NOTIFICATION-TYPE
    STATUS      current
    DESCRIPTION
        "SNMPTrap, ai channel-15 in slot 8"
::= { slot8-ai-Trap 16 }

----------------------------------------------------------------
-- 1.3.6.1.4.1.8691.10.2500.91.6
    slot8-ao-Trap OBJECT IDENTIFIER ::= { slot8-io-Trap 6 }
----------------------------------------------------------------

slot8Trap-ao-00 NOTIFICATION-TYPE
    STATUS      current
    DESCRIPTION
        "SNMPTrap, ao channel-00 in slot 8"
::= { slot8-ao-Trap 1 }

slot8Trap-ao-01 NOTIFICATION-TYPE
    STATUS      current
    DESCRIPTION
        "SNMPTrap, ao channel-01 in slot 8"
::= { slot8-ao-Trap 2 }

slot8Trap-ao-02 NOTIFICATION-TYPE
    STATUS      current
    DESCRIPTION
        "SNMPTrap, ao channel-02 in slot 8"
::= { slot8-ao-Trap 3 }

slot8Trap-ao-03 NOTIFICATION-TYPE
    STATUS      current
    DESCRIPTION
        "SNMPTrap, ao channel-03 in slot 8"
::= { slot8-ao-Trap 4 }

slot8Trap-ao-04 NOTIFICATION-TYPE
    STATUS      current
    DESCRIPTION
        "SNMPTrap, ao channel-04 in slot 8"
::= { slot8-ao-Trap 5 }

slot8Trap-ao-05 NOTIFICATION-TYPE
    STATUS      current
    DESCRIPTION
        "SNMPTrap, ao channel-05 in slot 8"
::= { slot8-ao-Trap 6 }

slot8Trap-ao-06 NOTIFICATION-TYPE
    STATUS      current
    DESCRIPTION
        "SNMPTrap, ao channel-06 in slot 8"
::= { slot8-ao-Trap 7 }

slot8Trap-ao-07 NOTIFICATION-TYPE
    STATUS      current
    DESCRIPTION
        "SNMPTrap, ao channel-07 in slot 8"
::= { slot8-ao-Trap 8 }

slot8Trap-ao-08 NOTIFICATION-TYPE
    STATUS      current
    DESCRIPTION
        "SNMPTrap, ao channel-08 in slot 8"
::= { slot8-ao-Trap 9 }

slot8Trap-ao-09 NOTIFICATION-TYPE
    STATUS      current
    DESCRIPTION
        "SNMPTrap, ao channel-09 in slot 8"
::= { slot8-ao-Trap 10 }

slot8Trap-ao-10 NOTIFICATION-TYPE
    STATUS      current
    DESCRIPTION
        "SNMPTrap, ao channel-10 in slot 8"
::= { slot8-ao-Trap 11 }

slot8Trap-ao-11 NOTIFICATION-TYPE
    STATUS      current
    DESCRIPTION
        "SNMPTrap, ao channel-11 in slot 8"
::= { slot8-ao-Trap 12 }

slot8Trap-ao-12 NOTIFICATION-TYPE
    STATUS      current
    DESCRIPTION
        "SNMPTrap, ao channel-12 in slot 8"
::= { slot8-ao-Trap 13 }

slot8Trap-ao-13 NOTIFICATION-TYPE
    STATUS      current
    DESCRIPTION
        "SNMPTrap, ao channel-13 in slot 8"
::= { slot8-ao-Trap 14 }

slot8Trap-ao-14 NOTIFICATION-TYPE
    STATUS      current
    DESCRIPTION
        "SNMPTrap, ao channel-14 in slot 8"
::= { slot8-ao-Trap 15 }

slot8Trap-ao-15 NOTIFICATION-TYPE
    STATUS      current
    DESCRIPTION
        "SNMPTrap, ao channel-15 in slot 8"
::= { slot8-ao-Trap 16 }

----------------------------------------------------------------
-- 1.3.6.1.4.1.8691.10.2500.91.7
    slot8-rtd-Trap OBJECT IDENTIFIER ::= { slot8-io-Trap 7 }
----------------------------------------------------------------

slot8Trap-rtd-00 NOTIFICATION-TYPE
    STATUS      current
    DESCRIPTION
        "SNMPTrap, rtd channel-00 in slot 8"
::= { slot8-rtd-Trap 1 }

slot8Trap-rtd-01 NOTIFICATION-TYPE
    STATUS      current
    DESCRIPTION
        "SNMPTrap, rtd channel-01 in slot 8"
::= { slot8-rtd-Trap 2 }

slot8Trap-rtd-02 NOTIFICATION-TYPE
    STATUS      current
    DESCRIPTION
        "SNMPTrap, rtd channel-02 in slot 8"
::= { slot8-rtd-Trap 3 }

slot8Trap-rtd-03 NOTIFICATION-TYPE
    STATUS      current
    DESCRIPTION
        "SNMPTrap, rtd channel-03 in slot 8"
::= { slot8-rtd-Trap 4 }

slot8Trap-rtd-04 NOTIFICATION-TYPE
    STATUS      current
    DESCRIPTION
        "SNMPTrap, rtd channel-04 in slot 8"
::= { slot8-rtd-Trap 5 }

slot8Trap-rtd-05 NOTIFICATION-TYPE
    STATUS      current
    DESCRIPTION
        "SNMPTrap, rtd channel-05 in slot 8"
::= { slot8-rtd-Trap 6 }

slot8Trap-rtd-06 NOTIFICATION-TYPE
    STATUS      current
    DESCRIPTION
        "SNMPTrap, rtd channel-06 in slot 8"
::= { slot8-rtd-Trap 7 }

slot8Trap-rtd-07 NOTIFICATION-TYPE
    STATUS      current
    DESCRIPTION
        "SNMPTrap, rtd channel-07 in slot 8"
::= { slot8-rtd-Trap 8 }

slot8Trap-rtd-08 NOTIFICATION-TYPE
    STATUS      current
    DESCRIPTION
        "SNMPTrap, rtd channel-08 in slot 8"
::= { slot8-rtd-Trap 9 }

slot8Trap-rtd-09 NOTIFICATION-TYPE
    STATUS      current
    DESCRIPTION
        "SNMPTrap, rtd channel-09 in slot 8"
::= { slot8-rtd-Trap 10 }

slot8Trap-rtd-10 NOTIFICATION-TYPE
    STATUS      current
    DESCRIPTION
        "SNMPTrap, rtd channel-10 in slot 8"
::= { slot8-rtd-Trap 11 }

slot8Trap-rtd-11 NOTIFICATION-TYPE
    STATUS      current
    DESCRIPTION
        "SNMPTrap, rtd channel-11 in slot 8"
::= { slot8-rtd-Trap 12 }

slot8Trap-rtd-12 NOTIFICATION-TYPE
    STATUS      current
    DESCRIPTION
        "SNMPTrap, rtd channel-12 in slot 8"
::= { slot8-rtd-Trap 13 }

slot8Trap-rtd-13 NOTIFICATION-TYPE
    STATUS      current
    DESCRIPTION
        "SNMPTrap, rtd channel-13 in slot 8"
::= { slot8-rtd-Trap 14 }

slot8Trap-rtd-14 NOTIFICATION-TYPE
    STATUS      current
    DESCRIPTION
        "SNMPTrap, rtd channel-14 in slot 8"
::= { slot8-rtd-Trap 15 }

slot8Trap-rtd-15 NOTIFICATION-TYPE
    STATUS      current
    DESCRIPTION
        "SNMPTrap, rtd channel-15 in slot 8"
::= { slot8-rtd-Trap 16 }

----------------------------------------------------------------
-- 1.3.6.1.4.1.8691.10.2500.91.8
    slot8-tc-Trap OBJECT IDENTIFIER ::= { slot8-io-Trap 8 }
----------------------------------------------------------------

slot8Trap-tc-00 NOTIFICATION-TYPE
    STATUS      current
    DESCRIPTION
        "SNMPTrap, tc channel-00 in slot 8"
::= { slot8-tc-Trap 1 }

slot8Trap-tc-01 NOTIFICATION-TYPE
    STATUS      current
    DESCRIPTION
        "SNMPTrap, tc channel-01 in slot 8"
::= { slot8-tc-Trap 2 }

slot8Trap-tc-02 NOTIFICATION-TYPE
    STATUS      current
    DESCRIPTION
        "SNMPTrap, tc channel-02 in slot 8"
::= { slot8-tc-Trap 3 }

slot8Trap-tc-03 NOTIFICATION-TYPE
    STATUS      current
    DESCRIPTION
        "SNMPTrap, tc channel-03 in slot 8"
::= { slot8-tc-Trap 4 }

slot8Trap-tc-04 NOTIFICATION-TYPE
    STATUS      current
    DESCRIPTION
        "SNMPTrap, tc channel-04 in slot 8"
::= { slot8-tc-Trap 5 }

slot8Trap-tc-05 NOTIFICATION-TYPE
    STATUS      current
    DESCRIPTION
        "SNMPTrap, tc channel-05 in slot 8"
::= { slot8-tc-Trap 6 }

slot8Trap-tc-06 NOTIFICATION-TYPE
    STATUS      current
    DESCRIPTION
        "SNMPTrap, tc channel-06 in slot 8"
::= { slot8-tc-Trap 7 }

slot8Trap-tc-07 NOTIFICATION-TYPE
    STATUS      current
    DESCRIPTION
        "SNMPTrap, tc channel-07 in slot 8"
::= { slot8-tc-Trap 8 }

slot8Trap-tc-08 NOTIFICATION-TYPE
    STATUS      current
    DESCRIPTION
        "SNMPTrap, tc channel-08 in slot 8"
::= { slot8-tc-Trap 9 }

slot8Trap-tc-09 NOTIFICATION-TYPE
    STATUS      current
    DESCRIPTION
        "SNMPTrap, tc channel-09 in slot 8"
::= { slot8-tc-Trap 10 }

slot8Trap-tc-10 NOTIFICATION-TYPE
    STATUS      current
    DESCRIPTION
        "SNMPTrap, tc channel-10 in slot 8"
::= { slot8-tc-Trap 11 }

slot8Trap-tc-11 NOTIFICATION-TYPE
    STATUS      current
    DESCRIPTION
        "SNMPTrap, tc channel-11 in slot 8"
::= { slot8-tc-Trap 12 }

slot8Trap-tc-12 NOTIFICATION-TYPE
    STATUS      current
    DESCRIPTION
        "SNMPTrap, tc channel-12 in slot 8"
::= { slot8-tc-Trap 13 }

slot8Trap-tc-13 NOTIFICATION-TYPE
    STATUS      current
    DESCRIPTION
        "SNMPTrap, tc channel-13 in slot 8"
::= { slot8-tc-Trap 14 }

slot8Trap-tc-14 NOTIFICATION-TYPE
    STATUS      current
    DESCRIPTION
        "SNMPTrap, tc channel-14 in slot 8"
::= { slot8-tc-Trap 15 }

slot8Trap-tc-15 NOTIFICATION-TYPE
    STATUS      current
    DESCRIPTION
        "SNMPTrap, tc channel-15 in slot 8"
::= { slot8-tc-Trap 16 }					

END
