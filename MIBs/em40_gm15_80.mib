GEISTMFG-EM40GM15-80-MIB DEFINITIONS ::= BEGIN

IMPORTS
	MODULE-IDENTITY, OBJECT-TYPE, enterprises, Unsigned32 FROM SNMPv2-SMI;

geistmfg MODULE-IDENTITY
	LAST-UPDATED "200705170000Z"
	ORGANIZATION "Geist Manufacturing"
	CONTACT-INFO "support@geistmfg.com/800.432.3219"
	DESCRIPTION "The MIB for EM40/GM15-80"
	::= { enterprises 21239 }
	

em40gm15_80 OBJECT IDENTIFIER
	::=  { geistmfg 14 }


productInfo OBJECT IDENTIFIER
	::= { em40gm15_80 1 }

totalDeciAmps OBJECT IDENTIFIER
	::= { em40gm15_80 2 }

circuit4 OBJECT IDENTIFIER
	::= { em40gm15_80 3 }

circuit3 OBJECT IDENTIFIER
	::= { em40gm15_80 4 }

circuit2 OBJECT IDENTIFIER
	::= { em40gm15_80 5 }

circuit1 OBJECT IDENTIFIER
	::= { em40gm15_80 6 }




productTitle    OBJECT-TYPE
   SYNTAX DisplayString
   ACCESS read-only
   STATUS mandatory
   DESCRIPTION
      "Name of product"
   ::= { productInfo 1 }
   
productVersion    OBJECT-TYPE
   SYNTAX DisplayString
   ACCESS read-only
   STATUS mandatory
   DESCRIPTION
      "Firmware version"
   ::= { productInfo 2 }

productName    OBJECT-TYPE
   SYNTAX DisplayString
   ACCESS read-only
   STATUS mandatory
   DESCRIPTION
      "Unit friendly name"
   ::= { productInfo 3 }

productMAC    OBJECT-TYPE
   SYNTAX DisplayString
   ACCESS read-only
   STATUS mandatory
   DESCRIPTION
      "Unit MAC address"
   ::= { productInfo 4 }

productIP    OBJECT-TYPE
   SYNTAX DisplayString
   ACCESS read-only
   STATUS mandatory
   DESCRIPTION
      "IP address of the unit"
   ::= { productInfo 5 }




totalDeciAmpsPhaseA   OBJECT-TYPE
   SYNTAX INTEGER(0..300)
   UNITS "0.1 Amps"
   ACCESS read-only
   STATUS mandatory
   DESCRIPTION
   "Total Amps consumed by PhaseA, in units of 0.1 amps"
   ::= { totalDeciAmps 1 }

totalDeciAmpsPhaseB   OBJECT-TYPE
   SYNTAX INTEGER(0..300)
   UNITS "0.1 Amps"
   ACCESS read-only
   STATUS mandatory
   DESCRIPTION
   "Total Amps consumed by PhaseB, in units of 0.1 amps"
   ::= { totalDeciAmps 2 }

totalDeciAmpsPhaseC   OBJECT-TYPE
   SYNTAX INTEGER(0..300)
   UNITS "0.1 Amps"
   ACCESS read-only
   STATUS mandatory
   DESCRIPTION
   "Total Amps consumed by PhaseC, in units of 0.1 amps"
   ::= { totalDeciAmps 3 }





outlet1AB-1Name OBJECT-TYPE
   SYNTAX DisplayString
   ACCESS read-only
   STATUS mandatory
   DESCRIPTION
   "Friendly name for outlet 1"
   ::= { circuit4 1 }

outlet1AB-1DeciAmps OBJECT-TYPE
   SYNTAX INTEGER(0..255)
   UNITS "0.1 Amps"
   ACCESS read-only
   STATUS mandatory
   DESCRIPTION
   "Amps used by outlet 1, in units of 0.1 amps"
   ::= { circuit4 2 }

outlet2BC-1Name OBJECT-TYPE
   SYNTAX DisplayString
   ACCESS read-only
   STATUS mandatory
   DESCRIPTION
   "Friendly name for outlet 2"
   ::= { circuit4 3 }

outlet2BC-1DeciAmps OBJECT-TYPE
   SYNTAX INTEGER(0..255)
   UNITS "0.1 Amps"
   ACCESS read-only
   STATUS mandatory
   DESCRIPTION
   "Amps used by outlet 2, in units of 0.1 amps"
   ::= { circuit4 4 }

outlet3CA-1Name OBJECT-TYPE
   SYNTAX DisplayString
   ACCESS read-only
   STATUS mandatory
   DESCRIPTION
   "Friendly name for outlet 3"
   ::= { circuit4 5 }

outlet3CA-1DeciAmps OBJECT-TYPE
   SYNTAX INTEGER(0..255)
   UNITS "0.1 Amps"
   ACCESS read-only
   STATUS mandatory
   DESCRIPTION
   "Amps used by outlet 3, in units of 0.1 amps"
   ::= { circuit4 6 }



outlet4AB-2Name OBJECT-TYPE
   SYNTAX DisplayString
   ACCESS read-only
   STATUS mandatory
   DESCRIPTION
   "Friendly name for outlet 4"
   ::= { circuit3 1 }

outlet4AB-2DeciAmps OBJECT-TYPE
   SYNTAX INTEGER(0..255)
   UNITS "0.1 Amps"
   ACCESS read-only
   STATUS mandatory
   DESCRIPTION
   "Amps used by outlet 4, in units of 0.1 amps"
   ::= { circuit3 2 }

outlet5BC-2Name OBJECT-TYPE
   SYNTAX DisplayString
   ACCESS read-only
   STATUS mandatory
   DESCRIPTION
   "Friendly name for outlet 5"
   ::= { circuit3 3 }

outlet5BC-2DeciAmps OBJECT-TYPE
   SYNTAX INTEGER(0..255)
   UNITS "0.1 Amps"
   ACCESS read-only
   STATUS mandatory
   DESCRIPTION
   "Amps used by outlet 5, in units of 0.1 amps"
   ::= { circuit3 4 }

outlet6CA-2Name OBJECT-TYPE
   SYNTAX DisplayString
   ACCESS read-only
   STATUS mandatory
   DESCRIPTION
   "Friendly name for outlet 6"
   ::= { circuit3 5 }

outlet6CA-2DeciAmps OBJECT-TYPE
   SYNTAX INTEGER(0..255)
   UNITS "0.1 Amps"
   ACCESS read-only
   STATUS mandatory
   DESCRIPTION
   "Amps used by outlet 6, in units of 0.1 amps"
   ::= { circuit3 6 }



outlet7AB-3Name OBJECT-TYPE
   SYNTAX DisplayString
   ACCESS read-only
   STATUS mandatory
   DESCRIPTION
   "Friendly name for outlet 7"
   ::= { circuit2 1 }

outlet7AB-3DeciAmps OBJECT-TYPE
   SYNTAX INTEGER(0..255)
   UNITS "0.1 Amps"
   ACCESS read-only
   STATUS mandatory
   DESCRIPTION
   "Amps used by outlet 7, in units of 0.1 amps"
   ::= { circuit2 2 }

outlet8BC-3Name OBJECT-TYPE
   SYNTAX DisplayString
   ACCESS read-only
   STATUS mandatory
   DESCRIPTION
   "Friendly name for outlet 8"
   ::= { circuit2 3 }

outlet8BC-3DeciAmps OBJECT-TYPE
   SYNTAX INTEGER(0..255)
   UNITS "0.1 Amps"
   ACCESS read-only
   STATUS mandatory
   DESCRIPTION
   "Amps used by outlet 8, in units of 0.1 amps"
   ::= { circuit2 4 }

outlet9CA-3Name OBJECT-TYPE
   SYNTAX DisplayString
   ACCESS read-only
   STATUS mandatory
   DESCRIPTION
   "Friendly name for outlet 9"
   ::= { circuit2 5 }

outlet9CA-3DeciAmps OBJECT-TYPE
   SYNTAX INTEGER(0..255)
   UNITS "0.1 Amps"
   ACCESS read-only
   STATUS mandatory
   DESCRIPTION
   "Amps used by outlet 9, in units of 0.1 amps"
   ::= { circuit2 6 }



outlet10AB-4Name OBJECT-TYPE
   SYNTAX DisplayString
   ACCESS read-only
   STATUS mandatory
   DESCRIPTION
   "Friendly name for outlet 10"
   ::= { circuit1 1 }

outlet10AB-4DeciAmps OBJECT-TYPE
   SYNTAX INTEGER(0..255)
   UNITS "0.1 Amps"
   ACCESS read-only
   STATUS mandatory
   DESCRIPTION
   "Amps used by outlet 10, in units of 0.1 amps"
   ::= { circuit1 2 }

outlet11BC-4Name OBJECT-TYPE
   SYNTAX DisplayString
   ACCESS read-only
   STATUS mandatory
   DESCRIPTION
   "Friendly name for outlet 11"
   ::= { circuit1 3 }

outlet11BC-4DeciAmps OBJECT-TYPE
   SYNTAX INTEGER(0..255)
   UNITS "0.1 Amps"
   ACCESS read-only
   STATUS mandatory
   DESCRIPTION
   "Amps used by outlet 11, in units of 0.1 amps"
   ::= { circuit1 4 }

outlet12CA-4Name OBJECT-TYPE
   SYNTAX DisplayString
   ACCESS read-only
   STATUS mandatory
   DESCRIPTION
   "Friendly name for outlet 12"
   ::= { circuit1 5 }

outlet12CA-4DeciAmps OBJECT-TYPE
   SYNTAX INTEGER(0..255)
   UNITS "0.1 Amps"
   ACCESS read-only
   STATUS mandatory
   DESCRIPTION
   "Amps used by outlet 12, in units of 0.1 amps"
   ::= { circuit1 6 }





totalDeciAmpsPhaseATRAP TRAP-TYPE
ENTERPRISE geistmfg
VARIABLES { totalDeciAmpsPhaseA }
DESCRIPTION "Amps PhaseA Trap"
::= 1

totalDeciAmpsPhaseBTRAP TRAP-TYPE
ENTERPRISE geistmfg
VARIABLES { totalDeciAmpsPhaseB }
DESCRIPTION "Amps PhaseB Trap"
::= 2

totalDeciAmpsPhaseCTRAP TRAP-TYPE
ENTERPRISE geistmfg
VARIABLES { totalDeciAmpsPhaseC }
DESCRIPTION "Amps PhaseC Trap"
::= 3





outlet1AB-1DeciAmpsTRAP TRAP-TYPE
ENTERPRISE geistmfg
VARIABLES { outlet1AB-1DeciAmps }
DESCRIPTION "Amps outlet1AB-1DeciAmps Trap"
::= 4

outlet2BC-1DeciAmpsTRAP TRAP-TYPE
ENTERPRISE geistmfg
VARIABLES { outlet2BC-1DeciAmps }
DESCRIPTION "Amps outlet2BC-1DeciAmps Trap"
::= 5

outlet3CA-1DeciAmpsTRAP TRAP-TYPE
ENTERPRISE geistmfg
VARIABLES { outlet3CA-1DeciAmps }
DESCRIPTION "Amps outlet3CA-1DeciAmps Trap"
::= 6



outlet4AB-2DeciAmpsTRAP TRAP-TYPE
ENTERPRISE geistmfg
VARIABLES { outlet4AB-2DeciAmps }
DESCRIPTION "Amps outlet4AB-2DeciAmps Trap"
::= 7

outlet5BC-2DeciAmpsTRAP TRAP-TYPE
ENTERPRISE geistmfg
VARIABLES { outlet5BC-2DeciAmps }
DESCRIPTION "Amps outlet5BC-2DeciAmps Trap"
::= 8

outlet6CA-2DeciAmpsTRAP TRAP-TYPE
ENTERPRISE geistmfg
VARIABLES { outlet6CA-2DeciAmps }
DESCRIPTION "Amps outlet6CA-2DeciAmps Trap"
::= 9



outlet7AB-3DeciAmpsTRAP TRAP-TYPE
ENTERPRISE geistmfg
VARIABLES { outlet7AB-3DeciAmps }
DESCRIPTION "Amps outlet7AB-3DeciAmps Trap"
::= 10

outlet8BC-3DeciAmpsTRAP TRAP-TYPE
ENTERPRISE geistmfg
VARIABLES { outlet8BC-3DeciAmps }
DESCRIPTION "Amps outlet8BC-3DeciAmps Trap"
::= 11

outlet9CA-3DeciAmpsTRAP TRAP-TYPE
ENTERPRISE geistmfg
VARIABLES { outlet9CA-3DeciAmps }
DESCRIPTION "Amps outlet9CA-3DeciAmps Trap"
::= 12



outlet10AB-4DeciAmpsTRAP TRAP-TYPE
ENTERPRISE geistmfg
VARIABLES { outlet10AB-4DeciAmps }
DESCRIPTION "Amps outlet10AB-4DeciAmps Trap"
::= 13

outlet11BC-4DeciAmpsTRAP TRAP-TYPE
ENTERPRISE geistmfg
VARIABLES { outlet11BC-4DeciAmps }
DESCRIPTION "Amps outlet11BC-4DeciAmps Trap"
::= 14

outlet12CA-4DeciAmpsTRAP TRAP-TYPE
ENTERPRISE geistmfg
VARIABLES { outlet12CA-4DeciAmps }
DESCRIPTION "Amps outlet12CA-4DeciAmps Trap"
::= 15



END
