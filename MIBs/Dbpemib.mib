UPS-MIB DEFINITIONS ::= BEGIN

IMPORTS
--      AutonomousType
--              FROM RFC1316-MIB
        TRAP-TYPE
                FROM RFC-1215
        DisplayString
                FROM RFC1213-MIB
        OBJECT-TYPE
                FROM RFC-1212
        Gauge, IpAddress,Counter, TimeTicks, mgmt, private
                FROM RFC1155-SMI
--      TestAndIncr, TimeInterval, TimeStamp
--              FROM SNMPv2-TC
            ;

PositiveInteger ::=
    INTEGER

NonNegativeInteger ::=
    INTEGER

TimeStamp ::=
    TimeTicks

TimeInterval ::=
    INTEGER (0..2147483647)

TestAndIncr ::=
    INTEGER (0..2147483647)

AutonomousType ::=
    DisplayString

enterprises      OBJECT IDENTIFIER ::= { private 1 }
upsMIB     OBJECT IDENTIFIER ::= { enterprises  5763 }
--mib-2      OBJECT IDENTIFIER ::= { mgmt    1 }
--upsMIB     OBJECT IDENTIFIER ::= { mib-2  33 }
upsObjects OBJECT IDENTIFIER ::= { upsMIB  1 }
CustomUpsMIB OBJECT IDENTIFIER ::= { upsMIB  2 }
setup	OBJECT IDENTIFIER ::= { upsMIB  3 }

upsStatus OBJECT IDENTIFIER ::= { CustomUpsMIB  1 }

Mainsok OBJECT-TYPE
    SYNTAX  INTEGER 
    ACCESS  read-only
    STATUS  mandatory
    DESCRIPTION
           "mainsok"
    ::= { upsStatus  1 }

Mainsfail OBJECT-TYPE
    SYNTAX  INTEGER 
    ACCESS  read-only
    STATUS  mandatory
    DESCRIPTION
           "mains fail"
    ::= { upsStatus  2 }

Overload OBJECT-TYPE
    SYNTAX  INTEGER 
    ACCESS  read-only
    STATUS  mandatory
    DESCRIPTION
           "Over load"
    ::= { upsStatus  3 }

Batterylow OBJECT-TYPE
    SYNTAX  INTEGER
    ACCESS  read-only
    STATUS  mandatory
    DESCRIPTION
           "Battery low"
    ::= { upsStatus  4 }

Scheduledshutdown OBJECT-TYPE
    SYNTAX  INTEGER 
    ACCESS  read-only
    STATUS  mandatory
    DESCRIPTION
           "Scheduled shutdown"
    ::= { upsStatus  5 }

Testpassed OBJECT-TYPE
    SYNTAX  INTEGER 
    ACCESS  read-only
    STATUS  mandatory
    DESCRIPTION
           "Test passed"
    ::= { upsStatus  6 }


Testfailed OBJECT-TYPE
    SYNTAX  INTEGER 
    ACCESS  read-only
    STATUS  mandatory
    DESCRIPTION
           "Test Failed"
    ::= { upsStatus  7 }

Testinvalid OBJECT-TYPE
    SYNTAX  INTEGER 
    ACCESS  read-only
    STATUS  mandatory
    DESCRIPTION
           "Test invalid"
    ::= { upsStatus  8 }

Testbeingdone OBJECT-TYPE
    SYNTAX  INTEGER 
    ACCESS  read-only
    STATUS  mandatory
    DESCRIPTION
           "Test being done"
    ::= { upsStatus  9 }

Loadonstaticbypass OBJECT-TYPE
    SYNTAX  INTEGER 
    ACCESS  read-only
    STATUS  mandatory
    DESCRIPTION
           "Load on static bypass"
    ::= { upsStatus  10 }


upsParameters OBJECT IDENTIFIER ::= { CustomUpsMIB  2 }

MainsVoltage OBJECT-TYPE
    SYNTAX  DisplayString
    ACCESS  read-only
    STATUS  mandatory
    DESCRIPTION
           "MainsVoltage."
    ::= { upsParameters  1 }

DCVoltage OBJECT-TYPE
    SYNTAX  DisplayString
    ACCESS  read-only
    STATUS  mandatory
    DESCRIPTION
           "DCVoltage."
    ::= { upsParameters  2 }

BatteryCurrent OBJECT-TYPE
    SYNTAX  DisplayString
    ACCESS  read-only
    STATUS  mandatory
    DESCRIPTION
           "BatteryCurrent."
    ::= { upsParameters  3 }

OutputVoltage OBJECT-TYPE
    SYNTAX  DisplayString
    ACCESS  read-only
    STATUS  mandatory
    DESCRIPTION
           "OutputVoltage."
    ::= { upsParameters  4 }

BatteryVoltage OBJECT-TYPE
    SYNTAX  DisplayString
    ACCESS  read-only
    STATUS  mandatory
    DESCRIPTION
           "BatteryVoltage."
    ::= { upsParameters  5 }

UPSLoad OBJECT-TYPE
    SYNTAX  DisplayString
    ACCESS  read-only
    STATUS  mandatory
    DESCRIPTION
           "UPSLoad."
    ::= { upsParameters  6 }

MainsFrequency OBJECT-TYPE
    SYNTAX  DisplayString
    ACCESS  read-only
    STATUS  mandatory
    DESCRIPTION
           "MainsFrequency."
    ::= { upsParameters  7 }

UPSTemp OBJECT-TYPE
    SYNTAX  DisplayString
    ACCESS  read-only
    STATUS  mandatory
    DESCRIPTION
           "UPSTemp."
    ::= { upsParameters  8 }

BatteryTime OBJECT-TYPE
    SYNTAX  DisplayString
    ACCESS  read-only
    STATUS  mandatory
    DESCRIPTION
           "BatteryTime."
    ::= { upsParameters  9 }

upsConfiguration OBJECT IDENTIFIER ::= { CustomUpsMIB  3 }

LowBatteryRunTime OBJECT-TYPE
    SYNTAX  DisplayString
    ACCESS  read-write
    STATUS  mandatory
    DESCRIPTION
           "LowBatteryRunTime."
    ::= { upsConfiguration  1 }

ShutDownDelay OBJECT-TYPE
    SYNTAX  DisplayString
    ACCESS  read-write
    STATUS  mandatory
    DESCRIPTION
           "ShutDownDelay."
    ::= { upsConfiguration  2 }

LowBatteryCapacity OBJECT-TYPE
    SYNTAX  DisplayString
    ACCESS  read-write
    STATUS  mandatory
    DESCRIPTION
           "LowBatteryCapacity."
    ::= { upsConfiguration  3 }

WakeUpDelay OBJECT-TYPE
    SYNTAX  DisplayString
    ACCESS  read-write
    STATUS  mandatory
    DESCRIPTION
           "WakeUpDelay."
    ::= { upsConfiguration  4 }


BatteryAH OBJECT-TYPE
    SYNTAX  DisplayString
    ACCESS  read-write
    STATUS  mandatory
    DESCRIPTION
           "BatteryAH."
    ::= { upsConfiguration  5 }










upsIdent OBJECT IDENTIFIER ::= { upsObjects  1 }

upsIdentManufacturer OBJECT-TYPE
    SYNTAX  DisplayString
    ACCESS  read-only
    STATUS  mandatory
    DESCRIPTION
           "The name of the UPS manufacturer."
    ::= { upsIdent  1 }

upsIdentModel OBJECT-TYPE
    SYNTAX  DisplayString
    ACCESS  read-only
    STATUS  mandatory
    DESCRIPTION
           "The UPS Model designation."
    ::= { upsIdent  2 }

upsIdentUPSSoftwareVersion OBJECT-TYPE
    SYNTAX  DisplayString
    ACCESS  read-only
    STATUS  mandatory
    DESCRIPTION
           "The UPS firmware/software version(s).  This variable
               may or may not have the same value as
               upsIdentAgentSoftwareVersion in some implementations."
    ::= { upsIdent  3 }

upsIdentAgentSoftwareVersion OBJECT-TYPE
    SYNTAX  DisplayString
    ACCESS  read-only
    STATUS  mandatory
    DESCRIPTION
           "The UPS agent software version.  This variable may or
               may not have the same value as
               upsIdentUPSSoftwareVersion in some implementations."
    ::= { upsIdent  4 }

upsIdentName OBJECT-TYPE
    SYNTAX  DisplayString
    ACCESS  read-write
    STATUS  mandatory
    DESCRIPTION
           "A string identifying the UPS.  This object should be
               set by the administrator."
    ::= { upsIdent  5 }

upsIdentAttachedDevices OBJECT-TYPE
    SYNTAX  DisplayString
    ACCESS  read-write
    STATUS  mandatory
    DESCRIPTION
           "A string identifying the devices attached to the
               output(s) of the UPS.  This object should be set by
               the administrator."
    ::= { upsIdent  6 }

upsBattery OBJECT IDENTIFIER ::= { upsObjects  2 }

upsBatteryCondition OBJECT-TYPE
    SYNTAX  DisplayString  
    ACCESS  read-only
    STATUS  mandatory
    DESCRIPTION
           "Ups Battery Condition "
    ::= { upsBattery  1 }

upsBatteryStatus OBJECT-TYPE
    SYNTAX  DisplayString 
    ACCESS  read-only
    STATUS  mandatory
    DESCRIPTION
           "The indication of the capacity remaining in the UPS
               system's batteries.   A value of batteryNormal
               indicates that the remaining run-time is greater than
               upsConfigLowBattTime.  A value of batteryLow indicates
               that the remaining battery run-time is less than or
               equal to upsConfigLowBattTime.  A value of
               batteryDepleted indicates that the UPS will be unable
               to sustain the present load when and if the utility
               power is lost (including the possibility that the
               utility power is currently absent and the UPS is
               unable to sustain the output)."
    ::= { upsBattery  2 }

upsBatteryCharge OBJECT-TYPE
    SYNTAX  DisplayString  -- UNITS seconds
    ACCESS  read-only
    STATUS  mandatory
    DESCRIPTION
           "Battery Charge "
    ::= { upsBattery  3 }

upsSecondsOnBattery OBJECT-TYPE
    SYNTAX  DisplayString  -- UNITS seconds
    ACCESS  read-only
    STATUS  mandatory
    DESCRIPTION
           "If the unit is on battery power, the elapsed time
               since the UPS last switched to battery power, or the
               time since the network management subsystem was last
               restarted, whichever is less.  Zero shall be returned
               if the unit is not on battery power."
    ::= { upsBattery  4 }

upsEstimatedMinutesRemaining OBJECT-TYPE
    SYNTAX  DisplayString     -- UNITS minutes
    ACCESS  read-only
    STATUS  mandatory
    DESCRIPTION
           "An estimate of the time to battery charge depletion
               under the present load conditions if the utility power
               is off and remains off, or if it were to be lost and
               remain off."
    ::= { upsBattery  5 }

upsEstimatedChargeRemaining OBJECT-TYPE
    SYNTAX  DisplayString     -- UNITS percent
    ACCESS  read-only
    STATUS  mandatory
    DESCRIPTION
           "An estimate of the battery charge remaining expressed
               as a percent of full charge."
    ::= { upsBattery  6 }

upsBatteryVoltage1 OBJECT-TYPE
    SYNTAX  DisplayString  -- UNITS 0.1 Volt DC
    ACCESS  read-only
    STATUS  mandatory
    DESCRIPTION
           "The magnitude of the present battery voltage."
    ::= { upsBattery  7 }

upsBatteryCurrent1 OBJECT-TYPE
    SYNTAX  DisplayString    -- UNITS 0.1 Amp DC
    ACCESS  read-only
    STATUS  mandatory
    DESCRIPTION
           "The present battery current."
    ::= { upsBattery  8 }

upsBatteryTemperature OBJECT-TYPE
    SYNTAX  DisplayString    -- UNITS degrees Centigrade
    ACCESS  read-only
    STATUS  mandatory
    DESCRIPTION
           "The ambient temperature at or near the UPS Battery
               casing."
    ::= { upsBattery  9 }

upsBatteryVoltage2 OBJECT-TYPE
    SYNTAX  DisplayString  -- UNITS 0.1 Volt DC
    ACCESS  read-only
    STATUS  mandatory
    DESCRIPTION
           "The magnitude of the present battery voltage."
    ::= { upsBattery  10 }

upsBatteryCurrent2 OBJECT-TYPE
    SYNTAX  DisplayString    -- UNITS 0.1 Amp DC
    ACCESS  read-only
    STATUS  mandatory
    DESCRIPTION
           "The present battery current."
    ::= { upsBattery  11 }

upsBatteryTotalMin OBJECT-TYPE
    SYNTAX  DisplayString    -- UNITS 0.1 Amp DC
    ACCESS  read-only
    STATUS  mandatory
    DESCRIPTION
           "BatteryTotalMin."
    ::= { upsBattery  12 }

upsInput OBJECT IDENTIFIER ::= { upsObjects  3 }

upsInputLineBads OBJECT-TYPE
    SYNTAX  DisplayString
    ACCESS  read-only
    STATUS  mandatory
    DESCRIPTION
           "A count of the number of times the input entered an
               out-of-tolerance condition as defined by the
               manufacturer.  This count is incremented by one each
               time the input transitions from zero out-of-tolerance
               lines to one or more input lines out-of-tolerance."
    ::= { upsInput  1 }

upsInputNumLines OBJECT-TYPE
    SYNTAX  DisplayString
    ACCESS  read-only
    STATUS  mandatory
    DESCRIPTION
           "The number of input lines utilized in this device.
               This variable indicates the number of rows in the
               input table."
    ::= { upsInput  2 }

upsInputPowerFactor OBJECT-TYPE
    SYNTAX  DisplayString
    ACCESS  read-only
    STATUS  mandatory
    DESCRIPTION
           "The number of input lines utilized in this device.
               This variable indicates the number of rows in the
               input table."
    ::= { upsInput  3 }

upsInputFrequencyR OBJECT-TYPE
    SYNTAX  DisplayString  -- UNITS 0.1 Hertz
    ACCESS  read-only
    STATUS  mandatory
    DESCRIPTION
           "The present input frequency."
    ::= { upsInput  4 }

upsInputFrequencyY OBJECT-TYPE
    SYNTAX  DisplayString  -- UNITS 0.1 Hertz
    ACCESS  read-only
    STATUS  mandatory
    DESCRIPTION
           "The present input frequency."
    ::= { upsInput  5 }

upsInputFrequencyB OBJECT-TYPE
    SYNTAX  DisplayString  -- UNITS 0.1 Hertz
    ACCESS  read-only
    STATUS  mandatory
    DESCRIPTION
           "The present input frequency."
    ::= { upsInput  6 }

upsInputVoltageR OBJECT-TYPE
    SYNTAX  DisplayString  -- UNITS RMS Volts
    ACCESS  read-only
    STATUS  mandatory
    DESCRIPTION
           "The magnitude of the present input voltage."
    ::= { upsInput  7 }

upsInputVoltageY OBJECT-TYPE
    SYNTAX  DisplayString  -- UNITS RMS Volts
    ACCESS  read-only
    STATUS  mandatory
    DESCRIPTION
           "The magnitude of the present input voltage."
    ::= { upsInput  8 }

upsInputVoltageB OBJECT-TYPE
    SYNTAX  DisplayString  -- UNITS RMS Volts
    ACCESS  read-only
    STATUS  mandatory
    DESCRIPTION
           "The magnitude of the present input voltage."
    ::= { upsInput  9 }

upsInputCurrentR OBJECT-TYPE
    SYNTAX  DisplayString  -- UNITS 0.1 RMS Amp
    ACCESS  read-only
    STATUS  mandatory
    DESCRIPTION
           "The magnitude of the present input current."
    ::= { upsInput  10 }

upsInputCurrentY OBJECT-TYPE
    SYNTAX  DisplayString  -- UNITS 0.1 RMS Amp
    ACCESS  read-only
    STATUS  mandatory
    DESCRIPTION
           "The magnitude of the present input current."
    ::= { upsInput  11 }

upsInputCurrentB OBJECT-TYPE
    SYNTAX  DisplayString  -- UNITS 0.1 RMS Amp
    ACCESS  read-only
    STATUS  mandatory
    DESCRIPTION
           "The magnitude of the present input current."
    ::= { upsInput  12 }

upsInputTruePowerR OBJECT-TYPE
    SYNTAX  DisplayString  -- UNITS Watts
    ACCESS  read-only
    STATUS  mandatory
    DESCRIPTION
           "The magnitude of the present input true power."
    ::= { upsInput  13 }

upsInputTruePowerY OBJECT-TYPE
    SYNTAX  DisplayString  -- UNITS Watts
    ACCESS  read-only
    STATUS  mandatory
    DESCRIPTION
           "The magnitude of the present input true power."
    ::= { upsInput  14 }

upsInputTruePowerB OBJECT-TYPE
    SYNTAX  DisplayString  -- UNITS Watts
    ACCESS  read-only
    STATUS  mandatory
    DESCRIPTION
           "The magnitude of the present input true power."
    ::= { upsInput  15 }

upsInputApperentPowerR OBJECT-TYPE
    SYNTAX  DisplayString  -- UNITS 0.1 RMS Amp
    ACCESS  read-only
    STATUS  mandatory
    DESCRIPTION
           "The magnitude of the present input Apperent Power."
    ::= { upsInput  16 }


upsInputApperentPowerY OBJECT-TYPE
    SYNTAX  DisplayString  -- UNITS 0.1 RMS Amp
    ACCESS  read-only
    STATUS  mandatory
    DESCRIPTION
           "The magnitude of the present input Apperent Power."
    ::= { upsInput  17 }

upsInputApperentPowerB OBJECT-TYPE
    SYNTAX  DisplayString  -- UNITS 0.1 RMS Amp
    ACCESS  read-only
    STATUS  mandatory
    DESCRIPTION
           "The magnitude of the present input Apperent Power."
    ::= { upsInput  18 }

upsInputVoltAToNR OBJECT-TYPE
    SYNTAX  DisplayString  -- UNITS Watts
    ACCESS  read-only
    STATUS  mandatory
    DESCRIPTION
           "The magnitude of the present input Voltage."
    ::= { upsInput  19 }

upsInputVoltAToNY OBJECT-TYPE
    SYNTAX  DisplayString  -- UNITS Watts
    ACCESS  read-only
    STATUS  mandatory
    DESCRIPTION
           "The magnitude of the present input Voltage."
    ::= { upsInput  20 }

upsInputVoltAToNB OBJECT-TYPE
    SYNTAX  DisplayString  -- UNITS Watts
    ACCESS  read-only
    STATUS  mandatory
    DESCRIPTION
           "The magnitude of the present input Voltage."
    ::= { upsInput  21 }

upsOutput OBJECT IDENTIFIER ::= { upsObjects  4 }

upsOutputSource OBJECT-TYPE
    SYNTAX  DisplayString 
    ACCESS  read-only
    STATUS  mandatory
    DESCRIPTION
           "The present source of output power.  The enumeration
               none(2) indicates that there is no source of output
               power (and therefore no output power), for example,
               the system has opened the output breaker."
    ::= { upsOutput  1 }

upsOutputFrequency OBJECT-TYPE
    SYNTAX  DisplayString  -- UNITS 0.1 Hertz
    ACCESS  read-only
    STATUS  mandatory
    DESCRIPTION
           "The present output frequency."
    ::= { upsOutput  2 }

upsOutputNumLines OBJECT-TYPE
    SYNTAX  DisplayString
    ACCESS  read-only
    STATUS  mandatory
    DESCRIPTION
           "The number of output lines utilized in this device.
               This variable indicates the number of rows in the
               output table."
    ::= { upsOutput  3 }

upsOutputPowerFactor OBJECT-TYPE
    SYNTAX  DisplayString
    ACCESS  read-only
    STATUS  mandatory
    DESCRIPTION
           "Ups Power Factor "
    ::= { upsOutput  4 }

upsOutputVoltageR OBJECT-TYPE
    SYNTAX  DisplayString  -- UNITS 0.1 RMS Amp
    ACCESS  read-only
    STATUS  mandatory
    DESCRIPTION
           "The present output Voltage."
    ::= { upsOutput  5 }

upsOutputVoltageY OBJECT-TYPE
    SYNTAX  DisplayString  -- UNITS 0.1 RMS Amp
    ACCESS  read-only
    STATUS  mandatory
    DESCRIPTION
           "The present output Voltage."
    ::= { upsOutput  6 }

upsOutputVoltageB OBJECT-TYPE
    SYNTAX  DisplayString  -- UNITS 0.1 RMS Amp
    ACCESS  read-only
    STATUS  mandatory
    DESCRIPTION
           "The present output Voltage."
    ::= { upsOutput  7 }

upsOutputCurrentR OBJECT-TYPE
    SYNTAX  DisplayString  -- UNITS 0.1 RMS Amp
    ACCESS  read-only
    STATUS  mandatory
    DESCRIPTION
           "The present output current."
    ::= { upsOutput  8 }

upsOutputCurrentY OBJECT-TYPE
    SYNTAX  DisplayString  -- UNITS 0.1 RMS Amp
    ACCESS  read-only
    STATUS  mandatory
    DESCRIPTION
           "The present output current."
    ::= { upsOutput  9 }

upsOutputCurrentB OBJECT-TYPE
    SYNTAX  DisplayString  -- UNITS 0.1 RMS Amp
    ACCESS  read-only
    STATUS  mandatory
    DESCRIPTION
           "The present output current."
    ::= { upsOutput  10 }

upsOutputPowerR OBJECT-TYPE
    SYNTAX  DisplayString  -- UNITS Watts
    ACCESS  read-only
    STATUS  mandatory
    DESCRIPTION
           "The present output true power."
    ::= { upsOutput  11 }

upsOutputPowerY OBJECT-TYPE
    SYNTAX  DisplayString  -- UNITS Watts
    ACCESS  read-only
    STATUS  mandatory
    DESCRIPTION
           "The present output true power."
    ::= { upsOutput  12 }

upsOutputPowerB OBJECT-TYPE
    SYNTAX  DisplayString  -- UNITS Watts
    ACCESS  read-only
    STATUS  mandatory
    DESCRIPTION
           "The present output true power."
    ::= { upsOutput  13 }

upsOutputPercentLoadR OBJECT-TYPE
    SYNTAX  DisplayString     -- UNITS percent
    ACCESS  read-only
    STATUS  mandatory
    DESCRIPTION
           "The percentage of the UPS power capacity presently
               being used on this output line, i.e., the greater of
               the percent load of true power capacity and the
               percent load of VA."
    ::= { upsOutput  14 }

upsOutputPercentLoadY OBJECT-TYPE
    SYNTAX  DisplayString     -- UNITS percent
    ACCESS  read-only
    STATUS  mandatory
    DESCRIPTION
           "The percentage of the UPS power capacity presently
               being used on this output line, i.e., the greater of
               the percent load of true power capacity and the
               percent load of VA."
    ::= { upsOutput  15 }

upsOutputPercentLoadB OBJECT-TYPE
    SYNTAX  DisplayString     -- UNITS percent
    ACCESS  read-only
    STATUS  mandatory
    DESCRIPTION
           "The percentage of the UPS power capacity presently
               being used on this output line, i.e., the greater of
               the percent load of true power capacity and the
               percent load of VA."
    ::= { upsOutput  16 }

upsOutputApperentPowerR OBJECT-TYPE
    SYNTAX  DisplayString  -- UNITS Watts
    ACCESS  read-only
    STATUS  mandatory
    DESCRIPTION
           "The present output true power."
    ::= { upsOutput  17 }

upsOutputApperentPowerY OBJECT-TYPE
    SYNTAX  DisplayString  -- UNITS Watts
    ACCESS  read-only
    STATUS  mandatory
    DESCRIPTION
           "The present output true power."
    ::= { upsOutput  18 }

upsOutputApperentPowerB OBJECT-TYPE
    SYNTAX  DisplayString  -- UNITS Watts
    ACCESS  read-only
    STATUS  mandatory
    DESCRIPTION
           "The present output true power."
    ::= { upsOutput  19 }

upsOutputVoltAToNR OBJECT-TYPE
    SYNTAX  DisplayString     -- UNITS percent
    ACCESS  read-only
    STATUS  mandatory
    DESCRIPTION
           "The percentage of the UPS power capacity presently
               being used on this output line, i.e., the greater of
               the percent load of true power capacity and the
               percent load of VA."
    ::= { upsOutput  20 }

upsOutputVoltAToNY OBJECT-TYPE
    SYNTAX  DisplayString     -- UNITS percent
    ACCESS  read-only
    STATUS  mandatory
    DESCRIPTION
           "The percentage of the UPS power capacity presently
               being used on this output line, i.e., the greater of
               the percent load of true power capacity and the
               percent load of VA."
    ::= { upsOutput  21 }

upsOutputVoltAToNB OBJECT-TYPE
    SYNTAX  DisplayString     -- UNITS percent
    ACCESS  read-only
    STATUS  mandatory
    DESCRIPTION
           "The percentage of the UPS power capacity presently
               being used on this output line, i.e., the greater of
               the percent load of true power capacity and the
               percent load of VA."
    ::= { upsOutput  22 }


upsBypass OBJECT IDENTIFIER ::= { upsObjects  5 }

upsBypassFrequency OBJECT-TYPE
    SYNTAX  DisplayString  -- UNITS 0.1 Hertz
    ACCESS  read-only
    STATUS  mandatory
    DESCRIPTION
           "The present bypass frequency."
    ::= { upsBypass  1 }

upsBypassNumLines OBJECT-TYPE
    SYNTAX  DisplayString
    ACCESS  read-only
    STATUS  mandatory
    DESCRIPTION
           "The number of bypass lines utilized in this device.
               This entry indicates the number of rows in the bypass
               table."
    ::= { upsBypass  2 }

upsBypassVoltageR OBJECT-TYPE
    SYNTAX  DisplayString  -- UNITS RMS Volts
    ACCESS  read-only
    STATUS  mandatory
    DESCRIPTION
           "The present bypass voltage."
    ::= { upsBypass  3 }

upsBypassVoltageY OBJECT-TYPE
    SYNTAX  DisplayString  -- UNITS RMS Volts
    ACCESS  read-only
    STATUS  mandatory
    DESCRIPTION
           "The present bypass voltage."
    ::= { upsBypass  4 }

upsBypassVoltageB OBJECT-TYPE
    SYNTAX  DisplayString  -- UNITS RMS Volts
    ACCESS  read-only
    STATUS  mandatory
    DESCRIPTION
           "The present bypass voltage."
    ::= { upsBypass  5 }

upsBypassCurrentR OBJECT-TYPE
    SYNTAX  DisplayString  -- UNITS 0.1 RMS Amp
    ACCESS  read-only
    STATUS  mandatory
    DESCRIPTION
           "The present bypass current."
    ::= { upsBypass  6 }

upsBypassCurrentY OBJECT-TYPE
    SYNTAX  DisplayString  -- UNITS 0.1 RMS Amp
    ACCESS  read-only
    STATUS  mandatory
    DESCRIPTION
           "The present bypass current."
    ::= { upsBypass  7 }

upsBypassCurrentB OBJECT-TYPE
    SYNTAX  DisplayString  -- UNITS 0.1 RMS Amp
    ACCESS  read-only
    STATUS  mandatory
    DESCRIPTION
           "The present bypass current."
    ::= { upsBypass  8 }

upsBypassPowerR OBJECT-TYPE
    SYNTAX  DisplayString  -- UNITS Watts
    ACCESS  read-only
    STATUS  mandatory
    DESCRIPTION
           "The present true power conveyed by the bypass."
    ::= { upsBypass  9 }

upsBypassPowerY OBJECT-TYPE
    SYNTAX  DisplayString  -- UNITS Watts
    ACCESS  read-only
    STATUS  mandatory
    DESCRIPTION
           "The present true power conveyed by the bypass."
    ::= { upsBypass  10 }

upsBypassPowerB OBJECT-TYPE
    SYNTAX  DisplayString  -- UNITS Watts
    ACCESS  read-only
    STATUS  mandatory
    DESCRIPTION
           "The present true power conveyed by the bypass."
    ::= { upsBypass  11 }

upsWellKnownAlarms OBJECT IDENTIFIER ::= { upsObjects  6 }

upsAlarmsDCOverCurrent OBJECT-TYPE
      SYNTAX  INTEGER { -NA-(3)  }
      ACCESS read-only
      STATUS mandatory
      DESCRIPTION
              "Ups DC Over Current."
      ::= { upsWellKnownAlarms 1 }

upsAlarmInvertorTrip OBJECT-TYPE
      SYNTAX  INTEGER { -NA-(3)  }
      ACCESS read-only
      STATUS mandatory
      DESCRIPTION
              "Ups Invertor Trip"
      ::= { upsWellKnownAlarms 2 }

upsAlarmRectifierOVOC OBJECT-TYPE
      SYNTAX  INTEGER { -NA-(3)  }
      ACCESS read-only
      STATUS mandatory
      DESCRIPTION
              "Ups Rectifier OVOC."
      ::= { upsWellKnownAlarms 3 }

upsAlarmRectifierTrip OBJECT-TYPE
      SYNTAX  INTEGER { -NA-(3)  }
      ACCESS read-only
      STATUS mandatory
      DESCRIPTION
              "Ups Rectfier Trip."
      ::= { upsWellKnownAlarms 4 }

upsAlarmInputSinglePhase OBJECT-TYPE
      SYNTAX  INTEGER { -NA-(3)  }
      ACCESS read-only
      STATUS mandatory
      DESCRIPTION
              "InputSinglePhase."
      ::= { upsWellKnownAlarms 5 }

upsAlarmRectfierFuseFail OBJECT-TYPE
      SYNTAX  INTEGER { -NA-(3)  }
      ACCESS read-only
      STATUS mandatory
      DESCRIPTION
              "RectfierFuseFail."
      ::= { upsWellKnownAlarms 6 }

upsAlarmBatteryPrelow OBJECT-TYPE
      SYNTAX  INTEGER { -NA-(3)  }
      ACCESS read-only
      STATUS mandatory
      DESCRIPTION
              "BatteryPrelow."
      ::= { upsWellKnownAlarms 7 }

upsAlarmBatteryLowTrip OBJECT-TYPE
      SYNTAX  INTEGER { -NA-(3)  }
      ACCESS read-only
      STATUS mandatory
      DESCRIPTION
              "BatteryLowTrip."
      ::= { upsWellKnownAlarms 8 }

upsAlarmPhaseUUV OBJECT-TYPE
      SYNTAX  INTEGER { -NA-(3)  }
      ACCESS read-only
      STATUS mandatory
      DESCRIPTION
              "PhaseUUV."
      ::= { upsWellKnownAlarms 9 }

upsAlarmPhaseVUV OBJECT-TYPE
      SYNTAX  INTEGER { -NA-(3)  }
      ACCESS read-only
      STATUS mandatory
      DESCRIPTION
              "PhaseVUV."
      ::= { upsWellKnownAlarms 10 }

upsAlarmPhaseWUV OBJECT-TYPE
      SYNTAX  INTEGER { -NA-(3)  }
      ACCESS read-only
      STATUS mandatory
      DESCRIPTION
              "PhaseWUV."
      ::= { upsWellKnownAlarms 11 }

upsAlarmPhaseUOV OBJECT-TYPE
      SYNTAX  INTEGER { -NA-(3)  }
      ACCESS read-only
      STATUS mandatory
      DESCRIPTION
              "PhaseUOV."
      ::= { upsWellKnownAlarms 12 }

upsAlarmPhaseVOV OBJECT-TYPE
      SYNTAX  INTEGER { -NA-(3)  }
      ACCESS read-only
      STATUS mandatory
      DESCRIPTION
              "PhaseVOV."
      ::= { upsWellKnownAlarms 13 }

upsAlarmPhaseWOV OBJECT-TYPE
      SYNTAX  INTEGER { -NA-(3)  }
      ACCESS read-only
      STATUS mandatory
      DESCRIPTION
              "PhaseWOV."
      ::= { upsWellKnownAlarms 14 }

upsAlarmDCOverVoltage OBJECT-TYPE
      SYNTAX  INTEGER { -NA-(3)  }
      ACCESS read-only
      STATUS mandatory
      DESCRIPTION
              "DCOverVoltage."
      ::= { upsWellKnownAlarms 15 }

upsAlarm16 OBJECT-TYPE
      SYNTAX  INTEGER { -NA-(3)  }
      ACCESS read-only
      STATUS mandatory
      DESCRIPTION
              "Alarm#16."
      ::= { upsWellKnownAlarms 16 }

  upsAlarmTempBad OBJECT-TYPE
      SYNTAX  INTEGER { -NA-(3)  }
      ACCESS read-only
      STATUS mandatory
      DESCRIPTION
              "TempBad."
      ::= { upsWellKnownAlarms 17 }

   upsAlarmInputBad OBJECT-TYPE
      SYNTAX  INTEGER { -NA-(3)  }
      ACCESS read-only
      STATUS mandatory
       DESCRIPTION
               "InputBad."
       ::= { upsWellKnownAlarms  18 }

   upsAlarmOutputBad OBJECT-TYPE
      SYNTAX  INTEGER { -NA-(3)  }
      ACCESS read-only
      STATUS mandatory
       DESCRIPTION
               "OutputBad."
       ::= { upsWellKnownAlarms  19 }

  upsAlarmOutputOverload OBJECT-TYPE
      SYNTAX  INTEGER { -NA-(3)  }
      ACCESS read-only
      STATUS mandatory
      DESCRIPTION
              "OutputOverload."
      ::= { upsWellKnownAlarms 20 }

   upsAlarmBypassBad OBJECT-TYPE
      SYNTAX  INTEGER { -NA-(3)  }
      ACCESS read-only
      STATUS mandatory
       DESCRIPTION
               "BypassBad."
       ::= { upsWellKnownAlarms 21 }

 upsAlarmOutputOff OBJECT-TYPE
      SYNTAX  INTEGER { -NA-(3)  }
      ACCESS read-only
      STATUS mandatory
      DESCRIPTION
               "OutputOff."
      ::= { upsWellKnownAlarms 22 }

 upsAlarmShutDown OBJECT-TYPE
      SYNTAX  INTEGER { -NA-(3)  }
      ACCESS read-only
      STATUS mandatory
      DESCRIPTION
               "The UPS has shutdown as requested, i.e., the output
               is off."
      ::= { upsWellKnownAlarms 23 }

upsAlarmChargerFailed OBJECT-TYPE
      SYNTAX  INTEGER { -NA-(3)  }
      ACCESS read-only
      STATUS mandatory
       DESCRIPTION
               "An uncorrected problem has been detected within the
               UPS charger subsystem."
       ::= { upsWellKnownAlarms 24 }

upsAlarmUpsSystemOff OBJECT-TYPE
      SYNTAX  INTEGER { NO(0), YES(1) ,-NA-(3) }
      ACCESS read-only
      STATUS mandatory
      DESCRIPTION
               "The output of the UPS is in the off state."
      ::= { upsWellKnownAlarms 25 }

upsAlarmFanFailure OBJECT-TYPE
      SYNTAX  INTEGER { NO(0), YES(1) ,-NA-(3) }
      ACCESS read-only
      STATUS mandatory
       DESCRIPTION
               "The failure of one or more fans in the UPS has been
               detected."
       ::= { upsWellKnownAlarms 26 }

upsAlarmFuseFailure OBJECT-TYPE
      SYNTAX  INTEGER { -NA-(3)  }
      ACCESS read-only
      STATUS mandatory
       DESCRIPTION
               "The failure of one or more fuses has been detected."
       ::= { upsWellKnownAlarms 27 }

upsAlarmGeneralFault OBJECT-TYPE
      SYNTAX  INTEGER { -NA-(3)  }
      ACCESS read-only
      STATUS mandatory
       DESCRIPTION
               "A general fault in the UPS has been detected."
       ::= { upsWellKnownAlarms 28 }

upsAlarmAwaitingPower OBJECT-TYPE
      SYNTAX  INTEGER { -NA-(3)  }
      ACCESS read-only
      STATUS mandatory
       DESCRIPTION
               "The UPS output is off and the UPS is awaiting the
               return of input power."
       ::= { upsWellKnownAlarms 29 }

 upsAlarmShutdownPending OBJECT-TYPE
      SYNTAX  INTEGER { NO(0), YES(1) ,-NA-(3) }
      ACCESS read-only
      STATUS mandatory
      DESCRIPTION
              "A upsShutdownAfterDelay countdown is underway."
      ::= { upsWellKnownAlarms 30 }

  upsAlarmShutdownImminent OBJECT-TYPE
      SYNTAX  INTEGER { -NA-(3)  }
      ACCESS read-only
      STATUS mandatory
       DESCRIPTION
               "The UPS will turn off power to the load in less than
               5 seconds; this may be either a timed shutdown or a
               low battery shutdown."
      ::= { upsWellKnownAlarms 31 }

upsAlarmAmbientTemp OBJECT-TYPE
      SYNTAX  INTEGER { NO(0), YES(1) ,-NA-(3) }
      ACCESS read-only
      STATUS mandatory
      DESCRIPTION
              "One or more batteries have been determined to require
              replacement."
      ::= { upsWellKnownAlarms 32 }

upsAlarmInvertorTemp OBJECT-TYPE
      SYNTAX  INTEGER { NO(0), YES(1) ,-NA-(3) }
      ACCESS read-only
      STATUS mandatory
      DESCRIPTION
              "The UPS is drawing power from the batteries."
      ::= { upsWellKnownAlarms 33 }

  upsAlarmBypassTemp OBJECT-TYPE
      SYNTAX  INTEGER { -NA-(3)  }
      ACCESS read-only
      STATUS mandatory
      DESCRIPTION
               "The remaining battery run-time is less than or equal
               to upsConfigLowBattTime."
      ::= { upsWellKnownAlarms 34 }

  upsAlarmBatteryTemp OBJECT-TYPE
      SYNTAX  INTEGER { -NA-(3)  }
      ACCESS read-only
      STATUS mandatory
      DESCRIPTION
              "The UPS will be unable to sustain the present load
              when and if the utility power is lost."
      ::= { upsWellKnownAlarms 35 }


    upsAlarmInvertorFail OBJECT-TYPE
      SYNTAX  INTEGER { -NA-(3)  }
      ACCESS read-only
      STATUS mandatory
       DESCRIPTION
               "The Bypass is presently engaged on the UPS."
       ::= { upsWellKnownAlarms  36 }

upsAlarmEmergencyPowerOff OBJECT-TYPE
      SYNTAX  INTEGER { -NA-(3)  }
      ACCESS read-only
      STATUS mandatory
       DESCRIPTION
               "The entire UPS has shutdown as commanded."
       ::= { upsWellKnownAlarms 37 }


  upsAlarmBatteryGrError OBJECT-TYPE
      SYNTAX  INTEGER { -NA-(3) }
      ACCESS read-only
      STATUS mandatory
       DESCRIPTION
               "The UPS system is in the off state."
       ::= { upsWellKnownAlarms 38 }


 upsAlarmCircuitOpen OBJECT-TYPE
      SYNTAX  INTEGER { -NA-(3)  }
      ACCESS read-only
      STATUS mandatory
      DESCRIPTION
              "The result of the last diagnostic test indicates a
              failure."
      ::= { upsWellKnownAlarms 39 }

  upsAlarmSyncError OBJECT-TYPE
      SYNTAX  INTEGER { -NA-(3) }
      ACCESS read-only
      STATUS mandatory
      DESCRIPTION
              "A problem has been encountered in the
              communications between the agent and the UPS."
      ::= { upsWellKnownAlarms 40 }


upsTest OBJECT IDENTIFIER ::= { upsObjects  7 }

upsTestResultsSummary OBJECT-TYPE
    SYNTAX  DisplayString 
    ACCESS  read-only
    STATUS  mandatory
    DESCRIPTION
           "The results of the current or last UPS diagnostics
               test performed.  The values for donePass(1),
               doneWarning(2), and doneError(3) indicate that the
               test completed either successfully, with a warning, or
               with an error, respectively.  The value aborted(4) is
               returned for tests which are aborted by setting the
               value of upsTestId to upsTestAbortTestInProgress.
               Tests which have not yet concluded are indicated by
               inProgress(5).  The value noTestsInitiated(6)
               indicates that no previous test results are available,
               such as is the case when no tests have been run since
               the last reinitialization of the network management
               subsystem and the system has no provision for non-
               volatile storage of test results."
    ::= { upsTest  1 }

upsTestResultsDetail OBJECT-TYPE
    SYNTAX  DisplayString
    ACCESS  read-only
    STATUS  mandatory
    DESCRIPTION
           "Additional information about upsTestResultsSummary.
               If no additional information available, a zero length
               string is returned."
    ::= { upsTest  2 }

  upsTestId OBJECT-TYPE
      SYNTAX DisplayString
      ACCESS read-write
      STATUS mandatory
      DESCRIPTION
              "The test named by an OBJECT IDENTIFIER which
              allows a standard mechanism for the initiation of
              test, including the well known tests identified in
              this document as well as those introduced by a
              particular implementation, i.e., as
              documented in the private enterprise MIB definition
              for the device.

              Setting this variable initiates the named test.  Sets
              to this variable require the presence of
              upsTestSpinLock in the same SNMP message.

              The set request will be rejected with an appropriate
              error message if the requested test cannot be
              performed, including attempts to start a test when
              another test is already in progress.  Tests in
              progress may be aborted by setting this variable to
              upsTestAbortTestInProgress.

              Read operations return the value of the name of the
              test in progress if a test is in progress or the name
              of the last test performed if no test is in progress,
              unless no test has bee run, in which case the well
              known value upsTestNoTestsInitiated is returned."
              ::= { upsTest 3 }

upsControl OBJECT IDENTIFIER ::= { upsObjects  8 }

upsShutdownType OBJECT-TYPE
    SYNTAX  DisplayString
    ACCESS  read-write
    STATUS  mandatory
    DESCRIPTION
           "This object determines the nature of the action to be
               taken at the time when the countdown of the
               upsShutdownAfterDelay and upsRebootWithDuration
               objects reaches zero.

               Setting this object to output(1) indicates that
               shutdown requests should cause only the output of the
               UPS to turn off.  Setting this object to system(2)
               indicates that shutdown requests will cause the entire
               UPS system to turn off."
    ::= { upsControl  1 }

upsShutdownAfterDelay OBJECT-TYPE
    SYNTAX  DisplayString     -- UNITS seconds
    ACCESS  read-write
    STATUS  mandatory
    DESCRIPTION
           "Setting this object will shutdown (i.e., turn off)
               either the UPS output or the UPS system (as determined
               by the value of upsShutdownType at the time of
               shutdown) after the indicated number of seconds, or
               less if the UPS batteries become depleted. Setting
               this object to 0 will cause the shutdown to occur
               immediately.  Setting this object to -1 will abort the
               countdown.  If the system is already in the desired
               state at the time the countdown reaches 0, then
               nothing will happen.  That is, there is no additional
               action at that time if upsShutdownType = system and
               the system is already off.  Similarly, there is no
               additional action at that time if upsShutdownType =
               output and the output is already off.  When read,
               upsShutdownAfterDelay will return the number of
               seconds remaining until shutdown, or -1 if no shutdown
               countdown is in effect.  On some systems, if the agent
               is restarted while a shutdown countdown is in effect,
               the countdown may be aborted.  Sets to this object
               override any upsShutdownAfterDelay already in effect."
    ::= { upsControl  2 }

upsStartupAfterDelay OBJECT-TYPE
    SYNTAX  DisplayString     -- UNITS seconds
    ACCESS  read-write
    STATUS  mandatory
    DESCRIPTION
           "Setting this object will start the output after the
               indicated number of seconds, including starting the
               UPS, if necessary.  Setting this object to 0 will
               cause the startup to occur immediately.  Setting this
               object to -1 will abort the countdown.  If the output
               is already on at the time the countdown reaches 0,
               then nothing will happen.  Sets to this object
               override the effect of any upsStartupAfterDelay
               countdown or upsRebootWithDuration countdown in
               progress.  When read, upsStartupAfterDelay will return
               the number of seconds until startup, or -1 if no
               startup countdown is in effect.  If the countdown
               expires during a utility failure, the startup shall
               not occur until the utility power is restored.  On
               some systems, if the agent is restarted while a
               startup countdown is in effect, the countdown is
               aborted."
    ::= { upsControl  3 }

upsRebootWithDuration OBJECT-TYPE
    SYNTAX  DisplayString     -- UNITS seconds
    ACCESS  read-write
    STATUS  mandatory
    DESCRIPTION
           "Setting this object will immediately shutdown (i.e.,
               turn off) either the UPS output or the UPS system (as
               determined by the value of upsShutdownType at the time
               of shutdown) for a period equal to the indicated
               number of seconds, after which time the output will be
               started, including starting the UPS, if necessary.  If
               the number of seconds required to perform the request
               is greater than the requested duration, then the
               requested shutdown and startup cycle shall be
               performed in the minimum time possible, but in no case
               shall this require more than the requested duration
               plus 60 seconds.  When read, upsRebootWithDuration
               shall return the number of seconds remaining in the
               countdown, or -1 if no countdown is in progress.  If
               the startup should occur during a utility failure, the
               startup shall not occur until the utility power is
               restored."
    ::= { upsControl  4 }

upsAutoRestart OBJECT-TYPE
    SYNTAX  DisplayString
    ACCESS  read-write
    STATUS  mandatory
    DESCRIPTION
           "Setting this object to 'on' will cause the UPS system
               to restart after a shutdown if the shutdown occurred
               during a power loss as a result of either a
               upsShutdownAfterDelay or an internal battery depleted
               condition.  Setting this object to 'off' will prevent
               the UPS system from restarting after a shutdown until
               an operator manually or remotely explicitly restarts
               it.  If the UPS is in a startup or reboot countdown,
               then the UPS will not restart until that delay has
               been satisfied."
    ::= { upsControl  5 }

upsConfig OBJECT IDENTIFIER ::= { upsObjects  9 }

upsConfigInputVoltage OBJECT-TYPE
    SYNTAX  DisplayString  -- UNITS RMS Volts
    ACCESS  read-write
    STATUS  mandatory
    DESCRIPTION
           "The magnitude of the nominal input voltage.  On those
               systems which support read-write access to this
               object, if there is an attempt to set this variable to
               a value that is not supported, the request must be
               rejected and the agent shall respond with an
               appropriate error message, i.e., badValue for SNMPv1,
               or inconsistentValue for SNMPv2."
    ::= { upsConfig  1 }

upsConfigInputFreq OBJECT-TYPE
    SYNTAX  DisplayString  -- UNITS 0.1 Hertz
    ACCESS  read-write
    STATUS  mandatory
    DESCRIPTION
           "The nominal input frequency.  On those systems which
               support read-write access to this object, if there is
               an attempt to set this variable to a value that is not
               supported, the request must be rejected and the agent
               shall respond with an appropriate error message, i.e.,
               badValue for SNMPv1, or inconsistentValue for SNMPv2."
    ::= { upsConfig  2 }

upsConfigOutputVoltage OBJECT-TYPE
    SYNTAX  DisplayString  -- UNITS RMS Volts
    ACCESS  read-write
    STATUS  mandatory
    DESCRIPTION
           "The magnitude of the nominal output voltage.  On
               those systems which support read-write access to this
               object, if there is an attempt to set this variable to
               a value that is not supported, the request must be
               rejected and the agent shall respond with an
               appropriate error message, i.e., badValue for SNMPv1,
               or inconsistentValue for SNMPv2."
    ::= { upsConfig  3 }

upsConfigOutputFreq OBJECT-TYPE
    SYNTAX  DisplayString  -- UNITS 0.1 Hertz
    ACCESS  read-write
    STATUS  mandatory
    DESCRIPTION
           "The nominal output frequency.  On those systems which
               support read-write access to this object, if there is
               an attempt to set this variable to a value that is not
               supported, the request must be rejected and the agent
               shall respond with an appropriate error message, i.e.,
               badValue for SNMPv1, or inconsistentValue for SNMPv2."
    ::= { upsConfig  4 }

upsConfigOutputVA OBJECT-TYPE
    SYNTAX  DisplayString  -- UNITS Volt-Amps
    ACCESS  read-only
    STATUS  mandatory
    DESCRIPTION
           "The magnitude of the nominal Volt-Amp rating."
    ::= { upsConfig  5 }

upsConfigOutputPower OBJECT-TYPE
    SYNTAX  DisplayString  -- UNITS Watts
    ACCESS  read-only
    STATUS  mandatory
    DESCRIPTION
           "The magnitude of the nominal true power rating."
    ::= { upsConfig  6 }

upsConfigLowBattTime OBJECT-TYPE
    SYNTAX  DisplayString  -- UNITS minutes
    ACCESS  read-write
    STATUS  mandatory
    DESCRIPTION
           "The value of upsEstimatedMinutesRemaining at which a
               lowBattery condition is declared.  For agents which
               support only discrete (discontinuous) values, then the
               agent shall round up to the next supported value.  If
               the requested value is larger than the largest
               supported value, then the largest supported value
               shall be selected."
    ::= { upsConfig  7 }

upsConfigAudibleStatus OBJECT-TYPE
    SYNTAX  DisplayString
    ACCESS  read-write
    STATUS  mandatory
    DESCRIPTION
           "The requested state of the audible alarm.  When in
               the disabled state, the audible alarm should never
               sound.  The enabled state is self-describing.  Setting
               this object to muted(3) when the audible alarm is
               sounding shall temporarily silence the alarm.  It will
               remain muted until it would normally stop sounding and
               the value returned for read operations during this
               period shall equal muted(3).  At the end of this
               period, the value shall revert to enabled(2).  Writes
               of the value muted(3) when the audible alarm is not
               sounding shall be accepted but otherwise shall have no
               effect."
    ::= { upsConfig  8 }

upsConfigLowVoltageTransferPoint OBJECT-TYPE
    SYNTAX  DisplayString  -- UNITS RMS Volts
    ACCESS  read-write
    STATUS  mandatory
    DESCRIPTION
           "The minimum input line voltage allowed before the UPS
               system transfers to battery backup."
    ::= { upsConfig  9 }

upsConfigHighVoltageTransferPoint OBJECT-TYPE
    SYNTAX  DisplayString  -- UNITS RMS Volts
    ACCESS  read-write
    STATUS  mandatory
    DESCRIPTION
           "The maximum line voltage allowed before the UPS
               system transfers to battery backup."
    ::= { upsConfig  10 }

upsConfigBatteryDate OBJECT-TYPE
    SYNTAX  DisplayString  -- UNITS RMS Volts
    ACCESS  read-write
    STATUS  mandatory
    DESCRIPTION
           "The minimum input line voltage allowed before the UPS
               system transfers to battery backup."
    ::= { upsConfig  11 }

upsConfigBatteryLife OBJECT-TYPE
    SYNTAX  DisplayString  -- UNITS RMS Volts
    ACCESS  read-write
    STATUS  mandatory
    DESCRIPTION
           "The maximum line voltage allowed before the UPS
               system transfers to battery backup."
    ::= { upsConfig  12 }

upsMisc OBJECT IDENTIFIER ::= { upsObjects  30 }

upsMiscInDate OBJECT-TYPE
    SYNTAX  DisplayString 
    ACCESS  read-write
    STATUS  mandatory
    DESCRIPTION
           "Ups Misc Date."
    ::= { upsMisc  1 }

upsMiscTime OBJECT-TYPE
    SYNTAX  DisplayString 
    ACCESS  read-write
    STATUS  mandatory
    DESCRIPTION
           "Ups Misc Time."
    ::= { upsMisc  2 }

upsMiscBaud OBJECT-TYPE
    SYNTAX  DisplayString 
    ACCESS  read-write
    STATUS  mandatory
    DESCRIPTION
           "Ups Misc Baud Rate."
    ::= { upsMisc  3 }

upsMiscTimeOut OBJECT-TYPE
    SYNTAX  DisplayString 
    ACCESS  read-write
    STATUS  mandatory
    DESCRIPTION
           "Ups Misc Time Out."
    ::= { upsMisc  4 }

upsMiscWeeklySelfTest OBJECT-TYPE
    SYNTAX  DisplayString 
    ACCESS  read-write
    STATUS  mandatory
    DESCRIPTION
           "WeeklySelfTest."
    ::= { upsMisc  5 }

upsMiscMonthlySelfTest OBJECT-TYPE
    SYNTAX  DisplayString 
    ACCESS  read-write
    STATUS  mandatory
    DESCRIPTION
           "MonthlySelfTest."
    ::= { upsMisc  6 }

upsMiscByte1 OBJECT-TYPE
    SYNTAX  DisplayString 
    ACCESS  read-write
    STATUS  mandatory
    DESCRIPTION
           "Ups Misc Byte."
    ::= { upsMisc  7 }

upsMiscByte2 OBJECT-TYPE
    SYNTAX  DisplayString 
    ACCESS  read-write
    STATUS  mandatory
    DESCRIPTION
           "Ups Misc Byte."
    ::= { upsMisc  8 }

upsMiscByte3 OBJECT-TYPE
    SYNTAX  DisplayString 
    ACCESS  read-write
    STATUS  mandatory
    DESCRIPTION
           "Ups Misc Byte."
    ::= { upsMisc  9 }

upsMiscByte4 OBJECT-TYPE
    SYNTAX  DisplayString 
    ACCESS  read-write
    STATUS  mandatory
    DESCRIPTION
           "Ups Misc Byte."
    ::= { upsMisc  10 }

upsMiscDailyShutDown OBJECT-TYPE
    SYNTAX  DisplayString 
    ACCESS  read-write
    STATUS  mandatory
    DESCRIPTION
           "DailyShutDown."
    ::= { upsMisc  11 }

upsMiscDailyStartUp OBJECT-TYPE
    SYNTAX  DisplayString 
    ACCESS  read-write
    STATUS  mandatory
    DESCRIPTION
           "DailyStartUp."
    ::= { upsMisc  12 }

upsMiscShort3 OBJECT-TYPE
    SYNTAX  DisplayString 
    ACCESS  read-write
    STATUS  mandatory
    DESCRIPTION
           "Ups Misc Byte."
    ::= { upsMisc  13 }

upsMiscShort4 OBJECT-TYPE
    SYNTAX  DisplayString 
    ACCESS  read-write
    STATUS  mandatory
    DESCRIPTION
           "Ups Misc Byte."
    ::= { upsMisc  14 }

upsMiscWeeklyShutDown OBJECT-TYPE
    SYNTAX  DisplayString 
    ACCESS  read-write
    STATUS  mandatory
    DESCRIPTION
           "WeeklyShutDown."
    ::= { upsMisc  15 }

upsMiscWeeklyStartUp OBJECT-TYPE
    SYNTAX  DisplayString 
    ACCESS  read-write
    STATUS  mandatory
    DESCRIPTION
           "WeeklyStartUp."
    ::= { upsMisc  16 }


trapReceiverIPAddress1 OBJECT-TYPE
    SYNTAX  IpAddress
    ACCESS  read-write
    STATUS mandatory
    DESCRIPTION
        "Trap receiver IP address1"
    ::= { setup 1 }

trapReceiverIPAddress2 OBJECT-TYPE
    SYNTAX  IpAddress
    ACCESS  read-write
    STATUS mandatory
    DESCRIPTION
        "Trap receiver IP address2"
    ::= { setup 2 }

trapCommunity OBJECT-TYPE
    SYNTAX  DisplayString (SIZE (0..7))
    ACCESS  read-write
    STATUS mandatory
    DESCRIPTION
        "Trap community to be used by agent to send trap"
    ::= { setup 3 }

END
