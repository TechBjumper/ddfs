--
-- snmp.MIB
-- MIB generated by CAREL
-- Friday, 29 March 2019
--

CAREL-snmp-MIB DEFINITIONS ::= BEGIN

IMPORTS
	OBJECT-GROUP, NOTIFICATION-GROUP
		FROM SNMPv2-CONF			
	enterprises, MODULE-IDENTITY, OBJECT-TYPE, NOTIFICATION-TYPE, Integer32,
	IpAddress, Counter32, Unsigned32, TimeTicks, Opaque, Counter32, Gauge32
		FROM SNMPv2-SMI
	DisplayString, TruthValue
		FROM SNMPv2-TC;
		
snmp MODULE-IDENTITY
    LAST-UPDATED  "201903291150Z"		-- March 29, 2019 at 11:50 GMT
    ORGANIZATION  "CAREL Industries S.r.l."
    CONTACT-INFO
        "
                Carel Industries S.r.l.
                Via dell'Industria, 11
                35020 Brugine (PD) Italy
                Tel: +39 049 9716611
                E-mail: carel@carel.com
        "
    DESCRIPTION
        "This is the MIB module for the snmp device."
	REVISION "201903291150Z"
	DESCRIPTION
		""
	::= { enterprises 9839 }

-- =====================
--
--  Textual Conventions
--
-- =====================

--
-- Define the Float Textual Convention
--   This definition was written by David Perkins.
--

Float ::= TEXTUAL-CONVENTION
    STATUS      current
    DESCRIPTION
        "A single precision floating-point number.  The semantics
         and encoding are identical for type 'single' defined in
         IEEE Standard for Binary Floating-Point,
         ANSI/IEEE Std 754-1985.
         The value is restricted to the BER serialization of
         the following ASN.1 type:
             FLOATTYPE ::= [120] IMPLICIT FloatType
         (note: the value 120 is the sum of '30'h and '48'h)
         The BER serialization of the length for values of
         this type must use the definite length, short
         encoding form.

         For example, the BER serialization of value 123
         of type FLOATTYPE is '9f780442f60000'h.  (The tag
         is '9f78'h; the length is '04'h; and the value is
         '42f60000'h.) The BER serialization of value
         '9f780442f60000'h of data type Opaque is
         '44079f780442f60000'h. (The tag is '44'h; the length
         is '07'h; and the value is '9f780442f60000'h.)"
    SYNTAX Opaque (SIZE (7))


--
-- Node definitions
--

-- 1.3.6.1.4.1.9839.1.2
snmpVariables OBJECT IDENTIFIER ::= { snmp 1 2 }

-- 1.3.6.1.4.1.9839.1.2.1.0
p1-CISNIENIE OBJECT-TYPE
	SYNTAX Integer32 (0.0..10.0)
	UNITS "bar"
	MAX-ACCESS read-only
	STATUS current
	DESCRIPTION "CISNIENIE-CZUJNIK-1"
	::= { snmpVariables 1 }

-- 1.3.6.1.4.1.9839.1.2.2.0
p2-CISNIENIE OBJECT-TYPE
	SYNTAX Integer32 (0.0..10.0)
	UNITS "bar"
	MAX-ACCESS read-only
	STATUS current
	DESCRIPTION "CISNIENIE-CZUJNIK-2"
	::= { snmpVariables 2 }

-- 1.3.6.1.4.1.9839.1.2.3.0
p3-CISNIENIE OBJECT-TYPE
	SYNTAX Integer32 (0.0..10.0)
	UNITS "bar"
	MAX-ACCESS read-only
	STATUS current
	DESCRIPTION "CISNIENIE-CZUJNIK-3"
	::= { snmpVariables 3 }

-- 1.3.6.1.4.1.9839.1.2.4.0
p4-CISNIENIE OBJECT-TYPE
	SYNTAX Integer32 (0.0..10.0)
	UNITS "bar"
	MAX-ACCESS read-only
	STATUS current
	DESCRIPTION "CISNIENIE-CZUJNIK-4"
	::= { snmpVariables 4 }

-- 1.3.6.1.4.1.9839.1.2.5.0
p1-AWARIA-BOOL-Active OBJECT-TYPE
	SYNTAX BITS
	UNITS "No Units"
	MAX-ACCESS read-only
	STATUS current
	DESCRIPTION "AWARIA-CZUJNIKA-P1"
	::= { snmpVariables 5 }

-- 1.3.6.1.4.1.9839.1.2.6.0
p2-AWARIA-BOOL-Active OBJECT-TYPE
	SYNTAX BITS
	UNITS "No Units"
	MAX-ACCESS read-only
	STATUS current
	DESCRIPTION "AWARIA-CZUJNIKA-P2"
	::= { snmpVariables 6 }

-- 1.3.6.1.4.1.9839.1.2.7.0
p3-AWARIA-BOOL-Active OBJECT-TYPE
	SYNTAX BITS
	UNITS "No Units"
	MAX-ACCESS read-only
	STATUS current
	DESCRIPTION "AWARIA-CZUJNIKA-P3"
	::= { snmpVariables 7 }

-- 1.3.6.1.4.1.9839.1.2.8.0
p4-AWARIA-BOOL-Active OBJECT-TYPE
	SYNTAX BITS
	UNITS "No Units"
	MAX-ACCESS read-only
	STATUS current
	DESCRIPTION "AWARIA-CZUJNIKA-P4"
	::= { snmpVariables 8 }

-- 1.3.6.1.4.1.9839.1.2.9.0
p1-awaria OBJECT-TYPE
	SYNTAX Integer32 (-32768..32767)
	UNITS "No Units"
	MAX-ACCESS read-only
	STATUS current
	DESCRIPTION "KOD-AWARII-CZUJNIKA-CISNIENIA-P1"
	::= { snmpVariables 9 }

-- 1.3.6.1.4.1.9839.1.2.10.0
p2-awaria OBJECT-TYPE
	SYNTAX Integer32 (-32768..32767)
	UNITS "No Units"
	MAX-ACCESS read-only
	STATUS current
	DESCRIPTION "KOD-AWARII-CZUJNIKA-CISNIENIA-P2"
	::= { snmpVariables 10 }

-- 1.3.6.1.4.1.9839.1.2.11.0
p3-awaria OBJECT-TYPE
	SYNTAX Integer32 (-32768..32767)
	UNITS "No Units"
	MAX-ACCESS read-only
	STATUS current
	DESCRIPTION "KOD-AWARII-CZUJNIKA-CISNIENIA-P3"
	::= { snmpVariables 11 }

-- 1.3.6.1.4.1.9839.1.2.12.0
p4-awaria OBJECT-TYPE
	SYNTAX Integer32 (-32768..32767)
	UNITS "No Units"
	MAX-ACCESS read-only
	STATUS current
	DESCRIPTION "KOD-AWARII-CZUJNIKA-CISNIENIA-P4"
	::= { snmpVariables 12 }



-- 1.3.6.1.4.1.9839.1000
snmpTraps OBJECT IDENTIFIER ::= { snmp 1000 }



END

--
-- snmp.MIB
--
