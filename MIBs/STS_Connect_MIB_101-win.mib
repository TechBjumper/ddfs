-- SOCOMEC UPS MIB
-- STS MIB 
--
-- { iso org(3) dod(6) internet(1) private(4) enterprises(1) socomecSicon(4555)
-- software(1) network(10) sts(1) }
-- ==============================================================================================

-- build on 5.01-5 from UPS MIB
-- vers. 1.00 creation

SOCOMECUPSSTS-MIB DEFINITIONS ::= BEGIN

IMPORTS
  DisplayString, TimeStamp, TimeInterval, TestAndIncr,
  AutonomousType
    FROM SNMPv2-TC
  enterprises
    FROM RFC1155-SMI
  OBJECT-TYPE
    FROM RFC-1212
  DisplayString
    FROM RFC1213-MIB
  TRAP-TYPE
    FROM RFC-1215;

PositiveInteger ::= INTEGER (1..2147483647)
NonNegativeInteger ::= INTEGER (1..2147483647)



socomecUPS      OBJECT IDENTIFIER ::= { enterprises 4555 }
software        OBJECT IDENTIFIER ::= { socomecUPS 1 }
network         OBJECT IDENTIFIER ::= { software 1 }
connectsts      OBJECT IDENTIFIER ::= { network 10 }
stsObjects      OBJECT IDENTIFIER ::= { connectsts 1 }
stsTraps        OBJECT IDENTIFIER ::= { connectsts 2 }


stsIdent        OBJECT IDENTIFIER ::= { stsObjects 1 }
stsSource1      OBJECT IDENTIFIER ::= { stsObjects 2 }      
stsSource2      OBJECT IDENTIFIER ::= { stsObjects 3 }      
stsSources      OBJECT IDENTIFIER ::= { stsObjects 4 }      
stsOutput       OBJECT IDENTIFIER ::= { stsObjects 5 }
stsAlarm        OBJECT IDENTIFIER ::= { stsObjects 6 }
stsAgent	OBJECT IDENTIFIER ::= { stsObjects 7 }

-- ===========================================================================
--
-- stsIdentification
--
--     All objects in this group except for STS IdentName and
--     stsIdentAttachedDevices are set at device initialization
--     and remain static.
--
-- ===========================================================================

stsIdentModel OBJECT-TYPE
      SYNTAX DisplayString (SIZE (0..63))
      ACCESS read-only
      STATUS mandatory
      DESCRIPTION
          "The STS Model designation."
      ::= { stsIdent 1 }

stsIdentSerialNumber OBJECT-TYPE
      SYNTAX DisplayString (SIZE(0..15))
      ACCESS read-only
      STATUS mandatory
      DESCRIPTION
          "The STS serial number"
      ::= { stsIdent 2 }

stsIdentFirmwareVersion OBJECT-TYPE
       SYNTAX DisplayString (SIZE (0..63))
       ACCESS read-only
       STATUS mandatory
       DESCRIPTION
           "The STS firmware version."
      ::= { stsIdent 3 }

stsIdentAgentSoftwareVersion OBJECT-TYPE
      SYNTAX DisplayString (SIZE(0..31))
      ACCESS read-only
      STATUS mandatory
      DESCRIPTION
          "Connect ME software version."
      ::= { stsIdent 4 }


-- ===========================================================================
--
-- sts Source 1 status
--
-- ===========================================================================

stsSource1Status OBJECT-TYPE
     SYNTAX INTEGER {
           unknown(1),
           source1OK(2),
           source1Critical(3),
           source1OutTol(4),
           source1Absent(5)
     }
     ACCESS read-only
     STATUS mandatory
     DESCRIPTION
         "Source 1 status"
     ::= { stsSource1 1 }

stsSource1Prefered OBJECT-TYPE
     SYNTAX INTEGER {
           no(1),
           yes(2)
	 }
     ACCESS read-only
     STATUS mandatory
     DESCRIPTION
         "Source 1 is prefered source"
     ::= { stsSource1 2 }

stsSource1Frequency OBJECT-TYPE
     SYNTAX INTEGER
     ACCESS read-only
     STATUS mandatory
     DESCRIPTION
         "Source1 input frequency in 0.1 HZ."
     ::= { stsSource1 3 }


stsSource1NumLines OBJECT-TYPE
     SYNTAX INTEGER
     ACCESS read-only
     STATUS mandatory
     DESCRIPTION
         "The number of phases"
     ::= { stsSource1 4 }


stsSource1Table OBJECT-TYPE
    SYNTAX SEQUENCE OF StsSource1Entry
    ACCESS not-accessible
    STATUS mandatory
    DESCRIPTION
        "A list of input table entries"
    ::= { stsSource1  5 }


stsSource1Entry OBJECT-TYPE
    SYNTAX StsSource1Entry
    ACCESS not-accessible
    STATUS mandatory
    DESCRIPTION
        "Array of measurements"
    INDEX { stsSource1LineIndex }
    ::= { stsSource1Table  1 }

StsSource1Entry ::= SEQUENCE {
             stsSource1LineIndex INTEGER,
             stsSource1Voltage INTEGER
             }

stsSource1LineIndex OBJECT-TYPE
     SYNTAX INTEGER (0..65535)
     ACCESS read-only
     STATUS mandatory
     DESCRIPTION
         "Source 1 phase number."
     ::= { stsSource1Entry 1 }

stsSource1Voltage OBJECT-TYPE
     SYNTAX INTEGER
     ACCESS read-only
     STATUS mandatory
     DESCRIPTION
         "Source 1 input voltage (V) or (U) in volts. in volts."
     ::= { stsSource1Entry 2 }

-- ===========================================================================
--
-- sts Source 2 status
--
-- ===========================================================================

stsSource2Status OBJECT-TYPE
     SYNTAX INTEGER {
           unknown(1),
           source2OK(2),
           source2Critical(3),
           source2OutTol(4),
           source2Absent(5)
     }
     ACCESS read-only
     STATUS mandatory
     DESCRIPTION
         "Source 2 status"
     ::= { stsSource2 1 }

stsSource2Prefered OBJECT-TYPE
     SYNTAX INTEGER {
           no(1),
           yes(2)
	 }
     ACCESS read-only
     STATUS mandatory
     DESCRIPTION
         "Source 2 is prefered source"
     ::= { stsSource2 2 }

stsSource2Frequency OBJECT-TYPE
     SYNTAX INTEGER
     ACCESS read-only
     STATUS mandatory
     DESCRIPTION
         "Source 2 input frequency in 0.1 HZ."
     ::= { stsSource2 3 }


stsSource2NumLines OBJECT-TYPE
     SYNTAX INTEGER
     ACCESS read-only
     STATUS mandatory
     DESCRIPTION
         "Number of phases"
     ::= { stsSource2 4 }


stsSource2Table OBJECT-TYPE
    SYNTAX SEQUENCE OF StsSource2Entry
    ACCESS not-accessible
    STATUS mandatory
    DESCRIPTION
        "A list of input table entries"
    ::= { stsSource2  5 }

stsSource2Entry OBJECT-TYPE
    SYNTAX StsSource2Entry
    ACCESS not-accessible
    STATUS mandatory
    DESCRIPTION
        "Array of measurements"
    INDEX { stsSource2LineIndex }
    ::= { stsSource2Table  1 }

StsSource2Entry ::= SEQUENCE {
             stsSource2LineIndex INTEGER,
             stsSource2Voltage INTEGER
             }

stsSource2LineIndex OBJECT-TYPE
     SYNTAX INTEGER (0..65535)
     ACCESS read-only
     STATUS mandatory
     DESCRIPTION
         "Source 2 phase number"
     ::= { stsSource2Entry 1 }

stsSource2Voltage OBJECT-TYPE
     SYNTAX INTEGER
     ACCESS read-only
     STATUS mandatory
     DESCRIPTION
         "Source 2 input voltage (V) or (U) in volts."
     ::= { stsSource2Entry 2 }

-- ===========================================================================
--
-- stsSources
--
-- ===========================================================================
stsSourcesInteraction OBJECT-TYPE
     SYNTAX INTEGER {
           unknown(1),
           synchron(2),
           sliding(3),
           asychron(4)
     }
     ACCESS read-only
     STATUS mandatory
     DESCRIPTION
         "Sources synchronisation status"
     ::= { stsSources 1 }

-- ===========================================================================
--
-- stsOutput 
--
-- ===========================================================================

stsOutputLoadStatus OBJECT-TYPE
     SYNTAX INTEGER {
           unknown(1),
           outputLoadOnPreferredSource(2),
           outputLoadOnAlternateSource(3),
           outputLoadOFF(4),
           outputLoadOnMBP1(5),
           outputLoadOnMBP2(6)
     }
     ACCESS read-only
     STATUS mandatory
     DESCRIPTION
         "Output load status"
     ::= { stsOutput 1 }

stsOutputStatus OBJECT-TYPE
     SYNTAX INTEGER {
           unknown(1),
           outputOnSwitch1(2),
           outputOnSwitch2(3),
           outputOFF(4)
     }
     ACCESS read-only
     STATUS mandatory
     DESCRIPTION
         "Static switches status"
     ::= { stsOutput 2 }


stsOutputFrequency OBJECT-TYPE
     SYNTAX INTEGER
     ACCESS read-only
     STATUS mandatory
     DESCRIPTION
         "Output frequency in 0.1 HZ."
     ::= { stsOutput 3 }

stsOutputLoadRate OBJECT-TYPE
     SYNTAX INTEGER
     ACCESS read-only
     STATUS mandatory
     DESCRIPTION
         "Output Load Rate in %."
     ::= { stsOutput 4 }

stsOutputNumLines OBJECT-TYPE
     SYNTAX INTEGER
     ACCESS read-only
     STATUS mandatory
     DESCRIPTION
         "Number of phases"
     ::= { stsOutput 5 }

stsOutputTable OBJECT-TYPE
    SYNTAX SEQUENCE OF StsOutputEntry
    ACCESS not-accessible
    STATUS mandatory
    DESCRIPTION
        "A list of input table entries.  The number of entries"
    ::= { stsOutput  6 }

stsOutputEntry OBJECT-TYPE
    SYNTAX StsOutputEntry
    ACCESS not-accessible
    STATUS mandatory
    DESCRIPTION
        "Array of measurements"
    INDEX { stsOutputLineIndex }
    ::= { stsOutputTable  1 }

StsOutputEntry ::= SEQUENCE {
             stsOutputLineIndex INTEGER,
             stsOutputVoltage INTEGER,
             stsOutputCurrent INTEGER,
             stsOutputkVA INTEGER,
			 stsOutputkW INTEGER,
             stsOutputCrestFactor INTEGER,
             stsOutputPowerFactor INTEGER
             }

stsOutputLineIndex OBJECT-TYPE
     SYNTAX INTEGER (0..65535)
     ACCESS read-only
     STATUS mandatory
     DESCRIPTION
         "Output phase number."
     ::= { stsOutputEntry 1 }

stsOutputVoltage OBJECT-TYPE
     SYNTAX INTEGER
     ACCESS read-only
     STATUS mandatory
     DESCRIPTION
         "Output voltage (V) or (U) in volts."
     ::= { stsOutputEntry 2 }

stsOutputCurrent OBJECT-TYPE
     SYNTAX INTEGER
     ACCESS read-only
     STATUS mandatory
     DESCRIPTION
         "Output current in Amps."
     ::= { stsOutputEntry 3 }

stsOutputkVA OBJECT-TYPE
     SYNTAX INTEGER
     ACCESS read-only
     STATUS mandatory
     DESCRIPTION
         "Output active power in kVA."
     ::= { stsOutputEntry 4 }

stsOutputkW OBJECT-TYPE
     SYNTAX INTEGER
     ACCESS read-only
     STATUS mandatory
     DESCRIPTION
         "Output power in kW."
     ::= { stsOutputEntry 5 }

stsOutputCrestFactor OBJECT-TYPE
     SYNTAX INTEGER
     ACCESS read-only
     STATUS mandatory
     DESCRIPTION
         "Output CrestFactor *10"
     ::= { stsOutputEntry 6 }

stsOutputPowerFactor OBJECT-TYPE
     SYNTAX INTEGER
     ACCESS read-only
     STATUS mandatory
     DESCRIPTION
         "Output PowerFactor *100"
     ::= { stsOutputEntry 7 }

-- ===========================================================================
--
-- STS ALARMS
--
-- ===========================================================================

stsWellKnownAlarms OBJECT IDENTIFIER ::= { stsAlarm  1 }

stsImminentStop OBJECT-TYPE
     SYNTAX INTEGER
     ACCESS read-only
     STATUS mandatory
     DESCRIPTION
         "Imminent Stop"
     ::= { stsWellKnownAlarms 1 }

stsTransferImpossible OBJECT-TYPE
     SYNTAX INTEGER
     ACCESS read-only
     STATUS mandatory
     DESCRIPTION
         "Transfer Impossible"
     ::= { stsWellKnownAlarms 2 }


stsConsecutiveDetection OBJECT-TYPE
     SYNTAX INTEGER
     ACCESS read-only
     STATUS mandatory
     DESCRIPTION
         "Transfer locked after several consecutive detections"
     ::= { stsWellKnownAlarms 3 }

stsOverload OBJECT-TYPE
     SYNTAX INTEGER
     ACCESS read-only
     STATUS mandatory
     DESCRIPTION
         "STS in overload"
     ::= { stsWellKnownAlarms 4 }

stsString1Alarm OBJECT-TYPE
     SYNTAX INTEGER
     ACCESS read-only
     STATUS mandatory
     DESCRIPTION
         "String 1 failure or degraded or short circuit"
     ::= { stsWellKnownAlarms 5 }

stsString2Alarm OBJECT-TYPE
     SYNTAX INTEGER
     ACCESS read-only
     STATUS mandatory
     DESCRIPTION
         "String 2 failure or degraded or short circuit"
     ::= { stsWellKnownAlarms 6 }

stsPreventiveMaintenance OBJECT-TYPE
     SYNTAX INTEGER
     ACCESS read-only
     STATUS mandatory
     DESCRIPTION
         "Preventive Maintenance"
     ::= { stsWellKnownAlarms 7 }

stsGeneralAlarm OBJECT-TYPE
     SYNTAX INTEGER
     ACCESS read-only
     STATUS mandatory
     DESCRIPTION
         "STS general alarm"
     ::= { stsWellKnownAlarms 8 }

stsCustomInputAlarm OBJECT-TYPE
     SYNTAX INTEGER
     ACCESS read-only
     STATUS mandatory
     DESCRIPTION
         "Custom Input Alarm"
     ::= { stsWellKnownAlarms 9 }

-- ===========================================================================
-- stsAgent
--
-- Agent
-- ===========================================================================	 
	 
stsAgentTrapString OBJECT-TYPE
        SYNTAX DisplayString
        ACCESS read-only
        STATUS mandatory
        DESCRIPTION
                "This OID allows traps to be sent with an octet string argument"
        ::= { stsAgent 1 }

-- ===========================================================================
-- stsTraps
--
-- Traps group
-- ===========================================================================

   -- This section defines the well-known notifications sent by
   -- STS agents.
   -- Care must be taken to insure that no particular notification
   -- is sent to a single receiving entity more often than once
   -- every five seconds.

   stsTrapImminentStop TRAP-TYPE
       ENTERPRISE stsTraps
       VARIABLES { stsAgentTrapString }
       DESCRIPTION
               "STS Imminent Stop"
     ::= 1

   stsTrapOverload	TRAP-TYPE
       ENTERPRISE stsTraps
       VARIABLES { stsAgentTrapString }
       DESCRIPTION
               "STS in Overload"
     ::= 2

   stsTrapSwitchOnPreferedSource	TRAP-TYPE
       ENTERPRISE stsTraps
       VARIABLES { stsAgentTrapString }
       DESCRIPTION
               "The load is supplied by the prefered source"
     ::= 3

   stsTrapSwitchOnAlternateSource	TRAP-TYPE
       ENTERPRISE stsTraps
       VARIABLES { stsAgentTrapString }
       DESCRIPTION
               "The load is supplied by the alternate source"
     ::= 4

   stsTrapSource1PreferredSource	TRAP-TYPE
       ENTERPRISE stsTraps
       VARIABLES { stsAgentTrapString }
       DESCRIPTION
               "The source 1 is the preferred source"
     ::= 5

   stsTrapOutputLoadOFF	TRAP-TYPE
       ENTERPRISE stsTraps
       VARIABLES { stsAgentTrapString }
       DESCRIPTION
               "Load not supplied"
     ::= 6
	 
   stsTrapGeneralAlarm	TRAP-TYPE
       ENTERPRISE stsTraps
       VARIABLES { stsAgentTrapString }
       DESCRIPTION
               "STS general alarm"
     ::= 7	 

   stsTrapAlarmCancelled	TRAP-TYPE
       ENTERPRISE stsTraps
       VARIABLES { stsAgentTrapString }
       DESCRIPTION
               "Alarm cancelled. STS in normal situation"
     ::= 8	 

END
