------------------------------------------------------------
-- EMERSON NETWORK POWER
-- SIC MIB
------------------------------------------------------------

ENP-HipulseU-MIB DEFINITIONS ::= BEGIN

IMPORTS
	MODULE-IDENTITY, OBJECT-TYPE, NOTIFICATION-TYPE,
	Integer32, Counter32, enterprises
		FROM SNMPv2-SMI
	TEXTUAL-CONVENTION, DisplayString, DateAndTime
		FROM SNMPv2-TC;
		
		
------------------------------------------------------------
-- Node definitions
------------------------------------------------------------

enp OBJECT IDENTIFIER ::= { enterprises 13400 }

products OBJECT IDENTIFIER ::= { enp 2 }

hipulseuMIB MODULE-IDENTITY
	LAST-UPDATED "200902011512Z"
	ORGANIZATION "
		EMERSON NETWORK POWER (ENP)"
	CONTACT-INFO "
		EMERSON NETWORK POWER"
	DESCRIPTION "
		EMERSON NETWORK POWER (ENP) SIC MIB."
	::= { products 14 }


------------------------------------------------------------
-- Textual conventions
------------------------------------------------------------

Status ::= TEXTUAL-CONVENTION
	STATUS current
	DESCRIPTION "
		The severity of the alarm. One of
		(0) informational
		(1) warning
		(2) critical"
	SYNTAX INTEGER {
		informational(0),
		warning(1),
		critical(2) }
		
StatusChange ::= TEXTUAL-CONVENTION
	STATUS current
	DESCRIPTION "
		Indicates 'activated' (0) or 'deactivated' (1) alarm events."
	SYNTAX INTEGER {
		activated(0),
		deactivated(1) }


------------------------------------------------------------
-- 1.1 Identification of the plant { hipulseuMIB 1 }
------------------------------------------------------------

ident OBJECT IDENTIFIER ::= { hipulseuMIB 1 }

identManufacturer OBJECT-TYPE
	SYNTAX DisplayString
	MAX-ACCESS read-only
	STATUS current
	DESCRIPTION "
		The name of the device manufacturer."
	::= { ident 1 }

identModel OBJECT-TYPE
	SYNTAX DisplayString
	MAX-ACCESS read-only
	STATUS current
	DESCRIPTION "
		The manufacturers model designation of the device."
	::= { ident 2 }

identIndex OBJECT-TYPE
	SYNTAX Integer32
	MAX-ACCESS read-write
	STATUS current
	DESCRIPTION "
		The sequence number of the device."
	::= { ident 3 }
	

------------------------------------------------------------
-- 1.2 system values { hipulseuMIB 2 }
------------------------------------------------------------

system OBJECT IDENTIFIER ::= { hipulseuMIB 2 }


-- ------------------------------------------------------------------------ 
-- 1.2.1 the status group
-- ------------------------------------------------------------------------ 

status OBJECT IDENTIFIER ::= { system 1 }

	systemStatus OBJECT-TYPE
		SYNTAX Status
		MAX-ACCESS read-only
		STATUS current
		DESCRIPTION "
			Status of the complete plant (highest alarm). One of
			(0) normal
			(1) warning
			(2) critical"
		::= { status 1 }
		
	roomTemperature OBJECT-TYPE
	    SYNTAX Integer32
	    MAX-ACCESS read-only
	    STATUS current
	    DESCRIPTION
	        "Room temperature, stored as 0.01 Celsius degree."
	    ::= { status 2 }


-- ------------------------------------------------------------------------ 
-- 1.2.2 the input group
-- ------------------------------------------------------------------------ 

input OBJECT IDENTIFIER ::= { system 2 }

    inputLineVoltageA OBJECT-TYPE
        SYNTAX Integer32
        MAX-ACCESS read-only
        STATUS current
        DESCRIPTION
            "Input line voltage A, stored as 0.01 V."
        ::= { input 1 }

    inputLineVoltageB OBJECT-TYPE
        SYNTAX Integer32
        MAX-ACCESS read-only
        STATUS current
        DESCRIPTION
            "Input line voltage B, stored as 0.01 V."
        ::= { input 2 }

    inputLineVoltageC OBJECT-TYPE
        SYNTAX Integer32
        MAX-ACCESS read-only
        STATUS current
        DESCRIPTION
            "Input line voltage C, stored as 0.01 V."
        ::= { input 3 }
        
	inputCurrentA OBJECT-TYPE
        SYNTAX Integer32
        MAX-ACCESS read-only
        STATUS current
        DESCRIPTION
            "Input current A, stored as 0.01 A."
        ::= { input 4 }
        
	inputCurrentB OBJECT-TYPE
		SYNTAX Integer32
        MAX-ACCESS read-only
        STATUS current
        DESCRIPTION
            "Input current B, stored as 0.01 A."
        ::= { input 5 }
        
	inputCurrentC OBJECT-TYPE
		SYNTAX Integer32
		MAX-ACCESS read-only
        STATUS current
        DESCRIPTION
            "Input current C, stored as 0.01 A."
        ::= { input 6 }
        
    inputFrequency OBJECT-TYPE
        SYNTAX Integer32
        MAX-ACCESS read-only
        STATUS current
        DESCRIPTION
            "Input frequency, stored as 0.01 Hz."
        ::= { input 7 }   
	

-- ------------------------------------------------------------------------ 
-- 1.2.3 the bypass group
-- ------------------------------------------------------------------------ 

bypass OBJECT IDENTIFIER ::= { system 3 }

    bypassPhaseVoltageA OBJECT-TYPE
        SYNTAX Integer32
        MAX-ACCESS read-only
        STATUS current
        DESCRIPTION
            "Bypass phase voltage A, stored as 0.01 V."
        ::= { bypass 1 }

    bypassPhaseVoltageB OBJECT-TYPE
        SYNTAX Integer32
        MAX-ACCESS read-only
        STATUS current
        DESCRIPTION
            "Bypass phase voltage B, stored as 0.01 V."
        ::= { bypass 2 }

    bypassPhaseVoltageC OBJECT-TYPE
        SYNTAX Integer32
        MAX-ACCESS read-only
        STATUS current
        DESCRIPTION
            "Bypass phase voltage C, stored as 0.01 V."
        ::= { bypass 3 }
        
    bypassFrequency OBJECT-TYPE
        SYNTAX Integer32
        MAX-ACCESS read-only
        STATUS current
        DESCRIPTION
            "Bypass frequency, stored as 0.01 Hz."
        ::= { bypass 4 }


-- ------------------------------------------------------------------------ 
-- 1.2.4 the output group
-- ------------------------------------------------------------------------ 

output OBJECT IDENTIFIER ::= { system 4 }

    outputPhaseVoltageA OBJECT-TYPE
        SYNTAX Integer32
        MAX-ACCESS read-only
        STATUS current
        DESCRIPTION
            "Output phase voltage A, stored as 0.01 V."
        ::= { output 1 }

    outputPhaseVoltageB OBJECT-TYPE
        SYNTAX Integer32
        MAX-ACCESS read-only
        STATUS current
        DESCRIPTION
            "Output phase voltage B, stored as 0.01 V."
        ::= { output 2 }

    outputPhaseVoltageC OBJECT-TYPE
        SYNTAX Integer32
        MAX-ACCESS read-only
        STATUS current
        DESCRIPTION
            "Output phase voltage C, stored as 0.01 V."
        ::= { output 3 }
        
	outputCurrentA OBJECT-TYPE
        SYNTAX Integer32
        MAX-ACCESS read-only
        STATUS current
        DESCRIPTION
            "Output current A, stored as 0.01 A."
        ::= { output 4 }
        
	outputCurrentB OBJECT-TYPE
		SYNTAX Integer32
        MAX-ACCESS read-only
        STATUS current
        DESCRIPTION
            "Output current B, stored as 0.01 A."
        ::= { output 5 }
        
	outputCurrentC OBJECT-TYPE
		SYNTAX Integer32
		MAX-ACCESS read-only
        STATUS current
        DESCRIPTION
            "Output current C, stored as 0.01 A."
        ::= { output 6 }
        
    outputFrequency OBJECT-TYPE
        SYNTAX Integer32
        MAX-ACCESS read-only
        STATUS current
        DESCRIPTION
            "Output frequency, stored as 0.01 Hz."
        ::= { output 7 }
        
	outputPowerFactorA OBJECT-TYPE
        SYNTAX Integer32
        MAX-ACCESS read-only
        STATUS current
        DESCRIPTION
            "Output power factor A, stored as 0.01."
        ::= { output 8 }
        
	outputPowerFactorB OBJECT-TYPE
        SYNTAX Integer32
        MAX-ACCESS read-only
        STATUS current
        DESCRIPTION
            "Output power factor B, stored as 0.01."
        ::= { output 9 }
        
	outputPowerFactorC OBJECT-TYPE
        SYNTAX Integer32
        MAX-ACCESS read-only
        STATUS current
        DESCRIPTION
            "Output power factor C, stored as 0.01."
        ::= { output 10 }
        
	outputActivePowerA OBJECT-TYPE
        SYNTAX Integer32
        MAX-ACCESS read-only
        STATUS current
        DESCRIPTION
            "Output active power A, stored as 0.01 kW."
        ::= { output 11 }
        
	outputActivePowerB OBJECT-TYPE
        SYNTAX Integer32
        MAX-ACCESS read-only
        STATUS current
        DESCRIPTION
            "Output active power B, stored as 0.01 kW."
        ::= { output 12 }
        
	outputActivePowerC OBJECT-TYPE
        SYNTAX Integer32
        MAX-ACCESS read-only
        STATUS current
        DESCRIPTION
            "Output active power C, stored as 0.01 kW."
        ::= { output 13 }
        
	outputApparentPowerA OBJECT-TYPE
		SYNTAX Integer32
        MAX-ACCESS read-only
        STATUS current
        DESCRIPTION
            "Output apparent power A, stored as 0.01 kVA."
        ::= { output 14 }
        
	outputApparentPowerB OBJECT-TYPE
		SYNTAX Integer32
        MAX-ACCESS read-only
        STATUS current
        DESCRIPTION
            "Output apparent power B, stored as 0.01 kVA."
        ::= { output 15 }
        
	outputApparentPowerC OBJECT-TYPE
		SYNTAX Integer32
        MAX-ACCESS read-only
        STATUS current
        DESCRIPTION
            "Output apparent power C, stored as 0.01 kVA."
        ::= { output 16 }

	outputReactivePowerA OBJECT-TYPE
		SYNTAX Integer32
        MAX-ACCESS read-only
        STATUS current
        DESCRIPTION
            "Output load A, stored as 0.01 KVAR."
        ::= { output 17 }
        
	outputReactivePowerB OBJECT-TYPE
		SYNTAX Integer32
        MAX-ACCESS read-only
        STATUS current
        DESCRIPTION
            "Output load B, stored as 0.01 KVAR."
        ::= { output 18 }
        
	outputReactivePowerC OBJECT-TYPE
		SYNTAX Integer32
        MAX-ACCESS read-only
        STATUS current
        DESCRIPTION
            "Output load C, stored as 0.01 KVAR."
        ::= { output 19 }
                
	outputLoadA OBJECT-TYPE
		SYNTAX Integer32
        MAX-ACCESS read-only
        STATUS current
        DESCRIPTION
            "Output load A, stored as 0.01 %."
        ::= { output 20 }
        
	outputLoadB OBJECT-TYPE
		SYNTAX Integer32
        MAX-ACCESS read-only
        STATUS current
        DESCRIPTION
            "Output load B, stored as 0.01 %."
        ::= { output 21 }
        
	outputLoadC OBJECT-TYPE
		SYNTAX Integer32
        MAX-ACCESS read-only
        STATUS current
        DESCRIPTION
            "Output load C, stored as 0.01 %."
        ::= { output 22 }
        
	outputCrestFactorA OBJECT-TYPE
		SYNTAX Integer32
        MAX-ACCESS read-only
        STATUS current
        DESCRIPTION
            "Output crest factor A, stored as 0.01."
        ::= { output 23 }
        
	outputCrestFactorB OBJECT-TYPE
		SYNTAX Integer32
        MAX-ACCESS read-only
        STATUS current
        DESCRIPTION
            "Output crest factor B, stored as 0.01."
        ::= { output 24 }
        
	outputCrestFactorC OBJECT-TYPE
		SYNTAX Integer32
        MAX-ACCESS read-only
        STATUS current
        DESCRIPTION
            "Output crest factor C, stored as 0.01."
        ::= { output 25 }
	

-- ------------------------------------------------------------------------ 
-- 1.2.5 the battery group
-- ------------------------------------------------------------------------ 

battery OBJECT IDENTIFIER ::= { system 5 }

    batteryVoltage OBJECT-TYPE
        SYNTAX Integer32
        MAX-ACCESS read-only
        STATUS current
        DESCRIPTION
            "Battery voltage, stored as 0.01 V."
        ::= { battery 1 }
        
	batteryCurrent OBJECT-TYPE
        SYNTAX Integer32
        MAX-ACCESS read-only
        STATUS current
        DESCRIPTION
            "Battery current, stored as 0.01 A."
        ::= { battery 2 } 
        
	batteryRemainsTime OBJECT-TYPE
        SYNTAX Integer32
        MAX-ACCESS read-only
        STATUS current
        DESCRIPTION
            "Battery remains time, stored as 0.01 minutes."
        ::= { battery 3 }
		
	batteryTemperature OBJECT-TYPE
	    SYNTAX Integer32
	    MAX-ACCESS read-only
	    STATUS current
	    DESCRIPTION
	        "Battery temperature, stored as 0.01 Celsius degree."
        ::= { battery 4 }


-- ------------------------------------------------------------------------ 
-- 1.2.6 the parallel group
-- ------------------------------------------------------------------------ 

parallel OBJECT IDENTIFIER ::= { system 6 }

	parallelCapability OBJECT-TYPE
        SYNTAX Integer32
        MAX-ACCESS read-only
        STATUS current
        DESCRIPTION
            "Parallel set number, stored as 0.01."
        ::= { parallel 1 }

	parallelID OBJECT-TYPE
        SYNTAX Integer32
        MAX-ACCESS read-only
        STATUS current
        DESCRIPTION
            "Parallel id, stored as 1."
        ::= { parallel 2 }
	
	parallelActivePowerA OBJECT-TYPE
		SYNTAX Integer32
        MAX-ACCESS read-only
        STATUS current
        DESCRIPTION
            "Parallel active power A, stored as 0.01 kW."
        ::= { parallel 3 }
        
	parallelActivePowerB OBJECT-TYPE
        SYNTAX Integer32
        MAX-ACCESS read-only
        STATUS current
        DESCRIPTION
            "Parallel active power B, stored as 0.01 kW."
        ::= { parallel 4 }
        
	parallelActivePowerC OBJECT-TYPE
        SYNTAX Integer32
        MAX-ACCESS read-only
        STATUS current
        DESCRIPTION
            "Parallel active power C, stored as 0.01 kW."
        ::= { parallel 5 }
        
	parallelApparentPowerA OBJECT-TYPE
		SYNTAX Integer32
        MAX-ACCESS read-only
        STATUS current
        DESCRIPTION
            "Parallel apparent power A, stored as 0.01 kVA."
        ::= { parallel 6 }
        
	parallelApparentPowerB OBJECT-TYPE
		SYNTAX Integer32
        MAX-ACCESS read-only
        STATUS current
        DESCRIPTION
            "Parallel apparent power B, stored as 0.01 kVA."
        ::= { parallel 7 }
        
	parallelApparentPowerC OBJECT-TYPE
		SYNTAX Integer32
        MAX-ACCESS read-only
        STATUS current
        DESCRIPTION
            "Parallel apparent power C, stored as 0.01 kVA."
        ::= { parallel 8 }

	parallelReactivePowerA OBJECT-TYPE
		SYNTAX Integer32
        MAX-ACCESS read-only
        STATUS current
        DESCRIPTION
            "Parallel apparent power A, stored as 0.01 KVAR."
        ::= { parallel 9 }
        
	parallelReactivePowerB OBJECT-TYPE
		SYNTAX Integer32
        MAX-ACCESS read-only
        STATUS current
        DESCRIPTION
            "Parallel apparent power B, stored as 0.01 KVAR."
        ::= { parallel 10 }
        
	parallelReactivePowerC OBJECT-TYPE
		SYNTAX Integer32
        MAX-ACCESS read-only
        STATUS current
        DESCRIPTION
            "Parallel apparent power C, stored as 0.01 KVAR."
        ::= { parallel 11 }


------------------------------------------------------------
-- 1.3 Alarm trap table { hipulseuMIB 3 }
------------------------------------------------------------

alarmTrapTable OBJECT-TYPE
	SYNTAX SEQUENCE OF AlarmTrapEntry
	MAX-ACCESS not-accessible
	STATUS current
	DESCRIPTION "
		Table holding information about the submitted alarm traps."
	::= { hipulseuMIB 3 }

alarmTrapEntry OBJECT-TYPE
	SYNTAX AlarmTrapEntry
	MAX-ACCESS not-accessible
	STATUS current
	DESCRIPTION "
		An entry (conceptual row) in the alarmTrapTable."
	INDEX { alarmIndex }
	::= { alarmTrapTable 1 }

AlarmTrapEntry ::= SEQUENCE {
	alarmIndex Counter32,
	alarmTime DisplayString,
	alarmStatusChange StatusChange,
	alarmSeverity Status,
	alarmDescription DisplayString,
	alarmId Integer32 }

alarmIndex OBJECT-TYPE
	SYNTAX Counter32
	MAX-ACCESS read-only
	STATUS current
	DESCRIPTION "
		The unique sequence number of this alarm trap."
	::= { alarmTrapEntry 1 }

alarmTime OBJECT-TYPE
	SYNTAX DisplayString
	MAX-ACCESS read-only
	STATUS current
	DESCRIPTION "
		Date and time when event occured."
	::= { alarmTrapEntry 2 }

alarmStatusChange OBJECT-TYPE
	SYNTAX StatusChange
	MAX-ACCESS read-only
	STATUS current
	DESCRIPTION "
		Indicates 'activated' (0) or 'deactivated' (1) alarm events."
	::= { alarmTrapEntry 3 }

alarmSeverity OBJECT-TYPE
	SYNTAX Status
	MAX-ACCESS read-only
	STATUS current
	DESCRIPTION "
		The severity of the alarm. One of
		(0) informational
		(1) warning
		(2) critical"
	::= { alarmTrapEntry 4 }
	
alarmDescription OBJECT-TYPE
	SYNTAX DisplayString
	MAX-ACCESS read-only
	STATUS current
	DESCRIPTION "
		Free-text description of alarm."
	::= { alarmTrapEntry 5 }
	
alarmId OBJECT-TYPE
	SYNTAX Integer32
	MAX-ACCESS read-only
	STATUS current
	DESCRIPTION "
		Alarm id."
	::= { alarmTrapEntry 6 }


------------------------------------------------------------
-- End of MIB definitions
------------------------------------------------------------

END
