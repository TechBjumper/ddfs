-- Toshiba MIB
-- UPS MIB for Toshiba 4300 Series Uninterruptible Power Supply
--
--{iso(1) org(3) dod(6) internet(1) private(4) enterprises(1) toshiba(186) 
-- equ(1) equups(19) ticups(2) rmti4 (5) ups4300(3)}
--=============================================================================

TIC-RMTI4-4300-MIB DEFINITIONS ::= BEGIN

--=============================================================================
-- Update : May 28, 2015
-- By     : Edwin Rubio, Toshiba International Corp.
-- For    : 4300 4th Draft MIB for RemotEye 4
-- Revised: Renamed upsTrapBypass to upsTrapOnBypass, and upsTrapBypassClear to upsTrapOnBypassClear
--=============================================================================
-- Update : March 19, 2015
-- By     : Edwin Rubio, Toshiba International Corp.
-- Revised: Removed upsStsCtlCfgRemoteBypassSwitch
--		  : Added upsStsCtlCfgUserDefinedOverloadSetPoint
--		  : Added upsAlarmUserDefinedOverloadWarning
--		  : Added upsTrapUserDefinedOverloadWarning
--		  : Added upsTrapUserDefinedOverloadWarning
--=============================================================================
-- Update : April 27, 2014
-- By     : Edwin Rubio, Toshiba International Corp.
-- Revised: Changed OID upsInputCurrentPhaseA to upsInputCurrent and modified description 
--		  : Changed OID upsBatteryNumStrings to upsBatteryInParallel
--=============================================================================
-- Update : April 15, 2014
-- By     : Edwin Rubio, Toshiba International Corp.
-- Revised: Removed upsOutputPowerTotalVAinPercent OID (upsOuput 23)
--		  : Renamed upsAlarmBatteryOn to upsAlarmOnBattery
--=============================================================================
-- Update : Jan 13, 2014
-- By     : Edwin Rubio, Toshiba International Corp.
-- Revised: upsInput 8: Changed OID Name from "upsInputPhaseCurrentA" to "upsInputCurrentPhaseA"
--		  : upsInput 12: Changed OID Name from "upsInputVoltagePercentA" to "upsInputLLVoltagePercentA"
--		  :	upsInput 13: Changed OID Name from "upsInputVoltagePercentB" to "upsInputLLVoltagePercentB"
--		  : upsInput 14: Changed OID Name from "upsInputVoltagePercentC" to "upsInputLLVoltagePercentC"
--		  : upsInput 18: Changed OID Name from "upsInputRatedPowerinWatt" to "upsInputRatedActivePower"
--		  : upsInput 19: Changed OID Name from "upsInputRatedPowerinVA" to "upsInputRatedApperentPower"
--        : upsInput 20: Changed OID Name from "upsInputVIUVDetectionLevel" to "upsInputUnderVoltageDetectLevel"
--	  	  : upsInput 21: Changed OID Name from "upsInputVIOVDetectionLevel" to "upsInputOverVoltageDetectLevel"
--	  	  : upsOutput 8: Changed OID Name from "upsOutputPhaseCurrentA" to "upsOutputCurrentPhaseA
--	  	  : upsOutput 9: Changed OID Name from "upsOutputPhaseCurrentB" to "upsOutputCurrentPhaseB"
--	  	  : upsOutput 10: Changed OID Name from "upsOutputPhaseCurrentC" to "upsOutputCurrentPhaseC"
--	  	  : upsOutput 14: Changed OID Name from "upsOutputPowerTotalinKilowatt" to "upsOutputTotalActivePower"
--	  	  : upsOutput 22: Changed OID Name from "upsOutputPowerTotalWattinPercent" to "upsOutputTotalActivePowerPercent"
--	  	  : upsOutput 27: Changed OID Name from "upsOutputRatedPowerinWatt" to "upsOutputRatedActivePower"
--	  	  : upsOutput 28: Changed OID Name from "upsOutputRatedPowerinVA" to "upsOutputRatedApparentPower"
--	  	  : upsOutput 29: Changed OID Name from "upsOutputVOUVDetectionLevel" to "upsOutputUnderVoltageDetectLevel"
--	  	  : upsOutput 30: Changed OID Name from "upsOutputVOOVDetectionLevel" to "upsOutputOverVoltageDetectLevel"
--	  	  : upsBypass 14: Changed OID Name from "upsBypassUVDetectionLevel" to "upsBypassUnderVoltageDetectLevel"
--	  	  : upsBypass 15: Changed OID Name from "upsBypassOVDetectionLevel" to "upsBypassOverVoltageDetectLevel"
--		  : upsBattery 8: Changed OID Name from "upsBatteryLowBattDetectionLevel" to "upsBatteryRatedLowBattLevel"
--	  	  : upsBattery 13: Changed OID Name from "upsBatteryinSeries" to "upsBatteryInSeries"
--	  	  : upsBattery 14: Changed OID Name from "upsBatteryinParallel" to "upsBatteryNumStrings"
--	  	  : upsBattery 16: Changed OID Name from "upsBatteryInstalledDate" to "upsBatteryInstallationDate"
--	  	  : upsStsCtlCfg 3: Changed OID Name from "upsStsCtlCfgCurrentState" to "upsStsCtlCfgPresentMode"
--	  	  : upsStsCtlCfg 4: Changed OID Name from "upsStsCtlCfgServicePortBaudRate" to "upsStsCtlCfgServicePortCommSetting"
--	  	  : upsStsCtlCfg 5: Changed OID Name from "upsStsCtlCfgRMTIPortBaudRate" to "upsStsCtlCfgRMTIPortCommSetting"
--	  	  : upsStsCtlCfgChangeSecurtiyLevel removed from MIB
--	  	  : upsStsCtlCfgManageADMINPWD removed from MIB
--	  	  : upsStsCtlCfg 8: Changed OID Name from "upsStsCtlCfgAutoReTransfer" to "upsStsCtlCfgAutoTransferMode"
--	  	  : upsDisplay 5: Changed OID Name from "upsDispalyRMTIInstallDate" to "upsDisplayRMTIInstallationDate"
--	  	  : upsDsiplay 7: Changed OID Name from "upsDisplayRMTIInstallStatus" to "upsDisplayRMTIInstallationStatus"
--	  	  : upsWellKnownAlarms 5/upsTrap 9 & 18: Changed OID Name from "upsAlarmDCOverVoltage" to "upsAlarmDCBusOverVoltage"
--	  	  : upsWellKnownAlarms 9/upsTrap 17 & 18: Changed OID Name from "upsAlarmHeatSinkOverheat" to "upsAlarmUPSOverheat"
--	  	  : upsWellKnownAlarms 13/upsTrap 25 & 26: Changed OID Name from "upsAlarmDCUnderVoltAtBoostUp" to "upsAlarmDCBusUnderVoltAtBoostUp"
--	  	  : upsWellKnownAlarms 14/upsTrap 27 & 28: Changed OID Name from "upsAlarmDCUnderVoltAtCharge" to "upsAlarmDCBusUnderVoltAtCharge"
--		  : upsAlarmWarning removed from MIB
--	  	  : upsWellKnownAlarms 26/upsTrap 51 & 52: Changed OID Name from "upsAlarmBatteryAtShutdownlevel" to "upsAlarmBatteryDepleted"
--	  	  : upsWellKnownAlarms 29/upsTrap 57 & 58: Changed OID Name from "upsAlarmBypass" to "upsAlarmOnBypass"
--	  	  : upsWellKnownAlarms 34/upsTrap 67 & 68: Changed OID Name from "upsAlarmOutputLoadWarning" to "upsAlarmOutputOverloadWarning"
--	  	  : upsWellKnownAlarms 41/upsTrap 81 & 82: Changed OID Name from "upsAlarmRemotEyeDownLinkCommError" to "upsAlarmRemotEyeCommError"
--	  	  : upsWellKnownAlarms 50/upsTrap 99 & 100: Changed OID Name from "upsAlarmTimedShutdown" to "upsAlarmShutdownPending"
--	  	  : upsWellKnownAlarms 55/upsTrap 109 & 110: Changed OID Name from "upsAlarmAutoReTransferEnable" to "upsAlarmAutoTransferEnable"
--	  	  : upsWellKnownAlarms 59/upsTrap 117 & 118: Changed OID Name from "upsAlarmOutputFrequency" to "upsAlarmOutputFrequency50Hz"
--	  	  : upsWellKnownAlarms 69/upsTrap 137 & 138: Changed OID Name from "upsAlarmBatteryOn" to "upsAlarmOnBattery"
--	  	  : upsWellKnownAlarms 70/upsTrap 129 & 140: upsAlarmLogInError added to MIB
--	  	  : upsPwd 2: Changed OID Name from "upsPwdAdminCurrentLogin" to "upsPwdAdminCurrentPwd"
--	  	  : upsPwd 3: Changed OID Name from "upsPwdAdminCurrentPswd" to "upsPwdAdminNewPwd"
--=============================================================================
-- Update : December 22, 2013
-- By     : Tiffany Tye, Toshiba International Corp.
-- Revised: upsBatteryRatedAmpereHour add units
--        : upsBatteryInstalledDate add units
--        : upsBatteryRatedBackupTime add object
--=============================================================================
-- Update : July 1, 2013
-- By     : Edwin Rubio, Toshiba International Corp.
--=============================================================================

IMPORTS
  DisplayString, TimeStamp, TimeInterval, TestAndIncr, AutonomousType
    FROM SNMPv2-TC
  enterprises
    FROM RFC1155-SMI
  OBJECT-TYPE
    FROM RFC-1212
  TRAP-TYPE
    FROM RFC-1215;

PositiveInteger    ::= INTEGER (0..2147483647)
NonNegativeInteger ::= INTEGER (0..2147483647)

toshiba 	OBJECT IDENTIFIER ::= { enterprises 186 }
equ		OBJECT IDENTIFIER ::= { toshiba 1 }
equUPS	OBJECT IDENTIFIER ::= { equ 19 }
ticUPS     	OBJECT IDENTIFIER ::= { equUPS 2 }
rmti4		OBJECT IDENTIFIER ::= { ticUPS 5 }
ups4300	OBJECT IDENTIFIER ::= { rmti4 3 }

upsIdent     OBJECT IDENTIFIER ::= { ups4300 1 }
upsInput     OBJECT IDENTIFIER ::= { ups4300 2 }
upsOutput    OBJECT IDENTIFIER ::= { ups4300 3 }
upsBypass    OBJECT IDENTIFIER ::= { ups4300 4 }
upsDCBus     OBJECT IDENTIFIER ::= { ups4300 5 }
upsBattery   OBJECT IDENTIFIER ::= { ups4300 6 }
upsStsCtlCfg OBJECT IDENTIFIER ::= { ups4300 7 }
upsHistory   OBJECT IDENTIFIER ::= { ups4300 8 }
upsDisplay   OBJECT IDENTIFIER ::= { ups4300 9 }
upsAlarm     OBJECT IDENTIFIER ::= { ups4300 10 }
upsPassword  OBJECT IDENTIFIER ::= { ups4300 11 }
upsTrap      OBJECT IDENTIFIER ::= { ups4300 12 }

-- ===========================================================================
-- upsIdent - Group 1
-- The UPS Identification Group
-- ===========================================================================

upsIdentManufacturer OBJECT-TYPE
    SYNTAX DisplayString (SIZE (0..16))
    ACCESS read-only
    STATUS mandatory
    DESCRIPTION
        "The name of the UPS manufacturer."
    ::= { upsIdent 1 }
	
upsIdentTypeform OBJECT-TYPE
    SYNTAX DisplayString (SIZE(0..16))
    ACCESS read-only
    STATUS mandatory
    DESCRIPTION
        "The UPS Typeform."
    ::= { upsIdent 2 }

upsIdentSerialNumber OBJECT-TYPE
    SYNTAX DisplayString (SIZE(0..16))
    ACCESS read-only
    STATUS mandatory
    DESCRIPTION
        "The UPS Serial Number."
    ::= { upsIdent 3 }

upsIdentSysName OBJECT-TYPE
    SYNTAX DisplayString (SIZE(0..16))
    ACCESS read-write
    STATUS mandatory
    DESCRIPTION
        "A string identifying the UPS. This object should be
         set by the administrator."
    ::= { upsIdent 4 }

upsIdentAttachedDevices OBJECT-TYPE
    SYNTAX DisplayString (SIZE(0..16))
    ACCESS read-write
    STATUS mandatory
    DESCRIPTION
        "A string identifying the devices attached to the
         output(s) of the UPS. This object should be set by
         the administrator."
    ::= { upsIdent 5 }

upsIdentInstallationDate OBJECT-TYPE
    SYNTAX DisplayString (SIZE(10))
    ACCESS read-write
    STATUS mandatory
    DESCRIPTION
        "The UPS installation date in MM/DD/YYYY format."
    ::= { upsIdent 6 }

-- ===========================================================================
-- upsInput - Group 2
-- The UPS Input Data Group 
-- ===========================================================================

upsInputNumOfPhases OBJECT-TYPE
    SYNTAX INTEGER
    ACCESS read-only
    STATUS mandatory
    DESCRIPTION
        "The number of input lines."
    ::= { upsInput 1 }

upsInputLLVoltageAB OBJECT-TYPE
    SYNTAX INTEGER
    UNITS  "RMS Volts"
    ACCESS read-only
    STATUS mandatory
    DESCRIPTION
        "The input line to line voltage for AB in RMS volts."
    ::= { upsInput 2 }

upsInputLLVoltageBC OBJECT-TYPE
    SYNTAX INTEGER
    UNITS  "RMS Volts"
    ACCESS read-only
    STATUS mandatory
    DESCRIPTION
        "The input line to line voltage for BC in RMS volts."
    ::= { upsInput 3 }

upsInputLLVoltageCA OBJECT-TYPE
    SYNTAX INTEGER
    UNITS  "RMS Volts"
    ACCESS read-only
    STATUS mandatory
    DESCRIPTION
        "The input line to line voltage for CA in RMS volts."
    ::= { upsInput 4 }

upsInputLNVoltageAN OBJECT-TYPE
    SYNTAX INTEGER
    UNITS  "RMS Volts"
    ACCESS read-only
    STATUS mandatory
    DESCRIPTION
        "The input line to neutral voltage for AN in RMS volts."
    ::= { upsInput 5 }

upsInputLNVoltageBN OBJECT-TYPE
    SYNTAX INTEGER
    UNITS  "RMS Volts"
    ACCESS read-only
    STATUS mandatory
    DESCRIPTION
        "The input line to neutral voltage for BN in RMS volts."
    ::= { upsInput 6 }

upsInputLNVoltageCN OBJECT-TYPE
    SYNTAX INTEGER
    UNITS  "RMS Volts"
    ACCESS read-only
    STATUS mandatory
    DESCRIPTION
        "The input line to neutral voltage for CN in RMS volts."
    ::= { upsInput 7 }

upsInputCurrent OBJECT-TYPE
    SYNTAX INTEGER
    UNITS  "Amp"
    ACCESS read-only
    STATUS mandatory
    DESCRIPTION
        "The input current in amps."
    ::= { upsInput 8 }

upsInputFrequencyA OBJECT-TYPE
    SYNTAX INTEGER
    UNITS  "0.1 Hertz"
    ACCESS read-only
    STATUS mandatory
    DESCRIPTION
        "The input frequency for phase A in Hertz."
    ::= { upsInput 9 }

upsInputFrequencyB OBJECT-TYPE
    SYNTAX INTEGER
    UNITS  "0.1 Hertz"
    ACCESS read-only
    STATUS mandatory
    DESCRIPTION
        "The input frequency for phase B in Hertz."
    ::= { upsInput 10 }

upsInputFrequencyC OBJECT-TYPE
    SYNTAX INTEGER
    UNITS  "0.1 Hertz"
    ACCESS read-only
    STATUS mandatory
    DESCRIPTION
        "The input frequency for phase C in Hertz."
    ::= { upsInput 11 }

upsInputLLVoltagePercentA OBJECT-TYPE
    SYNTAX INTEGER
    UNITS  "Percent"
    ACCESS read-only
    STATUS mandatory
    DESCRIPTION
        "The input voltage for phase A in percent."
    ::= { upsInput 12 }

upsInputLLVoltagePercentB OBJECT-TYPE
    SYNTAX INTEGER
    UNITS  "Percent"
    ACCESS read-only
    STATUS mandatory
    DESCRIPTION
        "The input voltage for phase B in percent."
    ::= { upsInput 13 }

upsInputLLVoltagePercentC OBJECT-TYPE
    SYNTAX INTEGER
    UNITS  "Percent"
    ACCESS read-only
    STATUS mandatory
    DESCRIPTION
        "The input voltage for phase C in percent."
    ::= { upsInput 14 }

upsInputRatedLLVoltage OBJECT-TYPE
    SYNTAX INTEGER
    UNITS  "Voltage"
    ACCESS read-only
    STATUS mandatory
    DESCRIPTION
        "The rated input line to line voltage."
    ::= { upsInput 15 }

upsInputRatedLNVoltage OBJECT-TYPE
    SYNTAX INTEGER
    UNITS  "Voltage"
    ACCESS read-only
    STATUS mandatory
    DESCRIPTION
        "The rated input line to neutral voltage."
    ::= { upsInput 16 }

upsInputRatedCurrent OBJECT-TYPE
    SYNTAX INTEGER
    UNITS  "Amp"
    ACCESS read-only
    STATUS mandatory
    DESCRIPTION
        "The rated input current."
    ::= { upsInput 17 }

upsInputRatedActivePower OBJECT-TYPE
    SYNTAX INTEGER
    UNITS  "watt"
    ACCESS read-only
    STATUS mandatory
    DESCRIPTION
        "The rated input power in watt."
    ::= { upsInput 18 }

upsInputRatedApperentPower OBJECT-TYPE
    SYNTAX INTEGER
    UNITS  "Volt-Amp"
    ACCESS read-only
    STATUS mandatory
    DESCRIPTION
        "The rated input power in volt-amp."
    ::= { upsInput 19 }

upsInputUnderVoltageDetectLevel OBJECT-TYPE
    SYNTAX INTEGER
    UNITS  "Percent"
    ACCESS read-only
    STATUS mandatory
    DESCRIPTION
        "The input voltage under voltage detection level."
    ::= { upsInput 20 }

upsInputOverVoltageDetectLevel OBJECT-TYPE
    SYNTAX INTEGER
    UNITS  "Percent"
    ACCESS read-only
    STATUS mandatory
    DESCRIPTION
        "The input voltage over voltage detection level."
    ::= { upsInput 21 }

upsInputPhaseChk OBJECT-TYPE
    SYNTAX INTEGER {
        disable(1),
        enable(2)
    }
    ACCESS read-only
    STATUS mandatory
    DESCRIPTION
        "Enable phase check."
    ::= { upsInput 22 }

-- ===========================================================================
-- upsOutput - Group 3
-- The UPS Output Data Group
-- ===========================================================================

upsOutputNumOfPhases OBJECT-TYPE
    SYNTAX INTEGER
    ACCESS read-only
    STATUS mandatory
    DESCRIPTION
        "The number of output line."
    ::= { upsOutput 1 }

upsOutputLLVoltageAB OBJECT-TYPE
    SYNTAX INTEGER
    UNITS  "RMS Volts"
    ACCESS read-only
    STATUS mandatory
    DESCRIPTION
        "The Output line to line voltage for AB in RMS volts."
    ::= { upsOutput 2 }

upsOutputLLVoltageBC OBJECT-TYPE
    SYNTAX INTEGER
    UNITS  "RMS Volts"
    ACCESS read-only
    STATUS mandatory
    DESCRIPTION
        "The Output line to line voltage for BC in RMS volts."
    ::= { upsOutput 3 }

upsOutputLLVoltageCA OBJECT-TYPE
    SYNTAX INTEGER
    UNITS  "RMS Volts"
    ACCESS read-only
    STATUS mandatory
    DESCRIPTION
        "The Output line to line voltage for CA in RMS volts."
    ::= { upsOutput 4 }

upsOutputLNVoltageAN OBJECT-TYPE
    SYNTAX INTEGER
    UNITS  "RMS Volts"
    ACCESS read-only
    STATUS mandatory
    DESCRIPTION
        "The Output line to neutral voltage for AN in RMS volts."
    ::= { upsOutput 5 }

upsOutputLNVoltageBN OBJECT-TYPE
    SYNTAX INTEGER
    UNITS  "RMS Volts"
    ACCESS read-only
    STATUS mandatory
    DESCRIPTION
        "The Output line to neutral voltage for BN in RMS volts."
    ::= { upsOutput 6 }

upsOutputLNVoltageCN OBJECT-TYPE
    SYNTAX INTEGER
    UNITS  "RMS Volts"
    ACCESS read-only
    STATUS mandatory
    DESCRIPTION
        "The Output line to neutral voltage for CN in RMS volts."
    ::= { upsOutput 7 }

upsOutputCurrentPhaseA OBJECT-TYPE
    SYNTAX INTEGER
    UNITS  "Amp"
    ACCESS read-only
    STATUS mandatory
    DESCRIPTION
        "The Output phase current for phase A in amps."
    ::= { upsOutput 8 }

upsOutputCurrentPhaseB OBJECT-TYPE
    SYNTAX INTEGER
    UNITS  "Amp"
    ACCESS read-only
    STATUS mandatory
    DESCRIPTION
        "The Output phase current for phase B in amps."
    ::= { upsOutput 9 }

upsOutputCurrentPhaseC OBJECT-TYPE
    SYNTAX INTEGER
    UNITS  "Amp"
    ACCESS read-only
    STATUS mandatory
    DESCRIPTION
        "The Output phase current for phase C in amps."
    ::= { upsOutput 10 }

upsOutputFrequencyA OBJECT-TYPE
    SYNTAX INTEGER
    UNITS  "0.1 Hertz"
    ACCESS read-only
    STATUS mandatory
    DESCRIPTION
        "The Output frequency for phase A in Hertz."
    ::= { upsOutput 11 }

upsOutputFrequencyB OBJECT-TYPE
    SYNTAX INTEGER
    UNITS  "0.1 Hertz"
    ACCESS read-only
    STATUS mandatory
    DESCRIPTION
        "The Output frequency for phase B in Hertz."
    ::= { upsOutput 12 }

upsOutputFrequencyC OBJECT-TYPE
    SYNTAX INTEGER
    UNITS  "0.1 Hertz"
    ACCESS read-only
    STATUS mandatory
    DESCRIPTION
        "The Output frequency for phase C in Hertz."
    ::= { upsOutput 13 }

upsOutputTotalActivePower OBJECT-TYPE
    SYNTAX INTEGER
    UNITS  "Kilowatt"
    ACCESS read-only
    STATUS mandatory
    DESCRIPTION
        "The total Output power for in Kilowatts."
    ::= { upsOutput 14 }

upsOutputVoltagePercentA OBJECT-TYPE
    SYNTAX INTEGER
    UNITS  "Percent"
    ACCESS read-only
    STATUS mandatory
    DESCRIPTION
        "The Output voltage for Phase A in percent."
    ::= { upsOutput 15 }

upsOutputVoltagePercentB OBJECT-TYPE
    SYNTAX INTEGER
    UNITS  "Percent"
    ACCESS read-only
    STATUS mandatory
    DESCRIPTION
        "The Output voltage for Phase B in percent."
    ::= { upsOutput 16 }

upsOutputVoltagePercentC OBJECT-TYPE
    SYNTAX INTEGER
    UNITS  "Percent"
    ACCESS read-only
    STATUS mandatory
    DESCRIPTION
        "The Output voltage for Phase C in percent."
    ::= { upsOutput 17 }

upsOutputTotalCurrentPercent OBJECT-TYPE
    SYNTAX INTEGER
    UNITS  "PERCENT"
    ACCESS read-only
    STATUS mandatory
    DESCRIPTION
        "The total output current for in percent."
    ::= { upsOutput 18 }

upsOutputCurrentPercentA OBJECT-TYPE
    SYNTAX INTEGER
    UNITS  "PERCENT"
    ACCESS read-only
    STATUS mandatory
    DESCRIPTION
        "The Output current for phase A in percent."
    ::= { upsOutput 19 }

upsOutputCurrentPercentB OBJECT-TYPE
    SYNTAX INTEGER
    UNITS  "PERCENT"
    ACCESS read-only
    STATUS mandatory
    DESCRIPTION
        "The Output current for phase B in percent."
    ::= { upsOutput 20 }

upsOutputCurrentPercentC OBJECT-TYPE
    SYNTAX INTEGER
    UNITS  "PERCENT"
    ACCESS read-only
    STATUS mandatory
    DESCRIPTION
        "The Output current for phase C in percent."
    ::= { upsOutput 21 }

upsOutputTotalActivePowerPercent OBJECT-TYPE
    SYNTAX INTEGER
    UNITS  "Percent"
    ACCESS read-only
    STATUS mandatory
    DESCRIPTION
        "The total Output power (Watt) in percent."
    ::= { upsOutput 22 }

upsOutputPowerFactor OBJECT-TYPE
    SYNTAX INTEGER
    ACCESS read-only
    STATUS mandatory
    DESCRIPTION
        "The Output power factor."
    ::= { upsOutput 23 }

upsOutputRatedLLVoltage OBJECT-TYPE
    SYNTAX INTEGER
    UNITS  "Voltage"
    ACCESS read-only
    STATUS mandatory
    DESCRIPTION
        "The rated output line to line voltage."
    ::= { upsOutput 24 }

upsOutputRatedLNVoltage OBJECT-TYPE
    SYNTAX INTEGER
    UNITS  "Voltage"
    ACCESS read-only
    STATUS mandatory
    DESCRIPTION
        "The rated output line to neutral voltage."
    ::= { upsOutput 25 }

upsOutputRatedCurrent OBJECT-TYPE
    SYNTAX INTEGER
    UNITS  "Amp"
    ACCESS read-only
    STATUS mandatory
    DESCRIPTION
        "The rated output line to neutral voltage."
    ::= { upsOutput 26 }

upsOutputRatedActivePower OBJECT-TYPE
    SYNTAX INTEGER
    UNITS  "watt"
    ACCESS read-only
    STATUS mandatory
    DESCRIPTION
        "The rated output power in watt."
    ::= { upsOutput 27 }

upsOutputRatedApparentPower OBJECT-TYPE
    SYNTAX INTEGER
    UNITS  "Volt-Amp"
    ACCESS read-only
    STATUS mandatory
    DESCRIPTION
        "The rated output power in volt-amp."
    ::= { upsOutput 28 }

upsOutputUnderVoltageDetectLevel OBJECT-TYPE
    SYNTAX INTEGER
    UNITS  "Volt"
    ACCESS read-only
    STATUS mandatory
    DESCRIPTION
        "The output voltage under the voltage detection level."
    ::= { upsOutput 29 }

upsOutputOverVoltageDetectLevel OBJECT-TYPE
    SYNTAX INTEGER
    UNITS  "Volt"
    ACCESS read-only
    STATUS mandatory
    DESCRIPTION
        "The output voltage over the voltage detection level."
    ::= { upsOutput 30 }

-- ===========================================================================
-- upsBypass - Group 4
-- The UPS Output Data Group
-- ===========================================================================

upsBypassNumOfPhases OBJECT-TYPE
    SYNTAX INTEGER
    UNITS  "Percent"
    ACCESS read-only
    STATUS mandatory
    DESCRIPTION
        "The number of Bypass Lines."
    ::= { upsBypass 1 }

upsBypassLLVoltageAB OBJECT-TYPE
    SYNTAX INTEGER
    UNITS  "RMS Volts"
    ACCESS read-only
    STATUS mandatory
    DESCRIPTION
        "The Bypass line to line voltage for AB in RMS volts."
    ::= { upsBypass 2 }

upsBypassLLVoltageBC OBJECT-TYPE
    SYNTAX INTEGER
    UNITS  "RMS Volts"
    ACCESS read-only
    STATUS mandatory
    DESCRIPTION
        "The Bypass line to line voltage for BC in RMS volts."
    ::= { upsBypass 3 }

upsBypassLLVoltageCA OBJECT-TYPE
    SYNTAX INTEGER
    UNITS  "RMS Volts"
    ACCESS read-only
    STATUS mandatory
    DESCRIPTION
        "The Bypass line to line voltage for CA in RMS volts."
    ::= { upsBypass 4 }

upsBypassLNVoltageAN OBJECT-TYPE
    SYNTAX INTEGER
    UNITS  "RMS Volts"
    ACCESS read-only
    STATUS mandatory
    DESCRIPTION
        "The Bypass line to neutral voltage for AN in RMS volts."
    ::= { upsBypass 5 }

upsBypassLNVoltageBN OBJECT-TYPE
    SYNTAX INTEGER
    UNITS  "RMS Volts"
    ACCESS read-only
    STATUS mandatory
    DESCRIPTION
        "The Bypass line to neutral voltage for BN in RMS volts."
    ::= { upsBypass 6 }

upsBypassLNVoltageCN OBJECT-TYPE
    SYNTAX INTEGER
    UNITS  "RMS Volts"
    ACCESS read-only
    STATUS mandatory
    DESCRIPTION
        "The Bypass line to neutral voltage for CN in RMS volts."
    ::= { upsBypass 7 }

upsBypassFrequencyA OBJECT-TYPE
    SYNTAX INTEGER
    UNITS  "0.1 Hertz"
    ACCESS read-only
    STATUS mandatory
    DESCRIPTION
        "The Bypass frequency for phase A in Hertz."
    ::= { upsBypass 8 }

upsBypassFrequencyB OBJECT-TYPE
    SYNTAX INTEGER
    UNITS  "0.1 Hertz"
    ACCESS read-only
    STATUS mandatory
    DESCRIPTION
        "The Bypass frequency for phase B in Hertz."
    ::= { upsBypass 9 }

upsBypassFrequencyC OBJECT-TYPE
    SYNTAX INTEGER
    UNITS  "0.1 Hertz"
    ACCESS read-only
    STATUS mandatory
    DESCRIPTION
        "The Bypass frequency for phase C in Hertz."
    ::= { upsBypass 10 }

upsBypassVoltagePercentA OBJECT-TYPE
    SYNTAX INTEGER
    UNITS  "Percent"
    ACCESS read-only
    STATUS mandatory
    DESCRIPTION
        "The Bypass voltage for Phase A in percent."
    ::= { upsBypass 11 }

upsBypassVoltagePercentB OBJECT-TYPE
    SYNTAX INTEGER
    UNITS  "Percent"
    ACCESS read-only
    STATUS mandatory
    DESCRIPTION
        "The Bypass voltage for Phase B in percent."
    ::= { upsBypass 12 }

upsBypassVoltagePercentC OBJECT-TYPE
    SYNTAX INTEGER
    UNITS  "Percent"
    ACCESS read-only
    STATUS mandatory
    DESCRIPTION
        "The Bypass voltage for Phase C in percent."
    ::= { upsBypass 13 }

upsBypassUnderVoltageDetectLevel OBJECT-TYPE
    SYNTAX INTEGER
    UNITS  "Percent"
    ACCESS read-only
    STATUS mandatory
    DESCRIPTION
        "The bypass voltage under voltage detection level."
    ::= { upsBypass 14 }

upsBypassOverVoltageDetectLevel OBJECT-TYPE
    SYNTAX INTEGER
    UNITS  "Percent"
    ACCESS read-only
    STATUS mandatory
    DESCRIPTION
        "The bypass voltage over voltage detection level."
    ::= { upsBypass 15 }
	
-- ===========================================================================
-- upsDCBus - Group 5
-- The UPS DC Bus Data Group
-- ===========================================================================
upsDCBusTotalVoltage OBJECT-TYPE
    SYNTAX INTEGER
    UNITS  "DC Volts"
    ACCESS read-only
    STATUS mandatory
    DESCRIPTION
        "The Total DC Bus voltage in DC volts."
    ::= { upsDCBus 1 }

-- ===========================================================================
-- upsBattery - Group 6
-- The UPS Battery Data Group
-- ===========================================================================

upsBatteryStatus OBJECT-TYPE
    SYNTAX INTEGER {
         unknown(1),
         batteryNormal(2),
         batteryLow(3),
         batteryDepleted(4),
         batteryDischarging(5),
         batteryFailure(6)
    }
    ACCESS read-only
    STATUS mandatory
    DESCRIPTION
"The indication of the capacity remaining in the UPS system's battery. A value of battery Normal indicates that the remaining run-time sufficient to handle the load. A value of battery Low indicates the battery level is low. Continued operation in battery mode will deplete batteries. A value of battery Depleted indicates that the UPS will be unable to sustain the present load when and if the utility power is lost(including the possibility that the utility power is currently absent and the UPS is unable to sustain the output). A value of battery Discharging indicates UPS system is in Battery power."
    ::= { upsBattery 1 }

upsElapsedTimeOnBatteryPower OBJECT-TYPE
    SYNTAX NonNegativeInteger
    UNITS   "Second"
    ACCESS read-only
    STATUS mandatory
    DESCRIPTION
"If the unit is on battery power, the elapsed time since the UPS on battery power, or the time since the network management subsystem was last restarted, whichever is less. Zero shall be returned if the unit is not on battery power."
    ::= { upsBattery 2 }

upsBatteryEstimatedBatteryRuntime OBJECT-TYPE
     SYNTAX PositiveInteger
     UNITS "minutes"
     ACCESS read-only
     STATUS mandatory
     DESCRIPTION
         "An estimate of the time to battery charge depletion
          under the present load conditions if the utility power
          is off and remains off, or if it were to be lost and
          remain off."
     ::= { upsBattery 3 }

upsBatteryVoltage OBJECT-TYPE
    SYNTAX INTEGER
    UNITS  "DC Volt"
    ACCESS read-only
    STATUS mandatory
    DESCRIPTION
        "The magnitude of the present battery voltage in DC Volt."
    ::= { upsBattery 4 }

upsBatteryDischargeCurrent OBJECT-TYPE
    SYNTAX INTEGER
    UNITS  "DC Amp"
    ACCESS read-only
    STATUS mandatory
    DESCRIPTION
        "The present battery discharge current in 1/10 DC Amp."
    ::= { upsBattery 5 }

upsBatteryEqualizeChargeTime OBJECT-TYPE
    SYNTAX INTEGER
    UNITS  "Hours"
    ACCESS read-write
    STATUS mandatory
    DESCRIPTION
        "The amount of charging time to equalize the batteries."
    ::= { upsBattery 6 }

upsBatteryFloatChargeVoltage OBJECT-TYPE
    SYNTAX INTEGER
    UNITS  "DC Volt"
    ACCESS read-write
    STATUS mandatory
    DESCRIPTION
        "The battery floating charge voltage."
    ::= { upsBattery 7 }

upsBatteryRatedLowBattLevel OBJECT-TYPE
    SYNTAX INTEGER
    UNITS  "DC Volt"
    ACCESS read-only
    STATUS mandatory
    DESCRIPTION
        "The low battery detection level."
    ::= { upsBattery 8 }

upsBatteryAutoTest OBJECT-TYPE
    SYNTAX INTEGER {
        disable(1),
        enable(2)
    }
    ACCESS read-write
    STATUS mandatory
    DESCRIPTION
        "Enable auto battery test."
    ::= { upsBattery 9 }

upsBatteryAutoTestInterval OBJECT-TYPE
    SYNTAX INTEGER {
        daily(1),
        weekly(2),
		monthly(3)
    }
    ACCESS read-write
    STATUS mandatory
    DESCRIPTION
       "The frequency in which the battery will begin test automatically."
    ::= { upsBattery 10 }

upsBatteryTestatStartUp OBJECT-TYPE
    SYNTAX INTEGER {
        disable(1),
        enable(2)
    }
    ACCESS read-write
    STATUS mandatory
    DESCRIPTION
        "Enable battery test at Start up."
    ::= { upsBattery 11 }

upsBatteryPwrFailEqualizeDuration OBJECT-TYPE
    SYNTAX INTEGER
    UNITS  "Seconds"
    ACCESS read-write
    STATUS mandatory
    DESCRIPTION
        "The time the batteries take to equalize charge after failure."
    ::= { upsBattery 12 }

upsBatteryInSeries OBJECT-TYPE
    SYNTAX INTEGER
    ACCESS read-write
    STATUS mandatory
    DESCRIPTION
        "The number of battery in series."
    ::= { upsBattery 13 }

upsBatteryInParallel OBJECT-TYPE
    SYNTAX INTEGER
    ACCESS read-write
    STATUS mandatory
    DESCRIPTION
        "The number of battery in Parallel."
    ::= { upsBattery 14 }

upsBatteryRatedAmpereHour OBJECT-TYPE
    SYNTAX INTEGER
    UNITS  "AHr"
    ACCESS read-write
    STATUS mandatory
    DESCRIPTION
        "The rated battery in ampere hour."
    ::= { upsBattery 15 }

upsBatteryInstallationDate OBJECT-TYPE
    SYNTAX DisplayString (SIZE(10))
    UNITS  "mm/dd/yyyy"
    ACCESS read-only
    STATUS mandatory
    DESCRIPTION
        "The battery install date."
    ::= { upsBattery 16 }

upsBatteryStartEqualizeCh OBJECT-TYPE
    SYNTAX INTEGER {
        disable(1),
        enable(2)
    }
    ACCESS read-write
    STATUS mandatory
    DESCRIPTION
        "Start Equalize Charge."
    ::= { upsBattery 17 }

upsBatteryRatedBackupTime OBJECT-TYPE
     SYNTAX DisplayString (SIZE(0..8))
     UNITS "minutes"
     ACCESS read-write
     STATUS mandatory
     DESCRIPTION
         "The Battery rated holding time in minutes."
     ::= { upsBattery 18 }

-- ===========================================================================
-- upsStsCtlCfg - Group 7
-- The UPS status, control and configuration
-- ===========================================================================

upsStsCtlCfgPresentDate OBJECT-TYPE
    SYNTAX NonNegativeInteger
    ACCESS read-write
    STATUS mandatory
    DESCRIPTION 
"The present date of the UPS. This is configurable by Administrator."
    ::= { upsStsCtlCfg 1 }

upsStsCtlCfgPresentTime OBJECT-TYPE
    SYNTAX NonNegativeInteger
    ACCESS read-write
    STATUS mandatory
    DESCRIPTION 
"The present time of the UPS. This is configurable by Administrator."
    ::= { upsStsCtlCfg 2 }

upsStsCtlCfgPresentMode OBJECT-TYPE
    SYNTAX INTEGER {
        shutdown0(1),
        shutdown1(2),
        shutdown2(3),
        shutdown3(4),
        shutdown4(5),
        shutdown5(6),
        bypass0(7),
        bypass1(8),
        bypass2(9),
        online0(10),
        online1(11),
        backup(12),
        cvcf(13),
        bypass3(14),
        bypass4(15),
        bypass5(16),
        bypass6(17)
    }
    ACCESS read-only
    STATUS mandatory
    DESCRIPTION
        "The present mode of the UPS system."
    ::= { upsStsCtlCfg 3 }

upsStsCtlCfgServicePortCommSetting OBJECT-TYPE
    SYNTAX INTEGER {
        bd9600(1),
        bd19200(2), 
        bd38400(3),
        bd57600(4),
        bd115200(5)
    }
    ACCESS read-only
    STATUS mandatory
    DESCRIPTION
        "The UPS service port baud rate settings."
    ::= { upsStsCtlCfg 4 }

upsStsCtlCfgRMTIPortCommSetting OBJECT-TYPE
    SYNTAX INTEGER {
        bd9600(1),
        bd19200(2), 
        bd38400(3),
        bd57600(4),
        bd115200(5)
    }
    ACCESS read-only
    STATUS mandatory
    DESCRIPTION
        "The RemotEye 4 port baud rate settings."
    ::= { upsStsCtlCfg 5 }

upsStsCtlCfgAutoRestart OBJECT-TYPE
    SYNTAX INTEGER {
        disable(1),
        enable(2)
    }
    ACCESS read-write
    STATUS mandatory
    DESCRIPTION
        "Enables the UPS to start in inverter mode."
    ::= { upsStsCtlCfg 6 }

upsStsCtlCfgAutoTransferMode OBJECT-TYPE
    SYNTAX INTEGER {
        disable(1),
        enable(2)
    }
    ACCESS read-write
    STATUS mandatory
    DESCRIPTION
        "The UPS service enable auto transfer."
    ::= { upsStsCtlCfg 7 }
	
upsStsCtlCfgUserDefinedOverloadSetPoint OBJECT-TYPE
    SYNTAX INTEGER
	UNITS "%"
    ACCESS read-write
    STATUS mandatory
    DESCRIPTION 
        "The maximum output load % defined by the user."
    ::= { upsStsCtlCfg 8 }

-- ===========================================================================
-- upsHistory - Group 8
-- The UPS History Data Group
-- ===========================================================================
upsHistorySysOperationTime OBJECT-TYPE
    SYNTAX DisplayString (SIZE(0..255))
    UNITS  "Days/Hours/Minutes"
    ACCESS read-only
    STATUS mandatory
    DESCRIPTION 
        "The amount of time the UPS has been on."
    ::= { upsHistory 1 }

upsHistoryInverterOperationTime OBJECT-TYPE
    SYNTAX DisplayString (SIZE(0..255))
    UNITS  "Days/Hours/Minutes"
    ACCESS read-only
    STATUS mandatory
    DESCRIPTION 
        "The amount of time the UPS has been in On-Line Mode."
    ::= { upsHistory 2 }

upsHistoryTotalNumBackup OBJECT-TYPE
    SYNTAX NonNegativeInteger
    ACCESS read-only
    STATUS mandatory
    DESCRIPTION 
        "Total number of times the UPS has been in Back-Up mode."
    ::= { upsHistory 3 }

upsHistoryTotalNumFaults OBJECT-TYPE
    SYNTAX NonNegativeInteger
    ACCESS read-only
    STATUS mandatory
    DESCRIPTION 
        "Total number of faults that has occurred on the UPS."
    ::= { upsHistory 4 }

upsHistoryTotalNumOperationModeChange OBJECT-TYPE
    SYNTAX NonNegativeInteger
    ACCESS read-only
    STATUS mandatory
    DESCRIPTION 
        "The number of mode changes that has occurred."
    ::= { upsHistory 5 }

-- ===========================================================================
-- upsDisplay - Group 9
-- The UPS Display Data Group
-- ===========================================================================
upsDisplayFirmwareVersion OBJECT-TYPE
    SYNTAX DisplayString (SIZE(0..15))
    ACCESS read-only
    STATUS mandatory
    DESCRIPTION
        "The firmware version of the display."
    ::= { upsDisplay 1 }

upsDisplayFirmwareBuildDate OBJECT-TYPE
    SYNTAX DisplayString (SIZE(0..15))
    ACCESS read-only
    STATUS mandatory
    DESCRIPTION
        "The firmware build date of the display."
    ::= { upsDisplay 2 }

upsDisplayFirmwareBuiltTime OBJECT-TYPE
    SYNTAX DisplayString (SIZE(0..15))
    ACCESS read-only
    STATUS mandatory
    DESCRIPTION
        "The firmware build time of the display."
    ::= { upsDisplay 3 }

upsDisplayBuzzerStatus OBJECT-TYPE
    SYNTAX INTEGER {
        off(1),
        idle(2),
        sound(3),
        silenced(4)
    }          
    ACCESS read-only
    STATUS mandatory
    DESCRIPTION
        "Shows the current state of the buzzer."
    ::= { upsDisplay 4 }

upsDisplayRMTIInstallationDate OBJECT-TYPE
    SYNTAX DisplayString(SIZE(8))
    ACCESS read-only
    STATUS mandatory
    DESCRIPTION
        "The RMTI installation date."
    ::= { upsDisplay 5 }

upsDisplayRMTIVersion OBJECT-TYPE
    SYNTAX DisplayString(SIZE(0..15))
    ACCESS read-only
    STATUS mandatory
    DESCRIPTION
        "The RMTI installation date."
    ::= { upsDisplay 6 }

upsDisplayRMTIInstallationStatus OBJECT-TYPE
    SYNTAX INTEGER {
        uninstalled(1),
        installed(2)
    }          
    ACCESS read-only
    STATUS mandatory
    DESCRIPTION
        "Shows the installation status of the RMTI."
    ::= { upsDisplay 7 }

upsDisplayRMTIDataLink OBJECT-TYPE
    SYNTAX INTEGER {
        unknown(1),
        link-down(2),
        link-up(3)
    }          
    ACCESS read-only
    STATUS mandatory
    DESCRIPTION
        "Shows the data status of the RMTI."
    ::= { upsDisplay 8 }

upsDisplayRMTINetworkLink OBJECT-TYPE
    SYNTAX INTEGER {
        unknown(1),
        link-down(2),
        link-up(3)
    }          
    ACCESS read-only
    STATUS mandatory
    DESCRIPTION
        "Shows the network status of the RMTI."
    ::= { upsDisplay 9 }

-- ===========================================================================
-- upsAlarm - Group 10
-- The UPS Alarm List
-- ===========================================================================
upsAlarmsPresent OBJECT-TYPE
    SYNTAX Gauge32
    ACCESS read-only
    STATUS mandatory
    DESCRIPTION
        "The present number of active alarm conditions."
    ::= { upsAlarm 1 }

upsAlarmTable OBJECT-TYPE
    SYNTAX SEQUENCE OF UpsAlarmEntry
    ACCESS not-accessible
    STATUS mandatory
    DESCRIPTION
        "A list of alarm table entries. The table contains
         zero, one, or many rows at any moment, depending upon
         the number of alarm conditions in effect. The table
         is initially empty at agent start-up. The agent
         creates a row in the table each time a condition is
         detected and deletes that row when that condition no
         longer pertains. The agent creates the first row with
         upsAlarmId equal to 1, and increments the value of
         upsAlarmId each time a new row is created, wrapping to
         the first free value greater than or equal to 1 when
         the maximum value of upsAlarmId would otherwise be
         exceeded. Consequently, after multiple operations,
         the table may become sparse, e.g., containing entries
         for rows 95, 100, 101, and 203 and the entries should
         not be assumed to be in chronological order because
         upsAlarmId might have wrapped.

         Alarms are named by an OBJECT IDENTIFIER,
         upsAlarmDescr, to allow a single table to
         reflect well known alarms plus alarms defined by a
         particular implementation, i.e., as documented in the
         private enterprise MIB definition for the device. No
         two rows will have the same value of upsAlarmDescr,
         since alarms define conditions. In order to meet this
         requirement, care should be taken in the definition of
         alarm conditions to insure that a system cannot enter
         the same condition multiple times simultaneously.

         The number of rows in the table at any given time is
         reflected by the value of upsAlarmsPresent."
    ::= { upsAlarm  2 }

upsAlarmEntry OBJECT-TYPE
    SYNTAX UpsAlarmEntry
    ACCESS not-accessible
    STATUS mandatory
    DESCRIPTION
        "An entry containing information applicable to a
         particular alarm."
    INDEX { upsAlarmId }
    ::= { upsAlarmTable  1 }

UpsAlarmEntry ::=
    SEQUENCE {
        upsAlarmId              PositiveInteger,
        upsAlarmDescr           AutonomousType,
        upsAlarmTime            TimeStamp
    }

-- ===========================================================================
-- upsAlarmTable/upsAlarmEntry/upsAlarmId
-- ===========================================================================
upsAlarmId OBJECT-TYPE
    SYNTAX PositiveInteger
    ACCESS not-accessible
    STATUS mandatory
    DESCRIPTION
        "A unique identifier for an alarm condition. This
         value must remain constant."
    ::= { upsAlarmEntry 1 }

upsAlarmDescr OBJECT-TYPE
    SYNTAX AutonomousType
    ACCESS read-only
    STATUS mandatory
    DESCRIPTION
        "A reference to an alarm description object. The
         object referenced should not be accessible, but rather
         be used to provide a unique description of the alarm
         condition."
    ::= { upsAlarmEntry 2 }

-- ===========================================================================
-- .../upsAlarmTime
-- ===========================================================================
upsAlarmTime OBJECT-TYPE
    SYNTAX TimeStamp
    ACCESS read-only
    STATUS mandatory
    DESCRIPTION
        "The value of upsConfigSystemTime when the alarm condition was
         detected. If the alarm condition was detected at the
         time of agent start-up and presumably existed before
         agent start-up, the value of upsAlarmTime shall equal 0."
    ::= { upsAlarmEntry 3 }

upsWellKnownAlarms OBJECT IDENTIFIER ::= { upsAlarm  3 }

upsAlarmFault OBJECT-TYPE 
    SYNTAX INTEGER
    ACCESS read-only
    STATUS mandatory
    DESCRIPTION
        "Fault: One or more fault reported."
    ::= { upsWellKnownAlarms 1 }

upsAlarmOpenFuse OBJECT-TYPE 
    SYNTAX INTEGER
    ACCESS read-only
    STATUS mandatory
    DESCRIPTION
        "Fault: An open fuse reported."
    ::= { upsWellKnownAlarms 2 }

upsAlarmCurrentLimitFault OBJECT-TYPE 
    SYNTAX INTEGER
    ACCESS read-only
    STATUS mandatory
    DESCRIPTION
        "Fault: A current limit reported."
    ::= { upsWellKnownAlarms 3 }

upsAlarmDCBusOverCurrent OBJECT-TYPE 
    SYNTAX INTEGER
    ACCESS read-only
    STATUS mandatory
    DESCRIPTION
        "Fault: A DC bus over current reported."
    ::= { upsWellKnownAlarms 4 }

upsAlarmDCBusOverVoltage OBJECT-TYPE 
    SYNTAX INTEGER
    ACCESS read-only
    STATUS mandatory
    DESCRIPTION
        "Fault: A DC bus over voltage reported."
    ::= { upsWellKnownAlarms 5 }

upsAlarmDCBusImbalance OBJECT-TYPE 
    SYNTAX INTEGER
    ACCESS read-only
    STATUS mandatory
    DESCRIPTION
        "Fault: A DC bus imbalance reported."
    ::= { upsWellKnownAlarms 6 }

upsAlarmOutputUnderVoltage OBJECT-TYPE 
    SYNTAX INTEGER
    ACCESS read-only
    STATUS mandatory
    DESCRIPTION
        "Fault: An inverter output under voltage reported."
    ::= { upsWellKnownAlarms 7 }

upsAlarmOutputOverVoltage OBJECT-TYPE 
    SYNTAX INTEGER
    ACCESS read-only
    STATUS mandatory
    DESCRIPTION
        "Fault: An inverter output over voltage reported."
    ::= { upsWellKnownAlarms 8 }

upsAlarmUPSOverheat OBJECT-TYPE 
    SYNTAX INTEGER
    ACCESS read-only
    STATUS mandatory
    DESCRIPTION
        "Fault: Heat sink or device overheat reported."
    ::= { upsWellKnownAlarms 9 }

upsAlarmUPSOverload OBJECT-TYPE 
    SYNTAX INTEGER
    ACCESS read-only
    STATUS mandatory
    DESCRIPTION
        "Fault: A UPS overload reported."
    ::= { upsWellKnownAlarms 10 }

upsAlarmChargerOverVoltageFault OBJECT-TYPE 
    SYNTAX INTEGER
    ACCESS read-only
    STATUS mandatory
    DESCRIPTION
        "Fault: Charger over voltage reported."
    ::= { upsWellKnownAlarms 11 }

upsAlarmOutputOverCurrent OBJECT-TYPE 
    SYNTAX INTEGER
    ACCESS read-only
    STATUS mandatory
    DESCRIPTION
        "Fault: A output over current reported."
    ::= { upsWellKnownAlarms 12 }

upsAlarmDCBusUnderVoltAtBoostUp OBJECT-TYPE 
    SYNTAX INTEGER
    ACCESS read-only
    STATUS mandatory
    DESCRIPTION
        "Fault: A DC bus under voltage reported during DC bus boost-up."
    ::= { upsWellKnownAlarms 13 }

upsAlarmDCBusUnderVoltAtCharge OBJECT-TYPE 
    SYNTAX INTEGER
    ACCESS read-only
    STATUS mandatory
    DESCRIPTION
        "Fault: A DC bus under voltage during DC bus charging reported."
    ::= { upsWellKnownAlarms 14 }

upsAlarmBypassOverheat OBJECT-TYPE 
    SYNTAX INTEGER
    ACCESS read-only
    STATUS mandatory
    DESCRIPTION
        "Fault: A bypass Overheat reported."
    ::= { upsWellKnownAlarms 15 }

upsAlarmInputPhaseRotationError OBJECT-TYPE
    SYNTAX INTEGER
    ACCESS read-only
    STATUS mandatory
    DESCRIPTION
        "Fault: Input Phase Rotation Error."
    ::= { upsWellKnownAlarms 16 }

upsAlarmBypassPhaseRotationError OBJECT-TYPE
    SYNTAX INTEGER
    ACCESS read-only
    STATUS mandatory
    DESCRIPTION
        "Fault: Bypass Phase Rotation Error."
    ::= { upsWellKnownAlarms 17 }

upsAlarmInputOverVoltage OBJECT-TYPE 
    SYNTAX INTEGER
    ACCESS read-only
    STATUS mandatory
    DESCRIPTION
        "Warning: An input over voltage reported."
    ::= { upsWellKnownAlarms 18 }

upsAlarmInputUnderVoltage OBJECT-TYPE 
    SYNTAX INTEGER
    ACCESS read-only
    STATUS mandatory
    DESCRIPTION
        "Warning: An input under voltage reported."
    ::= { upsWellKnownAlarms 19 }

upsAlarmInputBypassFrequencyError OBJECT-TYPE 
    SYNTAX INTEGER
    ACCESS read-only
    STATUS mandatory
    DESCRIPTION
        "Warning: An input or bypass frequency error reported."
    ::= { upsWellKnownAlarms 20 }

upsAlarmBypassOverVoltage OBJECT-TYPE 
    SYNTAX INTEGER
    ACCESS read-only
    STATUS mandatory
    DESCRIPTION
        "Warning: A bypass over voltage reported."
    ::= { upsWellKnownAlarms 21 }

upsAlarmBypassUnderVoltage OBJECT-TYPE 
    SYNTAX INTEGER
    ACCESS read-only
    STATUS mandatory
    DESCRIPTION
        "Warning: A bypass under voltage reported."
    ::= { upsWellKnownAlarms 22 }

upsAlarmBatteryTestFailed OBJECT-TYPE 
    SYNTAX INTEGER
    ACCESS read-only
    STATUS mandatory
    DESCRIPTION
        "Warning: A battery test failed event reported."
    ::= { upsWellKnownAlarms 23 }

upsAlarmSystemTestFailed OBJECT-TYPE 
    SYNTAX INTEGER
    ACCESS read-only
    STATUS mandatory
    DESCRIPTION
        "Warning: A system test failed event reported."
    ::= { upsWellKnownAlarms 24 }

upsAlarmBatteryLow OBJECT-TYPE
    SYNTAX INTEGER
    ACCESS read-only
    STATUS mandatory
    DESCRIPTION
        "Warning: Battery voltage reached low battery level."
    ::= { upsWellKnownAlarms 25 }

upsAlarmBatteryDepleted OBJECT-TYPE
    SYNTAX INTEGER
    ACCESS read-only
    STATUS mandatory
    DESCRIPTION
        "Warning: A Battery shut down voltage level reached during backup or parallel mode."
    ::= { upsWellKnownAlarms 26 }

upsAlarmBatteryVoltageNotGood OBJECT-TYPE
    SYNTAX INTEGER
    ACCESS read-only
    STATUS mandatory
    DESCRIPTION
        "Warning: Battery Voltage is not good."
    ::= { upsWellKnownAlarms 27 }

upsAlarmBatteryMCCBOff OBJECT-TYPE
    SYNTAX INTEGER
    ACCESS read-only
    STATUS mandatory
    DESCRIPTION
        "Warning: Battery MCCB is off."
    ::= { upsWellKnownAlarms 28 }

upsAlarmOnBypass OBJECT-TYPE 
    SYNTAX INTEGER
    ACCESS read-only
    STATUS mandatory
    DESCRIPTION
        "Warning: UPS is in Bypass mode."
    ::= { upsWellKnownAlarms 29 }

upsAlarmChargerOverVoltageWarning OBJECT-TYPE 
    SYNTAX INTEGER
    ACCESS read-only
    STATUS mandatory
    DESCRIPTION
        "Warning: Charger over voltage reported."
    ::= { upsWellKnownAlarms 30 }

upsAlarmBatteryOverheat OBJECT-TYPE 
    SYNTAX INTEGER
    ACCESS read-only
    STATUS mandatory
    DESCRIPTION
        "Warning: A Battery overheat reported."
    ::= { upsWellKnownAlarms 31 }

upsAlarmSystemOverheat OBJECT-TYPE 
    SYNTAX INTEGER
    ACCESS read-only
    STATUS mandatory
    DESCRIPTION
        "Warning: A system overheat reported."
    ::= { upsWellKnownAlarms 32 }

upsAlarmInverterOverloadWarning OBJECT-TYPE 
    SYNTAX INTEGER
    ACCESS read-only
    STATUS mandatory
    DESCRIPTION
        "Warning: An inverter overload reported. UPS will switch to bypass operation or shut down if no action is taken. Shut down excess equipment to reduce Load."
    ::= { upsWellKnownAlarms 33 }
	
upsAlarmUserDefinedOverloadWarning OBJECT-TYPE 
    SYNTAX INTEGER
    ACCESS read-only
    STATUS mandatory
    DESCRIPTION
        "Warning: The inverter output load % is greater than the user defined overload set point (default: 110%)."
    ::= { upsWellKnownAlarms 34 }

upsAlarmOutputOverloadWarning OBJECT-TYPE 
    SYNTAX INTEGER
    ACCESS read-only
    STATUS mandatory
    DESCRIPTION
        "Warning: An output load is more than 110% reported. UPS will switch to bypass operation or shut down if no action is taken. Shut down excess equipment to reduce Load."
    ::= { upsWellKnownAlarms 35 }

upsAlarmCurrentLimitWarning OBJECT-TYPE 
    SYNTAX INTEGER
    ACCESS read-only
    STATUS mandatory
    DESCRIPTION
        "Warning: A current limit reported."
    ::= { upsWellKnownAlarms 36 }

upsAlarmAsyncOperation OBJECT-TYPE 
    SYNTAX INTEGER
    ACCESS read-only
    STATUS mandatory
    DESCRIPTION
        "Warning: Input and output are Asynchronous."
    ::= { upsWellKnownAlarms 37 }

upsAlarmServiceUPS OBJECT-TYPE 
    SYNTAX INTEGER
    ACCESS read-only
    STATUS mandatory
    DESCRIPTION
        "Warning: UPS is in need of service. Please contact authorized Toshiba service center for assistance."
    ::= { upsWellKnownAlarms 38 }

upsAlarmBatteryNearExpiration OBJECT-TYPE 
    SYNTAX INTEGER
    ACCESS read-only
    STATUS mandatory
    DESCRIPTION
        "Warning: Batteries are nearing the end of their expected lifetime."
    ::= { upsWellKnownAlarms 39 }

upsAlarmBatteryExpired OBJECT-TYPE 
    SYNTAX INTEGER
    ACCESS read-only
    STATUS mandatory
    DESCRIPTION
        "Warning: Batteries have reached their expected lifetime and require replacement."
    ::= { upsWellKnownAlarms 40 }

upsAlarmDispCommError OBJECT-TYPE 
    SYNTAX INTEGER
    ACCESS read-only
    STATUS mandatory
    DESCRIPTION
        "Warning: A communication error between the main controller and display controller reported."
    ::= { upsWellKnownAlarms 41 }

upsAlarmRemotEyeCommError OBJECT-TYPE 
    SYNTAX INTEGER
    ACCESS read-only
    STATUS mandatory
    DESCRIPTION
        "Warning: A Communication error between the main control and the RemotEye 4 reported."
    ::= { upsWellKnownAlarms 42 }

upsAlarmRemotEyeUplinkCommError OBJECT-TYPE 
    SYNTAX INTEGER
    ACCESS read-only
    STATUS mandatory
    DESCRIPTION
        "Warning: A communication error between the RemotEye 4 and the network reported."
    ::= { upsWellKnownAlarms 43 }

upsAlarmServicePortCommError OBJECT-TYPE 
    SYNTAX INTEGER
    ACCESS read-only
    STATUS mandatory
    DESCRIPTION
        "Warning: A communication error between the main controller and the service communication port reported."
    ::= { upsWellKnownAlarms 44 }

upsAlarmROMtoEEError OBJECT-TYPE 
    SYNTAX INTEGER
    ACCESS read-only
    STATUS mandatory
    DESCRIPTION
        "Warning: An error occurred when writing from ROM to EEPROM."
    ::= { upsWellKnownAlarms 45 }

upsAlarmEEtoRAMError OBJECT-TYPE 
    SYNTAX INTEGER
    ACCESS read-only
    STATUS mandatory
    DESCRIPTION
        "Warning: An error occurred when writing from EEPROM to SRAM."
    ::= { upsWellKnownAlarms 46 }

upsAlarmMCCBTrip OBJECT-TYPE 
    SYNTAX INTEGER
    ACCESS read-only
    STATUS mandatory
    DESCRIPTION
        "Warning: Input MCCB trip reported."
    ::= { upsWellKnownAlarms 47 }

upsAlarmEEUpdateError OBJECT-TYPE 
    SYNTAX INTEGER
    ACCESS read-only
    STATUS mandatory
    DESCRIPTION
        "Warning: An error during EEprom update reported."
    ::= { upsWellKnownAlarms 48 }

upsAlarmPowerFailure OBJECT-TYPE 
    SYNTAX INTEGER
    ACCESS read-only
    STATUS mandatory
    DESCRIPTION
        "Info: A power failure reported."
    ::= { upsWellKnownAlarms 49 }

upsAlarmEPOTripped OBJECT-TYPE 
    SYNTAX INTEGER
    ACCESS read-only
    STATUS mandatory
    DESCRIPTION
        "Info: EPO has tripped."
    ::= { upsWellKnownAlarms 50 }

upsAlarmShutdownPending OBJECT-TYPE 
    SYNTAX INTEGER
    ACCESS read-only
    STATUS mandatory
    DESCRIPTION
        "Info: UPS has gone to output shut-down by programmed timer command."
    ::= { upsWellKnownAlarms 51 }

upsAlarmLANShutdown OBJECT-TYPE 
    SYNTAX INTEGER
    ACCESS read-only
    STATUS mandatory
    DESCRIPTION
        "Info: UPS has gone to output shut-down by LAN shut-down command."
    ::= { upsWellKnownAlarms 52 }

upsAlarmRemoteShutdown OBJECT-TYPE 
    SYNTAX INTEGER
    ACCESS read-only
    STATUS mandatory
    DESCRIPTION
        "Info: UPS has gone to output shut-down by remote shut-down command."
    ::= { upsWellKnownAlarms 53 }

upsAlarmDelayStartup OBJECT-TYPE 
    SYNTAX INTEGER
    ACCESS read-only
    STATUS mandatory
    DESCRIPTION
        "Info: UPS is waiting at a specified time set by user before it can start up."
    ::= { upsWellKnownAlarms 54 }

upsAlarmRemoteSwitchEnable OBJECT-TYPE 
    SYNTAX INTEGER
    ACCESS read-only
    STATUS mandatory
    DESCRIPTION
        "Info: Remote switch control enabled."
    ::= { upsWellKnownAlarms 55 }

upsAlarmAutoTransferEnable OBJECT-TYPE 
    SYNTAX INTEGER
    ACCESS read-only
    STATUS mandatory
    DESCRIPTION
        "Info: Auto re-transfer enabled."
    ::= { upsWellKnownAlarms 56 }

upsAlarmProtectiveCharging OBJECT-TYPE 
    SYNTAX INTEGER
    ACCESS read-only
    STATUS mandatory
    DESCRIPTION
        "Info: Protective Charging is set."
    ::= { upsWellKnownAlarms 57 }

upsAlarmEqualizedCharging OBJECT-TYPE 
    SYNTAX INTEGER
    ACCESS read-only
    STATUS mandatory
    DESCRIPTION
        "Info: Equalized Charging enabled."
    ::= { upsWellKnownAlarms 58 }

upsAlarmManualMode OBJECT-TYPE 
    SYNTAX INTEGER
    ACCESS read-only
    STATUS mandatory
    DESCRIPTION
        "Info: Manual mode is selected."
    ::= { upsWellKnownAlarms 59 }

upsAlarmOutputFrequency50Hz OBJECT-TYPE 
    SYNTAX INTEGER
    ACCESS read-only
    STATUS mandatory
    DESCRIPTION
        "Info: Output Frequency is selected to 50Hz."
    ::= { upsWellKnownAlarms 60 }

upsAlarmInverterStartup OBJECT-TYPE 
    SYNTAX INTEGER
    ACCESS read-only
    STATUS mandatory
    DESCRIPTION
        "Info: UPS has immediately switched to inverter from start-up."
    ::= { upsWellKnownAlarms 61 }

upsAlarmBatteryTestInProgress OBJECT-TYPE 
    SYNTAX INTEGER
    ACCESS read-only
    STATUS mandatory
    DESCRIPTION
        "Info: A battery test in progress reported."
    ::= { upsWellKnownAlarms 62 }

upsAlarmForcedBypass OBJECT-TYPE 
    SYNTAX INTEGER
    ACCESS read-only
    STATUS mandatory
    DESCRIPTION
        "Info: UPS has been forced to bypass mode."
    ::= { upsWellKnownAlarms 63 }

upsAlarmFirmwareUpdate OBJECT-TYPE 
    SYNTAX INTEGER
    ACCESS read-only
    STATUS mandatory
    DESCRIPTION
        "Info: Firmware has been updated."
    ::= { upsWellKnownAlarms 64 }

upsAlarmEE1ST OBJECT-TYPE 
    SYNTAX INTEGER
    ACCESS read-only
    STATUS mandatory
    DESCRIPTION
        "Info: EEPROM value are the first time."
    ::= { upsWellKnownAlarms 65 }

upsAlarmBypassEnable OBJECT-TYPE 
    SYNTAX INTEGER
    ACCESS read-only
    STATUS mandatory
    DESCRIPTION
        "Info: Bypass Enabled."
    ::= { upsWellKnownAlarms 66 }

upsAlarmBatteryTestDisable OBJECT-TYPE 
    SYNTAX INTEGER
    ACCESS read-only
    STATUS mandatory
    DESCRIPTION
        "Info: Battery Test Disabled."
    ::= { upsWellKnownAlarms 67 }

upsAlarmDefaultCalibration OBJECT-TYPE 
    SYNTAX INTEGER
    ACCESS read-only
    STATUS mandatory
    DESCRIPTION
        "Info: Touch Panel module is using default values instead of calibrated one."
    ::= { upsWellKnownAlarms 68 }

upsAlarmOutputOff OBJECT-TYPE 
    SYNTAX INTEGER
    ACCESS read-only
    STATUS mandatory
    DESCRIPTION
        "Info: An output off reported."
    ::= { upsWellKnownAlarms 69 }

upsAlarmOnBattery OBJECT-TYPE
    SYNTAX INTEGER
    ACCESS read-only
    STATUS mandatory
    DESCRIPTION
        "Info: The UPS is on Battery mode; it is supplying output power from its batteries."
    ::= { upsWellKnownAlarms 70 }

upsAlarmLogInError OBJECT-TYPE
    SYNTAX INTEGER
    ACCESS read-only
    STATUS mandatory
    DESCRIPTION
        "Info: Error during log in."
    ::= { upsWellKnownAlarms 71 }

-- ===========================================================================
-- upsPassword - Group 11
-- The UPS Password group
-- ===========================================================================
upsPwdAdminCurrentAccessLevel OBJECT-TYPE
    SYNTAX DisplayString (SIZE (0..15))
    ACCESS read-only
    STATUS mandatory
    DESCRIPTION
        "The administrator access level."
    ::= { upsPassword 1 }

upsPwdAdminCurrentPwd OBJECT-TYPE
    SYNTAX DisplayString (SIZE (0..31))
    ACCESS read-write
    STATUS mandatory
    DESCRIPTION
        "The administrator access login name."
    ::= { upsPassword 2 }

upsPwdAdminNewPswd OBJECT-TYPE
    SYNTAX DisplayString (SIZE (0..15))
    ACCESS read-write
    STATUS mandatory
    DESCRIPTION
        "The current password."
    ::= { upsPassword 3 }

-- ===========================================================================
-- upsTrap - Group 12
-- Traps group
-- ===========================================================================
upsTrapFault TRAP-TYPE
    ENTERPRISE ups4300 
    DESCRIPTION
        "Fault: One or more fault reported."
    ::= 1

upsTrapFaultClear TRAP-TYPE
    ENTERPRISE ups4300  
    DESCRIPTION
        "Fault Clear: One or more fault reported."
    ::= 2

upsTrapOpenFuse TRAP-TYPE 
    ENTERPRISE ups4300 
    DESCRIPTION
        "Fault: An open fuse reported."
    ::= 3

upsTrapOpenFuseClear TRAP-TYPE 
    ENTERPRISE ups4300
    DESCRIPTION
        "Fault Clear: An open fuse reported."
    ::= 4

upsTrapCurrentLimitFault TRAP-TYPE
    ENTERPRISE ups4300
    DESCRIPTION
        "Fault: A current limit fault reported. Contact your Toshiba authorized service center for examination."
    ::= 5

upsTrapCurrentLimitFaultClear TRAP-TYPE
    ENTERPRISE ups4300
    DESCRIPTION
        "Fault Clear: A current limit fault reported. Contact your Toshiba authorized service center for examination."
    ::= 6

upsTrapDCBusOverCurrent TRAP-TYPE 
    ENTERPRISE ups4300
    DESCRIPTION
        "Fault: A DC bus over current reported. Contact your Toshiba authorized service center for examination."
    ::= 7

upsTrapDCBusOverCurrentClear TRAP-TYPE 
    ENTERPRISE ups4300
    DESCRIPTION
        "Fault Clear: A DC bus over current reported. Contact your Toshiba authorized service center for examination."
    ::= 8

upsTrapDCBusOverVoltage TRAP-TYPE 
    ENTERPRISE ups4300
    DESCRIPTION
        "Fault: A DC bus over voltage reported. Contact your Toshiba authorized service center for examination."
    ::= 9

upsTrapDCBusOverVoltageClear TRAP-TYPE 
    ENTERPRISE ups4300
    DESCRIPTION
        "Fault Clear: A DC bus over voltage reported. Contact your Toshiba authorized service center for examination."
    ::= 10

upsTrapDCBusImbalance TRAP-TYPE 
    ENTERPRISE ups4300
    DESCRIPTION
        "Fault: A DC bus imbalance reported. Contact your Toshiba authorized service center for examination."
    ::= 11

upsTrapDCBusImbalanceClear TRAP-TYPE 
    ENTERPRISE ups4300
    DESCRIPTION
        "Fault Clear: A DC bus imbalance reported. Contact your Toshiba authorized service center for examination."
    ::= 12

upsTrapOutputUnderVoltage TRAP-TYPE 
    ENTERPRISE ups4300
    DESCRIPTION
        "Fault: An output under voltage reported. Contact your Toshiba authorized service center for examination."
    ::= 13

upsTrapOutputUnderVoltageClear TRAP-TYPE 
    ENTERPRISE ups4300
    DESCRIPTION
        "Fault Clear: An output under voltage reported. Contact your Toshiba authorized service center for examination."
    ::= 14

upsTrapOutputOverVoltage TRAP-TYPE 
    ENTERPRISE ups4300
    DESCRIPTION
        "Fault: An output over voltage reported. Contact your Toshiba authorized service center for examination."
    ::= 15

upsTrapOutputOverVoltageClear TRAP-TYPE 
    ENTERPRISE ups4300
    DESCRIPTION
        "Fault Clear: An output over voltage reported. Contact your Toshiba authorized service center for examination."
    ::= 16

upsTrapUPSOverheat TRAP-TYPE 
    ENTERPRISE ups4300
    DESCRIPTION
        "Fault: A Heat sink or device overheat reported."
    ::= 17

upsTrapUPSOverheatClear TRAP-TYPE 
    ENTERPRISE ups4300
    DESCRIPTION
        "Fault Clear: A Heat sink or device overheat reported."
    ::= 18

upsTrapUPSOverload TRAP-TYPE 
    ENTERPRISE ups4300 
    DESCRIPTION
        "Fault: A UPS overload reported."
    ::= 19

upsTrapUPSOverloadClear TRAP-TYPE 
    ENTERPRISE ups4300 
    DESCRIPTION
        "Fault Clear: A UPS overload reported."
    ::= 20

upsTrapChargerOvervoltageFault TRAP-TYPE 
    ENTERPRISE ups4300
    DESCRIPTION
        "Fault: Charger over voltage reported."
    ::= 21

upsTrapChargerOvervoltageFaultClear TRAP-TYPE 
    ENTERPRISE ups4300
    DESCRIPTION
        "Fault Clear: Charger over voltage reported."
    ::= 22

upsTrapOutputOvercurrent TRAP-TYPE 
    ENTERPRISE ups4300
    DESCRIPTION
        "Fault: An output over current reported."
    ::= 23

upsTrapOutputOvercurrentClear TRAP-TYPE 
    ENTERPRISE ups4300
    DESCRIPTION
        "Fault Clear: An output over current reported."
    ::= 24

upsTrapDCBusUnderVoltAtBoostUp TRAP-TYPE 
    ENTERPRISE ups4300
    DESCRIPTION
        "Fault: A DC bus under voltage during boost-up reported."
    ::= 25

upsTrapDCBusUnderVoltAtBoostUpClear TRAP-TYPE 
    ENTERPRISE ups4300
    DESCRIPTION
        "Fault Clear: A DC bus under voltage during boost-up reported."
    ::= 26

upsTrapDCBusUnderVoltAtCharge TRAP-TYPE 
    ENTERPRISE ups4300
    DESCRIPTION
        "Fault: A DC bus under voltage during charging reported."
    ::= 27

upsTrapDCBusUnderVoltAtChargeClear TRAP-TYPE 
    ENTERPRISE ups4300
    DESCRIPTION
        "Fault Clear: A DC bus under voltage during charging reported."
    ::= 28

upsTrapBypassOverheat TRAP-TYPE
    ENTERPRISE ups4300
    DESCRIPTION
        "Fault: A Bypass overheat reported."
    ::= 29

upsTrapBypassOverheatClear TRAP-TYPE
    ENTERPRISE ups4300
    DESCRIPTION
        "Fault Clear: A Bypass overheat reported."
    ::= 30

upsTrapInputPhaseRotationError TRAP-TYPE
    ENTERPRISE ups4300
    DESCRIPTION
        "Fault: Input Phase Rotation Error reported."
    ::= 31

upsTrapInputPhaseRotationErrorClear TRAP-TYPE
    ENTERPRISE ups4300
    DESCRIPTION
        "Fault Clear: Input Phase Rotation Error reported."
    ::= 32

upsTrapBypassPhaseRotationError TRAP-TYPE
    ENTERPRISE ups4300
    DESCRIPTION
        "Fault: Bypass Phase Rotation Error reported."
    ::= 33

upsTrapBypassPhaseRotationErrorClear TRAP-TYPE
    ENTERPRISE ups4300
    DESCRIPTION
        "Fault Clear: Bypass Phase Rotation Error reported."
    ::= 34

upsTrapInputOverVoltage TRAP-TYPE 
    ENTERPRISE ups4300
    DESCRIPTION
        "Warning: An input over voltage reported."
    ::= 35

upsTrapInputOverVoltageClear TRAP-TYPE 
    ENTERPRISE ups4300
    DESCRIPTION
        "Warning Clear: An input over voltage reported."
    ::= 36

upsTrapInputUnderVoltage TRAP-TYPE 
    ENTERPRISE ups4300 
    DESCRIPTION
        "Warning: An input under voltage reported."
    ::= 37

upsTrapInputUnderVoltageClear TRAP-TYPE 
    ENTERPRISE ups4300 
    DESCRIPTION
        "Warning Clear: An input under voltage reported."
    ::= 38

upsTrapInputBypassFrequencyError TRAP-TYPE 
    ENTERPRISE ups4300
    DESCRIPTION
        "Warning: An input/bypass frequency error reported."
    ::= 39

upsTrapInputBypassFrequencyErrorClear TRAP-TYPE 
    ENTERPRISE ups4300
    DESCRIPTION
        "Warning Clear: An input/bypass frequency error reported."
    ::= 40

upsTrapBypassOverVoltage TRAP-TYPE 
    ENTERPRISE ups4300 
    DESCRIPTION
        "Warning: A bypass over voltage reported."
    ::= 41

upsTrapBypassOverVoltageClear TRAP-TYPE 
    ENTERPRISE ups4300 
    DESCRIPTION
        "Warning Clear: A bypass over voltage reported."
    ::= 42

upsTrapBypassUnderVoltage TRAP-TYPE 
    ENTERPRISE ups4300 
    DESCRIPTION
        "Warning: A bypass under voltage reported."
    ::= 43

upsTrapBypassUnderVoltageClear TRAP-TYPE 
    ENTERPRISE ups4300 
    DESCRIPTION
        "Warning Clear: A bypass under voltage reported."
    ::= 44

upsTrapBatteryTestFailed TRAP-TYPE 
    ENTERPRISE ups4300
    DESCRIPTION
        "Warning: A battery test failed event reported."
    ::= 45

upsTrapBatteryTestFailedClear TRAP-TYPE 
    ENTERPRISE ups4300
    DESCRIPTION
        "Warning Clear: A battery test failed event reported."
    ::= 46

upsTrapSystemTestFailed TRAP-TYPE
    ENTERPRISE ups4300
    DESCRIPTION
        "Warning: A system test failed event reported."	
    ::= 47

upsTrapSystemTestFailedClear TRAP-TYPE
    ENTERPRISE ups4300
    DESCRIPTION
        "Warning Clear: A system test failed event reported."
    ::= 48

upsTrapBatteryLow TRAP-TYPE
    ENTERPRISE ups4300
    DESCRIPTION
        "Warning: A low battery level reported."
    ::= 49

upsTrapBatteryLowClear TRAP-TYPE
    ENTERPRISE ups4300
    DESCRIPTION
        "Warning Clear: A low battery level reported."
    ::= 50

upsTrapBatteryDepleted TRAP-TYPE
    ENTERPRISE ups4300
    DESCRIPTION
        "Warning: A shut-down battery level reported."
    ::= 51

upsTrapBatteryDepletedClear TRAP-TYPE
    ENTERPRISE ups4300
    DESCRIPTION
        "Warning Clear: A shut-down battery level reported."
    ::= 52

upsTrapBatteryVoltageNotGood TRAP-TYPE
    ENTERPRISE ups4300
    DESCRIPTION
        "Warning: Battery Voltage not good reported."
    ::= 53

upsTrapBatteryVoltageNotGoodClear TRAP-TYPE
    ENTERPRISE ups4300
    DESCRIPTION
        "Warning Clear: Battery Voltage not good reported."
    ::= 54

upsTrapBatteryMCCBOff TRAP-TYPE
    ENTERPRISE ups4300
    DESCRIPTION
        "Warning: Battery MCCB is off."
    ::= 55

upsTrapBatteryMCCBOffClear TRAP-TYPE
    ENTERPRISE ups4300
    DESCRIPTION
        "Warning Clear: Battery MCCB is off."
    ::= 56

upsTrapOnBypass TRAP-TYPE 
    ENTERPRISE ups4300
    DESCRIPTION
        "Warning: UPS is in bypass reported."
    ::= 57

upsTrapOnBypassClear TRAP-TYPE 
    ENTERPRISE ups4300
    DESCRIPTION
        "Warning Clear: UPS is in bypass reported."
    ::= 58

upsTrapChargerOverVoltageWarning TRAP-TYPE 
    ENTERPRISE ups4300
    DESCRIPTION
        "Warning: Charger over voltage reported."
    ::= 59

upsTrapChargerOverVoltageWarningClear TRAP-TYPE 
    ENTERPRISE ups4300
    DESCRIPTION
        "Warning Clear: Charger over voltage reported."
    ::= 60

upsTrapBatteryOverheat TRAP-TYPE
    ENTERPRISE ups4300
    DESCRIPTION
        "Warning: A battery overheat reported."
    ::= 61

upsTrapBatteryOverheatClear TRAP-TYPE
    ENTERPRISE ups4300
    DESCRIPTION
        "Warning Clear: A battery overheat reported."
    ::= 62

upsTrapSystemOverheat TRAP-TYPE 
    ENTERPRISE ups4300
    DESCRIPTION
        "Warning: A system overheat reported."
    ::= 63

upsTrapSystemOverheatClear TRAP-TYPE 
    ENTERPRISE ups4300
    DESCRIPTION
        "Warning Clear: A system overheat reported."
    ::= 64
upsTrapInverterOverloadWarning TRAP-TYPE 
    ENTERPRISE ups4300
    DESCRIPTION
        "Warning: Inverter overload reported."
    ::= 65

upsTrapInverterOverloadWarningClear TRAP-TYPE 
    ENTERPRISE ups4300
    DESCRIPTION
        "Warning Clear: Inverter overload reported."
    ::= 66

upsTrapOutputOverloadWarning TRAP-TYPE 
    ENTERPRISE ups4300
    DESCRIPTION
        "Warning: An output load is more than 100% reported."
    ::= 67

upsTrapOutputOverloadWarningClear TRAP-TYPE 
    ENTERPRISE ups4300
    DESCRIPTION
        "Warning Clear: An output load is more than 100% reported."
    ::= 68
	
upsTrapUserDefinedOverloadWarning TRAP-TYPE 
    ENTERPRISE ups4300
    DESCRIPTION
        "Warning: The inverter output load % is greater than the user defined overload set point (default: 110%)."
    ::= 69
	
upsTrapUserDefinedOverloadWarningClear TRAP-TYPE 
    ENTERPRISE ups4300
    DESCRIPTION
        "Warning Clear: The inverter output load % is greater than the user defined overload set point (default: 110%)."
    ::= 70

upsTrapCurrentLimitWarning TRAP-TYPE
    ENTERPRISE ups4300
    DESCRIPTION
        "Warning: A current limit reported."
    ::= 71

upsTrapCurrentLimitWarningClear TRAP-TYPE
    ENTERPRISE ups4300
    DESCRIPTION
        "Warning Clear: A current limit reported."
    ::= 72

upsTrapAsyncOperation TRAP-TYPE 
    ENTERPRISE ups4300
    DESCRIPTION
        "Warning: An Asynchronous operation reported."
    ::= 73

upsTrapAsyncOperationClear TRAP-TYPE 
    ENTERPRISE ups4300
    DESCRIPTION
        "Warning Clear: An Asynchronous operation reported."
    ::= 74

upsTrapServiceUPS TRAP-TYPE 
    ENTERPRISE ups4300
    DESCRIPTION
        "Warning: UPS is in need of service."
    ::= 75

upsTrapServiceUPSClear TRAP-TYPE 
    ENTERPRISE ups4300
    DESCRIPTION
        "Warning Clear: UPS is in need of service."
    ::= 76

upsTrapBatteryNearExpiration TRAP-TYPE 
    ENTERPRISE ups4300
    DESCRIPTION
        "Warning: A near expiration of batteries reported."
    ::= 77

upsTrapBatteryNearExpirationClear TRAP-TYPE 
    ENTERPRISE ups4300
    DESCRIPTION
        "Warning Clear: A near expiration of batteries reported."
    ::= 78

upsTrapBatteryExpired TRAP-TYPE 
    ENTERPRISE ups4300
    DESCRIPTION
        "Warning: Batteries has expired reported."
    ::= 79

upsTrapBatteryExpiredClear TRAP-TYPE 
    ENTERPRISE ups4300
    DESCRIPTION
        "Warning Clear: Batteries has expired reported."
    ::= 80

upsTrapDispCommError TRAP-TYPE 
    ENTERPRISE ups4300
    DESCRIPTION
        "Warning: A communication error between the main controller and the display controller reported."
    ::= 81

upsTrapDispCommErrorClear TRAP-TYPE 
    ENTERPRISE ups4300
    DESCRIPTION
        "Warning Clear: A communication error between the main controller and the display controller reported."
    ::= 82

upsTrapRemotEyeCommError TRAP-TYPE
    ENTERPRISE ups4300
    DESCRIPTION
        "Warning: A communication error between the main control and the RemotEye 4 reported."
    ::= 83

upsTrapRemotEyeCommErrorClear TRAP-TYPE
    ENTERPRISE ups4300
    DESCRIPTION
        "Warning Clear: A communication error between the main control and the RemotEye 4 reported."
    ::= 84

upsTrapRemotEyeUplinkCommError TRAP-TYPE 
    ENTERPRISE ups4300
    DESCRIPTION
        "Warning: A communication error between the RemotEye 4 and the network reported."
    ::= 85

upsTrapRemotEyeUplinkCommErrorClear TRAP-TYPE 
    ENTERPRISE ups4300
    DESCRIPTION
        "Warning Clear: A communication error between the RemotEye 4 and the network reported."
    ::= 86

upsTrapServicePortCommError TRAP-TYPE 
    ENTERPRISE ups4300
    DESCRIPTION
        "Warning: A communication error between the main controller and the service port reported."
    ::= 87

upsTrapServicePortCommErrorClear TRAP-TYPE 
    ENTERPRISE ups4300
    DESCRIPTION
        "Warning Clear: A communication error between the main controller and the service port reported."
    ::= 88

upsTrapROMtoEEError TRAP-TYPE 
    ENTERPRISE ups4300
    DESCRIPTION
        "Warning: An error occurred when writing from ROM to EEPROM reported."
    ::= 89

upsTrapROMtoEEErrorClear TRAP-TYPE 
    ENTERPRISE ups4300
    DESCRIPTION
        "Warning Clear: An error occurred when writing from ROM to EEPROM reported."
    ::= 90

upsTrapEEtoRAMError TRAP-TYPE 
    ENTERPRISE ups4300
    DESCRIPTION
        "Warning: An error occurred when writing from EEPROM to SRAM reported."
    ::= 91

upsTrapEEtoRAMErrorClear TRAP-TYPE 
    ENTERPRISE ups4300
    DESCRIPTION
        "Warning Clear: An error occurred when writing from EEPROM to SRAM reported."
    ::= 92

upsTrapMCCBTrip TRAP-TYPE 
    ENTERPRISE ups4300
    DESCRIPTION
        "Warning: Input MCCB trip reported."
    ::= 93

upsTrapMCCBTripClear TRAP-TYPE 
    ENTERPRISE ups4300
    DESCRIPTION
        "Warning Clear: Input MCCB trip reported."
    ::= 94

upsTrapEEUpdateError TRAP-TYPE 
    ENTERPRISE ups4300
    DESCRIPTION
        "Warning: An error during EEprom update reported."
    ::= 95

upsTrapEEUpdateErrorClear TRAP-TYPE 
    ENTERPRISE ups4300
    DESCRIPTION
        "Warning Clear: An error during EEprom update reported."
    ::= 96

upsTrapPowerFailure TRAP-TYPE 
    ENTERPRISE ups4300
    DESCRIPTION
        "Info: A power failure reported."
    ::= 97

upsTrapPowerFailureClear TRAP-TYPE 
    ENTERPRISE ups4300
    DESCRIPTION
        "Info Clear: A power failure reported."
    ::= 98

upsTrapEPOTripped TRAP-TYPE 
    ENTERPRISE ups4300
    DESCRIPTION
        "Info: EPO has tripped reported."
    ::= 99

upsTrapEPOTrippedClear TRAP-TYPE 
    ENTERPRISE ups4300
    DESCRIPTION
        "Info Clear: EPO has tripped reported."
    ::= 100

upsTrapShutdownPending TRAP-TYPE 
    ENTERPRISE ups4300
    DESCRIPTION
        "Info: UPS has entered output shut-down by programmed timer command."
    ::= 101

upsTrapShutdownPendingClear TRAP-TYPE 
    ENTERPRISE ups4300
    DESCRIPTION
        "Info Clear: UPS has entered output shut-down by programmed timer command."
    ::= 102

upsTrapLANShutdown TRAP-TYPE 
    ENTERPRISE ups4300
    DESCRIPTION
        "Info: UPS has entered output shut-down by LAN shut-down command."
    ::= 103

upsTrapLANShutdownClear TRAP-TYPE 
    ENTERPRISE ups4300
    DESCRIPTION
        "Info Clear: UPS has entered output shut-down by LAN shut-down command."
    ::= 104

upsTrapRemoteShutdown TRAP-TYPE 
    ENTERPRISE ups4300
    DESCRIPTION
        "Info: UPS has entered output shut-down by Remote shut-down command."
    ::= 105

upsTrapRemoteShutdownClear TRAP-TYPE 
    ENTERPRISE ups4300
    DESCRIPTION
        "Info Clear: UPS has entered output shut-down by Remote shut-down command."
    ::= 106

upsTrapDelayStartup TRAP-TYPE 
    ENTERPRISE ups4300
    DESCRIPTION
        "Info: UPS is waiting at a specified time set by user before it can start up."
    ::= 107

upsTrapDelayStartupClear TRAP-TYPE 
    ENTERPRISE ups4300
    DESCRIPTION
        "Info Clear: UPS is waiting at a specified time set by user before it can start up."
    ::= 108

upsTrapRemoteSwitchEnable TRAP-TYPE 
    ENTERPRISE ups4300
    DESCRIPTION
        "Info: Remote Switch control enabled."
    ::= 109

upsTrapRemoteSwitchEnableClear TRAP-TYPE 
    ENTERPRISE ups4300
    DESCRIPTION
        "Info Clear: Remote Switch control enabled."
    ::= 110

upsTrapAutoTransferEnable TRAP-TYPE 
    ENTERPRISE ups4300
    DESCRIPTION
        "Info: Auto Re-transfer enabled."
    ::= 111

upsTrapAutoTransferEnableClear TRAP-TYPE 
    ENTERPRISE ups4300
    DESCRIPTION
        "Info Clear: Auto Re-transfer enabled."
    ::= 112

upsTrapProtectiveCharging TRAP-TYPE 
    ENTERPRISE ups4300
    DESCRIPTION
        "Info: Protective Charging set."
    ::= 113

upsTrapProtectiveChargingClear TRAP-TYPE 
    ENTERPRISE ups4300
    DESCRIPTION
        "Info Clear: Protective Charging set."
    ::= 114

upsTrapEqualizedCharging TRAP-TYPE 
    ENTERPRISE ups4300
    DESCRIPTION
        "Info: Equalized Charging set."
    ::= 115

upsTrapEqualizedChargingClear TRAP-TYPE 
    ENTERPRISE ups4300
    DESCRIPTION
        "Info Clear: Equalized Charging set."
    ::= 116

upsTrapManualMode TRAP-TYPE 
    ENTERPRISE ups4300
    DESCRIPTION
        "Info: Manual Mode selected."
    ::= 117

upsTrapManualModeClear TRAP-TYPE 
    ENTERPRISE ups4300
    DESCRIPTION
        "Info Clear: Manual Mode selected."
    ::= 118

upsTrapOutputFrequency50Hz TRAP-TYPE 
    ENTERPRISE ups4300
    DESCRIPTION
        "Info: Output frequency is selected to 50Hz."
    ::= 119

upsTrapOutputFrequency50HzClear TRAP-TYPE 
    ENTERPRISE ups4300
    DESCRIPTION
        "Info Clear: Output frequency is selected to 50Hz."
    ::= 120

upsTrapInverterStartup TRAP-TYPE 
    ENTERPRISE ups4300
    DESCRIPTION
        "Info: UPS has immediately switch to inverter at start-up."
    ::= 121

upsTrapInverterStartupClear TRAP-TYPE 
    ENTERPRISE ups4300
    DESCRIPTION
        "Info Clear: UPS has immediately switch to inverter at start-up."
    ::= 122

upsTrapBatteryTestInProgress TRAP-TYPE
    ENTERPRISE ups4300
    DESCRIPTION
        "Info: A battery test in progress reported."
    ::= 123

upsTrapBatteryTestInProgressClear TRAP-TYPE
    ENTERPRISE ups4300
    DESCRIPTION
        "Info Clear: A battery test in progress reported."	
    ::= 124

upsTrapForcedBypass TRAP-TYPE
    ENTERPRISE ups4300
    DESCRIPTION
        "Info: UPS has been forced to bypass mode."
    ::= 125

upsTrapForcedBypassClear TRAP-TYPE
    ENTERPRISE ups4300
    DESCRIPTION
        "Info Clear: UPS has been forced to bypass mode."	
    ::= 126

upsTrapFirmwareUpdate TRAP-TYPE
    ENTERPRISE ups4300
    DESCRIPTION
        "Info: Firmware has been updated."
    ::= 127

upsTrapFirmwareUpdateClear TRAP-TYPE
    ENTERPRISE ups4300
    DESCRIPTION
        "Info Clear: Firmware has been updated."	
    ::= 128

upsTrapEE1ST TRAP-TYPE
    ENTERPRISE ups4300
    DESCRIPTION
        "Info: EEPROM value are the first time."
    ::= 129

upsTrapEE1STClear TRAP-TYPE
    ENTERPRISE ups4300
    DESCRIPTION
        "Info Clear: EEPROM value are the first time."	
    ::= 130

upsTrapBypassEnable TRAP-TYPE
    ENTERPRISE ups4300
    DESCRIPTION
        "Info: Bypass Enabled."
    ::= 131

upsTrapBypassEnableClear TRAP-TYPE
    ENTERPRISE ups4300
    DESCRIPTION
        "Info Clear: Bypass Enabled."	
    ::= 132

upsTrapBatteryTestDisabled TRAP-TYPE
    ENTERPRISE ups4300
    DESCRIPTION
        "Info: Battery Test Disabled."
    ::= 133

upsTrapBatteryTestDisabledClear TRAP-TYPE
    ENTERPRISE ups4300
    DESCRIPTION
        "Info Clear: Battery Test Disabled."	
    ::= 134

upsTrapDefaultCalibration TRAP-TYPE 
    ENTERPRISE ups4300
    DESCRIPTION
        "Info: Touch Panel module is using default value instead of calibrated ones."
    ::= 135

upsTrapDefaultCalibrationClear TRAP-TYPE 
    ENTERPRISE ups4300
    DESCRIPTION
        "Info Clear: Touch Panel module is using default value instead of calibrated ones."
    ::= 136

upsTrapOutputOff TRAP-TYPE
    ENTERPRISE ups4300
    DESCRIPTION
        "Info: The UPS system output is off."
    ::= 137

upsTrapOutputOffClear TRAP-TYPE
    ENTERPRISE ups4300
    DESCRIPTION
        "Info Clear: The UPS system output is off."
    ::= 138

upsTrapOnBattery TRAP-TYPE
    ENTERPRISE ups4300
    DESCRIPTION
        "Info: The UPS is on Battery mode; it is supplying output power from its batteries."
    ::= 139

upsTrapOnBatteryClear TRAP-TYPE
    ENTERPRISE ups4300
    DESCRIPTION
        "Info Clear: The UPS is on Battery mode; it is supplying output power from its batteries."
    ::= 140

upsTrapLogInError TRAP-TYPE 
    ENTERPRISE ups4300
    DESCRIPTION
        "Info: UPS Password is incorrect."
    ::= 141

upsTrapLogInErrorClear TRAP-TYPE 
    ENTERPRISE ups4300
    DESCRIPTION
        "Info Clear: UPS Password is incorrect."
    ::= 142
	
END
