IT-WATCHDOGS-MIB DEFINITIONS ::= BEGIN

IMPORTS 


DisplayString, TruthValue					FROM SNMPv2-TC
MODULE-IDENTITY, OBJECT-TYPE, enterprises, Unsigned32		FROM SNMPv2-SMI
TRAP-TYPE							FROM RFC-1215;

itwatchdogs MODULE-IDENTITY
	LAST-UPDATED "200801100000Z"
	ORGANIZATION "I.T. Watchdogs"
	CONTACT-INFO "support@itwatchdogs.com"
	DESCRIPTION "The MIB for I.T. Watchdogs Products"
	::= { enterprises 17373 }

itwatchdogs OBJECT IDENTIFIER
	::= { enterprises 17373 }
	
Owl OBJECT IDENTIFIER
	::= { itwatchdogs 3 }

deviceInfo OBJECT IDENTIFIER
	::= { Owl 1 }

productTitle OBJECT-TYPE
	SYNTAX DisplayString
	MAX-ACCESS read-only
	STATUS current
	DESCRIPTION "Product name"
	::= { deviceInfo 1 }

productVersion OBJECT-TYPE
	SYNTAX DisplayString
	MAX-ACCESS read-only
	STATUS current
	DESCRIPTION "Product version"
	::= { deviceInfo 2 }

productFriendlyName OBJECT-TYPE
	SYNTAX DisplayString
	MAX-ACCESS read-only
	STATUS current
	DESCRIPTION "User-assigned name"
	::= { deviceInfo 3 }

productMacAddress OBJECT-TYPE
	SYNTAX DisplayString
	MAX-ACCESS read-only
	STATUS current
	DESCRIPTION "Product's unique MAC address"
	::= { deviceInfo 4 }

productUrl OBJECT-TYPE
	SYNTAX DisplayString
	MAX-ACCESS read-only
	STATUS current
	DESCRIPTION "Product's main URL access point"
	::= { deviceInfo 5 }

alarmTripType OBJECT-TYPE
        SYNTAX INTEGER(0..9)
        MAX-ACCESS read-only
        STATUS current
        DESCRIPTION "Type of alarm trip. 0 = None, 1 = Low, 2 = High, 3 = Unplugged"
        ::= { deviceInfo 6 }


productHardware OBJECT-TYPE
        SYNTAX DisplayString
        MAX-ACCESS read-only
        STATUS current
        DESCRIPTION "Product's hardware type"
        ::= { deviceInfo 7 }
sensorCountsBase OBJECT IDENTIFIER
	::= { deviceInfo 8 }
	
sensorCounts OBJECT IDENTIFIER
	::= { sensorCountsBase 1 }
	
climateCount OBJECT-TYPE
        SYNTAX INTEGER(0..16)
        MAX-ACCESS read-only
        STATUS current
        DESCRIPTION "Number of climate monitors currently plugged in"
        ::= { sensorCounts 2 }
        
powerMonitorCount OBJECT-TYPE
        SYNTAX INTEGER(0..16)
        MAX-ACCESS read-only
        STATUS current
        DESCRIPTION "Number of power monitors currently plugged in"
        ::= { sensorCounts 3 }
        
tempSensorCount OBJECT-TYPE
        SYNTAX INTEGER(0..16)
        MAX-ACCESS read-only
        STATUS current
        DESCRIPTION "Number of temperature sensors currently plugged in"
        ::= { sensorCounts 4 }
        
airflowSensorCount OBJECT-TYPE
        SYNTAX INTEGER(0..16)
        MAX-ACCESS read-only
        STATUS current
        DESCRIPTION "Number of airflow sensors currently plugged in"
        ::= { sensorCounts 5 }
        
powerOnlyCount OBJECT-TYPE
        SYNTAX INTEGER(0..16)
        MAX-ACCESS read-only
        STATUS current
        DESCRIPTION "Number of power only monitors currently plugged in"
        ::= { sensorCounts 6 }
        
doorSensorCount OBJECT-TYPE
        SYNTAX INTEGER(0..16)
        MAX-ACCESS read-only
        STATUS current
        DESCRIPTION "Number of door sensors currently plugged in"
        ::= { sensorCounts 7 }
        
waterSensorCount OBJECT-TYPE
        SYNTAX INTEGER(0..16)
        MAX-ACCESS read-only
        STATUS current
        DESCRIPTION "Number of water sensors currently plugged in"
        ::= { sensorCounts 8 }

currentSensorCount OBJECT-TYPE
        SYNTAX INTEGER(0..16)
        MAX-ACCESS read-only
        STATUS current
        DESCRIPTION "Number of current sensors currently plugged in"
        ::= { sensorCounts 9 }
        
millivoltSensorCount OBJECT-TYPE
        SYNTAX INTEGER(0..16)
        MAX-ACCESS read-only
        STATUS current
        DESCRIPTION "Number of millivolt sensors currently plugged in"
        ::= { sensorCounts 10 }
        
power3ChSensorCount OBJECT-TYPE
        SYNTAX INTEGER(0..16)
        MAX-ACCESS read-only
        STATUS current
        DESCRIPTION "Number of 3 channel power monitors currently plugged in"
        ::= { sensorCounts 11 }

outletCount OBJECT-TYPE
        SYNTAX INTEGER(0..16)
        MAX-ACCESS read-only
        STATUS current
        DESCRIPTION "Number of outlets currently plugged in"
        ::= { sensorCounts 12 }

vsfcCount OBJECT-TYPE
        SYNTAX INTEGER(0..16)
        MAX-ACCESS read-only
        STATUS current
        DESCRIPTION "Number of fan controller monitors currently plugged in"
        ::= { sensorCounts 13 }

ctrl3ChCount OBJECT-TYPE
        SYNTAX INTEGER(0..16)
        MAX-ACCESS read-only
        STATUS current
        DESCRIPTION "Number of 3 channel controllers currently plugged in"
        ::= { sensorCounts 14 }

ctrlGrpAmpsCount OBJECT-TYPE
        SYNTAX INTEGER(0..16)
        MAX-ACCESS read-only
        STATUS current
        DESCRIPTION "Number of amperage controllers currently plugged in"
        ::= { sensorCounts 15 }

ctrlOutputCount OBJECT-TYPE
        SYNTAX INTEGER(0..16)
        MAX-ACCESS read-only
        STATUS current
        DESCRIPTION "Number of output controllers currently plugged in"
        ::= { sensorCounts 16 }

dewpointSensorCount OBJECT-TYPE
        SYNTAX INTEGER(0..16)
        MAX-ACCESS read-only
        STATUS current
        DESCRIPTION "Number of dewpoint sensors currently plugged in"
        ::= { sensorCounts 17 }
        
digitalSensorCount OBJECT-TYPE
        SYNTAX INTEGER(0..16)
        MAX-ACCESS read-only
        STATUS current
        DESCRIPTION "Number of digital sensors currently plugged in"
        ::= { sensorCounts 18 }

dstsSensorCount OBJECT-TYPE
        SYNTAX INTEGER(0..16)
        MAX-ACCESS read-only
        STATUS current
        DESCRIPTION "Number of DSTS controllers currently plugged in"
        ::= { sensorCounts 19 }
        
cpmSensorCount OBJECT-TYPE
        SYNTAX INTEGER(0..16)
        MAX-ACCESS read-only
        STATUS current
        DESCRIPTION "Number of city power sensors currently plugged in"
        ::= { sensorCounts 20 }        
        
smokeAlarmSensorCount OBJECT-TYPE
        SYNTAX INTEGER(0..16)
        MAX-ACCESS read-only
        STATUS current
        DESCRIPTION "Number of smoke alarm sensors currently plugged in"
        ::= { sensorCounts 21 }
        
neg48VdcSensorCount OBJECT-TYPE
        SYNTAX INTEGER(0..16)
        MAX-ACCESS read-only
        STATUS current
        DESCRIPTION "Number of -48Vdc sensors currently plugged in"
        ::= { sensorCounts 22 }        
        
pos30VdcSensorCount OBJECT-TYPE
        SYNTAX INTEGER(0..16)
        MAX-ACCESS read-only
        STATUS current
        DESCRIPTION "Number of 30Vdc sensors currently plugged in"
        ::= { sensorCounts 23 }             

climateTable OBJECT-TYPE
	SYNTAX SEQUENCE OF ClimateEntry
	MAX-ACCESS  not-accessible
	STATUS current
	DESCRIPTION "Climate sensors (internal sensors for climate units)"
	::= { Owl 2 }

powMonTable OBJECT-TYPE
	SYNTAX SEQUENCE OF PowMonEntry
	MAX-ACCESS  not-accessible
	STATUS current
	DESCRIPTION "A table of Power Monitors"
	::= { Owl 3 }

tempSensorTable OBJECT-TYPE
	SYNTAX SEQUENCE OF TempSensorEntry
	MAX-ACCESS  not-accessible
	STATUS current
	DESCRIPTION "A table of temperature sensors"
	::= { Owl 4 }

airFlowSensorTable OBJECT-TYPE
	SYNTAX SEQUENCE OF AirFlowSensorEntry
	MAX-ACCESS  not-accessible
	STATUS current
	DESCRIPTION "A table of airflow sensors"
	::= { Owl 5 }

powerTable OBJECT-TYPE
	SYNTAX SEQUENCE OF PowerEntry
	MAX-ACCESS  not-accessible
	STATUS current
	DESCRIPTION "A table of Power-Only devices"
	::= { Owl 6 }

doorSensorTable OBJECT-TYPE
	SYNTAX SEQUENCE OF DoorSensorEntry
	MAX-ACCESS  not-accessible
	STATUS current
	DESCRIPTION "A table of door sensors"
	::= { Owl 7 }

waterSensorTable OBJECT-TYPE
	SYNTAX SEQUENCE OF WaterSensorEntry
	MAX-ACCESS  not-accessible
	STATUS current
	DESCRIPTION "A table of water sensors"
	::= { Owl 8 }

currentMonitorTable OBJECT-TYPE
	SYNTAX SEQUENCE OF CurrentMonitorEntry
	MAX-ACCESS  not-accessible
	STATUS current
	DESCRIPTION "A table of current monitors"
	::= { Owl 9 }

millivoltMonitorTable OBJECT-TYPE
	SYNTAX SEQUENCE OF MillivoltMonitorEntry
	MAX-ACCESS  not-accessible
	STATUS current
	DESCRIPTION "A table of millivolt monitors"
	::= { Owl 10 }

pow3ChTable OBJECT-TYPE
	SYNTAX SEQUENCE OF Pow3ChEntry
	MAX-ACCESS  not-accessible
	STATUS current
	DESCRIPTION "A table of Power Monitor 3 Channel"
	::= { Owl 11 }

outletTable OBJECT-TYPE
	SYNTAX SEQUENCE OF OutletEntry
	MAX-ACCESS  not-accessible
	STATUS current
	DESCRIPTION "A table of outlets"
	::= { Owl 12 }

vsfcTable OBJECT-TYPE
	SYNTAX SEQUENCE OF VsfcEntry
	MAX-ACCESS  not-accessible
	STATUS current
	DESCRIPTION "VSFC sensors (internal sensors for VSFC units)"
	::= { Owl 13 }

ctrl3ChTable OBJECT-TYPE
	SYNTAX SEQUENCE OF Ctrl3ChEntry
	MAX-ACCESS  not-accessible
	STATUS current
	DESCRIPTION "A table of a 3 phase outlet control"
	::= { Owl 14 }

ctrlGrpAmpsTable OBJECT-TYPE
	SYNTAX SEQUENCE OF CtrlGrpAmpsEntry
	MAX-ACCESS  not-accessible
	STATUS current
	DESCRIPTION "A table of Control Group Amp readings"
	::= { Owl 15 }

ctrlOutletTable OBJECT-TYPE
	SYNTAX SEQUENCE OF CtrlOutletEntry
	MAX-ACCESS  not-accessible
	STATUS current
	DESCRIPTION "A table of outlet information"
	::= { Owl 16 }

dewPointSensorTable OBJECT-TYPE
	SYNTAX SEQUENCE OF DewPointSensorEntry
	MAX-ACCESS  not-accessible
	STATUS current
	DESCRIPTION "A table of dew point sensors"
	::= { Owl 17 }

digitalSensorTable OBJECT-TYPE
	SYNTAX SEQUENCE OF DigitalSensorEntry
	MAX-ACCESS  not-accessible
	STATUS current
	DESCRIPTION "A table of digital sensors"
	::= { Owl 18 }

dstsTable OBJECT-TYPE
	SYNTAX SEQUENCE OF DstsEntry
	MAX-ACCESS  not-accessible
	STATUS current
	DESCRIPTION "Digital Static Transfer Switch status"
	::= { Owl 19 }

cpmSensorTable OBJECT-TYPE
	SYNTAX SEQUENCE OF CpmSensorEntry
	MAX-ACCESS  not-accessible
	STATUS current
	DESCRIPTION "A table of city power sensors"
	::= { Owl 20 }

smokeAlarmTable OBJECT-TYPE
	SYNTAX SEQUENCE OF SmokeAlarmEntry
	MAX-ACCESS  not-accessible
	STATUS current
	DESCRIPTION "A table of smoke alarm sensors"
	::= { Owl 21 }

neg48VdcSensorTable OBJECT-TYPE
	SYNTAX SEQUENCE OF Neg48VdcSensorEntry
	MAX-ACCESS  not-accessible
	STATUS current
	DESCRIPTION "A table of -48Vdc sensors"
	::= { Owl 22 }

pos30VdcSensorTable OBJECT-TYPE
	SYNTAX SEQUENCE OF Pos30VdcSensorEntry
	MAX-ACCESS  not-accessible
	STATUS current
	DESCRIPTION "A table of 30Vdc sensors"
	::= { Owl 23 }

ctrl3ChIECTable OBJECT-TYPE
	SYNTAX SEQUENCE OF Ctrl3ChIECEntry
	MAX-ACCESS  not-accessible
	STATUS current
	DESCRIPTION "A table of a 3 phase outlet control"
	::= { Owl 24 }

climateEntry OBJECT-TYPE
	SYNTAX  ClimateEntry
	MAX-ACCESS  not-accessible
	STATUS current
	DESCRIPTION 
		"Entry in the climate table: each entry contains
an index (climateIndex) and other details"
	INDEX { climateIndex }
	::= { climateTable 1 }

ClimateEntry ::= SEQUENCE {
	climateIndex		INTEGER(1..1),
	climateSerial		DisplayString,
	climateName		DisplayString,
	climateAvail		Unsigned32,
	climateTempC		INTEGER(-50..100),
	climateTempF		INTEGER(-58..212),
	climateHumidity		INTEGER(0..100),
	climateLight		INTEGER(0..100),
	climateAirflow		INTEGER(0..100),
	climateSound		INTEGER(0..100),
	climateIO1		INTEGER(0..100),
	climateIO2		INTEGER(0..100),
	climateIO3		INTEGER(0..100)
}

climateIndex OBJECT-TYPE
	SYNTAX  INTEGER(1..1)
	MAX-ACCESS  not-accessible
	STATUS current
	DESCRIPTION "Table entry index value"
	::= { climateEntry  1 }
	
climateSerial OBJECT-TYPE
	SYNTAX  DisplayString
	MAX-ACCESS  read-only
	STATUS current
	DESCRIPTION "Serial Number"
	::= { climateEntry  2 }
	
climateName OBJECT-TYPE
	SYNTAX  DisplayString
	MAX-ACCESS  read-only
	STATUS current
	DESCRIPTION "Friendly Name"
	::= { climateEntry  3 }
	
climateAvail OBJECT-TYPE
	SYNTAX  Unsigned32
	MAX-ACCESS  read-only
	STATUS current
	DESCRIPTION "Is device currently plugged in?"
	::= { climateEntry  4 }
	
climateTempC OBJECT-TYPE
	SYNTAX  INTEGER(-50..100)
	MAX-ACCESS  read-only
	STATUS current
	DESCRIPTION "Current reading for Temperature (C)"
	::= { climateEntry  5 }
	
climateTempF OBJECT-TYPE
	SYNTAX  INTEGER(-58..212)
	MAX-ACCESS  read-only
	STATUS current
	DESCRIPTION "Current reading for Temperature (F)"
	::= { climateEntry  6 }
	
climateHumidity OBJECT-TYPE
	SYNTAX  INTEGER(0..100)
	MAX-ACCESS  read-only
	STATUS current
	DESCRIPTION "Current reading for Humidity"
	::= { climateEntry  7 }
	
climateLight OBJECT-TYPE
	SYNTAX  INTEGER(0..100)
	MAX-ACCESS  read-only
	STATUS current
	DESCRIPTION "Current reading for Ambient Light"
	::= { climateEntry  8 }
	
climateAirflow OBJECT-TYPE
	SYNTAX  INTEGER(0..100)
	MAX-ACCESS  read-only
	STATUS current
	DESCRIPTION "Current reading for Airflow"
	::= { climateEntry  9 }
	
climateSound OBJECT-TYPE
	SYNTAX  INTEGER(0..100)
	MAX-ACCESS  read-only
	STATUS current
	DESCRIPTION "Current reading for Sound"
	::= { climateEntry  10 }
	
climateIO1 OBJECT-TYPE
	SYNTAX  INTEGER(0..100)
	MAX-ACCESS  read-only
	STATUS current
	DESCRIPTION "Current reading for Analog Input 1"
	::= { climateEntry  11 }
	
climateIO2 OBJECT-TYPE
	SYNTAX  INTEGER(0..100)
	MAX-ACCESS  read-only
	STATUS current
	DESCRIPTION "Current reading for Analog Input 2"
	::= { climateEntry  12 }
	
climateIO3 OBJECT-TYPE
	SYNTAX  INTEGER(0..100)
	MAX-ACCESS  read-only
	STATUS current
	DESCRIPTION "Current reading for Analog Input 3"
	::= { climateEntry  13 }
	
powMonEntry OBJECT-TYPE
	SYNTAX  PowMonEntry
	MAX-ACCESS  not-accessible
	STATUS current
	DESCRIPTION 
		"Entry in the power monitor table: each entry contains
an index (powMonIndex) and other power monitoring details"
	INDEX { powMonIndex }
	::= { powMonTable 1 }

PowMonEntry ::= SEQUENCE {
	powMonIndex		INTEGER(1..100),
	powMonSerial		DisplayString,
	powMonName		DisplayString,
	powMonAvail		Unsigned32,
	powMonKWattHrs		Unsigned32,
	powMonVolts		Unsigned32,
	powMonVoltMax		Unsigned32,
	powMonVoltMin		Unsigned32,
	powMonVoltPk		Unsigned32,
	powMonAmpsX10		Unsigned32,
	powMonRealPow		Unsigned32,
	powMonAppPow		Unsigned32,
	powMonPwrFact		INTEGER(0..100),
	powMonOutlet1		INTEGER(0..100),
	powMonOutlet2		INTEGER(0..100)
}

powMonIndex OBJECT-TYPE
	SYNTAX  INTEGER(1..100)
	MAX-ACCESS  not-accessible
	STATUS current
	DESCRIPTION "Table entry index value"
	::= { powMonEntry  1 }
	
powMonSerial OBJECT-TYPE
	SYNTAX  DisplayString
	MAX-ACCESS  read-only
	STATUS current
	DESCRIPTION "Serial Number"
	::= { powMonEntry  2 }
	
powMonName OBJECT-TYPE
	SYNTAX  DisplayString
	MAX-ACCESS  read-only
	STATUS current
	DESCRIPTION "Friendly Name"
	::= { powMonEntry  3 }
	
powMonAvail OBJECT-TYPE
	SYNTAX  Unsigned32
	MAX-ACCESS  read-only
	STATUS current
	DESCRIPTION "Is device currently plugged in?"
	::= { powMonEntry  4 }
	
powMonKWattHrs OBJECT-TYPE
	SYNTAX  Unsigned32
	MAX-ACCESS  read-only
	STATUS current
	DESCRIPTION "KWatt-Hours"
	::= { powMonEntry  5 }
	
powMonVolts OBJECT-TYPE
	SYNTAX  Unsigned32
	MAX-ACCESS  read-only
	STATUS current
	DESCRIPTION "Volts"
	::= { powMonEntry  6 }
	
powMonVoltMax OBJECT-TYPE
	SYNTAX  Unsigned32
	MAX-ACCESS  read-only
	STATUS current
	DESCRIPTION "Volts (Max)"
	::= { powMonEntry  7 }
	
powMonVoltMin OBJECT-TYPE
	SYNTAX  Unsigned32
	MAX-ACCESS  read-only
	STATUS current
	DESCRIPTION "Volts (Min)"
	::= { powMonEntry  8 }
	
powMonVoltPk OBJECT-TYPE
	SYNTAX  Unsigned32
	MAX-ACCESS  read-only
	STATUS current
	DESCRIPTION "Volts (Peak)"
	::= { powMonEntry  9 }
	
powMonAmpsX10 OBJECT-TYPE
	SYNTAX  Unsigned32
	MAX-ACCESS  read-only
	STATUS current
	DESCRIPTION "Amps x 10"
	::= { powMonEntry  10 }
	
powMonRealPow OBJECT-TYPE
	SYNTAX  Unsigned32
	MAX-ACCESS  read-only
	STATUS current
	DESCRIPTION "Real Power"
	::= { powMonEntry  11 }
	
powMonAppPow OBJECT-TYPE
	SYNTAX  Unsigned32
	MAX-ACCESS  read-only
	STATUS current
	DESCRIPTION "Apparent Power"
	::= { powMonEntry  12 }
	
powMonPwrFact OBJECT-TYPE
	SYNTAX  INTEGER(0..100)
	MAX-ACCESS  read-only
	STATUS current
	DESCRIPTION "Power Factor"
	::= { powMonEntry  13 }
	
powMonOutlet1 OBJECT-TYPE
	SYNTAX  INTEGER(0..100)
	MAX-ACCESS  read-only
	STATUS current
	DESCRIPTION "Outlet 1"
	::= { powMonEntry  14 }
	
powMonOutlet2 OBJECT-TYPE
	SYNTAX  INTEGER(0..100)
	MAX-ACCESS  read-only
	STATUS current
	DESCRIPTION "Outlet 2"
	::= { powMonEntry  15 }
	
tempSensorEntry OBJECT-TYPE
	SYNTAX  TempSensorEntry
	MAX-ACCESS  not-accessible
	STATUS current
	DESCRIPTION 
		"Entry in the temperature sensor table: each entry contains
an index (tempIndex) and other sensor details"
	INDEX { tempSensorIndex }
	::= { tempSensorTable 1 }

TempSensorEntry ::= SEQUENCE {
	tempSensorIndex		INTEGER(1..100),
	tempSensorSerial		DisplayString,
	tempSensorName		DisplayString,
	tempSensorAvail		Unsigned32,
	tempSensorTempC		INTEGER(-50..100),
	tempSensorTempF		INTEGER(-58..212)
}

tempSensorIndex OBJECT-TYPE
	SYNTAX  INTEGER(1..100)
	MAX-ACCESS  not-accessible
	STATUS current
	DESCRIPTION "Table entry index value"
	::= { tempSensorEntry  1 }
	
tempSensorSerial OBJECT-TYPE
	SYNTAX  DisplayString
	MAX-ACCESS  read-only
	STATUS current
	DESCRIPTION "Serial Number"
	::= { tempSensorEntry  2 }
	
tempSensorName OBJECT-TYPE
	SYNTAX  DisplayString
	MAX-ACCESS  read-only
	STATUS current
	DESCRIPTION "Friendly Name"
	::= { tempSensorEntry  3 }
	
tempSensorAvail OBJECT-TYPE
	SYNTAX  Unsigned32
	MAX-ACCESS  read-only
	STATUS current
	DESCRIPTION "Is device currently plugged in?"
	::= { tempSensorEntry  4 }
	
tempSensorTempC OBJECT-TYPE
	SYNTAX  INTEGER(-50..100)
	MAX-ACCESS  read-only
	STATUS current
	DESCRIPTION "Temperature in Celsius"
	::= { tempSensorEntry  5 }
	
tempSensorTempF OBJECT-TYPE
	SYNTAX  INTEGER(-58..212)
	MAX-ACCESS  read-only
	STATUS current
	DESCRIPTION "Temperature in Fahrenheit"
	::= { tempSensorEntry  6 }
	
airFlowSensorEntry OBJECT-TYPE
	SYNTAX  AirFlowSensorEntry
	MAX-ACCESS  not-accessible
	STATUS current
	DESCRIPTION 
		"Entry in the air flow sensor table: each entry contains
an index (airFlowSensorIndex) and other sensor details"
	INDEX { airFlowSensorIndex }
	::= { airFlowSensorTable 1 }

AirFlowSensorEntry ::= SEQUENCE {
	airFlowSensorIndex		INTEGER(1..100),
	airFlowSensorSerial		DisplayString,
	airFlowSensorName		DisplayString,
	airFlowSensorAvail		Unsigned32,
	airFlowSensorTempC		INTEGER(-50..100),
	airFlowSensorTempF		INTEGER(-58..212),
	airFlowSensorFlow		INTEGER(0..100),
	airFlowSensorHumidity		INTEGER(0..100)
}

airFlowSensorIndex OBJECT-TYPE
	SYNTAX  INTEGER(1..100)
	MAX-ACCESS  not-accessible
	STATUS current
	DESCRIPTION "Table entry index value"
	::= { airFlowSensorEntry  1 }
	
airFlowSensorSerial OBJECT-TYPE
	SYNTAX  DisplayString
	MAX-ACCESS  read-only
	STATUS current
	DESCRIPTION "Serial Number"
	::= { airFlowSensorEntry  2 }
	
airFlowSensorName OBJECT-TYPE
	SYNTAX  DisplayString
	MAX-ACCESS  read-only
	STATUS current
	DESCRIPTION "Friendly Name"
	::= { airFlowSensorEntry  3 }
	
airFlowSensorAvail OBJECT-TYPE
	SYNTAX  Unsigned32
	MAX-ACCESS  read-only
	STATUS current
	DESCRIPTION "Is device currently plugged in?"
	::= { airFlowSensorEntry  4 }
	
airFlowSensorTempC OBJECT-TYPE
	SYNTAX  INTEGER(-50..100)
	MAX-ACCESS  read-only
	STATUS current
	DESCRIPTION "Temperature reading in C"
	::= { airFlowSensorEntry  5 }
	
airFlowSensorTempF OBJECT-TYPE
	SYNTAX  INTEGER(-58..212)
	MAX-ACCESS  read-only
	STATUS current
	DESCRIPTION "Temperature reading in F"
	::= { airFlowSensorEntry  6 }
	
airFlowSensorFlow OBJECT-TYPE
	SYNTAX  INTEGER(0..100)
	MAX-ACCESS  read-only
	STATUS current
	DESCRIPTION "Air flow reading"
	::= { airFlowSensorEntry  7 }
	
airFlowSensorHumidity OBJECT-TYPE
	SYNTAX  INTEGER(0..100)
	MAX-ACCESS  read-only
	STATUS current
	DESCRIPTION "Humidity reading"
	::= { airFlowSensorEntry  8 }
	
powerEntry OBJECT-TYPE
	SYNTAX  PowerEntry
	MAX-ACCESS  not-accessible
	STATUS current
	DESCRIPTION 
		"Entry in the power-only device table: each entry contains
an index (powerIndex) and other power details"
	INDEX { powerIndex }
	::= { powerTable 1 }

PowerEntry ::= SEQUENCE {
	powerIndex		INTEGER(1..100),
	powerSerial		DisplayString,
	powerName		DisplayString,
	powerAvail		Unsigned32,
	powerVolts		Unsigned32,
	powerAmps		Unsigned32,
	powerRealPow		Unsigned32,
	powerAppPow		Unsigned32,
	powerPwrFactor		INTEGER(0..100)
}

powerIndex OBJECT-TYPE
	SYNTAX  INTEGER(1..100)
	MAX-ACCESS  not-accessible
	STATUS current
	DESCRIPTION "Table entry index value"
	::= { powerEntry  1 }
	
powerSerial OBJECT-TYPE
	SYNTAX  DisplayString
	MAX-ACCESS  read-only
	STATUS current
	DESCRIPTION "Serial Number"
	::= { powerEntry  2 }
	
powerName OBJECT-TYPE
	SYNTAX  DisplayString
	MAX-ACCESS  read-only
	STATUS current
	DESCRIPTION "Friendly Name"
	::= { powerEntry  3 }
	
powerAvail OBJECT-TYPE
	SYNTAX  Unsigned32
	MAX-ACCESS  read-only
	STATUS current
	DESCRIPTION "Is device currently plugged in?"
	::= { powerEntry  4 }
	
powerVolts OBJECT-TYPE
	SYNTAX  Unsigned32
	MAX-ACCESS  read-only
	STATUS current
	DESCRIPTION "Volts"
	::= { powerEntry  5 }
	
powerAmps OBJECT-TYPE
	SYNTAX  Unsigned32
	MAX-ACCESS  read-only
	STATUS current
	DESCRIPTION "Amps"
	::= { powerEntry  6 }
	
powerRealPow OBJECT-TYPE
	SYNTAX  Unsigned32
	MAX-ACCESS  read-only
	STATUS current
	DESCRIPTION "Real Power"
	::= { powerEntry  7 }
	
powerAppPow OBJECT-TYPE
	SYNTAX  Unsigned32
	MAX-ACCESS  read-only
	STATUS current
	DESCRIPTION "Apparent Power"
	::= { powerEntry  8 }
	
powerPwrFactor OBJECT-TYPE
	SYNTAX  INTEGER(0..100)
	MAX-ACCESS  read-only
	STATUS current
	DESCRIPTION "Power Factor"
	::= { powerEntry  9 }
	
doorSensorEntry OBJECT-TYPE
	SYNTAX  DoorSensorEntry
	MAX-ACCESS  not-accessible
	STATUS current
	DESCRIPTION 
		"Entry in the door sensor table: each entry contains
an index (doorSensorIndex) and other sensor details"
	INDEX { doorSensorIndex }
	::= { doorSensorTable 1 }

DoorSensorEntry ::= SEQUENCE {
	doorSensorIndex		INTEGER(1..100),
	doorSensorSerial		DisplayString,
	doorSensorName		DisplayString,
	doorSensorAvail		Unsigned32,
	doorSensorStatus		INTEGER(0..100)
}

doorSensorIndex OBJECT-TYPE
	SYNTAX  INTEGER(1..100)
	MAX-ACCESS  not-accessible
	STATUS current
	DESCRIPTION "Table entry index value"
	::= { doorSensorEntry  1 }
	
doorSensorSerial OBJECT-TYPE
	SYNTAX  DisplayString
	MAX-ACCESS  read-only
	STATUS current
	DESCRIPTION "Serial Number"
	::= { doorSensorEntry  2 }
	
doorSensorName OBJECT-TYPE
	SYNTAX  DisplayString
	MAX-ACCESS  read-only
	STATUS current
	DESCRIPTION "Friendly Name"
	::= { doorSensorEntry  3 }
	
doorSensorAvail OBJECT-TYPE
	SYNTAX  Unsigned32
	MAX-ACCESS  read-only
	STATUS current
	DESCRIPTION "Is device currently plugged in?"
	::= { doorSensorEntry  4 }
	
doorSensorStatus OBJECT-TYPE
	SYNTAX  INTEGER(0..100)
	MAX-ACCESS  read-only
	STATUS current
	DESCRIPTION "Door sensor status"
	::= { doorSensorEntry  5 }
	
waterSensorEntry OBJECT-TYPE
	SYNTAX  WaterSensorEntry
	MAX-ACCESS  not-accessible
	STATUS current
	DESCRIPTION 
		"Entry in the water sensor table: each entry contains
an index (waterSensorIndex) and other sensor details"
	INDEX { waterSensorIndex }
	::= { waterSensorTable 1 }

WaterSensorEntry ::= SEQUENCE {
	waterSensorIndex		INTEGER(1..100),
	waterSensorSerial		DisplayString,
	waterSensorName		DisplayString,
	waterSensorAvail		Unsigned32,
	waterSensorDampness		INTEGER(0..100)
}

waterSensorIndex OBJECT-TYPE
	SYNTAX  INTEGER(1..100)
	MAX-ACCESS  not-accessible
	STATUS current
	DESCRIPTION "Table entry index value"
	::= { waterSensorEntry  1 }
	
waterSensorSerial OBJECT-TYPE
	SYNTAX  DisplayString
	MAX-ACCESS  read-only
	STATUS current
	DESCRIPTION "Serial Number"
	::= { waterSensorEntry  2 }
	
waterSensorName OBJECT-TYPE
	SYNTAX  DisplayString
	MAX-ACCESS  read-only
	STATUS current
	DESCRIPTION "Friendly Name"
	::= { waterSensorEntry  3 }
	
waterSensorAvail OBJECT-TYPE
	SYNTAX  Unsigned32
	MAX-ACCESS  read-only
	STATUS current
	DESCRIPTION "Is device currently plugged in?"
	::= { waterSensorEntry  4 }
	
waterSensorDampness OBJECT-TYPE
	SYNTAX  INTEGER(0..100)
	MAX-ACCESS  read-only
	STATUS current
	DESCRIPTION "Dampness of the water sensor"
	::= { waterSensorEntry  5 }
	
currentMonitorEntry OBJECT-TYPE
	SYNTAX  CurrentMonitorEntry
	MAX-ACCESS  not-accessible
	STATUS current
	DESCRIPTION 
		"Entry in the current monitor table: each entry contains
an index (currentMonitorIndex) and other sensor details"
	INDEX { currentMonitorIndex }
	::= { currentMonitorTable 1 }

CurrentMonitorEntry ::= SEQUENCE {
	currentMonitorIndex		INTEGER(1..100),
	currentMonitorSerial		DisplayString,
	currentMonitorName		DisplayString,
	currentMonitorAvail		Unsigned32,
	currentMonitorAmps		INTEGER(0..30)
}

currentMonitorIndex OBJECT-TYPE
	SYNTAX  INTEGER(1..100)
	MAX-ACCESS  not-accessible
	STATUS current
	DESCRIPTION "Table entry index value"
	::= { currentMonitorEntry  1 }
	
currentMonitorSerial OBJECT-TYPE
	SYNTAX  DisplayString
	MAX-ACCESS  read-only
	STATUS current
	DESCRIPTION "Serial Number"
	::= { currentMonitorEntry  2 }
	
currentMonitorName OBJECT-TYPE
	SYNTAX  DisplayString
	MAX-ACCESS  read-only
	STATUS current
	DESCRIPTION "Friendly Name"
	::= { currentMonitorEntry  3 }
	
currentMonitorAvail OBJECT-TYPE
	SYNTAX  Unsigned32
	MAX-ACCESS  read-only
	STATUS current
	DESCRIPTION "Is device currently plugged in?"
	::= { currentMonitorEntry  4 }
	
currentMonitorAmps OBJECT-TYPE
	SYNTAX  INTEGER(0..30)
	MAX-ACCESS  read-only
	STATUS current
	DESCRIPTION "Current in amps"
	::= { currentMonitorEntry  5 }
	
millivoltMonitorEntry OBJECT-TYPE
	SYNTAX  MillivoltMonitorEntry
	MAX-ACCESS  not-accessible
	STATUS current
	DESCRIPTION 
		"Entry in the millivolt monitor table: each entry contains
an index (millivoltMonitorIndex) and other sensor details"
	INDEX { millivoltMonitorIndex }
	::= { millivoltMonitorTable 1 }

MillivoltMonitorEntry ::= SEQUENCE {
	millivoltMonitorIndex		INTEGER(1..100),
	millivoltMonitorSerial		DisplayString,
	millivoltMonitorName		DisplayString,
	millivoltMonitorAvail		Unsigned32,
	millivoltMonitorMV		INTEGER(0..5000)
}

millivoltMonitorIndex OBJECT-TYPE
	SYNTAX  INTEGER(1..100)
	MAX-ACCESS  not-accessible
	STATUS current
	DESCRIPTION "Table entry index value"
	::= { millivoltMonitorEntry  1 }
	
millivoltMonitorSerial OBJECT-TYPE
	SYNTAX  DisplayString
	MAX-ACCESS  read-only
	STATUS current
	DESCRIPTION "Serial Number"
	::= { millivoltMonitorEntry  2 }
	
millivoltMonitorName OBJECT-TYPE
	SYNTAX  DisplayString
	MAX-ACCESS  read-only
	STATUS current
	DESCRIPTION "Friendly Name"
	::= { millivoltMonitorEntry  3 }
	
millivoltMonitorAvail OBJECT-TYPE
	SYNTAX  Unsigned32
	MAX-ACCESS  read-only
	STATUS current
	DESCRIPTION "Is device currently plugged in?"
	::= { millivoltMonitorEntry  4 }
	
millivoltMonitorMV OBJECT-TYPE
	SYNTAX  INTEGER(0..5000)
	MAX-ACCESS  read-only
	STATUS current
	DESCRIPTION "millivolts"
	::= { millivoltMonitorEntry  5 }
	
pow3ChEntry OBJECT-TYPE
	SYNTAX  Pow3ChEntry
	MAX-ACCESS  not-accessible
	STATUS current
	DESCRIPTION 
		"Entry in the power monitor 3 channel table: each entry contains
an index (pow3ChIndex) and other power monitoring details"
	INDEX { pow3ChIndex }
	::= { pow3ChTable 1 }

Pow3ChEntry ::= SEQUENCE {
	pow3ChIndex		INTEGER(1..100),
	pow3ChSerial		DisplayString,
	pow3ChName		DisplayString,
	pow3ChAvail		Unsigned32,
	pow3ChKWattHrsA		Unsigned32,
	pow3ChVoltsA		Unsigned32,
	pow3ChVoltMaxA		Unsigned32,
	pow3ChVoltMinA		Unsigned32,
	pow3ChVoltPkA		Unsigned32,
	pow3ChAmpsX10A		Unsigned32,
	pow3ChRealPowA		Unsigned32,
	pow3ChAppPowA		Unsigned32,
	pow3ChPwrFactA		INTEGER(0..100),
	pow3ChKWattHrsB		Unsigned32,
	pow3ChVoltsB		Unsigned32,
	pow3ChVoltMaxB		Unsigned32,
	pow3ChVoltMinB		Unsigned32,
	pow3ChVoltPkB		Unsigned32,
	pow3ChAmpsX10B		Unsigned32,
	pow3ChRealPowB		Unsigned32,
	pow3ChAppPowB		Unsigned32,
	pow3ChPwrFactB		INTEGER(0..100),
	pow3ChKWattHrsC		Unsigned32,
	pow3ChVoltsC		Unsigned32,
	pow3ChVoltMaxC		Unsigned32,
	pow3ChVoltMinC		Unsigned32,
	pow3ChVoltPkC		Unsigned32,
	pow3ChAmpsX10C		Unsigned32,
	pow3ChRealPowC		Unsigned32,
	pow3ChAppPowC		Unsigned32,
	pow3ChPwrFactC		INTEGER(0..100)
}

pow3ChIndex OBJECT-TYPE
	SYNTAX  INTEGER(1..100)
	MAX-ACCESS  not-accessible
	STATUS current
	DESCRIPTION "Table entry index value"
	::= { pow3ChEntry  1 }
	
pow3ChSerial OBJECT-TYPE
	SYNTAX  DisplayString
	MAX-ACCESS  read-only
	STATUS current
	DESCRIPTION "Serial Number"
	::= { pow3ChEntry  2 }
	
pow3ChName OBJECT-TYPE
	SYNTAX  DisplayString
	MAX-ACCESS  read-only
	STATUS current
	DESCRIPTION "Friendly Name"
	::= { pow3ChEntry  3 }
	
pow3ChAvail OBJECT-TYPE
	SYNTAX  Unsigned32
	MAX-ACCESS  read-only
	STATUS current
	DESCRIPTION "Is device currently plugged in?"
	::= { pow3ChEntry  4 }
	
pow3ChKWattHrsA OBJECT-TYPE
	SYNTAX  Unsigned32
	MAX-ACCESS  read-only
	STATUS current
	DESCRIPTION "KWatt-Hours A"
	::= { pow3ChEntry  5 }
	
pow3ChVoltsA OBJECT-TYPE
	SYNTAX  Unsigned32
	MAX-ACCESS  read-only
	STATUS current
	DESCRIPTION "Volts A"
	::= { pow3ChEntry  6 }
	
pow3ChVoltMaxA OBJECT-TYPE
	SYNTAX  Unsigned32
	MAX-ACCESS  read-only
	STATUS current
	DESCRIPTION "Volts (Max) A"
	::= { pow3ChEntry  7 }
	
pow3ChVoltMinA OBJECT-TYPE
	SYNTAX  Unsigned32
	MAX-ACCESS  read-only
	STATUS current
	DESCRIPTION "Volts (Min) A"
	::= { pow3ChEntry  8 }
	
pow3ChVoltPkA OBJECT-TYPE
	SYNTAX  Unsigned32
	MAX-ACCESS  read-only
	STATUS current
	DESCRIPTION "Volts (Peak) A"
	::= { pow3ChEntry  9 }
	
pow3ChAmpsX10A OBJECT-TYPE
	SYNTAX  Unsigned32
	MAX-ACCESS  read-only
	STATUS current
	DESCRIPTION "Amps x 10 A"
	::= { pow3ChEntry  10 }
	
pow3ChRealPowA OBJECT-TYPE
	SYNTAX  Unsigned32
	MAX-ACCESS  read-only
	STATUS current
	DESCRIPTION "Real Power A"
	::= { pow3ChEntry  11 }
	
pow3ChAppPowA OBJECT-TYPE
	SYNTAX  Unsigned32
	MAX-ACCESS  read-only
	STATUS current
	DESCRIPTION "Apparent Power A"
	::= { pow3ChEntry  12 }
	
pow3ChPwrFactA OBJECT-TYPE
	SYNTAX  INTEGER(0..100)
	MAX-ACCESS  read-only
	STATUS current
	DESCRIPTION "Power Factor A"
	::= { pow3ChEntry  13 }
	
pow3ChKWattHrsB OBJECT-TYPE
	SYNTAX  Unsigned32
	MAX-ACCESS  read-only
	STATUS current
	DESCRIPTION "KWatt-Hours B"
	::= { pow3ChEntry  14 }
	
pow3ChVoltsB OBJECT-TYPE
	SYNTAX  Unsigned32
	MAX-ACCESS  read-only
	STATUS current
	DESCRIPTION "Volts B"
	::= { pow3ChEntry  15 }
	
pow3ChVoltMaxB OBJECT-TYPE
	SYNTAX  Unsigned32
	MAX-ACCESS  read-only
	STATUS current
	DESCRIPTION "Volts (Max) B"
	::= { pow3ChEntry  16 }
	
pow3ChVoltMinB OBJECT-TYPE
	SYNTAX  Unsigned32
	MAX-ACCESS  read-only
	STATUS current
	DESCRIPTION "Volts (Min) B"
	::= { pow3ChEntry  17 }
	
pow3ChVoltPkB OBJECT-TYPE
	SYNTAX  Unsigned32
	MAX-ACCESS  read-only
	STATUS current
	DESCRIPTION "Volts (Peak) B"
	::= { pow3ChEntry  18 }
	
pow3ChAmpsX10B OBJECT-TYPE
	SYNTAX  Unsigned32
	MAX-ACCESS  read-only
	STATUS current
	DESCRIPTION "Amps x 10 B"
	::= { pow3ChEntry  19 }
	
pow3ChRealPowB OBJECT-TYPE
	SYNTAX  Unsigned32
	MAX-ACCESS  read-only
	STATUS current
	DESCRIPTION "Real Power B"
	::= { pow3ChEntry  20 }
	
pow3ChAppPowB OBJECT-TYPE
	SYNTAX  Unsigned32
	MAX-ACCESS  read-only
	STATUS current
	DESCRIPTION "Apparent Power B"
	::= { pow3ChEntry  21 }
	
pow3ChPwrFactB OBJECT-TYPE
	SYNTAX  INTEGER(0..100)
	MAX-ACCESS  read-only
	STATUS current
	DESCRIPTION "Power Factor B"
	::= { pow3ChEntry  22 }
	
pow3ChKWattHrsC OBJECT-TYPE
	SYNTAX  Unsigned32
	MAX-ACCESS  read-only
	STATUS current
	DESCRIPTION "KWatt-Hours C"
	::= { pow3ChEntry  23 }
	
pow3ChVoltsC OBJECT-TYPE
	SYNTAX  Unsigned32
	MAX-ACCESS  read-only
	STATUS current
	DESCRIPTION "Volts C"
	::= { pow3ChEntry  24 }
	
pow3ChVoltMaxC OBJECT-TYPE
	SYNTAX  Unsigned32
	MAX-ACCESS  read-only
	STATUS current
	DESCRIPTION "Volts (Max) C"
	::= { pow3ChEntry  25 }
	
pow3ChVoltMinC OBJECT-TYPE
	SYNTAX  Unsigned32
	MAX-ACCESS  read-only
	STATUS current
	DESCRIPTION "Volts (Min) C"
	::= { pow3ChEntry  26 }
	
pow3ChVoltPkC OBJECT-TYPE
	SYNTAX  Unsigned32
	MAX-ACCESS  read-only
	STATUS current
	DESCRIPTION "Volts (Peak) C"
	::= { pow3ChEntry  27 }
	
pow3ChAmpsX10C OBJECT-TYPE
	SYNTAX  Unsigned32
	MAX-ACCESS  read-only
	STATUS current
	DESCRIPTION "Amps x 10 C"
	::= { pow3ChEntry  28 }
	
pow3ChRealPowC OBJECT-TYPE
	SYNTAX  Unsigned32
	MAX-ACCESS  read-only
	STATUS current
	DESCRIPTION "Real Power C"
	::= { pow3ChEntry  29 }
	
pow3ChAppPowC OBJECT-TYPE
	SYNTAX  Unsigned32
	MAX-ACCESS  read-only
	STATUS current
	DESCRIPTION "Apparent Power C"
	::= { pow3ChEntry  30 }
	
pow3ChPwrFactC OBJECT-TYPE
	SYNTAX  INTEGER(0..100)
	MAX-ACCESS  read-only
	STATUS current
	DESCRIPTION "Power Factor C"
	::= { pow3ChEntry  31 }
	
outletEntry OBJECT-TYPE
	SYNTAX  OutletEntry
	MAX-ACCESS  not-accessible
	STATUS current
	DESCRIPTION 
		"Entry in the outlet table: each entry contains
an index (outletIndex) and other sensor details"
	INDEX { outletIndex }
	::= { outletTable 1 }

OutletEntry ::= SEQUENCE {
	outletIndex		INTEGER(1..100),
	outletSerial		DisplayString,
	outletName		DisplayString,
	outletAvail		Unsigned32,
	outlet1Status		INTEGER(0..100),
	outlet2Status		INTEGER(0..100)
}

outletIndex OBJECT-TYPE
	SYNTAX  INTEGER(1..100)
	MAX-ACCESS  not-accessible
	STATUS current
	DESCRIPTION "Table entry index value"
	::= { outletEntry  1 }
	
outletSerial OBJECT-TYPE
	SYNTAX  DisplayString
	MAX-ACCESS  read-only
	STATUS current
	DESCRIPTION "Serial Number"
	::= { outletEntry  2 }
	
outletName OBJECT-TYPE
	SYNTAX  DisplayString
	MAX-ACCESS  read-only
	STATUS current
	DESCRIPTION "Friendly Name"
	::= { outletEntry  3 }
	
outletAvail OBJECT-TYPE
	SYNTAX  Unsigned32
	MAX-ACCESS  read-only
	STATUS current
	DESCRIPTION "Is device currently plugged in?"
	::= { outletEntry  4 }
	
outlet1Status OBJECT-TYPE
	SYNTAX  INTEGER(0..100)
	MAX-ACCESS  read-only
	STATUS current
	DESCRIPTION "Outlet 1 status"
	::= { outletEntry  5 }
	
outlet2Status OBJECT-TYPE
	SYNTAX  INTEGER(0..100)
	MAX-ACCESS  read-only
	STATUS current
	DESCRIPTION "Outlet 2 status"
	::= { outletEntry  6 }
	
vsfcEntry OBJECT-TYPE
	SYNTAX  VsfcEntry
	MAX-ACCESS  not-accessible
	STATUS current
	DESCRIPTION 
		"Entry in the vsfc table: each entry contains
an index (vsfcIndex) and other details"
	INDEX { vsfcIndex }
	::= { vsfcTable 1 }

VsfcEntry ::= SEQUENCE {
	vsfcIndex		INTEGER(1..1),
	vsfcSerial		DisplayString,
	vsfcName		DisplayString,
	vsfcAvail		Unsigned32,
	vsfcSetPointC		INTEGER(18..38),
	vsfcSetPointF		INTEGER(64..100),
	vsfcIntTempC		INTEGER(-20..50),
	vsfcIntTempF		INTEGER(-4..122),
	vsfcExt1TempC		INTEGER(-20..50),
	vsfcExt1TempF		INTEGER(-20..122),
	vsfcExt2TempC		INTEGER(-20..50),
	vsfcExt2TempF		INTEGER(-20..122),
	vsfcExt3TempC		INTEGER(-20..50),
	vsfcExt3TempF		INTEGER(-20..122),
	vsfcExt4TempC		INTEGER(-20..50),
	vsfcExt4TempF		INTEGER(-20..122),
	vsfcFanSpeed		INTEGER(0..100)
}

vsfcIndex OBJECT-TYPE
	SYNTAX  INTEGER(1..1)
	MAX-ACCESS  not-accessible
	STATUS current
	DESCRIPTION "Table entry index value"
	::= { vsfcEntry  1 }
	
vsfcSerial OBJECT-TYPE
	SYNTAX  DisplayString
	MAX-ACCESS  read-only
	STATUS current
	DESCRIPTION "Serial Number"
	::= { vsfcEntry  2 }
	
vsfcName OBJECT-TYPE
	SYNTAX  DisplayString
	MAX-ACCESS  read-only
	STATUS current
	DESCRIPTION "Friendly Name"
	::= { vsfcEntry  3 }
	
vsfcAvail OBJECT-TYPE
	SYNTAX  Unsigned32
	MAX-ACCESS  read-only
	STATUS current
	DESCRIPTION "Is device currently plugged in?"
	::= { vsfcEntry  4 }
	
vsfcSetPointC OBJECT-TYPE
	SYNTAX  INTEGER(18..38)
	MAX-ACCESS  read-only
	STATUS current
	DESCRIPTION "Current temperature set point in C"
	::= { vsfcEntry  5 }
	
vsfcSetPointF OBJECT-TYPE
	SYNTAX  INTEGER(64..100)
	MAX-ACCESS  read-only
	STATUS current
	DESCRIPTION "Current temperature set point in F"
	::= { vsfcEntry  6 }
	
vsfcIntTempC OBJECT-TYPE
	SYNTAX  INTEGER(-20..50)
	MAX-ACCESS  read-only
	STATUS current
	DESCRIPTION "Current internal temperature reading in C"
	::= { vsfcEntry  7 }
	
vsfcIntTempF OBJECT-TYPE
	SYNTAX  INTEGER(-4..122)
	MAX-ACCESS  read-only
	STATUS current
	DESCRIPTION "Current internal temperature reading in F"
	::= { vsfcEntry  8 }
	
vsfcExt1TempC OBJECT-TYPE
	SYNTAX  INTEGER(-20..50)
	MAX-ACCESS  read-only
	STATUS current
	DESCRIPTION "Current reading for external temp 1 in C"
	::= { vsfcEntry  9 }
	
vsfcExt1TempF OBJECT-TYPE
	SYNTAX  INTEGER(-20..122)
	MAX-ACCESS  read-only
	STATUS current
	DESCRIPTION "Current reading for external temp 1 in F"
	::= { vsfcEntry  10 }
	
vsfcExt2TempC OBJECT-TYPE
	SYNTAX  INTEGER(-20..50)
	MAX-ACCESS  read-only
	STATUS current
	DESCRIPTION "Current reading for external temp 2 in C"
	::= { vsfcEntry  11 }
	
vsfcExt2TempF OBJECT-TYPE
	SYNTAX  INTEGER(-20..122)
	MAX-ACCESS  read-only
	STATUS current
	DESCRIPTION "Current reading for external temp 2 in F"
	::= { vsfcEntry  12 }
	
vsfcExt3TempC OBJECT-TYPE
	SYNTAX  INTEGER(-20..50)
	MAX-ACCESS  read-only
	STATUS current
	DESCRIPTION "Current reading for external temp 3 in C"
	::= { vsfcEntry  13 }
	
vsfcExt3TempF OBJECT-TYPE
	SYNTAX  INTEGER(-20..122)
	MAX-ACCESS  read-only
	STATUS current
	DESCRIPTION "Current reading for external temp 3 in F"
	::= { vsfcEntry  14 }
	
vsfcExt4TempC OBJECT-TYPE
	SYNTAX  INTEGER(-20..50)
	MAX-ACCESS  read-only
	STATUS current
	DESCRIPTION "Current reading for external temp 4 in C"
	::= { vsfcEntry  15 }
	
vsfcExt4TempF OBJECT-TYPE
	SYNTAX  INTEGER(-20..122)
	MAX-ACCESS  read-only
	STATUS current
	DESCRIPTION "Current reading for external temp 4 in F"
	::= { vsfcEntry  16 }
	
vsfcFanSpeed OBJECT-TYPE
	SYNTAX  INTEGER(0..100)
	MAX-ACCESS  read-only
	STATUS current
	DESCRIPTION "Current reading for Fan Speed"
	::= { vsfcEntry  17 }
	
ctrl3ChEntry OBJECT-TYPE
	SYNTAX  Ctrl3ChEntry
	MAX-ACCESS  not-accessible
	STATUS current
	DESCRIPTION 
		"Entry in the 3 phase outlet control table: each entry contains
an index (ctrl3ChIndex) and other outlet control monitoring details"
	INDEX { ctrl3ChIndex }
	::= { ctrl3ChTable 1 }

Ctrl3ChEntry ::= SEQUENCE {
	ctrl3ChIndex		INTEGER(1..1),
	ctrl3ChSerial		DisplayString,
	ctrl3ChName		DisplayString,
	ctrl3ChAvail		Unsigned32,
	ctrl3ChVoltsA		Unsigned32,
	ctrl3ChVoltPkA		Unsigned32,
	ctrl3ChAmpsA		Unsigned32,
	ctrl3ChAmpPkA		Unsigned32,
	ctrl3ChRealPowA		Unsigned32,
	ctrl3ChAppPowA		Unsigned32,
	ctrl3ChPwrFactA		INTEGER(0..100),
	ctrl3ChVoltsB		Unsigned32,
	ctrl3ChVoltPkB		Unsigned32,
	ctrl3ChAmpsB		Unsigned32,
	ctrl3ChAmpPkB		Unsigned32,
	ctrl3ChRealPowB		Unsigned32,
	ctrl3ChAppPowB		Unsigned32,
	ctrl3ChPwrFactB		INTEGER(0..100),
	ctrl3ChVoltsC		Unsigned32,
	ctrl3ChVoltPkC		Unsigned32,
	ctrl3ChAmpsC		Unsigned32,
	ctrl3ChAmpPkC		Unsigned32,
	ctrl3ChRealPowC		Unsigned32,
	ctrl3ChAppPowC		Unsigned32,
	ctrl3ChPwrFactC		INTEGER(0..100)
}

ctrl3ChIndex OBJECT-TYPE
	SYNTAX  INTEGER(1..1)
	MAX-ACCESS  not-accessible
	STATUS current
	DESCRIPTION "Table entry index value"
	::= { ctrl3ChEntry  1 }
	
ctrl3ChSerial OBJECT-TYPE
	SYNTAX  DisplayString
	MAX-ACCESS  read-only
	STATUS current
	DESCRIPTION "Serial Number"
	::= { ctrl3ChEntry  2 }
	
ctrl3ChName OBJECT-TYPE
	SYNTAX  DisplayString
	MAX-ACCESS  read-only
	STATUS current
	DESCRIPTION "Friendly Name"
	::= { ctrl3ChEntry  3 }
	
ctrl3ChAvail OBJECT-TYPE
	SYNTAX  Unsigned32
	MAX-ACCESS  read-only
	STATUS current
	DESCRIPTION "Is device currently plugged in?"
	::= { ctrl3ChEntry  4 }
	
ctrl3ChVoltsA OBJECT-TYPE
	SYNTAX  Unsigned32
	MAX-ACCESS  read-only
	STATUS current
	DESCRIPTION "Volts A"
	::= { ctrl3ChEntry  5 }
	
ctrl3ChVoltPkA OBJECT-TYPE
	SYNTAX  Unsigned32
	MAX-ACCESS  read-only
	STATUS current
	DESCRIPTION "Volts (Peak) A"
	::= { ctrl3ChEntry  6 }
	
ctrl3ChAmpsA OBJECT-TYPE
	SYNTAX  Unsigned32
	MAX-ACCESS  read-only
	STATUS current
	DESCRIPTION "Amps A"
	::= { ctrl3ChEntry  7 }
	
ctrl3ChAmpPkA OBJECT-TYPE
	SYNTAX  Unsigned32
	MAX-ACCESS  read-only
	STATUS current
	DESCRIPTION "Amps Peak A"
	::= { ctrl3ChEntry  8 }
	
ctrl3ChRealPowA OBJECT-TYPE
	SYNTAX  Unsigned32
	MAX-ACCESS  read-only
	STATUS current
	DESCRIPTION "Real Power A"
	::= { ctrl3ChEntry  9 }
	
ctrl3ChAppPowA OBJECT-TYPE
	SYNTAX  Unsigned32
	MAX-ACCESS  read-only
	STATUS current
	DESCRIPTION "Apparent Power A"
	::= { ctrl3ChEntry  10 }
	
ctrl3ChPwrFactA OBJECT-TYPE
	SYNTAX  INTEGER(0..100)
	MAX-ACCESS  read-only
	STATUS current
	DESCRIPTION "Power Factor A"
	::= { ctrl3ChEntry  11 }
	
ctrl3ChVoltsB OBJECT-TYPE
	SYNTAX  Unsigned32
	MAX-ACCESS  read-only
	STATUS current
	DESCRIPTION "Volts B"
	::= { ctrl3ChEntry  12 }
	
ctrl3ChVoltPkB OBJECT-TYPE
	SYNTAX  Unsigned32
	MAX-ACCESS  read-only
	STATUS current
	DESCRIPTION "Volts (Peak) B"
	::= { ctrl3ChEntry  13 }
	
ctrl3ChAmpsB OBJECT-TYPE
	SYNTAX  Unsigned32
	MAX-ACCESS  read-only
	STATUS current
	DESCRIPTION "Amps B"
	::= { ctrl3ChEntry  14 }
	
ctrl3ChAmpPkB OBJECT-TYPE
	SYNTAX  Unsigned32
	MAX-ACCESS  read-only
	STATUS current
	DESCRIPTION "Amps Peak B"
	::= { ctrl3ChEntry  15 }
	
ctrl3ChRealPowB OBJECT-TYPE
	SYNTAX  Unsigned32
	MAX-ACCESS  read-only
	STATUS current
	DESCRIPTION "Real Power B"
	::= { ctrl3ChEntry  16 }
	
ctrl3ChAppPowB OBJECT-TYPE
	SYNTAX  Unsigned32
	MAX-ACCESS  read-only
	STATUS current
	DESCRIPTION "Apparent Power B"
	::= { ctrl3ChEntry  17 }
	
ctrl3ChPwrFactB OBJECT-TYPE
	SYNTAX  INTEGER(0..100)
	MAX-ACCESS  read-only
	STATUS current
	DESCRIPTION "Power Factor B"
	::= { ctrl3ChEntry  18 }
	
ctrl3ChVoltsC OBJECT-TYPE
	SYNTAX  Unsigned32
	MAX-ACCESS  read-only
	STATUS current
	DESCRIPTION "Volts C"
	::= { ctrl3ChEntry  19 }
	
ctrl3ChVoltPkC OBJECT-TYPE
	SYNTAX  Unsigned32
	MAX-ACCESS  read-only
	STATUS current
	DESCRIPTION "Volts (Peak) C"
	::= { ctrl3ChEntry  20 }
	
ctrl3ChAmpsC OBJECT-TYPE
	SYNTAX  Unsigned32
	MAX-ACCESS  read-only
	STATUS current
	DESCRIPTION "Amps C"
	::= { ctrl3ChEntry  21 }
	
ctrl3ChAmpPkC OBJECT-TYPE
	SYNTAX  Unsigned32
	MAX-ACCESS  read-only
	STATUS current
	DESCRIPTION "Amps Peak C"
	::= { ctrl3ChEntry  22 }
	
ctrl3ChRealPowC OBJECT-TYPE
	SYNTAX  Unsigned32
	MAX-ACCESS  read-only
	STATUS current
	DESCRIPTION "Real Power C"
	::= { ctrl3ChEntry  23 }
	
ctrl3ChAppPowC OBJECT-TYPE
	SYNTAX  Unsigned32
	MAX-ACCESS  read-only
	STATUS current
	DESCRIPTION "Apparent Power C"
	::= { ctrl3ChEntry  24 }
	
ctrl3ChPwrFactC OBJECT-TYPE
	SYNTAX  INTEGER(0..100)
	MAX-ACCESS  read-only
	STATUS current
	DESCRIPTION "Power Factor C"
	::= { ctrl3ChEntry  25 }
	
ctrlGrpAmpsEntry OBJECT-TYPE
	SYNTAX  CtrlGrpAmpsEntry
	MAX-ACCESS  not-accessible
	STATUS current
	DESCRIPTION 
		"Entry in the Control Group Amps table: each entry contains
an index (ctrlGrpAmpsIndex) and other sensor details"
	INDEX { ctrlGrpAmpsIndex }
	::= { ctrlGrpAmpsTable 1 }

CtrlGrpAmpsEntry ::= SEQUENCE {
	ctrlGrpAmpsIndex		INTEGER(1..1),
	ctrlGrpAmpsSerial		DisplayString,
	ctrlGrpAmpsName		DisplayString,
	ctrlGrpAmpsAvail		Unsigned32,
	ctrlGrpAmpsA		Unsigned32,
	ctrlGrpAmpsB		Unsigned32,
	ctrlGrpAmpsC		Unsigned32,
	ctrlGrpAmpsD		Unsigned32,
	ctrlGrpAmpsE		Unsigned32,
	ctrlGrpAmpsF		Unsigned32
}

ctrlGrpAmpsIndex OBJECT-TYPE
	SYNTAX  INTEGER(1..1)
	MAX-ACCESS  not-accessible
	STATUS current
	DESCRIPTION "Table entry index value"
	::= { ctrlGrpAmpsEntry  1 }
	
ctrlGrpAmpsSerial OBJECT-TYPE
	SYNTAX  DisplayString
	MAX-ACCESS  read-only
	STATUS current
	DESCRIPTION "Serial Number"
	::= { ctrlGrpAmpsEntry  2 }
	
ctrlGrpAmpsName OBJECT-TYPE
	SYNTAX  DisplayString
	MAX-ACCESS  read-only
	STATUS current
	DESCRIPTION "Friendly Name"
	::= { ctrlGrpAmpsEntry  3 }
	
ctrlGrpAmpsAvail OBJECT-TYPE
	SYNTAX  Unsigned32
	MAX-ACCESS  read-only
	STATUS current
	DESCRIPTION "Is device currently plugged in?"
	::= { ctrlGrpAmpsEntry  4 }
	
ctrlGrpAmpsA OBJECT-TYPE
	SYNTAX  Unsigned32
	MAX-ACCESS  read-only
	STATUS current
	DESCRIPTION "Amps Group A"
	::= { ctrlGrpAmpsEntry  5 }
	
ctrlGrpAmpsB OBJECT-TYPE
	SYNTAX  Unsigned32
	MAX-ACCESS  read-only
	STATUS current
	DESCRIPTION "Amps Group B"
	::= { ctrlGrpAmpsEntry  6 }
	
ctrlGrpAmpsC OBJECT-TYPE
	SYNTAX  Unsigned32
	MAX-ACCESS  read-only
	STATUS current
	DESCRIPTION "Amps Group C"
	::= { ctrlGrpAmpsEntry  7 }
	
ctrlGrpAmpsD OBJECT-TYPE
	SYNTAX  Unsigned32
	MAX-ACCESS  read-only
	STATUS current
	DESCRIPTION "Amps Group D"
	::= { ctrlGrpAmpsEntry  8 }
	
ctrlGrpAmpsE OBJECT-TYPE
	SYNTAX  Unsigned32
	MAX-ACCESS  read-only
	STATUS current
	DESCRIPTION "Amps Group E"
	::= { ctrlGrpAmpsEntry  9 }
	
ctrlGrpAmpsF OBJECT-TYPE
	SYNTAX  Unsigned32
	MAX-ACCESS  read-only
	STATUS current
	DESCRIPTION "Amps Group F"
	::= { ctrlGrpAmpsEntry  10 }
	
ctrlOutletEntry OBJECT-TYPE
	SYNTAX  CtrlOutletEntry
	MAX-ACCESS  not-accessible
	STATUS current
	DESCRIPTION 
		"Entry in the control outlet table: each entry contains
an index (ctrlOutletIndex) and other sensor details"
	INDEX { ctrlOutletIndex }
	::= { ctrlOutletTable 1 }

CtrlOutletEntry ::= SEQUENCE {
	ctrlOutletIndex		INTEGER(1..100),
	ctrlOutletName		DisplayString,
	ctrlOutletStatus		Unsigned32,
	ctrlOutletFeedback		Unsigned32,
	ctrlOutletPending		Unsigned32,
	ctrlOutletAmps		Unsigned32,
	ctrlOutletGroup		DisplayString,
	ctrlOutletUpDelay		Unsigned32,
	ctrlOutletDwnDelay		Unsigned32,
	ctrlOutletRbtDelay		Unsigned32,
	ctrlOutletURL		DisplayString
}

ctrlOutletIndex OBJECT-TYPE
	SYNTAX  INTEGER(1..100)
	MAX-ACCESS  not-accessible
	STATUS current
	DESCRIPTION "Outlet Number"
	::= { ctrlOutletEntry  1 }
	
ctrlOutletName OBJECT-TYPE
	SYNTAX  DisplayString
	MAX-ACCESS  read-only
	STATUS current
	DESCRIPTION "Outlet Friendly Name"
	::= { ctrlOutletEntry  2 }
	
ctrlOutletStatus OBJECT-TYPE
	SYNTAX  Unsigned32
	MAX-ACCESS  read-only
	STATUS current
	DESCRIPTION "Current Outlet Status"
	::= { ctrlOutletEntry  3 }
	
ctrlOutletFeedback OBJECT-TYPE
	SYNTAX  Unsigned32
	MAX-ACCESS  read-only
	STATUS current
	DESCRIPTION "Outlet Feedback Value, should be equal to status"
	::= { ctrlOutletEntry  4 }
	
ctrlOutletPending OBJECT-TYPE
	SYNTAX  Unsigned32
	MAX-ACCESS  read-only
	STATUS current
	DESCRIPTION "Outlet Status to be set to"
	::= { ctrlOutletEntry  5 }
	
ctrlOutletAmps OBJECT-TYPE
	SYNTAX  Unsigned32
	MAX-ACCESS  read-only
	STATUS current
	DESCRIPTION "Outlet Amps readings"
	::= { ctrlOutletEntry  6 }
	
ctrlOutletGroup OBJECT-TYPE
	SYNTAX  DisplayString
	MAX-ACCESS  read-only
	STATUS current
	DESCRIPTION "Outlet Group"
	::= { ctrlOutletEntry  7 }
	
ctrlOutletUpDelay OBJECT-TYPE
	SYNTAX  Unsigned32
	MAX-ACCESS  read-only
	STATUS current
	DESCRIPTION "Outlet Power Up Delay"
	::= { ctrlOutletEntry  8 }
	
ctrlOutletDwnDelay OBJECT-TYPE
	SYNTAX  Unsigned32
	MAX-ACCESS  read-only
	STATUS current
	DESCRIPTION "Outlet Power Down Delay"
	::= { ctrlOutletEntry  9 }
	
ctrlOutletRbtDelay OBJECT-TYPE
	SYNTAX  Unsigned32
	MAX-ACCESS  read-only
	STATUS current
	DESCRIPTION "Outlet Reboot Delay"
	::= { ctrlOutletEntry  10 }
	
ctrlOutletURL OBJECT-TYPE
	SYNTAX  DisplayString
	MAX-ACCESS  read-only
	STATUS current
	DESCRIPTION "Outlet URL"
	::= { ctrlOutletEntry  11 }
	
dewPointSensorEntry OBJECT-TYPE
	SYNTAX  DewPointSensorEntry
	MAX-ACCESS  not-accessible
	STATUS current
	DESCRIPTION 
		"Entry in the dew point sensor table: each entry contains
an index (dewPointSensorIndex) and other sensor details"
	INDEX { dewPointSensorIndex }
	::= { dewPointSensorTable 1 }

DewPointSensorEntry ::= SEQUENCE {
	dewPointSensorIndex		INTEGER(1..100),
	dewPointSensorSerial		DisplayString,
	dewPointSensorName		DisplayString,
	dewPointSensorAvail		Unsigned32,
	dewPointSensorDewPointC		INTEGER(-50..100),
	dewPointSensorDewPointF		INTEGER(-58..212),
	dewPointSensorTempC		INTEGER(-50..100),
	dewPointSensorTempF		INTEGER(-58..212),
	dewPointSensorHumidity		INTEGER(0..100)
}

dewPointSensorIndex OBJECT-TYPE
	SYNTAX  INTEGER(1..100)
	MAX-ACCESS  not-accessible
	STATUS current
	DESCRIPTION "Table entry index value"
	::= { dewPointSensorEntry  1 }
	
dewPointSensorSerial OBJECT-TYPE
	SYNTAX  DisplayString
	MAX-ACCESS  read-only
	STATUS current
	DESCRIPTION "Serial Number"
	::= { dewPointSensorEntry  2 }
	
dewPointSensorName OBJECT-TYPE
	SYNTAX  DisplayString
	MAX-ACCESS  read-only
	STATUS current
	DESCRIPTION "Friendly Name"
	::= { dewPointSensorEntry  3 }
	
dewPointSensorAvail OBJECT-TYPE
	SYNTAX  Unsigned32
	MAX-ACCESS  read-only
	STATUS current
	DESCRIPTION "Is device currently plugged in?"
	::= { dewPointSensorEntry  4 }
	
dewPointSensorDewPointC OBJECT-TYPE
	SYNTAX  INTEGER(-50..100)
	MAX-ACCESS  read-only
	STATUS current
	DESCRIPTION "Dew point reading in C"
	::= { dewPointSensorEntry  5 }
	
dewPointSensorDewPointF OBJECT-TYPE
	SYNTAX  INTEGER(-58..212)
	MAX-ACCESS  read-only
	STATUS current
	DESCRIPTION "Dew point reading in F"
	::= { dewPointSensorEntry  6 }
	
dewPointSensorTempC OBJECT-TYPE
	SYNTAX  INTEGER(-50..100)
	MAX-ACCESS  read-only
	STATUS current
	DESCRIPTION "Temperature reading in C"
	::= { dewPointSensorEntry  7 }
	
dewPointSensorTempF OBJECT-TYPE
	SYNTAX  INTEGER(-58..212)
	MAX-ACCESS  read-only
	STATUS current
	DESCRIPTION "Temperature reading in F"
	::= { dewPointSensorEntry  8 }
	
dewPointSensorHumidity OBJECT-TYPE
	SYNTAX  INTEGER(0..100)
	MAX-ACCESS  read-only
	STATUS current
	DESCRIPTION "Humidity reading"
	::= { dewPointSensorEntry  9 }
	
digitalSensorEntry OBJECT-TYPE
	SYNTAX  DigitalSensorEntry
	MAX-ACCESS  not-accessible
	STATUS current
	DESCRIPTION 
		"Entry in the digital sensor table: each entry contains
an index (digitalSensorIndex) and other sensor details"
	INDEX { digitalSensorIndex }
	::= { digitalSensorTable 1 }

DigitalSensorEntry ::= SEQUENCE {
	digitalSensorIndex		INTEGER(1..100),
	digitalSensorSerial		DisplayString,
	digitalSensorName		DisplayString,
	digitalSensorAvail		Unsigned32,
	digitalSensorDigital		INTEGER(0..100)
}

digitalSensorIndex OBJECT-TYPE
	SYNTAX  INTEGER(1..100)
	MAX-ACCESS  not-accessible
	STATUS current
	DESCRIPTION "Table entry index value"
	::= { digitalSensorEntry  1 }
	
digitalSensorSerial OBJECT-TYPE
	SYNTAX  DisplayString
	MAX-ACCESS  read-only
	STATUS current
	DESCRIPTION "Serial Number"
	::= { digitalSensorEntry  2 }
	
digitalSensorName OBJECT-TYPE
	SYNTAX  DisplayString
	MAX-ACCESS  read-only
	STATUS current
	DESCRIPTION "Friendly Name"
	::= { digitalSensorEntry  3 }
	
digitalSensorAvail OBJECT-TYPE
	SYNTAX  Unsigned32
	MAX-ACCESS  read-only
	STATUS current
	DESCRIPTION "Is device currently plugged in?"
	::= { digitalSensorEntry  4 }
	
digitalSensorDigital OBJECT-TYPE
	SYNTAX  INTEGER(0..100)
	MAX-ACCESS  read-only
	STATUS current
	DESCRIPTION "Digital sensor status"
	::= { digitalSensorEntry  5 }
	
dstsEntry OBJECT-TYPE
	SYNTAX  DstsEntry
	MAX-ACCESS  not-accessible
	STATUS current
	DESCRIPTION 
		"Entry in the DSTS table: each entry contains
an index (dstsIndex) and other details"
	INDEX { dstsIndex }
	::= { dstsTable 1 }

DstsEntry ::= SEQUENCE {
	dstsIndex		INTEGER(1..1),
	dstsSerial		DisplayString,
	dstsName		DisplayString,
	dstsAvail		Unsigned32,
	dstsVoltsA		Unsigned32,
	dstsAmpsA		Unsigned32,
	dstsVoltsB		Unsigned32,
	dstsAmpsB		Unsigned32,
	dstsSourceAActive		Unsigned32,
	dstsSourceBActive		Unsigned32,
	dstsPowerStatusA		Unsigned32,
	dstsPowerStatusB		Unsigned32,
	dstsSourceATempC		INTEGER(-20..50),
	dstsSourceBTempC		INTEGER(-20..50)
}

dstsIndex OBJECT-TYPE
	SYNTAX  INTEGER(1..1)
	MAX-ACCESS  not-accessible
	STATUS current
	DESCRIPTION "Table entry index value"
	::= { dstsEntry  1 }
	
dstsSerial OBJECT-TYPE
	SYNTAX  DisplayString
	MAX-ACCESS  read-only
	STATUS current
	DESCRIPTION "Serial Number"
	::= { dstsEntry  2 }
	
dstsName OBJECT-TYPE
	SYNTAX  DisplayString
	MAX-ACCESS  read-only
	STATUS current
	DESCRIPTION "Friendly Name"
	::= { dstsEntry  3 }
	
dstsAvail OBJECT-TYPE
	SYNTAX  Unsigned32
	MAX-ACCESS  read-only
	STATUS current
	DESCRIPTION "Is device currently plugged in?"
	::= { dstsEntry  4 }
	
dstsVoltsA OBJECT-TYPE
	SYNTAX  Unsigned32
	MAX-ACCESS  read-only
	STATUS current
	DESCRIPTION "RMS Voltage of Side A"
	::= { dstsEntry  5 }
	
dstsAmpsA OBJECT-TYPE
	SYNTAX  Unsigned32
	MAX-ACCESS  read-only
	STATUS current
	DESCRIPTION "RMS Current of Side A"
	::= { dstsEntry  6 }
	
dstsVoltsB OBJECT-TYPE
	SYNTAX  Unsigned32
	MAX-ACCESS  read-only
	STATUS current
	DESCRIPTION "RMS Voltage of Side B"
	::= { dstsEntry  7 }
	
dstsAmpsB OBJECT-TYPE
	SYNTAX  Unsigned32
	MAX-ACCESS  read-only
	STATUS current
	DESCRIPTION "RMS Current of Side B"
	::= { dstsEntry  8 }
	
dstsSourceAActive OBJECT-TYPE
	SYNTAX  Unsigned32
	MAX-ACCESS  read-only
	STATUS current
	DESCRIPTION "If 99, source A active"
	::= { dstsEntry  9 }
	
dstsSourceBActive OBJECT-TYPE
	SYNTAX  Unsigned32
	MAX-ACCESS  read-only
	STATUS current
	DESCRIPTION "If 99, source B active"
	::= { dstsEntry  10 }
	
dstsPowerStatusA OBJECT-TYPE
	SYNTAX  Unsigned32
	MAX-ACCESS  read-only
	STATUS current
	DESCRIPTION "Power Quality of source A"
	::= { dstsEntry  11 }
	
dstsPowerStatusB OBJECT-TYPE
	SYNTAX  Unsigned32
	MAX-ACCESS  read-only
	STATUS current
	DESCRIPTION "Power Quality of Source B"
	::= { dstsEntry  12 }
	
dstsSourceATempC OBJECT-TYPE
	SYNTAX  INTEGER(-20..50)
	MAX-ACCESS  read-only
	STATUS current
	DESCRIPTION "Current reading for Source A temp in C"
	::= { dstsEntry  13 }
	
dstsSourceBTempC OBJECT-TYPE
	SYNTAX  INTEGER(-20..50)
	MAX-ACCESS  read-only
	STATUS current
	DESCRIPTION "Current reading for Source B temp in C"
	::= { dstsEntry  14 }
	
cpmSensorEntry OBJECT-TYPE
	SYNTAX  CpmSensorEntry
	MAX-ACCESS  not-accessible
	STATUS current
	DESCRIPTION 
		"Entry in the city power sensor table: each entry contains
an index (cpmSensorIndex) and other sensor details"
	INDEX { cpmSensorIndex }
	::= { cpmSensorTable 1 }

CpmSensorEntry ::= SEQUENCE {
	cpmSensorIndex		INTEGER(1..100),
	cpmSensorSerial		DisplayString,
	cpmSensorName		DisplayString,
	cpmSensorAvail		Unsigned32,
	cpmSensorStatus		INTEGER(0..100)
}

cpmSensorIndex OBJECT-TYPE
	SYNTAX  INTEGER(1..100)
	MAX-ACCESS  not-accessible
	STATUS current
	DESCRIPTION "Table entry index value"
	::= { cpmSensorEntry  1 }
	
cpmSensorSerial OBJECT-TYPE
	SYNTAX  DisplayString
	MAX-ACCESS  read-only
	STATUS current
	DESCRIPTION "Serial Number"
	::= { cpmSensorEntry  2 }
	
cpmSensorName OBJECT-TYPE
	SYNTAX  DisplayString
	MAX-ACCESS  read-only
	STATUS current
	DESCRIPTION "Friendly Name"
	::= { cpmSensorEntry  3 }
	
cpmSensorAvail OBJECT-TYPE
	SYNTAX  Unsigned32
	MAX-ACCESS  read-only
	STATUS current
	DESCRIPTION "Is device currently plugged in?"
	::= { cpmSensorEntry  4 }
	
cpmSensorStatus OBJECT-TYPE
	SYNTAX  INTEGER(0..100)
	MAX-ACCESS  read-only
	STATUS current
	DESCRIPTION "City Power sensor status"
	::= { cpmSensorEntry  5 }
	
smokeAlarmEntry OBJECT-TYPE
	SYNTAX  SmokeAlarmEntry
	MAX-ACCESS  not-accessible
	STATUS current
	DESCRIPTION 
		"Entry in the smoke alarm sensor table: each entry contains
an index (smokeAlarmIndex) and other sensor details"
	INDEX { smokeAlarmIndex }
	::= { smokeAlarmTable 1 }

SmokeAlarmEntry ::= SEQUENCE {
	smokeAlarmIndex		INTEGER(1..100),
	smokeAlarmSerial		DisplayString,
	smokeAlarmName		DisplayString,
	smokeAlarmAvail		Unsigned32,
	smokeAlarmStatus		INTEGER(0..100)
}

smokeAlarmIndex OBJECT-TYPE
	SYNTAX  INTEGER(1..100)
	MAX-ACCESS  not-accessible
	STATUS current
	DESCRIPTION "Table entry index value"
	::= { smokeAlarmEntry  1 }
	
smokeAlarmSerial OBJECT-TYPE
	SYNTAX  DisplayString
	MAX-ACCESS  read-only
	STATUS current
	DESCRIPTION "Serial Number"
	::= { smokeAlarmEntry  2 }
	
smokeAlarmName OBJECT-TYPE
	SYNTAX  DisplayString
	MAX-ACCESS  read-only
	STATUS current
	DESCRIPTION "Friendly Name"
	::= { smokeAlarmEntry  3 }
	
smokeAlarmAvail OBJECT-TYPE
	SYNTAX  Unsigned32
	MAX-ACCESS  read-only
	STATUS current
	DESCRIPTION "Is device currently plugged in?"
	::= { smokeAlarmEntry  4 }
	
smokeAlarmStatus OBJECT-TYPE
	SYNTAX  INTEGER(0..100)
	MAX-ACCESS  read-only
	STATUS current
	DESCRIPTION "Smoke alarm status"
	::= { smokeAlarmEntry  5 }
	
neg48VdcSensorEntry OBJECT-TYPE
	SYNTAX  Neg48VdcSensorEntry
	MAX-ACCESS  not-accessible
	STATUS current
	DESCRIPTION 
		"Entry in the -48Vdc sensor table: each entry contains
an index (neg48VdcSensorIndex) and other sensor details"
	INDEX { neg48VdcSensorIndex }
	::= { neg48VdcSensorTable 1 }

Neg48VdcSensorEntry ::= SEQUENCE {
	neg48VdcSensorIndex		INTEGER(1..100),
	neg48VdcSensorSerial		DisplayString,
	neg48VdcSensorName		DisplayString,
	neg48VdcSensorAvail		Unsigned32,
	neg48VdcSensorVoltage		INTEGER(-100..10)
}

neg48VdcSensorIndex OBJECT-TYPE
	SYNTAX  INTEGER(1..100)
	MAX-ACCESS  not-accessible
	STATUS current
	DESCRIPTION "Table entry index value"
	::= { neg48VdcSensorEntry  1 }
	
neg48VdcSensorSerial OBJECT-TYPE
	SYNTAX  DisplayString
	MAX-ACCESS  read-only
	STATUS current
	DESCRIPTION "Serial Number"
	::= { neg48VdcSensorEntry  2 }
	
neg48VdcSensorName OBJECT-TYPE
	SYNTAX  DisplayString
	MAX-ACCESS  read-only
	STATUS current
	DESCRIPTION "Friendly Name"
	::= { neg48VdcSensorEntry  3 }
	
neg48VdcSensorAvail OBJECT-TYPE
	SYNTAX  Unsigned32
	MAX-ACCESS  read-only
	STATUS current
	DESCRIPTION "Is device currently plugged in?"
	::= { neg48VdcSensorEntry  4 }
	
neg48VdcSensorVoltage OBJECT-TYPE
	SYNTAX  INTEGER(-100..10)
	MAX-ACCESS  read-only
	STATUS current
	DESCRIPTION "-48Vdc Sensor value"
	::= { neg48VdcSensorEntry  5 }
	
pos30VdcSensorEntry OBJECT-TYPE
	SYNTAX  Pos30VdcSensorEntry
	MAX-ACCESS  not-accessible
	STATUS current
	DESCRIPTION 
		"Entry in the 30Vdc sensor table: each entry contains
an index (pos30VdcSensorIndex) and other sensor details"
	INDEX { pos30VdcSensorIndex }
	::= { pos30VdcSensorTable 1 }

Pos30VdcSensorEntry ::= SEQUENCE {
	pos30VdcSensorIndex		INTEGER(1..100),
	pos30VdcSensorSerial		DisplayString,
	pos30VdcSensorName		DisplayString,
	pos30VdcSensorAvail		Unsigned32,
	pos30VdcSensorVoltage		INTEGER(-10..100)
}

pos30VdcSensorIndex OBJECT-TYPE
	SYNTAX  INTEGER(1..100)
	MAX-ACCESS  not-accessible
	STATUS current
	DESCRIPTION "Table entry index value"
	::= { pos30VdcSensorEntry  1 }
	
pos30VdcSensorSerial OBJECT-TYPE
	SYNTAX  DisplayString
	MAX-ACCESS  read-only
	STATUS current
	DESCRIPTION "Serial Number"
	::= { pos30VdcSensorEntry  2 }
	
pos30VdcSensorName OBJECT-TYPE
	SYNTAX  DisplayString
	MAX-ACCESS  read-only
	STATUS current
	DESCRIPTION "Friendly Name"
	::= { pos30VdcSensorEntry  3 }
	
pos30VdcSensorAvail OBJECT-TYPE
	SYNTAX  Unsigned32
	MAX-ACCESS  read-only
	STATUS current
	DESCRIPTION "Is device currently plugged in?"
	::= { pos30VdcSensorEntry  4 }
	
pos30VdcSensorVoltage OBJECT-TYPE
	SYNTAX  INTEGER(-10..100)
	MAX-ACCESS  read-only
	STATUS current
	DESCRIPTION "30Vdc Sensor value"
	::= { pos30VdcSensorEntry  5 }
	
ctrl3ChIECEntry OBJECT-TYPE
	SYNTAX  Ctrl3ChIECEntry
	MAX-ACCESS  not-accessible
	STATUS current
	DESCRIPTION 
		"Entry in the 3 phase outlet control table: each entry contains
an index (ctrl3ChIndex) and other outlet control monitoring details"
	INDEX { ctrl3ChIECIndex }
	::= { ctrl3ChIECTable 1 }

Ctrl3ChIECEntry ::= SEQUENCE {
	ctrl3ChIECIndex		INTEGER(1..1),
	ctrl3ChIECSerial		DisplayString,
	ctrl3ChIECName		DisplayString,
	ctrl3ChIECAvail		Unsigned32,
	ctrl3ChIECKWattHrsA		Unsigned32,
	ctrl3ChIECVoltsA		Unsigned32,
	ctrl3ChIECVoltPkA		Unsigned32,
	ctrl3ChIECAmpsA		Unsigned32,
	ctrl3ChIECAmpPkA		Unsigned32,
	ctrl3ChIECRealPowA		Unsigned32,
	ctrl3ChIECAppPowA		Unsigned32,
	ctrl3ChIECPwrFactA		INTEGER(0..100),
	ctrl3ChIECKWattHrsB		Unsigned32,
	ctrl3ChIECVoltsB		Unsigned32,
	ctrl3ChIECVoltPkB		Unsigned32,
	ctrl3ChIECAmpsB		Unsigned32,
	ctrl3ChIECAmpPkB		Unsigned32,
	ctrl3ChIECRealPowB		Unsigned32,
	ctrl3ChIECAppPowB		Unsigned32,
	ctrl3ChIECPwrFactB		INTEGER(0..100),
	ctrl3ChIECKWattHrsC		Unsigned32,
	ctrl3ChIECVoltsC		Unsigned32,
	ctrl3ChIECVoltPkC		Unsigned32,
	ctrl3ChIECAmpsC		Unsigned32,
	ctrl3ChIECAmpPkC		Unsigned32,
	ctrl3ChIECRealPowC		Unsigned32,
	ctrl3ChIECAppPowC		Unsigned32,
	ctrl3ChIECPwrFactC		INTEGER(0..100)
}

ctrl3ChIECIndex OBJECT-TYPE
	SYNTAX  INTEGER(1..1)
	MAX-ACCESS  not-accessible
	STATUS current
	DESCRIPTION "Table entry index value"
	::= { ctrl3ChIECEntry  1 }
	
ctrl3ChIECSerial OBJECT-TYPE
	SYNTAX  DisplayString
	MAX-ACCESS  read-only
	STATUS current
	DESCRIPTION "Serial Number"
	::= { ctrl3ChIECEntry  2 }
	
ctrl3ChIECName OBJECT-TYPE
	SYNTAX  DisplayString
	MAX-ACCESS  read-only
	STATUS current
	DESCRIPTION "Friendly Name"
	::= { ctrl3ChIECEntry  3 }
	
ctrl3ChIECAvail OBJECT-TYPE
	SYNTAX  Unsigned32
	MAX-ACCESS  read-only
	STATUS current
	DESCRIPTION "Is device currently plugged in?"
	::= { ctrl3ChIECEntry  4 }
	
ctrl3ChIECKWattHrsA OBJECT-TYPE
	SYNTAX  Unsigned32
	MAX-ACCESS  read-only
	STATUS current
	DESCRIPTION "KWatt-Hours A"
	::= { ctrl3ChIECEntry  5 }
	
ctrl3ChIECVoltsA OBJECT-TYPE
	SYNTAX  Unsigned32
	MAX-ACCESS  read-only
	STATUS current
	DESCRIPTION "Volts A"
	::= { ctrl3ChIECEntry  6 }
	
ctrl3ChIECVoltPkA OBJECT-TYPE
	SYNTAX  Unsigned32
	MAX-ACCESS  read-only
	STATUS current
	DESCRIPTION "Volts (Peak) A"
	::= { ctrl3ChIECEntry  7 }
	
ctrl3ChIECAmpsA OBJECT-TYPE
	SYNTAX  Unsigned32
	MAX-ACCESS  read-only
	STATUS current
	DESCRIPTION "Amps A"
	::= { ctrl3ChIECEntry  8 }
	
ctrl3ChIECAmpPkA OBJECT-TYPE
	SYNTAX  Unsigned32
	MAX-ACCESS  read-only
	STATUS current
	DESCRIPTION "Amps Peak A"
	::= { ctrl3ChIECEntry  9 }
	
ctrl3ChIECRealPowA OBJECT-TYPE
	SYNTAX  Unsigned32
	MAX-ACCESS  read-only
	STATUS current
	DESCRIPTION "Real Power A"
	::= { ctrl3ChIECEntry  10 }
	
ctrl3ChIECAppPowA OBJECT-TYPE
	SYNTAX  Unsigned32
	MAX-ACCESS  read-only
	STATUS current
	DESCRIPTION "Apparent Power A"
	::= { ctrl3ChIECEntry  11 }
	
ctrl3ChIECPwrFactA OBJECT-TYPE
	SYNTAX  INTEGER(0..100)
	MAX-ACCESS  read-only
	STATUS current
	DESCRIPTION "Power Factor A"
	::= { ctrl3ChIECEntry  12 }
	
ctrl3ChIECKWattHrsB OBJECT-TYPE
	SYNTAX  Unsigned32
	MAX-ACCESS  read-only
	STATUS current
	DESCRIPTION "KWatt-Hours B"
	::= { ctrl3ChIECEntry  13 }
	
ctrl3ChIECVoltsB OBJECT-TYPE
	SYNTAX  Unsigned32
	MAX-ACCESS  read-only
	STATUS current
	DESCRIPTION "Volts B"
	::= { ctrl3ChIECEntry  14 }
	
ctrl3ChIECVoltPkB OBJECT-TYPE
	SYNTAX  Unsigned32
	MAX-ACCESS  read-only
	STATUS current
	DESCRIPTION "Volts (Peak) B"
	::= { ctrl3ChIECEntry  15 }
	
ctrl3ChIECAmpsB OBJECT-TYPE
	SYNTAX  Unsigned32
	MAX-ACCESS  read-only
	STATUS current
	DESCRIPTION "Amps B"
	::= { ctrl3ChIECEntry  16 }
	
ctrl3ChIECAmpPkB OBJECT-TYPE
	SYNTAX  Unsigned32
	MAX-ACCESS  read-only
	STATUS current
	DESCRIPTION "Amps Peak B"
	::= { ctrl3ChIECEntry  17 }
	
ctrl3ChIECRealPowB OBJECT-TYPE
	SYNTAX  Unsigned32
	MAX-ACCESS  read-only
	STATUS current
	DESCRIPTION "Real Power B"
	::= { ctrl3ChIECEntry  18 }
	
ctrl3ChIECAppPowB OBJECT-TYPE
	SYNTAX  Unsigned32
	MAX-ACCESS  read-only
	STATUS current
	DESCRIPTION "Apparent Power B"
	::= { ctrl3ChIECEntry  19 }
	
ctrl3ChIECPwrFactB OBJECT-TYPE
	SYNTAX  INTEGER(0..100)
	MAX-ACCESS  read-only
	STATUS current
	DESCRIPTION "Power Factor B"
	::= { ctrl3ChIECEntry  20 }
	
ctrl3ChIECKWattHrsC OBJECT-TYPE
	SYNTAX  Unsigned32
	MAX-ACCESS  read-only
	STATUS current
	DESCRIPTION "KWatt-Hours C"
	::= { ctrl3ChIECEntry  21 }
	
ctrl3ChIECVoltsC OBJECT-TYPE
	SYNTAX  Unsigned32
	MAX-ACCESS  read-only
	STATUS current
	DESCRIPTION "Volts C"
	::= { ctrl3ChIECEntry  22 }
	
ctrl3ChIECVoltPkC OBJECT-TYPE
	SYNTAX  Unsigned32
	MAX-ACCESS  read-only
	STATUS current
	DESCRIPTION "Volts (Peak) C"
	::= { ctrl3ChIECEntry  23 }
	
ctrl3ChIECAmpsC OBJECT-TYPE
	SYNTAX  Unsigned32
	MAX-ACCESS  read-only
	STATUS current
	DESCRIPTION "Amps C"
	::= { ctrl3ChIECEntry  24 }
	
ctrl3ChIECAmpPkC OBJECT-TYPE
	SYNTAX  Unsigned32
	MAX-ACCESS  read-only
	STATUS current
	DESCRIPTION "Amps Peak C"
	::= { ctrl3ChIECEntry  25 }
	
ctrl3ChIECRealPowC OBJECT-TYPE
	SYNTAX  Unsigned32
	MAX-ACCESS  read-only
	STATUS current
	DESCRIPTION "Real Power C"
	::= { ctrl3ChIECEntry  26 }
	
ctrl3ChIECAppPowC OBJECT-TYPE
	SYNTAX  Unsigned32
	MAX-ACCESS  read-only
	STATUS current
	DESCRIPTION "Apparent Power C"
	::= { ctrl3ChIECEntry  27 }
	
ctrl3ChIECPwrFactC OBJECT-TYPE
	SYNTAX  INTEGER(0..100)
	MAX-ACCESS  read-only
	STATUS current
	DESCRIPTION "Power Factor C"
	::= { ctrl3ChIECEntry  28 }
	
cmTestTRAP TRAP-TYPE
	ENTERPRISE itwatchdogs
	DESCRIPTION "Test SNMP Trap"
	::= 10101
	
cmClimateTempCTRAP TRAP-TYPE
ENTERPRISE itwatchdogs
VARIABLES { climateTempC, climateName, productFriendlyName, alarmTripType }
DESCRIPTION "Climate Temperature Sensor Trap"
::= 10205

cmClimateTempFTRAP TRAP-TYPE
ENTERPRISE itwatchdogs
VARIABLES { climateTempF, climateName, productFriendlyName, alarmTripType }
DESCRIPTION "Climate Temperature Sensor Trap"
::= 10206

cmClimateHumidityTRAP TRAP-TYPE
ENTERPRISE itwatchdogs
VARIABLES { climateHumidity, climateName, productFriendlyName, alarmTripType }
DESCRIPTION "Climate Humidity Sensor Trap"
::= 10207

cmClimateLightTRAP TRAP-TYPE
ENTERPRISE itwatchdogs
VARIABLES { climateLight, climateName, productFriendlyName, alarmTripType }
DESCRIPTION "Climate Light Sensor Trap"
::= 10208

cmClimateAirflowTRAP TRAP-TYPE
ENTERPRISE itwatchdogs
VARIABLES { climateAirflow, climateName, productFriendlyName, alarmTripType }
DESCRIPTION "Climate Air Flow Sensor Trap"
::= 10209

cmClimateSoundTRAP TRAP-TYPE
ENTERPRISE itwatchdogs
VARIABLES { climateSound, climateName, productFriendlyName, alarmTripType }
DESCRIPTION "Climate Sound Sensor Trap"
::= 10210

cmClimateIO1TRAP TRAP-TYPE
ENTERPRISE itwatchdogs
VARIABLES { climateIO1, climateName, productFriendlyName, alarmTripType }
DESCRIPTION "Climate IO1 Sensor Trap"
::= 10211

cmClimateIO2TRAP TRAP-TYPE
ENTERPRISE itwatchdogs
VARIABLES { climateIO2, climateName, productFriendlyName, alarmTripType }
DESCRIPTION "Climate IO2 Sensor Trap"
::= 10212

cmClimateIO3TRAP TRAP-TYPE
ENTERPRISE itwatchdogs
VARIABLES { climateIO3, climateName, productFriendlyName, alarmTripType }
DESCRIPTION "Climate IO3 Sensor Trap"
::= 10213

cmPowMonKWattHrsTRAP TRAP-TYPE
ENTERPRISE itwatchdogs
VARIABLES { powMonKWattHrs, powMonName, productFriendlyName, alarmTripType }
DESCRIPTION "Kilo Watt Hours Trap"
::= 10305

cmPowMonVoltsTRAP TRAP-TYPE
ENTERPRISE itwatchdogs
VARIABLES { powMonVolts, powMonName, productFriendlyName, alarmTripType }
DESCRIPTION "Volts Trap"
::= 10306

cmPowMonVoltMaxTRAP TRAP-TYPE
ENTERPRISE itwatchdogs
VARIABLES { powMonVoltMax, powMonName, productFriendlyName, alarmTripType }
DESCRIPTION "Volts Max Trap"
::= 10307

cmPowMonVoltMinTRAP TRAP-TYPE
ENTERPRISE itwatchdogs
VARIABLES { powMonVoltMin, powMonName, productFriendlyName, alarmTripType }
DESCRIPTION "Volts Min Trap"
::= 10308

cmPowMonVoltPkTRAP TRAP-TYPE
ENTERPRISE itwatchdogs
VARIABLES { powMonVoltPk, powMonName, productFriendlyName, alarmTripType }
DESCRIPTION "Volt Peak Trap"
::= 10309

cmPowMonAmpsX10TRAP TRAP-TYPE
ENTERPRISE itwatchdogs
VARIABLES { powMonAmpsX10, powMonName, productFriendlyName, alarmTripType }
DESCRIPTION "Amps x 10 Trap"
::= 10310

cmPowMonRealPowTRAP TRAP-TYPE
ENTERPRISE itwatchdogs
VARIABLES { powMonRealPow, powMonName, productFriendlyName, alarmTripType }
DESCRIPTION "Real Power Trap"
::= 10311

cmPowMonAppPowTRAP TRAP-TYPE
ENTERPRISE itwatchdogs
VARIABLES { powMonAppPow, powMonName, productFriendlyName, alarmTripType }
DESCRIPTION "Apparent Power Trap"
::= 10312

cmPowMonPwrFactTRAP TRAP-TYPE
ENTERPRISE itwatchdogs
VARIABLES { powMonPwrFact, powMonName, productFriendlyName, alarmTripType }
DESCRIPTION "Power Factor Trap"
::= 10313

cmPowMonOutlet1TRAP TRAP-TYPE
ENTERPRISE itwatchdogs
VARIABLES { powMonOutlet1, powMonName, productFriendlyName, alarmTripType }
DESCRIPTION "Outlet 1 Trap"
::= 10314

cmPowMonOutlet2TRAP TRAP-TYPE
ENTERPRISE itwatchdogs
VARIABLES { powMonOutlet2, powMonName, productFriendlyName, alarmTripType }
DESCRIPTION "Outlet 2 Trap"
::= 10315

cmTempSensorTempCTRAP TRAP-TYPE
ENTERPRISE itwatchdogs
VARIABLES { tempSensorTempC, tempSensorName, productFriendlyName, alarmTripType }
DESCRIPTION "Remote Temp Sensor - Temperature Trap"
::= 10405

cmTempSensorTempFTRAP TRAP-TYPE
ENTERPRISE itwatchdogs
VARIABLES { tempSensorTempF, tempSensorName, productFriendlyName, alarmTripType }
DESCRIPTION "Remote Temp Sensor - Temperature Trap"
::= 10406

cmAirFlowSensorTempCTRAP TRAP-TYPE
ENTERPRISE itwatchdogs
VARIABLES { airFlowSensorTempC, airFlowSensorName, productFriendlyName, alarmTripType }
DESCRIPTION "Remote Air Flow Sensor - Temperature Trap"
::= 10505

cmAirFlowSensorTempFTRAP TRAP-TYPE
ENTERPRISE itwatchdogs
VARIABLES { airFlowSensorTempF, airFlowSensorName, productFriendlyName, alarmTripType }
DESCRIPTION "Remote Air Flow Sensor - Temperature Trap"
::= 10506

cmAirFlowSensorFlowTRAP TRAP-TYPE
ENTERPRISE itwatchdogs
VARIABLES { airFlowSensorFlow, airFlowSensorName, productFriendlyName, alarmTripType }
DESCRIPTION "Remote Air Flow Sensor - Air Flow Trap"
::= 10507

cmAirFlowSensorHumidityTRAP TRAP-TYPE
ENTERPRISE itwatchdogs
VARIABLES { airFlowSensorHumidity, airFlowSensorName, productFriendlyName, alarmTripType }
DESCRIPTION "Remote Air Flow Sensor - Humidity"
::= 10508

cmPowerVoltsTRAP TRAP-TYPE
ENTERPRISE itwatchdogs
VARIABLES { powerVolts, powerName, productFriendlyName, alarmTripType }
DESCRIPTION "Power-Only Volts Trap"
::= 10605

cmPowerAmpsTRAP TRAP-TYPE
ENTERPRISE itwatchdogs
VARIABLES { powerAmps, powerName, productFriendlyName, alarmTripType }
DESCRIPTION "Power-Only Amps Trap"
::= 10606

cmPowerRealPowTRAP TRAP-TYPE
ENTERPRISE itwatchdogs
VARIABLES { powerRealPow, powerName, productFriendlyName, alarmTripType }
DESCRIPTION "Power-Only Watts Trap"
::= 10607

cmPowerAppPowTRAP TRAP-TYPE
ENTERPRISE itwatchdogs
VARIABLES { powerAppPow, powerName, productFriendlyName, alarmTripType }
DESCRIPTION "Power-Only Volt Amps Trap"
::= 10608

cmPowerPwrFactorTRAP TRAP-TYPE
ENTERPRISE itwatchdogs
VARIABLES { powerPwrFactor, powerName, productFriendlyName, alarmTripType }
DESCRIPTION "Power-Only Power Factor Trap"
::= 10609

cmDoorSensorStatusTRAP TRAP-TYPE
ENTERPRISE itwatchdogs
VARIABLES { doorSensorStatus, doorSensorName, productFriendlyName, alarmTripType }
DESCRIPTION "Door sensor Trap"
::= 10705

cmWaterSensorDampnessTRAP TRAP-TYPE
ENTERPRISE itwatchdogs
VARIABLES { waterSensorDampness, waterSensorName, productFriendlyName, alarmTripType }
DESCRIPTION "Water sensor Trap"
::= 10805

cmCurrentMonitorAmpsTRAP TRAP-TYPE
ENTERPRISE itwatchdogs
VARIABLES { currentMonitorAmps, currentMonitorName, productFriendlyName, alarmTripType }
DESCRIPTION "Current Monitor Amps Trap"
::= 10905

cmMillivoltMonitorMVTRAP TRAP-TYPE
ENTERPRISE itwatchdogs
VARIABLES { millivoltMonitorMV, millivoltMonitorName, productFriendlyName, alarmTripType }
DESCRIPTION "Millivolt Monitor Trap"
::= 11005

cmPow3ChKWattHrsATRAP TRAP-TYPE
ENTERPRISE itwatchdogs
VARIABLES { pow3ChKWattHrsA, pow3ChName, productFriendlyName, alarmTripType }
DESCRIPTION "Kilo Watt Hours A Trap"
::= 11105

cmPow3ChVoltsATRAP TRAP-TYPE
ENTERPRISE itwatchdogs
VARIABLES { pow3ChVoltsA, pow3ChName, productFriendlyName, alarmTripType }
DESCRIPTION "Volts A Trap"
::= 11106

cmPow3ChVoltMaxATRAP TRAP-TYPE
ENTERPRISE itwatchdogs
VARIABLES { pow3ChVoltMaxA, pow3ChName, productFriendlyName, alarmTripType }
DESCRIPTION "Volts Max A Trap"
::= 11107

cmPow3ChVoltMinATRAP TRAP-TYPE
ENTERPRISE itwatchdogs
VARIABLES { pow3ChVoltMinA, pow3ChName, productFriendlyName, alarmTripType }
DESCRIPTION "Volts Min A Trap"
::= 11108

cmPow3ChVoltPkATRAP TRAP-TYPE
ENTERPRISE itwatchdogs
VARIABLES { pow3ChVoltPkA, pow3ChName, productFriendlyName, alarmTripType }
DESCRIPTION "Volt Peak A Trap"
::= 11109

cmPow3ChAmpsX10ATRAP TRAP-TYPE
ENTERPRISE itwatchdogs
VARIABLES { pow3ChAmpsX10A, pow3ChName, productFriendlyName, alarmTripType }
DESCRIPTION "Amps x 10 A Trap"
::= 11110

cmPow3ChRealPowATRAP TRAP-TYPE
ENTERPRISE itwatchdogs
VARIABLES { pow3ChRealPowA, pow3ChName, productFriendlyName, alarmTripType }
DESCRIPTION "Real Power A Trap"
::= 11111

cmPow3ChAppPowATRAP TRAP-TYPE
ENTERPRISE itwatchdogs
VARIABLES { pow3ChAppPowA, pow3ChName, productFriendlyName, alarmTripType }
DESCRIPTION "Apparent Power A Trap"
::= 11112

cmPow3ChPwrFactATRAP TRAP-TYPE
ENTERPRISE itwatchdogs
VARIABLES { pow3ChPwrFactA, pow3ChName, productFriendlyName, alarmTripType }
DESCRIPTION "Power Factor A Trap"
::= 11113

cmPow3ChKWattHrsBTRAP TRAP-TYPE
ENTERPRISE itwatchdogs
VARIABLES { pow3ChKWattHrsB, pow3ChName, productFriendlyName, alarmTripType }
DESCRIPTION "Kilo Watt Hours B Trap"
::= 11114

cmPow3ChVoltsBTRAP TRAP-TYPE
ENTERPRISE itwatchdogs
VARIABLES { pow3ChVoltsB, pow3ChName, productFriendlyName, alarmTripType }
DESCRIPTION "Volts B Trap"
::= 11115

cmPow3ChVoltMaxBTRAP TRAP-TYPE
ENTERPRISE itwatchdogs
VARIABLES { pow3ChVoltMaxB, pow3ChName, productFriendlyName, alarmTripType }
DESCRIPTION "Volts Max B Trap"
::= 11116

cmPow3ChVoltMinBTRAP TRAP-TYPE
ENTERPRISE itwatchdogs
VARIABLES { pow3ChVoltMinB, pow3ChName, productFriendlyName, alarmTripType }
DESCRIPTION "Volts Min B Trap"
::= 11117

cmPow3ChVoltPkBTRAP TRAP-TYPE
ENTERPRISE itwatchdogs
VARIABLES { pow3ChVoltPkB, pow3ChName, productFriendlyName, alarmTripType }
DESCRIPTION "Volt Peak B Trap"
::= 11118

cmPow3ChAmpsX10BTRAP TRAP-TYPE
ENTERPRISE itwatchdogs
VARIABLES { pow3ChAmpsX10B, pow3ChName, productFriendlyName, alarmTripType }
DESCRIPTION "Amps x 10 B Trap"
::= 11119

cmPow3ChRealPowBTRAP TRAP-TYPE
ENTERPRISE itwatchdogs
VARIABLES { pow3ChRealPowB, pow3ChName, productFriendlyName, alarmTripType }
DESCRIPTION "Real Power B Trap"
::= 11120

cmPow3ChAppPowBTRAP TRAP-TYPE
ENTERPRISE itwatchdogs
VARIABLES { pow3ChAppPowB, pow3ChName, productFriendlyName, alarmTripType }
DESCRIPTION "Apparent Power B Trap"
::= 11121

cmPow3ChPwrFactBTRAP TRAP-TYPE
ENTERPRISE itwatchdogs
VARIABLES { pow3ChPwrFactB, pow3ChName, productFriendlyName, alarmTripType }
DESCRIPTION "Power Factor B Trap"
::= 11122

cmPow3ChKWattHrsCTRAP TRAP-TYPE
ENTERPRISE itwatchdogs
VARIABLES { pow3ChKWattHrsC, pow3ChName, productFriendlyName, alarmTripType }
DESCRIPTION "Kilo Watt Hours C Trap"
::= 11123

cmPow3ChVoltsCTRAP TRAP-TYPE
ENTERPRISE itwatchdogs
VARIABLES { pow3ChVoltsC, pow3ChName, productFriendlyName, alarmTripType }
DESCRIPTION "Volts C Trap"
::= 11124

cmPow3ChVoltMaxCTRAP TRAP-TYPE
ENTERPRISE itwatchdogs
VARIABLES { pow3ChVoltMaxC, pow3ChName, productFriendlyName, alarmTripType }
DESCRIPTION "Volts Max C Trap"
::= 11125

cmPow3ChVoltMinCTRAP TRAP-TYPE
ENTERPRISE itwatchdogs
VARIABLES { pow3ChVoltMinC, pow3ChName, productFriendlyName, alarmTripType }
DESCRIPTION "Volts Min C Trap"
::= 11126

cmPow3ChVoltPkCTRAP TRAP-TYPE
ENTERPRISE itwatchdogs
VARIABLES { pow3ChVoltPkC, pow3ChName, productFriendlyName, alarmTripType }
DESCRIPTION "Volt Peak C Trap"
::= 11127

cmPow3ChAmpsX10CTRAP TRAP-TYPE
ENTERPRISE itwatchdogs
VARIABLES { pow3ChAmpsX10C, pow3ChName, productFriendlyName, alarmTripType }
DESCRIPTION "Amps x 10 C Trap"
::= 11128

cmPow3ChRealPowCTRAP TRAP-TYPE
ENTERPRISE itwatchdogs
VARIABLES { pow3ChRealPowC, pow3ChName, productFriendlyName, alarmTripType }
DESCRIPTION "Real Power C Trap"
::= 11129

cmPow3ChAppPowCTRAP TRAP-TYPE
ENTERPRISE itwatchdogs
VARIABLES { pow3ChAppPowC, pow3ChName, productFriendlyName, alarmTripType }
DESCRIPTION "Apparent Power C Trap"
::= 11130

cmPow3ChPwrFactCTRAP TRAP-TYPE
ENTERPRISE itwatchdogs
VARIABLES { pow3ChPwrFactC, pow3ChName, productFriendlyName, alarmTripType }
DESCRIPTION "Power Factor C Trap"
::= 11131

cmOutlet1StatusTRAP TRAP-TYPE
ENTERPRISE itwatchdogs
VARIABLES { outlet1Status, outletName, productFriendlyName, alarmTripType }
DESCRIPTION "Outlet 1 Status Trap"
::= 11205

cmOutlet2StatusTRAP TRAP-TYPE
ENTERPRISE itwatchdogs
VARIABLES { outlet2Status, outletName, productFriendlyName, alarmTripType }
DESCRIPTION "Outlet 2 Status Trap"
::= 11206

cmVsfcSetPointCTRAP TRAP-TYPE
ENTERPRISE itwatchdogs
VARIABLES { vsfcSetPointC, vsfcName, productFriendlyName, alarmTripType }
DESCRIPTION "Vsfc Temp Set Point Sensor Trap"
::= 11305

cmVsfcSetPointFTRAP TRAP-TYPE
ENTERPRISE itwatchdogs
VARIABLES { vsfcSetPointF, vsfcName, productFriendlyName, alarmTripType }
DESCRIPTION "Vsfc Temp Set Point Sensor Trap"
::= 11306

cmVsfcIntTempCTRAP TRAP-TYPE
ENTERPRISE itwatchdogs
VARIABLES { vsfcIntTempC, vsfcName, productFriendlyName, alarmTripType }
DESCRIPTION "Vsfc Internal Temp Sensor Trap"
::= 11307

cmVsfcIntTempFTRAP TRAP-TYPE
ENTERPRISE itwatchdogs
VARIABLES { vsfcIntTempF, vsfcName, productFriendlyName, alarmTripType }
DESCRIPTION "Vsfc Internal Temp Sensor Trap"
::= 11308

cmVsfcExt1TempCTRAP TRAP-TYPE
ENTERPRISE itwatchdogs
VARIABLES { vsfcExt1TempC, vsfcName, productFriendlyName, alarmTripType }
DESCRIPTION "Vsfc External Temp 1 Sensor Trap"
::= 11309

cmVsfcExt1TempFTRAP TRAP-TYPE
ENTERPRISE itwatchdogs
VARIABLES { vsfcExt1TempF, vsfcName, productFriendlyName, alarmTripType }
DESCRIPTION "Vsfc External Temp 1 Sensor Trap"
::= 11310

cmVsfcExt2TempCTRAP TRAP-TYPE
ENTERPRISE itwatchdogs
VARIABLES { vsfcExt2TempC, vsfcName, productFriendlyName, alarmTripType }
DESCRIPTION "Vsfc External Temp 2 Sensor Trap"
::= 11311

cmVsfcExt2TempFTRAP TRAP-TYPE
ENTERPRISE itwatchdogs
VARIABLES { vsfcExt2TempF, vsfcName, productFriendlyName, alarmTripType }
DESCRIPTION "Vsfc External Temp 2 Sensor Trap"
::= 11312

cmVsfcExt3TempCTRAP TRAP-TYPE
ENTERPRISE itwatchdogs
VARIABLES { vsfcExt3TempC, vsfcName, productFriendlyName, alarmTripType }
DESCRIPTION "Vsfc External Temp 3 Sensor Trap"
::= 11313

cmVsfcExt3TempFTRAP TRAP-TYPE
ENTERPRISE itwatchdogs
VARIABLES { vsfcExt3TempF, vsfcName, productFriendlyName, alarmTripType }
DESCRIPTION "Vsfc External Temp 3 Sensor Trap"
::= 11314

cmVsfcExt4TempCTRAP TRAP-TYPE
ENTERPRISE itwatchdogs
VARIABLES { vsfcExt4TempC, vsfcName, productFriendlyName, alarmTripType }
DESCRIPTION "Vsfc External Temp 4 Sensor Trap"
::= 11315

cmVsfcExt4TempFTRAP TRAP-TYPE
ENTERPRISE itwatchdogs
VARIABLES { vsfcExt4TempF, vsfcName, productFriendlyName, alarmTripType }
DESCRIPTION "Vsfc External Temp 4 Sensor Trap"
::= 11316

cmVsfcFanSpeedTRAP TRAP-TYPE
ENTERPRISE itwatchdogs
VARIABLES { vsfcFanSpeed, vsfcName, productFriendlyName, alarmTripType }
DESCRIPTION "Vsfc Fan Speed Sensor Trap"
::= 11317

cmCtrl3ChVoltsATRAP TRAP-TYPE
ENTERPRISE itwatchdogs
VARIABLES { ctrl3ChVoltsA, ctrl3ChName, productFriendlyName, alarmTripType }
DESCRIPTION "Volts A Trap"
::= 11405

cmCtrl3ChVoltPkATRAP TRAP-TYPE
ENTERPRISE itwatchdogs
VARIABLES { ctrl3ChVoltPkA, ctrl3ChName, productFriendlyName, alarmTripType }
DESCRIPTION "Volt Peak A Trap"
::= 11406

cmCtrl3ChAmpsATRAP TRAP-TYPE
ENTERPRISE itwatchdogs
VARIABLES { ctrl3ChAmpsA, ctrl3ChName, productFriendlyName, alarmTripType }
DESCRIPTION "Amps A Trap"
::= 11407

cmCtrl3ChAmpPkATRAP TRAP-TYPE
ENTERPRISE itwatchdogs
VARIABLES { ctrl3ChAmpPkA, ctrl3ChName, productFriendlyName, alarmTripType }
DESCRIPTION "Amps Peak A Trap"
::= 11408

cmCtrl3ChRealPowATRAP TRAP-TYPE
ENTERPRISE itwatchdogs
VARIABLES { ctrl3ChRealPowA, ctrl3ChName, productFriendlyName, alarmTripType }
DESCRIPTION "Real Power A Trap"
::= 11409

cmCtrl3ChAppPowATRAP TRAP-TYPE
ENTERPRISE itwatchdogs
VARIABLES { ctrl3ChAppPowA, ctrl3ChName, productFriendlyName, alarmTripType }
DESCRIPTION "Apparent Power A Trap"
::= 11410

cmCtrl3ChPwrFactATRAP TRAP-TYPE
ENTERPRISE itwatchdogs
VARIABLES { ctrl3ChPwrFactA, ctrl3ChName, productFriendlyName, alarmTripType }
DESCRIPTION "Power Factor A Trap"
::= 11411

cmCtrl3ChVoltsBTRAP TRAP-TYPE
ENTERPRISE itwatchdogs
VARIABLES { ctrl3ChVoltsB, ctrl3ChName, productFriendlyName, alarmTripType }
DESCRIPTION "Volts B Trap"
::= 11412

cmCtrl3ChVoltPkBTRAP TRAP-TYPE
ENTERPRISE itwatchdogs
VARIABLES { ctrl3ChVoltPkB, ctrl3ChName, productFriendlyName, alarmTripType }
DESCRIPTION "Volt Peak B Trap"
::= 11413

cmCtrl3ChAmpsBTRAP TRAP-TYPE
ENTERPRISE itwatchdogs
VARIABLES { ctrl3ChAmpsB, ctrl3ChName, productFriendlyName, alarmTripType }
DESCRIPTION "Amps B Trap"
::= 11414

cmCtrl3ChAmpPkBTRAP TRAP-TYPE
ENTERPRISE itwatchdogs
VARIABLES { ctrl3ChAmpPkB, ctrl3ChName, productFriendlyName, alarmTripType }
DESCRIPTION "Amps Peak B Trap"
::= 11415

cmCtrl3ChRealPowBTRAP TRAP-TYPE
ENTERPRISE itwatchdogs
VARIABLES { ctrl3ChRealPowB, ctrl3ChName, productFriendlyName, alarmTripType }
DESCRIPTION "Real Power B Trap"
::= 11416

cmCtrl3ChAppPowBTRAP TRAP-TYPE
ENTERPRISE itwatchdogs
VARIABLES { ctrl3ChAppPowB, ctrl3ChName, productFriendlyName, alarmTripType }
DESCRIPTION "Apparent Power B Trap"
::= 11417

cmCtrl3ChPwrFactBTRAP TRAP-TYPE
ENTERPRISE itwatchdogs
VARIABLES { ctrl3ChPwrFactB, ctrl3ChName, productFriendlyName, alarmTripType }
DESCRIPTION "Power Factor B Trap"
::= 11418

cmCtrl3ChVoltsCTRAP TRAP-TYPE
ENTERPRISE itwatchdogs
VARIABLES { ctrl3ChVoltsC, ctrl3ChName, productFriendlyName, alarmTripType }
DESCRIPTION "Volts C Trap"
::= 11419

cmCtrl3ChVoltPkCTRAP TRAP-TYPE
ENTERPRISE itwatchdogs
VARIABLES { ctrl3ChVoltPkC, ctrl3ChName, productFriendlyName, alarmTripType }
DESCRIPTION "Volt Peak C Trap"
::= 11420

cmCtrl3ChAmpsCTRAP TRAP-TYPE
ENTERPRISE itwatchdogs
VARIABLES { ctrl3ChAmpsC, ctrl3ChName, productFriendlyName, alarmTripType }
DESCRIPTION "Amps C Trap"
::= 11421

cmCtrl3ChAmpPkCTRAP TRAP-TYPE
ENTERPRISE itwatchdogs
VARIABLES { ctrl3ChAmpPkC, ctrl3ChName, productFriendlyName, alarmTripType }
DESCRIPTION "Amps Peak C Trap"
::= 11422

cmCtrl3ChRealPowCTRAP TRAP-TYPE
ENTERPRISE itwatchdogs
VARIABLES { ctrl3ChRealPowC, ctrl3ChName, productFriendlyName, alarmTripType }
DESCRIPTION "Real Power C Trap"
::= 11423

cmCtrl3ChAppPowCTRAP TRAP-TYPE
ENTERPRISE itwatchdogs
VARIABLES { ctrl3ChAppPowC, ctrl3ChName, productFriendlyName, alarmTripType }
DESCRIPTION "Apparent Power C Trap"
::= 11424

cmCtrl3ChPwrFactCTRAP TRAP-TYPE
ENTERPRISE itwatchdogs
VARIABLES { ctrl3ChPwrFactC, ctrl3ChName, productFriendlyName, alarmTripType }
DESCRIPTION "Power Factor C Trap"
::= 11425

cmCtrlGrpAmpsATRAP TRAP-TYPE
ENTERPRISE itwatchdogs
VARIABLES { ctrlGrpAmpsA, ctrlGrpAmpsName, productFriendlyName, alarmTripType }
DESCRIPTION "Group A Amps Trap"
::= 11505

cmCtrlGrpAmpsBTRAP TRAP-TYPE
ENTERPRISE itwatchdogs
VARIABLES { ctrlGrpAmpsB, ctrlGrpAmpsName, productFriendlyName, alarmTripType }
DESCRIPTION "Group B Amps Trap"
::= 11506

cmCtrlGrpAmpsCTRAP TRAP-TYPE
ENTERPRISE itwatchdogs
VARIABLES { ctrlGrpAmpsC, ctrlGrpAmpsName, productFriendlyName, alarmTripType }
DESCRIPTION "Group C Amps Trap"
::= 11507

cmCtrlGrpAmpsDTRAP TRAP-TYPE
ENTERPRISE itwatchdogs
VARIABLES { ctrlGrpAmpsD, ctrlGrpAmpsName, productFriendlyName, alarmTripType }
DESCRIPTION "Group D Amps Trap"
::= 11508

cmCtrlGrpAmpsETRAP TRAP-TYPE
ENTERPRISE itwatchdogs
VARIABLES { ctrlGrpAmpsE, ctrlGrpAmpsName, productFriendlyName, alarmTripType }
DESCRIPTION "Group E Amps Trap"
::= 11509

cmCtrlGrpAmpsFTRAP TRAP-TYPE
ENTERPRISE itwatchdogs
VARIABLES { ctrlGrpAmpsF, ctrlGrpAmpsName, productFriendlyName, alarmTripType }
DESCRIPTION "Group F Amps Trap"
::= 11510

cmDewPointSensorDewPointCTRAP TRAP-TYPE
ENTERPRISE itwatchdogs
VARIABLES { dewPointSensorDewPointC, dewPointSensorName, productFriendlyName, alarmTripType }
DESCRIPTION "Remote Dew Point Sensor - Dew Point Trap"
::= 11705

cmDewPointSensorDewPointFTRAP TRAP-TYPE
ENTERPRISE itwatchdogs
VARIABLES { dewPointSensorDewPointF, dewPointSensorName, productFriendlyName, alarmTripType }
DESCRIPTION "Remote Dew Point Sensor - Dew Point Trap"
::= 11706

cmDewPointSensorTempCTRAP TRAP-TYPE
ENTERPRISE itwatchdogs
VARIABLES { dewPointSensorTempC, dewPointSensorName, productFriendlyName, alarmTripType }
DESCRIPTION "Remote Dew Point Sensor - Temperature Trap"
::= 11707

cmDewPointSensorTempFTRAP TRAP-TYPE
ENTERPRISE itwatchdogs
VARIABLES { dewPointSensorTempF, dewPointSensorName, productFriendlyName, alarmTripType }
DESCRIPTION "Remote Dew Point Sensor - Temperature Trap"
::= 11708

cmDewPointSensorHumidityTRAP TRAP-TYPE
ENTERPRISE itwatchdogs
VARIABLES { dewPointSensorHumidity, dewPointSensorName, productFriendlyName, alarmTripType }
DESCRIPTION "Remote Dew Point Sensor - Humidity"
::= 11709

cmDigitalSensorDigitalTRAP TRAP-TYPE
ENTERPRISE itwatchdogs
VARIABLES { digitalSensorDigital, digitalSensorName, productFriendlyName, alarmTripType }
DESCRIPTION "Digital sensor Trap"
::= 11805

cmDstsVoltsATRAP TRAP-TYPE
ENTERPRISE itwatchdogs
VARIABLES { dstsVoltsA, dstsName, productFriendlyName, alarmTripType }
DESCRIPTION "RMS Voltage of Side A Set Point Sensor Trap"
::= 11905

cmDstsAmpsATRAP TRAP-TYPE
ENTERPRISE itwatchdogs
VARIABLES { dstsAmpsA, dstsName, productFriendlyName, alarmTripType }
DESCRIPTION "RMS Current of Side A Set Point Sensor Trap"
::= 11906

cmDstsVoltsBTRAP TRAP-TYPE
ENTERPRISE itwatchdogs
VARIABLES { dstsVoltsB, dstsName, productFriendlyName, alarmTripType }
DESCRIPTION "RMS Voltage of Side B Set Point Sensor Trap"
::= 11907

cmDstsAmpsBTRAP TRAP-TYPE
ENTERPRISE itwatchdogs
VARIABLES { dstsAmpsB, dstsName, productFriendlyName, alarmTripType }
DESCRIPTION "RMS Current of Side B Set Point Sensor Trap"
::= 11908

cmDstsSourceAActiveTRAP TRAP-TYPE
ENTERPRISE itwatchdogs
VARIABLES { dstsSourceAActive, dstsName, productFriendlyName, alarmTripType }
DESCRIPTION "Source A Active Set Point Sensor Trap"
::= 11909

cmDstsSourceBActiveTRAP TRAP-TYPE
ENTERPRISE itwatchdogs
VARIABLES { dstsSourceBActive, dstsName, productFriendlyName, alarmTripType }
DESCRIPTION "Source B Active Set Point Sensor Trap"
::= 11910

cmDstsPowerStatusATRAP TRAP-TYPE
ENTERPRISE itwatchdogs
VARIABLES { dstsPowerStatusA, dstsName, productFriendlyName, alarmTripType }
DESCRIPTION "Source A Power Qualilty Active Set Point Sensor Trap"
::= 11911

cmDstsPowerStatusBTRAP TRAP-TYPE
ENTERPRISE itwatchdogs
VARIABLES { dstsPowerStatusB, dstsName, productFriendlyName, alarmTripType }
DESCRIPTION "Source B Power Qualilty Active Set Point Sensor Trap"
::= 11912

cmDstsSourceATempCTRAP TRAP-TYPE
ENTERPRISE itwatchdogs
VARIABLES { dstsSourceATempC, dstsName, productFriendlyName, alarmTripType }
DESCRIPTION "Source A Temp Sensor Trap"
::= 11913

cmDstsSourceBTempCTRAP TRAP-TYPE
ENTERPRISE itwatchdogs
VARIABLES { dstsSourceBTempC, dstsName, productFriendlyName, alarmTripType }
DESCRIPTION "Source B Temp Sensor Trap"
::= 11914

cmCpmSensorStatusTRAP TRAP-TYPE
ENTERPRISE itwatchdogs
VARIABLES { cpmSensorStatus, cpmSensorName, productFriendlyName, alarmTripType }
DESCRIPTION "City Power sensor Trap"
::= 12005

cmSmokeAlarmStatusTRAP TRAP-TYPE
ENTERPRISE itwatchdogs
VARIABLES { smokeAlarmStatus, smokeAlarmName, productFriendlyName, alarmTripType }
DESCRIPTION "Smoke alarm Trap"
::= 12105

cmNeg48VdcSensorVoltageTRAP TRAP-TYPE
ENTERPRISE itwatchdogs
VARIABLES { neg48VdcSensorVoltage, neg48VdcSensorName, productFriendlyName, alarmTripType }
DESCRIPTION "-48Vdc Sensor Trap"
::= 12205

cmPos30VdcSensorVoltageTRAP TRAP-TYPE
ENTERPRISE itwatchdogs
VARIABLES { pos30VdcSensorVoltage, pos30VdcSensorName, productFriendlyName, alarmTripType }
DESCRIPTION "30Vdc Sensor Trap"
::= 12305

cmCtrl3ChIECKWattHrsATRAP TRAP-TYPE
ENTERPRISE itwatchdogs
VARIABLES { ctrl3ChIECKWattHrsA, ctrl3ChIECName, productFriendlyName, alarmTripType }
DESCRIPTION "Kilo Watt Hours A Trap"
::= 12405

cmCtrl3ChIECVoltsATRAP TRAP-TYPE
ENTERPRISE itwatchdogs
VARIABLES { ctrl3ChIECVoltsA, ctrl3ChIECName, productFriendlyName, alarmTripType }
DESCRIPTION "Volts A Trap"
::= 12406

cmCtrl3ChIECVoltPkATRAP TRAP-TYPE
ENTERPRISE itwatchdogs
VARIABLES { ctrl3ChIECVoltPkA, ctrl3ChIECName, productFriendlyName, alarmTripType }
DESCRIPTION "Volt Peak A Trap"
::= 12407

cmCtrl3ChIECAmpsATRAP TRAP-TYPE
ENTERPRISE itwatchdogs
VARIABLES { ctrl3ChIECAmpsA, ctrl3ChIECName, productFriendlyName, alarmTripType }
DESCRIPTION "Amps A Trap"
::= 12408

cmCtrl3ChIECAmpPkATRAP TRAP-TYPE
ENTERPRISE itwatchdogs
VARIABLES { ctrl3ChIECAmpPkA, ctrl3ChIECName, productFriendlyName, alarmTripType }
DESCRIPTION "Amps Peak A Trap"
::= 12409

cmCtrl3ChIECRealPowATRAP TRAP-TYPE
ENTERPRISE itwatchdogs
VARIABLES { ctrl3ChIECRealPowA, ctrl3ChIECName, productFriendlyName, alarmTripType }
DESCRIPTION "Real Power A Trap"
::= 12410

cmCtrl3ChIECAppPowATRAP TRAP-TYPE
ENTERPRISE itwatchdogs
VARIABLES { ctrl3ChIECAppPowA, ctrl3ChIECName, productFriendlyName, alarmTripType }
DESCRIPTION "Apparent Power A Trap"
::= 12411

cmCtrl3ChIECPwrFactATRAP TRAP-TYPE
ENTERPRISE itwatchdogs
VARIABLES { ctrl3ChIECPwrFactA, ctrl3ChIECName, productFriendlyName, alarmTripType }
DESCRIPTION "Power Factor A Trap"
::= 12412

cmCtrl3ChIECKWattHrsBTRAP TRAP-TYPE
ENTERPRISE itwatchdogs
VARIABLES { ctrl3ChIECKWattHrsB, ctrl3ChIECName, productFriendlyName, alarmTripType }
DESCRIPTION "Kilo Watt Hours B Trap"
::= 12413

cmCtrl3ChIECVoltsBTRAP TRAP-TYPE
ENTERPRISE itwatchdogs
VARIABLES { ctrl3ChIECVoltsB, ctrl3ChIECName, productFriendlyName, alarmTripType }
DESCRIPTION "Volts B Trap"
::= 12414

cmCtrl3ChIECVoltPkBTRAP TRAP-TYPE
ENTERPRISE itwatchdogs
VARIABLES { ctrl3ChIECVoltPkB, ctrl3ChIECName, productFriendlyName, alarmTripType }
DESCRIPTION "Volt Peak B Trap"
::= 12415

cmCtrl3ChIECAmpsBTRAP TRAP-TYPE
ENTERPRISE itwatchdogs
VARIABLES { ctrl3ChIECAmpsB, ctrl3ChIECName, productFriendlyName, alarmTripType }
DESCRIPTION "Amps B Trap"
::= 12416

cmCtrl3ChIECAmpPkBTRAP TRAP-TYPE
ENTERPRISE itwatchdogs
VARIABLES { ctrl3ChIECAmpPkB, ctrl3ChIECName, productFriendlyName, alarmTripType }
DESCRIPTION "Amps Peak B Trap"
::= 12417

cmCtrl3ChIECRealPowBTRAP TRAP-TYPE
ENTERPRISE itwatchdogs
VARIABLES { ctrl3ChIECRealPowB, ctrl3ChIECName, productFriendlyName, alarmTripType }
DESCRIPTION "Real Power B Trap"
::= 12418

cmCtrl3ChIECAppPowBTRAP TRAP-TYPE
ENTERPRISE itwatchdogs
VARIABLES { ctrl3ChIECAppPowB, ctrl3ChIECName, productFriendlyName, alarmTripType }
DESCRIPTION "Apparent Power B Trap"
::= 12419

cmCtrl3ChIECPwrFactBTRAP TRAP-TYPE
ENTERPRISE itwatchdogs
VARIABLES { ctrl3ChIECPwrFactB, ctrl3ChIECName, productFriendlyName, alarmTripType }
DESCRIPTION "Power Factor B Trap"
::= 12420

cmCtrl3ChIECKWattHrsCTRAP TRAP-TYPE
ENTERPRISE itwatchdogs
VARIABLES { ctrl3ChIECKWattHrsC, ctrl3ChIECName, productFriendlyName, alarmTripType }
DESCRIPTION "Kilo Watt Hours C Trap"
::= 12421

cmCtrl3ChIECVoltsCTRAP TRAP-TYPE
ENTERPRISE itwatchdogs
VARIABLES { ctrl3ChIECVoltsC, ctrl3ChIECName, productFriendlyName, alarmTripType }
DESCRIPTION "Volts C Trap"
::= 12422

cmCtrl3ChIECVoltPkCTRAP TRAP-TYPE
ENTERPRISE itwatchdogs
VARIABLES { ctrl3ChIECVoltPkC, ctrl3ChIECName, productFriendlyName, alarmTripType }
DESCRIPTION "Volt Peak C Trap"
::= 12423

cmCtrl3ChIECAmpsCTRAP TRAP-TYPE
ENTERPRISE itwatchdogs
VARIABLES { ctrl3ChIECAmpsC, ctrl3ChIECName, productFriendlyName, alarmTripType }
DESCRIPTION "Amps C Trap"
::= 12424

cmCtrl3ChIECAmpPkCTRAP TRAP-TYPE
ENTERPRISE itwatchdogs
VARIABLES { ctrl3ChIECAmpPkC, ctrl3ChIECName, productFriendlyName, alarmTripType }
DESCRIPTION "Amps Peak C Trap"
::= 12425

cmCtrl3ChIECRealPowCTRAP TRAP-TYPE
ENTERPRISE itwatchdogs
VARIABLES { ctrl3ChIECRealPowC, ctrl3ChIECName, productFriendlyName, alarmTripType }
DESCRIPTION "Real Power C Trap"
::= 12426

cmCtrl3ChIECAppPowCTRAP TRAP-TYPE
ENTERPRISE itwatchdogs
VARIABLES { ctrl3ChIECAppPowC, ctrl3ChIECName, productFriendlyName, alarmTripType }
DESCRIPTION "Apparent Power C Trap"
::= 12427

cmCtrl3ChIECPwrFactCTRAP TRAP-TYPE
ENTERPRISE itwatchdogs
VARIABLES { ctrl3ChIECPwrFactC, ctrl3ChIECName, productFriendlyName, alarmTripType }
DESCRIPTION "Power Factor C Trap"
::= 12428

cmClimateTempCCLEAR TRAP-TYPE
ENTERPRISE itwatchdogs
VARIABLES { climateTempC, climateName, productFriendlyName, alarmTripType }
DESCRIPTION "Climate Temperature Sensor Clear Trap"
::= 20205

cmClimateTempFCLEAR TRAP-TYPE
ENTERPRISE itwatchdogs
VARIABLES { climateTempF, climateName, productFriendlyName, alarmTripType }
DESCRIPTION "Climate Temperature Sensor Clear Trap"
::= 20206

cmClimateHumidityCLEAR TRAP-TYPE
ENTERPRISE itwatchdogs
VARIABLES { climateHumidity, climateName, productFriendlyName, alarmTripType }
DESCRIPTION "Climate Humidity Sensor Clear Trap"
::= 20207

cmClimateLightCLEAR TRAP-TYPE
ENTERPRISE itwatchdogs
VARIABLES { climateLight, climateName, productFriendlyName, alarmTripType }
DESCRIPTION "Climate Light Sensor Clear Trap"
::= 20208

cmClimateAirflowCLEAR TRAP-TYPE
ENTERPRISE itwatchdogs
VARIABLES { climateAirflow, climateName, productFriendlyName, alarmTripType }
DESCRIPTION "Climate Air Flow Sensor Clear Trap"
::= 20209

cmClimateSoundCLEAR TRAP-TYPE
ENTERPRISE itwatchdogs
VARIABLES { climateSound, climateName, productFriendlyName, alarmTripType }
DESCRIPTION "Climate Sound Sensor Clear Trap"
::= 20210

cmClimateIO1CLEAR TRAP-TYPE
ENTERPRISE itwatchdogs
VARIABLES { climateIO1, climateName, productFriendlyName, alarmTripType }
DESCRIPTION "Climate IO1 Sensor Clear Trap"
::= 20211

cmClimateIO2CLEAR TRAP-TYPE
ENTERPRISE itwatchdogs
VARIABLES { climateIO2, climateName, productFriendlyName, alarmTripType }
DESCRIPTION "Climate IO2 Sensor Clear Trap"
::= 20212

cmClimateIO3CLEAR TRAP-TYPE
ENTERPRISE itwatchdogs
VARIABLES { climateIO3, climateName, productFriendlyName, alarmTripType }
DESCRIPTION "Climate IO3 Sensor Clear Trap"
::= 20213

cmPowMonKWattHrsCLEAR TRAP-TYPE
ENTERPRISE itwatchdogs
VARIABLES { powMonKWattHrs, powMonName, productFriendlyName, alarmTripType }
DESCRIPTION "Kilo Watt Hours Clear Trap"
::= 20305

cmPowMonVoltsCLEAR TRAP-TYPE
ENTERPRISE itwatchdogs
VARIABLES { powMonVolts, powMonName, productFriendlyName, alarmTripType }
DESCRIPTION "Volts Clear Trap"
::= 20306

cmPowMonVoltMaxCLEAR TRAP-TYPE
ENTERPRISE itwatchdogs
VARIABLES { powMonVoltMax, powMonName, productFriendlyName, alarmTripType }
DESCRIPTION "Volts Max Clear Trap"
::= 20307

cmPowMonVoltMinCLEAR TRAP-TYPE
ENTERPRISE itwatchdogs
VARIABLES { powMonVoltMin, powMonName, productFriendlyName, alarmTripType }
DESCRIPTION "Volts Min Clear Trap"
::= 20308

cmPowMonVoltPkCLEAR TRAP-TYPE
ENTERPRISE itwatchdogs
VARIABLES { powMonVoltPk, powMonName, productFriendlyName, alarmTripType }
DESCRIPTION "Volt Peak Clear Trap"
::= 20309

cmPowMonAmpsX10CLEAR TRAP-TYPE
ENTERPRISE itwatchdogs
VARIABLES { powMonAmpsX10, powMonName, productFriendlyName, alarmTripType }
DESCRIPTION "Amps x 10 Clear Trap"
::= 20310

cmPowMonRealPowCLEAR TRAP-TYPE
ENTERPRISE itwatchdogs
VARIABLES { powMonRealPow, powMonName, productFriendlyName, alarmTripType }
DESCRIPTION "Real Power Clear Trap"
::= 20311

cmPowMonAppPowCLEAR TRAP-TYPE
ENTERPRISE itwatchdogs
VARIABLES { powMonAppPow, powMonName, productFriendlyName, alarmTripType }
DESCRIPTION "Apparent Power Clear Trap"
::= 20312

cmPowMonPwrFactCLEAR TRAP-TYPE
ENTERPRISE itwatchdogs
VARIABLES { powMonPwrFact, powMonName, productFriendlyName, alarmTripType }
DESCRIPTION "Power Factor Clear Trap"
::= 20313

cmPowMonOutlet1CLEAR TRAP-TYPE
ENTERPRISE itwatchdogs
VARIABLES { powMonOutlet1, powMonName, productFriendlyName, alarmTripType }
DESCRIPTION "Outlet 1 Clear Trap"
::= 20314

cmPowMonOutlet2CLEAR TRAP-TYPE
ENTERPRISE itwatchdogs
VARIABLES { powMonOutlet2, powMonName, productFriendlyName, alarmTripType }
DESCRIPTION "Outlet 2 Clear Trap"
::= 20315

cmTempSensorTempCCLEAR TRAP-TYPE
ENTERPRISE itwatchdogs
VARIABLES { tempSensorTempC, tempSensorName, productFriendlyName, alarmTripType }
DESCRIPTION "Remote Temp Sensor - Temperature Clear Trap"
::= 20405

cmTempSensorTempFCLEAR TRAP-TYPE
ENTERPRISE itwatchdogs
VARIABLES { tempSensorTempF, tempSensorName, productFriendlyName, alarmTripType }
DESCRIPTION "Remote Temp Sensor - Temperature Clear Trap"
::= 20406

cmAirFlowSensorTempCCLEAR TRAP-TYPE
ENTERPRISE itwatchdogs
VARIABLES { airFlowSensorTempC, airFlowSensorName, productFriendlyName, alarmTripType }
DESCRIPTION "Remote Air Flow Sensor - Temperature Clear Trap"
::= 20505

cmAirFlowSensorTempFCLEAR TRAP-TYPE
ENTERPRISE itwatchdogs
VARIABLES { airFlowSensorTempF, airFlowSensorName, productFriendlyName, alarmTripType }
DESCRIPTION "Remote Air Flow Sensor - Temperature Clear Trap"
::= 20506

cmAirFlowSensorFlowCLEAR TRAP-TYPE
ENTERPRISE itwatchdogs
VARIABLES { airFlowSensorFlow, airFlowSensorName, productFriendlyName, alarmTripType }
DESCRIPTION "Remote Air Flow Sensor - Air Flow Clear Trap"
::= 20507

cmAirFlowSensorHumidityCLEAR TRAP-TYPE
ENTERPRISE itwatchdogs
VARIABLES { airFlowSensorHumidity, airFlowSensorName, productFriendlyName, alarmTripType }
DESCRIPTION "Remote Air Flow Sensor - Humidity Clear Trap"
::= 20508

cmPowerVoltsCLEAR TRAP-TYPE
ENTERPRISE itwatchdogs
VARIABLES { powerVolts, powerName, productFriendlyName, alarmTripType }
DESCRIPTION "Power-Only Volts Clear Trap"
::= 20605

cmPowerAmpsCLEAR TRAP-TYPE
ENTERPRISE itwatchdogs
VARIABLES { powerAmps, powerName, productFriendlyName, alarmTripType }
DESCRIPTION "Power-Only Amps Clear Trap"
::= 20606

cmPowerRealPowCLEAR TRAP-TYPE
ENTERPRISE itwatchdogs
VARIABLES { powerRealPow, powerName, productFriendlyName, alarmTripType }
DESCRIPTION "Power-Only Watts Clear Trap"
::= 20607

cmPowerAppPowCLEAR TRAP-TYPE
ENTERPRISE itwatchdogs
VARIABLES { powerAppPow, powerName, productFriendlyName, alarmTripType }
DESCRIPTION "Power-Only Volt Amps Clear Trap"
::= 20608

cmPowerPwrFactorCLEAR TRAP-TYPE
ENTERPRISE itwatchdogs
VARIABLES { powerPwrFactor, powerName, productFriendlyName, alarmTripType }
DESCRIPTION "Power-Only Power Factor Clear Trap"
::= 20609

cmDoorSensorStatusCLEAR TRAP-TYPE
ENTERPRISE itwatchdogs
VARIABLES { doorSensorStatus, doorSensorName, productFriendlyName, alarmTripType }
DESCRIPTION "Door sensor Clear Trap"
::= 20705

cmWaterSensorDampnessCLEAR TRAP-TYPE
ENTERPRISE itwatchdogs
VARIABLES { waterSensorDampness, waterSensorName, productFriendlyName, alarmTripType }
DESCRIPTION "Water sensor Clear Trap"
::= 20805

cmCurrentMonitorAmpsCLEAR TRAP-TYPE
ENTERPRISE itwatchdogs
VARIABLES { currentMonitorAmps, currentMonitorName, productFriendlyName, alarmTripType }
DESCRIPTION "Current Monitor Amps Clear Trap"
::= 20905

cmMillivoltMonitorMVCLEAR TRAP-TYPE
ENTERPRISE itwatchdogs
VARIABLES { millivoltMonitorMV, millivoltMonitorName, productFriendlyName, alarmTripType }
DESCRIPTION "Millivolt Monitor Clear Trap"
::= 21005

cmPow3ChKWattHrsACLEAR TRAP-TYPE
ENTERPRISE itwatchdogs
VARIABLES { pow3ChKWattHrsA, pow3ChName, productFriendlyName, alarmTripType }
DESCRIPTION "Kilo Watt Hours A Clear Trap"
::= 21105

cmPow3ChVoltsACLEAR TRAP-TYPE
ENTERPRISE itwatchdogs
VARIABLES { pow3ChVoltsA, pow3ChName, productFriendlyName, alarmTripType }
DESCRIPTION "Volts A Clear Trap"
::= 21106

cmPow3ChVoltMaxACLEAR TRAP-TYPE
ENTERPRISE itwatchdogs
VARIABLES { pow3ChVoltMaxA, pow3ChName, productFriendlyName, alarmTripType }
DESCRIPTION "Volts Max A Clear Trap"
::= 21107

cmPow3ChVoltMinACLEAR TRAP-TYPE
ENTERPRISE itwatchdogs
VARIABLES { pow3ChVoltMinA, pow3ChName, productFriendlyName, alarmTripType }
DESCRIPTION "Volts Min A Clear Trap"
::= 21108

cmPow3ChVoltPkACLEAR TRAP-TYPE
ENTERPRISE itwatchdogs
VARIABLES { pow3ChVoltPkA, pow3ChName, productFriendlyName, alarmTripType }
DESCRIPTION "Volt Peak A Clear Trap"
::= 21109

cmPow3ChAmpsX10ACLEAR TRAP-TYPE
ENTERPRISE itwatchdogs
VARIABLES { pow3ChAmpsX10A, pow3ChName, productFriendlyName, alarmTripType }
DESCRIPTION "Amps x 10 A Clear Trap"
::= 21110

cmPow3ChRealPowACLEAR TRAP-TYPE
ENTERPRISE itwatchdogs
VARIABLES { pow3ChRealPowA, pow3ChName, productFriendlyName, alarmTripType }
DESCRIPTION "Real Power A Clear Trap"
::= 21111

cmPow3ChAppPowACLEAR TRAP-TYPE
ENTERPRISE itwatchdogs
VARIABLES { pow3ChAppPowA, pow3ChName, productFriendlyName, alarmTripType }
DESCRIPTION "Apparent Power A Clear Trap"
::= 21112

cmPow3ChPwrFactACLEAR TRAP-TYPE
ENTERPRISE itwatchdogs
VARIABLES { pow3ChPwrFactA, pow3ChName, productFriendlyName, alarmTripType }
DESCRIPTION "Power Factor A Clear Trap"
::= 21113

cmPow3ChKWattHrsBCLEAR TRAP-TYPE
ENTERPRISE itwatchdogs
VARIABLES { pow3ChKWattHrsB, pow3ChName, productFriendlyName, alarmTripType }
DESCRIPTION "Kilo Watt Hours B Clear Trap"
::= 21114

cmPow3ChVoltsBCLEAR TRAP-TYPE
ENTERPRISE itwatchdogs
VARIABLES { pow3ChVoltsB, pow3ChName, productFriendlyName, alarmTripType }
DESCRIPTION "Volts B Clear Trap"
::= 21115

cmPow3ChVoltMaxBCLEAR TRAP-TYPE
ENTERPRISE itwatchdogs
VARIABLES { pow3ChVoltMaxB, pow3ChName, productFriendlyName, alarmTripType }
DESCRIPTION "Volts Max B Clear Trap"
::= 21116

cmPow3ChVoltMinBCLEAR TRAP-TYPE
ENTERPRISE itwatchdogs
VARIABLES { pow3ChVoltMinB, pow3ChName, productFriendlyName, alarmTripType }
DESCRIPTION "Volts Min B Clear Trap"
::= 21117

cmPow3ChVoltPkBCLEAR TRAP-TYPE
ENTERPRISE itwatchdogs
VARIABLES { pow3ChVoltPkB, pow3ChName, productFriendlyName, alarmTripType }
DESCRIPTION "Volt Peak B Clear Trap"
::= 21118

cmPow3ChAmpsX10BCLEAR TRAP-TYPE
ENTERPRISE itwatchdogs
VARIABLES { pow3ChAmpsX10B, pow3ChName, productFriendlyName, alarmTripType }
DESCRIPTION "Amps x 10 B Clear Trap"
::= 21119

cmPow3ChRealPowBCLEAR TRAP-TYPE
ENTERPRISE itwatchdogs
VARIABLES { pow3ChRealPowB, pow3ChName, productFriendlyName, alarmTripType }
DESCRIPTION "Real Power B Clear Trap"
::= 21120

cmPow3ChAppPowBCLEAR TRAP-TYPE
ENTERPRISE itwatchdogs
VARIABLES { pow3ChAppPowB, pow3ChName, productFriendlyName, alarmTripType }
DESCRIPTION "Apparent Power B Clear Trap"
::= 21121

cmPow3ChPwrFactBCLEAR TRAP-TYPE
ENTERPRISE itwatchdogs
VARIABLES { pow3ChPwrFactB, pow3ChName, productFriendlyName, alarmTripType }
DESCRIPTION "Power Factor B Clear Trap"
::= 21122

cmPow3ChKWattHrsCCLEAR TRAP-TYPE
ENTERPRISE itwatchdogs
VARIABLES { pow3ChKWattHrsC, pow3ChName, productFriendlyName, alarmTripType }
DESCRIPTION "Kilo Watt Hours C Clear Trap"
::= 21123

cmPow3ChVoltsCCLEAR TRAP-TYPE
ENTERPRISE itwatchdogs
VARIABLES { pow3ChVoltsC, pow3ChName, productFriendlyName, alarmTripType }
DESCRIPTION "Volts C Clear Trap"
::= 21124

cmPow3ChVoltMaxCCLEAR TRAP-TYPE
ENTERPRISE itwatchdogs
VARIABLES { pow3ChVoltMaxC, pow3ChName, productFriendlyName, alarmTripType }
DESCRIPTION "Volts Max C Clear Trap"
::= 21125

cmPow3ChVoltMinCCLEAR TRAP-TYPE
ENTERPRISE itwatchdogs
VARIABLES { pow3ChVoltMinC, pow3ChName, productFriendlyName, alarmTripType }
DESCRIPTION "Volts Min C Clear Trap"
::= 21126

cmPow3ChVoltPkCCLEAR TRAP-TYPE
ENTERPRISE itwatchdogs
VARIABLES { pow3ChVoltPkC, pow3ChName, productFriendlyName, alarmTripType }
DESCRIPTION "Volt Peak C Clear Trap"
::= 21127

cmPow3ChAmpsX10CCLEAR TRAP-TYPE
ENTERPRISE itwatchdogs
VARIABLES { pow3ChAmpsX10C, pow3ChName, productFriendlyName, alarmTripType }
DESCRIPTION "Amps x 10 C Clear Trap"
::= 21128

cmPow3ChRealPowCCLEAR TRAP-TYPE
ENTERPRISE itwatchdogs
VARIABLES { pow3ChRealPowC, pow3ChName, productFriendlyName, alarmTripType }
DESCRIPTION "Real Power C Clear Trap"
::= 21129

cmPow3ChAppPowCCLEAR TRAP-TYPE
ENTERPRISE itwatchdogs
VARIABLES { pow3ChAppPowC, pow3ChName, productFriendlyName, alarmTripType }
DESCRIPTION "Apparent Power C Clear Trap"
::= 21130

cmPow3ChPwrFactCCLEAR TRAP-TYPE
ENTERPRISE itwatchdogs
VARIABLES { pow3ChPwrFactC, pow3ChName, productFriendlyName, alarmTripType }
DESCRIPTION "Power Factor C Clear Trap"
::= 21131

cmOutlet1StatusCLEAR TRAP-TYPE
ENTERPRISE itwatchdogs
VARIABLES { outlet1Status, outletName, productFriendlyName, alarmTripType }
DESCRIPTION "Outlet 1 Status Clear Trap"
::= 21205

cmOutlet2StatusCLEAR TRAP-TYPE
ENTERPRISE itwatchdogs
VARIABLES { outlet2Status, outletName, productFriendlyName, alarmTripType }
DESCRIPTION "Outlet 2 Status Clear Trap"
::= 21206

cmVsfcSetPointCCLEAR TRAP-TYPE
ENTERPRISE itwatchdogs
VARIABLES { vsfcSetPointC, vsfcName, productFriendlyName, alarmTripType }
DESCRIPTION "Vsfc Temp Set Point Sensor Clear"
::= 21305

cmVsfcSetPointFCLEAR TRAP-TYPE
ENTERPRISE itwatchdogs
VARIABLES { vsfcSetPointF, vsfcName, productFriendlyName, alarmTripType }
DESCRIPTION "Vsfc Temp Set Point Sensor Clear"
::= 21306

cmVsfcIntTempCCLEAR TRAP-TYPE
ENTERPRISE itwatchdogs
VARIABLES { vsfcIntTempC, vsfcName, productFriendlyName, alarmTripType }
DESCRIPTION "Vsfc Internal Temp Sensor Clear"
::= 21307

cmVsfcIntTempFCLEAR TRAP-TYPE
ENTERPRISE itwatchdogs
VARIABLES { vsfcIntTempF, vsfcName, productFriendlyName, alarmTripType }
DESCRIPTION "Vsfc Internal Temp Sensor Clear"
::= 21308

cmVsfcExt1TempCCLEAR TRAP-TYPE
ENTERPRISE itwatchdogs
VARIABLES { vsfcExt1TempC, vsfcName, productFriendlyName, alarmTripType }
DESCRIPTION "Vsfc External Temp 1 Sensor Clear"
::= 21309

cmVsfcExt1TempFCLEAR TRAP-TYPE
ENTERPRISE itwatchdogs
VARIABLES { vsfcExt1TempF, vsfcName, productFriendlyName, alarmTripType }
DESCRIPTION "Vsfc External Temp 1 Sensor Clear"
::= 21310

cmVsfcExt2TempCCLEAR TRAP-TYPE
ENTERPRISE itwatchdogs
VARIABLES { vsfcExt2TempC, vsfcName, productFriendlyName, alarmTripType }
DESCRIPTION "Vsfc External Temp 2 Sensor Clear"
::= 21311

cmVsfcExt2TempFCLEAR TRAP-TYPE
ENTERPRISE itwatchdogs
VARIABLES { vsfcExt2TempF, vsfcName, productFriendlyName, alarmTripType }
DESCRIPTION "Vsfc External Temp 2 Sensor Clear"
::= 21312

cmVsfcExt3TempCCLEAR TRAP-TYPE
ENTERPRISE itwatchdogs
VARIABLES { vsfcExt3TempC, vsfcName, productFriendlyName, alarmTripType }
DESCRIPTION "Vsfc External Temp 3 Sensor Clear"
::= 21313

cmVsfcExt3TempFCLEAR TRAP-TYPE
ENTERPRISE itwatchdogs
VARIABLES { vsfcExt3TempF, vsfcName, productFriendlyName, alarmTripType }
DESCRIPTION "Vsfc External Temp 3 Sensor Clear"
::= 21314

cmVsfcExt4TempCCLEAR TRAP-TYPE
ENTERPRISE itwatchdogs
VARIABLES { vsfcExt4TempC, vsfcName, productFriendlyName, alarmTripType }
DESCRIPTION "Vsfc External Temp 4 Sensor Clear"
::= 21315

cmVsfcExt4TempFCLEAR TRAP-TYPE
ENTERPRISE itwatchdogs
VARIABLES { vsfcExt4TempF, vsfcName, productFriendlyName, alarmTripType }
DESCRIPTION "Vsfc External Temp 4 Sensor Clear"
::= 21316

cmVsfcFanSpeedCLEAR TRAP-TYPE
ENTERPRISE itwatchdogs
VARIABLES { vsfcFanSpeed, vsfcName, productFriendlyName, alarmTripType }
DESCRIPTION "Vsfc Fan Speed Sensor Clear"
::= 21317

cmCtrl3ChVoltsACLEAR TRAP-TYPE
ENTERPRISE itwatchdogs
VARIABLES { ctrl3ChVoltsA, ctrl3ChName, productFriendlyName, alarmTripType }
DESCRIPTION "Volts A Clear"
::= 21405

cmCtrl3ChVoltPkACLEAR TRAP-TYPE
ENTERPRISE itwatchdogs
VARIABLES { ctrl3ChVoltPkA, ctrl3ChName, productFriendlyName, alarmTripType }
DESCRIPTION "Volt Peak A Clear"
::= 21406

cmCtrl3ChAmpsACLEAR TRAP-TYPE
ENTERPRISE itwatchdogs
VARIABLES { ctrl3ChAmpsA, ctrl3ChName, productFriendlyName, alarmTripType }
DESCRIPTION "Amps A Clear"
::= 21407

cmCtrl3ChAmpPkACLEAR TRAP-TYPE
ENTERPRISE itwatchdogs
VARIABLES { ctrl3ChAmpPkA, ctrl3ChName, productFriendlyName, alarmTripType }
DESCRIPTION "Amps Peak A Clear"
::= 21408

cmCtrl3ChRealPowACLEAR TRAP-TYPE
ENTERPRISE itwatchdogs
VARIABLES { ctrl3ChRealPowA, ctrl3ChName, productFriendlyName, alarmTripType }
DESCRIPTION "Real Power A Clear"
::= 21409

cmCtrl3ChAppPowACLEAR TRAP-TYPE
ENTERPRISE itwatchdogs
VARIABLES { ctrl3ChAppPowA, ctrl3ChName, productFriendlyName, alarmTripType }
DESCRIPTION "Apparent Power A Clear"
::= 21410

cmCtrl3ChPwrFactACLEAR TRAP-TYPE
ENTERPRISE itwatchdogs
VARIABLES { ctrl3ChPwrFactA, ctrl3ChName, productFriendlyName, alarmTripType }
DESCRIPTION "Power Factor A Clear"
::= 21411

cmCtrl3ChVoltsBCLEAR TRAP-TYPE
ENTERPRISE itwatchdogs
VARIABLES { ctrl3ChVoltsB, ctrl3ChName, productFriendlyName, alarmTripType }
DESCRIPTION "Volts B Clear"
::= 21412

cmCtrl3ChVoltPkBCLEAR TRAP-TYPE
ENTERPRISE itwatchdogs
VARIABLES { ctrl3ChVoltPkB, ctrl3ChName, productFriendlyName, alarmTripType }
DESCRIPTION "Volt Peak B Clear"
::= 21413

cmCtrl3ChAmpsBCLEAR TRAP-TYPE
ENTERPRISE itwatchdogs
VARIABLES { ctrl3ChAmpsB, ctrl3ChName, productFriendlyName, alarmTripType }
DESCRIPTION "Amps B Clear"
::= 21414

cmCtrl3ChAmpPkBCLEAR TRAP-TYPE
ENTERPRISE itwatchdogs
VARIABLES { ctrl3ChAmpPkB, ctrl3ChName, productFriendlyName, alarmTripType }
DESCRIPTION "Amps Peak B Clear"
::= 21415

cmCtrl3ChRealPowBCLEAR TRAP-TYPE
ENTERPRISE itwatchdogs
VARIABLES { ctrl3ChRealPowB, ctrl3ChName, productFriendlyName, alarmTripType }
DESCRIPTION "Real Power B Clear"
::= 21416

cmCtrl3ChAppPowBCLEAR TRAP-TYPE
ENTERPRISE itwatchdogs
VARIABLES { ctrl3ChAppPowB, ctrl3ChName, productFriendlyName, alarmTripType }
DESCRIPTION "Apparent Power B Clear"
::= 21417

cmCtrl3ChPwrFactBCLEAR TRAP-TYPE
ENTERPRISE itwatchdogs
VARIABLES { ctrl3ChPwrFactB, ctrl3ChName, productFriendlyName, alarmTripType }
DESCRIPTION "Power Factor B Clear"
::= 21418

cmCtrl3ChVoltsCCLEAR TRAP-TYPE
ENTERPRISE itwatchdogs
VARIABLES { ctrl3ChVoltsC, ctrl3ChName, productFriendlyName, alarmTripType }
DESCRIPTION "Volts C Clear"
::= 21419

cmCtrl3ChVoltPkCCLEAR TRAP-TYPE
ENTERPRISE itwatchdogs
VARIABLES { ctrl3ChVoltPkC, ctrl3ChName, productFriendlyName, alarmTripType }
DESCRIPTION "Volt Peak C Clear"
::= 21420

cmCtrl3ChAmpsCCLEAR TRAP-TYPE
ENTERPRISE itwatchdogs
VARIABLES { ctrl3ChAmpsC, ctrl3ChName, productFriendlyName, alarmTripType }
DESCRIPTION "Amps C Clear"
::= 21421

cmCtrl3ChAmpPkCCLEAR TRAP-TYPE
ENTERPRISE itwatchdogs
VARIABLES { ctrl3ChAmpPkC, ctrl3ChName, productFriendlyName, alarmTripType }
DESCRIPTION "Amps Peak C Clear"
::= 21422

cmCtrl3ChRealPowCCLEAR TRAP-TYPE
ENTERPRISE itwatchdogs
VARIABLES { ctrl3ChRealPowC, ctrl3ChName, productFriendlyName, alarmTripType }
DESCRIPTION "Real Power C Clear"
::= 21423

cmCtrl3ChAppPowCCLEAR TRAP-TYPE
ENTERPRISE itwatchdogs
VARIABLES { ctrl3ChAppPowC, ctrl3ChName, productFriendlyName, alarmTripType }
DESCRIPTION "Apparent Power C Clear"
::= 21424

cmCtrl3ChPwrFactCCLEAR TRAP-TYPE
ENTERPRISE itwatchdogs
VARIABLES { ctrl3ChPwrFactC, ctrl3ChName, productFriendlyName, alarmTripType }
DESCRIPTION "Power Factor C Clear"
::= 21425

cmCtrlGrpAmpsACLEAR TRAP-TYPE
ENTERPRISE itwatchdogs
VARIABLES { ctrlGrpAmpsA, ctrlGrpAmpsName, productFriendlyName, alarmTripType }
DESCRIPTION "Group A Amps Clear Trap"
::= 21505

cmCtrlGrpAmpsBCLEAR TRAP-TYPE
ENTERPRISE itwatchdogs
VARIABLES { ctrlGrpAmpsB, ctrlGrpAmpsName, productFriendlyName, alarmTripType }
DESCRIPTION "Group B Amps Clear Trap"
::= 21506

cmCtrlGrpAmpsCCLEAR TRAP-TYPE
ENTERPRISE itwatchdogs
VARIABLES { ctrlGrpAmpsC, ctrlGrpAmpsName, productFriendlyName, alarmTripType }
DESCRIPTION "Group C Amps Clear Trap"
::= 21507

cmCtrlGrpAmpsDCLEAR TRAP-TYPE
ENTERPRISE itwatchdogs
VARIABLES { ctrlGrpAmpsD, ctrlGrpAmpsName, productFriendlyName, alarmTripType }
DESCRIPTION "Group D Amps Clear Trap"
::= 21508

cmCtrlGrpAmpsECLEAR TRAP-TYPE
ENTERPRISE itwatchdogs
VARIABLES { ctrlGrpAmpsE, ctrlGrpAmpsName, productFriendlyName, alarmTripType }
DESCRIPTION "Group E Amps Clear Trap"
::= 21509

cmCtrlGrpAmpsFCLEAR TRAP-TYPE
ENTERPRISE itwatchdogs
VARIABLES { ctrlGrpAmpsF, ctrlGrpAmpsName, productFriendlyName, alarmTripType }
DESCRIPTION "Group F Amps Clear Trap"
::= 21510

cmDewPointSensorDewPointCCLEAR TRAP-TYPE
ENTERPRISE itwatchdogs
VARIABLES { dewPointSensorDewPointC, dewPointSensorName, productFriendlyName, alarmTripType }
DESCRIPTION "Remote Dew Point Sensor - Dew Point Clear Trap"
::= 21705

cmDewPointSensorDewPointFCLEAR TRAP-TYPE
ENTERPRISE itwatchdogs
VARIABLES { dewPointSensorDewPointF, dewPointSensorName, productFriendlyName, alarmTripType }
DESCRIPTION "Remote Dew Point Sensor - Dew Point Clear Trap"
::= 21706

cmDewPointSensorTempCCLEAR TRAP-TYPE
ENTERPRISE itwatchdogs
VARIABLES { dewPointSensorTempC, dewPointSensorName, productFriendlyName, alarmTripType }
DESCRIPTION "Remote Dew Point Sensor - Temperature Clear Trap"
::= 21707

cmDewPointSensorTempFCLEAR TRAP-TYPE
ENTERPRISE itwatchdogs
VARIABLES { dewPointSensorTempF, dewPointSensorName, productFriendlyName, alarmTripType }
DESCRIPTION "Remote Dew Point Sensor - Temperature Clear Trap"
::= 21708

cmDewPointSensorHumidityCLEAR TRAP-TYPE
ENTERPRISE itwatchdogs
VARIABLES { dewPointSensorHumidity, dewPointSensorName, productFriendlyName, alarmTripType }
DESCRIPTION "Remote Dew Point Sensor - Humidity Clear Trap"
::= 21709

cmDigitalSensorDigitalCLEAR TRAP-TYPE
ENTERPRISE itwatchdogs
VARIABLES { digitalSensorDigital, digitalSensorName, productFriendlyName, alarmTripType }
DESCRIPTION "Digital sensor Clear Trap"
::= 21805

cmDstsVoltsACLEAR TRAP-TYPE
ENTERPRISE itwatchdogs
VARIABLES { dstsVoltsA, dstsName, productFriendlyName, alarmTripType }
DESCRIPTION "RMS Voltage of Side A Set Point Sensor Clear"
::= 21905

cmDstsAmpsACLEAR TRAP-TYPE
ENTERPRISE itwatchdogs
VARIABLES { dstsAmpsA, dstsName, productFriendlyName, alarmTripType }
DESCRIPTION "RMS Current of Side A Set Point Sensor Clear"
::= 21906

cmDstsVoltsBCLEAR TRAP-TYPE
ENTERPRISE itwatchdogs
VARIABLES { dstsVoltsB, dstsName, productFriendlyName, alarmTripType }
DESCRIPTION "RMS Voltage of Side B Set Point Sensor Clear"
::= 21907

cmDstsAmpsBCLEAR TRAP-TYPE
ENTERPRISE itwatchdogs
VARIABLES { dstsAmpsB, dstsName, productFriendlyName, alarmTripType }
DESCRIPTION "RMS Current of Side B Set Point Sensor Clear"
::= 21908

cmDstsSourceAActiveCLEAR TRAP-TYPE
ENTERPRISE itwatchdogs
VARIABLES { dstsSourceAActive, dstsName, productFriendlyName, alarmTripType }
DESCRIPTION "Source A Active Set Point Sensor Clear"
::= 21909

cmDstsSourceBActiveCLEAR TRAP-TYPE
ENTERPRISE itwatchdogs
VARIABLES { dstsSourceBActive, dstsName, productFriendlyName, alarmTripType }
DESCRIPTION "Source B Active Set Point Sensor Clear"
::= 21910

cmDstsPowerStatusACLEAR TRAP-TYPE
ENTERPRISE itwatchdogs
VARIABLES { dstsPowerStatusA, dstsName, productFriendlyName, alarmTripType }
DESCRIPTION "Source A Power Qualilty Active Set Point Sensor Clear"
::= 21911

cmDstsPowerStatusBCLEAR TRAP-TYPE
ENTERPRISE itwatchdogs
VARIABLES { dstsPowerStatusB, dstsName, productFriendlyName, alarmTripType }
DESCRIPTION "Source B Power Qualilty Active Set Point Sensor Clear"
::= 21912

cmDstsSourceATempCCLEAR TRAP-TYPE
ENTERPRISE itwatchdogs
VARIABLES { dstsSourceATempC, dstsName, productFriendlyName, alarmTripType }
DESCRIPTION "Source A Temp Sensor Clear"
::= 21913

cmDstsSourceBTempCCLEAR TRAP-TYPE
ENTERPRISE itwatchdogs
VARIABLES { dstsSourceBTempC, dstsName, productFriendlyName, alarmTripType }
DESCRIPTION "Source B Temp Sensor Clear"
::= 21914

cmCpmSensorStatusCLEAR TRAP-TYPE
ENTERPRISE itwatchdogs
VARIABLES { cpmSensorStatus, cpmSensorName, productFriendlyName, alarmTripType }
DESCRIPTION "City Power sensor Clear Trap"
::= 22005

cmSmokeAlarmStatusCLEAR TRAP-TYPE
ENTERPRISE itwatchdogs
VARIABLES { smokeAlarmStatus, smokeAlarmName, productFriendlyName, alarmTripType }
DESCRIPTION "Smoke alarm Clear Trap"
::= 22105

cmNeg48VdcSensorVoltageCLEAR TRAP-TYPE
ENTERPRISE itwatchdogs
VARIABLES { neg48VdcSensorVoltage, neg48VdcSensorName, productFriendlyName, alarmTripType }
DESCRIPTION "-48Vdc Sensor Clear Trap"
::= 22205

cmPos30VdcSensorVoltageCLEAR TRAP-TYPE
ENTERPRISE itwatchdogs
VARIABLES { pos30VdcSensorVoltage, pos30VdcSensorName, productFriendlyName, alarmTripType }
DESCRIPTION "30Vdc Sensor Clear Trap"
::= 22305

cmCtrl3ChIECKWattHrsACLEAR TRAP-TYPE
ENTERPRISE itwatchdogs
VARIABLES { ctrl3ChIECKWattHrsA, ctrl3ChIECName, productFriendlyName, alarmTripType }
DESCRIPTION "Kilo Watt Hours A Clear Trap"
::= 22405

cmCtrl3ChIECVoltsACLEAR TRAP-TYPE
ENTERPRISE itwatchdogs
VARIABLES { ctrl3ChIECVoltsA, ctrl3ChIECName, productFriendlyName, alarmTripType }
DESCRIPTION "Volts A Clear"
::= 22406

cmCtrl3ChIECVoltPkACLEAR TRAP-TYPE
ENTERPRISE itwatchdogs
VARIABLES { ctrl3ChIECVoltPkA, ctrl3ChIECName, productFriendlyName, alarmTripType }
DESCRIPTION "Volt Peak A Clear"
::= 22407

cmCtrl3ChIECAmpsACLEAR TRAP-TYPE
ENTERPRISE itwatchdogs
VARIABLES { ctrl3ChIECAmpsA, ctrl3ChIECName, productFriendlyName, alarmTripType }
DESCRIPTION "Amps A Clear"
::= 22408

cmCtrl3ChIECAmpPkACLEAR TRAP-TYPE
ENTERPRISE itwatchdogs
VARIABLES { ctrl3ChIECAmpPkA, ctrl3ChIECName, productFriendlyName, alarmTripType }
DESCRIPTION "Amps Peak A Clear"
::= 22409

cmCtrl3ChIECRealPowACLEAR TRAP-TYPE
ENTERPRISE itwatchdogs
VARIABLES { ctrl3ChIECRealPowA, ctrl3ChIECName, productFriendlyName, alarmTripType }
DESCRIPTION "Real Power A Clear"
::= 22410

cmCtrl3ChIECAppPowACLEAR TRAP-TYPE
ENTERPRISE itwatchdogs
VARIABLES { ctrl3ChIECAppPowA, ctrl3ChIECName, productFriendlyName, alarmTripType }
DESCRIPTION "Apparent Power A Clear"
::= 22411

cmCtrl3ChIECPwrFactACLEAR TRAP-TYPE
ENTERPRISE itwatchdogs
VARIABLES { ctrl3ChIECPwrFactA, ctrl3ChIECName, productFriendlyName, alarmTripType }
DESCRIPTION "Power Factor A Clear"
::= 22412

cmCtrl3ChIECKWattHrsBCLEAR TRAP-TYPE
ENTERPRISE itwatchdogs
VARIABLES { ctrl3ChIECKWattHrsB, ctrl3ChIECName, productFriendlyName, alarmTripType }
DESCRIPTION "Kilo Watt Hours B Clear Trap"
::= 22413

cmCtrl3ChIECVoltsBCLEAR TRAP-TYPE
ENTERPRISE itwatchdogs
VARIABLES { ctrl3ChIECVoltsB, ctrl3ChIECName, productFriendlyName, alarmTripType }
DESCRIPTION "Volts B Clear"
::= 22414

cmCtrl3ChIECVoltPkBCLEAR TRAP-TYPE
ENTERPRISE itwatchdogs
VARIABLES { ctrl3ChIECVoltPkB, ctrl3ChIECName, productFriendlyName, alarmTripType }
DESCRIPTION "Volt Peak B Clear"
::= 22415

cmCtrl3ChIECAmpsBCLEAR TRAP-TYPE
ENTERPRISE itwatchdogs
VARIABLES { ctrl3ChIECAmpsB, ctrl3ChIECName, productFriendlyName, alarmTripType }
DESCRIPTION "Amps B Clear"
::= 22416

cmCtrl3ChIECAmpPkBCLEAR TRAP-TYPE
ENTERPRISE itwatchdogs
VARIABLES { ctrl3ChIECAmpPkB, ctrl3ChIECName, productFriendlyName, alarmTripType }
DESCRIPTION "Amps Peak B Clear"
::= 22417

cmCtrl3ChIECRealPowBCLEAR TRAP-TYPE
ENTERPRISE itwatchdogs
VARIABLES { ctrl3ChIECRealPowB, ctrl3ChIECName, productFriendlyName, alarmTripType }
DESCRIPTION "Real Power B Clear"
::= 22418

cmCtrl3ChIECAppPowBCLEAR TRAP-TYPE
ENTERPRISE itwatchdogs
VARIABLES { ctrl3ChIECAppPowB, ctrl3ChIECName, productFriendlyName, alarmTripType }
DESCRIPTION "Apparent Power B Clear"
::= 22419

cmCtrl3ChIECPwrFactBCLEAR TRAP-TYPE
ENTERPRISE itwatchdogs
VARIABLES { ctrl3ChIECPwrFactB, ctrl3ChIECName, productFriendlyName, alarmTripType }
DESCRIPTION "Power Factor B Clear"
::= 22420

cmCtrl3ChIECKWattHrsCCLEAR TRAP-TYPE
ENTERPRISE itwatchdogs
VARIABLES { ctrl3ChIECKWattHrsC, ctrl3ChIECName, productFriendlyName, alarmTripType }
DESCRIPTION "Kilo Watt Hours C Clear Trap"
::= 22421

cmCtrl3ChIECVoltsCCLEAR TRAP-TYPE
ENTERPRISE itwatchdogs
VARIABLES { ctrl3ChIECVoltsC, ctrl3ChIECName, productFriendlyName, alarmTripType }
DESCRIPTION "Volts C Clear"
::= 22422

cmCtrl3ChIECVoltPkCCLEAR TRAP-TYPE
ENTERPRISE itwatchdogs
VARIABLES { ctrl3ChIECVoltPkC, ctrl3ChIECName, productFriendlyName, alarmTripType }
DESCRIPTION "Volt Peak C Clear"
::= 22423

cmCtrl3ChIECAmpsCCLEAR TRAP-TYPE
ENTERPRISE itwatchdogs
VARIABLES { ctrl3ChIECAmpsC, ctrl3ChIECName, productFriendlyName, alarmTripType }
DESCRIPTION "Amps C Clear"
::= 22424

cmCtrl3ChIECAmpPkCCLEAR TRAP-TYPE
ENTERPRISE itwatchdogs
VARIABLES { ctrl3ChIECAmpPkC, ctrl3ChIECName, productFriendlyName, alarmTripType }
DESCRIPTION "Amps Peak C Clear"
::= 22425

cmCtrl3ChIECRealPowCCLEAR TRAP-TYPE
ENTERPRISE itwatchdogs
VARIABLES { ctrl3ChIECRealPowC, ctrl3ChIECName, productFriendlyName, alarmTripType }
DESCRIPTION "Real Power C Clear"
::= 22426

cmCtrl3ChIECAppPowCCLEAR TRAP-TYPE
ENTERPRISE itwatchdogs
VARIABLES { ctrl3ChIECAppPowC, ctrl3ChIECName, productFriendlyName, alarmTripType }
DESCRIPTION "Apparent Power C Clear"
::= 22427

cmCtrl3ChIECPwrFactCCLEAR TRAP-TYPE
ENTERPRISE itwatchdogs
VARIABLES { ctrl3ChIECPwrFactC, ctrl3ChIECName, productFriendlyName, alarmTripType }
DESCRIPTION "Power Factor C Clear"
::= 22428

END
