------------------------------------------------------------
-- EMERSON NETWORK POWER
-- SIC MIB
------------------------------------------------------------

ENP-APM-MIB DEFINITIONS ::= BEGIN

IMPORTS
	MODULE-IDENTITY, OBJECT-TYPE, NOTIFICATION-TYPE,
	Integer32, Counter32, enterprises
		FROM SNMPv2-SMI
	TEXTUAL-CONVENTION, DisplayString, DateAndTime
		FROM SNMPv2-TC;
		
		
------------------------------------------------------------
-- Node definitions
------------------------------------------------------------

enp OBJECT IDENTIFIER ::= { enterprises 13400 }

products OBJECT IDENTIFIER ::= { enp 2 }

apmMIB MODULE-IDENTITY
	LAST-UPDATED "200902011512Z"
	ORGANIZATION "
		EMERSON NETWORK POWER (ENP)"
	CONTACT-INFO "
		EMERSON NETWORK POWER"
	DESCRIPTION "
		EMERSON NETWORK POWER (ENP) SIC MIB."
	::= { products 20 }


------------------------------------------------------------
-- Textual conventions
------------------------------------------------------------

Status ::= TEXTUAL-CONVENTION
	STATUS current
	DESCRIPTION "
		The severity of the alarm. One of
		(0) informational
		(1) warning
		(2) critical"
	SYNTAX INTEGER {
		informational(0),
		warning(1),
		critical(2) }
		
StatusChange ::= TEXTUAL-CONVENTION
	STATUS current
	DESCRIPTION "
		Indicates 'activated' (0) or 'deactivated' (1) alarm events."
	SYNTAX INTEGER {
		activated(0),
		deactivated(1) }


------------------------------------------------------------
-- 1.1 Identification of the plant { apmMIB 1 }
------------------------------------------------------------

ident OBJECT IDENTIFIER ::= { apmMIB 1 }

identManufacturer OBJECT-TYPE
	SYNTAX DisplayString
	MAX-ACCESS read-only
	STATUS current
	DESCRIPTION "
		The name of the device manufacturer."
	::= { ident 1 }

identModel OBJECT-TYPE
	SYNTAX DisplayString
	MAX-ACCESS read-only
	STATUS current
	DESCRIPTION "
		The manufacturers model designation of the device."
	::= { ident 2 }

identIndex OBJECT-TYPE
	SYNTAX Integer32
	MAX-ACCESS read-write
	STATUS current
	DESCRIPTION "
		The sequence number of the device."
	::= { ident 3 }
	

------------------------------------------------------------
-- 1.2 system values { apmMIB 2 }
------------------------------------------------------------

system OBJECT IDENTIFIER ::= { apmMIB 2 }


-- ------------------------------------------------------------------------ 
-- 1.2.1 the status group
-- ------------------------------------------------------------------------ 

status OBJECT IDENTIFIER ::= { system 1 }

	systemStatus OBJECT-TYPE
		SYNTAX Status
		MAX-ACCESS read-only
		STATUS current
		DESCRIPTION "
			Status of the complete plant (highest alarm). One of
			(0) normal
			(1) warning
			(2) critical"
		::= { status 1 }


-- ------------------------------------------------------------------------ 
-- 1.2.2 the system output group
-- ------------------------------------------------------------------------ 

systemoutput OBJECT IDENTIFIER ::= { system 2 }

    systemoutputAcitvePowerA OBJECT-TYPE
        SYNTAX Integer32
        MAX-ACCESS read-only
        STATUS current
        DESCRIPTION
            "system output Acitve Power A, stored as 0.01 kW."
        ::= { systemoutput 1 }

    systemoutputAcitvePowerB OBJECT-TYPE
        SYNTAX Integer32
        MAX-ACCESS read-only
        STATUS current
        DESCRIPTION
            "system output Acitve Power B, stored as 0.01 kW."
        ::= { systemoutput 2 }

    systemoutputAcitvePowerC OBJECT-TYPE
        SYNTAX Integer32
        MAX-ACCESS read-only
        STATUS current
        DESCRIPTION
            "system output Acitve Power C, stored as 0.01 kW."
        ::= { systemoutput 3 }
        
    systemoutputAppPowerA OBJECT-TYPE
        SYNTAX Integer32
        MAX-ACCESS read-only
        STATUS current
        DESCRIPTION
            "system output App Power A, stored as 0.01 kVA."
        ::= { systemoutput 4 }

    systemoutputAppPowerB OBJECT-TYPE
        SYNTAX Integer32
        MAX-ACCESS read-only
        STATUS current
        DESCRIPTION
            "system output App Power B, stored as 0.01 kVA."
        ::= { systemoutput 5 }

    systemoutputAppPowerC OBJECT-TYPE
        SYNTAX Integer32
        MAX-ACCESS read-only
        STATUS current
        DESCRIPTION
            "system output App Power C, stored as 0.01 kVA."
        ::= { systemoutput 6 }

    systemoutputReactivePowerA OBJECT-TYPE
        SYNTAX Integer32
        MAX-ACCESS read-only
        STATUS current
        DESCRIPTION
            "system output Reactive Power A, stored as 0.01 kVAR."
        ::= { systemoutput 7 }

    systemoutputReactivePowerB OBJECT-TYPE
        SYNTAX Integer32
        MAX-ACCESS read-only
        STATUS current
        DESCRIPTION
            "system output Reactive Power B, stored as 0.01 kVAR."
        ::= { systemoutput 8 }

    systemoutputReactivePowerC OBJECT-TYPE
        SYNTAX Integer32
        MAX-ACCESS read-only
        STATUS current
        DESCRIPTION
            "system output Reactive Power C, stored as 0.01 kVAR."
        ::= { systemoutput 9 }



-- ------------------------------------------------------------------------ 
-- 1.2.3 the systemparam group
-- ------------------------------------------------------------------------ 

systemparam OBJECT IDENTIFIER ::= { system 3 }


    systemparamUnitModules OBJECT-TYPE
        SYNTAX Integer32
        MAX-ACCESS read-only
        STATUS current
        DESCRIPTION
            "system param Unit Modules, stored as 0.01."
        ::= { systemparam 1 }

    systemparamUnitCapacity OBJECT-TYPE
        SYNTAX Integer32
        MAX-ACCESS read-only
        STATUS current
        DESCRIPTION
            "system param Unit Capacity, stored as 0.01 kVA."
        ::= { systemparam 2 }

    systemparamModuleCapacity OBJECT-TYPE
        SYNTAX Integer32
        MAX-ACCESS read-only
        STATUS current
        DESCRIPTION
            "system param Module Capacity, stored as 0.01 kVA."
        ::= { systemparam 3 }

-- ------------------------------------------------------------------------ 
-- 1.2.4 the main group
-- ------------------------------------------------------------------------ 

analogdata OBJECT IDENTIFIER ::= { system 4 }

    inputPhaseVoltageA OBJECT-TYPE
        SYNTAX Integer32
        MAX-ACCESS read-only
        STATUS current
        DESCRIPTION
            "Input Phase Voltage A, stored as 0.01 V."
        ::= { analogdata 1 }

    inputPhaseVoltageB OBJECT-TYPE
        SYNTAX Integer32
        MAX-ACCESS read-only
        STATUS current
        DESCRIPTION
            "Input Phase Voltage B, stored as 0.01 V."
        ::= { analogdata 2 }

    inputPhaseVoltageC OBJECT-TYPE
        SYNTAX Integer32
        MAX-ACCESS read-only
        STATUS current
        DESCRIPTION
            "Input Phase Voltage C, stored as 0.01 V."
        ::= { analogdata 3 }

    inputLineVoltageA OBJECT-TYPE
        SYNTAX Integer32
        MAX-ACCESS read-only
        STATUS current
        DESCRIPTION
            "Input Line Voltage A, stored as 0.01 V."
        ::= { analogdata 4 }

    inputLineVoltageB OBJECT-TYPE
        SYNTAX Integer32
        MAX-ACCESS read-only
        STATUS current
        DESCRIPTION
            "Input Line Voltage B, stored as 0.01 V."
        ::= { analogdata 5 }

    inputLineVoltageC OBJECT-TYPE
        SYNTAX Integer32
        MAX-ACCESS read-only
        STATUS current
        DESCRIPTION
            "Input Line Voltage C, stored as 0.01 V."
        ::= { analogdata 6 }

    inputCurrentA OBJECT-TYPE
        SYNTAX Integer32
        MAX-ACCESS read-only
        STATUS current
        DESCRIPTION
            "Input Current A, stored as 0.01 A."
        ::= { analogdata 7 }

    inputCurrentB OBJECT-TYPE
        SYNTAX Integer32
        MAX-ACCESS read-only
        STATUS current
        DESCRIPTION
            "Input Current B, stored as 0.01 A."
        ::= { analogdata 8 }

    inputCurrentC OBJECT-TYPE
        SYNTAX Integer32
        MAX-ACCESS read-only
        STATUS current
        DESCRIPTION
            "Input Current C, stored as 0.01 A."
        ::= { analogdata 9 }

    inputFrequency OBJECT-TYPE
        SYNTAX Integer32
        MAX-ACCESS read-only
        STATUS current
        DESCRIPTION
            "Input Frequency, stored as 0.01 Hz."
        ::= { analogdata 10 }

    inputPowerFactorA OBJECT-TYPE
        SYNTAX Integer32
        MAX-ACCESS read-only
        STATUS current
        DESCRIPTION
            "Input Power Factor A, stored as 0.01."
        ::= { analogdata 11 }

    inputPowerFactorB OBJECT-TYPE
        SYNTAX Integer32
        MAX-ACCESS read-only
        STATUS current
        DESCRIPTION
            "Input Power Factor B, stored as 0.01."
        ::= { analogdata 12 }

    inputPowerFactorC OBJECT-TYPE
        SYNTAX Integer32
        MAX-ACCESS read-only
        STATUS current
        DESCRIPTION
            "Input Power Factor C, stored as 0.01."
        ::= { analogdata 13 }

    dCBus1Voltage OBJECT-TYPE
        SYNTAX Integer32
        MAX-ACCESS read-only
        STATUS current
        DESCRIPTION
            "DCBus1 Voltage, stored as 0.01 V."
        ::= { analogdata 14 }

    dCBus2Voltage OBJECT-TYPE
        SYNTAX Integer32
        MAX-ACCESS read-only
        STATUS current
        DESCRIPTION
            "DCBus2 Voltage, stored as 0.01 V."
        ::= { analogdata 15 }

    outputVoltageA OBJECT-TYPE
    	SYNTAX Integer32
    	MAX-ACCESS read-only
        STATUS current
        DESCRIPTION
            "Output voltage A, stored as 0.01 V."
        ::= { analogdata 16 }

    outputVoltageB OBJECT-TYPE
    	SYNTAX Integer32
    	MAX-ACCESS read-only
        STATUS current
        DESCRIPTION
            "Output voltage B, stored as 0.01 V."
        ::= { analogdata 17 }

    outputVoltageC OBJECT-TYPE
    	SYNTAX Integer32
    	MAX-ACCESS read-only
        STATUS current
        DESCRIPTION
            "Output voltage C, stored as 0.01 V."
        ::= { analogdata 18 }

    outputCurrentA OBJECT-TYPE
        SYNTAX Integer32
        MAX-ACCESS read-only
        STATUS current
        DESCRIPTION
            "Output current A, stored as 0.01 A."
        ::= { analogdata 19 }

    outputCurrentB OBJECT-TYPE
        SYNTAX Integer32
        MAX-ACCESS read-only
        STATUS current
        DESCRIPTION
            "Output current B, stored as 0.01 A."
        ::= { analogdata 20 }

    outputCurrentC OBJECT-TYPE
        SYNTAX Integer32
        MAX-ACCESS read-only
        STATUS current
        DESCRIPTION
            "Output current C, stored as 0.01 A."
        ::= { analogdata 21 }

    outputFrequency OBJECT-TYPE
        SYNTAX Integer32
        MAX-ACCESS read-only
        STATUS current
        DESCRIPTION
            "Output Frequency, stored as 0.01 Hz."
        ::= { analogdata 22 }

    outputPowerFactorA OBJECT-TYPE
        SYNTAX Integer32
        MAX-ACCESS read-only
        STATUS current
        DESCRIPTION
            "Output Power Factor A, stored as 0.01."
        ::= { analogdata 23 }

    outputPowerFactorB OBJECT-TYPE
        SYNTAX Integer32
        MAX-ACCESS read-only
        STATUS current
        DESCRIPTION
            "Output Power Factor B, stored as 0.01."
        ::= { analogdata 24 }

    outputPowerFactorC OBJECT-TYPE
        SYNTAX Integer32
        MAX-ACCESS read-only
        STATUS current
        DESCRIPTION
            "Output Power Factor C, stored as 0.01."
        ::= { analogdata 25 }

    outputAcitvePowerA OBJECT-TYPE
        SYNTAX Integer32
        MAX-ACCESS read-only
        STATUS current
        DESCRIPTION
            "Output Acitve Power A, stored as 0.01 kW."
        ::= { analogdata 26 }

    outputAcitvePowerB OBJECT-TYPE
        SYNTAX Integer32
        MAX-ACCESS read-only
        STATUS current
        DESCRIPTION
            "Output Acitve Power B, stored as 0.01 kW."
        ::= { analogdata 27 }

    outputAcitvePowerC OBJECT-TYPE
        SYNTAX Integer32
        MAX-ACCESS read-only
        STATUS current
        DESCRIPTION
            "Output Acitve Power C, stored as 0.01 kW."
        ::= { analogdata 28 }

    outputReactivePowerA OBJECT-TYPE
        SYNTAX Integer32
        MAX-ACCESS read-only
        STATUS current
        DESCRIPTION
            "Output Reactive Power A, stored as 0.01 KVAR."
        ::= { analogdata 29 }

    outputReactivePowerB OBJECT-TYPE
        SYNTAX Integer32
        MAX-ACCESS read-only
        STATUS current
        DESCRIPTION
            "Output Reactive Power B, stored as 0.01 KVAR."
        ::= { analogdata 30 }

    outputReactivePowerC OBJECT-TYPE
        SYNTAX Integer32
        MAX-ACCESS read-only
        STATUS current
        DESCRIPTION
            "Output Reactive Power C, stored as 0.01 KVAR."
        ::= { analogdata 31 }

    outputAppPowerA OBJECT-TYPE
        SYNTAX Integer32
        MAX-ACCESS read-only
        STATUS current
        DESCRIPTION
            "Output App Power A, stored as 0.01 kVA."
        ::= { analogdata 32 }

    outputAppPowerB OBJECT-TYPE
        SYNTAX Integer32
        MAX-ACCESS read-only
        STATUS current
        DESCRIPTION
            "Output App Power B, stored as 0.01 kVA."
        ::= { analogdata 33 }

    outputAppPowerC OBJECT-TYPE
        SYNTAX Integer32
        MAX-ACCESS read-only
        STATUS current
        DESCRIPTION
            "Output App Power C, stored as 0.01 kVA."
        ::= { analogdata 34 }

    outputLoadA OBJECT-TYPE
        SYNTAX Integer32
        MAX-ACCESS read-only
        STATUS current
        DESCRIPTION
            "Output Load A, stored as 0.01 %."
        ::= { analogdata 35 }

    outputLoadB OBJECT-TYPE
        SYNTAX Integer32
        MAX-ACCESS read-only
        STATUS current
        DESCRIPTION
            "Output Load B, stored as 0.01 %."
        ::= { analogdata 36 }

    outputLoadC OBJECT-TYPE
        SYNTAX Integer32
        MAX-ACCESS read-only
        STATUS current
        DESCRIPTION
            "Output Load C, stored as 0.01 %."
        ::= { analogdata 37 }

    outputCrestFactorA OBJECT-TYPE
        SYNTAX Integer32
        MAX-ACCESS read-only
        STATUS current
        DESCRIPTION
            "Output Crest Factor A, stored as 0.01 ."
        ::= { analogdata 38 }

    outputCrestFactorB OBJECT-TYPE
        SYNTAX Integer32
        MAX-ACCESS read-only
        STATUS current
        DESCRIPTION
            "Output Crest Factor B, stored as 0.01 ."
        ::= { analogdata 39 }

    outputCrestFactorC OBJECT-TYPE
        SYNTAX Integer32
        MAX-ACCESS read-only
        STATUS current
        DESCRIPTION
            "Output Crest Factor C, stored as 0.01 ."
        ::= { analogdata 40 }

    bypassVoltageA OBJECT-TYPE
        SYNTAX Integer32
        MAX-ACCESS read-only
        STATUS current
        DESCRIPTION
            "Bypass Voltage A, stored as 0.01 V."
        ::= { analogdata 41 }

    bypassVoltageB OBJECT-TYPE
        SYNTAX Integer32
        MAX-ACCESS read-only
        STATUS current
        DESCRIPTION
            "Bypass Voltage B, stored as 0.01 V."
        ::= { analogdata 42 }

    bypassVoltageC OBJECT-TYPE
        SYNTAX Integer32
        MAX-ACCESS read-only
        STATUS current
        DESCRIPTION
            "Bypass Voltage C, stored as 0.01 V."
        ::= { analogdata 43 }

    bypassFrequency OBJECT-TYPE
        SYNTAX Integer32
        MAX-ACCESS read-only
        STATUS current
        DESCRIPTION
            "Bypass Frequency, stored as 0.01 Hz."
        ::= { analogdata 44 }

    positiveBatteryVoltage OBJECT-TYPE
        SYNTAX Integer32
        MAX-ACCESS read-only
        STATUS current
        DESCRIPTION
            "positive Battery Voltage, stored as 0.01 V."
        ::= { analogdata 45 }

    positiveBatteryCurrent OBJECT-TYPE
        SYNTAX Integer32
        MAX-ACCESS read-only
        STATUS current
        DESCRIPTION
            "positive Battery Current, stored as 0.01 A."
        ::= { analogdata 46 }

    negativeBatteryVoltage OBJECT-TYPE
        SYNTAX Integer32
        MAX-ACCESS read-only
        STATUS current
        DESCRIPTION
            "negative Battery Voltage, stored as 0.01 V."
        ::= { analogdata 47 }

    negativeBatteryCurrent OBJECT-TYPE
        SYNTAX Integer32
        MAX-ACCESS read-only
        STATUS current
        DESCRIPTION
            "negative Battery Current, stored as 0.01 A."
        ::= { analogdata 48 }

    batteryAgingRate OBJECT-TYPE
        SYNTAX Integer32
        MAX-ACCESS read-only
        STATUS current
        DESCRIPTION
            "Battery Aging Rate, stored as 0.01."
        ::= { analogdata 49 }

    batteryRemainsTime OBJECT-TYPE
        SYNTAX Integer32
        MAX-ACCESS read-only
        STATUS current
        DESCRIPTION
            "Battery Remains Time, stored as 0.01 Hour."
        ::= { analogdata 50 }

    batteryTemperature OBJECT-TYPE
        SYNTAX Integer32
        MAX-ACCESS read-only
        STATUS current
        DESCRIPTION
            "Battery Temperature, stored as 0.01 &deg;C."
        ::= { analogdata 51 }

    batteryEnvironmentTemperature OBJECT-TYPE
        SYNTAX Integer32
        MAX-ACCESS read-only
        STATUS current
        DESCRIPTION
            "Battery Environment Temperature, stored as 0.01 &deg;C."
        ::= { analogdata 52 }


analogdata1 OBJECT IDENTIFIER ::= { system 5 }

    inputPhaseVoltageA1 OBJECT-TYPE
        SYNTAX Integer32
        MAX-ACCESS read-only
        STATUS current
        DESCRIPTION
            "Input Phase Voltage A, stored as 0.01 V."
        ::= { analogdata1 1 }

    inputPhaseVoltageB1 OBJECT-TYPE
        SYNTAX Integer32
        MAX-ACCESS read-only
        STATUS current
        DESCRIPTION
            "Input Phase Voltage B, stored as 0.01 V."
        ::= { analogdata1 2 }

    inputPhaseVoltageC1 OBJECT-TYPE
        SYNTAX Integer32
        MAX-ACCESS read-only
        STATUS current
        DESCRIPTION
            "Input Phase Voltage C, stored as 0.01 V."
        ::= { analogdata1 3 }

    inputLineVoltageA1 OBJECT-TYPE
        SYNTAX Integer32
        MAX-ACCESS read-only
        STATUS current
        DESCRIPTION
            "Input Line Voltage A, stored as 0.01 V."
        ::= { analogdata1 4 }

    inputLineVoltageB1 OBJECT-TYPE
        SYNTAX Integer32
        MAX-ACCESS read-only
        STATUS current
        DESCRIPTION
            "Input Line Voltage B, stored as 0.01 V."
        ::= { analogdata1 5 }

    inputLineVoltageC1 OBJECT-TYPE
        SYNTAX Integer32
        MAX-ACCESS read-only
        STATUS current
        DESCRIPTION
            "Input Line Voltage C, stored as 0.01 V."
        ::= { analogdata1 6 }

    inputCurrentA1 OBJECT-TYPE
        SYNTAX Integer32
        MAX-ACCESS read-only
        STATUS current
        DESCRIPTION
            "Input Current A, stored as 0.01 A."
        ::= { analogdata1 7 }

    inputCurrentB1 OBJECT-TYPE
        SYNTAX Integer32
        MAX-ACCESS read-only
        STATUS current
        DESCRIPTION
            "Input Current B, stored as 0.01 A."
        ::= { analogdata1 8 }

    inputCurrentC1 OBJECT-TYPE
        SYNTAX Integer32
        MAX-ACCESS read-only
        STATUS current
        DESCRIPTION
            "Input Current C, stored as 0.01 A."
        ::= { analogdata1 9 }

    inputFrequency1 OBJECT-TYPE
        SYNTAX Integer32
        MAX-ACCESS read-only
        STATUS current
        DESCRIPTION
            "Input Frequency, stored as 0.01 Hz."
        ::= { analogdata1 10 }

    inputPowerFactorA1 OBJECT-TYPE
        SYNTAX Integer32
        MAX-ACCESS read-only
        STATUS current
        DESCRIPTION
            "Input Power Factor A, stored as 0.01."
        ::= { analogdata1 11 }

    inputPowerFactorB1 OBJECT-TYPE
        SYNTAX Integer32
        MAX-ACCESS read-only
        STATUS current
        DESCRIPTION
            "Input Power Factor B, stored as 0.01."
        ::= { analogdata1 12 }

    inputPowerFactorC1 OBJECT-TYPE
        SYNTAX Integer32
        MAX-ACCESS read-only
        STATUS current
        DESCRIPTION
            "Input Power Factor C, stored as 0.01."
        ::= { analogdata1 13 }

    dCBus1Voltage1 OBJECT-TYPE
        SYNTAX Integer32
        MAX-ACCESS read-only
        STATUS current
        DESCRIPTION
            "DCBus1 Voltage, stored as 0.01 V."
        ::= { analogdata1 14 }

    dCBus2Voltage1 OBJECT-TYPE
        SYNTAX Integer32
        MAX-ACCESS read-only
        STATUS current
        DESCRIPTION
            "DCBus2 Voltage, stored as 0.01 V."
        ::= { analogdata1 15 }

    outputVoltageA1 OBJECT-TYPE
    	SYNTAX Integer32
    	MAX-ACCESS read-only
        STATUS current
        DESCRIPTION
            "Output voltage A, stored as 0.01 V."
        ::= { analogdata1 16 }

    outputVoltageB1 OBJECT-TYPE
    	SYNTAX Integer32
    	MAX-ACCESS read-only
        STATUS current
        DESCRIPTION
            "Output voltage B, stored as 0.01 V."
        ::= { analogdata1 17 }

    outputVoltageC1 OBJECT-TYPE
    	SYNTAX Integer32
    	MAX-ACCESS read-only
        STATUS current
        DESCRIPTION
            "Output voltage C, stored as 0.01 V."
        ::= { analogdata1 18 }

    outputCurrentA1 OBJECT-TYPE
        SYNTAX Integer32
        MAX-ACCESS read-only
        STATUS current
        DESCRIPTION
            "Output current A, stored as 0.01 A."
        ::= { analogdata1 19 }

    outputCurrentB1 OBJECT-TYPE
        SYNTAX Integer32
        MAX-ACCESS read-only
        STATUS current
        DESCRIPTION
            "Output current B, stored as 0.01 A."
        ::= { analogdata1 20 }

    outputCurrentC1 OBJECT-TYPE
        SYNTAX Integer32
        MAX-ACCESS read-only
        STATUS current
        DESCRIPTION
            "Output current C, stored as 0.01 A."
        ::= { analogdata1 21 }

    outputFrequency1 OBJECT-TYPE
        SYNTAX Integer32
        MAX-ACCESS read-only
        STATUS current
        DESCRIPTION
            "Output Frequency, stored as 0.01 Hz."
        ::= { analogdata1 22 }

    outputPowerFactorA1 OBJECT-TYPE
        SYNTAX Integer32
        MAX-ACCESS read-only
        STATUS current
        DESCRIPTION
            "Output Power Factor A, stored as 0.01."
        ::= { analogdata1 23 }

    outputPowerFactorB1 OBJECT-TYPE
        SYNTAX Integer32
        MAX-ACCESS read-only
        STATUS current
        DESCRIPTION
            "Output Power Factor B, stored as 0.01."
        ::= { analogdata1 24 }

    outputPowerFactorC1 OBJECT-TYPE
        SYNTAX Integer32
        MAX-ACCESS read-only
        STATUS current
        DESCRIPTION
            "Output Power Factor C, stored as 0.01."
        ::= { analogdata1 25 }

    outputAcitvePowerA1 OBJECT-TYPE
        SYNTAX Integer32
        MAX-ACCESS read-only
        STATUS current
        DESCRIPTION
            "Output Acitve Power A, stored as 0.01 kW."
        ::= { analogdata1 26 }

    outputAcitvePowerB1 OBJECT-TYPE
        SYNTAX Integer32
        MAX-ACCESS read-only
        STATUS current
        DESCRIPTION
            "Output Acitve Power B, stored as 0.01 kW."
        ::= { analogdata1 27 }

    outputAcitvePowerC1 OBJECT-TYPE
        SYNTAX Integer32
        MAX-ACCESS read-only
        STATUS current
        DESCRIPTION
            "Output Acitve Power C, stored as 0.01 kW."
        ::= { analogdata1 28 }

    outputReactivePowerA1 OBJECT-TYPE
        SYNTAX Integer32
        MAX-ACCESS read-only
        STATUS current
        DESCRIPTION
            "Output Reactive Power A, stored as 0.01 KVAR."
        ::= { analogdata1 29 }

    outputReactivePowerB1 OBJECT-TYPE
        SYNTAX Integer32
        MAX-ACCESS read-only
        STATUS current
        DESCRIPTION
            "Output Reactive Power B, stored as 0.01 KVAR."
        ::= { analogdata1 30 }

    outputReactivePowerC1 OBJECT-TYPE
        SYNTAX Integer32
        MAX-ACCESS read-only
        STATUS current
        DESCRIPTION
            "Output Reactive Power C, stored as 0.01 KVAR."
        ::= { analogdata1 31 }

    outputAppPowerA1 OBJECT-TYPE
        SYNTAX Integer32
        MAX-ACCESS read-only
        STATUS current
        DESCRIPTION
            "Output App Power A, stored as 0.01 kVA."
        ::= { analogdata1 32 }

    outputAppPowerB1 OBJECT-TYPE
        SYNTAX Integer32
        MAX-ACCESS read-only
        STATUS current
        DESCRIPTION
            "Output App Power B, stored as 0.01 kVA."
        ::= { analogdata1 33 }

    outputAppPowerC1 OBJECT-TYPE
        SYNTAX Integer32
        MAX-ACCESS read-only
        STATUS current
        DESCRIPTION
            "Output App Power C, stored as 0.01 kVA."
        ::= { analogdata1 34 }

    outputLoadA1 OBJECT-TYPE
        SYNTAX Integer32
        MAX-ACCESS read-only
        STATUS current
        DESCRIPTION
            "Output Load A, stored as 0.01 %."
        ::= { analogdata1 35 }

    outputLoadB1 OBJECT-TYPE
        SYNTAX Integer32
        MAX-ACCESS read-only
        STATUS current
        DESCRIPTION
            "Output Load B, stored as 0.01 %."
        ::= { analogdata1 36 }

    outputLoadC1 OBJECT-TYPE
        SYNTAX Integer32
        MAX-ACCESS read-only
        STATUS current
        DESCRIPTION
            "Output Load C, stored as 0.01 %."
        ::= { analogdata1 37 }

    outputCrestFactorA1 OBJECT-TYPE
        SYNTAX Integer32
        MAX-ACCESS read-only
        STATUS current
        DESCRIPTION
            "Output Crest Factor A, stored as 0.01 ."
        ::= { analogdata1 38 }

    outputCrestFactorB1 OBJECT-TYPE
        SYNTAX Integer32
        MAX-ACCESS read-only
        STATUS current
        DESCRIPTION
            "Output Crest Factor B, stored as 0.01 ."
        ::= { analogdata1 39 }

    outputCrestFactorC1 OBJECT-TYPE
        SYNTAX Integer32
        MAX-ACCESS read-only
        STATUS current
        DESCRIPTION
            "Output Crest Factor C, stored as 0.01 ."
        ::= { analogdata1 40 }

    bypassVoltageA1 OBJECT-TYPE
        SYNTAX Integer32
        MAX-ACCESS read-only
        STATUS current
        DESCRIPTION
            "Bypass Voltage A, stored as 0.01 V."
        ::= { analogdata1 41 }

    bypassVoltageB1 OBJECT-TYPE
        SYNTAX Integer32
        MAX-ACCESS read-only
        STATUS current
        DESCRIPTION
            "Bypass Voltage B, stored as 0.01 V."
        ::= { analogdata1 42 }

    bypassVoltageC1 OBJECT-TYPE
        SYNTAX Integer32
        MAX-ACCESS read-only
        STATUS current
        DESCRIPTION
            "Bypass Voltage C, stored as 0.01 V."
        ::= { analogdata1 43 }

    bypassFrequency1 OBJECT-TYPE
        SYNTAX Integer32
        MAX-ACCESS read-only
        STATUS current
        DESCRIPTION
            "Bypass Frequency, stored as 0.01 Hz."
        ::= { analogdata1 44 }

    positiveBatteryVoltage1 OBJECT-TYPE
        SYNTAX Integer32
        MAX-ACCESS read-only
        STATUS current
        DESCRIPTION
            "positive Battery Voltage, stored as 0.01 V."
        ::= { analogdata1 45 }

    positiveBatteryCurrent1 OBJECT-TYPE
        SYNTAX Integer32
        MAX-ACCESS read-only
        STATUS current
        DESCRIPTION
            "positive Battery Current, stored as 0.01 A."
        ::= { analogdata1 46 }

    negativeBatteryVoltage1 OBJECT-TYPE
        SYNTAX Integer32
        MAX-ACCESS read-only
        STATUS current
        DESCRIPTION
            "negative Battery Voltage, stored as 0.01 V."
        ::= { analogdata1 47 }

    negativeBatteryCurrent1 OBJECT-TYPE
        SYNTAX Integer32
        MAX-ACCESS read-only
        STATUS current
        DESCRIPTION
            "negative Battery Current, stored as 0.01 A."
        ::= { analogdata1 48 }

    batteryAgingRate1 OBJECT-TYPE
        SYNTAX Integer32
        MAX-ACCESS read-only
        STATUS current
        DESCRIPTION
            "Battery Aging Rate, stored as 0.01."
        ::= { analogdata1 49 }

    batteryRemainsTime1 OBJECT-TYPE
        SYNTAX Integer32
        MAX-ACCESS read-only
        STATUS current
        DESCRIPTION
            "Battery Remains Time, stored as 0.01 Hour."
        ::= { analogdata1 50 }

    batteryTemperature1 OBJECT-TYPE
        SYNTAX Integer32
        MAX-ACCESS read-only
        STATUS current
        DESCRIPTION
            "Battery Temperature, stored as 0.01 &deg;C."
        ::= { analogdata1 51 }

    batteryEnvironmentTemperature1 OBJECT-TYPE
        SYNTAX Integer32
        MAX-ACCESS read-only
        STATUS current
        DESCRIPTION
            "Battery Environment Temperature, stored as 0.01 &deg;C."
        ::= { analogdata1 52 }
        
analogdata2 OBJECT IDENTIFIER ::= { system 6 }

    inputPhaseVoltageA2 OBJECT-TYPE
        SYNTAX Integer32
        MAX-ACCESS read-only
        STATUS current
        DESCRIPTION
            "Input Phase Voltage A, stored as 0.01 V."
        ::= { analogdata2 1 }

    inputPhaseVoltageB2 OBJECT-TYPE
        SYNTAX Integer32
        MAX-ACCESS read-only
        STATUS current
        DESCRIPTION
            "Input Phase Voltage B, stored as 0.01 V."
        ::= { analogdata2 2 }

    inputPhaseVoltageC2 OBJECT-TYPE
        SYNTAX Integer32
        MAX-ACCESS read-only
        STATUS current
        DESCRIPTION
            "Input Phase Voltage C, stored as 0.01 V."
        ::= { analogdata2 3 }

    inputLineVoltageA2 OBJECT-TYPE
        SYNTAX Integer32
        MAX-ACCESS read-only
        STATUS current
        DESCRIPTION
            "Input Line Voltage A, stored as 0.01 V."
        ::= { analogdata2 4 }

    inputLineVoltageB2 OBJECT-TYPE
        SYNTAX Integer32
        MAX-ACCESS read-only
        STATUS current
        DESCRIPTION
            "Input Line Voltage B, stored as 0.01 V."
        ::= { analogdata2 5 }

    inputLineVoltageC2 OBJECT-TYPE
        SYNTAX Integer32
        MAX-ACCESS read-only
        STATUS current
        DESCRIPTION
            "Input Line Voltage C, stored as 0.01 V."
        ::= { analogdata2 6 }

    inputCurrentA2 OBJECT-TYPE
        SYNTAX Integer32
        MAX-ACCESS read-only
        STATUS current
        DESCRIPTION
            "Input Current A, stored as 0.01 A."
        ::= { analogdata2 7 }

    inputCurrentB2 OBJECT-TYPE
        SYNTAX Integer32
        MAX-ACCESS read-only
        STATUS current
        DESCRIPTION
            "Input Current B, stored as 0.01 A."
        ::= { analogdata2 8 }

    inputCurrentC2 OBJECT-TYPE
        SYNTAX Integer32
        MAX-ACCESS read-only
        STATUS current
        DESCRIPTION
            "Input Current C, stored as 0.01 A."
        ::= { analogdata2 9 }

    inputFrequency2 OBJECT-TYPE
        SYNTAX Integer32
        MAX-ACCESS read-only
        STATUS current
        DESCRIPTION
            "Input Frequency, stored as 0.01 Hz."
        ::= { analogdata2 10 }

    inputPowerFactorA2 OBJECT-TYPE
        SYNTAX Integer32
        MAX-ACCESS read-only
        STATUS current
        DESCRIPTION
            "Input Power Factor A, stored as 0.01."
        ::= { analogdata2 11 }

    inputPowerFactorB2 OBJECT-TYPE
        SYNTAX Integer32
        MAX-ACCESS read-only
        STATUS current
        DESCRIPTION
            "Input Power Factor B, stored as 0.01."
        ::= { analogdata2 12 }

    inputPowerFactorC2 OBJECT-TYPE
        SYNTAX Integer32
        MAX-ACCESS read-only
        STATUS current
        DESCRIPTION
            "Input Power Factor C, stored as 0.01."
        ::= { analogdata2 13 }

    dCBus1Voltage2 OBJECT-TYPE
        SYNTAX Integer32
        MAX-ACCESS read-only
        STATUS current
        DESCRIPTION
            "DCBus1 Voltage, stored as 0.01 V."
        ::= { analogdata2 14 }

    dCBus2Voltage2 OBJECT-TYPE
        SYNTAX Integer32
        MAX-ACCESS read-only
        STATUS current
        DESCRIPTION
            "DCBus2 Voltage, stored as 0.01 V."
        ::= { analogdata2 15 }

    outputVoltageA2 OBJECT-TYPE
    	SYNTAX Integer32
    	MAX-ACCESS read-only
        STATUS current
        DESCRIPTION
            "Output voltage A, stored as 0.01 V."
        ::= { analogdata2 16 }

    outputVoltageB2 OBJECT-TYPE
    	SYNTAX Integer32
    	MAX-ACCESS read-only
        STATUS current
        DESCRIPTION
            "Output voltage B, stored as 0.01 V."
        ::= { analogdata2 17 }

    outputVoltageC2 OBJECT-TYPE
    	SYNTAX Integer32
    	MAX-ACCESS read-only
        STATUS current
        DESCRIPTION
            "Output voltage C, stored as 0.01 V."
        ::= { analogdata2 18 }

    outputCurrentA2 OBJECT-TYPE
        SYNTAX Integer32
        MAX-ACCESS read-only
        STATUS current
        DESCRIPTION
            "Output current A, stored as 0.01 A."
        ::= { analogdata2 19 }

    outputCurrentB2 OBJECT-TYPE
        SYNTAX Integer32
        MAX-ACCESS read-only
        STATUS current
        DESCRIPTION
            "Output current B, stored as 0.01 A."
        ::= { analogdata2 20 }

    outputCurrentC2 OBJECT-TYPE
        SYNTAX Integer32
        MAX-ACCESS read-only
        STATUS current
        DESCRIPTION
            "Output current C, stored as 0.01 A."
        ::= { analogdata2 21 }

    outputFrequency2 OBJECT-TYPE
        SYNTAX Integer32
        MAX-ACCESS read-only
        STATUS current
        DESCRIPTION
            "Output Frequency, stored as 0.01 Hz."
        ::= { analogdata2 22 }

    outputPowerFactorA2 OBJECT-TYPE
        SYNTAX Integer32
        MAX-ACCESS read-only
        STATUS current
        DESCRIPTION
            "Output Power Factor A, stored as 0.01."
        ::= { analogdata2 23 }

    outputPowerFactorB2 OBJECT-TYPE
        SYNTAX Integer32
        MAX-ACCESS read-only
        STATUS current
        DESCRIPTION
            "Output Power Factor B, stored as 0.01."
        ::= { analogdata2 24 }

    outputPowerFactorC2 OBJECT-TYPE
        SYNTAX Integer32
        MAX-ACCESS read-only
        STATUS current
        DESCRIPTION
            "Output Power Factor C, stored as 0.01."
        ::= { analogdata2 25 }

    outputAcitvePowerA2 OBJECT-TYPE
        SYNTAX Integer32
        MAX-ACCESS read-only
        STATUS current
        DESCRIPTION
            "Output Acitve Power A, stored as 0.01 kW."
        ::= { analogdata2 26 }

    outputAcitvePowerB2 OBJECT-TYPE
        SYNTAX Integer32
        MAX-ACCESS read-only
        STATUS current
        DESCRIPTION
            "Output Acitve Power B, stored as 0.01 kW."
        ::= { analogdata2 27 }

    outputAcitvePowerC2 OBJECT-TYPE
        SYNTAX Integer32
        MAX-ACCESS read-only
        STATUS current
        DESCRIPTION
            "Output Acitve Power C, stored as 0.01 kW."
        ::= { analogdata2 28 }

    outputReactivePowerA2 OBJECT-TYPE
        SYNTAX Integer32
        MAX-ACCESS read-only
        STATUS current
        DESCRIPTION
            "Output Reactive Power A, stored as 0.01 KVAR."
        ::= { analogdata2 29 }

    outputReactivePowerB2 OBJECT-TYPE
        SYNTAX Integer32
        MAX-ACCESS read-only
        STATUS current
        DESCRIPTION
            "Output Reactive Power B, stored as 0.01 KVAR."
        ::= { analogdata2 30 }

    outputReactivePowerC2 OBJECT-TYPE
        SYNTAX Integer32
        MAX-ACCESS read-only
        STATUS current
        DESCRIPTION
            "Output Reactive Power C, stored as 0.01 KVAR."
        ::= { analogdata2 31 }

    outputAppPowerA2 OBJECT-TYPE
        SYNTAX Integer32
        MAX-ACCESS read-only
        STATUS current
        DESCRIPTION
            "Output App Power A, stored as 0.01 kVA."
        ::= { analogdata2 32 }

    outputAppPowerB2 OBJECT-TYPE
        SYNTAX Integer32
        MAX-ACCESS read-only
        STATUS current
        DESCRIPTION
            "Output App Power B, stored as 0.01 kVA."
        ::= { analogdata2 33 }

    outputAppPowerC2 OBJECT-TYPE
        SYNTAX Integer32
        MAX-ACCESS read-only
        STATUS current
        DESCRIPTION
            "Output App Power C, stored as 0.01 kVA."
        ::= { analogdata2 34 }

    outputLoadA2 OBJECT-TYPE
        SYNTAX Integer32
        MAX-ACCESS read-only
        STATUS current
        DESCRIPTION
            "Output Load A, stored as 0.01 %."
        ::= { analogdata2 35 }

    outputLoadB2 OBJECT-TYPE
        SYNTAX Integer32
        MAX-ACCESS read-only
        STATUS current
        DESCRIPTION
            "Output Load B, stored as 0.01 %."
        ::= { analogdata2 36 }

    outputLoadC2 OBJECT-TYPE
        SYNTAX Integer32
        MAX-ACCESS read-only
        STATUS current
        DESCRIPTION
            "Output Load C, stored as 0.01 %."
        ::= { analogdata2 37 }

    outputCrestFactorA2 OBJECT-TYPE
        SYNTAX Integer32
        MAX-ACCESS read-only
        STATUS current
        DESCRIPTION
            "Output Crest Factor A, stored as 0.01 ."
        ::= { analogdata2 38 }

    outputCrestFactorB2 OBJECT-TYPE
        SYNTAX Integer32
        MAX-ACCESS read-only
        STATUS current
        DESCRIPTION
            "Output Crest Factor B, stored as 0.01 ."
        ::= { analogdata2 39 }

    outputCrestFactorC2 OBJECT-TYPE
        SYNTAX Integer32
        MAX-ACCESS read-only
        STATUS current
        DESCRIPTION
            "Output Crest Factor C, stored as 0.01 ."
        ::= { analogdata2 40 }

    bypassVoltageA2 OBJECT-TYPE
        SYNTAX Integer32
        MAX-ACCESS read-only
        STATUS current
        DESCRIPTION
            "Bypass Voltage A, stored as 0.01 V."
        ::= { analogdata2 41 }

    bypassVoltageB2 OBJECT-TYPE
        SYNTAX Integer32
        MAX-ACCESS read-only
        STATUS current
        DESCRIPTION
            "Bypass Voltage B, stored as 0.01 V."
        ::= { analogdata2 42 }

    bypassVoltageC2 OBJECT-TYPE
        SYNTAX Integer32
        MAX-ACCESS read-only
        STATUS current
        DESCRIPTION
            "Bypass Voltage C, stored as 0.01 V."
        ::= { analogdata2 43 }

    bypassFrequency2 OBJECT-TYPE
        SYNTAX Integer32
        MAX-ACCESS read-only
        STATUS current
        DESCRIPTION
            "Bypass Frequency, stored as 0.01 Hz."
        ::= { analogdata2 44 }

    positiveBatteryVoltage2 OBJECT-TYPE
        SYNTAX Integer32
        MAX-ACCESS read-only
        STATUS current
        DESCRIPTION
            "positive Battery Voltage, stored as 0.01 V."
        ::= { analogdata2 45 }

    positiveBatteryCurrent2 OBJECT-TYPE
        SYNTAX Integer32
        MAX-ACCESS read-only
        STATUS current
        DESCRIPTION
            "positive Battery Current, stored as 0.01 A."
        ::= { analogdata2 46 }

    negativeBatteryVoltage2 OBJECT-TYPE
        SYNTAX Integer32
        MAX-ACCESS read-only
        STATUS current
        DESCRIPTION
            "negative Battery Voltage, stored as 0.01 V."
        ::= { analogdata2 47 }

    negativeBatteryCurrent2 OBJECT-TYPE
        SYNTAX Integer32
        MAX-ACCESS read-only
        STATUS current
        DESCRIPTION
            "negative Battery Current, stored as 0.01 A."
        ::= { analogdata2 48 }

    batteryAgingRate2 OBJECT-TYPE
        SYNTAX Integer32
        MAX-ACCESS read-only
        STATUS current
        DESCRIPTION
            "Battery Aging Rate, stored as 0.01."
        ::= { analogdata2 49 }

    batteryRemainsTime2 OBJECT-TYPE
        SYNTAX Integer32
        MAX-ACCESS read-only
        STATUS current
        DESCRIPTION
            "Battery Remains Time, stored as 0.01 Hour."
        ::= { analogdata2 50 }

    batteryTemperature2 OBJECT-TYPE
        SYNTAX Integer32
        MAX-ACCESS read-only
        STATUS current
        DESCRIPTION
            "Battery Temperature, stored as 0.01 &deg;C."
        ::= { analogdata2 51 }

    batteryEnvironmentTemperature2 OBJECT-TYPE
        SYNTAX Integer32
        MAX-ACCESS read-only
        STATUS current
        DESCRIPTION
            "Battery Environment Temperature, stored as 0.01 &deg;C."
        ::= { analogdata2 52 }

analogdata3 OBJECT IDENTIFIER ::= { system 7 }

    inputPhaseVoltageA3 OBJECT-TYPE
        SYNTAX Integer32
        MAX-ACCESS read-only
        STATUS current
        DESCRIPTION
            "Input Phase Voltage A, stored as 0.01 V."
        ::= { analogdata3 1 }

    inputPhaseVoltageB3 OBJECT-TYPE
        SYNTAX Integer32
        MAX-ACCESS read-only
        STATUS current
        DESCRIPTION
            "Input Phase Voltage B, stored as 0.01 V."
        ::= { analogdata3 2 }

    inputPhaseVoltageC3 OBJECT-TYPE
        SYNTAX Integer32
        MAX-ACCESS read-only
        STATUS current
        DESCRIPTION
            "Input Phase Voltage C, stored as 0.01 V."
        ::= { analogdata3 3 }

    inputLineVoltageA3 OBJECT-TYPE
        SYNTAX Integer32
        MAX-ACCESS read-only
        STATUS current
        DESCRIPTION
            "Input Line Voltage A, stored as 0.01 V."
        ::= { analogdata3 4 }

    inputLineVoltageB3 OBJECT-TYPE
        SYNTAX Integer32
        MAX-ACCESS read-only
        STATUS current
        DESCRIPTION
            "Input Line Voltage B, stored as 0.01 V."
        ::= { analogdata3 5 }

    inputLineVoltageC3 OBJECT-TYPE
        SYNTAX Integer32
        MAX-ACCESS read-only
        STATUS current
        DESCRIPTION
            "Input Line Voltage C, stored as 0.01 V."
        ::= { analogdata3 6 }

    inputCurrentA3 OBJECT-TYPE
        SYNTAX Integer32
        MAX-ACCESS read-only
        STATUS current
        DESCRIPTION
            "Input Current A, stored as 0.01 A."
        ::= { analogdata3 7 }

    inputCurrentB3 OBJECT-TYPE
        SYNTAX Integer32
        MAX-ACCESS read-only
        STATUS current
        DESCRIPTION
            "Input Current B, stored as 0.01 A."
        ::= { analogdata3 8 }

    inputCurrentC3 OBJECT-TYPE
        SYNTAX Integer32
        MAX-ACCESS read-only
        STATUS current
        DESCRIPTION
            "Input Current C, stored as 0.01 A."
        ::= { analogdata3 9 }

    inputFrequency3 OBJECT-TYPE
        SYNTAX Integer32
        MAX-ACCESS read-only
        STATUS current
        DESCRIPTION
            "Input Frequency, stored as 0.01 Hz."
        ::= { analogdata3 10 }

    inputPowerFactorA3 OBJECT-TYPE
        SYNTAX Integer32
        MAX-ACCESS read-only
        STATUS current
        DESCRIPTION
            "Input Power Factor A, stored as 0.01."
        ::= { analogdata3 11 }

    inputPowerFactorB3 OBJECT-TYPE
        SYNTAX Integer32
        MAX-ACCESS read-only
        STATUS current
        DESCRIPTION
            "Input Power Factor B, stored as 0.01."
        ::= { analogdata3 12 }

    inputPowerFactorC3 OBJECT-TYPE
        SYNTAX Integer32
        MAX-ACCESS read-only
        STATUS current
        DESCRIPTION
            "Input Power Factor C, stored as 0.01."
        ::= { analogdata3 13 }

    dCBus1Voltage3 OBJECT-TYPE
        SYNTAX Integer32
        MAX-ACCESS read-only
        STATUS current
        DESCRIPTION
            "DCBus1 Voltage, stored as 0.01 V."
        ::= { analogdata3 14 }

    dCBus2Voltage3 OBJECT-TYPE
        SYNTAX Integer32
        MAX-ACCESS read-only
        STATUS current
        DESCRIPTION
            "DCBus2 Voltage, stored as 0.01 V."
        ::= { analogdata3 15 }

    outputVoltageA3 OBJECT-TYPE
    	SYNTAX Integer32
    	MAX-ACCESS read-only
        STATUS current
        DESCRIPTION
            "Output voltage A, stored as 0.01 V."
        ::= { analogdata3 16 }

    outputVoltageB3 OBJECT-TYPE
    	SYNTAX Integer32
    	MAX-ACCESS read-only
        STATUS current
        DESCRIPTION
            "Output voltage B, stored as 0.01 V."
        ::= { analogdata3 17 }

    outputVoltageC3 OBJECT-TYPE
    	SYNTAX Integer32
    	MAX-ACCESS read-only
        STATUS current
        DESCRIPTION
            "Output voltage C, stored as 0.01 V."
        ::= { analogdata3 18 }

    outputCurrentA3 OBJECT-TYPE
        SYNTAX Integer32
        MAX-ACCESS read-only
        STATUS current
        DESCRIPTION
            "Output current A, stored as 0.01 A."
        ::= { analogdata3 19 }

    outputCurrentB3 OBJECT-TYPE
        SYNTAX Integer32
        MAX-ACCESS read-only
        STATUS current
        DESCRIPTION
            "Output current B, stored as 0.01 A."
        ::= { analogdata3 20 }

    outputCurrentC3 OBJECT-TYPE
        SYNTAX Integer32
        MAX-ACCESS read-only
        STATUS current
        DESCRIPTION
            "Output current C, stored as 0.01 A."
        ::= { analogdata3 21 }

    outputFrequency3 OBJECT-TYPE
        SYNTAX Integer32
        MAX-ACCESS read-only
        STATUS current
        DESCRIPTION
            "Output Frequency, stored as 0.01 Hz."
        ::= { analogdata3 22 }

    outputPowerFactorA3 OBJECT-TYPE
        SYNTAX Integer32
        MAX-ACCESS read-only
        STATUS current
        DESCRIPTION
            "Output Power Factor A, stored as 0.01."
        ::= { analogdata3 23 }

    outputPowerFactorB3 OBJECT-TYPE
        SYNTAX Integer32
        MAX-ACCESS read-only
        STATUS current
        DESCRIPTION
            "Output Power Factor B, stored as 0.01."
        ::= { analogdata3 24 }

    outputPowerFactorC3 OBJECT-TYPE
        SYNTAX Integer32
        MAX-ACCESS read-only
        STATUS current
        DESCRIPTION
            "Output Power Factor C, stored as 0.01."
        ::= { analogdata3 25 }

    outputAcitvePowerA3 OBJECT-TYPE
        SYNTAX Integer32
        MAX-ACCESS read-only
        STATUS current
        DESCRIPTION
            "Output Acitve Power A, stored as 0.01 kW."
        ::= { analogdata3 26 }

    outputAcitvePowerB3 OBJECT-TYPE
        SYNTAX Integer32
        MAX-ACCESS read-only
        STATUS current
        DESCRIPTION
            "Output Acitve Power B, stored as 0.01 kW."
        ::= { analogdata3 27 }

    outputAcitvePowerC3 OBJECT-TYPE
        SYNTAX Integer32
        MAX-ACCESS read-only
        STATUS current
        DESCRIPTION
            "Output Acitve Power C, stored as 0.01 kW."
        ::= { analogdata3 28 }

    outputReactivePowerA3 OBJECT-TYPE
        SYNTAX Integer32
        MAX-ACCESS read-only
        STATUS current
        DESCRIPTION
            "Output Reactive Power A, stored as 0.01 KVAR."
        ::= { analogdata3 29 }

    outputReactivePowerB3 OBJECT-TYPE
        SYNTAX Integer32
        MAX-ACCESS read-only
        STATUS current
        DESCRIPTION
            "Output Reactive Power B, stored as 0.01 KVAR."
        ::= { analogdata3 30 }

    outputReactivePowerC3 OBJECT-TYPE
        SYNTAX Integer32
        MAX-ACCESS read-only
        STATUS current
        DESCRIPTION
            "Output Reactive Power C, stored as 0.01 KVAR."
        ::= { analogdata3 31 }

    outputAppPowerA3 OBJECT-TYPE
        SYNTAX Integer32
        MAX-ACCESS read-only
        STATUS current
        DESCRIPTION
            "Output App Power A, stored as 0.01 kVA."
        ::= { analogdata3 32 }

    outputAppPowerB3 OBJECT-TYPE
        SYNTAX Integer32
        MAX-ACCESS read-only
        STATUS current
        DESCRIPTION
            "Output App Power B, stored as 0.01 kVA."
        ::= { analogdata3 33 }

    outputAppPowerC3 OBJECT-TYPE
        SYNTAX Integer32
        MAX-ACCESS read-only
        STATUS current
        DESCRIPTION
            "Output App Power C, stored as 0.01 kVA."
        ::= { analogdata3 34 }

    outputLoadA3 OBJECT-TYPE
        SYNTAX Integer32
        MAX-ACCESS read-only
        STATUS current
        DESCRIPTION
            "Output Load A, stored as 0.01 %."
        ::= { analogdata3 35 }

    outputLoadB3 OBJECT-TYPE
        SYNTAX Integer32
        MAX-ACCESS read-only
        STATUS current
        DESCRIPTION
            "Output Load B, stored as 0.01 %."
        ::= { analogdata3 36 }

    outputLoadC3 OBJECT-TYPE
        SYNTAX Integer32
        MAX-ACCESS read-only
        STATUS current
        DESCRIPTION
            "Output Load C, stored as 0.01 %."
        ::= { analogdata3 37 }

    outputCrestFactorA3 OBJECT-TYPE
        SYNTAX Integer32
        MAX-ACCESS read-only
        STATUS current
        DESCRIPTION
            "Output Crest Factor A, stored as 0.01 ."
        ::= { analogdata3 38 }

    outputCrestFactorB3 OBJECT-TYPE
        SYNTAX Integer32
        MAX-ACCESS read-only
        STATUS current
        DESCRIPTION
            "Output Crest Factor B, stored as 0.01 ."
        ::= { analogdata3 39 }

    outputCrestFactorC3 OBJECT-TYPE
        SYNTAX Integer32
        MAX-ACCESS read-only
        STATUS current
        DESCRIPTION
            "Output Crest Factor C, stored as 0.01 ."
        ::= { analogdata3 40 }

    bypassVoltageA3 OBJECT-TYPE
        SYNTAX Integer32
        MAX-ACCESS read-only
        STATUS current
        DESCRIPTION
            "Bypass Voltage A, stored as 0.01 V."
        ::= { analogdata3 41 }

    bypassVoltageB3 OBJECT-TYPE
        SYNTAX Integer32
        MAX-ACCESS read-only
        STATUS current
        DESCRIPTION
            "Bypass Voltage B, stored as 0.01 V."
        ::= { analogdata3 42 }

    bypassVoltageC3 OBJECT-TYPE
        SYNTAX Integer32
        MAX-ACCESS read-only
        STATUS current
        DESCRIPTION
            "Bypass Voltage C, stored as 0.01 V."
        ::= { analogdata3 43 }

    bypassFrequency3 OBJECT-TYPE
        SYNTAX Integer32
        MAX-ACCESS read-only
        STATUS current
        DESCRIPTION
            "Bypass Frequency, stored as 0.01 Hz."
        ::= { analogdata3 44 }

    positiveBatteryVoltage3 OBJECT-TYPE
        SYNTAX Integer32
        MAX-ACCESS read-only
        STATUS current
        DESCRIPTION
            "positive Battery Voltage, stored as 0.01 V."
        ::= { analogdata3 45 }

    positiveBatteryCurrent3 OBJECT-TYPE
        SYNTAX Integer32
        MAX-ACCESS read-only
        STATUS current
        DESCRIPTION
            "positive Battery Current, stored as 0.01 A."
        ::= { analogdata3 46 }

    negativeBatteryVoltage3 OBJECT-TYPE
        SYNTAX Integer32
        MAX-ACCESS read-only
        STATUS current
        DESCRIPTION
            "negative Battery Voltage, stored as 0.01 V."
        ::= { analogdata3 47 }

    negativeBatteryCurrent3 OBJECT-TYPE
        SYNTAX Integer32
        MAX-ACCESS read-only
        STATUS current
        DESCRIPTION
            "negative Battery Current, stored as 0.01 A."
        ::= { analogdata3 48 }

    batteryAgingRate3 OBJECT-TYPE
        SYNTAX Integer32
        MAX-ACCESS read-only
        STATUS current
        DESCRIPTION
            "Battery Aging Rate, stored as 0.01."
        ::= { analogdata3 49 }

    batteryRemainsTime3 OBJECT-TYPE
        SYNTAX Integer32
        MAX-ACCESS read-only
        STATUS current
        DESCRIPTION
            "Battery Remains Time, stored as 0.01 Hour."
        ::= { analogdata3 50 }

    batteryTemperature3 OBJECT-TYPE
        SYNTAX Integer32
        MAX-ACCESS read-only
        STATUS current
        DESCRIPTION
            "Battery Temperature, stored as 0.01 &deg;C."
        ::= { analogdata3 51 }

    batteryEnvironmentTemperature3 OBJECT-TYPE
        SYNTAX Integer32
        MAX-ACCESS read-only
        STATUS current
        DESCRIPTION
            "Battery Environment Temperature, stored as 0.01 &deg;C."
        ::= { analogdata3 52 }
        
analogdata4 OBJECT IDENTIFIER ::= { system 8 }

    inputPhaseVoltageA4 OBJECT-TYPE
        SYNTAX Integer32
        MAX-ACCESS read-only
        STATUS current
        DESCRIPTION
            "Input Phase Voltage A, stored as 0.01 V."
        ::= { analogdata4 1 }

    inputPhaseVoltageB4 OBJECT-TYPE
        SYNTAX Integer32
        MAX-ACCESS read-only
        STATUS current
        DESCRIPTION
            "Input Phase Voltage B, stored as 0.01 V."
        ::= { analogdata4 2 }

    inputPhaseVoltageC4 OBJECT-TYPE
        SYNTAX Integer32
        MAX-ACCESS read-only
        STATUS current
        DESCRIPTION
            "Input Phase Voltage C, stored as 0.01 V."
        ::= { analogdata4 3 }

    inputLineVoltageA4 OBJECT-TYPE
        SYNTAX Integer32
        MAX-ACCESS read-only
        STATUS current
        DESCRIPTION
            "Input Line Voltage A, stored as 0.01 V."
        ::= { analogdata4 4 }

    inputLineVoltageB4 OBJECT-TYPE
        SYNTAX Integer32
        MAX-ACCESS read-only
        STATUS current
        DESCRIPTION
            "Input Line Voltage B, stored as 0.01 V."
        ::= { analogdata4 5 }

    inputLineVoltageC4 OBJECT-TYPE
        SYNTAX Integer32
        MAX-ACCESS read-only
        STATUS current
        DESCRIPTION
            "Input Line Voltage C, stored as 0.01 V."
        ::= { analogdata4 6 }

    inputCurrentA4 OBJECT-TYPE
        SYNTAX Integer32
        MAX-ACCESS read-only
        STATUS current
        DESCRIPTION
            "Input Current A, stored as 0.01 A."
        ::= { analogdata4 7 }

    inputCurrentB4 OBJECT-TYPE
        SYNTAX Integer32
        MAX-ACCESS read-only
        STATUS current
        DESCRIPTION
            "Input Current B, stored as 0.01 A."
        ::= { analogdata4 8 }

    inputCurrentC4 OBJECT-TYPE
        SYNTAX Integer32
        MAX-ACCESS read-only
        STATUS current
        DESCRIPTION
            "Input Current C, stored as 0.01 A."
        ::= { analogdata4 9 }

    inputFrequency4 OBJECT-TYPE
        SYNTAX Integer32
        MAX-ACCESS read-only
        STATUS current
        DESCRIPTION
            "Input Frequency, stored as 0.01 Hz."
        ::= { analogdata4 10 }

    inputPowerFactorA4 OBJECT-TYPE
        SYNTAX Integer32
        MAX-ACCESS read-only
        STATUS current
        DESCRIPTION
            "Input Power Factor A, stored as 0.01."
        ::= { analogdata4 11 }

    inputPowerFactorB4 OBJECT-TYPE
        SYNTAX Integer32
        MAX-ACCESS read-only
        STATUS current
        DESCRIPTION
            "Input Power Factor B, stored as 0.01."
        ::= { analogdata4 12 }

    inputPowerFactorC4 OBJECT-TYPE
        SYNTAX Integer32
        MAX-ACCESS read-only
        STATUS current
        DESCRIPTION
            "Input Power Factor C, stored as 0.01."
        ::= { analogdata4 13 }

    dCBus1Voltage4 OBJECT-TYPE
        SYNTAX Integer32
        MAX-ACCESS read-only
        STATUS current
        DESCRIPTION
            "DCBus1 Voltage, stored as 0.01 V."
        ::= { analogdata4 14 }

    dCBus2Voltage4 OBJECT-TYPE
        SYNTAX Integer32
        MAX-ACCESS read-only
        STATUS current
        DESCRIPTION
            "DCBus2 Voltage, stored as 0.01 V."
        ::= { analogdata4 15 }

    outputVoltageA4 OBJECT-TYPE
    	SYNTAX Integer32
    	MAX-ACCESS read-only
        STATUS current
        DESCRIPTION
            "Output voltage A, stored as 0.01 V."
        ::= { analogdata4 16 }

    outputVoltageB4 OBJECT-TYPE
    	SYNTAX Integer32
    	MAX-ACCESS read-only
        STATUS current
        DESCRIPTION
            "Output voltage B, stored as 0.01 V."
        ::= { analogdata4 17 }

    outputVoltageC4 OBJECT-TYPE
    	SYNTAX Integer32
    	MAX-ACCESS read-only
        STATUS current
        DESCRIPTION
            "Output voltage C, stored as 0.01 V."
        ::= { analogdata4 18 }

    outputCurrentA4 OBJECT-TYPE
        SYNTAX Integer32
        MAX-ACCESS read-only
        STATUS current
        DESCRIPTION
            "Output current A, stored as 0.01 A."
        ::= { analogdata4 19 }

    outputCurrentB4 OBJECT-TYPE
        SYNTAX Integer32
        MAX-ACCESS read-only
        STATUS current
        DESCRIPTION
            "Output current B, stored as 0.01 A."
        ::= { analogdata4 20 }

    outputCurrentC4 OBJECT-TYPE
        SYNTAX Integer32
        MAX-ACCESS read-only
        STATUS current
        DESCRIPTION
            "Output current C, stored as 0.01 A."
        ::= { analogdata4 21 }

    outputFrequency4 OBJECT-TYPE
        SYNTAX Integer32
        MAX-ACCESS read-only
        STATUS current
        DESCRIPTION
            "Output Frequency, stored as 0.01 Hz."
        ::= { analogdata4 22 }

    outputPowerFactorA4 OBJECT-TYPE
        SYNTAX Integer32
        MAX-ACCESS read-only
        STATUS current
        DESCRIPTION
            "Output Power Factor A, stored as 0.01."
        ::= { analogdata4 23 }

    outputPowerFactorB4 OBJECT-TYPE
        SYNTAX Integer32
        MAX-ACCESS read-only
        STATUS current
        DESCRIPTION
            "Output Power Factor B, stored as 0.01."
        ::= { analogdata4 24 }

    outputPowerFactorC4 OBJECT-TYPE
        SYNTAX Integer32
        MAX-ACCESS read-only
        STATUS current
        DESCRIPTION
            "Output Power Factor C, stored as 0.01."
        ::= { analogdata4 25 }

    outputAcitvePowerA4 OBJECT-TYPE
        SYNTAX Integer32
        MAX-ACCESS read-only
        STATUS current
        DESCRIPTION
            "Output Acitve Power A, stored as 0.01 kW."
        ::= { analogdata4 26 }

    outputAcitvePowerB4 OBJECT-TYPE
        SYNTAX Integer32
        MAX-ACCESS read-only
        STATUS current
        DESCRIPTION
            "Output Acitve Power B, stored as 0.01 kW."
        ::= { analogdata4 27 }

    outputAcitvePowerC4 OBJECT-TYPE
        SYNTAX Integer32
        MAX-ACCESS read-only
        STATUS current
        DESCRIPTION
            "Output Acitve Power C, stored as 0.01 kW."
        ::= { analogdata4 28 }

    outputReactivePowerA4 OBJECT-TYPE
        SYNTAX Integer32
        MAX-ACCESS read-only
        STATUS current
        DESCRIPTION
            "Output Reactive Power A, stored as 0.01 KVAR."
        ::= { analogdata4 29 }

    outputReactivePowerB4 OBJECT-TYPE
        SYNTAX Integer32
        MAX-ACCESS read-only
        STATUS current
        DESCRIPTION
            "Output Reactive Power B, stored as 0.01 KVAR."
        ::= { analogdata4 30 }

    outputReactivePowerC4 OBJECT-TYPE
        SYNTAX Integer32
        MAX-ACCESS read-only
        STATUS current
        DESCRIPTION
            "Output Reactive Power C, stored as 0.01 KVAR."
        ::= { analogdata4 31 }

    outputAppPowerA4 OBJECT-TYPE
        SYNTAX Integer32
        MAX-ACCESS read-only
        STATUS current
        DESCRIPTION
            "Output App Power A, stored as 0.01 kVA."
        ::= { analogdata4 32 }

    outputAppPowerB4 OBJECT-TYPE
        SYNTAX Integer32
        MAX-ACCESS read-only
        STATUS current
        DESCRIPTION
            "Output App Power B, stored as 0.01 kVA."
        ::= { analogdata4 33 }

    outputAppPowerC4 OBJECT-TYPE
        SYNTAX Integer32
        MAX-ACCESS read-only
        STATUS current
        DESCRIPTION
            "Output App Power C, stored as 0.01 kVA."
        ::= { analogdata4 34 }

    outputLoadA4 OBJECT-TYPE
        SYNTAX Integer32
        MAX-ACCESS read-only
        STATUS current
        DESCRIPTION
            "Output Load A, stored as 0.01 %."
        ::= { analogdata4 35 }

    outputLoadB4 OBJECT-TYPE
        SYNTAX Integer32
        MAX-ACCESS read-only
        STATUS current
        DESCRIPTION
            "Output Load B, stored as 0.01 %."
        ::= { analogdata4 36 }

    outputLoadC4 OBJECT-TYPE
        SYNTAX Integer32
        MAX-ACCESS read-only
        STATUS current
        DESCRIPTION
            "Output Load C, stored as 0.01 %."
        ::= { analogdata4 37 }

    outputCrestFactorA4 OBJECT-TYPE
        SYNTAX Integer32
        MAX-ACCESS read-only
        STATUS current
        DESCRIPTION
            "Output Crest Factor A, stored as 0.01 ."
        ::= { analogdata4 38 }

    outputCrestFactorB4 OBJECT-TYPE
        SYNTAX Integer32
        MAX-ACCESS read-only
        STATUS current
        DESCRIPTION
            "Output Crest Factor B, stored as 0.01 ."
        ::= { analogdata4 39 }

    outputCrestFactorC4 OBJECT-TYPE
        SYNTAX Integer32
        MAX-ACCESS read-only
        STATUS current
        DESCRIPTION
            "Output Crest Factor C, stored as 0.01 ."
        ::= { analogdata4 40 }

    bypassVoltageA4 OBJECT-TYPE
        SYNTAX Integer32
        MAX-ACCESS read-only
        STATUS current
        DESCRIPTION
            "Bypass Voltage A, stored as 0.01 V."
        ::= { analogdata4 41 }

    bypassVoltageB4 OBJECT-TYPE
        SYNTAX Integer32
        MAX-ACCESS read-only
        STATUS current
        DESCRIPTION
            "Bypass Voltage B, stored as 0.01 V."
        ::= { analogdata4 42 }

    bypassVoltageC4 OBJECT-TYPE
        SYNTAX Integer32
        MAX-ACCESS read-only
        STATUS current
        DESCRIPTION
            "Bypass Voltage C, stored as 0.01 V."
        ::= { analogdata4 43 }

    bypassFrequency4 OBJECT-TYPE
        SYNTAX Integer32
        MAX-ACCESS read-only
        STATUS current
        DESCRIPTION
            "Bypass Frequency, stored as 0.01 Hz."
        ::= { analogdata4 44 }

    positiveBatteryVoltage4 OBJECT-TYPE
        SYNTAX Integer32
        MAX-ACCESS read-only
        STATUS current
        DESCRIPTION
            "positive Battery Voltage, stored as 0.01 V."
        ::= { analogdata4 45 }

    positiveBatteryCurrent4 OBJECT-TYPE
        SYNTAX Integer32
        MAX-ACCESS read-only
        STATUS current
        DESCRIPTION
            "positive Battery Current, stored as 0.01 A."
        ::= { analogdata4 46 }

    negativeBatteryVoltage4 OBJECT-TYPE
        SYNTAX Integer32
        MAX-ACCESS read-only
        STATUS current
        DESCRIPTION
            "negative Battery Voltage, stored as 0.01 V."
        ::= { analogdata4 47 }

    negativeBatteryCurrent4 OBJECT-TYPE
        SYNTAX Integer32
        MAX-ACCESS read-only
        STATUS current
        DESCRIPTION
            "negative Battery Current, stored as 0.01 A."
        ::= { analogdata4 48 }

    batteryAgingRate4 OBJECT-TYPE
        SYNTAX Integer32
        MAX-ACCESS read-only
        STATUS current
        DESCRIPTION
            "Battery Aging Rate, stored as 0.01."
        ::= { analogdata4 49 }

    batteryRemainsTime4 OBJECT-TYPE
        SYNTAX Integer32
        MAX-ACCESS read-only
        STATUS current
        DESCRIPTION
            "Battery Remains Time, stored as 0.01 Hour."
        ::= { analogdata4 50 }

    batteryTemperature4 OBJECT-TYPE
        SYNTAX Integer32
        MAX-ACCESS read-only
        STATUS current
        DESCRIPTION
            "Battery Temperature, stored as 0.01 &deg;C."
        ::= { analogdata4 51 }

    batteryEnvironmentTemperature4 OBJECT-TYPE
        SYNTAX Integer32
        MAX-ACCESS read-only
        STATUS current
        DESCRIPTION
            "Battery Environment Temperature, stored as 0.01 &deg;C."
        ::= { analogdata4 52 }
        
-- ------------------------------------------------------------------------ 
-- 1.2.5 the branch1 group
-- ------------------------------------------------------------------------ 

branch1 OBJECT IDENTIFIER ::= { system 20 }

    branch1Current OBJECT-TYPE
    	SYNTAX Integer32
    	MAX-ACCESS read-only
        STATUS current
        DESCRIPTION
            "Branch1 Current, stored as 0.01 A."
        ::= { branch1 1 }

	branch1ElectricEnergy OBJECT-TYPE
        SYNTAX Integer32
        MAX-ACCESS read-only
        STATUS current
        DESCRIPTION
            "Branch1 Electric Energy, stored as 0.01 kWh."
        ::= { branch1 2 }

	branch1SwitchStatus OBJECT-TYPE
        SYNTAX Integer32
        MAX-ACCESS read-only
        STATUS current
        DESCRIPTION
            "Branch1 Switch Status, stored as 0.01."
        ::= { branch1 3 }
        
	branch1ActivePower OBJECT-TYPE
        SYNTAX Integer32
        MAX-ACCESS read-only
        STATUS current
        DESCRIPTION
            "Branch1 Active Power, stored as 0.01 kW."
        ::= { branch1 4 }

	branch1ApparentPower OBJECT-TYPE
        SYNTAX Integer32
        MAX-ACCESS read-only
        STATUS current
        DESCRIPTION
            "Branch1 Apparent Power, stored as 0.01 kVA."
        ::= { branch1 5 }

	branch1THDi OBJECT-TYPE
        SYNTAX Integer32
        MAX-ACCESS read-only
        STATUS current
        DESCRIPTION
            "Branch1 THDi, stored as 0.01 %."
        ::= { branch1 6 }

	branch1RatedCurrent OBJECT-TYPE
        SYNTAX Integer32
        MAX-ACCESS read-only
        STATUS current
        DESCRIPTION
            "Branch1 Rated Current, stored as 0.01 A."
        ::= { branch1 7 }

	branch1LoadRatio OBJECT-TYPE
        SYNTAX Integer32
        MAX-ACCESS read-only
        STATUS current
        DESCRIPTION "
        	Branch1 Load Ratio. stored as 0.01 %"
        ::= { branch1 8 }

	branch1PowerFactor OBJECT-TYPE
        SYNTAX Integer32
        MAX-ACCESS read-only
        STATUS current
        DESCRIPTION
            "Branch1 Power Factor, stored as 0.01."
        ::= { branch1 9 }


-- ------------------------------------------------------------------------ 
-- 1.2.5 the branch2 group
-- ------------------------------------------------------------------------ 

branch2 OBJECT IDENTIFIER ::= { system 21 }

    branch2Current OBJECT-TYPE
    	SYNTAX Integer32
    	MAX-ACCESS read-only
        STATUS current
        DESCRIPTION
            "Branch2 Current, stored as 0.01 A."
        ::= { branch2 1 }

	branch2ElectricEnergy OBJECT-TYPE
        SYNTAX Integer32
        MAX-ACCESS read-only
        STATUS current
        DESCRIPTION
            "Branch2 Electric Energy, stored as 0.01 kWh."
        ::= { branch2 2 }

	branch2SwitchStatus OBJECT-TYPE
        SYNTAX Integer32
        MAX-ACCESS read-only
        STATUS current
        DESCRIPTION
            "branch2 Switch Status, stored as 0.01."
        ::= { branch2 3 }
        
	branch2ActivePower OBJECT-TYPE
        SYNTAX Integer32
        MAX-ACCESS read-only
        STATUS current
        DESCRIPTION
            "branch2 Active Power, stored as 0.01 kW."
        ::= { branch2 4 }

	branch2ApparentPower OBJECT-TYPE
        SYNTAX Integer32
        MAX-ACCESS read-only
        STATUS current
        DESCRIPTION
            "branch2 Apparent Power, stored as 0.01 kVA."
        ::= { branch2 5 }

	branch2THDi OBJECT-TYPE
        SYNTAX Integer32
        MAX-ACCESS read-only
        STATUS current
        DESCRIPTION
            "branch2 THDi, stored as 0.01 %."
        ::= { branch2 6 }

	branch2RatedCurrent OBJECT-TYPE
        SYNTAX Integer32
        MAX-ACCESS read-only
        STATUS current
        DESCRIPTION
            "branch2 Rated Current, stored as 0.01 A."
        ::= { branch2 7 }

	branch2LoadRatio OBJECT-TYPE
        SYNTAX Integer32
        MAX-ACCESS read-only
        STATUS current
        DESCRIPTION "
        	branch2 Load Ratio. stored as 0.01 %"
        ::= { branch2 8 }

	branch2PowerFactor OBJECT-TYPE
        SYNTAX Integer32
        MAX-ACCESS read-only
        STATUS current
        DESCRIPTION
            "branch2 Power Factor, stored as 0.01."
        ::= { branch2 9 }


-- ------------------------------------------------------------------------ 
-- 1.2.6 the branch3 group
-- ------------------------------------------------------------------------ 

branch3 OBJECT IDENTIFIER ::= { system 22 }

    branch3Current OBJECT-TYPE
    	SYNTAX Integer32
    	MAX-ACCESS read-only
        STATUS current
        DESCRIPTION
            "branch3 Current, stored as 0.01 A."
        ::= { branch3 1 }

	branch3ElectricEnergy OBJECT-TYPE
        SYNTAX Integer32
        MAX-ACCESS read-only
        STATUS current
        DESCRIPTION
            "branch3 Electric Energy, stored as 0.01 kWh."
        ::= { branch3 2 }

	branch3SwitchStatus OBJECT-TYPE
        SYNTAX Integer32
        MAX-ACCESS read-only
        STATUS current
        DESCRIPTION
            "branch3 Switch Status, stored as 0.01."
        ::= { branch3 3 }
        
	branch3ActivePower OBJECT-TYPE
        SYNTAX Integer32
        MAX-ACCESS read-only
        STATUS current
        DESCRIPTION
            "branch3 Active Power, stored as 0.01 kW."
        ::= { branch3 4 }

	branch3ApparentPower OBJECT-TYPE
        SYNTAX Integer32
        MAX-ACCESS read-only
        STATUS current
        DESCRIPTION
            "branch3 Apparent Power, stored as 0.01 kVA."
        ::= { branch3 5 }

	branch3THDi OBJECT-TYPE
        SYNTAX Integer32
        MAX-ACCESS read-only
        STATUS current
        DESCRIPTION
            "branch3 THDi, stored as 0.01 %."
        ::= { branch3 6 }

	branch3RatedCurrent OBJECT-TYPE
        SYNTAX Integer32
        MAX-ACCESS read-only
        STATUS current
        DESCRIPTION
            "branch3 Rated Current, stored as 0.01 A."
        ::= { branch3 7 }

	branch3LoadRatio OBJECT-TYPE
        SYNTAX Integer32
        MAX-ACCESS read-only
        STATUS current
        DESCRIPTION "
        	branch3 Load Ratio. stored as 0.01 %"
        ::= { branch3 8 }

	branch3PowerFactor OBJECT-TYPE
        SYNTAX Integer32
        MAX-ACCESS read-only
        STATUS current
        DESCRIPTION
            "branch3 Power Factor, stored as 0.01."
        ::= { branch3 9 }


-- ------------------------------------------------------------------------ 
-- 1.2.7 the branch4 group
-- ------------------------------------------------------------------------ 

branch4 OBJECT IDENTIFIER ::= { system 23 }

    branch4Current OBJECT-TYPE
    	SYNTAX Integer32
    	MAX-ACCESS read-only
        STATUS current
        DESCRIPTION
            "branch4 Current, stored as 0.01 A."
        ::= { branch4 1 }

	branch4ElectricEnergy OBJECT-TYPE
        SYNTAX Integer32
        MAX-ACCESS read-only
        STATUS current
        DESCRIPTION
            "branch4 Electric Energy, stored as 0.01 kWh."
        ::= { branch4 2 }

	branch4SwitchStatus OBJECT-TYPE
        SYNTAX Integer32
        MAX-ACCESS read-only
        STATUS current
        DESCRIPTION
            "branch4 Switch Status, stored as 0.01."
        ::= { branch4 3 }
        
	branch4ActivePower OBJECT-TYPE
        SYNTAX Integer32
        MAX-ACCESS read-only
        STATUS current
        DESCRIPTION
            "branch4 Active Power, stored as 0.01 kW."
        ::= { branch4 4 }

	branch4ApparentPower OBJECT-TYPE
        SYNTAX Integer32
        MAX-ACCESS read-only
        STATUS current
        DESCRIPTION
            "branch4 Apparent Power, stored as 0.01 kVA."
        ::= { branch4 5 }

	branch4THDi OBJECT-TYPE
        SYNTAX Integer32
        MAX-ACCESS read-only
        STATUS current
        DESCRIPTION
            "branch4 THDi, stored as 0.01 %."
        ::= { branch4 6 }

	branch4RatedCurrent OBJECT-TYPE
        SYNTAX Integer32
        MAX-ACCESS read-only
        STATUS current
        DESCRIPTION
            "branch4 Rated Current, stored as 0.01 A."
        ::= { branch4 7 }

	branch4LoadRatio OBJECT-TYPE
        SYNTAX Integer32
        MAX-ACCESS read-only
        STATUS current
        DESCRIPTION "
        	branch4 Load Ratio. stored as 0.01 %"
        ::= { branch4 8 }

	branch4PowerFactor OBJECT-TYPE
        SYNTAX Integer32
        MAX-ACCESS read-only
        STATUS current
        DESCRIPTION
            "branch4 Power Factor, stored as 0.01."
        ::= { branch4 9 }


-- ------------------------------------------------------------------------ 
-- 1.2.8 the branch5 group
-- ------------------------------------------------------------------------ 

branch5 OBJECT IDENTIFIER ::= { system 24 }

    branch5Current OBJECT-TYPE
    	SYNTAX Integer32
    	MAX-ACCESS read-only
        STATUS current
        DESCRIPTION
            "branch5 Current, stored as 0.01 A."
        ::= { branch5 1 }

	branch5ElectricEnergy OBJECT-TYPE
        SYNTAX Integer32
        MAX-ACCESS read-only
        STATUS current
        DESCRIPTION
            "branch5 Electric Energy, stored as 0.01 kWh."
        ::= { branch5 2 }

	branch5SwitchStatus OBJECT-TYPE
        SYNTAX Integer32
        MAX-ACCESS read-only
        STATUS current
        DESCRIPTION
            "branch5 Switch Status, stored as 0.01."
        ::= { branch5 3 }
        
	branch5ActivePower OBJECT-TYPE
        SYNTAX Integer32
        MAX-ACCESS read-only
        STATUS current
        DESCRIPTION
            "branch5 Active Power, stored as 0.01 kW."
        ::= { branch5 4 }

	branch5ApparentPower OBJECT-TYPE
        SYNTAX Integer32
        MAX-ACCESS read-only
        STATUS current
        DESCRIPTION
            "branch5 Apparent Power, stored as 0.01 kVA."
        ::= { branch5 5 }

	branch5THDi OBJECT-TYPE
        SYNTAX Integer32
        MAX-ACCESS read-only
        STATUS current
        DESCRIPTION
            "branch5 THDi, stored as 0.01 %."
        ::= { branch5 6 }

	branch5RatedCurrent OBJECT-TYPE
        SYNTAX Integer32
        MAX-ACCESS read-only
        STATUS current
        DESCRIPTION
            "branch5 Rated Current, stored as 0.01 A."
        ::= { branch5 7 }

	branch5LoadRatio OBJECT-TYPE
        SYNTAX Integer32
        MAX-ACCESS read-only
        STATUS current
        DESCRIPTION "
        	branch5 Load Ratio. stored as 0.01 %"
        ::= { branch5 8 }

	branch5PowerFactor OBJECT-TYPE
        SYNTAX Integer32
        MAX-ACCESS read-only
        STATUS current
        DESCRIPTION
            "branch5 Power Factor, stored as 0.01."
        ::= { branch5 9 }


-- ------------------------------------------------------------------------ 
-- 1.2.9 the branch6 group
-- ------------------------------------------------------------------------ 

branch6 OBJECT IDENTIFIER ::= { system 25 }

    branch6Current OBJECT-TYPE
    	SYNTAX Integer32
    	MAX-ACCESS read-only
        STATUS current
        DESCRIPTION
            "branch6 Current, stored as 0.01 A."
        ::= { branch6 1 }

	branch6ElectricEnergy OBJECT-TYPE
        SYNTAX Integer32
        MAX-ACCESS read-only
        STATUS current
        DESCRIPTION
            "branch6 Electric Energy, stored as 0.01 kWh."
        ::= { branch6 2 }

	branch6SwitchStatus OBJECT-TYPE
        SYNTAX Integer32
        MAX-ACCESS read-only
        STATUS current
        DESCRIPTION
            "branch6 Switch Status, stored as 0.01."
        ::= { branch6 3 }
        
	branch6ActivePower OBJECT-TYPE
        SYNTAX Integer32
        MAX-ACCESS read-only
        STATUS current
        DESCRIPTION
            "branch6 Active Power, stored as 0.01 kW."
        ::= { branch6 4 }

	branch6ApparentPower OBJECT-TYPE
        SYNTAX Integer32
        MAX-ACCESS read-only
        STATUS current
        DESCRIPTION
            "branch6 Apparent Power, stored as 0.01 kVA."
        ::= { branch6 5 }

	branch6THDi OBJECT-TYPE
        SYNTAX Integer32
        MAX-ACCESS read-only
        STATUS current
        DESCRIPTION
            "branch6 THDi, stored as 0.01 %."
        ::= { branch6 6 }

	branch6RatedCurrent OBJECT-TYPE
        SYNTAX Integer32
        MAX-ACCESS read-only
        STATUS current
        DESCRIPTION
            "branch6 Rated Current, stored as 0.01 A."
        ::= { branch6 7 }

	branch6LoadRatio OBJECT-TYPE
        SYNTAX Integer32
        MAX-ACCESS read-only
        STATUS current
        DESCRIPTION "
        	branch6 Load Ratio. stored as 0.01 %"
        ::= { branch6 8 }

	branch6PowerFactor OBJECT-TYPE
        SYNTAX Integer32
        MAX-ACCESS read-only
        STATUS current
        DESCRIPTION
            "branch6 Power Factor, stored as 0.01."
        ::= { branch6 9 }


-- ------------------------------------------------------------------------ 
-- 1.2.10 the branch7 group
-- ------------------------------------------------------------------------ 

branch7 OBJECT IDENTIFIER ::= { system 26 }

    branch7Current OBJECT-TYPE
    	SYNTAX Integer32
    	MAX-ACCESS read-only
        STATUS current
        DESCRIPTION
            "branch7 Current, stored as 0.01 A."
        ::= { branch7 1 }

	branch7ElectricEnergy OBJECT-TYPE
        SYNTAX Integer32
        MAX-ACCESS read-only
        STATUS current
        DESCRIPTION
            "branch7 Electric Energy, stored as 0.01 kWh."
        ::= { branch7 2 }

	branch7SwitchStatus OBJECT-TYPE
        SYNTAX Integer32
        MAX-ACCESS read-only
        STATUS current
        DESCRIPTION
            "branch7 Switch Status, stored as 0.01."
        ::= { branch7 3 }
        
	branch7ActivePower OBJECT-TYPE
        SYNTAX Integer32
        MAX-ACCESS read-only
        STATUS current
        DESCRIPTION
            "branch7 Active Power, stored as 0.01 kW."
        ::= { branch7 4 }

	branch7ApparentPower OBJECT-TYPE
        SYNTAX Integer32
        MAX-ACCESS read-only
        STATUS current
        DESCRIPTION
            "branch7 Apparent Power, stored as 0.01 kVA."
        ::= { branch7 5 }

	branch7THDi OBJECT-TYPE
        SYNTAX Integer32
        MAX-ACCESS read-only
        STATUS current
        DESCRIPTION
            "branch7 THDi, stored as 0.01 %."
        ::= { branch7 6 }

	branch7RatedCurrent OBJECT-TYPE
        SYNTAX Integer32
        MAX-ACCESS read-only
        STATUS current
        DESCRIPTION
            "branch7 Rated Current, stored as 0.01 A."
        ::= { branch7 7 }

	branch7LoadRatio OBJECT-TYPE
        SYNTAX Integer32
        MAX-ACCESS read-only
        STATUS current
        DESCRIPTION "
        	branch7 Load Ratio. stored as 0.01 %"
        ::= { branch7 8 }

	branch7PowerFactor OBJECT-TYPE
        SYNTAX Integer32
        MAX-ACCESS read-only
        STATUS current
        DESCRIPTION
            "branch7 Power Factor, stored as 0.01."
        ::= { branch7 9 }


-- ------------------------------------------------------------------------ 
-- 1.2.11 the branch8 group
-- ------------------------------------------------------------------------ 

branch8 OBJECT IDENTIFIER ::= { system 27 }

    branch8Current OBJECT-TYPE
    	SYNTAX Integer32
    	MAX-ACCESS read-only
        STATUS current
        DESCRIPTION
            "branch8 Current, stored as 0.01 A."
        ::= { branch8 1 }

	branch8ElectricEnergy OBJECT-TYPE
        SYNTAX Integer32
        MAX-ACCESS read-only
        STATUS current
        DESCRIPTION
            "branch8 Electric Energy, stored as 0.01 kWh."
        ::= { branch8 2 }

	branch8SwitchStatus OBJECT-TYPE
        SYNTAX Integer32
        MAX-ACCESS read-only
        STATUS current
        DESCRIPTION
            "branch8 Switch Status, stored as 0.01."
        ::= { branch8 3 }
        
	branch8ActivePower OBJECT-TYPE
        SYNTAX Integer32
        MAX-ACCESS read-only
        STATUS current
        DESCRIPTION
            "branch8 Active Power, stored as 0.01 kW."
        ::= { branch8 4 }

	branch8ApparentPower OBJECT-TYPE
        SYNTAX Integer32
        MAX-ACCESS read-only
        STATUS current
        DESCRIPTION
            "branch8 Apparent Power, stored as 0.01 kVA."
        ::= { branch8 5 }

	branch8THDi OBJECT-TYPE
        SYNTAX Integer32
        MAX-ACCESS read-only
        STATUS current
        DESCRIPTION
            "branch8 THDi, stored as 0.01 %."
        ::= { branch8 6 }

	branch8RatedCurrent OBJECT-TYPE
        SYNTAX Integer32
        MAX-ACCESS read-only
        STATUS current
        DESCRIPTION
            "branch8 Rated Current, stored as 0.01 A."
        ::= { branch8 7 }

	branch8LoadRatio OBJECT-TYPE
        SYNTAX Integer32
        MAX-ACCESS read-only
        STATUS current
        DESCRIPTION "
        	branch8 Load Ratio. stored as 0.01 %"
        ::= { branch8 8 }

	branch8PowerFactor OBJECT-TYPE
        SYNTAX Integer32
        MAX-ACCESS read-only
        STATUS current
        DESCRIPTION
            "branch8 Power Factor, stored as 0.01."
        ::= { branch8 9 }


-- ------------------------------------------------------------------------ 
-- 1.2.12 the branch9 group
-- ------------------------------------------------------------------------ 

branch9 OBJECT IDENTIFIER ::= { system 28 }

    branch9Current OBJECT-TYPE
    	SYNTAX Integer32
    	MAX-ACCESS read-only
        STATUS current
        DESCRIPTION
            "branch9 Current, stored as 0.01 A."
        ::= { branch9 1 }

	branch9ElectricEnergy OBJECT-TYPE
        SYNTAX Integer32
        MAX-ACCESS read-only
        STATUS current
        DESCRIPTION
            "branch9 Electric Energy, stored as 0.01 kWh."
        ::= { branch9 2 }

	branch9SwitchStatus OBJECT-TYPE
        SYNTAX Integer32
        MAX-ACCESS read-only
        STATUS current
        DESCRIPTION
            "branch9 Switch Status, stored as 0.01."
        ::= { branch9 3 }
        
	branch9ActivePower OBJECT-TYPE
        SYNTAX Integer32
        MAX-ACCESS read-only
        STATUS current
        DESCRIPTION
            "branch9 Active Power, stored as 0.01 kW."
        ::= { branch9 4 }

	branch9ApparentPower OBJECT-TYPE
        SYNTAX Integer32
        MAX-ACCESS read-only
        STATUS current
        DESCRIPTION
            "branch9 Apparent Power, stored as 0.01 kVA."
        ::= { branch9 5 }

	branch9THDi OBJECT-TYPE
        SYNTAX Integer32
        MAX-ACCESS read-only
        STATUS current
        DESCRIPTION
            "branch9 THDi, stored as 0.01 %."
        ::= { branch9 6 }

	branch9RatedCurrent OBJECT-TYPE
        SYNTAX Integer32
        MAX-ACCESS read-only
        STATUS current
        DESCRIPTION
            "branch9 Rated Current, stored as 0.01 A."
        ::= { branch9 7 }

	branch9LoadRatio OBJECT-TYPE
        SYNTAX Integer32
        MAX-ACCESS read-only
        STATUS current
        DESCRIPTION "
        	branch9 Load Ratio. stored as 0.01 %"
        ::= { branch9 8 }

	branch9PowerFactor OBJECT-TYPE
        SYNTAX Integer32
        MAX-ACCESS read-only
        STATUS current
        DESCRIPTION
            "branch9 Power Factor, stored as 0.01."
        ::= { branch9 9 }


-- ------------------------------------------------------------------------ 
-- 1.2.13 the branch10 group
-- ------------------------------------------------------------------------ 

branch10 OBJECT IDENTIFIER ::= { system 29 }

    branch10Current OBJECT-TYPE
    	SYNTAX Integer32
    	MAX-ACCESS read-only
        STATUS current
        DESCRIPTION
            "branch10 Current, stored as 0.01 A."
        ::= { branch10 1 }

	branch10ElectricEnergy OBJECT-TYPE
        SYNTAX Integer32
        MAX-ACCESS read-only
        STATUS current
        DESCRIPTION
            "branch10 Electric Energy, stored as 0.01 kWh."
        ::= { branch10 2 }

	branch10SwitchStatus OBJECT-TYPE
        SYNTAX Integer32
        MAX-ACCESS read-only
        STATUS current
        DESCRIPTION
            "branch10 Switch Status, stored as 0.01."
        ::= { branch10 3 }
        
	branch10ActivePower OBJECT-TYPE
        SYNTAX Integer32
        MAX-ACCESS read-only
        STATUS current
        DESCRIPTION
            "branch10 Active Power, stored as 0.01 kW."
        ::= { branch10 4 }

	branch10ApparentPower OBJECT-TYPE
        SYNTAX Integer32
        MAX-ACCESS read-only
        STATUS current
        DESCRIPTION
            "branch10 Apparent Power, stored as 0.01 kVA."
        ::= { branch10 5 }

	branch10THDi OBJECT-TYPE
        SYNTAX Integer32
        MAX-ACCESS read-only
        STATUS current
        DESCRIPTION
            "branch10 THDi, stored as 0.01 %."
        ::= { branch10 6 }

	branch10RatedCurrent OBJECT-TYPE
        SYNTAX Integer32
        MAX-ACCESS read-only
        STATUS current
        DESCRIPTION
            "branch10 Rated Current, stored as 0.01 A."
        ::= { branch10 7 }

	branch10LoadRatio OBJECT-TYPE
        SYNTAX Integer32
        MAX-ACCESS read-only
        STATUS current
        DESCRIPTION "
        	branch10 Load Ratio. stored as 0.01 %"
        ::= { branch10 8 }

	branch10PowerFactor OBJECT-TYPE
        SYNTAX Integer32
        MAX-ACCESS read-only
        STATUS current
        DESCRIPTION
            "branch10 Power Factor, stored as 0.01."
        ::= { branch10 9 }


-- ------------------------------------------------------------------------ 
-- 1.2.14 the branch11 group
-- ------------------------------------------------------------------------ 

branch11 OBJECT IDENTIFIER ::= { system 30 }

    branch11Current OBJECT-TYPE
    	SYNTAX Integer32
    	MAX-ACCESS read-only
        STATUS current
        DESCRIPTION
            "branch11 Current, stored as 0.01 A."
        ::= { branch11 1 }

	branch11ElectricEnergy OBJECT-TYPE
        SYNTAX Integer32
        MAX-ACCESS read-only
        STATUS current
        DESCRIPTION
            "branch11 Electric Energy, stored as 0.01 kWh."
        ::= { branch11 2 }

	branch11SwitchStatus OBJECT-TYPE
        SYNTAX Integer32
        MAX-ACCESS read-only
        STATUS current
        DESCRIPTION
            "branch11 Switch Status, stored as 0.01."
        ::= { branch11 3 }
        
	branch11ActivePower OBJECT-TYPE
        SYNTAX Integer32
        MAX-ACCESS read-only
        STATUS current
        DESCRIPTION
            "branch11 Active Power, stored as 0.01 kW."
        ::= { branch11 4 }

	branch11ApparentPower OBJECT-TYPE
        SYNTAX Integer32
        MAX-ACCESS read-only
        STATUS current
        DESCRIPTION
            "branch11 Apparent Power, stored as 0.01 kVA."
        ::= { branch11 5 }

	branch11THDi OBJECT-TYPE
        SYNTAX Integer32
        MAX-ACCESS read-only
        STATUS current
        DESCRIPTION
            "branch11 THDi, stored as 0.01 %."
        ::= { branch11 6 }

	branch11RatedCurrent OBJECT-TYPE
        SYNTAX Integer32
        MAX-ACCESS read-only
        STATUS current
        DESCRIPTION
            "branch11 Rated Current, stored as 0.01 A."
        ::= { branch11 7 }

	branch11LoadRatio OBJECT-TYPE
        SYNTAX Integer32
        MAX-ACCESS read-only
        STATUS current
        DESCRIPTION "
        	branch11 Load Ratio. stored as 0.01 %"
        ::= { branch11 8 }

	branch11PowerFactor OBJECT-TYPE
        SYNTAX Integer32
        MAX-ACCESS read-only
        STATUS current
        DESCRIPTION
            "branch11 Power Factor, stored as 0.01."
        ::= { branch11 9 }


-- ------------------------------------------------------------------------ 
-- 1.2.15 the branch12 group
-- ------------------------------------------------------------------------ 

branch12 OBJECT IDENTIFIER ::= { system 31 }

    branch12Current OBJECT-TYPE
    	SYNTAX Integer32
    	MAX-ACCESS read-only
        STATUS current
        DESCRIPTION
            "branch12 Current, stored as 0.01 A."
        ::= { branch12 1 }

	branch12ElectricEnergy OBJECT-TYPE
        SYNTAX Integer32
        MAX-ACCESS read-only
        STATUS current
        DESCRIPTION
            "branch12 Electric Energy, stored as 0.01 kWh."
        ::= { branch12 2 }

	branch12SwitchStatus OBJECT-TYPE
        SYNTAX Integer32
        MAX-ACCESS read-only
        STATUS current
        DESCRIPTION
            "branch12 Switch Status, stored as 0.01."
        ::= { branch12 3 }
        
	branch12ActivePower OBJECT-TYPE
        SYNTAX Integer32
        MAX-ACCESS read-only
        STATUS current
        DESCRIPTION
            "branch12 Active Power, stored as 0.01 kW."
        ::= { branch12 4 }

	branch12ApparentPower OBJECT-TYPE
        SYNTAX Integer32
        MAX-ACCESS read-only
        STATUS current
        DESCRIPTION
            "branch12 Apparent Power, stored as 0.01 kVA."
        ::= { branch12 5 }

	branch12THDi OBJECT-TYPE
        SYNTAX Integer32
        MAX-ACCESS read-only
        STATUS current
        DESCRIPTION
            "branch12 THDi, stored as 0.01 %."
        ::= { branch12 6 }

	branch12RatedCurrent OBJECT-TYPE
        SYNTAX Integer32
        MAX-ACCESS read-only
        STATUS current
        DESCRIPTION
            "branch12 Rated Current, stored as 0.01 A."
        ::= { branch12 7 }

	branch12LoadRatio OBJECT-TYPE
        SYNTAX Integer32
        MAX-ACCESS read-only
        STATUS current
        DESCRIPTION "
        	branch12 Load Ratio. stored as 0.01 %"
        ::= { branch12 8 }

	branch12PowerFactor OBJECT-TYPE
        SYNTAX Integer32
        MAX-ACCESS read-only
        STATUS current
        DESCRIPTION
            "branch12 Power Factor, stored as 0.01."
        ::= { branch12 9 }


-- ------------------------------------------------------------------------ 
-- 1.2.16 the branch13 group
-- ------------------------------------------------------------------------ 

branch13 OBJECT IDENTIFIER ::= { system 32 }

    branch13Current OBJECT-TYPE
    	SYNTAX Integer32
    	MAX-ACCESS read-only
        STATUS current
        DESCRIPTION
            "branch13 Current, stored as 0.01 A."
        ::= { branch13 1 }

	branch13ElectricEnergy OBJECT-TYPE
        SYNTAX Integer32
        MAX-ACCESS read-only
        STATUS current
        DESCRIPTION
            "branch13 Electric Energy, stored as 0.01 kWh."
        ::= { branch13 2 }

	branch13SwitchStatus OBJECT-TYPE
        SYNTAX Integer32
        MAX-ACCESS read-only
        STATUS current
        DESCRIPTION
            "branch13 Switch Status, stored as 0.01."
        ::= { branch13 3 }
        
	branch13ActivePower OBJECT-TYPE
        SYNTAX Integer32
        MAX-ACCESS read-only
        STATUS current
        DESCRIPTION
            "branch13 Active Power, stored as 0.01 kW."
        ::= { branch13 4 }

	branch13ApparentPower OBJECT-TYPE
        SYNTAX Integer32
        MAX-ACCESS read-only
        STATUS current
        DESCRIPTION
            "branch13 Apparent Power, stored as 0.01 kVA."
        ::= { branch13 5 }

	branch13THDi OBJECT-TYPE
        SYNTAX Integer32
        MAX-ACCESS read-only
        STATUS current
        DESCRIPTION
            "branch13 THDi, stored as 0.01 %."
        ::= { branch13 6 }

	branch13RatedCurrent OBJECT-TYPE
        SYNTAX Integer32
        MAX-ACCESS read-only
        STATUS current
        DESCRIPTION
            "branch13 Rated Current, stored as 0.01 A."
        ::= { branch13 7 }

	branch13LoadRatio OBJECT-TYPE
        SYNTAX Integer32
        MAX-ACCESS read-only
        STATUS current
        DESCRIPTION "
        	branch13 Load Ratio. stored as 0.01 %"
        ::= { branch13 8 }

	branch13PowerFactor OBJECT-TYPE
        SYNTAX Integer32
        MAX-ACCESS read-only
        STATUS current
        DESCRIPTION
            "branch13 Power Factor, stored as 0.01."
        ::= { branch13 9 }


-- ------------------------------------------------------------------------ 
-- 1.2.17 the branch14 group
-- ------------------------------------------------------------------------ 

branch14 OBJECT IDENTIFIER ::= { system 33 }

    branch14Current OBJECT-TYPE
    	SYNTAX Integer32
    	MAX-ACCESS read-only
        STATUS current
        DESCRIPTION
            "branch14 Current, stored as 0.01 A."
        ::= { branch14 1 }

	branch14ElectricEnergy OBJECT-TYPE
        SYNTAX Integer32
        MAX-ACCESS read-only
        STATUS current
        DESCRIPTION
            "branch14 Electric Energy, stored as 0.01 kWh."
        ::= { branch14 2 }

	branch14SwitchStatus OBJECT-TYPE
        SYNTAX Integer32
        MAX-ACCESS read-only
        STATUS current
        DESCRIPTION
            "branch14 Switch Status, stored as 0.01."
        ::= { branch14 3 }
        
	branch14ActivePower OBJECT-TYPE
        SYNTAX Integer32
        MAX-ACCESS read-only
        STATUS current
        DESCRIPTION
            "branch14 Active Power, stored as 0.01 kW."
        ::= { branch14 4 }

	branch14ApparentPower OBJECT-TYPE
        SYNTAX Integer32
        MAX-ACCESS read-only
        STATUS current
        DESCRIPTION
            "branch14 Apparent Power, stored as 0.01 kVA."
        ::= { branch14 5 }

	branch14THDi OBJECT-TYPE
        SYNTAX Integer32
        MAX-ACCESS read-only
        STATUS current
        DESCRIPTION
            "branch14 THDi, stored as 0.01 %."
        ::= { branch14 6 }

	branch14RatedCurrent OBJECT-TYPE
        SYNTAX Integer32
        MAX-ACCESS read-only
        STATUS current
        DESCRIPTION
            "branch14 Rated Current, stored as 0.01 A."
        ::= { branch14 7 }

	branch14LoadRatio OBJECT-TYPE
        SYNTAX Integer32
        MAX-ACCESS read-only
        STATUS current
        DESCRIPTION "
        	branch14 Load Ratio. stored as 0.01 %"
        ::= { branch14 8 }

	branch14PowerFactor OBJECT-TYPE
        SYNTAX Integer32
        MAX-ACCESS read-only
        STATUS current
        DESCRIPTION
            "branch14 Power Factor, stored as 0.01."
        ::= { branch14 9 }


-- ------------------------------------------------------------------------ 
-- 1.2.18 the branch15 group
-- ------------------------------------------------------------------------ 

branch15 OBJECT IDENTIFIER ::= { system 34 }

    branch15Current OBJECT-TYPE
    	SYNTAX Integer32
    	MAX-ACCESS read-only
        STATUS current
        DESCRIPTION
            "branch15 Current, stored as 0.01 A."
        ::= { branch15 1 }

	branch15ElectricEnergy OBJECT-TYPE
        SYNTAX Integer32
        MAX-ACCESS read-only
        STATUS current
        DESCRIPTION
            "branch15 Electric Energy, stored as 0.01 kWh."
        ::= { branch15 2 }

	branch15SwitchStatus OBJECT-TYPE
        SYNTAX Integer32
        MAX-ACCESS read-only
        STATUS current
        DESCRIPTION
            "branch15 Switch Status, stored as 0.01."
        ::= { branch15 3 }
        
	branch15ActivePower OBJECT-TYPE
        SYNTAX Integer32
        MAX-ACCESS read-only
        STATUS current
        DESCRIPTION
            "branch15 Active Power, stored as 0.01 kW."
        ::= { branch15 4 }

	branch15ApparentPower OBJECT-TYPE
        SYNTAX Integer32
        MAX-ACCESS read-only
        STATUS current
        DESCRIPTION
            "branch15 Apparent Power, stored as 0.01 kVA."
        ::= { branch15 5 }

	branch15THDi OBJECT-TYPE
        SYNTAX Integer32
        MAX-ACCESS read-only
        STATUS current
        DESCRIPTION
            "branch15 THDi, stored as 0.01 %."
        ::= { branch15 6 }

	branch15RatedCurrent OBJECT-TYPE
        SYNTAX Integer32
        MAX-ACCESS read-only
        STATUS current
        DESCRIPTION
            "branch15 Rated Current, stored as 0.01 A."
        ::= { branch15 7 }

	branch15LoadRatio OBJECT-TYPE
        SYNTAX Integer32
        MAX-ACCESS read-only
        STATUS current
        DESCRIPTION "
        	branch15 Load Ratio. stored as 0.01 %"
        ::= { branch15 8 }

	branch15PowerFactor OBJECT-TYPE
        SYNTAX Integer32
        MAX-ACCESS read-only
        STATUS current
        DESCRIPTION
            "branch15 Power Factor, stored as 0.01."
        ::= { branch15 9 }


-- ------------------------------------------------------------------------ 
-- 1.2.19 the branch16 group
-- ------------------------------------------------------------------------ 

branch16 OBJECT IDENTIFIER ::= { system 35 }

    branch16Current OBJECT-TYPE
    	SYNTAX Integer32
    	MAX-ACCESS read-only
        STATUS current
        DESCRIPTION
            "branch16 Current, stored as 0.01 A."
        ::= { branch16 1 }

	branch16ElectricEnergy OBJECT-TYPE
        SYNTAX Integer32
        MAX-ACCESS read-only
        STATUS current
        DESCRIPTION
            "branch16 Electric Energy, stored as 0.01 kWh."
        ::= { branch16 2 }

	branch16SwitchStatus OBJECT-TYPE
        SYNTAX Integer32
        MAX-ACCESS read-only
        STATUS current
        DESCRIPTION
            "branch16 Switch Status, stored as 0.01."
        ::= { branch16 3 }
        
	branch16ActivePower OBJECT-TYPE
        SYNTAX Integer32
        MAX-ACCESS read-only
        STATUS current
        DESCRIPTION
            "branch16 Active Power, stored as 0.01 kW."
        ::= { branch16 4 }

	branch16ApparentPower OBJECT-TYPE
        SYNTAX Integer32
        MAX-ACCESS read-only
        STATUS current
        DESCRIPTION
            "branch16 Apparent Power, stored as 0.01 kVA."
        ::= { branch16 5 }

	branch16THDi OBJECT-TYPE
        SYNTAX Integer32
        MAX-ACCESS read-only
        STATUS current
        DESCRIPTION
            "branch16 THDi, stored as 0.01 %."
        ::= { branch16 6 }

	branch16RatedCurrent OBJECT-TYPE
        SYNTAX Integer32
        MAX-ACCESS read-only
        STATUS current
        DESCRIPTION
            "branch16 Rated Current, stored as 0.01 A."
        ::= { branch16 7 }

	branch16LoadRatio OBJECT-TYPE
        SYNTAX Integer32
        MAX-ACCESS read-only
        STATUS current
        DESCRIPTION "
        	branch16 Load Ratio. stored as 0.01 %"
        ::= { branch16 8 }

	branch16PowerFactor OBJECT-TYPE
        SYNTAX Integer32
        MAX-ACCESS read-only
        STATUS current
        DESCRIPTION
            "branch16 Power Factor, stored as 0.01."
        ::= { branch16 9 }


-- ------------------------------------------------------------------------ 
-- 1.2.20 the branch17 group
-- ------------------------------------------------------------------------ 

branch17 OBJECT IDENTIFIER ::= { system 36 }

    branch17Current OBJECT-TYPE
    	SYNTAX Integer32
    	MAX-ACCESS read-only
        STATUS current
        DESCRIPTION
            "branch17 Current, stored as 0.01 A."
        ::= { branch17 1 }

	branch17ElectricEnergy OBJECT-TYPE
        SYNTAX Integer32
        MAX-ACCESS read-only
        STATUS current
        DESCRIPTION
            "branch17 Electric Energy, stored as 0.01 kWh."
        ::= { branch17 2 }

	branch17SwitchStatus OBJECT-TYPE
        SYNTAX Integer32
        MAX-ACCESS read-only
        STATUS current
        DESCRIPTION
            "branch17 Switch Status, stored as 0.01."
        ::= { branch17 3 }
        
	branch17ActivePower OBJECT-TYPE
        SYNTAX Integer32
        MAX-ACCESS read-only
        STATUS current
        DESCRIPTION
            "branch17 Active Power, stored as 0.01 kW."
        ::= { branch17 4 }

	branch17ApparentPower OBJECT-TYPE
        SYNTAX Integer32
        MAX-ACCESS read-only
        STATUS current
        DESCRIPTION
            "branch17 Apparent Power, stored as 0.01 kVA."
        ::= { branch17 5 }

	branch17THDi OBJECT-TYPE
        SYNTAX Integer32
        MAX-ACCESS read-only
        STATUS current
        DESCRIPTION
            "branch17 THDi, stored as 0.01 %."
        ::= { branch17 6 }

	branch17RatedCurrent OBJECT-TYPE
        SYNTAX Integer32
        MAX-ACCESS read-only
        STATUS current
        DESCRIPTION
            "branch17 Rated Current, stored as 0.01 A."
        ::= { branch17 7 }

	branch17LoadRatio OBJECT-TYPE
        SYNTAX Integer32
        MAX-ACCESS read-only
        STATUS current
        DESCRIPTION "
        	branch17 Load Ratio. stored as 0.01 %"
        ::= { branch17 8 }

	branch17PowerFactor OBJECT-TYPE
        SYNTAX Integer32
        MAX-ACCESS read-only
        STATUS current
        DESCRIPTION
            "branch17 Power Factor, stored as 0.01."
        ::= { branch17 9 }


-- ------------------------------------------------------------------------ 
-- 1.2.21 the branch18 group
-- ------------------------------------------------------------------------ 

branch18 OBJECT IDENTIFIER ::= { system 37 }

    branch18Current OBJECT-TYPE
    	SYNTAX Integer32
    	MAX-ACCESS read-only
        STATUS current
        DESCRIPTION
            "branch18 Current, stored as 0.01 A."
        ::= { branch18 1 }

	branch18ElectricEnergy OBJECT-TYPE
        SYNTAX Integer32
        MAX-ACCESS read-only
        STATUS current
        DESCRIPTION
            "branch18 Electric Energy, stored as 0.01 kWh."
        ::= { branch18 2 }

	branch18SwitchStatus OBJECT-TYPE
        SYNTAX Integer32
        MAX-ACCESS read-only
        STATUS current
        DESCRIPTION
            "branch18 Switch Status, stored as 0.01."
        ::= { branch18 3 }
        
	branch18ActivePower OBJECT-TYPE
        SYNTAX Integer32
        MAX-ACCESS read-only
        STATUS current
        DESCRIPTION
            "branch18 Active Power, stored as 0.01 kW."
        ::= { branch18 4 }

	branch18ApparentPower OBJECT-TYPE
        SYNTAX Integer32
        MAX-ACCESS read-only
        STATUS current
        DESCRIPTION
            "branch18 Apparent Power, stored as 0.01 kVA."
        ::= { branch18 5 }

	branch18THDi OBJECT-TYPE
        SYNTAX Integer32
        MAX-ACCESS read-only
        STATUS current
        DESCRIPTION
            "branch18 THDi, stored as 0.01 %."
        ::= { branch18 6 }

	branch18RatedCurrent OBJECT-TYPE
        SYNTAX Integer32
        MAX-ACCESS read-only
        STATUS current
        DESCRIPTION
            "branch18 Rated Current, stored as 0.01 A."
        ::= { branch18 7 }

	branch18LoadRatio OBJECT-TYPE
        SYNTAX Integer32
        MAX-ACCESS read-only
        STATUS current
        DESCRIPTION "
        	branch18 Load Ratio. stored as 0.01 %"
        ::= { branch18 8 }

	branch18PowerFactor OBJECT-TYPE
        SYNTAX Integer32
        MAX-ACCESS read-only
        STATUS current
        DESCRIPTION
            "branch18 Power Factor, stored as 0.01."
        ::= { branch18 9 }


-- ------------------------------------------------------------------------ 
-- 1.2.22 the branch19 group
-- ------------------------------------------------------------------------ 

branch19 OBJECT IDENTIFIER ::= { system 38 }

    branch19Current OBJECT-TYPE
    	SYNTAX Integer32
    	MAX-ACCESS read-only
        STATUS current
        DESCRIPTION
            "branch19 Current, stored as 0.01 A."
        ::= { branch19 1 }

	branch19ElectricEnergy OBJECT-TYPE
        SYNTAX Integer32
        MAX-ACCESS read-only
        STATUS current
        DESCRIPTION
            "branch19 Electric Energy, stored as 0.01 kWh."
        ::= { branch19 2 }

	branch19SwitchStatus OBJECT-TYPE
        SYNTAX Integer32
        MAX-ACCESS read-only
        STATUS current
        DESCRIPTION
            "branch19 Switch Status, stored as 0.01."
        ::= { branch19 3 }
        
	branch19ActivePower OBJECT-TYPE
        SYNTAX Integer32
        MAX-ACCESS read-only
        STATUS current
        DESCRIPTION
            "branch19 Active Power, stored as 0.01 kW."
        ::= { branch19 4 }

	branch19ApparentPower OBJECT-TYPE
        SYNTAX Integer32
        MAX-ACCESS read-only
        STATUS current
        DESCRIPTION
            "branch19 Apparent Power, stored as 0.01 kVA."
        ::= { branch19 5 }

	branch19THDi OBJECT-TYPE
        SYNTAX Integer32
        MAX-ACCESS read-only
        STATUS current
        DESCRIPTION
            "branch19 THDi, stored as 0.01 %."
        ::= { branch19 6 }

	branch19RatedCurrent OBJECT-TYPE
        SYNTAX Integer32
        MAX-ACCESS read-only
        STATUS current
        DESCRIPTION
            "branch19 Rated Current, stored as 0.01 A."
        ::= { branch19 7 }

	branch19LoadRatio OBJECT-TYPE
        SYNTAX Integer32
        MAX-ACCESS read-only
        STATUS current
        DESCRIPTION "
        	branch19 Load Ratio. stored as 0.01 %"
        ::= { branch19 8 }

	branch19PowerFactor OBJECT-TYPE
        SYNTAX Integer32
        MAX-ACCESS read-only
        STATUS current
        DESCRIPTION
            "branch19 Power Factor, stored as 0.01."
        ::= { branch19 9 }


-- ------------------------------------------------------------------------ 
-- 1.2.23 the branch20 group
-- ------------------------------------------------------------------------ 

branch20 OBJECT IDENTIFIER ::= { system 39 }

    branch20Current OBJECT-TYPE
    	SYNTAX Integer32
    	MAX-ACCESS read-only
        STATUS current
        DESCRIPTION
            "branch20 Current, stored as 0.01 A."
        ::= { branch20 1 }

	branch20ElectricEnergy OBJECT-TYPE
        SYNTAX Integer32
        MAX-ACCESS read-only
        STATUS current
        DESCRIPTION
            "branch20 Electric Energy, stored as 0.01 kWh."
        ::= { branch20 2 }

	branch20SwitchStatus OBJECT-TYPE
        SYNTAX Integer32
        MAX-ACCESS read-only
        STATUS current
        DESCRIPTION
            "branch20 Switch Status, stored as 0.01."
        ::= { branch20 3 }
        
	branch20ActivePower OBJECT-TYPE
        SYNTAX Integer32
        MAX-ACCESS read-only
        STATUS current
        DESCRIPTION
            "branch20 Active Power, stored as 0.01 kW."
        ::= { branch20 4 }

	branch20ApparentPower OBJECT-TYPE
        SYNTAX Integer32
        MAX-ACCESS read-only
        STATUS current
        DESCRIPTION
            "branch20 Apparent Power, stored as 0.01 kVA."
        ::= { branch20 5 }

	branch20THDi OBJECT-TYPE
        SYNTAX Integer32
        MAX-ACCESS read-only
        STATUS current
        DESCRIPTION
            "branch20 THDi, stored as 0.01 %."
        ::= { branch20 6 }

	branch20RatedCurrent OBJECT-TYPE
        SYNTAX Integer32
        MAX-ACCESS read-only
        STATUS current
        DESCRIPTION
            "branch20 Rated Current, stored as 0.01 A."
        ::= { branch20 7 }

	branch20LoadRatio OBJECT-TYPE
        SYNTAX Integer32
        MAX-ACCESS read-only
        STATUS current
        DESCRIPTION "
        	branch20 Load Ratio. stored as 0.01 %"
        ::= { branch20 8 }

	branch20PowerFactor OBJECT-TYPE
        SYNTAX Integer32
        MAX-ACCESS read-only
        STATUS current
        DESCRIPTION
            "branch20 Power Factor, stored as 0.01."
        ::= { branch20 9 }


-- ------------------------------------------------------------------------ 
-- 1.2.24 the branch21 group
-- ------------------------------------------------------------------------ 

branch21 OBJECT IDENTIFIER ::= { system 40 }

    branch21Current OBJECT-TYPE
    	SYNTAX Integer32
    	MAX-ACCESS read-only
        STATUS current
        DESCRIPTION
            "branch21 Current, stored as 0.01 A."
        ::= { branch21 1 }

	branch21ElectricEnergy OBJECT-TYPE
        SYNTAX Integer32
        MAX-ACCESS read-only
        STATUS current
        DESCRIPTION
            "branch21 Electric Energy, stored as 0.01 kWh."
        ::= { branch21 2 }

	branch21SwitchStatus OBJECT-TYPE
        SYNTAX Integer32
        MAX-ACCESS read-only
        STATUS current
        DESCRIPTION
            "branch21 Switch Status, stored as 0.01."
        ::= { branch21 3 }
        
	branch21ActivePower OBJECT-TYPE
        SYNTAX Integer32
        MAX-ACCESS read-only
        STATUS current
        DESCRIPTION
            "branch21 Active Power, stored as 0.01 kW."
        ::= { branch21 4 }

	branch21ApparentPower OBJECT-TYPE
        SYNTAX Integer32
        MAX-ACCESS read-only
        STATUS current
        DESCRIPTION
            "branch21 Apparent Power, stored as 0.01 kVA."
        ::= { branch21 5 }

	branch21THDi OBJECT-TYPE
        SYNTAX Integer32
        MAX-ACCESS read-only
        STATUS current
        DESCRIPTION
            "branch21 THDi, stored as 0.01 %."
        ::= { branch21 6 }

	branch21RatedCurrent OBJECT-TYPE
        SYNTAX Integer32
        MAX-ACCESS read-only
        STATUS current
        DESCRIPTION
            "branch21 Rated Current, stored as 0.01 A."
        ::= { branch21 7 }

	branch21LoadRatio OBJECT-TYPE
        SYNTAX Integer32
        MAX-ACCESS read-only
        STATUS current
        DESCRIPTION "
        	branch21 Load Ratio. stored as 0.01 %"
        ::= { branch21 8 }

	branch21PowerFactor OBJECT-TYPE
        SYNTAX Integer32
        MAX-ACCESS read-only
        STATUS current
        DESCRIPTION
            "branch21 Power Factor, stored as 0.01."
        ::= { branch21 9 }


-- ------------------------------------------------------------------------ 
-- 1.2.25 the branch22 group
-- ------------------------------------------------------------------------ 

branch22 OBJECT IDENTIFIER ::= { system 41 }

    branch22Current OBJECT-TYPE
    	SYNTAX Integer32
    	MAX-ACCESS read-only
        STATUS current
        DESCRIPTION
            "branch22 Current, stored as 0.01 A."
        ::= { branch22 1 }

	branch22ElectricEnergy OBJECT-TYPE
        SYNTAX Integer32
        MAX-ACCESS read-only
        STATUS current
        DESCRIPTION
            "branch22 Electric Energy, stored as 0.01 kWh."
        ::= { branch22 2 }

	branch22SwitchStatus OBJECT-TYPE
        SYNTAX Integer32
        MAX-ACCESS read-only
        STATUS current
        DESCRIPTION
            "branch22 Switch Status, stored as 0.01."
        ::= { branch22 3 }
        
	branch22ActivePower OBJECT-TYPE
        SYNTAX Integer32
        MAX-ACCESS read-only
        STATUS current
        DESCRIPTION
            "branch22 Active Power, stored as 0.01 kW."
        ::= { branch22 4 }

	branch22ApparentPower OBJECT-TYPE
        SYNTAX Integer32
        MAX-ACCESS read-only
        STATUS current
        DESCRIPTION
            "branch22 Apparent Power, stored as 0.01 kVA."
        ::= { branch22 5 }

	branch22THDi OBJECT-TYPE
        SYNTAX Integer32
        MAX-ACCESS read-only
        STATUS current
        DESCRIPTION
            "branch22 THDi, stored as 0.01 %."
        ::= { branch22 6 }

	branch22RatedCurrent OBJECT-TYPE
        SYNTAX Integer32
        MAX-ACCESS read-only
        STATUS current
        DESCRIPTION
            "branch22 Rated Current, stored as 0.01 A."
        ::= { branch22 7 }

	branch22LoadRatio OBJECT-TYPE
        SYNTAX Integer32
        MAX-ACCESS read-only
        STATUS current
        DESCRIPTION "
        	branch22 Load Ratio. stored as 0.01 %"
        ::= { branch22 8 }

	branch22PowerFactor OBJECT-TYPE
        SYNTAX Integer32
        MAX-ACCESS read-only
        STATUS current
        DESCRIPTION
            "branch22 Power Factor, stored as 0.01."
        ::= { branch22 9 }


-- ------------------------------------------------------------------------ 
-- 1.2.26 the branch23 group
-- ------------------------------------------------------------------------ 

branch23 OBJECT IDENTIFIER ::= { system 42 }

    branch23Current OBJECT-TYPE
    	SYNTAX Integer32
    	MAX-ACCESS read-only
        STATUS current
        DESCRIPTION
            "branch23 Current, stored as 0.01 A."
        ::= { branch23 1 }

	branch23ElectricEnergy OBJECT-TYPE
        SYNTAX Integer32
        MAX-ACCESS read-only
        STATUS current
        DESCRIPTION
            "branch23 Electric Energy, stored as 0.01 kWh."
        ::= { branch23 2 }

	branch23SwitchStatus OBJECT-TYPE
        SYNTAX Integer32
        MAX-ACCESS read-only
        STATUS current
        DESCRIPTION
            "branch23 Switch Status, stored as 0.01."
        ::= { branch23 3 }
        
	branch23ActivePower OBJECT-TYPE
        SYNTAX Integer32
        MAX-ACCESS read-only
        STATUS current
        DESCRIPTION
            "branch23 Active Power, stored as 0.01 kW."
        ::= { branch23 4 }

	branch23ApparentPower OBJECT-TYPE
        SYNTAX Integer32
        MAX-ACCESS read-only
        STATUS current
        DESCRIPTION
            "branch23 Apparent Power, stored as 0.01 kVA."
        ::= { branch23 5 }

	branch23THDi OBJECT-TYPE
        SYNTAX Integer32
        MAX-ACCESS read-only
        STATUS current
        DESCRIPTION
            "branch23 THDi, stored as 0.01 %."
        ::= { branch23 6 }

	branch23RatedCurrent OBJECT-TYPE
        SYNTAX Integer32
        MAX-ACCESS read-only
        STATUS current
        DESCRIPTION
            "branch23 Rated Current, stored as 0.01 A."
        ::= { branch23 7 }

	branch23LoadRatio OBJECT-TYPE
        SYNTAX Integer32
        MAX-ACCESS read-only
        STATUS current
        DESCRIPTION "
        	branch23 Load Ratio. stored as 0.01 %"
        ::= { branch23 8 }

	branch23PowerFactor OBJECT-TYPE
        SYNTAX Integer32
        MAX-ACCESS read-only
        STATUS current
        DESCRIPTION
            "branch23 Power Factor, stored as 0.01."
        ::= { branch23 9 }


-- ------------------------------------------------------------------------ 
-- 1.2.27 the branch24 group
-- ------------------------------------------------------------------------ 

branch24 OBJECT IDENTIFIER ::= { system 43 }

    branch24Current OBJECT-TYPE
    	SYNTAX Integer32
    	MAX-ACCESS read-only
        STATUS current
        DESCRIPTION
            "branch24 Current, stored as 0.01 A."
        ::= { branch24 1 }

	branch24ElectricEnergy OBJECT-TYPE
        SYNTAX Integer32
        MAX-ACCESS read-only
        STATUS current
        DESCRIPTION
            "branch24 Electric Energy, stored as 0.01 kWh."
        ::= { branch24 2 }

	branch24SwitchStatus OBJECT-TYPE
        SYNTAX Integer32
        MAX-ACCESS read-only
        STATUS current
        DESCRIPTION
            "branch24 Switch Status, stored as 0.01."
        ::= { branch24 3 }
        
	branch24ActivePower OBJECT-TYPE
        SYNTAX Integer32
        MAX-ACCESS read-only
        STATUS current
        DESCRIPTION
            "branch24 Active Power, stored as 0.01 kW."
        ::= { branch24 4 }

	branch24ApparentPower OBJECT-TYPE
        SYNTAX Integer32
        MAX-ACCESS read-only
        STATUS current
        DESCRIPTION
            "branch24 Apparent Power, stored as 0.01 kVA."
        ::= { branch24 5 }

	branch24THDi OBJECT-TYPE
        SYNTAX Integer32
        MAX-ACCESS read-only
        STATUS current
        DESCRIPTION
            "branch24 THDi, stored as 0.01 %."
        ::= { branch24 6 }

	branch24RatedCurrent OBJECT-TYPE
        SYNTAX Integer32
        MAX-ACCESS read-only
        STATUS current
        DESCRIPTION
            "branch24 Rated Current, stored as 0.01 A."
        ::= { branch24 7 }

	branch24LoadRatio OBJECT-TYPE
        SYNTAX Integer32
        MAX-ACCESS read-only
        STATUS current
        DESCRIPTION "
        	branch24 Load Ratio. stored as 0.01 %"
        ::= { branch24 8 }

	branch24PowerFactor OBJECT-TYPE
        SYNTAX Integer32
        MAX-ACCESS read-only
        STATUS current
        DESCRIPTION
            "branch24 Power Factor, stored as 0.01."
        ::= { branch24 9 }


-- ------------------------------------------------------------------------ 
-- 1.2.28 the branch25 group
-- ------------------------------------------------------------------------ 

branch25 OBJECT IDENTIFIER ::= { system 44 }

    branch25Current OBJECT-TYPE
    	SYNTAX Integer32
    	MAX-ACCESS read-only
        STATUS current
        DESCRIPTION
            "branch25 Current, stored as 0.01 A."
        ::= { branch25 1 }

	branch25ElectricEnergy OBJECT-TYPE
        SYNTAX Integer32
        MAX-ACCESS read-only
        STATUS current
        DESCRIPTION
            "branch25 Electric Energy, stored as 0.01 kWh."
        ::= { branch25 2 }

	branch25SwitchStatus OBJECT-TYPE
        SYNTAX Integer32
        MAX-ACCESS read-only
        STATUS current
        DESCRIPTION
            "branch25 Switch Status, stored as 0.01."
        ::= { branch25 3 }
        
	branch25ActivePower OBJECT-TYPE
        SYNTAX Integer32
        MAX-ACCESS read-only
        STATUS current
        DESCRIPTION
            "branch25 Active Power, stored as 0.01 kW."
        ::= { branch25 4 }

	branch25ApparentPower OBJECT-TYPE
        SYNTAX Integer32
        MAX-ACCESS read-only
        STATUS current
        DESCRIPTION
            "branch25 Apparent Power, stored as 0.01 kVA."
        ::= { branch25 5 }

	branch25THDi OBJECT-TYPE
        SYNTAX Integer32
        MAX-ACCESS read-only
        STATUS current
        DESCRIPTION
            "branch25 THDi, stored as 0.01 %."
        ::= { branch25 6 }

	branch25RatedCurrent OBJECT-TYPE
        SYNTAX Integer32
        MAX-ACCESS read-only
        STATUS current
        DESCRIPTION
            "branch25 Rated Current, stored as 0.01 A."
        ::= { branch25 7 }

	branch25LoadRatio OBJECT-TYPE
        SYNTAX Integer32
        MAX-ACCESS read-only
        STATUS current
        DESCRIPTION "
        	branch25 Load Ratio. stored as 0.01 %"
        ::= { branch25 8 }

	branch25PowerFactor OBJECT-TYPE
        SYNTAX Integer32
        MAX-ACCESS read-only
        STATUS current
        DESCRIPTION
            "branch25 Power Factor, stored as 0.01."
        ::= { branch25 9 }


-- ------------------------------------------------------------------------ 
-- 1.2.29 the branch26 group
-- ------------------------------------------------------------------------ 

branch26 OBJECT IDENTIFIER ::= { system 45 }

    branch26Current OBJECT-TYPE
    	SYNTAX Integer32
    	MAX-ACCESS read-only
        STATUS current
        DESCRIPTION
            "branch26 Current, stored as 0.01 A."
        ::= { branch26 1 }

	branch26ElectricEnergy OBJECT-TYPE
        SYNTAX Integer32
        MAX-ACCESS read-only
        STATUS current
        DESCRIPTION
            "branch26 Electric Energy, stored as 0.01 kWh."
        ::= { branch26 2 }

	branch26SwitchStatus OBJECT-TYPE
        SYNTAX Integer32
        MAX-ACCESS read-only
        STATUS current
        DESCRIPTION
            "branch26 Switch Status, stored as 0.01."
        ::= { branch26 3 }
        
	branch26ActivePower OBJECT-TYPE
        SYNTAX Integer32
        MAX-ACCESS read-only
        STATUS current
        DESCRIPTION
            "branch26 Active Power, stored as 0.01 kW."
        ::= { branch26 4 }

	branch26ApparentPower OBJECT-TYPE
        SYNTAX Integer32
        MAX-ACCESS read-only
        STATUS current
        DESCRIPTION
            "branch26 Apparent Power, stored as 0.01 kVA."
        ::= { branch26 5 }

	branch26THDi OBJECT-TYPE
        SYNTAX Integer32
        MAX-ACCESS read-only
        STATUS current
        DESCRIPTION
            "branch26 THDi, stored as 0.01 %."
        ::= { branch26 6 }

	branch26RatedCurrent OBJECT-TYPE
        SYNTAX Integer32
        MAX-ACCESS read-only
        STATUS current
        DESCRIPTION
            "branch26 Rated Current, stored as 0.01 A."
        ::= { branch26 7 }

	branch26LoadRatio OBJECT-TYPE
        SYNTAX Integer32
        MAX-ACCESS read-only
        STATUS current
        DESCRIPTION "
        	branch26 Load Ratio. stored as 0.01 %"
        ::= { branch26 8 }

	branch26PowerFactor OBJECT-TYPE
        SYNTAX Integer32
        MAX-ACCESS read-only
        STATUS current
        DESCRIPTION
            "branch26 Power Factor, stored as 0.01."
        ::= { branch26 9 }


-- ------------------------------------------------------------------------ 
-- 1.2.30 the branch27 group
-- ------------------------------------------------------------------------ 

branch27 OBJECT IDENTIFIER ::= { system 46 }

    branch27Current OBJECT-TYPE
    	SYNTAX Integer32
    	MAX-ACCESS read-only
        STATUS current
        DESCRIPTION
            "branch27 Current, stored as 0.01 A."
        ::= { branch27 1 }

	branch27ElectricEnergy OBJECT-TYPE
        SYNTAX Integer32
        MAX-ACCESS read-only
        STATUS current
        DESCRIPTION
            "branch27 Electric Energy, stored as 0.01 kWh."
        ::= { branch27 2 }

	branch27SwitchStatus OBJECT-TYPE
        SYNTAX Integer32
        MAX-ACCESS read-only
        STATUS current
        DESCRIPTION
            "branch27 Switch Status, stored as 0.01."
        ::= { branch27 3 }
        
	branch27ActivePower OBJECT-TYPE
        SYNTAX Integer32
        MAX-ACCESS read-only
        STATUS current
        DESCRIPTION
            "branch27 Active Power, stored as 0.01 kW."
        ::= { branch27 4 }

	branch27ApparentPower OBJECT-TYPE
        SYNTAX Integer32
        MAX-ACCESS read-only
        STATUS current
        DESCRIPTION
            "branch27 Apparent Power, stored as 0.01 kVA."
        ::= { branch27 5 }

	branch27THDi OBJECT-TYPE
        SYNTAX Integer32
        MAX-ACCESS read-only
        STATUS current
        DESCRIPTION
            "branch27 THDi, stored as 0.01 %."
        ::= { branch27 6 }

	branch27RatedCurrent OBJECT-TYPE
        SYNTAX Integer32
        MAX-ACCESS read-only
        STATUS current
        DESCRIPTION
            "branch27 Rated Current, stored as 0.01 A."
        ::= { branch27 7 }

	branch27LoadRatio OBJECT-TYPE
        SYNTAX Integer32
        MAX-ACCESS read-only
        STATUS current
        DESCRIPTION "
        	branch27 Load Ratio. stored as 0.01 %"
        ::= { branch27 8 }

	branch27PowerFactor OBJECT-TYPE
        SYNTAX Integer32
        MAX-ACCESS read-only
        STATUS current
        DESCRIPTION
            "branch27 Power Factor, stored as 0.01."
        ::= { branch27 9 }


-- ------------------------------------------------------------------------ 
-- 1.2.31 the branch28 group
-- ------------------------------------------------------------------------ 

branch28 OBJECT IDENTIFIER ::= { system 47 }

    branch28Current OBJECT-TYPE
    	SYNTAX Integer32
    	MAX-ACCESS read-only
        STATUS current
        DESCRIPTION
            "branch28 Current, stored as 0.01 A."
        ::= { branch28 1 }

	branch28ElectricEnergy OBJECT-TYPE
        SYNTAX Integer32
        MAX-ACCESS read-only
        STATUS current
        DESCRIPTION
            "branch28 Electric Energy, stored as 0.01 kWh."
        ::= { branch28 2 }

	branch28SwitchStatus OBJECT-TYPE
        SYNTAX Integer32
        MAX-ACCESS read-only
        STATUS current
        DESCRIPTION
            "branch28 Switch Status, stored as 0.01."
        ::= { branch28 3 }
        
	branch28ActivePower OBJECT-TYPE
        SYNTAX Integer32
        MAX-ACCESS read-only
        STATUS current
        DESCRIPTION
            "branch28 Active Power, stored as 0.01 kW."
        ::= { branch28 4 }

	branch28ApparentPower OBJECT-TYPE
        SYNTAX Integer32
        MAX-ACCESS read-only
        STATUS current
        DESCRIPTION
            "branch28 Apparent Power, stored as 0.01 kVA."
        ::= { branch28 5 }

	branch28THDi OBJECT-TYPE
        SYNTAX Integer32
        MAX-ACCESS read-only
        STATUS current
        DESCRIPTION
            "branch28 THDi, stored as 0.01 %."
        ::= { branch28 6 }

	branch28RatedCurrent OBJECT-TYPE
        SYNTAX Integer32
        MAX-ACCESS read-only
        STATUS current
        DESCRIPTION
            "branch28 Rated Current, stored as 0.01 A."
        ::= { branch28 7 }

	branch28LoadRatio OBJECT-TYPE
        SYNTAX Integer32
        MAX-ACCESS read-only
        STATUS current
        DESCRIPTION "
        	branch28 Load Ratio. stored as 0.01 %"
        ::= { branch28 8 }

	branch28PowerFactor OBJECT-TYPE
        SYNTAX Integer32
        MAX-ACCESS read-only
        STATUS current
        DESCRIPTION
            "branch28 Power Factor, stored as 0.01."
        ::= { branch28 9 }


-- ------------------------------------------------------------------------ 
-- 1.2.32 the branch29 group
-- ------------------------------------------------------------------------ 

branch29 OBJECT IDENTIFIER ::= { system 48 }

    branch29Current OBJECT-TYPE
    	SYNTAX Integer32
    	MAX-ACCESS read-only
        STATUS current
        DESCRIPTION
            "branch29 Current, stored as 0.01 A."
        ::= { branch29 1 }

	branch29ElectricEnergy OBJECT-TYPE
        SYNTAX Integer32
        MAX-ACCESS read-only
        STATUS current
        DESCRIPTION
            "branch29 Electric Energy, stored as 0.01 kWh."
        ::= { branch29 2 }

	branch29SwitchStatus OBJECT-TYPE
        SYNTAX Integer32
        MAX-ACCESS read-only
        STATUS current
        DESCRIPTION
            "branch29 Switch Status, stored as 0.01."
        ::= { branch29 3 }
        
	branch29ActivePower OBJECT-TYPE
        SYNTAX Integer32
        MAX-ACCESS read-only
        STATUS current
        DESCRIPTION
            "branch29 Active Power, stored as 0.01 kW."
        ::= { branch29 4 }

	branch29ApparentPower OBJECT-TYPE
        SYNTAX Integer32
        MAX-ACCESS read-only
        STATUS current
        DESCRIPTION
            "branch29 Apparent Power, stored as 0.01 kVA."
        ::= { branch29 5 }

	branch29THDi OBJECT-TYPE
        SYNTAX Integer32
        MAX-ACCESS read-only
        STATUS current
        DESCRIPTION
            "branch29 THDi, stored as 0.01 %."
        ::= { branch29 6 }

	branch29RatedCurrent OBJECT-TYPE
        SYNTAX Integer32
        MAX-ACCESS read-only
        STATUS current
        DESCRIPTION
            "branch29 Rated Current, stored as 0.01 A."
        ::= { branch29 7 }

	branch29LoadRatio OBJECT-TYPE
        SYNTAX Integer32
        MAX-ACCESS read-only
        STATUS current
        DESCRIPTION "
        	branch29 Load Ratio. stored as 0.01 %"
        ::= { branch29 8 }

	branch29PowerFactor OBJECT-TYPE
        SYNTAX Integer32
        MAX-ACCESS read-only
        STATUS current
        DESCRIPTION
            "branch29 Power Factor, stored as 0.01."
        ::= { branch29 9 }


-- ------------------------------------------------------------------------ 
-- 1.2.33 the branch30 group
-- ------------------------------------------------------------------------ 

branch30 OBJECT IDENTIFIER ::= { system 49 }

    branch30Current OBJECT-TYPE
    	SYNTAX Integer32
    	MAX-ACCESS read-only
        STATUS current
        DESCRIPTION
            "branch30 Current, stored as 0.01 A."
        ::= { branch30 1 }

	branch30ElectricEnergy OBJECT-TYPE
        SYNTAX Integer32
        MAX-ACCESS read-only
        STATUS current
        DESCRIPTION
            "branch30 Electric Energy, stored as 0.01 kWh."
        ::= { branch30 2 }

	branch30SwitchStatus OBJECT-TYPE
        SYNTAX Integer32
        MAX-ACCESS read-only
        STATUS current
        DESCRIPTION
            "branch30 Switch Status, stored as 0.01."
        ::= { branch30 3 }
        
	branch30ActivePower OBJECT-TYPE
        SYNTAX Integer32
        MAX-ACCESS read-only
        STATUS current
        DESCRIPTION
            "branch30 Active Power, stored as 0.01 kW."
        ::= { branch30 4 }

	branch30ApparentPower OBJECT-TYPE
        SYNTAX Integer32
        MAX-ACCESS read-only
        STATUS current
        DESCRIPTION
            "branch30 Apparent Power, stored as 0.01 kVA."
        ::= { branch30 5 }

	branch30THDi OBJECT-TYPE
        SYNTAX Integer32
        MAX-ACCESS read-only
        STATUS current
        DESCRIPTION
            "branch30 THDi, stored as 0.01 %."
        ::= { branch30 6 }

	branch30RatedCurrent OBJECT-TYPE
        SYNTAX Integer32
        MAX-ACCESS read-only
        STATUS current
        DESCRIPTION
            "branch30 Rated Current, stored as 0.01 A."
        ::= { branch30 7 }

	branch30LoadRatio OBJECT-TYPE
        SYNTAX Integer32
        MAX-ACCESS read-only
        STATUS current
        DESCRIPTION "
        	branch30 Load Ratio. stored as 0.01 %"
        ::= { branch30 8 }

	branch30PowerFactor OBJECT-TYPE
        SYNTAX Integer32
        MAX-ACCESS read-only
        STATUS current
        DESCRIPTION
            "branch30 Power Factor, stored as 0.01."
        ::= { branch30 9 }


-- ------------------------------------------------------------------------ 
-- 1.2.34 the branch31 group
-- ------------------------------------------------------------------------ 

branch31 OBJECT IDENTIFIER ::= { system 50 }

    branch31Current OBJECT-TYPE
    	SYNTAX Integer32
    	MAX-ACCESS read-only
        STATUS current
        DESCRIPTION
            "branch31 Current, stored as 0.01 A."
        ::= { branch31 1 }

	branch31ElectricEnergy OBJECT-TYPE
        SYNTAX Integer32
        MAX-ACCESS read-only
        STATUS current
        DESCRIPTION
            "branch31 Electric Energy, stored as 0.01 kWh."
        ::= { branch31 2 }

	branch31SwitchStatus OBJECT-TYPE
        SYNTAX Integer32
        MAX-ACCESS read-only
        STATUS current
        DESCRIPTION
            "branch31 Switch Status, stored as 0.01."
        ::= { branch31 3 }
        
	branch31ActivePower OBJECT-TYPE
        SYNTAX Integer32
        MAX-ACCESS read-only
        STATUS current
        DESCRIPTION
            "branch31 Active Power, stored as 0.01 kW."
        ::= { branch31 4 }

	branch31ApparentPower OBJECT-TYPE
        SYNTAX Integer32
        MAX-ACCESS read-only
        STATUS current
        DESCRIPTION
            "branch31 Apparent Power, stored as 0.01 kVA."
        ::= { branch31 5 }

	branch31THDi OBJECT-TYPE
        SYNTAX Integer32
        MAX-ACCESS read-only
        STATUS current
        DESCRIPTION
            "branch31 THDi, stored as 0.01 %."
        ::= { branch31 6 }

	branch31RatedCurrent OBJECT-TYPE
        SYNTAX Integer32
        MAX-ACCESS read-only
        STATUS current
        DESCRIPTION
            "branch31 Rated Current, stored as 0.01 A."
        ::= { branch31 7 }

	branch31LoadRatio OBJECT-TYPE
        SYNTAX Integer32
        MAX-ACCESS read-only
        STATUS current
        DESCRIPTION "
        	branch31 Load Ratio. stored as 0.01 %"
        ::= { branch31 8 }

	branch31PowerFactor OBJECT-TYPE
        SYNTAX Integer32
        MAX-ACCESS read-only
        STATUS current
        DESCRIPTION
            "branch31 Power Factor, stored as 0.01."
        ::= { branch31 9 }


-- ------------------------------------------------------------------------ 
-- 1.2.35 the branch32 group
-- ------------------------------------------------------------------------ 

branch32 OBJECT IDENTIFIER ::= { system 51 }

    branch32Current OBJECT-TYPE
    	SYNTAX Integer32
    	MAX-ACCESS read-only
        STATUS current
        DESCRIPTION
            "branch32 Current, stored as 0.01 A."
        ::= { branch32 1 }

	branch32ElectricEnergy OBJECT-TYPE
        SYNTAX Integer32
        MAX-ACCESS read-only
        STATUS current
        DESCRIPTION
            "branch32 Electric Energy, stored as 0.01 kWh."
        ::= { branch32 2 }

	branch32SwitchStatus OBJECT-TYPE
        SYNTAX Integer32
        MAX-ACCESS read-only
        STATUS current
        DESCRIPTION
            "branch32 Switch Status, stored as 0.01."
        ::= { branch32 3 }
        
	branch32ActivePower OBJECT-TYPE
        SYNTAX Integer32
        MAX-ACCESS read-only
        STATUS current
        DESCRIPTION
            "branch32 Active Power, stored as 0.01 kW."
        ::= { branch32 4 }

	branch32ApparentPower OBJECT-TYPE
        SYNTAX Integer32
        MAX-ACCESS read-only
        STATUS current
        DESCRIPTION
            "branch32 Apparent Power, stored as 0.01 kVA."
        ::= { branch32 5 }

	branch32THDi OBJECT-TYPE
        SYNTAX Integer32
        MAX-ACCESS read-only
        STATUS current
        DESCRIPTION
            "branch32 THDi, stored as 0.01 %."
        ::= { branch32 6 }

	branch32RatedCurrent OBJECT-TYPE
        SYNTAX Integer32
        MAX-ACCESS read-only
        STATUS current
        DESCRIPTION
            "branch32 Rated Current, stored as 0.01 A."
        ::= { branch32 7 }

	branch32LoadRatio OBJECT-TYPE
        SYNTAX Integer32
        MAX-ACCESS read-only
        STATUS current
        DESCRIPTION "
        	branch32 Load Ratio. stored as 0.01 %"
        ::= { branch32 8 }

	branch32PowerFactor OBJECT-TYPE
        SYNTAX Integer32
        MAX-ACCESS read-only
        STATUS current
        DESCRIPTION
            "branch32 Power Factor, stored as 0.01."
        ::= { branch32 9 }


-- ------------------------------------------------------------------------ 
-- 1.2.36 the branch33 group
-- ------------------------------------------------------------------------ 

branch33 OBJECT IDENTIFIER ::= { system 52 }

    branch33Current OBJECT-TYPE
    	SYNTAX Integer32
    	MAX-ACCESS read-only
        STATUS current
        DESCRIPTION
            "branch33 Current, stored as 0.01 A."
        ::= { branch33 1 }

	branch33ElectricEnergy OBJECT-TYPE
        SYNTAX Integer32
        MAX-ACCESS read-only
        STATUS current
        DESCRIPTION
            "branch33 Electric Energy, stored as 0.01 kWh."
        ::= { branch33 2 }

	branch33SwitchStatus OBJECT-TYPE
        SYNTAX Integer32
        MAX-ACCESS read-only
        STATUS current
        DESCRIPTION
            "branch33 Switch Status, stored as 0.01."
        ::= { branch33 3 }
        
	branch33ActivePower OBJECT-TYPE
        SYNTAX Integer32
        MAX-ACCESS read-only
        STATUS current
        DESCRIPTION
            "branch33 Active Power, stored as 0.01 kW."
        ::= { branch33 4 }

	branch33ApparentPower OBJECT-TYPE
        SYNTAX Integer32
        MAX-ACCESS read-only
        STATUS current
        DESCRIPTION
            "branch33 Apparent Power, stored as 0.01 kVA."
        ::= { branch33 5 }

	branch33THDi OBJECT-TYPE
        SYNTAX Integer32
        MAX-ACCESS read-only
        STATUS current
        DESCRIPTION
            "branch33 THDi, stored as 0.01 %."
        ::= { branch33 6 }

	branch33RatedCurrent OBJECT-TYPE
        SYNTAX Integer32
        MAX-ACCESS read-only
        STATUS current
        DESCRIPTION
            "branch33 Rated Current, stored as 0.01 A."
        ::= { branch33 7 }

	branch33LoadRatio OBJECT-TYPE
        SYNTAX Integer32
        MAX-ACCESS read-only
        STATUS current
        DESCRIPTION "
        	branch33 Load Ratio. stored as 0.01 %"
        ::= { branch33 8 }

	branch33PowerFactor OBJECT-TYPE
        SYNTAX Integer32
        MAX-ACCESS read-only
        STATUS current
        DESCRIPTION
            "branch33 Power Factor, stored as 0.01."
        ::= { branch33 9 }


-- ------------------------------------------------------------------------ 
-- 1.2.37 the branch34 group
-- ------------------------------------------------------------------------ 

branch34 OBJECT IDENTIFIER ::= { system 53 }

    branch34Current OBJECT-TYPE
    	SYNTAX Integer32
    	MAX-ACCESS read-only
        STATUS current
        DESCRIPTION
            "branch34 Current, stored as 0.01 A."
        ::= { branch34 1 }

	branch34ElectricEnergy OBJECT-TYPE
        SYNTAX Integer32
        MAX-ACCESS read-only
        STATUS current
        DESCRIPTION
            "branch34 Electric Energy, stored as 0.01 kWh."
        ::= { branch34 2 }

	branch34SwitchStatus OBJECT-TYPE
        SYNTAX Integer32
        MAX-ACCESS read-only
        STATUS current
        DESCRIPTION
            "branch34 Switch Status, stored as 0.01."
        ::= { branch34 3 }
        
	branch34ActivePower OBJECT-TYPE
        SYNTAX Integer32
        MAX-ACCESS read-only
        STATUS current
        DESCRIPTION
            "branch34 Active Power, stored as 0.01 kW."
        ::= { branch34 4 }

	branch34ApparentPower OBJECT-TYPE
        SYNTAX Integer32
        MAX-ACCESS read-only
        STATUS current
        DESCRIPTION
            "branch34 Apparent Power, stored as 0.01 kVA."
        ::= { branch34 5 }

	branch34THDi OBJECT-TYPE
        SYNTAX Integer32
        MAX-ACCESS read-only
        STATUS current
        DESCRIPTION
            "branch34 THDi, stored as 0.01 %."
        ::= { branch34 6 }

	branch34RatedCurrent OBJECT-TYPE
        SYNTAX Integer32
        MAX-ACCESS read-only
        STATUS current
        DESCRIPTION
            "branch34 Rated Current, stored as 0.01 A."
        ::= { branch34 7 }

	branch34LoadRatio OBJECT-TYPE
        SYNTAX Integer32
        MAX-ACCESS read-only
        STATUS current
        DESCRIPTION "
        	branch34 Load Ratio. stored as 0.01 %"
        ::= { branch34 8 }

	branch34PowerFactor OBJECT-TYPE
        SYNTAX Integer32
        MAX-ACCESS read-only
        STATUS current
        DESCRIPTION
            "branch34 Power Factor, stored as 0.01."
        ::= { branch34 9 }


-- ------------------------------------------------------------------------ 
-- 1.2.38 the branch35 group
-- ------------------------------------------------------------------------ 

branch35 OBJECT IDENTIFIER ::= { system 54 }

    branch35Current OBJECT-TYPE
    	SYNTAX Integer32
    	MAX-ACCESS read-only
        STATUS current
        DESCRIPTION
            "branch35 Current, stored as 0.01 A."
        ::= { branch35 1 }

	branch35ElectricEnergy OBJECT-TYPE
        SYNTAX Integer32
        MAX-ACCESS read-only
        STATUS current
        DESCRIPTION
            "branch35 Electric Energy, stored as 0.01 kWh."
        ::= { branch35 2 }

	branch35SwitchStatus OBJECT-TYPE
        SYNTAX Integer32
        MAX-ACCESS read-only
        STATUS current
        DESCRIPTION
            "branch35 Switch Status, stored as 0.01."
        ::= { branch35 3 }
        
	branch35ActivePower OBJECT-TYPE
        SYNTAX Integer32
        MAX-ACCESS read-only
        STATUS current
        DESCRIPTION
            "branch35 Active Power, stored as 0.01 kW."
        ::= { branch35 4 }

	branch35ApparentPower OBJECT-TYPE
        SYNTAX Integer32
        MAX-ACCESS read-only
        STATUS current
        DESCRIPTION
            "branch35 Apparent Power, stored as 0.01 kVA."
        ::= { branch35 5 }

	branch35THDi OBJECT-TYPE
        SYNTAX Integer32
        MAX-ACCESS read-only
        STATUS current
        DESCRIPTION
            "branch35 THDi, stored as 0.01 %."
        ::= { branch35 6 }

	branch35RatedCurrent OBJECT-TYPE
        SYNTAX Integer32
        MAX-ACCESS read-only
        STATUS current
        DESCRIPTION
            "branch35 Rated Current, stored as 0.01 A."
        ::= { branch35 7 }

	branch35LoadRatio OBJECT-TYPE
        SYNTAX Integer32
        MAX-ACCESS read-only
        STATUS current
        DESCRIPTION "
        	branch35 Load Ratio. stored as 0.01 %"
        ::= { branch35 8 }

	branch35PowerFactor OBJECT-TYPE
        SYNTAX Integer32
        MAX-ACCESS read-only
        STATUS current
        DESCRIPTION
            "branch35 Power Factor, stored as 0.01."
        ::= { branch35 9 }


-- ------------------------------------------------------------------------ 
-- 1.2.39 the branch36 group
-- ------------------------------------------------------------------------ 

branch36 OBJECT IDENTIFIER ::= { system 55 }

    branch36Current OBJECT-TYPE
    	SYNTAX Integer32
    	MAX-ACCESS read-only
        STATUS current
        DESCRIPTION
            "branch36 Current, stored as 0.01 A."
        ::= { branch36 1 }

	branch36ElectricEnergy OBJECT-TYPE
        SYNTAX Integer32
        MAX-ACCESS read-only
        STATUS current
        DESCRIPTION
            "branch36 Electric Energy, stored as 0.01 kWh."
        ::= { branch36 2 }

	branch36SwitchStatus OBJECT-TYPE
        SYNTAX Integer32
        MAX-ACCESS read-only
        STATUS current
        DESCRIPTION
            "branch36 Switch Status, stored as 0.01."
        ::= { branch36 3 }
        
	branch36ActivePower OBJECT-TYPE
        SYNTAX Integer32
        MAX-ACCESS read-only
        STATUS current
        DESCRIPTION
            "branch36 Active Power, stored as 0.01 kW."
        ::= { branch36 4 }

	branch36ApparentPower OBJECT-TYPE
        SYNTAX Integer32
        MAX-ACCESS read-only
        STATUS current
        DESCRIPTION
            "branch36 Apparent Power, stored as 0.01 kVA."
        ::= { branch36 5 }

	branch36THDi OBJECT-TYPE
        SYNTAX Integer32
        MAX-ACCESS read-only
        STATUS current
        DESCRIPTION
            "branch36 THDi, stored as 0.01 %."
        ::= { branch36 6 }

	branch36RatedCurrent OBJECT-TYPE
        SYNTAX Integer32
        MAX-ACCESS read-only
        STATUS current
        DESCRIPTION
            "branch36 Rated Current, stored as 0.01 A."
        ::= { branch36 7 }

	branch36LoadRatio OBJECT-TYPE
        SYNTAX Integer32
        MAX-ACCESS read-only
        STATUS current
        DESCRIPTION "
        	branch36 Load Ratio. stored as 0.01 %"
        ::= { branch36 8 }

	branch36PowerFactor OBJECT-TYPE
        SYNTAX Integer32
        MAX-ACCESS read-only
        STATUS current
        DESCRIPTION
            "branch36 Power Factor, stored as 0.01."
        ::= { branch36 9 }


-- ------------------------------------------------------------------------ 
-- 1.2.40 the branch37 group
-- ------------------------------------------------------------------------ 

branch37 OBJECT IDENTIFIER ::= { system 56 }

    branch37Current OBJECT-TYPE
    	SYNTAX Integer32
    	MAX-ACCESS read-only
        STATUS current
        DESCRIPTION
            "branch37 Current, stored as 0.01 A."
        ::= { branch37 1 }

	branch37ElectricEnergy OBJECT-TYPE
        SYNTAX Integer32
        MAX-ACCESS read-only
        STATUS current
        DESCRIPTION
            "branch37 Electric Energy, stored as 0.01 kWh."
        ::= { branch37 2 }

	branch37SwitchStatus OBJECT-TYPE
        SYNTAX Integer32
        MAX-ACCESS read-only
        STATUS current
        DESCRIPTION
            "branch37 Switch Status, stored as 0.01."
        ::= { branch37 3 }
        
	branch37ActivePower OBJECT-TYPE
        SYNTAX Integer32
        MAX-ACCESS read-only
        STATUS current
        DESCRIPTION
            "branch37 Active Power, stored as 0.01 kW."
        ::= { branch37 4 }

	branch37ApparentPower OBJECT-TYPE
        SYNTAX Integer32
        MAX-ACCESS read-only
        STATUS current
        DESCRIPTION
            "branch37 Apparent Power, stored as 0.01 kVA."
        ::= { branch37 5 }

	branch37THDi OBJECT-TYPE
        SYNTAX Integer32
        MAX-ACCESS read-only
        STATUS current
        DESCRIPTION
            "branch37 THDi, stored as 0.01 %."
        ::= { branch37 6 }

	branch37RatedCurrent OBJECT-TYPE
        SYNTAX Integer32
        MAX-ACCESS read-only
        STATUS current
        DESCRIPTION
            "branch37 Rated Current, stored as 0.01 A."
        ::= { branch37 7 }

	branch37LoadRatio OBJECT-TYPE
        SYNTAX Integer32
        MAX-ACCESS read-only
        STATUS current
        DESCRIPTION "
        	branch37 Load Ratio. stored as 0.01 %"
        ::= { branch37 8 }

	branch37PowerFactor OBJECT-TYPE
        SYNTAX Integer32
        MAX-ACCESS read-only
        STATUS current
        DESCRIPTION
            "branch37 Power Factor, stored as 0.01."
        ::= { branch37 9 }


-- ------------------------------------------------------------------------ 
-- 1.2.41 the branch38 group
-- ------------------------------------------------------------------------ 

branch38 OBJECT IDENTIFIER ::= { system 57 }

    branch38Current OBJECT-TYPE
    	SYNTAX Integer32
    	MAX-ACCESS read-only
        STATUS current
        DESCRIPTION
            "branch38 Current, stored as 0.01 A."
        ::= { branch38 1 }

	branch38ElectricEnergy OBJECT-TYPE
        SYNTAX Integer32
        MAX-ACCESS read-only
        STATUS current
        DESCRIPTION
            "branch38 Electric Energy, stored as 0.01 kWh."
        ::= { branch38 2 }

	branch38SwitchStatus OBJECT-TYPE
        SYNTAX Integer32
        MAX-ACCESS read-only
        STATUS current
        DESCRIPTION
            "branch38 Switch Status, stored as 0.01."
        ::= { branch38 3 }
        
	branch38ActivePower OBJECT-TYPE
        SYNTAX Integer32
        MAX-ACCESS read-only
        STATUS current
        DESCRIPTION
            "branch38 Active Power, stored as 0.01 kW."
        ::= { branch38 4 }

	branch38ApparentPower OBJECT-TYPE
        SYNTAX Integer32
        MAX-ACCESS read-only
        STATUS current
        DESCRIPTION
            "branch38 Apparent Power, stored as 0.01 kVA."
        ::= { branch38 5 }

	branch38THDi OBJECT-TYPE
        SYNTAX Integer32
        MAX-ACCESS read-only
        STATUS current
        DESCRIPTION
            "branch38 THDi, stored as 0.01 %."
        ::= { branch38 6 }

	branch38RatedCurrent OBJECT-TYPE
        SYNTAX Integer32
        MAX-ACCESS read-only
        STATUS current
        DESCRIPTION
            "branch38 Rated Current, stored as 0.01 A."
        ::= { branch38 7 }

	branch38LoadRatio OBJECT-TYPE
        SYNTAX Integer32
        MAX-ACCESS read-only
        STATUS current
        DESCRIPTION "
        	branch38 Load Ratio. stored as 0.01 %"
        ::= { branch38 8 }

	branch38PowerFactor OBJECT-TYPE
        SYNTAX Integer32
        MAX-ACCESS read-only
        STATUS current
        DESCRIPTION
            "branch38 Power Factor, stored as 0.01."
        ::= { branch38 9 }


-- ------------------------------------------------------------------------ 
-- 1.2.42 the branch39 group
-- ------------------------------------------------------------------------ 

branch39 OBJECT IDENTIFIER ::= { system 58 }

    branch39Current OBJECT-TYPE
    	SYNTAX Integer32
    	MAX-ACCESS read-only
        STATUS current
        DESCRIPTION
            "branch39 Current, stored as 0.01 A."
        ::= { branch39 1 }

	branch39ElectricEnergy OBJECT-TYPE
        SYNTAX Integer32
        MAX-ACCESS read-only
        STATUS current
        DESCRIPTION
            "branch39 Electric Energy, stored as 0.01 kWh."
        ::= { branch39 2 }

	branch39SwitchStatus OBJECT-TYPE
        SYNTAX Integer32
        MAX-ACCESS read-only
        STATUS current
        DESCRIPTION
            "branch39 Switch Status, stored as 0.01."
        ::= { branch39 3 }
        
	branch39ActivePower OBJECT-TYPE
        SYNTAX Integer32
        MAX-ACCESS read-only
        STATUS current
        DESCRIPTION
            "branch39 Active Power, stored as 0.01 kW."
        ::= { branch39 4 }

	branch39ApparentPower OBJECT-TYPE
        SYNTAX Integer32
        MAX-ACCESS read-only
        STATUS current
        DESCRIPTION
            "branch39 Apparent Power, stored as 0.01 kVA."
        ::= { branch39 5 }

	branch39THDi OBJECT-TYPE
        SYNTAX Integer32
        MAX-ACCESS read-only
        STATUS current
        DESCRIPTION
            "branch39 THDi, stored as 0.01 %."
        ::= { branch39 6 }

	branch39RatedCurrent OBJECT-TYPE
        SYNTAX Integer32
        MAX-ACCESS read-only
        STATUS current
        DESCRIPTION
            "branch39 Rated Current, stored as 0.01 A."
        ::= { branch39 7 }

	branch39LoadRatio OBJECT-TYPE
        SYNTAX Integer32
        MAX-ACCESS read-only
        STATUS current
        DESCRIPTION "
        	branch39 Load Ratio. stored as 0.01 %"
        ::= { branch39 8 }

	branch39PowerFactor OBJECT-TYPE
        SYNTAX Integer32
        MAX-ACCESS read-only
        STATUS current
        DESCRIPTION
            "branch39 Power Factor, stored as 0.01."
        ::= { branch39 9 }


-- ------------------------------------------------------------------------ 
-- 1.2.43 the branch40 group
-- ------------------------------------------------------------------------ 

branch40 OBJECT IDENTIFIER ::= { system 59 }

    branch40Current OBJECT-TYPE
    	SYNTAX Integer32
    	MAX-ACCESS read-only
        STATUS current
        DESCRIPTION
            "branch40 Current, stored as 0.01 A."
        ::= { branch40 1 }

	branch40ElectricEnergy OBJECT-TYPE
        SYNTAX Integer32
        MAX-ACCESS read-only
        STATUS current
        DESCRIPTION
            "branch40 Electric Energy, stored as 0.01 kWh."
        ::= { branch40 2 }

	branch40SwitchStatus OBJECT-TYPE
        SYNTAX Integer32
        MAX-ACCESS read-only
        STATUS current
        DESCRIPTION
            "branch40 Switch Status, stored as 0.01."
        ::= { branch40 3 }
        
	branch40ActivePower OBJECT-TYPE
        SYNTAX Integer32
        MAX-ACCESS read-only
        STATUS current
        DESCRIPTION
            "branch40 Active Power, stored as 0.01 kW."
        ::= { branch40 4 }

	branch40ApparentPower OBJECT-TYPE
        SYNTAX Integer32
        MAX-ACCESS read-only
        STATUS current
        DESCRIPTION
            "branch40 Apparent Power, stored as 0.01 kVA."
        ::= { branch40 5 }

	branch40THDi OBJECT-TYPE
        SYNTAX Integer32
        MAX-ACCESS read-only
        STATUS current
        DESCRIPTION
            "branch40 THDi, stored as 0.01 %."
        ::= { branch40 6 }

	branch40RatedCurrent OBJECT-TYPE
        SYNTAX Integer32
        MAX-ACCESS read-only
        STATUS current
        DESCRIPTION
            "branch40 Rated Current, stored as 0.01 A."
        ::= { branch40 7 }

	branch40LoadRatio OBJECT-TYPE
        SYNTAX Integer32
        MAX-ACCESS read-only
        STATUS current
        DESCRIPTION "
        	branch40 Load Ratio. stored as 0.01 %"
        ::= { branch40 8 }

	branch40PowerFactor OBJECT-TYPE
        SYNTAX Integer32
        MAX-ACCESS read-only
        STATUS current
        DESCRIPTION
            "branch40 Power Factor, stored as 0.01."
        ::= { branch40 9 }


-- ------------------------------------------------------------------------ 
-- 1.2.44 the branch41 group
-- ------------------------------------------------------------------------ 

branch41 OBJECT IDENTIFIER ::= { system 60 }

    branch41Current OBJECT-TYPE
    	SYNTAX Integer32
    	MAX-ACCESS read-only
        STATUS current
        DESCRIPTION
            "branch41 Current, stored as 0.01 A."
        ::= { branch41 1 }

	branch41ElectricEnergy OBJECT-TYPE
        SYNTAX Integer32
        MAX-ACCESS read-only
        STATUS current
        DESCRIPTION
            "branch41 Electric Energy, stored as 0.01 kWh."
        ::= { branch41 2 }

	branch41SwitchStatus OBJECT-TYPE
        SYNTAX Integer32
        MAX-ACCESS read-only
        STATUS current
        DESCRIPTION
            "branch41 Switch Status, stored as 0.01."
        ::= { branch41 3 }
        
	branch41ActivePower OBJECT-TYPE
        SYNTAX Integer32
        MAX-ACCESS read-only
        STATUS current
        DESCRIPTION
            "branch41 Active Power, stored as 0.01 kW."
        ::= { branch41 4 }

	branch41ApparentPower OBJECT-TYPE
        SYNTAX Integer32
        MAX-ACCESS read-only
        STATUS current
        DESCRIPTION
            "branch41 Apparent Power, stored as 0.01 kVA."
        ::= { branch41 5 }

	branch41THDi OBJECT-TYPE
        SYNTAX Integer32
        MAX-ACCESS read-only
        STATUS current
        DESCRIPTION
            "branch41 THDi, stored as 0.01 %."
        ::= { branch41 6 }

	branch41RatedCurrent OBJECT-TYPE
        SYNTAX Integer32
        MAX-ACCESS read-only
        STATUS current
        DESCRIPTION
            "branch41 Rated Current, stored as 0.01 A."
        ::= { branch41 7 }

	branch41LoadRatio OBJECT-TYPE
        SYNTAX Integer32
        MAX-ACCESS read-only
        STATUS current
        DESCRIPTION "
        	branch41 Load Ratio. stored as 0.01 %"
        ::= { branch41 8 }

	branch41PowerFactor OBJECT-TYPE
        SYNTAX Integer32
        MAX-ACCESS read-only
        STATUS current
        DESCRIPTION
            "branch41 Power Factor, stored as 0.01."
        ::= { branch41 9 }


-- ------------------------------------------------------------------------ 
-- 1.2.45 the branch42 group
-- ------------------------------------------------------------------------ 

branch42 OBJECT IDENTIFIER ::= { system 61 }

    branch42Current OBJECT-TYPE
    	SYNTAX Integer32
    	MAX-ACCESS read-only
        STATUS current
        DESCRIPTION
            "branch42 Current, stored as 0.01 A."
        ::= { branch42 1 }

	branch42ElectricEnergy OBJECT-TYPE
        SYNTAX Integer32
        MAX-ACCESS read-only
        STATUS current
        DESCRIPTION
            "branch42 Electric Energy, stored as 0.01 kWh."
        ::= { branch42 2 }

	branch42SwitchStatus OBJECT-TYPE
        SYNTAX Integer32
        MAX-ACCESS read-only
        STATUS current
        DESCRIPTION
            "branch42 Switch Status, stored as 0.01."
        ::= { branch42 3 }
        
	branch42ActivePower OBJECT-TYPE
        SYNTAX Integer32
        MAX-ACCESS read-only
        STATUS current
        DESCRIPTION
            "branch42 Active Power, stored as 0.01 kW."
        ::= { branch42 4 }

	branch42ApparentPower OBJECT-TYPE
        SYNTAX Integer32
        MAX-ACCESS read-only
        STATUS current
        DESCRIPTION
            "branch42 Apparent Power, stored as 0.01 kVA."
        ::= { branch42 5 }

	branch42THDi OBJECT-TYPE
        SYNTAX Integer32
        MAX-ACCESS read-only
        STATUS current
        DESCRIPTION
            "branch42 THDi, stored as 0.01 %."
        ::= { branch42 6 }

	branch42RatedCurrent OBJECT-TYPE
        SYNTAX Integer32
        MAX-ACCESS read-only
        STATUS current
        DESCRIPTION
            "branch42 Rated Current, stored as 0.01 A."
        ::= { branch42 7 }

	branch42LoadRatio OBJECT-TYPE
        SYNTAX Integer32
        MAX-ACCESS read-only
        STATUS current
        DESCRIPTION "
        	branch42 Load Ratio. stored as 0.01 %"
        ::= { branch42 8 }

	branch42PowerFactor OBJECT-TYPE
        SYNTAX Integer32
        MAX-ACCESS read-only
        STATUS current
        DESCRIPTION
            "branch42 Power Factor, stored as 0.01."
        ::= { branch42 9 }


-- ------------------------------------------------------------------------ 
-- 1.2.46 the branch43 group
-- ------------------------------------------------------------------------ 

branch43 OBJECT IDENTIFIER ::= { system 62 }

    branch43Current OBJECT-TYPE
    	SYNTAX Integer32
    	MAX-ACCESS read-only
        STATUS current
        DESCRIPTION
            "branch43 Current, stored as 0.01 A."
        ::= { branch43 1 }

	branch43ElectricEnergy OBJECT-TYPE
        SYNTAX Integer32
        MAX-ACCESS read-only
        STATUS current
        DESCRIPTION
            "branch43 Electric Energy, stored as 0.01 kWh."
        ::= { branch43 2 }

	branch43SwitchStatus OBJECT-TYPE
        SYNTAX Integer32
        MAX-ACCESS read-only
        STATUS current
        DESCRIPTION
            "branch43 Switch Status, stored as 0.01."
        ::= { branch43 3 }
        
	branch43ActivePower OBJECT-TYPE
        SYNTAX Integer32
        MAX-ACCESS read-only
        STATUS current
        DESCRIPTION
            "branch43 Active Power, stored as 0.01 kW."
        ::= { branch43 4 }

	branch43ApparentPower OBJECT-TYPE
        SYNTAX Integer32
        MAX-ACCESS read-only
        STATUS current
        DESCRIPTION
            "branch43 Apparent Power, stored as 0.01 kVA."
        ::= { branch43 5 }

	branch43THDi OBJECT-TYPE
        SYNTAX Integer32
        MAX-ACCESS read-only
        STATUS current
        DESCRIPTION
            "branch43 THDi, stored as 0.01 %."
        ::= { branch43 6 }

	branch43RatedCurrent OBJECT-TYPE
        SYNTAX Integer32
        MAX-ACCESS read-only
        STATUS current
        DESCRIPTION
            "branch43 Rated Current, stored as 0.01 A."
        ::= { branch43 7 }

	branch43LoadRatio OBJECT-TYPE
        SYNTAX Integer32
        MAX-ACCESS read-only
        STATUS current
        DESCRIPTION "
        	branch43 Load Ratio. stored as 0.01 %"
        ::= { branch43 8 }

	branch43PowerFactor OBJECT-TYPE
        SYNTAX Integer32
        MAX-ACCESS read-only
        STATUS current
        DESCRIPTION
            "branch43 Power Factor, stored as 0.01."
        ::= { branch43 9 }


-- ------------------------------------------------------------------------ 
-- 1.2.47 the branch44 group
-- ------------------------------------------------------------------------ 

branch44 OBJECT IDENTIFIER ::= { system 63 }

    branch44Current OBJECT-TYPE
    	SYNTAX Integer32
    	MAX-ACCESS read-only
        STATUS current
        DESCRIPTION
            "branch44 Current, stored as 0.01 A."
        ::= { branch44 1 }

	branch44ElectricEnergy OBJECT-TYPE
        SYNTAX Integer32
        MAX-ACCESS read-only
        STATUS current
        DESCRIPTION
            "branch44 Electric Energy, stored as 0.01 kWh."
        ::= { branch44 2 }

	branch44SwitchStatus OBJECT-TYPE
        SYNTAX Integer32
        MAX-ACCESS read-only
        STATUS current
        DESCRIPTION
            "branch44 Switch Status, stored as 0.01."
        ::= { branch44 3 }
        
	branch44ActivePower OBJECT-TYPE
        SYNTAX Integer32
        MAX-ACCESS read-only
        STATUS current
        DESCRIPTION
            "branch44 Active Power, stored as 0.01 kW."
        ::= { branch44 4 }

	branch44ApparentPower OBJECT-TYPE
        SYNTAX Integer32
        MAX-ACCESS read-only
        STATUS current
        DESCRIPTION
            "branch44 Apparent Power, stored as 0.01 kVA."
        ::= { branch44 5 }

	branch44THDi OBJECT-TYPE
        SYNTAX Integer32
        MAX-ACCESS read-only
        STATUS current
        DESCRIPTION
            "branch44 THDi, stored as 0.01 %."
        ::= { branch44 6 }

	branch44RatedCurrent OBJECT-TYPE
        SYNTAX Integer32
        MAX-ACCESS read-only
        STATUS current
        DESCRIPTION
            "branch44 Rated Current, stored as 0.01 A."
        ::= { branch44 7 }

	branch44LoadRatio OBJECT-TYPE
        SYNTAX Integer32
        MAX-ACCESS read-only
        STATUS current
        DESCRIPTION "
        	branch44 Load Ratio. stored as 0.01 %"
        ::= { branch44 8 }

	branch44PowerFactor OBJECT-TYPE
        SYNTAX Integer32
        MAX-ACCESS read-only
        STATUS current
        DESCRIPTION
            "branch44 Power Factor, stored as 0.01."
        ::= { branch44 9 }


-- ------------------------------------------------------------------------ 
-- 1.2.48 the branch45 group
-- ------------------------------------------------------------------------ 

branch45 OBJECT IDENTIFIER ::= { system 64 }

    branch45Current OBJECT-TYPE
    	SYNTAX Integer32
    	MAX-ACCESS read-only
        STATUS current
        DESCRIPTION
            "branch45 Current, stored as 0.01 A."
        ::= { branch45 1 }

	branch45ElectricEnergy OBJECT-TYPE
        SYNTAX Integer32
        MAX-ACCESS read-only
        STATUS current
        DESCRIPTION
            "branch45 Electric Energy, stored as 0.01 kWh."
        ::= { branch45 2 }

	branch45SwitchStatus OBJECT-TYPE
        SYNTAX Integer32
        MAX-ACCESS read-only
        STATUS current
        DESCRIPTION
            "branch45 Switch Status, stored as 0.01."
        ::= { branch45 3 }
        
	branch45ActivePower OBJECT-TYPE
        SYNTAX Integer32
        MAX-ACCESS read-only
        STATUS current
        DESCRIPTION
            "branch45 Active Power, stored as 0.01 kW."
        ::= { branch45 4 }

	branch45ApparentPower OBJECT-TYPE
        SYNTAX Integer32
        MAX-ACCESS read-only
        STATUS current
        DESCRIPTION
            "branch45 Apparent Power, stored as 0.01 kVA."
        ::= { branch45 5 }

	branch45THDi OBJECT-TYPE
        SYNTAX Integer32
        MAX-ACCESS read-only
        STATUS current
        DESCRIPTION
            "branch45 THDi, stored as 0.01 %."
        ::= { branch45 6 }

	branch45RatedCurrent OBJECT-TYPE
        SYNTAX Integer32
        MAX-ACCESS read-only
        STATUS current
        DESCRIPTION
            "branch45 Rated Current, stored as 0.01 A."
        ::= { branch45 7 }

	branch45LoadRatio OBJECT-TYPE
        SYNTAX Integer32
        MAX-ACCESS read-only
        STATUS current
        DESCRIPTION "
        	branch45 Load Ratio. stored as 0.01 %"
        ::= { branch45 8 }

	branch45PowerFactor OBJECT-TYPE
        SYNTAX Integer32
        MAX-ACCESS read-only
        STATUS current
        DESCRIPTION
            "branch45 Power Factor, stored as 0.01."
        ::= { branch45 9 }


-- ------------------------------------------------------------------------ 
-- 1.2.49 the branch46 group
-- ------------------------------------------------------------------------ 

branch46 OBJECT IDENTIFIER ::= { system 65 }

    branch46Current OBJECT-TYPE
    	SYNTAX Integer32
    	MAX-ACCESS read-only
        STATUS current
        DESCRIPTION
            "branch46 Current, stored as 0.01 A."
        ::= { branch46 1 }

	branch46ElectricEnergy OBJECT-TYPE
        SYNTAX Integer32
        MAX-ACCESS read-only
        STATUS current
        DESCRIPTION
            "branch46 Electric Energy, stored as 0.01 kWh."
        ::= { branch46 2 }

	branch46SwitchStatus OBJECT-TYPE
        SYNTAX Integer32
        MAX-ACCESS read-only
        STATUS current
        DESCRIPTION
            "branch46 Switch Status, stored as 0.01."
        ::= { branch46 3 }
        
	branch46ActivePower OBJECT-TYPE
        SYNTAX Integer32
        MAX-ACCESS read-only
        STATUS current
        DESCRIPTION
            "branch46 Active Power, stored as 0.01 kW."
        ::= { branch46 4 }

	branch46ApparentPower OBJECT-TYPE
        SYNTAX Integer32
        MAX-ACCESS read-only
        STATUS current
        DESCRIPTION
            "branch46 Apparent Power, stored as 0.01 kVA."
        ::= { branch46 5 }

	branch46THDi OBJECT-TYPE
        SYNTAX Integer32
        MAX-ACCESS read-only
        STATUS current
        DESCRIPTION
            "branch46 THDi, stored as 0.01 %."
        ::= { branch46 6 }

	branch46RatedCurrent OBJECT-TYPE
        SYNTAX Integer32
        MAX-ACCESS read-only
        STATUS current
        DESCRIPTION
            "branch46 Rated Current, stored as 0.01 A."
        ::= { branch46 7 }

	branch46LoadRatio OBJECT-TYPE
        SYNTAX Integer32
        MAX-ACCESS read-only
        STATUS current
        DESCRIPTION "
        	branch46 Load Ratio. stored as 0.01 %"
        ::= { branch46 8 }

	branch46PowerFactor OBJECT-TYPE
        SYNTAX Integer32
        MAX-ACCESS read-only
        STATUS current
        DESCRIPTION
            "branch46 Power Factor, stored as 0.01."
        ::= { branch46 9 }


-- ------------------------------------------------------------------------ 
-- 1.2.50 the branch47 group
-- ------------------------------------------------------------------------ 

branch47 OBJECT IDENTIFIER ::= { system 66 }

    branch47Current OBJECT-TYPE
    	SYNTAX Integer32
    	MAX-ACCESS read-only
        STATUS current
        DESCRIPTION
            "branch47 Current, stored as 0.01 A."
        ::= { branch47 1 }

	branch47ElectricEnergy OBJECT-TYPE
        SYNTAX Integer32
        MAX-ACCESS read-only
        STATUS current
        DESCRIPTION
            "branch47 Electric Energy, stored as 0.01 kWh."
        ::= { branch47 2 }

	branch47SwitchStatus OBJECT-TYPE
        SYNTAX Integer32
        MAX-ACCESS read-only
        STATUS current
        DESCRIPTION
            "branch47 Switch Status, stored as 0.01."
        ::= { branch47 3 }
        
	branch47ActivePower OBJECT-TYPE
        SYNTAX Integer32
        MAX-ACCESS read-only
        STATUS current
        DESCRIPTION
            "branch47 Active Power, stored as 0.01 kW."
        ::= { branch47 4 }

	branch47ApparentPower OBJECT-TYPE
        SYNTAX Integer32
        MAX-ACCESS read-only
        STATUS current
        DESCRIPTION
            "branch47 Apparent Power, stored as 0.01 kVA."
        ::= { branch47 5 }

	branch47THDi OBJECT-TYPE
        SYNTAX Integer32
        MAX-ACCESS read-only
        STATUS current
        DESCRIPTION
            "branch47 THDi, stored as 0.01 %."
        ::= { branch47 6 }

	branch47RatedCurrent OBJECT-TYPE
        SYNTAX Integer32
        MAX-ACCESS read-only
        STATUS current
        DESCRIPTION
            "branch47 Rated Current, stored as 0.01 A."
        ::= { branch47 7 }

	branch47LoadRatio OBJECT-TYPE
        SYNTAX Integer32
        MAX-ACCESS read-only
        STATUS current
        DESCRIPTION "
        	branch47 Load Ratio. stored as 0.01 %"
        ::= { branch47 8 }

	branch47PowerFactor OBJECT-TYPE
        SYNTAX Integer32
        MAX-ACCESS read-only
        STATUS current
        DESCRIPTION
            "branch47 Power Factor, stored as 0.01."
        ::= { branch47 9 }


-- ------------------------------------------------------------------------ 
-- 1.2.51 the branch48 group
-- ------------------------------------------------------------------------ 

branch48 OBJECT IDENTIFIER ::= { system 67 }

    branch48Current OBJECT-TYPE
    	SYNTAX Integer32
    	MAX-ACCESS read-only
        STATUS current
        DESCRIPTION
            "branch48 Current, stored as 0.01 A."
        ::= { branch48 1 }

	branch48ElectricEnergy OBJECT-TYPE
        SYNTAX Integer32
        MAX-ACCESS read-only
        STATUS current
        DESCRIPTION
            "branch48 Electric Energy, stored as 0.01 kWh."
        ::= { branch48 2 }

	branch48SwitchStatus OBJECT-TYPE
        SYNTAX Integer32
        MAX-ACCESS read-only
        STATUS current
        DESCRIPTION
            "branch48 Switch Status, stored as 0.01."
        ::= { branch48 3 }
        
	branch48ActivePower OBJECT-TYPE
        SYNTAX Integer32
        MAX-ACCESS read-only
        STATUS current
        DESCRIPTION
            "branch48 Active Power, stored as 0.01 kW."
        ::= { branch48 4 }

	branch48ApparentPower OBJECT-TYPE
        SYNTAX Integer32
        MAX-ACCESS read-only
        STATUS current
        DESCRIPTION
            "branch48 Apparent Power, stored as 0.01 kVA."
        ::= { branch48 5 }

	branch48THDi OBJECT-TYPE
        SYNTAX Integer32
        MAX-ACCESS read-only
        STATUS current
        DESCRIPTION
            "branch48 THDi, stored as 0.01 %."
        ::= { branch48 6 }

	branch48RatedCurrent OBJECT-TYPE
        SYNTAX Integer32
        MAX-ACCESS read-only
        STATUS current
        DESCRIPTION
            "branch48 Rated Current, stored as 0.01 A."
        ::= { branch48 7 }

	branch48LoadRatio OBJECT-TYPE
        SYNTAX Integer32
        MAX-ACCESS read-only
        STATUS current
        DESCRIPTION "
        	branch48 Load Ratio. stored as 0.01 %"
        ::= { branch48 8 }

	branch48PowerFactor OBJECT-TYPE
        SYNTAX Integer32
        MAX-ACCESS read-only
        STATUS current
        DESCRIPTION
            "branch48 Power Factor, stored as 0.01."
        ::= { branch48 9 }


-- ------------------------------------------------------------------------ 
-- 1.2.52 the branch49 group
-- ------------------------------------------------------------------------ 

branch49 OBJECT IDENTIFIER ::= { system 68 }

    branch49Current OBJECT-TYPE
    	SYNTAX Integer32
    	MAX-ACCESS read-only
        STATUS current
        DESCRIPTION
            "branch49 Current, stored as 0.01 A."
        ::= { branch49 1 }

	branch49ElectricEnergy OBJECT-TYPE
        SYNTAX Integer32
        MAX-ACCESS read-only
        STATUS current
        DESCRIPTION
            "branch49 Electric Energy, stored as 0.01 kWh."
        ::= { branch49 2 }

	branch49SwitchStatus OBJECT-TYPE
        SYNTAX Integer32
        MAX-ACCESS read-only
        STATUS current
        DESCRIPTION
            "branch49 Switch Status, stored as 0.01."
        ::= { branch49 3 }
        
	branch49ActivePower OBJECT-TYPE
        SYNTAX Integer32
        MAX-ACCESS read-only
        STATUS current
        DESCRIPTION
            "branch49 Active Power, stored as 0.01 kW."
        ::= { branch49 4 }

	branch49ApparentPower OBJECT-TYPE
        SYNTAX Integer32
        MAX-ACCESS read-only
        STATUS current
        DESCRIPTION
            "branch49 Apparent Power, stored as 0.01 kVA."
        ::= { branch49 5 }

	branch49THDi OBJECT-TYPE
        SYNTAX Integer32
        MAX-ACCESS read-only
        STATUS current
        DESCRIPTION
            "branch49 THDi, stored as 0.01 %."
        ::= { branch49 6 }

	branch49RatedCurrent OBJECT-TYPE
        SYNTAX Integer32
        MAX-ACCESS read-only
        STATUS current
        DESCRIPTION
            "branch49 Rated Current, stored as 0.01 A."
        ::= { branch49 7 }

	branch49LoadRatio OBJECT-TYPE
        SYNTAX Integer32
        MAX-ACCESS read-only
        STATUS current
        DESCRIPTION "
        	branch49 Load Ratio. stored as 0.01 %"
        ::= { branch49 8 }

	branch49PowerFactor OBJECT-TYPE
        SYNTAX Integer32
        MAX-ACCESS read-only
        STATUS current
        DESCRIPTION
            "branch49 Power Factor, stored as 0.01."
        ::= { branch49 9 }


-- ------------------------------------------------------------------------ 
-- 1.2.53 the branch50 group
-- ------------------------------------------------------------------------ 

branch50 OBJECT IDENTIFIER ::= { system 69 }

    branch50Current OBJECT-TYPE
    	SYNTAX Integer32
    	MAX-ACCESS read-only
        STATUS current
        DESCRIPTION
            "branch50 Current, stored as 0.01 A."
        ::= { branch50 1 }

	branch50ElectricEnergy OBJECT-TYPE
        SYNTAX Integer32
        MAX-ACCESS read-only
        STATUS current
        DESCRIPTION
            "branch50 Electric Energy, stored as 0.01 kWh."
        ::= { branch50 2 }

	branch50SwitchStatus OBJECT-TYPE
        SYNTAX Integer32
        MAX-ACCESS read-only
        STATUS current
        DESCRIPTION
            "branch50 Switch Status, stored as 0.01."
        ::= { branch50 3 }
        
	branch50ActivePower OBJECT-TYPE
        SYNTAX Integer32
        MAX-ACCESS read-only
        STATUS current
        DESCRIPTION
            "branch50 Active Power, stored as 0.01 kW."
        ::= { branch50 4 }

	branch50ApparentPower OBJECT-TYPE
        SYNTAX Integer32
        MAX-ACCESS read-only
        STATUS current
        DESCRIPTION
            "branch50 Apparent Power, stored as 0.01 kVA."
        ::= { branch50 5 }

	branch50THDi OBJECT-TYPE
        SYNTAX Integer32
        MAX-ACCESS read-only
        STATUS current
        DESCRIPTION
            "branch50 THDi, stored as 0.01 %."
        ::= { branch50 6 }

	branch50RatedCurrent OBJECT-TYPE
        SYNTAX Integer32
        MAX-ACCESS read-only
        STATUS current
        DESCRIPTION
            "branch50 Rated Current, stored as 0.01 A."
        ::= { branch50 7 }

	branch50LoadRatio OBJECT-TYPE
        SYNTAX Integer32
        MAX-ACCESS read-only
        STATUS current
        DESCRIPTION "
        	branch50 Load Ratio. stored as 0.01 %"
        ::= { branch50 8 }

	branch50PowerFactor OBJECT-TYPE
        SYNTAX Integer32
        MAX-ACCESS read-only
        STATUS current
        DESCRIPTION
            "branch50 Power Factor, stored as 0.01."
        ::= { branch50 9 }


-- ------------------------------------------------------------------------ 
-- 1.2.54 the branch51 group
-- ------------------------------------------------------------------------ 

branch51 OBJECT IDENTIFIER ::= { system 70 }

    branch51Current OBJECT-TYPE
    	SYNTAX Integer32
    	MAX-ACCESS read-only
        STATUS current
        DESCRIPTION
            "branch51 Current, stored as 0.01 A."
        ::= { branch51 1 }

	branch51ElectricEnergy OBJECT-TYPE
        SYNTAX Integer32
        MAX-ACCESS read-only
        STATUS current
        DESCRIPTION
            "branch51 Electric Energy, stored as 0.01 kWh."
        ::= { branch51 2 }

	branch51SwitchStatus OBJECT-TYPE
        SYNTAX Integer32
        MAX-ACCESS read-only
        STATUS current
        DESCRIPTION
            "branch51 Switch Status, stored as 0.01."
        ::= { branch51 3 }
        
	branch51ActivePower OBJECT-TYPE
        SYNTAX Integer32
        MAX-ACCESS read-only
        STATUS current
        DESCRIPTION
            "branch51 Active Power, stored as 0.01 kW."
        ::= { branch51 4 }

	branch51ApparentPower OBJECT-TYPE
        SYNTAX Integer32
        MAX-ACCESS read-only
        STATUS current
        DESCRIPTION
            "branch51 Apparent Power, stored as 0.01 kVA."
        ::= { branch51 5 }

	branch51THDi OBJECT-TYPE
        SYNTAX Integer32
        MAX-ACCESS read-only
        STATUS current
        DESCRIPTION
            "branch51 THDi, stored as 0.01 %."
        ::= { branch51 6 }

	branch51RatedCurrent OBJECT-TYPE
        SYNTAX Integer32
        MAX-ACCESS read-only
        STATUS current
        DESCRIPTION
            "branch51 Rated Current, stored as 0.01 A."
        ::= { branch51 7 }

	branch51LoadRatio OBJECT-TYPE
        SYNTAX Integer32
        MAX-ACCESS read-only
        STATUS current
        DESCRIPTION "
        	branch51 Load Ratio. stored as 0.01 %"
        ::= { branch51 8 }

	branch51PowerFactor OBJECT-TYPE
        SYNTAX Integer32
        MAX-ACCESS read-only
        STATUS current
        DESCRIPTION
            "branch51 Power Factor, stored as 0.01."
        ::= { branch51 9 }


-- ------------------------------------------------------------------------ 
-- 1.2.55 the branch52 group
-- ------------------------------------------------------------------------ 

branch52 OBJECT IDENTIFIER ::= { system 71 }

    branch52Current OBJECT-TYPE
    	SYNTAX Integer32
    	MAX-ACCESS read-only
        STATUS current
        DESCRIPTION
            "branch52 Current, stored as 0.01 A."
        ::= { branch52 1 }

	branch52ElectricEnergy OBJECT-TYPE
        SYNTAX Integer32
        MAX-ACCESS read-only
        STATUS current
        DESCRIPTION
            "branch52 Electric Energy, stored as 0.01 kWh."
        ::= { branch52 2 }

	branch52SwitchStatus OBJECT-TYPE
        SYNTAX Integer32
        MAX-ACCESS read-only
        STATUS current
        DESCRIPTION
            "branch52 Switch Status, stored as 0.01."
        ::= { branch52 3 }
        
	branch52ActivePower OBJECT-TYPE
        SYNTAX Integer32
        MAX-ACCESS read-only
        STATUS current
        DESCRIPTION
            "branch52 Active Power, stored as 0.01 kW."
        ::= { branch52 4 }

	branch52ApparentPower OBJECT-TYPE
        SYNTAX Integer32
        MAX-ACCESS read-only
        STATUS current
        DESCRIPTION
            "branch52 Apparent Power, stored as 0.01 kVA."
        ::= { branch52 5 }

	branch52THDi OBJECT-TYPE
        SYNTAX Integer32
        MAX-ACCESS read-only
        STATUS current
        DESCRIPTION
            "branch52 THDi, stored as 0.01 %."
        ::= { branch52 6 }

	branch52RatedCurrent OBJECT-TYPE
        SYNTAX Integer32
        MAX-ACCESS read-only
        STATUS current
        DESCRIPTION
            "branch52 Rated Current, stored as 0.01 A."
        ::= { branch52 7 }

	branch52LoadRatio OBJECT-TYPE
        SYNTAX Integer32
        MAX-ACCESS read-only
        STATUS current
        DESCRIPTION "
        	branch52 Load Ratio. stored as 0.01 %"
        ::= { branch52 8 }

	branch52PowerFactor OBJECT-TYPE
        SYNTAX Integer32
        MAX-ACCESS read-only
        STATUS current
        DESCRIPTION
            "branch52 Power Factor, stored as 0.01."
        ::= { branch52 9 }


-- ------------------------------------------------------------------------ 
-- 1.2.56 the branch53 group
-- ------------------------------------------------------------------------ 

branch53 OBJECT IDENTIFIER ::= { system 72 }

    branch53Current OBJECT-TYPE
    	SYNTAX Integer32
    	MAX-ACCESS read-only
        STATUS current
        DESCRIPTION
            "branch53 Current, stored as 0.01 A."
        ::= { branch53 1 }

	branch53ElectricEnergy OBJECT-TYPE
        SYNTAX Integer32
        MAX-ACCESS read-only
        STATUS current
        DESCRIPTION
            "branch53 Electric Energy, stored as 0.01 kWh."
        ::= { branch53 2 }

	branch53SwitchStatus OBJECT-TYPE
        SYNTAX Integer32
        MAX-ACCESS read-only
        STATUS current
        DESCRIPTION
            "branch53 Switch Status, stored as 0.01."
        ::= { branch53 3 }
        
	branch53ActivePower OBJECT-TYPE
        SYNTAX Integer32
        MAX-ACCESS read-only
        STATUS current
        DESCRIPTION
            "branch53 Active Power, stored as 0.01 kW."
        ::= { branch53 4 }

	branch53ApparentPower OBJECT-TYPE
        SYNTAX Integer32
        MAX-ACCESS read-only
        STATUS current
        DESCRIPTION
            "branch53 Apparent Power, stored as 0.01 kVA."
        ::= { branch53 5 }

	branch53THDi OBJECT-TYPE
        SYNTAX Integer32
        MAX-ACCESS read-only
        STATUS current
        DESCRIPTION
            "branch53 THDi, stored as 0.01 %."
        ::= { branch53 6 }

	branch53RatedCurrent OBJECT-TYPE
        SYNTAX Integer32
        MAX-ACCESS read-only
        STATUS current
        DESCRIPTION
            "branch53 Rated Current, stored as 0.01 A."
        ::= { branch53 7 }

	branch53LoadRatio OBJECT-TYPE
        SYNTAX Integer32
        MAX-ACCESS read-only
        STATUS current
        DESCRIPTION "
        	branch53 Load Ratio. stored as 0.01 %"
        ::= { branch53 8 }

	branch53PowerFactor OBJECT-TYPE
        SYNTAX Integer32
        MAX-ACCESS read-only
        STATUS current
        DESCRIPTION
            "branch53 Power Factor, stored as 0.01."
        ::= { branch53 9 }


-- ------------------------------------------------------------------------ 
-- 1.2.57 the branch54 group
-- ------------------------------------------------------------------------ 

branch54 OBJECT IDENTIFIER ::= { system 73 }

    branch54Current OBJECT-TYPE
    	SYNTAX Integer32
    	MAX-ACCESS read-only
        STATUS current
        DESCRIPTION
            "branch54 Current, stored as 0.01 A."
        ::= { branch54 1 }

	branch54ElectricEnergy OBJECT-TYPE
        SYNTAX Integer32
        MAX-ACCESS read-only
        STATUS current
        DESCRIPTION
            "branch54 Electric Energy, stored as 0.01 kWh."
        ::= { branch54 2 }

	branch54SwitchStatus OBJECT-TYPE
        SYNTAX Integer32
        MAX-ACCESS read-only
        STATUS current
        DESCRIPTION
            "branch54 Switch Status, stored as 0.01."
        ::= { branch54 3 }
        
	branch54ActivePower OBJECT-TYPE
        SYNTAX Integer32
        MAX-ACCESS read-only
        STATUS current
        DESCRIPTION
            "branch54 Active Power, stored as 0.01 kW."
        ::= { branch54 4 }

	branch54ApparentPower OBJECT-TYPE
        SYNTAX Integer32
        MAX-ACCESS read-only
        STATUS current
        DESCRIPTION
            "branch54 Apparent Power, stored as 0.01 kVA."
        ::= { branch54 5 }

	branch54THDi OBJECT-TYPE
        SYNTAX Integer32
        MAX-ACCESS read-only
        STATUS current
        DESCRIPTION
            "branch54 THDi, stored as 0.01 %."
        ::= { branch54 6 }

	branch54RatedCurrent OBJECT-TYPE
        SYNTAX Integer32
        MAX-ACCESS read-only
        STATUS current
        DESCRIPTION
            "branch54 Rated Current, stored as 0.01 A."
        ::= { branch54 7 }

	branch54LoadRatio OBJECT-TYPE
        SYNTAX Integer32
        MAX-ACCESS read-only
        STATUS current
        DESCRIPTION "
        	branch54 Load Ratio. stored as 0.01 %"
        ::= { branch54 8 }

	branch54PowerFactor OBJECT-TYPE
        SYNTAX Integer32
        MAX-ACCESS read-only
        STATUS current
        DESCRIPTION
            "branch54 Power Factor, stored as 0.01."
        ::= { branch54 9 }


------------------------------------------------------------
-- 1.3 Alarm trap table { apmMIB 3 }
------------------------------------------------------------

alarmTrapTable OBJECT-TYPE
	SYNTAX SEQUENCE OF AlarmTrapEntry
	MAX-ACCESS not-accessible
	STATUS current
	DESCRIPTION "
		Table holding information about the submitted alarm traps."
	::= { apmMIB 3 }

alarmTrapEntry OBJECT-TYPE
	SYNTAX AlarmTrapEntry
	MAX-ACCESS not-accessible
	STATUS current
	DESCRIPTION "
		An entry (conceptual row) in the alarmTrapTable."
	INDEX { alarmIndex }
	::= { alarmTrapTable 1 }

AlarmTrapEntry ::= SEQUENCE {
	alarmIndex Counter32,
	alarmTime DisplayString,
	alarmStatusChange StatusChange,
	alarmSeverity Status,
	alarmDescription DisplayString,
	alarmId Integer32 }

alarmIndex OBJECT-TYPE
	SYNTAX Counter32
	MAX-ACCESS read-only
	STATUS current
	DESCRIPTION "
		The unique sequence number of this alarm trap."
	::= { alarmTrapEntry 1 }

alarmTime OBJECT-TYPE
	SYNTAX DisplayString
	MAX-ACCESS read-only
	STATUS current
	DESCRIPTION "
		Date and time when event occured."
	::= { alarmTrapEntry 2 }

alarmStatusChange OBJECT-TYPE
	SYNTAX StatusChange
	MAX-ACCESS read-only
	STATUS current
	DESCRIPTION "
		Indicates 'activated' (0) or 'deactivated' (1) alarm events."
	::= { alarmTrapEntry 3 }

alarmSeverity OBJECT-TYPE
	SYNTAX Status
	MAX-ACCESS read-only
	STATUS current
	DESCRIPTION "
		The severity of the alarm. One of
		(0) informational
		(1) warning
		(2) critical"
	::= { alarmTrapEntry 4 }
	
alarmDescription OBJECT-TYPE
	SYNTAX DisplayString
	MAX-ACCESS read-only
	STATUS current
	DESCRIPTION "
		Free-text description of alarm."
	::= { alarmTrapEntry 5 }
	
alarmId OBJECT-TYPE
	SYNTAX Integer32
	MAX-ACCESS read-only
	STATUS current
	DESCRIPTION "
		Alarm id."
	::= { alarmTrapEntry 6 }


------------------------------------------------------------
-- End of MIB definitions
------------------------------------------------------------

END
