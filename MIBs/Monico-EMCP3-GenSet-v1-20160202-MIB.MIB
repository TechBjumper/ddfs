Monico-EMCP3-GenSet-v1-MIB DEFINITIONS ::= BEGIN
    IMPORTS
    enterprises
        FROM RFC1155-SMI
    OBJECT-TYPE
        FROM RFC-1212
    TRAP-TYPE
        FROM RFC-1215;


    monico OBJECT IDENTIFIER ::= { enterprises 36282 }

    monicoProducts OBJECT IDENTIFIER ::= { monico 1 }

    monicoGateway OBJECT IDENTIFIER ::= { monicoProducts 1 }

    monicoGeneric OBJECT IDENTIFIER ::= { monicoGateway 1 }

    compressor OBJECT IDENTIFIER ::= { monicoGeneric 1 }

    emcpdata OBJECT IDENTIFIER ::= { compressor 1 }

    spacer OBJECT-TYPE
        SYNTAX              INTEGER
        ACCESS              read-only
        STATUS              mandatory
        DESCRIPTION         "Please replace this text with your description."
        ::= { emcpdata 1 }

    genD OBJECT IDENTIFIER ::= { emcpdata 2 }

    tot-kWHrsExport OBJECT-TYPE
        SYNTAX              INTEGER
        ACCESS              read-only
        STATUS              mandatory
        DESCRIPTION         "Total kWHr Export"
        ::= { genD 1 }

    phC-ReactivePower OBJECT-TYPE
        SYNTAX              INTEGER
        ACCESS              read-only
        STATUS              mandatory
        DESCRIPTION         "Generator Phase C Reactive Power"
        ::= { genD 2 }

    phC-PowerFactorx1000 OBJECT-TYPE
        SYNTAX              INTEGER
        ACCESS              read-only
        STATUS              mandatory
        DESCRIPTION         "Generator Phase C Power Factor X1000"
        ::= { genD 3 }

    phC-PowerFactorLag OBJECT-TYPE
        SYNTAX              INTEGER
        ACCESS              read-only
        STATUS              mandatory
        DESCRIPTION         "Generator Phase C Power Factor Lead/Lag"
        ::= { genD 4 }

    phC-RealPower OBJECT-TYPE
        SYNTAX              INTEGER
        ACCESS              read-only
        STATUS              mandatory
        DESCRIPTION         "Generator Phase C Real Power"
        ::= { genD 5 }

    phC-ApparentPower OBJECT-TYPE
        SYNTAX              INTEGER
        ACCESS              read-only
        STATUS              mandatory
        DESCRIPTION         "Generator Phase C Apparent Power"
        ::= { genD 6 }

    phC-LtoLRMSVolts OBJECT-TYPE
        SYNTAX              INTEGER
        ACCESS              read-only
        STATUS              mandatory
        DESCRIPTION         "Generator Phase C Line to Line RMS Voltage"
        ::= { genD 7 }

    phC-LtoNRMSVolts OBJECT-TYPE
        SYNTAX              INTEGER
        ACCESS              read-only
        STATUS              mandatory
        DESCRIPTION         "Generator Phase C Line to Neutral RMS Voltage"
        ::= { genD 8 }

    phC-RMSCurrent OBJECT-TYPE
        SYNTAX              INTEGER
        ACCESS              read-only
        STATUS              mandatory
        DESCRIPTION         "Generator Phase C RMS Current"
        ::= { genD 9 }

    phB-ReactivePower OBJECT-TYPE
        SYNTAX              INTEGER
        ACCESS              read-only
        STATUS              mandatory
        DESCRIPTION         "Generator Phase B Reactive Power"
        ::= { genD 10 }

    phB-PowerFactorx1000 OBJECT-TYPE
        SYNTAX              INTEGER
        ACCESS              read-only
        STATUS              mandatory
        DESCRIPTION         "Generator Phase B Power Factor X1000"
        ::= { genD 11 }

    phB-PowerFactorLag OBJECT-TYPE
        SYNTAX              INTEGER
        ACCESS              read-only
        STATUS              mandatory
        DESCRIPTION         "Generator Phase B Power Factor Lead/Lag"
        ::= { genD 12 }

    phB-RealPower OBJECT-TYPE
        SYNTAX              INTEGER
        ACCESS              read-only
        STATUS              mandatory
        DESCRIPTION         "Generator Phase B Real Power"
        ::= { genD 13 }

    phB-ApparentPower OBJECT-TYPE
        SYNTAX              INTEGER
        ACCESS              read-only
        STATUS              mandatory
        DESCRIPTION         "Generator Phase B Apparent Power"
        ::= { genD 14 }

    phB-LtoLRMSVolts OBJECT-TYPE
        SYNTAX              INTEGER
        ACCESS              read-only
        STATUS              mandatory
        DESCRIPTION         "Generator Phase B Line to Line RMS Voltage"
        ::= { genD 15 }

    phB-LtoNRMSVolts OBJECT-TYPE
        SYNTAX              INTEGER
        ACCESS              read-only
        STATUS              mandatory
        DESCRIPTION         "Generator Phase B Line to Neutral RMS Voltage"
        ::= { genD 16 }

    phB-RMSCurrent OBJECT-TYPE
        SYNTAX              INTEGER
        ACCESS              read-only
        STATUS              mandatory
        DESCRIPTION         "Generator Phase B RMS Current"
        ::= { genD 17 }

    phA-ReactivePower OBJECT-TYPE
        SYNTAX              INTEGER
        ACCESS              read-only
        STATUS              mandatory
        DESCRIPTION         "Generator Phase A Reactive Power"
        ::= { genD 18 }

    phA-PowerFactorx1000 OBJECT-TYPE
        SYNTAX              INTEGER
        ACCESS              read-only
        STATUS              mandatory
        DESCRIPTION         "Generator Phase A Power Factor X1000"
        ::= { genD 19 }

    phA-PowerFactorLag OBJECT-TYPE
        SYNTAX              INTEGER
        ACCESS              read-only
        STATUS              mandatory
        DESCRIPTION         "Generator Phase A Power Factor Lead/Lag"
        ::= { genD 20 }

    phA-RealPower OBJECT-TYPE
        SYNTAX              INTEGER
        ACCESS              read-only
        STATUS              mandatory
        DESCRIPTION         "Generator Phase A Real Power"
        ::= { genD 21 }

    phA-ApparentPower OBJECT-TYPE
        SYNTAX              INTEGER
        ACCESS              read-only
        STATUS              mandatory
        DESCRIPTION         "Generator Phase A Apparent Power"
        ::= { genD 22 }

    phALtoLRMSVolts OBJECT-TYPE
        SYNTAX              INTEGER
        ACCESS              read-only
        STATUS              mandatory
        DESCRIPTION         "Generator Phase A Line to Line RMS Voltage"
        ::= { genD 23 }

    phA-LtoNRMSVolts OBJECT-TYPE
        SYNTAX              INTEGER
        ACCESS              read-only
        STATUS              mandatory
        DESCRIPTION         "Generator Phase A Line to Neutral RMS Voltage"
        ::= { genD 24 }

    phA-RMSCurrent OBJECT-TYPE
        SYNTAX              INTEGER
        ACCESS              read-only
        STATUS              mandatory
        DESCRIPTION         "Generator Phase A RMS Current"
        ::= { genD 25 }

    totalRealPower OBJECT-TYPE
        SYNTAX              INTEGER
        ACCESS              read-only
        STATUS              mandatory
        DESCRIPTION         "Generator Total Real Power"
        ::= { genD 26 }

    totalReactivePower OBJECT-TYPE
        SYNTAX              INTEGER
        ACCESS              read-only
        STATUS              mandatory
        DESCRIPTION         "Generator Total Reactive Power"
        ::= { genD 27 }

    totalApparentPower OBJECT-TYPE
        SYNTAX              INTEGER
        ACCESS              read-only
        STATUS              mandatory
        DESCRIPTION         "Generator Total Apparent Power"
        ::= { genD 28 }

    overallPowerFactorx1000 OBJECT-TYPE
        SYNTAX              INTEGER
        ACCESS              read-only
        STATUS              mandatory
        DESCRIPTION         "Generator Overall Power Factor X1000"
        ::= { genD 29 }

    overallPowerFactorLag OBJECT-TYPE
        SYNTAX              INTEGER
        ACCESS              read-only
        STATUS              mandatory
        DESCRIPTION         "Generator Overall Power Factor Lead/Lag"
        ::= { genD 30 }

    avgLtoLRMSVolts OBJECT-TYPE
        SYNTAX              INTEGER
        ACCESS              read-only
        STATUS              mandatory
        DESCRIPTION         "Generator Average Line to Line RMS Voltage"
        ::= { genD 31 }

    avgLtoNRMSVolts OBJECT-TYPE
        SYNTAX              INTEGER
        ACCESS              read-only
        STATUS              mandatory
        DESCRIPTION         "Generator Average Line to Neutral RMS Voltage"
        ::= { genD 32 }

    avgFrequencyx100 OBJECT-TYPE
        SYNTAX              INTEGER
        ACCESS              read-only
        STATUS              mandatory
        DESCRIPTION         "Generator Average Frequency X100"
        ::= { genD 33 }

    avgRMSCurrent OBJECT-TYPE
        SYNTAX              INTEGER
        ACCESS              read-only
        STATUS              mandatory
        DESCRIPTION         "Generator Average RMS Current"
        ::= { genD 34 }

    realTimeClock-Seconds OBJECT-TYPE
        SYNTAX              INTEGER
        ACCESS              read-only
        STATUS              mandatory
        DESCRIPTION         "Real Time Clock-Seconds"
        ::= { genD 35 }

    realTimeClock-Minutes OBJECT-TYPE
        SYNTAX              INTEGER
        ACCESS              read-only
        STATUS              mandatory
        DESCRIPTION         "Real Time Clock-Minutes"
        ::= { genD 36 }

    realTimeClock-Hours OBJECT-TYPE
        SYNTAX              INTEGER
        ACCESS              read-only
        STATUS              mandatory
        DESCRIPTION         "Real Time Clock-Hours"
        ::= { genD 37 }

    realTimeClock-Day OBJECT-TYPE
        SYNTAX              INTEGER
        ACCESS              read-only
        STATUS              mandatory
        DESCRIPTION         "Real Time Clock-Day"
        ::= { genD 38 }

    realTimeClock-Month OBJECT-TYPE
        SYNTAX              INTEGER
        ACCESS              read-only
        STATUS              mandatory
        DESCRIPTION         "Real Time Clock-Month"
        ::= { genD 39 }

    realTimeClock-Year OBJECT-TYPE
        SYNTAX              INTEGER
        ACCESS              read-only
        STATUS              mandatory
        DESCRIPTION         "Real Time Clock-Year"
        ::= { genD 40 }

    maintHoursRemaining OBJECT-TYPE
        SYNTAX              INTEGER
        ACCESS              read-only
        STATUS              mandatory
        DESCRIPTION         "Hours Remaining until Maintenance"
        ::= { genD 41 }

    engineOperatingsHrsx10 OBJECT-TYPE
        SYNTAX              INTEGER
        ACCESS              read-only
        STATUS              mandatory
        DESCRIPTION         "Engine Operating Hours X10"
        ::= { genD 42 }

    actualTorque OBJECT-TYPE
        SYNTAX              INTEGER
        ACCESS              read-only
        STATUS              mandatory
        DESCRIPTION         "Actual Torque"
        ::= { genD 43 }

    engineRPMx8 OBJECT-TYPE
        SYNTAX              INTEGER
        ACCESS              read-only
        STATUS              mandatory
        DESCRIPTION         "Engine RPM X8"
        ::= { genD 44 }

    turbo1CompInletPressPSIx10 OBJECT-TYPE
        SYNTAX              INTEGER
        ACCESS              read-only
        STATUS              mandatory
        DESCRIPTION         "Turbo 1 Compressor Inlet Pressure - PSI X10"
        ::= { genD 45 }

    turbo2CompInletPressPSIx10 OBJECT-TYPE
        SYNTAX              INTEGER
        ACCESS              read-only
        STATUS              mandatory
        DESCRIPTION         "Turbo 2 Compressor Inlet Pressure - PSI X10"
        ::= { genD 46 }

    engineCoolantTempF OBJECT-TYPE
        SYNTAX              INTEGER
        ACCESS              read-only
        STATUS              mandatory
        DESCRIPTION         "Engine Coolant Temperature"
        ::= { genD 47 }

    engineFuelTempF OBJECT-TYPE
        SYNTAX              INTEGER
        ACCESS              read-only
        STATUS              mandatory
        DESCRIPTION         "Engine Fuel Temperature"
        ::= { genD 48 }

    fuelPressPSIx10 OBJECT-TYPE
        SYNTAX              INTEGER
        ACCESS              read-only
        STATUS              mandatory
        DESCRIPTION         "Fuel Pressure X10"
        ::= { genD 49 }

    engineOilPressPSIx10 OBJECT-TYPE
        SYNTAX              INTEGER
        ACCESS              read-only
        STATUS              mandatory
        DESCRIPTION         "Engine Oil Pressure X10"
        ::= { genD 50 }

    instanFuelConumpGalx100 OBJECT-TYPE
        SYNTAX              INTEGER
        ACCESS              read-only
        STATUS              mandatory
        DESCRIPTION         "Instantaneous Fuel Consumption X100"
        ::= { genD 51 }

    atmosphericPressurePSIx10 OBJECT-TYPE
        SYNTAX              INTEGER
        ACCESS              read-only
        STATUS              mandatory
        DESCRIPTION         "Atmospheric Pressure PSI X10"
        ::= { genD 52 }

    boostPressurePSIx10 OBJECT-TYPE
        SYNTAX              INTEGER
        ACCESS              read-only
        STATUS              mandatory
        DESCRIPTION         "Intake Manifold 1 Pressure (Boost Pressure) X10"
        ::= { genD 53 }

    intakeManifoldTempF OBJECT-TYPE
        SYNTAX              INTEGER
        ACCESS              read-only
        STATUS              mandatory
        DESCRIPTION         "Intake Manifold Temperature"
        ::= { genD 54 }

    airFilterDiffPressPSIx100 OBJECT-TYPE
        SYNTAX              INTEGER
        ACCESS              read-only
        STATUS              mandatory
        DESCRIPTION         "Air Filter Differential Pressure X100"
        ::= { genD 55 }

    exhaustTempF OBJECT-TYPE
        SYNTAX              INTEGER
        ACCESS              read-only
        STATUS              mandatory
        DESCRIPTION         "Exhaust Temperature"
        ::= { genD 56 }

    batteryVoltagex10 OBJECT-TYPE
        SYNTAX              INTEGER
        ACCESS              read-only
        STATUS              mandatory
        DESCRIPTION         "Battery Voltage X10"
        ::= { genD 57 }

    keyswitchBatteryVoltsx10 OBJECT-TYPE
        SYNTAX              INTEGER
        ACCESS              read-only
        STATUS              mandatory
        DESCRIPTION         "Keyswitch Battery Voltage X10"
        ::= { genD 58 }

    engineStatus OBJECT-TYPE
        SYNTAX              INTEGER
        ACCESS              read-only
        STATUS              mandatory
        DESCRIPTION         "Engine Status"
        ::= { genD 59 }

    emgergencyShutdown OBJECT-TYPE
        SYNTAX              INTEGER
        ACCESS              read-only
        STATUS              mandatory
        DESCRIPTION         "Emgergency Shutdown"
        ::= { genD 60 }

    engineRatedPowerx2 OBJECT-TYPE
        SYNTAX              INTEGER
        ACCESS              read-only
        STATUS              mandatory
        DESCRIPTION         "Engine Rated Power X2"
        ::= { genD 61 }

    engineRatedSpeedx8 OBJECT-TYPE
        SYNTAX              INTEGER
        ACCESS              read-only
        STATUS              mandatory
        DESCRIPTION         "Engine Rated Speed X8"
        ::= { genD 62 }

    desEngSpeedx8 OBJECT-TYPE
        SYNTAX              INTEGER
        ACCESS              read-only
        STATUS              mandatory
        DESCRIPTION         "Desired Engine Speed X8"
        ::= { genD 63 }

    throttlePostionx2point5 OBJECT-TYPE
        SYNTAX              INTEGER
        ACCESS              read-only
        STATUS              mandatory
        DESCRIPTION         "Throttle Postion X2.5"
        ::= { genD 64 }

    percentLoad OBJECT-TYPE
        SYNTAX              INTEGER
        ACCESS              read-only
        STATUS              mandatory
        DESCRIPTION         "Engine Percent Load"
        ::= { genD 65 }

    engWasteOilResLevelx2point5 OBJECT-TYPE
        SYNTAX              INTEGER
        ACCESS              read-only
        STATUS              mandatory
        DESCRIPTION         "Engine Waste Oil Resevoir Level X2.5"
        ::= { genD 66 }

    rightExhaustTempF OBJECT-TYPE
        SYNTAX              INTEGER
        ACCESS              read-only
        STATUS              mandatory
        DESCRIPTION         "Right ExhaustTemperature F"
        ::= { genD 67 }

    leftExhaustTempF OBJECT-TYPE
        SYNTAX              INTEGER
        ACCESS              read-only
        STATUS              mandatory
        DESCRIPTION         "Left Exhaust Temperature F"
        ::= { genD 68 }

    turbo1TubineInletTempF OBJECT-TYPE
        SYNTAX              INTEGER
        ACCESS              read-only
        STATUS              mandatory
        DESCRIPTION         "Turbo 1 Turbine Inlet Temperature F"
        ::= { genD 69 }

    turbo2TubineInletTempF OBJECT-TYPE
        SYNTAX              INTEGER
        ACCESS              read-only
        STATUS              mandatory
        DESCRIPTION         "Turbo 2 Turbine Inlet Temperature F"
        ::= { genD 70 }

    turbo1TubineOutletTempF OBJECT-TYPE
        SYNTAX              INTEGER
        ACCESS              read-only
        STATUS              mandatory
        DESCRIPTION         "Turbo 1 Turbine Outlet Temperature F"
        ::= { genD 71 }

    turbo2TubineOutletTempF OBJECT-TYPE
        SYNTAX              INTEGER
        ACCESS              read-only
        STATUS              mandatory
        DESCRIPTION         "Turbo 2 Turbine Outlet Temperature"
        ::= { genD 72 }

    oilFilterDiffPressPSIx10 OBJECT-TYPE
        SYNTAX              INTEGER
        ACCESS              read-only
        STATUS              mandatory
        DESCRIPTION         "Oil Filter Differential Pressure PSI X10"
        ::= { genD 73 }

    fuelFilterDiffPressPSI OBJECT-TYPE
        SYNTAX              INTEGER
        ACCESS              read-only
        STATUS              mandatory
        DESCRIPTION         "Fuel Filter Differential Pressure PSI"
        ::= { genD 74 }

    totalFuelConsumpGal OBJECT-TYPE
        SYNTAX              INTEGER
        ACCESS              read-only
        STATUS              mandatory
        DESCRIPTION         "Total Fuel Consumption Gallons"
        ::= { genD 75 }

    engineOilTempF OBJECT-TYPE
        SYNTAX              INTEGER
        ACCESS              read-only
        STATUS              mandatory
        DESCRIPTION         "Engine Oil Temperature F"
        ::= { genD 76 }

    engineIntercoolerTempF OBJECT-TYPE
        SYNTAX              INTEGER
        ACCESS              read-only
        STATUS              mandatory
        DESCRIPTION         "Engine Intercooler Temperature F"
        ::= { genD 77 }

    engineOilLevelPercentx2point5 OBJECT-TYPE
        SYNTAX              INTEGER
        ACCESS              read-only
        STATUS              mandatory
        DESCRIPTION         "Engine Oil Level Percent X2.5"
        ::= { genD 78 }

    engineCoolantLevelPercentx2point5 OBJECT-TYPE
        SYNTAX              INTEGER
        ACCESS              read-only
        STATUS              mandatory
        DESCRIPTION         "Engine Coolant Level Percent X2.5"
        ::= { genD 79 }

    engineCoolantPressPSI OBJECT-TYPE
        SYNTAX              INTEGER
        ACCESS              read-only
        STATUS              mandatory
        DESCRIPTION         "Engine Coolant Pressure PSI"
        ::= { genD 80 }

    crankcasePressurePSIx10 OBJECT-TYPE
        SYNTAX              INTEGER
        ACCESS              read-only
        STATUS              mandatory
        DESCRIPTION         "Crankcase Pressure PSI X10"
        ::= { genD 81 }

    ambientAirTempF OBJECT-TYPE
        SYNTAX              INTEGER
        ACCESS              read-only
        STATUS              mandatory
        DESCRIPTION         "Ambient Air Temperature F"
        ::= { genD 82 }

    netBatteryCurrentAmps OBJECT-TYPE
        SYNTAX              INTEGER
        ACCESS              read-only
        STATUS              mandatory
        DESCRIPTION         "Net Battery Current Amps"
        ::= { genD 83 }

    engineShutdownRequest OBJECT-TYPE
        SYNTAX              INTEGER
        ACCESS              read-only
        STATUS              mandatory
        DESCRIPTION         "Engine Shutdown Request"
        ::= { genD 84 }

    fuelLevelPercentx10 OBJECT-TYPE
        SYNTAX              INTEGER
        ACCESS              read-only
        STATUS              mandatory
        DESCRIPTION         "Fuel Level Percent X10"
        ::= { genD 85 }

    maintWeeksRemaining OBJECT-TYPE
        SYNTAX              INTEGER
        ACCESS              read-only
        STATUS              mandatory
        DESCRIPTION         "Weeks Remaining until Maintenance"
        ::= { genD 86 }

    dM1-SPN1 OBJECT-TYPE
        SYNTAX              INTEGER
        ACCESS              read-only
        STATUS              mandatory
        DESCRIPTION         "GSC Active Diagnostic Code 1-SPN"
        ::= { genD 87 }

    dM1-FMI1 OBJECT-TYPE
        SYNTAX              INTEGER
        ACCESS              read-only
        STATUS              mandatory
        DESCRIPTION         "GSC Active Diagnostic Code 1-FMI"
        ::= { genD 88 }

    dM1-OC1 OBJECT-TYPE
        SYNTAX              INTEGER
        ACCESS              read-only
        STATUS              mandatory
        DESCRIPTION         "GSC Number of Occurrences 1"
        ::= { genD 89 }

    dM1-SPN2 OBJECT-TYPE
        SYNTAX              INTEGER
        ACCESS              read-only
        STATUS              mandatory
        DESCRIPTION         "GSC Active Diagnostic Code 2-SPN"
        ::= { genD 90 }

    dM1-FMI2 OBJECT-TYPE
        SYNTAX              INTEGER
        ACCESS              read-only
        STATUS              mandatory
        DESCRIPTION         "GSC Active Diagnostic Code 2-FMI"
        ::= { genD 91 }

    dM1-OC2 OBJECT-TYPE
        SYNTAX              INTEGER
        ACCESS              read-only
        STATUS              mandatory
        DESCRIPTION         "GSC Number of Occurrences 2"
        ::= { genD 92 }

    dM1-SPN3 OBJECT-TYPE
        SYNTAX              INTEGER
        ACCESS              read-only
        STATUS              mandatory
        DESCRIPTION         "GSC Active Diagnostic Code 3-SPN"
        ::= { genD 93 }

    dM1-FMI3 OBJECT-TYPE
        SYNTAX              INTEGER
        ACCESS              read-only
        STATUS              mandatory
        DESCRIPTION         "GSC Active Diagnostic Code 3-FMI"
        ::= { genD 94 }

    dM1-OC3 OBJECT-TYPE
        SYNTAX              INTEGER
        ACCESS              read-only
        STATUS              mandatory
        DESCRIPTION         "GSC Number of Occurrences 3"
        ::= { genD 95 }

    dM1-SPN4 OBJECT-TYPE
        SYNTAX              INTEGER
        ACCESS              read-only
        STATUS              mandatory
        DESCRIPTION         "GSC Active Diagnostic Code 4-SPN"
        ::= { genD 96 }

    dM1-FMI4 OBJECT-TYPE
        SYNTAX              INTEGER
        ACCESS              read-only
        STATUS              mandatory
        DESCRIPTION         "GSC Active Diagnostic Code 4-FMI"
        ::= { genD 97 }

    dMI1-OC4 OBJECT-TYPE
        SYNTAX              INTEGER
        ACCESS              read-only
        STATUS              mandatory
        DESCRIPTION         "GSC Number of Occurrences 4"
        ::= { genD 98 }

    dM1-SPN5 OBJECT-TYPE
        SYNTAX              INTEGER
        ACCESS              read-only
        STATUS              mandatory
        DESCRIPTION         "GSC Active Diagnostic Code 5-SPN"
        ::= { genD 99 }

    dM1-FMI5 OBJECT-TYPE
        SYNTAX              INTEGER
        ACCESS              read-only
        STATUS              mandatory
        DESCRIPTION         "GSC Active Diagnostic Code 5-FMI"
        ::= { genD 100 }

    dM1-OC5 OBJECT-TYPE
        SYNTAX              INTEGER
        ACCESS              read-only
        STATUS              mandatory
        DESCRIPTION         "GSC Number of Occurrences 5"
        ::= { genD 101 }

    dM2-SPN1 OBJECT-TYPE
        SYNTAX              INTEGER
        ACCESS              read-only
        STATUS              mandatory
        DESCRIPTION         "GSC Previously Active Diagnostic Code 1-SPN"
        ::= { genD 102 }

    dM2-FIM1 OBJECT-TYPE
        SYNTAX              INTEGER
        ACCESS              read-only
        STATUS              mandatory
        DESCRIPTION         "GSC Previously Active Diagnostic Code 1-FMI"
        ::= { genD 103 }

    dM2-OC1 OBJECT-TYPE
        SYNTAX              INTEGER
        ACCESS              read-only
        STATUS              mandatory
        DESCRIPTION         "GSC Previously Number of Occurrences 1"
        ::= { genD 104 }

    dM2-SPN2 OBJECT-TYPE
        SYNTAX              INTEGER
        ACCESS              read-only
        STATUS              mandatory
        DESCRIPTION         "GSC Previously Active Diagnostic Code 2-SPN"
        ::= { genD 105 }

    dM2-FMI2 OBJECT-TYPE
        SYNTAX              INTEGER
        ACCESS              read-only
        STATUS              mandatory
        DESCRIPTION         "GSC Previously Active Diagnostic Code 2-FMI"
        ::= { genD 106 }

    dM2-OC2 OBJECT-TYPE
        SYNTAX              INTEGER
        ACCESS              read-only
        STATUS              mandatory
        DESCRIPTION         "GSC Previously Number of Occurrences 2"
        ::= { genD 107 }

    dM2-SPN3 OBJECT-TYPE
        SYNTAX              INTEGER
        ACCESS              read-only
        STATUS              mandatory
        DESCRIPTION         "GSC Previously Active Diagnostic Code 3-SPN"
        ::= { genD 108 }

    dM2-FMI3 OBJECT-TYPE
        SYNTAX              INTEGER
        ACCESS              read-only
        STATUS              mandatory
        DESCRIPTION         "GSC Previously Active Diagnostic Code 3-FMI"
        ::= { genD 109 }

    dM2-OC3 OBJECT-TYPE
        SYNTAX              INTEGER
        ACCESS              read-only
        STATUS              mandatory
        DESCRIPTION         "GSC Previously Number of Occurrences 3"
        ::= { genD 110 }

    dM2-SPN4 OBJECT-TYPE
        SYNTAX              INTEGER
        ACCESS              read-only
        STATUS              mandatory
        DESCRIPTION         "GSC Previously Active Diagnostic Code 4-SPN"
        ::= { genD 111 }

    dM2-FMI4 OBJECT-TYPE
        SYNTAX              INTEGER
        ACCESS              read-only
        STATUS              mandatory
        DESCRIPTION         "GSC Previously Active Diagnostic Code 4-FMI"
        ::= { genD 112 }

    dM2-OC4 OBJECT-TYPE
        SYNTAX              INTEGER
        ACCESS              read-only
        STATUS              mandatory
        DESCRIPTION         "GSC Previously Number of Occurrences 4"
        ::= { genD 113 }

    dM2-SPN5 OBJECT-TYPE
        SYNTAX              INTEGER
        ACCESS              read-only
        STATUS              mandatory
        DESCRIPTION         "GSC Previously Active Diagnostic Code 5-SPN"
        ::= { genD 114 }

    dM2-FMI5 OBJECT-TYPE
        SYNTAX              INTEGER
        ACCESS              read-only
        STATUS              mandatory
        DESCRIPTION         "GSC Previously Active Diagnostic Code 5-FMI"
        ::= { genD 115 }

    dM2-OC5 OBJECT-TYPE
        SYNTAX              INTEGER
        ACCESS              read-only
        STATUS              mandatory
        DESCRIPTION         "GSC Previously Number of Occurrences 5"
        ::= { genD 116 }

    dM1-SPN1-1 OBJECT-TYPE
        SYNTAX              INTEGER
        ACCESS              read-only
        STATUS              mandatory
        DESCRIPTION         "Engine Active Diagnostic Code 1-SPN"
        ::= { genD 117 }

    dM1-FIM1 OBJECT-TYPE
        SYNTAX              INTEGER
        ACCESS              read-only
        STATUS              mandatory
        DESCRIPTION         "Engine Active Diagnostic Code 1-FMI"
        ::= { genD 118 }

    dM1-OC1-1 OBJECT-TYPE
        SYNTAX              INTEGER
        ACCESS              read-only
        STATUS              mandatory
        DESCRIPTION         "Engine Number of Occurrences 1"
        ::= { genD 119 }

    dM1-SPN2-1 OBJECT-TYPE
        SYNTAX              INTEGER
        ACCESS              read-only
        STATUS              mandatory
        DESCRIPTION         "Engine Active Diagnostic Code 2-SPN"
        ::= { genD 120 }

    dM1-FMI2-1 OBJECT-TYPE
        SYNTAX              INTEGER
        ACCESS              read-only
        STATUS              mandatory
        DESCRIPTION         "Engine Active Diagnostic Code 2-FMI"
        ::= { genD 121 }

    dM1-OC2-1 OBJECT-TYPE
        SYNTAX              INTEGER
        ACCESS              read-only
        STATUS              mandatory
        DESCRIPTION         "Engine Number of Occurrences 2"
        ::= { genD 122 }

    dM1-SPN3-1 OBJECT-TYPE
        SYNTAX              INTEGER
        ACCESS              read-only
        STATUS              mandatory
        DESCRIPTION         "Engine Active Diagnostic Code 3-SPN"
        ::= { genD 123 }

    dM1-FMI3-1 OBJECT-TYPE
        SYNTAX              INTEGER
        ACCESS              read-only
        STATUS              mandatory
        DESCRIPTION         "Engine Active Diagnostic Code 3-FMI"
        ::= { genD 124 }

    dM1-OC3-1 OBJECT-TYPE
        SYNTAX              INTEGER
        ACCESS              read-only
        STATUS              mandatory
        DESCRIPTION         "Engine Number of Occurrences 3"
        ::= { genD 125 }

    dM1-SPN4-1 OBJECT-TYPE
        SYNTAX              INTEGER
        ACCESS              read-only
        STATUS              mandatory
        DESCRIPTION         "Engine Active Diagnostic Code 4-SPN"
        ::= { genD 126 }

    dM1-FMI4-1 OBJECT-TYPE
        SYNTAX              INTEGER
        ACCESS              read-only
        STATUS              mandatory
        DESCRIPTION         "Engine Active Diagnostic Code 4-FMI"
        ::= { genD 127 }

    dM1-OC4-1 OBJECT-TYPE
        SYNTAX              INTEGER
        ACCESS              read-only
        STATUS              mandatory
        DESCRIPTION         "Engine Number of Occurrences 4"
        ::= { genD 128 }

    dM1-SPN5-1 OBJECT-TYPE
        SYNTAX              INTEGER
        ACCESS              read-only
        STATUS              mandatory
        DESCRIPTION         "Engine Active Diagnostic Code 5-SPN"
        ::= { genD 129 }

    dM1-FMI5-1 OBJECT-TYPE
        SYNTAX              INTEGER
        ACCESS              read-only
        STATUS              mandatory
        DESCRIPTION         "Engine Active Diagnostic Code 5-FMI"
        ::= { genD 130 }

    dM1-OC5-1 OBJECT-TYPE
        SYNTAX              INTEGER
        ACCESS              read-only
        STATUS              mandatory
        DESCRIPTION         "Engine Number of Occurrences 5"
        ::= { genD 131 }

    dM2-SPN1-2 OBJECT-TYPE
        SYNTAX              INTEGER
        ACCESS              read-only
        STATUS              mandatory
        DESCRIPTION         "Engine Previously Active Diagnostic Code 1-SPN"
        ::= { genD 132 }

    dM2-FMI1-2 OBJECT-TYPE
        SYNTAX              INTEGER
        ACCESS              read-only
        STATUS              mandatory
        DESCRIPTION         "Engine Previously Active Diagnostic Code 1-FMI"
        ::= { genD 133 }

    dM2-OC1-2 OBJECT-TYPE
        SYNTAX              INTEGER
        ACCESS              read-only
        STATUS              mandatory
        DESCRIPTION         "Engine Previously Number of Occurrences 1"
        ::= { genD 134 }

    dM2-SPN2-2 OBJECT-TYPE
        SYNTAX              INTEGER
        ACCESS              read-only
        STATUS              mandatory
        DESCRIPTION         "Engine Previously Active Diagnostic Code 2-SPN"
        ::= { genD 135 }

    dM2-FMI2-2 OBJECT-TYPE
        SYNTAX              INTEGER
        ACCESS              read-only
        STATUS              mandatory
        DESCRIPTION         "Engine Previously Active Diagnostic Code 2-FMI"
        ::= { genD 136 }

    dM2-OC2-2 OBJECT-TYPE
        SYNTAX              INTEGER
        ACCESS              read-only
        STATUS              mandatory
        DESCRIPTION         "Engine Previously Number of Occurrences 2"
        ::= { genD 137 }

    dM2-SPN3-2 OBJECT-TYPE
        SYNTAX              INTEGER
        ACCESS              read-only
        STATUS              mandatory
        DESCRIPTION         "Engine Previously Active Diagnostic Code 3-SPN"
        ::= { genD 138 }

    dM2-FMI3-2 OBJECT-TYPE
        SYNTAX              INTEGER
        ACCESS              read-only
        STATUS              mandatory
        DESCRIPTION         "Engine Previously Active Diagnostic Code 3-FMI"
        ::= { genD 139 }

    dM2-OC3-2 OBJECT-TYPE
        SYNTAX              INTEGER
        ACCESS              read-only
        STATUS              mandatory
        DESCRIPTION         "Engine Previously Number of Occurrences 3"
        ::= { genD 140 }

    dM2-SPN4-2 OBJECT-TYPE
        SYNTAX              INTEGER
        ACCESS              read-only
        STATUS              mandatory
        DESCRIPTION         "Engine Previously Active Diagnostic Code 4-SPN"
        ::= { genD 141 }

    dM2-FMI4-2 OBJECT-TYPE
        SYNTAX              INTEGER
        ACCESS              read-only
        STATUS              mandatory
        DESCRIPTION         "Engine Previously Active Diagnostic Code 4-FMI"
        ::= { genD 142 }

    dm2-OC4-2 OBJECT-TYPE
        SYNTAX              INTEGER
        ACCESS              read-only
        STATUS              mandatory
        DESCRIPTION         "Engine Previously Number of Occurrences 4"
        ::= { genD 143 }

    dM2-SPN5-2 OBJECT-TYPE
        SYNTAX              INTEGER
        ACCESS              read-only
        STATUS              mandatory
        DESCRIPTION         "Engine Previously Active Diagnostic Code 5-SPN"
        ::= { genD 144 }

    dM2-FMI5-2 OBJECT-TYPE
        SYNTAX              INTEGER
        ACCESS              read-only
        STATUS              mandatory
        DESCRIPTION         "Engine Previously Active Diagnostic Code 5-FMI"
        ::= { genD 145 }

    dM2-OC5-2 OBJECT-TYPE
        SYNTAX              INTEGER
        ACCESS              read-only
        STATUS              mandatory
        DESCRIPTION         "Engine Previously Number of Occurrences 5"
        ::= { genD 146 }

    engine OBJECT IDENTIFIER ::= { monicoGeneric 2 }

    emcptraps OBJECT IDENTIFIER ::= { engine 1 }

    subgroup OBJECT IDENTIFIER ::= { emcptraps 1 }

    genT OBJECT IDENTIFIER ::= { emcptraps 2 }

    extHighFuelLevelShutdown OBJECT-TYPE
        SYNTAX              INTEGER
        ACCESS              read-only
        STATUS              mandatory
        DESCRIPTION         "Ext Tank High Fuel Lvl S/D (38-0)"
        ::= { genT 1 }

    extLowFuelLevelShutdown OBJECT-TYPE
        SYNTAX              INTEGER
        ACCESS              read-only
        STATUS              mandatory
        DESCRIPTION         "Ext Tank LowFuel Lvl S/D (38-1)"
        ::= { genT 2 }

    extFuelLvlSensShortHigh OBJECT-TYPE
        SYNTAX              INTEGER
        ACCESS              read-only
        STATUS              mandatory
        DESCRIPTION         "Ext Tank High Fuel Lvl Snsr Shrt High (38-3)"
        ::= { genT 3 }

    extFuelLevelSnesShortLow OBJECT-TYPE
        SYNTAX              INTEGER
        ACCESS              read-only
        STATUS              mandatory
        DESCRIPTION         "F09408 High Coolant Temperature Shutdown"
        ::= { genT 4 }

    extHighFuelLvlWarning OBJECT-TYPE
        SYNTAX              INTEGER
        ACCESS              read-only
        STATUS              mandatory
        DESCRIPTION         "Ext Tank Fuel Lvl Warning (38-15)"
        ::= { genT 5 }

    extLowFuelLvlWarning OBJECT-TYPE
        SYNTAX              INTEGER
        ACCESS              read-only
        STATUS              mandatory
        DESCRIPTION         "Ext Tank Low Fuel Lvl Warning (38-17)"
        ::= { genT 6 }

    highStartPressShutdown OBJECT-TYPE
        SYNTAX              INTEGER
        ACCESS              read-only
        STATUS              mandatory
        DESCRIPTION         "High Starting Air Press S/D (82-0)"
        ::= { genT 7 }

    lowStartPressShutdown OBJECT-TYPE
        SYNTAX              INTEGER
        ACCESS              read-only
        STATUS              mandatory
        DESCRIPTION         "Low Starting Air Pressure S/D (82-1)"
        ::= { genT 8 }

    startAirPresSensShrtHigh OBJECT-TYPE
        SYNTAX              INTEGER
        ACCESS              read-only
        STATUS              mandatory
        DESCRIPTION         "Starting Air Pres Sensor Short High (82-3)"
        ::= { genT 9 }

    startAirPresSensShrtLow OBJECT-TYPE
        SYNTAX              INTEGER
        ACCESS              read-only
        STATUS              mandatory
        DESCRIPTION         "Starting Air Pres Sensor Short Low (82-4)"
        ::= { genT 10 }

    highStartAirPressWarning OBJECT-TYPE
        SYNTAX              INTEGER
        ACCESS              read-only
        STATUS              mandatory
        DESCRIPTION         "High Start Air Press Warning (82-15)"
        ::= { genT 11 }

    lowStartAirPressWarning OBJECT-TYPE
        SYNTAX              INTEGER
        ACCESS              read-only
        STATUS              mandatory
        DESCRIPTION         "Low Start Air Press Warning (82-17)"
        ::= { genT 12 }

    highFuelFltrDiffShutdown OBJECT-TYPE
        SYNTAX              INTEGER
        ACCESS              read-only
        STATUS              mandatory
        DESCRIPTION         "High Fuel Fltr Diff Pres S/D (95-0)"
        ::= { genT 13 }

    lowFuelFltrDiffShutdown OBJECT-TYPE
        SYNTAX              INTEGER
        ACCESS              read-only
        STATUS              mandatory
        DESCRIPTION         "Low Fuel Fltr Diff Pres S/D (95-1)"
        ::= { genT 14 }

    fFDiffPresSnsShortHigh OBJECT-TYPE
        SYNTAX              INTEGER
        ACCESS              read-only
        STATUS              mandatory
        DESCRIPTION         "Fuel Fltr Dif Pres Sns Short High (95-3)"
        ::= { genT 15 }

    fFDiffPresSnsShortLow OBJECT-TYPE
        SYNTAX              INTEGER
        ACCESS              read-only
        STATUS              mandatory
        DESCRIPTION         "Fuel Fltr Dif Pres Snsr Short Low (95-4)"
        ::= { genT 16 }

    highFuelFltrDiffPresWrn OBJECT-TYPE
        SYNTAX              INTEGER
        ACCESS              read-only
        STATUS              mandatory
        DESCRIPTION         "High Fuel Fltr Diff Pres Warning (95-15)"
        ::= { genT 17 }

    lowFuelFltrDiffPresWrn OBJECT-TYPE
        SYNTAX              INTEGER
        ACCESS              read-only
        STATUS              mandatory
        DESCRIPTION         "Low Fuel Fltr Diff Pres Warning (95-17)"
        ::= { genT 18 }

    highFuelLevelShutdown OBJECT-TYPE
        SYNTAX              INTEGER
        ACCESS              read-only
        STATUS              mandatory
        DESCRIPTION         "High Fuel Lvl S/D (96-0)"
        ::= { genT 19 }

    lowFuelLevelShutdown OBJECT-TYPE
        SYNTAX              INTEGER
        ACCESS              read-only
        STATUS              mandatory
        DESCRIPTION         "Low Fuel Lvl S/D (96-1)"
        ::= { genT 20 }

    fuelLvlSnsShortHigh OBJECT-TYPE
        SYNTAX              INTEGER
        ACCESS              read-only
        STATUS              mandatory
        DESCRIPTION         "Fue Lvl Sens Short High (96-3)"
        ::= { genT 21 }

    fuelLvlSnsShortLow OBJECT-TYPE
        SYNTAX              INTEGER
        ACCESS              read-only
        STATUS              mandatory
        DESCRIPTION         "Fue Lvl Sens Short Low (96-4)"
        ::= { genT 22 }

    highFuelWarning OBJECT-TYPE
        SYNTAX              INTEGER
        ACCESS              read-only
        STATUS              mandatory
        DESCRIPTION         "High Fuel Level Warning (96-15)"
        ::= { genT 23 }

    lowFuelWarning OBJECT-TYPE
        SYNTAX              INTEGER
        ACCESS              read-only
        STATUS              mandatory
        DESCRIPTION         "Low Fuel Level Warning (96-17)"
        ::= { genT 24 }

    highEngineOilLvlSD OBJECT-TYPE
        SYNTAX              INTEGER
        ACCESS              read-only
        STATUS              mandatory
        DESCRIPTION         "High Engine Oil Lvl S/D (98-0)"
        ::= { genT 25 }

    lowEngineOilLvlSD OBJECT-TYPE
        SYNTAX              INTEGER
        ACCESS              read-only
        STATUS              mandatory
        DESCRIPTION         "Low Engine Oil Lvl S/D (98-1)"
        ::= { genT 26 }

    engOilSnsrShortHigh OBJECT-TYPE
        SYNTAX              INTEGER
        ACCESS              read-only
        STATUS              mandatory
        DESCRIPTION         "Eng Oil Lvl Sens Short High (98-3)"
        ::= { genT 27 }

    engOilSnsrShortLow OBJECT-TYPE
        SYNTAX              INTEGER
        ACCESS              read-only
        STATUS              mandatory
        DESCRIPTION         "Eng Oil Lvl Sens Short Low (98-4)"
        ::= { genT 28 }

    highEngOilLvlWarning OBJECT-TYPE
        SYNTAX              INTEGER
        ACCESS              read-only
        STATUS              mandatory
        DESCRIPTION         "High Eng Oil Lvl Warning (98-15)"
        ::= { genT 29 }

    lowEngOilLvlWarning OBJECT-TYPE
        SYNTAX              INTEGER
        ACCESS              read-only
        STATUS              mandatory
        DESCRIPTION         "Low Eng Oil Lvl Warning (98-17)"
        ::= { genT 30 }

    highOilFltDifPresSD OBJECT-TYPE
        SYNTAX              INTEGER
        ACCESS              read-only
        STATUS              mandatory
        DESCRIPTION         "High Oil Fltr Dif Pres S/D (99-0)"
        ::= { genT 31 }

    lowOilFltDifPresSD OBJECT-TYPE
        SYNTAX              INTEGER
        ACCESS              read-only
        STATUS              mandatory
        DESCRIPTION         "Low Oil Fltr Dif Pres S/D (99-1)"
        ::= { genT 32 }

    oilFltrDifPresShortHigh OBJECT-TYPE
        SYNTAX              INTEGER
        ACCESS              read-only
        STATUS              mandatory
        DESCRIPTION         "Oil Fltr Diff Pres Sns Short High (99-3)"
        ::= { genT 33 }

    oilFltrDifPresShortLow OBJECT-TYPE
        SYNTAX              INTEGER
        ACCESS              read-only
        STATUS              mandatory
        DESCRIPTION         "Oil Fltr Diff Pres Sns Short Low (99-4)"
        ::= { genT 34 }

    highOilFltDifPresWarn OBJECT-TYPE
        SYNTAX              INTEGER
        ACCESS              read-only
        STATUS              mandatory
        DESCRIPTION         "High Oil Fltr Dif Pres Warning (99-15)"
        ::= { genT 35 }

    lowOilFltDifPresWarn OBJECT-TYPE
        SYNTAX              INTEGER
        ACCESS              read-only
        STATUS              mandatory
        DESCRIPTION         "Low Oil Fltr Dif Pres Warning (99-17)"
        ::= { genT 36 }

    lowEngineOilPresSD OBJECT-TYPE
        SYNTAX              INTEGER
        ACCESS              read-only
        STATUS              mandatory
        DESCRIPTION         "Low Eng Oil Pres S/D (100-1)"
        ::= { genT 37 }

    lowEngineOilPresWarn OBJECT-TYPE
        SYNTAX              INTEGER
        ACCESS              read-only
        STATUS              mandatory
        DESCRIPTION         "Low Eng Oil Pres Warn (100-17)"
        ::= { genT 38 }

    highAirFltrDifPresSD OBJECT-TYPE
        SYNTAX              INTEGER
        ACCESS              read-only
        STATUS              mandatory
        DESCRIPTION         "High Air Flt Dif Pres S/D (107-0)"
        ::= { genT 39 }

    lowAirFltrDifPresSD OBJECT-TYPE
        SYNTAX              INTEGER
        ACCESS              read-only
        STATUS              mandatory
        DESCRIPTION         "Low Air Flt Dif Pres S/D (107-1)"
        ::= { genT 40 }

    airFltrDifPresShortHigh OBJECT-TYPE
        SYNTAX              INTEGER
        ACCESS              read-only
        STATUS              mandatory
        DESCRIPTION         "Air Fltr Dif Pres Sens Shrt High (107-3)"
        ::= { genT 41 }

    airFltrDifPresShortLow OBJECT-TYPE
        SYNTAX              INTEGER
        ACCESS              read-only
        STATUS              mandatory
        DESCRIPTION         "Air Fltr Dif Pres Sens Shrt Low (107-4)"
        ::= { genT 42 }

    highAirFltrDifPResWarn OBJECT-TYPE
        SYNTAX              INTEGER
        ACCESS              read-only
        STATUS              mandatory
        DESCRIPTION         "High Air Pres Dif Pres Warn (107-15)"
        ::= { genT 43 }

    lowAirFltrDifPResWarn OBJECT-TYPE
        SYNTAX              INTEGER
        ACCESS              read-only
        STATUS              mandatory
        DESCRIPTION         "Low Air Pres Dif Pres Warn (107-17)"
        ::= { genT 44 }

    highEngCoolTempSD OBJECT-TYPE
        SYNTAX              INTEGER
        ACCESS              read-only
        STATUS              mandatory
        DESCRIPTION         "High Eng Cool Temp S/D (110-0)"
        ::= { genT 45 }

    highEngCoolTempWarn OBJECT-TYPE
        SYNTAX              INTEGER
        ACCESS              read-only
        STATUS              mandatory
        DESCRIPTION         "High Eng Cool Temp Warn (110-15)"
        ::= { genT 46 }

    lowEngCoolTempWarn OBJECT-TYPE
        SYNTAX              INTEGER
        ACCESS              read-only
        STATUS              mandatory
        DESCRIPTION         "Low Eng Cool Temp Warn (110-17)"
        ::= { genT 47 }

    highEngCoolLvlSD OBJECT-TYPE
        SYNTAX              INTEGER
        ACCESS              read-only
        STATUS              mandatory
        DESCRIPTION         "High Engine Cool Lvl S/D (111-0)"
        ::= { genT 48 }

    lowEngCoolLvlSD OBJECT-TYPE
        SYNTAX              INTEGER
        ACCESS              read-only
        STATUS              mandatory
        DESCRIPTION         "Low Engine Cool Lvl S/D (111-1)"
        ::= { genT 49 }

    engCoolLvlSnsShrtHi OBJECT-TYPE
        SYNTAX              INTEGER
        ACCESS              read-only
        STATUS              mandatory
        DESCRIPTION         "Eng Cool Lvl Sns Shrt High (111-3)"
        ::= { genT 50 }

    engCoolLvlSnsShrtLow OBJECT-TYPE
        SYNTAX              INTEGER
        ACCESS              read-only
        STATUS              mandatory
        DESCRIPTION         "Eng Cool Lvl Sns Shrt Low (111-4)"
        ::= { genT 51 }

    highEngCoolLvlWarn OBJECT-TYPE
        SYNTAX              INTEGER
        ACCESS              read-only
        STATUS              mandatory
        DESCRIPTION         "High Eng Cool Lvl Warn (111-15)"
        ::= { genT 52 }

    lowEngCoolLvlWarn OBJECT-TYPE
        SYNTAX              INTEGER
        ACCESS              read-only
        STATUS              mandatory
        DESCRIPTION         "High Eng Cool Lvl Warn (111-17)"
        ::= { genT 53 }

    highFireExtPresSD OBJECT-TYPE
        SYNTAX              INTEGER
        ACCESS              read-only
        STATUS              mandatory
        DESCRIPTION         "Fire Extinguisher Pres S/D (137-0)"
        ::= { genT 54 }

    lowFireExtPresSD OBJECT-TYPE
        SYNTAX              INTEGER
        ACCESS              read-only
        STATUS              mandatory
        DESCRIPTION         "Low Fire Extinguisher Pres S/D (137-1)"
        ::= { genT 55 }

    fireExtPresSnsShrtHigh OBJECT-TYPE
        SYNTAX              INTEGER
        ACCESS              read-only
        STATUS              mandatory
        DESCRIPTION         "Low Fire Extinguisher Pres Shrt High (137-3)"
        ::= { genT 56 }

    fireExtPresSnsShrtLow OBJECT-TYPE
        SYNTAX              INTEGER
        ACCESS              read-only
        STATUS              mandatory
        DESCRIPTION         "Low Fire Extinguisher Pres Shrt Low (137-4)"
        ::= { genT 57 }

    highFireExtPresWarn OBJECT-TYPE
        SYNTAX              INTEGER
        ACCESS              read-only
        STATUS              mandatory
        DESCRIPTION         "High Fire Ext Pres Warn (137-15)"
        ::= { genT 58 }

    lowFireExtPresWarn OBJECT-TYPE
        SYNTAX              INTEGER
        ACCESS              read-only
        STATUS              mandatory
        DESCRIPTION         "Low Fire Ext Pres Warn (137-17)"
        ::= { genT 59 }

    lowBatChrgSysVoltWarn OBJECT-TYPE
        SYNTAX              INTEGER
        ACCESS              read-only
        STATUS              mandatory
        DESCRIPTION         "Low Batt Sys Voltage Warn (167-17)"
        ::= { genT 60 }

    highBattVoltageSD OBJECT-TYPE
        SYNTAX              INTEGER
        ACCESS              read-only
        STATUS              mandatory
        DESCRIPTION         "High Batt Voltage S/D (168-0)"
        ::= { genT 61 }

    highBattVoltageWarn OBJECT-TYPE
        SYNTAX              INTEGER
        ACCESS              read-only
        STATUS              mandatory
        DESCRIPTION         "F24022-Low Transmission Oil Pressure Shutdown"
        ::= { genT 62 }

    lowBattVoltageWarn OBJECT-TYPE
        SYNTAX              INTEGER
        ACCESS              read-only
        STATUS              mandatory
        DESCRIPTION         "Low Batt Voltage Warn (168-17)"
        ::= { genT 63 }

    highAmbAirTempSD OBJECT-TYPE
        SYNTAX              INTEGER
        ACCESS              read-only
        STATUS              mandatory
        DESCRIPTION         "High Amb Air Temp S/D (171-0)"
        ::= { genT 64 }

    lowAmbAirTempSD OBJECT-TYPE
        SYNTAX              INTEGER
        ACCESS              read-only
        STATUS              mandatory
        DESCRIPTION         "Low Amb Air Temp S/D (171-1)"
        ::= { genT 65 }

    ambAirSnsShortHigh OBJECT-TYPE
        SYNTAX              INTEGER
        ACCESS              read-only
        STATUS              mandatory
        DESCRIPTION         "Amb Air Sns Short High (171-3)"
        ::= { genT 66 }

    ambAirSnsShortLow OBJECT-TYPE
        SYNTAX              INTEGER
        ACCESS              read-only
        STATUS              mandatory
        DESCRIPTION         "Amb Air Sns Short Low (171-4)"
        ::= { genT 67 }

    highAmbAirTempWarn OBJECT-TYPE
        SYNTAX              INTEGER
        ACCESS              read-only
        STATUS              mandatory
        DESCRIPTION         "High Amb Air Temp Warn (171-15)"
        ::= { genT 68 }

    lowAmbAirTempWarn OBJECT-TYPE
        SYNTAX              INTEGER
        ACCESS              read-only
        STATUS              mandatory
        DESCRIPTION         "Low Amb Air Temp Warn (171-17)"
        ::= { genT 69 }

    highExhTempSD OBJECT-TYPE
        SYNTAX              INTEGER
        ACCESS              read-only
        STATUS              mandatory
        DESCRIPTION         "High Exh Temp S/D (173-0)"
        ::= { genT 70 }

    lowExhTempSD OBJECT-TYPE
        SYNTAX              INTEGER
        ACCESS              read-only
        STATUS              mandatory
        DESCRIPTION         "Low Exh Temp S/D (173-1)"
        ::= { genT 71 }

    exhTempSnsShrtHigh OBJECT-TYPE
        SYNTAX              INTEGER
        ACCESS              read-only
        STATUS              mandatory
        DESCRIPTION         "Exh Temp Sns Shrt High (173-3)"
        ::= { genT 72 }

    exhTempSnsShrtLow OBJECT-TYPE
        SYNTAX              INTEGER
        ACCESS              read-only
        STATUS              mandatory
        DESCRIPTION         "Exh Temp Sns Shrt Low (173-4)"
        ::= { genT 73 }

    highExhTempWarn OBJECT-TYPE
        SYNTAX              INTEGER
        ACCESS              read-only
        STATUS              mandatory
        DESCRIPTION         "High Exh Temp Warn (173-15)"
        ::= { genT 74 }

    lowExhTempWarn OBJECT-TYPE
        SYNTAX              INTEGER
        ACCESS              read-only
        STATUS              mandatory
        DESCRIPTION         "Low Exh Temp Warn (173-17)"
        ::= { genT 75 }

    highEngOilTempSD OBJECT-TYPE
        SYNTAX              INTEGER
        ACCESS              read-only
        STATUS              mandatory
        DESCRIPTION         "High Eng Oil Temp S/D (175-0)"
        ::= { genT 76 }

    lowEngOilTempSD OBJECT-TYPE
        SYNTAX              INTEGER
        ACCESS              read-only
        STATUS              mandatory
        DESCRIPTION         "Low Eng Oil Temp S/D (175-1)"
        ::= { genT 77 }

    engOilTempSnsShrtHigh OBJECT-TYPE
        SYNTAX              INTEGER
        ACCESS              read-only
        STATUS              mandatory
        DESCRIPTION         "Eng Oil Temp Sns Short High (175-3)"
        ::= { genT 78 }

    engOilTempSnsShrtLow OBJECT-TYPE
        SYNTAX              INTEGER
        ACCESS              read-only
        STATUS              mandatory
        DESCRIPTION         "Eng Oil Temp Sns Short Low (175-4)"
        ::= { genT 79 }

    highEngOilTempWarn OBJECT-TYPE
        SYNTAX              INTEGER
        ACCESS              read-only
        STATUS              mandatory
        DESCRIPTION         "High Eng Oil Temp Warn (175-15)"
        ::= { genT 80 }

    lowEngOilTempWarn OBJECT-TYPE
        SYNTAX              INTEGER
        ACCESS              read-only
        STATUS              mandatory
        DESCRIPTION         "Low Eng Oil Temp Warn (175-17)"
        ::= { genT 81 }

    engOverspeedSD OBJECT-TYPE
        SYNTAX              INTEGER
        ACCESS              read-only
        STATUS              mandatory
        DESCRIPTION         "Eng Overspd S/D (190-0)"
        ::= { genT 82 }

    engUnderSpeedSD OBJECT-TYPE
        SYNTAX              INTEGER
        ACCESS              read-only
        STATUS              mandatory
        DESCRIPTION         "Eng UnderSpd S/D (190-1)"
        ::= { genT 83 }

    engSpdSnsErr-NA OBJECT-TYPE
        SYNTAX              INTEGER
        ACCESS              read-only
        STATUS              mandatory
        DESCRIPTION         "Eng Spd Sns Erratic or Not There (190-2)"
        ::= { genT 84 }

    engSpdSnsOpen OBJECT-TYPE
        SYNTAX              INTEGER
        ACCESS              read-only
        STATUS              mandatory
        DESCRIPTION         "Eng Speed Sns Open (190-5)"
        ::= { genT 85 }

    engUnderSpdWarn OBJECT-TYPE
        SYNTAX              INTEGER
        ACCESS              read-only
        STATUS              mandatory
        DESCRIPTION         "Engi Under Spd Warn (190-17)"
        ::= { genT 86 }

    sCADADataLinkFault OBJECT-TYPE
        SYNTAX              INTEGER
        ACCESS              read-only
        STATUS              mandatory
        DESCRIPTION         "SCADA Data Link Fault (625-11)"
        ::= { genT 87 }

    primaryDataLinkFault OBJECT-TYPE
        SYNTAX              INTEGER
        ACCESS              read-only
        STATUS              mandatory
        DESCRIPTION         "Primary Data Link Fault (639-11)"
        ::= { genT 88 }

    customEvent-1HighSD OBJECT-TYPE
        SYNTAX              INTEGER
        ACCESS              read-only
        STATUS              mandatory
        DESCRIPTION         "Custom Event #1 High S/D (701-0)"
        ::= { genT 89 }

    customEvent-1LowSD OBJECT-TYPE
        SYNTAX              INTEGER
        ACCESS              read-only
        STATUS              mandatory
        DESCRIPTION         "Custom Event #1 Low SD (701-1)"
        ::= { genT 90 }

    customEvent-1HighWarn OBJECT-TYPE
        SYNTAX              INTEGER
        ACCESS              read-only
        STATUS              mandatory
        DESCRIPTION         "Custom Event #1 High Warn (701-15)"
        ::= { genT 91 }

    customEvent-1LowWarn OBJECT-TYPE
        SYNTAX              INTEGER
        ACCESS              read-only
        STATUS              mandatory
        DESCRIPTION         "Custom Event #1 Low Warn (701-17)"
        ::= { genT 92 }

    customEvent-1Status OBJECT-TYPE
        SYNTAX              INTEGER
        ACCESS              read-only
        STATUS              mandatory
        DESCRIPTION         "Custom Event #1 Status Active (701-31)"
        ::= { genT 93 }

    customEvent-2HighSD OBJECT-TYPE
        SYNTAX              INTEGER
        ACCESS              read-only
        STATUS              mandatory
        DESCRIPTION         "Custom Event #2 High SD (702-0)"
        ::= { genT 94 }

    customEvent-2LowSD OBJECT-TYPE
        SYNTAX              INTEGER
        ACCESS              read-only
        STATUS              mandatory
        DESCRIPTION         "Custom Event #2 Low SD (702-1)"
        ::= { genT 95 }

    customEvent-2HighWarn OBJECT-TYPE
        SYNTAX              INTEGER
        ACCESS              read-only
        STATUS              mandatory
        DESCRIPTION         "Custom Event #2 High Warn (702-15)"
        ::= { genT 96 }

    customEvent-2LowWarn OBJECT-TYPE
        SYNTAX              INTEGER
        ACCESS              read-only
        STATUS              mandatory
        DESCRIPTION         "Custom Event #2 Low Warn (702-17)"
        ::= { genT 97 }

    customEvent-2Status OBJECT-TYPE
        SYNTAX              INTEGER
        ACCESS              read-only
        STATUS              mandatory
        DESCRIPTION         "Custom Event #2 Status Active (702-31)"
        ::= { genT 98 }

    customEvent-3HighSD OBJECT-TYPE
        SYNTAX              INTEGER
        ACCESS              read-only
        STATUS              mandatory
        DESCRIPTION         "Custom Event #3 High SD (703-0)"
        ::= { genT 99 }

    customEvent-3LowSD OBJECT-TYPE
        SYNTAX              INTEGER
        ACCESS              read-only
        STATUS              mandatory
        DESCRIPTION         "Custom Event #3 Low SD (703-1)"
        ::= { genT 100 }

    customEvent-3HighWarn OBJECT-TYPE
        SYNTAX              INTEGER
        ACCESS              read-only
        STATUS              mandatory
        DESCRIPTION         "Custom Event #3 High Warn (703-15)"
        ::= { genT 101 }

    customEvent-3LowWarn OBJECT-TYPE
        SYNTAX              INTEGER
        ACCESS              read-only
        STATUS              mandatory
        DESCRIPTION         "Custom Event #3 Low Warn (703-17)"
        ::= { genT 102 }

    customEvent-3Status OBJECT-TYPE
        SYNTAX              INTEGER
        ACCESS              read-only
        STATUS              mandatory
        DESCRIPTION         "Custom Event #4 Status Active (704-31)"
        ::= { genT 103 }

    customEvent-4HighSD OBJECT-TYPE
        SYNTAX              INTEGER
        ACCESS              read-only
        STATUS              mandatory
        DESCRIPTION         "Custom Event #4 High SD (704-0)"
        ::= { genT 104 }

    customEvent-4LowSD OBJECT-TYPE
        SYNTAX              INTEGER
        ACCESS              read-only
        STATUS              mandatory
        DESCRIPTION         "Custom Event #4 Low SD (704-1)"
        ::= { genT 105 }

    customEvent-4HighWarn OBJECT-TYPE
        SYNTAX              INTEGER
        ACCESS              read-only
        STATUS              mandatory
        DESCRIPTION         "Custom Event #4 High Warn (704-15)"
        ::= { genT 106 }

    customEvent-4LowWarn OBJECT-TYPE
        SYNTAX              INTEGER
        ACCESS              read-only
        STATUS              mandatory
        DESCRIPTION         "Custom Event #4 Low Warn (704-17)"
        ::= { genT 107 }

    customEvent-4Status OBJECT-TYPE
        SYNTAX              INTEGER
        ACCESS              read-only
        STATUS              mandatory
        DESCRIPTION         "Custom Event #4 Status Active (704-31)"
        ::= { genT 108 }

    customEvent-5HighSD OBJECT-TYPE
        SYNTAX              INTEGER
        ACCESS              read-only
        STATUS              mandatory
        DESCRIPTION         "Custom Event #5 High SD (705-0)"
        ::= { genT 109 }

    customEvent-5LowSD OBJECT-TYPE
        SYNTAX              INTEGER
        ACCESS              read-only
        STATUS              mandatory
        DESCRIPTION         "Custom Event #5 Low SD (705-1)"
        ::= { genT 110 }

    customEvent-5HighWarn OBJECT-TYPE
        SYNTAX              INTEGER
        ACCESS              read-only
        STATUS              mandatory
        DESCRIPTION         "Custom Event #5 High Warn (705-15)"
        ::= { genT 111 }

    customEvent-5LowWarn OBJECT-TYPE
        SYNTAX              INTEGER
        ACCESS              read-only
        STATUS              mandatory
        DESCRIPTION         "Custom Event #5 Low Warn (705-17)"
        ::= { genT 112 }

    customEvent-5Status OBJECT-TYPE
        SYNTAX              INTEGER
        ACCESS              read-only
        STATUS              mandatory
        DESCRIPTION         "Custom Event #5 Status Active (705-31)"
        ::= { genT 113 }

    customEvent-6HighSD OBJECT-TYPE
        SYNTAX              INTEGER
        ACCESS              read-only
        STATUS              mandatory
        DESCRIPTION         "Custom Event #6 High SD (706-0)"
        ::= { genT 114 }

    customEvent-6LowSD OBJECT-TYPE
        SYNTAX              INTEGER
        ACCESS              read-only
        STATUS              mandatory
        DESCRIPTION         "Custom Event #6 Low SD (706-1)"
        ::= { genT 115 }

    customEvent-6HighWarn OBJECT-TYPE
        SYNTAX              INTEGER
        ACCESS              read-only
        STATUS              mandatory
        DESCRIPTION         "Custom Event #6 High Warn (706-15)"
        ::= { genT 116 }

    customEvent-6LowWarn OBJECT-TYPE
        SYNTAX              INTEGER
        ACCESS              read-only
        STATUS              mandatory
        DESCRIPTION         "Custom Event #6 Low Warn (706-17)"
        ::= { genT 117 }

    customEvent-6Status OBJECT-TYPE
        SYNTAX              INTEGER
        ACCESS              read-only
        STATUS              mandatory
        DESCRIPTION         "Custom Event #6 Status Active (706-31)"
        ::= { genT 118 }

    digOut1ShortHigh OBJECT-TYPE
        SYNTAX              INTEGER
        ACCESS              read-only
        STATUS              mandatory
        DESCRIPTION         "Dig Out #1 Short High (924-3)"
        ::= { genT 119 }

    digOut2ShortHigh OBJECT-TYPE
        SYNTAX              INTEGER
        ACCESS              read-only
        STATUS              mandatory
        DESCRIPTION         "Dig Out #2 Short High (925-3)"
        ::= { genT 120 }

    emergencyStopSD OBJECT-TYPE
        SYNTAX              INTEGER
        ACCESS              read-only
        STATUS              mandatory
        DESCRIPTION         "Emer Stop S/D (970-31)"
        ::= { genT 121 }

    highGenBearingTemp1SD OBJECT-TYPE
        SYNTAX              INTEGER
        ACCESS              read-only
        STATUS              mandatory
        DESCRIPTION         "High Gen1 Bearing Temp (1122-0)"
        ::= { genT 122 }

    lowGenRearBearingTempSD OBJECT-TYPE
        SYNTAX              INTEGER
        ACCESS              read-only
        STATUS              mandatory
        DESCRIPTION         "Low Gen Rear Bearing Temp S/D (1122-1)"
        ::= { genT 123 }

    rGenBearTmpSnsShrtHigh OBJECT-TYPE
        SYNTAX              INTEGER
        ACCESS              read-only
        STATUS              mandatory
        DESCRIPTION         "Gen Rear Bear Temp Sns Short High (1122-3)"
        ::= { genT 124 }

    rGenBearTmpSnsShrtLow OBJECT-TYPE
        SYNTAX              INTEGER
        ACCESS              read-only
        STATUS              mandatory
        DESCRIPTION         "Gen Rear Bear Temp Sns Short Low (1122-4)"
        ::= { genT 125 }

    highRearGenBearTempWarn OBJECT-TYPE
        SYNTAX              INTEGER
        ACCESS              read-only
        STATUS              mandatory
        DESCRIPTION         "High Rear Gen Bear Temp Warn (1122-15)"
        ::= { genT 126 }

    lowRearGenBearTempWarn OBJECT-TYPE
        SYNTAX              INTEGER
        ACCESS              read-only
        STATUS              mandatory
        DESCRIPTION         "Low Rear Gen Bear Temp Warn (1122-17)"
        ::= { genT 127 }

    accDataLinkFault OBJECT-TYPE
        SYNTAX              INTEGER
        ACCESS              read-only
        STATUS              mandatory
        DESCRIPTION         "Acc Data Link Fault (1231-11)"
        ::= { genT 128 }

    fuelTankLeakRuptureBasin OBJECT-TYPE
        SYNTAX              INTEGER
        ACCESS              read-only
        STATUS              mandatory
        DESCRIPTION         "Fuel Tank Leak-Ruptured Basin (1239-31)"
        ::= { genT 129 }

    engiFailToStartSD OBJECT-TYPE
        SYNTAX              INTEGER
        ACCESS              read-only
        STATUS              mandatory
        DESCRIPTION         "Eng Fail to Start S/D (1664-31)"
        ::= { genT 130 }

    highRightExhaustTempSD OBJECT-TYPE
        SYNTAX              INTEGER
        ACCESS              read-only
        STATUS              mandatory
        DESCRIPTION         "High Right ET S/D (2433-0)"
        ::= { genT 131 }

    lowExhaustTempSD OBJECT-TYPE
        SYNTAX              INTEGER
        ACCESS              read-only
        STATUS              mandatory
        DESCRIPTION         "Low Right ET S/D (2433-1)"
        ::= { genT 132 }

    rightETSnsShortHigh OBJECT-TYPE
        SYNTAX              INTEGER
        ACCESS              read-only
        STATUS              mandatory
        DESCRIPTION         "Right ET Sns Short High (2433-3)"
        ::= { genT 133 }

    rightETSnsShortLow OBJECT-TYPE
        SYNTAX              INTEGER
        ACCESS              read-only
        STATUS              mandatory
        DESCRIPTION         "Right ET Sns Short Low (2433-4)"
        ::= { genT 134 }

    highRightETWarning OBJECT-TYPE
        SYNTAX              INTEGER
        ACCESS              read-only
        STATUS              mandatory
        DESCRIPTION         "High Right ET Warn (2433-15)"
        ::= { genT 135 }

    lowRightETWarning OBJECT-TYPE
        SYNTAX              INTEGER
        ACCESS              read-only
        STATUS              mandatory
        DESCRIPTION         "Low Right ET Warn (2433-17)"
        ::= { genT 136 }

    highLeftETShutdown OBJECT-TYPE
        SYNTAX              INTEGER
        ACCESS              read-only
        STATUS              mandatory
        DESCRIPTION         "High Left ET Shutdown (2434-0)"
        ::= { genT 137 }

    lowLeftETShutdown OBJECT-TYPE
        SYNTAX              INTEGER
        ACCESS              read-only
        STATUS              mandatory
        DESCRIPTION         "Low Left ET Shutdown (2434-1)"
        ::= { genT 138 }

    leftETSnsShortHigh OBJECT-TYPE
        SYNTAX              INTEGER
        ACCESS              read-only
        STATUS              mandatory
        DESCRIPTION         "Left Exh Temp Sns Short High (2434-3)"
        ::= { genT 139 }

    leftETSnsShortLow OBJECT-TYPE
        SYNTAX              INTEGER
        ACCESS              read-only
        STATUS              mandatory
        DESCRIPTION         "Left Exh Temp Sns Short Low (2434-4)"
        ::= { genT 140 }

    highLeftEngTempWarn OBJECT-TYPE
        SYNTAX              INTEGER
        ACCESS              read-only
        STATUS              mandatory
        DESCRIPTION         "High Left ET S/D (2434-15)"
        ::= { genT 141 }

    lowLeftEngTempWarn OBJECT-TYPE
        SYNTAX              INTEGER
        ACCESS              read-only
        STATUS              mandatory
        DESCRIPTION         "Low Left ET S/D (2434-17)"
        ::= { genT 142 }

    genOverFreqSD OBJECT-TYPE
        SYNTAX              INTEGER
        ACCESS              read-only
        STATUS              mandatory
        DESCRIPTION         "Gen Over Freq S/D (2436-0)"
        ::= { genT 143 }

    genUnderFreqSD OBJECT-TYPE
        SYNTAX              INTEGER
        ACCESS              read-only
        STATUS              mandatory
        DESCRIPTION         "Gen Under Freq S/D (2436-1)"
        ::= { genT 144 }

    engGenFreqMismatch OBJECT-TYPE
        SYNTAX              INTEGER
        ACCESS              read-only
        STATUS              mandatory
        DESCRIPTION         "Eng/Gen Freq Mismatch (2436-2)"
        ::= { genT 145 }

    genOutputSnsFailure OBJECT-TYPE
        SYNTAX              INTEGER
        ACCESS              read-only
        STATUS              mandatory
        DESCRIPTION         "Gen Sensing Sys Failure (2436-12)"
        ::= { genT 146 }

    genOverFreqWarn OBJECT-TYPE
        SYNTAX              INTEGER
        ACCESS              read-only
        STATUS              mandatory
        DESCRIPTION         "Gen Over Freq Warn (2436-15)"
        ::= { genT 147 }

    genUnderFreqWarn OBJECT-TYPE
        SYNTAX              INTEGER
        ACCESS              read-only
        STATUS              mandatory
        DESCRIPTION         "Gen Under Freq Warn (2436-17)"
        ::= { genT 148 }

    genOverVoltageSD OBJECT-TYPE
        SYNTAX              INTEGER
        ACCESS              read-only
        STATUS              mandatory
        DESCRIPTION         "Gen Over Volt S/D (2440-0)"
        ::= { genT 149 }

    genUnderVoltageSD OBJECT-TYPE
        SYNTAX              INTEGER
        ACCESS              read-only
        STATUS              mandatory
        DESCRIPTION         "Gen Under Volt S/D (2440-1)"
        ::= { genT 150 }

    genOverVoltageWarn OBJECT-TYPE
        SYNTAX              INTEGER
        ACCESS              read-only
        STATUS              mandatory
        DESCRIPTION         "Gen Over Volt Warn (2440-15)"
        ::= { genT 151 }

    genUnderVoltageWarn OBJECT-TYPE
        SYNTAX              INTEGER
        ACCESS              read-only
        STATUS              mandatory
        DESCRIPTION         "Gen Under Volt Warn (2440-17)"
        ::= { genT 152 }

    genOverCurrentSD OBJECT-TYPE
        SYNTAX              INTEGER
        ACCESS              read-only
        STATUS              mandatory
        DESCRIPTION         "Genover Current Shutdown (2448-0)"
        ::= { genT 153 }

    genOverCurrentWarn OBJECT-TYPE
        SYNTAX              INTEGER
        ACCESS              read-only
        STATUS              mandatory
        DESCRIPTION         "Gen Over Current Warning (2448-15)"
        ::= { genT 154 }

    genRevPowerSD OBJECT-TYPE
        SYNTAX              INTEGER
        ACCESS              read-only
        STATUS              mandatory
        DESCRIPTION         "Gen Reverse Power S/D (2452-1)"
        ::= { genT 155 }

    genRevPowerWarn OBJECT-TYPE
        SYNTAX              INTEGER
        ACCESS              read-only
        STATUS              mandatory
        DESCRIPTION         "Gen Reverse Power Warn (2452-17)"
        ::= { genT 156 }

    servMaintIntervalWarn OBJECT-TYPE
        SYNTAX              INTEGER
        ACCESS              read-only
        STATUS              mandatory
        DESCRIPTION         "Service Maint Inter Warn (2648-31)"
        ::= { genT 157 }

    airDamperClosed OBJECT-TYPE
        SYNTAX              INTEGER
        ACCESS              read-only
        STATUS              mandatory
        DESCRIPTION         "Air Damp Closed (4000-31)"
        ::= { genT 158 }

    aTSinNormPosition OBJECT-TYPE
        SYNTAX              INTEGER
        ACCESS              read-only
        STATUS              mandatory
        DESCRIPTION         "ATS in Norm Position (4001-31)"
        ::= { genT 159 }

    aTSinEmergencyPosition OBJECT-TYPE
        SYNTAX              INTEGER
        ACCESS              read-only
        STATUS              mandatory
        DESCRIPTION         "ATS in Emergency Position (4002-31)"
        ::= { genT 160 }

    battChargerFailure OBJECT-TYPE
        SYNTAX              INTEGER
        ACCESS              read-only
        STATUS              mandatory
        DESCRIPTION         "Batt Charger Failure (4003-31)"
        ::= { genT 161 }

    genCircBreakClosed OBJECT-TYPE
        SYNTAX              INTEGER
        ACCESS              read-only
        STATUS              mandatory
        DESCRIPTION         "Gen Circ Break Closed (4004-31)"
        ::= { genT 162 }

    utilityCircBreakClosed OBJECT-TYPE
        SYNTAX              INTEGER
        ACCESS              read-only
        STATUS              mandatory
        DESCRIPTION         "Utility Circ Break Closed (4005-31)"
        ::= { genT 163 }

    engineInCooldown OBJECT-TYPE
        SYNTAX              INTEGER
        ACCESS              read-only
        STATUS              mandatory
        DESCRIPTION         "Eng In Cooldown (4006-31)"
        ::= { genT 164 }

    genCntrlNotInAutoWarn OBJECT-TYPE
        SYNTAX              INTEGER
        ACCESS              read-only
        STATUS              mandatory
        DESCRIPTION         "Gen Cntrl Not In Auto Warn (4007-31)"
        ::= { genT 165 }

    unexpectedEngShutdown OBJECT-TYPE
        SYNTAX              INTEGER
        ACCESS              read-only
        STATUS              mandatory
        DESCRIPTION         "Unexpected Eng S/D (4008-31)"
        ::= { genT 166 }

    lossOfUtility OBJECT-TYPE
        SYNTAX              INTEGER
        ACCESS              read-only
        STATUS              mandatory
        DESCRIPTION         "Loss of Utility (4017-31)"
        ::= { genT 167 }

    noShutdownRequested OBJECT-TYPE
        SYNTAX              INTEGER
        ACCESS              read-only
        STATUS              mandatory
        DESCRIPTION         "No Shutdown Requested"
        ::= { genT 168 }

    shutdownRequested OBJECT-TYPE
        SYNTAX              INTEGER
        ACCESS              read-only
        STATUS              mandatory
        DESCRIPTION         "Shutdown Requested"
        ::= { genT 169 }

    engineStopped OBJECT-TYPE
        SYNTAX              INTEGER
        ACCESS              read-only
        STATUS              mandatory
        DESCRIPTION         "Engine Stopped"
        ::= { genT 170 }

    enginePreStart OBJECT-TYPE
        SYNTAX              INTEGER
        ACCESS              read-only
        STATUS              mandatory
        DESCRIPTION         "Engine Pre-Start"
        ::= { genT 171 }

    engineStarting OBJECT-TYPE
        SYNTAX              INTEGER
        ACCESS              read-only
        STATUS              mandatory
        DESCRIPTION         "Engine Starting"
        ::= { genT 172 }

    engineWarmUp OBJECT-TYPE
        SYNTAX              INTEGER
        ACCESS              read-only
        STATUS              mandatory
        DESCRIPTION         "Engine Warming Up"
        ::= { genT 173 }

    engineRunning OBJECT-TYPE
        SYNTAX              INTEGER
        ACCESS              read-only
        STATUS              mandatory
        DESCRIPTION         "Engine Running"
        ::= { genT 174 }

    engineCoolDown OBJECT-TYPE
        SYNTAX              INTEGER
        ACCESS              read-only
        STATUS              mandatory
        DESCRIPTION         "Engine Cooling Down"
        ::= { genT 175 }

    engineStopping OBJECT-TYPE
        SYNTAX              INTEGER
        ACCESS              read-only
        STATUS              mandatory
        DESCRIPTION         "Engine Stopping"
        ::= { genT 176 }

    enginePostRun OBJECT-TYPE
        SYNTAX              INTEGER
        ACCESS              read-only
        STATUS              mandatory
        DESCRIPTION         "Engine Post-Run"
        ::= { genT 177 }

    isEMCPonline OBJECT-TYPE
        SYNTAX              INTEGER
        ACCESS              read-only
        STATUS              mandatory
        DESCRIPTION         "J1939 Comm Status - Is EMCP3 Online"
        ::= { genT 178 }

    isEngineOnline OBJECT-TYPE
        SYNTAX              INTEGER
        ACCESS              read-only
        STATUS              mandatory
        DESCRIPTION         "J1939 Comm Status - Is Engine Online"
        ::= { genT 179 }

    globalFault OBJECT-TYPE
        SYNTAX              INTEGER
        ACCESS              read-only
        STATUS              mandatory
        DESCRIPTION         "Global Fault Code Status Indicator"
        ::= { genT 180 }

    engineFault OBJECT-TYPE
        SYNTAX              INTEGER
        ACCESS              read-only
        STATUS              mandatory
        DESCRIPTION         "Global Engine Fault Code Indicator"
        ::= { genT 181 }

    eMCPFault OBJECT-TYPE
        SYNTAX              INTEGER
        ACCESS              read-only
        STATUS              mandatory
        DESCRIPTION         "Global EMCP Fault Code Indicator"
        ::= { genT 182 }

    engineShutdown OBJECT-TYPE
        SYNTAX              INTEGER
        ACCESS              read-only
        STATUS              mandatory
        DESCRIPTION         "Engine Shutdown (Red Stop Lamp)"
        ::= { genT 183 }

    globalWarning OBJECT-TYPE
        SYNTAX              INTEGER
        ACCESS              read-only
        STATUS              mandatory
        DESCRIPTION         "GlobalWarning (Amber Warning Lamp)"
        ::= { genT 184 }

    monicoH100 OBJECT IDENTIFIER ::= { monicoGateway 2 }

    gsD OBJECT IDENTIFIER ::= { monicoH100 1 }

    gsT OBJECT IDENTIFIER ::= { monicoH100 2 }

    monicoCommon OBJECT IDENTIFIER ::= { monico 2 }

    monicoRegids OBJECT IDENTIFIER ::= { monico 3 }

    monicoExperimental OBJECT IDENTIFIER ::= { monico 4 }


    gsTraps TRAP-TYPE
        ENTERPRISE          monico
        DESCRIPTION         "gs Traps"
        ::= 1

    genTraps TRAP-TYPE
        ENTERPRISE          monico
        VARIABLES           {
                                extHighFuelLevelShutdown,
                                extLowFuelLevelShutdown,
                                extFuelLvlSensShortHigh,
                                extFuelLevelSnesShortLow,
                                extHighFuelLvlWarning,
                                extLowFuelLvlWarning,
                                highStartPressShutdown,
                                lowStartPressShutdown,
                                startAirPresSensShrtHigh,
                                startAirPresSensShrtLow,
                                highStartAirPressWarning,
                                lowStartAirPressWarning,
                                highFuelFltrDiffShutdown,
                                lowFuelFltrDiffShutdown,
                                fFDiffPresSnsShortHigh,
                                fFDiffPresSnsShortLow,
                                highFuelFltrDiffPresWrn,
                                lowFuelFltrDiffPresWrn,
                                highFuelLevelShutdown,
                                lowFuelLevelShutdown,
                                fuelLvlSnsShortHigh,
                                fuelLvlSnsShortLow,
                                highFuelWarning,
                                lowFuelWarning,
                                highEngineOilLvlSD,
                                lowEngineOilLvlSD,
                                engOilSnsrShortHigh,
                                engOilSnsrShortLow,
                                highEngOilLvlWarning,
                                lowEngOilLvlWarning,
                                highOilFltDifPresSD,
                                lowOilFltDifPresSD,
                                oilFltrDifPresShortHigh,
                                oilFltrDifPresShortLow,
                                highOilFltDifPresWarn,
                                lowOilFltDifPresWarn,
                                lowEngineOilPresSD,
                                lowEngineOilPresWarn,
                                highAirFltrDifPresSD,
                                lowAirFltrDifPresSD,
                                airFltrDifPresShortHigh,
                                airFltrDifPresShortLow,
                                highAirFltrDifPResWarn,
                                lowAirFltrDifPResWarn,
                                highEngCoolTempSD,
                                highEngCoolTempWarn,
                                lowEngCoolTempWarn,
                                highEngCoolLvlSD,
                                lowEngCoolLvlSD,
                                engCoolLvlSnsShrtHi,
                                engCoolLvlSnsShrtLow,
                                highEngCoolLvlWarn,
                                lowEngCoolLvlWarn,
                                highFireExtPresSD,
                                lowFireExtPresSD,
                                fireExtPresSnsShrtHigh,
                                fireExtPresSnsShrtLow,
                                highFireExtPresWarn,
                                lowFireExtPresWarn,
                                lowBatChrgSysVoltWarn,
                                highBattVoltageSD,
                                highBattVoltageWarn,
                                lowBattVoltageWarn,
                                highAmbAirTempSD,
                                lowAmbAirTempSD,
                                ambAirSnsShortHigh,
                                ambAirSnsShortLow,
                                highAmbAirTempWarn,
                                lowAmbAirTempWarn,
                                highExhTempSD,
                                lowExhTempSD,
                                exhTempSnsShrtHigh,
                                exhTempSnsShrtLow,
                                highExhTempWarn,
                                lowExhTempWarn,
                                highEngOilTempSD,
                                lowEngOilTempSD,
                                engOilTempSnsShrtHigh,
                                engOilTempSnsShrtLow,
                                highEngOilTempWarn,
                                lowEngOilTempWarn,
                                engOverspeedSD,
                                engUnderSpeedSD,
                                engSpdSnsErr-NA,
                                engSpdSnsOpen,
                                engUnderSpdWarn,
                                sCADADataLinkFault,
                                primaryDataLinkFault,
                                customEvent-1HighSD,
                                customEvent-1LowSD,
                                customEvent-1HighWarn,
                                customEvent-1LowWarn,
                                customEvent-1Status,
                                customEvent-2HighSD,
                                customEvent-2LowSD,
                                customEvent-2HighWarn,
                                customEvent-2LowWarn,
                                customEvent-2Status,
                                customEvent-3HighSD,
                                customEvent-3LowSD,
                                customEvent-3HighWarn,
                                customEvent-3LowWarn,
                                customEvent-3Status,
                                customEvent-4HighSD,
                                customEvent-4LowSD,
                                customEvent-4HighWarn,
                                customEvent-4LowWarn,
                                customEvent-4Status,
                                customEvent-5HighSD,
                                customEvent-5LowSD,
                                customEvent-5HighWarn,
                                customEvent-5LowWarn,
                                customEvent-5Status,
                                customEvent-6HighSD,
                                customEvent-6LowSD,
                                customEvent-6HighWarn,
                                customEvent-6LowWarn,
                                customEvent-6Status,
                                digOut1ShortHigh,
                                digOut2ShortHigh,
                                emergencyStopSD,
                                highGenBearingTemp1SD,
                                lowGenRearBearingTempSD,
                                rGenBearTmpSnsShrtHigh,
                                rGenBearTmpSnsShrtLow,
                                highRearGenBearTempWarn,
                                lowRearGenBearTempWarn,
                                accDataLinkFault,
                                fuelTankLeakRuptureBasin,
                                engiFailToStartSD,
                                highRightExhaustTempSD,
                                lowExhaustTempSD,
                                rightETSnsShortHigh,
                                rightETSnsShortLow,
                                highRightETWarning,
                                lowRightETWarning,
                                highLeftETShutdown,
                                lowLeftETShutdown,
                                leftETSnsShortHigh,
                                leftETSnsShortLow,
                                highLeftEngTempWarn,
                                lowLeftEngTempWarn,
                                genOverFreqSD,
                                genUnderFreqSD,
                                engGenFreqMismatch,
                                genOutputSnsFailure,
                                genOverFreqWarn,
                                genUnderFreqWarn,
                                genOverVoltageSD,
                                genUnderVoltageSD,
                                genOverVoltageWarn,
                                genUnderVoltageWarn,
                                genOverCurrentSD,
                                genOverCurrentWarn,
                                genRevPowerSD,
                                genRevPowerWarn,
                                servMaintIntervalWarn,
                                airDamperClosed,
                                aTSinNormPosition,
                                aTSinEmergencyPosition,
                                battChargerFailure,
                                genCircBreakClosed,
                                utilityCircBreakClosed,
                                engineInCooldown,
                                genCntrlNotInAutoWarn,
                                unexpectedEngShutdown,
                                lossOfUtility,
                                noShutdownRequested,
                                shutdownRequested,
                                engineStopped,
                                enginePreStart,
                                engineStarting,
                                engineWarmUp,
                                engineRunning,
                                engineCoolDown,
                                engineStopping,
                                enginePostRun,
                                isEMCPonline,
                                isEngineOnline,
                                globalFault,
                                engineFault,
                                eMCPFault,
                                engineShutdown,
                                globalWarning
                            }
        DESCRIPTION         "Please replace this text with your description."
        ::= 2


END
