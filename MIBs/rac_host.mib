DELL-RAC-MIB DEFINITIONS ::= BEGIN
     
  IMPORTS
     enterprises
        FROM SNMPv2-SMI
     OBJECT-TYPE
        FROM SNMPv2-SMI
     TRAP-TYPE
        FROM RFC-1215;
  

    -- text convention ------------------------------------------------------------------------     

         DisplayString ::=
             OCTET STRING
          -- This data type is used to model textual information taken
          -- from the NVT ASCII character set.  By convention, objects
          -- with this syntax are declared as having
          --
          --      SIZE (0..1023)

         DellString    ::= DisplayString (SIZE (0..1023))
     
         DellRacType   ::= INTEGER {
           other(1),               -- the DRAC type is not one of the following
           unknown(2),             -- the DRAC type is unknown
           DracIII(3),             -- Drac III
           ERA(4),                 -- ERA
           DRAC4(5),               -- Drac 4
           DRAC5(6),               -- Drac 5
           DRAC5MC(7),             -- Drac 5/MC
           CMC(8)                  -- CMC
         }
         
         DellStatus    ::= INTEGER {
             other(1),               -- the status of the object is not one of the following:
             unknown(2),             -- the status of the object is unknown
                                     --  (not known or monitored)
             ok(3),                  -- the status of the object is ok
             nonCritical(4),         -- the status of the object is warning, non-critical
             critical(5),            -- the status of the object is critical (failure)
             nonRecoverable(6)       -- the status of the object is non-recoverable (dead)
         }

     -- MIB Objects ----------------------------------------------------------------------------

        dell                          OBJECT IDENTIFIER ::= { enterprises    674   }
        server3                       OBJECT IDENTIFIER ::= { dell           10892 }
        drsOutofBandGroup             OBJECT IDENTIFIER ::= { server3        2     }
        drsInformationGroup           OBJECT IDENTIFIER ::= { drsOutofBandGroup     1 }
        drsProductInfoGroup           OBJECT IDENTIFIER ::= { drsInformationGroup   1 }
        drsFirmwareGroup              OBJECT IDENTIFIER ::= { drsInformationGroup   2 }
        drsStatusGroup                OBJECT IDENTIFIER ::= { drsOutofBandGroup     2 }
        drsChassisStatusGroup         OBJECT IDENTIFIER ::= { drsOutofBandGroup     3 }
        drsStatusNowGroup             OBJECT IDENTIFIER ::= { drsChassisStatusGroup 1 }
        drsStatusPrevGroup            OBJECT IDENTIFIER ::= { drsChassisStatusGroup 2 }
        drsStatusChangeGroup          OBJECT IDENTIFIER ::= { drsChassisStatusGroup 3 }
        drsCMCAlertGroup              OBJECT IDENTIFIER ::= { drsOutofBandGroup    20 }
        drsChassisAlertVariables      OBJECT IDENTIFIER ::= { drsCMCAlertGroup     10 }
        drsChassisAlertGroup          OBJECT IDENTIFIER ::= { drsCMCAlertGroup   2000 }
        drsAlertGroup                 OBJECT IDENTIFIER ::= { drsOutofBandGroup  5000 }
        drsAlertVariables             OBJECT IDENTIFIER ::= { drsAlertGroup        10 }
        
     -- Variables and Traps ------------------------------------------------------------------------

            drsProductName      OBJECT-TYPE
                SYNTAX          DellString
                ACCESS          read-only
                STATUS          mandatory
                DESCRIPTION     "0001.0001.0001 This attribute defines the product name of a 
                                chassis management controller or remote access card. " 
               ::= { drsProductInfoGroup 1 }

            drsProductShortName OBJECT-TYPE
                SYNTAX          DellString
                ACCESS          read-only
                STATUS          mandatory
                DESCRIPTION     "0001.0001.0002 This attribute defines the short product name of a 
                                chassis management controller or remote access card. " 
               ::= { drsProductInfoGroup 2 }

            drsProductDescription OBJECT-TYPE
                SYNTAX          DellString
                ACCESS          read-only
                STATUS          mandatory
                DESCRIPTION     "0001.0001.0003 This attribute defines the product description of a 
                                chassis management controller or remote access card. " 
               ::= { drsProductInfoGroup 3 }

            drsProductManufacturer OBJECT-TYPE
                SYNTAX          DellString
                ACCESS          read-only
                STATUS          mandatory
                DESCRIPTION     "0001.0001.0004 This attribute defines the product manufacturer of a 
                                chassis management controller or remote access card. " 
               ::= { drsProductInfoGroup 4 }

            drsProductVersion OBJECT-TYPE
                SYNTAX          DellString
                ACCESS          read-only
                STATUS          mandatory
                DESCRIPTION     "0001.0001.0005 This attribute defines the product version of a 
                                chassis management controller or remote access card. " 
               ::= { drsProductInfoGroup 5 }

            drsChassisServiceTag OBJECT-TYPE
                SYNTAX          DellString
                ACCESS          read-only
                STATUS          mandatory
                DESCRIPTION     "0001.0001.0007 This attribute defines the Service Tag of the chassis. " 
               ::= { drsProductInfoGroup 6 }

            drsProductURL       OBJECT-TYPE
                SYNTAX          DellString 
                ACCESS          read-only
                STATUS          mandatory
                DESCRIPTION     "0001.0001.0006 This attribute defines the out-of-band UI URL of a 
                                chassis management controller or remote access card. "
                ::= { drsProductInfoGroup 7 }
                        
            drsProductChassisAssetTag  OBJECT-TYPE
                SYNTAX          DellString 
                ACCESS          read-only
                STATUS          mandatory
                DESCRIPTION     "0001.0001.0008 This attribute defines the Asset Tag of the chassis. "
                ::= { drsProductInfoGroup 8 }

            drsProductChassisLocation  OBJECT-TYPE
                SYNTAX          DellString 
                ACCESS          read-only
                STATUS          mandatory
                DESCRIPTION     "0001.0001.0009 This attribute defines the location of the chassis. "
                ::= { drsProductInfoGroup 9 }

            drsProductChassisName  OBJECT-TYPE
                SYNTAX          DellString 
                ACCESS          read-only
                STATUS          mandatory
                DESCRIPTION     "0001.0001.0010 This attribute defines the name of the chassis. "
                ::= { drsProductInfoGroup 10 }

            drsSystemServiceTag  OBJECT-TYPE
                SYNTAX          DellString 
                ACCESS          read-only
                STATUS          mandatory
                DESCRIPTION     "0001.0001.0011 This attribute defines the service tag of a system. "
                ::= { drsProductInfoGroup 11 }

            drsProductSystemAssetTag  OBJECT-TYPE
                SYNTAX          DellString 
                ACCESS          read-only
                STATUS          mandatory
                DESCRIPTION     "0001.0001.0012 This attribute defines the asset tag of a system. "
                ::= { drsProductInfoGroup 12 }

            drsProductSystemSlot OBJECT-TYPE
                SYNTAX          DellString 
                ACCESS          read-only
                STATUS          mandatory
                DESCRIPTION     "0001.0001.0013 This attribute defines the slot number of a system or CMC. "
               ::= { drsProductInfoGroup 13 }

            drsProductType  OBJECT-TYPE
                SYNTAX          DellRacType
                ACCESS          read-only
                STATUS          mandatory
                DESCRIPTION     "0001.0001.0014 This attribute defines the type of a 
                                chassis management controller or remote access card. "
               ::= { drsProductInfoGroup 14 }
               
            drsFirmwareVersion  OBJECT-TYPE
                SYNTAX          DellString
                ACCESS          read-only
                STATUS          mandatory
                DESCRIPTION     "0001.0002.0001 This attribute defines the firmware version of a 
                                chassis management controller or remote access card. " 
               ::= { drsFirmwareGroup 1 }

            drsGlobalSystemStatus OBJECT-TYPE
                SYNTAX          DellStatus
                ACCESS          read-only
                STATUS          mandatory
                DESCRIPTION     "0002.0001.0001 This attribute defines the overall chassis status
                                being monitored by the chassis management controller or remote access card." 
               ::= { drsStatusGroup 1 }

            drsGlobalCurrStatus OBJECT-TYPE
                SYNTAX          DellStatus
                ACCESS          read-only
                STATUS          mandatory
                DESCRIPTION     "0003.0001.0001 This attribute defines the overall chassis status
                                being monitored by the chassis management controller." 
               ::= { drsStatusNowGroup 1 }

            drsIOMCurrStatus  OBJECT-TYPE
                SYNTAX          DellStatus
                ACCESS          read-only
                STATUS          mandatory
                DESCRIPTION     "0003.0001.0002 This attribute defines the IOM subsystem status
                                being monitored by the chassis management controller." 
               ::= { drsStatusNowGroup 2 }

            drsKVMCurrStatus  OBJECT-TYPE
                SYNTAX          DellStatus
                ACCESS          read-only
                STATUS          mandatory
                DESCRIPTION     "0003.0001.0003 This attribute defines the iKVM subsystem health status
                                being monitored by the chassis management controller." 
               ::= { drsStatusNowGroup 3 }

            drsRedCurrStatus  OBJECT-TYPE
                SYNTAX          DellStatus
                ACCESS          read-only
                STATUS          mandatory
                DESCRIPTION     "0003.0001.0004 This attribute defines the Redundancy status
                                being monitored by the chassis management controller." 
               ::= { drsStatusNowGroup 4 }

            drsPowerCurrStatus OBJECT-TYPE
                SYNTAX          DellStatus
                ACCESS          read-only
                STATUS          mandatory
                DESCRIPTION     "0003.0001.0005 This attribute defines the Power subsystem health status
                                being monitored by the chassis management controller." 
               ::= { drsStatusNowGroup 5 }

            drsFanCurrStatus OBJECT-TYPE
                SYNTAX          DellStatus
                ACCESS          read-only
                STATUS          mandatory
                DESCRIPTION     "0003.0001.0006 This attribute defines the Fan subsystem health status
                                being monitored by the chassis management controller." 
               ::= { drsStatusNowGroup 6 }

            drsBladeCurrStatus OBJECT-TYPE
                SYNTAX          DellStatus
                ACCESS          read-only
                STATUS          mandatory
                DESCRIPTION     "0003.0001.0007 This attribute defines the Blade subsystem health status
                                being monitored by the chassis management controller." 
               ::= { drsStatusNowGroup 7 }

            drsTempCurrStatus OBJECT-TYPE
                SYNTAX          DellStatus
                ACCESS          read-only
                STATUS          mandatory
                DESCRIPTION     "0003.0001.0008 This attribute defines the Temp Sensor subsystem health status
                                being monitored by the chassis management controller." 
               ::= { drsStatusNowGroup 8 }

            drsCMCCurrStatus OBJECT-TYPE
                SYNTAX          DellStatus
                ACCESS          read-only
                STATUS          mandatory
                DESCRIPTION     "0003.0001.0009 This attribute defines the CMC health status
                                being monitored by the chassis management controller." 
               ::= { drsStatusNowGroup 9 }

            drsGlobalPrevStatus OBJECT-TYPE
                SYNTAX          DellStatus
                ACCESS          read-only
                STATUS          mandatory
                DESCRIPTION     "0003.0002.0001 This attribute defines the previous chassis status
                                recorded by the chassis management controller." 
               ::= { drsStatusPrevGroup 1 }
                
            drsIOMPrevStatus    OBJECT-TYPE
                SYNTAX          DellStatus
                ACCESS          read-only
                STATUS          mandatory
                DESCRIPTION     "0003.0002.0002 This attribute defines the previous IOM subsystem status
                                recorded by the chassis management controller." 
               ::= { drsStatusPrevGroup 2 }

            drsKVMPrevStatus    OBJECT-TYPE
                SYNTAX          DellStatus
                ACCESS          read-only
                STATUS          mandatory
                DESCRIPTION     "0003.0002.0003 This attribute defines the previous iKVM subsystem health status
                                recorded by the chassis management controller." 
               ::= { drsStatusPrevGroup 3 }

            drsRedPrevStatus    OBJECT-TYPE
                SYNTAX          DellStatus
                ACCESS          read-only
                STATUS          mandatory
                DESCRIPTION     "0003.0002.0004 This attribute defines the previous Redundancy status
                                recorded by the chassis management controller." 
               ::= { drsStatusPrevGroup 4 }

            drsPowerPrevStatus  OBJECT-TYPE
                SYNTAX          DellStatus
                ACCESS          read-only
                STATUS          mandatory
                DESCRIPTION     "0003.0002.0005 This attribute defines the previous Power subsystem health status
                                recorded by the chassis management controller." 
               ::= { drsStatusPrevGroup 5 }

            drsFanPrevStatus OBJECT-TYPE
                SYNTAX          DellStatus
                ACCESS          read-only
                STATUS          mandatory
                DESCRIPTION     "0003.0002.0006 This attribute defines the previous Fan health status
                                being monitored by the chassis management controller." 
               ::= { drsStatusPrevGroup 6 }

            drsBladePrevStatus  OBJECT-TYPE
                SYNTAX          DellStatus
                ACCESS          read-only
                STATUS          mandatory
                DESCRIPTION     "0003.0002.0007 This attribute defines the previous Blade subsystem health status
                                recorded by the chassis management controller." 
               ::= { drsStatusPrevGroup 7 }

            drsTempPrevStatus OBJECT-TYPE
                SYNTAX          DellStatus
                ACCESS          read-only
                STATUS          mandatory
                DESCRIPTION     "0003.0002.0008 This attribute defines the previous Temp Sensor health status
                                being monitored by the chassis management controller." 
               ::= { drsStatusPrevGroup 8 }

            drsCMCPrevStatus OBJECT-TYPE
                SYNTAX          DellStatus
                ACCESS          read-only
                STATUS          mandatory
                DESCRIPTION     "0003.0002.0009 This attribute defines the previous CMC health status
                                being monitored by the chassis management controller." 
               ::= { drsStatusPrevGroup 9 }

            drsGlobalChangeTime OBJECT-TYPE
                SYNTAX          TimeTicks
                ACCESS          read-only
                STATUS          mandatory
                DESCRIPTION     "0003.0003.0001 This attribute defines the timestamp of the most recent 
                                 global status change." 
               ::= { drsStatusChangeGroup 1 }

            drsIOMChangeTime    OBJECT-TYPE
                SYNTAX          TimeTicks
                ACCESS          read-only
                STATUS          mandatory
                DESCRIPTION     "0003.0003.0002 This attribute defines the timestamp of the most recent 
                                 IOM status change." 
               ::= { drsStatusChangeGroup 2 }

            drsKVMChangeTime    OBJECT-TYPE
                SYNTAX          TimeTicks
                ACCESS          read-only
                STATUS          mandatory
                DESCRIPTION     "0003.0003.0003 This attribute defines the timestamp of the most recent 
                                iKVM status change." 
               ::= { drsStatusChangeGroup 3 }

            drsRedChangeTime    OBJECT-TYPE
                SYNTAX          TimeTicks
                ACCESS          read-only
                STATUS          mandatory
                DESCRIPTION     "0003.0003.0004 This attribute defines the timestamp of the most recent 
                                Redundancy status change." 
               ::= { drsStatusChangeGroup 4 }

            drsPowerChangeTime  OBJECT-TYPE
                SYNTAX          TimeTicks
                ACCESS          read-only
                STATUS          mandatory
                DESCRIPTION     "0003.0003.0005 This attribute defines the timestamp of the most recent 
                                Power health status change." 
               ::= { drsStatusChangeGroup 5 }

            drsFanChangeTime OBJECT-TYPE
                SYNTAX          TimeTicks
                ACCESS          read-only
                STATUS          mandatory
                DESCRIPTION     "0003.0003.0006 This attribute defines the timestamp of the most recent 
                                Fan health status change." 
               ::= { drsStatusChangeGroup 6 }

            drsBladeChangeTime  OBJECT-TYPE
                SYNTAX          TimeTicks
                ACCESS          read-only
                STATUS          mandatory
                DESCRIPTION     "0003.0003.0007 This attribute defines the timestamp of the most recent 
                                Blade health status change." 
               ::= { drsStatusChangeGroup 7 }

            drsTempChangeTime OBJECT-TYPE
                SYNTAX          TimeTicks
                ACCESS          read-only
                STATUS          mandatory
                DESCRIPTION     "0003.0003.0008 This attribute defines the timestamp of the most recent 
                                Temp Sensor health status change." 
               ::= { drsStatusChangeGroup 8 }

            drsCMCChangeTime OBJECT-TYPE
                SYNTAX          TimeTicks
                ACCESS          read-only
                STATUS          mandatory
                DESCRIPTION     "0003.0003.0009 This attribute defines the timestamp of the most recent 
                                CMC health status change." 
               ::= { drsStatusChangeGroup 9 }

            drsCASubSystem      OBJECT-TYPE
                SYNTAX		  DellString
                ACCESS		  read-only
                STATUS		  mandatory
                DESCRIPTION     "0020.0010.0001 This attribute defines the Sub-System Name of the CMC Alert"
               ::= { drsChassisAlertVariables 1 }

            drsCASSCurrStatus   OBJECT-TYPE
                SYNTAX		  DellStatus
                ACCESS		  read-only
                STATUS		  mandatory
                DESCRIPTION     "0020.0010.0002 This attribute defines the Current Status of the Alerting 
                                 Sub-System"
               ::= { drsChassisAlertVariables 2 }

            drsCASSPrevStatus   OBJECT-TYPE
                SYNTAX		  DellStatus
                ACCESS		  read-only
                STATUS		  mandatory
                DESCRIPTION     "0020.0010.0003 This attribute defines the Previous Status of the Alerting 
                                 Sub-System"
               ::= { drsChassisAlertVariables 3 }

            drsCASSChangeTime   OBJECT-TYPE
                SYNTAX		  TimeTicks
                ACCESS		  read-only
                STATUS		  mandatory
                DESCRIPTION     "0020.0010.0004 This attribute defines the Timestamp of Most Recent Change of 
                                 the Alerting Sub-System"
               ::= { drsChassisAlertVariables 4 }

            drsCAMessage        OBJECT-TYPE
                SYNTAX		  DellString
                ACCESS		  read-only
                STATUS		  mandatory
                DESCRIPTION     "0020.0010.0005 This attribute defines the CSSD message of the CMC Alert"
               ::= { drsChassisAlertVariables 5 }

            alertCMCTestTrap  TRAP-TYPE
                ENTERPRISE 	  drsOutofBandGroup
                DESCRIPTION   "The CMC has generated a test trap"
                --#TYPE "CMC Test Trap"
								--#SUMMARY "CMC Test Trap"
                --#SEVERITY INFORMATIONAL
                --#CATEGORY Error Events
               ::= 2000
              
            alertCMCNormalTrap  TRAP-TYPE
                ENTERPRISE  	  drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a return-to-normal or informational event."
                --#TYPE "CMC Return-to-Normal / Informational Trap"
								--#SUMMARY "Return-to-Normal / Informational Trap from CMC in system '%s' in location '%s', message: '%s'"
								--#ARGUMENTS {0,1,7}
                --#SEVERITY NORMAL
                --#CATEGORY Error Events
               ::= 2002

            alertCMCWarningTrap TRAP-TYPE
                ENTERPRISE 	    drsOutofBandGroup
                VARIABLES {     drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a warning event."
                --#TYPE "CMC Warning Trap"
								--#SUMMARY "Warning Trap from CMC in system '%s' in location '%s', message: '%s'"
								--#ARGUMENTS {0,1,7}
                --#SEVERITY WARNING
                --#CATEGORY Error Events
               ::= 2003

            alertCMCCriticalTrap TRAP-TYPE
                ENTERPRISE 	    drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a critical event."
                --#TYPE "CMC Critical Trap"
								--#SUMMARY "Critical Trap from CMC in system '%s' in location '%s', message: '%s'"
								--#ARGUMENTS {0,1,7}
                --#SEVERITY CRITICAL
                --#CATEGORY Error Events
               ::= 2004

            alertCMCNonRecoverableTrap TRAP-TYPE
                ENTERPRISE 	    drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a catastrophic event."
                --#TYPE "CMC Non-Recoverable Trap"
								--#SUMMARY "Non-Recoverable Trap from CMC in system '%s' in location '%s', message: '%s'"
								--#ARGUMENTS {0,1,7}
                --#SEVERITY NON-RECOVERABLE
                --#CATEGORY Error Events
               ::= 2005
               
    --
    -- Non-CMC Alerting
    --

        drsAlertSystem         OBJECT-TYPE
            SYNTAX             OCTET STRING (SIZE (0..255))
            ACCESS             read-only
            STATUS             mandatory
            DESCRIPTION
            "5000.0010.0001 Name of the system generating the alert."
            --DEFAULT get-function-async    get_%n_async
            --DEFAULT next-function-async   std_next_async
            ::= { drsAlertVariables 1 }

        drsAlertTableIndexOID  OBJECT-TYPE
            SYNTAX             OBJECT IDENTIFIER
            ACCESS             read-only
            STATUS             mandatory
            DESCRIPTION
            "5000.0010.0002 0.0"
            --DEFAULT get-function-async    get_OID_null_async
            --DEFAULT next-function-async   std_next_async
            ::= { drsAlertVariables 2 }

        drsAlertMessage        OBJECT-TYPE
            SYNTAX             OCTET STRING (SIZE (0..1024))
            ACCESS             read-only
            STATUS             mandatory
            DESCRIPTION
            "5000.0010.0003 Message describing the alert."
            --DEFAULT get-function-async    get_string_null_async
            --DEFAULT next-function-async   std_next_async
            ::= { drsAlertVariables 3 }

        drsAlertCurrentStatus  OBJECT-TYPE
            SYNTAX             DellStatus
            ACCESS             read-only
            STATUS             mandatory
            DESCRIPTION
            "5000.0010.0004 Current status of object causing the alert."
            --DEFAULT get-function-async    get_dellstatus_unknow_async
            --DEFAULT next-function-async   std_next_async
            ::= { drsAlertVariables 4 }

        drsAlertPreviousStatus OBJECT-TYPE
            SYNTAX             DellStatus
            ACCESS             read-only
            STATUS             mandatory
            DESCRIPTION
            "5000.0010.0005 Previous status of object causing the alert."
            --DEFAULT get-function-async    get_dellstatus_unknow_async
            --DEFAULT next-function-async   std_next_async
            ::= { drsAlertVariables 5 }

        drsAlertData           OBJECT-TYPE
            SYNTAX             OCTET STRING (SIZE (0..1024))
            ACCESS             read-only
            STATUS             mandatory
            DESCRIPTION
            "5000.0010.0006 Alert data."
            --DEFAULT get-function-async    get_string_null_async
            --DEFAULT next-function-async   std_next_async
            ::= { drsAlertVariables 6 }

        alertDrscTestTrapEvent      TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC generated a test trap event in response to a user request."
        --#TYPE "Dell RAC Test TRAP Event"
        --#SUMMARY "%s"
        --#ARGUMENTS {2}
        --#SEVERITY INFORMATIONAL
        --#CATEGORY Status Events
        ::= 1001
    
        alertDrscAuthError          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Authentication Failures during a time period have Exceeded a Threshold."
        --#TYPE "Dell RAC Authentication Error"
        --#SUMMARY "%s"
        --#ARGUMENTS {2}
        --#SEVERITY MINOR
        --#CATEGORY Error Events
        ::= 1002

        alertDrscLostESM          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC cannot communicate with the baseboard management controller (ESM)."
        --#TYPE "Dell RAC Lost Communication with ESM"
        --#SUMMARY "%s"
        --#ARGUMENTS {2}
        --#SEVERITY MINOR
        --#CATEGORY Error Events
        ::= 1003

        alertDrscFoundESM          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC is communicating normally with the baseboard management controller (ESM)."
        --#TYPE "Dell RAC Communication with ESM is OK"
        --#SUMMARY "%s"
        --#ARGUMENTS {2}
        --#SEVERITY INFORMATIONAL
        --#CATEGORY Error Events
        ::= 1004

        alertDrscPowerOff          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a System power state change to powered-off."
        --#TYPE "Dell RAC Detected System Powered-Off"
        --#SUMMARY "%s"
        --#ARGUMENTS {2}
        --#SEVERITY CRITICAL
        --#CATEGORY Error Events
        ::= 1005

        alertDrscPowerOn          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a system power state change to powered-on."
        --#TYPE "Dell RAC Detected System Powered-On"
        --#SUMMARY "%s"
        --#ARGUMENTS {2}
        --#SEVERITY INFORMATIONAL
        --#CATEGORY Error Events
        ::= 1006

        alertDrscWatchdogExpired          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the system watchdog has expired indicating a system hang."
        --#TYPE "Dell RAC Detected Watchdog Expired"
        --#SUMMARY "%s"
        --#ARGUMENTS {2}
        --#SEVERITY CRITICAL
        --#CATEGORY Error Events
        ::= 1007

        alertDrscBattLow          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Battery charge is below 25% indicating that the battery may only be able to power the DRSC for 8-10 minutes."
        --#TYPE "Dell RAC Battery Charge Low"
        --#SUMMARY "%s"
        --#ARGUMENTS {2}
        --#SEVERITY MINOR
        --#CATEGORY Error Events
        ::= 1008

        alertDrscTempNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has retured to a normal value."
        --#TYPE "Dell RAC Temperature Normal"
        --#SUMMARY "%s"
        --#ARGUMENTS {2}
        --#SEVERITY INFORMATIONAL
        --#CATEGORY Error Events
        ::= 1009

        alertDrscTempWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has detected a Warning value."
        --#TYPE "Dell RAC Temperature Warning"
        --#SUMMARY "%s"
        --#ARGUMENTS {2}
        --#SEVERITY MINOR
        --#CATEGORY Error Events
        ::= 1010

        alertDrscTempCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has detected a failure (or critical) value."
        --#TYPE "Dell RAC Temperature Failure"
        --#SUMMARY "%s"
        --#ARGUMENTS {2}
        --#SEVERITY CRITICAL
        --#CATEGORY Error Events
        ::= 1011

        alertDrscVoltNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage has returned to a normal value."
        --#TYPE "Dell RAC Voltage Normal"
        --#SUMMARY "%s"
        --#ARGUMENTS {2}
        --#SEVERITY INFORMATIONAL
        --#CATEGORY Error Events
        ::= 1012

        alertDrscVoltWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage probe has detected a warning value."
        --#TYPE "Dell RAC Battery Warning"
        --#SUMMARY "%s"
        --#ARGUMENTS {2}
        --#SEVERITY MINOR
        --#CATEGORY Error Events
        ::= 1013

        alertDrscVoltCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage probe has detected a failure (or critical) value."
        --#TYPE "Dell RAC Voltage Failure"
        --#SUMMARY "%s"
        --#ARGUMENTS {2}
        --#SEVERITY CRITICAL
        --#CATEGORY Error Events
        ::= 1014

        alertDrscSELWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Warning."
        --#TYPE "Dell RAC System Event Log Warning"
        --#SUMMARY "%s"
        --#ARGUMENTS {2}
        --#SEVERITY MAJOR
        --#CATEGORY Error Events
        ::= 1015

        alertDrscSELCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Critical."
        --#TYPE "Dell RAC System Event Log Critical"
        --#SUMMARY "%s"
        --#ARGUMENTS {2}
        --#SEVERITY CRITICAL
        --#CATEGORY Error Events
        ::= 1016

        alertDrscSEL80percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 80% full."
        --#TYPE "Dell System Event Log 80% Full Warning"
        --#SUMMARY "%s"
        --#ARGUMENTS {2}
        --#SEVERITY MAJOR
        --#CATEGORY Status Events
        ::= 1017

        alertDrscSEL90percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 90% full."
        --#TYPE " Dell System Event Log 90% Full Warning "
        --#SUMMARY "%s"
        --#ARGUMENTS {2}
        --#SEVERITY MAJOR
        --#CATEGORY Status Events
        ::= 1018

        alertDrscSEL100percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 100% full."
        --#TYPE " Dell System Event Log 100% Full Warning "
        --#SUMMARY "%s"
        --#ARGUMENTS {2}
        --#SEVERITY MAJOR
        --#CATEGORY Status Events
        ::= 1019

        alertDrscSELNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Normal."
        --#TYPE "Dell RAC System Event Log Normal"
        --#SUMMARY "%s"
        --#ARGUMENTS {2}
        --#SEVERITY INFORMATIONAL
        --#CATEGORY Error Events
        ::= 1020
END
