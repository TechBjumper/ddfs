-- ***********************************************
-- COOLTERA-GLOBAL-REG.mib
--
-- Cooltera Limited Global Definitions.
-- ***********************************************

COOLTERA-GLOBAL-REG DEFINITIONS ::= BEGIN

	IMPORTS
		MODULE-IDENTITY, OBJECT-IDENTITY,
		enterprises
			FROM SNMPv2-SMI;

	cooltera MODULE-IDENTITY
		LAST-UPDATED			"201801301000Z"
		ORGANIZATION			"Cooltera Limited"
		CONTACT-INFO			"
								Fircroft House
								Fircroft Way
								Edenbridge
								Kent
								TN8 6EJ
								Phone: +44 1732 867105
								E-mail: support@cooltera.com"

		DESCRIPTION				"
			A MIB module containing top-level OID definitions
			for various sub-trees for Cooltera's enterprise MIB modules."

		REVISION				"201801301000Z"
		DESCRIPTION				"
			Rev 1.0
			Initial version of MIB module COOLTERA-GLOBAL-REG."

		::= { enterprises 51077 }

END
