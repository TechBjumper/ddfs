--
-- CAREL-bce.MIB
-- MIB generated by CAREL
-- Tuesday, 11 April 2006
--

    CAREL-bce-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        bceMIB MODULE-IDENTITY
      		LAST-UPDATED  "200604111645Z"		-- February 21, 2013 at 09:24 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the BCE Uniflair device."
		REVISION   "200604111645Z"		-- April 11, 2006 at 16:45 GMT
		DESCRIPTION
		"This is the original version of this MIB"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { bceMIB 1 }

        -- 1.3.6.1.4.1.9839.2.1.1.1
        pump-on OBJECT-TYPE
                    SYNTAX Integer32 (0..1)
                    UNITS "N/A"
                    MAX-ACCESS read-only
                    STATUS current
                    DESCRIPTION "SYSTEM_ON"
                    ::= { digitalObjects 1 }

        -- 1.3.6.1.4.1.9839.2.1.1.2
        spin1 OBJECT-TYPE
                    SYNTAX Integer32 (0..1)
                    UNITS "N/A"
                    MAX-ACCESS read-only
                    STATUS current
                    DESCRIPTION "COMPRESSOR 1 STARTING"
                    ::= { digitalObjects 2 }

        -- 1.3.6.1.4.1.9839.2.1.1.3
        spin2 OBJECT-TYPE
                    SYNTAX Integer32 (0..1)
                    UNITS "N/A"
                    MAX-ACCESS read-only
                    STATUS current
                    DESCRIPTION "COMPRESSOR 2 STARTING"
                    ::= { digitalObjects 3 }

        -- 1.3.6.1.4.1.9839.2.1.1.4
        spin3 OBJECT-TYPE
                    SYNTAX Integer32 (0..1)
                    UNITS "N/A"
                    MAX-ACCESS read-only
                    STATUS current
                    DESCRIPTION "COMPRESSOR 3 STARTING"
                    ::= { digitalObjects 4 }

        -- 1.3.6.1.4.1.9839.2.1.1.6
        etv-bp-gc OBJECT-TYPE
                    SYNTAX Integer32 (0..1)
                    UNITS "N/A"
                    MAX-ACCESS read-only
                    STATUS current
                    DESCRIPTION "COMPRESSOR 1 HOTGAS ELECTROVALVE"
                    ::= { digitalObjects 6 }

        -- 1.3.6.1.4.1.9839.2.1.1.7
        etv-bp-gc-c2 OBJECT-TYPE
                    SYNTAX Integer32 (0..1)
                    UNITS "N/A"
                    MAX-ACCESS read-only
                    STATUS current
                    DESCRIPTION "COMPRESSOR 2 HOTGAS ELECTROVALVE"
                    ::= { digitalObjects 7 }

        -- 1.3.6.1.4.1.9839.2.1.1.8
        etv-bp-gc-c3 OBJECT-TYPE
                    SYNTAX Integer32 (0..1)
                    UNITS "N/A"
                    MAX-ACCESS read-only
                    STATUS current
                    DESCRIPTION "COMPRESSOR 3 HOTGAS ELECTROVALVE"
                    ::= { digitalObjects 8 }

        -- 1.3.6.1.4.1.9839.2.1.1.10
        compressor1 OBJECT-TYPE
                    SYNTAX Integer32 (0..1)
                    UNITS "N/A"
                    MAX-ACCESS read-only
                    STATUS current
                    DESCRIPTION "COMPRESSOR 1 RUNNING"
                    ::= { digitalObjects 10 }

        -- 1.3.6.1.4.1.9839.2.1.1.11
        compressor2 OBJECT-TYPE
                    SYNTAX Integer32 (0..1)
                    UNITS "N/A"
                    MAX-ACCESS read-only
                    STATUS current
                    DESCRIPTION "COMPRESSOR 2 RUNNING"
                    ::= { digitalObjects 11 }

        -- 1.3.6.1.4.1.9839.2.1.1.12
        compressor3 OBJECT-TYPE
                    SYNTAX Integer32 (0..1)
                    UNITS "N/A"
                    MAX-ACCESS read-only
                    STATUS current
                    DESCRIPTION "COMPRESSOR 3 RUNNING"
                    ::= { digitalObjects 12 }

        -- 1.3.6.1.4.1.9839.2.1.1.14
        pompa1 OBJECT-TYPE
                    SYNTAX Integer32 (0..1)
                    UNITS "N/A"
                    MAX-ACCESS read-only
                    STATUS current
                    DESCRIPTION "PUMP 1 ON "
                    ::= { digitalObjects 14 }

        -- 1.3.6.1.4.1.9839.2.1.1.15
        pompa2 OBJECT-TYPE
                    SYNTAX Integer32 (0..1)
                    UNITS "N/A"
                    MAX-ACCESS read-only
                    STATUS current
                    DESCRIPTION "PUMP 2 ON"
                    ::= { digitalObjects 15 }

        -- 1.3.6.1.4.1.9839.2.1.1.16
        pompa-fc OBJECT-TYPE
                    SYNTAX Integer32 (0..1)
                    UNITS "N/A"
                    MAX-ACCESS read-only
                    STATUS current
                    DESCRIPTION "FREECOOLING PUMP ON"
                    ::= { digitalObjects 16 }

        -- 1.3.6.1.4.1.9839.2.1.1.17
        heater OBJECT-TYPE
                    SYNTAX Integer32 (0..1)
                    UNITS "N/A"
                    MAX-ACCESS read-only
                    STATUS current
                    DESCRIPTION "ANTIFREEZE HEATERS"
                    ::= { digitalObjects 17 }

        -- 1.3.6.1.4.1.9839.2.1.1.18
        x-cmd-iv OBJECT-TYPE
                    SYNTAX Integer32 (0..1)
                    UNITS "N/A"
                    MAX-ACCESS read-only
                    STATUS current
                    DESCRIPTION "WATER MOTORIZED HYDRAULIC VALVE"
                    ::= { digitalObjects 18 }

        -- 1.3.6.1.4.1.9839.2.1.1.19
        valvola-fc OBJECT-TYPE
                    SYNTAX Integer32 (0..1)
                    UNITS "N/A"
                    MAX-ACCESS read-only
                    STATUS current
                    DESCRIPTION "WATER MOTORIZED FREECOOLING VALVE"
                    ::= { digitalObjects 19 }

        -- 1.3.6.1.4.1.9839.2.1.1.21
        etv-cond1-2 OBJECT-TYPE
                    SYNTAX Integer32 (0..1)
                    UNITS "N/A"
                    MAX-ACCESS read-only
                    STATUS current
                    DESCRIPTION "CONDENSING SOLENOID 1 VALVE"
                    ::= { digitalObjects 21 }

        -- 1.3.6.1.4.1.9839.2.1.1.22
        etv-cond3-4 OBJECT-TYPE
                    SYNTAX Integer32 (0..1)
                    UNITS "N/A"
                    MAX-ACCESS read-only
                    STATUS current
                    DESCRIPTION "CONDENSING SOLENOID 2 VALVE"
                    ::= { digitalObjects 22 }

        -- 1.3.6.1.4.1.9839.2.1.1.23
        etv-cond5-6 OBJECT-TYPE
                    SYNTAX Integer32 (0..1)
                    UNITS "N/A"
                    MAX-ACCESS read-only
                    STATUS current
                    DESCRIPTION "CONDENSING SOLENOID 3 VALVE"
                    ::= { digitalObjects 23 }

        -- 1.3.6.1.4.1.9839.2.1.1.24
        etv-cond7-8 OBJECT-TYPE
                    SYNTAX Integer32 (0..1)
                    UNITS "N/A"
                    MAX-ACCESS read-only
                    STATUS current
                    DESCRIPTION "CONDENSING SOLENOID 4 VALVE"
                    ::= { digitalObjects 24 }

        -- 1.3.6.1.4.1.9839.2.1.1.25
        etv-cond9-10 OBJECT-TYPE
                    SYNTAX Integer32 (0..1)
                    UNITS "N/A"
                    MAX-ACCESS read-only
                    STATUS current
                    DESCRIPTION "CONDENSING SOLENOID 5 VALVE"
                    ::= { digitalObjects 25 }

        -- 1.3.6.1.4.1.9839.2.1.1.31
        preal-flux-ev OBJECT-TYPE
                    SYNTAX Integer32 (0..1)
                    UNITS "N/A"
                    MAX-ACCESS read-only
                    STATUS current
                    DESCRIPTION "EVAPORATOR WATER FLOW PREALARM"
                    ::= { digitalObjects 31 }

        -- 1.3.6.1.4.1.9839.2.1.1.32
        al-flux-ev OBJECT-TYPE
                    SYNTAX Integer32 (0..1)
                    UNITS "N/A"
                    MAX-ACCESS read-only
                    STATUS current
                    DESCRIPTION "EVAPORATOR WATER FLOW ALARM"
                    ::= { digitalObjects 32 }

        -- 1.3.6.1.4.1.9839.2.1.1.33
        preal-flux-pump-con OBJECT-TYPE
                    SYNTAX Integer32 (0..1)
                    UNITS "N/A"
                    MAX-ACCESS read-only
                    STATUS current
                    DESCRIPTION "CONDENSING  WATER FLOW PREALARM"
                    ::= { digitalObjects 33 }

        -- 1.3.6.1.4.1.9839.2.1.1.34
        al-flux-con OBJECT-TYPE
                    SYNTAX Integer32 (0..1)
                    UNITS "N/A"
                    MAX-ACCESS read-only
                    STATUS current
                    DESCRIPTION "CONDENSING  WATER FLOW ALARM"
                    ::= { digitalObjects 34 }

        -- 1.3.6.1.4.1.9839.2.1.1.35
        al-af-warm OBJECT-TYPE
                    SYNTAX Integer32 (0..1)
                    UNITS "N/A"
                    MAX-ACCESS read-only
                    STATUS current
                    DESCRIPTION "ANTIFREEZE WARNING"
                    ::= { digitalObjects 35 }

        -- 1.3.6.1.4.1.9839.2.1.1.36
        preal-af-alarm OBJECT-TYPE
                    SYNTAX Integer32 (0..1)
                    UNITS "N/A"
                    MAX-ACCESS read-only
                    STATUS current
                    DESCRIPTION "ANTIFREEZE PREALARM"
                    ::= { digitalObjects 36 }

        -- 1.3.6.1.4.1.9839.2.1.1.37
        al-af-alarm OBJECT-TYPE
                    SYNTAX Integer32 (0..1)
                    UNITS "N/A"
                    MAX-ACCESS read-only
                    STATUS current
                    DESCRIPTION "ANTIFREEZE ALARM"
                    ::= { digitalObjects 37 }

        -- 1.3.6.1.4.1.9839.2.1.1.38
        mal-ht-win OBJECT-TYPE
                    SYNTAX Integer32 (0..1)
                    UNITS "N/A"
                    MAX-ACCESS read-only
                    STATUS current
                    DESCRIPTION "WATER IN TEMPERATURE ABOVE MAXIMUM LIMIT"
                    ::= { digitalObjects 38 }

        -- 1.3.6.1.4.1.9839.2.1.1.39
        mal-lt-win OBJECT-TYPE
                    SYNTAX Integer32 (0..1)
                    UNITS "N/A"
                    MAX-ACCESS read-only
                    STATUS current
                    DESCRIPTION "WATER IN TEMPERATURE BELOW LOW LIMIT"
                    ::= { digitalObjects 39 }

        -- 1.3.6.1.4.1.9839.2.1.1.40
        mlow-temp-wout OBJECT-TYPE
                    SYNTAX Integer32 (0..1)
                    UNITS "N/A"
                    MAX-ACCESS read-only
                    STATUS current
                    DESCRIPTION "EVAPORATOR HI WATER TEMPERATURE (OPERATING LIMITS)"
                    ::= { digitalObjects 40 }

        -- 1.3.6.1.4.1.9839.2.1.1.41
        mlow-temp-hwin OBJECT-TYPE
                    SYNTAX Integer32 (0..1)
                    UNITS "N/A"
                    MAX-ACCESS read-only
                    STATUS current
                    DESCRIPTION "EVAPORATOR LOW WATER TEMPERATURE (OPERATING LIMITS)"
                    ::= { digitalObjects 41 }

        -- 1.3.6.1.4.1.9839.2.1.1.42
        mhi-temp-wout OBJECT-TYPE
                    SYNTAX Integer32 (0..1)
                    UNITS "N/A"
                    MAX-ACCESS read-only
                    STATUS current
                    DESCRIPTION "CONDENSER HI WATER TEMPERATURE (OPERATING LIMITS)"
                    ::= { digitalObjects 42 }

        -- 1.3.6.1.4.1.9839.2.1.1.43
        mhi-temp-hwin OBJECT-TYPE
                    SYNTAX Integer32 (0..1)
                    UNITS "N/A"
                    MAX-ACCESS read-only
                    STATUS current
                    DESCRIPTION "CONDENSER LOW WATER TEMPERATURE (OPERATING LIMITS)"
                    ::= { digitalObjects 43 }

        -- 1.3.6.1.4.1.9839.2.1.1.44
        preal-tp-fan OBJECT-TYPE
                    SYNTAX Integer32 (0..1)
                    UNITS "N/A"
                    MAX-ACCESS read-only
                    STATUS current
                    DESCRIPTION "FANS THERMAL PREALARM"
                    ::= { digitalObjects 44 }

        -- 1.3.6.1.4.1.9839.2.1.1.45
        al-tp-fan OBJECT-TYPE
                    SYNTAX Integer32 (0..1)
                    UNITS "N/A"
                    MAX-ACCESS read-only
                    STATUS current
                    DESCRIPTION "FANS THERMAL ALARM"
                    ::= { digitalObjects 45 }

        -- 1.3.6.1.4.1.9839.2.1.1.46
        preal-fase OBJECT-TYPE
                    SYNTAX Integer32 (0..1)
                    UNITS "N/A"
                    MAX-ACCESS read-only
                    STATUS current
                    DESCRIPTION "MAINS PHASE/ VOLT.OUT OF LIMIT PREALARM"
                    ::= { digitalObjects 46 }

        -- 1.3.6.1.4.1.9839.2.1.1.47
        alg-fase OBJECT-TYPE
                    SYNTAX Integer32 (0..1)
                    UNITS "N/A"
                    MAX-ACCESS read-only
                    STATUS current
                    DESCRIPTION "MAINS PHASE/ VOLT.OUT OF LIMIT ALARM"
                    ::= { digitalObjects 47 }

        -- 1.3.6.1.4.1.9839.2.1.1.48
        mal-freq-rilev OBJECT-TYPE
                    SYNTAX Integer32 (0..1)
                    UNITS "N/A"
                    MAX-ACCESS read-only
                    STATUS current
                    DESCRIPTION "SUPPLY FREQUENCY NOT DETECTED"
                    ::= { digitalObjects 48 }

        -- 1.3.6.1.4.1.9839.2.1.1.49
        mal-isol-valve OBJECT-TYPE
                    SYNTAX Integer32 (0..1)
                    UNITS "N/A"
                    MAX-ACCESS read-only
                    STATUS current
                    DESCRIPTION "ISOLATING VALVE NOT FULLY OPEN"
                    ::= { digitalObjects 49 }

        -- 1.3.6.1.4.1.9839.2.1.1.50
        mal-access OBJECT-TYPE
                    SYNTAX Integer32 (0..1)
                    UNITS "N/A"
                    MAX-ACCESS read-only
                    STATUS current
                    DESCRIPTION "WRONG PASSWORD ALARM"
                    ::= { digitalObjects 50 }

        -- 1.3.6.1.4.1.9839.2.1.1.51
        mal-or-ore-compr OBJECT-TYPE
                    SYNTAX Integer32 (0..1)
                    UNITS "N/A"
                    MAX-ACCESS read-only
                    STATUS current
                    DESCRIPTION "COMPRESSOR HOUR COUNTER"
                    ::= { digitalObjects 51 }

        -- 1.3.6.1.4.1.9839.2.1.1.52
        mal-or-ore-pump OBJECT-TYPE
                    SYNTAX Integer32 (0..1)
                    UNITS "N/A"
                    MAX-ACCESS read-only
                    STATUS current
                    DESCRIPTION "PUMP HOUR COUNTER"
                    ::= { digitalObjects 52 }

        -- 1.3.6.1.4.1.9839.2.1.1.53
        mal-pompa1 OBJECT-TYPE
                    SYNTAX Integer32 (0..1)
                    UNITS "N/A"
                    MAX-ACCESS read-only
                    STATUS current
                    DESCRIPTION "CIRCULATING PUMP 1 OVERLOAD ALARM"
                    ::= { digitalObjects 53 }

        -- 1.3.6.1.4.1.9839.2.1.1.54
        mal-pompa2 OBJECT-TYPE
                    SYNTAX Integer32 (0..1)
                    UNITS "N/A"
                    MAX-ACCESS read-only
                    STATUS current
                    DESCRIPTION "CIRCULATING PUMP 2 OVERLOAD ALARM"
                    ::= { digitalObjects 54 }

        -- 1.3.6.1.4.1.9839.2.1.1.55
        mal-pompafc OBJECT-TYPE
                    SYNTAX Integer32 (0..1)
                    UNITS "N/A"
                    MAX-ACCESS read-only
                    STATUS current
                    DESCRIPTION "FREECOOLING PUMP OVERLOAD ALARM"
                    ::= { digitalObjects 55 }

        -- 1.3.6.1.4.1.9839.2.1.1.56
        mperm-mem-error OBJECT-TYPE
                    SYNTAX Integer32 (0..1)
                    UNITS "N/A"
                    MAX-ACCESS read-only
                    STATUS current
                    DESCRIPTION "PERMANENT MEMORY ERROR"
                    ::= { digitalObjects 56 }

        -- 1.3.6.1.4.1.9839.2.1.1.57
        global-alarm OBJECT-TYPE
                    SYNTAX Integer32 (0..1)
                    UNITS "N/A"
                    MAX-ACCESS read-only
                    STATUS current
                    DESCRIPTION "GLOBAL ALARM"
                    ::= { digitalObjects 57 }

        -- 1.3.6.1.4.1.9839.2.1.1.58
        alarm-a OBJECT-TYPE
                    SYNTAX Integer32 (0..1)
                    UNITS "N/A"
                    MAX-ACCESS read-only
                    STATUS current
                    DESCRIPTION "TYPE A ALARM"
                    ::= { digitalObjects 58 }

        -- 1.3.6.1.4.1.9839.2.1.1.59
        alarm-b OBJECT-TYPE
                    SYNTAX Integer32 (0..1)
                    UNITS "N/A"
                    MAX-ACCESS read-only
                    STATUS current
                    DESCRIPTION "TYPE B ALARM"
                    ::= { digitalObjects 59 }

        -- 1.3.6.1.4.1.9839.2.1.1.60
        alarm-c OBJECT-TYPE
                    SYNTAX Integer32 (0..1)
                    UNITS "N/A"
                    MAX-ACCESS read-only
                    STATUS current
                    DESCRIPTION "TYPE C ALARM"
                    ::= { digitalObjects 60 }

        -- 1.3.6.1.4.1.9839.2.1.1.61
        mal-lan OBJECT-TYPE
                    SYNTAX Integer32 (0..1)
                    UNITS "N/A"
                    MAX-ACCESS read-only
                    STATUS current
                    DESCRIPTION "INTERRUPTED LAN ALARM"
                    ::= { digitalObjects 61 }

        -- 1.3.6.1.4.1.9839.2.1.1.62
        mal-lan-board2 OBJECT-TYPE
                    SYNTAX Integer32 (0..1)
                    UNITS "N/A"
                    MAX-ACCESS read-only
                    STATUS current
                    DESCRIPTION "BOARD 2 DISCONNECTED"
                    ::= { digitalObjects 62 }

        -- 1.3.6.1.4.1.9839.2.1.1.63
        mal-offline-c1 OBJECT-TYPE
                    SYNTAX Integer32 (0..1)
                    UNITS "N/A"
                    MAX-ACCESS read-only
                    STATUS current
                    DESCRIPTION "COMUNICATION FAILURE COMPRESSOR 1"
                    ::= { digitalObjects 63 }

        -- 1.3.6.1.4.1.9839.2.1.1.64
        mal-offline-c2 OBJECT-TYPE
                    SYNTAX Integer32 (0..1)
                    UNITS "N/A"
                    MAX-ACCESS read-only
                    STATUS current
                    DESCRIPTION "COMUNICATION FAILURE COMPRESSOR 2"
                    ::= { digitalObjects 64 }

        -- 1.3.6.1.4.1.9839.2.1.1.65
        mal-offline-c3 OBJECT-TYPE
                    SYNTAX Integer32 (0..1)
                    UNITS "N/A"
                    MAX-ACCESS read-only
                    STATUS current
                    DESCRIPTION "COMUNICATION FAILURE COMPRESSOR 3"
                    ::= { digitalObjects 65 }

        -- 1.3.6.1.4.1.9839.2.1.1.67
        mal-comm-nok OBJECT-TYPE
                    SYNTAX Integer32 (0..1)
                    UNITS "N/A"
                    MAX-ACCESS read-only
                    STATUS current
                    DESCRIPTION "COMUNICATION FAILURE COM FIELDBUS 2"
                    ::= { digitalObjects 67 }

        -- 1.3.6.1.4.1.9839.2.1.1.68
        mal-offline-pms OBJECT-TYPE
                    SYNTAX Integer32 (0..1)
                    UNITS "N/A"
                    MAX-ACCESS read-only
                    STATUS current
                    DESCRIPTION "COMUNICATION FAILURE POWER ENERGY"
                    ::= { digitalObjects 68 }

        -- 1.3.6.1.4.1.9839.2.1.1.69
        mal-offline-vent-ec OBJECT-TYPE
                    SYNTAX Integer32 (0..1)
                    UNITS "N/A"
                    MAX-ACCESS read-only
                    STATUS current
                    DESCRIPTION "COMUNICATION FAILURE EC FANS"
                    ::= { digitalObjects 69 }

        -- 1.3.6.1.4.1.9839.2.1.1.70
        al-offline-pump OBJECT-TYPE
                    SYNTAX Integer32 (0..1)
                    UNITS "N/A"
                    MAX-ACCESS read-only
                    STATUS current
                    DESCRIPTION "COMUNICATION FAILURE INVERTER PUMP"
                    ::= { digitalObjects 70 }

        -- 1.3.6.1.4.1.9839.2.1.1.71
        mal-cc1 OBJECT-TYPE
                    SYNTAX Integer32 (0..1)
                    UNITS "N/A"
                    MAX-ACCESS read-only
                    STATUS current
                    DESCRIPTION "COMPRESSOR 1  HIGH PRESSURE SWITCH ALARM"
                    ::= { digitalObjects 71 }

        -- 1.3.6.1.4.1.9839.2.1.1.72
        mal-cc2 OBJECT-TYPE
                    SYNTAX Integer32 (0..1)
                    UNITS "N/A"
                    MAX-ACCESS read-only
                    STATUS current
                    DESCRIPTION "COMPRESSOR 2  HIGH PRESSURE SWITCH ALARM"
                    ::= { digitalObjects 72 }

        -- 1.3.6.1.4.1.9839.2.1.1.73
        mal-cc3 OBJECT-TYPE
                    SYNTAX Integer32 (0..1)
                    UNITS "N/A"
                    MAX-ACCESS read-only
                    STATUS current
                    DESCRIPTION "COMPRESSOR 3  HIGH PRESSURE SWITCH ALARM"
                    ::= { digitalObjects 73 }

        -- 1.3.6.1.4.1.9839.2.1.1.75
        mal-hp OBJECT-TYPE
                    SYNTAX Integer32 (0..1)
                    UNITS "N/A"
                    MAX-ACCESS read-only
                    STATUS current
                    DESCRIPTION "COMPRESSOR 1  HIGH PRESSURE ALARM"
                    ::= { digitalObjects 75 }

        -- 1.3.6.1.4.1.9839.2.1.1.76
        mal-hp-c2 OBJECT-TYPE
                    SYNTAX Integer32 (0..1)
                    UNITS "N/A"
                    MAX-ACCESS read-only
                    STATUS current
                    DESCRIPTION "COMPRESSOR 2  HIGH PRESSURE ALARM"
                    ::= { digitalObjects 76 }

        -- 1.3.6.1.4.1.9839.2.1.1.77
        mal-hp-c3 OBJECT-TYPE
                    SYNTAX Integer32 (0..1)
                    UNITS "N/A"
                    MAX-ACCESS read-only
                    STATUS current
                    DESCRIPTION "COMPRESSOR 3  HIGH PRESSURE ALARM"
                    ::= { digitalObjects 77 }

        -- 1.3.6.1.4.1.9839.2.1.1.79
        preal-bp OBJECT-TYPE
                    SYNTAX Integer32 (0..1)
                    UNITS "N/A"
                    MAX-ACCESS read-only
                    STATUS current
                    DESCRIPTION "LOW PRESSURE PREALARM"
                    ::= { digitalObjects 79 }

        -- 1.3.6.1.4.1.9839.2.1.1.80
        al-grave-bp OBJECT-TYPE
                    SYNTAX Integer32 (0..1)
                    UNITS "N/A"
                    MAX-ACCESS read-only
                    STATUS current
                    DESCRIPTION "LOW PRESSURE ALARM"
                    ::= { digitalObjects 80 }

        -- 1.3.6.1.4.1.9839.2.1.1.81
        mal-lp OBJECT-TYPE
                    SYNTAX Integer32 (0..1)
                    UNITS "N/A"
                    MAX-ACCESS read-only
                    STATUS current
                    DESCRIPTION "COMPRESSOR 1  LOW PRESSURE ALARM"
                    ::= { digitalObjects 81 }

        -- 1.3.6.1.4.1.9839.2.1.1.82
        mal-lp-c2 OBJECT-TYPE
                    SYNTAX Integer32 (0..1)
                    UNITS "N/A"
                    MAX-ACCESS read-only
                    STATUS current
                    DESCRIPTION "COMPRESSOR 2  LOW PRESSURE ALARM"
                    ::= { digitalObjects 82 }

        -- 1.3.6.1.4.1.9839.2.1.1.83
        mal-lp-c3 OBJECT-TYPE
                    SYNTAX Integer32 (0..1)
                    UNITS "N/A"
                    MAX-ACCESS read-only
                    STATUS current
                    DESCRIPTION "COMPRESSOR 3  LOW PRESSURE ALARM"
                    ::= { digitalObjects 83 }

        -- 1.3.6.1.4.1.9839.2.1.1.85
        mal-sonda-twin OBJECT-TYPE
                    SYNTAX Integer32 (0..1)
                    UNITS "N/A"
                    MAX-ACCESS read-only
                    STATUS current
                    DESCRIPTION "WATER IN TEMPERATURE SENSOR FAILURE"
                    ::= { digitalObjects 85 }

        -- 1.3.6.1.4.1.9839.2.1.1.86
        mal-sonda-twout OBJECT-TYPE
                    SYNTAX Integer32 (0..1)
                    UNITS "N/A"
                    MAX-ACCESS read-only
                    STATUS current
                    DESCRIPTION "WATER OUT TEMPERATURE SENSOR FAILURE"
                    ::= { digitalObjects 86 }

        -- 1.3.6.1.4.1.9839.2.1.1.87
        mal-sonda-thwin OBJECT-TYPE
                    SYNTAX Integer32 (0..1)
                    UNITS "N/A"
                    MAX-ACCESS read-only
                    STATUS current
                    DESCRIPTION "HOT WATER IN TEMPERATURE SENSOR FAILURE"
                    ::= { digitalObjects 87 }

        -- 1.3.6.1.4.1.9839.2.1.1.88
        mal-sonda-thwout OBJECT-TYPE
                    SYNTAX Integer32 (0..1)
                    UNITS "N/A"
                    MAX-ACCESS read-only
                    STATUS current
                    DESCRIPTION "HOT WATER OUT TEMPERATURE SENSOR FAILURE"
                    ::= { digitalObjects 88 }

        -- 1.3.6.1.4.1.9839.2.1.1.89
        mal-sonda-level OBJECT-TYPE
                    SYNTAX Integer32 (0..1)
                    UNITS "N/A"
                    MAX-ACCESS read-only
                    STATUS current
                    DESCRIPTION "EVAPORATOR LEVEL 1 TRASDUCER FAILURE"
                    ::= { digitalObjects 89 }

        -- 1.3.6.1.4.1.9839.2.1.1.90
        mal-sonda-level2 OBJECT-TYPE
                    SYNTAX Integer32 (0..1)
                    UNITS "N/A"
                    MAX-ACCESS read-only
                    STATUS current
                    DESCRIPTION "EVAPORATOR LEVEL 2 TRASDUCER FAILURE"
                    ::= { digitalObjects 90 }

        -- 1.3.6.1.4.1.9839.2.1.1.91
        mal-sonda-te OBJECT-TYPE
                    SYNTAX Integer32 (0..1)
                    UNITS "N/A"
                    MAX-ACCESS read-only
                    STATUS current
                    DESCRIPTION "OUTDOOR AIR TEMP. SENSOR FAILURE/DISCONNECTED"
                    ::= { digitalObjects 91 }

        -- 1.3.6.1.4.1.9839.2.1.1.92
        mal-sonda-tinevap OBJECT-TYPE
                    SYNTAX Integer32 (0..1)
                    UNITS "N/A"
                    MAX-ACCESS read-only
                    STATUS current
                    DESCRIPTION "EVAPORATOR PRESSURE SENSOR FAILURE"
                    ::= { digitalObjects 92 }

        -- 1.3.6.1.4.1.9839.2.1.1.93
        mal-sonda-tliq OBJECT-TYPE
                    SYNTAX Integer32 (0..1)
                    UNITS "N/A"
                    MAX-ACCESS read-only
                    STATUS current
                    DESCRIPTION "LIQUID PRESSURE SENSOR FAILURE"
                    ::= { digitalObjects 93 }

        -- 1.3.6.1.4.1.9839.2.1.1.94
        mal-sonda-pcc OBJECT-TYPE
                    SYNTAX Integer32 (0..1)
                    UNITS "N/A"
                    MAX-ACCESS read-only
                    STATUS current
                    DESCRIPTION "LIQUID TEMPERATURE SENSOR FAILURE"
                    ::= { digitalObjects 94 }

        -- 1.3.6.1.4.1.9839.2.1.1.95
        mal-sonda-pdisch OBJECT-TYPE
                    SYNTAX Integer32 (0..1)
                    UNITS "N/A"
                    MAX-ACCESS read-only
                    STATUS current
                    DESCRIPTION "DISCHARGE PRESSURE SENSOR FAILURE"
                    ::= { digitalObjects 95 }

        -- 1.3.6.1.4.1.9839.2.1.1.96
        mal-sonda-pin OBJECT-TYPE
                    SYNTAX Integer32 (0..1)
                    UNITS "N/A"
                    MAX-ACCESS read-only
                    STATUS current
                    DESCRIPTION "WATER IN PRESSURE SENSOR FAILURE"
                    ::= { digitalObjects 96 }

        -- 1.3.6.1.4.1.9839.2.1.1.97
        mal-sonda-pout OBJECT-TYPE
                    SYNTAX Integer32 (0..1)
                    UNITS "N/A"
                    MAX-ACCESS read-only
                    STATUS current
                    DESCRIPTION "WATER OUT PRESSURE SENSOR FAILURE"
                    ::= { digitalObjects 97 }

        -- 1.3.6.1.4.1.9839.2.1.1.98
        mor-err-sw OBJECT-TYPE
                    SYNTAX Integer32 (0..1)
                    UNITS "N/A"
                    MAX-ACCESS read-only
                    STATUS current
                    DESCRIPTION "BOARD 2 SOFTWARE NOT COMPATIBLE"
                    ::= { digitalObjects 98 }

        -- 1.3.6.1.4.1.9839.2.1.1.99
        mor-err-bms OBJECT-TYPE
                    SYNTAX Integer32 (0..1)
                    UNITS "N/A"
                    MAX-ACCESS read-only
                    STATUS current
                    DESCRIPTION "BMS ERROR WRITE"
                    ::= { digitalObjects 99 }

        -- 1.3.6.1.4.1.9839.2.1.1.100
        al-serius-pump-inv OBJECT-TYPE
                    SYNTAX Integer32 (0..1)
                    UNITS "N/A"
                    MAX-ACCESS read-only
                    STATUS current
                    DESCRIPTION "INVERTER PUMP ALARM (SERIUS)"
                    ::= { digitalObjects 100 }

        -- 1.3.6.1.4.1.9839.2.1.1.101
        al-not-serius-pump-inv OBJECT-TYPE
                    SYNTAX Integer32 (0..1)
                    UNITS "N/A"
                    MAX-ACCESS read-only
                    STATUS current
                    DESCRIPTION "INVERTER PUMP ALARM (NOT SERIUS)"
                    ::= { digitalObjects 101 }

        -- 1.3.6.1.4.1.9839.2.1.1.102
        mal-low-wat-pres OBJECT-TYPE
                    SYNTAX Integer32 (0..1)
                    UNITS "N/A"
                    MAX-ACCESS read-only
                    STATUS current
                    DESCRIPTION "WATER PRESSURE ABOVE MAXIMUM LIMIT"
                    ::= { digitalObjects 102 }

        -- 1.3.6.1.4.1.9839.2.1.1.103
        mal-hi-wat-pres OBJECT-TYPE
                    SYNTAX Integer32 (0..1)
                    UNITS "N/A"
                    MAX-ACCESS read-only
                    STATUS current
                    DESCRIPTION "WATER PRESSURE BELOW LOW LIMIT"
                    ::= { digitalObjects 103 }

        -- 1.3.6.1.4.1.9839.2.1.1.104
        mal-ups OBJECT-TYPE
                    SYNTAX Integer32 (0..1)
                    UNITS "N/A"
                    MAX-ACCESS read-only
                    STATUS current
                    DESCRIPTION "EXTERNAL UPS ALARM"
                    ::= { digitalObjects 104 }

        -- 1.3.6.1.4.1.9839.2.1.1.107
        failure-c1 OBJECT-TYPE
                    SYNTAX Integer32 (0..1)
                    UNITS "N/A"
                    MAX-ACCESS read-only
                    STATUS current
                    DESCRIPTION "ALARM COMPRESSOR 1"
                    ::= { digitalObjects 107 }

        -- 1.3.6.1.4.1.9839.2.1.1.108
        failure-c2 OBJECT-TYPE
                    SYNTAX Integer32 (0..1)
                    UNITS "N/A"
                    MAX-ACCESS read-only
                    STATUS current
                    DESCRIPTION "ALARM COMPRESSOR 2"
                    ::= { digitalObjects 108 }

        -- 1.3.6.1.4.1.9839.2.1.1.109
        failure-c3 OBJECT-TYPE
                    SYNTAX Integer32 (0..1)
                    UNITS "N/A"
                    MAX-ACCESS read-only
                    STATUS current
                    DESCRIPTION "ALARM COMPRESSOR 3"
                    ::= { digitalObjects 109 }

        -- 1.3.6.1.4.1.9839.2.1.1.111
        mal-hcurr OBJECT-TYPE
                    SYNTAX Integer32 (0..1)
                    UNITS "N/A"
                    MAX-ACCESS read-only
                    STATUS current
                    DESCRIPTION "AL. COMPRESSOR 1  HIGH CURRENT "
                    ::= { digitalObjects 111 }

        -- 1.3.6.1.4.1.9839.2.1.1.112
        mal-hcurr-c2 OBJECT-TYPE
                    SYNTAX Integer32 (0..1)
                    UNITS "N/A"
                    MAX-ACCESS read-only
                    STATUS current
                    DESCRIPTION "AL. COMPRESSOR 2  HIGH CURRENT "
                    ::= { digitalObjects 112 }

        -- 1.3.6.1.4.1.9839.2.1.1.113
        mal-hcurr-c3 OBJECT-TYPE
                    SYNTAX Integer32 (0..1)
                    UNITS "N/A"
                    MAX-ACCESS read-only
                    STATUS current
                    DESCRIPTION "AL. COMPRESSOR 3  HIGH CURRENT "
                    ::= { digitalObjects 113 }

        -- 1.3.6.1.4.1.9839.2.1.1.115
        mal-cavity-ht OBJECT-TYPE
                    SYNTAX Integer32 (0..1)
                    UNITS "N/A"
                    MAX-ACCESS read-only
                    STATUS current
                    DESCRIPTION "AL. COMPR. 1  HIGH TEMPERATURE CAVITY ANOMALY"
                    ::= { digitalObjects 115 }

        -- 1.3.6.1.4.1.9839.2.1.1.116
        mal-cavity-ht-c2 OBJECT-TYPE
                    SYNTAX Integer32 (0..1)
                    UNITS "N/A"
                    MAX-ACCESS read-only
                    STATUS current
                    DESCRIPTION "AL. COMPR. 2  HIGH TEMPERATURE CAVITY ANOMALY"
                    ::= { digitalObjects 116 }

        -- 1.3.6.1.4.1.9839.2.1.1.117
        mal-cavity-ht-c3 OBJECT-TYPE
                    SYNTAX Integer32 (0..1)
                    UNITS "N/A"
                    MAX-ACCESS read-only
                    STATUS current
                    DESCRIPTION "AL. COMPR. 3  HIGH TEMPERATURE CAVITY ANOMALY"
                    ::= { digitalObjects 117 }

        -- 1.3.6.1.4.1.9839.2.1.1.119
        mal-hrt-cmpr OBJECT-TYPE
                    SYNTAX Integer32 (0..1)
                    UNITS "N/A"
                    MAX-ACCESS read-only
                    STATUS current
                    DESCRIPTION "AL. COMPR. 1  TOT COMPRESSION RATIO ANOMALY"
                    ::= { digitalObjects 119 }

        -- 1.3.6.1.4.1.9839.2.1.1.120
        mal-hrt-cmpr-c2 OBJECT-TYPE
                    SYNTAX Integer32 (0..1)
                    UNITS "N/A"
                    MAX-ACCESS read-only
                    STATUS current
                    DESCRIPTION "AL. COMPR. 2  TOT COMPRESSION RATIO ANOMALY"
                    ::= { digitalObjects 120 }

        -- 1.3.6.1.4.1.9839.2.1.1.121
        mal-hrt-cmpr-c3 OBJECT-TYPE
                    SYNTAX Integer32 (0..1)
                    UNITS "N/A"
                    MAX-ACCESS read-only
                    STATUS current
                    DESCRIPTION "AL. COMPR. 3  TOT COMPRESSION RATIO ANOMALY"
                    ::= { digitalObjects 121 }

        -- 1.3.6.1.4.1.9839.2.1.1.123
        mal-bearing OBJECT-TYPE
                    SYNTAX Integer32 (0..1)
                    UNITS "N/A"
                    MAX-ACCESS read-only
                    STATUS current
                    DESCRIPTION "AL. COMPRESSOR 1  BEARING MOTOR FAULT "
                    ::= { digitalObjects 123 }

        -- 1.3.6.1.4.1.9839.2.1.1.124
        mal-bearing-c2 OBJECT-TYPE
                    SYNTAX Integer32 (0..1)
                    UNITS "N/A"
                    MAX-ACCESS read-only
                    STATUS current
                    DESCRIPTION "AL. COMPRESSOR 2  BEARING MOTOR FAULT "
                    ::= { digitalObjects 124 }

        -- 1.3.6.1.4.1.9839.2.1.1.125
        mal-bearing-c3 OBJECT-TYPE
                    SYNTAX Integer32 (0..1)
                    UNITS "N/A"
                    MAX-ACCESS read-only
                    STATUS current
                    DESCRIPTION "AL. COMPRESSOR 3  BEARING MOTOR FAULT "
                    ::= { digitalObjects 125 }

        -- 1.3.6.1.4.1.9839.2.1.1.127
        mal-ht-scr OBJECT-TYPE
                    SYNTAX Integer32 (0..1)
                    UNITS "N/A"
                    MAX-ACCESS read-only
                    STATUS current
                    DESCRIPTION "AL. COMPRESSOR 1 SCR HIGH TEMPERATURE"
                    ::= { digitalObjects 127 }

        -- 1.3.6.1.4.1.9839.2.1.1.128
        mal-ht-scr-c2 OBJECT-TYPE
                    SYNTAX Integer32 (0..1)
                    UNITS "N/A"
                    MAX-ACCESS read-only
                    STATUS current
                    DESCRIPTION "AL. COMPRESSOR 2 SCR HIGH TEMPERATURE"
                    ::= { digitalObjects 128 }

        -- 1.3.6.1.4.1.9839.2.1.1.129
        mal-ht-scr-c3 OBJECT-TYPE
                    SYNTAX Integer32 (0..1)
                    UNITS "N/A"
                    MAX-ACCESS read-only
                    STATUS current
                    DESCRIPTION "AL. COMPRESSOR 3 SCR HIGH TEMPERATURE"
                    ::= { digitalObjects 129 }

        -- 1.3.6.1.4.1.9839.2.1.1.131
        mlow-voltage1 OBJECT-TYPE
                    SYNTAX Integer32 (0..1)
                    UNITS "N/A"
                    MAX-ACCESS read-only
                    STATUS current
                    DESCRIPTION "AL. COMPRESSOR 1 DC-BUS VOLTAGE BELOW ACCEPTABLE MINIMUM VALUE"
                    ::= { digitalObjects 131 }

        -- 1.3.6.1.4.1.9839.2.1.1.132
        mlow-voltage2 OBJECT-TYPE
                    SYNTAX Integer32 (0..1)
                    UNITS "N/A"
                    MAX-ACCESS read-only
                    STATUS current
                    DESCRIPTION "AL. COMPRESSOR 2 DC-BUS VOLTAGE BELOW ACCEPTABLE MINIMUM VALUE"
                    ::= { digitalObjects 132 }

        -- 1.3.6.1.4.1.9839.2.1.1.133
        mlow-voltage3 OBJECT-TYPE
                    SYNTAX Integer32 (0..1)
                    UNITS "N/A"
                    MAX-ACCESS read-only
                    STATUS current
                    DESCRIPTION "AL. COMPRESSOR 3 DC-BUS VOLTAGE BELOW ACCEPTABLE MINIMUM VALUE"
                    ::= { digitalObjects 133 }

        -- 1.3.6.1.4.1.9839.2.1.1.134
        mlow-voltage4 OBJECT-TYPE
                    SYNTAX Integer32 (0..1)
                    UNITS "N/A"
                    MAX-ACCESS read-only
                    STATUS current
                    DESCRIPTION "AL. COMPRESSOR 4 DC-BUS VOLTAGE BELOW ACCEPTABLE MINIMUM VALUE"
                    ::= { digitalObjects 134 }

        -- 1.3.6.1.4.1.9839.2.1.1.135
        mal-sensor-fail OBJECT-TYPE
                    SYNTAX Integer32 (0..1)
                    UNITS "N/A"
                    MAX-ACCESS read-only
                    STATUS current
                    DESCRIPTION "AL. COMPRESSOR 1  SENSORE FAULT"
                    ::= { digitalObjects 135 }

        -- 1.3.6.1.4.1.9839.2.1.1.136
        mal-sensor-fail-c2 OBJECT-TYPE
                    SYNTAX Integer32 (0..1)
                    UNITS "N/A"
                    MAX-ACCESS read-only
                    STATUS current
                    DESCRIPTION "AL. COMPRESSOR 2  SENSORE FAULT"
                    ::= { digitalObjects 136 }

        -- 1.3.6.1.4.1.9839.2.1.1.137
        mal-sensor-fail-c3 OBJECT-TYPE
                    SYNTAX Integer32 (0..1)
                    UNITS "N/A"
                    MAX-ACCESS read-only
                    STATUS current
                    DESCRIPTION "AL. COMPRESSOR 3  SENSORE FAULT"
                    ::= { digitalObjects 137 }

        -- 1.3.6.1.4.1.9839.2.1.1.139
        mal-inv-ht OBJECT-TYPE
                    SYNTAX Integer32 (0..1)
                    UNITS "N/A"
                    MAX-ACCESS read-only
                    STATUS current
                    DESCRIPTION "AL. COMPRESSOR 1 INVERTER HIGH TEMPERATURE"
                    ::= { digitalObjects 139 }

        -- 1.3.6.1.4.1.9839.2.1.1.140
        mal-inv-ht-c2 OBJECT-TYPE
                    SYNTAX Integer32 (0..1)
                    UNITS "N/A"
                    MAX-ACCESS read-only
                    STATUS current
                    DESCRIPTION "AL. COMPRESSOR 2 INVERTER HIGH TEMPERATURE"
                    ::= { digitalObjects 140 }

        -- 1.3.6.1.4.1.9839.2.1.1.141
        mal-inv-ht-c3 OBJECT-TYPE
                    SYNTAX Integer32 (0..1)
                    UNITS "N/A"
                    MAX-ACCESS read-only
                    STATUS current
                    DESCRIPTION "AL. COMPRESSOR 3 INVERTER HIGH TEMPERATURE"
                    ::= { digitalObjects 141 }

        -- 1.3.6.1.4.1.9839.2.1.1.143
        mal-disch-ht OBJECT-TYPE
                    SYNTAX Integer32 (0..1)
                    UNITS "N/A"
                    MAX-ACCESS read-only
                    STATUS current
                    DESCRIPTION "AL. COMPRESSOR 1 HIGH DISCHARGE TEMPERATURE"
                    ::= { digitalObjects 143 }

        -- 1.3.6.1.4.1.9839.2.1.1.144
        mal-disch-ht-c2 OBJECT-TYPE
                    SYNTAX Integer32 (0..1)
                    UNITS "N/A"
                    MAX-ACCESS read-only
                    STATUS current
                    DESCRIPTION "AL. COMPRESSOR 2 HIGH DISCHARGE TEMPERATURE"
                    ::= { digitalObjects 144 }

        -- 1.3.6.1.4.1.9839.2.1.1.145
        mal-disch-ht-c3 OBJECT-TYPE
                    SYNTAX Integer32 (0..1)
                    UNITS "N/A"
                    MAX-ACCESS read-only
                    STATUS current
                    DESCRIPTION "AL. COMPRESSOR 3 HIGH DISCHARGE TEMPERATURE"
                    ::= { digitalObjects 145 }

        -- 1.3.6.1.4.1.9839.2.1.1.147
        or-al-exv-auto OBJECT-TYPE
                    SYNTAX Integer32 (0..1)
                    UNITS "N/A"
                    MAX-ACCESS read-only
                    STATUS current
                    DESCRIPTION "COMMISSIONING ERROR EXPANSION VALVE"
                    ::= { digitalObjects 147 }

        -- 1.3.6.1.4.1.9839.2.1.1.201
        k-syson OBJECT-TYPE
                    SYNTAX Integer32 (0..1)
                    UNITS "N/A"
                    MAX-ACCESS read-write
                    STATUS current
                    DESCRIPTION "UNIT REMOTE SWITCH-ON/OFF CONTROL"
                    ::= { digitalObjects 201 }

        -- 1.3.6.1.4.1.9839.2.1.1.202
        sleep-mode OBJECT-TYPE
                    SYNTAX Integer32 (0..1)
                    UNITS "N/A"
                    MAX-ACCESS read-write
                    STATUS current
                    DESCRIPTION "SET BACK MODE (SLEEP MODE)"
                    ::= { digitalObjects 202 }

        -- 1.3.6.1.4.1.9839.2.1.1.203
        xs-res-al OBJECT-TYPE
                    SYNTAX Integer32 (0..1)
                    UNITS "N/A"
                    MAX-ACCESS read-write
                    STATUS current
                    DESCRIPTION "BUZZER AND ALARM REMOTE RESET CONTROL"
                    ::= { digitalObjects 203 }

        -- 1.3.6.1.4.1.9839.2.1.1.204
        res-socomec OBJECT-TYPE
                    SYNTAX Integer32 (0..1)
                    UNITS "N/A"
                    MAX-ACCESS read-write
                    STATUS current
                    DESCRIPTION "SOCOMEC RESET"
                    ::= { digitalObjects 204 }

        -- 1.3.6.1.4.1.9839.2.1.1.205
        lowp-sp OBJECT-TYPE
                    SYNTAX Integer32 (0..1)
                    UNITS "N/A"
                    MAX-ACCESS read-write
                    STATUS current
                    DESCRIPTION "LOW POWER REQUEST"
                    ::= { digitalObjects 205 }



        -- 1.3.6.1.4.1.9839.2.1.2
        analogObjects OBJECT IDENTIFIER ::= { bceMIB 2 }

        -- 1.3.6.1.4.1.9839.2.1.2.1
        temp-wout OBJECT-TYPE
                    SYNTAX Integer32 (12345..12345)
                    UNITS "C x10"
                    MAX-ACCESS read-only
                    STATUS current
                    DESCRIPTION "WATER OUT TEMPERATURE"
                    ::= { analogObjects 1 }

        -- 1.3.6.1.4.1.9839.2.1.2.2
        temp-win OBJECT-TYPE
                    SYNTAX Integer32 (12345..12345)
                    UNITS "C x10"
                    MAX-ACCESS read-only
                    STATUS current
                    DESCRIPTION "WATER INPUT TEMPERATURE"
                    ::= { analogObjects 2 }

        -- 1.3.6.1.4.1.9839.2.1.2.3
        press-dischc-dbar OBJECT-TYPE
                    SYNTAX Integer32 (12345..12345)
                    UNITS "bar x10"
                    MAX-ACCESS read-only
                    STATUS current
                    DESCRIPTION "REFRIGERANT DISCHARGE PRESSURE"
                    ::= { analogObjects 3 }

        -- 1.3.6.1.4.1.9839.2.1.2.4
        press-evap-dbar OBJECT-TYPE
                    SYNTAX Integer32 (12345..12345)
                    UNITS "bar x10"
                    MAX-ACCESS read-only
                    STATUS current
                    DESCRIPTION "EVAPORATOR REFRIGERANT PRESSURE"
                    ::= { analogObjects 4 }

        -- 1.3.6.1.4.1.9839.2.1.2.5
        temp-evap OBJECT-TYPE
                    SYNTAX Integer32 (12345..12345)
                    UNITS "C x10"
                    MAX-ACCESS read-only
                    STATUS current
                    DESCRIPTION "COMPRESSOR 1  EVAPORATOR TEMPERATURE"
                    ::= { analogObjects 5 }

        -- 1.3.6.1.4.1.9839.2.1.2.6
        temp-evap-c2 OBJECT-TYPE
                    SYNTAX Integer32 (12345..12345)
                    UNITS "C x10"
                    MAX-ACCESS read-only
                    STATUS current
                    DESCRIPTION "COMPRESSOR 2  EVAPORATOR TEMPERATURE"
                    ::= { analogObjects 6 }

        -- 1.3.6.1.4.1.9839.2.1.2.7
        temp-evap-c3 OBJECT-TYPE
                    SYNTAX Integer32 (12345..12345)
                    UNITS "C x10"
                    MAX-ACCESS read-only
                    STATUS current
                    DESCRIPTION "COMPRESSOR 3  EVAPORATOR TEMPERATURE"
                    ::= { analogObjects 7 }

        -- 1.3.6.1.4.1.9839.2.1.2.9
        temp-cond OBJECT-TYPE
                    SYNTAX Integer32 (12345..12345)
                    UNITS "C x10"
                    MAX-ACCESS read-only
                    STATUS current
                    DESCRIPTION "COMPRESSOR 1  CONDENSING TEMPERATURE"
                    ::= { analogObjects 9 }

        -- 1.3.6.1.4.1.9839.2.1.2.10
        temp-cond-c2 OBJECT-TYPE
                    SYNTAX Integer32 (12345..12345)
                    UNITS "C x10"
                    MAX-ACCESS read-only
                    STATUS current
                    DESCRIPTION "COMPRESSOR 2  CONDENSING TEMPERATURE"
                    ::= { analogObjects 10 }

        -- 1.3.6.1.4.1.9839.2.1.2.11
        temp-cond-c3 OBJECT-TYPE
                    SYNTAX Integer32 (12345..12345)
                    UNITS "C x10"
                    MAX-ACCESS read-only
                    STATUS current
                    DESCRIPTION "COMPRESSOR 3  CONDENSING TEMPERATURE"
                    ::= { analogObjects 11 }

        -- 1.3.6.1.4.1.9839.2.1.2.13
        temp-liq OBJECT-TYPE
                    SYNTAX Integer32 (12345..12345)
                    UNITS "C x10"
                    MAX-ACCESS read-only
                    STATUS current
                    DESCRIPTION "LIQUID TEMPERATURE"
                    ::= { analogObjects 13 }

        -- 1.3.6.1.4.1.9839.2.1.2.14
        t-cond-pco OBJECT-TYPE
                    SYNTAX Integer32 (12345..12345)
                    UNITS "C x10"
                    MAX-ACCESS read-only
                    STATUS current
                    DESCRIPTION "LIQUID SATURATED TEMPERATURE"
                    ::= { analogObjects 14 }

        -- 1.3.6.1.4.1.9839.2.1.2.15
        subcooling OBJECT-TYPE
                    SYNTAX Integer32 (12345..12345)
                    UNITS "C x10"
                    MAX-ACCESS read-only
                    STATUS current
                    DESCRIPTION "SUBCOOLING"
                    ::= { analogObjects 15 }

        -- 1.3.6.1.4.1.9839.2.1.2.16
        superheat OBJECT-TYPE
                    SYNTAX Integer32 (12345..12345)
                    UNITS "C x10"
                    MAX-ACCESS read-only
                    STATUS current
                    DESCRIPTION "COMPRESSORE 1 SUPERHEAT"
                    ::= { analogObjects 16 }

        -- 1.3.6.1.4.1.9839.2.1.2.17
        superheat-c2 OBJECT-TYPE
                    SYNTAX Integer32 (12345..12345)
                    UNITS "C x10"
                    MAX-ACCESS read-only
                    STATUS current
                    DESCRIPTION "COMPRESSORE 2 SUPERHEAT"
                    ::= { analogObjects 17 }

        -- 1.3.6.1.4.1.9839.2.1.2.18
        superheat-c3 OBJECT-TYPE
                    SYNTAX Integer32 (12345..12345)
                    UNITS "C x10"
                    MAX-ACCESS read-only
                    STATUS current
                    DESCRIPTION "COMPRESSORE 3 SUPERHEAT"
                    ::= { analogObjects 18 }

        -- 1.3.6.1.4.1.9839.2.1.2.20
        suct-press OBJECT-TYPE
                    SYNTAX Integer32 (12345..12345)
                    UNITS "kPa x10"
                    MAX-ACCESS read-only
                    STATUS current
                    DESCRIPTION "COMPRESSOR 1  EVAPORATOR PRESSURE"
                    ::= { analogObjects 20 }

        -- 1.3.6.1.4.1.9839.2.1.2.21
        suct-press-c2 OBJECT-TYPE
                    SYNTAX Integer32 (12345..12345)
                    UNITS "kPa x10"
                    MAX-ACCESS read-only
                    STATUS current
                    DESCRIPTION "COMPRESSOR 2  EVAPORATOR PRESSURE"
                    ::= { analogObjects 21 }

        -- 1.3.6.1.4.1.9839.2.1.2.22
        suct-press-c3 OBJECT-TYPE
                    SYNTAX Integer32 (12345..12345)
                    UNITS "kPa x10"
                    MAX-ACCESS read-only
                    STATUS current
                    DESCRIPTION "COMPRESSOR 3  EVAPORATOR PRESSURE"
                    ::= { analogObjects 22 }

        -- 1.3.6.1.4.1.9839.2.1.2.24
        disch-press OBJECT-TYPE
                    SYNTAX Integer32 (12345..12345)
                    UNITS "kPa x10"
                    MAX-ACCESS read-only
                    STATUS current
                    DESCRIPTION "COMPRESSOR 1  CONDENSING PRESSURE"
                    ::= { analogObjects 24 }

        -- 1.3.6.1.4.1.9839.2.1.2.25
        disch-press-c2 OBJECT-TYPE
                    SYNTAX Integer32 (12345..12345)
                    UNITS "kPa x10"
                    MAX-ACCESS read-only
                    STATUS current
                    DESCRIPTION "COMPRESSOR 2  CONDENSING PRESSURE"
                    ::= { analogObjects 25 }

        -- 1.3.6.1.4.1.9839.2.1.2.26
        disch-press-c3 OBJECT-TYPE
                    SYNTAX Integer32 (12345..12345)
                    UNITS "kPa x10"
                    MAX-ACCESS read-only
                    STATUS current
                    DESCRIPTION "COMPRESSOR 3  CONDENSING PRESSURE"
                    ::= { analogObjects 26 }

        -- 1.3.6.1.4.1.9839.2.1.2.28
        press-condc OBJECT-TYPE
                    SYNTAX Integer32 (12345..12345)
                    UNITS "kPa x10"
                    MAX-ACCESS read-only
                    STATUS current
                    DESCRIPTION "LIQUID PRESSURE"
                    ::= { analogObjects 28 }

        -- 1.3.6.1.4.1.9839.2.1.2.29
        disch-temp OBJECT-TYPE
                    SYNTAX Integer32 (12345..12345)
                    UNITS "C x10"
                    MAX-ACCESS read-only
                    STATUS current
                    DESCRIPTION "COMPRESSORE 1 DISCHARGE TEMPERATURE"
                    ::= { analogObjects 29 }

        -- 1.3.6.1.4.1.9839.2.1.2.30
        disch-temp-c2 OBJECT-TYPE
                    SYNTAX Integer32 (12345..12345)
                    UNITS "C x10"
                    MAX-ACCESS read-only
                    STATUS current
                    DESCRIPTION "COMPRESSORE 2 DISCHARGE TEMPERATURE"
                    ::= { analogObjects 30 }

        -- 1.3.6.1.4.1.9839.2.1.2.31
        disch-temp-c3 OBJECT-TYPE
                    SYNTAX Integer32 (12345..12345)
                    UNITS "C x10"
                    MAX-ACCESS read-only
                    STATUS current
                    DESCRIPTION "COMPRESSORE 3 DISCHARGE TEMPERATURE"
                    ::= { analogObjects 31 }

        -- 1.3.6.1.4.1.9839.2.1.2.33
        scr-temp OBJECT-TYPE
                    SYNTAX Integer32 (12345..12345)
                    UNITS "C x10"
                    MAX-ACCESS read-only
                    STATUS current
                    DESCRIPTION "COMPRESSORE 1 SCR TEMPERATURE"
                    ::= { analogObjects 33 }

        -- 1.3.6.1.4.1.9839.2.1.2.34
        scr-temp-c2 OBJECT-TYPE
                    SYNTAX Integer32 (12345..12345)
                    UNITS "C x10"
                    MAX-ACCESS read-only
                    STATUS current
                    DESCRIPTION "COMPRESSORE 2 SCR TEMPERATURE"
                    ::= { analogObjects 34 }

        -- 1.3.6.1.4.1.9839.2.1.2.35
        scr-temp-c3 OBJECT-TYPE
                    SYNTAX Integer32 (12345..12345)
                    UNITS "C x10"
                    MAX-ACCESS read-only
                    STATUS current
                    DESCRIPTION "COMPRESSORE 3 SCR TEMPERATURE"
                    ::= { analogObjects 35 }

        -- 1.3.6.1.4.1.9839.2.1.2.37
        cav-temp OBJECT-TYPE
                    SYNTAX Integer32 (12345..12345)
                    UNITS "C x10"
                    MAX-ACCESS read-only
                    STATUS current
                    DESCRIPTION "COMPRESSORE 1 CAVITY TEMPERATURE"
                    ::= { analogObjects 37 }

        -- 1.3.6.1.4.1.9839.2.1.2.38
        cav-temp-c2 OBJECT-TYPE
                    SYNTAX Integer32 (12345..12345)
                    UNITS "C x10"
                    MAX-ACCESS read-only
                    STATUS current
                    DESCRIPTION "COMPRESSORE 2 CAVITY TEMPERATURE"
                    ::= { analogObjects 38 }

        -- 1.3.6.1.4.1.9839.2.1.2.39
        cav-temp-c3 OBJECT-TYPE
                    SYNTAX Integer32 (12345..12345)
                    UNITS "C x10"
                    MAX-ACCESS read-only
                    STATUS current
                    DESCRIPTION "COMPRESSORE 3 CAVITY TEMPERATURE"
                    ::= { analogObjects 39 }

        -- 1.3.6.1.4.1.9839.2.1.2.41
        bmc-temp OBJECT-TYPE
                    SYNTAX Integer32 (12345..12345)
                    UNITS "C x10"
                    MAX-ACCESS read-only
                    STATUS current
                    DESCRIPTION "COMPRESSORE 1 BMC TEMPERATURE"
                    ::= { analogObjects 41 }

        -- 1.3.6.1.4.1.9839.2.1.2.42
        bmc-temp-c2 OBJECT-TYPE
                    SYNTAX Integer32 (12345..12345)
                    UNITS "C x10"
                    MAX-ACCESS read-only
                    STATUS current
                    DESCRIPTION "COMPRESSORE 2 BMC TEMPERATURE"
                    ::= { analogObjects 42 }

        -- 1.3.6.1.4.1.9839.2.1.2.43
        bmc-temp-c3 OBJECT-TYPE
                    SYNTAX Integer32 (12345..12345)
                    UNITS "C x10"
                    MAX-ACCESS read-only
                    STATUS current
                    DESCRIPTION "COMPRESSORE 3 BMC TEMPERATURE"
                    ::= { analogObjects 43 }

        -- 1.3.6.1.4.1.9839.2.1.2.45
        bpl-temp OBJECT-TYPE
                    SYNTAX Integer32 (12345..12345)
                    UNITS "C x10"
                    MAX-ACCESS read-only
                    STATUS current
                    DESCRIPTION "COMPRESSORE 1 BACKPLANE PCB"
                    ::= { analogObjects 45 }

        -- 1.3.6.1.4.1.9839.2.1.2.46
        bpl-temp-c2 OBJECT-TYPE
                    SYNTAX Integer32 (12345..12345)
                    UNITS "C x10"
                    MAX-ACCESS read-only
                    STATUS current
                    DESCRIPTION "COMPRESSORE 2 BACKPLANE PCB"
                    ::= { analogObjects 46 }

        -- 1.3.6.1.4.1.9839.2.1.2.47
        bpl-temp-c3 OBJECT-TYPE
                    SYNTAX Integer32 (12345..12345)
                    UNITS "C x10"
                    MAX-ACCESS read-only
                    STATUS current
                    DESCRIPTION "COMPRESSORE 3 BACKPLANE PCB"
                    ::= { analogObjects 47 }

        -- 1.3.6.1.4.1.9839.2.1.2.49
        inverter-temp OBJECT-TYPE
                    SYNTAX Integer32 (12345..12345)
                    UNITS "C x10"
                    MAX-ACCESS read-only
                    STATUS current
                    DESCRIPTION "COMPRESSOR 1 INVERTER TEMPERATURE"
                    ::= { analogObjects 49 }

        -- 1.3.6.1.4.1.9839.2.1.2.50
        inverter-temp-c2 OBJECT-TYPE
                    SYNTAX Integer32 (12345..12345)
                    UNITS "C x10"
                    MAX-ACCESS read-only
                    STATUS current
                    DESCRIPTION "COMPRESSOR 2 INVERTER TEMPERATURE"
                    ::= { analogObjects 50 }

        -- 1.3.6.1.4.1.9839.2.1.2.51
        inverter-temp-c3 OBJECT-TYPE
                    SYNTAX Integer32 (12345..12345)
                    UNITS "C x10"
                    MAX-ACCESS read-only
                    STATUS current
                    DESCRIPTION "COMPRESSOR 3 INVERTER TEMPERATURE"
                    ::= { analogObjects 51 }

        -- 1.3.6.1.4.1.9839.2.1.2.53
        cool-request OBJECT-TYPE
                    SYNTAX Integer32 (12345..12345)
                    UNITS "% x10"
                    MAX-ACCESS read-only
                    STATUS current
                    DESCRIPTION "COMPRESSOR 1 POWER DEMAND"
                    ::= { analogObjects 53 }

        -- 1.3.6.1.4.1.9839.2.1.2.54
        cool-request-c2 OBJECT-TYPE
                    SYNTAX Integer32 (12345..12345)
                    UNITS "% x10"
                    MAX-ACCESS read-only
                    STATUS current
                    DESCRIPTION "COMPRESSOR 2 POWER DEMAND"
                    ::= { analogObjects 54 }

        -- 1.3.6.1.4.1.9839.2.1.2.55
        cool-request-c3 OBJECT-TYPE
                    SYNTAX Integer32 (12345..12345)
                    UNITS "% x10"
                    MAX-ACCESS read-only
                    STATUS current
                    DESCRIPTION "COMPRESSOR 3 POWER DEMAND"
                    ::= { analogObjects 55 }

        -- 1.3.6.1.4.1.9839.2.1.2.57
        igv OBJECT-TYPE
                    SYNTAX Integer32 (12345..12345)
                    UNITS "% x10"
                    MAX-ACCESS read-only
                    STATUS current
                    DESCRIPTION "COMPRESSOR 1 INLET GUIDE VANE"
                    ::= { analogObjects 57 }

        -- 1.3.6.1.4.1.9839.2.1.2.58
        igv-c2 OBJECT-TYPE
                    SYNTAX Integer32 (12345..12345)
                    UNITS "% x10"
                    MAX-ACCESS read-only
                    STATUS current
                    DESCRIPTION "COMPRESSOR 2 INLET GUIDE VANE"
                    ::= { analogObjects 58 }

        -- 1.3.6.1.4.1.9839.2.1.2.59
        igv-c3 OBJECT-TYPE
                    SYNTAX Integer32 (12345..12345)
                    UNITS "% x10"
                    MAX-ACCESS read-only
                    STATUS current
                    DESCRIPTION "COMPRESSOR 3 INLET GUIDE VANE"
                    ::= { analogObjects 59 }

        -- 1.3.6.1.4.1.9839.2.1.2.61
        exv1-pos OBJECT-TYPE
                    SYNTAX Integer32 (12345..12345)
                    UNITS "% x10"
                    MAX-ACCESS read-only
                    STATUS current
                    DESCRIPTION "COMPR. 1 ELECTRONIC VALVE POSITION"
                    ::= { analogObjects 61 }

        -- 1.3.6.1.4.1.9839.2.1.2.62
        exv1-pos-c2 OBJECT-TYPE
                    SYNTAX Integer32 (12345..12345)
                    UNITS "% x10"
                    MAX-ACCESS read-only
                    STATUS current
                    DESCRIPTION "COMPR. 2 ELECTRONIC VALVE POSITION"
                    ::= { analogObjects 62 }

        -- 1.3.6.1.4.1.9839.2.1.2.63
        exv1-pos-c3 OBJECT-TYPE
                    SYNTAX Integer32 (12345..12345)
                    UNITS "% x10"
                    MAX-ACCESS read-only
                    STATUS current
                    DESCRIPTION "COMPR. 3 ELECTRONIC VALVE POSITION"
                    ::= { analogObjects 63 }

        -- 1.3.6.1.4.1.9839.2.1.2.65
        evap-level-m OBJECT-TYPE
                    SYNTAX Integer32 (12345..12345)
                    UNITS "% x10"
                    MAX-ACCESS read-only
                    STATUS current
                    DESCRIPTION "EVAPORATOR ACTUAL LEVEL"
                    ::= { analogObjects 65 }

        -- 1.3.6.1.4.1.9839.2.1.2.66
        main-power OBJECT-TYPE
                    SYNTAX Integer32 (12345..12345)
                    UNITS "kW x10"
                    MAX-ACCESS read-only
                    STATUS current
                    DESCRIPTION "COMPRESSORE 1 ACTUAL POWER DEMAND"
                    ::= { analogObjects 66 }

        -- 1.3.6.1.4.1.9839.2.1.2.67
        main-power-c2 OBJECT-TYPE
                    SYNTAX Integer32 (12345..12345)
                    UNITS "kW x10"
                    MAX-ACCESS read-only
                    STATUS current
                    DESCRIPTION "COMPRESSORE 2 ACTUAL POWER DEMAND"
                    ::= { analogObjects 67 }

        -- 1.3.6.1.4.1.9839.2.1.2.68
        main-power-c3 OBJECT-TYPE
                    SYNTAX Integer32 (12345..12345)
                    UNITS "kW x10"
                    MAX-ACCESS read-only
                    STATUS current
                    DESCRIPTION "COMPRESSORE 3 ACTUAL POWER DEMAND"
                    ::= { analogObjects 68 }

        -- 1.3.6.1.4.1.9839.2.1.2.70
        motor-kw OBJECT-TYPE
                    SYNTAX Integer32 (12345..12345)
                    UNITS "kW x10"
                    MAX-ACCESS read-only
                    STATUS current
                    DESCRIPTION "COMPRESSORE 1 ACTUAL POWER ABSORBED"
                    ::= { analogObjects 70 }

        -- 1.3.6.1.4.1.9839.2.1.2.71
        motor-kw-c2 OBJECT-TYPE
                    SYNTAX Integer32 (12345..12345)
                    UNITS "kW x10"
                    MAX-ACCESS read-only
                    STATUS current
                    DESCRIPTION "COMPRESSORE 2 ACTUAL POWER ABSORBED"
                    ::= { analogObjects 71 }

        -- 1.3.6.1.4.1.9839.2.1.2.72
        motor-kw-c3 OBJECT-TYPE
                    SYNTAX Integer32 (12345..12345)
                    UNITS "kW x10"
                    MAX-ACCESS read-only
                    STATUS current
                    DESCRIPTION "COMPRESSORE 3 ACTUAL POWER ABSORBED"
                    ::= { analogObjects 72 }

        -- 1.3.6.1.4.1.9839.2.1.2.74
        earthcurr OBJECT-TYPE
                    SYNTAX Integer32 (12345..12345)
                    UNITS "A x10"
                    MAX-ACCESS read-only
                    STATUS current
                    DESCRIPTION "COMPRESSOR 1 EARTH CURRENT"
                    ::= { analogObjects 74 }

        -- 1.3.6.1.4.1.9839.2.1.2.75
        earthcurr-c2 OBJECT-TYPE
                    SYNTAX Integer32 (12345..12345)
                    UNITS "A x10"
                    MAX-ACCESS read-only
                    STATUS current
                    DESCRIPTION "COMPRESSOR 2 EARTH CURRENT"
                    ::= { analogObjects 75 }

        -- 1.3.6.1.4.1.9839.2.1.2.76
        earthcurr-c3 OBJECT-TYPE
                    SYNTAX Integer32 (12345..12345)
                    UNITS "A x10"
                    MAX-ACCESS read-only
                    STATUS current
                    DESCRIPTION "COMPRESSOR 3 EARTH CURRENT"
                    ::= { analogObjects 76 }

        -- 1.3.6.1.4.1.9839.2.1.2.78
        t-set-e OBJECT-TYPE
                    SYNTAX Integer32 (60..250)
                    UNITS "C x10"
                    MAX-ACCESS read-write
                    STATUS current
                    DESCRIPTION "SUMMER SETPOINT"
                    ::= { analogObjects 78 }

        -- 1.3.6.1.4.1.9839.2.1.2.79
        t-set-d OBJECT-TYPE
                    SYNTAX Integer32 (60..250)
                    UNITS "C x10"
                    MAX-ACCESS read-write
                    STATUS current
                    DESCRIPTION "SUMMER SECOND SETPOINT"
                    ::= { analogObjects 79 }

        -- 1.3.6.1.4.1.9839.2.1.2.80
        t-set-sm OBJECT-TYPE
                    SYNTAX Integer32 (60..250)
                    UNITS "C x10"
                    MAX-ACCESS read-write
                    STATUS current
                    DESCRIPTION "DEL.WATER T. SUMMER SETBACK MODE SETP."
                    ::= { analogObjects 80 }

        -- 1.3.6.1.4.1.9839.2.1.2.81
        af-alarm-set OBJECT-TYPE
                    SYNTAX Integer32 (-100..50)
                    UNITS "C x10"
                    MAX-ACCESS read-write
                    STATUS current
                    DESCRIPTION "ANTIFREEZE SETPOINT"
                    DEFVAL { 0 }
                    ::= { analogObjects 81 }

        -- 1.3.6.1.4.1.9839.2.1.2.82
        af-warm-set OBJECT-TYPE
                    SYNTAX Integer32 (-100..50)
                    UNITS "C x10"
                    MAX-ACCESS read-write
                    STATUS current
                    DESCRIPTION "ANTIFREEZE WARNING SETPOINT"
                    DEFVAL { 0 }
                    ::= { analogObjects 82 }

        -- 1.3.6.1.4.1.9839.2.1.2.83
        set-ht-win-e OBJECT-TYPE
                    SYNTAX Integer32 (-150..350)
                    UNITS "C x10"
                    MAX-ACCESS read-write
                    STATUS current
                    DESCRIPTION "CW INLET HIGH TEMP. ALARM THRESHOLD"
                    DEFVAL { 0 }
                    ::= { analogObjects 83 }

        -- 1.3.6.1.4.1.9839.2.1.2.84
        set-lt-win-e OBJECT-TYPE
                    SYNTAX Integer32 (-150..250)
                    UNITS "C x10"
                    MAX-ACCESS read-write
                    STATUS current
                    DESCRIPTION "CW INLET LOW TEMP. ALARM THRESHOLD"
                    DEFVAL { 0 }
                    ::= { analogObjects 84 }

        -- 1.3.6.1.4.1.9839.2.1.2.85
        ofs-spv OBJECT-TYPE
                    SYNTAX Integer32 (1..30)
                    UNITS "N/A"
                    MAX-ACCESS read-write
                    STATUS current
                    DESCRIPTION "OFFSET SUPERVISOR"
                    ::= { analogObjects 85 }

        -- 1.3.6.1.4.1.9839.2.1.2.101
        temp-ext OBJECT-TYPE
                    SYNTAX Integer32 (12345..12345)
                    UNITS "C x10"
                    MAX-ACCESS read-only
                    STATUS current
                    DESCRIPTION "EXTERNAL TEMPERATURE"
                    ::= { analogObjects 101 }

        -- 1.3.6.1.4.1.9839.2.1.2.102
        temp-inevap OBJECT-TYPE
                    SYNTAX Integer32 (12345..12345)
                    UNITS "C x10"
                    MAX-ACCESS read-only
                    STATUS current
                    DESCRIPTION "EVAPORATOR WATER INLET"
                    ::= { analogObjects 102 }

        -- 1.3.6.1.4.1.9839.2.1.2.103
        t-set-regol OBJECT-TYPE
                    SYNTAX Integer32 (12345..12345)
                    UNITS "C x10"
                    MAX-ACCESS read-only
                    STATUS current
                    DESCRIPTION "ACTIVE WATER SETPOINT"
                    ::= { analogObjects 103 }

        -- 1.3.6.1.4.1.9839.2.1.2.104
        offsetmodul OBJECT-TYPE
                    SYNTAX Integer32 (12345..12345)
                    UNITS "C x10"
                    MAX-ACCESS read-only
                    STATUS current
                    DESCRIPTION "REMOTE SETPOINT VALUE"
                    ::= { analogObjects 104 }

        -- 1.3.6.1.4.1.9839.2.1.2.105
        reg-ramp OBJECT-TYPE
                    SYNTAX Integer32 (12345..12345)
                    UNITS "% x10"
                    MAX-ACCESS read-only
                    STATUS current
                    DESCRIPTION "COOLING REGULATION RAMP"
                    ::= { analogObjects 105 }



        -- 1.3.6.1.4.1.9839.2.1.3
        integerObjects OBJECT IDENTIFIER ::= { bceMIB 3 }

        -- 1.3.6.1.4.1.9839.2.1.3.1
        actrpm OBJECT-TYPE
                    SYNTAX Integer32 (12345..12345)
                    UNITS "rpm"
                    MAX-ACCESS read-only
                    STATUS current
                    DESCRIPTION "COMPRESSOR 1 ACTUAL SHAFT SPEED"
                    ::= { integerObjects 1 }

        -- 1.3.6.1.4.1.9839.2.1.3.2
        actrpm-c2 OBJECT-TYPE
                    SYNTAX Integer32 (12345..12345)
                    UNITS "rpm"
                    MAX-ACCESS read-only
                    STATUS current
                    DESCRIPTION "COMPRESSOR 2 ACTUAL SHAFT SPEED"
                    ::= { integerObjects 2 }

        -- 1.3.6.1.4.1.9839.2.1.3.3
        actrpm-c3 OBJECT-TYPE
                    SYNTAX Integer32 (12345..12345)
                    UNITS "rpm"
                    MAX-ACCESS read-only
                    STATUS current
                    DESCRIPTION "COMPRESSOR 3 ACTUAL SHAFT SPEED"
                    ::= { integerObjects 3 }

        -- 1.3.6.1.4.1.9839.2.1.3.5
        surge-speed OBJECT-TYPE
                    SYNTAX Integer32 (12345..12345)
                    UNITS "rpm"
                    MAX-ACCESS read-only
                    STATUS current
                    DESCRIPTION "COMPR. 1 ESTIMATED MINIMUN SPEED"
                    ::= { integerObjects 5 }

        -- 1.3.6.1.4.1.9839.2.1.3.6
        surge-speed-c2 OBJECT-TYPE
                    SYNTAX Integer32 (12345..12345)
                    UNITS "rpm"
                    MAX-ACCESS read-only
                    STATUS current
                    DESCRIPTION "COMPR. 2 ESTIMATED MINIMUN SPEED"
                    ::= { integerObjects 6 }

        -- 1.3.6.1.4.1.9839.2.1.3.7
        surge-speed-c3 OBJECT-TYPE
                    SYNTAX Integer32 (12345..12345)
                    UNITS "rpm"
                    MAX-ACCESS read-only
                    STATUS current
                    DESCRIPTION "COMPR. 3 ESTIMATED MINIMUN SPEED"
                    ::= { integerObjects 7 }

        -- 1.3.6.1.4.1.9839.2.1.3.9
        choke-speed OBJECT-TYPE
                    SYNTAX Integer32 (12345..12345)
                    UNITS "rpm"
                    MAX-ACCESS read-only
                    STATUS current
                    DESCRIPTION "COMPR. 1 ESTIMATED MAXIMUN SPEED"
                    ::= { integerObjects 9 }

        -- 1.3.6.1.4.1.9839.2.1.3.10
        choke-speed-c2 OBJECT-TYPE
                    SYNTAX Integer32 (12345..12345)
                    UNITS "rpm"
                    MAX-ACCESS read-only
                    STATUS current
                    DESCRIPTION "COMPR. 2 ESTIMATED MAXIMUN SPEED"
                    ::= { integerObjects 10 }

        -- 1.3.6.1.4.1.9839.2.1.3.11
        choke-speed-c3 OBJECT-TYPE
                    SYNTAX Integer32 (12345..12345)
                    UNITS "rpm"
                    MAX-ACCESS read-only
                    STATUS current
                    DESCRIPTION "COMPR. 3 ESTIMATED MAXIMUN SPEED"
                    ::= { integerObjects 11 }

        -- 1.3.6.1.4.1.9839.2.1.3.13
        mains-vac OBJECT-TYPE
                    SYNTAX Integer32 (12345..12345)
                    UNITS "V"
                    MAX-ACCESS read-only
                    STATUS current
                    DESCRIPTION "COMPRESSOR 1 MAINS VOLTAGE"
                    ::= { integerObjects 13 }

        -- 1.3.6.1.4.1.9839.2.1.3.14
        mains-vac-c2 OBJECT-TYPE
                    SYNTAX Integer32 (12345..12345)
                    UNITS "V"
                    MAX-ACCESS read-only
                    STATUS current
                    DESCRIPTION "COMPRESSOR 2 MAINS VOLTAGE"
                    ::= { integerObjects 14 }

        -- 1.3.6.1.4.1.9839.2.1.3.15
        mains-vac-c3 OBJECT-TYPE
                    SYNTAX Integer32 (12345..12345)
                    UNITS "V"
                    MAX-ACCESS read-only
                    STATUS current
                    DESCRIPTION "COMPRESSOR 3 MAINS VOLTAGE"
                    ::= { integerObjects 15 }

        -- 1.3.6.1.4.1.9839.2.1.3.17
        mains-amp OBJECT-TYPE
                    SYNTAX Integer32 (12345..12345)
                    UNITS "A"
                    MAX-ACCESS read-only
                    STATUS current
                    DESCRIPTION "COMPRESSOR 1 MAINS CURRENT"
                    ::= { integerObjects 17 }

        -- 1.3.6.1.4.1.9839.2.1.3.18
        mains-amp-c2 OBJECT-TYPE
                    SYNTAX Integer32 (12345..12345)
                    UNITS "A"
                    MAX-ACCESS read-only
                    STATUS current
                    DESCRIPTION "COMPRESSOR 2 MAINS CURRENT"
                    ::= { integerObjects 18 }

        -- 1.3.6.1.4.1.9839.2.1.3.19
        mains-amp-c3 OBJECT-TYPE
                    SYNTAX Integer32 (12345..12345)
                    UNITS "A"
                    MAX-ACCESS read-only
                    STATUS current
                    DESCRIPTION "COMPRESSOR 3 MAINS CURRENT"
                    ::= { integerObjects 19 }

        -- 1.3.6.1.4.1.9839.2.1.3.21
        dc-reg OBJECT-TYPE
                    SYNTAX Integer32 (12345..12345)
                    UNITS "V"
                    MAX-ACCESS read-only
                    STATUS current
                    DESCRIPTION "COMPRESSOR 1 SPARE DC REGULATION"
                    ::= { integerObjects 21 }

        -- 1.3.6.1.4.1.9839.2.1.3.22
        dc-reg-c2 OBJECT-TYPE
                    SYNTAX Integer32 (12345..12345)
                    UNITS "V"
                    MAX-ACCESS read-only
                    STATUS current
                    DESCRIPTION "COMPRESSOR 2 SPARE DC REGULATION"
                    ::= { integerObjects 22 }

        -- 1.3.6.1.4.1.9839.2.1.3.23
        dc-reg-c3 OBJECT-TYPE
                    SYNTAX Integer32 (12345..12345)
                    UNITS "V"
                    MAX-ACCESS read-only
                    STATUS current
                    DESCRIPTION "COMPRESSOR 3 SPARE DC REGULATION"
                    ::= { integerObjects 23 }

        -- 1.3.6.1.4.1.9839.2.1.3.25
        dc-bus-volt OBJECT-TYPE
                    SYNTAX Integer32 (12345..12345)
                    UNITS "V"
                    MAX-ACCESS read-only
                    STATUS current
                    DESCRIPTION "COMPRESSOR 1 BUS VOLTAGE"
                    ::= { integerObjects 25 }

        -- 1.3.6.1.4.1.9839.2.1.3.26
        dc-bus-volt-c2 OBJECT-TYPE
                    SYNTAX Integer32 (12345..12345)
                    UNITS "V"
                    MAX-ACCESS read-only
                    STATUS current
                    DESCRIPTION "COMPRESSOR 2 BUS VOLTAGE"
                    ::= { integerObjects 26 }

        -- 1.3.6.1.4.1.9839.2.1.3.27
        dc-bus-volt-c3 OBJECT-TYPE
                    SYNTAX Integer32 (12345..12345)
                    UNITS "V"
                    MAX-ACCESS read-only
                    STATUS current
                    DESCRIPTION "COMPRESSOR 3 BUS VOLTAGE"
                    ::= { integerObjects 27 }

        -- 1.3.6.1.4.1.9839.2.1.3.29
        level-sp-calc OBJECT-TYPE
                    SYNTAX Integer32 (12345..12345)
                    UNITS "%"
                    MAX-ACCESS read-only
                    STATUS current
                    DESCRIPTION "EVAPORATOR CALCULATED LEVEL"
                    ::= { integerObjects 29 }

        -- 1.3.6.1.4.1.9839.2.1.3.30
        ore-compr1 OBJECT-TYPE
                    SYNTAX Integer32 (12345..12345)
                    UNITS "hour"
                    MAX-ACCESS read-only
                    STATUS current
                    DESCRIPTION "COMPRESSOR 1 RUN HOURS"
                    ::= { integerObjects 30 }

        -- 1.3.6.1.4.1.9839.2.1.3.31
        ore-compr2 OBJECT-TYPE
                    SYNTAX Integer32 (12345..12345)
                    UNITS "hour"
                    MAX-ACCESS read-only
                    STATUS current
                    DESCRIPTION "COMPRESSOR 2 RUN HOURS"
                    ::= { integerObjects 31 }

        -- 1.3.6.1.4.1.9839.2.1.3.32
        ore-compr3 OBJECT-TYPE
                    SYNTAX Integer32 (12345..12345)
                    UNITS "hour"
                    MAX-ACCESS read-only
                    STATUS current
                    DESCRIPTION "COMPRESSOR 3 RUN HOURS"
                    ::= { integerObjects 32 }

        -- 1.3.6.1.4.1.9839.2.1.3.33
        ore-compr4 OBJECT-TYPE
                    SYNTAX Integer32 (12345..12345)
                    UNITS "hour"
                    MAX-ACCESS read-only
                    STATUS current
                    DESCRIPTION "COMPRESSOR 4 RUN HOURS"
                    ::= { integerObjects 33 }

        -- 1.3.6.1.4.1.9839.2.1.3.34
        press-ratio-ii OBJECT-TYPE
                    SYNTAX Integer32 (12345..12345)
                    UNITS "N/A"
                    MAX-ACCESS read-only
                    STATUS current
                    DESCRIPTION "COMPRESSOR 1 PRESSURE RATIO"
                    ::= { integerObjects 34 }

        -- 1.3.6.1.4.1.9839.2.1.3.35
        press-ratio-mm OBJECT-TYPE
                    SYNTAX Integer32 (12345..12345)
                    UNITS "N/A"
                    MAX-ACCESS read-only
                    STATUS current
                    DESCRIPTION "COMPRESSOR 1 PRESSURE RATIO (X 1000)"
                    ::= { integerObjects 35 }

        -- 1.3.6.1.4.1.9839.2.1.3.36
        press-ratio-ii-c2 OBJECT-TYPE
                    SYNTAX Integer32 (12345..12345)
                    UNITS "N/A"
                    MAX-ACCESS read-only
                    STATUS current
                    DESCRIPTION "COMPRESSOR 2 PRESSURE RATIO"
                    ::= { integerObjects 36 }

        -- 1.3.6.1.4.1.9839.2.1.3.37
        press-ratio-mm-c2 OBJECT-TYPE
                    SYNTAX Integer32 (12345..12345)
                    UNITS "N/A"
                    MAX-ACCESS read-only
                    STATUS current
                    DESCRIPTION "COMPRESSOR 2 PRESSURE RATIO (X 1000)"
                    ::= { integerObjects 37 }

        -- 1.3.6.1.4.1.9839.2.1.3.38
        press-ratio-ii-c3 OBJECT-TYPE
                    SYNTAX Integer32 (12345..12345)
                    UNITS "N/A"
                    MAX-ACCESS read-only
                    STATUS current
                    DESCRIPTION "COMPRESSOR 3 PRESSURE RATIO"
                    ::= { integerObjects 38 }

        -- 1.3.6.1.4.1.9839.2.1.3.39
        press-ratio-mm-c3 OBJECT-TYPE
                    SYNTAX Integer32 (12345..12345)
                    UNITS "N/A"
                    MAX-ACCESS read-only
                    STATUS current
                    DESCRIPTION "COMPRESSOR 3 PRESSURE RATIO (X 1000)"
                    ::= { integerObjects 39 }

        -- 1.3.6.1.4.1.9839.2.1.3.42
        motor-fault OBJECT-TYPE
                    SYNTAX Integer32 (12345..12345)
                    UNITS "N/A"
                    MAX-ACCESS read-only
                    STATUS current
                    DESCRIPTION "COMPRESSOR 1 MOTOR FAULT CODE"
                    ::= { integerObjects 42 }

        -- 1.3.6.1.4.1.9839.2.1.3.43
        motor-alarm OBJECT-TYPE
                    SYNTAX Integer32 (12345..12345)
                    UNITS "N/A"
                    MAX-ACCESS read-only
                    STATUS current
                    DESCRIPTION "COMPRESSOR 1 MOTOR ALARM CODE"
                    ::= { integerObjects 43 }

        -- 1.3.6.1.4.1.9839.2.1.3.44
        bear-fault OBJECT-TYPE
                    SYNTAX Integer32 (12345..12345)
                    UNITS "N/A"
                    MAX-ACCESS read-only
                    STATUS current
                    DESCRIPTION "COMPRESSOR 1 BEARING FAULT CODE"
                    ::= { integerObjects 44 }

        -- 1.3.6.1.4.1.9839.2.1.3.45
        bear-alarm OBJECT-TYPE
                    SYNTAX Integer32 (12345..12345)
                    UNITS "N/A"
                    MAX-ACCESS read-only
                    STATUS current
                    DESCRIPTION "COMPRESSOR 1 BEARING ALARM CODE"
                    ::= { integerObjects 45 }

        -- 1.3.6.1.4.1.9839.2.1.3.46
        motor-fault-c2 OBJECT-TYPE
                    SYNTAX Integer32 (12345..12345)
                    UNITS "N/A"
                    MAX-ACCESS read-only
                    STATUS current
                    DESCRIPTION "COMPRESSOR 2 MOTOR FAULT CODE"
                    ::= { integerObjects 46 }

        -- 1.3.6.1.4.1.9839.2.1.3.47
        motor-alarm-c2 OBJECT-TYPE
                    SYNTAX Integer32 (12345..12345)
                    UNITS "N/A"
                    MAX-ACCESS read-only
                    STATUS current
                    DESCRIPTION "COMPRESSOR 2 MOTOR ALARM CODE"
                    ::= { integerObjects 47 }

        -- 1.3.6.1.4.1.9839.2.1.3.48
        bear-fault-c2 OBJECT-TYPE
                    SYNTAX Integer32 (12345..12345)
                    UNITS "N/A"
                    MAX-ACCESS read-only
                    STATUS current
                    DESCRIPTION "COMPRESSOR 2 BEARING FAULT CODE"
                    ::= { integerObjects 48 }

        -- 1.3.6.1.4.1.9839.2.1.3.49
        bear-alarm-c2 OBJECT-TYPE
                    SYNTAX Integer32 (12345..12345)
                    UNITS "N/A"
                    MAX-ACCESS read-only
                    STATUS current
                    DESCRIPTION "COMPRESSOR 2 BEARING ALARM CODE"
                    ::= { integerObjects 49 }

        -- 1.3.6.1.4.1.9839.2.1.3.50
        motor-fault-c3 OBJECT-TYPE
                    SYNTAX Integer32 (12345..12345)
                    UNITS "N/A"
                    MAX-ACCESS read-only
                    STATUS current
                    DESCRIPTION "COMPRESSOR 3 MOTOR FAULT CODE"
                    ::= { integerObjects 50 }

        -- 1.3.6.1.4.1.9839.2.1.3.51
        motor-alarm-c3 OBJECT-TYPE
                    SYNTAX Integer32 (12345..12345)
                    UNITS "N/A"
                    MAX-ACCESS read-only
                    STATUS current
                    DESCRIPTION "COMPRESSOR 3 MOTOR ALARM CODE"
                    ::= { integerObjects 51 }

        -- 1.3.6.1.4.1.9839.2.1.3.52
        bear-fault-c3 OBJECT-TYPE
                    SYNTAX Integer32 (12345..12345)
                    UNITS "N/A"
                    MAX-ACCESS read-only
                    STATUS current
                    DESCRIPTION "COMPRESSOR 3 BEARING FAULT CODE"
                    ::= { integerObjects 52 }

        -- 1.3.6.1.4.1.9839.2.1.3.53
        bear-alarm-c3 OBJECT-TYPE
                    SYNTAX Integer32 (12345..12345)
                    UNITS "N/A"
                    MAX-ACCESS read-only
                    STATUS current
                    DESCRIPTION "COMPRESSOR 3 BEARING ALARM CODE"
                    ::= { integerObjects 53 }

        -- 1.3.6.1.4.1.9839.2.1.3.58
        ctrl-mode OBJECT-TYPE
                    SYNTAX Integer32 (12345..12345)
                    UNITS "N/A"
                    MAX-ACCESS read-only
                    STATUS current
                    DESCRIPTION "COMPRESSOR 1 CTRL MODE"
                    ::= { integerObjects 58 }

        -- 1.3.6.1.4.1.9839.2.1.3.59
        ctrl-mode-c2 OBJECT-TYPE
                    SYNTAX Integer32 (12345..12345)
                    UNITS "N/A"
                    MAX-ACCESS read-only
                    STATUS current
                    DESCRIPTION "COMPRESSOR 2 CTRL MODE"
                    ::= { integerObjects 59 }

        -- 1.3.6.1.4.1.9839.2.1.3.60
        ctrl-mode-c3 OBJECT-TYPE
                    SYNTAX Integer32 (12345..12345)
                    UNITS "N/A"
                    MAX-ACCESS read-only
                    STATUS current
                    DESCRIPTION "COMPRESSOR 3 CTRL MODE"
                    ::= { integerObjects 60 }

        -- 1.3.6.1.4.1.9839.2.1.3.62
        current-minute OBJECT-TYPE
                    SYNTAX Integer32 (12345..12345)
                    UNITS "m"
                    MAX-ACCESS read-only
                    STATUS current
                    DESCRIPTION "MINUTE"
                    ::= { integerObjects 62 }

        -- 1.3.6.1.4.1.9839.2.1.3.63
        current-hour OBJECT-TYPE
                    SYNTAX Integer32 (12345..12345)
                    UNITS "hour"
                    MAX-ACCESS read-only
                    STATUS current
                    DESCRIPTION "HOUR"
                    ::= { integerObjects 63 }

        -- 1.3.6.1.4.1.9839.2.1.3.64
        current-day OBJECT-TYPE
                    SYNTAX Integer32 (12345..12345)
                    UNITS "day"
                    MAX-ACCESS read-only
                    STATUS current
                    DESCRIPTION "DAY"
                    ::= { integerObjects 64 }

        -- 1.3.6.1.4.1.9839.2.1.3.65
        current-month OBJECT-TYPE
                    SYNTAX Integer32 (12345..12345)
                    UNITS "N/A"
                    MAX-ACCESS read-only
                    STATUS current
                    DESCRIPTION "MONTH"
                    ::= { integerObjects 65 }

        -- 1.3.6.1.4.1.9839.2.1.3.66
        current-year OBJECT-TYPE
                    SYNTAX Integer32 (12345..12345)
                    UNITS "N/A"
                    MAX-ACCESS read-only
                    STATUS current
                    DESCRIPTION "YEAR"
                    ::= { integerObjects 66 }

        -- 1.3.6.1.4.1.9839.2.1.3.67
        matricola-i OBJECT-TYPE
                    SYNTAX Integer32 (12345..12345)
                    UNITS "N/A"
                    MAX-ACCESS read-only
                    STATUS current
                    DESCRIPTION "UNIT SERIAL NUMBER 1"
                    ::= { integerObjects 67 }

        -- 1.3.6.1.4.1.9839.2.1.3.68
        matricola-hn OBJECT-TYPE
                    SYNTAX Integer32 (12345..12345)
                    UNITS "N/A"
                    MAX-ACCESS read-only
                    STATUS current
                    DESCRIPTION "UNIT SERIAL NUMBER 2"
                    ::= { integerObjects 68 }

        -- 1.3.6.1.4.1.9839.2.1.3.69
        matricola-ln OBJECT-TYPE
                    SYNTAX Integer32 (12345..12345)
                    UNITS "N/A"
                    MAX-ACCESS read-only
                    STATUS current
                    DESCRIPTION "UNIT SERIAL NUMBER 3"
                    ::= { integerObjects 69 }

        -- 1.3.6.1.4.1.9839.2.1.3.71
        bios-release-l OBJECT-TYPE
                    SYNTAX Integer32 (12345..12345)
                    UNITS "N/A"
                    MAX-ACCESS read-only
                    STATUS current
                    DESCRIPTION "BIOS RELEASE 1"
                    ::= { integerObjects 71 }

        -- 1.3.6.1.4.1.9839.2.1.3.72
        bios-release-h OBJECT-TYPE
                    SYNTAX Integer32 (12345..12345)
                    UNITS "N/A"
                    MAX-ACCESS read-only
                    STATUS current
                    DESCRIPTION "BIOS RELEASE 2"
                    ::= { integerObjects 72 }

        -- 1.3.6.1.4.1.9839.2.1.3.73
        sw-versione-l OBJECT-TYPE
                    SYNTAX Integer32 (12345..12345)
                    UNITS "N/A"
                    MAX-ACCESS read-only
                    STATUS current
                    DESCRIPTION "SW RELEASE 1"
                    ::= { integerObjects 73 }

        -- 1.3.6.1.4.1.9839.2.1.3.74
        sw-versione-h OBJECT-TYPE
                    SYNTAX Integer32 (12345..12345)
                    UNITS "N/A"
                    MAX-ACCESS read-only
                    STATUS current
                    DESCRIPTION "SW RELEASE 2"
                    ::= { integerObjects 74 }

        -- 1.3.6.1.4.1.9839.2.1.3.101
        unit-type OBJECT-TYPE
                    SYNTAX Integer32 (12345..12345)
                    UNITS "N/A"
                    MAX-ACCESS read-only
                    STATUS current
                    DESCRIPTION "UNIT TYPE"
                    ::= { integerObjects 101 }


        -- 1.3.6.1.4.1.9839.2.1.3.103
        unit-model-air-cond OBJECT-TYPE
                    SYNTAX Integer32 (12345..12345)
                    UNITS "N/A"
                    MAX-ACCESS read-only
                    STATUS current
                    DESCRIPTION "BCEC C MODEL"
                    ::= { integerObjects 103 }

        -- 1.3.6.1.4.1.9839.2.1.3.104
        pump-conf OBJECT-TYPE
                    SYNTAX Integer32 (12345..12345)
                    UNITS "N/A"
                    MAX-ACCESS read-only
                    STATUS current
                    DESCRIPTION "CIRCULATION PUMP NUMBER"
                    ::= { integerObjects 104 }

        -- 1.3.6.1.4.1.9839.2.1.3.105
        pump-control-type OBJECT-TYPE
                    SYNTAX Integer32 (12345..12345)
                    UNITS "N/A"
                    MAX-ACCESS read-only
                    STATUS current
                    DESCRIPTION "INVERTER PUMP CONTROL TYPE"
                    ::= { integerObjects 105 }

        -- 1.3.6.1.4.1.9839.2.1.3.106
        fan-type OBJECT-TYPE
                    SYNTAX Integer32 (12345..12345)
                    UNITS "N/A"
                    MAX-ACCESS read-only
                    STATUS current
                    DESCRIPTION "FANS TYPE"
                    ::= { integerObjects 106 }

        -- 1.3.6.1.4.1.9839.2.1.3.107
        fan-control-type OBJECT-TYPE
                    SYNTAX Integer32 (12345..12345)
                    UNITS "N/A"
                    MAX-ACCESS read-only
                    STATUS current
                    DESCRIPTION "FANS CONTROL TYPE"
                    ::= { integerObjects 107 }

        -- 1.3.6.1.4.1.9839.2.1.3.108
        aux-type OBJECT-TYPE
                    SYNTAX Integer32 (12345..12345)
                    UNITS "N/A"
                    MAX-ACCESS read-only
                    STATUS current
                    DESCRIPTION "AUXILIARY TYPE"
                    ::= { integerObjects 108 }

        -- 1.3.6.1.4.1.9839.2.1.3.109
        isol-valve-time OBJECT-TYPE
                    SYNTAX Integer32 (12345..12345)
                    UNITS "s"
                    MAX-ACCESS read-only
                    STATUS current
                    DESCRIPTION "ISOLATING VALVE ON DELAY TIME"
                    ::= { integerObjects 109 }

        -- 1.3.6.1.4.1.9839.2.1.3.110
        power-type OBJECT-TYPE
                    SYNTAX Integer32 (12345..12345)
                    UNITS "N/A"
                    MAX-ACCESS read-only
                    STATUS current
                    DESCRIPTION "POWER TYPE"
                    ::= { integerObjects 110 }

        -- 1.3.6.1.4.1.9839.2.1.3.111
        int-time OBJECT-TYPE
                    SYNTAX Integer32 (12345..12345)
                    UNITS "s"
                    MAX-ACCESS read-only
                    STATUS current
                    DESCRIPTION "INTEGRAL TIME PID MECCANICAL COOLING"
                    ::= { integerObjects 111 }

        -- 1.3.6.1.4.1.9839.2.1.3.112
        int-time-in OBJECT-TYPE
                    SYNTAX Integer32 (12345..12345)
                    UNITS "s"
                    MAX-ACCESS read-only
                    STATUS current
                    DESCRIPTION "INTEGRAL TIME PID MECCANICAL COOLING (TRANSIENT)"
                    ::= { integerObjects 112 }

        -- 1.3.6.1.4.1.9839.2.1.3.113
        int-time-fc OBJECT-TYPE
                    SYNTAX Integer32 (12345..12345)
                    UNITS "s"
                    MAX-ACCESS read-only
                    STATUS current
                    DESCRIPTION "INTEGRAL TIME BAND PID FREECOOLING"
                    ::= { integerObjects 113 }

        -- 1.3.6.1.4.1.9839.2.1.3.114
        d-time OBJECT-TYPE
                    SYNTAX Integer32 (12345..12345)
                    UNITS "s"
                    MAX-ACCESS read-only
                    STATUS current
                    DESCRIPTION "DERIVATIVE TIME PID MECCANICAL COOLING"
                    ::= { integerObjects 114 }

        
	
	END

--
-- CAREL-bce.MIB
--
