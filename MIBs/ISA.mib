--
-- isa.MIB
-- MIB generated
-- Friday, 01 April 2011
--

    ISA-MIB DEFINITIONS ::= BEGIN

		IMPORTS
			OBJECT-GROUP		FROM SNMPv2-CONF			
			sysContact, sysName,
			sysLocation		FROM SNMPv2-MIB
			enterprises, MODULE-IDENTITY,
			OBJECT-TYPE, Integer32	FROM SNMPv2-SMI
			DisplayString		FROM RFC1213-MIB;		
		
        isaMIB MODULE-IDENTITY
      		LAST-UPDATED  "200712101120Z"		-- December 10, 2007 at 11:20 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the ISA device."
      		REVISION  "200712101120Z"		-- December 10, 2007 at 11:20 GMT
      		DESCRIPTION
                "This is the original version of the MIB."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
 		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.
		
		
       -- 1.3.6.1.4.1.9839.2.1.1
        digitalObjects OBJECT IDENTIFIER ::= { isaMIB 1 }

        -- 1.3.6.1.4.1.9839.2.1.1.1
        systemon OBJECT-TYPE
                    SYNTAX Integer32 (0..1)
                    UNITS "N/A"
                    MAX-ACCESS read-only
                    STATUS current
                    DESCRIPTION "SYSTEM ON"
                    ::= { digitalObjects 1 }

        -- 1.3.6.1.4.1.9839.2.1.1.2
        compress1 OBJECT-TYPE
                    SYNTAX Integer32 (0..1)
                    UNITS "N/A"
                    MAX-ACCESS read-only
                    STATUS current
                    DESCRIPTION "COMPRESSOR 1"
                    ::= { digitalObjects 2 }

        -- 1.3.6.1.4.1.9839.2.1.1.3
        compress2 OBJECT-TYPE
                    SYNTAX Integer32 (0..1)
                    UNITS "N/A"
                    MAX-ACCESS read-only
                    STATUS current
                    DESCRIPTION "COMPRESSOR 2"
                    ::= { digitalObjects 3 }


        -- 1.3.6.1.4.1.9839.2.1.1.4
        pompa1 OBJECT-TYPE
                    SYNTAX Integer32 (0..1)
                    UNITS "N/A"
                    MAX-ACCESS read-only
                    STATUS current
                    DESCRIPTION "PUMP 1"
                    ::= { digitalObjects 4 }

        -- 1.3.6.1.4.1.9839.2.1.1.5
        pompa2 OBJECT-TYPE
                    SYNTAX Integer32 (0..1)
                    UNITS "N/A"
                    MAX-ACCESS read-only
                    STATUS current
                    DESCRIPTION "PUMP 2"
                    ::= { digitalObjects 5 }

        -- 1.3.6.1.4.1.9839.2.1.1.6
        pompa-fc OBJECT-TYPE
                    SYNTAX Integer32 (0..1)
                    UNITS "N/A"
                    MAX-ACCESS read-only
                    STATUS current
                    DESCRIPTION "FREE-COOLING PUMP"
                    ::= { digitalObjects 6 }

        -- 1.3.6.1.4.1.9839.2.1.1.7
        inverno OBJECT-TYPE
                    SYNTAX Integer32 (0..1)
                    UNITS "N/A"
                    MAX-ACCESS read-only
                    STATUS current
                    DESCRIPTION "WINTER MODE (HEAT PUMP ONLY)"
                    ::= { digitalObjects 7 }

        -- 1.3.6.1.4.1.9839.2.1.1.8
        heat-rec-on OBJECT-TYPE
                    SYNTAX Integer32 (0..1)
                    UNITS "N/A"
                    MAX-ACCESS read-only
                    STATUS current
                    DESCRIPTION "HEAT RECOVERY (OPTION)"
                    ::= { digitalObjects 8 }

        -- 1.3.6.1.4.1.9839.2.1.1.9
        heater OBJECT-TYPE
                    SYNTAX Integer32 (0..1)
                    UNITS "N/A"
                    MAX-ACCESS read-only
                    STATUS current
                    DESCRIPTION "ANTIFREEZE HEATERS (OPTION)"
                    ::= { digitalObjects 9 }

        -- 1.3.6.1.4.1.9839.2.1.1.10
        defrost-circ1 OBJECT-TYPE
                    SYNTAX Integer32 (0..1)
                    UNITS "N/A"
                    MAX-ACCESS read-only
                    STATUS current
                    DESCRIPTION "CIRCUIT 1 DEFROST"
                    ::= { digitalObjects 10 }

        -- 1.3.6.1.4.1.9839.2.1.1.11
        defrost-circ2 OBJECT-TYPE
                    SYNTAX Integer32 (0..1)
                    UNITS "N/A"
                    MAX-ACCESS read-only
                    STATUS current
                    DESCRIPTION "CIRCUIT 2 DEFROST"
                    ::= { digitalObjects 11 }

        -- 1.3.6.1.4.1.9839.2.1.1.12
        k-syson OBJECT-TYPE
                    SYNTAX Integer32 (0..1)
                    UNITS "N/A"
                    MAX-ACCESS read-write
                    STATUS current
                    DESCRIPTION "SUMMER-WINTER MODE"
                    ::= { digitalObjects 13 }

        -- 1.3.6.1.4.1.9839.2.1.1.13
        k-est-inv OBJECT-TYPE
                    SYNTAX Integer32 (0..1)
                    UNITS "N/A"
                    MAX-ACCESS read-write
                    STATUS current
                    DESCRIPTION "UNIT ON/OFF"
                    ::= { digitalObjects 12 }


        -- 1.3.6.1.4.1.9839.2.1.1.14
        glb-al OBJECT-TYPE
                    SYNTAX Integer32 (0..1)
                    UNITS "N/A"
                    MAX-ACCESS read-only
                    STATUS current
                    DESCRIPTION "GENERAL ALARM"
                    ::= { digitalObjects 14 }

        -- 1.3.6.1.4.1.9839.2.1.1.15
        or-al-2lev OBJECT-TYPE
                    SYNTAX Integer32 (0..1)
                    UNITS "N/A"
                    MAX-ACCESS read-only
                    STATUS current
                    DESCRIPTION "SECOND LEVEL ALARM"
                    ::= { digitalObjects 15 }

        -- 1.3.6.1.4.1.9839.2.1.1.16
        mal-access OBJECT-TYPE
                    SYNTAX Integer32 (0..1)
                    UNITS "N/A"
                    MAX-ACCESS read-only
                    STATUS current
                    DESCRIPTION "ATTEMPT TO ACCESS WITH WRONG PASSWORD"
                    ::= { digitalObjects 16 }

        -- 1.3.6.1.4.1.9839.2.1.1.17
        al-fase OBJECT-TYPE
                    SYNTAX Integer32 (0..1)
                    UNITS "N/A"
                    MAX-ACCESS read-only
                    STATUS current
                    DESCRIPTION "WRONG PHASE SEQUENCE ALARM"
                    ::= { digitalObjects 17 }

        -- 1.3.6.1.4.1.9839.2.1.1.18
        mal-flusso-h2o OBJECT-TYPE
                    SYNTAX Integer32 (0..1)
                    UNITS "N/A"
                    MAX-ACCESS read-only
                    STATUS current
                    DESCRIPTION "WATER FLOW FAILURE"
                    ::= { digitalObjects 18 }

        -- 1.3.6.1.4.1.9839.2.1.1.19
        mal-ht-win OBJECT-TYPE
                    SYNTAX Integer32 (0..1)
                    UNITS "N/A"
                    MAX-ACCESS read-only
                    STATUS current
                    DESCRIPTION "WATER IN TEMPERATURE ABOVE MAXIMUM LIMIT"
                    ::= { digitalObjects 19 }

        -- 1.3.6.1.4.1.9839.2.1.1.20
        mal-lt-win OBJECT-TYPE
                    SYNTAX Integer32 (0..1)
                    UNITS "N/A"
                    MAX-ACCESS read-only
                    STATUS current
                    DESCRIPTION "WATER IN TEMPERATURE BELOW LOW LIMIT"
                    ::= { digitalObjects 20 }

        -- 1.3.6.1.4.1.9839.2.1.1.21
        mal-pompa1 OBJECT-TYPE
                    SYNTAX Integer32 (0..1)
                    UNITS "N/A"
                    MAX-ACCESS read-only
                    STATUS current
                    DESCRIPTION "PUMP 1 FAILURE"
                    ::= { digitalObjects 21 }

        -- 1.3.6.1.4.1.9839.2.1.1.22
        mal-pompa2 OBJECT-TYPE
                    SYNTAX Integer32 (0..1)
                    UNITS "N/A"
                    MAX-ACCESS read-only
                    STATUS current
                    DESCRIPTION "PUMP 2 FAILURE"
                    ::= { digitalObjects 22 }

        -- 1.3.6.1.4.1.9839.2.1.1.23
        mal-pompafc OBJECT-TYPE
                    SYNTAX Integer32 (0..1)
                    UNITS "N/A"
                    MAX-ACCESS read-only
                    STATUS current
                    DESCRIPTION "FREE-COOLING PUMP FAILURE"
                    ::= { digitalObjects 23 }

        -- 1.3.6.1.4.1.9839.2.1.1.24
        mal-lan OBJECT-TYPE
                    SYNTAX Integer32 (0..1)
                    UNITS "N/A"
                    MAX-ACCESS read-only
                    STATUS current
                    DESCRIPTION "LAN FAILURE"
                    ::= { digitalObjects 24 }

        -- 1.3.6.1.4.1.9839.2.1.1.25
        defrost-np OBJECT-TYPE
                    SYNTAX Integer32 (0..1)
                    UNITS "N/A"
                    MAX-ACCESS read-only
                    STATUS current
                    DESCRIPTION "DEFROST NOT POSSIBLE"
                    ::= { digitalObjects 25 }

        -- 1.3.6.1.4.1.9839.2.1.1.26
        mpreal-bp1 OBJECT-TYPE
                    SYNTAX Integer32 (0..1)
                    UNITS "N/A"
                    MAX-ACCESS read-only
                    STATUS current
                    DESCRIPTION "CIRCUIT 1 LOW PRESSURE PREALARM"
                    ::= { digitalObjects 26 }

        -- 1.3.6.1.4.1.9839.2.1.1.27
        mpreal-bp2 OBJECT-TYPE
                    SYNTAX Integer32 (0..1)
                    UNITS "N/A"
                    MAX-ACCESS read-only
                    STATUS current
                    DESCRIPTION "CIRCUIT 2 LOW PRESSURE PREALARM"
                    ::= { digitalObjects 27 }

        -- 1.3.6.1.4.1.9839.2.1.1.28
        al-bp1 OBJECT-TYPE
                    SYNTAX Integer32 (0..1)
                    UNITS "N/A"
                    MAX-ACCESS read-only
                    STATUS current
                    DESCRIPTION "CIRCUIT 1 LOW PRESSURE ALARM"
                    ::= { digitalObjects 28 }

        -- 1.3.6.1.4.1.9839.2.1.1.29
        al-bp2 OBJECT-TYPE
                    SYNTAX Integer32 (0..1)
                    UNITS "N/A"
                    MAX-ACCESS read-only
                    STATUS current
                    DESCRIPTION "CIRCUIT 2 LOW PRESSURE ALARM"
                    ::= { digitalObjects 29 }

        -- 1.3.6.1.4.1.9839.2.1.1.30
        mal-ap1 OBJECT-TYPE
                    SYNTAX Integer32 (0..1)
                    UNITS "N/A"
                    MAX-ACCESS read-only
                    STATUS current
                    DESCRIPTION "CIRCUIT 1 HIGH PRESSURE ALARM"
                    ::= { digitalObjects 30 }

        -- 1.3.6.1.4.1.9839.2.1.1.31
        mal-ap2 OBJECT-TYPE
                    SYNTAX Integer32 (0..1)
                    UNITS "N/A"
                    MAX-ACCESS read-only
                    STATUS current
                    DESCRIPTION "CIRCUIT 2 HIGH PRESSURE ALARM"
                    ::= { digitalObjects 31 }

        -- 1.3.6.1.4.1.9839.2.1.1.32
        mal-tpdgt OBJECT-TYPE
                    SYNTAX Integer32 (0..1)
                    UNITS "N/A"
                    MAX-ACCESS read-only
                    STATUS current
                    DESCRIPTION "COMPRESSOR 1 THERMOPROTECTOR ALARM"
                    ::= { digitalObjects 32 }

        -- 1.3.6.1.4.1.9839.2.1.1.33
        mal-tpdgt2 OBJECT-TYPE
                    SYNTAX Integer32 (0..1)
                    UNITS "N/A"
                    MAX-ACCESS read-only
                    STATUS current
                    DESCRIPTION "COMPRESSOR 2 THERMOPROTECTOR ALARM"
                    ::= { digitalObjects 33 }

        -- 1.3.6.1.4.1.9839.2.1.1.34
        al-af1 OBJECT-TYPE
                    SYNTAX Integer32 (0..1)
                    UNITS "N/A"
                    MAX-ACCESS read-only
                    STATUS current
                    DESCRIPTION "CIRCUIT 1 ANTIFREEZE ALARM"
                    ::= { digitalObjects 34 }

        -- 1.3.6.1.4.1.9839.2.1.1.35
        al-af2 OBJECT-TYPE
                    SYNTAX Integer32 (0..1)
                    UNITS "N/A"
                    MAX-ACCESS read-only
                    STATUS current
                    DESCRIPTION "CIRCUIT 2 ANTIFREEZE ALARM"
                    ::= { digitalObjects 35 }

        -- 1.3.6.1.4.1.9839.2.1.1.36
        mal-sonda-twin OBJECT-TYPE
                    SYNTAX Integer32 (0..1)
                    UNITS "N/A"
                    MAX-ACCESS read-only
                    STATUS current
                    DESCRIPTION "WATER IN TEMPERATURE SENSOR FAILURE"
                    ::= { digitalObjects 36 }

        -- 1.3.6.1.4.1.9839.2.1.1.37
        mal-sonda-twout OBJECT-TYPE
                    SYNTAX Integer32 (0..1)
                    UNITS "N/A"
                    MAX-ACCESS read-only
                    STATUS current
                    DESCRIPTION "CIRCUIT 1 WATER OUT TEMPERATURE SENSOR FAILURE"
                    ::= { digitalObjects 37 }

        -- 1.3.6.1.4.1.9839.2.1.1.38
        mal-sonda-twaccu OBJECT-TYPE
                    SYNTAX Integer32 (0..1)
                    UNITS "N/A"
                    MAX-ACCESS read-only
                    STATUS current
                    DESCRIPTION " CIRCUIT 2 WATER OUT TEMPERATURE SENSOR FAILURE "
                    ::= { digitalObjects 38 }

        -- 1.3.6.1.4.1.9839.2.1.1.39
        mal-sonda-te OBJECT-TYPE
                    SYNTAX Integer32 (0..1)
                    UNITS "N/A"
                    MAX-ACCESS read-only
                    STATUS current
                    DESCRIPTION "EXTERNAL AIR TEMPERATURE SENSOR FAILURE"
                    ::= { digitalObjects 39 }

        -- 1.3.6.1.4.1.9839.2.1.1.49
        mal-sonda-pc1 OBJECT-TYPE
                    SYNTAX Integer32 (0..1)
                    UNITS "N/A"
                    MAX-ACCESS read-only
                    STATUS current
                    DESCRIPTION "CIRCUIT 1 CONDENSING PRESSURE SENSOR FAILURE"
                    ::= { digitalObjects 49 }

        -- 1.3.6.1.4.1.9839.2.1.1.41
        mal-sonda-pc2 OBJECT-TYPE
                    SYNTAX Integer32 (0..1)
                    UNITS "N/A"
                    MAX-ACCESS read-only
                    STATUS current
                    DESCRIPTION "CIRCUIT 2 CONDENSING PRESSURE SENSOR FAILURE"
                    ::= { digitalObjects 41 }

        -- 1.3.6.1.4.1.9839.2.1.1.42
        mal-sonda-pev1 OBJECT-TYPE
                    SYNTAX Integer32 (0..1)
                    UNITS "N/A"
                    MAX-ACCESS read-only
                    STATUS current
                    DESCRIPTION "CIRCUIT 1 EVAPORATING PRESSURE SENSOR FAILURE"
                    ::= { digitalObjects 42 }

        -- 1.3.6.1.4.1.9839.2.1.1.43
        mal-sonda-pev2 OBJECT-TYPE
                    SYNTAX Integer32 (0..1)
                    UNITS "N/A"
                    MAX-ACCESS read-only
                    STATUS current
                    DESCRIPTION "CIRCUIT 2 EVAPORATING PRESSURE SENSOR FAILURE"
                    ::= { digitalObjects 43 }

        -- 1.3.6.1.4.1.9839.2.1.1.44
        mal-ore-compr1 OBJECT-TYPE
                    SYNTAX Integer32 (0..1)
                    UNITS "N/A"
                    MAX-ACCESS read-only
                    STATUS current
                    DESCRIPTION "COMPRESSOR 1 EXCEEDED MAXIMUM RUN HOURS"
                    ::= { digitalObjects 44 }

        -- 1.3.6.1.4.1.9839.2.1.1.45
        mal-ore-compr2 OBJECT-TYPE
                    SYNTAX Integer32 (0..1)
                    UNITS "N/A"
                    MAX-ACCESS read-only
                    STATUS current
                    DESCRIPTION "COMPRESSOR 2 EXCEEDED MAXIMUM RUN HOURS"
                    ::= { digitalObjects 45 }

        -- 1.3.6.1.4.1.9839.2.1.1.46
        mal-ore-pump1 OBJECT-TYPE
                    SYNTAX Integer32 (0..1)
                    UNITS "N/A"
                    MAX-ACCESS read-only
                    STATUS current
                    DESCRIPTION "PUMP 1 EXCEEDED MAXIMUM RUN HOURS"
                    ::= { digitalObjects 46 }

        -- 1.3.6.1.4.1.9839.2.1.1.47
        mal-ore-pump2 OBJECT-TYPE
                    SYNTAX Integer32 (0..1)
                    UNITS "N/A"
                    MAX-ACCESS read-only
                    STATUS current
                    DESCRIPTION "PUMP 2 EXCEEDED MAXIMUM RUN HOURS"
                    ::= { digitalObjects 47 }

        -- 1.3.6.1.4.1.9839.2.1.1.48
        mal-ore-pumpfc OBJECT-TYPE
                    SYNTAX Integer32 (0..1)
                    UNITS "N/A"
                    MAX-ACCESS read-only
                    STATUS current
                    DESCRIPTION " FREE-COOLING PUMP EXCEEDED MAXIMUM RUN HOURS "
                    ::= { digitalObjects 48 }

        -- 1.3.6.1.4.1.9839.2.1.1.53
        pump-down-circ1 OBJECT-TYPE
                    SYNTAX Integer32 (0..1)
                    UNITS "N/A"
                    MAX-ACCESS read-only
                    STATUS current
                    DESCRIPTION "CIRCUIT 1 PUMP-DOWN FAILED"
                    ::= { digitalObjects 53 }

        -- 1.3.6.1.4.1.9839.2.1.1.54
        pump-down-circ2 OBJECT-TYPE
                    SYNTAX Integer32 (0..1)
                    UNITS "N/A"
                    MAX-ACCESS read-only
                    STATUS current
                    DESCRIPTION "CIRCUIT 2 PUMP-DOWN FAILED"
                    ::= { digitalObjects 54 }

        -- 1.3.6.1.4.1.9839.2.1.1.55
        alta-tc OBJECT-TYPE
                    SYNTAX Integer32 (0..1)
                    UNITS "N/A"
                    MAX-ACCESS read-only
                    STATUS current
                    DESCRIPTION "HIGH CONDENSING TEMPERATURE"
                    ::= { digitalObjects 55 }

        -- 1.3.6.1.4.1.9839.2.1.1.56
        shut-off-valve-circ1 OBJECT-TYPE
                    SYNTAX Integer32 (0..1)
                    UNITS "N/A"
                    MAX-ACCESS read-only
                    STATUS current
                    DESCRIPTION "CIRC. 1 REFRIGERANT SHUT-OFF VALVE"
                    ::= { digitalObjects 56 }

       -- 1.3.6.1.4.1.9839.2.1.1.57
        shut-off-valve-circ2 OBJECT-TYPE
                    SYNTAX Integer32 (0..1)
                    UNITS "N/A"
                    MAX-ACCESS read-only
                    STATUS current
                    DESCRIPTION "CIRC. 2 REFRIGERANT SHUT-OFF VALVE"
                    ::= { digitalObjects 57 }

        -- 1.3.6.1.4.1.9839.2.1.1.58
        ustby1-2 OBJECT-TYPE
                    SYNTAX Integer32 (0..1)
                    UNITS "N/A"
                    MAX-ACCESS read-only
                    STATUS current
                    DESCRIPTION "N. OF STAND-BY UNITS ONE (O) - TWO (1)"
                    ::= { digitalObjects 58 }

        -- 1.3.6.1.4.1.9839.2.1.1.63
        xs-res-al OBJECT-TYPE
                    SYNTAX Integer32 (0..1)
                    UNITS "N/A"
                    MAX-ACCESS read-write
                    STATUS current
                    DESCRIPTION "ALARM RESET"
                    ::= { digitalObjects 63 }

        -- 1.3.6.1.4.1.9839.2.1.1.64
        chg-pump OBJECT-TYPE
                    SYNTAX Integer32 (0..1)
                    UNITS "N/A"
                    MAX-ACCESS read-write
                    STATUS current
                    DESCRIPTION "PUMPS CHANGEOVER"
                    ::= { digitalObjects 64 }

        -- 1.3.6.1.4.1.9839.2.1.1.65
        sleep-mode OBJECT-TYPE
                    SYNTAX Integer32 (0..1)
                    UNITS "N/A"
                    MAX-ACCESS read-write
                    STATUS current
                    DESCRIPTION "SETBACK MODE (SLEEP MODE)"
                    ::= { digitalObjects 65 }

        -- 1.3.6.1.4.1.9839.2.1.1.66
        test-sm OBJECT-TYPE
                    SYNTAX Integer32 (0..1)
                    UNITS "N/A"
                    MAX-ACCESS read-write
                    STATUS current
                    DESCRIPTION "SETBACK MODE: CYCLICAN START OF FAN"
                    ::= { digitalObjects 66 }

        -- 1.3.6.1.4.1.9839.2.1.1.67
        ab-mediath OBJECT-TYPE
                    SYNTAX Integer32 (0..1)
                    UNITS "N/A"
                    MAX-ACCESS read-write
                    STATUS current
                    DESCRIPTION "ENABLE MEAN VALUES REGULATION"
                    ::= { digitalObjects 67 }

        -- 1.3.6.1.4.1.9839.2.1.1.74
        circ1-defrost OBJECT-TYPE
                    SYNTAX Integer32 (0..1)
                    UNITS "N/A"
                    MAX-ACCESS read-only
                    STATUS current
                    DESCRIPTION "DEFROST CIRCUIT 1"
                    ::= { digitalObjects 74 }

  	-- 1.3.6.1.4.1.9839.2.1.1.75
        circ2-defrost OBJECT-TYPE
                    SYNTAX Integer32 (0..1)
                    UNITS "N/A"
                    MAX-ACCESS read-only
                    STATUS current
                    DESCRIPTION "DEFROST CIRCUIT 2"
                    ::= { digitalObjects 75 }

  	-- 1.3.6.1.4.1.9839.2.1.1.77
        fans-thermal-alarm OBJECT-TYPE
                    SYNTAX Integer32 (0..1)
                    UNITS "N/A"
                    MAX-ACCESS read-only
                    STATUS current
                    DESCRIPTION "FANS THERMAL ALARM"
                    ::= { digitalObjects 77 }

	-- 1.3.6.1.4.1.9839.2.1.1.81
        etv-oil-comp1 OBJECT-TYPE
                    SYNTAX Integer32 (0..1)
                    UNITS "N/A"
                    MAX-ACCESS read-only
                    STATUS current
                    DESCRIPTION "ETV OIL COMPRESSOR 1"
                    ::= { digitalObjects 81 }

 	-- 1.3.6.1.4.1.9839.2.1.1.82
        etv-oil-comp2 OBJECT-TYPE
                    SYNTAX Integer32 (0..1)
                    UNITS "N/A"
                    MAX-ACCESS read-only
                    STATUS current
                    DESCRIPTION "ETV OIL COMPRESSOR 2"
                    ::= { digitalObjects 82 }

 	-- 1.3.6.1.4.1.9839.2.1.1.83
        etv-oil-comp1-alarm OBJECT-TYPE
                    SYNTAX Integer32 (0..1)
                    UNITS "N/A"
                    MAX-ACCESS read-only
                    STATUS current
                    DESCRIPTION "ETV OIL COMPRESSOR 1 ALARM"
                    ::= { digitalObjects 83 }

 	-- 1.3.6.1.4.1.9839.2.1.1.84
        etv-oil-comp2-alarm OBJECT-TYPE
                    SYNTAX Integer32 (0..1)
                    UNITS "N/A"
                    MAX-ACCESS read-only
                    STATUS current
                    DESCRIPTION "ETV OIL COMPRESSOR 2 ALARM"
                    ::= { digitalObjects 84 }

 	-- 1.3.6.1.4.1.9839.2.1.1.111
        inv-comp-alarm OBJECT-TYPE
                    SYNTAX Integer32 (0..1)
                    UNITS "N/A"
                    MAX-ACCESS read-only
                    STATUS current
                    DESCRIPTION "INVERTER COMPRESSOR ALARM"
                    ::= { digitalObjects 111 }

	-- 1.3.6.1.4.1.9839.2.1.1.112
        inv-pump-alarm OBJECT-TYPE
                    SYNTAX Integer32 (0..1)
                    UNITS "N/A"
                    MAX-ACCESS read-only
                    STATUS current
                    DESCRIPTION "INVERTER PUMP ALARM"
                    ::= { digitalObjects 112 }

	-- 1.3.6.1.4.1.9839.2.1.1.113
        pCOe-offline-alarm OBJECT-TYPE
                    SYNTAX Integer32 (0..1)
                    UNITS "N/A"
                    MAX-ACCESS read-only
                    STATUS current
                    DESCRIPTION "OFFLINE PCOE BOARD ALARM"
                    ::= { digitalObjects 113 }

	-- 1.3.6.1.4.1.9839.2.1.1.114
        winlet-pressureprobe-alarm OBJECT-TYPE
                    SYNTAX Integer32 (0..1)
                    UNITS "N/A"
                    MAX-ACCESS read-only
                    STATUS current
                    DESCRIPTION "WATER INLET PRESSURE PROBE ALARM"
                    ::= { digitalObjects 114 }

	-- 1.3.6.1.4.1.9839.2.1.1.115
        woutlet-pressureprobe-alarm OBJECT-TYPE
                    SYNTAX Integer32 (0..1)
                    UNITS "N/A"
                    MAX-ACCESS read-only
                    STATUS current
                    DESCRIPTION "WATER OUTLET PRESSURE PROBE ALARM"
                    ::= { digitalObjects 115 }

	-- 1.3.6.1.4.1.9839.2.1.1.122
        electhermo-valve-alarm OBJECT-TYPE
                    SYNTAX Integer32 (0..1)
                    UNITS "N/A"
                    MAX-ACCESS read-only
                    STATUS current
                    DESCRIPTION "ELECTRONIC THERMOSTATIC VALVE ALARM"
                    ::= { digitalObjects 122 }

	-- 1.3.6.1.4.1.9839.2.1.1.141
        tlan-communication-alarm OBJECT-TYPE
                    SYNTAX Integer32 (0..1)
                    UNITS "N/A"
                    MAX-ACCESS read-only
                    STATUS current
                    DESCRIPTION "T-LAN COMMUNICATION ALARM"
                    ::= { digitalObjects 141 }


        -- 1.3.6.1.4.1.9839.2.1.2
        analogObjects OBJECT IDENTIFIER ::= { isaMIB 2 }

        -- 1.3.6.1.4.1.9839.2.1.2.1
        temp-wout OBJECT-TYPE
                    SYNTAX Integer32 (-32767..32767)
                    UNITS "degrees C"
                    MAX-ACCESS read-only
                    STATUS current
                    DESCRIPTION "WATER OUT TEMPERATURE"
                    ::= { analogObjects 1 }

        -- 1.3.6.1.4.1.9839.2.1.2.2
        temp-wout2 OBJECT-TYPE
                    SYNTAX Integer32 (-32767..32767)
                    UNITS "degrees C"
                    MAX-ACCESS read-only
                    STATUS current
                    DESCRIPTION "CIRCUIT 2 WATER OUT TEMPERATURE (ONLY BI-CIRC.)"
                    ::= { analogObjects 2 }

        -- 1.3.6.1.4.1.9839.2.1.2.3
        t-wout-regol OBJECT-TYPE
                    SYNTAX Integer32 (-32767..32767)
                    UNITS "degrees C"
                    MAX-ACCESS read-only
                    STATUS current
                    DESCRIPTION "REGULATION WATER OUT TEMPERATURE"
                    ::= { analogObjects 3 }

        -- 1.3.6.1.4.1.9839.2.1.2.4
        temp-win OBJECT-TYPE
                    SYNTAX Integer32 (-32767..32767)
                    UNITS "degrees C"
                    MAX-ACCESS read-only
                    STATUS current
                    DESCRIPTION "WATER IN TEMPERATURE"
                    ::= { analogObjects 4 }

        -- 1.3.6.1.4.1.9839.2.1.2.5
        temp-ext OBJECT-TYPE
                    SYNTAX Integer32 (-32767..32767)
                    UNITS "degrees C"
                    MAX-ACCESS read-only
                    STATUS current
                    DESCRIPTION "EXTERNAL AIR TEMPERATURE"
                    ::= { analogObjects 5 }

        -- 1.3.6.1.4.1.9839.2.1.2.6
        temp-wr OBJECT-TYPE
                    SYNTAX Integer32 (-32767..32767)
                    UNITS "degrees C"
                    MAX-ACCESS read-only
                    STATUS current
                    DESCRIPTION "HEAT RECOVERY WATER INLET TEMPERATURE"
                    ::= { analogObjects 6 }

        -- 1.3.6.1.4.1.9839.2.1.2.7
        xv-press-cond1 OBJECT-TYPE
                    SYNTAX Integer32 (-32767..32767)
                    UNITS "bar"
                    MAX-ACCESS read-only
                    STATUS current
                    DESCRIPTION "CIRCUIT 1 CONDENSING PRESSURE"
                    ::= { analogObjects 7 }

        -- 1.3.6.1.4.1.9839.2.1.2.8
        xv-press-cond2 OBJECT-TYPE
                    SYNTAX Integer32 (-32767..32767)
                    UNITS "bar"
                    MAX-ACCESS read-only
                    STATUS current
                    DESCRIPTION "CIRCUIT 2 CONDENSING PRESSURE"
                    ::= { analogObjects 8 }

        -- 1.3.6.1.4.1.9839.2.1.2.9
        xv-press-evap1 OBJECT-TYPE
                    SYNTAX Integer32 (-32767..32767)
                    UNITS "bar"
                    MAX-ACCESS read-only
                    STATUS current
                    DESCRIPTION "CIRCUIT 1 EVAPORATING PRESSURE"
                    ::= { analogObjects 9 }

        -- 1.3.6.1.4.1.9839.2.1.2.10
        xv-press-evap2 OBJECT-TYPE
                    SYNTAX Integer32 (-32767..32767)
                    UNITS "bar"
                    MAX-ACCESS read-only
                    STATUS current
                    DESCRIPTION "CIRCUIT 2 EVAPORATING PRESSURE"
                    ::= { analogObjects 10 }

        -- 1.3.6.1.4.1.9839.2.1.2.11
        temp-cond1 OBJECT-TYPE
                    SYNTAX Integer32 (-32767..32767)
                    UNITS "degrees C"
                    MAX-ACCESS read-only
                    STATUS current
                    DESCRIPTION "CIRCUIT 1 CONDENSING TEMPERATURE"
                    ::= { analogObjects 11 }

        -- 1.3.6.1.4.1.9839.2.1.2.12
        temp-cond2 OBJECT-TYPE
                    SYNTAX Integer32 (-32767..32767)
                    UNITS "degrees C"
                    MAX-ACCESS read-only
                    STATUS current
                    DESCRIPTION "CIRCUIT 2 CONDENSING TEMPERATURE"
                    ::= { analogObjects 12 }

        -- 1.3.6.1.4.1.9839.2.1.2.13
        temp-evap1 OBJECT-TYPE
                    SYNTAX Integer32 (-32767..32767)
                    UNITS "degrees C"
                    MAX-ACCESS read-only
                    STATUS current
                    DESCRIPTION "CIRCUIT 1 EVAPORATING TEMPERATURE"
                    ::= { analogObjects 13 }

        -- 1.3.6.1.4.1.9839.2.1.2.14
        temp-evap2 OBJECT-TYPE
                    SYNTAX Integer32 (-32767..32767)
                    UNITS "degrees C"
                    MAX-ACCESS read-only
                    STATUS current
                    DESCRIPTION "CIRCUIT 2 EVAPORATING TEMPERATURE"
                    ::= { analogObjects 14 }

        -- 1.3.6.1.4.1.9839.2.1.2.15
        x-rampa-vent2 OBJECT-TYPE
                    SYNTAX Integer32 (-32767..32767)
                    UNITS "%"
                    MAX-ACCESS read-only
                    STATUS current
                    DESCRIPTION "FAN MODULATING RAMP"
                    ::= { analogObjects 15 }

        -- 1.3.6.1.4.1.9839.2.1.2.16
        t-set-regol OBJECT-TYPE
                    SYNTAX Integer32 (-32767..32767)
                    UNITS "degrees C"
                    MAX-ACCESS read-only
                    STATUS current
                    DESCRIPTION "LEAVING TEMP.REGULATION SETPOINT"
                    ::= { analogObjects 16 }

        -- 1.3.6.1.4.1.9839.2.1.2.17
        zona-neutra OBJECT-TYPE
                    SYNTAX Integer32 (-32767..32767)
                    UNITS "degrees C"
                    MAX-ACCESS read-only
                    STATUS current
                    DESCRIPTION "MAX HYSTERESI"
                    ::= { analogObjects 17 }

        -- 1.3.6.1.4.1.9839.2.1.2.18
        actual-sheat-c1 OBJECT-TYPE
                    SYNTAX Integer32 (-32767..32767)
                    UNITS "degrees C"
                    MAX-ACCESS read-only
                    STATUS current
                    DESCRIPTION "CIRCUIT 1 SUPERHEATING"
                    ::= { analogObjects 18 }

        -- 1.3.6.1.4.1.9839.2.1.2.19
        actual-sheat-c2 OBJECT-TYPE
                    SYNTAX Integer32 (-32767..32767)
                    UNITS "degrees C"
                    MAX-ACCESS read-only
                    STATUS current
                    DESCRIPTION " CIRCUIT 2 SUPERHEATING "
                    ::= { analogObjects 19 }

        -- 1.3.6.1.4.1.9839.2.1.2.20
         saturation-temp-c1 OBJECT-TYPE
                    SYNTAX Integer32 (-32767..32767)
                    UNITS "degrees C"
                    MAX-ACCESS read-only
                    STATUS current
                    DESCRIPTION " CIRCUIT 1 SATURATION TEMPERATURE EVD400"
                    ::= { analogObjects 20 }

        -- 1.3.6.1.4.1.9839.2.1.2.21
        saturation-temp-c2 OBJECT-TYPE
                    SYNTAX Integer32 (-32767..32767)
                    UNITS "degrees C"
                    MAX-ACCESS read-only
                    STATUS current
                    DESCRIPTION " CIRCUIT 2 SATURATION TEMPERATURE EVD400"
                    ::= { analogObjects 21 }

        -- 1.3.6.1.4.1.9839.2.1.2.22
        ofs-spv OBJECT-TYPE
                    SYNTAX Integer32 (1..99)
                    UNITS "N/A"
                    MAX-ACCESS read-write
                    STATUS current
                    DESCRIPTION "OFFSET FOR SERIAL COMMUNICATION"
                    ::= { analogObjects 22 }

        -- 1.3.6.1.4.1.9839.2.1.2.23
        t-set-e OBJECT-TYPE
                    SYNTAX Integer32 (60..180)
                    UNITS "degrees C"
                    MAX-ACCESS read-write
                    STATUS current
                    DESCRIPTION "SUMMER SETPOINT"
                    ::= { analogObjects 23 }

        -- 1.3.6.1.4.1.9839.2.1.2.24
        t-set-d OBJECT-TYPE
                    SYNTAX Integer32 (60..180)
                    UNITS "degrees C"
                    MAX-ACCESS read-write
                    STATUS current
                    DESCRIPTION "SUMMER SECOND SETPOINT"
                    ::= { analogObjects 24 }

        -- 1.3.6.1.4.1.9839.2.1.2.25
        t-set-sm OBJECT-TYPE
                    SYNTAX Integer32 (80..180)
                    UNITS "degrees C"
                    MAX-ACCESS read-write
                    STATUS current
                    DESCRIPTION "SETBACK MODE SUMMER SETPOINT"
                    ::= { analogObjects 25 }

        -- 1.3.6.1.4.1.9839.2.1.2.26
        t-set-i OBJECT-TYPE
                    SYNTAX Integer32 (280..530)
                    UNITS "degrees C"
                    MAX-ACCESS read-write
                    STATUS current
                    DESCRIPTION "WINTER SETPOINT"
                    ::= { analogObjects 26 }

        -- 1.3.6.1.4.1.9839.2.1.2.27
        t-set-c-sm OBJECT-TYPE
                    SYNTAX Integer32 (280..530)
                    UNITS "degrees C"
                    MAX-ACCESS read-write
                    STATUS current
                    DESCRIPTION "SETBACK MODE WINTER SETPOINT"
                    ::= { analogObjects 27 }

        -- 1.3.6.1.4.1.9839.2.1.2.28
        set-ht-win-e OBJECT-TYPE
                    SYNTAX Integer32 (-150..250)
                    UNITS "degrees C"
                    MAX-ACCESS read-write
                    STATUS current
                    DESCRIPTION "WATER IN HIGH TEMPERATURE ALARM THRESHOLD-SUMMER"
                    ::= { analogObjects 28 }

        -- 1.3.6.1.4.1.9839.2.1.2.29
        set-lt-win-e OBJECT-TYPE
                    SYNTAX Integer32 (-150..250)
                    UNITS "degrees C"
                    MAX-ACCESS read-write
                    STATUS current
                    DESCRIPTION "WATER IN LOW TEMPERATURE ALARM THRESHOLD-SUMMER"
                    ::= { analogObjects 29 }

        -- 1.3.6.1.4.1.9839.2.1.2.30
        set-ht-win-i OBJECT-TYPE
                    SYNTAX Integer32 (200..500)
                    UNITS "degrees C"
                    MAX-ACCESS read-write
                    STATUS current
                    DESCRIPTION "WATER IN HIGH TEMPERATURE ALARM THRESHOLD-WINTER"
                    ::= { analogObjects 30 }

        -- 1.3.6.1.4.1.9839.2.1.2.31
        set-lt-win-i OBJECT-TYPE
                    SYNTAX Integer32 (200..500)
                    UNITS "degrees C"
                    MAX-ACCESS read-write
                    STATUS current
                    DESCRIPTION "WATER IN LOW TEMPERATURE ALARM THRESHOLD-WINTER"
                    ::= { analogObjects 31 }

        -- 1.3.6.1.4.1.9839.2.1.2.32
        summer-TextsetP-P1 OBJECT-TYPE
                    SYNTAX Integer32 (-150..250)
                    UNITS "degrees C"
                    MAX-ACCESS read-write
                    STATUS current
                    DESCRIPTION "SUMMER T.EXT COMPENS.: P1 T.EXT SETP."
                    ::= { analogObjects 32 }

        -- 1.3.6.1.4.1.9839.2.1.2.33
        summer-TwoutsetP-P2 OBJECT-TYPE
                    SYNTAX Integer32 (-150..250)
                    UNITS "degrees C"
                    MAX-ACCESS read-write
                    STATUS current
                    DESCRIPTION "SUMMER T.EXT COMPENS.: P2 T.WOUT SETP."
                    ::= { analogObjects 33 }

        -- 1.3.6.1.4.1.9839.2.1.2.34
        summer-TextsetP-P2 OBJECT-TYPE
                    SYNTAX Integer32 (-150..250)
                    UNITS "degrees C"
                    MAX-ACCESS read-write
                    STATUS current
                    DESCRIPTION "SUMMER T.EXT COMPENS.: P2 T.EXT SETP."
                    ::= { analogObjects 34 }

        -- 1.3.6.1.4.1.9839.2.1.2.35
        winter-TextsetP-P1 OBJECT-TYPE
                    SYNTAX Integer32 (-150..250)
                    UNITS "degrees C"
                    MAX-ACCESS read-write
                    STATUS current
                    DESCRIPTION "WINTER T.EXT COMPENS.: P1 T.EXT SETP."
                    ::= { analogObjects 35 }

        -- 1.3.6.1.4.1.9839.2.1.2.36
        winter-TwoutsetP-P2 OBJECT-TYPE
                    SYNTAX Integer32 (-150..250)
                    UNITS "degrees C"
                    MAX-ACCESS read-write
                    STATUS current
                    DESCRIPTION "WINTER T.EXT COMPENS.: P2 T.WOUT SETP."
                    ::= { analogObjects 36 }

        -- 1.3.6.1.4.1.9839.2.1.2.37
        winter-TextsetP-P2 OBJECT-TYPE
                    SYNTAX Integer32 (-150..250)
                    UNITS "degrees C"
                    MAX-ACCESS read-write
                    STATUS current
                    DESCRIPTION "WINTER T.EXT COMPENS.: P2 T.EXT SETP."
                    ::= { analogObjects 37 }

        -- 1.3.6.1.4.1.9839.2.1.2.38
        set-delta-fc OBJECT-TYPE
                    SYNTAX Integer32 (0..80)
                    UNITS "degrees C"
                    MAX-ACCESS read-write
                    STATUS current
                    DESCRIPTION "FREECOOLING DELTAT SETPOINT"
                    ::= { analogObjects 38 }

        -- 1.3.6.1.4.1.9839.2.1.2.39
        super-h-set OBJECT-TYPE
                    SYNTAX Integer32 (30..100)
                    UNITS "degrees C"
                    MAX-ACCESS read-write
                    STATUS current
                    DESCRIPTION "SUMMER SUPERHEATING"
                    ::= { analogObjects 39 }

        -- 1.3.6.1.4.1.9839.2.1.2.40
        ssh-set-hp OBJECT-TYPE
                    SYNTAX Integer32 (30..100)
                    UNITS "degrees C"
                    MAX-ACCESS read-write
                    STATUS current
                    DESCRIPTION "WINTER SUPERHEATING"
                    ::= { analogObjects 40 }

        -- 1.3.6.1.4.1.9839.2.1.2.164
        frequency-comp1 OBJECT-TYPE
                    SYNTAX Integer32 (30..90)
                    UNITS "Hz"
                    MAX-ACCESS read-only
                    STATUS current
                    DESCRIPTION "COMPRESSOR 1 FREQUENCY"
                    ::= { analogObjects 164 }

        -- 1.3.6.1.4.1.9839.2.1.3
        integerObjects OBJECT IDENTIFIER ::= { isaMIB 3 }

        -- 1.3.6.1.4.1.9839.2.1.3.1
        stato-comp1 OBJECT-TYPE
                    SYNTAX Integer32 (-32767..32767)
                    UNITS "h"
                    MAX-ACCESS read-only
                    STATUS current
                    DESCRIPTION "COMPRESSOR 1 STATUS"
                    ::= { integerObjects 1 }

        -- 1.3.6.1.4.1.9839.2.1.3.2
        stato-comp2 OBJECT-TYPE
                    SYNTAX Integer32 (-32767..32767)
                    UNITS "h"
                    MAX-ACCESS read-only
                    STATUS current
                    DESCRIPTION " COMPRESSOR 2 STATUS"
                    ::= { integerObjects 2 }

        -- 1.3.6.1.4.1.9839.2.1.3.3
        stato-pompa1 OBJECT-TYPE
                    SYNTAX Integer32 (-32767..32767)
                    UNITS ""
                    MAX-ACCESS read-only
                    STATUS current
                    DESCRIPTION " PUMP 1 STATUS"
                    ::= { integerObjects 3 }

        -- 1.3.6.1.4.1.9839.2.1.3.4
        stato-pompa2 OBJECT-TYPE
                    SYNTAX Integer32 (-32767..32767)
                    UNITS ""
                    MAX-ACCESS read-only
                    STATUS current
                    DESCRIPTION " PUMP 2 STATUS"
                    ::= { integerObjects 4 }

        -- 1.3.6.1.4.1.9839.2.1.3.5
        stato-pompafc OBJECT-TYPE
                    SYNTAX Integer32 (-32767..32767)
                    UNITS "N/A"
                    MAX-ACCESS read-only
                    STATUS current
                    DESCRIPTION " FREE-COOLING PUMP STATUS"
                    ::= { integerObjects 5 }

        -- 1.3.6.1.4.1.9839.2.1.3.6
         show-setmode OBJECT-TYPE
                    SYNTAX Integer32 (-32767..32767)
                    UNITS "h"
                    MAX-ACCESS read-only
                    STATUS current
                    DESCRIPTION "ACTUAL SET POINT MODE"
                    ::= { integerObjects 6 }


        -- 1.3.6.1.4.1.9839.2.1.3.7
        ore-compr1 OBJECT-TYPE
                    SYNTAX Integer32 (-32767..32767)
                    UNITS "h"
                    MAX-ACCESS read-only
                    STATUS current
                    DESCRIPTION "COMPRESSOR 1 RUN HOURS"
                    ::= { integerObjects 7 }

        -- 1.3.6.1.4.1.9839.2.1.3.8
        ore-compr2 OBJECT-TYPE
                    SYNTAX Integer32 (-32767..32767)
                    UNITS "h"
                    MAX-ACCESS read-only
                    STATUS current
                    DESCRIPTION "COMPRESSOR 2 RUN HOURS"
                    ::= { integerObjects 8 }


        -- 1.3.6.1.4.1.9839.2.1.3.9
        ore-pump1 OBJECT-TYPE
                    SYNTAX Integer32 (-32767..32767)
                    UNITS "h"
                    MAX-ACCESS read-only
                    STATUS current
                    DESCRIPTION "PUMP 1 RUN HOURS"
                    ::= { integerObjects 9 }

        -- 1.3.6.1.4.1.9839.2.1.3.10
        ore-pump2 OBJECT-TYPE
                    SYNTAX Integer32 (-32767..32767)
                    UNITS "h"
                    MAX-ACCESS read-only
                    STATUS current
                    DESCRIPTION "PUMP 2 RUN HOURS"
                    ::= { integerObjects 10 }

        -- 1.3.6.1.4.1.9839.2.1.3.11
        ore-pumpfc OBJECT-TYPE
                    SYNTAX Integer32 (-32767..32767)
                    UNITS "h"
                    MAX-ACCESS read-only
                    STATUS current
                    DESCRIPTION "FREE-COOLING PUMP RUN HOURS"
                    ::= { integerObjects 11 }

        -- 1.3.6.1.4.1.9839.2.1.3.12
        spunti-c1 OBJECT-TYPE
                    SYNTAX Integer32 (-32767..32767)
                    UNITS "n"
                    MAX-ACCESS read-only
                    STATUS current
                    DESCRIPTION "COMPRESSOR 1 STARTING NUMBER"
                    ::= { integerObjects 12 }

        -- 1.3.6.1.4.1.9839.2.1.3.13
        spunti10k-c1 OBJECT-TYPE
                    SYNTAX Integer32 (-32767..32767)
                    UNITS "nx10000"
                    MAX-ACCESS read-only
                    STATUS current
                    DESCRIPTION "COMPRESSOR 1 STARTING NUMBER (x10000)"
                    ::= { integerObjects 13 }

        -- 1.3.6.1.4.1.9839.2.1.3.14
        spunti-c2 OBJECT-TYPE
                    SYNTAX Integer32 (-32767..32767)
                    UNITS "n"
                    MAX-ACCESS read-only
                    STATUS current
                    DESCRIPTION "COMPRESSOR 2 STARTING NUMBER"
                    ::= { integerObjects 14 }

        -- 1.3.6.1.4.1.9839.2.1.3.15
        spunti10k-c2 OBJECT-TYPE
                    SYNTAX Integer32 (-32767..32767)
                    UNITS "nx10000"
                    MAX-ACCESS read-only
                    STATUS current
                    DESCRIPTION "COMPRESSOR 2 STARTING NUMBER (x10000)"
                    ::= { integerObjects 15 }


        -- 1.3.6.1.4.1.9839.2.1.3.16
        num-def-c1 OBJECT-TYPE
                    SYNTAX Integer32 (-32767..32767)
                    UNITS "n"
                    MAX-ACCESS read-only
                    STATUS current
                    DESCRIPTION "CIRCUIT 1 DEFROSTING NUMBER"
                    ::= { integerObjects 16 }

        -- 1.3.6.1.4.1.9839.2.1.3.17
        n10k-def-c1 OBJECT-TYPE
                    SYNTAX Integer32 (-32767..32767)
                    UNITS "nx10000"
                    MAX-ACCESS read-only
                    STATUS current
                    DESCRIPTION "CIRCUIT 1 DEFROSTING NUMBER (x10000)"
                    ::= { integerObjects 17 }

        -- 1.3.6.1.4.1.9839.2.1.3.18
        num-def-c2 OBJECT-TYPE
                    SYNTAX Integer32 (-32767..32767)
                    UNITS "n"
                    MAX-ACCESS read-only
                    STATUS current
                    DESCRIPTION "CIRCUIT 2 DEFROSTING NUMBER"
                    ::= { integerObjects 18 }

        -- 1.3.6.1.4.1.9839.2.1.3.19
        n10k-def-c2 OBJECT-TYPE
                    SYNTAX Integer32 (-32767..32767)
                    UNITS "nx10000"
                    MAX-ACCESS read-only
                    STATUS current
                    DESCRIPTION "CIRCUIT 2 DEFROSTING NUMBER (x10000)"
                    ::= { integerObjects 19 }

        -- 1.3.6.1.4.1.9839.2.1.3.20
        num-def-both OBJECT-TYPE
                    SYNTAX Integer32 (-32767..32767)
                    UNITS "n"
                    MAX-ACCESS read-only
                    STATUS current
                    DESCRIPTION "DEFROSTING TOTAL NUMBER"
                    ::= { integerObjects 20 }

        -- 1.3.6.1.4.1.9839.2.1.3.21
        n10k-def-both OBJECT-TYPE
                    SYNTAX Integer32 (-32767..32767)
                    UNITS "nx10000"
                    MAX-ACCESS read-only
                    STATUS current
                    DESCRIPTION "DEFROSTING TOTAL NUMBER (x10000)"
                    ::= { integerObjects 21 }

        -- 1.3.6.1.4.1.9839.2.1.3.22
        num-def-np OBJECT-TYPE
                    SYNTAX Integer32 (-32767..32767)
                    UNITS "n"
                    MAX-ACCESS read-only
                    STATUS current
                    DESCRIPTION "DEFROSTING FAILURE NUMBER"
                    ::= { integerObjects 22 }

        -- 1.3.6.1.4.1.9839.2.1.3.23
        n10k-def-np OBJECT-TYPE
                    SYNTAX Integer32 (-32767..32767)
                    UNITS "nx10000"
                    MAX-ACCESS read-only
                    STATUS current
                    DESCRIPTION "DEFROSTING FAILURE NUMBER (x10000)"
                    ::= { integerObjects 23 }

        -- 1.3.6.1.4.1.9839.2.1.3.24
        unit-type OBJECT-TYPE
                    SYNTAX Integer32 (-32767..32767)
                    UNITS "s"
                    MAX-ACCESS read-only
                    STATUS current
                    DESCRIPTION "UNIT TYPE"
                    ::= { integerObjects 24 }

        -- 1.3.6.1.4.1.9839.2.1.3.25
        pump-conf OBJECT-TYPE
                    SYNTAX Integer32 (-32767..32767)
                    UNITS "s"
                    MAX-ACCESS read-only
                    STATUS current
                    DESCRIPTION "CIRCULATION PUMP CONFIG"
                    ::= { integerObjects 25}

        -- 1.3.6.1.4.1.9839.2.1.3.26
        lan-unit OBJECT-TYPE
                    SYNTAX Integer32 (-32767..32767)
                    UNITS "n"
                    MAX-ACCESS read-only
                    STATUS current
                    DESCRIPTION "LAN TOTAL UNIT"
                    ::= { integerObjects 26 }

        -- 1.3.6.1.4.1.9839.2.1.3.27
        durata-defrost OBJECT-TYPE
                    SYNTAX Integer32 (-32767..32767)
                    UNITS "s"
                    MAX-ACCESS read-only
                    STATUS current
                    DESCRIPTION "LAST DEFROST TIME LENGTH"
                    ::= { integerObjects 27 }

        -- 1.3.6.1.4.1.9839.2.1.3.28
        day OBJECT-TYPE
                    SYNTAX Integer32 (-32767..32767)
                    UNITS "n"
                    MAX-ACCESS read-only
                    STATUS current
                    DESCRIPTION "DAY"
                    ::= { integerObjects 28 }


        -- 1.3.6.1.4.1.9839.2.1.3.29
        month OBJECT-TYPE
                    SYNTAX Integer32 (-32767..32767)
                    UNITS "n"
                    MAX-ACCESS read-only
                    STATUS current
                    DESCRIPTION "MONTH"
                    ::= { integerObjects 29 }


        -- 1.3.6.1.4.1.9839.2.1.3.30
        year OBJECT-TYPE
                    SYNTAX Integer32 (-32767..32767)
                    UNITS "n"
                    MAX-ACCESS read-only
                    STATUS current
                    DESCRIPTION "YEAR"
                    ::= { integerObjects 30 }


        -- 1.3.6.1.4.1.9839.2.1.3.31
        hour OBJECT-TYPE
                    SYNTAX Integer32 (-32767..32767)
                    UNITS "n"
                    MAX-ACCESS read-only
                    STATUS current
                    DESCRIPTION "HOUR"
                    ::= { integerObjects 31 }


        -- 1.3.6.1.4.1.9839.2.1.3.32
        minute OBJECT-TYPE
                    SYNTAX Integer32 (-32767..32767)
                    UNITS "n"
                    MAX-ACCESS read-only
                    STATUS current
                    DESCRIPTION "MINUTE"
                    ::= { integerObjects 32 }

        -- 1.3.6.1.4.1.9839.2.1.3.33
        position-valve-c1 OBJECT-TYPE
                    SYNTAX Integer32 (-32767..32767)
                    UNITS "n"
                    MAX-ACCESS read-only
                    STATUS current
                    DESCRIPTION "CIRCUIT 1 EXV POSITION"
                    ::= { integerObjects 33 }

        -- 1.3.6.1.4.1.9839.2.1.3.34
        position-valve-c2 OBJECT-TYPE
                    SYNTAX Integer32 (-32767..32767)
                    UNITS "n"
                    MAX-ACCESS read-only
                    STATUS current
                    DESCRIPTION " CIRCUIT 2 EXV POSITION "
                    ::= { integerObjects 34 }

        -- 1.3.6.1.4.1.9839.2.1.3.35
        restart-delay OBJECT-TYPE
                    SYNTAX Integer32 (-32767..32767)
                    UNITS "s"
                    MAX-ACCESS read-only
                    STATUS current
                    DESCRIPTION "RESTART DELAY"
                    ::= { integerObjects 35 }

        -- 1.3.6.1.4.1.9839.2.1.3.36
        regul-delay OBJECT-TYPE
                    SYNTAX Integer32 (-32767..32767)
                    UNITS "s"
                    MAX-ACCESS read-only
                    STATUS current
                    DESCRIPTION "REGULATION START TRANSITORY"
                    ::= { integerObjects 36 }

        -- 1.3.6.1.4.1.9839.2.1.3.37
        alarm-delay OBJECT-TYPE
                    SYNTAX Integer32 (-32767..32767)
                    UNITS "min"
                    MAX-ACCESS read-write
                    STATUS current
                    DESCRIPTION "WATER HIGH-LOW TEMP.ALARM DELAY"
                    ::= { integerObjects 37 }

        -- 1.3.6.1.4.1.9839.2.1.3.39
        time-lowp-run OBJECT-TYPE
                    SYNTAX Integer32 (0..300)
                    UNITS "s"
                    MAX-ACCESS read-write
                    STATUS current
                    DESCRIPTION "LOW PRESSURE RUN DELAY"
                    ::= { integerObjects 39 }

        -- 1.3.6.1.4.1.9839.2.1.3.40
        time-lowp OBJECT-TYPE
                    SYNTAX Integer32 (0..90)
                    UNITS "s"
                    MAX-ACCESS read-write
                    STATUS current
                    DESCRIPTION "LOW PRESSURE START DELAY"
                    ::= { integerObjects 40 }

        -- 1.3.6.1.4.1.9839.2.1.3.41
        t-std-by OBJECT-TYPE
                    SYNTAX Integer32 (0..300)
                    UNITS "h"
                    MAX-ACCESS read-write
                    STATUS current
                    DESCRIPTION "STAND-BY CYCLE TIME"
                    ::= { integerObjects 41 }

        -- 1.3.6.1.4.1.9839.2.1.3.42
        ore-rot-pompe OBJECT-TYPE
                    SYNTAX Integer32 (0..300)
                    UNITS "h"
                    MAX-ACCESS read-write
                    STATUS current
                    DESCRIPTION "RUN STAND-BY PUMP CYCLE TIME"
                    ::= { integerObjects 42 }

        -- 1.3.6.1.4.1.9839.2.1.3.43
        ciclo-sm OBJECT-TYPE
                    SYNTAX Integer32 (0..300)
                    UNITS "min"
                    MAX-ACCESS read-write
                    STATUS current
                    DESCRIPTION "SETBACK MODE CYCLE TIME"
                    ::= { integerObjects 43 }

        -- 1.3.6.1.4.1.9839.2.1.3.44
        set-hm100-c1 OBJECT-TYPE
                    SYNTAX Integer32 (0..320)
                    UNITS "hx100"
                    MAX-ACCESS read-write
                    STATUS current
                    DESCRIPTION "COMPRESSOR 1 RUN HOURS ALARM LIMIT"
                    ::= { integerObjects 44 }

        -- 1.3.6.1.4.1.9839.2.1.3.45
        set-hm100-c2 OBJECT-TYPE
                    SYNTAX Integer32 (0..320)
                    UNITS "hx100"
                    MAX-ACCESS read-write
                    STATUS current
                    DESCRIPTION "COMPRESSOR 2 RUN HOURS ALARM LIMIT"
                    ::= { integerObjects 45 }

        -- 1.3.6.1.4.1.9839.2.1.3.46
        set-hm100-p1 OBJECT-TYPE
                    SYNTAX Integer32 (0..320)
                    UNITS "hx100"
                    MAX-ACCESS read-write
                    STATUS current
                    DESCRIPTION "PUMP 1 RUN HOURS ALARM LIMIT"
                    ::= { integerObjects 46 }

        -- 1.3.6.1.4.1.9839.2.1.3.47
        set-hm100-p2 OBJECT-TYPE
                    SYNTAX Integer32 (0..320)
                    UNITS "hx100"
                    MAX-ACCESS read-write
                    STATUS current
                    DESCRIPTION "PUMP 2 RUN HOURS ALARM LIMIT"
                    ::= { integerObjects 47 }

        -- 1.3.6.1.4.1.9839.2.1.3.48
        set-hm100-pfc OBJECT-TYPE
                    SYNTAX Integer32 (0..320)
                    UNITS "hx100"
                    MAX-ACCESS read-write
                    STATUS current
                    DESCRIPTION "FREECOOLING PUMP RUN HOURS ALARM LIMIT"
                    ::= { integerObjects 48 }

        -- 1.3.6.1.4.1.9839.2.1.3.49
        offset-send-var OBJECT-TYPE
                    SYNTAX Integer32 (-32767..32767)
                    UNITS "N/A"
                    MAX-ACCESS read-write
                    STATUS current
                    DESCRIPTION "SENDING VARIABLES OFFSET"
                    ::= { integerObjects 49 }

        -- 1.3.6.1.4.1.9839.2.1.3.71
        dead-zone OBJECT-TYPE
                    SYNTAX Integer32 (-32767..32767)
                    UNITS "N/A"
                    MAX-ACCESS read-only
                    STATUS current
                    DESCRIPTION "DEAD ZONE"
                    ::= { integerObjects 71 }

        -- 1.3.6.1.4.1.9839.2.1.3.77
        inverter-speed-reg OBJECT-TYPE
                    SYNTAX Integer32 (-32767..32767)
                    UNITS "%"
                    MAX-ACCESS read-only
                    STATUS current
                    DESCRIPTION "INVERTER SPEED MODULATION (0...100%)"
                    ::= { integerObjects 77 }

	
	END

--
-- isa.MIB
--
