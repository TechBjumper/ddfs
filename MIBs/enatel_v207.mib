-- ENATEL SM32 MIB.
--
-- Author                   Date        Comment
-- ==================================================================
-- Michael McCormick	17/08/2008  	Initial
-- Regis Savry		01/12/2009  	added variables for the set request + revamp of traps handling + SNMP v2c
-- Regis Savry		09/06/2010  	added extra alarm trap numbers
-- Tony Ruiter		5 July 2011 	Made adjustements to powermodule table to allow it to compile in vietnam.
-- Tony Ruiter		28 May 2012		Made adjustments to capitalisation of power module table.
-- Tony Ruiter		12 August 2014	Put MIB through online parser fixed compatability issues with power module table
--									Added All alarm traps
--									Added new renewables nodes : solar,wind current, today\yesterday kWh
--									Added new renewables traps : solar, wind module alarms etc.
-- Tony Ruiter		23 Jan 2015		Added 5 "relay pulse" output nodes to allow toggling of relays from SNMP
-- Tony Ruiter		 4 Nov 2015 	Added all hybrid nodes read\write using new table system starting at index
-- Tony Ruiter		 6 Sep 2016		Added nodes
--										- Full 24 bloc strings for first 2 battery strings
--										- Firmware version nodes and webpage version node
--										- Readable Nodes, Holding Nodes, and a committing node for battery capacity and peukerts
--										- Number of communicating rectifiers
--										- Battery current limit Enabled, and setpoint
--										- NTP Enabled, NTP Server Address


Enatel DEFINITIONS ::= BEGIN

IMPORTS
   enterprises, IpAddress, Gauge, TimeTicks     FROM RFC1155-SMI
   DisplayString                                FROM RFC1213-MIB
   OBJECT-TYPE                                  FROM RFC-1212
   TRAP-TYPE                                    FROM RFC-1215
   NOTIFICATION-TYPE,Integer32					FROM SNMPv2-SMI;

enatel          	             		OBJECT IDENTIFIER ::=  { enterprises 21940 }
sitedata	                     		OBJECT IDENTIFIER ::=  { enatel 1 }
sm32		                     		OBJECT IDENTIFIER ::=  { enatel 2 }
sm36		                     		OBJECT IDENTIFIER ::=  { enatel 3 }
firmwareversions                   		OBJECT IDENTIFIER ::=  { sitedata 5 }
traps		                     		OBJECT IDENTIFIER ::=  { sm32 1 }
acmonitoring        	        		OBJECT IDENTIFIER ::=  { sm32 3 }
acmainsmonitor1		            		OBJECT IDENTIFIER ::=  { acmonitoring 1 }
acmainsmonitor2	                		OBJECT IDENTIFIER ::=  { acmonitoring 2 }
acmainsmonitor1int            			OBJECT IDENTIFIER ::=  { acmainsmonitor1 2 }
acmainsmonitor2int            			OBJECT IDENTIFIER ::=  { acmainsmonitor2 2 }
acmainsmonitor1string           		OBJECT IDENTIFIER ::=  { acmainsmonitor1 1 }
acmainsmonitor2string           		OBJECT IDENTIFIER ::=  { acmainsmonitor2 1 }
dcmonitoring       	            		OBJECT IDENTIFIER ::=  { sm32 4 }
dcmonitoringstring              		OBJECT IDENTIFIER ::=  { dcmonitoring 1 }
dcmonitoringint               			OBJECT IDENTIFIER ::=  { dcmonitoring 2 }
kwh										OBJECT IDENTIFIER ::=  { dcmonitoring 3 }
kwhtoday								OBJECT IDENTIFIER ::=  { kwh 1 }
kwhyesterday							OBJECT IDENTIFIER ::=  { kwh 2 }
control									OBJECT IDENTIFIER ::=  { sm32 5 }
systemcontrol							OBJECT IDENTIFIER ::=  { control 1 }
batterycontrol							OBJECT IDENTIFIER ::=  { control 2 }
rectifierscontrol						OBJECT IDENTIFIER ::=  { control 3 }
alarmthresholds							OBJECT IDENTIFIER ::=  { control 4 }
powermodules							OBJECT IDENTIFIER ::=  { control 5 }
relaypulse								OBJECT IDENTIFIER ::=  { control 6 }
batterycapacity							OBJECT IDENTIFIER ::=  { control 7 }
ntp										OBJECT IDENTIFIER ::=  { control 8 }
phasebalancing							OBJECT IDENTIFIER ::=  { control 9 }
convertercontrol						OBJECT IDENTIFIER ::=  { control 10 }
currentalarmthresholds					OBJECT IDENTIFIER ::=  { alarmthresholds 1 }
temperaturealarmthresholds				OBJECT IDENTIFIER ::=  { alarmthresholds 2 }
acalarmthresholds						OBJECT IDENTIFIER ::=  { alarmthresholds 3 }
voltagealarmthresholds					OBJECT IDENTIFIER ::=  { alarmthresholds 4 }
lvdalarmthresholds						OBJECT IDENTIFIER ::=  { alarmthresholds 5 }

-- Battery monitoring branches
batterystrings						OBJECT IDENTIFIER ::=  { dcmonitoring 4 }
string1								OBJECT IDENTIFIER ::=  { batterystrings 1 }
string2								OBJECT IDENTIFIER ::=  { batterystrings 2 }
string3								OBJECT IDENTIFIER ::=  { batterystrings 3 }
string4								OBJECT IDENTIFIER ::=  { batterystrings 4 }
string5								OBJECT IDENTIFIER ::=  { batterystrings 5 }
string6								OBJECT IDENTIFIER ::=  { batterystrings 6 }
string7								OBJECT IDENTIFIER ::=  { batterystrings 7 }
string8								OBJECT IDENTIFIER ::=  { batterystrings 8 }
string9								OBJECT IDENTIFIER ::=  { batterystrings 9 }
string10							OBJECT IDENTIFIER ::=  { batterystrings 10 }

-- Hybrid OID branches
hybrid						OBJECT IDENTIFIER ::=  { sm32 10 }
alarms						OBJECT IDENTIFIER ::=  { sm32 11 }
hybsetup					OBJECT IDENTIFIER ::=  { hybrid 1 }
hybgeneralsetup				OBJECT IDENTIFIER ::=  { hybsetup 1 }
hybadvancedsetup			OBJECT IDENTIFIER ::=  { hybsetup 2 }
hybcyclesetup				OBJECT IDENTIFIER ::=  { hybsetup 3 }
hyblowbatcapsetup			OBJECT IDENTIFIER ::=  { hybcyclesetup 1 }
hybcomchargesetup			OBJECT IDENTIFIER ::=  { hybcyclesetup 2 }
hybstarttimeasetup			OBJECT IDENTIFIER ::=  { hybcyclesetup 3 }
hybstarttimebsetup			OBJECT IDENTIFIER ::=  { hybcyclesetup 4 }
hyblowvoltagestartsetup		OBJECT IDENTIFIER ::=  { hybcyclesetup 5 }
hybextendedchargesetup		OBJECT IDENTIFIER ::=  { hybcyclesetup 6 }
hybgentestsetup				OBJECT IDENTIFIER ::=  { hybcyclesetup 7 }
hybextralowvoltagestart		OBJECT IDENTIFIER ::=  { hybcyclesetup 8 }
hybsolaroptimisation		OBJECT IDENTIFIER ::=  { hybsetup 4 }
hybsolaroptgeneralsetup		OBJECT IDENTIFIER ::=  { hybsolaroptimisation 1 }
hybfueltanksetup			OBJECT IDENTIFIER ::=  { hybsetup 5 }
hybtankconfig				OBJECT IDENTIFIER ::=  { hybfueltanksetup 1 }
hybfueltank1setup			OBJECT IDENTIFIER ::=  { hybfueltanksetup 2 }
hybfueltank2setup			OBJECT IDENTIFIER ::=  { hybfueltanksetup 3 }
hybstatus					OBJECT IDENTIFIER ::=  { hybrid 2 }
hybcurrents					OBJECT IDENTIFIER ::=  { hybstatus 1 }
hybpowers					OBJECT IDENTIFIER ::=  { hybstatus 2 }
hybrunhours					OBJECT IDENTIFIER ::=  { hybstatus 3 }
hybstate					OBJECT IDENTIFIER ::=  { hybstatus 4 }
hybacmonitoring				OBJECT IDENTIFIER ::=  { hybstatus 5 }
hybflags					OBJECT IDENTIFIER ::=  { hybstatus 6 }
hybgeneralflags				OBJECT IDENTIFIER ::=  { hybflags 1 }
hybgen1flags				OBJECT IDENTIFIER ::=  { hybflags 2 }
hybgen2flags				OBJECT IDENTIFIER ::=  { hybflags 3 }
hybgridflags				OBJECT IDENTIFIER ::=  { hybflags 4 }
hybfueltanks				OBJECT IDENTIFIER ::=  { hybstatus 7 }
hybfueltankgeneral			OBJECT IDENTIFIER ::=  { hybfueltanks 1 }
hybfueltank1				OBJECT IDENTIFIER ::=  { hybfueltanks 2 }
hybfueltank2				OBJECT IDENTIFIER ::=  { hybfueltanks 3 }


	ALARMS			::=   INTEGER { idle(0), active(1) }


sitelocation1 OBJECT-TYPE
   SYNTAX DisplayString
   UNITS ""
   MAX-ACCESS read-write
   STATUS current
   DESCRIPTION
      "Site Location information 1"
   ::= { sitedata 1 }

sitelocation2 OBJECT-TYPE
   SYNTAX DisplayString
   UNITS ""
   MAX-ACCESS read-write
   STATUS current
   DESCRIPTION
      "Site Location information 2"
   ::= { sitedata 2 }

sitelocation3 OBJECT-TYPE
   SYNTAX DisplayString
   UNITS ""
   MAX-ACCESS read-write
   STATUS current
   DESCRIPTION
      "Site Location information 3"
   ::= { sitedata 3 }


mm1voltagephase1 OBJECT-TYPE
   SYNTAX DisplayString
   UNITS "Volts"
   MAX-ACCESS read-only
   STATUS obsolete
   DESCRIPTION
      "Mains Monitor 1 Voltage Phase 1"
   ::= { acmainsmonitor1string 1 }

mm1voltagephase1int OBJECT-TYPE
   SYNTAX Integer32
   UNITS "Millivolts"
   MAX-ACCESS read-only
   STATUS current
   DESCRIPTION
      "Mains Monitor 1 Voltage Phase 1"
   ::= { acmainsmonitor1int 1 }

mm1voltagephase2 OBJECT-TYPE
   SYNTAX DisplayString
   UNITS "Volts"
   MAX-ACCESS read-only
   STATUS obsolete
   DESCRIPTION
      "Mains Monitor 1 Voltage Phase 2"
   ::= { acmainsmonitor1string 2 }

mm1voltagephase2int OBJECT-TYPE
   SYNTAX Integer32
   UNITS "Millivolts"
   MAX-ACCESS read-only
   STATUS current
   DESCRIPTION
      "Mains Monitor 1 Voltage Phase 2"
   ::= { acmainsmonitor1int 2 }

mm1voltagephase3 OBJECT-TYPE
   SYNTAX DisplayString
   UNITS "Volts"
   MAX-ACCESS read-only
   STATUS obsolete
   DESCRIPTION
      "Mains Monitor 1 Voltage Phase 3"
   ::= { acmainsmonitor1string 3 }

mm1voltagephase3int OBJECT-TYPE
   SYNTAX Integer32
   UNITS "Millivolts"
   MAX-ACCESS read-only
   STATUS current
   DESCRIPTION
      "Mains Monitor 1 Voltage Phase 3"
   ::= { acmainsmonitor1int 3 }

mm1currentphase1 OBJECT-TYPE
   SYNTAX DisplayString
   UNITS "Amps"
   MAX-ACCESS read-only
   STATUS obsolete
   DESCRIPTION
      "Mains Monitor 1 Current Phase 1"
   ::= { acmainsmonitor1string 4 }

mm1currentphase1int OBJECT-TYPE
   SYNTAX Integer32
   UNITS "Milliamps"
   MAX-ACCESS read-only
   STATUS current
   DESCRIPTION
      "Mains Monitor 1 Current Phase 1"
   ::= { acmainsmonitor1int 4 }

mm1currentphase2 OBJECT-TYPE
   SYNTAX DisplayString
   UNITS "Amps"
   MAX-ACCESS read-only
   STATUS obsolete
   DESCRIPTION
      "Mains Monitor 1 Current Phase 2"
   ::= { acmainsmonitor1string 5 }

mm1currentphase2int OBJECT-TYPE
   SYNTAX Integer32
   UNITS "Milliamps"
   MAX-ACCESS read-only
   STATUS current
   DESCRIPTION
      "Mains Monitor 1 Current Phase 2"
   ::= { acmainsmonitor1int 5 }

mm1currentphase3 OBJECT-TYPE
   SYNTAX DisplayString
   UNITS "Amps"
   MAX-ACCESS read-only
   STATUS obsolete
   DESCRIPTION
      "Mains Monitor 1 Current Phase 3"
   ::= { acmainsmonitor1string 6 }

mm1currentphase3int OBJECT-TYPE
   SYNTAX Integer32
   UNITS "Milliamps"
   MAX-ACCESS read-only
   STATUS current
   DESCRIPTION
      "Mains Monitor 1 Current Phase 3"
   ::= { acmainsmonitor1int 6 }

mm1frequency OBJECT-TYPE
   SYNTAX DisplayString
   UNITS "Hz"
   MAX-ACCESS read-only
   STATUS obsolete
   DESCRIPTION
      "Mains Monitor 1 Frequency"
   ::= { acmainsmonitor1string 7 }

mm1frequencyint OBJECT-TYPE
   SYNTAX Integer32
   UNITS "Hz"
   MAX-ACCESS read-only
   STATUS current
   DESCRIPTION
      "Mains Monitor 1 Frequency"
   ::= { acmainsmonitor1int 7 }

mm2voltagephase1 OBJECT-TYPE
   SYNTAX DisplayString
   UNITS "Volts"
   MAX-ACCESS read-only
   STATUS obsolete
   DESCRIPTION
      "Mains Monitor 2 Voltage Phase 1"
   ::= { acmainsmonitor2string 1 }

mm2voltagephase1int OBJECT-TYPE
   SYNTAX Integer32
   UNITS "Volts"
   MAX-ACCESS read-only
   STATUS current
   DESCRIPTION
      "Mains Monitor 2 Voltage Phase 1"
   ::= { acmainsmonitor2int 1 }

mm2voltagephase2 OBJECT-TYPE
   SYNTAX DisplayString
   UNITS "Volts"
   MAX-ACCESS read-only
   STATUS obsolete
   DESCRIPTION
      "Mains Monitor 2 Voltage Phase 2"
   ::= { acmainsmonitor2string 2 }

mm2voltagephase2int OBJECT-TYPE
   SYNTAX Integer32
   UNITS "Millivolts"
   MAX-ACCESS read-only
   STATUS current
   DESCRIPTION
      "Mains Monitor 2 Voltage Phase 2"
   ::= { acmainsmonitor2int 2 }

mm2voltagephase3 OBJECT-TYPE
   SYNTAX DisplayString
   UNITS "Volts"
   MAX-ACCESS read-only
   STATUS obsolete
   DESCRIPTION
      "Mains Monitor 2 Voltage Phase 3"
   ::= { acmainsmonitor2string 3 }

mm2voltagephase3int OBJECT-TYPE
   SYNTAX Integer32
   UNITS "Millivolts"
   MAX-ACCESS read-only
   STATUS current
   DESCRIPTION
      "Mains Monitor 2 Voltage Phase 3"
   ::= { acmainsmonitor2int 3 }

mm2currentphase1 OBJECT-TYPE
   SYNTAX DisplayString
   UNITS "Amps"
   MAX-ACCESS read-only
   STATUS obsolete
   DESCRIPTION
      "Mains Monitor 2 Current Phase 1"
   ::= { acmainsmonitor2string 4 }

mm2currentphase1int OBJECT-TYPE
   SYNTAX Integer32
   UNITS "Milliamps"
   MAX-ACCESS read-only
   STATUS current
   DESCRIPTION
      "Mains Monitor 2 Current Phase 1"
   ::= { acmainsmonitor2int 4 }


mm2currentphase2 OBJECT-TYPE
   SYNTAX DisplayString
   UNITS "Amps"
   MAX-ACCESS read-only
   STATUS obsolete
   DESCRIPTION
      "Mains Monitor 2 Current Phase 2"
   ::= { acmainsmonitor2string 5 }

mm2currentphase2int OBJECT-TYPE
   SYNTAX Integer32
   UNITS "Milliamps"
   MAX-ACCESS read-only
   STATUS current
   DESCRIPTION
      "Mains Monitor 2 Current Phase 2"
   ::= { acmainsmonitor2int 5 }

mm2currentphase3 OBJECT-TYPE
   SYNTAX DisplayString
   UNITS "Amps"
   MAX-ACCESS read-only
   STATUS obsolete
   DESCRIPTION
      "Mains Monitor 2 Current Phase 3"
   ::= { acmainsmonitor2string 6 }

mm2currentphase3int OBJECT-TYPE
   SYNTAX Integer32
   UNITS "Milliamps"
   MAX-ACCESS read-only
   STATUS current
   DESCRIPTION
      "Mains Monitor 2 Current Phase 3"
   ::= { acmainsmonitor2int 6 }

mm2frequency OBJECT-TYPE
   SYNTAX DisplayString
   UNITS "Hz"
   MAX-ACCESS read-only
   STATUS obsolete
   DESCRIPTION
      "Mains Monitor 2 Frequency"
   ::= { acmainsmonitor2string 7 }

mm2frequencyint OBJECT-TYPE
   SYNTAX Integer32
   UNITS "Hz"
   MAX-ACCESS read-only
   STATUS current
   DESCRIPTION
      "Mains Monitor 2 Frequency"
   ::= { acmainsmonitor2int 7 }

-- DC MONITORING

rectifiervoltage OBJECT-TYPE
   SYNTAX DisplayString
   UNITS "Volts"
   MAX-ACCESS read-only
   STATUS obsolete
   DESCRIPTION
      "Bus 1 Voltage"
   ::= { dcmonitoringstring 1 }

rectifiervoltageint OBJECT-TYPE
   SYNTAX Integer32
   UNITS "Millivolts"
   MAX-ACCESS read-only
   STATUS current
   DESCRIPTION
      "Bus 1 Voltage"
   ::= { dcmonitoringint 1 }

rectifiercurrent OBJECT-TYPE
   SYNTAX DisplayString
   UNITS "Amps"
   MAX-ACCESS read-only
   STATUS obsolete
   DESCRIPTION
      "Rectifier Current"
   ::= { dcmonitoringstring 2 }

rectifiercurrentint OBJECT-TYPE
   SYNTAX Integer32
   UNITS "Amps"
   MAX-ACCESS read-only
   STATUS current
   DESCRIPTION
      "Rectifier Current"
   ::= { dcmonitoringint 2 }

convertervoltage12v OBJECT-TYPE
   SYNTAX DisplayString
   UNITS "Volts"
   MAX-ACCESS read-only
   STATUS obsolete
   DESCRIPTION
      "Converter Voltage"
   ::= { dcmonitoringstring 3 }

convertervoltage12vint OBJECT-TYPE
   SYNTAX Integer32
   UNITS "Millivolts"
   MAX-ACCESS read-only
   STATUS current
   DESCRIPTION
      "Converter Voltage"
   ::= { dcmonitoringint 3 }

convertercurrent12v OBJECT-TYPE
   SYNTAX DisplayString
   UNITS "Amps"
   MAX-ACCESS read-only
   STATUS obsolete
   DESCRIPTION
      "Converter Current"
   ::= { dcmonitoringstring 4 }

convertercurrent12vint OBJECT-TYPE
   SYNTAX Integer32
   UNITS "Amps"
   MAX-ACCESS read-only
   STATUS current
   DESCRIPTION
      "Converter Current"
   ::= { dcmonitoringint 4 }

convertervoltage24v OBJECT-TYPE
   SYNTAX DisplayString
   UNITS "Volts"
   MAX-ACCESS read-only
   STATUS obsolete
   DESCRIPTION
      "Converter Voltage"
   ::= { dcmonitoringstring 5 }

convertervoltage24vint OBJECT-TYPE
   SYNTAX Integer32
   UNITS "Millivolts"
   MAX-ACCESS read-only
   STATUS current
   DESCRIPTION
      "Converter Voltage"
   ::= { dcmonitoringint 5 }

convertercurrent24v OBJECT-TYPE
   SYNTAX DisplayString
   UNITS "Amps"
   MAX-ACCESS read-only
   STATUS obsolete
   DESCRIPTION
      "Converter Current"
   ::= { dcmonitoringstring 6 }

convertercurrent24vint OBJECT-TYPE
   SYNTAX Integer32
   UNITS "Amps"
   MAX-ACCESS read-only
   STATUS current
   DESCRIPTION
      "Converter Current"
   ::= { dcmonitoringint 6 }

convertervoltage48v OBJECT-TYPE
   SYNTAX DisplayString
   UNITS "Volts"
   MAX-ACCESS read-only
   STATUS obsolete
   DESCRIPTION
      "Converter Voltage"
   ::= { dcmonitoringstring 7 }

convertervoltage48vint OBJECT-TYPE
   SYNTAX Integer32
   UNITS "Millivolts"
   MAX-ACCESS read-only
   STATUS current
   DESCRIPTION
      "Converter Voltage"
   ::= { dcmonitoringint 7 }

convertercurrent48v OBJECT-TYPE
   SYNTAX DisplayString
   UNITS "Amps"
   MAX-ACCESS read-only
   STATUS obsolete
   DESCRIPTION
      "Converter Current"
   ::= { dcmonitoringstring 8 }

convertercurrent48vint OBJECT-TYPE
   SYNTAX Integer32
   UNITS "Amps"
   MAX-ACCESS read-only
   STATUS current
   DESCRIPTION
      "Converter Current"
   ::= { dcmonitoringint 8 }

convertervoltage60v OBJECT-TYPE
   SYNTAX DisplayString
   UNITS "Volts"
   MAX-ACCESS read-only
   STATUS obsolete
   DESCRIPTION
      "Converter Voltage"
   ::= { dcmonitoringstring 9 }

convertervoltage60vint OBJECT-TYPE
   SYNTAX Integer32
   UNITS "Millivolts"
   MAX-ACCESS read-only
   STATUS current
   DESCRIPTION
      "Converter Voltage"
   ::= { dcmonitoringint 9 }

convertercurrent60v OBJECT-TYPE
   SYNTAX DisplayString
   UNITS "Amps"
   MAX-ACCESS read-only
   STATUS obsolete
   DESCRIPTION
      "Converter Current"
   ::= { dcmonitoringstring 10 }

convertercurrent60vint OBJECT-TYPE
   SYNTAX Integer32
   UNITS "Amps"
   MAX-ACCESS read-only
   STATUS current
   DESCRIPTION
      "Converter Current"
   ::= { dcmonitoringint 10 }

invertervoltage OBJECT-TYPE
   SYNTAX DisplayString
   UNITS "Volts"
   MAX-ACCESS read-only
   STATUS obsolete
   DESCRIPTION
      "Converter Voltage"
   ::= { dcmonitoringstring 11 }

invertervoltageint OBJECT-TYPE
   SYNTAX Integer32
   UNITS "Millivolts"
   MAX-ACCESS read-only
   STATUS current
   DESCRIPTION
      "Converter Voltage"
   ::= { dcmonitoringint 11 }

invertercurrent OBJECT-TYPE
   SYNTAX DisplayString
   UNITS "Amps"
   MAX-ACCESS read-only
   STATUS obsolete
   DESCRIPTION
      "Converter Current"
   ::= { dcmonitoringstring 12 }

invertercurrentint OBJECT-TYPE
   SYNTAX Integer32
   UNITS "Milliamps"
   MAX-ACCESS read-only
   STATUS current
   DESCRIPTION
      "Converter Current"
   ::= { dcmonitoringint 12 }

loadcurrent OBJECT-TYPE
   SYNTAX DisplayString
   UNITS "Amps"
   MAX-ACCESS read-only
   STATUS obsolete
   DESCRIPTION
      "Load Current"
   ::= { dcmonitoringstring 13 }

loadcurrentint OBJECT-TYPE
   SYNTAX Integer32
   UNITS "Amps"
   MAX-ACCESS read-only
   STATUS current
   DESCRIPTION
      "Load Current"
   ::= { dcmonitoringint 13 }

batterycurrent OBJECT-TYPE
   SYNTAX DisplayString
   UNITS "Amps"
   MAX-ACCESS read-only
   STATUS obsolete
   DESCRIPTION
      "Battery Current"
   ::= { dcmonitoringstring 14 }

batterycurrentint OBJECT-TYPE
   SYNTAX Integer32
   UNITS "Amps"
   MAX-ACCESS read-only
   STATUS current
   DESCRIPTION
      "Battery Current"
   ::= { dcmonitoringint 14 }

batterytemperature OBJECT-TYPE
   SYNTAX DisplayString
   UNITS "DegC"
   MAX-ACCESS read-only
   STATUS obsolete
   DESCRIPTION
      "Battery Temperature"
   ::= { dcmonitoringstring 15 }

batterytemperatureint OBJECT-TYPE
   SYNTAX Integer32
   UNITS "0.1 DegC"
   MAX-ACCESS read-only
   STATUS current
   DESCRIPTION
      "Battery Temperature"
   ::= { dcmonitoringint 15 }

ambienttemperature OBJECT-TYPE
   SYNTAX DisplayString
   UNITS "DegC"
   MAX-ACCESS read-only
   STATUS obsolete
   DESCRIPTION
      "Ambient Temperature"
   ::= { dcmonitoringstring 16 }

ambienttemperatureint OBJECT-TYPE
   SYNTAX Integer32
   UNITS "0.1 DegC"
   MAX-ACCESS read-only
   STATUS current
   DESCRIPTION
      "Ambient Temperature"
   ::= { dcmonitoringint 16 }

batterycapacitystr OBJECT-TYPE
   SYNTAX DisplayString
   UNITS "%"
   MAX-ACCESS read-only
   STATUS obsolete
   DESCRIPTION
      "Battery Capacity"
   ::= { dcmonitoringstring 17 }

batterycapacityint OBJECT-TYPE
   SYNTAX Integer32
   UNITS "%"
   MAX-ACCESS read-only
   STATUS current
   DESCRIPTION
      "Battery Capacity"
   ::= { dcmonitoringint 17 }

staticbypassoutputpower OBJECT-TYPE
   SYNTAX DisplayString
   UNITS "VA"
   MAX-ACCESS read-only
   STATUS obsolete
   DESCRIPTION
      "Static Bypass Output Power"
   ::= { dcmonitoringstring 18 }

staticbypassoutputpowerint OBJECT-TYPE
   SYNTAX Integer32
   UNITS "VA"
   MAX-ACCESS read-only
   STATUS current
   DESCRIPTION
      "Static Bypass Output Power"
   ::= { dcmonitoringint 18 }

staticbypassoutputcurrent OBJECT-TYPE
   SYNTAX DisplayString
   UNITS "A"
   MAX-ACCESS read-only
   STATUS obsolete
   DESCRIPTION
      "Static Bypass Output Current"
   ::= { dcmonitoringstring 19 }

staticbypassoutputcurrentint OBJECT-TYPE
   SYNTAX Integer32
   UNITS "mA"
   MAX-ACCESS read-only
   STATUS current
   DESCRIPTION
      "Static Bypass Output Current"
   ::= { dcmonitoringint 19 }

staticbypassoutputvoltage OBJECT-TYPE
   SYNTAX DisplayString
   UNITS "V"
   MAX-ACCESS read-only
   STATUS obsolete
   DESCRIPTION
      "Static Bypass Output Voltage"
   ::= { dcmonitoringstring 20 }

staticbypassoutputvoltageint OBJECT-TYPE
   SYNTAX Integer32
   UNITS "mV"
   MAX-ACCESS read-only
   STATUS current
   DESCRIPTION
      "Static Bypass Output Voltage"
   ::= { dcmonitoringint 20 }

staticbypassoutputfrequency OBJECT-TYPE
   SYNTAX DisplayString
   UNITS "Hz"
   MAX-ACCESS read-only
   STATUS obsolete
   DESCRIPTION
      "Static Bypass Output Frequency"
   ::= { dcmonitoringstring 21 }

staticbypassoutputfrequencyint OBJECT-TYPE
   SYNTAX Integer32
   UNITS "Hz"
   MAX-ACCESS read-only
   STATUS current
   DESCRIPTION
      "Static Bypass Output Frequency"
   ::= { dcmonitoringint 21 }

staticbypassinverterinputvoltage OBJECT-TYPE
   SYNTAX DisplayString
   UNITS "V"
   MAX-ACCESS read-only
   STATUS obsolete
   DESCRIPTION
      "Static Bypass Inverter Input Voltage"
   ::= { dcmonitoringstring 22 }

staticbypassinverterinputvoltageint OBJECT-TYPE
   SYNTAX Integer32
   UNITS "mV"
   MAX-ACCESS read-only
   STATUS current
   DESCRIPTION
      "Static Bypass Inverter Input Voltage"
   ::= { dcmonitoringint 22 }

staticbypassmainsinputvoltage OBJECT-TYPE
   SYNTAX DisplayString
   UNITS "V"
   MAX-ACCESS read-only
   STATUS obsolete
   DESCRIPTION
      "Static Bypass Mains Input Voltage"
   ::= { dcmonitoringstring 23 }

staticbypassmainsinputvoltageint OBJECT-TYPE
   SYNTAX Integer32
   UNITS "mV"
   MAX-ACCESS read-only
   STATUS current
   DESCRIPTION
      "Static Bypass Mains Input Voltage"
   ::= { dcmonitoringint 23 }



batterydischargetimeremainingint OBJECT-TYPE
   SYNTAX INTEGER
   UNITS "minutes"
   MAX-ACCESS read-only
   STATUS current
   DESCRIPTION
      "Battery Discharge Time Remaining"
   ::= { dcmonitoringint 24 }

solarcurrent OBJECT-TYPE
   SYNTAX DisplayString
   UNITS "Amps"
   MAX-ACCESS read-only
   STATUS obsolete
   DESCRIPTION
      "Solar Current"
   ::= { dcmonitoringint 25 }

windcurrent OBJECT-TYPE
   SYNTAX DisplayString
   UNITS "Amps"
   MAX-ACCESS read-only
   STATUS obsolete
   DESCRIPTION
      "Wind Current"
   ::= { dcmonitoringint 26 }


kwhtodayload1 OBJECT-TYPE
   SYNTAX DisplayString
   UNITS "kWhx100"
   MAX-ACCESS read-only
   STATUS obsolete
   DESCRIPTION
      "kWh Today Load 1"
   ::= { kwhtoday 1 }

kwhtodayload2 OBJECT-TYPE
   SYNTAX DisplayString
   UNITS "kWhx100"
   MAX-ACCESS read-only
   STATUS obsolete
   DESCRIPTION
      "kWh Today Load 2"
   ::= { kwhtoday 2 }

kwhtodayload3 OBJECT-TYPE
   SYNTAX DisplayString
   UNITS "kWhx100"
   MAX-ACCESS read-only
   STATUS obsolete
   DESCRIPTION
      "kWh Today Load 3"
   ::= { kwhtoday 3 }

kwhtodaybatchrg OBJECT-TYPE
   SYNTAX DisplayString
   UNITS "kWhx100"
   MAX-ACCESS read-only
   STATUS obsolete
   DESCRIPTION
      "kWh Today Battery Charge"
   ::= { kwhtoday 4 }

kwhtodaybatdis OBJECT-TYPE
   SYNTAX DisplayString
   UNITS "kWhx100"
   MAX-ACCESS read-only
   STATUS obsolete
   DESCRIPTION
      "kWh Today Battery Discharge"
   ::= { kwhtoday 5 }

kwhtodaysolar OBJECT-TYPE
   SYNTAX DisplayString
   UNITS "kWhx100"
   MAX-ACCESS read-only
   STATUS obsolete
   DESCRIPTION
      "kWh Today Solar"
   ::= { kwhtoday 6 }

kwhtodaywind OBJECT-TYPE
   SYNTAX DisplayString
   UNITS "kWhx100"
   MAX-ACCESS read-only
   STATUS obsolete
   DESCRIPTION
      "kWh Today Wind"
   ::= { kwhtoday 7 }

kwhtodaygrid OBJECT-TYPE
   SYNTAX DisplayString
   UNITS "kWhx100"
   MAX-ACCESS read-only
   STATUS obsolete
   DESCRIPTION
      "kWh Today Grid"
   ::= { kwhtoday 8 }

kwhtodaygen1 OBJECT-TYPE
   SYNTAX DisplayString
   UNITS "kWhx100"
   MAX-ACCESS read-only
   STATUS obsolete
   DESCRIPTION
      "kWh Today Generator 1"
   ::= { kwhtoday 9 }

kwhtodaygen2 OBJECT-TYPE
   SYNTAX DisplayString
   UNITS "kWhx100"
   MAX-ACCESS read-only
   STATUS obsolete
   DESCRIPTION
      "kWh Today Generator 2"
   ::= { kwhtoday 10 }







kwhyesterdayload1 OBJECT-TYPE
   SYNTAX DisplayString
   UNITS "kWhx100"
   MAX-ACCESS read-only
   STATUS obsolete
   DESCRIPTION
      "kWh Yesterday Load 1"
   ::= { kwhyesterday 1 }

kwhyesterdayload2 OBJECT-TYPE
   SYNTAX DisplayString
   UNITS "kWhx100"
   MAX-ACCESS read-only
   STATUS obsolete
   DESCRIPTION
      "kWh Yesterday Load 2"
   ::= { kwhyesterday 2 }

kwhyesterdayload3 OBJECT-TYPE
   SYNTAX DisplayString
   UNITS "kWhx100"
   MAX-ACCESS read-only
   STATUS obsolete
   DESCRIPTION
      "kWh Yesterday Load 3"
   ::= { kwhyesterday 3 }

kwhyesterdaybatchrg OBJECT-TYPE
   SYNTAX DisplayString
   UNITS "kWhx100"
   MAX-ACCESS read-only
   STATUS obsolete
   DESCRIPTION
      "kWh Yesterday Battery Charge"
   ::= { kwhyesterday 4 }

kwhyesterdaybatdis OBJECT-TYPE
   SYNTAX DisplayString
   UNITS "kWhx100"
   MAX-ACCESS read-only
   STATUS obsolete
   DESCRIPTION
      "kWh Yesterday Battery Discharge"
   ::= { kwhyesterday 5 }

kwhyesterdaysolar OBJECT-TYPE
   SYNTAX DisplayString
   UNITS "kWhx100"
   MAX-ACCESS read-only
   STATUS obsolete
   DESCRIPTION
      "kWh Yesterday Solar"
   ::= { kwhyesterday 6 }

kwhyesterdaywind OBJECT-TYPE
   SYNTAX DisplayString
   UNITS "kWhx100"
   MAX-ACCESS read-only
   STATUS obsolete
   DESCRIPTION
      "kWh Yesterday Wind"
   ::= { kwhyesterday 7 }

kwhyesterdaygrid OBJECT-TYPE
   SYNTAX DisplayString
   UNITS "kWhx100"
   MAX-ACCESS read-only
   STATUS obsolete
   DESCRIPTION
      "kWh Yesterday Grid"
   ::= { kwhyesterday 8 }

kwhyesterdaygen1 OBJECT-TYPE
   SYNTAX DisplayString
   UNITS "kWhx100"
   MAX-ACCESS read-only
   STATUS obsolete
   DESCRIPTION
      "kWh Yesterday Generator 1"
   ::= { kwhyesterday 9 }

kwhyesterdaygen2 OBJECT-TYPE
   SYNTAX DisplayString
   UNITS "kWhx100"
   MAX-ACCESS read-only
   STATUS obsolete
   DESCRIPTION
      "kWh Yesterday Generator 2"
   ::= { kwhyesterday 10 }


















batterytestenable OBJECT-TYPE
    SYNTAX INTEGER { yes(1), no(0) }
    MAX-ACCESS read-write
    STATUS current
    DESCRIPTION
        "Initiate/start a battery test procedure"
    ::= { batterycontrol 1 }

batterymanualequiliseenable OBJECT-TYPE
    SYNTAX INTEGER { yes(1), no(0) }
    MAX-ACCESS read-write
    STATUS current
    DESCRIPTION
        "Initiate/start a battery manual equilise procedure"
    ::= { batterycontrol 2 }

rectifierpowersaveenable OBJECT-TYPE
    SYNTAX INTEGER { yes(1), no(0) }
    MAX-ACCESS read-write
    STATUS current
    DESCRIPTION
        "Enable/disable load based rectifier shutdown function"
    ::= { rectifierscontrol 1 }

rectifierfloatvoltagesetpoint OBJECT-TYPE
    SYNTAX INTEGER
	UNITS "mV"
    MAX-ACCESS read-write
    STATUS current
    DESCRIPTION
        "rectifier float voltage set point"
    ::= { rectifierscontrol 2 }


systemtime OBJECT-TYPE
   SYNTAX DisplayString
   UNITS ""
   MAX-ACCESS read-write
   STATUS current
   DESCRIPTION
      "System time"
   ::= { systemcontrol 1 }

loadcurrenthighalarmsetpoint OBJECT-TYPE
    SYNTAX INTEGER
	UNITS "A"
    MAX-ACCESS read-write
    STATUS current
    DESCRIPTION
        "Load Current High Alarm Setpoint"
    ::= { currentalarmthresholds 1 }

batterycurrenthighalarmsetpoint OBJECT-TYPE
    SYNTAX INTEGER
	UNITS "A"
    MAX-ACCESS read-write
    STATUS current
    DESCRIPTION
        "Battery Current High Alarm Setpoint"
    ::= { currentalarmthresholds 2 }

batterystringcurrenthighalarmsetpoint OBJECT-TYPE
    SYNTAX INTEGER
	UNITS "A"
    MAX-ACCESS read-write
    STATUS current
    DESCRIPTION
        "Battery String Current High Alarm Setpoint"
    ::= { currentalarmthresholds 3 }

batterystringcurrentimbalancethreshold OBJECT-TYPE
    SYNTAX INTEGER
	UNITS "A"
    MAX-ACCESS read-write
    STATUS current
    DESCRIPTION
        "Battery String Current Imbalance Threshold"
    ::= { currentalarmthresholds 4 }

batterydischargethreshold OBJECT-TYPE
    SYNTAX INTEGER
	UNITS "A"
    MAX-ACCESS read-write
    STATUS current
    DESCRIPTION
        "Battery Discharge Threshold"
    ::= { currentalarmthresholds 5 }

batterytemperaturelowalarmsetpoint OBJECT-TYPE
    SYNTAX INTEGER
	UNITS "0.1 DegC"
    MAX-ACCESS read-write
    STATUS current
    DESCRIPTION
        "Battery Temperature Low Alarm Setpoint"
    ::= { temperaturealarmthresholds 1 }

batterytemperaturehighalarmsetpoint OBJECT-TYPE
    SYNTAX INTEGER
	UNITS "0.1 DegC"
    MAX-ACCESS read-write
    STATUS current
    DESCRIPTION
        "Battery Temperature High Alarm Setpoint"
    ::= { temperaturealarmthresholds 2 }

batterytemperaturehysteresis OBJECT-TYPE
    SYNTAX INTEGER
	UNITS "0.1 DegC"
    MAX-ACCESS read-write
    STATUS current
    DESCRIPTION
        "Battery Temperature Hysteresis"
    ::= { temperaturealarmthresholds 3 }

ambienttemperaturelowalarmsetpoint OBJECT-TYPE
    SYNTAX INTEGER
	UNITS "0.1 DegC"
    MAX-ACCESS read-write
    STATUS current
    DESCRIPTION
        "Ambient Temperature Low Alarm Setpoint"
    ::= { temperaturealarmthresholds 4 }

ambienttemperaturehighalarmsetpoint OBJECT-TYPE
    SYNTAX INTEGER
	UNITS "0.1 DegC"
    MAX-ACCESS read-write
    STATUS current
    DESCRIPTION
        "Ambient Temperature High Alarm Setpoint"
    ::= { temperaturealarmthresholds 5 }

ambienttemperaturehysteresis OBJECT-TYPE
    SYNTAX INTEGER
	UNITS "0.1 DegC"
    MAX-ACCESS read-write
    STATUS current
    DESCRIPTION
        "Ambient Temperature Hysteresis"
    ::= { temperaturealarmthresholds 6 }

acvoltagehighalarmsetpoint OBJECT-TYPE
   SYNTAX INTEGER
   UNITS "mV"
   MAX-ACCESS read-write
   STATUS current
   DESCRIPTION
      "AC Voltage High Alarm Setpoint"
   ::= { acalarmthresholds 1 }

acvoltagelowalarmsetpoint OBJECT-TYPE
   SYNTAX INTEGER
   UNITS "mV"
   MAX-ACCESS read-write
   STATUS current
   DESCRIPTION
      "AC Voltage Low Alarm Setpoint"
   ::= { acalarmthresholds 2 }

acphaselostalarmsetpoint OBJECT-TYPE
   SYNTAX INTEGER
   UNITS "mV"
   MAX-ACCESS read-write
   STATUS current
   DESCRIPTION
      "AC Phase Lost Alarm Setpoint"
   ::= { acalarmthresholds 3 }

accurrenthighalarmsetpoint OBJECT-TYPE
   SYNTAX INTEGER
   UNITS "A"
   MAX-ACCESS read-write
   STATUS current
   DESCRIPTION
      "AC Current High Alarm Setpoint"
   ::= { acalarmthresholds 4 }

acfrequencyhighalarmsetpoint OBJECT-TYPE
   SYNTAX INTEGER
   UNITS "Hz"
   MAX-ACCESS read-write
   STATUS current
   DESCRIPTION
      "AC Frequency High Alarm Setpoint"
   ::= { acalarmthresholds 5 }

acfrequencylowalarmsetpoint OBJECT-TYPE
   SYNTAX INTEGER
   UNITS "Hz"
   MAX-ACCESS read-write
   STATUS current
   DESCRIPTION
      "AC Frequency Low Alarm Setpoint"
   ::= { acalarmthresholds 6 }

highvoltsalarmbus1setpoint OBJECT-TYPE
   SYNTAX INTEGER
   UNITS "mV"
   MAX-ACCESS read-write
   STATUS current
   DESCRIPTION
      "High Volts Alarm Bus 1 Setpoint"
   ::= { voltagealarmthresholds 1 }

highfloatalarmbus1setpoint OBJECT-TYPE
   SYNTAX INTEGER
   UNITS "mV"
   MAX-ACCESS read-write
   STATUS current
   DESCRIPTION
      "High Float Alarm Bus 1 Setpoint"
   ::= { voltagealarmthresholds 2 }

lowfloatalarmbus1setpoint OBJECT-TYPE
   SYNTAX INTEGER
   UNITS "mV"
   MAX-ACCESS read-write
   STATUS current
   DESCRIPTION
      "Low Float Alarm Bus 1 Setpoint"
   ::= { voltagealarmthresholds 3 }

lowvoltsalarmbus1setpoint OBJECT-TYPE
   SYNTAX INTEGER
   UNITS "mV"
   MAX-ACCESS read-write
   STATUS current
   DESCRIPTION
      "Low Volts Alarm Bus 1 Setpoint"
   ::= { voltagealarmthresholds 4 }

highvoltsalarmbus2setpoint OBJECT-TYPE
   SYNTAX INTEGER
   UNITS "mV"
   MAX-ACCESS read-write
   STATUS current
   DESCRIPTION
      "High Volts Alarm Bus 2 Setpoint"
   ::= { voltagealarmthresholds 5 }

highfloatalarmbus2setpoint OBJECT-TYPE
   SYNTAX INTEGER
   UNITS "mV"
   MAX-ACCESS read-write
   STATUS current
   DESCRIPTION
      "High Float Alarm Bus 2 Setpoint"
   ::= { voltagealarmthresholds 6 }

lowfloatalarmbus2setpoint OBJECT-TYPE
   SYNTAX INTEGER
   UNITS "mV"
   MAX-ACCESS read-write
   STATUS current
   DESCRIPTION
      "Low Float Alarm Bus 2 Setpoint"
   ::= { voltagealarmthresholds 7 }

lowvoltsalarmbus2setpoint OBJECT-TYPE
   SYNTAX INTEGER
   UNITS "mV"
   MAX-ACCESS read-write
   STATUS current
   DESCRIPTION
      "Low Volts Alarm Bus 2 Setpoint"
   ::= { voltagealarmthresholds 8 }

batterysymmetrythreshold OBJECT-TYPE
   SYNTAX INTEGER
   UNITS "mV"
   MAX-ACCESS read-write
   STATUS current
   DESCRIPTION
      "Battery Symmetry Threshold"
   ::= { voltagealarmthresholds 9 }

batterystringopenthreshold OBJECT-TYPE
   SYNTAX INTEGER
   UNITS "mV"
   MAX-ACCESS read-write
   STATUS current
   DESCRIPTION
      "Battery String Open Threshold"
   ::= { voltagealarmthresholds 10 }

lvd1disconnectsetpoint OBJECT-TYPE
   SYNTAX INTEGER
   UNITS "mV"
   MAX-ACCESS read-write
   STATUS current
   DESCRIPTION
      "LVD 1 Disconnect Setpoint"
   ::= { lvdalarmthresholds 1 }

lvd1reconnectsetpoint OBJECT-TYPE
   SYNTAX INTEGER
   UNITS "mV"
   MAX-ACCESS read-write
   STATUS current
   DESCRIPTION
      "LVD 1 Reconnect Setpoint"
   ::= { lvdalarmthresholds 2 }

lvd2disconnectsetpoint OBJECT-TYPE
   SYNTAX INTEGER
   UNITS "mV"
   MAX-ACCESS read-write
   STATUS current
   DESCRIPTION
      "LVD 2 Disconnect Setpoint"
   ::= { lvdalarmthresholds 3 }

lvd2reconnectsetpoint OBJECT-TYPE
   SYNTAX INTEGER
   UNITS "mV"
   MAX-ACCESS read-write
   STATUS current
   DESCRIPTION
      "LVD 2 Reconnect Setpoint"
   ::= { lvdalarmthresholds 4 }

lvd3disconnectsetpoint OBJECT-TYPE
   SYNTAX INTEGER
   UNITS "mV"
   MAX-ACCESS read-write
   STATUS current
   DESCRIPTION
      "LVD 3 Disconnect Setpoint"
   ::= { lvdalarmthresholds 5 }

lvd3reconnectsetpoint OBJECT-TYPE
   SYNTAX INTEGER
   UNITS "mV"
   MAX-ACCESS read-write
   STATUS current
   DESCRIPTION
      "LVD 3 Reconnect Setpoint"
   ::= { lvdalarmthresholds 6 }
































powermoduleTable OBJECT-TYPE
    SYNTAX SEQUENCE OF PowermoduleEntry
    MAX-ACCESS not-accessible
    STATUS current
    DESCRIPTION
        "power modules table"
    ::= { powermodules 1 }



powermoduleEntry OBJECT-TYPE
    SYNTAX PowermoduleEntry
    MAX-ACCESS not-accessible
    STATUS current
    DESCRIPTION
        ""
    INDEX { modulenumber }
     ::= { powermoduleTable 1 }

PowermoduleEntry ::=
    SEQUENCE {
	modulenumber
		INTEGER,
	powermoduleid
		DisplayString,
    powermoduleshutdown
            INTEGER,
    powermodulefanspeed1
            INTEGER,
    powermodulefanspeed2
            INTEGER,
	powermoduleoutputcurrent
		INTEGER,
	powermoduletemperature1
            INTEGER,
    powermoduletemperature2
            INTEGER,
    powermodulealarmstatus
            INTEGER
	}

modulenumber  OBJECT-TYPE
    SYNTAX INTEGER (0.. 255)
    MAX-ACCESS not-accessible
    STATUS current
    DESCRIPTION
        "Address of power module"
    ::= { powermoduleEntry 1 }



powermoduleid OBJECT-TYPE
    SYNTAX DisplayString
	UNITS ""
    MAX-ACCESS read-only
    STATUS current
    DESCRIPTION
        "Power Module ID"
    ::= { powermoduleEntry 2 }

powermoduleshutdown OBJECT-TYPE
    SYNTAX INTEGER { yes(1), no(0) }
	UNITS ""
    MAX-ACCESS read-write
    STATUS current
    DESCRIPTION
        "Power Module Shutdown Command"
    ::= { powermoduleEntry 3 }

powermodulefanspeed1 OBJECT-TYPE
    SYNTAX INTEGER
	UNITS "rpm"
    MAX-ACCESS read-only
    STATUS current
    DESCRIPTION
        "Power Module Fan Speed 1"
    ::= { powermoduleEntry 4 }

powermodulefanspeed2 OBJECT-TYPE
    SYNTAX INTEGER
	UNITS "rpm"
    MAX-ACCESS read-only
    STATUS current
    DESCRIPTION
        "Power module Fan Speed 2"
    ::= { powermoduleEntry 5 }

powermoduleoutputcurrent OBJECT-TYPE
    SYNTAX INTEGER
	UNITS "A"
    MAX-ACCESS read-only
    STATUS current
    DESCRIPTION
        "Power Module Output Current"
    ::= { powermoduleEntry 6 }

powermoduletemperature1 OBJECT-TYPE
    SYNTAX INTEGER
	UNITS "0.1 DegC"
    MAX-ACCESS read-only
    STATUS current
    DESCRIPTION
        "Power Module Temperature Measurment 1"
    ::= { powermoduleEntry 7 }

powermoduletemperature2 OBJECT-TYPE
    SYNTAX INTEGER
	UNITS "0.1 DegC"
    MAX-ACCESS read-only
    STATUS current
    DESCRIPTION
        "Power Module Temperature Measurment 2"
    ::= { powermoduleEntry 8 }

powermodulealarmstatus OBJECT-TYPE
    SYNTAX INTEGER
	UNITS ""
    MAX-ACCESS read-only
    STATUS current
    DESCRIPTION
        "Power Module Alarm status word"
    ::= { powermoduleEntry 9 }



-- ***********************************************************************
--                      5 Relay pulse nodes
-- ***********************************************************************

relayA OBJECT-TYPE
    SYNTAX INTEGER { yes(1), no(0) }
    MAX-ACCESS read-write
    STATUS current
    DESCRIPTION
        "Initiate relay pulse on notional relay A"
    ::= { relaypulse 1 }

relayB OBJECT-TYPE
    SYNTAX INTEGER { yes(1), no(0) }
    MAX-ACCESS read-write
    STATUS current
    DESCRIPTION
        "Initiate relay pulse on notional relay B"
    ::= { relaypulse 2 }

relayC OBJECT-TYPE
    SYNTAX INTEGER { yes(1), no(0) }
    MAX-ACCESS read-write
    STATUS current
    DESCRIPTION
        "Initiate relay pulse on notional relay C"
    ::= { relaypulse 3 }

relayD OBJECT-TYPE
    SYNTAX INTEGER { yes(1), no(0) }
    MAX-ACCESS read-write
    STATUS current
    DESCRIPTION
        "Initiate relay pulse on notional relay D"
    ::= { relaypulse 4 }

relayE OBJECT-TYPE
    SYNTAX INTEGER { yes(1), no(0) }
    MAX-ACCESS read-write
    STATUS current
    DESCRIPTION
        "Initiate relay pulse on notional relay E"
    ::= { relaypulse 5 }

	
-- AUTOMATICALLY GENERATED NODES
spbuztout OBJECT-TYPE
   SYNTAX Integer32
   UNITS "Seconds"
   MAX-ACCESS read-write
   STATUS current
   DESCRIPTION
      "Buzzer Timeout"
   ::= { systemcontrol 2 }

rstmonitor OBJECT-TYPE
   SYNTAX Integer32
   UNITS ""
   MAX-ACCESS read-write
   STATUS current
   DESCRIPTION
      "Reset Monitor"
   ::= { systemcontrol 3 }

verfwmn OBJECT-TYPE
   SYNTAX Integer32
   UNITS ""
   MAX-ACCESS read-only
   STATUS current
   DESCRIPTION
      "Main Firmware Version"
   ::= { firmwareversions 1 }

verfwadc OBJECT-TYPE
   SYNTAX Integer32
   UNITS ""
   MAX-ACCESS read-only
   STATUS current
   DESCRIPTION
      "ADC Firmware Version"
   ::= { firmwareversions 2 }

verfwdisp OBJECT-TYPE
   SYNTAX Integer32
   UNITS ""
   MAX-ACCESS read-only
   STATUS current
   DESCRIPTION
      "Display Firmware Version"
   ::= { firmwareversions 3 }

verfwnt OBJECT-TYPE
   SYNTAX Integer32
   UNITS ""
   MAX-ACCESS read-only
   STATUS current
   DESCRIPTION
      "Network Firmware Version"
   ::= { firmwareversions 5 }

verwebnt OBJECT-TYPE
   SYNTAX Integer32
   UNITS ""
   MAX-ACCESS read-only
   STATUS current
   DESCRIPTION
      "Network Webpage Version"
   ::= { firmwareversions 6 }

batt10hcap OBJECT-TYPE
   SYNTAX Integer32
   UNITS "AH"
   MAX-ACCESS read-only
   STATUS current
   DESCRIPTION
      "Battery 10h Capacity"
   ::= { batterycapacity 1 }

battxhhours OBJECT-TYPE
   SYNTAX Integer32
   UNITS "Hours"
   MAX-ACCESS read-only
   STATUS current
   DESCRIPTION
      "Battery Xh Hours"
   ::= { batterycapacity 2 }

battxhcap OBJECT-TYPE
   SYNTAX Integer32
   UNITS "AH"
   MAX-ACCESS read-only
   STATUS current
   DESCRIPTION
      "Battery Xh Capacity"
   ::= { batterycapacity 3 }

writebatt10hcap OBJECT-TYPE
   SYNTAX Integer32
   UNITS "AH"
   MAX-ACCESS read-write
   STATUS current
   DESCRIPTION
      "Battery 10h Capacity"
   ::= { batterycapacity 4 }

writebattxhhours OBJECT-TYPE
   SYNTAX Integer32
   UNITS "Hours"
   MAX-ACCESS read-write
   STATUS current
   DESCRIPTION
      "Battery Xh Hours"
   ::= { batterycapacity 5 }

writebattxhcap OBJECT-TYPE
   SYNTAX Integer32
   UNITS "AH"
   MAX-ACCESS read-write
   STATUS current
   DESCRIPTION
      "Battery Xh Capacity"
   ::= { batterycapacity 6 }

commitbattcap OBJECT-TYPE
   SYNTAX Integer32
   UNITS ""
   MAX-ACCESS read-write
   STATUS current
   DESCRIPTION
      "Commit Battery Capacity Values"
   ::= { batterycapacity 7 }

numcomrect OBJECT-TYPE
   SYNTAX Integer32
   UNITS ""
   MAX-ACCESS read-only
   STATUS current
   DESCRIPTION
      "Number of communicating rectifiers"
   ::= { rectifierscontrol 3 }

enbbattilimit OBJECT-TYPE
   SYNTAX Integer32
   UNITS ""
   MAX-ACCESS read-write
   STATUS current
   DESCRIPTION
      "Battery Current Limit Enabled"
   ::= { batterycontrol 3 }

spbattilimit OBJECT-TYPE
   SYNTAX Integer32
   UNITS "0.001 %"
   MAX-ACCESS read-write
   STATUS current
   DESCRIPTION
      "Battery Current Limit"
   ::= { batterycontrol 4 }

enbntp OBJECT-TYPE
   SYNTAX Integer32
   UNITS ""
   MAX-ACCESS read-write
   STATUS current
   DESCRIPTION
      "NTP Enable"
   ::= { ntp 1 }

spntpserver OBJECT-TYPE
   SYNTAX DisplayString
   UNITS ""
   MAX-ACCESS read-write
   STATUS current
   DESCRIPTION
      "NTP Server Address"
   ::= { ntp 2 }

spntpgmtofs OBJECT-TYPE
   SYNTAX DisplayString
   UNITS ""
   MAX-ACCESS read-write
   STATUS current
   DESCRIPTION
      "NTP GMT Timezone Offset"
   ::= { ntp 3 }

dosyncmonreset OBJECT-TYPE
   SYNTAX Integer32
   UNITS ""
   MAX-ACCESS read-write
   STATUS current
   DESCRIPTION
      "NTP Synchronisation and Monitor Reset"
   ::= { ntp 4 }

spconv12v OBJECT-TYPE
   SYNTAX Integer32
   UNITS "mV"
   MAX-ACCESS read-write
   STATUS current
   DESCRIPTION
      "12V Converter Voltage Setpoint"
   ::= { convertercontrol 1 }

spconv24v OBJECT-TYPE
   SYNTAX Integer32
   UNITS "mV"
   MAX-ACCESS read-write
   STATUS current
   DESCRIPTION
      "24V Converter Voltage Setpoint"
   ::= { convertercontrol 2 }

spconv48v OBJECT-TYPE
   SYNTAX Integer32
   UNITS "mV"
   MAX-ACCESS read-write
   STATUS current
   DESCRIPTION
      "48V Converter Voltage Setpoint"
   ::= { convertercontrol 3 }

spconv60v OBJECT-TYPE
   SYNTAX Integer32
   UNITS "mV"
   MAX-ACCESS read-write
   STATUS current
   DESCRIPTION
      "60V Converter Voltage Setpoint"
   ::= { convertercontrol 4 }

sprenwvbias OBJECT-TYPE
   SYNTAX Integer32
   UNITS "mV"
   MAX-ACCESS read-write
   STATUS current
   DESCRIPTION
      "Renewables Voltage Setpoint Bias"
   ::= { powermodules 2 }

enbbattpequal OBJECT-TYPE
   SYNTAX Integer32
   UNITS ""
   MAX-ACCESS read-write
   STATUS current
   DESCRIPTION
      "Periodic Equalise Enabled"
   ::= { batterycontrol 13 }

spbattpequalint OBJECT-TYPE
   SYNTAX Integer32
   UNITS "Days"
   MAX-ACCESS read-write
   STATUS current
   DESCRIPTION
      "Periodic Equalise Interval"
   ::= { batterycontrol 14 }

spbattpequaldur OBJECT-TYPE
   SYNTAX Integer32
   UNITS "Minutes"
   MAX-ACCESS read-write
   STATUS current
   DESCRIPTION
      "Periodic Equalise Duration"
   ::= { batterycontrol 15 }

spbattpequalv OBJECT-TYPE
   SYNTAX Integer32
   UNITS "mV"
   MAX-ACCESS read-write
   STATUS current
   DESCRIPTION
      "Periodic Equalise Setpoint"
   ::= { batterycontrol 16 }

spbattmequaldur OBJECT-TYPE
   SYNTAX Integer32
   UNITS "Minutes"
   MAX-ACCESS read-write
   STATUS current
   DESCRIPTION
      "Manual Equalise Duration"
   ::= { batterycontrol 17 }

spbattmequalv OBJECT-TYPE
   SYNTAX Integer32
   UNITS "mV"
   MAX-ACCESS read-write
   STATUS current
   DESCRIPTION
      "Manual Equalise Setpoint"
   ::= { batterycontrol 18 }

enbbattfchg OBJECT-TYPE
   SYNTAX Integer32
   UNITS ""
   MAX-ACCESS read-write
   STATUS current
   DESCRIPTION
      "Fast Charge Enabled"
   ::= { batterycontrol 5 }

spbattfchgv OBJECT-TYPE
   SYNTAX Integer32
   UNITS "mV"
   MAX-ACCESS read-write
   STATUS current
   DESCRIPTION
      "Fast Charge Voltage Setpoint"
   ::= { batterycontrol 6 }

spbattfchgcapthres OBJECT-TYPE
   SYNTAX Integer32
   UNITS "0.001 %"
   MAX-ACCESS read-write
   STATUS current
   DESCRIPTION
      "Fast Charge Battery Capacity Start"
   ::= { batterycontrol 7 }

spbattfchgdur OBJECT-TYPE
   SYNTAX Integer32
   UNITS "Minutes"
   MAX-ACCESS read-write
   STATUS current
   DESCRIPTION
      "Fast Charge Discharge Duration Start"
   ::= { batterycontrol 8 }

spbattfchgvstart OBJECT-TYPE
   SYNTAX Integer32
   UNITS "mV"
   MAX-ACCESS read-write
   STATUS current
   DESCRIPTION
      "Fast Charge Bus Voltage Start"
   ::= { batterycontrol 9 }

spbattfchgtimelim OBJECT-TYPE
   SYNTAX Integer32
   UNITS "Minutes"
   MAX-ACCESS read-write
   STATUS current
   DESCRIPTION
      "Fast Charge Time Limit"
   ::= { batterycontrol 10 }

enbbattfchgilowterm OBJECT-TYPE
   SYNTAX Integer32
   UNITS "mA"
   MAX-ACCESS read-write
   STATUS current
   DESCRIPTION
      "Fast Charge Low Current Termination"
   ::= { batterycontrol 11 }

spbattfchgrchg OBJECT-TYPE
   SYNTAX Integer32
   UNITS "0.001 %"
   MAX-ACCESS read-write
   STATUS current
   DESCRIPTION
      "Fast Charge Recharge (% of the discharge)"
   ::= { batterycontrol 12 }

enbrecttcomp OBJECT-TYPE
   SYNTAX Integer32
   UNITS ""
   MAX-ACCESS read-write
   STATUS current
   DESCRIPTION
      "Temperature Compensation Rectifiers Enabled"
   ::= { rectifierscontrol 4 }

enbconvtcomp OBJECT-TYPE
   SYNTAX Integer32
   UNITS ""
   MAX-ACCESS read-write
   STATUS current
   DESCRIPTION
      "Temperature Compensation Converters Enabled"
   ::= { convertercontrol 5 }

spbatttestdur OBJECT-TYPE
   SYNTAX Integer32
   UNITS "Minutes"
   MAX-ACCESS read-write
   STATUS current
   DESCRIPTION
      "Battery Test Duration"
   ::= { batterycontrol 19 }

spbatttestvterm OBJECT-TYPE
   SYNTAX Integer32
   UNITS "mV"
   MAX-ACCESS read-write
   STATUS current
   DESCRIPTION
      "Battery Test Termination Voltage"
   ::= { batterycontrol 20 }

enbbatttestlo OBJECT-TYPE
   SYNTAX Integer32
   UNITS ""
   MAX-ACCESS read-write
   STATUS current
   DESCRIPTION
      "Battery Test Lockout Active"
   ::= { batterycontrol 21 }

spbatttestint OBJECT-TYPE
   SYNTAX Integer32
   UNITS "Days"
   MAX-ACCESS read-write
   STATUS current
   DESCRIPTION
      "Periodic Battery Test Interval"
   ::= { batterycontrol 22 }

enbhybgen1inst OBJECT-TYPE
   SYNTAX Integer32
   UNITS ""
   MAX-ACCESS read-write
   STATUS current
   DESCRIPTION
      "Hybrid Generator 1 Installed"
   ::= { hybgeneralsetup 1 }

enbhybgen2inst OBJECT-TYPE
   SYNTAX Integer32
   UNITS ""
   MAX-ACCESS read-write
   STATUS current
   DESCRIPTION
      "Hybrid Generator 2 Installed"
   ::= { hybgeneralsetup 2 }

enbhybgridinst OBJECT-TYPE
   SYNTAX Integer32
   UNITS ""
   MAX-ACCESS read-write
   STATUS current
   DESCRIPTION
      "Hybrid Grid Installed"
   ::= { hybgeneralsetup 3 }

dishybantistall OBJECT-TYPE
   SYNTAX Integer32
   UNITS ""
   MAX-ACCESS read-write
   STATUS current
   DESCRIPTION
      "Hybrid Disable Antistall"
   ::= { hybgeneralsetup 4 }

dishybmpp OBJECT-TYPE
   SYNTAX Integer32
   UNITS ""
   MAX-ACCESS read-write
   STATUS current
   DESCRIPTION
      "Hybrid Disable MPP"
   ::= { hybgeneralsetup 5 }

enbhybacmmeas OBJECT-TYPE
   SYNTAX Integer32
   UNITS ""
   MAX-ACCESS read-write
   STATUS current
   DESCRIPTION
      "Hybrid Use ACM Measurements"
   ::= { hybgeneralsetup 6 }

sphybacmeff OBJECT-TYPE
   SYNTAX Integer32
   UNITS "0.001 %"
   MAX-ACCESS read-write
   STATUS current
   DESCRIPTION
      "Hybrid Non ACM Measured Efficiency"
   ::= { hybgeneralsetup 7 }

sphybgenratedpwr OBJECT-TYPE
   SYNTAX Integer32
   UNITS "W"
   MAX-ACCESS read-write
   STATUS current
   DESCRIPTION
      "Hybrid Generator Rated Power"
   ::= { hybadvancedsetup 1 }

sphybgenopt OBJECT-TYPE
   SYNTAX Integer32
   UNITS "0.001 %"
   MAX-ACCESS read-write
   STATUS current
   DESCRIPTION
      "Hybrid Optimal Generator Load"
   ::= { hybadvancedsetup 2 }

sphyblowpwrthres OBJECT-TYPE
   SYNTAX Integer32
   UNITS "0.001 %"
   MAX-ACCESS read-write
   STATUS current
   DESCRIPTION
      "Hybrid Low Power Alarm Factor"
   ::= { hybadvancedsetup 3 }

sphybnomacfreq OBJECT-TYPE
   SYNTAX Integer32
   UNITS "Hz"
   MAX-ACCESS read-write
   STATUS current
   DESCRIPTION
      "Hybrid Nominal AC Frequency"
   ::= { hybadvancedsetup 4 }

sphybacfreqthres OBJECT-TYPE
   SYNTAX Integer32
   UNITS "Hz"
   MAX-ACCESS read-write
   STATUS current
   DESCRIPTION
      "Hybrid AC Frequency Threshold"
   ::= { hybadvancedsetup 5 }

sphybgenwarmpwr OBJECT-TYPE
   SYNTAX Integer32
   UNITS "W"
   MAX-ACCESS read-write
   STATUS current
   DESCRIPTION
      "Hybrid Generator Warm Up Power"
   ::= { hybadvancedsetup 6 }

sphybgenwarmdur OBJECT-TYPE
   SYNTAX Integer32
   UNITS "Minutes"
   MAX-ACCESS read-write
   STATUS current
   DESCRIPTION
      "Hybrid Generator Warm Up Duration"
   ::= { hybadvancedsetup 7 }

sphybgencooldur OBJECT-TYPE
   SYNTAX Integer32
   UNITS "Minutes"
   MAX-ACCESS read-write
   STATUS current
   DESCRIPTION
      "Hybrid Generator Cool Down Duration"
   ::= { hybadvancedsetup 8 }

sphybgenshutdowndur OBJECT-TYPE
   SYNTAX Integer32
   UNITS "Minutes"
   MAX-ACCESS read-write
   STATUS current
   DESCRIPTION
      "Hybrid Generator Shutdown Allowance"
   ::= { hybadvancedsetup 9 }

sphybmpprepeat OBJECT-TYPE
   SYNTAX Integer32
   UNITS "Minutes"
   MAX-ACCESS read-write
   STATUS current
   DESCRIPTION
      "Hybrid MPPS Repeat"
   ::= { hybadvancedsetup 10 }

sphybmaxpwr OBJECT-TYPE
   SYNTAX Integer32
   UNITS "W"
   MAX-ACCESS read-write
   STATUS current
   DESCRIPTION
      "Hybrid Maximum Power Limit"
   ::= { hybadvancedsetup 11 }

sphybtermlowbatamps OBJECT-TYPE
   SYNTAX Integer32
   UNITS "mA"
   MAX-ACCESS read-write
   STATUS current
   DESCRIPTION
      "Hybrid Low Batt Amps Termination Level"
   ::= { hybadvancedsetup 12 }

sphybtermfloatbatamps OBJECT-TYPE
   SYNTAX Integer32
   UNITS "mA"
   MAX-ACCESS read-write
   STATUS current
   DESCRIPTION
      "Hybrid Float Batt Amps Termination Level"
   ::= { hybadvancedsetup 13 }

sphybtermbatcap OBJECT-TYPE
   SYNTAX Integer32
   UNITS "0.001 %"
   MAX-ACCESS read-write
   STATUS current
   DESCRIPTION
      "Hybrid Stop when Battery Capacity >"
   ::= { hybadvancedsetup 14 }

sphybstartsigdur OBJECT-TYPE
   SYNTAX Integer32
   UNITS "Seconds"
   MAX-ACCESS read-write
   STATUS current
   DESCRIPTION
      "Hybrid Start Generator Signal Duration"
   ::= { hybadvancedsetup 15 }

sphybbatineff OBJECT-TYPE
   SYNTAX Integer32
   UNITS "0.001 %"
   MAX-ACCESS read-write
   STATUS current
   DESCRIPTION
      "Hybrid Battery Recharge Inefficiency"
   ::= { hybadvancedsetup 16 }

sphybgridgooddur OBJECT-TYPE
   SYNTAX Integer32
   UNITS "Minutes"
   MAX-ACCESS read-write
   STATUS current
   DESCRIPTION
      "Hybrid Grid Good Timeout"
   ::= { hybadvancedsetup 17 }

sphybgridbaddur OBJECT-TYPE
   SYNTAX Integer32
   UNITS "Minutes"
   MAX-ACCESS read-write
   STATUS current
   DESCRIPTION
      "Hybrid Grid Bad Timeout"
   ::= { hybadvancedsetup 18 }

sphybstartretries OBJECT-TYPE
   SYNTAX Integer32
   UNITS ""
   MAX-ACCESS read-write
   STATUS current
   DESCRIPTION
      "Hybrid Start Fail Retries"
   ::= { hybadvancedsetup 19 }

sphyb1hretries OBJECT-TYPE
   SYNTAX Integer32
   UNITS ""
   MAX-ACCESS read-write
   STATUS current
   DESCRIPTION
      "Hybrid  1 Hour Retries"
   ::= { hybadvancedsetup 20 }

enbhyblowcapstart OBJECT-TYPE
   SYNTAX Integer32
   UNITS ""
   MAX-ACCESS read-write
   STATUS current
   DESCRIPTION
      "Hybrid Low Battery Capacity Start Enabled"
   ::= { hyblowbatcapsetup 1 }

sphyblowbatcapstartthres OBJECT-TYPE
   SYNTAX Integer32
   UNITS "0.001 %"
   MAX-ACCESS read-write
   STATUS current
   DESCRIPTION
      "Hybrid Low Battery Capacity Start % Threshold"
   ::= { hyblowbatcapsetup 2 }

sphyblowbatcapstartdur OBJECT-TYPE
   SYNTAX Integer32
   UNITS "Hours"
   MAX-ACCESS read-write
   STATUS current
   DESCRIPTION
      "Hybrid Low Battery Capacity Start Duration"
   ::= { hyblowbatcapsetup 3 }

enbhyblowbatcapstopfull OBJECT-TYPE
   SYNTAX Integer32
   UNITS ""
   MAX-ACCESS read-write
   STATUS current
   DESCRIPTION
      "Hybrid Low Battery Capacity Stop When Bat Full"
   ::= { hyblowbatcapsetup 4 }

enbhyblowbatcapstoplowamps OBJECT-TYPE
   SYNTAX Integer32
   UNITS ""
   MAX-ACCESS read-write
   STATUS current
   DESCRIPTION
      "Hybrid Low Battery Capacity Stop When Low Amps"
   ::= { hyblowbatcapsetup 5 }

enbhyblowbatcapstopfloatamps OBJECT-TYPE
   SYNTAX Integer32
   UNITS ""
   MAX-ACCESS read-write
   STATUS current
   DESCRIPTION
      "Hybrid Low Battery Capacity Stop When Float Amps"
   ::= { hyblowbatcapsetup 6 }

sphybcomchargedur OBJECT-TYPE
   SYNTAX Integer32
   UNITS "Hours"
   MAX-ACCESS read-write
   STATUS current
   DESCRIPTION
      "Hybrid Commissioning Charge Duration"
   ::= { hybcomchargesetup 1 }

enbhybstarta OBJECT-TYPE
   SYNTAX Integer32
   UNITS ""
   MAX-ACCESS read-write
   STATUS current
   DESCRIPTION
      "Hybrid Start Time A Enabled"
   ::= { hybstarttimeasetup 1 }

sphybstartatime OBJECT-TYPE
   SYNTAX DisplayString
   UNITS "HH:MM"
   MAX-ACCESS read-write
   STATUS current
   DESCRIPTION
      "Hybrid Start Time A Start Time"
   ::= { hybstarttimeasetup 2 }

sphybstartadur OBJECT-TYPE
   SYNTAX Integer32
   UNITS "Hours"
   MAX-ACCESS read-write
   STATUS current
   DESCRIPTION
      "Hybrid Start Time A Duration"
   ::= { hybstarttimeasetup 3 }

enbhybstartastopfull OBJECT-TYPE
   SYNTAX Integer32
   UNITS ""
   MAX-ACCESS read-write
   STATUS current
   DESCRIPTION
      "Hybrid Start Time A Stop When Bat Full"
   ::= { hybstarttimeasetup 4 }

enbhybstartastoplowamps OBJECT-TYPE
   SYNTAX Integer32
   UNITS ""
   MAX-ACCESS read-write
   STATUS current
   DESCRIPTION
      "Hybrid Start Time A Stop When Low Amps"
   ::= { hybstarttimeasetup 5 }

enbhybstartastopfloatamps OBJECT-TYPE
   SYNTAX Integer32
   UNITS ""
   MAX-ACCESS read-write
   STATUS current
   DESCRIPTION
      "Hybrid Start Time A Stop When Float Amps"
   ::= { hybstarttimeasetup 6 }

enbhybstartb OBJECT-TYPE
   SYNTAX Integer32
   UNITS ""
   MAX-ACCESS read-write
   STATUS current
   DESCRIPTION
      "Hybrid Start Time B Enabled"
   ::= { hybstarttimebsetup 1 }

sphybstartbtime OBJECT-TYPE
   SYNTAX DisplayString
   UNITS "HH:MM"
   MAX-ACCESS read-write
   STATUS current
   DESCRIPTION
      "Hybrid Start Time B Start Time"
   ::= { hybstarttimebsetup 2 }

sphybstartbdur OBJECT-TYPE
   SYNTAX Integer32
   UNITS "Hours"
   MAX-ACCESS read-write
   STATUS current
   DESCRIPTION
      "Hybrid Start Time B Duration"
   ::= { hybstarttimebsetup 3 }

enbhybstartbstopfull OBJECT-TYPE
   SYNTAX Integer32
   UNITS ""
   MAX-ACCESS read-write
   STATUS current
   DESCRIPTION
      "Hybrid Start Time B Stop When Bat Full"
   ::= { hybstarttimebsetup 4 }

enbhybstartbstoplowamps OBJECT-TYPE
   SYNTAX Integer32
   UNITS ""
   MAX-ACCESS read-write
   STATUS current
   DESCRIPTION
      "Hybrid Start Time B Stop When Low Amps"
   ::= { hybstarttimebsetup 5 }

enbhybstartbstopfloatamps OBJECT-TYPE
   SYNTAX Integer32
   UNITS ""
   MAX-ACCESS read-write
   STATUS current
   DESCRIPTION
      "Hybrid Start Time B Stop When Float Amps"
   ::= { hybstarttimebsetup 6 }

enbhyblowvoltstart OBJECT-TYPE
   SYNTAX Integer32
   UNITS ""
   MAX-ACCESS read-write
   STATUS current
   DESCRIPTION
      "Hybrid Low Voltage Start Enabled"
   ::= { hyblowvoltagestartsetup 1 }

sphyblowvoltstartthres OBJECT-TYPE
   SYNTAX Integer32
   UNITS "mV"
   MAX-ACCESS read-write
   STATUS current
   DESCRIPTION
      "Hybrid Low Voltage Start Threshold"
   ::= { hyblowvoltagestartsetup 2 }

sphyblowvoltstartdur OBJECT-TYPE
   SYNTAX Integer32
   UNITS "Hours"
   MAX-ACCESS read-write
   STATUS current
   DESCRIPTION
      "Hybrid Low Voltage Start Duration"
   ::= { hyblowvoltagestartsetup 3 }

sphyblowvoltstarttempcomp OBJECT-TYPE
   SYNTAX Integer32
   UNITS "mV/176C/Cell"
   MAX-ACCESS read-write
   STATUS current
   DESCRIPTION
      "Hybrid Low Voltage Start Temperature Compensation"
   ::= { hyblowvoltagestartsetup 4 }

enbhyblowvoltstopfull OBJECT-TYPE
   SYNTAX Integer32
   UNITS ""
   MAX-ACCESS read-write
   STATUS current
   DESCRIPTION
      "Hybrid Low Voltage Stop When Bat Full"
   ::= { hyblowvoltagestartsetup 5 }

enbhyblowvoltstoplowamps OBJECT-TYPE
   SYNTAX Integer32
   UNITS ""
   MAX-ACCESS read-write
   STATUS current
   DESCRIPTION
      "Hybrid Low Voltage When Low Amps"
   ::= { hyblowvoltagestartsetup 6 }

enbhyblowvoltstopfloatamps OBJECT-TYPE
   SYNTAX Integer32
   UNITS ""
   MAX-ACCESS read-write
   STATUS current
   DESCRIPTION
      "Hybrid Low Voltage Stop When Float Amps"
   ::= { hyblowvoltagestartsetup 7 }

enbhybextcharge OBJECT-TYPE
   SYNTAX Integer32
   UNITS ""
   MAX-ACCESS read-write
   STATUS current
   DESCRIPTION
      "Hybrid Extended Charge Enabled"
   ::= { hybextendedchargesetup 1 }

sphybextchargestarttime OBJECT-TYPE
   SYNTAX DisplayString
   UNITS "HH:MM"
   MAX-ACCESS read-write
   STATUS current
   DESCRIPTION
      "Hybrid Extended Charge Start Time"
   ::= { hybextendedchargesetup 2 }

sphybextchargecapthres OBJECT-TYPE
   SYNTAX Integer32
   UNITS "0.001 %"
   MAX-ACCESS read-write
   STATUS current
   DESCRIPTION
      "Hybrid Extended Charge Capacity Threshold"
   ::= { hybextendedchargesetup 3 }

sphybextchargeint OBJECT-TYPE
   SYNTAX Integer32
   UNITS "Days"
   MAX-ACCESS read-write
   STATUS current
   DESCRIPTION
      "Hybrid Extended Charge Interval (Days)"
   ::= { hybextendedchargesetup 4 }

sphybextchargedur OBJECT-TYPE
   SYNTAX Integer32
   UNITS "Hours"
   MAX-ACCESS read-write
   STATUS current
   DESCRIPTION
      "Hybrid Extended Charge Duration"
   ::= { hybextendedchargesetup 5 }

enbhybextchargestopfull OBJECT-TYPE
   SYNTAX Integer32
   UNITS ""
   MAX-ACCESS read-write
   STATUS current
   DESCRIPTION
      "Hybrid Extended Charge Stop When Bat Full"
   ::= { hybextendedchargesetup 6 }

enbhybextchargestoplowamps OBJECT-TYPE
   SYNTAX Integer32
   UNITS ""
   MAX-ACCESS read-write
   STATUS current
   DESCRIPTION
      "Hybrid Extended Charge Stop When Low Amps"
   ::= { hybextendedchargesetup 7 }

enbhybextchargestopfloatamps OBJECT-TYPE
   SYNTAX Integer32
   UNITS ""
   MAX-ACCESS read-write
   STATUS current
   DESCRIPTION
      "Hybrid Extended Charge Stop When Float Amps"
   ::= { hybextendedchargesetup 8 }

enbhybgentest OBJECT-TYPE
   SYNTAX Integer32
   UNITS ""
   MAX-ACCESS read-write
   STATUS current
   DESCRIPTION
      "Hybrid Generator Test Enabled"
   ::= { hybgentestsetup 1 }

sphybgenteststarttime OBJECT-TYPE
   SYNTAX DisplayString
   UNITS "HH:MM"
   MAX-ACCESS read-write
   STATUS current
   DESCRIPTION
      "Hybrid Generator Test Start Time"
   ::= { hybgentestsetup 2 }

sphybgentestint OBJECT-TYPE
   SYNTAX Integer32
   UNITS "Days"
   MAX-ACCESS read-write
   STATUS current
   DESCRIPTION
      "Hybrid Generator Test Interval (Days)"
   ::= { hybgentestsetup 3 }

sphybgentestdur OBJECT-TYPE
   SYNTAX Integer32
   UNITS "Hours"
   MAX-ACCESS read-write
   STATUS current
   DESCRIPTION
      "Hybrid Generator Test Duration"
   ::= { hybgentestsetup 4 }

enbhybsolaropt OBJECT-TYPE
   SYNTAX Integer32
   UNITS ""
   MAX-ACCESS read-write
   STATUS current
   DESCRIPTION
      "Hybrid Solar Optimisation Enabled"
   ::= { hybsolaroptgeneralsetup 1 }

sphybsolaroptrisesetpwrthres OBJECT-TYPE
   SYNTAX Integer32
   UNITS "W"
   MAX-ACCESS read-write
   STATUS current
   DESCRIPTION
      "Hybrid Solar Optimisation Sunrise\Sunset Threshold Power"
   ::= { hybsolaroptgeneralsetup 2 }

sphybsolaroptsunriseofs OBJECT-TYPE
   SYNTAX DisplayString
   UNITS ""
   MAX-ACCESS read-write
   STATUS current
   DESCRIPTION
      "Hybrid Solar Optimisation Sunrise Offset"
   ::= { hybsolaroptgeneralsetup 3 }

sphybsolaroptsunsetofs OBJECT-TYPE
   SYNTAX DisplayString
   UNITS ""
   MAX-ACCESS read-write
   STATUS current
   DESCRIPTION
      "Hybrid Solar Optimisation Sunset Offset"
   ::= { hybsolaroptgeneralsetup 4 }

sphybsolaroptsunrisedef OBJECT-TYPE
   SYNTAX DisplayString
   UNITS ""
   MAX-ACCESS read-write
   STATUS current
   DESCRIPTION
      "Hybrid Solar Optimisation Default Sunrise Time"
   ::= { hybsolaroptgeneralsetup 5 }

sphybsolaroptsunsetdef OBJECT-TYPE
   SYNTAX DisplayString
   UNITS ""
   MAX-ACCESS read-write
   STATUS current
   DESCRIPTION
      "Hybrid Solar Optimisation Default Sunset Time"
   ::= { hybsolaroptgeneralsetup 6 }

enbhybexlowvoltstart OBJECT-TYPE
   SYNTAX Integer32
   UNITS ""
   MAX-ACCESS read-write
   STATUS current
   DESCRIPTION
      "Hybrid Extra Low Voltage Start Enabled"
   ::= { hybextralowvoltagestart 1 }

sphybexlowvoltstartthres OBJECT-TYPE
   SYNTAX Integer32
   UNITS "mV"
   MAX-ACCESS read-write
   STATUS current
   DESCRIPTION
      "Hybrid Extra Low Voltage Start Threshold"
   ::= { hybextralowvoltagestart 2 }

sphybexlowvoltstartdur OBJECT-TYPE
   SYNTAX Integer32
   UNITS "Hours"
   MAX-ACCESS read-write
   STATUS current
   DESCRIPTION
      "Hybrid Extra Low Voltage Start Duration"
   ::= { hybextralowvoltagestart 3 }

sphybexlowvoltstarttempcomp OBJECT-TYPE
   SYNTAX Integer32
   UNITS "mV/176C/Cell"
   MAX-ACCESS read-write
   STATUS current
   DESCRIPTION
      "Hybrid Extra Low Voltage Start Temperature Compensation"
   ::= { hybextralowvoltagestart 4 }

enbhybexlowvoltstopfull OBJECT-TYPE
   SYNTAX Integer32
   UNITS ""
   MAX-ACCESS read-write
   STATUS current
   DESCRIPTION
      "Hybrid Extra Low Voltage Stop When Bat Full"
   ::= { hybextralowvoltagestart 5 }

sphybexlowvoltstopfullthres OBJECT-TYPE
   SYNTAX Integer32
   UNITS "0.001 %"
   MAX-ACCESS read-write
   STATUS current
   DESCRIPTION
      "Hybrid Extra Low Voltage Bat Full Capacity"
   ::= { hybextralowvoltagestart 6 }

enbhybexlowvoltstoplowamps OBJECT-TYPE
   SYNTAX Integer32
   UNITS ""
   MAX-ACCESS read-write
   STATUS current
   DESCRIPTION
      "Hybrid Extra Low Voltage Stop When Low Amps"
   ::= { hybextralowvoltagestart 7 }

sphybexlowvoltstoplowampsthres OBJECT-TYPE
   SYNTAX Integer32
   UNITS "mA"
   MAX-ACCESS read-write
   STATUS current
   DESCRIPTION
      "Hybrid Extra Low Voltage Low Amps Threshold"
   ::= { hybextralowvoltagestart 8 }

sphybfueltank1sens0lvl OBJECT-TYPE
   SYNTAX Integer32
   UNITS ""
   MAX-ACCESS read-write
   STATUS current
   DESCRIPTION
      "Hybrid Fuel Tank 1 Sensor at 0% Level"
   ::= { hybfueltank1setup 1 }

sphybfueltank1sens100lvl OBJECT-TYPE
   SYNTAX Integer32
   UNITS ""
   MAX-ACCESS read-write
   STATUS current
   DESCRIPTION
      "Hybrid Fuel Tank 1 Sensor at 100% Level"
   ::= { hybfueltank1setup 2 }

sphybfueltank1vol100 OBJECT-TYPE
   SYNTAX Integer32
   UNITS "0.001 %"
   MAX-ACCESS read-write
   STATUS current
   DESCRIPTION
      "Hybrid Fuel Tank 1 Volume at 100% Level"
   ::= { hybfueltank1setup 3 }

sphybfueltank1vol80 OBJECT-TYPE
   SYNTAX Integer32
   UNITS "0.001 %"
   MAX-ACCESS read-write
   STATUS current
   DESCRIPTION
      "Hybrid Fuel Tank 1 Volume at 80% Level"
   ::= { hybfueltank1setup 4 }

sphybfueltank1vol60 OBJECT-TYPE
   SYNTAX Integer32
   UNITS "0.001 %"
   MAX-ACCESS read-write
   STATUS current
   DESCRIPTION
      "Hybrid Fuel Tank 1 Volume at 60% Level"
   ::= { hybfueltank1setup 5 }

sphybfueltank1vol40 OBJECT-TYPE
   SYNTAX Integer32
   UNITS "0.001 %"
   MAX-ACCESS read-write
   STATUS current
   DESCRIPTION
      "Hybrid Fuel Tank 1 Volume at 40% Level"
   ::= { hybfueltank1setup 6 }

sphybfueltank1vol20 OBJECT-TYPE
   SYNTAX Integer32
   UNITS "0.001 %"
   MAX-ACCESS read-write
   STATUS current
   DESCRIPTION
      "Hybrid Fuel Tank 1 Volume at 20% Level"
   ::= { hybfueltank1setup 7 }

sphybfueltank1vol0 OBJECT-TYPE
   SYNTAX Integer32
   UNITS "0.001 %"
   MAX-ACCESS read-write
   STATUS current
   DESCRIPTION
      "Hybrid Fuel Tank 1 Volume at 0% Level"
   ::= { hybfueltank1setup 8 }

sphybfueltank1volcap OBJECT-TYPE
   SYNTAX Integer32
   UNITS "Litres"
   MAX-ACCESS read-write
   STATUS current
   DESCRIPTION
      "Hybrid Fuel Tank 1 Volume (l)"
   ::= { hybfueltank1setup 9 }

sphybfueltank1refill OBJECT-TYPE
   SYNTAX Integer32
   UNITS "0.001 %"
   MAX-ACCESS read-write
   STATUS current
   DESCRIPTION
      "Hybrid Fuel Tank 1 Refill Threshold"
   ::= { hybfueltank1setup 10 }

sphybfueltank1low OBJECT-TYPE
   SYNTAX Integer32
   UNITS "0.001 %"
   MAX-ACCESS read-write
   STATUS current
   DESCRIPTION
      "Hybrid Fuel Tank 1 Low Threshold"
   ::= { hybfueltank1setup 11 }

valhybfueltank1sensor OBJECT-TYPE
   SYNTAX Integer32
   UNITS ""
   MAX-ACCESS read-only
   STATUS current
   DESCRIPTION
      "Hybrid Fuel Tank 1 Raw Sensor Reading"
   ::= { hybfueltank1setup 12 }

valhybfueltank1volpct OBJECT-TYPE
   SYNTAX Integer32
   UNITS "0.001 %"
   MAX-ACCESS read-only
   STATUS current
   DESCRIPTION
      "Hybrid Fuel Tank 1 Volume (%)"
   ::= { hybfueltank1setup 13 }

valhybfueltank1voll OBJECT-TYPE
   SYNTAX Integer32
   UNITS "Litres"
   MAX-ACCESS read-only
   STATUS current
   DESCRIPTION
      "Hybrid Fuel Tank 1 Volume (l)"
   ::= { hybfueltank1setup 14 }

valhybfueltank1lvlpct OBJECT-TYPE
   SYNTAX Integer32
   UNITS "0.001 %"
   MAX-ACCESS read-only
   STATUS current
   DESCRIPTION
      "Hybrid Fuel Tank 1 Level (%)"
   ::= { hybfueltank1setup 15 }

sphybfueltank2sens0lvl OBJECT-TYPE
   SYNTAX Integer32
   UNITS ""
   MAX-ACCESS read-write
   STATUS current
   DESCRIPTION
      "Hybrid Fuel Tank 2 Sensor at 0% Level"
   ::= { hybfueltank2setup 1 }

sphybfueltank2sens100lvl OBJECT-TYPE
   SYNTAX Integer32
   UNITS ""
   MAX-ACCESS read-write
   STATUS current
   DESCRIPTION
      "Hybrid Fuel Tank 2 Sensor at 100% Level"
   ::= { hybfueltank2setup 2 }

sphybfueltank2vol100 OBJECT-TYPE
   SYNTAX Integer32
   UNITS "0.001 %"
   MAX-ACCESS read-write
   STATUS current
   DESCRIPTION
      "Hybrid Fuel Tank 2 Volume at 100% Level"
   ::= { hybfueltank2setup 3 }

sphybfueltank2vol80 OBJECT-TYPE
   SYNTAX Integer32
   UNITS "0.001 %"
   MAX-ACCESS read-write
   STATUS current
   DESCRIPTION
      "Hybrid Fuel Tank 2 Volume at 80% Level"
   ::= { hybfueltank2setup 4 }

sphybfueltank2vol60 OBJECT-TYPE
   SYNTAX Integer32
   UNITS "0.001 %"
   MAX-ACCESS read-write
   STATUS current
   DESCRIPTION
      "Hybrid Fuel Tank 2 Volume at 60% Level"
   ::= { hybfueltank2setup 5 }

sphybfueltank2vol40 OBJECT-TYPE
   SYNTAX Integer32
   UNITS "0.001 %"
   MAX-ACCESS read-write
   STATUS current
   DESCRIPTION
      "Hybrid Fuel Tank 2 Volume at 40% Level"
   ::= { hybfueltank2setup 6 }

sphybfueltank2vol20 OBJECT-TYPE
   SYNTAX Integer32
   UNITS "0.001 %"
   MAX-ACCESS read-write
   STATUS current
   DESCRIPTION
      "Hybrid Fuel Tank 2 Volume at 20% Level"
   ::= { hybfueltank2setup 7 }

sphybfueltank2vol0 OBJECT-TYPE
   SYNTAX Integer32
   UNITS "0.001 %"
   MAX-ACCESS read-write
   STATUS current
   DESCRIPTION
      "Hybrid Fuel Tank 2 Volume at 0% Level"
   ::= { hybfueltank2setup 8 }

sphybfueltank2volcap OBJECT-TYPE
   SYNTAX Integer32
   UNITS "Litres"
   MAX-ACCESS read-write
   STATUS current
   DESCRIPTION
      "Hybrid Fuel Tank 2 Volume (l)"
   ::= { hybfueltank2setup 9 }

sphybfueltank2refill OBJECT-TYPE
   SYNTAX Integer32
   UNITS "0.001 %"
   MAX-ACCESS read-write
   STATUS current
   DESCRIPTION
      "Hybrid Fuel Tank 2 Refill Threshold"
   ::= { hybfueltank2setup 10 }

sphybfueltank2low OBJECT-TYPE
   SYNTAX Integer32
   UNITS "0.001 %"
   MAX-ACCESS read-write
   STATUS current
   DESCRIPTION
      "Hybrid Fuel Tank 2 Low Threshold"
   ::= { hybfueltank2setup 11 }

valhybfueltank2sensor OBJECT-TYPE
   SYNTAX Integer32
   UNITS ""
   MAX-ACCESS read-only
   STATUS current
   DESCRIPTION
      "Hybrid Fuel Tank 2 Raw Sensor Reading"
   ::= { hybfueltank2setup 12 }

valhybfueltank2volpct OBJECT-TYPE
   SYNTAX Integer32
   UNITS "0.001 %"
   MAX-ACCESS read-only
   STATUS current
   DESCRIPTION
      "Hybrid Fuel Tank 2 Volume (%)"
   ::= { hybfueltank2setup 13 }

valhybfueltank2voll OBJECT-TYPE
   SYNTAX Integer32
   UNITS "Litres"
   MAX-ACCESS read-only
   STATUS current
   DESCRIPTION
      "Hybrid Fuel Tank 2 Volume (l)"
   ::= { hybfueltank2setup 14 }

valhybfueltank2lvlpct OBJECT-TYPE
   SYNTAX Integer32
   UNITS "0.001 %"
   MAX-ACCESS read-only
   STATUS current
   DESCRIPTION
      "Hybrid Fuel Tank 2 Level (%)"
   ::= { hybfueltank2setup 15 }

enmhybfueltankcfg OBJECT-TYPE
   SYNTAX Integer32
   UNITS ""
   MAX-ACCESS read-write
   STATUS current
   DESCRIPTION
      "Hybrid Fuel Tank Configuration"
   ::= { hybtankconfig 1 }

phbalen OBJECT-TYPE
   SYNTAX Integer32
   UNITS ""
   MAX-ACCESS read-write
   STATUS current
   DESCRIPTION
      "Phase Balancing Enabled"
   ::= { phasebalancing 1 }

phbalacreccur OBJECT-TYPE
   SYNTAX Integer32
   UNITS ""
   MAX-ACCESS read-write
   STATUS current
   DESCRIPTION
      "Phase Balancing use AC Monitor 2 for AC Rectifier Currents"
   ::= { phasebalancing 2 }

phbalacfullscale OBJECT-TYPE
   SYNTAX Integer32
   UNITS "mA"
   MAX-ACCESS read-write
   STATUS current
   DESCRIPTION
      "Phase Balancing AC Current full Scale"
   ::= { phasebalancing 3 }

phbalacbackoffcurlim OBJECT-TYPE
   SYNTAX Integer32
   UNITS "mA"
   MAX-ACCESS read-write
   STATUS current
   DESCRIPTION
      "Phase Balancing AC Backoff Current Limit"
   ::= { phasebalancing 4 }

phbalacbackoffredpower OBJECT-TYPE
   SYNTAX Integer32
   UNITS "W"
   MAX-ACCESS read-write
   STATUS current
   DESCRIPTION
      "Phase Balancing AC Backoff Reduction Power"
   ::= { phasebalancing 5 }

almwdusr1_16 OBJECT-TYPE
   SYNTAX Integer32
   UNITS ""
   MAX-ACCESS read-only
   STATUS current
   DESCRIPTION
      "User Alarms 1 - 16"
   ::= { alarms 1 }

almwdusr16_32 OBJECT-TYPE
   SYNTAX Integer32
   UNITS ""
   MAX-ACCESS read-only
   STATUS current
   DESCRIPTION
      "User Alarms 16 - 32"
   ::= { alarms 2 }

almwdrect OBJECT-TYPE
   SYNTAX Integer32
   UNITS ""
   MAX-ACCESS read-only
   STATUS current
   DESCRIPTION
      "Rectifier Alarms"
   ::= { alarms 3 }

almwdconv OBJECT-TYPE
   SYNTAX Integer32
   UNITS ""
   MAX-ACCESS read-only
   STATUS current
   DESCRIPTION
      "Converter Alarms"
   ::= { alarms 4 }

almwdinv OBJECT-TYPE
   SYNTAX Integer32
   UNITS ""
   MAX-ACCESS read-only
   STATUS current
   DESCRIPTION
      "Inverter Alarms"
   ::= { alarms 5 }

almwddev OBJECT-TYPE
   SYNTAX Integer32
   UNITS ""
   MAX-ACCESS read-only
   STATUS current
   DESCRIPTION
      "Device Alarms"
   ::= { alarms 6 }

almwdvolt OBJECT-TYPE
   SYNTAX Integer32
   UNITS ""
   MAX-ACCESS read-only
   STATUS current
   DESCRIPTION
      "Voltage Alarms"
   ::= { alarms 7 }

almwditemp OBJECT-TYPE
   SYNTAX Integer32
   UNITS ""
   MAX-ACCESS read-only
   STATUS current
   DESCRIPTION
      "Current and Temperature Alarms"
   ::= { alarms 8 }

almwdmon OBJECT-TYPE
   SYNTAX Integer32
   UNITS ""
   MAX-ACCESS read-only
   STATUS current
   DESCRIPTION
      "Monitor Alarms"
   ::= { alarms 9 }

almwdac OBJECT-TYPE
   SYNTAX Integer32
   UNITS ""
   MAX-ACCESS read-only
   STATUS current
   DESCRIPTION
      "AC Alarms"
   ::= { alarms 10 }

almwdsbm OBJECT-TYPE
   SYNTAX Integer32
   UNITS ""
   MAX-ACCESS read-only
   STATUS current
   DESCRIPTION
      "Static Bypass Alarms"
   ::= { alarms 11 }

almwdren OBJECT-TYPE
   SYNTAX Integer32
   UNITS ""
   MAX-ACCESS read-only
   STATUS current
   DESCRIPTION
      "Renewables Alarms"
   ::= { alarms 12 }

almwdsconv1 OBJECT-TYPE
   SYNTAX Integer32
   UNITS ""
   MAX-ACCESS read-only
   STATUS current
   DESCRIPTION
      "Solar Device Alarms 1"
   ::= { alarms 13 }

almwdsconv2 OBJECT-TYPE
   SYNTAX Integer32
   UNITS ""
   MAX-ACCESS read-only
   STATUS current
   DESCRIPTION
      "Solar Device Alarms 2"
   ::= { alarms 14 }

almwdwconv1 OBJECT-TYPE
   SYNTAX Integer32
   UNITS ""
   MAX-ACCESS read-only
   STATUS current
   DESCRIPTION
      "Wind Device Alarms 1"
   ::= { alarms 15 }

almwdwconv2 OBJECT-TYPE
   SYNTAX Integer32
   UNITS ""
   MAX-ACCESS read-only
   STATUS current
   DESCRIPTION
      "Wind Device Alarms 2"
   ::= { alarms 16 }

almwdhyb1 OBJECT-TYPE
   SYNTAX Integer32
   UNITS ""
   MAX-ACCESS read-only
   STATUS current
   DESCRIPTION
      "Hybrid Alarms 1"
   ::= { alarms 17 }

almwdhyb2 OBJECT-TYPE
   SYNTAX Integer32
   UNITS ""
   MAX-ACCESS read-only
   STATUS current
   DESCRIPTION
      "Hybrid Alarms 2"
   ::= { alarms 18 }

almwdhyb3 OBJECT-TYPE
   SYNTAX Integer32
   UNITS ""
   MAX-ACCESS read-only
   STATUS current
   DESCRIPTION
      "Hybrid Alarms 3"
   ::= { alarms 19 }

almwdhyb4 OBJECT-TYPE
   SYNTAX Integer32
   UNITS ""
   MAX-ACCESS read-only
   STATUS current
   DESCRIPTION
      "Hybrid Alarms 4"
   ::= { alarms 20 }

almwdhyb5 OBJECT-TYPE
   SYNTAX Integer32
   UNITS ""
   MAX-ACCESS read-only
   STATUS current
   DESCRIPTION
      "Hybrid Alarms 5"
   ::= { alarms 21 }

almwdhyb6 OBJECT-TYPE
   SYNTAX Integer32
   UNITS ""
   MAX-ACCESS read-only
   STATUS current
   DESCRIPTION
      "Hybrid Alarms 6"
   ::= { alarms 22 }

almwdhybop OBJECT-TYPE
   SYNTAX Integer32
   UNITS ""
   MAX-ACCESS read-only
   STATUS current
   DESCRIPTION
      "Hybrid Outputs"
   ::= { alarms 23 }

almwdacm1 OBJECT-TYPE
   SYNTAX Integer32
   UNITS ""
   MAX-ACCESS read-only
   STATUS current
   DESCRIPTION
      "Mains Monitor 1 Alarms"
   ::= { alarms 24 }

almwdacm2 OBJECT-TYPE
   SYNTAX Integer32
   UNITS ""
   MAX-ACCESS read-only
   STATUS current
   DESCRIPTION
      "Mains Monitor 2 Alarms"
   ::= { alarms 25 }

almwdphbal OBJECT-TYPE
   SYNTAX Integer32
   UNITS ""
   MAX-ACCESS read-only
   STATUS current
   DESCRIPTION
      "Phase Balancing Alarms"
   ::= { alarms 26 }

batt1_amps OBJECT-TYPE
   SYNTAX Integer32
   UNITS "mA"
   MAX-ACCESS read-only
   STATUS current
   DESCRIPTION
      "Battery String 1 Current"
   ::= { string1 1 }

batt1_temp OBJECT-TYPE
   SYNTAX Integer32
   UNITS "0.1 DegC"
   MAX-ACCESS read-only
   STATUS current
   DESCRIPTION
      "Battery String 1 Temperature"
   ::= { string1 2 }

batt1_bloc1v OBJECT-TYPE
   SYNTAX Integer32
   UNITS "mV"
   MAX-ACCESS read-only
   STATUS current
   DESCRIPTION
      "Battery String 1 Bloc 1 Voltage"
   ::= { string1 3 }

batt1_bloc2v OBJECT-TYPE
   SYNTAX Integer32
   UNITS "mV"
   MAX-ACCESS read-only
   STATUS current
   DESCRIPTION
      "Battery String 1 Bloc 2 Voltage"
   ::= { string1 4 }

batt1_bloc3v OBJECT-TYPE
   SYNTAX Integer32
   UNITS "mV"
   MAX-ACCESS read-only
   STATUS current
   DESCRIPTION
      "Battery String 1 Bloc 3 Voltage"
   ::= { string1 5 }

batt1_bloc4v OBJECT-TYPE
   SYNTAX Integer32
   UNITS "mV"
   MAX-ACCESS read-only
   STATUS current
   DESCRIPTION
      "Battery String 1 Bloc 4 Voltage"
   ::= { string1 6 }

batt1_bloc5v OBJECT-TYPE
   SYNTAX Integer32
   UNITS "mV"
   MAX-ACCESS read-only
   STATUS current
   DESCRIPTION
      "Battery String 1 Bloc 5 Voltage"
   ::= { string1 7 }

batt1_bloc6v OBJECT-TYPE
   SYNTAX Integer32
   UNITS "mV"
   MAX-ACCESS read-only
   STATUS current
   DESCRIPTION
      "Battery String 1 Bloc 6 Voltage"
   ::= { string1 8 }

batt1_bloc7v OBJECT-TYPE
   SYNTAX Integer32
   UNITS "mV"
   MAX-ACCESS read-only
   STATUS current
   DESCRIPTION
      "Battery String 1 Bloc 7 Voltage"
   ::= { string1 9 }

batt1_bloc8v OBJECT-TYPE
   SYNTAX Integer32
   UNITS "mV"
   MAX-ACCESS read-only
   STATUS current
   DESCRIPTION
      "Battery String 1 Bloc 8 Voltage"
   ::= { string1 10 }

batt1_bloc9v OBJECT-TYPE
   SYNTAX Integer32
   UNITS "mV"
   MAX-ACCESS read-only
   STATUS current
   DESCRIPTION
      "Battery String 1 Bloc 9 Voltage"
   ::= { string1 11 }

batt1_bloc10v OBJECT-TYPE
   SYNTAX Integer32
   UNITS "mV"
   MAX-ACCESS read-only
   STATUS current
   DESCRIPTION
      "Battery String 1 Bloc 10 Voltage"
   ::= { string1 12 }

batt1_bloc11v OBJECT-TYPE
   SYNTAX Integer32
   UNITS "mV"
   MAX-ACCESS read-only
   STATUS current
   DESCRIPTION
      "Battery String 1 Bloc 11 Voltage"
   ::= { string1 13 }

batt1_bloc12v OBJECT-TYPE
   SYNTAX Integer32
   UNITS "mV"
   MAX-ACCESS read-only
   STATUS current
   DESCRIPTION
      "Battery String 1 Bloc 12 Voltage"
   ::= { string1 14 }

batt1_bloc13v OBJECT-TYPE
   SYNTAX Integer32
   UNITS "mV"
   MAX-ACCESS read-only
   STATUS current
   DESCRIPTION
      "Battery String 1 Bloc 13 Voltage"
   ::= { string1 15 }

batt1_bloc14v OBJECT-TYPE
   SYNTAX Integer32
   UNITS "mV"
   MAX-ACCESS read-only
   STATUS current
   DESCRIPTION
      "Battery String 1 Bloc 14 Voltage"
   ::= { string1 16 }

batt1_bloc15v OBJECT-TYPE
   SYNTAX Integer32
   UNITS "mV"
   MAX-ACCESS read-only
   STATUS current
   DESCRIPTION
      "Battery String 1 Bloc 15 Voltage"
   ::= { string1 17 }

batt1_bloc16v OBJECT-TYPE
   SYNTAX Integer32
   UNITS "mV"
   MAX-ACCESS read-only
   STATUS current
   DESCRIPTION
      "Battery String 1 Bloc 16 Voltage"
   ::= { string1 18 }

batt1_bloc17v OBJECT-TYPE
   SYNTAX Integer32
   UNITS "mV"
   MAX-ACCESS read-only
   STATUS current
   DESCRIPTION
      "Battery String 1 Bloc 17 Voltage"
   ::= { string1 19 }

batt1_bloc18v OBJECT-TYPE
   SYNTAX Integer32
   UNITS "mV"
   MAX-ACCESS read-only
   STATUS current
   DESCRIPTION
      "Battery String 1 Bloc 18 Voltage"
   ::= { string1 20 }

batt1_bloc19v OBJECT-TYPE
   SYNTAX Integer32
   UNITS "mV"
   MAX-ACCESS read-only
   STATUS current
   DESCRIPTION
      "Battery String 1 Bloc 19 Voltage"
   ::= { string1 21 }

batt1_bloc20v OBJECT-TYPE
   SYNTAX Integer32
   UNITS "mV"
   MAX-ACCESS read-only
   STATUS current
   DESCRIPTION
      "Battery String 1 Bloc 20 Voltage"
   ::= { string1 22 }

batt1_bloc21v OBJECT-TYPE
   SYNTAX Integer32
   UNITS "mV"
   MAX-ACCESS read-only
   STATUS current
   DESCRIPTION
      "Battery String 1 Bloc 21 Voltage"
   ::= { string1 23 }

batt1_bloc22v OBJECT-TYPE
   SYNTAX Integer32
   UNITS "mV"
   MAX-ACCESS read-only
   STATUS current
   DESCRIPTION
      "Battery String 1 Bloc 22 Voltage"
   ::= { string1 24 }

batt1_bloc23v OBJECT-TYPE
   SYNTAX Integer32
   UNITS "mV"
   MAX-ACCESS read-only
   STATUS current
   DESCRIPTION
      "Battery String 1 Bloc 23 Voltage"
   ::= { string1 25 }

batt1_bloc24v OBJECT-TYPE
   SYNTAX Integer32
   UNITS "mV"
   MAX-ACCESS read-only
   STATUS current
   DESCRIPTION
      "Battery String 1 Bloc 24 Voltage"
   ::= { string1 26 }

batt2_amps OBJECT-TYPE
   SYNTAX Integer32
   UNITS "mA"
   MAX-ACCESS read-only
   STATUS current
   DESCRIPTION
      "Battery String 2 Current"
   ::= { string2 1 }

batt2_temp OBJECT-TYPE
   SYNTAX Integer32
   UNITS "0.1 DegC"
   MAX-ACCESS read-only
   STATUS current
   DESCRIPTION
      "Battery String 2 Temperature"
   ::= { string2 2 }

batt2_bloc1v OBJECT-TYPE
   SYNTAX Integer32
   UNITS "mV"
   MAX-ACCESS read-only
   STATUS current
   DESCRIPTION
      "Battery String 2 Bloc 1 Voltage"
   ::= { string2 3 }

batt2_bloc2v OBJECT-TYPE
   SYNTAX Integer32
   UNITS "mV"
   MAX-ACCESS read-only
   STATUS current
   DESCRIPTION
      "Battery String 2 Bloc 2 Voltage"
   ::= { string2 4 }

batt2_bloc3v OBJECT-TYPE
   SYNTAX Integer32
   UNITS "mV"
   MAX-ACCESS read-only
   STATUS current
   DESCRIPTION
      "Battery String 2 Bloc 3 Voltage"
   ::= { string2 5 }

batt2_bloc4v OBJECT-TYPE
   SYNTAX Integer32
   UNITS "mV"
   MAX-ACCESS read-only
   STATUS current
   DESCRIPTION
      "Battery String 2 Bloc 4 Voltage"
   ::= { string2 6 }

batt2_bloc5v OBJECT-TYPE
   SYNTAX Integer32
   UNITS "mV"
   MAX-ACCESS read-only
   STATUS current
   DESCRIPTION
      "Battery String 2 Bloc 5 Voltage"
   ::= { string2 7 }

batt2_bloc6v OBJECT-TYPE
   SYNTAX Integer32
   UNITS "mV"
   MAX-ACCESS read-only
   STATUS current
   DESCRIPTION
      "Battery String 2 Bloc 6 Voltage"
   ::= { string2 8 }

batt2_bloc7v OBJECT-TYPE
   SYNTAX Integer32
   UNITS "mV"
   MAX-ACCESS read-only
   STATUS current
   DESCRIPTION
      "Battery String 2 Bloc 7 Voltage"
   ::= { string2 9 }

batt2_bloc8v OBJECT-TYPE
   SYNTAX Integer32
   UNITS "mV"
   MAX-ACCESS read-only
   STATUS current
   DESCRIPTION
      "Battery String 2 Bloc 8 Voltage"
   ::= { string2 10 }

batt2_bloc9v OBJECT-TYPE
   SYNTAX Integer32
   UNITS "mV"
   MAX-ACCESS read-only
   STATUS current
   DESCRIPTION
      "Battery String 2 Bloc 9 Voltage"
   ::= { string2 11 }

batt2_bloc10v OBJECT-TYPE
   SYNTAX Integer32
   UNITS "mV"
   MAX-ACCESS read-only
   STATUS current
   DESCRIPTION
      "Battery String 2 Bloc 10 Voltage"
   ::= { string2 12 }

batt2_bloc11v OBJECT-TYPE
   SYNTAX Integer32
   UNITS "mV"
   MAX-ACCESS read-only
   STATUS current
   DESCRIPTION
      "Battery String 2 Bloc 11 Voltage"
   ::= { string2 13 }

batt2_bloc12v OBJECT-TYPE
   SYNTAX Integer32
   UNITS "mV"
   MAX-ACCESS read-only
   STATUS current
   DESCRIPTION
      "Battery String 2 Bloc 12 Voltage"
   ::= { string2 14 }

batt2_bloc13v OBJECT-TYPE
   SYNTAX Integer32
   UNITS "mV"
   MAX-ACCESS read-only
   STATUS current
   DESCRIPTION
      "Battery String 2 Bloc 13 Voltage"
   ::= { string2 15 }

batt2_bloc14v OBJECT-TYPE
   SYNTAX Integer32
   UNITS "mV"
   MAX-ACCESS read-only
   STATUS current
   DESCRIPTION
      "Battery String 2 Bloc 14 Voltage"
   ::= { string2 16 }

batt2_bloc15v OBJECT-TYPE
   SYNTAX Integer32
   UNITS "mV"
   MAX-ACCESS read-only
   STATUS current
   DESCRIPTION
      "Battery String 2 Bloc 15 Voltage"
   ::= { string2 17 }

batt2_bloc16v OBJECT-TYPE
   SYNTAX Integer32
   UNITS "mV"
   MAX-ACCESS read-only
   STATUS current
   DESCRIPTION
      "Battery String 2 Bloc 16 Voltage"
   ::= { string2 18 }

batt2_bloc17v OBJECT-TYPE
   SYNTAX Integer32
   UNITS "mV"
   MAX-ACCESS read-only
   STATUS current
   DESCRIPTION
      "Battery String 2 Bloc 17 Voltage"
   ::= { string2 19 }

batt2_bloc18v OBJECT-TYPE
   SYNTAX Integer32
   UNITS "mV"
   MAX-ACCESS read-only
   STATUS current
   DESCRIPTION
      "Battery String 2 Bloc 18 Voltage"
   ::= { string2 20 }

batt2_bloc19v OBJECT-TYPE
   SYNTAX Integer32
   UNITS "mV"
   MAX-ACCESS read-only
   STATUS current
   DESCRIPTION
      "Battery String 2 Bloc 19 Voltage"
   ::= { string2 21 }

batt2_bloc20v OBJECT-TYPE
   SYNTAX Integer32
   UNITS "mV"
   MAX-ACCESS read-only
   STATUS current
   DESCRIPTION
      "Battery String 2 Bloc 20 Voltage"
   ::= { string2 22 }

batt2_bloc21v OBJECT-TYPE
   SYNTAX Integer32
   UNITS "mV"
   MAX-ACCESS read-only
   STATUS current
   DESCRIPTION
      "Battery String 2 Bloc 21 Voltage"
   ::= { string2 23 }

batt2_bloc22v OBJECT-TYPE
   SYNTAX Integer32
   UNITS "mV"
   MAX-ACCESS read-only
   STATUS current
   DESCRIPTION
      "Battery String 2 Bloc 22 Voltage"
   ::= { string2 24 }

batt2_bloc23v OBJECT-TYPE
   SYNTAX Integer32
   UNITS "mV"
   MAX-ACCESS read-only
   STATUS current
   DESCRIPTION
      "Battery String 2 Bloc 23 Voltage"
   ::= { string2 25 }

batt2_bloc24v OBJECT-TYPE
   SYNTAX Integer32
   UNITS "mV"
   MAX-ACCESS read-only
   STATUS current
   DESCRIPTION
      "Battery String 2 Bloc 24 Voltage"
   ::= { string2 26 }

batt3_amps OBJECT-TYPE
   SYNTAX Integer32
   UNITS "mA"
   MAX-ACCESS read-only
   STATUS current
   DESCRIPTION
      "Battery String 3 Current"
   ::= { string3 1 }

batt3_temp OBJECT-TYPE
   SYNTAX Integer32
   UNITS "0.1 DegC"
   MAX-ACCESS read-only
   STATUS current
   DESCRIPTION
      "Battery String 3 Temperature"
   ::= { string3 2 }

batt3_bloc1v OBJECT-TYPE
   SYNTAX Integer32
   UNITS "mV"
   MAX-ACCESS read-only
   STATUS current
   DESCRIPTION
      "Battery String 3 Bloc 1 Voltage"
   ::= { string3 3 }

batt3_bloc2v OBJECT-TYPE
   SYNTAX Integer32
   UNITS "mV"
   MAX-ACCESS read-only
   STATUS current
   DESCRIPTION
      "Battery String 3 Bloc 2 Voltage"
   ::= { string3 4 }

batt3_bloc3v OBJECT-TYPE
   SYNTAX Integer32
   UNITS "mV"
   MAX-ACCESS read-only
   STATUS current
   DESCRIPTION
      "Battery String 3 Bloc 3 Voltage"
   ::= { string3 5 }

batt3_bloc4v OBJECT-TYPE
   SYNTAX Integer32
   UNITS "mV"
   MAX-ACCESS read-only
   STATUS current
   DESCRIPTION
      "Battery String 3 Bloc 4 Voltage"
   ::= { string3 6 }

batt4_amps OBJECT-TYPE
   SYNTAX Integer32
   UNITS "mA"
   MAX-ACCESS read-only
   STATUS current
   DESCRIPTION
      "Battery String 4 Current"
   ::= { string4 1 }

batt4_temp OBJECT-TYPE
   SYNTAX Integer32
   UNITS "0.1 DegC"
   MAX-ACCESS read-only
   STATUS current
   DESCRIPTION
      "Battery String 4 Temperature"
   ::= { string4 2 }

batt4_bloc1v OBJECT-TYPE
   SYNTAX Integer32
   UNITS "mV"
   MAX-ACCESS read-only
   STATUS current
   DESCRIPTION
      "Battery String 4 Bloc 1 Voltage"
   ::= { string4 3 }

batt4_bloc2v OBJECT-TYPE
   SYNTAX Integer32
   UNITS "mV"
   MAX-ACCESS read-only
   STATUS current
   DESCRIPTION
      "Battery String 4 Bloc 2 Voltage"
   ::= { string4 4 }

batt4_bloc3v OBJECT-TYPE
   SYNTAX Integer32
   UNITS "mV"
   MAX-ACCESS read-only
   STATUS current
   DESCRIPTION
      "Battery String 4 Bloc 3 Voltage"
   ::= { string4 5 }

batt4_bloc4v OBJECT-TYPE
   SYNTAX Integer32
   UNITS "mV"
   MAX-ACCESS read-only
   STATUS current
   DESCRIPTION
      "Battery String 4 Bloc 4 Voltage"
   ::= { string4 6 }

batt5_amps OBJECT-TYPE
   SYNTAX Integer32
   UNITS "mA"
   MAX-ACCESS read-only
   STATUS current
   DESCRIPTION
      "Battery String 5 Current"
   ::= { string5 1 }

batt5_temp OBJECT-TYPE
   SYNTAX Integer32
   UNITS "0.1 DegC"
   MAX-ACCESS read-only
   STATUS current
   DESCRIPTION
      "Battery String 5 Temperature"
   ::= { string5 2 }

batt5_bloc1v OBJECT-TYPE
   SYNTAX Integer32
   UNITS "mV"
   MAX-ACCESS read-only
   STATUS current
   DESCRIPTION
      "Battery String 5 Bloc 1 Voltage"
   ::= { string5 3 }

batt5_bloc2v OBJECT-TYPE
   SYNTAX Integer32
   UNITS "mV"
   MAX-ACCESS read-only
   STATUS current
   DESCRIPTION
      "Battery String 5 Bloc 2 Voltage"
   ::= { string5 4 }

batt5_bloc3v OBJECT-TYPE
   SYNTAX Integer32
   UNITS "mV"
   MAX-ACCESS read-only
   STATUS current
   DESCRIPTION
      "Battery String 5 Bloc 3 Voltage"
   ::= { string5 5 }

batt5_bloc4v OBJECT-TYPE
   SYNTAX Integer32
   UNITS "mV"
   MAX-ACCESS read-only
   STATUS current
   DESCRIPTION
      "Battery String 5 Bloc 4 Voltage"
   ::= { string5 6 }

batt6_amps OBJECT-TYPE
   SYNTAX Integer32
   UNITS "mA"
   MAX-ACCESS read-only
   STATUS current
   DESCRIPTION
      "Battery String 6 Current"
   ::= { string6 1 }

batt6_temp OBJECT-TYPE
   SYNTAX Integer32
   UNITS "0.1 DegC"
   MAX-ACCESS read-only
   STATUS current
   DESCRIPTION
      "Battery String 6 Temperature"
   ::= { string6 2 }

batt6_bloc1v OBJECT-TYPE
   SYNTAX Integer32
   UNITS "mV"
   MAX-ACCESS read-only
   STATUS current
   DESCRIPTION
      "Battery String 6 Bloc 1 Voltage"
   ::= { string6 3 }

batt6_bloc2v OBJECT-TYPE
   SYNTAX Integer32
   UNITS "mV"
   MAX-ACCESS read-only
   STATUS current
   DESCRIPTION
      "Battery String 6 Bloc 2 Voltage"
   ::= { string6 4 }

batt6_bloc3v OBJECT-TYPE
   SYNTAX Integer32
   UNITS "mV"
   MAX-ACCESS read-only
   STATUS current
   DESCRIPTION
      "Battery String 6 Bloc 3 Voltage"
   ::= { string6 5 }

batt6_bloc4v OBJECT-TYPE
   SYNTAX Integer32
   UNITS "mV"
   MAX-ACCESS read-only
   STATUS current
   DESCRIPTION
      "Battery String 6 Bloc 4 Voltage"
   ::= { string6 6 }

batt7_amps OBJECT-TYPE
   SYNTAX Integer32
   UNITS "mA"
   MAX-ACCESS read-only
   STATUS current
   DESCRIPTION
      "Battery String 7 Current"
   ::= { string7 1 }

batt7_temp OBJECT-TYPE
   SYNTAX Integer32
   UNITS "0.1 DegC"
   MAX-ACCESS read-only
   STATUS current
   DESCRIPTION
      "Battery String 7 Temperature"
   ::= { string7 2 }

batt7_bloc1v OBJECT-TYPE
   SYNTAX Integer32
   UNITS "mV"
   MAX-ACCESS read-only
   STATUS current
   DESCRIPTION
      "Battery String 7 Bloc 1 Voltage"
   ::= { string7 3 }

batt7_bloc2v OBJECT-TYPE
   SYNTAX Integer32
   UNITS "mV"
   MAX-ACCESS read-only
   STATUS current
   DESCRIPTION
      "Battery String 7 Bloc 2 Voltage"
   ::= { string7 4 }

batt7_bloc3v OBJECT-TYPE
   SYNTAX Integer32
   UNITS "mV"
   MAX-ACCESS read-only
   STATUS current
   DESCRIPTION
      "Battery String 7 Bloc 3 Voltage"
   ::= { string7 5 }

batt7_bloc4v OBJECT-TYPE
   SYNTAX Integer32
   UNITS "mV"
   MAX-ACCESS read-only
   STATUS current
   DESCRIPTION
      "Battery String 7 Bloc 4 Voltage"
   ::= { string7 6 }

batt8_amps OBJECT-TYPE
   SYNTAX Integer32
   UNITS "mA"
   MAX-ACCESS read-only
   STATUS current
   DESCRIPTION
      "Battery String 8 Current"
   ::= { string8 1 }

batt8_temp OBJECT-TYPE
   SYNTAX Integer32
   UNITS "0.1 DegC"
   MAX-ACCESS read-only
   STATUS current
   DESCRIPTION
      "Battery String 8 Temperature"
   ::= { string8 2 }

batt8_bloc1v OBJECT-TYPE
   SYNTAX Integer32
   UNITS "mV"
   MAX-ACCESS read-only
   STATUS current
   DESCRIPTION
      "Battery String 8 Bloc 1 Voltage"
   ::= { string8 3 }

batt8_bloc2v OBJECT-TYPE
   SYNTAX Integer32
   UNITS "mV"
   MAX-ACCESS read-only
   STATUS current
   DESCRIPTION
      "Battery String 8 Bloc 2 Voltage"
   ::= { string8 4 }

batt8_bloc3v OBJECT-TYPE
   SYNTAX Integer32
   UNITS "mV"
   MAX-ACCESS read-only
   STATUS current
   DESCRIPTION
      "Battery String 8 Bloc 3 Voltage"
   ::= { string8 5 }

batt8_bloc4v OBJECT-TYPE
   SYNTAX Integer32
   UNITS "mV"
   MAX-ACCESS read-only
   STATUS current
   DESCRIPTION
      "Battery String 8 Bloc 4 Voltage"
   ::= { string8 6 }

batt9_amps OBJECT-TYPE
   SYNTAX Integer32
   UNITS "mA"
   MAX-ACCESS read-only
   STATUS current
   DESCRIPTION
      "Battery String 9 Current"
   ::= { string9 1 }

batt9_temp OBJECT-TYPE
   SYNTAX Integer32
   UNITS "0.1 DegC"
   MAX-ACCESS read-only
   STATUS current
   DESCRIPTION
      "Battery String 9 Temperature"
   ::= { string9 2 }

batt9_bloc1v OBJECT-TYPE
   SYNTAX Integer32
   UNITS "mV"
   MAX-ACCESS read-only
   STATUS current
   DESCRIPTION
      "Battery String 9 Bloc 1 Voltage"
   ::= { string9 3 }

batt9_bloc2v OBJECT-TYPE
   SYNTAX Integer32
   UNITS "mV"
   MAX-ACCESS read-only
   STATUS current
   DESCRIPTION
      "Battery String 9 Bloc 2 Voltage"
   ::= { string9 4 }

batt9_bloc3v OBJECT-TYPE
   SYNTAX Integer32
   UNITS "mV"
   MAX-ACCESS read-only
   STATUS current
   DESCRIPTION
      "Battery String 9 Bloc 3 Voltage"
   ::= { string9 5 }

batt9_bloc4v OBJECT-TYPE
   SYNTAX Integer32
   UNITS "mV"
   MAX-ACCESS read-only
   STATUS current
   DESCRIPTION
      "Battery String 9 Bloc 4 Voltage"
   ::= { string9 6 }

batt10_amps OBJECT-TYPE
   SYNTAX Integer32
   UNITS "mA"
   MAX-ACCESS read-only
   STATUS current
   DESCRIPTION
      "Battery String 10 Current"
   ::= { string10 1 }

batt10_temp OBJECT-TYPE
   SYNTAX Integer32
   UNITS "0.1 DegC"
   MAX-ACCESS read-only
   STATUS current
   DESCRIPTION
      "Battery String 10 Temperature"
   ::= { string10 2 }

batt10_bloc1v OBJECT-TYPE
   SYNTAX Integer32
   UNITS "mV"
   MAX-ACCESS read-only
   STATUS current
   DESCRIPTION
      "Battery String 10 Bloc 1 Voltage"
   ::= { string10 3 }

batt10_bloc2v OBJECT-TYPE
   SYNTAX Integer32
   UNITS "mV"
   MAX-ACCESS read-only
   STATUS current
   DESCRIPTION
      "Battery String 10 Bloc 2 Voltage"
   ::= { string10 4 }

batt10_bloc3v OBJECT-TYPE
   SYNTAX Integer32
   UNITS "mV"
   MAX-ACCESS read-only
   STATUS current
   DESCRIPTION
      "Battery String 10 Bloc 3 Voltage"
   ::= { string10 5 }

batt10_bloc4v OBJECT-TYPE
   SYNTAX Integer32
   UNITS "mV"
   MAX-ACCESS read-only
   STATUS current
   DESCRIPTION
      "Battery String 10 Bloc 4 Voltage"
   ::= { string10 6 }

valhybrecti OBJECT-TYPE
   SYNTAX Integer32
   UNITS "mA"
   MAX-ACCESS read-only
   STATUS current
   DESCRIPTION
      "Rectifier Current"
   ::= { hybcurrents 1 }

valhybsolari OBJECT-TYPE
   SYNTAX Integer32
   UNITS "mA"
   MAX-ACCESS read-only
   STATUS current
   DESCRIPTION
      "Solar Current"
   ::= { hybcurrents 2 }

valhybwindi OBJECT-TYPE
   SYNTAX Integer32
   UNITS "mA"
   MAX-ACCESS read-only
   STATUS current
   DESCRIPTION
      "Wind Current"
   ::= { hybcurrents 3 }

valhybbati OBJECT-TYPE
   SYNTAX Integer32
   UNITS "mA"
   MAX-ACCESS read-only
   STATUS current
   DESCRIPTION
      "Battery Current"
   ::= { hybcurrents 4 }

valhybloadi OBJECT-TYPE
   SYNTAX Integer32
   UNITS "mA"
   MAX-ACCESS read-only
   STATUS current
   DESCRIPTION
      "Load Current"
   ::= { hybcurrents 5 }

valhybload1i OBJECT-TYPE
   SYNTAX Integer32
   UNITS "mA"
   MAX-ACCESS read-only
   STATUS current
   DESCRIPTION
      "Load Current 1"
   ::= { hybcurrents 6 }

valhybload2i OBJECT-TYPE
   SYNTAX Integer32
   UNITS "mA"
   MAX-ACCESS read-only
   STATUS current
   DESCRIPTION
      "Load Current 2"
   ::= { hybcurrents 7 }

valhybload3i OBJECT-TYPE
   SYNTAX Integer32
   UNITS "mA"
   MAX-ACCESS read-only
   STATUS current
   DESCRIPTION
      "Load Current 3"
   ::= { hybcurrents 8 }

valhybrectp OBJECT-TYPE
   SYNTAX Integer32
   UNITS "W"
   MAX-ACCESS read-only
   STATUS current
   DESCRIPTION
      "Rectifier Power"
   ::= { hybpowers 1 }

valhybsolarp OBJECT-TYPE
   SYNTAX Integer32
   UNITS "W"
   MAX-ACCESS read-only
   STATUS current
   DESCRIPTION
      "Solar Power"
   ::= { hybpowers 2 }

valhybwindp OBJECT-TYPE
   SYNTAX Integer32
   UNITS "W"
   MAX-ACCESS read-only
   STATUS current
   DESCRIPTION
      "Wind Power"
   ::= { hybpowers 3 }

valhybbatp OBJECT-TYPE
   SYNTAX Integer32
   UNITS "W"
   MAX-ACCESS read-only
   STATUS current
   DESCRIPTION
      "Battery Power"
   ::= { hybpowers 4 }

valhybloadp OBJECT-TYPE
   SYNTAX Integer32
   UNITS "W"
   MAX-ACCESS read-only
   STATUS current
   DESCRIPTION
      "Load Power"
   ::= { hybpowers 5 }

valhybload1p OBJECT-TYPE
   SYNTAX Integer32
   UNITS "W"
   MAX-ACCESS read-only
   STATUS current
   DESCRIPTION
      "Load Power 1"
   ::= { hybpowers 6 }

valhybload2p OBJECT-TYPE
   SYNTAX Integer32
   UNITS "W"
   MAX-ACCESS read-only
   STATUS current
   DESCRIPTION
      "Load Power 2"
   ::= { hybpowers 7 }

valhybload3p OBJECT-TYPE
   SYNTAX Integer32
   UNITS "W"
   MAX-ACCESS read-only
   STATUS current
   DESCRIPTION
      "Load Power 3"
   ::= { hybpowers 8 }

valgen1runhours OBJECT-TYPE
   SYNTAX Integer32
   UNITS "Hours"
   MAX-ACCESS read-only
   STATUS current
   DESCRIPTION
      "Generator 1 Run Hours"
   ::= { hybrunhours 1 }

valgen2runhours OBJECT-TYPE
   SYNTAX Integer32
   UNITS "Hours"
   MAX-ACCESS read-only
   STATUS current
   DESCRIPTION
      "Generator 2 Run Hours"
   ::= { hybrunhours 2 }

valgridrunhours OBJECT-TYPE
   SYNTAX Integer32
   UNITS "Hours"
   MAX-ACCESS read-only
   STATUS current
   DESCRIPTION
      "Grid Run Hours"
   ::= { hybrunhours 3 }

valhybcyclastendreas OBJECT-TYPE
   SYNTAX DisplayString
   UNITS ""
   MAX-ACCESS read-only
   STATUS current
   DESCRIPTION
      "Hybrid Last Cycle End Reason"
   ::= { hybstate 1 }

valhybcyclaststartreas OBJECT-TYPE
   SYNTAX DisplayString
   UNITS ""
   MAX-ACCESS read-only
   STATUS current
   DESCRIPTION
      "Hybrid Last Cycle Start Reason"
   ::= { hybstate 2 }

valhybstate OBJECT-TYPE
   SYNTAX DisplayString
   UNITS ""
   MAX-ACCESS read-only
   STATUS current
   DESCRIPTION
      "Hybrid State"
   ::= { hybstate 3 }

valhybcycleelapsed OBJECT-TYPE
   SYNTAX DisplayString
   UNITS ""
   MAX-ACCESS read-only
   STATUS current
   DESCRIPTION
      "Hybrid Cycle Time Elapsed"
   ::= { hybstate 4 }

valhybgenretriesrem OBJECT-TYPE
   SYNTAX Integer32
   UNITS ""
   MAX-ACCESS read-only
   STATUS current
   DESCRIPTION
      "Hybrid Generator Start Retries Remaining"
   ::= { hybstate 5 }

valhyb1hretriesrem OBJECT-TYPE
   SYNTAX Integer32
   UNITS ""
   MAX-ACCESS read-only
   STATUS current
   DESCRIPTION
      "Hybrid 1h Cooldown Retries Remaining"
   ::= { hybstate 6 }

valhybnextextchrg OBJECT-TYPE
   SYNTAX DisplayString
   UNITS ""
   MAX-ACCESS read-only
   STATUS current
   DESCRIPTION
      "Hybrid Next Extended Charge Cycle Start"
   ::= { hybstate 7 }

valhybnextgentest OBJECT-TYPE
   SYNTAX DisplayString
   UNITS ""
   MAX-ACCESS read-only
   STATUS current
   DESCRIPTION
      "Hybrid Next Generator Test Start"
   ::= { hybstate 8 }

valhybpwrlim OBJECT-TYPE
   SYNTAX Integer32
   UNITS "W"
   MAX-ACCESS read-only
   STATUS current
   DESCRIPTION
      "Hybrid Rectifier Power Limit"
   ::= { hybstate 9 }

valhybnextmpp OBJECT-TYPE
   SYNTAX DisplayString
   UNITS ""
   MAX-ACCESS read-only
   STATUS current
   DESCRIPTION
      "Hybrid Time Until Next MPP"
   ::= { hybstate 10 }

valhyblastmpppeak OBJECT-TYPE
   SYNTAX Integer32
   UNITS "W"
   MAX-ACCESS read-only
   STATUS current
   DESCRIPTION
      "Hybrid Last MPP Real Peak Generator Power"
   ::= { hybstate 11 }

valhyblastloadpeak OBJECT-TYPE
   SYNTAX Integer32
   UNITS "W"
   MAX-ACCESS read-only
   STATUS current
   DESCRIPTION
      "Hybrid Last Load Value at MPP Peak"
   ::= { hybstate 12 }

valhybrapidrepeats OBJECT-TYPE
   SYNTAX Integer32
   UNITS ""
   MAX-ACCESS read-only
   STATUS current
   DESCRIPTION
      "Hybrid MPP Rapid Repeats Remaining"
   ::= { hybstate 13 }

valhybsoloptstatus OBJECT-TYPE
   SYNTAX DisplayString
   UNITS ""
   MAX-ACCESS read-only
   STATUS current
   DESCRIPTION
      "Hybrid Solar Optimisation Status"
   ::= { hybstate 14 }

valhybsoloptinhbstart OBJECT-TYPE
   SYNTAX DisplayString
   UNITS ""
   MAX-ACCESS read-only
   STATUS current
   DESCRIPTION
      "Hybrid Solar Optimisation Inhibit Start Time"
   ::= { hybstate 15 }

valhybsoloptinhbstop OBJECT-TYPE
   SYNTAX DisplayString
   UNITS ""
   MAX-ACCESS read-only
   STATUS current
   DESCRIPTION
      "Hybrid Solar Optimisation Inhibit Stop Time"
   ::= { hybstate 16 }

valhybacphase1v OBJECT-TYPE
   SYNTAX Integer32
   UNITS "mV"
   MAX-ACCESS read-only
   STATUS current
   DESCRIPTION
      "Hybrid AC Phase 1 Voltage"
   ::= { hybacmonitoring 1 }

valhybacphase2v OBJECT-TYPE
   SYNTAX Integer32
   UNITS "mV"
   MAX-ACCESS read-only
   STATUS current
   DESCRIPTION
      "Hybrid AC Phase 2 Voltage"
   ::= { hybacmonitoring 2 }

valhybacphase3v OBJECT-TYPE
   SYNTAX Integer32
   UNITS "mV"
   MAX-ACCESS read-only
   STATUS current
   DESCRIPTION
      "Hybrid AC Phase 3 Voltage"
   ::= { hybacmonitoring 3 }

valhybacphase1a OBJECT-TYPE
   SYNTAX Integer32
   UNITS "mA"
   MAX-ACCESS read-only
   STATUS current
   DESCRIPTION
      "Hybrid AC Phase 1 Current"
   ::= { hybacmonitoring 4 }

valhybacphase2a OBJECT-TYPE
   SYNTAX Integer32
   UNITS "mA"
   MAX-ACCESS read-only
   STATUS current
   DESCRIPTION
      "Hybrid AC Phase 2 Current"
   ::= { hybacmonitoring 5 }

valhybacphase3a OBJECT-TYPE
   SYNTAX Integer32
   UNITS "mA"
   MAX-ACCESS read-only
   STATUS current
   DESCRIPTION
      "Hybrid AC Phase 3 Current"
   ::= { hybacmonitoring 6 }

valhybacfreqhp OBJECT-TYPE
   SYNTAX Integer32
   UNITS "Hz"
   MAX-ACCESS read-only
   STATUS current
   DESCRIPTION
      "Hybrid AC Frequency (High Precision)"
   ::= { hybacmonitoring 7 }

valhybacpow OBJECT-TYPE
   SYNTAX Integer32
   UNITS "W"
   MAX-ACCESS read-only
   STATUS current
   DESCRIPTION
      "Hybrid AC Power"
   ::= { hybacmonitoring 8 }

flghybrescyc OBJECT-TYPE
   SYNTAX Integer32
   UNITS ""
   MAX-ACCESS read-only
   STATUS current
   DESCRIPTION
      "Hybrid Resume Cycle Latched"
   ::= { hybgeneralflags 1 }

flghybfixedpwr OBJECT-TYPE
   SYNTAX Integer32
   UNITS ""
   MAX-ACCESS read-only
   STATUS current
   DESCRIPTION
      "Hybrid Running Fixed Power"
   ::= { hybgeneralflags 2 }

flghybgenstrttrial OBJECT-TYPE
   SYNTAX Integer32
   UNITS ""
   MAX-ACCESS read-only
   STATUS current
   DESCRIPTION
      "Hybrid Generator Startup Trial"
   ::= { hybgeneralflags 3 }

flghybgenrunning OBJECT-TYPE
   SYNTAX Integer32
   UNITS ""
   MAX-ACCESS read-only
   STATUS current
   DESCRIPTION
      "Hybrid Generator Running"
   ::= { hybgeneralflags 4 }

flghybgenstopped OBJECT-TYPE
   SYNTAX Integer32
   UNITS ""
   MAX-ACCESS read-only
   STATUS current
   DESCRIPTION
      "Hybrid Generator Stopped"
   ::= { hybgeneralflags 5 }

flghybmpprapidmode OBJECT-TYPE
   SYNTAX Integer32
   UNITS ""
   MAX-ACCESS read-only
   STATUS current
   DESCRIPTION
      "Hybrid MPP Rapid Repeat Mode"
   ::= { hybgeneralflags 6 }

flghybstallpwr OBJECT-TYPE
   SYNTAX Integer32
   UNITS ""
   MAX-ACCESS read-only
   STATUS current
   DESCRIPTION
      "Hybrid Stall Power Active"
   ::= { hybgeneralflags 7 }

flghybabort OBJECT-TYPE
   SYNTAX Integer32
   UNITS ""
   MAX-ACCESS read-only
   STATUS current
   DESCRIPTION
      "Hybrid Abort In Progress"
   ::= { hybgeneralflags 8 }

flghybprevmppfail OBJECT-TYPE
   SYNTAX Integer32
   UNITS ""
   MAX-ACCESS read-only
   STATUS current
   DESCRIPTION
      "Hybrid Previous MPP Failed"
   ::= { hybgeneralflags 9 }

flghybmcbopen OBJECT-TYPE
   SYNTAX Integer32
   UNITS ""
   MAX-ACCESS read-only
   STATUS current
   DESCRIPTION
      "Hybrid One Or More Battery MCBs Are Open"
   ::= { hybgeneralflags 10 }

flghybgenacmfail OBJECT-TYPE
   SYNTAX Integer32
   UNITS ""
   MAX-ACCESS read-only
   STATUS current
   DESCRIPTION
      "Hybrid Generator ACM Fail"
   ::= { hybgeneralflags 11 }

flghybiggenderate OBJECT-TYPE
   SYNTAX Integer32
   UNITS ""
   MAX-ACCESS read-only
   STATUS current
   DESCRIPTION
      "Hybrid Ignoring Generator Derating"
   ::= { hybgeneralflags 12 }

flghybfastcharge OBJECT-TYPE
   SYNTAX Integer32
   UNITS ""
   MAX-ACCESS read-only
   STATUS current
   DESCRIPTION
      "Hybrid Fast Charge Active"
   ::= { hybgeneralflags 13 }

flghyballrectoff OBJECT-TYPE
   SYNTAX Integer32
   UNITS ""
   MAX-ACCESS read-only
   STATUS current
   DESCRIPTION
      "Hybrid All Rectifiers Off"
   ::= { hybgeneralflags 14 }

flghybgridforced OBJECT-TYPE
   SYNTAX Integer32
   UNITS ""
   MAX-ACCESS read-only
   STATUS current
   DESCRIPTION
      "Hybrid Grid AC Supply Being Forced"
   ::= { hybgeneralflags 16 }

valhybacsource OBJECT-TYPE
   SYNTAX DisplayString
   UNITS ""
   MAX-ACCESS read-only
   STATUS current
   DESCRIPTION
      "Hybrid Rectifier AC Source"
   ::= { hybgeneralflags 18 }

flghyballgenfaillock OBJECT-TYPE
   SYNTAX Integer32
   UNITS ""
   MAX-ACCESS read-only
   STATUS current
   DESCRIPTION
      "Hybrid All Generator Fail Lockout"
   ::= { hybgeneralflags 19 }

flghybantistallcfgoff OBJECT-TYPE
   SYNTAX Integer32
   UNITS ""
   MAX-ACCESS read-only
   STATUS current
   DESCRIPTION
      "Hybrid Antistall Configured Off"
   ::= { hybgeneralflags 20 }

flghybantistallgridoff OBJECT-TYPE
   SYNTAX Integer32
   UNITS ""
   MAX-ACCESS read-only
   STATUS current
   DESCRIPTION
      "Hybrid Antistall Off Due to Grid Presence"
   ::= { hybgeneralflags 21 }

flghybgen1retry OBJECT-TYPE
   SYNTAX Integer32
   UNITS ""
   MAX-ACCESS read-only
   STATUS current
   DESCRIPTION
      "Hybrid Generator 1 Retry Allowed"
   ::= { hybgen1flags 1 }

flghybgen1lowoilpress OBJECT-TYPE
   SYNTAX Integer32
   UNITS ""
   MAX-ACCESS read-only
   STATUS current
   DESCRIPTION
      "Hybrid Generator 1 Low Oil Pressure"
   ::= { hybgen1flags 2 }

flghybgen1hightemp OBJECT-TYPE
   SYNTAX Integer32
   UNITS ""
   MAX-ACCESS read-only
   STATUS current
   DESCRIPTION
      "Hybrid Generator 1 High Temperature"
   ::= { hybgen1flags 3 }

flghybgen1lowbatvolts OBJECT-TYPE
   SYNTAX Integer32
   UNITS ""
   MAX-ACCESS read-only
   STATUS current
   DESCRIPTION
      "Hybrid Generator 1 Low Battery Volts"
   ::= { hybgen1flags 4 }

flghybgen1manlockout OBJECT-TYPE
   SYNTAX Integer32
   UNITS ""
   MAX-ACCESS read-only
   STATUS current
   DESCRIPTION
      "Hybrid Generator 1 Manual Lockout"
   ::= { hybgen1flags 5 }

flghybgen1startpulse OBJECT-TYPE
   SYNTAX Integer32
   UNITS ""
   MAX-ACCESS read-only
   STATUS current
   DESCRIPTION
      "Hybrid Generator 1 Start Pulse"
   ::= { hybgen1flags 6 }

flghybgen1startlevel OBJECT-TYPE
   SYNTAX Integer32
   UNITS ""
   MAX-ACCESS read-only
   STATUS current
   DESCRIPTION
      "Hybrid Generator 1 Start Level"
   ::= { hybgen1flags 7 }

flghybgen1fail OBJECT-TYPE
   SYNTAX Integer32
   UNITS ""
   MAX-ACCESS read-only
   STATUS current
   DESCRIPTION
      "Hybrid Generator 1 Fail"
   ::= { hybgen1flags 8 }

flghybgen1phasefail OBJECT-TYPE
   SYNTAX Integer32
   UNITS ""
   MAX-ACCESS read-only
   STATUS current
   DESCRIPTION
      "Hybrid Generator 1 Phase Fail"
   ::= { hybgen1flags 9 }

flghybgen1lowpwr OBJECT-TYPE
   SYNTAX Integer32
   UNITS ""
   MAX-ACCESS read-only
   STATUS current
   DESCRIPTION
      "Hybrid Generator 1 Low Power"
   ::= { hybgen1flags 10 }

flghybgen1urglowpwr OBJECT-TYPE
   SYNTAX Integer32
   UNITS ""
   MAX-ACCESS read-only
   STATUS current
   DESCRIPTION
      "Hybrid Generator 1 Urgent Low Power"
   ::= { hybgen1flags 11 }

flghybgen1failtostop OBJECT-TYPE
   SYNTAX Integer32
   UNITS ""
   MAX-ACCESS read-only
   STATUS current
   DESCRIPTION
      "Hybrid Generator 1 Failed To Stop"
   ::= { hybgen1flags 12 }

flghybgen2retry OBJECT-TYPE
   SYNTAX Integer32
   UNITS ""
   MAX-ACCESS read-only
   STATUS current
   DESCRIPTION
      "Hybrid Generator 2 Retry Granted"
   ::= { hybgen2flags 1 }

flghybgen2lowoilpress OBJECT-TYPE
   SYNTAX Integer32
   UNITS ""
   MAX-ACCESS read-only
   STATUS current
   DESCRIPTION
      "Hybrid Generator 2 Low Oil Pressure"
   ::= { hybgen2flags 2 }

flghybgen2hightemp OBJECT-TYPE
   SYNTAX Integer32
   UNITS ""
   MAX-ACCESS read-only
   STATUS current
   DESCRIPTION
      "Hybrid Generator 2 High Temperature"
   ::= { hybgen2flags 3 }

flghybgen2lowbatvolts OBJECT-TYPE
   SYNTAX Integer32
   UNITS ""
   MAX-ACCESS read-only
   STATUS current
   DESCRIPTION
      "Hybrid Generator 2 Low Battery Volts"
   ::= { hybgen2flags 4 }

flghybgen2manlockout OBJECT-TYPE
   SYNTAX Integer32
   UNITS ""
   MAX-ACCESS read-only
   STATUS current
   DESCRIPTION
      "Hybrid Generator 2 Manual Lockout"
   ::= { hybgen2flags 5 }

flghybgen2startpulse OBJECT-TYPE
   SYNTAX Integer32
   UNITS ""
   MAX-ACCESS read-only
   STATUS current
   DESCRIPTION
      "Hybrid Generator 2 Start Pulse"
   ::= { hybgen2flags 6 }

flghybgen2startlevel OBJECT-TYPE
   SYNTAX Integer32
   UNITS ""
   MAX-ACCESS read-only
   STATUS current
   DESCRIPTION
      "Hybrid Generator 2 Start Level"
   ::= { hybgen2flags 7 }

flghybgen2fail OBJECT-TYPE
   SYNTAX Integer32
   UNITS ""
   MAX-ACCESS read-only
   STATUS current
   DESCRIPTION
      "Hybrid Generator 2 Fail"
   ::= { hybgen2flags 8 }

flghybgen2phasefail OBJECT-TYPE
   SYNTAX Integer32
   UNITS ""
   MAX-ACCESS read-only
   STATUS current
   DESCRIPTION
      "Hybrid Generator 2 Phase Fail"
   ::= { hybgen2flags 9 }

flghybgen2lowpwr OBJECT-TYPE
   SYNTAX Integer32
   UNITS ""
   MAX-ACCESS read-only
   STATUS current
   DESCRIPTION
      "Hybrid Generator 2 Low Power"
   ::= { hybgen2flags 10 }

flghybgen2urglowpwr OBJECT-TYPE
   SYNTAX Integer32
   UNITS ""
   MAX-ACCESS read-only
   STATUS current
   DESCRIPTION
      "Hybrid Generator 2 Urgent Low Power"
   ::= { hybgen2flags 11 }

flghybgen2failtostop OBJECT-TYPE
   SYNTAX Integer32
   UNITS ""
   MAX-ACCESS read-only
   STATUS current
   DESCRIPTION
      "Hybrid Generator 2 Failed To Stop"
   ::= { hybgen2flags 12 }

flghybgridlostimmed OBJECT-TYPE
   SYNTAX Integer32
   UNITS ""
   MAX-ACCESS read-only
   STATUS current
   DESCRIPTION
      "Hybrid Grid Lost (Immediate)"
   ::= { hybgridflags 1 }

flghybgridlostcond OBJECT-TYPE
   SYNTAX Integer32
   UNITS ""
   MAX-ACCESS read-only
   STATUS current
   DESCRIPTION
      "Hybrid Grid Lost (Conditioned)"
   ::= { hybgridflags 2 }

flghybfuel1logicerr OBJECT-TYPE
   SYNTAX Integer32
   UNITS ""
   MAX-ACCESS read-only
   STATUS current
   DESCRIPTION
      "Hybrid Fuel Tank 1 Logic Error"
   ::= { hybfueltank1 1 }

flghybfuel1emptynonurg OBJECT-TYPE
   SYNTAX Integer32
   UNITS ""
   MAX-ACCESS read-only
   STATUS current
   DESCRIPTION
      "Hybrid Fuel Tank 1 Empty Non Urgent Alarm"
   ::= { hybfueltank1 2 }

flghybfuel1emptyurg OBJECT-TYPE
   SYNTAX Integer32
   UNITS ""
   MAX-ACCESS read-only
   STATUS current
   DESCRIPTION
      "Hybrid Fuel Tank 1 Empty Urgent Alarm"
   ::= { hybfueltank1 3 }

flghybfuel2logicerr OBJECT-TYPE
   SYNTAX Integer32
   UNITS ""
   MAX-ACCESS read-only
   STATUS current
   DESCRIPTION
      "Hybrid Fuel Tank 2 Logic Error"
   ::= { hybfueltank2 1 }

flghybfuel2emptynonurg OBJECT-TYPE
   SYNTAX Integer32
   UNITS ""
   MAX-ACCESS read-only
   STATUS current
   DESCRIPTION
      "Hybrid Fuel Tank 2 Empty Non Urgent Alarm"
   ::= { hybfueltank2 2 }

flghybfuel2emptyurg OBJECT-TYPE
   SYNTAX Integer32
   UNITS ""
   MAX-ACCESS read-only
   STATUS current
   DESCRIPTION
      "Hybrid Fuel Tank 2 Empty Urgent Alarm"
   ::= { hybfueltank2 3 }



-- ALARMS

readwritetrap1 OBJECT-TYPE
    SYNTAX ALARMS
    MAX-ACCESS read-write
    STATUS current
	DESCRIPTION
		"SM32 Trap 1"
	::= { traps 1 }

readwritetrap2 OBJECT-TYPE
    SYNTAX ALARMS
    MAX-ACCESS read-write
    STATUS current
	DESCRIPTION
		"SM32 Trap 2"
	::= { traps 2 }

readwritetrap3 OBJECT-TYPE
    SYNTAX ALARMS
    MAX-ACCESS read-write
    STATUS current
	DESCRIPTION
		"SM32 Trap 3"
	::= { traps 3 }

readwritetrap4 OBJECT-TYPE
    SYNTAX ALARMS
    MAX-ACCESS read-write
    STATUS current
	DESCRIPTION
		"SM32 Trap 4"
	::= { traps 4 }

readwritetrap5 OBJECT-TYPE
    SYNTAX ALARMS
    MAX-ACCESS read-write
    STATUS current
	DESCRIPTION
		"SM32 Trap 5"
	::= { traps 5 }


-- ALARMS SNMPv2 and SNMPv3 Trap definitions


communityerror TRAP-TYPE
   ENTERPRISE enatel
   DESCRIPTION
      "INFORMATION: An access has been made with the wrong community"
   --#TYPE "SM32 Trap 1"
   --#SUMMARY "Community error"
   --#ARGUMENTS { }
   --#SEVERITY INFORMATIONAL
   --#TIMEINDEX 1
   --#HELP ""
   --#HELPTAG 0
   --#STATE OPERATIONAL
   ::= 1

iprestricterror TRAP-TYPE
   ENTERPRISE enatel
   DESCRIPTION
      "INFORMATION: An access has been made from an unknown IP address"
   --#TYPE "SM32 Trap 1"
   --#SUMMARY "IP error"
   --#ARGUMENTS { }
   --#SEVERITY INFORMATIONAL
   --#TIMEINDEX 1
   --#HELP ""
   --#HELPTAG 0
   --#STATE OPERATIONAL
   ::= 2

setdisablederror TRAP-TYPE
   ENTERPRISE enatel
   DESCRIPTION
      "INFORMATION: An access has been made to write an variable but SET is disabled at the monitor"
   --#TYPE "SM32 Trap 1"
   --#SUMMARY "Can not process SET request. SET is Disabled"
   --#ARGUMENTS { }
   --#SEVERITY INFORMATIONAL
   --#TIMEINDEX 1
   --#HELP ""
   --#HELPTAG 0
   --#STATE OPERATIONAL
   ::= 3

snmpversionerror TRAP-TYPE
   ENTERPRISE enatel
   DESCRIPTION
      "INFORMATION: An access has been made with an unsupported SNMP version"
   --#TYPE "SM32 Trap 1"
   --#SUMMARY "Unsuported Version"
   --#ARGUMENTS { }
   --#SEVERITY INFORMATIONAL
   --#TIMEINDEX 1
   --#HELP ""
   --#HELPTAG 0
   --#STATE OPERATIONAL
   ::= 4
























useralarm1on TRAP-TYPE
   ENTERPRISE enatel
   DESCRIPTION
      "INFORMATION: User Alarm 1 has activated"
   --#TYPE "SM32 Trap"
   --#SUMMARY "User Alarm 1 Active"
   --#ARGUMENTS { }
   --#SEVERITY CRITICAL
   --#TIMEINDEX 1
   --#HELP ""
   --#HELPTAG 0
   --#STATE OPERATIONAL
   ::= 10

useralarm1off TRAP-TYPE
   ENTERPRISE enatel
   DESCRIPTION
      "INFORMATION: User Alarm 1 has returned to normal"
   --#TYPE "SM32 Trap"
   --#SUMMARY "User Alarm 1 Normal"
   --#ARGUMENTS { }
   --#SEVERITY INFORMATIONAL
   --#TIMEINDEX 1
   --#HELP ""
   --#HELPTAG 0
   --#STATE OPERATIONAL
   ::= 11

useralarm2on TRAP-TYPE
   ENTERPRISE enatel
   DESCRIPTION
      "INFORMATION: User Alarm 2 has activated"
   --#TYPE "SM32 Trap"
   --#SUMMARY "User Alarm 2 Active"
   --#ARGUMENTS { }
   --#SEVERITY CRITICAL
   --#TIMEINDEX 1
   --#HELP ""
   --#HELPTAG 0
   --#STATE OPERATIONAL
   ::= 12

useralarm2off TRAP-TYPE
   ENTERPRISE enatel
   DESCRIPTION
      "INFORMATION: User Alarm 2 has returned to normal"
   --#TYPE "SM32 Trap"
   --#SUMMARY "User Alarm 2 Normal"
   --#ARGUMENTS { }
   --#SEVERITY INFORMATIONAL
   --#TIMEINDEX 1
   --#HELP ""
   --#HELPTAG 0
   --#STATE OPERATIONAL
   ::= 13

useralarm3on TRAP-TYPE
   ENTERPRISE enatel
   DESCRIPTION
      "INFORMATION: User Alarm 3 has activated"
   --#TYPE "SM32 Trap"
   --#SUMMARY "User Alarm 3 Active"
   --#ARGUMENTS { }
   --#SEVERITY CRITICAL
   --#TIMEINDEX 1
   --#HELP ""
   --#HELPTAG 0
   --#STATE OPERATIONAL
   ::= 14

useralarm3off TRAP-TYPE
   ENTERPRISE enatel
   DESCRIPTION
      "INFORMATION: User Alarm 3 has returned to normal"
   --#TYPE "SM32 Trap"
   --#SUMMARY "User Alarm 3 Normal"
   --#ARGUMENTS { }
   --#SEVERITY INFORMATIONAL
   --#TIMEINDEX 1
   --#HELP ""
   --#HELPTAG 0
   --#STATE OPERATIONAL
   ::= 15

useralarm4on TRAP-TYPE
   ENTERPRISE enatel
   DESCRIPTION
      "INFORMATION: User Alarm 4 has activated"
   --#TYPE "SM32 Trap"
   --#SUMMARY "User Alarm 2 Active"
   --#ARGUMENTS { }
   --#SEVERITY CRITICAL
   --#TIMEINDEX 1
   --#HELP ""
   --#HELPTAG 0
   --#STATE OPERATIONAL
   ::= 16

useralarm4off TRAP-TYPE
   ENTERPRISE enatel
   DESCRIPTION
      "INFORMATION: User Alarm 4 has returned to normal"
   --#TYPE "SM32 Trap"
   --#SUMMARY "User Alarm 4 Normal"
   --#ARGUMENTS { }
   --#SEVERITY INFORMATIONAL
   --#TIMEINDEX 1
   --#HELP ""
   --#HELPTAG 0
   --#STATE OPERATIONAL
   ::= 17

useralarm5on TRAP-TYPE
   ENTERPRISE enatel
   DESCRIPTION
      "INFORMATION: User Alarm 5 has activated"
   --#TYPE "SM32 Trap"
   --#SUMMARY "User Alarm 5 Active"
   --#ARGUMENTS { }
   --#SEVERITY CRITICAL
   --#TIMEINDEX 1
   --#HELP ""
   --#HELPTAG 0
   --#STATE OPERATIONAL
   ::= 18

useralarm5off TRAP-TYPE
   ENTERPRISE enatel
   DESCRIPTION
      "INFORMATION: User Alarm 5 has returned to normal"
   --#TYPE "SM32 Trap"
   --#SUMMARY "User Alarm 5 Normal"
   --#ARGUMENTS { }
   --#SEVERITY INFORMATIONAL
   --#TIMEINDEX 1
   --#HELP ""
   --#HELPTAG 0
   --#STATE OPERATIONAL
   ::= 19

useralarm6on TRAP-TYPE
   ENTERPRISE enatel
   DESCRIPTION
      "INFORMATION: User Alarm 6 has activated"
   --#TYPE "SM32 Trap"
   --#SUMMARY "User Alarm 6 Active"
   --#ARGUMENTS { }
   --#SEVERITY CRITICAL
   --#TIMEINDEX 1
   --#HELP ""
   --#HELPTAG 0
   --#STATE OPERATIONAL
   ::= 20

useralarm6off TRAP-TYPE
   ENTERPRISE enatel
   DESCRIPTION
      "INFORMATION: User Alarm 6 has returned to normal"
   --#TYPE "SM32 Trap"
   --#SUMMARY "User Alarm 6 Normal"
   --#ARGUMENTS { }
   --#SEVERITY INFORMATIONAL
   --#TIMEINDEX 1
   --#HELP ""
   --#HELPTAG 0
   --#STATE OPERATIONAL
   ::= 21


useralarm7on TRAP-TYPE
   ENTERPRISE enatel
   DESCRIPTION
      "INFORMATION: User Alarm 7 has activated"
   --#TYPE "SM32 Trap"
   --#SUMMARY "User Alarm 7 Active"
   --#ARGUMENTS { }
   --#SEVERITY CRITICAL
   --#TIMEINDEX 1
   --#HELP ""
   --#HELPTAG 0
   --#STATE OPERATIONAL
   ::= 22

useralarm7off TRAP-TYPE
   ENTERPRISE enatel
   DESCRIPTION
      "INFORMATION: User Alarm 7 has returned to normal"
   --#TYPE "SM32 Trap"
   --#SUMMARY "User Alarm 7 Normal"
   --#ARGUMENTS { }
   --#SEVERITY INFORMATIONAL
   --#TIMEINDEX 1
   --#HELP ""
   --#HELPTAG 0
   --#STATE OPERATIONAL
   ::= 23

useralarm8on TRAP-TYPE
   ENTERPRISE enatel
   DESCRIPTION
      "INFORMATION: User Alarm 8 has activated"
   --#TYPE "SM32 Trap"
   --#SUMMARY "User Alarm 8 Active"
   --#ARGUMENTS { }
   --#SEVERITY CRITICAL
   --#TIMEINDEX 1
   --#HELP ""
   --#HELPTAG 0
   --#STATE OPERATIONAL
   ::= 24

useralarm8off TRAP-TYPE
   ENTERPRISE enatel
   DESCRIPTION
      "INFORMATION: User Alarm 8 has returned to normal"
   --#TYPE "SM32 Trap"
   --#SUMMARY "User Alarm 8 Normal"
   --#ARGUMENTS { }
   --#SEVERITY INFORMATIONAL
   --#TIMEINDEX 1
   --#HELP ""
   --#HELPTAG 0
   --#STATE OPERATIONAL
   ::= 25

useralarm9on TRAP-TYPE
   ENTERPRISE enatel
   DESCRIPTION
      "INFORMATION: User Alarm 9 has activated"
   --#TYPE "SM32 Trap"
   --#SUMMARY "User Alarm 9 Active"
   --#ARGUMENTS { }
   --#SEVERITY CRITICAL
   --#TIMEINDEX 1
   --#HELP ""
   --#HELPTAG 0
   --#STATE OPERATIONAL
   ::= 26

useralarm9off TRAP-TYPE
   ENTERPRISE enatel
   DESCRIPTION
      "INFORMATION: User Alarm 9 has returned to normal"
   --#TYPE "SM32 Trap"
   --#SUMMARY "User Alarm 9 Normal"
   --#ARGUMENTS { }
   --#SEVERITY INFORMATIONAL
   --#TIMEINDEX 1
   --#HELP ""
   --#HELPTAG 0
   --#STATE OPERATIONAL
   ::= 27

useralarm10on TRAP-TYPE
   ENTERPRISE enatel
   DESCRIPTION
      "INFORMATION: User Alarm 10 has activated"
   --#TYPE "SM32 Trap"
   --#SUMMARY "User Alarm 10 Active"
   --#ARGUMENTS { }
   --#SEVERITY CRITICAL
   --#TIMEINDEX 1
   --#HELP ""
   --#HELPTAG 0
   --#STATE OPERATIONAL
   ::= 28

useralarm10off TRAP-TYPE
   ENTERPRISE enatel
   DESCRIPTION
      "INFORMATION: User Alarm 10 has returned to normal"
   --#TYPE "SM32 Trap"
   --#SUMMARY "User Alarm 10 Normal"
   --#ARGUMENTS { }
   --#SEVERITY INFORMATIONAL
   --#TIMEINDEX 1
   --#HELP ""
   --#HELPTAG 0
   --#STATE OPERATIONAL
   ::= 29

useralarm11on TRAP-TYPE
   ENTERPRISE enatel
   DESCRIPTION
      "INFORMATION: User Alarm 11 has activated"
   --#TYPE "SM32 Trap"
   --#SUMMARY "User Alarm 11 Active"
   --#ARGUMENTS { }
   --#SEVERITY CRITICAL
   --#TIMEINDEX 1
   --#HELP ""
   --#HELPTAG 0
   --#STATE OPERATIONAL
   ::= 30

useralarm11off TRAP-TYPE
   ENTERPRISE enatel
   DESCRIPTION
      "INFORMATION: User Alarm 11 has returned to normal"
   --#TYPE "SM32 Trap"
   --#SUMMARY "User Alarm 11 Normal"
   --#ARGUMENTS { }
   --#SEVERITY INFORMATIONAL
   --#TIMEINDEX 1
   --#HELP ""
   --#HELPTAG 0
   --#STATE OPERATIONAL
   ::= 31

useralarm12on TRAP-TYPE
   ENTERPRISE enatel
   DESCRIPTION
      "INFORMATION: User Alarm 12 has activated"
   --#TYPE "SM32 Trap"
   --#SUMMARY "User Alarm 12 Active"
   --#ARGUMENTS { }
   --#SEVERITY CRITICAL
   --#TIMEINDEX 1
   --#HELP ""
   --#HELPTAG 0
   --#STATE OPERATIONAL
   ::= 32

useralarm12off TRAP-TYPE
   ENTERPRISE enatel
   DESCRIPTION
      "INFORMATION: User Alarm 12 has returned to normal"
   --#TYPE "SM32 Trap"
   --#SUMMARY "User Alarm 12 Normal"
   --#ARGUMENTS { }
   --#SEVERITY INFORMATIONAL
   --#TIMEINDEX 1
   --#HELP ""
   --#HELPTAG 0
   --#STATE OPERATIONAL
   ::= 33

useralarm13on TRAP-TYPE
   ENTERPRISE enatel
   DESCRIPTION
      "INFORMATION: User Alarm 13 has activated"
   --#TYPE "SM32 Trap"
   --#SUMMARY "User Alarm 13 Active"
   --#ARGUMENTS { }
   --#SEVERITY CRITICAL
   --#TIMEINDEX 1
   --#HELP ""
   --#HELPTAG 0
   --#STATE OPERATIONAL
   ::= 34

useralarm13off TRAP-TYPE
   ENTERPRISE enatel
   DESCRIPTION
      "INFORMATION: User Alarm 13 has returned to normal"
   --#TYPE "SM32 Trap"
   --#SUMMARY "User Alarm 13 Normal"
   --#ARGUMENTS { }
   --#SEVERITY INFORMATIONAL
   --#TIMEINDEX 1
   --#HELP ""
   --#HELPTAG 0
   --#STATE OPERATIONAL
   ::= 35

useralarm14on TRAP-TYPE
   ENTERPRISE enatel
   DESCRIPTION
      "INFORMATION: User Alarm 14 has activated"
   --#TYPE "SM32 Trap"
   --#SUMMARY "User Alarm 14 Active"
   --#ARGUMENTS { }
   --#SEVERITY CRITICAL
   --#TIMEINDEX 1
   --#HELP ""
   --#HELPTAG 0
   --#STATE OPERATIONAL
   ::= 36

useralarm14off TRAP-TYPE
   ENTERPRISE enatel
   DESCRIPTION
      "INFORMATION: User Alarm 14 has returned to normal"
   --#TYPE "SM32 Trap"
   --#SUMMARY "User Alarm 14 Normal"
   --#ARGUMENTS { }
   --#SEVERITY INFORMATIONAL
   --#TIMEINDEX 1
   --#HELP ""
   --#HELPTAG 0
   --#STATE OPERATIONAL
   ::= 37


useralarm15on TRAP-TYPE
   ENTERPRISE enatel
   DESCRIPTION
      "INFORMATION: User Alarm 15 has activated"
   --#TYPE "SM32 Trap"
   --#SUMMARY "User Alarm 15 Active"
   --#ARGUMENTS { }
   --#SEVERITY CRITICAL
   --#TIMEINDEX 1
   --#HELP ""
   --#HELPTAG 0
   --#STATE OPERATIONAL
   ::= 38

useralarm15off TRAP-TYPE
   ENTERPRISE enatel
   DESCRIPTION
      "INFORMATION: User Alarm 15 has returned to normal"
   --#TYPE "SM32 Trap"
   --#SUMMARY "User Alarm 15 Normal"
   --#ARGUMENTS { }
   --#SEVERITY INFORMATIONAL
   --#TIMEINDEX 1
   --#HELP ""
   --#HELPTAG 0
   --#STATE OPERATIONAL
   ::= 39

useralarm16on TRAP-TYPE
   ENTERPRISE enatel
   DESCRIPTION
      "INFORMATION: User Alarm 16 has activated"
   --#TYPE "SM32 Trap"
   --#SUMMARY "User Alarm 16 Active"
   --#ARGUMENTS { }
   --#SEVERITY CRITICAL
   --#TIMEINDEX 1
   --#HELP ""
   --#HELPTAG 0
   --#STATE OPERATIONAL
   ::= 40

useralarm16off TRAP-TYPE
   ENTERPRISE enatel
   DESCRIPTION
      "INFORMATION: User Alarm 16 has returned to normal"
   --#TYPE "SM32 Trap"
   --#SUMMARY "User Alarm 16 Normal"
   --#ARGUMENTS { }
   --#SEVERITY INFORMATIONAL
   --#TIMEINDEX 1
   --#HELP ""
   --#HELPTAG 0
   --#STATE OPERATIONAL
   ::= 41

useralarm17on TRAP-TYPE
   ENTERPRISE enatel
   DESCRIPTION
      "INFORMATION: User Alarm 17 has activated"
   --#TYPE "SM32 Trap"
   --#SUMMARY "User Alarm 17 Active"
   --#ARGUMENTS { }
   --#SEVERITY CRITICAL
   --#TIMEINDEX 1
   --#HELP ""
   --#HELPTAG 0
   --#STATE OPERATIONAL
   ::= 42

useralarm17off TRAP-TYPE
   ENTERPRISE enatel
   DESCRIPTION
      "INFORMATION: User Alarm 17 has returned to normal"
   --#TYPE "SM32 Trap"
   --#SUMMARY "User Alarm 17 Normal"
   --#ARGUMENTS { }
   --#SEVERITY INFORMATIONAL
   --#TIMEINDEX 1
   --#HELP ""
   --#HELPTAG 0
   --#STATE OPERATIONAL
   ::= 43

useralarm18on TRAP-TYPE
   ENTERPRISE enatel
   DESCRIPTION
      "INFORMATION: User Alarm 18 has activated"
   --#TYPE "SM32 Trap"
   --#SUMMARY "User Alarm 18 Active"
   --#ARGUMENTS { }
   --#SEVERITY CRITICAL
   --#TIMEINDEX 1
   --#HELP ""
   --#HELPTAG 0
   --#STATE OPERATIONAL
   ::= 44

useralarm18off TRAP-TYPE
   ENTERPRISE enatel
   DESCRIPTION
      "INFORMATION: User Alarm 18 has returned to normal"
   --#TYPE "SM32 Trap"
   --#SUMMARY "User Alarm 18 Normal"
   --#ARGUMENTS { }
   --#SEVERITY INFORMATIONAL
   --#TIMEINDEX 1
   --#HELP ""
   --#HELPTAG 0
   --#STATE OPERATIONAL
   ::= 45

useralarm19on TRAP-TYPE
   ENTERPRISE enatel
   DESCRIPTION
      "INFORMATION: User Alarm 19 has activated"
   --#TYPE "SM32 Trap"
   --#SUMMARY "User Alarm 19 Active"
   --#ARGUMENTS { }
   --#SEVERITY CRITICAL
   --#TIMEINDEX 1
   --#HELP ""
   --#HELPTAG 0
   --#STATE OPERATIONAL
   ::= 46

useralarm19off TRAP-TYPE
   ENTERPRISE enatel
   DESCRIPTION
      "INFORMATION: User Alarm 19 has returned to normal"
   --#TYPE "SM32 Trap"
   --#SUMMARY "User Alarm 19 Normal"
   --#ARGUMENTS { }
   --#SEVERITY INFORMATIONAL
   --#TIMEINDEX 1
   --#HELP ""
   --#HELPTAG 0
   --#STATE OPERATIONAL
   ::= 47

useralarm20on TRAP-TYPE
   ENTERPRISE enatel
   DESCRIPTION
      "INFORMATION: User Alarm 20 has activated"
   --#TYPE "SM32 Trap"
   --#SUMMARY "User Alarm 20 Active"
   --#ARGUMENTS { }
   --#SEVERITY CRITICAL
   --#TIMEINDEX 1
   --#HELP ""
   --#HELPTAG 0
   --#STATE OPERATIONAL
   ::= 48

useralarm20off TRAP-TYPE
   ENTERPRISE enatel
   DESCRIPTION
      "INFORMATION: User Alarm 20 has returned to normal"
   --#TYPE "SM32 Trap"
   --#SUMMARY "User Alarm 20 Normal"
   --#ARGUMENTS { }
   --#SEVERITY INFORMATIONAL
   --#TIMEINDEX 1
   --#HELP ""
   --#HELPTAG 0
   --#STATE OPERATIONAL
   ::= 49

useralarm21on TRAP-TYPE
   ENTERPRISE enatel
   DESCRIPTION
      "INFORMATION: User Alarm 21 has activated"
   --#TYPE "SM32 Trap"
   --#SUMMARY "User Alarm 21 Active"
   --#ARGUMENTS { }
   --#SEVERITY CRITICAL
   --#TIMEINDEX 1
   --#HELP ""
   --#HELPTAG 0
   --#STATE OPERATIONAL
   ::= 50

useralarm21off TRAP-TYPE
   ENTERPRISE enatel
   DESCRIPTION
      "INFORMATION: User Alarm 21 has returned to normal"
   --#TYPE "SM32 Trap"
   --#SUMMARY "User Alarm 21 Normal"
   --#ARGUMENTS { }
   --#SEVERITY INFORMATIONAL
   --#TIMEINDEX 1
   --#HELP ""
   --#HELPTAG 0
   --#STATE OPERATIONAL
   ::= 51

useralarm22on TRAP-TYPE
   ENTERPRISE enatel
   DESCRIPTION
      "INFORMATION: User Alarm 22 has activated"
   --#TYPE "SM32 Trap"
   --#SUMMARY "User Alarm 22 Active"
   --#ARGUMENTS { }
   --#SEVERITY CRITICAL
   --#TIMEINDEX 1
   --#HELP ""
   --#HELPTAG 0
   --#STATE OPERATIONAL
   ::= 52

useralarm22off TRAP-TYPE
   ENTERPRISE enatel
   DESCRIPTION
      "INFORMATION: User Alarm 22 has returned to normal"
   --#TYPE "SM32 Trap"
   --#SUMMARY "User Alarm 22 Normal"
   --#ARGUMENTS { }
   --#SEVERITY INFORMATIONAL
   --#TIMEINDEX 1
   --#HELP ""
   --#HELPTAG 0
   --#STATE OPERATIONAL
   ::= 53

useralarm23on TRAP-TYPE
   ENTERPRISE enatel
   DESCRIPTION
      "INFORMATION: User Alarm 23 has activated"
   --#TYPE "SM32 Trap"
   --#SUMMARY "User Alarm 23 Active"
   --#ARGUMENTS { }
   --#SEVERITY CRITICAL
   --#TIMEINDEX 1
   --#HELP ""
   --#HELPTAG 0
   --#STATE OPERATIONAL
   ::= 54

useralarm23off TRAP-TYPE
   ENTERPRISE enatel
   DESCRIPTION
      "INFORMATION: User Alarm 23 has returned to normal"
   --#TYPE "SM32 Trap"
   --#SUMMARY "User Alarm 23 Normal"
   --#ARGUMENTS { }
   --#SEVERITY INFORMATIONAL
   --#TIMEINDEX 1
   --#HELP ""
   --#HELPTAG 0
   --#STATE OPERATIONAL
   ::= 55

useralarm24on TRAP-TYPE
   ENTERPRISE enatel
   DESCRIPTION
      "INFORMATION: User Alarm 24 has activated"
   --#TYPE "SM32 Trap"
   --#SUMMARY "User Alarm 24 Active"
   --#ARGUMENTS { }
   --#SEVERITY CRITICAL
   --#TIMEINDEX 1
   --#HELP ""
   --#HELPTAG 0
   --#STATE OPERATIONAL
   ::= 56

useralarm24off TRAP-TYPE
   ENTERPRISE enatel
   DESCRIPTION
      "INFORMATION: User Alarm 24 has returned to normal"
   --#TYPE "SM32 Trap"
   --#SUMMARY "User Alarm 24 Normal"
   --#ARGUMENTS { }
   --#SEVERITY INFORMATIONAL
   --#TIMEINDEX 1
   --#HELP ""
   --#HELPTAG 0
   --#STATE OPERATIONAL
   ::= 57

useralarm25on TRAP-TYPE
   ENTERPRISE enatel
   DESCRIPTION
      "INFORMATION: User Alarm 25 has activated"
   --#TYPE "SM32 Trap"
   --#SUMMARY "User Alarm 25 Active"
   --#ARGUMENTS { }
   --#SEVERITY CRITICAL
   --#TIMEINDEX 1
   --#HELP ""
   --#HELPTAG 0
   --#STATE OPERATIONAL
   ::= 58

useralarm25off TRAP-TYPE
   ENTERPRISE enatel
   DESCRIPTION
      "INFORMATION: User Alarm 25 has returned to normal"
   --#TYPE "SM32 Trap"
   --#SUMMARY "User Alarm 25 Normal"
   --#ARGUMENTS { }
   --#SEVERITY INFORMATIONAL
   --#TIMEINDEX 1
   --#HELP ""
   --#HELPTAG 0
   --#STATE OPERATIONAL
   ::= 59

useralarm26on TRAP-TYPE
   ENTERPRISE enatel
   DESCRIPTION
      "INFORMATION: User Alarm 26 has activated"
   --#TYPE "SM32 Trap"
   --#SUMMARY "User Alarm 26 Active"
   --#ARGUMENTS { }
   --#SEVERITY CRITICAL
   --#TIMEINDEX 1
   --#HELP ""
   --#HELPTAG 0
   --#STATE OPERATIONAL
   ::= 60

useralarm26off TRAP-TYPE
   ENTERPRISE enatel
   DESCRIPTION
      "INFORMATION: User Alarm 26 has returned to normal"
   --#TYPE "SM32 Trap"
   --#SUMMARY "User Alarm 26 Normal"
   --#ARGUMENTS { }
   --#SEVERITY INFORMATIONAL
   --#TIMEINDEX 1
   --#HELP ""
   --#HELPTAG 0
   --#STATE OPERATIONAL
   ::= 61

useralarm27on TRAP-TYPE
   ENTERPRISE enatel
   DESCRIPTION
      "INFORMATION: User Alarm 27 has activated"
   --#TYPE "SM32 Trap"
   --#SUMMARY "User Alarm 27 Active"
   --#ARGUMENTS { }
   --#SEVERITY CRITICAL
   --#TIMEINDEX 1
   --#HELP ""
   --#HELPTAG 0
   --#STATE OPERATIONAL
   ::= 62

useralarm27off TRAP-TYPE
   ENTERPRISE enatel
   DESCRIPTION
      "INFORMATION: User Alarm 27 has returned to normal"
   --#TYPE "SM32 Trap"
   --#SUMMARY "User Alarm 27 Normal"
   --#ARGUMENTS { }
   --#SEVERITY INFORMATIONAL
   --#TIMEINDEX 1
   --#HELP ""
   --#HELPTAG 0
   --#STATE OPERATIONAL
   ::= 63

useralarm28on TRAP-TYPE
   ENTERPRISE enatel
   DESCRIPTION
      "INFORMATION: User Alarm 28 has activated"
   --#TYPE "SM32 Trap"
   --#SUMMARY "User Alarm 28 Active"
   --#ARGUMENTS { }
   --#SEVERITY CRITICAL
   --#TIMEINDEX 1
   --#HELP ""
   --#HELPTAG 0
   --#STATE OPERATIONAL
   ::= 64

useralarm28off TRAP-TYPE
   ENTERPRISE enatel
   DESCRIPTION
      "INFORMATION: User Alarm 28 has returned to normal"
   --#TYPE "SM32 Trap"
   --#SUMMARY "User Alarm 28 Normal"
   --#ARGUMENTS { }
   --#SEVERITY INFORMATIONAL
   --#TIMEINDEX 1
   --#HELP ""
   --#HELPTAG 0
   --#STATE OPERATIONAL
   ::= 65

  useralarm29on TRAP-TYPE
   ENTERPRISE enatel
   DESCRIPTION
      "INFORMATION: User Alarm 29 has activated"
   --#TYPE "SM32 Trap"
   --#SUMMARY "User Alarm 29 Active"
   --#ARGUMENTS { }
   --#SEVERITY CRITICAL
   --#TIMEINDEX 1
   --#HELP ""
   --#HELPTAG 0
   --#STATE OPERATIONAL
   ::= 66

useralarm29off TRAP-TYPE
   ENTERPRISE enatel
   DESCRIPTION
      "INFORMATION: User Alarm 29 has returned to normal"
   --#TYPE "SM32 Trap"
   --#SUMMARY "User Alarm 29 Normal"
   --#ARGUMENTS { }
   --#SEVERITY INFORMATIONAL
   --#TIMEINDEX 1
   --#HELP ""
   --#HELPTAG 0
   --#STATE OPERATIONAL
   ::= 67

useralarm30on TRAP-TYPE
   ENTERPRISE enatel
   DESCRIPTION
      "INFORMATION: User Alarm 30 has activated"
   --#TYPE "SM32 Trap"
   --#SUMMARY "User Alarm 30 Active"
   --#ARGUMENTS { }
   --#SEVERITY CRITICAL
   --#TIMEINDEX 1
   --#HELP ""
   --#HELPTAG 0
   --#STATE OPERATIONAL
   ::= 68

useralarm30off TRAP-TYPE
   ENTERPRISE enatel
   DESCRIPTION
      "INFORMATION: User Alarm 30 has returned to normal"
   --#TYPE "SM32 Trap"
   --#SUMMARY "User Alarm 30 Normal"
   --#ARGUMENTS { }
   --#SEVERITY INFORMATIONAL
   --#TIMEINDEX 1
   --#HELP ""
   --#HELPTAG 0
   --#STATE OPERATIONAL
   ::= 69

useralarm31on TRAP-TYPE
   ENTERPRISE enatel
   DESCRIPTION
      "INFORMATION: User Alarm 31 has activated"
   --#TYPE "SM32 Trap"
   --#SUMMARY "User Alarm 31 Active"
   --#ARGUMENTS { }
   --#SEVERITY CRITICAL
   --#TIMEINDEX 1
   --#HELP ""
   --#HELPTAG 0
   --#STATE OPERATIONAL
   ::= 70

useralarm31off TRAP-TYPE
   ENTERPRISE enatel
   DESCRIPTION
      "INFORMATION: User Alarm 31 has returned to normal"
   --#TYPE "SM32 Trap"
   --#SUMMARY "User Alarm 31 Normal"
   --#ARGUMENTS { }
   --#SEVERITY INFORMATIONAL
   --#TIMEINDEX 1
   --#HELP ""
   --#HELPTAG 0
   --#STATE OPERATIONAL
   ::= 71

useralarm32on TRAP-TYPE
   ENTERPRISE enatel
   DESCRIPTION
      "INFORMATION: User Alarm 32 has activated"
   --#TYPE "SM32 Trap"
   --#SUMMARY "User Alarm 32 Active"
   --#ARGUMENTS { }
   --#SEVERITY CRITICAL
   --#TIMEINDEX 1
   --#HELP ""
   --#HELPTAG 0
   --#STATE OPERATIONAL
   ::= 72

useralarm32off TRAP-TYPE
   ENTERPRISE enatel
   DESCRIPTION
      "INFORMATION: User Alarm 32 has returned to normal"
   --#TYPE "SM32 Trap"
   --#SUMMARY "User Alarm 32 Normal"
   --#ARGUMENTS { }
   --#SEVERITY INFORMATIONAL
   --#TIMEINDEX 1
   --#HELP ""
   --#HELPTAG 0
   --#STATE OPERATIONAL
   ::= 73



rectifiermainsfailon TRAP-TYPE
   ENTERPRISE enatel
   DESCRIPTION
      "INFORMATION: Rectifier Mains fail Alarm"
   --#TYPE "SM32 Trap"
   --#SUMMARY "Rectifier Mains fail Alarm Active"
   --#ARGUMENTS { }
   --#SEVERITY CRITICAL
   --#TIMEINDEX 1
   --#HELP ""
   --#HELPTAG 0
   --#STATE OPERATIONAL
   ::= 74

rectifiermainsfailoff TRAP-TYPE
   ENTERPRISE enatel
   DESCRIPTION
      "INFORMATION: Rectifier Mains fail has returned to normal"
   --#TYPE "SM32 Trap"
   --#SUMMARY "Rectifier Mains fail Normal"
   --#ARGUMENTS { }
   --#SEVERITY INFORMATIONAL
   --#TIMEINDEX 1
   --#HELP ""
   --#HELPTAG 0
   --#STATE OPERATIONAL
   ::= 75


rectifierovertemperatureon TRAP-TYPE
   ENTERPRISE enatel
   DESCRIPTION
      "INFORMATION: Rectifier Alarm: Over Temperature"
   --#TYPE "SM32 Trap"
   --#SUMMARY "Rectifier Alarm: Over Temperature Active"
   --#ARGUMENTS { }
   --#SEVERITY CRITICAL
   --#TIMEINDEX 1
   --#HELP ""
   --#HELPTAG 0
   --#STATE OPERATIONAL
   ::= 78

rectifierovertemperatureoff TRAP-TYPE
   ENTERPRISE enatel
   DESCRIPTION
      "INFORMATION: Rectifier Alarm Over Temperature has returned to normal"
   --#TYPE "SM32 Trap"
   --#SUMMARY "Rectifier Alarm Over Temperature Normal"
   --#ARGUMENTS { }
   --#SEVERITY INFORMATIONAL
   --#TIMEINDEX 1
   --#HELP ""
   --#HELPTAG 0
   --#STATE OPERATIONAL
   ::= 79

rectifierfanfailon TRAP-TYPE
   ENTERPRISE enatel
   DESCRIPTION
      "INFORMATION: Rectifier Alarm: Fan Fail"
   --#TYPE "SM32 Trap"
   --#SUMMARY "Rectifier Alarm: Fan Fail Active"
   --#ARGUMENTS { }
   --#SEVERITY CRITICAL
   --#TIMEINDEX 1
   --#HELP ""
   --#HELPTAG 0
   --#STATE OPERATIONAL
   ::= 80

rectifierfanfailoff TRAP-TYPE
   ENTERPRISE enatel
   DESCRIPTION
      "INFORMATION: Rectifier Alarm: Fan Fail has returned to normal"
   --#TYPE "SM32 Trap"
   --#SUMMARY "Rectifier Alarm: Fan Fail Normal"
   --#ARGUMENTS { }
   --#SEVERITY INFORMATIONAL
   --#TIMEINDEX 1
   --#HELP ""
   --#HELPTAG 0
   --#STATE OPERATIONAL
   ::= 81

rectifiercurrentlimiton TRAP-TYPE
   ENTERPRISE enatel
   DESCRIPTION
      "INFORMATION: Rectifier Alarm: Current Limit"
   --#TYPE "SM32 Trap"
   --#SUMMARY "Rectifier Alarm: Current Limit Active"
   --#ARGUMENTS { }
   --#SEVERITY CRITICAL
   --#TIMEINDEX 1
   --#HELP ""
   --#HELPTAG 0
   --#STATE OPERATIONAL
   ::= 82

rectifiercurrentlimitoff TRAP-TYPE
   ENTERPRISE enatel
   DESCRIPTION
      "INFORMATION: Rectifier Alarm: Current Limit has returned to normal"
   --#TYPE "SM32 Trap"
   --#SUMMARY "Rectifier Alarm: Current Limit Normal"
   --#ARGUMENTS { }
   --#SEVERITY INFORMATIONAL
   --#TIMEINDEX 1
   --#HELP ""
   --#HELPTAG 0
   --#STATE OPERATIONAL
   ::= 83

rectifierovervoltageshutdownon TRAP-TYPE
   ENTERPRISE enatel
   DESCRIPTION
      "INFORMATION: Rectifier Alarm: Over Voltage Shutdown"
   --#TYPE "SM32 Trap"
   --#SUMMARY "Rectifier Alarm: Over Voltage Shutdown Active"
   --#ARGUMENTS { }
   --#SEVERITY CRITICAL
   --#TIMEINDEX 1
   --#HELP ""
   --#HELPTAG 0
   --#STATE OPERATIONAL
   ::= 84

rectifierovervoltageshutdownoff TRAP-TYPE
   ENTERPRISE enatel
   DESCRIPTION
      "INFORMATION: Rectifier Alarm: Over Voltage Shutdown has returned to normal"
   --#TYPE "SM32 Trap"
   --#SUMMARY "Rectifier Alarm: Over Voltage Shutdown Normal"
   --#ARGUMENTS { }
   --#SEVERITY INFORMATIONAL
   --#TIMEINDEX 1
   --#HELP ""
   --#HELPTAG 0
   --#STATE OPERATIONAL
   ::= 85

rectifierbrownouton TRAP-TYPE
   ENTERPRISE enatel
   DESCRIPTION
      "INFORMATION: Rectifier Alarm: Brownout"
   --#TYPE "SM32 Trap"
   --#SUMMARY "Rectifier Alarm: Brownout Active"
   --#ARGUMENTS { }
   --#SEVERITY CRITICAL
   --#TIMEINDEX 1
   --#HELP ""
   --#HELPTAG 0
   --#STATE OPERATIONAL
   ::= 86

rectifierbrownoutoff TRAP-TYPE
   ENTERPRISE enatel
   DESCRIPTION
      "INFORMATION: Rectifier Alarm: Brownout has returned to normal"
   --#TYPE "SM32 Trap"
   --#SUMMARY "Rectifier Alarm: Brownout Normal"
   --#ARGUMENTS { }
   --#SEVERITY INFORMATIONAL
   --#TIMEINDEX 1
   --#HELP ""
   --#HELPTAG 0
   --#STATE OPERATIONAL
   ::= 87


rectifierpostmateon TRAP-TYPE
   ENTERPRISE enatel
   DESCRIPTION
      "INFORMATION: Rectifier Alarm: Postmate"
   --#TYPE "SM32 Trap"
   --#SUMMARY "Rectifier Alarm: Postmate Active"
   --#ARGUMENTS { }
   --#SEVERITY CRITICAL
   --#TIMEINDEX 1
   --#HELP ""
   --#HELPTAG 0
   --#STATE OPERATIONAL
   ::= 88

rectifierpostmateoff TRAP-TYPE
   ENTERPRISE enatel
   DESCRIPTION
      "INFORMATION: Rectifier Alarm: Postmate has returned to normal"
   --#TYPE "SM32 Trap"
   --#SUMMARY "Rectifier Alarm: Postmate Normal"
   --#ARGUMENTS { }
   --#SEVERITY INFORMATIONAL
   --#TIMEINDEX 1
   --#HELP ""
   --#HELPTAG 0
   --#STATE OPERATIONAL
   ::= 89


rectifierbooston TRAP-TYPE
   ENTERPRISE enatel
   DESCRIPTION
      "INFORMATION: Rectifier Alarm: Boost"
   --#TYPE "SM32 Trap"
   --#SUMMARY "Rectifier Alarm: Boost Active"
   --#ARGUMENTS { }
   --#SEVERITY CRITICAL
   --#TIMEINDEX 1
   --#HELP ""
   --#HELPTAG 0
   --#STATE OPERATIONAL
   ::= 98

rectifierboostoff TRAP-TYPE
   ENTERPRISE enatel
   DESCRIPTION
      "INFORMATION: Rectifier Alarm: Boost has returned to normal"
   --#TYPE "SM32 Trap"
   --#SUMMARY "Rectifier Alarm: Boost Normal"
   --#ARGUMENTS { }
   --#SEVERITY INFORMATIONAL
   --#TIMEINDEX 1
   --#HELP ""
   --#HELPTAG 0
   --#STATE OPERATIONAL
   ::= 99

rectifiershutdownon TRAP-TYPE
   ENTERPRISE enatel
   DESCRIPTION
      "INFORMATION: Rectifier Alarm: Shutdown"
   --#TYPE "SM32 Trap"
   --#SUMMARY "Rectifier Alarm: Shutdown Active"
   --#ARGUMENTS { }
   --#SEVERITY CRITICAL
   --#TIMEINDEX 1
   --#HELP ""
   --#HELPTAG 0
   --#STATE OPERATIONAL
   ::= 100

rectifiershutdownoff TRAP-TYPE
   ENTERPRISE enatel
   DESCRIPTION
      "INFORMATION:Rectifier Alarm: Shutdown has returned to normal"
   --#TYPE "SM32 Trap"
   --#SUMMARY "Rectifier Alarm: Shutdown Normal"
   --#ARGUMENTS { }
   --#SEVERITY INFORMATIONAL
   --#TIMEINDEX 1
   --#HELP ""
   --#HELPTAG 0
   --#STATE OPERATIONAL
   ::= 101

rectifiereepromfailon TRAP-TYPE
   ENTERPRISE enatel
   DESCRIPTION
      "INFORMATION: Rectifier Alarm: EEPROM Fail"
   --#TYPE "SM32 Trap"
   --#SUMMARY "Rectifier Alarm: EEPROM Fail Active"
   --#ARGUMENTS { }
   --#SEVERITY CRITICAL
   --#TIMEINDEX 1
   --#HELP ""
   --#HELPTAG 0
   --#STATE OPERATIONAL
   ::= 102

rectifiereepromfailoff TRAP-TYPE
   ENTERPRISE enatel
   DESCRIPTION
      "INFORMATION:Rectifier Alarm: EEPROM Fail has returned to normal"
   --#TYPE "SM32 Trap"
   --#SUMMARY "Rectifier Alarm: EEPROM Fail Normal"
   --#ARGUMENTS { }
   --#SEVERITY INFORMATIONAL
   --#TIMEINDEX 1
   --#HELP ""
   --#HELPTAG 0
   --#STATE OPERATIONAL
   ::= 103

rectifiersoftstartingon TRAP-TYPE
   ENTERPRISE enatel
   DESCRIPTION
      "INFORMATION: Rectifier Alarm: Soft Starting"
   --#TYPE "SM32 Trap"
   --#SUMMARY "Rectifier Alarm: Soft Starting Active"
   --#ARGUMENTS { }
   --#SEVERITY CRITICAL
   --#TIMEINDEX 1
   --#HELP ""
   --#HELPTAG 0
   --#STATE OPERATIONAL
   ::= 104

rectifiersoftstartingoff TRAP-TYPE
   ENTERPRISE enatel
   DESCRIPTION
      "INFORMATION:Rectifier Alarm: Soft Starting has returned to normal"
   --#TYPE "SM32 Trap"
   --#SUMMARY "Rectifier Alarm: Soft Starting Normal"
   --#ARGUMENTS { }
   --#SEVERITY INFORMATIONAL
   --#TIMEINDEX 1
   --#HELP ""
   --#HELPTAG 0
   --#STATE OPERATIONAL
   ::= 105

converterinputfailon TRAP-TYPE
   ENTERPRISE enatel
   DESCRIPTION
      "INFORMATION: Converter Alarm: Input Fail"
   --#TYPE "SM32 Trap"
   --#SUMMARY "Converter Alarm: Input Fail Active"
   --#ARGUMENTS { }
   --#SEVERITY CRITICAL
   --#TIMEINDEX 1
   --#HELP ""
   --#HELPTAG 0
   --#STATE OPERATIONAL
   ::= 106

converterinputfailoff TRAP-TYPE
   ENTERPRISE enatel
   DESCRIPTION
      "INFORMATION:Converter Alarm: Input Fail has returned to normal"
   --#TYPE "SM32 Trap"
   --#SUMMARY "Converter Alarm: Input Fail Normal"
   --#ARGUMENTS { }
   --#SEVERITY INFORMATIONAL
   --#TIMEINDEX 1
   --#HELP ""
   --#HELPTAG 0
   --#STATE OPERATIONAL
   ::= 107



converterovertemperatureon TRAP-TYPE
   ENTERPRISE enatel
   DESCRIPTION
      "INFORMATION: Converter Alarm: Over Temperature"
   --#TYPE "SM32 Trap"
   --#SUMMARY "Converter Alarm: Over Temperature Active"
   --#ARGUMENTS { }
   --#SEVERITY CRITICAL
   --#TIMEINDEX 1
   --#HELP ""
   --#HELPTAG 0
   --#STATE OPERATIONAL
   ::= 110

converterovertemperatureoff TRAP-TYPE
   ENTERPRISE enatel
   DESCRIPTION
      "INFORMATION:Converter Alarm: Over Temperature has returned to normal"
   --#TYPE "SM32 Trap"
   --#SUMMARY "Converter Alarm: Over Temperature Normal"
   --#ARGUMENTS { }
   --#SEVERITY INFORMATIONAL
   --#TIMEINDEX 1
   --#HELP ""
   --#HELPTAG 0
   --#STATE OPERATIONAL
   ::= 111

converterfanfailon TRAP-TYPE
   ENTERPRISE enatel
   DESCRIPTION
      "INFORMATION: Converter Alarm: Fan Fail"
   --#TYPE "SM32 Trap"
   --#SUMMARY "Converter Alarm: Fan Fail Active"
   --#ARGUMENTS { }
   --#SEVERITY CRITICAL
   --#TIMEINDEX 1
   --#HELP ""
   --#HELPTAG 0
   --#STATE OPERATIONAL
   ::= 112

converterfanfailoff TRAP-TYPE
   ENTERPRISE enatel
   DESCRIPTION
      "INFORMATION:Converter Alarm: Fan Fail has returned to normal"
   --#TYPE "SM32 Trap"
   --#SUMMARY "Converter Alarm: Fan Fail Normal"
   --#ARGUMENTS { }
   --#SEVERITY INFORMATIONAL
   --#TIMEINDEX 1
   --#HELP ""
   --#HELPTAG 0
   --#STATE OPERATIONAL
   ::= 113

convertercurrentlimiton TRAP-TYPE
   ENTERPRISE enatel
   DESCRIPTION
      "INFORMATION: Converter Alarm: Current Limit"
   --#TYPE "SM32 Trap"
   --#SUMMARY "Converter Alarm: Current Limit Active"
   --#ARGUMENTS { }
   --#SEVERITY CRITICAL
   --#TIMEINDEX 1
   --#HELP ""
   --#HELPTAG 0
   --#STATE OPERATIONAL
   ::= 114

convertercurrentlimitoff TRAP-TYPE
   ENTERPRISE enatel
   DESCRIPTION
      "INFORMATION:Converter Alarm: Current Limit has returned to normal"
   --#TYPE "SM32 Trap"
   --#SUMMARY "Converter Alarm: Current Limit Normal"
   --#ARGUMENTS { }
   --#SEVERITY INFORMATIONAL
   --#TIMEINDEX 1
   --#HELP ""
   --#HELPTAG 0
   --#STATE OPERATIONAL
   ::= 115

converterovervoltageshutdownon TRAP-TYPE
   ENTERPRISE enatel
   DESCRIPTION
      "INFORMATION: Converter Alarm: Over Voltage Shutdown"
   --#TYPE "SM32 Trap"
   --#SUMMARY "Converter Alarm: Over Voltage Shutdown Active"
   --#ARGUMENTS { }
   --#SEVERITY CRITICAL
   --#TIMEINDEX 1
   --#HELP ""
   --#HELPTAG 0
   --#STATE OPERATIONAL
   ::= 116

converterovervoltageshutdownoff TRAP-TYPE
   ENTERPRISE enatel
   DESCRIPTION
      "INFORMATION:Converter Alarm: Over Voltage Shutdown has returned to normal"
   --#TYPE "SM32 Trap"
   --#SUMMARY "Converter Alarm: Over Voltage Shutdown Normal"
   --#ARGUMENTS { }
   --#SEVERITY INFORMATIONAL
   --#TIMEINDEX 1
   --#HELP ""
   --#HELPTAG 0
   --#STATE OPERATIONAL
   ::= 117

converterbrownouton TRAP-TYPE
   ENTERPRISE enatel
   DESCRIPTION
      "INFORMATION: Converter Alarm: Brownout Shutdown"
   --#TYPE "SM32 Trap"
   --#SUMMARY "Converter Alarm: Brownout Active"
   --#ARGUMENTS { }
   --#SEVERITY CRITICAL
   --#TIMEINDEX 1
   --#HELP ""
   --#HELPTAG 0
   --#STATE OPERATIONAL
   ::= 118

converterbrownoutoff TRAP-TYPE
   ENTERPRISE enatel
   DESCRIPTION
      "INFORMATION:Converter Alarm: Brownout has returned to normal"
   --#TYPE "SM32 Trap"
   --#SUMMARY "Converter Alarm: Brownout Normal"
   --#ARGUMENTS { }
   --#SEVERITY INFORMATIONAL
   --#TIMEINDEX 1
   --#HELP ""
   --#HELPTAG 0
   --#STATE OPERATIONAL
   ::= 119

converterpostmateon TRAP-TYPE
   ENTERPRISE enatel
   DESCRIPTION
      "INFORMATION: Converter Alarm: Postmate"
   --#TYPE "SM32 Trap"
   --#SUMMARY "Converter Alarm: Postmate Active"
   --#ARGUMENTS { }
   --#SEVERITY CRITICAL
   --#TIMEINDEX 1
   --#HELP ""
   --#HELPTAG 0
   --#STATE OPERATIONAL
   ::= 120

converterpostmateoff TRAP-TYPE
   ENTERPRISE enatel
   DESCRIPTION
      "INFORMATION:Converter Alarm: Postmate has returned to normal"
   --#TYPE "SM32 Trap"
   --#SUMMARY "Converter Alarm: Postmate Normal"
   --#ARGUMENTS { }
   --#SEVERITY INFORMATIONAL
   --#TIMEINDEX 1
   --#HELP ""
   --#HELPTAG 0
   --#STATE OPERATIONAL
   ::= 121

converterstandaloneon TRAP-TYPE
   ENTERPRISE enatel
   DESCRIPTION
      "INFORMATION: Converter Alarm: Standalone"
   --#TYPE "SM32 Trap"
   --#SUMMARY "Converter Alarm: Standalone Active"
   --#ARGUMENTS { }
   --#SEVERITY CRITICAL
   --#TIMEINDEX 1
   --#HELP ""
   --#HELPTAG 0
   --#STATE OPERATIONAL
   ::= 130

converterstandaloneoff TRAP-TYPE
   ENTERPRISE enatel
   DESCRIPTION
      "INFORMATION:Converter Alarm: Standalone has returned to normal"
   --#TYPE "SM32 Trap"
   --#SUMMARY "Converter Alarm: Standalone Normal"
   --#ARGUMENTS { }
   --#SEVERITY INFORMATIONAL
   --#TIMEINDEX 1
   --#HELP ""
   --#HELPTAG 0
   --#STATE OPERATIONAL
   ::= 131

convertershutdownon TRAP-TYPE
   ENTERPRISE enatel
   DESCRIPTION
      "INFORMATION: Converter Alarm: Shutdown"
   --#TYPE "SM32 Trap"
   --#SUMMARY "Converter Alarm: Shutdown Active"
   --#ARGUMENTS { }
   --#SEVERITY CRITICAL
   --#TIMEINDEX 1
   --#HELP ""
   --#HELPTAG 0
   --#STATE OPERATIONAL
   ::= 132

convertershutdownoff TRAP-TYPE
   ENTERPRISE enatel
   DESCRIPTION
      "INFORMATION:Converter Alarm: Shutdown has returned to normal"
   --#TYPE "SM32 Trap"
   --#SUMMARY "Converter Alarm: Shutdown Normal"
   --#ARGUMENTS { }
   --#SEVERITY INFORMATIONAL
   --#TIMEINDEX 1
   --#HELP ""
   --#HELPTAG 0
   --#STATE OPERATIONAL
   ::= 133

convertereepromfailon TRAP-TYPE
   ENTERPRISE enatel
   DESCRIPTION
      "INFORMATION: Converter Alarm: EEPROM Fail"
   --#TYPE "SM32 Trap"
   --#SUMMARY "Converter Alarm: EEPROM Fail Active"
   --#ARGUMENTS { }
   --#SEVERITY CRITICAL
   --#TIMEINDEX 1
   --#HELP ""
   --#HELPTAG 0
   --#STATE OPERATIONAL
   ::= 134

convertereepromfailoff TRAP-TYPE
   ENTERPRISE enatel
   DESCRIPTION
      "INFORMATION:Converter Alarm: EEPROM Fail has returned to normal"
   --#TYPE "SM32 Trap"
   --#SUMMARY "Converter Alarm: EEPROM Fail Normal"
   --#ARGUMENTS { }
   --#SEVERITY INFORMATIONAL
   --#TIMEINDEX 1
   --#HELP ""
   --#HELPTAG 0
   --#STATE OPERATIONAL
   ::= 135

convertersoftstartingon TRAP-TYPE
   ENTERPRISE enatel
   DESCRIPTION
      "INFORMATION: Converter Alarm: Soft Starting"
   --#TYPE "SM32 Trap"
   --#SUMMARY "Converter Alarm: Soft Starting Active"
   --#ARGUMENTS { }
   --#SEVERITY CRITICAL
   --#TIMEINDEX 1
   --#HELP ""
   --#HELPTAG 0
   --#STATE OPERATIONAL
   ::= 136

convertersoftstartingoff TRAP-TYPE
   ENTERPRISE enatel
   DESCRIPTION
      "INFORMATION:Converter Alarm: Soft Starting has returned to normal"
   --#TYPE "SM32 Trap"
   --#SUMMARY "Converter Alarm: Soft Starting Normal"
   --#ARGUMENTS { }
   --#SEVERITY INFORMATIONAL
   --#TIMEINDEX 1
   --#HELP ""
   --#HELPTAG 0
   --#STATE OPERATIONAL
   ::= 137

invertercommsfailon TRAP-TYPE
   ENTERPRISE enatel
   DESCRIPTION
      "INFORMATION: Inverter Alarm: Comms Fail"
   --#TYPE "SM32 Trap"
   --#SUMMARY "Inverter Alarm: Comms Fail Active"
   --#ARGUMENTS { }
   --#SEVERITY CRITICAL
   --#TIMEINDEX 1
   --#HELP ""
   --#HELPTAG 0
   --#STATE OPERATIONAL
   ::= 138

invertercommsfailoff TRAP-TYPE
   ENTERPRISE enatel
   DESCRIPTION
      "INFORMATION:Inverter Alarm: Comms Fail has returned to normal"
   --#TYPE "SM32 Trap"
   --#SUMMARY "Inverter Alarm: Comms Fail Normal"
   --#ARGUMENTS { }
   --#SEVERITY INFORMATIONAL
   --#TIMEINDEX 1
   --#HELP ""
   --#HELPTAG 0
   --#STATE OPERATIONAL
   ::= 139

inverterfailon TRAP-TYPE
   ENTERPRISE enatel
   DESCRIPTION
      "INFORMATION: Inverter Alarm: Inverter Fail"
   --#TYPE "SM32 Trap"
   --#SUMMARY "Inverter Alarm: Inverter Fail Active"
   --#ARGUMENTS { }
   --#SEVERITY CRITICAL
   --#TIMEINDEX 1
   --#HELP ""
   --#HELPTAG 0
   --#STATE OPERATIONAL
   ::= 140

inverterfailoff TRAP-TYPE
   ENTERPRISE enatel
   DESCRIPTION
      "INFORMATION:Inverter Alarm: Inverter Fail has returned to normal"
   --#TYPE "SM32 Trap"
   --#SUMMARY "Inverter Alarm: Inverter Fail Normal"
   --#ARGUMENTS { }
   --#SEVERITY INFORMATIONAL
   --#TIMEINDEX 1
   --#HELP ""
   --#HELPTAG 0
   --#STATE OPERATIONAL
   ::= 141

inverterovertemperatureon TRAP-TYPE
   ENTERPRISE enatel
   DESCRIPTION
      "INFORMATION: Inverter Alarm: Over Temperature"
   --#TYPE "SM32 Trap"
   --#SUMMARY "Inverter Alarm: Over Temperature Active"
   --#ARGUMENTS { }
   --#SEVERITY CRITICAL
   --#TIMEINDEX 1
   --#HELP ""
   --#HELPTAG 0
   --#STATE OPERATIONAL
   ::= 142

inverterovertemperatureoff TRAP-TYPE
   ENTERPRISE enatel
   DESCRIPTION
      "INFORMATION:Inverter Alarm: Over Temperature has returned to normal"
   --#TYPE "SM32 Trap"
   --#SUMMARY "Inverter Alarm: Over Temperature Normal"
   --#ARGUMENTS { }
   --#SEVERITY INFORMATIONAL
   --#TIMEINDEX 1
   --#HELP ""
   --#HELPTAG 0
   --#STATE OPERATIONAL
   ::= 143

inverterfanfailon TRAP-TYPE
   ENTERPRISE enatel
   DESCRIPTION
      "INFORMATION: Inverter Alarm: Fan Fail"
   --#TYPE "SM32 Trap"
   --#SUMMARY "Inverter Alarm: Fan Fail Active"
   --#ARGUMENTS { }
   --#SEVERITY CRITICAL
   --#TIMEINDEX 1
   --#HELP ""
   --#HELPTAG 0
   --#STATE OPERATIONAL
   ::= 144

inverterfanfailoff TRAP-TYPE
   ENTERPRISE enatel
   DESCRIPTION
      "INFORMATION:Inverter Alarm: Fan Fail has returned to normal"
   --#TYPE "SM32 Trap"
   --#SUMMARY "Inverter Alarm: Fan Fail Normal"
   --#ARGUMENTS { }
   --#SEVERITY INFORMATIONAL
   --#TIMEINDEX 1
   --#HELP ""
   --#HELPTAG 0
   --#STATE OPERATIONAL
   ::= 145

inverterpowerlimiton TRAP-TYPE
   ENTERPRISE enatel
   DESCRIPTION
      "INFORMATION: Inverter Alarm: Power Limit"
   --#TYPE "SM32 Trap"
   --#SUMMARY "Inverter Alarm: Power Limit Active"
   --#ARGUMENTS { }
   --#SEVERITY CRITICAL
   --#TIMEINDEX 1
   --#HELP ""
   --#HELPTAG 0
   --#STATE OPERATIONAL
   ::= 146

inverterpowerlimitoff TRAP-TYPE
   ENTERPRISE enatel
   DESCRIPTION
      "INFORMATION:Inverter Alarm: Power Limit has returned to normal"
   --#TYPE "SM32 Trap"
   --#SUMMARY "Inverter Alarm: Power Limit Normal"
   --#ARGUMENTS { }
   --#SEVERITY INFORMATIONAL
   --#TIMEINDEX 1
   --#HELP ""
   --#HELPTAG 0
   --#STATE OPERATIONAL
   ::= 147

inverterinputvoltagehighon TRAP-TYPE
   ENTERPRISE enatel
   DESCRIPTION
      "INFORMATION: Inverter Alarm: Input Voltage High"
   --#TYPE "SM32 Trap"
   --#SUMMARY "Inverter Alarm: Input Voltage High Active"
   --#ARGUMENTS { }
   --#SEVERITY CRITICAL
   --#TIMEINDEX 1
   --#HELP ""
   --#HELPTAG 0
   --#STATE OPERATIONAL
   ::= 148

inverterinputvoltagehighoff TRAP-TYPE
   ENTERPRISE enatel
   DESCRIPTION
      "INFORMATION:Inverter Alarm: Input Voltage High has returned to normal"
   --#TYPE "SM32 Trap"
   --#SUMMARY "Inverter Alarm: Input Voltage High Normal"
   --#ARGUMENTS { }
   --#SEVERITY INFORMATIONAL
   --#TIMEINDEX 1
   --#HELP ""
   --#HELPTAG 0
   --#STATE OPERATIONAL
   ::= 149

inverterinputvoltagelowon TRAP-TYPE
   ENTERPRISE enatel
   DESCRIPTION
      "INFORMATION: Inverter Alarm: Input Voltage Low"
   --#TYPE "SM32 Trap"
   --#SUMMARY "Inverter Alarm: Input Voltage Low Active"
   --#ARGUMENTS { }
   --#SEVERITY CRITICAL
   --#TIMEINDEX 1
   --#HELP ""
   --#HELPTAG 0
   --#STATE OPERATIONAL
   ::= 150

inverterinputvoltagelowoff TRAP-TYPE
   ENTERPRISE enatel
   DESCRIPTION
      "INFORMATION:Inverter Alarm: Input Voltage Low has returned to normal"
   --#TYPE "SM32 Trap"
   --#SUMMARY "Inverter Alarm: Input Voltage Low Normal"
   --#ARGUMENTS { }
   --#SEVERITY INFORMATIONAL
   --#TIMEINDEX 1
   --#HELP ""
   --#HELPTAG 0
   --#STATE OPERATIONAL
   ::= 151


inverteremergencypoweroffon TRAP-TYPE
   ENTERPRISE enatel
   DESCRIPTION
      "INFORMATION: Inverter Alarm: Emergency Power Off"
   --#TYPE "SM32 Trap"
   --#SUMMARY "Inverter Alarm: Emergency Power Off Active"
   --#ARGUMENTS { }
   --#SEVERITY CRITICAL
   --#TIMEINDEX 1
   --#HELP ""
   --#HELPTAG 0
   --#STATE OPERATIONAL
   ::= 152

inverteremergencypoweroffoff TRAP-TYPE
   ENTERPRISE enatel
   DESCRIPTION
      "INFORMATION:Inverter Alarm: Emergency Power Off has returned to normal"
   --#TYPE "SM32 Trap"
   --#SUMMARY "Inverter Alarm: Emergency Power Off Normal"
   --#ARGUMENTS { }
   --#SEVERITY INFORMATIONAL
   --#TIMEINDEX 1
   --#HELP ""
   --#HELPTAG 0
   --#STATE OPERATIONAL
   ::= 153

inverteroutputvoltagehighon TRAP-TYPE
   ENTERPRISE enatel
   DESCRIPTION
      "INFORMATION: Inverter Alarm: Output Voltage High"
   --#TYPE "SM32 Trap"
   --#SUMMARY "Inverter Alarm: Output Voltage High Active"
   --#ARGUMENTS { }
   --#SEVERITY CRITICAL
   --#TIMEINDEX 1
   --#HELP ""
   --#HELPTAG 0
   --#STATE OPERATIONAL
   ::= 154

inverteroutputvoltagehighoff TRAP-TYPE
   ENTERPRISE enatel
   DESCRIPTION
      "INFORMATION:Inverter Alarm: Output Voltage High has returned to normal"
   --#TYPE "SM32 Trap"
   --#SUMMARY "Inverter Alarm: Output Voltage High Normal"
   --#ARGUMENTS { }
   --#SEVERITY INFORMATIONAL
   --#TIMEINDEX 1
   --#HELP ""
   --#HELPTAG 0
   --#STATE OPERATIONAL
   ::= 155


inverteroutputvoltagelowon TRAP-TYPE
   ENTERPRISE enatel
   DESCRIPTION
      "INFORMATION: Inverter Alarm: Output Voltage Low"
   --#TYPE "SM32 Trap"
   --#SUMMARY "Inverter Alarm: Output Voltage Low Active"
   --#ARGUMENTS { }
   --#SEVERITY CRITICAL
   --#TIMEINDEX 1
   --#HELP ""
   --#HELPTAG 0
   --#STATE OPERATIONAL
   ::= 156

inverteroutputvoltagelowoff TRAP-TYPE
   ENTERPRISE enatel
   DESCRIPTION
      "INFORMATION:Inverter Alarm: Output Voltage Low has returned to normal"
   --#TYPE "SM32 Trap"
   --#SUMMARY "Inverter Alarm: Output Voltage Low Normal"
   --#ARGUMENTS { }
   --#SEVERITY INFORMATIONAL
   --#TIMEINDEX 1
   --#HELP ""
   --#HELPTAG 0
   --#STATE OPERATIONAL
   ::= 157

inverternegativepowerprotectionon TRAP-TYPE
   ENTERPRISE enatel
   DESCRIPTION
      "INFORMATION: Inverter Alarm: Negative Power Protection"
   --#TYPE "SM32 Trap"
   --#SUMMARY "Inverter Alarm: Negative Power Protection Active"
   --#ARGUMENTS { }
   --#SEVERITY CRITICAL
   --#TIMEINDEX 1
   --#HELP ""
   --#HELPTAG 0
   --#STATE OPERATIONAL
   ::= 158

inverternegativepowerprotectionoff TRAP-TYPE
   ENTERPRISE enatel
   DESCRIPTION
      "INFORMATION:Inverter Alarm: Negative Power Protection has returned to normal"
   --#TYPE "SM32 Trap"
   --#SUMMARY "Inverter Alarm: Negative Power Protection Normal"
   --#ARGUMENTS { }
   --#SEVERITY INFORMATIONAL
   --#TIMEINDEX 1
   --#HELP ""
   --#HELPTAG 0
   --#STATE OPERATIONAL
   ::= 159

inverteroutputvoltageabnormalon TRAP-TYPE
   ENTERPRISE enatel
   DESCRIPTION
      "INFORMATION: Inverter Alarm: Output Voltage Abnormal"
   --#TYPE "SM32 Trap"
   --#SUMMARY "Inverter Alarm: Output Voltage Abnormal Active"
   --#ARGUMENTS { }
   --#SEVERITY CRITICAL
   --#TIMEINDEX 1
   --#HELP ""
   --#HELPTAG 0
   --#STATE OPERATIONAL
   ::= 160

inverteroutputvoltageabnormaloff TRAP-TYPE
   ENTERPRISE enatel
   DESCRIPTION
      "INFORMATION:Inverter Alarm: Output Voltage Abnormal has returned to normal"
   --#TYPE "SM32 Trap"
   --#SUMMARY "Inverter Alarm: Output Voltage Abnormal Normal"
   --#ARGUMENTS { }
   --#SEVERITY INFORMATIONAL
   --#TIMEINDEX 1
   --#HELP ""
   --#HELPTAG 0
   --#STATE OPERATIONAL
   ::= 161

 invertersyncpulsefaulton TRAP-TYPE
   ENTERPRISE enatel
   DESCRIPTION
      "INFORMATION: Inverter Alarm: Sync Pulse Fault"
   --#TYPE "SM32 Trap"
   --#SUMMARY "Inverter Alarm: Sync Pulse Fault Active"
   --#ARGUMENTS { }
   --#SEVERITY CRITICAL
   --#TIMEINDEX 1
   --#HELP ""
   --#HELPTAG 0
   --#STATE OPERATIONAL
   ::= 162

invertersyncpulsefaultoff TRAP-TYPE
   ENTERPRISE enatel
   DESCRIPTION
      "INFORMATION:Inverter Alarm: Sync Pulse Fault has returned to normal"
   --#TYPE "SM32 Trap"
   --#SUMMARY "Inverter Alarm: Sync Pulse Fault Normal"
   --#ARGUMENTS { }
   --#SEVERITY INFORMATIONAL
   --#TIMEINDEX 1
   --#HELP ""
   --#HELPTAG 0
   --#STATE OPERATIONAL
   ::= 163

invertershutdownon TRAP-TYPE
   ENTERPRISE enatel
   DESCRIPTION
      "INFORMATION: Inverter Alarm: Shutdown"
   --#TYPE "SM32 Trap"
   --#SUMMARY "Inverter Alarm: Shutdown Active"
   --#ARGUMENTS { }
   --#SEVERITY CRITICAL
   --#TIMEINDEX 1
   --#HELP ""
   --#HELPTAG 0
   --#STATE OPERATIONAL
   ::= 164

invertershutdownoff TRAP-TYPE
   ENTERPRISE enatel
   DESCRIPTION
      "INFORMATION:Inverter Alarm: Shutdown has returned to normal"
   --#TYPE "SM32 Trap"
   --#SUMMARY "Inverter Alarm: Shutdown Normal"
   --#ARGUMENTS { }
   --#SEVERITY INFORMATIONAL
   --#TIMEINDEX 1
   --#HELP ""
   --#HELPTAG 0
   --#STATE OPERATIONAL
   ::= 165

invertereepromfailon TRAP-TYPE
   ENTERPRISE enatel
   DESCRIPTION
      "INFORMATION: Inverter Alarm: EEPROM Fail"
   --#TYPE "SM32 Trap"
   --#SUMMARY "Inverter Alarm: EEPROM Fail Active"
   --#ARGUMENTS { }
   --#SEVERITY CRITICAL
   --#TIMEINDEX 1
   --#HELP ""
   --#HELPTAG 0
   --#STATE OPERATIONAL
   ::= 166

invertereepromfailoff TRAP-TYPE
   ENTERPRISE enatel
   DESCRIPTION
      "INFORMATION:Inverter Alarm: EEPROM Fail has returned to normal"
   --#TYPE "SM32 Trap"
   --#SUMMARY "Inverter Alarm: EEPROM Fail Normal"
   --#ARGUMENTS { }
   --#SEVERITY INFORMATIONAL
   --#TIMEINDEX 1
   --#HELP ""
   --#HELPTAG 0
   --#STATE OPERATIONAL
   ::= 167

invertersoftstartfailon TRAP-TYPE
   ENTERPRISE enatel
   DESCRIPTION
      "INFORMATION: Inverter Alarm: Soft Start Fail"
   --#TYPE "SM32 Trap"
   --#SUMMARY "Inverter Alarm: Soft Start Fail Active"
   --#ARGUMENTS { }
   --#SEVERITY CRITICAL
   --#TIMEINDEX 1
   --#HELP ""
   --#HELPTAG 0
   --#STATE OPERATIONAL
   ::= 168

invertersoftstartfailoff TRAP-TYPE
   ENTERPRISE enatel
   DESCRIPTION
      "INFORMATION:Inverter Alarm: Soft Start Fail has returned to normal"
   --#TYPE "SM32 Trap"
   --#SUMMARY "Inverter Alarm: Soft Start Fail Normal"
   --#ARGUMENTS { }
   --#SEVERITY INFORMATIONAL
   --#TIMEINDEX 1
   --#HELP ""
   --#HELPTAG 0
   --#STATE OPERATIONAL
   ::= 169

nonurgentrectfailon TRAP-TYPE
   ENTERPRISE enatel
   DESCRIPTION
      "INFORMATION: Non-urgent Rectifier Fail"
   --#TYPE "SM32 Trap"
   --#SUMMARY "Non-urgent Rectifier Fail Active"
   --#ARGUMENTS { }
   --#SEVERITY CRITICAL
   --#TIMEINDEX 1
   --#HELP ""
   --#HELPTAG 0
   --#STATE OPERATIONAL
   ::= 170

nonurgentrectfailoff TRAP-TYPE
   ENTERPRISE enatel
   DESCRIPTION
      "INFORMATION:Non-urgent Rectifier Fail has returned to normal"
   --#TYPE "SM32 Trap"
   --#SUMMARY "Non-urgent Rectifier Fail Normal"
   --#ARGUMENTS { }
   --#SEVERITY INFORMATIONAL
   --#TIMEINDEX 1
   --#HELP ""
   --#HELPTAG 0
   --#STATE OPERATIONAL
   ::= 171

urgentrectfailon TRAP-TYPE
   ENTERPRISE enatel
   DESCRIPTION
      "INFORMATION: Urgent Rectifier Fail"
   --#TYPE "SM32 Trap"
   --#SUMMARY "Urgent Rectifier Fail Active"
   --#ARGUMENTS { }
   --#SEVERITY CRITICAL
   --#TIMEINDEX 1
   --#HELP ""
   --#HELPTAG 0
   --#STATE OPERATIONAL
   ::= 172

urgentrectfailoff TRAP-TYPE
   ENTERPRISE enatel
   DESCRIPTION
      "INFORMATION:Urgent Rectifier Fail has returned to normal"
   --#TYPE "SM32 Trap"
   --#SUMMARY "Urgent Rectifier Fail Normal"
   --#ARGUMENTS { }
   --#SEVERITY INFORMATIONAL
   --#TIMEINDEX 1
   --#HELP ""
   --#HELPTAG 0
   --#STATE OPERATIONAL
   ::= 173

allrectfailon TRAP-TYPE
   ENTERPRISE enatel
   DESCRIPTION
      "INFORMATION: All Rectifiers Failed"
   --#TYPE "SM32 Trap"
   --#SUMMARY "All Rectifiers Failed Active"
   --#ARGUMENTS { }
   --#SEVERITY CRITICAL
   --#TIMEINDEX 1
   --#HELP ""
   --#HELPTAG 0
   --#STATE OPERATIONAL
   ::= 174

allrectfailoff TRAP-TYPE
   ENTERPRISE enatel
   DESCRIPTION
      "INFORMATION:All Rectifiers Failed has returned to normal"
   --#TYPE "SM32 Trap"
   --#SUMMARY "All Rectifiers Failed Normal"
   --#ARGUMENTS { }
   --#SEVERITY INFORMATIONAL
   --#TIMEINDEX 1
   --#HELP ""
   --#HELPTAG 0
   --#STATE OPERATIONAL
   ::= 175

recturgcommsfailon TRAP-TYPE
   ENTERPRISE enatel
   DESCRIPTION
      "INFORMATION: Rectifier Urgent Communication Fail (many fails)"
   --#TYPE "SM32 Trap"
   --#SUMMARY "Rectifier Communication Fail Active"
   --#ARGUMENTS { }
   --#SEVERITY CRITICAL
   --#TIMEINDEX 1
   --#HELP ""
   --#HELPTAG 0
   --#STATE OPERATIONAL
   ::= 176

recturgcommsfailoff TRAP-TYPE
   ENTERPRISE enatel
   DESCRIPTION
      "INFORMATION:Rectifier Urgent Communication Fail (many fails) has returned to normal"
   --#TYPE "SM32 Trap"
   --#SUMMARY "Rectifier Communication Fail Normal"
   --#ARGUMENTS { }
   --#SEVERITY INFORMATIONAL
   --#TIMEINDEX 1
   --#HELP ""
   --#HELPTAG 0
   --#STATE OPERATIONAL
   ::= 177

rectnonurgentcommsfailon TRAP-TYPE
   ENTERPRISE enatel
   DESCRIPTION
      "INFORMATION: Rectifier Non Urgent Communication Fail (some fails)"
   --#TYPE "SM32 Trap"
   --#SUMMARY "Rectifier Non Urgent Communication Fail (some fails) Active"
   --#ARGUMENTS { }
   --#SEVERITY CRITICAL
   --#TIMEINDEX 1
   --#HELP ""
   --#HELPTAG 0
   --#STATE OPERATIONAL
   ::= 178

rectnonurgentcommsfailoff TRAP-TYPE
   ENTERPRISE enatel
   DESCRIPTION
      "INFORMATION: Rectifier Non Urgent Communication Fail (some fails) has returned to normal"
   --#TYPE "SM32 Trap"
   --#SUMMARY "Rectifier Non Urgent Communication Fail (some fails) Normal"
   --#ARGUMENTS { }
   --#SEVERITY INFORMATIONAL
   --#TIMEINDEX 1
   --#HELP ""
   --#HELPTAG 0
   --#STATE OPERATIONAL
   ::= 179


nonurgentconvfailon TRAP-TYPE
   ENTERPRISE enatel
   DESCRIPTION
      "INFORMATION: Non-urgent Converter Fail"
   --#TYPE "SM32 Trap"
   --#SUMMARY "Non-urgent Converter Fail Active"
   --#ARGUMENTS { }
   --#SEVERITY CRITICAL
   --#TIMEINDEX 1
   --#HELP ""
   --#HELPTAG 0
   --#STATE OPERATIONAL
   ::= 180

nonurgentconvfailoff TRAP-TYPE
   ENTERPRISE enatel
   DESCRIPTION
      "INFORMATION:Non-urgent Converter Fail has returned to normal"
   --#TYPE "SM32 Trap"
   --#SUMMARY "Non-urgent Converter Fail Normal"
   --#ARGUMENTS { }
   --#SEVERITY INFORMATIONAL
   --#TIMEINDEX 1
   --#HELP ""
   --#HELPTAG 0
   --#STATE OPERATIONAL
   ::= 181

 urgentconvfailon TRAP-TYPE
   ENTERPRISE enatel
   DESCRIPTION
      "INFORMATION: Urgent Converter Fail"
   --#TYPE "SM32 Trap"
   --#SUMMARY "Urgent Converter Fail Active"
   --#ARGUMENTS { }
   --#SEVERITY CRITICAL
   --#TIMEINDEX 1
   --#HELP ""
   --#HELPTAG 0
   --#STATE OPERATIONAL
   ::= 182

urgentconvfailoff TRAP-TYPE
   ENTERPRISE enatel
   DESCRIPTION
      "INFORMATION:Urgent Converter Fail has returned to normal"
   --#TYPE "SM32 Trap"
   --#SUMMARY "Urgent Converter Fail Normal"
   --#ARGUMENTS { }
   --#SEVERITY INFORMATIONAL
   --#TIMEINDEX 1
   --#HELP ""
   --#HELPTAG 0
   --#STATE OPERATIONAL
   ::= 183

allconvfailon TRAP-TYPE
   ENTERPRISE enatel
   DESCRIPTION
      "INFORMATION: All Converters Failed"
   --#TYPE "SM32 Trap"
   --#SUMMARY "All Converters Failed Active"
   --#ARGUMENTS { }
   --#SEVERITY CRITICAL
   --#TIMEINDEX 1
   --#HELP ""
   --#HELPTAG 0
   --#STATE OPERATIONAL
   ::= 184

allconvfailoff TRAP-TYPE
   ENTERPRISE enatel
   DESCRIPTION
      "INFORMATION:All Converters Failed has returned to normal"
   --#TYPE "SM32 Trap"
   --#SUMMARY "All Converters Failed Normal"
   --#ARGUMENTS { }
   --#SEVERITY INFORMATIONAL
   --#TIMEINDEX 1
   --#HELP ""
   --#HELPTAG 0
   --#STATE OPERATIONAL
   ::= 185

convcommsfailon TRAP-TYPE
   ENTERPRISE enatel
   DESCRIPTION
      "INFORMATION: Converter Communication Fail"
   --#TYPE "SM32 Trap"
   --#SUMMARY "Converter Communication Fail Active"
   --#ARGUMENTS { }
   --#SEVERITY CRITICAL
   --#TIMEINDEX 1
   --#HELP ""
   --#HELPTAG 0
   --#STATE OPERATIONAL
   ::= 186

convcommsfailoff TRAP-TYPE
   ENTERPRISE enatel
   DESCRIPTION
      "INFORMATION:Converter Communication Fail has returned to normal"
   --#TYPE "SM32 Trap"
   --#SUMMARY "Converter Communication Fail Normal"
   --#ARGUMENTS { }
   --#SEVERITY INFORMATIONAL
   --#TIMEINDEX 1
   --#HELP ""
   --#HELPTAG 0
   --#STATE OPERATIONAL
   ::= 187


 nonurgentinvfailon TRAP-TYPE
   ENTERPRISE enatel
   DESCRIPTION
      "INFORMATION: Non-urgent Inverter Fail"
   --#TYPE "SM32 Trap"
   --#SUMMARY "Non-urgent Inverter Fail Active"
   --#ARGUMENTS { }
   --#SEVERITY CRITICAL
   --#TIMEINDEX 1
   --#HELP ""
   --#HELPTAG 0
   --#STATE OPERATIONAL
   ::= 190

nonurgentinvfailoff TRAP-TYPE
   ENTERPRISE enatel
   DESCRIPTION
      "INFORMATION:Non-urgent Inverter Fail has returned to normal"
   --#TYPE "SM32 Trap"
   --#SUMMARY "Non-urgent Inverter Fail Normal"
   --#ARGUMENTS { }
   --#SEVERITY INFORMATIONAL
   --#TIMEINDEX 1
   --#HELP ""
   --#HELPTAG 0
   --#STATE OPERATIONAL
   ::= 191

urgentinvfailon TRAP-TYPE
   ENTERPRISE enatel
   DESCRIPTION
      "INFORMATION: Urgent Inverter Fail"
   --#TYPE "SM32 Trap"
   --#SUMMARY "Urgent Inverter Fail Active"
   --#ARGUMENTS { }
   --#SEVERITY CRITICAL
   --#TIMEINDEX 1
   --#HELP ""
   --#HELPTAG 0
   --#STATE OPERATIONAL
   ::= 192

urgentinvfailoff TRAP-TYPE
   ENTERPRISE enatel
   DESCRIPTION
      "INFORMATION: Urgent Inverter Fail has returned to normal"
   --#TYPE "SM32 Trap"
   --#SUMMARY "Urgent Inverter Fail Normal"
   --#ARGUMENTS { }
   --#SEVERITY INFORMATIONAL
   --#TIMEINDEX 1
   --#HELP ""
   --#HELPTAG 0
   --#STATE OPERATIONAL
   ::= 193

allinvfailon TRAP-TYPE
   ENTERPRISE enatel
   DESCRIPTION
      "INFORMATION: All Inverters Failed"
   --#TYPE "SM32 Trap"
   --#SUMMARY "All Inverters Failed Active"
   --#ARGUMENTS { }
   --#SEVERITY CRITICAL
   --#TIMEINDEX 1
   --#HELP ""
   --#HELPTAG 0
   --#STATE OPERATIONAL
   ::= 194

allinvfailoff TRAP-TYPE
   ENTERPRISE enatel
   DESCRIPTION
      "INFORMATION: All Inverters Failed has returned to normal"
   --#TYPE "SM32 Trap"
   --#SUMMARY "All Inverters Failed Normal"
   --#ARGUMENTS { }
   --#SEVERITY INFORMATIONAL
   --#TIMEINDEX 1
   --#HELP ""
   --#HELPTAG 0
   --#STATE OPERATIONAL
   ::= 195

invcommsfailon TRAP-TYPE
   ENTERPRISE enatel
   DESCRIPTION
      "INFORMATION: Inverter Communication Fail"
   --#TYPE "SM32 Trap"
   --#SUMMARY "Inverter Communication Fail Active"
   --#ARGUMENTS { }
   --#SEVERITY CRITICAL
   --#TIMEINDEX 1
   --#HELP ""
   --#HELPTAG 0
   --#STATE OPERATIONAL
   ::= 196

invcommsfailoff TRAP-TYPE
   ENTERPRISE enatel
   DESCRIPTION
      "INFORMATION: Inverter Communication Fail has returned to normal"
   --#TYPE "SM32 Trap"
   --#SUMMARY "Inverter Communication Fail Normal"
   --#ARGUMENTS { }
   --#SEVERITY INFORMATIONAL
   --#TIMEINDEX 1
   --#HELP ""
   --#HELPTAG 0
   --#STATE OPERATIONAL
   ::= 197

urgentlowvoltsbus1on TRAP-TYPE
   ENTERPRISE enatel
   DESCRIPTION
      "INFORMATION: Low Voltage Bus 1"
   --#TYPE "SM32 Trap"
   --#SUMMARY "Low Voltage Bus 1 Active"
   --#ARGUMENTS { }
   --#SEVERITY CRITICAL
   --#TIMEINDEX 1
   --#HELP ""
   --#HELPTAG 0
   --#STATE OPERATIONAL
   ::= 202

urgentlowvoltsbus1off TRAP-TYPE
   ENTERPRISE enatel
   DESCRIPTION
      "INFORMATION: Low Voltage Bus 1 has returned to normal"
   --#TYPE "SM32 Trap"
   --#SUMMARY "Low Voltage Bus 1 Normal"
   --#ARGUMENTS { }
   --#SEVERITY INFORMATIONAL
   --#TIMEINDEX 1
   --#HELP ""
   --#HELPTAG 0
   --#STATE OPERATIONAL
   ::= 203

urgentlowfloatbus1on TRAP-TYPE
   ENTERPRISE enatel
   DESCRIPTION
      "INFORMATION: Low Float Bus 1"
   --#TYPE "SM32 Trap"
   --#SUMMARY "Low Float Bus 1 Active"
   --#ARGUMENTS { }
   --#SEVERITY CRITICAL
   --#TIMEINDEX 1
   --#HELP ""
   --#HELPTAG 0
   --#STATE OPERATIONAL
   ::= 204

urgentlowfloatbus1off TRAP-TYPE
   ENTERPRISE enatel
   DESCRIPTION
      "INFORMATION: Low Float Bus 1 has returned to normal"
   --#TYPE "SM32 Trap"
   --#SUMMARY "Low Float Bus 1 Normal"
   --#ARGUMENTS { }
   --#SEVERITY INFORMATIONAL
   --#TIMEINDEX 1
   --#HELP ""
   --#HELPTAG 0
   --#STATE OPERATIONAL
   ::= 205

urgenthighvoltsbus1on TRAP-TYPE
   ENTERPRISE enatel
   DESCRIPTION
      "INFORMATION: High Volt Bus 1"
   --#TYPE "SM32 Trap"
   --#SUMMARY "High Volt Bus 1 Active"
   --#ARGUMENTS { }
   --#SEVERITY CRITICAL
   --#TIMEINDEX 1
   --#HELP ""
   --#HELPTAG 0
   --#STATE OPERATIONAL
   ::= 206

urgenthighvoltsbus1off TRAP-TYPE
   ENTERPRISE enatel
   DESCRIPTION
      "INFORMATION: High Volt Bus 1 has returned to normal"
   --#TYPE "SM32 Trap"
   --#SUMMARY "High Volt Bus 1 Normal"
   --#ARGUMENTS { }
   --#SEVERITY INFORMATIONAL
   --#TIMEINDEX 1
   --#HELP ""
   --#HELPTAG 0
   --#STATE OPERATIONAL
   ::= 207


urgenthighfloatbus1on TRAP-TYPE
   ENTERPRISE enatel
   DESCRIPTION
      "INFORMATION: High Float Bus 1"
   --#TYPE "SM32 Trap"
   --#SUMMARY "High Float Bus 1 Active"
   --#ARGUMENTS { }
   --#SEVERITY CRITICAL
   --#TIMEINDEX 1
   --#HELP ""
   --#HELPTAG 0
   --#STATE OPERATIONAL
   ::= 208

urgenthighfloatbus1off TRAP-TYPE
   ENTERPRISE enatel
   DESCRIPTION
      "INFORMATION: High Float Bus 1 has returned to normal"
   --#TYPE "SM32 Trap"
   --#SUMMARY "High Float Bus 1 Normal"
   --#ARGUMENTS { }
   --#SEVERITY INFORMATIONAL
   --#TIMEINDEX 1
   --#HELP ""
   --#HELPTAG 0
   --#STATE OPERATIONAL
   ::= 209

urgentlowvoltsbus2on TRAP-TYPE
   ENTERPRISE enatel
   DESCRIPTION
      "INFORMATION: Low Voltage Bus 2"
   --#TYPE "SM32 Trap"
   --#SUMMARY "Low Voltage Bus 2 Active"
   --#ARGUMENTS { }
   --#SEVERITY CRITICAL
   --#TIMEINDEX 1
   --#HELP ""
   --#HELPTAG 0
   --#STATE OPERATIONAL
   ::= 210

urgentlowvoltsbus2off TRAP-TYPE
   ENTERPRISE enatel
   DESCRIPTION
      "INFORMATION: Low Voltage Bus 2 has returned to normal"
   --#TYPE "SM32 Trap"
   --#SUMMARY "Low Voltage Bus 2 Normal"
   --#ARGUMENTS { }
   --#SEVERITY INFORMATIONAL
   --#TIMEINDEX 1
   --#HELP ""
   --#HELPTAG 0
   --#STATE OPERATIONAL
   ::= 211

urgentlowfloatbus2on TRAP-TYPE
   ENTERPRISE enatel
   DESCRIPTION
      "INFORMATION: Low Float Bus 2"
   --#TYPE "SM32 Trap"
   --#SUMMARY "Low Float Bus 2 Active"
   --#ARGUMENTS { }
   --#SEVERITY CRITICAL
   --#TIMEINDEX 1
   --#HELP ""
   --#HELPTAG 0
   --#STATE OPERATIONAL
   ::= 212

urgentlowfloatbus2off TRAP-TYPE
   ENTERPRISE enatel
   DESCRIPTION
      "INFORMATION: Low Float Bus 2 has returned to normal"
   --#TYPE "SM32 Trap"
   --#SUMMARY "Low Float Bus 2 Normal"
   --#ARGUMENTS { }
   --#SEVERITY INFORMATIONAL
   --#TIMEINDEX 1
   --#HELP ""
   --#HELPTAG 0
   --#STATE OPERATIONAL
   ::= 213

urgenthighvoltsbus2on TRAP-TYPE
   ENTERPRISE enatel
   DESCRIPTION
      "INFORMATION: High Voltage Bus 2"
   --#TYPE "SM32 Trap"
   --#SUMMARY "High Voltage Bus 2 Active"
   --#ARGUMENTS { }
   --#SEVERITY CRITICAL
   --#TIMEINDEX 1
   --#HELP ""
   --#HELPTAG 0
   --#STATE OPERATIONAL
   ::= 214

urgenthighvoltsbus2off TRAP-TYPE
   ENTERPRISE enatel
   DESCRIPTION
      "INFORMATION: High Voltage Bus 2 has returned to normal"
   --#TYPE "SM32 Trap"
   --#SUMMARY "High Voltage Bus 2 Normal"
   --#ARGUMENTS { }
   --#SEVERITY INFORMATIONAL
   --#TIMEINDEX 1
   --#HELP ""
   --#HELPTAG 0
   --#STATE OPERATIONAL
   ::= 215

urgenthighfloatbus2on TRAP-TYPE
   ENTERPRISE enatel
   DESCRIPTION
      "INFORMATION: High Float Bus 2"
   --#TYPE "SM32 Trap"
   --#SUMMARY "High Float Bus 2 Active"
   --#ARGUMENTS { }
   --#SEVERITY CRITICAL
   --#TIMEINDEX 1
   --#HELP ""
   --#HELPTAG 0
   --#STATE OPERATIONAL
   ::= 216

urgenthighfloatbus2off TRAP-TYPE
   ENTERPRISE enatel
   DESCRIPTION
      "INFORMATION: High Float Bus 2 has returned to normal"
   --#TYPE "SM32 Trap"
   --#SUMMARY "High Float Bus 2 Normal"
   --#ARGUMENTS { }
   --#SEVERITY INFORMATIONAL
   --#TIMEINDEX 1
   --#HELP ""
   --#HELPTAG 0
   --#STATE OPERATIONAL
   ::= 217

lvd1operateon TRAP-TYPE
   ENTERPRISE enatel
   DESCRIPTION
      "INFORMATION: LVD 1 Operate"
   --#TYPE "SM32 Trap"
   --#SUMMARY "LVD 1 Operate Active"
   --#ARGUMENTS { }
   --#SEVERITY CRITICAL
   --#TIMEINDEX 1
   --#HELP ""
   --#HELPTAG 0
   --#STATE OPERATIONAL
   ::= 218

lvd1operateoff TRAP-TYPE
   ENTERPRISE enatel
   DESCRIPTION
      "INFORMATION: LVD 1 Operate has returned to normal"
   --#TYPE "SM32 Trap"
   --#SUMMARY "LVD 1 Operate Normal"
   --#ARGUMENTS { }
   --#SEVERITY INFORMATIONAL
   --#TIMEINDEX 1
   --#HELP ""
   --#HELPTAG 0
   --#STATE OPERATIONAL
   ::= 219

lvd2operateon TRAP-TYPE
   ENTERPRISE enatel
   DESCRIPTION
      "INFORMATION: LVD 2 Operate"
   --#TYPE "SM32 Trap"
   --#SUMMARY "LVD 2 Operate Active"
   --#ARGUMENTS { }
   --#SEVERITY CRITICAL
   --#TIMEINDEX 1
   --#HELP ""
   --#HELPTAG 0
   --#STATE OPERATIONAL
   ::= 220

lvd2operateoff TRAP-TYPE
   ENTERPRISE enatel
   DESCRIPTION
      "INFORMATION: LVD 2 Operate has returned to normal"
   --#TYPE "SM32 Trap"
   --#SUMMARY "LVD 2 Operate Normal"
   --#ARGUMENTS { }
   --#SEVERITY INFORMATIONAL
   --#TIMEINDEX 1
   --#HELP ""
   --#HELPTAG 0
   --#STATE OPERATIONAL
   ::= 221

batterysymmetryon TRAP-TYPE
   ENTERPRISE enatel
   DESCRIPTION
      "INFORMATION: Battery Voltage Symmetry"
   --#TYPE "SM32 Trap"
   --#SUMMARY "Battery Voltage Symmetry Active"
   --#ARGUMENTS { }
   --#SEVERITY CRITICAL
   --#TIMEINDEX 1
   --#HELP ""
   --#HELPTAG 0
   --#STATE OPERATIONAL
   ::= 222

batterysymmetryoff TRAP-TYPE
   ENTERPRISE enatel
   DESCRIPTION
      "INFORMATION: Battery Voltage Symmetry has returned to normal"
   --#TYPE "SM32 Trap"
   --#SUMMARY "Battery Voltage Symmetry Normal"
   --#ARGUMENTS { }
   --#SEVERITY INFORMATIONAL
   --#TIMEINDEX 1
   --#HELP ""
   --#HELPTAG 0
   --#STATE OPERATIONAL
   ::= 223


lvd3operateon TRAP-TYPE
   ENTERPRISE enatel
   DESCRIPTION
      "INFORMATION: LVD 3 Operate"
   --#TYPE "SM32 Trap"
   --#SUMMARY "LVD 3 Operate Active"
   --#ARGUMENTS { }
   --#SEVERITY CRITICAL
   --#TIMEINDEX 1
   --#HELP ""
   --#HELPTAG 0
   --#STATE OPERATIONAL
   ::= 224

lvd3operateoff TRAP-TYPE
   ENTERPRISE enatel
   DESCRIPTION
      "INFORMATION: LVD 3 Operate has returned to normal"
   --#TYPE "SM32 Trap"
   --#SUMMARY "LVD 3 Operate Normal"
   --#ARGUMENTS { }
   --#SEVERITY INFORMATIONAL
   --#TIMEINDEX 1
   --#HELP ""
   --#HELPTAG 0
   --#STATE OPERATIONAL
   ::= 225

loadcurrenthighon TRAP-TYPE
   ENTERPRISE enatel
   DESCRIPTION
      "INFORMATION: Load Current High"
   --#TYPE "SM32 Trap"
   --#SUMMARY "Load Current High Active"
   --#ARGUMENTS { }
   --#SEVERITY CRITICAL
   --#TIMEINDEX 1
   --#HELP ""
   --#HELPTAG 0
   --#STATE OPERATIONAL
   ::= 234

loadcurrenthighoff TRAP-TYPE
   ENTERPRISE enatel
   DESCRIPTION
      "INFORMATION: Load Current High has returned to normal"
   --#TYPE "SM32 Trap"
   --#SUMMARY "Load Current High Normal"
   --#ARGUMENTS { }
   --#SEVERITY INFORMATIONAL
   --#TIMEINDEX 1
   --#HELP ""
   --#HELPTAG 0
   --#STATE OPERATIONAL
   ::= 235

indloadcurrenthighon TRAP-TYPE
   ENTERPRISE enatel
   DESCRIPTION
      "INFORMATION: Individual Load Current High"
   --#TYPE "SM32 Trap"
   --#SUMMARY "Individual Load Current High Active"
   --#ARGUMENTS { }
   --#SEVERITY CRITICAL
   --#TIMEINDEX 1
   --#HELP ""
   --#HELPTAG 0
   --#STATE OPERATIONAL
   ::= 236

indloadcurrenthighoff TRAP-TYPE
   ENTERPRISE enatel
   DESCRIPTION
      "INFORMATION: Individual Load Current High has returned to normal"
   --#TYPE "SM32 Trap"
   --#SUMMARY "Individual Load Current High Normal"
   --#ARGUMENTS { }
   --#SEVERITY INFORMATIONAL
   --#TIMEINDEX 1
   --#HELP ""
   --#HELPTAG 0
   --#STATE OPERATIONAL
   ::= 237

batterycurrenthighon TRAP-TYPE
   ENTERPRISE enatel
   DESCRIPTION
      "INFORMATION: Battery Current High"
   --#TYPE "SM32 Trap"
   --#SUMMARY "Battery Current High Active"
   --#ARGUMENTS { }
   --#SEVERITY CRITICAL
   --#TIMEINDEX 1
   --#HELP ""
   --#HELPTAG 0
   --#STATE OPERATIONAL
   ::= 238

batterycurrenthighoff TRAP-TYPE
   ENTERPRISE enatel
   DESCRIPTION
      "INFORMATION: Battery Current High has returned to normal"
   --#TYPE "SM32 Trap"
   --#SUMMARY "Battery Current High Normal"
   --#ARGUMENTS { }
   --#SEVERITY INFORMATIONAL
   --#TIMEINDEX 1
   --#HELP ""
   --#HELPTAG 0
   --#STATE OPERATIONAL
   ::= 239

batterystringcurrenthighon TRAP-TYPE
   ENTERPRISE enatel
   DESCRIPTION
      "INFORMATION: Battery String Current High"
   --#TYPE "SM32 Trap"
   --#SUMMARY "Battery String Current High Active"
   --#ARGUMENTS { }
   --#SEVERITY CRITICAL
   --#TIMEINDEX 1
   --#HELP ""
   --#HELPTAG 0
   --#STATE OPERATIONAL
   ::= 240

batterystringcurrenthighoff TRAP-TYPE
   ENTERPRISE enatel
   DESCRIPTION
      "INFORMATION: Battery String Current High has returned to normal"
   --#TYPE "SM32 Trap"
   --#SUMMARY "Battery String Current High Normal"
   --#ARGUMENTS { }
   --#SEVERITY INFORMATIONAL
   --#TIMEINDEX 1
   --#HELP ""
   --#HELPTAG 0
   --#STATE OPERATIONAL
   ::= 241

batterystringimbalanceon TRAP-TYPE
   ENTERPRISE enatel
   DESCRIPTION
      "INFORMATION: Battery String Imbalance"
   --#TYPE "SM32 Trap"
   --#SUMMARY "Battery String Imbalance Active"
   --#ARGUMENTS { }
   --#SEVERITY CRITICAL
   --#TIMEINDEX 1
   --#HELP ""
   --#HELPTAG 0
   --#STATE OPERATIONAL
   ::= 242

batterystringimbalanceoff TRAP-TYPE
   ENTERPRISE enatel
   DESCRIPTION
      "INFORMATION: Battery String Imbalance has returned to normal"
   --#TYPE "SM32 Trap"
   --#SUMMARY "Battery String Imbalance Normal"
   --#ARGUMENTS { }
   --#SEVERITY INFORMATIONAL
   --#TIMEINDEX 1
   --#HELP ""
   --#HELPTAG 0
   --#STATE OPERATIONAL
   ::= 243

batterystringopenon TRAP-TYPE
   ENTERPRISE enatel
   DESCRIPTION
      "INFORMATION: Battery String Open"
   --#TYPE "SM32 Trap"
   --#SUMMARY "Battery String Open Active"
   --#ARGUMENTS { }
   --#SEVERITY CRITICAL
   --#TIMEINDEX 1
   --#HELP ""
   --#HELPTAG 0
   --#STATE OPERATIONAL
   ::= 244

batterystringopenoff TRAP-TYPE
   ENTERPRISE enatel
   DESCRIPTION
      "INFORMATION: Battery String Open has returned to normal"
   --#TYPE "SM32 Trap"
   --#SUMMARY "Battery String Open Normal"
   --#ARGUMENTS { }
   --#SEVERITY INFORMATIONAL
   --#TIMEINDEX 1
   --#HELP ""
   --#HELPTAG 0
   --#STATE OPERATIONAL
   ::= 245

batterytemplowon TRAP-TYPE
   ENTERPRISE enatel
   DESCRIPTION
      "INFORMATION: Battery Temperature Low"
   --#TYPE "SM32 Trap"
   --#SUMMARY "Battery Temperature Low Active"
   --#ARGUMENTS { }
   --#SEVERITY CRITICAL
   --#TIMEINDEX 1
   --#HELP ""
   --#HELPTAG 0
   --#STATE OPERATIONAL
   ::= 246

batterytemplowoff TRAP-TYPE
   ENTERPRISE enatel
   DESCRIPTION
      "INFORMATION: Battery Temperature Low has returned to normal"
   --#TYPE "SM32 Trap"
   --#SUMMARY "Battery Temperature Low Normal"
   --#ARGUMENTS { }
   --#SEVERITY INFORMATIONAL
   --#TIMEINDEX 1
   --#HELP ""
   --#HELPTAG 0
   --#STATE OPERATIONAL
   ::= 247

batterytemphighon TRAP-TYPE
   ENTERPRISE enatel
   DESCRIPTION
      "INFORMATION: Battery Temperature High"
   --#TYPE "SM32 Trap"
   --#SUMMARY "Battery Temperature High Active"
   --#ARGUMENTS { }
   --#SEVERITY CRITICAL
   --#TIMEINDEX 1
   --#HELP ""
   --#HELPTAG 0
   --#STATE OPERATIONAL
   ::= 248

batterytemphighoff TRAP-TYPE
   ENTERPRISE enatel
   DESCRIPTION
      "INFORMATION: Battery Temperature High has returned to normal"
   --#TYPE "SM32 Trap"
   --#SUMMARY "Battery Temperature High Normal"
   --#ARGUMENTS { }
   --#SEVERITY INFORMATIONAL
   --#TIMEINDEX 1
   --#HELP ""
   --#HELPTAG 0
   --#STATE OPERATIONAL
   ::= 249

batterytempfaulton TRAP-TYPE
   ENTERPRISE enatel
   DESCRIPTION
      "INFORMATION: Battery Temperature Fault"
   --#TYPE "SM32 Trap"
   --#SUMMARY "Battery Temperature Fault Active"
   --#ARGUMENTS { }
   --#SEVERITY CRITICAL
   --#TIMEINDEX 1
   --#HELP ""
   --#HELPTAG 0
   --#STATE OPERATIONAL
   ::= 250

batterytempfaultoff TRAP-TYPE
   ENTERPRISE enatel
   DESCRIPTION
      "INFORMATION: Battery Temperature Fault has returned to normal"
   --#TYPE "SM32 Trap"
   --#SUMMARY "Battery Temperature Fault Normal"
   --#ARGUMENTS { }
   --#SEVERITY INFORMATIONAL
   --#TIMEINDEX 1
   --#HELP ""
   --#HELPTAG 0
   --#STATE OPERATIONAL
   ::= 251


ambienttemplowon TRAP-TYPE
   ENTERPRISE enatel
   DESCRIPTION
      "INFORMATION: Ambient Temperature Low"
   --#TYPE "SM32 Trap"
   --#SUMMARY "Ambient Temperature Low Active"
   --#ARGUMENTS { }
   --#SEVERITY CRITICAL
   --#TIMEINDEX 1
   --#HELP ""
   --#HELPTAG 0
   --#STATE OPERATIONAL
   ::= 252

ambienttemplowoff TRAP-TYPE
   ENTERPRISE enatel
   DESCRIPTION
      "INFORMATION: Ambient Temperature Low has returned to normal"
   --#TYPE "SM32 Trap"
   --#SUMMARY "Ambient Temperature Low Normal"
   --#ARGUMENTS { }
   --#SEVERITY INFORMATIONAL
   --#TIMEINDEX 1
   --#HELP ""
   --#HELPTAG 0
   --#STATE OPERATIONAL
   ::= 253

ambienttemphighon TRAP-TYPE
   ENTERPRISE enatel
   DESCRIPTION
      "INFORMATION: Ambient Temperature High"
   --#TYPE "SM32 Trap"
   --#SUMMARY "Ambient Temperature High Active"
   --#ARGUMENTS { }
   --#SEVERITY CRITICAL
   --#TIMEINDEX 1
   --#HELP ""
   --#HELPTAG 0
   --#STATE OPERATIONAL
   ::= 254

ambienttemphighoff TRAP-TYPE
   ENTERPRISE enatel
   DESCRIPTION
      "INFORMATION: Ambient Temperature High has returned to normal"
   --#TYPE "SM32 Trap"
   --#SUMMARY "Ambient Temperature High Normal"
   --#ARGUMENTS { }
   --#SEVERITY INFORMATIONAL
   --#TIMEINDEX 1
   --#HELP ""
   --#HELPTAG 0
   --#STATE OPERATIONAL
   ::= 255

ambienttempfaulton TRAP-TYPE
   ENTERPRISE enatel
   DESCRIPTION
      "INFORMATION: Ambient Temperature Fault"
   --#TYPE "SM32 Trap"
   --#SUMMARY "Ambient Temperature Fault Active"
   --#ARGUMENTS { }
   --#SEVERITY CRITICAL
   --#TIMEINDEX 1
   --#HELP ""
   --#HELPTAG 0
   --#STATE OPERATIONAL
   ::= 256

ambienttempfaultoff TRAP-TYPE
   ENTERPRISE enatel
   DESCRIPTION
      "INFORMATION:Ambient Temperature Fault has returned to normal"
   --#TYPE "SM32 Trap"
   --#SUMMARY "Ambient Temperature Fault Normal"
   --#ARGUMENTS { }
   --#SEVERITY INFORMATIONAL
   --#TIMEINDEX 1
   --#HELP ""
   --#HELPTAG 0
   --#STATE OPERATIONAL
   ::= 257

mcb1openon TRAP-TYPE
   ENTERPRISE enatel
   DESCRIPTION
      "INFORMATION: MCB 1 Open Fault"
   --#TYPE "SM32 Trap"
   --#SUMMARY "MCB 1 Open"
   --#ARGUMENTS { }
   --#SEVERITY CRITICAL
   --#TIMEINDEX 1
   --#HELP ""
   --#HELPTAG 0
   --#STATE OPERATIONAL
   ::= 258

mcb1openff TRAP-TYPE
   ENTERPRISE enatel
   DESCRIPTION
      "INFORMATION: MCB 1 Open Fault has returned to normal"
   --#TYPE "SM32 Trap"
   --#SUMMARY "MCB 1 Closed"
   --#ARGUMENTS { }
   --#SEVERITY INFORMATIONAL
   --#TIMEINDEX 1
   --#HELP ""
   --#HELPTAG 0
   --#STATE OPERATIONAL
   ::= 259


mcb2openon TRAP-TYPE
   ENTERPRISE enatel
   DESCRIPTION
      "INFORMATION: MCB 2 Open Fault"
   --#TYPE "SM32 Trap"
   --#SUMMARY "MCB 2 Open"
   --#ARGUMENTS { }
   --#SEVERITY CRITICAL
   --#TIMEINDEX 1
   --#HELP ""
   --#HELPTAG 0
   --#STATE OPERATIONAL
   ::= 260

mcb2openff TRAP-TYPE
   ENTERPRISE enatel
   DESCRIPTION
      "INFORMATION: MCB 2 Open Fault has returned to normal"
   --#TYPE "SM32 Trap"
   --#SUMMARY "MCB 2 Closed"
   --#ARGUMENTS { }
   --#SEVERITY INFORMATIONAL
   --#TIMEINDEX 1
   --#HELP ""
   --#HELPTAG 0
   --#STATE OPERATIONAL
   ::= 261

mcb3openon TRAP-TYPE
   ENTERPRISE enatel
   DESCRIPTION
      "INFORMATION: MCB 3 Open Fault"
   --#TYPE "SM32 Trap"
   --#SUMMARY "MCB 3 Open"
   --#ARGUMENTS { }
   --#SEVERITY CRITICAL
   --#TIMEINDEX 1
   --#HELP ""
   --#HELPTAG 0
   --#STATE OPERATIONAL
   ::= 262

mcb3openff TRAP-TYPE
   ENTERPRISE enatel
   DESCRIPTION
      "INFORMATION: MCB 3 Open Fault has returned to normal"
   --#TYPE "SM32 Trap"
   --#SUMMARY "MCB 3 Closed"
   --#ARGUMENTS { }
   --#SEVERITY INFORMATIONAL
   --#TIMEINDEX 1
   --#HELP ""
   --#HELPTAG 0
   --#STATE OPERATIONAL
   ::= 263


mcb4openon TRAP-TYPE
   ENTERPRISE enatel
   DESCRIPTION
      "INFORMATION: MCB 4 Open Fault"
   --#TYPE "SM32 Trap"
   --#SUMMARY "MCB 4 Open"
   --#ARGUMENTS { }
   --#SEVERITY CRITICAL
   --#TIMEINDEX 1
   --#HELP ""
   --#HELPTAG 0
   --#STATE OPERATIONAL
   ::= 264

mcb4openff TRAP-TYPE
   ENTERPRISE enatel
   DESCRIPTION
      "INFORMATION: MCB 4 Open Fault has returned to normal"
   --#TYPE "SM32 Trap"
   --#SUMMARY "MCB 4 Closed"
   --#ARGUMENTS { }
   --#SEVERITY INFORMATIONAL
   --#TIMEINDEX 1
   --#HELP ""
   --#HELPTAG 0
   --#STATE OPERATIONAL
   ::= 265

powersaveon TRAP-TYPE
   ENTERPRISE enatel
   DESCRIPTION
      "INFORMATION: Power Save Active"
   --#TYPE "SM32 Trap"
   --#SUMMARY " Power Save Active"
   --#ARGUMENTS { }
   --#SEVERITY INFORMATIONAL
   --#TIMEINDEX 1
   --#HELP ""
   --#HELPTAG 0
   --#STATE OPERATIONAL
   ::= 266

powersaveoff TRAP-TYPE
   ENTERPRISE enatel
   DESCRIPTION
      "INFORMATION: Power Save OFF"
   --#TYPE "SM32 Trap"
   --#SUMMARY "Power Save OFF"
   --#ARGUMENTS { }
   --#SEVERITY INFORMATIONAL
   --#TIMEINDEX 1
   --#HELP ""
   --#HELPTAG 0
   --#STATE OPERATIONAL
   ::= 267

periodiceqon TRAP-TYPE
   ENTERPRISE enatel
   DESCRIPTION
      "INFORMATION: Periodic Equalise Active"
   --#TYPE "SM32 Trap"
   --#SUMMARY "Periodic Equalise Active"
   --#ARGUMENTS { }
   --#SEVERITY INFORMATIONAL
   --#TIMEINDEX 1
   --#HELP ""
   --#HELPTAG 0
   --#STATE OPERATIONAL
   ::= 268

periodiceqoff TRAP-TYPE
   ENTERPRISE enatel
   DESCRIPTION
      "INFORMATION: Periodic Equalise OFF"
   --#TYPE "SM32 Trap"
   --#SUMMARY "Periodic Equalise OFF"
   --#ARGUMENTS { }
   --#SEVERITY INFORMATIONAL
   --#TIMEINDEX 1
   --#HELP ""
   --#HELPTAG 0
   --#STATE OPERATIONAL
   ::= 269

manualeqon TRAP-TYPE
   ENTERPRISE enatel
   DESCRIPTION
      "INFORMATION: Manual Equalise Active"
   --#TYPE "SM32 Trap"
   --#SUMMARY "Manual Equalise Active"
   --#ARGUMENTS { }
   --#SEVERITY INFORMATIONAL
   --#TIMEINDEX 1
   --#HELP ""
   --#HELPTAG 0
   --#STATE OPERATIONAL
   ::= 270

manualeqoff TRAP-TYPE
   ENTERPRISE enatel
   DESCRIPTION
      "INFORMATION: Manual Equalise OFF"
   --#TYPE "SM32 Trap"
   --#SUMMARY "Manual Equalise OFF"
   --#ARGUMENTS { }
   --#SEVERITY INFORMATIONAL
   --#TIMEINDEX 1
   --#HELP ""
   --#HELPTAG 0
   --#STATE OPERATIONAL
   ::= 271

fastchargeon TRAP-TYPE
   ENTERPRISE enatel
   DESCRIPTION
      "INFORMATION: Fast Charge Active"
   --#TYPE "SM32 Trap"
   --#SUMMARY "Fast Charge Active"
   --#ARGUMENTS { }
   --#SEVERITY INFORMATIONAL
   --#TIMEINDEX 1
   --#HELP ""
   --#HELPTAG 0
   --#STATE OPERATIONAL
   ::= 272

fastchargeoff TRAP-TYPE
   ENTERPRISE enatel
   DESCRIPTION
      "INFORMATION: Fast Charge OFF"
   --#TYPE "SM32 Trap"
   --#SUMMARY "Fast Charge OFF"
   --#ARGUMENTS { }
   --#SEVERITY INFORMATIONAL
   --#TIMEINDEX 1
   --#HELP ""
   --#HELPTAG 0
   --#STATE OPERATIONAL
   ::= 273

batteryteston TRAP-TYPE
   ENTERPRISE enatel
   DESCRIPTION
      "INFORMATION: Battery Test Active"
   --#TYPE "SM32 Trap"
   --#SUMMARY "Battery Test Active"
   --#ARGUMENTS { }
   --#SEVERITY INFORMATIONAL
   --#TIMEINDEX 1
   --#HELP ""
   --#HELPTAG 0
   --#STATE OPERATIONAL
   ::= 274

batterytestoff TRAP-TYPE
   ENTERPRISE enatel
   DESCRIPTION
      "INFORMATION: Battery Test OFF"
   --#TYPE "SM32 Trap"
   --#SUMMARY "Battery Test OFF"
   --#ARGUMENTS { }
   --#SEVERITY INFORMATIONAL
   --#TIMEINDEX 1
   --#HELP ""
   --#HELPTAG 0
   --#STATE OPERATIONAL
   ::= 275

batterydischargeon TRAP-TYPE
   ENTERPRISE enatel
   DESCRIPTION
      "INFORMATION: Battery Discharge Active"
   --#TYPE "SM32 Trap"
   --#SUMMARY "Battery Discharge Active"
   --#ARGUMENTS { }
   --#SEVERITY INFORMATIONAL
   --#TIMEINDEX 1
   --#HELP ""
   --#HELPTAG 0
   --#STATE OPERATIONAL
   ::= 276

batterydischargeoff TRAP-TYPE
   ENTERPRISE enatel
   DESCRIPTION
      "INFORMATION: Battery Discharge OFF"
   --#TYPE "SM32 Trap"
   --#SUMMARY "Battery Discharge OFF"
   --#ARGUMENTS { }
   --#SEVERITY INFORMATIONAL
   --#TIMEINDEX 1
   --#HELP ""
   --#HELPTAG 0
   --#STATE OPERATIONAL
   ::= 277

batterytestfailon TRAP-TYPE
   ENTERPRISE enatel
   DESCRIPTION
      "INFORMATION: Battery Test Fail"
   --#TYPE "SM32 Trap"
   --#SUMMARY " Battery Test Fail Active"
   --#ARGUMENTS { }
   --#SEVERITY CRITICAL
   --#TIMEINDEX 1
   --#HELP ""
   --#HELPTAG 0
   --#STATE OPERATIONAL
   ::= 278

batterytestfailoff TRAP-TYPE
   ENTERPRISE enatel
   DESCRIPTION
      "INFORMATION: Battery Test Fail has returned to normal"
   --#TYPE "SM32 Trap"
   --#SUMMARY " Battery Test Fail Normal"
   --#ARGUMENTS { }
   --#SEVERITY INFORMATIONAL
   --#TIMEINDEX 1
   --#HELP ""
   --#HELPTAG 0
   --#STATE OPERATIONAL
   ::= 279

batterycurrentlimiton TRAP-TYPE
   ENTERPRISE enatel
   DESCRIPTION
      "INFORMATION: Battery Current Limit Active"
   --#TYPE "SM32 Trap"
   --#SUMMARY "Battery Current Limit Active"
   --#ARGUMENTS { }
   --#SEVERITY CRITICAL
   --#TIMEINDEX 1
   --#HELP ""
   --#HELPTAG 0
   --#STATE OPERATIONAL
   ::= 280

batterycurrentlimitoff TRAP-TYPE
   ENTERPRISE enatel
   DESCRIPTION
      "INFORMATION: Battery Current Limit Active has returned to normal"
   --#TYPE "SM32 Trap"
   --#SUMMARY " Battery Current Limit  Normal"
   --#ARGUMENTS { }
   --#SEVERITY INFORMATIONAL
   --#TIMEINDEX 1
   --#HELP ""
   --#HELPTAG 0
   --#STATE OPERATIONAL
   ::= 281

rectifiersystemcurrentlimiton TRAP-TYPE
   ENTERPRISE enatel
   DESCRIPTION
      "INFORMATION: Rectifier System Current Limit Active"
   --#TYPE "SM32 Trap"
   --#SUMMARY "Rectifier System Current Limit Active"
   --#ARGUMENTS { }
   --#SEVERITY CRITICAL
   --#TIMEINDEX 1
   --#HELP ""
   --#HELPTAG 0
   --#STATE OPERATIONAL
   ::= 282

rectifiersystemcurrentlimitoff TRAP-TYPE
   ENTERPRISE enatel
   DESCRIPTION
      "INFORMATION: Rectifier System Current Limit Active has returned to normal"
   --#TYPE "SM32 Trap"
   --#SUMMARY " Rectifier System Current Limit Normal"
   --#ARGUMENTS { }
   --#SEVERITY INFORMATIONAL
   --#TIMEINDEX 1
   --#HELP ""
   --#HELPTAG 0
   --#STATE OPERATIONAL
   ::= 283

peripheralcommsfailedon TRAP-TYPE
   ENTERPRISE enatel
   DESCRIPTION
      "INFORMATION: Peripheral Device Comms Fail"
   --#TYPE "SM32 Trap"
   --#SUMMARY "Peripheral Device Comms Fail"
   --#ARGUMENTS { }
   --#SEVERITY CRITICAL
   --#TIMEINDEX 1
   --#HELP ""
   --#HELPTAG 0
   --#STATE OPERATIONAL
   ::= 284

peripheralcommsfailedoff TRAP-TYPE
   ENTERPRISE enatel
   DESCRIPTION
      "INFORMATION: Peripheral Device Comms Fail has returned to normal"
   --#TYPE "SM32 Trap"
   --#SUMMARY " Peripheral Device Comms  Normal"
   --#ARGUMENTS { }
   --#SEVERITY INFORMATIONAL
   --#TIMEINDEX 1
   --#HELP ""
   --#HELPTAG 0
   --#STATE OPERATIONAL
   ::= 285

lvdfailon TRAP-TYPE
   ENTERPRISE enatel
   DESCRIPTION
      "INFORMATION: LVD Fail"
   --#TYPE "SM32 Trap"
   --#SUMMARY "LVD Fail"
   --#ARGUMENTS { }
   --#SEVERITY CRITICAL
   --#TIMEINDEX 1
   --#HELP ""
   --#HELPTAG 0
   --#STATE OPERATIONAL
   ::= 286

lvdfailoff TRAP-TYPE
   ENTERPRISE enatel
   DESCRIPTION
      "INFORMATION: LVD Fail has returned to normal"
   --#TYPE "SM32 Trap"
   --#SUMMARY " LVD Fail  NORMAL"
   --#ARGUMENTS { }
   --#SEVERITY INFORMATIONAL
   --#TIMEINDEX 1
   --#HELP ""
   --#HELPTAG 0
   --#STATE OPERATIONAL
   ::= 287

adcfailon TRAP-TYPE
   ENTERPRISE enatel
   DESCRIPTION
      "INFORMATION: ADC Fail"
   --#TYPE "SM32 Trap"
   --#SUMMARY "ADC Fail"
   --#ARGUMENTS { }
   --#SEVERITY CRITICAL
   --#TIMEINDEX 1
   --#HELP ""
   --#HELPTAG 0
   --#STATE OPERATIONAL
   ::= 288

adcfailoff TRAP-TYPE
   ENTERPRISE enatel
   DESCRIPTION
      "INFORMATION:ADC Fail has returned to normal"
   --#TYPE "SM32 Trap"
   --#SUMMARY " ADC Fail  NORMAL"
   --#ARGUMENTS { }
   --#SEVERITY INFORMATIONAL
   --#TIMEINDEX 1
   --#HELP ""
   --#HELPTAG 0
   --#STATE OPERATIONAL
   ::= 289

logicerroron TRAP-TYPE
   ENTERPRISE enatel
   DESCRIPTION
      "INFORMATION: Logic Error"
   --#TYPE "SM32 Trap"
   --#SUMMARY "Logic Error"
   --#ARGUMENTS { }
   --#SEVERITY CRITICAL
   --#TIMEINDEX 1
   --#HELP ""
   --#HELPTAG 0
   --#STATE OPERATIONAL
   ::= 290

logicerroroff TRAP-TYPE
   ENTERPRISE enatel
   DESCRIPTION
      "INFORMATION:Logic Error has returned to normal"
   --#TYPE "SM32 Trap"
   --#SUMMARY " Logic Error  NORMAL"
   --#ARGUMENTS { }
   --#SEVERITY INFORMATIONAL
   --#TIMEINDEX 1
   --#HELP ""
   --#HELPTAG 0
   --#STATE OPERATIONAL
   ::= 291

monitorfanfailon TRAP-TYPE
   ENTERPRISE enatel
   DESCRIPTION
      "INFORMATION: Monitor Fan Fail"
   --#TYPE "SM32 Trap"
   --#SUMMARY "Monitor Fan Fail Active"
   --#ARGUMENTS { }
   --#SEVERITY CRITICAL
   --#TIMEINDEX 1
   --#HELP ""
   --#HELPTAG 0
   --#STATE OPERATIONAL
   ::= 292

monitorfanfailoff TRAP-TYPE
   ENTERPRISE enatel
   DESCRIPTION
      "INFORMATION: Monitor Fan Fail has returned to normal"
   --#TYPE "SM32 Trap"
   --#SUMMARY " Monitor Fan NORMAL"
   --#ARGUMENTS { }
   --#SEVERITY INFORMATIONAL
   --#TIMEINDEX 1
   --#HELP ""
   --#HELPTAG 0
   --#STATE OPERATIONAL
   ::= 293

rectifierpowerlimiton TRAP-TYPE
   ENTERPRISE enatel
   DESCRIPTION
      "INFORMATION: Rectifier Power Limit Active Alarm"
   --#TYPE "SM32 Trap"
   --#SUMMARY "Rectifier Power Limit Active"
   --#ARGUMENTS { }
   --#SEVERITY CRITICAL
   --#TIMEINDEX 1
   --#HELP ""
   --#HELPTAG 0
   --#STATE OPERATIONAL
   ::= 294

rectifierpowerlimitoff TRAP-TYPE
   ENTERPRISE enatel
   DESCRIPTION
      "INFORMATION: Rectifier Power Limit Active Alarm has returned to normal"
   --#TYPE "SM32 Trap"
   --#SUMMARY "Rectifier Power Limit Normal"
   --#ARGUMENTS { }
   --#SEVERITY INFORMATIONAL
   --#TIMEINDEX 1
   --#HELP ""
   --#HELPTAG 0
   --#STATE OPERATIONAL
   ::= 295


acvoltagehighon TRAP-TYPE
   ENTERPRISE enatel
   DESCRIPTION
      "INFORMATION: AC Voltage High"
   --#TYPE "SM32 Trap"
   --#SUMMARY "AC Voltage High Active"
   --#ARGUMENTS { }
   --#SEVERITY CRITICAL
   --#TIMEINDEX 1
   --#HELP ""
   --#HELPTAG 0
   --#STATE OPERATIONAL
   ::= 298

acvoltagehighoff TRAP-TYPE
   ENTERPRISE enatel
   DESCRIPTION
      "INFORMATION: AC Voltage High has returned to normal"
   --#TYPE "SM32 Trap"
   --#SUMMARY " AC Voltage High NORMAL"
   --#ARGUMENTS { }
   --#SEVERITY INFORMATIONAL
   --#TIMEINDEX 1
   --#HELP ""
   --#HELPTAG 0
   --#STATE OPERATIONAL
   ::= 299

acvoltagelowon TRAP-TYPE
   ENTERPRISE enatel
   DESCRIPTION
      "INFORMATION: AC Voltage Low"
   --#TYPE "SM32 Trap"
   --#SUMMARY "AC Voltage Low Active"
   --#ARGUMENTS { }
   --#SEVERITY CRITICAL
   --#TIMEINDEX 1
   --#HELP ""
   --#HELPTAG 0
   --#STATE OPERATIONAL
   ::= 300

acvoltagelowoff TRAP-TYPE
   ENTERPRISE enatel
   DESCRIPTION
      "INFORMATION: AC Voltage Low has returned to normal"
   --#TYPE "SM32 Trap"
   --#SUMMARY " AC Voltage Low NORMAL"
   --#ARGUMENTS { }
   --#SEVERITY INFORMATIONAL
   --#TIMEINDEX 1
   --#HELP ""
   --#HELPTAG 0
   --#STATE OPERATIONAL
   ::= 301

acphaseloston TRAP-TYPE
   ENTERPRISE enatel
   DESCRIPTION
      "INFORMATION: AC Phase Lost"
   --#TYPE "SM32 Trap"
   --#SUMMARY "AC Phase Lost Active"
   --#ARGUMENTS { }
   --#SEVERITY CRITICAL
   --#TIMEINDEX 1
   --#HELP ""
   --#HELPTAG 0
   --#STATE OPERATIONAL
   ::= 302

acphaselostoff TRAP-TYPE
   ENTERPRISE enatel
   DESCRIPTION
      "INFORMATION: AC Phase Lost has returned to normal"
   --#TYPE "SM32 Trap"
   --#SUMMARY " AC Phase Lost NORMAL"
   --#ARGUMENTS { }
   --#SEVERITY INFORMATIONAL
   --#TIMEINDEX 1
   --#HELP ""
   --#HELPTAG 0
   --#STATE OPERATIONAL
   ::= 303

accurrenthighon TRAP-TYPE
   ENTERPRISE enatel
   DESCRIPTION
      "INFORMATION: AC Current High"
   --#TYPE "SM32 Trap"
   --#SUMMARY "AC Current High Active"
   --#ARGUMENTS { }
   --#SEVERITY CRITICAL
   --#TIMEINDEX 1
   --#HELP ""
   --#HELPTAG 0
   --#STATE OPERATIONAL
   ::= 304

accurrenthighoff TRAP-TYPE
   ENTERPRISE enatel
   DESCRIPTION
      "INFORMATION: AC Current High has returned to normal"
   --#TYPE "SM32 Trap"
   --#SUMMARY " AC Current High NORMAL"
   --#ARGUMENTS { }
   --#SEVERITY INFORMATIONAL
   --#TIMEINDEX 1
   --#HELP ""
   --#HELPTAG 0
   --#STATE OPERATIONAL
   ::= 305

acfreqhighon TRAP-TYPE
   ENTERPRISE enatel
   DESCRIPTION
      "INFORMATION: AC Frequency High"
   --#TYPE "SM32 Trap"
   --#SUMMARY "AC Frequency High Active"
   --#ARGUMENTS { }
   --#SEVERITY CRITICAL
   --#TIMEINDEX 1
   --#HELP ""
   --#HELPTAG 0
   --#STATE OPERATIONAL
   ::= 306

acfreqhighoff TRAP-TYPE
   ENTERPRISE enatel
   DESCRIPTION
      "INFORMATION: AC Frequency High has returned to normal"
   --#TYPE "SM32 Trap"
   --#SUMMARY " AC Frequency High NORMAL"
   --#ARGUMENTS { }
   --#SEVERITY INFORMATIONAL
   --#TIMEINDEX 1
   --#HELP ""
   --#HELPTAG 0
   --#STATE OPERATIONAL
   ::= 307

acfreqlowon TRAP-TYPE
   ENTERPRISE enatel
   DESCRIPTION
      "INFORMATION:AC Frequency Low"
   --#TYPE "SM32 Trap"
   --#SUMMARY "AC Frequency Low Active"
   --#ARGUMENTS { }
   --#SEVERITY CRITICAL
   --#TIMEINDEX 1
   --#HELP ""
   --#HELPTAG 0
   --#STATE OPERATIONAL
   ::= 308

acfreqlowoff TRAP-TYPE
   ENTERPRISE enatel
   DESCRIPTION
      "INFORMATION: AC Frequency Low has returned to normal"
   --#TYPE "SM32 Trap"
   --#SUMMARY " AC Frequency Low NORMAL"
   --#ARGUMENTS { }
   --#SEVERITY INFORMATIONAL
   --#TIMEINDEX 1
   --#HELP ""
   --#HELPTAG 0
   --#STATE OPERATIONAL
   ::= 309

staticbypasscontrolpowerfailon TRAP-TYPE
   ENTERPRISE enatel
   DESCRIPTION
      "INFORMATION: Static Bypass Alarm: Control Power Fail "
   --#TYPE "SM32 Trap"
   --#SUMMARY "Static Bypass Alarm: Control Power Fail Active"
   --#ARGUMENTS { }
   --#SEVERITY CRITICAL
   --#TIMEINDEX 1
   --#HELP ""
   --#HELPTAG 0
   --#STATE OPERATIONAL
   ::= 330

staticbypasscontrolpowerfailoff TRAP-TYPE
   ENTERPRISE enatel
   DESCRIPTION
      "INFORMATION: Static Bypass Alarm: Control Power Fail has returned to normal"
   --#TYPE "SM32 Trap"
   --#SUMMARY " Static Bypass Alarm: Control Power Fail NORMAL"
   --#ARGUMENTS { }
   --#SEVERITY INFORMATIONAL
   --#TIMEINDEX 1
   --#HELP ""
   --#HELPTAG 0
   --#STATE OPERATIONAL
   ::= 331

staticbypassbypassunavailableon TRAP-TYPE
   ENTERPRISE enatel
   DESCRIPTION
      "INFORMATION: Static Bypass Alarm: Bypass Unavailable "
   --#TYPE "SM32 Trap"
   --#SUMMARY "Static Bypass Alarm: Bypass Unavailable Active"
   --#ARGUMENTS { }
   --#SEVERITY CRITICAL
   --#TIMEINDEX 1
   --#HELP ""
   --#HELPTAG 0
   --#STATE OPERATIONAL
   ::= 332

staticbypassbypassunavailableoff TRAP-TYPE
   ENTERPRISE enatel
   DESCRIPTION
      "INFORMATION: Static Bypass Alarm: Bypass Unavailable has returned to normal"
   --#TYPE "SM32 Trap"
   --#SUMMARY " Static Bypass Alarm: Bypass Unavailable NORMAL"
   --#ARGUMENTS { }
   --#SEVERITY INFORMATIONAL
   --#TIMEINDEX 1
   --#HELP ""
   --#HELPTAG 0
   --#STATE OPERATIONAL
   ::= 333

staticbypassovertemperatureon TRAP-TYPE
   ENTERPRISE enatel
   DESCRIPTION
      "INFORMATION: Static Bypass Alarm: Over Temperature "
   --#TYPE "SM32 Trap"
   --#SUMMARY "Static Bypass Alarm: Over Temperature Active"
   --#ARGUMENTS { }
   --#SEVERITY CRITICAL
   --#TIMEINDEX 1
   --#HELP ""
   --#HELPTAG 0
   --#STATE OPERATIONAL
   ::= 334

staticbypassovertemperatureoff TRAP-TYPE
   ENTERPRISE enatel
   DESCRIPTION
      "INFORMATION:Static Bypass Alarm: Over Temperature has returned to normal"
   --#TYPE "SM32 Trap"
   --#SUMMARY " Static Bypass Alarm: Over Temperature NORMAL"
   --#ARGUMENTS { }
   --#SEVERITY INFORMATIONAL
   --#TIMEINDEX 1
   --#HELP ""
   --#HELPTAG 0
   --#STATE OPERATIONAL
   ::= 335

staticbypassfanfailon TRAP-TYPE
   ENTERPRISE enatel
   DESCRIPTION
      "INFORMATION: Static Bypass Alarm: Fan Fail"
   --#TYPE "SM32 Trap"
   --#SUMMARY "Static Bypass Alarm: Fan Fail Active"
   --#ARGUMENTS { }
   --#SEVERITY CRITICAL
   --#TIMEINDEX 1
   --#HELP ""
   --#HELPTAG 0
   --#STATE OPERATIONAL
   ::= 336

staticbypassfanfailoff TRAP-TYPE
   ENTERPRISE enatel
   DESCRIPTION
      "INFORMATION:Static Bypass Alarm: Fan Fail has returned to normal"
   --#TYPE "SM32 Trap"
   --#SUMMARY " Static Bypass Alarm: Fan Fail NORMAL"
   --#ARGUMENTS { }
   --#SEVERITY INFORMATIONAL
   --#TIMEINDEX 1
   --#HELP ""
   --#HELPTAG 0
   --#STATE OPERATIONAL
   ::= 337

staticbypasspowerlimiton TRAP-TYPE
   ENTERPRISE enatel
   DESCRIPTION
      "INFORMATION: Static Bypass Alarm: Power Limit"
   --#TYPE "SM32 Trap"
   --#SUMMARY "Static Bypass Alarm: Power Limit Active"
   --#ARGUMENTS { }
   --#SEVERITY CRITICAL
   --#TIMEINDEX 1
   --#HELP ""
   --#HELPTAG 0
   --#STATE OPERATIONAL
   ::= 338

staticbypasspowerlimitoff TRAP-TYPE
   ENTERPRISE enatel
   DESCRIPTION
      "INFORMATION:Static Bypass Alarm: Power Limit has returned to normal"
   --#TYPE "SM32 Trap"
   --#SUMMARY " Static Bypass Alarm: Power Limit NORMAL"
   --#ARGUMENTS { }
   --#SEVERITY INFORMATIONAL
   --#TIMEINDEX 1
   --#HELP ""
   --#HELPTAG 0
   --#STATE OPERATIONAL
   ::= 339

staticbypassswitchfailon TRAP-TYPE
   ENTERPRISE enatel
   DESCRIPTION
      "INFORMATION: Static Bypass Alarm: Switch Fail"
   --#TYPE "SM32 Trap"
   --#SUMMARY "Static Bypass Alarm: Switch Fail Active"
   --#ARGUMENTS { }
   --#SEVERITY CRITICAL
   --#TIMEINDEX 1
   --#HELP ""
   --#HELPTAG 0
   --#STATE OPERATIONAL
   ::= 340

staticbypassswitchfailoff TRAP-TYPE
   ENTERPRISE enatel
   DESCRIPTION
      "INFORMATION:Static Bypass Alarm: Switch Fail has returned to normal"
   --#TYPE "SM32 Trap"
   --#SUMMARY " Static Bypass Alarm: Switch Fail NORMAL"
   --#ARGUMENTS { }
   --#SEVERITY INFORMATIONAL
   --#TIMEINDEX 1
   --#HELP ""
   --#HELPTAG 0
   --#STATE OPERATIONAL
   ::= 341

staticbypasspriorityalarmon TRAP-TYPE
   ENTERPRISE enatel
   DESCRIPTION
      "INFORMATION: Static Bypass Alarm: Priority Alarm"
   --#TYPE "SM32 Trap"
   --#SUMMARY "Static Bypass Alarm: Priority Alarm Active"
   --#ARGUMENTS { }
   --#SEVERITY CRITICAL
   --#TIMEINDEX 1
   --#HELP ""
   --#HELPTAG 0
   --#STATE OPERATIONAL
   ::= 342

staticbypasspriorityalarmoff TRAP-TYPE
   ENTERPRISE enatel
   DESCRIPTION
      "INFORMATION:Static Bypass Alarm: Priority Alarm has returned to normal"
   --#TYPE "SM32 Trap"
   --#SUMMARY " Static Bypass Alarm: Priority Alarm NORMAL"
   --#ARGUMENTS { }
   --#SEVERITY INFORMATIONAL
   --#TIMEINDEX 1
   --#HELP ""
   --#HELPTAG 0
   --#STATE OPERATIONAL
   ::= 343

staticbypassbackfeedrelayopenon TRAP-TYPE
   ENTERPRISE enatel
   DESCRIPTION
      "INFORMATION: Static Bypass Alarm: Backfeed Relay Open"
   --#TYPE "SM32 Trap"
   --#SUMMARY "Static Bypass Alarm: Backfeed Relay Open Active"
   --#ARGUMENTS { }
   --#SEVERITY CRITICAL
   --#TIMEINDEX 1
   --#HELP ""
   --#HELPTAG 0
   --#STATE OPERATIONAL
   ::= 344

staticbypassbackfeedrelayopenoff TRAP-TYPE
   ENTERPRISE enatel
   DESCRIPTION
      "INFORMATION:Static Bypass Alarm: Backfeed Relay Open has returned to normal"
   --#TYPE "SM32 Trap"
   --#SUMMARY " Static Bypass Alarm: Backfeed Relay Open NORMAL"
   --#ARGUMENTS { }
   --#SEVERITY INFORMATIONAL
   --#TIMEINDEX 1
   --#HELP ""
   --#HELPTAG 0
   --#STATE OPERATIONAL
   ::= 345


staticbypassscrshortcircuiton TRAP-TYPE
   ENTERPRISE enatel
   DESCRIPTION
      "INFORMATION: Static Bypass Alarm: SCR Short Circuit"
   --#TYPE "SM32 Trap"
   --#SUMMARY "Static Bypass Alarm: SCR Short Circuit Active"
   --#ARGUMENTS { }
   --#SEVERITY CRITICAL
   --#TIMEINDEX 1
   --#HELP ""
   --#HELPTAG 0
   --#STATE OPERATIONAL
   ::= 346

staticbypassscrshortcircuitoff TRAP-TYPE
   ENTERPRISE enatel
   DESCRIPTION
      "INFORMATION:SStatic Bypass Alarm: SCR Short Circuit has returned to normal"
   --#TYPE "SM32 Trap"
   --#SUMMARY " Static Bypass Alarm: SCR Short Circuit NORMAL"
   --#ARGUMENTS { }
   --#SEVERITY INFORMATIONAL
   --#TIMEINDEX 1
   --#HELP ""
   --#HELPTAG 0
   --#STATE OPERATIONAL
   ::= 347

staticbypassoutputshortcircuiton TRAP-TYPE
   ENTERPRISE enatel
   DESCRIPTION
      "INFORMATION: Static Bypass Alarm: Output Short Circuit"
   --#TYPE "SM32 Trap"
   --#SUMMARY "Static Bypass Alarm: Output Short Circuit Active"
   --#ARGUMENTS { }
   --#SEVERITY CRITICAL
   --#TIMEINDEX 1
   --#HELP ""
   --#HELPTAG 0
   --#STATE OPERATIONAL
   ::= 348

staticbypassoutputshortcircuitoff TRAP-TYPE
   ENTERPRISE enatel
   DESCRIPTION
      "INFORMATION:Static Bypass Alarm: Output Short Circuit has returned to normal"
   --#TYPE "SM32 Trap"
   --#SUMMARY " Static Bypass Alarm: Output Short Circuit NORMAL"
   --#ARGUMENTS { }
   --#SEVERITY INFORMATIONAL
   --#TIMEINDEX 1
   --#HELP ""
   --#HELPTAG 0
   --#STATE OPERATIONAL
   ::= 349

staticbypassfaultmodeon TRAP-TYPE
   ENTERPRISE enatel
   DESCRIPTION
      "INFORMATION: Static Bypass Alarm: Fault Mode"
   --#TYPE "SM32 Trap"
   --#SUMMARY "Static Bypass Alarm: Fault Mode Active"
   --#ARGUMENTS { }
   --#SEVERITY CRITICAL
   --#TIMEINDEX 1
   --#HELP ""
   --#HELPTAG 0
   --#STATE OPERATIONAL
   ::= 350

staticbypassfaultmodeoff TRAP-TYPE
   ENTERPRISE enatel
   DESCRIPTION
      "INFORMATION:Static Bypass Alarm: Fault Mode has returned to normal"
   --#TYPE "SM32 Trap"
   --#SUMMARY " Static Bypass Alarm: Fault Mode NORMAL"
   --#ARGUMENTS { }
   --#SEVERITY INFORMATIONAL
   --#TIMEINDEX 1
   --#HELP ""
   --#HELPTAG 0
   --#STATE OPERATIONAL
   ::= 351

staticbypassmodealarmon TRAP-TYPE
   ENTERPRISE enatel
   DESCRIPTION
      "INFORMATION: Static Bypass Alarm: Mode Alarm"
   --#TYPE "SM32 Trap"
   --#SUMMARY "Static Bypass Alarm: Mode Alarm Active"
   --#ARGUMENTS { }
   --#SEVERITY CRITICAL
   --#TIMEINDEX 1
   --#HELP ""
   --#HELPTAG 0
   --#STATE OPERATIONAL
   ::= 352

staticbypassmodealarmoff TRAP-TYPE
   ENTERPRISE enatel
   DESCRIPTION
      "INFORMATION:Static Bypass Alarm: Mode Alarm has returned to normal"
   --#TYPE "SM32 Trap"
   --#SUMMARY " Static Bypass Alarm: Mode Alarm NORMAL"
   --#ARGUMENTS { }
   --#SEVERITY INFORMATIONAL
   --#TIMEINDEX 1
   --#HELP ""
   --#HELPTAG 0
   --#STATE OPERATIONAL
   ::= 353

staticbypassinverterunavailableon TRAP-TYPE
   ENTERPRISE enatel
   DESCRIPTION
      "INFORMATION: Static Bypass Alarm: Inverter Unavailable"
   --#TYPE "SM32 Trap"
   --#SUMMARY "Static Bypass Alarm: Inverter Unavailable Active"
   --#ARGUMENTS { }
   --#SEVERITY CRITICAL
   --#TIMEINDEX 1
   --#HELP ""
   --#HELPTAG 0
   --#STATE OPERATIONAL
   ::= 354

staticbypassinverterunavailableoff TRAP-TYPE
   ENTERPRISE enatel
   DESCRIPTION
      "INFORMATION:Static Bypass Alarm: Inverter Unavailable has returned to normal"
   --#TYPE "SM32 Trap"
   --#SUMMARY " Static Bypass Alarm: Inverter Unavailable NORMAL"
   --#ARGUMENTS { }
   --#SEVERITY INFORMATIONAL
   --#TIMEINDEX 1
   --#HELP ""
   --#HELPTAG 0
   --#STATE OPERATIONAL
   ::= 355

staticbypassmainsunavailableon TRAP-TYPE
   ENTERPRISE enatel
   DESCRIPTION
      "INFORMATION: Static Bypass Alarm: Mains Unavailable"
   --#TYPE "SM32 Trap"
   --#SUMMARY "Static Bypass Alarm: Mains Unavailable Active"
   --#ARGUMENTS { }
   --#SEVERITY CRITICAL
   --#TIMEINDEX 1
   --#HELP ""
   --#HELPTAG 0
   --#STATE OPERATIONAL
   ::= 356

staticbypassmainsunavailableoff TRAP-TYPE
   ENTERPRISE enatel
   DESCRIPTION
      "INFORMATION:Static Bypass Alarm: Mains Unavailable has returned to normal"
   --#TYPE "SM32 Trap"
   --#SUMMARY " Static Bypass Alarm: Mains Unavailable NORMAL"
   --#ARGUMENTS { }
   --#SEVERITY INFORMATIONAL
   --#TIMEINDEX 1
   --#HELP ""
   --#HELPTAG 0
   --#STATE OPERATIONAL
   ::= 357

staticbypasseepromfailon TRAP-TYPE
   ENTERPRISE enatel
   DESCRIPTION
      "INFORMATION: Static Bypass Alarm: EEPROM Fail"
   --#TYPE "SM32 Trap"
   --#SUMMARY "Static Bypass Alarm: EEPROM Fail Active"
   --#ARGUMENTS { }
   --#SEVERITY CRITICAL
   --#TIMEINDEX 1
   --#HELP ""
   --#HELPTAG 0
   --#STATE OPERATIONAL
   ::= 358

staticbypasseepromfailoff TRAP-TYPE
   ENTERPRISE enatel
   DESCRIPTION
      "INFORMATION:Static Bypass Alarm: EEPROM Fail has returned to normal"
   --#TYPE "SM32 Trap"
   --#SUMMARY " Static Bypass Alarm: EEPROM Fail NORMAL"
   --#ARGUMENTS { }
   --#SEVERITY INFORMATIONAL
   --#TIMEINDEX 1
   --#HELP ""
   --#HELPTAG 0
   --#STATE OPERATIONAL
   ::= 359

staticbypassmbsabnormalpositionon TRAP-TYPE
   ENTERPRISE enatel
   DESCRIPTION
      "INFORMATION: Static Bypass Alarm: Manual Bypass Abnormal Switch Position"
   --#TYPE "SM32 Trap"
   --#SUMMARY "Static Bypass Alarm: Manual Bypass Abnormal Switch Position Active"
   --#ARGUMENTS { }
   --#SEVERITY CRITICAL
   --#TIMEINDEX 1
   --#HELP ""
   --#HELPTAG 0
   --#STATE OPERATIONAL
   ::= 360

staticbypassmbsabnormalpositionoff TRAP-TYPE
   ENTERPRISE enatel
   DESCRIPTION
      "INFORMATION:Static Bypass Alarm: Manual Bypass Abnormal Switch Position has returned to normal"
   --#TYPE "SM32 Trap"
   --#SUMMARY " Static Bypass Alarm: Manual Bypass Abnormal Switch Position NORMAL"
   --#ARGUMENTS { }
   --#SEVERITY INFORMATIONAL
   --#TIMEINDEX 1
   --#HELP ""
   --#HELPTAG 0
   --#STATE OPERATIONAL
   ::= 361

-- ****************************************************************************
--				Renewables Traps
-- ****************************************************************************


-- *************** Renewables Alarms (Monitor Generated Alarms) ***************

solarfailnonurgenton TRAP-TYPE
   ENTERPRISE enatel
   DESCRIPTION
      "INFORMATION: Solar Non-Urgent Fail"
   --#TYPE "SM32 Trap"
   --#SUMMARY "Solar Non-Urgent Fail Active"
   --#ARGUMENTS { }
   --#SEVERITY CRITICAL
   --#TIMEINDEX 1
   --#HELP ""
   --#HELPTAG 0
   --#STATE OPERATIONAL
   ::= 362

solarfailnonurgentoff TRAP-TYPE
   ENTERPRISE enatel
   DESCRIPTION
      "INFORMATION:Solar Non-Urgent Fail has returned to normal"
   --#TYPE "SM32 Trap"
   --#SUMMARY " Solar Non-Urgent Fail NORMAL"
   --#ARGUMENTS { }
   --#SEVERITY INFORMATIONAL
   --#TIMEINDEX 1
   --#HELP ""
   --#HELPTAG 0
   --#STATE OPERATIONAL
   ::= 363

solarfailurgenton TRAP-TYPE
   ENTERPRISE enatel
   DESCRIPTION
      "INFORMATION: Solar Urgent Fail"
   --#TYPE "SM32 Trap"
   --#SUMMARY "Solar Urgent Fail Active"
   --#ARGUMENTS { }
   --#SEVERITY CRITICAL
   --#TIMEINDEX 1
   --#HELP ""
   --#HELPTAG 0
   --#STATE OPERATIONAL
   ::= 364

solarfailurgentoff TRAP-TYPE
   ENTERPRISE enatel
   DESCRIPTION
      "INFORMATION:Solar Urgent Fail has returned to normal"
   --#TYPE "SM32 Trap"
   --#SUMMARY " Solar Urgent Fail NORMAL"
   --#ARGUMENTS { }
   --#SEVERITY INFORMATIONAL
   --#TIMEINDEX 1
   --#HELP ""
   --#HELPTAG 0
   --#STATE OPERATIONAL
   ::= 365

solarallfailon TRAP-TYPE
   ENTERPRISE enatel
   DESCRIPTION
      "INFORMATION: Solar All Converters Fail"
   --#TYPE "SM32 Trap"
   --#SUMMARY "Solar All Converters Fail Active"
   --#ARGUMENTS { }
   --#SEVERITY CRITICAL
   --#TIMEINDEX 1
   --#HELP ""
   --#HELPTAG 0
   --#STATE OPERATIONAL
   ::= 366

solarallfailoff TRAP-TYPE
   ENTERPRISE enatel
   DESCRIPTION
      "INFORMATION:Solar All Converters Fail has returned to normal"
   --#TYPE "SM32 Trap"
   --#SUMMARY " Solar All Converters Fail NORMAL"
   --#ARGUMENTS { }
   --#SEVERITY INFORMATIONAL
   --#TIMEINDEX 1
   --#HELP ""
   --#HELPTAG 0
   --#STATE OPERATIONAL
   ::= 367

solarcommsfailurgenton TRAP-TYPE
   ENTERPRISE enatel
   DESCRIPTION
      "INFORMATION: Solar Urgent Comms Fail"
   --#TYPE "SM32 Trap"
   --#SUMMARY "Solar Urgent Comms Fail Active"
   --#ARGUMENTS { }
   --#SEVERITY CRITICAL
   --#TIMEINDEX 1
   --#HELP ""
   --#HELPTAG 0
   --#STATE OPERATIONAL
   ::= 368

solarcommsfailurgentoff TRAP-TYPE
   ENTERPRISE enatel
   DESCRIPTION
      "INFORMATION:Solar Urgent Comms Fail has returned to normal"
   --#TYPE "SM32 Trap"
   --#SUMMARY " Solar Urgent Comms Fail NORMAL"
   --#ARGUMENTS { }
   --#SEVERITY INFORMATIONAL
   --#TIMEINDEX 1
   --#HELP ""
   --#HELPTAG 0
   --#STATE OPERATIONAL
   ::= 369

solarcommsfailnonurgenton TRAP-TYPE
   ENTERPRISE enatel
   DESCRIPTION
      "INFORMATION: Solar Non-Urgent Comms Fail"
   --#TYPE "SM32 Trap"
   --#SUMMARY "Solar Non-Urgent Comms Fail Active"
   --#ARGUMENTS { }
   --#SEVERITY CRITICAL
   --#TIMEINDEX 1
   --#HELP ""
   --#HELPTAG 0
   --#STATE OPERATIONAL
   ::= 370

solarcommsfailnonurgentoff TRAP-TYPE
   ENTERPRISE enatel
   DESCRIPTION
      "INFORMATION:Solar Non-Urgent Comms Fail has returned to normal"
   --#TYPE "SM32 Trap"
   --#SUMMARY " Solar Non-Urgent Comms Fail NORMAL"
   --#ARGUMENTS { }
   --#SEVERITY INFORMATIONAL
   --#TIMEINDEX 1
   --#HELP ""
   --#HELPTAG 0
   --#STATE OPERATIONAL
   ::= 371

windfailnonurgenton TRAP-TYPE
   ENTERPRISE enatel
   DESCRIPTION
      "INFORMATION: Wind Non-Urgent Fail"
   --#TYPE "SM32 Trap"
   --#SUMMARY "Wind Non-Urgent Fail Active"
   --#ARGUMENTS { }
   --#SEVERITY CRITICAL
   --#TIMEINDEX 1
   --#HELP ""
   --#HELPTAG 0
   --#STATE OPERATIONAL
   ::= 372

windfailnonurgentoff TRAP-TYPE
   ENTERPRISE enatel
   DESCRIPTION
      "INFORMATION:Wind Non-Urgent Fail has returned to normal"
   --#TYPE "SM32 Trap"
   --#SUMMARY "Wind Non-Urgent Fail NORMAL"
   --#ARGUMENTS { }
   --#SEVERITY INFORMATIONAL
   --#TIMEINDEX 1
   --#HELP ""
   --#HELPTAG 0
   --#STATE OPERATIONAL
   ::= 373

windfailurgenton TRAP-TYPE
   ENTERPRISE enatel
   DESCRIPTION
      "INFORMATION: Wind Urgent Fail"
   --#TYPE "SM32 Trap"
   --#SUMMARY "Wind Urgent Fail Active"
   --#ARGUMENTS { }
   --#SEVERITY CRITICAL
   --#TIMEINDEX 1
   --#HELP ""
   --#HELPTAG 0
   --#STATE OPERATIONAL
   ::= 374

windfailurgentoff TRAP-TYPE
   ENTERPRISE enatel
   DESCRIPTION
      "INFORMATION:Wind Urgent Fail has returned to normal"
   --#TYPE "SM32 Trap"
   --#SUMMARY "Wind Urgent Fail NORMAL"
   --#ARGUMENTS { }
   --#SEVERITY INFORMATIONAL
   --#TIMEINDEX 1
   --#HELP ""
   --#HELPTAG 0
   --#STATE OPERATIONAL
   ::= 375

windallfailon TRAP-TYPE
   ENTERPRISE enatel
   DESCRIPTION
      "INFORMATION: Wind All Converters Fail"
   --#TYPE "SM32 Trap"
   --#SUMMARY "Wind All Converters Fail Active"
   --#ARGUMENTS { }
   --#SEVERITY CRITICAL
   --#TIMEINDEX 1
   --#HELP ""
   --#HELPTAG 0
   --#STATE OPERATIONAL
   ::= 376

windallfailoff TRAP-TYPE
   ENTERPRISE enatel
   DESCRIPTION
      "INFORMATION:Wind All Converters Fail has returned to normal"
   --#TYPE "SM32 Trap"
   --#SUMMARY "Wind All Converters Fail NORMAL"
   --#ARGUMENTS { }
   --#SEVERITY INFORMATIONAL
   --#TIMEINDEX 1
   --#HELP ""
   --#HELPTAG 0
   --#STATE OPERATIONAL
   ::= 377

windcommsfailurgenton TRAP-TYPE
   ENTERPRISE enatel
   DESCRIPTION
      "INFORMATION: Wind Urgent Comms Fail"
   --#TYPE "SM32 Trap"
   --#SUMMARY "Wind Urgent Comms Fail Active"
   --#ARGUMENTS { }
   --#SEVERITY CRITICAL
   --#TIMEINDEX 1
   --#HELP ""
   --#HELPTAG 0
   --#STATE OPERATIONAL
   ::= 378

windcommsfailurgentoff TRAP-TYPE
   ENTERPRISE enatel
   DESCRIPTION
      "INFORMATION:Wind Urgent Comms Fail has returned to normal"
   --#TYPE "SM32 Trap"
   --#SUMMARY "Wind Urgent Comms Fail NORMAL"
   --#ARGUMENTS { }
   --#SEVERITY INFORMATIONAL
   --#TIMEINDEX 1
   --#HELP ""
   --#HELPTAG 0
   --#STATE OPERATIONAL
   ::= 379

windcommsfailnonurgenton TRAP-TYPE
   ENTERPRISE enatel
   DESCRIPTION
      "INFORMATION: Wind Non-Urgent Comms Fail"
   --#TYPE "SM32 Trap"
   --#SUMMARY "Wind Non-Urgent Comms Fail Active"
   --#ARGUMENTS { }
   --#SEVERITY CRITICAL
   --#TIMEINDEX 1
   --#HELP ""
   --#HELPTAG 0
   --#STATE OPERATIONAL
   ::= 380

windcommsfailnonurgentoff TRAP-TYPE
   ENTERPRISE enatel
   DESCRIPTION
      "INFORMATION:Wind Non-Urgent Comms Fail has returned to normal"
   --#TYPE "SM32 Trap"
   --#SUMMARY "Wind Non-Urgent Comms Fail NORMAL"
   --#ARGUMENTS { }
   --#SEVERITY INFORMATIONAL
   --#TIMEINDEX 1
   --#HELP ""
   --#HELPTAG 0
   --#STATE OPERATIONAL
   ::= 381



-- *************** Solar converter alarms ***************

solarpanelundervoltson TRAP-TYPE
   ENTERPRISE enatel
   DESCRIPTION
      "INFORMATION: Solar Converter Panel Under-Volts"
   --#TYPE "SM32 Trap"
   --#SUMMARY "Solar Converter Panel Under-Volts Active"
   --#ARGUMENTS { }
   --#SEVERITY CRITICAL
   --#TIMEINDEX 1
   --#HELP ""
   --#HELPTAG 0
   --#STATE OPERATIONAL
   ::= 394

solarpanelundervoltsoff TRAP-TYPE
   ENTERPRISE enatel
   DESCRIPTION
      "INFORMATION:Solar Converter Panel Under-Volts has returned to normal"
   --#TYPE "SM32 Trap"
   --#SUMMARY "Solar Converter Panel Under-Volts NORMAL"
   --#ARGUMENTS { }
   --#SEVERITY INFORMATIONAL
   --#TIMEINDEX 1
   --#HELP ""
   --#HELPTAG 0
   --#STATE OPERATIONAL
   ::= 395


solarconverterfailon TRAP-TYPE
   ENTERPRISE enatel
   DESCRIPTION
      "INFORMATION: Solar Converter Fail"
   --#TYPE "SM32 Trap"
   --#SUMMARY "Solar Converter Fail Active"
   --#ARGUMENTS { }
   --#SEVERITY CRITICAL
   --#TIMEINDEX 1
   --#HELP ""
   --#HELPTAG 0
   --#STATE OPERATIONAL
   ::= 396

solarconverterfailoff TRAP-TYPE
   ENTERPRISE enatel
   DESCRIPTION
      "INFORMATION:Solar Converter Fail has returned to normal"
   --#TYPE "SM32 Trap"
   --#SUMMARY "Solar Converter Fail NORMAL"
   --#ARGUMENTS { }
   --#SEVERITY INFORMATIONAL
   --#TIMEINDEX 1
   --#HELP ""
   --#HELPTAG 0
   --#STATE OPERATIONAL
   ::= 397


solarconverterovertempon TRAP-TYPE
   ENTERPRISE enatel
   DESCRIPTION
      "INFORMATION: Solar Converter Over Temperature"
   --#TYPE "SM32 Trap"
   --#SUMMARY "Solar Converter Over Temperature Active"
   --#ARGUMENTS { }
   --#SEVERITY CRITICAL
   --#TIMEINDEX 1
   --#HELP ""
   --#HELPTAG 0
   --#STATE OPERATIONAL
   ::= 398

solarconverterovertempoff TRAP-TYPE
   ENTERPRISE enatel
   DESCRIPTION
      "INFORMATION:Solar Converter Over Temperature has returned to normal"
   --#TYPE "SM32 Trap"
   --#SUMMARY "Solar Converter Over Temperature NORMAL"
   --#ARGUMENTS { }
   --#SEVERITY INFORMATIONAL
   --#TIMEINDEX 1
   --#HELP ""
   --#HELPTAG 0
   --#STATE OPERATIONAL
   ::= 399


solarconverterfanfailon TRAP-TYPE
   ENTERPRISE enatel
   DESCRIPTION
      "INFORMATION: Solar Converter Fan Fail"
   --#TYPE "SM32 Trap"
   --#SUMMARY "Solar Converter Fan Fail Active"
   --#ARGUMENTS { }
   --#SEVERITY CRITICAL
   --#TIMEINDEX 1
   --#HELP ""
   --#HELPTAG 0
   --#STATE OPERATIONAL
   ::= 400

solarconverterfanfailoff TRAP-TYPE
   ENTERPRISE enatel
   DESCRIPTION
      "INFORMATION:Solar Converter Fan Fail has returned to normal"
   --#TYPE "SM32 Trap"
   --#SUMMARY "Solar Converter Fan Fail NORMAL"
   --#ARGUMENTS { }
   --#SEVERITY INFORMATIONAL
   --#TIMEINDEX 1
   --#HELP ""
   --#HELPTAG 0
   --#STATE OPERATIONAL
   ::= 401

solardevicecurrentlimiton TRAP-TYPE
   ENTERPRISE enatel
   DESCRIPTION
      "INFORMATION: Solar Converter Device Current Limit"
   --#TYPE "SM32 Trap"
   --#SUMMARY "Solar Converter Device Current Limit Active"
   --#ARGUMENTS { }
   --#SEVERITY CRITICAL
   --#TIMEINDEX 1
   --#HELP ""
   --#HELPTAG 0
   --#STATE OPERATIONAL
   ::= 402

solardevicecurrentlimitoff TRAP-TYPE
   ENTERPRISE enatel
   DESCRIPTION
      "INFORMATION:Solar Converter Device Current Limit has returned to normal"
   --#TYPE "SM32 Trap"
   --#SUMMARY "Solar Converter Device Current Limit NORMAL"
   --#ARGUMENTS { }
   --#SEVERITY INFORMATIONAL
   --#TIMEINDEX 1
   --#HELP ""
   --#HELPTAG 0
   --#STATE OPERATIONAL
   ::= 403

solaroutputovervoltson TRAP-TYPE
   ENTERPRISE enatel
   DESCRIPTION
      "INFORMATION: Solar Converter Output Overvoltage"
   --#TYPE "SM32 Trap"
   --#SUMMARY "Solar Converter Output Overvoltage Active"
   --#ARGUMENTS { }
   --#SEVERITY CRITICAL
   --#TIMEINDEX 1
   --#HELP ""
   --#HELPTAG 0
   --#STATE OPERATIONAL
   ::= 404

solaroutputovervoltsoff TRAP-TYPE
   ENTERPRISE enatel
   DESCRIPTION
      "INFORMATION:Solar Converter Output Overvoltage has returned to normal"
   --#TYPE "SM32 Trap"
   --#SUMMARY "Solar Converter Output Overvoltage NORMAL"
   --#ARGUMENTS { }
   --#SEVERITY INFORMATIONAL
   --#TIMEINDEX 1
   --#HELP ""
   --#HELPTAG 0
   --#STATE OPERATIONAL
   ::= 405


solarconstantvoltageon TRAP-TYPE
   ENTERPRISE enatel
   DESCRIPTION
      "INFORMATION: Solar Converter Constant Voltage"
   --#TYPE "SM32 Trap"
   --#SUMMARY "Solar Converter Constant Voltage Active"
   --#ARGUMENTS { }
   --#SEVERITY CRITICAL
   --#TIMEINDEX 1
   --#HELP ""
   --#HELPTAG 0
   --#STATE OPERATIONAL
   ::= 406

solarconstantvoltageoff TRAP-TYPE
   ENTERPRISE enatel
   DESCRIPTION
      "INFORMATION:Solar Converter Constant Voltage has returned to normal"
   --#TYPE "SM32 Trap"
   --#SUMMARY "Solar Converter Constant Voltage NORMAL"
   --#ARGUMENTS { }
   --#SEVERITY INFORMATIONAL
   --#TIMEINDEX 1
   --#HELP ""
   --#HELPTAG 0
   --#STATE OPERATIONAL
   ::= 407

solarpostmateon TRAP-TYPE
   ENTERPRISE enatel
   DESCRIPTION
      "INFORMATION: Solar Converter Postmate"
   --#TYPE "SM32 Trap"
   --#SUMMARY "Solar Converter Postmate Active"
   --#ARGUMENTS { }
   --#SEVERITY CRITICAL
   --#TIMEINDEX 1
   --#HELP ""
   --#HELPTAG 0
   --#STATE OPERATIONAL
   ::= 408

solarpostmateoff TRAP-TYPE
   ENTERPRISE enatel
   DESCRIPTION
      "INFORMATION:Solar Converter Postmate has returned to normal"
   --#TYPE "SM32 Trap"
   --#SUMMARY "Solar Converter Postmate NORMAL"
   --#ARGUMENTS { }
   --#SEVERITY INFORMATIONAL
   --#TIMEINDEX 1
   --#HELP ""
   --#HELPTAG 0
   --#STATE OPERATIONAL
   ::= 409

solarbackflowprotecton TRAP-TYPE
   ENTERPRISE enatel
   DESCRIPTION
      "INFORMATION: Solar Converter Current Backflow Protection"
   --#TYPE "SM32 Trap"
   --#SUMMARY "Solar Converter Current Backflow Protection Active"
   --#ARGUMENTS { }
   --#SEVERITY CRITICAL
   --#TIMEINDEX 1
   --#HELP ""
   --#HELPTAG 0
   --#STATE OPERATIONAL
   ::= 410

solarbackflowprotectoff TRAP-TYPE
   ENTERPRISE enatel
   DESCRIPTION
      "INFORMATION:Solar Converter Current Backflow Protection has returned to normal"
   --#TYPE "SM32 Trap"
   --#SUMMARY "Solar Converter Current Backflow Protection NORMAL"
   --#ARGUMENTS { }
   --#SEVERITY INFORMATIONAL
   --#TIMEINDEX 1
   --#HELP ""
   --#HELPTAG 0
   --#STATE OPERATIONAL
   ::= 411

solartempsensefailon TRAP-TYPE
   ENTERPRISE enatel
   DESCRIPTION
      "INFORMATION: Solar Converter Temperature Sense Fail"
   --#TYPE "SM32 Trap"
   --#SUMMARY "Solar Converter Temperature Sense Fail Active"
   --#ARGUMENTS { }
   --#SEVERITY CRITICAL
   --#TIMEINDEX 1
   --#HELP ""
   --#HELPTAG 0
   --#STATE OPERATIONAL
   ::= 412

solartempsensefailoff TRAP-TYPE
   ENTERPRISE enatel
   DESCRIPTION
      "INFORMATION:Solar Converter Temperature Sense Fail has returned to normal"
   --#TYPE "SM32 Trap"
   --#SUMMARY "Solar Converter Temperature Sense Fail NORMAL"
   --#ARGUMENTS { }
   --#SEVERITY INFORMATIONAL
   --#TIMEINDEX 1
   --#HELP ""
   --#HELPTAG 0
   --#STATE OPERATIONAL
   ::= 413

solarinternalauxlowon TRAP-TYPE
   ENTERPRISE enatel
   DESCRIPTION
      "INFORMATION: Solar Converter Internal AUX Low"
   --#TYPE "SM32 Trap"
   --#SUMMARY "Solar Converter Internal AUX Low Active"
   --#ARGUMENTS { }
   --#SEVERITY CRITICAL
   --#TIMEINDEX 1
   --#HELP ""
   --#HELPTAG 0
   --#STATE OPERATIONAL
   ::= 414

solarinternalauxlowoff TRAP-TYPE
   ENTERPRISE enatel
   DESCRIPTION
      "INFORMATION:Solar Converter Internal AUX Low has returned to normal"
   --#TYPE "SM32 Trap"
   --#SUMMARY "Solar Converter Internal AUX Low NORMAL"
   --#ARGUMENTS { }
   --#SEVERITY INFORMATIONAL
   --#TIMEINDEX 1
   --#HELP ""
   --#HELPTAG 0
   --#STATE OPERATIONAL
   ::= 415

solarpanelovervoltson TRAP-TYPE
   ENTERPRISE enatel
   DESCRIPTION
      "INFORMATION: Solar Converter Panel Over-Volts"
   --#TYPE "SM32 Trap"
   --#SUMMARY "Solar Converter Panel Over-Volts Active"
   --#ARGUMENTS { }
   --#SEVERITY CRITICAL
   --#TIMEINDEX 1
   --#HELP ""
   --#HELPTAG 0
   --#STATE OPERATIONAL
   ::= 416

solarpanelovervoltsoff TRAP-TYPE
   ENTERPRISE enatel
   DESCRIPTION
      "INFORMATION:Solar Converter Panel Over-Volts has returned to normal"
   --#TYPE "SM32 Trap"
   --#SUMMARY "Solar Converter Panel Over-Volts NORMAL"
   --#ARGUMENTS { }
   --#SEVERITY INFORMATIONAL
   --#TIMEINDEX 1
   --#HELP ""
   --#HELPTAG 0
   --#STATE OPERATIONAL
   ::= 417

solarpvearthfaulton TRAP-TYPE
   ENTERPRISE enatel
   DESCRIPTION
      "INFORMATION: Solar Converter PV Earth Fault"
   --#TYPE "SM32 Trap"
   --#SUMMARY "Solar Converter PV Earth Fault Active"
   --#ARGUMENTS { }
   --#SEVERITY CRITICAL
   --#TIMEINDEX 1
   --#HELP ""
   --#HELPTAG 0
   --#STATE OPERATIONAL
   ::= 418

solarpvearthfaultoff TRAP-TYPE
   ENTERPRISE enatel
   DESCRIPTION
      "INFORMATION:Solar Converter PV Earth Fault has returned to normal"
   --#TYPE "SM32 Trap"
   --#SUMMARY "Solar Converter PV Earth Fault NORMAL"
   --#ARGUMENTS { }
   --#SEVERITY INFORMATIONAL
   --#TIMEINDEX 1
   --#HELP ""
   --#HELPTAG 0
   --#STATE OPERATIONAL
   ::= 419

solarconvertershutdownon TRAP-TYPE
   ENTERPRISE enatel
   DESCRIPTION
      "INFORMATION: Solar Converter Shutdown"
   --#TYPE "SM32 Trap"
   --#SUMMARY "Solar Converter Shutdown Active"
   --#ARGUMENTS { }
   --#SEVERITY CRITICAL
   --#TIMEINDEX 1
   --#HELP ""
   --#HELPTAG 0
   --#STATE OPERATIONAL
   ::= 420

solarconvertershutdownoff TRAP-TYPE
   ENTERPRISE enatel
   DESCRIPTION
      "INFORMATION:Solar Converter Shutdown has returned to normal"
   --#TYPE "SM32 Trap"
   --#SUMMARY "Solar Converter Shutdown NORMAL"
   --#ARGUMENTS { }
   --#SEVERITY INFORMATIONAL
   --#TIMEINDEX 1
   --#HELP ""
   --#HELPTAG 0
   --#STATE OPERATIONAL
   ::= 421

solareepromfailon TRAP-TYPE
   ENTERPRISE enatel
   DESCRIPTION
      "INFORMATION: Solar Converter EEPROM Fail"
   --#TYPE "SM32 Trap"
   --#SUMMARY "Solar Converter EEPROM Fail Active"
   --#ARGUMENTS { }
   --#SEVERITY CRITICAL
   --#TIMEINDEX 1
   --#HELP ""
   --#HELPTAG 0
   --#STATE OPERATIONAL
   ::= 422

solareepromfailoff TRAP-TYPE
   ENTERPRISE enatel
   DESCRIPTION
      "INFORMATION:Solar Converter EEPROM Fail has returned to normal"
   --#TYPE "SM32 Trap"
   --#SUMMARY "Solar Converter EEPROM Fail NORMAL"
   --#ARGUMENTS { }
   --#SEVERITY INFORMATIONAL
   --#TIMEINDEX 1
   --#HELP ""
   --#HELPTAG 0
   --#STATE OPERATIONAL
   ::= 423

solarsoftstartingon TRAP-TYPE
   ENTERPRISE enatel
   DESCRIPTION
      "INFORMATION: Solar Converter Soft Starting"
   --#TYPE "SM32 Trap"
   --#SUMMARY "Solar Converter Soft Starting Active"
   --#ARGUMENTS { }
   --#SEVERITY CRITICAL
   --#TIMEINDEX 1
   --#HELP ""
   --#HELPTAG 0
   --#STATE OPERATIONAL
   ::= 424

solarsoftstartingoff TRAP-TYPE
   ENTERPRISE enatel
   DESCRIPTION
      "INFORMATION:Solar Converter Soft Starting has returned to normal"
   --#TYPE "SM32 Trap"
   --#SUMMARY "Solar Converter Soft Starting NORMAL"
   --#ARGUMENTS { }
   --#SEVERITY INFORMATIONAL
   --#TIMEINDEX 1
   --#HELP ""
   --#HELPTAG 0
   --#STATE OPERATIONAL
   ::= 425

solarinputlimitedon TRAP-TYPE
   ENTERPRISE enatel
   DESCRIPTION
      "INFORMATION: Solar Converter Input Limited"
   --#TYPE "SM32 Trap"
   --#SUMMARY "Solar Converter Input Limited Active"
   --#ARGUMENTS { }
   --#SEVERITY CRITICAL
   --#TIMEINDEX 1
   --#HELP ""
   --#HELPTAG 0
   --#STATE OPERATIONAL
   ::= 456

solarinputlimitedoff TRAP-TYPE
   ENTERPRISE enatel
   DESCRIPTION
      "INFORMATION:Solar Converter Input Limited has returned to normal"
   --#TYPE "SM32 Trap"
   --#SUMMARY "Solar Converter Input Limited NORMAL"
   --#ARGUMENTS { }
   --#SEVERITY INFORMATIONAL
   --#TIMEINDEX 1
   --#HELP ""
   --#HELPTAG 0
   --#STATE OPERATIONAL
   ::= 457








-- *************** Wind converter alarms ***************

windturbineundervoltson TRAP-TYPE
   ENTERPRISE enatel
   DESCRIPTION
      "INFORMATION: Wind Converter Turbine Under-Volts"
   --#TYPE "SM32 Trap"
   --#SUMMARY "Wind Converter Turbine Under-Volts Active"
   --#ARGUMENTS { }
   --#SEVERITY CRITICAL
   --#TIMEINDEX 1
   --#HELP ""
   --#HELPTAG 0
   --#STATE OPERATIONAL
   ::= 458

windturbineundervoltsoff TRAP-TYPE
   ENTERPRISE enatel
   DESCRIPTION
      "INFORMATION:Wind Converter Turbine Under-Volts has returned to normal"
   --#TYPE "SM32 Trap"
   --#SUMMARY "Wind Converter Turbine Under-Volts NORMAL"
   --#ARGUMENTS { }
   --#SEVERITY INFORMATIONAL
   --#TIMEINDEX 1
   --#HELP ""
   --#HELPTAG 0
   --#STATE OPERATIONAL
   ::= 459


windconverterfailon TRAP-TYPE
   ENTERPRISE enatel
   DESCRIPTION
      "INFORMATION: Wind Converter Fail"
   --#TYPE "SM32 Trap"
   --#SUMMARY "Wind Converter Fail Active"
   --#ARGUMENTS { }
   --#SEVERITY CRITICAL
   --#TIMEINDEX 1
   --#HELP ""
   --#HELPTAG 0
   --#STATE OPERATIONAL
   ::= 460

windconverterfailoff TRAP-TYPE
   ENTERPRISE enatel
   DESCRIPTION
      "INFORMATION:Wind Converter Fail has returned to normal"
   --#TYPE "SM32 Trap"
   --#SUMMARY "Wind Converter Fail NORMAL"
   --#ARGUMENTS { }
   --#SEVERITY INFORMATIONAL
   --#TIMEINDEX 1
   --#HELP ""
   --#HELPTAG 0
   --#STATE OPERATIONAL
   ::= 461


windconverterovertempon TRAP-TYPE
   ENTERPRISE enatel
   DESCRIPTION
      "INFORMATION: Wind Converter Over Temperature"
   --#TYPE "SM32 Trap"
   --#SUMMARY "Wind Converter Over Temperature Active"
   --#ARGUMENTS { }
   --#SEVERITY CRITICAL
   --#TIMEINDEX 1
   --#HELP ""
   --#HELPTAG 0
   --#STATE OPERATIONAL
   ::= 462

windconverterovertempoff TRAP-TYPE
   ENTERPRISE enatel
   DESCRIPTION
      "INFORMATION:Wind Converter Over Temperature has returned to normal"
   --#TYPE "SM32 Trap"
   --#SUMMARY "Wind Converter Over Temperature NORMAL"
   --#ARGUMENTS { }
   --#SEVERITY INFORMATIONAL
   --#TIMEINDEX 1
   --#HELP ""
   --#HELPTAG 0
   --#STATE OPERATIONAL
   ::= 463


windconverterfanfailon TRAP-TYPE
   ENTERPRISE enatel
   DESCRIPTION
      "INFORMATION: Wind Converter Fan Fail"
   --#TYPE "SM32 Trap"
   --#SUMMARY "Wind Converter Fan Fail Active"
   --#ARGUMENTS { }
   --#SEVERITY CRITICAL
   --#TIMEINDEX 1
   --#HELP ""
   --#HELPTAG 0
   --#STATE OPERATIONAL
   ::= 464

windconverterfanfailoff TRAP-TYPE
   ENTERPRISE enatel
   DESCRIPTION
      "INFORMATION:Wind Converter Fan Fail has returned to normal"
   --#TYPE "SM32 Trap"
   --#SUMMARY "Wind Converter Fan Fail NORMAL"
   --#ARGUMENTS { }
   --#SEVERITY INFORMATIONAL
   --#TIMEINDEX 1
   --#HELP ""
   --#HELPTAG 0
   --#STATE OPERATIONAL
   ::= 465

winddevicecurrentlimiton TRAP-TYPE
   ENTERPRISE enatel
   DESCRIPTION
      "INFORMATION: Wind Converter Device Current Limit"
   --#TYPE "SM32 Trap"
   --#SUMMARY "Wind Converter Device Current Limit Active"
   --#ARGUMENTS { }
   --#SEVERITY CRITICAL
   --#TIMEINDEX 1
   --#HELP ""
   --#HELPTAG 0
   --#STATE OPERATIONAL
   ::= 466

winddevicecurrentlimitoff TRAP-TYPE
   ENTERPRISE enatel
   DESCRIPTION
      "INFORMATION:Wind Converter Device Current Limit has returned to normal"
   --#TYPE "SM32 Trap"
   --#SUMMARY "Wind Converter Device Current Limit NORMAL"
   --#ARGUMENTS { }
   --#SEVERITY INFORMATIONAL
   --#TIMEINDEX 1
   --#HELP ""
   --#HELPTAG 0
   --#STATE OPERATIONAL
   ::= 467

windoutputovervoltson TRAP-TYPE
   ENTERPRISE enatel
   DESCRIPTION
      "INFORMATION: Wind Converter Output Overvoltage"
   --#TYPE "SM32 Trap"
   --#SUMMARY "Wind Converter Output Overvoltage Active"
   --#ARGUMENTS { }
   --#SEVERITY CRITICAL
   --#TIMEINDEX 1
   --#HELP ""
   --#HELPTAG 0
   --#STATE OPERATIONAL
   ::= 468

windoutputovervoltsoff TRAP-TYPE
   ENTERPRISE enatel
   DESCRIPTION
      "INFORMATION:Wind Converter Output Overvoltage has returned to normal"
   --#TYPE "SM32 Trap"
   --#SUMMARY "Wind Converter Output Overvoltage NORMAL"
   --#ARGUMENTS { }
   --#SEVERITY INFORMATIONAL
   --#TIMEINDEX 1
   --#HELP ""
   --#HELPTAG 0
   --#STATE OPERATIONAL
   ::= 469


windconstantvoltageon TRAP-TYPE
   ENTERPRISE enatel
   DESCRIPTION
      "INFORMATION: Wind Converter Constant Voltage"
   --#TYPE "SM32 Trap"
   --#SUMMARY "Wind Converter Constant Voltage Active"
   --#ARGUMENTS { }
   --#SEVERITY CRITICAL
   --#TIMEINDEX 1
   --#HELP ""
   --#HELPTAG 0
   --#STATE OPERATIONAL
   ::= 470

windconstantvoltageoff TRAP-TYPE
   ENTERPRISE enatel
   DESCRIPTION
      "INFORMATION:Wind Converter Constant Voltage has returned to normal"
   --#TYPE "SM32 Trap"
   --#SUMMARY "Wind Converter Constant Voltage NORMAL"
   --#ARGUMENTS { }
   --#SEVERITY INFORMATIONAL
   --#TIMEINDEX 1
   --#HELP ""
   --#HELPTAG 0
   --#STATE OPERATIONAL
   ::= 471

windpostmateon TRAP-TYPE
   ENTERPRISE enatel
   DESCRIPTION
      "INFORMATION: Wind Converter Postmate"
   --#TYPE "SM32 Trap"
   --#SUMMARY "Wind Converter Postmate Active"
   --#ARGUMENTS { }
   --#SEVERITY CRITICAL
   --#TIMEINDEX 1
   --#HELP ""
   --#HELPTAG 0
   --#STATE OPERATIONAL
   ::= 472

windpostmateoff TRAP-TYPE
   ENTERPRISE enatel
   DESCRIPTION
      "INFORMATION:Wind Converter Postmate has returned to normal"
   --#TYPE "SM32 Trap"
   --#SUMMARY "Wind Converter Postmate NORMAL"
   --#ARGUMENTS { }
   --#SEVERITY INFORMATIONAL
   --#TIMEINDEX 1
   --#HELP ""
   --#HELPTAG 0
   --#STATE OPERATIONAL
   ::= 473

windbackflowprotecton TRAP-TYPE
   ENTERPRISE enatel
   DESCRIPTION
      "INFORMATION: Wind Converter Current Backflow Protection"
   --#TYPE "SM32 Trap"
   --#SUMMARY "Wind Converter Current Backflow Protection Active"
   --#ARGUMENTS { }
   --#SEVERITY CRITICAL
   --#TIMEINDEX 1
   --#HELP ""
   --#HELPTAG 0
   --#STATE OPERATIONAL
   ::= 474

windbackflowprotectoff TRAP-TYPE
   ENTERPRISE enatel
   DESCRIPTION
      "INFORMATION:Wind Converter Current Backflow Protection has returned to normal"
   --#TYPE "SM32 Trap"
   --#SUMMARY "Wind Converter Current Backflow Protection NORMAL"
   --#ARGUMENTS { }
   --#SEVERITY INFORMATIONAL
   --#TIMEINDEX 1
   --#HELP ""
   --#HELPTAG 0
   --#STATE OPERATIONAL
   ::= 475

windtempsensefailon TRAP-TYPE
   ENTERPRISE enatel
   DESCRIPTION
      "INFORMATION: Wind Converter Temperature Sense Fail"
   --#TYPE "SM32 Trap"
   --#SUMMARY "Wind Converter Temperature Sense Fail Active"
   --#ARGUMENTS { }
   --#SEVERITY CRITICAL
   --#TIMEINDEX 1
   --#HELP ""
   --#HELPTAG 0
   --#STATE OPERATIONAL
   ::= 476

windtempsensefailoff TRAP-TYPE
   ENTERPRISE enatel
   DESCRIPTION
      "INFORMATION:Wind Converter Temperature Sense Fail has returned to normal"
   --#TYPE "SM32 Trap"
   --#SUMMARY "Wind Converter Temperature Sense Fail NORMAL"
   --#ARGUMENTS { }
   --#SEVERITY INFORMATIONAL
   --#TIMEINDEX 1
   --#HELP ""
   --#HELPTAG 0
   --#STATE OPERATIONAL
   ::= 477

windinternalauxlowon TRAP-TYPE
   ENTERPRISE enatel
   DESCRIPTION
      "INFORMATION: Wind Converter Internal AUX Low"
   --#TYPE "SM32 Trap"
   --#SUMMARY "Wind Converter Internal AUX Low Active"
   --#ARGUMENTS { }
   --#SEVERITY CRITICAL
   --#TIMEINDEX 1
   --#HELP ""
   --#HELPTAG 0
   --#STATE OPERATIONAL
   ::= 478

windinternalauxlowoff TRAP-TYPE
   ENTERPRISE enatel
   DESCRIPTION
      "INFORMATION:Wind Converter Internal AUX Low has returned to normal"
   --#TYPE "SM32 Trap"
   --#SUMMARY "Wind Converter Internal AUX Low NORMAL"
   --#ARGUMENTS { }
   --#SEVERITY INFORMATIONAL
   --#TIMEINDEX 1
   --#HELP ""
   --#HELPTAG 0
   --#STATE OPERATIONAL
   ::= 479

windturbineovervoltson TRAP-TYPE
   ENTERPRISE enatel
   DESCRIPTION
      "INFORMATION: Wind Converter Turbine Over-Volts"
   --#TYPE "SM32 Trap"
   --#SUMMARY "Wind Converter Turbine Over-Volts Active"
   --#ARGUMENTS { }
   --#SEVERITY CRITICAL
   --#TIMEINDEX 1
   --#HELP ""
   --#HELPTAG 0
   --#STATE OPERATIONAL
   ::= 480

windturbineovervoltsoff TRAP-TYPE
   ENTERPRISE enatel
   DESCRIPTION
      "INFORMATION:Wind Converter Turbine Over-Volts has returned to normal"
   --#TYPE "SM32 Trap"
   --#SUMMARY "Wind Converter Turbine Over-Volts NORMAL"
   --#ARGUMENTS { }
   --#SEVERITY INFORMATIONAL
   --#TIMEINDEX 1
   --#HELP ""
   --#HELPTAG 0
   --#STATE OPERATIONAL
   ::= 481

windturbineearthfaulton TRAP-TYPE
   ENTERPRISE enatel
   DESCRIPTION
      "INFORMATION: Wind Converter Turbine Earth Fault"
   --#TYPE "SM32 Trap"
   --#SUMMARY "Wind Converter Turbine Earth Fault Active"
   --#ARGUMENTS { }
   --#SEVERITY CRITICAL
   --#TIMEINDEX 1
   --#HELP ""
   --#HELPTAG 0
   --#STATE OPERATIONAL
   ::= 482

windturbineearthfaultoff TRAP-TYPE
   ENTERPRISE enatel
   DESCRIPTION
      "INFORMATION:Wind Converter Turbine Earth Fault has returned to normal"
   --#TYPE "SM32 Trap"
   --#SUMMARY "Wind Converter Turbine Earth Fault NORMAL"
   --#ARGUMENTS { }
   --#SEVERITY INFORMATIONAL
   --#TIMEINDEX 1
   --#HELP ""
   --#HELPTAG 0
   --#STATE OPERATIONAL
   ::= 483

windconvertershutdownon TRAP-TYPE
   ENTERPRISE enatel
   DESCRIPTION
      "INFORMATION: Wind Converter Shutdown"
   --#TYPE "SM32 Trap"
   --#SUMMARY "Wind Converter Shutdown Active"
   --#ARGUMENTS { }
   --#SEVERITY CRITICAL
   --#TIMEINDEX 1
   --#HELP ""
   --#HELPTAG 0
   --#STATE OPERATIONAL
   ::= 484

windconvertershutdownoff TRAP-TYPE
   ENTERPRISE enatel
   DESCRIPTION
      "INFORMATION:Wind Converter Shutdown has returned to normal"
   --#TYPE "SM32 Trap"
   --#SUMMARY "Wind Converter Shutdown NORMAL"
   --#ARGUMENTS { }
   --#SEVERITY INFORMATIONAL
   --#TIMEINDEX 1
   --#HELP ""
   --#HELPTAG 0
   --#STATE OPERATIONAL
   ::= 485

windeepromfailon TRAP-TYPE
   ENTERPRISE enatel
   DESCRIPTION
      "INFORMATION: Wind Converter EEPROM Fail"
   --#TYPE "SM32 Trap"
   --#SUMMARY "Wind Converter EEPROM Fail Active"
   --#ARGUMENTS { }
   --#SEVERITY CRITICAL
   --#TIMEINDEX 1
   --#HELP ""
   --#HELPTAG 0
   --#STATE OPERATIONAL
   ::= 486

windeepromfailoff TRAP-TYPE
   ENTERPRISE enatel
   DESCRIPTION
      "INFORMATION:Wind Converter EEPROM Fail has returned to normal"
   --#TYPE "SM32 Trap"
   --#SUMMARY "Wind Converter EEPROM Fail NORMAL"
   --#ARGUMENTS { }
   --#SEVERITY INFORMATIONAL
   --#TIMEINDEX 1
   --#HELP ""
   --#HELPTAG 0
   --#STATE OPERATIONAL
   ::= 487

windsoftstartingon TRAP-TYPE
   ENTERPRISE enatel
   DESCRIPTION
      "INFORMATION: Wind Converter Soft Starting"
   --#TYPE "SM32 Trap"
   --#SUMMARY "Wind Converter Soft Starting Active"
   --#ARGUMENTS { }
   --#SEVERITY CRITICAL
   --#TIMEINDEX 1
   --#HELP ""
   --#HELPTAG 0
   --#STATE OPERATIONAL
   ::= 488

windsoftstartingoff TRAP-TYPE
   ENTERPRISE enatel
   DESCRIPTION
      "INFORMATION:Wind Converter Soft Starting has returned to normal"
   --#TYPE "SM32 Trap"
   --#SUMMARY "Wind Converter Soft Starting NORMAL"
   --#ARGUMENTS { }
   --#SEVERITY INFORMATIONAL
   --#TIMEINDEX 1
   --#HELP ""
   --#HELPTAG 0
   --#STATE OPERATIONAL
   ::= 489

windinputlimitedon TRAP-TYPE
   ENTERPRISE enatel
   DESCRIPTION
      "INFORMATION: Wind Converter Input Limited"
   --#TYPE "SM32 Trap"
   --#SUMMARY "Wind Converter Input Limited Active"
   --#ARGUMENTS { }
   --#SEVERITY CRITICAL
   --#TIMEINDEX 1
   --#HELP ""
   --#HELPTAG 0
   --#STATE OPERATIONAL
   ::= 520

windinputlimitedoff TRAP-TYPE
   ENTERPRISE enatel
   DESCRIPTION
      "INFORMATION:Wind Converter Input Limited has returned to normal"
   --#TYPE "SM32 Trap"
   --#SUMMARY "Wind Converter Input Limited NORMAL"
   --#ARGUMENTS { }
   --#SEVERITY INFORMATIONAL
   --#TIMEINDEX 1
   --#HELP ""
   --#HELPTAG 0
   --#STATE OPERATIONAL
   ::= 521




-- ****************************************************************************
--				Hybrid Traps
-- ****************************************************************************


almhybpwrfixedactive TRAP-TYPE
   ENTERPRISE enatel
      DESCRIPTION
      "INFORMATION: Fixed Power "
   --#TYPE "SM32 Trap"
   --#SUMMARY "Fixed Power Active"
   --#ARGUMENTS { }
   --#SEVERITY CRITICAL
   --#TIMEINDEX 1
   --#HELP ""
   --#HELPTAG 0
   --#STATE OPERATIONAL
   ::= 524

almhybpwrfixedinactive TRAP-TYPE
   ENTERPRISE enatel
      DESCRIPTION
      "INFORMATION: Fixed Power has returned to normal"
   --#TYPE "SM32 Trap"
   --#SUMMARY "Fixed Power NORMAL"
   --#ARGUMENTS { }
   --#SEVERITY INFORMATIONAL
   --#TIMEINDEX 1
   --#HELP ""
   --#HELPTAG 0
   --#STATE OPERATIONAL
   ::= 525

almhybgenrunactive TRAP-TYPE
   ENTERPRISE enatel
      DESCRIPTION
      "INFORMATION: Generator Running "
   --#TYPE "SM32 Trap"
   --#SUMMARY "Generator Running Active"
   --#ARGUMENTS { }
   --#SEVERITY CRITICAL
   --#TIMEINDEX 1
   --#HELP ""
   --#HELPTAG 0
   --#STATE OPERATIONAL
   ::= 528

almhybgenruninactive TRAP-TYPE
   ENTERPRISE enatel
      DESCRIPTION
      "INFORMATION: Generator Running has returned to normal"
   --#TYPE "SM32 Trap"
   --#SUMMARY "Generator Running NORMAL"
   --#ARGUMENTS { }
   --#SEVERITY INFORMATIONAL
   --#TIMEINDEX 1
   --#HELP ""
   --#HELPTAG 0
   --#STATE OPERATIONAL
   ::= 529

almhybgenstopactive TRAP-TYPE
   ENTERPRISE enatel
      DESCRIPTION
      "INFORMATION: Generator Stopped "
   --#TYPE "SM32 Trap"
   --#SUMMARY "Generator Stopped Active"
   --#ARGUMENTS { }
   --#SEVERITY CRITICAL
   --#TIMEINDEX 1
   --#HELP ""
   --#HELPTAG 0
   --#STATE OPERATIONAL
   ::= 530

almhybgenstopinactive TRAP-TYPE
   ENTERPRISE enatel
      DESCRIPTION
      "INFORMATION: Generator Stopped has returned to normal"
   --#TYPE "SM32 Trap"
   --#SUMMARY "Generator Stopped NORMAL"
   --#ARGUMENTS { }
   --#SEVERITY INFORMATIONAL
   --#TIMEINDEX 1
   --#HELP ""
   --#HELPTAG 0
   --#STATE OPERATIONAL
   ::= 531

almhybmpprpdrepactive TRAP-TYPE
   ENTERPRISE enatel
      DESCRIPTION
      "INFORMATION: MPP Rapid Repeat "
   --#TYPE "SM32 Trap"
   --#SUMMARY "MPP Rapid Repeat Active"
   --#ARGUMENTS { }
   --#SEVERITY CRITICAL
   --#TIMEINDEX 1
   --#HELP ""
   --#HELPTAG 0
   --#STATE OPERATIONAL
   ::= 532

almhybmpprpdrepinactive TRAP-TYPE
   ENTERPRISE enatel
      DESCRIPTION
      "INFORMATION: MPP Rapid Repeat has returned to normal"
   --#TYPE "SM32 Trap"
   --#SUMMARY "MPP Rapid Repeat NORMAL"
   --#ARGUMENTS { }
   --#SEVERITY INFORMATIONAL
   --#TIMEINDEX 1
   --#HELP ""
   --#HELPTAG 0
   --#STATE OPERATIONAL
   ::= 533

almhybstallpwractive TRAP-TYPE
   ENTERPRISE enatel
      DESCRIPTION
      "INFORMATION: Stall Power "
   --#TYPE "SM32 Trap"
   --#SUMMARY "Stall Power Active"
   --#ARGUMENTS { }
   --#SEVERITY CRITICAL
   --#TIMEINDEX 1
   --#HELP ""
   --#HELPTAG 0
   --#STATE OPERATIONAL
   ::= 536

almhybstallpwrinactive TRAP-TYPE
   ENTERPRISE enatel
      DESCRIPTION
      "INFORMATION: Stall Power has returned to normal"
   --#TYPE "SM32 Trap"
   --#SUMMARY "Stall Power NORMAL"
   --#ARGUMENTS { }
   --#SEVERITY INFORMATIONAL
   --#TIMEINDEX 1
   --#HELP ""
   --#HELPTAG 0
   --#STATE OPERATIONAL
   ::= 537

almhybmppprevfailactive TRAP-TYPE
   ENTERPRISE enatel
      DESCRIPTION
      "INFORMATION: Previous MPP Fail "
   --#TYPE "SM32 Trap"
   --#SUMMARY "Previous MPP Fail Active"
   --#ARGUMENTS { }
   --#SEVERITY CRITICAL
   --#TIMEINDEX 1
   --#HELP ""
   --#HELPTAG 0
   --#STATE OPERATIONAL
   ::= 542

almhybmppprevfailinactive TRAP-TYPE
   ENTERPRISE enatel
      DESCRIPTION
      "INFORMATION: Previous MPP Fail has returned to normal"
   --#TYPE "SM32 Trap"
   --#SUMMARY "Previous MPP Fail NORMAL"
   --#ARGUMENTS { }
   --#SEVERITY INFORMATIONAL
   --#TIMEINDEX 1
   --#HELP ""
   --#HELPTAG 0
   --#STATE OPERATIONAL
   ::= 543

almhybbatmcbopenactive TRAP-TYPE
   ENTERPRISE enatel
      DESCRIPTION
      "INFORMATION: Battery MCB Open "
   --#TYPE "SM32 Trap"
   --#SUMMARY "Battery MCB Open Active"
   --#ARGUMENTS { }
   --#SEVERITY CRITICAL
   --#TIMEINDEX 1
   --#HELP ""
   --#HELPTAG 0
   --#STATE OPERATIONAL
   ::= 560

almhybbatmcbopeninactive TRAP-TYPE
   ENTERPRISE enatel
      DESCRIPTION
      "INFORMATION: Battery MCB Open has returned to normal"
   --#TYPE "SM32 Trap"
   --#SUMMARY "Battery MCB Open NORMAL"
   --#ARGUMENTS { }
   --#SEVERITY INFORMATIONAL
   --#TIMEINDEX 1
   --#HELP ""
   --#HELPTAG 0
   --#STATE OPERATIONAL
   ::= 561

almhybacmgenfailactive TRAP-TYPE
   ENTERPRISE enatel
      DESCRIPTION
      "INFORMATION: Generator ACM Fail "
   --#TYPE "SM32 Trap"
   --#SUMMARY "Generator ACM Fail Active"
   --#ARGUMENTS { }
   --#SEVERITY CRITICAL
   --#TIMEINDEX 1
   --#HELP ""
   --#HELPTAG 0
   --#STATE OPERATIONAL
   ::= 570

almhybacmgenfailinactive TRAP-TYPE
   ENTERPRISE enatel
      DESCRIPTION
      "INFORMATION: Generator ACM Fail has returned to normal"
   --#TYPE "SM32 Trap"
   --#SUMMARY "Generator ACM Fail NORMAL"
   --#ARGUMENTS { }
   --#SEVERITY INFORMATIONAL
   --#TIMEINDEX 1
   --#HELP ""
   --#HELPTAG 0
   --#STATE OPERATIONAL
   ::= 571

almhybgridctdfailactive TRAP-TYPE
   ENTERPRISE enatel
      DESCRIPTION
      "INFORMATION: Grid Fail (Conditioned) "
   --#TYPE "SM32 Trap"
   --#SUMMARY "Grid Fail (Conditioned) Active"
   --#ARGUMENTS { }
   --#SEVERITY CRITICAL
   --#TIMEINDEX 1
   --#HELP ""
   --#HELPTAG 0
   --#STATE OPERATIONAL
   ::= 576

almhybgridctdfailinactive TRAP-TYPE
   ENTERPRISE enatel
      DESCRIPTION
      "INFORMATION: Grid Fail (Conditioned) has returned to normal"
   --#TYPE "SM32 Trap"
   --#SUMMARY "Grid Fail (Conditioned) NORMAL"
   --#ARGUMENTS { }
   --#SEVERITY INFORMATIONAL
   --#TIMEINDEX 1
   --#HELP ""
   --#HELPTAG 0
   --#STATE OPERATIONAL
   ::= 577

almhybigoppwractive TRAP-TYPE
   ENTERPRISE enatel
      DESCRIPTION
      "INFORMATION: Ignoring Optimal Power % "
   --#TYPE "SM32 Trap"
   --#SUMMARY "Ignoring Optimal Power % Active"
   --#ARGUMENTS { }
   --#SEVERITY CRITICAL
   --#TIMEINDEX 1
   --#HELP ""
   --#HELPTAG 0
   --#STATE OPERATIONAL
   ::= 584

almhybigoppwrinactive TRAP-TYPE
   ENTERPRISE enatel
      DESCRIPTION
      "INFORMATION: Ignoring Optimal Power % has returned to normal"
   --#TYPE "SM32 Trap"
   --#SUMMARY "Ignoring Optimal Power % NORMAL"
   --#ARGUMENTS { }
   --#SEVERITY INFORMATIONAL
   --#TIMEINDEX 1
   --#HELP ""
   --#HELPTAG 0
   --#STATE OPERATIONAL
   ::= 585

almhybbatmissingactive TRAP-TYPE
   ENTERPRISE enatel
      DESCRIPTION
      "INFORMATION: Battery Missing Alarm "
   --#TYPE "SM32 Trap"
   --#SUMMARY "Battery Missing Alarm Active"
   --#ARGUMENTS { }
   --#SEVERITY CRITICAL
   --#TIMEINDEX 1
   --#HELP ""
   --#HELPTAG 0
   --#STATE OPERATIONAL
   ::= 604

almhybbatmissinginactive TRAP-TYPE
   ENTERPRISE enatel
      DESCRIPTION
      "INFORMATION: Battery Missing Alarm has returned to normal"
   --#TYPE "SM32 Trap"
   --#SUMMARY "Battery Missing Alarm NORMAL"
   --#ARGUMENTS { }
   --#SEVERITY INFORMATIONAL
   --#TIMEINDEX 1
   --#HELP ""
   --#HELPTAG 0
   --#STATE OPERATIONAL
   ::= 605

almhybgen1oillowactive TRAP-TYPE
   ENTERPRISE enatel
      DESCRIPTION
      "INFORMATION: Generator 1 Low Oil "
   --#TYPE "SM32 Trap"
   --#SUMMARY "Generator 1 Low Oil Active"
   --#ARGUMENTS { }
   --#SEVERITY CRITICAL
   --#TIMEINDEX 1
   --#HELP ""
   --#HELPTAG 0
   --#STATE OPERATIONAL
   ::= 606

almhybgen1oillowinactive TRAP-TYPE
   ENTERPRISE enatel
      DESCRIPTION
      "INFORMATION: Generator 1 Low Oil has returned to normal"
   --#TYPE "SM32 Trap"
   --#SUMMARY "Generator 1 Low Oil NORMAL"
   --#ARGUMENTS { }
   --#SEVERITY INFORMATIONAL
   --#TIMEINDEX 1
   --#HELP ""
   --#HELPTAG 0
   --#STATE OPERATIONAL
   ::= 607

almhybgen1thighactive TRAP-TYPE
   ENTERPRISE enatel
      DESCRIPTION
      "INFORMATION: Generator 1 High Temp. "
   --#TYPE "SM32 Trap"
   --#SUMMARY "Generator 1 High Temp. Active"
   --#ARGUMENTS { }
   --#SEVERITY CRITICAL
   --#TIMEINDEX 1
   --#HELP ""
   --#HELPTAG 0
   --#STATE OPERATIONAL
   ::= 608

almhybgen1thighinactive TRAP-TYPE
   ENTERPRISE enatel
      DESCRIPTION
      "INFORMATION: Generator 1 High Temp. has returned to normal"
   --#TYPE "SM32 Trap"
   --#SUMMARY "Generator 1 High Temp. NORMAL"
   --#ARGUMENTS { }
   --#SEVERITY INFORMATIONAL
   --#TIMEINDEX 1
   --#HELP ""
   --#HELPTAG 0
   --#STATE OPERATIONAL
   ::= 609

almhybgen1battlowactive TRAP-TYPE
   ENTERPRISE enatel
      DESCRIPTION
      "INFORMATION: Generator 1 Low Batt. "
   --#TYPE "SM32 Trap"
   --#SUMMARY "Generator 1 Low Batt. Active"
   --#ARGUMENTS { }
   --#SEVERITY CRITICAL
   --#TIMEINDEX 1
   --#HELP ""
   --#HELPTAG 0
   --#STATE OPERATIONAL
   ::= 610

almhybgen1battlowinactive TRAP-TYPE
   ENTERPRISE enatel
      DESCRIPTION
      "INFORMATION: Generator 1 Low Batt. has returned to normal"
   --#TYPE "SM32 Trap"
   --#SUMMARY "Generator 1 Low Batt. NORMAL"
   --#ARGUMENTS { }
   --#SEVERITY INFORMATIONAL
   --#TIMEINDEX 1
   --#HELP ""
   --#HELPTAG 0
   --#STATE OPERATIONAL
   ::= 611

almhybgen2oillowactive TRAP-TYPE
   ENTERPRISE enatel
      DESCRIPTION
      "INFORMATION: Generator 2 Low Oil "
   --#TYPE "SM32 Trap"
   --#SUMMARY "Generator 2 Low Oil Active"
   --#ARGUMENTS { }
   --#SEVERITY CRITICAL
   --#TIMEINDEX 1
   --#HELP ""
   --#HELPTAG 0
   --#STATE OPERATIONAL
   ::= 612

almhybgen2oillowinactive TRAP-TYPE
   ENTERPRISE enatel
      DESCRIPTION
      "INFORMATION: Generator 2 Low Oil has returned to normal"
   --#TYPE "SM32 Trap"
   --#SUMMARY "Generator 2 Low Oil NORMAL"
   --#ARGUMENTS { }
   --#SEVERITY INFORMATIONAL
   --#TIMEINDEX 1
   --#HELP ""
   --#HELPTAG 0
   --#STATE OPERATIONAL
   ::= 613

almhybgen2thighactive TRAP-TYPE
   ENTERPRISE enatel
      DESCRIPTION
      "INFORMATION: Generator 2 High Temp. "
   --#TYPE "SM32 Trap"
   --#SUMMARY "Generator 2 High Temp. Active"
   --#ARGUMENTS { }
   --#SEVERITY CRITICAL
   --#TIMEINDEX 1
   --#HELP ""
   --#HELPTAG 0
   --#STATE OPERATIONAL
   ::= 614

almhybgen2thighinactive TRAP-TYPE
   ENTERPRISE enatel
      DESCRIPTION
      "INFORMATION: Generator 2 High Temp. has returned to normal"
   --#TYPE "SM32 Trap"
   --#SUMMARY "Generator 2 High Temp. NORMAL"
   --#ARGUMENTS { }
   --#SEVERITY INFORMATIONAL
   --#TIMEINDEX 1
   --#HELP ""
   --#HELPTAG 0
   --#STATE OPERATIONAL
   ::= 615

almhybgen2battlowactive TRAP-TYPE
   ENTERPRISE enatel
      DESCRIPTION
      "INFORMATION: Generator 2 Low Batt. "
   --#TYPE "SM32 Trap"
   --#SUMMARY "Generator 2 Low Batt. Active"
   --#ARGUMENTS { }
   --#SEVERITY CRITICAL
   --#TIMEINDEX 1
   --#HELP ""
   --#HELPTAG 0
   --#STATE OPERATIONAL
   ::= 616

almhybgen2battlowinactive TRAP-TYPE
   ENTERPRISE enatel
      DESCRIPTION
      "INFORMATION: Generator 2 Low Batt. has returned to normal"
   --#TYPE "SM32 Trap"
   --#SUMMARY "Generator 2 Low Batt. NORMAL"
   --#ARGUMENTS { }
   --#SEVERITY INFORMATIONAL
   --#TIMEINDEX 1
   --#HELP ""
   --#HELPTAG 0
   --#STATE OPERATIONAL
   ::= 617

almhybgenallgallactive TRAP-TYPE
   ENTERPRISE enatel
      DESCRIPTION
      "INFORMATION: All Generators Fail "
   --#TYPE "SM32 Trap"
   --#SUMMARY "All Generators Fail Active"
   --#ARGUMENTS { }
   --#SEVERITY CRITICAL
   --#TIMEINDEX 1
   --#HELP ""
   --#HELPTAG 0
   --#STATE OPERATIONAL
   ::= 620

almhybgenallgallinactive TRAP-TYPE
   ENTERPRISE enatel
      DESCRIPTION
      "INFORMATION: All Generators Fail has returned to normal"
   --#TYPE "SM32 Trap"
   --#SUMMARY "All Generators Fail NORMAL"
   --#ARGUMENTS { }
   --#SEVERITY INFORMATIONAL
   --#TIMEINDEX 1
   --#HELP ""
   --#HELPTAG 0
   --#STATE OPERATIONAL
   ::= 621

almhybgen1failactive TRAP-TYPE
   ENTERPRISE enatel
      DESCRIPTION
      "INFORMATION: Generator 1 Fail "
   --#TYPE "SM32 Trap"
   --#SUMMARY "Generator 1 Fail Active"
   --#ARGUMENTS { }
   --#SEVERITY CRITICAL
   --#TIMEINDEX 1
   --#HELP ""
   --#HELPTAG 0
   --#STATE OPERATIONAL
   ::= 622

almhybgen1failinactive TRAP-TYPE
   ENTERPRISE enatel
      DESCRIPTION
      "INFORMATION: Generator 1 Fail has returned to normal"
   --#TYPE "SM32 Trap"
   --#SUMMARY "Generator 1 Fail NORMAL"
   --#ARGUMENTS { }
   --#SEVERITY INFORMATIONAL
   --#TIMEINDEX 1
   --#HELP ""
   --#HELPTAG 0
   --#STATE OPERATIONAL
   ::= 623

almhybgen1phasefailactive TRAP-TYPE
   ENTERPRISE enatel
      DESCRIPTION
      "INFORMATION: Generator 1 Phase Fail "
   --#TYPE "SM32 Trap"
   --#SUMMARY "Generator 1 Phase Fail Active"
   --#ARGUMENTS { }
   --#SEVERITY CRITICAL
   --#TIMEINDEX 1
   --#HELP ""
   --#HELPTAG 0
   --#STATE OPERATIONAL
   ::= 624

almhybgen1phasefailinactive TRAP-TYPE
   ENTERPRISE enatel
      DESCRIPTION
      "INFORMATION: Generator 1 Phase Fail has returned to normal"
   --#TYPE "SM32 Trap"
   --#SUMMARY "Generator 1 Phase Fail NORMAL"
   --#ARGUMENTS { }
   --#SEVERITY INFORMATIONAL
   --#TIMEINDEX 1
   --#HELP ""
   --#HELPTAG 0
   --#STATE OPERATIONAL
   ::= 625

almhybgen1lowpwractive TRAP-TYPE
   ENTERPRISE enatel
      DESCRIPTION
      "INFORMATION: Generator 1 Low Power "
   --#TYPE "SM32 Trap"
   --#SUMMARY "Generator 1 Low Power Active"
   --#ARGUMENTS { }
   --#SEVERITY CRITICAL
   --#TIMEINDEX 1
   --#HELP ""
   --#HELPTAG 0
   --#STATE OPERATIONAL
   ::= 626

almhybgen1lowpwrinactive TRAP-TYPE
   ENTERPRISE enatel
      DESCRIPTION
      "INFORMATION: Generator 1 Low Power has returned to normal"
   --#TYPE "SM32 Trap"
   --#SUMMARY "Generator 1 Low Power NORMAL"
   --#ARGUMENTS { }
   --#SEVERITY INFORMATIONAL
   --#TIMEINDEX 1
   --#HELP ""
   --#HELPTAG 0
   --#STATE OPERATIONAL
   ::= 627

almhybgen1urglowpwractive TRAP-TYPE
   ENTERPRISE enatel
      DESCRIPTION
      "INFORMATION: Generator 1 Urgent Low Power "
   --#TYPE "SM32 Trap"
   --#SUMMARY "Generator 1 Urgent Low Power Active"
   --#ARGUMENTS { }
   --#SEVERITY CRITICAL
   --#TIMEINDEX 1
   --#HELP ""
   --#HELPTAG 0
   --#STATE OPERATIONAL
   ::= 628

almhybgen1urglowpwrinactive TRAP-TYPE
   ENTERPRISE enatel
      DESCRIPTION
      "INFORMATION: Generator 1 Urgent Low Power has returned to normal"
   --#TYPE "SM32 Trap"
   --#SUMMARY "Generator 1 Urgent Low Power NORMAL"
   --#ARGUMENTS { }
   --#SEVERITY INFORMATIONAL
   --#TIMEINDEX 1
   --#HELP ""
   --#HELPTAG 0
   --#STATE OPERATIONAL
   ::= 629

almhybgen1ovrrnactive TRAP-TYPE
   ENTERPRISE enatel
      DESCRIPTION
      "INFORMATION: Generator 1 Overrun "
   --#TYPE "SM32 Trap"
   --#SUMMARY "Generator 1 Overrun Active"
   --#ARGUMENTS { }
   --#SEVERITY CRITICAL
   --#TIMEINDEX 1
   --#HELP ""
   --#HELPTAG 0
   --#STATE OPERATIONAL
   ::= 630

almhybgen1ovrrninactive TRAP-TYPE
   ENTERPRISE enatel
      DESCRIPTION
      "INFORMATION: Generator 1 Overrun has returned to normal"
   --#TYPE "SM32 Trap"
   --#SUMMARY "Generator 1 Overrun NORMAL"
   --#ARGUMENTS { }
   --#SEVERITY INFORMATIONAL
   --#TIMEINDEX 1
   --#HELP ""
   --#HELPTAG 0
   --#STATE OPERATIONAL
   ::= 631

almhybgen2failactive TRAP-TYPE
   ENTERPRISE enatel
      DESCRIPTION
      "INFORMATION: Generator 2 Fail "
   --#TYPE "SM32 Trap"
   --#SUMMARY "Generator 2 Fail Active"
   --#ARGUMENTS { }
   --#SEVERITY CRITICAL
   --#TIMEINDEX 1
   --#HELP ""
   --#HELPTAG 0
   --#STATE OPERATIONAL
   ::= 632

almhybgen2failinactive TRAP-TYPE
   ENTERPRISE enatel
      DESCRIPTION
      "INFORMATION: Generator 2 Fail has returned to normal"
   --#TYPE "SM32 Trap"
   --#SUMMARY "Generator 2 Fail NORMAL"
   --#ARGUMENTS { }
   --#SEVERITY INFORMATIONAL
   --#TIMEINDEX 1
   --#HELP ""
   --#HELPTAG 0
   --#STATE OPERATIONAL
   ::= 633

almhybgen2phasefailactive TRAP-TYPE
   ENTERPRISE enatel
      DESCRIPTION
      "INFORMATION: Generator 2 Phase Fail "
   --#TYPE "SM32 Trap"
   --#SUMMARY "Generator 2 Phase Fail Active"
   --#ARGUMENTS { }
   --#SEVERITY CRITICAL
   --#TIMEINDEX 1
   --#HELP ""
   --#HELPTAG 0
   --#STATE OPERATIONAL
   ::= 634

almhybgen2phasefailinactive TRAP-TYPE
   ENTERPRISE enatel
      DESCRIPTION
      "INFORMATION: Generator 2 Phase Fail has returned to normal"
   --#TYPE "SM32 Trap"
   --#SUMMARY "Generator 2 Phase Fail NORMAL"
   --#ARGUMENTS { }
   --#SEVERITY INFORMATIONAL
   --#TIMEINDEX 1
   --#HELP ""
   --#HELPTAG 0
   --#STATE OPERATIONAL
   ::= 635

almhybgen2lowpwractive TRAP-TYPE
   ENTERPRISE enatel
      DESCRIPTION
      "INFORMATION: Generator 2 Low Power "
   --#TYPE "SM32 Trap"
   --#SUMMARY "Generator 2 Low Power Active"
   --#ARGUMENTS { }
   --#SEVERITY CRITICAL
   --#TIMEINDEX 1
   --#HELP ""
   --#HELPTAG 0
   --#STATE OPERATIONAL
   ::= 636

almhybgen2lowpwrinactive TRAP-TYPE
   ENTERPRISE enatel
      DESCRIPTION
      "INFORMATION: Generator 2 Low Power has returned to normal"
   --#TYPE "SM32 Trap"
   --#SUMMARY "Generator 2 Low Power NORMAL"
   --#ARGUMENTS { }
   --#SEVERITY INFORMATIONAL
   --#TIMEINDEX 1
   --#HELP ""
   --#HELPTAG 0
   --#STATE OPERATIONAL
   ::= 637

almhybgen2urglowpwractive TRAP-TYPE
   ENTERPRISE enatel
      DESCRIPTION
      "INFORMATION: Generator 2 Urgent Low Power "
   --#TYPE "SM32 Trap"
   --#SUMMARY "Generator 2 Urgent Low Power Active"
   --#ARGUMENTS { }
   --#SEVERITY CRITICAL
   --#TIMEINDEX 1
   --#HELP ""
   --#HELPTAG 0
   --#STATE OPERATIONAL
   ::= 638

almhybgen2urglowpwrinactive TRAP-TYPE
   ENTERPRISE enatel
      DESCRIPTION
      "INFORMATION: Generator 2 Urgent Low Power has returned to normal"
   --#TYPE "SM32 Trap"
   --#SUMMARY "Generator 2 Urgent Low Power NORMAL"
   --#ARGUMENTS { }
   --#SEVERITY INFORMATIONAL
   --#TIMEINDEX 1
   --#HELP ""
   --#HELPTAG 0
   --#STATE OPERATIONAL
   ::= 639

almhybgen2ovrrnactive TRAP-TYPE
   ENTERPRISE enatel
      DESCRIPTION
      "INFORMATION: Generator 2 Overrun "
   --#TYPE "SM32 Trap"
   --#SUMMARY "Generator 2 Overrun Active"
   --#ARGUMENTS { }
   --#SEVERITY CRITICAL
   --#TIMEINDEX 1
   --#HELP ""
   --#HELPTAG 0
   --#STATE OPERATIONAL
   ::= 640

almhybgen2ovrrninactive TRAP-TYPE
   ENTERPRISE enatel
      DESCRIPTION
      "INFORMATION: Generator 2 Overrun has returned to normal"
   --#TYPE "SM32 Trap"
   --#SUMMARY "Generator 2 Overrun NORMAL"
   --#ARGUMENTS { }
   --#SEVERITY INFORMATIONAL
   --#TIMEINDEX 1
   --#HELP ""
   --#HELPTAG 0
   --#STATE OPERATIONAL
   ::= 641

almhybacmgenfail2active TRAP-TYPE
   ENTERPRISE enatel
      DESCRIPTION
      "INFORMATION: Generator ACM Fail "
   --#TYPE "SM32 Trap"
   --#SUMMARY "Generator ACM Fail Active"
   --#ARGUMENTS { }
   --#SEVERITY CRITICAL
   --#TIMEINDEX 1
   --#HELP ""
   --#HELPTAG 0
   --#STATE OPERATIONAL
   ::= 642

almhybacmgenfail2inactive TRAP-TYPE
   ENTERPRISE enatel
      DESCRIPTION
      "INFORMATION: Generator ACM Fail has returned to normal"
   --#TYPE "SM32 Trap"
   --#SUMMARY "Generator ACM Fail NORMAL"
   --#ARGUMENTS { }
   --#SEVERITY INFORMATIONAL
   --#TIMEINDEX 1
   --#HELP ""
   --#HELPTAG 0
   --#STATE OPERATIONAL
   ::= 643

almhybtank1logerractive TRAP-TYPE
   ENTERPRISE enatel
      DESCRIPTION
      "INFORMATION: Fuel Tank 1 Logic Error "
   --#TYPE "SM32 Trap"
   --#SUMMARY "Fuel Tank 1 Logic Error Active"
   --#ARGUMENTS { }
   --#SEVERITY CRITICAL
   --#TIMEINDEX 1
   --#HELP ""
   --#HELPTAG 0
   --#STATE OPERATIONAL
   ::= 644

almhybtank1logerrinactive TRAP-TYPE
   ENTERPRISE enatel
      DESCRIPTION
      "INFORMATION: Fuel Tank 1 Logic Error has returned to normal"
   --#TYPE "SM32 Trap"
   --#SUMMARY "Fuel Tank 1 Logic Error NORMAL"
   --#ARGUMENTS { }
   --#SEVERITY INFORMATIONAL
   --#TIMEINDEX 1
   --#HELP ""
   --#HELPTAG 0
   --#STATE OPERATIONAL
   ::= 645

almhybtank2logerractive TRAP-TYPE
   ENTERPRISE enatel
      DESCRIPTION
      "INFORMATION: Fuel Tank 2 Logic Error "
   --#TYPE "SM32 Trap"
   --#SUMMARY "Fuel Tank 2 Logic Error Active"
   --#ARGUMENTS { }
   --#SEVERITY CRITICAL
   --#TIMEINDEX 1
   --#HELP ""
   --#HELPTAG 0
   --#STATE OPERATIONAL
   ::= 646

almhybtank2logerrinactive TRAP-TYPE
   ENTERPRISE enatel
      DESCRIPTION
      "INFORMATION: Fuel Tank 2 Logic Error has returned to normal"
   --#TYPE "SM32 Trap"
   --#SUMMARY "Fuel Tank 2 Logic Error NORMAL"
   --#ARGUMENTS { }
   --#SEVERITY INFORMATIONAL
   --#TIMEINDEX 1
   --#HELP ""
   --#HELPTAG 0
   --#STATE OPERATIONAL
   ::= 647

almhybtank1rfillactive TRAP-TYPE
   ENTERPRISE enatel
      DESCRIPTION
      "INFORMATION: Fuel Tank 1 Refill "
   --#TYPE "SM32 Trap"
   --#SUMMARY "Fuel Tank 1 Refill Active"
   --#ARGUMENTS { }
   --#SEVERITY CRITICAL
   --#TIMEINDEX 1
   --#HELP ""
   --#HELPTAG 0
   --#STATE OPERATIONAL
   ::= 650

almhybtank1rfillinactive TRAP-TYPE
   ENTERPRISE enatel
      DESCRIPTION
      "INFORMATION: Fuel Tank 1 Refill has returned to normal"
   --#TYPE "SM32 Trap"
   --#SUMMARY "Fuel Tank 1 Refill NORMAL"
   --#ARGUMENTS { }
   --#SEVERITY INFORMATIONAL
   --#TIMEINDEX 1
   --#HELP ""
   --#HELPTAG 0
   --#STATE OPERATIONAL
   ::= 651

almhybtank2rfillactive TRAP-TYPE
   ENTERPRISE enatel
      DESCRIPTION
      "INFORMATION: Fuel Tank 2 Refill "
   --#TYPE "SM32 Trap"
   --#SUMMARY "Fuel Tank 2 Refill Active"
   --#ARGUMENTS { }
   --#SEVERITY CRITICAL
   --#TIMEINDEX 1
   --#HELP ""
   --#HELPTAG 0
   --#STATE OPERATIONAL
   ::= 652

almhybtank2rfillinactive TRAP-TYPE
   ENTERPRISE enatel
      DESCRIPTION
      "INFORMATION: Fuel Tank 2 Refill has returned to normal"
   --#TYPE "SM32 Trap"
   --#SUMMARY "Fuel Tank 2 Refill NORMAL"
   --#ARGUMENTS { }
   --#SEVERITY INFORMATIONAL
   --#TIMEINDEX 1
   --#HELP ""
   --#HELPTAG 0
   --#STATE OPERATIONAL
   ::= 653

almhybtank1urgactive TRAP-TYPE
   ENTERPRISE enatel
      DESCRIPTION
      "INFORMATION: Fuel Tank 1 Urgent "
   --#TYPE "SM32 Trap"
   --#SUMMARY "Fuel Tank 1 Urgent Active"
   --#ARGUMENTS { }
   --#SEVERITY CRITICAL
   --#TIMEINDEX 1
   --#HELP ""
   --#HELPTAG 0
   --#STATE OPERATIONAL
   ::= 654

almhybtank1urginactive TRAP-TYPE
   ENTERPRISE enatel
      DESCRIPTION
      "INFORMATION: Fuel Tank 1 Urgent has returned to normal"
   --#TYPE "SM32 Trap"
   --#SUMMARY "Fuel Tank 1 Urgent NORMAL"
   --#ARGUMENTS { }
   --#SEVERITY INFORMATIONAL
   --#TIMEINDEX 1
   --#HELP ""
   --#HELPTAG 0
   --#STATE OPERATIONAL
   ::= 655

almhybtank2urgactive TRAP-TYPE
   ENTERPRISE enatel
      DESCRIPTION
      "INFORMATION: Fuel Tank 2 Urgent "
   --#TYPE "SM32 Trap"
   --#SUMMARY "Fuel Tank 2 Urgent Active"
   --#ARGUMENTS { }
   --#SEVERITY CRITICAL
   --#TIMEINDEX 1
   --#HELP ""
   --#HELPTAG 0
   --#STATE OPERATIONAL
   ::= 656

almhybtank2urginactive TRAP-TYPE
   ENTERPRISE enatel
      DESCRIPTION
      "INFORMATION: Fuel Tank 2 Urgent has returned to normal"
   --#TYPE "SM32 Trap"
   --#SUMMARY "Fuel Tank 2 Urgent NORMAL"
   --#ARGUMENTS { }
   --#SEVERITY INFORMATIONAL
   --#TIMEINDEX 1
   --#HELP ""
   --#HELPTAG 0
   --#STATE OPERATIONAL
   ::= 657

almphbalenumon TRAP-TYPE
   ENTERPRISE enatel
      DESCRIPTION
      "INFORMATION: Phase Balancing Enumerating "
   --#TYPE "SM32 Trap"
   --#SUMMARY "Phase Balancing Enumerating Active"
   --#ARGUMENTS { }
   --#SEVERITY CRITICAL
   --#TIMEINDEX 1
   --#HELP ""
   --#HELPTAG 0
   --#STATE OPERATIONAL
   ::= 714

almphbalenumoff TRAP-TYPE
   ENTERPRISE enatel
      DESCRIPTION
      "INFORMATION: Phase Balancing Enumerating has returned to normal"
   --#TYPE "SM32 Trap"
   --#SUMMARY "Phase Balancing Enumerating NORMAL"
   --#ARGUMENTS { }
   --#SEVERITY INFORMATIONAL
   --#TIMEINDEX 1
   --#HELP ""
   --#HELPTAG 0
   --#STATE OPERATIONAL
   ::= 715

almphbalacm1missingon TRAP-TYPE
   ENTERPRISE enatel
      DESCRIPTION
      "INFORMATION: Phase Balancing ACM 1 Missing "
   --#TYPE "SM32 Trap"
   --#SUMMARY "Phase Balancing ACM 1 Missing Active"
   --#ARGUMENTS { }
   --#SEVERITY CRITICAL
   --#TIMEINDEX 1
   --#HELP ""
   --#HELPTAG 0
   --#STATE OPERATIONAL
   ::= 716

almphbalacm1missingoff TRAP-TYPE
   ENTERPRISE enatel
      DESCRIPTION
      "INFORMATION: Phase Balancing ACM 1 Missing has returned to normal"
   --#TYPE "SM32 Trap"
   --#SUMMARY "Phase Balancing ACM 1 Missing NORMAL"
   --#ARGUMENTS { }
   --#SEVERITY INFORMATIONAL
   --#TIMEINDEX 1
   --#HELP ""
   --#HELPTAG 0
   --#STATE OPERATIONAL
   ::= 717

almphbalacm1incorrecton TRAP-TYPE
   ENTERPRISE enatel
      DESCRIPTION
      "INFORMATION: Phase Balancing ACM 1 Incorrect "
   --#TYPE "SM32 Trap"
   --#SUMMARY "Phase Balancing ACM 1 Incorrect Active"
   --#ARGUMENTS { }
   --#SEVERITY CRITICAL
   --#TIMEINDEX 1
   --#HELP ""
   --#HELPTAG 0
   --#STATE OPERATIONAL
   ::= 718

almphbalacm1incorrectoff TRAP-TYPE
   ENTERPRISE enatel
      DESCRIPTION
      "INFORMATION: Phase Balancing ACM 1 Incorrect has returned to normal"
   --#TYPE "SM32 Trap"
   --#SUMMARY "Phase Balancing ACM 1 Incorrect NORMAL"
   --#ARGUMENTS { }
   --#SEVERITY INFORMATIONAL
   --#TIMEINDEX 1
   --#HELP ""
   --#HELPTAG 0
   --#STATE OPERATIONAL
   ::= 719

almphbalbackoff1on TRAP-TYPE
   ENTERPRISE enatel
      DESCRIPTION
      "INFORMATION: Phase 1 Backoff "
   --#TYPE "SM32 Trap"
   --#SUMMARY "Phase 1 Backoff Active"
   --#ARGUMENTS { }
   --#SEVERITY CRITICAL
   --#TIMEINDEX 1
   --#HELP ""
   --#HELPTAG 0
   --#STATE OPERATIONAL
   ::= 720

almphbalbackoff1off TRAP-TYPE
   ENTERPRISE enatel
      DESCRIPTION
      "INFORMATION: Phase 1 Backoff has returned to normal"
   --#TYPE "SM32 Trap"
   --#SUMMARY "Phase 1 Backoff NORMAL"
   --#ARGUMENTS { }
   --#SEVERITY INFORMATIONAL
   --#TIMEINDEX 1
   --#HELP ""
   --#HELPTAG 0
   --#STATE OPERATIONAL
   ::= 721

almphbalbackoff2on TRAP-TYPE
   ENTERPRISE enatel
      DESCRIPTION
      "INFORMATION: Phase 2 Backoff "
   --#TYPE "SM32 Trap"
   --#SUMMARY "Phase 2 Backoff Active"
   --#ARGUMENTS { }
   --#SEVERITY CRITICAL
   --#TIMEINDEX 1
   --#HELP ""
   --#HELPTAG 0
   --#STATE OPERATIONAL
   ::= 722

almphbalbackoff2off TRAP-TYPE
   ENTERPRISE enatel
      DESCRIPTION
      "INFORMATION: Phase 2 Backoff has returned to normal"
   --#TYPE "SM32 Trap"
   --#SUMMARY "Phase 2 Backoff NORMAL"
   --#ARGUMENTS { }
   --#SEVERITY INFORMATIONAL
   --#TIMEINDEX 1
   --#HELP ""
   --#HELPTAG 0
   --#STATE OPERATIONAL
   ::= 723

almphbalbackoff3on TRAP-TYPE
   ENTERPRISE enatel
      DESCRIPTION
      "INFORMATION: Phase 3 Backoff "
   --#TYPE "SM32 Trap"
   --#SUMMARY "Phase 3 Backoff Active"
   --#ARGUMENTS { }
   --#SEVERITY CRITICAL
   --#TIMEINDEX 1
   --#HELP ""
   --#HELPTAG 0
   --#STATE OPERATIONAL
   ::= 724

almphbalbackoff3off TRAP-TYPE
   ENTERPRISE enatel
      DESCRIPTION
      "INFORMATION: Phase 3 Backoff has returned to normal"
   --#TYPE "SM32 Trap"
   --#SUMMARY "Phase 3 Backoff NORMAL"
   --#ARGUMENTS { }
   --#SEVERITY INFORMATIONAL
   --#TIMEINDEX 1
   --#HELP ""
   --#HELPTAG 0
   --#STATE OPERATIONAL
   ::= 725

almphbalacm2missingon TRAP-TYPE
   ENTERPRISE enatel
      DESCRIPTION
      "INFORMATION: Phase Balancing ACM 2 Missing "
   --#TYPE "SM32 Trap"
   --#SUMMARY "Phase Balancing ACM 2 Missing Active"
   --#ARGUMENTS { }
   --#SEVERITY CRITICAL
   --#TIMEINDEX 1
   --#HELP ""
   --#HELPTAG 0
   --#STATE OPERATIONAL
   ::= 726

almphbalacm2missingoff TRAP-TYPE
   ENTERPRISE enatel
      DESCRIPTION
      "INFORMATION: Phase Balancing ACM 2 Missing has returned to normal"
   --#TYPE "SM32 Trap"
   --#SUMMARY "Phase Balancing ACM 2 Missing NORMAL"
   --#ARGUMENTS { }
   --#SEVERITY INFORMATIONAL
   --#TIMEINDEX 1
   --#HELP ""
   --#HELPTAG 0
   --#STATE OPERATIONAL
   ::= 727

almphbalacm2incorrecton TRAP-TYPE
   ENTERPRISE enatel
      DESCRIPTION
      "INFORMATION: Phase Balancing ACM 2 Incorrect "
   --#TYPE "SM32 Trap"
   --#SUMMARY "Phase Balancing ACM 2 Incorrect Active"
   --#ARGUMENTS { }
   --#SEVERITY CRITICAL
   --#TIMEINDEX 1
   --#HELP ""
   --#HELPTAG 0
   --#STATE OPERATIONAL
   ::= 728

almphbalacm2incorrectoff TRAP-TYPE
   ENTERPRISE enatel
      DESCRIPTION
      "INFORMATION: Phase Balancing ACM 2 Incorrect has returned to normal"
   --#TYPE "SM32 Trap"
   --#SUMMARY "Phase Balancing ACM 2 Incorrect NORMAL"
   --#ARGUMENTS { }
   --#SEVERITY INFORMATIONAL
   --#TIMEINDEX 1
   --#HELP ""
   --#HELPTAG 0
   --#STATE OPERATIONAL
   ::= 729

almphbalclampingon TRAP-TYPE
   ENTERPRISE enatel
      DESCRIPTION
      "INFORMATION: Phase Balancing Clamping "
   --#TYPE "SM32 Trap"
   --#SUMMARY "Phase Balancing Clamping Active"
   --#ARGUMENTS { }
   --#SEVERITY CRITICAL
   --#TIMEINDEX 1
   --#HELP ""
   --#HELPTAG 0
   --#STATE OPERATIONAL
   ::= 730

almphbalclampingoff TRAP-TYPE
   ENTERPRISE enatel
      DESCRIPTION
      "INFORMATION: Phase Balancing Clamping has returned to normal"
   --#TYPE "SM32 Trap"
   --#SUMMARY "Phase Balancing Clamping NORMAL"
   --#ARGUMENTS { }
   --#SEVERITY INFORMATIONAL
   --#TIMEINDEX 1
   --#HELP ""
   --#HELPTAG 0
   --#STATE OPERATIONAL
   ::= 731

almphbalrectincorrecton TRAP-TYPE
   ENTERPRISE enatel
      DESCRIPTION
      "INFORMATION: Phase Balancing Rect Incorrect "
   --#TYPE "SM32 Trap"
   --#SUMMARY "Phase Balancing Rect Incorrect Active"
   --#ARGUMENTS { }
   --#SEVERITY CRITICAL
   --#TIMEINDEX 1
   --#HELP ""
   --#HELPTAG 0
   --#STATE OPERATIONAL
   ::= 732

almphbalrectincorrectoff TRAP-TYPE
   ENTERPRISE enatel
      DESCRIPTION
      "INFORMATION: Phase Balancing Rect Incorrect has returned to normal"
   --#TYPE "SM32 Trap"
   --#SUMMARY "Phase Balancing Rect Incorrect NORMAL"
   --#ARGUMENTS { }
   --#SEVERITY INFORMATIONAL
   --#TIMEINDEX 1
   --#HELP ""
   --#HELPTAG 0
   --#STATE OPERATIONAL
   ::= 733

almhybgenconvalactive TRAP-TYPE
   ENTERPRISE enatel
      DESCRIPTION
      "INFORMATION: Gen Contactor Value "
   --#TYPE "SM32 Trap"
   --#SUMMARY "Gen Contactor Value Active"
   --#ARGUMENTS { }
   --#SEVERITY CRITICAL
   --#TIMEINDEX 1
   --#HELP ""
   --#HELPTAG 0
   --#STATE OPERATIONAL
   ::= 746

almhybgenconvalinactive TRAP-TYPE
   ENTERPRISE enatel
      DESCRIPTION
      "INFORMATION: Gen Contactor Value has returned to normal"
   --#TYPE "SM32 Trap"
   --#SUMMARY "Gen Contactor Value NORMAL"
   --#ARGUMENTS { }
   --#SEVERITY INFORMATIONAL
   --#TIMEINDEX 1
   --#HELP ""
   --#HELPTAG 0
   --#STATE OPERATIONAL
   ::= 747

almhybfgridconvalactive TRAP-TYPE
   ENTERPRISE enatel
      DESCRIPTION
      "INFORMATION: Grid Contactor Value "
   --#TYPE "SM32 Trap"
   --#SUMMARY "Grid Contactor Value Active"
   --#ARGUMENTS { }
   --#SEVERITY CRITICAL
   --#TIMEINDEX 1
   --#HELP ""
   --#HELPTAG 0
   --#STATE OPERATIONAL
   ::= 748

almhybfgridconvalinactive TRAP-TYPE
   ENTERPRISE enatel
      DESCRIPTION
      "INFORMATION: Grid Contactor Value has returned to normal"
   --#TYPE "SM32 Trap"
   --#SUMMARY "Grid Contactor Value NORMAL"
   --#ARGUMENTS { }
   --#SEVERITY INFORMATIONAL
   --#TIMEINDEX 1
   --#HELP ""
   --#HELPTAG 0
   --#STATE OPERATIONAL
   ::= 749

almhybgen1strtpulactive TRAP-TYPE
   ENTERPRISE enatel
      DESCRIPTION
      "INFORMATION: Gen 1 Start Pulse "
   --#TYPE "SM32 Trap"
   --#SUMMARY "Gen 1 Start Pulse Active"
   --#ARGUMENTS { }
   --#SEVERITY CRITICAL
   --#TIMEINDEX 1
   --#HELP ""
   --#HELPTAG 0
   --#STATE OPERATIONAL
   ::= 750

almhybgen1strtpulinactive TRAP-TYPE
   ENTERPRISE enatel
      DESCRIPTION
      "INFORMATION: Gen 1 Start Pulse has returned to normal"
   --#TYPE "SM32 Trap"
   --#SUMMARY "Gen 1 Start Pulse NORMAL"
   --#ARGUMENTS { }
   --#SEVERITY INFORMATIONAL
   --#TIMEINDEX 1
   --#HELP ""
   --#HELPTAG 0
   --#STATE OPERATIONAL
   ::= 751

almhybgen1strtlvlactive TRAP-TYPE
   ENTERPRISE enatel
      DESCRIPTION
      "INFORMATION: Gen 1 Start Level "
   --#TYPE "SM32 Trap"
   --#SUMMARY "Gen 1 Start Level Active"
   --#ARGUMENTS { }
   --#SEVERITY CRITICAL
   --#TIMEINDEX 1
   --#HELP ""
   --#HELPTAG 0
   --#STATE OPERATIONAL
   ::= 752

almhybgen1strtlvlinactive TRAP-TYPE
   ENTERPRISE enatel
      DESCRIPTION
      "INFORMATION: Gen 1 Start Level has returned to normal"
   --#TYPE "SM32 Trap"
   --#SUMMARY "Gen 1 Start Level NORMAL"
   --#ARGUMENTS { }
   --#SEVERITY INFORMATIONAL
   --#TIMEINDEX 1
   --#HELP ""
   --#HELPTAG 0
   --#STATE OPERATIONAL
   ::= 753

almhybgen2strtpulactive TRAP-TYPE
   ENTERPRISE enatel
      DESCRIPTION
      "INFORMATION: Gen 2 Start Pulse  "
   --#TYPE "SM32 Trap"
   --#SUMMARY "Gen 2 Start Pulse  Active"
   --#ARGUMENTS { }
   --#SEVERITY CRITICAL
   --#TIMEINDEX 1
   --#HELP ""
   --#HELPTAG 0
   --#STATE OPERATIONAL
   ::= 754

almhybgen2strtpulinactive TRAP-TYPE
   ENTERPRISE enatel
      DESCRIPTION
      "INFORMATION: Gen 2 Start Pulse  has returned to normal"
   --#TYPE "SM32 Trap"
   --#SUMMARY "Gen 2 Start Pulse  NORMAL"
   --#ARGUMENTS { }
   --#SEVERITY INFORMATIONAL
   --#TIMEINDEX 1
   --#HELP ""
   --#HELPTAG 0
   --#STATE OPERATIONAL
   ::= 755

almhybgen2strtlvlactive TRAP-TYPE
   ENTERPRISE enatel
      DESCRIPTION
      "INFORMATION: Gen 2 Start Level "
   --#TYPE "SM32 Trap"
   --#SUMMARY "Gen 2 Start Level Active"
   --#ARGUMENTS { }
   --#SEVERITY CRITICAL
   --#TIMEINDEX 1
   --#HELP ""
   --#HELPTAG 0
   --#STATE OPERATIONAL
   ::= 756

almhybgen2strtlvlinactive TRAP-TYPE
   ENTERPRISE enatel
      DESCRIPTION
      "INFORMATION: Gen 2 Start Level has returned to normal"
   --#TYPE "SM32 Trap"
   --#SUMMARY "Gen 2 Start Level NORMAL"
   --#ARGUMENTS { }
   --#SEVERITY INFORMATIONAL
   --#TIMEINDEX 1
   --#HELP ""
   --#HELPTAG 0
   --#STATE OPERATIONAL
   ::= 757

almhybaccongen1active TRAP-TYPE
   ENTERPRISE enatel
      DESCRIPTION
      "INFORMATION: Gen 1 AC Contactor Coil "
   --#TYPE "SM32 Trap"
   --#SUMMARY "Gen 1 AC Contactor Coil Active"
   --#ARGUMENTS { }
   --#SEVERITY CRITICAL
   --#TIMEINDEX 1
   --#HELP ""
   --#HELPTAG 0
   --#STATE OPERATIONAL
   ::= 758

almhybaccongen1inactive TRAP-TYPE
   ENTERPRISE enatel
      DESCRIPTION
      "INFORMATION: Gen 1 AC Contactor Coil has returned to normal"
   --#TYPE "SM32 Trap"
   --#SUMMARY "Gen 1 AC Contactor Coil NORMAL"
   --#ARGUMENTS { }
   --#SEVERITY INFORMATIONAL
   --#TIMEINDEX 1
   --#HELP ""
   --#HELPTAG 0
   --#STATE OPERATIONAL
   ::= 759

almhybaccongen2active TRAP-TYPE
   ENTERPRISE enatel
      DESCRIPTION
      "INFORMATION: Gen 2 AC Contactor Coil "
   --#TYPE "SM32 Trap"
   --#SUMMARY "Gen 2 AC Contactor Coil Active"
   --#ARGUMENTS { }
   --#SEVERITY CRITICAL
   --#TIMEINDEX 1
   --#HELP ""
   --#HELPTAG 0
   --#STATE OPERATIONAL
   ::= 760

almhybaccongen2inactive TRAP-TYPE
   ENTERPRISE enatel
      DESCRIPTION
      "INFORMATION: Gen 2 AC Contactor Coil has returned to normal"
   --#TYPE "SM32 Trap"
   --#SUMMARY "Gen 2 AC Contactor Coil NORMAL"
   --#ARGUMENTS { }
   --#SEVERITY INFORMATIONAL
   --#TIMEINDEX 1
   --#HELP ""
   --#HELPTAG 0
   --#STATE OPERATIONAL
   ::= 761

almhybaccongenactive TRAP-TYPE
   ENTERPRISE enatel
      DESCRIPTION
      "INFORMATION: Gen AC Contactor Coil "
   --#TYPE "SM32 Trap"
   --#SUMMARY "Gen AC Contactor Coil Active"
   --#ARGUMENTS { }
   --#SEVERITY CRITICAL
   --#TIMEINDEX 1
   --#HELP ""
   --#HELPTAG 0
   --#STATE OPERATIONAL
   ::= 762

almhybaccongeninactive TRAP-TYPE
   ENTERPRISE enatel
      DESCRIPTION
      "INFORMATION: Gen AC Contactor Coil has returned to normal"
   --#TYPE "SM32 Trap"
   --#SUMMARY "Gen AC Contactor Coil NORMAL"
   --#ARGUMENTS { }
   --#SEVERITY INFORMATIONAL
   --#TIMEINDEX 1
   --#HELP ""
   --#HELPTAG 0
   --#STATE OPERATIONAL
   ::= 763

almhybaccongridactive TRAP-TYPE
   ENTERPRISE enatel
      DESCRIPTION
      "INFORMATION: Grid AC Contactor Coil "
   --#TYPE "SM32 Trap"
   --#SUMMARY "Grid AC Contactor Coil Active"
   --#ARGUMENTS { }
   --#SEVERITY CRITICAL
   --#TIMEINDEX 1
   --#HELP ""
   --#HELPTAG 0
   --#STATE OPERATIONAL
   ::= 764

almhybaccongridinactive TRAP-TYPE
   ENTERPRISE enatel
      DESCRIPTION
      "INFORMATION: Grid AC Contactor Coil has returned to normal"
   --#TYPE "SM32 Trap"
   --#SUMMARY "Grid AC Contactor Coil NORMAL"
   --#ARGUMENTS { }
   --#SEVERITY INFORMATIONAL
   --#TIMEINDEX 1
   --#HELP ""
   --#HELPTAG 0
   --#STATE OPERATIONAL
   ::= 765

almhybledcomchgactive TRAP-TYPE
   ENTERPRISE enatel
      DESCRIPTION
      "INFORMATION: Comm. Charge LED "
   --#TYPE "SM32 Trap"
   --#SUMMARY "Comm. Charge LED Active"
   --#ARGUMENTS { }
   --#SEVERITY CRITICAL
   --#TIMEINDEX 1
   --#HELP ""
   --#HELPTAG 0
   --#STATE OPERATIONAL
   ::= 772

almhybledcomchginactive TRAP-TYPE
   ENTERPRISE enatel
      DESCRIPTION
      "INFORMATION: Comm. Charge LED has returned to normal"
   --#TYPE "SM32 Trap"
   --#SUMMARY "Comm. Charge LED NORMAL"
   --#ARGUMENTS { }
   --#SEVERITY INFORMATIONAL
   --#TIMEINDEX 1
   --#HELP ""
   --#HELPTAG 0
   --#STATE OPERATIONAL
   ::= 773

almhybledhourgenactive TRAP-TYPE
   ENTERPRISE enatel
      DESCRIPTION
      "INFORMATION: 1 Hour Genset LED "
   --#TYPE "SM32 Trap"
   --#SUMMARY "1 Hour Genset LED Active"
   --#ARGUMENTS { }
   --#SEVERITY CRITICAL
   --#TIMEINDEX 1
   --#HELP ""
   --#HELPTAG 0
   --#STATE OPERATIONAL
   ::= 774

almhybledhourgeninactive TRAP-TYPE
   ENTERPRISE enatel
      DESCRIPTION
      "INFORMATION: 1 Hour Genset LED has returned to normal"
   --#TYPE "SM32 Trap"
   --#SUMMARY "1 Hour Genset LED NORMAL"
   --#ARGUMENTS { }
   --#SEVERITY INFORMATIONAL
   --#TIMEINDEX 1
   --#HELP ""
   --#HELPTAG 0
   --#STATE OPERATIONAL
   ::= 775

almac1p1vhighon TRAP-TYPE
   ENTERPRISE enatel
      DESCRIPTION
      "INFORMATION: AC Mains Monitor 1 Phase 1 Voltage High "
   --#TYPE "SM32 Trap"
   --#SUMMARY "AC Mains Monitor 1 Phase 1 Voltage High Active"
   --#ARGUMENTS { }
   --#SEVERITY CRITICAL
   --#TIMEINDEX 1
   --#HELP ""
   --#HELPTAG 0
   --#STATE OPERATIONAL
   ::= 778

almac1p1vhighoff TRAP-TYPE
   ENTERPRISE enatel
      DESCRIPTION
      "INFORMATION: AC Mains Monitor 1 Phase 1 Voltage High has returned to normal"
   --#TYPE "SM32 Trap"
   --#SUMMARY "AC Mains Monitor 1 Phase 1 Voltage High NORMAL"
   --#ARGUMENTS { }
   --#SEVERITY INFORMATIONAL
   --#TIMEINDEX 1
   --#HELP ""
   --#HELPTAG 0
   --#STATE OPERATIONAL
   ::= 779

almac1p1vlowon TRAP-TYPE
   ENTERPRISE enatel
      DESCRIPTION
      "INFORMATION: AC Mains Monitor 1 Phase 1 Voltage Low "
   --#TYPE "SM32 Trap"
   --#SUMMARY "AC Mains Monitor 1 Phase 1 Voltage Low Active"
   --#ARGUMENTS { }
   --#SEVERITY CRITICAL
   --#TIMEINDEX 1
   --#HELP ""
   --#HELPTAG 0
   --#STATE OPERATIONAL
   ::= 780

almac1p1vlowoff TRAP-TYPE
   ENTERPRISE enatel
      DESCRIPTION
      "INFORMATION: AC Mains Monitor 1 Phase 1 Voltage Low has returned to normal"
   --#TYPE "SM32 Trap"
   --#SUMMARY "AC Mains Monitor 1 Phase 1 Voltage Low NORMAL"
   --#ARGUMENTS { }
   --#SEVERITY INFORMATIONAL
   --#TIMEINDEX 1
   --#HELP ""
   --#HELPTAG 0
   --#STATE OPERATIONAL
   ::= 781

almac1p1loston TRAP-TYPE
   ENTERPRISE enatel
      DESCRIPTION
      "INFORMATION: AC Phase 1 Lost "
   --#TYPE "SM32 Trap"
   --#SUMMARY "AC Phase 1 Lost Active"
   --#ARGUMENTS { }
   --#SEVERITY CRITICAL
   --#TIMEINDEX 1
   --#HELP ""
   --#HELPTAG 0
   --#STATE OPERATIONAL
   ::= 782

almac1p1lostoff TRAP-TYPE
   ENTERPRISE enatel
      DESCRIPTION
      "INFORMATION: AC Phase 1 Lost has returned to normal"
   --#TYPE "SM32 Trap"
   --#SUMMARY "AC Phase 1 Lost NORMAL"
   --#ARGUMENTS { }
   --#SEVERITY INFORMATIONAL
   --#TIMEINDEX 1
   --#HELP ""
   --#HELPTAG 0
   --#STATE OPERATIONAL
   ::= 783

almac1p1ihighon TRAP-TYPE
   ENTERPRISE enatel
      DESCRIPTION
      "INFORMATION: AC Mains Monitor 1 Phase 1 Current High "
   --#TYPE "SM32 Trap"
   --#SUMMARY "AC Mains Monitor 1 Phase 1 Current High Active"
   --#ARGUMENTS { }
   --#SEVERITY CRITICAL
   --#TIMEINDEX 1
   --#HELP ""
   --#HELPTAG 0
   --#STATE OPERATIONAL
   ::= 784

almac1p1ihighoff TRAP-TYPE
   ENTERPRISE enatel
      DESCRIPTION
      "INFORMATION: AC Mains Monitor 1 Phase 1 Current High has returned to normal"
   --#TYPE "SM32 Trap"
   --#SUMMARY "AC Mains Monitor 1 Phase 1 Current High NORMAL"
   --#ARGUMENTS { }
   --#SEVERITY INFORMATIONAL
   --#TIMEINDEX 1
   --#HELP ""
   --#HELPTAG 0
   --#STATE OPERATIONAL
   ::= 785

almac1p2vhighon TRAP-TYPE
   ENTERPRISE enatel
      DESCRIPTION
      "INFORMATION: AC Mains Monitor 1 Phase 2 Voltage High "
   --#TYPE "SM32 Trap"
   --#SUMMARY "AC Mains Monitor 1 Phase 2 Voltage High Active"
   --#ARGUMENTS { }
   --#SEVERITY CRITICAL
   --#TIMEINDEX 1
   --#HELP ""
   --#HELPTAG 0
   --#STATE OPERATIONAL
   ::= 786

almac1p2vhighoff TRAP-TYPE
   ENTERPRISE enatel
      DESCRIPTION
      "INFORMATION: AC Mains Monitor 1 Phase 2 Voltage High has returned to normal"
   --#TYPE "SM32 Trap"
   --#SUMMARY "AC Mains Monitor 1 Phase 2 Voltage High NORMAL"
   --#ARGUMENTS { }
   --#SEVERITY INFORMATIONAL
   --#TIMEINDEX 1
   --#HELP ""
   --#HELPTAG 0
   --#STATE OPERATIONAL
   ::= 787

almac1p2vlowon TRAP-TYPE
   ENTERPRISE enatel
      DESCRIPTION
      "INFORMATION: AC Mains Monitor 1 Phase 2 Voltage Low "
   --#TYPE "SM32 Trap"
   --#SUMMARY "AC Mains Monitor 1 Phase 2 Voltage Low Active"
   --#ARGUMENTS { }
   --#SEVERITY CRITICAL
   --#TIMEINDEX 1
   --#HELP ""
   --#HELPTAG 0
   --#STATE OPERATIONAL
   ::= 788

almac1p2vlowoff TRAP-TYPE
   ENTERPRISE enatel
      DESCRIPTION
      "INFORMATION: AC Mains Monitor 1 Phase 2 Voltage Low has returned to normal"
   --#TYPE "SM32 Trap"
   --#SUMMARY "AC Mains Monitor 1 Phase 2 Voltage Low NORMAL"
   --#ARGUMENTS { }
   --#SEVERITY INFORMATIONAL
   --#TIMEINDEX 1
   --#HELP ""
   --#HELPTAG 0
   --#STATE OPERATIONAL
   ::= 789

almac1p2loston TRAP-TYPE
   ENTERPRISE enatel
      DESCRIPTION
      "INFORMATION: AC Phase 2 Lost "
   --#TYPE "SM32 Trap"
   --#SUMMARY "AC Phase 2 Lost Active"
   --#ARGUMENTS { }
   --#SEVERITY CRITICAL
   --#TIMEINDEX 1
   --#HELP ""
   --#HELPTAG 0
   --#STATE OPERATIONAL
   ::= 790

almac1p2lostoff TRAP-TYPE
   ENTERPRISE enatel
      DESCRIPTION
      "INFORMATION: AC Phase 2 Lost has returned to normal"
   --#TYPE "SM32 Trap"
   --#SUMMARY "AC Phase 2 Lost NORMAL"
   --#ARGUMENTS { }
   --#SEVERITY INFORMATIONAL
   --#TIMEINDEX 1
   --#HELP ""
   --#HELPTAG 0
   --#STATE OPERATIONAL
   ::= 791

almac1p2ihighon TRAP-TYPE
   ENTERPRISE enatel
      DESCRIPTION
      "INFORMATION: AC Mains Monitor 1 Phase 2 Current High "
   --#TYPE "SM32 Trap"
   --#SUMMARY "AC Mains Monitor 1 Phase 2 Current High Active"
   --#ARGUMENTS { }
   --#SEVERITY CRITICAL
   --#TIMEINDEX 1
   --#HELP ""
   --#HELPTAG 0
   --#STATE OPERATIONAL
   ::= 792

almac1p2ihighoff TRAP-TYPE
   ENTERPRISE enatel
      DESCRIPTION
      "INFORMATION: AC Mains Monitor 1 Phase 2 Current High has returned to normal"
   --#TYPE "SM32 Trap"
   --#SUMMARY "AC Mains Monitor 1 Phase 2 Current High NORMAL"
   --#ARGUMENTS { }
   --#SEVERITY INFORMATIONAL
   --#TIMEINDEX 1
   --#HELP ""
   --#HELPTAG 0
   --#STATE OPERATIONAL
   ::= 793

almac1p3vhighon TRAP-TYPE
   ENTERPRISE enatel
      DESCRIPTION
      "INFORMATION: AC Mains Monitor 1 Phase 3 Voltage High "
   --#TYPE "SM32 Trap"
   --#SUMMARY "AC Mains Monitor 1 Phase 3 Voltage High Active"
   --#ARGUMENTS { }
   --#SEVERITY CRITICAL
   --#TIMEINDEX 1
   --#HELP ""
   --#HELPTAG 0
   --#STATE OPERATIONAL
   ::= 794

almac1p3vhighoff TRAP-TYPE
   ENTERPRISE enatel
      DESCRIPTION
      "INFORMATION: AC Mains Monitor 1 Phase 3 Voltage High has returned to normal"
   --#TYPE "SM32 Trap"
   --#SUMMARY "AC Mains Monitor 1 Phase 3 Voltage High NORMAL"
   --#ARGUMENTS { }
   --#SEVERITY INFORMATIONAL
   --#TIMEINDEX 1
   --#HELP ""
   --#HELPTAG 0
   --#STATE OPERATIONAL
   ::= 795

almac1p3vlowon TRAP-TYPE
   ENTERPRISE enatel
      DESCRIPTION
      "INFORMATION: AC Mains Monitor 1 Phase 3 Voltage Low "
   --#TYPE "SM32 Trap"
   --#SUMMARY "AC Mains Monitor 1 Phase 3 Voltage Low Active"
   --#ARGUMENTS { }
   --#SEVERITY CRITICAL
   --#TIMEINDEX 1
   --#HELP ""
   --#HELPTAG 0
   --#STATE OPERATIONAL
   ::= 796

almac1p3vlowoff TRAP-TYPE
   ENTERPRISE enatel
      DESCRIPTION
      "INFORMATION: AC Mains Monitor 1 Phase 3 Voltage Low has returned to normal"
   --#TYPE "SM32 Trap"
   --#SUMMARY "AC Mains Monitor 1 Phase 3 Voltage Low NORMAL"
   --#ARGUMENTS { }
   --#SEVERITY INFORMATIONAL
   --#TIMEINDEX 1
   --#HELP ""
   --#HELPTAG 0
   --#STATE OPERATIONAL
   ::= 797

almac1p3loston TRAP-TYPE
   ENTERPRISE enatel
      DESCRIPTION
      "INFORMATION: AC Phase 3 Lost "
   --#TYPE "SM32 Trap"
   --#SUMMARY "AC Phase 3 Lost Active"
   --#ARGUMENTS { }
   --#SEVERITY CRITICAL
   --#TIMEINDEX 1
   --#HELP ""
   --#HELPTAG 0
   --#STATE OPERATIONAL
   ::= 798

almac1p3lostoff TRAP-TYPE
   ENTERPRISE enatel
      DESCRIPTION
      "INFORMATION: AC Phase 3 Lost has returned to normal"
   --#TYPE "SM32 Trap"
   --#SUMMARY "AC Phase 3 Lost NORMAL"
   --#ARGUMENTS { }
   --#SEVERITY INFORMATIONAL
   --#TIMEINDEX 1
   --#HELP ""
   --#HELPTAG 0
   --#STATE OPERATIONAL
   ::= 799

almac1p3ihighon TRAP-TYPE
   ENTERPRISE enatel
      DESCRIPTION
      "INFORMATION: AC Mains Monitor 1 Phase 3 Current High "
   --#TYPE "SM32 Trap"
   --#SUMMARY "AC Mains Monitor 1 Phase 3 Current High Active"
   --#ARGUMENTS { }
   --#SEVERITY CRITICAL
   --#TIMEINDEX 1
   --#HELP ""
   --#HELPTAG 0
   --#STATE OPERATIONAL
   ::= 800

almac1p3ihighoff TRAP-TYPE
   ENTERPRISE enatel
      DESCRIPTION
      "INFORMATION: AC Mains Monitor 1 Phase 3 Current High has returned to normal"
   --#TYPE "SM32 Trap"
   --#SUMMARY "AC Mains Monitor 1 Phase 3 Current High NORMAL"
   --#ARGUMENTS { }
   --#SEVERITY INFORMATIONAL
   --#TIMEINDEX 1
   --#HELP ""
   --#HELPTAG 0
   --#STATE OPERATIONAL
   ::= 801

almac1freqhighon TRAP-TYPE
   ENTERPRISE enatel
      DESCRIPTION
      "INFORMATION: AC Mains Monitor 1 Frequency High "
   --#TYPE "SM32 Trap"
   --#SUMMARY "AC Mains Monitor 1 Frequency High Active"
   --#ARGUMENTS { }
   --#SEVERITY CRITICAL
   --#TIMEINDEX 1
   --#HELP ""
   --#HELPTAG 0
   --#STATE OPERATIONAL
   ::= 802

almac1freqhighoff TRAP-TYPE
   ENTERPRISE enatel
      DESCRIPTION
      "INFORMATION: AC Mains Monitor 1 Frequency High has returned to normal"
   --#TYPE "SM32 Trap"
   --#SUMMARY "AC Mains Monitor 1 Frequency High NORMAL"
   --#ARGUMENTS { }
   --#SEVERITY INFORMATIONAL
   --#TIMEINDEX 1
   --#HELP ""
   --#HELPTAG 0
   --#STATE OPERATIONAL
   ::= 803

almac1freqlowon TRAP-TYPE
   ENTERPRISE enatel
      DESCRIPTION
      "INFORMATION: AC Mains Monitor 1 Frequency Low "
   --#TYPE "SM32 Trap"
   --#SUMMARY "AC Mains Monitor 1 Frequency Low Active"
   --#ARGUMENTS { }
   --#SEVERITY CRITICAL
   --#TIMEINDEX 1
   --#HELP ""
   --#HELPTAG 0
   --#STATE OPERATIONAL
   ::= 804

almac1freqlowoff TRAP-TYPE
   ENTERPRISE enatel
      DESCRIPTION
      "INFORMATION: AC Mains Monitor 1 Frequency Low has returned to normal"
   --#TYPE "SM32 Trap"
   --#SUMMARY "AC Mains Monitor 1 Frequency Low NORMAL"
   --#ARGUMENTS { }
   --#SEVERITY INFORMATIONAL
   --#TIMEINDEX 1
   --#HELP ""
   --#HELPTAG 0
   --#STATE OPERATIONAL
   ::= 805

almac2p1vhighon TRAP-TYPE
   ENTERPRISE enatel
      DESCRIPTION
      "INFORMATION: AC Mains Monitor 2 Phase 1 Voltage High "
   --#TYPE "SM32 Trap"
   --#SUMMARY "AC Mains Monitor 2 Phase 1 Voltage High Active"
   --#ARGUMENTS { }
   --#SEVERITY CRITICAL
   --#TIMEINDEX 1
   --#HELP ""
   --#HELPTAG 0
   --#STATE OPERATIONAL
   ::= 810

almac2p1vhighoff TRAP-TYPE
   ENTERPRISE enatel
      DESCRIPTION
      "INFORMATION: AC Mains Monitor 2 Phase 1 Voltage High has returned to normal"
   --#TYPE "SM32 Trap"
   --#SUMMARY "AC Mains Monitor 2 Phase 1 Voltage High NORMAL"
   --#ARGUMENTS { }
   --#SEVERITY INFORMATIONAL
   --#TIMEINDEX 1
   --#HELP ""
   --#HELPTAG 0
   --#STATE OPERATIONAL
   ::= 811

almac2p1vlowon TRAP-TYPE
   ENTERPRISE enatel
      DESCRIPTION
      "INFORMATION: AC Mains Monitor 2 Phase 1 Voltage Low "
   --#TYPE "SM32 Trap"
   --#SUMMARY "AC Mains Monitor 2 Phase 1 Voltage Low Active"
   --#ARGUMENTS { }
   --#SEVERITY CRITICAL
   --#TIMEINDEX 1
   --#HELP ""
   --#HELPTAG 0
   --#STATE OPERATIONAL
   ::= 812

almac2p1vlowoff TRAP-TYPE
   ENTERPRISE enatel
      DESCRIPTION
      "INFORMATION: AC Mains Monitor 2 Phase 1 Voltage Low has returned to normal"
   --#TYPE "SM32 Trap"
   --#SUMMARY "AC Mains Monitor 2 Phase 1 Voltage Low NORMAL"
   --#ARGUMENTS { }
   --#SEVERITY INFORMATIONAL
   --#TIMEINDEX 1
   --#HELP ""
   --#HELPTAG 0
   --#STATE OPERATIONAL
   ::= 813

almac2p1loston TRAP-TYPE
   ENTERPRISE enatel
      DESCRIPTION
      "INFORMATION: AC Mains Monitor 2 Phase 1 Lost "
   --#TYPE "SM32 Trap"
   --#SUMMARY "AC Mains Monitor 2 Phase 1 Lost Active"
   --#ARGUMENTS { }
   --#SEVERITY CRITICAL
   --#TIMEINDEX 1
   --#HELP ""
   --#HELPTAG 0
   --#STATE OPERATIONAL
   ::= 814

almac2p1lostoff TRAP-TYPE
   ENTERPRISE enatel
      DESCRIPTION
      "INFORMATION: AC Mains Monitor 2 Phase 1 Lost has returned to normal"
   --#TYPE "SM32 Trap"
   --#SUMMARY "AC Mains Monitor 2 Phase 1 Lost NORMAL"
   --#ARGUMENTS { }
   --#SEVERITY INFORMATIONAL
   --#TIMEINDEX 1
   --#HELP ""
   --#HELPTAG 0
   --#STATE OPERATIONAL
   ::= 815

almac2p1ihighon TRAP-TYPE
   ENTERPRISE enatel
      DESCRIPTION
      "INFORMATION: AC Mains Monitor 2 Phase 1 Current High "
   --#TYPE "SM32 Trap"
   --#SUMMARY "AC Mains Monitor 2 Phase 1 Current High Active"
   --#ARGUMENTS { }
   --#SEVERITY CRITICAL
   --#TIMEINDEX 1
   --#HELP ""
   --#HELPTAG 0
   --#STATE OPERATIONAL
   ::= 816

almac2p1ihighoff TRAP-TYPE
   ENTERPRISE enatel
      DESCRIPTION
      "INFORMATION: AC Mains Monitor 2 Phase 1 Current High has returned to normal"
   --#TYPE "SM32 Trap"
   --#SUMMARY "AC Mains Monitor 2 Phase 1 Current High NORMAL"
   --#ARGUMENTS { }
   --#SEVERITY INFORMATIONAL
   --#TIMEINDEX 1
   --#HELP ""
   --#HELPTAG 0
   --#STATE OPERATIONAL
   ::= 817

almac2p2vhighon TRAP-TYPE
   ENTERPRISE enatel
      DESCRIPTION
      "INFORMATION: AC Mains Monitor 2 Phase 2 Voltage High "
   --#TYPE "SM32 Trap"
   --#SUMMARY "AC Mains Monitor 2 Phase 2 Voltage High Active"
   --#ARGUMENTS { }
   --#SEVERITY CRITICAL
   --#TIMEINDEX 1
   --#HELP ""
   --#HELPTAG 0
   --#STATE OPERATIONAL
   ::= 818

almac2p2vhighoff TRAP-TYPE
   ENTERPRISE enatel
      DESCRIPTION
      "INFORMATION: AC Mains Monitor 2 Phase 2 Voltage High has returned to normal"
   --#TYPE "SM32 Trap"
   --#SUMMARY "AC Mains Monitor 2 Phase 2 Voltage High NORMAL"
   --#ARGUMENTS { }
   --#SEVERITY INFORMATIONAL
   --#TIMEINDEX 1
   --#HELP ""
   --#HELPTAG 0
   --#STATE OPERATIONAL
   ::= 819

almac2p2vlowon TRAP-TYPE
   ENTERPRISE enatel
      DESCRIPTION
      "INFORMATION: AC Mains Monitor 2 Phase 2 Voltage Low "
   --#TYPE "SM32 Trap"
   --#SUMMARY "AC Mains Monitor 2 Phase 2 Voltage Low Active"
   --#ARGUMENTS { }
   --#SEVERITY CRITICAL
   --#TIMEINDEX 1
   --#HELP ""
   --#HELPTAG 0
   --#STATE OPERATIONAL
   ::= 820

almac2p2vlowoff TRAP-TYPE
   ENTERPRISE enatel
      DESCRIPTION
      "INFORMATION: AC Mains Monitor 2 Phase 2 Voltage Low has returned to normal"
   --#TYPE "SM32 Trap"
   --#SUMMARY "AC Mains Monitor 2 Phase 2 Voltage Low NORMAL"
   --#ARGUMENTS { }
   --#SEVERITY INFORMATIONAL
   --#TIMEINDEX 1
   --#HELP ""
   --#HELPTAG 0
   --#STATE OPERATIONAL
   ::= 821

almac2p2loston TRAP-TYPE
   ENTERPRISE enatel
      DESCRIPTION
      "INFORMATION: AC Mains Monitor 2 Phase 2 Lost "
   --#TYPE "SM32 Trap"
   --#SUMMARY "AC Mains Monitor 2 Phase 2 Lost Active"
   --#ARGUMENTS { }
   --#SEVERITY CRITICAL
   --#TIMEINDEX 1
   --#HELP ""
   --#HELPTAG 0
   --#STATE OPERATIONAL
   ::= 822

almac2p2lostoff TRAP-TYPE
   ENTERPRISE enatel
      DESCRIPTION
      "INFORMATION: AC Mains Monitor 2 Phase 2 Lost has returned to normal"
   --#TYPE "SM32 Trap"
   --#SUMMARY "AC Mains Monitor 2 Phase 2 Lost NORMAL"
   --#ARGUMENTS { }
   --#SEVERITY INFORMATIONAL
   --#TIMEINDEX 1
   --#HELP ""
   --#HELPTAG 0
   --#STATE OPERATIONAL
   ::= 823

almac2p2ihighon TRAP-TYPE
   ENTERPRISE enatel
      DESCRIPTION
      "INFORMATION: AC Mains Monitor 2 Phase 2 Current High "
   --#TYPE "SM32 Trap"
   --#SUMMARY "AC Mains Monitor 2 Phase 2 Current High Active"
   --#ARGUMENTS { }
   --#SEVERITY CRITICAL
   --#TIMEINDEX 1
   --#HELP ""
   --#HELPTAG 0
   --#STATE OPERATIONAL
   ::= 824

almac2p2ihighoff TRAP-TYPE
   ENTERPRISE enatel
      DESCRIPTION
      "INFORMATION: AC Mains Monitor 2 Phase 2 Current High has returned to normal"
   --#TYPE "SM32 Trap"
   --#SUMMARY "AC Mains Monitor 2 Phase 2 Current High NORMAL"
   --#ARGUMENTS { }
   --#SEVERITY INFORMATIONAL
   --#TIMEINDEX 1
   --#HELP ""
   --#HELPTAG 0
   --#STATE OPERATIONAL
   ::= 825

almac2p3vhighon TRAP-TYPE
   ENTERPRISE enatel
      DESCRIPTION
      "INFORMATION: AC Mains Monitor 2 Phase 3 Voltage High "
   --#TYPE "SM32 Trap"
   --#SUMMARY "AC Mains Monitor 2 Phase 3 Voltage High Active"
   --#ARGUMENTS { }
   --#SEVERITY CRITICAL
   --#TIMEINDEX 1
   --#HELP ""
   --#HELPTAG 0
   --#STATE OPERATIONAL
   ::= 826

almac2p3vhighoff TRAP-TYPE
   ENTERPRISE enatel
      DESCRIPTION
      "INFORMATION: AC Mains Monitor 2 Phase 3 Voltage High has returned to normal"
   --#TYPE "SM32 Trap"
   --#SUMMARY "AC Mains Monitor 2 Phase 3 Voltage High NORMAL"
   --#ARGUMENTS { }
   --#SEVERITY INFORMATIONAL
   --#TIMEINDEX 1
   --#HELP ""
   --#HELPTAG 0
   --#STATE OPERATIONAL
   ::= 827

almac2p3vlowon TRAP-TYPE
   ENTERPRISE enatel
      DESCRIPTION
      "INFORMATION: AC Mains Monitor 2 Phase 3 Voltage Low "
   --#TYPE "SM32 Trap"
   --#SUMMARY "AC Mains Monitor 2 Phase 3 Voltage Low Active"
   --#ARGUMENTS { }
   --#SEVERITY CRITICAL
   --#TIMEINDEX 1
   --#HELP ""
   --#HELPTAG 0
   --#STATE OPERATIONAL
   ::= 828

almac2p3vlowoff TRAP-TYPE
   ENTERPRISE enatel
      DESCRIPTION
      "INFORMATION: AC Mains Monitor 2 Phase 3 Voltage Low has returned to normal"
   --#TYPE "SM32 Trap"
   --#SUMMARY "AC Mains Monitor 2 Phase 3 Voltage Low NORMAL"
   --#ARGUMENTS { }
   --#SEVERITY INFORMATIONAL
   --#TIMEINDEX 1
   --#HELP ""
   --#HELPTAG 0
   --#STATE OPERATIONAL
   ::= 829

almac2p3loston TRAP-TYPE
   ENTERPRISE enatel
      DESCRIPTION
      "INFORMATION: AC Mains Monitor 2 Phase 3 Lost "
   --#TYPE "SM32 Trap"
   --#SUMMARY "AC Mains Monitor 2 Phase 3 Lost Active"
   --#ARGUMENTS { }
   --#SEVERITY CRITICAL
   --#TIMEINDEX 1
   --#HELP ""
   --#HELPTAG 0
   --#STATE OPERATIONAL
   ::= 830

almac2p3lostoff TRAP-TYPE
   ENTERPRISE enatel
      DESCRIPTION
      "INFORMATION: AC Mains Monitor 2 Phase 3 Lost has returned to normal"
   --#TYPE "SM32 Trap"
   --#SUMMARY "AC Mains Monitor 2 Phase 3 Lost NORMAL"
   --#ARGUMENTS { }
   --#SEVERITY INFORMATIONAL
   --#TIMEINDEX 1
   --#HELP ""
   --#HELPTAG 0
   --#STATE OPERATIONAL
   ::= 831

almac2p3ihighon TRAP-TYPE
   ENTERPRISE enatel
      DESCRIPTION
      "INFORMATION: AC Mains Monitor 2 Phase 3 Current High "
   --#TYPE "SM32 Trap"
   --#SUMMARY "AC Mains Monitor 2 Phase 3 Current High Active"
   --#ARGUMENTS { }
   --#SEVERITY CRITICAL
   --#TIMEINDEX 1
   --#HELP ""
   --#HELPTAG 0
   --#STATE OPERATIONAL
   ::= 832

almac2p3ihighoff TRAP-TYPE
   ENTERPRISE enatel
      DESCRIPTION
      "INFORMATION: AC Mains Monitor 2 Phase 3 Current High has returned to normal"
   --#TYPE "SM32 Trap"
   --#SUMMARY "AC Mains Monitor 2 Phase 3 Current High NORMAL"
   --#ARGUMENTS { }
   --#SEVERITY INFORMATIONAL
   --#TIMEINDEX 1
   --#HELP ""
   --#HELPTAG 0
   --#STATE OPERATIONAL
   ::= 833

almac2freqhighon TRAP-TYPE
   ENTERPRISE enatel
      DESCRIPTION
      "INFORMATION: AC Mains Monitor 2 Frequency High "
   --#TYPE "SM32 Trap"
   --#SUMMARY "AC Mains Monitor 2 Frequency High Active"
   --#ARGUMENTS { }
   --#SEVERITY CRITICAL
   --#TIMEINDEX 1
   --#HELP ""
   --#HELPTAG 0
   --#STATE OPERATIONAL
   ::= 834

almac2freqhighoff TRAP-TYPE
   ENTERPRISE enatel
      DESCRIPTION
      "INFORMATION: AC Mains Monitor 2 Frequency High has returned to normal"
   --#TYPE "SM32 Trap"
   --#SUMMARY "AC Mains Monitor 2 Frequency High NORMAL"
   --#ARGUMENTS { }
   --#SEVERITY INFORMATIONAL
   --#TIMEINDEX 1
   --#HELP ""
   --#HELPTAG 0
   --#STATE OPERATIONAL
   ::= 835

almac2freqlowon TRAP-TYPE
   ENTERPRISE enatel
      DESCRIPTION
      "INFORMATION: AC Mains Monitor 2 Frequency Low "
   --#TYPE "SM32 Trap"
   --#SUMMARY "AC Mains Monitor 2 Frequency Low Active"
   --#ARGUMENTS { }
   --#SEVERITY CRITICAL
   --#TIMEINDEX 1
   --#HELP ""
   --#HELPTAG 0
   --#STATE OPERATIONAL
   ::= 836

almac2freqlowoff TRAP-TYPE
   ENTERPRISE enatel
      DESCRIPTION
      "INFORMATION: AC Mains Monitor 2 Frequency Low has returned to normal"
   --#TYPE "SM32 Trap"
   --#SUMMARY "AC Mains Monitor 2 Frequency Low NORMAL"
   --#ARGUMENTS { }
   --#SEVERITY INFORMATIONAL
   --#TIMEINDEX 1
   --#HELP ""
   --#HELPTAG 0
   --#STATE OPERATIONAL
   ::= 837


END
