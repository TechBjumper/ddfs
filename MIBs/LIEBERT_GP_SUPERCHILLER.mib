LIEBERT-GP-SUPERCHILLER-MIB DEFINITIONS ::= BEGIN

IMPORTS
         OBJECT-TYPE
                 FROM RFC-1212
	    lgpAcProducts
			    FROM LIEBERT-GP-REGISTRATION-MIB;

lgpSuperChiller OBJECT-IDENTITY
   STATUS      current
   DESCRIPTION "This branch is used to register Liebert Environmental 
               SuperChiller product information."
    ::= { lgpAcProducts 20 }


Microface OBJECT-IDENTITY
   STATUS      current
   DESCRIPTION "This branch contains Miroface variables."
    ::= { lgpSuperChiller 1 }

Hironet OBJECT-IDENTITY
   STATUS      current
   DESCRIPTION "This branch contains Hironet structure."
    ::= { Microface 1 }

-- =============================================================================
--  HironetBlockId - Hironet Block Structure
-- =============================================================================

HironetBlockId4 OBJECT-IDENTITY
   STATUS      current
   DESCRIPTION "This branch contains Hironet Block 4."
    ::= { Hironet 4 }

-- =============================================================================
--  Block 4
-- =============================================================================

RtcMin OBJECT-TYPE
     SYNTAX  INTEGER 
     ACCESS  read-write
     STATUS  mandatory
     DESCRIPTION
             "Real Time Clock minutes"
     ::= { HironetBlockId4 1 }

-- =============================================================================
--  End Block 4
-- =============================================================================

HironetBlockId5 OBJECT-IDENTITY
   STATUS      current
   DESCRIPTION "This branch contains Hironet Block 5."
    ::= { Hironet 5 }

-- =============================================================================
--  Block 5
-- =============================================================================

RtcHou OBJECT-TYPE
     SYNTAX  INTEGER
     ACCESS  read-write
     STATUS  mandatory
     DESCRIPTION
             "Real Time Clock hours"
     ::= { HironetBlockId5 1 }

RtcDay OBJECT-TYPE
     SYNTAX  INTEGER
     ACCESS  read-write
     STATUS  mandatory
     DESCRIPTION
             "Real Time Clock day"
     ::= { HironetBlockId5 2 }

RtcMon OBJECT-TYPE
     SYNTAX  INTEGER
     ACCESS  read-write
     STATUS  mandatory
     DESCRIPTION
             "Real Time Clock month"
     ::= { HironetBlockId5 3 }
     
RtcYea OBJECT-TYPE
     SYNTAX  INTEGER
     ACCESS  read-write
     STATUS  mandatory
     DESCRIPTION
             "Real Time Clock year"
     ::= { HironetBlockId5 4 }

-- =============================================================================
--  End Block 5
-- =============================================================================

HironetBlockId6 OBJECT-IDENTITY
   STATUS      current
   DESCRIPTION "This branch contains Hironet Block 6."
    ::= { Hironet 6 }

-- =============================================================================
--  Block 6
-- =============================================================================

TimeRec12M OBJECT-TYPE
     SYNTAX  INTEGER
     ACCESS  read-write
     STATUS  mandatory
     DESCRIPTION
             "Microface Logging Time of Graphic Data Record 1 and 2 (Temp + Humi); 0=2.5min, 1=5min, 2=30min, 3=1h, 4=12h, 5=24h, 6=2d, 7=4d, 8=8d."
     ::= { HironetBlockId6 1 }

TimeRec34M OBJECT-TYPE
     SYNTAX  INTEGER
     ACCESS  read-write
     STATUS  mandatory
     DESCRIPTION
             "Microface Logging Time of Graphic Data Record 3 and 4 (Temp + Humi); 0=2.5min, 1=5min, 2=30min, 3=1h, 4=12h, 5=24h, 6=2d, 7=4d, 8=8d."
     ::= { HironetBlockId6 2 }

HandShakHL OBJECT-TYPE
     SYNTAX  INTEGER
     ACCESS  read-write
     STATUS  mandatory
     DESCRIPTION
             "Connectivity handshake-status between Mic and Hirolink. -1 = Connectivity deactivated (Set by HL) , 0 = Connectivity Off (Set by Mic) , 1 = Start / Save Original Setpoints (Set by HL) , 2 = Ready / Setpoints Stored (Set by Mic) , 3 = HL Alive / Change Value (Set by HL) , 4 = Timeout Refreshed / Change Done (Set by Mic) , 5 = Stop / Restore Setpoints (Set by HL)"
     ::= { HironetBlockId6 3 }

-- =============================================================================
--  End Block 6
-- =============================================================================

HironetBlockId7 OBJECT-IDENTITY
   STATUS      current
   DESCRIPTION "This branch contains Hironet Block 7."
    ::= { Hironet 7 }

-- =============================================================================
--  Block 7
-- =============================================================================

OuTempSet2 OBJECT-TYPE
     SYNTAX  INTEGER
     ACCESS  read-write
     STATUS  mandatory
     DESCRIPTION
             "Outlet temp. setpoint 2 (-6 = NO)."
     ::= { HironetBlockId7 1 }

OuTempSetS OBJECT-TYPE
     SYNTAX  INTEGER
     ACCESS  read-write
     STATUS  mandatory
     DESCRIPTION
             " "
     ::= { HironetBlockId7 2 }

OutTempSet OBJECT-TYPE
     SYNTAX  INTEGER
     ACCESS  read-write
     STATUS  mandatory
     DESCRIPTION
             " "
     ::= { HironetBlockId7 3 }

-- =============================================================================
--  End Block 7
-- =============================================================================

HironetBlockId8 OBJECT-IDENTITY
   STATUS      current
   DESCRIPTION "This branch contains Hironet Block 8."
    ::= { Hironet 8 }

-- =============================================================================
--  Block 8
-- =============================================================================

CondHysBar OBJECT-TYPE
     SYNTAX  INTEGER
     ACCESS  read-write
     STATUS  mandatory
     DESCRIPTION
             " "
     ::= { HironetBlockId8 1 }

FanSpeedCo OBJECT-TYPE
     SYNTAX  INTEGER
     ACCESS  read-write
     STATUS  mandatory
     DESCRIPTION
             " "
     ::= { HironetBlockId8 2 }

AntiFreeze OBJECT-TYPE
     SYNTAX  INTEGER
     ACCESS  read-write
     STATUS  mandatory
     DESCRIPTION
             " "
     ::= { HironetBlockId8 3 }

OutThermo OBJECT-TYPE
     SYNTAX  INTEGER
     ACCESS  read-write
     STATUS  mandatory
     DESCRIPTION
             " "
     ::= { HironetBlockId8 4 }

BirneSetp OBJECT-TYPE
     SYNTAX  INTEGER
     ACCESS  read-write
     STATUS  mandatory
     DESCRIPTION
             " "
     ::= { HironetBlockId8 5 }

OuTeSetInt OBJECT-TYPE
     SYNTAX  INTEGER
     ACCESS  read-write
     STATUS  mandatory
     DESCRIPTION
             " "
     ::= { HironetBlockId8 6 }

OuTeSetHL OBJECT-TYPE
     SYNTAX  INTEGER
     ACCESS  read-write
     STATUS  mandatory
     DESCRIPTION
             " "
     ::= { HironetBlockId8 7 }

-- =============================================================================
--  End Block 8
-- =============================================================================

HironetBlockId9 OBJECT-IDENTITY
   STATUS      current
   DESCRIPTION "This branch contains Hironet Block 9."
    ::= { Hironet 9 }

-- =============================================================================
--  Block 9
-- =============================================================================

dtRoomAmb OBJECT-TYPE
     SYNTAX  INTEGER
     ACCESS  read-write
     STATUS  mandatory
     DESCRIPTION
             " "
     ::= { HironetBlockId9 1 }

CondSetp2 OBJECT-TYPE
     SYNTAX  INTEGER
     ACCESS  read-write
     STATUS  mandatory
     DESCRIPTION
             " "
     ::= { HironetBlockId9 2 }

CondIntg OBJECT-TYPE
     SYNTAX  INTEGER
     ACCESS  read-write
     STATUS  mandatory
     DESCRIPTION
             " "
     ::= { HironetBlockId9 3 }

StopCoLT OBJECT-TYPE
     SYNTAX  INTEGER
     ACCESS  read-write
     STATUS  mandatory
     DESCRIPTION
             " "
     ::= { HironetBlockId9 4 }

-- =============================================================================
--  End Block 9
-- =============================================================================

HironetBlockId10 OBJECT-IDENTITY
   STATUS      current
   DESCRIPTION "This branch contains Hironet Block 10."
    ::= { Hironet 10 }

-- =============================================================================
--  Block 10
-- =============================================================================

CompMiTime OBJECT-TYPE
     SYNTAX  INTEGER
     ACCESS  read-write
     STATUS  mandatory
     DESCRIPTION
             " "
     ::= { HironetBlockId10 1 }

PumpOverLa OBJECT-TYPE
     SYNTAX  INTEGER
     ACCESS  read-write
     STATUS  mandatory
     DESCRIPTION
             " "
     ::= { HironetBlockId10 2 }

FCDisaPart OBJECT-TYPE
     SYNTAX  INTEGER
     ACCESS  read-write
     STATUS  mandatory
     DESCRIPTION
             " "
     ::= { HironetBlockId10 3 }

CondContr OBJECT-TYPE
     SYNTAX  INTEGER
     ACCESS  read-write
     STATUS  mandatory
     DESCRIPTION
             " "
     ::= { HironetBlockId10 4 }

SP1AmbLo OBJECT-TYPE
     SYNTAX  INTEGER
     ACCESS  read-write
     STATUS  mandatory
     DESCRIPTION
             " "
     ::= { HironetBlockId10 5 }

SP2AmbHi OBJECT-TYPE
     SYNTAX  INTEGER
     ACCESS  read-write
     STATUS  mandatory
     DESCRIPTION
             " "
     ::= { HironetBlockId10 6 }

UserInpSe2 OBJECT-TYPE
     SYNTAX  INTEGER
     ACCESS  read-write
     STATUS  mandatory
     DESCRIPTION
             " "
     ::= { HironetBlockId10 7 }

-- =============================================================================
--  End Block 10
-- =============================================================================

HironetBlockId11 OBJECT-IDENTITY
   STATUS      current
   DESCRIPTION "This branch contains Hironet Block 11."
    ::= { Hironet 11 }

-- =============================================================================
--  Block 11
-- =============================================================================

HourPump1 OBJECT-TYPE
     SYNTAX  INTEGER
     ACCESS  read-write
     STATUS  mandatory
     DESCRIPTION
             " "
     ::= { HironetBlockId11 1 }

HourPump2 OBJECT-TYPE
     SYNTAX  INTEGER
     ACCESS  read-write
     STATUS  mandatory
     DESCRIPTION
             " "
     ::= { HironetBlockId11 2 }

HourComp1 OBJECT-TYPE
     SYNTAX  INTEGER
     ACCESS  read-write
     STATUS  mandatory
     DESCRIPTION
             " "
     ::= { HironetBlockId11 3 }

HourComp2 OBJECT-TYPE
     SYNTAX  INTEGER
     ACCESS  read-write
     STATUS  mandatory
     DESCRIPTION
             " "
     ::= { HironetBlockId11 4 }

HourFC OBJECT-TYPE
     SYNTAX  INTEGER
     ACCESS  read-write
     STATUS  mandatory
     DESCRIPTION
             " "
     ::= { HironetBlockId11 5 }

HourPump1M OBJECT-TYPE
     SYNTAX  INTEGER
     ACCESS  read-write
     STATUS  mandatory
     DESCRIPTION
             " "
     ::= { HironetBlockId11 6 }

HourPump2M OBJECT-TYPE
     SYNTAX  INTEGER
     ACCESS  read-write
     STATUS  mandatory
     DESCRIPTION
             " "
     ::= { HironetBlockId11 7 }

HourComp1M OBJECT-TYPE
     SYNTAX  INTEGER
     ACCESS  read-write
     STATUS  mandatory
     DESCRIPTION
             " "
     ::= { HironetBlockId11 8 }

HourComp2M OBJECT-TYPE
     SYNTAX  INTEGER
     ACCESS  read-write
     STATUS  mandatory
     DESCRIPTION
             " "
     ::= { HironetBlockId11 9 }

HourFCM OBJECT-TYPE
     SYNTAX  INTEGER
     ACCESS  read-write
     STATUS  mandatory
     DESCRIPTION
             " "
     ::= { HironetBlockId11 10 }

-- =============================================================================
--  End Block 11
-- =============================================================================

HironetBlockId12 OBJECT-IDENTITY
   STATUS      current
   DESCRIPTION "This branch contains Hironet Block 12."
    ::= { Hironet 12 }

-- =============================================================================
--  Block 12
-- =============================================================================

HourComp3 OBJECT-TYPE
     SYNTAX  INTEGER
     ACCESS  read-write
     STATUS  mandatory
     DESCRIPTION
             " "
     ::= { HironetBlockId12 1 }

HourComp4 OBJECT-TYPE
     SYNTAX  INTEGER
     ACCESS  read-write
     STATUS  mandatory
     DESCRIPTION
             " "
     ::= { HironetBlockId12 2 }

HourComp3M OBJECT-TYPE
     SYNTAX  INTEGER
     ACCESS  read-write
     STATUS  mandatory
     DESCRIPTION
             " "
     ::= { HironetBlockId12 3 }

HourComp4M OBJECT-TYPE
     SYNTAX  INTEGER
     ACCESS  read-write
     STATUS  mandatory
     DESCRIPTION
             " "
     ::= { HironetBlockId12 4 }

-- =============================================================================
--  End Block 12
-- =============================================================================

HironetBlockId13 OBJECT-IDENTITY
   STATUS      current
   DESCRIPTION "This branch contains Hironet Block 13."
    ::= { Hironet 13 }

-- =============================================================================
--  Block 13
-- =============================================================================

HWTempInWa OBJECT-TYPE
     SYNTAX  INTEGER
     ACCESS  read-write
     STATUS  mandatory
     DESCRIPTION
             " "
     ::= { HironetBlockId13 1 }

LWTempInWa OBJECT-TYPE
     SYNTAX  INTEGER
     ACCESS  read-write
     STATUS  mandatory
     DESCRIPTION
             " "
     ::= { HironetBlockId13 2 }

HWTempOutWa OBJECT-TYPE
     SYNTAX  INTEGER
     ACCESS  read-write
     STATUS  mandatory
     DESCRIPTION
             " "
     ::= { HironetBlockId13 3 }

LWTempOutWa OBJECT-TYPE
     SYNTAX  INTEGER
     ACCESS  read-write
     STATUS  mandatory
     DESCRIPTION
             " "
     ::= { HironetBlockId13 4 }

HWTempInAl OBJECT-TYPE
     SYNTAX  INTEGER
     ACCESS  read-write
     STATUS  mandatory
     DESCRIPTION
             " "
     ::= { HironetBlockId13 5 }

LWTempInAl OBJECT-TYPE
     SYNTAX  INTEGER
     ACCESS  read-write
     STATUS  mandatory
     DESCRIPTION
             " "
     ::= { HironetBlockId13 6 }

HWTempOutAl OBJECT-TYPE
     SYNTAX  INTEGER
     ACCESS  read-write
     STATUS  mandatory
     DESCRIPTION
             " "
     ::= { HironetBlockId13 7 }

LWTempOutAl OBJECT-TYPE
     SYNTAX  INTEGER
     ACCESS  read-write
     STATUS  mandatory
     DESCRIPTION
             " "
     ::= { HironetBlockId13 8 }

FreezeAuMa OBJECT-TYPE
     SYNTAX  INTEGER
     ACCESS  read-write
     STATUS  mandatory
     DESCRIPTION
             " "
     ::= { HironetBlockId13 9 }

LWPressAt OBJECT-TYPE
     SYNTAX  INTEGER
     ACCESS  read-write
     STATUS  mandatory
     DESCRIPTION
             " "
     ::= { HironetBlockId13 10 }

-- =============================================================================
--  End Block 13
-- =============================================================================

HironetBlockId14 OBJECT-IDENTITY
   STATUS      current
   DESCRIPTION "This branch contains Hironet Block 14."
    ::= { Hironet 14 }

-- =============================================================================
--  Block 14
-- =============================================================================

CompLowPrD OBJECT-TYPE
     SYNTAX  INTEGER
     ACCESS  read-write
     STATUS  mandatory
     DESCRIPTION
             " "
     ::= { HironetBlockId14 1 }

LWPresWaAl OBJECT-TYPE
     SYNTAX  INTEGER
     ACCESS  read-write
     STATUS  mandatory
     DESCRIPTION
             " "
     ::= { HironetBlockId14 2 }

CompHiPrWa OBJECT-TYPE
     SYNTAX  INTEGER
     ACCESS  read-write
     STATUS  mandatory
     DESCRIPTION
             " "
     ::= { HironetBlockId14 3 }

FreezeWaAt OBJECT-TYPE
     SYNTAX  INTEGER
     ACCESS  read-write
     STATUS  mandatory
     DESCRIPTION
             " "
     ::= { HironetBlockId14 4 }

-- =============================================================================
--  End Block 14
-- =============================================================================

HironetBlockId15 OBJECT-IDENTITY
   STATUS      current
   DESCRIPTION "This branch contains Hironet Block 15."
    ::= { Hironet 15 }

-- =============================================================================
--  Block 15
-- =============================================================================

LiqInjSta OBJECT-TYPE
     SYNTAX  INTEGER
     ACCESS  read-write
     STATUS  mandatory
     DESCRIPTION
             " "
     ::= { HironetBlockId15 1 }

LiqInjSto OBJECT-TYPE
     SYNTAX  INTEGER
     ACCESS  read-write
     STATUS  mandatory
     DESCRIPTION
             " "
     ::= { HironetBlockId15 2 }

-- =============================================================================
--  End Block 15
-- =============================================================================

HironetBlockId16 OBJECT-IDENTITY
   STATUS      current
   DESCRIPTION "This branch contains Hironet Block 16."
    ::= { Hironet 16 }

-- =============================================================================
--  Block 16
-- =============================================================================

StaStbyAt OBJECT-TYPE
     SYNTAX  INTEGER
     ACCESS  read-write
     STATUS  mandatory
     DESCRIPTION
             " "
     ::= { HironetBlockId16 1 }

UnitsMic OBJECT-TYPE
     SYNTAX  INTEGER
     ACCESS  read-write
     STATUS  mandatory
     DESCRIPTION
             " "
     ::= { HironetBlockId16 2 }

StdByUnits OBJECT-TYPE
     SYNTAX  INTEGER
     ACCESS  read-write
     STATUS  mandatory
     DESCRIPTION
             " "
     ::= { HironetBlockId16 3 }

RotationEN OBJECT-TYPE
     SYNTAX  INTEGER
     ACCESS  read-write
     STATUS  mandatory
     DESCRIPTION
             " "
     ::= { HironetBlockId16 4 }

RotatHou OBJECT-TYPE
     SYNTAX  INTEGER
     ACCESS  read-write
     STATUS  mandatory
     DESCRIPTION
             " "
     ::= { HironetBlockId16 5 }

RotatMin OBJECT-TYPE
     SYNTAX  INTEGER
     ACCESS  read-write
     STATUS  mandatory
     DESCRIPTION
             " "
     ::= { HironetBlockId16 6 }

AuRestart OBJECT-TYPE
     SYNTAX  INTEGER
     ACCESS  read-write
     STATUS  mandatory
     DESCRIPTION
             " "
     ::= { HironetBlockId16 7 }

ShareEN OBJECT-TYPE
     SYNTAX  INTEGER
     ACCESS  read-write
     STATUS  mandatory
     DESCRIPTION
             " "
     ::= { HironetBlockId16 8 }

CascadeEN OBJECT-TYPE
     SYNTAX  INTEGER
     ACCESS  read-write
     STATUS  mandatory
     DESCRIPTION
             " "
     ::= { HironetBlockId16 9 }

-- =============================================================================
--  End Block 16
-- =============================================================================

HironetBlockId17 OBJECT-IDENTITY
   STATUS      current
   DESCRIPTION "This branch contains Hironet Block 17."
    ::= { Hironet 17 }

-- =============================================================================
--  Block 17
-- =============================================================================

PerformRot OBJECT-TYPE
     SYNTAX  INTEGER
     ACCESS  read-write
     STATUS  mandatory
     DESCRIPTION
             " "
     ::= { HironetBlockId17 1 }

MicRotaEN OBJECT-TYPE
     SYNTAX  INTEGER
     ACCESS  read-write
     STATUS  mandatory
     DESCRIPTION
             " "
     ::= { HironetBlockId17 2 }

HMSysOnMi OBJECT-TYPE
     SYNTAX  INTEGER
     ACCESS  read-write
     STATUS  mandatory
     DESCRIPTION
             " "
     ::= { HironetBlockId17 3 }

-- =============================================================================
--  End Block 17
-- =============================================================================

HironetBlockId18 OBJECT-IDENTITY
   STATUS      current
   DESCRIPTION "This branch contains Hironet Block 18."
    ::= { Hironet 18 }

-- =============================================================================
--  Block 18
-- =============================================================================

GenAlarm OBJECT-TYPE
     SYNTAX  INTEGER
     ACCESS  read-write
     STATUS  mandatory
     DESCRIPTION
             " "
     ::= { HironetBlockId18 1 }

-- =============================================================================
--  End Block 18
-- =============================================================================

HironetBlockId19 OBJECT-IDENTITY
   STATUS      current
   DESCRIPTION "This branch contains Hironet Block 19."
    ::= { Hironet 19 }

-- =============================================================================
--  Block 19
-- =============================================================================

SymCool1 OBJECT-TYPE
     SYNTAX  INTEGER
     ACCESS  read-only
     STATUS  mandatory
     DESCRIPTION
             " "
     ::= { HironetBlockId19 1 }

SymCool2 OBJECT-TYPE
     SYNTAX  INTEGER
     ACCESS  read-only
     STATUS  mandatory
     DESCRIPTION
             " "
     ::= { HironetBlockId19 2 }

SymCool3 OBJECT-TYPE
     SYNTAX  INTEGER
     ACCESS  read-only
     STATUS  mandatory
     DESCRIPTION
             " "
     ::= { HironetBlockId19 3 }

SymCool4 OBJECT-TYPE
     SYNTAX  INTEGER
     ACCESS  read-only
     STATUS  mandatory
     DESCRIPTION
             " "
     ::= { HironetBlockId19 4 }

SymPump1 OBJECT-TYPE
     SYNTAX  INTEGER
     ACCESS  read-only
     STATUS  mandatory
     DESCRIPTION
             " "
     ::= { HironetBlockId19 5 }

SymPump2 OBJECT-TYPE
     SYNTAX  INTEGER
     ACCESS  read-only
     STATUS  mandatory
     DESCRIPTION
             " "
     ::= { HironetBlockId19 6 }

-- =============================================================================
--  End Block 19
-- =============================================================================

HironetBlockId20 OBJECT-IDENTITY
   STATUS      current
   DESCRIPTION "This branch contains Hironet Block 20."
    ::= { Hironet 20 }

-- =============================================================================
--  Block 20
-- =============================================================================

UnitAlarm OBJECT-TYPE
     SYNTAX  INTEGER
     ACCESS  read-only
     STATUS  mandatory
     DESCRIPTION
             " "
     ::= { HironetBlockId20 1 }

SinglState OBJECT-TYPE
     SYNTAX  INTEGER
     ACCESS  read-only
     STATUS  mandatory
     DESCRIPTION
             " "
     ::= { HironetBlockId20 2 }

TempSetac OBJECT-TYPE
     SYNTAX  INTEGER
     ACCESS  read-only
     STATUS  mandatory
     DESCRIPTION
             " "
     ::= { HironetBlockId20 3 }

FCCond OBJECT-TYPE
     SYNTAX  INTEGER
     ACCESS  read-only
     STATUS  mandatory
     DESCRIPTION
             " "
     ::= { HironetBlockId20 4 }

-- =============================================================================
--  End Block 20
-- =============================================================================

HironetBlockId21 OBJECT-IDENTITY
   STATUS      current
   DESCRIPTION "This branch contains Hironet Block 21."
    ::= { Hironet 21 }

-- =============================================================================
--  Block 21
-- =============================================================================

FCBarDi OBJECT-TYPE
     SYNTAX  INTEGER
     ACCESS  read-only
     STATUS  mandatory
     DESCRIPTION
             " "
     ::= { HironetBlockId21 1 }

DEBarDi OBJECT-TYPE
     SYNTAX  INTEGER
     ACCESS  read-only
     STATUS  mandatory
     DESCRIPTION
             " "
     ::= { HironetBlockId21 2 }

ShDEBarDi OBJECT-TYPE
     SYNTAX  INTEGER
     ACCESS  read-only
     STATUS  mandatory
     DESCRIPTION
             " "
     ::= { HironetBlockId21 3 }

ShFCBarDi OBJECT-TYPE
     SYNTAX  INTEGER
     ACCESS  read-only
     STATUS  mandatory
     DESCRIPTION
             " "
     ::= { HironetBlockId21 4 }

SingStatDi OBJECT-TYPE
     SYNTAX  INTEGER
     ACCESS  read-only
     STATUS  mandatory
     DESCRIPTION
             " "
     ::= { HironetBlockId21 5 }

-- =============================================================================
--  End Block 21
-- =============================================================================

HironetBlockId22 OBJECT-IDENTITY
   STATUS      current
   DESCRIPTION "This branch contains Hironet Block 22."
    ::= { Hironet 22 }

-- =============================================================================
--  Block 22
-- =============================================================================

InFlowStat OBJECT-TYPE
     SYNTAX  INTEGER
     ACCESS  read-only
     STATUS  mandatory
     DESCRIPTION
             " "
     ::= { HironetBlockId22 1 }

InLP1Stat OBJECT-TYPE
     SYNTAX  INTEGER
     ACCESS  read-only
     STATUS  mandatory
     DESCRIPTION
             " "
     ::= { HironetBlockId22 2 }

InLP2Stat OBJECT-TYPE
     SYNTAX  INTEGER
     ACCESS  read-only
     STATUS  mandatory
     DESCRIPTION
             " "
     ::= { HironetBlockId22 3 }

InHP1Stat OBJECT-TYPE
     SYNTAX  INTEGER
     ACCESS  read-only
     STATUS  mandatory
     DESCRIPTION
             " "
     ::= { HironetBlockId22 4 }

InHP2Stat OBJECT-TYPE
     SYNTAX  INTEGER
     ACCESS  read-only
     STATUS  mandatory
     DESCRIPTION
             " "
     ::= { HironetBlockId22 5 }

-- =============================================================================
--  End Block 22
-- =============================================================================

HironetBlockId23 OBJECT-IDENTITY
   STATUS      current
   DESCRIPTION "This branch contains Hironet Block 23."
    ::= { Hironet 23 }

-- =============================================================================
--  Block 23
-- =============================================================================

InTH1Stat OBJECT-TYPE
     SYNTAX  INTEGER
     ACCESS  read-only
     STATUS  mandatory
     DESCRIPTION
             " "
     ::= { HironetBlockId23 1 }

InTH2Stat OBJECT-TYPE
     SYNTAX  INTEGER
     ACCESS  read-only
     STATUS  mandatory
     DESCRIPTION
             " "
     ::= { HironetBlockId23 2 }

InOil1Stat OBJECT-TYPE
     SYNTAX  INTEGER
     ACCESS  read-only
     STATUS  mandatory
     DESCRIPTION
             " "
     ::= { HironetBlockId23 3 }

InOil2Stat OBJECT-TYPE
     SYNTAX  INTEGER
     ACCESS  read-only
     STATUS  mandatory
     DESCRIPTION
             " "
     ::= { HironetBlockId23 4 }

InHP3Stat OBJECT-TYPE
     SYNTAX  INTEGER
     ACCESS  read-only
     STATUS  mandatory
     DESCRIPTION
             " "
     ::= { HironetBlockId23 5 }

InHP4Stat OBJECT-TYPE
     SYNTAX  INTEGER
     ACCESS  read-only
     STATUS  mandatory
     DESCRIPTION
             " "
     ::= { HironetBlockId23 6 }

InLP3Stat OBJECT-TYPE
     SYNTAX  INTEGER
     ACCESS  read-only
     STATUS  mandatory
     DESCRIPTION
             " "
     ::= { HironetBlockId23 7 }

InLP4Stat OBJECT-TYPE
     SYNTAX  INTEGER
     ACCESS  read-only
     STATUS  mandatory
     DESCRIPTION
             " "
     ::= { HironetBlockId23 8 }

InOil3Stat OBJECT-TYPE
     SYNTAX  INTEGER
     ACCESS  read-only
     STATUS  mandatory
     DESCRIPTION
             " "
     ::= { HironetBlockId23 9 }

InOil4Stat OBJECT-TYPE
     SYNTAX  INTEGER
     ACCESS  read-only
     STATUS  mandatory
     DESCRIPTION
             " "
     ::= { HironetBlockId23 10 }

InTH3Stat OBJECT-TYPE
     SYNTAX  INTEGER
     ACCESS  read-only
     STATUS  mandatory
     DESCRIPTION
             " "
     ::= { HironetBlockId23 11 }

InTH4Stat OBJECT-TYPE
     SYNTAX  INTEGER
     ACCESS  read-only
     STATUS  mandatory
     DESCRIPTION
             " "
     ::= { HironetBlockId23 12 }

-- =============================================================================
--  End Block 23
-- =============================================================================

HironetBlockId24 OBJECT-IDENTITY
   STATUS      current
   DESCRIPTION "This branch contains Hironet Block 24."
    ::= { Hironet 24 }

-- =============================================================================
--  Block 24
-- =============================================================================

ShPTCInTe OBJECT-TYPE
     SYNTAX  INTEGER
     ACCESS  read-only
     STATUS  mandatory
     DESCRIPTION
             " "
     ::= { HironetBlockId24 1 }

ShPTCOuTe OBJECT-TYPE
     SYNTAX  INTEGER
     ACCESS  read-only
     STATUS  mandatory
     DESCRIPTION
             " "
     ::= { HironetBlockId24 2 }

ShPTCAmTe OBJECT-TYPE
     SYNTAX  INTEGER
     ACCESS  read-only
     STATUS  mandatory
     DESCRIPTION
             " "
     ::= { HironetBlockId24 3 }

ShPTCEvTe OBJECT-TYPE
     SYNTAX  INTEGER
     ACCESS  read-only
     STATUS  mandatory
     DESCRIPTION
             " "
     ::= { HironetBlockId24 4 }

PTCInTemp OBJECT-TYPE
     SYNTAX  INTEGER
     ACCESS  read-only
     STATUS  mandatory
     DESCRIPTION
             " "
     ::= { HironetBlockId24 5 }

PTCOuTemp OBJECT-TYPE
     SYNTAX  INTEGER
     ACCESS  read-only
     STATUS  mandatory
     DESCRIPTION
             " "
     ::= { HironetBlockId24 6 }

PTCAmbTemp OBJECT-TYPE
     SYNTAX  INTEGER
     ACCESS  read-only
     STATUS  mandatory
     DESCRIPTION
             " "
     ::= { HironetBlockId24 7 }

PTCEvaTem OBJECT-TYPE
     SYNTAX  INTEGER
     ACCESS  read-only
     STATUS  mandatory
     DESCRIPTION
             " "
     ::= { HironetBlockId24 8 }

-- =============================================================================
--  End Block 24
-- =============================================================================

HironetBlockId25 OBJECT-IDENTITY
   STATUS      current
   DESCRIPTION "This branch contains Hironet Block 25."
    ::= { Hironet 25 }

-- =============================================================================
--  Block 25
-- =============================================================================

HT11 OBJECT-TYPE
     SYNTAX  INTEGER
     ACCESS  read-only
     STATUS  mandatory
     DESCRIPTION
             " "
     ::= { HironetBlockId25 1 }

HT12 OBJECT-TYPE
     SYNTAX  INTEGER
     ACCESS  read-only
     STATUS  mandatory
     DESCRIPTION
             " "
     ::= { HironetBlockId25 2 }

HT21 OBJECT-TYPE
     SYNTAX  INTEGER
     ACCESS  read-only
     STATUS  mandatory
     DESCRIPTION
             " "
     ::= { HironetBlockId25 3 }

HT22 OBJECT-TYPE
     SYNTAX  INTEGER
     ACCESS  read-only
     STATUS  mandatory
     DESCRIPTION
             " "
     ::= { HironetBlockId25 4 }

-- =============================================================================
--  End Block 25
-- =============================================================================

HironetBlockId26 OBJECT-IDENTITY
   STATUS      current
   DESCRIPTION "This branch contains Hironet Block 26."
    ::= { Hironet 26 }

-- =============================================================================
--  Block 26
-- =============================================================================

UsrWPreBar OBJECT-TYPE
     SYNTAX  INTEGER
     ACCESS  read-only
     STATUS  mandatory
     DESCRIPTION
             " "
     ::= { HironetBlockId26 1 }

UsrWPreBa2 OBJECT-TYPE
     SYNTAX  INTEGER
     ACCESS  read-only
     STATUS  mandatory
     DESCRIPTION
             " "
     ::= { HironetBlockId26 2 }

HCurr OBJECT-TYPE
     SYNTAX  INTEGER
     ACCESS  read-only
     STATUS  mandatory
     DESCRIPTION
             " "
     ::= { HironetBlockId26 3 }

C1PresBar OBJECT-TYPE
     SYNTAX  INTEGER
     ACCESS  read-only
     STATUS  mandatory
     DESCRIPTION
             "Actual Condenser Pressure Input (in bar)."
     ::= { HironetBlockId26 4 }

C2PresBar OBJECT-TYPE
     SYNTAX  INTEGER
     ACCESS  read-only
     STATUS  mandatory
     DESCRIPTION
             "Actual Condenser Pressure Input (in bar)."
     ::= { HironetBlockId26 5 }

UsrShiftSe OBJECT-TYPE
     SYNTAX  INTEGER
     ACCESS  read-only
     STATUS  mandatory
     DESCRIPTION
             " "
     ::= { HironetBlockId26 6 }

UsrShiftS2 OBJECT-TYPE
     SYNTAX  INTEGER
     ACCESS  read-only
     STATUS  mandatory
     DESCRIPTION
             " "
     ::= { HironetBlockId26 7 }

UsrWPreVo OBJECT-TYPE
     SYNTAX  INTEGER
     ACCESS  read-only
     STATUS  mandatory
     DESCRIPTION
             " "
     ::= { HironetBlockId26 8 }

UsrWPreVo2 OBJECT-TYPE
     SYNTAX  INTEGER
     ACCESS  read-only
     STATUS  mandatory
     DESCRIPTION
             " "
     ::= { HironetBlockId26 9 }

C1PresVo OBJECT-TYPE
     SYNTAX  INTEGER
     ACCESS  read-only
     STATUS  mandatory
     DESCRIPTION
             "Calibration of Condenser Pressure Input (x bar at 0 V)."
     ::= { HironetBlockId26 10 }

-- =============================================================================
--  End Block 26
-- =============================================================================

HironetBlockId27 OBJECT-IDENTITY
   STATUS      current
   DESCRIPTION "This branch contains Hironet Block 27."
    ::= { Hironet 27 }

-- =============================================================================
--  Block 27
-- =============================================================================

C2PresVo OBJECT-TYPE
     SYNTAX  INTEGER
     ACCESS  read-only
     STATUS  mandatory
     DESCRIPTION
             "Calibration of Condenser Pressure Input (x bar at 0 V)."
     ::= { HironetBlockId27 1 }

C3PresBar OBJECT-TYPE
     SYNTAX  INTEGER
     ACCESS  read-only
     STATUS  mandatory
     DESCRIPTION
             "Actual Condenser Pressure Input (in bar)."
     ::= { HironetBlockId27 2 }

-- =============================================================================
--  End Block 27
-- =============================================================================

HironetBlockId28 OBJECT-IDENTITY
   STATUS      current
   DESCRIPTION "This branch contains Hironet Block 28."
    ::= { Hironet 28 }

-- =============================================================================
--  Block 28
-- =============================================================================

C4PresBar OBJECT-TYPE
     SYNTAX  INTEGER
     ACCESS  read-only
     STATUS  mandatory
     DESCRIPTION
             "Actual Condenser Pressure Input (in bar)."
     ::= { HironetBlockId28 1 }

C3PresVo OBJECT-TYPE
     SYNTAX  INTEGER
     ACCESS  read-only
     STATUS  mandatory
     DESCRIPTION
             "Actual Condenser Pressure Input (in volt)."
     ::= { HironetBlockId28 2 }

C4PresVo OBJECT-TYPE
     SYNTAX  INTEGER
     ACCESS  read-only
     STATUS  mandatory
     DESCRIPTION
             "Calibration of Condenser Pressure Input (x bar at 0 V)."
     ::= { HironetBlockId28 3 }

-- =============================================================================
--  End Block 28
-- =============================================================================

HironetBlockId29 OBJECT-IDENTITY
   STATUS      current
   DESCRIPTION "This branch contains Hironet Block 29."
    ::= { Hironet 29 }

-- =============================================================================
--  Block 29
-- =============================================================================

InREM OBJECT-TYPE
     SYNTAX  INTEGER
     ACCESS  read-only
     STATUS  mandatory
     DESCRIPTION
             " "
     ::= { HironetBlockId29 1 }

InFan OBJECT-TYPE
     SYNTAX  INTEGER
     ACCESS  read-only
     STATUS  mandatory
     DESCRIPTION
             " "
     ::= { HironetBlockId29 2 }

InFan34 OBJECT-TYPE
     SYNTAX  INTEGER
     ACCESS  read-only
     STATUS  mandatory
     DESCRIPTION
             " "
     ::= { HironetBlockId29 3 }

InUSR OBJECT-TYPE
     SYNTAX  INTEGER
     ACCESS  read-only
     STATUS  mandatory
     DESCRIPTION
             " "
     ::= { HironetBlockId29 4 }

-- =============================================================================
--  End Block 29
-- =============================================================================

HironetBlockId30 OBJECT-IDENTITY
   STATUS      current
   DESCRIPTION "This branch contains Hironet Block 30."
    ::= { Hironet 30 }

-- =============================================================================
--  Block 30
-- =============================================================================

InUSR2 OBJECT-TYPE
     SYNTAX  INTEGER
     ACCESS  read-only
     STATUS  mandatory
     DESCRIPTION
             " "
     ::= { HironetBlockId30 1 }

InFr1 OBJECT-TYPE
     SYNTAX  INTEGER
     ACCESS  read-only
     STATUS  mandatory
     DESCRIPTION
             " "
     ::= { HironetBlockId30 2 }

InFr2 OBJECT-TYPE
     SYNTAX  INTEGER
     ACCESS  read-only
     STATUS  mandatory
     DESCRIPTION
             " "
     ::= { HironetBlockId30 3 }

-- =============================================================================
--  End Block 30
-- =============================================================================

HironetBlockId31 OBJECT-IDENTITY
   STATUS      current
   DESCRIPTION "This branch contains Hironet Block 31."
    ::= { Hironet 31 }

-- =============================================================================
--  Block 31
-- =============================================================================

AnaConden1 OBJECT-TYPE
     SYNTAX  INTEGER
     ACCESS  read-only
     STATUS  mandatory
     DESCRIPTION
             "Analog Condenser Output 1."
     ::= { HironetBlockId31 1 }

AnaConden2 OBJECT-TYPE
     SYNTAX  INTEGER
     ACCESS  read-only
     STATUS  mandatory
     DESCRIPTION
             "Analog Condenser Output 2."
     ::= { HironetBlockId31 2 }

Valve3P OBJECT-TYPE
     SYNTAX  INTEGER
     ACCESS  read-only
     STATUS  mandatory
     DESCRIPTION
             "3 point valve 1 position"
     ::= { HironetBlockId31 3 }

AnaConden3 OBJECT-TYPE
     SYNTAX  INTEGER
     ACCESS  read-only
     STATUS  mandatory
     DESCRIPTION
             "Analog Condenser Output 3."
     ::= { HironetBlockId31 4 }

AnaConden4 OBJECT-TYPE
     SYNTAX  INTEGER
     ACCESS  read-only
     STATUS  mandatory
     DESCRIPTION
             "Analog Condenser Output 4."
     ::= { HironetBlockId31 5 }

-- =============================================================================
--  End Block 31
-- =============================================================================

HironetBlockId32 OBJECT-IDENTITY
   STATUS      current
   DESCRIPTION "This branch contains Hironet Block 32."
    ::= { Hironet 32 }

-- =============================================================================
--  Block 32
-- =============================================================================

ManCondFan OBJECT-TYPE
     SYNTAX  INTEGER
     ACCESS  read-only
     STATUS  mandatory
     DESCRIPTION
             " "
     ::= { HironetBlockId32 1 }

ManPump1 OBJECT-TYPE
     SYNTAX  INTEGER
     ACCESS  read-only
     STATUS  mandatory
     DESCRIPTION
             " "
     ::= { HironetBlockId32 2 }

ManPump2 OBJECT-TYPE
     SYNTAX  INTEGER
     ACCESS  read-only
     STATUS  mandatory
     DESCRIPTION
             " "
     ::= { HironetBlockId32 3 }

ManComp1 OBJECT-TYPE
     SYNTAX  INTEGER
     ACCESS  read-only
     STATUS  mandatory
     DESCRIPTION
             " "
     ::= { HironetBlockId32 4 }

ManComp1Pa OBJECT-TYPE
     SYNTAX  INTEGER
     ACCESS  read-only
     STATUS  mandatory
     DESCRIPTION
             " "
     ::= { HironetBlockId32 5 }

ManComp2 OBJECT-TYPE
     SYNTAX  INTEGER
     ACCESS  read-only
     STATUS  mandatory
     DESCRIPTION
             " "
     ::= { HironetBlockId32 6 }

ManComp2Pa OBJECT-TYPE
     SYNTAX  INTEGER
     ACCESS  read-only
     STATUS  mandatory
     DESCRIPTION
             " "
     ::= { HironetBlockId32 7 }

ManCondDiv OBJECT-TYPE
     SYNTAX  INTEGER
     ACCESS  read-only
     STATUS  mandatory
     DESCRIPTION
             " "
     ::= { HironetBlockId32 8 }

ManWaRelay OBJECT-TYPE
     SYNTAX  INTEGER
     ACCESS  read-only
     STATUS  mandatory
     DESCRIPTION
             " "
     ::= { HironetBlockId32 9 }

ManAIRelay OBJECT-TYPE
     SYNTAX  INTEGER
     ACCESS  read-only
     STATUS  mandatory
     DESCRIPTION
             " "
     ::= { HironetBlockId32 10 }

-- =============================================================================
--  End Block 32
-- =============================================================================

HironetBlockId33 OBJECT-IDENTITY
   STATUS      current
   DESCRIPTION "This branch contains Hironet Block 33."
    ::= { Hironet 33 }

-- =============================================================================
--  Block 33
-- =============================================================================

ManFanSt1 OBJECT-TYPE
     SYNTAX  INTEGER
     ACCESS  read-only
     STATUS  mandatory
     DESCRIPTION
             " "
     ::= { HironetBlockId33 1 }

ManFanSt2 OBJECT-TYPE
     SYNTAX  INTEGER
     ACCESS  read-only
     STATUS  mandatory
     DESCRIPTION
             " "
     ::= { HironetBlockId33 2 }

ManFanSt3 OBJECT-TYPE
     SYNTAX  INTEGER
     ACCESS  read-only
     STATUS  mandatory
     DESCRIPTION
             " "
     ::= { HironetBlockId33 3 }

ManFanSt4 OBJECT-TYPE
     SYNTAX  INTEGER
     ACCESS  read-only
     STATUS  mandatory
     DESCRIPTION
             " "
     ::= { HironetBlockId33 4 }

ManFanSt5 OBJECT-TYPE
     SYNTAX  INTEGER
     ACCESS  read-only
     STATUS  mandatory
     DESCRIPTION
             " "
     ::= { HironetBlockId33 5 }

ManFanSt6 OBJECT-TYPE
     SYNTAX  INTEGER
     ACCESS  read-only
     STATUS  mandatory
     DESCRIPTION
             " "
     ::= { HironetBlockId33 6 }

ManFanSt7 OBJECT-TYPE
     SYNTAX  INTEGER
     ACCESS  read-only
     STATUS  mandatory
     DESCRIPTION
             " "
     ::= { HironetBlockId33 7 }

ManFanSt8 OBJECT-TYPE
     SYNTAX  INTEGER
     ACCESS  read-only
     STATUS  mandatory
     DESCRIPTION
             " "
     ::= { HironetBlockId33 8 }

ManComp3 OBJECT-TYPE
     SYNTAX  INTEGER
     ACCESS  read-only
     STATUS  mandatory
     DESCRIPTION
             " "
     ::= { HironetBlockId33 9 }

ManComp4 OBJECT-TYPE
     SYNTAX  INTEGER
     ACCESS  read-only
     STATUS  mandatory
     DESCRIPTION
             " "
     ::= { HironetBlockId33 10 }

-- =============================================================================
--  End Block 33
-- =============================================================================

HironetBlockId34 OBJECT-IDENTITY
   STATUS      current
   DESCRIPTION "This branch contains Hironet Block 34."
    ::= { Hironet 34 }

-- =============================================================================
--  Block 34
-- =============================================================================

ManComp3Pa OBJECT-TYPE
     SYNTAX  INTEGER
     ACCESS  read-only
     STATUS  mandatory
     DESCRIPTION
             " "
     ::= { HironetBlockId34 1 }

ManComp4Pa OBJECT-TYPE
     SYNTAX  INTEGER
     ACCESS  read-only
     STATUS  mandatory
     DESCRIPTION
             " "
     ::= { HironetBlockId34 2 }

ManFanSt21 OBJECT-TYPE
     SYNTAX  INTEGER
     ACCESS  read-only
     STATUS  mandatory
     DESCRIPTION
             " "
     ::= { HironetBlockId34 3 }

ManFanSt22 OBJECT-TYPE
     SYNTAX  INTEGER
     ACCESS  read-only
     STATUS  mandatory
     DESCRIPTION
             " "
     ::= { HironetBlockId34 4 }

ManFanSt23 OBJECT-TYPE
     SYNTAX  INTEGER
     ACCESS  read-only
     STATUS  mandatory
     DESCRIPTION
             " "
     ::= { HironetBlockId34 5 }

ManFanSt24 OBJECT-TYPE
     SYNTAX  INTEGER
     ACCESS  read-only
     STATUS  mandatory
     DESCRIPTION
             " "
     ::= { HironetBlockId34 6 }

ManFanSt25 OBJECT-TYPE
     SYNTAX  INTEGER
     ACCESS  read-only
     STATUS  mandatory
     DESCRIPTION
             " "
     ::= { HironetBlockId34 7 }

ManFanSt26 OBJECT-TYPE
     SYNTAX  INTEGER
     ACCESS  read-only
     STATUS  mandatory
     DESCRIPTION
             " "
     ::= { HironetBlockId34 8 }

ManFanSt27 OBJECT-TYPE
     SYNTAX  INTEGER
     ACCESS  read-only
     STATUS  mandatory
     DESCRIPTION
             " "
     ::= { HironetBlockId34 9 }

ManFanSt28 OBJECT-TYPE
     SYNTAX  INTEGER
     ACCESS  read-only
     STATUS  mandatory
     DESCRIPTION
             " "
     ::= { HironetBlockId34 10 }

-- =============================================================================
--  End Block 34
-- =============================================================================

HironetBlockId35 OBJECT-IDENTITY
   STATUS      current
   DESCRIPTION "This branch contains Hironet Block 35."
    ::= { Hironet 35 }

-- =============================================================================
--  Block 35
-- =============================================================================

ManLoad1 OBJECT-TYPE
     SYNTAX  INTEGER
     ACCESS  read-only
     STATUS  mandatory
     DESCRIPTION
             "Status of the Load Output 1"
     ::= { HironetBlockId35 1 }

ManLoad2 OBJECT-TYPE
     SYNTAX  INTEGER
     ACCESS  read-only
     STATUS  mandatory
     DESCRIPTION
             "Status of the Load Output 2"
     ::= { HironetBlockId35 2 }

ManUnLoad1 OBJECT-TYPE
     SYNTAX  INTEGER
     ACCESS  read-only
     STATUS  mandatory
     DESCRIPTION
             "Status of the UnLoad Output 1"
     ::= { HironetBlockId35 3 }

ManUnLoad2 OBJECT-TYPE
     SYNTAX  INTEGER
     ACCESS  read-only
     STATUS  mandatory
     DESCRIPTION
             "Status of the UnLoad Output 2"
     ::= { HironetBlockId35 4 }

ManLoad3 OBJECT-TYPE
     SYNTAX  INTEGER
     ACCESS  read-only
     STATUS  mandatory
     DESCRIPTION
             "Status of the Load Output 3"
     ::= { HironetBlockId35 5 }

ManLoad4 OBJECT-TYPE
     SYNTAX  INTEGER
     ACCESS  read-only
     STATUS  mandatory
     DESCRIPTION
             "Status of the Load Output 4"
     ::= { HironetBlockId35 6 }

ManUnLoad3 OBJECT-TYPE
     SYNTAX  INTEGER
     ACCESS  read-only
     STATUS  mandatory
     DESCRIPTION
             "Status of the UnLoad Output 3"
     ::= { HironetBlockId35 7 }

ManUnLoad4 OBJECT-TYPE
     SYNTAX  INTEGER
     ACCESS  read-only
     STATUS  mandatory
     DESCRIPTION
             "Status of the UnLoad Output 4"
     ::= { HironetBlockId35 8 }

-- =============================================================================
--  End Block 35
-- =============================================================================

HironetBlockId36 OBJECT-IDENTITY
   STATUS      current
   DESCRIPTION "This branch contains Hironet Block 36."
    ::= { Hironet 36 }

-- =============================================================================
--  Block 36
-- =============================================================================

Record1M OBJECT-TYPE
     SYNTAX  INTEGER
     ACCESS  read-only
     STATUS  mandatory
     DESCRIPTION
             "Microface Graphic Data Record of Inlet Temperature"
     ::= { HironetBlockId36 1 }

-- =============================================================================
--  End Block 36
-- =============================================================================

HironetBlockId37 OBJECT-IDENTITY
   STATUS      current
   DESCRIPTION "This branch contains Hironet Block 37."
    ::= { Hironet 37 }

-- =============================================================================
--  Block 37
-- =============================================================================

Record2M OBJECT-TYPE
     SYNTAX  INTEGER
     ACCESS  read-only
     STATUS  mandatory
     DESCRIPTION
             "Microface Graphic Data Record of Outlet Temperature"
     ::= { HironetBlockId37 1 }

-- =============================================================================
--  End Block 37
-- =============================================================================

Alarme OBJECT-IDENTITY
   STATUS      current
   DESCRIPTION "This branch contains Hironet Alarms."
    ::= { Hironet 50 }

-- =============================================================================
--  Alarme
-- =============================================================================

GeneralAlarm  OBJECT-IDENTITY
    STATUS current
    DESCRIPTION
        ""
    ::= { Alarme 0 }

AlHP1  OBJECT-IDENTITY
    STATUS current
    DESCRIPTION
        ""
    ::= { Alarme 1 }

AlLP1  OBJECT-IDENTITY
    STATUS current
    DESCRIPTION
        ""
    ::= { Alarme 2 }

WaFlowSwit  OBJECT-IDENTITY
    STATUS current
    DESCRIPTION
        ""
    ::= { Alarme 3 }

AlFlowSwit  OBJECT-IDENTITY
    STATUS current
    DESCRIPTION
        ""
    ::= { Alarme 4 }

WaUserInp  OBJECT-IDENTITY
    STATUS current
    DESCRIPTION
        ""
    ::= { Alarme 5 }

AlUserInp  OBJECT-IDENTITY
    STATUS current
    DESCRIPTION
        ""
    ::= { Alarme 6 }

WaHWTempIn  OBJECT-IDENTITY
    STATUS current
    DESCRIPTION
        ""
    ::= { Alarme 7 }

WaHWTempOu  OBJECT-IDENTITY
    STATUS current
    DESCRIPTION
        ""
    ::= { Alarme 8 }

WaLWTempIn  OBJECT-IDENTITY
    STATUS current
    DESCRIPTION
        ""
    ::= { Alarme 9 }

WaLWTempOu  OBJECT-IDENTITY
    STATUS current
    DESCRIPTION
        ""
    ::= { Alarme 10 }

AlHWTempIn  OBJECT-IDENTITY
    STATUS current
    DESCRIPTION
        ""
    ::= { Alarme 11 }

AlHWTempOu  OBJECT-IDENTITY
    STATUS current
    DESCRIPTION
        ""
    ::= { Alarme 12 }

AlLWTempIn  OBJECT-IDENTITY
    STATUS current
    DESCRIPTION
        ""
    ::= { Alarme 13 }

AlLWTempOu  OBJECT-IDENTITY
    STATUS current
    DESCRIPTION
        ""
    ::= { Alarme 14 }

WaPump1Hou  OBJECT-IDENTITY
    STATUS current
    DESCRIPTION
        ""
    ::= { Alarme 15 }

WaPump2Hou  OBJECT-IDENTITY
    STATUS current
    DESCRIPTION
        ""
    ::= { Alarme 16 }

WaComp1Hou  OBJECT-IDENTITY
    STATUS current
    DESCRIPTION
        ""
    ::= { Alarme 17 }

WaComp2Hou  OBJECT-IDENTITY
    STATUS current
    DESCRIPTION
        ""
    ::= { Alarme 18 }

WaPTCIn  OBJECT-IDENTITY
    STATUS current
    DESCRIPTION
        ""
    ::= { Alarme 19 }

AlPTCIn  OBJECT-IDENTITY
    STATUS current
    DESCRIPTION
        ""
    ::= { Alarme 20 }

Wa1PTCOut  OBJECT-IDENTITY
    STATUS current
    DESCRIPTION
        ""
    ::= { Alarme 21 }

WaCondFanF  OBJECT-IDENTITY
    STATUS current
    DESCRIPTION
        ""
    ::= { Alarme 22 }

WaHWPressu  OBJECT-IDENTITY
    STATUS current
    DESCRIPTION
        ""
    ::= { Alarme 23 }

AlHWPressu  OBJECT-IDENTITY
    STATUS current
    DESCRIPTION
        ""
    ::= { Alarme 24 }

AlHP2  OBJECT-IDENTITY
    STATUS current
    DESCRIPTION
        ""
    ::= { Alarme 25 }

AlLP2  OBJECT-IDENTITY
    STATUS current
    DESCRIPTION
        ""
    ::= { Alarme 26 }

WaNet  OBJECT-IDENTITY
    STATUS current
    DESCRIPTION
        ""
    ::= { Alarme 27 }

WaOrEEPROM  OBJECT-IDENTITY
    STATUS current
    DESCRIPTION
        ""
    ::= { Alarme 28 }

ALCompCont  OBJECT-IDENTITY
    STATUS current
    DESCRIPTION
        ""
    ::= { Alarme 29 }

AlTH1  OBJECT-IDENTITY
    STATUS current
    DESCRIPTION
        ""
    ::= { Alarme 30 }

AlTH2  OBJECT-IDENTITY
    STATUS current
    DESCRIPTION
        ""
    ::= { Alarme 31 }

AlOil1  OBJECT-IDENTITY
    STATUS current
    DESCRIPTION
        ""
    ::= { Alarme 32 }

AlOil2  OBJECT-IDENTITY
    STATUS current
    DESCRIPTION
        ""
    ::= { Alarme 33 }

Wa1Freeze  OBJECT-IDENTITY
    STATUS current
    DESCRIPTION
        ""
    ::= { Alarme 34 }

Wa2Freeze  OBJECT-IDENTITY
    STATUS current
    DESCRIPTION
        ""
    ::= { Alarme 35 }

MeUnitOn  OBJECT-IDENTITY
    STATUS current
    DESCRIPTION
        ""
    ::= { Alarme 36 }

MeUnitOff  OBJECT-IDENTITY
    STATUS current
    DESCRIPTION
        ""
    ::= { Alarme 37 }

MeSleepMod  OBJECT-IDENTITY
    STATUS current
    DESCRIPTION
        ""
    ::= { Alarme 38 }

MeStandby  OBJECT-IDENTITY
    STATUS current
    DESCRIPTION
        ""
    ::= { Alarme 39 }

MePowerOn  OBJECT-IDENTITY
    STATUS current
    DESCRIPTION
        ""
    ::= { Alarme 40 }

MePowerOff  OBJECT-IDENTITY
    STATUS current
    DESCRIPTION
        ""
    ::= { Alarme 41 }

MeHP1Wa  OBJECT-IDENTITY
    STATUS current
    DESCRIPTION
        ""
    ::= { Alarme 59 }

MeHP2Wa  OBJECT-IDENTITY
    STATUS current
    DESCRIPTION
        ""
    ::= { Alarme 60 }

MeHP1Ok  OBJECT-IDENTITY
    STATUS current
    DESCRIPTION
        ""
    ::= { Alarme 61 }

MeHP2Ok  OBJECT-IDENTITY
    STATUS current
    DESCRIPTION
        ""
    ::= { Alarme 62 }

Wa2PTCOut  OBJECT-IDENTITY
    STATUS current
    DESCRIPTION
        ""
    ::= { Alarme 63 }

WaNetMast  OBJECT-IDENTITY
    STATUS current
    DESCRIPTION
        ""
    ::= { Alarme 64 }

Wa1FreezeM  OBJECT-IDENTITY
    STATUS current
    DESCRIPTION
        ""
    ::= { Alarme 65 }

Wa2FreezeM  OBJECT-IDENTITY
    STATUS current
    DESCRIPTION
        ""
    ::= { Alarme 66 }


AlCondFanF  OBJECT-IDENTITY
    STATUS current
    DESCRIPTION
        ""
    ::= { Alarme 68 }

WaPTCAmb  OBJECT-IDENTITY
    STATUS current
    DESCRIPTION
        ""
    ::= { Alarme 69 }

Al1PTCOut  OBJECT-IDENTITY
    STATUS current
    DESCRIPTION
        ""
    ::= { Alarme 70 }

Al2PTCOut  OBJECT-IDENTITY
    STATUS current
    DESCRIPTION
        ""
    ::= { Alarme 71 }

WaPTCEva  OBJECT-IDENTITY
    STATUS current
    DESCRIPTION
        ""
    ::= { Alarme 72 }

AlPTCEva  OBJECT-IDENTITY
    STATUS current
    DESCRIPTION
        ""
    ::= { Alarme 73 }

WaShPTCEva  OBJECT-IDENTITY
    STATUS current
    DESCRIPTION
        ""
    ::= { Alarme 74 }

AlShPTCEva  OBJECT-IDENTITY
    STATUS current
    DESCRIPTION
        ""
    ::= { Alarme 75 }

WaShPTCIn  OBJECT-IDENTITY
    STATUS current
    DESCRIPTION
        ""
    ::= { Alarme 76 }

WaHbError  OBJECT-IDENTITY
    STATUS current
    DESCRIPTION
        ""
    ::= { Alarme 77 }

WaSubGrErr  OBJECT-IDENTITY
    STATUS current
    DESCRIPTION
        ""
    ::= { Alarme 78 }

WaSubGr1nc  OBJECT-IDENTITY
    STATUS current
    DESCRIPTION
        ""
    ::= { Alarme 79 }

WaSubGr2nc  OBJECT-IDENTITY
    STATUS current
    DESCRIPTION
        ""
    ::= { Alarme 80 }

WaFCHou  OBJECT-IDENTITY
    STATUS current
    DESCRIPTION
        ""
    ::= { Alarme 81 }

WaCond2Fan  OBJECT-IDENTITY
    STATUS current
    DESCRIPTION
        ""
    ::= { Alarme 82 }

AlCond2Fan  OBJECT-IDENTITY
    STATUS current
    DESCRIPTION
        ""
    ::= { Alarme 83 }

AlLoCondP1  OBJECT-IDENTITY
    STATUS current
    DESCRIPTION
        ""
    ::= { Alarme 84 }

AlLoCondP2  OBJECT-IDENTITY
    STATUS current
    DESCRIPTION
        ""
    ::= { Alarme 85 }

AlHPTH1  OBJECT-IDENTITY
    STATUS current
    DESCRIPTION
        ""
    ::= { Alarme 86 }

AlHPTH2  OBJECT-IDENTITY
    STATUS current
    DESCRIPTION
        ""
    ::= { Alarme 87 }

AlSubGr1nc  OBJECT-IDENTITY
    STATUS current
    DESCRIPTION
        ""
    ::= { Alarme 88 }

AlSubGr2nc  OBJECT-IDENTITY
    STATUS current
    DESCRIPTION
        ""
    ::= { Alarme 89 }

AlNoDifPr1  OBJECT-IDENTITY
    STATUS current
    DESCRIPTION
        ""
    ::= { Alarme 90 }

AlNoDifPr2  OBJECT-IDENTITY
    STATUS current
    DESCRIPTION
        ""
    ::= { Alarme 91 }

AlMicAsIO  OBJECT-IDENTITY
    STATUS current
    DESCRIPTION
        ""
    ::= { Alarme 92 }

WaHiroSen1  OBJECT-IDENTITY
    STATUS current
    DESCRIPTION
        ""
    ::= { Alarme 93 }

WaHiroSen2  OBJECT-IDENTITY
    STATUS current
    DESCRIPTION
        ""
    ::= { Alarme 94 }

AlCond3Fan  OBJECT-IDENTITY
    STATUS current
    DESCRIPTION
        ""
    ::= { Alarme 95 }

AlCond4Fan  OBJECT-IDENTITY
    STATUS current
    DESCRIPTION
        ""
    ::= { Alarme 96 }

AlHPTH3  OBJECT-IDENTITY
    STATUS current
    DESCRIPTION
        ""
    ::= { Alarme 97 }

AlHPTH4  OBJECT-IDENTITY
    STATUS current
    DESCRIPTION
        ""
    ::= { Alarme 98 }

AlHP3  OBJECT-IDENTITY
    STATUS current
    DESCRIPTION
        ""
    ::= { Alarme 99 }

AlHP4  OBJECT-IDENTITY
    STATUS current
    DESCRIPTION
        ""
    ::= { Alarme 102 }

AlLP3  OBJECT-IDENTITY
    STATUS current
    DESCRIPTION
        ""
    ::= { Alarme 103 }

AlLP4  OBJECT-IDENTITY
    STATUS current
    DESCRIPTION
        ""
    ::= { Alarme 104 }

AlOil3  OBJECT-IDENTITY
    STATUS current
    DESCRIPTION
        ""
    ::= { Alarme 105 }

AlOil4  OBJECT-IDENTITY
    STATUS current
    DESCRIPTION
        ""
    ::= { Alarme 106 }

AlTH3  OBJECT-IDENTITY
    STATUS current
    DESCRIPTION
        ""
    ::= { Alarme 107 }

AlTH4  OBJECT-IDENTITY
    STATUS current
    DESCRIPTION
        ""
    ::= { Alarme 108 }

AlLoCondP3  OBJECT-IDENTITY
    STATUS current
    DESCRIPTION
        ""
    ::= { Alarme 109 }

AlLoCondP4  OBJECT-IDENTITY
    STATUS current
    DESCRIPTION
        ""
    ::= { Alarme 110 }

AlNoDifPr3  OBJECT-IDENTITY
    STATUS current
    DESCRIPTION
        ""
    ::= { Alarme 111 }

AlNoDifPr4  OBJECT-IDENTITY
    STATUS current
    DESCRIPTION
        ""
    ::= { Alarme 112 }

MeHP3Ok  OBJECT-IDENTITY
    STATUS current
    DESCRIPTION
        ""
    ::= { Alarme 113 }

MeHP4Ok  OBJECT-IDENTITY
    STATUS current
    DESCRIPTION
        ""
    ::= { Alarme 114 }

MeHP3Wa  OBJECT-IDENTITY
    STATUS current
    DESCRIPTION
        ""
    ::= { Alarme 115 }

MeHP4Wa  OBJECT-IDENTITY
    STATUS current
    DESCRIPTION
        ""
    ::= { Alarme 116 }

AlSubGr3nc  OBJECT-IDENTITY
    STATUS current
    DESCRIPTION
        ""
    ::= { Alarme 117 }

AlSubGr4nc  OBJECT-IDENTITY
    STATUS current
    DESCRIPTION
        ""
    ::= { Alarme 118 }

WaSubGr3nc  OBJECT-IDENTITY
    STATUS current
    DESCRIPTION
        ""
    ::= { Alarme 119 }

WaSubGr4nc  OBJECT-IDENTITY
    STATUS current
    DESCRIPTION
        ""
    ::= { Alarme 120 }

WaComp3Hou  OBJECT-IDENTITY
    STATUS current
    DESCRIPTION
        ""
    ::= { Alarme 121 }

WaComp4Hou  OBJECT-IDENTITY
    STATUS current
    DESCRIPTION
        ""
    ::= { Alarme 122 }

WaCond3Fan  OBJECT-IDENTITY
    STATUS current
    DESCRIPTION
        ""
    ::= { Alarme 123 }

WaCond4Fan  OBJECT-IDENTITY
    STATUS current
    DESCRIPTION
        ""
    ::= { Alarme 124 }

AlMicAsIO2  OBJECT-IDENTITY
    STATUS current
    DESCRIPTION
        ""
    ::= { Alarme 125 }

MeHP4Wa  OBJECT-IDENTITY
    STATUS current
    DESCRIPTION
        ""
    ::= { Alarme 126 }

WaUserInp2  OBJECT-IDENTITY
    STATUS current
    DESCRIPTION
        ""
    ::= { Alarme 127 }

AlUserInp2  OBJECT-IDENTITY
    STATUS current
    DESCRIPTION
        ""
    ::= { Alarme 128 }

MeRecovOK  OBJECT-IDENTITY
    STATUS current
    DESCRIPTION
        ""
    ::= { Alarme 129 }

END
