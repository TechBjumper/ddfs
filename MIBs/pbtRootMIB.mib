-- ****************************************************************************
-- *
-- * Module Name: PBT Root MIB
-- *
-- * Created 05/19/04
-- * Revised 07/30/04 MQ Added SpecialAgent.
-- * Revised 11/28/04 MQ Added branch for extensions to standard MIBs.
-- * Revised 03/05/05 MQ Added branch for DPS MIB.
-- * Revised 09/26/05 MQ Added branch for the BatteryAgentMIB.
-- * Revised 10/05/05 MQ Added branches for each type of SpecialAgent.
-- * Revised 11/10/05 MQ Added branch for SPSM. 
-- * Revised 01/04/06 MQ Added branches for each type of PowerAgent. 
-- * Revised 03/22/06 MQ Added EXM and EXM2.
-- * Revised 05/11/06 MQ Added ZTT+ and CPR. 
-- * Revised 07/17/06 MQ Added Prisma I and II. 
-- * Revised 05/04/07 MQ Added GP Transponder.
-- * Revised 02/01/08 MQ Added RemoteAgent. 
-- * Revised 01/09/09 MQ Added EXM2-SI
-- * 
-- * This MIB provides the root object identifier for the
-- * Phoenix Broadband Technologies MIB tree.  The enterprise ID 20433
-- * was assigned by the Internet Assigned Numbers Authority (IANA).
-- *
-- ****************************************************************************

PBT-ROOT-MIB DEFINITIONS ::= BEGIN

IMPORTS
     enterprises
          FROM RFC1155-SMI
;

pbtRoot  OBJECT IDENTIFIER ::= { enterprises 20433 }

-- DESCRIPTION
--     "pbtRoot defines the root of the PBT enterprises MIB tree. "


pbtTree  OBJECT IDENTIFIER  ::= { pbtRoot 1 }
 
-- DESCRIPTION
--     "pbtTree defines the beginning of the PBT MIB tree."     


pbtProducts OBJECT IDENTIFIER ::= { pbtTree 1}

--     DESCRIPTION
--     "Defines the base OID of the Phoenix Broadband product Tree"


pbtIntellAgents OBJECT IDENTIFIER ::= { pbtProducts 1}

--     DESCRIPTION
--     "Defines the base OID of the Phoenix Broadband IntellAgent Tree"



-- ContactAgents ---------------------------------------------------------------- 

pbtContactAgent OBJECT IDENTIFIER ::= { pbtIntellAgents 1}

--     DESCRIPTION
--     "Defines the base OID of the Phoenix Broadband ContactAgent MIB"




-- PowerAgents -------------------------------------------------------------------------------------- 

pbtPowerAgent OBJECT IDENTIFIER ::= { pbtIntellAgents 2}

--     DESCRIPTION
--     "Defines the base OID of the Phoenix Broadband PowerAgent MIB"


pbtDPS OBJECT IDENTIFIER ::= { pbtPowerAgent 1}

--     DESCRIPTION
--     "Defines the base OID of the Phoenix Broadband PowerAgent DPS MIB"

pbtSPSM OBJECT IDENTIFIER ::= { pbtPowerAgent 2}

--     DESCRIPTION
--     "Defines the base OID of the Phoenix Broadband PowerAgent SPSM MIB"

pbtPaHMS OBJECT IDENTIFIER ::= { pbtPowerAgent 3}

--     DESCRIPTION
--     "Defines the base OID of the Phoenix Broadband PowerAgent for HMS Power Supplies"

pbtPaAlphaAM OBJECT IDENTIFIER ::= { pbtPowerAgent 4}

--     DESCRIPTION
--     "Defines the base OID of the Phoenix Broadband PowerAgent for Alpha 
--      AM Power Supplies"

pbtPaAlphaXM OBJECT IDENTIFIER ::= { pbtPowerAgent 5}

--     DESCRIPTION
--     "Defines the base OID of the Phoenix Broadband PowerAgent for Alpha 
--      XM Power Supplies"

pbtPaAlphaXM2USM OBJECT IDENTIFIER ::= { pbtPowerAgent 6}

--     DESCRIPTION
--     "Defines the base OID of the Phoenix Broadband PowerAgent for Alpha 
--      XM2 Power Supplies with a USM 2.0 or 2.5 Interface"

pbtPaMultiPowerMPS1350 OBJECT IDENTIFIER ::= { pbtPowerAgent 7}

--     DESCRIPTION
--     "Defines the base OID of the Phoenix Broadband PowerAgent for 
--      Multipower MPS 1350 Power Supplies"

pbtPaAlphaEXM OBJECT IDENTIFIER ::= { pbtPowerAgent 8}

--     DESCRIPTION
--     "Defines the base OID of the Phoenix Broadband PowerAgent for 
--      the PBT Embedded Alpha XM transponder"

pbtPaAlphaEXM2 OBJECT IDENTIFIER ::= { pbtPowerAgent 9}

--     DESCRIPTION
--     "Defines the base OID of the Phoenix Broadband PowerAgent for 
--      the PBT Embedded Alpha XM2 transponder"

pbtPaAlphaZTTP OBJECT IDENTIFIER ::= { pbtPowerAgent 10}

--     DESCRIPTION
--     "Defines the base OID of the Phoenix Broadband PowerAgent for 
--      the PBT transponder for the Alpha (Lectro) ZTT+."

pbtPaAlphaCPR OBJECT IDENTIFIER ::= { pbtPowerAgent 11}

--     DESCRIPTION
--     "Defines the base OID of the Phoenix Broadband PowerAgent for 
--      the PBT transponder for the Alpha (Lectro) CPR."

pbtPaGP OBJECT IDENTIFIER ::= { pbtPowerAgent 12}

--     DESCRIPTION
--     "Defines the base OID of the Phoenix Broadband PowerAgent for 
--      the PBT General Purpose transponder."

pbtPaGPeD OBJECT IDENTIFIER ::= { pbtPowerAgent 13}

--     DESCRIPTION
--     "Defines the base OID of the Phoenix Broadband General Purpose 
--      transponder with an embedded DOCSIS modem.."

pbtPaAlphaEXM2-SI OBJECT IDENTIFIER ::= { pbtPowerAgent 14}

--     DESCRIPTION
--     "Defines the base OID of the Phoenix Broadband PowerAgent for 
--      the PBT Embedded Alpha XM2 transponder with Battery Sensor Interface"


-- SpecialAgents ------------------------------------------------------------------------------------ 

pbtSpecialAgent OBJECT IDENTIFIER ::= { pbtIntellAgents 3}

--     DESCRIPTION
--     "Defines the base OID of the Phoenix Broadband SpecialAgent MIB"


pbtSAMotorolaConstellation OBJECT IDENTIFIER ::= { pbtSpecialAgent 1}

--     DESCRIPTION
--     "Defines the base OID of the Phoenix Broadband Constellation SpecialAgent MIB"


pbtSACcorHomeWorx OBJECT IDENTIFIER ::= { pbtSpecialAgent 2}

--     DESCRIPTION
--     "Defines the base OID of the Phoenix Broadband Home Worx SpecialAgent MIB"


pbtSAMotorolaOmniStar OBJECT IDENTIFIER ::= { pbtSpecialAgent 3}

--     DESCRIPTION
--     "Defines the base OID of the Phoenix Broadband OmniStar SpecialAgent MIB"


pbtSAHarmonicHLP4200 OBJECT IDENTIFIER ::= { pbtSpecialAgent 4}

--     DESCRIPTION
--     "Defines the base OID of the Phoenix Broadband Harmonic HLP4200 SpecialAgent MIB"


pbtSASynchronousAMRX10 OBJECT IDENTIFIER ::= { pbtSpecialAgent 5}

--     DESCRIPTION
--     "Defines the base OID of the Phoenix Broadband Synchronous AMRX-10 SpecialAgent MIB"


pbtSAScientificAtlantaPrismaI OBJECT IDENTIFIER ::= { pbtSpecialAgent 6}

--     DESCRIPTION
--     "Defines the base OID of the Phoenix Broadband Scientific Atlanta Prisma I MIB"


pbtSAScientificAtlantaPrismaII OBJECT IDENTIFIER ::= { pbtSpecialAgent 7}

--     DESCRIPTION
--     "Defines the base OID of the Phoenix Broadband Scientific Atlanta Prisma II MIB"




-- BatteryAgents --------------------------------------------------------------------------------

pbtBatteryAgent OBJECT IDENTIFIER ::= { pbtIntellAgents 4}

--     DESCRIPTION
--     "Defines the base OID of the Phoenix Broadband BatteryAgent MIB"


-- RemoteAgents --------------------------------------------------------------------------------

pbtRemoteAgent OBJECT IDENTIFIER ::= { pbtIntellAgents 5}

--     DESCRIPTION
--     "Defines the base OID of the Phoenix Broadband pbtRemoteAgentMIB"



-- MIB Extensions ------------------------------------------------------------------------------

pbtExtensions OBJECT IDENTIFIER ::= { pbtTree 2}

--     DESCRIPTION
--     "Defines the base OID of Phoenix Broadband extensions to standard SNMP MIBs"


pbtEntityExtensions OBJECT IDENTIFIER ::= { pbtExtensions 1}

--     DESCRIPTION
--     "Defines the base OID of Phoenix Broadband extensions to the SNMP EntityMIB"


pbtPsExtensions OBJECT IDENTIFIER ::= { pbtExtensions 2}

--     DESCRIPTION
--     "Defines the base OID of Phoenix Broadband extensions to the SCTE-HMS-PS-MIB"



END
