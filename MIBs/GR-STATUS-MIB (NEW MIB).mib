GR-STATUS-MIB DEFINITIONS ::= BEGIN

--
-- GRC System Status MIB objects for agent module example implementations
--

IMPORTS
    MODULE-IDENTITY, OBJECT-TYPE,
    enterprises, Integer32, Opaque  FROM SNMPv2-SMI
;

grStatus MODULE-IDENTITY
    LAST-UPDATED "201805090000Z"
    ORGANIZATION "www.grcooling.com"
    CONTACT-INFO "Support Team - Green Revolution Cooling Inc.
                  email: support@grcooling.com"
    DESCRIPTION  "GRC System Status objects for agent module example implementations"
    REVISION     "201805090000Z"
    DESCRIPTION  "GR-STATUS-MIB v3.6.0 2018-05-09"
::= { enterprises 53964 }

-- Tank data

grTankData OBJECT-TYPE
    SYNTAX      SEQUENCE OF GrTankDataEntry
    MAX-ACCESS  not-accessible
    STATUS      current
    DESCRIPTION "Table for the tank data, one row per tank."
::= { grStatus 4 }

grTankDataEntry OBJECT-TYPE
    SYNTAX      GrTankDataEntry
    MAX-ACCESS  not-accessible
    STATUS      current
    DESCRIPTION "A row describing tank data."
    INDEX   { grTankIndex }
::= { grTankData 1 }

GrTankDataEntry ::= SEQUENCE {
    grTankIndex                 OCTET STRING,
    grTankNumber                Integer32,
    grTankTopA                  Opaque,
    grTankTopAStr               OCTET STRING,
    grTankTopB                  Opaque,
    grTankTopBStr               OCTET STRING,
    grTankOilOut                Opaque,
    grTankOilOutStr             OCTET STRING,
    grTankFloatSwitch           OCTET STRING,
    grTankOilLevel              Opaque,
    grTankOilLevelStr           OCTET STRING,
    grTankOilPressure           Opaque,
    grTankOilPressureStr        OCTET STRING,
    grTankBackupSystemActive    OCTET STRING
}

grTankIndex OBJECT-TYPE
    SYNTAX      OCTET STRING (SIZE (1..16))
    MAX-ACCESS  not-accessible
    STATUS      current
    DESCRIPTION "Tank index as an octet string (1..16)."
::= { grTankDataEntry 1 }

grTankNumber OBJECT-TYPE
    SYNTAX      Integer32
    MAX-ACCESS  read-only
    STATUS      current
    DESCRIPTION "Tank number as an integer (32)."
::= { grTankDataEntry 2 }

grTankTopA OBJECT-TYPE
    SYNTAX      Opaque
    MAX-ACCESS  read-only
    STATUS      current
    DESCRIPTION "Tank top a temperature as an opaque float."
::= { grTankDataEntry 3 }

grTankTopAStr OBJECT-TYPE
    SYNTAX      OCTET STRING
    MAX-ACCESS  read-only
    STATUS      current
    DESCRIPTION "Tank top a temperature as an octet string."
::= { grTankDataEntry 4 }

grTankTopB OBJECT-TYPE
    SYNTAX      Opaque
    MAX-ACCESS  read-only
    STATUS      current
    DESCRIPTION "Tank top b temperature as an opaque float."
::= { grTankDataEntry 5 }

grTankTopBStr OBJECT-TYPE
    SYNTAX      OCTET STRING
    MAX-ACCESS  read-only
    STATUS      current
    DESCRIPTION "Tank top b temperature as an octet string."
::= { grTankDataEntry 6 }

grTankOilOut OBJECT-TYPE
    SYNTAX      Opaque
    MAX-ACCESS  read-only
    STATUS      current
    DESCRIPTION "Tank oil out temperature as an opaque float."
::= { grTankDataEntry 7 }

grTankOilOutStr OBJECT-TYPE
    SYNTAX      OCTET STRING
    MAX-ACCESS  read-only
    STATUS      current
    DESCRIPTION "Tank oil out temperature as an octet string."
::= { grTankDataEntry 8 }

grTankFloatSwitch OBJECT-TYPE
    SYNTAX      OCTET STRING
    MAX-ACCESS  read-only
    STATUS      current
    DESCRIPTION "Tank float switch status as an octet string."
::= { grTankDataEntry 9 }

grTankOilLevel OBJECT-TYPE
    SYNTAX      Opaque
    MAX-ACCESS  read-only
    STATUS      current
    DESCRIPTION "Tank oil level as an opaque float."
::= { grTankDataEntry 10 }

grTankOilLevelStr OBJECT-TYPE
    SYNTAX      OCTET STRING
    MAX-ACCESS  read-only
    STATUS      current
    DESCRIPTION "Tank oil level as an octet string."
::= { grTankDataEntry 11 }

grTankOilPressure OBJECT-TYPE
    SYNTAX      Opaque
    MAX-ACCESS  read-only
    STATUS      current
    DESCRIPTION "Tank oil pressure as an opaque float."
::= { grTankDataEntry 12 }

grTankOilPressureStr OBJECT-TYPE
    SYNTAX      OCTET STRING
    MAX-ACCESS  read-only
    STATUS      current
    DESCRIPTION "Tank oil pressure as an octet string."
::= { grTankDataEntry 13 }

grTankBackupSystemActive OBJECT-TYPE
    SYNTAX      OCTET STRING
    MAX-ACCESS  read-only
    STATUS      current
    DESCRIPTION "Tank backup system active status as an octet string."
::= { grTankDataEntry 14 }

-- End of Tank data

grSystemName OBJECT-TYPE
    SYNTAX      OCTET STRING
    MAX-ACCESS  read-only
    STATUS      current
    DESCRIPTION "System name as an octet string."
::= { grStatus 1 }

grSetValue OBJECT-TYPE
    SYNTAX      Opaque
    MAX-ACCESS  read-only
    STATUS      current
    DESCRIPTION "System set point as an opaque float."
::= { grStatus 2 }

grSetValueStr OBJECT-TYPE
    SYNTAX      OCTET STRING
    MAX-ACCESS  read-only
    STATUS      current
    DESCRIPTION "System set point as an octet string."
::= { grStatus 3 }

grOilPumpSpeed OBJECT-TYPE
    SYNTAX      Opaque
    MAX-ACCESS  read-only
    STATUS      current
    DESCRIPTION "Oil pump speed as an opaque float."
::= { grStatus 5 }

grOilPumpSpeedStr OBJECT-TYPE
    SYNTAX      OCTET STRING
    MAX-ACCESS  read-only
    STATUS      current
    DESCRIPTION "Oil pump speed as an octet string."
::= { grStatus 6 }

grOilPumpContinuous OBJECT-TYPE
    SYNTAX      Opaque
    MAX-ACCESS  read-only
    STATUS      current
    DESCRIPTION "Oil pump continuous as an opaque float."
::= { grStatus 7 }

grOilPumpContinuousStr OBJECT-TYPE
    SYNTAX      OCTET STRING
    MAX-ACCESS  read-only
    STATUS      current
    DESCRIPTION "Oil pump continuous as an octet string."
::= { grStatus 8 }

grOilPumpBinary OBJECT-TYPE
    SYNTAX      OCTET STRING
    MAX-ACCESS  read-only
    STATUS      current
    DESCRIPTION "Oil pump binary as an octet string."
::= { grStatus 9 }

grCtFanSpeed OBJECT-TYPE
    SYNTAX      Opaque
    MAX-ACCESS  read-only
    STATUS      current
    DESCRIPTION "Cooling tower fan speed as an opaque float."
::= { grStatus 10 }

grCtFanSpeedStr OBJECT-TYPE
    SYNTAX      OCTET STRING
    MAX-ACCESS  read-only
    STATUS      current
    DESCRIPTION "Cooling tower fan speed as an octet string."
::= { grStatus 11 }

grCtFanContinuous OBJECT-TYPE
    SYNTAX      Opaque
    MAX-ACCESS  read-only
    STATUS      current
    DESCRIPTION "Cooling tower fan continuous as an opaque float."
::= { grStatus 12 }

grCtFanContinuousStr OBJECT-TYPE
    SYNTAX      OCTET STRING
    MAX-ACCESS  read-only
    STATUS      current
    DESCRIPTION "Cooling tower fan continuous as an octet string."
::= { grStatus 13 }

grCtFanBinary OBJECT-TYPE
    SYNTAX      OCTET STRING
    MAX-ACCESS  read-only
    STATUS      current
    DESCRIPTION "Cooling tower fan binary as an octet string."
::= { grStatus 14 }

grWp1Speed OBJECT-TYPE
    SYNTAX      Opaque
    MAX-ACCESS  read-only
    STATUS      current
    DESCRIPTION "Water pump 1 speed as an opaque float."
::= { grStatus 15 }

grWp1SpeedStr OBJECT-TYPE
    SYNTAX      OCTET STRING
    MAX-ACCESS  read-only
    STATUS      current
    DESCRIPTION "Water pump 1 speed as an octet string."
::= { grStatus 16 }

grWp1Continuous OBJECT-TYPE
    SYNTAX      Opaque
    MAX-ACCESS  read-only
    STATUS      current
    DESCRIPTION "Water pump 1 continuous as an opaque float."
::= { grStatus 17 }

grWp1ContinuousStr OBJECT-TYPE
    SYNTAX      OCTET STRING
    MAX-ACCESS  read-only
    STATUS      current
    DESCRIPTION "Water pump 1 continuous as an octet string."
::= { grStatus 18 }

grWp1Binary OBJECT-TYPE
    SYNTAX      OCTET STRING
    MAX-ACCESS  read-only
    STATUS      current
    DESCRIPTION "Water pump 1 binary as an octet string."
::= { grStatus 19 }

grWp2Speed OBJECT-TYPE
    SYNTAX      Opaque
    MAX-ACCESS  read-only
    STATUS      current
    DESCRIPTION "Water pump 2 speed as an opaque float."
::= { grStatus 20 }

grWp2SpeedStr OBJECT-TYPE
    SYNTAX      OCTET STRING
    MAX-ACCESS  read-only
    STATUS      current
    DESCRIPTION "Water pump 2 speed as an octet string."
::= { grStatus 21 }

grWp2Continuous OBJECT-TYPE
    SYNTAX      Opaque
    MAX-ACCESS  read-only
    STATUS      current
    DESCRIPTION "Water pump 2 continuous as an opaque float."
::= { grStatus 22 }

grWp2ContinuousStr OBJECT-TYPE
    SYNTAX      OCTET STRING
    MAX-ACCESS  read-only
    STATUS      current
    DESCRIPTION "Water pump 2 continuous as an octet string."
::= { grStatus 23 }

grWp2Binary OBJECT-TYPE
    SYNTAX      OCTET STRING
    MAX-ACCESS  read-only
    STATUS      current
    DESCRIPTION "Water pump 2 binary as an octet string."
::= { grStatus 24 }

grWaterValveSpeed OBJECT-TYPE
    SYNTAX      Opaque
    MAX-ACCESS  read-only
    STATUS      current
    DESCRIPTION "Water valve speed as an opaque float."
::= { grStatus 25 }

grWaterValveSpeedStr OBJECT-TYPE
    SYNTAX      OCTET STRING
    MAX-ACCESS  read-only
    STATUS      current
    DESCRIPTION "Water valve speed as an octet string."
::= { grStatus 26 }

grWaterValveContinuous OBJECT-TYPE
    SYNTAX      Opaque
    MAX-ACCESS  read-only
    STATUS      current
    DESCRIPTION "Water valve continuous as an opaque float."
::= { grStatus 27 }

grWaterValveContinuousStr OBJECT-TYPE
    SYNTAX      OCTET STRING
    MAX-ACCESS  read-only
    STATUS      current
    DESCRIPTION "Water valve continuous as an octet string."
::= { grStatus 28 }

grWaterValveBinary OBJECT-TYPE
    SYNTAX      OCTET STRING
    MAX-ACCESS  read-only
    STATUS      current
    DESCRIPTION "Water valve binary as an octet string."
::= { grStatus 29 }

grBackupSystemActive OBJECT-TYPE
    SYNTAX      OCTET STRING
    MAX-ACCESS  read-only
    STATUS      current
    DESCRIPTION "Backup system active status as an octet string."
::= { grStatus 30 }

grPumpFloatSwitch OBJECT-TYPE
    SYNTAX      OCTET STRING
    MAX-ACCESS  read-only
    STATUS      current
    DESCRIPTION "Pump float switch status as an octet string."
::= { grStatus 31 }

grCtFloatSwitch OBJECT-TYPE
    SYNTAX      OCTET STRING
    MAX-ACCESS  read-only
    STATUS      current
    DESCRIPTION "Ct float switch status as an octet string."
::= { grStatus 32 }

grOilPressure OBJECT-TYPE
    SYNTAX      Opaque
    MAX-ACCESS  read-only
    STATUS      current
    DESCRIPTION "Oil pressure as an opaque float."
::= { grStatus 33 }

grOilPressureStr OBJECT-TYPE
    SYNTAX      OCTET STRING
    MAX-ACCESS  read-only
    STATUS      current
    DESCRIPTION "Oil pressure as an octet string."
::= { grStatus 34 }

grVaccPressure OBJECT-TYPE
    SYNTAX      Opaque
    MAX-ACCESS  read-only
    STATUS      current
    DESCRIPTION "Vacumm Pressure as an opaque float."
::= { grStatus 35 }

grVaccPressureStr OBJECT-TYPE
    SYNTAX      OCTET STRING
    MAX-ACCESS  read-only
    STATUS      current
    DESCRIPTION "Vacumm Pressure as an octet string."
::= { grStatus 36 }

grWaterPressure OBJECT-TYPE
    SYNTAX      Opaque
    MAX-ACCESS  read-only
    STATUS      current
    DESCRIPTION "Water pressure as an opaque float."
::= { grStatus 37 }

grWaterPressureStr OBJECT-TYPE
    SYNTAX      OCTET STRING
    MAX-ACCESS  read-only
    STATUS      current
    DESCRIPTION "Water pressure as an octet string."
::= { grStatus 38 }

grFilterPressure OBJECT-TYPE
    SYNTAX      Opaque
    MAX-ACCESS  read-only
    STATUS      current
    DESCRIPTION "Filter Pressure as an opaque float."
::= { grStatus 39 }

grFilterPressureStr OBJECT-TYPE
    SYNTAX      OCTET STRING
    MAX-ACCESS  read-only
    STATUS      current
    DESCRIPTION "Filter Pressure as an octet string."
::= { grStatus 40 }

grExchangeIn OBJECT-TYPE
    SYNTAX      Opaque
    MAX-ACCESS  read-only
    STATUS      current
    DESCRIPTION "Exchange in temperature as an opaque float."
::= { grStatus 41 }

grExchangeInStr OBJECT-TYPE
    SYNTAX      OCTET STRING
    MAX-ACCESS  read-only
    STATUS      current
    DESCRIPTION "Exchange in temperature as an octet string."
::= { grStatus 42 }

grExchangeOut OBJECT-TYPE
    SYNTAX      Opaque
    MAX-ACCESS  read-only
    STATUS      current
    DESCRIPTION "Exchange out temperature as an opaque float."
::= { grStatus 43 }

grExchangeOutStr OBJECT-TYPE
    SYNTAX      OCTET STRING
    MAX-ACCESS  read-only
    STATUS      current
    DESCRIPTION "Exchange out temperature as an octet string."
::= { grStatus 44 }

grOilIn OBJECT-TYPE
    SYNTAX      Opaque
    MAX-ACCESS  read-only
    STATUS      current
    DESCRIPTION "Oil in temperature as an opaque float."
::= { grStatus 45 }

grOilInStr OBJECT-TYPE
    SYNTAX      OCTET STRING
    MAX-ACCESS  read-only
    STATUS      current
    DESCRIPTION "Oil in temperature as an octet string."
::= { grStatus 46 }

grOilOut OBJECT-TYPE
    SYNTAX      Opaque
    MAX-ACCESS  read-only
    STATUS      current
    DESCRIPTION "Oil out temperature as an opaque float."
::= { grStatus 47 }

grOilOutStr OBJECT-TYPE
    SYNTAX      OCTET STRING
    MAX-ACCESS  read-only
    STATUS      current
    DESCRIPTION "Oil out temperature as an octet string."
::= { grStatus 48 }

grAmbientSensor OBJECT-TYPE
    SYNTAX      Opaque
    MAX-ACCESS  read-only
    STATUS      current
    DESCRIPTION "Ambient temperature sensor as an opaque float."
::= { grStatus 49 }

grAmbientSensorStr OBJECT-TYPE
    SYNTAX      OCTET STRING
    MAX-ACCESS  read-only
    STATUS      current
    DESCRIPTION "Ambient temperature sensor as an octet string."
::= { grStatus 50 }

grVoltageDiv OBJECT-TYPE
    SYNTAX      Opaque
    MAX-ACCESS  read-only
    STATUS      current
    DESCRIPTION "Voltage divider as an opaque float."
::= { grStatus 51 }

grVoltageDivStr OBJECT-TYPE
    SYNTAX      OCTET STRING
    MAX-ACCESS  read-only
    STATUS      current
    DESCRIPTION "Voltage divider as an octet string."
::= { grStatus 52 }

grVoltageDivArd OBJECT-TYPE
    SYNTAX      Opaque
    MAX-ACCESS  read-only
    STATUS      current
    DESCRIPTION "Arduino voltage divider as an opaque float."
::= { grStatus 53 }

grVoltageDivArdStr OBJECT-TYPE
    SYNTAX      OCTET STRING
    MAX-ACCESS  read-only
    STATUS      current
    DESCRIPTION "Arduino voltage divider as an octet string."
::= { grStatus 54 }

grTvss1 OBJECT-TYPE
    SYNTAX      OCTET STRING
    MAX-ACCESS  read-only
    STATUS      current
    DESCRIPTION "TVSS alarm 1 status as an octet string."
::= { grStatus 55 }

grTvss2 OBJECT-TYPE
    SYNTAX      OCTET STRING
    MAX-ACCESS  read-only
    STATUS      current
    DESCRIPTION "TVSS alarm 2 status as an octet string."
::= { grStatus 56 }

grFire1 OBJECT-TYPE
    SYNTAX      OCTET STRING
    MAX-ACCESS  read-only
    STATUS      current
    DESCRIPTION "Fire alarm 1 status as an octet string."
::= { grStatus 57 }

grFire2 OBJECT-TYPE
    SYNTAX      OCTET STRING
    MAX-ACCESS  read-only
    STATUS      current
    DESCRIPTION "Fire alarm 2 status as an octet string."
::= { grStatus 58 }

grContainment1 OBJECT-TYPE
    SYNTAX      OCTET STRING
    MAX-ACCESS  read-only
    STATUS      current
    DESCRIPTION "Containment leak alarm 1 status as an octet string."
::= { grStatus 59 }

grContainment2 OBJECT-TYPE
    SYNTAX      OCTET STRING
    MAX-ACCESS  read-only
    STATUS      current
    DESCRIPTION "Containment leak alarm 2 status as an octet string."
::= { grStatus 60 }

grWaterTreatment OBJECT-TYPE
    SYNTAX      OCTET STRING
    MAX-ACCESS  read-only
    STATUS      current
    DESCRIPTION "Water treatment alarm 1 status as an octet string."
::= { grStatus 61 }

grPrimarySystemIRms OBJECT-TYPE
    SYNTAX      Opaque
    MAX-ACCESS  read-only
    STATUS      current
    DESCRIPTION "Primary system current rms as an opaque float."
::= { grStatus 62 }

grPrimarySystemIRmsStr OBJECT-TYPE
    SYNTAX      OCTET STRING
    MAX-ACCESS  read-only
    STATUS      current
    DESCRIPTION "Primary system current rms as an octet string."
::= { grStatus 63 }

grPrimarySystemVRms OBJECT-TYPE
    SYNTAX      Opaque
    MAX-ACCESS  read-only
    STATUS      current
    DESCRIPTION "Primary system voltage rms as an opaque float."
::= { grStatus 64 }

grPrimarySystemVRmsStr OBJECT-TYPE
    SYNTAX      OCTET STRING
    MAX-ACCESS  read-only
    STATUS      current
    DESCRIPTION "Primary system voltage rms as an octet string."
::= { grStatus 65 }

grSecondarySystemIRms OBJECT-TYPE
    SYNTAX      Opaque
    MAX-ACCESS  read-only
    STATUS      current
    DESCRIPTION "Secondary system current rms as an opaque float."
::= { grStatus 66 }

grSecondarySystemIRmsStr OBJECT-TYPE
    SYNTAX      OCTET STRING
    MAX-ACCESS  read-only
    STATUS      current
    DESCRIPTION "Secondary system current rms as an octet string."
::= { grStatus 67 }

grPrimarySystemPower OBJECT-TYPE
    SYNTAX      Opaque
    MAX-ACCESS  read-only
    STATUS      current
    DESCRIPTION "Primary system power as an opaque float."
::= { grStatus 68 }

grPrimarySystemPowerStr OBJECT-TYPE
    SYNTAX      OCTET STRING
    MAX-ACCESS  read-only
    STATUS      current
    DESCRIPTION "Primary system power as an octet string."
::= { grStatus 69 }

grCteIMonitor OBJECT-TYPE
    SYNTAX      Opaque
    MAX-ACCESS  read-only
    STATUS      current
    DESCRIPTION "CTE current monitor as an opaque float."
::= { grStatus 70 }

grCteIMonitorStr OBJECT-TYPE
    SYNTAX      OCTET STRING
    MAX-ACCESS  read-only
    STATUS      current
    DESCRIPTION "CTE current monitor as an octet string."
::= { grStatus 71 }

grCteVMonitor OBJECT-TYPE
    SYNTAX      Opaque
    MAX-ACCESS  read-only
    STATUS      current
    DESCRIPTION "CTE voltage monitor as an opaque float."
::= { grStatus 72 }

grCteVMonitorStr OBJECT-TYPE
    SYNTAX      OCTET STRING
    MAX-ACCESS  read-only
    STATUS      current
    DESCRIPTION "CTE voltage monitor as an octet string."
::= { grStatus 73 }

grCtePower OBJECT-TYPE
    SYNTAX      Opaque
    MAX-ACCESS  read-only
    STATUS      current
    DESCRIPTION "CTE power as an opaque float."
::= { grStatus 74 }

grCtePowerStr OBJECT-TYPE
    SYNTAX      OCTET STRING
    MAX-ACCESS  read-only
    STATUS      current
    DESCRIPTION "CTE power as an octet string."
::= { grStatus 75 }

grHeatDissipation OBJECT-TYPE
    SYNTAX      Opaque
    MAX-ACCESS  read-only
    STATUS      current
    DESCRIPTION "Heat dissipation as an opaque float."
::= { grStatus 76 }

grHeatDissipationStr OBJECT-TYPE
    SYNTAX      OCTET STRING
    MAX-ACCESS  read-only
    STATUS      current
    DESCRIPTION "Heat dissipation as an octet string."
::= { grStatus 77 }

END
