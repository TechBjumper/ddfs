KNUERR-COOLCON-MIB-V7 DEFINITIONS ::= BEGIN


IMPORTS
	MODULE-IDENTITY, OBJECT-TYPE, NOTIFICATION-TYPE, enterprises
		FROM SNMPv2-SMI
	DisplayString
		FROM RFC1213-MIB
	MODULE-COMPLIANCE, OBJECT-GROUP, NOTIFICATION-GROUP
		FROM SNMPv2-CONF
	TEXTUAL-CONVENTION
		FROM SNMPv2-TC
	;


		
		
coolingMib MODULE-IDENTITY
	LAST-UPDATED "200903170900Z"
	ORGANIZATION "Knuerr AG"
	CONTACT-INFO
		"Knürr Electronics GmbH
		Glashüttenstr. 1
		D-01623 Lommatzsch
		Germany

		www.knuerr.com
		fon +49 035241 56-0
		fax +49 035241 56-252"
	DESCRIPTION
		"The MIB for Knuerr cooling products CoolTherm and CoolLoop"
	REVISION "200903170900Z"
	DESCRIPTION
		"Revision 7 by LP"
	::= { knuerr 10 }


knuerr OBJECT IDENTIFIER 	::= { enterprises 2769 }

cooling OBJECT IDENTIFIER 	::= { knuerr 2 }

coolControl OBJECT IDENTIFIER 	::= { cooling 1 }

coolEnvironment OBJECT IDENTIFIER 	::= { coolControl 1 }

temp1 OBJECT IDENTIFIER 	::= { coolEnvironment 1 }

temp1Name OBJECT-TYPE
	SYNTAX  DisplayString
	MAX-ACCESS read-write
	STATUS  current
	DESCRIPTION
		"The name of the temperature reading"
	::= { temp1 1 }


temp1CalibrationOffset OBJECT-TYPE
	SYNTAX  INTEGER (-100..100)
	MAX-ACCESS read-write
	STATUS  current
	DESCRIPTION
		"Calibration offset in 0.1 degrees"
	::= { temp1 2 }


temp1Current OBJECT-TYPE
	SYNTAX  INTEGER (-20..100)
	MAX-ACCESS read-only
	STATUS  current
	DESCRIPTION
		"The current temperature reading in °C"
	::= { temp1 3 }


temp1SettingLevel OBJECT-TYPE
	SYNTAX  INTEGER (30..50)
	MAX-ACCESS read-write
	STATUS  current
	DESCRIPTION
		"The setting warm air temperature for air condition in °C"
	::= { temp1 4 }


temp1WarningLevel OBJECT-TYPE
	SYNTAX  INTEGER (30..55)
	MAX-ACCESS read-write
	STATUS  current
	DESCRIPTION
		"The warning temperature for warm air in °C"
	::= { temp1 5 }


temp1AlarmLevel OBJECT-TYPE
	SYNTAX  INTEGER (35..60)
	MAX-ACCESS read-write
	STATUS  current
	DESCRIPTION
		"The alarm temperature for warm air in °C"
	::= { temp1 6 }


temp2 OBJECT IDENTIFIER 	::= { coolEnvironment 2 }

temp2Name OBJECT-TYPE
	SYNTAX  DisplayString
	MAX-ACCESS read-write
	STATUS  current
	DESCRIPTION
		"The name of the temperature reading"
	::= { temp2 1 }


temp2CalibrationOffset OBJECT-TYPE
	SYNTAX  INTEGER (-100..100)
	MAX-ACCESS read-write
	STATUS  current
	DESCRIPTION
		"Calibration offset in 0.1 degrees"
	::= { temp2 2 }


temp2Current OBJECT-TYPE
	SYNTAX  INTEGER (-20..100)
	MAX-ACCESS read-only
	STATUS  current
	DESCRIPTION
		"The current temperature reading in °C"
	::= { temp2 3 }


temp2SettingLevel OBJECT-TYPE
	SYNTAX  INTEGER (15..25)
	MAX-ACCESS read-write
	STATUS  current
	DESCRIPTION
		"The setting cold air temperature for air condition in °C"
	::= { temp2 4 }


temp2WarningLevel OBJECT-TYPE
	SYNTAX  INTEGER (15..30)
	MAX-ACCESS read-write
	STATUS  current
	DESCRIPTION
		"The warning temperature for cold air in °C"
	::= { temp2 5 }


temp2AlarmLevel OBJECT-TYPE
	SYNTAX  INTEGER (20..35)
	MAX-ACCESS read-write
	STATUS  current
	DESCRIPTION
		"The alarm temperature for cold air in °C"
	::= { temp2 6 }


temp2DoorsOpenLevel OBJECT-TYPE
	SYNTAX  INTEGER (25..40)
	MAX-ACCESS read-write
	STATUS  current
	DESCRIPTION
		"The door open temperature for cold air in °C"
	::= { temp2 7 }


temp2ServerOFFLevel OBJECT-TYPE
	SYNTAX  INTEGER (30..50)
	MAX-ACCESS read-write
	STATUS  current
	DESCRIPTION
		"The server OFF temperature for cold air in °C"
	::= { temp2 8 }


temp3 OBJECT IDENTIFIER 	::= { coolEnvironment 3 }

temp3Name OBJECT-TYPE
	SYNTAX  DisplayString
	MAX-ACCESS read-write
	STATUS  current
	DESCRIPTION
		"The name of the warm air temperature reading in rack left"
	::= { temp3 1 }


temp3CalibrationOffset OBJECT-TYPE
	SYNTAX  INTEGER (-100..100)
	MAX-ACCESS read-write
	STATUS  current
	DESCRIPTION
		"Calibration offset in 0.1 degrees"
	::= { temp3 2 }


temp3Current OBJECT-TYPE
	SYNTAX  INTEGER (-20..100)
	MAX-ACCESS read-only
	STATUS  current
	DESCRIPTION
		"The current temperature reading in °C"
	::= { temp3 3 }


temp3WarningLevel OBJECT-TYPE
	SYNTAX  INTEGER (15..60)
	MAX-ACCESS read-write
	STATUS  current
	DESCRIPTION
		"The warning temperature for warm air in °C"
	::= { temp3 4 }


temp3AlarmLevel OBJECT-TYPE
	SYNTAX  INTEGER (20..60)
	MAX-ACCESS read-write
	STATUS  current
	DESCRIPTION
		"The alarm temperature for warm air in °C"
	::= { temp3 5 }


temp4 OBJECT IDENTIFIER 	::= { coolEnvironment 4 }

temp4Name OBJECT-TYPE
	SYNTAX  DisplayString
	MAX-ACCESS read-write
	STATUS  current
	DESCRIPTION
		"The name of the cold air temperature reading in rack left"
	::= { temp4 1 }


temp4CalibrationOffset OBJECT-TYPE
	SYNTAX  INTEGER (-100..100)
	MAX-ACCESS read-write
	STATUS  current
	DESCRIPTION
		"Calibration offset in 0.1 degrees"
	::= { temp4 2 }


temp4Current OBJECT-TYPE
	SYNTAX  INTEGER (-20..100)
	MAX-ACCESS read-only
	STATUS  current
	DESCRIPTION
		"The current temperature reading in °C"
	::= { temp4 3 }


temp4WarningLevel OBJECT-TYPE
	SYNTAX  INTEGER (15..60)
	MAX-ACCESS read-write
	STATUS  current
	DESCRIPTION
		"The warning temperature for warm air in °C"
	::= { temp4 4 }


temp4AlarmLevel OBJECT-TYPE
	SYNTAX  INTEGER (20..60)
	MAX-ACCESS read-write
	STATUS  current
	DESCRIPTION
		"The alarm temperature for warm air in °C"
	::= { temp4 5 }


temp5 OBJECT IDENTIFIER 	::= { coolEnvironment 5 }

temp5Name OBJECT-TYPE
	SYNTAX  DisplayString
	MAX-ACCESS read-write
	STATUS  current
	DESCRIPTION
		"The name of the warm air temperature reading in rack left"
	::= { temp5 1 }


temp5CalibrationOffset OBJECT-TYPE
	SYNTAX  INTEGER (-100..100)
	MAX-ACCESS read-write
	STATUS  current
	DESCRIPTION
		"Calibration offset in 0.1 degrees"
	::= { temp5 2 }


temp5Current OBJECT-TYPE
	SYNTAX  INTEGER (-20..100)
	MAX-ACCESS read-only
	STATUS  current
	DESCRIPTION
		"The current temperature reading in °C"
	::= { temp5 3 }


temp5WarningLevel OBJECT-TYPE
	SYNTAX  INTEGER (15..60)
	MAX-ACCESS read-write
	STATUS  current
	DESCRIPTION
		"The warning temperature for warm air in °C"
	::= { temp5 4 }


temp5AlarmLevel OBJECT-TYPE
	SYNTAX  INTEGER (20..60)
	MAX-ACCESS read-write
	STATUS  current
	DESCRIPTION
		"The alarm temperature for warm air in °C"
	::= { temp5 5 }


temp6 OBJECT IDENTIFIER 	::= { coolEnvironment 6 }

temp6Name OBJECT-TYPE
	SYNTAX  DisplayString
	MAX-ACCESS read-write
	STATUS  current
	DESCRIPTION
		"The name of the cold air temperature reading in rack right"
	::= { temp6 1 }


temp6CalibrationOffset OBJECT-TYPE
	SYNTAX  INTEGER (-100..100)
	MAX-ACCESS read-write
	STATUS  current
	DESCRIPTION
		"Calibration offset in 0.1 degrees"
	::= { temp6 2 }


temp6Current OBJECT-TYPE
	SYNTAX  INTEGER (-20..100)
	MAX-ACCESS read-only
	STATUS  current
	DESCRIPTION
		"The current temperature reading in °C"
	::= { temp6 3 }


temp6WarningLevel OBJECT-TYPE
	SYNTAX  INTEGER (15..60)
	MAX-ACCESS read-write
	STATUS  current
	DESCRIPTION
		"The warning temperature for warm air in °C"
	::= { temp6 4 }


temp6AlarmLevel OBJECT-TYPE
	SYNTAX  INTEGER (20..60)
	MAX-ACCESS read-write
	STATUS  current
	DESCRIPTION
		"The alarm temperature for warm air in °C"
	::= { temp6 5 }


hum1 OBJECT IDENTIFIER 	::= { coolEnvironment 7 }

hum1Name OBJECT-TYPE
	SYNTAX  DisplayString
	MAX-ACCESS read-write
	STATUS  current
	DESCRIPTION
		"The name of the humidity reading"
	::= { hum1 1 }


hum1Current OBJECT-TYPE
	SYNTAX  INTEGER (0..100)
	MAX-ACCESS read-only
	STATUS  current
	DESCRIPTION
		"The current humidity reading in %rH"
	::= { hum1 2 }


hum1LowAlarmLevel OBJECT-TYPE
	SYNTAX  INTEGER (0..100)
	MAX-ACCESS read-write
	STATUS  current
	DESCRIPTION
		"The lower alarm humidity in %rH"
	::= { hum1 3 }


hum1UpperAlarm OBJECT-TYPE
	SYNTAX  INTEGER (0..100)
	MAX-ACCESS read-write
	STATUS  current
	DESCRIPTION
		"The humidity upper alarm level in %rH"
	::= { hum1 4 }


tempOutWater OBJECT IDENTIFIER 	::= { coolEnvironment 8 }

tempOutWaterName OBJECT-TYPE
	SYNTAX  DisplayString
	MAX-ACCESS read-write
	STATUS  current
	DESCRIPTION
		"The name of the output water temperature reading"
	::= { tempOutWater 1 }


tempOutWaterCurrent OBJECT-TYPE
	SYNTAX  INTEGER (0..30)
	MAX-ACCESS read-only
	STATUS  current
	DESCRIPTION
		"The current output water temperature reading in degrees"
	::= { tempOutWater 2 }


tempOutWaterLoAlarmLevel OBJECT-TYPE
	SYNTAX  INTEGER (0..30)
	MAX-ACCESS read-write
	STATUS  current
	DESCRIPTION
		"The output water temperature low alarm level in degrees"
	::= { tempOutWater 3 }


tempOutWaterHiAlarmLevel OBJECT-TYPE
	SYNTAX  INTEGER (0..30)
	MAX-ACCESS read-write
	STATUS  current
	DESCRIPTION
		"The output water temperature upper alarm level in degrees"
	::= { tempOutWater 4 }


tempInWater OBJECT IDENTIFIER 	::= { coolEnvironment 9 }

tempInWaterName OBJECT-TYPE
	SYNTAX  DisplayString
	MAX-ACCESS read-write
	STATUS  current
	DESCRIPTION
		"The name of the input water temperature reading"
	::= { tempInWater 1 }


tempInWaterCurrent OBJECT-TYPE
	SYNTAX  INTEGER (0..30)
	MAX-ACCESS read-only
	STATUS  current
	DESCRIPTION
		"The current input water temperature reading in degrees"
	::= { tempInWater 2 }


tempInWaterLoAlarmLevel OBJECT-TYPE
	SYNTAX  INTEGER (0..30)
	MAX-ACCESS read-write
	STATUS  current
	DESCRIPTION
		"The input water temperature low alarm level in degrees"
	::= { tempInWater 3 }


tempInWaterHiAlarmLevel OBJECT-TYPE
	SYNTAX  INTEGER (0..30)
	MAX-ACCESS read-write
	STATUS  current
	DESCRIPTION
		"The input water temperature upper alarm level in degrees"
	::= { tempInWater 4 }


flowWater OBJECT IDENTIFIER 	::= { coolEnvironment 10 }

flowWaterName OBJECT-TYPE
	SYNTAX  DisplayString
	MAX-ACCESS read-write
	STATUS  current
	DESCRIPTION
		"The name of the water flow reading"
	::= { flowWater 1 }


flowWaterCurrent OBJECT-TYPE
	SYNTAX  INTEGER (0..200)
	MAX-ACCESS read-only
	STATUS  current
	DESCRIPTION
		"The current water flow reading in litres per minute"
	::= { flowWater 2 }


energyConsumptionMainsA1 OBJECT IDENTIFIER 	::= { coolEnvironment 11 }

currentL1A1 OBJECT-TYPE
	SYNTAX  INTEGER (0..100)
	MAX-ACCESS read-only
	STATUS  current
	DESCRIPTION
		"Mains A current L1 in 0.1 ampere"
	::= { energyConsumptionMainsA1 1 }


currentL2A1 OBJECT-TYPE
	SYNTAX  INTEGER (0..100)
	MAX-ACCESS read-only
	STATUS  current
	DESCRIPTION
		"Mains A: current L2 in 0.1 ampere"
	::= { energyConsumptionMainsA1 2 }


currentL3A1 OBJECT-TYPE
	SYNTAX  INTEGER (0..100)
	MAX-ACCESS read-only
	STATUS  current
	DESCRIPTION
		"Mains A: current L3 in 0.1 ampere"
	::= { energyConsumptionMainsA1 3 }


voltageL1A1 OBJECT-TYPE
	SYNTAX  INTEGER (0..500)
	MAX-ACCESS read-only
	STATUS  current
	DESCRIPTION
		"Mains A: voltage between L1 and N in 0.1 volts"
	::= { energyConsumptionMainsA1 4 }


voltageL2A1 OBJECT-TYPE
	SYNTAX  INTEGER (0..500)
	MAX-ACCESS read-only
	STATUS  current
	DESCRIPTION
		"Mains A: voltage between L2 and N in 0.1 volts"
	::= { energyConsumptionMainsA1 5 }


voltageL3A1 OBJECT-TYPE
	SYNTAX  INTEGER (0..500)
	MAX-ACCESS read-only
	STATUS  current
	DESCRIPTION
		"Mains A: voltage between L3 and N in 0.1 volts"
	::= { energyConsumptionMainsA1 6 }


activePowerMainsA1 OBJECT-TYPE
	SYNTAX  INTEGER (0..100)
	MAX-ACCESS read-only
	STATUS  current
	DESCRIPTION
		"The power consumption of mains A in watt"
	::= { energyConsumptionMainsA1 7 }


apparentPowerMainsA1 OBJECT-TYPE
	SYNTAX  INTEGER (0..100)
	MAX-ACCESS read-only
	STATUS  current
	DESCRIPTION
		"The apparent power factor of mains A in VA"
	::= { energyConsumptionMainsA1 8 }


reactivePowerMainsA1 OBJECT-TYPE
	SYNTAX  INTEGER (0..100)
	MAX-ACCESS read-only
	STATUS  current
	DESCRIPTION
		"The reactive power factor of mains A in var"
	::= { energyConsumptionMainsA1 9 }


cosphiA1 OBJECT-TYPE
	SYNTAX  INTEGER (0..100)
	MAX-ACCESS read-only
	STATUS  current
	DESCRIPTION
		"The power factor of mains A Rack 1"
	::= { energyConsumptionMainsA1 10 }


energyA1 OBJECT-TYPE
	SYNTAX  INTEGER (0..100)
	MAX-ACCESS read-only
	STATUS  current
	DESCRIPTION
		"The energy of mains A Rack 1 in 0,1kWh"
	::= { energyConsumptionMainsA1 11 }


energyB1 OBJECT-TYPE
	SYNTAX  INTEGER (0..100)
	MAX-ACCESS read-only
	STATUS  current
	DESCRIPTION
		"The energy of mains B Rack 1 in 0,1kWh"
	::= { energyConsumptionMainsB1 11 }


energyA2 OBJECT-TYPE
	SYNTAX  INTEGER (0..100)
	MAX-ACCESS read-only
	STATUS  current
	DESCRIPTION
		"The energy of mains A Rack 2 in 0,1kWh"
	::= { energyConsumptionMainsA2 11 }


energyB2 OBJECT-TYPE
	SYNTAX  INTEGER (0..100)
	MAX-ACCESS read-only
	STATUS  current
	DESCRIPTION
		"The energy of mains B Rack 2 in 0,1kWh"
	::= { energyConsumptionMainsB2 11 }


energyConsumptionMainsB1 OBJECT IDENTIFIER 	::= { coolEnvironment 12 }

currentL1B1 OBJECT-TYPE
	SYNTAX  INTEGER (0..1000)
	MAX-ACCESS read-only
	STATUS  current
	DESCRIPTION
		"Mains B current L1 in 0.1 ampere"
	::= { energyConsumptionMainsB1 1 }


currentL2B1 OBJECT-TYPE
	SYNTAX  INTEGER (0..1000)
	MAX-ACCESS read-only
	STATUS  current
	DESCRIPTION
		"Mains B: current L2 in 0.1 ampere"
	::= { energyConsumptionMainsB1 2 }


currentL3B1 OBJECT-TYPE
	SYNTAX  INTEGER (0..1000)
	MAX-ACCESS read-only
	STATUS  current
	DESCRIPTION
		"Mains B: current L3 in 0.1 ampere"
	::= { energyConsumptionMainsB1 3 }


voltageL1B1 OBJECT-TYPE
	SYNTAX  INTEGER (0..5000)
	MAX-ACCESS read-only
	STATUS  current
	DESCRIPTION
		"Mains B: voltage between L1 and N in 0.1 volts"
	::= { energyConsumptionMainsB1 4 }


voltageL2B1 OBJECT-TYPE
	SYNTAX  INTEGER (0..5000)
	MAX-ACCESS read-only
	STATUS  current
	DESCRIPTION
		"Mains B: voltage between L2 and N in 0.1 volts"
	::= { energyConsumptionMainsB1 5 }


voltageL3B1 OBJECT-TYPE
	SYNTAX  INTEGER (0..5000)
	MAX-ACCESS read-only
	STATUS  current
	DESCRIPTION
		"Mains B: voltage between L3 and N in 0.1 volts"
	::= { energyConsumptionMainsB1 6 }


activePowerMainsB1 OBJECT-TYPE
	SYNTAX  INTEGER (0..50000)
	MAX-ACCESS read-only
	STATUS  current
	DESCRIPTION
		"The power consumption of mains B in watt"
	::= { energyConsumptionMainsB1 7 }


apparentPowerMainsB1 OBJECT-TYPE
	SYNTAX  INTEGER (0..50000)
	MAX-ACCESS read-only
	STATUS  current
	DESCRIPTION
		"The apparent power factor of mains B in VA"
	::= { energyConsumptionMainsB1 8 }


reactivePowerMainsB1 OBJECT-TYPE
	SYNTAX  INTEGER (0..50000)
	MAX-ACCESS read-only
	STATUS  current
	DESCRIPTION
		"The reactive power factor of mains B in var"
	::= { energyConsumptionMainsB1 9 }


cosphiB1 OBJECT-TYPE
	SYNTAX  INTEGER (0..100)
	MAX-ACCESS read-only
	STATUS  current
	DESCRIPTION
		"The power factor of mains B in *100"
	::= { energyConsumptionMainsB1 10 }


fanValveValues OBJECT IDENTIFIER 	::= { coolEnvironment 13 }

fanValveValuesName OBJECT-TYPE
	SYNTAX  DisplayString
	MAX-ACCESS read-only
	STATUS  current
	DESCRIPTION
		"The name of fan value and valve position reading"
	::= { fanValveValues 1 }


fanSpeed OBJECT-TYPE
	SYNTAX  INTEGER (0..200)
	MAX-ACCESS read-only
	STATUS  current
	DESCRIPTION
		"The current fan speed reading in percent"
	::= { fanValveValues 2 }


valvePosition OBJECT-TYPE
	SYNTAX  INTEGER (0..200)
	MAX-ACCESS read-only
	STATUS  current
	DESCRIPTION
		"The current valve position reading in percent"
	::= { fanValveValues 3 }


energyConsumptionMainsA2 OBJECT IDENTIFIER 	::= { coolEnvironment 14 }

currentL1A2 OBJECT-TYPE
	SYNTAX  INTEGER (0..1000)
	MAX-ACCESS read-only
	STATUS  current
	DESCRIPTION
		"Mains B current L1 in 0.1 ampere"
	::= { energyConsumptionMainsA2 1 }


currentL2A2 OBJECT-TYPE
	SYNTAX  INTEGER (0..1000)
	MAX-ACCESS read-only
	STATUS  current
	DESCRIPTION
		"Mains B: current L2 in 0.1 ampere"
	::= { energyConsumptionMainsA2 2 }


currentL3A2 OBJECT-TYPE
	SYNTAX  INTEGER (0..1000)
	MAX-ACCESS read-only
	STATUS  current
	DESCRIPTION
		"Mains B: current L3 in 0.1 ampere"
	::= { energyConsumptionMainsA2 3 }


voltageL1A2 OBJECT-TYPE
	SYNTAX  INTEGER (0..5000)
	MAX-ACCESS read-only
	STATUS  current
	DESCRIPTION
		"Mains B: voltage between L1 and N in 0.1 volts"
	::= { energyConsumptionMainsA2 4 }


voltageL2A2 OBJECT-TYPE
	SYNTAX  INTEGER (0..5000)
	MAX-ACCESS read-only
	STATUS  current
	DESCRIPTION
		"Mains B: voltage between L2 and N in 0.1 volts"
	::= { energyConsumptionMainsA2 5 }


voltageL3A2 OBJECT-TYPE
	SYNTAX  INTEGER (0..5000)
	MAX-ACCESS read-only
	STATUS  current
	DESCRIPTION
		"Mains B: voltage between L3 and N in 0.1 volts"
	::= { energyConsumptionMainsA2 6 }


activePowerMainsA2 OBJECT-TYPE
	SYNTAX  INTEGER (0..50000)
	MAX-ACCESS read-only
	STATUS  current
	DESCRIPTION
		"The power consumption of mains B in watt"
	::= { energyConsumptionMainsA2 7 }


apparentPowerMainsA2 OBJECT-TYPE
	SYNTAX  INTEGER (0..50000)
	MAX-ACCESS read-only
	STATUS  current
	DESCRIPTION
		"The apparent power factor of mains B in VA"
	::= { energyConsumptionMainsA2 8 }


reactivePowerMainsA2 OBJECT-TYPE
	SYNTAX  INTEGER (0..50000)
	MAX-ACCESS read-only
	STATUS  current
	DESCRIPTION
		"The reactive power factor of mains B in var"
	::= { energyConsumptionMainsA2 9 }


cosphiA2 OBJECT-TYPE
	SYNTAX  INTEGER (0..100)
	MAX-ACCESS read-only
	STATUS  current
	DESCRIPTION
		"The power factor of mains B in *100"
	::= { energyConsumptionMainsA2 10 }


energyConsumptionMainsB2 OBJECT IDENTIFIER 	::= { coolEnvironment 15 }

currentL1B2 OBJECT-TYPE
	SYNTAX  INTEGER (0..1000)
	MAX-ACCESS read-only
	STATUS  current
	DESCRIPTION
		"Mains B current L1 in 0.1 ampere"
	::= { energyConsumptionMainsB2 1 }


currentL2B2 OBJECT-TYPE
	SYNTAX  INTEGER (0..1000)
	MAX-ACCESS read-only
	STATUS  current
	DESCRIPTION
		"Mains B: current L2 in 0.1 ampere"
	::= { energyConsumptionMainsB2 2 }


currentL3B2 OBJECT-TYPE
	SYNTAX  INTEGER (0..1000)
	MAX-ACCESS read-only
	STATUS  current
	DESCRIPTION
		"Mains B: current L3 in 0.1 ampere"
	::= { energyConsumptionMainsB2 3 }


voltageL1B2 OBJECT-TYPE
	SYNTAX  INTEGER (0..5000)
	MAX-ACCESS read-only
	STATUS  current
	DESCRIPTION
		"Mains B: voltage between L1 and N in 0.1 volts"
	::= { energyConsumptionMainsB2 4 }


voltageL2B2 OBJECT-TYPE
	SYNTAX  INTEGER (0..5000)
	MAX-ACCESS read-only
	STATUS  current
	DESCRIPTION
		"Mains B: voltage between L2 and N in 0.1 volts"
	::= { energyConsumptionMainsB2 5 }


voltageL3B2 OBJECT-TYPE
	SYNTAX  INTEGER (0..5000)
	MAX-ACCESS read-only
	STATUS  current
	DESCRIPTION
		"Mains B: voltage between L3 and N in 0.1 volts"
	::= { energyConsumptionMainsB2 6 }


activePowerMainsB2 OBJECT-TYPE
	SYNTAX  INTEGER (0..50000)
	MAX-ACCESS read-only
	STATUS  current
	DESCRIPTION
		"The power consumption of mains B in watt"
	::= { energyConsumptionMainsB2 7 }


apparentPowerMainsB2 OBJECT-TYPE
	SYNTAX  INTEGER (0..50000)
	MAX-ACCESS read-only
	STATUS  current
	DESCRIPTION
		"The apparent power factor of mains B in VA"
	::= { energyConsumptionMainsB2 8 }


reactivePowerMainsB2 OBJECT-TYPE
	SYNTAX  INTEGER (0..50000)
	MAX-ACCESS read-only
	STATUS  current
	DESCRIPTION
		"The reactive power factor of mains B in var"
	::= { energyConsumptionMainsB2 9 }


cosphiB2 OBJECT-TYPE
	SYNTAX  INTEGER (0..100)
	MAX-ACCESS read-only
	STATUS  current
	DESCRIPTION
		"The power factor of mains B in *100"
	::= { energyConsumptionMainsB2 10 }


coolContact OBJECT IDENTIFIER 	::= { coolControl 2 }

contactBasisNames OBJECT IDENTIFIER 	::= { coolContact 1 }

fan1Name OBJECT-TYPE
	SYNTAX  DisplayString
	MAX-ACCESS read-write
	STATUS  current
	DESCRIPTION
		"The name of fan 1"
	::= { contactBasisNames 1 }


fan2Name OBJECT-TYPE
	SYNTAX  DisplayString
	MAX-ACCESS read-write
	STATUS  current
	DESCRIPTION
		"The name of fan 2"
	::= { contactBasisNames 2 }


fan3Name OBJECT-TYPE
	SYNTAX  DisplayString
	MAX-ACCESS read-write
	STATUS  current
	DESCRIPTION
		"The name of fan 3"
	::= { contactBasisNames 3 }


fan4Name OBJECT-TYPE
	SYNTAX  DisplayString
	MAX-ACCESS read-write
	STATUS  current
	DESCRIPTION
		"The name of fan 4"
	::= { contactBasisNames 4 }


waterName OBJECT-TYPE
	SYNTAX  DisplayString
	MAX-ACCESS read-write
	STATUS  current
	DESCRIPTION
		"The name of the contact"
	::= { contactBasisNames 5 }


smokeName OBJECT-TYPE
	SYNTAX  DisplayString
	MAX-ACCESS read-write
	STATUS  current
	DESCRIPTION
		"The name of the contact"
	::= { contactBasisNames 6 }


mainsAName OBJECT-TYPE
	SYNTAX  DisplayString
	MAX-ACCESS read-write
	STATUS  current
	DESCRIPTION
		"The name of mains A"
	::= { contactBasisNames 7 }


mainsBName OBJECT-TYPE
	SYNTAX  DisplayString
	MAX-ACCESS read-write
	STATUS  current
	DESCRIPTION
		"The name of the input 8 PLC"
	::= { contactBasisNames 8 }


contactSmokeExtingNames OBJECT IDENTIFIER 	::= { coolContact 2 }

smokePreAlarm1Name OBJECT-TYPE
	SYNTAX  DisplayString
	MAX-ACCESS read-write
	STATUS  current
	DESCRIPTION
		"The name of the smoke pre alarm 1 contact"
	::= { contactSmokeExtingNames 1 }


smokeMainAlarm1Name OBJECT-TYPE
	SYNTAX  DisplayString
	MAX-ACCESS read-write
	STATUS  current
	DESCRIPTION
		"The name of the smoke main alarm 1 contact"
	::= { contactSmokeExtingNames 2 }


smokeDefectName OBJECT-TYPE
	SYNTAX  DisplayString
	MAX-ACCESS read-write
	STATUS  current
	DESCRIPTION
		"The name of the smoke detection defect contact"
	::= { contactSmokeExtingNames 3 }


smokeExtinguishedName OBJECT-TYPE
	SYNTAX  DisplayString
	MAX-ACCESS read-write
	STATUS  current
	DESCRIPTION
		"The name of the smoke extinguished contact"
	::= { contactSmokeExtingNames 4 }


smokePreAlarm2Name OBJECT-TYPE
	SYNTAX  DisplayString
	MAX-ACCESS read-write
	STATUS  current
	DESCRIPTION
		"The name of the smoke pre alarm 2 contact"
	::= { contactSmokeExtingNames 5 }


smokeMainAlarm2Name OBJECT-TYPE
	SYNTAX  DisplayString
	MAX-ACCESS read-write
	STATUS  current
	DESCRIPTION
		"The name of the smoke main alarm 2 contact"
	::= { contactSmokeExtingNames 6 }


contactDoorNames OBJECT IDENTIFIER 	::= { coolContact 3 }

doorLeftFrontName OBJECT-TYPE
	SYNTAX  DisplayString
	MAX-ACCESS read-write
	STATUS  current
	DESCRIPTION
		"The name of the contact"
	::= { contactDoorNames 1 }


doorLeftRearName OBJECT-TYPE
	SYNTAX  DisplayString
	MAX-ACCESS read-write
	STATUS  current
	DESCRIPTION
		"The name of the contact"
	::= { contactDoorNames 2 }


doorRightFrontName OBJECT-TYPE
	SYNTAX  DisplayString
	MAX-ACCESS read-write
	STATUS  current
	DESCRIPTION
		"The name of the contact"
	::= { contactDoorNames 3 }


doorRightRearName OBJECT-TYPE
	SYNTAX  DisplayString
	MAX-ACCESS read-write
	STATUS  current
	DESCRIPTION
		"The name of the contact"
	::= { contactDoorNames 4 }


doorCoolFrontName OBJECT-TYPE
	SYNTAX  DisplayString
	MAX-ACCESS read-write
	STATUS  current
	DESCRIPTION
		"The name of the contact"
	::= { contactDoorNames 5 }


doorCoolRearName OBJECT-TYPE
	SYNTAX  DisplayString
	MAX-ACCESS read-write
	STATUS  current
	DESCRIPTION
		"The name of the contact"
	::= { contactDoorNames 6 }


contactBasisCurrentStates OBJECT IDENTIFIER 	::= { coolContact 4 }

fan1CurrentState OBJECT-TYPE
	SYNTAX  INTEGER (0..1)
	MAX-ACCESS read-only
	STATUS  current
	DESCRIPTION
		"The current state of the fan 1 contact"
	::= { contactBasisCurrentStates 1 }


fan2CurrentState OBJECT-TYPE
	SYNTAX  INTEGER (0..1)
	MAX-ACCESS read-only
	STATUS  current
	DESCRIPTION
		"The current state of the fan 2 contact"
	::= { contactBasisCurrentStates 2 }


fan3CurrentState OBJECT-TYPE
	SYNTAX  INTEGER (0..1)
	MAX-ACCESS read-only
	STATUS  current
	DESCRIPTION
		"The current state of the fan 3 contact"
	::= { contactBasisCurrentStates 3 }


fan4CurrentState OBJECT-TYPE
	SYNTAX  INTEGER (0..1)
	MAX-ACCESS read-only
	STATUS  current
	DESCRIPTION
		"The current state of the fan 4 contact"
	::= { contactBasisCurrentStates 4 }


waterCurrentState OBJECT-TYPE
	SYNTAX  INTEGER (0..1)
	MAX-ACCESS read-only
	STATUS  current
	DESCRIPTION
		"The current state of water sensor contact"
	::= { contactBasisCurrentStates 5 }


smokeCurrentState OBJECT-TYPE
	SYNTAX  INTEGER (0..1)
	MAX-ACCESS read-only
	STATUS  current
	DESCRIPTION
		"The current state of smoke detector contact"
	::= { contactBasisCurrentStates 6 }


mainsACurrentState OBJECT-TYPE
	SYNTAX  INTEGER (0..1)
	MAX-ACCESS read-only
	STATUS  current
	DESCRIPTION
		"The current state of mains A contact"
	::= { contactBasisCurrentStates 7 }


mainsBCurrentState OBJECT-TYPE
	SYNTAX  INTEGER (0..1)
	MAX-ACCESS read-only
	STATUS  current
	DESCRIPTION
		"The current state of input 8 contact"
	::= { contactBasisCurrentStates 8 }


contactSmokeExtingCurrentStates OBJECT IDENTIFIER 	::= { coolContact 5 }

smokePreAlarm1CurrentState OBJECT-TYPE
	SYNTAX  INTEGER (0..1)
	MAX-ACCESS read-only
	STATUS  current
	DESCRIPTION
		"The current state of smoke pre-alarm 1 contact"
	::= { contactSmokeExtingCurrentStates 1 }


smokeMainAlarm1CurrentState OBJECT-TYPE
	SYNTAX  INTEGER (0..1)
	MAX-ACCESS read-only
	STATUS  current
	DESCRIPTION
		"The current state of smoke main alarm 1 contact"
	::= { contactSmokeExtingCurrentStates 2 }


smokeDefectCurrentState OBJECT-TYPE
	SYNTAX  INTEGER (0..1)
	MAX-ACCESS read-only
	STATUS  current
	DESCRIPTION
		"The current state of smoke defekt contact"
	::= { contactSmokeExtingCurrentStates 3 }


smokeExtinguishedCurrentState OBJECT-TYPE
	SYNTAX  INTEGER (0..1)
	MAX-ACCESS read-only
	STATUS  current
	DESCRIPTION
		"The current state of extinguishing released contact"
	::= { contactSmokeExtingCurrentStates 4 }


smokePreAlarm2CurrentState OBJECT-TYPE
	SYNTAX  INTEGER (0..1)
	MAX-ACCESS read-only
	STATUS  current
	DESCRIPTION
		"The current state of smoke pre-alarm 2 contact"
	::= { contactSmokeExtingCurrentStates 5 }


smokeMainAlarm2CurrentState OBJECT-TYPE
	SYNTAX  INTEGER (0..1)
	MAX-ACCESS read-only
	STATUS  current
	DESCRIPTION
		"The current state of smoke main alarm 2 contact"
	::= { contactSmokeExtingCurrentStates 6 }


contactDoorCurrentStates OBJECT IDENTIFIER 	::= { coolContact 6 }

doorLeftFrontCurrentState OBJECT-TYPE
	SYNTAX  INTEGER (0..1)
	MAX-ACCESS read-only
	STATUS  current
	DESCRIPTION
		"The current state of rack left door front contact"
	::= { contactDoorCurrentStates 1 }


doorLeftRearCurrentState OBJECT-TYPE
	SYNTAX  INTEGER (0..1)
	MAX-ACCESS read-only
	STATUS  current
	DESCRIPTION
		"The current state of rack left door rear contact"
	::= { contactDoorCurrentStates 2 }


doorRightFrontCurrentState OBJECT-TYPE
	SYNTAX  INTEGER (0..1)
	MAX-ACCESS read-only
	STATUS  current
	DESCRIPTION
		"The current state of rack right door front contact"
	::= { contactDoorCurrentStates 3 }


doorRightRearCurrentState OBJECT-TYPE
	SYNTAX  INTEGER (0..1)
	MAX-ACCESS read-only
	STATUS  current
	DESCRIPTION
		"The current state of rack right door rear contact"
	::= { contactDoorCurrentStates 4 }


doorCoolFrontCurrentState OBJECT-TYPE
	SYNTAX  INTEGER (0..1)
	MAX-ACCESS read-only
	STATUS  current
	DESCRIPTION
		"The current state of Cool-Loop(-Therm) door front contact"
	::= { contactDoorCurrentStates 5 }


doorCoolRearCurrentState OBJECT-TYPE
	SYNTAX  INTEGER (0..1)
	MAX-ACCESS read-only
	STATUS  current
	DESCRIPTION
		"The current state of Cool-Loop(-Therm) door rear contact"
	::= { contactDoorCurrentStates 6 }


contactBasisTraps OBJECT IDENTIFIER 	::= { coolContact 7 }

fan1Trap OBJECT-TYPE
	SYNTAX  INTEGER (0..1)
	MAX-ACCESS read-write
	STATUS  current
	DESCRIPTION
		"Set to 0 for trap disabled, 1 for enabled"
	::= { contactBasisTraps 1 }


fan2Trap OBJECT-TYPE
	SYNTAX  INTEGER (0..1)
	MAX-ACCESS read-write
	STATUS  current
	DESCRIPTION
		"Set to 0 for trap disabled, 1 for enabled"
	::= { contactBasisTraps 2 }


fan3Trap OBJECT-TYPE
	SYNTAX  INTEGER (0..1)
	MAX-ACCESS read-write
	STATUS  current
	DESCRIPTION
		"Set to 0 for trap disabled, 1 for enabled"
	::= { contactBasisTraps 3 }


fan4Trap OBJECT-TYPE
	SYNTAX  INTEGER (0..1)
	MAX-ACCESS read-write
	STATUS  current
	DESCRIPTION
		"Set to 0 for trap disabled, 1 for enabled"
	::= { contactBasisTraps 4 }


waterTrap OBJECT-TYPE
	SYNTAX  INTEGER (0..1)
	MAX-ACCESS read-write
	STATUS  current
	DESCRIPTION
		"Set to 0 for trap disabled, 1 for enabled"
	::= { contactBasisTraps 5 }


smokeTrap OBJECT-TYPE
	SYNTAX  INTEGER (0..1)
	MAX-ACCESS read-write
	STATUS  current
	DESCRIPTION
		"Set to 0 for trap disabled, 1 for enabled"
	::= { contactBasisTraps 6 }


mainsATrap OBJECT-TYPE
	SYNTAX  INTEGER (0..1)
	MAX-ACCESS read-write
	STATUS  current
	DESCRIPTION
		"Set to 0 for trap disabled, 1 for enabled"
	::= { contactBasisTraps 7 }


mainsBTrap OBJECT-TYPE
	SYNTAX  INTEGER (0..1)
	MAX-ACCESS read-write
	STATUS  current
	DESCRIPTION
		"Set to 0 for trap disabled, 1 for enabled"
	::= { contactBasisTraps 8 }


contactSmokeExtingTraps OBJECT IDENTIFIER 	::= { coolContact 8 }

smokePreAlarm1Trap OBJECT-TYPE
	SYNTAX  INTEGER (0..1)
	MAX-ACCESS read-write
	STATUS  current
	DESCRIPTION
		"Set to 0 for trap disabled, 1 for enabled"
	::= { contactSmokeExtingTraps 1 }


smokeMainAlarm1Trap OBJECT-TYPE
	SYNTAX  INTEGER (0..1)
	MAX-ACCESS read-write
	STATUS  current
	DESCRIPTION
		"Set to 0 for trap disabled, 1 for enabled"
	::= { contactSmokeExtingTraps 2 }


smokeDefectTrap OBJECT-TYPE
	SYNTAX  INTEGER (0..1)
	MAX-ACCESS read-write
	STATUS  current
	DESCRIPTION
		"Set to 0 for trap disabled, 1 for enabled"
	::= { contactSmokeExtingTraps 3 }


smokeExtinguishedTrap OBJECT-TYPE
	SYNTAX  INTEGER (0..1)
	MAX-ACCESS read-write
	STATUS  current
	DESCRIPTION
		"Set to 0 for trap disabled, 1 for enabled"
	::= { contactSmokeExtingTraps 4 }


smokePreAlarm2Trap OBJECT-TYPE
	SYNTAX  INTEGER (0..1)
	MAX-ACCESS read-write
	STATUS  current
	DESCRIPTION
		"Set to 0 for trap disabled, 1 for enabled"
	::= { contactSmokeExtingTraps 5 }


smokeMainAlarm2Trap OBJECT-TYPE
	SYNTAX  INTEGER (0..1)
	MAX-ACCESS read-write
	STATUS  current
	DESCRIPTION
		"Set to 0 for trap disabled, 1 for enabled"
	::= { contactSmokeExtingTraps 6 }


contactDoorTraps OBJECT IDENTIFIER 	::= { coolContact 9 }

doorLeftFrontTrap OBJECT-TYPE
	SYNTAX  INTEGER (0..1)
	MAX-ACCESS read-write
	STATUS  current
	DESCRIPTION
		"Set to 0 for trap disabled, 1 for enabled"
	::= { contactDoorTraps 1 }


doorLeftRearTrap OBJECT-TYPE
	SYNTAX  INTEGER (0..1)
	MAX-ACCESS read-write
	STATUS  current
	DESCRIPTION
		"Set to 0 for trap disabled, 1 for enabled"
	::= { contactDoorTraps 2 }


doorRightFrontTrap OBJECT-TYPE
	SYNTAX  INTEGER (0..1)
	MAX-ACCESS read-write
	STATUS  current
	DESCRIPTION
		"Set to 0 for trap disabled, 1 for enabled"
	::= { contactDoorTraps 3 }


doorRightRearTrap OBJECT-TYPE
	SYNTAX  INTEGER (0..1)
	MAX-ACCESS read-write
	STATUS  current
	DESCRIPTION
		"Set to 0 for trap disabled, 1 for enabled"
	::= { contactDoorTraps 4 }


doorCoolFrontTrap OBJECT-TYPE
	SYNTAX  INTEGER (0..1)
	MAX-ACCESS read-write
	STATUS  current
	DESCRIPTION
		"Set to 0 for trap disabled, 1 for enabled"
	::= { contactDoorTraps 5 }


doorCoolRearTrap OBJECT-TYPE
	SYNTAX  INTEGER (0..1)
	MAX-ACCESS read-write
	STATUS  current
	DESCRIPTION
		"Set to 0 for trap disabled, 1 for enabled"
	::= { contactDoorTraps 6 }


contactBasisTrapRepeat OBJECT IDENTIFIER 	::= { coolContact 10 }

fan1TrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 1 }


fan2TrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 2 }


fan3TrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 3 }


fan4TrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 4 }


waterTrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 5 }


smokeTrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 6 }


mainsATrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 7 }


mainsBTrapRepeat OBJECT-TYPE
	SYNTAX  INTEGER (0..600)
	MAX-ACCESS read-write
	STATUS  current
	DESCRIPTION
		"Set to '0' for no repetition after the first trap is sent, select '1' to '600' in seconds for enable repetition."
	::= { contactBasisTrapRepeat 8 }


contactSmokeExtingTrapRepeat OBJECT IDENTIFIER 	::= { coolContact 11 }

smokePreAlarm1TrapRepeat OBJECT-TYPE
	SYNTAX  INTEGER (0..600)
	MAX-ACCESS read-write
	STATUS  current
	DESCRIPTION
		"Set to '0' for no repetition after the first trap is sent, select '1' to '600' in seconds for enable repetition."
	::= { contactSmokeExtingTrapRepeat 1 }


smokeMainAlarm1TrapRepeat OBJECT-TYPE
	SYNTAX  INTEGER (0..600)
	MAX-ACCESS read-write
	STATUS  current
	DESCRIPTION
		"Set to '0' for no repetition after the first trap is sent, select '1' to '600' in seconds for enable repetition."
	::= { contactSmokeExtingTrapRepeat 2 }


smokeDefectTrapRepeat OBJECT-TYPE
	SYNTAX  INTEGER (0..600)
	MAX-ACCESS read-write
	STATUS  current
	DESCRIPTION
		"Set to '0' for no repetition after the first trap is sent, select '1' to '600' in seconds for enable repetition."
	::= { contactSmokeExtingTrapRepeat 3 }


smokeExtinguishedTrapRepeat OBJECT-TYPE
	SYNTAX  INTEGER (0..600)
	MAX-ACCESS read-write
	STATUS  current
	DESCRIPTION
		"Set to '0' for no repetition after the first trap is sent, select '1' to '600' in seconds for enable repetition."
	::= { contactSmokeExtingTrapRepeat 4 }


smokePreAlarm2TrapRepeat OBJECT-TYPE
	SYNTAX  INTEGER (0..600)
	MAX-ACCESS read-write
	STATUS  current
	DESCRIPTION
		"Set to '0' for no repetition after the first trap is sent, select '1' to '600' in seconds for enable repetition."
	::= { contactSmokeExtingTrapRepeat 5 }


smokeMainAlarm2TrapRepeat OBJECT-TYPE
	SYNTAX  INTEGER (0..600)
	MAX-ACCESS read-write
	STATUS  current
	DESCRIPTION
		"Set to '0' for no repetition after the first trap is sent, select '1' to '600' in seconds for enable repetition."
	::= { contactSmokeExtingTrapRepeat 6 }


contactDoorTrapRepeat OBJECT IDENTIFIER 	::= { coolContact 12 }

doorLeftFrontTrapRepeat OBJECT-TYPE
	SYNTAX  INTEGER (0..600)
	MAX-ACCESS read-write
	STATUS  current
	DESCRIPTION
		"Set to '0' for no repetition after the first trap is sent, select '1' to '600' in seconds for enable repetition."
	::= { contactDoorTrapRepeat 1 }


doorLeftRearTrapRepeat OBJECT-TYPE
	SYNTAX  INTEGER (0..600)
	MAX-ACCESS read-write
	STATUS  current
	DESCRIPTION
		"Set to '0' for no repetition after the first trap is sent, select '1' to '600' in seconds for enable repetition."
	::= { contactDoorTrapRepeat 2 }


doorRightFrontTrapRepeat OBJECT-TYPE
	SYNTAX  INTEGER (0..600)
	MAX-ACCESS read-write
	STATUS  current
	DESCRIPTION
		"Set to '0' for no repetition after the first trap is sent, select '1' to '600' in seconds for enable repetition."
	::= { contactDoorTrapRepeat 3 }


doorRightRearTrapRepeat OBJECT-TYPE
	SYNTAX  INTEGER (0..600)
	MAX-ACCESS read-write
	STATUS  current
	DESCRIPTION
		"Set to '0' for no repetition after the first trap is sent, select '1' to '600' in seconds for enable repetition."
	::= { contactDoorTrapRepeat 4 }


doorCoolFrontTrapRepeat OBJECT-TYPE
	SYNTAX  INTEGER (0..600)
	MAX-ACCESS read-write
	STATUS  current
	DESCRIPTION
		"Set to '0' for no repetition after the first trap is sent, select '1' to '600' in seconds for enable repetition."
	::= { contactDoorTrapRepeat 5 }


doorCoolRearTrapRepeat OBJECT-TYPE
	SYNTAX  INTEGER (0..600)
	MAX-ACCESS read-write
	STATUS  current
	DESCRIPTION
		"Set to '0' for no repetition after the first trap is sent, select '1' to '600' in seconds for enable repetition."
	::= { contactDoorTrapRepeat 6 }


coolOutput OBJECT IDENTIFIER 	::= { coolControl 3 }

outputEnables OBJECT IDENTIFIER 	::= { coolOutput 1 }

out1Enable OBJECT-TYPE
	SYNTAX  INTEGER (0..1)
	MAX-ACCESS read-write
	STATUS  current
	DESCRIPTION
		"Set to '1' enables the output"
	::= { outputEnables 1 }


out2Enable OBJECT-TYPE
	SYNTAX  INTEGER (0..1)
	MAX-ACCESS read-write
	STATUS  current
	DESCRIPTION
		"Set to '1' enables the output"
	::= { outputEnables 2 }


out3Enable OBJECT-TYPE
	SYNTAX  INTEGER (0..1)
	MAX-ACCESS read-write
	STATUS  current
	DESCRIPTION
		"Set to '1' enables the output"
	::= { outputEnables 3 }


out4Enable OBJECT-TYPE
	SYNTAX  INTEGER (0..1)
	MAX-ACCESS read-write
	STATUS  current
	DESCRIPTION
		"Set to '1' enables the output"
	::= { outputEnables 4 }


outputNames OBJECT IDENTIFIER 	::= { coolOutput 2 }

out1Name OBJECT-TYPE
	SYNTAX  DisplayString
	MAX-ACCESS read-write
	STATUS  current
	DESCRIPTION
		"The name of output 1"
	::= { outputNames 1 }


out2Name OBJECT-TYPE
	SYNTAX  DisplayString
	MAX-ACCESS read-write
	STATUS  current
	DESCRIPTION
		"The name of output 2"
	::= { outputNames 2 }


out3Name OBJECT-TYPE
	SYNTAX  DisplayString
	MAX-ACCESS read-write
	STATUS  current
	DESCRIPTION
		"The name of output 3"
	::= { outputNames 3 }


out4Name OBJECT-TYPE
	SYNTAX  DisplayString
	MAX-ACCESS read-write
	STATUS  current
	DESCRIPTION
		"The name of output 4"
	::= { outputNames 4 }


outputStates OBJECT IDENTIFIER 	::= { coolOutput 3 }

out1State OBJECT-TYPE
	SYNTAX  INTEGER (0..1)
	MAX-ACCESS read-only
	STATUS  current
	DESCRIPTION
		"Current State of output 1, '1' is enabled, '0' is not enabled."
	::= { outputStates 1 }


out2State OBJECT-TYPE
	SYNTAX  INTEGER (0..1)
	MAX-ACCESS read-only
	STATUS  current
	DESCRIPTION
		"Current State of output 2, '1' is enabled, '0' is not enabled."
	::= { outputStates 2 }


out3State OBJECT-TYPE
	SYNTAX  INTEGER (0..1)
	MAX-ACCESS read-only
	STATUS  current
	DESCRIPTION
		"Current State of output 3, '1' is enabled, '0' is not enabled."
	::= { outputStates 3 }


out4State OBJECT-TYPE
	SYNTAX  INTEGER (0..1)
	MAX-ACCESS read-only
	STATUS  current
	DESCRIPTION
		"Current State of output 4, '1' is enabled, '0' is not enabled."
	::= { outputStates 4 }


outputTraps OBJECT IDENTIFIER 	::= { coolOutput 4 }

out1Trap OBJECT-TYPE
	SYNTAX  INTEGER (0..1)
	MAX-ACCESS read-write
	STATUS  current
	DESCRIPTION
		"Set to '0' for trap disabled, '1' for enabled"
	::= { outputTraps 1 }


out2Trap OBJECT-TYPE
	SYNTAX  INTEGER (0..1)
	MAX-ACCESS read-write
	STATUS  current
	DESCRIPTION
		"Set to '0' for trap disabled, '1' for enabled"
	::= { outputTraps 2 }


out3Trap OBJECT-TYPE
	SYNTAX  INTEGER (0..1)
	MAX-ACCESS read-write
	STATUS  current
	DESCRIPTION
		"Set to '0' for trap disabled, '1' for enabled"
	::= { outputTraps 3 }


out4Trap OBJECT-TYPE
	SYNTAX  INTEGER (0..1)
	MAX-ACCESS read-write
	STATUS  current
	DESCRIPTION
		"Set to '0' for trap disabled, '1' for enabled"
	::= { outputTraps 4 }


outputTrapRepeat OBJECT IDENTIFIER 	::= { coolOutput 5 }

out1TrapRepeat OBJECT-TYPE
	SYNTAX  INTEGER (0..1)
	MAX-ACCESS read-write
	STATUS  current
	DESCRIPTION
		"Set to '0' for no repetition after the first trap is sent, select '1' to '600' in seconds for enable repetition."
	::= { outputTrapRepeat 1 }


out2TrapRepeat OBJECT-TYPE
	SYNTAX  INTEGER (0..1)
	MAX-ACCESS read-write
	STATUS  current
	DESCRIPTION
		"Set to '0' for no repetition after the first trap is sent, select '1' to '600' in seconds for enable repetition."
	::= { outputTrapRepeat 2 }


out3TrapRepeat OBJECT-TYPE
	SYNTAX  INTEGER (0..1)
	MAX-ACCESS read-write
	STATUS  current
	DESCRIPTION
		"Set to '0' for no repetition after the first trap is sent, select '1' to '600' in seconds for enable repetition."
	::= { outputTrapRepeat 3 }


out4TrapRepeat OBJECT-TYPE
	SYNTAX  INTEGER (0..1)
	MAX-ACCESS read-write
	STATUS  current
	DESCRIPTION
		"Set to '0' for no repetition after the first trap is sent, select '1' to '600' in seconds for enable repetition."
	::= { outputTrapRepeat 4 }


coolTrap OBJECT IDENTIFIER 	::= { coolControl 5 }

coolTraps OBJECT IDENTIFIER 	::= { coolTrap 0 }


fans NOTIFICATION-TYPE
	OBJECTS {
		fan1Norm,
		fan1Alarm,
		fan2Norm,
		fan2Alarm,
		fan3Norm,
		fan3Alarm,
		fan4Norm,
		fan4Alarm}
	STATUS  current
	DESCRIPTION
		"fan error alarms"
	::= { coolTraps 1 }


watersensor NOTIFICATION-TYPE
	OBJECTS {
		waterNorm,
		waterAlarm}
	STATUS  current
	DESCRIPTION "water leakage sensor alarm "
	::= { coolTraps 2 }


smokeDetect NOTIFICATION-TYPE
	OBJECTS {
		smokeNorm,
		smokeAlarm,
		smokePreAlarm1Norm,
		smokePreAlarm1Alarm,
		smokeMainAlarm1Norm,
		smokeMainAlarm1Alarm,
		smokeDefectNorm,
		smokeDefectAlarm,
		smokeExtinguishedNorm,
		smokeExtinguishedAlarm,
		smokePreAlarm2Norm,
		smokePreAlarm2Alarm,
		smokeMainAlarm2Norm,
		smokeMainAlarm2Alarm}
	STATUS  current
	DESCRIPTION "smoke sensor and smoke extinguishing system alarms"
	::= { coolTraps 3 }


mainsControl NOTIFICATION-TYPE
	OBJECTS {
		mainsANorm,
		mainsAAlarm,
		mainsBNorm,
		mainsBAlarm}
	STATUS  current
	DESCRIPTION "mains A/B switch error"
	::= { coolTraps 4 }


doors NOTIFICATION-TYPE
	OBJECTS {
		doorLeftFrontNorm,
		doorLeftFrontAlarm,
		doorLeftRearNorm,
		doorLeftRearAlarm,
		doorRightFrontNorm,
		doorRightFrontAlarm,
		doorRightRearNorm,
		doorRightRearAlarm,
		doorCfrontNorm,
		doorCfrontAlarm,
		doorCrearNorm,
		doorCrearAlarm}
	STATUS  current
	DESCRIPTION "door contact alarms"
	::= { coolTraps 5 }


outputs NOTIFICATION-TYPE
	OBJECTS {
		out1Norm,
		out1NotNorm,
		out2Norm,
		out2NotNorm,
		out3Norm,
		out3NotNorm,
		out4Norm,
		out4NotNorm}
	STATUS  current
	DESCRIPTION "digital output state notification"
	::= { coolTraps 6 }


temperatures NOTIFICATION-TYPE
	OBJECTS {
		temp1UpperNoWarning,
		temp1UpperWarning,
		temp1UpperNoAlarm,
		temp1UpperAlarm,
		temp2UpperNoWarning,
		temp2UpperWarning,
		temp2UpperNoAlarm,
		temp2UpperAlarm,
		temp3UpperNoWarning,
		temp3UpperWarning,
		temp3UpperNoAlarm,
		temp3UpperAlarm,
		temp4UpperNoWarning,
		temp4UpperWarning,
		temp4UpperNoAlarm,
		temp4UpperAlarm,
		temp5UpperNoWarning,
		temp5UpperWarning,
		temp5UpperNoAlarm,
		temp5UpperAlarm,
		temp6UpperNoWarning,
		temp6UpperWarning,
		temp6UpperNoAlarm,
		temp6UpperAlarm,
		temp2LowNoAlarm,
		temp2LowAlarm,
		coldwaterLowNormal,
		coldwaterLowAlarm,
		coldwaterUpperNormal,
		coldwaterUpperAlarm,
		warmwaterLowNormal,
		warmwaterLowAlarm,
		warmwaterUpperNormal,
		warmwaterUpperAlarm,
		temp2DoorOpenNorm,
		temp2DoorOpenAlarm,
		temp2ServerOFFNorm,
		temp2ServerOFFAlarm}
	STATUS  current
	DESCRIPTION "temperature warnings and alarms"
	::= { coolTraps 7 }


humidity NOTIFICATION-TYPE
	OBJECTS {
		humidityUpperNormal,
		humidityUpperAlarm,
		humidityLowNormal,
		humidityLowAlarm}
	STATUS  current
	DESCRIPTION "relative humidity alarms"
	::= { coolTraps 8 }


inputs NOTIFICATION-TYPE
	OBJECTS {
		in1Low,
		in1High,
		in2Low,
		in2High,
		in3Low,
		in3High,
		in4Low,
		in4High}
	STATUS  current
	DESCRIPTION "digital inputs state notification"
	::= { coolTraps 9 }


powerMeasurement NOTIFICATION-TYPE
	OBJECTS {
		currentRack1ANorm,
		currentRack1AAlarm,
		currentRack1BNorm,
		currentRack1BAlarm,
		currentRack2ANorm,
		currentRack2AAlarm,
		currentRack2BNorm,
		currentRack2BAlarm,
		voltageMainsA1Norm,
		voltageMainsA1Alarm,
		voltageMainsB1Norm,
		voltageMainsB1Alarm,
		voltageMainsA2Norm,
		voltageMainsA2Alarm,
		voltageMainsB2Norm,
		voltageMainsB2Alarm,
		powerMainsA1Norm,
		powerMainsA1Alarm,
		powerMainsB1Norm,
		powerMainsB1Alarm,
		powerMainsA2Norm,
		powerMainsA2Alarm,
		powerMainsB2Norm,
		powerMainsB2Alarm}
	STATUS  current
	DESCRIPTION "power measurement alarms"
	::= { coolTraps 10 }

coolTrapsGroup NOTIFICATION-GROUP
	NOTIFICATIONS {
		fans,
		watersensor,
		smokeDetect,
		mainsControl,
		doors,
		outputs,
		temperatures,
		humidity,
		inputs,
		powerMeasurement }
	STATUS  current
	DESCRIPTION "group of notifications"
	::= { coolTraps 12 }


fan1Normal NOTIFICATION-TYPE
	OBJECTS {
		fan1Norm}
	STATUS  current
	DESCRIPTION ""
	::= { coolTrap 1 }


fan1NotNormal NOTIFICATION-TYPE
	OBJECTS {
		fan1Alarm}
	STATUS  current
	DESCRIPTION ""
	::= { coolTrap 2 }


fan2Normal NOTIFICATION-TYPE
	OBJECTS {
		fan2Norm}
	STATUS  current
	DESCRIPTION ""
	::= { coolTrap 3 }


fan2NotNormal NOTIFICATION-TYPE
	OBJECTS {
		fan2Alarm}
	STATUS  current
	DESCRIPTION ""
	::= { coolTrap 4 }


fan3Normal NOTIFICATION-TYPE
	OBJECTS {
		fan3Norm}
	STATUS  current
	DESCRIPTION ""
	::= { coolTrap 5 }


fan3NotNormal NOTIFICATION-TYPE
	OBJECTS {
		fan3Alarm}
	STATUS  current
	DESCRIPTION ""
	::= { coolTrap 6 }


fan4Normal NOTIFICATION-TYPE
	OBJECTS {
		fan4Norm}
	STATUS  current
	DESCRIPTION ""
	::= { coolTrap 7 }


fan4NotNormal NOTIFICATION-TYPE
	OBJECTS {
		fan4Alarm}
	STATUS  current
	DESCRIPTION ""
	::= { coolTrap 8 }


waterNormal NOTIFICATION-TYPE
	OBJECTS {
		waterNorm}
	STATUS  current
	DESCRIPTION ""
	::= { coolTrap 9 }


waterNotNormal NOTIFICATION-TYPE
	OBJECTS {
		waterAlarm}
	STATUS  current
	DESCRIPTION ""
	::= { coolTrap 10 }


smokeNormal NOTIFICATION-TYPE
	OBJECTS {
		smokeNorm}
	STATUS  current
	DESCRIPTION ""
	::= { coolTrap 11 }


smokeNotNormal NOTIFICATION-TYPE
	OBJECTS {
		smokeAlarm}
	STATUS  current
	DESCRIPTION ""
	::= { coolTrap 12 }


mainsANormal NOTIFICATION-TYPE
	OBJECTS {
		mainsANorm}
	STATUS  current
	DESCRIPTION ""
	::= { coolTrap 13 }


mainsANotNormal NOTIFICATION-TYPE
	OBJECTS {
		mainsAAlarm}
	STATUS  current
	DESCRIPTION ""
	::= { coolTrap 14 }


mainsBNormal NOTIFICATION-TYPE
	OBJECTS {
		mainsBNorm}
	STATUS  current
	DESCRIPTION ""
	::= { coolTrap 15 }


mainsBNotNormal NOTIFICATION-TYPE
	OBJECTS {
		mainsBAlarm}
	STATUS  current
	DESCRIPTION ""
	::= { coolTrap 16 }


smokePreAlarmNormal NOTIFICATION-TYPE
	OBJECTS {
		smokePreAlarm1Norm}
	STATUS  current
	DESCRIPTION ""
	::= { coolTrap 17 }


smokePreAlarmNotNormal NOTIFICATION-TYPE
	OBJECTS {
		smokePreAlarm1Alarm}
	STATUS  current
	DESCRIPTION ""
	::= { coolTrap 18 }


smokeMainAlarmNormal NOTIFICATION-TYPE
	OBJECTS {
		smokeMainAlarm1Norm}
	STATUS  current
	DESCRIPTION ""
	::= { coolTrap 19 }


smokeMainAlarmNotNormal NOTIFICATION-TYPE
	OBJECTS {
		smokeMainAlarm1Alarm}
	STATUS  current
	DESCRIPTION ""
	::= { coolTrap 20 }


smokeDefectNormal NOTIFICATION-TYPE
	OBJECTS {
		smokeDefectNorm}
	STATUS  current
	DESCRIPTION ""
	::= { coolTrap 21 }


smokeDefectNotNormal NOTIFICATION-TYPE
	OBJECTS {
		smokeDefectAlarm}
	STATUS  current
	DESCRIPTION ""
	::= { coolTrap 22 }


smokeExtinguishedNormal NOTIFICATION-TYPE
	OBJECTS {
		smokeExtinguishedNorm}
	STATUS  current
	DESCRIPTION ""
	::= { coolTrap 23 }


smokeExtinguishedNotNormal NOTIFICATION-TYPE
	OBJECTS {
		smokeExtinguishedAlarm}
	STATUS  current
	DESCRIPTION ""
	::= { coolTrap 24 }


doorLeftFrontNormal NOTIFICATION-TYPE
	OBJECTS {
		doorLeftFrontNorm}
	STATUS  current
	DESCRIPTION ""
	::= { coolTrap 25 }


doorLeftFrontNotNormal NOTIFICATION-TYPE
	OBJECTS {
		doorLeftFrontAlarm}
	STATUS  current
	DESCRIPTION ""
	::= { coolTrap 26 }


doorLeftRearNormal NOTIFICATION-TYPE
	OBJECTS {
		doorLeftRearNorm}
	STATUS  current
	DESCRIPTION ""
	::= { coolTrap 27 }


doorLeftRearNotNormal NOTIFICATION-TYPE
	OBJECTS {
		doorLeftRearAlarm}
	STATUS  current
	DESCRIPTION ""
	::= { coolTrap 28 }


doorRightFrontNormal NOTIFICATION-TYPE
	OBJECTS {
		doorRightFrontNorm}
	STATUS  current
	DESCRIPTION ""
	::= { coolTrap 29 }


doorRightFrontNotNormal NOTIFICATION-TYPE
	OBJECTS {
		doorRightFrontAlarm}
	STATUS  current
	DESCRIPTION ""
	::= { coolTrap 30 }


doorRightRearNormal NOTIFICATION-TYPE
	OBJECTS {
		doorRightRearNorm}
	STATUS  current
	DESCRIPTION ""
	::= { coolTrap 31 }


doorRightRearNotNormal NOTIFICATION-TYPE
	OBJECTS {
		doorRightRearAlarm}
	STATUS  current
	DESCRIPTION ""
	::= { coolTrap 32 }


doorCfrontNormal NOTIFICATION-TYPE
	OBJECTS {
		doorCfrontNorm}
	STATUS  current
	DESCRIPTION ""
	::= { coolTrap 33 }


doorCfrontNotNormal NOTIFICATION-TYPE
	OBJECTS {
		doorCfrontAlarm}
	STATUS  current
	DESCRIPTION ""
	::= { coolTrap 34 }


doorCrearNormal NOTIFICATION-TYPE
	OBJECTS {
		doorCrearNorm}
	STATUS  current
	DESCRIPTION ""
	::= { coolTrap 35 }


doorCrearNotNormal NOTIFICATION-TYPE
	OBJECTS {
		doorCrearAlarm}
	STATUS  current
	DESCRIPTION ""
	::= { coolTrap 36 }


spare1Normal NOTIFICATION-TYPE
	OBJECTS {
		smokePreAlarm2Norm}
	STATUS  current
	DESCRIPTION ""
	::= { coolTrap 37 }


spare1NotNormal NOTIFICATION-TYPE
	OBJECTS {
		smokePreAlarm2Alarm}
	STATUS  current
	DESCRIPTION ""
	::= { coolTrap 38 }


spare2Normal NOTIFICATION-TYPE
	OBJECTS {
		smokeMainAlarm2Norm}
	STATUS  current
	DESCRIPTION ""
	::= { coolTrap 39 }


spare2NotNormal NOTIFICATION-TYPE
	OBJECTS {
		smokeMainAlarm2Alarm}
	STATUS  current
	DESCRIPTION ""
	::= { coolTrap 40 }


out1Normal NOTIFICATION-TYPE
	OBJECTS {
		out1Norm}
	STATUS  current
	DESCRIPTION ""
	::= { coolTrap 41 }


out1NotNormal NOTIFICATION-TYPE
	OBJECTS {
		out1NotNorm}
	STATUS  current
	DESCRIPTION ""
	::= { coolTrap 42 }


out2Normal NOTIFICATION-TYPE
	OBJECTS {
		out2Norm}
	STATUS  current
	DESCRIPTION ""
	::= { coolTrap 43 }


out2NotNormal NOTIFICATION-TYPE
	OBJECTS {
		out2NotNorm}
	STATUS  current
	DESCRIPTION ""
	::= { coolTrap 44 }


out3Normal NOTIFICATION-TYPE
	OBJECTS {
		out3Norm}
	STATUS  current
	DESCRIPTION ""
	::= { coolTrap 45 }


out3NotNormal NOTIFICATION-TYPE
	OBJECTS {
		out3NotNorm}
	STATUS  current
	DESCRIPTION ""
	::= { coolTrap 46 }


out4Normal NOTIFICATION-TYPE
	OBJECTS {
		out4Norm}
	STATUS  current
	DESCRIPTION ""
	::= { coolTrap 47 }


out4NotNormal NOTIFICATION-TYPE
	OBJECTS {
		out4NotNorm}
	STATUS  current
	DESCRIPTION ""
	::= { coolTrap 48 }


temp1UpperWarnNormal NOTIFICATION-TYPE
	OBJECTS {
		temp1UpperNoWarning}
	STATUS  current
	DESCRIPTION ""
	::= { coolTrap 49 }


temp1UpperWarnNotNormal NOTIFICATION-TYPE
	OBJECTS {
		temp1UpperWarning}
	STATUS  current
	DESCRIPTION ""
	::= { coolTrap 50 }


temp1UpperAlarmNormal NOTIFICATION-TYPE
	OBJECTS {
		temp2UpperNoAlarm}
	STATUS  current
	DESCRIPTION ""
	::= { coolTrap 51 }


temp1UpperAlarmNotNormal NOTIFICATION-TYPE
	OBJECTS {
		temp2UpperAlarm}
	STATUS  current
	DESCRIPTION ""
	::= { coolTrap 52 }


temp2UpperWarnNormal NOTIFICATION-TYPE
	OBJECTS {
		temp2UpperNoWarning}
	STATUS  current
	DESCRIPTION ""
	::= { coolTrap 53 }


temp2UpperWarnNotNormal NOTIFICATION-TYPE
	OBJECTS {
		temp2UpperWarning}
	STATUS  current
	DESCRIPTION ""
	::= { coolTrap 54 }


temp2UpperAlarmNormal NOTIFICATION-TYPE
	OBJECTS {
		temp2UpperNoAlarm}
	STATUS  current
	DESCRIPTION ""
	::= { coolTrap 55 }


temp2UpperAlarmNotNormal NOTIFICATION-TYPE
	OBJECTS {
		temp2UpperAlarm}
	STATUS  current
	DESCRIPTION ""
	::= { coolTrap 56 }


temp3UpperWarnNormal NOTIFICATION-TYPE
	OBJECTS {
		temp3UpperNoWarning}
	STATUS  current
	DESCRIPTION ""
	::= { coolTrap 57 }


temp3UpperWarnNotNormal NOTIFICATION-TYPE
	OBJECTS {
		temp3UpperWarning}
	STATUS  current
	DESCRIPTION ""
	::= { coolTrap 58 }


temp3UpperAlarmNormal NOTIFICATION-TYPE
	OBJECTS {
		temp3UpperNoAlarm}
	STATUS  current
	DESCRIPTION ""
	::= { coolTrap 59 }


temp3UpperAlarmNotNormal NOTIFICATION-TYPE
	OBJECTS {
		temp2UpperAlarm}
	STATUS  current
	DESCRIPTION ""
	::= { coolTrap 60 }


temp4UpperWarnNormal NOTIFICATION-TYPE
	OBJECTS {
		temp4UpperNoWarning}
	STATUS  current
	DESCRIPTION ""
	::= { coolTrap 61 }


temp4UpperWarnNotNormal NOTIFICATION-TYPE
	OBJECTS {
		temp4UpperWarning}
	STATUS  current
	DESCRIPTION ""
	::= { coolTrap 62 }


temp4UpperAlarmNormal NOTIFICATION-TYPE
	OBJECTS {
		temp4UpperNoAlarm}
	STATUS  current
	DESCRIPTION ""
	::= { coolTrap 63 }


temp4UpperAlarmNotNormal NOTIFICATION-TYPE
	OBJECTS {
		temp4UpperAlarm}
	STATUS  current
	DESCRIPTION ""
	::= { coolTrap 64 }


temp5UpperWarnNormal NOTIFICATION-TYPE
	OBJECTS {
		temp5UpperNoWarning}
	STATUS  current
	DESCRIPTION ""
	::= { coolTrap 65 }


temp5UpperWarnNotNormal NOTIFICATION-TYPE
	OBJECTS {
		temp5UpperWarning}
	STATUS  current
	DESCRIPTION ""
	::= { coolTrap 66 }


temp5UpperAlarmNormal NOTIFICATION-TYPE
	OBJECTS {
		temp5UpperNoAlarm}
	STATUS  current
	DESCRIPTION ""
	::= { coolTrap 67 }


temp5UpperAlarmNotNormal NOTIFICATION-TYPE
	OBJECTS {
		temp5UpperAlarm}
	STATUS  current
	DESCRIPTION ""
	::= { coolTrap 68 }


temp6UpperWarnNormal NOTIFICATION-TYPE
	OBJECTS {
		temp6UpperNoWarning}
	STATUS  current
	DESCRIPTION ""
	::= { coolTrap 69 }


temp6UpperWarnNotNormal NOTIFICATION-TYPE
	OBJECTS {
		temp6UpperWarning}
	STATUS  current
	DESCRIPTION ""
	::= { coolTrap 70 }


temp6UpperAlarmNormal NOTIFICATION-TYPE
	OBJECTS {
		temp6UpperNoAlarm}
	STATUS  current
	DESCRIPTION ""
	::= { coolTrap 71 }


temp6UpperAlarmNotNormal NOTIFICATION-TYPE
	OBJECTS {
		temp6UpperAlarm}
	STATUS  current
	DESCRIPTION ""
	::= { coolTrap 72 }


temp1LowAlarmNormal NOTIFICATION-TYPE
	OBJECTS {
		temp1LowNoAlarm}
	STATUS  current
	DESCRIPTION ""
	::= { coolTrap 73 }


temp1LowAlarmNotNormal NOTIFICATION-TYPE
	OBJECTS {
		temp1LowAlarm}
	STATUS  current
	DESCRIPTION ""
	::= { coolTrap 74 }


temp2LowAlarmNormal NOTIFICATION-TYPE
	OBJECTS {
		temp2LowNoAlarm}
	STATUS  current
	DESCRIPTION ""
	::= { coolTrap 75 }


temp2LowAlarmNotNormal NOTIFICATION-TYPE
	OBJECTS {
		temp2LowAlarm}
	STATUS  current
	DESCRIPTION ""
	::= { coolTrap 76 }


humidityUpperAlarmNormal NOTIFICATION-TYPE
	OBJECTS {
		humidityUpperNormal}
	STATUS  current
	DESCRIPTION ""
	::= { coolTrap 77 }


humidityUpperAlarmNotNormal NOTIFICATION-TYPE
	OBJECTS {
		humidityUpperAlarm}
	STATUS  current
	DESCRIPTION ""
	::= { coolTrap 78 }


humidityLowAlarmNormal NOTIFICATION-TYPE
	OBJECTS {
		humidityLowNormal}
	STATUS  current
	DESCRIPTION ""
	::= { coolTrap 79 }


humidityLowAlarmNotNormal NOTIFICATION-TYPE
	OBJECTS {
		humidityLowAlarm}
	STATUS  current
	DESCRIPTION ""
	::= { coolTrap 80 }


coldwaterLowAlarmNormal NOTIFICATION-TYPE
	OBJECTS {
		coldwaterLowNormal}
	STATUS  current
	DESCRIPTION ""
	::= { coolTrap 81 }


coldwaterLowAlarmNotNormal NOTIFICATION-TYPE
	OBJECTS {
		coldwaterLowAlarm}
	STATUS  current
	DESCRIPTION ""
	::= { coolTrap 82 }


coldwaterUpperAlarmNormal NOTIFICATION-TYPE
	OBJECTS {
		coldwaterUpperNormal}
	STATUS  current
	DESCRIPTION ""
	::= { coolTrap 83 }


coldwaterUpperAlarmNotNormal NOTIFICATION-TYPE
	OBJECTS {
		coldwaterUpperAlarm}
	STATUS  current
	DESCRIPTION ""
	::= { coolTrap 84 }


warmwaterLowAlarmNormal NOTIFICATION-TYPE
	OBJECTS {
		warmwaterLowNormal}
	STATUS  current
	DESCRIPTION ""
	::= { coolTrap 85 }


warmwaterLowAlarmNotNormal NOTIFICATION-TYPE
	OBJECTS {
		warmwaterLowAlarm}
	STATUS  current
	DESCRIPTION ""
	::= { coolTrap 86 }


warmwaterUpperAlarmNormal NOTIFICATION-TYPE
	OBJECTS {
		warmwaterUpperNormal}
	STATUS  current
	DESCRIPTION ""
	::= { coolTrap 87 }


warmwaterUpperAlarmNotNormal NOTIFICATION-TYPE
	OBJECTS {
		warmwaterUpperAlarm}
	STATUS  current
	DESCRIPTION ""
	::= { coolTrap 88 }


temp2DoorOpenNormal NOTIFICATION-TYPE
	OBJECTS {
		temp2DoorOpenNorm}
	STATUS  current
	DESCRIPTION ""
	::= { coolTrap 89 }


temp2DoorOpenNotNormal NOTIFICATION-TYPE
	OBJECTS {
		temp2DoorOpenAlarm}
	STATUS  current
	DESCRIPTION ""
	::= { coolTrap 90 }


temp2ServerOFFNormal NOTIFICATION-TYPE
	OBJECTS {
		temp2ServerOFFNorm}
	STATUS  current
	DESCRIPTION ""
	::= { coolTrap 91 }


temp2ServerOFFNotNormal NOTIFICATION-TYPE
	OBJECTS {
		temp2ServerOFFAlarm}
	STATUS  current
	DESCRIPTION ""
	::= { coolTrap 92 }


in1Normal NOTIFICATION-TYPE
	OBJECTS {
		in1Low}
	STATUS  current
	DESCRIPTION ""
	::= { coolTrap 93 }


in1NotNormal NOTIFICATION-TYPE
	OBJECTS {
		in1High}
	STATUS  current
	DESCRIPTION ""
	::= { coolTrap 94 }


in2Normal NOTIFICATION-TYPE
	OBJECTS {
		in2Low}
	STATUS  current
	DESCRIPTION ""
	::= { coolTrap 95 }


in2NotNormal NOTIFICATION-TYPE
	OBJECTS {
		in2High}
	STATUS  current
	DESCRIPTION ""
	::= { coolTrap 96 }


in3Normal NOTIFICATION-TYPE
	OBJECTS {
		in3Low}
	STATUS  current
	DESCRIPTION ""
	::= { coolTrap 97 }


in3NotNormal NOTIFICATION-TYPE
	OBJECTS {
		in3High}
	STATUS  current
	DESCRIPTION ""
	::= { coolTrap 98 }


in4Normal NOTIFICATION-TYPE
	OBJECTS {
		in4Low}
	STATUS  current
	DESCRIPTION ""
	::= { coolTrap 99 }


in4NotNormal NOTIFICATION-TYPE
	OBJECTS {
		in4High}
	STATUS  current
	DESCRIPTION ""
	::= { coolTrap 100 }


currentL1ANormal NOTIFICATION-TYPE
	OBJECTS {
		currentRack1ANorm}
	STATUS  current
	DESCRIPTION ""
	::= { coolTrap 101 }


currentL1ANotNormal NOTIFICATION-TYPE
	OBJECTS {
		currentRack1AAlarm}
	STATUS  current
	DESCRIPTION ""
	::= { coolTrap 102 }


voltageMainsANormal NOTIFICATION-TYPE
	OBJECTS {
		voltageMainsA1Norm}
	STATUS  current
	DESCRIPTION ""
	::= { coolTrap 113 }


voltageMainsANotNormal NOTIFICATION-TYPE
	OBJECTS {
		voltageMainsA1Alarm}
	STATUS  current
	DESCRIPTION ""
	::= { coolTrap 114 }


voltageMainsBNormal NOTIFICATION-TYPE
	OBJECTS {
		voltageMainsB1Norm}
	STATUS  current
	DESCRIPTION ""
	::= { coolTrap 115 }


voltageMainsBNotNormal NOTIFICATION-TYPE
	OBJECTS {
		voltageMainsB1Alarm}
	STATUS  current
	DESCRIPTION ""
	::= { coolTrap 116 }


powerMainsANormal NOTIFICATION-TYPE
	OBJECTS {
		powerMainsA1Norm}
	STATUS  current
	DESCRIPTION ""
	::= { coolTrap 117 }


powerMainsANotNormal NOTIFICATION-TYPE
	OBJECTS {
		powerMainsA1Alarm}
	STATUS  current
	DESCRIPTION ""
	::= { coolTrap 118 }


powerMainsBNormal NOTIFICATION-TYPE
	OBJECTS {
		powerMainsB1Norm}
	STATUS  current
	DESCRIPTION ""
	::= { coolTrap 119 }


powerMainsBNotNormal NOTIFICATION-TYPE
	OBJECTS {
		powerMainsB1Alarm}
	STATUS  current
	DESCRIPTION ""
	::= { coolTrap 120 }

coolTrapGroup NOTIFICATION-GROUP
	NOTIFICATIONS {
		fan1Normal,
		fan1NotNormal,
		fan2Normal,
		fan2NotNormal,
		fan3Normal,
		fan3NotNormal,
		fan4Normal,
		fan4NotNormal,
		waterNormal,
		waterNotNormal,
		smokeNormal,
		smokeNotNormal,
		mainsANormal,
		mainsANotNormal,
		mainsBNormal,
		mainsBNotNormal,
		smokePreAlarmNormal,
		smokePreAlarmNotNormal,
		smokeMainAlarmNormal,
		smokeMainAlarmNotNormal,
		smokeDefectNormal,
		smokeDefectNotNormal,
		smokeExtinguishedNormal,
		smokeExtinguishedNotNormal,
		doorLeftFrontNormal,
		doorLeftFrontNotNormal,
		doorLeftRearNormal,
		doorLeftRearNotNormal,
		doorRightFrontNormal,
		doorRightFrontNotNormal,
		doorRightRearNormal,
		doorRightRearNotNormal,
		doorCfrontNormal,
		doorCfrontNotNormal,
		doorCrearNormal,
		doorCrearNotNormal,
		spare1Normal,
		spare1NotNormal,
		spare2Normal,
		spare2NotNormal,
		out1Normal,
		out1NotNormal,
		out2Normal,
		out2NotNormal,
		out3Normal,
		out3NotNormal,
		out4Normal,
		out4NotNormal,
		temp1UpperWarnNormal,
		temp1UpperWarnNotNormal,
		temp1UpperAlarmNormal,
		temp1UpperAlarmNotNormal,
		temp2UpperWarnNormal,
		temp2UpperWarnNotNormal,
		temp2UpperAlarmNormal,
		temp2UpperAlarmNotNormal,
		temp3UpperWarnNormal,
		temp3UpperWarnNotNormal,
		temp3UpperAlarmNormal,
		temp3UpperAlarmNotNormal,
		temp4UpperWarnNormal,
		temp4UpperWarnNotNormal,
		temp4UpperAlarmNormal,
		temp4UpperAlarmNotNormal,
		temp5UpperWarnNormal,
		temp5UpperWarnNotNormal,
		temp5UpperAlarmNormal,
		temp5UpperAlarmNotNormal,
		temp6UpperWarnNormal,
		temp6UpperWarnNotNormal,
		temp6UpperAlarmNormal,
		temp6UpperAlarmNotNormal,
		temp1LowAlarmNormal,
		temp1LowAlarmNotNormal,
		temp2LowAlarmNormal,
		temp2LowAlarmNotNormal,
		humidityUpperAlarmNormal,
		humidityUpperAlarmNotNormal,
		humidityLowAlarmNormal,
		humidityLowAlarmNotNormal,
		coldwaterLowAlarmNormal,
		coldwaterLowAlarmNotNormal,
		coldwaterUpperAlarmNormal,
		coldwaterUpperAlarmNotNormal,
		warmwaterLowAlarmNormal,
		warmwaterLowAlarmNotNormal,
		warmwaterUpperAlarmNormal,
		warmwaterUpperAlarmNotNormal,
		temp2DoorOpenNormal,
		temp2DoorOpenNotNormal,
		temp2ServerOFFNormal,
		temp2ServerOFFNotNormal,
		in1Normal,
		in1NotNormal,
		in2Normal,
		in2NotNormal,
		in3Normal,
		in3NotNormal,
		in4Normal,
		in4NotNormal,
		currentL1ANormal,
		currentL1ANotNormal,
		currentL2ANormal,
		currentL2ANotNormal,
		currentL3ANormal,
		currentL3ANotNormal,
		currentL1BNormal,
		currentL1BNotNormal,
		currentL2BNormal,
		currentL2BNotNormal,
		currentL3BNormal,
		currentL3BNotNormal,
		voltageMainsANormal,
		voltageMainsANotNormal,
		voltageMainsBNormal,
		voltageMainsBNotNormal,
		powerMainsANormal,
		powerMainsANotNormal,
		powerMainsBNormal,
		powerMainsBNotNormal }
	STATUS  current
	DESCRIPTION ""
	::= { coolTrap 121 }

coolInput OBJECT IDENTIFIER 	::= { coolControl 6 }

inputNames OBJECT IDENTIFIER 	::= { coolInput 1 }

in1Name OBJECT-TYPE
	SYNTAX  DisplayString
	MAX-ACCESS read-write
	STATUS  current
	DESCRIPTION
		"The name of input 1"
	::= { inputNames 1 }


in2Name OBJECT-TYPE
	SYNTAX  DisplayString
	MAX-ACCESS read-write
	STATUS  current
	DESCRIPTION
		"The name of input 2"
	::= { inputNames 2 }


in3Name OBJECT-TYPE
	SYNTAX  DisplayString
	MAX-ACCESS read-write
	STATUS  current
	DESCRIPTION
		"The name of input 3"
	::= { inputNames 3 }


in4Name OBJECT-TYPE
	SYNTAX  DisplayString
	MAX-ACCESS read-write
	STATUS  current
	DESCRIPTION
		"The name of input 4"
	::= { inputNames 4 }


inputStates OBJECT IDENTIFIER 	::= { coolInput 2 }

in1State OBJECT-TYPE
	SYNTAX  INTEGER (0..1)
	MAX-ACCESS read-only
	STATUS  current
	DESCRIPTION
		"Current state of input 1, '1' is enabled, '0' is not enabled."
	::= { inputStates 1 }


in2State OBJECT-TYPE
	SYNTAX  INTEGER (0..1)
	MAX-ACCESS read-only
	STATUS  current
	DESCRIPTION
		"Current state of output 2, '1' is enabled, '0' is not enabled."
	::= { inputStates 2 }


in3State OBJECT-TYPE
	SYNTAX  INTEGER (0..1)
	MAX-ACCESS read-only
	STATUS  current
	DESCRIPTION
		"Current state of output 3, '1' is enabled, '0' is not enabled."
	::= { inputStates 3 }


in4State OBJECT-TYPE
	SYNTAX  INTEGER (0..1)
	MAX-ACCESS read-only
	STATUS  current
	DESCRIPTION
		"Current state of output 4, '1' is enabled, '0' is not enabled."
	::= { inputStates 4 }


inputTraps OBJECT IDENTIFIER 	::= { coolInput 3 }

in1Trap OBJECT-TYPE
	SYNTAX  INTEGER (0..1)
	MAX-ACCESS read-write
	STATUS  current
	DESCRIPTION
		"Set to '0' for trap disabled, '1' for enabled"
	::= { inputTraps 1 }


in2Trap OBJECT-TYPE
	SYNTAX  INTEGER (0..1)
	MAX-ACCESS read-write
	STATUS  current
	DESCRIPTION
		"Set to '0' for trap disabled, '1' for enabled"
	::= { inputTraps 2 }


in3Trap OBJECT-TYPE
	SYNTAX  INTEGER (0..1)
	MAX-ACCESS read-write
	STATUS  current
	DESCRIPTION
		"Set to '0' for trap disabled, '1' for enabled"
	::= { inputTraps 3 }


in4Trap OBJECT-TYPE
	SYNTAX  INTEGER (0..1)
	MAX-ACCESS read-write
	STATUS  current
	DESCRIPTION
		"Set to '0' for trap disabled, '1' for enabled"
	::= { inputTraps 4 }


inputTrapRepeat OBJECT IDENTIFIER 	::= { coolInput 4 }

in1TrapRepeat OBJECT-TYPE
	SYNTAX  INTEGER (0..1)
	MAX-ACCESS read-write
	STATUS  current
	DESCRIPTION
		"Set to '0' for no repetition after the first trap is sent, select '1' to '600' in seconds for enable repetition."
	::= { inputTrapRepeat 1 }


in2TrapRepeat OBJECT-TYPE
	SYNTAX  INTEGER (0..1)
	MAX-ACCESS read-write
	STATUS  current
	DESCRIPTION
		"Set to '0' for no repetition after the first trap is sent, select '1' to '600' in seconds for enable repetition."
	::= { inputTrapRepeat 2 }


in3TrapRepeat OBJECT-TYPE
	SYNTAX  INTEGER (0..1)
	MAX-ACCESS read-write
	STATUS  current
	DESCRIPTION
		"Set to '0' for no repetition after the first trap is sent, select '1' to '600' in seconds for enable repetition."
	::= { inputTrapRepeat 3 }


in4TrapRepeat OBJECT-TYPE
	SYNTAX  INTEGER (0..1)
	MAX-ACCESS read-write
	STATUS  current
	DESCRIPTION
		"Set to '0' for no repetition after the first trap is sent, select '1' to '600' in seconds for enable repetition."
	::= { inputTrapRepeat 4 }


coolTrapMsg OBJECT IDENTIFIER 	::= { coolControl 7 }

coolTrapMsgs OBJECT IDENTIFIER 	::= { coolTrapMsg 1 }

fan1Norm OBJECT-TYPE
	SYNTAX  OBJECT IDENTIFIER
	MAX-ACCESS read-only
	STATUS  current
	DESCRIPTION ""
	::= { coolTrapMsgs 1 }


fan1Alarm OBJECT-TYPE
	SYNTAX  OBJECT IDENTIFIER
	MAX-ACCESS read-only
	STATUS  current
	DESCRIPTION ""
	::= { coolTrapMsgs 2 }


fan2Norm OBJECT-TYPE
	SYNTAX  OBJECT IDENTIFIER
	MAX-ACCESS read-only
	STATUS  current
	DESCRIPTION ""
	::= { coolTrapMsgs 3 }


fan2Alarm OBJECT-TYPE
	SYNTAX  OBJECT IDENTIFIER
	MAX-ACCESS read-only
	STATUS  current
	DESCRIPTION ""
	::= { coolTrapMsgs 4 }


fan3Norm OBJECT-TYPE
	SYNTAX  OBJECT IDENTIFIER
	MAX-ACCESS read-only
	STATUS  current
	DESCRIPTION ""
	::= { coolTrapMsgs 5 }


fan3Alarm OBJECT-TYPE
	SYNTAX  OBJECT IDENTIFIER
	MAX-ACCESS read-only
	STATUS  current
	DESCRIPTION ""
	::= { coolTrapMsgs 6 }


fan4Norm OBJECT-TYPE
	SYNTAX  OBJECT IDENTIFIER
	MAX-ACCESS read-only
	STATUS  current
	DESCRIPTION ""
	::= { coolTrapMsgs 7 }


fan4Alarm OBJECT-TYPE
	SYNTAX  OBJECT IDENTIFIER
	MAX-ACCESS read-only
	STATUS  current
	DESCRIPTION ""
	::= { coolTrapMsgs 8 }


waterNorm OBJECT-TYPE
	SYNTAX  OBJECT IDENTIFIER
	MAX-ACCESS read-only
	STATUS  current
	DESCRIPTION ""
	::= { coolTrapMsgs 9 }


waterAlarm OBJECT-TYPE
	SYNTAX  OBJECT IDENTIFIER
	MAX-ACCESS read-only
	STATUS  current
	DESCRIPTION ""
	::= { coolTrapMsgs 10 }


smokeNorm OBJECT-TYPE
	SYNTAX  OBJECT IDENTIFIER
	MAX-ACCESS read-only
	STATUS  current
	DESCRIPTION ""
	::= { coolTrapMsgs 11 }


smokeAlarm OBJECT-TYPE
	SYNTAX  OBJECT IDENTIFIER
	MAX-ACCESS read-only
	STATUS  current
	DESCRIPTION ""
	::= { coolTrapMsgs 12 }


mainsANorm OBJECT-TYPE
	SYNTAX  OBJECT IDENTIFIER
	MAX-ACCESS read-only
	STATUS  current
	DESCRIPTION ""
	::= { coolTrapMsgs 13 }


mainsAAlarm OBJECT-TYPE
	SYNTAX  OBJECT IDENTIFIER
	MAX-ACCESS read-only
	STATUS  current
	DESCRIPTION ""
	::= { coolTrapMsgs 14 }


mainsBNorm OBJECT-TYPE
	SYNTAX  OBJECT IDENTIFIER
	MAX-ACCESS read-only
	STATUS  current
	DESCRIPTION ""
	::= { coolTrapMsgs 15 }


mainsBAlarm OBJECT-TYPE
	SYNTAX  OBJECT IDENTIFIER
	MAX-ACCESS read-only
	STATUS  current
	DESCRIPTION ""
	::= { coolTrapMsgs 16 }


smokePreAlarm1Norm OBJECT-TYPE
	SYNTAX  OBJECT IDENTIFIER
	MAX-ACCESS read-only
	STATUS  current
	DESCRIPTION ""
	::= { coolTrapMsgs 17 }


smokePreAlarm1Alarm OBJECT-TYPE
	SYNTAX  OBJECT IDENTIFIER
	MAX-ACCESS read-only
	STATUS  current
	DESCRIPTION ""
	::= { coolTrapMsgs 18 }


smokeMainAlarm1Norm OBJECT-TYPE
	SYNTAX  OBJECT IDENTIFIER
	MAX-ACCESS read-only
	STATUS  current
	DESCRIPTION ""
	::= { coolTrapMsgs 19 }


smokeMainAlarm1Alarm OBJECT-TYPE
	SYNTAX  OBJECT IDENTIFIER
	MAX-ACCESS read-only
	STATUS  current
	DESCRIPTION ""
	::= { coolTrapMsgs 20 }


smokeDefectNorm OBJECT-TYPE
	SYNTAX  OBJECT IDENTIFIER
	MAX-ACCESS read-only
	STATUS  current
	DESCRIPTION ""
	::= { coolTrapMsgs 21 }


smokeDefectAlarm OBJECT-TYPE
	SYNTAX  OBJECT IDENTIFIER
	MAX-ACCESS read-only
	STATUS  current
	DESCRIPTION ""
	::= { coolTrapMsgs 22 }


smokeExtinguishedNorm OBJECT-TYPE
	SYNTAX  OBJECT IDENTIFIER
	MAX-ACCESS read-only
	STATUS  current
	DESCRIPTION ""
	::= { coolTrapMsgs 23 }


smokeExtinguishedAlarm OBJECT-TYPE
	SYNTAX  OBJECT IDENTIFIER
	MAX-ACCESS read-only
	STATUS  current
	DESCRIPTION ""
	::= { coolTrapMsgs 24 }


doorLeftFrontNorm OBJECT-TYPE
	SYNTAX  OBJECT IDENTIFIER
	MAX-ACCESS read-only
	STATUS  current
	DESCRIPTION ""
	::= { coolTrapMsgs 25 }


doorLeftFrontAlarm OBJECT-TYPE
	SYNTAX  OBJECT IDENTIFIER
	MAX-ACCESS read-only
	STATUS  current
	DESCRIPTION ""
	::= { coolTrapMsgs 26 }


doorLeftRearNorm OBJECT-TYPE
	SYNTAX  OBJECT IDENTIFIER
	MAX-ACCESS read-only
	STATUS  current
	DESCRIPTION ""
	::= { coolTrapMsgs 27 }


doorLeftRearAlarm OBJECT-TYPE
	SYNTAX  OBJECT IDENTIFIER
	MAX-ACCESS read-only
	STATUS  current
	DESCRIPTION ""
	::= { coolTrapMsgs 28 }


doorRightFrontNorm OBJECT-TYPE
	SYNTAX  OBJECT IDENTIFIER
	MAX-ACCESS read-only
	STATUS  current
	DESCRIPTION ""
	::= { coolTrapMsgs 29 }


doorRightFrontAlarm OBJECT-TYPE
	SYNTAX  OBJECT IDENTIFIER
	MAX-ACCESS read-only
	STATUS  current
	DESCRIPTION ""
	::= { coolTrapMsgs 30 }


doorRightRearNorm OBJECT-TYPE
	SYNTAX  OBJECT IDENTIFIER
	MAX-ACCESS read-only
	STATUS  current
	DESCRIPTION ""
	::= { coolTrapMsgs 31 }


doorRightRearAlarm OBJECT-TYPE
	SYNTAX  OBJECT IDENTIFIER
	MAX-ACCESS read-only
	STATUS  current
	DESCRIPTION ""
	::= { coolTrapMsgs 32 }


doorCfrontNorm OBJECT-TYPE
	SYNTAX  OBJECT IDENTIFIER
	MAX-ACCESS read-only
	STATUS  current
	DESCRIPTION ""
	::= { coolTrapMsgs 33 }


doorCfrontAlarm OBJECT-TYPE
	SYNTAX  OBJECT IDENTIFIER
	MAX-ACCESS read-only
	STATUS  current
	DESCRIPTION ""
	::= { coolTrapMsgs 34 }


doorCrearNorm OBJECT-TYPE
	SYNTAX  OBJECT IDENTIFIER
	MAX-ACCESS read-only
	STATUS  current
	DESCRIPTION ""
	::= { coolTrapMsgs 35 }


doorCrearAlarm OBJECT-TYPE
	SYNTAX  OBJECT IDENTIFIER
	MAX-ACCESS read-only
	STATUS  current
	DESCRIPTION ""
	::= { coolTrapMsgs 36 }


smokePreAlarm2Norm OBJECT-TYPE
	SYNTAX  OBJECT IDENTIFIER
	MAX-ACCESS read-only
	STATUS  current
	DESCRIPTION ""
	::= { coolTrapMsgs 37 }


smokePreAlarm2Alarm OBJECT-TYPE
	SYNTAX  OBJECT IDENTIFIER
	MAX-ACCESS read-only
	STATUS  current
	DESCRIPTION ""
	::= { coolTrapMsgs 38 }


smokeMainAlarm2Norm OBJECT-TYPE
	SYNTAX  OBJECT IDENTIFIER
	MAX-ACCESS read-only
	STATUS  current
	DESCRIPTION ""
	::= { coolTrapMsgs 39 }


smokeMainAlarm2Alarm OBJECT-TYPE
	SYNTAX  OBJECT IDENTIFIER
	MAX-ACCESS read-only
	STATUS  current
	DESCRIPTION ""
	::= { coolTrapMsgs 40 }


out1Norm OBJECT-TYPE
	SYNTAX  OBJECT IDENTIFIER
	MAX-ACCESS read-only
	STATUS  current
	DESCRIPTION ""
	::= { coolTrapMsgs 41 }


out1NotNorm OBJECT-TYPE
	SYNTAX  OBJECT IDENTIFIER
	MAX-ACCESS read-only
	STATUS  current
	DESCRIPTION ""
	::= { coolTrapMsgs 42 }


out2Norm OBJECT-TYPE
	SYNTAX  OBJECT IDENTIFIER
	MAX-ACCESS read-only
	STATUS  current
	DESCRIPTION ""
	::= { coolTrapMsgs 43 }


out2NotNorm OBJECT-TYPE
	SYNTAX  OBJECT IDENTIFIER
	MAX-ACCESS read-only
	STATUS  current
	DESCRIPTION ""
	::= { coolTrapMsgs 44 }


out3Norm OBJECT-TYPE
	SYNTAX  OBJECT IDENTIFIER
	MAX-ACCESS read-only
	STATUS  current
	DESCRIPTION ""
	::= { coolTrapMsgs 45 }


out3NotNorm OBJECT-TYPE
	SYNTAX  OBJECT IDENTIFIER
	MAX-ACCESS read-only
	STATUS  current
	DESCRIPTION ""
	::= { coolTrapMsgs 46 }


out4Norm OBJECT-TYPE
	SYNTAX  OBJECT IDENTIFIER
	MAX-ACCESS read-only
	STATUS  current
	DESCRIPTION ""
	::= { coolTrapMsgs 47 }


out4NotNorm OBJECT-TYPE
	SYNTAX  OBJECT IDENTIFIER
	MAX-ACCESS read-only
	STATUS  current
	DESCRIPTION ""
	::= { coolTrapMsgs 48 }


temp1UpperNoWarning OBJECT-TYPE
	SYNTAX  OBJECT IDENTIFIER
	MAX-ACCESS read-only
	STATUS  current
	DESCRIPTION ""
	::= { coolTrapMsgs 49 }


temp1UpperWarning OBJECT-TYPE
	SYNTAX  OBJECT IDENTIFIER
	MAX-ACCESS read-only
	STATUS  current
	DESCRIPTION ""
	::= { coolTrapMsgs 50 }


temp1UpperNoAlarm OBJECT-TYPE
	SYNTAX  OBJECT IDENTIFIER
	MAX-ACCESS read-only
	STATUS  current
	DESCRIPTION ""
	::= { coolTrapMsgs 51 }


temp1UpperAlarm OBJECT-TYPE
	SYNTAX  OBJECT IDENTIFIER
	MAX-ACCESS read-only
	STATUS  current
	DESCRIPTION ""
	::= { coolTrapMsgs 52 }


temp2UpperNoWarning OBJECT-TYPE
	SYNTAX  OBJECT IDENTIFIER
	MAX-ACCESS read-only
	STATUS  current
	DESCRIPTION ""
	::= { coolTrapMsgs 53 }


temp2UpperWarning OBJECT-TYPE
	SYNTAX  OBJECT IDENTIFIER
	MAX-ACCESS read-only
	STATUS  current
	DESCRIPTION ""
	::= { coolTrapMsgs 54 }


temp2UpperNoAlarm OBJECT-TYPE
	SYNTAX  OBJECT IDENTIFIER
	MAX-ACCESS read-only
	STATUS  current
	DESCRIPTION ""
	::= { coolTrapMsgs 55 }


temp2UpperAlarm OBJECT-TYPE
	SYNTAX  OBJECT IDENTIFIER
	MAX-ACCESS read-only
	STATUS  current
	DESCRIPTION ""
	::= { coolTrapMsgs 56 }


temp3UpperNoWarning OBJECT-TYPE
	SYNTAX  OBJECT IDENTIFIER
	MAX-ACCESS read-only
	STATUS  current
	DESCRIPTION ""
	::= { coolTrapMsgs 57 }


temp3UpperWarning OBJECT-TYPE
	SYNTAX  OBJECT IDENTIFIER
	MAX-ACCESS read-only
	STATUS  current
	DESCRIPTION ""
	::= { coolTrapMsgs 58 }


temp3UpperNoAlarm OBJECT-TYPE
	SYNTAX  OBJECT IDENTIFIER
	MAX-ACCESS read-only
	STATUS  current
	DESCRIPTION ""
	::= { coolTrapMsgs 59 }


temp3UpperAlarm OBJECT-TYPE
	SYNTAX  OBJECT IDENTIFIER
	MAX-ACCESS read-only
	STATUS  current
	DESCRIPTION ""
	::= { coolTrapMsgs 60 }


temp4UpperNoWarning OBJECT-TYPE
	SYNTAX  OBJECT IDENTIFIER
	MAX-ACCESS read-only
	STATUS  current
	DESCRIPTION ""
	::= { coolTrapMsgs 61 }


temp4UpperWarning OBJECT-TYPE
	SYNTAX  OBJECT IDENTIFIER
	MAX-ACCESS read-only
	STATUS  current
	DESCRIPTION ""
	::= { coolTrapMsgs 62 }


temp4UpperNoAlarm OBJECT-TYPE
	SYNTAX  OBJECT IDENTIFIER
	MAX-ACCESS read-only
	STATUS  current
	DESCRIPTION ""
	::= { coolTrapMsgs 63 }


temp4UpperAlarm OBJECT-TYPE
	SYNTAX  OBJECT IDENTIFIER
	MAX-ACCESS read-only
	STATUS  current
	DESCRIPTION ""
	::= { coolTrapMsgs 64 }


temp5UpperNoWarning OBJECT-TYPE
	SYNTAX  OBJECT IDENTIFIER
	MAX-ACCESS read-only
	STATUS  current
	DESCRIPTION ""
	::= { coolTrapMsgs 65 }


temp5UpperWarning OBJECT-TYPE
	SYNTAX  OBJECT IDENTIFIER
	MAX-ACCESS read-only
	STATUS  current
	DESCRIPTION ""
	::= { coolTrapMsgs 66 }


temp5UpperNoAlarm OBJECT-TYPE
	SYNTAX  OBJECT IDENTIFIER
	MAX-ACCESS read-only
	STATUS  current
	DESCRIPTION ""
	::= { coolTrapMsgs 67 }


temp5UpperAlarm OBJECT-TYPE
	SYNTAX  OBJECT IDENTIFIER
	MAX-ACCESS read-only
	STATUS  current
	DESCRIPTION ""
	::= { coolTrapMsgs 68 }


temp6UpperNoWarning OBJECT-TYPE
	SYNTAX  OBJECT IDENTIFIER
	MAX-ACCESS read-only
	STATUS  current
	DESCRIPTION ""
	::= { coolTrapMsgs 69 }


temp6UpperWarning OBJECT-TYPE
	SYNTAX  OBJECT IDENTIFIER
	MAX-ACCESS read-only
	STATUS  current
	DESCRIPTION ""
	::= { coolTrapMsgs 70 }


temp6UpperNoAlarm OBJECT-TYPE
	SYNTAX  OBJECT IDENTIFIER
	MAX-ACCESS read-only
	STATUS  current
	DESCRIPTION ""
	::= { coolTrapMsgs 71 }


temp6UpperAlarm OBJECT-TYPE
	SYNTAX  OBJECT IDENTIFIER
	MAX-ACCESS read-only
	STATUS  current
	DESCRIPTION ""
	::= { coolTrapMsgs 72 }


temp1LowNoAlarm OBJECT-TYPE
	SYNTAX  OBJECT IDENTIFIER
	MAX-ACCESS read-only
	STATUS  current
	DESCRIPTION ""
	::= { coolTrapMsgs 73 }


temp1LowAlarm OBJECT-TYPE
	SYNTAX  OBJECT IDENTIFIER
	MAX-ACCESS read-only
	STATUS  current
	DESCRIPTION ""
	::= { coolTrapMsgs 74 }


temp2LowNoAlarm OBJECT-TYPE
	SYNTAX  OBJECT IDENTIFIER
	MAX-ACCESS read-only
	STATUS  current
	DESCRIPTION ""
	::= { coolTrapMsgs 75 }


temp2LowAlarm OBJECT-TYPE
	SYNTAX  OBJECT IDENTIFIER
	MAX-ACCESS read-only
	STATUS  current
	DESCRIPTION ""
	::= { coolTrapMsgs 76 }


humidityUpperNormal OBJECT-TYPE
	SYNTAX  OBJECT IDENTIFIER
	MAX-ACCESS read-only
	STATUS  current
	DESCRIPTION ""
	::= { coolTrapMsgs 77 }


humidityUpperAlarm OBJECT-TYPE
	SYNTAX  OBJECT IDENTIFIER
	MAX-ACCESS read-only
	STATUS  current
	DESCRIPTION ""
	::= { coolTrapMsgs 78 }


humidityLowNormal OBJECT-TYPE
	SYNTAX  OBJECT IDENTIFIER
	MAX-ACCESS read-only
	STATUS  current
	DESCRIPTION ""
	::= { coolTrapMsgs 79 }


humidityLowAlarm OBJECT-TYPE
	SYNTAX  OBJECT IDENTIFIER
	MAX-ACCESS read-only
	STATUS  current
	DESCRIPTION ""
	::= { coolTrapMsgs 80 }


coldwaterLowNormal OBJECT-TYPE
	SYNTAX  OBJECT IDENTIFIER
	MAX-ACCESS read-only
	STATUS  current
	DESCRIPTION ""
	::= { coolTrapMsgs 81 }


coldwaterLowAlarm OBJECT-TYPE
	SYNTAX  OBJECT IDENTIFIER
	MAX-ACCESS read-only
	STATUS  current
	DESCRIPTION ""
	::= { coolTrapMsgs 82 }


coldwaterUpperNormal OBJECT-TYPE
	SYNTAX  OBJECT IDENTIFIER
	MAX-ACCESS read-only
	STATUS  current
	DESCRIPTION ""
	::= { coolTrapMsgs 83 }


coldwaterUpperAlarm OBJECT-TYPE
	SYNTAX  OBJECT IDENTIFIER
	MAX-ACCESS read-only
	STATUS  current
	DESCRIPTION ""
	::= { coolTrapMsgs 84 }


warmwaterLowNormal OBJECT-TYPE
	SYNTAX  OBJECT IDENTIFIER
	MAX-ACCESS read-only
	STATUS  current
	DESCRIPTION ""
	::= { coolTrapMsgs 85 }


warmwaterLowAlarm OBJECT-TYPE
	SYNTAX  OBJECT IDENTIFIER
	MAX-ACCESS read-only
	STATUS  current
	DESCRIPTION ""
	::= { coolTrapMsgs 86 }


warmwaterUpperNormal OBJECT-TYPE
	SYNTAX  OBJECT IDENTIFIER
	MAX-ACCESS read-only
	STATUS  current
	DESCRIPTION ""
	::= { coolTrapMsgs 87 }


warmwaterUpperAlarm OBJECT-TYPE
	SYNTAX  OBJECT IDENTIFIER
	MAX-ACCESS read-only
	STATUS  current
	DESCRIPTION ""
	::= { coolTrapMsgs 88 }


temp2DoorOpenNorm OBJECT-TYPE
	SYNTAX  OBJECT IDENTIFIER
	MAX-ACCESS read-only
	STATUS  current
	DESCRIPTION ""
	::= { coolTrapMsgs 89 }


temp2DoorOpenAlarm OBJECT-TYPE
	SYNTAX  OBJECT IDENTIFIER
	MAX-ACCESS read-only
	STATUS  current
	DESCRIPTION ""
	::= { coolTrapMsgs 90 }


temp2ServerOFFNorm OBJECT-TYPE
	SYNTAX  OBJECT IDENTIFIER
	MAX-ACCESS read-only
	STATUS  current
	DESCRIPTION ""
	::= { coolTrapMsgs 91 }


temp2ServerOFFAlarm OBJECT-TYPE
	SYNTAX  OBJECT IDENTIFIER
	MAX-ACCESS read-only
	STATUS  current
	DESCRIPTION ""
	::= { coolTrapMsgs 92 }


in1Low OBJECT-TYPE
	SYNTAX  OBJECT IDENTIFIER
	MAX-ACCESS read-only
	STATUS  current
	DESCRIPTION ""
	::= { coolTrapMsgs 93 }


in1High OBJECT-TYPE
	SYNTAX  OBJECT IDENTIFIER
	MAX-ACCESS read-only
	STATUS  current
	DESCRIPTION ""
	::= { coolTrapMsgs 94 }


in2Low OBJECT-TYPE
	SYNTAX  OBJECT IDENTIFIER
	MAX-ACCESS read-only
	STATUS  current
	DESCRIPTION ""
	::= { coolTrapMsgs 95 }


in2High OBJECT-TYPE
	SYNTAX  OBJECT IDENTIFIER
	MAX-ACCESS read-only
	STATUS  current
	DESCRIPTION ""
	::= { coolTrapMsgs 96 }


in3Low OBJECT-TYPE
	SYNTAX  OBJECT IDENTIFIER
	MAX-ACCESS read-only
	STATUS  current
	DESCRIPTION ""
	::= { coolTrapMsgs 97 }


in3High OBJECT-TYPE
	SYNTAX  OBJECT IDENTIFIER
	MAX-ACCESS read-only
	STATUS  current
	DESCRIPTION ""
	::= { coolTrapMsgs 98 }


in4Low OBJECT-TYPE
	SYNTAX  OBJECT IDENTIFIER
	MAX-ACCESS read-only
	STATUS  current
	DESCRIPTION ""
	::= { coolTrapMsgs 99 }


in4High OBJECT-TYPE
	SYNTAX  OBJECT IDENTIFIER
	MAX-ACCESS read-only
	STATUS  current
	DESCRIPTION ""
	::= { coolTrapMsgs 100 }


currentRack1ANorm OBJECT-TYPE
	SYNTAX  OBJECT IDENTIFIER
	MAX-ACCESS read-only
	STATUS  current
	DESCRIPTION ""
	::= { coolTrapMsgs 101 }


currentRack1AAlarm OBJECT-TYPE
	SYNTAX  OBJECT IDENTIFIER
	MAX-ACCESS read-only
	STATUS  current
	DESCRIPTION ""
	::= { coolTrapMsgs 102 }


currentRack1BNorm OBJECT-TYPE
	SYNTAX  OBJECT IDENTIFIER
	MAX-ACCESS read-only
	STATUS  current
	DESCRIPTION ""
	::= { coolTrapMsgs 103 }


currentRack1BAlarm OBJECT-TYPE
	SYNTAX  OBJECT IDENTIFIER
	MAX-ACCESS read-only
	STATUS  current
	DESCRIPTION ""
	::= { coolTrapMsgs 104 }


currentRack2ANorm OBJECT-TYPE
	SYNTAX  OBJECT IDENTIFIER
	MAX-ACCESS read-only
	STATUS  current
	DESCRIPTION ""
	::= { coolTrapMsgs 105 }


currentRack2AAlarm OBJECT-TYPE
	SYNTAX  OBJECT IDENTIFIER
	MAX-ACCESS read-only
	STATUS  current
	DESCRIPTION ""
	::= { coolTrapMsgs 106 }


currentRack2BNorm OBJECT-TYPE
	SYNTAX  OBJECT IDENTIFIER
	MAX-ACCESS read-only
	STATUS  current
	DESCRIPTION ""
	::= { coolTrapMsgs 107 }


currentRack2BAlarm OBJECT-TYPE
	SYNTAX  OBJECT IDENTIFIER
	MAX-ACCESS read-only
	STATUS  current
	DESCRIPTION ""
	::= { coolTrapMsgs 108 }


voltageMainsA1Norm OBJECT-TYPE
	SYNTAX  OBJECT IDENTIFIER
	MAX-ACCESS read-only
	STATUS  current
	DESCRIPTION ""
	::= { coolTrapMsgs 109 }


voltageMainsA1Alarm OBJECT-TYPE
	SYNTAX  OBJECT IDENTIFIER
	MAX-ACCESS read-only
	STATUS  current
	DESCRIPTION ""
	::= { coolTrapMsgs 110 }


voltageMainsB1Norm OBJECT-TYPE
	SYNTAX  OBJECT IDENTIFIER
	MAX-ACCESS read-only
	STATUS  current
	DESCRIPTION ""
	::= { coolTrapMsgs 111 }


voltageMainsB1Alarm OBJECT-TYPE
	SYNTAX  OBJECT IDENTIFIER
	MAX-ACCESS read-only
	STATUS  current
	DESCRIPTION ""
	::= { coolTrapMsgs 112 }


voltageMainsA2Norm OBJECT-TYPE
	SYNTAX  OBJECT IDENTIFIER
	MAX-ACCESS read-only
	STATUS  current
	DESCRIPTION ""
	::= { coolTrapMsgs 113 }


voltageMainsA2Alarm OBJECT-TYPE
	SYNTAX  OBJECT IDENTIFIER
	MAX-ACCESS read-only
	STATUS  current
	DESCRIPTION ""
	::= { coolTrapMsgs 114 }


voltageMainsB2Norm OBJECT-TYPE
	SYNTAX  OBJECT IDENTIFIER
	MAX-ACCESS read-only
	STATUS  current
	DESCRIPTION ""
	::= { coolTrapMsgs 115 }


voltageMainsB2Alarm OBJECT-TYPE
	SYNTAX  OBJECT IDENTIFIER
	MAX-ACCESS read-only
	STATUS  current
	DESCRIPTION ""
	::= { coolTrapMsgs 116 }


powerMainsA1Norm OBJECT-TYPE
	SYNTAX  OBJECT IDENTIFIER
	MAX-ACCESS read-only
	STATUS  current
	DESCRIPTION ""
	::= { coolTrapMsgs 117 }


powerMainsA2Norm OBJECT-TYPE
	SYNTAX  OBJECT IDENTIFIER
	MAX-ACCESS read-only
	STATUS  current
	DESCRIPTION ""
	::= { coolTrapMsgs 121 }


powerMainsA2Alarm OBJECT-TYPE
	SYNTAX  OBJECT IDENTIFIER
	MAX-ACCESS read-only
	STATUS  current
	DESCRIPTION ""
	::= { coolTrapMsgs 122 }


powerMainsB2Norm OBJECT-TYPE
	SYNTAX  OBJECT IDENTIFIER
	MAX-ACCESS read-only
	STATUS  current
	DESCRIPTION ""
	::= { coolTrapMsgs 123 }


powerMainsB2Alarm OBJECT-TYPE
	SYNTAX  OBJECT IDENTIFIER
	MAX-ACCESS read-only
	STATUS  current
	DESCRIPTION ""
	::= { coolTrapMsgs 124 }


powerMainsA1Alarm OBJECT-TYPE
	SYNTAX  OBJECT IDENTIFIER
	MAX-ACCESS read-only
	STATUS  current
	DESCRIPTION ""
	::= { coolTrapMsgs 118 }


powerMainsB1Norm OBJECT-TYPE
	SYNTAX  OBJECT IDENTIFIER
	MAX-ACCESS read-only
	STATUS  current
	DESCRIPTION ""
	::= { coolTrapMsgs 119 }


powerMainsB1Alarm OBJECT-TYPE
	SYNTAX  OBJECT IDENTIFIER
	MAX-ACCESS read-only
	STATUS  current
	DESCRIPTION ""
	::= { coolTrapMsgs 120 }



currentL2ANormal NOTIFICATION-TYPE
	OBJECTS {
		currentRack1ANorm}
	STATUS  current
	DESCRIPTION ""
	::= { coolTrap 103 }


currentL3ANormal NOTIFICATION-TYPE
	OBJECTS {
		currentRack1ANorm}
	STATUS  current
	DESCRIPTION ""
	::= { coolTrap 105 }


currentL2ANotNormal NOTIFICATION-TYPE
	OBJECTS {
		currentRack1AAlarm}
	STATUS  current
	DESCRIPTION ""
	::= { coolTrap 104 }


currentL3ANotNormal NOTIFICATION-TYPE
	OBJECTS {
		currentRack1AAlarm}
	STATUS  current
	DESCRIPTION ""
	::= { coolTrap 106 }


currentL1BNormal NOTIFICATION-TYPE
	OBJECTS {
		currentRack1BNorm}
	STATUS  current
	DESCRIPTION ""
	::= { coolTrap 107 }


currentL2BNormal NOTIFICATION-TYPE
	OBJECTS {
		currentRack1BNorm}
	STATUS  current
	DESCRIPTION ""
	::= { coolTrap 109 }


currentL3BNormal NOTIFICATION-TYPE
	OBJECTS {
		currentRack1BNorm}
	STATUS  current
	DESCRIPTION ""
	::= { coolTrap 111 }


currentL1BNotNormal NOTIFICATION-TYPE
	OBJECTS {
		currentRack1BAlarm}
	STATUS  current
	DESCRIPTION ""
	::= { coolTrap 108 }


currentL2BNotNormal NOTIFICATION-TYPE
	OBJECTS {
		currentRack1BAlarm}
	STATUS  current
	DESCRIPTION ""
	::= { coolTrap 110 }


currentL3BNotNormal NOTIFICATION-TYPE
	OBJECTS {
		currentRack1BAlarm}
	STATUS  current
	DESCRIPTION ""
	::= { coolTrap 112 }

temp1Group OBJECT-GROUP
	OBJECTS {
		temp1Name,
		temp1CalibrationOffset,
		temp1Current,
		temp1SettingLevel,
		temp1WarningLevel,
		temp1AlarmLevel }
	STATUS  current
	DESCRIPTION ""
	::= { temp1 7 }

temp2Group OBJECT-GROUP
	OBJECTS {
		temp2Name,
		temp2CalibrationOffset,
		temp2Current,
		temp2SettingLevel,
		temp2WarningLevel,
		temp2AlarmLevel,
		temp2DoorsOpenLevel,
		temp2ServerOFFLevel }
	STATUS  current
	DESCRIPTION ""
	::= { temp2 9 }

temp3Group OBJECT-GROUP
	OBJECTS {
		temp3Name,
		temp3CalibrationOffset,
		temp3Current,
		temp3WarningLevel,
		temp3AlarmLevel }
	STATUS  current
	DESCRIPTION ""
	::= { temp3 6 }

temp4Group OBJECT-GROUP
	OBJECTS {
		temp4Name,
		temp4CalibrationOffset,
		temp4Current,
		temp4WarningLevel,
		temp4AlarmLevel }
	STATUS  current
	DESCRIPTION ""
	::= { temp4 6 }

temp5Group OBJECT-GROUP
	OBJECTS {
		temp5Name,
		temp5CalibrationOffset,
		temp5Current,
		temp5WarningLevel,
		temp5AlarmLevel }
	STATUS  current
	DESCRIPTION ""
	::= { temp5 6 }

temp6Group OBJECT-GROUP
	OBJECTS {
		temp6Name,
		temp6CalibrationOffset,
		temp6Current,
		temp6WarningLevel,
		temp6AlarmLevel }
	STATUS  current
	DESCRIPTION ""
	::= { temp6 6 }

hum1Group OBJECT-GROUP
	OBJECTS {
		hum1Name,
		hum1Current,
		hum1LowAlarmLevel,
		hum1UpperAlarm }
	STATUS  current
	DESCRIPTION ""
	::= { hum1 5 }

tempOutWaterGroup OBJECT-GROUP
	OBJECTS {
		tempOutWaterName,
		tempOutWaterCurrent,
		tempOutWaterLoAlarmLevel,
		tempOutWaterHiAlarmLevel }
	STATUS  current
	DESCRIPTION ""
	::= { tempOutWater 5 }

tempInWaterGroup OBJECT-GROUP
	OBJECTS {
		tempInWaterName,
		tempInWaterCurrent,
		tempInWaterLoAlarmLevel,
		tempInWaterHiAlarmLevel }
	STATUS  current
	DESCRIPTION ""
	::= { tempInWater 5 }

flowWaterGroup OBJECT-GROUP
	OBJECTS {
		flowWaterName,
		flowWaterCurrent }
	STATUS  current
	DESCRIPTION ""
	::= { flowWater 3 }

energyConsumptionMainsA1Group OBJECT-GROUP
	OBJECTS {
		currentL1A1,
		currentL2A1,
		currentL3A1,
		voltageL1A1,
		voltageL2A1,
		voltageL3A1,
		activePowerMainsA1,
		apparentPowerMainsA1,
		reactivePowerMainsA1,
		cosphiA1,
		energyA1 }
	STATUS  current
	DESCRIPTION ""
	::= { energyConsumptionMainsA1 12 }

energyConsumptionMainsB1Group OBJECT-GROUP
	OBJECTS {
		currentL1B1,
		currentL2B1,
		currentL3B1,
		voltageL1B1,
		voltageL2B1,
		voltageL3B1,
		activePowerMainsB1,
		apparentPowerMainsB1,
		reactivePowerMainsB1,
		cosphiB1,
		energyB1 }
	STATUS  current
	DESCRIPTION ""
	::= { energyConsumptionMainsB1 12 }

fanValveValuesGroup OBJECT-GROUP
	OBJECTS {
		fanValveValuesName,
		fanSpeed,
		valvePosition }
	STATUS  current
	DESCRIPTION ""
	::= { fanValveValues 4 }

energyConsumptionMainsA2Group OBJECT-GROUP
	OBJECTS {
		currentL1A2,
		currentL2A2,
		currentL3A2,
		voltageL1A2,
		voltageL2A2,
		voltageL3A2,
		activePowerMainsA2,
		apparentPowerMainsA2,
		reactivePowerMainsA2,
		cosphiA2,
		energyA2 }
	STATUS  current
	DESCRIPTION ""
	::= { energyConsumptionMainsA2 12 }

energyConsumptionMainsB2Group OBJECT-GROUP
	OBJECTS {
		currentL1B2,
		currentL2B2,
		currentL3B2,
		voltageL1B2,
		voltageL2B2,
		voltageL3B2,
		activePowerMainsB2,
		apparentPowerMainsB2,
		reactivePowerMainsB2,
		cosphiB2,
		energyB2 }
	STATUS  current
	DESCRIPTION ""
	::= { energyConsumptionMainsB2 12 }

contactBasisNamesGroup OBJECT-GROUP
	OBJECTS {
		fan1Name,
		fan2Name,
		fan3Name,
		fan4Name,
		waterName,
		smokeName,
		mainsAName,
		mainsBName }
	STATUS  current
	DESCRIPTION ""
	::= { contactBasisNames 9 }

contactSmokeExtingNamesGroup OBJECT-GROUP
	OBJECTS {
		smokePreAlarm1Name,
		smokeMainAlarm1Name,
		smokeDefectName,
		smokeExtinguishedName,
		smokePreAlarm2Name,
		smokeMainAlarm2Name }
	STATUS  current
	DESCRIPTION ""
	::= { contactSmokeExtingNames 7 }

contactDoorNamesGroup OBJECT-GROUP
	OBJECTS {
		doorLeftFrontName,
		doorLeftRearName,
		doorRightFrontName,
		doorRightRearName,
		doorCoolFrontName,
		doorCoolRearName }
	STATUS  current
	DESCRIPTION ""
	::= { contactDoorNames 7 }

contactBasisCurrentStatesGroup OBJECT-GROUP
	OBJECTS {
		fan1CurrentState,
		fan2CurrentState,
		fan3CurrentState,
		fan4CurrentState,
		waterCurrentState,
		smokeCurrentState,
		mainsACurrentState,
		mainsBCurrentState }
	STATUS  current
	DESCRIPTION ""
	::= { contactBasisCurrentStates 9 }

contactSmokeExtingCurrentStatesGroup OBJECT-GROUP
	OBJECTS {
		smokePreAlarm1CurrentState,
		smokeMainAlarm1CurrentState,
		smokeDefectCurrentState,
		smokeExtinguishedCurrentState,
		smokePreAlarm2CurrentState,
		smokeMainAlarm2CurrentState }
	STATUS  current
	DESCRIPTION ""
	::= { contactSmokeExtingCurrentStates 7 }

contactDoorCurrentStatesGroup OBJECT-GROUP
	OBJECTS {
		doorLeftFrontCurrentState,
		doorLeftRearCurrentState,
		doorRightFrontCurrentState,
		doorRightRearCurrentState,
		doorCoolFrontCurrentState,
		doorCoolRearCurrentState }
	STATUS  current
	DESCRIPTION ""
	::= { contactDoorCurrentStates 7 }

contactBasisTrapsGroup OBJECT-GROUP
	OBJECTS {
		fan1Trap,
		fan2Trap,
		fan3Trap,
		fan4Trap,
		waterTrap,
		smokeTrap,
		mainsATrap,
		mainsBTrap }
	STATUS  current
	DESCRIPTION ""
	::= { contactBasisTraps 9 }

contactSmokeExtingTrapsGroup OBJECT-GROUP
	OBJECTS {
		smokePreAlarm1Trap,
		smokeMainAlarm1Trap,
		smokeDefectTrap,
		smokeExtinguishedTrap,
		smokePreAlarm2Trap,
		smokeMainAlarm2Trap }
	STATUS  current
	DESCRIPTION ""
	::= { contactSmokeExtingTraps 7 }

contactDoorTrapsGroup OBJECT-GROUP
	OBJECTS {
		doorLeftFrontTrap,
		doorLeftRearTrap,
		doorRightFrontTrap,
		doorRightRearTrap,
		doorCoolFrontTrap,
		doorCoolRearTrap }
	STATUS  current
	DESCRIPTION ""
	::= { contactDoorTraps 7 }

contactBasisTrapRepeatGroup OBJECT-GROUP
	OBJECTS {
		fan1TrapRepeat,
		fan2TrapRepeat,
		fan3TrapRepeat,
		fan4TrapRepeat,
		waterTrapRepeat,
		smokeTrapRepeat,
		mainsATrapRepeat,
		mainsBTrapRepeat }
	STATUS  current
	DESCRIPTION ""
	::= { contactBasisTrapRepeat 9 }

contactSmokeExtingTrapRepeatGroup OBJECT-GROUP
	OBJECTS {
		smokePreAlarm1TrapRepeat,
		smokeMainAlarm1TrapRepeat,
		smokeDefectTrapRepeat,
		smokeExtinguishedTrapRepeat,
		smokePreAlarm2TrapRepeat,
		smokeMainAlarm2TrapRepeat }
	STATUS  current
	DESCRIPTION ""
	::= { contactSmokeExtingTrapRepeat 7 }

contactDoorTrapRepeatGroup OBJECT-GROUP
	OBJECTS {
		doorLeftFrontTrapRepeat,
		doorLeftRearTrapRepeat,
		doorRightFrontTrapRepeat,
		doorRightRearTrapRepeat,
		doorCoolFrontTrapRepeat,
		doorCoolRearTrapRepeat }
	STATUS  current
	DESCRIPTION ""
	::= { contactDoorTrapRepeat 7 }

outputEnablesGroup OBJECT-GROUP
	OBJECTS {
		out1Enable,
		out2Enable,
		out3Enable,
		out4Enable }
	STATUS  current
	DESCRIPTION ""
	::= { outputEnables 5 }

outputNamesGroup OBJECT-GROUP
	OBJECTS {
		out1Name,
		out2Name,
		out3Name,
		out4Name }
	STATUS  current
	DESCRIPTION ""
	::= { outputNames 5 }

outputStatesGroup OBJECT-GROUP
	OBJECTS {
		out1State,
		out2State,
		out3State,
		out4State }
	STATUS  current
	DESCRIPTION ""
	::= { outputStates 5 }

outputTrapsGroup OBJECT-GROUP
	OBJECTS {
		out1Trap,
		out2Trap,
		out3Trap,
		out4Trap }
	STATUS  current
	DESCRIPTION ""
	::= { outputTraps 5 }

outputTrapRepeatGroup OBJECT-GROUP
	OBJECTS {
		out1TrapRepeat,
		out2TrapRepeat,
		out3TrapRepeat,
		out4TrapRepeat }
	STATUS  current
	DESCRIPTION ""
	::= { outputTrapRepeat 5 }

inputNamesGroup OBJECT-GROUP
	OBJECTS {
		in1Name,
		in2Name,
		in3Name,
		in4Name }
	STATUS  current
	DESCRIPTION ""
	::= { inputNames 5 }

inputStatesGroup OBJECT-GROUP
	OBJECTS {
		in1State,
		in2State,
		in3State,
		in4State }
	STATUS  current
	DESCRIPTION ""
	::= { inputStates 5 }

inputTrapsGroup OBJECT-GROUP
	OBJECTS {
		in1Trap,
		in2Trap,
		in3Trap,
		in4Trap }
	STATUS  current
	DESCRIPTION ""
	::= { inputTraps 5 }

inputTrapRepeatGroup OBJECT-GROUP
	OBJECTS {
		in1TrapRepeat,
		in2TrapRepeat,
		in3TrapRepeat,
		in4TrapRepeat }
	STATUS  current
	DESCRIPTION ""
	::= { inputTrapRepeat 5 }

cooltrapMsgsGroup OBJECT-GROUP
	OBJECTS {
		fan1Norm,
		fan1Alarm,
		fan2Norm,
		fan2Alarm,
		fan3Norm,
		fan3Alarm,
		fan4Norm,
		fan4Alarm,
		waterNorm,
		waterAlarm,
		smokeNorm,
		smokeAlarm,
		mainsANorm,
		mainsAAlarm,
		mainsBNorm,
		mainsBAlarm,
		smokePreAlarm1Norm,
		smokePreAlarm1Alarm,
		smokeMainAlarm1Norm,
		smokeMainAlarm1Alarm,
		smokeDefectNorm,
		smokeDefectAlarm,
		smokeExtinguishedNorm,
		smokeExtinguishedAlarm,
		doorLeftFrontNorm,
		doorLeftFrontAlarm,
		doorLeftRearNorm,
		doorLeftRearAlarm,
		doorRightFrontNorm,
		doorRightFrontAlarm,
		doorRightRearNorm,
		doorRightRearAlarm,
		doorCfrontNorm,
		doorCfrontAlarm,
		doorCrearNorm,
		doorCrearAlarm,
		smokePreAlarm2Norm,
		smokePreAlarm2Alarm,
		smokeMainAlarm2Norm,
		smokeMainAlarm2Alarm,
		out1Norm,
		out1NotNorm,
		out2Norm,
		out2NotNorm,
		out3Norm,
		out3NotNorm,
		out4Norm,
		out4NotNorm,
		temp1UpperNoWarning,
		temp1UpperWarning,
		temp1UpperNoAlarm,
		temp1UpperAlarm,
		temp2UpperNoWarning,
		temp2UpperWarning,
		temp2UpperNoAlarm,
		temp2UpperAlarm,
		temp3UpperNoWarning,
		temp3UpperWarning,
		temp3UpperNoAlarm,
		temp3UpperAlarm,
		temp4UpperNoWarning,
		temp4UpperWarning,
		temp4UpperNoAlarm,
		temp4UpperAlarm,
		temp5UpperNoWarning,
		temp5UpperWarning,
		temp5UpperNoAlarm,
		temp5UpperAlarm,
		temp6UpperNoWarning,
		temp6UpperWarning,
		temp6UpperNoAlarm,
		temp6UpperAlarm,
		temp1LowNoAlarm,
		temp1LowAlarm,
		temp2LowNoAlarm,
		temp2LowAlarm,
		humidityUpperNormal,
		humidityUpperAlarm,
		humidityLowNormal,
		humidityLowAlarm,
		coldwaterLowNormal,
		coldwaterLowAlarm,
		coldwaterUpperNormal,
		coldwaterUpperAlarm,
		warmwaterLowNormal,
		warmwaterLowAlarm,
		warmwaterUpperNormal,
		warmwaterUpperAlarm,
		temp2DoorOpenNorm,
		temp2DoorOpenAlarm,
		temp2ServerOFFNorm,
		temp2ServerOFFAlarm,
		in1Low,
		in1High,
		in2Low,
		in2High,
		in3Low,
		in3High,
		in4Low,
		in4High,
		currentRack1ANorm,
		currentRack1AAlarm,
		currentRack1BNorm,
		currentRack1BAlarm,
		currentRack2ANorm,
		currentRack2AAlarm,
		currentRack2BNorm,
		currentRack2BAlarm,
		voltageMainsA1Norm,
		voltageMainsA1Alarm,
		voltageMainsB1Norm,
		voltageMainsB1Alarm,
		voltageMainsA2Norm,
		voltageMainsA2Alarm,
		voltageMainsB2Norm,
		voltageMainsB2Alarm,
		powerMainsA1Norm,
		powerMainsA1Alarm,
		powerMainsB1Norm,
		powerMainsB1Alarm,
		powerMainsA2Norm,
		powerMainsA2Alarm,
		powerMainsB2Norm,
		powerMainsB2Alarm }
	STATUS  current
	DESCRIPTION ""
	::= { coolTrapMsgs 125 }

END
