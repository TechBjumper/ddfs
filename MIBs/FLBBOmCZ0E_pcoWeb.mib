--
-- CAREL-flbbomcz0e.MIB
-- MIB generated by CAREL
-- Thursday, 25 June 2009
--

    CAREL-flbbomcz0e-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        flbbomcz0eMIB MODULE-IDENTITY
      		LAST-UPDATED  "200906251541Z"		-- June 25, 2009 at 15:41 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the flbbomcz0e device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { flbbomcz0eMIB 1 }

        -- 1.3.6.1.4.1.9839.2.1.1.1
        dig1 OBJECT-TYPE
                    SYNTAX Integer32 (0..1)
                    UNITS "N/A"
                    MAX-ACCESS read-only
                    STATUS current
                    DESCRIPTION "Digital input number  1"
                    ::= { digitalObjects 1 }

        -- 1.3.6.1.4.1.9839.2.1.1.2
        dig2 OBJECT-TYPE
                    SYNTAX Integer32 (0..1)
                    UNITS "N/A"
                    MAX-ACCESS read-only
                    STATUS current
                    DESCRIPTION "Digital input number  2"
                    ::= { digitalObjects 2 }

        -- 1.3.6.1.4.1.9839.2.1.1.3
        dig3 OBJECT-TYPE
                    SYNTAX Integer32 (0..1)
                    UNITS "N/A"
                    MAX-ACCESS read-only
                    STATUS current
                    DESCRIPTION "Digital input number  3"
                    ::= { digitalObjects 3 }

        -- 1.3.6.1.4.1.9839.2.1.1.4
        dig4 OBJECT-TYPE
                    SYNTAX Integer32 (0..1)
                    UNITS "N/A"
                    MAX-ACCESS read-only
                    STATUS current
                    DESCRIPTION "Digital input number  4"
                    ::= { digitalObjects 4 }

        -- 1.3.6.1.4.1.9839.2.1.1.5
        dig5 OBJECT-TYPE
                    SYNTAX Integer32 (0..1)
                    UNITS "N/A"
                    MAX-ACCESS read-only
                    STATUS current
                    DESCRIPTION "Digital input number  5"
                    ::= { digitalObjects 5 }

        -- 1.3.6.1.4.1.9839.2.1.1.6
        dig6 OBJECT-TYPE
                    SYNTAX Integer32 (0..1)
                    UNITS "N/A"
                    MAX-ACCESS read-only
                    STATUS current
                    DESCRIPTION "Digital input number  6"
                    ::= { digitalObjects 6 }

        -- 1.3.6.1.4.1.9839.2.1.1.7
        dig7 OBJECT-TYPE
                    SYNTAX Integer32 (0..1)
                    UNITS "N/A"
                    MAX-ACCESS read-only
                    STATUS current
                    DESCRIPTION "Digital input number  7"
                    ::= { digitalObjects 7 }

        -- 1.3.6.1.4.1.9839.2.1.1.8
        dig8 OBJECT-TYPE
                    SYNTAX Integer32 (0..1)
                    UNITS "N/A"
                    MAX-ACCESS read-only
                    STATUS current
                    DESCRIPTION "Digital input number  8"
                    ::= { digitalObjects 8 }

        -- 1.3.6.1.4.1.9839.2.1.1.9
        dig9 OBJECT-TYPE
                    SYNTAX Integer32 (0..1)
                    UNITS "N/A"
                    MAX-ACCESS read-only
                    STATUS current
                    DESCRIPTION "Digital input number  9"
                    ::= { digitalObjects 9 }

        -- 1.3.6.1.4.1.9839.2.1.1.10
        dig10 OBJECT-TYPE
                    SYNTAX Integer32 (0..1)
                    UNITS "N/A"
                    MAX-ACCESS read-only
                    STATUS current
                    DESCRIPTION "Digital input number  10"
                    ::= { digitalObjects 10 }

        -- 1.3.6.1.4.1.9839.2.1.1.11
        dig11 OBJECT-TYPE
                    SYNTAX Integer32 (0..1)
                    UNITS "N/A"
                    MAX-ACCESS read-only
                    STATUS current
                    DESCRIPTION "Humidifier water level contact"
                    ::= { digitalObjects 11 }

        -- 1.3.6.1.4.1.9839.2.1.1.12
        dig12 OBJECT-TYPE
                    SYNTAX Integer32 (0..1)
                    UNITS "N/A"
                    MAX-ACCESS read-only
                    STATUS current
                    DESCRIPTION "Digital input number  12"
                    ::= { digitalObjects 12 }

        -- 1.3.6.1.4.1.9839.2.1.1.13
        dig13 OBJECT-TYPE
                    SYNTAX Integer32 (0..1)
                    UNITS "N/A"
                    MAX-ACCESS read-only
                    STATUS current
                    DESCRIPTION "Digital input number  13"
                    ::= { digitalObjects 13 }

        -- 1.3.6.1.4.1.9839.2.1.1.14
        dig14 OBJECT-TYPE
                    SYNTAX Integer32 (0..1)
                    UNITS "N/A"
                    MAX-ACCESS read-only
                    STATUS current
                    DESCRIPTION "Digital input number  14"
                    ::= { digitalObjects 14 }

        -- 1.3.6.1.4.1.9839.2.1.1.15
        dig15 OBJECT-TYPE
                    SYNTAX Integer32 (0..1)
                    UNITS "N/A"
                    MAX-ACCESS read-only
                    STATUS current
                    DESCRIPTION "Digital output number  1"
                    ::= { digitalObjects 15 }

        -- 1.3.6.1.4.1.9839.2.1.1.16
        dig16 OBJECT-TYPE
                    SYNTAX Integer32 (0..1)
                    UNITS "N/A"
                    MAX-ACCESS read-only
                    STATUS current
                    DESCRIPTION "Digital output number  2"
                    ::= { digitalObjects 16 }

        -- 1.3.6.1.4.1.9839.2.1.1.17
        dig17 OBJECT-TYPE
                    SYNTAX Integer32 (0..1)
                    UNITS "N/A"
                    MAX-ACCESS read-only
                    STATUS current
                    DESCRIPTION "Digital output number  3"
                    ::= { digitalObjects 17 }

        -- 1.3.6.1.4.1.9839.2.1.1.18
        dig18 OBJECT-TYPE
                    SYNTAX Integer32 (0..1)
                    UNITS "N/A"
                    MAX-ACCESS read-only
                    STATUS current
                    DESCRIPTION "Digital output number  4"
                    ::= { digitalObjects 18 }

        -- 1.3.6.1.4.1.9839.2.1.1.19
        dig19 OBJECT-TYPE
                    SYNTAX Integer32 (0..1)
                    UNITS "N/A"
                    MAX-ACCESS read-only
                    STATUS current
                    DESCRIPTION "Digital output number  5"
                    ::= { digitalObjects 19 }

        -- 1.3.6.1.4.1.9839.2.1.1.20
        dig20 OBJECT-TYPE
                    SYNTAX Integer32 (0..1)
                    UNITS "N/A"
                    MAX-ACCESS read-only
                    STATUS current
                    DESCRIPTION "Digital output number  6"
                    ::= { digitalObjects 20 }

        -- 1.3.6.1.4.1.9839.2.1.1.21
        dig21 OBJECT-TYPE
                    SYNTAX Integer32 (0..1)
                    UNITS "N/A"
                    MAX-ACCESS read-only
                    STATUS current
                    DESCRIPTION "Digital output number  7"
                    ::= { digitalObjects 21 }

        -- 1.3.6.1.4.1.9839.2.1.1.22
        dig22 OBJECT-TYPE
                    SYNTAX Integer32 (0..1)
                    UNITS "N/A"
                    MAX-ACCESS read-only
                    STATUS current
                    DESCRIPTION "Digital output number  8"
                    ::= { digitalObjects 22 }

        -- 1.3.6.1.4.1.9839.2.1.1.23
        dig23 OBJECT-TYPE
                    SYNTAX Integer32 (0..1)
                    UNITS "N/A"
                    MAX-ACCESS read-only
                    STATUS current
                    DESCRIPTION "Digital output number  9"
                    ::= { digitalObjects 23 }

        -- 1.3.6.1.4.1.9839.2.1.1.24
        dig24 OBJECT-TYPE
                    SYNTAX Integer32 (0..1)
                    UNITS "N/A"
                    MAX-ACCESS read-only
                    STATUS current
                    DESCRIPTION "Digital output number  10"
                    ::= { digitalObjects 24 }

        -- 1.3.6.1.4.1.9839.2.1.1.25
        dig25 OBJECT-TYPE
                    SYNTAX Integer32 (0..1)
                    UNITS "N/A"
                    MAX-ACCESS read-only
                    STATUS current
                    DESCRIPTION "Digital output number  11"
                    ::= { digitalObjects 25 }

        -- 1.3.6.1.4.1.9839.2.1.1.26
        dig26 OBJECT-TYPE
                    SYNTAX Integer32 (0..1)
                    UNITS "N/A"
                    MAX-ACCESS read-only
                    STATUS current
                    DESCRIPTION "Compressor 1 general alarm"
                    ::= { digitalObjects 26 }

        -- 1.3.6.1.4.1.9839.2.1.1.27
        dig27 OBJECT-TYPE
                    SYNTAX Integer32 (0..1)
                    UNITS "N/A"
                    MAX-ACCESS read-only
                    STATUS current
                    DESCRIPTION "Compressor 2 general alarm"
                    ::= { digitalObjects 27 }

        -- 1.3.6.1.4.1.9839.2.1.1.28
        dig28 OBJECT-TYPE
                    SYNTAX Integer32 (0..1)
                    UNITS "N/A"
                    MAX-ACCESS read-only
                    STATUS current
                    DESCRIPTION "Compressor 1 low pressure alarm"
                    ::= { digitalObjects 28 }

        -- 1.3.6.1.4.1.9839.2.1.1.29
        dig29 OBJECT-TYPE
                    SYNTAX Integer32 (0..1)
                    UNITS "N/A"
                    MAX-ACCESS read-only
                    STATUS current
                    DESCRIPTION "Compressor 2 low pressure alarm"
                    ::= { digitalObjects 29 }

        -- 1.3.6.1.4.1.9839.2.1.1.30
        dig30 OBJECT-TYPE
                    SYNTAX Integer32 (0..1)
                    UNITS "N/A"
                    MAX-ACCESS read-only
                    STATUS current
                    DESCRIPTION "Air flow alarm"
                    ::= { digitalObjects 30 }

        -- 1.3.6.1.4.1.9839.2.1.1.31
        dig31 OBJECT-TYPE
                    SYNTAX Integer32 (0..1)
                    UNITS "N/A"
                    MAX-ACCESS read-only
                    STATUS current
                    DESCRIPTION "Fan thermal cut-out alarm"
                    ::= { digitalObjects 31 }

        -- 1.3.6.1.4.1.9839.2.1.1.32
        dig32 OBJECT-TYPE
                    SYNTAX Integer32 (0..1)
                    UNITS "N/A"
                    MAX-ACCESS read-only
                    STATUS current
                    DESCRIPTION "Heater 1 thermal cut-out alarm"
                    ::= { digitalObjects 32 }

        -- 1.3.6.1.4.1.9839.2.1.1.33
        dig33 OBJECT-TYPE
                    SYNTAX Integer32 (0..1)
                    UNITS "N/A"
                    MAX-ACCESS read-only
                    STATUS current
                    DESCRIPTION "Heater 2 thermal cut-out alarm"
                    ::= { digitalObjects 33 }

        -- 1.3.6.1.4.1.9839.2.1.1.34
        dig34 OBJECT-TYPE
                    SYNTAX Integer32 (0..1)
                    UNITS "N/A"
                    MAX-ACCESS read-only
                    STATUS current
                    DESCRIPTION "Fire/smoke alarm"
                    ::= { digitalObjects 34 }

        -- 1.3.6.1.4.1.9839.2.1.1.35
        dig35 OBJECT-TYPE
                    SYNTAX Integer32 (0..1)
                    UNITS "N/A"
                    MAX-ACCESS read-only
                    STATUS current
                    DESCRIPTION "Clogged filter alarm"
                    ::= { digitalObjects 35 }

        -- 1.3.6.1.4.1.9839.2.1.1.36
        dig36 OBJECT-TYPE
                    SYNTAX Integer32 (0..1)
                    UNITS "N/A"
                    MAX-ACCESS read-only
                    STATUS current
                    DESCRIPTION "High ambient temperature alarm"
                    ::= { digitalObjects 36 }

        -- 1.3.6.1.4.1.9839.2.1.1.37
        dig37 OBJECT-TYPE
                    SYNTAX Integer32 (0..1)
                    UNITS "N/A"
                    MAX-ACCESS read-only
                    STATUS current
                    DESCRIPTION "Low ambient temperature alarm"
                    ::= { digitalObjects 37 }

        -- 1.3.6.1.4.1.9839.2.1.1.38
        dig38 OBJECT-TYPE
                    SYNTAX Integer32 (0..1)
                    UNITS "N/A"
                    MAX-ACCESS read-only
                    STATUS current
                    DESCRIPTION "High ambient humidity alarm"
                    ::= { digitalObjects 38 }

        -- 1.3.6.1.4.1.9839.2.1.1.39
        dig39 OBJECT-TYPE
                    SYNTAX Integer32 (0..1)
                    UNITS "N/A"
                    MAX-ACCESS read-only
                    STATUS current
                    DESCRIPTION "Low ambient humidity alarm"
                    ::= { digitalObjects 39 }

        -- 1.3.6.1.4.1.9839.2.1.1.40
        dig40 OBJECT-TYPE
                    SYNTAX Integer32 (0..1)
                    UNITS "N/A"
                    MAX-ACCESS read-only
                    STATUS current
                    DESCRIPTION "Compressor 1 op. hours threshold alarm"
                    ::= { digitalObjects 40 }

        -- 1.3.6.1.4.1.9839.2.1.1.41
        dig41 OBJECT-TYPE
                    SYNTAX Integer32 (0..1)
                    UNITS "N/A"
                    MAX-ACCESS read-only
                    STATUS current
                    DESCRIPTION "Compressor 2 op. hours threshold alarm"
                    ::= { digitalObjects 41 }

        -- 1.3.6.1.4.1.9839.2.1.1.42
        dig42 OBJECT-TYPE
                    SYNTAX Integer32 (0..1)
                    UNITS "N/A"
                    MAX-ACCESS read-only
                    STATUS current
                    DESCRIPTION "Fan op. hours threshold alarm"
                    ::= { digitalObjects 42 }

        -- 1.3.6.1.4.1.9839.2.1.1.43
        dig43 OBJECT-TYPE
                    SYNTAX Integer32 (0..1)
                    UNITS "N/A"
                    MAX-ACCESS read-only
                    STATUS current
                    DESCRIPTION "Ambient temp. probe damage alarm"
                    ::= { digitalObjects 43 }

        -- 1.3.6.1.4.1.9839.2.1.1.44
        dig44 OBJECT-TYPE
                    SYNTAX Integer32 (0..1)
                    UNITS "N/A"
                    MAX-ACCESS read-only
                    STATUS current
                    DESCRIPTION "Recov. temp. probe damage alarm"
                    ::= { digitalObjects 44 }

        -- 1.3.6.1.4.1.9839.2.1.1.45
        dig45 OBJECT-TYPE
                    SYNTAX Integer32 (0..1)
                    UNITS "N/A"
                    MAX-ACCESS read-only
                    STATUS current
                    DESCRIPTION "External temp. probe damage alarm"
                    ::= { digitalObjects 45 }

        -- 1.3.6.1.4.1.9839.2.1.1.46
        dig46 OBJECT-TYPE
                    SYNTAX Integer32 (0..1)
                    UNITS "N/A"
                    MAX-ACCESS read-only
                    STATUS current
                    DESCRIPTION "Delivery temp. probe damage alarm"
                    ::= { digitalObjects 46 }

        -- 1.3.6.1.4.1.9839.2.1.1.47
        dig47 OBJECT-TYPE
                    SYNTAX Integer32 (0..1)
                    UNITS "N/A"
                    MAX-ACCESS read-only
                    STATUS current
                    DESCRIPTION "Ambient humidity probe damage alarm"
                    ::= { digitalObjects 47 }

        -- 1.3.6.1.4.1.9839.2.1.1.48
        dig48 OBJECT-TYPE
                    SYNTAX Integer32 (0..1)
                    UNITS "N/A"
                    MAX-ACCESS read-only
                    STATUS current
                    DESCRIPTION "Pressure probe 1 damage alarm"
                    ::= { digitalObjects 48 }

        -- 1.3.6.1.4.1.9839.2.1.1.49
        dig49 OBJECT-TYPE
                    SYNTAX Integer32 (0..1)
                    UNITS "N/A"
                    MAX-ACCESS read-only
                    STATUS current
                    DESCRIPTION "Pressure probe 2 damage alarm"
                    ::= { digitalObjects 49 }

        -- 1.3.6.1.4.1.9839.2.1.1.50
        dig50 OBJECT-TYPE
                    SYNTAX Integer32 (0..1)
                    UNITS "N/A"
                    MAX-ACCESS read-only
                    STATUS current
                    DESCRIPTION "Condens. temp. probe 1 damage alarm"
                    ::= { digitalObjects 50 }

        -- 1.3.6.1.4.1.9839.2.1.1.51
        dig51 OBJECT-TYPE
                    SYNTAX Integer32 (0..1)
                    UNITS "N/A"
                    MAX-ACCESS read-only
                    STATUS current
                    DESCRIPTION "Condens. temp. probe 2 damage alarm"
                    ::= { digitalObjects 51 }

        -- 1.3.6.1.4.1.9839.2.1.1.52
        dig52 OBJECT-TYPE
                    SYNTAX Integer32 (0..1)
                    UNITS "N/A"
                    MAX-ACCESS read-only
                    STATUS current
                    DESCRIPTION "High humidifier current alarm"
                    ::= { digitalObjects 52 }

        -- 1.3.6.1.4.1.9839.2.1.1.53
        dig53 OBJECT-TYPE
                    SYNTAX Integer32 (0..1)
                    UNITS "N/A"
                    MAX-ACCESS read-only
                    STATUS current
                    DESCRIPTION "Humidifier water low alarm"
                    ::= { digitalObjects 53 }

        -- 1.3.6.1.4.1.9839.2.1.1.54
        dig54 OBJECT-TYPE
                    SYNTAX Integer32 (0..1)
                    UNITS "N/A"
                    MAX-ACCESS read-only
                    STATUS current
                    DESCRIPTION "Humidifier current failure alarm"
                    ::= { digitalObjects 54 }

        -- 1.3.6.1.4.1.9839.2.1.1.55
        dig55 OBJECT-TYPE
                    SYNTAX Integer32 (0..1)
                    UNITS "N/A"
                    MAX-ACCESS read-only
                    STATUS current
                    DESCRIPTION "Clock board damage alarm"
                    ::= { digitalObjects 55 }

        -- 1.3.6.1.4.1.9839.2.1.1.56
        dig56 OBJECT-TYPE
                    SYNTAX Integer32 (0..1)
                    UNITS "N/A"
                    MAX-ACCESS read-only
                    STATUS current
                    DESCRIPTION "Circuit 1 high pressure alarm"
                    ::= { digitalObjects 56 }

        -- 1.3.6.1.4.1.9839.2.1.1.57
        dig57 OBJECT-TYPE
                    SYNTAX Integer32 (0..1)
                    UNITS "N/A"
                    MAX-ACCESS read-only
                    STATUS current
                    DESCRIPTION "Circuit 2 high pressure alarm"
                    ::= { digitalObjects 57 }

        -- 1.3.6.1.4.1.9839.2.1.1.58
        dig58 OBJECT-TYPE
                    SYNTAX Integer32 (0..1)
                    UNITS "N/A"
                    MAX-ACCESS read-only
                    STATUS current
                    DESCRIPTION "Flooding alarm"
                    ::= { digitalObjects 58 }

        -- 1.3.6.1.4.1.9839.2.1.1.59
        dig59 OBJECT-TYPE
                    SYNTAX Integer32 (0..1)
                    UNITS "N/A"
                    MAX-ACCESS read-only
                    STATUS current
                    DESCRIPTION "Auxiliary alarm"
                    ::= { digitalObjects 59 }

        -- 1.3.6.1.4.1.9839.2.1.1.60
        dig60 OBJECT-TYPE
                    SYNTAX Integer32 (0..1)
                    UNITS "N/A"
                    MAX-ACCESS read-only
                    STATUS current
                    DESCRIPTION "Humidifier op. hours threshold alarm"
                    ::= { digitalObjects 60 }

        -- 1.3.6.1.4.1.9839.2.1.1.61
        dig61 OBJECT-TYPE
                    SYNTAX Integer32 (0..1)
                    UNITS "N/A"
                    MAX-ACCESS read-only
                    STATUS current
                    DESCRIPTION "Condens. fan 1 th. cut-out alarm"
                    ::= { digitalObjects 61 }

        -- 1.3.6.1.4.1.9839.2.1.1.62
        dig62 OBJECT-TYPE
                    SYNTAX Integer32 (0..1)
                    UNITS "N/A"
                    MAX-ACCESS read-only
                    STATUS current
                    DESCRIPTION "Condens. fan 2 th. cut-out alarm"
                    ::= { digitalObjects 62 }

        -- 1.3.6.1.4.1.9839.2.1.1.63
        dig63 OBJECT-TYPE
                    SYNTAX Integer32 (0..1)
                    UNITS "N/A"
                    MAX-ACCESS read-only
                    STATUS current
                    DESCRIPTION "Compressor/cooling coil enable with recovery coil"
                    ::= { digitalObjects 63 }

        -- 1.3.6.1.4.1.9839.2.1.1.64
        dig64 OBJECT-TYPE
                    SYNTAX Integer32 (0..1)
                    UNITS "N/A"
                    MAX-ACCESS read-only
                    STATUS current
                    DESCRIPTION "Circuit 1 driver offline alarm"
                    ::= { digitalObjects 64 }

        -- 1.3.6.1.4.1.9839.2.1.1.65
        dig65 OBJECT-TYPE
                    SYNTAX Integer32 (0..1)
                    UNITS "N/A"
                    MAX-ACCESS read-only
                    STATUS current
                    DESCRIPTION "Circuit 2 driver offline alarm"
                    ::= { digitalObjects 65 }

        -- 1.3.6.1.4.1.9839.2.1.1.66
        dig66 OBJECT-TYPE
                    SYNTAX Integer32 (0..1)
                    UNITS "N/A"
                    MAX-ACCESS read-only
                    STATUS current
                    DESCRIPTION "Cylinder 1 maintenance alarm"
                    ::= { digitalObjects 66 }

        -- 1.3.6.1.4.1.9839.2.1.1.67
        dig67 OBJECT-TYPE
                    SYNTAX Integer32 (0..1)
                    UNITS "N/A"
                    MAX-ACCESS read-only
                    STATUS current
                    DESCRIPTION "Cylinder 1 maintenance pre-alarm"
                    ::= { digitalObjects 67 }

        -- 1.3.6.1.4.1.9839.2.1.1.68
        dig68 OBJECT-TYPE
                    SYNTAX Integer32 (0..1)
                    UNITS "N/A"
                    MAX-ACCESS read-only
                    STATUS current
                    DESCRIPTION "High conductivity alarm"
                    ::= { digitalObjects 68 }

        -- 1.3.6.1.4.1.9839.2.1.1.69
        dig69 OBJECT-TYPE
                    SYNTAX Integer32 (0..1)
                    UNITS "N/A"
                    MAX-ACCESS read-only
                    STATUS current
                    DESCRIPTION "High conductivity pre-alarm"
                    ::= { digitalObjects 69 }

        -- 1.3.6.1.4.1.9839.2.1.1.70
        dig70 OBJECT-TYPE
                    SYNTAX Integer32 (0..1)
                    UNITS "N/A"
                    MAX-ACCESS read-only
                    STATUS current
                    DESCRIPTION "Low production alarm"
                    ::= { digitalObjects 70 }

        -- 1.3.6.1.4.1.9839.2.1.1.71
        dig71 OBJECT-TYPE
                    SYNTAX Integer32 (0..1)
                    UNITS "N/A"
                    MAX-ACCESS read-only
                    STATUS current
                    DESCRIPTION "Drain alarm"
                    ::= { digitalObjects 71 }

        -- 1.3.6.1.4.1.9839.2.1.1.72
        dig72 OBJECT-TYPE
                    SYNTAX Integer32 (0..1)
                    UNITS "N/A"
                    MAX-ACCESS read-only
                    STATUS current
                    DESCRIPTION "Cylinder full alarm"
                    ::= { digitalObjects 72 }

        -- 1.3.6.1.4.1.9839.2.1.1.73
        dig73 OBJECT-TYPE
                    SYNTAX Integer32 (0..1)
                    UNITS "N/A"
                    MAX-ACCESS read-only
                    STATUS current
                    DESCRIPTION "Cylinder 1 pre-deterioration"
                    ::= { digitalObjects 73 }

        -- 1.3.6.1.4.1.9839.2.1.1.74
        dig74 OBJECT-TYPE
                    SYNTAX Integer32 (0..1)
                    UNITS "N/A"
                    MAX-ACCESS read-only
                    STATUS current
                    DESCRIPTION "Foam presence alarm"
                    ::= { digitalObjects 74 }

        -- 1.3.6.1.4.1.9839.2.1.1.75
        dig75 OBJECT-TYPE
                    SYNTAX Integer32 (0..1)
                    UNITS "N/A"
                    MAX-ACCESS read-only
                    STATUS current
                    DESCRIPTION "Cylinder deteriorated"
                    ::= { digitalObjects 75 }

        -- 1.3.6.1.4.1.9839.2.1.1.76
        dig76 OBJECT-TYPE
                    SYNTAX Integer32 (0..1)
                    UNITS "N/A"
                    MAX-ACCESS read-only
                    STATUS current
                    DESCRIPTION "Recommended maintenance alarm"
                    ::= { digitalObjects 76 }

        -- 1.3.6.1.4.1.9839.2.1.1.77
        dig77 OBJECT-TYPE
                    SYNTAX Integer32 (0..1)
                    UNITS "N/A"
                    MAX-ACCESS read-only
                    STATUS current
                    DESCRIPTION "Recommended maintenance pre-alarm"
                    ::= { digitalObjects 77 }

        -- 1.3.6.1.4.1.9839.2.1.1.78
        dig78 OBJECT-TYPE
                    SYNTAX Integer32 (0..1)
                    UNITS "N/A"
                    MAX-ACCESS read-write
                    STATUS current
                    DESCRIPTION "External temperature probe enable"
                    ::= { digitalObjects 78 }

        -- 1.3.6.1.4.1.9839.2.1.1.79
        dig79 OBJECT-TYPE
                    SYNTAX Integer32 (0..1)
                    UNITS "N/A"
                    MAX-ACCESS read-write
                    STATUS current
                    DESCRIPTION "Pressure probe 1 enable"
                    ::= { digitalObjects 79 }

        -- 1.3.6.1.4.1.9839.2.1.1.80
        dig80 OBJECT-TYPE
                    SYNTAX Integer32 (0..1)
                    UNITS "N/A"
                    MAX-ACCESS read-write
                    STATUS current
                    DESCRIPTION "Pressure probe 2 enable"
                    ::= { digitalObjects 80 }

        -- 1.3.6.1.4.1.9839.2.1.1.81
        dig81 OBJECT-TYPE
                    SYNTAX Integer32 (0..1)
                    UNITS "N/A"
                    MAX-ACCESS read-write
                    STATUS current
                    DESCRIPTION "Humidity probe enable"
                    ::= { digitalObjects 81 }

        -- 1.3.6.1.4.1.9839.2.1.1.82
        dig82 OBJECT-TYPE
                    SYNTAX Integer32 (0..1)
                    UNITS "N/A"
                    MAX-ACCESS read-write
                    STATUS current
                    DESCRIPTION "Delivery probe enable"
                    ::= { digitalObjects 82 }

        -- 1.3.6.1.4.1.9839.2.1.1.83
        dig83 OBJECT-TYPE
                    SYNTAX Integer32 (0..1)
                    UNITS "N/A"
                    MAX-ACCESS read-write
                    STATUS current
                    DESCRIPTION "Condensation temperature probe 1 enable"
                    ::= { digitalObjects 83 }

        -- 1.3.6.1.4.1.9839.2.1.1.84
        dig84 OBJECT-TYPE
                    SYNTAX Integer32 (0..1)
                    UNITS "N/A"
                    MAX-ACCESS read-write
                    STATUS current
                    DESCRIPTION "Condensation temperature probe 2 enable"
                    ::= { digitalObjects 84 }

        -- 1.3.6.1.4.1.9839.2.1.1.85
        dig85 OBJECT-TYPE
                    SYNTAX Integer32 (0..1)
                    UNITS "N/A"
                    MAX-ACCESS read-write
                    STATUS current
                    DESCRIPTION "Recovery probe enable"
                    ::= { digitalObjects 85 }

        -- 1.3.6.1.4.1.9839.2.1.1.86
        dig86 OBJECT-TYPE
                    SYNTAX Integer32 (0..1)
                    UNITS "N/A"
                    MAX-ACCESS read-write
                    STATUS current
                    DESCRIPTION "Configuration of modulating output 6 (0=renewal damper; 1=recovery valve)"
                    ::= { digitalObjects 86 }

        -- 1.3.6.1.4.1.9839.2.1.1.87
        dig87 OBJECT-TYPE
                    SYNTAX Integer32 (0..1)
                    UNITS "N/A"
                    MAX-ACCESS read-write
                    STATUS current
                    DESCRIPTION "Unit type (0=ED; 1=CW)"
                    ::= { digitalObjects 87 }

        -- 1.3.6.1.4.1.9839.2.1.1.88
        dig88 OBJECT-TYPE
                    SYNTAX Integer32 (0..1)
                    UNITS "N/A"
                    MAX-ACCESS read-write
                    STATUS current
                    DESCRIPTION "Configuration of modulating output 2 (0=hot valve; 1=analogue humidifier)"
                    ::= { digitalObjects 88 }

        -- 1.3.6.1.4.1.9839.2.1.1.89
        dig89 OBJECT-TYPE
                    SYNTAX Integer32 (0..1)
                    UNITS "N/A"
                    MAX-ACCESS read-write
                    STATUS current
                    DESCRIPTION "Modulating delivery fan enable"
                    ::= { digitalObjects 89 }

        -- 1.3.6.1.4.1.9839.2.1.1.90
        dig90 OBJECT-TYPE
                    SYNTAX Integer32 (0..1)
                    UNITS "N/A"
                    MAX-ACCESS read-write
                    STATUS current
                    DESCRIPTION "Heating mode"
                    ::= { digitalObjects 90 }

        -- 1.3.6.1.4.1.9839.2.1.1.91
        dig91 OBJECT-TYPE
                    SYNTAX Integer32 (0..1)
                    UNITS "N/A"
                    MAX-ACCESS read-write
                    STATUS current
                    DESCRIPTION "Type of cooling coil valve (0=0-10v; 1=3point)"
                    ::= { digitalObjects 91 }

        -- 1.3.6.1.4.1.9839.2.1.1.92
        dig92 OBJECT-TYPE
                    SYNTAX Integer32 (0..1)
                    UNITS "N/A"
                    MAX-ACCESS read-write
                    STATUS current
                    DESCRIPTION "Type of heating coil valve (0=0-10v; 1=3point)"
                    ::= { digitalObjects 92 }

        -- 1.3.6.1.4.1.9839.2.1.1.93
        dig93 OBJECT-TYPE
                    SYNTAX Integer32 (0..1)
                    UNITS "N/A"
                    MAX-ACCESS read-write
                    STATUS current
                    DESCRIPTION "Humidifier 0-10 V modulating output enable"
                    ::= { digitalObjects 93 }

        -- 1.3.6.1.4.1.9839.2.1.1.94
        dig94 OBJECT-TYPE
                    SYNTAX Integer32 (0..1)
                    UNITS "N/A"
                    MAX-ACCESS read-write
                    STATUS current
                    DESCRIPTION "Main CW unit coil type (0=C/F; 1=cooling)"
                    ::= { digitalObjects 94 }

        -- 1.3.6.1.4.1.9839.2.1.1.95
        dig95 OBJECT-TYPE
                    SYNTAX Integer32 (0..1)
                    UNITS "N/A"
                    MAX-ACCESS read-write
                    STATUS current
                    DESCRIPTION "Type of condenser (0=single coil; 1=separate coils)"
                    ::= { digitalObjects 95 }

        -- 1.3.6.1.4.1.9839.2.1.1.96
        dig96 OBJECT-TYPE
                    SYNTAX Integer32 (0..1)
                    UNITS "N/A"
                    MAX-ACCESS read-write
                    STATUS current
                    DESCRIPTION "Fan type selection (0=inverter; 1=capacity steps)"
                    ::= { digitalObjects 96 }

        -- 1.3.6.1.4.1.9839.2.1.1.97
        dig97 OBJECT-TYPE
                    SYNTAX Integer32 (0..1)
                    UNITS "N/A"
                    MAX-ACCESS read-write
                    STATUS current
                    DESCRIPTION "Condensation function enable"
                    ::= { digitalObjects 97 }

        -- 1.3.6.1.4.1.9839.2.1.1.98
        dig98 OBJECT-TYPE
                    SYNTAX Integer32 (0..1)
                    UNITS "N/A"
                    MAX-ACCESS read-write
                    STATUS current
                    DESCRIPTION "High pressure Prevent function enable"
                    ::= { digitalObjects 98 }

        -- 1.3.6.1.4.1.9839.2.1.1.99
        dig99 OBJECT-TYPE
                    SYNTAX Integer32 (0..1)
                    UNITS "N/A"
                    MAX-ACCESS read-write
                    STATUS current
                    DESCRIPTION "Delivery limit function enable"
                    ::= { digitalObjects 99 }

        -- 1.3.6.1.4.1.9839.2.1.1.100
        dig100 OBJECT-TYPE
                    SYNTAX Integer32 (0..1)
                    UNITS "N/A"
                    MAX-ACCESS read-write
                    STATUS current
                    DESCRIPTION "Cooling coil enable for dehumidif."
                    ::= { digitalObjects 100 }

        -- 1.3.6.1.4.1.9839.2.1.1.101
        dig101 OBJECT-TYPE
                    SYNTAX Integer32 (0..1)
                    UNITS "N/A"
                    MAX-ACCESS read-write
                    STATUS current
                    DESCRIPTION "Recovery coil enable"
                    ::= { digitalObjects 101 }

        -- 1.3.6.1.4.1.9839.2.1.1.102
        dig102 OBJECT-TYPE
                    SYNTAX Integer32 (0..1)
                    UNITS "N/A"
                    MAX-ACCESS read-write
                    STATUS current
                    DESCRIPTION "Dehumid. contact logic (0=NO; 1=NC)"
                    ::= { digitalObjects 102 }

        -- 1.3.6.1.4.1.9839.2.1.1.103
        dig103 OBJECT-TYPE
                    SYNTAX Integer32 (0..1)
                    UNITS "N/A"
                    MAX-ACCESS read-write
                    STATUS current
                    DESCRIPTION "Compressor capacity step enable"
                    ::= { digitalObjects 103 }

        -- 1.3.6.1.4.1.9839.2.1.1.104
        dig104 OBJECT-TYPE
                    SYNTAX Integer32 (0..1)
                    UNITS "N/A"
                    MAX-ACCESS read-write
                    STATUS current
                    DESCRIPTION "Cap. step contact logic (0=NC; 1=NO)"
                    ::= { digitalObjects 104 }

        -- 1.3.6.1.4.1.9839.2.1.1.105
        dig105 OBJECT-TYPE
                    SYNTAX Integer32 (0..1)
                    UNITS "N/A"
                    MAX-ACCESS read-write
                    STATUS current
                    DESCRIPTION "Temperature reg. type (0=P; 1=P+I)"
                    ::= { digitalObjects 105 }

        -- 1.3.6.1.4.1.9839.2.1.1.106
        dig106 OBJECT-TYPE
                    SYNTAX Integer32 (0..1)
                    UNITS "N/A"
                    MAX-ACCESS read-write
                    STATUS current
                    DESCRIPTION "Integr. humidifier enable"
                    ::= { digitalObjects 106 }

        -- 1.3.6.1.4.1.9839.2.1.1.107
        dig107 OBJECT-TYPE
                    SYNTAX Integer32 (0..1)
                    UNITS "N/A"
                    MAX-ACCESS read-write
                    STATUS current
                    DESCRIPTION "Carel Master Control enable"
                    ::= { digitalObjects 107 }

        -- 1.3.6.1.4.1.9839.2.1.1.108
        dig108 OBJECT-TYPE
                    SYNTAX Integer32 (0..1)
                    UNITS "N/A"
                    MAX-ACCESS read-write
                    STATUS current
                    DESCRIPTION "Unit stand-by enable in temperature"
                    ::= { digitalObjects 108 }

        -- 1.3.6.1.4.1.9839.2.1.1.109
        dig109 OBJECT-TYPE
                    SYNTAX Integer32 (0..1)
                    UNITS "N/A"
                    MAX-ACCESS read-write
                    STATUS current
                    DESCRIPTION "On-Off time zone enable"
                    ::= { digitalObjects 109 }

        -- 1.3.6.1.4.1.9839.2.1.1.110
        dig110 OBJECT-TYPE
                    SYNTAX Integer32 (0..1)
                    UNITS "N/A"
                    MAX-ACCESS read-write
                    STATUS current
                    DESCRIPTION "Temperature time zone enable"
                    ::= { digitalObjects 110 }

        -- 1.3.6.1.4.1.9839.2.1.1.111
        dig111 OBJECT-TYPE
                    SYNTAX Integer32 (0..1)
                    UNITS "N/A"
                    MAX-ACCESS read-write
                    STATUS current
                    DESCRIPTION "Humidity time zone enable"
                    ::= { digitalObjects 111 }

        -- 1.3.6.1.4.1.9839.2.1.1.112
        dig112 OBJECT-TYPE
                    SYNTAX Integer32 (0..1)
                    UNITS "N/A"
                    MAX-ACCESS read-write
                    STATUS current
                    DESCRIPTION "Unit shutdown from key enable"
                    ::= { digitalObjects 112 }

        -- 1.3.6.1.4.1.9839.2.1.1.113
        dig113 OBJECT-TYPE
                    SYNTAX Integer32 (0..1)
                    UNITS "N/A"
                    MAX-ACCESS read-write
                    STATUS current
                    DESCRIPTION "Remote On-Off digital input enable"
                    ::= { digitalObjects 113 }

        -- 1.3.6.1.4.1.9839.2.1.1.114
        dig114 OBJECT-TYPE
                    SYNTAX Integer32 (0..1)
                    UNITS "N/A"
                    MAX-ACCESS read-write
                    STATUS current
                    DESCRIPTION "Unit On-Off from supervisor"
                    ::= { digitalObjects 114 }

        -- 1.3.6.1.4.1.9839.2.1.1.115
        dig115 OBJECT-TYPE
                    SYNTAX Integer32 (0..1)
                    UNITS "N/A"
                    MAX-ACCESS read-write
                    STATUS current
                    DESCRIPTION "Digital output 7 configuration (0=recovery valve; 1=non-serious alarms)"
                    ::= { digitalObjects 115 }

        -- 1.3.6.1.4.1.9839.2.1.1.116
        dig116 OBJECT-TYPE
                    SYNTAX Integer32 (0..1)
                    UNITS "N/A"
                    MAX-ACCESS read-write
                    STATUS current
                    DESCRIPTION "Temperature unit of measurement selection"
                    ::= { digitalObjects 116 }

        -- 1.3.6.1.4.1.9839.2.1.1.117
        dig117 OBJECT-TYPE
                    SYNTAX Integer32 (0..1)
                    UNITS "N/A"
                    MAX-ACCESS read-write
                    STATUS current
                    DESCRIPTION "Time regulation confirmation"
                    ::= { digitalObjects 117 }

        -- 1.3.6.1.4.1.9839.2.1.1.118
        dig118 OBJECT-TYPE
                    SYNTAX Integer32 (0..1)
                    UNITS "N/A"
                    MAX-ACCESS read-write
                    STATUS current
                    DESCRIPTION "Minutes regulation confirmation"
                    ::= { digitalObjects 118 }

        -- 1.3.6.1.4.1.9839.2.1.1.119
        dig119 OBJECT-TYPE
                    SYNTAX Integer32 (0..1)
                    UNITS "N/A"
                    MAX-ACCESS read-write
                    STATUS current
                    DESCRIPTION "Date regulation confirmation"
                    ::= { digitalObjects 119 }

        -- 1.3.6.1.4.1.9839.2.1.1.120
        dig120 OBJECT-TYPE
                    SYNTAX Integer32 (0..1)
                    UNITS "N/A"
                    MAX-ACCESS read-write
                    STATUS current
                    DESCRIPTION "Month regulation confirmation"
                    ::= { digitalObjects 120 }

        -- 1.3.6.1.4.1.9839.2.1.1.121
        dig121 OBJECT-TYPE
                    SYNTAX Integer32 (0..1)
                    UNITS "N/A"
                    MAX-ACCESS read-write
                    STATUS current
                    DESCRIPTION "Year regulation confirmation"
                    ::= { digitalObjects 121 }

        -- 1.3.6.1.4.1.9839.2.1.1.122
        dig122 OBJECT-TYPE
                    SYNTAX Integer32 (0..1)
                    UNITS "N/A"
                    MAX-ACCESS read-write
                    STATUS current
                    DESCRIPTION "Supervisor alarm reset"
                    ::= { digitalObjects 122 }

        -- 1.3.6.1.4.1.9839.2.1.1.123
        dig123 OBJECT-TYPE
                    SYNTAX Integer32 (0..1)
                    UNITS "N/A"
                    MAX-ACCESS read-write
                    STATUS current
                    DESCRIPTION "Compressors Off with CT regulation"
                    ::= { digitalObjects 123 }

        -- 1.3.6.1.4.1.9839.2.1.1.124
        dig124 OBJECT-TYPE
                    SYNTAX Integer32 (0..1)
                    UNITS "N/A"
                    MAX-ACCESS read-write
                    STATUS current
                    DESCRIPTION "Heaters and humidifier remote control enable"
                    ::= { digitalObjects 124 }

        -- 1.3.6.1.4.1.9839.2.1.1.125
        dig125 OBJECT-TYPE
                    SYNTAX Integer32 (0..1)
                    UNITS "N/A"
                    MAX-ACCESS read-write
                    STATUS current
                    DESCRIPTION "DC reg. logic (Pre - Post)"
                    ::= { digitalObjects 125 }

        -- 1.3.6.1.4.1.9839.2.1.1.126
        dig126 OBJECT-TYPE
                    SYNTAX Integer32 (0..1)
                    UNITS "N/A"
                    MAX-ACCESS read-write
                    STATUS current
                    DESCRIPTION "Black-out alarm enable"
                    ::= { digitalObjects 126 }

        -- 1.3.6.1.4.1.9839.2.1.1.128
        dig128 OBJECT-TYPE
                    SYNTAX Integer32 (0..1)
                    UNITS "N/A"
                    MAX-ACCESS read-only
                    STATUS current
                    DESCRIPTION "Driver 1 Probe S1 alarm"
                    ::= { digitalObjects 128 }

        -- 1.3.6.1.4.1.9839.2.1.1.129
        dig129 OBJECT-TYPE
                    SYNTAX Integer32 (0..1)
                    UNITS "N/A"
                    MAX-ACCESS read-only
                    STATUS current
                    DESCRIPTION "Driver 1 Probe S2 alarm"
                    ::= { digitalObjects 129 }

        -- 1.3.6.1.4.1.9839.2.1.1.130
        dig130 OBJECT-TYPE
                    SYNTAX Integer32 (0..1)
                    UNITS "N/A"
                    MAX-ACCESS read-only
                    STATUS current
                    DESCRIPTION "Driver 1 Probe S3 alarm"
                    ::= { digitalObjects 130 }

        -- 1.3.6.1.4.1.9839.2.1.1.131
        dig131 OBJECT-TYPE
                    SYNTAX Integer32 (0..1)
                    UNITS "N/A"
                    MAX-ACCESS read-only
                    STATUS current
                    DESCRIPTION "Driver 2 Probe S1 alarm"
                    ::= { digitalObjects 131 }

        -- 1.3.6.1.4.1.9839.2.1.1.132
        dig132 OBJECT-TYPE
                    SYNTAX Integer32 (0..1)
                    UNITS "N/A"
                    MAX-ACCESS read-only
                    STATUS current
                    DESCRIPTION "Driver 2 Probe S2 alarm"
                    ::= { digitalObjects 132 }

        -- 1.3.6.1.4.1.9839.2.1.1.133
        dig133 OBJECT-TYPE
                    SYNTAX Integer32 (0..1)
                    UNITS "N/A"
                    MAX-ACCESS read-only
                    STATUS current
                    DESCRIPTION "Driver 2 Probe S3 alarm"
                    ::= { digitalObjects 133 }

        -- 1.3.6.1.4.1.9839.2.1.1.134
        dig134 OBJECT-TYPE
                    SYNTAX Integer32 (0..1)
                    UNITS "N/A"
                    MAX-ACCESS read-write
                    STATUS current
                    DESCRIPTION "Diff. air pressure sensor enable"
                    ::= { digitalObjects 134 }

        -- 1.3.6.1.4.1.9839.2.1.1.135
        dig135 OBJECT-TYPE
                    SYNTAX Integer32 (0..1)
                    UNITS "N/A"
                    MAX-ACCESS read-only
                    STATUS current
                    DESCRIPTION "Diff. air pressure sensor alarm"
                    ::= { digitalObjects 135 }



        -- 1.3.6.1.4.1.9839.2.1.2
        analogObjects OBJECT IDENTIFIER ::= { flbbomcz0eMIB 2 }

        -- 1.3.6.1.4.1.9839.2.1.2.1
        ana1 OBJECT-TYPE
                    SYNTAX Integer32 (-32767..32767)
                    UNITS "N/A"
                    MAX-ACCESS read-only
                    STATUS current
                    DESCRIPTION "Ambient humidity probe reading"
                    ::= { analogObjects 1 }

        -- 1.3.6.1.4.1.9839.2.1.2.2
        ana2 OBJECT-TYPE
                    SYNTAX Integer32 (-32767..32767)
                    UNITS "N/A"
                    MAX-ACCESS read-only
                    STATUS current
                    DESCRIPTION "Pressure probe 1 reading"
                    ::= { analogObjects 2 }

        -- 1.3.6.1.4.1.9839.2.1.2.3
        ana3 OBJECT-TYPE
                    SYNTAX Integer32 (-32767..32767)
                    UNITS "N/A"
                    MAX-ACCESS read-only
                    STATUS current
                    DESCRIPTION "Pressure probe 2 reading"
                    ::= { analogObjects 3 }

        -- 1.3.6.1.4.1.9839.2.1.2.4
        ana4 OBJECT-TYPE
                    SYNTAX Integer32 (-32767..32767)
                    UNITS "N/A"
                    MAX-ACCESS read-only
                    STATUS current
                    DESCRIPTION "Ambient temp. probe reading"
                    ::= { analogObjects 4 }

        -- 1.3.6.1.4.1.9839.2.1.2.5
        ana5 OBJECT-TYPE
                    SYNTAX Integer32 (-32767..32767)
                    UNITS "N/A"
                    MAX-ACCESS read-only
                    STATUS current
                    DESCRIPTION "Delivery air temp. probe reading"
                    ::= { analogObjects 5 }

        -- 1.3.6.1.4.1.9839.2.1.2.6
        ana6 OBJECT-TYPE
                    SYNTAX Integer32 (-32767..32767)
                    UNITS "N/A"
                    MAX-ACCESS read-only
                    STATUS current
                    DESCRIPTION "External temp. probe reading"
                    ::= { analogObjects 6 }

        -- 1.3.6.1.4.1.9839.2.1.2.7
        ana7 OBJECT-TYPE
                    SYNTAX Integer32 (-32767..32767)
                    UNITS "N/A"
                    MAX-ACCESS read-only
                    STATUS current
                    DESCRIPTION "Condens. 1 temp. probe reading"
                    ::= { analogObjects 7 }

        -- 1.3.6.1.4.1.9839.2.1.2.8
        ana8 OBJECT-TYPE
                    SYNTAX Integer32 (-32767..32767)
                    UNITS "N/A"
                    MAX-ACCESS read-only
                    STATUS current
                    DESCRIPTION "Condens. 2 temp. probe reading"
                    ::= { analogObjects 8 }

        -- 1.3.6.1.4.1.9839.2.1.2.9
        ana9 OBJECT-TYPE
                    SYNTAX Integer32 (-32767..32767)
                    UNITS "N/A"
                    MAX-ACCESS read-only
                    STATUS current
                    DESCRIPTION "Recovery water temp. probe reading"
                    ::= { analogObjects 9 }

        -- 1.3.6.1.4.1.9839.2.1.2.10
        ana10 OBJECT-TYPE
                    SYNTAX Integer32 (-32767..32767)
                    UNITS "N/A"
                    MAX-ACCESS read-write
                    STATUS current
                    DESCRIPTION "Temperature Setpoint"
                    ::= { analogObjects 10 }

        -- 1.3.6.1.4.1.9839.2.1.2.11
        ana11 OBJECT-TYPE
                    SYNTAX Integer32 (-32767..32767)
                    UNITS "N/A"
                    MAX-ACCESS read-write
                    STATUS current
                    DESCRIPTION "Minimum limit of Temperature Setpoint"
                    ::= { analogObjects 11 }

        -- 1.3.6.1.4.1.9839.2.1.2.12
        ana12 OBJECT-TYPE
                    SYNTAX Integer32 (-32767..32767)
                    UNITS "N/A"
                    MAX-ACCESS read-write
                    STATUS current
                    DESCRIPTION "Maximum limit of Temperature Setpoint"
                    ::= { analogObjects 12 }

        -- 1.3.6.1.4.1.9839.2.1.2.13
        ana13 OBJECT-TYPE
                    SYNTAX Integer32 (-32767..32767)
                    UNITS "N/A"
                    MAX-ACCESS read-write
                    STATUS current
                    DESCRIPTION "Humidity Setpoint"
                    ::= { analogObjects 13 }

        -- 1.3.6.1.4.1.9839.2.1.2.14
        ana14 OBJECT-TYPE
                    SYNTAX Integer32 (-32767..32767)
                    UNITS "N/A"
                    MAX-ACCESS read-write
                    STATUS current
                    DESCRIPTION "Minimum limit of Humidity Setpoint"
                    ::= { analogObjects 14 }

        -- 1.3.6.1.4.1.9839.2.1.2.15
        ana15 OBJECT-TYPE
                    SYNTAX Integer32 (-32767..32767)
                    UNITS "N/A"
                    MAX-ACCESS read-write
                    STATUS current
                    DESCRIPTION "Maximum limit of Humidity Setpoint"
                    ::= { analogObjects 15 }

        -- 1.3.6.1.4.1.9839.2.1.2.16
        ana16 OBJECT-TYPE
                    SYNTAX Integer32 (-32767..32767)
                    UNITS "N/A"
                    MAX-ACCESS read-write
                    STATUS current
                    DESCRIPTION "Time zone Setpoint for temperature Z1"
                    ::= { analogObjects 16 }

        -- 1.3.6.1.4.1.9839.2.1.2.17
        ana17 OBJECT-TYPE
                    SYNTAX Integer32 (-32767..32767)
                    UNITS "N/A"
                    MAX-ACCESS read-write
                    STATUS current
                    DESCRIPTION "Time zone Setpoint for temperature Z2"
                    ::= { analogObjects 17 }

        -- 1.3.6.1.4.1.9839.2.1.2.18
        ana18 OBJECT-TYPE
                    SYNTAX Integer32 (-32767..32767)
                    UNITS "N/A"
                    MAX-ACCESS read-write
                    STATUS current
                    DESCRIPTION "Time zone Setpoint for temperature Z3"
                    ::= { analogObjects 18 }

        -- 1.3.6.1.4.1.9839.2.1.2.19
        ana19 OBJECT-TYPE
                    SYNTAX Integer32 (-32767..32767)
                    UNITS "N/A"
                    MAX-ACCESS read-write
                    STATUS current
                    DESCRIPTION "Time zone Setpoint for temperature Z4"
                    ::= { analogObjects 19 }

        -- 1.3.6.1.4.1.9839.2.1.2.20
        ana20 OBJECT-TYPE
                    SYNTAX Integer32 (-32767..32767)
                    UNITS "N/A"
                    MAX-ACCESS read-write
                    STATUS current
                    DESCRIPTION "Time zone Setpoint for humidity Z1"
                    ::= { analogObjects 20 }

        -- 1.3.6.1.4.1.9839.2.1.2.21
        ana21 OBJECT-TYPE
                    SYNTAX Integer32 (-32767..32767)
                    UNITS "N/A"
                    MAX-ACCESS read-write
                    STATUS current
                    DESCRIPTION "Time zone Setpoint for humidity Z2"
                    ::= { analogObjects 21 }

        -- 1.3.6.1.4.1.9839.2.1.2.22
        ana22 OBJECT-TYPE
                    SYNTAX Integer32 (-32767..32767)
                    UNITS "N/A"
                    MAX-ACCESS read-write
                    STATUS current
                    DESCRIPTION "Time zone Setpoint for humidity Z3"
                    ::= { analogObjects 22 }

        -- 1.3.6.1.4.1.9839.2.1.2.23
        ana23 OBJECT-TYPE
                    SYNTAX Integer32 (-32767..32767)
                    UNITS "N/A"
                    MAX-ACCESS read-write
                    STATUS current
                    DESCRIPTION "Time zone Setpoint for humidity Z4"
                    ::= { analogObjects 23 }

        -- 1.3.6.1.4.1.9839.2.1.2.24
        ana24 OBJECT-TYPE
                    SYNTAX Integer32 (-32767..32767)
                    UNITS "N/A"
                    MAX-ACCESS read-write
                    STATUS current
                    DESCRIPTION "Neutral temperature zone"
                    ::= { analogObjects 24 }

        -- 1.3.6.1.4.1.9839.2.1.2.25
        ana25 OBJECT-TYPE
                    SYNTAX Integer32 (-32767..32767)
                    UNITS "N/A"
                    MAX-ACCESS read-write
                    STATUS current
                    DESCRIPTION "Cooling differential"
                    ::= { analogObjects 25 }

        -- 1.3.6.1.4.1.9839.2.1.2.26
        ana26 OBJECT-TYPE
                    SYNTAX Integer32 (-32767..32767)
                    UNITS "N/A"
                    MAX-ACCESS read-write
                    STATUS current
                    DESCRIPTION "Heating differential"
                    ::= { analogObjects 26 }

        -- 1.3.6.1.4.1.9839.2.1.2.27
        ana27 OBJECT-TYPE
                    SYNTAX Integer32 (-32767..32767)
                    UNITS "N/A"
                    MAX-ACCESS read-write
                    STATUS current
                    DESCRIPTION "Humidification differential"
                    ::= { analogObjects 27 }

        -- 1.3.6.1.4.1.9839.2.1.2.28
        ana28 OBJECT-TYPE
                    SYNTAX Integer32 (-32767..32767)
                    UNITS "N/A"
                    MAX-ACCESS read-write
                    STATUS current
                    DESCRIPTION "Dehumidification differential"
                    ::= { analogObjects 28 }

        -- 1.3.6.1.4.1.9839.2.1.2.29
        ana29 OBJECT-TYPE
                    SYNTAX Integer32 (-32767..32767)
                    UNITS "N/A"
                    MAX-ACCESS read-write
                    STATUS current
                    DESCRIPTION "Maximum Temp. set compensation offset"
                    ::= { analogObjects 29 }

        -- 1.3.6.1.4.1.9839.2.1.2.30
        ana30 OBJECT-TYPE
                    SYNTAX Integer32 (-32767..32767)
                    UNITS "N/A"
                    MAX-ACCESS read-write
                    STATUS current
                    DESCRIPTION "External temp. probe calibration"
                    ::= { analogObjects 30 }

        -- 1.3.6.1.4.1.9839.2.1.2.31
        ana31 OBJECT-TYPE
                    SYNTAX Integer32 (-32767..32767)
                    UNITS "N/A"
                    MAX-ACCESS read-write
                    STATUS current
                    DESCRIPTION "Condens. 1 pressure probe calibration"
                    ::= { analogObjects 31 }

        -- 1.3.6.1.4.1.9839.2.1.2.32
        ana32 OBJECT-TYPE
                    SYNTAX Integer32 (-32767..32767)
                    UNITS "N/A"
                    MAX-ACCESS read-write
                    STATUS current
                    DESCRIPTION "Condens. 2 pressure probe calibration"
                    ::= { analogObjects 32 }

        -- 1.3.6.1.4.1.9839.2.1.2.33
        ana33 OBJECT-TYPE
                    SYNTAX Integer32 (-32767..32767)
                    UNITS "N/A"
                    MAX-ACCESS read-write
                    STATUS current
                    DESCRIPTION "Humidity probe calibration"
                    ::= { analogObjects 33 }

        -- 1.3.6.1.4.1.9839.2.1.2.34
        ana34 OBJECT-TYPE
                    SYNTAX Integer32 (-32767..32767)
                    UNITS "N/A"
                    MAX-ACCESS read-write
                    STATUS current
                    DESCRIPTION "Ambient temp. probe calibration"
                    ::= { analogObjects 34 }

        -- 1.3.6.1.4.1.9839.2.1.2.35
        ana35 OBJECT-TYPE
                    SYNTAX Integer32 (-32767..32767)
                    UNITS "N/A"
                    MAX-ACCESS read-write
                    STATUS current
                    DESCRIPTION "Delivery temp. probe calibration"
                    ::= { analogObjects 35 }

        -- 1.3.6.1.4.1.9839.2.1.2.36
        ana36 OBJECT-TYPE
                    SYNTAX Integer32 (-32767..32767)
                    UNITS "N/A"
                    MAX-ACCESS read-write
                    STATUS current
                    DESCRIPTION "Condens.1 temp. probe calibration"
                    ::= { analogObjects 36 }

        -- 1.3.6.1.4.1.9839.2.1.2.37
        ana37 OBJECT-TYPE
                    SYNTAX Integer32 (-32767..32767)
                    UNITS "N/A"
                    MAX-ACCESS read-write
                    STATUS current
                    DESCRIPTION "Condens.2 temp. probe calibration"
                    ::= { analogObjects 37 }

        -- 1.3.6.1.4.1.9839.2.1.2.38
        ana38 OBJECT-TYPE
                    SYNTAX Integer32 (-32767..32767)
                    UNITS "N/A"
                    MAX-ACCESS read-write
                    STATUS current
                    DESCRIPTION "Not used"
                    ::= { analogObjects 38 }

        -- 1.3.6.1.4.1.9839.2.1.2.39
        ana39 OBJECT-TYPE
                    SYNTAX Integer32 (-32767..32767)
                    UNITS "N/A"
                    MAX-ACCESS read-write
                    STATUS current
                    DESCRIPTION "Dehumid. stop temp. differential"
                    ::= { analogObjects 39 }

        -- 1.3.6.1.4.1.9839.2.1.2.40
        ana40 OBJECT-TYPE
                    SYNTAX Integer32 (-32767..32767)
                    UNITS "N/A"
                    MAX-ACCESS read-write
                    STATUS current
                    DESCRIPTION "Delivery air differential"
                    ::= { analogObjects 40 }

        -- 1.3.6.1.4.1.9839.2.1.2.41
        ana41 OBJECT-TYPE
                    SYNTAX Integer32 (-32767..32767)
                    UNITS "N/A"
                    MAX-ACCESS read-write
                    STATUS current
                    DESCRIPTION "Ext. air for compensation differential"
                    ::= { analogObjects 41 }

        -- 1.3.6.1.4.1.9839.2.1.2.42
        ana42 OBJECT-TYPE
                    SYNTAX Integer32 (-32767..32767)
                    UNITS "N/A"
                    MAX-ACCESS read-write
                    STATUS current
                    DESCRIPTION "High pressure alarm differential"
                    ::= { analogObjects 42 }

        -- 1.3.6.1.4.1.9839.2.1.2.43
        ana43 OBJECT-TYPE
                    SYNTAX Integer32 (-32767..32767)
                    UNITS "N/A"
                    MAX-ACCESS read-write
                    STATUS current
                    DESCRIPTION "Condensation differential (pressure)"
                    ::= { analogObjects 43 }

        -- 1.3.6.1.4.1.9839.2.1.2.44
        ana44 OBJECT-TYPE
                    SYNTAX Integer32 (-32767..32767)
                    UNITS "N/A"
                    MAX-ACCESS read-write
                    STATUS current
                    DESCRIPTION "Condensation differential (temperat.)"
                    ::= { analogObjects 44 }

        -- 1.3.6.1.4.1.9839.2.1.2.45
        ana45 OBJECT-TYPE
                    SYNTAX Integer32 (-32767..32767)
                    UNITS "N/A"
                    MAX-ACCESS read-write
                    STATUS current
                    DESCRIPTION "Max. condensation fan speed"
                    ::= { analogObjects 45 }

        -- 1.3.6.1.4.1.9839.2.1.2.46
        ana46 OBJECT-TYPE
                    SYNTAX Integer32 (-32767..32767)
                    UNITS "N/A"
                    MAX-ACCESS read-write
                    STATUS current
                    DESCRIPTION "Min. condensation fan speed"
                    ::= { analogObjects 46 }

        -- 1.3.6.1.4.1.9839.2.1.2.47
        ana47 OBJECT-TYPE
                    SYNTAX Integer32 (-32767..32767)
                    UNITS "N/A"
                    MAX-ACCESS read-write
                    STATUS current
                    DESCRIPTION "Condensation Setpoint (pressure)"
                    ::= { analogObjects 47 }

        -- 1.3.6.1.4.1.9839.2.1.2.48
        ana48 OBJECT-TYPE
                    SYNTAX Integer32 (-32767..32767)
                    UNITS "N/A"
                    MAX-ACCESS read-write
                    STATUS current
                    DESCRIPTION "Condensation Setpoint (temperature)"
                    ::= { analogObjects 48 }

        -- 1.3.6.1.4.1.9839.2.1.2.49
        ana49 OBJECT-TYPE
                    SYNTAX Integer32 (-32767..32767)
                    UNITS "N/A"
                    MAX-ACCESS read-write
                    STATUS current
                    DESCRIPTION "High temperature unit override differential"
                    ::= { analogObjects 49 }

        -- 1.3.6.1.4.1.9839.2.1.2.50
        ana50 OBJECT-TYPE
                    SYNTAX Integer32 (-32767..32767)
                    UNITS "N/A"
                    MAX-ACCESS read-write
                    STATUS current
                    DESCRIPTION "Low temperature unit override differential"
                    ::= { analogObjects 50 }

        -- 1.3.6.1.4.1.9839.2.1.2.51
        ana51 OBJECT-TYPE
                    SYNTAX Integer32 (-32767..32767)
                    UNITS "N/A"
                    MAX-ACCESS read-write
                    STATUS current
                    DESCRIPTION "High temperature unit override Offset"
                    ::= { analogObjects 51 }

        -- 1.3.6.1.4.1.9839.2.1.2.52
        ana52 OBJECT-TYPE
                    SYNTAX Integer32 (-32767..32767)
                    UNITS "N/A"
                    MAX-ACCESS read-write
                    STATUS current
                    DESCRIPTION "Low temperature unit override Offset"
                    ::= { analogObjects 52 }

        -- 1.3.6.1.4.1.9839.2.1.2.53
        ana53 OBJECT-TYPE
                    SYNTAX Integer32 (-32767..32767)
                    UNITS "N/A"
                    MAX-ACCESS read-write
                    STATUS current
                    DESCRIPTION "High ambient temperature alarm offset"
                    ::= { analogObjects 53 }

        -- 1.3.6.1.4.1.9839.2.1.2.54
        ana54 OBJECT-TYPE
                    SYNTAX Integer32 (-32767..32767)
                    UNITS "N/A"
                    MAX-ACCESS read-write
                    STATUS current
                    DESCRIPTION "Low ambient temperature alarm offset"
                    ::= { analogObjects 54 }

        -- 1.3.6.1.4.1.9839.2.1.2.55
        ana55 OBJECT-TYPE
                    SYNTAX Integer32 (-32767..32767)
                    UNITS "N/A"
                    MAX-ACCESS read-write
                    STATUS current
                    DESCRIPTION "High ambient humidity alarm offset"
                    ::= { analogObjects 55 }

        -- 1.3.6.1.4.1.9839.2.1.2.56
        ana56 OBJECT-TYPE
                    SYNTAX Integer32 (-32767..32767)
                    UNITS "N/A"
                    MAX-ACCESS read-write
                    STATUS current
                    DESCRIPTION "Low ambient humidity alarm offset"
                    ::= { analogObjects 56 }

        -- 1.3.6.1.4.1.9839.2.1.2.57
        ana57 OBJECT-TYPE
                    SYNTAX Integer32 (-32767..32767)
                    UNITS "N/A"
                    MAX-ACCESS read-write
                    STATUS current
                    DESCRIPTION "Maximum delivery fan speed"
                    ::= { analogObjects 57 }

        -- 1.3.6.1.4.1.9839.2.1.2.58
        ana58 OBJECT-TYPE
                    SYNTAX Integer32 (-32767..32767)
                    UNITS "N/A"
                    MAX-ACCESS read-write
                    STATUS current
                    DESCRIPTION "Minimum delivery fan speed"
                    ::= { analogObjects 58 }

        -- 1.3.6.1.4.1.9839.2.1.2.59
        ana59 OBJECT-TYPE
                    SYNTAX Integer32 (-32767..32767)
                    UNITS "N/A"
                    MAX-ACCESS read-write
                    STATUS current
                    DESCRIPTION "Maximum humidifier production"
                    ::= { analogObjects 59 }

        -- 1.3.6.1.4.1.9839.2.1.2.60
        ana60 OBJECT-TYPE
                    SYNTAX Integer32 (-32767..32767)
                    UNITS "N/A"
                    MAX-ACCESS read-write
                    STATUS current
                    DESCRIPTION "Humidifier modulating output opening end point"
                    ::= { analogObjects 60 }

        -- 1.3.6.1.4.1.9839.2.1.2.61
        ana61 OBJECT-TYPE
                    SYNTAX Integer32 (-32767..32767)
                    UNITS "N/A"
                    MAX-ACCESS read-write
                    STATUS current
                    DESCRIPTION "Humidifier modulating output opening start point"
                    ::= { analogObjects 61 }

        -- 1.3.6.1.4.1.9839.2.1.2.62
        ana62 OBJECT-TYPE
                    SYNTAX Integer32 (-32767..32767)
                    UNITS "N/A"
                    MAX-ACCESS read-write
                    STATUS current
                    DESCRIPTION "Max. humidity probe value"
                    ::= { analogObjects 62 }

        -- 1.3.6.1.4.1.9839.2.1.2.63
        ana63 OBJECT-TYPE
                    SYNTAX Integer32 (-32767..32767)
                    UNITS "N/A"
                    MAX-ACCESS read-write
                    STATUS current
                    DESCRIPTION "Min. humidity probe value"
                    ::= { analogObjects 63 }

        -- 1.3.6.1.4.1.9839.2.1.2.64
        ana64 OBJECT-TYPE
                    SYNTAX Integer32 (-32767..32767)
                    UNITS "N/A"
                    MAX-ACCESS read-write
                    STATUS current
                    DESCRIPTION "Maximum pressure probe 1 value"
                    ::= { analogObjects 64 }

        -- 1.3.6.1.4.1.9839.2.1.2.65
        ana65 OBJECT-TYPE
                    SYNTAX Integer32 (-32767..32767)
                    UNITS "N/A"
                    MAX-ACCESS read-write
                    STATUS current
                    DESCRIPTION "Minimum pressure probe 1 value"
                    ::= { analogObjects 65 }

        -- 1.3.6.1.4.1.9839.2.1.2.66
        ana66 OBJECT-TYPE
                    SYNTAX Integer32 (-32767..32767)
                    UNITS "N/A"
                    MAX-ACCESS read-write
                    STATUS current
                    DESCRIPTION "Maximum pressure probe 2 value"
                    ::= { analogObjects 66 }

        -- 1.3.6.1.4.1.9839.2.1.2.67
        ana67 OBJECT-TYPE
                    SYNTAX Integer32 (-32767..32767)
                    UNITS "N/A"
                    MAX-ACCESS read-write
                    STATUS current
                    DESCRIPTION "Minimum pressure probe 2 value"
                    ::= { analogObjects 67 }

        -- 1.3.6.1.4.1.9839.2.1.2.68
        ana68 OBJECT-TYPE
                    SYNTAX Integer32 (-32767..32767)
                    UNITS "N/A"
                    MAX-ACCESS read-write
                    STATUS current
                    DESCRIPTION "Dehumidifier stop low temperature limit offset"
                    ::= { analogObjects 68 }

        -- 1.3.6.1.4.1.9839.2.1.2.69
        ana69 OBJECT-TYPE
                    SYNTAX Integer32 (-32767..32767)
                    UNITS "N/A"
                    MAX-ACCESS read-write
                    STATUS current
                    DESCRIPTION "Prevent differential (pressure)"
                    ::= { analogObjects 69 }

        -- 1.3.6.1.4.1.9839.2.1.2.70
        ana70 OBJECT-TYPE
                    SYNTAX Integer32 (-32767..32767)
                    UNITS "N/A"
                    MAX-ACCESS read-write
                    STATUS current
                    DESCRIPTION "Prevent differential (temperature)"
                    ::= { analogObjects 70 }

        -- 1.3.6.1.4.1.9839.2.1.2.71
        ana71 OBJECT-TYPE
                    SYNTAX Integer32 (-32767..32767)
                    UNITS "N/A"
                    MAX-ACCESS read-write
                    STATUS current
                    DESCRIPTION "Prevent Setpoint (pressure)"
                    ::= { analogObjects 71 }

        -- 1.3.6.1.4.1.9839.2.1.2.72
        ana72 OBJECT-TYPE
                    SYNTAX Integer32 (-32767..32767)
                    UNITS "N/A"
                    MAX-ACCESS read-write
                    STATUS current
                    DESCRIPTION "Prevent Setpoint (temperature)"
                    ::= { analogObjects 72 }

        -- 1.3.6.1.4.1.9839.2.1.2.74
        ana74 OBJECT-TYPE
                    SYNTAX Integer32 (-32767..32767)
                    UNITS "N/A"
                    MAX-ACCESS read-write
                    STATUS current
                    DESCRIPTION "High pressure alarm Setpoint"
                    ::= { analogObjects 74 }

        -- 1.3.6.1.4.1.9839.2.1.2.75
        ana75 OBJECT-TYPE
                    SYNTAX Integer32 (-32767..32767)
                    UNITS "N/A"
                    MAX-ACCESS read-write
                    STATUS current
                    DESCRIPTION "Delivery air Setpoint"
                    ::= { analogObjects 75 }

        -- 1.3.6.1.4.1.9839.2.1.2.76
        ana76 OBJECT-TYPE
                    SYNTAX Integer32 (-32767..32767)
                    UNITS "N/A"
                    MAX-ACCESS read-write
                    STATUS current
                    DESCRIPTION "Compensation from external air Setpoint"
                    ::= { analogObjects 76 }

        -- 1.3.6.1.4.1.9839.2.1.2.77
        ana77 OBJECT-TYPE
                    SYNTAX Integer32 (-32767..32767)
                    UNITS "N/A"
                    MAX-ACCESS read-write
                    STATUS current
                    DESCRIPTION "Dehumid. delivery fan speed"
                    ::= { analogObjects 77 }

        -- 1.3.6.1.4.1.9839.2.1.2.78
        ana78 OBJECT-TYPE
                    SYNTAX Integer32 (-32767..32767)
                    UNITS "N/A"
                    MAX-ACCESS read-only
                    STATUS current
                    DESCRIPTION "Current value of super heat driver 1"
                    ::= { analogObjects 78 }

        -- 1.3.6.1.4.1.9839.2.1.2.79
        ana79 OBJECT-TYPE
                    SYNTAX Integer32 (-32767..32767)
                    UNITS "N/A"
                    MAX-ACCESS read-only
                    STATUS current
                    DESCRIPTION "Driver 1 evaporation temperature"
                    ::= { analogObjects 79 }

        -- 1.3.6.1.4.1.9839.2.1.2.80
        ana80 OBJECT-TYPE
                    SYNTAX Integer32 (-32767..32767)
                    UNITS "N/A"
                    MAX-ACCESS read-only
                    STATUS current
                    DESCRIPTION "Driver 1 intake temperature"
                    ::= { analogObjects 80 }

        -- 1.3.6.1.4.1.9839.2.1.2.81
        ana81 OBJECT-TYPE
                    SYNTAX Integer32 (-32767..32767)
                    UNITS "N/A"
                    MAX-ACCESS read-only
                    STATUS current
                    DESCRIPTION "Driver 1 evaporation pressure"
                    ::= { analogObjects 81 }

        -- 1.3.6.1.4.1.9839.2.1.2.82
        ana82 OBJECT-TYPE
                    SYNTAX Integer32 (-32767..32767)
                    UNITS "N/A"
                    MAX-ACCESS read-only
                    STATUS current
                    DESCRIPTION "Driver 1 condensation temperature"
                    ::= { analogObjects 82 }

        -- 1.3.6.1.4.1.9839.2.1.2.83
        ana83 OBJECT-TYPE
                    SYNTAX Integer32 (-32767..32767)
                    UNITS "N/A"
                    MAX-ACCESS read-only
                    STATUS current
                    DESCRIPTION "Current value of super heat driver 2"
                    ::= { analogObjects 83 }

        -- 1.3.6.1.4.1.9839.2.1.2.84
        ana84 OBJECT-TYPE
                    SYNTAX Integer32 (-32767..32767)
                    UNITS "N/A"
                    MAX-ACCESS read-only
                    STATUS current
                    DESCRIPTION "Driver 2 evaporation temperature"
                    ::= { analogObjects 84 }

        -- 1.3.6.1.4.1.9839.2.1.2.85
        ana85 OBJECT-TYPE
                    SYNTAX Integer32 (-32767..32767)
                    UNITS "N/A"
                    MAX-ACCESS read-only
                    STATUS current
                    DESCRIPTION "Driver 2 intake temperature"
                    ::= { analogObjects 85 }

        -- 1.3.6.1.4.1.9839.2.1.2.86
        ana86 OBJECT-TYPE
                    SYNTAX Integer32 (-32767..32767)
                    UNITS "N/A"
                    MAX-ACCESS read-only
                    STATUS current
                    DESCRIPTION "Driver 2 evaporation pressure"
                    ::= { analogObjects 86 }

        -- 1.3.6.1.4.1.9839.2.1.2.87
        ana87 OBJECT-TYPE
                    SYNTAX Integer32 (-32767..32767)
                    UNITS "N/A"
                    MAX-ACCESS read-only
                    STATUS current
                    DESCRIPTION "Driver 2 condensation temperature"
                    ::= { analogObjects 87 }

        -- 1.3.6.1.4.1.9839.2.1.2.88
        ana88 OBJECT-TYPE
                    SYNTAX Integer32 (-32767..32767)
                    UNITS "N/A"
                    MAX-ACCESS read-write
                    STATUS current
                    DESCRIPTION "Recovery Offset (FcW regulation)"
                    ::= { analogObjects 88 }

        -- 1.3.6.1.4.1.9839.2.1.2.89
        ana89 OBJECT-TYPE
                    SYNTAX Integer32 (-32767..32767)
                    UNITS "N/A"
                    MAX-ACCESS read-write
                    STATUS current
                    DESCRIPTION "Temperature difference (ambient - external) (FcW regulation)"
                    ::= { analogObjects 89 }

        -- 1.3.6.1.4.1.9839.2.1.2.90
        ana90 OBJECT-TYPE
                    SYNTAX Integer32 (-32767..32767)
                    UNITS "N/A"
                    MAX-ACCESS read-write
                    STATUS current
                    DESCRIPTION "Water inlet high temperature (FcW regulation)"
                    ::= { analogObjects 90 }

        -- 1.3.6.1.4.1.9839.2.1.2.91
        ana91 OBJECT-TYPE
                    SYNTAX Integer32 (-32767..32767)
                    UNITS "N/A"
                    MAX-ACCESS read-write
                    STATUS current
                    DESCRIPTION "Water inlet low temperature (FcW regulation)"
                    ::= { analogObjects 91 }

        -- 1.3.6.1.4.1.9839.2.1.2.92
        ana92 OBJECT-TYPE
                    SYNTAX Integer32 (-32767..32767)
                    UNITS "N/A"
                    MAX-ACCESS read-write
                    STATUS current
                    DESCRIPTION "Recovery Offset (FcA-t regulation)"
                    ::= { analogObjects 92 }

        -- 1.3.6.1.4.1.9839.2.1.2.93
        ana93 OBJECT-TYPE
                    SYNTAX Integer32 (-32767..32767)
                    UNITS "N/A"
                    MAX-ACCESS read-write
                    STATUS current
                    DESCRIPTION "External air high temperature (FcA-t regulation)"
                    ::= { analogObjects 93 }

        -- 1.3.6.1.4.1.9839.2.1.2.94
        ana94 OBJECT-TYPE
                    SYNTAX Integer32 (-32767..32767)
                    UNITS "N/A"
                    MAX-ACCESS read-write
                    STATUS current
                    DESCRIPTION "External air low temperature (FcA-t regulation)"
                    ::= { analogObjects 94 }

        -- 1.3.6.1.4.1.9839.2.1.2.95
        ana95 OBJECT-TYPE
                    SYNTAX Integer32 (-32767..32767)
                    UNITS "N/A"
                    MAX-ACCESS read-write
                    STATUS current
                    DESCRIPTION "Renewal air damper output voltage"
                    ::= { analogObjects 95 }

        -- 1.3.6.1.4.1.9839.2.1.2.96
        ana96 OBJECT-TYPE
                    SYNTAX Integer32 (-32767..32767)
                    UNITS "N/A"
                    MAX-ACCESS read-write
                    STATUS current
                    DESCRIPTION "Entalpic differential"
                    ::= { analogObjects 96 }

        -- 1.3.6.1.4.1.9839.2.1.2.97
        ana97 OBJECT-TYPE
                    SYNTAX Integer32 (-32767..32767)
                    UNITS "N/A"
                    MAX-ACCESS read-write
                    STATUS current
                    DESCRIPTION "Maximum external humidity probe value"
                    ::= { analogObjects 97 }

        -- 1.3.6.1.4.1.9839.2.1.2.98
        ana98 OBJECT-TYPE
                    SYNTAX Integer32 (-32767..32767)
                    UNITS "N/A"
                    MAX-ACCESS read-write
                    STATUS current
                    DESCRIPTION "Variable setpoint probe minimum value"
                    ::= { analogObjects 98 }

        -- 1.3.6.1.4.1.9839.2.1.2.99
        ana99 OBJECT-TYPE
                    SYNTAX Integer32 (-32767..32767)
                    UNITS "N/A"
                    MAX-ACCESS read-write
                    STATUS current
                    DESCRIPTION "Variable setpoint probe maximum value"
                    ::= { analogObjects 99 }

        -- 1.3.6.1.4.1.9839.2.1.2.100
        ana100 OBJECT-TYPE
                    SYNTAX Integer32 (-32767..32767)
                    UNITS "N/A"
                    MAX-ACCESS read-write
                    STATUS current
                    DESCRIPTION "Theoretical delta value (efficiency)"
                    ::= { analogObjects 100 }

        -- 1.3.6.1.4.1.9839.2.1.2.101
        ana101 OBJECT-TYPE
                    SYNTAX Integer32 (-32767..32767)
                    UNITS "N/A"
                    MAX-ACCESS read-write
                    STATUS current
                    DESCRIPTION "Recovery Offset (DC regulation)"
                    ::= { analogObjects 101 }

        -- 1.3.6.1.4.1.9839.2.1.2.102
        ana102 OBJECT-TYPE
                    SYNTAX Integer32 (-32767..32767)
                    UNITS "N/A"
                    MAX-ACCESS read-write
                    STATUS current
                    DESCRIPTION "High inlet temperature (DC regulation)"
                    ::= { analogObjects 102 }

        -- 1.3.6.1.4.1.9839.2.1.2.103
        ana103 OBJECT-TYPE
                    SYNTAX Integer32 (-32767..32767)
                    UNITS "N/A"
                    MAX-ACCESS read-only
                    STATUS current
                    DESCRIPTION "Water inlet temperature"
                    ::= { analogObjects 103 }

        -- 1.3.6.1.4.1.9839.2.1.2.104
        ana104 OBJECT-TYPE
                    SYNTAX Integer32 (-32767..32767)
                    UNITS "N/A"
                    MAX-ACCESS read-only
                    STATUS current
                    DESCRIPTION "Water outlet temperature"
                    ::= { analogObjects 104 }

        -- 1.3.6.1.4.1.9839.2.1.2.105
        ana105 OBJECT-TYPE
                    SYNTAX Integer32 (-32767..32767)
                    UNITS "N/A"
                    MAX-ACCESS read-only
                    STATUS current
                    DESCRIPTION "External air humidity"
                    ::= { analogObjects 105 }

        -- 1.3.6.1.4.1.9839.2.1.2.106
        ana106 OBJECT-TYPE
                    SYNTAX Integer32 (-32767..32767)
                    UNITS "N/A"
                    MAX-ACCESS read-write
                    STATUS current
                    DESCRIPTION "Cooling V3P stroke start (2° step)"
                    ::= { analogObjects 106 }

        -- 1.3.6.1.4.1.9839.2.1.2.107
        ana107 OBJECT-TYPE
                    SYNTAX Integer32 (-32767..32767)
                    UNITS "N/A"
                    MAX-ACCESS read-write
                    STATUS current
                    DESCRIPTION "Cooling V3P stroke end (2° step)"
                    ::= { analogObjects 107 }

        -- 1.3.6.1.4.1.9839.2.1.2.108
        ana108 OBJECT-TYPE
                    SYNTAX Integer32 (-32767..32767)
                    UNITS "N/A"
                    MAX-ACCESS read-write
                    STATUS current
                    DESCRIPTION "Dehumid. fan override offset"
                    ::= { analogObjects 108 }

        -- 1.3.6.1.4.1.9839.2.1.2.109
        ana109 OBJECT-TYPE
                    SYNTAX Integer32 (-32767..32767)
                    UNITS "N/A"
                    MAX-ACCESS read-write
                    STATUS current
                    DESCRIPTION "Defrost Setpoint"
                    ::= { analogObjects 109 }



        -- 1.3.6.1.4.1.9839.2.1.3
        integerObjects OBJECT IDENTIFIER ::= { flbbomcz0eMIB 3 }

        -- 1.3.6.1.4.1.9839.2.1.3.1
        int1 OBJECT-TYPE
                    SYNTAX Integer32 (-32767..32767)
                    UNITS "N/A"
                    MAX-ACCESS read-only
                    STATUS current
                    DESCRIPTION "Analogue output 1"
                    ::= { integerObjects 1 }

        -- 1.3.6.1.4.1.9839.2.1.3.2
        int2 OBJECT-TYPE
                    SYNTAX Integer32 (-32767..32767)
                    UNITS "N/A"
                    MAX-ACCESS read-only
                    STATUS current
                    DESCRIPTION "Analogue output 2"
                    ::= { integerObjects 2 }

        -- 1.3.6.1.4.1.9839.2.1.3.3
        int3 OBJECT-TYPE
                    SYNTAX Integer32 (-32767..32767)
                    UNITS "N/A"
                    MAX-ACCESS read-only
                    STATUS current
                    DESCRIPTION "Analogue output 3"
                    ::= { integerObjects 3 }

        -- 1.3.6.1.4.1.9839.2.1.3.4
        int4 OBJECT-TYPE
                    SYNTAX Integer32 (-32767..32767)
                    UNITS "N/A"
                    MAX-ACCESS read-only
                    STATUS current
                    DESCRIPTION "Analogue output 4"
                    ::= { integerObjects 4 }

        -- 1.3.6.1.4.1.9839.2.1.3.5
        int5 OBJECT-TYPE
                    SYNTAX Integer32 (-32767..32767)
                    UNITS "N/A"
                    MAX-ACCESS read-only
                    STATUS current
                    DESCRIPTION "Current time"
                    ::= { integerObjects 5 }

        -- 1.3.6.1.4.1.9839.2.1.3.6
        int6 OBJECT-TYPE
                    SYNTAX Integer32 (-32767..32767)
                    UNITS "N/A"
                    MAX-ACCESS read-only
                    STATUS current
                    DESCRIPTION "Current minutes"
                    ::= { integerObjects 6 }

        -- 1.3.6.1.4.1.9839.2.1.3.7
        int7 OBJECT-TYPE
                    SYNTAX Integer32 (-32767..32767)
                    UNITS "N/A"
                    MAX-ACCESS read-only
                    STATUS current
                    DESCRIPTION "Day"
                    ::= { integerObjects 7 }

        -- 1.3.6.1.4.1.9839.2.1.3.8
        int8 OBJECT-TYPE
                    SYNTAX Integer32 (-32767..32767)
                    UNITS "N/A"
                    MAX-ACCESS read-only
                    STATUS current
                    DESCRIPTION "Month"
                    ::= { integerObjects 8 }

        -- 1.3.6.1.4.1.9839.2.1.3.9
        int9 OBJECT-TYPE
                    SYNTAX Integer32 (-32767..32767)
                    UNITS "N/A"
                    MAX-ACCESS read-only
                    STATUS current
                    DESCRIPTION "Year"
                    ::= { integerObjects 9 }

        -- 1.3.6.1.4.1.9839.2.1.3.10
        int10 OBJECT-TYPE
                    SYNTAX Integer32 (-32767..32767)
                    UNITS "N/A"
                    MAX-ACCESS read-only
                    STATUS current
                    DESCRIPTION "Day of the week"
                    ::= { integerObjects 10 }

        -- 1.3.6.1.4.1.9839.2.1.3.11
        int11 OBJECT-TYPE
                    SYNTAX Integer32 (-32767..32767)
                    UNITS "N/A"
                    MAX-ACCESS read-write
                    STATUS current
                    DESCRIPTION "Time setting"
                    ::= { integerObjects 11 }

        -- 1.3.6.1.4.1.9839.2.1.3.12
        int12 OBJECT-TYPE
                    SYNTAX Integer32 (-32767..32767)
                    UNITS "N/A"
                    MAX-ACCESS read-write
                    STATUS current
                    DESCRIPTION "Minutes setting"
                    ::= { integerObjects 12 }

        -- 1.3.6.1.4.1.9839.2.1.3.13
        int13 OBJECT-TYPE
                    SYNTAX Integer32 (-32767..32767)
                    UNITS "N/A"
                    MAX-ACCESS read-write
                    STATUS current
                    DESCRIPTION "Day setting"
                    ::= { integerObjects 13 }

        -- 1.3.6.1.4.1.9839.2.1.3.14
        int14 OBJECT-TYPE
                    SYNTAX Integer32 (-32767..32767)
                    UNITS "N/A"
                    MAX-ACCESS read-write
                    STATUS current
                    DESCRIPTION "Month setting"
                    ::= { integerObjects 14 }

        -- 1.3.6.1.4.1.9839.2.1.3.15
        int15 OBJECT-TYPE
                    SYNTAX Integer32 (-32767..32767)
                    UNITS "N/A"
                    MAX-ACCESS read-write
                    STATUS current
                    DESCRIPTION "Year setting"
                    ::= { integerObjects 15 }

        -- 1.3.6.1.4.1.9839.2.1.3.16
        int16 OBJECT-TYPE
                    SYNTAX Integer32 (-32767..32767)
                    UNITS "N/A"
                    MAX-ACCESS read-write
                    STATUS current
                    DESCRIPTION "Number of compressors"
                    ::= { integerObjects 16 }

        -- 1.3.6.1.4.1.9839.2.1.3.17
        int17 OBJECT-TYPE
                    SYNTAX Integer32 (-32767..32767)
                    UNITS "N/A"
                    MAX-ACCESS read-write
                    STATUS current
                    DESCRIPTION "Number of compressors for dehumid."
                    ::= { integerObjects 17 }

        -- 1.3.6.1.4.1.9839.2.1.3.18
        int18 OBJECT-TYPE
                    SYNTAX Integer32 (-32767..32767)
                    UNITS "N/A"
                    MAX-ACCESS read-write
                    STATUS current
                    DESCRIPTION "Selection of number of On-Off fans"
                    ::= { integerObjects 18 }

        -- 1.3.6.1.4.1.9839.2.1.3.19
        int19 OBJECT-TYPE
                    SYNTAX Integer32 (-32767..32767)
                    UNITS "N/A"
                    MAX-ACCESS read-write
                    STATUS current
                    DESCRIPTION "Number of heaters for heating"
                    ::= { integerObjects 19 }

        -- 1.3.6.1.4.1.9839.2.1.3.20
        int20 OBJECT-TYPE
                    SYNTAX Integer32 (-32767..32767)
                    UNITS "N/A"
                    MAX-ACCESS read-write
                    STATUS current
                    DESCRIPTION "Configuration of analogue input 2 (0=circ. 1 press.; 1= circ.1 temp.; 2=ext. humidity)"
                    ::= { integerObjects 20 }

        -- 1.3.6.1.4.1.9839.2.1.3.21
        int21 OBJECT-TYPE
                    SYNTAX Integer32 (-32767..32767)
                    UNITS "N/A"
                    MAX-ACCESS read-write
                    STATUS current
                    DESCRIPTION "Configuration of analogue input 3 (0= circ.2 press.; 1= circ.2 temp.)"
                    ::= { integerObjects 21 }

        -- 1.3.6.1.4.1.9839.2.1.3.22
        int22 OBJECT-TYPE
                    SYNTAX Integer32 (-32767..32767)
                    UNITS "N/A"
                    MAX-ACCESS read-write
                    STATUS current
                    DESCRIPTION "Analog input 6 configuration (0=water out; 1=variable setpoint; 2= diff. air pressure)"
                    ::= { integerObjects 22 }

        -- 1.3.6.1.4.1.9839.2.1.3.23
        int23 OBJECT-TYPE
                    SYNTAX Integer32 (-32767..32767)
                    UNITS "N/A"
                    MAX-ACCESS read-write
                    STATUS current
                    DESCRIPTION "Humidity probe signal type (2=0-1V; 3=0-10V; 4=current)"
                    ::= { integerObjects 23 }

        -- 1.3.6.1.4.1.9839.2.1.3.24
        int24 OBJECT-TYPE
                    SYNTAX Integer32 (-32767..32767)
                    UNITS "N/A"
                    MAX-ACCESS read-write
                    STATUS current
                    DESCRIPTION "Pressure probe 1 signal type (2=0-1V; 3=0-10V; 4= current)"
                    ::= { integerObjects 24 }

        -- 1.3.6.1.4.1.9839.2.1.3.25
        int25 OBJECT-TYPE
                    SYNTAX Integer32 (-32767..32767)
                    UNITS "N/A"
                    MAX-ACCESS read-write
                    STATUS current
                    DESCRIPTION "Pressure probe 2 signal type (2=0-1V; 3=0-10V; 4= current)"
                    ::= { integerObjects 25 }

        -- 1.3.6.1.4.1.9839.2.1.3.26
        int26 OBJECT-TYPE
                    SYNTAX Integer32 (-32767..32767)
                    UNITS "N/A"
                    MAX-ACCESS read-write
                    STATUS current
                    DESCRIPTION "Condens. 1 temp. probe signal type (0=ntc; 1=pt1000; 2=0-1V; 3=0-10V; 4= current)"
                    ::= { integerObjects 26 }

        -- 1.3.6.1.4.1.9839.2.1.3.27
        int27 OBJECT-TYPE
                    SYNTAX Integer32 (-32767..32767)
                    UNITS "N/A"
                    MAX-ACCESS read-write
                    STATUS current
                    DESCRIPTION "Condens. 2 temp. probe signal type (0=ntc; 1=pt1000; 2=0-1V; 3=0-10V; 4= current)"
                    ::= { integerObjects 27 }

        -- 1.3.6.1.4.1.9839.2.1.3.28
        int28 OBJECT-TYPE
                    SYNTAX Integer32 (-32767..32767)
                    UNITS "N/A"
                    MAX-ACCESS read-write
                    STATUS current
                    DESCRIPTION "Ext. temperature probe signal type (0=ntc; 1=pt1000)"
                    ::= { integerObjects 28 }

        -- 1.3.6.1.4.1.9839.2.1.3.29
        int29 OBJECT-TYPE
                    SYNTAX Integer32 (-32767..32767)
                    UNITS "N/A"
                    MAX-ACCESS read-write
                    STATUS current
                    DESCRIPTION "Recovery temperature probe signal type (0=ntc; 1=pt1000)"
                    ::= { integerObjects 29 }

        -- 1.3.6.1.4.1.9839.2.1.3.30
        int30 OBJECT-TYPE
                    SYNTAX Integer32 (-32767..32767)
                    UNITS "N/A"
                    MAX-ACCESS read-write
                    STATUS current
                    DESCRIPTION "Ambient temperature probe signal type (0=ntc; 1=pt1000)"
                    ::= { integerObjects 30 }

        -- 1.3.6.1.4.1.9839.2.1.3.31
        int31 OBJECT-TYPE
                    SYNTAX Integer32 (-32767..32767)
                    UNITS "N/A"
                    MAX-ACCESS read-write
                    STATUS current
                    DESCRIPTION "Delivery temperature probe signal type (0=ntc; 1=pt1000)"
                    ::= { integerObjects 31 }

        -- 1.3.6.1.4.1.9839.2.1.3.32
        int32 OBJECT-TYPE
                    SYNTAX Integer32 (-32767..32767)
                    UNITS "N/A"
                    MAX-ACCESS read-write
                    STATUS current
                    DESCRIPTION "Refrigerant selection (0=no; 1=R22; 2=134a; 3=404a; 4=407C; 5=410A)"
                    ::= { integerObjects 32 }

        -- 1.3.6.1.4.1.9839.2.1.3.33
        int33 OBJECT-TYPE
                    SYNTAX Integer32 (-32767..32767)
                    UNITS "N/A"
                    MAX-ACCESS read-write
                    STATUS current
                    DESCRIPTION "Air flow switch alarm delay"
                    ::= { integerObjects 33 }

        -- 1.3.6.1.4.1.9839.2.1.3.34
        int34 OBJECT-TYPE
                    SYNTAX Integer32 (-32767..32767)
                    UNITS "N/A"
                    MAX-ACCESS read-write
                    STATUS current
                    DESCRIPTION "Delivery fan shutdown delay"
                    ::= { integerObjects 34 }

        -- 1.3.6.1.4.1.9839.2.1.3.35
        int35 OBJECT-TYPE
                    SYNTAX Integer32 (-32767..32767)
                    UNITS "N/A"
                    MAX-ACCESS read-write
                    STATUS current
                    DESCRIPTION "Delivery fan start-up delay"
                    ::= { integerObjects 35 }

        -- 1.3.6.1.4.1.9839.2.1.3.36
        int36 OBJECT-TYPE
                    SYNTAX Integer32 (-32767..32767)
                    UNITS "N/A"
                    MAX-ACCESS read-write
                    STATUS current
                    DESCRIPTION "Non-serious alarm 7 relay activation delay"
                    ::= { integerObjects 36 }

        -- 1.3.6.1.4.1.9839.2.1.3.37
        int37 OBJECT-TYPE
                    SYNTAX Integer32 (-32767..32767)
                    UNITS "N/A"
                    MAX-ACCESS read-write
                    STATUS current
                    DESCRIPTION "Serious alarm 8 relay activation delay"
                    ::= { integerObjects 37 }

        -- 1.3.6.1.4.1.9839.2.1.3.38
        int38 OBJECT-TYPE
                    SYNTAX Integer32 (-32767..32767)
                    UNITS "N/A"
                    MAX-ACCESS read-write
                    STATUS current
                    DESCRIPTION "Water flow switch alarm on start-up delay"
                    ::= { integerObjects 38 }

        -- 1.3.6.1.4.1.9839.2.1.3.39
        int39 OBJECT-TYPE
                    SYNTAX Integer32 (-32767..32767)
                    UNITS "N/A"
                    MAX-ACCESS read-write
                    STATUS current
                    DESCRIPTION "Delay between start-up of different compressors"
                    ::= { integerObjects 39 }

        -- 1.3.6.1.4.1.9839.2.1.3.40
        int40 OBJECT-TYPE
                    SYNTAX Integer32 (-32767..32767)
                    UNITS "N/A"
                    MAX-ACCESS read-write
                    STATUS current
                    DESCRIPTION "Heater activation delay"
                    ::= { integerObjects 40 }

        -- 1.3.6.1.4.1.9839.2.1.3.41
        int41 OBJECT-TYPE
                    SYNTAX Integer32 (-32767..32767)
                    UNITS "N/A"
                    MAX-ACCESS read-write
                    STATUS current
                    DESCRIPTION "Low pressure alarm delay"
                    ::= { integerObjects 41 }

        -- 1.3.6.1.4.1.9839.2.1.3.42
        int42 OBJECT-TYPE
                    SYNTAX Integer32 (-32767..32767)
                    UNITS "N/A"
                    MAX-ACCESS read-write
                    STATUS current
                    DESCRIPTION "P+I regulation integration time"
                    ::= { integerObjects 42 }

        -- 1.3.6.1.4.1.9839.2.1.3.43
        int43 OBJECT-TYPE
                    SYNTAX Integer32 (-32767..32767)
                    UNITS "N/A"
                    MAX-ACCESS read-write
                    STATUS current
                    DESCRIPTION "Minimum compressor shutdown duration"
                    ::= { integerObjects 43 }

        -- 1.3.6.1.4.1.9839.2.1.3.44
        int44 OBJECT-TYPE
                    SYNTAX Integer32 (-32767..32767)
                    UNITS "N/A"
                    MAX-ACCESS read-write
                    STATUS current
                    DESCRIPTION "Minimum compressor start-up duration"
                    ::= { integerObjects 44 }

        -- 1.3.6.1.4.1.9839.2.1.3.45
        int45 OBJECT-TYPE
                    SYNTAX Integer32 (-32767..32767)
                    UNITS "N/A"
                    MAX-ACCESS read-write
                    STATUS current
                    DESCRIPTION "Delay between compressor start-ups"
                    ::= { integerObjects 45 }

        -- 1.3.6.1.4.1.9839.2.1.3.46
        int46 OBJECT-TYPE
                    SYNTAX Integer32 (-32767..32767)
                    UNITS "N/A"
                    MAX-ACCESS read-write
                    STATUS current
                    DESCRIPTION "Capacity step activation delay"
                    ::= { integerObjects 46 }

        -- 1.3.6.1.4.1.9839.2.1.3.47
        int47 OBJECT-TYPE
                    SYNTAX Integer32 (-32767..32767)
                    UNITS "N/A"
                    MAX-ACCESS read-write
                    STATUS current
                    DESCRIPTION "3-point valve excursion time (Valve 1)"
                    ::= { integerObjects 47 }

        -- 1.3.6.1.4.1.9839.2.1.3.48
        int48 OBJECT-TYPE
                    SYNTAX Integer32 (-32767..32767)
                    UNITS "N/A"
                    MAX-ACCESS read-write
                    STATUS current
                    DESCRIPTION "Humidity high/low temperature alarms delay"
                    ::= { integerObjects 48 }

        -- 1.3.6.1.4.1.9839.2.1.3.49
        int49 OBJECT-TYPE
                    SYNTAX Integer32 (-32767..32767)
                    UNITS "N/A"
                    MAX-ACCESS read-write
                    STATUS current
                    DESCRIPTION "High conductivity pre-alarm threshold"
                    ::= { integerObjects 49 }

        -- 1.3.6.1.4.1.9839.2.1.3.50
        int50 OBJECT-TYPE
                    SYNTAX Integer32 (-32767..32767)
                    UNITS "N/A"
                    MAX-ACCESS read-write
                    STATUS current
                    DESCRIPTION "High conductivity alarm threshold"
                    ::= { integerObjects 50 }

        -- 1.3.6.1.4.1.9839.2.1.3.51
        int51 OBJECT-TYPE
                    SYNTAX Integer32 (-32767..32767)
                    UNITS "N/A"
                    MAX-ACCESS read-write
                    STATUS current
                    DESCRIPTION "Humidifier type"
                    ::= { integerObjects 51 }

        -- 1.3.6.1.4.1.9839.2.1.3.52
        int52 OBJECT-TYPE
                    SYNTAX Integer32 (-32767..32767)
                    UNITS "N/A"
                    MAX-ACCESS read-write
                    STATUS current
                    DESCRIPTION "On-Off time zone start hour F1-1"
                    ::= { integerObjects 52 }

        -- 1.3.6.1.4.1.9839.2.1.3.53
        int53 OBJECT-TYPE
                    SYNTAX Integer32 (-32767..32767)
                    UNITS "N/A"
                    MAX-ACCESS read-write
                    STATUS current
                    DESCRIPTION "On-Off time zone start minutes F1-1"
                    ::= { integerObjects 53 }

        -- 1.3.6.1.4.1.9839.2.1.3.54
        int54 OBJECT-TYPE
                    SYNTAX Integer32 (-32767..32767)
                    UNITS "N/A"
                    MAX-ACCESS read-write
                    STATUS current
                    DESCRIPTION "On-Off time zone end hour F1-1"
                    ::= { integerObjects 54 }

        -- 1.3.6.1.4.1.9839.2.1.3.55
        int55 OBJECT-TYPE
                    SYNTAX Integer32 (-32767..32767)
                    UNITS "N/A"
                    MAX-ACCESS read-write
                    STATUS current
                    DESCRIPTION "On-Off time zone end minutes F1-1"
                    ::= { integerObjects 55 }

        -- 1.3.6.1.4.1.9839.2.1.3.56
        int56 OBJECT-TYPE
                    SYNTAX Integer32 (-32767..32767)
                    UNITS "N/A"
                    MAX-ACCESS read-write
                    STATUS current
                    DESCRIPTION "On-Off time zone start hour F1-2"
                    ::= { integerObjects 56 }

        -- 1.3.6.1.4.1.9839.2.1.3.57
        int57 OBJECT-TYPE
                    SYNTAX Integer32 (-32767..32767)
                    UNITS "N/A"
                    MAX-ACCESS read-write
                    STATUS current
                    DESCRIPTION "On-Off time zone start minutes F1-2"
                    ::= { integerObjects 57 }

        -- 1.3.6.1.4.1.9839.2.1.3.58
        int58 OBJECT-TYPE
                    SYNTAX Integer32 (-32767..32767)
                    UNITS "N/A"
                    MAX-ACCESS read-write
                    STATUS current
                    DESCRIPTION "On-Off time zone end hour F1-2"
                    ::= { integerObjects 58 }

        -- 1.3.6.1.4.1.9839.2.1.3.59
        int59 OBJECT-TYPE
                    SYNTAX Integer32 (-32767..32767)
                    UNITS "N/A"
                    MAX-ACCESS read-write
                    STATUS current
                    DESCRIPTION "On-Off time zone end minutes F1-2"
                    ::= { integerObjects 59 }

        -- 1.3.6.1.4.1.9839.2.1.3.60
        int60 OBJECT-TYPE
                    SYNTAX Integer32 (-32767..32767)
                    UNITS "N/A"
                    MAX-ACCESS read-write
                    STATUS current
                    DESCRIPTION "On-Off time zone start hour F2"
                    ::= { integerObjects 60 }

        -- 1.3.6.1.4.1.9839.2.1.3.61
        int61 OBJECT-TYPE
                    SYNTAX Integer32 (-32767..32767)
                    UNITS "N/A"
                    MAX-ACCESS read-write
                    STATUS current
                    DESCRIPTION "On-Off time zone start minutes F2"
                    ::= { integerObjects 61 }

        -- 1.3.6.1.4.1.9839.2.1.3.62
        int62 OBJECT-TYPE
                    SYNTAX Integer32 (-32767..32767)
                    UNITS "N/A"
                    MAX-ACCESS read-write
                    STATUS current
                    DESCRIPTION "On-Off time zone end hour  F2"
                    ::= { integerObjects 62 }

        -- 1.3.6.1.4.1.9839.2.1.3.63
        int63 OBJECT-TYPE
                    SYNTAX Integer32 (-32767..32767)
                    UNITS "N/A"
                    MAX-ACCESS read-write
                    STATUS current
                    DESCRIPTION "On-Off time zone end minutes F2"
                    ::= { integerObjects 63 }

        -- 1.3.6.1.4.1.9839.2.1.3.64
        int64 OBJECT-TYPE
                    SYNTAX Integer32 (-32767..32767)
                    UNITS "N/A"
                    MAX-ACCESS read-write
                    STATUS current
                    DESCRIPTION "Temperature time zone start hour Z1"
                    ::= { integerObjects 64 }

        -- 1.3.6.1.4.1.9839.2.1.3.65
        int65 OBJECT-TYPE
                    SYNTAX Integer32 (-32767..32767)
                    UNITS "N/A"
                    MAX-ACCESS read-write
                    STATUS current
                    DESCRIPTION "Temperature time zone start minutes Z1"
                    ::= { integerObjects 65 }

        -- 1.3.6.1.4.1.9839.2.1.3.66
        int66 OBJECT-TYPE
                    SYNTAX Integer32 (-32767..32767)
                    UNITS "N/A"
                    MAX-ACCESS read-write
                    STATUS current
                    DESCRIPTION "Hour for start of time zone for temperature Z2"
                    ::= { integerObjects 66 }

        -- 1.3.6.1.4.1.9839.2.1.3.67
        int67 OBJECT-TYPE
                    SYNTAX Integer32 (-32767..32767)
                    UNITS "N/A"
                    MAX-ACCESS read-write
                    STATUS current
                    DESCRIPTION "Minutes for start of time zone for temperature Z2"
                    ::= { integerObjects 67 }

        -- 1.3.6.1.4.1.9839.2.1.3.68
        int68 OBJECT-TYPE
                    SYNTAX Integer32 (-32767..32767)
                    UNITS "N/A"
                    MAX-ACCESS read-write
                    STATUS current
                    DESCRIPTION "Hour for start of time zone for temperature Z3"
                    ::= { integerObjects 68 }

        -- 1.3.6.1.4.1.9839.2.1.3.69
        int69 OBJECT-TYPE
                    SYNTAX Integer32 (-32767..32767)
                    UNITS "N/A"
                    MAX-ACCESS read-write
                    STATUS current
                    DESCRIPTION "Minutes for start of time zone for temperature Z3"
                    ::= { integerObjects 69 }

        -- 1.3.6.1.4.1.9839.2.1.3.70
        int70 OBJECT-TYPE
                    SYNTAX Integer32 (-32767..32767)
                    UNITS "N/A"
                    MAX-ACCESS read-write
                    STATUS current
                    DESCRIPTION "Hour for start of time zone for temperature Z4"
                    ::= { integerObjects 70 }

        -- 1.3.6.1.4.1.9839.2.1.3.71
        int71 OBJECT-TYPE
                    SYNTAX Integer32 (-32767..32767)
                    UNITS "N/A"
                    MAX-ACCESS read-write
                    STATUS current
                    DESCRIPTION "Minutes for start of time zone for temperature Z4"
                    ::= { integerObjects 71 }

        -- 1.3.6.1.4.1.9839.2.1.3.72
        int72 OBJECT-TYPE
                    SYNTAX Integer32 (-32767..32767)
                    UNITS "N/A"
                    MAX-ACCESS read-write
                    STATUS current
                    DESCRIPTION "Hour for start of time zone for humidity Z1"
                    ::= { integerObjects 72 }

        -- 1.3.6.1.4.1.9839.2.1.3.73
        int73 OBJECT-TYPE
                    SYNTAX Integer32 (-32767..32767)
                    UNITS "N/A"
                    MAX-ACCESS read-write
                    STATUS current
                    DESCRIPTION "Minutes for start of time zone for humidity Z1"
                    ::= { integerObjects 73 }

        -- 1.3.6.1.4.1.9839.2.1.3.74
        int74 OBJECT-TYPE
                    SYNTAX Integer32 (-32767..32767)
                    UNITS "N/A"
                    MAX-ACCESS read-write
                    STATUS current
                    DESCRIPTION "Hour for start of time zone for humidity Z2"
                    ::= { integerObjects 74 }

        -- 1.3.6.1.4.1.9839.2.1.3.75
        int75 OBJECT-TYPE
                    SYNTAX Integer32 (-32767..32767)
                    UNITS "N/A"
                    MAX-ACCESS read-write
                    STATUS current
                    DESCRIPTION "Minutes for start of time zone for humidity Z2"
                    ::= { integerObjects 75 }

        -- 1.3.6.1.4.1.9839.2.1.3.76
        int76 OBJECT-TYPE
                    SYNTAX Integer32 (-32767..32767)
                    UNITS "N/A"
                    MAX-ACCESS read-write
                    STATUS current
                    DESCRIPTION "Hour for start of time zone for humidity Z3"
                    ::= { integerObjects 76 }

        -- 1.3.6.1.4.1.9839.2.1.3.77
        int77 OBJECT-TYPE
                    SYNTAX Integer32 (-32767..32767)
                    UNITS "N/A"
                    MAX-ACCESS read-write
                    STATUS current
                    DESCRIPTION "Minutes for start of time zone for humidity Z3"
                    ::= { integerObjects 77 }

        -- 1.3.6.1.4.1.9839.2.1.3.78
        int78 OBJECT-TYPE
                    SYNTAX Integer32 (-32767..32767)
                    UNITS "N/A"
                    MAX-ACCESS read-write
                    STATUS current
                    DESCRIPTION "Hour for start of time zone for humidity Z4"
                    ::= { integerObjects 78 }

        -- 1.3.6.1.4.1.9839.2.1.3.79
        int79 OBJECT-TYPE
                    SYNTAX Integer32 (-32767..32767)
                    UNITS "N/A"
                    MAX-ACCESS read-write
                    STATUS current
                    DESCRIPTION "Minutes for start of time zone for humidity Z4"
                    ::= { integerObjects 79 }

        -- 1.3.6.1.4.1.9839.2.1.3.80
        int80 OBJECT-TYPE
                    SYNTAX Integer32 (-32767..32767)
                    UNITS "N/A"
                    MAX-ACCESS read-write
                    STATUS current
                    DESCRIPTION "On-Off Time zone selection Monday (0=F1; 1=F2; 2=F3; 3=F4)"
                    ::= { integerObjects 80 }

        -- 1.3.6.1.4.1.9839.2.1.3.81
        int81 OBJECT-TYPE
                    SYNTAX Integer32 (-32767..32767)
                    UNITS "N/A"
                    MAX-ACCESS read-write
                    STATUS current
                    DESCRIPTION "On-Off Time zone selection Tuesday (0=F1; 1=F2; 2=F3; 3=F4)"
                    ::= { integerObjects 81 }

        -- 1.3.6.1.4.1.9839.2.1.3.82
        int82 OBJECT-TYPE
                    SYNTAX Integer32 (-32767..32767)
                    UNITS "N/A"
                    MAX-ACCESS read-write
                    STATUS current
                    DESCRIPTION "On-Off Time zone selection Wednesday (0=F1; 1=F2; 2=F3; 3=F4)"
                    ::= { integerObjects 82 }

        -- 1.3.6.1.4.1.9839.2.1.3.83
        int83 OBJECT-TYPE
                    SYNTAX Integer32 (-32767..32767)
                    UNITS "N/A"
                    MAX-ACCESS read-write
                    STATUS current
                    DESCRIPTION "On-Off Time zone selection Thursday (0=F1; 1=F2; 2=F3; 3=F4)"
                    ::= { integerObjects 83 }

        -- 1.3.6.1.4.1.9839.2.1.3.84
        int84 OBJECT-TYPE
                    SYNTAX Integer32 (-32767..32767)
                    UNITS "N/A"
                    MAX-ACCESS read-write
                    STATUS current
                    DESCRIPTION "On-Off Time zone selection Friday (0=F1; 1=F2; 2=F3; 3=F4)"
                    ::= { integerObjects 84 }

        -- 1.3.6.1.4.1.9839.2.1.3.85
        int85 OBJECT-TYPE
                    SYNTAX Integer32 (-32767..32767)
                    UNITS "N/A"
                    MAX-ACCESS read-write
                    STATUS current
                    DESCRIPTION "On-Off Time zone selection Saturday (0=F1; 1=F2; 2=F3; 3=F4)"
                    ::= { integerObjects 85 }

        -- 1.3.6.1.4.1.9839.2.1.3.86
        int86 OBJECT-TYPE
                    SYNTAX Integer32 (-32767..32767)
                    UNITS "N/A"
                    MAX-ACCESS read-write
                    STATUS current
                    DESCRIPTION "On-Off Time zone selection Sunday (0=F1; 1=F2; 2=F3; 3=F4)"
                    ::= { integerObjects 86 }

        -- 1.3.6.1.4.1.9839.2.1.3.87
        int87 OBJECT-TYPE
                    SYNTAX Integer32 (-32767..32767)
                    UNITS "N/A"
                    MAX-ACCESS read-write
                    STATUS current
                    DESCRIPTION "Condensation fan Speed-up time"
                    ::= { integerObjects 87 }

        -- 1.3.6.1.4.1.9839.2.1.3.88
        int88 OBJECT-TYPE
                    SYNTAX Integer32 (-32767..32767)
                    UNITS "N/A"
                    MAX-ACCESS read-write
                    STATUS current
                    DESCRIPTION "Compressor 1 operating hours threshold"
                    ::= { integerObjects 88 }

        -- 1.3.6.1.4.1.9839.2.1.3.89
        int89 OBJECT-TYPE
                    SYNTAX Integer32 (-32767..32767)
                    UNITS "N/A"
                    MAX-ACCESS read-write
                    STATUS current
                    DESCRIPTION "Compressor 2 operating hours threshold"
                    ::= { integerObjects 89 }

        -- 1.3.6.1.4.1.9839.2.1.3.90
        int90 OBJECT-TYPE
                    SYNTAX Integer32 (-32767..32767)
                    UNITS "N/A"
                    MAX-ACCESS read-write
                    STATUS current
                    DESCRIPTION "Humidifier operating hours threshold"
                    ::= { integerObjects 90 }

        -- 1.3.6.1.4.1.9839.2.1.3.91
        int91 OBJECT-TYPE
                    SYNTAX Integer32 (-32767..32767)
                    UNITS "N/A"
                    MAX-ACCESS read-write
                    STATUS current
                    DESCRIPTION "Fan operating hours threshold"
                    ::= { integerObjects 91 }

        -- 1.3.6.1.4.1.9839.2.1.3.92
        int92 OBJECT-TYPE
                    SYNTAX Integer32 (-32767..32767)
                    UNITS "N/A"
                    MAX-ACCESS read-write
                    STATUS current
                    DESCRIPTION "Rotation mode of units on pLAN network"
                    ::= { integerObjects 92 }

        -- 1.3.6.1.4.1.9839.2.1.3.93
        int93 OBJECT-TYPE
                    SYNTAX Integer32 (-32767..32767)
                    UNITS "N/A"
                    MAX-ACCESS read-write
                    STATUS current
                    DESCRIPTION "Ambient high temperature override delays"
                    ::= { integerObjects 93 }

        -- 1.3.6.1.4.1.9839.2.1.3.94
        int94 OBJECT-TYPE
                    SYNTAX Integer32 (-32767..32767)
                    UNITS "N/A"
                    MAX-ACCESS read-write
                    STATUS current
                    DESCRIPTION "Ambient low temperature override delays"
                    ::= { integerObjects 94 }

        -- 1.3.6.1.4.1.9839.2.1.3.95
        int95 OBJECT-TYPE
                    SYNTAX Integer32 (-32767..32767)
                    UNITS "N/A"
                    MAX-ACCESS read-write
                    STATUS current
                    DESCRIPTION "Automatic rotation day interval"
                    ::= { integerObjects 95 }

        -- 1.3.6.1.4.1.9839.2.1.3.96
        int96 OBJECT-TYPE
                    SYNTAX Integer32 (-32767..32767)
                    UNITS "N/A"
                    MAX-ACCESS read-write
                    STATUS current
                    DESCRIPTION "Automatic rotation hour"
                    ::= { integerObjects 96 }

        -- 1.3.6.1.4.1.9839.2.1.3.97
        int97 OBJECT-TYPE
                    SYNTAX Integer32 (-32767..32767)
                    UNITS "N/A"
                    MAX-ACCESS read-write
                    STATUS current
                    DESCRIPTION "Automatic rotation minutes"
                    ::= { integerObjects 97 }

        -- 1.3.6.1.4.1.9839.2.1.3.98
        int98 OBJECT-TYPE
                    SYNTAX Integer32 (-32767..32767)
                    UNITS "N/A"
                    MAX-ACCESS read-write
                    STATUS current
                    DESCRIPTION "Number of units in Stand-by mode"
                    ::= { integerObjects 98 }

        -- 1.3.6.1.4.1.9839.2.1.3.99
        int99 OBJECT-TYPE
                    SYNTAX Integer32 (-32767..32767)
                    UNITS "N/A"
                    MAX-ACCESS read-write
                    STATUS current
                    DESCRIPTION "Interval of automation rotation of units on pLAN network"
                    ::= { integerObjects 99 }

        -- 1.3.6.1.4.1.9839.2.1.3.100
        int100 OBJECT-TYPE
                    SYNTAX Integer32 (-32767..32767)
                    UNITS "N/A"
                    MAX-ACCESS read-write
                    STATUS current
                    DESCRIPTION "PLAN participation class board 1  (0=not present ; 1=present/no rotat.; 2=present/rotation)"
                    ::= { integerObjects 100 }

        -- 1.3.6.1.4.1.9839.2.1.3.101
        int101 OBJECT-TYPE
                    SYNTAX Integer32 (-32767..32767)
                    UNITS "N/A"
                    MAX-ACCESS read-write
                    STATUS current
                    DESCRIPTION "PLAN participation class board 2  (0=present/Rotat.; 1=present/no rotat.; 2=not present )"
                    ::= { integerObjects 101 }

        -- 1.3.6.1.4.1.9839.2.1.3.102
        int102 OBJECT-TYPE
                    SYNTAX Integer32 (-32767..32767)
                    UNITS "N/A"
                    MAX-ACCESS read-write
                    STATUS current
                    DESCRIPTION "PLAN participation class board 3  (0=present/Rotat.; 1=present/no rotat.; 2=not present )"
                    ::= { integerObjects 102 }

        -- 1.3.6.1.4.1.9839.2.1.3.103
        int103 OBJECT-TYPE
                    SYNTAX Integer32 (-32767..32767)
                    UNITS "N/A"
                    MAX-ACCESS read-write
                    STATUS current
                    DESCRIPTION "PLAN participation class board 4  (0=present/Rotat.; 1=present/no rotat.; 2=not present )"
                    ::= { integerObjects 103 }

        -- 1.3.6.1.4.1.9839.2.1.3.104
        int104 OBJECT-TYPE
                    SYNTAX Integer32 (-32767..32767)
                    UNITS "N/A"
                    MAX-ACCESS read-write
                    STATUS current
                    DESCRIPTION "PLAN participation class board 5  (0=present/Rotat.; 1=present/no rotat.; 2=not present )"
                    ::= { integerObjects 104 }

        -- 1.3.6.1.4.1.9839.2.1.3.105
        int105 OBJECT-TYPE
                    SYNTAX Integer32 (-32767..32767)
                    UNITS "N/A"
                    MAX-ACCESS read-write
                    STATUS current
                    DESCRIPTION "PLAN participation class board 6  (0=present/Rotat.; 1=present/no rotat.; 2=not present )"
                    ::= { integerObjects 105 }

        -- 1.3.6.1.4.1.9839.2.1.3.106
        int106 OBJECT-TYPE
                    SYNTAX Integer32 (-32767..32767)
                    UNITS "N/A"
                    MAX-ACCESS read-write
                    STATUS current
                    DESCRIPTION "PLAN participation class board 7  (0=present/Rotat.; 1=present/no rotat.; 2=not present )"
                    ::= { integerObjects 106 }

        -- 1.3.6.1.4.1.9839.2.1.3.107
        int107 OBJECT-TYPE
                    SYNTAX Integer32 (-32767..32767)
                    UNITS "N/A"
                    MAX-ACCESS read-write
                    STATUS current
                    DESCRIPTION "PLAN participation class board 8  (0=present/Rotat.; 1=present/no rotat.; 2=not present )"
                    ::= { integerObjects 107 }

        -- 1.3.6.1.4.1.9839.2.1.3.108
        int108 OBJECT-TYPE
                    SYNTAX Integer32 (-32767..32767)
                    UNITS "N/A"
                    MAX-ACCESS read-write
                    STATUS current
                    DESCRIPTION "PLAN participation class board 9  (0=present/Rotat.; 1=present/no rotat.; 2=not present )"
                    ::= { integerObjects 108 }

        -- 1.3.6.1.4.1.9839.2.1.3.109
        int109 OBJECT-TYPE
                    SYNTAX Integer32 (-32767..32767)
                    UNITS "N/A"
                    MAX-ACCESS read-write
                    STATUS current
                    DESCRIPTION "PLAN participation class board 10  (0=present/Rotat.; 1=present/no rotat.; 2=not present )"
                    ::= { integerObjects 109 }

        -- 1.3.6.1.4.1.9839.2.1.3.110
        int110 OBJECT-TYPE
                    SYNTAX Integer32 (-32767..32767)
                    UNITS "N/A"
                    MAX-ACCESS read-write
                    STATUS current
                    DESCRIPTION "PLAN participation class board 11  (0=present/Rotat.; 1=present/no rotat.; 2=not present )"
                    ::= { integerObjects 110 }

        -- 1.3.6.1.4.1.9839.2.1.3.111
        int111 OBJECT-TYPE
                    SYNTAX Integer32 (-32767..32767)
                    UNITS "N/A"
                    MAX-ACCESS read-write
                    STATUS current
                    DESCRIPTION "PLAN participation class board 12  (0=present/Rotat.; 1=present/no rotat.; 2=not present )"
                    ::= { integerObjects 111 }

        -- 1.3.6.1.4.1.9839.2.1.3.112
        int112 OBJECT-TYPE
                    SYNTAX Integer32 (-32767..32767)
                    UNITS "N/A"
                    MAX-ACCESS read-write
                    STATUS current
                    DESCRIPTION "PLAN participation class board 13  (0=present/Rotat.; 1=present/no rotat.; 2=not present )"
                    ::= { integerObjects 112 }

        -- 1.3.6.1.4.1.9839.2.1.3.113
        int113 OBJECT-TYPE
                    SYNTAX Integer32 (-32767..32767)
                    UNITS "N/A"
                    MAX-ACCESS read-write
                    STATUS current
                    DESCRIPTION "PLAN participation class board 14  (0=present/Rotat.; 1=present/no rotat.; 2=not present )"
                    ::= { integerObjects 113 }

        -- 1.3.6.1.4.1.9839.2.1.3.114
        int114 OBJECT-TYPE
                    SYNTAX Integer32 (-32767..32767)
                    UNITS "N/A"
                    MAX-ACCESS read-write
                    STATUS current
                    DESCRIPTION "PLAN participation class board 815 (0=present/Rotat.; 1=present/no rotat.; 2=not present )"
                    ::= { integerObjects 114 }

        -- 1.3.6.1.4.1.9839.2.1.3.115
        int115 OBJECT-TYPE
                    SYNTAX Integer32 (-32767..32767)
                    UNITS "N/A"
                    MAX-ACCESS read-write
                    STATUS current
                    DESCRIPTION "PLAN participation class board 16  (0=present/Rotat.; 1=present/no rotat.; 2=not present )"
                    ::= { integerObjects 115 }

        -- 1.3.6.1.4.1.9839.2.1.3.116
        int116 OBJECT-TYPE
                    SYNTAX Integer32 (-32767..32767)
                    UNITS "N/A"
                    MAX-ACCESS read-only
                    STATUS current
                    DESCRIPTION "Driver 1 valve position"
                    ::= { integerObjects 116 }

        -- 1.3.6.1.4.1.9839.2.1.3.117
        int117 OBJECT-TYPE
                    SYNTAX Integer32 (-32767..32767)
                    UNITS "N/A"
                    MAX-ACCESS read-only
                    STATUS current
                    DESCRIPTION "Driver 2 valve position"
                    ::= { integerObjects 117 }

        -- 1.3.6.1.4.1.9839.2.1.3.118
        int118 OBJECT-TYPE
                    SYNTAX Integer32 (-32767..32767)
                    UNITS "N/A"
                    MAX-ACCESS read-write
                    STATUS current
                    DESCRIPTION "Start-up with delivery damper delay"
                    ::= { integerObjects 118 }

        -- 1.3.6.1.4.1.9839.2.1.3.119
        int119 OBJECT-TYPE
                    SYNTAX Integer32 (-32767..32767)
                    UNITS "N/A"
                    MAX-ACCESS read-write
                    STATUS current
                    DESCRIPTION "Atmospheric pressure"
                    ::= { integerObjects 119 }

        -- 1.3.6.1.4.1.9839.2.1.3.120
        int120 OBJECT-TYPE
                    SYNTAX Integer32 (-32767..32767)
                    UNITS "N/A"
                    MAX-ACCESS read-write
                    STATUS current
                    DESCRIPTION "Efficiency delay"
                    ::= { integerObjects 120 }

        -- 1.3.6.1.4.1.9839.2.1.3.121
        int121 OBJECT-TYPE
                    SYNTAX Integer32 (-32767..32767)
                    UNITS "N/A"
                    MAX-ACCESS read-write
                    STATUS current
                    DESCRIPTION "High pressure alarm automatic reset attempts"
                    ::= { integerObjects 121 }

        -- 1.3.6.1.4.1.9839.2.1.3.122
        int122 OBJECT-TYPE
                    SYNTAX Integer32 (-32767..32767)
                    UNITS "N/A"
                    MAX-ACCESS read-write
                    STATUS current
                    DESCRIPTION "High pressure alarm automatic reset time"
                    ::= { integerObjects 122 }

        -- 1.3.6.1.4.1.9839.2.1.3.123
        int123 OBJECT-TYPE
                    SYNTAX Integer32 (-32767..32767)
                    UNITS "N/A"
                    MAX-ACCESS read-write
                    STATUS current
                    DESCRIPTION "Low pressure alarm automatic reset attempts"
                    ::= { integerObjects 123 }

        -- 1.3.6.1.4.1.9839.2.1.3.124
        int124 OBJECT-TYPE
                    SYNTAX Integer32 (-32767..32767)
                    UNITS "N/A"
                    MAX-ACCESS read-write
                    STATUS current
                    DESCRIPTION "Low pressure alarm automatic reset time"
                    ::= { integerObjects 124 }

        -- 1.3.6.1.4.1.9839.2.1.3.125
        int125 OBJECT-TYPE
                    SYNTAX Integer32 (-32767..32767)
                    UNITS "N/A"
                    MAX-ACCESS read-write
                    STATUS current
                    DESCRIPTION "Recovery management type"
                    ::= { integerObjects 125 }

        -- 1.3.6.1.4.1.9839.2.1.3.126
        int126 OBJECT-TYPE
                    SYNTAX Integer32 (-32767..32767)
                    UNITS "N/A"
                    MAX-ACCESS read-write
                    STATUS current
                    DESCRIPTION "Compressors ON delay with recovery in dehumid. (DC regulation)"
                    ::= { integerObjects 126 }

        -- 1.3.6.1.4.1.9839.2.1.3.127
        int127 OBJECT-TYPE
                    SYNTAX Integer32 (-32767..32767)
                    UNITS "N/A"
                    MAX-ACCESS read-write
                    STATUS current
                    DESCRIPTION "Compressor rotation enable"
                    ::= { integerObjects 127 }

        -- 1.3.6.1.4.1.9839.2.1.3.128
        int128 OBJECT-TYPE
                    SYNTAX Integer32 (-32767..32767)
                    UNITS "N/A"
                    MAX-ACCESS read-write
                    STATUS current
                    DESCRIPTION "Residual time on periodic cylinder drain"
                    ::= { integerObjects 128 }

        -- 1.3.6.1.4.1.9839.2.1.3.129
        int129 OBJECT-TYPE
                    SYNTAX Integer32 (-32767..32767)
                    UNITS "N/A"
                    MAX-ACCESS read-write
                    STATUS current
                    DESCRIPTION "Water flow in running status alarm delay"
                    ::= { integerObjects 129 }


	
	END

--
-- CAREL-flbbomcz0e.MIB
--
