--
-- CAREL-mod_ch_18.MIB
-- MIB generated by CAREL
-- Tuesday, 16 November 2010
--

    CAREL-mod_ch_18-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        mod_ch_18MIB MODULE-IDENTITY
      		LAST-UPDATED  "201011161635Z"		-- November 16, 2010 at 16:35 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the mod_ch_18 device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { mod_ch_18MIB 1 }

        -- 1.3.6.1.4.1.9839.2.1.1.1
        syson_s OBJECT-TYPE
                    SYNTAX Integer32 (0..1)
                    UNITS "N/A"
                    MAX-ACCESS read-only
                    STATUS current
                    DESCRIPTION "Unit On / Off"
                    ::= { digitalObjects 1 }

        -- 1.3.6.1.4.1.9839.2.1.1.10
        dout_1 OBJECT-TYPE
                    SYNTAX Integer32 (0..1)
                    UNITS "N/A"
                    MAX-ACCESS read-only
                    STATUS current
                    DESCRIPTION "Digital output n.1"
                    ::= { digitalObjects 10 }

        -- 1.3.6.1.4.1.9839.2.1.1.11
        dout_2 OBJECT-TYPE
                    SYNTAX Integer32 (0..1)
                    UNITS "N/A"
                    MAX-ACCESS read-only
                    STATUS current
                    DESCRIPTION "Digital output n.2"
                    ::= { digitalObjects 11 }

        -- 1.3.6.1.4.1.9839.2.1.1.12
        dout_3 OBJECT-TYPE
                    SYNTAX Integer32 (0..1)
                    UNITS "N/A"
                    MAX-ACCESS read-only
                    STATUS current
                    DESCRIPTION "Digital output n.3"
                    ::= { digitalObjects 12 }

        -- 1.3.6.1.4.1.9839.2.1.1.13
        dout_4 OBJECT-TYPE
                    SYNTAX Integer32 (0..1)
                    UNITS "N/A"
                    MAX-ACCESS read-only
                    STATUS current
                    DESCRIPTION "Digital output n.4"
                    ::= { digitalObjects 13 }

        -- 1.3.6.1.4.1.9839.2.1.1.14
        dout_5 OBJECT-TYPE
                    SYNTAX Integer32 (0..1)
                    UNITS "N/A"
                    MAX-ACCESS read-only
                    STATUS current
                    DESCRIPTION "Digital output n.5"
                    ::= { digitalObjects 14 }

        -- 1.3.6.1.4.1.9839.2.1.1.15
        dout_6 OBJECT-TYPE
                    SYNTAX Integer32 (0..1)
                    UNITS "N/A"
                    MAX-ACCESS read-only
                    STATUS current
                    DESCRIPTION "Digital output n.6"
                    ::= { digitalObjects 15 }

        -- 1.3.6.1.4.1.9839.2.1.1.16
        dout_7 OBJECT-TYPE
                    SYNTAX Integer32 (0..1)
                    UNITS "N/A"
                    MAX-ACCESS read-only
                    STATUS current
                    DESCRIPTION "Digital output n.7"
                    ::= { digitalObjects 16 }

        -- 1.3.6.1.4.1.9839.2.1.1.17
        dout_8 OBJECT-TYPE
                    SYNTAX Integer32 (0..1)
                    UNITS "N/A"
                    MAX-ACCESS read-only
                    STATUS current
                    DESCRIPTION "Digital output n.8"
                    ::= { digitalObjects 17 }

        -- 1.3.6.1.4.1.9839.2.1.1.18
        dout_9 OBJECT-TYPE
                    SYNTAX Integer32 (0..1)
                    UNITS "N/A"
                    MAX-ACCESS read-only
                    STATUS current
                    DESCRIPTION "Digital output n.9"
                    ::= { digitalObjects 18 }

        -- 1.3.6.1.4.1.9839.2.1.1.19
        dout_10 OBJECT-TYPE
                    SYNTAX Integer32 (0..1)
                    UNITS "N/A"
                    MAX-ACCESS read-only
                    STATUS current
                    DESCRIPTION "Digital output n.10"
                    ::= { digitalObjects 19 }

        -- 1.3.6.1.4.1.9839.2.1.1.20
        dout_11 OBJECT-TYPE
                    SYNTAX Integer32 (0..1)
                    UNITS "N/A"
                    MAX-ACCESS read-only
                    STATUS current
                    DESCRIPTION "Digital output n.11"
                    ::= { digitalObjects 20 }

        -- 1.3.6.1.4.1.9839.2.1.1.21
        dout_12 OBJECT-TYPE
                    SYNTAX Integer32 (0..1)
                    UNITS "N/A"
                    MAX-ACCESS read-only
                    STATUS current
                    DESCRIPTION "Digital output n.12"
                    ::= { digitalObjects 21 }

        -- 1.3.6.1.4.1.9839.2.1.1.22
        dout_13 OBJECT-TYPE
                    SYNTAX Integer32 (0..1)
                    UNITS "N/A"
                    MAX-ACCESS read-only
                    STATUS current
                    DESCRIPTION "Digital output n.13"
                    ::= { digitalObjects 22 }

        -- 1.3.6.1.4.1.9839.2.1.1.23
        en_driver1 OBJECT-TYPE
                    SYNTAX Integer32 (0..1)
                    UNITS "N/A"
                    MAX-ACCESS read-only
                    STATUS current
                    DESCRIPTION "Enable Driver 1"
                    ::= { digitalObjects 23 }

        -- 1.3.6.1.4.1.9839.2.1.1.24
        en_driver2 OBJECT-TYPE
                    SYNTAX Integer32 (0..1)
                    UNITS "N/A"
                    MAX-ACCESS read-only
                    STATUS current
                    DESCRIPTION "Enable Driver 2"
                    ::= { digitalObjects 24 }

        -- 1.3.6.1.4.1.9839.2.1.1.25
        en_driver3 OBJECT-TYPE
                    SYNTAX Integer32 (0..1)
                    UNITS "N/A"
                    MAX-ACCESS read-only
                    STATUS current
                    DESCRIPTION "Enable Driver 3"
                    ::= { digitalObjects 25 }

        -- 1.3.6.1.4.1.9839.2.1.1.26
        en_driver4 OBJECT-TYPE
                    SYNTAX Integer32 (0..1)
                    UNITS "N/A"
                    MAX-ACCESS read-only
                    STATUS current
                    DESCRIPTION "Enable Driver 4"
                    ::= { digitalObjects 26 }

        -- 1.3.6.1.4.1.9839.2.1.1.27
        en_pump2 OBJECT-TYPE
                    SYNTAX Integer32 (0..1)
                    UNITS "N/A"
                    MAX-ACCESS read-only
                    STATUS current
                    DESCRIPTION "Enable second Pump"
                    ::= { digitalObjects 27 }

        -- 1.3.6.1.4.1.9839.2.1.1.28
        master OBJECT-TYPE
                    SYNTAX Integer32 (0..1)
                    UNITS "N/A"
                    MAX-ACCESS read-only
                    STATUS current
                    DESCRIPTION "Master mode"
                    ::= { digitalObjects 28 }

        -- 1.3.6.1.4.1.9839.2.1.1.29
        slave OBJECT-TYPE
                    SYNTAX Integer32 (0..1)
                    UNITS "N/A"
                    MAX-ACCESS read-only
                    STATUS current
                    DESCRIPTION "Slave mode"
                    ::= { digitalObjects 29 }

        -- 1.3.6.1.4.1.9839.2.1.1.30
        en_b1 OBJECT-TYPE
                    SYNTAX Integer32 (0..1)
                    UNITS "N/A"
                    MAX-ACCESS read-write
                    STATUS current
                    DESCRIPTION "Enable probe B1"
                    DEFVAL { 1 }
                    ::= { digitalObjects 30 }

        -- 1.3.6.1.4.1.9839.2.1.1.31
        en_b2 OBJECT-TYPE
                    SYNTAX Integer32 (0..1)
                    UNITS "N/A"
                    MAX-ACCESS read-write
                    STATUS current
                    DESCRIPTION "Enable probe B2"
                    DEFVAL { 1 }
                    ::= { digitalObjects 31 }

        -- 1.3.6.1.4.1.9839.2.1.1.32
        en_b3 OBJECT-TYPE
                    SYNTAX Integer32 (0..1)
                    UNITS "N/A"
                    MAX-ACCESS read-write
                    STATUS current
                    DESCRIPTION "Enable probe B3"
                    DEFVAL { 1 }
                    ::= { digitalObjects 32 }

        -- 1.3.6.1.4.1.9839.2.1.1.33
        en_b4 OBJECT-TYPE
                    SYNTAX Integer32 (0..1)
                    UNITS "N/A"
                    MAX-ACCESS read-write
                    STATUS current
                    DESCRIPTION "Enable probe B4"
                    DEFVAL { 1 }
                    ::= { digitalObjects 33 }

        -- 1.3.6.1.4.1.9839.2.1.1.34
        en_b5 OBJECT-TYPE
                    SYNTAX Integer32 (0..1)
                    UNITS "N/A"
                    MAX-ACCESS read-write
                    STATUS current
                    DESCRIPTION "Enable probe B5"
                    DEFVAL { 1 }
                    ::= { digitalObjects 34 }

        -- 1.3.6.1.4.1.9839.2.1.1.35
        en_b6 OBJECT-TYPE
                    SYNTAX Integer32 (0..1)
                    UNITS "N/A"
                    MAX-ACCESS read-write
                    STATUS current
                    DESCRIPTION "Enable probe B6"
                    DEFVAL { 1 }
                    ::= { digitalObjects 35 }

        -- 1.3.6.1.4.1.9839.2.1.1.36
        en_b7 OBJECT-TYPE
                    SYNTAX Integer32 (0..1)
                    UNITS "N/A"
                    MAX-ACCESS read-write
                    STATUS current
                    DESCRIPTION "Enable probe B7"
                    DEFVAL { 1 }
                    ::= { digitalObjects 36 }

        -- 1.3.6.1.4.1.9839.2.1.1.37
        en_b8 OBJECT-TYPE
                    SYNTAX Integer32 (0..1)
                    UNITS "N/A"
                    MAX-ACCESS read-write
                    STATUS current
                    DESCRIPTION "Enable probe B8"
                    DEFVAL { 1 }
                    ::= { digitalObjects 37 }

        -- 1.3.6.1.4.1.9839.2.1.1.38
        en_manag_fancoils OBJECT-TYPE
                    SYNTAX Integer32 (0..1)
                    UNITS "N/A"
                    MAX-ACCESS read-write
                    STATUS current
                    DESCRIPTION "Enable fancoils management"
                    DEFVAL { 1 }
                    ::= { digitalObjects 38 }

        -- 1.3.6.1.4.1.9839.2.1.1.39
        pco1_board OBJECT-TYPE
                    SYNTAX Integer32 (0..1)
                    UNITS "N/A"
                    MAX-ACCESS read-only
                    STATUS current
                    DESCRIPTION "pCO1 board"
                    ::= { digitalObjects 39 }

        -- 1.3.6.1.4.1.9839.2.1.1.40
        main_pump OBJECT-TYPE
                    SYNTAX Integer32 (0..1)
                    UNITS "N/A"
                    MAX-ACCESS read-only
                    STATUS current
                    DESCRIPTION "Main pump (or main fan)"
                    ::= { digitalObjects 40 }

        -- 1.3.6.1.4.1.9839.2.1.1.41
        cond_pump OBJECT-TYPE
                    SYNTAX Integer32 (0..1)
                    UNITS "N/A"
                    MAX-ACCESS read-only
                    STATUS current
                    DESCRIPTION "Condenser pump"
                    ::= { digitalObjects 41 }

        -- 1.3.6.1.4.1.9839.2.1.1.42
        superv_onoff OBJECT-TYPE
                    SYNTAX Integer32 (0..1)
                    UNITS "N/A"
                    MAX-ACCESS read-write
                    STATUS current
                    DESCRIPTION "On/Off from supervisor"
                    DEFVAL { 1 }
                    ::= { digitalObjects 42 }

        -- 1.3.6.1.4.1.9839.2.1.1.43
        pco2_board OBJECT-TYPE
                    SYNTAX Integer32 (0..1)
                    UNITS "N/A"
                    MAX-ACCESS read-only
                    STATUS current
                    DESCRIPTION "pCO2 board"
                    ::= { digitalObjects 43 }

        -- 1.3.6.1.4.1.9839.2.1.1.44
        sum_win_sup OBJECT-TYPE
                    SYNTAX Integer32 (0..1)
                    UNITS "N/A"
                    MAX-ACCESS read-write
                    STATUS current
                    DESCRIPTION "Select Chiller / HP mode for supervisor"
                    ::= { digitalObjects 44 }

        -- 1.3.6.1.4.1.9839.2.1.1.45
        pcoc_board OBJECT-TYPE
                    SYNTAX Integer32 (0..1)
                    UNITS "N/A"
                    MAX-ACCESS read-only
                    STATUS current
                    DESCRIPTION "pCOC board"
                    ::= { digitalObjects 45 }

        -- 1.3.6.1.4.1.9839.2.1.1.46
        en_freecooling OBJECT-TYPE
                    SYNTAX Integer32 (0..1)
                    UNITS "N/A"
                    MAX-ACCESS read-only
                    STATUS current
                    DESCRIPTION "Freecooling unit selected"
                    ::= { digitalObjects 46 }

        -- 1.3.6.1.4.1.9839.2.1.1.47
        en_aa_unit OBJECT-TYPE
                    SYNTAX Integer32 (0..1)
                    UNITS "N/A"
                    MAX-ACCESS read-only
                    STATUS current
                    DESCRIPTION "AIR/AIR unit selected"
                    ::= { digitalObjects 47 }

        -- 1.3.6.1.4.1.9839.2.1.1.48
        en_ww_unit OBJECT-TYPE
                    SYNTAX Integer32 (0..1)
                    UNITS "N/A"
                    MAX-ACCESS read-only
                    STATUS current
                    DESCRIPTION "WATER/WATER unit selected: enable condenser pump"
                    ::= { digitalObjects 48 }

        -- 1.3.6.1.4.1.9839.2.1.1.49
        sum_win_sel OBJECT-TYPE
                    SYNTAX Integer32 (0..1)
                    UNITS "N/A"
                    MAX-ACCESS read-only
                    STATUS current
                    DESCRIPTION "Digital input for selecting chiller / HP mode"
                    ::= { digitalObjects 49 }

        -- 1.3.6.1.4.1.9839.2.1.1.50
        en_sum_win OBJECT-TYPE
                    SYNTAX Integer32 (0..1)
                    UNITS "N/A"
                    MAX-ACCESS read-write
                    STATUS current
                    DESCRIPTION "Enable dig. input chiller / HP mode"
                    ::= { digitalObjects 50 }

        -- 1.3.6.1.4.1.9839.2.1.1.51
        cooling_heating OBJECT-TYPE
                    SYNTAX Integer32 (0..1)
                    UNITS "N/A"
                    MAX-ACCESS read-only
                    STATUS current
                    DESCRIPTION "Function mode (Summer/Winter)"
                    ::= { digitalObjects 51 }

        -- 1.3.6.1.4.1.9839.2.1.1.52
        pcoxs_board OBJECT-TYPE
                    SYNTAX Integer32 (0..1)
                    UNITS "N/A"
                    MAX-ACCESS read-only
                    STATUS current
                    DESCRIPTION "pCOxs board"
                    ::= { digitalObjects 52 }

        -- 1.3.6.1.4.1.9839.2.1.1.53
        cond_config OBJECT-TYPE
                    SYNTAX Integer32 (0..1)
                    UNITS "N/A"
                    MAX-ACCESS read-write
                    STATUS current
                    DESCRIPTION "Select type of condenser (1=DOUBLE)"
                    ::= { digitalObjects 53 }

        -- 1.3.6.1.4.1.9839.2.1.1.54
        not_en_aa_unit OBJECT-TYPE
                    SYNTAX Integer32 (0..1)
                    UNITS "N/A"
                    MAX-ACCESS read-only
                    STATUS current
                    DESCRIPTION "No air unit"
                    ::= { digitalObjects 54 }

        -- 1.3.6.1.4.1.9839.2.1.1.55
        main_pump2 OBJECT-TYPE
                    SYNTAX Integer32 (0..1)
                    UNITS "N/A"
                    MAX-ACCESS read-only
                    STATUS current
                    DESCRIPTION "Main pump 2 status     "
                    ::= { digitalObjects 55 }

        -- 1.3.6.1.4.1.9839.2.1.1.56
        inverter_steps OBJECT-TYPE
                    SYNTAX Integer32 (0..1)
                    UNITS "N/A"
                    MAX-ACCESS read-write
                    STATUS current
                    DESCRIPTION "Select operation (inverter or stepped)"
                    ::= { digitalObjects 56 }

        -- 1.3.6.1.4.1.9839.2.1.1.57
        rst_alarms OBJECT-TYPE
                    SYNTAX Integer32 (0..1)
                    UNITS "N/A"
                    MAX-ACCESS read-write
                    STATUS current
                    DESCRIPTION "Reset alarms"
                    ::= { digitalObjects 57 }

        -- 1.3.6.1.4.1.9839.2.1.1.58
        fc_valve_type OBJECT-TYPE
                    SYNTAX Integer32 (0..1)
                    UNITS "N/A"
                    MAX-ACCESS read-write
                    STATUS current
                    DESCRIPTION "Select type of freecooling valve (1 = 0-10V)"
                    DEFVAL { 0 }
                    ::= { digitalObjects 58 }

        -- 1.3.6.1.4.1.9839.2.1.1.59
        not_fc_vlv_type OBJECT-TYPE
                    SYNTAX Integer32 (0..1)
                    UNITS "N/A"
                    MAX-ACCESS read-only
                    STATUS current
                    DESCRIPTION "Type of freecooling valve (0=no valve)"
                    ::= { digitalObjects 59 }

        -- 1.3.6.1.4.1.9839.2.1.1.60
        unloads_logic OBJECT-TYPE
                    SYNTAX Integer32 (0..1)
                    UNITS "N/A"
                    MAX-ACCESS read-write
                    STATUS current
                    DESCRIPTION "Select unloaders logic"
                    ::= { digitalObjects 60 }

        -- 1.3.6.1.4.1.9839.2.1.1.61
        valve4way_logic OBJECT-TYPE
                    SYNTAX Integer32 (0..1)
                    UNITS "N/A"
                    MAX-ACCESS read-write
                    STATUS current
                    DESCRIPTION "Select 4-way valve logic"
                    ::= { digitalObjects 61 }

        -- 1.3.6.1.4.1.9839.2.1.1.62
        aout1_not_dig OBJECT-TYPE
                    SYNTAX Integer32 (0..1)
                    UNITS "N/A"
                    MAX-ACCESS read-only
                    STATUS current
                    DESCRIPTION "Analog out 1 used for dig. Output"
                    ::= { digitalObjects 62 }

        -- 1.3.6.1.4.1.9839.2.1.1.63
        aout2_not_dig OBJECT-TYPE
                    SYNTAX Integer32 (0..1)
                    UNITS "N/A"
                    MAX-ACCESS read-only
                    STATUS current
                    DESCRIPTION "Analog out 2 used for dig. Output"
                    ::= { digitalObjects 63 }

        -- 1.3.6.1.4.1.9839.2.1.1.64
        reg_priority OBJECT-TYPE
                    SYNTAX Integer32 (0..1)
                    UNITS "N/A"
                    MAX-ACCESS read-write
                    STATUS current
                    DESCRIPTION "Recover priority  (1= recover)"
                    ::= { digitalObjects 64 }

        -- 1.3.6.1.4.1.9839.2.1.1.65
        unit1_online OBJECT-TYPE
                    SYNTAX Integer32 (0..1)
                    UNITS "N/A"
                    MAX-ACCESS read-only
                    STATUS current
                    DESCRIPTION "Unit 1 online"
                    ::= { digitalObjects 65 }

        -- 1.3.6.1.4.1.9839.2.1.1.66
        en_comp1 OBJECT-TYPE
                    SYNTAX Integer32 (0..1)
                    UNITS "N/A"
                    MAX-ACCESS read-only
                    STATUS current
                    DESCRIPTION "Enable compressor 1"
                    ::= { digitalObjects 66 }

        -- 1.3.6.1.4.1.9839.2.1.1.67
        en_comp2 OBJECT-TYPE
                    SYNTAX Integer32 (0..1)
                    UNITS "N/A"
                    MAX-ACCESS read-only
                    STATUS current
                    DESCRIPTION "Enable compressor 2"
                    ::= { digitalObjects 67 }

        -- 1.3.6.1.4.1.9839.2.1.1.68
        en_comp3 OBJECT-TYPE
                    SYNTAX Integer32 (0..1)
                    UNITS "N/A"
                    MAX-ACCESS read-only
                    STATUS current
                    DESCRIPTION "Enable compressor 3"
                    ::= { digitalObjects 68 }

        -- 1.3.6.1.4.1.9839.2.1.1.69
        en_comp4 OBJECT-TYPE
                    SYNTAX Integer32 (0..1)
                    UNITS "N/A"
                    MAX-ACCESS read-only
                    STATUS current
                    DESCRIPTION "Enable compressor 4"
                    ::= { digitalObjects 69 }

        -- 1.3.6.1.4.1.9839.2.1.1.70
        glb_al OBJECT-TYPE
                    SYNTAX Integer32 (0..1)
                    UNITS "N/A"
                    MAX-ACCESS read-only
                    STATUS current
                    DESCRIPTION "General alarm"
                    ::= { digitalObjects 70 }

        -- 1.3.6.1.4.1.9839.2.1.1.71
        man_freeze OBJECT-TYPE
                    SYNTAX Integer32 (0..1)
                    UNITS "N/A"
                    MAX-ACCESS read-only
                    STATUS current
                    DESCRIPTION "Antifreeze alarm"
                    ::= { digitalObjects 71 }

        -- 1.3.6.1.4.1.9839.2.1.1.72
        mal_ov1 OBJECT-TYPE
                    SYNTAX Integer32 (0..1)
                    UNITS "N/A"
                    MAX-ACCESS read-only
                    STATUS current
                    DESCRIPTION "Compressor 1 overload"
                    ::= { digitalObjects 72 }

        -- 1.3.6.1.4.1.9839.2.1.1.73
        mal_ov2 OBJECT-TYPE
                    SYNTAX Integer32 (0..1)
                    UNITS "N/A"
                    MAX-ACCESS read-only
                    STATUS current
                    DESCRIPTION "Compressor 2 overload"
                    ::= { digitalObjects 73 }

        -- 1.3.6.1.4.1.9839.2.1.1.74
        mal_ov3 OBJECT-TYPE
                    SYNTAX Integer32 (0..1)
                    UNITS "N/A"
                    MAX-ACCESS read-only
                    STATUS current
                    DESCRIPTION "Compressor 3 overload"
                    ::= { digitalObjects 74 }

        -- 1.3.6.1.4.1.9839.2.1.1.75
        mal_ov4 OBJECT-TYPE
                    SYNTAX Integer32 (0..1)
                    UNITS "N/A"
                    MAX-ACCESS read-only
                    STATUS current
                    DESCRIPTION "Compressor 4 overload"
                    ::= { digitalObjects 75 }

        -- 1.3.6.1.4.1.9839.2.1.1.76
        mal_cflow OBJECT-TYPE
                    SYNTAX Integer32 (0..1)
                    UNITS "N/A"
                    MAX-ACCESS read-only
                    STATUS current
                    DESCRIPTION "Condensator flow alarm"
                    ::= { digitalObjects 76 }

        -- 1.3.6.1.4.1.9839.2.1.1.77
        mal_eflow OBJECT-TYPE
                    SYNTAX Integer32 (0..1)
                    UNITS "N/A"
                    MAX-ACCESS read-only
                    STATUS current
                    DESCRIPTION "Evaporator flow alarm"
                    ::= { digitalObjects 77 }

        -- 1.3.6.1.4.1.9839.2.1.1.78
        mal_hp1 OBJECT-TYPE
                    SYNTAX Integer32 (0..1)
                    UNITS "N/A"
                    MAX-ACCESS read-only
                    STATUS current
                    DESCRIPTION "circuit1 high pressure alarm (pressurestat)"
                    ::= { digitalObjects 78 }

        -- 1.3.6.1.4.1.9839.2.1.1.79
        mal_hp2 OBJECT-TYPE
                    SYNTAX Integer32 (0..1)
                    UNITS "N/A"
                    MAX-ACCESS read-only
                    STATUS current
                    DESCRIPTION "circuit2 high pressure alarm (pressurestat)"
                    ::= { digitalObjects 79 }

        -- 1.3.6.1.4.1.9839.2.1.1.80
        mal_od1 OBJECT-TYPE
                    SYNTAX Integer32 (0..1)
                    UNITS "N/A"
                    MAX-ACCESS read-only
                    STATUS current
                    DESCRIPTION "circuit1 oil differential alarm"
                    ::= { digitalObjects 80 }

        -- 1.3.6.1.4.1.9839.2.1.1.81
        mal_od2 OBJECT-TYPE
                    SYNTAX Integer32 (0..1)
                    UNITS "N/A"
                    MAX-ACCESS read-only
                    STATUS current
                    DESCRIPTION "circuit2 oil differential alarm"
                    ::= { digitalObjects 81 }

        -- 1.3.6.1.4.1.9839.2.1.1.82
        mal_lp1 OBJECT-TYPE
                    SYNTAX Integer32 (0..1)
                    UNITS "N/A"
                    MAX-ACCESS read-only
                    STATUS current
                    DESCRIPTION "circuit1 low pressure alarm"
                    ::= { digitalObjects 82 }

        -- 1.3.6.1.4.1.9839.2.1.1.83
        mal_lp2 OBJECT-TYPE
                    SYNTAX Integer32 (0..1)
                    UNITS "N/A"
                    MAX-ACCESS read-only
                    STATUS current
                    DESCRIPTION "circuit2 low pressure alarm"
                    ::= { digitalObjects 83 }

        -- 1.3.6.1.4.1.9839.2.1.1.84
        mal_hpt1 OBJECT-TYPE
                    SYNTAX Integer32 (0..1)
                    UNITS "N/A"
                    MAX-ACCESS read-only
                    STATUS current
                    DESCRIPTION "Transducer 1 high pressure alarm"
                    ::= { digitalObjects 84 }

        -- 1.3.6.1.4.1.9839.2.1.1.85
        mal_hpt2 OBJECT-TYPE
                    SYNTAX Integer32 (0..1)
                    UNITS "N/A"
                    MAX-ACCESS read-only
                    STATUS current
                    DESCRIPTION "Transducer 2 high pressure alarm"
                    ::= { digitalObjects 85 }

        -- 1.3.6.1.4.1.9839.2.1.1.86
        mal_serious OBJECT-TYPE
                    SYNTAX Integer32 (0..1)
                    UNITS "N/A"
                    MAX-ACCESS read-only
                    STATUS current
                    DESCRIPTION "Serious alarm from digital input"
                    ::= { digitalObjects 86 }

        -- 1.3.6.1.4.1.9839.2.1.1.87
        mal_f1_overload OBJECT-TYPE
                    SYNTAX Integer32 (0..1)
                    UNITS "N/A"
                    MAX-ACCESS read-only
                    STATUS current
                    DESCRIPTION "Condensator fan 1 overload"
                    ::= { digitalObjects 87 }

        -- 1.3.6.1.4.1.9839.2.1.1.88
        mal_f2_overload OBJECT-TYPE
                    SYNTAX Integer32 (0..1)
                    UNITS "N/A"
                    MAX-ACCESS read-only
                    STATUS current
                    DESCRIPTION "Condensator fan 2 overload"
                    ::= { digitalObjects 88 }

        -- 1.3.6.1.4.1.9839.2.1.1.89
        mal_f3_overload OBJECT-TYPE
                    SYNTAX Integer32 (0..1)
                    UNITS "N/A"
                    MAX-ACCESS read-only
                    STATUS current
                    DESCRIPTION "Condensator fan 3 overload"
                    ::= { digitalObjects 89 }

        -- 1.3.6.1.4.1.9839.2.1.1.90
        mal_fan OBJECT-TYPE
                    SYNTAX Integer32 (0..1)
                    UNITS "N/A"
                    MAX-ACCESS read-only
                    STATUS current
                    DESCRIPTION "Main fan overload"
                    ::= { digitalObjects 90 }

        -- 1.3.6.1.4.1.9839.2.1.1.91
        mal_cpump OBJECT-TYPE
                    SYNTAX Integer32 (0..1)
                    UNITS "N/A"
                    MAX-ACCESS read-only
                    STATUS current
                    DESCRIPTION "Condensator pump overload"
                    ::= { digitalObjects 91 }

        -- 1.3.6.1.4.1.9839.2.1.1.92
        mal_pump OBJECT-TYPE
                    SYNTAX Integer32 (0..1)
                    UNITS "N/A"
                    MAX-ACCESS read-only
                    STATUS current
                    DESCRIPTION "Evaporator pump overload"
                    ::= { digitalObjects 92 }

        -- 1.3.6.1.4.1.9839.2.1.1.93
        mal_unit1_offl OBJECT-TYPE
                    SYNTAX Integer32 (0..1)
                    UNITS "N/A"
                    MAX-ACCESS read-only
                    STATUS current
                    DESCRIPTION "Unit 1 off-line"
                    ::= { digitalObjects 93 }

        -- 1.3.6.1.4.1.9839.2.1.1.94
        mal_unit2_offl OBJECT-TYPE
                    SYNTAX Integer32 (0..1)
                    UNITS "N/A"
                    MAX-ACCESS read-only
                    STATUS current
                    DESCRIPTION "Unit 2 off-line"
                    ::= { digitalObjects 94 }

        -- 1.3.6.1.4.1.9839.2.1.1.95
        mal_unit3_offl OBJECT-TYPE
                    SYNTAX Integer32 (0..1)
                    UNITS "N/A"
                    MAX-ACCESS read-only
                    STATUS current
                    DESCRIPTION "Unit 3 off-line"
                    ::= { digitalObjects 95 }

        -- 1.3.6.1.4.1.9839.2.1.1.96
        mal_unit4_offl OBJECT-TYPE
                    SYNTAX Integer32 (0..1)
                    UNITS "N/A"
                    MAX-ACCESS read-only
                    STATUS current
                    DESCRIPTION "Unit 4 off-line"
                    ::= { digitalObjects 96 }

        -- 1.3.6.1.4.1.9839.2.1.1.97
        mal_b1 OBJECT-TYPE
                    SYNTAX Integer32 (0..1)
                    UNITS "N/A"
                    MAX-ACCESS read-only
                    STATUS current
                    DESCRIPTION "b1 probe broken or not connected"
                    ::= { digitalObjects 97 }

        -- 1.3.6.1.4.1.9839.2.1.1.98
        mal_b2 OBJECT-TYPE
                    SYNTAX Integer32 (0..1)
                    UNITS "N/A"
                    MAX-ACCESS read-only
                    STATUS current
                    DESCRIPTION "b2 probe broken or not connected"
                    ::= { digitalObjects 98 }

        -- 1.3.6.1.4.1.9839.2.1.1.99
        mal_b3 OBJECT-TYPE
                    SYNTAX Integer32 (0..1)
                    UNITS "N/A"
                    MAX-ACCESS read-only
                    STATUS current
                    DESCRIPTION "b3 probe broken or not connected"
                    ::= { digitalObjects 99 }

        -- 1.3.6.1.4.1.9839.2.1.1.100
        mal_b4 OBJECT-TYPE
                    SYNTAX Integer32 (0..1)
                    UNITS "N/A"
                    MAX-ACCESS read-only
                    STATUS current
                    DESCRIPTION "b4 probe broken or not connected"
                    ::= { digitalObjects 100 }

        -- 1.3.6.1.4.1.9839.2.1.1.101
        mal_b5 OBJECT-TYPE
                    SYNTAX Integer32 (0..1)
                    UNITS "N/A"
                    MAX-ACCESS read-only
                    STATUS current
                    DESCRIPTION "b5 probe broken or not connected"
                    ::= { digitalObjects 101 }

        -- 1.3.6.1.4.1.9839.2.1.1.102
        mal_b6 OBJECT-TYPE
                    SYNTAX Integer32 (0..1)
                    UNITS "N/A"
                    MAX-ACCESS read-only
                    STATUS current
                    DESCRIPTION "b6 probe broken or not connected"
                    ::= { digitalObjects 102 }

        -- 1.3.6.1.4.1.9839.2.1.1.103
        mal_b7 OBJECT-TYPE
                    SYNTAX Integer32 (0..1)
                    UNITS "N/A"
                    MAX-ACCESS read-only
                    STATUS current
                    DESCRIPTION "b7 probe broken or not connected"
                    ::= { digitalObjects 103 }

        -- 1.3.6.1.4.1.9839.2.1.1.104
        mal_b8 OBJECT-TYPE
                    SYNTAX Integer32 (0..1)
                    UNITS "N/A"
                    MAX-ACCESS read-only
                    STATUS current
                    DESCRIPTION "b8 probe broken or not connected"
                    ::= { digitalObjects 104 }

        -- 1.3.6.1.4.1.9839.2.1.1.105
        mal_h_main_pump OBJECT-TYPE
                    SYNTAX Integer32 (0..1)
                    UNITS "N/A"
                    MAX-ACCESS read-only
                    STATUS current
                    DESCRIPTION "Main fun or main pump maintenance alarm"
                    ::= { digitalObjects 105 }

        -- 1.3.6.1.4.1.9839.2.1.1.106
        mal_h_comp1 OBJECT-TYPE
                    SYNTAX Integer32 (0..1)
                    UNITS "N/A"
                    MAX-ACCESS read-only
                    STATUS current
                    DESCRIPTION "Compressor 1 maintenance alarm"
                    ::= { digitalObjects 106 }

        -- 1.3.6.1.4.1.9839.2.1.1.107
        mal_h_comp2 OBJECT-TYPE
                    SYNTAX Integer32 (0..1)
                    UNITS "N/A"
                    MAX-ACCESS read-only
                    STATUS current
                    DESCRIPTION "Compressor 2 maintenance alarm"
                    ::= { digitalObjects 107 }

        -- 1.3.6.1.4.1.9839.2.1.1.108
        mal_h_comp3 OBJECT-TYPE
                    SYNTAX Integer32 (0..1)
                    UNITS "N/A"
                    MAX-ACCESS read-only
                    STATUS current
                    DESCRIPTION "Compressor 3 maintenance alarm"
                    ::= { digitalObjects 108 }

        -- 1.3.6.1.4.1.9839.2.1.1.109
        mal_h_comp4 OBJECT-TYPE
                    SYNTAX Integer32 (0..1)
                    UNITS "N/A"
                    MAX-ACCESS read-only
                    STATUS current
                    DESCRIPTION "Compressor 4 maintenance alarm"
                    ::= { digitalObjects 109 }

        -- 1.3.6.1.4.1.9839.2.1.1.110
        mal_clock32 OBJECT-TYPE
                    SYNTAX Integer32 (0..1)
                    UNITS "N/A"
                    MAX-ACCESS read-only
                    STATUS current
                    DESCRIPTION "32 clock board broken or not connected"
                    ::= { digitalObjects 110 }

        -- 1.3.6.1.4.1.9839.2.1.1.111
        supv_dev1 OBJECT-TYPE
                    SYNTAX Integer32 (0..1)
                    UNITS "N/A"
                    MAX-ACCESS read-only
                    STATUS current
                    DESCRIPTION "Required step 1"
                    ::= { digitalObjects 111 }

        -- 1.3.6.1.4.1.9839.2.1.1.112
        supv_dev2 OBJECT-TYPE
                    SYNTAX Integer32 (0..1)
                    UNITS "N/A"
                    MAX-ACCESS read-only
                    STATUS current
                    DESCRIPTION "Required step 2"
                    ::= { digitalObjects 112 }

        -- 1.3.6.1.4.1.9839.2.1.1.113
        supv_dev3 OBJECT-TYPE
                    SYNTAX Integer32 (0..1)
                    UNITS "N/A"
                    MAX-ACCESS read-only
                    STATUS current
                    DESCRIPTION "Required step 3"
                    ::= { digitalObjects 113 }

        -- 1.3.6.1.4.1.9839.2.1.1.114
        supv_dev4 OBJECT-TYPE
                    SYNTAX Integer32 (0..1)
                    UNITS "N/A"
                    MAX-ACCESS read-only
                    STATUS current
                    DESCRIPTION "Required step 4"
                    ::= { digitalObjects 114 }

        -- 1.3.6.1.4.1.9839.2.1.1.115
        pressostat_defr OBJECT-TYPE
                    SYNTAX Integer32 (0..1)
                    UNITS "N/A"
                    MAX-ACCESS read-only
                    STATUS current
                    DESCRIPTION "Defrost with pressure"
                    ::= { digitalObjects 115 }

        -- 1.3.6.1.4.1.9839.2.1.1.116
        not_en_ww_unit OBJECT-TYPE
                    SYNTAX Integer32 (0..1)
                    UNITS "N/A"
                    MAX-ACCESS read-only
                    STATUS current
                    DESCRIPTION "No unit water-water"
                    ::= { digitalObjects 116 }

        -- 1.3.6.1.4.1.9839.2.1.1.117
        en_recover OBJECT-TYPE
                    SYNTAX Integer32 (0..1)
                    UNITS "N/A"
                    MAX-ACCESS read-only
                    STATUS current
                    DESCRIPTION "Unit with recovery"
                    ::= { digitalObjects 117 }

        -- 1.3.6.1.4.1.9839.2.1.1.118
        not_en_ext_setp OBJECT-TYPE
                    SYNTAX Integer32 (0..1)
                    UNITS "N/A"
                    MAX-ACCESS read-only
                    STATUS current
                    DESCRIPTION "Unit without external setpoint"
                    ::= { digitalObjects 118 }

        -- 1.3.6.1.4.1.9839.2.1.1.119
        unit_is_hp OBJECT-TYPE
                    SYNTAX Integer32 (0..1)
                    UNITS "N/A"
                    MAX-ACCESS read-only
                    STATUS current
                    DESCRIPTION "Unit heat pump"
                    ::= { digitalObjects 119 }

        -- 1.3.6.1.4.1.9839.2.1.1.120
        enable_aout1 OBJECT-TYPE
                    SYNTAX Integer32 (0..1)
                    UNITS "N/A"
                    MAX-ACCESS read-only
                    STATUS current
                    DESCRIPTION "First analog output used"
                    ::= { digitalObjects 120 }

        -- 1.3.6.1.4.1.9839.2.1.1.121
        enable_aout2 OBJECT-TYPE
                    SYNTAX Integer32 (0..1)
                    UNITS "N/A"
                    MAX-ACCESS read-only
                    STATUS current
                    DESCRIPTION "Second analog output used"
                    ::= { digitalObjects 121 }

        -- 1.3.6.1.4.1.9839.2.1.1.122
        en_compens OBJECT-TYPE
                    SYNTAX Integer32 (0..1)
                    UNITS "N/A"
                    MAX-ACCESS read-write
                    STATUS current
                    DESCRIPTION "Enable compensation setpoint with ext temp"
                    ::= { digitalObjects 122 }

        -- 1.3.6.1.4.1.9839.2.1.1.123
        en_ext_setp OBJECT-TYPE
                    SYNTAX Integer32 (0..1)
                    UNITS "N/A"
                    MAX-ACCESS read-write
                    STATUS current
                    DESCRIPTION "Unit with external setpoint"
                    ::= { digitalObjects 123 }

        -- 1.3.6.1.4.1.9839.2.1.1.124
        en_compr1 OBJECT-TYPE
                    SYNTAX Integer32 (0..1)
                    UNITS "N/A"
                    MAX-ACCESS read-write
                    STATUS current
                    DESCRIPTION "Enable compressor 1"
                    ::= { digitalObjects 124 }

        -- 1.3.6.1.4.1.9839.2.1.1.125
        en_compr2 OBJECT-TYPE
                    SYNTAX Integer32 (0..1)
                    UNITS "N/A"
                    MAX-ACCESS read-write
                    STATUS current
                    DESCRIPTION "Enable compressor 2"
                    ::= { digitalObjects 125 }

        -- 1.3.6.1.4.1.9839.2.1.1.126
        en_compr3 OBJECT-TYPE
                    SYNTAX Integer32 (0..1)
                    UNITS "N/A"
                    MAX-ACCESS read-write
                    STATUS current
                    DESCRIPTION "Enable compressor 3"
                    ::= { digitalObjects 126 }

        -- 1.3.6.1.4.1.9839.2.1.1.127
        en_compr4 OBJECT-TYPE
                    SYNTAX Integer32 (0..1)
                    UNITS "N/A"
                    MAX-ACCESS read-write
                    STATUS current
                    DESCRIPTION "Enable compressor 4"
                    ::= { digitalObjects 127 }

        -- 1.3.6.1.4.1.9839.2.1.1.128
        en_compr5 OBJECT-TYPE
                    SYNTAX Integer32 (0..1)
                    UNITS "N/A"
                    MAX-ACCESS read-write
                    STATUS current
                    DESCRIPTION "Enable compressor 5"
                    ::= { digitalObjects 128 }

        -- 1.3.6.1.4.1.9839.2.1.1.129
        en_compr6 OBJECT-TYPE
                    SYNTAX Integer32 (0..1)
                    UNITS "N/A"
                    MAX-ACCESS read-write
                    STATUS current
                    DESCRIPTION "Enable compressor 6"
                    ::= { digitalObjects 129 }

        -- 1.3.6.1.4.1.9839.2.1.1.130
        en_compr7 OBJECT-TYPE
                    SYNTAX Integer32 (0..1)
                    UNITS "N/A"
                    MAX-ACCESS read-write
                    STATUS current
                    DESCRIPTION "Enable compressor 7"
                    ::= { digitalObjects 130 }

        -- 1.3.6.1.4.1.9839.2.1.1.131
        en_compr8 OBJECT-TYPE
                    SYNTAX Integer32 (0..1)
                    UNITS "N/A"
                    MAX-ACCESS read-write
                    STATUS current
                    DESCRIPTION "Enable compressor 8"
                    ::= { digitalObjects 131 }

        -- 1.3.6.1.4.1.9839.2.1.1.132
        not_syson_s OBJECT-TYPE
                    SYNTAX Integer32 (0..1)
                    UNITS "N/A"
                    MAX-ACCESS read-only
                    STATUS current
                    DESCRIPTION "Unit OFF"
                    ::= { digitalObjects 132 }

        -- 1.3.6.1.4.1.9839.2.1.1.133
        mal_probe_d1 OBJECT-TYPE
                    SYNTAX Integer32 (0..1)
                    UNITS "N/A"
                    MAX-ACCESS read-only
                    STATUS current
                    DESCRIPTION "Driver1 circuit1 Probe error"
                    ::= { digitalObjects 133 }

        -- 1.3.6.1.4.1.9839.2.1.1.134
        mal_eeprom_d1 OBJECT-TYPE
                    SYNTAX Integer32 (0..1)
                    UNITS "N/A"
                    MAX-ACCESS read-only
                    STATUS current
                    DESCRIPTION "Driver1 circuit1 Eeprom error"
                    ::= { digitalObjects 134 }

        -- 1.3.6.1.4.1.9839.2.1.1.135
        mal_step_m_d1 OBJECT-TYPE
                    SYNTAX Integer32 (0..1)
                    UNITS "N/A"
                    MAX-ACCESS read-only
                    STATUS current
                    DESCRIPTION "Driver1 circuit1 Step motor error"
                    ::= { digitalObjects 135 }

        -- 1.3.6.1.4.1.9839.2.1.1.136
        mal_battery_d1 OBJECT-TYPE
                    SYNTAX Integer32 (0..1)
                    UNITS "N/A"
                    MAX-ACCESS read-only
                    STATUS current
                    DESCRIPTION "Driver1 circuit1 battery error"
                    ::= { digitalObjects 136 }

        -- 1.3.6.1.4.1.9839.2.1.1.137
        mal_mop_d1 OBJECT-TYPE
                    SYNTAX Integer32 (0..1)
                    UNITS "N/A"
                    MAX-ACCESS read-only
                    STATUS current
                    DESCRIPTION "Driver1 circuit1 high pressure evaporator (MOP)"
                    ::= { digitalObjects 137 }

        -- 1.3.6.1.4.1.9839.2.1.1.138
        mal_lop_d1 OBJECT-TYPE
                    SYNTAX Integer32 (0..1)
                    UNITS "N/A"
                    MAX-ACCESS read-only
                    STATUS current
                    DESCRIPTION "Driver1 circuit1 low pressure evaporator (LOP)"
                    ::= { digitalObjects 138 }

        -- 1.3.6.1.4.1.9839.2.1.1.139
        mal_l_sheat_d1 OBJECT-TYPE
                    SYNTAX Integer32 (0..1)
                    UNITS "N/A"
                    MAX-ACCESS read-only
                    STATUS current
                    DESCRIPTION "Driver1 circuit1 low Superheat"
                    ::= { digitalObjects 139 }

        -- 1.3.6.1.4.1.9839.2.1.1.140
        mal_vlv_err_d1 OBJECT-TYPE
                    SYNTAX Integer32 (0..1)
                    UNITS "N/A"
                    MAX-ACCESS read-only
                    STATUS current
                    DESCRIPTION "Driver1 circuit1  valve not closed during power OFF"
                    ::= { digitalObjects 140 }

        -- 1.3.6.1.4.1.9839.2.1.1.141
        mal_h_sheat_d1 OBJECT-TYPE
                    SYNTAX Integer32 (0..1)
                    UNITS "N/A"
                    MAX-ACCESS read-only
                    STATUS current
                    DESCRIPTION "Driver1  circuit1 high temperature suction"
                    ::= { digitalObjects 141 }

        -- 1.3.6.1.4.1.9839.2.1.1.142
        mgo_ahead_en1 OBJECT-TYPE
                    SYNTAX Integer32 (0..1)
                    UNITS "N/A"
                    MAX-ACCESS read-only
                    STATUS current
                    DESCRIPTION "Driver1 circuit1 Waiting for Eeprom/batt.charged"
                    ::= { digitalObjects 142 }

        -- 1.3.6.1.4.1.9839.2.1.1.143
        mal_probe_d2 OBJECT-TYPE
                    SYNTAX Integer32 (0..1)
                    UNITS "N/A"
                    MAX-ACCESS read-only
                    STATUS current
                    DESCRIPTION "Driver2 circuit1 Probe error"
                    ::= { digitalObjects 143 }

        -- 1.3.6.1.4.1.9839.2.1.1.144
        mal_eeprom_d2 OBJECT-TYPE
                    SYNTAX Integer32 (0..1)
                    UNITS "N/A"
                    MAX-ACCESS read-only
                    STATUS current
                    DESCRIPTION "Driver2 circuit1 Eeprom error"
                    ::= { digitalObjects 144 }

        -- 1.3.6.1.4.1.9839.2.1.1.145
        mal_step_m_d2 OBJECT-TYPE
                    SYNTAX Integer32 (0..1)
                    UNITS "N/A"
                    MAX-ACCESS read-only
                    STATUS current
                    DESCRIPTION "Driver2 circuit1 Step motor error"
                    ::= { digitalObjects 145 }

        -- 1.3.6.1.4.1.9839.2.1.1.146
        mal_battery_d2 OBJECT-TYPE
                    SYNTAX Integer32 (0..1)
                    UNITS "N/A"
                    MAX-ACCESS read-only
                    STATUS current
                    DESCRIPTION "Driver2 circuit1 battery error"
                    ::= { digitalObjects 146 }

        -- 1.3.6.1.4.1.9839.2.1.1.147
        mal_mop_d2 OBJECT-TYPE
                    SYNTAX Integer32 (0..1)
                    UNITS "N/A"
                    MAX-ACCESS read-only
                    STATUS current
                    DESCRIPTION "Driver2  circuit1 high pressure evaporator (MOP)"
                    ::= { digitalObjects 147 }

        -- 1.3.6.1.4.1.9839.2.1.1.148
        mal_lop_d2 OBJECT-TYPE
                    SYNTAX Integer32 (0..1)
                    UNITS "N/A"
                    MAX-ACCESS read-only
                    STATUS current
                    DESCRIPTION "Driver2 circuit1 low pressure evaporator (LOP)"
                    ::= { digitalObjects 148 }

        -- 1.3.6.1.4.1.9839.2.1.1.149
        mal_l_sheat_d2 OBJECT-TYPE
                    SYNTAX Integer32 (0..1)
                    UNITS "N/A"
                    MAX-ACCESS read-only
                    STATUS current
                    DESCRIPTION "Driver2 circuit1 low Superheat"
                    ::= { digitalObjects 149 }

        -- 1.3.6.1.4.1.9839.2.1.1.150
        mal_vlv_err_d2 OBJECT-TYPE
                    SYNTAX Integer32 (0..1)
                    UNITS "N/A"
                    MAX-ACCESS read-only
                    STATUS current
                    DESCRIPTION "Driver2 circuit1  Valve not closed during power OFF"
                    ::= { digitalObjects 150 }

        -- 1.3.6.1.4.1.9839.2.1.1.151
        mal_h_sheat_d2 OBJECT-TYPE
                    SYNTAX Integer32 (0..1)
                    UNITS "N/A"
                    MAX-ACCESS read-only
                    STATUS current
                    DESCRIPTION "Driver2 circuit1 high temperature suction"
                    ::= { digitalObjects 151 }

        -- 1.3.6.1.4.1.9839.2.1.1.152
        mgo_ahead_en2 OBJECT-TYPE
                    SYNTAX Integer32 (0..1)
                    UNITS "N/A"
                    MAX-ACCESS read-only
                    STATUS current
                    DESCRIPTION "Driver2 circuit1 Waiting for Eeprom/batt.charged"
                    ::= { digitalObjects 152 }

        -- 1.3.6.1.4.1.9839.2.1.1.153
        mal_probe_d3 OBJECT-TYPE
                    SYNTAX Integer32 (0..1)
                    UNITS "N/A"
                    MAX-ACCESS read-only
                    STATUS current
                    DESCRIPTION "Driver1 circuit2 Probe error"
                    ::= { digitalObjects 153 }

        -- 1.3.6.1.4.1.9839.2.1.1.154
        mal_eeprom_d3 OBJECT-TYPE
                    SYNTAX Integer32 (0..1)
                    UNITS "N/A"
                    MAX-ACCESS read-only
                    STATUS current
                    DESCRIPTION "Driver1 circuit2 Eeprom error"
                    ::= { digitalObjects 154 }

        -- 1.3.6.1.4.1.9839.2.1.1.155
        mal_step_m_d3 OBJECT-TYPE
                    SYNTAX Integer32 (0..1)
                    UNITS "N/A"
                    MAX-ACCESS read-only
                    STATUS current
                    DESCRIPTION "Driver1 circuit2 Step motor error"
                    ::= { digitalObjects 155 }

        -- 1.3.6.1.4.1.9839.2.1.1.156
        mal_battery_d3 OBJECT-TYPE
                    SYNTAX Integer32 (0..1)
                    UNITS "N/A"
                    MAX-ACCESS read-only
                    STATUS current
                    DESCRIPTION "Driver1 circuit2 battery error"
                    ::= { digitalObjects 156 }

        -- 1.3.6.1.4.1.9839.2.1.1.157
        mal_mop_d3 OBJECT-TYPE
                    SYNTAX Integer32 (0..1)
                    UNITS "N/A"
                    MAX-ACCESS read-only
                    STATUS current
                    DESCRIPTION "Driver1 circuit2 high pressure evaporator (MOP)"
                    ::= { digitalObjects 157 }

        -- 1.3.6.1.4.1.9839.2.1.1.158
        mal_lop_d3 OBJECT-TYPE
                    SYNTAX Integer32 (0..1)
                    UNITS "N/A"
                    MAX-ACCESS read-only
                    STATUS current
                    DESCRIPTION "Driver1 circuit2 low pressure evaporator (LOP)"
                    ::= { digitalObjects 158 }

        -- 1.3.6.1.4.1.9839.2.1.1.159
        mal_l_sheat_d3 OBJECT-TYPE
                    SYNTAX Integer32 (0..1)
                    UNITS "N/A"
                    MAX-ACCESS read-only
                    STATUS current
                    DESCRIPTION "Driver1 circuit2 low Superheat"
                    ::= { digitalObjects 159 }

        -- 1.3.6.1.4.1.9839.2.1.1.160
        mal_vlv_err_d3 OBJECT-TYPE
                    SYNTAX Integer32 (0..1)
                    UNITS "N/A"
                    MAX-ACCESS read-only
                    STATUS current
                    DESCRIPTION "Driver1 circuit2  Valve not closed during power OFF"
                    ::= { digitalObjects 160 }

        -- 1.3.6.1.4.1.9839.2.1.1.161
        mal_h_sheat_d3 OBJECT-TYPE
                    SYNTAX Integer32 (0..1)
                    UNITS "N/A"
                    MAX-ACCESS read-only
                    STATUS current
                    DESCRIPTION "Driver1 circuit2 high temperature suction"
                    ::= { digitalObjects 161 }

        -- 1.3.6.1.4.1.9839.2.1.1.162
        mgo_ahead_en3 OBJECT-TYPE
                    SYNTAX Integer32 (0..1)
                    UNITS "N/A"
                    MAX-ACCESS read-only
                    STATUS current
                    DESCRIPTION "Driver1 circuit2 Waiting for Eeprom/batt.charged"
                    ::= { digitalObjects 162 }

        -- 1.3.6.1.4.1.9839.2.1.1.163
        mal_probe_d4 OBJECT-TYPE
                    SYNTAX Integer32 (0..1)
                    UNITS "N/A"
                    MAX-ACCESS read-only
                    STATUS current
                    DESCRIPTION "Driver2 circuit2 Probe error"
                    ::= { digitalObjects 163 }

        -- 1.3.6.1.4.1.9839.2.1.1.164
        mal_eeprom_d4 OBJECT-TYPE
                    SYNTAX Integer32 (0..1)
                    UNITS "N/A"
                    MAX-ACCESS read-only
                    STATUS current
                    DESCRIPTION "Driver2 circuit2 Eeprom error"
                    ::= { digitalObjects 164 }

        -- 1.3.6.1.4.1.9839.2.1.1.165
        mal_step_m_d4 OBJECT-TYPE
                    SYNTAX Integer32 (0..1)
                    UNITS "N/A"
                    MAX-ACCESS read-only
                    STATUS current
                    DESCRIPTION "Driver2 circuit2 Step motor error"
                    ::= { digitalObjects 165 }

        -- 1.3.6.1.4.1.9839.2.1.1.166
        mal_battery_d4 OBJECT-TYPE
                    SYNTAX Integer32 (0..1)
                    UNITS "N/A"
                    MAX-ACCESS read-only
                    STATUS current
                    DESCRIPTION "Driver2 circuit2 battery error"
                    ::= { digitalObjects 166 }

        -- 1.3.6.1.4.1.9839.2.1.1.167
        mal_mop_d4 OBJECT-TYPE
                    SYNTAX Integer32 (0..1)
                    UNITS "N/A"
                    MAX-ACCESS read-only
                    STATUS current
                    DESCRIPTION "Driver2 circuit2 high pressure evaporator (MOP)"
                    ::= { digitalObjects 167 }

        -- 1.3.6.1.4.1.9839.2.1.1.168
        mal_lop_d4 OBJECT-TYPE
                    SYNTAX Integer32 (0..1)
                    UNITS "N/A"
                    MAX-ACCESS read-only
                    STATUS current
                    DESCRIPTION "Driver2 circuit2 low pressure evaporator (LOP)"
                    ::= { digitalObjects 168 }

        -- 1.3.6.1.4.1.9839.2.1.1.169
        mal_l_sheat_d4 OBJECT-TYPE
                    SYNTAX Integer32 (0..1)
                    UNITS "N/A"
                    MAX-ACCESS read-only
                    STATUS current
                    DESCRIPTION "Driver2 circuit2 low Superheat"
                    ::= { digitalObjects 169 }

        -- 1.3.6.1.4.1.9839.2.1.1.170
        mal_vlv_err_d4 OBJECT-TYPE
                    SYNTAX Integer32 (0..1)
                    UNITS "N/A"
                    MAX-ACCESS read-only
                    STATUS current
                    DESCRIPTION "Driver2 circuit2  Valve not closed during power OFF"
                    ::= { digitalObjects 170 }

        -- 1.3.6.1.4.1.9839.2.1.1.171
        mal_h_sheat_d4 OBJECT-TYPE
                    SYNTAX Integer32 (0..1)
                    UNITS "N/A"
                    MAX-ACCESS read-only
                    STATUS current
                    DESCRIPTION "Driver2 circuit2 high temperature suction"
                    ::= { digitalObjects 171 }

        -- 1.3.6.1.4.1.9839.2.1.1.172
        mgo_ahead_en4 OBJECT-TYPE
                    SYNTAX Integer32 (0..1)
                    UNITS "N/A"
                    MAX-ACCESS read-only
                    STATUS current
                    DESCRIPTION "Driver2 circuit2 Waiting for Eeprom/batt.charged"
                    ::= { digitalObjects 172 }

        -- 1.3.6.1.4.1.9839.2.1.1.173
        mal_driver1_offl OBJECT-TYPE
                    SYNTAX Integer32 (0..1)
                    UNITS "N/A"
                    MAX-ACCESS read-only
                    STATUS current
                    DESCRIPTION "Driver1 circuit1 Offline"
                    ::= { digitalObjects 173 }

        -- 1.3.6.1.4.1.9839.2.1.1.174
        mal_driver2_offl OBJECT-TYPE
                    SYNTAX Integer32 (0..1)
                    UNITS "N/A"
                    MAX-ACCESS read-only
                    STATUS current
                    DESCRIPTION "Driver2 circuit1 Offline"
                    ::= { digitalObjects 174 }

        -- 1.3.6.1.4.1.9839.2.1.1.175
        mal_driver3_offl OBJECT-TYPE
                    SYNTAX Integer32 (0..1)
                    UNITS "N/A"
                    MAX-ACCESS read-only
                    STATUS current
                    DESCRIPTION "Driver1 circuit2 Offline"
                    ::= { digitalObjects 175 }

        -- 1.3.6.1.4.1.9839.2.1.1.176
        mal_driver4_offl OBJECT-TYPE
                    SYNTAX Integer32 (0..1)
                    UNITS "N/A"
                    MAX-ACCESS read-only
                    STATUS current
                    DESCRIPTION "Driver2 circuit2 Offline"
                    ::= { digitalObjects 176 }

        -- 1.3.6.1.4.1.9839.2.1.1.177
        hpprevent_circ1 OBJECT-TYPE
                    SYNTAX Integer32 (0..1)
                    UNITS "N/A"
                    MAX-ACCESS read-only
                    STATUS current
                    DESCRIPTION "High pressure prevent circuit 1"
                    ::= { digitalObjects 177 }

        -- 1.3.6.1.4.1.9839.2.1.1.178
        hpprevent_circ2 OBJECT-TYPE
                    SYNTAX Integer32 (0..1)
                    UNITS "N/A"
                    MAX-ACCESS read-only
                    STATUS current
                    DESCRIPTION "High pressure prevent circuit 2"
                    ::= { digitalObjects 178 }

        -- 1.3.6.1.4.1.9839.2.1.1.179
        change_hour OBJECT-TYPE
                    SYNTAX Integer32 (0..1)
                    UNITS "N/A"
                    MAX-ACCESS read-write
                    STATUS current
                    DESCRIPTION "Confirm change hour/date"
                    ::= { digitalObjects 179 }

        -- 1.3.6.1.4.1.9839.2.1.1.180
        en_inlet_probe OBJECT-TYPE
                    SYNTAX Integer32 (0..1)
                    UNITS "N/A"
                    MAX-ACCESS read-only
                    STATUS current
                    DESCRIPTION "Enable inlet probe"
                    ::= { digitalObjects 180 }

        -- 1.3.6.1.4.1.9839.2.1.1.181
        en_outlet_probe OBJECT-TYPE
                    SYNTAX Integer32 (0..1)
                    UNITS "N/A"
                    MAX-ACCESS read-only
                    STATUS current
                    DESCRIPTION "Enable outlet probe"
                    ::= { digitalObjects 181 }

        -- 1.3.6.1.4.1.9839.2.1.1.182
        cooling_active OBJECT-TYPE
                    SYNTAX Integer32 (0..1)
                    UNITS "N/A"
                    MAX-ACCESS read-only
                    STATUS current
                    DESCRIPTION "Cooling mode"
                    ::= { digitalObjects 182 }

        -- 1.3.6.1.4.1.9839.2.1.1.183
        heating_active OBJECT-TYPE
                    SYNTAX Integer32 (0..1)
                    UNITS "N/A"
                    MAX-ACCESS read-only
                    STATUS current
                    DESCRIPTION "Heating mode"
                    ::= { digitalObjects 183 }



        -- 1.3.6.1.4.1.9839.2.1.2
        analogObjects OBJECT IDENTIFIER ::= { mod_ch_18MIB 2 }

        -- 1.3.6.1.4.1.9839.2.1.2.1
        ain_1 OBJECT-TYPE
                    SYNTAX Integer32 (-32767..32767)
                    UNITS "bar/&deg;C x10"
                    MAX-ACCESS read-only
                    STATUS current
                    DESCRIPTION "Analogue input 1"
                    ::= { analogObjects 1 }

        -- 1.3.6.1.4.1.9839.2.1.2.2
        ain_2 OBJECT-TYPE
                    SYNTAX Integer32 (-32767..32767)
                    UNITS "bar/&deg;C x10"
                    MAX-ACCESS read-only
                    STATUS current
                    DESCRIPTION "Analogue input 2"
                    ::= { analogObjects 2 }

        -- 1.3.6.1.4.1.9839.2.1.2.3
        ain_3 OBJECT-TYPE
                    SYNTAX Integer32 (-32767..32767)
                    UNITS "bar/&deg;C x10"
                    MAX-ACCESS read-only
                    STATUS current
                    DESCRIPTION "Analogue input 3"
                    ::= { analogObjects 3 }

        -- 1.3.6.1.4.1.9839.2.1.2.4
        ain_4 OBJECT-TYPE
                    SYNTAX Integer32 (-32767..32767)
                    UNITS "bar/&deg;C x10"
                    MAX-ACCESS read-only
                    STATUS current
                    DESCRIPTION "Analogue input 4"
                    ::= { analogObjects 4 }

        -- 1.3.6.1.4.1.9839.2.1.2.5
        ain_5 OBJECT-TYPE
                    SYNTAX Integer32 (-32767..32767)
                    UNITS "bar/&deg;C x10"
                    MAX-ACCESS read-only
                    STATUS current
                    DESCRIPTION "Analogue input 5"
                    ::= { analogObjects 5 }

        -- 1.3.6.1.4.1.9839.2.1.2.6
        ain_6 OBJECT-TYPE
                    SYNTAX Integer32 (-32767..32767)
                    UNITS "bar/&deg;C x10"
                    MAX-ACCESS read-only
                    STATUS current
                    DESCRIPTION "Analogue input 6"
                    ::= { analogObjects 6 }

        -- 1.3.6.1.4.1.9839.2.1.2.7
        ain_7 OBJECT-TYPE
                    SYNTAX Integer32 (-32767..32767)
                    UNITS "bar/&deg;C x10"
                    MAX-ACCESS read-only
                    STATUS current
                    DESCRIPTION "Analogue input 7"
                    ::= { analogObjects 7 }

        -- 1.3.6.1.4.1.9839.2.1.2.8
        ain_8 OBJECT-TYPE
                    SYNTAX Integer32 (-32767..32767)
                    UNITS "bar/&deg;C x10"
                    MAX-ACCESS read-only
                    STATUS current
                    DESCRIPTION "Analogue input 8"
                    ::= { analogObjects 8 }

        -- 1.3.6.1.4.1.9839.2.1.2.9
        analog_out_1 OBJECT-TYPE
                    SYNTAX Integer32 (-32767..32767)
                    UNITS "% x10"
                    MAX-ACCESS read-only
                    STATUS current
                    DESCRIPTION "Analogue output 1"
                    ::= { analogObjects 9 }

        -- 1.3.6.1.4.1.9839.2.1.2.10
        analog_out_2 OBJECT-TYPE
                    SYNTAX Integer32 (-32767..32767)
                    UNITS "% x10"
                    MAX-ACCESS read-only
                    STATUS current
                    DESCRIPTION "Analogue output 2"
                    ::= { analogObjects 10 }

        -- 1.3.6.1.4.1.9839.2.1.2.11
        s_temp_setpoint OBJECT-TYPE
                    SYNTAX Integer32 (-32767..32767)
                    UNITS "°C x10"
                    MAX-ACCESS read-write
                    STATUS current
                    DESCRIPTION "Cooling set point (evaporator set point)"
                    ::= { analogObjects 11 }

        -- 1.3.6.1.4.1.9839.2.1.2.12
        w_temp_setpoint OBJECT-TYPE
                    SYNTAX Integer32 (-32767..32767)
                    UNITS "°C x10"
                    MAX-ACCESS read-write
                    STATUS current
                    DESCRIPTION "Heating set point (condenser set point)"
                    ::= { analogObjects 12 }

        -- 1.3.6.1.4.1.9839.2.1.2.13
        cond_setpoint OBJECT-TYPE
                    SYNTAX Integer32 (-32767..32767)
                    UNITS "bar/&deg;C x10"
                    MAX-ACCESS read-write
                    STATUS current
                    DESCRIPTION "Condenser control set point"
                    ::= { analogObjects 13 }

        -- 1.3.6.1.4.1.9839.2.1.2.14
        in_temp_setp OBJECT-TYPE
                    SYNTAX Integer32 (-32767..32767)
                    UNITS "°C x10"
                    MAX-ACCESS read-only
                    STATUS current
                    DESCRIPTION "Current set point"
                    ::= { analogObjects 14 }

        -- 1.3.6.1.4.1.9839.2.1.2.16
        fc_delta OBJECT-TYPE
                    SYNTAX Integer32 (-32767..32767)
                    UNITS "°C x10"
                    MAX-ACCESS read-write
                    STATUS current
                    DESCRIPTION "Freecooling Delta min"
                    ::= { analogObjects 16 }

        -- 1.3.6.1.4.1.9839.2.1.2.17
        fc_diff OBJECT-TYPE
                    SYNTAX Integer32 (-32767..32767)
                    UNITS "°C x10"
                    MAX-ACCESS read-write
                    STATUS current
                    DESCRIPTION "Freecooling Diff"
                    ::= { analogObjects 17 }

        -- 1.3.6.1.4.1.9839.2.1.2.18
        start_defr_setp OBJECT-TYPE
                    SYNTAX Integer32 (-32767..32767)
                    UNITS "bar/&deg;C x10"
                    MAX-ACCESS read-write
                    STATUS current
                    DESCRIPTION "Start defrost setpoint"
                    ::= { analogObjects 18 }

        -- 1.3.6.1.4.1.9839.2.1.2.19
        stop_defr_setp OBJECT-TYPE
                    SYNTAX Integer32 (-32767..32767)
                    UNITS "bar/&deg;C x10"
                    MAX-ACCESS read-write
                    STATUS current
                    DESCRIPTION "Stop defrost setpoint"
                    ::= { analogObjects 19 }

        -- 1.3.6.1.4.1.9839.2.1.2.20
        sum_low_t_lim OBJECT-TYPE
                    SYNTAX Integer32 (-32767..32767)
                    UNITS "°C x10"
                    MAX-ACCESS read-write
                    STATUS current
                    DESCRIPTION "Low summer limit setpoint"
                    ::= { analogObjects 20 }

        -- 1.3.6.1.4.1.9839.2.1.2.21
        sum_high_t_lim OBJECT-TYPE
                    SYNTAX Integer32 (-32767..32767)
                    UNITS "°C x10"
                    MAX-ACCESS read-write
                    STATUS current
                    DESCRIPTION "High summer limit setpoint"
                    ::= { analogObjects 21 }

        -- 1.3.6.1.4.1.9839.2.1.2.22
        win_low_t_lim OBJECT-TYPE
                    SYNTAX Integer32 (-32767..32767)
                    UNITS "°C x10"
                    MAX-ACCESS read-write
                    STATUS current
                    DESCRIPTION "Low winter limit setpoint"
                    ::= { analogObjects 22 }

        -- 1.3.6.1.4.1.9839.2.1.2.23
        win_high_t_lim OBJECT-TYPE
                    SYNTAX Integer32 (-32767..32767)
                    UNITS "°C x10"
                    MAX-ACCESS read-write
                    STATUS current
                    DESCRIPTION "High winter limit setpoint"
                    ::= { analogObjects 23 }

        -- 1.3.6.1.4.1.9839.2.1.2.24
        rec_setp OBJECT-TYPE
                    SYNTAX Integer32 (-32767..32767)
                    UNITS "°C x10"
                    MAX-ACCESS read-write
                    STATUS current
                    DESCRIPTION "Recovery setpoint"
                    ::= { analogObjects 24 }

        -- 1.3.6.1.4.1.9839.2.1.2.25
        rec_diff OBJECT-TYPE
                    SYNTAX Integer32 (-32767..32767)
                    UNITS "°C x10"
                    MAX-ACCESS read-write
                    STATUS current
                    DESCRIPTION "Recovery differential"
                    ::= { analogObjects 25 }

        -- 1.3.6.1.4.1.9839.2.1.2.26
        aout_1_disp_s OBJECT-TYPE
                    SYNTAX Integer32 (-32767..32767)
                    UNITS "N/A"
                    MAX-ACCESS read-only
                    STATUS current
                    DESCRIPTION "Status 1 analog output"
                    ::= { analogObjects 26 }

        -- 1.3.6.1.4.1.9839.2.1.2.27
        aout_2_disp_s OBJECT-TYPE
                    SYNTAX Integer32 (-32767..32767)
                    UNITS "N/A"
                    MAX-ACCESS read-only
                    STATUS current
                    DESCRIPTION "Status 2 analog output"
                    ::= { analogObjects 27 }

        -- 1.3.6.1.4.1.9839.2.1.2.28
        cond_diff OBJECT-TYPE
                    SYNTAX Integer32 (-32767..32767)
                    UNITS "bar/&deg;C x10"
                    MAX-ACCESS read-write
                    STATUS current
                    DESCRIPTION "Cond differential"
                    ::= { analogObjects 28 }

        -- 1.3.6.1.4.1.9839.2.1.2.29
        actual_sheat_d1 OBJECT-TYPE
                    SYNTAX Integer32 (-32767..32767)
                    UNITS "°K x10"
                    MAX-ACCESS read-only
                    STATUS current
                    DESCRIPTION "Actual SuperHeat driver 1 (circ.1)"
                    ::= { analogObjects 29 }

        -- 1.3.6.1.4.1.9839.2.1.2.30
        actual_sheat_d2 OBJECT-TYPE
                    SYNTAX Integer32 (-32767..32767)
                    UNITS "°K x10"
                    MAX-ACCESS read-only
                    STATUS current
                    DESCRIPTION "Actual SuperHeat driver 2 (circ.1)"
                    ::= { analogObjects 30 }

        -- 1.3.6.1.4.1.9839.2.1.2.31
        actual_sheat_d3 OBJECT-TYPE
                    SYNTAX Integer32 (-32767..32767)
                    UNITS "°K x10"
                    MAX-ACCESS read-only
                    STATUS current
                    DESCRIPTION "Actual SuperHeat driver 1 (circ.2)"
                    ::= { analogObjects 31 }

        -- 1.3.6.1.4.1.9839.2.1.2.32
        actual_sheat_d4 OBJECT-TYPE
                    SYNTAX Integer32 (-32767..32767)
                    UNITS "°K x10"
                    MAX-ACCESS read-only
                    STATUS current
                    DESCRIPTION "Actual SuperHeat driver 2 (circ.2)"
                    ::= { analogObjects 32 }

        -- 1.3.6.1.4.1.9839.2.1.2.33
        saturation_temp_d1 OBJECT-TYPE
                    SYNTAX Integer32 (-32767..32767)
                    UNITS "°C x10"
                    MAX-ACCESS read-only
                    STATUS current
                    DESCRIPTION "Saturation temp driver 1 (circ.1)"
                    ::= { analogObjects 33 }

        -- 1.3.6.1.4.1.9839.2.1.2.34
        saturation_temp_d2 OBJECT-TYPE
                    SYNTAX Integer32 (-32767..32767)
                    UNITS "°C x10"
                    MAX-ACCESS read-only
                    STATUS current
                    DESCRIPTION "Saturation temp driver 2 (circ.1)"
                    ::= { analogObjects 34 }

        -- 1.3.6.1.4.1.9839.2.1.2.35
        saturation_temp_d3 OBJECT-TYPE
                    SYNTAX Integer32 (-32767..32767)
                    UNITS "°C x10"
                    MAX-ACCESS read-only
                    STATUS current
                    DESCRIPTION "Saturation temp driver 1 (circ.2)"
                    ::= { analogObjects 35 }

        -- 1.3.6.1.4.1.9839.2.1.2.36
        saturation_temp_d4 OBJECT-TYPE
                    SYNTAX Integer32 (-32767..32767)
                    UNITS "°C x10"
                    MAX-ACCESS read-only
                    STATUS current
                    DESCRIPTION "Saturation temp driver 2 (circ.2)"
                    ::= { analogObjects 36 }

        -- 1.3.6.1.4.1.9839.2.1.2.37
        suction_temp_d1 OBJECT-TYPE
                    SYNTAX Integer32 (-32767..32767)
                    UNITS "°C x10"
                    MAX-ACCESS read-only
                    STATUS current
                    DESCRIPTION "Suction temp driver 1 (circ.1)"
                    ::= { analogObjects 37 }

        -- 1.3.6.1.4.1.9839.2.1.2.38
        suction_temp_d2 OBJECT-TYPE
                    SYNTAX Integer32 (-32767..32767)
                    UNITS "°C x10"
                    MAX-ACCESS read-only
                    STATUS current
                    DESCRIPTION "Suction temp driver 2 (circ.1)"
                    ::= { analogObjects 38 }

        -- 1.3.6.1.4.1.9839.2.1.2.39
        suction_temp_d3 OBJECT-TYPE
                    SYNTAX Integer32 (-32767..32767)
                    UNITS "°C x10"
                    MAX-ACCESS read-only
                    STATUS current
                    DESCRIPTION "Suction temp driver 1 (circ.2)"
                    ::= { analogObjects 39 }

        -- 1.3.6.1.4.1.9839.2.1.2.40
        suction_temp_d4 OBJECT-TYPE
                    SYNTAX Integer32 (-32767..32767)
                    UNITS "°C x10"
                    MAX-ACCESS read-only
                    STATUS current
                    DESCRIPTION "Suction temp driver 2 (circ.2)"
                    ::= { analogObjects 40 }

        -- 1.3.6.1.4.1.9839.2.1.2.41
        suction_press_d1 OBJECT-TYPE
                    SYNTAX Integer32 (-32767..32767)
                    UNITS "°C x10"
                    MAX-ACCESS read-only
                    STATUS current
                    DESCRIPTION "Suction press driver 1 (circ.1)"
                    ::= { analogObjects 41 }

        -- 1.3.6.1.4.1.9839.2.1.2.42
        suction_press_d2 OBJECT-TYPE
                    SYNTAX Integer32 (-32767..32767)
                    UNITS "°C x10"
                    MAX-ACCESS read-only
                    STATUS current
                    DESCRIPTION "Suction press driver 2 (circ.1)"
                    ::= { analogObjects 42 }

        -- 1.3.6.1.4.1.9839.2.1.2.43
        suction_press_d3 OBJECT-TYPE
                    SYNTAX Integer32 (-32767..32767)
                    UNITS "°C x10"
                    MAX-ACCESS read-only
                    STATUS current
                    DESCRIPTION "Suction press driver 1 (circ.2)"
                    ::= { analogObjects 43 }

        -- 1.3.6.1.4.1.9839.2.1.2.44
        suction_press_d4 OBJECT-TYPE
                    SYNTAX Integer32 (-32767..32767)
                    UNITS "°C x10"
                    MAX-ACCESS read-only
                    STATUS current
                    DESCRIPTION "Suction press driver 2 (circ.2)"
                    ::= { analogObjects 44 }

        -- 1.3.6.1.4.1.9839.2.1.2.45
        active_in_temp OBJECT-TYPE
                    SYNTAX Integer32 (-32767..32767)
                    UNITS "°C x10"
                    MAX-ACCESS read-only
                    STATUS current
                    DESCRIPTION "Main input temperature"
                    ::= { analogObjects 45 }

        -- 1.3.6.1.4.1.9839.2.1.2.46
        active_out_temp OBJECT-TYPE
                    SYNTAX Integer32 (-32767..32767)
                    UNITS "°C x10"
                    MAX-ACCESS read-only
                    STATUS current
                    DESCRIPTION "Main output temperature"
                    ::= { analogObjects 46 }



        -- 1.3.6.1.4.1.9839.2.1.3
        integerObjects OBJECT IDENTIFIER ::= { mod_ch_18MIB 3 }

        -- 1.3.6.1.4.1.9839.2.1.3.10
        cu_remote_ctrl OBJECT-TYPE
                    SYNTAX Integer32 (-32767..32767)
                    UNITS "N/A"
                    MAX-ACCESS read-only
                    STATUS current
                    DESCRIPTION "Compressor remote control status"
                    ::= { integerObjects 10 }

        -- 1.3.6.1.4.1.9839.2.1.3.11
        recover_mode OBJECT-TYPE
                    SYNTAX Integer32 (-32767..32767)
                    UNITS "N/A"
                    MAX-ACCESS read-only
                    STATUS current
                    DESCRIPTION "Recovery mode "
                    ::= { integerObjects 11 }

        -- 1.3.6.1.4.1.9839.2.1.3.12
        unit_status OBJECT-TYPE
                    SYNTAX Integer32 (-32767..32767)
                    UNITS "N/A"
                    MAX-ACCESS read-only
                    STATUS current
                    DESCRIPTION "Unit status"
                    ::= { integerObjects 12 }

        -- 1.3.6.1.4.1.9839.2.1.3.13
        cond_fans_mng OBJECT-TYPE
                    SYNTAX Integer32 (0..2)
                    UNITS "N/A"
                    MAX-ACCESS read-write
                    STATUS current
                    DESCRIPTION "Fan control type (1= Press,2= Temp)"
                    DEFVAL { 2 }
                    ::= { integerObjects 13 }

        -- 1.3.6.1.4.1.9839.2.1.3.20
        x_h_main_pump OBJECT-TYPE
                    SYNTAX Integer32 (-32767..32767)
                    UNITS "N/A"
                    MAX-ACCESS read-only
                    STATUS current
                    DESCRIPTION "Main pump operating hour count (high byte)"
                    ::= { integerObjects 20 }

        -- 1.3.6.1.4.1.9839.2.1.3.21
        x_l_main_pump OBJECT-TYPE
                    SYNTAX Integer32 (0..32767)
                    UNITS "hour"
                    MAX-ACCESS read-only
                    STATUS current
                    DESCRIPTION "Main pump operating hour count (low byte)"
                    ::= { integerObjects 21 }

        -- 1.3.6.1.4.1.9839.2.1.3.22
        x_h_comp1 OBJECT-TYPE
                    SYNTAX Integer32 (0..32767)
                    UNITS "N/A"
                    MAX-ACCESS read-only
                    STATUS current
                    DESCRIPTION "Compressor 1 operating hour count (high byte)"
                    ::= { integerObjects 22 }

        -- 1.3.6.1.4.1.9839.2.1.3.23
        x_l_comp1 OBJECT-TYPE
                    SYNTAX Integer32 (0..32767)
                    UNITS "hour"
                    MAX-ACCESS read-only
                    STATUS current
                    DESCRIPTION "Compressor 1 operating hour count (low byte)"
                    ::= { integerObjects 23 }

        -- 1.3.6.1.4.1.9839.2.1.3.24
        x_h_comp2 OBJECT-TYPE
                    SYNTAX Integer32 (0..32767)
                    UNITS "N/A"
                    MAX-ACCESS read-only
                    STATUS current
                    DESCRIPTION "Compressor 2 operating hour count (high byte)"
                    ::= { integerObjects 24 }

        -- 1.3.6.1.4.1.9839.2.1.3.25
        x_l_comp2 OBJECT-TYPE
                    SYNTAX Integer32 (0..32767)
                    UNITS "hour"
                    MAX-ACCESS read-only
                    STATUS current
                    DESCRIPTION "Compressor 2 operating hour count (low byte)"
                    ::= { integerObjects 25 }

        -- 1.3.6.1.4.1.9839.2.1.3.26
        x_h_comp3 OBJECT-TYPE
                    SYNTAX Integer32 (0..32767)
                    UNITS "N/A"
                    MAX-ACCESS read-only
                    STATUS current
                    DESCRIPTION "Compressor 3 operating hour count (high byte)"
                    ::= { integerObjects 26 }

        -- 1.3.6.1.4.1.9839.2.1.3.27
        x_l_comp3 OBJECT-TYPE
                    SYNTAX Integer32 (0..32767)
                    UNITS "hour"
                    MAX-ACCESS read-only
                    STATUS current
                    DESCRIPTION "Compressor 3 operating hour count (low byte)"
                    ::= { integerObjects 27 }

        -- 1.3.6.1.4.1.9839.2.1.3.28
        x_h_comp4 OBJECT-TYPE
                    SYNTAX Integer32 (0..32767)
                    UNITS "N/A"
                    MAX-ACCESS read-only
                    STATUS current
                    DESCRIPTION "Compressor 4 operating hour count (high byte)"
                    ::= { integerObjects 28 }

        -- 1.3.6.1.4.1.9839.2.1.3.29
        x_l_comp4 OBJECT-TYPE
                    SYNTAX Integer32 (0..32767)
                    UNITS "hour"
                    MAX-ACCESS read-only
                    STATUS current
                    DESCRIPTION "Compressor 4 operating hour count (low byte)"
                    ::= { integerObjects 29 }

        -- 1.3.6.1.4.1.9839.2.1.3.30
        config_unit OBJECT-TYPE
                    SYNTAX Integer32 (-32767..32767)
                    UNITS "N/A"
                    MAX-ACCESS read-only
                    STATUS current
                    DESCRIPTION "Device configuration for all units ( 0=CCCC, 1=CpCp, 2=Cppp)"
                    ::= { integerObjects 30 }

        -- 1.3.6.1.4.1.9839.2.1.3.31
        config_type OBJECT-TYPE
                    SYNTAX Integer32 (0..23)
                    UNITS "N/A"
                    MAX-ACCESS read-write
                    STATUS current
                    DESCRIPTION "Select type of unit: 0 to 23 (see manual)"
                    DEFVAL { 16 }
                    ::= { integerObjects 31 }

        -- 1.3.6.1.4.1.9839.2.1.3.32
        ph_circ_type OBJECT-TYPE
                    SYNTAX Integer32 (-32767..32767)
                    UNITS "N/A"
                    MAX-ACCESS read-only
                    STATUS current
                    DESCRIPTION "Type of circuit"
                    ::= { integerObjects 32 }

        -- 1.3.6.1.4.1.9839.2.1.3.33
        n_comps OBJECT-TYPE
                    SYNTAX Integer32 (1..8)
                    UNITS "N/A"
                    MAX-ACCESS read-write
                    STATUS current
                    DESCRIPTION "Total number of compressors on the machine"
                    DEFVAL { 1 }
                    ::= { integerObjects 33 }

        -- 1.3.6.1.4.1.9839.2.1.3.34
        comps_x_unit OBJECT-TYPE
                    SYNTAX Integer32 (1..4)
                    UNITS "N/A"
                    MAX-ACCESS read-only
                    STATUS current
                    DESCRIPTION "Number of compressors per unit"
                    DEFVAL { 1 }
                    ::= { integerObjects 34 }

        -- 1.3.6.1.4.1.9839.2.1.3.35
        n_unloaders OBJECT-TYPE
                    SYNTAX Integer32 (1..3)
                    UNITS "N/A"
                    MAX-ACCESS read-write
                    STATUS current
                    DESCRIPTION "Number of Unloaders per compressor (same for all units)"
                    DEFVAL { 3 }
                    ::= { integerObjects 35 }

        -- 1.3.6.1.4.1.9839.2.1.3.36
        cond_fans OBJECT-TYPE
                    SYNTAX Integer32 (0..3)
                    UNITS "N/A"
                    MAX-ACCESS read-write
                    STATUS current
                    DESCRIPTION "Number of condenser fans"
                    DEFVAL { 1 }
                    ::= { integerObjects 36 }

        -- 1.3.6.1.4.1.9839.2.1.3.37
        fan1_speed_reg OBJECT-TYPE
                    SYNTAX Integer32 (-32767..32767)
                    UNITS "N/A"
                    MAX-ACCESS read-only
                    STATUS current
                    DESCRIPTION "Inverter speed circuit 1"
                    ::= { integerObjects 37 }

        -- 1.3.6.1.4.1.9839.2.1.3.38
        fan2_speed_reg OBJECT-TYPE
                    SYNTAX Integer32 (-32767..32767)
                    UNITS "N/A"
                    MAX-ACCESS read-only
                    STATUS current
                    DESCRIPTION "Inverter speed circuit 2"
                    ::= { integerObjects 38 }

        -- 1.3.6.1.4.1.9839.2.1.3.39
        freecool_valve OBJECT-TYPE
                    SYNTAX Integer32 (-32767..32767)
                    UNITS "N/A"
                    MAX-ACCESS read-only
                    STATUS current
                    DESCRIPTION "Freecooling valve opening"
                    ::= { integerObjects 39 }

        -- 1.3.6.1.4.1.9839.2.1.3.40
        aout_1_display OBJECT-TYPE
                    SYNTAX Integer32 (-32767..32767)
                    UNITS "N/A"
                    MAX-ACCESS read-only
                    STATUS current
                    DESCRIPTION "Status of analogue output 1"
                    ::= { integerObjects 40 }

        -- 1.3.6.1.4.1.9839.2.1.3.41
        aout_2_display OBJECT-TYPE
                    SYNTAX Integer32 (-32767..32767)
                    UNITS "N/A"
                    MAX-ACCESS read-only
                    STATUS current
                    DESCRIPTION "Status of analogue output 2"
                    ::= { integerObjects 41 }

        -- 1.3.6.1.4.1.9839.2.1.3.42
        defr_type OBJECT-TYPE
                    SYNTAX Integer32 (1..3)
                    UNITS "N/A"
                    MAX-ACCESS read-write
                    STATUS current
                    DESCRIPTION "Type of defrost (0=temp, 1=Press,2= pressostat)"
                    DEFVAL { 3 }
                    ::= { integerObjects 42 }

        -- 1.3.6.1.4.1.9839.2.1.3.43
        thr_defr OBJECT-TYPE
                    SYNTAX Integer32 (-32767..32767)
                    UNITS "s"
                    MAX-ACCESS read-write
                    STATUS current
                    DESCRIPTION "Delay time start defrost"
                    ::= { integerObjects 43 }

        -- 1.3.6.1.4.1.9839.2.1.3.44
        defr_max_time OBJECT-TYPE
                    SYNTAX Integer32 (-32767..32767)
                    UNITS "s"
                    MAX-ACCESS read-write
                    STATUS current
                    DESCRIPTION "Time max defrost"
                    ::= { integerObjects 44 }

        -- 1.3.6.1.4.1.9839.2.1.3.45
        defr_comp_off_t OBJECT-TYPE
                    SYNTAX Integer32 (-32767..32767)
                    UNITS "s"
                    MAX-ACCESS read-write
                    STATUS current
                    DESCRIPTION "Enable force compressors off when the defrost starts or ends"
                    ::= { integerObjects 45 }

        -- 1.3.6.1.4.1.9839.2.1.3.47
        drivers_number OBJECT-TYPE
                    SYNTAX Integer32 (-32767..32767)
                    UNITS "N/A"
                    MAX-ACCESS read-write
                    STATUS current
                    DESCRIPTION "Number driver"
                    ::= { integerObjects 47 }

        -- 1.3.6.1.4.1.9839.2.1.3.48
        sheat_set_ch_d1 OBJECT-TYPE
                    SYNTAX Integer32 (-32767..32767)
                    UNITS "°C"
                    MAX-ACCESS read-write
                    STATUS current
                    DESCRIPTION "SuperHeat setpoint for driver1 circuit1 in Chiller operation"
                    ::= { integerObjects 48 }

        -- 1.3.6.1.4.1.9839.2.1.3.50
        sheat_set_ch_d3 OBJECT-TYPE
                    SYNTAX Integer32 (-32767..32767)
                    UNITS "°C"
                    MAX-ACCESS read-write
                    STATUS current
                    DESCRIPTION "SuperHeat setpoint for driver1 circuit2 in Chiller operation"
                    ::= { integerObjects 50 }

        -- 1.3.6.1.4.1.9839.2.1.3.52
        sheat_set_hp_d1 OBJECT-TYPE
                    SYNTAX Integer32 (-32767..32767)
                    UNITS "°C"
                    MAX-ACCESS read-write
                    STATUS current
                    DESCRIPTION "SuperHeat setpoint driver1 circuit1 in HP operation"
                    ::= { integerObjects 52 }

        -- 1.3.6.1.4.1.9839.2.1.3.53
        sheat_set_hp_d2 OBJECT-TYPE
                    SYNTAX Integer32 (-32767..32767)
                    UNITS "°C"
                    MAX-ACCESS read-write
                    STATUS current
                    DESCRIPTION "SuperHeat setpoint driver2 circuit1 in HP operation"
                    ::= { integerObjects 53 }

        -- 1.3.6.1.4.1.9839.2.1.3.54
        sheat_set_hp_d3 OBJECT-TYPE
                    SYNTAX Integer32 (-32767..32767)
                    UNITS "°C"
                    MAX-ACCESS read-write
                    STATUS current
                    DESCRIPTION "SuperHeat setpoint driver1 circuit2 in HP operation"
                    ::= { integerObjects 54 }

        -- 1.3.6.1.4.1.9839.2.1.3.55
        sheat_set_hp_d4 OBJECT-TYPE
                    SYNTAX Integer32 (-32767..32767)
                    UNITS "°C"
                    MAX-ACCESS read-write
                    STATUS current
                    DESCRIPTION "SuperHeat setpoint driver2 circuit2 in HP operation"
                    ::= { integerObjects 55 }

        -- 1.3.6.1.4.1.9839.2.1.3.56
        sheat_set_df_d1 OBJECT-TYPE
                    SYNTAX Integer32 (-32767..32767)
                    UNITS "°C"
                    MAX-ACCESS read-write
                    STATUS current
                    DESCRIPTION "SuperHeat setpoint driver1 circuit1 in Defrost operation"
                    ::= { integerObjects 56 }

        -- 1.3.6.1.4.1.9839.2.1.3.58
        sheat_set_df_d3 OBJECT-TYPE
                    SYNTAX Integer32 (-32767..32767)
                    UNITS "°C"
                    MAX-ACCESS read-write
                    STATUS current
                    DESCRIPTION "SuperHeat setpoint driver1 circuit2 in Defrost operation"
                    ::= { integerObjects 58 }

        -- 1.3.6.1.4.1.9839.2.1.3.60
        thresh_lop_ch OBJECT-TYPE
                    SYNTAX Integer32 (-32767..32767)
                    UNITS "°C"
                    MAX-ACCESS read-write
                    STATUS current
                    DESCRIPTION "MOP limit in chiller operation"
                    ::= { integerObjects 60 }

        -- 1.3.6.1.4.1.9839.2.1.3.61
        thresh_mop_ch OBJECT-TYPE
                    SYNTAX Integer32 (-32767..32767)
                    UNITS "°C"
                    MAX-ACCESS read-write
                    STATUS current
                    DESCRIPTION "LOP limit in chiller operation"
                    ::= { integerObjects 61 }

        -- 1.3.6.1.4.1.9839.2.1.3.62
        thresh_lop_hp OBJECT-TYPE
                    SYNTAX Integer32 (-32767..32767)
                    UNITS "°C"
                    MAX-ACCESS read-write
                    STATUS current
                    DESCRIPTION "MOP limit in defrost operation"
                    ::= { integerObjects 62 }

        -- 1.3.6.1.4.1.9839.2.1.3.63
        thresh_mop_hp OBJECT-TYPE
                    SYNTAX Integer32 (-32767..32767)
                    UNITS "°C"
                    MAX-ACCESS read-write
                    STATUS current
                    DESCRIPTION "LOP limit in defrost operation"
                    ::= { integerObjects 63 }

        -- 1.3.6.1.4.1.9839.2.1.3.64
        thresh_lop_df OBJECT-TYPE
                    SYNTAX Integer32 (-32767..32767)
                    UNITS "°C"
                    MAX-ACCESS read-write
                    STATUS current
                    DESCRIPTION "MOP limit in heat pump operation"
                    ::= { integerObjects 64 }

        -- 1.3.6.1.4.1.9839.2.1.3.65
        thresh_mop_df OBJECT-TYPE
                    SYNTAX Integer32 (-32767..32767)
                    UNITS "°C"
                    MAX-ACCESS read-write
                    STATUS current
                    DESCRIPTION "LOP limit in heat pump operation"
                    ::= { integerObjects 65 }

        -- 1.3.6.1.4.1.9839.2.1.3.66
        lminute OBJECT-TYPE
                    SYNTAX Integer32 (0..59)
                    UNITS "min"
                    MAX-ACCESS read-write
                    STATUS current
                    DESCRIPTION "Setting minute"
                    ::= { integerObjects 66 }

        -- 1.3.6.1.4.1.9839.2.1.3.67
        lhour OBJECT-TYPE
                    SYNTAX Integer32 (0..23)
                    UNITS "hour"
                    MAX-ACCESS read-write
                    STATUS current
                    DESCRIPTION "Setting hour"
                    ::= { integerObjects 67 }

        -- 1.3.6.1.4.1.9839.2.1.3.68
        minute OBJECT-TYPE
                    SYNTAX Integer32 (0..59)
                    UNITS "min"
                    MAX-ACCESS read-only
                    STATUS current
                    DESCRIPTION "Actual minute"
                    ::= { integerObjects 68 }

        -- 1.3.6.1.4.1.9839.2.1.3.69
        hour OBJECT-TYPE
                    SYNTAX Integer32 (1..24)
                    UNITS "hour"
                    MAX-ACCESS read-only
                    STATUS current
                    DESCRIPTION "Actual hour"
                    ::= { integerObjects 69 }

        -- 1.3.6.1.4.1.9839.2.1.3.70
        type_ain1 OBJECT-TYPE
                    SYNTAX Integer32 (-32767..32767)
                    UNITS "N/A"
                    MAX-ACCESS read-only
                    STATUS current
                    DESCRIPTION "Type of probe connected to analogue input 1"
                    ::= { integerObjects 70 }

        -- 1.3.6.1.4.1.9839.2.1.3.71
        type_ain2 OBJECT-TYPE
                    SYNTAX Integer32 (-32767..32767)
                    UNITS "N/A"
                    MAX-ACCESS read-only
                    STATUS current
                    DESCRIPTION "Type of probe connected to analogue input 2"
                    ::= { integerObjects 71 }

        -- 1.3.6.1.4.1.9839.2.1.3.72
        type_ain3 OBJECT-TYPE
                    SYNTAX Integer32 (-32767..32767)
                    UNITS "N/A"
                    MAX-ACCESS read-only
                    STATUS current
                    DESCRIPTION "Type of probe connected to analogue input 3"
                    ::= { integerObjects 72 }

        -- 1.3.6.1.4.1.9839.2.1.3.73
        type_ain4 OBJECT-TYPE
                    SYNTAX Integer32 (-32767..32767)
                    UNITS "N/A"
                    MAX-ACCESS read-only
                    STATUS current
                    DESCRIPTION "Type of probe connected to analogue input 4"
                    ::= { integerObjects 73 }

        -- 1.3.6.1.4.1.9839.2.1.3.74
        type_ain5 OBJECT-TYPE
                    SYNTAX Integer32 (-32767..32767)
                    UNITS "N/A"
                    MAX-ACCESS read-only
                    STATUS current
                    DESCRIPTION "Type of probe connected to analogue input 5"
                    ::= { integerObjects 74 }

        -- 1.3.6.1.4.1.9839.2.1.3.75
        type_ain6 OBJECT-TYPE
                    SYNTAX Integer32 (-32767..32767)
                    UNITS "N/A"
                    MAX-ACCESS read-only
                    STATUS current
                    DESCRIPTION "Type of probe connected to analogue input 6"
                    ::= { integerObjects 75 }

        -- 1.3.6.1.4.1.9839.2.1.3.76
        type_ain7 OBJECT-TYPE
                    SYNTAX Integer32 (-32767..32767)
                    UNITS "N/A"
                    MAX-ACCESS read-only
                    STATUS current
                    DESCRIPTION "Type of probe connected to analogue input 7"
                    ::= { integerObjects 76 }

        -- 1.3.6.1.4.1.9839.2.1.3.77
        type_ain8 OBJECT-TYPE
                    SYNTAX Integer32 (-32767..32767)
                    UNITS "N/A"
                    MAX-ACCESS read-only
                    STATUS current
                    DESCRIPTION "Type of probe connected to analogue input 8"
                    ::= { integerObjects 77 }

        -- 1.3.6.1.4.1.9839.2.1.3.78
        total_steps OBJECT-TYPE
                    SYNTAX Integer32 (-32767..32767)
                    UNITS "N/A"
                    MAX-ACCESS read-only
                    STATUS current
                    DESCRIPTION "Total steps of the unit"
                    ::= { integerObjects 78 }

        -- 1.3.6.1.4.1.9839.2.1.3.79
        total_steps_act OBJECT-TYPE
                    SYNTAX Integer32 (-32767..32767)
                    UNITS "N/A"
                    MAX-ACCESS read-only
                    STATUS current
                    DESCRIPTION "Active step on the unit"
                    ::= { integerObjects 79 }

        -- 1.3.6.1.4.1.9839.2.1.3.80
        position_valve_d1 OBJECT-TYPE
                    SYNTAX Integer32 (-32767..32767)
                    UNITS "step"
                    MAX-ACCESS read-only
                    STATUS current
                    DESCRIPTION "Current valve position for driver1 (circ.1)"
                    ::= { integerObjects 80 }

        -- 1.3.6.1.4.1.9839.2.1.3.81
        position_valve_d2 OBJECT-TYPE
                    SYNTAX Integer32 (-32767..32767)
                    UNITS "step"
                    MAX-ACCESS read-only
                    STATUS current
                    DESCRIPTION "Current valve position for driver2 (circ.1)"
                    ::= { integerObjects 81 }

        -- 1.3.6.1.4.1.9839.2.1.3.82
        position_valve_d3 OBJECT-TYPE
                    SYNTAX Integer32 (-32767..32767)
                    UNITS "step"
                    MAX-ACCESS read-only
                    STATUS current
                    DESCRIPTION "Current valve position for driver1 (circ.2)"
                    ::= { integerObjects 82 }

        -- 1.3.6.1.4.1.9839.2.1.3.83
        position_valve_d4 OBJECT-TYPE
                    SYNTAX Integer32 (-32767..32767)
                    UNITS "step"
                    MAX-ACCESS read-only
                    STATUS current
                    DESCRIPTION "Current valve position for driver2 (circ.2)"
                    ::= { integerObjects 83 }

        -- 1.3.6.1.4.1.9839.2.1.3.84
        status_mng_unit1 OBJECT-TYPE
                    SYNTAX Integer32 (-32767..32767)
                    UNITS "N/A"
                    MAX-ACCESS read-only
                    STATUS current
                    DESCRIPTION "Status unit (Frecooling, prevent, HPPrev, recover)"
                    ::= { integerObjects 84 }

        -- 1.3.6.1.4.1.9839.2.1.3.85
        status_mng_unit OBJECT-TYPE
                    SYNTAX Integer32 (-32767..32767)
                    UNITS "N/A"
                    MAX-ACCESS read-only
                    STATUS current
                    DESCRIPTION "Status unit (Defrost, pumpdown..)"
                    ::= { integerObjects 85 }

        -- 1.3.6.1.4.1.9839.2.1.3.86
        version OBJECT-TYPE
                    SYNTAX Integer32 (-32767..32767)
                    UNITS "N/A"
                    MAX-ACCESS read-only
                    STATUS current
                    DESCRIPTION "SW version"
                    ::= { integerObjects 86 }


	
	END

--
-- CAREL-mod_ch_18.MIB
--
