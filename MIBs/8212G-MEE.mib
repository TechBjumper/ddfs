--------------------------------------------------------------------------------
-- PDI SNMP MIB FOR 8212G
-- M4G,BCMS 
--
-- Revision 1.00
-- January 17, 2008
--------------------------------------------------------------------------------
D8212G-MEE DEFINITIONS ::= BEGIN

IMPORTS
  org, iso, dod, internet, directory, mgmt, experimental, private, enterprises
    FROM RFC-1155-SMI 
  OBJECT-TYPE
    FROM RFC-1212
  DisplayString
    FROM RFC-1213;

--------------------------------------------------------------------------------
-- OID hierarchy
--------------------------------------------------------------------------------

pdi         	OBJECT IDENTIFIER ::= { enterprises 24436 }
 products    	OBJECT IDENTIFIER ::= { pdi 1 }
  remdisplay	OBJECT IDENTIFIER ::= { products 5 }
   d8212g		OBJECT IDENTIFIER ::= { remdisplay 2 }
    display		OBJECT IDENTIFIER ::= { d8212g 1 }
    device1		OBJECT IDENTIFIER ::= { d8212g 2 }
     pdu1		OBJECT IDENTIFIER ::= { device1 4 }
    device2		OBJECT IDENTIFIER ::= { d8212g 3 }
     bcmsplus1	OBJECT IDENTIFIER ::= { device2 7 }
    device3		OBJECT IDENTIFIER ::= { d8212g 4 }
     bcmsplus2	OBJECT IDENTIFIER ::= { device3 7 }
    displaytraps  OBJECT IDENTIFIER ::= { d8212g 14 }

--------------------------------------------------------------------------------
-- Display register values
--------------------------------------------------------------------------------

display-alarm
	OBJECT-TYPE
	SYNTAX  INTEGER
	ACCESS  read-only
	STATUS  mandatory
	DESCRIPTION "alarm register
				bit 0:	Communications Error 1
				bit 1:	Communications Error 2
				bit 2:	Communications Error 3
				bit 3:	Communications Error 4
				bit 4:	Communications Error 5
				bit 5:	Communications Error 6
				bit 6:	Communications Error 7
				bit 7:	Communications Error 8
				bit 8:	Communications Error 9
				bit 9:	Communications Error 10
				bit 10:	Communications Error 11
				bit 11:	Communications Error 12
				bit 12:	Summary Alarm
				bits 13 - 15: Always read as 0"
		::= { display 1 }

display-banner-1
	OBJECT-TYPE
	SYNTAX  INTEGER
	ACCESS  read-write
	STATUS  mandatory
	DESCRIPTION "Banner Character 1"
		::= { display 2 }

display-banner-2
	OBJECT-TYPE
	SYNTAX  INTEGER
	ACCESS  read-write
	STATUS  mandatory
	DESCRIPTION "Banner Character 2"
		::= { display 3 }

display-banner-3
	OBJECT-TYPE
	SYNTAX  INTEGER
	ACCESS  read-write
	STATUS  mandatory
	DESCRIPTION "Banner Character 3"
		::= { display 4 }

display-banner-4
	OBJECT-TYPE
	SYNTAX  INTEGER
	ACCESS  read-write
	STATUS  mandatory
	DESCRIPTION "Banner Character 4"
		::= { display 5 }

display-banner-5
	OBJECT-TYPE
	SYNTAX  INTEGER
	ACCESS  read-write
	STATUS  mandatory
	DESCRIPTION "Banner Character 5"
		::= { display 6 }

display-banner-6
	OBJECT-TYPE
	SYNTAX  INTEGER
	ACCESS  read-write
	STATUS  mandatory
	DESCRIPTION "Banner Character 6"
		::= { display 7 }

display-banner-7
	OBJECT-TYPE
	SYNTAX  INTEGER
	ACCESS  read-write
	STATUS  mandatory
	DESCRIPTION "Banner Character 7"
		::= { display 8 }

display-banner-8
	OBJECT-TYPE
	SYNTAX  INTEGER
	ACCESS  read-write
	STATUS  mandatory
	DESCRIPTION "Banner Character 8"
		::= { display 9 }

display-banner-9
	OBJECT-TYPE
	SYNTAX  INTEGER
	ACCESS  read-write
	STATUS  mandatory
	DESCRIPTION "Banner Character 9"
		::= { display 10 }

display-banner-10
	OBJECT-TYPE
	SYNTAX  INTEGER
	ACCESS  read-write
	STATUS  mandatory
	DESCRIPTION "Banner Character 10"
		::= { display 11 }

display-banner-11
	OBJECT-TYPE
	SYNTAX  INTEGER
	ACCESS  read-write
	STATUS  mandatory
	DESCRIPTION "Banner Character 11"
		::= { display 12 }

display-banner-12
	OBJECT-TYPE
	SYNTAX  INTEGER
	ACCESS  read-write
	STATUS  mandatory
	DESCRIPTION "Banner Character 12"
		::= { display 13 }

display-banner-13
	OBJECT-TYPE
	SYNTAX  INTEGER
	ACCESS  read-write
	STATUS  mandatory
	DESCRIPTION "Banner Character 13"
		::= { display 14 }

display-banner-14
	OBJECT-TYPE
	SYNTAX  INTEGER
	ACCESS  read-write
	STATUS  mandatory
	DESCRIPTION "Banner Character 14"
		::= { display 15 }

display-banner-15
	OBJECT-TYPE
	SYNTAX  INTEGER
	ACCESS  read-write
	STATUS  mandatory
	DESCRIPTION "Banner Character 15"
		::= { display 16 }

display-banner-16
	OBJECT-TYPE
	SYNTAX  INTEGER
	ACCESS  read-write
	STATUS  mandatory
	DESCRIPTION "Banner Character 16"
		::= { display 17 }

display-banner-17
	OBJECT-TYPE
	SYNTAX  INTEGER
	ACCESS  read-write
	STATUS  mandatory
	DESCRIPTION "Banner Character 17"
		::= { display 18 }

display-banner-18
	OBJECT-TYPE
	SYNTAX  INTEGER
	ACCESS  read-write
	STATUS  mandatory
	DESCRIPTION "Banner Character 18"
		::= { display 19 }

display-banner-19
	OBJECT-TYPE
	SYNTAX  INTEGER
	ACCESS  read-write
	STATUS  mandatory
	DESCRIPTION "Banner Character 19"
		::= { display 20 }

display-banner-20
	OBJECT-TYPE
	SYNTAX  INTEGER
	ACCESS  read-write
	STATUS  mandatory
	DESCRIPTION "Banner Character 20"
		::= { display 21 }

display-banner-21
	OBJECT-TYPE
	SYNTAX  INTEGER
	ACCESS  read-write
	STATUS  mandatory
	DESCRIPTION "Banner Character 21"
		::= { display 22 }

display-banner-22
	OBJECT-TYPE
	SYNTAX  INTEGER
	ACCESS  read-write
	STATUS  mandatory
	DESCRIPTION "Banner Character 22"
		::= { display 23 }

display-banner-23
	OBJECT-TYPE
	SYNTAX  INTEGER
	ACCESS  read-write
	STATUS  mandatory
	DESCRIPTION "Banner Character 23"
		::= { display 24 }

display-banner-24
	OBJECT-TYPE
	SYNTAX  INTEGER
	ACCESS  read-write
	STATUS  mandatory
	DESCRIPTION "Banner Character 24"
		::= { display 25 }

display-banner-25
	OBJECT-TYPE
	SYNTAX  INTEGER
	ACCESS  read-write
	STATUS  mandatory
	DESCRIPTION "Banner Character 25"
		::= { display 26 }

display-banner-26
	OBJECT-TYPE
	SYNTAX  INTEGER
	ACCESS  read-write
	STATUS  mandatory
	DESCRIPTION "Banner Character 26"
		::= { display 27 }

display-banner-27
	OBJECT-TYPE
	SYNTAX  INTEGER
	ACCESS  read-write
	STATUS  mandatory
	DESCRIPTION "Banner Character 27"
		::= { display 28 }

display-banner-28
	OBJECT-TYPE
	SYNTAX  INTEGER
	ACCESS  read-write
	STATUS  mandatory
	DESCRIPTION "Banner Character 28"
		::= { display 29 }

display-banner-29
	OBJECT-TYPE
	SYNTAX  INTEGER
	ACCESS  read-write
	STATUS  mandatory
	DESCRIPTION "Banner Character 29"
		::= { display 30 }

display-banner-30
	OBJECT-TYPE
	SYNTAX  INTEGER
	ACCESS  read-write
	STATUS  mandatory
	DESCRIPTION "Banner Character 30"
		::= { display 31 }

display-banner-31
	OBJECT-TYPE
	SYNTAX  INTEGER
	ACCESS  read-write
	STATUS  mandatory
	DESCRIPTION "Banner Character 31"
		::= { display 32 }

display-banner-32
	OBJECT-TYPE
	SYNTAX  INTEGER
	ACCESS  read-write
	STATUS  mandatory
	DESCRIPTION "Banner Character 32"
		::= { display 33 }

display-banner-33
	OBJECT-TYPE
	SYNTAX  INTEGER
	ACCESS  read-write
	STATUS  mandatory
	DESCRIPTION "Banner Character 33"
		::= { display 34 }

display-banner-34
	OBJECT-TYPE
	SYNTAX  INTEGER
	ACCESS  read-write
	STATUS  mandatory
	DESCRIPTION "Banner Character 34"
		::= { display 35 }

display-banner-35
	OBJECT-TYPE
	SYNTAX  INTEGER
	ACCESS  read-write
	STATUS  mandatory
	DESCRIPTION "Banner Character 35"
		::= { display 36 }

display-banner-36
	OBJECT-TYPE
	SYNTAX  INTEGER
	ACCESS  read-write
	STATUS  mandatory
	DESCRIPTION "Banner Character 36"
		::= { display 37 }

display-banner-37
	OBJECT-TYPE
	SYNTAX  INTEGER
	ACCESS  read-write
	STATUS  mandatory
	DESCRIPTION "Banner Character 37"
		::= { display 38 }

display-banner-38
	OBJECT-TYPE
	SYNTAX  INTEGER
	ACCESS  read-write
	STATUS  mandatory
	DESCRIPTION "Banner Character 38"
		::= { display 39 }

display-banner-39
	OBJECT-TYPE
	SYNTAX  INTEGER
	ACCESS  read-write
	STATUS  mandatory
	DESCRIPTION "Banner Character 39"
		::= { display 40 }

display-banner-40
	OBJECT-TYPE
	SYNTAX  INTEGER
	ACCESS  read-write
	STATUS  mandatory
	DESCRIPTION "Banner Character 40"
		::= { display 41 }

display-version
	OBJECT-TYPE
	SYNTAX  INTEGER
	ACCESS  read-only
	STATUS  mandatory
	DESCRIPTION "Software Version"
		::= { display 42 }

display-revision
	OBJECT-TYPE
	SYNTAX  INTEGER
	ACCESS  read-only
	STATUS  mandatory
	DESCRIPTION "Software Revision"
		::= { display 43 }

display-number-devices
	OBJECT-TYPE
	SYNTAX  INTEGER
	ACCESS  read-write
	STATUS  mandatory
	DESCRIPTION "Number of Devices"
		::= { display 44 }

display-device-1-options
	OBJECT-TYPE
	SYNTAX  INTEGER
	ACCESS  read-write
	STATUS  mandatory
	DESCRIPTION "Device 1 options - same for all devices below
			BCMS PLUS:        bit 0:	Panel Size (0=225, 1=400) 
bit 1:	CB Zero Current Alarms(1 = enable)
bit 2:	CB Warnings (1 = enable)
bit 3:	CB Alarms (1 = enable)
bit 4:	Total Currents Alarms(1 = enable)
bit 5:	Voltage Alarms(1 = enable)
bits 6 - 15: Always read as 0

			BCMS CB:		bit 1:	Total Currents Alarms(1 = enable)
bit 2:	Voltage Alarms(1 = enable)
bits 3 - 15: Always read as 0"
		::= { display 45 }

display-device-2-options
	OBJECT-TYPE
	SYNTAX  INTEGER
	ACCESS  read-write
	STATUS  mandatory
	DESCRIPTION "Device 2 options"
		::= { display 46 }

display-device-3-options
	OBJECT-TYPE
	SYNTAX  INTEGER
	ACCESS  read-write
	STATUS  mandatory
	DESCRIPTION "Device 3 options"
		::= { display 47 }

display-device-4-options
	OBJECT-TYPE
	SYNTAX  INTEGER
	ACCESS  read-write
	STATUS  mandatory
	DESCRIPTION "Device 4 options"
		::= { display 48 }

display-device-5-options
	OBJECT-TYPE
	SYNTAX  INTEGER
	ACCESS  read-write
	STATUS  mandatory
	DESCRIPTION "Device 5 options"
		::= { display 49 }

display-device-6-options
	OBJECT-TYPE
	SYNTAX  INTEGER
	ACCESS  read-write
	STATUS  mandatory
	DESCRIPTION "Device 6 options"
		::= { display 50 }

display-device-7-options
	OBJECT-TYPE
	SYNTAX  INTEGER
	ACCESS  read-write
	STATUS  mandatory
	DESCRIPTION "Device 7 options"
		::= { display 51 }

display-device-8-options
	OBJECT-TYPE
	SYNTAX  INTEGER
	ACCESS  read-write
	STATUS  mandatory
	DESCRIPTION "Device 8 options"
		::= { display 52 }

display-device-9-options
	OBJECT-TYPE
	SYNTAX  INTEGER
	ACCESS  read-write
	STATUS  mandatory
	DESCRIPTION "Device 9 options"
		::= { display 53 }

display-device-10-options
	OBJECT-TYPE
	SYNTAX  INTEGER
	ACCESS  read-write
	STATUS  mandatory
	DESCRIPTION "Device 10 options"
		::= { display 54 }

display-device-11-options
	OBJECT-TYPE
	SYNTAX  INTEGER
	ACCESS  read-write
	STATUS  mandatory
	DESCRIPTION "Device 11 options"
		::= { display 55 }

display-device-12-options
	OBJECT-TYPE
	SYNTAX  INTEGER
	ACCESS  read-write
	STATUS  mandatory
	DESCRIPTION "Device 12 options"
		::= { display 56 }

--------------------------------------------------------------------------------
-- PDU register values
--------------------------------------------------------------------------------

pdu1-input-voltage-1-ab
	OBJECT-TYPE
	SYNTAX  INTEGER
	ACCESS  read-only
	STATUS  mandatory
	DESCRIPTION "Input Voltage 1 AB"
		::= { pdu1 1 }

pdu1-input-voltage-1-bc
	OBJECT-TYPE
	SYNTAX  INTEGER
	ACCESS  read-only
	STATUS  mandatory
	DESCRIPTION "Input Voltage 1 BC"
		::= { pdu1 2 }

pdu1-input-voltage-1-ca
	OBJECT-TYPE
	SYNTAX  INTEGER
	ACCESS  read-only
	STATUS  mandatory
	DESCRIPTION "Input Voltage 1 CA"
		::= { pdu1 3 }

pdu1-input-voltage-1-frequency
	OBJECT-TYPE
	SYNTAX  INTEGER
	ACCESS  read-only
	STATUS  mandatory
	DESCRIPTION "Input Voltage 1 Frequency"
		::= { pdu1 4 }

pdu1-input-voltage-1-ab-thd
	OBJECT-TYPE
	SYNTAX  INTEGER
	ACCESS  read-only
	STATUS  mandatory
	DESCRIPTION "Input Voltage 1 AB THD"
		::= { pdu1 5 }

pdu1-input-voltage-1-bc-thd
	OBJECT-TYPE
	SYNTAX  INTEGER
	ACCESS  read-only
	STATUS  mandatory
	DESCRIPTION "Input Voltage 1 BC THD"
		::= { pdu1 6 }

pdu1-input-voltage-1-ca-thd
	OBJECT-TYPE
	SYNTAX  INTEGER
	ACCESS  read-only
	STATUS  mandatory
	DESCRIPTION "Input Voltage 1 CA THD"
		::= { pdu1 7 }

pdu1-input-voltage-2-ab
	OBJECT-TYPE
	SYNTAX  INTEGER
	ACCESS  read-only
	STATUS  mandatory
	DESCRIPTION "Input Voltage 2 AB - optional second input"
		::= { pdu1 8 }

pdu1-input-voltage-2-bc
	OBJECT-TYPE
	SYNTAX  INTEGER
	ACCESS  read-only
	STATUS  mandatory
	DESCRIPTION "Input Voltage 2 BC - optional second input"
		::= { pdu1 9 }

pdu1-input-voltage-2-ca
	OBJECT-TYPE
	SYNTAX  INTEGER
	ACCESS  read-only
	STATUS  mandatory
	DESCRIPTION "Input Voltage 2 CA - optional second input"
		::= { pdu1 10 }

pdu1-input-voltage-2-frequency
	OBJECT-TYPE
	SYNTAX  INTEGER
	ACCESS  read-only
	STATUS  mandatory
	DESCRIPTION "Input Voltage 2 Frequency - optional second input"
		::= { pdu1 11 }

pdu1-phase-difference-v1-to-v2
	OBJECT-TYPE
	SYNTAX  INTEGER
	ACCESS  read-only
	STATUS  mandatory
	DESCRIPTION "Phase difference input V1 to Input V2 - optional second input"
		::= { pdu1 12 }

pdu1-input-voltage-2-ab-thd
	OBJECT-TYPE
	SYNTAX  INTEGER
	ACCESS  read-only
	STATUS  mandatory
	DESCRIPTION "Input Voltage 2 AB THD - optional second input"
		::= { pdu1 13 }

pdu1-input-voltage-2-bc-thd
	OBJECT-TYPE
	SYNTAX  INTEGER
	ACCESS  read-only
	STATUS  mandatory
	DESCRIPTION "Input Voltage 2 BC THD - optional second input"
		::= { pdu1 14 }

pdu1-input-voltage-2-ca-thd
	OBJECT-TYPE
	SYNTAX  INTEGER
	ACCESS  read-only
	STATUS  mandatory
	DESCRIPTION "Input Voltage 2 CA THD - optional second input"
		::= { pdu1 15 }

pdu1-output-voltage-1-ab
	OBJECT-TYPE
	SYNTAX  INTEGER
	ACCESS  read-only
	STATUS  mandatory
	DESCRIPTION "Output Voltage 1 AB"
		::= { pdu1 16 }

pdu1-output-voltage-1-bc
	OBJECT-TYPE
	SYNTAX  INTEGER
	ACCESS  read-only
	STATUS  mandatory
	DESCRIPTION "Output Voltage 1 BC"
		::= { pdu1 17 }

pdu1-output-voltage-1-ca
	OBJECT-TYPE
	SYNTAX  INTEGER
	ACCESS  read-only
	STATUS  mandatory
	DESCRIPTION "Output Voltage 1 CA"
		::= { pdu1 18 }

pdu1-output-voltage-1-an
	OBJECT-TYPE
	SYNTAX  INTEGER
	ACCESS  read-only
	STATUS  mandatory
	DESCRIPTION "Output Voltage 1 AN"
		::= { pdu1 19 }

pdu1-output-voltage-1-bn
	OBJECT-TYPE
	SYNTAX  INTEGER
	ACCESS  read-only
	STATUS  mandatory
	DESCRIPTION "Output Voltage 1 BN"
		::= { pdu1 20 }

pdu1-output-voltage-1-cn
	OBJECT-TYPE
	SYNTAX  INTEGER
	ACCESS  read-only
	STATUS  mandatory
	DESCRIPTION "Output Voltage 1 CN"
		::= { pdu1 21 }

pdu1-output-current-1-a
	OBJECT-TYPE
	SYNTAX  INTEGER
	ACCESS  read-only
	STATUS  mandatory
	DESCRIPTION "Output Current 1 A"
		::= { pdu1 22 }

pdu1-output-current-1-b
	OBJECT-TYPE
	SYNTAX  INTEGER
	ACCESS  read-only
	STATUS  mandatory
	DESCRIPTION "Output Current 1 B"
		::= { pdu1 23 }

pdu1-output-current-1-c
	OBJECT-TYPE
	SYNTAX  INTEGER
	ACCESS  read-only
	STATUS  mandatory
	DESCRIPTION "Output Current 1 C"
		::= { pdu1 24 }

pdu1-output-1-kw-a
	OBJECT-TYPE
	SYNTAX  INTEGER
	ACCESS  read-only
	STATUS  mandatory
	DESCRIPTION "Output 1 KW A"
		::= { pdu1 25 }

pdu1-output-1-kw-b
	OBJECT-TYPE
	SYNTAX  INTEGER
	ACCESS  read-only
	STATUS  mandatory
	DESCRIPTION "Output 1 KW B"
		::= { pdu1 26 }

pdu1-output-1-kw-c
	OBJECT-TYPE
	SYNTAX  INTEGER
	ACCESS  read-only
	STATUS  mandatory
	DESCRIPTION "Output 1 KW C"
		::= { pdu1 27 }

pdu1-output-1-kw-total
	OBJECT-TYPE
	SYNTAX  INTEGER
	ACCESS  read-only
	STATUS  mandatory
	DESCRIPTION "Output 1 KW Total"
		::= { pdu1 28 }

pdu1-output-1-kva-a
	OBJECT-TYPE
	SYNTAX  INTEGER
	ACCESS  read-only
	STATUS  mandatory
	DESCRIPTION "Output 1 KVA A"
		::= { pdu1 29 }

pdu1-output-1-kva-b
	OBJECT-TYPE
	SYNTAX  INTEGER
	ACCESS  read-only
	STATUS  mandatory
	DESCRIPTION "Output 1 KVA B"
		::= { pdu1 30 }

pdu1-output-1-kva-c
	OBJECT-TYPE
	SYNTAX  INTEGER
	ACCESS  read-only
	STATUS  mandatory
	DESCRIPTION "Output 1 KVA C"
		::= { pdu1 31 }

pdu1-output-1-kva-total
	OBJECT-TYPE
	SYNTAX  INTEGER
	ACCESS  read-only
	STATUS  mandatory
	DESCRIPTION "Output 1 KVA Total"
		::= { pdu1 32 }

pdu1-output-1-kvar-a
	OBJECT-TYPE
	SYNTAX  INTEGER
	ACCESS  read-only
	STATUS  mandatory
	DESCRIPTION "Output 1 KVAR A"
		::= { pdu1 33 }

pdu1-output-1-kvar-b
	OBJECT-TYPE
	SYNTAX  INTEGER
	ACCESS  read-only
	STATUS  mandatory
	DESCRIPTION "Output 1 KVAR B"
		::= { pdu1 34 }

pdu1-output-1-kvar-c
	OBJECT-TYPE
	SYNTAX  INTEGER
	ACCESS  read-only
	STATUS  mandatory
	DESCRIPTION "Output 1 KVAR C"
		::= { pdu1 35 }

pdu1-output-1-kvar-total
	OBJECT-TYPE
	SYNTAX  INTEGER
	ACCESS  read-only
	STATUS  mandatory
	DESCRIPTION "Output 1 KVAR Total"
		::= { pdu1 36 }

pdu1-output-1-pf-a
	OBJECT-TYPE
	SYNTAX  INTEGER
	ACCESS  read-only
	STATUS  mandatory
	DESCRIPTION "Output 1 PF A"
		::= { pdu1 37 }

pdu1-output-1-pf-b
	OBJECT-TYPE
	SYNTAX  INTEGER
	ACCESS  read-only
	STATUS  mandatory
	DESCRIPTION "Output 1 PF B"
		::= { pdu1 38 }

pdu1-output-1-pf-c
	OBJECT-TYPE
	SYNTAX  INTEGER
	ACCESS  read-only
	STATUS  mandatory
	DESCRIPTION "Output 1 PF C"
		::= { pdu1 39 }

pdu1-output-1-kwh-low
	OBJECT-TYPE
	SYNTAX  INTEGER
	ACCESS  read-only
	STATUS  mandatory
	DESCRIPTION "Output 1 KWH low"
		::= { pdu1 40 }

pdu1-output-1-kwh-high
	OBJECT-TYPE
	SYNTAX  INTEGER
	ACCESS  read-only
	STATUS  mandatory
	DESCRIPTION "Output 1 KWH high"
		::= { pdu1 41 }

pdu1-neutral-current
	OBJECT-TYPE
	SYNTAX  INTEGER
	ACCESS  read-only
	STATUS  mandatory
	DESCRIPTION "Output Neutral current"
		::= { pdu1 42 }

pdu1-ground-current
	OBJECT-TYPE
	SYNTAX  INTEGER
	ACCESS  read-only
	STATUS  mandatory
	DESCRIPTION "Output Ground Current"
		::= { pdu1 43 }

pdu1-output-voltage-2-ab
	OBJECT-TYPE
	SYNTAX  INTEGER
	ACCESS  read-only
	STATUS  mandatory
	DESCRIPTION "Output Voltage 2 AB - Optional Second Output"
		::= { pdu1 44 }

pdu1-output-voltage-2-bc
	OBJECT-TYPE
	SYNTAX  INTEGER
	ACCESS  read-only
	STATUS  mandatory
	DESCRIPTION "Output Voltage 2 BC - Optional Second Output"
		::= { pdu1 45 }

pdu1-output-voltage-2-ca
	OBJECT-TYPE
	SYNTAX  INTEGER
	ACCESS  read-only
	STATUS  mandatory
	DESCRIPTION "Output Voltage 2 CA - Optional Second Output"
		::= { pdu1 46 }

pdu1-output-voltage-2-an
	OBJECT-TYPE
	SYNTAX  INTEGER
	ACCESS  read-only
	STATUS  mandatory
	DESCRIPTION "Output Voltage 2 AN - Optional Second Output"
		::= { pdu1 47 }

pdu1-output-voltage-2-bn
	OBJECT-TYPE
	SYNTAX  INTEGER
	ACCESS  read-only
	STATUS  mandatory
	DESCRIPTION "Output Voltage 2 BN - Optional Second Output"
		::= { pdu1 48 }

pdu1-output-voltage-2-cn
	OBJECT-TYPE
	SYNTAX  INTEGER
	ACCESS  read-only
	STATUS  mandatory
	DESCRIPTION "Output Voltage 2 CN - Optional Second Output"
		::= { pdu1 49 }

pdu1-output-current-2-a
	OBJECT-TYPE
	SYNTAX  INTEGER
	ACCESS  read-only
	STATUS  mandatory
	DESCRIPTION "Output Current 2 A - Optional Second Output"
		::= { pdu1 50 }

pdu1-output-current-2-b
	OBJECT-TYPE
	SYNTAX  INTEGER
	ACCESS  read-only
	STATUS  mandatory
	DESCRIPTION "Output Current 2 B - Optional Second Output"
		::= { pdu1 51 }

pdu1-output-current-2-c
	OBJECT-TYPE
	SYNTAX  INTEGER
	ACCESS  read-only
	STATUS  mandatory
	DESCRIPTION "Output Current 2 C - Optional Second Output"
		::= { pdu1 52 }

pdu1-output-2-kw-a
	OBJECT-TYPE
	SYNTAX  INTEGER
	ACCESS  read-only
	STATUS  mandatory
	DESCRIPTION "Output KW A - Optional Second Output"
		::= { pdu1 53 }

pdu1-output-2-kw-b
	OBJECT-TYPE
	SYNTAX  INTEGER
	ACCESS  read-only
	STATUS  mandatory
	DESCRIPTION "Output KW B - Optional Second Output"
		::= { pdu1 54 }

pdu1-output-2-kw-c
	OBJECT-TYPE
	SYNTAX  INTEGER
	ACCESS  read-only
	STATUS  mandatory
	DESCRIPTION "Output KW C - Optional Second Output"
		::= { pdu1 55 }

pdu1-output-2-kw-total
	OBJECT-TYPE
	SYNTAX  INTEGER
	ACCESS  read-only
	STATUS  mandatory
	DESCRIPTION "Output KW Total - Optional Second Output"
		::= { pdu1 56 }

pdu1-output-2-kva-a
	OBJECT-TYPE
	SYNTAX  INTEGER
	ACCESS  read-only
	STATUS  mandatory
	DESCRIPTION "Output KVA A - Optional Second Output"
		::= { pdu1 57 }

pdu1-output-2-kva-b
	OBJECT-TYPE
	SYNTAX  INTEGER
	ACCESS  read-only
	STATUS  mandatory
	DESCRIPTION "Output KVA B - Optional Second Output"
		::= { pdu1 58 }

pdu1-output-2-kva-c
	OBJECT-TYPE
	SYNTAX  INTEGER
	ACCESS  read-only
	STATUS  mandatory
	DESCRIPTION "Output KVA C - Optional Second Output"
		::= { pdu1 59 }

pdu1-output-2-kva-total
	OBJECT-TYPE
	SYNTAX  INTEGER
	ACCESS  read-only
	STATUS  mandatory
	DESCRIPTION "Output KVA Total - Optional Second Output"
		::= { pdu1 60 }

pdu1-output-2-kvar-a
	OBJECT-TYPE
	SYNTAX  INTEGER
	ACCESS  read-only
	STATUS  mandatory
	DESCRIPTION "Output KVAR A - Optional Second Output"
		::= { pdu1 61 }

pdu1-output-2-kvar-b
	OBJECT-TYPE
	SYNTAX  INTEGER
	ACCESS  read-only
	STATUS  mandatory
	DESCRIPTION "Output KVAR B - Optional Second Output"
		::= { pdu1 62 }

pdu1-output-2-kvar-c
	OBJECT-TYPE
	SYNTAX  INTEGER
	ACCESS  read-only
	STATUS  mandatory
	DESCRIPTION "Output KVAR C - Optional Second Output"
		::= { pdu1 63 }

pdu1-output-2-kvar-total
	OBJECT-TYPE
	SYNTAX  INTEGER
	ACCESS  read-only
	STATUS  mandatory
	DESCRIPTION "Output KVAR Total - Optional Second Output"
		::= { pdu1 64 }

pdu1-output-2-pf-a
	OBJECT-TYPE
	SYNTAX  INTEGER
	ACCESS  read-only
	STATUS  mandatory
	DESCRIPTION "Output PF A - Optional Second Output"
		::= { pdu1 65 }

pdu1-output-2-pf-b
	OBJECT-TYPE
	SYNTAX  INTEGER
	ACCESS  read-only
	STATUS  mandatory
	DESCRIPTION "Output PF B - Optional Second Output"
		::= { pdu1 66 }

pdu1-output-2-pf-c
	OBJECT-TYPE
	SYNTAX  INTEGER
	ACCESS  read-only
	STATUS  mandatory
	DESCRIPTION "Output PF C - Optional Second Output"
		::= { pdu1 67 }

pdu1-output-2-kwh-low
	OBJECT-TYPE
	SYNTAX  INTEGER
	ACCESS  read-only
	STATUS  mandatory
	DESCRIPTION "Output KWH low - Optional Second Output"
		::= { pdu1 68 }

pdu1-output-2-kwh-high
	OBJECT-TYPE
	SYNTAX  INTEGER
	ACCESS  read-only
	STATUS  mandatory
	DESCRIPTION "Output KWH high - Optional Second Output"
		::= { pdu1 69 }

pdu1-summary-alarms
	OBJECT-TYPE
	SYNTAX  INTEGER
	ACCESS  read-only
	STATUS  mandatory
	DESCRIPTION "Summary Alarm
                   bit 0: Voltage Alarm
                   bit 1: Current Alarm
                   bit 2: Building Alarm
                   bit 3: Digital Alarm
                   bit 4: EPO
                   bit 5: Remote EPO
                   bit 6: Thermal Overtemp
                   bit 7: Thermal Hightemp
                   bit 8: Phase Rotation
                   bits 9-15 not used"
		::= { pdu1 70 }

pdu1-summary-alarms-latched
	OBJECT-TYPE
	SYNTAX  INTEGER
	ACCESS  read-write
	STATUS  mandatory
	DESCRIPTION "Summary Alarm Latched
                    - Same bits as Summary Alarm"
		::= { pdu1 71 }

pdu1-input-voltage-1-alarms
	OBJECT-TYPE
	SYNTAX  INTEGER
	ACCESS  read-only
	STATUS  mandatory
	DESCRIPTION "Input Voltage 1 Alarms
                   bit 0: Volt AB High
                   bit 1: Volt AB Low
                   bit 2: Volt BC High
                   bit 3: Volt BC Low
                   bit 4: Volt CA High
                   bit 5: Volt CA Low
                   bits 6-15 not used"
		::= { pdu1 72 }

pdu1-input-voltage-1-alarms-latched
	OBJECT-TYPE
	SYNTAX  INTEGER
	ACCESS  read-write
	STATUS  mandatory
	DESCRIPTION "Input Voltage 1 Alarms Latched
                    - Same bits as Input Voltage 1 Alarms"
		::= { pdu1 73 }

pdu1-input-voltage-2-alarms
	OBJECT-TYPE
	SYNTAX  INTEGER
	ACCESS  read-only
	STATUS  mandatory
	DESCRIPTION "Input Voltage 2 Alarms
                   bit 0: Volt AB High
                   bit 1: Volt AB Low
                   bit 2: Volt BC High
                   bit 3: Volt BC Low
                   bit 4: Volt CA High
                   bit 5: Volt CA Low
                   bits 6-15 not used"
		::= { pdu1 74 }

pdu1-input-voltage-2-alarms-latched
	OBJECT-TYPE
	SYNTAX  INTEGER
	ACCESS  read-write
	STATUS  mandatory
	DESCRIPTION "Input Voltage 2 Alarms Latched
                    - Same bits as Input Voltage 2 Alarms"
		::= { pdu1 75 }

pdu1-output-voltage-1-alarms
	OBJECT-TYPE
	SYNTAX  INTEGER
	ACCESS  read-only
	STATUS  mandatory
	DESCRIPTION "Output Voltage 1 Alarms
                   bit 0: Volt AB High
                   bit 1: Volt AB Low
                   bit 2: Volt BC High
                   bit 3: Volt BC Low
                   bit 4: Volt CA High
                   bit 5: Volt CA Low
                   bit 6: Volt AN High
                   bit 7: Volt AN Low
                   bit 8: Volt BN High
                   bit 9: Volt BN Low
                   bit 10: Volt CN High
                   bit 11: Volt CN Low
                   bits 12-15 not used"
		::= { pdu1 76 }

pdu1-output-voltage-1-alarms-latched
	OBJECT-TYPE
	SYNTAX  INTEGER
	ACCESS  read-write
	STATUS  mandatory
	DESCRIPTION "Output Voltage 1 Alarms Latched
                    - Same bits as Output Voltage 1 Alarms"
		::= { pdu1 77 }

pdu1-output-voltage-2-alarms
	OBJECT-TYPE
	SYNTAX  INTEGER
	ACCESS  read-only
	STATUS  mandatory
	DESCRIPTION "Output Voltage 1 Alarms
			  - Optional Second Output
                   bit 0: Volt AB High
                   bit 1: Volt AB Low
                   bit 2: Volt BC High
                   bit 3: Volt BC Low
                   bit 4: Volt CA High
                   bit 5: Volt CA Low
                   bit 6: Volt AN High
                   bit 7: Volt AN Low
                   bit 8: Volt BN High
                   bit 9: Volt BN Low
                   bit 10: Volt CN High
                   bit 11: Volt CN Low
                   bits 12-15 not used"
		::= { pdu1 78 }

pdu1-output-voltage-2-alarms-latched
	OBJECT-TYPE
	SYNTAX  INTEGER
	ACCESS  read-write
	STATUS  mandatory
	DESCRIPTION "Output Voltage 2 Alarms Latched
                    - Same bits as Output Current 1 Alarms
                    - Optional Second Output"
		::= { pdu1 79 }

pdu1-output-current-1-alarms
	OBJECT-TYPE
	SYNTAX  INTEGER
	ACCESS  read-only
	STATUS  mandatory
	DESCRIPTION "Output Current 1 Alarms
                   bit 0: Current A High
                   bit 1: Current A Low
                   bit 2: Current B High
                   bit 3: Current B Low
                   bit 4: Current C High
                   bit 5: Current C Low
                   bit 6: Neutral Current High
                   bit 7: Neutral Current Low
                   bit 8: Ground Current High
                   bit 9: Ground Current Low
                   bits 10-15 not used"
		::= { pdu1 80 }

pdu1-output-current-1-alarms-latched
	OBJECT-TYPE
	SYNTAX  INTEGER
	ACCESS  read-write
	STATUS  mandatory
	DESCRIPTION "Output Current 2 Alarms Latched
                    - Same bits as Output Voltage 2 Alarms"
		::= { pdu1 81 }

pdu1-output-current-2-alarms
	OBJECT-TYPE
	SYNTAX  INTEGER
	ACCESS  read-only
	STATUS  mandatory
	DESCRIPTION "Output Current 2 Alarms
			  - Optional Second Output
                   bit 0: Current A High
                   bit 1: Current A Low
                   bit 2: Current B High
                   bit 3: Current B Low
                   bit 4: Current C High
                   bit 5: Current C Low
                   bits 6-15 not used"
		::= { pdu1 82 }

pdu1-output-current-2-alarms-latched
	OBJECT-TYPE
	SYNTAX  INTEGER
	ACCESS  read-write
	STATUS  mandatory
	DESCRIPTION "Output Current 2 Alarms Latched
                    - Same bits as Output Current 2 Alarms
                    - Optional Second Output"
		::= { pdu1 83 }

pdu1-output-power-1-alarms
	OBJECT-TYPE
	SYNTAX  INTEGER
	ACCESS  read-only
	STATUS  mandatory
	DESCRIPTION "Output Power 1 Alarms
                   bit 0: KW A High
                   bit 1: KW B High
                   bit 2: KW C High
                   bit 3: KW Total High
                   bit 4: KVA A High
                   bit 5: KVA B High
                   bit 6: KVA C High
                   bit 7: KVA Total High
                   bits 8-15 not used"
		::= { pdu1 84 }

pdu1-output-power-1-alarms-latched
	OBJECT-TYPE
	SYNTAX  INTEGER
	ACCESS  read-write
	STATUS  mandatory
	DESCRIPTION "Output Power 1 Alarms Latched
                    - Same bits as Output Power 1 Alarms"
		::= { pdu1 85 }

pdu1-output-power-2-alarms
	OBJECT-TYPE
	SYNTAX  INTEGER
	ACCESS  read-only
	STATUS  mandatory
	DESCRIPTION "Output Power 2 Alarms
                   - Optional Second Output
                   bit 0: KW A High
                   bit 1: KW B High
                   bit 2: KW C High
                   bit 3: KW Total High
                   bit 4: KVA A High
                   bit 5: KVA B High
                   bit 6: KVA C High
                   bit 7: KVA Total High
                   bits 8-15 not used"
		::= { pdu1 86 }

pdu1-output-power-2-alarms-latched
	OBJECT-TYPE
	SYNTAX  INTEGER
	ACCESS  read-write
	STATUS  mandatory
	DESCRIPTION "Output Power 2 Alarms Latched
                    - Same bits as Output Power 2 Alarms
                    - Optional Second Output"
		::= { pdu1 87 }

pdu-building-alarms
	OBJECT-TYPE
	SYNTAX  INTEGER
	ACCESS  read-only
	STATUS  mandatory
	DESCRIPTION "Building Alarms
                   bit 0: Building Alarm 1
                   bit 1: Building Alarm 2
                   bit 2: Building Alarm 3
                   bit 3: Building Alarm 4
                   bit 4: Building Alarm 5 - Optional Advanced Contractor
                   bit 5: Building Alarm 6 - Optional Advanced Contractor
                   bit 6: Building Alarm 7 - Optional Advanced Contractor
                   bit 7: Building Alarm 8 - Optional Advanced Contractor
                   bits 8-15 not used"
		::= { pdu1 88 }

pdu-building-alarms-latched
	OBJECT-TYPE
	SYNTAX  INTEGER
	ACCESS  read-write
	STATUS  mandatory
	DESCRIPTION "Building Alarms Latched
                    - Same bits as Building Alarms"
		::= { pdu1 89 }

pdu-digital-alarms
	OBJECT-TYPE
	SYNTAX  INTEGER
	ACCESS  read-only
	STATUS  mandatory
	DESCRIPTION "Digital Alarms
                   bit 0: Digital Alarm 1
                   bit 1: Digital Alarm 2
                   bit 2: Digital Alarm 3
                   bit 3: Digital Alarm 4
                   bits 4-15 not used"
		::= { pdu1 90 }

pdu-digital-alarms-latched
	OBJECT-TYPE
	SYNTAX  INTEGER
	ACCESS  read-write
	STATUS  mandatory
	DESCRIPTION "Digital Alarms Latched
                    - Same bits as Digital Alarms"
		::= { pdu1 91 }

pdu-reserver-1
	OBJECT-TYPE
	SYNTAX  INTEGER
	ACCESS  read-only
	STATUS  mandatory
	DESCRIPTION "Reserved 1"
		::= { pdu1 92 }

pdu-reserver-2
	OBJECT-TYPE
	SYNTAX  INTEGER
	ACCESS  read-only
	STATUS  mandatory
	DESCRIPTION "Reserved 2"
		::= { pdu1 93 }

pdu-reserver-3
	OBJECT-TYPE
	SYNTAX  INTEGER
	ACCESS  read-only
	STATUS  mandatory
	DESCRIPTION "Reserved 3"
		::= { pdu1 94 }

pdu-reserver-4
	OBJECT-TYPE
	SYNTAX  INTEGER
	ACCESS  read-only
	STATUS  mandatory
	DESCRIPTION "Reserved 4"
		::= { pdu1 95 }

pdu-reserver-5
	OBJECT-TYPE
	SYNTAX  INTEGER
	ACCESS  read-only
	STATUS  mandatory
	DESCRIPTION "Reserved 5"
		::= { pdu1 96 }

pdu-reserver-6
	OBJECT-TYPE
	SYNTAX  INTEGER
	ACCESS  read-only
	STATUS  mandatory
	DESCRIPTION "Reserved 6"
		::= { pdu1 97 }

pdu-reserver-7
	OBJECT-TYPE
	SYNTAX  INTEGER
	ACCESS  read-only
	STATUS  mandatory
	DESCRIPTION "Reserved 7"
		::= { pdu1 98 }

pdu-reserver-8
	OBJECT-TYPE
	SYNTAX  INTEGER
	ACCESS  read-only
	STATUS  mandatory
	DESCRIPTION "Reserved 8"
		::= { pdu1 99 }

pdu1-enable
	OBJECT-TYPE
	SYNTAX  INTEGER
	ACCESS  read-write
	STATUS  mandatory
	DESCRIPTION "Enable - Enables write to calibration and limits"
		::= { pdu1 100 }

pdu1-setup
	OBJECT-TYPE
	SYNTAX  INTEGER
	ACCESS  read-write
	STATUS  mandatory
	DESCRIPTION "setup
                   bit 0: Second output enabled
                   bit 1: Second Input enabled
                   bit 2: Advanced Contractor enabled
                   bits 3-15 not used"
		::= { pdu1 101 }

pdu1-nominal-input-voltage-1
	OBJECT-TYPE
	SYNTAX  INTEGER
	ACCESS  read-write
	STATUS  mandatory
	DESCRIPTION "Nominal Input Voltage 1"
		::= { pdu1 102 }

pdu1-nominal-output-voltage-1
	OBJECT-TYPE
	SYNTAX  INTEGER
	ACCESS  read-write
	STATUS  mandatory
	DESCRIPTION "Nominal Output Voltage 1"
		::= { pdu1 103 }

pdu1-nominal-input-output-voltage-2
	OBJECT-TYPE
	SYNTAX  INTEGER
	ACCESS  read-write
	STATUS  mandatory
	DESCRIPTION "Nominal Input/Output Voltage 2"
		::= { pdu1 104 }

pdu1-rated-output-current-1
	OBJECT-TYPE
	SYNTAX  INTEGER
	ACCESS  read-write
	STATUS  mandatory
	DESCRIPTION "Rated Output Current 1"
		::= { pdu1 105 }

pdu1-rated-output-current-2
	OBJECT-TYPE
	SYNTAX  INTEGER
	ACCESS  read-write
	STATUS  mandatory
	DESCRIPTION "Rated Output Current 2"
		::= { pdu1 106 }

pdu1-rated-neutrral-current
	OBJECT-TYPE
	SYNTAX  INTEGER
	ACCESS  read-write
	STATUS  mandatory
	DESCRIPTION "Nominal Input Voltage 1"
		::= { pdu1 107 }

pdu1-ct-ratio-output-1
	OBJECT-TYPE
	SYNTAX  INTEGER
	ACCESS  read-write
	STATUS  mandatory
	DESCRIPTION "CT Ratio Output 1"
		::= { pdu1 108 }

pdu1-ct-ratio-output-2
	OBJECT-TYPE
	SYNTAX  INTEGER
	ACCESS  read-write
	STATUS  mandatory
	DESCRIPTION "CT Ratio Output 2"
		::= { pdu1 109 }

pdu1-ct-ratio-neutral
	OBJECT-TYPE
	SYNTAX  INTEGER
	ACCESS  read-write
	STATUS  mandatory
	DESCRIPTION "CT ratio Neutral"
		::= { pdu1 110 }

pdu1-kva
	OBJECT-TYPE
	SYNTAX  INTEGER
	ACCESS  read-write
	STATUS  mandatory
	DESCRIPTION "KVA"
		::= { pdu1 111 }

pdu1-input-voltage-1-ll-high-limit
	OBJECT-TYPE
	SYNTAX  INTEGER
	ACCESS  read-write
	STATUS  mandatory
	DESCRIPTION "Input Voltage 1 LL High Limit"
		::= { pdu1 112 }

pdu1-input-voltage-1-ll-low-limit
	OBJECT-TYPE
	SYNTAX  INTEGER
	ACCESS  read-write
	STATUS  mandatory
	DESCRIPTION "Input Voltage 1 LL Low Limit"
		::= { pdu1 113 }

pdu1-frequency-v1-high-limit
	OBJECT-TYPE
	SYNTAX  INTEGER
	ACCESS  read-write
	STATUS  mandatory
	DESCRIPTION "Frequency Voltage 1 High Limit"
		::= { pdu1 114 }

pdu1-frequency-v1-low-limit
	OBJECT-TYPE
	SYNTAX  INTEGER
	ACCESS  read-write
	STATUS  mandatory
	DESCRIPTION "Frequency Voltage 1 Low Limit"
		::= { pdu1 115 }

pdu1-input-voltage-2-ll-high-limit
	OBJECT-TYPE
	SYNTAX  INTEGER
	ACCESS  read-write
	STATUS  mandatory
	DESCRIPTION "Input Voltage 2 LL High Limit - Optional Second Input"
		::= { pdu1 116 }

pdu1-input-voltage-2-ll-low-limit
	OBJECT-TYPE
	SYNTAX  INTEGER
	ACCESS  read-write
	STATUS  mandatory
	DESCRIPTION "Input Voltage 2 LL Low Limit - Optional Second Input"
		::= { pdu1 117 }

pdu1-frequency-v2-high-limit
	OBJECT-TYPE
	SYNTAX  INTEGER
	ACCESS  read-write
	STATUS  mandatory
	DESCRIPTION "Frequency Voltage 2 High Limit - Optional Second Input"
		::= { pdu1 118 }

pdu1-frequency-v2-low-limit
	OBJECT-TYPE
	SYNTAX  INTEGER
	ACCESS  read-write
	STATUS  mandatory
	DESCRIPTION "Frequency Voltage 2 Low Limit - Optional Second Input"
		::= { pdu1 119 }

pdu1-phase-input-1-and-input-2
	OBJECT-TYPE
	SYNTAX  INTEGER
	ACCESS  read-write
	STATUS  mandatory
	DESCRIPTION "Phase Input 1 and Input 2 - Optional Second Input"
		::= { pdu1 120 }

pdu1-output-voltage-1-ll-high-limit
	OBJECT-TYPE
	SYNTAX  INTEGER
	ACCESS  read-write
	STATUS  mandatory
	DESCRIPTION "Output Voltage 1 LL High Limit"
		::= { pdu1 121 }

pdu1-output-voltage-1-ll-low-limit
	OBJECT-TYPE
	SYNTAX  INTEGER
	ACCESS  read-write
	STATUS  mandatory
	DESCRIPTION "Output Voltage 1 LL Low Limit"
		::= { pdu1 122 }

pdu1-output-voltage-1-ln-high-limit
	OBJECT-TYPE
	SYNTAX  INTEGER
	ACCESS  read-write
	STATUS  mandatory
	DESCRIPTION "Output Voltage 1 LN High Limit"
		::= { pdu1 123 }

pdu1-output-voltage-1-ln-low-limit
	OBJECT-TYPE
	SYNTAX  INTEGER
	ACCESS  read-write
	STATUS  mandatory
	DESCRIPTION "Output Voltage 1 LN Low Limit"
		::= { pdu1 124 }

pdu1-output-current-1-high-limit
	OBJECT-TYPE
	SYNTAX  INTEGER
	ACCESS  read-write
	STATUS  mandatory
	DESCRIPTION "Output Current 1 High Limit"
		::= { pdu1 125 }

pdu1-output-current-1-low-limit
	OBJECT-TYPE
	SYNTAX  INTEGER
	ACCESS  read-write
	STATUS  mandatory
	DESCRIPTION "Output Current 1 Low Limit"
		::= { pdu1 126 }

pdu1-output-kw-1-high-limit
	OBJECT-TYPE
	SYNTAX  INTEGER
	ACCESS  read-write
	STATUS  mandatory
	DESCRIPTION "Output KW 1 High Limit"
		::= { pdu1 127 }

pdu1-output-kva-1-high-limit
	OBJECT-TYPE
	SYNTAX  INTEGER
	ACCESS  read-write
	STATUS  mandatory
	DESCRIPTION "Output KVA 1 High Limit"
		::= { pdu1 128 }

pdu1-output-neutral-high-limit
	OBJECT-TYPE
	SYNTAX  INTEGER
	ACCESS  read-write
	STATUS  mandatory
	DESCRIPTION "Output Neutral High Limit"
		::= { pdu1 129 }

pdu1-output-neutral-low-limit
	OBJECT-TYPE
	SYNTAX  INTEGER
	ACCESS  read-write
	STATUS  mandatory
	DESCRIPTION "Output Neutral Low Limit"
		::= { pdu1 130 }

pdu1-output-ground-high-limit
	OBJECT-TYPE
	SYNTAX  INTEGER
	ACCESS  read-write
	STATUS  mandatory
	DESCRIPTION "Output Ground High Limit"
		::= { pdu1 131 }

pdu1-output-ground-low-limit
	OBJECT-TYPE
	SYNTAX  INTEGER
	ACCESS  read-write
	STATUS  mandatory
	DESCRIPTION "Output Ground Low Limit"
		::= { pdu1 132 }

pdu1-output-voltage-2-ll-high-limit
	OBJECT-TYPE
	SYNTAX  INTEGER
	ACCESS  read-write
	STATUS  mandatory
	DESCRIPTION "Output Voltage 2 LL High Limit - Optional Second Output"
		::= { pdu1 133 }

pdu1-output-voltage-2-ll-low-limit
	OBJECT-TYPE
	SYNTAX  INTEGER
	ACCESS  read-write
	STATUS  mandatory
	DESCRIPTION "Output Voltage 2 LL Low Limit - Optional Second Output"
		::= { pdu1 134 }

pdu1-output-voltage-2-ln-high-limit
	OBJECT-TYPE
	SYNTAX  INTEGER
	ACCESS  read-write
	STATUS  mandatory
	DESCRIPTION "Output Voltage 2 LN High Limit - Optional Second Output"
		::= { pdu1 135 }

pdu1-output-voltage-2-ln-low-limit
	OBJECT-TYPE
	SYNTAX  INTEGER
	ACCESS  read-write
	STATUS  mandatory
	DESCRIPTION "Output Voltage 2 LN Low Limit - Optional Second Output"
		::= { pdu1 136 }

pdu1-output-current-2-high-limit
	OBJECT-TYPE
	SYNTAX  INTEGER
	ACCESS  read-write
	STATUS  mandatory
	DESCRIPTION "Output Current 2 High Limit"
		::= { pdu1 137 }

pdu1-output-current-2-low-limit
	OBJECT-TYPE
	SYNTAX  INTEGER
	ACCESS  read-write
	STATUS  mandatory
	DESCRIPTION "Output Current 2 Low Limit"
		::= { pdu1 138 }

pdu1-output-kw-2-high-limit
	OBJECT-TYPE
	SYNTAX  INTEGER
	ACCESS  read-write
	STATUS  mandatory
	DESCRIPTION "Output KW 2 High Limit"
		::= { pdu1 139 }

pdu1-output-kvw-2-high-limit
	OBJECT-TYPE
	SYNTAX  INTEGER
	ACCESS  read-write
	STATUS  mandatory
	DESCRIPTION "Output KVA 2 High Limit"
		::= { pdu1 140 }

pdu1-building-alarm-enable
	OBJECT-TYPE
	SYNTAX  INTEGER
	ACCESS  read-write
	STATUS  mandatory
	DESCRIPTION "Building Alarm Enable - Enable is High
			 bit 0: Building Alarm 1
			 bit 1: Building Alarm 2
			 bit 2: Building Alarm 3
			 bit 3: Building Alarm 4
			 bit 4: Building Alarm 5 - Optional Advanced Contractor
			 bit 5: Building Alarm 6 - Optional Advanced Contractor
			 bit 6: Building Alarm 7 - Optional Advanced Contractor
			 bit 7: Building Alarm 8 - Optional Advanced Contractor
			 bits 8-15: not used"
		::= { pdu1 141 }

pdu1-building-alarm-nominal
	OBJECT-TYPE
	SYNTAX  INTEGER
	ACCESS  read-write
	STATUS  mandatory
	DESCRIPTION "Building Alarm Nominal - Nominal Closed is High
			 Bits same as Building Alarm Enable"
		::= { pdu1 142 }

pdu1-digital-alarm-enable
	OBJECT-TYPE
	SYNTAX  INTEGER
	ACCESS  read-write
	STATUS  mandatory
	DESCRIPTION "Digital Alarm Enable - Enable is High
			 bit 0: Digital Alarm 1
			 bit 1: Digital Alarm 2
			 bit 2: Digital Alarm 3
			 bit 3: Digital Alarm 4
                   bits 4-15: not used"
		::= { pdu1 143 }

pdu1-digital-alarm-nominal
	OBJECT-TYPE
	SYNTAX  INTEGER
	ACCESS  read-write
	STATUS  mandatory
	DESCRIPTION "Digital Alarm Nominal - Nominal Closed is High
			 Bits same as Digital Alarm Enable"
		::= { pdu1 144 }

pdu1-building-alarm-1-name-1-2
	OBJECT-TYPE
	SYNTAX  INTEGER
	ACCESS  read-write
	STATUS  mandatory
	DESCRIPTION "Building Alarm 1 Name 1-2 - 2 characters in one integer"
		::= { pdu1 145 }

pdu1-building-alarm-1-name-3-4
	OBJECT-TYPE
	SYNTAX  INTEGER
	ACCESS  read-write
	STATUS  mandatory
	DESCRIPTION "Building Alarm 1 Name 3-4 - 2 characters in one integer"
		::= { pdu1 146 }

pdu1-building-alarm-1-name-5-6
	OBJECT-TYPE
	SYNTAX  INTEGER
	ACCESS  read-write
	STATUS  mandatory
	DESCRIPTION "Building Alarm 1 Name 5-6 - 2 characters in one integer"
		::= { pdu1 147 }

pdu1-building-alarm-1-name-7-8
	OBJECT-TYPE
	SYNTAX  INTEGER
	ACCESS  read-write
	STATUS  mandatory
	DESCRIPTION "Building Alarm 1 Name 7-8 - 2 characters in one integer"
		::= { pdu1 148 }

pdu1-building-alarm-2-name-1-2
	OBJECT-TYPE
	SYNTAX  INTEGER
	ACCESS  read-write
	STATUS  mandatory
	DESCRIPTION "Building Alarm 2 Name 1-2 - 2 characters in one integer"
		::= { pdu1 149 }

pdu1-building-alarm-2-name-3-4
	OBJECT-TYPE
	SYNTAX  INTEGER
	ACCESS  read-write
	STATUS  mandatory
	DESCRIPTION "Building Alarm 2 Name 3-4 - 2 characters in one integer"
		::= { pdu1 150 }

pdu1-building-alarm-2-name-5-6
	OBJECT-TYPE
	SYNTAX  INTEGER
	ACCESS  read-write
	STATUS  mandatory
	DESCRIPTION "Building Alarm 2 Name 5-6 - 2 characters in one integer"
		::= { pdu1 151 }

pdu1-building-alarm-2-name-7-8
	OBJECT-TYPE
	SYNTAX  INTEGER
	ACCESS  read-write
	STATUS  mandatory
	DESCRIPTION "Building Alarm 2 Name 7-8 - 2 characters in one integer"
		::= { pdu1 152 }

pdu1-building-alarm-3-name-1-2
	OBJECT-TYPE
	SYNTAX  INTEGER
	ACCESS  read-write
	STATUS  mandatory
	DESCRIPTION "Building Alarm 3 Name 1-2 - 2 characters in one integer"
		::= { pdu1 153 }

pdu1-building-alarm-3-name-3-4
	OBJECT-TYPE
	SYNTAX  INTEGER
	ACCESS  read-write
	STATUS  mandatory
	DESCRIPTION "Building Alarm 3 Name 3-4 - 2 characters in one integer"
		::= { pdu1 154 }

pdu1-building-alarm-3-name-5-6
	OBJECT-TYPE
	SYNTAX  INTEGER
	ACCESS  read-write
	STATUS  mandatory
	DESCRIPTION "Building Alarm 3 Name 5-6 - 2 characters in one integer"
		::= { pdu1 155 }

pdu1-building-alarm-3-name-7-8
	OBJECT-TYPE
	SYNTAX  INTEGER
	ACCESS  read-write
	STATUS  mandatory
	DESCRIPTION "Building Alarm 3 Name 7-8 - 2 characters in one integer"
		::= { pdu1 156 }

pdu1-building-alarm-4-name-1-2
	OBJECT-TYPE
	SYNTAX  INTEGER
	ACCESS  read-write
	STATUS  mandatory
	DESCRIPTION "Building Alarm 4 Name 1-2 - 2 characters in one integer"
		::= { pdu1 157 }

pdu1-building-alarm-4-name-3-4
	OBJECT-TYPE
	SYNTAX  INTEGER
	ACCESS  read-write
	STATUS  mandatory
	DESCRIPTION "Building Alarm 4 Name 3-4 - 2 characters in one integer"
		::= { pdu1 158 }

pdu1-building-alarm-4-name-5-6
	OBJECT-TYPE
	SYNTAX  INTEGER
	ACCESS  read-write
	STATUS  mandatory
	DESCRIPTION "Building Alarm 4 Name 5-6 - 2 characters in one integer"
		::= { pdu1 159 }

pdu1-building-alarm-4-name-7-8
	OBJECT-TYPE
	SYNTAX  INTEGER
	ACCESS  read-write
	STATUS  mandatory
	DESCRIPTION "Building Alarm 4 Name 7-8 - 2 characters in one integer"
		::= { pdu1 160 }

pdu1-building-alarm-5-name-1-2
	OBJECT-TYPE
	SYNTAX  INTEGER
	ACCESS  read-write
	STATUS  mandatory
	DESCRIPTION "Building Alarm 5 Name 1-2 - 2 characters in one integer
                   - Optional Advanced Contractor"
		::= { pdu1 161 }

pdu1-building-alarm-5-name-3-4
	OBJECT-TYPE
	SYNTAX  INTEGER
	ACCESS  read-write
	STATUS  mandatory
	DESCRIPTION "Building Alarm 5 Name 3-4 - 2 characters in one integer
                   - Optional Advanced Contractor"
		::= { pdu1 162 }

pdu1-building-alarm-5-name-5-6
	OBJECT-TYPE
	SYNTAX  INTEGER
	ACCESS  read-write
	STATUS  mandatory
	DESCRIPTION "Building Alarm 5 Name 5-6 - 2 characters in one integer
                   - Optional Advanced Contractor"
		::= { pdu1 163 }

pdu1-building-alarm-5-name-7-8
	OBJECT-TYPE
	SYNTAX  INTEGER
	ACCESS  read-write
	STATUS  mandatory
	DESCRIPTION "Building Alarm 5 Name 7-8 - 2 characters in one integer
                   - Optional Advanced Contractor"
		::= { pdu1 164 }

pdu1-building-alarm-6-name-1-2
	OBJECT-TYPE
	SYNTAX  INTEGER
	ACCESS  read-write
	STATUS  mandatory
	DESCRIPTION "Building Alarm 5 Name 1-2 - 6 characters in one integer
                   - Optional Advanced Contractor"
		::= { pdu1 165 }

pdu1-building-alarm-6-name-3-4
	OBJECT-TYPE
	SYNTAX  INTEGER
	ACCESS  read-write
	STATUS  mandatory
	DESCRIPTION "Building Alarm 6 Name 3-4 - 2 characters in one integer
                   - Optional Advanced Contractor"
		::= { pdu1 166 }

pdu1-building-alarm-6-name-5-6
	OBJECT-TYPE
	SYNTAX  INTEGER
	ACCESS  read-write
	STATUS  mandatory
	DESCRIPTION "Building Alarm 6 Name 5-6 - 2 characters in one integer
                   - Optional Advanced Contractor"
		::= { pdu1 167 }

pdu1-building-alarm-6-name-7-8
	OBJECT-TYPE
	SYNTAX  INTEGER
	ACCESS  read-write
	STATUS  mandatory
	DESCRIPTION "Building Alarm 6 Name 7-8 - 2 characters in one integer
                   - Optional Advanced Contractor"
		::= { pdu1 168 }

pdu1-building-alarm-7-name-1-2
	OBJECT-TYPE
	SYNTAX  INTEGER
	ACCESS  read-write
	STATUS  mandatory
	DESCRIPTION "Building Alarm 7 Name 1-2 - 2 characters in one integer
                   - Optional Advanced Contractor"
		::= { pdu1 169 }

pdu1-building-alarm-7-name-3-4
	OBJECT-TYPE
	SYNTAX  INTEGER
	ACCESS  read-write
	STATUS  mandatory
	DESCRIPTION "Building Alarm 7 Name 3-4 - 2 characters in one integer
                   - Optional Advanced Contractor"
		::= { pdu1 170 }

pdu1-building-alarm-7-name-5-6
	OBJECT-TYPE
	SYNTAX  INTEGER
	ACCESS  read-write
	STATUS  mandatory
	DESCRIPTION "Building Alarm 7 Name 5-6 - 2 characters in one integer
                   - Optional Advanced Contractor"
		::= { pdu1 171 }

pdu1-building-alarm-7-name-7-8
	OBJECT-TYPE
	SYNTAX  INTEGER
	ACCESS  read-write
	STATUS  mandatory
	DESCRIPTION "Building Alarm 7 Name 7-8 - 2 characters in one integer
                   - Optional Advanced Contractor"
		::= { pdu1 172 }

pdu1-building-alarm-8-name-1-2
	OBJECT-TYPE
	SYNTAX  INTEGER
	ACCESS  read-write
	STATUS  mandatory
	DESCRIPTION "Building Alarm 8 Name 1-2 - 2 characters in one integer
                   - Optional Advanced Contractor"
		::= { pdu1 173 }

pdu1-building-alarm-8-name-3-4
	OBJECT-TYPE
	SYNTAX  INTEGER
	ACCESS  read-write
	STATUS  mandatory
	DESCRIPTION "Building Alarm 8 Name 3-4 - 2 characters in one integer
                   - Optional Advanced Contractor"
		::= { pdu1 174 }

pdu1-building-alarm-8-name-5-6
	OBJECT-TYPE
	SYNTAX  INTEGER
	ACCESS  read-write
	STATUS  mandatory
	DESCRIPTION "Building Alarm 8 Name 5-6 - 2 characters in one integer
                   - Optional Advanced Contractor"
		::= { pdu1 175 }

pdu1-building-alarm-8-name-7-8
	OBJECT-TYPE
	SYNTAX  INTEGER
	ACCESS  read-write
	STATUS  mandatory
	DESCRIPTION "Building Alarm 8 Name 7-8 - 2 characters in one integer
                   - Optional Advanced Contractor"
		::= { pdu1 176 }

pdu1-digital-alarm-1-name-1-2
	OBJECT-TYPE
	SYNTAX  INTEGER
	ACCESS  read-write
	STATUS  mandatory
	DESCRIPTION "Digital Alarm 1 Name 1-2 - 2 characters in one integer"
		::= { pdu1 177 }

pdu1-digital-alarm-1-name-3-4
	OBJECT-TYPE
	SYNTAX  INTEGER
	ACCESS  read-write
	STATUS  mandatory
	DESCRIPTION "Digital Alarm 1 Name 3-4 - 2 characters in one integer"
		::= { pdu1 178 }

pdu1-digital-alarm-1-name-5-6
	OBJECT-TYPE
	SYNTAX  INTEGER
	ACCESS  read-write
	STATUS  mandatory
	DESCRIPTION "Digital Alarm 1 Name 5-6 - 2 characters in one integer"
		::= { pdu1 179 }

pdu1-digital-alarm-1-name-7-8
	OBJECT-TYPE
	SYNTAX  INTEGER
	ACCESS  read-write
	STATUS  mandatory
	DESCRIPTION "Digital Alarm 1 Name 7-8 - 2 characters in one integer"
		::= { pdu1 180 }

pdu1-digital-alarm-2-name-1-2
	OBJECT-TYPE
	SYNTAX  INTEGER
	ACCESS  read-write
	STATUS  mandatory
	DESCRIPTION "Digital Alarm 2 Name 1-2 - 2 characters in one integer"
		::= { pdu1 181 }

pdu1-digital-alarm-2-name-3-4
	OBJECT-TYPE
	SYNTAX  INTEGER
	ACCESS  read-write
	STATUS  mandatory
	DESCRIPTION "Digital Alarm 2 Name 3-4 - 2 characters in one integer"
		::= { pdu1 182 }

pdu1-digital-alarm-2-name-5-6
	OBJECT-TYPE
	SYNTAX  INTEGER
	ACCESS  read-write
	STATUS  mandatory
	DESCRIPTION "Digital Alarm 2 Name 5-6 - 2 characters in one integer"
		::= { pdu1 183 }

pdu1-digital-alarm-2-name-7-8
	OBJECT-TYPE
	SYNTAX  INTEGER
	ACCESS  read-write
	STATUS  mandatory
	DESCRIPTION "Digital Alarm 2 Name 7-8 - 2 characters in one integer"
		::= { pdu1 184 }

pdu1-digital-alarm-3-name-1-2
	OBJECT-TYPE
	SYNTAX  INTEGER
	ACCESS  read-write
	STATUS  mandatory
	DESCRIPTION "Digital Alarm 3 Name 1-2 - 2 characters in one integer"
		::= { pdu1 185 }

pdu1-digital-alarm-3-name-3-4
	OBJECT-TYPE
	SYNTAX  INTEGER
	ACCESS  read-write
	STATUS  mandatory
	DESCRIPTION "Digital Alarm 3 Name 3-4 - 2 characters in one integer"
		::= { pdu1 186 }

pdu1-digital-alarm-3-name-5-6
	OBJECT-TYPE
	SYNTAX  INTEGER
	ACCESS  read-write
	STATUS  mandatory
	DESCRIPTION "Digital Alarm 3 Name 5-6 - 2 characters in one integer"
		::= { pdu1 187 }

pdu1-digital-alarm-3-name-7-8
	OBJECT-TYPE
	SYNTAX  INTEGER
	ACCESS  read-write
	STATUS  mandatory
	DESCRIPTION "Digital Alarm 3 Name 7-8 - 2 characters in one integer"
		::= { pdu1 188 }

pdu1-digital-alarm-4-name-1-2
	OBJECT-TYPE
	SYNTAX  INTEGER
	ACCESS  read-write
	STATUS  mandatory
	DESCRIPTION "Digital Alarm 4 Name 1-2 - 2 characters in one integer"
		::= { pdu1 189 }

pdu1-digital-alarm-4-name-3-4
	OBJECT-TYPE
	SYNTAX  INTEGER
	ACCESS  read-write
	STATUS  mandatory
	DESCRIPTION "Digital Alarm 4 Name 3-4 - 2 characters in one integer"
		::= { pdu1 190 }

pdu1-digital-alarm-4-name-5-6
	OBJECT-TYPE
	SYNTAX  INTEGER
	ACCESS  read-write
	STATUS  mandatory
	DESCRIPTION "Digital Alarm 4 Name 5-6 - 2 characters in one integer"
		::= { pdu1 191 }

pdu1-digital-alarm-4-name-7-8
	OBJECT-TYPE
	SYNTAX  INTEGER
	ACCESS  read-write
	STATUS  mandatory
	DESCRIPTION "Digital Alarm 4 Name 7-8 - 2 characters in one integer"
		::= { pdu1 192 }

pdu1-relay-1-alarm-point
	OBJECT-TYPE
	SYNTAX  INTEGER
	ACCESS  read-write
	STATUS  mandatory
	DESCRIPTION "Relay 1 Alarm Point"
		::= { pdu1 193 }

pdu1-relay-2-alarm-point
	OBJECT-TYPE
	SYNTAX  INTEGER
	ACCESS  read-write
	STATUS  mandatory
	DESCRIPTION "Relay 2 Alarm Point"
		::= { pdu1 194 }

pdu1-relay-3-alarm-point
	OBJECT-TYPE
	SYNTAX  INTEGER
	ACCESS  read-write
	STATUS  mandatory
	DESCRIPTION "Relay 3 Alarm Point"
		::= { pdu1 195 }

pdu1-relay-4-alarm-point
	OBJECT-TYPE
	SYNTAX  INTEGER
	ACCESS  read-write
	STATUS  mandatory
	DESCRIPTION "Relay 4 Alarm Point"
		::= { pdu1 196 }

pdu1-relay-5-alarm-point
	OBJECT-TYPE
	SYNTAX  INTEGER
	ACCESS  read-write
	STATUS  mandatory
	DESCRIPTION "Relay 5 Alarm Point - Optional Advanced Contractor"
		::= { pdu1 197 }

pdu1-relay-6-alarm-point
	OBJECT-TYPE
	SYNTAX  INTEGER
	ACCESS  read-write
	STATUS  mandatory
	DESCRIPTION "Relay 6 Alarm Point - Optional Advanced Contractor"
		::= { pdu1 198 }

pdu1-relay-7-alarm-point
	OBJECT-TYPE
	SYNTAX  INTEGER
	ACCESS  read-write
	STATUS  mandatory
	DESCRIPTION "Relay 7 Alarm Point - Optional Advanced Contractor"
		::= { pdu1 199 }

pdu1-relay-8-alarm-point
	OBJECT-TYPE
	SYNTAX  INTEGER
	ACCESS  read-write
	STATUS  mandatory
	DESCRIPTION "Relay 8 Alarm Point - Optional Advanced Contractor"
		::= { pdu1 200 }

pdu1-relay-1-alarm-bits
	OBJECT-TYPE
	SYNTAX  INTEGER
	ACCESS  read-write
	STATUS  mandatory
	DESCRIPTION "Relay 1 Alarm Bits - Which Bits of the Alarm Points will be Alarmed"
		::= { pdu1 201 }

pdu1-relay-2-alarm-bits
	OBJECT-TYPE
	SYNTAX  INTEGER
	ACCESS  read-write
	STATUS  mandatory
	DESCRIPTION "Relay 2 Alarm Bits"
		::= { pdu1 202 }

pdu1-relay-3-alarm-bits
	OBJECT-TYPE
	SYNTAX  INTEGER
	ACCESS  read-write
	STATUS  mandatory
	DESCRIPTION "Relay 3 Alarm Bits"
		::= { pdu1 203 }

pdu1-relay-4-alarm-bits
	OBJECT-TYPE
	SYNTAX  INTEGER
	ACCESS  read-write
	STATUS  mandatory
	DESCRIPTION "Relay 4 Alarm Bits"
		::= { pdu1 204 }

pdu1-relay-5-alarm-bits
	OBJECT-TYPE
	SYNTAX  INTEGER
	ACCESS  read-write
	STATUS  mandatory
	DESCRIPTION "Relay 5 Alarm Bits - Optional Advanced Contractor"
		::= { pdu1 205 }

pdu1-relay-6-alarm-bits
	OBJECT-TYPE
	SYNTAX  INTEGER
	ACCESS  read-write
	STATUS  mandatory
	DESCRIPTION "Relay 6 Alarm Bits - Optional Advanced Contractor"
		::= { pdu1 206 }

pdu1-relay-7-alarm-bits
	OBJECT-TYPE
	SYNTAX  INTEGER
	ACCESS  read-write
	STATUS  mandatory
	DESCRIPTION "Relay 7 Alarm Bits - Optional Advanced Contractor"
		::= { pdu1 207 }

pdu1-relay-8-alarm-bits
	OBJECT-TYPE
	SYNTAX  INTEGER
	ACCESS  read-write
	STATUS  mandatory
	DESCRIPTION "Relay 8 Alarm Bits - Optional Advanced Contractor"
		::= { pdu1 208 }


--------------------------------------------------------------------------------
-- BCMSPLUS register values
--------------------------------------------------------------------------------

bcms1-cb1a-current
	OBJECT-TYPE
	SYNTAX  INTEGER
	ACCESS  read-only
	STATUS  mandatory
	DESCRIPTION "CB1A Current
		     Note for all currents 1-42: 100 = 100 amps"
		::= { bcmsplus1 1 }
  
bcms1-cb1b-current
	OBJECT-TYPE
	SYNTAX  INTEGER
	ACCESS  read-only
	STATUS  mandatory
	DESCRIPTION "CB1B Current"
		::= { bcmsplus1 2 }

bcms1-cb1c-current
	OBJECT-TYPE
	SYNTAX  INTEGER
	ACCESS  read-only
	STATUS  mandatory
	DESCRIPTION "CB1C Current"
		::= { bcmsplus1 3 }

bcms1-cb2a-current
	OBJECT-TYPE
	SYNTAX  INTEGER
	ACCESS  read-only
	STATUS  mandatory
	DESCRIPTION "CB2A Current"
		::= { bcmsplus1 4 }

bcms1-cb2b-current
	OBJECT-TYPE
	SYNTAX  INTEGER
	ACCESS  read-only
	STATUS  mandatory
	DESCRIPTION "CB2B Current"
		::= { bcmsplus1 5 }

bcms1-cb2c-current
	OBJECT-TYPE
	SYNTAX  INTEGER
	ACCESS  read-only
	STATUS  mandatory
	DESCRIPTION "CB2C Current"
		::= { bcmsplus1 6 }

bcms1-cb3a-current
	OBJECT-TYPE
	SYNTAX  INTEGER
	ACCESS  read-only
	STATUS  mandatory
	DESCRIPTION "CB3A Current"
		::= { bcmsplus1 7 }

bcms1-cb3b-current
	OBJECT-TYPE
	SYNTAX  INTEGER
	ACCESS  read-only
	STATUS  mandatory
	DESCRIPTION "CB3B Current"
		::= { bcmsplus1 8 }

bcms1-cb3c-current
	OBJECT-TYPE
	SYNTAX  INTEGER
	ACCESS  read-only
	STATUS  mandatory
	DESCRIPTION "CB3C Current"
		::= { bcmsplus1 9 }

bcms1-cb4a-current
	OBJECT-TYPE
	SYNTAX  INTEGER
	ACCESS  read-only
	STATUS  mandatory
	DESCRIPTION "CB4A Current"
		::= { bcmsplus1 10 }

bcms1-cb4b-current
	OBJECT-TYPE
	SYNTAX  INTEGER
	ACCESS  read-only
	STATUS  mandatory
	DESCRIPTION "CB4B Current"
		::= { bcmsplus1 11 }
  
bcms1-cb4c-current
	OBJECT-TYPE
	SYNTAX  INTEGER
	ACCESS  read-only
	STATUS  mandatory
	DESCRIPTION "CB4C Current"
		::= { bcmsplus1 12 }

bcms1-cb5a-current
	OBJECT-TYPE
	SYNTAX  INTEGER
	ACCESS  read-only
	STATUS  mandatory
	DESCRIPTION "CB5A Current"
		::= { bcmsplus1 13 }

bcms1-cb5b-current
	OBJECT-TYPE
	SYNTAX  INTEGER
	ACCESS  read-only
	STATUS  mandatory
	DESCRIPTION "CB5B Current"
		::= { bcmsplus1 14 }

bcms1-cb5c-current
	OBJECT-TYPE
	SYNTAX  INTEGER
	ACCESS  read-only
	STATUS  mandatory
	DESCRIPTION "CB5C Current"
		::= { bcmsplus1 15 }

bcms1-cb6a-current
	OBJECT-TYPE
	SYNTAX  INTEGER
	ACCESS  read-only
	STATUS  mandatory
	DESCRIPTION "CB6A Current"
		::= { bcmsplus1 16 }

bcms1-cb6b-current
	OBJECT-TYPE
	SYNTAX  INTEGER
	ACCESS  read-only
	STATUS  mandatory
	DESCRIPTION "CB6B Current"
		::= { bcmsplus1 17 }

bcms1-cb6c-current
	OBJECT-TYPE
	SYNTAX  INTEGER
	ACCESS  read-only
	STATUS  mandatory
	DESCRIPTION "CB6C Current"
		::= { bcmsplus1 18 }

bcms1-cb7a-current
	OBJECT-TYPE
	SYNTAX  INTEGER
	ACCESS  read-only
	STATUS  mandatory
	DESCRIPTION "CB7A Current"
		::= { bcmsplus1 19 }

bcms1-cb7b-current
	OBJECT-TYPE
	SYNTAX  INTEGER
	ACCESS  read-only
	STATUS  mandatory
	DESCRIPTION "CB7B Current"
		::= { bcmsplus1 20 }

bcms1-cb7c-current
	OBJECT-TYPE
	SYNTAX  INTEGER
	ACCESS  read-only
	STATUS  mandatory
	DESCRIPTION "CB7C Current"
		::= { bcmsplus1 21 }
  
bcms1-cb8a-current
	OBJECT-TYPE
	SYNTAX  INTEGER
	ACCESS  read-only
	STATUS  mandatory
	DESCRIPTION "CB8A Current"
		::= { bcmsplus1 22 }

bcms1-cb8b-current
	OBJECT-TYPE
	SYNTAX  INTEGER
	ACCESS  read-only
	STATUS  mandatory
	DESCRIPTION "CB8B Current"
		::= { bcmsplus1 23 }

bcms1-cb8c-current
	OBJECT-TYPE
	SYNTAX  INTEGER
	ACCESS  read-only
	STATUS  mandatory
	DESCRIPTION "CB8C Current"
		::= { bcmsplus1 24 }

bcms1-cb9a-current
	OBJECT-TYPE
	SYNTAX  INTEGER
	ACCESS  read-only
	STATUS  mandatory
	DESCRIPTION "CB9A Current"
		::= { bcmsplus1 25 }

bcms1-cb9b-current
	OBJECT-TYPE
	SYNTAX  INTEGER
	ACCESS  read-only
	STATUS  mandatory
	DESCRIPTION "CB9B Current"
		::= { bcmsplus1 26 }

bcms1-cb9c-current
	OBJECT-TYPE
	SYNTAX  INTEGER
	ACCESS  read-only
	STATUS  mandatory
	DESCRIPTION "CB9C Current"
		::= { bcmsplus1 27 }

bcms1-cb10a-current
	OBJECT-TYPE
	SYNTAX  INTEGER
	ACCESS  read-only
	STATUS  mandatory
	DESCRIPTION "CB10A Current"
		::= { bcmsplus1 28 }

bcms1-cb10b-current
	OBJECT-TYPE
	SYNTAX  INTEGER
	ACCESS  read-only
	STATUS  mandatory
	DESCRIPTION "CB10B Current"
		::= { bcmsplus1 29 }

bcms1-cb10c-current
	OBJECT-TYPE
	SYNTAX  INTEGER
	ACCESS  read-only
	STATUS  mandatory
	DESCRIPTION "CB10C Current"
		::= { bcmsplus1 30 }

bcms1-cb11a-current
	OBJECT-TYPE
	SYNTAX  INTEGER
	ACCESS  read-only
	STATUS  mandatory
	DESCRIPTION "CB11A Current"
		::= { bcmsplus1 31 }
  
bcms1-cb11b-current
	OBJECT-TYPE
	SYNTAX  INTEGER
	ACCESS  read-only
	STATUS  mandatory
	DESCRIPTION "CB11B Current"
		::= { bcmsplus1 32 }

bcms1-cb11c-current
	OBJECT-TYPE
	SYNTAX  INTEGER
	ACCESS  read-only
	STATUS  mandatory
	DESCRIPTION "CB11C Current"
		::= { bcmsplus1 33 }

bcms1-cb12a-current
	OBJECT-TYPE
	SYNTAX  INTEGER
	ACCESS  read-only
	STATUS  mandatory
	DESCRIPTION "CB12A Current"
		::= { bcmsplus1 34 }

bcms1-cb12b-current
	OBJECT-TYPE
	SYNTAX  INTEGER
	ACCESS  read-only
	STATUS  mandatory
	DESCRIPTION "CB12B Current"
		::= { bcmsplus1 35 }

bcms1-cb12c-current
	OBJECT-TYPE
	SYNTAX  INTEGER
	ACCESS  read-only
	STATUS  mandatory
	DESCRIPTION "CB12C Current"
		::= { bcmsplus1 36 }

bcms1-cb13a-current
	OBJECT-TYPE
	SYNTAX  INTEGER
	ACCESS  read-only
	STATUS  mandatory
	DESCRIPTION "CB13A Current"
		::= { bcmsplus1 37 }

bcms1-cb13b-current
	OBJECT-TYPE
	SYNTAX  INTEGER
	ACCESS  read-only
	STATUS  mandatory
	DESCRIPTION "CB13B Current"
		::= { bcmsplus1 38 }

bcms1-cb13c-current
	OBJECT-TYPE
	SYNTAX  INTEGER
	ACCESS  read-only
	STATUS  mandatory
	DESCRIPTION "CB13C Current"
		::= { bcmsplus1 39 }

bcms1-cb14a-current
	OBJECT-TYPE
	SYNTAX  INTEGER
	ACCESS  read-only
	STATUS  mandatory
	DESCRIPTION "CB14A Current"
		::= { bcmsplus1 40 }

bcms1-cb14b-current
	OBJECT-TYPE
	SYNTAX  INTEGER
	ACCESS  read-only
	STATUS  mandatory
	DESCRIPTION "CB14B Current"
		::= { bcmsplus1 41 }
  
bcms1-cb14c-current
	OBJECT-TYPE
	SYNTAX  INTEGER
	ACCESS  read-only
	STATUS  mandatory
	DESCRIPTION "CB14C Current"
		::= { bcmsplus1 42 }

bcms1-cb1a-min
	OBJECT-TYPE
	SYNTAX  INTEGER
	ACCESS  read-only
	STATUS  mandatory
	DESCRIPTION "set1 CB1A Min
		     Note for all minumum currents 1-42: 100 = 100 amps"
		::= { bcmsplus1 43 }

bcms1-cb1b-min
	OBJECT-TYPE
	SYNTAX  INTEGER
	ACCESS  read-only
	STATUS  mandatory
	DESCRIPTION "set1 CB1B Min"
		::= { bcmsplus1 44 }

bcms1-cb1c-min
	OBJECT-TYPE
	SYNTAX  INTEGER
	ACCESS  read-only
	STATUS  mandatory
	DESCRIPTION "set1 CB1C Min"
		::= { bcmsplus1 45 }

bcms1-cb2a-min
	OBJECT-TYPE
	SYNTAX  INTEGER
	ACCESS  read-only
	STATUS  mandatory
	DESCRIPTION "set1A CB2AMin"
		::= { bcmsplus1 46 }

bcms1-cb2b-min
	OBJECT-TYPE
	SYNTAX  INTEGER
	ACCESS  read-only
	STATUS  mandatory
	DESCRIPTION "set1 CB2B Min"
		::= { bcmsplus1 47 }

bcms1-cb2c-min
	OBJECT-TYPE
	SYNTAX  INTEGER
	ACCESS  read-only
	STATUS  mandatory
	DESCRIPTION "set1 CB2C Min"
		::= { bcmsplus1 48 }

bcms1-cb3a-min
	OBJECT-TYPE
	SYNTAX  INTEGER
	ACCESS  read-only
	STATUS  mandatory
	DESCRIPTION "set1 CB3A Min"
		::= { bcmsplus1 49 }

bcms1-cb3b-min
	OBJECT-TYPE
	SYNTAX  INTEGER
	ACCESS  read-only
	STATUS  mandatory
	DESCRIPTION "set1 CB3B Min"
		::= { bcmsplus1 50 }

bcms1-cb3c-min
	OBJECT-TYPE
	SYNTAX  INTEGER
	ACCESS  read-only
	STATUS  mandatory
	DESCRIPTION "set1 CB3C Min"
		::= { bcmsplus1 51 }
  
bcms1-cb4a-min
	OBJECT-TYPE
	SYNTAX  INTEGER
	ACCESS  read-only
	STATUS  mandatory
	DESCRIPTION "set1 CB4A Min"
		::= { bcmsplus1 52 }

bcms1-cb4b-min
	OBJECT-TYPE
	SYNTAX  INTEGER
	ACCESS  read-only
	STATUS  mandatory
	DESCRIPTION "set1 CB4B Min"
		::= { bcmsplus1 53 }

bcms1-cb4c-min
	OBJECT-TYPE
	SYNTAX  INTEGER
	ACCESS  read-only
	STATUS  mandatory
	DESCRIPTION "set1 CB4C Min"
		::= { bcmsplus1 54 }

bcms1-cb5a-min
	OBJECT-TYPE
	SYNTAX  INTEGER
	ACCESS  read-only
	STATUS  mandatory
	DESCRIPTION "set1 CB5A Min"
		::= { bcmsplus1 55 }

bcms1-cb5b-min
	OBJECT-TYPE
	SYNTAX  INTEGER
	ACCESS  read-only
	STATUS  mandatory
	DESCRIPTION "set1 CB5B Min"
		::= { bcmsplus1 56 }

bcms1-cb5c-min
	OBJECT-TYPE
	SYNTAX  INTEGER
	ACCESS  read-only
	STATUS  mandatory
	DESCRIPTION "set1 CB5C Min"
		::= { bcmsplus1 57 }

bcms1-cb6a-min
	OBJECT-TYPE
	SYNTAX  INTEGER
	ACCESS  read-only
	STATUS  mandatory
	DESCRIPTION "set1 CB6A Min"
		::= { bcmsplus1 58 }

bcms1-cb6b-min
	OBJECT-TYPE
	SYNTAX  INTEGER
	ACCESS  read-only
	STATUS  mandatory
	DESCRIPTION "set1 CB6B Min"
		::= { bcmsplus1 59 }

bcms1-cb6c-min
	OBJECT-TYPE
	SYNTAX  INTEGER
	ACCESS  read-only
	STATUS  mandatory
	DESCRIPTION "set1 CB6C Min"
		::= { bcmsplus1 60 }

bcms1-cb7a-min
	OBJECT-TYPE
	SYNTAX  INTEGER
	ACCESS  read-only
	STATUS  mandatory
	DESCRIPTION "set1 CB7A Min"
		::= { bcmsplus1 61 }
  
bcms1-cb7b-min
	OBJECT-TYPE
	SYNTAX  INTEGER
	ACCESS  read-only
	STATUS  mandatory
	DESCRIPTION "set1 CB7B Min"
		::= { bcmsplus1 62 }

bcms1-cb7c-min
	OBJECT-TYPE
	SYNTAX  INTEGER
	ACCESS  read-only
	STATUS  mandatory
	DESCRIPTION "set1 CB7C Min"
		::= { bcmsplus1 63 }

bcms1-cb8a-min
	OBJECT-TYPE
	SYNTAX  INTEGER
	ACCESS  read-only
	STATUS  mandatory
	DESCRIPTION "set1 CB8A Min"
		::= { bcmsplus1 64 }

bcms1-cb8b-min
	OBJECT-TYPE
	SYNTAX  INTEGER
	ACCESS  read-only
	STATUS  mandatory
	DESCRIPTION "set1 CB8B Min"
		::= { bcmsplus1 65 }

bcms1-cb8c-min
	OBJECT-TYPE
	SYNTAX  INTEGER
	ACCESS  read-only
	STATUS  mandatory
	DESCRIPTION "set1 CB8C Min"
		::= { bcmsplus1 66 }

bcms1-cb9a-min
	OBJECT-TYPE
	SYNTAX  INTEGER
	ACCESS  read-only
	STATUS  mandatory
	DESCRIPTION "set1 CB9A Min"
		::= { bcmsplus1 67 }

bcms1-cb9b-min
	OBJECT-TYPE
	SYNTAX  INTEGER
	ACCESS  read-only
	STATUS  mandatory
	DESCRIPTION "set1 CB9B Min"
		::= { bcmsplus1 68 }

bcms1-cb9c-min
	OBJECT-TYPE
	SYNTAX  INTEGER
	ACCESS  read-only
	STATUS  mandatory
	DESCRIPTION "set1 CB9C Min"
		::= { bcmsplus1 69 }

bcms1-cb10a-min
	OBJECT-TYPE
	SYNTAX  INTEGER
	ACCESS  read-only
	STATUS  mandatory
	DESCRIPTION "set1 CB10A Min"
		::= { bcmsplus1 70 }

bcms1-cb10b-min
	OBJECT-TYPE
	SYNTAX  INTEGER
	ACCESS  read-only
	STATUS  mandatory
	DESCRIPTION "set1 CB10B Min"
		::= { bcmsplus1 71 }
  
bcms1-cb10c-min
	OBJECT-TYPE
	SYNTAX  INTEGER
	ACCESS  read-only
	STATUS  mandatory
	DESCRIPTION "set1 CB10C Min"
		::= { bcmsplus1 72 }

bcms1-cb11a-min
	OBJECT-TYPE
	SYNTAX  INTEGER
	ACCESS  read-only
	STATUS  mandatory
	DESCRIPTION "set1 CB11A Min"
		::= { bcmsplus1 73 }

bcms1-cb11b-min
	OBJECT-TYPE
	SYNTAX  INTEGER
	ACCESS  read-only
	STATUS  mandatory
	DESCRIPTION "set1 CB11B Min"
		::= { bcmsplus1 74 }

bcms1-cb11c-min
	OBJECT-TYPE
	SYNTAX  INTEGER
	ACCESS  read-only
	STATUS  mandatory
	DESCRIPTION "set1 CB11C Min"
		::= { bcmsplus1 75 }

bcms1-cb12a-min
	OBJECT-TYPE
	SYNTAX  INTEGER
	ACCESS  read-only
	STATUS  mandatory
	DESCRIPTION "set1 CB12A Min"
		::= { bcmsplus1 76 }

bcms1-cb12b-min
	OBJECT-TYPE
	SYNTAX  INTEGER
	ACCESS  read-only
	STATUS  mandatory
	DESCRIPTION "set1 CB12B Min"
		::= { bcmsplus1 77 }

bcms1-cb12c-min
	OBJECT-TYPE
	SYNTAX  INTEGER
	ACCESS  read-only
	STATUS  mandatory
	DESCRIPTION "set1 CB12C Min"
		::= { bcmsplus1 78 }

bcms1-cb13a-min
	OBJECT-TYPE
	SYNTAX  INTEGER
	ACCESS  read-only
	STATUS  mandatory
	DESCRIPTION "set1 CB13A Min"
		::= { bcmsplus1 79 }

bcms1-cb13b-min
	OBJECT-TYPE
	SYNTAX  INTEGER
	ACCESS  read-only
	STATUS  mandatory
	DESCRIPTION "set1 CB13B Min"
		::= { bcmsplus1 80 }

bcms1-cb13c-min
	OBJECT-TYPE
	SYNTAX  INTEGER
	ACCESS  read-only
	STATUS  mandatory
	DESCRIPTION "set1 CB13C Min"
		::= { bcmsplus1 81 }
  
bcms1-cb14a-min
	OBJECT-TYPE
	SYNTAX  INTEGER
	ACCESS  read-only
	STATUS  mandatory
	DESCRIPTION "set1 CB14A Min"
		::= { bcmsplus1 82 }

bcms1-cb14b-min
	OBJECT-TYPE
	SYNTAX  INTEGER
	ACCESS  read-only
	STATUS  mandatory
	DESCRIPTION "set1 CB14B Min"
		::= { bcmsplus1 83 }

bcms1-cb14c-min
	OBJECT-TYPE
	SYNTAX  INTEGER
	ACCESS  read-only
	STATUS  mandatory
	DESCRIPTION "set1 CB14C Min"
		::= { bcmsplus1 84 }

bcms1-cb1a-max
	OBJECT-TYPE
	SYNTAX  INTEGER
	ACCESS  read-only
	STATUS  mandatory
	DESCRIPTION "set1 CB1A Max
		     Note for all maximum currents 1-42: 100 = 100 amps"
		::= { bcmsplus1 85 }

bcms1-cb1b-max
	OBJECT-TYPE
	SYNTAX  INTEGER
	ACCESS  read-only
	STATUS  mandatory
	DESCRIPTION "set1 CB1B Max"
		::= { bcmsplus1 86 }

bcms1-cb1c-max
	OBJECT-TYPE
	SYNTAX  INTEGER
	ACCESS  read-only
	STATUS  mandatory
	DESCRIPTION "set1 CB1C Max"
		::= { bcmsplus1 87 }

bcms1-cb2a-max
	OBJECT-TYPE
	SYNTAX  INTEGER
	ACCESS  read-only
	STATUS  mandatory
	DESCRIPTION "set1 CB2A Max"
		::= { bcmsplus1 88 }

bcms1-cb2b-max
	OBJECT-TYPE
	SYNTAX  INTEGER
	ACCESS  read-only
	STATUS  mandatory
	DESCRIPTION "set1 CB2B Max"
		::= { bcmsplus1 89 }

bcms1-cb2c-max
	OBJECT-TYPE
	SYNTAX  INTEGER
	ACCESS  read-only
	STATUS  mandatory
	DESCRIPTION "set1 CB2C Max"
		::= { bcmsplus1 90 }

bcms1-cb3a-max
	OBJECT-TYPE
	SYNTAX  INTEGER
	ACCESS  read-only
	STATUS  mandatory
	DESCRIPTION "set1 CB3A Max"
		::= { bcmsplus1 91 }
  
bcms1-cb3b-max
	OBJECT-TYPE
	SYNTAX  INTEGER
	ACCESS  read-only
	STATUS  mandatory
	DESCRIPTION "set1 CB3B Max"
		::= { bcmsplus1 92 }

bcms1-cb3c-max
	OBJECT-TYPE
	SYNTAX  INTEGER
	ACCESS  read-only
	STATUS  mandatory
	DESCRIPTION "set1 CB3C Max"
		::= { bcmsplus1 93 }

bcms1-cb4a-max
	OBJECT-TYPE
	SYNTAX  INTEGER
	ACCESS  read-only
	STATUS  mandatory
	DESCRIPTION "set1 CB4A Max"
		::= { bcmsplus1 94 }

bcms1-cb4B-max
	OBJECT-TYPE
	SYNTAX  INTEGER
	ACCESS  read-only
	STATUS  mandatory
	DESCRIPTION "set1 CB4B Max"
		::= { bcmsplus1 95 }

bcms1-cb4C-max
	OBJECT-TYPE
	SYNTAX  INTEGER
	ACCESS  read-only
	STATUS  mandatory
	DESCRIPTION "set1 CB4C Max"
		::= { bcmsplus1 96 }

bcms1-cb5A-max
	OBJECT-TYPE
	SYNTAX  INTEGER
	ACCESS  read-only
	STATUS  mandatory
	DESCRIPTION "set1 CB5A Max"
		::= { bcmsplus1 97 }

bcms1-cb5B-max
	OBJECT-TYPE
	SYNTAX  INTEGER
	ACCESS  read-only
	STATUS  mandatory
	DESCRIPTION "set1 CB5B Max"
		::= { bcmsplus1 98 }

bcms1-cb5C-max
	OBJECT-TYPE
	SYNTAX  INTEGER
	ACCESS  read-only
	STATUS  mandatory
	DESCRIPTION "set1 CB5C Max"
		::= { bcmsplus1 99 }


bcms1-cb6A-max
	OBJECT-TYPE
	SYNTAX  INTEGER
	ACCESS  read-only
	STATUS  mandatory
	DESCRIPTION "set1 CB6A Max"
		::= { bcmsplus1 100 }

bcms1-cb6B-max
	OBJECT-TYPE
	SYNTAX  INTEGER
	ACCESS  read-only
	STATUS  mandatory
	DESCRIPTION "set1 CB6B Max"
		::= { bcmsplus1 101 }
  
bcms1-cb6C-max
	OBJECT-TYPE
	SYNTAX  INTEGER
	ACCESS  read-only
	STATUS  mandatory
	DESCRIPTION "set1 CB6C Max"
		::= { bcmsplus1 102 }

bcms1-cb7A-max
	OBJECT-TYPE
	SYNTAX  INTEGER
	ACCESS  read-only
	STATUS  mandatory
	DESCRIPTION "set1 CB7A Max"
		::= { bcmsplus1 103 }

bcms1-cb7B-max
	OBJECT-TYPE
	SYNTAX  INTEGER
	ACCESS  read-only
	STATUS  mandatory
	DESCRIPTION "set1 CB7B Max"
		::= { bcmsplus1 104 }

bcms1-cb7C-max
	OBJECT-TYPE
	SYNTAX  INTEGER
	ACCESS  read-only
	STATUS  mandatory
	DESCRIPTION "set1 CB7C Max"
		::= { bcmsplus1 105 }

bcms1-cb8A-max
	OBJECT-TYPE
	SYNTAX  INTEGER
	ACCESS  read-only
	STATUS  mandatory
	DESCRIPTION "set1 CB8A Max"
		::= { bcmsplus1 106 }

bcms1-cb8B-max
	OBJECT-TYPE
	SYNTAX  INTEGER
	ACCESS  read-only
	STATUS  mandatory
	DESCRIPTION "set1 CB8B Max"
		::= { bcmsplus1 107 }

bcms1-cb8C-max
	OBJECT-TYPE
	SYNTAX  INTEGER
	ACCESS  read-only
	STATUS  mandatory
	DESCRIPTION "set1 CB8C Max"
		::= { bcmsplus1 108 }

bcms1-cb9A-max
	OBJECT-TYPE
	SYNTAX  INTEGER
	ACCESS  read-only
	STATUS  mandatory
	DESCRIPTION "set1 CB9A Max"
		::= { bcmsplus1 109 }

bcms1-cb9B-max
	OBJECT-TYPE
	SYNTAX  INTEGER
	ACCESS  read-only
	STATUS  mandatory
	DESCRIPTION "set1 CB9B Max"
		::= { bcmsplus1 110 }

bcms1-cb9C-max
	OBJECT-TYPE
	SYNTAX  INTEGER
	ACCESS  read-only
	STATUS  mandatory
	DESCRIPTION "set1 CB9C Max"
		::= { bcmsplus1 111 }
  
bcms1-cb10A-max
	OBJECT-TYPE
	SYNTAX  INTEGER
	ACCESS  read-only
	STATUS  mandatory
	DESCRIPTION "set1 CB10A Max"
		::= { bcmsplus1 112 }

bcms1-cb10B-max
	OBJECT-TYPE
	SYNTAX  INTEGER
	ACCESS  read-only
	STATUS  mandatory
	DESCRIPTION "set1 CB10B Max"
		::= { bcmsplus1 113 }

bcms1-cb10C-max
	OBJECT-TYPE
	SYNTAX  INTEGER
	ACCESS  read-only
	STATUS  mandatory
	DESCRIPTION "set1 CB10C Max"
		::= { bcmsplus1 114 }

bcms1-cb11A-max
	OBJECT-TYPE
	SYNTAX  INTEGER
	ACCESS  read-only
	STATUS  mandatory
	DESCRIPTION "set1 CB11A Max"
		::= { bcmsplus1 115 }

bcms1-cb11B-max
	OBJECT-TYPE
	SYNTAX  INTEGER
	ACCESS  read-only
	STATUS  mandatory
	DESCRIPTION "set1 CB11B Max"
		::= { bcmsplus1 116 }

bcms1-cb11C-max
	OBJECT-TYPE
	SYNTAX  INTEGER
	ACCESS  read-only
	STATUS  mandatory
	DESCRIPTION "set1 CB11C Max"
		::= { bcmsplus1 117 }

bcms1-cb12A-max
	OBJECT-TYPE
	SYNTAX  INTEGER
	ACCESS  read-only
	STATUS  mandatory
	DESCRIPTION "set1 CB12A Max"
		::= { bcmsplus1 118 }

bcms1-cb12B-max
	OBJECT-TYPE
	SYNTAX  INTEGER
	ACCESS  read-only
	STATUS  mandatory
	DESCRIPTION "set1 CB12B Max"
		::= { bcmsplus1 119 }

bcms1-cb12C-max
	OBJECT-TYPE
	SYNTAX  INTEGER
	ACCESS  read-only
	STATUS  mandatory
	DESCRIPTION "set1 CB12C Max"
		::= { bcmsplus1 120 }

bcms1-cb13A-max
	OBJECT-TYPE
	SYNTAX  INTEGER
	ACCESS  read-only
	STATUS  mandatory
	DESCRIPTION "set1 CB13A Max"
		::= { bcmsplus1 121 }
  
bcms1-cb13B-max
	OBJECT-TYPE
	SYNTAX  INTEGER
	ACCESS  read-only
	STATUS  mandatory
	DESCRIPTION "set1 CB13B Max"
		::= { bcmsplus1 122 }

bcms1-cb13C-max
	OBJECT-TYPE
	SYNTAX  INTEGER
	ACCESS  read-only
	STATUS  mandatory
	DESCRIPTION "set1 CB13C Max"
		::= { bcmsplus1 123 }

bcms1-cb14A-max
	OBJECT-TYPE
	SYNTAX  INTEGER
	ACCESS  read-only
	STATUS  mandatory
	DESCRIPTION "set1 CB14A Max"
		::= { bcmsplus1 124 }

bcms1-cb14B-max
	OBJECT-TYPE
	SYNTAX  INTEGER
	ACCESS  read-only
	STATUS  mandatory
	DESCRIPTION "set1 CB14B Max"
		::= { bcmsplus1 125 }

bcms1-cb14C-max
	OBJECT-TYPE
	SYNTAX  INTEGER
	ACCESS  read-only
	STATUS  mandatory
	DESCRIPTION "set1 CB14C Max"
		::= { bcmsplus1 126 }

bcms1-Zero
	OBJECT-TYPE
	SYNTAX  INTEGER
	ACCESS  read-write
	STATUS  mandatory
	DESCRIPTION "set1 Zero
		     	 Bit 0 = CB1
                   Bit 13 = CB14"
		::= { bcmsplus1 127 }

bcms1-Warning
	OBJECT-TYPE
	SYNTAX  INTEGER
	ACCESS  read-write
	STATUS  mandatory
	DESCRIPTION "set1 Warning
		     Bit 0 = CB1
                 Bit 13 = CB14"
		::= { bcmsplus1 128 }

bcms1-Alarm
	OBJECT-TYPE
	SYNTAX  INTEGER
	ACCESS  read-write
	STATUS  mandatory
	DESCRIPTION "set1 Alarm
		       Bit 0 = CB1
                   Bit 13 = CB14"
		::= { bcmsplus1 129 }

bcms1-cb1-Breaker-Size
	OBJECT-TYPE
	SYNTAX  INTEGER
	ACCESS  read-write
	STATUS  mandatory
	DESCRIPTION "set1 CB1 Breaker-Size
		       Note for all breaker sizes 1-14: 100 = 100 amps
                   Range is 20 to 600 amps"
		::= { bcmsplus1 130 }

bcms1-cb2-Breaker-Size
	OBJECT-TYPE
	SYNTAX  INTEGER
	ACCESS  read-write
	STATUS  mandatory
	DESCRIPTION "set1 CB2 Breaker-Size"
		::= { bcmsplus1 131 }

bcms1-cb3-Breaker-Size
	OBJECT-TYPE
	SYNTAX  INTEGER
	ACCESS  read-write
	STATUS  mandatory
	DESCRIPTION "set1 CB3 Breaker-Size"
		::= { bcmsplus1 132 }

bcms1-cb4-Breaker-Size
	OBJECT-TYPE
	SYNTAX  INTEGER
	ACCESS  read-write
	STATUS  mandatory
	DESCRIPTION "set1 CB4 Breaker-Size"
		::= { bcmsplus1 133 }

bcms1-cb5-Breaker-Size
	OBJECT-TYPE
	SYNTAX  INTEGER
	ACCESS  read-write
	STATUS  mandatory
	DESCRIPTION "set1 CB5 Breaker-Size"
		::= { bcmsplus1 134 }

bcms1-cb6-Breaker-Size
	OBJECT-TYPE
	SYNTAX  INTEGER
	ACCESS  read-write
	STATUS  mandatory
	DESCRIPTION "set1 CB6 Breaker-Size"
		::= { bcmsplus1 135 }
  
bcms1-cb7-Breaker-Size
	OBJECT-TYPE
	SYNTAX  INTEGER
	ACCESS  read-write
	STATUS  mandatory
	DESCRIPTION "set1 CB7 Breaker-Size"
		::= { bcmsplus1 136 }

bcms1-cb8-Breaker-Size
	OBJECT-TYPE
	SYNTAX  INTEGER
	ACCESS  read-write
	STATUS  mandatory
	DESCRIPTION "set1 CB8 Breaker-Size"
		::= { bcmsplus1 137 }

bcms1-cb9-Breaker-Size
	OBJECT-TYPE
	SYNTAX  INTEGER
	ACCESS  read-write
	STATUS  mandatory
	DESCRIPTION "set1 CB9 Breaker-Size"
		::= { bcmsplus1 138 }

bcms1-cb10-Breaker-Size
	OBJECT-TYPE
	SYNTAX  INTEGER
	ACCESS  read-write
	STATUS  mandatory
	DESCRIPTION "set1 CB10 Breaker-Size"
		::= { bcmsplus1 139 }

bcms1-cb11-Breaker-Size
	OBJECT-TYPE
	SYNTAX  INTEGER
	ACCESS  read-write
	STATUS  mandatory
	DESCRIPTION "set1 CB11 Breaker-Size"
		::= { bcmsplus1 140 }

bcms1-cb12-Breaker-Size
	OBJECT-TYPE
	SYNTAX  INTEGER
	ACCESS  read-write
	STATUS  mandatory
	DESCRIPTION "set1 CB12 Breaker-Size"
		::= { bcmsplus1 141 }

bcms1-cb13-Breaker-Size
	OBJECT-TYPE
	SYNTAX  INTEGER
	ACCESS  read-write
	STATUS  mandatory
	DESCRIPTION "set1 CB13 Breaker-Size"
		::= { bcmsplus1 142 }

bcms1-cb14-Breaker-Size
	OBJECT-TYPE
	SYNTAX  INTEGER
	ACCESS  read-write
	STATUS  mandatory
	DESCRIPTION "set1 CB14 Breaker-Size"
		::= { bcmsplus1 143 }

bcms1-cb1a-kw
	OBJECT-TYPE
	SYNTAX  INTEGER
	ACCESS  read-write
	STATUS  mandatory
	DESCRIPTION "CB1A KW
		     Note: for all kw 1-42: 100 = 10.0KW"  
		::= { bcmsplus1 144 }

bcms1-cb1b-kw
	OBJECT-TYPE
	SYNTAX  INTEGER
	ACCESS  read-only
	STATUS  mandatory
	DESCRIPTION "CB1B KW"
		::= { bcmsplus1 145 }

bcms1-cb1c-kw
	OBJECT-TYPE
	SYNTAX  INTEGER
	ACCESS  read-only
	STATUS  mandatory
	DESCRIPTION "CB1C KW"
		::= { bcmsplus1 146 }

bcms1-cb2a-kw
	OBJECT-TYPE
	SYNTAX  INTEGER
	ACCESS  read-only
	STATUS  mandatory
	DESCRIPTION "CB2A KW"
		::= { bcmsplus1 147 }
  
bcms1-cb2b-kw
	OBJECT-TYPE
	SYNTAX  INTEGER
	ACCESS  read-only
	STATUS  mandatory
	DESCRIPTION "CB2B KW"
		::= { bcmsplus1 148 }

bcms1-cb2c-kw
	OBJECT-TYPE
	SYNTAX  INTEGER
	ACCESS  read-only
	STATUS  mandatory
	DESCRIPTION "CB2C KW"
		::= { bcmsplus1 149 }

bcms1-cb3a-kw
	OBJECT-TYPE
	SYNTAX  INTEGER
	ACCESS  read-only
	STATUS  mandatory
	DESCRIPTION "CB3A KW"
		::= { bcmsplus1 150 }

bcms1-cb3b-kw
	OBJECT-TYPE
	SYNTAX  INTEGER
	ACCESS  read-only
	STATUS  mandatory
	DESCRIPTION "CB3B KW"
		::= { bcmsplus1 151 }

bcms1-cb3c-kw
	OBJECT-TYPE
	SYNTAX  INTEGER
	ACCESS  read-only
	STATUS  mandatory
	DESCRIPTION "CB3C KW"
		::= { bcmsplus1 152 }

bcms1-cb4a-kw
	OBJECT-TYPE
	SYNTAX  INTEGER
	ACCESS  read-only
	STATUS  mandatory
	DESCRIPTION "CB4A KW"
		::= { bcmsplus1 153 }

bcms1-cb4b-kw
	OBJECT-TYPE
	SYNTAX  INTEGER
	ACCESS  read-only
	STATUS  mandatory
	DESCRIPTION "CB4B KW"
		::= { bcmsplus1 154 }

bcms1-cb4c-kw
	OBJECT-TYPE
	SYNTAX  INTEGER
	ACCESS  read-only
	STATUS  mandatory
	DESCRIPTION "CB4C KW"
		::= { bcmsplus1 155 }

bcms1-cb5a-kw
	OBJECT-TYPE
	SYNTAX  INTEGER
	ACCESS  read-only
	STATUS  mandatory
	DESCRIPTION "CB5A KW"
		::= { bcmsplus1 156 }

bcms1-cb5b-kw
	OBJECT-TYPE
	SYNTAX  INTEGER
	ACCESS  read-only
	STATUS  mandatory
	DESCRIPTION "CB5B KW"
		::= { bcmsplus1 157 }
  
bcms1-cb5c-kw
	OBJECT-TYPE
	SYNTAX  INTEGER
	ACCESS  read-only
	STATUS  mandatory
	DESCRIPTION "CB5C KW"
		::= { bcmsplus1 158 }

bcms1-cb6a-kw
	OBJECT-TYPE
	SYNTAX  INTEGER
	ACCESS  read-only
	STATUS  mandatory
	DESCRIPTION "CB6A KW"
		::= { bcmsplus1 159 }

bcms1-cb6b-kw
	OBJECT-TYPE
	SYNTAX  INTEGER
	ACCESS  read-only
	STATUS  mandatory
	DESCRIPTION "CB6B KW"
		::= { bcmsplus1 160 }

bcms1-cb6c-kw
	OBJECT-TYPE
	SYNTAX  INTEGER
	ACCESS  read-only
	STATUS  mandatory
	DESCRIPTION "CB6C KW"
		::= { bcmsplus1 161 }

bcms1-cb7a-kw
	OBJECT-TYPE
	SYNTAX  INTEGER
	ACCESS  read-only
	STATUS  mandatory
	DESCRIPTION "CB7A KW"
		::= { bcmsplus1 162 }

bcms1-cb7b-kw
	OBJECT-TYPE
	SYNTAX  INTEGER
	ACCESS  read-only
	STATUS  mandatory
	DESCRIPTION "CB7B KW"
		::= { bcmsplus1 163 }

bcms1-cb7c-kw
	OBJECT-TYPE
	SYNTAX  INTEGER
	ACCESS  read-only
	STATUS  mandatory
	DESCRIPTION "CB7C KW"
		::= { bcmsplus1 164 }

bcms1-cb8a-kw
	OBJECT-TYPE
	SYNTAX  INTEGER
	ACCESS  read-only
	STATUS  mandatory
	DESCRIPTION "CB8A KW"
		::= { bcmsplus1 165 }

bcms1-cb8b-kw
	OBJECT-TYPE
	SYNTAX  INTEGER
	ACCESS  read-only
	STATUS  mandatory
	DESCRIPTION "CB8B KW"
		::= { bcmsplus1 166 }

bcms1-cb8c-kw
	OBJECT-TYPE
	SYNTAX  INTEGER
	ACCESS  read-only
	STATUS  mandatory
	DESCRIPTION "CB8C KW"
		::= { bcmsplus1 167 }
  
bcms1-cb9a-kw
	OBJECT-TYPE
	SYNTAX  INTEGER
	ACCESS  read-only
	STATUS  mandatory
	DESCRIPTION "CB9A KW"
		::= { bcmsplus1 168 }

bcms1-cb9b-kw
	OBJECT-TYPE
	SYNTAX  INTEGER
	ACCESS  read-only
	STATUS  mandatory
	DESCRIPTION "CB9B KW"
		::= { bcmsplus1 169 }

bcms1-cb9c-kw
	OBJECT-TYPE
	SYNTAX  INTEGER
	ACCESS  read-only
	STATUS  mandatory
	DESCRIPTION "CB9C KW"
		::= { bcmsplus1 170 }

bcms1-cb10a-kw
	OBJECT-TYPE
	SYNTAX  INTEGER
	ACCESS  read-only
	STATUS  mandatory
	DESCRIPTION "CB10A KW"
		::= { bcmsplus1 171 }

bcms1-cb10b-kw
	OBJECT-TYPE
	SYNTAX  INTEGER
	ACCESS  read-only
	STATUS  mandatory
	DESCRIPTION "CB10B KW"
		::= { bcmsplus1 172 }

bcms1-cb10c-kw
	OBJECT-TYPE
	SYNTAX  INTEGER
	ACCESS  read-only
	STATUS  mandatory
	DESCRIPTION "CB10C KW"
		::= { bcmsplus1 173 }

bcms1-cb11a-kw
	OBJECT-TYPE
	SYNTAX  INTEGER
	ACCESS  read-only
	STATUS  mandatory
	DESCRIPTION "CB11A KW"
		::= { bcmsplus1 174 }

bcms1-cb11b-kw
	OBJECT-TYPE
	SYNTAX  INTEGER
	ACCESS  read-only
	STATUS  mandatory
	DESCRIPTION "CB11B KW"
		::= { bcmsplus1 175 }

bcms1-cb11c-kw
	OBJECT-TYPE
	SYNTAX  INTEGER
	ACCESS  read-only
	STATUS  mandatory
	DESCRIPTION "CB11C KW"
		::= { bcmsplus1 176 }

bcms1-cb12a-kw
	OBJECT-TYPE
	SYNTAX  INTEGER
	ACCESS  read-only
	STATUS  mandatory
	DESCRIPTION "CB12A KW"
		::= { bcmsplus1 177 }
  
bcms1-cb12b-kw
	OBJECT-TYPE
	SYNTAX  INTEGER
	ACCESS  read-only
	STATUS  mandatory
	DESCRIPTION "CB12B KW"
		::= { bcmsplus1 178 }

bcms1-cb12c-kw
	OBJECT-TYPE
	SYNTAX  INTEGER
	ACCESS  read-only
	STATUS  mandatory
	DESCRIPTION "CB12C KW"
		::= { bcmsplus1 179 }

bcms1-cb13a-kw
	OBJECT-TYPE
	SYNTAX  INTEGER
	ACCESS  read-only
	STATUS  mandatory
	DESCRIPTION "CB13A KW"
		::= { bcmsplus1 180 }

bcms1-cb13b-kw
	OBJECT-TYPE
	SYNTAX  INTEGER
	ACCESS  read-only
	STATUS  mandatory
	DESCRIPTION "CB13B KW"
		::= { bcmsplus1 181 }

bcms1-cb13c-kw
	OBJECT-TYPE
	SYNTAX  INTEGER
	ACCESS  read-only
	STATUS  mandatory
	DESCRIPTION "CB13C KW"
		::= { bcmsplus1 182 }

bcms1-cb14a-kw
	OBJECT-TYPE
	SYNTAX  INTEGER
	ACCESS  read-only
	STATUS  mandatory
	DESCRIPTION "CB14A KW"
		::= { bcmsplus1 183 }

bcms1-cb14b-kw
	OBJECT-TYPE
	SYNTAX  INTEGER
	ACCESS  read-only
	STATUS  mandatory
	DESCRIPTION "CB14B KW"
		::= { bcmsplus1 184 }

bcms1-cb14c-kw
	OBJECT-TYPE
	SYNTAX  INTEGER
	ACCESS  read-only
	STATUS  mandatory
	DESCRIPTION "CB14C KW"
		::= { bcmsplus1 185 }

bcms1-cb1a-kva
	OBJECT-TYPE
	SYNTAX  INTEGER
	ACCESS  read-only
	STATUS  mandatory
	DESCRIPTION "CB1A KVA
		     Note: for all kva 1-42: 100 = 10.0KW"  
		::= { bcmsplus1 186 }

bcms1-cb1b-kva
	OBJECT-TYPE
	SYNTAX  INTEGER
	ACCESS  read-only
	STATUS  mandatory
	DESCRIPTION "CB1B KVA"
		::= { bcmsplus1 187 }
  
bcms1-cb1c-kva
	OBJECT-TYPE
	SYNTAX  INTEGER
	ACCESS  read-only
	STATUS  mandatory
	DESCRIPTION "CB1C KVA"
		::= { bcmsplus1 188 }

bcms1-cb2a-kva
	OBJECT-TYPE
	SYNTAX  INTEGER
	ACCESS  read-only
	STATUS  mandatory
	DESCRIPTION "CB2A KVA"
		::= { bcmsplus1 189 }

bcms1-cb2b-kva
	OBJECT-TYPE
	SYNTAX  INTEGER
	ACCESS  read-only
	STATUS  mandatory
	DESCRIPTION "CB2B KVA"
		::= { bcmsplus1 190 }

bcms1-cb2c-kva
	OBJECT-TYPE
	SYNTAX  INTEGER
	ACCESS  read-only
	STATUS  mandatory
	DESCRIPTION "CB2C KVA"
		::= { bcmsplus1 191 }

bcms1-cb3a-kva
	OBJECT-TYPE
	SYNTAX  INTEGER
	ACCESS  read-only
	STATUS  mandatory
	DESCRIPTION "CB3A KVA"
		::= { bcmsplus1 192 }

bcms1-cb3b-kva
	OBJECT-TYPE
	SYNTAX  INTEGER
	ACCESS  read-only
	STATUS  mandatory
	DESCRIPTION "CB3B KVA"
		::= { bcmsplus1 193 }

bcms1-cb3c-kva
	OBJECT-TYPE
	SYNTAX  INTEGER
	ACCESS  read-only
	STATUS  mandatory
	DESCRIPTION "CB3C KVA"
		::= { bcmsplus1 194 }

bcms1-cb4a-kva
	OBJECT-TYPE
	SYNTAX  INTEGER
	ACCESS  read-only
	STATUS  mandatory
	DESCRIPTION "CB4A KVA"
		::= { bcmsplus1 195 }

bcms1-cb4b-kva
	OBJECT-TYPE
	SYNTAX  INTEGER
	ACCESS  read-only
	STATUS  mandatory
	DESCRIPTION "CB4B KVA"
		::= { bcmsplus1 196 }

bcms1-cb4c-kva
	OBJECT-TYPE
	SYNTAX  INTEGER
	ACCESS  read-only
	STATUS  mandatory
	DESCRIPTION "CB4C KVA"
		::= { bcmsplus1 197 }
  
bcms1-cb5a-kva
	OBJECT-TYPE
	SYNTAX  INTEGER
	ACCESS  read-only
	STATUS  mandatory
	DESCRIPTION "CB5A KVA"
		::= { bcmsplus1 198 }

bcms1-cb5b-kva
	OBJECT-TYPE
	SYNTAX  INTEGER
	ACCESS  read-only
	STATUS  mandatory
	DESCRIPTION "CB5B KVA"
		::= { bcmsplus1 199 }

bcms1-cb5c-kva
	OBJECT-TYPE
	SYNTAX  INTEGER
	ACCESS  read-only
	STATUS  mandatory
	DESCRIPTION "CB5C KVA"
		::= { bcmsplus1 200 }

bcms1-cb6a-kva
	OBJECT-TYPE
	SYNTAX  INTEGER
	ACCESS  read-only
	STATUS  mandatory
	DESCRIPTION "CB6A KVA"
		::= { bcmsplus1 201 }

bcms1-cb6b-kva
	OBJECT-TYPE
	SYNTAX  INTEGER
	ACCESS  read-only
	STATUS  mandatory
	DESCRIPTION "CB6B KVA"
		::= { bcmsplus1 202 }

bcms1-cb6c-kva
	OBJECT-TYPE
	SYNTAX  INTEGER
	ACCESS  read-only
	STATUS  mandatory
	DESCRIPTION "CB6C KVA"
		::= { bcmsplus1 203 }

bcms1-cb7a-kva
	OBJECT-TYPE
	SYNTAX  INTEGER
	ACCESS  read-only
	STATUS  mandatory
	DESCRIPTION "CB7A KVA"
		::= { bcmsplus1 204 }

bcms1-cb7b-kva
	OBJECT-TYPE
	SYNTAX  INTEGER
	ACCESS  read-only
	STATUS  mandatory
	DESCRIPTION "CB7B KVA"
		::= { bcmsplus1 205 }

bcms1-cb7c-kva
	OBJECT-TYPE
	SYNTAX  INTEGER
	ACCESS  read-only
	STATUS  mandatory
	DESCRIPTION "CB7C KVA"
		::= { bcmsplus1 206 }

bcms1-cb8a-kva
	OBJECT-TYPE
	SYNTAX  INTEGER
	ACCESS  read-only
	STATUS  mandatory
	DESCRIPTION "CB8A KVA"
		::= { bcmsplus1 207 }
  
bcms1-cb8b-kva
	OBJECT-TYPE
	SYNTAX  INTEGER
	ACCESS  read-only
	STATUS  mandatory
	DESCRIPTION "CB8B KVA"
		::= { bcmsplus1 208 }

bcms1-cb8c-kva
	OBJECT-TYPE
	SYNTAX  INTEGER
	ACCESS  read-only
	STATUS  mandatory
	DESCRIPTION "CB8C KVA"
		::= { bcmsplus1 209 }

bcms1-cb9a-kva
	OBJECT-TYPE
	SYNTAX  INTEGER
	ACCESS  read-only
	STATUS  mandatory
	DESCRIPTION "CB9A KVA"
		::= { bcmsplus1 210 }

bcms1-cb9b-kva
	OBJECT-TYPE
	SYNTAX  INTEGER
	ACCESS  read-only
	STATUS  mandatory
	DESCRIPTION "CB9B KVA"
		::= { bcmsplus1 211 }

bcms1-cb9c-kva
	OBJECT-TYPE
	SYNTAX  INTEGER
	ACCESS  read-only
	STATUS  mandatory
	DESCRIPTION "CB9C KVA"
		::= { bcmsplus1 212 }

bcms1-cb10a-kva
	OBJECT-TYPE
	SYNTAX  INTEGER
	ACCESS  read-only
	STATUS  mandatory
	DESCRIPTION "CB10A KVA"
		::= { bcmsplus1 213 }

bcms1-cb10b-kva
	OBJECT-TYPE
	SYNTAX  INTEGER
	ACCESS  read-only
	STATUS  mandatory
	DESCRIPTION "CB10B KVA"
		::= { bcmsplus1 214 }

bcms1-cb10c-kva
	OBJECT-TYPE
	SYNTAX  INTEGER
	ACCESS  read-only
	STATUS  mandatory
	DESCRIPTION "CB10C KVA"
		::= { bcmsplus1 215 }

bcms1-cb11a-kva
	OBJECT-TYPE
	SYNTAX  INTEGER
	ACCESS  read-only
	STATUS  mandatory
	DESCRIPTION "CB11A KVA"
		::= { bcmsplus1 216 }

bcms1-cb11b-kva
	OBJECT-TYPE
	SYNTAX  INTEGER
	ACCESS  read-only
	STATUS  mandatory
	DESCRIPTION "CB11B KVA"
		::= { bcmsplus1 217 }
  
bcms1-cb11c-kva
	OBJECT-TYPE
	SYNTAX  INTEGER
	ACCESS  read-only
	STATUS  mandatory
	DESCRIPTION "CB11C KVA"
		::= { bcmsplus1 218 }

bcms1-cb12a-kva
	OBJECT-TYPE
	SYNTAX  INTEGER
	ACCESS  read-only
	STATUS  mandatory
	DESCRIPTION "CB12A KVA"
		::= { bcmsplus1 219 }

bcms1-cb12b-kva
	OBJECT-TYPE
	SYNTAX  INTEGER
	ACCESS  read-only
	STATUS  mandatory
	DESCRIPTION "CB12B KVA"
		::= { bcmsplus1 220 }

bcms1-cb12c-kva
	OBJECT-TYPE
	SYNTAX  INTEGER
	ACCESS  read-only
	STATUS  mandatory
	DESCRIPTION "CB12C KVA"
		::= { bcmsplus1 221 }

bcms1-cb13a-kva
	OBJECT-TYPE
	SYNTAX  INTEGER
	ACCESS  read-only
	STATUS  mandatory
	DESCRIPTION "CB13A KVA"
		::= { bcmsplus1 222 }

bcms1-cb13b-kva
	OBJECT-TYPE
	SYNTAX  INTEGER
	ACCESS  read-only
	STATUS  mandatory
	DESCRIPTION "CB13B KVA"
		::= { bcmsplus1 223 }

bcms1-cb13c-kva
	OBJECT-TYPE
	SYNTAX  INTEGER
	ACCESS  read-only
	STATUS  mandatory
	DESCRIPTION "CB13C KVA"
		::= { bcmsplus1 224 }

bcms1-cb14a-kva
	OBJECT-TYPE
	SYNTAX  INTEGER
	ACCESS  read-only
	STATUS  mandatory
	DESCRIPTION "CB14A KVA"
		::= { bcmsplus1 225 }

bcms1-cb14b-kva
	OBJECT-TYPE
	SYNTAX  INTEGER
	ACCESS  read-only
	STATUS  mandatory
	DESCRIPTION "CB14B KVA"
		::= { bcmsplus1 226 }

bcms1-cb14c-kva
	OBJECT-TYPE
	SYNTAX  INTEGER
	ACCESS  read-only
	STATUS  mandatory
	DESCRIPTION "CB14C KVA"
		::= { bcmsplus1 227 }

bcms1-cb1a-kvar
	OBJECT-TYPE
	SYNTAX  INTEGER
	ACCESS  read-only
	STATUS  mandatory
	DESCRIPTION "CB1A KVAR
		     Note: for all kvar 1-42: 100 = 10.0KW"  
		::= { bcmsplus1 228 }

bcms1-cb1b-kvar
	OBJECT-TYPE
	SYNTAX  INTEGER
	ACCESS  read-only
	STATUS  mandatory
	DESCRIPTION "CB1B KVAR"
		::= { bcmsplus1 229 }
  
bcms1-cb1c-kvar
	OBJECT-TYPE
	SYNTAX  INTEGER
	ACCESS  read-only
	STATUS  mandatory
	DESCRIPTION "CB1C KVAR"
		::= { bcmsplus1 230 }

bcms1-cb2a-kvar
	OBJECT-TYPE
	SYNTAX  INTEGER
	ACCESS  read-only
	STATUS  mandatory
	DESCRIPTION "CB2A KVAR"
		::= { bcmsplus1 231 }

bcms1-cb2b-kvar
	OBJECT-TYPE
	SYNTAX  INTEGER
	ACCESS  read-only
	STATUS  mandatory
	DESCRIPTION "CB2B KVAR"
		::= { bcmsplus1 232 }

bcms1-cb2c-kvar
	OBJECT-TYPE
	SYNTAX  INTEGER
	ACCESS  read-only
	STATUS  mandatory
	DESCRIPTION "CB2C KVAR"
		::= { bcmsplus1 233 }

bcms1-cb3a-kvar
	OBJECT-TYPE
	SYNTAX  INTEGER
	ACCESS  read-only
	STATUS  mandatory
	DESCRIPTION "CB3A KVAR"
		::= { bcmsplus1 234 }

bcms1-cb3b-kvar
	OBJECT-TYPE
	SYNTAX  INTEGER
	ACCESS  read-only
	STATUS  mandatory
	DESCRIPTION "CB3B KVAR"
		::= { bcmsplus1 235 }

bcms1-cb3c-kvar
	OBJECT-TYPE
	SYNTAX  INTEGER
	ACCESS  read-only
	STATUS  mandatory
	DESCRIPTION "CB3C KVAR"
		::= { bcmsplus1 236 }

bcms1-cb4a-kvar
	OBJECT-TYPE
	SYNTAX  INTEGER
	ACCESS  read-only
	STATUS  mandatory
	DESCRIPTION "CB4A KVAR"
		::= { bcmsplus1 237 }

bcms1-cb4b-kvar
	OBJECT-TYPE
	SYNTAX  INTEGER
	ACCESS  read-only
	STATUS  mandatory
	DESCRIPTION "CB4B KVAR"
		::= { bcmsplus1 238 }

bcms1-cb4c-kvar
	OBJECT-TYPE
	SYNTAX  INTEGER
	ACCESS  read-only
	STATUS  mandatory
	DESCRIPTION "CB4C KVAR"
		::= { bcmsplus1 239 }
  
bcms1-cb5a-kvar
	OBJECT-TYPE
	SYNTAX  INTEGER
	ACCESS  read-only
	STATUS  mandatory
	DESCRIPTION "CB5A KVAR"
		::= { bcmsplus1 240 }

bcms1-cb5b-kvar
	OBJECT-TYPE
	SYNTAX  INTEGER
	ACCESS  read-only
	STATUS  mandatory
	DESCRIPTION "CB5B KVAR"
		::= { bcmsplus1 241 }

bcms1-cb5c-kvar
	OBJECT-TYPE
	SYNTAX  INTEGER
	ACCESS  read-only
	STATUS  mandatory
	DESCRIPTION "CB5C KVAR"
		::= { bcmsplus1 242 }

bcms1-cb6a-kvar
	OBJECT-TYPE
	SYNTAX  INTEGER
	ACCESS  read-only
	STATUS  mandatory
	DESCRIPTION "CB6A KVAR"
		::= { bcmsplus1 243 }

bcms1-cb6b-kvar
	OBJECT-TYPE
	SYNTAX  INTEGER
	ACCESS  read-only
	STATUS  mandatory
	DESCRIPTION "CB6B KVAR"
		::= { bcmsplus1 244 }

bcms1-cb6c-kvar
	OBJECT-TYPE
	SYNTAX  INTEGER
	ACCESS  read-only
	STATUS  mandatory
	DESCRIPTION "CB6C KVAR"
		::= { bcmsplus1 245 }

bcms1-cb7a-kvar
	OBJECT-TYPE
	SYNTAX  INTEGER
	ACCESS  read-only
	STATUS  mandatory
	DESCRIPTION "CB7A KVAR"
		::= { bcmsplus1 246 }

bcms1-cb7b-kvar
	OBJECT-TYPE
	SYNTAX  INTEGER
	ACCESS  read-only
	STATUS  mandatory
	DESCRIPTION "CB7B KVAR"
		::= { bcmsplus1 247 }

bcms1-cb7c-kvar
	OBJECT-TYPE
	SYNTAX  INTEGER
	ACCESS  read-only
	STATUS  mandatory
	DESCRIPTION "CB7C KVAR"
		::= { bcmsplus1 248 }

bcms1-cb8a-kvar
	OBJECT-TYPE
	SYNTAX  INTEGER
	ACCESS  read-only
	STATUS  mandatory
	DESCRIPTION "CB8A KVAR"
		::= { bcmsplus1 249 }
  
bcms1-cb8b-kvar
	OBJECT-TYPE
	SYNTAX  INTEGER
	ACCESS  read-only
	STATUS  mandatory
	DESCRIPTION "CB8B KVAR"
		::= { bcmsplus1 250 }

bcms1-cb8c-kvar
	OBJECT-TYPE
	SYNTAX  INTEGER
	ACCESS  read-only
	STATUS  mandatory
	DESCRIPTION "CB8C KVAR"
		::= { bcmsplus1 251 }

bcms1-cb9a-kvar
	OBJECT-TYPE
	SYNTAX  INTEGER
	ACCESS  read-only
	STATUS  mandatory
	DESCRIPTION "CB9A KVAR"
		::= { bcmsplus1 252 }

bcms1-cb9b-kvar
	OBJECT-TYPE
	SYNTAX  INTEGER
	ACCESS  read-only
	STATUS  mandatory
	DESCRIPTION "CB9B KVAR"
		::= { bcmsplus1 253 }

bcms1-cb9c-kvar
	OBJECT-TYPE
	SYNTAX  INTEGER
	ACCESS  read-only
	STATUS  mandatory
	DESCRIPTION "CB9C KVAR"
		::= { bcmsplus1 254 }

bcms1-cb10a-kvar
	OBJECT-TYPE
	SYNTAX  INTEGER
	ACCESS  read-only
	STATUS  mandatory
	DESCRIPTION "CB10A KVAR"
		::= { bcmsplus1 255 }

bcms1-cb10b-kvar
	OBJECT-TYPE
	SYNTAX  INTEGER
	ACCESS  read-only
	STATUS  mandatory
	DESCRIPTION "CB10B KVAR"
		::= { bcmsplus1 256}

bcms1-cb10c-kvar
	OBJECT-TYPE
	SYNTAX  INTEGER
	ACCESS  read-only
	STATUS  mandatory
	DESCRIPTION "CB10C KVAR"
		::= { bcmsplus1 257 }

bcms1-cb11a-kvar
	OBJECT-TYPE
	SYNTAX  INTEGER
	ACCESS  read-only
	STATUS  mandatory
	DESCRIPTION "CB11A KVAR"
		::= { bcmsplus1 258 }

bcms1-cb11b-kvar
	OBJECT-TYPE
	SYNTAX  INTEGER
	ACCESS  read-only
	STATUS  mandatory
	DESCRIPTION "CB11B KVAR"
		::= { bcmsplus1 259 }
  
bcms1-cb11c-kvar
	OBJECT-TYPE
	SYNTAX  INTEGER
	ACCESS  read-only
	STATUS  mandatory
	DESCRIPTION "CB11C KVAR"
		::= { bcmsplus1 260 }

bcms1-cb12a-kvar
	OBJECT-TYPE
	SYNTAX  INTEGER
	ACCESS  read-only
	STATUS  mandatory
	DESCRIPTION "CB12A KVAR"
		::= { bcmsplus1 261 }

bcms1-cb12b-kvar
	OBJECT-TYPE
	SYNTAX  INTEGER
	ACCESS  read-only
	STATUS  mandatory
	DESCRIPTION "CB12B KVAR"
		::= { bcmsplus1 262 }

bcms1-cb12c-kvar
	OBJECT-TYPE
	SYNTAX  INTEGER
	ACCESS  read-only
	STATUS  mandatory
	DESCRIPTION "CB12C KVAR"
		::= { bcmsplus1 263 }

bcms1-cb13a-kvar
	OBJECT-TYPE
	SYNTAX  INTEGER
	ACCESS  read-only
	STATUS  mandatory
	DESCRIPTION "CB13A KVAR"
		::= { bcmsplus1 264 }

bcms1-cb13b-kvar
	OBJECT-TYPE
	SYNTAX  INTEGER
	ACCESS  read-only
	STATUS  mandatory
	DESCRIPTION "CB13B KVAR"
		::= { bcmsplus1 265 }

bcms1-cb13c-kvar
	OBJECT-TYPE
	SYNTAX  INTEGER
	ACCESS  read-only
	STATUS  mandatory
	DESCRIPTION "CB13C KVAR"
		::= { bcmsplus1 266 }

bcms1-cb14a-kvar
	OBJECT-TYPE
	SYNTAX  INTEGER
	ACCESS  read-only
	STATUS  mandatory
	DESCRIPTION "CB14A KVAR"
		::= { bcmsplus1 267 }

bcms1-cb14b-kvar
	OBJECT-TYPE
	SYNTAX  INTEGER
	ACCESS  read-only
	STATUS  mandatory
	DESCRIPTION "CB14B KVAR"
		::= { bcmsplus1 268 }

bcms1-cb14c-kvar
	OBJECT-TYPE
	SYNTAX  INTEGER
	ACCESS  read-only
	STATUS  mandatory
	DESCRIPTION "CB14C KVAR"
		::= { bcmsplus1 269 }

bcms1-cb1a-pf
	OBJECT-TYPE
	SYNTAX  INTEGER
	ACCESS  read-only
	STATUS  mandatory
	DESCRIPTION "CB1A PF
		     Note: for all pf 1-42: 100 = 100%"  
		::= { bcmsplus1 270 }

bcms1-cb1b-pf
	OBJECT-TYPE
	SYNTAX  INTEGER
	ACCESS  read-only
	STATUS  mandatory
	DESCRIPTION "CB1B PF"
		::= { bcmsplus1 271 }
  
bcms1-cb1c-pf
	OBJECT-TYPE
	SYNTAX  INTEGER
	ACCESS  read-only
	STATUS  mandatory
	DESCRIPTION "CB1C PF"
		::= { bcmsplus1 272 }

bcms1-cb2a-pf
	OBJECT-TYPE
	SYNTAX  INTEGER
	ACCESS  read-only
	STATUS  mandatory
	DESCRIPTION "CB2A PF"
		::= { bcmsplus1 273 }

bcms1-cb2b-pf
	OBJECT-TYPE
	SYNTAX  INTEGER
	ACCESS  read-only
	STATUS  mandatory
	DESCRIPTION "CB2B PF"
		::= { bcmsplus1 274 }

bcms1-cb2c-pf
	OBJECT-TYPE
	SYNTAX  INTEGER
	ACCESS  read-only
	STATUS  mandatory
	DESCRIPTION "CB2C PF"
		::= { bcmsplus1 275 }

bcms1-cb3a-pf
	OBJECT-TYPE
	SYNTAX  INTEGER
	ACCESS  read-only
	STATUS  mandatory
	DESCRIPTION "CB3A PF"
		::= { bcmsplus1 276 }

bcms1-cb3b-pf
	OBJECT-TYPE
	SYNTAX  INTEGER
	ACCESS  read-only
	STATUS  mandatory
	DESCRIPTION "CB3B PF"
		::= { bcmsplus1 277 }

bcms1-cb3c-pf
	OBJECT-TYPE
	SYNTAX  INTEGER
	ACCESS  read-only
	STATUS  mandatory
	DESCRIPTION "CB3C PF"
		::= { bcmsplus1 278 }

bcms1-cb4a-pf
	OBJECT-TYPE
	SYNTAX  INTEGER
	ACCESS  read-only
	STATUS  mandatory
	DESCRIPTION "CB4A PF"
		::= { bcmsplus1 279 }

bcms1-cb4b-pf
	OBJECT-TYPE
	SYNTAX  INTEGER
	ACCESS  read-only
	STATUS  mandatory
	DESCRIPTION "CB4B PF"
		::= { bcmsplus1 280 }

bcms1-cb4c-pf
	OBJECT-TYPE
	SYNTAX  INTEGER
	ACCESS  read-only
	STATUS  mandatory
	DESCRIPTION "CB4C PF"
		::= { bcmsplus1 281 }
  
bcms1-cb5a-pf
	OBJECT-TYPE
	SYNTAX  INTEGER
	ACCESS  read-only
	STATUS  mandatory
	DESCRIPTION "CB5A PF"
		::= { bcmsplus1 282 }

bcms1-cb5b-pf
	OBJECT-TYPE
	SYNTAX  INTEGER
	ACCESS  read-only
	STATUS  mandatory
	DESCRIPTION "CB5B PF"
		::= { bcmsplus1 283 }

bcms1-cb5c-pf
	OBJECT-TYPE
	SYNTAX  INTEGER
	ACCESS  read-only
	STATUS  mandatory
	DESCRIPTION "CB5C PF"
		::= { bcmsplus1 284 }

bcms1-cb6a-pf
	OBJECT-TYPE
	SYNTAX  INTEGER
	ACCESS  read-only
	STATUS  mandatory
	DESCRIPTION "CB6A PF"
		::= { bcmsplus1 285 }

bcms1-cb6b-pf
	OBJECT-TYPE
	SYNTAX  INTEGER
	ACCESS  read-only
	STATUS  mandatory
	DESCRIPTION "CB6B PF"
		::= { bcmsplus1 286 }

bcms1-cb6c-pf
	OBJECT-TYPE
	SYNTAX  INTEGER
	ACCESS  read-only
	STATUS  mandatory
	DESCRIPTION "CB6C PF"
		::= { bcmsplus1 287 }

bcms1-cb7a-pf
	OBJECT-TYPE
	SYNTAX  INTEGER
	ACCESS  read-only
	STATUS  mandatory
	DESCRIPTION "CB7A PF"
		::= { bcmsplus1 288 }

bcms1-cb7b-pf
	OBJECT-TYPE
	SYNTAX  INTEGER
	ACCESS  read-only
	STATUS  mandatory
	DESCRIPTION "CB7B PF"
		::= { bcmsplus1 289 }

bcms1-cb7c-pf
	OBJECT-TYPE
	SYNTAX  INTEGER
	ACCESS  read-only
	STATUS  mandatory
	DESCRIPTION "CB7C PF"
		::= { bcmsplus1 290 }

bcms1-cb8a-pf
	OBJECT-TYPE
	SYNTAX  INTEGER
	ACCESS  read-only
	STATUS  mandatory
	DESCRIPTION "CB8A PF"
		::= { bcmsplus1 291 }
  
bcms1-cb8b-pf
	OBJECT-TYPE
	SYNTAX  INTEGER
	ACCESS  read-only
	STATUS  mandatory
	DESCRIPTION "CB8B PF"
		::= { bcmsplus1 292 }

bcms1-cb8c-pf
	OBJECT-TYPE
	SYNTAX  INTEGER
	ACCESS  read-only
	STATUS  mandatory
	DESCRIPTION "CB8C PF"
		::= { bcmsplus1 293 }

bcms1-cb9a-pf
	OBJECT-TYPE
	SYNTAX  INTEGER
	ACCESS  read-only
	STATUS  mandatory
	DESCRIPTION "CB9A PF"
		::= { bcmsplus1 294 }

bcms1-cb9b-pf
	OBJECT-TYPE
	SYNTAX  INTEGER
	ACCESS  read-only
	STATUS  mandatory
	DESCRIPTION "CB9B PF"
		::= { bcmsplus1 295 }

bcms1-cb9c-pf
	OBJECT-TYPE
	SYNTAX  INTEGER
	ACCESS  read-only
	STATUS  mandatory
	DESCRIPTION "CB9C PF"
		::= { bcmsplus1 296 }

bcms1-cb10a-pf
	OBJECT-TYPE
	SYNTAX  INTEGER
	ACCESS  read-only
	STATUS  mandatory
	DESCRIPTION "CB10A PF"
		::= { bcmsplus1 297 }

bcms1-cb10b-pf
	OBJECT-TYPE
	SYNTAX  INTEGER
	ACCESS  read-only
	STATUS  mandatory
	DESCRIPTION "CB10B PF"
		::= { bcmsplus1 298 }

bcms1-cb10c-pf
	OBJECT-TYPE
	SYNTAX  INTEGER
	ACCESS  read-only
	STATUS  mandatory
	DESCRIPTION "CB10C PF"
		::= { bcmsplus1 299 }

bcms1-cb11a-pf
	OBJECT-TYPE
	SYNTAX  INTEGER
	ACCESS  read-only
	STATUS  mandatory
	DESCRIPTION "CB11A PF"
		::= { bcmsplus1 300 }

bcms1-cb11b-pf
	OBJECT-TYPE
	SYNTAX  INTEGER
	ACCESS  read-only
	STATUS  mandatory
	DESCRIPTION "CB11B PF"
		::= { bcmsplus1 301 }
  
bcms1-cb11c-pf
	OBJECT-TYPE
	SYNTAX  INTEGER
	ACCESS  read-only
	STATUS  mandatory
	DESCRIPTION "CB11C PF"
		::= { bcmsplus1 302 }

bcms1-cb12a-pf
	OBJECT-TYPE
	SYNTAX  INTEGER
	ACCESS  read-only
	STATUS  mandatory
	DESCRIPTION "CB12A PF"
		::= { bcmsplus1 303 }

bcms1-cb12b-pf
	OBJECT-TYPE
	SYNTAX  INTEGER
	ACCESS  read-only
	STATUS  mandatory
	DESCRIPTION "CB12B PF"
		::= { bcmsplus1 304 }

bcms1-cb12c-pf
	OBJECT-TYPE
	SYNTAX  INTEGER
	ACCESS  read-only
	STATUS  mandatory
	DESCRIPTION "CB12C PF"
		::= { bcmsplus1 305 }

bcms1-cb13a-pf
	OBJECT-TYPE
	SYNTAX  INTEGER
	ACCESS  read-only
	STATUS  mandatory
	DESCRIPTION "CB13A PF"
		::= { bcmsplus1 306 }

bcms1-cb13b-pf
	OBJECT-TYPE
	SYNTAX  INTEGER
	ACCESS  read-only
	STATUS  mandatory
	DESCRIPTION "CB13B PF"
		::= { bcmsplus1 307 }

bcms1-cb13c-pf
	OBJECT-TYPE
	SYNTAX  INTEGER
	ACCESS  read-only
	STATUS  mandatory
	DESCRIPTION "CB13C PF"
		::= { bcmsplus1 308 }

bcms1-cb14a-pf
	OBJECT-TYPE
	SYNTAX  INTEGER
	ACCESS  read-only
	STATUS  mandatory
	DESCRIPTION "CB14A PF"
		::= { bcmsplus1 309 }

bcms1-cb14b-pf
	OBJECT-TYPE
	SYNTAX  INTEGER
	ACCESS  read-only
	STATUS  mandatory
	DESCRIPTION "CB14B PF"
		::= { bcmsplus1 310 }

bcms1-cb14c-pf
	OBJECT-TYPE
	SYNTAX  INTEGER
	ACCESS  read-only
	STATUS  mandatory
	DESCRIPTION "CB14C PF"
		::= { bcmsplus1 311 }

bcms1-cb1-percent-load
	OBJECT-TYPE
	SYNTAX  INTEGER
	ACCESS  read-only
	STATUS  mandatory
	DESCRIPTION "set1 CB1 Percent Load
		       Note for all breaker sizes 1-14: 100 = 100 amps
                   Range is 20 to 600 amps"
		::= { bcmsplus1 312 }

bcms1-cb2-percent-load
	OBJECT-TYPE
	SYNTAX  INTEGER
	ACCESS  read-only
	STATUS  mandatory
	DESCRIPTION "set1 CB2 Percent Load"
		::= { bcmsplus1 313 }

bcms1-cb3-percent-load
	OBJECT-TYPE
	SYNTAX  INTEGER
	ACCESS  read-only
	STATUS  mandatory
	DESCRIPTION "set1 CB3 Percent Load"
		::= { bcmsplus1 314 }

bcms1-cb4-percent-load
	OBJECT-TYPE
	SYNTAX  INTEGER
	ACCESS  read-only
	STATUS  mandatory
	DESCRIPTION "set1 CB4 Percent Load"
		::= { bcmsplus1 315 }

bcms1-cb5-percent-load
	OBJECT-TYPE
	SYNTAX  INTEGER
	ACCESS  read-only
	STATUS  mandatory
	DESCRIPTION "set1 CB5 Percent Load"
		::= { bcmsplus1 316 }

bcms1-cb6-percent-load
	OBJECT-TYPE
	SYNTAX  INTEGER
	ACCESS  read-only
	STATUS  mandatory
	DESCRIPTION "set1 CB6 Percent Load"
		::= { bcmsplus1 317 }
  
bcms1-cb7-percent-load
	OBJECT-TYPE
	SYNTAX  INTEGER
	ACCESS  read-only
	STATUS  mandatory
	DESCRIPTION "set1 CB7 Percent Load"
		::= { bcmsplus1 318 }

bcms1-cb8-percent-load
	OBJECT-TYPE
	SYNTAX  INTEGER
	ACCESS  read-only
	STATUS  mandatory
	DESCRIPTION "set1 CB8 Percent Load"
		::= { bcmsplus1 319 }

bcms1-cb9-percent-load
	OBJECT-TYPE
	SYNTAX  INTEGER
	ACCESS  read-only
	STATUS  mandatory
	DESCRIPTION "set1 CB9 Percent Load"
		::= { bcmsplus1 320 }

bcms1-cb10-percent-load
	OBJECT-TYPE
	SYNTAX  INTEGER
	ACCESS  read-only
	STATUS  mandatory
	DESCRIPTION "set1 CB10 Percent Load"
		::= { bcmsplus1 321 }

bcms1-cb11-percent-load
	OBJECT-TYPE
	SYNTAX  INTEGER
	ACCESS  read-only
	STATUS  mandatory
	DESCRIPTION "set1 CB11 Percent Load"
		::= { bcmsplus1 322 }

bcms1-cb12-percent-load
	OBJECT-TYPE
	SYNTAX  INTEGER
	ACCESS  read-only
	STATUS  mandatory
	DESCRIPTION "set1 CB12 Percent Load"
		::= { bcmsplus1 323 }

bcms1-cb13-percent-load
	OBJECT-TYPE
	SYNTAX  INTEGER
	ACCESS  read-only
	STATUS  mandatory
	DESCRIPTION "set1 CB13 Percent Load"
		::= { bcmsplus1 324 }

bcms1-cb14-percent-load
	OBJECT-TYPE
	SYNTAX  INTEGER
	ACCESS  read-only
	STATUS  mandatory
	DESCRIPTION "set1 CB14 Percent Load"
		::= { bcmsplus1 325 }

bcms1-cb1a-crest-factor
	OBJECT-TYPE
	SYNTAX  INTEGER
	ACCESS  read-write
	STATUS  mandatory
	DESCRIPTION "CB1A Crest Factor
		     Note: for all Crest Factor 1-42: 141 = 1.41"  
		::= { bcmsplus1 326 }

bcms1-cb1b-crest-factor
	OBJECT-TYPE
	SYNTAX  INTEGER
	ACCESS  read-only
	STATUS  mandatory
	DESCRIPTION "CB1B Crest Factor"
		::= { bcmsplus1 327 }

bcms1-cb1c-crest-factor
	OBJECT-TYPE
	SYNTAX  INTEGER
	ACCESS  read-only
	STATUS  mandatory
	DESCRIPTION "CB1C Crest Factor"
		::= { bcmsplus1 328 }

bcms1-cb2a-crest-factor
	OBJECT-TYPE
	SYNTAX  INTEGER
	ACCESS  read-only
	STATUS  mandatory
	DESCRIPTION "CB2A Crest Factor"
		::= { bcmsplus1 329 }
  
bcms1-cb2b-crest-factor
	OBJECT-TYPE
	SYNTAX  INTEGER
	ACCESS  read-only
	STATUS  mandatory
	DESCRIPTION "CB2B Crest Factor"
		::= { bcmsplus1 330 }

bcms1-cb2c-crest-factor
	OBJECT-TYPE
	SYNTAX  INTEGER
	ACCESS  read-only
	STATUS  mandatory
	DESCRIPTION "CB2C Crest Factor"
		::= { bcmsplus1 331 }

bcms1-cb3a-crest-factor
	OBJECT-TYPE
	SYNTAX  INTEGER
	ACCESS  read-only
	STATUS  mandatory
	DESCRIPTION "CB3A Crest Factor"
		::= { bcmsplus1 332 }

bcms1-cb3b-crest-factor
	OBJECT-TYPE
	SYNTAX  INTEGER
	ACCESS  read-only
	STATUS  mandatory
	DESCRIPTION "CB3B Crest Factor"
		::= { bcmsplus1 333 }

bcms1-cb3c-crest-factor
	OBJECT-TYPE
	SYNTAX  INTEGER
	ACCESS  read-only
	STATUS  mandatory
	DESCRIPTION "CB3C Crest Factor"
		::= { bcmsplus1 334 }

bcms1-cb4a-crest-factor
	OBJECT-TYPE
	SYNTAX  INTEGER
	ACCESS  read-only
	STATUS  mandatory
	DESCRIPTION "CB4A Crest Factor"
		::= { bcmsplus1 335 }

bcms1-cb4b-crest-factor
	OBJECT-TYPE
	SYNTAX  INTEGER
	ACCESS  read-only
	STATUS  mandatory
	DESCRIPTION "CB4B Crest Factor"
		::= { bcmsplus1 336 }

bcms1-cb4c-crest-factor
	OBJECT-TYPE
	SYNTAX  INTEGER
	ACCESS  read-only
	STATUS  mandatory
	DESCRIPTION "CB4C Crest Factor"
		::= { bcmsplus1 337 }

bcms1-cb5a-crest-factor
	OBJECT-TYPE
	SYNTAX  INTEGER
	ACCESS  read-only
	STATUS  mandatory
	DESCRIPTION "CB5A Crest Factor"
		::= { bcmsplus1 338 }

bcms1-cb5b-crest-factor
	OBJECT-TYPE
	SYNTAX  INTEGER
	ACCESS  read-only
	STATUS  mandatory
	DESCRIPTION "CB5B Crest Factor"
		::= { bcmsplus1 339 }
  
bcms1-cb5c-crest-factor
	OBJECT-TYPE
	SYNTAX  INTEGER
	ACCESS  read-only
	STATUS  mandatory
	DESCRIPTION "CB5C Crest Factor"
		::= { bcmsplus1 340 }

bcms1-cb6a-crest-factor
	OBJECT-TYPE
	SYNTAX  INTEGER
	ACCESS  read-only
	STATUS  mandatory
	DESCRIPTION "CB6A Crest Factor"
		::= { bcmsplus1 341 }

bcms1-cb6b-crest-factor
	OBJECT-TYPE
	SYNTAX  INTEGER
	ACCESS  read-only
	STATUS  mandatory
	DESCRIPTION "CB6B Crest Factor"
		::= { bcmsplus1 342 }

bcms1-cb6c-crest-factor
	OBJECT-TYPE
	SYNTAX  INTEGER
	ACCESS  read-only
	STATUS  mandatory
	DESCRIPTION "CB6C Crest Factor"
		::= { bcmsplus1 343 }

bcms1-cb7a-crest-factor
	OBJECT-TYPE
	SYNTAX  INTEGER
	ACCESS  read-only
	STATUS  mandatory
	DESCRIPTION "CB7A Crest Factor"
		::= { bcmsplus1 344 }

bcms1-cb7b-crest-factor
	OBJECT-TYPE
	SYNTAX  INTEGER
	ACCESS  read-only
	STATUS  mandatory
	DESCRIPTION "CB7B Crest Factor"
		::= { bcmsplus1 345 }

bcms1-cb7c-crest-factor
	OBJECT-TYPE
	SYNTAX  INTEGER
	ACCESS  read-only
	STATUS  mandatory
	DESCRIPTION "CB7C Crest Factor"
		::= { bcmsplus1 346 }

bcms1-cb8a-crest-factor
	OBJECT-TYPE
	SYNTAX  INTEGER
	ACCESS  read-only
	STATUS  mandatory
	DESCRIPTION "CB8A Crest Factor"
		::= { bcmsplus1 347 }

bcms1-cb8b-crest-factor
	OBJECT-TYPE
	SYNTAX  INTEGER
	ACCESS  read-only
	STATUS  mandatory
	DESCRIPTION "CB8B Crest Factor"
		::= { bcmsplus1 348 }

bcms1-cb8c-crest-factor
	OBJECT-TYPE
	SYNTAX  INTEGER
	ACCESS  read-only
	STATUS  mandatory
	DESCRIPTION "CB8C Crest Factor"
		::= { bcmsplus1 349 }
  
bcms1-cb9a-crest-factor
	OBJECT-TYPE
	SYNTAX  INTEGER
	ACCESS  read-only
	STATUS  mandatory
	DESCRIPTION "CB9A Crest Factor"
		::= { bcmsplus1 350 }

bcms1-cb9b-crest-factor
	OBJECT-TYPE
	SYNTAX  INTEGER
	ACCESS  read-only
	STATUS  mandatory
	DESCRIPTION "CB9B Crest Factor"
		::= { bcmsplus1 351 }

bcms1-cb9c-crest-factor
	OBJECT-TYPE
	SYNTAX  INTEGER
	ACCESS  read-only
	STATUS  mandatory
	DESCRIPTION "CB9C Crest Factor"
		::= { bcmsplus1 352 }

bcms1-cb10a-crest-factor
	OBJECT-TYPE
	SYNTAX  INTEGER
	ACCESS  read-only
	STATUS  mandatory
	DESCRIPTION "CB10A Crest Factor"
		::= { bcmsplus1 353 }

bcms1-cb10b-crest-factor
	OBJECT-TYPE
	SYNTAX  INTEGER
	ACCESS  read-only
	STATUS  mandatory
	DESCRIPTION "CB10B Crest Factor"
		::= { bcmsplus1 354 }

bcms1-cb10c-crest-factor
	OBJECT-TYPE
	SYNTAX  INTEGER
	ACCESS  read-only
	STATUS  mandatory
	DESCRIPTION "CB10C Crest Factor"
		::= { bcmsplus1 355 }

bcms1-cb11a-crest-factor
	OBJECT-TYPE
	SYNTAX  INTEGER
	ACCESS  read-only
	STATUS  mandatory
	DESCRIPTION "CB11A Crest Factor"
		::= { bcmsplus1 356 }

bcms1-cb11b-crest-factor
	OBJECT-TYPE
	SYNTAX  INTEGER
	ACCESS  read-only
	STATUS  mandatory
	DESCRIPTION "CB11B Crest Factor"
		::= { bcmsplus1 357 }

bcms1-cb11c-crest-factor
	OBJECT-TYPE
	SYNTAX  INTEGER
	ACCESS  read-only
	STATUS  mandatory
	DESCRIPTION "CB11C Crest Factor"
		::= { bcmsplus1 358 }

bcms1-cb12a-crest-factor
	OBJECT-TYPE
	SYNTAX  INTEGER
	ACCESS  read-only
	STATUS  mandatory
	DESCRIPTION "CB12A Crest Factor"
		::= { bcmsplus1 359 }
  
bcms1-cb12b-crest-factor
	OBJECT-TYPE
	SYNTAX  INTEGER
	ACCESS  read-only
	STATUS  mandatory
	DESCRIPTION "CB12B Crest Factor"
		::= { bcmsplus1 360 }

bcms1-cb12c-crest-factor
	OBJECT-TYPE
	SYNTAX  INTEGER
	ACCESS  read-only
	STATUS  mandatory
	DESCRIPTION "CB12C Crest Factor"
		::= { bcmsplus1 361 }

bcms1-cb13a-crest-factor
	OBJECT-TYPE
	SYNTAX  INTEGER
	ACCESS  read-only
	STATUS  mandatory
	DESCRIPTION "CB13A Crest Factor"
		::= { bcmsplus1 362 }

bcms1-cb13b-crest-factor
	OBJECT-TYPE
	SYNTAX  INTEGER
	ACCESS  read-only
	STATUS  mandatory
	DESCRIPTION "CB13B Crest Factor"
		::= { bcmsplus1 363 }

bcms1-cb13c-crest-factor
	OBJECT-TYPE
	SYNTAX  INTEGER
	ACCESS  read-only
	STATUS  mandatory
	DESCRIPTION "CB13C Crest Factor"
		::= { bcmsplus1 364 }

bcms1-cb14a-crest-factor
	OBJECT-TYPE
	SYNTAX  INTEGER
	ACCESS  read-only
	STATUS  mandatory
	DESCRIPTION "CB14A Crest Factor"
		::= { bcmsplus1 365 }

bcms1-cb14b-crest-factor
	OBJECT-TYPE
	SYNTAX  INTEGER
	ACCESS  read-only
	STATUS  mandatory
	DESCRIPTION "CB14B Crest Factor"
		::= { bcmsplus1 366 }

bcms1-cb14c-crest-factor
	OBJECT-TYPE
	SYNTAX  INTEGER
	ACCESS  read-only
	STATUS  mandatory
	DESCRIPTION "CB14C Crest Factor"
		::= { bcmsplus1 367 }

bcms1-cb1a-percent-thd
	OBJECT-TYPE
	SYNTAX  INTEGER
	ACCESS  read-only
	STATUS  mandatory
	DESCRIPTION "CB1A Percent THD
		     Note: for all Percent THD 1-42: 10 = 10%"  
		::= { bcmsplus1 368 }

bcms1-cb1b-percent-thd
	OBJECT-TYPE
	SYNTAX  INTEGER
	ACCESS  read-only
	STATUS  mandatory
	DESCRIPTION "CB1B Percent THD"
		::= { bcmsplus1 369 }
  
bcms1-cb1c-percent-thd
	OBJECT-TYPE
	SYNTAX  INTEGER
	ACCESS  read-only
	STATUS  mandatory
	DESCRIPTION "CB1C Percent THD"
		::= { bcmsplus1 370 }

bcms1-cb2a-percent-thd
	OBJECT-TYPE
	SYNTAX  INTEGER
	ACCESS  read-only
	STATUS  mandatory
	DESCRIPTION "CB2A Percent THD"
		::= { bcmsplus1 371 }

bcms1-cb2b-percent-thd
	OBJECT-TYPE
	SYNTAX  INTEGER
	ACCESS  read-only
	STATUS  mandatory
	DESCRIPTION "CB2B Percent THD"
		::= { bcmsplus1 372 }

bcms1-cb2c-percent-thd
	OBJECT-TYPE
	SYNTAX  INTEGER
	ACCESS  read-only
	STATUS  mandatory
	DESCRIPTION "CB2C Percent THD"
		::= { bcmsplus1 373 }

bcms1-cb3a-percent-thd
	OBJECT-TYPE
	SYNTAX  INTEGER
	ACCESS  read-only
	STATUS  mandatory
	DESCRIPTION "CB3A Percent THD"
		::= { bcmsplus1 374 }

bcms1-cb3b-percent-thd
	OBJECT-TYPE
	SYNTAX  INTEGER
	ACCESS  read-only
	STATUS  mandatory
	DESCRIPTION "CB3B Percent THD"
		::= { bcmsplus1 375 }

bcms1-cb3c-percent-thd
	OBJECT-TYPE
	SYNTAX  INTEGER
	ACCESS  read-only
	STATUS  mandatory
	DESCRIPTION "CB3C Percent THD"
		::= { bcmsplus1 376 }

bcms1-cb4a-percent-thd
	OBJECT-TYPE
	SYNTAX  INTEGER
	ACCESS  read-only
	STATUS  mandatory
	DESCRIPTION "CB4A Percent THD"
		::= { bcmsplus1 377 }

bcms1-cb4b-percent-thd
	OBJECT-TYPE
	SYNTAX  INTEGER
	ACCESS  read-only
	STATUS  mandatory
	DESCRIPTION "CB4B Percent THD"
		::= { bcmsplus1 378 }

bcms1-cb4c-percent-thd
	OBJECT-TYPE
	SYNTAX  INTEGER
	ACCESS  read-only
	STATUS  mandatory
	DESCRIPTION "CB4C Percent THD"
		::= { bcmsplus1 379 }
  
bcms1-cb5a-percent-thd
	OBJECT-TYPE
	SYNTAX  INTEGER
	ACCESS  read-only
	STATUS  mandatory
	DESCRIPTION "CB5A Percent THD"
		::= { bcmsplus1 380 }

bcms1-cb5b-percent-thd
	OBJECT-TYPE
	SYNTAX  INTEGER
	ACCESS  read-only
	STATUS  mandatory
	DESCRIPTION "CB5B Percent THD"
		::= { bcmsplus1 381 }

bcms1-cb5c-percent-thd
	OBJECT-TYPE
	SYNTAX  INTEGER
	ACCESS  read-only
	STATUS  mandatory
	DESCRIPTION "CB5C Percent THD"
		::= { bcmsplus1 382 }

bcms1-cb6a-percent-thd
	OBJECT-TYPE
	SYNTAX  INTEGER
	ACCESS  read-only
	STATUS  mandatory
	DESCRIPTION "CB6A Percent THD"
		::= { bcmsplus1 383 }

bcms1-cb6b-percent-thd
	OBJECT-TYPE
	SYNTAX  INTEGER
	ACCESS  read-only
	STATUS  mandatory
	DESCRIPTION "CB6B Percent THD"
		::= { bcmsplus1 384 }

bcms1-cb6c-percent-thd
	OBJECT-TYPE
	SYNTAX  INTEGER
	ACCESS  read-only
	STATUS  mandatory
	DESCRIPTION "CB6C Percent THD"
		::= { bcmsplus1 385 }

bcms1-cb7a-percent-thd
	OBJECT-TYPE
	SYNTAX  INTEGER
	ACCESS  read-only
	STATUS  mandatory
	DESCRIPTION "CB7A Percent THD"
		::= { bcmsplus1 386 }

bcms1-cb7b-percent-thd
	OBJECT-TYPE
	SYNTAX  INTEGER
	ACCESS  read-only
	STATUS  mandatory
	DESCRIPTION "CB7B Percent THD"
		::= { bcmsplus1 387 }

bcms1-cb7c-percent-thd
	OBJECT-TYPE
	SYNTAX  INTEGER
	ACCESS  read-only
	STATUS  mandatory
	DESCRIPTION "CB7C Percent THD"
		::= { bcmsplus1 388 }

bcms1-cb8a-percent-thd
	OBJECT-TYPE
	SYNTAX  INTEGER
	ACCESS  read-only
	STATUS  mandatory
	DESCRIPTION "CB8A Percent THD"
		::= { bcmsplus1 389 }
  
bcms1-cb8b-percent-thd
	OBJECT-TYPE
	SYNTAX  INTEGER
	ACCESS  read-only
	STATUS  mandatory
	DESCRIPTION "CB8B Percent THD"
		::= { bcmsplus1 390 }

bcms1-cb8c-percent-thd
	OBJECT-TYPE
	SYNTAX  INTEGER
	ACCESS  read-only
	STATUS  mandatory
	DESCRIPTION "CB8C Percent THD"
		::= { bcmsplus1 391 }

bcms1-cb9a-percent-thd
	OBJECT-TYPE
	SYNTAX  INTEGER
	ACCESS  read-only
	STATUS  mandatory
	DESCRIPTION "CB9A Percent THD"
		::= { bcmsplus1 392 }

bcms1-cb9b-percent-thd
	OBJECT-TYPE
	SYNTAX  INTEGER
	ACCESS  read-only
	STATUS  mandatory
	DESCRIPTION "CB9B Percent THD"
		::= { bcmsplus1 393 }

bcms1-cb9c-percent-thd
	OBJECT-TYPE
	SYNTAX  INTEGER
	ACCESS  read-only
	STATUS  mandatory
	DESCRIPTION "CB9C Percent THD"
		::= { bcmsplus1 394 }

bcms1-cb10a-percent-thd
	OBJECT-TYPE
	SYNTAX  INTEGER
	ACCESS  read-only
	STATUS  mandatory
	DESCRIPTION "CB10A Percent THD"
		::= { bcmsplus1 395 }

bcms1-cb10b-percent-thd
	OBJECT-TYPE
	SYNTAX  INTEGER
	ACCESS  read-only
	STATUS  mandatory
	DESCRIPTION "CB10B Percent THD"
		::= { bcmsplus1 396 }

bcms1-cb10c-percent-thd
	OBJECT-TYPE
	SYNTAX  INTEGER
	ACCESS  read-only
	STATUS  mandatory
	DESCRIPTION "CB10C Percent THD"
		::= { bcmsplus1 397 }

bcms1-cb11a-percent-thd
	OBJECT-TYPE
	SYNTAX  INTEGER
	ACCESS  read-only
	STATUS  mandatory
	DESCRIPTION "CB11A Percent THD"
		::= { bcmsplus1 398 }

bcms1-cb11b-percent-thd
	OBJECT-TYPE
	SYNTAX  INTEGER
	ACCESS  read-only
	STATUS  mandatory
	DESCRIPTION "CB11B Percent THD"
		::= { bcmsplus1 399 }
  
bcms1-cb11c-percent-thd
	OBJECT-TYPE
	SYNTAX  INTEGER
	ACCESS  read-only
	STATUS  mandatory
	DESCRIPTION "CB11C Percent THD"
		::= { bcmsplus1 400 }

bcms1-cb12a-percent-thd
	OBJECT-TYPE
	SYNTAX  INTEGER
	ACCESS  read-only
	STATUS  mandatory
	DESCRIPTION "CB12A Percent THD"
		::= { bcmsplus1 401 }

bcms1-cb12b-percent-thd
	OBJECT-TYPE
	SYNTAX  INTEGER
	ACCESS  read-only
	STATUS  mandatory
	DESCRIPTION "CB12B Percent THD"
		::= { bcmsplus1 402 }

bcms1-cb12c-percent-thd
	OBJECT-TYPE
	SYNTAX  INTEGER
	ACCESS  read-only
	STATUS  mandatory
	DESCRIPTION "CB12C Percent THD"
		::= { bcmsplus1 403 }

bcms1-cb13a-percent-thd
	OBJECT-TYPE
	SYNTAX  INTEGER
	ACCESS  read-only
	STATUS  mandatory
	DESCRIPTION "CB13A Percent THD"
		::= { bcmsplus1 404 }

bcms1-cb13b-percent-thd
	OBJECT-TYPE
	SYNTAX  INTEGER
	ACCESS  read-only
	STATUS  mandatory
	DESCRIPTION "CB13B Percent THD"
		::= { bcmsplus1 405 }

bcms1-cb13c-percent-thd
	OBJECT-TYPE
	SYNTAX  INTEGER
	ACCESS  read-only
	STATUS  mandatory
	DESCRIPTION "CB13C Percent THD"
		::= { bcmsplus1 406 }

bcms1-cb14a-percent-thd
	OBJECT-TYPE
	SYNTAX  INTEGER
	ACCESS  read-only
	STATUS  mandatory
	DESCRIPTION "CB14A Percent THD"
		::= { bcmsplus1 407 }

bcms1-cb14b-percent-thd
	OBJECT-TYPE
	SYNTAX  INTEGER
	ACCESS  read-only
	STATUS  mandatory
	DESCRIPTION "CB14B Percent THD"
		::= { bcmsplus1 408 }

bcms1-cb14c-percent-thd
	OBJECT-TYPE
	SYNTAX  INTEGER
	ACCESS  read-only
	STATUS  mandatory
	DESCRIPTION "CB14C Percent THD"
		::= { bcmsplus1 409 }
bcms1-cb1a-kwh-low
	OBJECT-TYPE
	SYNTAX  INTEGER
	ACCESS  read-only
	STATUS  mandatory
	DESCRIPTION "CB1A KWH Low
		     Note: for all KWH, Low is lower 16 bits and high 
                       is upper 16 bits for a 32 bit word"  
		::= { bcmsplus1 410 }

bcms1-cb1a-kwh-high
	OBJECT-TYPE
	SYNTAX  INTEGER
	ACCESS  read-only
	STATUS  mandatory
	DESCRIPTION "CB1A KWH High"
		::= { bcmsplus1 411 }

bcms1-cb1b-kwh-low
	OBJECT-TYPE
	SYNTAX  INTEGER
	ACCESS  read-only
	STATUS  mandatory
	DESCRIPTION "CB1B KWH Low"
		::= { bcmsplus1 412 }

bcms1-cb1b-kwh-high
	OBJECT-TYPE
	SYNTAX  INTEGER
	ACCESS  read-only
	STATUS  mandatory
	DESCRIPTION "CB1B KWH High"
		::= { bcmsplus1 413 }

bcms1-cb1c-kwh-low
	OBJECT-TYPE
	SYNTAX  INTEGER
	ACCESS  read-only
	STATUS  mandatory
	DESCRIPTION "CB1C KWH Low"
		::= { bcmsplus1 414 }

bcms1-cb1c-kwh-high
	OBJECT-TYPE
	SYNTAX  INTEGER
	ACCESS  read-only
	STATUS  mandatory
	DESCRIPTION "CB1C KWH High"
		::= { bcmsplus1 415 }

bcms1-cb2a-kwh-low
	OBJECT-TYPE
	SYNTAX  INTEGER
	ACCESS  read-only
	STATUS  mandatory
	DESCRIPTION "CB2A KWH Low"
		::= { bcmsplus1 416 }
  
bcms1-cb2a-kwh-high
	OBJECT-TYPE
	SYNTAX  INTEGER
	ACCESS  read-only
	STATUS  mandatory
	DESCRIPTION "CB2A KWH High"
		::= { bcmsplus1 417 }

bcms1-cb2b-kwh-low
	OBJECT-TYPE
	SYNTAX  INTEGER
	ACCESS  read-only
	STATUS  mandatory
	DESCRIPTION "CB2B KWH Low"
		::= { bcmsplus1 418 }

bcms1-cb2b-kwh-high
	OBJECT-TYPE
	SYNTAX  INTEGER
	ACCESS  read-only
	STATUS  mandatory
	DESCRIPTION "CB2B KWH High"
		::= { bcmsplus1 419 }

bcms1-cb2c-kwh-low
	OBJECT-TYPE
	SYNTAX  INTEGER
	ACCESS  read-only
	STATUS  mandatory
	DESCRIPTION "CB2C KWH Low"
		::= { bcmsplus1 420 }

bcms1-cb2c-kwh-high
	OBJECT-TYPE
	SYNTAX  INTEGER
	ACCESS  read-only
	STATUS  mandatory
	DESCRIPTION "CB2C KWH High"
		::= { bcmsplus1 421 }

bcms1-cb3a-kwh-low
	OBJECT-TYPE
	SYNTAX  INTEGER
	ACCESS  read-only
	STATUS  mandatory
	DESCRIPTION "CB3A KWH Low"
		::= { bcmsplus1 422 }

bcms1-cb3a-kwh-high
	OBJECT-TYPE
	SYNTAX  INTEGER
	ACCESS  read-only
	STATUS  mandatory
	DESCRIPTION "CB3A KWH High"
		::= { bcmsplus1 423 }

bcms1-cb3b-kwh-low
	OBJECT-TYPE
	SYNTAX  INTEGER
	ACCESS  read-only
	STATUS  mandatory
	DESCRIPTION "CB3B KWH Low"
		::= { bcmsplus1 424 }

bcms1-cb3b-kwh-high
	OBJECT-TYPE
	SYNTAX  INTEGER
	ACCESS  read-only
	STATUS  mandatory
	DESCRIPTION "CB3B KWH High"
		::= { bcmsplus1 425 }

bcms1-cb3c-kwh-low
	OBJECT-TYPE
	SYNTAX  INTEGER
	ACCESS  read-only
	STATUS  mandatory
	DESCRIPTION "CB3C KWH Low"
		::= { bcmsplus1 426 }

bcms1-cb3c-kwh-high
	OBJECT-TYPE
	SYNTAX  INTEGER
	ACCESS  read-only
	STATUS  mandatory
	DESCRIPTION "CB3C KWH High"
		::= { bcmsplus1 427 }

bcms1-cb4a-kwh-low
	OBJECT-TYPE
	SYNTAX  INTEGER
	ACCESS  read-only
	STATUS  mandatory
	DESCRIPTION "CB4A KWH Low"
		::= { bcmsplus1 428 }

bcms1-cb4a-kwh-high
	OBJECT-TYPE
	SYNTAX  INTEGER
	ACCESS  read-only
	STATUS  mandatory
	DESCRIPTION "CB4A KWH High"
		::= { bcmsplus1 429 }

bcms1-cb4b-kwh-low
	OBJECT-TYPE
	SYNTAX  INTEGER
	ACCESS  read-only
	STATUS  mandatory
	DESCRIPTION "CB4B KWH Low"
		::= { bcmsplus1 430 }

bcms1-cb4b-kwh-high
	OBJECT-TYPE
	SYNTAX  INTEGER
	ACCESS  read-only
	STATUS  mandatory
	DESCRIPTION "CB4B KWH High"
		::= { bcmsplus1 431 }

bcms1-cb4c-kwh-low
	OBJECT-TYPE
	SYNTAX  INTEGER
	ACCESS  read-only
	STATUS  mandatory
	DESCRIPTION "CB4C KWH Low"
		::= { bcmsplus1 432 }

bcms1-cb4c-kwh-high
	OBJECT-TYPE
	SYNTAX  INTEGER
	ACCESS  read-only
	STATUS  mandatory
	DESCRIPTION "CB4C KWH High"
		::= { bcmsplus1 433 }
  
bcms1-cb5a-kwh-low
	OBJECT-TYPE
	SYNTAX  INTEGER
	ACCESS  read-only
	STATUS  mandatory
	DESCRIPTION "CB5A KWH Low"
		::= { bcmsplus1 434 }

bcms1-cb5a-kwh-high
	OBJECT-TYPE
	SYNTAX  INTEGER
	ACCESS  read-only
	STATUS  mandatory
	DESCRIPTION "CB5A KWH High"
		::= { bcmsplus1 435 }

bcms1-cb5b-kwh-low
	OBJECT-TYPE
	SYNTAX  INTEGER
	ACCESS  read-only
	STATUS  mandatory
	DESCRIPTION "CB5B KWH Low"
		::= { bcmsplus1 436 }
  
bcms1-cb5b-kwh-high
	OBJECT-TYPE
	SYNTAX  INTEGER
	ACCESS  read-only
	STATUS  mandatory
	DESCRIPTION "CB5B KWH High"
		::= { bcmsplus1 437 }

bcms1-cb5c-kwh-low
	OBJECT-TYPE
	SYNTAX  INTEGER
	ACCESS  read-only
	STATUS  mandatory
	DESCRIPTION "CB5C KWH Low"
		::= { bcmsplus1 438 }

bcms1-cb5c-kwh-high
	OBJECT-TYPE
	SYNTAX  INTEGER
	ACCESS  read-only
	STATUS  mandatory
	DESCRIPTION "CB5C KWH High"
		::= { bcmsplus1 439 }

bcms1-cb6a-kwh-low
	OBJECT-TYPE
	SYNTAX  INTEGER
	ACCESS  read-only
	STATUS  mandatory
	DESCRIPTION "CB6A KWH Low"
		::= { bcmsplus1 440 }

bcms1-cb6a-kwh-high
	OBJECT-TYPE
	SYNTAX  INTEGER
	ACCESS  read-only
	STATUS  mandatory
	DESCRIPTION "CB6A KWH High"
		::= { bcmsplus1 441 }

bcms1-cb6b-kwh-low
	OBJECT-TYPE
	SYNTAX  INTEGER
	ACCESS  read-only
	STATUS  mandatory
	DESCRIPTION "CB6B KWH Low"
		::= { bcmsplus1 442 }

bcms1-cb6b-kwh-high
	OBJECT-TYPE
	SYNTAX  INTEGER
	ACCESS  read-only
	STATUS  mandatory
	DESCRIPTION "CB6B KWH High"
		::= { bcmsplus1 443 }

bcms1-cb6c-kwh-low
	OBJECT-TYPE
	SYNTAX  INTEGER
	ACCESS  read-only
	STATUS  mandatory
	DESCRIPTION "CB6C KWH Low"
		::= { bcmsplus1 444 }

bcms1-cb6c-kwh-high
	OBJECT-TYPE
	SYNTAX  INTEGER
	ACCESS  read-only
	STATUS  mandatory
	DESCRIPTION "CB6C KWH High"
		::= { bcmsplus1 445 }

bcms1-cb7a-kwh-low
	OBJECT-TYPE
	SYNTAX  INTEGER
	ACCESS  read-only
	STATUS  mandatory
	DESCRIPTION "CB7A KWH Low"
		::= { bcmsplus1 446 }

bcms1-cb7a-kwh-high
	OBJECT-TYPE
	SYNTAX  INTEGER
	ACCESS  read-only
	STATUS  mandatory
	DESCRIPTION "CB7A KWH High"
		::= { bcmsplus1 447 }

bcms1-cb7b-kwh-low
	OBJECT-TYPE
	SYNTAX  INTEGER
	ACCESS  read-only
	STATUS  mandatory
	DESCRIPTION "CB7B KWH Low"
		::= { bcmsplus1 448 }

bcms1-cb7b-kwh-high
	OBJECT-TYPE
	SYNTAX  INTEGER
	ACCESS  read-only
	STATUS  mandatory
	DESCRIPTION "CB7B KWH High"
		::= { bcmsplus1 449 }

bcms1-cb7c-kwh-low
	OBJECT-TYPE
	SYNTAX  INTEGER
	ACCESS  read-only
	STATUS  mandatory
	DESCRIPTION "CB7C KWH Low"
		::= { bcmsplus1 450 }

bcms1-cb7c-kwh-high
	OBJECT-TYPE
	SYNTAX  INTEGER
	ACCESS  read-only
	STATUS  mandatory
	DESCRIPTION "CB7C KWH High"
		::= { bcmsplus1 451 }

bcms1-cb8a-kwh-low
	OBJECT-TYPE
	SYNTAX  INTEGER
	ACCESS  read-only
	STATUS  mandatory
	DESCRIPTION "CB8A KWH Low"
		::= { bcmsplus1 452 }

bcms1-cb8a-kwh-high
	OBJECT-TYPE
	SYNTAX  INTEGER
	ACCESS  read-only
	STATUS  mandatory
	DESCRIPTION "CB8A KWH High"
		::= { bcmsplus1 453 }
  
bcms1-cb8b-kwh-low
	OBJECT-TYPE
	SYNTAX  INTEGER
	ACCESS  read-only
	STATUS  mandatory
	DESCRIPTION "CB8B KWH Low"
		::= { bcmsplus1 454 }

bcms1-cb8b-kwh-high
	OBJECT-TYPE
	SYNTAX  INTEGER
	ACCESS  read-only
	STATUS  mandatory
	DESCRIPTION "CB8B KWH High"
		::= { bcmsplus1 455 }

bcms1-cb8c-kwh-low
	OBJECT-TYPE
	SYNTAX  INTEGER
	ACCESS  read-only
	STATUS  mandatory
	DESCRIPTION "CB8C KWH Low"
		::= { bcmsplus1 456 }
  
bcms1-cb8c-kwh-high
	OBJECT-TYPE
	SYNTAX  INTEGER
	ACCESS  read-only
	STATUS  mandatory
	DESCRIPTION "CB8C KWH High"
		::= { bcmsplus1 457 }

bcms1-cb9a-kwh-low
	OBJECT-TYPE
	SYNTAX  INTEGER
	ACCESS  read-only
	STATUS  mandatory
	DESCRIPTION "CB9A KWH Low"
		::= { bcmsplus1 458 }

bcms1-cb9a-kwh-high
	OBJECT-TYPE
	SYNTAX  INTEGER
	ACCESS  read-only
	STATUS  mandatory
	DESCRIPTION "CB9A KWH High"
		::= { bcmsplus1 459 }

bcms1-cb9b-kwh-low
	OBJECT-TYPE
	SYNTAX  INTEGER
	ACCESS  read-only
	STATUS  mandatory
	DESCRIPTION "CB9B KWH Low"
		::= { bcmsplus1 460 }

bcms1-cb9b-kwh-high
	OBJECT-TYPE
	SYNTAX  INTEGER
	ACCESS  read-only
	STATUS  mandatory
	DESCRIPTION "CB9B KWH High"
		::= { bcmsplus1 461 }

bcms1-cb9c-kwh-low
	OBJECT-TYPE
	SYNTAX  INTEGER
	ACCESS  read-only
	STATUS  mandatory
	DESCRIPTION "CB9C KWH Low"
		::= { bcmsplus1 462 }

bcms1-cb9c-kwh-high
	OBJECT-TYPE
	SYNTAX  INTEGER
	ACCESS  read-only
	STATUS  mandatory
	DESCRIPTION "CB9C KWH High"
		::= { bcmsplus1 463 }

bcms1-cb10a-kwh-low
	OBJECT-TYPE
	SYNTAX  INTEGER
	ACCESS  read-only
	STATUS  mandatory
	DESCRIPTION "CB10A KWH Low"
		::= { bcmsplus1 464 }

bcms1-cb10a-kwh-high
	OBJECT-TYPE
	SYNTAX  INTEGER
	ACCESS  read-only
	STATUS  mandatory
	DESCRIPTION "CB10A KWH High"
		::= { bcmsplus1 465 }

bcms1-cb10b-kwh-low
	OBJECT-TYPE
	SYNTAX  INTEGER
	ACCESS  read-only
	STATUS  mandatory
	DESCRIPTION "CB10B KWH Low"
		::= { bcmsplus1 466 }

bcms1-cb10b-kwh-high
	OBJECT-TYPE
	SYNTAX  INTEGER
	ACCESS  read-only
	STATUS  mandatory
	DESCRIPTION "CB10B KWH High"
		::= { bcmsplus1 467 }

bcms1-cb10c-kwh-low
	OBJECT-TYPE
	SYNTAX  INTEGER
	ACCESS  read-only
	STATUS  mandatory
	DESCRIPTION "CB10C KWH Low"
		::= { bcmsplus1 468 }

bcms1-cb10c-kwh-high
	OBJECT-TYPE
	SYNTAX  INTEGER
	ACCESS  read-only
	STATUS  mandatory
	DESCRIPTION "CB10C KWH High"
		::= { bcmsplus1 469 }

bcms1-cb11a-kwh-low
	OBJECT-TYPE
	SYNTAX  INTEGER
	ACCESS  read-only
	STATUS  mandatory
	DESCRIPTION "CB11A KWH Low"
		::= { bcmsplus1 470 }

bcms1-cb11a-kwh-high
	OBJECT-TYPE
	SYNTAX  INTEGER
	ACCESS  read-only
	STATUS  mandatory
	DESCRIPTION "CB11A KWH High"
		::= { bcmsplus1 471 }

bcms1-cb11b-kwh-low
	OBJECT-TYPE
	SYNTAX  INTEGER
	ACCESS  read-only
	STATUS  mandatory
	DESCRIPTION "CB11B KWH Low"
		::= { bcmsplus1 472 }

bcms1-cb11b-kwh-high
	OBJECT-TYPE
	SYNTAX  INTEGER
	ACCESS  read-only
	STATUS  mandatory
	DESCRIPTION "CB11B KWH High"
		::= { bcmsplus1 473 }
  
bcms1-cb11c-kwh-low
	OBJECT-TYPE
	SYNTAX  INTEGER
	ACCESS  read-only
	STATUS  mandatory
	DESCRIPTION "CB11C KWH Low"
		::= { bcmsplus1 474 }

bcms1-cb11c-kwh-high
	OBJECT-TYPE
	SYNTAX  INTEGER
	ACCESS  read-only
	STATUS  mandatory
	DESCRIPTION "CB11C KWH High"
		::= { bcmsplus1 475 }

bcms1-cb12a-kwh-low
	OBJECT-TYPE
	SYNTAX  INTEGER
	ACCESS  read-only
	STATUS  mandatory
	DESCRIPTION "CB12A KWH Low"
		::= { bcmsplus1 476 }
  
bcms1-cb12a-kwh-high
	OBJECT-TYPE
	SYNTAX  INTEGER
	ACCESS  read-only
	STATUS  mandatory
	DESCRIPTION "CB12A KWH High"
		::= { bcmsplus1 477 }

bcms1-cb12b-kwh-low
	OBJECT-TYPE
	SYNTAX  INTEGER
	ACCESS  read-only
	STATUS  mandatory
	DESCRIPTION "CB12B KWH Low"
		::= { bcmsplus1 478 }

bcms1-cb12b-kwh-high
	OBJECT-TYPE
	SYNTAX  INTEGER
	ACCESS  read-only
	STATUS  mandatory
	DESCRIPTION "CB12B KWH High"
		::= { bcmsplus1 479 }

bcms1-cb12c-kwh-low
	OBJECT-TYPE
	SYNTAX  INTEGER
	ACCESS  read-only
	STATUS  mandatory
	DESCRIPTION "CB12C KWH Low"
		::= { bcmsplus1 480 }

bcms1-cb12c-kwh-high
	OBJECT-TYPE
	SYNTAX  INTEGER
	ACCESS  read-only
	STATUS  mandatory
	DESCRIPTION "CB12C KWH High"
		::= { bcmsplus1 481 }

bcms1-cb13a-kwh-low
	OBJECT-TYPE
	SYNTAX  INTEGER
	ACCESS  read-only
	STATUS  mandatory
	DESCRIPTION "CB13A KWH Low"
		::= { bcmsplus1 482 }

bcms1-cb13a-kwh-high
	OBJECT-TYPE
	SYNTAX  INTEGER
	ACCESS  read-only
	STATUS  mandatory
	DESCRIPTION "CB13A KWH High"
		::= { bcmsplus1 483 }

bcms1-cb13b-kwh-low
	OBJECT-TYPE
	SYNTAX  INTEGER
	ACCESS  read-only
	STATUS  mandatory
	DESCRIPTION "CB13B KWH Low"
		::= { bcmsplus1 484 }

bcms1-cb13b-kwh-high
	OBJECT-TYPE
	SYNTAX  INTEGER
	ACCESS  read-only
	STATUS  mandatory
	DESCRIPTION "CB13B KWH High"
		::= { bcmsplus1 485 }

bcms1-cb13c-kwh-low
	OBJECT-TYPE
	SYNTAX  INTEGER
	ACCESS  read-only
	STATUS  mandatory
	DESCRIPTION "CB13C KWH Low"
		::= { bcmsplus1 486 }

bcms1-cb13c-kwh-high
	OBJECT-TYPE
	SYNTAX  INTEGER
	ACCESS  read-only
	STATUS  mandatory
	DESCRIPTION "CB13C KWH High"
		::= { bcmsplus1 487 }

bcms1-cb14a-kwh-low
	OBJECT-TYPE
	SYNTAX  INTEGER
	ACCESS  read-only
	STATUS  mandatory
	DESCRIPTION "CB14A KWH Low"
		::= { bcmsplus1 488 }

bcms1-cb14a-kwh-high
	OBJECT-TYPE
	SYNTAX  INTEGER
	ACCESS  read-only
	STATUS  mandatory
	DESCRIPTION "CB14A KWH High"
		::= { bcmsplus1 489 }

bcms1-cb14b-kwh-low
	OBJECT-TYPE
	SYNTAX  INTEGER
	ACCESS  read-only
	STATUS  mandatory
	DESCRIPTION "CB14B KWH Low"
		::= { bcmsplus1 490 }

bcms1-cb14b-kwh-high
	OBJECT-TYPE
	SYNTAX  INTEGER
	ACCESS  read-only
	STATUS  mandatory
	DESCRIPTION "CB14B KWH High"
		::= { bcmsplus1 491 }

bcms1-cb14c-kwh-low
	OBJECT-TYPE
	SYNTAX  INTEGER
	ACCESS  read-only
	STATUS  mandatory
	DESCRIPTION "CB14C KWH Low"
		::= { bcmsplus1 492 }

bcms1-cb14c-kwh-high
	OBJECT-TYPE
	SYNTAX  INTEGER
	ACCESS  read-only
	STATUS  mandatory
	DESCRIPTION "CB14C KWH High"
		::= { bcmsplus1 493 }

bcms1-full-load-percentage
	OBJECT-TYPE
	SYNTAX  INTEGER
	ACCESS  read-write
	STATUS  mandatory
	DESCRIPTION "Full Load Percentage
		     Note:  percentage of breaker size used for percent load 100 = 100%"
		::= { bcmsplus1 494 }

bcms1-global-breaker-size
	OBJECT-TYPE
	SYNTAX  INTEGER
	ACCESS  read-write
	STATUS  mandatory
	DESCRIPTION "Global-breaker-size
		     Note for global breaker size: 100 = 100 amps
                     Range is 20 to 600 amps"
		::= { bcmsplus1 495 }

bcms1-phase-warning-threshold
	OBJECT-TYPE
	SYNTAX  INTEGER
	ACCESS  read-write
	STATUS  mandatory
	DESCRIPTION "Phase-warning-threshold
		     Note: Phase warning threshold: 70 = 70% of breaker size
                     range is 0-100%"
		::= { bcmsplus1 496 }

bcms1-phase-alarm-threshold
	OBJECT-TYPE
	SYNTAX  INTEGER
	ACCESS  read-write
	STATUS  mandatory
	DESCRIPTION "Phase-alarm-threshold
		     Note: Phase alarm threshold: 80 = 80% of breaker size
                     range is 0-100%"
		::= { bcmsplus1 497 }

bcms1-neutral-warning-threshold
	OBJECT-TYPE
	SYNTAX  INTEGER
	ACCESS  read-write
	STATUS  mandatory
	DESCRIPTION "Neutral-warning-threshold
		     Note: Neutral warning threshold: 70 = 70% of breaker size
                     range is 0-100%"
		::= { bcmsplus1 498}

bcms1-neutral-alarm-threshold
	OBJECT-TYPE
	SYNTAX  INTEGER
	ACCESS  read-write
	STATUS  mandatory
	DESCRIPTION "Neutral-alarm-threshold
		     Note: Neutral alarm threshold: 80 = 80% of breaker size
                     range is 0-100%"
		::= { bcmsplus1 499 }

bcms1-warning-time-delay
	OBJECT-TYPE
	SYNTAX  INTEGER
	ACCESS  read-write
	STATUS  mandatory
	DESCRIPTION "warning-time-delay
		     Note: warning time delay: units are in seconds"                     
		::= { bcmsplus1 500 }

bcms1-alarm-time-delay
	OBJECT-TYPE
	SYNTAX  INTEGER
	ACCESS  read-write
	STATUS  mandatory
	DESCRIPTION "alarm-time-delay
		     Note: alarm time delay: units are in seconds"                     
		::= { bcmsplus1 501 }

bcms1-min-max-reset
	OBJECT-TYPE
	SYNTAX  INTEGER
	ACCESS  read-write
	STATUS  mandatory
	DESCRIPTION "Min-max-Reset
                     Note: Min-max Reset: writing to this register will clear minimum
		     and maximum current values"
		::= { bcmsplus1 502 }

bcms1-kwh-reset
	OBJECT-TYPE
	SYNTAX  INTEGER
	ACCESS  read-write
	STATUS  mandatory
	DESCRIPTION "Kwh-Reset
                     Note: Kwh Reset: writing to this register will clear kwh values"
		::= { bcmsplus1 503 }

bcms1-latched-summary-register
	OBJECT-TYPE
	SYNTAX  INTEGER
	ACCESS  read-write
	STATUS  mandatory
	DESCRIPTION "Latched Summary Register
			bit 0:	Warning Register 
			bit 1:	Alarm Register 
			bit 2:	Zero Current Register 
			bit 3:	Over Voltage Register 
			bit 4:	Under Voltage Register 
			bits 5 - 15: Always read as 0"
		::= { bcmsplus1 504 }

bcms1-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 - 15: Not Used"
		::= { bcmsplus1 505 }

bcms1-current-option-setting
	OBJECT-TYPE
	SYNTAX  INTEGER
	ACCESS  read-only
	STATUS  mandatory
	DESCRIPTION "Current-Option-Setting
			bit 0: CB1 is main
			bit 1: Neutral CTs
			bits 2 - 14: Not Used
			bit 15: Current Loss" 
		::= { bcmsplus1 506 }


bcms1-voltage-option-setting
	OBJECT-TYPE
	SYNTAX  INTEGER
	ACCESS  read-only
	STATUS  mandatory
	DESCRIPTION "Voltage-Option-Setting
			bit 0:	option 0
			bit 1:	option 1
			bit 2: 	option 2 
			bit 3: 	Not Used
			bit 4: 	Not Used
			bit 5: 	Set to 50Hz
			bits 6 - 15: Not Used
                     Option 0: no voltage monitoring.  (154-331 & 336-347 not used)
                     Option 1: One voltage feeding 1 or 2 panel boards. 
                     Option 2: One voltage feeding breakerset 1 and another feeding breakerset 2."
		::= { bcmsplus1 507 }

bcms1-voltage-a-b
	OBJECT-TYPE
	SYNTAX  INTEGER
	ACCESS  read-only
	STATUS  mandatory
	DESCRIPTION "Voltage-A-B
                     Note for all voltages: 1200 = 120.0 volts"
		::= { bcmsplus1 508 }

bcms1-voltage-b-c
	OBJECT-TYPE
	SYNTAX  INTEGER
	ACCESS  read-only
	STATUS  mandatory
	DESCRIPTION "Voltage-B-C"
		::= { bcmsplus1 509 }

bcms1-voltage-c-a
	OBJECT-TYPE
	SYNTAX  INTEGER
	ACCESS  read-only
	STATUS  mandatory
	DESCRIPTION "Voltage-C-A"
		::= { bcmsplus1 510 }

bcms1-voltage-a-n
	OBJECT-TYPE
	SYNTAX  INTEGER
	ACCESS  read-only
	STATUS  mandatory
	DESCRIPTION "Voltage-A-N"
		::= { bcmsplus1 511 }

bcms1-voltage-b-n
	OBJECT-TYPE
	SYNTAX  INTEGER
	ACCESS  read-only
	STATUS  mandatory
	DESCRIPTION "Voltage-B-N"
		::= { bcmsplus1 512 }

bcms1-voltage-c-n
	OBJECT-TYPE
	SYNTAX  INTEGER
	ACCESS  read-only
	STATUS  mandatory
	DESCRIPTION "Voltage-C-N"
		::= { bcmsplus1 513 }

bcms1-over-voltage-alarm-threshhold
	OBJECT-TYPE
	SYNTAX  INTEGER
	ACCESS  read-write
	STATUS  mandatory
	DESCRIPTION "Over-Voltage-Alarm-Threshhold
                     Note All Over and Under Voltage is for L-L values"
		::= { bcmsplus1 514 }

bcms1-under-voltage-alarm-threshhold
	OBJECT-TYPE
	SYNTAX  INTEGER
	ACCESS  read-write
	STATUS  mandatory
	DESCRIPTION "Under-Voltage-Alarm-Threshhold"
		::= { bcmsplus1 515 }

bcms1-voltage-frequency
	OBJECT-TYPE
	SYNTAX  INTEGER
	ACCESS  read-only
	STATUS  mandatory
	DESCRIPTION "Voltage-Frequency
                     note for frequency: 600 = 60.0Hz
                     Range is 40-70Hz
                     Note if insufficient voltage is present frequency will read 0xFFFF"
		::= { bcmsplus1 516 }

bcms1-voltage-thd-phase-a
	OBJECT-TYPE
	SYNTAX  INTEGER
	ACCESS  read-only
	STATUS  mandatory
	DESCRIPTION "Voltage-THD-Phase-A"
		::= { bcmsplus1 517 }

bcms1-voltage-thd-phase-b
	OBJECT-TYPE
	SYNTAX  INTEGER
	ACCESS  read-only
	STATUS  mandatory
	DESCRIPTION "Voltage-THD-Phase-B"
		::= { bcmsplus1 518 }

bcms1-voltage-thd-phase-c
	OBJECT-TYPE
	SYNTAX  INTEGER
	ACCESS  read-only
	STATUS  mandatory
	DESCRIPTION "Voltage-THD-Phase-C"
		::= { bcmsplus1 519 }

--------------------------------------------------------------------------------
-- BCMSPLUS register values
--------------------------------------------------------------------------------

bcms2-cb1a-current
	OBJECT-TYPE
	SYNTAX  INTEGER
	ACCESS  read-only
	STATUS  mandatory
	DESCRIPTION "CB1A Current
		     Note for all currents 1-42: 100 = 100 amps"
		::= { bcmsplus2 1 }
  
bcms2-cb1b-current
	OBJECT-TYPE
	SYNTAX  INTEGER
	ACCESS  read-only
	STATUS  mandatory
	DESCRIPTION "CB1B Current"
		::= { bcmsplus2 2 }

bcms2-cb1c-current
	OBJECT-TYPE
	SYNTAX  INTEGER
	ACCESS  read-only
	STATUS  mandatory
	DESCRIPTION "CB1C Current"
		::= { bcmsplus2 3 }

bcms2-cb2a-current
	OBJECT-TYPE
	SYNTAX  INTEGER
	ACCESS  read-only
	STATUS  mandatory
	DESCRIPTION "CB2A Current"
		::= { bcmsplus2 4 }

bcms2-cb2b-current
	OBJECT-TYPE
	SYNTAX  INTEGER
	ACCESS  read-only
	STATUS  mandatory
	DESCRIPTION "CB2B Current"
		::= { bcmsplus2 5 }

bcms2-cb2c-current
	OBJECT-TYPE
	SYNTAX  INTEGER
	ACCESS  read-only
	STATUS  mandatory
	DESCRIPTION "CB2C Current"
		::= { bcmsplus2 6 }

bcms2-cb3a-current
	OBJECT-TYPE
	SYNTAX  INTEGER
	ACCESS  read-only
	STATUS  mandatory
	DESCRIPTION "CB3A Current"
		::= { bcmsplus2 7 }

bcms2-cb3b-current
	OBJECT-TYPE
	SYNTAX  INTEGER
	ACCESS  read-only
	STATUS  mandatory
	DESCRIPTION "CB3B Current"
		::= { bcmsplus2 8 }

bcms2-cb3c-current
	OBJECT-TYPE
	SYNTAX  INTEGER
	ACCESS  read-only
	STATUS  mandatory
	DESCRIPTION "CB3C Current"
		::= { bcmsplus2 9 }

bcms2-cb4a-current
	OBJECT-TYPE
	SYNTAX  INTEGER
	ACCESS  read-only
	STATUS  mandatory
	DESCRIPTION "CB4A Current"
		::= { bcmsplus2 10 }

bcms2-cb4b-current
	OBJECT-TYPE
	SYNTAX  INTEGER
	ACCESS  read-only
	STATUS  mandatory
	DESCRIPTION "CB4B Current"
		::= { bcmsplus2 11 }
  
bcms2-cb4c-current
	OBJECT-TYPE
	SYNTAX  INTEGER
	ACCESS  read-only
	STATUS  mandatory
	DESCRIPTION "CB4C Current"
		::= { bcmsplus2 12 }

bcms2-cb5a-current
	OBJECT-TYPE
	SYNTAX  INTEGER
	ACCESS  read-only
	STATUS  mandatory
	DESCRIPTION "CB5A Current"
		::= { bcmsplus2 13 }

bcms2-cb5b-current
	OBJECT-TYPE
	SYNTAX  INTEGER
	ACCESS  read-only
	STATUS  mandatory
	DESCRIPTION "CB5B Current"
		::= { bcmsplus2 14 }

bcms2-cb5c-current
	OBJECT-TYPE
	SYNTAX  INTEGER
	ACCESS  read-only
	STATUS  mandatory
	DESCRIPTION "CB5C Current"
		::= { bcmsplus2 15 }

bcms2-cb6a-current
	OBJECT-TYPE
	SYNTAX  INTEGER
	ACCESS  read-only
	STATUS  mandatory
	DESCRIPTION "CB6A Current"
		::= { bcmsplus2 16 }

bcms2-cb6b-current
	OBJECT-TYPE
	SYNTAX  INTEGER
	ACCESS  read-only
	STATUS  mandatory
	DESCRIPTION "CB6B Current"
		::= { bcmsplus2 17 }

bcms2-cb6c-current
	OBJECT-TYPE
	SYNTAX  INTEGER
	ACCESS  read-only
	STATUS  mandatory
	DESCRIPTION "CB6C Current"
		::= { bcmsplus2 18 }

bcms2-cb7a-current
	OBJECT-TYPE
	SYNTAX  INTEGER
	ACCESS  read-only
	STATUS  mandatory
	DESCRIPTION "CB7A Current"
		::= { bcmsplus2 19 }

bcms2-cb7b-current
	OBJECT-TYPE
	SYNTAX  INTEGER
	ACCESS  read-only
	STATUS  mandatory
	DESCRIPTION "CB7B Current"
		::= { bcmsplus2 20 }

bcms2-cb7c-current
	OBJECT-TYPE
	SYNTAX  INTEGER
	ACCESS  read-only
	STATUS  mandatory
	DESCRIPTION "CB7C Current"
		::= { bcmsplus2 21 }
  
bcms2-cb8a-current
	OBJECT-TYPE
	SYNTAX  INTEGER
	ACCESS  read-only
	STATUS  mandatory
	DESCRIPTION "CB8A Current"
		::= { bcmsplus2 22 }

bcms2-cb8b-current
	OBJECT-TYPE
	SYNTAX  INTEGER
	ACCESS  read-only
	STATUS  mandatory
	DESCRIPTION "CB8B Current"
		::= { bcmsplus2 23 }

bcms2-cb8c-current
	OBJECT-TYPE
	SYNTAX  INTEGER
	ACCESS  read-only
	STATUS  mandatory
	DESCRIPTION "CB8C Current"
		::= { bcmsplus2 24 }

bcms2-cb9a-current
	OBJECT-TYPE
	SYNTAX  INTEGER
	ACCESS  read-only
	STATUS  mandatory
	DESCRIPTION "CB9A Current"
		::= { bcmsplus2 25 }

bcms2-cb9b-current
	OBJECT-TYPE
	SYNTAX  INTEGER
	ACCESS  read-only
	STATUS  mandatory
	DESCRIPTION "CB9B Current"
		::= { bcmsplus2 26 }

bcms2-cb9c-current
	OBJECT-TYPE
	SYNTAX  INTEGER
	ACCESS  read-only
	STATUS  mandatory
	DESCRIPTION "CB9C Current"
		::= { bcmsplus2 27 }

bcms2-cb10a-current
	OBJECT-TYPE
	SYNTAX  INTEGER
	ACCESS  read-only
	STATUS  mandatory
	DESCRIPTION "CB10A Current"
		::= { bcmsplus2 28 }

bcms2-cb10b-current
	OBJECT-TYPE
	SYNTAX  INTEGER
	ACCESS  read-only
	STATUS  mandatory
	DESCRIPTION "CB10B Current"
		::= { bcmsplus2 29 }

bcms2-cb10c-current
	OBJECT-TYPE
	SYNTAX  INTEGER
	ACCESS  read-only
	STATUS  mandatory
	DESCRIPTION "CB10C Current"
		::= { bcmsplus2 30 }

bcms2-cb11a-current
	OBJECT-TYPE
	SYNTAX  INTEGER
	ACCESS  read-only
	STATUS  mandatory
	DESCRIPTION "CB11A Current"
		::= { bcmsplus2 31 }
  
bcms2-cb11b-current
	OBJECT-TYPE
	SYNTAX  INTEGER
	ACCESS  read-only
	STATUS  mandatory
	DESCRIPTION "CB11B Current"
		::= { bcmsplus2 32 }

bcms2-cb11c-current
	OBJECT-TYPE
	SYNTAX  INTEGER
	ACCESS  read-only
	STATUS  mandatory
	DESCRIPTION "CB11C Current"
		::= { bcmsplus2 33 }

bcms2-cb12a-current
	OBJECT-TYPE
	SYNTAX  INTEGER
	ACCESS  read-only
	STATUS  mandatory
	DESCRIPTION "CB12A Current"
		::= { bcmsplus2 34 }

bcms2-cb12b-current
	OBJECT-TYPE
	SYNTAX  INTEGER
	ACCESS  read-only
	STATUS  mandatory
	DESCRIPTION "CB12B Current"
		::= { bcmsplus2 35 }

bcms2-cb12c-current
	OBJECT-TYPE
	SYNTAX  INTEGER
	ACCESS  read-only
	STATUS  mandatory
	DESCRIPTION "CB12C Current"
		::= { bcmsplus2 36 }

bcms2-cb13a-current
	OBJECT-TYPE
	SYNTAX  INTEGER
	ACCESS  read-only
	STATUS  mandatory
	DESCRIPTION "CB13A Current"
		::= { bcmsplus2 37 }

bcms2-cb13b-current
	OBJECT-TYPE
	SYNTAX  INTEGER
	ACCESS  read-only
	STATUS  mandatory
	DESCRIPTION "CB13B Current"
		::= { bcmsplus2 38 }

bcms2-cb13c-current
	OBJECT-TYPE
	SYNTAX  INTEGER
	ACCESS  read-only
	STATUS  mandatory
	DESCRIPTION "CB13C Current"
		::= { bcmsplus2 39 }

bcms2-cb14a-current
	OBJECT-TYPE
	SYNTAX  INTEGER
	ACCESS  read-only
	STATUS  mandatory
	DESCRIPTION "CB14A Current"
		::= { bcmsplus2 40 }

bcms2-cb14b-current
	OBJECT-TYPE
	SYNTAX  INTEGER
	ACCESS  read-only
	STATUS  mandatory
	DESCRIPTION "CB14B Current"
		::= { bcmsplus2 41 }
  
bcms2-cb14c-current
	OBJECT-TYPE
	SYNTAX  INTEGER
	ACCESS  read-only
	STATUS  mandatory
	DESCRIPTION "CB14C Current"
		::= { bcmsplus2 42 }

bcms2-cb1a-min
	OBJECT-TYPE
	SYNTAX  INTEGER
	ACCESS  read-only
	STATUS  mandatory
	DESCRIPTION "set1 CB1A Min
		     Note for all minumum currents 1-42: 100 = 100 amps"
		::= { bcmsplus2 43 }

bcms2-cb1b-min
	OBJECT-TYPE
	SYNTAX  INTEGER
	ACCESS  read-only
	STATUS  mandatory
	DESCRIPTION "set1 CB1B Min"
		::= { bcmsplus2 44 }

bcms2-cb1c-min
	OBJECT-TYPE
	SYNTAX  INTEGER
	ACCESS  read-only
	STATUS  mandatory
	DESCRIPTION "set1 CB1C Min"
		::= { bcmsplus2 45 }

bcms2-cb2a-min
	OBJECT-TYPE
	SYNTAX  INTEGER
	ACCESS  read-only
	STATUS  mandatory
	DESCRIPTION "set1A CB2AMin"
		::= { bcmsplus2 46 }

bcms2-cb2b-min
	OBJECT-TYPE
	SYNTAX  INTEGER
	ACCESS  read-only
	STATUS  mandatory
	DESCRIPTION "set1 CB2B Min"
		::= { bcmsplus2 47 }

bcms2-cb2c-min
	OBJECT-TYPE
	SYNTAX  INTEGER
	ACCESS  read-only
	STATUS  mandatory
	DESCRIPTION "set1 CB2C Min"
		::= { bcmsplus2 48 }

bcms2-cb3a-min
	OBJECT-TYPE
	SYNTAX  INTEGER
	ACCESS  read-only
	STATUS  mandatory
	DESCRIPTION "set1 CB3A Min"
		::= { bcmsplus2 49 }

bcms2-cb3b-min
	OBJECT-TYPE
	SYNTAX  INTEGER
	ACCESS  read-only
	STATUS  mandatory
	DESCRIPTION "set1 CB3B Min"
		::= { bcmsplus2 50 }

bcms2-cb3c-min
	OBJECT-TYPE
	SYNTAX  INTEGER
	ACCESS  read-only
	STATUS  mandatory
	DESCRIPTION "set1 CB3C Min"
		::= { bcmsplus2 51 }
  
bcms2-cb4a-min
	OBJECT-TYPE
	SYNTAX  INTEGER
	ACCESS  read-only
	STATUS  mandatory
	DESCRIPTION "set1 CB4A Min"
		::= { bcmsplus2 52 }

bcms2-cb4b-min
	OBJECT-TYPE
	SYNTAX  INTEGER
	ACCESS  read-only
	STATUS  mandatory
	DESCRIPTION "set1 CB4B Min"
		::= { bcmsplus2 53 }

bcms2-cb4c-min
	OBJECT-TYPE
	SYNTAX  INTEGER
	ACCESS  read-only
	STATUS  mandatory
	DESCRIPTION "set1 CB4C Min"
		::= { bcmsplus2 54 }

bcms2-cb5a-min
	OBJECT-TYPE
	SYNTAX  INTEGER
	ACCESS  read-only
	STATUS  mandatory
	DESCRIPTION "set1 CB5A Min"
		::= { bcmsplus2 55 }

bcms2-cb5b-min
	OBJECT-TYPE
	SYNTAX  INTEGER
	ACCESS  read-only
	STATUS  mandatory
	DESCRIPTION "set1 CB5B Min"
		::= { bcmsplus2 56 }

bcms2-cb5c-min
	OBJECT-TYPE
	SYNTAX  INTEGER
	ACCESS  read-only
	STATUS  mandatory
	DESCRIPTION "set1 CB5C Min"
		::= { bcmsplus2 57 }

bcms2-cb6a-min
	OBJECT-TYPE
	SYNTAX  INTEGER
	ACCESS  read-only
	STATUS  mandatory
	DESCRIPTION "set1 CB6A Min"
		::= { bcmsplus2 58 }

bcms2-cb6b-min
	OBJECT-TYPE
	SYNTAX  INTEGER
	ACCESS  read-only
	STATUS  mandatory
	DESCRIPTION "set1 CB6B Min"
		::= { bcmsplus2 59 }

bcms2-cb6c-min
	OBJECT-TYPE
	SYNTAX  INTEGER
	ACCESS  read-only
	STATUS  mandatory
	DESCRIPTION "set1 CB6C Min"
		::= { bcmsplus2 60 }

bcms2-cb7a-min
	OBJECT-TYPE
	SYNTAX  INTEGER
	ACCESS  read-only
	STATUS  mandatory
	DESCRIPTION "set1 CB7A Min"
		::= { bcmsplus2 61 }
  
bcms2-cb7b-min
	OBJECT-TYPE
	SYNTAX  INTEGER
	ACCESS  read-only
	STATUS  mandatory
	DESCRIPTION "set1 CB7B Min"
		::= { bcmsplus2 62 }

bcms2-cb7c-min
	OBJECT-TYPE
	SYNTAX  INTEGER
	ACCESS  read-only
	STATUS  mandatory
	DESCRIPTION "set1 CB7C Min"
		::= { bcmsplus2 63 }

bcms2-cb8a-min
	OBJECT-TYPE
	SYNTAX  INTEGER
	ACCESS  read-only
	STATUS  mandatory
	DESCRIPTION "set1 CB8A Min"
		::= { bcmsplus2 64 }

bcms2-cb8b-min
	OBJECT-TYPE
	SYNTAX  INTEGER
	ACCESS  read-only
	STATUS  mandatory
	DESCRIPTION "set1 CB8B Min"
		::= { bcmsplus2 65 }

bcms2-cb8c-min
	OBJECT-TYPE
	SYNTAX  INTEGER
	ACCESS  read-only
	STATUS  mandatory
	DESCRIPTION "set1 CB8C Min"
		::= { bcmsplus2 66 }

bcms2-cb9a-min
	OBJECT-TYPE
	SYNTAX  INTEGER
	ACCESS  read-only
	STATUS  mandatory
	DESCRIPTION "set1 CB9A Min"
		::= { bcmsplus2 67 }

bcms2-cb9b-min
	OBJECT-TYPE
	SYNTAX  INTEGER
	ACCESS  read-only
	STATUS  mandatory
	DESCRIPTION "set1 CB9B Min"
		::= { bcmsplus2 68 }

bcms2-cb9c-min
	OBJECT-TYPE
	SYNTAX  INTEGER
	ACCESS  read-only
	STATUS  mandatory
	DESCRIPTION "set1 CB9C Min"
		::= { bcmsplus2 69 }

bcms2-cb10a-min
	OBJECT-TYPE
	SYNTAX  INTEGER
	ACCESS  read-only
	STATUS  mandatory
	DESCRIPTION "set1 CB10A Min"
		::= { bcmsplus2 70 }

bcms2-cb10b-min
	OBJECT-TYPE
	SYNTAX  INTEGER
	ACCESS  read-only
	STATUS  mandatory
	DESCRIPTION "set1 CB10B Min"
		::= { bcmsplus2 71 }
  
bcms2-cb10c-min
	OBJECT-TYPE
	SYNTAX  INTEGER
	ACCESS  read-only
	STATUS  mandatory
	DESCRIPTION "set1 CB10C Min"
		::= { bcmsplus2 72 }

bcms2-cb11a-min
	OBJECT-TYPE
	SYNTAX  INTEGER
	ACCESS  read-only
	STATUS  mandatory
	DESCRIPTION "set1 CB11A Min"
		::= { bcmsplus2 73 }

bcms2-cb11b-min
	OBJECT-TYPE
	SYNTAX  INTEGER
	ACCESS  read-only
	STATUS  mandatory
	DESCRIPTION "set1 CB11B Min"
		::= { bcmsplus2 74 }

bcms2-cb11c-min
	OBJECT-TYPE
	SYNTAX  INTEGER
	ACCESS  read-only
	STATUS  mandatory
	DESCRIPTION "set1 CB11C Min"
		::= { bcmsplus2 75 }

bcms2-cb12a-min
	OBJECT-TYPE
	SYNTAX  INTEGER
	ACCESS  read-only
	STATUS  mandatory
	DESCRIPTION "set1 CB12A Min"
		::= { bcmsplus2 76 }

bcms2-cb12b-min
	OBJECT-TYPE
	SYNTAX  INTEGER
	ACCESS  read-only
	STATUS  mandatory
	DESCRIPTION "set1 CB12B Min"
		::= { bcmsplus2 77 }

bcms2-cb12c-min
	OBJECT-TYPE
	SYNTAX  INTEGER
	ACCESS  read-only
	STATUS  mandatory
	DESCRIPTION "set1 CB12C Min"
		::= { bcmsplus2 78 }

bcms2-cb13a-min
	OBJECT-TYPE
	SYNTAX  INTEGER
	ACCESS  read-only
	STATUS  mandatory
	DESCRIPTION "set1 CB13A Min"
		::= { bcmsplus2 79 }

bcms2-cb13b-min
	OBJECT-TYPE
	SYNTAX  INTEGER
	ACCESS  read-only
	STATUS  mandatory
	DESCRIPTION "set1 CB13B Min"
		::= { bcmsplus2 80 }

bcms2-cb13c-min
	OBJECT-TYPE
	SYNTAX  INTEGER
	ACCESS  read-only
	STATUS  mandatory
	DESCRIPTION "set1 CB13C Min"
		::= { bcmsplus2 81 }
  
bcms2-cb14a-min
	OBJECT-TYPE
	SYNTAX  INTEGER
	ACCESS  read-only
	STATUS  mandatory
	DESCRIPTION "set1 CB14A Min"
		::= { bcmsplus2 82 }

bcms2-cb14b-min
	OBJECT-TYPE
	SYNTAX  INTEGER
	ACCESS  read-only
	STATUS  mandatory
	DESCRIPTION "set1 CB14B Min"
		::= { bcmsplus2 83 }

bcms2-cb14c-min
	OBJECT-TYPE
	SYNTAX  INTEGER
	ACCESS  read-only
	STATUS  mandatory
	DESCRIPTION "set1 CB14C Min"
		::= { bcmsplus2 84 }

bcms2-cb1a-max
	OBJECT-TYPE
	SYNTAX  INTEGER
	ACCESS  read-only
	STATUS  mandatory
	DESCRIPTION "set1 CB1A Max
		     Note for all maximum currents 1-42: 100 = 100 amps"
		::= { bcmsplus2 85 }

bcms2-cb1b-max
	OBJECT-TYPE
	SYNTAX  INTEGER
	ACCESS  read-only
	STATUS  mandatory
	DESCRIPTION "set1 CB1B Max"
		::= { bcmsplus2 86 }

bcms2-cb1c-max
	OBJECT-TYPE
	SYNTAX  INTEGER
	ACCESS  read-only
	STATUS  mandatory
	DESCRIPTION "set1 CB1C Max"
		::= { bcmsplus2 87 }

bcms2-cb2a-max
	OBJECT-TYPE
	SYNTAX  INTEGER
	ACCESS  read-only
	STATUS  mandatory
	DESCRIPTION "set1 CB2A Max"
		::= { bcmsplus2 88 }

bcms2-cb2b-max
	OBJECT-TYPE
	SYNTAX  INTEGER
	ACCESS  read-only
	STATUS  mandatory
	DESCRIPTION "set1 CB2B Max"
		::= { bcmsplus2 89 }

bcms2-cb2c-max
	OBJECT-TYPE
	SYNTAX  INTEGER
	ACCESS  read-only
	STATUS  mandatory
	DESCRIPTION "set1 CB2C Max"
		::= { bcmsplus2 90 }

bcms2-cb3a-max
	OBJECT-TYPE
	SYNTAX  INTEGER
	ACCESS  read-only
	STATUS  mandatory
	DESCRIPTION "set1 CB3A Max"
		::= { bcmsplus2 91 }
  
bcms2-cb3b-max
	OBJECT-TYPE
	SYNTAX  INTEGER
	ACCESS  read-only
	STATUS  mandatory
	DESCRIPTION "set1 CB3B Max"
		::= { bcmsplus2 92 }

bcms2-cb3c-max
	OBJECT-TYPE
	SYNTAX  INTEGER
	ACCESS  read-only
	STATUS  mandatory
	DESCRIPTION "set1 CB3C Max"
		::= { bcmsplus2 93 }

bcms2-cb4a-max
	OBJECT-TYPE
	SYNTAX  INTEGER
	ACCESS  read-only
	STATUS  mandatory
	DESCRIPTION "set1 CB4A Max"
		::= { bcmsplus2 94 }

bcms2-cb4B-max
	OBJECT-TYPE
	SYNTAX  INTEGER
	ACCESS  read-only
	STATUS  mandatory
	DESCRIPTION "set1 CB4B Max"
		::= { bcmsplus2 95 }

bcms2-cb4C-max
	OBJECT-TYPE
	SYNTAX  INTEGER
	ACCESS  read-only
	STATUS  mandatory
	DESCRIPTION "set1 CB4C Max"
		::= { bcmsplus2 96 }

bcms2-cb5A-max
	OBJECT-TYPE
	SYNTAX  INTEGER
	ACCESS  read-only
	STATUS  mandatory
	DESCRIPTION "set1 CB5A Max"
		::= { bcmsplus2 97 }

bcms2-cb5B-max
	OBJECT-TYPE
	SYNTAX  INTEGER
	ACCESS  read-only
	STATUS  mandatory
	DESCRIPTION "set1 CB5B Max"
		::= { bcmsplus2 98 }

bcms2-cb5C-max
	OBJECT-TYPE
	SYNTAX  INTEGER
	ACCESS  read-only
	STATUS  mandatory
	DESCRIPTION "set1 CB5C Max"
		::= { bcmsplus2 99 }


bcms2-cb6A-max
	OBJECT-TYPE
	SYNTAX  INTEGER
	ACCESS  read-only
	STATUS  mandatory
	DESCRIPTION "set1 CB6A Max"
		::= { bcmsplus2 100 }

bcms2-cb6B-max
	OBJECT-TYPE
	SYNTAX  INTEGER
	ACCESS  read-only
	STATUS  mandatory
	DESCRIPTION "set1 CB6B Max"
		::= { bcmsplus2 101 }
  
bcms2-cb6C-max
	OBJECT-TYPE
	SYNTAX  INTEGER
	ACCESS  read-only
	STATUS  mandatory
	DESCRIPTION "set1 CB6C Max"
		::= { bcmsplus2 102 }

bcms2-cb7A-max
	OBJECT-TYPE
	SYNTAX  INTEGER
	ACCESS  read-only
	STATUS  mandatory
	DESCRIPTION "set1 CB7A Max"
		::= { bcmsplus2 103 }

bcms2-cb7B-max
	OBJECT-TYPE
	SYNTAX  INTEGER
	ACCESS  read-only
	STATUS  mandatory
	DESCRIPTION "set1 CB7B Max"
		::= { bcmsplus2 104 }

bcms2-cb7C-max
	OBJECT-TYPE
	SYNTAX  INTEGER
	ACCESS  read-only
	STATUS  mandatory
	DESCRIPTION "set1 CB7C Max"
		::= { bcmsplus2 105 }

bcms2-cb8A-max
	OBJECT-TYPE
	SYNTAX  INTEGER
	ACCESS  read-only
	STATUS  mandatory
	DESCRIPTION "set1 CB8A Max"
		::= { bcmsplus2 106 }

bcms2-cb8B-max
	OBJECT-TYPE
	SYNTAX  INTEGER
	ACCESS  read-only
	STATUS  mandatory
	DESCRIPTION "set1 CB8B Max"
		::= { bcmsplus2 107 }

bcms2-cb8C-max
	OBJECT-TYPE
	SYNTAX  INTEGER
	ACCESS  read-only
	STATUS  mandatory
	DESCRIPTION "set1 CB8C Max"
		::= { bcmsplus2 108 }

bcms2-cb9A-max
	OBJECT-TYPE
	SYNTAX  INTEGER
	ACCESS  read-only
	STATUS  mandatory
	DESCRIPTION "set1 CB9A Max"
		::= { bcmsplus2 109 }

bcms2-cb9B-max
	OBJECT-TYPE
	SYNTAX  INTEGER
	ACCESS  read-only
	STATUS  mandatory
	DESCRIPTION "set1 CB9B Max"
		::= { bcmsplus2 110 }

bcms2-cb9C-max
	OBJECT-TYPE
	SYNTAX  INTEGER
	ACCESS  read-only
	STATUS  mandatory
	DESCRIPTION "set1 CB9C Max"
		::= { bcmsplus2 111 }
  
bcms2-cb10A-max
	OBJECT-TYPE
	SYNTAX  INTEGER
	ACCESS  read-only
	STATUS  mandatory
	DESCRIPTION "set1 CB10A Max"
		::= { bcmsplus2 112 }

bcms2-cb10B-max
	OBJECT-TYPE
	SYNTAX  INTEGER
	ACCESS  read-only
	STATUS  mandatory
	DESCRIPTION "set1 CB10B Max"
		::= { bcmsplus2 113 }

bcms2-cb10C-max
	OBJECT-TYPE
	SYNTAX  INTEGER
	ACCESS  read-only
	STATUS  mandatory
	DESCRIPTION "set1 CB10C Max"
		::= { bcmsplus2 114 }

bcms2-cb11A-max
	OBJECT-TYPE
	SYNTAX  INTEGER
	ACCESS  read-only
	STATUS  mandatory
	DESCRIPTION "set1 CB11A Max"
		::= { bcmsplus2 115 }

bcms2-cb11B-max
	OBJECT-TYPE
	SYNTAX  INTEGER
	ACCESS  read-only
	STATUS  mandatory
	DESCRIPTION "set1 CB11B Max"
		::= { bcmsplus2 116 }

bcms2-cb11C-max
	OBJECT-TYPE
	SYNTAX  INTEGER
	ACCESS  read-only
	STATUS  mandatory
	DESCRIPTION "set1 CB11C Max"
		::= { bcmsplus2 117 }

bcms2-cb12A-max
	OBJECT-TYPE
	SYNTAX  INTEGER
	ACCESS  read-only
	STATUS  mandatory
	DESCRIPTION "set1 CB12A Max"
		::= { bcmsplus2 118 }

bcms2-cb12B-max
	OBJECT-TYPE
	SYNTAX  INTEGER
	ACCESS  read-only
	STATUS  mandatory
	DESCRIPTION "set1 CB12B Max"
		::= { bcmsplus2 119 }

bcms2-cb12C-max
	OBJECT-TYPE
	SYNTAX  INTEGER
	ACCESS  read-only
	STATUS  mandatory
	DESCRIPTION "set1 CB12C Max"
		::= { bcmsplus2 120 }

bcms2-cb13A-max
	OBJECT-TYPE
	SYNTAX  INTEGER
	ACCESS  read-only
	STATUS  mandatory
	DESCRIPTION "set1 CB13A Max"
		::= { bcmsplus2 121 }
  
bcms2-cb13B-max
	OBJECT-TYPE
	SYNTAX  INTEGER
	ACCESS  read-only
	STATUS  mandatory
	DESCRIPTION "set1 CB13B Max"
		::= { bcmsplus2 122 }

bcms2-cb13C-max
	OBJECT-TYPE
	SYNTAX  INTEGER
	ACCESS  read-only
	STATUS  mandatory
	DESCRIPTION "set1 CB13C Max"
		::= { bcmsplus2 123 }

bcms2-cb14A-max
	OBJECT-TYPE
	SYNTAX  INTEGER
	ACCESS  read-only
	STATUS  mandatory
	DESCRIPTION "set1 CB14A Max"
		::= { bcmsplus2 124 }

bcms2-cb14B-max
	OBJECT-TYPE
	SYNTAX  INTEGER
	ACCESS  read-only
	STATUS  mandatory
	DESCRIPTION "set1 CB14B Max"
		::= { bcmsplus2 125 }

bcms2-cb14C-max
	OBJECT-TYPE
	SYNTAX  INTEGER
	ACCESS  read-only
	STATUS  mandatory
	DESCRIPTION "set1 CB14C Max"
		::= { bcmsplus2 126 }

bcms2-Zero
	OBJECT-TYPE
	SYNTAX  INTEGER
	ACCESS  read-write
	STATUS  mandatory
	DESCRIPTION "set1 Zero
		     	 Bit 0 = CB1
                   Bit 13 = CB14"
		::= { bcmsplus2 127 }

bcms2-Warning
	OBJECT-TYPE
	SYNTAX  INTEGER
	ACCESS  read-write
	STATUS  mandatory
	DESCRIPTION "set1 Warning
		     Bit 0 = CB1
                 Bit 13 = CB14"
		::= { bcmsplus2 128 }

bcms2-Alarm
	OBJECT-TYPE
	SYNTAX  INTEGER
	ACCESS  read-write
	STATUS  mandatory
	DESCRIPTION "set1 Alarm
		       Bit 0 = CB1
                   Bit 13 = CB14"
		::= { bcmsplus2 129 }

bcms2-cb1-Breaker-Size
	OBJECT-TYPE
	SYNTAX  INTEGER
	ACCESS  read-write
	STATUS  mandatory
	DESCRIPTION "set1 CB1 Breaker-Size
		       Note for all breaker sizes 1-14: 100 = 100 amps
                   Range is 20 to 600 amps"
		::= { bcmsplus2 130 }

bcms2-cb2-Breaker-Size
	OBJECT-TYPE
	SYNTAX  INTEGER
	ACCESS  read-write
	STATUS  mandatory
	DESCRIPTION "set1 CB2 Breaker-Size"
		::= { bcmsplus2 131 }

bcms2-cb3-Breaker-Size
	OBJECT-TYPE
	SYNTAX  INTEGER
	ACCESS  read-write
	STATUS  mandatory
	DESCRIPTION "set1 CB3 Breaker-Size"
		::= { bcmsplus2 132 }

bcms2-cb4-Breaker-Size
	OBJECT-TYPE
	SYNTAX  INTEGER
	ACCESS  read-write
	STATUS  mandatory
	DESCRIPTION "set1 CB4 Breaker-Size"
		::= { bcmsplus2 133 }

bcms2-cb5-Breaker-Size
	OBJECT-TYPE
	SYNTAX  INTEGER
	ACCESS  read-write
	STATUS  mandatory
	DESCRIPTION "set1 CB5 Breaker-Size"
		::= { bcmsplus2 134 }

bcms2-cb6-Breaker-Size
	OBJECT-TYPE
	SYNTAX  INTEGER
	ACCESS  read-write
	STATUS  mandatory
	DESCRIPTION "set1 CB6 Breaker-Size"
		::= { bcmsplus2 135 }
  
bcms2-cb7-Breaker-Size
	OBJECT-TYPE
	SYNTAX  INTEGER
	ACCESS  read-write
	STATUS  mandatory
	DESCRIPTION "set1 CB7 Breaker-Size"
		::= { bcmsplus2 136 }

bcms2-cb8-Breaker-Size
	OBJECT-TYPE
	SYNTAX  INTEGER
	ACCESS  read-write
	STATUS  mandatory
	DESCRIPTION "set1 CB8 Breaker-Size"
		::= { bcmsplus2 137 }

bcms2-cb9-Breaker-Size
	OBJECT-TYPE
	SYNTAX  INTEGER
	ACCESS  read-write
	STATUS  mandatory
	DESCRIPTION "set1 CB9 Breaker-Size"
		::= { bcmsplus2 138 }

bcms2-cb10-Breaker-Size
	OBJECT-TYPE
	SYNTAX  INTEGER
	ACCESS  read-write
	STATUS  mandatory
	DESCRIPTION "set1 CB10 Breaker-Size"
		::= { bcmsplus2 139 }

bcms2-cb11-Breaker-Size
	OBJECT-TYPE
	SYNTAX  INTEGER
	ACCESS  read-write
	STATUS  mandatory
	DESCRIPTION "set1 CB11 Breaker-Size"
		::= { bcmsplus2 140 }

bcms2-cb12-Breaker-Size
	OBJECT-TYPE
	SYNTAX  INTEGER
	ACCESS  read-write
	STATUS  mandatory
	DESCRIPTION "set1 CB12 Breaker-Size"
		::= { bcmsplus2 141 }

bcms2-cb13-Breaker-Size
	OBJECT-TYPE
	SYNTAX  INTEGER
	ACCESS  read-write
	STATUS  mandatory
	DESCRIPTION "set1 CB13 Breaker-Size"
		::= { bcmsplus2 142 }

bcms2-cb14-Breaker-Size
	OBJECT-TYPE
	SYNTAX  INTEGER
	ACCESS  read-write
	STATUS  mandatory
	DESCRIPTION "set1 CB14 Breaker-Size"
		::= { bcmsplus2 143 }

bcms2-cb1a-kw
	OBJECT-TYPE
	SYNTAX  INTEGER
	ACCESS  read-write
	STATUS  mandatory
	DESCRIPTION "CB1A KW
		     Note: for all kw 1-42: 100 = 10.0KW"  
		::= { bcmsplus2 144 }

bcms2-cb1b-kw
	OBJECT-TYPE
	SYNTAX  INTEGER
	ACCESS  read-only
	STATUS  mandatory
	DESCRIPTION "CB1B KW"
		::= { bcmsplus2 145 }

bcms2-cb1c-kw
	OBJECT-TYPE
	SYNTAX  INTEGER
	ACCESS  read-only
	STATUS  mandatory
	DESCRIPTION "CB1C KW"
		::= { bcmsplus2 146 }

bcms2-cb2a-kw
	OBJECT-TYPE
	SYNTAX  INTEGER
	ACCESS  read-only
	STATUS  mandatory
	DESCRIPTION "CB2A KW"
		::= { bcmsplus2 147 }
  
bcms2-cb2b-kw
	OBJECT-TYPE
	SYNTAX  INTEGER
	ACCESS  read-only
	STATUS  mandatory
	DESCRIPTION "CB2B KW"
		::= { bcmsplus2 148 }

bcms2-cb2c-kw
	OBJECT-TYPE
	SYNTAX  INTEGER
	ACCESS  read-only
	STATUS  mandatory
	DESCRIPTION "CB2C KW"
		::= { bcmsplus2 149 }

bcms2-cb3a-kw
	OBJECT-TYPE
	SYNTAX  INTEGER
	ACCESS  read-only
	STATUS  mandatory
	DESCRIPTION "CB3A KW"
		::= { bcmsplus2 150 }

bcms2-cb3b-kw
	OBJECT-TYPE
	SYNTAX  INTEGER
	ACCESS  read-only
	STATUS  mandatory
	DESCRIPTION "CB3B KW"
		::= { bcmsplus2 151 }

bcms2-cb3c-kw
	OBJECT-TYPE
	SYNTAX  INTEGER
	ACCESS  read-only
	STATUS  mandatory
	DESCRIPTION "CB3C KW"
		::= { bcmsplus2 152 }

bcms2-cb4a-kw
	OBJECT-TYPE
	SYNTAX  INTEGER
	ACCESS  read-only
	STATUS  mandatory
	DESCRIPTION "CB4A KW"
		::= { bcmsplus2 153 }

bcms2-cb4b-kw
	OBJECT-TYPE
	SYNTAX  INTEGER
	ACCESS  read-only
	STATUS  mandatory
	DESCRIPTION "CB4B KW"
		::= { bcmsplus2 154 }

bcms2-cb4c-kw
	OBJECT-TYPE
	SYNTAX  INTEGER
	ACCESS  read-only
	STATUS  mandatory
	DESCRIPTION "CB4C KW"
		::= { bcmsplus2 155 }

bcms2-cb5a-kw
	OBJECT-TYPE
	SYNTAX  INTEGER
	ACCESS  read-only
	STATUS  mandatory
	DESCRIPTION "CB5A KW"
		::= { bcmsplus2 156 }

bcms2-cb5b-kw
	OBJECT-TYPE
	SYNTAX  INTEGER
	ACCESS  read-only
	STATUS  mandatory
	DESCRIPTION "CB5B KW"
		::= { bcmsplus2 157 }
  
bcms2-cb5c-kw
	OBJECT-TYPE
	SYNTAX  INTEGER
	ACCESS  read-only
	STATUS  mandatory
	DESCRIPTION "CB5C KW"
		::= { bcmsplus2 158 }

bcms2-cb6a-kw
	OBJECT-TYPE
	SYNTAX  INTEGER
	ACCESS  read-only
	STATUS  mandatory
	DESCRIPTION "CB6A KW"
		::= { bcmsplus2 159 }

bcms2-cb6b-kw
	OBJECT-TYPE
	SYNTAX  INTEGER
	ACCESS  read-only
	STATUS  mandatory
	DESCRIPTION "CB6B KW"
		::= { bcmsplus2 160 }

bcms2-cb6c-kw
	OBJECT-TYPE
	SYNTAX  INTEGER
	ACCESS  read-only
	STATUS  mandatory
	DESCRIPTION "CB6C KW"
		::= { bcmsplus2 161 }

bcms2-cb7a-kw
	OBJECT-TYPE
	SYNTAX  INTEGER
	ACCESS  read-only
	STATUS  mandatory
	DESCRIPTION "CB7A KW"
		::= { bcmsplus2 162 }

bcms2-cb7b-kw
	OBJECT-TYPE
	SYNTAX  INTEGER
	ACCESS  read-only
	STATUS  mandatory
	DESCRIPTION "CB7B KW"
		::= { bcmsplus2 163 }

bcms2-cb7c-kw
	OBJECT-TYPE
	SYNTAX  INTEGER
	ACCESS  read-only
	STATUS  mandatory
	DESCRIPTION "CB7C KW"
		::= { bcmsplus2 164 }

bcms2-cb8a-kw
	OBJECT-TYPE
	SYNTAX  INTEGER
	ACCESS  read-only
	STATUS  mandatory
	DESCRIPTION "CB8A KW"
		::= { bcmsplus2 165 }

bcms2-cb8b-kw
	OBJECT-TYPE
	SYNTAX  INTEGER
	ACCESS  read-only
	STATUS  mandatory
	DESCRIPTION "CB8B KW"
		::= { bcmsplus2 166 }

bcms2-cb8c-kw
	OBJECT-TYPE
	SYNTAX  INTEGER
	ACCESS  read-only
	STATUS  mandatory
	DESCRIPTION "CB8C KW"
		::= { bcmsplus2 167 }
  
bcms2-cb9a-kw
	OBJECT-TYPE
	SYNTAX  INTEGER
	ACCESS  read-only
	STATUS  mandatory
	DESCRIPTION "CB9A KW"
		::= { bcmsplus2 168 }

bcms2-cb9b-kw
	OBJECT-TYPE
	SYNTAX  INTEGER
	ACCESS  read-only
	STATUS  mandatory
	DESCRIPTION "CB9B KW"
		::= { bcmsplus2 169 }

bcms2-cb9c-kw
	OBJECT-TYPE
	SYNTAX  INTEGER
	ACCESS  read-only
	STATUS  mandatory
	DESCRIPTION "CB9C KW"
		::= { bcmsplus2 170 }

bcms2-cb10a-kw
	OBJECT-TYPE
	SYNTAX  INTEGER
	ACCESS  read-only
	STATUS  mandatory
	DESCRIPTION "CB10A KW"
		::= { bcmsplus2 171 }

bcms2-cb10b-kw
	OBJECT-TYPE
	SYNTAX  INTEGER
	ACCESS  read-only
	STATUS  mandatory
	DESCRIPTION "CB10B KW"
		::= { bcmsplus2 172 }

bcms2-cb10c-kw
	OBJECT-TYPE
	SYNTAX  INTEGER
	ACCESS  read-only
	STATUS  mandatory
	DESCRIPTION "CB10C KW"
		::= { bcmsplus2 173 }

bcms2-cb11a-kw
	OBJECT-TYPE
	SYNTAX  INTEGER
	ACCESS  read-only
	STATUS  mandatory
	DESCRIPTION "CB11A KW"
		::= { bcmsplus2 174 }

bcms2-cb11b-kw
	OBJECT-TYPE
	SYNTAX  INTEGER
	ACCESS  read-only
	STATUS  mandatory
	DESCRIPTION "CB11B KW"
		::= { bcmsplus2 175 }

bcms2-cb11c-kw
	OBJECT-TYPE
	SYNTAX  INTEGER
	ACCESS  read-only
	STATUS  mandatory
	DESCRIPTION "CB11C KW"
		::= { bcmsplus2 176 }

bcms2-cb12a-kw
	OBJECT-TYPE
	SYNTAX  INTEGER
	ACCESS  read-only
	STATUS  mandatory
	DESCRIPTION "CB12A KW"
		::= { bcmsplus2 177 }
  
bcms2-cb12b-kw
	OBJECT-TYPE
	SYNTAX  INTEGER
	ACCESS  read-only
	STATUS  mandatory
	DESCRIPTION "CB12B KW"
		::= { bcmsplus2 178 }

bcms2-cb12c-kw
	OBJECT-TYPE
	SYNTAX  INTEGER
	ACCESS  read-only
	STATUS  mandatory
	DESCRIPTION "CB12C KW"
		::= { bcmsplus2 179 }

bcms2-cb13a-kw
	OBJECT-TYPE
	SYNTAX  INTEGER
	ACCESS  read-only
	STATUS  mandatory
	DESCRIPTION "CB13A KW"
		::= { bcmsplus2 180 }

bcms2-cb13b-kw
	OBJECT-TYPE
	SYNTAX  INTEGER
	ACCESS  read-only
	STATUS  mandatory
	DESCRIPTION "CB13B KW"
		::= { bcmsplus2 181 }

bcms2-cb13c-kw
	OBJECT-TYPE
	SYNTAX  INTEGER
	ACCESS  read-only
	STATUS  mandatory
	DESCRIPTION "CB13C KW"
		::= { bcmsplus2 182 }

bcms2-cb14a-kw
	OBJECT-TYPE
	SYNTAX  INTEGER
	ACCESS  read-only
	STATUS  mandatory
	DESCRIPTION "CB14A KW"
		::= { bcmsplus2 183 }

bcms2-cb14b-kw
	OBJECT-TYPE
	SYNTAX  INTEGER
	ACCESS  read-only
	STATUS  mandatory
	DESCRIPTION "CB14B KW"
		::= { bcmsplus2 184 }

bcms2-cb14c-kw
	OBJECT-TYPE
	SYNTAX  INTEGER
	ACCESS  read-only
	STATUS  mandatory
	DESCRIPTION "CB14C KW"
		::= { bcmsplus2 185 }

bcms2-cb1a-kva
	OBJECT-TYPE
	SYNTAX  INTEGER
	ACCESS  read-only
	STATUS  mandatory
	DESCRIPTION "CB1A KVA
		     Note: for all kva 1-42: 100 = 10.0KW"  
		::= { bcmsplus2 186 }

bcms2-cb1b-kva
	OBJECT-TYPE
	SYNTAX  INTEGER
	ACCESS  read-only
	STATUS  mandatory
	DESCRIPTION "CB1B KVA"
		::= { bcmsplus2 187 }
  
bcms2-cb1c-kva
	OBJECT-TYPE
	SYNTAX  INTEGER
	ACCESS  read-only
	STATUS  mandatory
	DESCRIPTION "CB1C KVA"
		::= { bcmsplus2 188 }

bcms2-cb2a-kva
	OBJECT-TYPE
	SYNTAX  INTEGER
	ACCESS  read-only
	STATUS  mandatory
	DESCRIPTION "CB2A KVA"
		::= { bcmsplus2 189 }

bcms2-cb2b-kva
	OBJECT-TYPE
	SYNTAX  INTEGER
	ACCESS  read-only
	STATUS  mandatory
	DESCRIPTION "CB2B KVA"
		::= { bcmsplus2 190 }

bcms2-cb2c-kva
	OBJECT-TYPE
	SYNTAX  INTEGER
	ACCESS  read-only
	STATUS  mandatory
	DESCRIPTION "CB2C KVA"
		::= { bcmsplus2 191 }

bcms2-cb3a-kva
	OBJECT-TYPE
	SYNTAX  INTEGER
	ACCESS  read-only
	STATUS  mandatory
	DESCRIPTION "CB3A KVA"
		::= { bcmsplus2 192 }

bcms2-cb3b-kva
	OBJECT-TYPE
	SYNTAX  INTEGER
	ACCESS  read-only
	STATUS  mandatory
	DESCRIPTION "CB3B KVA"
		::= { bcmsplus2 193 }

bcms2-cb3c-kva
	OBJECT-TYPE
	SYNTAX  INTEGER
	ACCESS  read-only
	STATUS  mandatory
	DESCRIPTION "CB3C KVA"
		::= { bcmsplus2 194 }

bcms2-cb4a-kva
	OBJECT-TYPE
	SYNTAX  INTEGER
	ACCESS  read-only
	STATUS  mandatory
	DESCRIPTION "CB4A KVA"
		::= { bcmsplus2 195 }

bcms2-cb4b-kva
	OBJECT-TYPE
	SYNTAX  INTEGER
	ACCESS  read-only
	STATUS  mandatory
	DESCRIPTION "CB4B KVA"
		::= { bcmsplus2 196 }

bcms2-cb4c-kva
	OBJECT-TYPE
	SYNTAX  INTEGER
	ACCESS  read-only
	STATUS  mandatory
	DESCRIPTION "CB4C KVA"
		::= { bcmsplus2 197 }
  
bcms2-cb5a-kva
	OBJECT-TYPE
	SYNTAX  INTEGER
	ACCESS  read-only
	STATUS  mandatory
	DESCRIPTION "CB5A KVA"
		::= { bcmsplus2 198 }

bcms2-cb5b-kva
	OBJECT-TYPE
	SYNTAX  INTEGER
	ACCESS  read-only
	STATUS  mandatory
	DESCRIPTION "CB5B KVA"
		::= { bcmsplus2 199 }

bcms2-cb5c-kva
	OBJECT-TYPE
	SYNTAX  INTEGER
	ACCESS  read-only
	STATUS  mandatory
	DESCRIPTION "CB5C KVA"
		::= { bcmsplus2 200 }

bcms2-cb6a-kva
	OBJECT-TYPE
	SYNTAX  INTEGER
	ACCESS  read-only
	STATUS  mandatory
	DESCRIPTION "CB6A KVA"
		::= { bcmsplus2 201 }

bcms2-cb6b-kva
	OBJECT-TYPE
	SYNTAX  INTEGER
	ACCESS  read-only
	STATUS  mandatory
	DESCRIPTION "CB6B KVA"
		::= { bcmsplus2 202 }

bcms2-cb6c-kva
	OBJECT-TYPE
	SYNTAX  INTEGER
	ACCESS  read-only
	STATUS  mandatory
	DESCRIPTION "CB6C KVA"
		::= { bcmsplus2 203 }

bcms2-cb7a-kva
	OBJECT-TYPE
	SYNTAX  INTEGER
	ACCESS  read-only
	STATUS  mandatory
	DESCRIPTION "CB7A KVA"
		::= { bcmsplus2 204 }

bcms2-cb7b-kva
	OBJECT-TYPE
	SYNTAX  INTEGER
	ACCESS  read-only
	STATUS  mandatory
	DESCRIPTION "CB7B KVA"
		::= { bcmsplus2 205 }

bcms2-cb7c-kva
	OBJECT-TYPE
	SYNTAX  INTEGER
	ACCESS  read-only
	STATUS  mandatory
	DESCRIPTION "CB7C KVA"
		::= { bcmsplus2 206 }

bcms2-cb8a-kva
	OBJECT-TYPE
	SYNTAX  INTEGER
	ACCESS  read-only
	STATUS  mandatory
	DESCRIPTION "CB8A KVA"
		::= { bcmsplus2 207 }
  
bcms2-cb8b-kva
	OBJECT-TYPE
	SYNTAX  INTEGER
	ACCESS  read-only
	STATUS  mandatory
	DESCRIPTION "CB8B KVA"
		::= { bcmsplus2 208 }

bcms2-cb8c-kva
	OBJECT-TYPE
	SYNTAX  INTEGER
	ACCESS  read-only
	STATUS  mandatory
	DESCRIPTION "CB8C KVA"
		::= { bcmsplus2 209 }

bcms2-cb9a-kva
	OBJECT-TYPE
	SYNTAX  INTEGER
	ACCESS  read-only
	STATUS  mandatory
	DESCRIPTION "CB9A KVA"
		::= { bcmsplus2 210 }

bcms2-cb9b-kva
	OBJECT-TYPE
	SYNTAX  INTEGER
	ACCESS  read-only
	STATUS  mandatory
	DESCRIPTION "CB9B KVA"
		::= { bcmsplus2 211 }

bcms2-cb9c-kva
	OBJECT-TYPE
	SYNTAX  INTEGER
	ACCESS  read-only
	STATUS  mandatory
	DESCRIPTION "CB9C KVA"
		::= { bcmsplus2 212 }

bcms2-cb10a-kva
	OBJECT-TYPE
	SYNTAX  INTEGER
	ACCESS  read-only
	STATUS  mandatory
	DESCRIPTION "CB10A KVA"
		::= { bcmsplus2 213 }

bcms2-cb10b-kva
	OBJECT-TYPE
	SYNTAX  INTEGER
	ACCESS  read-only
	STATUS  mandatory
	DESCRIPTION "CB10B KVA"
		::= { bcmsplus2 214 }

bcms2-cb10c-kva
	OBJECT-TYPE
	SYNTAX  INTEGER
	ACCESS  read-only
	STATUS  mandatory
	DESCRIPTION "CB10C KVA"
		::= { bcmsplus2 215 }

bcms2-cb11a-kva
	OBJECT-TYPE
	SYNTAX  INTEGER
	ACCESS  read-only
	STATUS  mandatory
	DESCRIPTION "CB11A KVA"
		::= { bcmsplus2 216 }

bcms2-cb11b-kva
	OBJECT-TYPE
	SYNTAX  INTEGER
	ACCESS  read-only
	STATUS  mandatory
	DESCRIPTION "CB11B KVA"
		::= { bcmsplus2 217 }
  
bcms2-cb11c-kva
	OBJECT-TYPE
	SYNTAX  INTEGER
	ACCESS  read-only
	STATUS  mandatory
	DESCRIPTION "CB11C KVA"
		::= { bcmsplus2 218 }

bcms2-cb12a-kva
	OBJECT-TYPE
	SYNTAX  INTEGER
	ACCESS  read-only
	STATUS  mandatory
	DESCRIPTION "CB12A KVA"
		::= { bcmsplus2 219 }

bcms2-cb12b-kva
	OBJECT-TYPE
	SYNTAX  INTEGER
	ACCESS  read-only
	STATUS  mandatory
	DESCRIPTION "CB12B KVA"
		::= { bcmsplus2 220 }

bcms2-cb12c-kva
	OBJECT-TYPE
	SYNTAX  INTEGER
	ACCESS  read-only
	STATUS  mandatory
	DESCRIPTION "CB12C KVA"
		::= { bcmsplus2 221 }

bcms2-cb13a-kva
	OBJECT-TYPE
	SYNTAX  INTEGER
	ACCESS  read-only
	STATUS  mandatory
	DESCRIPTION "CB13A KVA"
		::= { bcmsplus2 222 }

bcms2-cb13b-kva
	OBJECT-TYPE
	SYNTAX  INTEGER
	ACCESS  read-only
	STATUS  mandatory
	DESCRIPTION "CB13B KVA"
		::= { bcmsplus2 223 }

bcms2-cb13c-kva
	OBJECT-TYPE
	SYNTAX  INTEGER
	ACCESS  read-only
	STATUS  mandatory
	DESCRIPTION "CB13C KVA"
		::= { bcmsplus2 224 }

bcms2-cb14a-kva
	OBJECT-TYPE
	SYNTAX  INTEGER
	ACCESS  read-only
	STATUS  mandatory
	DESCRIPTION "CB14A KVA"
		::= { bcmsplus2 225 }

bcms2-cb14b-kva
	OBJECT-TYPE
	SYNTAX  INTEGER
	ACCESS  read-only
	STATUS  mandatory
	DESCRIPTION "CB14B KVA"
		::= { bcmsplus2 226 }

bcms2-cb14c-kva
	OBJECT-TYPE
	SYNTAX  INTEGER
	ACCESS  read-only
	STATUS  mandatory
	DESCRIPTION "CB14C KVA"
		::= { bcmsplus2 227 }

bcms2-cb1a-kvar
	OBJECT-TYPE
	SYNTAX  INTEGER
	ACCESS  read-only
	STATUS  mandatory
	DESCRIPTION "CB1A KVAR
		     Note: for all kvar 1-42: 100 = 10.0KW"  
		::= { bcmsplus2 228 }

bcms2-cb1b-kvar
	OBJECT-TYPE
	SYNTAX  INTEGER
	ACCESS  read-only
	STATUS  mandatory
	DESCRIPTION "CB1B KVAR"
		::= { bcmsplus2 229 }
  
bcms2-cb1c-kvar
	OBJECT-TYPE
	SYNTAX  INTEGER
	ACCESS  read-only
	STATUS  mandatory
	DESCRIPTION "CB1C KVAR"
		::= { bcmsplus2 230 }

bcms2-cb2a-kvar
	OBJECT-TYPE
	SYNTAX  INTEGER
	ACCESS  read-only
	STATUS  mandatory
	DESCRIPTION "CB2A KVAR"
		::= { bcmsplus2 231 }

bcms2-cb2b-kvar
	OBJECT-TYPE
	SYNTAX  INTEGER
	ACCESS  read-only
	STATUS  mandatory
	DESCRIPTION "CB2B KVAR"
		::= { bcmsplus2 232 }

bcms2-cb2c-kvar
	OBJECT-TYPE
	SYNTAX  INTEGER
	ACCESS  read-only
	STATUS  mandatory
	DESCRIPTION "CB2C KVAR"
		::= { bcmsplus2 233 }

bcms2-cb3a-kvar
	OBJECT-TYPE
	SYNTAX  INTEGER
	ACCESS  read-only
	STATUS  mandatory
	DESCRIPTION "CB3A KVAR"
		::= { bcmsplus2 234 }

bcms2-cb3b-kvar
	OBJECT-TYPE
	SYNTAX  INTEGER
	ACCESS  read-only
	STATUS  mandatory
	DESCRIPTION "CB3B KVAR"
		::= { bcmsplus2 235 }

bcms2-cb3c-kvar
	OBJECT-TYPE
	SYNTAX  INTEGER
	ACCESS  read-only
	STATUS  mandatory
	DESCRIPTION "CB3C KVAR"
		::= { bcmsplus2 236 }

bcms2-cb4a-kvar
	OBJECT-TYPE
	SYNTAX  INTEGER
	ACCESS  read-only
	STATUS  mandatory
	DESCRIPTION "CB4A KVAR"
		::= { bcmsplus2 237 }

bcms2-cb4b-kvar
	OBJECT-TYPE
	SYNTAX  INTEGER
	ACCESS  read-only
	STATUS  mandatory
	DESCRIPTION "CB4B KVAR"
		::= { bcmsplus2 238 }

bcms2-cb4c-kvar
	OBJECT-TYPE
	SYNTAX  INTEGER
	ACCESS  read-only
	STATUS  mandatory
	DESCRIPTION "CB4C KVAR"
		::= { bcmsplus2 239 }
  
bcms2-cb5a-kvar
	OBJECT-TYPE
	SYNTAX  INTEGER
	ACCESS  read-only
	STATUS  mandatory
	DESCRIPTION "CB5A KVAR"
		::= { bcmsplus2 240 }

bcms2-cb5b-kvar
	OBJECT-TYPE
	SYNTAX  INTEGER
	ACCESS  read-only
	STATUS  mandatory
	DESCRIPTION "CB5B KVAR"
		::= { bcmsplus2 241 }

bcms2-cb5c-kvar
	OBJECT-TYPE
	SYNTAX  INTEGER
	ACCESS  read-only
	STATUS  mandatory
	DESCRIPTION "CB5C KVAR"
		::= { bcmsplus2 242 }

bcms2-cb6a-kvar
	OBJECT-TYPE
	SYNTAX  INTEGER
	ACCESS  read-only
	STATUS  mandatory
	DESCRIPTION "CB6A KVAR"
		::= { bcmsplus2 243 }

bcms2-cb6b-kvar
	OBJECT-TYPE
	SYNTAX  INTEGER
	ACCESS  read-only
	STATUS  mandatory
	DESCRIPTION "CB6B KVAR"
		::= { bcmsplus2 244 }

bcms2-cb6c-kvar
	OBJECT-TYPE
	SYNTAX  INTEGER
	ACCESS  read-only
	STATUS  mandatory
	DESCRIPTION "CB6C KVAR"
		::= { bcmsplus2 245 }

bcms2-cb7a-kvar
	OBJECT-TYPE
	SYNTAX  INTEGER
	ACCESS  read-only
	STATUS  mandatory
	DESCRIPTION "CB7A KVAR"
		::= { bcmsplus2 246 }

bcms2-cb7b-kvar
	OBJECT-TYPE
	SYNTAX  INTEGER
	ACCESS  read-only
	STATUS  mandatory
	DESCRIPTION "CB7B KVAR"
		::= { bcmsplus2 247 }

bcms2-cb7c-kvar
	OBJECT-TYPE
	SYNTAX  INTEGER
	ACCESS  read-only
	STATUS  mandatory
	DESCRIPTION "CB7C KVAR"
		::= { bcmsplus2 248 }

bcms2-cb8a-kvar
	OBJECT-TYPE
	SYNTAX  INTEGER
	ACCESS  read-only
	STATUS  mandatory
	DESCRIPTION "CB8A KVAR"
		::= { bcmsplus2 249 }
  
bcms2-cb8b-kvar
	OBJECT-TYPE
	SYNTAX  INTEGER
	ACCESS  read-only
	STATUS  mandatory
	DESCRIPTION "CB8B KVAR"
		::= { bcmsplus2 250 }

bcms2-cb8c-kvar
	OBJECT-TYPE
	SYNTAX  INTEGER
	ACCESS  read-only
	STATUS  mandatory
	DESCRIPTION "CB8C KVAR"
		::= { bcmsplus2 251 }

bcms2-cb9a-kvar
	OBJECT-TYPE
	SYNTAX  INTEGER
	ACCESS  read-only
	STATUS  mandatory
	DESCRIPTION "CB9A KVAR"
		::= { bcmsplus2 252 }

bcms2-cb9b-kvar
	OBJECT-TYPE
	SYNTAX  INTEGER
	ACCESS  read-only
	STATUS  mandatory
	DESCRIPTION "CB9B KVAR"
		::= { bcmsplus2 253 }

bcms2-cb9c-kvar
	OBJECT-TYPE
	SYNTAX  INTEGER
	ACCESS  read-only
	STATUS  mandatory
	DESCRIPTION "CB9C KVAR"
		::= { bcmsplus2 254 }

bcms2-cb10a-kvar
	OBJECT-TYPE
	SYNTAX  INTEGER
	ACCESS  read-only
	STATUS  mandatory
	DESCRIPTION "CB10A KVAR"
		::= { bcmsplus2 255 }

bcms2-cb10b-kvar
	OBJECT-TYPE
	SYNTAX  INTEGER
	ACCESS  read-only
	STATUS  mandatory
	DESCRIPTION "CB10B KVAR"
		::= { bcmsplus2 256}

bcms2-cb10c-kvar
	OBJECT-TYPE
	SYNTAX  INTEGER
	ACCESS  read-only
	STATUS  mandatory
	DESCRIPTION "CB10C KVAR"
		::= { bcmsplus2 257 }

bcms2-cb11a-kvar
	OBJECT-TYPE
	SYNTAX  INTEGER
	ACCESS  read-only
	STATUS  mandatory
	DESCRIPTION "CB11A KVAR"
		::= { bcmsplus2 258 }

bcms2-cb11b-kvar
	OBJECT-TYPE
	SYNTAX  INTEGER
	ACCESS  read-only
	STATUS  mandatory
	DESCRIPTION "CB11B KVAR"
		::= { bcmsplus2 259 }
  
bcms2-cb11c-kvar
	OBJECT-TYPE
	SYNTAX  INTEGER
	ACCESS  read-only
	STATUS  mandatory
	DESCRIPTION "CB11C KVAR"
		::= { bcmsplus2 260 }

bcms2-cb12a-kvar
	OBJECT-TYPE
	SYNTAX  INTEGER
	ACCESS  read-only
	STATUS  mandatory
	DESCRIPTION "CB12A KVAR"
		::= { bcmsplus2 261 }

bcms2-cb12b-kvar
	OBJECT-TYPE
	SYNTAX  INTEGER
	ACCESS  read-only
	STATUS  mandatory
	DESCRIPTION "CB12B KVAR"
		::= { bcmsplus2 262 }

bcms2-cb12c-kvar
	OBJECT-TYPE
	SYNTAX  INTEGER
	ACCESS  read-only
	STATUS  mandatory
	DESCRIPTION "CB12C KVAR"
		::= { bcmsplus2 263 }

bcms2-cb13a-kvar
	OBJECT-TYPE
	SYNTAX  INTEGER
	ACCESS  read-only
	STATUS  mandatory
	DESCRIPTION "CB13A KVAR"
		::= { bcmsplus2 264 }

bcms2-cb13b-kvar
	OBJECT-TYPE
	SYNTAX  INTEGER
	ACCESS  read-only
	STATUS  mandatory
	DESCRIPTION "CB13B KVAR"
		::= { bcmsplus2 265 }

bcms2-cb13c-kvar
	OBJECT-TYPE
	SYNTAX  INTEGER
	ACCESS  read-only
	STATUS  mandatory
	DESCRIPTION "CB13C KVAR"
		::= { bcmsplus2 266 }

bcms2-cb14a-kvar
	OBJECT-TYPE
	SYNTAX  INTEGER
	ACCESS  read-only
	STATUS  mandatory
	DESCRIPTION "CB14A KVAR"
		::= { bcmsplus2 267 }

bcms2-cb14b-kvar
	OBJECT-TYPE
	SYNTAX  INTEGER
	ACCESS  read-only
	STATUS  mandatory
	DESCRIPTION "CB14B KVAR"
		::= { bcmsplus2 268 }

bcms2-cb14c-kvar
	OBJECT-TYPE
	SYNTAX  INTEGER
	ACCESS  read-only
	STATUS  mandatory
	DESCRIPTION "CB14C KVAR"
		::= { bcmsplus2 269 }

bcms2-cb1a-pf
	OBJECT-TYPE
	SYNTAX  INTEGER
	ACCESS  read-only
	STATUS  mandatory
	DESCRIPTION "CB1A PF
		     Note: for all pf 1-42: 100 = 100%"  
		::= { bcmsplus2 270 }

bcms2-cb1b-pf
	OBJECT-TYPE
	SYNTAX  INTEGER
	ACCESS  read-only
	STATUS  mandatory
	DESCRIPTION "CB1B PF"
		::= { bcmsplus2 271 }
  
bcms2-cb1c-pf
	OBJECT-TYPE
	SYNTAX  INTEGER
	ACCESS  read-only
	STATUS  mandatory
	DESCRIPTION "CB1C PF"
		::= { bcmsplus2 272 }

bcms2-cb2a-pf
	OBJECT-TYPE
	SYNTAX  INTEGER
	ACCESS  read-only
	STATUS  mandatory
	DESCRIPTION "CB2A PF"
		::= { bcmsplus2 273 }

bcms2-cb2b-pf
	OBJECT-TYPE
	SYNTAX  INTEGER
	ACCESS  read-only
	STATUS  mandatory
	DESCRIPTION "CB2B PF"
		::= { bcmsplus2 274 }

bcms2-cb2c-pf
	OBJECT-TYPE
	SYNTAX  INTEGER
	ACCESS  read-only
	STATUS  mandatory
	DESCRIPTION "CB2C PF"
		::= { bcmsplus2 275 }

bcms2-cb3a-pf
	OBJECT-TYPE
	SYNTAX  INTEGER
	ACCESS  read-only
	STATUS  mandatory
	DESCRIPTION "CB3A PF"
		::= { bcmsplus2 276 }

bcms2-cb3b-pf
	OBJECT-TYPE
	SYNTAX  INTEGER
	ACCESS  read-only
	STATUS  mandatory
	DESCRIPTION "CB3B PF"
		::= { bcmsplus2 277 }

bcms2-cb3c-pf
	OBJECT-TYPE
	SYNTAX  INTEGER
	ACCESS  read-only
	STATUS  mandatory
	DESCRIPTION "CB3C PF"
		::= { bcmsplus2 278 }

bcms2-cb4a-pf
	OBJECT-TYPE
	SYNTAX  INTEGER
	ACCESS  read-only
	STATUS  mandatory
	DESCRIPTION "CB4A PF"
		::= { bcmsplus2 279 }

bcms2-cb4b-pf
	OBJECT-TYPE
	SYNTAX  INTEGER
	ACCESS  read-only
	STATUS  mandatory
	DESCRIPTION "CB4B PF"
		::= { bcmsplus2 280 }

bcms2-cb4c-pf
	OBJECT-TYPE
	SYNTAX  INTEGER
	ACCESS  read-only
	STATUS  mandatory
	DESCRIPTION "CB4C PF"
		::= { bcmsplus2 281 }
  
bcms2-cb5a-pf
	OBJECT-TYPE
	SYNTAX  INTEGER
	ACCESS  read-only
	STATUS  mandatory
	DESCRIPTION "CB5A PF"
		::= { bcmsplus2 282 }

bcms2-cb5b-pf
	OBJECT-TYPE
	SYNTAX  INTEGER
	ACCESS  read-only
	STATUS  mandatory
	DESCRIPTION "CB5B PF"
		::= { bcmsplus2 283 }

bcms2-cb5c-pf
	OBJECT-TYPE
	SYNTAX  INTEGER
	ACCESS  read-only
	STATUS  mandatory
	DESCRIPTION "CB5C PF"
		::= { bcmsplus2 284 }

bcms2-cb6a-pf
	OBJECT-TYPE
	SYNTAX  INTEGER
	ACCESS  read-only
	STATUS  mandatory
	DESCRIPTION "CB6A PF"
		::= { bcmsplus2 285 }

bcms2-cb6b-pf
	OBJECT-TYPE
	SYNTAX  INTEGER
	ACCESS  read-only
	STATUS  mandatory
	DESCRIPTION "CB6B PF"
		::= { bcmsplus2 286 }

bcms2-cb6c-pf
	OBJECT-TYPE
	SYNTAX  INTEGER
	ACCESS  read-only
	STATUS  mandatory
	DESCRIPTION "CB6C PF"
		::= { bcmsplus2 287 }

bcms2-cb7a-pf
	OBJECT-TYPE
	SYNTAX  INTEGER
	ACCESS  read-only
	STATUS  mandatory
	DESCRIPTION "CB7A PF"
		::= { bcmsplus2 288 }

bcms2-cb7b-pf
	OBJECT-TYPE
	SYNTAX  INTEGER
	ACCESS  read-only
	STATUS  mandatory
	DESCRIPTION "CB7B PF"
		::= { bcmsplus2 289 }

bcms2-cb7c-pf
	OBJECT-TYPE
	SYNTAX  INTEGER
	ACCESS  read-only
	STATUS  mandatory
	DESCRIPTION "CB7C PF"
		::= { bcmsplus2 290 }

bcms2-cb8a-pf
	OBJECT-TYPE
	SYNTAX  INTEGER
	ACCESS  read-only
	STATUS  mandatory
	DESCRIPTION "CB8A PF"
		::= { bcmsplus2 291 }
  
bcms2-cb8b-pf
	OBJECT-TYPE
	SYNTAX  INTEGER
	ACCESS  read-only
	STATUS  mandatory
	DESCRIPTION "CB8B PF"
		::= { bcmsplus2 292 }

bcms2-cb8c-pf
	OBJECT-TYPE
	SYNTAX  INTEGER
	ACCESS  read-only
	STATUS  mandatory
	DESCRIPTION "CB8C PF"
		::= { bcmsplus2 293 }

bcms2-cb9a-pf
	OBJECT-TYPE
	SYNTAX  INTEGER
	ACCESS  read-only
	STATUS  mandatory
	DESCRIPTION "CB9A PF"
		::= { bcmsplus2 294 }

bcms2-cb9b-pf
	OBJECT-TYPE
	SYNTAX  INTEGER
	ACCESS  read-only
	STATUS  mandatory
	DESCRIPTION "CB9B PF"
		::= { bcmsplus2 295 }

bcms2-cb9c-pf
	OBJECT-TYPE
	SYNTAX  INTEGER
	ACCESS  read-only
	STATUS  mandatory
	DESCRIPTION "CB9C PF"
		::= { bcmsplus2 296 }

bcms2-cb10a-pf
	OBJECT-TYPE
	SYNTAX  INTEGER
	ACCESS  read-only
	STATUS  mandatory
	DESCRIPTION "CB10A PF"
		::= { bcmsplus2 297 }

bcms2-cb10b-pf
	OBJECT-TYPE
	SYNTAX  INTEGER
	ACCESS  read-only
	STATUS  mandatory
	DESCRIPTION "CB10B PF"
		::= { bcmsplus2 298 }

bcms2-cb10c-pf
	OBJECT-TYPE
	SYNTAX  INTEGER
	ACCESS  read-only
	STATUS  mandatory
	DESCRIPTION "CB10C PF"
		::= { bcmsplus2 299 }

bcms2-cb11a-pf
	OBJECT-TYPE
	SYNTAX  INTEGER
	ACCESS  read-only
	STATUS  mandatory
	DESCRIPTION "CB11A PF"
		::= { bcmsplus2 300 }

bcms2-cb11b-pf
	OBJECT-TYPE
	SYNTAX  INTEGER
	ACCESS  read-only
	STATUS  mandatory
	DESCRIPTION "CB11B PF"
		::= { bcmsplus2 301 }
  
bcms2-cb11c-pf
	OBJECT-TYPE
	SYNTAX  INTEGER
	ACCESS  read-only
	STATUS  mandatory
	DESCRIPTION "CB11C PF"
		::= { bcmsplus2 302 }

bcms2-cb12a-pf
	OBJECT-TYPE
	SYNTAX  INTEGER
	ACCESS  read-only
	STATUS  mandatory
	DESCRIPTION "CB12A PF"
		::= { bcmsplus2 303 }

bcms2-cb12b-pf
	OBJECT-TYPE
	SYNTAX  INTEGER
	ACCESS  read-only
	STATUS  mandatory
	DESCRIPTION "CB12B PF"
		::= { bcmsplus2 304 }

bcms2-cb12c-pf
	OBJECT-TYPE
	SYNTAX  INTEGER
	ACCESS  read-only
	STATUS  mandatory
	DESCRIPTION "CB12C PF"
		::= { bcmsplus2 305 }

bcms2-cb13a-pf
	OBJECT-TYPE
	SYNTAX  INTEGER
	ACCESS  read-only
	STATUS  mandatory
	DESCRIPTION "CB13A PF"
		::= { bcmsplus2 306 }

bcms2-cb13b-pf
	OBJECT-TYPE
	SYNTAX  INTEGER
	ACCESS  read-only
	STATUS  mandatory
	DESCRIPTION "CB13B PF"
		::= { bcmsplus2 307 }

bcms2-cb13c-pf
	OBJECT-TYPE
	SYNTAX  INTEGER
	ACCESS  read-only
	STATUS  mandatory
	DESCRIPTION "CB13C PF"
		::= { bcmsplus2 308 }

bcms2-cb14a-pf
	OBJECT-TYPE
	SYNTAX  INTEGER
	ACCESS  read-only
	STATUS  mandatory
	DESCRIPTION "CB14A PF"
		::= { bcmsplus2 309 }

bcms2-cb14b-pf
	OBJECT-TYPE
	SYNTAX  INTEGER
	ACCESS  read-only
	STATUS  mandatory
	DESCRIPTION "CB14B PF"
		::= { bcmsplus2 310 }

bcms2-cb14c-pf
	OBJECT-TYPE
	SYNTAX  INTEGER
	ACCESS  read-only
	STATUS  mandatory
	DESCRIPTION "CB14C PF"
		::= { bcmsplus2 311 }

bcms2-cb1-percent-load
	OBJECT-TYPE
	SYNTAX  INTEGER
	ACCESS  read-only
	STATUS  mandatory
	DESCRIPTION "set1 CB1 Percent Load
		       Note for all breaker sizes 1-14: 100 = 100 amps
                   Range is 20 to 600 amps"
		::= { bcmsplus2 312 }

bcms2-cb2-percent-load
	OBJECT-TYPE
	SYNTAX  INTEGER
	ACCESS  read-only
	STATUS  mandatory
	DESCRIPTION "set1 CB2 Percent Load"
		::= { bcmsplus2 313 }

bcms2-cb3-percent-load
	OBJECT-TYPE
	SYNTAX  INTEGER
	ACCESS  read-only
	STATUS  mandatory
	DESCRIPTION "set1 CB3 Percent Load"
		::= { bcmsplus2 314 }

bcms2-cb4-percent-load
	OBJECT-TYPE
	SYNTAX  INTEGER
	ACCESS  read-only
	STATUS  mandatory
	DESCRIPTION "set1 CB4 Percent Load"
		::= { bcmsplus2 315 }

bcms2-cb5-percent-load
	OBJECT-TYPE
	SYNTAX  INTEGER
	ACCESS  read-only
	STATUS  mandatory
	DESCRIPTION "set1 CB5 Percent Load"
		::= { bcmsplus2 316 }

bcms2-cb6-percent-load
	OBJECT-TYPE
	SYNTAX  INTEGER
	ACCESS  read-only
	STATUS  mandatory
	DESCRIPTION "set1 CB6 Percent Load"
		::= { bcmsplus2 317 }
  
bcms2-cb7-percent-load
	OBJECT-TYPE
	SYNTAX  INTEGER
	ACCESS  read-only
	STATUS  mandatory
	DESCRIPTION "set1 CB7 Percent Load"
		::= { bcmsplus2 318 }

bcms2-cb8-percent-load
	OBJECT-TYPE
	SYNTAX  INTEGER
	ACCESS  read-only
	STATUS  mandatory
	DESCRIPTION "set1 CB8 Percent Load"
		::= { bcmsplus2 319 }

bcms2-cb9-percent-load
	OBJECT-TYPE
	SYNTAX  INTEGER
	ACCESS  read-only
	STATUS  mandatory
	DESCRIPTION "set1 CB9 Percent Load"
		::= { bcmsplus2 320 }

bcms2-cb10-percent-load
	OBJECT-TYPE
	SYNTAX  INTEGER
	ACCESS  read-only
	STATUS  mandatory
	DESCRIPTION "set1 CB10 Percent Load"
		::= { bcmsplus2 321 }

bcms2-cb11-percent-load
	OBJECT-TYPE
	SYNTAX  INTEGER
	ACCESS  read-only
	STATUS  mandatory
	DESCRIPTION "set1 CB11 Percent Load"
		::= { bcmsplus2 322 }

bcms2-cb12-percent-load
	OBJECT-TYPE
	SYNTAX  INTEGER
	ACCESS  read-only
	STATUS  mandatory
	DESCRIPTION "set1 CB12 Percent Load"
		::= { bcmsplus2 323 }

bcms2-cb13-percent-load
	OBJECT-TYPE
	SYNTAX  INTEGER
	ACCESS  read-only
	STATUS  mandatory
	DESCRIPTION "set1 CB13 Percent Load"
		::= { bcmsplus2 324 }

bcms2-cb14-percent-load
	OBJECT-TYPE
	SYNTAX  INTEGER
	ACCESS  read-only
	STATUS  mandatory
	DESCRIPTION "set1 CB14 Percent Load"
		::= { bcmsplus2 325 }

bcms2-cb1a-crest-factor
	OBJECT-TYPE
	SYNTAX  INTEGER
	ACCESS  read-write
	STATUS  mandatory
	DESCRIPTION "CB1A Crest Factor
		     Note: for all Crest Factor 1-42: 141 = 1.41"  
		::= { bcmsplus2 326 }

bcms2-cb1b-crest-factor
	OBJECT-TYPE
	SYNTAX  INTEGER
	ACCESS  read-only
	STATUS  mandatory
	DESCRIPTION "CB1B Crest Factor"
		::= { bcmsplus2 327 }

bcms2-cb1c-crest-factor
	OBJECT-TYPE
	SYNTAX  INTEGER
	ACCESS  read-only
	STATUS  mandatory
	DESCRIPTION "CB1C Crest Factor"
		::= { bcmsplus2 328 }

bcms2-cb2a-crest-factor
	OBJECT-TYPE
	SYNTAX  INTEGER
	ACCESS  read-only
	STATUS  mandatory
	DESCRIPTION "CB2A Crest Factor"
		::= { bcmsplus2 329 }
  
bcms2-cb2b-crest-factor
	OBJECT-TYPE
	SYNTAX  INTEGER
	ACCESS  read-only
	STATUS  mandatory
	DESCRIPTION "CB2B Crest Factor"
		::= { bcmsplus2 330 }

bcms2-cb2c-crest-factor
	OBJECT-TYPE
	SYNTAX  INTEGER
	ACCESS  read-only
	STATUS  mandatory
	DESCRIPTION "CB2C Crest Factor"
		::= { bcmsplus2 331 }

bcms2-cb3a-crest-factor
	OBJECT-TYPE
	SYNTAX  INTEGER
	ACCESS  read-only
	STATUS  mandatory
	DESCRIPTION "CB3A Crest Factor"
		::= { bcmsplus2 332 }

bcms2-cb3b-crest-factor
	OBJECT-TYPE
	SYNTAX  INTEGER
	ACCESS  read-only
	STATUS  mandatory
	DESCRIPTION "CB3B Crest Factor"
		::= { bcmsplus2 333 }

bcms2-cb3c-crest-factor
	OBJECT-TYPE
	SYNTAX  INTEGER
	ACCESS  read-only
	STATUS  mandatory
	DESCRIPTION "CB3C Crest Factor"
		::= { bcmsplus2 334 }

bcms2-cb4a-crest-factor
	OBJECT-TYPE
	SYNTAX  INTEGER
	ACCESS  read-only
	STATUS  mandatory
	DESCRIPTION "CB4A Crest Factor"
		::= { bcmsplus2 335 }

bcms2-cb4b-crest-factor
	OBJECT-TYPE
	SYNTAX  INTEGER
	ACCESS  read-only
	STATUS  mandatory
	DESCRIPTION "CB4B Crest Factor"
		::= { bcmsplus2 336 }

bcms2-cb4c-crest-factor
	OBJECT-TYPE
	SYNTAX  INTEGER
	ACCESS  read-only
	STATUS  mandatory
	DESCRIPTION "CB4C Crest Factor"
		::= { bcmsplus2 337 }

bcms2-cb5a-crest-factor
	OBJECT-TYPE
	SYNTAX  INTEGER
	ACCESS  read-only
	STATUS  mandatory
	DESCRIPTION "CB5A Crest Factor"
		::= { bcmsplus2 338 }

bcms2-cb5b-crest-factor
	OBJECT-TYPE
	SYNTAX  INTEGER
	ACCESS  read-only
	STATUS  mandatory
	DESCRIPTION "CB5B Crest Factor"
		::= { bcmsplus2 339 }
  
bcms2-cb5c-crest-factor
	OBJECT-TYPE
	SYNTAX  INTEGER
	ACCESS  read-only
	STATUS  mandatory
	DESCRIPTION "CB5C Crest Factor"
		::= { bcmsplus2 340 }

bcms2-cb6a-crest-factor
	OBJECT-TYPE
	SYNTAX  INTEGER
	ACCESS  read-only
	STATUS  mandatory
	DESCRIPTION "CB6A Crest Factor"
		::= { bcmsplus2 341 }

bcms2-cb6b-crest-factor
	OBJECT-TYPE
	SYNTAX  INTEGER
	ACCESS  read-only
	STATUS  mandatory
	DESCRIPTION "CB6B Crest Factor"
		::= { bcmsplus2 342 }

bcms2-cb6c-crest-factor
	OBJECT-TYPE
	SYNTAX  INTEGER
	ACCESS  read-only
	STATUS  mandatory
	DESCRIPTION "CB6C Crest Factor"
		::= { bcmsplus2 343 }

bcms2-cb7a-crest-factor
	OBJECT-TYPE
	SYNTAX  INTEGER
	ACCESS  read-only
	STATUS  mandatory
	DESCRIPTION "CB7A Crest Factor"
		::= { bcmsplus2 344 }

bcms2-cb7b-crest-factor
	OBJECT-TYPE
	SYNTAX  INTEGER
	ACCESS  read-only
	STATUS  mandatory
	DESCRIPTION "CB7B Crest Factor"
		::= { bcmsplus2 345 }

bcms2-cb7c-crest-factor
	OBJECT-TYPE
	SYNTAX  INTEGER
	ACCESS  read-only
	STATUS  mandatory
	DESCRIPTION "CB7C Crest Factor"
		::= { bcmsplus2 346 }

bcms2-cb8a-crest-factor
	OBJECT-TYPE
	SYNTAX  INTEGER
	ACCESS  read-only
	STATUS  mandatory
	DESCRIPTION "CB8A Crest Factor"
		::= { bcmsplus2 347 }

bcms2-cb8b-crest-factor
	OBJECT-TYPE
	SYNTAX  INTEGER
	ACCESS  read-only
	STATUS  mandatory
	DESCRIPTION "CB8B Crest Factor"
		::= { bcmsplus2 348 }

bcms2-cb8c-crest-factor
	OBJECT-TYPE
	SYNTAX  INTEGER
	ACCESS  read-only
	STATUS  mandatory
	DESCRIPTION "CB8C Crest Factor"
		::= { bcmsplus2 349 }
  
bcms2-cb9a-crest-factor
	OBJECT-TYPE
	SYNTAX  INTEGER
	ACCESS  read-only
	STATUS  mandatory
	DESCRIPTION "CB9A Crest Factor"
		::= { bcmsplus2 350 }

bcms2-cb9b-crest-factor
	OBJECT-TYPE
	SYNTAX  INTEGER
	ACCESS  read-only
	STATUS  mandatory
	DESCRIPTION "CB9B Crest Factor"
		::= { bcmsplus2 351 }

bcms2-cb9c-crest-factor
	OBJECT-TYPE
	SYNTAX  INTEGER
	ACCESS  read-only
	STATUS  mandatory
	DESCRIPTION "CB9C Crest Factor"
		::= { bcmsplus2 352 }

bcms2-cb10a-crest-factor
	OBJECT-TYPE
	SYNTAX  INTEGER
	ACCESS  read-only
	STATUS  mandatory
	DESCRIPTION "CB10A Crest Factor"
		::= { bcmsplus2 353 }

bcms2-cb10b-crest-factor
	OBJECT-TYPE
	SYNTAX  INTEGER
	ACCESS  read-only
	STATUS  mandatory
	DESCRIPTION "CB10B Crest Factor"
		::= { bcmsplus2 354 }

bcms2-cb10c-crest-factor
	OBJECT-TYPE
	SYNTAX  INTEGER
	ACCESS  read-only
	STATUS  mandatory
	DESCRIPTION "CB10C Crest Factor"
		::= { bcmsplus2 355 }

bcms2-cb11a-crest-factor
	OBJECT-TYPE
	SYNTAX  INTEGER
	ACCESS  read-only
	STATUS  mandatory
	DESCRIPTION "CB11A Crest Factor"
		::= { bcmsplus2 356 }

bcms2-cb11b-crest-factor
	OBJECT-TYPE
	SYNTAX  INTEGER
	ACCESS  read-only
	STATUS  mandatory
	DESCRIPTION "CB11B Crest Factor"
		::= { bcmsplus2 357 }

bcms2-cb11c-crest-factor
	OBJECT-TYPE
	SYNTAX  INTEGER
	ACCESS  read-only
	STATUS  mandatory
	DESCRIPTION "CB11C Crest Factor"
		::= { bcmsplus2 358 }

bcms2-cb12a-crest-factor
	OBJECT-TYPE
	SYNTAX  INTEGER
	ACCESS  read-only
	STATUS  mandatory
	DESCRIPTION "CB12A Crest Factor"
		::= { bcmsplus2 359 }
  
bcms2-cb12b-crest-factor
	OBJECT-TYPE
	SYNTAX  INTEGER
	ACCESS  read-only
	STATUS  mandatory
	DESCRIPTION "CB12B Crest Factor"
		::= { bcmsplus2 360 }

bcms2-cb12c-crest-factor
	OBJECT-TYPE
	SYNTAX  INTEGER
	ACCESS  read-only
	STATUS  mandatory
	DESCRIPTION "CB12C Crest Factor"
		::= { bcmsplus2 361 }

bcms2-cb13a-crest-factor
	OBJECT-TYPE
	SYNTAX  INTEGER
	ACCESS  read-only
	STATUS  mandatory
	DESCRIPTION "CB13A Crest Factor"
		::= { bcmsplus2 362 }

bcms2-cb13b-crest-factor
	OBJECT-TYPE
	SYNTAX  INTEGER
	ACCESS  read-only
	STATUS  mandatory
	DESCRIPTION "CB13B Crest Factor"
		::= { bcmsplus2 363 }

bcms2-cb13c-crest-factor
	OBJECT-TYPE
	SYNTAX  INTEGER
	ACCESS  read-only
	STATUS  mandatory
	DESCRIPTION "CB13C Crest Factor"
		::= { bcmsplus2 364 }

bcms2-cb14a-crest-factor
	OBJECT-TYPE
	SYNTAX  INTEGER
	ACCESS  read-only
	STATUS  mandatory
	DESCRIPTION "CB14A Crest Factor"
		::= { bcmsplus2 365 }

bcms2-cb14b-crest-factor
	OBJECT-TYPE
	SYNTAX  INTEGER
	ACCESS  read-only
	STATUS  mandatory
	DESCRIPTION "CB14B Crest Factor"
		::= { bcmsplus2 366 }

bcms2-cb14c-crest-factor
	OBJECT-TYPE
	SYNTAX  INTEGER
	ACCESS  read-only
	STATUS  mandatory
	DESCRIPTION "CB14C Crest Factor"
		::= { bcmsplus2 367 }

bcms2-cb1a-percent-thd
	OBJECT-TYPE
	SYNTAX  INTEGER
	ACCESS  read-only
	STATUS  mandatory
	DESCRIPTION "CB1A Percent THD
		     Note: for all Percent THD 1-42: 10 = 10%"  
		::= { bcmsplus2 368 }

bcms2-cb1b-percent-thd
	OBJECT-TYPE
	SYNTAX  INTEGER
	ACCESS  read-only
	STATUS  mandatory
	DESCRIPTION "CB1B Percent THD"
		::= { bcmsplus2 369 }
  
bcms2-cb1c-percent-thd
	OBJECT-TYPE
	SYNTAX  INTEGER
	ACCESS  read-only
	STATUS  mandatory
	DESCRIPTION "CB1C Percent THD"
		::= { bcmsplus2 370 }

bcms2-cb2a-percent-thd
	OBJECT-TYPE
	SYNTAX  INTEGER
	ACCESS  read-only
	STATUS  mandatory
	DESCRIPTION "CB2A Percent THD"
		::= { bcmsplus2 371 }

bcms2-cb2b-percent-thd
	OBJECT-TYPE
	SYNTAX  INTEGER
	ACCESS  read-only
	STATUS  mandatory
	DESCRIPTION "CB2B Percent THD"
		::= { bcmsplus2 372 }

bcms2-cb2c-percent-thd
	OBJECT-TYPE
	SYNTAX  INTEGER
	ACCESS  read-only
	STATUS  mandatory
	DESCRIPTION "CB2C Percent THD"
		::= { bcmsplus2 373 }

bcms2-cb3a-percent-thd
	OBJECT-TYPE
	SYNTAX  INTEGER
	ACCESS  read-only
	STATUS  mandatory
	DESCRIPTION "CB3A Percent THD"
		::= { bcmsplus2 374 }

bcms2-cb3b-percent-thd
	OBJECT-TYPE
	SYNTAX  INTEGER
	ACCESS  read-only
	STATUS  mandatory
	DESCRIPTION "CB3B Percent THD"
		::= { bcmsplus2 375 }

bcms2-cb3c-percent-thd
	OBJECT-TYPE
	SYNTAX  INTEGER
	ACCESS  read-only
	STATUS  mandatory
	DESCRIPTION "CB3C Percent THD"
		::= { bcmsplus2 376 }

bcms2-cb4a-percent-thd
	OBJECT-TYPE
	SYNTAX  INTEGER
	ACCESS  read-only
	STATUS  mandatory
	DESCRIPTION "CB4A Percent THD"
		::= { bcmsplus2 377 }

bcms2-cb4b-percent-thd
	OBJECT-TYPE
	SYNTAX  INTEGER
	ACCESS  read-only
	STATUS  mandatory
	DESCRIPTION "CB4B Percent THD"
		::= { bcmsplus2 378 }

bcms2-cb4c-percent-thd
	OBJECT-TYPE
	SYNTAX  INTEGER
	ACCESS  read-only
	STATUS  mandatory
	DESCRIPTION "CB4C Percent THD"
		::= { bcmsplus2 379 }
  
bcms2-cb5a-percent-thd
	OBJECT-TYPE
	SYNTAX  INTEGER
	ACCESS  read-only
	STATUS  mandatory
	DESCRIPTION "CB5A Percent THD"
		::= { bcmsplus2 380 }

bcms2-cb5b-percent-thd
	OBJECT-TYPE
	SYNTAX  INTEGER
	ACCESS  read-only
	STATUS  mandatory
	DESCRIPTION "CB5B Percent THD"
		::= { bcmsplus2 381 }

bcms2-cb5c-percent-thd
	OBJECT-TYPE
	SYNTAX  INTEGER
	ACCESS  read-only
	STATUS  mandatory
	DESCRIPTION "CB5C Percent THD"
		::= { bcmsplus2 382 }

bcms2-cb6a-percent-thd
	OBJECT-TYPE
	SYNTAX  INTEGER
	ACCESS  read-only
	STATUS  mandatory
	DESCRIPTION "CB6A Percent THD"
		::= { bcmsplus2 383 }

bcms2-cb6b-percent-thd
	OBJECT-TYPE
	SYNTAX  INTEGER
	ACCESS  read-only
	STATUS  mandatory
	DESCRIPTION "CB6B Percent THD"
		::= { bcmsplus2 384 }

bcms2-cb6c-percent-thd
	OBJECT-TYPE
	SYNTAX  INTEGER
	ACCESS  read-only
	STATUS  mandatory
	DESCRIPTION "CB6C Percent THD"
		::= { bcmsplus2 385 }

bcms2-cb7a-percent-thd
	OBJECT-TYPE
	SYNTAX  INTEGER
	ACCESS  read-only
	STATUS  mandatory
	DESCRIPTION "CB7A Percent THD"
		::= { bcmsplus2 386 }

bcms2-cb7b-percent-thd
	OBJECT-TYPE
	SYNTAX  INTEGER
	ACCESS  read-only
	STATUS  mandatory
	DESCRIPTION "CB7B Percent THD"
		::= { bcmsplus2 387 }

bcms2-cb7c-percent-thd
	OBJECT-TYPE
	SYNTAX  INTEGER
	ACCESS  read-only
	STATUS  mandatory
	DESCRIPTION "CB7C Percent THD"
		::= { bcmsplus2 388 }

bcms2-cb8a-percent-thd
	OBJECT-TYPE
	SYNTAX  INTEGER
	ACCESS  read-only
	STATUS  mandatory
	DESCRIPTION "CB8A Percent THD"
		::= { bcmsplus2 389 }
  
bcms2-cb8b-percent-thd
	OBJECT-TYPE
	SYNTAX  INTEGER
	ACCESS  read-only
	STATUS  mandatory
	DESCRIPTION "CB8B Percent THD"
		::= { bcmsplus2 390 }

bcms2-cb8c-percent-thd
	OBJECT-TYPE
	SYNTAX  INTEGER
	ACCESS  read-only
	STATUS  mandatory
	DESCRIPTION "CB8C Percent THD"
		::= { bcmsplus2 391 }

bcms2-cb9a-percent-thd
	OBJECT-TYPE
	SYNTAX  INTEGER
	ACCESS  read-only
	STATUS  mandatory
	DESCRIPTION "CB9A Percent THD"
		::= { bcmsplus2 392 }

bcms2-cb9b-percent-thd
	OBJECT-TYPE
	SYNTAX  INTEGER
	ACCESS  read-only
	STATUS  mandatory
	DESCRIPTION "CB9B Percent THD"
		::= { bcmsplus2 393 }

bcms2-cb9c-percent-thd
	OBJECT-TYPE
	SYNTAX  INTEGER
	ACCESS  read-only
	STATUS  mandatory
	DESCRIPTION "CB9C Percent THD"
		::= { bcmsplus2 394 }

bcms2-cb10a-percent-thd
	OBJECT-TYPE
	SYNTAX  INTEGER
	ACCESS  read-only
	STATUS  mandatory
	DESCRIPTION "CB10A Percent THD"
		::= { bcmsplus2 395 }

bcms2-cb10b-percent-thd
	OBJECT-TYPE
	SYNTAX  INTEGER
	ACCESS  read-only
	STATUS  mandatory
	DESCRIPTION "CB10B Percent THD"
		::= { bcmsplus2 396 }

bcms2-cb10c-percent-thd
	OBJECT-TYPE
	SYNTAX  INTEGER
	ACCESS  read-only
	STATUS  mandatory
	DESCRIPTION "CB10C Percent THD"
		::= { bcmsplus2 397 }

bcms2-cb11a-percent-thd
	OBJECT-TYPE
	SYNTAX  INTEGER
	ACCESS  read-only
	STATUS  mandatory
	DESCRIPTION "CB11A Percent THD"
		::= { bcmsplus2 398 }

bcms2-cb11b-percent-thd
	OBJECT-TYPE
	SYNTAX  INTEGER
	ACCESS  read-only
	STATUS  mandatory
	DESCRIPTION "CB11B Percent THD"
		::= { bcmsplus2 399 }
  
bcms2-cb11c-percent-thd
	OBJECT-TYPE
	SYNTAX  INTEGER
	ACCESS  read-only
	STATUS  mandatory
	DESCRIPTION "CB11C Percent THD"
		::= { bcmsplus2 400 }

bcms2-cb12a-percent-thd
	OBJECT-TYPE
	SYNTAX  INTEGER
	ACCESS  read-only
	STATUS  mandatory
	DESCRIPTION "CB12A Percent THD"
		::= { bcmsplus2 401 }

bcms2-cb12b-percent-thd
	OBJECT-TYPE
	SYNTAX  INTEGER
	ACCESS  read-only
	STATUS  mandatory
	DESCRIPTION "CB12B Percent THD"
		::= { bcmsplus2 402 }

bcms2-cb12c-percent-thd
	OBJECT-TYPE
	SYNTAX  INTEGER
	ACCESS  read-only
	STATUS  mandatory
	DESCRIPTION "CB12C Percent THD"
		::= { bcmsplus2 403 }

bcms2-cb13a-percent-thd
	OBJECT-TYPE
	SYNTAX  INTEGER
	ACCESS  read-only
	STATUS  mandatory
	DESCRIPTION "CB13A Percent THD"
		::= { bcmsplus2 404 }

bcms2-cb13b-percent-thd
	OBJECT-TYPE
	SYNTAX  INTEGER
	ACCESS  read-only
	STATUS  mandatory
	DESCRIPTION "CB13B Percent THD"
		::= { bcmsplus2 405 }

bcms2-cb13c-percent-thd
	OBJECT-TYPE
	SYNTAX  INTEGER
	ACCESS  read-only
	STATUS  mandatory
	DESCRIPTION "CB13C Percent THD"
		::= { bcmsplus2 406 }

bcms2-cb14a-percent-thd
	OBJECT-TYPE
	SYNTAX  INTEGER
	ACCESS  read-only
	STATUS  mandatory
	DESCRIPTION "CB14A Percent THD"
		::= { bcmsplus2 407 }

bcms2-cb14b-percent-thd
	OBJECT-TYPE
	SYNTAX  INTEGER
	ACCESS  read-only
	STATUS  mandatory
	DESCRIPTION "CB14B Percent THD"
		::= { bcmsplus2 408 }

bcms2-cb14c-percent-thd
	OBJECT-TYPE
	SYNTAX  INTEGER
	ACCESS  read-only
	STATUS  mandatory
	DESCRIPTION "CB14C Percent THD"
		::= { bcmsplus2 409 }
bcms2-cb1a-kwh-low
	OBJECT-TYPE
	SYNTAX  INTEGER
	ACCESS  read-only
	STATUS  mandatory
	DESCRIPTION "CB1A KWH Low
		     Note: for all KWH, Low is lower 16 bits and high 
                       is upper 16 bits for a 32 bit word"  
		::= { bcmsplus2 410 }

bcms2-cb1a-kwh-high
	OBJECT-TYPE
	SYNTAX  INTEGER
	ACCESS  read-only
	STATUS  mandatory
	DESCRIPTION "CB1A KWH High"
		::= { bcmsplus2 411 }

bcms2-cb1b-kwh-low
	OBJECT-TYPE
	SYNTAX  INTEGER
	ACCESS  read-only
	STATUS  mandatory
	DESCRIPTION "CB1B KWH Low"
		::= { bcmsplus2 412 }

bcms2-cb1b-kwh-high
	OBJECT-TYPE
	SYNTAX  INTEGER
	ACCESS  read-only
	STATUS  mandatory
	DESCRIPTION "CB1B KWH High"
		::= { bcmsplus2 413 }

bcms2-cb1c-kwh-low
	OBJECT-TYPE
	SYNTAX  INTEGER
	ACCESS  read-only
	STATUS  mandatory
	DESCRIPTION "CB1C KWH Low"
		::= { bcmsplus2 414 }

bcms2-cb1c-kwh-high
	OBJECT-TYPE
	SYNTAX  INTEGER
	ACCESS  read-only
	STATUS  mandatory
	DESCRIPTION "CB1C KWH High"
		::= { bcmsplus2 415 }

bcms2-cb2a-kwh-low
	OBJECT-TYPE
	SYNTAX  INTEGER
	ACCESS  read-only
	STATUS  mandatory
	DESCRIPTION "CB2A KWH Low"
		::= { bcmsplus2 416 }
  
bcms2-cb2a-kwh-high
	OBJECT-TYPE
	SYNTAX  INTEGER
	ACCESS  read-only
	STATUS  mandatory
	DESCRIPTION "CB2A KWH High"
		::= { bcmsplus2 417 }

bcms2-cb2b-kwh-low
	OBJECT-TYPE
	SYNTAX  INTEGER
	ACCESS  read-only
	STATUS  mandatory
	DESCRIPTION "CB2B KWH Low"
		::= { bcmsplus2 418 }

bcms2-cb2b-kwh-high
	OBJECT-TYPE
	SYNTAX  INTEGER
	ACCESS  read-only
	STATUS  mandatory
	DESCRIPTION "CB2B KWH High"
		::= { bcmsplus2 419 }

bcms2-cb2c-kwh-low
	OBJECT-TYPE
	SYNTAX  INTEGER
	ACCESS  read-only
	STATUS  mandatory
	DESCRIPTION "CB2C KWH Low"
		::= { bcmsplus2 420 }

bcms2-cb2c-kwh-high
	OBJECT-TYPE
	SYNTAX  INTEGER
	ACCESS  read-only
	STATUS  mandatory
	DESCRIPTION "CB2C KWH High"
		::= { bcmsplus2 421 }

bcms2-cb3a-kwh-low
	OBJECT-TYPE
	SYNTAX  INTEGER
	ACCESS  read-only
	STATUS  mandatory
	DESCRIPTION "CB3A KWH Low"
		::= { bcmsplus2 422 }

bcms2-cb3a-kwh-high
	OBJECT-TYPE
	SYNTAX  INTEGER
	ACCESS  read-only
	STATUS  mandatory
	DESCRIPTION "CB3A KWH High"
		::= { bcmsplus2 423 }

bcms2-cb3b-kwh-low
	OBJECT-TYPE
	SYNTAX  INTEGER
	ACCESS  read-only
	STATUS  mandatory
	DESCRIPTION "CB3B KWH Low"
		::= { bcmsplus2 424 }

bcms2-cb3b-kwh-high
	OBJECT-TYPE
	SYNTAX  INTEGER
	ACCESS  read-only
	STATUS  mandatory
	DESCRIPTION "CB3B KWH High"
		::= { bcmsplus2 425 }

bcms2-cb3c-kwh-low
	OBJECT-TYPE
	SYNTAX  INTEGER
	ACCESS  read-only
	STATUS  mandatory
	DESCRIPTION "CB3C KWH Low"
		::= { bcmsplus2 426 }

bcms2-cb3c-kwh-high
	OBJECT-TYPE
	SYNTAX  INTEGER
	ACCESS  read-only
	STATUS  mandatory
	DESCRIPTION "CB3C KWH High"
		::= { bcmsplus2 427 }

bcms2-cb4a-kwh-low
	OBJECT-TYPE
	SYNTAX  INTEGER
	ACCESS  read-only
	STATUS  mandatory
	DESCRIPTION "CB4A KWH Low"
		::= { bcmsplus2 428 }

bcms2-cb4a-kwh-high
	OBJECT-TYPE
	SYNTAX  INTEGER
	ACCESS  read-only
	STATUS  mandatory
	DESCRIPTION "CB4A KWH High"
		::= { bcmsplus2 429 }

bcms2-cb4b-kwh-low
	OBJECT-TYPE
	SYNTAX  INTEGER
	ACCESS  read-only
	STATUS  mandatory
	DESCRIPTION "CB4B KWH Low"
		::= { bcmsplus2 430 }

bcms2-cb4b-kwh-high
	OBJECT-TYPE
	SYNTAX  INTEGER
	ACCESS  read-only
	STATUS  mandatory
	DESCRIPTION "CB4B KWH High"
		::= { bcmsplus2 431 }

bcms2-cb4c-kwh-low
	OBJECT-TYPE
	SYNTAX  INTEGER
	ACCESS  read-only
	STATUS  mandatory
	DESCRIPTION "CB4C KWH Low"
		::= { bcmsplus2 432 }

bcms2-cb4c-kwh-high
	OBJECT-TYPE
	SYNTAX  INTEGER
	ACCESS  read-only
	STATUS  mandatory
	DESCRIPTION "CB4C KWH High"
		::= { bcmsplus2 433 }
  
bcms2-cb5a-kwh-low
	OBJECT-TYPE
	SYNTAX  INTEGER
	ACCESS  read-only
	STATUS  mandatory
	DESCRIPTION "CB5A KWH Low"
		::= { bcmsplus2 434 }

bcms2-cb5a-kwh-high
	OBJECT-TYPE
	SYNTAX  INTEGER
	ACCESS  read-only
	STATUS  mandatory
	DESCRIPTION "CB5A KWH High"
		::= { bcmsplus2 435 }

bcms2-cb5b-kwh-low
	OBJECT-TYPE
	SYNTAX  INTEGER
	ACCESS  read-only
	STATUS  mandatory
	DESCRIPTION "CB5B KWH Low"
		::= { bcmsplus2 436 }
  
bcms2-cb5b-kwh-high
	OBJECT-TYPE
	SYNTAX  INTEGER
	ACCESS  read-only
	STATUS  mandatory
	DESCRIPTION "CB5B KWH High"
		::= { bcmsplus2 437 }

bcms2-cb5c-kwh-low
	OBJECT-TYPE
	SYNTAX  INTEGER
	ACCESS  read-only
	STATUS  mandatory
	DESCRIPTION "CB5C KWH Low"
		::= { bcmsplus2 438 }

bcms2-cb5c-kwh-high
	OBJECT-TYPE
	SYNTAX  INTEGER
	ACCESS  read-only
	STATUS  mandatory
	DESCRIPTION "CB5C KWH High"
		::= { bcmsplus2 439 }

bcms2-cb6a-kwh-low
	OBJECT-TYPE
	SYNTAX  INTEGER
	ACCESS  read-only
	STATUS  mandatory
	DESCRIPTION "CB6A KWH Low"
		::= { bcmsplus2 440 }

bcms2-cb6a-kwh-high
	OBJECT-TYPE
	SYNTAX  INTEGER
	ACCESS  read-only
	STATUS  mandatory
	DESCRIPTION "CB6A KWH High"
		::= { bcmsplus2 441 }

bcms2-cb6b-kwh-low
	OBJECT-TYPE
	SYNTAX  INTEGER
	ACCESS  read-only
	STATUS  mandatory
	DESCRIPTION "CB6B KWH Low"
		::= { bcmsplus2 442 }

bcms2-cb6b-kwh-high
	OBJECT-TYPE
	SYNTAX  INTEGER
	ACCESS  read-only
	STATUS  mandatory
	DESCRIPTION "CB6B KWH High"
		::= { bcmsplus2 443 }

bcms2-cb6c-kwh-low
	OBJECT-TYPE
	SYNTAX  INTEGER
	ACCESS  read-only
	STATUS  mandatory
	DESCRIPTION "CB6C KWH Low"
		::= { bcmsplus2 444 }

bcms2-cb6c-kwh-high
	OBJECT-TYPE
	SYNTAX  INTEGER
	ACCESS  read-only
	STATUS  mandatory
	DESCRIPTION "CB6C KWH High"
		::= { bcmsplus2 445 }

bcms2-cb7a-kwh-low
	OBJECT-TYPE
	SYNTAX  INTEGER
	ACCESS  read-only
	STATUS  mandatory
	DESCRIPTION "CB7A KWH Low"
		::= { bcmsplus2 446 }

bcms2-cb7a-kwh-high
	OBJECT-TYPE
	SYNTAX  INTEGER
	ACCESS  read-only
	STATUS  mandatory
	DESCRIPTION "CB7A KWH High"
		::= { bcmsplus2 447 }

bcms2-cb7b-kwh-low
	OBJECT-TYPE
	SYNTAX  INTEGER
	ACCESS  read-only
	STATUS  mandatory
	DESCRIPTION "CB7B KWH Low"
		::= { bcmsplus2 448 }

bcms2-cb7b-kwh-high
	OBJECT-TYPE
	SYNTAX  INTEGER
	ACCESS  read-only
	STATUS  mandatory
	DESCRIPTION "CB7B KWH High"
		::= { bcmsplus2 449 }

bcms2-cb7c-kwh-low
	OBJECT-TYPE
	SYNTAX  INTEGER
	ACCESS  read-only
	STATUS  mandatory
	DESCRIPTION "CB7C KWH Low"
		::= { bcmsplus2 450 }

bcms2-cb7c-kwh-high
	OBJECT-TYPE
	SYNTAX  INTEGER
	ACCESS  read-only
	STATUS  mandatory
	DESCRIPTION "CB7C KWH High"
		::= { bcmsplus2 451 }

bcms2-cb8a-kwh-low
	OBJECT-TYPE
	SYNTAX  INTEGER
	ACCESS  read-only
	STATUS  mandatory
	DESCRIPTION "CB8A KWH Low"
		::= { bcmsplus2 452 }

bcms2-cb8a-kwh-high
	OBJECT-TYPE
	SYNTAX  INTEGER
	ACCESS  read-only
	STATUS  mandatory
	DESCRIPTION "CB8A KWH High"
		::= { bcmsplus2 453 }
  
bcms2-cb8b-kwh-low
	OBJECT-TYPE
	SYNTAX  INTEGER
	ACCESS  read-only
	STATUS  mandatory
	DESCRIPTION "CB8B KWH Low"
		::= { bcmsplus2 454 }

bcms2-cb8b-kwh-high
	OBJECT-TYPE
	SYNTAX  INTEGER
	ACCESS  read-only
	STATUS  mandatory
	DESCRIPTION "CB8B KWH High"
		::= { bcmsplus2 455 }

bcms2-cb8c-kwh-low
	OBJECT-TYPE
	SYNTAX  INTEGER
	ACCESS  read-only
	STATUS  mandatory
	DESCRIPTION "CB8C KWH Low"
		::= { bcmsplus2 456 }
  
bcms2-cb8c-kwh-high
	OBJECT-TYPE
	SYNTAX  INTEGER
	ACCESS  read-only
	STATUS  mandatory
	DESCRIPTION "CB8C KWH High"
		::= { bcmsplus2 457 }

bcms2-cb9a-kwh-low
	OBJECT-TYPE
	SYNTAX  INTEGER
	ACCESS  read-only
	STATUS  mandatory
	DESCRIPTION "CB9A KWH Low"
		::= { bcmsplus2 458 }

bcms2-cb9a-kwh-high
	OBJECT-TYPE
	SYNTAX  INTEGER
	ACCESS  read-only
	STATUS  mandatory
	DESCRIPTION "CB9A KWH High"
		::= { bcmsplus2 459 }

bcms2-cb9b-kwh-low
	OBJECT-TYPE
	SYNTAX  INTEGER
	ACCESS  read-only
	STATUS  mandatory
	DESCRIPTION "CB9B KWH Low"
		::= { bcmsplus2 460 }

bcms2-cb9b-kwh-high
	OBJECT-TYPE
	SYNTAX  INTEGER
	ACCESS  read-only
	STATUS  mandatory
	DESCRIPTION "CB9B KWH High"
		::= { bcmsplus2 461 }

bcms2-cb9c-kwh-low
	OBJECT-TYPE
	SYNTAX  INTEGER
	ACCESS  read-only
	STATUS  mandatory
	DESCRIPTION "CB9C KWH Low"
		::= { bcmsplus2 462 }

bcms2-cb9c-kwh-high
	OBJECT-TYPE
	SYNTAX  INTEGER
	ACCESS  read-only
	STATUS  mandatory
	DESCRIPTION "CB9C KWH High"
		::= { bcmsplus2 463 }

bcms2-cb10a-kwh-low
	OBJECT-TYPE
	SYNTAX  INTEGER
	ACCESS  read-only
	STATUS  mandatory
	DESCRIPTION "CB10A KWH Low"
		::= { bcmsplus2 464 }

bcms2-cb10a-kwh-high
	OBJECT-TYPE
	SYNTAX  INTEGER
	ACCESS  read-only
	STATUS  mandatory
	DESCRIPTION "CB10A KWH High"
		::= { bcmsplus2 465 }

bcms2-cb10b-kwh-low
	OBJECT-TYPE
	SYNTAX  INTEGER
	ACCESS  read-only
	STATUS  mandatory
	DESCRIPTION "CB10B KWH Low"
		::= { bcmsplus2 466 }

bcms2-cb10b-kwh-high
	OBJECT-TYPE
	SYNTAX  INTEGER
	ACCESS  read-only
	STATUS  mandatory
	DESCRIPTION "CB10B KWH High"
		::= { bcmsplus2 467 }

bcms2-cb10c-kwh-low
	OBJECT-TYPE
	SYNTAX  INTEGER
	ACCESS  read-only
	STATUS  mandatory
	DESCRIPTION "CB10C KWH Low"
		::= { bcmsplus2 468 }

bcms2-cb10c-kwh-high
	OBJECT-TYPE
	SYNTAX  INTEGER
	ACCESS  read-only
	STATUS  mandatory
	DESCRIPTION "CB10C KWH High"
		::= { bcmsplus2 469 }

bcms2-cb11a-kwh-low
	OBJECT-TYPE
	SYNTAX  INTEGER
	ACCESS  read-only
	STATUS  mandatory
	DESCRIPTION "CB11A KWH Low"
		::= { bcmsplus2 470 }

bcms2-cb11a-kwh-high
	OBJECT-TYPE
	SYNTAX  INTEGER
	ACCESS  read-only
	STATUS  mandatory
	DESCRIPTION "CB11A KWH High"
		::= { bcmsplus2 471 }

bcms2-cb11b-kwh-low
	OBJECT-TYPE
	SYNTAX  INTEGER
	ACCESS  read-only
	STATUS  mandatory
	DESCRIPTION "CB11B KWH Low"
		::= { bcmsplus2 472 }

bcms2-cb11b-kwh-high
	OBJECT-TYPE
	SYNTAX  INTEGER
	ACCESS  read-only
	STATUS  mandatory
	DESCRIPTION "CB11B KWH High"
		::= { bcmsplus2 473 }
  
bcms2-cb11c-kwh-low
	OBJECT-TYPE
	SYNTAX  INTEGER
	ACCESS  read-only
	STATUS  mandatory
	DESCRIPTION "CB11C KWH Low"
		::= { bcmsplus2 474 }

bcms2-cb11c-kwh-high
	OBJECT-TYPE
	SYNTAX  INTEGER
	ACCESS  read-only
	STATUS  mandatory
	DESCRIPTION "CB11C KWH High"
		::= { bcmsplus2 475 }

bcms2-cb12a-kwh-low
	OBJECT-TYPE
	SYNTAX  INTEGER
	ACCESS  read-only
	STATUS  mandatory
	DESCRIPTION "CB12A KWH Low"
		::= { bcmsplus2 476 }
  
bcms2-cb12a-kwh-high
	OBJECT-TYPE
	SYNTAX  INTEGER
	ACCESS  read-only
	STATUS  mandatory
	DESCRIPTION "CB12A KWH High"
		::= { bcmsplus2 477 }

bcms2-cb12b-kwh-low
	OBJECT-TYPE
	SYNTAX  INTEGER
	ACCESS  read-only
	STATUS  mandatory
	DESCRIPTION "CB12B KWH Low"
		::= { bcmsplus2 478 }

bcms2-cb12b-kwh-high
	OBJECT-TYPE
	SYNTAX  INTEGER
	ACCESS  read-only
	STATUS  mandatory
	DESCRIPTION "CB12B KWH High"
		::= { bcmsplus2 479 }

bcms2-cb12c-kwh-low
	OBJECT-TYPE
	SYNTAX  INTEGER
	ACCESS  read-only
	STATUS  mandatory
	DESCRIPTION "CB12C KWH Low"
		::= { bcmsplus2 480 }

bcms2-cb12c-kwh-high
	OBJECT-TYPE
	SYNTAX  INTEGER
	ACCESS  read-only
	STATUS  mandatory
	DESCRIPTION "CB12C KWH High"
		::= { bcmsplus2 481 }

bcms2-cb13a-kwh-low
	OBJECT-TYPE
	SYNTAX  INTEGER
	ACCESS  read-only
	STATUS  mandatory
	DESCRIPTION "CB13A KWH Low"
		::= { bcmsplus2 482 }

bcms2-cb13a-kwh-high
	OBJECT-TYPE
	SYNTAX  INTEGER
	ACCESS  read-only
	STATUS  mandatory
	DESCRIPTION "CB13A KWH High"
		::= { bcmsplus2 483 }

bcms2-cb13b-kwh-low
	OBJECT-TYPE
	SYNTAX  INTEGER
	ACCESS  read-only
	STATUS  mandatory
	DESCRIPTION "CB13B KWH Low"
		::= { bcmsplus2 484 }

bcms2-cb13b-kwh-high
	OBJECT-TYPE
	SYNTAX  INTEGER
	ACCESS  read-only
	STATUS  mandatory
	DESCRIPTION "CB13B KWH High"
		::= { bcmsplus2 485 }

bcms2-cb13c-kwh-low
	OBJECT-TYPE
	SYNTAX  INTEGER
	ACCESS  read-only
	STATUS  mandatory
	DESCRIPTION "CB13C KWH Low"
		::= { bcmsplus2 486 }

bcms2-cb13c-kwh-high
	OBJECT-TYPE
	SYNTAX  INTEGER
	ACCESS  read-only
	STATUS  mandatory
	DESCRIPTION "CB13C KWH High"
		::= { bcmsplus2 487 }

bcms2-cb14a-kwh-low
	OBJECT-TYPE
	SYNTAX  INTEGER
	ACCESS  read-only
	STATUS  mandatory
	DESCRIPTION "CB14A KWH Low"
		::= { bcmsplus2 488 }

bcms2-cb14a-kwh-high
	OBJECT-TYPE
	SYNTAX  INTEGER
	ACCESS  read-only
	STATUS  mandatory
	DESCRIPTION "CB14A KWH High"
		::= { bcmsplus2 489 }

bcms2-cb14b-kwh-low
	OBJECT-TYPE
	SYNTAX  INTEGER
	ACCESS  read-only
	STATUS  mandatory
	DESCRIPTION "CB14B KWH Low"
		::= { bcmsplus2 490 }

bcms2-cb14b-kwh-high
	OBJECT-TYPE
	SYNTAX  INTEGER
	ACCESS  read-only
	STATUS  mandatory
	DESCRIPTION "CB14B KWH High"
		::= { bcmsplus2 491 }

bcms2-cb14c-kwh-low
	OBJECT-TYPE
	SYNTAX  INTEGER
	ACCESS  read-only
	STATUS  mandatory
	DESCRIPTION "CB14C KWH Low"
		::= { bcmsplus2 492 }

bcms2-cb14c-kwh-high
	OBJECT-TYPE
	SYNTAX  INTEGER
	ACCESS  read-only
	STATUS  mandatory
	DESCRIPTION "CB14C KWH High"
		::= { bcmsplus2 493 }

bcms2-full-load-percentage
	OBJECT-TYPE
	SYNTAX  INTEGER
	ACCESS  read-write
	STATUS  mandatory
	DESCRIPTION "Full Load Percentage
		     Note:  percentage of breaker size used for percent load 100 = 100%"
		::= { bcmsplus2 494 }

bcms2-global-breaker-size
	OBJECT-TYPE
	SYNTAX  INTEGER
	ACCESS  read-write
	STATUS  mandatory
	DESCRIPTION "Global-breaker-size
		     Note for global breaker size: 100 = 100 amps
                     Range is 20 to 600 amps"
		::= { bcmsplus2 495 }

bcms2-phase-warning-threshold
	OBJECT-TYPE
	SYNTAX  INTEGER
	ACCESS  read-write
	STATUS  mandatory
	DESCRIPTION "Phase-warning-threshold
		     Note: Phase warning threshold: 70 = 70% of breaker size
                     range is 0-100%"
		::= { bcmsplus2 496 }

bcms2-phase-alarm-threshold
	OBJECT-TYPE
	SYNTAX  INTEGER
	ACCESS  read-write
	STATUS  mandatory
	DESCRIPTION "Phase-alarm-threshold
		     Note: Phase alarm threshold: 80 = 80% of breaker size
                     range is 0-100%"
		::= { bcmsplus2 497 }

bcms2-neutral-warning-threshold
	OBJECT-TYPE
	SYNTAX  INTEGER
	ACCESS  read-write
	STATUS  mandatory
	DESCRIPTION "Neutral-warning-threshold
		     Note: Neutral warning threshold: 70 = 70% of breaker size
                     range is 0-100%"
		::= { bcmsplus2 498}

bcms2-neutral-alarm-threshold
	OBJECT-TYPE
	SYNTAX  INTEGER
	ACCESS  read-write
	STATUS  mandatory
	DESCRIPTION "Neutral-alarm-threshold
		     Note: Neutral alarm threshold: 80 = 80% of breaker size
                     range is 0-100%"
		::= { bcmsplus2 499 }

bcms2-warning-time-delay
	OBJECT-TYPE
	SYNTAX  INTEGER
	ACCESS  read-write
	STATUS  mandatory
	DESCRIPTION "warning-time-delay
		     Note: warning time delay: units are in seconds"                     
		::= { bcmsplus2 500 }

bcms2-alarm-time-delay
	OBJECT-TYPE
	SYNTAX  INTEGER
	ACCESS  read-write
	STATUS  mandatory
	DESCRIPTION "alarm-time-delay
		     Note: alarm time delay: units are in seconds"                     
		::= { bcmsplus2 501 }

bcms2-min-max-reset
	OBJECT-TYPE
	SYNTAX  INTEGER
	ACCESS  read-write
	STATUS  mandatory
	DESCRIPTION "Min-max-Reset
                     Note: Min-max Reset: writing to this register will clear minimum
		     and maximum current values"
		::= { bcmsplus2 502 }

bcms2-kwh-reset
	OBJECT-TYPE
	SYNTAX  INTEGER
	ACCESS  read-write
	STATUS  mandatory
	DESCRIPTION "Kwh-Reset
                     Note: Kwh Reset: writing to this register will clear kwh values"
		::= { bcmsplus2 503 }

bcms2-latched-summary-register
	OBJECT-TYPE
	SYNTAX  INTEGER
	ACCESS  read-write
	STATUS  mandatory
	DESCRIPTION "Latched Summary Register
			bit 0:	Warning Register 
			bit 1:	Alarm Register 
			bit 2:	Zero Current Register 
			bit 3:	Over Voltage Register 
			bit 4:	Under Voltage Register 
			bits 5 - 15: Always read as 0"
		::= { bcmsplus2 504 }

bcms2-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 - 15: Not Used"
		::= { bcmsplus2 505 }

bcms2-current-option-setting
	OBJECT-TYPE
	SYNTAX  INTEGER
	ACCESS  read-only
	STATUS  mandatory
	DESCRIPTION "Current-Option-Setting
			bit 0: CB1 is main
			bit 1: Neutral CTs
			bits 2 - 14: Not Used
			bit 15: Current Loss" 
		::= { bcmsplus2 506 }


bcms2-voltage-option-setting
	OBJECT-TYPE
	SYNTAX  INTEGER
	ACCESS  read-only
	STATUS  mandatory
	DESCRIPTION "Voltage-Option-Setting
			bit 0:	option 0
			bit 1:	option 1
			bit 2: 	option 2 
			bit 3: 	Not Used
			bit 4: 	Not Used
			bit 5: 	Set to 50Hz
			bits 6 - 15: Not Used
                     Option 0: no voltage monitoring.  (154-331 & 336-347 not used)
                     Option 1: One voltage feeding 1 or 2 panel boards. 
                     Option 2: One voltage feeding breakerset 1 and another feeding breakerset 2."
		::= { bcmsplus2 507 }

bcms2-voltage-a-b
	OBJECT-TYPE
	SYNTAX  INTEGER
	ACCESS  read-only
	STATUS  mandatory
	DESCRIPTION "Voltage-A-B
                     Note for all voltages: 1200 = 120.0 volts"
		::= { bcmsplus2 508 }

bcms2-voltage-b-c
	OBJECT-TYPE
	SYNTAX  INTEGER
	ACCESS  read-only
	STATUS  mandatory
	DESCRIPTION "Voltage-B-C"
		::= { bcmsplus2 509 }

bcms2-voltage-c-a
	OBJECT-TYPE
	SYNTAX  INTEGER
	ACCESS  read-only
	STATUS  mandatory
	DESCRIPTION "Voltage-C-A"
		::= { bcmsplus2 510 }

bcms2-voltage-a-n
	OBJECT-TYPE
	SYNTAX  INTEGER
	ACCESS  read-only
	STATUS  mandatory
	DESCRIPTION "Voltage-A-N"
		::= { bcmsplus2 511 }

bcms2-voltage-b-n
	OBJECT-TYPE
	SYNTAX  INTEGER
	ACCESS  read-only
	STATUS  mandatory
	DESCRIPTION "Voltage-B-N"
		::= { bcmsplus2 512 }

bcms2-voltage-c-n
	OBJECT-TYPE
	SYNTAX  INTEGER
	ACCESS  read-only
	STATUS  mandatory
	DESCRIPTION "Voltage-C-N"
		::= { bcmsplus2 513 }

bcms2-over-voltage-alarm-threshhold
	OBJECT-TYPE
	SYNTAX  INTEGER
	ACCESS  read-write
	STATUS  mandatory
	DESCRIPTION "Over-Voltage-Alarm-Threshhold
                     Note All Over and Under Voltage is for L-L values"
		::= { bcmsplus2 514 }

bcms2-under-voltage-alarm-threshhold
	OBJECT-TYPE
	SYNTAX  INTEGER
	ACCESS  read-write
	STATUS  mandatory
	DESCRIPTION "Under-Voltage-Alarm-Threshhold"
		::= { bcmsplus2 515 }

bcms2-voltage-frequency
	OBJECT-TYPE
	SYNTAX  INTEGER
	ACCESS  read-only
	STATUS  mandatory
	DESCRIPTION "Voltage-Frequency
                     note for frequency: 600 = 60.0Hz
                     Range is 40-70Hz
                     Note if insufficient voltage is present frequency will read 0xFFFF"
		::= { bcmsplus2 516 }

bcms2-voltage-thd-phase-a
	OBJECT-TYPE
	SYNTAX  INTEGER
	ACCESS  read-only
	STATUS  mandatory
	DESCRIPTION "Voltage-THD-Phase-A"
		::= { bcmsplus2 517 }

bcms2-voltage-thd-phase-b
	OBJECT-TYPE
	SYNTAX  INTEGER
	ACCESS  read-only
	STATUS  mandatory
	DESCRIPTION "Voltage-THD-Phase-B"
		::= { bcmsplus2 518 }

bcms2-voltage-thd-phase-c
	OBJECT-TYPE
	SYNTAX  INTEGER
	ACCESS  read-only
	STATUS  mandatory
	DESCRIPTION "Voltage-THD-Phase-C"
		::= { bcmsplus2 519 }

--------------------------------------------------------------------------------
-- Trap register values
--------------------------------------------------------------------------------

display-summary-trap
        TRAP-TYPE
	  ENTERPRISE	displaytraps
	  VARIABLES		{ display-alarm }
	  DESCRIPTION	"Dispaly Summary Alarm Trap"
	  ::= 1


END
