SNMPPDU-MIB DEFINITIONS ::= BEGIN

IMPORTS
    enterprises, Counter,
    TimeTicks, Gauge                FROM RFC1155-SMI
    OBJECT-TYPE                     FROM RFC-1212
    sysUpTime, DisplayString		  FROM RFC1213-MIB
TRAP-TYPE                           FROM RFC-1215;

pdu OBJECT IDENTIFIER ::= { enterprises 23273}
ipdu OBJECT IDENTIFIER ::= { pdu 1 }
devicename OBJECT IDENTIFIER ::= { ipdu 1 }
masterstatus OBJECT IDENTIFIER ::= { ipdu 2 }
slavestatus OBJECT IDENTIFIER ::= { ipdu 3 }

deviceName OBJECT-TYPE
    SYNTAX DisplayString (SIZE (255))
    ACCESS read-write
    STATUS optional
    DESCRIPTION
            "device name."
    ::= { devicename 1 }

masterVoltageL1 OBJECT-TYPE
    SYNTAX INTEGER (SIZE (0-65535))
    ACCESS read-only
    STATUS optional
    DESCRIPTION
            "Master Line 1 total votage."
    ::= { masterstatus 1 }

masterCurrentL1 OBJECT-TYPE
    SYNTAX INTEGER (SIZE (0-65535))
    ACCESS read-only
    STATUS optional
    DESCRIPTION
            "Master Line 1 total current."
    ::= { masterstatus 2 }

masterEnergyL1 OBJECT-TYPE
    SYNTAX INTEGER (SIZE (0-65535))
    ACCESS read-only
    STATUS optional
    DESCRIPTION
            "Master Line 1 total energy ."
    ::= { masterstatus 3 }

masterVoltageL2 OBJECT-TYPE
    SYNTAX INTEGER (SIZE (0-65535))
    ACCESS read-only
    STATUS optional
    DESCRIPTION
            "Master Line 2 total votage."
    ::= { masterstatus 4 }

masterCurrentL2 OBJECT-TYPE
    SYNTAX INTEGER (SIZE (0-65535))
    ACCESS read-only
    STATUS optional
    DESCRIPTION
            "Master Line 2 total current."
    ::= { masterstatus 5 }

masterEnergyL2 OBJECT-TYPE
    SYNTAX INTEGER (SIZE (0-65535))
    ACCESS read-only
    STATUS optional
    DESCRIPTION
            "Master Line 2 total energy ."
    ::= { masterstatus 6 }


masterVoltageL3 OBJECT-TYPE
    SYNTAX INTEGER (SIZE (0-65535))
    ACCESS read-only
    STATUS optional
    DESCRIPTION
            "Master Line 3 total votage."
    ::= { masterstatus 7 }

masterCurrentL3 OBJECT-TYPE
    SYNTAX INTEGER (SIZE (0-65535))
    ACCESS read-only
    STATUS optional
    DESCRIPTION
            "Master Line 3 total current."
    ::= { masterstatus 8 }

masterEnergyL3 OBJECT-TYPE
    SYNTAX INTEGER (SIZE (0-65535))
    ACCESS read-only
    STATUS optional
    DESCRIPTION
            "Master Line 3 total energy ."
    ::= { masterstatus 9 }
    
masterTemperature OBJECT-TYPE
    SYNTAX INTEGER (SIZE (0-65535))
    ACCESS read-only
    STATUS optional
    DESCRIPTION
            "Master Temperature ."
    ::= { masterstatus 10 }

masterHumidity OBJECT-TYPE
    SYNTAX INTEGER (SIZE (0-65535))
    ACCESS read-only
    STATUS optional
    DESCRIPTION
            "Master Humidity ."
    ::= { masterstatus 11 }
    
slaveVoltageL1 OBJECT-TYPE
    SYNTAX INTEGER (SIZE (0-65535))
    ACCESS read-only
    STATUS optional
    DESCRIPTION
            "Slave Line 1 total votage."
    ::= { slavestatus 1 }

slaveCurrentL1 OBJECT-TYPE
    SYNTAX INTEGER (SIZE (0-65535))
    ACCESS read-only
    STATUS optional
    DESCRIPTION
            "Slave Line 1 total current."
    ::= { slavestatus 2 }

slaveEnergyL1 OBJECT-TYPE
    SYNTAX INTEGER (SIZE (0-65535))
    ACCESS read-only
    STATUS optional
    DESCRIPTION
            "Slave Line 1 total energy ."
    ::= { slavestatus 3 }


slaveVoltageL2 OBJECT-TYPE
    SYNTAX INTEGER (SIZE (0-65535))
    ACCESS read-only
    STATUS optional
    DESCRIPTION
            "Slave Line 2 total votage."
    ::= { slavestatus 4 }

slaveCurrentL2 OBJECT-TYPE
    SYNTAX INTEGER (SIZE (0-65535))
    ACCESS read-only
    STATUS optional
    DESCRIPTION
            "Slave Line 2 total current."
    ::= { slavestatus 5 }

slaveEnergyL2 OBJECT-TYPE
    SYNTAX INTEGER (SIZE (0-65535))
    ACCESS read-only
    STATUS optional
    DESCRIPTION
            "Slave Line 2 total energy ."
    ::= { slavestatus 6 }


slaveVoltageL3 OBJECT-TYPE
    SYNTAX INTEGER (SIZE (0-65535))
    ACCESS read-only
    STATUS optional
    DESCRIPTION
            "Slave Line 3 total votage."
    ::= { slavestatus 7 }

slaveCurrentL3 OBJECT-TYPE
    SYNTAX INTEGER (SIZE (0-65535))
    ACCESS read-only
    STATUS optional
    DESCRIPTION
            "Slave Line 3 total current."
    ::= { slavestatus 8 }

slaveEnergyL3 OBJECT-TYPE
    SYNTAX INTEGER (SIZE (0-65535))
    ACCESS read-only
    STATUS optional
    DESCRIPTION
            "Slave Line 3 total energy ."
    ::= { slavestatus 9 }
    
slaveTemperature OBJECT-TYPE
    SYNTAX INTEGER (SIZE (0-65535))
    ACCESS read-only
    STATUS optional
    DESCRIPTION
            "Slave Temperature ."
    ::= { slavestatus 10 }

slaveHumidity OBJECT-TYPE
    SYNTAX INTEGER (SIZE (0-65535))
    ACCESS read-only
    STATUS optional
    DESCRIPTION
            "Slave Humidity ."
    ::= { slavestatus 11 }
    
END
