-- ============================================================================
-- MIYAKAWA.PTC5050 MIB(2009.08.18)
--
-- Copyright (c) 2007 MIYAKAWA ELECTRIC WORKS LTD.
-- All rights reserved.
-- 
-- ============================================================================

MIYAKAWA-MIB DEFINITIONS ::= BEGIN

--IMPORTS
--	MODULE-IDENTITY,
--	OBJECT-TYPE,
--	enterprises
--		FROM SNMPv2-SMI
--	;
	
    miyakawa 				MODULE-IDENTITY								-- 1.3.6.1.4.1.14703
        LAST-UPDATED	    "200908180000Z"
        ORGANIZATION	    "(C) MIYAKAWA, INC."
        CONTACT-INFO        "http://www.msk.co.jp/"
        DESCRIPTION         "TERMS-pro PTC5050 MIB"
        REVISION			"200908180000Z"
        DESCRIPTION			""
        ::= { enterprises 14703 }
	
	dsiunit				OBJECT IDENTIFIER	::= { miyakawa 2 }			-- 1.3.6.1.4.1.14703.2
--	dsiSystem			OBJECT IDENTIFIER	::= { dsiunit 1 }			-- 1.3.6.1.4.1.14703.2.1
--	dsiStatus 			OBJECT IDENTIFIER	::= { dsiunit 2 }			-- 1.3.6.1.4.1.14703.2.2
	pdu 				OBJECT IDENTIFIER	::= { dsiunit 3 }			-- 1.3.6.1.4.1.14703.2.3
	pduSystem 			OBJECT IDENTIFIER	::= { pdu 1 }				-- 1.3.6.1.4.1.14703.2.3.1
	pduInfomation 		OBJECT IDENTIFIER	::= { pduSystem 1 }			-- 1.3.6.1.4.1.14703.2.3.1.1
	pduSetTable 		OBJECT IDENTIFIER	::= { pduSystem 2 }			-- 1.3.6.1.4.1.14703.2.3.1.2
	pduStatus 			OBJECT IDENTIFIER	::= { pdu 2 }				-- 1.3.6.1.4.1.14703.2.3.2
	pduPeakTable 		OBJECT IDENTIFIER	::= { pduStatus 2 }			-- 1.3.6.1.4.1.14703.2.3.2.2
	pduAveTable		 	OBJECT IDENTIFIER	::= { pduStatus 3 }			-- 1.3.6.1.4.1.14703.2.3.2.3
	pduBtmTable 		OBJECT IDENTIFIER	::= { pduStatus 4 }			-- 1.3.6.1.4.1.14703.2.3.2.4
	pduWaveTable 		OBJECT IDENTIFIER	::= { pduStatus 5 }			-- 1.3.6.1.4.1.14703.2.3.2.5
	pduPhaseTable 		OBJECT IDENTIFIER	::= { pduStatus 6 }			-- 1.3.6.1.4.1.14703.2.3.2.6
	pduWaveTable2 		OBJECT IDENTIFIER	::= { pduStatus 7 }			-- 1.3.6.1.4.1.14703.2.3.2.7
	pduWaveTable3 		OBJECT IDENTIFIER	::= { pduStatus 8 }			-- 1.3.6.1.4.1.14703.2.3.2.8
	
	pduVolType			OBJECT-TYPE										-- 1.3.6.1.4.1.14703.2.3.1.2.1
		SYNTAX			OCTET STRING ( SIZE (64) )
		MAX-ACCESS		read-write
		STATUS			current
		DESCRIPTION		"Volatage Variety"
		::= { pduSetTable 1 }
	
	pduPhsLag	 		OBJECT-TYPE										-- 1.3.6.1.4.1.14703.2.3.1.2.2
		SYNTAX			INTEGER ( 1..2 )
		MAX-ACCESS		read-write
		STATUS			current
		DESCRIPTION		"Phase Difference Offset"
		::= { pduSetTable 2 }
	
	-- Sensor Peak
	
	pduPeakTempEntry	OBJECT-TYPE										-- 1.3.6.1.4.1.14703.2.3.2.2.1
		SYNTAX			OCTET STRING ( SIZE (192) )
		MAX-ACCESS		read-only
		STATUS			current
		DESCRIPTION		"Temperature Peak Value"
		::= { pduPeakTable 1 }
	
	pduPeakCurrentEnrty	OBJECT-TYPE										-- 1.3.6.1.4.1.14703.2.3.2.2.2
		SYNTAX			OCTET STRING ( SIZE (192) )
		MAX-ACCESS		read-only
		STATUS			current
		DESCRIPTION		"Electric Current Peak Value"
		::= { pduPeakTable 2 }
	
	pduPeakVolEntry		OBJECT-TYPE										-- 1.3.6.1.4.1.14703.2.3.2.2.3
		SYNTAX			OCTET STRING ( SIZE (3) )
		MAX-ACCESS		read-only
		STATUS			current
		DESCRIPTION		"Voltage Peak Value"
		::= { pduPeakTable 3 }
	
	pduPeakWatEntry		OBJECT-TYPE										-- 1.3.6.1.4.1.14703.2.3.2.2.4
		SYNTAX			OCTET STRING ( SIZE (192) )
		MAX-ACCESS		read-only
		STATUS			current
		DESCRIPTION		"Electric Power Peak Value"
		::= { pduPeakTable 4 }
	
	pduPeakFrcEntry		OBJECT-TYPE										-- 1.3.6.1.4.1.14703.2.3.2.2.5
		SYNTAX			OCTET STRING ( SIZE (192) )
		MAX-ACCESS		read-only
		STATUS			current
		DESCRIPTION		"Power Factor Peak Value"
		::= { pduPeakTable 5 }
	
	pduPeakLongWatEntry	OBJECT-TYPE										-- 1.3.6.1.4.1.14703.2.3.2.2.6
		SYNTAX			OCTET STRING ( SIZE (320) )
		MAX-ACCESS		read-only
		STATUS			current
		DESCRIPTION		"Electric Power Peak Value（4 byte）"
		::= { pduPeakTable 6 }
	
	-- Sensor Average
	
	pduAveTempEntry		OBJECT-TYPE										-- 1.3.6.1.4.1.14703.2.3.2.3.1
		SYNTAX			OCTET STRING ( SIZE (192) )
		MAX-ACCESS		read-only
		STATUS			current
		DESCRIPTION		"Temeprature Average Value"
		::= { pduAveTable 1 }
	
	pduAveCurrentEnrty	OBJECT-TYPE										-- 1.3.6.1.4.1.14703.2.3.2.3.2
		SYNTAX			OCTET STRING ( SIZE (192) )
		MAX-ACCESS		read-only
		STATUS			current
		DESCRIPTION		"Electric Current Average Value"
		::= { pduAveTable 2 }
	
	pduAveVolEntry		OBJECT-TYPE										-- 1.3.6.1.4.1.14703.2.3.2.3.3
		SYNTAX			OCTET STRING ( SIZE (3) )
		MAX-ACCESS		read-only
		STATUS			current
		DESCRIPTION		"Voltage Average Value"
		::= { pduAveTable 3 }
	
	pduAveWatEntry		OBJECT-TYPE										-- 1.3.6.1.4.1.14703.2.3.2.3.4
		SYNTAX			OCTET STRING ( SIZE (192) )
		MAX-ACCESS		read-only
		STATUS			current
		DESCRIPTION		"Electric Power Average Value"
		::= { pduAveTable 4 }
	
	pduAveFrcEntry		OBJECT-TYPE										-- 1.3.6.1.4.1.14703.2.3.2.3.5
		SYNTAX			OCTET STRING ( SIZE (192) )
		MAX-ACCESS		read-only
		STATUS			current
		DESCRIPTION		"Power Factor Average Value"
		::= { pduAveTable 5 }
	
	pduAveLongWatEntry	OBJECT-TYPE										-- 1.3.6.1.4.1.14703.2.3.2.3.6
		SYNTAX			OCTET STRING ( SIZE (320) )
		MAX-ACCESS		read-only
		STATUS			current
		DESCRIPTION		"Electric Power Average Value（4 byte）"
		::= { pduAveTable 6 }
	
	-- Sensor Bottom
	
	pduBtmTempEntry		OBJECT-TYPE										-- 1.3.6.1.4.1.14703.2.3.2.4.1
		SYNTAX			OCTET STRING ( SIZE (192) )
		MAX-ACCESS		read-only
		STATUS			current
		DESCRIPTION		"Temperature Bottom Value"
		::= { pduBtmTable 1 }
	
	pduBtmCurrentEnrty	OBJECT-TYPE										-- 1.3.6.1.4.1.14703.2.3.2.4.2
		SYNTAX			OCTET STRING ( SIZE (192) )
		MAX-ACCESS		read-only
		STATUS			current
		DESCRIPTION		"Electric Current Bottom Value"
		::= { pduBtmTable 2 }
	
	pduBtmVolEntry		OBJECT-TYPE										-- 1.3.6.1.4.1.14703.2.3.2.4.3
		SYNTAX			OCTET STRING ( SIZE (3) )
		MAX-ACCESS		read-only
		STATUS			current
		DESCRIPTION		"Voltage Bottom Value"
		::= { pduBtmTable 3 }
	
	pduBtmWatEntry		OBJECT-TYPE										-- 1.3.6.1.4.1.14703.2.3.2.4.4
		SYNTAX			OCTET STRING ( SIZE (192) )
		MAX-ACCESS		read-only
		STATUS			current
		DESCRIPTION		"Electric Power Bottom Value"
		::= { pduBtmTable 4 }
	
	pduBtmFrcEntry		OBJECT-TYPE										-- 1.3.6.1.4.1.14703.2.3.2.4.5
		SYNTAX			OCTET STRING ( SIZE (192) )
		MAX-ACCESS		read-only
		STATUS			current
		DESCRIPTION		"Power Factor Bottom Value"
		::= { pduBtmTable 5 }
	
	pduBtmLongWatEntry	OBJECT-TYPE										-- 1.3.6.1.4.1.14703.2.3.2.4.6
		SYNTAX			OCTET STRING ( SIZE (320) )
		MAX-ACCESS		read-only
		STATUS			current
		DESCRIPTION		"Electric Power Average Value（4 byte）"
		::= { pduBtmTable 6 }
	
	-- Electric Current Waveform（Sampling Data from 359 data）
	
	pduWaveValUnit1		OBJECT-TYPE										-- 1.3.6.1.4.1.14703.2.3.2.5.1
		SYNTAX			OCTET STRING ( SIZE (721) )
		MAX-ACCESS		read-only
		STATUS			current
		DESCRIPTION		"Waveform (Unit Number1）"
		::= { pduWaveTable 1 }
	
	--  pduWaveValUnit2 -> pduWaveValUnit63
	
	pduWaveValUnit64		OBJECT-TYPE										-- 1.3.6.1.4.1.14703.2.3.2.5.64
		SYNTAX			OCTET STRING ( SIZE (721) )
		MAX-ACCESS		read-only
		STATUS			current
		DESCRIPTION		"Waveform (Unit Number64）"
		::= { pduWaveTable 64 }
	
	-- 
	
	pduPhaseLag			OBJECT-TYPE										-- 1.3.6.1.4.1.14703.2.3.2.6.1
		SYNTAX			OCTET STRING ( SIZE (64) )
		MAX-ACCESS		read-only
		STATUS			current
		DESCRIPTION		"Phase Difference"
		::= { pduPhaseTable 1 }
	
	-- Electric Current Waveform（Sampling Data from 359 data）＋Frequency ＋Voltage＋Phase Difference＋Electirc Current＋Voltage＋Electric Power
	
	pduWave2ValUnit1	OBJECT-TYPE										-- 1.3.6.1.4.1.14703.2.3.2.7.1
		SYNTAX			OCTET STRING ( SIZE (728) )
		MAX-ACCESS		read-only
		STATUS			current
		DESCRIPTION		"Waveform2 (Unit Number1）"
		::= { pduWaveTable2 1 }
	
	--  pduWave2ValUnit2 -> pduWave2ValUnit63
	
	pduWave2ValUnit64	OBJECT-TYPE										-- 1.3.6.1.4.1.14703.2.3.2.7.64
		SYNTAX			OCTET STRING ( SIZE (728) )
		MAX-ACCESS		read-only
		STATUS			current
		DESCRIPTION		"Waveform2 (Unit Number64）"
		::= { pduWaveTable2 64 }
	
	-- Electric Current Waveform（Sampling Data from 359 data）＋Frequency ＋Voltage＋Phase Difference＋Electirc Current＋Voltage＋Electric Power
	
	pduWave3ValUnit1	OBJECT-TYPE										-- 1.3.6.1.4.1.14703.2.3.2.8.1
		SYNTAX			OCTET STRING ( SIZE (730) )
		MAX-ACCESS		read-only
		STATUS			current
		DESCRIPTION		"Waveform3 (Unit Number1）"
		::= { pduWaveTable3 1 }
	
	--  pduWave3ValUnit2 -> pduWave3ValUnit63
	
	pduWave3ValUnit64	OBJECT-TYPE										-- 1.3.6.1.4.1.14703.2.3.2.8.64
		SYNTAX			OCTET STRING ( SIZE (730) )
		MAX-ACCESS		read-only
		STATUS			current
		DESCRIPTION		"Waveform3 (Unit Number64）"
		::= { pduWaveTable3 64 }
END
