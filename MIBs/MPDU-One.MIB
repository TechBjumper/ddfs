NETPDU-MIB DEFINITIONS ::= BEGIN

IMPORTS
    enterprises, Counter,
    TimeTicks, Gauge                FROM RFC1155-SMI
    OBJECT-TYPE                     FROM RFC-1212
    sysUpTime, DisplayString	   FROM RFC1213-MIB
TRAP-TYPE                           FROM RFC-1215;

clever OBJECT IDENTIFIER ::= { enterprises 30966 }
cleverPDU OBJECT IDENTIFIER ::= { clever 10 }
mPDU OBJECT IDENTIFIER ::= { cleverPDU 2 }
deviceinfo OBJECT IDENTIFIER ::= { mPDU 1 }
totalinputinfo OBJECT IDENTIFIER ::= { mPDU 2 }
temhum OBJECT IDENTIFIER ::= { mPDU 3 }
outputCurrent OBJECT IDENTIFIER ::= { mPDU 4 }
outputPF OBJECT IDENTIFIER ::= { mPDU 5 }
outputEnergy OBJECT IDENTIFIER ::= { mPDU 6 }
outputswitch OBJECT IDENTIFIER ::= { mPDU 7 }
outputCurrentOne OBJECT IDENTIFIER ::= { outputCurrent 1 }
outputCurrentTwo OBJECT IDENTIFIER ::= { outputCurrent 2 }
outputCurrentThree OBJECT IDENTIFIER ::= { outputCurrent 3 }
outputPFOne OBJECT IDENTIFIER ::= { outputPF 1 }
outputPFTwo OBJECT IDENTIFIER ::= { outputPF 2 }
outputPFThree OBJECT IDENTIFIER ::= { outputPF 3 }
outputEnergyOne OBJECT IDENTIFIER ::= { outputEnergy 1 }
outputEnergyTwo OBJECT IDENTIFIER ::= { outputEnergy 2 }
outputEnergyThree OBJECT IDENTIFIER ::= { outputEnergy 3 }
outputswitchOne OBJECT IDENTIFIER ::= { outputswitch 1 }
outputswitchTwo OBJECT IDENTIFIER ::= { outputswitch 2 }
outputswitchThree OBJECT IDENTIFIER ::= { outputswitch 3 }
slaveoneinto OBJECT IDENTIFIER ::= { mPDU 8 }
slaveonetem OBJECT IDENTIFIER ::= { mPDU 9 }
slaveonecur OBJECT IDENTIFIER ::= { mPDU 10 }
slaveonepf OBJECT IDENTIFIER ::= { mPDU 11 }
slaveoneen OBJECT IDENTIFIER ::= { mPDU 12 }
slaveonesw OBJECT IDENTIFIER ::= { mPDU 13 }
slaveonecurA OBJECT IDENTIFIER ::= { slaveonecur 1 }
slaveonecurB OBJECT IDENTIFIER ::= { slaveonecur 2 }
slaveonecurC OBJECT IDENTIFIER ::= { slaveonecur 3 }
slaveonepfA OBJECT IDENTIFIER ::= { slaveonepf 1 }
slaveonepfB OBJECT IDENTIFIER ::= { slaveonepf 2 }
slaveonepfC OBJECT IDENTIFIER ::= { slaveonepf 3 }
slaveoneenA OBJECT IDENTIFIER ::= { slaveoneen 1 }
slaveoneenB OBJECT IDENTIFIER ::= { slaveoneen 2 }
slaveoneenC OBJECT IDENTIFIER ::= { slaveoneen 3 }
slaveoneswA OBJECT IDENTIFIER ::= { slaveonesw 1 }
slaveoneswB OBJECT IDENTIFIER ::= { slaveonesw 2 }
slaveoneswC OBJECT IDENTIFIER ::= { slaveonesw 3 }
slavetwointo OBJECT IDENTIFIER ::= { mPDU 14 }
slavetwotem OBJECT IDENTIFIER ::= { mPDU 15 }
slavetwocur OBJECT IDENTIFIER ::= { mPDU 16 }
slavetwopf OBJECT IDENTIFIER ::= { mPDU 17 }
slavetwoen OBJECT IDENTIFIER ::= { mPDU 18 }
slavetwosw OBJECT IDENTIFIER ::= { mPDU 19 }
slavetwocurA OBJECT IDENTIFIER ::= { slavetwocur 1 }
slavetwocurB OBJECT IDENTIFIER ::= { slavetwocur 2 }
slavetwocurC OBJECT IDENTIFIER ::= { slavetwocur 3 }
slavetwopfA OBJECT IDENTIFIER ::= { slavetwopf 1 }
slavetwopfB OBJECT IDENTIFIER ::= { slavetwopf 2 }
slavetwopfC OBJECT IDENTIFIER ::= { slavetwopf 3 }
slavetwoenA OBJECT IDENTIFIER ::= { slavetwoen 1 }
slavetwoenB OBJECT IDENTIFIER ::= { slavetwoen 2 }
slavetwoenC OBJECT IDENTIFIER ::= { slavetwoen 3 }
slavetwoswA OBJECT IDENTIFIER ::= { slavetwosw 1 }
slavetwoswB OBJECT IDENTIFIER ::= { slavetwosw 2 }
slavetwoswC OBJECT IDENTIFIER ::= { slavetwosw 3 }
slavethreeinto OBJECT IDENTIFIER ::= { mPDU 20 }
slavethreetem OBJECT IDENTIFIER ::= { mPDU 21 }
slavethreecur OBJECT IDENTIFIER ::= { mPDU 22 }
slavethreepf OBJECT IDENTIFIER ::= { mPDU 23 }
slavethreeen OBJECT IDENTIFIER ::= { mPDU 24 }
slavethreesw OBJECT IDENTIFIER ::= { mPDU 25 }
slavethreecurA OBJECT IDENTIFIER ::= { slavethreecur 1 }
slavethreecurB OBJECT IDENTIFIER ::= { slavethreecur 2 }
slavethreecurC OBJECT IDENTIFIER ::= { slavethreecur 3 }
slavethreepfA OBJECT IDENTIFIER ::= { slavethreepf 1 }
slavethreepfB OBJECT IDENTIFIER ::= { slavethreepf 2 }
slavethreepfC OBJECT IDENTIFIER ::= { slavethreepf 3 }
slavethreeenA OBJECT IDENTIFIER ::= { slavethreeen 1 }
slavethreeenB OBJECT IDENTIFIER ::= { slavethreeen 2 }
slavethreeenC OBJECT IDENTIFIER ::= { slavethreeen 3 }
slavethreeswA OBJECT IDENTIFIER ::= { slavethreesw 1 }
slavethreeswB OBJECT IDENTIFIER ::= { slavethreesw 2 }
slavethreeswC OBJECT IDENTIFIER ::= { slavethreesw 3 }
slavefourinto OBJECT IDENTIFIER ::= { mPDU 26 }
slavefourtem OBJECT IDENTIFIER ::= { mPDU 27 }
slavefourcur OBJECT IDENTIFIER ::= { mPDU 28 }
slavefourpf OBJECT IDENTIFIER ::= { mPDU 29 }
slavefouren OBJECT IDENTIFIER ::= { mPDU 30 }
slavefoursw OBJECT IDENTIFIER ::= { mPDU 31 }
slavefourcurA OBJECT IDENTIFIER ::= { slavefourcur 1 }
slavefourcurB OBJECT IDENTIFIER ::= { slavefourcur 2 }
slavefourcurC OBJECT IDENTIFIER ::= { slavefourcur 3 }
slavefourpfA OBJECT IDENTIFIER ::= { slavefourpf 1 }
slavefourpfB OBJECT IDENTIFIER ::= { slavefourpf 2 }
slavefourpfC OBJECT IDENTIFIER ::= { slavefourpf 3 }
slavefourenA OBJECT IDENTIFIER ::= { slavefouren 1 }
slavefourenB OBJECT IDENTIFIER ::= { slavefouren 2 }
slavefourenC OBJECT IDENTIFIER ::= { slavefouren 3 }
slavefourswA OBJECT IDENTIFIER ::= { slavefoursw 1 }
slavefourswB OBJECT IDENTIFIER ::= { slavefoursw 2 }
slavefourswC OBJECT IDENTIFIER ::= { slavefoursw 3 }

DeviceName OBJECT-TYPE
    SYNTAX DisplayString (SIZE (255))
    ACCESS read-write
    STATUS optional
    DESCRIPTION
            "device name."
    ::= { deviceinfo 1 }
DeviceAddress OBJECT-TYPE
    SYNTAX INTEGER (0..65535)
    ACCESS read-write
    STATUS optional
    DESCRIPTION
            "device address."
    ::= { deviceinfo 2 }
DeviceType  OBJECT-TYPE
    SYNTAX DisplayString (SIZE (255))
    ACCESS read-write
    STATUS optional
    DESCRIPTION
            "device type."
    ::= { deviceinfo 3 }
ModbusAddress OBJECT-TYPE
    SYNTAX INTEGER (0..65535)
    ACCESS read-write
    STATUS optional
    DESCRIPTION
            "modbus address."
    ::= { deviceinfo 4 }	
DeviceBaud  OBJECT-TYPE
    SYNTAX INTEGER (0..65535)
    ACCESS read-write
    STATUS optional
    DESCRIPTION
            "Device Baud."
    ::= { deviceinfo 5 }
	
MaterVoltageL1 OBJECT-TYPE
    SYNTAX INTEGER (0..65535)
    ACCESS read-write
    STATUS optional
    DESCRIPTION
            "total votage L1."
    ::= { totalinputinfo 1 }
MaterVoltageL2 OBJECT-TYPE
    SYNTAX INTEGER (0..65535)
    ACCESS read-write
    STATUS optional
    DESCRIPTION
            "total votage L2."
    ::= { totalinputinfo 2 }

MaterCurrentL1 OBJECT-TYPE
    SYNTAX INTEGER (0..65535)
    ACCESS read-write
    STATUS optional
    DESCRIPTION
            "total current L1.this value enlagrge 10 times."
    ::= { totalinputinfo 4 }	
MaterCurrentL2 OBJECT-TYPE
    SYNTAX INTEGER (0..65535)
    ACCESS read-write
    STATUS optional
    DESCRIPTION
            "total current L2.this value enlagrge 10 times."
    ::= { totalinputinfo 5 }
	
MaterPowerFactorL1 OBJECT-TYPE
    SYNTAX INTEGER (0..65535)
    ACCESS read-write
    STATUS optional
    DESCRIPTION
            "total power factor L1.this value enlagrge 100 times."
    ::= { totalinputinfo 7 }	
MaterPowerFactorL2 OBJECT-TYPE
    SYNTAX INTEGER (0..65535)
    ACCESS read-write
    STATUS optional
    DESCRIPTION
            "total power factor L2.this value enlagrge 100 times."
    ::= { totalinputinfo 8 }
	
MaterEnergyL1 OBJECT-TYPE
    SYNTAX INTEGER (0..65535)
    ACCESS read-write
    STATUS optional
    DESCRIPTION
            "total energy L1..this value enlagrge 10 times."
    ::= { totalinputinfo 10 }	
MaterEnergyL2 OBJECT-TYPE
    SYNTAX INTEGER (0..65535)
    ACCESS read-write
    STATUS optional
    DESCRIPTION
            "total energy L2..this value enlagrge 10 times."
    ::= { totalinputinfo 11 }
	
MaterTemperatureOne OBJECT-TYPE
    SYNTAX INTEGER (0..65535)
    ACCESS read-write
    STATUS optional
    DESCRIPTION
            "Temperature One ."
    ::= { temhum 1 }										
MaterTemperatureTwo OBJECT-TYPE
    SYNTAX INTEGER (0..65535)
    ACCESS read-write
    STATUS optional
    DESCRIPTION
            "Temperature Two ."
    ::= { temhum 2 }
MaterHumidityOne OBJECT-TYPE
    SYNTAX INTEGER (0..65535)
    ACCESS read-write
    STATUS optional
    DESCRIPTION
            "Humidity One ."
    ::= { temhum 3 }										
MaterHumidityTwo OBJECT-TYPE
    SYNTAX INTEGER (0..65535)
    ACCESS read-write
    STATUS optional
    DESCRIPTION
            "Humidity Two ."
    ::= { temhum 4 }	
	
MaterOutputCurrent1 OBJECT-TYPE
    SYNTAX INTEGER (0..65535)
    ACCESS read-write
    STATUS optional
    DESCRIPTION
            "total current.this value enlagrge 10 times."
    ::= { outputCurrentOne 1 }	
MaterOutputCurrent2 OBJECT-TYPE
    SYNTAX INTEGER (0..65535)
    ACCESS read-write
    STATUS optional
    DESCRIPTION
            "total current.this value enlagrge 10 times."
    ::= { outputCurrentOne 2 }
MaterOutputCurrent3 OBJECT-TYPE
    SYNTAX INTEGER (0..65535)
    ACCESS read-write
    STATUS optional
    DESCRIPTION
            "total current.this value enlagrge 10 times."
    ::= { outputCurrentOne 3 }	
MaterOutputCurrent4 OBJECT-TYPE
    SYNTAX INTEGER (0..65535)
    ACCESS read-write
    STATUS optional
    DESCRIPTION
            "total current.this value enlagrge 10 times."
    ::= { outputCurrentOne 4 }	
MaterOutputCurrent5 OBJECT-TYPE
    SYNTAX INTEGER (0..65535)
    ACCESS read-write
    STATUS optional
    DESCRIPTION
            "total current.this value enlagrge 10 times."
    ::= { outputCurrentOne 5 }	
MaterOutputCurrent6 OBJECT-TYPE
    SYNTAX INTEGER (0..65535)
    ACCESS read-write
    STATUS optional
    DESCRIPTION
            "total current.this value enlagrge 10 times."
    ::= { outputCurrentOne 6 }
MaterOutputCurrent7 OBJECT-TYPE
    SYNTAX INTEGER (0..65535)
    ACCESS read-write
    STATUS optional
    DESCRIPTION
            "total current.this value enlagrge 10 times."
    ::= { outputCurrentOne 7 }	
MaterOutputCurrent8 OBJECT-TYPE
    SYNTAX INTEGER (0..65535)
    ACCESS read-write
    STATUS optional
    DESCRIPTION
            "total current.this value enlagrge 10 times."
    ::= { outputCurrentOne 8 }
			
MaterOutputCurrent9 OBJECT-TYPE
    SYNTAX INTEGER (0..65535)
    ACCESS read-write
    STATUS optional
    DESCRIPTION
            "total current.this value enlagrge 10 times."
    ::= { outputCurrentTwo 1 }	
MaterOutputCurrent10 OBJECT-TYPE
    SYNTAX INTEGER (0..65535)
    ACCESS read-write
    STATUS optional
    DESCRIPTION
            "total current.this value enlagrge 10 times."
    ::= { outputCurrentTwo 2 }
MaterOutputCurrent11 OBJECT-TYPE
    SYNTAX INTEGER (0..65535)
    ACCESS read-write
    STATUS optional
    DESCRIPTION
            "total current.this value enlagrge 10 times."
    ::= { outputCurrentTwo 3 }	
MaterOutputCurrent12 OBJECT-TYPE
    SYNTAX INTEGER (0..65535)
    ACCESS read-write
    STATUS optional
    DESCRIPTION
            "total current.this value enlagrge 10 times."
    ::= { outputCurrentTwo 4 }	
MaterOutputCurrent13 OBJECT-TYPE
    SYNTAX INTEGER (0..65535)
    ACCESS read-write
    STATUS optional
    DESCRIPTION
            "total current.this value enlagrge 10 times."
    ::= { outputCurrentTwo 5 }	
MaterOutputCurrent14 OBJECT-TYPE
    SYNTAX INTEGER (0..65535)
    ACCESS read-write
    STATUS optional
    DESCRIPTION
            "total current.this value enlagrge 10 times."
    ::= { outputCurrentTwo 6 }
MaterOutputCurrent15 OBJECT-TYPE
    SYNTAX INTEGER (0..65535)
    ACCESS read-write
    STATUS optional
    DESCRIPTION
            "total current.this value enlagrge 10 times."
    ::= { outputCurrentTwo 7 }	
MaterOutputCurrent16 OBJECT-TYPE
    SYNTAX INTEGER (0..65535)
    ACCESS read-write
    STATUS optional
    DESCRIPTION
            "total current.this value enlagrge 10 times."
    ::= { outputCurrentTwo 8 }
		
MaterOutputCurrent17 OBJECT-TYPE
    SYNTAX INTEGER (0..65535)
    ACCESS read-write
    STATUS optional
    DESCRIPTION
            "total current.this value enlagrge 10 times."
    ::= { outputCurrentThree 1 }	
MaterOutputCurrent18 OBJECT-TYPE
    SYNTAX INTEGER (0..65535)
    ACCESS read-write
    STATUS optional
    DESCRIPTION
            "total current.this value enlagrge 10 times."
    ::= { outputCurrentThree 2 }
MaterOutputCurrent19 OBJECT-TYPE
    SYNTAX INTEGER (0..65535)
    ACCESS read-write
    STATUS optional
    DESCRIPTION
            "total current.this value enlagrge 10 times."
    ::= { outputCurrentThree 3 }	
MaterOutputCurrent20 OBJECT-TYPE
    SYNTAX INTEGER (0..65535)
    ACCESS read-write
    STATUS optional
    DESCRIPTION
            "total current.this value enlagrge 10 times."
    ::= { outputCurrentThree 4 }
		
MaterOutputCurrent21 OBJECT-TYPE
    SYNTAX INTEGER (0..65535)
    ACCESS read-write
    STATUS optional
    DESCRIPTION
            "total current.this value enlagrge 10 times."
    ::= { outputCurrentThree 5 }	
MaterOutputCurrent22 OBJECT-TYPE
    SYNTAX INTEGER (0..65535)
    ACCESS read-write
    STATUS optional
    DESCRIPTION
            "total current.this value enlagrge 10 times."
    ::= { outputCurrentThree 6 }
MaterOutputCurrent23 OBJECT-TYPE
    SYNTAX INTEGER (0..65535)
    ACCESS read-write
    STATUS optional
    DESCRIPTION
            "total current.this value enlagrge 10 times."
    ::= { outputCurrentThree 7 }	
MaterOutputCurrent24 OBJECT-TYPE
    SYNTAX INTEGER (0..65535)
    ACCESS read-write
    STATUS optional
    DESCRIPTION
            "total current.this value enlagrge 10 times."
    ::= { outputCurrentThree 8 }													
	
MaterOutputPF1 OBJECT-TYPE
    SYNTAX INTEGER (0..65535)
    ACCESS read-write
    STATUS optional
    DESCRIPTION
            "power factor.this value enlagrge 100 times."
    ::= { outputPFOne 1 }	
MaterOutputPF2 OBJECT-TYPE
    SYNTAX INTEGER (0..65535)
    ACCESS read-write
    STATUS optional
    DESCRIPTION
            "power factor.this value enlagrge 100 times."
    ::= { outputPFOne 2 }
MaterOutputPF3 OBJECT-TYPE
    SYNTAX INTEGER (0..65535)
    ACCESS read-write
    STATUS optional
    DESCRIPTION
            "power factor.this value enlagrge 100 times."
    ::= { outputPFOne 3 }
MaterOutputPF4 OBJECT-TYPE
    SYNTAX INTEGER (0..65535)
    ACCESS read-write
    STATUS optional
    DESCRIPTION
            "power factor.this value enlagrge 100 times."
    ::= { outputPFOne 4 }
MaterOutputPF5 OBJECT-TYPE
    SYNTAX INTEGER (0..65535)
    ACCESS read-write
    STATUS optional
    DESCRIPTION
            "power factor.this value enlagrge 100 times."
    ::= { outputPFOne 5 }	
MaterOutputPF6 OBJECT-TYPE
    SYNTAX INTEGER (0..65535)
    ACCESS read-write
    STATUS optional
    DESCRIPTION
            "power factor.this value enlagrge 100 times."
    ::= { outputPFOne 6 }
MaterOutputPF7 OBJECT-TYPE
    SYNTAX INTEGER (0..65535)
    ACCESS read-write
    STATUS optional
    DESCRIPTION
            "power factor.this value enlagrge 100 times."
    ::= { outputPFOne 7 }
MaterOutputPF8 OBJECT-TYPE
    SYNTAX INTEGER (0..65535)
    ACCESS read-write
    STATUS optional
    DESCRIPTION
            "power factor.this value enlagrge 100 times."
    ::= { outputPFOne 8 }
		
MaterOutputPF9 OBJECT-TYPE
    SYNTAX INTEGER (0..65535)
    ACCESS read-write
    STATUS optional
    DESCRIPTION
            "power factor.this value enlagrge 100 times."
    ::= { outputPFTwo 1 }	
MaterOutputPF10 OBJECT-TYPE
    SYNTAX INTEGER (0..65535)
    ACCESS read-write
    STATUS optional
    DESCRIPTION
            "power factor.this value enlagrge 100 times."
    ::= { outputPFTwo 2 }
MaterOutputPF11 OBJECT-TYPE
    SYNTAX INTEGER (0..65535)
    ACCESS read-write
    STATUS optional
    DESCRIPTION
            "power factor.this value enlagrge 100 times."
    ::= { outputPFTwo 3 }
MaterOutputPF12 OBJECT-TYPE
    SYNTAX INTEGER (0..65535)
    ACCESS read-write
    STATUS optional
    DESCRIPTION
            "power factor.this value enlagrge 100 times."
    ::= { outputPFTwo 4 }
MaterOutputPF13 OBJECT-TYPE
    SYNTAX INTEGER (0..65535)
    ACCESS read-write
    STATUS optional
    DESCRIPTION
            "power factor.this value enlagrge 100 times."
    ::= { outputPFTwo 5 }	
MaterOutputPF14 OBJECT-TYPE
    SYNTAX INTEGER (0..65535)
    ACCESS read-write
    STATUS optional
    DESCRIPTION
            "power factor.this value enlagrge 100 times."
    ::= { outputPFTwo 6 }
MaterOutputPF15 OBJECT-TYPE
    SYNTAX INTEGER (0..65535)
    ACCESS read-write
    STATUS optional
    DESCRIPTION
            "power factor.this value enlagrge 100 times."
    ::= { outputPFTwo 7 }
MaterOutputPF16 OBJECT-TYPE
    SYNTAX INTEGER (0..65535)
    ACCESS read-write
    STATUS optional
    DESCRIPTION
            "power factor.this value enlagrge 100 times."
    ::= { outputPFTwo 8 }
		
MaterOutputPF17 OBJECT-TYPE
    SYNTAX INTEGER (0..65535)
    ACCESS read-write
    STATUS optional
    DESCRIPTION
            "power factor.this value enlagrge 100 times."
    ::= { outputPFThree 1 }	
MaterOutputPF18 OBJECT-TYPE
    SYNTAX INTEGER (0..65535)
    ACCESS read-write
    STATUS optional
    DESCRIPTION
            "power factor.this value enlagrge 100 times."
    ::= { outputPFThree 2 }
MaterOutputPF19 OBJECT-TYPE
    SYNTAX INTEGER (0..65535)
    ACCESS read-write
    STATUS optional
    DESCRIPTION
            "power factor.this value enlagrge 100 times."
    ::= { outputPFThree 3 }
MaterOutputPF20 OBJECT-TYPE
    SYNTAX INTEGER (0..65535)
    ACCESS read-write
    STATUS optional
    DESCRIPTION
            "power factor.this value enlagrge 100 times."
    ::= { outputPFThree 4 }
MaterOutputPF21 OBJECT-TYPE
    SYNTAX INTEGER (0..65535)
    ACCESS read-write
    STATUS optional
    DESCRIPTION
            "power factor.this value enlagrge 100 times."
    ::= { outputPFThree 5 }	
MaterOutputPF22 OBJECT-TYPE
    SYNTAX INTEGER (0..65535)
    ACCESS read-write
    STATUS optional
    DESCRIPTION
            "power factor.this value enlagrge 100 times."
    ::= { outputPFThree 6 }
MaterOutputPF23 OBJECT-TYPE
    SYNTAX INTEGER (0..65535)
    ACCESS read-write
    STATUS optional
    DESCRIPTION
            "power factor.this value enlagrge 100 times."
    ::= { outputPFThree 7 }
MaterOutputPF24 OBJECT-TYPE
    SYNTAX INTEGER (0..65535)
    ACCESS read-write
    STATUS optional
    DESCRIPTION
            "power factor.this value enlagrge 100 times."
    ::= { outputPFThree 8 }	
	
MaterOutputEnergy1 OBJECT-TYPE
    SYNTAX INTEGER (0..65535)
    ACCESS read-write
    STATUS optional
    DESCRIPTION
            "Output energy.this value enlagrge 10 times"
    ::= { outputEnergyOne 1 }	
MaterOutputEnergy2 OBJECT-TYPE
    SYNTAX INTEGER (0..65535)
    ACCESS read-write
    STATUS optional
    DESCRIPTION
            "Output energy.this value enlagrge 10 times"
    ::= { outputEnergyOne 2 }
MaterOutputEnergy3 OBJECT-TYPE
    SYNTAX INTEGER (0..65535)
    ACCESS read-write
    STATUS optional
    DESCRIPTION
            "Output energy.this value enlagrge 10 times"
    ::= { outputEnergyOne 3 }
MaterOutputEnergy4 OBJECT-TYPE
    SYNTAX INTEGER (0..65535)
    ACCESS read-write
    STATUS optional
    DESCRIPTION
            "Output energy.this value enlagrge 10 times"
    ::= { outputEnergyOne 4 }
MaterOutputEnergy5 OBJECT-TYPE
    SYNTAX INTEGER (0..65535)
    ACCESS read-write
    STATUS optional
    DESCRIPTION
            "Output energy.this value enlagrge 10 times"
    ::= { outputEnergyOne 5 }	
MaterOutputEnergy6 OBJECT-TYPE
    SYNTAX INTEGER (0..65535)
    ACCESS read-write
    STATUS optional
    DESCRIPTION
            "Output energy.this value enlagrge 10 times"
    ::= { outputEnergyOne 6 }
MaterOutputEnergy7 OBJECT-TYPE
    SYNTAX INTEGER (0..65535)
    ACCESS read-write
    STATUS optional
    DESCRIPTION
            "Output energy.this value enlagrge 10 times"
    ::= { outputEnergyOne 7 }
MaterOutputEnergy8 OBJECT-TYPE
    SYNTAX INTEGER (0..65535)
    ACCESS read-write
    STATUS optional
    DESCRIPTION
            "Output energy.this value enlagrge 10 times"
    ::= { outputEnergyOne 8 }	
		
MaterOutputEnergy9 OBJECT-TYPE
    SYNTAX INTEGER (0..65535)
    ACCESS read-write
    STATUS optional
    DESCRIPTION
            "Output energy.this value enlagrge 10 times"
    ::= { outputEnergyTwo 1 }	
MaterOutputEnergy10 OBJECT-TYPE
    SYNTAX INTEGER (0..65535)
    ACCESS read-write
    STATUS optional
    DESCRIPTION
            "Output energy.this value enlagrge 10 times"
    ::= { outputEnergyTwo 2 }
MaterOutputEnergy11 OBJECT-TYPE
    SYNTAX INTEGER (0..65535)
    ACCESS read-write
    STATUS optional
    DESCRIPTION
            "Output energy.this value enlagrge 10 times"
    ::= { outputEnergyTwo 3 }
MaterOutputEnergy12 OBJECT-TYPE
    SYNTAX INTEGER (0..65535)
    ACCESS read-write
    STATUS optional
    DESCRIPTION
            "Output energy.this value enlagrge 10 times"
    ::= { outputEnergyTwo 4 }
MaterOutputEnergy13 OBJECT-TYPE
    SYNTAX INTEGER (0..65535)
    ACCESS read-write
    STATUS optional
    DESCRIPTION
            "Output energy.this value enlagrge 10 times"
    ::= { outputEnergyTwo 5 }	
MaterOutputEnergy14 OBJECT-TYPE
    SYNTAX INTEGER (0..65535)
    ACCESS read-write
    STATUS optional
    DESCRIPTION
            "Output energy.this value enlagrge 10 times"
    ::= { outputEnergyTwo 6 }
MaterOutputEnergy15 OBJECT-TYPE
    SYNTAX INTEGER (0..65535)
    ACCESS read-write
    STATUS optional
    DESCRIPTION
            "Output energy.this value enlagrge 10 times"
    ::= { outputEnergyTwo 7 }
MaterOutputEnergy16 OBJECT-TYPE
    SYNTAX INTEGER (0..65535)
    ACCESS read-write
    STATUS optional
    DESCRIPTION
            "Output energy.this value enlagrge 10 times"
    ::= { outputEnergyTwo 8 }	
	
MaterOutputEnergy17 OBJECT-TYPE
    SYNTAX INTEGER (0..65535)
    ACCESS read-write
    STATUS optional
    DESCRIPTION
            "Output energy.this value enlagrge 10 times"
    ::= { outputEnergyThree 1 }	
MaterOutputEnergy18 OBJECT-TYPE
    SYNTAX INTEGER (0..65535)
    ACCESS read-write
    STATUS optional
    DESCRIPTION
            "Output energy.this value enlagrge 10 times"
    ::= { outputEnergyThree 2 }
MaterOutputEnergy19 OBJECT-TYPE
    SYNTAX INTEGER (0..65535)
    ACCESS read-write
    STATUS optional
    DESCRIPTION
            "Output energy.this value enlagrge 10 times"
    ::= { outputEnergyThree 3 }
MaterOutputEnergy20 OBJECT-TYPE
    SYNTAX INTEGER (0..65535)
    ACCESS read-write
    STATUS optional
    DESCRIPTION
            "Output energy.this value enlagrge 10 times"
    ::= { outputEnergyThree 4 }
MaterOutputEnergy21 OBJECT-TYPE
    SYNTAX INTEGER (0..65535)
    ACCESS read-write
    STATUS optional
    DESCRIPTION
            "Output energy.this value enlagrge 10 times"
    ::= { outputEnergyThree 5 }	
MaterOutputEnergy22 OBJECT-TYPE
    SYNTAX INTEGER (0..65535)
    ACCESS read-write
    STATUS optional
    DESCRIPTION
            "Output energy.this value enlagrge 10 times"
    ::= { outputEnergyThree 6 }
MaterOutputEnergy23 OBJECT-TYPE
    SYNTAX INTEGER (0..65535)
    ACCESS read-write
    STATUS optional
    DESCRIPTION
            "Output energy.this value enlagrge 10 times"
    ::= { outputEnergyThree 7 }
MaterOutputEnergy24  OBJECT-TYPE
    SYNTAX INTEGER (0..65535)
    ACCESS read-write
    STATUS optional
    DESCRIPTION
            "Output energy.this value enlagrge 10 times"
    ::= { outputEnergyThree 8 }	

MaterSwitch1 OBJECT-TYPE
    SYNTAX DisplayString (SIZE (255))
    ACCESS read-write
    STATUS optional
    DESCRIPTION
            "output switch 1 ."
    ::= { outputswitchOne 1 }
MaterSwitch2 OBJECT-TYPE
    SYNTAX DisplayString (SIZE (255))
    ACCESS read-write
    STATUS optional
    DESCRIPTION
            "output switch 2 ."
    ::= { outputswitchOne 2 }
MaterSwitch3 OBJECT-TYPE
    SYNTAX DisplayString (SIZE (255))
    ACCESS read-write
    STATUS optional
    DESCRIPTION
            "output switch 3 ."
    ::= { outputswitchOne 3 }
MaterSwitch4 OBJECT-TYPE
    SYNTAX DisplayString (SIZE (255))
    ACCESS read-write
    STATUS optional
    DESCRIPTION
            "output switch 4 ."
    ::= { outputswitchOne 4 }	
MaterSwitch5 OBJECT-TYPE
    SYNTAX DisplayString (SIZE (255))
    ACCESS read-write
    STATUS optional
    DESCRIPTION
            "output switch 5 ."
    ::= { outputswitchOne 5 }
MaterSwitch6 OBJECT-TYPE
    SYNTAX DisplayString (SIZE (255))
    ACCESS read-write
    STATUS optional
    DESCRIPTION
            "output switch 6 ."
    ::= { outputswitchOne 6 }
MaterSwitch7 OBJECT-TYPE
    SYNTAX DisplayString (SIZE (255))
    ACCESS read-write
    STATUS optional
    DESCRIPTION
            "output switch 7 ."
    ::= { outputswitchOne 7 }
MaterSwitch8 OBJECT-TYPE
    SYNTAX DisplayString (SIZE (255))
    ACCESS read-write
    STATUS optional
    DESCRIPTION
            "output switch 8 ."
    ::= { outputswitchOne 8 }	
		
MaterSwitch9 OBJECT-TYPE
    SYNTAX DisplayString (SIZE (255))
    ACCESS read-write
    STATUS optional
    DESCRIPTION
            "output switch 9 ."
    ::= { outputswitchTwo 1 }
MaterSwitch10 OBJECT-TYPE
    SYNTAX DisplayString (SIZE (255))
    ACCESS read-write
    STATUS optional
    DESCRIPTION
            "output switch 10 ."
    ::= { outputswitchTwo 2 }
MaterSwitch11 OBJECT-TYPE
    SYNTAX DisplayString (SIZE (255))
    ACCESS read-write
    STATUS optional
    DESCRIPTION
            "output switch 11 ."
    ::= { outputswitchTwo 3 }
MaterSwitch12 OBJECT-TYPE
    SYNTAX DisplayString (SIZE (255))
    ACCESS read-write
    STATUS optional
    DESCRIPTION
            "output switch 12 ."
    ::= { outputswitchTwo 4 }	
MaterSwitch13 OBJECT-TYPE
    SYNTAX DisplayString (SIZE (255))
    ACCESS read-write
    STATUS optional
    DESCRIPTION
            "output switch 13 ."
    ::= { outputswitchTwo 5 }
MaterSwitch14 OBJECT-TYPE
    SYNTAX DisplayString (SIZE (255))
    ACCESS read-write
    STATUS optional
    DESCRIPTION
            "output switch 14 ."
    ::= { outputswitchTwo 6 }
MaterSwitch15 OBJECT-TYPE
    SYNTAX DisplayString (SIZE (255))
    ACCESS read-write
    STATUS optional
    DESCRIPTION
            "output switch 15 ."
    ::= { outputswitchTwo 7 }
	
MaterSwitch16 OBJECT-TYPE
    SYNTAX DisplayString (SIZE (255))
    ACCESS read-write
    STATUS optional
    DESCRIPTION
            "output switch 16 ."
    ::= { outputswitchTwo 8 }	
MaterSwitch17 OBJECT-TYPE
    SYNTAX DisplayString (SIZE (255))
    ACCESS read-write
    STATUS optional
    DESCRIPTION
            " output switch 17 ."
    ::= { outputswitchThree 1 }
MaterSwitch18 OBJECT-TYPE
    SYNTAX DisplayString (SIZE (255))
    ACCESS read-write
    STATUS optional
    DESCRIPTION
            "output switch 18 ."
    ::= { outputswitchThree 2 }
MaterSwitch19 OBJECT-TYPE
    SYNTAX DisplayString (SIZE (255))
    ACCESS read-write
    STATUS optional
    DESCRIPTION
            "output switch 19 ."
    ::= { outputswitchThree 3 }
MaterSwitch20 OBJECT-TYPE
    SYNTAX DisplayString (SIZE (255))
    ACCESS read-write
    STATUS optional
    DESCRIPTION
            "output switch 20 ."
    ::= { outputswitchThree 4 }	
MaterSwitch21 OBJECT-TYPE
    SYNTAX DisplayString (SIZE (255))
    ACCESS read-write
    STATUS optional
    DESCRIPTION
            "output switch 21 ."
    ::= { outputswitchThree 5 }
MaterSwitch22 OBJECT-TYPE
    SYNTAX DisplayString (SIZE (255))
    ACCESS read-write
    STATUS optional
    DESCRIPTION
            "output switch 22 ."
    ::= { outputswitchThree 6 }
MaterSwitch23 OBJECT-TYPE
    SYNTAX DisplayString (SIZE (255))
    ACCESS read-write
    STATUS optional
    DESCRIPTION
            "output switch 23 ."
    ::= { outputswitchThree 7}
MaterSwitch24 OBJECT-TYPE
    SYNTAX DisplayString (SIZE (255))
    ACCESS read-write
    STATUS optional
    DESCRIPTION
            "output switch 24 ."
    ::= { outputswitchThree 8 }					

Slave1VoltageL1 OBJECT-TYPE
    SYNTAX INTEGER (0..65535)
    ACCESS read-write
    STATUS optional
    DESCRIPTION
            "slave 1  votage L1."
    ::= { slaveoneinto 1 }
Slave1VoltageL2 OBJECT-TYPE
    SYNTAX INTEGER (0..65535)
    ACCESS read-write
    STATUS optional
    DESCRIPTION
            "slave 1  votage L2."
    ::= { slaveoneinto 2 }

Slave1CurrentL1 OBJECT-TYPE
    SYNTAX INTEGER (0..65535)
    ACCESS read-write
    STATUS optional
    DESCRIPTION
            "slave 1  current L1.this value enlagrge 10 times."
    ::= { slaveoneinto 4 }	
Slave1CurrentL2 OBJECT-TYPE
    SYNTAX INTEGER (0..65535)
    ACCESS read-write
    STATUS optional
    DESCRIPTION
            "slave 1  current L2.this value enlagrge 10 times."
    ::= { slaveoneinto 5 }

Slave1PowerFactorL1 OBJECT-TYPE
    SYNTAX INTEGER (0..65535)
    ACCESS read-write
    STATUS optional
    DESCRIPTION
            "slave 1  power factor L1.this value enlagrge 100 times."
    ::= { slaveoneinto 7 }	
Slave1PowerFactorL2 OBJECT-TYPE
    SYNTAX INTEGER (0..65535)
    ACCESS read-write
    STATUS optional
    DESCRIPTION
            "slave 1  power factor L2.this value enlagrge 100 times."
    ::= { slaveoneinto 8 }

Slave1EnergyL1 OBJECT-TYPE
    SYNTAX INTEGER (0..65535)
    ACCESS read-write
    STATUS optional
    DESCRIPTION
            "slave 1  energy L1..this value enlagrge 10 times."
    ::= { slaveoneinto 10 }	
Slave1EnergyL2 OBJECT-TYPE
    SYNTAX INTEGER (0..65535)
    ACCESS read-write
    STATUS optional
    DESCRIPTION
            "slave 1  energy L2..this value enlagrge 10 times."
    ::= { slaveoneinto 11 }
	
Slave1TemperatureOne OBJECT-TYPE
    SYNTAX INTEGER (0..65535)
    ACCESS read-write
    STATUS optional
    DESCRIPTION
            "slave 1 Temperature One ."
    ::= { slaveonetem 1 }										
Slave1TemperatureTwo OBJECT-TYPE
    SYNTAX INTEGER (0..65535)
    ACCESS read-write
    STATUS optional
    DESCRIPTION
            "slave 1 Temperature Two ."
    ::= { slaveonetem 2 }
Slave1HumidityOne OBJECT-TYPE
    SYNTAX INTEGER (0..65535)
    ACCESS read-write
    STATUS optional
    DESCRIPTION
            "slave 1 Humidity One ."
    ::= { slaveonetem 3 }										
Slave1HumidityTwo OBJECT-TYPE
    SYNTAX INTEGER (0..65535)
    ACCESS read-write
    STATUS optional
    DESCRIPTION
            "slave 1 Humidity Two ."
    ::= { slaveonetem 4 }	
	
Slave1OutputCurrent1 OBJECT-TYPE
    SYNTAX INTEGER (0..65535)
    ACCESS read-write
    STATUS optional
    DESCRIPTION
            "slave 1 current.this value enlagrge 10 times."
    ::= { slaveonecurA 1 }	
Slave1OutputCurrent2 OBJECT-TYPE
    SYNTAX INTEGER (0..65535)
    ACCESS read-write
    STATUS optional
    DESCRIPTION
            "slave 1 current.this value enlagrge 10 times."
    ::= { slaveonecurA 2 }
Slave1OutputCurrent3 OBJECT-TYPE
    SYNTAX INTEGER (0..65535)
    ACCESS read-write
    STATUS optional
    DESCRIPTION
            "slave 1 current.this value enlagrge 10 times."
    ::= { slaveonecurA 3 }	
Slave1OutputCurrent4 OBJECT-TYPE
    SYNTAX INTEGER (0..65535)
    ACCESS read-write
    STATUS optional
    DESCRIPTION
            "slave 1 current.this value enlagrge 10 times."
    ::= { slaveonecurA 4 }	
Slave1OutputCurrent5 OBJECT-TYPE
    SYNTAX INTEGER (0..65535)
    ACCESS read-write
    STATUS optional
    DESCRIPTION
            "slave 1 current.this value enlagrge 10 times."
    ::= { slaveonecurA 5 }	
Slave1OutputCurrent6 OBJECT-TYPE
    SYNTAX INTEGER (0..65535)
    ACCESS read-write
    STATUS optional
    DESCRIPTION
            "slave 1 current.this value enlagrge 10 times."
    ::= { slaveonecurA 6 }
Slave1OutputCurrent7 OBJECT-TYPE
    SYNTAX INTEGER (0..65535)
    ACCESS read-write
    STATUS optional
    DESCRIPTION
            "slave 1 current.this value enlagrge 10 times."
    ::= { slaveonecurA 7 }	
Slave1OutputCurrent8 OBJECT-TYPE
    SYNTAX INTEGER (0..65535)
    ACCESS read-write
    STATUS optional
    DESCRIPTION
            "slave 1 current.this value enlagrge 10 times."
    ::= { slaveonecurA 8 }
			
Slave1OutputCurrent9 OBJECT-TYPE
    SYNTAX INTEGER (0..65535)
    ACCESS read-write
    STATUS optional
    DESCRIPTION
            "slave 1 current.this value enlagrge 10 times."
    ::= { slaveonecurB 1 }	
Slave1OutputCurrent10 OBJECT-TYPE
    SYNTAX INTEGER (0..65535)
    ACCESS read-write
    STATUS optional
    DESCRIPTION
            "slave 1 current.this value enlagrge 10 times."
    ::= { slaveonecurB 2 }
Slave1OutputCurrent11 OBJECT-TYPE
    SYNTAX INTEGER (0..65535)
    ACCESS read-write
    STATUS optional
    DESCRIPTION
            "slave 1 current.this value enlagrge 10 times."
    ::= { slaveonecurB 3 }	
Slave1OutputCurrent12 OBJECT-TYPE
    SYNTAX INTEGER (0..65535)
    ACCESS read-write
    STATUS optional
    DESCRIPTION
            "slave 1 current.this value enlagrge 10 times."
    ::= { slaveonecurB 4 }	
Slave1OutputCurrent13 OBJECT-TYPE
    SYNTAX INTEGER (0..65535)
    ACCESS read-write
    STATUS optional
    DESCRIPTION
            "slave 1 current.this value enlagrge 10 times."
    ::= { slaveonecurB 5 }	
Slave1OutputCurrent14 OBJECT-TYPE
    SYNTAX INTEGER (0..65535)
    ACCESS read-write
    STATUS optional
    DESCRIPTION
            "slave 1 current.this value enlagrge 10 times."
    ::= { slaveonecurB 6 }
Slave1OutputCurrent15 OBJECT-TYPE
    SYNTAX INTEGER (0..65535)
    ACCESS read-write
    STATUS optional
    DESCRIPTION
            "slave 1 current.this value enlagrge 10 times."
    ::= { slaveonecurB 7 }	
Slave1OutputCurrent16 OBJECT-TYPE
    SYNTAX INTEGER (0..65535)
    ACCESS read-write
    STATUS optional
    DESCRIPTION
            "slave 1 current.this value enlagrge 10 times."
    ::= { slaveonecurB 8 }
		
Slave1OutputCurrent17 OBJECT-TYPE
    SYNTAX INTEGER (0..65535)
    ACCESS read-write
    STATUS optional
    DESCRIPTION
            "slave 1 current.this value enlagrge 10 times."
    ::= { slaveonecurC 1 }	
Slave1OutputCurrent18 OBJECT-TYPE
    SYNTAX INTEGER (0..65535)
    ACCESS read-write
    STATUS optional
    DESCRIPTION
            "slave 1 current.this value enlagrge 10 times."
    ::= { slaveonecurC 2 }
Slave1OutputCurrent19 OBJECT-TYPE
    SYNTAX INTEGER (0..65535)
    ACCESS read-write
    STATUS optional
    DESCRIPTION
            "slave 1 current.this value enlagrge 10 times."
    ::= { slaveonecurC 3 }	
Slave1OutputCurrent20 OBJECT-TYPE
    SYNTAX INTEGER (0..65535)
    ACCESS read-write
    STATUS optional
    DESCRIPTION
            "slave 1 current.this value enlagrge 10 times."
    ::= { slaveonecurC 4 }
		
Slave1OutputCurrent21 OBJECT-TYPE
    SYNTAX INTEGER (0..65535)
    ACCESS read-write
    STATUS optional
    DESCRIPTION
            "slave 1 current.this value enlagrge 10 times."
    ::= { slaveonecurC 5 }	
Slave1OutputCurrent22 OBJECT-TYPE
    SYNTAX INTEGER (0..65535)
    ACCESS read-write
    STATUS optional
    DESCRIPTION
            "slave 1 current.this value enlagrge 10 times."
    ::= { slaveonecurC 6 }
Slave1OutputCurrent23 OBJECT-TYPE
    SYNTAX INTEGER (0..65535)
    ACCESS read-write
    STATUS optional
    DESCRIPTION
            "slave 1 current.this value enlagrge 10 times."
    ::= { slaveonecurC 7 }	
Slave1OutputCurrent24 OBJECT-TYPE
    SYNTAX INTEGER (0..65535)
    ACCESS read-write
    STATUS optional
    DESCRIPTION
            "slave 1 current.this value enlagrge 10 times."
    ::= { slaveonecurC 8 }													
	
Slave1OutputPF1 OBJECT-TYPE
    SYNTAX INTEGER (0..65535)
    ACCESS read-write
    STATUS optional
    DESCRIPTION
            "slave 1 power factor.this value enlagrge 100 times."
    ::= { slaveonepfA 1 }	
Slave1OutputPF2 OBJECT-TYPE
    SYNTAX INTEGER (0..65535)
    ACCESS read-write
    STATUS optional
    DESCRIPTION
            "slave 1 power factor.this value enlagrge 100 times."
    ::= { slaveonepfA 2 }
Slave1OutputPF3 OBJECT-TYPE
    SYNTAX INTEGER (0..65535)
    ACCESS read-write
    STATUS optional
    DESCRIPTION
            "slave 1 power factor.this value enlagrge 100 times."
    ::= { slaveonepfA 3 }
Slave1OutputPF4 OBJECT-TYPE
    SYNTAX INTEGER (0..65535)
    ACCESS read-write
    STATUS optional
    DESCRIPTION
            "slave 1 power factor.this value enlagrge 100 times."
    ::= { slaveonepfA 4 }
Slave1OutputPF5 OBJECT-TYPE
    SYNTAX INTEGER (0..65535)
    ACCESS read-write
    STATUS optional
    DESCRIPTION
            "slave 1 power factor.this value enlagrge 100 times."
    ::= { slaveonepfA 5 }	
Slave1OutputPF6 OBJECT-TYPE
    SYNTAX INTEGER (0..65535)
    ACCESS read-write
    STATUS optional
    DESCRIPTION
            "slave 1 power factor.this value enlagrge 100 times."
    ::= { slaveonepfA 6 }
Slave1OutputPF7 OBJECT-TYPE
    SYNTAX INTEGER (0..65535)
    ACCESS read-write
    STATUS optional
    DESCRIPTION
            "slave 1 power factor.this value enlagrge 100 times."
    ::= { slaveonepfA 7 }
Slave1OutputPF8 OBJECT-TYPE
    SYNTAX INTEGER (0..65535)
    ACCESS read-write
    STATUS optional
    DESCRIPTION
            "slave 1 power factor.this value enlagrge 100 times."
    ::= { slaveonepfA 8 }
		
Slave1OutputPF9 OBJECT-TYPE
    SYNTAX INTEGER (0..65535)
    ACCESS read-write
    STATUS optional
    DESCRIPTION
            "slave 1 power factor.this value enlagrge 100 times."
    ::= { slaveonepfB 1 }	
Slave1OutputPF10 OBJECT-TYPE
    SYNTAX INTEGER (0..65535)
    ACCESS read-write
    STATUS optional
    DESCRIPTION
            "slave 1 power factor.this value enlagrge 100 times."
    ::= { slaveonepfB 2 }
Slave1OutputPF11 OBJECT-TYPE
    SYNTAX INTEGER (0..65535)
    ACCESS read-write
    STATUS optional
    DESCRIPTION
            "slave 1 power factor.this value enlagrge 100 times."
    ::= { slaveonepfB 3 }
Slave1OutputPF12 OBJECT-TYPE
    SYNTAX INTEGER (0..65535)
    ACCESS read-write
    STATUS optional
    DESCRIPTION
            "slave 1 power factor.this value enlagrge 100 times."
    ::= { slaveonepfB 4 }
Slave1OutputPF13 OBJECT-TYPE
    SYNTAX INTEGER (0..65535)
    ACCESS read-write
    STATUS optional
    DESCRIPTION
            "slave 1 power factor.this value enlagrge 100 times."
    ::= { slaveonepfB 5 }	
Slave1OutputPF14 OBJECT-TYPE
    SYNTAX INTEGER (0..65535)
    ACCESS read-write
    STATUS optional
    DESCRIPTION
            "slave 1 power factor.this value enlagrge 100 times."
    ::= { slaveonepfB 6 }
Slave1OutputPF15 OBJECT-TYPE
    SYNTAX INTEGER (0..65535)
    ACCESS read-write
    STATUS optional
    DESCRIPTION
            "slave 1 power factor.this value enlagrge 100 times."
    ::= { slaveonepfB 7 }
Slave1OutputPF16 OBJECT-TYPE
    SYNTAX INTEGER (0..65535)
    ACCESS read-write
    STATUS optional
    DESCRIPTION
            "slave 1 power factor.this value enlagrge 100 times."
    ::= { slaveonepfB 8 }
		
Slave1OutputPF17 OBJECT-TYPE
    SYNTAX INTEGER (0..65535)
    ACCESS read-write
    STATUS optional
    DESCRIPTION
            "slave 1 power factor.this value enlagrge 100 times."
    ::= { slaveonepfC 1 }	
Slave1OutputPF18 OBJECT-TYPE
    SYNTAX INTEGER (0..65535)
    ACCESS read-write
    STATUS optional
    DESCRIPTION
            "slave 1 power factor.this value enlagrge 100 times."
    ::= { slaveonepfC 2 }
Slave1OutputPF19 OBJECT-TYPE
    SYNTAX INTEGER (0..65535)
    ACCESS read-write
    STATUS optional
    DESCRIPTION
            "slave 1 power factor.this value enlagrge 100 times."
    ::= { slaveonepfC 3 }
Slave1OutputPF20 OBJECT-TYPE
    SYNTAX INTEGER (0..65535)
    ACCESS read-write
    STATUS optional
    DESCRIPTION
            "slave 1 power factor.this value enlagrge 100 times."
    ::= { slaveonepfC 4 }
Slave1OutputPF21 OBJECT-TYPE
    SYNTAX INTEGER (0..65535)
    ACCESS read-write
    STATUS optional
    DESCRIPTION
            "slave 1 power factor.this value enlagrge 100 times."
    ::= { slaveonepfC 5 }	
Slave1OutputPF22 OBJECT-TYPE
    SYNTAX INTEGER (0..65535)
    ACCESS read-write
    STATUS optional
    DESCRIPTION
            "slave 1 power factor.this value enlagrge 100 times."
    ::= { slaveonepfC 6 }
Slave1OutputPF23 OBJECT-TYPE
    SYNTAX INTEGER (0..65535)
    ACCESS read-write
    STATUS optional
    DESCRIPTION
            "slave 1 power factor.this value enlagrge 100 times."
    ::= { slaveonepfC 7 }
Slave1OutputPF24 OBJECT-TYPE
    SYNTAX INTEGER (0..65535)
    ACCESS read-write
    STATUS optional
    DESCRIPTION
            "slave 1 power factor.this value enlagrge 100 times."
    ::= { slaveonepfC 8 }	
	
Slave1OutputEnergy1 OBJECT-TYPE
    SYNTAX INTEGER (0..65535)
    ACCESS read-write
    STATUS optional
    DESCRIPTION
            "slave 1 Output energy.this value enlagrge 10 times"
    ::= { slaveoneenA 1 }	
Slave1OutputEnergy2 OBJECT-TYPE
    SYNTAX INTEGER (0..65535)
    ACCESS read-write
    STATUS optional
    DESCRIPTION
            "slave 1 Output energy.this value enlagrge 10 times"
    ::= { slaveoneenA 2 }
Slave1OutputEnergy3 OBJECT-TYPE
    SYNTAX INTEGER (0..65535)
    ACCESS read-write
    STATUS optional
    DESCRIPTION
            "slave 1 Output energy.this value enlagrge 10 times"
    ::= { slaveoneenA 3 }
Slave1OutputEnergy4 OBJECT-TYPE
    SYNTAX INTEGER (0..65535)
    ACCESS read-write
    STATUS optional
    DESCRIPTION
            "slave 1 Output energy.this value enlagrge 10 times"
    ::= { slaveoneenA 4 }
Slave1OutputEnergy5 OBJECT-TYPE
    SYNTAX INTEGER (0..65535)
    ACCESS read-write
    STATUS optional
    DESCRIPTION
            "slave 1 Output energy.this value enlagrge 10 times"
    ::= { slaveoneenA 5 }	
Slave1OutputEnergy6 OBJECT-TYPE
    SYNTAX INTEGER (0..65535)
    ACCESS read-write
    STATUS optional
    DESCRIPTION
            "slave 1 Output energy.this value enlagrge 10 times"
    ::= { slaveoneenA 6 }
Slave1OutputEnergy7 OBJECT-TYPE
    SYNTAX INTEGER (0..65535)
    ACCESS read-write
    STATUS optional
    DESCRIPTION
            "slave 1 Output energy.this value enlagrge 10 times"
    ::= { slaveoneenA 7 }
Slave1OutputEnergy8 OBJECT-TYPE
    SYNTAX INTEGER (0..65535)
    ACCESS read-write
    STATUS optional
    DESCRIPTION
            "slave 1 Output energy.this value enlagrge 10 times"
    ::= { slaveoneenA 8 }	
		
Slave1OutputEnergy9 OBJECT-TYPE
    SYNTAX INTEGER (0..65535)
    ACCESS read-write
    STATUS optional
    DESCRIPTION
            "slave 1 Output energy.this value enlagrge 10 times"
    ::= { slaveoneenB 1 }	
Slave1OutputEnergy10 OBJECT-TYPE
    SYNTAX INTEGER (0..65535)
    ACCESS read-write
    STATUS optional
    DESCRIPTION
            "slave 1 Output energy.this value enlagrge 10 times"
    ::= { slaveoneenB 2 }
Slave1OutputEnergy11 OBJECT-TYPE
    SYNTAX INTEGER (0..65535)
    ACCESS read-write
    STATUS optional
    DESCRIPTION
            "slave 1 Output energy.this value enlagrge 10 times"
    ::= { slaveoneenB 3 }
Slave1OutputEnergy12 OBJECT-TYPE
    SYNTAX INTEGER (0..65535)
    ACCESS read-write
    STATUS optional
    DESCRIPTION
            "slave 1 Output energy.this value enlagrge 10 times"
    ::= { slaveoneenB 4 }
Slave1OutputEnergy13 OBJECT-TYPE
    SYNTAX INTEGER (0..65535)
    ACCESS read-write
    STATUS optional
    DESCRIPTION
            "slave 1 Output energy.this value enlagrge 10 times"
    ::= { slaveoneenB 5 }	
Slave1OutputEnergy14 OBJECT-TYPE
    SYNTAX INTEGER (0..65535)
    ACCESS read-write
    STATUS optional
    DESCRIPTION
            "slave 1 Output energy.this value enlagrge 10 times"
    ::= { slaveoneenB 6 }
Slave1OutputEnergy15 OBJECT-TYPE
    SYNTAX INTEGER (0..65535)
    ACCESS read-write
    STATUS optional
    DESCRIPTION
            "slave 1 Output energy.this value enlagrge 10 times"
    ::= { slaveoneenB 7 }
Slave1OutputEnergy16 OBJECT-TYPE
    SYNTAX INTEGER (0..65535)
    ACCESS read-write
    STATUS optional
    DESCRIPTION
            "slave 1 Output energy.this value enlagrge 10 times"
    ::= { slaveoneenB 8 }	
	
Slave1OutputEnergy17 OBJECT-TYPE
    SYNTAX INTEGER (0..65535)
    ACCESS read-write
    STATUS optional
    DESCRIPTION
            "slave 1 Output energy.this value enlagrge 10 times"
    ::= { slaveoneenC 1 }	
Slave1OutputEnergy18 OBJECT-TYPE
    SYNTAX INTEGER (0..65535)
    ACCESS read-write
    STATUS optional
    DESCRIPTION
            "slave 1 Output energy.this value enlagrge 10 times"
    ::= { slaveoneenC 2 }
Slave1OutputEnergy19 OBJECT-TYPE
    SYNTAX INTEGER (0..65535)
    ACCESS read-write
    STATUS optional
    DESCRIPTION
            "slave 1 Output energy.this value enlagrge 10 times"
    ::= { slaveoneenC 3 }
Slave1OutputEnergy20 OBJECT-TYPE
    SYNTAX INTEGER (0..65535)
    ACCESS read-write
    STATUS optional
    DESCRIPTION
            "slave 1 Output energy.this value enlagrge 10 times"
    ::= { slaveoneenC 4 }
Slave1OutputEnergy21 OBJECT-TYPE
    SYNTAX INTEGER (0..65535)
    ACCESS read-write
    STATUS optional
    DESCRIPTION
            "slave 1 Output energy.this value enlagrge 10 times"
    ::= { slaveoneenC 5 }	
Slave1OutputEnergy22 OBJECT-TYPE
    SYNTAX INTEGER (0..65535)
    ACCESS read-write
    STATUS optional
    DESCRIPTION
            "slave 1 Output energy.this value enlagrge 10 times"
    ::= { slaveoneenC 6 }
Slave1OutputEnergy23 OBJECT-TYPE
    SYNTAX INTEGER (0..65535)
    ACCESS read-write
    STATUS optional
    DESCRIPTION
            "slave 1 Output energy.this value enlagrge 10 times"
    ::= { slaveoneenC 7 }
Slave1OutputEnergy24  OBJECT-TYPE
    SYNTAX INTEGER (0..65535)
    ACCESS read-write
    STATUS optional
    DESCRIPTION
            "slave 1 Output energy.this value enlagrge 10 times"
    ::= { slaveoneenC 8 }	

Slave1Switch1 OBJECT-TYPE
    SYNTAX DisplayString (SIZE (255))
    ACCESS read-write
    STATUS optional
    DESCRIPTION
            "slave 1 output switch 1 ."
    ::= { slaveoneswA 1 }
Slave1Switch2 OBJECT-TYPE
    SYNTAX DisplayString (SIZE (255))
    ACCESS read-write
    STATUS optional
    DESCRIPTION
            "slave 1 output switch 2 ."
    ::= { slaveoneswA 2 }
Slave1Switch3 OBJECT-TYPE
    SYNTAX DisplayString (SIZE (255))
    ACCESS read-write
    STATUS optional
    DESCRIPTION
            "slave 1 output switch 3 ."
    ::= { slaveoneswA 3 }
Slave1Switch4 OBJECT-TYPE
    SYNTAX DisplayString (SIZE (255))
    ACCESS read-write
    STATUS optional
    DESCRIPTION
            "slave 1 output switch 4 ."
    ::= { slaveoneswA 4 }	
Slave1Switch5 OBJECT-TYPE
    SYNTAX DisplayString (SIZE (255))
    ACCESS read-write
    STATUS optional
    DESCRIPTION
            "slave 1 output switch 5 ."
    ::= { slaveoneswA 5 }
Slave1Switch6 OBJECT-TYPE
    SYNTAX DisplayString (SIZE (255))
    ACCESS read-write
    STATUS optional
    DESCRIPTION
            "slave 1 output switch 6 ."
    ::= { slaveoneswA 6 }
Slave1Switch7 OBJECT-TYPE
    SYNTAX DisplayString (SIZE (255))
    ACCESS read-write
    STATUS optional
    DESCRIPTION
            "slave 1 output switch 7 ."
    ::= { slaveoneswA 7 }
Slave1Switch8 OBJECT-TYPE
    SYNTAX DisplayString (SIZE (255))
    ACCESS read-write
    STATUS optional
    DESCRIPTION
            "slave 1 output switch 8 ."
    ::= { slaveoneswA 8 }	
		
Slave1Switch9 OBJECT-TYPE
    SYNTAX DisplayString (SIZE (255))
    ACCESS read-write
    STATUS optional
    DESCRIPTION
            "slave 1 output switch 9 ."
    ::= { slaveoneswB 1 }
Slave1Switch10 OBJECT-TYPE
    SYNTAX DisplayString (SIZE (255))
    ACCESS read-write
    STATUS optional
    DESCRIPTION
            "slave 1 output switch 10 ."
    ::= { slaveoneswB 2 }
Slave1Switch11 OBJECT-TYPE
    SYNTAX DisplayString (SIZE (255))
    ACCESS read-write
    STATUS optional
    DESCRIPTION
            "slave 1 output switch 11 ."
    ::= { slaveoneswB 3 }
Slave1Switch12 OBJECT-TYPE
    SYNTAX DisplayString (SIZE (255))
    ACCESS read-write
    STATUS optional
    DESCRIPTION
            "slave 1 output switch 12 ."
    ::= { slaveoneswB 4 }	
Slave1Switch13 OBJECT-TYPE
    SYNTAX DisplayString (SIZE (255))
    ACCESS read-write
    STATUS optional
    DESCRIPTION
            "slave 1 output switch 13 ."
    ::= { slaveoneswB 5 }
Slave1Switch14 OBJECT-TYPE
    SYNTAX DisplayString (SIZE (255))
    ACCESS read-write
    STATUS optional
    DESCRIPTION
            "slave 1 output switch 14 ."
    ::= { slaveoneswB 6 }
Slave1Switch15 OBJECT-TYPE
    SYNTAX DisplayString (SIZE (255))
    ACCESS read-write
    STATUS optional
    DESCRIPTION
            "slave 1 output switch 15 ."
    ::= { slaveoneswB 7 }
	
Slave1Switch16 OBJECT-TYPE
    SYNTAX DisplayString (SIZE (255))
    ACCESS read-write
    STATUS optional
    DESCRIPTION
            "slave 1 output switch 16 ."
    ::= { slaveoneswB 8 }	
Slave1Switch17 OBJECT-TYPE
    SYNTAX DisplayString (SIZE (255))
    ACCESS read-write
    STATUS optional
    DESCRIPTION
            " slave 1 output switch 17 ."
    ::= { slaveoneswC 1 }
Slave1Switch18 OBJECT-TYPE
    SYNTAX DisplayString (SIZE (255))
    ACCESS read-write
    STATUS optional
    DESCRIPTION
            "slave 1 output switch 18 ."
    ::= { slaveoneswC 2 }
Slave1Switch19 OBJECT-TYPE
    SYNTAX DisplayString (SIZE (255))
    ACCESS read-write
    STATUS optional
    DESCRIPTION
            "slave 1 output switch 19 ."
    ::= { slaveoneswC 3 }
Slave1Switch20 OBJECT-TYPE
    SYNTAX DisplayString (SIZE (255))
    ACCESS read-write
    STATUS optional
    DESCRIPTION
            "slave 1 output switch 20 ."
    ::= { slaveoneswC 4 }	
Slave1Switch21 OBJECT-TYPE
    SYNTAX DisplayString (SIZE (255))
    ACCESS read-write
    STATUS optional
    DESCRIPTION
            "slave 1 output switch 21 ."
    ::= { slaveoneswC 5 }
Slave1Switch22 OBJECT-TYPE
    SYNTAX DisplayString (SIZE (255))
    ACCESS read-write
    STATUS optional
    DESCRIPTION
            "slave 1 output switch 22 ."
    ::= { slaveoneswC 6 }
Slave1Switch23 OBJECT-TYPE
    SYNTAX DisplayString (SIZE (255))
    ACCESS read-write
    STATUS optional
    DESCRIPTION
            "slave 1 output switch 23 ."
    ::= { slaveoneswC 7}
Slave1Switch24 OBJECT-TYPE
    SYNTAX DisplayString (SIZE (255))
    ACCESS read-write
    STATUS optional
    DESCRIPTION
            "slave 1 output switch 24 ."
    ::= { slaveoneswC 8 }
	
Slave2VoltageL1 OBJECT-TYPE
    SYNTAX INTEGER (0..65535)
    ACCESS read-write
    STATUS optional
    DESCRIPTION
            "slave 2  votage L1."
    ::= { slavetwointo 1 }
Slave2VoltageL2 OBJECT-TYPE
    SYNTAX INTEGER (0..65535)
    ACCESS read-write
    STATUS optional
    DESCRIPTION
            "slave 2  votage L2."
    ::= { slavetwointo 2 }

Slave2CurrentL1 OBJECT-TYPE
    SYNTAX INTEGER (0..65535)
    ACCESS read-write
    STATUS optional
    DESCRIPTION
            "slave 2  current L1.this value enlagrge 10 times."
    ::= { slavetwointo 4 }	
Slave2CurrentL2 OBJECT-TYPE
    SYNTAX INTEGER (0..65535)
    ACCESS read-write
    STATUS optional
    DESCRIPTION
            "slave 2  current L2.this value enlagrge 10 times."
    ::= { slavetwointo 5 }

Slave2PowerFactorL1 OBJECT-TYPE
    SYNTAX INTEGER (0..65535)
    ACCESS read-write
    STATUS optional
    DESCRIPTION
            "slave 2  power factor L1.this value enlagrge 100 times."
    ::= { slavetwointo 7 }	
Slave2PowerFactorL2 OBJECT-TYPE
    SYNTAX INTEGER (0..65535)
    ACCESS read-write
    STATUS optional
    DESCRIPTION
            "slave 2  power factor L2.this value enlagrge 100 times."
    ::= { slavetwointo 8 }

Slave2EnergyL1 OBJECT-TYPE
    SYNTAX INTEGER (0..65535)
    ACCESS read-write
    STATUS optional
    DESCRIPTION
            "slave 2  energy L1..this value enlagrge 10 times."
    ::= { slavetwointo 10 }	
Slave2EnergyL2 OBJECT-TYPE
    SYNTAX INTEGER (0..65535)
    ACCESS read-write
    STATUS optional
    DESCRIPTION
            "slave 2  energy L2..this value enlagrge 10 times."
    ::= { slavetwointo 11 }
	
Slave2TemperatureOne OBJECT-TYPE
    SYNTAX INTEGER (0..65535)
    ACCESS read-write
    STATUS optional
    DESCRIPTION
            "slave 2 Temperature One ."
    ::= { slavetwotem 1 }										
Slave2TemperatureTwo OBJECT-TYPE
    SYNTAX INTEGER (0..65535)
    ACCESS read-write
    STATUS optional
    DESCRIPTION
            "slave 2 Temperature Two ."
    ::= { slavetwotem 2 }
Slave2HumidityOne OBJECT-TYPE
    SYNTAX INTEGER (0..65535)
    ACCESS read-write
    STATUS optional
    DESCRIPTION
            "slave 2 Humidity One ."
    ::= { slavetwotem 3 }										
Slave2HumidityTwo OBJECT-TYPE
    SYNTAX INTEGER (0..65535)
    ACCESS read-write
    STATUS optional
    DESCRIPTION
            "slave 2 Humidity Two ."
    ::= { slavetwotem 4 }	
	
Slave2OutputCurrent1 OBJECT-TYPE
    SYNTAX INTEGER (0..65535)
    ACCESS read-write
    STATUS optional
    DESCRIPTION
            "slave 2 current.this value enlagrge 10 times."
    ::= { slavetwocurA 1 }	
Slave2OutputCurrent2 OBJECT-TYPE
    SYNTAX INTEGER (0..65535)
    ACCESS read-write
    STATUS optional
    DESCRIPTION
            "slave 2 current.this value enlagrge 10 times."
    ::= { slavetwocurA 2 }
Slave2OutputCurrent3 OBJECT-TYPE
    SYNTAX INTEGER (0..65535)
    ACCESS read-write
    STATUS optional
    DESCRIPTION
            "slave 2 current.this value enlagrge 10 times."
    ::= { slavetwocurA 3 }	
Slave2OutputCurrent4 OBJECT-TYPE
    SYNTAX INTEGER (0..65535)
    ACCESS read-write
    STATUS optional
    DESCRIPTION
            "slave 2 current.this value enlagrge 10 times."
    ::= { slavetwocurA 4 }	
Slave2OutputCurrent5 OBJECT-TYPE
    SYNTAX INTEGER (0..65535)
    ACCESS read-write
    STATUS optional
    DESCRIPTION
            "slave 2 current.this value enlagrge 10 times."
    ::= { slavetwocurA 5 }	
Slave2OutputCurrent6 OBJECT-TYPE
    SYNTAX INTEGER (0..65535)
    ACCESS read-write
    STATUS optional
    DESCRIPTION
            "slave 2 current.this value enlagrge 10 times."
    ::= { slavetwocurA 6 }
Slave2OutputCurrent7 OBJECT-TYPE
    SYNTAX INTEGER (0..65535)
    ACCESS read-write
    STATUS optional
    DESCRIPTION
            "slave 2 current.this value enlagrge 10 times."
    ::= { slavetwocurA 7 }	
Slave2OutputCurrent8 OBJECT-TYPE
    SYNTAX INTEGER (0..65535)
    ACCESS read-write
    STATUS optional
    DESCRIPTION
            "slave 2 current.this value enlagrge 10 times."
    ::= { slavetwocurA 8 }
			
Slave2OutputCurrent9 OBJECT-TYPE
    SYNTAX INTEGER (0..65535)
    ACCESS read-write
    STATUS optional
    DESCRIPTION
            "slave 2 current.this value enlagrge 10 times."
    ::= { slavetwocurB 1 }	
Slave2OutputCurrent10 OBJECT-TYPE
    SYNTAX INTEGER (0..65535)
    ACCESS read-write
    STATUS optional
    DESCRIPTION
            "slave 2 current.this value enlagrge 10 times."
    ::= { slavetwocurB 2 }
Slave2OutputCurrent11 OBJECT-TYPE
    SYNTAX INTEGER (0..65535)
    ACCESS read-write
    STATUS optional
    DESCRIPTION
            "slave 2 current.this value enlagrge 10 times."
    ::= { slavetwocurB 3 }	
Slave2OutputCurrent12 OBJECT-TYPE
    SYNTAX INTEGER (0..65535)
    ACCESS read-write
    STATUS optional
    DESCRIPTION
            "slave 2 current.this value enlagrge 10 times."
    ::= { slavetwocurB 4 }	
Slave2OutputCurrent13 OBJECT-TYPE
    SYNTAX INTEGER (0..65535)
    ACCESS read-write
    STATUS optional
    DESCRIPTION
            "slave 2 current.this value enlagrge 10 times."
    ::= { slavetwocurB 5 }	
Slave2OutputCurrent14 OBJECT-TYPE
    SYNTAX INTEGER (0..65535)
    ACCESS read-write
    STATUS optional
    DESCRIPTION
            "slave 2 current.this value enlagrge 10 times."
    ::= { slavetwocurB 6 }
Slave2OutputCurrent15 OBJECT-TYPE
    SYNTAX INTEGER (0..65535)
    ACCESS read-write
    STATUS optional
    DESCRIPTION
            "slave 2 current.this value enlagrge 10 times."
    ::= { slavetwocurB 7 }	
Slave2OutputCurrent16 OBJECT-TYPE
    SYNTAX INTEGER (0..65535)
    ACCESS read-write
    STATUS optional
    DESCRIPTION
            "slave 2 current.this value enlagrge 10 times."
    ::= { slavetwocurB 8 }
		
Slave2OutputCurrent17 OBJECT-TYPE
    SYNTAX INTEGER (0..65535)
    ACCESS read-write
    STATUS optional
    DESCRIPTION
            "slave 2 current.this value enlagrge 10 times."
    ::= { slavetwocurC 1 }	
Slave2OutputCurrent18 OBJECT-TYPE
    SYNTAX INTEGER (0..65535)
    ACCESS read-write
    STATUS optional
    DESCRIPTION
            "slave 2 current.this value enlagrge 10 times."
    ::= { slavetwocurC 2 }
Slave2OutputCurrent19 OBJECT-TYPE
    SYNTAX INTEGER (0..65535)
    ACCESS read-write
    STATUS optional
    DESCRIPTION
            "slave 2 current.this value enlagrge 10 times."
    ::= { slavetwocurC 3 }	
Slave2OutputCurrent20 OBJECT-TYPE
    SYNTAX INTEGER (0..65535)
    ACCESS read-write
    STATUS optional
    DESCRIPTION
            "slave 2 current.this value enlagrge 10 times."
    ::= { slavetwocurC 4 }
		
Slave2OutputCurrent21 OBJECT-TYPE
    SYNTAX INTEGER (0..65535)
    ACCESS read-write
    STATUS optional
    DESCRIPTION
            "slave 2 current.this value enlagrge 10 times."
    ::= { slavetwocurC 5 }	
Slave2OutputCurrent22 OBJECT-TYPE
    SYNTAX INTEGER (0..65535)
    ACCESS read-write
    STATUS optional
    DESCRIPTION
            "slave 2 current.this value enlagrge 10 times."
    ::= { slavetwocurC 6 }
Slave2OutputCurrent23 OBJECT-TYPE
    SYNTAX INTEGER (0..65535)
    ACCESS read-write
    STATUS optional
    DESCRIPTION
            "slave 2 current.this value enlagrge 10 times."
    ::= { slavetwocurC 7 }	
Slave2OutputCurrent24 OBJECT-TYPE
    SYNTAX INTEGER (0..65535)
    ACCESS read-write
    STATUS optional
    DESCRIPTION
            "slave 2 current.this value enlagrge 10 times."
    ::= { slavetwocurC 8 }													
	
Slave2OutputPF1 OBJECT-TYPE
    SYNTAX INTEGER (0..65535)
    ACCESS read-write
    STATUS optional
    DESCRIPTION
            "slave 2 power factor.this value enlagrge 100 times."
    ::= { slavetwopfA 1 }	
Slave2OutputPF2 OBJECT-TYPE
    SYNTAX INTEGER (0..65535)
    ACCESS read-write
    STATUS optional
    DESCRIPTION
            "slave 2 power factor.this value enlagrge 100 times."
    ::= { slavetwopfA 2 }
Slave2OutputPF3 OBJECT-TYPE
    SYNTAX INTEGER (0..65535)
    ACCESS read-write
    STATUS optional
    DESCRIPTION
            "slave 2 power factor.this value enlagrge 100 times."
    ::= { slavetwopfA 3 }
Slave2OutputPF4 OBJECT-TYPE
    SYNTAX INTEGER (0..65535)
    ACCESS read-write
    STATUS optional
    DESCRIPTION
            "slave 2 power factor.this value enlagrge 100 times."
    ::= { slavetwopfA 4 }
Slave2OutputPF5 OBJECT-TYPE
    SYNTAX INTEGER (0..65535)
    ACCESS read-write
    STATUS optional
    DESCRIPTION
            "slave 2 power factor.this value enlagrge 100 times."
    ::= { slavetwopfA 5 }	
Slave2OutputPF6 OBJECT-TYPE
    SYNTAX INTEGER (0..65535)
    ACCESS read-write
    STATUS optional
    DESCRIPTION
            "slave 2 power factor.this value enlagrge 100 times."
    ::= { slavetwopfA 6 }
Slave2OutputPF7 OBJECT-TYPE
    SYNTAX INTEGER (0..65535)
    ACCESS read-write
    STATUS optional
    DESCRIPTION
            "slave 2 power factor.this value enlagrge 100 times."
    ::= { slavetwopfA 7 }
Slave2OutputPF8 OBJECT-TYPE
    SYNTAX INTEGER (0..65535)
    ACCESS read-write
    STATUS optional
    DESCRIPTION
            "slave 2 power factor.this value enlagrge 100 times."
    ::= { slavetwopfA 8 }
		
Slave2OutputPF9 OBJECT-TYPE
    SYNTAX INTEGER (0..65535)
    ACCESS read-write
    STATUS optional
    DESCRIPTION
            "slave 2 power factor.this value enlagrge 100 times."
    ::= { slavetwopfB 1 }	
Slave2OutputPF10 OBJECT-TYPE
    SYNTAX INTEGER (0..65535)
    ACCESS read-write
    STATUS optional
    DESCRIPTION
            "slave 2 power factor.this value enlagrge 100 times."
    ::= { slavetwopfB 2 }
Slave2OutputPF11 OBJECT-TYPE
    SYNTAX INTEGER (0..65535)
    ACCESS read-write
    STATUS optional
    DESCRIPTION
            "slave 2 power factor.this value enlagrge 100 times."
    ::= { slavetwopfB 3 }
Slave2OutputPF12 OBJECT-TYPE
    SYNTAX INTEGER (0..65535)
    ACCESS read-write
    STATUS optional
    DESCRIPTION
            "slave 2 power factor.this value enlagrge 100 times."
    ::= { slavetwopfB 4 }
Slave2OutputPF13 OBJECT-TYPE
    SYNTAX INTEGER (0..65535)
    ACCESS read-write
    STATUS optional
    DESCRIPTION
            "slave 2 power factor.this value enlagrge 100 times."
    ::= { slavetwopfB 5 }	
Slave2OutputPF14 OBJECT-TYPE
    SYNTAX INTEGER (0..65535)
    ACCESS read-write
    STATUS optional
    DESCRIPTION
            "slave 2 power factor.this value enlagrge 100 times."
    ::= { slavetwopfB 6 }
Slave2OutputPF15 OBJECT-TYPE
    SYNTAX INTEGER (0..65535)
    ACCESS read-write
    STATUS optional
    DESCRIPTION
            "slave 2 power factor.this value enlagrge 100 times."
    ::= { slavetwopfB 7 }
Slave2OutputPF16 OBJECT-TYPE
    SYNTAX INTEGER (0..65535)
    ACCESS read-write
    STATUS optional
    DESCRIPTION
            "slave 2 power factor.this value enlagrge 100 times."
    ::= { slavetwopfB 8 }
		
Slave2OutputPF17 OBJECT-TYPE
    SYNTAX INTEGER (0..65535)
    ACCESS read-write
    STATUS optional
    DESCRIPTION
            "slave 2 power factor.this value enlagrge 100 times."
    ::= { slavetwopfC 1 }	
Slave2OutputPF18 OBJECT-TYPE
    SYNTAX INTEGER (0..65535)
    ACCESS read-write
    STATUS optional
    DESCRIPTION
            "slave 2 power factor.this value enlagrge 100 times."
    ::= { slavetwopfC 2 }
Slave2OutputPF19 OBJECT-TYPE
    SYNTAX INTEGER (0..65535)
    ACCESS read-write
    STATUS optional
    DESCRIPTION
            "slave 2 power factor.this value enlagrge 100 times."
    ::= { slavetwopfC 3 }
Slave2OutputPF20 OBJECT-TYPE
    SYNTAX INTEGER (0..65535)
    ACCESS read-write
    STATUS optional
    DESCRIPTION
            "slave 2 power factor.this value enlagrge 100 times."
    ::= { slavetwopfC 4 }
Slave2OutputPF21 OBJECT-TYPE
    SYNTAX INTEGER (0..65535)
    ACCESS read-write
    STATUS optional
    DESCRIPTION
            "slave 2 power factor.this value enlagrge 100 times."
    ::= { slavetwopfC 5 }	
Slave2OutputPF22 OBJECT-TYPE
    SYNTAX INTEGER (0..65535)
    ACCESS read-write
    STATUS optional
    DESCRIPTION
            "slave 2 power factor.this value enlagrge 100 times."
    ::= { slavetwopfC 6 }
Slave2OutputPF23 OBJECT-TYPE
    SYNTAX INTEGER (0..65535)
    ACCESS read-write
    STATUS optional
    DESCRIPTION
            "slave 2 power factor.this value enlagrge 100 times."
    ::= { slavetwopfC 7 }
Slave2OutputPF24 OBJECT-TYPE
    SYNTAX INTEGER (0..65535)
    ACCESS read-write
    STATUS optional
    DESCRIPTION
            "slave 2 power factor.this value enlagrge 100 times."
    ::= { slavetwopfC 8 }	
	
Slave2OutputEnergy1 OBJECT-TYPE
    SYNTAX INTEGER (0..65535)
    ACCESS read-write
    STATUS optional
    DESCRIPTION
            "slave 2 Output energy.this value enlagrge 10 times"
    ::= { slavetwoenA 1 }	
Slave2OutputEnergy2 OBJECT-TYPE
    SYNTAX INTEGER (0..65535)
    ACCESS read-write
    STATUS optional
    DESCRIPTION
            "slave 2 Output energy.this value enlagrge 10 times"
    ::= { slavetwoenA 2 }
Slave2OutputEnergy3 OBJECT-TYPE
    SYNTAX INTEGER (0..65535)
    ACCESS read-write
    STATUS optional
    DESCRIPTION
            "slave 2 Output energy.this value enlagrge 10 times"
    ::= { slavetwoenA 3 }
Slave2OutputEnergy4 OBJECT-TYPE
    SYNTAX INTEGER (0..65535)
    ACCESS read-write
    STATUS optional
    DESCRIPTION
            "slave 2 Output energy.this value enlagrge 10 times"
    ::= { slavetwoenA 4 }
Slave2OutputEnergy5 OBJECT-TYPE
    SYNTAX INTEGER (0..65535)
    ACCESS read-write
    STATUS optional
    DESCRIPTION
            "slave 2 Output energy.this value enlagrge 10 times"
    ::= { slavetwoenA 5 }	
Slave1OutputEnergy6 OBJECT-TYPE
    SYNTAX INTEGER (0..65535)
    ACCESS read-write
    STATUS optional
    DESCRIPTION
            "slave 1 Output energy.this value enlagrge 10 times"
    ::= { slavetwoenA 6 }
Slave21OutputEnergy7 OBJECT-TYPE
    SYNTAX INTEGER (0..65535)
    ACCESS read-write
    STATUS optional
    DESCRIPTION
            "slave 2 Output energy.this value enlagrge 10 times"
    ::= { slavetwoenA 7 }
Slave2OutputEnergy8 OBJECT-TYPE
    SYNTAX INTEGER (0..65535)
    ACCESS read-write
    STATUS optional
    DESCRIPTION
            "slave 2 Output energy.this value enlagrge 10 times"
    ::= { slavetwoenA 8 }	
		
Slave2OutputEnergy9 OBJECT-TYPE
    SYNTAX INTEGER (0..65535)
    ACCESS read-write
    STATUS optional
    DESCRIPTION
            "slave 2 Output energy.this value enlagrge 10 times"
    ::= { slavetwoenB 1 }	
Slave2OutputEnergy10 OBJECT-TYPE
    SYNTAX INTEGER (0..65535)
    ACCESS read-write
    STATUS optional
    DESCRIPTION
            "slave 2 Output energy.this value enlagrge 10 times"
    ::= { slavetwoenB 2 }
Slave2OutputEnergy11 OBJECT-TYPE
    SYNTAX INTEGER (0..65535)
    ACCESS read-write
    STATUS optional
    DESCRIPTION
            "slave 2 Output energy.this value enlagrge 10 times"
    ::= { slavetwoenB 3 }
Slave2OutputEnergy12 OBJECT-TYPE
    SYNTAX INTEGER (0..65535)
    ACCESS read-write
    STATUS optional
    DESCRIPTION
            "slave 2 Output energy.this value enlagrge 10 times"
    ::= { slavetwoenB 4 }
Slave2OutputEnergy13 OBJECT-TYPE
    SYNTAX INTEGER (0..65535)
    ACCESS read-write
    STATUS optional
    DESCRIPTION
            "slave 2 Output energy.this value enlagrge 10 times"
    ::= { slavetwoenB 5 }	
Slave2OutputEnergy14 OBJECT-TYPE
    SYNTAX INTEGER (0..65535)
    ACCESS read-write
    STATUS optional
    DESCRIPTION
            "slave 2 Output energy.this value enlagrge 10 times"
    ::= { slavetwoenB 6 }
Slave2OutputEnergy15 OBJECT-TYPE
    SYNTAX INTEGER (0..65535)
    ACCESS read-write
    STATUS optional
    DESCRIPTION
            "slave 2 Output energy.this value enlagrge 10 times"
    ::= { slavetwoenB 7 }
Slave2OutputEnergy16 OBJECT-TYPE
    SYNTAX INTEGER (0..65535)
    ACCESS read-write
    STATUS optional
    DESCRIPTION
            "slave 2 Output energy.this value enlagrge 10 times"
    ::= { slavetwoenB 8 }	
	
Slave2OutputEnergy17 OBJECT-TYPE
    SYNTAX INTEGER (0..65535)
    ACCESS read-write
    STATUS optional
    DESCRIPTION
            "slave 2 Output energy.this value enlagrge 10 times"
    ::= { slavetwoenC 1 }	
Slave2OutputEnergy18 OBJECT-TYPE
    SYNTAX INTEGER (0..65535)
    ACCESS read-write
    STATUS optional
    DESCRIPTION
            "slave 2 Output energy.this value enlagrge 10 times"
    ::= { slavetwoenC 2 }
Slave2OutputEnergy19 OBJECT-TYPE
    SYNTAX INTEGER (0..65535)
    ACCESS read-write
    STATUS optional
    DESCRIPTION
            "slave 2 Output energy.this value enlagrge 10 times"
    ::= { slavetwoenC 3 }
Slave2OutputEnergy20 OBJECT-TYPE
    SYNTAX INTEGER (0..65535)
    ACCESS read-write
    STATUS optional
    DESCRIPTION
            "slave 2 Output energy.this value enlagrge 10 times"
    ::= { slavetwoenC 4 }
Slave2OutputEnergy21 OBJECT-TYPE
    SYNTAX INTEGER (0..65535)
    ACCESS read-write
    STATUS optional
    DESCRIPTION
            "slave 2 Output energy.this value enlagrge 10 times"
    ::= { slavetwoenC 5 }	
Slave2OutputEnergy22 OBJECT-TYPE
    SYNTAX INTEGER (0..65535)
    ACCESS read-write
    STATUS optional
    DESCRIPTION
            "slave 2 Output energy.this value enlagrge 10 times"
    ::= { slavetwoenC 6 }
Slave2OutputEnergy23 OBJECT-TYPE
    SYNTAX INTEGER (0..65535)
    ACCESS read-write
    STATUS optional
    DESCRIPTION
            "slave 2 Output energy.this value enlagrge 10 times"
    ::= { slavetwoenC 7 }
Slave2OutputEnergy24  OBJECT-TYPE
    SYNTAX INTEGER (0..65535)
    ACCESS read-write
    STATUS optional
    DESCRIPTION
            "slave 2 Output energy.this value enlagrge 10 times"
    ::= { slavetwoenC 8 }	

Slave2Switch1 OBJECT-TYPE
    SYNTAX DisplayString (SIZE (255))
    ACCESS read-write
    STATUS optional
    DESCRIPTION
            "slave 2 output switch 1 ."
    ::= { slavetwoswA 1 }
Slave2Switch2 OBJECT-TYPE
    SYNTAX DisplayString (SIZE (255))
    ACCESS read-write
    STATUS optional
    DESCRIPTION
            "slave 2 output switch 2 ."
    ::= { slavetwoswA 2 }
Slave2Switch3 OBJECT-TYPE
    SYNTAX DisplayString (SIZE (255))
    ACCESS read-write
    STATUS optional
    DESCRIPTION
            "slave 2 output switch 3 ."
    ::= { slavetwoswA 3 }
Slave2Switch4 OBJECT-TYPE
    SYNTAX DisplayString (SIZE (255))
    ACCESS read-write
    STATUS optional
    DESCRIPTION
            "slave 2 output switch 4 ."
    ::= { slavetwoswA 4 }	
Slave2Switch5 OBJECT-TYPE
    SYNTAX DisplayString (SIZE (255))
    ACCESS read-write
    STATUS optional
    DESCRIPTION
            "slave 2 output switch 5 ."
    ::= { slavetwoswA 5 }
Slave2Switch6 OBJECT-TYPE
    SYNTAX DisplayString (SIZE (255))
    ACCESS read-write
    STATUS optional
    DESCRIPTION
            "slave 2 output switch 6 ."
    ::= { slavetwoswA 6 }
Slave2Switch7 OBJECT-TYPE
    SYNTAX DisplayString (SIZE (255))
    ACCESS read-write
    STATUS optional
    DESCRIPTION
            "slave 2 output switch 7 ."
    ::= { slavetwoswA 7 }
Slave2Switch8 OBJECT-TYPE
    SYNTAX DisplayString (SIZE (255))
    ACCESS read-write
    STATUS optional
    DESCRIPTION
            "slave 2 output switch 8 ."
    ::= { slavetwoswA 8 }	
		
Slave2Switch9 OBJECT-TYPE
    SYNTAX DisplayString (SIZE (255))
    ACCESS read-write
    STATUS optional
    DESCRIPTION
            "slave 2 output switch 9 ."
    ::= { slavetwoswB 1 }
Slave2Switch10 OBJECT-TYPE
    SYNTAX DisplayString (SIZE (255))
    ACCESS read-write
    STATUS optional
    DESCRIPTION
            "slave 2 output switch 10 ."
    ::= { slavetwoswB 2 }
Slave2Switch11 OBJECT-TYPE
    SYNTAX DisplayString (SIZE (255))
    ACCESS read-write
    STATUS optional
    DESCRIPTION
            "slave 2 output switch 11 ."
    ::= { slavetwoswB 3 }
Slave2Switch12 OBJECT-TYPE
    SYNTAX DisplayString (SIZE (255))
    ACCESS read-write
    STATUS optional
    DESCRIPTION
            "slave 2 output switch 12 ."
    ::= { slavetwoswB 4 }	
Slave2Switch13 OBJECT-TYPE
    SYNTAX DisplayString (SIZE (255))
    ACCESS read-write
    STATUS optional
    DESCRIPTION
            "slave 2 output switch 13 ."
    ::= { slavetwoswB 5 }
Slave2Switch14 OBJECT-TYPE
    SYNTAX DisplayString (SIZE (255))
    ACCESS read-write
    STATUS optional
    DESCRIPTION
            "slave 2 output switch 14 ."
    ::= { slavetwoswB 6 }
Slave2Switch15 OBJECT-TYPE
    SYNTAX DisplayString (SIZE (255))
    ACCESS read-write
    STATUS optional
    DESCRIPTION
            "slave 2 output switch 15 ."
    ::= { slavetwoswB 7 }
	
Slave2Switch16 OBJECT-TYPE
    SYNTAX DisplayString (SIZE (255))
    ACCESS read-write
    STATUS optional
    DESCRIPTION
            "slave 2 output switch 16 ."
    ::= { slavetwoswB 8 }	
Slave2Switch17 OBJECT-TYPE
    SYNTAX DisplayString (SIZE (255))
    ACCESS read-write
    STATUS optional
    DESCRIPTION
            " slave 2 output switch 17 ."
    ::= { slavetwoswC 1 }
Slave2Switch18 OBJECT-TYPE
    SYNTAX DisplayString (SIZE (255))
    ACCESS read-write
    STATUS optional
    DESCRIPTION
            "slave 2 output switch 18 ."
    ::= { slavetwoswC 2 }
Slave2Switch19 OBJECT-TYPE
    SYNTAX DisplayString (SIZE (255))
    ACCESS read-write
    STATUS optional
    DESCRIPTION
            "slave 2 output switch 19 ."
    ::= { slavetwoswC 3 }
Slave2Switch20 OBJECT-TYPE
    SYNTAX DisplayString (SIZE (255))
    ACCESS read-write
    STATUS optional
    DESCRIPTION
            "slave 2 output switch 20 ."
    ::= { slavetwoswC 4 }	
Slave2Switch21 OBJECT-TYPE
    SYNTAX DisplayString (SIZE (255))
    ACCESS read-write
    STATUS optional
    DESCRIPTION
            "slave 2 output switch 21 ."
    ::= { slavetwoswC 5 }
Slave2Switch22 OBJECT-TYPE
    SYNTAX DisplayString (SIZE (255))
    ACCESS read-write
    STATUS optional
    DESCRIPTION
            "slave 2 output switch 22 ."
    ::= { slavetwoswC 6 }
Slave2Switch23 OBJECT-TYPE
    SYNTAX DisplayString (SIZE (255))
    ACCESS read-write
    STATUS optional
    DESCRIPTION
            "slave 2 output switch 23 ."
    ::= { slavetwoswC 7}
Slave2Switch24 OBJECT-TYPE
    SYNTAX DisplayString (SIZE (255))
    ACCESS read-write
    STATUS optional
    DESCRIPTION
            "slave 2 output switch 24 ."
    ::= { slavetwoswC 8 }

Slave3VoltageL1 OBJECT-TYPE
    SYNTAX INTEGER (0..65535)
    ACCESS read-write
    STATUS optional
    DESCRIPTION
            "slave 3  votage L1."
    ::= { slavethreeinto 1 }
Slave3VoltageL2 OBJECT-TYPE
    SYNTAX INTEGER (0..65535)
    ACCESS read-write
    STATUS optional
    DESCRIPTION
            "slave 3  votage L2."
    ::= { slavethreeinto 2 }

Slave3CurrentL1 OBJECT-TYPE
    SYNTAX INTEGER (0..65535)
    ACCESS read-write
    STATUS optional
    DESCRIPTION
            "slave 3  current L1.this value enlagrge 10 times."
    ::= { slavethreeinto 4 }	
Slave3CurrentL2 OBJECT-TYPE
    SYNTAX INTEGER (0..65535)
    ACCESS read-write
    STATUS optional
    DESCRIPTION
            "slave 3  current L2.this value enlagrge 10 times."
    ::= { slavethreeinto 5 }
	
Slave3PowerFactorL1 OBJECT-TYPE
    SYNTAX INTEGER (0..65535)
    ACCESS read-write
    STATUS optional
    DESCRIPTION
            "slave 3  power factor L1.this value enlagrge 100 times."
    ::= { slavethreeinto 7 }	
Slave3PowerFactorL2 OBJECT-TYPE
    SYNTAX INTEGER (0..65535)
    ACCESS read-write
    STATUS optional
    DESCRIPTION
            "slave 3  power factor L2.this value enlagrge 100 times."
    ::= { slavethreeinto 8 }
	
Slave3EnergyL1 OBJECT-TYPE
    SYNTAX INTEGER (0..65535)
    ACCESS read-write
    STATUS optional
    DESCRIPTION
            "slave 3  energy L1..this value enlagrge 10 times."
    ::= { slavethreeinto 10 }	
Slave3EnergyL2 OBJECT-TYPE
    SYNTAX INTEGER (0..65535)
    ACCESS read-write
    STATUS optional
    DESCRIPTION
            "slave 3  energy L2..this value enlagrge 10 times."
    ::= { slavethreeinto 11 }
	
Slave3TemperatureOne OBJECT-TYPE
    SYNTAX INTEGER (0..65535)
    ACCESS read-write
    STATUS optional
    DESCRIPTION
            "slave 3 Temperature One ."
    ::= { slavethreetem 1 }										
Slave3TemperatureTwo OBJECT-TYPE
    SYNTAX INTEGER (0..65535)
    ACCESS read-write
    STATUS optional
    DESCRIPTION
            "slave 3 Temperature Two ."
    ::= { slavethreetem 2 }
Slave3HumidityOne OBJECT-TYPE
    SYNTAX INTEGER (0..65535)
    ACCESS read-write
    STATUS optional
    DESCRIPTION
            "slave 3 Humidity One ."
    ::= { slavethreetem 3 }										
Slave3HumidityTwo OBJECT-TYPE
    SYNTAX INTEGER (0..65535)
    ACCESS read-write
    STATUS optional
    DESCRIPTION
            "slave 3 Humidity Two ."
    ::= { slavethreetem 4 }	
	
Slave3OutputCurrent1 OBJECT-TYPE
    SYNTAX INTEGER (0..65535)
    ACCESS read-write
    STATUS optional
    DESCRIPTION
            "slave 3 current.this value enlagrge 10 times."
    ::= { slavethreecurA 1 }	
Slave3OutputCurrent2 OBJECT-TYPE
    SYNTAX INTEGER (0..65535)
    ACCESS read-write
    STATUS optional
    DESCRIPTION
            "slave 3 current.this value enlagrge 10 times."
    ::= { slavethreecurA 2 }
Slave3OutputCurrent3 OBJECT-TYPE
    SYNTAX INTEGER (0..65535)
    ACCESS read-write
    STATUS optional
    DESCRIPTION
            "slave 3 current.this value enlagrge 10 times."
    ::= { slavethreecurA 3 }	
Slave3OutputCurrent4 OBJECT-TYPE
    SYNTAX INTEGER (0..65535)
    ACCESS read-write
    STATUS optional
    DESCRIPTION
            "slave 3 current.this value enlagrge 10 times."
    ::= { slavethreecurA 4 }	
Slave3OutputCurrent5 OBJECT-TYPE
    SYNTAX INTEGER (0..65535)
    ACCESS read-write
    STATUS optional
    DESCRIPTION
            "slave 3 current.this value enlagrge 10 times."
    ::= { slavethreecurA 5 }	
Slave3OutputCurrent6 OBJECT-TYPE
    SYNTAX INTEGER (0..65535)
    ACCESS read-write
    STATUS optional
    DESCRIPTION
            "slave 3 current.this value enlagrge 10 times."
    ::= { slavethreecurA 6 }
Slave3OutputCurrent7 OBJECT-TYPE
    SYNTAX INTEGER (0..65535)
    ACCESS read-write
    STATUS optional
    DESCRIPTION
            "slave 3 current.this value enlagrge 10 times."
    ::= { slavethreecurA 7 }	
Slave3OutputCurrent8 OBJECT-TYPE
    SYNTAX INTEGER (0..65535)
    ACCESS read-write
    STATUS optional
    DESCRIPTION
            "slave 3 current.this value enlagrge 10 times."
    ::= { slavethreecurA 8 }
			
Slave3OutputCurrent9 OBJECT-TYPE
    SYNTAX INTEGER (0..65535)
    ACCESS read-write
    STATUS optional
    DESCRIPTION
            "slave 3 current.this value enlagrge 10 times."
    ::= { slavethreecurB 1 }	
Slave3OutputCurrent10 OBJECT-TYPE
    SYNTAX INTEGER (0..65535)
    ACCESS read-write
    STATUS optional
    DESCRIPTION
            "slave 3 current.this value enlagrge 10 times."
    ::= { slavethreecurB 2 }
Slave3OutputCurrent11 OBJECT-TYPE
    SYNTAX INTEGER (0..65535)
    ACCESS read-write
    STATUS optional
    DESCRIPTION
            "slave 3 current.this value enlagrge 10 times."
    ::= { slavethreecurB 3 }	
Slave3OutputCurrent12 OBJECT-TYPE
    SYNTAX INTEGER (0..65535)
    ACCESS read-write
    STATUS optional
    DESCRIPTION
            "slave 3 current.this value enlagrge 10 times."
    ::= { slavethreecurB 4 }	
Slave3OutputCurrent13 OBJECT-TYPE
    SYNTAX INTEGER (0..65535)
    ACCESS read-write
    STATUS optional
    DESCRIPTION
            "slave 3 current.this value enlagrge 10 times."
    ::= { slavethreecurB 5 }	
Slave3OutputCurrent14 OBJECT-TYPE
    SYNTAX INTEGER (0..65535)
    ACCESS read-write
    STATUS optional
    DESCRIPTION
            "slave 3 current.this value enlagrge 10 times."
    ::= { slavethreecurB 6 }
Slave3OutputCurrent15 OBJECT-TYPE
    SYNTAX INTEGER (0..65535)
    ACCESS read-write
    STATUS optional
    DESCRIPTION
            "slave 3 current.this value enlagrge 10 times."
    ::= { slavethreecurB 7 }	
Slave3OutputCurrent16 OBJECT-TYPE
    SYNTAX INTEGER (0..65535)
    ACCESS read-write
    STATUS optional
    DESCRIPTION
            "slave 3 current.this value enlagrge 10 times."
    ::= { slavethreecurB 8 }
		
Slave3OutputCurrent17 OBJECT-TYPE
    SYNTAX INTEGER (0..65535)
    ACCESS read-write
    STATUS optional
    DESCRIPTION
            "slave 3 current.this value enlagrge 10 times."
    ::= { slavethreecurC 1 }	
Slave3OutputCurrent18 OBJECT-TYPE
    SYNTAX INTEGER (0..65535)
    ACCESS read-write
    STATUS optional
    DESCRIPTION
            "slave 3 current.this value enlagrge 10 times."
    ::= { slavethreecurC 2 }
Slave3OutputCurrent19 OBJECT-TYPE
    SYNTAX INTEGER (0..65535)
    ACCESS read-write
    STATUS optional
    DESCRIPTION
            "slave 3 current.this value enlagrge 10 times."
    ::= { slavethreecurC 3 }	
Slave3OutputCurrent20 OBJECT-TYPE
    SYNTAX INTEGER (0..65535)
    ACCESS read-write
    STATUS optional
    DESCRIPTION
            "slave 3 current.this value enlagrge 10 times."
    ::= { slavethreecurC 4 }
		
Slave3OutputCurrent21 OBJECT-TYPE
    SYNTAX INTEGER (0..65535)
    ACCESS read-write
    STATUS optional
    DESCRIPTION
            "slave 3 current.this value enlagrge 10 times."
    ::= { slavethreecurC 5 }	
Slave3OutputCurrent22 OBJECT-TYPE
    SYNTAX INTEGER (0..65535)
    ACCESS read-write
    STATUS optional
    DESCRIPTION
            "slave 3 current.this value enlagrge 10 times."
    ::= { slavethreecurC 6 }
Slave3OutputCurrent23 OBJECT-TYPE
    SYNTAX INTEGER (0..65535)
    ACCESS read-write
    STATUS optional
    DESCRIPTION
            "slave 3 current.this value enlagrge 10 times."
    ::= { slavethreecurC 7 }	
Slave3OutputCurrent24 OBJECT-TYPE
    SYNTAX INTEGER (0..65535)
    ACCESS read-write
    STATUS optional
    DESCRIPTION
            "slave 3 current.this value enlagrge 10 times."
    ::= { slavethreecurC 8 }													
	
Slave3OutputPF1 OBJECT-TYPE
    SYNTAX INTEGER (0..65535)
    ACCESS read-write
    STATUS optional
    DESCRIPTION
            "slave 3 power factor.this value enlagrge 100 times."
    ::= { slavethreepfA 1 }	
Slave3OutputPF2 OBJECT-TYPE
    SYNTAX INTEGER (0..65535)
    ACCESS read-write
    STATUS optional
    DESCRIPTION
            "slave 3 power factor.this value enlagrge 100 times."
    ::= { slavethreepfA 2 }
Slave3OutputPF3 OBJECT-TYPE
    SYNTAX INTEGER (0..65535)
    ACCESS read-write
    STATUS optional
    DESCRIPTION
            "slave 3 power factor.this value enlagrge 100 times."
    ::= { slavethreepfA 3 }
Slave3OutputPF4 OBJECT-TYPE
    SYNTAX INTEGER (0..65535)
    ACCESS read-write
    STATUS optional
    DESCRIPTION
            "slave 3 power factor.this value enlagrge 100 times."
    ::= { slavethreepfA 4 }
Slave3OutputPF5 OBJECT-TYPE
    SYNTAX INTEGER (0..65535)
    ACCESS read-write
    STATUS optional
    DESCRIPTION
            "slave 3 power factor.this value enlagrge 100 times."
    ::= { slavethreepfA 5 }	
Slave3OutputPF6 OBJECT-TYPE
    SYNTAX INTEGER (0..65535)
    ACCESS read-write
    STATUS optional
    DESCRIPTION
            "slave 3 power factor.this value enlagrge 100 times."
    ::= { slavethreepfA 6 }
Slave3OutputPF7 OBJECT-TYPE
    SYNTAX INTEGER (0..65535)
    ACCESS read-write
    STATUS optional
    DESCRIPTION
            "slave 3 power factor.this value enlagrge 100 times."
    ::= { slavethreepfA 7 }
Slave3OutputPF8 OBJECT-TYPE
    SYNTAX INTEGER (0..65535)
    ACCESS read-write
    STATUS optional
    DESCRIPTION
            "slave 3 power factor.this value enlagrge 100 times."
    ::= { slavethreepfA 8 }
		
Slave3OutputPF9 OBJECT-TYPE
    SYNTAX INTEGER (0..65535)
    ACCESS read-write
    STATUS optional
    DESCRIPTION
            "slave 3 power factor.this value enlagrge 100 times."
    ::= { slavethreepfB 1 }	
Slave3OutputPF10 OBJECT-TYPE
    SYNTAX INTEGER (0..65535)
    ACCESS read-write
    STATUS optional
    DESCRIPTION
            "slave 3 power factor.this value enlagrge 100 times."
    ::= { slavethreepfB 2 }
Slave3OutputPF11 OBJECT-TYPE
    SYNTAX INTEGER (0..65535)
    ACCESS read-write
    STATUS optional
    DESCRIPTION
            "slave 3 power factor.this value enlagrge 100 times."
    ::= { slavethreepfB 3 }
Slave3OutputPF12 OBJECT-TYPE
    SYNTAX INTEGER (0..65535)
    ACCESS read-write
    STATUS optional
    DESCRIPTION
            "slave 3 power factor.this value enlagrge 100 times."
    ::= { slavethreepfB 4 }
Slave3OutputPF13 OBJECT-TYPE
    SYNTAX INTEGER (0..65535)
    ACCESS read-write
    STATUS optional
    DESCRIPTION
            "slave 3 power factor.this value enlagrge 100 times."
    ::= { slavethreepfB 5 }	
Slave3OutputPF14 OBJECT-TYPE
    SYNTAX INTEGER (0..65535)
    ACCESS read-write
    STATUS optional
    DESCRIPTION
            "slave 3 power factor.this value enlagrge 100 times."
    ::= { slavethreepfB 6 }
Slave3OutputPF15 OBJECT-TYPE
    SYNTAX INTEGER (0..65535)
    ACCESS read-write
    STATUS optional
    DESCRIPTION
            "slave 3 power factor.this value enlagrge 100 times."
    ::= { slavethreepfB 7 }
Slave3OutputPF16 OBJECT-TYPE
    SYNTAX INTEGER (0..65535)
    ACCESS read-write
    STATUS optional
    DESCRIPTION
            "slave 3 power factor.this value enlagrge 100 times."
    ::= { slavethreepfB 8 }
		
Slave3OutputPF17 OBJECT-TYPE
    SYNTAX INTEGER (0..65535)
    ACCESS read-write
    STATUS optional
    DESCRIPTION
            "slave 3 power factor.this value enlagrge 100 times."
    ::= { slavethreepfC 1 }	
Slave3OutputPF18 OBJECT-TYPE
    SYNTAX INTEGER (0..65535)
    ACCESS read-write
    STATUS optional
    DESCRIPTION
            "slave 3 power factor.this value enlagrge 100 times."
    ::= { slavethreepfC 2 }
Slave3OutputPF19 OBJECT-TYPE
    SYNTAX INTEGER (0..65535)
    ACCESS read-write
    STATUS optional
    DESCRIPTION
            "slave 3 power factor.this value enlagrge 100 times."
    ::= { slavethreepfC 3 }
Slave3OutputPF20 OBJECT-TYPE
    SYNTAX INTEGER (0..65535)
    ACCESS read-write
    STATUS optional
    DESCRIPTION
            "slave 3 power factor.this value enlagrge 100 times."
    ::= { slavethreepfC 4 }
Slave3OutputPF21 OBJECT-TYPE
    SYNTAX INTEGER (0..65535)
    ACCESS read-write
    STATUS optional
    DESCRIPTION
            "slave 3 power factor.this value enlagrge 100 times."
    ::= { slavethreepfC 5 }	
Slave3OutputPF22 OBJECT-TYPE
    SYNTAX INTEGER (0..65535)
    ACCESS read-write
    STATUS optional
    DESCRIPTION
            "slave 3 power factor.this value enlagrge 100 times."
    ::= { slavethreepfC 6 }
Slave3OutputPF23 OBJECT-TYPE
    SYNTAX INTEGER (0..65535)
    ACCESS read-write
    STATUS optional
    DESCRIPTION
            "slave 3 power factor.this value enlagrge 100 times."
    ::= { slavethreepfC 7 }
Slave3OutputPF24 OBJECT-TYPE
    SYNTAX INTEGER (0..65535)
    ACCESS read-write
    STATUS optional
    DESCRIPTION
            "slave 3 power factor.this value enlagrge 100 times."
    ::= { slavethreepfC 8 }	
	
Slave3OutputEnergy1 OBJECT-TYPE
    SYNTAX INTEGER (0..65535)
    ACCESS read-write
    STATUS optional
    DESCRIPTION
            "slave 3 Output energy.this value enlagrge 10 times"
    ::= { slavethreeenA 1 }	
Slave3OutputEnergy2 OBJECT-TYPE
    SYNTAX INTEGER (0..65535)
    ACCESS read-write
    STATUS optional
    DESCRIPTION
            "slave 3 Output energy.this value enlagrge 10 times"
    ::= { slavethreeenA 2 }
Slave3OutputEnergy3 OBJECT-TYPE
    SYNTAX INTEGER (0..65535)
    ACCESS read-write
    STATUS optional
    DESCRIPTION
            "slave 3 Output energy.this value enlagrge 10 times"
    ::= { slavethreeenA 3 }
Slave3OutputEnergy4 OBJECT-TYPE
    SYNTAX INTEGER (0..65535)
    ACCESS read-write
    STATUS optional
    DESCRIPTION
            "slave 3 Output energy.this value enlagrge 10 times"
    ::= { slavethreeenA 4 }
Slave3OutputEnergy5 OBJECT-TYPE
    SYNTAX INTEGER (0..65535)
    ACCESS read-write
    STATUS optional
    DESCRIPTION
            "slave 3 Output energy.this value enlagrge 10 times"
    ::= { slavethreeenA 5 }	
Slave3OutputEnergy6 OBJECT-TYPE
    SYNTAX INTEGER (0..65535)
    ACCESS read-write
    STATUS optional
    DESCRIPTION
            "slave 3 Output energy.this value enlagrge 10 times"
    ::= { slavethreeenA 6 }
Slave31OutputEnergy7 OBJECT-TYPE
    SYNTAX INTEGER (0..65535)
    ACCESS read-write
    STATUS optional
    DESCRIPTION
            "slave 3 Output energy.this value enlagrge 10 times"
    ::= { slavethreeenA 7 }
Slave3OutputEnergy8 OBJECT-TYPE
    SYNTAX INTEGER (0..65535)
    ACCESS read-write
    STATUS optional
    DESCRIPTION
            "slave 3 Output energy.this value enlagrge 10 times"
    ::= { slavethreeenA 8 }	
		
Slave3OutputEnergy9 OBJECT-TYPE
    SYNTAX INTEGER (0..65535)
    ACCESS read-write
    STATUS optional
    DESCRIPTION
            "slave 3 Output energy.this value enlagrge 10 times"
    ::= { slavethreeenB 1 }	
Slave3OutputEnergy10 OBJECT-TYPE
    SYNTAX INTEGER (0..65535)
    ACCESS read-write
    STATUS optional
    DESCRIPTION
            "slave 3 Output energy.this value enlagrge 10 times"
    ::= { slavethreeenB 2 }
Slave3OutputEnergy11 OBJECT-TYPE
    SYNTAX INTEGER (0..65535)
    ACCESS read-write
    STATUS optional
    DESCRIPTION
            "slave 3 Output energy.this value enlagrge 10 times"
    ::= { slavethreeenB 3 }
Slave3OutputEnergy12 OBJECT-TYPE
    SYNTAX INTEGER (0..65535)
    ACCESS read-write
    STATUS optional
    DESCRIPTION
            "slave 3 Output energy.this value enlagrge 10 times"
    ::= { slavethreeenB 4 }
Slave3OutputEnergy13 OBJECT-TYPE
    SYNTAX INTEGER (0..65535)
    ACCESS read-write
    STATUS optional
    DESCRIPTION
            "slave 3 Output energy.this value enlagrge 10 times"
    ::= { slavethreeenB 5 }	
Slave3OutputEnergy14 OBJECT-TYPE
    SYNTAX INTEGER (0..65535)
    ACCESS read-write
    STATUS optional
    DESCRIPTION
            "slave 3 Output energy.this value enlagrge 10 times"
    ::= { slavethreeenB 6 }
Slave3OutputEnergy15 OBJECT-TYPE
    SYNTAX INTEGER (0..65535)
    ACCESS read-write
    STATUS optional
    DESCRIPTION
            "slave 3 Output energy.this value enlagrge 10 times"
    ::= { slavethreeenB 7 }
Slave3OutputEnergy16 OBJECT-TYPE
    SYNTAX INTEGER (0..65535)
    ACCESS read-write
    STATUS optional
    DESCRIPTION
            "slave 3 Output energy.this value enlagrge 10 times"
    ::= { slavethreeenB 8 }	
	
Slave3OutputEnergy17 OBJECT-TYPE
    SYNTAX INTEGER (0..65535)
    ACCESS read-write
    STATUS optional
    DESCRIPTION
            "slave 3 Output energy.this value enlagrge 10 times"
    ::= { slavethreeenC 1 }	
Slave3OutputEnergy18 OBJECT-TYPE
    SYNTAX INTEGER (0..65535)
    ACCESS read-write
    STATUS optional
    DESCRIPTION
            "slave 3 Output energy.this value enlagrge 10 times"
    ::= { slavethreeenC 2 }
Slave3OutputEnergy19 OBJECT-TYPE
    SYNTAX INTEGER (0..65535)
    ACCESS read-write
    STATUS optional
    DESCRIPTION
            "slave 3 Output energy.this value enlagrge 10 times"
    ::= { slavethreeenC 3 }
Slave3OutputEnergy20 OBJECT-TYPE
    SYNTAX INTEGER (0..65535)
    ACCESS read-write
    STATUS optional
    DESCRIPTION
            "slave 3 Output energy.this value enlagrge 10 times"
    ::= { slavethreeenC 4 }
Slave3OutputEnergy21 OBJECT-TYPE
    SYNTAX INTEGER (0..65535)
    ACCESS read-write
    STATUS optional
    DESCRIPTION
            "slave 3 Output energy.this value enlagrge 10 times"
    ::= { slavethreeenC 5 }	
Slave3OutputEnergy22 OBJECT-TYPE
    SYNTAX INTEGER (0..65535)
    ACCESS read-write
    STATUS optional
    DESCRIPTION
            "slave 3 Output energy.this value enlagrge 10 times"
    ::= { slavethreeenC 6 }
Slave3OutputEnergy23 OBJECT-TYPE
    SYNTAX INTEGER (0..65535)
    ACCESS read-write
    STATUS optional
    DESCRIPTION
            "slave 3 Output energy.this value enlagrge 10 times"
    ::= { slavethreeenC 7 }
Slave3OutputEnergy24  OBJECT-TYPE
    SYNTAX INTEGER (0..65535)
    ACCESS read-write
    STATUS optional
    DESCRIPTION
            "slave 3 Output energy.this value enlagrge 10 times"
    ::= { slavethreeenC 8 }	

Slave3Switch1 OBJECT-TYPE
    SYNTAX DisplayString (SIZE (255))
    ACCESS read-write
    STATUS optional
    DESCRIPTION
            "slave 3 output switch 1 ."
    ::= { slavethreeswA 1 }
Slave3Switch2 OBJECT-TYPE
    SYNTAX DisplayString (SIZE (255))
    ACCESS read-write
    STATUS optional
    DESCRIPTION
            "slave 3 output switch 2 ."
    ::= { slavethreeswA 2 }
Slave3Switch3 OBJECT-TYPE
    SYNTAX DisplayString (SIZE (255))
    ACCESS read-write
    STATUS optional
    DESCRIPTION
            "slave 3 output switch 3 ."
    ::= { slavethreeswA 3 }
Slave3Switch4 OBJECT-TYPE
    SYNTAX DisplayString (SIZE (255))
    ACCESS read-write
    STATUS optional
    DESCRIPTION
            "slave 3 output switch 4 ."
    ::= { slavethreeswA 4 }	
Slave3Switch5 OBJECT-TYPE
    SYNTAX DisplayString (SIZE (255))
    ACCESS read-write
    STATUS optional
    DESCRIPTION
            "slave 3 output switch 5 ."
    ::= { slavethreeswA 5 }
Slave3Switch6 OBJECT-TYPE
    SYNTAX DisplayString (SIZE (255))
    ACCESS read-write
    STATUS optional
    DESCRIPTION
            "slave 3 output switch 6 ."
    ::= { slavethreeswA 6 }
Slave3Switch7 OBJECT-TYPE
    SYNTAX DisplayString (SIZE (255))
    ACCESS read-write
    STATUS optional
    DESCRIPTION
            "slave 3 output switch 7 ."
    ::= { slavethreeswA 7 }
Slave3Switch8 OBJECT-TYPE
    SYNTAX DisplayString (SIZE (255))
    ACCESS read-write
    STATUS optional
    DESCRIPTION
            "slave 3 output switch 8 ."
    ::= { slavethreeswA 8 }	
		
Slave3Switch9 OBJECT-TYPE
    SYNTAX DisplayString (SIZE (255))
    ACCESS read-write
    STATUS optional
    DESCRIPTION
            "slave 3 output switch 9 ."
    ::= { slavethreeswB 1 }
Slave3Switch10 OBJECT-TYPE
    SYNTAX DisplayString (SIZE (255))
    ACCESS read-write
    STATUS optional
    DESCRIPTION
            "slave 3 output switch 10 ."
    ::= { slavethreeswB 2 }
Slave3Switch11 OBJECT-TYPE
    SYNTAX DisplayString (SIZE (255))
    ACCESS read-write
    STATUS optional
    DESCRIPTION
            "slave 3 output switch 11 ."
    ::= { slavethreeswB 3 }
Slave3Switch12 OBJECT-TYPE
    SYNTAX DisplayString (SIZE (255))
    ACCESS read-write
    STATUS optional
    DESCRIPTION
            "slave 3 output switch 12 ."
    ::= { slavethreeswB 4 }	
Slave3Switch13 OBJECT-TYPE
    SYNTAX DisplayString (SIZE (255))
    ACCESS read-write
    STATUS optional
    DESCRIPTION
            "slave 3 output switch 13 ."
    ::= { slavethreeswB 5 }
Slave3Switch14 OBJECT-TYPE
    SYNTAX DisplayString (SIZE (255))
    ACCESS read-write
    STATUS optional
    DESCRIPTION
            "slave 3 output switch 14 ."
    ::= { slavethreeswB 6 }
Slave3Switch15 OBJECT-TYPE
    SYNTAX DisplayString (SIZE (255))
    ACCESS read-write
    STATUS optional
    DESCRIPTION
            "slave 3 output switch 15 ."
    ::= { slavethreeswB 7 }
	
Slave3Switch16 OBJECT-TYPE
    SYNTAX DisplayString (SIZE (255))
    ACCESS read-write
    STATUS optional
    DESCRIPTION
            "slave 3 output switch 16 ."
    ::= { slavethreeswB 8 }	
Slave3Switch17 OBJECT-TYPE
    SYNTAX DisplayString (SIZE (255))
    ACCESS read-write
    STATUS optional
    DESCRIPTION
            " slave 3 output switch 17 ."
    ::= { slavethreeswC 1 }
Slave3Switch18 OBJECT-TYPE
    SYNTAX DisplayString (SIZE (255))
    ACCESS read-write
    STATUS optional
    DESCRIPTION
            "slave 3 output switch 18 ."
    ::= { slavethreeswC 2 }
Slave3Switch19 OBJECT-TYPE
    SYNTAX DisplayString (SIZE (255))
    ACCESS read-write
    STATUS optional
    DESCRIPTION
            "slave 3 output switch 19 ."
    ::= { slavethreeswC 3 }
Slave3Switch20 OBJECT-TYPE
    SYNTAX DisplayString (SIZE (255))
    ACCESS read-write
    STATUS optional
    DESCRIPTION
            "slave 3 output switch 20 ."
    ::= { slavethreeswC 4 }	
Slave3Switch21 OBJECT-TYPE
    SYNTAX DisplayString (SIZE (255))
    ACCESS read-write
    STATUS optional
    DESCRIPTION
            "slave 3 output switch 21 ."
    ::= { slavethreeswC 5 }
Slave3Switch22 OBJECT-TYPE
    SYNTAX DisplayString (SIZE (255))
    ACCESS read-write
    STATUS optional
    DESCRIPTION
            "slave 3 output switch 22 ."
    ::= { slavethreeswC 6 }
Slave3Switch23 OBJECT-TYPE
    SYNTAX DisplayString (SIZE (255))
    ACCESS read-write
    STATUS optional
    DESCRIPTION
            "slave 3 output switch 23 ."
    ::= { slavethreeswC 7}
Slave3Switch24 OBJECT-TYPE
    SYNTAX DisplayString (SIZE (255))
    ACCESS read-write
    STATUS optional
    DESCRIPTION
            "slave 3 output switch 24 ."
    ::= { slavethreeswC 8 }
	
Slave4VoltageL1 OBJECT-TYPE
    SYNTAX INTEGER (0..65535)
    ACCESS read-write
    STATUS optional
    DESCRIPTION
            "slave 4  votage L1."
    ::= { slavefourinto 1 }
Slave4VoltageL2 OBJECT-TYPE
    SYNTAX INTEGER (0..65535)
    ACCESS read-write
    STATUS optional
    DESCRIPTION
            "slave 4  votage L2."
    ::= { slavefourinto 2 }

Slave4CurrentL1 OBJECT-TYPE
    SYNTAX INTEGER (0..65535)
    ACCESS read-write
    STATUS optional
    DESCRIPTION
            "slave 4  current L1.this value enlagrge 10 times."
    ::= { slavefourinto 4 }	
Slave4CurrentL2 OBJECT-TYPE
    SYNTAX INTEGER (0..65535)
    ACCESS read-write
    STATUS optional
    DESCRIPTION
            "slave 4  current L2.this value enlagrge 10 times."
    ::= { slavefourinto 5 }

Slave4PowerFactorL1 OBJECT-TYPE
    SYNTAX INTEGER (0..65535)
    ACCESS read-write
    STATUS optional
    DESCRIPTION
            "slave 4  power factor L1.this value enlagrge 100 times."
    ::= { slavefourinto 7 }	
Slave4PowerFactorL2 OBJECT-TYPE
    SYNTAX INTEGER (0..65535)
    ACCESS read-write
    STATUS optional
    DESCRIPTION
            "slave 4  power factor L2.this value enlagrge 100 times."
    ::= { slavefourinto 8 }
	
Slave4EnergyL1 OBJECT-TYPE
    SYNTAX INTEGER (0..65535)
    ACCESS read-write
    STATUS optional
    DESCRIPTION
            "slave 4  energy L1..this value enlagrge 10 times."
    ::= { slavefourinto 10 }	
Slave4EnergyL2 OBJECT-TYPE
    SYNTAX INTEGER (0..65535)
    ACCESS read-write
    STATUS optional
    DESCRIPTION
            "slave 4 energy L2..this value enlagrge 10 times."
    ::= { slavefourinto 11 }
	
Slave4TemperatureOne OBJECT-TYPE
    SYNTAX INTEGER (0..65535)
    ACCESS read-write
    STATUS optional
    DESCRIPTION
            "slave 4 Temperature One ."
    ::= { slavefourtem 1 }										
Slave4TemperatureTwo OBJECT-TYPE
    SYNTAX INTEGER (0..65535)
    ACCESS read-write
    STATUS optional
    DESCRIPTION
            "slave 4 Temperature Two ."
    ::= { slavefourtem 2 }
Slave4HumidityOne OBJECT-TYPE
    SYNTAX INTEGER (0..65535)
    ACCESS read-write
    STATUS optional
    DESCRIPTION
            "slave 4 Humidity One ."
    ::= { slavefourtem 3 }										
Slave4HumidityTwo OBJECT-TYPE
    SYNTAX INTEGER (0..65535)
    ACCESS read-write
    STATUS optional
    DESCRIPTION
            "slave 4 Humidity Two ."
    ::= { slavefourtem 4 }	
	
Slave4OutputCurrent1 OBJECT-TYPE
    SYNTAX INTEGER (0..65535)
    ACCESS read-write
    STATUS optional
    DESCRIPTION
            "slave 4 current.this value enlagrge 10 times."
    ::= { slavefourcurA 1 }	
Slave4OutputCurrent2 OBJECT-TYPE
    SYNTAX INTEGER (0..65535)
    ACCESS read-write
    STATUS optional
    DESCRIPTION
            "slave 4 current.this value enlagrge 10 times."
    ::= { slavefourcurA 2 }
Slave4OutputCurrent3 OBJECT-TYPE
    SYNTAX INTEGER (0..65535)
    ACCESS read-write
    STATUS optional
    DESCRIPTION
            "slave 4 current.this value enlagrge 10 times."
    ::= { slavefourcurA 3 }	
Slave4OutputCurrent4 OBJECT-TYPE
    SYNTAX INTEGER (0..65535)
    ACCESS read-write
    STATUS optional
    DESCRIPTION
            "slave 4 current.this value enlagrge 10 times."
    ::= { slavefourcurA 4 }	
Slave4OutputCurrent5 OBJECT-TYPE
    SYNTAX INTEGER (0..65535)
    ACCESS read-write
    STATUS optional
    DESCRIPTION
            "slave 4 current.this value enlagrge 10 times."
    ::= { slavefourcurA 5 }	
Slave4OutputCurrent6 OBJECT-TYPE
    SYNTAX INTEGER (0..65535)
    ACCESS read-write
    STATUS optional
    DESCRIPTION
            "slave 4 current.this value enlagrge 10 times."
    ::= { slavefourcurA 6 }
Slave4OutputCurrent7 OBJECT-TYPE
    SYNTAX INTEGER (0..65535)
    ACCESS read-write
    STATUS optional
    DESCRIPTION
            "slave 4 current.this value enlagrge 10 times."
    ::= { slavefourcurA 7 }	
Slave4OutputCurrent8 OBJECT-TYPE
    SYNTAX INTEGER (0..65535)
    ACCESS read-write
    STATUS optional
    DESCRIPTION
            "slave 4 current.this value enlagrge 10 times."
    ::= { slavefourcurA 8 }
			
Slave4OutputCurrent9 OBJECT-TYPE
    SYNTAX INTEGER (0..65535)
    ACCESS read-write
    STATUS optional
    DESCRIPTION
            "slave 4 current.this value enlagrge 10 times."
    ::= { slavefourcurB 1 }	
Slave4OutputCurrent10 OBJECT-TYPE
    SYNTAX INTEGER (0..65535)
    ACCESS read-write
    STATUS optional
    DESCRIPTION
            "slave 4 current.this value enlagrge 10 times."
    ::= { slavefourcurB 2 }
Slave4OutputCurrent11 OBJECT-TYPE
    SYNTAX INTEGER (0..65535)
    ACCESS read-write
    STATUS optional
    DESCRIPTION
            "slave 4 current.this value enlagrge 10 times."
    ::= { slavefourcurB 3 }	
Slave4OutputCurrent12 OBJECT-TYPE
    SYNTAX INTEGER (0..65535)
    ACCESS read-write
    STATUS optional
    DESCRIPTION
            "slave 4 current.this value enlagrge 10 times."
    ::= { slavefourcurB 4 }	
Slave4OutputCurrent13 OBJECT-TYPE
    SYNTAX INTEGER (0..65535)
    ACCESS read-write
    STATUS optional
    DESCRIPTION
            "slave 4 current.this value enlagrge 10 times."
    ::= { slavefourcurB 5 }	
Slave4OutputCurrent14 OBJECT-TYPE
    SYNTAX INTEGER (0..65535)
    ACCESS read-write
    STATUS optional
    DESCRIPTION
            "slave 4 current.this value enlagrge 10 times."
    ::= { slavefourcurB 6 }
Slave4OutputCurrent15 OBJECT-TYPE
    SYNTAX INTEGER (0..65535)
    ACCESS read-write
    STATUS optional
    DESCRIPTION
            "slave 4 current.this value enlagrge 10 times."
    ::= { slavefourcurB 7 }	
Slave4OutputCurrent16 OBJECT-TYPE
    SYNTAX INTEGER (0..65535)
    ACCESS read-write
    STATUS optional
    DESCRIPTION
            "slave 4 current.this value enlagrge 10 times."
    ::= { slavefourcurB 8 }
		
Slave4OutputCurrent17 OBJECT-TYPE
    SYNTAX INTEGER (0..65535)
    ACCESS read-write
    STATUS optional
    DESCRIPTION
            "slave 4 current.this value enlagrge 10 times."
    ::= { slavefourcurC 1 }	
Slave4OutputCurrent18 OBJECT-TYPE
    SYNTAX INTEGER (0..65535)
    ACCESS read-write
    STATUS optional
    DESCRIPTION
            "slave 4 current.this value enlagrge 10 times."
    ::= { slavefourcurC 2 }
Slave4OutputCurrent19 OBJECT-TYPE
    SYNTAX INTEGER (0..65535)
    ACCESS read-write
    STATUS optional
    DESCRIPTION
            "slave 4 current.this value enlagrge 10 times."
    ::= { slavefourcurC 3 }	
Slave4OutputCurrent20 OBJECT-TYPE
    SYNTAX INTEGER (0..65535)
    ACCESS read-write
    STATUS optional
    DESCRIPTION
            "slave 4 current.this value enlagrge 10 times."
    ::= { slavefourcurC 4 }
		
Slave4OutputCurrent21 OBJECT-TYPE
    SYNTAX INTEGER (0..65535)
    ACCESS read-write
    STATUS optional
    DESCRIPTION
            "slave 4 current.this value enlagrge 10 times."
    ::= { slavefourcurC 5 }	
Slave4OutputCurrent22 OBJECT-TYPE
    SYNTAX INTEGER (0..65535)
    ACCESS read-write
    STATUS optional
    DESCRIPTION
            "slave 4 current.this value enlagrge 10 times."
    ::= { slavefourcurC 6 }
Slave4OutputCurrent23 OBJECT-TYPE
    SYNTAX INTEGER (0..65535)
    ACCESS read-write
    STATUS optional
    DESCRIPTION
            "slave 4 current.this value enlagrge 10 times."
    ::= { slavefourcurC 7 }	
Slave4OutputCurrent24 OBJECT-TYPE
    SYNTAX INTEGER (0..65535)
    ACCESS read-write
    STATUS optional
    DESCRIPTION
            "slave 4 current.this value enlagrge 10 times."
    ::= { slavefourcurC 8 }													
	
Slave4OutputPF1 OBJECT-TYPE
    SYNTAX INTEGER (0..65535)
    ACCESS read-write
    STATUS optional
    DESCRIPTION
            "slave 4 power factor.this value enlagrge 100 times."
    ::= { slavefourpfA 1 }	
Slave4OutputPF2 OBJECT-TYPE
    SYNTAX INTEGER (0..65535)
    ACCESS read-write
    STATUS optional
    DESCRIPTION
            "slave 4 power factor.this value enlagrge 100 times."
    ::= { slavefourpfA 2 }
Slave4OutputPF3 OBJECT-TYPE
    SYNTAX INTEGER (0..65535)
    ACCESS read-write
    STATUS optional
    DESCRIPTION
            "slave 4 power factor.this value enlagrge 100 times."
    ::= { slavefourpfA 3 }
Slave4OutputPF4 OBJECT-TYPE
    SYNTAX INTEGER (0..65535)
    ACCESS read-write
    STATUS optional
    DESCRIPTION
            "slave 4 power factor.this value enlagrge 100 times."
    ::= { slavefourpfA 4 }
Slave4OutputPF5 OBJECT-TYPE
    SYNTAX INTEGER (0..65535)
    ACCESS read-write
    STATUS optional
    DESCRIPTION
            "slave 4 power factor.this value enlagrge 100 times."
    ::= { slavefourpfA 5 }	
Slave4OutputPF6 OBJECT-TYPE
    SYNTAX INTEGER (0..65535)
    ACCESS read-write
    STATUS optional
    DESCRIPTION
            "slave 4 power factor.this value enlagrge 100 times."
    ::= { slavefourpfA 6 }
Slave4OutputPF7 OBJECT-TYPE
    SYNTAX INTEGER (0..65535)
    ACCESS read-write
    STATUS optional
    DESCRIPTION
            "slave 4 power factor.this value enlagrge 100 times."
    ::= { slavefourpfA 7 }
Slave4OutputPF8 OBJECT-TYPE
    SYNTAX INTEGER (0..65535)
    ACCESS read-write
    STATUS optional
    DESCRIPTION
            "slave 4 power factor.this value enlagrge 100 times."
    ::= { slavefourpfA 8 }
		
Slave4OutputPF9 OBJECT-TYPE
    SYNTAX INTEGER (0..65535)
    ACCESS read-write
    STATUS optional
    DESCRIPTION
            "slave 4 power factor.this value enlagrge 100 times."
    ::= { slavefourpfB 1 }	
Slave4OutputPF10 OBJECT-TYPE
    SYNTAX INTEGER (0..65535)
    ACCESS read-write
    STATUS optional
    DESCRIPTION
            "slave 4 power factor.this value enlagrge 100 times."
    ::= { slavefourpfB 2 }
Slave4OutputPF11 OBJECT-TYPE
    SYNTAX INTEGER (0..65535)
    ACCESS read-write
    STATUS optional
    DESCRIPTION
            "slave 4 power factor.this value enlagrge 100 times."
    ::= { slavefourpfB 3 }
Slave4OutputPF12 OBJECT-TYPE
    SYNTAX INTEGER (0..65535)
    ACCESS read-write
    STATUS optional
    DESCRIPTION
            "slave 4 power factor.this value enlagrge 100 times."
    ::= { slavefourpfB 4 }
Slave4OutputPF13 OBJECT-TYPE
    SYNTAX INTEGER (0..65535)
    ACCESS read-write
    STATUS optional
    DESCRIPTION
            "slave 4 power factor.this value enlagrge 100 times."
    ::= { slavefourpfB 5 }	
Slave4OutputPF14 OBJECT-TYPE
    SYNTAX INTEGER (0..65535)
    ACCESS read-write
    STATUS optional
    DESCRIPTION
            "slave 4 power factor.this value enlagrge 100 times."
    ::= { slavefourpfB 6 }
Slave4OutputPF15 OBJECT-TYPE
    SYNTAX INTEGER (0..65535)
    ACCESS read-write
    STATUS optional
    DESCRIPTION
            "slave 4 power factor.this value enlagrge 100 times."
    ::= { slavefourpfB 7 }
Slave4OutputPF16 OBJECT-TYPE
    SYNTAX INTEGER (0..65535)
    ACCESS read-write
    STATUS optional
    DESCRIPTION
            "slave 4 power factor.this value enlagrge 100 times."
    ::= { slavefourpfB 8 }
		
Slave4OutputPF17 OBJECT-TYPE
    SYNTAX INTEGER (0..65535)
    ACCESS read-write
    STATUS optional
    DESCRIPTION
            "slave 4 power factor.this value enlagrge 100 times."
    ::= { slavefourpfC 1 }	
Slave4OutputPF18 OBJECT-TYPE
    SYNTAX INTEGER (0..65535)
    ACCESS read-write
    STATUS optional
    DESCRIPTION
            "slave 4 power factor.this value enlagrge 100 times."
    ::= { slavefourpfC 2 }
Slave4OutputPF19 OBJECT-TYPE
    SYNTAX INTEGER (0..65535)
    ACCESS read-write
    STATUS optional
    DESCRIPTION
            "slave 3 power factor.this value enlagrge 100 times."
    ::= { slavefourpfC 3 }
Slave4OutputPF20 OBJECT-TYPE
    SYNTAX INTEGER (0..65535)
    ACCESS read-write
    STATUS optional
    DESCRIPTION
            "slave 4 power factor.this value enlagrge 100 times."
    ::= { slavefourpfC 4 }
Slave4OutputPF21 OBJECT-TYPE
    SYNTAX INTEGER (0..65535)
    ACCESS read-write
    STATUS optional
    DESCRIPTION
            "slave 4 power factor.this value enlagrge 100 times."
    ::= { slavefourpfC 5 }	
Slave4OutputPF22 OBJECT-TYPE
    SYNTAX INTEGER (0..65535)
    ACCESS read-write
    STATUS optional
    DESCRIPTION
            "slave 4 power factor.this value enlagrge 100 times."
    ::= { slavefourpfC 6 }
Slave4OutputPF23 OBJECT-TYPE
    SYNTAX INTEGER (0..65535)
    ACCESS read-write
    STATUS optional
    DESCRIPTION
            "slave 4 power factor.this value enlagrge 100 times."
    ::= { slavefourpfC 7 }
Slave4OutputPF24 OBJECT-TYPE
    SYNTAX INTEGER (0..65535)
    ACCESS read-write
    STATUS optional
    DESCRIPTION
            "slave 4 power factor.this value enlagrge 100 times."
    ::= { slavefourpfC 8 }	
	
Slave4OutputEnergy1 OBJECT-TYPE
    SYNTAX INTEGER (0..65535)
    ACCESS read-write
    STATUS optional
    DESCRIPTION
            "slave 4 Output energy.this value enlagrge 10 times"
    ::= { slavefourenA 1 }	
Slave4OutputEnergy2 OBJECT-TYPE
    SYNTAX INTEGER (0..65535)
    ACCESS read-write
    STATUS optional
    DESCRIPTION
            "slave 4 Output energy.this value enlagrge 10 times"
    ::= { slavefourenA 2 }
Slave4OutputEnergy3 OBJECT-TYPE
    SYNTAX INTEGER (0..65535)
    ACCESS read-write
    STATUS optional
    DESCRIPTION
            "slave 4 Output energy.this value enlagrge 10 times"
    ::= { slavefourenA 3 }
Slave4OutputEnergy4 OBJECT-TYPE
    SYNTAX INTEGER (0..65535)
    ACCESS read-write
    STATUS optional
    DESCRIPTION
            "slave 4 Output energy.this value enlagrge 10 times"
    ::= { slavefourenA 4 }
Slave4OutputEnergy5 OBJECT-TYPE
    SYNTAX INTEGER (0..65535)
    ACCESS read-write
    STATUS optional
    DESCRIPTION
            "slave 4 Output energy.this value enlagrge 10 times"
    ::= { slavefourenA 5 }	
Slave4OutputEnergy6 OBJECT-TYPE
    SYNTAX INTEGER (0..65535)
    ACCESS read-write
    STATUS optional
    DESCRIPTION
            "slave 4 Output energy.this value enlagrge 10 times"
    ::= { slavefourenA 6 }
Slave41OutputEnergy7 OBJECT-TYPE
    SYNTAX INTEGER (0..65535)
    ACCESS read-write
    STATUS optional
    DESCRIPTION
            "slave 4 Output energy.this value enlagrge 10 times"
    ::= { slavefourenA 7 }
Slave4OutputEnergy8 OBJECT-TYPE
    SYNTAX INTEGER (0..65535)
    ACCESS read-write
    STATUS optional
    DESCRIPTION
            "slave 4 Output energy.this value enlagrge 10 times"
    ::= { slavefourenA 8 }	
		
Slave4OutputEnergy9 OBJECT-TYPE
    SYNTAX INTEGER (0..65535)
    ACCESS read-write
    STATUS optional
    DESCRIPTION
            "slave 4 Output energy.this value enlagrge 10 times"
    ::= { slavefourenB 1 }	
Slave4OutputEnergy10 OBJECT-TYPE
    SYNTAX INTEGER (0..65535)
    ACCESS read-write
    STATUS optional
    DESCRIPTION
            "slave 4 Output energy.this value enlagrge 10 times"
    ::= { slavefourenB 2 }
Slave4OutputEnergy11 OBJECT-TYPE
    SYNTAX INTEGER (0..65535)
    ACCESS read-write
    STATUS optional
    DESCRIPTION
            "slave 4 Output energy.this value enlagrge 10 times"
    ::= { slavefourenB 3 }
Slave4OutputEnergy12 OBJECT-TYPE
    SYNTAX INTEGER (0..65535)
    ACCESS read-write
    STATUS optional
    DESCRIPTION
            "slave 4 Output energy.this value enlagrge 10 times"
    ::= { slavefourenB 4 }
Slave4OutputEnergy13 OBJECT-TYPE
    SYNTAX INTEGER (0..65535)
    ACCESS read-write
    STATUS optional
    DESCRIPTION
            "slave 4 Output energy.this value enlagrge 10 times"
    ::= { slavefourenB 5 }	
Slave4OutputEnergy14 OBJECT-TYPE
    SYNTAX INTEGER (0..65535)
    ACCESS read-write
    STATUS optional
    DESCRIPTION
            "slave 4 Output energy.this value enlagrge 10 times"
    ::= { slavefourenB 6 }
Slave4OutputEnergy15 OBJECT-TYPE
    SYNTAX INTEGER (0..65535)
    ACCESS read-write
    STATUS optional
    DESCRIPTION
            "slave 4 Output energy.this value enlagrge 10 times"
    ::= { slavefourenB 7 }
Slave4OutputEnergy16 OBJECT-TYPE
    SYNTAX INTEGER (0..65535)
    ACCESS read-write
    STATUS optional
    DESCRIPTION
            "slave 4 Output energy.this value enlagrge 10 times"
    ::= { slavefourenB 8 }	
	
Slave4OutputEnergy17 OBJECT-TYPE
    SYNTAX INTEGER (0..65535)
    ACCESS read-write
    STATUS optional
    DESCRIPTION
            "slave 4 Output energy.this value enlagrge 10 times"
    ::= { slavefourenC 1 }	
Slave4OutputEnergy18 OBJECT-TYPE
    SYNTAX INTEGER (0..65535)
    ACCESS read-write
    STATUS optional
    DESCRIPTION
            "slave 4 Output energy.this value enlagrge 10 times"
    ::= { slavefourenC 2 }
Slave4OutputEnergy19 OBJECT-TYPE
    SYNTAX INTEGER (0..65535)
    ACCESS read-write
    STATUS optional
    DESCRIPTION
            "slave 4 Output energy.this value enlagrge 10 times"
    ::= { slavefourenC 3 }
Slave4OutputEnergy20 OBJECT-TYPE
    SYNTAX INTEGER (0..65535)
    ACCESS read-write
    STATUS optional
    DESCRIPTION
            "slave 4 Output energy.this value enlagrge 10 times"
    ::= { slavefourenC 4 }
Slave4OutputEnergy21 OBJECT-TYPE
    SYNTAX INTEGER (0..65535)
    ACCESS read-write
    STATUS optional
    DESCRIPTION
            "slave 4 Output energy.this value enlagrge 10 times"
    ::= { slavefourenC 5 }	
Slave4OutputEnergy22 OBJECT-TYPE
    SYNTAX INTEGER (0..65535)
    ACCESS read-write
    STATUS optional
    DESCRIPTION
            "slave 4 Output energy.this value enlagrge 10 times"
    ::= { slavefourenC 6 }
Slave4OutputEnergy23 OBJECT-TYPE
    SYNTAX INTEGER (0..65535)
    ACCESS read-write
    STATUS optional
    DESCRIPTION
            "slave 4 Output energy.this value enlagrge 10 times"
    ::= { slavefourenC 7 }
Slave4OutputEnergy24  OBJECT-TYPE
    SYNTAX INTEGER (0..65535)
    ACCESS read-write
    STATUS optional
    DESCRIPTION
            "slave 4 Output energy.this value enlagrge 10 times"
    ::= { slavefourenC 8 }	

Slave4Switch1 OBJECT-TYPE
    SYNTAX DisplayString (SIZE (255))
    ACCESS read-write
    STATUS optional
    DESCRIPTION
            "slave 4 output switch 1 ."
    ::= { slavefourswA 1 }
Slave4Switch2 OBJECT-TYPE
    SYNTAX DisplayString (SIZE (255))
    ACCESS read-write
    STATUS optional
    DESCRIPTION
            "slave 4 output switch 2 ."
    ::= { slavefourswA 2 }
Slave4Switch3 OBJECT-TYPE
    SYNTAX DisplayString (SIZE (255))
    ACCESS read-write
    STATUS optional
    DESCRIPTION
            "slave 4 output switch 3 ."
    ::= { slavefourswA 3 }
Slave4Switch4 OBJECT-TYPE
    SYNTAX DisplayString (SIZE (255))
    ACCESS read-write
    STATUS optional
    DESCRIPTION
            "slave 4 output switch 4 ."
    ::= { slavefourswA 4 }	
Slave4Switch5 OBJECT-TYPE
    SYNTAX DisplayString (SIZE (255))
    ACCESS read-write
    STATUS optional
    DESCRIPTION
            "slave 4 output switch 5 ."
    ::= { slavefourswA 5 }
Slave4Switch6 OBJECT-TYPE
    SYNTAX DisplayString (SIZE (255))
    ACCESS read-write
    STATUS optional
    DESCRIPTION
            "slave 4 output switch 6 ."
    ::= { slavefourswA 6 }
Slave4Switch7 OBJECT-TYPE
    SYNTAX DisplayString (SIZE (255))
    ACCESS read-write
    STATUS optional
    DESCRIPTION
            "slave 4 output switch 7 ."
    ::= { slavefourswA 7 }
Slave4Switch8 OBJECT-TYPE
    SYNTAX DisplayString (SIZE (255))
    ACCESS read-write
    STATUS optional
    DESCRIPTION
            "slave 4 output switch 8 ."
    ::= { slavefourswA 8 }	
		
Slave4Switch9 OBJECT-TYPE
    SYNTAX DisplayString (SIZE (255))
    ACCESS read-write
    STATUS optional
    DESCRIPTION
            "slave 4 output switch 9 ."
    ::= { slavefourswB 1 }
Slave4Switch10 OBJECT-TYPE
    SYNTAX DisplayString (SIZE (255))
    ACCESS read-write
    STATUS optional
    DESCRIPTION
            "slave 4 output switch 10 ."
    ::= { slavefourswB 2 }
Slave4Switch11 OBJECT-TYPE
    SYNTAX DisplayString (SIZE (255))
    ACCESS read-write
    STATUS optional
    DESCRIPTION
            "slave 4 output switch 11 ."
    ::= { slavefourswB 3 }
Slave4Switch12 OBJECT-TYPE
    SYNTAX DisplayString (SIZE (255))
    ACCESS read-write
    STATUS optional
    DESCRIPTION
            "slave 4 output switch 12 ."
    ::= { slavefourswB 4 }	
Slave4Switch13 OBJECT-TYPE
    SYNTAX DisplayString (SIZE (255))
    ACCESS read-write
    STATUS optional
    DESCRIPTION
            "slave 4 output switch 13 ."
    ::= { slavefourswB 5 }
Slave4Switch14 OBJECT-TYPE
    SYNTAX DisplayString (SIZE (255))
    ACCESS read-write
    STATUS optional
    DESCRIPTION
            "slave 4 output switch 14 ."
    ::= { slavefourswB 6 }
Slave4Switch15 OBJECT-TYPE
    SYNTAX DisplayString (SIZE (255))
    ACCESS read-write
    STATUS optional
    DESCRIPTION
            "slave 4 output switch 15 ."
    ::= { slavefourswB 7 }
	
Slave4Switch16 OBJECT-TYPE
    SYNTAX DisplayString (SIZE (255))
    ACCESS read-write
    STATUS optional
    DESCRIPTION
            "slave 4 output switch 16 ."
    ::= { slavefourswB 8 }	
Slave4Switch17 OBJECT-TYPE
    SYNTAX DisplayString (SIZE (255))
    ACCESS read-write
    STATUS optional
    DESCRIPTION
            " slave 4 output switch 17 ."
    ::= { slavefourswC 1 }
Slave4Switch18 OBJECT-TYPE
    SYNTAX DisplayString (SIZE (255))
    ACCESS read-write
    STATUS optional
    DESCRIPTION
            "slave 4 output switch 18 ."
    ::= { slavefourswC 2 }
Slave4Switch19 OBJECT-TYPE
    SYNTAX DisplayString (SIZE (255))
    ACCESS read-write
    STATUS optional
    DESCRIPTION
            "slave 4 output switch 19 ."
    ::= { slavefourswC 3 }
Slave4Switch20 OBJECT-TYPE
    SYNTAX DisplayString (SIZE (255))
    ACCESS read-write
    STATUS optional
    DESCRIPTION
            "slave 4 output switch 20 ."
    ::= { slavefourswC 4 }	
Slave4Switch21 OBJECT-TYPE
    SYNTAX DisplayString (SIZE (255))
    ACCESS read-write
    STATUS optional
    DESCRIPTION
            "slave 4 output switch 21 ."
    ::= { slavefourswC 5 }
Slave4Switch22 OBJECT-TYPE
    SYNTAX DisplayString (SIZE (255))
    ACCESS read-write
    STATUS optional
    DESCRIPTION
            "slave 4 output switch 22 ."
    ::= { slavefourswC 6 }
Slave4Switch23 OBJECT-TYPE
    SYNTAX DisplayString (SIZE (255))
    ACCESS read-write
    STATUS optional
    DESCRIPTION
            "slave 4 output switch 23 ."
    ::= { slavefourswC 7}
Slave4Switch24 OBJECT-TYPE
    SYNTAX DisplayString (SIZE (255))
    ACCESS read-write
    STATUS optional
    DESCRIPTION
            "slave 4 output switch 24 ."
    ::= { slavefourswC 8 }



END
