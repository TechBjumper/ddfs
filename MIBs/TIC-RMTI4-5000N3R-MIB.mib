-- Toshiba MIB
-- UPS MIB for Toshiba Uninterruptible Power Supplies
--
--{iso(1) org(3) dod(6) internet(1) private(4) enterprises(1) toshiba(186) 
-- equ(1) equups(19) ticups(2) rmti4 (5) ups5000N3R(6)}
--=============================================================================

TIC-RMTI4-5000N3R-MIB DEFINITIONS ::= BEGIN

--=============================================================================
-- Update : March 31, 2016
-- By     : Edwin Rubio, Toshiba International Corp.
-- For    : 5000 N3R First Draft Mib
--=============================================================================

IMPORTS
  DisplayString, TimeStamp, TimeInterval, TestAndIncr, AutonomousType
    FROM SNMPv2-TC
  enterprises
    FROM RFC1155-SMI
  OBJECT-TYPE
    FROM RFC-1212
  TRAP-TYPE
    FROM RFC-1215;

PositiveInteger    ::= INTEGER (0..2147483647)
NonNegativeInteger ::= INTEGER (0..2147483647)

toshiba      OBJECT IDENTIFIER ::= { enterprises 186 }
equ          OBJECT IDENTIFIER ::= { toshiba 1 }
equUPS       OBJECT IDENTIFIER ::= { equ 19 }
ticUPS       OBJECT IDENTIFIER ::= { equUPS 2 }
rmti4        OBJECT IDENTIFIER ::= { ticUPS 5 }
ups5000N3R      OBJECT IDENTIFIER ::= { rmti4 6 }

upsIdent     OBJECT IDENTIFIER ::= { ups5000N3R 1 }
upsInput     OBJECT IDENTIFIER ::= { ups5000N3R 2 }
upsOutput    OBJECT IDENTIFIER ::= { ups5000N3R 3 }
upsBypass    OBJECT IDENTIFIER ::= { ups5000N3R 4 }
upsDCBus     OBJECT IDENTIFIER ::= { ups5000N3R 5 }
upsBattery   OBJECT IDENTIFIER ::= { ups5000N3R 6 }
upsStsCtlCfg OBJECT IDENTIFIER ::= { ups5000N3R 7 }
upsHistory   OBJECT IDENTIFIER ::= { ups5000N3R 8 }
upsDisplay   OBJECT IDENTIFIER ::= { ups5000N3R 9 }
upsAlarm     OBJECT IDENTIFIER ::= { ups5000N3R 10 }
upsPassword  OBJECT IDENTIFIER ::= { ups5000N3R 11 }
upsTrap      OBJECT IDENTIFIER ::= { ups5000N3R 12 }

-- ===========================================================================
-- upsIdent - RMTI4 Group 1
-- The UPS Identification Group
-- ===========================================================================

upsIdentManufacturer OBJECT-TYPE
    SYNTAX DisplayString (SIZE (0..16))
    ACCESS read-only
    STATUS mandatory
    DESCRIPTION
        "The name of the UPS manufacturer."
    ::= { upsIdent 1 }

upsIdentTypeform OBJECT-TYPE
    SYNTAX DisplayString (SIZE(0..16))
    ACCESS read-only
    STATUS mandatory
    DESCRIPTION
        "The UPS Typeform."
    ::= { upsIdent 2 }

upsIdentSerialNumber OBJECT-TYPE
    SYNTAX DisplayString (SIZE(0..16))
    ACCESS read-only
    STATUS mandatory
    DESCRIPTION
        "The UPS Serial Number."
    ::= { upsIdent 3 }

upsIdentSysName OBJECT-TYPE
    SYNTAX DisplayString (SIZE(0..16))
    ACCESS read-write
    STATUS mandatory
    DESCRIPTION
        "A string identifying the UPS. This object should be
         set by the administrator."
    ::= { upsIdent 4 }

upsIdentAttachedDevices OBJECT-TYPE
    SYNTAX DisplayString (SIZE(0..16))
    ACCESS read-write
    STATUS mandatory
    DESCRIPTION
        "A string identifying the devices attached to the
         output(s) of the UPS. This object should be set by
         the administrator."
    ::= { upsIdent 5 }

upsIdentInstallationDate OBJECT-TYPE
    SYNTAX DisplayString (SIZE(8))
    ACCESS read-write
    STATUS mandatory
    DESCRIPTION
        "The UPS installation date in YYYYMMDD format."
    ::= { upsIdent 6 }

-- ===========================================================================
-- upsInput - RMTI4 Group 2
-- The UPS Input Data Group 
-- ===========================================================================

upsInputNumofPhases OBJECT-TYPE
    SYNTAX INTEGER
    ACCESS read-only
    STATUS mandatory
    DESCRIPTION
        "The number of input lines."
    ::= { upsInput 1 }
	
upsInputLLVoltageAB OBJECT-TYPE
    SYNTAX INTEGER
    UNITS  "0.1 RMS Volts"
    ACCESS read-only
    STATUS mandatory
    DESCRIPTION
        "The input line to line voltage for AB in RMS volts."
    ::= { upsInput 2 }

upsInputLLVoltageBC OBJECT-TYPE
    SYNTAX INTEGER
    UNITS  "0.1 RMS Volts"
    ACCESS read-only
    STATUS mandatory
    DESCRIPTION
        "The input line to line voltage for BC in RMS volts."
    ::= { upsInput 3 }

upsInputLLVoltageCA OBJECT-TYPE
    SYNTAX INTEGER
    UNITS  "0.1 RMS Volts"
    ACCESS read-only
    STATUS mandatory
    DESCRIPTION
        "The input line to line voltage for CA in RMS volts."
    ::= { upsInput 4 }

upsInputLNVoltageAN OBJECT-TYPE
    SYNTAX INTEGER
    UNITS  "0.1 RMS Volts"
    ACCESS read-only
    STATUS mandatory
    DESCRIPTION
        "The input line to neutral voltage for AN in RMS volts."
    ::= { upsInput 5 }

upsInputLNVoltageBN OBJECT-TYPE
    SYNTAX INTEGER
    UNITS  "0.1 RMS Volts"
    ACCESS read-only
    STATUS mandatory
    DESCRIPTION
        "The input line to neutral voltage for BN in RMS volts."
    ::= { upsInput 6 }

upsInputLNVoltageCN OBJECT-TYPE
    SYNTAX INTEGER
    UNITS  "0.1 RMS Volts"
    ACCESS read-only
    STATUS mandatory
    DESCRIPTION
        "The input line to neutral voltage for CN in RMS volts."
    ::= { upsInput 7 }
	
upsInputCurrentPhaseA OBJECT-TYPE
    SYNTAX INTEGER
    UNITS  "0.1 Amp"
    ACCESS read-only
    STATUS mandatory
    DESCRIPTION
        "The input phase current for phase A in amps."
    ::= { upsInput 8 }

upsInputCurrentPhaseB OBJECT-TYPE
    SYNTAX INTEGER
    UNITS  "0.1 Amp"
    ACCESS read-only
    STATUS mandatory
    DESCRIPTION
        "The input phase current for phase B in amps."
    ::= { upsInput 9 }

upsInputCurrentPhaseC OBJECT-TYPE
    SYNTAX INTEGER
    UNITS  "0.1 Amp"
    ACCESS read-only
    STATUS mandatory
    DESCRIPTION
        "The input phase current for phase C in amps."
    ::= { upsInput 10 }	

upsInputFrequency OBJECT-TYPE
    SYNTAX INTEGER
    UNITS  "0.1 Hertz"
    ACCESS read-only
    STATUS mandatory
    DESCRIPTION
        "The input frequency in Hertz."
    ::= { upsInput 11 }
	
upsInputLLVoltagePercentA OBJECT-TYPE
    SYNTAX INTEGER
    UNITS  "Percent"
    ACCESS read-only
    STATUS mandatory
    DESCRIPTION
        "The input voltage for phase A in percent."
    ::= { upsInput 12 }

upsInputLLVoltagePercentB OBJECT-TYPE
    SYNTAX INTEGER
    UNITS  "Percent"
    ACCESS read-only
    STATUS mandatory
    DESCRIPTION
        "The input voltage for phase B in percent."
    ::= { upsInput 13 }

upsInputLLVoltagePercentC OBJECT-TYPE
    SYNTAX INTEGER
    UNITS  "Percent"
    ACCESS read-only
    STATUS mandatory
    DESCRIPTION
        "The input voltage for phase C in percent."
    ::= { upsInput 14 }

upsInputCurrentPercentA OBJECT-TYPE
    SYNTAX INTEGER
    UNITS  "0.1 PERCENT"
    ACCESS read-only
    STATUS mandatory
    DESCRIPTION
        "The input phase current for phase A in percent."
    ::= { upsInput 15 }

upsInputCurrentPercentB OBJECT-TYPE
    SYNTAX INTEGER
    UNITS  "0.1 PERCENT"
    ACCESS read-only
    STATUS mandatory
    DESCRIPTION
        "The input phase current for phase B in percent."
    ::= { upsInput 16 }

upsInputCurrentPercentC OBJECT-TYPE
    SYNTAX INTEGER
    UNITS  "0.1 PERCENT"
    ACCESS read-only
    STATUS mandatory
    DESCRIPTION
        "The input phase current for phase C in percent."
    ::= { upsInput 17 }

upsInputRatedLLVoltage OBJECT-TYPE
    SYNTAX INTEGER
    UNITS  "Voltage"
    ACCESS read-write
    STATUS mandatory
    DESCRIPTION
        "The rated input line to line voltage."
    ::= { upsInput 18 }

upsInputRatedLNVoltage OBJECT-TYPE
    SYNTAX INTEGER
    UNITS  "Voltage"
    ACCESS read-write
    STATUS mandatory
    DESCRIPTION
        "The rated input line to neutral voltage."
    ::= { upsInput 19 }

upsInputRatedCurrent OBJECT-TYPE
    SYNTAX INTEGER
    UNITS  "Amp"
    ACCESS read-only
    STATUS mandatory
    DESCRIPTION
        "The rated input line to neutral voltage."
    ::= { upsInput 20 }

upsInputRatedFrequency OBJECT-TYPE
    SYNTAX INTEGER
    UNITS  "0.1 Hertz"
    ACCESS read-only
    STATUS mandatory
    DESCRIPTION
        "The input rated frequency in Hertz."
    ::= { upsInput 21 }

upsInputRatedActivePower OBJECT-TYPE
    SYNTAX INTEGER
    UNITS  "watt"
    ACCESS read-only
    STATUS mandatory
    DESCRIPTION
        "The rated input power in watt."
    ::= { upsInput 22 }

upsInputRatedApperentPower OBJECT-TYPE
    SYNTAX INTEGER
    UNITS  "Volt-Amp"
    ACCESS read-only
    STATUS mandatory
    DESCRIPTION
        "The rated input power in volt-amp."
    ::= { upsInput 23 }

-- ===========================================================================
-- upsOutput - RMTI4 Group 3
-- The UPS Output Data Group
-- ===========================================================================

upsOutputNumOfPhases OBJECT-TYPE
    SYNTAX INTEGER
    ACCESS read-only
    STATUS mandatory
    DESCRIPTION
        "The number of output line"
    ::= { upsOutput 1 }

upsOutputLLVoltageAB OBJECT-TYPE
    SYNTAX INTEGER
    UNITS  "0.1 RMS Volts"
    ACCESS read-only
    STATUS mandatory
    DESCRIPTION
        "The Output line to line voltage for AB in RMS volts."
    ::= { upsOutput 2 }

upsOutputLLVoltageBC OBJECT-TYPE
    SYNTAX INTEGER
    UNITS  "0.1 RMS Volts"
    ACCESS read-only
    STATUS mandatory
    DESCRIPTION
        "The Output line to line voltage for BC in RMS volts."
    ::= { upsOutput 3 }

upsOutputLLVoltageCA OBJECT-TYPE
    SYNTAX INTEGER
    UNITS  "0.1 RMS Volts"
    ACCESS read-only
    STATUS mandatory
    DESCRIPTION
        "The Output line to line voltage for CA in RMS volts."
    ::= { upsOutput 4 }

upsOutputLNVoltageAN OBJECT-TYPE
    SYNTAX INTEGER
    UNITS  "0.1 RMS Volts"
    ACCESS read-only
    STATUS mandatory
    DESCRIPTION
        "The Output line to neutral voltage for AN in RMS volts."
    ::= { upsOutput 5 }

upsOutputLNVoltageBN OBJECT-TYPE
    SYNTAX INTEGER
    UNITS  "0.1 RMS Volts"
    ACCESS read-only
    STATUS mandatory
    DESCRIPTION
        "The Output line to neutral voltage for BN in RMS volts."
    ::= { upsOutput 6 }

upsOutputLNVoltageCN OBJECT-TYPE
    SYNTAX INTEGER
    UNITS  "0.1 RMS Volts"
    ACCESS read-only
    STATUS mandatory
    DESCRIPTION
        "The Output line to neutral voltage for CN in RMS volts."
    ::= { upsOutput 7 }

upsOutputCurrentPhaseA OBJECT-TYPE
    SYNTAX INTEGER
    UNITS  "0.1 Amp"
    ACCESS read-only
    STATUS mandatory
    DESCRIPTION
        "The Output phase current for phase A in amps."
    ::= { upsOutput 8 }

upsOutputCurrentPhaseB OBJECT-TYPE
    SYNTAX INTEGER
    UNITS  "0.1 Amp"
    ACCESS read-only
    STATUS mandatory
    DESCRIPTION
        "The Output phase current for phase B in amps."
    ::= { upsOutput 9 }

upsOutputCurrentPhaseC OBJECT-TYPE
    SYNTAX INTEGER
    UNITS  "0.1 Amp"
    ACCESS read-only
    STATUS mandatory
    DESCRIPTION
        "The Output phase current for phase C in amps."
    ::= { upsOutput 10 }

upsOutputFrequency OBJECT-TYPE
    SYNTAX INTEGER
    UNITS  "0.1 Hertz"
    ACCESS read-only
    STATUS mandatory
    DESCRIPTION
        "The Output frequency in Hertz."
    ::= { upsOutput 11 }

upsOutputTotalActivePower  OBJECT-TYPE
    SYNTAX INTEGER
    UNITS  "0.1 Kilowatt"
    ACCESS read-only
    STATUS mandatory
    DESCRIPTION
        "The total Output power for in Kilowatts."
    ::= { upsOutput 12 }

upsOutputVoltagePercentA OBJECT-TYPE
    SYNTAX INTEGER
    UNITS  "Percent"
    ACCESS read-only
    STATUS mandatory
    DESCRIPTION
        "The Output voltage for Phase A in percent."
    ::= { upsOutput 13 }

upsOutputVoltagePercentB OBJECT-TYPE
    SYNTAX INTEGER
    UNITS  "Percent"
    ACCESS read-only
    STATUS mandatory
    DESCRIPTION
        "The Output voltage for Phase B in percent."
    ::= { upsOutput 14 }

upsOutputVoltagePercentC OBJECT-TYPE
    SYNTAX INTEGER
    UNITS  "Percent"
    ACCESS read-only
    STATUS mandatory
    DESCRIPTION
        "The Output voltage for Phase C in percent."
    ::= { upsOutput 15 }

upsOutputCurrentPercentA OBJECT-TYPE
    SYNTAX INTEGER
    UNITS  "PERCENT"
    ACCESS read-only
    STATUS mandatory
    DESCRIPTION
        "The Output current for phase A in percent."
    ::= { upsOutput 16 }

upsOutputCurrentPercentB OBJECT-TYPE
    SYNTAX INTEGER
    UNITS  "PERCENT"
    ACCESS read-only
    STATUS mandatory
    DESCRIPTION
        "The Output current for phase B in percent."
    ::= { upsOutput 17 }

upsOutputCurrentPercentC OBJECT-TYPE
    SYNTAX INTEGER
    UNITS  "PERCENT"
    ACCESS read-only
    STATUS mandatory
    DESCRIPTION
        "The Output current for phase C in percent."
    ::= { upsOutput 18 }

upsOutputTotalActivePowerPercent  OBJECT-TYPE
    SYNTAX INTEGER
    UNITS  "Percent"
    ACCESS read-only
    STATUS mandatory
    DESCRIPTION
        "The total Output power (Watt) in percent."
    ::= { upsOutput 19 }

upsOutputPowerFactor OBJECT-TYPE
    SYNTAX INTEGER       
    UNITS  "0.01"
    ACCESS read-only
    STATUS mandatory
    DESCRIPTION
        "The Output power factor."
    ::= { upsOutput 20 }

upsOutputRatedPowerFactor OBJECT-TYPE
    SYNTAX INTEGER    
    UNITS  "0.01"
    ACCESS read-only
    STATUS mandatory
    DESCRIPTION
        "The Output rated power factor."
    ::= { upsOutput 21 }

upsOutputRatedLLVoltage OBJECT-TYPE
    SYNTAX INTEGER
    UNITS  "Voltage"
    ACCESS read-write
    STATUS mandatory
    DESCRIPTION
        "The rated output line to line voltage."
    ::= { upsOutput 22 }

upsOutputRatedLNVoltage OBJECT-TYPE
    SYNTAX INTEGER
    UNITS  "Voltage"
    ACCESS read-write
    STATUS mandatory
    DESCRIPTION
        "The rated output line to neutral voltage."
    ::= { upsOutput 23 }

upsOutputRatedFrequency OBJECT-TYPE
    SYNTAX INTEGER
    UNITS  "0.1 Hertz"
    ACCESS read-only
    STATUS mandatory
    DESCRIPTION
        "The Output rated frequency in Hertz."
    ::= { upsOutput 24 }

upsOutputRatedActivePower OBJECT-TYPE
    SYNTAX INTEGER
    UNITS  "watt"
    ACCESS read-only
    STATUS mandatory
    DESCRIPTION
        "The rated output power in watt."
    ::= { upsOutput 25 }

upsOutputRatedApparentPower OBJECT-TYPE
    SYNTAX INTEGER
    UNITS  "Volt-Amp"
    ACCESS read-only
    STATUS mandatory
    DESCRIPTION
        "The rated output power in volt-amp."
    ::= { upsOutput 26 }

upsOutputUnderVoltageDetectLevel OBJECT-TYPE
    SYNTAX INTEGER
    UNITS  "0.1 Percent"
    ACCESS read-only
    STATUS mandatory
    DESCRIPTION
        "The output voltage undervoltage detection level."
    ::= { upsOutput 27 }

upsOutputOverVoltageDetectLevel OBJECT-TYPE
    SYNTAX INTEGER
    UNITS  "0.1 Percent"
    ACCESS read-only
    STATUS mandatory
    DESCRIPTION
        "The outputput voltage overvoltage detection level."
    ::= { upsOutput 28 }

upsOutputVoltageAdjustment OBJECT-TYPE
    SYNTAX DisplayString (SIZE(4))
    ACCESS read-write
    STATUS mandatory
    DESCRIPTION
        "The Output voltage adjustment used to calibrate output voltage. Range: -5.0 to 5.0"
    ::= { upsOutput 29 }

-- ===========================================================================
-- upsBypass - RMTI4 Group 4
-- The UPS Output Data Group
-- ===========================================================================

upsBypassNumOfPhases OBJECT-TYPE
    SYNTAX INTEGER

    ACCESS read-only
    STATUS mandatory
    DESCRIPTION
        "The no of Bypass Lines."
    ::= { upsBypass 1 }

upsBypassLLVoltageAB OBJECT-TYPE
    SYNTAX INTEGER
    UNITS  "0.1 RMS Volts"
    ACCESS read-only
    STATUS mandatory
    DESCRIPTION
        "The Bypass line to line voltage for AB in RMS volts."
    ::= { upsBypass 2 }

upsBypassLLVoltageBC OBJECT-TYPE
    SYNTAX INTEGER
    UNITS  "0.1 RMS Volts"
    ACCESS read-only
    STATUS mandatory
    DESCRIPTION
        "The Bypass line to line voltage for BC in RMS volts."
    ::= { upsBypass 3 }

upsBypassLLVoltageCA OBJECT-TYPE
    SYNTAX INTEGER
    UNITS  "0.1 RMS Volts"
    ACCESS read-only
    STATUS mandatory
    DESCRIPTION
        "The Bypass line to line voltage for CA in RMS volts."
    ::= { upsBypass 4 }

upsBypassLNVoltageAN OBJECT-TYPE
    SYNTAX INTEGER
    UNITS  "0.1 RMS Volts"
    ACCESS read-only
    STATUS mandatory
    DESCRIPTION
        "The Bypass line to neutral voltage for AN in RMS volts."
    ::= { upsBypass 5 }

upsBypassLNVoltageBN OBJECT-TYPE
    SYNTAX INTEGER
    UNITS  "0.1 RMS Volts"
    ACCESS read-only
    STATUS mandatory
    DESCRIPTION
        "The Bypass line to neutral voltage for BN in RMS volts."
    ::= { upsBypass 6 }

upsBypassLNVoltageCN OBJECT-TYPE
    SYNTAX INTEGER
    UNITS  "0.1 RMS Volts"
    ACCESS read-only
    STATUS mandatory
    DESCRIPTION
        "The Bypass line to neutral voltage for CN in RMS volts."
    ::= { upsBypass 7 }

upsBypassCurrentPhaseA OBJECT-TYPE
    SYNTAX INTEGER
    UNITS  "0.1 Amp"
    ACCESS read-only
    STATUS mandatory
    DESCRIPTION
        "The Bypass phase current for phase A in amps."
    ::= { upsBypass 8 }

upsBypassCurrentPhaseB OBJECT-TYPE
    SYNTAX INTEGER
    UNITS  "0.1 Amp"
    ACCESS read-only
    STATUS mandatory
    DESCRIPTION
        "The Bypass phase current for phase B in amps."
    ::= { upsBypass 9 }

upsBypassCurrentPhaseC OBJECT-TYPE
    SYNTAX INTEGER
    UNITS  "0.1 Amp"
    ACCESS read-only
    STATUS mandatory
    DESCRIPTION
        "The Bypass phase current for phase C in amps."
    ::= { upsBypass 10 }

upsBypassFrequency OBJECT-TYPE
    SYNTAX INTEGER
    UNITS  "0.1 Hertz"
    ACCESS read-only
    STATUS mandatory
    DESCRIPTION
        "The Bypass frequency for phase A in Hertz."
    ::= { upsBypass 11 }

upsBypassVoltagePercentA OBJECT-TYPE
    SYNTAX INTEGER
    UNITS  "Percent"
    ACCESS read-only
    STATUS mandatory
    DESCRIPTION
        "The Bypass voltage for Phase A in percent."
    ::= { upsBypass 12 }

upsBypassVoltagePercentB OBJECT-TYPE
    SYNTAX INTEGER
    UNITS  "Percent"
    ACCESS read-only
    STATUS mandatory
    DESCRIPTION
        "The Bypass voltage for Phase B in percent."
    ::= { upsBypass 13 }

upsBypassVoltagePercentC OBJECT-TYPE
    SYNTAX INTEGER
    UNITS  "Percent"
    ACCESS read-only
    STATUS mandatory
    DESCRIPTION
        "The Bypass voltage for Phase C in percent."
    ::= { upsBypass 14 }

upsBypassRatedLLVoltage OBJECT-TYPE
    SYNTAX INTEGER
    UNITS  "Voltage"
    ACCESS read-only
    STATUS mandatory
    DESCRIPTION
        "The rated bypass line to line voltage."
    ::= { upsBypass 15 }

upsBypassRatedLNVoltage OBJECT-TYPE
    SYNTAX INTEGER
    UNITS  "Voltage"
    ACCESS read-only
    STATUS mandatory
    DESCRIPTION
        "The rated bypass line to neutral voltage."
    ::= { upsBypass 16 }

upsBypassUnderVoltageDetectLevel OBJECT-TYPE
    SYNTAX INTEGER
    UNITS  "0.1 Percent"
    ACCESS read-only
    STATUS mandatory
    DESCRIPTION
        "The bypass voltage undervoltage detection level."
    ::= { upsBypass 17 }

upsBypassOverVoltageDetectLevel OBJECT-TYPE
    SYNTAX INTEGER
    UNITS  "0.1 Percent"
    ACCESS read-only
    STATUS mandatory
    DESCRIPTION
        "The bypass voltage overvoltage detection level."
    ::= { upsBypass 18 }

-- ===========================================================================
-- upsDCBus - RMTI4 Group 5
-- The UPS DC Bus Data Group
-- ===========================================================================
upsDCBusTotalVoltage OBJECT-TYPE
    SYNTAX INTEGER
    UNITS  "DC Volts"
    ACCESS read-only
    STATUS mandatory
    DESCRIPTION
        "The Total DC Bus voltage in DC volts."
    ::= { upsDCBus 1 }

upsDCBusPositiveVoltage OBJECT-TYPE
    SYNTAX INTEGER
    UNITS  "DC Volts"
    ACCESS read-only
    STATUS mandatory
    DESCRIPTION
        "The DC Bus positive voltage in DC volts."
    ::= { upsDCBus 2 }

upsDCBusNegativeVoltage OBJECT-TYPE
    SYNTAX INTEGER
    UNITS  "DC Volts"
    ACCESS read-only
    STATUS mandatory
    DESCRIPTION
        "The DC Bus negative voltage in DC volts."
    ::= { upsDCBus 3 }

-- ===========================================================================
-- upsBattery RMTI4 Group 6
-- The UPS Battery Data Group
-- ===========================================================================

upsBatteryStatus OBJECT-TYPE
    SYNTAX INTEGER {
         unknown(1),
         batteryNormal(2),
         batteryLow(3),
         batteryDepleted(4),
         batteryDischarging(5),
         batteryFailure(6)
    }
    ACCESS read-only
    STATUS mandatory
    DESCRIPTION
        "The indication of the capacity remaining in the UPS system's batteries. 
         A value of batteryNormal indicates that the remaining run-time sufficient 
         to handle the load. A value of batteryLow indicates the battery level is 
         low. Continued operation in battery mode will deplate batteries. A value 
         of batteryDepleted indicates that the UPS will be unable to sustain the 
         present load when and if the utility power is lost (including the 
         possibility that the utility power is currently absent and the UPS is 
         unable to sustain the output). A value of batteryDischarging indicates UPS 
         system is in Battery power."
    ::= { upsBattery 1 }

upsElapsedTimeOnBatteryPower OBJECT-TYPE
    SYNTAX NonNegativeInteger
    UNITS   "Second"
    ACCESS read-only
    STATUS mandatory
    DESCRIPTION
        "If the unit is on battery power, the elapsed time
         since the UPS on battery power, or the
         time since the network management subsystem was last
         restarted, whichever is less. Zero shall be returned
         if the unit is not on battery power."
    ::= { upsBattery 2 }
	
upsEstimatedBatteryRuntime OBJECT-TYPE
     SYNTAX PositiveInteger
     UNITS "minutes"
     ACCESS read-only
     STATUS mandatory
     DESCRIPTION
         "An estimate of the time to battery charge depletion 
		 under the present load conditions if the utility power 
		 is off and remains off, or if it were to be lost and 
		 remain off."
     ::= { upsBattery 3 }

upsBatteryVoltage OBJECT-TYPE
    SYNTAX INTEGER
    UNITS  "DC Volt"
    ACCESS read-only
    STATUS mandatory
    DESCRIPTION
        "The magnitude of the present battery voltage in DC Volt."
    ::= { upsBattery 4 }

upsBatteryCurrent OBJECT-TYPE
    SYNTAX INTEGER
    UNITS  "DC Amp"
    ACCESS read-only
    STATUS mandatory
    DESCRIPTION
        "The present battery current in DC Amp."
    ::= { upsBattery 5 }

upsBatteryCapacity OBJECT-TYPE
    SYNTAX INTEGER
    UNITS  "Percent"
    ACCESS read-only
    STATUS mandatory
    DESCRIPTION
        "The present battery capacity Percent."
    ::= { upsBattery 6 }

upsBatteryChargeStatus OBJECT-TYPE
    SYNTAX INTEGER {
         charging(1),
         equalize(2),
         protective(3),
         discharging(4),
         stopped(5),
         off(6)
    }
    ACCESS read-only
    STATUS mandatory
    DESCRIPTION
        "The state of the battery charger."
    ::= { upsBattery 7 }

upsBatteryRatedVoltage OBJECT-TYPE
    SYNTAX INTEGER
    UNITS  "0.1 DC Volt"
    ACCESS read-only
    STATUS mandatory
    DESCRIPTION
        "The rated battery voltage in DC Volt."
    ::= { upsBattery 8 }

upsBatteryRatedDischargeCurrent OBJECT-TYPE
    SYNTAX INTEGER
    UNITS  "0.1 DC Amp"
    ACCESS read-only
    STATUS mandatory
    DESCRIPTION
        "The rated battery discharge current in 1/10 DC Amp."
    ::= { upsBattery 9 }

upsBatteryEnableEqualizeCharge OBJECT-TYPE
    SYNTAX INTEGER {
        disable(1),
        enable(2)
    }
    ACCESS read-only
    STATUS mandatory
    DESCRIPTION
        "Equalize Charge Mode."
    ::= { upsBattery 10 }

upsBatteryManualEqualizeCharge OBJECT-TYPE
    SYNTAX INTEGER {
        start(1),
        stop(2)
    }
    ACCESS read-only
    STATUS mandatory
    DESCRIPTION
        "Manually initiate Equalize Charge Mode."
    ::= { upsBattery 11 }

upsBatteryEqualizeChargeTime OBJECT-TYPE
    SYNTAX INTEGER
    UNITS  "Hours"
    ACCESS read-only
    STATUS mandatory
    DESCRIPTION
        "The amount of charging time to equalize the batteries."
    ::= { upsBattery 12 }

upsBatteryPreventativeChargeVoltage OBJECT-TYPE
    SYNTAX INTEGER
    UNITS  "0.1 DC Volt"
    ACCESS read-only
    STATUS mandatory
    DESCRIPTION
        "Preventative charge voltage."
    ::= { upsBattery 13 }

upsBatteryEqualizeChargeVoltage OBJECT-TYPE
    SYNTAX INTEGER
    UNITS  "0.1 DC Volt"
    ACCESS read-only
    STATUS mandatory
    DESCRIPTION
        "Equalize charge voltage."
    ::= { upsBattery 14 }

upsBatteryRatedAmpereHour OBJECT-TYPE
    SYNTAX INTEGER
    UNITS  "Ampere-Hour"
    ACCESS read-only
    STATUS mandatory
    DESCRIPTION
        "The rated battery in ampere hour."
    ::= { upsBattery 15 }

upsBatteryRatedLowBattLevel OBJECT-TYPE
    SYNTAX INTEGER
    UNITS  "0.1 DC Volt"
    ACCESS read-only
    STATUS mandatory
    DESCRIPTION
        "The low battery detection level."
    ::= { upsBattery 16 }

upsBatteryShutdownLvl OBJECT-TYPE
    SYNTAX INTEGER
    UNITS  "0.1 DC Volt"
    ACCESS read-only
    STATUS mandatory
    DESCRIPTION
        "Battery shutdown level."
    ::= { upsBattery 17 }

upsBatteryAutoTest OBJECT-TYPE
    SYNTAX INTEGER {
        disable(1),
        enable(2)
    }
    ACCESS read-write
    STATUS mandatory
    DESCRIPTION
        "Enable auto battery test."
    ::= { upsBattery 18 }

upsBatteryAutoTestInterval OBJECT-TYPE
    SYNTAX INTEGER
    UNITS  "Hour" 
    ACCESS read-write
    STATUS mandatory
    DESCRIPTION
        "The frequency, in hours, in which the battery will begin test automatically."
    ::= { upsBattery 19 }

upsBatteryPwrFailEqualizeDuration OBJECT-TYPE
    SYNTAX INTEGER
    UNITS  "Minute"
    ACCESS read-only
    STATUS mandatory
    DESCRIPTION
        "The time the batteries take to equalize charge after failure."
    ::= { upsBattery 20 }

upsBatteryinSeries OBJECT-TYPE
    SYNTAX INTEGER
    ACCESS read-only
    STATUS mandatory
    DESCRIPTION
        "The number of battery in series."
    ::= { upsBattery 21 }

upsBatteryinParallel OBJECT-TYPE
    SYNTAX INTEGER
    ACCESS read-only
    STATUS mandatory
    DESCRIPTION
        "The number of battery in Parallel."
    ::= { upsBattery 22 }

upsBatteryInstallationDate OBJECT-TYPE
    SYNTAX DisplayString (SIZE(8))
    ACCESS read-write
    STATUS mandatory
    DESCRIPTION
        "The battery install date."
    ::= { upsBattery 23 }

-- ===========================================================================
-- upsStsCtlCfg RMTI4 Group 7
-- The UPS status, control and configuration
-- ===========================================================================

upsStsCtlCfgPresentDate OBJECT-TYPE
    SYNTAX INTEGER
    ACCESS read-write
    STATUS mandatory
    DESCRIPTION 
        "The present date of the UPS. This is configurable by Administrator. DDmmddyy, for example set 04071615 is Thursday July 16, 2015 (Note: DD 00 - Sunday)."
    ::= { upsStsCtlCfg 1 }

upsStsCtlCfgPresentTime OBJECT-TYPE
    SYNTAX NonNegativeInteger
    ACCESS read-write
    STATUS mandatory
    DESCRIPTION 
        "The present time of the UPS. This is configurable by Administrator. 24 Hour Format: HHMMSS. For example, 140600 is 02:06PM "
    ::= { upsStsCtlCfg 2 }

upsStsCtlCfgPresentMode OBJECT-TYPE
    SYNTAX INTEGER {
        online(1),
        bypass(2),
        backup(3),
        batttest(4),
        shutdown(5),
        precharge(6),
        gatecheck(7),
        unknown(8)
    }
    ACCESS read-only
    STATUS mandatory
    DESCRIPTION
        "The present mode of the UPS system."
    ::= { upsStsCtlCfg 3 }

upsStsCtlCfgFaults OBJECT-TYPE
    SYNTAX NonNegativeInteger
    ACCESS read-only
    STATUS mandatory
    DESCRIPTION
        "The faults currently detected by the UPS."
    ::= { upsStsCtlCfg 4 }

upsStsCtlCfgWarnings OBJECT-TYPE
    SYNTAX NonNegativeInteger
    ACCESS read-only
    STATUS mandatory
    DESCRIPTION
        "The warnings currently detected by the UPS."
    ::= { upsStsCtlCfg 5 }

upsStsCtlCfgStatus OBJECT-TYPE
    SYNTAX NonNegativeInteger
    ACCESS read-only
    STATUS mandatory
    DESCRIPTION
        "The current status of the UPS."
    ::= { upsStsCtlCfg 6 }

upsStsCtlCfgChangeSecurityLevel OBJECT-TYPE
    SYNTAX DisplayString (SIZE(0..16))
    ACCESS read-write
    STATUS mandatory
    DESCRIPTION
        "The current security level of the UPS system"
    ::= { upsStsCtlCfg 7 }

upsStsCtlCfgManageADMINPWD OBJECT-TYPE
    SYNTAX DisplayString (SIZE(0..8))
    ACCESS read-write
    STATUS mandatory
    DESCRIPTION
        "The Administration password"
    ::= { upsStsCtlCfg 8 }
	
upsStsCtlCfgUserDefinedOverloadSetPoint OBJECT-TYPE
    SYNTAX INTEGER
	UNITS "%"
    ACCESS read-write
    STATUS mandatory
    DESCRIPTION 
        "The maximum output load % defined by the user."
    ::= { upsStsCtlCfg 9 }
	
upsStsCtlCfgRemoteStatus OBJECT-TYPE
    SYNTAX INTEGER {
        remoterun(1),
        remotestop(2)
    }
    ACCESS read-only
    STATUS mandatory
    DESCRIPTION 
        "Remote Status"
    ::= { upsStsCtlCfg 10 }
	
upsStsCtlCfgFan1Speed OBJECT-TYPE
    SYNTAX INTEGER
	UNITS "RPM"
    ACCESS read-only
    STATUS mandatory
    DESCRIPTION 
        "Fan 1 speed in RPM."
    ::= { upsStsCtlCfg 11 }
	
upsStsCtlCfgFan2Speed OBJECT-TYPE
    SYNTAX INTEGER
	UNITS "RPM"
    ACCESS read-only
    STATUS mandatory
    DESCRIPTION 
        "Fan 2 speed in RPM."
    ::= { upsStsCtlCfg 12 }

-- ===========================================================================
-- upsHistory RMTI4 Group 8
-- The UPS History Data Group
-- ===========================================================================
upsHistorySysOperationTime OBJECT-TYPE
    SYNTAX NonNegativeInteger
    UNITS  "Minute"
    ACCESS read-only
    STATUS mandatory
    DESCRIPTION 
        "The amount of time the UPS has been on."
    ::= { upsHistory 1 }

upsHistoryInverterOperationTime OBJECT-TYPE
    SYNTAX NonNegativeInteger
    UNITS  "Minute"
    ACCESS read-only
    STATUS mandatory
    DESCRIPTION 
        "The amount of time the UPS has been in On-Line Mode."
    ::= { upsHistory 2 }

upsHistoryBackupOperationTime OBJECT-TYPE
    SYNTAX NonNegativeInteger
    UNITS  "Minute"
    ACCESS read-only
    STATUS mandatory
    DESCRIPTION 
        "The amount of time the UPS has been in BackUp Mode."
    ::= { upsHistory 3 }

upsHistoryTotalNumBackup OBJECT-TYPE
    SYNTAX NonNegativeInteger
    ACCESS read-only
    STATUS mandatory
    DESCRIPTION 
        "Total number of times the UPS has been in Back-Up mode."
    ::= { upsHistory 4 }

upsHistoryTotalNumFaults OBJECT-TYPE
    SYNTAX NonNegativeInteger
    ACCESS read-only
    STATUS mandatory
    DESCRIPTION 
        "Total number of faults that has occurred on the UPS."
    ::= { upsHistory 5 }

upsHistoryTotalNumOperationModeChange OBJECT-TYPE
    SYNTAX NonNegativeInteger
    ACCESS read-only
    STATUS mandatory
    DESCRIPTION 
        "The number of mode changes that has occurred."
    ::= { upsHistory 6 }

-- ===========================================================================
-- upsDisplay RMTI4 Group 9
-- The UPS Display Data Group
-- ===========================================================================
upsDisplayFirmwareVersion OBJECT-TYPE
    SYNTAX DisplayString (SIZE(0..15))
    ACCESS read-only
    STATUS mandatory
    DESCRIPTION
        "The firmware version of the display."
    ::= { upsDisplay 1 }

upsDisplayFirmwareBuildDate OBJECT-TYPE
    SYNTAX DisplayString (SIZE(0..15))
    ACCESS read-only
    STATUS mandatory
    DESCRIPTION
        "The firmware build date of the display."
    ::= { upsDisplay 2 }

upsDisplayFirmwareBuiltTime OBJECT-TYPE
    SYNTAX DisplayString (SIZE(0..15))
    ACCESS read-only
    STATUS mandatory
    DESCRIPTION
        "The firmware build time of the display."
    ::= { upsDisplay 3 }

upsDisplayRMTIInstallDate OBJECT-TYPE
    SYNTAX DisplayString(SIZE(8))
    ACCESS read-only
    STATUS mandatory
    DESCRIPTION
        "The RMTI installation date."
    ::= { upsDisplay 4 }

upsDisplayRMTIVersion OBJECT-TYPE
    SYNTAX DisplayString(SIZE(0..15))
    ACCESS read-only
    STATUS mandatory
    DESCRIPTION
        "The RMTI installation date."
    ::= { upsDisplay 5 }

upsDisplayRMTIInstallationDate OBJECT-TYPE
    SYNTAX INTEGER {
        uninstalled(1),
        installed(2)
    }          
    ACCESS read-only
    STATUS mandatory
    DESCRIPTION
        "Shows the installation status of the RMTI."
    ::= { upsDisplay 6 }

upsDisplayRMTIDataLink OBJECT-TYPE
    SYNTAX INTEGER {
        unknown(1),
        link-down(2),
        link-up(3)
    }          
    ACCESS read-only
    STATUS mandatory
    DESCRIPTION
        "Shows the data status of the RMTI."
    ::= { upsDisplay 7 }

upsDisplayRMTINetworkLink OBJECT-TYPE
    SYNTAX INTEGER {
        unknown(1),
        link-down(2),
        link-up(3)
    }          
    ACCESS read-only
    STATUS mandatory
    DESCRIPTION
        "Shows the network status of the RMTI."
    ::= { upsDisplay 8 }

-- ===========================================================================
-- upsAlarm RMTI4 Group 10
-- The UPS Alarm List
-- ===========================================================================
upsAlarmsPresent OBJECT-TYPE
    SYNTAX Gauge32
    ACCESS read-only
    STATUS mandatory
    DESCRIPTION
        "The present number of active alarm conditions."
    ::= { upsAlarm 1 }

upsAlarmTable OBJECT-TYPE
    SYNTAX SEQUENCE OF UpsAlarmEntry
    ACCESS not-accessible
    STATUS mandatory
    DESCRIPTION
        "A list of alarm table entries. The table contains
         zero, one, or many rows at any moment, depending upon
         the number of alarm conditions in effect. The table
         is initially empty at agent startup. The agent
         creates a row in the table each time a condition is
         detected and deletes that row when that condition no
         longer pertains. The agent creates the first row with
         upsAlarmId equal to 1, and increments the value of
         upsAlarmId each time a new row is created, wrapping to
         the first free value greater than or equal to 1 when
         the maximum value of upsAlarmId would otherwise be
         exceeded. Consequently, after multiple operations,
         the table may become sparse, e.g., containing entries
         for rows 95, 100, 101, and 203 and the entries should
         not be assumed to be in chronological order because
         upsAlarmId might have wrapped.

         Alarms are named by an OBJECT IDENTIFIER,
         upsAlarmDescr, to allow a single table to
         reflect well known alarms plus alarms defined by a
         particular implementation, i.e., as documented in the
         private enterprise MIB definition for the device. No
         two rows will have the same value of upsAlarmDescr,
         since alarms define conditions. In order to meet this
         requirement, care should be taken in the definition of
         alarm conditions to insure that a system cannot enter
         the same condition multiple times simultaneously.

         The number of rows in the table at any given time is
         reflected by the value of upsAlarmsPresent."
    ::= { upsAlarm  2 }

upsAlarmEntry OBJECT-TYPE
    SYNTAX UpsAlarmEntry
    ACCESS not-accessible
    STATUS mandatory
    DESCRIPTION
        "An entry containing information applicable to a
         particular alarm."
    INDEX { upsAlarmId }
    ::= { upsAlarmTable  1 }

UpsAlarmEntry ::=
    SEQUENCE {
        upsAlarmId              PositiveInteger,
        upsAlarmDescr           AutonomousType,
        upsAlarmTime            TimeStamp
    }

-- ===========================================================================
-- upsAlarmTable/upsAlarmEntry/upsAlarmId
-- ===========================================================================
upsAlarmId OBJECT-TYPE
    SYNTAX PositiveInteger
    ACCESS not-accessible
    STATUS mandatory
    DESCRIPTION
        "An unique identifier for an alarm condition. This
         value must remain constant."
    ::= { upsAlarmEntry 1 }

upsAlarmDescr OBJECT-TYPE
    SYNTAX AutonomousType
    ACCESS read-only
    STATUS mandatory
    DESCRIPTION
        "A reference to an alarm description object. The
         object referenced should not be accessible, but rather
         be used to provide a unique description of the alarm
         condition."
    ::= { upsAlarmEntry 2 }

-- ===========================================================================
-- .../upsAlarmTime
-- ===========================================================================
upsAlarmTime OBJECT-TYPE
    SYNTAX TimeStamp
    ACCESS read-only
    STATUS mandatory
    DESCRIPTION
        "The value of upsConfigSystemTime when the alarm condition was
          detected. If the alarm condition was detected at the
          time of agent startup and presumably existed before
          agent startup, the value of upsAlarmTime shall equal 0."
    ::= { upsAlarmEntry 3 }

upsWellKnownAlarms OBJECT IDENTIFIER ::= { upsAlarm  3 }

upsAlarmFault OBJECT-TYPE 
    SYNTAX INTEGER
    ACCESS read-only
    STATUS mandatory
    DESCRIPTION
        "Fault: One or more fault reported."
    ::= { upsWellKnownAlarms 1 }

upsAlarmEPOTrippedFault OBJECT-TYPE 
    SYNTAX INTEGER
    ACCESS read-only
    STATUS mandatory
    DESCRIPTION
        "Fault: EPO has tripped."
    ::= { upsWellKnownAlarms 2 }

upsAlarmCurrentLimitFault OBJECT-TYPE 
    SYNTAX INTEGER
    ACCESS read-only
    STATUS mandatory
    DESCRIPTION
        "Fault: Input Over Current reported."
    ::= { upsWellKnownAlarms 3 }

upsAlarmDCBusAbnormal OBJECT-TYPE 
    SYNTAX INTEGER
    ACCESS read-only
    STATUS mandatory
    DESCRIPTION
        "Fault: DC bus abnormality occurred."
    ::= { upsWellKnownAlarms 4 }

upsAlarmDCBusOverVoltage OBJECT-TYPE 
    SYNTAX INTEGER
    ACCESS read-only
    STATUS mandatory
    DESCRIPTION
        "Fault: A DC bus overvoltage repoprted."
    ::= { upsWellKnownAlarms 5 }

upsAlarmDCBusImbalance OBJECT-TYPE 
    SYNTAX INTEGER
    ACCESS read-only
    STATUS mandatory
    DESCRIPTION
        "Fault: A DC bus imbalance reported."
    ::= { upsWellKnownAlarms 6 }

upsAlarmInverterOverVoltage OBJECT-TYPE 
    SYNTAX INTEGER
    ACCESS read-only
    STATUS mandatory
    DESCRIPTION
        "Fault: An inverter overvoltage reported."
    ::= { upsWellKnownAlarms 7 }

upsAlarmInverterUnderVoltage OBJECT-TYPE 
    SYNTAX INTEGER
    ACCESS read-only
    STATUS mandatory
    DESCRIPTION
        "Fault: An inverter undervoltage reported."
    ::= { upsWellKnownAlarms 8 }

upsAlarmUPSOverheat OBJECT-TYPE 
    SYNTAX INTEGER
    ACCESS read-only
    STATUS mandatory
    DESCRIPTION
        "Fault: Device overheat reported."
    ::= { upsWellKnownAlarms 9 }

upsAlarmLoadAbnormal OBJECT-TYPE 
    SYNTAX INTEGER
    ACCESS read-only
    STATUS mandatory
    DESCRIPTION
        "Fault: A output overload has occurred frequently."
    ::= { upsWellKnownAlarms 10 }

upsAlarmChopperOverCurrent OBJECT-TYPE 
    SYNTAX INTEGER
    ACCESS read-only
    STATUS mandatory
    DESCRIPTION
        "Fault: Chopper overcurrent reported."
    ::= { upsWellKnownAlarms 11 }

upsAlarmInverterOverCurrent OBJECT-TYPE 
    SYNTAX INTEGER
    ACCESS read-only
    STATUS mandatory
    DESCRIPTION
        "Fault: Inverter overcurrent reported."
    ::= { upsWellKnownAlarms 12 }

upsAlarmPreChargeError OBJECT-TYPE 
    SYNTAX INTEGER
    ACCESS read-only
    STATUS mandatory
    DESCRIPTION
        "Fault: Precharge Error reported."
    ::= { upsWellKnownAlarms 13 }

upsAlarmDCBusUnderVoltage OBJECT-TYPE 
    SYNTAX INTEGER
    ACCESS read-only
    STATUS mandatory
    DESCRIPTION
        "Fault: A DC bus undervoltage reported."
    ::= { upsWellKnownAlarms 14 }

upsAlarmBypassOverheat OBJECT-TYPE 
    SYNTAX INTEGER
    ACCESS read-only
    STATUS mandatory
    DESCRIPTION
        "Fault: A bypass Overheat reported."
    ::= { upsWellKnownAlarms 15 }

upsAlarmPCBAbnormal OBJECT-TYPE 
    SYNTAX INTEGER
    ACCESS read-only
    STATUS mandatory
    DESCRIPTION
        "Fault: An abnormality has occurred with the PCB."
    ::= { upsWellKnownAlarms 16 }

--upsAlarmDummyFault OBJECT-TYPE 
--    SYNTAX INTEGER
--    ACCESS read-only
--    STATUS mandatory
--    DESCRIPTION
--        "Fault: Test fault has been set."
--    ::= { upsWellKnownAlarms 17 }

upsAlarmInputPhaseRotationError OBJECT-TYPE
    SYNTAX INTEGER
    ACCESS read-only
    STATUS mandatory
    DESCRIPTION
        "Fault: Input Phase Rotation Error."
    ::= { upsWellKnownAlarms 18 }

upsAlarmBypassPhaseRotationError OBJECT-TYPE
    SYNTAX INTEGER
    ACCESS read-only
    STATUS mandatory
    DESCRIPTION
        "Fault: Bypass Phase Rotation Error."
    ::= { upsWellKnownAlarms 19 }

upsAlarmInputAbnormal OBJECT-TYPE 
    SYNTAX INTEGER
    ACCESS read-only
    STATUS mandatory
    DESCRIPTION
        "Fault: An abnormality with input circuit occurred with the PCB."
    ::= { upsWellKnownAlarms 20 }

upsAlarmPowerSupplyOutofRange OBJECT-TYPE 
    SYNTAX INTEGER
    ACCESS read-only
    STATUS mandatory
    DESCRIPTION
        "Fault: An abnormality with power supply for control PCB detected."
    ::= { upsWellKnownAlarms 21 }

upsAlarmInverterVoltageAbnormal OBJECT-TYPE 
    SYNTAX INTEGER
    ACCESS read-only
    STATUS mandatory
    DESCRIPTION
        "Fault: An inverter voltage out of spec reported."
    ::= { upsWellKnownAlarms 22 }

upsAlarmOutputVoltageAbnormal OBJECT-TYPE 
    SYNTAX INTEGER
    ACCESS read-only
    STATUS mandatory
    DESCRIPTION
        "Fault: An output voltage out of spec reported."
    ::= { upsWellKnownAlarms 23 }

upsAlarmOutputUnderVoltage OBJECT-TYPE 
    SYNTAX INTEGER
    ACCESS read-only
    STATUS mandatory
    DESCRIPTION
        "Fault: An output under voltage reported."
    ::= { upsWellKnownAlarms 24 }

upsAlarmCurrentAbnormal OBJECT-TYPE 
    SYNTAX INTEGER
    ACCESS read-only
    STATUS mandatory
    DESCRIPTION
        "Fault: Current Abnormality reported."
    ::= { upsWellKnownAlarms 25 }

upsAlarmInverterOutputVoltageAbnormal OBJECT-TYPE 
    SYNTAX INTEGER
    ACCESS read-only
    STATUS mandatory
    DESCRIPTION
        "Fault: An inverter output voltage out of spec reported."
    ::= { upsWellKnownAlarms 26 }

upsAlarmGateVoltageLost OBJECT-TYPE 
    SYNTAX INTEGER
    ACCESS read-only
    STATUS mandatory
    DESCRIPTION
        "Fault: Gate Voltage lost reported."
    ::= { upsWellKnownAlarms 27 }

upsAlarmInverterCurrentError OBJECT-TYPE 
    SYNTAX INTEGER
    ACCESS read-only
    STATUS mandatory
    DESCRIPTION
        "Fault: Inverter current error reported."
    ::= { upsWellKnownAlarms 28 }

upsAlarmInverterBypassVoltageMismatch OBJECT-TYPE 
    SYNTAX INTEGER
    ACCESS read-only
    STATUS mandatory
    DESCRIPTION
        "Fault: An inverter and bypass voltage out of spec reported."
    ::= { upsWellKnownAlarms 29 }

upsAlarmNoControlConnection OBJECT-TYPE 
    SYNTAX INTEGER
    ACCESS read-only
    STATUS mandatory
    DESCRIPTION
        "Fault: Control PCB is disconnected."
    ::= { upsWellKnownAlarms 30 }

upsAlarmInputVoltageError OBJECT-TYPE 
    SYNTAX INTEGER
    ACCESS read-only
    STATUS mandatory
    DESCRIPTION
        "Warning: An input voltage error reported."
    ::= { upsWellKnownAlarms 31 }

upsAlarmBattVoltExceed OBJECT-TYPE 
    SYNTAX INTEGER
    ACCESS read-only
    STATUS mandatory
    DESCRIPTION
        "Warning: Battery voltage exceeded."
    ::= { upsWellKnownAlarms 32 }

upsAlarmBypassFrequencyError OBJECT-TYPE 
    SYNTAX INTEGER
    ACCESS read-only
    STATUS mandatory
    DESCRIPTION
        "Warning: Bypass frequency error reported."
    ::= { upsWellKnownAlarms 33 }

upsAlarmInputFrequencyError OBJECT-TYPE 
    SYNTAX INTEGER
    ACCESS read-only
    STATUS mandatory
    DESCRIPTION
        "Warning: An input frequency error reported."
    ::= { upsWellKnownAlarms 34 }

upsAlarmBypassError OBJECT-TYPE 
    SYNTAX INTEGER
    ACCESS read-only
    STATUS mandatory
    DESCRIPTION
        "Warning: Bypass voltage out of spec reported."
    ::= { upsWellKnownAlarms 35 }

upsAlarmEEtoRAMError OBJECT-TYPE 
    SYNTAX INTEGER
    ACCESS read-only
    STATUS mandatory
    DESCRIPTION
        "Warning: An error occurred when writing from EEPROM to SRAM."
    ::= { upsWellKnownAlarms 36 }

upsAlarmBatteryTestFailed OBJECT-TYPE 
    SYNTAX INTEGER
    ACCESS read-only
    STATUS mandatory
    DESCRIPTION
        "Warning: A battery test failed event reported."
    ::= { upsWellKnownAlarms 37 }

upsAlarmBatteryAbnormal OBJECT-TYPE 
    SYNTAX INTEGER
    ACCESS read-only
    STATUS mandatory
    DESCRIPTION
        "Warning: A battery abnormality reported."
    ::= { upsWellKnownAlarms 38 }

upsAlarmBatteryLow OBJECT-TYPE
    SYNTAX INTEGER
    ACCESS read-only
    STATUS mandatory
    DESCRIPTION
        "Warning: Battery voltage reached low battery level."
    ::= { upsWellKnownAlarms 39 }

upsAlarmBatteryDepleted OBJECT-TYPE
    SYNTAX INTEGER
    ACCESS read-only
    STATUS mandatory
    DESCRIPTION
        "Warning: A Battery shutdown voltage level reached."
    ::= { upsWellKnownAlarms 40 }

upsAlarmBatteryVoltageBelowShutdown OBJECT-TYPE
    SYNTAX INTEGER
    ACCESS read-only
    STATUS mandatory
    DESCRIPTION
        "Warning: Battery shutdown voltage lower than shutdown level."
    ::= { upsWellKnownAlarms 41 }

upsAlarmBatteryContactOpen OBJECT-TYPE
    SYNTAX INTEGER
    ACCESS read-only
    STATUS mandatory
    DESCRIPTION
        "Warning: Battery contact open."
    ::= { upsWellKnownAlarms 42 }

upsAlarmOutputCurrentExceeded OBJECT-TYPE 
    SYNTAX INTEGER
    ACCESS read-only
    STATUS mandatory
    DESCRIPTION
        "Warning: Output current exceeded."
    ::= { upsWellKnownAlarms 43 }

upsAlarmChargerVoltageAbnormal OBJECT-TYPE 
    SYNTAX INTEGER
    ACCESS read-only
    STATUS mandatory
    DESCRIPTION
        "Warning: Charger voltage abnormal reported."
    ::= { upsWellKnownAlarms 45 }

upsAlarmBattOverheatBattBreakerOpen OBJECT-TYPE 
    SYNTAX INTEGER
    ACCESS read-only
    STATUS mandatory
    DESCRIPTION
        "Warning: Battery overheat/battery breaker open."
    ::= { upsWellKnownAlarms 46 }

upsAlarmOutputOverloadWarning OBJECT-TYPE 
    SYNTAX INTEGER
    ACCESS read-only
    STATUS mandatory
    DESCRIPTION
        "Warning: Output load exceed 110%."
    ::= { upsWellKnownAlarms 47 }

upsAlarmInverterOverLoadWarning OBJECT-TYPE 
    SYNTAX INTEGER
    ACCESS read-only
    STATUS mandatory
    DESCRIPTION
        "Warning: Inverter Overload reported."
    ::= { upsWellKnownAlarms 48 }

upsAlarmOutputLoadExceeded OBJECT-TYPE 
    SYNTAX INTEGER
    ACCESS read-only
    STATUS mandatory
    DESCRIPTION
        "Warning: Output load exceed detection threshold."
    ::= { upsWellKnownAlarms 49 }

upsAlarmCurrentLimitWarning OBJECT-TYPE 
    SYNTAX INTEGER
    ACCESS read-only
    STATUS mandatory
    DESCRIPTION
        "Warning: A current limit reported."
    ::= { upsWellKnownAlarms 50 }

upsAlarmAsyncOperation OBJECT-TYPE 
    SYNTAX INTEGER
    ACCESS read-only
    STATUS mandatory
    DESCRIPTION
        "Warning: Inverter and bypass are Asynchronous."
    ::= { upsWellKnownAlarms 51 }

upsAlarmOutputOverload OBJECT-TYPE 
    SYNTAX INTEGER
    ACCESS read-only
    STATUS mandatory
    DESCRIPTION
        "Warning: Output overload within specified time."
    ::= { upsWellKnownAlarms 52 }
	
upsAlarmUserDefinedOverloadWarning OBJECT-TYPE 
    SYNTAX INTEGER
    ACCESS read-only
    STATUS mandatory
    DESCRIPTION
        "Warning: The inverter output load % is greater than the user defined overload set point (default: 110%)."
    ::= { upsWellKnownAlarms 53 }

upsAlarmCoolingFanAbnormal OBJECT-TYPE 
    SYNTAX INTEGER
    ACCESS read-only
    STATUS mandatory
    DESCRIPTION
        "Warning: Cooling Fan Abnormal reported."
    ::= { upsWellKnownAlarms 54 }

upsAlarmVoltDeviationExceedBattVolt OBJECT-TYPE 
    SYNTAX INTEGER
    ACCESS read-only
    STATUS mandatory
    DESCRIPTION
        "Warning: Voltage Deviation across battery breaker exceeded."
    ::= { upsWellKnownAlarms 55 }

upsAlarmInverterOutputVoltOutofSpec OBJECT-TYPE 
    SYNTAX INTEGER
    ACCESS read-only
    STATUS mandatory
    DESCRIPTION
        "Warning: Input Voltage and Output voltage out of spec."
    ::= { upsWellKnownAlarms 56 }

upsAlarmLocalButtonAbnormal OBJECT-TYPE 
    SYNTAX INTEGER
    ACCESS read-only
    STATUS mandatory
    DESCRIPTION
        "Warning: Local button abnormal reported."
    ::= { upsWellKnownAlarms 57 }

upsAlarmBatteryOverTemperature OBJECT-TYPE 
    SYNTAX INTEGER
    ACCESS read-only
    STATUS mandatory
    DESCRIPTION
        "Warning: Battery OverTemperature occurs for more than 2 hrs."
    ::= { upsWellKnownAlarms 58 }

upsAlarmDischargeWarning OBJECT-TYPE 
    SYNTAX INTEGER
    ACCESS read-only
    STATUS mandatory
    DESCRIPTION
        "Warning: Discharge warning reported."
    ::= { upsWellKnownAlarms 59 }

upsAlarmBypPCBNoComm OBJECT-TYPE 
    SYNTAX INTEGER
    ACCESS read-only
    STATUS mandatory
    DESCRIPTION
        "Warning: Communication lost with Bypass PCB."
    ::= { upsWellKnownAlarms 60 }

upsAlarmAutoTransferDisabled OBJECT-TYPE 
    SYNTAX INTEGER
    ACCESS read-only
    STATUS mandatory
    DESCRIPTION
        "Warning: Auto Transfer Disabled."
    ::= { upsWellKnownAlarms 61 }

upsAlarmControlPCBSupplyError OBJECT-TYPE 
    SYNTAX INTEGER
    ACCESS read-only
    STATUS mandatory
    DESCRIPTION
        "Warning: Control PCB power supply error reported."
    ::= { upsWellKnownAlarms 62 }

upsAlarmROMtoEEError OBJECT-TYPE 
    SYNTAX INTEGER
    ACCESS read-only
    STATUS mandatory
    DESCRIPTION
        "Warning: An error occurred when writing from ROM to EEPROM."
    ::= { upsWellKnownAlarms 63 }

upsAlarmOnBypass OBJECT-TYPE 
    SYNTAX INTEGER
    ACCESS read-only
    STATUS mandatory
    DESCRIPTION
        "Warning: The UPS is in Stop (Bypass) mode"
    ::= { upsWellKnownAlarms 64 }

upsAlarmPowerFailure OBJECT-TYPE 
    SYNTAX INTEGER
    ACCESS read-only
    STATUS mandatory
    DESCRIPTION
        "Info: A power failure reported."
    ::= { upsWellKnownAlarms 65 }

upsAlarmEPOTripped OBJECT-TYPE 
    SYNTAX INTEGER
    ACCESS read-only
    STATUS mandatory
    DESCRIPTION
        "Info: EPO has tripped."
    ::= { upsWellKnownAlarms 66 }

upsAlarmRemoteSwitchEnable OBJECT-TYPE 
    SYNTAX INTEGER
    ACCESS read-only
    STATUS mandatory
    DESCRIPTION
        "Info: Remote switch control enabled."
    ::= { upsWellKnownAlarms 67 }

upsAlarmAutoTransferEnable OBJECT-TYPE 
    SYNTAX INTEGER
    ACCESS read-only
    STATUS mandatory
    DESCRIPTION
        "Info: Auto re-transfer enabled."
    ::= { upsWellKnownAlarms 68 }

upsAlarmProtectiveCharging OBJECT-TYPE 
    SYNTAX INTEGER
    ACCESS read-only
    STATUS mandatory
    DESCRIPTION
        "Info: Protective Charging is set."
    ::= { upsWellKnownAlarms 69 }

upsAlarmEqualizedCharging OBJECT-TYPE 
    SYNTAX INTEGER
    ACCESS read-only
    STATUS mandatory
    DESCRIPTION
        "Info: Equalized Charging enabled."
    ::= { upsWellKnownAlarms 70 }

upsAlarmManualMode OBJECT-TYPE 
    SYNTAX INTEGER
    ACCESS read-only
    STATUS mandatory
    DESCRIPTION
        "Info: Manual mode is selected."
    ::= { upsWellKnownAlarms 71 }

upsAlarmOutputFrequency50Hz OBJECT-TYPE 
    SYNTAX INTEGER
    ACCESS read-only
    STATUS mandatory
    DESCRIPTION
        "Info: Output Frequency is selected to 50Hz."
    ::= { upsWellKnownAlarms 72 }

upsAlarmBatteryTestInProgress OBJECT-TYPE 
    SYNTAX INTEGER
    ACCESS read-only
    STATUS mandatory
    DESCRIPTION
        "Info: A battery test in progress reported."
    ::= { upsWellKnownAlarms 73 }

upsAlarmForcedBypass OBJECT-TYPE 
    SYNTAX INTEGER
    ACCESS read-only
    STATUS mandatory
    DESCRIPTION
        "Info: UPS has been forced to bypass mode."
    ::= { upsWellKnownAlarms 74 }

upsAlarmFirmwareUpdate OBJECT-TYPE 
    SYNTAX INTEGER
    ACCESS read-only
    STATUS mandatory
    DESCRIPTION
        "Info: Firmware has been updated."
    ::= { upsWellKnownAlarms 75 }

upsAlarmEE1ST OBJECT-TYPE 
    SYNTAX INTEGER
    ACCESS read-only
    STATUS mandatory
    DESCRIPTION
        "Info: EEPROM value are the first time."
    ::= { upsWellKnownAlarms 76 }

upsAlarmBypassEnable OBJECT-TYPE 
    SYNTAX INTEGER
    ACCESS read-only
    STATUS mandatory
    DESCRIPTION
        "Info: Bypass Enabled."
    ::= { upsWellKnownAlarms 77 }

upsAlarmBatteryTestDisable OBJECT-TYPE 
    SYNTAX INTEGER
    ACCESS read-only
    STATUS mandatory
    DESCRIPTION
        "Info: Battery Test Disabled."
    ::= { upsWellKnownAlarms 78 }

upsAlarmDefaultCalibration OBJECT-TYPE 
    SYNTAX INTEGER
    ACCESS read-only
    STATUS mandatory
    DESCRIPTION
        "Info: Touch Panel module is using default values instead of calibrated one."
    ::= { upsWellKnownAlarms 79 }

upsAlarmShutdownPending OBJECT-TYPE 
    SYNTAX INTEGER
    ACCESS read-only
    STATUS mandatory
    DESCRIPTION
        "Info: An output shutdown in progress reported. Output will turn off after delay."
    ::= { upsWellKnownAlarms 80 }

upsAlarmOutputOff OBJECT-TYPE 
    SYNTAX INTEGER
    ACCESS read-only
    STATUS mandatory
    DESCRIPTION
        "Info: An output off reported."
    ::= { upsWellKnownAlarms 81 }

upsAlarmOnBattery OBJECT-TYPE
    SYNTAX INTEGER
    ACCESS read-only
    STATUS mandatory
    DESCRIPTION
        "Info: The UPS is on Battery mode; it is supplying output power from its batteries."
    ::= { upsWellKnownAlarms 82 }
	
upsAlarmLogInError OBJECT-TYPE
    SYNTAX INTEGER
    ACCESS read-only
    STATUS mandatory
    DESCRIPTION
        "Info: The UPS Admin Password is incorrect."
    ::= { upsWellKnownAlarms 83 }

    
-- ===========================================================================
-- upsPassword  RMTI4 Group 11
-- The UPS Password group
-- ===========================================================================
upsPwdAdminCurrentAccessLevel OBJECT-TYPE
    SYNTAX DisplayString (SIZE (0..15))
    ACCESS read-only
    STATUS mandatory
    DESCRIPTION
        "The administrator access level."
    ::= { upsPassword 1 }

upsPwdAdminCurrentPswd OBJECT-TYPE
    SYNTAX DisplayString (SIZE (0..15))
    ACCESS read-write
    STATUS mandatory
    DESCRIPTION
        "The current password."
    ::= { upsPassword 2 }

upsPwdAdminNewPswd OBJECT-TYPE
    SYNTAX DisplayString (SIZE (0..7))
    ACCESS read-write
    STATUS mandatory
    DESCRIPTION
        "The current password."
    ::= { upsPassword 3 }

-- ===========================================================================
-- upsTraps - Group 12
-- Traps group
-- ===========================================================================
upsTrapFault TRAP-TYPE
    ENTERPRISE ups5000N3R 
    DESCRIPTION
        "Fault: One or more fault reported."
    ::= 1

upsTrapFaultClear TRAP-TYPE
    ENTERPRISE ups5000N3R  
    DESCRIPTION
        "Fault Clear: One or more fault reported."
    ::= 2

upsTrapEPOTrippedFault TRAP-TYPE
    ENTERPRISE ups5000N3R
    DESCRIPTION
        "Fault: EPO Activated."
    ::= 3

upsTrapEPOTrippedFaultClear TRAP-TYPE
    ENTERPRISE ups5000N3R
    DESCRIPTION
        "Fault Clear: EPO Activated."
    ::= 4

upsTrapCurrentLimitFault TRAP-TYPE
    ENTERPRISE ups5000N3R
    DESCRIPTION
        "Fault: A input over current reported. Contact your Toshiba authorized service center for examination."
    ::= 5

upsTrapCurrentLimitFaultClear TRAP-TYPE
    ENTERPRISE ups5000N3R
    DESCRIPTION
        "Fault Clear: A input over current reported. Contact your Toshiba authorized service center for examination."
    ::= 6

upsTrapDCBusAbnormal TRAP-TYPE 
    ENTERPRISE ups5000N3R
    DESCRIPTION
        "Fault: A DC bus abnormality reported. Contact your Toshiba authorized service center for assistance."
    ::= 7

upsTrapDCBusAbnormalClear TRAP-TYPE 
    ENTERPRISE ups5000N3R
    DESCRIPTION
        "Fault Clear: A DC bus abnormality reported. Contact your Toshiba authorized service center for assistance."
    ::= 8

upsTrapDCBusOverVoltage TRAP-TYPE 
    ENTERPRISE ups5000N3R
    DESCRIPTION
        "Fault: A DC bus overvoltage reported. Contact your Toshiba authorized service center for examination."
    ::= 9

upsTrapDCBusOverVoltageClear TRAP-TYPE 
    ENTERPRISE ups5000N3R
    DESCRIPTION
        "Fault Clear: A DC bus overvoltage reported. Contact your Toshiba authorized service center for examination."
    ::= 10

upsTrapDCBusImbalance TRAP-TYPE 
    ENTERPRISE ups5000N3R
    DESCRIPTION
        "Fault: A DC bus imbalance reported. Contact your Toshiba authorized service center for examination."
    ::= 11

upsTrapDCBusImbalanceClear TRAP-TYPE 
    ENTERPRISE ups5000N3R
    DESCRIPTION
        "Fault Clear: A DC bus imbalance reported. Contact your Toshiba authorized service center for examination."
    ::= 12

upsTrapInverterOverVoltage TRAP-TYPE 
    ENTERPRISE ups5000N3R
    DESCRIPTION
        "Fault: An inverter overvoltage reported. Contact your Toshiba authorized service center for examination."
    ::= 13

upsTrapInverterOverVoltageClear TRAP-TYPE 
    ENTERPRISE ups5000N3R
    DESCRIPTION
        "Fault Clear: An inverter overvoltage reported. Contact your Toshiba authorized service center for examination."
    ::= 14

upsTrapInverterUnderVoltage TRAP-TYPE 
    ENTERPRISE ups5000N3R
    DESCRIPTION
        "Fault: An output undervoltage reported. Contact your Toshiba authorized service center for examination."
    ::= 15

upsTrapInverterUnderVoltageClear TRAP-TYPE 
    ENTERPRISE ups5000N3R
    DESCRIPTION
        "Fault Clear: An output undervoltage reported. Contact your Toshiba authorized service center for examination."
    ::= 16

upsTrapUPSOverheat TRAP-TYPE 
    ENTERPRISE ups5000N3R
    DESCRIPTION
        "Fault: Device overheat reported."
    ::= 17

upsTrapUPSOverheatClear TRAP-TYPE 
    ENTERPRISE ups5000N3R
    DESCRIPTION
        "Fault Clear: Device overheat reported."
    ::= 18

upsTrapLoadAbnormal TRAP-TYPE 
    ENTERPRISE ups5000N3R 
    DESCRIPTION
        "Fault: Output overload reported frequently within 5 minutes."
    ::= 19

upsTrapLoadAbnormalClear TRAP-TYPE 
    ENTERPRISE ups5000N3R 
    DESCRIPTION
        "Fault Clear: Output overload reported frequently within 5 minutes."
    ::= 20

upsTrapChopperOverCurrent TRAP-TYPE 
    ENTERPRISE ups5000N3R
    DESCRIPTION
        "Fault: Chopper over current reported."
    ::= 21

upsTrapChopperOverCurrentClear TRAP-TYPE 
    ENTERPRISE ups5000N3R
    DESCRIPTION
        "Fault Clear: Chopper over current reported."
    ::= 22

upsTrapInverterOvercurrent TRAP-TYPE 
    ENTERPRISE ups5000N3R
    DESCRIPTION
        "Fault: An inverter overcurrent reported."
    ::= 23

upsTrapInverterOvercurrentClear TRAP-TYPE 
    ENTERPRISE ups5000N3R
    DESCRIPTION
        "Fault Clear: An inverter overcurrent reported."
    ::= 24

upsTrapPreChargeError TRAP-TYPE 
    ENTERPRISE ups5000N3R
    DESCRIPTION
        "Fault: Pre-Charge Error reported."
    ::= 25

upsTrapPreChargeErrorClear TRAP-TYPE 
    ENTERPRISE ups5000N3R
    DESCRIPTION
        "Fault Clear: Pre-Charge Error reported."
    ::= 26

upsTrapDCBusUnderVoltage TRAP-TYPE 
    ENTERPRISE ups5000N3R
    DESCRIPTION
        "Fault: A DC bus undervoltage reported."
    ::= 27

upsTrapDCBusUnderVoltageClear TRAP-TYPE 
    ENTERPRISE ups5000N3R
    DESCRIPTION
        "Fault Clear: A DC bus undervoltage reported."
    ::= 28

upsTrapBypassOverheat TRAP-TYPE
    ENTERPRISE ups5000N3R
    DESCRIPTION
        "Fault: A Bypass overheat reported."
    ::= 29

upsTrapBypassOverheatClear TRAP-TYPE
    ENTERPRISE ups5000N3R
    DESCRIPTION
        "Fault Clear: A Bypass overheat reported."
    ::= 30

upsTrapPCBAbnormal TRAP-TYPE 
    ENTERPRISE ups5000N3R 
    DESCRIPTION
        "Fault: An abnormality has occurred with the PCB."
    ::= 31

upsTrapPCBAbnormalClear TRAP-TYPE 
    ENTERPRISE ups5000N3R 
    DESCRIPTION
        "Fault Clear: An abnormality has occurred with the PCB."
    ::= 32

--upsTrapDummyFault TRAP-TYPE 
--    ENTERPRISE ups5000N3R 
--    DESCRIPTION
--        "Fault: Test fault has been set."
--    ::= 33

--upsTrapDummyFaultClear TRAP-TYPE 
--    ENTERPRISE ups5000N3R 
--    DESCRIPTION
--        "Fault Clear: Test fault has been set."
--    ::= 34

upsTrapInputPhaseRotationError TRAP-TYPE
    ENTERPRISE ups5000N3R
    DESCRIPTION
        "Fault: Input Phase Rotation Error reported."
    ::= 35

upsTrapInputPhaseRotationErrorClear TRAP-TYPE
    ENTERPRISE ups5000N3R
    DESCRIPTION
        "Fault Clear: Input Phase Rotation Error reported."
    ::= 36

upsTrapBypassPhaseRotationError TRAP-TYPE
    ENTERPRISE ups5000N3R
    DESCRIPTION
        "Fault: Bypass Phase Rotation Error reported."
    ::= 37

upsTrapBypassPhaseRotationErrorClear TRAP-TYPE
    ENTERPRISE ups5000N3R
    DESCRIPTION
        "Fault Clear: Bypass Phase Rotation Error reported."
    ::= 38

upsTrapInputAbnormal TRAP-TYPE 
    ENTERPRISE ups5000N3R 
    DESCRIPTION
        "Fault: An abnormality with input circuit occurred with the PCB."
    ::= 39

upsTrapInputAbnormalClear TRAP-TYPE 
    ENTERPRISE ups5000N3R 
    DESCRIPTION
        "Fault Clear: An abnormality with input circuit occurred with the PCB."
    ::= 40

upsTrapPowerSupplyOutofRange TRAP-TYPE 
    ENTERPRISE ups5000N3R 
    DESCRIPTION
        "Fault: An abnormality with power supply for control PCB detected."
    ::= 41

upsTrapPowerSupplyOutofRangeClear TRAP-TYPE 
    ENTERPRISE ups5000N3R 
    DESCRIPTION
        "Fault Clear: An abnormality with power supply for control PCB detected."
    ::= 42

upsTrapInverterVoltageAbnormal TRAP-TYPE 
    ENTERPRISE ups5000N3R 
    DESCRIPTION
        "Fault: An inverter voltage out of spec reported."
    ::= 43

upsTrapInverterVoltageAbnormalClear TRAP-TYPE 
    ENTERPRISE ups5000N3R 
    DESCRIPTION
        "Fault Clear: An inverter voltage out of spec reported."
    ::= 44

upsTrapOutputVoltageAbnormal TRAP-TYPE 
    ENTERPRISE ups5000N3R 
    DESCRIPTION
        "Fault: An output voltage out of spec reported."
    ::= 45

upsTrapOutputVoltageAbnormalClear TRAP-TYPE 
    ENTERPRISE ups5000N3R 
    DESCRIPTION
        "Fault Clear: An output voltage out of spec reported."
    ::= 46

upsTrapOutputUnderVoltage TRAP-TYPE 
    ENTERPRISE ups5000N3R 
    DESCRIPTION
        "Fault: An output under voltage reported."
    ::= 47

upsTrapOutputUnderVoltageeClear TRAP-TYPE 
    ENTERPRISE ups5000N3R 
    DESCRIPTION
        "Fault Clear: An output under voltage reported."
    ::= 48

upsTrapCurrentAbnormal TRAP-TYPE 
    ENTERPRISE ups5000N3R 
    DESCRIPTION
        "Fault: Current Abnormality reported."
    ::= 49

upsTrapCurrentAbnormalClear TRAP-TYPE 
    ENTERPRISE ups5000N3R 
    DESCRIPTION
        "Fault Clear: Current Abnormality reported."
    ::= 50

upsTrapInverterOutputVoltageAbnormal TRAP-TYPE 
    ENTERPRISE ups5000N3R 
    DESCRIPTION
        "Fault: An inverter output voltage out of spec reported."
    ::= 51

upsTrapInverterOutputVoltageAbnormalClear TRAP-TYPE 
    ENTERPRISE ups5000N3R 
    DESCRIPTION
        "Fault Clear: An inverter output voltage out of spec reported."
    ::= 52

upsTrapGateVoltagelost TRAP-TYPE 
    ENTERPRISE ups5000N3R 
    DESCRIPTION
        "Fault: Gate Voltage lost reported."
    ::= 53

upsTrapGateVoltagelostClear TRAP-TYPE 
    ENTERPRISE ups5000N3R 
    DESCRIPTION
        "Fault Clear: Gate Voltage lost reported."
    ::= 54

upsTrapInverterCurrentError TRAP-TYPE 
    ENTERPRISE ups5000N3R
    DESCRIPTION
        "Fault: Inverter current error reported."
    ::= 55

upsTrapInverterCurrentErrorClear TRAP-TYPE 
    ENTERPRISE ups5000N3R
    DESCRIPTION
        "Fault Clear: Inverter current error reported."
    ::= 56

upsTrapInverterBypassVoltageMismatch TRAP-TYPE 
    ENTERPRISE ups5000N3R
    DESCRIPTION
        "Fault: An inverter and bypass voltage out of spec reported."
    ::= 57

upsTrapInverterBypassVoltageMismatchClear TRAP-TYPE 
    ENTERPRISE ups5000N3R
    DESCRIPTION
        "Fault Clear: An inverter and bypass voltage out of spec reported."
    ::= 58

upsTrapNoControlConnection TRAP-TYPE 
    ENTERPRISE ups5000N3R
    DESCRIPTION
        "Fault: Control PCB is disconnected."
    ::= 59

upsTrapNoControlConnectionClear TRAP-TYPE 
    ENTERPRISE ups5000N3R
    DESCRIPTION
        "Fault Clear: Control PCB is disconnected."
    ::= 60

upsTrapInputVoltageError TRAP-TYPE 
    ENTERPRISE ups5000N3R
    DESCRIPTION
        "Warning: An input voltage error reported."
    ::= 61

upsTrapInputVoltageErrorClear TRAP-TYPE 
    ENTERPRISE ups5000N3R
    DESCRIPTION
        "Warning Clear: An input voltage error reported."
    ::= 62

upsTrapBattVoltExceed TRAP-TYPE 
    ENTERPRISE ups5000N3R
    DESCRIPTION
        "Warning: Battery voltage exceeded."
    ::= 63

upsTrapBattVoltExceedClear TRAP-TYPE 
    ENTERPRISE ups5000N3R
    DESCRIPTION
        "Warning Clear: Battery voltage exceeded."
    ::= 64

upsTrapBypassFrequencyError TRAP-TYPE 
    ENTERPRISE ups5000N3R
    DESCRIPTION
        "Warning: An bypass frequency error reported."
    ::= 65

upsTrapBypassFrequencyErrorClear TRAP-TYPE 
    ENTERPRISE ups5000N3R
    DESCRIPTION
        "Warning Clear: An bypass frequency error reported."
    ::= 66

upsTrapInputFrequencyError TRAP-TYPE 
    ENTERPRISE ups5000N3R
    DESCRIPTION
        "Warning: An input frequency error reported."
    ::= 67

upsTrapInputFrequencyErrorClear TRAP-TYPE 
    ENTERPRISE ups5000N3R
    DESCRIPTION
        "Warning Clear: An input frequency error reported."
    ::= 68

upsTrapBypassError TRAP-TYPE 
    ENTERPRISE ups5000N3R
    DESCRIPTION
        "Warning: Bypass voltage out of spec reported."
    ::= 69

upsTrapBypassErrorClear TRAP-TYPE 
    ENTERPRISE ups5000N3R
    DESCRIPTION
        "Warning Clear: Bypass voltage out of spec reported."
    ::= 70

upsTrapEEPROMtoRAMError TRAP-TYPE 
    ENTERPRISE ups5000N3R
    DESCRIPTION
        "Warning: An error occurred when writing from EEPROM to SRAM reported."
    ::= 71

upsTrapEEPROMtoRAMErrorClear TRAP-TYPE 
    ENTERPRISE ups5000N3R
    DESCRIPTION
        "Warning Clear: An error occurred when writing from EEPROM to SRAM reported."
    ::= 72

upsTrapBatteryTestFailed TRAP-TYPE 
    ENTERPRISE ups5000N3R
    DESCRIPTION
        "Warning: A battery test failed event reported."
    ::= 73

upsTrapBatteryTestFailedClear TRAP-TYPE 
    ENTERPRISE ups5000N3R
    DESCRIPTION
        "Warning Clear: A battery test failed event reported."
    ::= 74

upsTrapBatteryAbnormal TRAP-TYPE 
    ENTERPRISE ups5000N3R
    DESCRIPTION
        "Warning: A battery abnormality reported."
    ::= 75

upsTrapBatteryAbnormalClear TRAP-TYPE 
    ENTERPRISE ups5000N3R
    DESCRIPTION
        "Warning Clear: A battery abnormality reported."
    ::= 76

upsTrapBatteryLow TRAP-TYPE
    ENTERPRISE ups5000N3R
    DESCRIPTION
        "Warning: A low battery level reported."
    ::= 77

upsTrapBatteryLowClear TRAP-TYPE
    ENTERPRISE ups5000N3R
    DESCRIPTION
        "Warning Clear: A low battery level reported."
    ::= 78

upsTrapBatteryDepleted TRAP-TYPE
    ENTERPRISE ups5000N3R
    DESCRIPTION
        "Warning: A shutdown battery level reported."
    ::= 79

upsTrapBatteryDepletedClear TRAP-TYPE
    ENTERPRISE ups5000N3R
    DESCRIPTION
        "Warning Clear: A shutdown battery level reported."
    ::= 80

upsTrapBatteryBelowShutdown TRAP-TYPE
    ENTERPRISE ups5000N3R
    DESCRIPTION
        "Warning: Battery shutdown voltage lower than shutdown level."
    ::= 81

upsTrapBatteryBelowShutdownClear TRAP-TYPE
    ENTERPRISE ups5000N3R
    DESCRIPTION
        "Warning Clear: Battery shutdown voltage lower than shutdown level."
    ::= 82

upsTrapBatteryContactOpen TRAP-TYPE
    ENTERPRISE ups5000N3R
    DESCRIPTION
        "Warning: Battery contact open."
    ::= 83

upsTrapBatteryContactOpenClear TRAP-TYPE
    ENTERPRISE ups5000N3R
    DESCRIPTION
        "Warning Clear: Battery contact open."
    ::= 84

upsTrapOutputCurrentExceeded TRAP-TYPE
    ENTERPRISE ups5000N3R
    DESCRIPTION
        "Warning: Output current exceeded."
    ::= 85

upsTrapOutputCurrentExceededClear TRAP-TYPE
    ENTERPRISE ups5000N3R
    DESCRIPTION
        "Warning Clear: Output current exceeded."
    ::= 86

upsTrapChargerVoltageAbnormal TRAP-TYPE 
    ENTERPRISE ups5000N3R
    DESCRIPTION
        "Warning: Charger voltage abnormality reported."
    ::= 89

upsTrapChargerVoltageAbnormalClear TRAP-TYPE 
    ENTERPRISE ups5000N3R
    DESCRIPTION
        "Warning Clear: Charger voltage abnormality reported."
    ::= 90

upsTrapBattOverheatBattBreakerOpen TRAP-TYPE
    ENTERPRISE ups5000N3R
    DESCRIPTION
        "Warning: Battery overheat/battery breaker open."
    ::= 91

upsTrapBattOverheatBattBreakerOpenClear TRAP-TYPE
    ENTERPRISE ups5000N3R
    DESCRIPTION
        "Warning Clear: Battery overheat/battery breaker open."
    ::= 92

upsTrapOutputOverloadWarning TRAP-TYPE 
    ENTERPRISE ups5000N3R
    DESCRIPTION
        "Warning: Output load exceed 110%."
    ::= 93

upsTrapOutputOverloadWarningClear TRAP-TYPE 
    ENTERPRISE ups5000N3R
    DESCRIPTION
        "Warning Clear: Output load exceed 110%."
    ::= 94

upsTrapInverterOverloadWarning TRAP-TYPE 
    ENTERPRISE ups5000N3R
    DESCRIPTION
        "Warning: Inverter overload reported."
    ::= 95

upsTrapInverterOverloadWarningClear TRAP-TYPE 
    ENTERPRISE ups5000N3R
    DESCRIPTION
        "Warning Clear: Inverter overload reported."
    ::= 96

upsTrapOutputLoadExceeded TRAP-TYPE
    ENTERPRISE ups5000N3R
    DESCRIPTION
        "Warning: Output load exceed detection threshold."
    ::= 97

upsTrapOutputLoadExceededClear TRAP-TYPE
    ENTERPRISE ups5000N3R
    DESCRIPTION
        "Warning Clear: Output load exceed detection threshold."
    ::= 98

upsTrapCurrentLimitWarning TRAP-TYPE
    ENTERPRISE ups5000N3R
    DESCRIPTION
        "Warning: A current limit reported."
    ::= 99

upsTrapCurrentLimitWarningClear TRAP-TYPE
    ENTERPRISE ups5000N3R
    DESCRIPTION
        "Warning Clear: A current limit reported."
    ::= 100

upsTrapAsyncOperation TRAP-TYPE 
    ENTERPRISE ups5000N3R
    DESCRIPTION
        "Warning: An Asynchronous operation reported."
    ::= 101

upsTrapAsyncOperationClear TRAP-TYPE 
    ENTERPRISE ups5000N3R
    DESCRIPTION
        "Warning Clear: An Asynchronous operation reported."
    ::= 102

upsTrapOutputOverload TRAP-TYPE
    ENTERPRISE ups5000N3R
    DESCRIPTION
        "Warning: Output overload within specified time."
    ::= 103

upsTrapOutputOverloadClear TRAP-TYPE
    ENTERPRISE ups5000N3R
    DESCRIPTION
        "Warning Clear: Output overload within specified time."
    ::= 104
	
upsTrapUserDefinedOverloadWarning TRAP-TYPE 
    ENTERPRISE ups5000N3R
    DESCRIPTION
        "Warning: The inverter output load % is greater than the user defined overload set point (default: 110%)."
    ::= 105
	
upsTrapUserDefinedOverloadWarningClear TRAP-TYPE 
    ENTERPRISE ups5000N3R
    DESCRIPTION
        "Warning Clear: The inverter output load % is greater than the user defined overload set point (default: 110%)."
    ::= 106

upsTrapCoolingFanAbnormal TRAP-TYPE
    ENTERPRISE ups5000N3R
    DESCRIPTION
        "Warning: Cooling Fan Abnormal reported."
    ::= 107

upsTrapCoolingFanAbnormalClear TRAP-TYPE
    ENTERPRISE ups5000N3R
    DESCRIPTION
        "Warning Clear: Cooling Fan Abnormal reported."
    ::= 108

upsTrapVoltDeviationExceedBattVolt TRAP-TYPE
    ENTERPRISE ups5000N3R
    DESCRIPTION
        "Warning: Voltage Deviation across battery breaker exceeded."
    ::= 109

upsTrapVoltDeviationExceedBattVoltClear TRAP-TYPE
    ENTERPRISE ups5000N3R
    DESCRIPTION
        "Warning Clear: Voltage Deviation across battery breaker exceeded."
    ::= 110

upsTrapInverterOutputVoltOutofSpec TRAP-TYPE
    ENTERPRISE ups5000N3R
    DESCRIPTION
        "Warning: Input Voltage and Output voltage out of spec."
    ::= 111

upsTrapInverterOutputVoltOutofSpecClear TRAP-TYPE
    ENTERPRISE ups5000N3R
    DESCRIPTION
        "Warning Clear: Input Voltage and Output voltage out of spec."
    ::= 112

upsTrapLocalButtonAbnormal TRAP-TYPE
    ENTERPRISE ups5000N3R
    DESCRIPTION
        "Warning: Local button abnormal reported."
    ::= 113

upsTrapLocalButtonAbnormalClear TRAP-TYPE
    ENTERPRISE ups5000N3R
    DESCRIPTION
        "Warning Clear: Local button abnormal reported."
    ::= 114

upsTrapBatteryOverTemperature TRAP-TYPE
    ENTERPRISE ups5000N3R
    DESCRIPTION
        "Warning: Battery OverTemperature occurs for more than 2 hrs."
    ::= 115

upsTrapBatteryOverTemperatureClear TRAP-TYPE
    ENTERPRISE ups5000N3R
    DESCRIPTION
        "Warning Clear: Battery OverTemperature occurs for more than 2 hrs."
    ::= 116

upsTrapDischargeWarning TRAP-TYPE
    ENTERPRISE ups5000N3R
    DESCRIPTION
        "Warning: Discharge warning reported."
    ::= 117

upsTrapDischargeWarningClear TRAP-TYPE
    ENTERPRISE ups5000N3R
    DESCRIPTION
        "Warning Clear: Discharge warning reported."
    ::= 118

upsTrapBypPCBNoComm TRAP-TYPE
    ENTERPRISE ups5000N3R
    DESCRIPTION
        "Warning: Communication lost with Bypass PCB."
    ::= 119

upsTrapBypPCBNoCommClear TRAP-TYPE
    ENTERPRISE ups5000N3R
    DESCRIPTION
        "Warning Clear: Communication lost with Bypass PCB."
    ::= 120

upsTrapAutoTransferDisabled TRAP-TYPE
    ENTERPRISE ups5000N3R
    DESCRIPTION
        "Warning: Auto Transfer Disabled."
    ::= 121

upsTrapAutoTransferDisabledClear TRAP-TYPE
    ENTERPRISE ups5000N3R
    DESCRIPTION
        "Warning Clear: Auto Transfer Disabled."
    ::= 122

upsTrapControlPCBSupplyError TRAP-TYPE
    ENTERPRISE ups5000N3R
    DESCRIPTION
        "Warning: Control PCB power supply error reported."
    ::= 123

upsTrapControlPCBSupplyErrorClear TRAP-TYPE
    ENTERPRISE ups5000N3R
    DESCRIPTION
        "Warning Clear: Control PCB power supply error reported."
    ::= 124

upsTrapROMtoEEError TRAP-TYPE 
    ENTERPRISE ups5000N3R
    DESCRIPTION
        "Warning: An error occurred when writing from ROM to EEPROM reported."
    ::= 125

upsTrapROMtoEEErrorClear TRAP-TYPE 
    ENTERPRISE ups5000N3R
    DESCRIPTION
        "Warning Clear: An error occurred when writing from ROM to EEPROM reported."
    ::= 126

upsTrapOnBypass TRAP-TYPE
    ENTERPRISE ups5000N3R
    DESCRIPTION
        "Warning: The UPS is in Stop (Bypass) mode."
    ::= 127

upsTrapOnBypassClear TRAP-TYPE
    ENTERPRISE ups5000N3R
    DESCRIPTION
        "Warning Clear: The UPS is in Stop (Bypass) mode."
    ::= 128

upsTrapPowerFailure TRAP-TYPE 
    ENTERPRISE ups5000N3R
    DESCRIPTION
        "Info: A power failure reported."
    ::= 129

upsTrapPowerFailureClear TRAP-TYPE 
    ENTERPRISE ups5000N3R
    DESCRIPTION
        "Info Clear: A power failure reported."
    ::= 130

upsTrapEPOTripped TRAP-TYPE 
    ENTERPRISE ups5000N3R
    DESCRIPTION
        "Info: EPO has tripped reported."
    ::= 131

upsTrapEPOTrippedClear TRAP-TYPE 
    ENTERPRISE ups5000N3R
    DESCRIPTION
        "Info Clear: EPO has tripped reported."
    ::= 132

upsTrapRemoteSwitch TRAP-TYPE 
    ENTERPRISE ups5000N3R
    DESCRIPTION
        "Info: Remote Switch control enabled."
    ::= 133

upsTrapRemoteSwitchClear TRAP-TYPE 
    ENTERPRISE ups5000N3R
    DESCRIPTION
        "Info Clear: Remote Switch control enabled."
    ::= 134

upsTrapAutoTransferEnable TRAP-TYPE 
    ENTERPRISE ups5000N3R
    DESCRIPTION
        "Info: Auto Re-transfer enabled."
    ::= 135

upsTrapAutoTransferEnableClear TRAP-TYPE 
    ENTERPRISE ups5000N3R
    DESCRIPTION
        "Info Clear: Auto Re-transfer enabled."
    ::= 136

upsTrapProtectiveCharging TRAP-TYPE 
    ENTERPRISE ups5000N3R
    DESCRIPTION
        "Info: Protective Charging set."
    ::= 137

upsTrapProtectiveChargingClear TRAP-TYPE 
    ENTERPRISE ups5000N3R
    DESCRIPTION
        "Info Clear: Protective Charging set."
    ::= 138

upsTrapEqualizedCharging TRAP-TYPE 
    ENTERPRISE ups5000N3R
    DESCRIPTION
        "Info: Equalized Charging set."
    ::= 139

upsTrapEqualizedChargingClear TRAP-TYPE 
    ENTERPRISE ups5000N3R
    DESCRIPTION
        "Info Clear: Equalized Charging set."
    ::= 140

upsTrapManualMode TRAP-TYPE 
    ENTERPRISE ups5000N3R
    DESCRIPTION
        "Info: Manual Mode selected."
    ::= 141

upsTrapManualModeClear TRAP-TYPE 
    ENTERPRISE ups5000N3R
    DESCRIPTION
        "Info Clear: Manual Mode selected."
    ::= 142

upsTrapOutputFrequency50Hz TRAP-TYPE 
    ENTERPRISE ups5000N3R
    DESCRIPTION
        "Info: Output frequency is selected to 50Hz."
    ::= 143

upsTrapOutputFrequency50HzClear TRAP-TYPE 
    ENTERPRISE ups5000N3R
    DESCRIPTION
        "Info Clear: Output frequency is selected to 50Hz."
    ::= 144

upsTrapBatteryTestInProgress TRAP-TYPE
    ENTERPRISE ups5000N3R
    DESCRIPTION
        "Info: A battery test in progress reported."
    ::= 145

upsTrapBatteryTestInProgressClear TRAP-TYPE
    ENTERPRISE ups5000N3R
    DESCRIPTION
        "Info Clear: A battery test in progress reported."	
    ::= 146

upsTrapForcedBypass TRAP-TYPE
    ENTERPRISE ups5000N3R
    DESCRIPTION
        "Info: UPS has been forced to bypass mode."
    ::= 147

upsTrapForcedBypassClear TRAP-TYPE
    ENTERPRISE ups5000N3R
    DESCRIPTION
        "Info Clear: UPS has been forced to bypass mode."	
    ::= 148

upsTrapFirmwareUpdate TRAP-TYPE
    ENTERPRISE ups5000N3R
    DESCRIPTION
        "Info: Firmware has been upated."
    ::= 149

upsTrapFirmwareUpdateClear TRAP-TYPE
    ENTERPRISE ups5000N3R
    DESCRIPTION
        "Info Clear: Firmware has been upated."	
    ::= 150

upsTrapEE1ST TRAP-TYPE
    ENTERPRISE ups5000N3R
    DESCRIPTION
        "Info: EEPROM value are the first time."
    ::= 151

upsTrapEE1STClear TRAP-TYPE
    ENTERPRISE ups5000N3R
    DESCRIPTION
        "Info Clear: EEPROM value are the first time."	
    ::= 152

upsTrapBypassEnable TRAP-TYPE
    ENTERPRISE ups5000N3R
    DESCRIPTION
        "Info: Bypass Enabled."
    ::= 153

upsTrapBypassEnableClear TRAP-TYPE
    ENTERPRISE ups5000N3R
    DESCRIPTION
        "Info Clear: Bypass Enabled."	
    ::= 154

upsTrapBatteryTestDisabled TRAP-TYPE
    ENTERPRISE ups5000N3R
    DESCRIPTION
        "Info: Battery Test Disabled."
    ::= 155

upsTrapBatteryTestDisabledClear TRAP-TYPE
    ENTERPRISE ups5000N3R
    DESCRIPTION
        "Info Clear: Battery Test Disabled."	
    ::= 156

upsTrapDefaultCalibration TRAP-TYPE 
    ENTERPRISE ups5000N3R
    DESCRIPTION
        "Info: Touch Panel module is using default value instead of calibrated ones."
    ::= 157

upsTrapDefaultCalibrationClear TRAP-TYPE 
    ENTERPRISE ups5000N3R
    DESCRIPTION
        "Info Clear: Touch Panel module is using default value instead of calibrated ones."
    ::= 158

upsTrapShutdownPending TRAP-TYPE
    ENTERPRISE ups5000N3R
    DESCRIPTION
        "Info: A output shutdown in progress reported. Output will turn off after delay."
    ::= 159

upsTrapShutdownPendingClear TRAP-TYPE
    ENTERPRISE ups5000N3R
    DESCRIPTION
        "Info Clear: A output shutdown in progress reported. Output will turn off after delay."
    ::= 160

upsTrapOutputOff TRAP-TYPE
    ENTERPRISE ups5000N3R
    DESCRIPTION
        "Info: The UPS system output is off."
    ::= 161

upsTrapOutputOffClear TRAP-TYPE
    ENTERPRISE ups5000N3R
    DESCRIPTION
        "Info Clear: The UPS system output is off."
    ::= 162

upsTrapOnBattery TRAP-TYPE
    ENTERPRISE ups5000N3R
    DESCRIPTION
        "Info: The UPS is on Battery mode; it is supplying output power from its batteries."
    ::= 163

upsTrapOnBatteryClear TRAP-TYPE
    ENTERPRISE ups5000N3R
    DESCRIPTION
        "Info Clear: The UPS is on Battery mode; it is supplying output power from its batteries."
    ::= 164

upsTrapLogInError TRAP-TYPE 
    ENTERPRISE ups5000N3R
    DESCRIPTION
        "Info: UPS Password is incorrect."
    ::= 165

upsTrapLogInErrorClear TRAP-TYPE 
    ENTERPRISE ups5000N3R
    DESCRIPTION
        "Info Clear: UPS Password is incorrect."
    ::= 166
	
END
