-- *************************************************
-- ITMeters.mib
--
-- Created:07-Dec-19 9:35 AM AST
--
-- Copyright 2019 Tridium, Inc.
-- *************************************************
--


ITMETERS DEFINITIONS ::= BEGIN

-- MIB II Extension Definitions for hub management

IMPORTS
         OBJECT-TYPE
               FROM RFC-1212
         TRAP-TYPE
               FROM RFC-1215
         enterprises, IpAddress, Counter, TimeTicks, Gauge
               FROM RFC1155-SMI
         DisplayString
               FROM RFC1213-MIB;

    tridium           OBJECT IDENTIFIER ::= { enterprises 4131 }
    tridiumStation    OBJECT IDENTIFIER ::= { tridium 1 }

version    OBJECT-TYPE
    SYNTAX     DisplayString
    ACCESS     read-only
    STATUS     mandatory
    DESCRIPTION
    "Current software version"
    ::=  { tridiumStation 1 }

action   OBJECT-TYPE
    SYNTAX            INTEGER{
                       noAction(0),
                       ackAll(1)
                      }
    ACCESS            read-write
    STATUS            mandatory
    DESCRIPTION
    "Provides means for manager to perform actions on the alarm table. 0 (no action) or 1 (acknowledge all)."
    ::=  { tridiumStation 2 }

-- ***********************************
-- *
-- *  Alarm table declarations
-- *
-- ***********************************

alarmTable   OBJECT-TYPE
    SYNTAX                SEQUENCE OF AlarmTableEntry
    ACCESS                not-accessible
    STATUS                mandatory
    DESCRIPTION
    "A list of alarms in the station which have an snmp recipient (configured to store received alarms)."
    ::=  { tridiumStation 3 }

alarmTableEntry  OBJECT-TYPE
    SYNTAX                AlarmTableEntry
    ACCESS                not-accessible
    STATUS                mandatory
    DESCRIPTION
    "An alarm table entry containing data for a specific alarm."
    INDEX  { alarmId }  ::=   { alarmTable 1 }

AlarmTableEntry ::= SEQUENCE {
        timestamp        DisplayString,
        uuid             OCTET STRING,
        sourceState      INTEGER,
        ackState         INTEGER,
        ackRequired      INTEGER,
        source           DisplayString,
        alarmClass       DisplayString,
        priority         INTEGER,
        normalTime       DisplayString,
        ackTime          DisplayString,
        user             DisplayString,
        alarmData        DisplayString,
        alarmTransition  INTEGER,
        lastUpdate       DisplayString,
        alarmId          INTEGER
    }

timestamp   OBJECT-TYPE
    SYNTAX           DisplayString
    ACCESS           read-only
    STATUS           mandatory
    DESCRIPTION
    "Indicates the time when the alarm occurred."
    ::=   { alarmTableEntry 1 }

uuid   OBJECT-TYPE
    SYNTAX           OCTET STRING(SIZE(0..255))
    ACCESS           read-only
    STATUS           mandatory
    DESCRIPTION
    "The unique universal identifier of the alarm."
    ::=   { alarmTableEntry 2 }

sourceState   OBJECT-TYPE
    SYNTAX           INTEGER {
                       normal(0),
                       offnormal(1),
                       fault(2),
                       alert(3)
                     }
    ACCESS           read-only
    STATUS           mandatory
    DESCRIPTION
    "The current state of the source.  normal(0), offnormal(1), fault(2), or alert(3)."
    ::=   { alarmTableEntry 3 }

ackState   OBJECT-TYPE
    SYNTAX           INTEGER {
                       acked(0),
                       unacked(1),
                       ackPending(2)
                     }
    ACCESS           read-write
    STATUS           mandatory
    DESCRIPTION
    "Indicates if the alarm has been acknowledged.  acked(0), unacked(1), or ackPending(2).
     Alarm can be acknowledged by setting ackState to 'acked'(0)"
    ::=   { alarmTableEntry 4 }

ackRequired   OBJECT-TYPE
    SYNTAX           INTEGER {
                       false(0),
                       true(1)
                     }
    ACCESS           read-only
    STATUS           mandatory
    DESCRIPTION
    "Indicates if an acknowledgement is required for the alarm.  false(0), or true(1)."
    ::=   { alarmTableEntry 5 }

source    OBJECT-TYPE
    SYNTAX           DisplayString
    ACCESS           read-only
    STATUS           mandatory
    DESCRIPTION
    "Indicates the path to the station object which generated the alarm."
    ::=   { alarmTableEntry 6 }

alarmClass  OBJECT-TYPE
    SYNTAX           DisplayString
    ACCESS           read-only
    STATUS           mandatory
    DESCRIPTION
    "The alarm class for the alarm."
    ::=   { alarmTableEntry 7 }

priority   OBJECT-TYPE
    SYNTAX           INTEGER(0..255)
    ACCESS           read-only
    STATUS           mandatory
    DESCRIPTION
    "The priority of the alarm (0=high, 255=low)."
    ::=   { alarmTableEntry 8 }

normalTime   OBJECT-TYPE
    SYNTAX           DisplayString
    ACCESS           read-only
    STATUS           mandatory
    DESCRIPTION
    "The time at which the alarm goes back to normal state."
    ::=   { alarmTableEntry 9 }

ackTime  OBJECT-TYPE
    SYNTAX           DisplayString
    ACCESS           read-only
    STATUS           mandatory
    DESCRIPTION
    "The time at which the alarm is acked. Note that
     interpretation of this value depends upon the state of the alarm."
    ::=   { alarmTableEntry 10 }

user   OBJECT-TYPE
    SYNTAX           DisplayString
    ACCESS           read-only
    STATUS           mandatory
    DESCRIPTION
    "The name of the user who acknowledged the alarm."
    ::=   { alarmTableEntry 11 }

alarmData     OBJECT-TYPE
    SYNTAX           DisplayString
    ACCESS           read-only
    STATUS           mandatory
    DESCRIPTION
    "A string containing dynamic alarm data, in key-value pairs."
    ::=   { alarmTableEntry 12 }

alarmTransition   OBJECT-TYPE
    SYNTAX           INTEGER {
                       normal(0),
                       offnormal(1),
                       fault(2),
                       alert(3)
                     }
    ACCESS           read-only
    STATUS           mandatory
    DESCRIPTION
    "The initial state of the source.  normal(0), offnormal(1), fault(2), or alert(3)."
    ::=   { alarmTableEntry 13 }

lastUpdate  OBJECT-TYPE
    SYNTAX           DisplayString
    ACCESS           read-only
    STATUS           mandatory
    DESCRIPTION
    "The time at which the alarm was last updated. Updates occur
     at creation, acknowlegement, and changes to alarmData such as notes."
    ::=   { alarmTableEntry 14 }

alarmId   OBJECT-TYPE
    SYNTAX           INTEGER(0..2147483647)
    ACCESS           read-only
    STATUS           mandatory
    DESCRIPTION
    "Numerical identifier for the alarm in the Snmp alarm table.
     Used as an index to address table entries"
    ::=   { alarmTableEntry 15 }


-- ***********************************
-- *
-- *  Input table declarations
-- *
-- ***********************************

inputTable   OBJECT-TYPE
    SYNTAX                SEQUENCE OF InputTableEntry
    ACCESS                not-accessible
    STATUS                mandatory
    DESCRIPTION
    "A list of snmp input (read-only) object values."
    ::=  { tridiumStation 4 }

inputTableEntry  OBJECT-TYPE
    SYNTAX                InputTableEntry
    ACCESS                not-accessible
    STATUS                mandatory
    DESCRIPTION
    "An input table entry containing data for a specific input."
    INDEX  { inputIndex }  ::=   { inputTable 1 }

InputTableEntry ::= SEQUENCE {
        inputIndex       INTEGER,
        inputName        DisplayString,
        inputValue       DisplayString
    }

inputIndex   OBJECT-TYPE
    SYNTAX           INTEGER(0..2147483647)
    ACCESS           read-only
    STATUS           mandatory
    DESCRIPTION
    "The index in the input table for a particular snmp input
	 object.  Used to address table entries."
    ::=   { inputTableEntry 1 }


inputName    OBJECT-TYPE
    SYNTAX           DisplayString
    ACCESS           read-only
    STATUS           mandatory
    DESCRIPTION
    "Name of station object."
    ::=   { inputTableEntry 2 }

inputValue    OBJECT-TYPE
    SYNTAX           DisplayString
    ACCESS           read-write
    STATUS           mandatory
    DESCRIPTION
    "Current value of station object. Is read-write ."
    ::=   { inputTableEntry 3 }



-- ***********************************
-- *
-- *  Output table declarations
-- *
-- ***********************************

outputTable   OBJECT-TYPE
    SYNTAX                SEQUENCE OF OutputTableEntry
    ACCESS                not-accessible
    STATUS                mandatory
    DESCRIPTION
    "A list of snmp output (read-only) object values."
    ::=  { tridiumStation 5 }

outputTableEntry  OBJECT-TYPE
    SYNTAX                OutputTableEntry
    ACCESS                not-accessible
    STATUS                mandatory
    DESCRIPTION
    "An output table entry containing data for a specific output."
    INDEX  { outputIndex }  ::=   { outputTable 1 }

OutputTableEntry ::= SEQUENCE {
        outputIndex       INTEGER,
        outputName        DisplayString,
        outputValue       DisplayString
    }

outputIndex   OBJECT-TYPE
    SYNTAX           INTEGER(0..2147483647)
    ACCESS           read-only
    STATUS           mandatory
    DESCRIPTION
    "The index in the output table for a particular snmp output
	 object.  Used to address table entries."
    ::=   { outputTableEntry 1 }


outputName    OBJECT-TYPE
    SYNTAX           DisplayString
    ACCESS           read-only
    STATUS           mandatory
    DESCRIPTION
    "Name of station object."
    ::=   { outputTableEntry 2 }

outputValue    OBJECT-TYPE
    SYNTAX           DisplayString
    ACCESS           read-only
    STATUS           mandatory
    DESCRIPTION
    "Current value of station object. Is read-only ."
    ::=   { outputTableEntry 3 }


-- ***********************************
-- *
-- *  ExportTables
-- *
-- ***********************************

    exportTables    OBJECT IDENTIFIER ::= { tridiumStation 6 }

-- ***********************************
-- *
-- *  Export
-- *
-- ***********************************
    export    OBJECT IDENTIFIER ::= { exportTables 1 }

-- ***********************************
-- *
-- *  ExportInput table declarations
-- *
-- ***********************************

exportInputTable   OBJECT-TYPE
    SYNTAX                SEQUENCE OF ExportInputTableEntry
    ACCESS                not-accessible
    STATUS                mandatory
    DESCRIPTION
    "A list of snmp exportInput (read-only) object values."
    ::=  { export 1 }

exportInputTableEntry  OBJECT-TYPE
    SYNTAX                ExportInputTableEntry
    ACCESS                not-accessible
    STATUS                mandatory
    DESCRIPTION
    "An exportInput table entry containing data for a specific exportInput."
    INDEX  { exportInputIndex }  ::=   { exportInputTable 1 }

ExportInputTableEntry ::= SEQUENCE {
        exportInputIndex       INTEGER,
        exportInputName        DisplayString,
        exportInputValue       DisplayString
    }

exportInputIndex   OBJECT-TYPE
    SYNTAX           INTEGER(0..2147483647)
    ACCESS           read-only
    STATUS           mandatory
    DESCRIPTION
    "The index in the exportInput table for a particular snmp exportInput
	 object.  Used to address table entries."
    ::=   { exportInputTableEntry 1 }


exportInputName    OBJECT-TYPE
    SYNTAX           DisplayString
    ACCESS           read-only
    STATUS           mandatory
    DESCRIPTION
    "Name of station object."
    ::=   { exportInputTableEntry 2 }

exportInputValue    OBJECT-TYPE
    SYNTAX           DisplayString
    ACCESS           read-write
    STATUS           mandatory
    DESCRIPTION
    "Current value of station object. Is read-write ."
    ::=   { exportInputTableEntry 3 }



-- ***********************************
-- *
-- *  ExportOutput table declarations
-- *
-- ***********************************

exportOutputTable   OBJECT-TYPE
    SYNTAX                SEQUENCE OF ExportOutputTableEntry
    ACCESS                not-accessible
    STATUS                mandatory
    DESCRIPTION
    "A list of snmp exportOutput (read-only) object values."
    ::=  { export 2 }

exportOutputTableEntry  OBJECT-TYPE
    SYNTAX                ExportOutputTableEntry
    ACCESS                not-accessible
    STATUS                mandatory
    DESCRIPTION
    "An exportOutput table entry containing data for a specific exportOutput."
    INDEX  { exportOutputIndex }  ::=   { exportOutputTable 1 }

ExportOutputTableEntry ::= SEQUENCE {
        exportOutputIndex       INTEGER,
        exportOutputName        DisplayString,
        exportOutputValue       DisplayString
    }

exportOutputIndex   OBJECT-TYPE
    SYNTAX           INTEGER(0..2147483647)
    ACCESS           read-only
    STATUS           mandatory
    DESCRIPTION
    "The index in the exportOutput table for a particular snmp exportOutput
	 object.  Used to address table entries."
    ::=   { exportOutputTableEntry 1 }


exportOutputName    OBJECT-TYPE
    SYNTAX           DisplayString
    ACCESS           read-only
    STATUS           mandatory
    DESCRIPTION
    "Name of station object."
    ::=   { exportOutputTableEntry 2 }

exportOutputValue    OBJECT-TYPE
    SYNTAX           DisplayString
    ACCESS           read-only
    STATUS           mandatory
    DESCRIPTION
    "Current value of station object. Is read-only ."
    ::=   { exportOutputTableEntry 3 }


-- ***********************************
-- *
-- *  B01_D216
-- *
-- ***********************************
    b01_D216    OBJECT IDENTIFIER ::= { exportTables 2 }

-- ***********************************
-- *
-- *  B01_D216Input table declarations
-- *
-- ***********************************

b01_D216InputTable   OBJECT-TYPE
    SYNTAX                SEQUENCE OF B01_D216InputTableEntry
    ACCESS                not-accessible
    STATUS                mandatory
    DESCRIPTION
    "A list of snmp b01_D216Input (read-only) object values."
    ::=  { b01_D216 1 }

b01_D216InputTableEntry  OBJECT-TYPE
    SYNTAX                B01_D216InputTableEntry
    ACCESS                not-accessible
    STATUS                mandatory
    DESCRIPTION
    "An b01_D216Input table entry containing data for a specific b01_D216Input."
    INDEX  { b01_D216InputIndex }  ::=   { b01_D216InputTable 1 }

B01_D216InputTableEntry ::= SEQUENCE {
        b01_D216InputIndex       INTEGER,
        b01_D216InputName        DisplayString,
        b01_D216InputValue       DisplayString
    }

b01_D216InputIndex   OBJECT-TYPE
    SYNTAX           INTEGER(0..2147483647)
    ACCESS           read-only
    STATUS           mandatory
    DESCRIPTION
    "The index in the b01_D216Input table for a particular snmp b01_D216Input
	 object.  Used to address table entries."
    ::=   { b01_D216InputTableEntry 1 }


b01_D216InputName    OBJECT-TYPE
    SYNTAX           DisplayString
    ACCESS           read-only
    STATUS           mandatory
    DESCRIPTION
    "Name of station object."
    ::=   { b01_D216InputTableEntry 2 }

b01_D216InputValue    OBJECT-TYPE
    SYNTAX           DisplayString
    ACCESS           read-write
    STATUS           mandatory
    DESCRIPTION
    "Current value of station object. Is read-write ."
    ::=   { b01_D216InputTableEntry 3 }



-- ***********************************
-- *
-- *  B01_D216Output table declarations
-- *
-- ***********************************

b01_D216OutputTable   OBJECT-TYPE
    SYNTAX                SEQUENCE OF B01_D216OutputTableEntry
    ACCESS                not-accessible
    STATUS                mandatory
    DESCRIPTION
    "A list of snmp b01_D216Output (read-only) object values."
    ::=  { b01_D216 2 }

b01_D216OutputTableEntry  OBJECT-TYPE
    SYNTAX                B01_D216OutputTableEntry
    ACCESS                not-accessible
    STATUS                mandatory
    DESCRIPTION
    "An b01_D216Output table entry containing data for a specific b01_D216Output."
    INDEX  { b01_D216OutputIndex }  ::=   { b01_D216OutputTable 1 }

B01_D216OutputTableEntry ::= SEQUENCE {
        b01_D216OutputIndex       INTEGER,
        b01_D216OutputName        DisplayString,
        b01_D216OutputValue       DisplayString
    }

b01_D216OutputIndex   OBJECT-TYPE
    SYNTAX           INTEGER(0..2147483647)
    ACCESS           read-only
    STATUS           mandatory
    DESCRIPTION
    "The index in the b01_D216Output table for a particular snmp b01_D216Output
	 object.  Used to address table entries."
    ::=   { b01_D216OutputTableEntry 1 }


b01_D216OutputName    OBJECT-TYPE
    SYNTAX           DisplayString
    ACCESS           read-only
    STATUS           mandatory
    DESCRIPTION
    "Name of station object."
    ::=   { b01_D216OutputTableEntry 2 }

b01_D216OutputValue    OBJECT-TYPE
    SYNTAX           DisplayString
    ACCESS           read-only
    STATUS           mandatory
    DESCRIPTION
    "Current value of station object. Is read-only ."
    ::=   { b01_D216OutputTableEntry 3 }


-- ***********************************
-- *
-- *  B01_D217
-- *
-- ***********************************
    b01_D217    OBJECT IDENTIFIER ::= { exportTables 3 }

-- ***********************************
-- *
-- *  B01_D217Input table declarations
-- *
-- ***********************************

b01_D217InputTable   OBJECT-TYPE
    SYNTAX                SEQUENCE OF B01_D217InputTableEntry
    ACCESS                not-accessible
    STATUS                mandatory
    DESCRIPTION
    "A list of snmp b01_D217Input (read-only) object values."
    ::=  { b01_D217 1 }

b01_D217InputTableEntry  OBJECT-TYPE
    SYNTAX                B01_D217InputTableEntry
    ACCESS                not-accessible
    STATUS                mandatory
    DESCRIPTION
    "An b01_D217Input table entry containing data for a specific b01_D217Input."
    INDEX  { b01_D217InputIndex }  ::=   { b01_D217InputTable 1 }

B01_D217InputTableEntry ::= SEQUENCE {
        b01_D217InputIndex       INTEGER,
        b01_D217InputName        DisplayString,
        b01_D217InputValue       DisplayString
    }

b01_D217InputIndex   OBJECT-TYPE
    SYNTAX           INTEGER(0..2147483647)
    ACCESS           read-only
    STATUS           mandatory
    DESCRIPTION
    "The index in the b01_D217Input table for a particular snmp b01_D217Input
	 object.  Used to address table entries."
    ::=   { b01_D217InputTableEntry 1 }


b01_D217InputName    OBJECT-TYPE
    SYNTAX           DisplayString
    ACCESS           read-only
    STATUS           mandatory
    DESCRIPTION
    "Name of station object."
    ::=   { b01_D217InputTableEntry 2 }

b01_D217InputValue    OBJECT-TYPE
    SYNTAX           DisplayString
    ACCESS           read-write
    STATUS           mandatory
    DESCRIPTION
    "Current value of station object. Is read-write ."
    ::=   { b01_D217InputTableEntry 3 }



-- ***********************************
-- *
-- *  B01_D217Output table declarations
-- *
-- ***********************************

b01_D217OutputTable   OBJECT-TYPE
    SYNTAX                SEQUENCE OF B01_D217OutputTableEntry
    ACCESS                not-accessible
    STATUS                mandatory
    DESCRIPTION
    "A list of snmp b01_D217Output (read-only) object values."
    ::=  { b01_D217 2 }

b01_D217OutputTableEntry  OBJECT-TYPE
    SYNTAX                B01_D217OutputTableEntry
    ACCESS                not-accessible
    STATUS                mandatory
    DESCRIPTION
    "An b01_D217Output table entry containing data for a specific b01_D217Output."
    INDEX  { b01_D217OutputIndex }  ::=   { b01_D217OutputTable 1 }

B01_D217OutputTableEntry ::= SEQUENCE {
        b01_D217OutputIndex       INTEGER,
        b01_D217OutputName        DisplayString,
        b01_D217OutputValue       DisplayString
    }

b01_D217OutputIndex   OBJECT-TYPE
    SYNTAX           INTEGER(0..2147483647)
    ACCESS           read-only
    STATUS           mandatory
    DESCRIPTION
    "The index in the b01_D217Output table for a particular snmp b01_D217Output
	 object.  Used to address table entries."
    ::=   { b01_D217OutputTableEntry 1 }


b01_D217OutputName    OBJECT-TYPE
    SYNTAX           DisplayString
    ACCESS           read-only
    STATUS           mandatory
    DESCRIPTION
    "Name of station object."
    ::=   { b01_D217OutputTableEntry 2 }

b01_D217OutputValue    OBJECT-TYPE
    SYNTAX           DisplayString
    ACCESS           read-only
    STATUS           mandatory
    DESCRIPTION
    "Current value of station object. Is read-only ."
    ::=   { b01_D217OutputTableEntry 3 }


-- ***********************************
-- *
-- *  B01_D218
-- *
-- ***********************************
    b01_D218    OBJECT IDENTIFIER ::= { exportTables 4 }

-- ***********************************
-- *
-- *  B01_D218Input table declarations
-- *
-- ***********************************

b01_D218InputTable   OBJECT-TYPE
    SYNTAX                SEQUENCE OF B01_D218InputTableEntry
    ACCESS                not-accessible
    STATUS                mandatory
    DESCRIPTION
    "A list of snmp b01_D218Input (read-only) object values."
    ::=  { b01_D218 1 }

b01_D218InputTableEntry  OBJECT-TYPE
    SYNTAX                B01_D218InputTableEntry
    ACCESS                not-accessible
    STATUS                mandatory
    DESCRIPTION
    "An b01_D218Input table entry containing data for a specific b01_D218Input."
    INDEX  { b01_D218InputIndex }  ::=   { b01_D218InputTable 1 }

B01_D218InputTableEntry ::= SEQUENCE {
        b01_D218InputIndex       INTEGER,
        b01_D218InputName        DisplayString,
        b01_D218InputValue       DisplayString
    }

b01_D218InputIndex   OBJECT-TYPE
    SYNTAX           INTEGER(0..2147483647)
    ACCESS           read-only
    STATUS           mandatory
    DESCRIPTION
    "The index in the b01_D218Input table for a particular snmp b01_D218Input
	 object.  Used to address table entries."
    ::=   { b01_D218InputTableEntry 1 }


b01_D218InputName    OBJECT-TYPE
    SYNTAX           DisplayString
    ACCESS           read-only
    STATUS           mandatory
    DESCRIPTION
    "Name of station object."
    ::=   { b01_D218InputTableEntry 2 }

b01_D218InputValue    OBJECT-TYPE
    SYNTAX           DisplayString
    ACCESS           read-write
    STATUS           mandatory
    DESCRIPTION
    "Current value of station object. Is read-write ."
    ::=   { b01_D218InputTableEntry 3 }



-- ***********************************
-- *
-- *  B01_D218Output table declarations
-- *
-- ***********************************

b01_D218OutputTable   OBJECT-TYPE
    SYNTAX                SEQUENCE OF B01_D218OutputTableEntry
    ACCESS                not-accessible
    STATUS                mandatory
    DESCRIPTION
    "A list of snmp b01_D218Output (read-only) object values."
    ::=  { b01_D218 2 }

b01_D218OutputTableEntry  OBJECT-TYPE
    SYNTAX                B01_D218OutputTableEntry
    ACCESS                not-accessible
    STATUS                mandatory
    DESCRIPTION
    "An b01_D218Output table entry containing data for a specific b01_D218Output."
    INDEX  { b01_D218OutputIndex }  ::=   { b01_D218OutputTable 1 }

B01_D218OutputTableEntry ::= SEQUENCE {
        b01_D218OutputIndex       INTEGER,
        b01_D218OutputName        DisplayString,
        b01_D218OutputValue       DisplayString
    }

b01_D218OutputIndex   OBJECT-TYPE
    SYNTAX           INTEGER(0..2147483647)
    ACCESS           read-only
    STATUS           mandatory
    DESCRIPTION
    "The index in the b01_D218Output table for a particular snmp b01_D218Output
	 object.  Used to address table entries."
    ::=   { b01_D218OutputTableEntry 1 }


b01_D218OutputName    OBJECT-TYPE
    SYNTAX           DisplayString
    ACCESS           read-only
    STATUS           mandatory
    DESCRIPTION
    "Name of station object."
    ::=   { b01_D218OutputTableEntry 2 }

b01_D218OutputValue    OBJECT-TYPE
    SYNTAX           DisplayString
    ACCESS           read-only
    STATUS           mandatory
    DESCRIPTION
    "Current value of station object. Is read-only ."
    ::=   { b01_D218OutputTableEntry 3 }


-- ***********************************
-- *
-- *  B01_D300
-- *
-- ***********************************
    b01_D300    OBJECT IDENTIFIER ::= { exportTables 5 }

-- ***********************************
-- *
-- *  B01_D300Input table declarations
-- *
-- ***********************************

b01_D300InputTable   OBJECT-TYPE
    SYNTAX                SEQUENCE OF B01_D300InputTableEntry
    ACCESS                not-accessible
    STATUS                mandatory
    DESCRIPTION
    "A list of snmp b01_D300Input (read-only) object values."
    ::=  { b01_D300 1 }

b01_D300InputTableEntry  OBJECT-TYPE
    SYNTAX                B01_D300InputTableEntry
    ACCESS                not-accessible
    STATUS                mandatory
    DESCRIPTION
    "An b01_D300Input table entry containing data for a specific b01_D300Input."
    INDEX  { b01_D300InputIndex }  ::=   { b01_D300InputTable 1 }

B01_D300InputTableEntry ::= SEQUENCE {
        b01_D300InputIndex       INTEGER,
        b01_D300InputName        DisplayString,
        b01_D300InputValue       DisplayString
    }

b01_D300InputIndex   OBJECT-TYPE
    SYNTAX           INTEGER(0..2147483647)
    ACCESS           read-only
    STATUS           mandatory
    DESCRIPTION
    "The index in the b01_D300Input table for a particular snmp b01_D300Input
	 object.  Used to address table entries."
    ::=   { b01_D300InputTableEntry 1 }


b01_D300InputName    OBJECT-TYPE
    SYNTAX           DisplayString
    ACCESS           read-only
    STATUS           mandatory
    DESCRIPTION
    "Name of station object."
    ::=   { b01_D300InputTableEntry 2 }

b01_D300InputValue    OBJECT-TYPE
    SYNTAX           DisplayString
    ACCESS           read-write
    STATUS           mandatory
    DESCRIPTION
    "Current value of station object. Is read-write ."
    ::=   { b01_D300InputTableEntry 3 }



-- ***********************************
-- *
-- *  B01_D300Output table declarations
-- *
-- ***********************************

b01_D300OutputTable   OBJECT-TYPE
    SYNTAX                SEQUENCE OF B01_D300OutputTableEntry
    ACCESS                not-accessible
    STATUS                mandatory
    DESCRIPTION
    "A list of snmp b01_D300Output (read-only) object values."
    ::=  { b01_D300 2 }

b01_D300OutputTableEntry  OBJECT-TYPE
    SYNTAX                B01_D300OutputTableEntry
    ACCESS                not-accessible
    STATUS                mandatory
    DESCRIPTION
    "An b01_D300Output table entry containing data for a specific b01_D300Output."
    INDEX  { b01_D300OutputIndex }  ::=   { b01_D300OutputTable 1 }

B01_D300OutputTableEntry ::= SEQUENCE {
        b01_D300OutputIndex       INTEGER,
        b01_D300OutputName        DisplayString,
        b01_D300OutputValue       DisplayString
    }

b01_D300OutputIndex   OBJECT-TYPE
    SYNTAX           INTEGER(0..2147483647)
    ACCESS           read-only
    STATUS           mandatory
    DESCRIPTION
    "The index in the b01_D300Output table for a particular snmp b01_D300Output
	 object.  Used to address table entries."
    ::=   { b01_D300OutputTableEntry 1 }


b01_D300OutputName    OBJECT-TYPE
    SYNTAX           DisplayString
    ACCESS           read-only
    STATUS           mandatory
    DESCRIPTION
    "Name of station object."
    ::=   { b01_D300OutputTableEntry 2 }

b01_D300OutputValue    OBJECT-TYPE
    SYNTAX           DisplayString
    ACCESS           read-only
    STATUS           mandatory
    DESCRIPTION
    "Current value of station object. Is read-only ."
    ::=   { b01_D300OutputTableEntry 3 }


-- ***********************************
-- *
-- *  B01_D301
-- *
-- ***********************************
    b01_D301    OBJECT IDENTIFIER ::= { exportTables 6 }

-- ***********************************
-- *
-- *  B01_D301Input table declarations
-- *
-- ***********************************

b01_D301InputTable   OBJECT-TYPE
    SYNTAX                SEQUENCE OF B01_D301InputTableEntry
    ACCESS                not-accessible
    STATUS                mandatory
    DESCRIPTION
    "A list of snmp b01_D301Input (read-only) object values."
    ::=  { b01_D301 1 }

b01_D301InputTableEntry  OBJECT-TYPE
    SYNTAX                B01_D301InputTableEntry
    ACCESS                not-accessible
    STATUS                mandatory
    DESCRIPTION
    "An b01_D301Input table entry containing data for a specific b01_D301Input."
    INDEX  { b01_D301InputIndex }  ::=   { b01_D301InputTable 1 }

B01_D301InputTableEntry ::= SEQUENCE {
        b01_D301InputIndex       INTEGER,
        b01_D301InputName        DisplayString,
        b01_D301InputValue       DisplayString
    }

b01_D301InputIndex   OBJECT-TYPE
    SYNTAX           INTEGER(0..2147483647)
    ACCESS           read-only
    STATUS           mandatory
    DESCRIPTION
    "The index in the b01_D301Input table for a particular snmp b01_D301Input
	 object.  Used to address table entries."
    ::=   { b01_D301InputTableEntry 1 }


b01_D301InputName    OBJECT-TYPE
    SYNTAX           DisplayString
    ACCESS           read-only
    STATUS           mandatory
    DESCRIPTION
    "Name of station object."
    ::=   { b01_D301InputTableEntry 2 }

b01_D301InputValue    OBJECT-TYPE
    SYNTAX           DisplayString
    ACCESS           read-write
    STATUS           mandatory
    DESCRIPTION
    "Current value of station object. Is read-write ."
    ::=   { b01_D301InputTableEntry 3 }



-- ***********************************
-- *
-- *  B01_D301Output table declarations
-- *
-- ***********************************

b01_D301OutputTable   OBJECT-TYPE
    SYNTAX                SEQUENCE OF B01_D301OutputTableEntry
    ACCESS                not-accessible
    STATUS                mandatory
    DESCRIPTION
    "A list of snmp b01_D301Output (read-only) object values."
    ::=  { b01_D301 2 }

b01_D301OutputTableEntry  OBJECT-TYPE
    SYNTAX                B01_D301OutputTableEntry
    ACCESS                not-accessible
    STATUS                mandatory
    DESCRIPTION
    "An b01_D301Output table entry containing data for a specific b01_D301Output."
    INDEX  { b01_D301OutputIndex }  ::=   { b01_D301OutputTable 1 }

B01_D301OutputTableEntry ::= SEQUENCE {
        b01_D301OutputIndex       INTEGER,
        b01_D301OutputName        DisplayString,
        b01_D301OutputValue       DisplayString
    }

b01_D301OutputIndex   OBJECT-TYPE
    SYNTAX           INTEGER(0..2147483647)
    ACCESS           read-only
    STATUS           mandatory
    DESCRIPTION
    "The index in the b01_D301Output table for a particular snmp b01_D301Output
	 object.  Used to address table entries."
    ::=   { b01_D301OutputTableEntry 1 }


b01_D301OutputName    OBJECT-TYPE
    SYNTAX           DisplayString
    ACCESS           read-only
    STATUS           mandatory
    DESCRIPTION
    "Name of station object."
    ::=   { b01_D301OutputTableEntry 2 }

b01_D301OutputValue    OBJECT-TYPE
    SYNTAX           DisplayString
    ACCESS           read-only
    STATUS           mandatory
    DESCRIPTION
    "Current value of station object. Is read-only ."
    ::=   { b01_D301OutputTableEntry 3 }


-- ***********************************
-- *
-- *  B01_D302
-- *
-- ***********************************
    b01_D302    OBJECT IDENTIFIER ::= { exportTables 7 }

-- ***********************************
-- *
-- *  B01_D302Input table declarations
-- *
-- ***********************************

b01_D302InputTable   OBJECT-TYPE
    SYNTAX                SEQUENCE OF B01_D302InputTableEntry
    ACCESS                not-accessible
    STATUS                mandatory
    DESCRIPTION
    "A list of snmp b01_D302Input (read-only) object values."
    ::=  { b01_D302 1 }

b01_D302InputTableEntry  OBJECT-TYPE
    SYNTAX                B01_D302InputTableEntry
    ACCESS                not-accessible
    STATUS                mandatory
    DESCRIPTION
    "An b01_D302Input table entry containing data for a specific b01_D302Input."
    INDEX  { b01_D302InputIndex }  ::=   { b01_D302InputTable 1 }

B01_D302InputTableEntry ::= SEQUENCE {
        b01_D302InputIndex       INTEGER,
        b01_D302InputName        DisplayString,
        b01_D302InputValue       DisplayString
    }

b01_D302InputIndex   OBJECT-TYPE
    SYNTAX           INTEGER(0..2147483647)
    ACCESS           read-only
    STATUS           mandatory
    DESCRIPTION
    "The index in the b01_D302Input table for a particular snmp b01_D302Input
	 object.  Used to address table entries."
    ::=   { b01_D302InputTableEntry 1 }


b01_D302InputName    OBJECT-TYPE
    SYNTAX           DisplayString
    ACCESS           read-only
    STATUS           mandatory
    DESCRIPTION
    "Name of station object."
    ::=   { b01_D302InputTableEntry 2 }

b01_D302InputValue    OBJECT-TYPE
    SYNTAX           DisplayString
    ACCESS           read-write
    STATUS           mandatory
    DESCRIPTION
    "Current value of station object. Is read-write ."
    ::=   { b01_D302InputTableEntry 3 }



-- ***********************************
-- *
-- *  B01_D302Output table declarations
-- *
-- ***********************************

b01_D302OutputTable   OBJECT-TYPE
    SYNTAX                SEQUENCE OF B01_D302OutputTableEntry
    ACCESS                not-accessible
    STATUS                mandatory
    DESCRIPTION
    "A list of snmp b01_D302Output (read-only) object values."
    ::=  { b01_D302 2 }

b01_D302OutputTableEntry  OBJECT-TYPE
    SYNTAX                B01_D302OutputTableEntry
    ACCESS                not-accessible
    STATUS                mandatory
    DESCRIPTION
    "An b01_D302Output table entry containing data for a specific b01_D302Output."
    INDEX  { b01_D302OutputIndex }  ::=   { b01_D302OutputTable 1 }

B01_D302OutputTableEntry ::= SEQUENCE {
        b01_D302OutputIndex       INTEGER,
        b01_D302OutputName        DisplayString,
        b01_D302OutputValue       DisplayString
    }

b01_D302OutputIndex   OBJECT-TYPE
    SYNTAX           INTEGER(0..2147483647)
    ACCESS           read-only
    STATUS           mandatory
    DESCRIPTION
    "The index in the b01_D302Output table for a particular snmp b01_D302Output
	 object.  Used to address table entries."
    ::=   { b01_D302OutputTableEntry 1 }


b01_D302OutputName    OBJECT-TYPE
    SYNTAX           DisplayString
    ACCESS           read-only
    STATUS           mandatory
    DESCRIPTION
    "Name of station object."
    ::=   { b01_D302OutputTableEntry 2 }

b01_D302OutputValue    OBJECT-TYPE
    SYNTAX           DisplayString
    ACCESS           read-only
    STATUS           mandatory
    DESCRIPTION
    "Current value of station object. Is read-only ."
    ::=   { b01_D302OutputTableEntry 3 }


-- ***********************************
-- *
-- *  B01_D304
-- *
-- ***********************************
    b01_D304    OBJECT IDENTIFIER ::= { exportTables 8 }

-- ***********************************
-- *
-- *  B01_D304Input table declarations
-- *
-- ***********************************

b01_D304InputTable   OBJECT-TYPE
    SYNTAX                SEQUENCE OF B01_D304InputTableEntry
    ACCESS                not-accessible
    STATUS                mandatory
    DESCRIPTION
    "A list of snmp b01_D304Input (read-only) object values."
    ::=  { b01_D304 1 }

b01_D304InputTableEntry  OBJECT-TYPE
    SYNTAX                B01_D304InputTableEntry
    ACCESS                not-accessible
    STATUS                mandatory
    DESCRIPTION
    "An b01_D304Input table entry containing data for a specific b01_D304Input."
    INDEX  { b01_D304InputIndex }  ::=   { b01_D304InputTable 1 }

B01_D304InputTableEntry ::= SEQUENCE {
        b01_D304InputIndex       INTEGER,
        b01_D304InputName        DisplayString,
        b01_D304InputValue       DisplayString
    }

b01_D304InputIndex   OBJECT-TYPE
    SYNTAX           INTEGER(0..2147483647)
    ACCESS           read-only
    STATUS           mandatory
    DESCRIPTION
    "The index in the b01_D304Input table for a particular snmp b01_D304Input
	 object.  Used to address table entries."
    ::=   { b01_D304InputTableEntry 1 }


b01_D304InputName    OBJECT-TYPE
    SYNTAX           DisplayString
    ACCESS           read-only
    STATUS           mandatory
    DESCRIPTION
    "Name of station object."
    ::=   { b01_D304InputTableEntry 2 }

b01_D304InputValue    OBJECT-TYPE
    SYNTAX           DisplayString
    ACCESS           read-write
    STATUS           mandatory
    DESCRIPTION
    "Current value of station object. Is read-write ."
    ::=   { b01_D304InputTableEntry 3 }



-- ***********************************
-- *
-- *  B01_D304Output table declarations
-- *
-- ***********************************

b01_D304OutputTable   OBJECT-TYPE
    SYNTAX                SEQUENCE OF B01_D304OutputTableEntry
    ACCESS                not-accessible
    STATUS                mandatory
    DESCRIPTION
    "A list of snmp b01_D304Output (read-only) object values."
    ::=  { b01_D304 2 }

b01_D304OutputTableEntry  OBJECT-TYPE
    SYNTAX                B01_D304OutputTableEntry
    ACCESS                not-accessible
    STATUS                mandatory
    DESCRIPTION
    "An b01_D304Output table entry containing data for a specific b01_D304Output."
    INDEX  { b01_D304OutputIndex }  ::=   { b01_D304OutputTable 1 }

B01_D304OutputTableEntry ::= SEQUENCE {
        b01_D304OutputIndex       INTEGER,
        b01_D304OutputName        DisplayString,
        b01_D304OutputValue       DisplayString
    }

b01_D304OutputIndex   OBJECT-TYPE
    SYNTAX           INTEGER(0..2147483647)
    ACCESS           read-only
    STATUS           mandatory
    DESCRIPTION
    "The index in the b01_D304Output table for a particular snmp b01_D304Output
	 object.  Used to address table entries."
    ::=   { b01_D304OutputTableEntry 1 }


b01_D304OutputName    OBJECT-TYPE
    SYNTAX           DisplayString
    ACCESS           read-only
    STATUS           mandatory
    DESCRIPTION
    "Name of station object."
    ::=   { b01_D304OutputTableEntry 2 }

b01_D304OutputValue    OBJECT-TYPE
    SYNTAX           DisplayString
    ACCESS           read-only
    STATUS           mandatory
    DESCRIPTION
    "Current value of station object. Is read-only ."
    ::=   { b01_D304OutputTableEntry 3 }


-- ***********************************
-- *
-- *  B01_D305
-- *
-- ***********************************
    b01_D305    OBJECT IDENTIFIER ::= { exportTables 9 }

-- ***********************************
-- *
-- *  B01_D305Input table declarations
-- *
-- ***********************************

b01_D305InputTable   OBJECT-TYPE
    SYNTAX                SEQUENCE OF B01_D305InputTableEntry
    ACCESS                not-accessible
    STATUS                mandatory
    DESCRIPTION
    "A list of snmp b01_D305Input (read-only) object values."
    ::=  { b01_D305 1 }

b01_D305InputTableEntry  OBJECT-TYPE
    SYNTAX                B01_D305InputTableEntry
    ACCESS                not-accessible
    STATUS                mandatory
    DESCRIPTION
    "An b01_D305Input table entry containing data for a specific b01_D305Input."
    INDEX  { b01_D305InputIndex }  ::=   { b01_D305InputTable 1 }

B01_D305InputTableEntry ::= SEQUENCE {
        b01_D305InputIndex       INTEGER,
        b01_D305InputName        DisplayString,
        b01_D305InputValue       DisplayString
    }

b01_D305InputIndex   OBJECT-TYPE
    SYNTAX           INTEGER(0..2147483647)
    ACCESS           read-only
    STATUS           mandatory
    DESCRIPTION
    "The index in the b01_D305Input table for a particular snmp b01_D305Input
	 object.  Used to address table entries."
    ::=   { b01_D305InputTableEntry 1 }


b01_D305InputName    OBJECT-TYPE
    SYNTAX           DisplayString
    ACCESS           read-only
    STATUS           mandatory
    DESCRIPTION
    "Name of station object."
    ::=   { b01_D305InputTableEntry 2 }

b01_D305InputValue    OBJECT-TYPE
    SYNTAX           DisplayString
    ACCESS           read-write
    STATUS           mandatory
    DESCRIPTION
    "Current value of station object. Is read-write ."
    ::=   { b01_D305InputTableEntry 3 }



-- ***********************************
-- *
-- *  B01_D305Output table declarations
-- *
-- ***********************************

b01_D305OutputTable   OBJECT-TYPE
    SYNTAX                SEQUENCE OF B01_D305OutputTableEntry
    ACCESS                not-accessible
    STATUS                mandatory
    DESCRIPTION
    "A list of snmp b01_D305Output (read-only) object values."
    ::=  { b01_D305 2 }

b01_D305OutputTableEntry  OBJECT-TYPE
    SYNTAX                B01_D305OutputTableEntry
    ACCESS                not-accessible
    STATUS                mandatory
    DESCRIPTION
    "An b01_D305Output table entry containing data for a specific b01_D305Output."
    INDEX  { b01_D305OutputIndex }  ::=   { b01_D305OutputTable 1 }

B01_D305OutputTableEntry ::= SEQUENCE {
        b01_D305OutputIndex       INTEGER,
        b01_D305OutputName        DisplayString,
        b01_D305OutputValue       DisplayString
    }

b01_D305OutputIndex   OBJECT-TYPE
    SYNTAX           INTEGER(0..2147483647)
    ACCESS           read-only
    STATUS           mandatory
    DESCRIPTION
    "The index in the b01_D305Output table for a particular snmp b01_D305Output
	 object.  Used to address table entries."
    ::=   { b01_D305OutputTableEntry 1 }


b01_D305OutputName    OBJECT-TYPE
    SYNTAX           DisplayString
    ACCESS           read-only
    STATUS           mandatory
    DESCRIPTION
    "Name of station object."
    ::=   { b01_D305OutputTableEntry 2 }

b01_D305OutputValue    OBJECT-TYPE
    SYNTAX           DisplayString
    ACCESS           read-only
    STATUS           mandatory
    DESCRIPTION
    "Current value of station object. Is read-only ."
    ::=   { b01_D305OutputTableEntry 3 }


-- ***********************************
-- *
-- *  B01_D306
-- *
-- ***********************************
    b01_D306    OBJECT IDENTIFIER ::= { exportTables 10 }

-- ***********************************
-- *
-- *  B01_D306Input table declarations
-- *
-- ***********************************

b01_D306InputTable   OBJECT-TYPE
    SYNTAX                SEQUENCE OF B01_D306InputTableEntry
    ACCESS                not-accessible
    STATUS                mandatory
    DESCRIPTION
    "A list of snmp b01_D306Input (read-only) object values."
    ::=  { b01_D306 1 }

b01_D306InputTableEntry  OBJECT-TYPE
    SYNTAX                B01_D306InputTableEntry
    ACCESS                not-accessible
    STATUS                mandatory
    DESCRIPTION
    "An b01_D306Input table entry containing data for a specific b01_D306Input."
    INDEX  { b01_D306InputIndex }  ::=   { b01_D306InputTable 1 }

B01_D306InputTableEntry ::= SEQUENCE {
        b01_D306InputIndex       INTEGER,
        b01_D306InputName        DisplayString,
        b01_D306InputValue       DisplayString
    }

b01_D306InputIndex   OBJECT-TYPE
    SYNTAX           INTEGER(0..2147483647)
    ACCESS           read-only
    STATUS           mandatory
    DESCRIPTION
    "The index in the b01_D306Input table for a particular snmp b01_D306Input
	 object.  Used to address table entries."
    ::=   { b01_D306InputTableEntry 1 }


b01_D306InputName    OBJECT-TYPE
    SYNTAX           DisplayString
    ACCESS           read-only
    STATUS           mandatory
    DESCRIPTION
    "Name of station object."
    ::=   { b01_D306InputTableEntry 2 }

b01_D306InputValue    OBJECT-TYPE
    SYNTAX           DisplayString
    ACCESS           read-write
    STATUS           mandatory
    DESCRIPTION
    "Current value of station object. Is read-write ."
    ::=   { b01_D306InputTableEntry 3 }



-- ***********************************
-- *
-- *  B01_D306Output table declarations
-- *
-- ***********************************

b01_D306OutputTable   OBJECT-TYPE
    SYNTAX                SEQUENCE OF B01_D306OutputTableEntry
    ACCESS                not-accessible
    STATUS                mandatory
    DESCRIPTION
    "A list of snmp b01_D306Output (read-only) object values."
    ::=  { b01_D306 2 }

b01_D306OutputTableEntry  OBJECT-TYPE
    SYNTAX                B01_D306OutputTableEntry
    ACCESS                not-accessible
    STATUS                mandatory
    DESCRIPTION
    "An b01_D306Output table entry containing data for a specific b01_D306Output."
    INDEX  { b01_D306OutputIndex }  ::=   { b01_D306OutputTable 1 }

B01_D306OutputTableEntry ::= SEQUENCE {
        b01_D306OutputIndex       INTEGER,
        b01_D306OutputName        DisplayString,
        b01_D306OutputValue       DisplayString
    }

b01_D306OutputIndex   OBJECT-TYPE
    SYNTAX           INTEGER(0..2147483647)
    ACCESS           read-only
    STATUS           mandatory
    DESCRIPTION
    "The index in the b01_D306Output table for a particular snmp b01_D306Output
	 object.  Used to address table entries."
    ::=   { b01_D306OutputTableEntry 1 }


b01_D306OutputName    OBJECT-TYPE
    SYNTAX           DisplayString
    ACCESS           read-only
    STATUS           mandatory
    DESCRIPTION
    "Name of station object."
    ::=   { b01_D306OutputTableEntry 2 }

b01_D306OutputValue    OBJECT-TYPE
    SYNTAX           DisplayString
    ACCESS           read-only
    STATUS           mandatory
    DESCRIPTION
    "Current value of station object. Is read-only ."
    ::=   { b01_D306OutputTableEntry 3 }


-- ***********************************
-- *
-- *  B01_D307
-- *
-- ***********************************
    b01_D307    OBJECT IDENTIFIER ::= { exportTables 11 }

-- ***********************************
-- *
-- *  B01_D307Input table declarations
-- *
-- ***********************************

b01_D307InputTable   OBJECT-TYPE
    SYNTAX                SEQUENCE OF B01_D307InputTableEntry
    ACCESS                not-accessible
    STATUS                mandatory
    DESCRIPTION
    "A list of snmp b01_D307Input (read-only) object values."
    ::=  { b01_D307 1 }

b01_D307InputTableEntry  OBJECT-TYPE
    SYNTAX                B01_D307InputTableEntry
    ACCESS                not-accessible
    STATUS                mandatory
    DESCRIPTION
    "An b01_D307Input table entry containing data for a specific b01_D307Input."
    INDEX  { b01_D307InputIndex }  ::=   { b01_D307InputTable 1 }

B01_D307InputTableEntry ::= SEQUENCE {
        b01_D307InputIndex       INTEGER,
        b01_D307InputName        DisplayString,
        b01_D307InputValue       DisplayString
    }

b01_D307InputIndex   OBJECT-TYPE
    SYNTAX           INTEGER(0..2147483647)
    ACCESS           read-only
    STATUS           mandatory
    DESCRIPTION
    "The index in the b01_D307Input table for a particular snmp b01_D307Input
	 object.  Used to address table entries."
    ::=   { b01_D307InputTableEntry 1 }


b01_D307InputName    OBJECT-TYPE
    SYNTAX           DisplayString
    ACCESS           read-only
    STATUS           mandatory
    DESCRIPTION
    "Name of station object."
    ::=   { b01_D307InputTableEntry 2 }

b01_D307InputValue    OBJECT-TYPE
    SYNTAX           DisplayString
    ACCESS           read-write
    STATUS           mandatory
    DESCRIPTION
    "Current value of station object. Is read-write ."
    ::=   { b01_D307InputTableEntry 3 }



-- ***********************************
-- *
-- *  B01_D307Output table declarations
-- *
-- ***********************************

b01_D307OutputTable   OBJECT-TYPE
    SYNTAX                SEQUENCE OF B01_D307OutputTableEntry
    ACCESS                not-accessible
    STATUS                mandatory
    DESCRIPTION
    "A list of snmp b01_D307Output (read-only) object values."
    ::=  { b01_D307 2 }

b01_D307OutputTableEntry  OBJECT-TYPE
    SYNTAX                B01_D307OutputTableEntry
    ACCESS                not-accessible
    STATUS                mandatory
    DESCRIPTION
    "An b01_D307Output table entry containing data for a specific b01_D307Output."
    INDEX  { b01_D307OutputIndex }  ::=   { b01_D307OutputTable 1 }

B01_D307OutputTableEntry ::= SEQUENCE {
        b01_D307OutputIndex       INTEGER,
        b01_D307OutputName        DisplayString,
        b01_D307OutputValue       DisplayString
    }

b01_D307OutputIndex   OBJECT-TYPE
    SYNTAX           INTEGER(0..2147483647)
    ACCESS           read-only
    STATUS           mandatory
    DESCRIPTION
    "The index in the b01_D307Output table for a particular snmp b01_D307Output
	 object.  Used to address table entries."
    ::=   { b01_D307OutputTableEntry 1 }


b01_D307OutputName    OBJECT-TYPE
    SYNTAX           DisplayString
    ACCESS           read-only
    STATUS           mandatory
    DESCRIPTION
    "Name of station object."
    ::=   { b01_D307OutputTableEntry 2 }

b01_D307OutputValue    OBJECT-TYPE
    SYNTAX           DisplayString
    ACCESS           read-only
    STATUS           mandatory
    DESCRIPTION
    "Current value of station object. Is read-only ."
    ::=   { b01_D307OutputTableEntry 3 }


-- ***********************************
-- *
-- *  B01_D308
-- *
-- ***********************************
    b01_D308    OBJECT IDENTIFIER ::= { exportTables 12 }

-- ***********************************
-- *
-- *  B01_D308Input table declarations
-- *
-- ***********************************

b01_D308InputTable   OBJECT-TYPE
    SYNTAX                SEQUENCE OF B01_D308InputTableEntry
    ACCESS                not-accessible
    STATUS                mandatory
    DESCRIPTION
    "A list of snmp b01_D308Input (read-only) object values."
    ::=  { b01_D308 1 }

b01_D308InputTableEntry  OBJECT-TYPE
    SYNTAX                B01_D308InputTableEntry
    ACCESS                not-accessible
    STATUS                mandatory
    DESCRIPTION
    "An b01_D308Input table entry containing data for a specific b01_D308Input."
    INDEX  { b01_D308InputIndex }  ::=   { b01_D308InputTable 1 }

B01_D308InputTableEntry ::= SEQUENCE {
        b01_D308InputIndex       INTEGER,
        b01_D308InputName        DisplayString,
        b01_D308InputValue       DisplayString
    }

b01_D308InputIndex   OBJECT-TYPE
    SYNTAX           INTEGER(0..2147483647)
    ACCESS           read-only
    STATUS           mandatory
    DESCRIPTION
    "The index in the b01_D308Input table for a particular snmp b01_D308Input
	 object.  Used to address table entries."
    ::=   { b01_D308InputTableEntry 1 }


b01_D308InputName    OBJECT-TYPE
    SYNTAX           DisplayString
    ACCESS           read-only
    STATUS           mandatory
    DESCRIPTION
    "Name of station object."
    ::=   { b01_D308InputTableEntry 2 }

b01_D308InputValue    OBJECT-TYPE
    SYNTAX           DisplayString
    ACCESS           read-write
    STATUS           mandatory
    DESCRIPTION
    "Current value of station object. Is read-write ."
    ::=   { b01_D308InputTableEntry 3 }



-- ***********************************
-- *
-- *  B01_D308Output table declarations
-- *
-- ***********************************

b01_D308OutputTable   OBJECT-TYPE
    SYNTAX                SEQUENCE OF B01_D308OutputTableEntry
    ACCESS                not-accessible
    STATUS                mandatory
    DESCRIPTION
    "A list of snmp b01_D308Output (read-only) object values."
    ::=  { b01_D308 2 }

b01_D308OutputTableEntry  OBJECT-TYPE
    SYNTAX                B01_D308OutputTableEntry
    ACCESS                not-accessible
    STATUS                mandatory
    DESCRIPTION
    "An b01_D308Output table entry containing data for a specific b01_D308Output."
    INDEX  { b01_D308OutputIndex }  ::=   { b01_D308OutputTable 1 }

B01_D308OutputTableEntry ::= SEQUENCE {
        b01_D308OutputIndex       INTEGER,
        b01_D308OutputName        DisplayString,
        b01_D308OutputValue       DisplayString
    }

b01_D308OutputIndex   OBJECT-TYPE
    SYNTAX           INTEGER(0..2147483647)
    ACCESS           read-only
    STATUS           mandatory
    DESCRIPTION
    "The index in the b01_D308Output table for a particular snmp b01_D308Output
	 object.  Used to address table entries."
    ::=   { b01_D308OutputTableEntry 1 }


b01_D308OutputName    OBJECT-TYPE
    SYNTAX           DisplayString
    ACCESS           read-only
    STATUS           mandatory
    DESCRIPTION
    "Name of station object."
    ::=   { b01_D308OutputTableEntry 2 }

b01_D308OutputValue    OBJECT-TYPE
    SYNTAX           DisplayString
    ACCESS           read-only
    STATUS           mandatory
    DESCRIPTION
    "Current value of station object. Is read-only ."
    ::=   { b01_D308OutputTableEntry 3 }


-- ***********************************
-- *
-- *  B01_D309
-- *
-- ***********************************
    b01_D309    OBJECT IDENTIFIER ::= { exportTables 13 }

-- ***********************************
-- *
-- *  B01_D309Input table declarations
-- *
-- ***********************************

b01_D309InputTable   OBJECT-TYPE
    SYNTAX                SEQUENCE OF B01_D309InputTableEntry
    ACCESS                not-accessible
    STATUS                mandatory
    DESCRIPTION
    "A list of snmp b01_D309Input (read-only) object values."
    ::=  { b01_D309 1 }

b01_D309InputTableEntry  OBJECT-TYPE
    SYNTAX                B01_D309InputTableEntry
    ACCESS                not-accessible
    STATUS                mandatory
    DESCRIPTION
    "An b01_D309Input table entry containing data for a specific b01_D309Input."
    INDEX  { b01_D309InputIndex }  ::=   { b01_D309InputTable 1 }

B01_D309InputTableEntry ::= SEQUENCE {
        b01_D309InputIndex       INTEGER,
        b01_D309InputName        DisplayString,
        b01_D309InputValue       DisplayString
    }

b01_D309InputIndex   OBJECT-TYPE
    SYNTAX           INTEGER(0..2147483647)
    ACCESS           read-only
    STATUS           mandatory
    DESCRIPTION
    "The index in the b01_D309Input table for a particular snmp b01_D309Input
	 object.  Used to address table entries."
    ::=   { b01_D309InputTableEntry 1 }


b01_D309InputName    OBJECT-TYPE
    SYNTAX           DisplayString
    ACCESS           read-only
    STATUS           mandatory
    DESCRIPTION
    "Name of station object."
    ::=   { b01_D309InputTableEntry 2 }

b01_D309InputValue    OBJECT-TYPE
    SYNTAX           DisplayString
    ACCESS           read-write
    STATUS           mandatory
    DESCRIPTION
    "Current value of station object. Is read-write ."
    ::=   { b01_D309InputTableEntry 3 }



-- ***********************************
-- *
-- *  B01_D309Output table declarations
-- *
-- ***********************************

b01_D309OutputTable   OBJECT-TYPE
    SYNTAX                SEQUENCE OF B01_D309OutputTableEntry
    ACCESS                not-accessible
    STATUS                mandatory
    DESCRIPTION
    "A list of snmp b01_D309Output (read-only) object values."
    ::=  { b01_D309 2 }

b01_D309OutputTableEntry  OBJECT-TYPE
    SYNTAX                B01_D309OutputTableEntry
    ACCESS                not-accessible
    STATUS                mandatory
    DESCRIPTION
    "An b01_D309Output table entry containing data for a specific b01_D309Output."
    INDEX  { b01_D309OutputIndex }  ::=   { b01_D309OutputTable 1 }

B01_D309OutputTableEntry ::= SEQUENCE {
        b01_D309OutputIndex       INTEGER,
        b01_D309OutputName        DisplayString,
        b01_D309OutputValue       DisplayString
    }

b01_D309OutputIndex   OBJECT-TYPE
    SYNTAX           INTEGER(0..2147483647)
    ACCESS           read-only
    STATUS           mandatory
    DESCRIPTION
    "The index in the b01_D309Output table for a particular snmp b01_D309Output
	 object.  Used to address table entries."
    ::=   { b01_D309OutputTableEntry 1 }


b01_D309OutputName    OBJECT-TYPE
    SYNTAX           DisplayString
    ACCESS           read-only
    STATUS           mandatory
    DESCRIPTION
    "Name of station object."
    ::=   { b01_D309OutputTableEntry 2 }

b01_D309OutputValue    OBJECT-TYPE
    SYNTAX           DisplayString
    ACCESS           read-only
    STATUS           mandatory
    DESCRIPTION
    "Current value of station object. Is read-only ."
    ::=   { b01_D309OutputTableEntry 3 }


-- ***********************************
-- *
-- *  B01_D310
-- *
-- ***********************************
    b01_D310    OBJECT IDENTIFIER ::= { exportTables 14 }

-- ***********************************
-- *
-- *  B01_D310Input table declarations
-- *
-- ***********************************

b01_D310InputTable   OBJECT-TYPE
    SYNTAX                SEQUENCE OF B01_D310InputTableEntry
    ACCESS                not-accessible
    STATUS                mandatory
    DESCRIPTION
    "A list of snmp b01_D310Input (read-only) object values."
    ::=  { b01_D310 1 }

b01_D310InputTableEntry  OBJECT-TYPE
    SYNTAX                B01_D310InputTableEntry
    ACCESS                not-accessible
    STATUS                mandatory
    DESCRIPTION
    "An b01_D310Input table entry containing data for a specific b01_D310Input."
    INDEX  { b01_D310InputIndex }  ::=   { b01_D310InputTable 1 }

B01_D310InputTableEntry ::= SEQUENCE {
        b01_D310InputIndex       INTEGER,
        b01_D310InputName        DisplayString,
        b01_D310InputValue       DisplayString
    }

b01_D310InputIndex   OBJECT-TYPE
    SYNTAX           INTEGER(0..2147483647)
    ACCESS           read-only
    STATUS           mandatory
    DESCRIPTION
    "The index in the b01_D310Input table for a particular snmp b01_D310Input
	 object.  Used to address table entries."
    ::=   { b01_D310InputTableEntry 1 }


b01_D310InputName    OBJECT-TYPE
    SYNTAX           DisplayString
    ACCESS           read-only
    STATUS           mandatory
    DESCRIPTION
    "Name of station object."
    ::=   { b01_D310InputTableEntry 2 }

b01_D310InputValue    OBJECT-TYPE
    SYNTAX           DisplayString
    ACCESS           read-write
    STATUS           mandatory
    DESCRIPTION
    "Current value of station object. Is read-write ."
    ::=   { b01_D310InputTableEntry 3 }



-- ***********************************
-- *
-- *  B01_D310Output table declarations
-- *
-- ***********************************

b01_D310OutputTable   OBJECT-TYPE
    SYNTAX                SEQUENCE OF B01_D310OutputTableEntry
    ACCESS                not-accessible
    STATUS                mandatory
    DESCRIPTION
    "A list of snmp b01_D310Output (read-only) object values."
    ::=  { b01_D310 2 }

b01_D310OutputTableEntry  OBJECT-TYPE
    SYNTAX                B01_D310OutputTableEntry
    ACCESS                not-accessible
    STATUS                mandatory
    DESCRIPTION
    "An b01_D310Output table entry containing data for a specific b01_D310Output."
    INDEX  { b01_D310OutputIndex }  ::=   { b01_D310OutputTable 1 }

B01_D310OutputTableEntry ::= SEQUENCE {
        b01_D310OutputIndex       INTEGER,
        b01_D310OutputName        DisplayString,
        b01_D310OutputValue       DisplayString
    }

b01_D310OutputIndex   OBJECT-TYPE
    SYNTAX           INTEGER(0..2147483647)
    ACCESS           read-only
    STATUS           mandatory
    DESCRIPTION
    "The index in the b01_D310Output table for a particular snmp b01_D310Output
	 object.  Used to address table entries."
    ::=   { b01_D310OutputTableEntry 1 }


b01_D310OutputName    OBJECT-TYPE
    SYNTAX           DisplayString
    ACCESS           read-only
    STATUS           mandatory
    DESCRIPTION
    "Name of station object."
    ::=   { b01_D310OutputTableEntry 2 }

b01_D310OutputValue    OBJECT-TYPE
    SYNTAX           DisplayString
    ACCESS           read-only
    STATUS           mandatory
    DESCRIPTION
    "Current value of station object. Is read-only ."
    ::=   { b01_D310OutputTableEntry 3 }


-- ***********************************
-- *
-- *  B01_D320
-- *
-- ***********************************
    b01_D320    OBJECT IDENTIFIER ::= { exportTables 15 }

-- ***********************************
-- *
-- *  B01_D320Input table declarations
-- *
-- ***********************************

b01_D320InputTable   OBJECT-TYPE
    SYNTAX                SEQUENCE OF B01_D320InputTableEntry
    ACCESS                not-accessible
    STATUS                mandatory
    DESCRIPTION
    "A list of snmp b01_D320Input (read-only) object values."
    ::=  { b01_D320 1 }

b01_D320InputTableEntry  OBJECT-TYPE
    SYNTAX                B01_D320InputTableEntry
    ACCESS                not-accessible
    STATUS                mandatory
    DESCRIPTION
    "An b01_D320Input table entry containing data for a specific b01_D320Input."
    INDEX  { b01_D320InputIndex }  ::=   { b01_D320InputTable 1 }

B01_D320InputTableEntry ::= SEQUENCE {
        b01_D320InputIndex       INTEGER,
        b01_D320InputName        DisplayString,
        b01_D320InputValue       DisplayString
    }

b01_D320InputIndex   OBJECT-TYPE
    SYNTAX           INTEGER(0..2147483647)
    ACCESS           read-only
    STATUS           mandatory
    DESCRIPTION
    "The index in the b01_D320Input table for a particular snmp b01_D320Input
	 object.  Used to address table entries."
    ::=   { b01_D320InputTableEntry 1 }


b01_D320InputName    OBJECT-TYPE
    SYNTAX           DisplayString
    ACCESS           read-only
    STATUS           mandatory
    DESCRIPTION
    "Name of station object."
    ::=   { b01_D320InputTableEntry 2 }

b01_D320InputValue    OBJECT-TYPE
    SYNTAX           DisplayString
    ACCESS           read-write
    STATUS           mandatory
    DESCRIPTION
    "Current value of station object. Is read-write ."
    ::=   { b01_D320InputTableEntry 3 }



-- ***********************************
-- *
-- *  B01_D320Output table declarations
-- *
-- ***********************************

b01_D320OutputTable   OBJECT-TYPE
    SYNTAX                SEQUENCE OF B01_D320OutputTableEntry
    ACCESS                not-accessible
    STATUS                mandatory
    DESCRIPTION
    "A list of snmp b01_D320Output (read-only) object values."
    ::=  { b01_D320 2 }

b01_D320OutputTableEntry  OBJECT-TYPE
    SYNTAX                B01_D320OutputTableEntry
    ACCESS                not-accessible
    STATUS                mandatory
    DESCRIPTION
    "An b01_D320Output table entry containing data for a specific b01_D320Output."
    INDEX  { b01_D320OutputIndex }  ::=   { b01_D320OutputTable 1 }

B01_D320OutputTableEntry ::= SEQUENCE {
        b01_D320OutputIndex       INTEGER,
        b01_D320OutputName        DisplayString,
        b01_D320OutputValue       DisplayString
    }

b01_D320OutputIndex   OBJECT-TYPE
    SYNTAX           INTEGER(0..2147483647)
    ACCESS           read-only
    STATUS           mandatory
    DESCRIPTION
    "The index in the b01_D320Output table for a particular snmp b01_D320Output
	 object.  Used to address table entries."
    ::=   { b01_D320OutputTableEntry 1 }


b01_D320OutputName    OBJECT-TYPE
    SYNTAX           DisplayString
    ACCESS           read-only
    STATUS           mandatory
    DESCRIPTION
    "Name of station object."
    ::=   { b01_D320OutputTableEntry 2 }

b01_D320OutputValue    OBJECT-TYPE
    SYNTAX           DisplayString
    ACCESS           read-only
    STATUS           mandatory
    DESCRIPTION
    "Current value of station object. Is read-only ."
    ::=   { b01_D320OutputTableEntry 3 }


-- ***********************************
-- *
-- *  B01_D321
-- *
-- ***********************************
    b01_D321    OBJECT IDENTIFIER ::= { exportTables 16 }

-- ***********************************
-- *
-- *  B01_D321Input table declarations
-- *
-- ***********************************

b01_D321InputTable   OBJECT-TYPE
    SYNTAX                SEQUENCE OF B01_D321InputTableEntry
    ACCESS                not-accessible
    STATUS                mandatory
    DESCRIPTION
    "A list of snmp b01_D321Input (read-only) object values."
    ::=  { b01_D321 1 }

b01_D321InputTableEntry  OBJECT-TYPE
    SYNTAX                B01_D321InputTableEntry
    ACCESS                not-accessible
    STATUS                mandatory
    DESCRIPTION
    "An b01_D321Input table entry containing data for a specific b01_D321Input."
    INDEX  { b01_D321InputIndex }  ::=   { b01_D321InputTable 1 }

B01_D321InputTableEntry ::= SEQUENCE {
        b01_D321InputIndex       INTEGER,
        b01_D321InputName        DisplayString,
        b01_D321InputValue       DisplayString
    }

b01_D321InputIndex   OBJECT-TYPE
    SYNTAX           INTEGER(0..2147483647)
    ACCESS           read-only
    STATUS           mandatory
    DESCRIPTION
    "The index in the b01_D321Input table for a particular snmp b01_D321Input
	 object.  Used to address table entries."
    ::=   { b01_D321InputTableEntry 1 }


b01_D321InputName    OBJECT-TYPE
    SYNTAX           DisplayString
    ACCESS           read-only
    STATUS           mandatory
    DESCRIPTION
    "Name of station object."
    ::=   { b01_D321InputTableEntry 2 }

b01_D321InputValue    OBJECT-TYPE
    SYNTAX           DisplayString
    ACCESS           read-write
    STATUS           mandatory
    DESCRIPTION
    "Current value of station object. Is read-write ."
    ::=   { b01_D321InputTableEntry 3 }



-- ***********************************
-- *
-- *  B01_D321Output table declarations
-- *
-- ***********************************

b01_D321OutputTable   OBJECT-TYPE
    SYNTAX                SEQUENCE OF B01_D321OutputTableEntry
    ACCESS                not-accessible
    STATUS                mandatory
    DESCRIPTION
    "A list of snmp b01_D321Output (read-only) object values."
    ::=  { b01_D321 2 }

b01_D321OutputTableEntry  OBJECT-TYPE
    SYNTAX                B01_D321OutputTableEntry
    ACCESS                not-accessible
    STATUS                mandatory
    DESCRIPTION
    "An b01_D321Output table entry containing data for a specific b01_D321Output."
    INDEX  { b01_D321OutputIndex }  ::=   { b01_D321OutputTable 1 }

B01_D321OutputTableEntry ::= SEQUENCE {
        b01_D321OutputIndex       INTEGER,
        b01_D321OutputName        DisplayString,
        b01_D321OutputValue       DisplayString
    }

b01_D321OutputIndex   OBJECT-TYPE
    SYNTAX           INTEGER(0..2147483647)
    ACCESS           read-only
    STATUS           mandatory
    DESCRIPTION
    "The index in the b01_D321Output table for a particular snmp b01_D321Output
	 object.  Used to address table entries."
    ::=   { b01_D321OutputTableEntry 1 }


b01_D321OutputName    OBJECT-TYPE
    SYNTAX           DisplayString
    ACCESS           read-only
    STATUS           mandatory
    DESCRIPTION
    "Name of station object."
    ::=   { b01_D321OutputTableEntry 2 }

b01_D321OutputValue    OBJECT-TYPE
    SYNTAX           DisplayString
    ACCESS           read-only
    STATUS           mandatory
    DESCRIPTION
    "Current value of station object. Is read-only ."
    ::=   { b01_D321OutputTableEntry 3 }


-- ***********************************
-- *
-- *  B01_D322
-- *
-- ***********************************
    b01_D322    OBJECT IDENTIFIER ::= { exportTables 17 }

-- ***********************************
-- *
-- *  B01_D322Input table declarations
-- *
-- ***********************************

b01_D322InputTable   OBJECT-TYPE
    SYNTAX                SEQUENCE OF B01_D322InputTableEntry
    ACCESS                not-accessible
    STATUS                mandatory
    DESCRIPTION
    "A list of snmp b01_D322Input (read-only) object values."
    ::=  { b01_D322 1 }

b01_D322InputTableEntry  OBJECT-TYPE
    SYNTAX                B01_D322InputTableEntry
    ACCESS                not-accessible
    STATUS                mandatory
    DESCRIPTION
    "An b01_D322Input table entry containing data for a specific b01_D322Input."
    INDEX  { b01_D322InputIndex }  ::=   { b01_D322InputTable 1 }

B01_D322InputTableEntry ::= SEQUENCE {
        b01_D322InputIndex       INTEGER,
        b01_D322InputName        DisplayString,
        b01_D322InputValue       DisplayString
    }

b01_D322InputIndex   OBJECT-TYPE
    SYNTAX           INTEGER(0..2147483647)
    ACCESS           read-only
    STATUS           mandatory
    DESCRIPTION
    "The index in the b01_D322Input table for a particular snmp b01_D322Input
	 object.  Used to address table entries."
    ::=   { b01_D322InputTableEntry 1 }


b01_D322InputName    OBJECT-TYPE
    SYNTAX           DisplayString
    ACCESS           read-only
    STATUS           mandatory
    DESCRIPTION
    "Name of station object."
    ::=   { b01_D322InputTableEntry 2 }

b01_D322InputValue    OBJECT-TYPE
    SYNTAX           DisplayString
    ACCESS           read-write
    STATUS           mandatory
    DESCRIPTION
    "Current value of station object. Is read-write ."
    ::=   { b01_D322InputTableEntry 3 }



-- ***********************************
-- *
-- *  B01_D322Output table declarations
-- *
-- ***********************************

b01_D322OutputTable   OBJECT-TYPE
    SYNTAX                SEQUENCE OF B01_D322OutputTableEntry
    ACCESS                not-accessible
    STATUS                mandatory
    DESCRIPTION
    "A list of snmp b01_D322Output (read-only) object values."
    ::=  { b01_D322 2 }

b01_D322OutputTableEntry  OBJECT-TYPE
    SYNTAX                B01_D322OutputTableEntry
    ACCESS                not-accessible
    STATUS                mandatory
    DESCRIPTION
    "An b01_D322Output table entry containing data for a specific b01_D322Output."
    INDEX  { b01_D322OutputIndex }  ::=   { b01_D322OutputTable 1 }

B01_D322OutputTableEntry ::= SEQUENCE {
        b01_D322OutputIndex       INTEGER,
        b01_D322OutputName        DisplayString,
        b01_D322OutputValue       DisplayString
    }

b01_D322OutputIndex   OBJECT-TYPE
    SYNTAX           INTEGER(0..2147483647)
    ACCESS           read-only
    STATUS           mandatory
    DESCRIPTION
    "The index in the b01_D322Output table for a particular snmp b01_D322Output
	 object.  Used to address table entries."
    ::=   { b01_D322OutputTableEntry 1 }


b01_D322OutputName    OBJECT-TYPE
    SYNTAX           DisplayString
    ACCESS           read-only
    STATUS           mandatory
    DESCRIPTION
    "Name of station object."
    ::=   { b01_D322OutputTableEntry 2 }

b01_D322OutputValue    OBJECT-TYPE
    SYNTAX           DisplayString
    ACCESS           read-only
    STATUS           mandatory
    DESCRIPTION
    "Current value of station object. Is read-only ."
    ::=   { b01_D322OutputTableEntry 3 }


-- ***********************************
-- *
-- *  B01_D324
-- *
-- ***********************************
    b01_D324    OBJECT IDENTIFIER ::= { exportTables 18 }

-- ***********************************
-- *
-- *  B01_D324Input table declarations
-- *
-- ***********************************

b01_D324InputTable   OBJECT-TYPE
    SYNTAX                SEQUENCE OF B01_D324InputTableEntry
    ACCESS                not-accessible
    STATUS                mandatory
    DESCRIPTION
    "A list of snmp b01_D324Input (read-only) object values."
    ::=  { b01_D324 1 }

b01_D324InputTableEntry  OBJECT-TYPE
    SYNTAX                B01_D324InputTableEntry
    ACCESS                not-accessible
    STATUS                mandatory
    DESCRIPTION
    "An b01_D324Input table entry containing data for a specific b01_D324Input."
    INDEX  { b01_D324InputIndex }  ::=   { b01_D324InputTable 1 }

B01_D324InputTableEntry ::= SEQUENCE {
        b01_D324InputIndex       INTEGER,
        b01_D324InputName        DisplayString,
        b01_D324InputValue       DisplayString
    }

b01_D324InputIndex   OBJECT-TYPE
    SYNTAX           INTEGER(0..2147483647)
    ACCESS           read-only
    STATUS           mandatory
    DESCRIPTION
    "The index in the b01_D324Input table for a particular snmp b01_D324Input
	 object.  Used to address table entries."
    ::=   { b01_D324InputTableEntry 1 }


b01_D324InputName    OBJECT-TYPE
    SYNTAX           DisplayString
    ACCESS           read-only
    STATUS           mandatory
    DESCRIPTION
    "Name of station object."
    ::=   { b01_D324InputTableEntry 2 }

b01_D324InputValue    OBJECT-TYPE
    SYNTAX           DisplayString
    ACCESS           read-write
    STATUS           mandatory
    DESCRIPTION
    "Current value of station object. Is read-write ."
    ::=   { b01_D324InputTableEntry 3 }



-- ***********************************
-- *
-- *  B01_D324Output table declarations
-- *
-- ***********************************

b01_D324OutputTable   OBJECT-TYPE
    SYNTAX                SEQUENCE OF B01_D324OutputTableEntry
    ACCESS                not-accessible
    STATUS                mandatory
    DESCRIPTION
    "A list of snmp b01_D324Output (read-only) object values."
    ::=  { b01_D324 2 }

b01_D324OutputTableEntry  OBJECT-TYPE
    SYNTAX                B01_D324OutputTableEntry
    ACCESS                not-accessible
    STATUS                mandatory
    DESCRIPTION
    "An b01_D324Output table entry containing data for a specific b01_D324Output."
    INDEX  { b01_D324OutputIndex }  ::=   { b01_D324OutputTable 1 }

B01_D324OutputTableEntry ::= SEQUENCE {
        b01_D324OutputIndex       INTEGER,
        b01_D324OutputName        DisplayString,
        b01_D324OutputValue       DisplayString
    }

b01_D324OutputIndex   OBJECT-TYPE
    SYNTAX           INTEGER(0..2147483647)
    ACCESS           read-only
    STATUS           mandatory
    DESCRIPTION
    "The index in the b01_D324Output table for a particular snmp b01_D324Output
	 object.  Used to address table entries."
    ::=   { b01_D324OutputTableEntry 1 }


b01_D324OutputName    OBJECT-TYPE
    SYNTAX           DisplayString
    ACCESS           read-only
    STATUS           mandatory
    DESCRIPTION
    "Name of station object."
    ::=   { b01_D324OutputTableEntry 2 }

b01_D324OutputValue    OBJECT-TYPE
    SYNTAX           DisplayString
    ACCESS           read-only
    STATUS           mandatory
    DESCRIPTION
    "Current value of station object. Is read-only ."
    ::=   { b01_D324OutputTableEntry 3 }


-- ***********************************
-- *
-- *  B01_D325
-- *
-- ***********************************
    b01_D325    OBJECT IDENTIFIER ::= { exportTables 19 }

-- ***********************************
-- *
-- *  B01_D325Input table declarations
-- *
-- ***********************************

b01_D325InputTable   OBJECT-TYPE
    SYNTAX                SEQUENCE OF B01_D325InputTableEntry
    ACCESS                not-accessible
    STATUS                mandatory
    DESCRIPTION
    "A list of snmp b01_D325Input (read-only) object values."
    ::=  { b01_D325 1 }

b01_D325InputTableEntry  OBJECT-TYPE
    SYNTAX                B01_D325InputTableEntry
    ACCESS                not-accessible
    STATUS                mandatory
    DESCRIPTION
    "An b01_D325Input table entry containing data for a specific b01_D325Input."
    INDEX  { b01_D325InputIndex }  ::=   { b01_D325InputTable 1 }

B01_D325InputTableEntry ::= SEQUENCE {
        b01_D325InputIndex       INTEGER,
        b01_D325InputName        DisplayString,
        b01_D325InputValue       DisplayString
    }

b01_D325InputIndex   OBJECT-TYPE
    SYNTAX           INTEGER(0..2147483647)
    ACCESS           read-only
    STATUS           mandatory
    DESCRIPTION
    "The index in the b01_D325Input table for a particular snmp b01_D325Input
	 object.  Used to address table entries."
    ::=   { b01_D325InputTableEntry 1 }


b01_D325InputName    OBJECT-TYPE
    SYNTAX           DisplayString
    ACCESS           read-only
    STATUS           mandatory
    DESCRIPTION
    "Name of station object."
    ::=   { b01_D325InputTableEntry 2 }

b01_D325InputValue    OBJECT-TYPE
    SYNTAX           DisplayString
    ACCESS           read-write
    STATUS           mandatory
    DESCRIPTION
    "Current value of station object. Is read-write ."
    ::=   { b01_D325InputTableEntry 3 }



-- ***********************************
-- *
-- *  B01_D325Output table declarations
-- *
-- ***********************************

b01_D325OutputTable   OBJECT-TYPE
    SYNTAX                SEQUENCE OF B01_D325OutputTableEntry
    ACCESS                not-accessible
    STATUS                mandatory
    DESCRIPTION
    "A list of snmp b01_D325Output (read-only) object values."
    ::=  { b01_D325 2 }

b01_D325OutputTableEntry  OBJECT-TYPE
    SYNTAX                B01_D325OutputTableEntry
    ACCESS                not-accessible
    STATUS                mandatory
    DESCRIPTION
    "An b01_D325Output table entry containing data for a specific b01_D325Output."
    INDEX  { b01_D325OutputIndex }  ::=   { b01_D325OutputTable 1 }

B01_D325OutputTableEntry ::= SEQUENCE {
        b01_D325OutputIndex       INTEGER,
        b01_D325OutputName        DisplayString,
        b01_D325OutputValue       DisplayString
    }

b01_D325OutputIndex   OBJECT-TYPE
    SYNTAX           INTEGER(0..2147483647)
    ACCESS           read-only
    STATUS           mandatory
    DESCRIPTION
    "The index in the b01_D325Output table for a particular snmp b01_D325Output
	 object.  Used to address table entries."
    ::=   { b01_D325OutputTableEntry 1 }


b01_D325OutputName    OBJECT-TYPE
    SYNTAX           DisplayString
    ACCESS           read-only
    STATUS           mandatory
    DESCRIPTION
    "Name of station object."
    ::=   { b01_D325OutputTableEntry 2 }

b01_D325OutputValue    OBJECT-TYPE
    SYNTAX           DisplayString
    ACCESS           read-only
    STATUS           mandatory
    DESCRIPTION
    "Current value of station object. Is read-only ."
    ::=   { b01_D325OutputTableEntry 3 }


-- ***********************************
-- *
-- *  B01_D326
-- *
-- ***********************************
    b01_D326    OBJECT IDENTIFIER ::= { exportTables 20 }

-- ***********************************
-- *
-- *  B01_D326Input table declarations
-- *
-- ***********************************

b01_D326InputTable   OBJECT-TYPE
    SYNTAX                SEQUENCE OF B01_D326InputTableEntry
    ACCESS                not-accessible
    STATUS                mandatory
    DESCRIPTION
    "A list of snmp b01_D326Input (read-only) object values."
    ::=  { b01_D326 1 }

b01_D326InputTableEntry  OBJECT-TYPE
    SYNTAX                B01_D326InputTableEntry
    ACCESS                not-accessible
    STATUS                mandatory
    DESCRIPTION
    "An b01_D326Input table entry containing data for a specific b01_D326Input."
    INDEX  { b01_D326InputIndex }  ::=   { b01_D326InputTable 1 }

B01_D326InputTableEntry ::= SEQUENCE {
        b01_D326InputIndex       INTEGER,
        b01_D326InputName        DisplayString,
        b01_D326InputValue       DisplayString
    }

b01_D326InputIndex   OBJECT-TYPE
    SYNTAX           INTEGER(0..2147483647)
    ACCESS           read-only
    STATUS           mandatory
    DESCRIPTION
    "The index in the b01_D326Input table for a particular snmp b01_D326Input
	 object.  Used to address table entries."
    ::=   { b01_D326InputTableEntry 1 }


b01_D326InputName    OBJECT-TYPE
    SYNTAX           DisplayString
    ACCESS           read-only
    STATUS           mandatory
    DESCRIPTION
    "Name of station object."
    ::=   { b01_D326InputTableEntry 2 }

b01_D326InputValue    OBJECT-TYPE
    SYNTAX           DisplayString
    ACCESS           read-write
    STATUS           mandatory
    DESCRIPTION
    "Current value of station object. Is read-write ."
    ::=   { b01_D326InputTableEntry 3 }



-- ***********************************
-- *
-- *  B01_D326Output table declarations
-- *
-- ***********************************

b01_D326OutputTable   OBJECT-TYPE
    SYNTAX                SEQUENCE OF B01_D326OutputTableEntry
    ACCESS                not-accessible
    STATUS                mandatory
    DESCRIPTION
    "A list of snmp b01_D326Output (read-only) object values."
    ::=  { b01_D326 2 }

b01_D326OutputTableEntry  OBJECT-TYPE
    SYNTAX                B01_D326OutputTableEntry
    ACCESS                not-accessible
    STATUS                mandatory
    DESCRIPTION
    "An b01_D326Output table entry containing data for a specific b01_D326Output."
    INDEX  { b01_D326OutputIndex }  ::=   { b01_D326OutputTable 1 }

B01_D326OutputTableEntry ::= SEQUENCE {
        b01_D326OutputIndex       INTEGER,
        b01_D326OutputName        DisplayString,
        b01_D326OutputValue       DisplayString
    }

b01_D326OutputIndex   OBJECT-TYPE
    SYNTAX           INTEGER(0..2147483647)
    ACCESS           read-only
    STATUS           mandatory
    DESCRIPTION
    "The index in the b01_D326Output table for a particular snmp b01_D326Output
	 object.  Used to address table entries."
    ::=   { b01_D326OutputTableEntry 1 }


b01_D326OutputName    OBJECT-TYPE
    SYNTAX           DisplayString
    ACCESS           read-only
    STATUS           mandatory
    DESCRIPTION
    "Name of station object."
    ::=   { b01_D326OutputTableEntry 2 }

b01_D326OutputValue    OBJECT-TYPE
    SYNTAX           DisplayString
    ACCESS           read-only
    STATUS           mandatory
    DESCRIPTION
    "Current value of station object. Is read-only ."
    ::=   { b01_D326OutputTableEntry 3 }


-- ***********************************
-- *
-- *  B01_D327
-- *
-- ***********************************
    b01_D327    OBJECT IDENTIFIER ::= { exportTables 21 }

-- ***********************************
-- *
-- *  B01_D327Input table declarations
-- *
-- ***********************************

b01_D327InputTable   OBJECT-TYPE
    SYNTAX                SEQUENCE OF B01_D327InputTableEntry
    ACCESS                not-accessible
    STATUS                mandatory
    DESCRIPTION
    "A list of snmp b01_D327Input (read-only) object values."
    ::=  { b01_D327 1 }

b01_D327InputTableEntry  OBJECT-TYPE
    SYNTAX                B01_D327InputTableEntry
    ACCESS                not-accessible
    STATUS                mandatory
    DESCRIPTION
    "An b01_D327Input table entry containing data for a specific b01_D327Input."
    INDEX  { b01_D327InputIndex }  ::=   { b01_D327InputTable 1 }

B01_D327InputTableEntry ::= SEQUENCE {
        b01_D327InputIndex       INTEGER,
        b01_D327InputName        DisplayString,
        b01_D327InputValue       DisplayString
    }

b01_D327InputIndex   OBJECT-TYPE
    SYNTAX           INTEGER(0..2147483647)
    ACCESS           read-only
    STATUS           mandatory
    DESCRIPTION
    "The index in the b01_D327Input table for a particular snmp b01_D327Input
	 object.  Used to address table entries."
    ::=   { b01_D327InputTableEntry 1 }


b01_D327InputName    OBJECT-TYPE
    SYNTAX           DisplayString
    ACCESS           read-only
    STATUS           mandatory
    DESCRIPTION
    "Name of station object."
    ::=   { b01_D327InputTableEntry 2 }

b01_D327InputValue    OBJECT-TYPE
    SYNTAX           DisplayString
    ACCESS           read-write
    STATUS           mandatory
    DESCRIPTION
    "Current value of station object. Is read-write ."
    ::=   { b01_D327InputTableEntry 3 }



-- ***********************************
-- *
-- *  B01_D327Output table declarations
-- *
-- ***********************************

b01_D327OutputTable   OBJECT-TYPE
    SYNTAX                SEQUENCE OF B01_D327OutputTableEntry
    ACCESS                not-accessible
    STATUS                mandatory
    DESCRIPTION
    "A list of snmp b01_D327Output (read-only) object values."
    ::=  { b01_D327 2 }

b01_D327OutputTableEntry  OBJECT-TYPE
    SYNTAX                B01_D327OutputTableEntry
    ACCESS                not-accessible
    STATUS                mandatory
    DESCRIPTION
    "An b01_D327Output table entry containing data for a specific b01_D327Output."
    INDEX  { b01_D327OutputIndex }  ::=   { b01_D327OutputTable 1 }

B01_D327OutputTableEntry ::= SEQUENCE {
        b01_D327OutputIndex       INTEGER,
        b01_D327OutputName        DisplayString,
        b01_D327OutputValue       DisplayString
    }

b01_D327OutputIndex   OBJECT-TYPE
    SYNTAX           INTEGER(0..2147483647)
    ACCESS           read-only
    STATUS           mandatory
    DESCRIPTION
    "The index in the b01_D327Output table for a particular snmp b01_D327Output
	 object.  Used to address table entries."
    ::=   { b01_D327OutputTableEntry 1 }


b01_D327OutputName    OBJECT-TYPE
    SYNTAX           DisplayString
    ACCESS           read-only
    STATUS           mandatory
    DESCRIPTION
    "Name of station object."
    ::=   { b01_D327OutputTableEntry 2 }

b01_D327OutputValue    OBJECT-TYPE
    SYNTAX           DisplayString
    ACCESS           read-only
    STATUS           mandatory
    DESCRIPTION
    "Current value of station object. Is read-only ."
    ::=   { b01_D327OutputTableEntry 3 }


-- ***********************************
-- *
-- *  B01_D328
-- *
-- ***********************************
    b01_D328    OBJECT IDENTIFIER ::= { exportTables 22 }

-- ***********************************
-- *
-- *  B01_D328Input table declarations
-- *
-- ***********************************

b01_D328InputTable   OBJECT-TYPE
    SYNTAX                SEQUENCE OF B01_D328InputTableEntry
    ACCESS                not-accessible
    STATUS                mandatory
    DESCRIPTION
    "A list of snmp b01_D328Input (read-only) object values."
    ::=  { b01_D328 1 }

b01_D328InputTableEntry  OBJECT-TYPE
    SYNTAX                B01_D328InputTableEntry
    ACCESS                not-accessible
    STATUS                mandatory
    DESCRIPTION
    "An b01_D328Input table entry containing data for a specific b01_D328Input."
    INDEX  { b01_D328InputIndex }  ::=   { b01_D328InputTable 1 }

B01_D328InputTableEntry ::= SEQUENCE {
        b01_D328InputIndex       INTEGER,
        b01_D328InputName        DisplayString,
        b01_D328InputValue       DisplayString
    }

b01_D328InputIndex   OBJECT-TYPE
    SYNTAX           INTEGER(0..2147483647)
    ACCESS           read-only
    STATUS           mandatory
    DESCRIPTION
    "The index in the b01_D328Input table for a particular snmp b01_D328Input
	 object.  Used to address table entries."
    ::=   { b01_D328InputTableEntry 1 }


b01_D328InputName    OBJECT-TYPE
    SYNTAX           DisplayString
    ACCESS           read-only
    STATUS           mandatory
    DESCRIPTION
    "Name of station object."
    ::=   { b01_D328InputTableEntry 2 }

b01_D328InputValue    OBJECT-TYPE
    SYNTAX           DisplayString
    ACCESS           read-write
    STATUS           mandatory
    DESCRIPTION
    "Current value of station object. Is read-write ."
    ::=   { b01_D328InputTableEntry 3 }



-- ***********************************
-- *
-- *  B01_D328Output table declarations
-- *
-- ***********************************

b01_D328OutputTable   OBJECT-TYPE
    SYNTAX                SEQUENCE OF B01_D328OutputTableEntry
    ACCESS                not-accessible
    STATUS                mandatory
    DESCRIPTION
    "A list of snmp b01_D328Output (read-only) object values."
    ::=  { b01_D328 2 }

b01_D328OutputTableEntry  OBJECT-TYPE
    SYNTAX                B01_D328OutputTableEntry
    ACCESS                not-accessible
    STATUS                mandatory
    DESCRIPTION
    "An b01_D328Output table entry containing data for a specific b01_D328Output."
    INDEX  { b01_D328OutputIndex }  ::=   { b01_D328OutputTable 1 }

B01_D328OutputTableEntry ::= SEQUENCE {
        b01_D328OutputIndex       INTEGER,
        b01_D328OutputName        DisplayString,
        b01_D328OutputValue       DisplayString
    }

b01_D328OutputIndex   OBJECT-TYPE
    SYNTAX           INTEGER(0..2147483647)
    ACCESS           read-only
    STATUS           mandatory
    DESCRIPTION
    "The index in the b01_D328Output table for a particular snmp b01_D328Output
	 object.  Used to address table entries."
    ::=   { b01_D328OutputTableEntry 1 }


b01_D328OutputName    OBJECT-TYPE
    SYNTAX           DisplayString
    ACCESS           read-only
    STATUS           mandatory
    DESCRIPTION
    "Name of station object."
    ::=   { b01_D328OutputTableEntry 2 }

b01_D328OutputValue    OBJECT-TYPE
    SYNTAX           DisplayString
    ACCESS           read-only
    STATUS           mandatory
    DESCRIPTION
    "Current value of station object. Is read-only ."
    ::=   { b01_D328OutputTableEntry 3 }


-- ***********************************
-- *
-- *  B01_D329
-- *
-- ***********************************
    b01_D329    OBJECT IDENTIFIER ::= { exportTables 23 }

-- ***********************************
-- *
-- *  B01_D329Input table declarations
-- *
-- ***********************************

b01_D329InputTable   OBJECT-TYPE
    SYNTAX                SEQUENCE OF B01_D329InputTableEntry
    ACCESS                not-accessible
    STATUS                mandatory
    DESCRIPTION
    "A list of snmp b01_D329Input (read-only) object values."
    ::=  { b01_D329 1 }

b01_D329InputTableEntry  OBJECT-TYPE
    SYNTAX                B01_D329InputTableEntry
    ACCESS                not-accessible
    STATUS                mandatory
    DESCRIPTION
    "An b01_D329Input table entry containing data for a specific b01_D329Input."
    INDEX  { b01_D329InputIndex }  ::=   { b01_D329InputTable 1 }

B01_D329InputTableEntry ::= SEQUENCE {
        b01_D329InputIndex       INTEGER,
        b01_D329InputName        DisplayString,
        b01_D329InputValue       DisplayString
    }

b01_D329InputIndex   OBJECT-TYPE
    SYNTAX           INTEGER(0..2147483647)
    ACCESS           read-only
    STATUS           mandatory
    DESCRIPTION
    "The index in the b01_D329Input table for a particular snmp b01_D329Input
	 object.  Used to address table entries."
    ::=   { b01_D329InputTableEntry 1 }


b01_D329InputName    OBJECT-TYPE
    SYNTAX           DisplayString
    ACCESS           read-only
    STATUS           mandatory
    DESCRIPTION
    "Name of station object."
    ::=   { b01_D329InputTableEntry 2 }

b01_D329InputValue    OBJECT-TYPE
    SYNTAX           DisplayString
    ACCESS           read-write
    STATUS           mandatory
    DESCRIPTION
    "Current value of station object. Is read-write ."
    ::=   { b01_D329InputTableEntry 3 }



-- ***********************************
-- *
-- *  B01_D329Output table declarations
-- *
-- ***********************************

b01_D329OutputTable   OBJECT-TYPE
    SYNTAX                SEQUENCE OF B01_D329OutputTableEntry
    ACCESS                not-accessible
    STATUS                mandatory
    DESCRIPTION
    "A list of snmp b01_D329Output (read-only) object values."
    ::=  { b01_D329 2 }

b01_D329OutputTableEntry  OBJECT-TYPE
    SYNTAX                B01_D329OutputTableEntry
    ACCESS                not-accessible
    STATUS                mandatory
    DESCRIPTION
    "An b01_D329Output table entry containing data for a specific b01_D329Output."
    INDEX  { b01_D329OutputIndex }  ::=   { b01_D329OutputTable 1 }

B01_D329OutputTableEntry ::= SEQUENCE {
        b01_D329OutputIndex       INTEGER,
        b01_D329OutputName        DisplayString,
        b01_D329OutputValue       DisplayString
    }

b01_D329OutputIndex   OBJECT-TYPE
    SYNTAX           INTEGER(0..2147483647)
    ACCESS           read-only
    STATUS           mandatory
    DESCRIPTION
    "The index in the b01_D329Output table for a particular snmp b01_D329Output
	 object.  Used to address table entries."
    ::=   { b01_D329OutputTableEntry 1 }


b01_D329OutputName    OBJECT-TYPE
    SYNTAX           DisplayString
    ACCESS           read-only
    STATUS           mandatory
    DESCRIPTION
    "Name of station object."
    ::=   { b01_D329OutputTableEntry 2 }

b01_D329OutputValue    OBJECT-TYPE
    SYNTAX           DisplayString
    ACCESS           read-only
    STATUS           mandatory
    DESCRIPTION
    "Current value of station object. Is read-only ."
    ::=   { b01_D329OutputTableEntry 3 }


-- ***********************************
-- *
-- *  B01_D340
-- *
-- ***********************************
    b01_D340    OBJECT IDENTIFIER ::= { exportTables 24 }

-- ***********************************
-- *
-- *  B01_D340Input table declarations
-- *
-- ***********************************

b01_D340InputTable   OBJECT-TYPE
    SYNTAX                SEQUENCE OF B01_D340InputTableEntry
    ACCESS                not-accessible
    STATUS                mandatory
    DESCRIPTION
    "A list of snmp b01_D340Input (read-only) object values."
    ::=  { b01_D340 1 }

b01_D340InputTableEntry  OBJECT-TYPE
    SYNTAX                B01_D340InputTableEntry
    ACCESS                not-accessible
    STATUS                mandatory
    DESCRIPTION
    "An b01_D340Input table entry containing data for a specific b01_D340Input."
    INDEX  { b01_D340InputIndex }  ::=   { b01_D340InputTable 1 }

B01_D340InputTableEntry ::= SEQUENCE {
        b01_D340InputIndex       INTEGER,
        b01_D340InputName        DisplayString,
        b01_D340InputValue       DisplayString
    }

b01_D340InputIndex   OBJECT-TYPE
    SYNTAX           INTEGER(0..2147483647)
    ACCESS           read-only
    STATUS           mandatory
    DESCRIPTION
    "The index in the b01_D340Input table for a particular snmp b01_D340Input
	 object.  Used to address table entries."
    ::=   { b01_D340InputTableEntry 1 }


b01_D340InputName    OBJECT-TYPE
    SYNTAX           DisplayString
    ACCESS           read-only
    STATUS           mandatory
    DESCRIPTION
    "Name of station object."
    ::=   { b01_D340InputTableEntry 2 }

b01_D340InputValue    OBJECT-TYPE
    SYNTAX           DisplayString
    ACCESS           read-write
    STATUS           mandatory
    DESCRIPTION
    "Current value of station object. Is read-write ."
    ::=   { b01_D340InputTableEntry 3 }



-- ***********************************
-- *
-- *  B01_D340Output table declarations
-- *
-- ***********************************

b01_D340OutputTable   OBJECT-TYPE
    SYNTAX                SEQUENCE OF B01_D340OutputTableEntry
    ACCESS                not-accessible
    STATUS                mandatory
    DESCRIPTION
    "A list of snmp b01_D340Output (read-only) object values."
    ::=  { b01_D340 2 }

b01_D340OutputTableEntry  OBJECT-TYPE
    SYNTAX                B01_D340OutputTableEntry
    ACCESS                not-accessible
    STATUS                mandatory
    DESCRIPTION
    "An b01_D340Output table entry containing data for a specific b01_D340Output."
    INDEX  { b01_D340OutputIndex }  ::=   { b01_D340OutputTable 1 }

B01_D340OutputTableEntry ::= SEQUENCE {
        b01_D340OutputIndex       INTEGER,
        b01_D340OutputName        DisplayString,
        b01_D340OutputValue       DisplayString
    }

b01_D340OutputIndex   OBJECT-TYPE
    SYNTAX           INTEGER(0..2147483647)
    ACCESS           read-only
    STATUS           mandatory
    DESCRIPTION
    "The index in the b01_D340Output table for a particular snmp b01_D340Output
	 object.  Used to address table entries."
    ::=   { b01_D340OutputTableEntry 1 }


b01_D340OutputName    OBJECT-TYPE
    SYNTAX           DisplayString
    ACCESS           read-only
    STATUS           mandatory
    DESCRIPTION
    "Name of station object."
    ::=   { b01_D340OutputTableEntry 2 }

b01_D340OutputValue    OBJECT-TYPE
    SYNTAX           DisplayString
    ACCESS           read-only
    STATUS           mandatory
    DESCRIPTION
    "Current value of station object. Is read-only ."
    ::=   { b01_D340OutputTableEntry 3 }


-- ***********************************
-- *
-- *  B01_D341
-- *
-- ***********************************
    b01_D341    OBJECT IDENTIFIER ::= { exportTables 25 }

-- ***********************************
-- *
-- *  B01_D341Input table declarations
-- *
-- ***********************************

b01_D341InputTable   OBJECT-TYPE
    SYNTAX                SEQUENCE OF B01_D341InputTableEntry
    ACCESS                not-accessible
    STATUS                mandatory
    DESCRIPTION
    "A list of snmp b01_D341Input (read-only) object values."
    ::=  { b01_D341 1 }

b01_D341InputTableEntry  OBJECT-TYPE
    SYNTAX                B01_D341InputTableEntry
    ACCESS                not-accessible
    STATUS                mandatory
    DESCRIPTION
    "An b01_D341Input table entry containing data for a specific b01_D341Input."
    INDEX  { b01_D341InputIndex }  ::=   { b01_D341InputTable 1 }

B01_D341InputTableEntry ::= SEQUENCE {
        b01_D341InputIndex       INTEGER,
        b01_D341InputName        DisplayString,
        b01_D341InputValue       DisplayString
    }

b01_D341InputIndex   OBJECT-TYPE
    SYNTAX           INTEGER(0..2147483647)
    ACCESS           read-only
    STATUS           mandatory
    DESCRIPTION
    "The index in the b01_D341Input table for a particular snmp b01_D341Input
	 object.  Used to address table entries."
    ::=   { b01_D341InputTableEntry 1 }


b01_D341InputName    OBJECT-TYPE
    SYNTAX           DisplayString
    ACCESS           read-only
    STATUS           mandatory
    DESCRIPTION
    "Name of station object."
    ::=   { b01_D341InputTableEntry 2 }

b01_D341InputValue    OBJECT-TYPE
    SYNTAX           DisplayString
    ACCESS           read-write
    STATUS           mandatory
    DESCRIPTION
    "Current value of station object. Is read-write ."
    ::=   { b01_D341InputTableEntry 3 }



-- ***********************************
-- *
-- *  B01_D341Output table declarations
-- *
-- ***********************************

b01_D341OutputTable   OBJECT-TYPE
    SYNTAX                SEQUENCE OF B01_D341OutputTableEntry
    ACCESS                not-accessible
    STATUS                mandatory
    DESCRIPTION
    "A list of snmp b01_D341Output (read-only) object values."
    ::=  { b01_D341 2 }

b01_D341OutputTableEntry  OBJECT-TYPE
    SYNTAX                B01_D341OutputTableEntry
    ACCESS                not-accessible
    STATUS                mandatory
    DESCRIPTION
    "An b01_D341Output table entry containing data for a specific b01_D341Output."
    INDEX  { b01_D341OutputIndex }  ::=   { b01_D341OutputTable 1 }

B01_D341OutputTableEntry ::= SEQUENCE {
        b01_D341OutputIndex       INTEGER,
        b01_D341OutputName        DisplayString,
        b01_D341OutputValue       DisplayString
    }

b01_D341OutputIndex   OBJECT-TYPE
    SYNTAX           INTEGER(0..2147483647)
    ACCESS           read-only
    STATUS           mandatory
    DESCRIPTION
    "The index in the b01_D341Output table for a particular snmp b01_D341Output
	 object.  Used to address table entries."
    ::=   { b01_D341OutputTableEntry 1 }


b01_D341OutputName    OBJECT-TYPE
    SYNTAX           DisplayString
    ACCESS           read-only
    STATUS           mandatory
    DESCRIPTION
    "Name of station object."
    ::=   { b01_D341OutputTableEntry 2 }

b01_D341OutputValue    OBJECT-TYPE
    SYNTAX           DisplayString
    ACCESS           read-only
    STATUS           mandatory
    DESCRIPTION
    "Current value of station object. Is read-only ."
    ::=   { b01_D341OutputTableEntry 3 }


-- ***********************************
-- *
-- *  B01_D342
-- *
-- ***********************************
    b01_D342    OBJECT IDENTIFIER ::= { exportTables 26 }

-- ***********************************
-- *
-- *  B01_D342Input table declarations
-- *
-- ***********************************

b01_D342InputTable   OBJECT-TYPE
    SYNTAX                SEQUENCE OF B01_D342InputTableEntry
    ACCESS                not-accessible
    STATUS                mandatory
    DESCRIPTION
    "A list of snmp b01_D342Input (read-only) object values."
    ::=  { b01_D342 1 }

b01_D342InputTableEntry  OBJECT-TYPE
    SYNTAX                B01_D342InputTableEntry
    ACCESS                not-accessible
    STATUS                mandatory
    DESCRIPTION
    "An b01_D342Input table entry containing data for a specific b01_D342Input."
    INDEX  { b01_D342InputIndex }  ::=   { b01_D342InputTable 1 }

B01_D342InputTableEntry ::= SEQUENCE {
        b01_D342InputIndex       INTEGER,
        b01_D342InputName        DisplayString,
        b01_D342InputValue       DisplayString
    }

b01_D342InputIndex   OBJECT-TYPE
    SYNTAX           INTEGER(0..2147483647)
    ACCESS           read-only
    STATUS           mandatory
    DESCRIPTION
    "The index in the b01_D342Input table for a particular snmp b01_D342Input
	 object.  Used to address table entries."
    ::=   { b01_D342InputTableEntry 1 }


b01_D342InputName    OBJECT-TYPE
    SYNTAX           DisplayString
    ACCESS           read-only
    STATUS           mandatory
    DESCRIPTION
    "Name of station object."
    ::=   { b01_D342InputTableEntry 2 }

b01_D342InputValue    OBJECT-TYPE
    SYNTAX           DisplayString
    ACCESS           read-write
    STATUS           mandatory
    DESCRIPTION
    "Current value of station object. Is read-write ."
    ::=   { b01_D342InputTableEntry 3 }



-- ***********************************
-- *
-- *  B01_D342Output table declarations
-- *
-- ***********************************

b01_D342OutputTable   OBJECT-TYPE
    SYNTAX                SEQUENCE OF B01_D342OutputTableEntry
    ACCESS                not-accessible
    STATUS                mandatory
    DESCRIPTION
    "A list of snmp b01_D342Output (read-only) object values."
    ::=  { b01_D342 2 }

b01_D342OutputTableEntry  OBJECT-TYPE
    SYNTAX                B01_D342OutputTableEntry
    ACCESS                not-accessible
    STATUS                mandatory
    DESCRIPTION
    "An b01_D342Output table entry containing data for a specific b01_D342Output."
    INDEX  { b01_D342OutputIndex }  ::=   { b01_D342OutputTable 1 }

B01_D342OutputTableEntry ::= SEQUENCE {
        b01_D342OutputIndex       INTEGER,
        b01_D342OutputName        DisplayString,
        b01_D342OutputValue       DisplayString
    }

b01_D342OutputIndex   OBJECT-TYPE
    SYNTAX           INTEGER(0..2147483647)
    ACCESS           read-only
    STATUS           mandatory
    DESCRIPTION
    "The index in the b01_D342Output table for a particular snmp b01_D342Output
	 object.  Used to address table entries."
    ::=   { b01_D342OutputTableEntry 1 }


b01_D342OutputName    OBJECT-TYPE
    SYNTAX           DisplayString
    ACCESS           read-only
    STATUS           mandatory
    DESCRIPTION
    "Name of station object."
    ::=   { b01_D342OutputTableEntry 2 }

b01_D342OutputValue    OBJECT-TYPE
    SYNTAX           DisplayString
    ACCESS           read-only
    STATUS           mandatory
    DESCRIPTION
    "Current value of station object. Is read-only ."
    ::=   { b01_D342OutputTableEntry 3 }


-- ***********************************
-- *
-- *  B01_D344
-- *
-- ***********************************
    b01_D344    OBJECT IDENTIFIER ::= { exportTables 27 }

-- ***********************************
-- *
-- *  B01_D344Input table declarations
-- *
-- ***********************************

b01_D344InputTable   OBJECT-TYPE
    SYNTAX                SEQUENCE OF B01_D344InputTableEntry
    ACCESS                not-accessible
    STATUS                mandatory
    DESCRIPTION
    "A list of snmp b01_D344Input (read-only) object values."
    ::=  { b01_D344 1 }

b01_D344InputTableEntry  OBJECT-TYPE
    SYNTAX                B01_D344InputTableEntry
    ACCESS                not-accessible
    STATUS                mandatory
    DESCRIPTION
    "An b01_D344Input table entry containing data for a specific b01_D344Input."
    INDEX  { b01_D344InputIndex }  ::=   { b01_D344InputTable 1 }

B01_D344InputTableEntry ::= SEQUENCE {
        b01_D344InputIndex       INTEGER,
        b01_D344InputName        DisplayString,
        b01_D344InputValue       DisplayString
    }

b01_D344InputIndex   OBJECT-TYPE
    SYNTAX           INTEGER(0..2147483647)
    ACCESS           read-only
    STATUS           mandatory
    DESCRIPTION
    "The index in the b01_D344Input table for a particular snmp b01_D344Input
	 object.  Used to address table entries."
    ::=   { b01_D344InputTableEntry 1 }


b01_D344InputName    OBJECT-TYPE
    SYNTAX           DisplayString
    ACCESS           read-only
    STATUS           mandatory
    DESCRIPTION
    "Name of station object."
    ::=   { b01_D344InputTableEntry 2 }

b01_D344InputValue    OBJECT-TYPE
    SYNTAX           DisplayString
    ACCESS           read-write
    STATUS           mandatory
    DESCRIPTION
    "Current value of station object. Is read-write ."
    ::=   { b01_D344InputTableEntry 3 }



-- ***********************************
-- *
-- *  B01_D344Output table declarations
-- *
-- ***********************************

b01_D344OutputTable   OBJECT-TYPE
    SYNTAX                SEQUENCE OF B01_D344OutputTableEntry
    ACCESS                not-accessible
    STATUS                mandatory
    DESCRIPTION
    "A list of snmp b01_D344Output (read-only) object values."
    ::=  { b01_D344 2 }

b01_D344OutputTableEntry  OBJECT-TYPE
    SYNTAX                B01_D344OutputTableEntry
    ACCESS                not-accessible
    STATUS                mandatory
    DESCRIPTION
    "An b01_D344Output table entry containing data for a specific b01_D344Output."
    INDEX  { b01_D344OutputIndex }  ::=   { b01_D344OutputTable 1 }

B01_D344OutputTableEntry ::= SEQUENCE {
        b01_D344OutputIndex       INTEGER,
        b01_D344OutputName        DisplayString,
        b01_D344OutputValue       DisplayString
    }

b01_D344OutputIndex   OBJECT-TYPE
    SYNTAX           INTEGER(0..2147483647)
    ACCESS           read-only
    STATUS           mandatory
    DESCRIPTION
    "The index in the b01_D344Output table for a particular snmp b01_D344Output
	 object.  Used to address table entries."
    ::=   { b01_D344OutputTableEntry 1 }


b01_D344OutputName    OBJECT-TYPE
    SYNTAX           DisplayString
    ACCESS           read-only
    STATUS           mandatory
    DESCRIPTION
    "Name of station object."
    ::=   { b01_D344OutputTableEntry 2 }

b01_D344OutputValue    OBJECT-TYPE
    SYNTAX           DisplayString
    ACCESS           read-only
    STATUS           mandatory
    DESCRIPTION
    "Current value of station object. Is read-only ."
    ::=   { b01_D344OutputTableEntry 3 }


-- ***********************************
-- *
-- *  B01_D345
-- *
-- ***********************************
    b01_D345    OBJECT IDENTIFIER ::= { exportTables 28 }

-- ***********************************
-- *
-- *  B01_D345Input table declarations
-- *
-- ***********************************

b01_D345InputTable   OBJECT-TYPE
    SYNTAX                SEQUENCE OF B01_D345InputTableEntry
    ACCESS                not-accessible
    STATUS                mandatory
    DESCRIPTION
    "A list of snmp b01_D345Input (read-only) object values."
    ::=  { b01_D345 1 }

b01_D345InputTableEntry  OBJECT-TYPE
    SYNTAX                B01_D345InputTableEntry
    ACCESS                not-accessible
    STATUS                mandatory
    DESCRIPTION
    "An b01_D345Input table entry containing data for a specific b01_D345Input."
    INDEX  { b01_D345InputIndex }  ::=   { b01_D345InputTable 1 }

B01_D345InputTableEntry ::= SEQUENCE {
        b01_D345InputIndex       INTEGER,
        b01_D345InputName        DisplayString,
        b01_D345InputValue       DisplayString
    }

b01_D345InputIndex   OBJECT-TYPE
    SYNTAX           INTEGER(0..2147483647)
    ACCESS           read-only
    STATUS           mandatory
    DESCRIPTION
    "The index in the b01_D345Input table for a particular snmp b01_D345Input
	 object.  Used to address table entries."
    ::=   { b01_D345InputTableEntry 1 }


b01_D345InputName    OBJECT-TYPE
    SYNTAX           DisplayString
    ACCESS           read-only
    STATUS           mandatory
    DESCRIPTION
    "Name of station object."
    ::=   { b01_D345InputTableEntry 2 }

b01_D345InputValue    OBJECT-TYPE
    SYNTAX           DisplayString
    ACCESS           read-write
    STATUS           mandatory
    DESCRIPTION
    "Current value of station object. Is read-write ."
    ::=   { b01_D345InputTableEntry 3 }



-- ***********************************
-- *
-- *  B01_D345Output table declarations
-- *
-- ***********************************

b01_D345OutputTable   OBJECT-TYPE
    SYNTAX                SEQUENCE OF B01_D345OutputTableEntry
    ACCESS                not-accessible
    STATUS                mandatory
    DESCRIPTION
    "A list of snmp b01_D345Output (read-only) object values."
    ::=  { b01_D345 2 }

b01_D345OutputTableEntry  OBJECT-TYPE
    SYNTAX                B01_D345OutputTableEntry
    ACCESS                not-accessible
    STATUS                mandatory
    DESCRIPTION
    "An b01_D345Output table entry containing data for a specific b01_D345Output."
    INDEX  { b01_D345OutputIndex }  ::=   { b01_D345OutputTable 1 }

B01_D345OutputTableEntry ::= SEQUENCE {
        b01_D345OutputIndex       INTEGER,
        b01_D345OutputName        DisplayString,
        b01_D345OutputValue       DisplayString
    }

b01_D345OutputIndex   OBJECT-TYPE
    SYNTAX           INTEGER(0..2147483647)
    ACCESS           read-only
    STATUS           mandatory
    DESCRIPTION
    "The index in the b01_D345Output table for a particular snmp b01_D345Output
	 object.  Used to address table entries."
    ::=   { b01_D345OutputTableEntry 1 }


b01_D345OutputName    OBJECT-TYPE
    SYNTAX           DisplayString
    ACCESS           read-only
    STATUS           mandatory
    DESCRIPTION
    "Name of station object."
    ::=   { b01_D345OutputTableEntry 2 }

b01_D345OutputValue    OBJECT-TYPE
    SYNTAX           DisplayString
    ACCESS           read-only
    STATUS           mandatory
    DESCRIPTION
    "Current value of station object. Is read-only ."
    ::=   { b01_D345OutputTableEntry 3 }


-- ***********************************
-- *
-- *  B01_D346
-- *
-- ***********************************
    b01_D346    OBJECT IDENTIFIER ::= { exportTables 29 }

-- ***********************************
-- *
-- *  B01_D346Input table declarations
-- *
-- ***********************************

b01_D346InputTable   OBJECT-TYPE
    SYNTAX                SEQUENCE OF B01_D346InputTableEntry
    ACCESS                not-accessible
    STATUS                mandatory
    DESCRIPTION
    "A list of snmp b01_D346Input (read-only) object values."
    ::=  { b01_D346 1 }

b01_D346InputTableEntry  OBJECT-TYPE
    SYNTAX                B01_D346InputTableEntry
    ACCESS                not-accessible
    STATUS                mandatory
    DESCRIPTION
    "An b01_D346Input table entry containing data for a specific b01_D346Input."
    INDEX  { b01_D346InputIndex }  ::=   { b01_D346InputTable 1 }

B01_D346InputTableEntry ::= SEQUENCE {
        b01_D346InputIndex       INTEGER,
        b01_D346InputName        DisplayString,
        b01_D346InputValue       DisplayString
    }

b01_D346InputIndex   OBJECT-TYPE
    SYNTAX           INTEGER(0..2147483647)
    ACCESS           read-only
    STATUS           mandatory
    DESCRIPTION
    "The index in the b01_D346Input table for a particular snmp b01_D346Input
	 object.  Used to address table entries."
    ::=   { b01_D346InputTableEntry 1 }


b01_D346InputName    OBJECT-TYPE
    SYNTAX           DisplayString
    ACCESS           read-only
    STATUS           mandatory
    DESCRIPTION
    "Name of station object."
    ::=   { b01_D346InputTableEntry 2 }

b01_D346InputValue    OBJECT-TYPE
    SYNTAX           DisplayString
    ACCESS           read-write
    STATUS           mandatory
    DESCRIPTION
    "Current value of station object. Is read-write ."
    ::=   { b01_D346InputTableEntry 3 }



-- ***********************************
-- *
-- *  B01_D346Output table declarations
-- *
-- ***********************************

b01_D346OutputTable   OBJECT-TYPE
    SYNTAX                SEQUENCE OF B01_D346OutputTableEntry
    ACCESS                not-accessible
    STATUS                mandatory
    DESCRIPTION
    "A list of snmp b01_D346Output (read-only) object values."
    ::=  { b01_D346 2 }

b01_D346OutputTableEntry  OBJECT-TYPE
    SYNTAX                B01_D346OutputTableEntry
    ACCESS                not-accessible
    STATUS                mandatory
    DESCRIPTION
    "An b01_D346Output table entry containing data for a specific b01_D346Output."
    INDEX  { b01_D346OutputIndex }  ::=   { b01_D346OutputTable 1 }

B01_D346OutputTableEntry ::= SEQUENCE {
        b01_D346OutputIndex       INTEGER,
        b01_D346OutputName        DisplayString,
        b01_D346OutputValue       DisplayString
    }

b01_D346OutputIndex   OBJECT-TYPE
    SYNTAX           INTEGER(0..2147483647)
    ACCESS           read-only
    STATUS           mandatory
    DESCRIPTION
    "The index in the b01_D346Output table for a particular snmp b01_D346Output
	 object.  Used to address table entries."
    ::=   { b01_D346OutputTableEntry 1 }


b01_D346OutputName    OBJECT-TYPE
    SYNTAX           DisplayString
    ACCESS           read-only
    STATUS           mandatory
    DESCRIPTION
    "Name of station object."
    ::=   { b01_D346OutputTableEntry 2 }

b01_D346OutputValue    OBJECT-TYPE
    SYNTAX           DisplayString
    ACCESS           read-only
    STATUS           mandatory
    DESCRIPTION
    "Current value of station object. Is read-only ."
    ::=   { b01_D346OutputTableEntry 3 }


-- ***********************************
-- *
-- *  B01_D347
-- *
-- ***********************************
    b01_D347    OBJECT IDENTIFIER ::= { exportTables 30 }

-- ***********************************
-- *
-- *  B01_D347Input table declarations
-- *
-- ***********************************

b01_D347InputTable   OBJECT-TYPE
    SYNTAX                SEQUENCE OF B01_D347InputTableEntry
    ACCESS                not-accessible
    STATUS                mandatory
    DESCRIPTION
    "A list of snmp b01_D347Input (read-only) object values."
    ::=  { b01_D347 1 }

b01_D347InputTableEntry  OBJECT-TYPE
    SYNTAX                B01_D347InputTableEntry
    ACCESS                not-accessible
    STATUS                mandatory
    DESCRIPTION
    "An b01_D347Input table entry containing data for a specific b01_D347Input."
    INDEX  { b01_D347InputIndex }  ::=   { b01_D347InputTable 1 }

B01_D347InputTableEntry ::= SEQUENCE {
        b01_D347InputIndex       INTEGER,
        b01_D347InputName        DisplayString,
        b01_D347InputValue       DisplayString
    }

b01_D347InputIndex   OBJECT-TYPE
    SYNTAX           INTEGER(0..2147483647)
    ACCESS           read-only
    STATUS           mandatory
    DESCRIPTION
    "The index in the b01_D347Input table for a particular snmp b01_D347Input
	 object.  Used to address table entries."
    ::=   { b01_D347InputTableEntry 1 }


b01_D347InputName    OBJECT-TYPE
    SYNTAX           DisplayString
    ACCESS           read-only
    STATUS           mandatory
    DESCRIPTION
    "Name of station object."
    ::=   { b01_D347InputTableEntry 2 }

b01_D347InputValue    OBJECT-TYPE
    SYNTAX           DisplayString
    ACCESS           read-write
    STATUS           mandatory
    DESCRIPTION
    "Current value of station object. Is read-write ."
    ::=   { b01_D347InputTableEntry 3 }



-- ***********************************
-- *
-- *  B01_D347Output table declarations
-- *
-- ***********************************

b01_D347OutputTable   OBJECT-TYPE
    SYNTAX                SEQUENCE OF B01_D347OutputTableEntry
    ACCESS                not-accessible
    STATUS                mandatory
    DESCRIPTION
    "A list of snmp b01_D347Output (read-only) object values."
    ::=  { b01_D347 2 }

b01_D347OutputTableEntry  OBJECT-TYPE
    SYNTAX                B01_D347OutputTableEntry
    ACCESS                not-accessible
    STATUS                mandatory
    DESCRIPTION
    "An b01_D347Output table entry containing data for a specific b01_D347Output."
    INDEX  { b01_D347OutputIndex }  ::=   { b01_D347OutputTable 1 }

B01_D347OutputTableEntry ::= SEQUENCE {
        b01_D347OutputIndex       INTEGER,
        b01_D347OutputName        DisplayString,
        b01_D347OutputValue       DisplayString
    }

b01_D347OutputIndex   OBJECT-TYPE
    SYNTAX           INTEGER(0..2147483647)
    ACCESS           read-only
    STATUS           mandatory
    DESCRIPTION
    "The index in the b01_D347Output table for a particular snmp b01_D347Output
	 object.  Used to address table entries."
    ::=   { b01_D347OutputTableEntry 1 }


b01_D347OutputName    OBJECT-TYPE
    SYNTAX           DisplayString
    ACCESS           read-only
    STATUS           mandatory
    DESCRIPTION
    "Name of station object."
    ::=   { b01_D347OutputTableEntry 2 }

b01_D347OutputValue    OBJECT-TYPE
    SYNTAX           DisplayString
    ACCESS           read-only
    STATUS           mandatory
    DESCRIPTION
    "Current value of station object. Is read-only ."
    ::=   { b01_D347OutputTableEntry 3 }


-- ***********************************
-- *
-- *  B01_D348
-- *
-- ***********************************
    b01_D348    OBJECT IDENTIFIER ::= { exportTables 31 }

-- ***********************************
-- *
-- *  B01_D348Input table declarations
-- *
-- ***********************************

b01_D348InputTable   OBJECT-TYPE
    SYNTAX                SEQUENCE OF B01_D348InputTableEntry
    ACCESS                not-accessible
    STATUS                mandatory
    DESCRIPTION
    "A list of snmp b01_D348Input (read-only) object values."
    ::=  { b01_D348 1 }

b01_D348InputTableEntry  OBJECT-TYPE
    SYNTAX                B01_D348InputTableEntry
    ACCESS                not-accessible
    STATUS                mandatory
    DESCRIPTION
    "An b01_D348Input table entry containing data for a specific b01_D348Input."
    INDEX  { b01_D348InputIndex }  ::=   { b01_D348InputTable 1 }

B01_D348InputTableEntry ::= SEQUENCE {
        b01_D348InputIndex       INTEGER,
        b01_D348InputName        DisplayString,
        b01_D348InputValue       DisplayString
    }

b01_D348InputIndex   OBJECT-TYPE
    SYNTAX           INTEGER(0..2147483647)
    ACCESS           read-only
    STATUS           mandatory
    DESCRIPTION
    "The index in the b01_D348Input table for a particular snmp b01_D348Input
	 object.  Used to address table entries."
    ::=   { b01_D348InputTableEntry 1 }


b01_D348InputName    OBJECT-TYPE
    SYNTAX           DisplayString
    ACCESS           read-only
    STATUS           mandatory
    DESCRIPTION
    "Name of station object."
    ::=   { b01_D348InputTableEntry 2 }

b01_D348InputValue    OBJECT-TYPE
    SYNTAX           DisplayString
    ACCESS           read-write
    STATUS           mandatory
    DESCRIPTION
    "Current value of station object. Is read-write ."
    ::=   { b01_D348InputTableEntry 3 }



-- ***********************************
-- *
-- *  B01_D348Output table declarations
-- *
-- ***********************************

b01_D348OutputTable   OBJECT-TYPE
    SYNTAX                SEQUENCE OF B01_D348OutputTableEntry
    ACCESS                not-accessible
    STATUS                mandatory
    DESCRIPTION
    "A list of snmp b01_D348Output (read-only) object values."
    ::=  { b01_D348 2 }

b01_D348OutputTableEntry  OBJECT-TYPE
    SYNTAX                B01_D348OutputTableEntry
    ACCESS                not-accessible
    STATUS                mandatory
    DESCRIPTION
    "An b01_D348Output table entry containing data for a specific b01_D348Output."
    INDEX  { b01_D348OutputIndex }  ::=   { b01_D348OutputTable 1 }

B01_D348OutputTableEntry ::= SEQUENCE {
        b01_D348OutputIndex       INTEGER,
        b01_D348OutputName        DisplayString,
        b01_D348OutputValue       DisplayString
    }

b01_D348OutputIndex   OBJECT-TYPE
    SYNTAX           INTEGER(0..2147483647)
    ACCESS           read-only
    STATUS           mandatory
    DESCRIPTION
    "The index in the b01_D348Output table for a particular snmp b01_D348Output
	 object.  Used to address table entries."
    ::=   { b01_D348OutputTableEntry 1 }


b01_D348OutputName    OBJECT-TYPE
    SYNTAX           DisplayString
    ACCESS           read-only
    STATUS           mandatory
    DESCRIPTION
    "Name of station object."
    ::=   { b01_D348OutputTableEntry 2 }

b01_D348OutputValue    OBJECT-TYPE
    SYNTAX           DisplayString
    ACCESS           read-only
    STATUS           mandatory
    DESCRIPTION
    "Current value of station object. Is read-only ."
    ::=   { b01_D348OutputTableEntry 3 }


-- ***********************************
-- *
-- *  B01_D349
-- *
-- ***********************************
    b01_D349    OBJECT IDENTIFIER ::= { exportTables 32 }

-- ***********************************
-- *
-- *  B01_D349Input table declarations
-- *
-- ***********************************

b01_D349InputTable   OBJECT-TYPE
    SYNTAX                SEQUENCE OF B01_D349InputTableEntry
    ACCESS                not-accessible
    STATUS                mandatory
    DESCRIPTION
    "A list of snmp b01_D349Input (read-only) object values."
    ::=  { b01_D349 1 }

b01_D349InputTableEntry  OBJECT-TYPE
    SYNTAX                B01_D349InputTableEntry
    ACCESS                not-accessible
    STATUS                mandatory
    DESCRIPTION
    "An b01_D349Input table entry containing data for a specific b01_D349Input."
    INDEX  { b01_D349InputIndex }  ::=   { b01_D349InputTable 1 }

B01_D349InputTableEntry ::= SEQUENCE {
        b01_D349InputIndex       INTEGER,
        b01_D349InputName        DisplayString,
        b01_D349InputValue       DisplayString
    }

b01_D349InputIndex   OBJECT-TYPE
    SYNTAX           INTEGER(0..2147483647)
    ACCESS           read-only
    STATUS           mandatory
    DESCRIPTION
    "The index in the b01_D349Input table for a particular snmp b01_D349Input
	 object.  Used to address table entries."
    ::=   { b01_D349InputTableEntry 1 }


b01_D349InputName    OBJECT-TYPE
    SYNTAX           DisplayString
    ACCESS           read-only
    STATUS           mandatory
    DESCRIPTION
    "Name of station object."
    ::=   { b01_D349InputTableEntry 2 }

b01_D349InputValue    OBJECT-TYPE
    SYNTAX           DisplayString
    ACCESS           read-write
    STATUS           mandatory
    DESCRIPTION
    "Current value of station object. Is read-write ."
    ::=   { b01_D349InputTableEntry 3 }



-- ***********************************
-- *
-- *  B01_D349Output table declarations
-- *
-- ***********************************

b01_D349OutputTable   OBJECT-TYPE
    SYNTAX                SEQUENCE OF B01_D349OutputTableEntry
    ACCESS                not-accessible
    STATUS                mandatory
    DESCRIPTION
    "A list of snmp b01_D349Output (read-only) object values."
    ::=  { b01_D349 2 }

b01_D349OutputTableEntry  OBJECT-TYPE
    SYNTAX                B01_D349OutputTableEntry
    ACCESS                not-accessible
    STATUS                mandatory
    DESCRIPTION
    "An b01_D349Output table entry containing data for a specific b01_D349Output."
    INDEX  { b01_D349OutputIndex }  ::=   { b01_D349OutputTable 1 }

B01_D349OutputTableEntry ::= SEQUENCE {
        b01_D349OutputIndex       INTEGER,
        b01_D349OutputName        DisplayString,
        b01_D349OutputValue       DisplayString
    }

b01_D349OutputIndex   OBJECT-TYPE
    SYNTAX           INTEGER(0..2147483647)
    ACCESS           read-only
    STATUS           mandatory
    DESCRIPTION
    "The index in the b01_D349Output table for a particular snmp b01_D349Output
	 object.  Used to address table entries."
    ::=   { b01_D349OutputTableEntry 1 }


b01_D349OutputName    OBJECT-TYPE
    SYNTAX           DisplayString
    ACCESS           read-only
    STATUS           mandatory
    DESCRIPTION
    "Name of station object."
    ::=   { b01_D349OutputTableEntry 2 }

b01_D349OutputValue    OBJECT-TYPE
    SYNTAX           DisplayString
    ACCESS           read-only
    STATUS           mandatory
    DESCRIPTION
    "Current value of station object. Is read-only ."
    ::=   { b01_D349OutputTableEntry 3 }


-- ***********************************
-- *
-- *  B01_D350
-- *
-- ***********************************
    b01_D350    OBJECT IDENTIFIER ::= { exportTables 33 }

-- ***********************************
-- *
-- *  B01_D350Input table declarations
-- *
-- ***********************************

b01_D350InputTable   OBJECT-TYPE
    SYNTAX                SEQUENCE OF B01_D350InputTableEntry
    ACCESS                not-accessible
    STATUS                mandatory
    DESCRIPTION
    "A list of snmp b01_D350Input (read-only) object values."
    ::=  { b01_D350 1 }

b01_D350InputTableEntry  OBJECT-TYPE
    SYNTAX                B01_D350InputTableEntry
    ACCESS                not-accessible
    STATUS                mandatory
    DESCRIPTION
    "An b01_D350Input table entry containing data for a specific b01_D350Input."
    INDEX  { b01_D350InputIndex }  ::=   { b01_D350InputTable 1 }

B01_D350InputTableEntry ::= SEQUENCE {
        b01_D350InputIndex       INTEGER,
        b01_D350InputName        DisplayString,
        b01_D350InputValue       DisplayString
    }

b01_D350InputIndex   OBJECT-TYPE
    SYNTAX           INTEGER(0..2147483647)
    ACCESS           read-only
    STATUS           mandatory
    DESCRIPTION
    "The index in the b01_D350Input table for a particular snmp b01_D350Input
	 object.  Used to address table entries."
    ::=   { b01_D350InputTableEntry 1 }


b01_D350InputName    OBJECT-TYPE
    SYNTAX           DisplayString
    ACCESS           read-only
    STATUS           mandatory
    DESCRIPTION
    "Name of station object."
    ::=   { b01_D350InputTableEntry 2 }

b01_D350InputValue    OBJECT-TYPE
    SYNTAX           DisplayString
    ACCESS           read-write
    STATUS           mandatory
    DESCRIPTION
    "Current value of station object. Is read-write ."
    ::=   { b01_D350InputTableEntry 3 }



-- ***********************************
-- *
-- *  B01_D350Output table declarations
-- *
-- ***********************************

b01_D350OutputTable   OBJECT-TYPE
    SYNTAX                SEQUENCE OF B01_D350OutputTableEntry
    ACCESS                not-accessible
    STATUS                mandatory
    DESCRIPTION
    "A list of snmp b01_D350Output (read-only) object values."
    ::=  { b01_D350 2 }

b01_D350OutputTableEntry  OBJECT-TYPE
    SYNTAX                B01_D350OutputTableEntry
    ACCESS                not-accessible
    STATUS                mandatory
    DESCRIPTION
    "An b01_D350Output table entry containing data for a specific b01_D350Output."
    INDEX  { b01_D350OutputIndex }  ::=   { b01_D350OutputTable 1 }

B01_D350OutputTableEntry ::= SEQUENCE {
        b01_D350OutputIndex       INTEGER,
        b01_D350OutputName        DisplayString,
        b01_D350OutputValue       DisplayString
    }

b01_D350OutputIndex   OBJECT-TYPE
    SYNTAX           INTEGER(0..2147483647)
    ACCESS           read-only
    STATUS           mandatory
    DESCRIPTION
    "The index in the b01_D350Output table for a particular snmp b01_D350Output
	 object.  Used to address table entries."
    ::=   { b01_D350OutputTableEntry 1 }


b01_D350OutputName    OBJECT-TYPE
    SYNTAX           DisplayString
    ACCESS           read-only
    STATUS           mandatory
    DESCRIPTION
    "Name of station object."
    ::=   { b01_D350OutputTableEntry 2 }

b01_D350OutputValue    OBJECT-TYPE
    SYNTAX           DisplayString
    ACCESS           read-only
    STATUS           mandatory
    DESCRIPTION
    "Current value of station object. Is read-only ."
    ::=   { b01_D350OutputTableEntry 3 }


-- ***********************************
-- *
-- *  B01_D360
-- *
-- ***********************************
    b01_D360    OBJECT IDENTIFIER ::= { exportTables 34 }

-- ***********************************
-- *
-- *  B01_D360Input table declarations
-- *
-- ***********************************

b01_D360InputTable   OBJECT-TYPE
    SYNTAX                SEQUENCE OF B01_D360InputTableEntry
    ACCESS                not-accessible
    STATUS                mandatory
    DESCRIPTION
    "A list of snmp b01_D360Input (read-only) object values."
    ::=  { b01_D360 1 }

b01_D360InputTableEntry  OBJECT-TYPE
    SYNTAX                B01_D360InputTableEntry
    ACCESS                not-accessible
    STATUS                mandatory
    DESCRIPTION
    "An b01_D360Input table entry containing data for a specific b01_D360Input."
    INDEX  { b01_D360InputIndex }  ::=   { b01_D360InputTable 1 }

B01_D360InputTableEntry ::= SEQUENCE {
        b01_D360InputIndex       INTEGER,
        b01_D360InputName        DisplayString,
        b01_D360InputValue       DisplayString
    }

b01_D360InputIndex   OBJECT-TYPE
    SYNTAX           INTEGER(0..2147483647)
    ACCESS           read-only
    STATUS           mandatory
    DESCRIPTION
    "The index in the b01_D360Input table for a particular snmp b01_D360Input
	 object.  Used to address table entries."
    ::=   { b01_D360InputTableEntry 1 }


b01_D360InputName    OBJECT-TYPE
    SYNTAX           DisplayString
    ACCESS           read-only
    STATUS           mandatory
    DESCRIPTION
    "Name of station object."
    ::=   { b01_D360InputTableEntry 2 }

b01_D360InputValue    OBJECT-TYPE
    SYNTAX           DisplayString
    ACCESS           read-write
    STATUS           mandatory
    DESCRIPTION
    "Current value of station object. Is read-write ."
    ::=   { b01_D360InputTableEntry 3 }



-- ***********************************
-- *
-- *  B01_D360Output table declarations
-- *
-- ***********************************

b01_D360OutputTable   OBJECT-TYPE
    SYNTAX                SEQUENCE OF B01_D360OutputTableEntry
    ACCESS                not-accessible
    STATUS                mandatory
    DESCRIPTION
    "A list of snmp b01_D360Output (read-only) object values."
    ::=  { b01_D360 2 }

b01_D360OutputTableEntry  OBJECT-TYPE
    SYNTAX                B01_D360OutputTableEntry
    ACCESS                not-accessible
    STATUS                mandatory
    DESCRIPTION
    "An b01_D360Output table entry containing data for a specific b01_D360Output."
    INDEX  { b01_D360OutputIndex }  ::=   { b01_D360OutputTable 1 }

B01_D360OutputTableEntry ::= SEQUENCE {
        b01_D360OutputIndex       INTEGER,
        b01_D360OutputName        DisplayString,
        b01_D360OutputValue       DisplayString
    }

b01_D360OutputIndex   OBJECT-TYPE
    SYNTAX           INTEGER(0..2147483647)
    ACCESS           read-only
    STATUS           mandatory
    DESCRIPTION
    "The index in the b01_D360Output table for a particular snmp b01_D360Output
	 object.  Used to address table entries."
    ::=   { b01_D360OutputTableEntry 1 }


b01_D360OutputName    OBJECT-TYPE
    SYNTAX           DisplayString
    ACCESS           read-only
    STATUS           mandatory
    DESCRIPTION
    "Name of station object."
    ::=   { b01_D360OutputTableEntry 2 }

b01_D360OutputValue    OBJECT-TYPE
    SYNTAX           DisplayString
    ACCESS           read-only
    STATUS           mandatory
    DESCRIPTION
    "Current value of station object. Is read-only ."
    ::=   { b01_D360OutputTableEntry 3 }


-- ***********************************
-- *
-- *  B01_D361
-- *
-- ***********************************
    b01_D361    OBJECT IDENTIFIER ::= { exportTables 35 }

-- ***********************************
-- *
-- *  B01_D361Input table declarations
-- *
-- ***********************************

b01_D361InputTable   OBJECT-TYPE
    SYNTAX                SEQUENCE OF B01_D361InputTableEntry
    ACCESS                not-accessible
    STATUS                mandatory
    DESCRIPTION
    "A list of snmp b01_D361Input (read-only) object values."
    ::=  { b01_D361 1 }

b01_D361InputTableEntry  OBJECT-TYPE
    SYNTAX                B01_D361InputTableEntry
    ACCESS                not-accessible
    STATUS                mandatory
    DESCRIPTION
    "An b01_D361Input table entry containing data for a specific b01_D361Input."
    INDEX  { b01_D361InputIndex }  ::=   { b01_D361InputTable 1 }

B01_D361InputTableEntry ::= SEQUENCE {
        b01_D361InputIndex       INTEGER,
        b01_D361InputName        DisplayString,
        b01_D361InputValue       DisplayString
    }

b01_D361InputIndex   OBJECT-TYPE
    SYNTAX           INTEGER(0..2147483647)
    ACCESS           read-only
    STATUS           mandatory
    DESCRIPTION
    "The index in the b01_D361Input table for a particular snmp b01_D361Input
	 object.  Used to address table entries."
    ::=   { b01_D361InputTableEntry 1 }


b01_D361InputName    OBJECT-TYPE
    SYNTAX           DisplayString
    ACCESS           read-only
    STATUS           mandatory
    DESCRIPTION
    "Name of station object."
    ::=   { b01_D361InputTableEntry 2 }

b01_D361InputValue    OBJECT-TYPE
    SYNTAX           DisplayString
    ACCESS           read-write
    STATUS           mandatory
    DESCRIPTION
    "Current value of station object. Is read-write ."
    ::=   { b01_D361InputTableEntry 3 }



-- ***********************************
-- *
-- *  B01_D361Output table declarations
-- *
-- ***********************************

b01_D361OutputTable   OBJECT-TYPE
    SYNTAX                SEQUENCE OF B01_D361OutputTableEntry
    ACCESS                not-accessible
    STATUS                mandatory
    DESCRIPTION
    "A list of snmp b01_D361Output (read-only) object values."
    ::=  { b01_D361 2 }

b01_D361OutputTableEntry  OBJECT-TYPE
    SYNTAX                B01_D361OutputTableEntry
    ACCESS                not-accessible
    STATUS                mandatory
    DESCRIPTION
    "An b01_D361Output table entry containing data for a specific b01_D361Output."
    INDEX  { b01_D361OutputIndex }  ::=   { b01_D361OutputTable 1 }

B01_D361OutputTableEntry ::= SEQUENCE {
        b01_D361OutputIndex       INTEGER,
        b01_D361OutputName        DisplayString,
        b01_D361OutputValue       DisplayString
    }

b01_D361OutputIndex   OBJECT-TYPE
    SYNTAX           INTEGER(0..2147483647)
    ACCESS           read-only
    STATUS           mandatory
    DESCRIPTION
    "The index in the b01_D361Output table for a particular snmp b01_D361Output
	 object.  Used to address table entries."
    ::=   { b01_D361OutputTableEntry 1 }


b01_D361OutputName    OBJECT-TYPE
    SYNTAX           DisplayString
    ACCESS           read-only
    STATUS           mandatory
    DESCRIPTION
    "Name of station object."
    ::=   { b01_D361OutputTableEntry 2 }

b01_D361OutputValue    OBJECT-TYPE
    SYNTAX           DisplayString
    ACCESS           read-only
    STATUS           mandatory
    DESCRIPTION
    "Current value of station object. Is read-only ."
    ::=   { b01_D361OutputTableEntry 3 }


-- ***********************************
-- *
-- *  B01_D362
-- *
-- ***********************************
    b01_D362    OBJECT IDENTIFIER ::= { exportTables 36 }

-- ***********************************
-- *
-- *  B01_D362Input table declarations
-- *
-- ***********************************

b01_D362InputTable   OBJECT-TYPE
    SYNTAX                SEQUENCE OF B01_D362InputTableEntry
    ACCESS                not-accessible
    STATUS                mandatory
    DESCRIPTION
    "A list of snmp b01_D362Input (read-only) object values."
    ::=  { b01_D362 1 }

b01_D362InputTableEntry  OBJECT-TYPE
    SYNTAX                B01_D362InputTableEntry
    ACCESS                not-accessible
    STATUS                mandatory
    DESCRIPTION
    "An b01_D362Input table entry containing data for a specific b01_D362Input."
    INDEX  { b01_D362InputIndex }  ::=   { b01_D362InputTable 1 }

B01_D362InputTableEntry ::= SEQUENCE {
        b01_D362InputIndex       INTEGER,
        b01_D362InputName        DisplayString,
        b01_D362InputValue       DisplayString
    }

b01_D362InputIndex   OBJECT-TYPE
    SYNTAX           INTEGER(0..2147483647)
    ACCESS           read-only
    STATUS           mandatory
    DESCRIPTION
    "The index in the b01_D362Input table for a particular snmp b01_D362Input
	 object.  Used to address table entries."
    ::=   { b01_D362InputTableEntry 1 }


b01_D362InputName    OBJECT-TYPE
    SYNTAX           DisplayString
    ACCESS           read-only
    STATUS           mandatory
    DESCRIPTION
    "Name of station object."
    ::=   { b01_D362InputTableEntry 2 }

b01_D362InputValue    OBJECT-TYPE
    SYNTAX           DisplayString
    ACCESS           read-write
    STATUS           mandatory
    DESCRIPTION
    "Current value of station object. Is read-write ."
    ::=   { b01_D362InputTableEntry 3 }



-- ***********************************
-- *
-- *  B01_D362Output table declarations
-- *
-- ***********************************

b01_D362OutputTable   OBJECT-TYPE
    SYNTAX                SEQUENCE OF B01_D362OutputTableEntry
    ACCESS                not-accessible
    STATUS                mandatory
    DESCRIPTION
    "A list of snmp b01_D362Output (read-only) object values."
    ::=  { b01_D362 2 }

b01_D362OutputTableEntry  OBJECT-TYPE
    SYNTAX                B01_D362OutputTableEntry
    ACCESS                not-accessible
    STATUS                mandatory
    DESCRIPTION
    "An b01_D362Output table entry containing data for a specific b01_D362Output."
    INDEX  { b01_D362OutputIndex }  ::=   { b01_D362OutputTable 1 }

B01_D362OutputTableEntry ::= SEQUENCE {
        b01_D362OutputIndex       INTEGER,
        b01_D362OutputName        DisplayString,
        b01_D362OutputValue       DisplayString
    }

b01_D362OutputIndex   OBJECT-TYPE
    SYNTAX           INTEGER(0..2147483647)
    ACCESS           read-only
    STATUS           mandatory
    DESCRIPTION
    "The index in the b01_D362Output table for a particular snmp b01_D362Output
	 object.  Used to address table entries."
    ::=   { b01_D362OutputTableEntry 1 }


b01_D362OutputName    OBJECT-TYPE
    SYNTAX           DisplayString
    ACCESS           read-only
    STATUS           mandatory
    DESCRIPTION
    "Name of station object."
    ::=   { b01_D362OutputTableEntry 2 }

b01_D362OutputValue    OBJECT-TYPE
    SYNTAX           DisplayString
    ACCESS           read-only
    STATUS           mandatory
    DESCRIPTION
    "Current value of station object. Is read-only ."
    ::=   { b01_D362OutputTableEntry 3 }


-- ***********************************
-- *
-- *  B01_D364
-- *
-- ***********************************
    b01_D364    OBJECT IDENTIFIER ::= { exportTables 37 }

-- ***********************************
-- *
-- *  B01_D364Input table declarations
-- *
-- ***********************************

b01_D364InputTable   OBJECT-TYPE
    SYNTAX                SEQUENCE OF B01_D364InputTableEntry
    ACCESS                not-accessible
    STATUS                mandatory
    DESCRIPTION
    "A list of snmp b01_D364Input (read-only) object values."
    ::=  { b01_D364 1 }

b01_D364InputTableEntry  OBJECT-TYPE
    SYNTAX                B01_D364InputTableEntry
    ACCESS                not-accessible
    STATUS                mandatory
    DESCRIPTION
    "An b01_D364Input table entry containing data for a specific b01_D364Input."
    INDEX  { b01_D364InputIndex }  ::=   { b01_D364InputTable 1 }

B01_D364InputTableEntry ::= SEQUENCE {
        b01_D364InputIndex       INTEGER,
        b01_D364InputName        DisplayString,
        b01_D364InputValue       DisplayString
    }

b01_D364InputIndex   OBJECT-TYPE
    SYNTAX           INTEGER(0..2147483647)
    ACCESS           read-only
    STATUS           mandatory
    DESCRIPTION
    "The index in the b01_D364Input table for a particular snmp b01_D364Input
	 object.  Used to address table entries."
    ::=   { b01_D364InputTableEntry 1 }


b01_D364InputName    OBJECT-TYPE
    SYNTAX           DisplayString
    ACCESS           read-only
    STATUS           mandatory
    DESCRIPTION
    "Name of station object."
    ::=   { b01_D364InputTableEntry 2 }

b01_D364InputValue    OBJECT-TYPE
    SYNTAX           DisplayString
    ACCESS           read-write
    STATUS           mandatory
    DESCRIPTION
    "Current value of station object. Is read-write ."
    ::=   { b01_D364InputTableEntry 3 }



-- ***********************************
-- *
-- *  B01_D364Output table declarations
-- *
-- ***********************************

b01_D364OutputTable   OBJECT-TYPE
    SYNTAX                SEQUENCE OF B01_D364OutputTableEntry
    ACCESS                not-accessible
    STATUS                mandatory
    DESCRIPTION
    "A list of snmp b01_D364Output (read-only) object values."
    ::=  { b01_D364 2 }

b01_D364OutputTableEntry  OBJECT-TYPE
    SYNTAX                B01_D364OutputTableEntry
    ACCESS                not-accessible
    STATUS                mandatory
    DESCRIPTION
    "An b01_D364Output table entry containing data for a specific b01_D364Output."
    INDEX  { b01_D364OutputIndex }  ::=   { b01_D364OutputTable 1 }

B01_D364OutputTableEntry ::= SEQUENCE {
        b01_D364OutputIndex       INTEGER,
        b01_D364OutputName        DisplayString,
        b01_D364OutputValue       DisplayString
    }

b01_D364OutputIndex   OBJECT-TYPE
    SYNTAX           INTEGER(0..2147483647)
    ACCESS           read-only
    STATUS           mandatory
    DESCRIPTION
    "The index in the b01_D364Output table for a particular snmp b01_D364Output
	 object.  Used to address table entries."
    ::=   { b01_D364OutputTableEntry 1 }


b01_D364OutputName    OBJECT-TYPE
    SYNTAX           DisplayString
    ACCESS           read-only
    STATUS           mandatory
    DESCRIPTION
    "Name of station object."
    ::=   { b01_D364OutputTableEntry 2 }

b01_D364OutputValue    OBJECT-TYPE
    SYNTAX           DisplayString
    ACCESS           read-only
    STATUS           mandatory
    DESCRIPTION
    "Current value of station object. Is read-only ."
    ::=   { b01_D364OutputTableEntry 3 }


-- ***********************************
-- *
-- *  B01_D365
-- *
-- ***********************************
    b01_D365    OBJECT IDENTIFIER ::= { exportTables 38 }

-- ***********************************
-- *
-- *  B01_D365Input table declarations
-- *
-- ***********************************

b01_D365InputTable   OBJECT-TYPE
    SYNTAX                SEQUENCE OF B01_D365InputTableEntry
    ACCESS                not-accessible
    STATUS                mandatory
    DESCRIPTION
    "A list of snmp b01_D365Input (read-only) object values."
    ::=  { b01_D365 1 }

b01_D365InputTableEntry  OBJECT-TYPE
    SYNTAX                B01_D365InputTableEntry
    ACCESS                not-accessible
    STATUS                mandatory
    DESCRIPTION
    "An b01_D365Input table entry containing data for a specific b01_D365Input."
    INDEX  { b01_D365InputIndex }  ::=   { b01_D365InputTable 1 }

B01_D365InputTableEntry ::= SEQUENCE {
        b01_D365InputIndex       INTEGER,
        b01_D365InputName        DisplayString,
        b01_D365InputValue       DisplayString
    }

b01_D365InputIndex   OBJECT-TYPE
    SYNTAX           INTEGER(0..2147483647)
    ACCESS           read-only
    STATUS           mandatory
    DESCRIPTION
    "The index in the b01_D365Input table for a particular snmp b01_D365Input
	 object.  Used to address table entries."
    ::=   { b01_D365InputTableEntry 1 }


b01_D365InputName    OBJECT-TYPE
    SYNTAX           DisplayString
    ACCESS           read-only
    STATUS           mandatory
    DESCRIPTION
    "Name of station object."
    ::=   { b01_D365InputTableEntry 2 }

b01_D365InputValue    OBJECT-TYPE
    SYNTAX           DisplayString
    ACCESS           read-write
    STATUS           mandatory
    DESCRIPTION
    "Current value of station object. Is read-write ."
    ::=   { b01_D365InputTableEntry 3 }



-- ***********************************
-- *
-- *  B01_D365Output table declarations
-- *
-- ***********************************

b01_D365OutputTable   OBJECT-TYPE
    SYNTAX                SEQUENCE OF B01_D365OutputTableEntry
    ACCESS                not-accessible
    STATUS                mandatory
    DESCRIPTION
    "A list of snmp b01_D365Output (read-only) object values."
    ::=  { b01_D365 2 }

b01_D365OutputTableEntry  OBJECT-TYPE
    SYNTAX                B01_D365OutputTableEntry
    ACCESS                not-accessible
    STATUS                mandatory
    DESCRIPTION
    "An b01_D365Output table entry containing data for a specific b01_D365Output."
    INDEX  { b01_D365OutputIndex }  ::=   { b01_D365OutputTable 1 }

B01_D365OutputTableEntry ::= SEQUENCE {
        b01_D365OutputIndex       INTEGER,
        b01_D365OutputName        DisplayString,
        b01_D365OutputValue       DisplayString
    }

b01_D365OutputIndex   OBJECT-TYPE
    SYNTAX           INTEGER(0..2147483647)
    ACCESS           read-only
    STATUS           mandatory
    DESCRIPTION
    "The index in the b01_D365Output table for a particular snmp b01_D365Output
	 object.  Used to address table entries."
    ::=   { b01_D365OutputTableEntry 1 }


b01_D365OutputName    OBJECT-TYPE
    SYNTAX           DisplayString
    ACCESS           read-only
    STATUS           mandatory
    DESCRIPTION
    "Name of station object."
    ::=   { b01_D365OutputTableEntry 2 }

b01_D365OutputValue    OBJECT-TYPE
    SYNTAX           DisplayString
    ACCESS           read-only
    STATUS           mandatory
    DESCRIPTION
    "Current value of station object. Is read-only ."
    ::=   { b01_D365OutputTableEntry 3 }


-- ***********************************
-- *
-- *  B01_D367
-- *
-- ***********************************
    b01_D367    OBJECT IDENTIFIER ::= { exportTables 39 }

-- ***********************************
-- *
-- *  B01_D367Input table declarations
-- *
-- ***********************************

b01_D367InputTable   OBJECT-TYPE
    SYNTAX                SEQUENCE OF B01_D367InputTableEntry
    ACCESS                not-accessible
    STATUS                mandatory
    DESCRIPTION
    "A list of snmp b01_D367Input (read-only) object values."
    ::=  { b01_D367 1 }

b01_D367InputTableEntry  OBJECT-TYPE
    SYNTAX                B01_D367InputTableEntry
    ACCESS                not-accessible
    STATUS                mandatory
    DESCRIPTION
    "An b01_D367Input table entry containing data for a specific b01_D367Input."
    INDEX  { b01_D367InputIndex }  ::=   { b01_D367InputTable 1 }

B01_D367InputTableEntry ::= SEQUENCE {
        b01_D367InputIndex       INTEGER,
        b01_D367InputName        DisplayString,
        b01_D367InputValue       DisplayString
    }

b01_D367InputIndex   OBJECT-TYPE
    SYNTAX           INTEGER(0..2147483647)
    ACCESS           read-only
    STATUS           mandatory
    DESCRIPTION
    "The index in the b01_D367Input table for a particular snmp b01_D367Input
	 object.  Used to address table entries."
    ::=   { b01_D367InputTableEntry 1 }


b01_D367InputName    OBJECT-TYPE
    SYNTAX           DisplayString
    ACCESS           read-only
    STATUS           mandatory
    DESCRIPTION
    "Name of station object."
    ::=   { b01_D367InputTableEntry 2 }

b01_D367InputValue    OBJECT-TYPE
    SYNTAX           DisplayString
    ACCESS           read-write
    STATUS           mandatory
    DESCRIPTION
    "Current value of station object. Is read-write ."
    ::=   { b01_D367InputTableEntry 3 }



-- ***********************************
-- *
-- *  B01_D367Output table declarations
-- *
-- ***********************************

b01_D367OutputTable   OBJECT-TYPE
    SYNTAX                SEQUENCE OF B01_D367OutputTableEntry
    ACCESS                not-accessible
    STATUS                mandatory
    DESCRIPTION
    "A list of snmp b01_D367Output (read-only) object values."
    ::=  { b01_D367 2 }

b01_D367OutputTableEntry  OBJECT-TYPE
    SYNTAX                B01_D367OutputTableEntry
    ACCESS                not-accessible
    STATUS                mandatory
    DESCRIPTION
    "An b01_D367Output table entry containing data for a specific b01_D367Output."
    INDEX  { b01_D367OutputIndex }  ::=   { b01_D367OutputTable 1 }

B01_D367OutputTableEntry ::= SEQUENCE {
        b01_D367OutputIndex       INTEGER,
        b01_D367OutputName        DisplayString,
        b01_D367OutputValue       DisplayString
    }

b01_D367OutputIndex   OBJECT-TYPE
    SYNTAX           INTEGER(0..2147483647)
    ACCESS           read-only
    STATUS           mandatory
    DESCRIPTION
    "The index in the b01_D367Output table for a particular snmp b01_D367Output
	 object.  Used to address table entries."
    ::=   { b01_D367OutputTableEntry 1 }


b01_D367OutputName    OBJECT-TYPE
    SYNTAX           DisplayString
    ACCESS           read-only
    STATUS           mandatory
    DESCRIPTION
    "Name of station object."
    ::=   { b01_D367OutputTableEntry 2 }

b01_D367OutputValue    OBJECT-TYPE
    SYNTAX           DisplayString
    ACCESS           read-only
    STATUS           mandatory
    DESCRIPTION
    "Current value of station object. Is read-only ."
    ::=   { b01_D367OutputTableEntry 3 }


-- ***********************************
-- *
-- *  B01_D368
-- *
-- ***********************************
    b01_D368    OBJECT IDENTIFIER ::= { exportTables 40 }

-- ***********************************
-- *
-- *  B01_D368Input table declarations
-- *
-- ***********************************

b01_D368InputTable   OBJECT-TYPE
    SYNTAX                SEQUENCE OF B01_D368InputTableEntry
    ACCESS                not-accessible
    STATUS                mandatory
    DESCRIPTION
    "A list of snmp b01_D368Input (read-only) object values."
    ::=  { b01_D368 1 }

b01_D368InputTableEntry  OBJECT-TYPE
    SYNTAX                B01_D368InputTableEntry
    ACCESS                not-accessible
    STATUS                mandatory
    DESCRIPTION
    "An b01_D368Input table entry containing data for a specific b01_D368Input."
    INDEX  { b01_D368InputIndex }  ::=   { b01_D368InputTable 1 }

B01_D368InputTableEntry ::= SEQUENCE {
        b01_D368InputIndex       INTEGER,
        b01_D368InputName        DisplayString,
        b01_D368InputValue       DisplayString
    }

b01_D368InputIndex   OBJECT-TYPE
    SYNTAX           INTEGER(0..2147483647)
    ACCESS           read-only
    STATUS           mandatory
    DESCRIPTION
    "The index in the b01_D368Input table for a particular snmp b01_D368Input
	 object.  Used to address table entries."
    ::=   { b01_D368InputTableEntry 1 }


b01_D368InputName    OBJECT-TYPE
    SYNTAX           DisplayString
    ACCESS           read-only
    STATUS           mandatory
    DESCRIPTION
    "Name of station object."
    ::=   { b01_D368InputTableEntry 2 }

b01_D368InputValue    OBJECT-TYPE
    SYNTAX           DisplayString
    ACCESS           read-write
    STATUS           mandatory
    DESCRIPTION
    "Current value of station object. Is read-write ."
    ::=   { b01_D368InputTableEntry 3 }



-- ***********************************
-- *
-- *  B01_D368Output table declarations
-- *
-- ***********************************

b01_D368OutputTable   OBJECT-TYPE
    SYNTAX                SEQUENCE OF B01_D368OutputTableEntry
    ACCESS                not-accessible
    STATUS                mandatory
    DESCRIPTION
    "A list of snmp b01_D368Output (read-only) object values."
    ::=  { b01_D368 2 }

b01_D368OutputTableEntry  OBJECT-TYPE
    SYNTAX                B01_D368OutputTableEntry
    ACCESS                not-accessible
    STATUS                mandatory
    DESCRIPTION
    "An b01_D368Output table entry containing data for a specific b01_D368Output."
    INDEX  { b01_D368OutputIndex }  ::=   { b01_D368OutputTable 1 }

B01_D368OutputTableEntry ::= SEQUENCE {
        b01_D368OutputIndex       INTEGER,
        b01_D368OutputName        DisplayString,
        b01_D368OutputValue       DisplayString
    }

b01_D368OutputIndex   OBJECT-TYPE
    SYNTAX           INTEGER(0..2147483647)
    ACCESS           read-only
    STATUS           mandatory
    DESCRIPTION
    "The index in the b01_D368Output table for a particular snmp b01_D368Output
	 object.  Used to address table entries."
    ::=   { b01_D368OutputTableEntry 1 }


b01_D368OutputName    OBJECT-TYPE
    SYNTAX           DisplayString
    ACCESS           read-only
    STATUS           mandatory
    DESCRIPTION
    "Name of station object."
    ::=   { b01_D368OutputTableEntry 2 }

b01_D368OutputValue    OBJECT-TYPE
    SYNTAX           DisplayString
    ACCESS           read-only
    STATUS           mandatory
    DESCRIPTION
    "Current value of station object. Is read-only ."
    ::=   { b01_D368OutputTableEntry 3 }


-- ***********************************
-- *
-- *  B01_D369
-- *
-- ***********************************
    b01_D369    OBJECT IDENTIFIER ::= { exportTables 41 }

-- ***********************************
-- *
-- *  B01_D369Input table declarations
-- *
-- ***********************************

b01_D369InputTable   OBJECT-TYPE
    SYNTAX                SEQUENCE OF B01_D369InputTableEntry
    ACCESS                not-accessible
    STATUS                mandatory
    DESCRIPTION
    "A list of snmp b01_D369Input (read-only) object values."
    ::=  { b01_D369 1 }

b01_D369InputTableEntry  OBJECT-TYPE
    SYNTAX                B01_D369InputTableEntry
    ACCESS                not-accessible
    STATUS                mandatory
    DESCRIPTION
    "An b01_D369Input table entry containing data for a specific b01_D369Input."
    INDEX  { b01_D369InputIndex }  ::=   { b01_D369InputTable 1 }

B01_D369InputTableEntry ::= SEQUENCE {
        b01_D369InputIndex       INTEGER,
        b01_D369InputName        DisplayString,
        b01_D369InputValue       DisplayString
    }

b01_D369InputIndex   OBJECT-TYPE
    SYNTAX           INTEGER(0..2147483647)
    ACCESS           read-only
    STATUS           mandatory
    DESCRIPTION
    "The index in the b01_D369Input table for a particular snmp b01_D369Input
	 object.  Used to address table entries."
    ::=   { b01_D369InputTableEntry 1 }


b01_D369InputName    OBJECT-TYPE
    SYNTAX           DisplayString
    ACCESS           read-only
    STATUS           mandatory
    DESCRIPTION
    "Name of station object."
    ::=   { b01_D369InputTableEntry 2 }

b01_D369InputValue    OBJECT-TYPE
    SYNTAX           DisplayString
    ACCESS           read-write
    STATUS           mandatory
    DESCRIPTION
    "Current value of station object. Is read-write ."
    ::=   { b01_D369InputTableEntry 3 }



-- ***********************************
-- *
-- *  B01_D369Output table declarations
-- *
-- ***********************************

b01_D369OutputTable   OBJECT-TYPE
    SYNTAX                SEQUENCE OF B01_D369OutputTableEntry
    ACCESS                not-accessible
    STATUS                mandatory
    DESCRIPTION
    "A list of snmp b01_D369Output (read-only) object values."
    ::=  { b01_D369 2 }

b01_D369OutputTableEntry  OBJECT-TYPE
    SYNTAX                B01_D369OutputTableEntry
    ACCESS                not-accessible
    STATUS                mandatory
    DESCRIPTION
    "An b01_D369Output table entry containing data for a specific b01_D369Output."
    INDEX  { b01_D369OutputIndex }  ::=   { b01_D369OutputTable 1 }

B01_D369OutputTableEntry ::= SEQUENCE {
        b01_D369OutputIndex       INTEGER,
        b01_D369OutputName        DisplayString,
        b01_D369OutputValue       DisplayString
    }

b01_D369OutputIndex   OBJECT-TYPE
    SYNTAX           INTEGER(0..2147483647)
    ACCESS           read-only
    STATUS           mandatory
    DESCRIPTION
    "The index in the b01_D369Output table for a particular snmp b01_D369Output
	 object.  Used to address table entries."
    ::=   { b01_D369OutputTableEntry 1 }


b01_D369OutputName    OBJECT-TYPE
    SYNTAX           DisplayString
    ACCESS           read-only
    STATUS           mandatory
    DESCRIPTION
    "Name of station object."
    ::=   { b01_D369OutputTableEntry 2 }

b01_D369OutputValue    OBJECT-TYPE
    SYNTAX           DisplayString
    ACCESS           read-only
    STATUS           mandatory
    DESCRIPTION
    "Current value of station object. Is read-only ."
    ::=   { b01_D369OutputTableEntry 3 }


-- ***********************************
-- *
-- *  B01_D370
-- *
-- ***********************************
    b01_D370    OBJECT IDENTIFIER ::= { exportTables 42 }

-- ***********************************
-- *
-- *  B01_D370Input table declarations
-- *
-- ***********************************

b01_D370InputTable   OBJECT-TYPE
    SYNTAX                SEQUENCE OF B01_D370InputTableEntry
    ACCESS                not-accessible
    STATUS                mandatory
    DESCRIPTION
    "A list of snmp b01_D370Input (read-only) object values."
    ::=  { b01_D370 1 }

b01_D370InputTableEntry  OBJECT-TYPE
    SYNTAX                B01_D370InputTableEntry
    ACCESS                not-accessible
    STATUS                mandatory
    DESCRIPTION
    "An b01_D370Input table entry containing data for a specific b01_D370Input."
    INDEX  { b01_D370InputIndex }  ::=   { b01_D370InputTable 1 }

B01_D370InputTableEntry ::= SEQUENCE {
        b01_D370InputIndex       INTEGER,
        b01_D370InputName        DisplayString,
        b01_D370InputValue       DisplayString
    }

b01_D370InputIndex   OBJECT-TYPE
    SYNTAX           INTEGER(0..2147483647)
    ACCESS           read-only
    STATUS           mandatory
    DESCRIPTION
    "The index in the b01_D370Input table for a particular snmp b01_D370Input
	 object.  Used to address table entries."
    ::=   { b01_D370InputTableEntry 1 }


b01_D370InputName    OBJECT-TYPE
    SYNTAX           DisplayString
    ACCESS           read-only
    STATUS           mandatory
    DESCRIPTION
    "Name of station object."
    ::=   { b01_D370InputTableEntry 2 }

b01_D370InputValue    OBJECT-TYPE
    SYNTAX           DisplayString
    ACCESS           read-write
    STATUS           mandatory
    DESCRIPTION
    "Current value of station object. Is read-write ."
    ::=   { b01_D370InputTableEntry 3 }



-- ***********************************
-- *
-- *  B01_D370Output table declarations
-- *
-- ***********************************

b01_D370OutputTable   OBJECT-TYPE
    SYNTAX                SEQUENCE OF B01_D370OutputTableEntry
    ACCESS                not-accessible
    STATUS                mandatory
    DESCRIPTION
    "A list of snmp b01_D370Output (read-only) object values."
    ::=  { b01_D370 2 }

b01_D370OutputTableEntry  OBJECT-TYPE
    SYNTAX                B01_D370OutputTableEntry
    ACCESS                not-accessible
    STATUS                mandatory
    DESCRIPTION
    "An b01_D370Output table entry containing data for a specific b01_D370Output."
    INDEX  { b01_D370OutputIndex }  ::=   { b01_D370OutputTable 1 }

B01_D370OutputTableEntry ::= SEQUENCE {
        b01_D370OutputIndex       INTEGER,
        b01_D370OutputName        DisplayString,
        b01_D370OutputValue       DisplayString
    }

b01_D370OutputIndex   OBJECT-TYPE
    SYNTAX           INTEGER(0..2147483647)
    ACCESS           read-only
    STATUS           mandatory
    DESCRIPTION
    "The index in the b01_D370Output table for a particular snmp b01_D370Output
	 object.  Used to address table entries."
    ::=   { b01_D370OutputTableEntry 1 }


b01_D370OutputName    OBJECT-TYPE
    SYNTAX           DisplayString
    ACCESS           read-only
    STATUS           mandatory
    DESCRIPTION
    "Name of station object."
    ::=   { b01_D370OutputTableEntry 2 }

b01_D370OutputValue    OBJECT-TYPE
    SYNTAX           DisplayString
    ACCESS           read-only
    STATUS           mandatory
    DESCRIPTION
    "Current value of station object. Is read-only ."
    ::=   { b01_D370OutputTableEntry 3 }


-- ***********************************
-- *
-- *  B01_D366
-- *
-- ***********************************
    b01_D366    OBJECT IDENTIFIER ::= { exportTables 43 }

-- ***********************************
-- *
-- *  B01_D366Input table declarations
-- *
-- ***********************************

b01_D366InputTable   OBJECT-TYPE
    SYNTAX                SEQUENCE OF B01_D366InputTableEntry
    ACCESS                not-accessible
    STATUS                mandatory
    DESCRIPTION
    "A list of snmp b01_D366Input (read-only) object values."
    ::=  { b01_D366 1 }

b01_D366InputTableEntry  OBJECT-TYPE
    SYNTAX                B01_D366InputTableEntry
    ACCESS                not-accessible
    STATUS                mandatory
    DESCRIPTION
    "An b01_D366Input table entry containing data for a specific b01_D366Input."
    INDEX  { b01_D366InputIndex }  ::=   { b01_D366InputTable 1 }

B01_D366InputTableEntry ::= SEQUENCE {
        b01_D366InputIndex       INTEGER,
        b01_D366InputName        DisplayString,
        b01_D366InputValue       DisplayString
    }

b01_D366InputIndex   OBJECT-TYPE
    SYNTAX           INTEGER(0..2147483647)
    ACCESS           read-only
    STATUS           mandatory
    DESCRIPTION
    "The index in the b01_D366Input table for a particular snmp b01_D366Input
	 object.  Used to address table entries."
    ::=   { b01_D366InputTableEntry 1 }


b01_D366InputName    OBJECT-TYPE
    SYNTAX           DisplayString
    ACCESS           read-only
    STATUS           mandatory
    DESCRIPTION
    "Name of station object."
    ::=   { b01_D366InputTableEntry 2 }

b01_D366InputValue    OBJECT-TYPE
    SYNTAX           DisplayString
    ACCESS           read-write
    STATUS           mandatory
    DESCRIPTION
    "Current value of station object. Is read-write ."
    ::=   { b01_D366InputTableEntry 3 }



-- ***********************************
-- *
-- *  B01_D366Output table declarations
-- *
-- ***********************************

b01_D366OutputTable   OBJECT-TYPE
    SYNTAX                SEQUENCE OF B01_D366OutputTableEntry
    ACCESS                not-accessible
    STATUS                mandatory
    DESCRIPTION
    "A list of snmp b01_D366Output (read-only) object values."
    ::=  { b01_D366 2 }

b01_D366OutputTableEntry  OBJECT-TYPE
    SYNTAX                B01_D366OutputTableEntry
    ACCESS                not-accessible
    STATUS                mandatory
    DESCRIPTION
    "An b01_D366Output table entry containing data for a specific b01_D366Output."
    INDEX  { b01_D366OutputIndex }  ::=   { b01_D366OutputTable 1 }

B01_D366OutputTableEntry ::= SEQUENCE {
        b01_D366OutputIndex       INTEGER,
        b01_D366OutputName        DisplayString,
        b01_D366OutputValue       DisplayString
    }

b01_D366OutputIndex   OBJECT-TYPE
    SYNTAX           INTEGER(0..2147483647)
    ACCESS           read-only
    STATUS           mandatory
    DESCRIPTION
    "The index in the b01_D366Output table for a particular snmp b01_D366Output
	 object.  Used to address table entries."
    ::=   { b01_D366OutputTableEntry 1 }


b01_D366OutputName    OBJECT-TYPE
    SYNTAX           DisplayString
    ACCESS           read-only
    STATUS           mandatory
    DESCRIPTION
    "Name of station object."
    ::=   { b01_D366OutputTableEntry 2 }

b01_D366OutputValue    OBJECT-TYPE
    SYNTAX           DisplayString
    ACCESS           read-only
    STATUS           mandatory
    DESCRIPTION
    "Current value of station object. Is read-only ."
    ::=   { b01_D366OutputTableEntry 3 }


-- ***********************************
-- *
-- *  B01_D212
-- *
-- ***********************************
    b01_D212    OBJECT IDENTIFIER ::= { exportTables 44 }

-- ***********************************
-- *
-- *  B01_D212Input table declarations
-- *
-- ***********************************

b01_D212InputTable   OBJECT-TYPE
    SYNTAX                SEQUENCE OF B01_D212InputTableEntry
    ACCESS                not-accessible
    STATUS                mandatory
    DESCRIPTION
    "A list of snmp b01_D212Input (read-only) object values."
    ::=  { b01_D212 1 }

b01_D212InputTableEntry  OBJECT-TYPE
    SYNTAX                B01_D212InputTableEntry
    ACCESS                not-accessible
    STATUS                mandatory
    DESCRIPTION
    "An b01_D212Input table entry containing data for a specific b01_D212Input."
    INDEX  { b01_D212InputIndex }  ::=   { b01_D212InputTable 1 }

B01_D212InputTableEntry ::= SEQUENCE {
        b01_D212InputIndex       INTEGER,
        b01_D212InputName        DisplayString,
        b01_D212InputValue       DisplayString
    }

b01_D212InputIndex   OBJECT-TYPE
    SYNTAX           INTEGER(0..2147483647)
    ACCESS           read-only
    STATUS           mandatory
    DESCRIPTION
    "The index in the b01_D212Input table for a particular snmp b01_D212Input
	 object.  Used to address table entries."
    ::=   { b01_D212InputTableEntry 1 }


b01_D212InputName    OBJECT-TYPE
    SYNTAX           DisplayString
    ACCESS           read-only
    STATUS           mandatory
    DESCRIPTION
    "Name of station object."
    ::=   { b01_D212InputTableEntry 2 }

b01_D212InputValue    OBJECT-TYPE
    SYNTAX           DisplayString
    ACCESS           read-write
    STATUS           mandatory
    DESCRIPTION
    "Current value of station object. Is read-write ."
    ::=   { b01_D212InputTableEntry 3 }



-- ***********************************
-- *
-- *  B01_D212Output table declarations
-- *
-- ***********************************

b01_D212OutputTable   OBJECT-TYPE
    SYNTAX                SEQUENCE OF B01_D212OutputTableEntry
    ACCESS                not-accessible
    STATUS                mandatory
    DESCRIPTION
    "A list of snmp b01_D212Output (read-only) object values."
    ::=  { b01_D212 2 }

b01_D212OutputTableEntry  OBJECT-TYPE
    SYNTAX                B01_D212OutputTableEntry
    ACCESS                not-accessible
    STATUS                mandatory
    DESCRIPTION
    "An b01_D212Output table entry containing data for a specific b01_D212Output."
    INDEX  { b01_D212OutputIndex }  ::=   { b01_D212OutputTable 1 }

B01_D212OutputTableEntry ::= SEQUENCE {
        b01_D212OutputIndex       INTEGER,
        b01_D212OutputName        DisplayString,
        b01_D212OutputValue       DisplayString
    }

b01_D212OutputIndex   OBJECT-TYPE
    SYNTAX           INTEGER(0..2147483647)
    ACCESS           read-only
    STATUS           mandatory
    DESCRIPTION
    "The index in the b01_D212Output table for a particular snmp b01_D212Output
	 object.  Used to address table entries."
    ::=   { b01_D212OutputTableEntry 1 }


b01_D212OutputName    OBJECT-TYPE
    SYNTAX           DisplayString
    ACCESS           read-only
    STATUS           mandatory
    DESCRIPTION
    "Name of station object."
    ::=   { b01_D212OutputTableEntry 2 }

b01_D212OutputValue    OBJECT-TYPE
    SYNTAX           DisplayString
    ACCESS           read-only
    STATUS           mandatory
    DESCRIPTION
    "Current value of station object. Is read-only ."
    ::=   { b01_D212OutputTableEntry 3 }


-- ***********************************
-- *
-- *  B01_D213
-- *
-- ***********************************
    b01_D213    OBJECT IDENTIFIER ::= { exportTables 45 }

-- ***********************************
-- *
-- *  B01_D213Input table declarations
-- *
-- ***********************************

b01_D213InputTable   OBJECT-TYPE
    SYNTAX                SEQUENCE OF B01_D213InputTableEntry
    ACCESS                not-accessible
    STATUS                mandatory
    DESCRIPTION
    "A list of snmp b01_D213Input (read-only) object values."
    ::=  { b01_D213 1 }

b01_D213InputTableEntry  OBJECT-TYPE
    SYNTAX                B01_D213InputTableEntry
    ACCESS                not-accessible
    STATUS                mandatory
    DESCRIPTION
    "An b01_D213Input table entry containing data for a specific b01_D213Input."
    INDEX  { b01_D213InputIndex }  ::=   { b01_D213InputTable 1 }

B01_D213InputTableEntry ::= SEQUENCE {
        b01_D213InputIndex       INTEGER,
        b01_D213InputName        DisplayString,
        b01_D213InputValue       DisplayString
    }

b01_D213InputIndex   OBJECT-TYPE
    SYNTAX           INTEGER(0..2147483647)
    ACCESS           read-only
    STATUS           mandatory
    DESCRIPTION
    "The index in the b01_D213Input table for a particular snmp b01_D213Input
	 object.  Used to address table entries."
    ::=   { b01_D213InputTableEntry 1 }


b01_D213InputName    OBJECT-TYPE
    SYNTAX           DisplayString
    ACCESS           read-only
    STATUS           mandatory
    DESCRIPTION
    "Name of station object."
    ::=   { b01_D213InputTableEntry 2 }

b01_D213InputValue    OBJECT-TYPE
    SYNTAX           DisplayString
    ACCESS           read-write
    STATUS           mandatory
    DESCRIPTION
    "Current value of station object. Is read-write ."
    ::=   { b01_D213InputTableEntry 3 }



-- ***********************************
-- *
-- *  B01_D213Output table declarations
-- *
-- ***********************************

b01_D213OutputTable   OBJECT-TYPE
    SYNTAX                SEQUENCE OF B01_D213OutputTableEntry
    ACCESS                not-accessible
    STATUS                mandatory
    DESCRIPTION
    "A list of snmp b01_D213Output (read-only) object values."
    ::=  { b01_D213 2 }

b01_D213OutputTableEntry  OBJECT-TYPE
    SYNTAX                B01_D213OutputTableEntry
    ACCESS                not-accessible
    STATUS                mandatory
    DESCRIPTION
    "An b01_D213Output table entry containing data for a specific b01_D213Output."
    INDEX  { b01_D213OutputIndex }  ::=   { b01_D213OutputTable 1 }

B01_D213OutputTableEntry ::= SEQUENCE {
        b01_D213OutputIndex       INTEGER,
        b01_D213OutputName        DisplayString,
        b01_D213OutputValue       DisplayString
    }

b01_D213OutputIndex   OBJECT-TYPE
    SYNTAX           INTEGER(0..2147483647)
    ACCESS           read-only
    STATUS           mandatory
    DESCRIPTION
    "The index in the b01_D213Output table for a particular snmp b01_D213Output
	 object.  Used to address table entries."
    ::=   { b01_D213OutputTableEntry 1 }


b01_D213OutputName    OBJECT-TYPE
    SYNTAX           DisplayString
    ACCESS           read-only
    STATUS           mandatory
    DESCRIPTION
    "Name of station object."
    ::=   { b01_D213OutputTableEntry 2 }

b01_D213OutputValue    OBJECT-TYPE
    SYNTAX           DisplayString
    ACCESS           read-only
    STATUS           mandatory
    DESCRIPTION
    "Current value of station object. Is read-only ."
    ::=   { b01_D213OutputTableEntry 3 }


-- ***********************************
-- *
-- *  B01_D260
-- *
-- ***********************************
    b01_D260    OBJECT IDENTIFIER ::= { exportTables 46 }

-- ***********************************
-- *
-- *  B01_D260Input table declarations
-- *
-- ***********************************

b01_D260InputTable   OBJECT-TYPE
    SYNTAX                SEQUENCE OF B01_D260InputTableEntry
    ACCESS                not-accessible
    STATUS                mandatory
    DESCRIPTION
    "A list of snmp b01_D260Input (read-only) object values."
    ::=  { b01_D260 1 }

b01_D260InputTableEntry  OBJECT-TYPE
    SYNTAX                B01_D260InputTableEntry
    ACCESS                not-accessible
    STATUS                mandatory
    DESCRIPTION
    "An b01_D260Input table entry containing data for a specific b01_D260Input."
    INDEX  { b01_D260InputIndex }  ::=   { b01_D260InputTable 1 }

B01_D260InputTableEntry ::= SEQUENCE {
        b01_D260InputIndex       INTEGER,
        b01_D260InputName        DisplayString,
        b01_D260InputValue       DisplayString
    }

b01_D260InputIndex   OBJECT-TYPE
    SYNTAX           INTEGER(0..2147483647)
    ACCESS           read-only
    STATUS           mandatory
    DESCRIPTION
    "The index in the b01_D260Input table for a particular snmp b01_D260Input
	 object.  Used to address table entries."
    ::=   { b01_D260InputTableEntry 1 }


b01_D260InputName    OBJECT-TYPE
    SYNTAX           DisplayString
    ACCESS           read-only
    STATUS           mandatory
    DESCRIPTION
    "Name of station object."
    ::=   { b01_D260InputTableEntry 2 }

b01_D260InputValue    OBJECT-TYPE
    SYNTAX           DisplayString
    ACCESS           read-write
    STATUS           mandatory
    DESCRIPTION
    "Current value of station object. Is read-write ."
    ::=   { b01_D260InputTableEntry 3 }



-- ***********************************
-- *
-- *  B01_D260Output table declarations
-- *
-- ***********************************

b01_D260OutputTable   OBJECT-TYPE
    SYNTAX                SEQUENCE OF B01_D260OutputTableEntry
    ACCESS                not-accessible
    STATUS                mandatory
    DESCRIPTION
    "A list of snmp b01_D260Output (read-only) object values."
    ::=  { b01_D260 2 }

b01_D260OutputTableEntry  OBJECT-TYPE
    SYNTAX                B01_D260OutputTableEntry
    ACCESS                not-accessible
    STATUS                mandatory
    DESCRIPTION
    "An b01_D260Output table entry containing data for a specific b01_D260Output."
    INDEX  { b01_D260OutputIndex }  ::=   { b01_D260OutputTable 1 }

B01_D260OutputTableEntry ::= SEQUENCE {
        b01_D260OutputIndex       INTEGER,
        b01_D260OutputName        DisplayString,
        b01_D260OutputValue       DisplayString
    }

b01_D260OutputIndex   OBJECT-TYPE
    SYNTAX           INTEGER(0..2147483647)
    ACCESS           read-only
    STATUS           mandatory
    DESCRIPTION
    "The index in the b01_D260Output table for a particular snmp b01_D260Output
	 object.  Used to address table entries."
    ::=   { b01_D260OutputTableEntry 1 }


b01_D260OutputName    OBJECT-TYPE
    SYNTAX           DisplayString
    ACCESS           read-only
    STATUS           mandatory
    DESCRIPTION
    "Name of station object."
    ::=   { b01_D260OutputTableEntry 2 }

b01_D260OutputValue    OBJECT-TYPE
    SYNTAX           DisplayString
    ACCESS           read-only
    STATUS           mandatory
    DESCRIPTION
    "Current value of station object. Is read-only ."
    ::=   { b01_D260OutputTableEntry 3 }


-- ***********************************
-- *
-- *  B01_D261
-- *
-- ***********************************
    b01_D261    OBJECT IDENTIFIER ::= { exportTables 47 }

-- ***********************************
-- *
-- *  B01_D261Input table declarations
-- *
-- ***********************************

b01_D261InputTable   OBJECT-TYPE
    SYNTAX                SEQUENCE OF B01_D261InputTableEntry
    ACCESS                not-accessible
    STATUS                mandatory
    DESCRIPTION
    "A list of snmp b01_D261Input (read-only) object values."
    ::=  { b01_D261 1 }

b01_D261InputTableEntry  OBJECT-TYPE
    SYNTAX                B01_D261InputTableEntry
    ACCESS                not-accessible
    STATUS                mandatory
    DESCRIPTION
    "An b01_D261Input table entry containing data for a specific b01_D261Input."
    INDEX  { b01_D261InputIndex }  ::=   { b01_D261InputTable 1 }

B01_D261InputTableEntry ::= SEQUENCE {
        b01_D261InputIndex       INTEGER,
        b01_D261InputName        DisplayString,
        b01_D261InputValue       DisplayString
    }

b01_D261InputIndex   OBJECT-TYPE
    SYNTAX           INTEGER(0..2147483647)
    ACCESS           read-only
    STATUS           mandatory
    DESCRIPTION
    "The index in the b01_D261Input table for a particular snmp b01_D261Input
	 object.  Used to address table entries."
    ::=   { b01_D261InputTableEntry 1 }


b01_D261InputName    OBJECT-TYPE
    SYNTAX           DisplayString
    ACCESS           read-only
    STATUS           mandatory
    DESCRIPTION
    "Name of station object."
    ::=   { b01_D261InputTableEntry 2 }

b01_D261InputValue    OBJECT-TYPE
    SYNTAX           DisplayString
    ACCESS           read-write
    STATUS           mandatory
    DESCRIPTION
    "Current value of station object. Is read-write ."
    ::=   { b01_D261InputTableEntry 3 }



-- ***********************************
-- *
-- *  B01_D261Output table declarations
-- *
-- ***********************************

b01_D261OutputTable   OBJECT-TYPE
    SYNTAX                SEQUENCE OF B01_D261OutputTableEntry
    ACCESS                not-accessible
    STATUS                mandatory
    DESCRIPTION
    "A list of snmp b01_D261Output (read-only) object values."
    ::=  { b01_D261 2 }

b01_D261OutputTableEntry  OBJECT-TYPE
    SYNTAX                B01_D261OutputTableEntry
    ACCESS                not-accessible
    STATUS                mandatory
    DESCRIPTION
    "An b01_D261Output table entry containing data for a specific b01_D261Output."
    INDEX  { b01_D261OutputIndex }  ::=   { b01_D261OutputTable 1 }

B01_D261OutputTableEntry ::= SEQUENCE {
        b01_D261OutputIndex       INTEGER,
        b01_D261OutputName        DisplayString,
        b01_D261OutputValue       DisplayString
    }

b01_D261OutputIndex   OBJECT-TYPE
    SYNTAX           INTEGER(0..2147483647)
    ACCESS           read-only
    STATUS           mandatory
    DESCRIPTION
    "The index in the b01_D261Output table for a particular snmp b01_D261Output
	 object.  Used to address table entries."
    ::=   { b01_D261OutputTableEntry 1 }


b01_D261OutputName    OBJECT-TYPE
    SYNTAX           DisplayString
    ACCESS           read-only
    STATUS           mandatory
    DESCRIPTION
    "Name of station object."
    ::=   { b01_D261OutputTableEntry 2 }

b01_D261OutputValue    OBJECT-TYPE
    SYNTAX           DisplayString
    ACCESS           read-only
    STATUS           mandatory
    DESCRIPTION
    "Current value of station object. Is read-only ."
    ::=   { b01_D261OutputTableEntry 3 }


-- ***********************************
-- *
-- *  B01_D262
-- *
-- ***********************************
    b01_D262    OBJECT IDENTIFIER ::= { exportTables 48 }

-- ***********************************
-- *
-- *  B01_D262Input table declarations
-- *
-- ***********************************

b01_D262InputTable   OBJECT-TYPE
    SYNTAX                SEQUENCE OF B01_D262InputTableEntry
    ACCESS                not-accessible
    STATUS                mandatory
    DESCRIPTION
    "A list of snmp b01_D262Input (read-only) object values."
    ::=  { b01_D262 1 }

b01_D262InputTableEntry  OBJECT-TYPE
    SYNTAX                B01_D262InputTableEntry
    ACCESS                not-accessible
    STATUS                mandatory
    DESCRIPTION
    "An b01_D262Input table entry containing data for a specific b01_D262Input."
    INDEX  { b01_D262InputIndex }  ::=   { b01_D262InputTable 1 }

B01_D262InputTableEntry ::= SEQUENCE {
        b01_D262InputIndex       INTEGER,
        b01_D262InputName        DisplayString,
        b01_D262InputValue       DisplayString
    }

b01_D262InputIndex   OBJECT-TYPE
    SYNTAX           INTEGER(0..2147483647)
    ACCESS           read-only
    STATUS           mandatory
    DESCRIPTION
    "The index in the b01_D262Input table for a particular snmp b01_D262Input
	 object.  Used to address table entries."
    ::=   { b01_D262InputTableEntry 1 }


b01_D262InputName    OBJECT-TYPE
    SYNTAX           DisplayString
    ACCESS           read-only
    STATUS           mandatory
    DESCRIPTION
    "Name of station object."
    ::=   { b01_D262InputTableEntry 2 }

b01_D262InputValue    OBJECT-TYPE
    SYNTAX           DisplayString
    ACCESS           read-write
    STATUS           mandatory
    DESCRIPTION
    "Current value of station object. Is read-write ."
    ::=   { b01_D262InputTableEntry 3 }



-- ***********************************
-- *
-- *  B01_D262Output table declarations
-- *
-- ***********************************

b01_D262OutputTable   OBJECT-TYPE
    SYNTAX                SEQUENCE OF B01_D262OutputTableEntry
    ACCESS                not-accessible
    STATUS                mandatory
    DESCRIPTION
    "A list of snmp b01_D262Output (read-only) object values."
    ::=  { b01_D262 2 }

b01_D262OutputTableEntry  OBJECT-TYPE
    SYNTAX                B01_D262OutputTableEntry
    ACCESS                not-accessible
    STATUS                mandatory
    DESCRIPTION
    "An b01_D262Output table entry containing data for a specific b01_D262Output."
    INDEX  { b01_D262OutputIndex }  ::=   { b01_D262OutputTable 1 }

B01_D262OutputTableEntry ::= SEQUENCE {
        b01_D262OutputIndex       INTEGER,
        b01_D262OutputName        DisplayString,
        b01_D262OutputValue       DisplayString
    }

b01_D262OutputIndex   OBJECT-TYPE
    SYNTAX           INTEGER(0..2147483647)
    ACCESS           read-only
    STATUS           mandatory
    DESCRIPTION
    "The index in the b01_D262Output table for a particular snmp b01_D262Output
	 object.  Used to address table entries."
    ::=   { b01_D262OutputTableEntry 1 }


b01_D262OutputName    OBJECT-TYPE
    SYNTAX           DisplayString
    ACCESS           read-only
    STATUS           mandatory
    DESCRIPTION
    "Name of station object."
    ::=   { b01_D262OutputTableEntry 2 }

b01_D262OutputValue    OBJECT-TYPE
    SYNTAX           DisplayString
    ACCESS           read-only
    STATUS           mandatory
    DESCRIPTION
    "Current value of station object. Is read-only ."
    ::=   { b01_D262OutputTableEntry 3 }


-- ***********************************
-- *
-- *  B01_D263
-- *
-- ***********************************
    b01_D263    OBJECT IDENTIFIER ::= { exportTables 49 }

-- ***********************************
-- *
-- *  B01_D263Input table declarations
-- *
-- ***********************************

b01_D263InputTable   OBJECT-TYPE
    SYNTAX                SEQUENCE OF B01_D263InputTableEntry
    ACCESS                not-accessible
    STATUS                mandatory
    DESCRIPTION
    "A list of snmp b01_D263Input (read-only) object values."
    ::=  { b01_D263 1 }

b01_D263InputTableEntry  OBJECT-TYPE
    SYNTAX                B01_D263InputTableEntry
    ACCESS                not-accessible
    STATUS                mandatory
    DESCRIPTION
    "An b01_D263Input table entry containing data for a specific b01_D263Input."
    INDEX  { b01_D263InputIndex }  ::=   { b01_D263InputTable 1 }

B01_D263InputTableEntry ::= SEQUENCE {
        b01_D263InputIndex       INTEGER,
        b01_D263InputName        DisplayString,
        b01_D263InputValue       DisplayString
    }

b01_D263InputIndex   OBJECT-TYPE
    SYNTAX           INTEGER(0..2147483647)
    ACCESS           read-only
    STATUS           mandatory
    DESCRIPTION
    "The index in the b01_D263Input table for a particular snmp b01_D263Input
	 object.  Used to address table entries."
    ::=   { b01_D263InputTableEntry 1 }


b01_D263InputName    OBJECT-TYPE
    SYNTAX           DisplayString
    ACCESS           read-only
    STATUS           mandatory
    DESCRIPTION
    "Name of station object."
    ::=   { b01_D263InputTableEntry 2 }

b01_D263InputValue    OBJECT-TYPE
    SYNTAX           DisplayString
    ACCESS           read-write
    STATUS           mandatory
    DESCRIPTION
    "Current value of station object. Is read-write ."
    ::=   { b01_D263InputTableEntry 3 }



-- ***********************************
-- *
-- *  B01_D263Output table declarations
-- *
-- ***********************************

b01_D263OutputTable   OBJECT-TYPE
    SYNTAX                SEQUENCE OF B01_D263OutputTableEntry
    ACCESS                not-accessible
    STATUS                mandatory
    DESCRIPTION
    "A list of snmp b01_D263Output (read-only) object values."
    ::=  { b01_D263 2 }

b01_D263OutputTableEntry  OBJECT-TYPE
    SYNTAX                B01_D263OutputTableEntry
    ACCESS                not-accessible
    STATUS                mandatory
    DESCRIPTION
    "An b01_D263Output table entry containing data for a specific b01_D263Output."
    INDEX  { b01_D263OutputIndex }  ::=   { b01_D263OutputTable 1 }

B01_D263OutputTableEntry ::= SEQUENCE {
        b01_D263OutputIndex       INTEGER,
        b01_D263OutputName        DisplayString,
        b01_D263OutputValue       DisplayString
    }

b01_D263OutputIndex   OBJECT-TYPE
    SYNTAX           INTEGER(0..2147483647)
    ACCESS           read-only
    STATUS           mandatory
    DESCRIPTION
    "The index in the b01_D263Output table for a particular snmp b01_D263Output
	 object.  Used to address table entries."
    ::=   { b01_D263OutputTableEntry 1 }


b01_D263OutputName    OBJECT-TYPE
    SYNTAX           DisplayString
    ACCESS           read-only
    STATUS           mandatory
    DESCRIPTION
    "Name of station object."
    ::=   { b01_D263OutputTableEntry 2 }

b01_D263OutputValue    OBJECT-TYPE
    SYNTAX           DisplayString
    ACCESS           read-only
    STATUS           mandatory
    DESCRIPTION
    "Current value of station object. Is read-only ."
    ::=   { b01_D263OutputTableEntry 3 }


-- ***********************************
-- *
-- *  B01_D264
-- *
-- ***********************************
    b01_D264    OBJECT IDENTIFIER ::= { exportTables 50 }

-- ***********************************
-- *
-- *  B01_D264Input table declarations
-- *
-- ***********************************

b01_D264InputTable   OBJECT-TYPE
    SYNTAX                SEQUENCE OF B01_D264InputTableEntry
    ACCESS                not-accessible
    STATUS                mandatory
    DESCRIPTION
    "A list of snmp b01_D264Input (read-only) object values."
    ::=  { b01_D264 1 }

b01_D264InputTableEntry  OBJECT-TYPE
    SYNTAX                B01_D264InputTableEntry
    ACCESS                not-accessible
    STATUS                mandatory
    DESCRIPTION
    "An b01_D264Input table entry containing data for a specific b01_D264Input."
    INDEX  { b01_D264InputIndex }  ::=   { b01_D264InputTable 1 }

B01_D264InputTableEntry ::= SEQUENCE {
        b01_D264InputIndex       INTEGER,
        b01_D264InputName        DisplayString,
        b01_D264InputValue       DisplayString
    }

b01_D264InputIndex   OBJECT-TYPE
    SYNTAX           INTEGER(0..2147483647)
    ACCESS           read-only
    STATUS           mandatory
    DESCRIPTION
    "The index in the b01_D264Input table for a particular snmp b01_D264Input
	 object.  Used to address table entries."
    ::=   { b01_D264InputTableEntry 1 }


b01_D264InputName    OBJECT-TYPE
    SYNTAX           DisplayString
    ACCESS           read-only
    STATUS           mandatory
    DESCRIPTION
    "Name of station object."
    ::=   { b01_D264InputTableEntry 2 }

b01_D264InputValue    OBJECT-TYPE
    SYNTAX           DisplayString
    ACCESS           read-write
    STATUS           mandatory
    DESCRIPTION
    "Current value of station object. Is read-write ."
    ::=   { b01_D264InputTableEntry 3 }



-- ***********************************
-- *
-- *  B01_D264Output table declarations
-- *
-- ***********************************

b01_D264OutputTable   OBJECT-TYPE
    SYNTAX                SEQUENCE OF B01_D264OutputTableEntry
    ACCESS                not-accessible
    STATUS                mandatory
    DESCRIPTION
    "A list of snmp b01_D264Output (read-only) object values."
    ::=  { b01_D264 2 }

b01_D264OutputTableEntry  OBJECT-TYPE
    SYNTAX                B01_D264OutputTableEntry
    ACCESS                not-accessible
    STATUS                mandatory
    DESCRIPTION
    "An b01_D264Output table entry containing data for a specific b01_D264Output."
    INDEX  { b01_D264OutputIndex }  ::=   { b01_D264OutputTable 1 }

B01_D264OutputTableEntry ::= SEQUENCE {
        b01_D264OutputIndex       INTEGER,
        b01_D264OutputName        DisplayString,
        b01_D264OutputValue       DisplayString
    }

b01_D264OutputIndex   OBJECT-TYPE
    SYNTAX           INTEGER(0..2147483647)
    ACCESS           read-only
    STATUS           mandatory
    DESCRIPTION
    "The index in the b01_D264Output table for a particular snmp b01_D264Output
	 object.  Used to address table entries."
    ::=   { b01_D264OutputTableEntry 1 }


b01_D264OutputName    OBJECT-TYPE
    SYNTAX           DisplayString
    ACCESS           read-only
    STATUS           mandatory
    DESCRIPTION
    "Name of station object."
    ::=   { b01_D264OutputTableEntry 2 }

b01_D264OutputValue    OBJECT-TYPE
    SYNTAX           DisplayString
    ACCESS           read-only
    STATUS           mandatory
    DESCRIPTION
    "Current value of station object. Is read-only ."
    ::=   { b01_D264OutputTableEntry 3 }


-- ***********************************
-- *
-- *  B01_D265
-- *
-- ***********************************
    b01_D265    OBJECT IDENTIFIER ::= { exportTables 51 }

-- ***********************************
-- *
-- *  B01_D265Input table declarations
-- *
-- ***********************************

b01_D265InputTable   OBJECT-TYPE
    SYNTAX                SEQUENCE OF B01_D265InputTableEntry
    ACCESS                not-accessible
    STATUS                mandatory
    DESCRIPTION
    "A list of snmp b01_D265Input (read-only) object values."
    ::=  { b01_D265 1 }

b01_D265InputTableEntry  OBJECT-TYPE
    SYNTAX                B01_D265InputTableEntry
    ACCESS                not-accessible
    STATUS                mandatory
    DESCRIPTION
    "An b01_D265Input table entry containing data for a specific b01_D265Input."
    INDEX  { b01_D265InputIndex }  ::=   { b01_D265InputTable 1 }

B01_D265InputTableEntry ::= SEQUENCE {
        b01_D265InputIndex       INTEGER,
        b01_D265InputName        DisplayString,
        b01_D265InputValue       DisplayString
    }

b01_D265InputIndex   OBJECT-TYPE
    SYNTAX           INTEGER(0..2147483647)
    ACCESS           read-only
    STATUS           mandatory
    DESCRIPTION
    "The index in the b01_D265Input table for a particular snmp b01_D265Input
	 object.  Used to address table entries."
    ::=   { b01_D265InputTableEntry 1 }


b01_D265InputName    OBJECT-TYPE
    SYNTAX           DisplayString
    ACCESS           read-only
    STATUS           mandatory
    DESCRIPTION
    "Name of station object."
    ::=   { b01_D265InputTableEntry 2 }

b01_D265InputValue    OBJECT-TYPE
    SYNTAX           DisplayString
    ACCESS           read-write
    STATUS           mandatory
    DESCRIPTION
    "Current value of station object. Is read-write ."
    ::=   { b01_D265InputTableEntry 3 }



-- ***********************************
-- *
-- *  B01_D265Output table declarations
-- *
-- ***********************************

b01_D265OutputTable   OBJECT-TYPE
    SYNTAX                SEQUENCE OF B01_D265OutputTableEntry
    ACCESS                not-accessible
    STATUS                mandatory
    DESCRIPTION
    "A list of snmp b01_D265Output (read-only) object values."
    ::=  { b01_D265 2 }

b01_D265OutputTableEntry  OBJECT-TYPE
    SYNTAX                B01_D265OutputTableEntry
    ACCESS                not-accessible
    STATUS                mandatory
    DESCRIPTION
    "An b01_D265Output table entry containing data for a specific b01_D265Output."
    INDEX  { b01_D265OutputIndex }  ::=   { b01_D265OutputTable 1 }

B01_D265OutputTableEntry ::= SEQUENCE {
        b01_D265OutputIndex       INTEGER,
        b01_D265OutputName        DisplayString,
        b01_D265OutputValue       DisplayString
    }

b01_D265OutputIndex   OBJECT-TYPE
    SYNTAX           INTEGER(0..2147483647)
    ACCESS           read-only
    STATUS           mandatory
    DESCRIPTION
    "The index in the b01_D265Output table for a particular snmp b01_D265Output
	 object.  Used to address table entries."
    ::=   { b01_D265OutputTableEntry 1 }


b01_D265OutputName    OBJECT-TYPE
    SYNTAX           DisplayString
    ACCESS           read-only
    STATUS           mandatory
    DESCRIPTION
    "Name of station object."
    ::=   { b01_D265OutputTableEntry 2 }

b01_D265OutputValue    OBJECT-TYPE
    SYNTAX           DisplayString
    ACCESS           read-only
    STATUS           mandatory
    DESCRIPTION
    "Current value of station object. Is read-only ."
    ::=   { b01_D265OutputTableEntry 3 }


-- ***********************************
-- *
-- *  B01_D210
-- *
-- ***********************************
    b01_D210    OBJECT IDENTIFIER ::= { exportTables 52 }

-- ***********************************
-- *
-- *  B01_D210Input table declarations
-- *
-- ***********************************

b01_D210InputTable   OBJECT-TYPE
    SYNTAX                SEQUENCE OF B01_D210InputTableEntry
    ACCESS                not-accessible
    STATUS                mandatory
    DESCRIPTION
    "A list of snmp b01_D210Input (read-only) object values."
    ::=  { b01_D210 1 }

b01_D210InputTableEntry  OBJECT-TYPE
    SYNTAX                B01_D210InputTableEntry
    ACCESS                not-accessible
    STATUS                mandatory
    DESCRIPTION
    "An b01_D210Input table entry containing data for a specific b01_D210Input."
    INDEX  { b01_D210InputIndex }  ::=   { b01_D210InputTable 1 }

B01_D210InputTableEntry ::= SEQUENCE {
        b01_D210InputIndex       INTEGER,
        b01_D210InputName        DisplayString,
        b01_D210InputValue       DisplayString
    }

b01_D210InputIndex   OBJECT-TYPE
    SYNTAX           INTEGER(0..2147483647)
    ACCESS           read-only
    STATUS           mandatory
    DESCRIPTION
    "The index in the b01_D210Input table for a particular snmp b01_D210Input
	 object.  Used to address table entries."
    ::=   { b01_D210InputTableEntry 1 }


b01_D210InputName    OBJECT-TYPE
    SYNTAX           DisplayString
    ACCESS           read-only
    STATUS           mandatory
    DESCRIPTION
    "Name of station object."
    ::=   { b01_D210InputTableEntry 2 }

b01_D210InputValue    OBJECT-TYPE
    SYNTAX           DisplayString
    ACCESS           read-write
    STATUS           mandatory
    DESCRIPTION
    "Current value of station object. Is read-write ."
    ::=   { b01_D210InputTableEntry 3 }



-- ***********************************
-- *
-- *  B01_D210Output table declarations
-- *
-- ***********************************

b01_D210OutputTable   OBJECT-TYPE
    SYNTAX                SEQUENCE OF B01_D210OutputTableEntry
    ACCESS                not-accessible
    STATUS                mandatory
    DESCRIPTION
    "A list of snmp b01_D210Output (read-only) object values."
    ::=  { b01_D210 2 }

b01_D210OutputTableEntry  OBJECT-TYPE
    SYNTAX                B01_D210OutputTableEntry
    ACCESS                not-accessible
    STATUS                mandatory
    DESCRIPTION
    "An b01_D210Output table entry containing data for a specific b01_D210Output."
    INDEX  { b01_D210OutputIndex }  ::=   { b01_D210OutputTable 1 }

B01_D210OutputTableEntry ::= SEQUENCE {
        b01_D210OutputIndex       INTEGER,
        b01_D210OutputName        DisplayString,
        b01_D210OutputValue       DisplayString
    }

b01_D210OutputIndex   OBJECT-TYPE
    SYNTAX           INTEGER(0..2147483647)
    ACCESS           read-only
    STATUS           mandatory
    DESCRIPTION
    "The index in the b01_D210Output table for a particular snmp b01_D210Output
	 object.  Used to address table entries."
    ::=   { b01_D210OutputTableEntry 1 }


b01_D210OutputName    OBJECT-TYPE
    SYNTAX           DisplayString
    ACCESS           read-only
    STATUS           mandatory
    DESCRIPTION
    "Name of station object."
    ::=   { b01_D210OutputTableEntry 2 }

b01_D210OutputValue    OBJECT-TYPE
    SYNTAX           DisplayString
    ACCESS           read-only
    STATUS           mandatory
    DESCRIPTION
    "Current value of station object. Is read-only ."
    ::=   { b01_D210OutputTableEntry 3 }


-- ***********************************
-- *
-- *  B01_D211
-- *
-- ***********************************
    b01_D211    OBJECT IDENTIFIER ::= { exportTables 53 }

-- ***********************************
-- *
-- *  B01_D211Input table declarations
-- *
-- ***********************************

b01_D211InputTable   OBJECT-TYPE
    SYNTAX                SEQUENCE OF B01_D211InputTableEntry
    ACCESS                not-accessible
    STATUS                mandatory
    DESCRIPTION
    "A list of snmp b01_D211Input (read-only) object values."
    ::=  { b01_D211 1 }

b01_D211InputTableEntry  OBJECT-TYPE
    SYNTAX                B01_D211InputTableEntry
    ACCESS                not-accessible
    STATUS                mandatory
    DESCRIPTION
    "An b01_D211Input table entry containing data for a specific b01_D211Input."
    INDEX  { b01_D211InputIndex }  ::=   { b01_D211InputTable 1 }

B01_D211InputTableEntry ::= SEQUENCE {
        b01_D211InputIndex       INTEGER,
        b01_D211InputName        DisplayString,
        b01_D211InputValue       DisplayString
    }

b01_D211InputIndex   OBJECT-TYPE
    SYNTAX           INTEGER(0..2147483647)
    ACCESS           read-only
    STATUS           mandatory
    DESCRIPTION
    "The index in the b01_D211Input table for a particular snmp b01_D211Input
	 object.  Used to address table entries."
    ::=   { b01_D211InputTableEntry 1 }


b01_D211InputName    OBJECT-TYPE
    SYNTAX           DisplayString
    ACCESS           read-only
    STATUS           mandatory
    DESCRIPTION
    "Name of station object."
    ::=   { b01_D211InputTableEntry 2 }

b01_D211InputValue    OBJECT-TYPE
    SYNTAX           DisplayString
    ACCESS           read-write
    STATUS           mandatory
    DESCRIPTION
    "Current value of station object. Is read-write ."
    ::=   { b01_D211InputTableEntry 3 }



-- ***********************************
-- *
-- *  B01_D211Output table declarations
-- *
-- ***********************************

b01_D211OutputTable   OBJECT-TYPE
    SYNTAX                SEQUENCE OF B01_D211OutputTableEntry
    ACCESS                not-accessible
    STATUS                mandatory
    DESCRIPTION
    "A list of snmp b01_D211Output (read-only) object values."
    ::=  { b01_D211 2 }

b01_D211OutputTableEntry  OBJECT-TYPE
    SYNTAX                B01_D211OutputTableEntry
    ACCESS                not-accessible
    STATUS                mandatory
    DESCRIPTION
    "An b01_D211Output table entry containing data for a specific b01_D211Output."
    INDEX  { b01_D211OutputIndex }  ::=   { b01_D211OutputTable 1 }

B01_D211OutputTableEntry ::= SEQUENCE {
        b01_D211OutputIndex       INTEGER,
        b01_D211OutputName        DisplayString,
        b01_D211OutputValue       DisplayString
    }

b01_D211OutputIndex   OBJECT-TYPE
    SYNTAX           INTEGER(0..2147483647)
    ACCESS           read-only
    STATUS           mandatory
    DESCRIPTION
    "The index in the b01_D211Output table for a particular snmp b01_D211Output
	 object.  Used to address table entries."
    ::=   { b01_D211OutputTableEntry 1 }


b01_D211OutputName    OBJECT-TYPE
    SYNTAX           DisplayString
    ACCESS           read-only
    STATUS           mandatory
    DESCRIPTION
    "Name of station object."
    ::=   { b01_D211OutputTableEntry 2 }

b01_D211OutputValue    OBJECT-TYPE
    SYNTAX           DisplayString
    ACCESS           read-only
    STATUS           mandatory
    DESCRIPTION
    "Current value of station object. Is read-only ."
    ::=   { b01_D211OutputTableEntry 3 }


-- ***********************************
-- *
-- *  B01_D266
-- *
-- ***********************************
    b01_D266    OBJECT IDENTIFIER ::= { exportTables 54 }

-- ***********************************
-- *
-- *  B01_D266Input table declarations
-- *
-- ***********************************

b01_D266InputTable   OBJECT-TYPE
    SYNTAX                SEQUENCE OF B01_D266InputTableEntry
    ACCESS                not-accessible
    STATUS                mandatory
    DESCRIPTION
    "A list of snmp b01_D266Input (read-only) object values."
    ::=  { b01_D266 1 }

b01_D266InputTableEntry  OBJECT-TYPE
    SYNTAX                B01_D266InputTableEntry
    ACCESS                not-accessible
    STATUS                mandatory
    DESCRIPTION
    "An b01_D266Input table entry containing data for a specific b01_D266Input."
    INDEX  { b01_D266InputIndex }  ::=   { b01_D266InputTable 1 }

B01_D266InputTableEntry ::= SEQUENCE {
        b01_D266InputIndex       INTEGER,
        b01_D266InputName        DisplayString,
        b01_D266InputValue       DisplayString
    }

b01_D266InputIndex   OBJECT-TYPE
    SYNTAX           INTEGER(0..2147483647)
    ACCESS           read-only
    STATUS           mandatory
    DESCRIPTION
    "The index in the b01_D266Input table for a particular snmp b01_D266Input
	 object.  Used to address table entries."
    ::=   { b01_D266InputTableEntry 1 }


b01_D266InputName    OBJECT-TYPE
    SYNTAX           DisplayString
    ACCESS           read-only
    STATUS           mandatory
    DESCRIPTION
    "Name of station object."
    ::=   { b01_D266InputTableEntry 2 }

b01_D266InputValue    OBJECT-TYPE
    SYNTAX           DisplayString
    ACCESS           read-write
    STATUS           mandatory
    DESCRIPTION
    "Current value of station object. Is read-write ."
    ::=   { b01_D266InputTableEntry 3 }



-- ***********************************
-- *
-- *  B01_D266Output table declarations
-- *
-- ***********************************

b01_D266OutputTable   OBJECT-TYPE
    SYNTAX                SEQUENCE OF B01_D266OutputTableEntry
    ACCESS                not-accessible
    STATUS                mandatory
    DESCRIPTION
    "A list of snmp b01_D266Output (read-only) object values."
    ::=  { b01_D266 2 }

b01_D266OutputTableEntry  OBJECT-TYPE
    SYNTAX                B01_D266OutputTableEntry
    ACCESS                not-accessible
    STATUS                mandatory
    DESCRIPTION
    "An b01_D266Output table entry containing data for a specific b01_D266Output."
    INDEX  { b01_D266OutputIndex }  ::=   { b01_D266OutputTable 1 }

B01_D266OutputTableEntry ::= SEQUENCE {
        b01_D266OutputIndex       INTEGER,
        b01_D266OutputName        DisplayString,
        b01_D266OutputValue       DisplayString
    }

b01_D266OutputIndex   OBJECT-TYPE
    SYNTAX           INTEGER(0..2147483647)
    ACCESS           read-only
    STATUS           mandatory
    DESCRIPTION
    "The index in the b01_D266Output table for a particular snmp b01_D266Output
	 object.  Used to address table entries."
    ::=   { b01_D266OutputTableEntry 1 }


b01_D266OutputName    OBJECT-TYPE
    SYNTAX           DisplayString
    ACCESS           read-only
    STATUS           mandatory
    DESCRIPTION
    "Name of station object."
    ::=   { b01_D266OutputTableEntry 2 }

b01_D266OutputValue    OBJECT-TYPE
    SYNTAX           DisplayString
    ACCESS           read-only
    STATUS           mandatory
    DESCRIPTION
    "Current value of station object. Is read-only ."
    ::=   { b01_D266OutputTableEntry 3 }


-- ***********************************
-- *
-- *  B01_D267
-- *
-- ***********************************
    b01_D267    OBJECT IDENTIFIER ::= { exportTables 55 }

-- ***********************************
-- *
-- *  B01_D267Input table declarations
-- *
-- ***********************************

b01_D267InputTable   OBJECT-TYPE
    SYNTAX                SEQUENCE OF B01_D267InputTableEntry
    ACCESS                not-accessible
    STATUS                mandatory
    DESCRIPTION
    "A list of snmp b01_D267Input (read-only) object values."
    ::=  { b01_D267 1 }

b01_D267InputTableEntry  OBJECT-TYPE
    SYNTAX                B01_D267InputTableEntry
    ACCESS                not-accessible
    STATUS                mandatory
    DESCRIPTION
    "An b01_D267Input table entry containing data for a specific b01_D267Input."
    INDEX  { b01_D267InputIndex }  ::=   { b01_D267InputTable 1 }

B01_D267InputTableEntry ::= SEQUENCE {
        b01_D267InputIndex       INTEGER,
        b01_D267InputName        DisplayString,
        b01_D267InputValue       DisplayString
    }

b01_D267InputIndex   OBJECT-TYPE
    SYNTAX           INTEGER(0..2147483647)
    ACCESS           read-only
    STATUS           mandatory
    DESCRIPTION
    "The index in the b01_D267Input table for a particular snmp b01_D267Input
	 object.  Used to address table entries."
    ::=   { b01_D267InputTableEntry 1 }


b01_D267InputName    OBJECT-TYPE
    SYNTAX           DisplayString
    ACCESS           read-only
    STATUS           mandatory
    DESCRIPTION
    "Name of station object."
    ::=   { b01_D267InputTableEntry 2 }

b01_D267InputValue    OBJECT-TYPE
    SYNTAX           DisplayString
    ACCESS           read-write
    STATUS           mandatory
    DESCRIPTION
    "Current value of station object. Is read-write ."
    ::=   { b01_D267InputTableEntry 3 }



-- ***********************************
-- *
-- *  B01_D267Output table declarations
-- *
-- ***********************************

b01_D267OutputTable   OBJECT-TYPE
    SYNTAX                SEQUENCE OF B01_D267OutputTableEntry
    ACCESS                not-accessible
    STATUS                mandatory
    DESCRIPTION
    "A list of snmp b01_D267Output (read-only) object values."
    ::=  { b01_D267 2 }

b01_D267OutputTableEntry  OBJECT-TYPE
    SYNTAX                B01_D267OutputTableEntry
    ACCESS                not-accessible
    STATUS                mandatory
    DESCRIPTION
    "An b01_D267Output table entry containing data for a specific b01_D267Output."
    INDEX  { b01_D267OutputIndex }  ::=   { b01_D267OutputTable 1 }

B01_D267OutputTableEntry ::= SEQUENCE {
        b01_D267OutputIndex       INTEGER,
        b01_D267OutputName        DisplayString,
        b01_D267OutputValue       DisplayString
    }

b01_D267OutputIndex   OBJECT-TYPE
    SYNTAX           INTEGER(0..2147483647)
    ACCESS           read-only
    STATUS           mandatory
    DESCRIPTION
    "The index in the b01_D267Output table for a particular snmp b01_D267Output
	 object.  Used to address table entries."
    ::=   { b01_D267OutputTableEntry 1 }


b01_D267OutputName    OBJECT-TYPE
    SYNTAX           DisplayString
    ACCESS           read-only
    STATUS           mandatory
    DESCRIPTION
    "Name of station object."
    ::=   { b01_D267OutputTableEntry 2 }

b01_D267OutputValue    OBJECT-TYPE
    SYNTAX           DisplayString
    ACCESS           read-only
    STATUS           mandatory
    DESCRIPTION
    "Current value of station object. Is read-only ."
    ::=   { b01_D267OutputTableEntry 3 }


-- ***********************************
-- *
-- *  B01_D268
-- *
-- ***********************************
    b01_D268    OBJECT IDENTIFIER ::= { exportTables 56 }

-- ***********************************
-- *
-- *  B01_D268Input table declarations
-- *
-- ***********************************

b01_D268InputTable   OBJECT-TYPE
    SYNTAX                SEQUENCE OF B01_D268InputTableEntry
    ACCESS                not-accessible
    STATUS                mandatory
    DESCRIPTION
    "A list of snmp b01_D268Input (read-only) object values."
    ::=  { b01_D268 1 }

b01_D268InputTableEntry  OBJECT-TYPE
    SYNTAX                B01_D268InputTableEntry
    ACCESS                not-accessible
    STATUS                mandatory
    DESCRIPTION
    "An b01_D268Input table entry containing data for a specific b01_D268Input."
    INDEX  { b01_D268InputIndex }  ::=   { b01_D268InputTable 1 }

B01_D268InputTableEntry ::= SEQUENCE {
        b01_D268InputIndex       INTEGER,
        b01_D268InputName        DisplayString,
        b01_D268InputValue       DisplayString
    }

b01_D268InputIndex   OBJECT-TYPE
    SYNTAX           INTEGER(0..2147483647)
    ACCESS           read-only
    STATUS           mandatory
    DESCRIPTION
    "The index in the b01_D268Input table for a particular snmp b01_D268Input
	 object.  Used to address table entries."
    ::=   { b01_D268InputTableEntry 1 }


b01_D268InputName    OBJECT-TYPE
    SYNTAX           DisplayString
    ACCESS           read-only
    STATUS           mandatory
    DESCRIPTION
    "Name of station object."
    ::=   { b01_D268InputTableEntry 2 }

b01_D268InputValue    OBJECT-TYPE
    SYNTAX           DisplayString
    ACCESS           read-write
    STATUS           mandatory
    DESCRIPTION
    "Current value of station object. Is read-write ."
    ::=   { b01_D268InputTableEntry 3 }



-- ***********************************
-- *
-- *  B01_D268Output table declarations
-- *
-- ***********************************

b01_D268OutputTable   OBJECT-TYPE
    SYNTAX                SEQUENCE OF B01_D268OutputTableEntry
    ACCESS                not-accessible
    STATUS                mandatory
    DESCRIPTION
    "A list of snmp b01_D268Output (read-only) object values."
    ::=  { b01_D268 2 }

b01_D268OutputTableEntry  OBJECT-TYPE
    SYNTAX                B01_D268OutputTableEntry
    ACCESS                not-accessible
    STATUS                mandatory
    DESCRIPTION
    "An b01_D268Output table entry containing data for a specific b01_D268Output."
    INDEX  { b01_D268OutputIndex }  ::=   { b01_D268OutputTable 1 }

B01_D268OutputTableEntry ::= SEQUENCE {
        b01_D268OutputIndex       INTEGER,
        b01_D268OutputName        DisplayString,
        b01_D268OutputValue       DisplayString
    }

b01_D268OutputIndex   OBJECT-TYPE
    SYNTAX           INTEGER(0..2147483647)
    ACCESS           read-only
    STATUS           mandatory
    DESCRIPTION
    "The index in the b01_D268Output table for a particular snmp b01_D268Output
	 object.  Used to address table entries."
    ::=   { b01_D268OutputTableEntry 1 }


b01_D268OutputName    OBJECT-TYPE
    SYNTAX           DisplayString
    ACCESS           read-only
    STATUS           mandatory
    DESCRIPTION
    "Name of station object."
    ::=   { b01_D268OutputTableEntry 2 }

b01_D268OutputValue    OBJECT-TYPE
    SYNTAX           DisplayString
    ACCESS           read-only
    STATUS           mandatory
    DESCRIPTION
    "Current value of station object. Is read-only ."
    ::=   { b01_D268OutputTableEntry 3 }


-- ***********************************
-- *
-- *  B01_D269
-- *
-- ***********************************
    b01_D269    OBJECT IDENTIFIER ::= { exportTables 57 }

-- ***********************************
-- *
-- *  B01_D269Input table declarations
-- *
-- ***********************************

b01_D269InputTable   OBJECT-TYPE
    SYNTAX                SEQUENCE OF B01_D269InputTableEntry
    ACCESS                not-accessible
    STATUS                mandatory
    DESCRIPTION
    "A list of snmp b01_D269Input (read-only) object values."
    ::=  { b01_D269 1 }

b01_D269InputTableEntry  OBJECT-TYPE
    SYNTAX                B01_D269InputTableEntry
    ACCESS                not-accessible
    STATUS                mandatory
    DESCRIPTION
    "An b01_D269Input table entry containing data for a specific b01_D269Input."
    INDEX  { b01_D269InputIndex }  ::=   { b01_D269InputTable 1 }

B01_D269InputTableEntry ::= SEQUENCE {
        b01_D269InputIndex       INTEGER,
        b01_D269InputName        DisplayString,
        b01_D269InputValue       DisplayString
    }

b01_D269InputIndex   OBJECT-TYPE
    SYNTAX           INTEGER(0..2147483647)
    ACCESS           read-only
    STATUS           mandatory
    DESCRIPTION
    "The index in the b01_D269Input table for a particular snmp b01_D269Input
	 object.  Used to address table entries."
    ::=   { b01_D269InputTableEntry 1 }


b01_D269InputName    OBJECT-TYPE
    SYNTAX           DisplayString
    ACCESS           read-only
    STATUS           mandatory
    DESCRIPTION
    "Name of station object."
    ::=   { b01_D269InputTableEntry 2 }

b01_D269InputValue    OBJECT-TYPE
    SYNTAX           DisplayString
    ACCESS           read-write
    STATUS           mandatory
    DESCRIPTION
    "Current value of station object. Is read-write ."
    ::=   { b01_D269InputTableEntry 3 }



-- ***********************************
-- *
-- *  B01_D269Output table declarations
-- *
-- ***********************************

b01_D269OutputTable   OBJECT-TYPE
    SYNTAX                SEQUENCE OF B01_D269OutputTableEntry
    ACCESS                not-accessible
    STATUS                mandatory
    DESCRIPTION
    "A list of snmp b01_D269Output (read-only) object values."
    ::=  { b01_D269 2 }

b01_D269OutputTableEntry  OBJECT-TYPE
    SYNTAX                B01_D269OutputTableEntry
    ACCESS                not-accessible
    STATUS                mandatory
    DESCRIPTION
    "An b01_D269Output table entry containing data for a specific b01_D269Output."
    INDEX  { b01_D269OutputIndex }  ::=   { b01_D269OutputTable 1 }

B01_D269OutputTableEntry ::= SEQUENCE {
        b01_D269OutputIndex       INTEGER,
        b01_D269OutputName        DisplayString,
        b01_D269OutputValue       DisplayString
    }

b01_D269OutputIndex   OBJECT-TYPE
    SYNTAX           INTEGER(0..2147483647)
    ACCESS           read-only
    STATUS           mandatory
    DESCRIPTION
    "The index in the b01_D269Output table for a particular snmp b01_D269Output
	 object.  Used to address table entries."
    ::=   { b01_D269OutputTableEntry 1 }


b01_D269OutputName    OBJECT-TYPE
    SYNTAX           DisplayString
    ACCESS           read-only
    STATUS           mandatory
    DESCRIPTION
    "Name of station object."
    ::=   { b01_D269OutputTableEntry 2 }

b01_D269OutputValue    OBJECT-TYPE
    SYNTAX           DisplayString
    ACCESS           read-only
    STATUS           mandatory
    DESCRIPTION
    "Current value of station object. Is read-only ."
    ::=   { b01_D269OutputTableEntry 3 }


-- ***********************************
-- *
-- *  B01_D214
-- *
-- ***********************************
    b01_D214    OBJECT IDENTIFIER ::= { exportTables 58 }

-- ***********************************
-- *
-- *  B01_D214Input table declarations
-- *
-- ***********************************

b01_D214InputTable   OBJECT-TYPE
    SYNTAX                SEQUENCE OF B01_D214InputTableEntry
    ACCESS                not-accessible
    STATUS                mandatory
    DESCRIPTION
    "A list of snmp b01_D214Input (read-only) object values."
    ::=  { b01_D214 1 }

b01_D214InputTableEntry  OBJECT-TYPE
    SYNTAX                B01_D214InputTableEntry
    ACCESS                not-accessible
    STATUS                mandatory
    DESCRIPTION
    "An b01_D214Input table entry containing data for a specific b01_D214Input."
    INDEX  { b01_D214InputIndex }  ::=   { b01_D214InputTable 1 }

B01_D214InputTableEntry ::= SEQUENCE {
        b01_D214InputIndex       INTEGER,
        b01_D214InputName        DisplayString,
        b01_D214InputValue       DisplayString
    }

b01_D214InputIndex   OBJECT-TYPE
    SYNTAX           INTEGER(0..2147483647)
    ACCESS           read-only
    STATUS           mandatory
    DESCRIPTION
    "The index in the b01_D214Input table for a particular snmp b01_D214Input
	 object.  Used to address table entries."
    ::=   { b01_D214InputTableEntry 1 }


b01_D214InputName    OBJECT-TYPE
    SYNTAX           DisplayString
    ACCESS           read-only
    STATUS           mandatory
    DESCRIPTION
    "Name of station object."
    ::=   { b01_D214InputTableEntry 2 }

b01_D214InputValue    OBJECT-TYPE
    SYNTAX           DisplayString
    ACCESS           read-write
    STATUS           mandatory
    DESCRIPTION
    "Current value of station object. Is read-write ."
    ::=   { b01_D214InputTableEntry 3 }



-- ***********************************
-- *
-- *  B01_D214Output table declarations
-- *
-- ***********************************

b01_D214OutputTable   OBJECT-TYPE
    SYNTAX                SEQUENCE OF B01_D214OutputTableEntry
    ACCESS                not-accessible
    STATUS                mandatory
    DESCRIPTION
    "A list of snmp b01_D214Output (read-only) object values."
    ::=  { b01_D214 2 }

b01_D214OutputTableEntry  OBJECT-TYPE
    SYNTAX                B01_D214OutputTableEntry
    ACCESS                not-accessible
    STATUS                mandatory
    DESCRIPTION
    "An b01_D214Output table entry containing data for a specific b01_D214Output."
    INDEX  { b01_D214OutputIndex }  ::=   { b01_D214OutputTable 1 }

B01_D214OutputTableEntry ::= SEQUENCE {
        b01_D214OutputIndex       INTEGER,
        b01_D214OutputName        DisplayString,
        b01_D214OutputValue       DisplayString
    }

b01_D214OutputIndex   OBJECT-TYPE
    SYNTAX           INTEGER(0..2147483647)
    ACCESS           read-only
    STATUS           mandatory
    DESCRIPTION
    "The index in the b01_D214Output table for a particular snmp b01_D214Output
	 object.  Used to address table entries."
    ::=   { b01_D214OutputTableEntry 1 }


b01_D214OutputName    OBJECT-TYPE
    SYNTAX           DisplayString
    ACCESS           read-only
    STATUS           mandatory
    DESCRIPTION
    "Name of station object."
    ::=   { b01_D214OutputTableEntry 2 }

b01_D214OutputValue    OBJECT-TYPE
    SYNTAX           DisplayString
    ACCESS           read-only
    STATUS           mandatory
    DESCRIPTION
    "Current value of station object. Is read-only ."
    ::=   { b01_D214OutputTableEntry 3 }


-- ***********************************
-- *
-- *  B01_D215
-- *
-- ***********************************
    b01_D215    OBJECT IDENTIFIER ::= { exportTables 59 }

-- ***********************************
-- *
-- *  B01_D215Input table declarations
-- *
-- ***********************************

b01_D215InputTable   OBJECT-TYPE
    SYNTAX                SEQUENCE OF B01_D215InputTableEntry
    ACCESS                not-accessible
    STATUS                mandatory
    DESCRIPTION
    "A list of snmp b01_D215Input (read-only) object values."
    ::=  { b01_D215 1 }

b01_D215InputTableEntry  OBJECT-TYPE
    SYNTAX                B01_D215InputTableEntry
    ACCESS                not-accessible
    STATUS                mandatory
    DESCRIPTION
    "An b01_D215Input table entry containing data for a specific b01_D215Input."
    INDEX  { b01_D215InputIndex }  ::=   { b01_D215InputTable 1 }

B01_D215InputTableEntry ::= SEQUENCE {
        b01_D215InputIndex       INTEGER,
        b01_D215InputName        DisplayString,
        b01_D215InputValue       DisplayString
    }

b01_D215InputIndex   OBJECT-TYPE
    SYNTAX           INTEGER(0..2147483647)
    ACCESS           read-only
    STATUS           mandatory
    DESCRIPTION
    "The index in the b01_D215Input table for a particular snmp b01_D215Input
	 object.  Used to address table entries."
    ::=   { b01_D215InputTableEntry 1 }


b01_D215InputName    OBJECT-TYPE
    SYNTAX           DisplayString
    ACCESS           read-only
    STATUS           mandatory
    DESCRIPTION
    "Name of station object."
    ::=   { b01_D215InputTableEntry 2 }

b01_D215InputValue    OBJECT-TYPE
    SYNTAX           DisplayString
    ACCESS           read-write
    STATUS           mandatory
    DESCRIPTION
    "Current value of station object. Is read-write ."
    ::=   { b01_D215InputTableEntry 3 }



-- ***********************************
-- *
-- *  B01_D215Output table declarations
-- *
-- ***********************************

b01_D215OutputTable   OBJECT-TYPE
    SYNTAX                SEQUENCE OF B01_D215OutputTableEntry
    ACCESS                not-accessible
    STATUS                mandatory
    DESCRIPTION
    "A list of snmp b01_D215Output (read-only) object values."
    ::=  { b01_D215 2 }

b01_D215OutputTableEntry  OBJECT-TYPE
    SYNTAX                B01_D215OutputTableEntry
    ACCESS                not-accessible
    STATUS                mandatory
    DESCRIPTION
    "An b01_D215Output table entry containing data for a specific b01_D215Output."
    INDEX  { b01_D215OutputIndex }  ::=   { b01_D215OutputTable 1 }

B01_D215OutputTableEntry ::= SEQUENCE {
        b01_D215OutputIndex       INTEGER,
        b01_D215OutputName        DisplayString,
        b01_D215OutputValue       DisplayString
    }

b01_D215OutputIndex   OBJECT-TYPE
    SYNTAX           INTEGER(0..2147483647)
    ACCESS           read-only
    STATUS           mandatory
    DESCRIPTION
    "The index in the b01_D215Output table for a particular snmp b01_D215Output
	 object.  Used to address table entries."
    ::=   { b01_D215OutputTableEntry 1 }


b01_D215OutputName    OBJECT-TYPE
    SYNTAX           DisplayString
    ACCESS           read-only
    STATUS           mandatory
    DESCRIPTION
    "Name of station object."
    ::=   { b01_D215OutputTableEntry 2 }

b01_D215OutputValue    OBJECT-TYPE
    SYNTAX           DisplayString
    ACCESS           read-only
    STATUS           mandatory
    DESCRIPTION
    "Current value of station object. Is read-only ."
    ::=   { b01_D215OutputTableEntry 3 }


-- ***********************************
-- *
-- *  B14_D1
-- *
-- ***********************************
    b14_D1    OBJECT IDENTIFIER ::= { exportTables 60 }

-- ***********************************
-- *
-- *  B14_D1Input table declarations
-- *
-- ***********************************

b14_D1InputTable   OBJECT-TYPE
    SYNTAX                SEQUENCE OF B14_D1InputTableEntry
    ACCESS                not-accessible
    STATUS                mandatory
    DESCRIPTION
    "A list of snmp b14_D1Input (read-only) object values."
    ::=  { b14_D1 1 }

b14_D1InputTableEntry  OBJECT-TYPE
    SYNTAX                B14_D1InputTableEntry
    ACCESS                not-accessible
    STATUS                mandatory
    DESCRIPTION
    "An b14_D1Input table entry containing data for a specific b14_D1Input."
    INDEX  { b14_D1InputIndex }  ::=   { b14_D1InputTable 1 }

B14_D1InputTableEntry ::= SEQUENCE {
        b14_D1InputIndex       INTEGER,
        b14_D1InputName        DisplayString,
        b14_D1InputValue       DisplayString
    }

b14_D1InputIndex   OBJECT-TYPE
    SYNTAX           INTEGER(0..2147483647)
    ACCESS           read-only
    STATUS           mandatory
    DESCRIPTION
    "The index in the b14_D1Input table for a particular snmp b14_D1Input
	 object.  Used to address table entries."
    ::=   { b14_D1InputTableEntry 1 }


b14_D1InputName    OBJECT-TYPE
    SYNTAX           DisplayString
    ACCESS           read-only
    STATUS           mandatory
    DESCRIPTION
    "Name of station object."
    ::=   { b14_D1InputTableEntry 2 }

b14_D1InputValue    OBJECT-TYPE
    SYNTAX           DisplayString
    ACCESS           read-write
    STATUS           mandatory
    DESCRIPTION
    "Current value of station object. Is read-write ."
    ::=   { b14_D1InputTableEntry 3 }



-- ***********************************
-- *
-- *  B14_D1Output table declarations
-- *
-- ***********************************

b14_D1OutputTable   OBJECT-TYPE
    SYNTAX                SEQUENCE OF B14_D1OutputTableEntry
    ACCESS                not-accessible
    STATUS                mandatory
    DESCRIPTION
    "A list of snmp b14_D1Output (read-only) object values."
    ::=  { b14_D1 2 }

b14_D1OutputTableEntry  OBJECT-TYPE
    SYNTAX                B14_D1OutputTableEntry
    ACCESS                not-accessible
    STATUS                mandatory
    DESCRIPTION
    "An b14_D1Output table entry containing data for a specific b14_D1Output."
    INDEX  { b14_D1OutputIndex }  ::=   { b14_D1OutputTable 1 }

B14_D1OutputTableEntry ::= SEQUENCE {
        b14_D1OutputIndex       INTEGER,
        b14_D1OutputName        DisplayString,
        b14_D1OutputValue       DisplayString
    }

b14_D1OutputIndex   OBJECT-TYPE
    SYNTAX           INTEGER(0..2147483647)
    ACCESS           read-only
    STATUS           mandatory
    DESCRIPTION
    "The index in the b14_D1Output table for a particular snmp b14_D1Output
	 object.  Used to address table entries."
    ::=   { b14_D1OutputTableEntry 1 }


b14_D1OutputName    OBJECT-TYPE
    SYNTAX           DisplayString
    ACCESS           read-only
    STATUS           mandatory
    DESCRIPTION
    "Name of station object."
    ::=   { b14_D1OutputTableEntry 2 }

b14_D1OutputValue    OBJECT-TYPE
    SYNTAX           DisplayString
    ACCESS           read-only
    STATUS           mandatory
    DESCRIPTION
    "Current value of station object. Is read-only ."
    ::=   { b14_D1OutputTableEntry 3 }


-- ***********************************
-- *
-- *  B14_D53
-- *
-- ***********************************
    b14_D53    OBJECT IDENTIFIER ::= { exportTables 61 }

-- ***********************************
-- *
-- *  B14_D53Input table declarations
-- *
-- ***********************************

b14_D53InputTable   OBJECT-TYPE
    SYNTAX                SEQUENCE OF B14_D53InputTableEntry
    ACCESS                not-accessible
    STATUS                mandatory
    DESCRIPTION
    "A list of snmp b14_D53Input (read-only) object values."
    ::=  { b14_D53 1 }

b14_D53InputTableEntry  OBJECT-TYPE
    SYNTAX                B14_D53InputTableEntry
    ACCESS                not-accessible
    STATUS                mandatory
    DESCRIPTION
    "An b14_D53Input table entry containing data for a specific b14_D53Input."
    INDEX  { b14_D53InputIndex }  ::=   { b14_D53InputTable 1 }

B14_D53InputTableEntry ::= SEQUENCE {
        b14_D53InputIndex       INTEGER,
        b14_D53InputName        DisplayString,
        b14_D53InputValue       DisplayString
    }

b14_D53InputIndex   OBJECT-TYPE
    SYNTAX           INTEGER(0..2147483647)
    ACCESS           read-only
    STATUS           mandatory
    DESCRIPTION
    "The index in the b14_D53Input table for a particular snmp b14_D53Input
	 object.  Used to address table entries."
    ::=   { b14_D53InputTableEntry 1 }


b14_D53InputName    OBJECT-TYPE
    SYNTAX           DisplayString
    ACCESS           read-only
    STATUS           mandatory
    DESCRIPTION
    "Name of station object."
    ::=   { b14_D53InputTableEntry 2 }

b14_D53InputValue    OBJECT-TYPE
    SYNTAX           DisplayString
    ACCESS           read-write
    STATUS           mandatory
    DESCRIPTION
    "Current value of station object. Is read-write ."
    ::=   { b14_D53InputTableEntry 3 }



-- ***********************************
-- *
-- *  B14_D53Output table declarations
-- *
-- ***********************************

b14_D53OutputTable   OBJECT-TYPE
    SYNTAX                SEQUENCE OF B14_D53OutputTableEntry
    ACCESS                not-accessible
    STATUS                mandatory
    DESCRIPTION
    "A list of snmp b14_D53Output (read-only) object values."
    ::=  { b14_D53 2 }

b14_D53OutputTableEntry  OBJECT-TYPE
    SYNTAX                B14_D53OutputTableEntry
    ACCESS                not-accessible
    STATUS                mandatory
    DESCRIPTION
    "An b14_D53Output table entry containing data for a specific b14_D53Output."
    INDEX  { b14_D53OutputIndex }  ::=   { b14_D53OutputTable 1 }

B14_D53OutputTableEntry ::= SEQUENCE {
        b14_D53OutputIndex       INTEGER,
        b14_D53OutputName        DisplayString,
        b14_D53OutputValue       DisplayString
    }

b14_D53OutputIndex   OBJECT-TYPE
    SYNTAX           INTEGER(0..2147483647)
    ACCESS           read-only
    STATUS           mandatory
    DESCRIPTION
    "The index in the b14_D53Output table for a particular snmp b14_D53Output
	 object.  Used to address table entries."
    ::=   { b14_D53OutputTableEntry 1 }


b14_D53OutputName    OBJECT-TYPE
    SYNTAX           DisplayString
    ACCESS           read-only
    STATUS           mandatory
    DESCRIPTION
    "Name of station object."
    ::=   { b14_D53OutputTableEntry 2 }

b14_D53OutputValue    OBJECT-TYPE
    SYNTAX           DisplayString
    ACCESS           read-only
    STATUS           mandatory
    DESCRIPTION
    "Current value of station object. Is read-only ."
    ::=   { b14_D53OutputTableEntry 3 }


-- ***********************************
-- *
-- *  B14_D52
-- *
-- ***********************************
    b14_D52    OBJECT IDENTIFIER ::= { exportTables 62 }

-- ***********************************
-- *
-- *  B14_D52Input table declarations
-- *
-- ***********************************

b14_D52InputTable   OBJECT-TYPE
    SYNTAX                SEQUENCE OF B14_D52InputTableEntry
    ACCESS                not-accessible
    STATUS                mandatory
    DESCRIPTION
    "A list of snmp b14_D52Input (read-only) object values."
    ::=  { b14_D52 1 }

b14_D52InputTableEntry  OBJECT-TYPE
    SYNTAX                B14_D52InputTableEntry
    ACCESS                not-accessible
    STATUS                mandatory
    DESCRIPTION
    "An b14_D52Input table entry containing data for a specific b14_D52Input."
    INDEX  { b14_D52InputIndex }  ::=   { b14_D52InputTable 1 }

B14_D52InputTableEntry ::= SEQUENCE {
        b14_D52InputIndex       INTEGER,
        b14_D52InputName        DisplayString,
        b14_D52InputValue       DisplayString
    }

b14_D52InputIndex   OBJECT-TYPE
    SYNTAX           INTEGER(0..2147483647)
    ACCESS           read-only
    STATUS           mandatory
    DESCRIPTION
    "The index in the b14_D52Input table for a particular snmp b14_D52Input
	 object.  Used to address table entries."
    ::=   { b14_D52InputTableEntry 1 }


b14_D52InputName    OBJECT-TYPE
    SYNTAX           DisplayString
    ACCESS           read-only
    STATUS           mandatory
    DESCRIPTION
    "Name of station object."
    ::=   { b14_D52InputTableEntry 2 }

b14_D52InputValue    OBJECT-TYPE
    SYNTAX           DisplayString
    ACCESS           read-write
    STATUS           mandatory
    DESCRIPTION
    "Current value of station object. Is read-write ."
    ::=   { b14_D52InputTableEntry 3 }



-- ***********************************
-- *
-- *  B14_D52Output table declarations
-- *
-- ***********************************

b14_D52OutputTable   OBJECT-TYPE
    SYNTAX                SEQUENCE OF B14_D52OutputTableEntry
    ACCESS                not-accessible
    STATUS                mandatory
    DESCRIPTION
    "A list of snmp b14_D52Output (read-only) object values."
    ::=  { b14_D52 2 }

b14_D52OutputTableEntry  OBJECT-TYPE
    SYNTAX                B14_D52OutputTableEntry
    ACCESS                not-accessible
    STATUS                mandatory
    DESCRIPTION
    "An b14_D52Output table entry containing data for a specific b14_D52Output."
    INDEX  { b14_D52OutputIndex }  ::=   { b14_D52OutputTable 1 }

B14_D52OutputTableEntry ::= SEQUENCE {
        b14_D52OutputIndex       INTEGER,
        b14_D52OutputName        DisplayString,
        b14_D52OutputValue       DisplayString
    }

b14_D52OutputIndex   OBJECT-TYPE
    SYNTAX           INTEGER(0..2147483647)
    ACCESS           read-only
    STATUS           mandatory
    DESCRIPTION
    "The index in the b14_D52Output table for a particular snmp b14_D52Output
	 object.  Used to address table entries."
    ::=   { b14_D52OutputTableEntry 1 }


b14_D52OutputName    OBJECT-TYPE
    SYNTAX           DisplayString
    ACCESS           read-only
    STATUS           mandatory
    DESCRIPTION
    "Name of station object."
    ::=   { b14_D52OutputTableEntry 2 }

b14_D52OutputValue    OBJECT-TYPE
    SYNTAX           DisplayString
    ACCESS           read-only
    STATUS           mandatory
    DESCRIPTION
    "Current value of station object. Is read-only ."
    ::=   { b14_D52OutputTableEntry 3 }


-- ***********************************
-- *
-- *  B14_D61
-- *
-- ***********************************
    b14_D61    OBJECT IDENTIFIER ::= { exportTables 63 }

-- ***********************************
-- *
-- *  B14_D61Input table declarations
-- *
-- ***********************************

b14_D61InputTable   OBJECT-TYPE
    SYNTAX                SEQUENCE OF B14_D61InputTableEntry
    ACCESS                not-accessible
    STATUS                mandatory
    DESCRIPTION
    "A list of snmp b14_D61Input (read-only) object values."
    ::=  { b14_D61 1 }

b14_D61InputTableEntry  OBJECT-TYPE
    SYNTAX                B14_D61InputTableEntry
    ACCESS                not-accessible
    STATUS                mandatory
    DESCRIPTION
    "An b14_D61Input table entry containing data for a specific b14_D61Input."
    INDEX  { b14_D61InputIndex }  ::=   { b14_D61InputTable 1 }

B14_D61InputTableEntry ::= SEQUENCE {
        b14_D61InputIndex       INTEGER,
        b14_D61InputName        DisplayString,
        b14_D61InputValue       DisplayString
    }

b14_D61InputIndex   OBJECT-TYPE
    SYNTAX           INTEGER(0..2147483647)
    ACCESS           read-only
    STATUS           mandatory
    DESCRIPTION
    "The index in the b14_D61Input table for a particular snmp b14_D61Input
	 object.  Used to address table entries."
    ::=   { b14_D61InputTableEntry 1 }


b14_D61InputName    OBJECT-TYPE
    SYNTAX           DisplayString
    ACCESS           read-only
    STATUS           mandatory
    DESCRIPTION
    "Name of station object."
    ::=   { b14_D61InputTableEntry 2 }

b14_D61InputValue    OBJECT-TYPE
    SYNTAX           DisplayString
    ACCESS           read-write
    STATUS           mandatory
    DESCRIPTION
    "Current value of station object. Is read-write ."
    ::=   { b14_D61InputTableEntry 3 }



-- ***********************************
-- *
-- *  B14_D61Output table declarations
-- *
-- ***********************************

b14_D61OutputTable   OBJECT-TYPE
    SYNTAX                SEQUENCE OF B14_D61OutputTableEntry
    ACCESS                not-accessible
    STATUS                mandatory
    DESCRIPTION
    "A list of snmp b14_D61Output (read-only) object values."
    ::=  { b14_D61 2 }

b14_D61OutputTableEntry  OBJECT-TYPE
    SYNTAX                B14_D61OutputTableEntry
    ACCESS                not-accessible
    STATUS                mandatory
    DESCRIPTION
    "An b14_D61Output table entry containing data for a specific b14_D61Output."
    INDEX  { b14_D61OutputIndex }  ::=   { b14_D61OutputTable 1 }

B14_D61OutputTableEntry ::= SEQUENCE {
        b14_D61OutputIndex       INTEGER,
        b14_D61OutputName        DisplayString,
        b14_D61OutputValue       DisplayString
    }

b14_D61OutputIndex   OBJECT-TYPE
    SYNTAX           INTEGER(0..2147483647)
    ACCESS           read-only
    STATUS           mandatory
    DESCRIPTION
    "The index in the b14_D61Output table for a particular snmp b14_D61Output
	 object.  Used to address table entries."
    ::=   { b14_D61OutputTableEntry 1 }


b14_D61OutputName    OBJECT-TYPE
    SYNTAX           DisplayString
    ACCESS           read-only
    STATUS           mandatory
    DESCRIPTION
    "Name of station object."
    ::=   { b14_D61OutputTableEntry 2 }

b14_D61OutputValue    OBJECT-TYPE
    SYNTAX           DisplayString
    ACCESS           read-only
    STATUS           mandatory
    DESCRIPTION
    "Current value of station object. Is read-only ."
    ::=   { b14_D61OutputTableEntry 3 }


-- ***********************************
-- *
-- *  B14_D62
-- *
-- ***********************************
    b14_D62    OBJECT IDENTIFIER ::= { exportTables 64 }

-- ***********************************
-- *
-- *  B14_D62Input table declarations
-- *
-- ***********************************

b14_D62InputTable   OBJECT-TYPE
    SYNTAX                SEQUENCE OF B14_D62InputTableEntry
    ACCESS                not-accessible
    STATUS                mandatory
    DESCRIPTION
    "A list of snmp b14_D62Input (read-only) object values."
    ::=  { b14_D62 1 }

b14_D62InputTableEntry  OBJECT-TYPE
    SYNTAX                B14_D62InputTableEntry
    ACCESS                not-accessible
    STATUS                mandatory
    DESCRIPTION
    "An b14_D62Input table entry containing data for a specific b14_D62Input."
    INDEX  { b14_D62InputIndex }  ::=   { b14_D62InputTable 1 }

B14_D62InputTableEntry ::= SEQUENCE {
        b14_D62InputIndex       INTEGER,
        b14_D62InputName        DisplayString,
        b14_D62InputValue       DisplayString
    }

b14_D62InputIndex   OBJECT-TYPE
    SYNTAX           INTEGER(0..2147483647)
    ACCESS           read-only
    STATUS           mandatory
    DESCRIPTION
    "The index in the b14_D62Input table for a particular snmp b14_D62Input
	 object.  Used to address table entries."
    ::=   { b14_D62InputTableEntry 1 }


b14_D62InputName    OBJECT-TYPE
    SYNTAX           DisplayString
    ACCESS           read-only
    STATUS           mandatory
    DESCRIPTION
    "Name of station object."
    ::=   { b14_D62InputTableEntry 2 }

b14_D62InputValue    OBJECT-TYPE
    SYNTAX           DisplayString
    ACCESS           read-write
    STATUS           mandatory
    DESCRIPTION
    "Current value of station object. Is read-write ."
    ::=   { b14_D62InputTableEntry 3 }



-- ***********************************
-- *
-- *  B14_D62Output table declarations
-- *
-- ***********************************

b14_D62OutputTable   OBJECT-TYPE
    SYNTAX                SEQUENCE OF B14_D62OutputTableEntry
    ACCESS                not-accessible
    STATUS                mandatory
    DESCRIPTION
    "A list of snmp b14_D62Output (read-only) object values."
    ::=  { b14_D62 2 }

b14_D62OutputTableEntry  OBJECT-TYPE
    SYNTAX                B14_D62OutputTableEntry
    ACCESS                not-accessible
    STATUS                mandatory
    DESCRIPTION
    "An b14_D62Output table entry containing data for a specific b14_D62Output."
    INDEX  { b14_D62OutputIndex }  ::=   { b14_D62OutputTable 1 }

B14_D62OutputTableEntry ::= SEQUENCE {
        b14_D62OutputIndex       INTEGER,
        b14_D62OutputName        DisplayString,
        b14_D62OutputValue       DisplayString
    }

b14_D62OutputIndex   OBJECT-TYPE
    SYNTAX           INTEGER(0..2147483647)
    ACCESS           read-only
    STATUS           mandatory
    DESCRIPTION
    "The index in the b14_D62Output table for a particular snmp b14_D62Output
	 object.  Used to address table entries."
    ::=   { b14_D62OutputTableEntry 1 }


b14_D62OutputName    OBJECT-TYPE
    SYNTAX           DisplayString
    ACCESS           read-only
    STATUS           mandatory
    DESCRIPTION
    "Name of station object."
    ::=   { b14_D62OutputTableEntry 2 }

b14_D62OutputValue    OBJECT-TYPE
    SYNTAX           DisplayString
    ACCESS           read-only
    STATUS           mandatory
    DESCRIPTION
    "Current value of station object. Is read-only ."
    ::=   { b14_D62OutputTableEntry 3 }


-- ***********************************
-- *
-- *  B14_D58
-- *
-- ***********************************
    b14_D58    OBJECT IDENTIFIER ::= { exportTables 65 }

-- ***********************************
-- *
-- *  B14_D58Input table declarations
-- *
-- ***********************************

b14_D58InputTable   OBJECT-TYPE
    SYNTAX                SEQUENCE OF B14_D58InputTableEntry
    ACCESS                not-accessible
    STATUS                mandatory
    DESCRIPTION
    "A list of snmp b14_D58Input (read-only) object values."
    ::=  { b14_D58 1 }

b14_D58InputTableEntry  OBJECT-TYPE
    SYNTAX                B14_D58InputTableEntry
    ACCESS                not-accessible
    STATUS                mandatory
    DESCRIPTION
    "An b14_D58Input table entry containing data for a specific b14_D58Input."
    INDEX  { b14_D58InputIndex }  ::=   { b14_D58InputTable 1 }

B14_D58InputTableEntry ::= SEQUENCE {
        b14_D58InputIndex       INTEGER,
        b14_D58InputName        DisplayString,
        b14_D58InputValue       DisplayString
    }

b14_D58InputIndex   OBJECT-TYPE
    SYNTAX           INTEGER(0..2147483647)
    ACCESS           read-only
    STATUS           mandatory
    DESCRIPTION
    "The index in the b14_D58Input table for a particular snmp b14_D58Input
	 object.  Used to address table entries."
    ::=   { b14_D58InputTableEntry 1 }


b14_D58InputName    OBJECT-TYPE
    SYNTAX           DisplayString
    ACCESS           read-only
    STATUS           mandatory
    DESCRIPTION
    "Name of station object."
    ::=   { b14_D58InputTableEntry 2 }

b14_D58InputValue    OBJECT-TYPE
    SYNTAX           DisplayString
    ACCESS           read-write
    STATUS           mandatory
    DESCRIPTION
    "Current value of station object. Is read-write ."
    ::=   { b14_D58InputTableEntry 3 }



-- ***********************************
-- *
-- *  B14_D58Output table declarations
-- *
-- ***********************************

b14_D58OutputTable   OBJECT-TYPE
    SYNTAX                SEQUENCE OF B14_D58OutputTableEntry
    ACCESS                not-accessible
    STATUS                mandatory
    DESCRIPTION
    "A list of snmp b14_D58Output (read-only) object values."
    ::=  { b14_D58 2 }

b14_D58OutputTableEntry  OBJECT-TYPE
    SYNTAX                B14_D58OutputTableEntry
    ACCESS                not-accessible
    STATUS                mandatory
    DESCRIPTION
    "An b14_D58Output table entry containing data for a specific b14_D58Output."
    INDEX  { b14_D58OutputIndex }  ::=   { b14_D58OutputTable 1 }

B14_D58OutputTableEntry ::= SEQUENCE {
        b14_D58OutputIndex       INTEGER,
        b14_D58OutputName        DisplayString,
        b14_D58OutputValue       DisplayString
    }

b14_D58OutputIndex   OBJECT-TYPE
    SYNTAX           INTEGER(0..2147483647)
    ACCESS           read-only
    STATUS           mandatory
    DESCRIPTION
    "The index in the b14_D58Output table for a particular snmp b14_D58Output
	 object.  Used to address table entries."
    ::=   { b14_D58OutputTableEntry 1 }


b14_D58OutputName    OBJECT-TYPE
    SYNTAX           DisplayString
    ACCESS           read-only
    STATUS           mandatory
    DESCRIPTION
    "Name of station object."
    ::=   { b14_D58OutputTableEntry 2 }

b14_D58OutputValue    OBJECT-TYPE
    SYNTAX           DisplayString
    ACCESS           read-only
    STATUS           mandatory
    DESCRIPTION
    "Current value of station object. Is read-only ."
    ::=   { b14_D58OutputTableEntry 3 }


-- ***********************************
-- *
-- *  B14_D82
-- *
-- ***********************************
    b14_D82    OBJECT IDENTIFIER ::= { exportTables 66 }

-- ***********************************
-- *
-- *  B14_D82Input table declarations
-- *
-- ***********************************

b14_D82InputTable   OBJECT-TYPE
    SYNTAX                SEQUENCE OF B14_D82InputTableEntry
    ACCESS                not-accessible
    STATUS                mandatory
    DESCRIPTION
    "A list of snmp b14_D82Input (read-only) object values."
    ::=  { b14_D82 1 }

b14_D82InputTableEntry  OBJECT-TYPE
    SYNTAX                B14_D82InputTableEntry
    ACCESS                not-accessible
    STATUS                mandatory
    DESCRIPTION
    "An b14_D82Input table entry containing data for a specific b14_D82Input."
    INDEX  { b14_D82InputIndex }  ::=   { b14_D82InputTable 1 }

B14_D82InputTableEntry ::= SEQUENCE {
        b14_D82InputIndex       INTEGER,
        b14_D82InputName        DisplayString,
        b14_D82InputValue       DisplayString
    }

b14_D82InputIndex   OBJECT-TYPE
    SYNTAX           INTEGER(0..2147483647)
    ACCESS           read-only
    STATUS           mandatory
    DESCRIPTION
    "The index in the b14_D82Input table for a particular snmp b14_D82Input
	 object.  Used to address table entries."
    ::=   { b14_D82InputTableEntry 1 }


b14_D82InputName    OBJECT-TYPE
    SYNTAX           DisplayString
    ACCESS           read-only
    STATUS           mandatory
    DESCRIPTION
    "Name of station object."
    ::=   { b14_D82InputTableEntry 2 }

b14_D82InputValue    OBJECT-TYPE
    SYNTAX           DisplayString
    ACCESS           read-write
    STATUS           mandatory
    DESCRIPTION
    "Current value of station object. Is read-write ."
    ::=   { b14_D82InputTableEntry 3 }



-- ***********************************
-- *
-- *  B14_D82Output table declarations
-- *
-- ***********************************

b14_D82OutputTable   OBJECT-TYPE
    SYNTAX                SEQUENCE OF B14_D82OutputTableEntry
    ACCESS                not-accessible
    STATUS                mandatory
    DESCRIPTION
    "A list of snmp b14_D82Output (read-only) object values."
    ::=  { b14_D82 2 }

b14_D82OutputTableEntry  OBJECT-TYPE
    SYNTAX                B14_D82OutputTableEntry
    ACCESS                not-accessible
    STATUS                mandatory
    DESCRIPTION
    "An b14_D82Output table entry containing data for a specific b14_D82Output."
    INDEX  { b14_D82OutputIndex }  ::=   { b14_D82OutputTable 1 }

B14_D82OutputTableEntry ::= SEQUENCE {
        b14_D82OutputIndex       INTEGER,
        b14_D82OutputName        DisplayString,
        b14_D82OutputValue       DisplayString
    }

b14_D82OutputIndex   OBJECT-TYPE
    SYNTAX           INTEGER(0..2147483647)
    ACCESS           read-only
    STATUS           mandatory
    DESCRIPTION
    "The index in the b14_D82Output table for a particular snmp b14_D82Output
	 object.  Used to address table entries."
    ::=   { b14_D82OutputTableEntry 1 }


b14_D82OutputName    OBJECT-TYPE
    SYNTAX           DisplayString
    ACCESS           read-only
    STATUS           mandatory
    DESCRIPTION
    "Name of station object."
    ::=   { b14_D82OutputTableEntry 2 }

b14_D82OutputValue    OBJECT-TYPE
    SYNTAX           DisplayString
    ACCESS           read-only
    STATUS           mandatory
    DESCRIPTION
    "Current value of station object. Is read-only ."
    ::=   { b14_D82OutputTableEntry 3 }


-- ***********************************
-- *
-- *  B14_D83
-- *
-- ***********************************
    b14_D83    OBJECT IDENTIFIER ::= { exportTables 67 }

-- ***********************************
-- *
-- *  B14_D83Input table declarations
-- *
-- ***********************************

b14_D83InputTable   OBJECT-TYPE
    SYNTAX                SEQUENCE OF B14_D83InputTableEntry
    ACCESS                not-accessible
    STATUS                mandatory
    DESCRIPTION
    "A list of snmp b14_D83Input (read-only) object values."
    ::=  { b14_D83 1 }

b14_D83InputTableEntry  OBJECT-TYPE
    SYNTAX                B14_D83InputTableEntry
    ACCESS                not-accessible
    STATUS                mandatory
    DESCRIPTION
    "An b14_D83Input table entry containing data for a specific b14_D83Input."
    INDEX  { b14_D83InputIndex }  ::=   { b14_D83InputTable 1 }

B14_D83InputTableEntry ::= SEQUENCE {
        b14_D83InputIndex       INTEGER,
        b14_D83InputName        DisplayString,
        b14_D83InputValue       DisplayString
    }

b14_D83InputIndex   OBJECT-TYPE
    SYNTAX           INTEGER(0..2147483647)
    ACCESS           read-only
    STATUS           mandatory
    DESCRIPTION
    "The index in the b14_D83Input table for a particular snmp b14_D83Input
	 object.  Used to address table entries."
    ::=   { b14_D83InputTableEntry 1 }


b14_D83InputName    OBJECT-TYPE
    SYNTAX           DisplayString
    ACCESS           read-only
    STATUS           mandatory
    DESCRIPTION
    "Name of station object."
    ::=   { b14_D83InputTableEntry 2 }

b14_D83InputValue    OBJECT-TYPE
    SYNTAX           DisplayString
    ACCESS           read-write
    STATUS           mandatory
    DESCRIPTION
    "Current value of station object. Is read-write ."
    ::=   { b14_D83InputTableEntry 3 }



-- ***********************************
-- *
-- *  B14_D83Output table declarations
-- *
-- ***********************************

b14_D83OutputTable   OBJECT-TYPE
    SYNTAX                SEQUENCE OF B14_D83OutputTableEntry
    ACCESS                not-accessible
    STATUS                mandatory
    DESCRIPTION
    "A list of snmp b14_D83Output (read-only) object values."
    ::=  { b14_D83 2 }

b14_D83OutputTableEntry  OBJECT-TYPE
    SYNTAX                B14_D83OutputTableEntry
    ACCESS                not-accessible
    STATUS                mandatory
    DESCRIPTION
    "An b14_D83Output table entry containing data for a specific b14_D83Output."
    INDEX  { b14_D83OutputIndex }  ::=   { b14_D83OutputTable 1 }

B14_D83OutputTableEntry ::= SEQUENCE {
        b14_D83OutputIndex       INTEGER,
        b14_D83OutputName        DisplayString,
        b14_D83OutputValue       DisplayString
    }

b14_D83OutputIndex   OBJECT-TYPE
    SYNTAX           INTEGER(0..2147483647)
    ACCESS           read-only
    STATUS           mandatory
    DESCRIPTION
    "The index in the b14_D83Output table for a particular snmp b14_D83Output
	 object.  Used to address table entries."
    ::=   { b14_D83OutputTableEntry 1 }


b14_D83OutputName    OBJECT-TYPE
    SYNTAX           DisplayString
    ACCESS           read-only
    STATUS           mandatory
    DESCRIPTION
    "Name of station object."
    ::=   { b14_D83OutputTableEntry 2 }

b14_D83OutputValue    OBJECT-TYPE
    SYNTAX           DisplayString
    ACCESS           read-only
    STATUS           mandatory
    DESCRIPTION
    "Current value of station object. Is read-only ."
    ::=   { b14_D83OutputTableEntry 3 }


-- ***********************************
-- *
-- *  B14_D80
-- *
-- ***********************************
    b14_D80    OBJECT IDENTIFIER ::= { exportTables 68 }

-- ***********************************
-- *
-- *  B14_D80Input table declarations
-- *
-- ***********************************

b14_D80InputTable   OBJECT-TYPE
    SYNTAX                SEQUENCE OF B14_D80InputTableEntry
    ACCESS                not-accessible
    STATUS                mandatory
    DESCRIPTION
    "A list of snmp b14_D80Input (read-only) object values."
    ::=  { b14_D80 1 }

b14_D80InputTableEntry  OBJECT-TYPE
    SYNTAX                B14_D80InputTableEntry
    ACCESS                not-accessible
    STATUS                mandatory
    DESCRIPTION
    "An b14_D80Input table entry containing data for a specific b14_D80Input."
    INDEX  { b14_D80InputIndex }  ::=   { b14_D80InputTable 1 }

B14_D80InputTableEntry ::= SEQUENCE {
        b14_D80InputIndex       INTEGER,
        b14_D80InputName        DisplayString,
        b14_D80InputValue       DisplayString
    }

b14_D80InputIndex   OBJECT-TYPE
    SYNTAX           INTEGER(0..2147483647)
    ACCESS           read-only
    STATUS           mandatory
    DESCRIPTION
    "The index in the b14_D80Input table for a particular snmp b14_D80Input
	 object.  Used to address table entries."
    ::=   { b14_D80InputTableEntry 1 }


b14_D80InputName    OBJECT-TYPE
    SYNTAX           DisplayString
    ACCESS           read-only
    STATUS           mandatory
    DESCRIPTION
    "Name of station object."
    ::=   { b14_D80InputTableEntry 2 }

b14_D80InputValue    OBJECT-TYPE
    SYNTAX           DisplayString
    ACCESS           read-write
    STATUS           mandatory
    DESCRIPTION
    "Current value of station object. Is read-write ."
    ::=   { b14_D80InputTableEntry 3 }



-- ***********************************
-- *
-- *  B14_D80Output table declarations
-- *
-- ***********************************

b14_D80OutputTable   OBJECT-TYPE
    SYNTAX                SEQUENCE OF B14_D80OutputTableEntry
    ACCESS                not-accessible
    STATUS                mandatory
    DESCRIPTION
    "A list of snmp b14_D80Output (read-only) object values."
    ::=  { b14_D80 2 }

b14_D80OutputTableEntry  OBJECT-TYPE
    SYNTAX                B14_D80OutputTableEntry
    ACCESS                not-accessible
    STATUS                mandatory
    DESCRIPTION
    "An b14_D80Output table entry containing data for a specific b14_D80Output."
    INDEX  { b14_D80OutputIndex }  ::=   { b14_D80OutputTable 1 }

B14_D80OutputTableEntry ::= SEQUENCE {
        b14_D80OutputIndex       INTEGER,
        b14_D80OutputName        DisplayString,
        b14_D80OutputValue       DisplayString
    }

b14_D80OutputIndex   OBJECT-TYPE
    SYNTAX           INTEGER(0..2147483647)
    ACCESS           read-only
    STATUS           mandatory
    DESCRIPTION
    "The index in the b14_D80Output table for a particular snmp b14_D80Output
	 object.  Used to address table entries."
    ::=   { b14_D80OutputTableEntry 1 }


b14_D80OutputName    OBJECT-TYPE
    SYNTAX           DisplayString
    ACCESS           read-only
    STATUS           mandatory
    DESCRIPTION
    "Name of station object."
    ::=   { b14_D80OutputTableEntry 2 }

b14_D80OutputValue    OBJECT-TYPE
    SYNTAX           DisplayString
    ACCESS           read-only
    STATUS           mandatory
    DESCRIPTION
    "Current value of station object. Is read-only ."
    ::=   { b14_D80OutputTableEntry 3 }


-- ***********************************
-- *
-- *  B14_D81
-- *
-- ***********************************
    b14_D81    OBJECT IDENTIFIER ::= { exportTables 69 }

-- ***********************************
-- *
-- *  B14_D81Input table declarations
-- *
-- ***********************************

b14_D81InputTable   OBJECT-TYPE
    SYNTAX                SEQUENCE OF B14_D81InputTableEntry
    ACCESS                not-accessible
    STATUS                mandatory
    DESCRIPTION
    "A list of snmp b14_D81Input (read-only) object values."
    ::=  { b14_D81 1 }

b14_D81InputTableEntry  OBJECT-TYPE
    SYNTAX                B14_D81InputTableEntry
    ACCESS                not-accessible
    STATUS                mandatory
    DESCRIPTION
    "An b14_D81Input table entry containing data for a specific b14_D81Input."
    INDEX  { b14_D81InputIndex }  ::=   { b14_D81InputTable 1 }

B14_D81InputTableEntry ::= SEQUENCE {
        b14_D81InputIndex       INTEGER,
        b14_D81InputName        DisplayString,
        b14_D81InputValue       DisplayString
    }

b14_D81InputIndex   OBJECT-TYPE
    SYNTAX           INTEGER(0..2147483647)
    ACCESS           read-only
    STATUS           mandatory
    DESCRIPTION
    "The index in the b14_D81Input table for a particular snmp b14_D81Input
	 object.  Used to address table entries."
    ::=   { b14_D81InputTableEntry 1 }


b14_D81InputName    OBJECT-TYPE
    SYNTAX           DisplayString
    ACCESS           read-only
    STATUS           mandatory
    DESCRIPTION
    "Name of station object."
    ::=   { b14_D81InputTableEntry 2 }

b14_D81InputValue    OBJECT-TYPE
    SYNTAX           DisplayString
    ACCESS           read-write
    STATUS           mandatory
    DESCRIPTION
    "Current value of station object. Is read-write ."
    ::=   { b14_D81InputTableEntry 3 }



-- ***********************************
-- *
-- *  B14_D81Output table declarations
-- *
-- ***********************************

b14_D81OutputTable   OBJECT-TYPE
    SYNTAX                SEQUENCE OF B14_D81OutputTableEntry
    ACCESS                not-accessible
    STATUS                mandatory
    DESCRIPTION
    "A list of snmp b14_D81Output (read-only) object values."
    ::=  { b14_D81 2 }

b14_D81OutputTableEntry  OBJECT-TYPE
    SYNTAX                B14_D81OutputTableEntry
    ACCESS                not-accessible
    STATUS                mandatory
    DESCRIPTION
    "An b14_D81Output table entry containing data for a specific b14_D81Output."
    INDEX  { b14_D81OutputIndex }  ::=   { b14_D81OutputTable 1 }

B14_D81OutputTableEntry ::= SEQUENCE {
        b14_D81OutputIndex       INTEGER,
        b14_D81OutputName        DisplayString,
        b14_D81OutputValue       DisplayString
    }

b14_D81OutputIndex   OBJECT-TYPE
    SYNTAX           INTEGER(0..2147483647)
    ACCESS           read-only
    STATUS           mandatory
    DESCRIPTION
    "The index in the b14_D81Output table for a particular snmp b14_D81Output
	 object.  Used to address table entries."
    ::=   { b14_D81OutputTableEntry 1 }


b14_D81OutputName    OBJECT-TYPE
    SYNTAX           DisplayString
    ACCESS           read-only
    STATUS           mandatory
    DESCRIPTION
    "Name of station object."
    ::=   { b14_D81OutputTableEntry 2 }

b14_D81OutputValue    OBJECT-TYPE
    SYNTAX           DisplayString
    ACCESS           read-only
    STATUS           mandatory
    DESCRIPTION
    "Current value of station object. Is read-only ."
    ::=   { b14_D81OutputTableEntry 3 }


-- ***********************************
-- *
-- *  B14_D3
-- *
-- ***********************************
    b14_D3    OBJECT IDENTIFIER ::= { exportTables 70 }

-- ***********************************
-- *
-- *  B14_D3Input table declarations
-- *
-- ***********************************

b14_D3InputTable   OBJECT-TYPE
    SYNTAX                SEQUENCE OF B14_D3InputTableEntry
    ACCESS                not-accessible
    STATUS                mandatory
    DESCRIPTION
    "A list of snmp b14_D3Input (read-only) object values."
    ::=  { b14_D3 1 }

b14_D3InputTableEntry  OBJECT-TYPE
    SYNTAX                B14_D3InputTableEntry
    ACCESS                not-accessible
    STATUS                mandatory
    DESCRIPTION
    "An b14_D3Input table entry containing data for a specific b14_D3Input."
    INDEX  { b14_D3InputIndex }  ::=   { b14_D3InputTable 1 }

B14_D3InputTableEntry ::= SEQUENCE {
        b14_D3InputIndex       INTEGER,
        b14_D3InputName        DisplayString,
        b14_D3InputValue       DisplayString
    }

b14_D3InputIndex   OBJECT-TYPE
    SYNTAX           INTEGER(0..2147483647)
    ACCESS           read-only
    STATUS           mandatory
    DESCRIPTION
    "The index in the b14_D3Input table for a particular snmp b14_D3Input
	 object.  Used to address table entries."
    ::=   { b14_D3InputTableEntry 1 }


b14_D3InputName    OBJECT-TYPE
    SYNTAX           DisplayString
    ACCESS           read-only
    STATUS           mandatory
    DESCRIPTION
    "Name of station object."
    ::=   { b14_D3InputTableEntry 2 }

b14_D3InputValue    OBJECT-TYPE
    SYNTAX           DisplayString
    ACCESS           read-write
    STATUS           mandatory
    DESCRIPTION
    "Current value of station object. Is read-write ."
    ::=   { b14_D3InputTableEntry 3 }



-- ***********************************
-- *
-- *  B14_D3Output table declarations
-- *
-- ***********************************

b14_D3OutputTable   OBJECT-TYPE
    SYNTAX                SEQUENCE OF B14_D3OutputTableEntry
    ACCESS                not-accessible
    STATUS                mandatory
    DESCRIPTION
    "A list of snmp b14_D3Output (read-only) object values."
    ::=  { b14_D3 2 }

b14_D3OutputTableEntry  OBJECT-TYPE
    SYNTAX                B14_D3OutputTableEntry
    ACCESS                not-accessible
    STATUS                mandatory
    DESCRIPTION
    "An b14_D3Output table entry containing data for a specific b14_D3Output."
    INDEX  { b14_D3OutputIndex }  ::=   { b14_D3OutputTable 1 }

B14_D3OutputTableEntry ::= SEQUENCE {
        b14_D3OutputIndex       INTEGER,
        b14_D3OutputName        DisplayString,
        b14_D3OutputValue       DisplayString
    }

b14_D3OutputIndex   OBJECT-TYPE
    SYNTAX           INTEGER(0..2147483647)
    ACCESS           read-only
    STATUS           mandatory
    DESCRIPTION
    "The index in the b14_D3Output table for a particular snmp b14_D3Output
	 object.  Used to address table entries."
    ::=   { b14_D3OutputTableEntry 1 }


b14_D3OutputName    OBJECT-TYPE
    SYNTAX           DisplayString
    ACCESS           read-only
    STATUS           mandatory
    DESCRIPTION
    "Name of station object."
    ::=   { b14_D3OutputTableEntry 2 }

b14_D3OutputValue    OBJECT-TYPE
    SYNTAX           DisplayString
    ACCESS           read-only
    STATUS           mandatory
    DESCRIPTION
    "Current value of station object. Is read-only ."
    ::=   { b14_D3OutputTableEntry 3 }


-- ***********************************
-- *
-- *  B14_D12
-- *
-- ***********************************
    b14_D12    OBJECT IDENTIFIER ::= { exportTables 71 }

-- ***********************************
-- *
-- *  B14_D12Input table declarations
-- *
-- ***********************************

b14_D12InputTable   OBJECT-TYPE
    SYNTAX                SEQUENCE OF B14_D12InputTableEntry
    ACCESS                not-accessible
    STATUS                mandatory
    DESCRIPTION
    "A list of snmp b14_D12Input (read-only) object values."
    ::=  { b14_D12 1 }

b14_D12InputTableEntry  OBJECT-TYPE
    SYNTAX                B14_D12InputTableEntry
    ACCESS                not-accessible
    STATUS                mandatory
    DESCRIPTION
    "An b14_D12Input table entry containing data for a specific b14_D12Input."
    INDEX  { b14_D12InputIndex }  ::=   { b14_D12InputTable 1 }

B14_D12InputTableEntry ::= SEQUENCE {
        b14_D12InputIndex       INTEGER,
        b14_D12InputName        DisplayString,
        b14_D12InputValue       DisplayString
    }

b14_D12InputIndex   OBJECT-TYPE
    SYNTAX           INTEGER(0..2147483647)
    ACCESS           read-only
    STATUS           mandatory
    DESCRIPTION
    "The index in the b14_D12Input table for a particular snmp b14_D12Input
	 object.  Used to address table entries."
    ::=   { b14_D12InputTableEntry 1 }


b14_D12InputName    OBJECT-TYPE
    SYNTAX           DisplayString
    ACCESS           read-only
    STATUS           mandatory
    DESCRIPTION
    "Name of station object."
    ::=   { b14_D12InputTableEntry 2 }

b14_D12InputValue    OBJECT-TYPE
    SYNTAX           DisplayString
    ACCESS           read-write
    STATUS           mandatory
    DESCRIPTION
    "Current value of station object. Is read-write ."
    ::=   { b14_D12InputTableEntry 3 }



-- ***********************************
-- *
-- *  B14_D12Output table declarations
-- *
-- ***********************************

b14_D12OutputTable   OBJECT-TYPE
    SYNTAX                SEQUENCE OF B14_D12OutputTableEntry
    ACCESS                not-accessible
    STATUS                mandatory
    DESCRIPTION
    "A list of snmp b14_D12Output (read-only) object values."
    ::=  { b14_D12 2 }

b14_D12OutputTableEntry  OBJECT-TYPE
    SYNTAX                B14_D12OutputTableEntry
    ACCESS                not-accessible
    STATUS                mandatory
    DESCRIPTION
    "An b14_D12Output table entry containing data for a specific b14_D12Output."
    INDEX  { b14_D12OutputIndex }  ::=   { b14_D12OutputTable 1 }

B14_D12OutputTableEntry ::= SEQUENCE {
        b14_D12OutputIndex       INTEGER,
        b14_D12OutputName        DisplayString,
        b14_D12OutputValue       DisplayString
    }

b14_D12OutputIndex   OBJECT-TYPE
    SYNTAX           INTEGER(0..2147483647)
    ACCESS           read-only
    STATUS           mandatory
    DESCRIPTION
    "The index in the b14_D12Output table for a particular snmp b14_D12Output
	 object.  Used to address table entries."
    ::=   { b14_D12OutputTableEntry 1 }


b14_D12OutputName    OBJECT-TYPE
    SYNTAX           DisplayString
    ACCESS           read-only
    STATUS           mandatory
    DESCRIPTION
    "Name of station object."
    ::=   { b14_D12OutputTableEntry 2 }

b14_D12OutputValue    OBJECT-TYPE
    SYNTAX           DisplayString
    ACCESS           read-only
    STATUS           mandatory
    DESCRIPTION
    "Current value of station object. Is read-only ."
    ::=   { b14_D12OutputTableEntry 3 }


-- ***********************************
-- *
-- *  B14_D13
-- *
-- ***********************************
    b14_D13    OBJECT IDENTIFIER ::= { exportTables 72 }

-- ***********************************
-- *
-- *  B14_D13Input table declarations
-- *
-- ***********************************

b14_D13InputTable   OBJECT-TYPE
    SYNTAX                SEQUENCE OF B14_D13InputTableEntry
    ACCESS                not-accessible
    STATUS                mandatory
    DESCRIPTION
    "A list of snmp b14_D13Input (read-only) object values."
    ::=  { b14_D13 1 }

b14_D13InputTableEntry  OBJECT-TYPE
    SYNTAX                B14_D13InputTableEntry
    ACCESS                not-accessible
    STATUS                mandatory
    DESCRIPTION
    "An b14_D13Input table entry containing data for a specific b14_D13Input."
    INDEX  { b14_D13InputIndex }  ::=   { b14_D13InputTable 1 }

B14_D13InputTableEntry ::= SEQUENCE {
        b14_D13InputIndex       INTEGER,
        b14_D13InputName        DisplayString,
        b14_D13InputValue       DisplayString
    }

b14_D13InputIndex   OBJECT-TYPE
    SYNTAX           INTEGER(0..2147483647)
    ACCESS           read-only
    STATUS           mandatory
    DESCRIPTION
    "The index in the b14_D13Input table for a particular snmp b14_D13Input
	 object.  Used to address table entries."
    ::=   { b14_D13InputTableEntry 1 }


b14_D13InputName    OBJECT-TYPE
    SYNTAX           DisplayString
    ACCESS           read-only
    STATUS           mandatory
    DESCRIPTION
    "Name of station object."
    ::=   { b14_D13InputTableEntry 2 }

b14_D13InputValue    OBJECT-TYPE
    SYNTAX           DisplayString
    ACCESS           read-write
    STATUS           mandatory
    DESCRIPTION
    "Current value of station object. Is read-write ."
    ::=   { b14_D13InputTableEntry 3 }



-- ***********************************
-- *
-- *  B14_D13Output table declarations
-- *
-- ***********************************

b14_D13OutputTable   OBJECT-TYPE
    SYNTAX                SEQUENCE OF B14_D13OutputTableEntry
    ACCESS                not-accessible
    STATUS                mandatory
    DESCRIPTION
    "A list of snmp b14_D13Output (read-only) object values."
    ::=  { b14_D13 2 }

b14_D13OutputTableEntry  OBJECT-TYPE
    SYNTAX                B14_D13OutputTableEntry
    ACCESS                not-accessible
    STATUS                mandatory
    DESCRIPTION
    "An b14_D13Output table entry containing data for a specific b14_D13Output."
    INDEX  { b14_D13OutputIndex }  ::=   { b14_D13OutputTable 1 }

B14_D13OutputTableEntry ::= SEQUENCE {
        b14_D13OutputIndex       INTEGER,
        b14_D13OutputName        DisplayString,
        b14_D13OutputValue       DisplayString
    }

b14_D13OutputIndex   OBJECT-TYPE
    SYNTAX           INTEGER(0..2147483647)
    ACCESS           read-only
    STATUS           mandatory
    DESCRIPTION
    "The index in the b14_D13Output table for a particular snmp b14_D13Output
	 object.  Used to address table entries."
    ::=   { b14_D13OutputTableEntry 1 }


b14_D13OutputName    OBJECT-TYPE
    SYNTAX           DisplayString
    ACCESS           read-only
    STATUS           mandatory
    DESCRIPTION
    "Name of station object."
    ::=   { b14_D13OutputTableEntry 2 }

b14_D13OutputValue    OBJECT-TYPE
    SYNTAX           DisplayString
    ACCESS           read-only
    STATUS           mandatory
    DESCRIPTION
    "Current value of station object. Is read-only ."
    ::=   { b14_D13OutputTableEntry 3 }


-- ***********************************
-- *
-- *  B14_D5
-- *
-- ***********************************
    b14_D5    OBJECT IDENTIFIER ::= { exportTables 73 }

-- ***********************************
-- *
-- *  B14_D5Input table declarations
-- *
-- ***********************************

b14_D5InputTable   OBJECT-TYPE
    SYNTAX                SEQUENCE OF B14_D5InputTableEntry
    ACCESS                not-accessible
    STATUS                mandatory
    DESCRIPTION
    "A list of snmp b14_D5Input (read-only) object values."
    ::=  { b14_D5 1 }

b14_D5InputTableEntry  OBJECT-TYPE
    SYNTAX                B14_D5InputTableEntry
    ACCESS                not-accessible
    STATUS                mandatory
    DESCRIPTION
    "An b14_D5Input table entry containing data for a specific b14_D5Input."
    INDEX  { b14_D5InputIndex }  ::=   { b14_D5InputTable 1 }

B14_D5InputTableEntry ::= SEQUENCE {
        b14_D5InputIndex       INTEGER,
        b14_D5InputName        DisplayString,
        b14_D5InputValue       DisplayString
    }

b14_D5InputIndex   OBJECT-TYPE
    SYNTAX           INTEGER(0..2147483647)
    ACCESS           read-only
    STATUS           mandatory
    DESCRIPTION
    "The index in the b14_D5Input table for a particular snmp b14_D5Input
	 object.  Used to address table entries."
    ::=   { b14_D5InputTableEntry 1 }


b14_D5InputName    OBJECT-TYPE
    SYNTAX           DisplayString
    ACCESS           read-only
    STATUS           mandatory
    DESCRIPTION
    "Name of station object."
    ::=   { b14_D5InputTableEntry 2 }

b14_D5InputValue    OBJECT-TYPE
    SYNTAX           DisplayString
    ACCESS           read-write
    STATUS           mandatory
    DESCRIPTION
    "Current value of station object. Is read-write ."
    ::=   { b14_D5InputTableEntry 3 }



-- ***********************************
-- *
-- *  B14_D5Output table declarations
-- *
-- ***********************************

b14_D5OutputTable   OBJECT-TYPE
    SYNTAX                SEQUENCE OF B14_D5OutputTableEntry
    ACCESS                not-accessible
    STATUS                mandatory
    DESCRIPTION
    "A list of snmp b14_D5Output (read-only) object values."
    ::=  { b14_D5 2 }

b14_D5OutputTableEntry  OBJECT-TYPE
    SYNTAX                B14_D5OutputTableEntry
    ACCESS                not-accessible
    STATUS                mandatory
    DESCRIPTION
    "An b14_D5Output table entry containing data for a specific b14_D5Output."
    INDEX  { b14_D5OutputIndex }  ::=   { b14_D5OutputTable 1 }

B14_D5OutputTableEntry ::= SEQUENCE {
        b14_D5OutputIndex       INTEGER,
        b14_D5OutputName        DisplayString,
        b14_D5OutputValue       DisplayString
    }

b14_D5OutputIndex   OBJECT-TYPE
    SYNTAX           INTEGER(0..2147483647)
    ACCESS           read-only
    STATUS           mandatory
    DESCRIPTION
    "The index in the b14_D5Output table for a particular snmp b14_D5Output
	 object.  Used to address table entries."
    ::=   { b14_D5OutputTableEntry 1 }


b14_D5OutputName    OBJECT-TYPE
    SYNTAX           DisplayString
    ACCESS           read-only
    STATUS           mandatory
    DESCRIPTION
    "Name of station object."
    ::=   { b14_D5OutputTableEntry 2 }

b14_D5OutputValue    OBJECT-TYPE
    SYNTAX           DisplayString
    ACCESS           read-only
    STATUS           mandatory
    DESCRIPTION
    "Current value of station object. Is read-only ."
    ::=   { b14_D5OutputTableEntry 3 }


-- ***********************************
-- *
-- *  B14_D4
-- *
-- ***********************************
    b14_D4    OBJECT IDENTIFIER ::= { exportTables 74 }

-- ***********************************
-- *
-- *  B14_D4Input table declarations
-- *
-- ***********************************

b14_D4InputTable   OBJECT-TYPE
    SYNTAX                SEQUENCE OF B14_D4InputTableEntry
    ACCESS                not-accessible
    STATUS                mandatory
    DESCRIPTION
    "A list of snmp b14_D4Input (read-only) object values."
    ::=  { b14_D4 1 }

b14_D4InputTableEntry  OBJECT-TYPE
    SYNTAX                B14_D4InputTableEntry
    ACCESS                not-accessible
    STATUS                mandatory
    DESCRIPTION
    "An b14_D4Input table entry containing data for a specific b14_D4Input."
    INDEX  { b14_D4InputIndex }  ::=   { b14_D4InputTable 1 }

B14_D4InputTableEntry ::= SEQUENCE {
        b14_D4InputIndex       INTEGER,
        b14_D4InputName        DisplayString,
        b14_D4InputValue       DisplayString
    }

b14_D4InputIndex   OBJECT-TYPE
    SYNTAX           INTEGER(0..2147483647)
    ACCESS           read-only
    STATUS           mandatory
    DESCRIPTION
    "The index in the b14_D4Input table for a particular snmp b14_D4Input
	 object.  Used to address table entries."
    ::=   { b14_D4InputTableEntry 1 }


b14_D4InputName    OBJECT-TYPE
    SYNTAX           DisplayString
    ACCESS           read-only
    STATUS           mandatory
    DESCRIPTION
    "Name of station object."
    ::=   { b14_D4InputTableEntry 2 }

b14_D4InputValue    OBJECT-TYPE
    SYNTAX           DisplayString
    ACCESS           read-write
    STATUS           mandatory
    DESCRIPTION
    "Current value of station object. Is read-write ."
    ::=   { b14_D4InputTableEntry 3 }



-- ***********************************
-- *
-- *  B14_D4Output table declarations
-- *
-- ***********************************

b14_D4OutputTable   OBJECT-TYPE
    SYNTAX                SEQUENCE OF B14_D4OutputTableEntry
    ACCESS                not-accessible
    STATUS                mandatory
    DESCRIPTION
    "A list of snmp b14_D4Output (read-only) object values."
    ::=  { b14_D4 2 }

b14_D4OutputTableEntry  OBJECT-TYPE
    SYNTAX                B14_D4OutputTableEntry
    ACCESS                not-accessible
    STATUS                mandatory
    DESCRIPTION
    "An b14_D4Output table entry containing data for a specific b14_D4Output."
    INDEX  { b14_D4OutputIndex }  ::=   { b14_D4OutputTable 1 }

B14_D4OutputTableEntry ::= SEQUENCE {
        b14_D4OutputIndex       INTEGER,
        b14_D4OutputName        DisplayString,
        b14_D4OutputValue       DisplayString
    }

b14_D4OutputIndex   OBJECT-TYPE
    SYNTAX           INTEGER(0..2147483647)
    ACCESS           read-only
    STATUS           mandatory
    DESCRIPTION
    "The index in the b14_D4Output table for a particular snmp b14_D4Output
	 object.  Used to address table entries."
    ::=   { b14_D4OutputTableEntry 1 }


b14_D4OutputName    OBJECT-TYPE
    SYNTAX           DisplayString
    ACCESS           read-only
    STATUS           mandatory
    DESCRIPTION
    "Name of station object."
    ::=   { b14_D4OutputTableEntry 2 }

b14_D4OutputValue    OBJECT-TYPE
    SYNTAX           DisplayString
    ACCESS           read-only
    STATUS           mandatory
    DESCRIPTION
    "Current value of station object. Is read-only ."
    ::=   { b14_D4OutputTableEntry 3 }


-- ***********************************
-- *
-- *  B14_D16
-- *
-- ***********************************
    b14_D16    OBJECT IDENTIFIER ::= { exportTables 75 }

-- ***********************************
-- *
-- *  B14_D16Input table declarations
-- *
-- ***********************************

b14_D16InputTable   OBJECT-TYPE
    SYNTAX                SEQUENCE OF B14_D16InputTableEntry
    ACCESS                not-accessible
    STATUS                mandatory
    DESCRIPTION
    "A list of snmp b14_D16Input (read-only) object values."
    ::=  { b14_D16 1 }

b14_D16InputTableEntry  OBJECT-TYPE
    SYNTAX                B14_D16InputTableEntry
    ACCESS                not-accessible
    STATUS                mandatory
    DESCRIPTION
    "An b14_D16Input table entry containing data for a specific b14_D16Input."
    INDEX  { b14_D16InputIndex }  ::=   { b14_D16InputTable 1 }

B14_D16InputTableEntry ::= SEQUENCE {
        b14_D16InputIndex       INTEGER,
        b14_D16InputName        DisplayString,
        b14_D16InputValue       DisplayString
    }

b14_D16InputIndex   OBJECT-TYPE
    SYNTAX           INTEGER(0..2147483647)
    ACCESS           read-only
    STATUS           mandatory
    DESCRIPTION
    "The index in the b14_D16Input table for a particular snmp b14_D16Input
	 object.  Used to address table entries."
    ::=   { b14_D16InputTableEntry 1 }


b14_D16InputName    OBJECT-TYPE
    SYNTAX           DisplayString
    ACCESS           read-only
    STATUS           mandatory
    DESCRIPTION
    "Name of station object."
    ::=   { b14_D16InputTableEntry 2 }

b14_D16InputValue    OBJECT-TYPE
    SYNTAX           DisplayString
    ACCESS           read-write
    STATUS           mandatory
    DESCRIPTION
    "Current value of station object. Is read-write ."
    ::=   { b14_D16InputTableEntry 3 }



-- ***********************************
-- *
-- *  B14_D16Output table declarations
-- *
-- ***********************************

b14_D16OutputTable   OBJECT-TYPE
    SYNTAX                SEQUENCE OF B14_D16OutputTableEntry
    ACCESS                not-accessible
    STATUS                mandatory
    DESCRIPTION
    "A list of snmp b14_D16Output (read-only) object values."
    ::=  { b14_D16 2 }

b14_D16OutputTableEntry  OBJECT-TYPE
    SYNTAX                B14_D16OutputTableEntry
    ACCESS                not-accessible
    STATUS                mandatory
    DESCRIPTION
    "An b14_D16Output table entry containing data for a specific b14_D16Output."
    INDEX  { b14_D16OutputIndex }  ::=   { b14_D16OutputTable 1 }

B14_D16OutputTableEntry ::= SEQUENCE {
        b14_D16OutputIndex       INTEGER,
        b14_D16OutputName        DisplayString,
        b14_D16OutputValue       DisplayString
    }

b14_D16OutputIndex   OBJECT-TYPE
    SYNTAX           INTEGER(0..2147483647)
    ACCESS           read-only
    STATUS           mandatory
    DESCRIPTION
    "The index in the b14_D16Output table for a particular snmp b14_D16Output
	 object.  Used to address table entries."
    ::=   { b14_D16OutputTableEntry 1 }


b14_D16OutputName    OBJECT-TYPE
    SYNTAX           DisplayString
    ACCESS           read-only
    STATUS           mandatory
    DESCRIPTION
    "Name of station object."
    ::=   { b14_D16OutputTableEntry 2 }

b14_D16OutputValue    OBJECT-TYPE
    SYNTAX           DisplayString
    ACCESS           read-only
    STATUS           mandatory
    DESCRIPTION
    "Current value of station object. Is read-only ."
    ::=   { b14_D16OutputTableEntry 3 }


-- ***********************************
-- *
-- *  B14_D17
-- *
-- ***********************************
    b14_D17    OBJECT IDENTIFIER ::= { exportTables 76 }

-- ***********************************
-- *
-- *  B14_D17Input table declarations
-- *
-- ***********************************

b14_D17InputTable   OBJECT-TYPE
    SYNTAX                SEQUENCE OF B14_D17InputTableEntry
    ACCESS                not-accessible
    STATUS                mandatory
    DESCRIPTION
    "A list of snmp b14_D17Input (read-only) object values."
    ::=  { b14_D17 1 }

b14_D17InputTableEntry  OBJECT-TYPE
    SYNTAX                B14_D17InputTableEntry
    ACCESS                not-accessible
    STATUS                mandatory
    DESCRIPTION
    "An b14_D17Input table entry containing data for a specific b14_D17Input."
    INDEX  { b14_D17InputIndex }  ::=   { b14_D17InputTable 1 }

B14_D17InputTableEntry ::= SEQUENCE {
        b14_D17InputIndex       INTEGER,
        b14_D17InputName        DisplayString,
        b14_D17InputValue       DisplayString
    }

b14_D17InputIndex   OBJECT-TYPE
    SYNTAX           INTEGER(0..2147483647)
    ACCESS           read-only
    STATUS           mandatory
    DESCRIPTION
    "The index in the b14_D17Input table for a particular snmp b14_D17Input
	 object.  Used to address table entries."
    ::=   { b14_D17InputTableEntry 1 }


b14_D17InputName    OBJECT-TYPE
    SYNTAX           DisplayString
    ACCESS           read-only
    STATUS           mandatory
    DESCRIPTION
    "Name of station object."
    ::=   { b14_D17InputTableEntry 2 }

b14_D17InputValue    OBJECT-TYPE
    SYNTAX           DisplayString
    ACCESS           read-write
    STATUS           mandatory
    DESCRIPTION
    "Current value of station object. Is read-write ."
    ::=   { b14_D17InputTableEntry 3 }



-- ***********************************
-- *
-- *  B14_D17Output table declarations
-- *
-- ***********************************

b14_D17OutputTable   OBJECT-TYPE
    SYNTAX                SEQUENCE OF B14_D17OutputTableEntry
    ACCESS                not-accessible
    STATUS                mandatory
    DESCRIPTION
    "A list of snmp b14_D17Output (read-only) object values."
    ::=  { b14_D17 2 }

b14_D17OutputTableEntry  OBJECT-TYPE
    SYNTAX                B14_D17OutputTableEntry
    ACCESS                not-accessible
    STATUS                mandatory
    DESCRIPTION
    "An b14_D17Output table entry containing data for a specific b14_D17Output."
    INDEX  { b14_D17OutputIndex }  ::=   { b14_D17OutputTable 1 }

B14_D17OutputTableEntry ::= SEQUENCE {
        b14_D17OutputIndex       INTEGER,
        b14_D17OutputName        DisplayString,
        b14_D17OutputValue       DisplayString
    }

b14_D17OutputIndex   OBJECT-TYPE
    SYNTAX           INTEGER(0..2147483647)
    ACCESS           read-only
    STATUS           mandatory
    DESCRIPTION
    "The index in the b14_D17Output table for a particular snmp b14_D17Output
	 object.  Used to address table entries."
    ::=   { b14_D17OutputTableEntry 1 }


b14_D17OutputName    OBJECT-TYPE
    SYNTAX           DisplayString
    ACCESS           read-only
    STATUS           mandatory
    DESCRIPTION
    "Name of station object."
    ::=   { b14_D17OutputTableEntry 2 }

b14_D17OutputValue    OBJECT-TYPE
    SYNTAX           DisplayString
    ACCESS           read-only
    STATUS           mandatory
    DESCRIPTION
    "Current value of station object. Is read-only ."
    ::=   { b14_D17OutputTableEntry 3 }


-- ***********************************
-- *
-- *  B14_D2
-- *
-- ***********************************
    b14_D2    OBJECT IDENTIFIER ::= { exportTables 77 }

-- ***********************************
-- *
-- *  B14_D2Input table declarations
-- *
-- ***********************************

b14_D2InputTable   OBJECT-TYPE
    SYNTAX                SEQUENCE OF B14_D2InputTableEntry
    ACCESS                not-accessible
    STATUS                mandatory
    DESCRIPTION
    "A list of snmp b14_D2Input (read-only) object values."
    ::=  { b14_D2 1 }

b14_D2InputTableEntry  OBJECT-TYPE
    SYNTAX                B14_D2InputTableEntry
    ACCESS                not-accessible
    STATUS                mandatory
    DESCRIPTION
    "An b14_D2Input table entry containing data for a specific b14_D2Input."
    INDEX  { b14_D2InputIndex }  ::=   { b14_D2InputTable 1 }

B14_D2InputTableEntry ::= SEQUENCE {
        b14_D2InputIndex       INTEGER,
        b14_D2InputName        DisplayString,
        b14_D2InputValue       DisplayString
    }

b14_D2InputIndex   OBJECT-TYPE
    SYNTAX           INTEGER(0..2147483647)
    ACCESS           read-only
    STATUS           mandatory
    DESCRIPTION
    "The index in the b14_D2Input table for a particular snmp b14_D2Input
	 object.  Used to address table entries."
    ::=   { b14_D2InputTableEntry 1 }


b14_D2InputName    OBJECT-TYPE
    SYNTAX           DisplayString
    ACCESS           read-only
    STATUS           mandatory
    DESCRIPTION
    "Name of station object."
    ::=   { b14_D2InputTableEntry 2 }

b14_D2InputValue    OBJECT-TYPE
    SYNTAX           DisplayString
    ACCESS           read-write
    STATUS           mandatory
    DESCRIPTION
    "Current value of station object. Is read-write ."
    ::=   { b14_D2InputTableEntry 3 }



-- ***********************************
-- *
-- *  B14_D2Output table declarations
-- *
-- ***********************************

b14_D2OutputTable   OBJECT-TYPE
    SYNTAX                SEQUENCE OF B14_D2OutputTableEntry
    ACCESS                not-accessible
    STATUS                mandatory
    DESCRIPTION
    "A list of snmp b14_D2Output (read-only) object values."
    ::=  { b14_D2 2 }

b14_D2OutputTableEntry  OBJECT-TYPE
    SYNTAX                B14_D2OutputTableEntry
    ACCESS                not-accessible
    STATUS                mandatory
    DESCRIPTION
    "An b14_D2Output table entry containing data for a specific b14_D2Output."
    INDEX  { b14_D2OutputIndex }  ::=   { b14_D2OutputTable 1 }

B14_D2OutputTableEntry ::= SEQUENCE {
        b14_D2OutputIndex       INTEGER,
        b14_D2OutputName        DisplayString,
        b14_D2OutputValue       DisplayString
    }

b14_D2OutputIndex   OBJECT-TYPE
    SYNTAX           INTEGER(0..2147483647)
    ACCESS           read-only
    STATUS           mandatory
    DESCRIPTION
    "The index in the b14_D2Output table for a particular snmp b14_D2Output
	 object.  Used to address table entries."
    ::=   { b14_D2OutputTableEntry 1 }


b14_D2OutputName    OBJECT-TYPE
    SYNTAX           DisplayString
    ACCESS           read-only
    STATUS           mandatory
    DESCRIPTION
    "Name of station object."
    ::=   { b14_D2OutputTableEntry 2 }

b14_D2OutputValue    OBJECT-TYPE
    SYNTAX           DisplayString
    ACCESS           read-only
    STATUS           mandatory
    DESCRIPTION
    "Current value of station object. Is read-only ."
    ::=   { b14_D2OutputTableEntry 3 }


-- ***********************************
-- *
-- *  B14_D15
-- *
-- ***********************************
    b14_D15    OBJECT IDENTIFIER ::= { exportTables 78 }

-- ***********************************
-- *
-- *  B14_D15Input table declarations
-- *
-- ***********************************

b14_D15InputTable   OBJECT-TYPE
    SYNTAX                SEQUENCE OF B14_D15InputTableEntry
    ACCESS                not-accessible
    STATUS                mandatory
    DESCRIPTION
    "A list of snmp b14_D15Input (read-only) object values."
    ::=  { b14_D15 1 }

b14_D15InputTableEntry  OBJECT-TYPE
    SYNTAX                B14_D15InputTableEntry
    ACCESS                not-accessible
    STATUS                mandatory
    DESCRIPTION
    "An b14_D15Input table entry containing data for a specific b14_D15Input."
    INDEX  { b14_D15InputIndex }  ::=   { b14_D15InputTable 1 }

B14_D15InputTableEntry ::= SEQUENCE {
        b14_D15InputIndex       INTEGER,
        b14_D15InputName        DisplayString,
        b14_D15InputValue       DisplayString
    }

b14_D15InputIndex   OBJECT-TYPE
    SYNTAX           INTEGER(0..2147483647)
    ACCESS           read-only
    STATUS           mandatory
    DESCRIPTION
    "The index in the b14_D15Input table for a particular snmp b14_D15Input
	 object.  Used to address table entries."
    ::=   { b14_D15InputTableEntry 1 }


b14_D15InputName    OBJECT-TYPE
    SYNTAX           DisplayString
    ACCESS           read-only
    STATUS           mandatory
    DESCRIPTION
    "Name of station object."
    ::=   { b14_D15InputTableEntry 2 }

b14_D15InputValue    OBJECT-TYPE
    SYNTAX           DisplayString
    ACCESS           read-write
    STATUS           mandatory
    DESCRIPTION
    "Current value of station object. Is read-write ."
    ::=   { b14_D15InputTableEntry 3 }



-- ***********************************
-- *
-- *  B14_D15Output table declarations
-- *
-- ***********************************

b14_D15OutputTable   OBJECT-TYPE
    SYNTAX                SEQUENCE OF B14_D15OutputTableEntry
    ACCESS                not-accessible
    STATUS                mandatory
    DESCRIPTION
    "A list of snmp b14_D15Output (read-only) object values."
    ::=  { b14_D15 2 }

b14_D15OutputTableEntry  OBJECT-TYPE
    SYNTAX                B14_D15OutputTableEntry
    ACCESS                not-accessible
    STATUS                mandatory
    DESCRIPTION
    "An b14_D15Output table entry containing data for a specific b14_D15Output."
    INDEX  { b14_D15OutputIndex }  ::=   { b14_D15OutputTable 1 }

B14_D15OutputTableEntry ::= SEQUENCE {
        b14_D15OutputIndex       INTEGER,
        b14_D15OutputName        DisplayString,
        b14_D15OutputValue       DisplayString
    }

b14_D15OutputIndex   OBJECT-TYPE
    SYNTAX           INTEGER(0..2147483647)
    ACCESS           read-only
    STATUS           mandatory
    DESCRIPTION
    "The index in the b14_D15Output table for a particular snmp b14_D15Output
	 object.  Used to address table entries."
    ::=   { b14_D15OutputTableEntry 1 }


b14_D15OutputName    OBJECT-TYPE
    SYNTAX           DisplayString
    ACCESS           read-only
    STATUS           mandatory
    DESCRIPTION
    "Name of station object."
    ::=   { b14_D15OutputTableEntry 2 }

b14_D15OutputValue    OBJECT-TYPE
    SYNTAX           DisplayString
    ACCESS           read-only
    STATUS           mandatory
    DESCRIPTION
    "Current value of station object. Is read-only ."
    ::=   { b14_D15OutputTableEntry 3 }


-- ***********************************
-- *
-- *  B14_D9
-- *
-- ***********************************
    b14_D9    OBJECT IDENTIFIER ::= { exportTables 79 }

-- ***********************************
-- *
-- *  B14_D9Input table declarations
-- *
-- ***********************************

b14_D9InputTable   OBJECT-TYPE
    SYNTAX                SEQUENCE OF B14_D9InputTableEntry
    ACCESS                not-accessible
    STATUS                mandatory
    DESCRIPTION
    "A list of snmp b14_D9Input (read-only) object values."
    ::=  { b14_D9 1 }

b14_D9InputTableEntry  OBJECT-TYPE
    SYNTAX                B14_D9InputTableEntry
    ACCESS                not-accessible
    STATUS                mandatory
    DESCRIPTION
    "An b14_D9Input table entry containing data for a specific b14_D9Input."
    INDEX  { b14_D9InputIndex }  ::=   { b14_D9InputTable 1 }

B14_D9InputTableEntry ::= SEQUENCE {
        b14_D9InputIndex       INTEGER,
        b14_D9InputName        DisplayString,
        b14_D9InputValue       DisplayString
    }

b14_D9InputIndex   OBJECT-TYPE
    SYNTAX           INTEGER(0..2147483647)
    ACCESS           read-only
    STATUS           mandatory
    DESCRIPTION
    "The index in the b14_D9Input table for a particular snmp b14_D9Input
	 object.  Used to address table entries."
    ::=   { b14_D9InputTableEntry 1 }


b14_D9InputName    OBJECT-TYPE
    SYNTAX           DisplayString
    ACCESS           read-only
    STATUS           mandatory
    DESCRIPTION
    "Name of station object."
    ::=   { b14_D9InputTableEntry 2 }

b14_D9InputValue    OBJECT-TYPE
    SYNTAX           DisplayString
    ACCESS           read-write
    STATUS           mandatory
    DESCRIPTION
    "Current value of station object. Is read-write ."
    ::=   { b14_D9InputTableEntry 3 }



-- ***********************************
-- *
-- *  B14_D9Output table declarations
-- *
-- ***********************************

b14_D9OutputTable   OBJECT-TYPE
    SYNTAX                SEQUENCE OF B14_D9OutputTableEntry
    ACCESS                not-accessible
    STATUS                mandatory
    DESCRIPTION
    "A list of snmp b14_D9Output (read-only) object values."
    ::=  { b14_D9 2 }

b14_D9OutputTableEntry  OBJECT-TYPE
    SYNTAX                B14_D9OutputTableEntry
    ACCESS                not-accessible
    STATUS                mandatory
    DESCRIPTION
    "An b14_D9Output table entry containing data for a specific b14_D9Output."
    INDEX  { b14_D9OutputIndex }  ::=   { b14_D9OutputTable 1 }

B14_D9OutputTableEntry ::= SEQUENCE {
        b14_D9OutputIndex       INTEGER,
        b14_D9OutputName        DisplayString,
        b14_D9OutputValue       DisplayString
    }

b14_D9OutputIndex   OBJECT-TYPE
    SYNTAX           INTEGER(0..2147483647)
    ACCESS           read-only
    STATUS           mandatory
    DESCRIPTION
    "The index in the b14_D9Output table for a particular snmp b14_D9Output
	 object.  Used to address table entries."
    ::=   { b14_D9OutputTableEntry 1 }


b14_D9OutputName    OBJECT-TYPE
    SYNTAX           DisplayString
    ACCESS           read-only
    STATUS           mandatory
    DESCRIPTION
    "Name of station object."
    ::=   { b14_D9OutputTableEntry 2 }

b14_D9OutputValue    OBJECT-TYPE
    SYNTAX           DisplayString
    ACCESS           read-only
    STATUS           mandatory
    DESCRIPTION
    "Current value of station object. Is read-only ."
    ::=   { b14_D9OutputTableEntry 3 }


-- ***********************************
-- *
-- *  B14_D8
-- *
-- ***********************************
    b14_D8    OBJECT IDENTIFIER ::= { exportTables 80 }

-- ***********************************
-- *
-- *  B14_D8Input table declarations
-- *
-- ***********************************

b14_D8InputTable   OBJECT-TYPE
    SYNTAX                SEQUENCE OF B14_D8InputTableEntry
    ACCESS                not-accessible
    STATUS                mandatory
    DESCRIPTION
    "A list of snmp b14_D8Input (read-only) object values."
    ::=  { b14_D8 1 }

b14_D8InputTableEntry  OBJECT-TYPE
    SYNTAX                B14_D8InputTableEntry
    ACCESS                not-accessible
    STATUS                mandatory
    DESCRIPTION
    "An b14_D8Input table entry containing data for a specific b14_D8Input."
    INDEX  { b14_D8InputIndex }  ::=   { b14_D8InputTable 1 }

B14_D8InputTableEntry ::= SEQUENCE {
        b14_D8InputIndex       INTEGER,
        b14_D8InputName        DisplayString,
        b14_D8InputValue       DisplayString
    }

b14_D8InputIndex   OBJECT-TYPE
    SYNTAX           INTEGER(0..2147483647)
    ACCESS           read-only
    STATUS           mandatory
    DESCRIPTION
    "The index in the b14_D8Input table for a particular snmp b14_D8Input
	 object.  Used to address table entries."
    ::=   { b14_D8InputTableEntry 1 }


b14_D8InputName    OBJECT-TYPE
    SYNTAX           DisplayString
    ACCESS           read-only
    STATUS           mandatory
    DESCRIPTION
    "Name of station object."
    ::=   { b14_D8InputTableEntry 2 }

b14_D8InputValue    OBJECT-TYPE
    SYNTAX           DisplayString
    ACCESS           read-write
    STATUS           mandatory
    DESCRIPTION
    "Current value of station object. Is read-write ."
    ::=   { b14_D8InputTableEntry 3 }



-- ***********************************
-- *
-- *  B14_D8Output table declarations
-- *
-- ***********************************

b14_D8OutputTable   OBJECT-TYPE
    SYNTAX                SEQUENCE OF B14_D8OutputTableEntry
    ACCESS                not-accessible
    STATUS                mandatory
    DESCRIPTION
    "A list of snmp b14_D8Output (read-only) object values."
    ::=  { b14_D8 2 }

b14_D8OutputTableEntry  OBJECT-TYPE
    SYNTAX                B14_D8OutputTableEntry
    ACCESS                not-accessible
    STATUS                mandatory
    DESCRIPTION
    "An b14_D8Output table entry containing data for a specific b14_D8Output."
    INDEX  { b14_D8OutputIndex }  ::=   { b14_D8OutputTable 1 }

B14_D8OutputTableEntry ::= SEQUENCE {
        b14_D8OutputIndex       INTEGER,
        b14_D8OutputName        DisplayString,
        b14_D8OutputValue       DisplayString
    }

b14_D8OutputIndex   OBJECT-TYPE
    SYNTAX           INTEGER(0..2147483647)
    ACCESS           read-only
    STATUS           mandatory
    DESCRIPTION
    "The index in the b14_D8Output table for a particular snmp b14_D8Output
	 object.  Used to address table entries."
    ::=   { b14_D8OutputTableEntry 1 }


b14_D8OutputName    OBJECT-TYPE
    SYNTAX           DisplayString
    ACCESS           read-only
    STATUS           mandatory
    DESCRIPTION
    "Name of station object."
    ::=   { b14_D8OutputTableEntry 2 }

b14_D8OutputValue    OBJECT-TYPE
    SYNTAX           DisplayString
    ACCESS           read-only
    STATUS           mandatory
    DESCRIPTION
    "Current value of station object. Is read-only ."
    ::=   { b14_D8OutputTableEntry 3 }


-- ***********************************
-- *
-- *  B14_D6
-- *
-- ***********************************
    b14_D6    OBJECT IDENTIFIER ::= { exportTables 81 }

-- ***********************************
-- *
-- *  B14_D6Input table declarations
-- *
-- ***********************************

b14_D6InputTable   OBJECT-TYPE
    SYNTAX                SEQUENCE OF B14_D6InputTableEntry
    ACCESS                not-accessible
    STATUS                mandatory
    DESCRIPTION
    "A list of snmp b14_D6Input (read-only) object values."
    ::=  { b14_D6 1 }

b14_D6InputTableEntry  OBJECT-TYPE
    SYNTAX                B14_D6InputTableEntry
    ACCESS                not-accessible
    STATUS                mandatory
    DESCRIPTION
    "An b14_D6Input table entry containing data for a specific b14_D6Input."
    INDEX  { b14_D6InputIndex }  ::=   { b14_D6InputTable 1 }

B14_D6InputTableEntry ::= SEQUENCE {
        b14_D6InputIndex       INTEGER,
        b14_D6InputName        DisplayString,
        b14_D6InputValue       DisplayString
    }

b14_D6InputIndex   OBJECT-TYPE
    SYNTAX           INTEGER(0..2147483647)
    ACCESS           read-only
    STATUS           mandatory
    DESCRIPTION
    "The index in the b14_D6Input table for a particular snmp b14_D6Input
	 object.  Used to address table entries."
    ::=   { b14_D6InputTableEntry 1 }


b14_D6InputName    OBJECT-TYPE
    SYNTAX           DisplayString
    ACCESS           read-only
    STATUS           mandatory
    DESCRIPTION
    "Name of station object."
    ::=   { b14_D6InputTableEntry 2 }

b14_D6InputValue    OBJECT-TYPE
    SYNTAX           DisplayString
    ACCESS           read-write
    STATUS           mandatory
    DESCRIPTION
    "Current value of station object. Is read-write ."
    ::=   { b14_D6InputTableEntry 3 }



-- ***********************************
-- *
-- *  B14_D6Output table declarations
-- *
-- ***********************************

b14_D6OutputTable   OBJECT-TYPE
    SYNTAX                SEQUENCE OF B14_D6OutputTableEntry
    ACCESS                not-accessible
    STATUS                mandatory
    DESCRIPTION
    "A list of snmp b14_D6Output (read-only) object values."
    ::=  { b14_D6 2 }

b14_D6OutputTableEntry  OBJECT-TYPE
    SYNTAX                B14_D6OutputTableEntry
    ACCESS                not-accessible
    STATUS                mandatory
    DESCRIPTION
    "An b14_D6Output table entry containing data for a specific b14_D6Output."
    INDEX  { b14_D6OutputIndex }  ::=   { b14_D6OutputTable 1 }

B14_D6OutputTableEntry ::= SEQUENCE {
        b14_D6OutputIndex       INTEGER,
        b14_D6OutputName        DisplayString,
        b14_D6OutputValue       DisplayString
    }

b14_D6OutputIndex   OBJECT-TYPE
    SYNTAX           INTEGER(0..2147483647)
    ACCESS           read-only
    STATUS           mandatory
    DESCRIPTION
    "The index in the b14_D6Output table for a particular snmp b14_D6Output
	 object.  Used to address table entries."
    ::=   { b14_D6OutputTableEntry 1 }


b14_D6OutputName    OBJECT-TYPE
    SYNTAX           DisplayString
    ACCESS           read-only
    STATUS           mandatory
    DESCRIPTION
    "Name of station object."
    ::=   { b14_D6OutputTableEntry 2 }

b14_D6OutputValue    OBJECT-TYPE
    SYNTAX           DisplayString
    ACCESS           read-only
    STATUS           mandatory
    DESCRIPTION
    "Current value of station object. Is read-only ."
    ::=   { b14_D6OutputTableEntry 3 }


-- ***********************************
-- *
-- *  B14_D11
-- *
-- ***********************************
    b14_D11    OBJECT IDENTIFIER ::= { exportTables 82 }

-- ***********************************
-- *
-- *  B14_D11Input table declarations
-- *
-- ***********************************

b14_D11InputTable   OBJECT-TYPE
    SYNTAX                SEQUENCE OF B14_D11InputTableEntry
    ACCESS                not-accessible
    STATUS                mandatory
    DESCRIPTION
    "A list of snmp b14_D11Input (read-only) object values."
    ::=  { b14_D11 1 }

b14_D11InputTableEntry  OBJECT-TYPE
    SYNTAX                B14_D11InputTableEntry
    ACCESS                not-accessible
    STATUS                mandatory
    DESCRIPTION
    "An b14_D11Input table entry containing data for a specific b14_D11Input."
    INDEX  { b14_D11InputIndex }  ::=   { b14_D11InputTable 1 }

B14_D11InputTableEntry ::= SEQUENCE {
        b14_D11InputIndex       INTEGER,
        b14_D11InputName        DisplayString,
        b14_D11InputValue       DisplayString
    }

b14_D11InputIndex   OBJECT-TYPE
    SYNTAX           INTEGER(0..2147483647)
    ACCESS           read-only
    STATUS           mandatory
    DESCRIPTION
    "The index in the b14_D11Input table for a particular snmp b14_D11Input
	 object.  Used to address table entries."
    ::=   { b14_D11InputTableEntry 1 }


b14_D11InputName    OBJECT-TYPE
    SYNTAX           DisplayString
    ACCESS           read-only
    STATUS           mandatory
    DESCRIPTION
    "Name of station object."
    ::=   { b14_D11InputTableEntry 2 }

b14_D11InputValue    OBJECT-TYPE
    SYNTAX           DisplayString
    ACCESS           read-write
    STATUS           mandatory
    DESCRIPTION
    "Current value of station object. Is read-write ."
    ::=   { b14_D11InputTableEntry 3 }



-- ***********************************
-- *
-- *  B14_D11Output table declarations
-- *
-- ***********************************

b14_D11OutputTable   OBJECT-TYPE
    SYNTAX                SEQUENCE OF B14_D11OutputTableEntry
    ACCESS                not-accessible
    STATUS                mandatory
    DESCRIPTION
    "A list of snmp b14_D11Output (read-only) object values."
    ::=  { b14_D11 2 }

b14_D11OutputTableEntry  OBJECT-TYPE
    SYNTAX                B14_D11OutputTableEntry
    ACCESS                not-accessible
    STATUS                mandatory
    DESCRIPTION
    "An b14_D11Output table entry containing data for a specific b14_D11Output."
    INDEX  { b14_D11OutputIndex }  ::=   { b14_D11OutputTable 1 }

B14_D11OutputTableEntry ::= SEQUENCE {
        b14_D11OutputIndex       INTEGER,
        b14_D11OutputName        DisplayString,
        b14_D11OutputValue       DisplayString
    }

b14_D11OutputIndex   OBJECT-TYPE
    SYNTAX           INTEGER(0..2147483647)
    ACCESS           read-only
    STATUS           mandatory
    DESCRIPTION
    "The index in the b14_D11Output table for a particular snmp b14_D11Output
	 object.  Used to address table entries."
    ::=   { b14_D11OutputTableEntry 1 }


b14_D11OutputName    OBJECT-TYPE
    SYNTAX           DisplayString
    ACCESS           read-only
    STATUS           mandatory
    DESCRIPTION
    "Name of station object."
    ::=   { b14_D11OutputTableEntry 2 }

b14_D11OutputValue    OBJECT-TYPE
    SYNTAX           DisplayString
    ACCESS           read-only
    STATUS           mandatory
    DESCRIPTION
    "Current value of station object. Is read-only ."
    ::=   { b14_D11OutputTableEntry 3 }


-- ***********************************
-- *
-- *  B14_D7
-- *
-- ***********************************
    b14_D7    OBJECT IDENTIFIER ::= { exportTables 83 }

-- ***********************************
-- *
-- *  B14_D7Input table declarations
-- *
-- ***********************************

b14_D7InputTable   OBJECT-TYPE
    SYNTAX                SEQUENCE OF B14_D7InputTableEntry
    ACCESS                not-accessible
    STATUS                mandatory
    DESCRIPTION
    "A list of snmp b14_D7Input (read-only) object values."
    ::=  { b14_D7 1 }

b14_D7InputTableEntry  OBJECT-TYPE
    SYNTAX                B14_D7InputTableEntry
    ACCESS                not-accessible
    STATUS                mandatory
    DESCRIPTION
    "An b14_D7Input table entry containing data for a specific b14_D7Input."
    INDEX  { b14_D7InputIndex }  ::=   { b14_D7InputTable 1 }

B14_D7InputTableEntry ::= SEQUENCE {
        b14_D7InputIndex       INTEGER,
        b14_D7InputName        DisplayString,
        b14_D7InputValue       DisplayString
    }

b14_D7InputIndex   OBJECT-TYPE
    SYNTAX           INTEGER(0..2147483647)
    ACCESS           read-only
    STATUS           mandatory
    DESCRIPTION
    "The index in the b14_D7Input table for a particular snmp b14_D7Input
	 object.  Used to address table entries."
    ::=   { b14_D7InputTableEntry 1 }


b14_D7InputName    OBJECT-TYPE
    SYNTAX           DisplayString
    ACCESS           read-only
    STATUS           mandatory
    DESCRIPTION
    "Name of station object."
    ::=   { b14_D7InputTableEntry 2 }

b14_D7InputValue    OBJECT-TYPE
    SYNTAX           DisplayString
    ACCESS           read-write
    STATUS           mandatory
    DESCRIPTION
    "Current value of station object. Is read-write ."
    ::=   { b14_D7InputTableEntry 3 }



-- ***********************************
-- *
-- *  B14_D7Output table declarations
-- *
-- ***********************************

b14_D7OutputTable   OBJECT-TYPE
    SYNTAX                SEQUENCE OF B14_D7OutputTableEntry
    ACCESS                not-accessible
    STATUS                mandatory
    DESCRIPTION
    "A list of snmp b14_D7Output (read-only) object values."
    ::=  { b14_D7 2 }

b14_D7OutputTableEntry  OBJECT-TYPE
    SYNTAX                B14_D7OutputTableEntry
    ACCESS                not-accessible
    STATUS                mandatory
    DESCRIPTION
    "An b14_D7Output table entry containing data for a specific b14_D7Output."
    INDEX  { b14_D7OutputIndex }  ::=   { b14_D7OutputTable 1 }

B14_D7OutputTableEntry ::= SEQUENCE {
        b14_D7OutputIndex       INTEGER,
        b14_D7OutputName        DisplayString,
        b14_D7OutputValue       DisplayString
    }

b14_D7OutputIndex   OBJECT-TYPE
    SYNTAX           INTEGER(0..2147483647)
    ACCESS           read-only
    STATUS           mandatory
    DESCRIPTION
    "The index in the b14_D7Output table for a particular snmp b14_D7Output
	 object.  Used to address table entries."
    ::=   { b14_D7OutputTableEntry 1 }


b14_D7OutputName    OBJECT-TYPE
    SYNTAX           DisplayString
    ACCESS           read-only
    STATUS           mandatory
    DESCRIPTION
    "Name of station object."
    ::=   { b14_D7OutputTableEntry 2 }

b14_D7OutputValue    OBJECT-TYPE
    SYNTAX           DisplayString
    ACCESS           read-only
    STATUS           mandatory
    DESCRIPTION
    "Current value of station object. Is read-only ."
    ::=   { b14_D7OutputTableEntry 3 }


-- ***********************************
-- *
-- *  B14_D14
-- *
-- ***********************************
    b14_D14    OBJECT IDENTIFIER ::= { exportTables 84 }

-- ***********************************
-- *
-- *  B14_D14Input table declarations
-- *
-- ***********************************

b14_D14InputTable   OBJECT-TYPE
    SYNTAX                SEQUENCE OF B14_D14InputTableEntry
    ACCESS                not-accessible
    STATUS                mandatory
    DESCRIPTION
    "A list of snmp b14_D14Input (read-only) object values."
    ::=  { b14_D14 1 }

b14_D14InputTableEntry  OBJECT-TYPE
    SYNTAX                B14_D14InputTableEntry
    ACCESS                not-accessible
    STATUS                mandatory
    DESCRIPTION
    "An b14_D14Input table entry containing data for a specific b14_D14Input."
    INDEX  { b14_D14InputIndex }  ::=   { b14_D14InputTable 1 }

B14_D14InputTableEntry ::= SEQUENCE {
        b14_D14InputIndex       INTEGER,
        b14_D14InputName        DisplayString,
        b14_D14InputValue       DisplayString
    }

b14_D14InputIndex   OBJECT-TYPE
    SYNTAX           INTEGER(0..2147483647)
    ACCESS           read-only
    STATUS           mandatory
    DESCRIPTION
    "The index in the b14_D14Input table for a particular snmp b14_D14Input
	 object.  Used to address table entries."
    ::=   { b14_D14InputTableEntry 1 }


b14_D14InputName    OBJECT-TYPE
    SYNTAX           DisplayString
    ACCESS           read-only
    STATUS           mandatory
    DESCRIPTION
    "Name of station object."
    ::=   { b14_D14InputTableEntry 2 }

b14_D14InputValue    OBJECT-TYPE
    SYNTAX           DisplayString
    ACCESS           read-write
    STATUS           mandatory
    DESCRIPTION
    "Current value of station object. Is read-write ."
    ::=   { b14_D14InputTableEntry 3 }



-- ***********************************
-- *
-- *  B14_D14Output table declarations
-- *
-- ***********************************

b14_D14OutputTable   OBJECT-TYPE
    SYNTAX                SEQUENCE OF B14_D14OutputTableEntry
    ACCESS                not-accessible
    STATUS                mandatory
    DESCRIPTION
    "A list of snmp b14_D14Output (read-only) object values."
    ::=  { b14_D14 2 }

b14_D14OutputTableEntry  OBJECT-TYPE
    SYNTAX                B14_D14OutputTableEntry
    ACCESS                not-accessible
    STATUS                mandatory
    DESCRIPTION
    "An b14_D14Output table entry containing data for a specific b14_D14Output."
    INDEX  { b14_D14OutputIndex }  ::=   { b14_D14OutputTable 1 }

B14_D14OutputTableEntry ::= SEQUENCE {
        b14_D14OutputIndex       INTEGER,
        b14_D14OutputName        DisplayString,
        b14_D14OutputValue       DisplayString
    }

b14_D14OutputIndex   OBJECT-TYPE
    SYNTAX           INTEGER(0..2147483647)
    ACCESS           read-only
    STATUS           mandatory
    DESCRIPTION
    "The index in the b14_D14Output table for a particular snmp b14_D14Output
	 object.  Used to address table entries."
    ::=   { b14_D14OutputTableEntry 1 }


b14_D14OutputName    OBJECT-TYPE
    SYNTAX           DisplayString
    ACCESS           read-only
    STATUS           mandatory
    DESCRIPTION
    "Name of station object."
    ::=   { b14_D14OutputTableEntry 2 }

b14_D14OutputValue    OBJECT-TYPE
    SYNTAX           DisplayString
    ACCESS           read-only
    STATUS           mandatory
    DESCRIPTION
    "Current value of station object. Is read-only ."
    ::=   { b14_D14OutputTableEntry 3 }


-- ***********************************
-- *
-- *  B14_D10
-- *
-- ***********************************
    b14_D10    OBJECT IDENTIFIER ::= { exportTables 85 }

-- ***********************************
-- *
-- *  B14_D10Input table declarations
-- *
-- ***********************************

b14_D10InputTable   OBJECT-TYPE
    SYNTAX                SEQUENCE OF B14_D10InputTableEntry
    ACCESS                not-accessible
    STATUS                mandatory
    DESCRIPTION
    "A list of snmp b14_D10Input (read-only) object values."
    ::=  { b14_D10 1 }

b14_D10InputTableEntry  OBJECT-TYPE
    SYNTAX                B14_D10InputTableEntry
    ACCESS                not-accessible
    STATUS                mandatory
    DESCRIPTION
    "An b14_D10Input table entry containing data for a specific b14_D10Input."
    INDEX  { b14_D10InputIndex }  ::=   { b14_D10InputTable 1 }

B14_D10InputTableEntry ::= SEQUENCE {
        b14_D10InputIndex       INTEGER,
        b14_D10InputName        DisplayString,
        b14_D10InputValue       DisplayString
    }

b14_D10InputIndex   OBJECT-TYPE
    SYNTAX           INTEGER(0..2147483647)
    ACCESS           read-only
    STATUS           mandatory
    DESCRIPTION
    "The index in the b14_D10Input table for a particular snmp b14_D10Input
	 object.  Used to address table entries."
    ::=   { b14_D10InputTableEntry 1 }


b14_D10InputName    OBJECT-TYPE
    SYNTAX           DisplayString
    ACCESS           read-only
    STATUS           mandatory
    DESCRIPTION
    "Name of station object."
    ::=   { b14_D10InputTableEntry 2 }

b14_D10InputValue    OBJECT-TYPE
    SYNTAX           DisplayString
    ACCESS           read-write
    STATUS           mandatory
    DESCRIPTION
    "Current value of station object. Is read-write ."
    ::=   { b14_D10InputTableEntry 3 }



-- ***********************************
-- *
-- *  B14_D10Output table declarations
-- *
-- ***********************************

b14_D10OutputTable   OBJECT-TYPE
    SYNTAX                SEQUENCE OF B14_D10OutputTableEntry
    ACCESS                not-accessible
    STATUS                mandatory
    DESCRIPTION
    "A list of snmp b14_D10Output (read-only) object values."
    ::=  { b14_D10 2 }

b14_D10OutputTableEntry  OBJECT-TYPE
    SYNTAX                B14_D10OutputTableEntry
    ACCESS                not-accessible
    STATUS                mandatory
    DESCRIPTION
    "An b14_D10Output table entry containing data for a specific b14_D10Output."
    INDEX  { b14_D10OutputIndex }  ::=   { b14_D10OutputTable 1 }

B14_D10OutputTableEntry ::= SEQUENCE {
        b14_D10OutputIndex       INTEGER,
        b14_D10OutputName        DisplayString,
        b14_D10OutputValue       DisplayString
    }

b14_D10OutputIndex   OBJECT-TYPE
    SYNTAX           INTEGER(0..2147483647)
    ACCESS           read-only
    STATUS           mandatory
    DESCRIPTION
    "The index in the b14_D10Output table for a particular snmp b14_D10Output
	 object.  Used to address table entries."
    ::=   { b14_D10OutputTableEntry 1 }


b14_D10OutputName    OBJECT-TYPE
    SYNTAX           DisplayString
    ACCESS           read-only
    STATUS           mandatory
    DESCRIPTION
    "Name of station object."
    ::=   { b14_D10OutputTableEntry 2 }

b14_D10OutputValue    OBJECT-TYPE
    SYNTAX           DisplayString
    ACCESS           read-only
    STATUS           mandatory
    DESCRIPTION
    "Current value of station object. Is read-only ."
    ::=   { b14_D10OutputTableEntry 3 }


-- ***********************************
-- *
-- *  B14_D43
-- *
-- ***********************************
    b14_D43    OBJECT IDENTIFIER ::= { exportTables 86 }

-- ***********************************
-- *
-- *  B14_D43Input table declarations
-- *
-- ***********************************

b14_D43InputTable   OBJECT-TYPE
    SYNTAX                SEQUENCE OF B14_D43InputTableEntry
    ACCESS                not-accessible
    STATUS                mandatory
    DESCRIPTION
    "A list of snmp b14_D43Input (read-only) object values."
    ::=  { b14_D43 1 }

b14_D43InputTableEntry  OBJECT-TYPE
    SYNTAX                B14_D43InputTableEntry
    ACCESS                not-accessible
    STATUS                mandatory
    DESCRIPTION
    "An b14_D43Input table entry containing data for a specific b14_D43Input."
    INDEX  { b14_D43InputIndex }  ::=   { b14_D43InputTable 1 }

B14_D43InputTableEntry ::= SEQUENCE {
        b14_D43InputIndex       INTEGER,
        b14_D43InputName        DisplayString,
        b14_D43InputValue       DisplayString
    }

b14_D43InputIndex   OBJECT-TYPE
    SYNTAX           INTEGER(0..2147483647)
    ACCESS           read-only
    STATUS           mandatory
    DESCRIPTION
    "The index in the b14_D43Input table for a particular snmp b14_D43Input
	 object.  Used to address table entries."
    ::=   { b14_D43InputTableEntry 1 }


b14_D43InputName    OBJECT-TYPE
    SYNTAX           DisplayString
    ACCESS           read-only
    STATUS           mandatory
    DESCRIPTION
    "Name of station object."
    ::=   { b14_D43InputTableEntry 2 }

b14_D43InputValue    OBJECT-TYPE
    SYNTAX           DisplayString
    ACCESS           read-write
    STATUS           mandatory
    DESCRIPTION
    "Current value of station object. Is read-write ."
    ::=   { b14_D43InputTableEntry 3 }



-- ***********************************
-- *
-- *  B14_D43Output table declarations
-- *
-- ***********************************

b14_D43OutputTable   OBJECT-TYPE
    SYNTAX                SEQUENCE OF B14_D43OutputTableEntry
    ACCESS                not-accessible
    STATUS                mandatory
    DESCRIPTION
    "A list of snmp b14_D43Output (read-only) object values."
    ::=  { b14_D43 2 }

b14_D43OutputTableEntry  OBJECT-TYPE
    SYNTAX                B14_D43OutputTableEntry
    ACCESS                not-accessible
    STATUS                mandatory
    DESCRIPTION
    "An b14_D43Output table entry containing data for a specific b14_D43Output."
    INDEX  { b14_D43OutputIndex }  ::=   { b14_D43OutputTable 1 }

B14_D43OutputTableEntry ::= SEQUENCE {
        b14_D43OutputIndex       INTEGER,
        b14_D43OutputName        DisplayString,
        b14_D43OutputValue       DisplayString
    }

b14_D43OutputIndex   OBJECT-TYPE
    SYNTAX           INTEGER(0..2147483647)
    ACCESS           read-only
    STATUS           mandatory
    DESCRIPTION
    "The index in the b14_D43Output table for a particular snmp b14_D43Output
	 object.  Used to address table entries."
    ::=   { b14_D43OutputTableEntry 1 }


b14_D43OutputName    OBJECT-TYPE
    SYNTAX           DisplayString
    ACCESS           read-only
    STATUS           mandatory
    DESCRIPTION
    "Name of station object."
    ::=   { b14_D43OutputTableEntry 2 }

b14_D43OutputValue    OBJECT-TYPE
    SYNTAX           DisplayString
    ACCESS           read-only
    STATUS           mandatory
    DESCRIPTION
    "Current value of station object. Is read-only ."
    ::=   { b14_D43OutputTableEntry 3 }


-- ***********************************
-- *
-- *  B14_D40
-- *
-- ***********************************
    b14_D40    OBJECT IDENTIFIER ::= { exportTables 87 }

-- ***********************************
-- *
-- *  B14_D40Input table declarations
-- *
-- ***********************************

b14_D40InputTable   OBJECT-TYPE
    SYNTAX                SEQUENCE OF B14_D40InputTableEntry
    ACCESS                not-accessible
    STATUS                mandatory
    DESCRIPTION
    "A list of snmp b14_D40Input (read-only) object values."
    ::=  { b14_D40 1 }

b14_D40InputTableEntry  OBJECT-TYPE
    SYNTAX                B14_D40InputTableEntry
    ACCESS                not-accessible
    STATUS                mandatory
    DESCRIPTION
    "An b14_D40Input table entry containing data for a specific b14_D40Input."
    INDEX  { b14_D40InputIndex }  ::=   { b14_D40InputTable 1 }

B14_D40InputTableEntry ::= SEQUENCE {
        b14_D40InputIndex       INTEGER,
        b14_D40InputName        DisplayString,
        b14_D40InputValue       DisplayString
    }

b14_D40InputIndex   OBJECT-TYPE
    SYNTAX           INTEGER(0..2147483647)
    ACCESS           read-only
    STATUS           mandatory
    DESCRIPTION
    "The index in the b14_D40Input table for a particular snmp b14_D40Input
	 object.  Used to address table entries."
    ::=   { b14_D40InputTableEntry 1 }


b14_D40InputName    OBJECT-TYPE
    SYNTAX           DisplayString
    ACCESS           read-only
    STATUS           mandatory
    DESCRIPTION
    "Name of station object."
    ::=   { b14_D40InputTableEntry 2 }

b14_D40InputValue    OBJECT-TYPE
    SYNTAX           DisplayString
    ACCESS           read-write
    STATUS           mandatory
    DESCRIPTION
    "Current value of station object. Is read-write ."
    ::=   { b14_D40InputTableEntry 3 }



-- ***********************************
-- *
-- *  B14_D40Output table declarations
-- *
-- ***********************************

b14_D40OutputTable   OBJECT-TYPE
    SYNTAX                SEQUENCE OF B14_D40OutputTableEntry
    ACCESS                not-accessible
    STATUS                mandatory
    DESCRIPTION
    "A list of snmp b14_D40Output (read-only) object values."
    ::=  { b14_D40 2 }

b14_D40OutputTableEntry  OBJECT-TYPE
    SYNTAX                B14_D40OutputTableEntry
    ACCESS                not-accessible
    STATUS                mandatory
    DESCRIPTION
    "An b14_D40Output table entry containing data for a specific b14_D40Output."
    INDEX  { b14_D40OutputIndex }  ::=   { b14_D40OutputTable 1 }

B14_D40OutputTableEntry ::= SEQUENCE {
        b14_D40OutputIndex       INTEGER,
        b14_D40OutputName        DisplayString,
        b14_D40OutputValue       DisplayString
    }

b14_D40OutputIndex   OBJECT-TYPE
    SYNTAX           INTEGER(0..2147483647)
    ACCESS           read-only
    STATUS           mandatory
    DESCRIPTION
    "The index in the b14_D40Output table for a particular snmp b14_D40Output
	 object.  Used to address table entries."
    ::=   { b14_D40OutputTableEntry 1 }


b14_D40OutputName    OBJECT-TYPE
    SYNTAX           DisplayString
    ACCESS           read-only
    STATUS           mandatory
    DESCRIPTION
    "Name of station object."
    ::=   { b14_D40OutputTableEntry 2 }

b14_D40OutputValue    OBJECT-TYPE
    SYNTAX           DisplayString
    ACCESS           read-only
    STATUS           mandatory
    DESCRIPTION
    "Current value of station object. Is read-only ."
    ::=   { b14_D40OutputTableEntry 3 }


-- ***********************************
-- *
-- *  B14_D44
-- *
-- ***********************************
    b14_D44    OBJECT IDENTIFIER ::= { exportTables 88 }

-- ***********************************
-- *
-- *  B14_D44Input table declarations
-- *
-- ***********************************

b14_D44InputTable   OBJECT-TYPE
    SYNTAX                SEQUENCE OF B14_D44InputTableEntry
    ACCESS                not-accessible
    STATUS                mandatory
    DESCRIPTION
    "A list of snmp b14_D44Input (read-only) object values."
    ::=  { b14_D44 1 }

b14_D44InputTableEntry  OBJECT-TYPE
    SYNTAX                B14_D44InputTableEntry
    ACCESS                not-accessible
    STATUS                mandatory
    DESCRIPTION
    "An b14_D44Input table entry containing data for a specific b14_D44Input."
    INDEX  { b14_D44InputIndex }  ::=   { b14_D44InputTable 1 }

B14_D44InputTableEntry ::= SEQUENCE {
        b14_D44InputIndex       INTEGER,
        b14_D44InputName        DisplayString,
        b14_D44InputValue       DisplayString
    }

b14_D44InputIndex   OBJECT-TYPE
    SYNTAX           INTEGER(0..2147483647)
    ACCESS           read-only
    STATUS           mandatory
    DESCRIPTION
    "The index in the b14_D44Input table for a particular snmp b14_D44Input
	 object.  Used to address table entries."
    ::=   { b14_D44InputTableEntry 1 }


b14_D44InputName    OBJECT-TYPE
    SYNTAX           DisplayString
    ACCESS           read-only
    STATUS           mandatory
    DESCRIPTION
    "Name of station object."
    ::=   { b14_D44InputTableEntry 2 }

b14_D44InputValue    OBJECT-TYPE
    SYNTAX           DisplayString
    ACCESS           read-write
    STATUS           mandatory
    DESCRIPTION
    "Current value of station object. Is read-write ."
    ::=   { b14_D44InputTableEntry 3 }



-- ***********************************
-- *
-- *  B14_D44Output table declarations
-- *
-- ***********************************

b14_D44OutputTable   OBJECT-TYPE
    SYNTAX                SEQUENCE OF B14_D44OutputTableEntry
    ACCESS                not-accessible
    STATUS                mandatory
    DESCRIPTION
    "A list of snmp b14_D44Output (read-only) object values."
    ::=  { b14_D44 2 }

b14_D44OutputTableEntry  OBJECT-TYPE
    SYNTAX                B14_D44OutputTableEntry
    ACCESS                not-accessible
    STATUS                mandatory
    DESCRIPTION
    "An b14_D44Output table entry containing data for a specific b14_D44Output."
    INDEX  { b14_D44OutputIndex }  ::=   { b14_D44OutputTable 1 }

B14_D44OutputTableEntry ::= SEQUENCE {
        b14_D44OutputIndex       INTEGER,
        b14_D44OutputName        DisplayString,
        b14_D44OutputValue       DisplayString
    }

b14_D44OutputIndex   OBJECT-TYPE
    SYNTAX           INTEGER(0..2147483647)
    ACCESS           read-only
    STATUS           mandatory
    DESCRIPTION
    "The index in the b14_D44Output table for a particular snmp b14_D44Output
	 object.  Used to address table entries."
    ::=   { b14_D44OutputTableEntry 1 }


b14_D44OutputName    OBJECT-TYPE
    SYNTAX           DisplayString
    ACCESS           read-only
    STATUS           mandatory
    DESCRIPTION
    "Name of station object."
    ::=   { b14_D44OutputTableEntry 2 }

b14_D44OutputValue    OBJECT-TYPE
    SYNTAX           DisplayString
    ACCESS           read-only
    STATUS           mandatory
    DESCRIPTION
    "Current value of station object. Is read-only ."
    ::=   { b14_D44OutputTableEntry 3 }


-- ***********************************
-- *
-- *  B14_D41
-- *
-- ***********************************
    b14_D41    OBJECT IDENTIFIER ::= { exportTables 89 }

-- ***********************************
-- *
-- *  B14_D41Input table declarations
-- *
-- ***********************************

b14_D41InputTable   OBJECT-TYPE
    SYNTAX                SEQUENCE OF B14_D41InputTableEntry
    ACCESS                not-accessible
    STATUS                mandatory
    DESCRIPTION
    "A list of snmp b14_D41Input (read-only) object values."
    ::=  { b14_D41 1 }

b14_D41InputTableEntry  OBJECT-TYPE
    SYNTAX                B14_D41InputTableEntry
    ACCESS                not-accessible
    STATUS                mandatory
    DESCRIPTION
    "An b14_D41Input table entry containing data for a specific b14_D41Input."
    INDEX  { b14_D41InputIndex }  ::=   { b14_D41InputTable 1 }

B14_D41InputTableEntry ::= SEQUENCE {
        b14_D41InputIndex       INTEGER,
        b14_D41InputName        DisplayString,
        b14_D41InputValue       DisplayString
    }

b14_D41InputIndex   OBJECT-TYPE
    SYNTAX           INTEGER(0..2147483647)
    ACCESS           read-only
    STATUS           mandatory
    DESCRIPTION
    "The index in the b14_D41Input table for a particular snmp b14_D41Input
	 object.  Used to address table entries."
    ::=   { b14_D41InputTableEntry 1 }


b14_D41InputName    OBJECT-TYPE
    SYNTAX           DisplayString
    ACCESS           read-only
    STATUS           mandatory
    DESCRIPTION
    "Name of station object."
    ::=   { b14_D41InputTableEntry 2 }

b14_D41InputValue    OBJECT-TYPE
    SYNTAX           DisplayString
    ACCESS           read-write
    STATUS           mandatory
    DESCRIPTION
    "Current value of station object. Is read-write ."
    ::=   { b14_D41InputTableEntry 3 }



-- ***********************************
-- *
-- *  B14_D41Output table declarations
-- *
-- ***********************************

b14_D41OutputTable   OBJECT-TYPE
    SYNTAX                SEQUENCE OF B14_D41OutputTableEntry
    ACCESS                not-accessible
    STATUS                mandatory
    DESCRIPTION
    "A list of snmp b14_D41Output (read-only) object values."
    ::=  { b14_D41 2 }

b14_D41OutputTableEntry  OBJECT-TYPE
    SYNTAX                B14_D41OutputTableEntry
    ACCESS                not-accessible
    STATUS                mandatory
    DESCRIPTION
    "An b14_D41Output table entry containing data for a specific b14_D41Output."
    INDEX  { b14_D41OutputIndex }  ::=   { b14_D41OutputTable 1 }

B14_D41OutputTableEntry ::= SEQUENCE {
        b14_D41OutputIndex       INTEGER,
        b14_D41OutputName        DisplayString,
        b14_D41OutputValue       DisplayString
    }

b14_D41OutputIndex   OBJECT-TYPE
    SYNTAX           INTEGER(0..2147483647)
    ACCESS           read-only
    STATUS           mandatory
    DESCRIPTION
    "The index in the b14_D41Output table for a particular snmp b14_D41Output
	 object.  Used to address table entries."
    ::=   { b14_D41OutputTableEntry 1 }


b14_D41OutputName    OBJECT-TYPE
    SYNTAX           DisplayString
    ACCESS           read-only
    STATUS           mandatory
    DESCRIPTION
    "Name of station object."
    ::=   { b14_D41OutputTableEntry 2 }

b14_D41OutputValue    OBJECT-TYPE
    SYNTAX           DisplayString
    ACCESS           read-only
    STATUS           mandatory
    DESCRIPTION
    "Current value of station object. Is read-only ."
    ::=   { b14_D41OutputTableEntry 3 }


-- ***********************************
-- *
-- *  B14_D42
-- *
-- ***********************************
    b14_D42    OBJECT IDENTIFIER ::= { exportTables 90 }

-- ***********************************
-- *
-- *  B14_D42Input table declarations
-- *
-- ***********************************

b14_D42InputTable   OBJECT-TYPE
    SYNTAX                SEQUENCE OF B14_D42InputTableEntry
    ACCESS                not-accessible
    STATUS                mandatory
    DESCRIPTION
    "A list of snmp b14_D42Input (read-only) object values."
    ::=  { b14_D42 1 }

b14_D42InputTableEntry  OBJECT-TYPE
    SYNTAX                B14_D42InputTableEntry
    ACCESS                not-accessible
    STATUS                mandatory
    DESCRIPTION
    "An b14_D42Input table entry containing data for a specific b14_D42Input."
    INDEX  { b14_D42InputIndex }  ::=   { b14_D42InputTable 1 }

B14_D42InputTableEntry ::= SEQUENCE {
        b14_D42InputIndex       INTEGER,
        b14_D42InputName        DisplayString,
        b14_D42InputValue       DisplayString
    }

b14_D42InputIndex   OBJECT-TYPE
    SYNTAX           INTEGER(0..2147483647)
    ACCESS           read-only
    STATUS           mandatory
    DESCRIPTION
    "The index in the b14_D42Input table for a particular snmp b14_D42Input
	 object.  Used to address table entries."
    ::=   { b14_D42InputTableEntry 1 }


b14_D42InputName    OBJECT-TYPE
    SYNTAX           DisplayString
    ACCESS           read-only
    STATUS           mandatory
    DESCRIPTION
    "Name of station object."
    ::=   { b14_D42InputTableEntry 2 }

b14_D42InputValue    OBJECT-TYPE
    SYNTAX           DisplayString
    ACCESS           read-write
    STATUS           mandatory
    DESCRIPTION
    "Current value of station object. Is read-write ."
    ::=   { b14_D42InputTableEntry 3 }



-- ***********************************
-- *
-- *  B14_D42Output table declarations
-- *
-- ***********************************

b14_D42OutputTable   OBJECT-TYPE
    SYNTAX                SEQUENCE OF B14_D42OutputTableEntry
    ACCESS                not-accessible
    STATUS                mandatory
    DESCRIPTION
    "A list of snmp b14_D42Output (read-only) object values."
    ::=  { b14_D42 2 }

b14_D42OutputTableEntry  OBJECT-TYPE
    SYNTAX                B14_D42OutputTableEntry
    ACCESS                not-accessible
    STATUS                mandatory
    DESCRIPTION
    "An b14_D42Output table entry containing data for a specific b14_D42Output."
    INDEX  { b14_D42OutputIndex }  ::=   { b14_D42OutputTable 1 }

B14_D42OutputTableEntry ::= SEQUENCE {
        b14_D42OutputIndex       INTEGER,
        b14_D42OutputName        DisplayString,
        b14_D42OutputValue       DisplayString
    }

b14_D42OutputIndex   OBJECT-TYPE
    SYNTAX           INTEGER(0..2147483647)
    ACCESS           read-only
    STATUS           mandatory
    DESCRIPTION
    "The index in the b14_D42Output table for a particular snmp b14_D42Output
	 object.  Used to address table entries."
    ::=   { b14_D42OutputTableEntry 1 }


b14_D42OutputName    OBJECT-TYPE
    SYNTAX           DisplayString
    ACCESS           read-only
    STATUS           mandatory
    DESCRIPTION
    "Name of station object."
    ::=   { b14_D42OutputTableEntry 2 }

b14_D42OutputValue    OBJECT-TYPE
    SYNTAX           DisplayString
    ACCESS           read-only
    STATUS           mandatory
    DESCRIPTION
    "Current value of station object. Is read-only ."
    ::=   { b14_D42OutputTableEntry 3 }


-- ***********************************
-- *
-- *  B14_D100
-- *
-- ***********************************
    b14_D100    OBJECT IDENTIFIER ::= { exportTables 91 }

-- ***********************************
-- *
-- *  B14_D100Input table declarations
-- *
-- ***********************************

b14_D100InputTable   OBJECT-TYPE
    SYNTAX                SEQUENCE OF B14_D100InputTableEntry
    ACCESS                not-accessible
    STATUS                mandatory
    DESCRIPTION
    "A list of snmp b14_D100Input (read-only) object values."
    ::=  { b14_D100 1 }

b14_D100InputTableEntry  OBJECT-TYPE
    SYNTAX                B14_D100InputTableEntry
    ACCESS                not-accessible
    STATUS                mandatory
    DESCRIPTION
    "An b14_D100Input table entry containing data for a specific b14_D100Input."
    INDEX  { b14_D100InputIndex }  ::=   { b14_D100InputTable 1 }

B14_D100InputTableEntry ::= SEQUENCE {
        b14_D100InputIndex       INTEGER,
        b14_D100InputName        DisplayString,
        b14_D100InputValue       DisplayString
    }

b14_D100InputIndex   OBJECT-TYPE
    SYNTAX           INTEGER(0..2147483647)
    ACCESS           read-only
    STATUS           mandatory
    DESCRIPTION
    "The index in the b14_D100Input table for a particular snmp b14_D100Input
	 object.  Used to address table entries."
    ::=   { b14_D100InputTableEntry 1 }


b14_D100InputName    OBJECT-TYPE
    SYNTAX           DisplayString
    ACCESS           read-only
    STATUS           mandatory
    DESCRIPTION
    "Name of station object."
    ::=   { b14_D100InputTableEntry 2 }

b14_D100InputValue    OBJECT-TYPE
    SYNTAX           DisplayString
    ACCESS           read-write
    STATUS           mandatory
    DESCRIPTION
    "Current value of station object. Is read-write ."
    ::=   { b14_D100InputTableEntry 3 }



-- ***********************************
-- *
-- *  B14_D100Output table declarations
-- *
-- ***********************************

b14_D100OutputTable   OBJECT-TYPE
    SYNTAX                SEQUENCE OF B14_D100OutputTableEntry
    ACCESS                not-accessible
    STATUS                mandatory
    DESCRIPTION
    "A list of snmp b14_D100Output (read-only) object values."
    ::=  { b14_D100 2 }

b14_D100OutputTableEntry  OBJECT-TYPE
    SYNTAX                B14_D100OutputTableEntry
    ACCESS                not-accessible
    STATUS                mandatory
    DESCRIPTION
    "An b14_D100Output table entry containing data for a specific b14_D100Output."
    INDEX  { b14_D100OutputIndex }  ::=   { b14_D100OutputTable 1 }

B14_D100OutputTableEntry ::= SEQUENCE {
        b14_D100OutputIndex       INTEGER,
        b14_D100OutputName        DisplayString,
        b14_D100OutputValue       DisplayString
    }

b14_D100OutputIndex   OBJECT-TYPE
    SYNTAX           INTEGER(0..2147483647)
    ACCESS           read-only
    STATUS           mandatory
    DESCRIPTION
    "The index in the b14_D100Output table for a particular snmp b14_D100Output
	 object.  Used to address table entries."
    ::=   { b14_D100OutputTableEntry 1 }


b14_D100OutputName    OBJECT-TYPE
    SYNTAX           DisplayString
    ACCESS           read-only
    STATUS           mandatory
    DESCRIPTION
    "Name of station object."
    ::=   { b14_D100OutputTableEntry 2 }

b14_D100OutputValue    OBJECT-TYPE
    SYNTAX           DisplayString
    ACCESS           read-only
    STATUS           mandatory
    DESCRIPTION
    "Current value of station object. Is read-only ."
    ::=   { b14_D100OutputTableEntry 3 }


-- ***********************************
-- *
-- *  B14_D101
-- *
-- ***********************************
    b14_D101    OBJECT IDENTIFIER ::= { exportTables 92 }

-- ***********************************
-- *
-- *  B14_D101Input table declarations
-- *
-- ***********************************

b14_D101InputTable   OBJECT-TYPE
    SYNTAX                SEQUENCE OF B14_D101InputTableEntry
    ACCESS                not-accessible
    STATUS                mandatory
    DESCRIPTION
    "A list of snmp b14_D101Input (read-only) object values."
    ::=  { b14_D101 1 }

b14_D101InputTableEntry  OBJECT-TYPE
    SYNTAX                B14_D101InputTableEntry
    ACCESS                not-accessible
    STATUS                mandatory
    DESCRIPTION
    "An b14_D101Input table entry containing data for a specific b14_D101Input."
    INDEX  { b14_D101InputIndex }  ::=   { b14_D101InputTable 1 }

B14_D101InputTableEntry ::= SEQUENCE {
        b14_D101InputIndex       INTEGER,
        b14_D101InputName        DisplayString,
        b14_D101InputValue       DisplayString
    }

b14_D101InputIndex   OBJECT-TYPE
    SYNTAX           INTEGER(0..2147483647)
    ACCESS           read-only
    STATUS           mandatory
    DESCRIPTION
    "The index in the b14_D101Input table for a particular snmp b14_D101Input
	 object.  Used to address table entries."
    ::=   { b14_D101InputTableEntry 1 }


b14_D101InputName    OBJECT-TYPE
    SYNTAX           DisplayString
    ACCESS           read-only
    STATUS           mandatory
    DESCRIPTION
    "Name of station object."
    ::=   { b14_D101InputTableEntry 2 }

b14_D101InputValue    OBJECT-TYPE
    SYNTAX           DisplayString
    ACCESS           read-write
    STATUS           mandatory
    DESCRIPTION
    "Current value of station object. Is read-write ."
    ::=   { b14_D101InputTableEntry 3 }



-- ***********************************
-- *
-- *  B14_D101Output table declarations
-- *
-- ***********************************

b14_D101OutputTable   OBJECT-TYPE
    SYNTAX                SEQUENCE OF B14_D101OutputTableEntry
    ACCESS                not-accessible
    STATUS                mandatory
    DESCRIPTION
    "A list of snmp b14_D101Output (read-only) object values."
    ::=  { b14_D101 2 }

b14_D101OutputTableEntry  OBJECT-TYPE
    SYNTAX                B14_D101OutputTableEntry
    ACCESS                not-accessible
    STATUS                mandatory
    DESCRIPTION
    "An b14_D101Output table entry containing data for a specific b14_D101Output."
    INDEX  { b14_D101OutputIndex }  ::=   { b14_D101OutputTable 1 }

B14_D101OutputTableEntry ::= SEQUENCE {
        b14_D101OutputIndex       INTEGER,
        b14_D101OutputName        DisplayString,
        b14_D101OutputValue       DisplayString
    }

b14_D101OutputIndex   OBJECT-TYPE
    SYNTAX           INTEGER(0..2147483647)
    ACCESS           read-only
    STATUS           mandatory
    DESCRIPTION
    "The index in the b14_D101Output table for a particular snmp b14_D101Output
	 object.  Used to address table entries."
    ::=   { b14_D101OutputTableEntry 1 }


b14_D101OutputName    OBJECT-TYPE
    SYNTAX           DisplayString
    ACCESS           read-only
    STATUS           mandatory
    DESCRIPTION
    "Name of station object."
    ::=   { b14_D101OutputTableEntry 2 }

b14_D101OutputValue    OBJECT-TYPE
    SYNTAX           DisplayString
    ACCESS           read-only
    STATUS           mandatory
    DESCRIPTION
    "Current value of station object. Is read-only ."
    ::=   { b14_D101OutputTableEntry 3 }


-- ***********************************
-- *
-- *  B14_D102
-- *
-- ***********************************
    b14_D102    OBJECT IDENTIFIER ::= { exportTables 93 }

-- ***********************************
-- *
-- *  B14_D102Input table declarations
-- *
-- ***********************************

b14_D102InputTable   OBJECT-TYPE
    SYNTAX                SEQUENCE OF B14_D102InputTableEntry
    ACCESS                not-accessible
    STATUS                mandatory
    DESCRIPTION
    "A list of snmp b14_D102Input (read-only) object values."
    ::=  { b14_D102 1 }

b14_D102InputTableEntry  OBJECT-TYPE
    SYNTAX                B14_D102InputTableEntry
    ACCESS                not-accessible
    STATUS                mandatory
    DESCRIPTION
    "An b14_D102Input table entry containing data for a specific b14_D102Input."
    INDEX  { b14_D102InputIndex }  ::=   { b14_D102InputTable 1 }

B14_D102InputTableEntry ::= SEQUENCE {
        b14_D102InputIndex       INTEGER,
        b14_D102InputName        DisplayString,
        b14_D102InputValue       DisplayString
    }

b14_D102InputIndex   OBJECT-TYPE
    SYNTAX           INTEGER(0..2147483647)
    ACCESS           read-only
    STATUS           mandatory
    DESCRIPTION
    "The index in the b14_D102Input table for a particular snmp b14_D102Input
	 object.  Used to address table entries."
    ::=   { b14_D102InputTableEntry 1 }


b14_D102InputName    OBJECT-TYPE
    SYNTAX           DisplayString
    ACCESS           read-only
    STATUS           mandatory
    DESCRIPTION
    "Name of station object."
    ::=   { b14_D102InputTableEntry 2 }

b14_D102InputValue    OBJECT-TYPE
    SYNTAX           DisplayString
    ACCESS           read-write
    STATUS           mandatory
    DESCRIPTION
    "Current value of station object. Is read-write ."
    ::=   { b14_D102InputTableEntry 3 }



-- ***********************************
-- *
-- *  B14_D102Output table declarations
-- *
-- ***********************************

b14_D102OutputTable   OBJECT-TYPE
    SYNTAX                SEQUENCE OF B14_D102OutputTableEntry
    ACCESS                not-accessible
    STATUS                mandatory
    DESCRIPTION
    "A list of snmp b14_D102Output (read-only) object values."
    ::=  { b14_D102 2 }

b14_D102OutputTableEntry  OBJECT-TYPE
    SYNTAX                B14_D102OutputTableEntry
    ACCESS                not-accessible
    STATUS                mandatory
    DESCRIPTION
    "An b14_D102Output table entry containing data for a specific b14_D102Output."
    INDEX  { b14_D102OutputIndex }  ::=   { b14_D102OutputTable 1 }

B14_D102OutputTableEntry ::= SEQUENCE {
        b14_D102OutputIndex       INTEGER,
        b14_D102OutputName        DisplayString,
        b14_D102OutputValue       DisplayString
    }

b14_D102OutputIndex   OBJECT-TYPE
    SYNTAX           INTEGER(0..2147483647)
    ACCESS           read-only
    STATUS           mandatory
    DESCRIPTION
    "The index in the b14_D102Output table for a particular snmp b14_D102Output
	 object.  Used to address table entries."
    ::=   { b14_D102OutputTableEntry 1 }


b14_D102OutputName    OBJECT-TYPE
    SYNTAX           DisplayString
    ACCESS           read-only
    STATUS           mandatory
    DESCRIPTION
    "Name of station object."
    ::=   { b14_D102OutputTableEntry 2 }

b14_D102OutputValue    OBJECT-TYPE
    SYNTAX           DisplayString
    ACCESS           read-only
    STATUS           mandatory
    DESCRIPTION
    "Current value of station object. Is read-only ."
    ::=   { b14_D102OutputTableEntry 3 }


-- ***********************************
-- *
-- *  B14_D133
-- *
-- ***********************************
    b14_D133    OBJECT IDENTIFIER ::= { exportTables 94 }

-- ***********************************
-- *
-- *  B14_D133Input table declarations
-- *
-- ***********************************

b14_D133InputTable   OBJECT-TYPE
    SYNTAX                SEQUENCE OF B14_D133InputTableEntry
    ACCESS                not-accessible
    STATUS                mandatory
    DESCRIPTION
    "A list of snmp b14_D133Input (read-only) object values."
    ::=  { b14_D133 1 }

b14_D133InputTableEntry  OBJECT-TYPE
    SYNTAX                B14_D133InputTableEntry
    ACCESS                not-accessible
    STATUS                mandatory
    DESCRIPTION
    "An b14_D133Input table entry containing data for a specific b14_D133Input."
    INDEX  { b14_D133InputIndex }  ::=   { b14_D133InputTable 1 }

B14_D133InputTableEntry ::= SEQUENCE {
        b14_D133InputIndex       INTEGER,
        b14_D133InputName        DisplayString,
        b14_D133InputValue       DisplayString
    }

b14_D133InputIndex   OBJECT-TYPE
    SYNTAX           INTEGER(0..2147483647)
    ACCESS           read-only
    STATUS           mandatory
    DESCRIPTION
    "The index in the b14_D133Input table for a particular snmp b14_D133Input
	 object.  Used to address table entries."
    ::=   { b14_D133InputTableEntry 1 }


b14_D133InputName    OBJECT-TYPE
    SYNTAX           DisplayString
    ACCESS           read-only
    STATUS           mandatory
    DESCRIPTION
    "Name of station object."
    ::=   { b14_D133InputTableEntry 2 }

b14_D133InputValue    OBJECT-TYPE
    SYNTAX           DisplayString
    ACCESS           read-write
    STATUS           mandatory
    DESCRIPTION
    "Current value of station object. Is read-write ."
    ::=   { b14_D133InputTableEntry 3 }



-- ***********************************
-- *
-- *  B14_D133Output table declarations
-- *
-- ***********************************

b14_D133OutputTable   OBJECT-TYPE
    SYNTAX                SEQUENCE OF B14_D133OutputTableEntry
    ACCESS                not-accessible
    STATUS                mandatory
    DESCRIPTION
    "A list of snmp b14_D133Output (read-only) object values."
    ::=  { b14_D133 2 }

b14_D133OutputTableEntry  OBJECT-TYPE
    SYNTAX                B14_D133OutputTableEntry
    ACCESS                not-accessible
    STATUS                mandatory
    DESCRIPTION
    "An b14_D133Output table entry containing data for a specific b14_D133Output."
    INDEX  { b14_D133OutputIndex }  ::=   { b14_D133OutputTable 1 }

B14_D133OutputTableEntry ::= SEQUENCE {
        b14_D133OutputIndex       INTEGER,
        b14_D133OutputName        DisplayString,
        b14_D133OutputValue       DisplayString
    }

b14_D133OutputIndex   OBJECT-TYPE
    SYNTAX           INTEGER(0..2147483647)
    ACCESS           read-only
    STATUS           mandatory
    DESCRIPTION
    "The index in the b14_D133Output table for a particular snmp b14_D133Output
	 object.  Used to address table entries."
    ::=   { b14_D133OutputTableEntry 1 }


b14_D133OutputName    OBJECT-TYPE
    SYNTAX           DisplayString
    ACCESS           read-only
    STATUS           mandatory
    DESCRIPTION
    "Name of station object."
    ::=   { b14_D133OutputTableEntry 2 }

b14_D133OutputValue    OBJECT-TYPE
    SYNTAX           DisplayString
    ACCESS           read-only
    STATUS           mandatory
    DESCRIPTION
    "Current value of station object. Is read-only ."
    ::=   { b14_D133OutputTableEntry 3 }


-- ***********************************
-- *
-- *  B14_D134
-- *
-- ***********************************
    b14_D134    OBJECT IDENTIFIER ::= { exportTables 95 }

-- ***********************************
-- *
-- *  B14_D134Input table declarations
-- *
-- ***********************************

b14_D134InputTable   OBJECT-TYPE
    SYNTAX                SEQUENCE OF B14_D134InputTableEntry
    ACCESS                not-accessible
    STATUS                mandatory
    DESCRIPTION
    "A list of snmp b14_D134Input (read-only) object values."
    ::=  { b14_D134 1 }

b14_D134InputTableEntry  OBJECT-TYPE
    SYNTAX                B14_D134InputTableEntry
    ACCESS                not-accessible
    STATUS                mandatory
    DESCRIPTION
    "An b14_D134Input table entry containing data for a specific b14_D134Input."
    INDEX  { b14_D134InputIndex }  ::=   { b14_D134InputTable 1 }

B14_D134InputTableEntry ::= SEQUENCE {
        b14_D134InputIndex       INTEGER,
        b14_D134InputName        DisplayString,
        b14_D134InputValue       DisplayString
    }

b14_D134InputIndex   OBJECT-TYPE
    SYNTAX           INTEGER(0..2147483647)
    ACCESS           read-only
    STATUS           mandatory
    DESCRIPTION
    "The index in the b14_D134Input table for a particular snmp b14_D134Input
	 object.  Used to address table entries."
    ::=   { b14_D134InputTableEntry 1 }


b14_D134InputName    OBJECT-TYPE
    SYNTAX           DisplayString
    ACCESS           read-only
    STATUS           mandatory
    DESCRIPTION
    "Name of station object."
    ::=   { b14_D134InputTableEntry 2 }

b14_D134InputValue    OBJECT-TYPE
    SYNTAX           DisplayString
    ACCESS           read-write
    STATUS           mandatory
    DESCRIPTION
    "Current value of station object. Is read-write ."
    ::=   { b14_D134InputTableEntry 3 }



-- ***********************************
-- *
-- *  B14_D134Output table declarations
-- *
-- ***********************************

b14_D134OutputTable   OBJECT-TYPE
    SYNTAX                SEQUENCE OF B14_D134OutputTableEntry
    ACCESS                not-accessible
    STATUS                mandatory
    DESCRIPTION
    "A list of snmp b14_D134Output (read-only) object values."
    ::=  { b14_D134 2 }

b14_D134OutputTableEntry  OBJECT-TYPE
    SYNTAX                B14_D134OutputTableEntry
    ACCESS                not-accessible
    STATUS                mandatory
    DESCRIPTION
    "An b14_D134Output table entry containing data for a specific b14_D134Output."
    INDEX  { b14_D134OutputIndex }  ::=   { b14_D134OutputTable 1 }

B14_D134OutputTableEntry ::= SEQUENCE {
        b14_D134OutputIndex       INTEGER,
        b14_D134OutputName        DisplayString,
        b14_D134OutputValue       DisplayString
    }

b14_D134OutputIndex   OBJECT-TYPE
    SYNTAX           INTEGER(0..2147483647)
    ACCESS           read-only
    STATUS           mandatory
    DESCRIPTION
    "The index in the b14_D134Output table for a particular snmp b14_D134Output
	 object.  Used to address table entries."
    ::=   { b14_D134OutputTableEntry 1 }


b14_D134OutputName    OBJECT-TYPE
    SYNTAX           DisplayString
    ACCESS           read-only
    STATUS           mandatory
    DESCRIPTION
    "Name of station object."
    ::=   { b14_D134OutputTableEntry 2 }

b14_D134OutputValue    OBJECT-TYPE
    SYNTAX           DisplayString
    ACCESS           read-only
    STATUS           mandatory
    DESCRIPTION
    "Current value of station object. Is read-only ."
    ::=   { b14_D134OutputTableEntry 3 }


-- ***********************************
-- *
-- *  B14_D131
-- *
-- ***********************************
    b14_D131    OBJECT IDENTIFIER ::= { exportTables 96 }

-- ***********************************
-- *
-- *  B14_D131Input table declarations
-- *
-- ***********************************

b14_D131InputTable   OBJECT-TYPE
    SYNTAX                SEQUENCE OF B14_D131InputTableEntry
    ACCESS                not-accessible
    STATUS                mandatory
    DESCRIPTION
    "A list of snmp b14_D131Input (read-only) object values."
    ::=  { b14_D131 1 }

b14_D131InputTableEntry  OBJECT-TYPE
    SYNTAX                B14_D131InputTableEntry
    ACCESS                not-accessible
    STATUS                mandatory
    DESCRIPTION
    "An b14_D131Input table entry containing data for a specific b14_D131Input."
    INDEX  { b14_D131InputIndex }  ::=   { b14_D131InputTable 1 }

B14_D131InputTableEntry ::= SEQUENCE {
        b14_D131InputIndex       INTEGER,
        b14_D131InputName        DisplayString,
        b14_D131InputValue       DisplayString
    }

b14_D131InputIndex   OBJECT-TYPE
    SYNTAX           INTEGER(0..2147483647)
    ACCESS           read-only
    STATUS           mandatory
    DESCRIPTION
    "The index in the b14_D131Input table for a particular snmp b14_D131Input
	 object.  Used to address table entries."
    ::=   { b14_D131InputTableEntry 1 }


b14_D131InputName    OBJECT-TYPE
    SYNTAX           DisplayString
    ACCESS           read-only
    STATUS           mandatory
    DESCRIPTION
    "Name of station object."
    ::=   { b14_D131InputTableEntry 2 }

b14_D131InputValue    OBJECT-TYPE
    SYNTAX           DisplayString
    ACCESS           read-write
    STATUS           mandatory
    DESCRIPTION
    "Current value of station object. Is read-write ."
    ::=   { b14_D131InputTableEntry 3 }



-- ***********************************
-- *
-- *  B14_D131Output table declarations
-- *
-- ***********************************

b14_D131OutputTable   OBJECT-TYPE
    SYNTAX                SEQUENCE OF B14_D131OutputTableEntry
    ACCESS                not-accessible
    STATUS                mandatory
    DESCRIPTION
    "A list of snmp b14_D131Output (read-only) object values."
    ::=  { b14_D131 2 }

b14_D131OutputTableEntry  OBJECT-TYPE
    SYNTAX                B14_D131OutputTableEntry
    ACCESS                not-accessible
    STATUS                mandatory
    DESCRIPTION
    "An b14_D131Output table entry containing data for a specific b14_D131Output."
    INDEX  { b14_D131OutputIndex }  ::=   { b14_D131OutputTable 1 }

B14_D131OutputTableEntry ::= SEQUENCE {
        b14_D131OutputIndex       INTEGER,
        b14_D131OutputName        DisplayString,
        b14_D131OutputValue       DisplayString
    }

b14_D131OutputIndex   OBJECT-TYPE
    SYNTAX           INTEGER(0..2147483647)
    ACCESS           read-only
    STATUS           mandatory
    DESCRIPTION
    "The index in the b14_D131Output table for a particular snmp b14_D131Output
	 object.  Used to address table entries."
    ::=   { b14_D131OutputTableEntry 1 }


b14_D131OutputName    OBJECT-TYPE
    SYNTAX           DisplayString
    ACCESS           read-only
    STATUS           mandatory
    DESCRIPTION
    "Name of station object."
    ::=   { b14_D131OutputTableEntry 2 }

b14_D131OutputValue    OBJECT-TYPE
    SYNTAX           DisplayString
    ACCESS           read-only
    STATUS           mandatory
    DESCRIPTION
    "Current value of station object. Is read-only ."
    ::=   { b14_D131OutputTableEntry 3 }


-- ***********************************
-- *
-- *  B14_D57
-- *
-- ***********************************
    b14_D57    OBJECT IDENTIFIER ::= { exportTables 97 }

-- ***********************************
-- *
-- *  B14_D57Input table declarations
-- *
-- ***********************************

b14_D57InputTable   OBJECT-TYPE
    SYNTAX                SEQUENCE OF B14_D57InputTableEntry
    ACCESS                not-accessible
    STATUS                mandatory
    DESCRIPTION
    "A list of snmp b14_D57Input (read-only) object values."
    ::=  { b14_D57 1 }

b14_D57InputTableEntry  OBJECT-TYPE
    SYNTAX                B14_D57InputTableEntry
    ACCESS                not-accessible
    STATUS                mandatory
    DESCRIPTION
    "An b14_D57Input table entry containing data for a specific b14_D57Input."
    INDEX  { b14_D57InputIndex }  ::=   { b14_D57InputTable 1 }

B14_D57InputTableEntry ::= SEQUENCE {
        b14_D57InputIndex       INTEGER,
        b14_D57InputName        DisplayString,
        b14_D57InputValue       DisplayString
    }

b14_D57InputIndex   OBJECT-TYPE
    SYNTAX           INTEGER(0..2147483647)
    ACCESS           read-only
    STATUS           mandatory
    DESCRIPTION
    "The index in the b14_D57Input table for a particular snmp b14_D57Input
	 object.  Used to address table entries."
    ::=   { b14_D57InputTableEntry 1 }


b14_D57InputName    OBJECT-TYPE
    SYNTAX           DisplayString
    ACCESS           read-only
    STATUS           mandatory
    DESCRIPTION
    "Name of station object."
    ::=   { b14_D57InputTableEntry 2 }

b14_D57InputValue    OBJECT-TYPE
    SYNTAX           DisplayString
    ACCESS           read-write
    STATUS           mandatory
    DESCRIPTION
    "Current value of station object. Is read-write ."
    ::=   { b14_D57InputTableEntry 3 }



-- ***********************************
-- *
-- *  B14_D57Output table declarations
-- *
-- ***********************************

b14_D57OutputTable   OBJECT-TYPE
    SYNTAX                SEQUENCE OF B14_D57OutputTableEntry
    ACCESS                not-accessible
    STATUS                mandatory
    DESCRIPTION
    "A list of snmp b14_D57Output (read-only) object values."
    ::=  { b14_D57 2 }

b14_D57OutputTableEntry  OBJECT-TYPE
    SYNTAX                B14_D57OutputTableEntry
    ACCESS                not-accessible
    STATUS                mandatory
    DESCRIPTION
    "An b14_D57Output table entry containing data for a specific b14_D57Output."
    INDEX  { b14_D57OutputIndex }  ::=   { b14_D57OutputTable 1 }

B14_D57OutputTableEntry ::= SEQUENCE {
        b14_D57OutputIndex       INTEGER,
        b14_D57OutputName        DisplayString,
        b14_D57OutputValue       DisplayString
    }

b14_D57OutputIndex   OBJECT-TYPE
    SYNTAX           INTEGER(0..2147483647)
    ACCESS           read-only
    STATUS           mandatory
    DESCRIPTION
    "The index in the b14_D57Output table for a particular snmp b14_D57Output
	 object.  Used to address table entries."
    ::=   { b14_D57OutputTableEntry 1 }


b14_D57OutputName    OBJECT-TYPE
    SYNTAX           DisplayString
    ACCESS           read-only
    STATUS           mandatory
    DESCRIPTION
    "Name of station object."
    ::=   { b14_D57OutputTableEntry 2 }

b14_D57OutputValue    OBJECT-TYPE
    SYNTAX           DisplayString
    ACCESS           read-only
    STATUS           mandatory
    DESCRIPTION
    "Current value of station object. Is read-only ."
    ::=   { b14_D57OutputTableEntry 3 }


-- ***********************************
-- *
-- *  B14_D56
-- *
-- ***********************************
    b14_D56    OBJECT IDENTIFIER ::= { exportTables 98 }

-- ***********************************
-- *
-- *  B14_D56Input table declarations
-- *
-- ***********************************

b14_D56InputTable   OBJECT-TYPE
    SYNTAX                SEQUENCE OF B14_D56InputTableEntry
    ACCESS                not-accessible
    STATUS                mandatory
    DESCRIPTION
    "A list of snmp b14_D56Input (read-only) object values."
    ::=  { b14_D56 1 }

b14_D56InputTableEntry  OBJECT-TYPE
    SYNTAX                B14_D56InputTableEntry
    ACCESS                not-accessible
    STATUS                mandatory
    DESCRIPTION
    "An b14_D56Input table entry containing data for a specific b14_D56Input."
    INDEX  { b14_D56InputIndex }  ::=   { b14_D56InputTable 1 }

B14_D56InputTableEntry ::= SEQUENCE {
        b14_D56InputIndex       INTEGER,
        b14_D56InputName        DisplayString,
        b14_D56InputValue       DisplayString
    }

b14_D56InputIndex   OBJECT-TYPE
    SYNTAX           INTEGER(0..2147483647)
    ACCESS           read-only
    STATUS           mandatory
    DESCRIPTION
    "The index in the b14_D56Input table for a particular snmp b14_D56Input
	 object.  Used to address table entries."
    ::=   { b14_D56InputTableEntry 1 }


b14_D56InputName    OBJECT-TYPE
    SYNTAX           DisplayString
    ACCESS           read-only
    STATUS           mandatory
    DESCRIPTION
    "Name of station object."
    ::=   { b14_D56InputTableEntry 2 }

b14_D56InputValue    OBJECT-TYPE
    SYNTAX           DisplayString
    ACCESS           read-write
    STATUS           mandatory
    DESCRIPTION
    "Current value of station object. Is read-write ."
    ::=   { b14_D56InputTableEntry 3 }



-- ***********************************
-- *
-- *  B14_D56Output table declarations
-- *
-- ***********************************

b14_D56OutputTable   OBJECT-TYPE
    SYNTAX                SEQUENCE OF B14_D56OutputTableEntry
    ACCESS                not-accessible
    STATUS                mandatory
    DESCRIPTION
    "A list of snmp b14_D56Output (read-only) object values."
    ::=  { b14_D56 2 }

b14_D56OutputTableEntry  OBJECT-TYPE
    SYNTAX                B14_D56OutputTableEntry
    ACCESS                not-accessible
    STATUS                mandatory
    DESCRIPTION
    "An b14_D56Output table entry containing data for a specific b14_D56Output."
    INDEX  { b14_D56OutputIndex }  ::=   { b14_D56OutputTable 1 }

B14_D56OutputTableEntry ::= SEQUENCE {
        b14_D56OutputIndex       INTEGER,
        b14_D56OutputName        DisplayString,
        b14_D56OutputValue       DisplayString
    }

b14_D56OutputIndex   OBJECT-TYPE
    SYNTAX           INTEGER(0..2147483647)
    ACCESS           read-only
    STATUS           mandatory
    DESCRIPTION
    "The index in the b14_D56Output table for a particular snmp b14_D56Output
	 object.  Used to address table entries."
    ::=   { b14_D56OutputTableEntry 1 }


b14_D56OutputName    OBJECT-TYPE
    SYNTAX           DisplayString
    ACCESS           read-only
    STATUS           mandatory
    DESCRIPTION
    "Name of station object."
    ::=   { b14_D56OutputTableEntry 2 }

b14_D56OutputValue    OBJECT-TYPE
    SYNTAX           DisplayString
    ACCESS           read-only
    STATUS           mandatory
    DESCRIPTION
    "Current value of station object. Is read-only ."
    ::=   { b14_D56OutputTableEntry 3 }


-- ***********************************
-- *
-- *  B14_D105
-- *
-- ***********************************
    b14_D105    OBJECT IDENTIFIER ::= { exportTables 99 }

-- ***********************************
-- *
-- *  B14_D105Input table declarations
-- *
-- ***********************************

b14_D105InputTable   OBJECT-TYPE
    SYNTAX                SEQUENCE OF B14_D105InputTableEntry
    ACCESS                not-accessible
    STATUS                mandatory
    DESCRIPTION
    "A list of snmp b14_D105Input (read-only) object values."
    ::=  { b14_D105 1 }

b14_D105InputTableEntry  OBJECT-TYPE
    SYNTAX                B14_D105InputTableEntry
    ACCESS                not-accessible
    STATUS                mandatory
    DESCRIPTION
    "An b14_D105Input table entry containing data for a specific b14_D105Input."
    INDEX  { b14_D105InputIndex }  ::=   { b14_D105InputTable 1 }

B14_D105InputTableEntry ::= SEQUENCE {
        b14_D105InputIndex       INTEGER,
        b14_D105InputName        DisplayString,
        b14_D105InputValue       DisplayString
    }

b14_D105InputIndex   OBJECT-TYPE
    SYNTAX           INTEGER(0..2147483647)
    ACCESS           read-only
    STATUS           mandatory
    DESCRIPTION
    "The index in the b14_D105Input table for a particular snmp b14_D105Input
	 object.  Used to address table entries."
    ::=   { b14_D105InputTableEntry 1 }


b14_D105InputName    OBJECT-TYPE
    SYNTAX           DisplayString
    ACCESS           read-only
    STATUS           mandatory
    DESCRIPTION
    "Name of station object."
    ::=   { b14_D105InputTableEntry 2 }

b14_D105InputValue    OBJECT-TYPE
    SYNTAX           DisplayString
    ACCESS           read-write
    STATUS           mandatory
    DESCRIPTION
    "Current value of station object. Is read-write ."
    ::=   { b14_D105InputTableEntry 3 }



-- ***********************************
-- *
-- *  B14_D105Output table declarations
-- *
-- ***********************************

b14_D105OutputTable   OBJECT-TYPE
    SYNTAX                SEQUENCE OF B14_D105OutputTableEntry
    ACCESS                not-accessible
    STATUS                mandatory
    DESCRIPTION
    "A list of snmp b14_D105Output (read-only) object values."
    ::=  { b14_D105 2 }

b14_D105OutputTableEntry  OBJECT-TYPE
    SYNTAX                B14_D105OutputTableEntry
    ACCESS                not-accessible
    STATUS                mandatory
    DESCRIPTION
    "An b14_D105Output table entry containing data for a specific b14_D105Output."
    INDEX  { b14_D105OutputIndex }  ::=   { b14_D105OutputTable 1 }

B14_D105OutputTableEntry ::= SEQUENCE {
        b14_D105OutputIndex       INTEGER,
        b14_D105OutputName        DisplayString,
        b14_D105OutputValue       DisplayString
    }

b14_D105OutputIndex   OBJECT-TYPE
    SYNTAX           INTEGER(0..2147483647)
    ACCESS           read-only
    STATUS           mandatory
    DESCRIPTION
    "The index in the b14_D105Output table for a particular snmp b14_D105Output
	 object.  Used to address table entries."
    ::=   { b14_D105OutputTableEntry 1 }


b14_D105OutputName    OBJECT-TYPE
    SYNTAX           DisplayString
    ACCESS           read-only
    STATUS           mandatory
    DESCRIPTION
    "Name of station object."
    ::=   { b14_D105OutputTableEntry 2 }

b14_D105OutputValue    OBJECT-TYPE
    SYNTAX           DisplayString
    ACCESS           read-only
    STATUS           mandatory
    DESCRIPTION
    "Current value of station object. Is read-only ."
    ::=   { b14_D105OutputTableEntry 3 }


-- ***********************************
-- *
-- *  B14_D65
-- *
-- ***********************************
    b14_D65    OBJECT IDENTIFIER ::= { exportTables 100 }

-- ***********************************
-- *
-- *  B14_D65Input table declarations
-- *
-- ***********************************

b14_D65InputTable   OBJECT-TYPE
    SYNTAX                SEQUENCE OF B14_D65InputTableEntry
    ACCESS                not-accessible
    STATUS                mandatory
    DESCRIPTION
    "A list of snmp b14_D65Input (read-only) object values."
    ::=  { b14_D65 1 }

b14_D65InputTableEntry  OBJECT-TYPE
    SYNTAX                B14_D65InputTableEntry
    ACCESS                not-accessible
    STATUS                mandatory
    DESCRIPTION
    "An b14_D65Input table entry containing data for a specific b14_D65Input."
    INDEX  { b14_D65InputIndex }  ::=   { b14_D65InputTable 1 }

B14_D65InputTableEntry ::= SEQUENCE {
        b14_D65InputIndex       INTEGER,
        b14_D65InputName        DisplayString,
        b14_D65InputValue       DisplayString
    }

b14_D65InputIndex   OBJECT-TYPE
    SYNTAX           INTEGER(0..2147483647)
    ACCESS           read-only
    STATUS           mandatory
    DESCRIPTION
    "The index in the b14_D65Input table for a particular snmp b14_D65Input
	 object.  Used to address table entries."
    ::=   { b14_D65InputTableEntry 1 }


b14_D65InputName    OBJECT-TYPE
    SYNTAX           DisplayString
    ACCESS           read-only
    STATUS           mandatory
    DESCRIPTION
    "Name of station object."
    ::=   { b14_D65InputTableEntry 2 }

b14_D65InputValue    OBJECT-TYPE
    SYNTAX           DisplayString
    ACCESS           read-write
    STATUS           mandatory
    DESCRIPTION
    "Current value of station object. Is read-write ."
    ::=   { b14_D65InputTableEntry 3 }



-- ***********************************
-- *
-- *  B14_D65Output table declarations
-- *
-- ***********************************

b14_D65OutputTable   OBJECT-TYPE
    SYNTAX                SEQUENCE OF B14_D65OutputTableEntry
    ACCESS                not-accessible
    STATUS                mandatory
    DESCRIPTION
    "A list of snmp b14_D65Output (read-only) object values."
    ::=  { b14_D65 2 }

b14_D65OutputTableEntry  OBJECT-TYPE
    SYNTAX                B14_D65OutputTableEntry
    ACCESS                not-accessible
    STATUS                mandatory
    DESCRIPTION
    "An b14_D65Output table entry containing data for a specific b14_D65Output."
    INDEX  { b14_D65OutputIndex }  ::=   { b14_D65OutputTable 1 }

B14_D65OutputTableEntry ::= SEQUENCE {
        b14_D65OutputIndex       INTEGER,
        b14_D65OutputName        DisplayString,
        b14_D65OutputValue       DisplayString
    }

b14_D65OutputIndex   OBJECT-TYPE
    SYNTAX           INTEGER(0..2147483647)
    ACCESS           read-only
    STATUS           mandatory
    DESCRIPTION
    "The index in the b14_D65Output table for a particular snmp b14_D65Output
	 object.  Used to address table entries."
    ::=   { b14_D65OutputTableEntry 1 }


b14_D65OutputName    OBJECT-TYPE
    SYNTAX           DisplayString
    ACCESS           read-only
    STATUS           mandatory
    DESCRIPTION
    "Name of station object."
    ::=   { b14_D65OutputTableEntry 2 }

b14_D65OutputValue    OBJECT-TYPE
    SYNTAX           DisplayString
    ACCESS           read-only
    STATUS           mandatory
    DESCRIPTION
    "Current value of station object. Is read-only ."
    ::=   { b14_D65OutputTableEntry 3 }


-- ***********************************
-- *
-- *  B14_D20
-- *
-- ***********************************
    b14_D20    OBJECT IDENTIFIER ::= { exportTables 101 }

-- ***********************************
-- *
-- *  B14_D20Input table declarations
-- *
-- ***********************************

b14_D20InputTable   OBJECT-TYPE
    SYNTAX                SEQUENCE OF B14_D20InputTableEntry
    ACCESS                not-accessible
    STATUS                mandatory
    DESCRIPTION
    "A list of snmp b14_D20Input (read-only) object values."
    ::=  { b14_D20 1 }

b14_D20InputTableEntry  OBJECT-TYPE
    SYNTAX                B14_D20InputTableEntry
    ACCESS                not-accessible
    STATUS                mandatory
    DESCRIPTION
    "An b14_D20Input table entry containing data for a specific b14_D20Input."
    INDEX  { b14_D20InputIndex }  ::=   { b14_D20InputTable 1 }

B14_D20InputTableEntry ::= SEQUENCE {
        b14_D20InputIndex       INTEGER,
        b14_D20InputName        DisplayString,
        b14_D20InputValue       DisplayString
    }

b14_D20InputIndex   OBJECT-TYPE
    SYNTAX           INTEGER(0..2147483647)
    ACCESS           read-only
    STATUS           mandatory
    DESCRIPTION
    "The index in the b14_D20Input table for a particular snmp b14_D20Input
	 object.  Used to address table entries."
    ::=   { b14_D20InputTableEntry 1 }


b14_D20InputName    OBJECT-TYPE
    SYNTAX           DisplayString
    ACCESS           read-only
    STATUS           mandatory
    DESCRIPTION
    "Name of station object."
    ::=   { b14_D20InputTableEntry 2 }

b14_D20InputValue    OBJECT-TYPE
    SYNTAX           DisplayString
    ACCESS           read-write
    STATUS           mandatory
    DESCRIPTION
    "Current value of station object. Is read-write ."
    ::=   { b14_D20InputTableEntry 3 }



-- ***********************************
-- *
-- *  B14_D20Output table declarations
-- *
-- ***********************************

b14_D20OutputTable   OBJECT-TYPE
    SYNTAX                SEQUENCE OF B14_D20OutputTableEntry
    ACCESS                not-accessible
    STATUS                mandatory
    DESCRIPTION
    "A list of snmp b14_D20Output (read-only) object values."
    ::=  { b14_D20 2 }

b14_D20OutputTableEntry  OBJECT-TYPE
    SYNTAX                B14_D20OutputTableEntry
    ACCESS                not-accessible
    STATUS                mandatory
    DESCRIPTION
    "An b14_D20Output table entry containing data for a specific b14_D20Output."
    INDEX  { b14_D20OutputIndex }  ::=   { b14_D20OutputTable 1 }

B14_D20OutputTableEntry ::= SEQUENCE {
        b14_D20OutputIndex       INTEGER,
        b14_D20OutputName        DisplayString,
        b14_D20OutputValue       DisplayString
    }

b14_D20OutputIndex   OBJECT-TYPE
    SYNTAX           INTEGER(0..2147483647)
    ACCESS           read-only
    STATUS           mandatory
    DESCRIPTION
    "The index in the b14_D20Output table for a particular snmp b14_D20Output
	 object.  Used to address table entries."
    ::=   { b14_D20OutputTableEntry 1 }


b14_D20OutputName    OBJECT-TYPE
    SYNTAX           DisplayString
    ACCESS           read-only
    STATUS           mandatory
    DESCRIPTION
    "Name of station object."
    ::=   { b14_D20OutputTableEntry 2 }

b14_D20OutputValue    OBJECT-TYPE
    SYNTAX           DisplayString
    ACCESS           read-only
    STATUS           mandatory
    DESCRIPTION
    "Current value of station object. Is read-only ."
    ::=   { b14_D20OutputTableEntry 3 }


-- ***********************************
-- *
-- *  B14_D34
-- *
-- ***********************************
    b14_D34    OBJECT IDENTIFIER ::= { exportTables 102 }

-- ***********************************
-- *
-- *  B14_D34Input table declarations
-- *
-- ***********************************

b14_D34InputTable   OBJECT-TYPE
    SYNTAX                SEQUENCE OF B14_D34InputTableEntry
    ACCESS                not-accessible
    STATUS                mandatory
    DESCRIPTION
    "A list of snmp b14_D34Input (read-only) object values."
    ::=  { b14_D34 1 }

b14_D34InputTableEntry  OBJECT-TYPE
    SYNTAX                B14_D34InputTableEntry
    ACCESS                not-accessible
    STATUS                mandatory
    DESCRIPTION
    "An b14_D34Input table entry containing data for a specific b14_D34Input."
    INDEX  { b14_D34InputIndex }  ::=   { b14_D34InputTable 1 }

B14_D34InputTableEntry ::= SEQUENCE {
        b14_D34InputIndex       INTEGER,
        b14_D34InputName        DisplayString,
        b14_D34InputValue       DisplayString
    }

b14_D34InputIndex   OBJECT-TYPE
    SYNTAX           INTEGER(0..2147483647)
    ACCESS           read-only
    STATUS           mandatory
    DESCRIPTION
    "The index in the b14_D34Input table for a particular snmp b14_D34Input
	 object.  Used to address table entries."
    ::=   { b14_D34InputTableEntry 1 }


b14_D34InputName    OBJECT-TYPE
    SYNTAX           DisplayString
    ACCESS           read-only
    STATUS           mandatory
    DESCRIPTION
    "Name of station object."
    ::=   { b14_D34InputTableEntry 2 }

b14_D34InputValue    OBJECT-TYPE
    SYNTAX           DisplayString
    ACCESS           read-write
    STATUS           mandatory
    DESCRIPTION
    "Current value of station object. Is read-write ."
    ::=   { b14_D34InputTableEntry 3 }



-- ***********************************
-- *
-- *  B14_D34Output table declarations
-- *
-- ***********************************

b14_D34OutputTable   OBJECT-TYPE
    SYNTAX                SEQUENCE OF B14_D34OutputTableEntry
    ACCESS                not-accessible
    STATUS                mandatory
    DESCRIPTION
    "A list of snmp b14_D34Output (read-only) object values."
    ::=  { b14_D34 2 }

b14_D34OutputTableEntry  OBJECT-TYPE
    SYNTAX                B14_D34OutputTableEntry
    ACCESS                not-accessible
    STATUS                mandatory
    DESCRIPTION
    "An b14_D34Output table entry containing data for a specific b14_D34Output."
    INDEX  { b14_D34OutputIndex }  ::=   { b14_D34OutputTable 1 }

B14_D34OutputTableEntry ::= SEQUENCE {
        b14_D34OutputIndex       INTEGER,
        b14_D34OutputName        DisplayString,
        b14_D34OutputValue       DisplayString
    }

b14_D34OutputIndex   OBJECT-TYPE
    SYNTAX           INTEGER(0..2147483647)
    ACCESS           read-only
    STATUS           mandatory
    DESCRIPTION
    "The index in the b14_D34Output table for a particular snmp b14_D34Output
	 object.  Used to address table entries."
    ::=   { b14_D34OutputTableEntry 1 }


b14_D34OutputName    OBJECT-TYPE
    SYNTAX           DisplayString
    ACCESS           read-only
    STATUS           mandatory
    DESCRIPTION
    "Name of station object."
    ::=   { b14_D34OutputTableEntry 2 }

b14_D34OutputValue    OBJECT-TYPE
    SYNTAX           DisplayString
    ACCESS           read-only
    STATUS           mandatory
    DESCRIPTION
    "Current value of station object. Is read-only ."
    ::=   { b14_D34OutputTableEntry 3 }


-- ***********************************
-- *
-- *  B14_D33
-- *
-- ***********************************
    b14_D33    OBJECT IDENTIFIER ::= { exportTables 103 }

-- ***********************************
-- *
-- *  B14_D33Input table declarations
-- *
-- ***********************************

b14_D33InputTable   OBJECT-TYPE
    SYNTAX                SEQUENCE OF B14_D33InputTableEntry
    ACCESS                not-accessible
    STATUS                mandatory
    DESCRIPTION
    "A list of snmp b14_D33Input (read-only) object values."
    ::=  { b14_D33 1 }

b14_D33InputTableEntry  OBJECT-TYPE
    SYNTAX                B14_D33InputTableEntry
    ACCESS                not-accessible
    STATUS                mandatory
    DESCRIPTION
    "An b14_D33Input table entry containing data for a specific b14_D33Input."
    INDEX  { b14_D33InputIndex }  ::=   { b14_D33InputTable 1 }

B14_D33InputTableEntry ::= SEQUENCE {
        b14_D33InputIndex       INTEGER,
        b14_D33InputName        DisplayString,
        b14_D33InputValue       DisplayString
    }

b14_D33InputIndex   OBJECT-TYPE
    SYNTAX           INTEGER(0..2147483647)
    ACCESS           read-only
    STATUS           mandatory
    DESCRIPTION
    "The index in the b14_D33Input table for a particular snmp b14_D33Input
	 object.  Used to address table entries."
    ::=   { b14_D33InputTableEntry 1 }


b14_D33InputName    OBJECT-TYPE
    SYNTAX           DisplayString
    ACCESS           read-only
    STATUS           mandatory
    DESCRIPTION
    "Name of station object."
    ::=   { b14_D33InputTableEntry 2 }

b14_D33InputValue    OBJECT-TYPE
    SYNTAX           DisplayString
    ACCESS           read-write
    STATUS           mandatory
    DESCRIPTION
    "Current value of station object. Is read-write ."
    ::=   { b14_D33InputTableEntry 3 }



-- ***********************************
-- *
-- *  B14_D33Output table declarations
-- *
-- ***********************************

b14_D33OutputTable   OBJECT-TYPE
    SYNTAX                SEQUENCE OF B14_D33OutputTableEntry
    ACCESS                not-accessible
    STATUS                mandatory
    DESCRIPTION
    "A list of snmp b14_D33Output (read-only) object values."
    ::=  { b14_D33 2 }

b14_D33OutputTableEntry  OBJECT-TYPE
    SYNTAX                B14_D33OutputTableEntry
    ACCESS                not-accessible
    STATUS                mandatory
    DESCRIPTION
    "An b14_D33Output table entry containing data for a specific b14_D33Output."
    INDEX  { b14_D33OutputIndex }  ::=   { b14_D33OutputTable 1 }

B14_D33OutputTableEntry ::= SEQUENCE {
        b14_D33OutputIndex       INTEGER,
        b14_D33OutputName        DisplayString,
        b14_D33OutputValue       DisplayString
    }

b14_D33OutputIndex   OBJECT-TYPE
    SYNTAX           INTEGER(0..2147483647)
    ACCESS           read-only
    STATUS           mandatory
    DESCRIPTION
    "The index in the b14_D33Output table for a particular snmp b14_D33Output
	 object.  Used to address table entries."
    ::=   { b14_D33OutputTableEntry 1 }


b14_D33OutputName    OBJECT-TYPE
    SYNTAX           DisplayString
    ACCESS           read-only
    STATUS           mandatory
    DESCRIPTION
    "Name of station object."
    ::=   { b14_D33OutputTableEntry 2 }

b14_D33OutputValue    OBJECT-TYPE
    SYNTAX           DisplayString
    ACCESS           read-only
    STATUS           mandatory
    DESCRIPTION
    "Current value of station object. Is read-only ."
    ::=   { b14_D33OutputTableEntry 3 }


-- ***********************************
-- *
-- *  B14_D35
-- *
-- ***********************************
    b14_D35    OBJECT IDENTIFIER ::= { exportTables 104 }

-- ***********************************
-- *
-- *  B14_D35Input table declarations
-- *
-- ***********************************

b14_D35InputTable   OBJECT-TYPE
    SYNTAX                SEQUENCE OF B14_D35InputTableEntry
    ACCESS                not-accessible
    STATUS                mandatory
    DESCRIPTION
    "A list of snmp b14_D35Input (read-only) object values."
    ::=  { b14_D35 1 }

b14_D35InputTableEntry  OBJECT-TYPE
    SYNTAX                B14_D35InputTableEntry
    ACCESS                not-accessible
    STATUS                mandatory
    DESCRIPTION
    "An b14_D35Input table entry containing data for a specific b14_D35Input."
    INDEX  { b14_D35InputIndex }  ::=   { b14_D35InputTable 1 }

B14_D35InputTableEntry ::= SEQUENCE {
        b14_D35InputIndex       INTEGER,
        b14_D35InputName        DisplayString,
        b14_D35InputValue       DisplayString
    }

b14_D35InputIndex   OBJECT-TYPE
    SYNTAX           INTEGER(0..2147483647)
    ACCESS           read-only
    STATUS           mandatory
    DESCRIPTION
    "The index in the b14_D35Input table for a particular snmp b14_D35Input
	 object.  Used to address table entries."
    ::=   { b14_D35InputTableEntry 1 }


b14_D35InputName    OBJECT-TYPE
    SYNTAX           DisplayString
    ACCESS           read-only
    STATUS           mandatory
    DESCRIPTION
    "Name of station object."
    ::=   { b14_D35InputTableEntry 2 }

b14_D35InputValue    OBJECT-TYPE
    SYNTAX           DisplayString
    ACCESS           read-write
    STATUS           mandatory
    DESCRIPTION
    "Current value of station object. Is read-write ."
    ::=   { b14_D35InputTableEntry 3 }



-- ***********************************
-- *
-- *  B14_D35Output table declarations
-- *
-- ***********************************

b14_D35OutputTable   OBJECT-TYPE
    SYNTAX                SEQUENCE OF B14_D35OutputTableEntry
    ACCESS                not-accessible
    STATUS                mandatory
    DESCRIPTION
    "A list of snmp b14_D35Output (read-only) object values."
    ::=  { b14_D35 2 }

b14_D35OutputTableEntry  OBJECT-TYPE
    SYNTAX                B14_D35OutputTableEntry
    ACCESS                not-accessible
    STATUS                mandatory
    DESCRIPTION
    "An b14_D35Output table entry containing data for a specific b14_D35Output."
    INDEX  { b14_D35OutputIndex }  ::=   { b14_D35OutputTable 1 }

B14_D35OutputTableEntry ::= SEQUENCE {
        b14_D35OutputIndex       INTEGER,
        b14_D35OutputName        DisplayString,
        b14_D35OutputValue       DisplayString
    }

b14_D35OutputIndex   OBJECT-TYPE
    SYNTAX           INTEGER(0..2147483647)
    ACCESS           read-only
    STATUS           mandatory
    DESCRIPTION
    "The index in the b14_D35Output table for a particular snmp b14_D35Output
	 object.  Used to address table entries."
    ::=   { b14_D35OutputTableEntry 1 }


b14_D35OutputName    OBJECT-TYPE
    SYNTAX           DisplayString
    ACCESS           read-only
    STATUS           mandatory
    DESCRIPTION
    "Name of station object."
    ::=   { b14_D35OutputTableEntry 2 }

b14_D35OutputValue    OBJECT-TYPE
    SYNTAX           DisplayString
    ACCESS           read-only
    STATUS           mandatory
    DESCRIPTION
    "Current value of station object. Is read-only ."
    ::=   { b14_D35OutputTableEntry 3 }


-- ***********************************
-- *
-- *  B14_D22
-- *
-- ***********************************
    b14_D22    OBJECT IDENTIFIER ::= { exportTables 105 }

-- ***********************************
-- *
-- *  B14_D22Input table declarations
-- *
-- ***********************************

b14_D22InputTable   OBJECT-TYPE
    SYNTAX                SEQUENCE OF B14_D22InputTableEntry
    ACCESS                not-accessible
    STATUS                mandatory
    DESCRIPTION
    "A list of snmp b14_D22Input (read-only) object values."
    ::=  { b14_D22 1 }

b14_D22InputTableEntry  OBJECT-TYPE
    SYNTAX                B14_D22InputTableEntry
    ACCESS                not-accessible
    STATUS                mandatory
    DESCRIPTION
    "An b14_D22Input table entry containing data for a specific b14_D22Input."
    INDEX  { b14_D22InputIndex }  ::=   { b14_D22InputTable 1 }

B14_D22InputTableEntry ::= SEQUENCE {
        b14_D22InputIndex       INTEGER,
        b14_D22InputName        DisplayString,
        b14_D22InputValue       DisplayString
    }

b14_D22InputIndex   OBJECT-TYPE
    SYNTAX           INTEGER(0..2147483647)
    ACCESS           read-only
    STATUS           mandatory
    DESCRIPTION
    "The index in the b14_D22Input table for a particular snmp b14_D22Input
	 object.  Used to address table entries."
    ::=   { b14_D22InputTableEntry 1 }


b14_D22InputName    OBJECT-TYPE
    SYNTAX           DisplayString
    ACCESS           read-only
    STATUS           mandatory
    DESCRIPTION
    "Name of station object."
    ::=   { b14_D22InputTableEntry 2 }

b14_D22InputValue    OBJECT-TYPE
    SYNTAX           DisplayString
    ACCESS           read-write
    STATUS           mandatory
    DESCRIPTION
    "Current value of station object. Is read-write ."
    ::=   { b14_D22InputTableEntry 3 }



-- ***********************************
-- *
-- *  B14_D22Output table declarations
-- *
-- ***********************************

b14_D22OutputTable   OBJECT-TYPE
    SYNTAX                SEQUENCE OF B14_D22OutputTableEntry
    ACCESS                not-accessible
    STATUS                mandatory
    DESCRIPTION
    "A list of snmp b14_D22Output (read-only) object values."
    ::=  { b14_D22 2 }

b14_D22OutputTableEntry  OBJECT-TYPE
    SYNTAX                B14_D22OutputTableEntry
    ACCESS                not-accessible
    STATUS                mandatory
    DESCRIPTION
    "An b14_D22Output table entry containing data for a specific b14_D22Output."
    INDEX  { b14_D22OutputIndex }  ::=   { b14_D22OutputTable 1 }

B14_D22OutputTableEntry ::= SEQUENCE {
        b14_D22OutputIndex       INTEGER,
        b14_D22OutputName        DisplayString,
        b14_D22OutputValue       DisplayString
    }

b14_D22OutputIndex   OBJECT-TYPE
    SYNTAX           INTEGER(0..2147483647)
    ACCESS           read-only
    STATUS           mandatory
    DESCRIPTION
    "The index in the b14_D22Output table for a particular snmp b14_D22Output
	 object.  Used to address table entries."
    ::=   { b14_D22OutputTableEntry 1 }


b14_D22OutputName    OBJECT-TYPE
    SYNTAX           DisplayString
    ACCESS           read-only
    STATUS           mandatory
    DESCRIPTION
    "Name of station object."
    ::=   { b14_D22OutputTableEntry 2 }

b14_D22OutputValue    OBJECT-TYPE
    SYNTAX           DisplayString
    ACCESS           read-only
    STATUS           mandatory
    DESCRIPTION
    "Current value of station object. Is read-only ."
    ::=   { b14_D22OutputTableEntry 3 }


-- ***********************************
-- *
-- *  B14_D28
-- *
-- ***********************************
    b14_D28    OBJECT IDENTIFIER ::= { exportTables 106 }

-- ***********************************
-- *
-- *  B14_D28Input table declarations
-- *
-- ***********************************

b14_D28InputTable   OBJECT-TYPE
    SYNTAX                SEQUENCE OF B14_D28InputTableEntry
    ACCESS                not-accessible
    STATUS                mandatory
    DESCRIPTION
    "A list of snmp b14_D28Input (read-only) object values."
    ::=  { b14_D28 1 }

b14_D28InputTableEntry  OBJECT-TYPE
    SYNTAX                B14_D28InputTableEntry
    ACCESS                not-accessible
    STATUS                mandatory
    DESCRIPTION
    "An b14_D28Input table entry containing data for a specific b14_D28Input."
    INDEX  { b14_D28InputIndex }  ::=   { b14_D28InputTable 1 }

B14_D28InputTableEntry ::= SEQUENCE {
        b14_D28InputIndex       INTEGER,
        b14_D28InputName        DisplayString,
        b14_D28InputValue       DisplayString
    }

b14_D28InputIndex   OBJECT-TYPE
    SYNTAX           INTEGER(0..2147483647)
    ACCESS           read-only
    STATUS           mandatory
    DESCRIPTION
    "The index in the b14_D28Input table for a particular snmp b14_D28Input
	 object.  Used to address table entries."
    ::=   { b14_D28InputTableEntry 1 }


b14_D28InputName    OBJECT-TYPE
    SYNTAX           DisplayString
    ACCESS           read-only
    STATUS           mandatory
    DESCRIPTION
    "Name of station object."
    ::=   { b14_D28InputTableEntry 2 }

b14_D28InputValue    OBJECT-TYPE
    SYNTAX           DisplayString
    ACCESS           read-write
    STATUS           mandatory
    DESCRIPTION
    "Current value of station object. Is read-write ."
    ::=   { b14_D28InputTableEntry 3 }



-- ***********************************
-- *
-- *  B14_D28Output table declarations
-- *
-- ***********************************

b14_D28OutputTable   OBJECT-TYPE
    SYNTAX                SEQUENCE OF B14_D28OutputTableEntry
    ACCESS                not-accessible
    STATUS                mandatory
    DESCRIPTION
    "A list of snmp b14_D28Output (read-only) object values."
    ::=  { b14_D28 2 }

b14_D28OutputTableEntry  OBJECT-TYPE
    SYNTAX                B14_D28OutputTableEntry
    ACCESS                not-accessible
    STATUS                mandatory
    DESCRIPTION
    "An b14_D28Output table entry containing data for a specific b14_D28Output."
    INDEX  { b14_D28OutputIndex }  ::=   { b14_D28OutputTable 1 }

B14_D28OutputTableEntry ::= SEQUENCE {
        b14_D28OutputIndex       INTEGER,
        b14_D28OutputName        DisplayString,
        b14_D28OutputValue       DisplayString
    }

b14_D28OutputIndex   OBJECT-TYPE
    SYNTAX           INTEGER(0..2147483647)
    ACCESS           read-only
    STATUS           mandatory
    DESCRIPTION
    "The index in the b14_D28Output table for a particular snmp b14_D28Output
	 object.  Used to address table entries."
    ::=   { b14_D28OutputTableEntry 1 }


b14_D28OutputName    OBJECT-TYPE
    SYNTAX           DisplayString
    ACCESS           read-only
    STATUS           mandatory
    DESCRIPTION
    "Name of station object."
    ::=   { b14_D28OutputTableEntry 2 }

b14_D28OutputValue    OBJECT-TYPE
    SYNTAX           DisplayString
    ACCESS           read-only
    STATUS           mandatory
    DESCRIPTION
    "Current value of station object. Is read-only ."
    ::=   { b14_D28OutputTableEntry 3 }


-- ***********************************
-- *
-- *  B14_D29
-- *
-- ***********************************
    b14_D29    OBJECT IDENTIFIER ::= { exportTables 107 }

-- ***********************************
-- *
-- *  B14_D29Input table declarations
-- *
-- ***********************************

b14_D29InputTable   OBJECT-TYPE
    SYNTAX                SEQUENCE OF B14_D29InputTableEntry
    ACCESS                not-accessible
    STATUS                mandatory
    DESCRIPTION
    "A list of snmp b14_D29Input (read-only) object values."
    ::=  { b14_D29 1 }

b14_D29InputTableEntry  OBJECT-TYPE
    SYNTAX                B14_D29InputTableEntry
    ACCESS                not-accessible
    STATUS                mandatory
    DESCRIPTION
    "An b14_D29Input table entry containing data for a specific b14_D29Input."
    INDEX  { b14_D29InputIndex }  ::=   { b14_D29InputTable 1 }

B14_D29InputTableEntry ::= SEQUENCE {
        b14_D29InputIndex       INTEGER,
        b14_D29InputName        DisplayString,
        b14_D29InputValue       DisplayString
    }

b14_D29InputIndex   OBJECT-TYPE
    SYNTAX           INTEGER(0..2147483647)
    ACCESS           read-only
    STATUS           mandatory
    DESCRIPTION
    "The index in the b14_D29Input table for a particular snmp b14_D29Input
	 object.  Used to address table entries."
    ::=   { b14_D29InputTableEntry 1 }


b14_D29InputName    OBJECT-TYPE
    SYNTAX           DisplayString
    ACCESS           read-only
    STATUS           mandatory
    DESCRIPTION
    "Name of station object."
    ::=   { b14_D29InputTableEntry 2 }

b14_D29InputValue    OBJECT-TYPE
    SYNTAX           DisplayString
    ACCESS           read-write
    STATUS           mandatory
    DESCRIPTION
    "Current value of station object. Is read-write ."
    ::=   { b14_D29InputTableEntry 3 }



-- ***********************************
-- *
-- *  B14_D29Output table declarations
-- *
-- ***********************************

b14_D29OutputTable   OBJECT-TYPE
    SYNTAX                SEQUENCE OF B14_D29OutputTableEntry
    ACCESS                not-accessible
    STATUS                mandatory
    DESCRIPTION
    "A list of snmp b14_D29Output (read-only) object values."
    ::=  { b14_D29 2 }

b14_D29OutputTableEntry  OBJECT-TYPE
    SYNTAX                B14_D29OutputTableEntry
    ACCESS                not-accessible
    STATUS                mandatory
    DESCRIPTION
    "An b14_D29Output table entry containing data for a specific b14_D29Output."
    INDEX  { b14_D29OutputIndex }  ::=   { b14_D29OutputTable 1 }

B14_D29OutputTableEntry ::= SEQUENCE {
        b14_D29OutputIndex       INTEGER,
        b14_D29OutputName        DisplayString,
        b14_D29OutputValue       DisplayString
    }

b14_D29OutputIndex   OBJECT-TYPE
    SYNTAX           INTEGER(0..2147483647)
    ACCESS           read-only
    STATUS           mandatory
    DESCRIPTION
    "The index in the b14_D29Output table for a particular snmp b14_D29Output
	 object.  Used to address table entries."
    ::=   { b14_D29OutputTableEntry 1 }


b14_D29OutputName    OBJECT-TYPE
    SYNTAX           DisplayString
    ACCESS           read-only
    STATUS           mandatory
    DESCRIPTION
    "Name of station object."
    ::=   { b14_D29OutputTableEntry 2 }

b14_D29OutputValue    OBJECT-TYPE
    SYNTAX           DisplayString
    ACCESS           read-only
    STATUS           mandatory
    DESCRIPTION
    "Current value of station object. Is read-only ."
    ::=   { b14_D29OutputTableEntry 3 }


-- ***********************************
-- *
-- *  B14_D30
-- *
-- ***********************************
    b14_D30    OBJECT IDENTIFIER ::= { exportTables 108 }

-- ***********************************
-- *
-- *  B14_D30Input table declarations
-- *
-- ***********************************

b14_D30InputTable   OBJECT-TYPE
    SYNTAX                SEQUENCE OF B14_D30InputTableEntry
    ACCESS                not-accessible
    STATUS                mandatory
    DESCRIPTION
    "A list of snmp b14_D30Input (read-only) object values."
    ::=  { b14_D30 1 }

b14_D30InputTableEntry  OBJECT-TYPE
    SYNTAX                B14_D30InputTableEntry
    ACCESS                not-accessible
    STATUS                mandatory
    DESCRIPTION
    "An b14_D30Input table entry containing data for a specific b14_D30Input."
    INDEX  { b14_D30InputIndex }  ::=   { b14_D30InputTable 1 }

B14_D30InputTableEntry ::= SEQUENCE {
        b14_D30InputIndex       INTEGER,
        b14_D30InputName        DisplayString,
        b14_D30InputValue       DisplayString
    }

b14_D30InputIndex   OBJECT-TYPE
    SYNTAX           INTEGER(0..2147483647)
    ACCESS           read-only
    STATUS           mandatory
    DESCRIPTION
    "The index in the b14_D30Input table for a particular snmp b14_D30Input
	 object.  Used to address table entries."
    ::=   { b14_D30InputTableEntry 1 }


b14_D30InputName    OBJECT-TYPE
    SYNTAX           DisplayString
    ACCESS           read-only
    STATUS           mandatory
    DESCRIPTION
    "Name of station object."
    ::=   { b14_D30InputTableEntry 2 }

b14_D30InputValue    OBJECT-TYPE
    SYNTAX           DisplayString
    ACCESS           read-write
    STATUS           mandatory
    DESCRIPTION
    "Current value of station object. Is read-write ."
    ::=   { b14_D30InputTableEntry 3 }



-- ***********************************
-- *
-- *  B14_D30Output table declarations
-- *
-- ***********************************

b14_D30OutputTable   OBJECT-TYPE
    SYNTAX                SEQUENCE OF B14_D30OutputTableEntry
    ACCESS                not-accessible
    STATUS                mandatory
    DESCRIPTION
    "A list of snmp b14_D30Output (read-only) object values."
    ::=  { b14_D30 2 }

b14_D30OutputTableEntry  OBJECT-TYPE
    SYNTAX                B14_D30OutputTableEntry
    ACCESS                not-accessible
    STATUS                mandatory
    DESCRIPTION
    "An b14_D30Output table entry containing data for a specific b14_D30Output."
    INDEX  { b14_D30OutputIndex }  ::=   { b14_D30OutputTable 1 }

B14_D30OutputTableEntry ::= SEQUENCE {
        b14_D30OutputIndex       INTEGER,
        b14_D30OutputName        DisplayString,
        b14_D30OutputValue       DisplayString
    }

b14_D30OutputIndex   OBJECT-TYPE
    SYNTAX           INTEGER(0..2147483647)
    ACCESS           read-only
    STATUS           mandatory
    DESCRIPTION
    "The index in the b14_D30Output table for a particular snmp b14_D30Output
	 object.  Used to address table entries."
    ::=   { b14_D30OutputTableEntry 1 }


b14_D30OutputName    OBJECT-TYPE
    SYNTAX           DisplayString
    ACCESS           read-only
    STATUS           mandatory
    DESCRIPTION
    "Name of station object."
    ::=   { b14_D30OutputTableEntry 2 }

b14_D30OutputValue    OBJECT-TYPE
    SYNTAX           DisplayString
    ACCESS           read-only
    STATUS           mandatory
    DESCRIPTION
    "Current value of station object. Is read-only ."
    ::=   { b14_D30OutputTableEntry 3 }


-- ***********************************
-- *
-- *  B14_D23
-- *
-- ***********************************
    b14_D23    OBJECT IDENTIFIER ::= { exportTables 109 }

-- ***********************************
-- *
-- *  B14_D23Input table declarations
-- *
-- ***********************************

b14_D23InputTable   OBJECT-TYPE
    SYNTAX                SEQUENCE OF B14_D23InputTableEntry
    ACCESS                not-accessible
    STATUS                mandatory
    DESCRIPTION
    "A list of snmp b14_D23Input (read-only) object values."
    ::=  { b14_D23 1 }

b14_D23InputTableEntry  OBJECT-TYPE
    SYNTAX                B14_D23InputTableEntry
    ACCESS                not-accessible
    STATUS                mandatory
    DESCRIPTION
    "An b14_D23Input table entry containing data for a specific b14_D23Input."
    INDEX  { b14_D23InputIndex }  ::=   { b14_D23InputTable 1 }

B14_D23InputTableEntry ::= SEQUENCE {
        b14_D23InputIndex       INTEGER,
        b14_D23InputName        DisplayString,
        b14_D23InputValue       DisplayString
    }

b14_D23InputIndex   OBJECT-TYPE
    SYNTAX           INTEGER(0..2147483647)
    ACCESS           read-only
    STATUS           mandatory
    DESCRIPTION
    "The index in the b14_D23Input table for a particular snmp b14_D23Input
	 object.  Used to address table entries."
    ::=   { b14_D23InputTableEntry 1 }


b14_D23InputName    OBJECT-TYPE
    SYNTAX           DisplayString
    ACCESS           read-only
    STATUS           mandatory
    DESCRIPTION
    "Name of station object."
    ::=   { b14_D23InputTableEntry 2 }

b14_D23InputValue    OBJECT-TYPE
    SYNTAX           DisplayString
    ACCESS           read-write
    STATUS           mandatory
    DESCRIPTION
    "Current value of station object. Is read-write ."
    ::=   { b14_D23InputTableEntry 3 }



-- ***********************************
-- *
-- *  B14_D23Output table declarations
-- *
-- ***********************************

b14_D23OutputTable   OBJECT-TYPE
    SYNTAX                SEQUENCE OF B14_D23OutputTableEntry
    ACCESS                not-accessible
    STATUS                mandatory
    DESCRIPTION
    "A list of snmp b14_D23Output (read-only) object values."
    ::=  { b14_D23 2 }

b14_D23OutputTableEntry  OBJECT-TYPE
    SYNTAX                B14_D23OutputTableEntry
    ACCESS                not-accessible
    STATUS                mandatory
    DESCRIPTION
    "An b14_D23Output table entry containing data for a specific b14_D23Output."
    INDEX  { b14_D23OutputIndex }  ::=   { b14_D23OutputTable 1 }

B14_D23OutputTableEntry ::= SEQUENCE {
        b14_D23OutputIndex       INTEGER,
        b14_D23OutputName        DisplayString,
        b14_D23OutputValue       DisplayString
    }

b14_D23OutputIndex   OBJECT-TYPE
    SYNTAX           INTEGER(0..2147483647)
    ACCESS           read-only
    STATUS           mandatory
    DESCRIPTION
    "The index in the b14_D23Output table for a particular snmp b14_D23Output
	 object.  Used to address table entries."
    ::=   { b14_D23OutputTableEntry 1 }


b14_D23OutputName    OBJECT-TYPE
    SYNTAX           DisplayString
    ACCESS           read-only
    STATUS           mandatory
    DESCRIPTION
    "Name of station object."
    ::=   { b14_D23OutputTableEntry 2 }

b14_D23OutputValue    OBJECT-TYPE
    SYNTAX           DisplayString
    ACCESS           read-only
    STATUS           mandatory
    DESCRIPTION
    "Current value of station object. Is read-only ."
    ::=   { b14_D23OutputTableEntry 3 }


-- ***********************************
-- *
-- *  B14_D24
-- *
-- ***********************************
    b14_D24    OBJECT IDENTIFIER ::= { exportTables 110 }

-- ***********************************
-- *
-- *  B14_D24Input table declarations
-- *
-- ***********************************

b14_D24InputTable   OBJECT-TYPE
    SYNTAX                SEQUENCE OF B14_D24InputTableEntry
    ACCESS                not-accessible
    STATUS                mandatory
    DESCRIPTION
    "A list of snmp b14_D24Input (read-only) object values."
    ::=  { b14_D24 1 }

b14_D24InputTableEntry  OBJECT-TYPE
    SYNTAX                B14_D24InputTableEntry
    ACCESS                not-accessible
    STATUS                mandatory
    DESCRIPTION
    "An b14_D24Input table entry containing data for a specific b14_D24Input."
    INDEX  { b14_D24InputIndex }  ::=   { b14_D24InputTable 1 }

B14_D24InputTableEntry ::= SEQUENCE {
        b14_D24InputIndex       INTEGER,
        b14_D24InputName        DisplayString,
        b14_D24InputValue       DisplayString
    }

b14_D24InputIndex   OBJECT-TYPE
    SYNTAX           INTEGER(0..2147483647)
    ACCESS           read-only
    STATUS           mandatory
    DESCRIPTION
    "The index in the b14_D24Input table for a particular snmp b14_D24Input
	 object.  Used to address table entries."
    ::=   { b14_D24InputTableEntry 1 }


b14_D24InputName    OBJECT-TYPE
    SYNTAX           DisplayString
    ACCESS           read-only
    STATUS           mandatory
    DESCRIPTION
    "Name of station object."
    ::=   { b14_D24InputTableEntry 2 }

b14_D24InputValue    OBJECT-TYPE
    SYNTAX           DisplayString
    ACCESS           read-write
    STATUS           mandatory
    DESCRIPTION
    "Current value of station object. Is read-write ."
    ::=   { b14_D24InputTableEntry 3 }



-- ***********************************
-- *
-- *  B14_D24Output table declarations
-- *
-- ***********************************

b14_D24OutputTable   OBJECT-TYPE
    SYNTAX                SEQUENCE OF B14_D24OutputTableEntry
    ACCESS                not-accessible
    STATUS                mandatory
    DESCRIPTION
    "A list of snmp b14_D24Output (read-only) object values."
    ::=  { b14_D24 2 }

b14_D24OutputTableEntry  OBJECT-TYPE
    SYNTAX                B14_D24OutputTableEntry
    ACCESS                not-accessible
    STATUS                mandatory
    DESCRIPTION
    "An b14_D24Output table entry containing data for a specific b14_D24Output."
    INDEX  { b14_D24OutputIndex }  ::=   { b14_D24OutputTable 1 }

B14_D24OutputTableEntry ::= SEQUENCE {
        b14_D24OutputIndex       INTEGER,
        b14_D24OutputName        DisplayString,
        b14_D24OutputValue       DisplayString
    }

b14_D24OutputIndex   OBJECT-TYPE
    SYNTAX           INTEGER(0..2147483647)
    ACCESS           read-only
    STATUS           mandatory
    DESCRIPTION
    "The index in the b14_D24Output table for a particular snmp b14_D24Output
	 object.  Used to address table entries."
    ::=   { b14_D24OutputTableEntry 1 }


b14_D24OutputName    OBJECT-TYPE
    SYNTAX           DisplayString
    ACCESS           read-only
    STATUS           mandatory
    DESCRIPTION
    "Name of station object."
    ::=   { b14_D24OutputTableEntry 2 }

b14_D24OutputValue    OBJECT-TYPE
    SYNTAX           DisplayString
    ACCESS           read-only
    STATUS           mandatory
    DESCRIPTION
    "Current value of station object. Is read-only ."
    ::=   { b14_D24OutputTableEntry 3 }


-- ***********************************
-- *
-- *  B14_D26
-- *
-- ***********************************
    b14_D26    OBJECT IDENTIFIER ::= { exportTables 111 }

-- ***********************************
-- *
-- *  B14_D26Input table declarations
-- *
-- ***********************************

b14_D26InputTable   OBJECT-TYPE
    SYNTAX                SEQUENCE OF B14_D26InputTableEntry
    ACCESS                not-accessible
    STATUS                mandatory
    DESCRIPTION
    "A list of snmp b14_D26Input (read-only) object values."
    ::=  { b14_D26 1 }

b14_D26InputTableEntry  OBJECT-TYPE
    SYNTAX                B14_D26InputTableEntry
    ACCESS                not-accessible
    STATUS                mandatory
    DESCRIPTION
    "An b14_D26Input table entry containing data for a specific b14_D26Input."
    INDEX  { b14_D26InputIndex }  ::=   { b14_D26InputTable 1 }

B14_D26InputTableEntry ::= SEQUENCE {
        b14_D26InputIndex       INTEGER,
        b14_D26InputName        DisplayString,
        b14_D26InputValue       DisplayString
    }

b14_D26InputIndex   OBJECT-TYPE
    SYNTAX           INTEGER(0..2147483647)
    ACCESS           read-only
    STATUS           mandatory
    DESCRIPTION
    "The index in the b14_D26Input table for a particular snmp b14_D26Input
	 object.  Used to address table entries."
    ::=   { b14_D26InputTableEntry 1 }


b14_D26InputName    OBJECT-TYPE
    SYNTAX           DisplayString
    ACCESS           read-only
    STATUS           mandatory
    DESCRIPTION
    "Name of station object."
    ::=   { b14_D26InputTableEntry 2 }

b14_D26InputValue    OBJECT-TYPE
    SYNTAX           DisplayString
    ACCESS           read-write
    STATUS           mandatory
    DESCRIPTION
    "Current value of station object. Is read-write ."
    ::=   { b14_D26InputTableEntry 3 }



-- ***********************************
-- *
-- *  B14_D26Output table declarations
-- *
-- ***********************************

b14_D26OutputTable   OBJECT-TYPE
    SYNTAX                SEQUENCE OF B14_D26OutputTableEntry
    ACCESS                not-accessible
    STATUS                mandatory
    DESCRIPTION
    "A list of snmp b14_D26Output (read-only) object values."
    ::=  { b14_D26 2 }

b14_D26OutputTableEntry  OBJECT-TYPE
    SYNTAX                B14_D26OutputTableEntry
    ACCESS                not-accessible
    STATUS                mandatory
    DESCRIPTION
    "An b14_D26Output table entry containing data for a specific b14_D26Output."
    INDEX  { b14_D26OutputIndex }  ::=   { b14_D26OutputTable 1 }

B14_D26OutputTableEntry ::= SEQUENCE {
        b14_D26OutputIndex       INTEGER,
        b14_D26OutputName        DisplayString,
        b14_D26OutputValue       DisplayString
    }

b14_D26OutputIndex   OBJECT-TYPE
    SYNTAX           INTEGER(0..2147483647)
    ACCESS           read-only
    STATUS           mandatory
    DESCRIPTION
    "The index in the b14_D26Output table for a particular snmp b14_D26Output
	 object.  Used to address table entries."
    ::=   { b14_D26OutputTableEntry 1 }


b14_D26OutputName    OBJECT-TYPE
    SYNTAX           DisplayString
    ACCESS           read-only
    STATUS           mandatory
    DESCRIPTION
    "Name of station object."
    ::=   { b14_D26OutputTableEntry 2 }

b14_D26OutputValue    OBJECT-TYPE
    SYNTAX           DisplayString
    ACCESS           read-only
    STATUS           mandatory
    DESCRIPTION
    "Current value of station object. Is read-only ."
    ::=   { b14_D26OutputTableEntry 3 }


-- ***********************************
-- *
-- *  B14_D27
-- *
-- ***********************************
    b14_D27    OBJECT IDENTIFIER ::= { exportTables 112 }

-- ***********************************
-- *
-- *  B14_D27Input table declarations
-- *
-- ***********************************

b14_D27InputTable   OBJECT-TYPE
    SYNTAX                SEQUENCE OF B14_D27InputTableEntry
    ACCESS                not-accessible
    STATUS                mandatory
    DESCRIPTION
    "A list of snmp b14_D27Input (read-only) object values."
    ::=  { b14_D27 1 }

b14_D27InputTableEntry  OBJECT-TYPE
    SYNTAX                B14_D27InputTableEntry
    ACCESS                not-accessible
    STATUS                mandatory
    DESCRIPTION
    "An b14_D27Input table entry containing data for a specific b14_D27Input."
    INDEX  { b14_D27InputIndex }  ::=   { b14_D27InputTable 1 }

B14_D27InputTableEntry ::= SEQUENCE {
        b14_D27InputIndex       INTEGER,
        b14_D27InputName        DisplayString,
        b14_D27InputValue       DisplayString
    }

b14_D27InputIndex   OBJECT-TYPE
    SYNTAX           INTEGER(0..2147483647)
    ACCESS           read-only
    STATUS           mandatory
    DESCRIPTION
    "The index in the b14_D27Input table for a particular snmp b14_D27Input
	 object.  Used to address table entries."
    ::=   { b14_D27InputTableEntry 1 }


b14_D27InputName    OBJECT-TYPE
    SYNTAX           DisplayString
    ACCESS           read-only
    STATUS           mandatory
    DESCRIPTION
    "Name of station object."
    ::=   { b14_D27InputTableEntry 2 }

b14_D27InputValue    OBJECT-TYPE
    SYNTAX           DisplayString
    ACCESS           read-write
    STATUS           mandatory
    DESCRIPTION
    "Current value of station object. Is read-write ."
    ::=   { b14_D27InputTableEntry 3 }



-- ***********************************
-- *
-- *  B14_D27Output table declarations
-- *
-- ***********************************

b14_D27OutputTable   OBJECT-TYPE
    SYNTAX                SEQUENCE OF B14_D27OutputTableEntry
    ACCESS                not-accessible
    STATUS                mandatory
    DESCRIPTION
    "A list of snmp b14_D27Output (read-only) object values."
    ::=  { b14_D27 2 }

b14_D27OutputTableEntry  OBJECT-TYPE
    SYNTAX                B14_D27OutputTableEntry
    ACCESS                not-accessible
    STATUS                mandatory
    DESCRIPTION
    "An b14_D27Output table entry containing data for a specific b14_D27Output."
    INDEX  { b14_D27OutputIndex }  ::=   { b14_D27OutputTable 1 }

B14_D27OutputTableEntry ::= SEQUENCE {
        b14_D27OutputIndex       INTEGER,
        b14_D27OutputName        DisplayString,
        b14_D27OutputValue       DisplayString
    }

b14_D27OutputIndex   OBJECT-TYPE
    SYNTAX           INTEGER(0..2147483647)
    ACCESS           read-only
    STATUS           mandatory
    DESCRIPTION
    "The index in the b14_D27Output table for a particular snmp b14_D27Output
	 object.  Used to address table entries."
    ::=   { b14_D27OutputTableEntry 1 }


b14_D27OutputName    OBJECT-TYPE
    SYNTAX           DisplayString
    ACCESS           read-only
    STATUS           mandatory
    DESCRIPTION
    "Name of station object."
    ::=   { b14_D27OutputTableEntry 2 }

b14_D27OutputValue    OBJECT-TYPE
    SYNTAX           DisplayString
    ACCESS           read-only
    STATUS           mandatory
    DESCRIPTION
    "Current value of station object. Is read-only ."
    ::=   { b14_D27OutputTableEntry 3 }


-- ***********************************
-- *
-- *  B14_D31
-- *
-- ***********************************
    b14_D31    OBJECT IDENTIFIER ::= { exportTables 113 }

-- ***********************************
-- *
-- *  B14_D31Input table declarations
-- *
-- ***********************************

b14_D31InputTable   OBJECT-TYPE
    SYNTAX                SEQUENCE OF B14_D31InputTableEntry
    ACCESS                not-accessible
    STATUS                mandatory
    DESCRIPTION
    "A list of snmp b14_D31Input (read-only) object values."
    ::=  { b14_D31 1 }

b14_D31InputTableEntry  OBJECT-TYPE
    SYNTAX                B14_D31InputTableEntry
    ACCESS                not-accessible
    STATUS                mandatory
    DESCRIPTION
    "An b14_D31Input table entry containing data for a specific b14_D31Input."
    INDEX  { b14_D31InputIndex }  ::=   { b14_D31InputTable 1 }

B14_D31InputTableEntry ::= SEQUENCE {
        b14_D31InputIndex       INTEGER,
        b14_D31InputName        DisplayString,
        b14_D31InputValue       DisplayString
    }

b14_D31InputIndex   OBJECT-TYPE
    SYNTAX           INTEGER(0..2147483647)
    ACCESS           read-only
    STATUS           mandatory
    DESCRIPTION
    "The index in the b14_D31Input table for a particular snmp b14_D31Input
	 object.  Used to address table entries."
    ::=   { b14_D31InputTableEntry 1 }


b14_D31InputName    OBJECT-TYPE
    SYNTAX           DisplayString
    ACCESS           read-only
    STATUS           mandatory
    DESCRIPTION
    "Name of station object."
    ::=   { b14_D31InputTableEntry 2 }

b14_D31InputValue    OBJECT-TYPE
    SYNTAX           DisplayString
    ACCESS           read-write
    STATUS           mandatory
    DESCRIPTION
    "Current value of station object. Is read-write ."
    ::=   { b14_D31InputTableEntry 3 }



-- ***********************************
-- *
-- *  B14_D31Output table declarations
-- *
-- ***********************************

b14_D31OutputTable   OBJECT-TYPE
    SYNTAX                SEQUENCE OF B14_D31OutputTableEntry
    ACCESS                not-accessible
    STATUS                mandatory
    DESCRIPTION
    "A list of snmp b14_D31Output (read-only) object values."
    ::=  { b14_D31 2 }

b14_D31OutputTableEntry  OBJECT-TYPE
    SYNTAX                B14_D31OutputTableEntry
    ACCESS                not-accessible
    STATUS                mandatory
    DESCRIPTION
    "An b14_D31Output table entry containing data for a specific b14_D31Output."
    INDEX  { b14_D31OutputIndex }  ::=   { b14_D31OutputTable 1 }

B14_D31OutputTableEntry ::= SEQUENCE {
        b14_D31OutputIndex       INTEGER,
        b14_D31OutputName        DisplayString,
        b14_D31OutputValue       DisplayString
    }

b14_D31OutputIndex   OBJECT-TYPE
    SYNTAX           INTEGER(0..2147483647)
    ACCESS           read-only
    STATUS           mandatory
    DESCRIPTION
    "The index in the b14_D31Output table for a particular snmp b14_D31Output
	 object.  Used to address table entries."
    ::=   { b14_D31OutputTableEntry 1 }


b14_D31OutputName    OBJECT-TYPE
    SYNTAX           DisplayString
    ACCESS           read-only
    STATUS           mandatory
    DESCRIPTION
    "Name of station object."
    ::=   { b14_D31OutputTableEntry 2 }

b14_D31OutputValue    OBJECT-TYPE
    SYNTAX           DisplayString
    ACCESS           read-only
    STATUS           mandatory
    DESCRIPTION
    "Current value of station object. Is read-only ."
    ::=   { b14_D31OutputTableEntry 3 }


-- ***********************************
-- *
-- *  B14_D32
-- *
-- ***********************************
    b14_D32    OBJECT IDENTIFIER ::= { exportTables 114 }

-- ***********************************
-- *
-- *  B14_D32Input table declarations
-- *
-- ***********************************

b14_D32InputTable   OBJECT-TYPE
    SYNTAX                SEQUENCE OF B14_D32InputTableEntry
    ACCESS                not-accessible
    STATUS                mandatory
    DESCRIPTION
    "A list of snmp b14_D32Input (read-only) object values."
    ::=  { b14_D32 1 }

b14_D32InputTableEntry  OBJECT-TYPE
    SYNTAX                B14_D32InputTableEntry
    ACCESS                not-accessible
    STATUS                mandatory
    DESCRIPTION
    "An b14_D32Input table entry containing data for a specific b14_D32Input."
    INDEX  { b14_D32InputIndex }  ::=   { b14_D32InputTable 1 }

B14_D32InputTableEntry ::= SEQUENCE {
        b14_D32InputIndex       INTEGER,
        b14_D32InputName        DisplayString,
        b14_D32InputValue       DisplayString
    }

b14_D32InputIndex   OBJECT-TYPE
    SYNTAX           INTEGER(0..2147483647)
    ACCESS           read-only
    STATUS           mandatory
    DESCRIPTION
    "The index in the b14_D32Input table for a particular snmp b14_D32Input
	 object.  Used to address table entries."
    ::=   { b14_D32InputTableEntry 1 }


b14_D32InputName    OBJECT-TYPE
    SYNTAX           DisplayString
    ACCESS           read-only
    STATUS           mandatory
    DESCRIPTION
    "Name of station object."
    ::=   { b14_D32InputTableEntry 2 }

b14_D32InputValue    OBJECT-TYPE
    SYNTAX           DisplayString
    ACCESS           read-write
    STATUS           mandatory
    DESCRIPTION
    "Current value of station object. Is read-write ."
    ::=   { b14_D32InputTableEntry 3 }



-- ***********************************
-- *
-- *  B14_D32Output table declarations
-- *
-- ***********************************

b14_D32OutputTable   OBJECT-TYPE
    SYNTAX                SEQUENCE OF B14_D32OutputTableEntry
    ACCESS                not-accessible
    STATUS                mandatory
    DESCRIPTION
    "A list of snmp b14_D32Output (read-only) object values."
    ::=  { b14_D32 2 }

b14_D32OutputTableEntry  OBJECT-TYPE
    SYNTAX                B14_D32OutputTableEntry
    ACCESS                not-accessible
    STATUS                mandatory
    DESCRIPTION
    "An b14_D32Output table entry containing data for a specific b14_D32Output."
    INDEX  { b14_D32OutputIndex }  ::=   { b14_D32OutputTable 1 }

B14_D32OutputTableEntry ::= SEQUENCE {
        b14_D32OutputIndex       INTEGER,
        b14_D32OutputName        DisplayString,
        b14_D32OutputValue       DisplayString
    }

b14_D32OutputIndex   OBJECT-TYPE
    SYNTAX           INTEGER(0..2147483647)
    ACCESS           read-only
    STATUS           mandatory
    DESCRIPTION
    "The index in the b14_D32Output table for a particular snmp b14_D32Output
	 object.  Used to address table entries."
    ::=   { b14_D32OutputTableEntry 1 }


b14_D32OutputName    OBJECT-TYPE
    SYNTAX           DisplayString
    ACCESS           read-only
    STATUS           mandatory
    DESCRIPTION
    "Name of station object."
    ::=   { b14_D32OutputTableEntry 2 }

b14_D32OutputValue    OBJECT-TYPE
    SYNTAX           DisplayString
    ACCESS           read-only
    STATUS           mandatory
    DESCRIPTION
    "Current value of station object. Is read-only ."
    ::=   { b14_D32OutputTableEntry 3 }


-- ***********************************
-- *
-- *  B14_D21
-- *
-- ***********************************
    b14_D21    OBJECT IDENTIFIER ::= { exportTables 115 }

-- ***********************************
-- *
-- *  B14_D21Input table declarations
-- *
-- ***********************************

b14_D21InputTable   OBJECT-TYPE
    SYNTAX                SEQUENCE OF B14_D21InputTableEntry
    ACCESS                not-accessible
    STATUS                mandatory
    DESCRIPTION
    "A list of snmp b14_D21Input (read-only) object values."
    ::=  { b14_D21 1 }

b14_D21InputTableEntry  OBJECT-TYPE
    SYNTAX                B14_D21InputTableEntry
    ACCESS                not-accessible
    STATUS                mandatory
    DESCRIPTION
    "An b14_D21Input table entry containing data for a specific b14_D21Input."
    INDEX  { b14_D21InputIndex }  ::=   { b14_D21InputTable 1 }

B14_D21InputTableEntry ::= SEQUENCE {
        b14_D21InputIndex       INTEGER,
        b14_D21InputName        DisplayString,
        b14_D21InputValue       DisplayString
    }

b14_D21InputIndex   OBJECT-TYPE
    SYNTAX           INTEGER(0..2147483647)
    ACCESS           read-only
    STATUS           mandatory
    DESCRIPTION
    "The index in the b14_D21Input table for a particular snmp b14_D21Input
	 object.  Used to address table entries."
    ::=   { b14_D21InputTableEntry 1 }


b14_D21InputName    OBJECT-TYPE
    SYNTAX           DisplayString
    ACCESS           read-only
    STATUS           mandatory
    DESCRIPTION
    "Name of station object."
    ::=   { b14_D21InputTableEntry 2 }

b14_D21InputValue    OBJECT-TYPE
    SYNTAX           DisplayString
    ACCESS           read-write
    STATUS           mandatory
    DESCRIPTION
    "Current value of station object. Is read-write ."
    ::=   { b14_D21InputTableEntry 3 }



-- ***********************************
-- *
-- *  B14_D21Output table declarations
-- *
-- ***********************************

b14_D21OutputTable   OBJECT-TYPE
    SYNTAX                SEQUENCE OF B14_D21OutputTableEntry
    ACCESS                not-accessible
    STATUS                mandatory
    DESCRIPTION
    "A list of snmp b14_D21Output (read-only) object values."
    ::=  { b14_D21 2 }

b14_D21OutputTableEntry  OBJECT-TYPE
    SYNTAX                B14_D21OutputTableEntry
    ACCESS                not-accessible
    STATUS                mandatory
    DESCRIPTION
    "An b14_D21Output table entry containing data for a specific b14_D21Output."
    INDEX  { b14_D21OutputIndex }  ::=   { b14_D21OutputTable 1 }

B14_D21OutputTableEntry ::= SEQUENCE {
        b14_D21OutputIndex       INTEGER,
        b14_D21OutputName        DisplayString,
        b14_D21OutputValue       DisplayString
    }

b14_D21OutputIndex   OBJECT-TYPE
    SYNTAX           INTEGER(0..2147483647)
    ACCESS           read-only
    STATUS           mandatory
    DESCRIPTION
    "The index in the b14_D21Output table for a particular snmp b14_D21Output
	 object.  Used to address table entries."
    ::=   { b14_D21OutputTableEntry 1 }


b14_D21OutputName    OBJECT-TYPE
    SYNTAX           DisplayString
    ACCESS           read-only
    STATUS           mandatory
    DESCRIPTION
    "Name of station object."
    ::=   { b14_D21OutputTableEntry 2 }

b14_D21OutputValue    OBJECT-TYPE
    SYNTAX           DisplayString
    ACCESS           read-only
    STATUS           mandatory
    DESCRIPTION
    "Current value of station object. Is read-only ."
    ::=   { b14_D21OutputTableEntry 3 }


-- ***********************************
-- *
-- *  B14_D25
-- *
-- ***********************************
    b14_D25    OBJECT IDENTIFIER ::= { exportTables 116 }

-- ***********************************
-- *
-- *  B14_D25Input table declarations
-- *
-- ***********************************

b14_D25InputTable   OBJECT-TYPE
    SYNTAX                SEQUENCE OF B14_D25InputTableEntry
    ACCESS                not-accessible
    STATUS                mandatory
    DESCRIPTION
    "A list of snmp b14_D25Input (read-only) object values."
    ::=  { b14_D25 1 }

b14_D25InputTableEntry  OBJECT-TYPE
    SYNTAX                B14_D25InputTableEntry
    ACCESS                not-accessible
    STATUS                mandatory
    DESCRIPTION
    "An b14_D25Input table entry containing data for a specific b14_D25Input."
    INDEX  { b14_D25InputIndex }  ::=   { b14_D25InputTable 1 }

B14_D25InputTableEntry ::= SEQUENCE {
        b14_D25InputIndex       INTEGER,
        b14_D25InputName        DisplayString,
        b14_D25InputValue       DisplayString
    }

b14_D25InputIndex   OBJECT-TYPE
    SYNTAX           INTEGER(0..2147483647)
    ACCESS           read-only
    STATUS           mandatory
    DESCRIPTION
    "The index in the b14_D25Input table for a particular snmp b14_D25Input
	 object.  Used to address table entries."
    ::=   { b14_D25InputTableEntry 1 }


b14_D25InputName    OBJECT-TYPE
    SYNTAX           DisplayString
    ACCESS           read-only
    STATUS           mandatory
    DESCRIPTION
    "Name of station object."
    ::=   { b14_D25InputTableEntry 2 }

b14_D25InputValue    OBJECT-TYPE
    SYNTAX           DisplayString
    ACCESS           read-write
    STATUS           mandatory
    DESCRIPTION
    "Current value of station object. Is read-write ."
    ::=   { b14_D25InputTableEntry 3 }



-- ***********************************
-- *
-- *  B14_D25Output table declarations
-- *
-- ***********************************

b14_D25OutputTable   OBJECT-TYPE
    SYNTAX                SEQUENCE OF B14_D25OutputTableEntry
    ACCESS                not-accessible
    STATUS                mandatory
    DESCRIPTION
    "A list of snmp b14_D25Output (read-only) object values."
    ::=  { b14_D25 2 }

b14_D25OutputTableEntry  OBJECT-TYPE
    SYNTAX                B14_D25OutputTableEntry
    ACCESS                not-accessible
    STATUS                mandatory
    DESCRIPTION
    "An b14_D25Output table entry containing data for a specific b14_D25Output."
    INDEX  { b14_D25OutputIndex }  ::=   { b14_D25OutputTable 1 }

B14_D25OutputTableEntry ::= SEQUENCE {
        b14_D25OutputIndex       INTEGER,
        b14_D25OutputName        DisplayString,
        b14_D25OutputValue       DisplayString
    }

b14_D25OutputIndex   OBJECT-TYPE
    SYNTAX           INTEGER(0..2147483647)
    ACCESS           read-only
    STATUS           mandatory
    DESCRIPTION
    "The index in the b14_D25Output table for a particular snmp b14_D25Output
	 object.  Used to address table entries."
    ::=   { b14_D25OutputTableEntry 1 }


b14_D25OutputName    OBJECT-TYPE
    SYNTAX           DisplayString
    ACCESS           read-only
    STATUS           mandatory
    DESCRIPTION
    "Name of station object."
    ::=   { b14_D25OutputTableEntry 2 }

b14_D25OutputValue    OBJECT-TYPE
    SYNTAX           DisplayString
    ACCESS           read-only
    STATUS           mandatory
    DESCRIPTION
    "Current value of station object. Is read-only ."
    ::=   { b14_D25OutputTableEntry 3 }


-- ***********************************
-- *
-- *  B14_D63
-- *
-- ***********************************
    b14_D63    OBJECT IDENTIFIER ::= { exportTables 117 }

-- ***********************************
-- *
-- *  B14_D63Input table declarations
-- *
-- ***********************************

b14_D63InputTable   OBJECT-TYPE
    SYNTAX                SEQUENCE OF B14_D63InputTableEntry
    ACCESS                not-accessible
    STATUS                mandatory
    DESCRIPTION
    "A list of snmp b14_D63Input (read-only) object values."
    ::=  { b14_D63 1 }

b14_D63InputTableEntry  OBJECT-TYPE
    SYNTAX                B14_D63InputTableEntry
    ACCESS                not-accessible
    STATUS                mandatory
    DESCRIPTION
    "An b14_D63Input table entry containing data for a specific b14_D63Input."
    INDEX  { b14_D63InputIndex }  ::=   { b14_D63InputTable 1 }

B14_D63InputTableEntry ::= SEQUENCE {
        b14_D63InputIndex       INTEGER,
        b14_D63InputName        DisplayString,
        b14_D63InputValue       DisplayString
    }

b14_D63InputIndex   OBJECT-TYPE
    SYNTAX           INTEGER(0..2147483647)
    ACCESS           read-only
    STATUS           mandatory
    DESCRIPTION
    "The index in the b14_D63Input table for a particular snmp b14_D63Input
	 object.  Used to address table entries."
    ::=   { b14_D63InputTableEntry 1 }


b14_D63InputName    OBJECT-TYPE
    SYNTAX           DisplayString
    ACCESS           read-only
    STATUS           mandatory
    DESCRIPTION
    "Name of station object."
    ::=   { b14_D63InputTableEntry 2 }

b14_D63InputValue    OBJECT-TYPE
    SYNTAX           DisplayString
    ACCESS           read-write
    STATUS           mandatory
    DESCRIPTION
    "Current value of station object. Is read-write ."
    ::=   { b14_D63InputTableEntry 3 }



-- ***********************************
-- *
-- *  B14_D63Output table declarations
-- *
-- ***********************************

b14_D63OutputTable   OBJECT-TYPE
    SYNTAX                SEQUENCE OF B14_D63OutputTableEntry
    ACCESS                not-accessible
    STATUS                mandatory
    DESCRIPTION
    "A list of snmp b14_D63Output (read-only) object values."
    ::=  { b14_D63 2 }

b14_D63OutputTableEntry  OBJECT-TYPE
    SYNTAX                B14_D63OutputTableEntry
    ACCESS                not-accessible
    STATUS                mandatory
    DESCRIPTION
    "An b14_D63Output table entry containing data for a specific b14_D63Output."
    INDEX  { b14_D63OutputIndex }  ::=   { b14_D63OutputTable 1 }

B14_D63OutputTableEntry ::= SEQUENCE {
        b14_D63OutputIndex       INTEGER,
        b14_D63OutputName        DisplayString,
        b14_D63OutputValue       DisplayString
    }

b14_D63OutputIndex   OBJECT-TYPE
    SYNTAX           INTEGER(0..2147483647)
    ACCESS           read-only
    STATUS           mandatory
    DESCRIPTION
    "The index in the b14_D63Output table for a particular snmp b14_D63Output
	 object.  Used to address table entries."
    ::=   { b14_D63OutputTableEntry 1 }


b14_D63OutputName    OBJECT-TYPE
    SYNTAX           DisplayString
    ACCESS           read-only
    STATUS           mandatory
    DESCRIPTION
    "Name of station object."
    ::=   { b14_D63OutputTableEntry 2 }

b14_D63OutputValue    OBJECT-TYPE
    SYNTAX           DisplayString
    ACCESS           read-only
    STATUS           mandatory
    DESCRIPTION
    "Current value of station object. Is read-only ."
    ::=   { b14_D63OutputTableEntry 3 }


-- ***********************************
-- *
-- *  B14_D64
-- *
-- ***********************************
    b14_D64    OBJECT IDENTIFIER ::= { exportTables 118 }

-- ***********************************
-- *
-- *  B14_D64Input table declarations
-- *
-- ***********************************

b14_D64InputTable   OBJECT-TYPE
    SYNTAX                SEQUENCE OF B14_D64InputTableEntry
    ACCESS                not-accessible
    STATUS                mandatory
    DESCRIPTION
    "A list of snmp b14_D64Input (read-only) object values."
    ::=  { b14_D64 1 }

b14_D64InputTableEntry  OBJECT-TYPE
    SYNTAX                B14_D64InputTableEntry
    ACCESS                not-accessible
    STATUS                mandatory
    DESCRIPTION
    "An b14_D64Input table entry containing data for a specific b14_D64Input."
    INDEX  { b14_D64InputIndex }  ::=   { b14_D64InputTable 1 }

B14_D64InputTableEntry ::= SEQUENCE {
        b14_D64InputIndex       INTEGER,
        b14_D64InputName        DisplayString,
        b14_D64InputValue       DisplayString
    }

b14_D64InputIndex   OBJECT-TYPE
    SYNTAX           INTEGER(0..2147483647)
    ACCESS           read-only
    STATUS           mandatory
    DESCRIPTION
    "The index in the b14_D64Input table for a particular snmp b14_D64Input
	 object.  Used to address table entries."
    ::=   { b14_D64InputTableEntry 1 }


b14_D64InputName    OBJECT-TYPE
    SYNTAX           DisplayString
    ACCESS           read-only
    STATUS           mandatory
    DESCRIPTION
    "Name of station object."
    ::=   { b14_D64InputTableEntry 2 }

b14_D64InputValue    OBJECT-TYPE
    SYNTAX           DisplayString
    ACCESS           read-write
    STATUS           mandatory
    DESCRIPTION
    "Current value of station object. Is read-write ."
    ::=   { b14_D64InputTableEntry 3 }



-- ***********************************
-- *
-- *  B14_D64Output table declarations
-- *
-- ***********************************

b14_D64OutputTable   OBJECT-TYPE
    SYNTAX                SEQUENCE OF B14_D64OutputTableEntry
    ACCESS                not-accessible
    STATUS                mandatory
    DESCRIPTION
    "A list of snmp b14_D64Output (read-only) object values."
    ::=  { b14_D64 2 }

b14_D64OutputTableEntry  OBJECT-TYPE
    SYNTAX                B14_D64OutputTableEntry
    ACCESS                not-accessible
    STATUS                mandatory
    DESCRIPTION
    "An b14_D64Output table entry containing data for a specific b14_D64Output."
    INDEX  { b14_D64OutputIndex }  ::=   { b14_D64OutputTable 1 }

B14_D64OutputTableEntry ::= SEQUENCE {
        b14_D64OutputIndex       INTEGER,
        b14_D64OutputName        DisplayString,
        b14_D64OutputValue       DisplayString
    }

b14_D64OutputIndex   OBJECT-TYPE
    SYNTAX           INTEGER(0..2147483647)
    ACCESS           read-only
    STATUS           mandatory
    DESCRIPTION
    "The index in the b14_D64Output table for a particular snmp b14_D64Output
	 object.  Used to address table entries."
    ::=   { b14_D64OutputTableEntry 1 }


b14_D64OutputName    OBJECT-TYPE
    SYNTAX           DisplayString
    ACCESS           read-only
    STATUS           mandatory
    DESCRIPTION
    "Name of station object."
    ::=   { b14_D64OutputTableEntry 2 }

b14_D64OutputValue    OBJECT-TYPE
    SYNTAX           DisplayString
    ACCESS           read-only
    STATUS           mandatory
    DESCRIPTION
    "Current value of station object. Is read-only ."
    ::=   { b14_D64OutputTableEntry 3 }


-- ***********************************
-- *
-- *  B14_D84
-- *
-- ***********************************
    b14_D84    OBJECT IDENTIFIER ::= { exportTables 119 }

-- ***********************************
-- *
-- *  B14_D84Input table declarations
-- *
-- ***********************************

b14_D84InputTable   OBJECT-TYPE
    SYNTAX                SEQUENCE OF B14_D84InputTableEntry
    ACCESS                not-accessible
    STATUS                mandatory
    DESCRIPTION
    "A list of snmp b14_D84Input (read-only) object values."
    ::=  { b14_D84 1 }

b14_D84InputTableEntry  OBJECT-TYPE
    SYNTAX                B14_D84InputTableEntry
    ACCESS                not-accessible
    STATUS                mandatory
    DESCRIPTION
    "An b14_D84Input table entry containing data for a specific b14_D84Input."
    INDEX  { b14_D84InputIndex }  ::=   { b14_D84InputTable 1 }

B14_D84InputTableEntry ::= SEQUENCE {
        b14_D84InputIndex       INTEGER,
        b14_D84InputName        DisplayString,
        b14_D84InputValue       DisplayString
    }

b14_D84InputIndex   OBJECT-TYPE
    SYNTAX           INTEGER(0..2147483647)
    ACCESS           read-only
    STATUS           mandatory
    DESCRIPTION
    "The index in the b14_D84Input table for a particular snmp b14_D84Input
	 object.  Used to address table entries."
    ::=   { b14_D84InputTableEntry 1 }


b14_D84InputName    OBJECT-TYPE
    SYNTAX           DisplayString
    ACCESS           read-only
    STATUS           mandatory
    DESCRIPTION
    "Name of station object."
    ::=   { b14_D84InputTableEntry 2 }

b14_D84InputValue    OBJECT-TYPE
    SYNTAX           DisplayString
    ACCESS           read-write
    STATUS           mandatory
    DESCRIPTION
    "Current value of station object. Is read-write ."
    ::=   { b14_D84InputTableEntry 3 }



-- ***********************************
-- *
-- *  B14_D84Output table declarations
-- *
-- ***********************************

b14_D84OutputTable   OBJECT-TYPE
    SYNTAX                SEQUENCE OF B14_D84OutputTableEntry
    ACCESS                not-accessible
    STATUS                mandatory
    DESCRIPTION
    "A list of snmp b14_D84Output (read-only) object values."
    ::=  { b14_D84 2 }

b14_D84OutputTableEntry  OBJECT-TYPE
    SYNTAX                B14_D84OutputTableEntry
    ACCESS                not-accessible
    STATUS                mandatory
    DESCRIPTION
    "An b14_D84Output table entry containing data for a specific b14_D84Output."
    INDEX  { b14_D84OutputIndex }  ::=   { b14_D84OutputTable 1 }

B14_D84OutputTableEntry ::= SEQUENCE {
        b14_D84OutputIndex       INTEGER,
        b14_D84OutputName        DisplayString,
        b14_D84OutputValue       DisplayString
    }

b14_D84OutputIndex   OBJECT-TYPE
    SYNTAX           INTEGER(0..2147483647)
    ACCESS           read-only
    STATUS           mandatory
    DESCRIPTION
    "The index in the b14_D84Output table for a particular snmp b14_D84Output
	 object.  Used to address table entries."
    ::=   { b14_D84OutputTableEntry 1 }


b14_D84OutputName    OBJECT-TYPE
    SYNTAX           DisplayString
    ACCESS           read-only
    STATUS           mandatory
    DESCRIPTION
    "Name of station object."
    ::=   { b14_D84OutputTableEntry 2 }

b14_D84OutputValue    OBJECT-TYPE
    SYNTAX           DisplayString
    ACCESS           read-only
    STATUS           mandatory
    DESCRIPTION
    "Current value of station object. Is read-only ."
    ::=   { b14_D84OutputTableEntry 3 }


-- ***********************************
-- *
-- *  B14_D85
-- *
-- ***********************************
    b14_D85    OBJECT IDENTIFIER ::= { exportTables 120 }

-- ***********************************
-- *
-- *  B14_D85Input table declarations
-- *
-- ***********************************

b14_D85InputTable   OBJECT-TYPE
    SYNTAX                SEQUENCE OF B14_D85InputTableEntry
    ACCESS                not-accessible
    STATUS                mandatory
    DESCRIPTION
    "A list of snmp b14_D85Input (read-only) object values."
    ::=  { b14_D85 1 }

b14_D85InputTableEntry  OBJECT-TYPE
    SYNTAX                B14_D85InputTableEntry
    ACCESS                not-accessible
    STATUS                mandatory
    DESCRIPTION
    "An b14_D85Input table entry containing data for a specific b14_D85Input."
    INDEX  { b14_D85InputIndex }  ::=   { b14_D85InputTable 1 }

B14_D85InputTableEntry ::= SEQUENCE {
        b14_D85InputIndex       INTEGER,
        b14_D85InputName        DisplayString,
        b14_D85InputValue       DisplayString
    }

b14_D85InputIndex   OBJECT-TYPE
    SYNTAX           INTEGER(0..2147483647)
    ACCESS           read-only
    STATUS           mandatory
    DESCRIPTION
    "The index in the b14_D85Input table for a particular snmp b14_D85Input
	 object.  Used to address table entries."
    ::=   { b14_D85InputTableEntry 1 }


b14_D85InputName    OBJECT-TYPE
    SYNTAX           DisplayString
    ACCESS           read-only
    STATUS           mandatory
    DESCRIPTION
    "Name of station object."
    ::=   { b14_D85InputTableEntry 2 }

b14_D85InputValue    OBJECT-TYPE
    SYNTAX           DisplayString
    ACCESS           read-write
    STATUS           mandatory
    DESCRIPTION
    "Current value of station object. Is read-write ."
    ::=   { b14_D85InputTableEntry 3 }



-- ***********************************
-- *
-- *  B14_D85Output table declarations
-- *
-- ***********************************

b14_D85OutputTable   OBJECT-TYPE
    SYNTAX                SEQUENCE OF B14_D85OutputTableEntry
    ACCESS                not-accessible
    STATUS                mandatory
    DESCRIPTION
    "A list of snmp b14_D85Output (read-only) object values."
    ::=  { b14_D85 2 }

b14_D85OutputTableEntry  OBJECT-TYPE
    SYNTAX                B14_D85OutputTableEntry
    ACCESS                not-accessible
    STATUS                mandatory
    DESCRIPTION
    "An b14_D85Output table entry containing data for a specific b14_D85Output."
    INDEX  { b14_D85OutputIndex }  ::=   { b14_D85OutputTable 1 }

B14_D85OutputTableEntry ::= SEQUENCE {
        b14_D85OutputIndex       INTEGER,
        b14_D85OutputName        DisplayString,
        b14_D85OutputValue       DisplayString
    }

b14_D85OutputIndex   OBJECT-TYPE
    SYNTAX           INTEGER(0..2147483647)
    ACCESS           read-only
    STATUS           mandatory
    DESCRIPTION
    "The index in the b14_D85Output table for a particular snmp b14_D85Output
	 object.  Used to address table entries."
    ::=   { b14_D85OutputTableEntry 1 }


b14_D85OutputName    OBJECT-TYPE
    SYNTAX           DisplayString
    ACCESS           read-only
    STATUS           mandatory
    DESCRIPTION
    "Name of station object."
    ::=   { b14_D85OutputTableEntry 2 }

b14_D85OutputValue    OBJECT-TYPE
    SYNTAX           DisplayString
    ACCESS           read-only
    STATUS           mandatory
    DESCRIPTION
    "Current value of station object. Is read-only ."
    ::=   { b14_D85OutputTableEntry 3 }


-- ***********************************
-- *
-- *  B14_D103
-- *
-- ***********************************
    b14_D103    OBJECT IDENTIFIER ::= { exportTables 121 }

-- ***********************************
-- *
-- *  B14_D103Input table declarations
-- *
-- ***********************************

b14_D103InputTable   OBJECT-TYPE
    SYNTAX                SEQUENCE OF B14_D103InputTableEntry
    ACCESS                not-accessible
    STATUS                mandatory
    DESCRIPTION
    "A list of snmp b14_D103Input (read-only) object values."
    ::=  { b14_D103 1 }

b14_D103InputTableEntry  OBJECT-TYPE
    SYNTAX                B14_D103InputTableEntry
    ACCESS                not-accessible
    STATUS                mandatory
    DESCRIPTION
    "An b14_D103Input table entry containing data for a specific b14_D103Input."
    INDEX  { b14_D103InputIndex }  ::=   { b14_D103InputTable 1 }

B14_D103InputTableEntry ::= SEQUENCE {
        b14_D103InputIndex       INTEGER,
        b14_D103InputName        DisplayString,
        b14_D103InputValue       DisplayString
    }

b14_D103InputIndex   OBJECT-TYPE
    SYNTAX           INTEGER(0..2147483647)
    ACCESS           read-only
    STATUS           mandatory
    DESCRIPTION
    "The index in the b14_D103Input table for a particular snmp b14_D103Input
	 object.  Used to address table entries."
    ::=   { b14_D103InputTableEntry 1 }


b14_D103InputName    OBJECT-TYPE
    SYNTAX           DisplayString
    ACCESS           read-only
    STATUS           mandatory
    DESCRIPTION
    "Name of station object."
    ::=   { b14_D103InputTableEntry 2 }

b14_D103InputValue    OBJECT-TYPE
    SYNTAX           DisplayString
    ACCESS           read-write
    STATUS           mandatory
    DESCRIPTION
    "Current value of station object. Is read-write ."
    ::=   { b14_D103InputTableEntry 3 }



-- ***********************************
-- *
-- *  B14_D103Output table declarations
-- *
-- ***********************************

b14_D103OutputTable   OBJECT-TYPE
    SYNTAX                SEQUENCE OF B14_D103OutputTableEntry
    ACCESS                not-accessible
    STATUS                mandatory
    DESCRIPTION
    "A list of snmp b14_D103Output (read-only) object values."
    ::=  { b14_D103 2 }

b14_D103OutputTableEntry  OBJECT-TYPE
    SYNTAX                B14_D103OutputTableEntry
    ACCESS                not-accessible
    STATUS                mandatory
    DESCRIPTION
    "An b14_D103Output table entry containing data for a specific b14_D103Output."
    INDEX  { b14_D103OutputIndex }  ::=   { b14_D103OutputTable 1 }

B14_D103OutputTableEntry ::= SEQUENCE {
        b14_D103OutputIndex       INTEGER,
        b14_D103OutputName        DisplayString,
        b14_D103OutputValue       DisplayString
    }

b14_D103OutputIndex   OBJECT-TYPE
    SYNTAX           INTEGER(0..2147483647)
    ACCESS           read-only
    STATUS           mandatory
    DESCRIPTION
    "The index in the b14_D103Output table for a particular snmp b14_D103Output
	 object.  Used to address table entries."
    ::=   { b14_D103OutputTableEntry 1 }


b14_D103OutputName    OBJECT-TYPE
    SYNTAX           DisplayString
    ACCESS           read-only
    STATUS           mandatory
    DESCRIPTION
    "Name of station object."
    ::=   { b14_D103OutputTableEntry 2 }

b14_D103OutputValue    OBJECT-TYPE
    SYNTAX           DisplayString
    ACCESS           read-only
    STATUS           mandatory
    DESCRIPTION
    "Current value of station object. Is read-only ."
    ::=   { b14_D103OutputTableEntry 3 }


-- ***********************************
-- *
-- *  B14_D104
-- *
-- ***********************************
    b14_D104    OBJECT IDENTIFIER ::= { exportTables 122 }

-- ***********************************
-- *
-- *  B14_D104Input table declarations
-- *
-- ***********************************

b14_D104InputTable   OBJECT-TYPE
    SYNTAX                SEQUENCE OF B14_D104InputTableEntry
    ACCESS                not-accessible
    STATUS                mandatory
    DESCRIPTION
    "A list of snmp b14_D104Input (read-only) object values."
    ::=  { b14_D104 1 }

b14_D104InputTableEntry  OBJECT-TYPE
    SYNTAX                B14_D104InputTableEntry
    ACCESS                not-accessible
    STATUS                mandatory
    DESCRIPTION
    "An b14_D104Input table entry containing data for a specific b14_D104Input."
    INDEX  { b14_D104InputIndex }  ::=   { b14_D104InputTable 1 }

B14_D104InputTableEntry ::= SEQUENCE {
        b14_D104InputIndex       INTEGER,
        b14_D104InputName        DisplayString,
        b14_D104InputValue       DisplayString
    }

b14_D104InputIndex   OBJECT-TYPE
    SYNTAX           INTEGER(0..2147483647)
    ACCESS           read-only
    STATUS           mandatory
    DESCRIPTION
    "The index in the b14_D104Input table for a particular snmp b14_D104Input
	 object.  Used to address table entries."
    ::=   { b14_D104InputTableEntry 1 }


b14_D104InputName    OBJECT-TYPE
    SYNTAX           DisplayString
    ACCESS           read-only
    STATUS           mandatory
    DESCRIPTION
    "Name of station object."
    ::=   { b14_D104InputTableEntry 2 }

b14_D104InputValue    OBJECT-TYPE
    SYNTAX           DisplayString
    ACCESS           read-write
    STATUS           mandatory
    DESCRIPTION
    "Current value of station object. Is read-write ."
    ::=   { b14_D104InputTableEntry 3 }



-- ***********************************
-- *
-- *  B14_D104Output table declarations
-- *
-- ***********************************

b14_D104OutputTable   OBJECT-TYPE
    SYNTAX                SEQUENCE OF B14_D104OutputTableEntry
    ACCESS                not-accessible
    STATUS                mandatory
    DESCRIPTION
    "A list of snmp b14_D104Output (read-only) object values."
    ::=  { b14_D104 2 }

b14_D104OutputTableEntry  OBJECT-TYPE
    SYNTAX                B14_D104OutputTableEntry
    ACCESS                not-accessible
    STATUS                mandatory
    DESCRIPTION
    "An b14_D104Output table entry containing data for a specific b14_D104Output."
    INDEX  { b14_D104OutputIndex }  ::=   { b14_D104OutputTable 1 }

B14_D104OutputTableEntry ::= SEQUENCE {
        b14_D104OutputIndex       INTEGER,
        b14_D104OutputName        DisplayString,
        b14_D104OutputValue       DisplayString
    }

b14_D104OutputIndex   OBJECT-TYPE
    SYNTAX           INTEGER(0..2147483647)
    ACCESS           read-only
    STATUS           mandatory
    DESCRIPTION
    "The index in the b14_D104Output table for a particular snmp b14_D104Output
	 object.  Used to address table entries."
    ::=   { b14_D104OutputTableEntry 1 }


b14_D104OutputName    OBJECT-TYPE
    SYNTAX           DisplayString
    ACCESS           read-only
    STATUS           mandatory
    DESCRIPTION
    "Name of station object."
    ::=   { b14_D104OutputTableEntry 2 }

b14_D104OutputValue    OBJECT-TYPE
    SYNTAX           DisplayString
    ACCESS           read-only
    STATUS           mandatory
    DESCRIPTION
    "Current value of station object. Is read-only ."
    ::=   { b14_D104OutputTableEntry 3 }


-- ***********************************
-- *
-- *  B14_D109
-- *
-- ***********************************
    b14_D109    OBJECT IDENTIFIER ::= { exportTables 123 }

-- ***********************************
-- *
-- *  B14_D109Input table declarations
-- *
-- ***********************************

b14_D109InputTable   OBJECT-TYPE
    SYNTAX                SEQUENCE OF B14_D109InputTableEntry
    ACCESS                not-accessible
    STATUS                mandatory
    DESCRIPTION
    "A list of snmp b14_D109Input (read-only) object values."
    ::=  { b14_D109 1 }

b14_D109InputTableEntry  OBJECT-TYPE
    SYNTAX                B14_D109InputTableEntry
    ACCESS                not-accessible
    STATUS                mandatory
    DESCRIPTION
    "An b14_D109Input table entry containing data for a specific b14_D109Input."
    INDEX  { b14_D109InputIndex }  ::=   { b14_D109InputTable 1 }

B14_D109InputTableEntry ::= SEQUENCE {
        b14_D109InputIndex       INTEGER,
        b14_D109InputName        DisplayString,
        b14_D109InputValue       DisplayString
    }

b14_D109InputIndex   OBJECT-TYPE
    SYNTAX           INTEGER(0..2147483647)
    ACCESS           read-only
    STATUS           mandatory
    DESCRIPTION
    "The index in the b14_D109Input table for a particular snmp b14_D109Input
	 object.  Used to address table entries."
    ::=   { b14_D109InputTableEntry 1 }


b14_D109InputName    OBJECT-TYPE
    SYNTAX           DisplayString
    ACCESS           read-only
    STATUS           mandatory
    DESCRIPTION
    "Name of station object."
    ::=   { b14_D109InputTableEntry 2 }

b14_D109InputValue    OBJECT-TYPE
    SYNTAX           DisplayString
    ACCESS           read-write
    STATUS           mandatory
    DESCRIPTION
    "Current value of station object. Is read-write ."
    ::=   { b14_D109InputTableEntry 3 }



-- ***********************************
-- *
-- *  B14_D109Output table declarations
-- *
-- ***********************************

b14_D109OutputTable   OBJECT-TYPE
    SYNTAX                SEQUENCE OF B14_D109OutputTableEntry
    ACCESS                not-accessible
    STATUS                mandatory
    DESCRIPTION
    "A list of snmp b14_D109Output (read-only) object values."
    ::=  { b14_D109 2 }

b14_D109OutputTableEntry  OBJECT-TYPE
    SYNTAX                B14_D109OutputTableEntry
    ACCESS                not-accessible
    STATUS                mandatory
    DESCRIPTION
    "An b14_D109Output table entry containing data for a specific b14_D109Output."
    INDEX  { b14_D109OutputIndex }  ::=   { b14_D109OutputTable 1 }

B14_D109OutputTableEntry ::= SEQUENCE {
        b14_D109OutputIndex       INTEGER,
        b14_D109OutputName        DisplayString,
        b14_D109OutputValue       DisplayString
    }

b14_D109OutputIndex   OBJECT-TYPE
    SYNTAX           INTEGER(0..2147483647)
    ACCESS           read-only
    STATUS           mandatory
    DESCRIPTION
    "The index in the b14_D109Output table for a particular snmp b14_D109Output
	 object.  Used to address table entries."
    ::=   { b14_D109OutputTableEntry 1 }


b14_D109OutputName    OBJECT-TYPE
    SYNTAX           DisplayString
    ACCESS           read-only
    STATUS           mandatory
    DESCRIPTION
    "Name of station object."
    ::=   { b14_D109OutputTableEntry 2 }

b14_D109OutputValue    OBJECT-TYPE
    SYNTAX           DisplayString
    ACCESS           read-only
    STATUS           mandatory
    DESCRIPTION
    "Current value of station object. Is read-only ."
    ::=   { b14_D109OutputTableEntry 3 }


-- ***********************************
-- *
-- *  B14_D115
-- *
-- ***********************************
    b14_D115    OBJECT IDENTIFIER ::= { exportTables 124 }

-- ***********************************
-- *
-- *  B14_D115Input table declarations
-- *
-- ***********************************

b14_D115InputTable   OBJECT-TYPE
    SYNTAX                SEQUENCE OF B14_D115InputTableEntry
    ACCESS                not-accessible
    STATUS                mandatory
    DESCRIPTION
    "A list of snmp b14_D115Input (read-only) object values."
    ::=  { b14_D115 1 }

b14_D115InputTableEntry  OBJECT-TYPE
    SYNTAX                B14_D115InputTableEntry
    ACCESS                not-accessible
    STATUS                mandatory
    DESCRIPTION
    "An b14_D115Input table entry containing data for a specific b14_D115Input."
    INDEX  { b14_D115InputIndex }  ::=   { b14_D115InputTable 1 }

B14_D115InputTableEntry ::= SEQUENCE {
        b14_D115InputIndex       INTEGER,
        b14_D115InputName        DisplayString,
        b14_D115InputValue       DisplayString
    }

b14_D115InputIndex   OBJECT-TYPE
    SYNTAX           INTEGER(0..2147483647)
    ACCESS           read-only
    STATUS           mandatory
    DESCRIPTION
    "The index in the b14_D115Input table for a particular snmp b14_D115Input
	 object.  Used to address table entries."
    ::=   { b14_D115InputTableEntry 1 }


b14_D115InputName    OBJECT-TYPE
    SYNTAX           DisplayString
    ACCESS           read-only
    STATUS           mandatory
    DESCRIPTION
    "Name of station object."
    ::=   { b14_D115InputTableEntry 2 }

b14_D115InputValue    OBJECT-TYPE
    SYNTAX           DisplayString
    ACCESS           read-write
    STATUS           mandatory
    DESCRIPTION
    "Current value of station object. Is read-write ."
    ::=   { b14_D115InputTableEntry 3 }



-- ***********************************
-- *
-- *  B14_D115Output table declarations
-- *
-- ***********************************

b14_D115OutputTable   OBJECT-TYPE
    SYNTAX                SEQUENCE OF B14_D115OutputTableEntry
    ACCESS                not-accessible
    STATUS                mandatory
    DESCRIPTION
    "A list of snmp b14_D115Output (read-only) object values."
    ::=  { b14_D115 2 }

b14_D115OutputTableEntry  OBJECT-TYPE
    SYNTAX                B14_D115OutputTableEntry
    ACCESS                not-accessible
    STATUS                mandatory
    DESCRIPTION
    "An b14_D115Output table entry containing data for a specific b14_D115Output."
    INDEX  { b14_D115OutputIndex }  ::=   { b14_D115OutputTable 1 }

B14_D115OutputTableEntry ::= SEQUENCE {
        b14_D115OutputIndex       INTEGER,
        b14_D115OutputName        DisplayString,
        b14_D115OutputValue       DisplayString
    }

b14_D115OutputIndex   OBJECT-TYPE
    SYNTAX           INTEGER(0..2147483647)
    ACCESS           read-only
    STATUS           mandatory
    DESCRIPTION
    "The index in the b14_D115Output table for a particular snmp b14_D115Output
	 object.  Used to address table entries."
    ::=   { b14_D115OutputTableEntry 1 }


b14_D115OutputName    OBJECT-TYPE
    SYNTAX           DisplayString
    ACCESS           read-only
    STATUS           mandatory
    DESCRIPTION
    "Name of station object."
    ::=   { b14_D115OutputTableEntry 2 }

b14_D115OutputValue    OBJECT-TYPE
    SYNTAX           DisplayString
    ACCESS           read-only
    STATUS           mandatory
    DESCRIPTION
    "Current value of station object. Is read-only ."
    ::=   { b14_D115OutputTableEntry 3 }


-- ***********************************
-- *
-- *  B14_D59
-- *
-- ***********************************
    b14_D59    OBJECT IDENTIFIER ::= { exportTables 125 }

-- ***********************************
-- *
-- *  B14_D59Input table declarations
-- *
-- ***********************************

b14_D59InputTable   OBJECT-TYPE
    SYNTAX                SEQUENCE OF B14_D59InputTableEntry
    ACCESS                not-accessible
    STATUS                mandatory
    DESCRIPTION
    "A list of snmp b14_D59Input (read-only) object values."
    ::=  { b14_D59 1 }

b14_D59InputTableEntry  OBJECT-TYPE
    SYNTAX                B14_D59InputTableEntry
    ACCESS                not-accessible
    STATUS                mandatory
    DESCRIPTION
    "An b14_D59Input table entry containing data for a specific b14_D59Input."
    INDEX  { b14_D59InputIndex }  ::=   { b14_D59InputTable 1 }

B14_D59InputTableEntry ::= SEQUENCE {
        b14_D59InputIndex       INTEGER,
        b14_D59InputName        DisplayString,
        b14_D59InputValue       DisplayString
    }

b14_D59InputIndex   OBJECT-TYPE
    SYNTAX           INTEGER(0..2147483647)
    ACCESS           read-only
    STATUS           mandatory
    DESCRIPTION
    "The index in the b14_D59Input table for a particular snmp b14_D59Input
	 object.  Used to address table entries."
    ::=   { b14_D59InputTableEntry 1 }


b14_D59InputName    OBJECT-TYPE
    SYNTAX           DisplayString
    ACCESS           read-only
    STATUS           mandatory
    DESCRIPTION
    "Name of station object."
    ::=   { b14_D59InputTableEntry 2 }

b14_D59InputValue    OBJECT-TYPE
    SYNTAX           DisplayString
    ACCESS           read-write
    STATUS           mandatory
    DESCRIPTION
    "Current value of station object. Is read-write ."
    ::=   { b14_D59InputTableEntry 3 }



-- ***********************************
-- *
-- *  B14_D59Output table declarations
-- *
-- ***********************************

b14_D59OutputTable   OBJECT-TYPE
    SYNTAX                SEQUENCE OF B14_D59OutputTableEntry
    ACCESS                not-accessible
    STATUS                mandatory
    DESCRIPTION
    "A list of snmp b14_D59Output (read-only) object values."
    ::=  { b14_D59 2 }

b14_D59OutputTableEntry  OBJECT-TYPE
    SYNTAX                B14_D59OutputTableEntry
    ACCESS                not-accessible
    STATUS                mandatory
    DESCRIPTION
    "An b14_D59Output table entry containing data for a specific b14_D59Output."
    INDEX  { b14_D59OutputIndex }  ::=   { b14_D59OutputTable 1 }

B14_D59OutputTableEntry ::= SEQUENCE {
        b14_D59OutputIndex       INTEGER,
        b14_D59OutputName        DisplayString,
        b14_D59OutputValue       DisplayString
    }

b14_D59OutputIndex   OBJECT-TYPE
    SYNTAX           INTEGER(0..2147483647)
    ACCESS           read-only
    STATUS           mandatory
    DESCRIPTION
    "The index in the b14_D59Output table for a particular snmp b14_D59Output
	 object.  Used to address table entries."
    ::=   { b14_D59OutputTableEntry 1 }


b14_D59OutputName    OBJECT-TYPE
    SYNTAX           DisplayString
    ACCESS           read-only
    STATUS           mandatory
    DESCRIPTION
    "Name of station object."
    ::=   { b14_D59OutputTableEntry 2 }

b14_D59OutputValue    OBJECT-TYPE
    SYNTAX           DisplayString
    ACCESS           read-only
    STATUS           mandatory
    DESCRIPTION
    "Current value of station object. Is read-only ."
    ::=   { b14_D59OutputTableEntry 3 }


-- ***********************************
-- *
-- *  B14_D111
-- *
-- ***********************************
    b14_D111    OBJECT IDENTIFIER ::= { exportTables 126 }

-- ***********************************
-- *
-- *  B14_D111Input table declarations
-- *
-- ***********************************

b14_D111InputTable   OBJECT-TYPE
    SYNTAX                SEQUENCE OF B14_D111InputTableEntry
    ACCESS                not-accessible
    STATUS                mandatory
    DESCRIPTION
    "A list of snmp b14_D111Input (read-only) object values."
    ::=  { b14_D111 1 }

b14_D111InputTableEntry  OBJECT-TYPE
    SYNTAX                B14_D111InputTableEntry
    ACCESS                not-accessible
    STATUS                mandatory
    DESCRIPTION
    "An b14_D111Input table entry containing data for a specific b14_D111Input."
    INDEX  { b14_D111InputIndex }  ::=   { b14_D111InputTable 1 }

B14_D111InputTableEntry ::= SEQUENCE {
        b14_D111InputIndex       INTEGER,
        b14_D111InputName        DisplayString,
        b14_D111InputValue       DisplayString
    }

b14_D111InputIndex   OBJECT-TYPE
    SYNTAX           INTEGER(0..2147483647)
    ACCESS           read-only
    STATUS           mandatory
    DESCRIPTION
    "The index in the b14_D111Input table for a particular snmp b14_D111Input
	 object.  Used to address table entries."
    ::=   { b14_D111InputTableEntry 1 }


b14_D111InputName    OBJECT-TYPE
    SYNTAX           DisplayString
    ACCESS           read-only
    STATUS           mandatory
    DESCRIPTION
    "Name of station object."
    ::=   { b14_D111InputTableEntry 2 }

b14_D111InputValue    OBJECT-TYPE
    SYNTAX           DisplayString
    ACCESS           read-write
    STATUS           mandatory
    DESCRIPTION
    "Current value of station object. Is read-write ."
    ::=   { b14_D111InputTableEntry 3 }



-- ***********************************
-- *
-- *  B14_D111Output table declarations
-- *
-- ***********************************

b14_D111OutputTable   OBJECT-TYPE
    SYNTAX                SEQUENCE OF B14_D111OutputTableEntry
    ACCESS                not-accessible
    STATUS                mandatory
    DESCRIPTION
    "A list of snmp b14_D111Output (read-only) object values."
    ::=  { b14_D111 2 }

b14_D111OutputTableEntry  OBJECT-TYPE
    SYNTAX                B14_D111OutputTableEntry
    ACCESS                not-accessible
    STATUS                mandatory
    DESCRIPTION
    "An b14_D111Output table entry containing data for a specific b14_D111Output."
    INDEX  { b14_D111OutputIndex }  ::=   { b14_D111OutputTable 1 }

B14_D111OutputTableEntry ::= SEQUENCE {
        b14_D111OutputIndex       INTEGER,
        b14_D111OutputName        DisplayString,
        b14_D111OutputValue       DisplayString
    }

b14_D111OutputIndex   OBJECT-TYPE
    SYNTAX           INTEGER(0..2147483647)
    ACCESS           read-only
    STATUS           mandatory
    DESCRIPTION
    "The index in the b14_D111Output table for a particular snmp b14_D111Output
	 object.  Used to address table entries."
    ::=   { b14_D111OutputTableEntry 1 }


b14_D111OutputName    OBJECT-TYPE
    SYNTAX           DisplayString
    ACCESS           read-only
    STATUS           mandatory
    DESCRIPTION
    "Name of station object."
    ::=   { b14_D111OutputTableEntry 2 }

b14_D111OutputValue    OBJECT-TYPE
    SYNTAX           DisplayString
    ACCESS           read-only
    STATUS           mandatory
    DESCRIPTION
    "Current value of station object. Is read-only ."
    ::=   { b14_D111OutputTableEntry 3 }


-- ***********************************
-- *
-- *  B14_D117
-- *
-- ***********************************
    b14_D117    OBJECT IDENTIFIER ::= { exportTables 127 }

-- ***********************************
-- *
-- *  B14_D117Input table declarations
-- *
-- ***********************************

b14_D117InputTable   OBJECT-TYPE
    SYNTAX                SEQUENCE OF B14_D117InputTableEntry
    ACCESS                not-accessible
    STATUS                mandatory
    DESCRIPTION
    "A list of snmp b14_D117Input (read-only) object values."
    ::=  { b14_D117 1 }

b14_D117InputTableEntry  OBJECT-TYPE
    SYNTAX                B14_D117InputTableEntry
    ACCESS                not-accessible
    STATUS                mandatory
    DESCRIPTION
    "An b14_D117Input table entry containing data for a specific b14_D117Input."
    INDEX  { b14_D117InputIndex }  ::=   { b14_D117InputTable 1 }

B14_D117InputTableEntry ::= SEQUENCE {
        b14_D117InputIndex       INTEGER,
        b14_D117InputName        DisplayString,
        b14_D117InputValue       DisplayString
    }

b14_D117InputIndex   OBJECT-TYPE
    SYNTAX           INTEGER(0..2147483647)
    ACCESS           read-only
    STATUS           mandatory
    DESCRIPTION
    "The index in the b14_D117Input table for a particular snmp b14_D117Input
	 object.  Used to address table entries."
    ::=   { b14_D117InputTableEntry 1 }


b14_D117InputName    OBJECT-TYPE
    SYNTAX           DisplayString
    ACCESS           read-only
    STATUS           mandatory
    DESCRIPTION
    "Name of station object."
    ::=   { b14_D117InputTableEntry 2 }

b14_D117InputValue    OBJECT-TYPE
    SYNTAX           DisplayString
    ACCESS           read-write
    STATUS           mandatory
    DESCRIPTION
    "Current value of station object. Is read-write ."
    ::=   { b14_D117InputTableEntry 3 }



-- ***********************************
-- *
-- *  B14_D117Output table declarations
-- *
-- ***********************************

b14_D117OutputTable   OBJECT-TYPE
    SYNTAX                SEQUENCE OF B14_D117OutputTableEntry
    ACCESS                not-accessible
    STATUS                mandatory
    DESCRIPTION
    "A list of snmp b14_D117Output (read-only) object values."
    ::=  { b14_D117 2 }

b14_D117OutputTableEntry  OBJECT-TYPE
    SYNTAX                B14_D117OutputTableEntry
    ACCESS                not-accessible
    STATUS                mandatory
    DESCRIPTION
    "An b14_D117Output table entry containing data for a specific b14_D117Output."
    INDEX  { b14_D117OutputIndex }  ::=   { b14_D117OutputTable 1 }

B14_D117OutputTableEntry ::= SEQUENCE {
        b14_D117OutputIndex       INTEGER,
        b14_D117OutputName        DisplayString,
        b14_D117OutputValue       DisplayString
    }

b14_D117OutputIndex   OBJECT-TYPE
    SYNTAX           INTEGER(0..2147483647)
    ACCESS           read-only
    STATUS           mandatory
    DESCRIPTION
    "The index in the b14_D117Output table for a particular snmp b14_D117Output
	 object.  Used to address table entries."
    ::=   { b14_D117OutputTableEntry 1 }


b14_D117OutputName    OBJECT-TYPE
    SYNTAX           DisplayString
    ACCESS           read-only
    STATUS           mandatory
    DESCRIPTION
    "Name of station object."
    ::=   { b14_D117OutputTableEntry 2 }

b14_D117OutputValue    OBJECT-TYPE
    SYNTAX           DisplayString
    ACCESS           read-only
    STATUS           mandatory
    DESCRIPTION
    "Current value of station object. Is read-only ."
    ::=   { b14_D117OutputTableEntry 3 }


-- ***********************************
-- *
-- *  B14_D108
-- *
-- ***********************************
    b14_D108    OBJECT IDENTIFIER ::= { exportTables 128 }

-- ***********************************
-- *
-- *  B14_D108Input table declarations
-- *
-- ***********************************

b14_D108InputTable   OBJECT-TYPE
    SYNTAX                SEQUENCE OF B14_D108InputTableEntry
    ACCESS                not-accessible
    STATUS                mandatory
    DESCRIPTION
    "A list of snmp b14_D108Input (read-only) object values."
    ::=  { b14_D108 1 }

b14_D108InputTableEntry  OBJECT-TYPE
    SYNTAX                B14_D108InputTableEntry
    ACCESS                not-accessible
    STATUS                mandatory
    DESCRIPTION
    "An b14_D108Input table entry containing data for a specific b14_D108Input."
    INDEX  { b14_D108InputIndex }  ::=   { b14_D108InputTable 1 }

B14_D108InputTableEntry ::= SEQUENCE {
        b14_D108InputIndex       INTEGER,
        b14_D108InputName        DisplayString,
        b14_D108InputValue       DisplayString
    }

b14_D108InputIndex   OBJECT-TYPE
    SYNTAX           INTEGER(0..2147483647)
    ACCESS           read-only
    STATUS           mandatory
    DESCRIPTION
    "The index in the b14_D108Input table for a particular snmp b14_D108Input
	 object.  Used to address table entries."
    ::=   { b14_D108InputTableEntry 1 }


b14_D108InputName    OBJECT-TYPE
    SYNTAX           DisplayString
    ACCESS           read-only
    STATUS           mandatory
    DESCRIPTION
    "Name of station object."
    ::=   { b14_D108InputTableEntry 2 }

b14_D108InputValue    OBJECT-TYPE
    SYNTAX           DisplayString
    ACCESS           read-write
    STATUS           mandatory
    DESCRIPTION
    "Current value of station object. Is read-write ."
    ::=   { b14_D108InputTableEntry 3 }



-- ***********************************
-- *
-- *  B14_D108Output table declarations
-- *
-- ***********************************

b14_D108OutputTable   OBJECT-TYPE
    SYNTAX                SEQUENCE OF B14_D108OutputTableEntry
    ACCESS                not-accessible
    STATUS                mandatory
    DESCRIPTION
    "A list of snmp b14_D108Output (read-only) object values."
    ::=  { b14_D108 2 }

b14_D108OutputTableEntry  OBJECT-TYPE
    SYNTAX                B14_D108OutputTableEntry
    ACCESS                not-accessible
    STATUS                mandatory
    DESCRIPTION
    "An b14_D108Output table entry containing data for a specific b14_D108Output."
    INDEX  { b14_D108OutputIndex }  ::=   { b14_D108OutputTable 1 }

B14_D108OutputTableEntry ::= SEQUENCE {
        b14_D108OutputIndex       INTEGER,
        b14_D108OutputName        DisplayString,
        b14_D108OutputValue       DisplayString
    }

b14_D108OutputIndex   OBJECT-TYPE
    SYNTAX           INTEGER(0..2147483647)
    ACCESS           read-only
    STATUS           mandatory
    DESCRIPTION
    "The index in the b14_D108Output table for a particular snmp b14_D108Output
	 object.  Used to address table entries."
    ::=   { b14_D108OutputTableEntry 1 }


b14_D108OutputName    OBJECT-TYPE
    SYNTAX           DisplayString
    ACCESS           read-only
    STATUS           mandatory
    DESCRIPTION
    "Name of station object."
    ::=   { b14_D108OutputTableEntry 2 }

b14_D108OutputValue    OBJECT-TYPE
    SYNTAX           DisplayString
    ACCESS           read-only
    STATUS           mandatory
    DESCRIPTION
    "Current value of station object. Is read-only ."
    ::=   { b14_D108OutputTableEntry 3 }


-- ***********************************
-- *
-- *  B14_D116
-- *
-- ***********************************
    b14_D116    OBJECT IDENTIFIER ::= { exportTables 129 }

-- ***********************************
-- *
-- *  B14_D116Input table declarations
-- *
-- ***********************************

b14_D116InputTable   OBJECT-TYPE
    SYNTAX                SEQUENCE OF B14_D116InputTableEntry
    ACCESS                not-accessible
    STATUS                mandatory
    DESCRIPTION
    "A list of snmp b14_D116Input (read-only) object values."
    ::=  { b14_D116 1 }

b14_D116InputTableEntry  OBJECT-TYPE
    SYNTAX                B14_D116InputTableEntry
    ACCESS                not-accessible
    STATUS                mandatory
    DESCRIPTION
    "An b14_D116Input table entry containing data for a specific b14_D116Input."
    INDEX  { b14_D116InputIndex }  ::=   { b14_D116InputTable 1 }

B14_D116InputTableEntry ::= SEQUENCE {
        b14_D116InputIndex       INTEGER,
        b14_D116InputName        DisplayString,
        b14_D116InputValue       DisplayString
    }

b14_D116InputIndex   OBJECT-TYPE
    SYNTAX           INTEGER(0..2147483647)
    ACCESS           read-only
    STATUS           mandatory
    DESCRIPTION
    "The index in the b14_D116Input table for a particular snmp b14_D116Input
	 object.  Used to address table entries."
    ::=   { b14_D116InputTableEntry 1 }


b14_D116InputName    OBJECT-TYPE
    SYNTAX           DisplayString
    ACCESS           read-only
    STATUS           mandatory
    DESCRIPTION
    "Name of station object."
    ::=   { b14_D116InputTableEntry 2 }

b14_D116InputValue    OBJECT-TYPE
    SYNTAX           DisplayString
    ACCESS           read-write
    STATUS           mandatory
    DESCRIPTION
    "Current value of station object. Is read-write ."
    ::=   { b14_D116InputTableEntry 3 }



-- ***********************************
-- *
-- *  B14_D116Output table declarations
-- *
-- ***********************************

b14_D116OutputTable   OBJECT-TYPE
    SYNTAX                SEQUENCE OF B14_D116OutputTableEntry
    ACCESS                not-accessible
    STATUS                mandatory
    DESCRIPTION
    "A list of snmp b14_D116Output (read-only) object values."
    ::=  { b14_D116 2 }

b14_D116OutputTableEntry  OBJECT-TYPE
    SYNTAX                B14_D116OutputTableEntry
    ACCESS                not-accessible
    STATUS                mandatory
    DESCRIPTION
    "An b14_D116Output table entry containing data for a specific b14_D116Output."
    INDEX  { b14_D116OutputIndex }  ::=   { b14_D116OutputTable 1 }

B14_D116OutputTableEntry ::= SEQUENCE {
        b14_D116OutputIndex       INTEGER,
        b14_D116OutputName        DisplayString,
        b14_D116OutputValue       DisplayString
    }

b14_D116OutputIndex   OBJECT-TYPE
    SYNTAX           INTEGER(0..2147483647)
    ACCESS           read-only
    STATUS           mandatory
    DESCRIPTION
    "The index in the b14_D116Output table for a particular snmp b14_D116Output
	 object.  Used to address table entries."
    ::=   { b14_D116OutputTableEntry 1 }


b14_D116OutputName    OBJECT-TYPE
    SYNTAX           DisplayString
    ACCESS           read-only
    STATUS           mandatory
    DESCRIPTION
    "Name of station object."
    ::=   { b14_D116OutputTableEntry 2 }

b14_D116OutputValue    OBJECT-TYPE
    SYNTAX           DisplayString
    ACCESS           read-only
    STATUS           mandatory
    DESCRIPTION
    "Current value of station object. Is read-only ."
    ::=   { b14_D116OutputTableEntry 3 }


-- ***********************************
-- *
-- *  B14_D107
-- *
-- ***********************************
    b14_D107    OBJECT IDENTIFIER ::= { exportTables 130 }

-- ***********************************
-- *
-- *  B14_D107Input table declarations
-- *
-- ***********************************

b14_D107InputTable   OBJECT-TYPE
    SYNTAX                SEQUENCE OF B14_D107InputTableEntry
    ACCESS                not-accessible
    STATUS                mandatory
    DESCRIPTION
    "A list of snmp b14_D107Input (read-only) object values."
    ::=  { b14_D107 1 }

b14_D107InputTableEntry  OBJECT-TYPE
    SYNTAX                B14_D107InputTableEntry
    ACCESS                not-accessible
    STATUS                mandatory
    DESCRIPTION
    "An b14_D107Input table entry containing data for a specific b14_D107Input."
    INDEX  { b14_D107InputIndex }  ::=   { b14_D107InputTable 1 }

B14_D107InputTableEntry ::= SEQUENCE {
        b14_D107InputIndex       INTEGER,
        b14_D107InputName        DisplayString,
        b14_D107InputValue       DisplayString
    }

b14_D107InputIndex   OBJECT-TYPE
    SYNTAX           INTEGER(0..2147483647)
    ACCESS           read-only
    STATUS           mandatory
    DESCRIPTION
    "The index in the b14_D107Input table for a particular snmp b14_D107Input
	 object.  Used to address table entries."
    ::=   { b14_D107InputTableEntry 1 }


b14_D107InputName    OBJECT-TYPE
    SYNTAX           DisplayString
    ACCESS           read-only
    STATUS           mandatory
    DESCRIPTION
    "Name of station object."
    ::=   { b14_D107InputTableEntry 2 }

b14_D107InputValue    OBJECT-TYPE
    SYNTAX           DisplayString
    ACCESS           read-write
    STATUS           mandatory
    DESCRIPTION
    "Current value of station object. Is read-write ."
    ::=   { b14_D107InputTableEntry 3 }



-- ***********************************
-- *
-- *  B14_D107Output table declarations
-- *
-- ***********************************

b14_D107OutputTable   OBJECT-TYPE
    SYNTAX                SEQUENCE OF B14_D107OutputTableEntry
    ACCESS                not-accessible
    STATUS                mandatory
    DESCRIPTION
    "A list of snmp b14_D107Output (read-only) object values."
    ::=  { b14_D107 2 }

b14_D107OutputTableEntry  OBJECT-TYPE
    SYNTAX                B14_D107OutputTableEntry
    ACCESS                not-accessible
    STATUS                mandatory
    DESCRIPTION
    "An b14_D107Output table entry containing data for a specific b14_D107Output."
    INDEX  { b14_D107OutputIndex }  ::=   { b14_D107OutputTable 1 }

B14_D107OutputTableEntry ::= SEQUENCE {
        b14_D107OutputIndex       INTEGER,
        b14_D107OutputName        DisplayString,
        b14_D107OutputValue       DisplayString
    }

b14_D107OutputIndex   OBJECT-TYPE
    SYNTAX           INTEGER(0..2147483647)
    ACCESS           read-only
    STATUS           mandatory
    DESCRIPTION
    "The index in the b14_D107Output table for a particular snmp b14_D107Output
	 object.  Used to address table entries."
    ::=   { b14_D107OutputTableEntry 1 }


b14_D107OutputName    OBJECT-TYPE
    SYNTAX           DisplayString
    ACCESS           read-only
    STATUS           mandatory
    DESCRIPTION
    "Name of station object."
    ::=   { b14_D107OutputTableEntry 2 }

b14_D107OutputValue    OBJECT-TYPE
    SYNTAX           DisplayString
    ACCESS           read-only
    STATUS           mandatory
    DESCRIPTION
    "Current value of station object. Is read-only ."
    ::=   { b14_D107OutputTableEntry 3 }


-- ***********************************
-- *
-- *  B14_D110
-- *
-- ***********************************
    b14_D110    OBJECT IDENTIFIER ::= { exportTables 131 }

-- ***********************************
-- *
-- *  B14_D110Input table declarations
-- *
-- ***********************************

b14_D110InputTable   OBJECT-TYPE
    SYNTAX                SEQUENCE OF B14_D110InputTableEntry
    ACCESS                not-accessible
    STATUS                mandatory
    DESCRIPTION
    "A list of snmp b14_D110Input (read-only) object values."
    ::=  { b14_D110 1 }

b14_D110InputTableEntry  OBJECT-TYPE
    SYNTAX                B14_D110InputTableEntry
    ACCESS                not-accessible
    STATUS                mandatory
    DESCRIPTION
    "An b14_D110Input table entry containing data for a specific b14_D110Input."
    INDEX  { b14_D110InputIndex }  ::=   { b14_D110InputTable 1 }

B14_D110InputTableEntry ::= SEQUENCE {
        b14_D110InputIndex       INTEGER,
        b14_D110InputName        DisplayString,
        b14_D110InputValue       DisplayString
    }

b14_D110InputIndex   OBJECT-TYPE
    SYNTAX           INTEGER(0..2147483647)
    ACCESS           read-only
    STATUS           mandatory
    DESCRIPTION
    "The index in the b14_D110Input table for a particular snmp b14_D110Input
	 object.  Used to address table entries."
    ::=   { b14_D110InputTableEntry 1 }


b14_D110InputName    OBJECT-TYPE
    SYNTAX           DisplayString
    ACCESS           read-only
    STATUS           mandatory
    DESCRIPTION
    "Name of station object."
    ::=   { b14_D110InputTableEntry 2 }

b14_D110InputValue    OBJECT-TYPE
    SYNTAX           DisplayString
    ACCESS           read-write
    STATUS           mandatory
    DESCRIPTION
    "Current value of station object. Is read-write ."
    ::=   { b14_D110InputTableEntry 3 }



-- ***********************************
-- *
-- *  B14_D110Output table declarations
-- *
-- ***********************************

b14_D110OutputTable   OBJECT-TYPE
    SYNTAX                SEQUENCE OF B14_D110OutputTableEntry
    ACCESS                not-accessible
    STATUS                mandatory
    DESCRIPTION
    "A list of snmp b14_D110Output (read-only) object values."
    ::=  { b14_D110 2 }

b14_D110OutputTableEntry  OBJECT-TYPE
    SYNTAX                B14_D110OutputTableEntry
    ACCESS                not-accessible
    STATUS                mandatory
    DESCRIPTION
    "An b14_D110Output table entry containing data for a specific b14_D110Output."
    INDEX  { b14_D110OutputIndex }  ::=   { b14_D110OutputTable 1 }

B14_D110OutputTableEntry ::= SEQUENCE {
        b14_D110OutputIndex       INTEGER,
        b14_D110OutputName        DisplayString,
        b14_D110OutputValue       DisplayString
    }

b14_D110OutputIndex   OBJECT-TYPE
    SYNTAX           INTEGER(0..2147483647)
    ACCESS           read-only
    STATUS           mandatory
    DESCRIPTION
    "The index in the b14_D110Output table for a particular snmp b14_D110Output
	 object.  Used to address table entries."
    ::=   { b14_D110OutputTableEntry 1 }


b14_D110OutputName    OBJECT-TYPE
    SYNTAX           DisplayString
    ACCESS           read-only
    STATUS           mandatory
    DESCRIPTION
    "Name of station object."
    ::=   { b14_D110OutputTableEntry 2 }

b14_D110OutputValue    OBJECT-TYPE
    SYNTAX           DisplayString
    ACCESS           read-only
    STATUS           mandatory
    DESCRIPTION
    "Current value of station object. Is read-only ."
    ::=   { b14_D110OutputTableEntry 3 }


-- ***********************************
-- *
-- *  B14_D114
-- *
-- ***********************************
    b14_D114    OBJECT IDENTIFIER ::= { exportTables 132 }

-- ***********************************
-- *
-- *  B14_D114Input table declarations
-- *
-- ***********************************

b14_D114InputTable   OBJECT-TYPE
    SYNTAX                SEQUENCE OF B14_D114InputTableEntry
    ACCESS                not-accessible
    STATUS                mandatory
    DESCRIPTION
    "A list of snmp b14_D114Input (read-only) object values."
    ::=  { b14_D114 1 }

b14_D114InputTableEntry  OBJECT-TYPE
    SYNTAX                B14_D114InputTableEntry
    ACCESS                not-accessible
    STATUS                mandatory
    DESCRIPTION
    "An b14_D114Input table entry containing data for a specific b14_D114Input."
    INDEX  { b14_D114InputIndex }  ::=   { b14_D114InputTable 1 }

B14_D114InputTableEntry ::= SEQUENCE {
        b14_D114InputIndex       INTEGER,
        b14_D114InputName        DisplayString,
        b14_D114InputValue       DisplayString
    }

b14_D114InputIndex   OBJECT-TYPE
    SYNTAX           INTEGER(0..2147483647)
    ACCESS           read-only
    STATUS           mandatory
    DESCRIPTION
    "The index in the b14_D114Input table for a particular snmp b14_D114Input
	 object.  Used to address table entries."
    ::=   { b14_D114InputTableEntry 1 }


b14_D114InputName    OBJECT-TYPE
    SYNTAX           DisplayString
    ACCESS           read-only
    STATUS           mandatory
    DESCRIPTION
    "Name of station object."
    ::=   { b14_D114InputTableEntry 2 }

b14_D114InputValue    OBJECT-TYPE
    SYNTAX           DisplayString
    ACCESS           read-write
    STATUS           mandatory
    DESCRIPTION
    "Current value of station object. Is read-write ."
    ::=   { b14_D114InputTableEntry 3 }



-- ***********************************
-- *
-- *  B14_D114Output table declarations
-- *
-- ***********************************

b14_D114OutputTable   OBJECT-TYPE
    SYNTAX                SEQUENCE OF B14_D114OutputTableEntry
    ACCESS                not-accessible
    STATUS                mandatory
    DESCRIPTION
    "A list of snmp b14_D114Output (read-only) object values."
    ::=  { b14_D114 2 }

b14_D114OutputTableEntry  OBJECT-TYPE
    SYNTAX                B14_D114OutputTableEntry
    ACCESS                not-accessible
    STATUS                mandatory
    DESCRIPTION
    "An b14_D114Output table entry containing data for a specific b14_D114Output."
    INDEX  { b14_D114OutputIndex }  ::=   { b14_D114OutputTable 1 }

B14_D114OutputTableEntry ::= SEQUENCE {
        b14_D114OutputIndex       INTEGER,
        b14_D114OutputName        DisplayString,
        b14_D114OutputValue       DisplayString
    }

b14_D114OutputIndex   OBJECT-TYPE
    SYNTAX           INTEGER(0..2147483647)
    ACCESS           read-only
    STATUS           mandatory
    DESCRIPTION
    "The index in the b14_D114Output table for a particular snmp b14_D114Output
	 object.  Used to address table entries."
    ::=   { b14_D114OutputTableEntry 1 }


b14_D114OutputName    OBJECT-TYPE
    SYNTAX           DisplayString
    ACCESS           read-only
    STATUS           mandatory
    DESCRIPTION
    "Name of station object."
    ::=   { b14_D114OutputTableEntry 2 }

b14_D114OutputValue    OBJECT-TYPE
    SYNTAX           DisplayString
    ACCESS           read-only
    STATUS           mandatory
    DESCRIPTION
    "Current value of station object. Is read-only ."
    ::=   { b14_D114OutputTableEntry 3 }


-- ***********************************
-- *
-- *  B14_D113
-- *
-- ***********************************
    b14_D113    OBJECT IDENTIFIER ::= { exportTables 133 }

-- ***********************************
-- *
-- *  B14_D113Input table declarations
-- *
-- ***********************************

b14_D113InputTable   OBJECT-TYPE
    SYNTAX                SEQUENCE OF B14_D113InputTableEntry
    ACCESS                not-accessible
    STATUS                mandatory
    DESCRIPTION
    "A list of snmp b14_D113Input (read-only) object values."
    ::=  { b14_D113 1 }

b14_D113InputTableEntry  OBJECT-TYPE
    SYNTAX                B14_D113InputTableEntry
    ACCESS                not-accessible
    STATUS                mandatory
    DESCRIPTION
    "An b14_D113Input table entry containing data for a specific b14_D113Input."
    INDEX  { b14_D113InputIndex }  ::=   { b14_D113InputTable 1 }

B14_D113InputTableEntry ::= SEQUENCE {
        b14_D113InputIndex       INTEGER,
        b14_D113InputName        DisplayString,
        b14_D113InputValue       DisplayString
    }

b14_D113InputIndex   OBJECT-TYPE
    SYNTAX           INTEGER(0..2147483647)
    ACCESS           read-only
    STATUS           mandatory
    DESCRIPTION
    "The index in the b14_D113Input table for a particular snmp b14_D113Input
	 object.  Used to address table entries."
    ::=   { b14_D113InputTableEntry 1 }


b14_D113InputName    OBJECT-TYPE
    SYNTAX           DisplayString
    ACCESS           read-only
    STATUS           mandatory
    DESCRIPTION
    "Name of station object."
    ::=   { b14_D113InputTableEntry 2 }

b14_D113InputValue    OBJECT-TYPE
    SYNTAX           DisplayString
    ACCESS           read-write
    STATUS           mandatory
    DESCRIPTION
    "Current value of station object. Is read-write ."
    ::=   { b14_D113InputTableEntry 3 }



-- ***********************************
-- *
-- *  B14_D113Output table declarations
-- *
-- ***********************************

b14_D113OutputTable   OBJECT-TYPE
    SYNTAX                SEQUENCE OF B14_D113OutputTableEntry
    ACCESS                not-accessible
    STATUS                mandatory
    DESCRIPTION
    "A list of snmp b14_D113Output (read-only) object values."
    ::=  { b14_D113 2 }

b14_D113OutputTableEntry  OBJECT-TYPE
    SYNTAX                B14_D113OutputTableEntry
    ACCESS                not-accessible
    STATUS                mandatory
    DESCRIPTION
    "An b14_D113Output table entry containing data for a specific b14_D113Output."
    INDEX  { b14_D113OutputIndex }  ::=   { b14_D113OutputTable 1 }

B14_D113OutputTableEntry ::= SEQUENCE {
        b14_D113OutputIndex       INTEGER,
        b14_D113OutputName        DisplayString,
        b14_D113OutputValue       DisplayString
    }

b14_D113OutputIndex   OBJECT-TYPE
    SYNTAX           INTEGER(0..2147483647)
    ACCESS           read-only
    STATUS           mandatory
    DESCRIPTION
    "The index in the b14_D113Output table for a particular snmp b14_D113Output
	 object.  Used to address table entries."
    ::=   { b14_D113OutputTableEntry 1 }


b14_D113OutputName    OBJECT-TYPE
    SYNTAX           DisplayString
    ACCESS           read-only
    STATUS           mandatory
    DESCRIPTION
    "Name of station object."
    ::=   { b14_D113OutputTableEntry 2 }

b14_D113OutputValue    OBJECT-TYPE
    SYNTAX           DisplayString
    ACCESS           read-only
    STATUS           mandatory
    DESCRIPTION
    "Current value of station object. Is read-only ."
    ::=   { b14_D113OutputTableEntry 3 }


-- ***********************************
-- *
-- *  B14_D118
-- *
-- ***********************************
    b14_D118    OBJECT IDENTIFIER ::= { exportTables 134 }

-- ***********************************
-- *
-- *  B14_D118Input table declarations
-- *
-- ***********************************

b14_D118InputTable   OBJECT-TYPE
    SYNTAX                SEQUENCE OF B14_D118InputTableEntry
    ACCESS                not-accessible
    STATUS                mandatory
    DESCRIPTION
    "A list of snmp b14_D118Input (read-only) object values."
    ::=  { b14_D118 1 }

b14_D118InputTableEntry  OBJECT-TYPE
    SYNTAX                B14_D118InputTableEntry
    ACCESS                not-accessible
    STATUS                mandatory
    DESCRIPTION
    "An b14_D118Input table entry containing data for a specific b14_D118Input."
    INDEX  { b14_D118InputIndex }  ::=   { b14_D118InputTable 1 }

B14_D118InputTableEntry ::= SEQUENCE {
        b14_D118InputIndex       INTEGER,
        b14_D118InputName        DisplayString,
        b14_D118InputValue       DisplayString
    }

b14_D118InputIndex   OBJECT-TYPE
    SYNTAX           INTEGER(0..2147483647)
    ACCESS           read-only
    STATUS           mandatory
    DESCRIPTION
    "The index in the b14_D118Input table for a particular snmp b14_D118Input
	 object.  Used to address table entries."
    ::=   { b14_D118InputTableEntry 1 }


b14_D118InputName    OBJECT-TYPE
    SYNTAX           DisplayString
    ACCESS           read-only
    STATUS           mandatory
    DESCRIPTION
    "Name of station object."
    ::=   { b14_D118InputTableEntry 2 }

b14_D118InputValue    OBJECT-TYPE
    SYNTAX           DisplayString
    ACCESS           read-write
    STATUS           mandatory
    DESCRIPTION
    "Current value of station object. Is read-write ."
    ::=   { b14_D118InputTableEntry 3 }



-- ***********************************
-- *
-- *  B14_D118Output table declarations
-- *
-- ***********************************

b14_D118OutputTable   OBJECT-TYPE
    SYNTAX                SEQUENCE OF B14_D118OutputTableEntry
    ACCESS                not-accessible
    STATUS                mandatory
    DESCRIPTION
    "A list of snmp b14_D118Output (read-only) object values."
    ::=  { b14_D118 2 }

b14_D118OutputTableEntry  OBJECT-TYPE
    SYNTAX                B14_D118OutputTableEntry
    ACCESS                not-accessible
    STATUS                mandatory
    DESCRIPTION
    "An b14_D118Output table entry containing data for a specific b14_D118Output."
    INDEX  { b14_D118OutputIndex }  ::=   { b14_D118OutputTable 1 }

B14_D118OutputTableEntry ::= SEQUENCE {
        b14_D118OutputIndex       INTEGER,
        b14_D118OutputName        DisplayString,
        b14_D118OutputValue       DisplayString
    }

b14_D118OutputIndex   OBJECT-TYPE
    SYNTAX           INTEGER(0..2147483647)
    ACCESS           read-only
    STATUS           mandatory
    DESCRIPTION
    "The index in the b14_D118Output table for a particular snmp b14_D118Output
	 object.  Used to address table entries."
    ::=   { b14_D118OutputTableEntry 1 }


b14_D118OutputName    OBJECT-TYPE
    SYNTAX           DisplayString
    ACCESS           read-only
    STATUS           mandatory
    DESCRIPTION
    "Name of station object."
    ::=   { b14_D118OutputTableEntry 2 }

b14_D118OutputValue    OBJECT-TYPE
    SYNTAX           DisplayString
    ACCESS           read-only
    STATUS           mandatory
    DESCRIPTION
    "Current value of station object. Is read-only ."
    ::=   { b14_D118OutputTableEntry 3 }


-- ***********************************
-- *
-- *  B14_D106
-- *
-- ***********************************
    b14_D106    OBJECT IDENTIFIER ::= { exportTables 135 }

-- ***********************************
-- *
-- *  B14_D106Input table declarations
-- *
-- ***********************************

b14_D106InputTable   OBJECT-TYPE
    SYNTAX                SEQUENCE OF B14_D106InputTableEntry
    ACCESS                not-accessible
    STATUS                mandatory
    DESCRIPTION
    "A list of snmp b14_D106Input (read-only) object values."
    ::=  { b14_D106 1 }

b14_D106InputTableEntry  OBJECT-TYPE
    SYNTAX                B14_D106InputTableEntry
    ACCESS                not-accessible
    STATUS                mandatory
    DESCRIPTION
    "An b14_D106Input table entry containing data for a specific b14_D106Input."
    INDEX  { b14_D106InputIndex }  ::=   { b14_D106InputTable 1 }

B14_D106InputTableEntry ::= SEQUENCE {
        b14_D106InputIndex       INTEGER,
        b14_D106InputName        DisplayString,
        b14_D106InputValue       DisplayString
    }

b14_D106InputIndex   OBJECT-TYPE
    SYNTAX           INTEGER(0..2147483647)
    ACCESS           read-only
    STATUS           mandatory
    DESCRIPTION
    "The index in the b14_D106Input table for a particular snmp b14_D106Input
	 object.  Used to address table entries."
    ::=   { b14_D106InputTableEntry 1 }


b14_D106InputName    OBJECT-TYPE
    SYNTAX           DisplayString
    ACCESS           read-only
    STATUS           mandatory
    DESCRIPTION
    "Name of station object."
    ::=   { b14_D106InputTableEntry 2 }

b14_D106InputValue    OBJECT-TYPE
    SYNTAX           DisplayString
    ACCESS           read-write
    STATUS           mandatory
    DESCRIPTION
    "Current value of station object. Is read-write ."
    ::=   { b14_D106InputTableEntry 3 }



-- ***********************************
-- *
-- *  B14_D106Output table declarations
-- *
-- ***********************************

b14_D106OutputTable   OBJECT-TYPE
    SYNTAX                SEQUENCE OF B14_D106OutputTableEntry
    ACCESS                not-accessible
    STATUS                mandatory
    DESCRIPTION
    "A list of snmp b14_D106Output (read-only) object values."
    ::=  { b14_D106 2 }

b14_D106OutputTableEntry  OBJECT-TYPE
    SYNTAX                B14_D106OutputTableEntry
    ACCESS                not-accessible
    STATUS                mandatory
    DESCRIPTION
    "An b14_D106Output table entry containing data for a specific b14_D106Output."
    INDEX  { b14_D106OutputIndex }  ::=   { b14_D106OutputTable 1 }

B14_D106OutputTableEntry ::= SEQUENCE {
        b14_D106OutputIndex       INTEGER,
        b14_D106OutputName        DisplayString,
        b14_D106OutputValue       DisplayString
    }

b14_D106OutputIndex   OBJECT-TYPE
    SYNTAX           INTEGER(0..2147483647)
    ACCESS           read-only
    STATUS           mandatory
    DESCRIPTION
    "The index in the b14_D106Output table for a particular snmp b14_D106Output
	 object.  Used to address table entries."
    ::=   { b14_D106OutputTableEntry 1 }


b14_D106OutputName    OBJECT-TYPE
    SYNTAX           DisplayString
    ACCESS           read-only
    STATUS           mandatory
    DESCRIPTION
    "Name of station object."
    ::=   { b14_D106OutputTableEntry 2 }

b14_D106OutputValue    OBJECT-TYPE
    SYNTAX           DisplayString
    ACCESS           read-only
    STATUS           mandatory
    DESCRIPTION
    "Current value of station object. Is read-only ."
    ::=   { b14_D106OutputTableEntry 3 }


-- ***********************************
-- *
-- *  B14_D54
-- *
-- ***********************************
    b14_D54    OBJECT IDENTIFIER ::= { exportTables 136 }

-- ***********************************
-- *
-- *  B14_D54Input table declarations
-- *
-- ***********************************

b14_D54InputTable   OBJECT-TYPE
    SYNTAX                SEQUENCE OF B14_D54InputTableEntry
    ACCESS                not-accessible
    STATUS                mandatory
    DESCRIPTION
    "A list of snmp b14_D54Input (read-only) object values."
    ::=  { b14_D54 1 }

b14_D54InputTableEntry  OBJECT-TYPE
    SYNTAX                B14_D54InputTableEntry
    ACCESS                not-accessible
    STATUS                mandatory
    DESCRIPTION
    "An b14_D54Input table entry containing data for a specific b14_D54Input."
    INDEX  { b14_D54InputIndex }  ::=   { b14_D54InputTable 1 }

B14_D54InputTableEntry ::= SEQUENCE {
        b14_D54InputIndex       INTEGER,
        b14_D54InputName        DisplayString,
        b14_D54InputValue       DisplayString
    }

b14_D54InputIndex   OBJECT-TYPE
    SYNTAX           INTEGER(0..2147483647)
    ACCESS           read-only
    STATUS           mandatory
    DESCRIPTION
    "The index in the b14_D54Input table for a particular snmp b14_D54Input
	 object.  Used to address table entries."
    ::=   { b14_D54InputTableEntry 1 }


b14_D54InputName    OBJECT-TYPE
    SYNTAX           DisplayString
    ACCESS           read-only
    STATUS           mandatory
    DESCRIPTION
    "Name of station object."
    ::=   { b14_D54InputTableEntry 2 }

b14_D54InputValue    OBJECT-TYPE
    SYNTAX           DisplayString
    ACCESS           read-write
    STATUS           mandatory
    DESCRIPTION
    "Current value of station object. Is read-write ."
    ::=   { b14_D54InputTableEntry 3 }



-- ***********************************
-- *
-- *  B14_D54Output table declarations
-- *
-- ***********************************

b14_D54OutputTable   OBJECT-TYPE
    SYNTAX                SEQUENCE OF B14_D54OutputTableEntry
    ACCESS                not-accessible
    STATUS                mandatory
    DESCRIPTION
    "A list of snmp b14_D54Output (read-only) object values."
    ::=  { b14_D54 2 }

b14_D54OutputTableEntry  OBJECT-TYPE
    SYNTAX                B14_D54OutputTableEntry
    ACCESS                not-accessible
    STATUS                mandatory
    DESCRIPTION
    "An b14_D54Output table entry containing data for a specific b14_D54Output."
    INDEX  { b14_D54OutputIndex }  ::=   { b14_D54OutputTable 1 }

B14_D54OutputTableEntry ::= SEQUENCE {
        b14_D54OutputIndex       INTEGER,
        b14_D54OutputName        DisplayString,
        b14_D54OutputValue       DisplayString
    }

b14_D54OutputIndex   OBJECT-TYPE
    SYNTAX           INTEGER(0..2147483647)
    ACCESS           read-only
    STATUS           mandatory
    DESCRIPTION
    "The index in the b14_D54Output table for a particular snmp b14_D54Output
	 object.  Used to address table entries."
    ::=   { b14_D54OutputTableEntry 1 }


b14_D54OutputName    OBJECT-TYPE
    SYNTAX           DisplayString
    ACCESS           read-only
    STATUS           mandatory
    DESCRIPTION
    "Name of station object."
    ::=   { b14_D54OutputTableEntry 2 }

b14_D54OutputValue    OBJECT-TYPE
    SYNTAX           DisplayString
    ACCESS           read-only
    STATUS           mandatory
    DESCRIPTION
    "Current value of station object. Is read-only ."
    ::=   { b14_D54OutputTableEntry 3 }


-- ***********************************
-- *
-- *  B14_D55
-- *
-- ***********************************
    b14_D55    OBJECT IDENTIFIER ::= { exportTables 137 }

-- ***********************************
-- *
-- *  B14_D55Input table declarations
-- *
-- ***********************************

b14_D55InputTable   OBJECT-TYPE
    SYNTAX                SEQUENCE OF B14_D55InputTableEntry
    ACCESS                not-accessible
    STATUS                mandatory
    DESCRIPTION
    "A list of snmp b14_D55Input (read-only) object values."
    ::=  { b14_D55 1 }

b14_D55InputTableEntry  OBJECT-TYPE
    SYNTAX                B14_D55InputTableEntry
    ACCESS                not-accessible
    STATUS                mandatory
    DESCRIPTION
    "An b14_D55Input table entry containing data for a specific b14_D55Input."
    INDEX  { b14_D55InputIndex }  ::=   { b14_D55InputTable 1 }

B14_D55InputTableEntry ::= SEQUENCE {
        b14_D55InputIndex       INTEGER,
        b14_D55InputName        DisplayString,
        b14_D55InputValue       DisplayString
    }

b14_D55InputIndex   OBJECT-TYPE
    SYNTAX           INTEGER(0..2147483647)
    ACCESS           read-only
    STATUS           mandatory
    DESCRIPTION
    "The index in the b14_D55Input table for a particular snmp b14_D55Input
	 object.  Used to address table entries."
    ::=   { b14_D55InputTableEntry 1 }


b14_D55InputName    OBJECT-TYPE
    SYNTAX           DisplayString
    ACCESS           read-only
    STATUS           mandatory
    DESCRIPTION
    "Name of station object."
    ::=   { b14_D55InputTableEntry 2 }

b14_D55InputValue    OBJECT-TYPE
    SYNTAX           DisplayString
    ACCESS           read-write
    STATUS           mandatory
    DESCRIPTION
    "Current value of station object. Is read-write ."
    ::=   { b14_D55InputTableEntry 3 }



-- ***********************************
-- *
-- *  B14_D55Output table declarations
-- *
-- ***********************************

b14_D55OutputTable   OBJECT-TYPE
    SYNTAX                SEQUENCE OF B14_D55OutputTableEntry
    ACCESS                not-accessible
    STATUS                mandatory
    DESCRIPTION
    "A list of snmp b14_D55Output (read-only) object values."
    ::=  { b14_D55 2 }

b14_D55OutputTableEntry  OBJECT-TYPE
    SYNTAX                B14_D55OutputTableEntry
    ACCESS                not-accessible
    STATUS                mandatory
    DESCRIPTION
    "An b14_D55Output table entry containing data for a specific b14_D55Output."
    INDEX  { b14_D55OutputIndex }  ::=   { b14_D55OutputTable 1 }

B14_D55OutputTableEntry ::= SEQUENCE {
        b14_D55OutputIndex       INTEGER,
        b14_D55OutputName        DisplayString,
        b14_D55OutputValue       DisplayString
    }

b14_D55OutputIndex   OBJECT-TYPE
    SYNTAX           INTEGER(0..2147483647)
    ACCESS           read-only
    STATUS           mandatory
    DESCRIPTION
    "The index in the b14_D55Output table for a particular snmp b14_D55Output
	 object.  Used to address table entries."
    ::=   { b14_D55OutputTableEntry 1 }


b14_D55OutputName    OBJECT-TYPE
    SYNTAX           DisplayString
    ACCESS           read-only
    STATUS           mandatory
    DESCRIPTION
    "Name of station object."
    ::=   { b14_D55OutputTableEntry 2 }

b14_D55OutputValue    OBJECT-TYPE
    SYNTAX           DisplayString
    ACCESS           read-only
    STATUS           mandatory
    DESCRIPTION
    "Current value of station object. Is read-only ."
    ::=   { b14_D55OutputTableEntry 3 }


-- ***********************************
-- *
-- *  B14_D51
-- *
-- ***********************************
    b14_D51    OBJECT IDENTIFIER ::= { exportTables 138 }

-- ***********************************
-- *
-- *  B14_D51Input table declarations
-- *
-- ***********************************

b14_D51InputTable   OBJECT-TYPE
    SYNTAX                SEQUENCE OF B14_D51InputTableEntry
    ACCESS                not-accessible
    STATUS                mandatory
    DESCRIPTION
    "A list of snmp b14_D51Input (read-only) object values."
    ::=  { b14_D51 1 }

b14_D51InputTableEntry  OBJECT-TYPE
    SYNTAX                B14_D51InputTableEntry
    ACCESS                not-accessible
    STATUS                mandatory
    DESCRIPTION
    "An b14_D51Input table entry containing data for a specific b14_D51Input."
    INDEX  { b14_D51InputIndex }  ::=   { b14_D51InputTable 1 }

B14_D51InputTableEntry ::= SEQUENCE {
        b14_D51InputIndex       INTEGER,
        b14_D51InputName        DisplayString,
        b14_D51InputValue       DisplayString
    }

b14_D51InputIndex   OBJECT-TYPE
    SYNTAX           INTEGER(0..2147483647)
    ACCESS           read-only
    STATUS           mandatory
    DESCRIPTION
    "The index in the b14_D51Input table for a particular snmp b14_D51Input
	 object.  Used to address table entries."
    ::=   { b14_D51InputTableEntry 1 }


b14_D51InputName    OBJECT-TYPE
    SYNTAX           DisplayString
    ACCESS           read-only
    STATUS           mandatory
    DESCRIPTION
    "Name of station object."
    ::=   { b14_D51InputTableEntry 2 }

b14_D51InputValue    OBJECT-TYPE
    SYNTAX           DisplayString
    ACCESS           read-write
    STATUS           mandatory
    DESCRIPTION
    "Current value of station object. Is read-write ."
    ::=   { b14_D51InputTableEntry 3 }



-- ***********************************
-- *
-- *  B14_D51Output table declarations
-- *
-- ***********************************

b14_D51OutputTable   OBJECT-TYPE
    SYNTAX                SEQUENCE OF B14_D51OutputTableEntry
    ACCESS                not-accessible
    STATUS                mandatory
    DESCRIPTION
    "A list of snmp b14_D51Output (read-only) object values."
    ::=  { b14_D51 2 }

b14_D51OutputTableEntry  OBJECT-TYPE
    SYNTAX                B14_D51OutputTableEntry
    ACCESS                not-accessible
    STATUS                mandatory
    DESCRIPTION
    "An b14_D51Output table entry containing data for a specific b14_D51Output."
    INDEX  { b14_D51OutputIndex }  ::=   { b14_D51OutputTable 1 }

B14_D51OutputTableEntry ::= SEQUENCE {
        b14_D51OutputIndex       INTEGER,
        b14_D51OutputName        DisplayString,
        b14_D51OutputValue       DisplayString
    }

b14_D51OutputIndex   OBJECT-TYPE
    SYNTAX           INTEGER(0..2147483647)
    ACCESS           read-only
    STATUS           mandatory
    DESCRIPTION
    "The index in the b14_D51Output table for a particular snmp b14_D51Output
	 object.  Used to address table entries."
    ::=   { b14_D51OutputTableEntry 1 }


b14_D51OutputName    OBJECT-TYPE
    SYNTAX           DisplayString
    ACCESS           read-only
    STATUS           mandatory
    DESCRIPTION
    "Name of station object."
    ::=   { b14_D51OutputTableEntry 2 }

b14_D51OutputValue    OBJECT-TYPE
    SYNTAX           DisplayString
    ACCESS           read-only
    STATUS           mandatory
    DESCRIPTION
    "Current value of station object. Is read-only ."
    ::=   { b14_D51OutputTableEntry 3 }


-- ***********************************
-- *
-- *  B14_D60
-- *
-- ***********************************
    b14_D60    OBJECT IDENTIFIER ::= { exportTables 139 }

-- ***********************************
-- *
-- *  B14_D60Input table declarations
-- *
-- ***********************************

b14_D60InputTable   OBJECT-TYPE
    SYNTAX                SEQUENCE OF B14_D60InputTableEntry
    ACCESS                not-accessible
    STATUS                mandatory
    DESCRIPTION
    "A list of snmp b14_D60Input (read-only) object values."
    ::=  { b14_D60 1 }

b14_D60InputTableEntry  OBJECT-TYPE
    SYNTAX                B14_D60InputTableEntry
    ACCESS                not-accessible
    STATUS                mandatory
    DESCRIPTION
    "An b14_D60Input table entry containing data for a specific b14_D60Input."
    INDEX  { b14_D60InputIndex }  ::=   { b14_D60InputTable 1 }

B14_D60InputTableEntry ::= SEQUENCE {
        b14_D60InputIndex       INTEGER,
        b14_D60InputName        DisplayString,
        b14_D60InputValue       DisplayString
    }

b14_D60InputIndex   OBJECT-TYPE
    SYNTAX           INTEGER(0..2147483647)
    ACCESS           read-only
    STATUS           mandatory
    DESCRIPTION
    "The index in the b14_D60Input table for a particular snmp b14_D60Input
	 object.  Used to address table entries."
    ::=   { b14_D60InputTableEntry 1 }


b14_D60InputName    OBJECT-TYPE
    SYNTAX           DisplayString
    ACCESS           read-only
    STATUS           mandatory
    DESCRIPTION
    "Name of station object."
    ::=   { b14_D60InputTableEntry 2 }

b14_D60InputValue    OBJECT-TYPE
    SYNTAX           DisplayString
    ACCESS           read-write
    STATUS           mandatory
    DESCRIPTION
    "Current value of station object. Is read-write ."
    ::=   { b14_D60InputTableEntry 3 }



-- ***********************************
-- *
-- *  B14_D60Output table declarations
-- *
-- ***********************************

b14_D60OutputTable   OBJECT-TYPE
    SYNTAX                SEQUENCE OF B14_D60OutputTableEntry
    ACCESS                not-accessible
    STATUS                mandatory
    DESCRIPTION
    "A list of snmp b14_D60Output (read-only) object values."
    ::=  { b14_D60 2 }

b14_D60OutputTableEntry  OBJECT-TYPE
    SYNTAX                B14_D60OutputTableEntry
    ACCESS                not-accessible
    STATUS                mandatory
    DESCRIPTION
    "An b14_D60Output table entry containing data for a specific b14_D60Output."
    INDEX  { b14_D60OutputIndex }  ::=   { b14_D60OutputTable 1 }

B14_D60OutputTableEntry ::= SEQUENCE {
        b14_D60OutputIndex       INTEGER,
        b14_D60OutputName        DisplayString,
        b14_D60OutputValue       DisplayString
    }

b14_D60OutputIndex   OBJECT-TYPE
    SYNTAX           INTEGER(0..2147483647)
    ACCESS           read-only
    STATUS           mandatory
    DESCRIPTION
    "The index in the b14_D60Output table for a particular snmp b14_D60Output
	 object.  Used to address table entries."
    ::=   { b14_D60OutputTableEntry 1 }


b14_D60OutputName    OBJECT-TYPE
    SYNTAX           DisplayString
    ACCESS           read-only
    STATUS           mandatory
    DESCRIPTION
    "Name of station object."
    ::=   { b14_D60OutputTableEntry 2 }

b14_D60OutputValue    OBJECT-TYPE
    SYNTAX           DisplayString
    ACCESS           read-only
    STATUS           mandatory
    DESCRIPTION
    "Current value of station object. Is read-only ."
    ::=   { b14_D60OutputTableEntry 3 }


-- ***********************************
-- *
-- *  B14_D50
-- *
-- ***********************************
    b14_D50    OBJECT IDENTIFIER ::= { exportTables 140 }

-- ***********************************
-- *
-- *  B14_D50Input table declarations
-- *
-- ***********************************

b14_D50InputTable   OBJECT-TYPE
    SYNTAX                SEQUENCE OF B14_D50InputTableEntry
    ACCESS                not-accessible
    STATUS                mandatory
    DESCRIPTION
    "A list of snmp b14_D50Input (read-only) object values."
    ::=  { b14_D50 1 }

b14_D50InputTableEntry  OBJECT-TYPE
    SYNTAX                B14_D50InputTableEntry
    ACCESS                not-accessible
    STATUS                mandatory
    DESCRIPTION
    "An b14_D50Input table entry containing data for a specific b14_D50Input."
    INDEX  { b14_D50InputIndex }  ::=   { b14_D50InputTable 1 }

B14_D50InputTableEntry ::= SEQUENCE {
        b14_D50InputIndex       INTEGER,
        b14_D50InputName        DisplayString,
        b14_D50InputValue       DisplayString
    }

b14_D50InputIndex   OBJECT-TYPE
    SYNTAX           INTEGER(0..2147483647)
    ACCESS           read-only
    STATUS           mandatory
    DESCRIPTION
    "The index in the b14_D50Input table for a particular snmp b14_D50Input
	 object.  Used to address table entries."
    ::=   { b14_D50InputTableEntry 1 }


b14_D50InputName    OBJECT-TYPE
    SYNTAX           DisplayString
    ACCESS           read-only
    STATUS           mandatory
    DESCRIPTION
    "Name of station object."
    ::=   { b14_D50InputTableEntry 2 }

b14_D50InputValue    OBJECT-TYPE
    SYNTAX           DisplayString
    ACCESS           read-write
    STATUS           mandatory
    DESCRIPTION
    "Current value of station object. Is read-write ."
    ::=   { b14_D50InputTableEntry 3 }



-- ***********************************
-- *
-- *  B14_D50Output table declarations
-- *
-- ***********************************

b14_D50OutputTable   OBJECT-TYPE
    SYNTAX                SEQUENCE OF B14_D50OutputTableEntry
    ACCESS                not-accessible
    STATUS                mandatory
    DESCRIPTION
    "A list of snmp b14_D50Output (read-only) object values."
    ::=  { b14_D50 2 }

b14_D50OutputTableEntry  OBJECT-TYPE
    SYNTAX                B14_D50OutputTableEntry
    ACCESS                not-accessible
    STATUS                mandatory
    DESCRIPTION
    "An b14_D50Output table entry containing data for a specific b14_D50Output."
    INDEX  { b14_D50OutputIndex }  ::=   { b14_D50OutputTable 1 }

B14_D50OutputTableEntry ::= SEQUENCE {
        b14_D50OutputIndex       INTEGER,
        b14_D50OutputName        DisplayString,
        b14_D50OutputValue       DisplayString
    }

b14_D50OutputIndex   OBJECT-TYPE
    SYNTAX           INTEGER(0..2147483647)
    ACCESS           read-only
    STATUS           mandatory
    DESCRIPTION
    "The index in the b14_D50Output table for a particular snmp b14_D50Output
	 object.  Used to address table entries."
    ::=   { b14_D50OutputTableEntry 1 }


b14_D50OutputName    OBJECT-TYPE
    SYNTAX           DisplayString
    ACCESS           read-only
    STATUS           mandatory
    DESCRIPTION
    "Name of station object."
    ::=   { b14_D50OutputTableEntry 2 }

b14_D50OutputValue    OBJECT-TYPE
    SYNTAX           DisplayString
    ACCESS           read-only
    STATUS           mandatory
    DESCRIPTION
    "Current value of station object. Is read-only ."
    ::=   { b14_D50OutputTableEntry 3 }


-- ***********************************
-- *
-- *  B14_D112
-- *
-- ***********************************
    b14_D112    OBJECT IDENTIFIER ::= { exportTables 141 }

-- ***********************************
-- *
-- *  B14_D112Input table declarations
-- *
-- ***********************************

b14_D112InputTable   OBJECT-TYPE
    SYNTAX                SEQUENCE OF B14_D112InputTableEntry
    ACCESS                not-accessible
    STATUS                mandatory
    DESCRIPTION
    "A list of snmp b14_D112Input (read-only) object values."
    ::=  { b14_D112 1 }

b14_D112InputTableEntry  OBJECT-TYPE
    SYNTAX                B14_D112InputTableEntry
    ACCESS                not-accessible
    STATUS                mandatory
    DESCRIPTION
    "An b14_D112Input table entry containing data for a specific b14_D112Input."
    INDEX  { b14_D112InputIndex }  ::=   { b14_D112InputTable 1 }

B14_D112InputTableEntry ::= SEQUENCE {
        b14_D112InputIndex       INTEGER,
        b14_D112InputName        DisplayString,
        b14_D112InputValue       DisplayString
    }

b14_D112InputIndex   OBJECT-TYPE
    SYNTAX           INTEGER(0..2147483647)
    ACCESS           read-only
    STATUS           mandatory
    DESCRIPTION
    "The index in the b14_D112Input table for a particular snmp b14_D112Input
	 object.  Used to address table entries."
    ::=   { b14_D112InputTableEntry 1 }


b14_D112InputName    OBJECT-TYPE
    SYNTAX           DisplayString
    ACCESS           read-only
    STATUS           mandatory
    DESCRIPTION
    "Name of station object."
    ::=   { b14_D112InputTableEntry 2 }

b14_D112InputValue    OBJECT-TYPE
    SYNTAX           DisplayString
    ACCESS           read-write
    STATUS           mandatory
    DESCRIPTION
    "Current value of station object. Is read-write ."
    ::=   { b14_D112InputTableEntry 3 }



-- ***********************************
-- *
-- *  B14_D112Output table declarations
-- *
-- ***********************************

b14_D112OutputTable   OBJECT-TYPE
    SYNTAX                SEQUENCE OF B14_D112OutputTableEntry
    ACCESS                not-accessible
    STATUS                mandatory
    DESCRIPTION
    "A list of snmp b14_D112Output (read-only) object values."
    ::=  { b14_D112 2 }

b14_D112OutputTableEntry  OBJECT-TYPE
    SYNTAX                B14_D112OutputTableEntry
    ACCESS                not-accessible
    STATUS                mandatory
    DESCRIPTION
    "An b14_D112Output table entry containing data for a specific b14_D112Output."
    INDEX  { b14_D112OutputIndex }  ::=   { b14_D112OutputTable 1 }

B14_D112OutputTableEntry ::= SEQUENCE {
        b14_D112OutputIndex       INTEGER,
        b14_D112OutputName        DisplayString,
        b14_D112OutputValue       DisplayString
    }

b14_D112OutputIndex   OBJECT-TYPE
    SYNTAX           INTEGER(0..2147483647)
    ACCESS           read-only
    STATUS           mandatory
    DESCRIPTION
    "The index in the b14_D112Output table for a particular snmp b14_D112Output
	 object.  Used to address table entries."
    ::=   { b14_D112OutputTableEntry 1 }


b14_D112OutputName    OBJECT-TYPE
    SYNTAX           DisplayString
    ACCESS           read-only
    STATUS           mandatory
    DESCRIPTION
    "Name of station object."
    ::=   { b14_D112OutputTableEntry 2 }

b14_D112OutputValue    OBJECT-TYPE
    SYNTAX           DisplayString
    ACCESS           read-only
    STATUS           mandatory
    DESCRIPTION
    "Current value of station object. Is read-only ."
    ::=   { b14_D112OutputTableEntry 3 }


-- ***********************************
-- *
-- *  B14_D132
-- *
-- ***********************************
    b14_D132    OBJECT IDENTIFIER ::= { exportTables 142 }

-- ***********************************
-- *
-- *  B14_D132Input table declarations
-- *
-- ***********************************

b14_D132InputTable   OBJECT-TYPE
    SYNTAX                SEQUENCE OF B14_D132InputTableEntry
    ACCESS                not-accessible
    STATUS                mandatory
    DESCRIPTION
    "A list of snmp b14_D132Input (read-only) object values."
    ::=  { b14_D132 1 }

b14_D132InputTableEntry  OBJECT-TYPE
    SYNTAX                B14_D132InputTableEntry
    ACCESS                not-accessible
    STATUS                mandatory
    DESCRIPTION
    "An b14_D132Input table entry containing data for a specific b14_D132Input."
    INDEX  { b14_D132InputIndex }  ::=   { b14_D132InputTable 1 }

B14_D132InputTableEntry ::= SEQUENCE {
        b14_D132InputIndex       INTEGER,
        b14_D132InputName        DisplayString,
        b14_D132InputValue       DisplayString
    }

b14_D132InputIndex   OBJECT-TYPE
    SYNTAX           INTEGER(0..2147483647)
    ACCESS           read-only
    STATUS           mandatory
    DESCRIPTION
    "The index in the b14_D132Input table for a particular snmp b14_D132Input
	 object.  Used to address table entries."
    ::=   { b14_D132InputTableEntry 1 }


b14_D132InputName    OBJECT-TYPE
    SYNTAX           DisplayString
    ACCESS           read-only
    STATUS           mandatory
    DESCRIPTION
    "Name of station object."
    ::=   { b14_D132InputTableEntry 2 }

b14_D132InputValue    OBJECT-TYPE
    SYNTAX           DisplayString
    ACCESS           read-write
    STATUS           mandatory
    DESCRIPTION
    "Current value of station object. Is read-write ."
    ::=   { b14_D132InputTableEntry 3 }



-- ***********************************
-- *
-- *  B14_D132Output table declarations
-- *
-- ***********************************

b14_D132OutputTable   OBJECT-TYPE
    SYNTAX                SEQUENCE OF B14_D132OutputTableEntry
    ACCESS                not-accessible
    STATUS                mandatory
    DESCRIPTION
    "A list of snmp b14_D132Output (read-only) object values."
    ::=  { b14_D132 2 }

b14_D132OutputTableEntry  OBJECT-TYPE
    SYNTAX                B14_D132OutputTableEntry
    ACCESS                not-accessible
    STATUS                mandatory
    DESCRIPTION
    "An b14_D132Output table entry containing data for a specific b14_D132Output."
    INDEX  { b14_D132OutputIndex }  ::=   { b14_D132OutputTable 1 }

B14_D132OutputTableEntry ::= SEQUENCE {
        b14_D132OutputIndex       INTEGER,
        b14_D132OutputName        DisplayString,
        b14_D132OutputValue       DisplayString
    }

b14_D132OutputIndex   OBJECT-TYPE
    SYNTAX           INTEGER(0..2147483647)
    ACCESS           read-only
    STATUS           mandatory
    DESCRIPTION
    "The index in the b14_D132Output table for a particular snmp b14_D132Output
	 object.  Used to address table entries."
    ::=   { b14_D132OutputTableEntry 1 }


b14_D132OutputName    OBJECT-TYPE
    SYNTAX           DisplayString
    ACCESS           read-only
    STATUS           mandatory
    DESCRIPTION
    "Name of station object."
    ::=   { b14_D132OutputTableEntry 2 }

b14_D132OutputValue    OBJECT-TYPE
    SYNTAX           DisplayString
    ACCESS           read-only
    STATUS           mandatory
    DESCRIPTION
    "Current value of station object. Is read-only ."
    ::=   { b14_D132OutputTableEntry 3 }


-- ***********************************
-- *
-- *  B14_D135
-- *
-- ***********************************
    b14_D135    OBJECT IDENTIFIER ::= { exportTables 143 }

-- ***********************************
-- *
-- *  B14_D135Input table declarations
-- *
-- ***********************************

b14_D135InputTable   OBJECT-TYPE
    SYNTAX                SEQUENCE OF B14_D135InputTableEntry
    ACCESS                not-accessible
    STATUS                mandatory
    DESCRIPTION
    "A list of snmp b14_D135Input (read-only) object values."
    ::=  { b14_D135 1 }

b14_D135InputTableEntry  OBJECT-TYPE
    SYNTAX                B14_D135InputTableEntry
    ACCESS                not-accessible
    STATUS                mandatory
    DESCRIPTION
    "An b14_D135Input table entry containing data for a specific b14_D135Input."
    INDEX  { b14_D135InputIndex }  ::=   { b14_D135InputTable 1 }

B14_D135InputTableEntry ::= SEQUENCE {
        b14_D135InputIndex       INTEGER,
        b14_D135InputName        DisplayString,
        b14_D135InputValue       DisplayString
    }

b14_D135InputIndex   OBJECT-TYPE
    SYNTAX           INTEGER(0..2147483647)
    ACCESS           read-only
    STATUS           mandatory
    DESCRIPTION
    "The index in the b14_D135Input table for a particular snmp b14_D135Input
	 object.  Used to address table entries."
    ::=   { b14_D135InputTableEntry 1 }


b14_D135InputName    OBJECT-TYPE
    SYNTAX           DisplayString
    ACCESS           read-only
    STATUS           mandatory
    DESCRIPTION
    "Name of station object."
    ::=   { b14_D135InputTableEntry 2 }

b14_D135InputValue    OBJECT-TYPE
    SYNTAX           DisplayString
    ACCESS           read-write
    STATUS           mandatory
    DESCRIPTION
    "Current value of station object. Is read-write ."
    ::=   { b14_D135InputTableEntry 3 }



-- ***********************************
-- *
-- *  B14_D135Output table declarations
-- *
-- ***********************************

b14_D135OutputTable   OBJECT-TYPE
    SYNTAX                SEQUENCE OF B14_D135OutputTableEntry
    ACCESS                not-accessible
    STATUS                mandatory
    DESCRIPTION
    "A list of snmp b14_D135Output (read-only) object values."
    ::=  { b14_D135 2 }

b14_D135OutputTableEntry  OBJECT-TYPE
    SYNTAX                B14_D135OutputTableEntry
    ACCESS                not-accessible
    STATUS                mandatory
    DESCRIPTION
    "An b14_D135Output table entry containing data for a specific b14_D135Output."
    INDEX  { b14_D135OutputIndex }  ::=   { b14_D135OutputTable 1 }

B14_D135OutputTableEntry ::= SEQUENCE {
        b14_D135OutputIndex       INTEGER,
        b14_D135OutputName        DisplayString,
        b14_D135OutputValue       DisplayString
    }

b14_D135OutputIndex   OBJECT-TYPE
    SYNTAX           INTEGER(0..2147483647)
    ACCESS           read-only
    STATUS           mandatory
    DESCRIPTION
    "The index in the b14_D135Output table for a particular snmp b14_D135Output
	 object.  Used to address table entries."
    ::=   { b14_D135OutputTableEntry 1 }


b14_D135OutputName    OBJECT-TYPE
    SYNTAX           DisplayString
    ACCESS           read-only
    STATUS           mandatory
    DESCRIPTION
    "Name of station object."
    ::=   { b14_D135OutputTableEntry 2 }

b14_D135OutputValue    OBJECT-TYPE
    SYNTAX           DisplayString
    ACCESS           read-only
    STATUS           mandatory
    DESCRIPTION
    "Current value of station object. Is read-only ."
    ::=   { b14_D135OutputTableEntry 3 }


-- ***********************************
-- *
-- *  B14_D130
-- *
-- ***********************************
    b14_D130    OBJECT IDENTIFIER ::= { exportTables 144 }

-- ***********************************
-- *
-- *  B14_D130Input table declarations
-- *
-- ***********************************

b14_D130InputTable   OBJECT-TYPE
    SYNTAX                SEQUENCE OF B14_D130InputTableEntry
    ACCESS                not-accessible
    STATUS                mandatory
    DESCRIPTION
    "A list of snmp b14_D130Input (read-only) object values."
    ::=  { b14_D130 1 }

b14_D130InputTableEntry  OBJECT-TYPE
    SYNTAX                B14_D130InputTableEntry
    ACCESS                not-accessible
    STATUS                mandatory
    DESCRIPTION
    "An b14_D130Input table entry containing data for a specific b14_D130Input."
    INDEX  { b14_D130InputIndex }  ::=   { b14_D130InputTable 1 }

B14_D130InputTableEntry ::= SEQUENCE {
        b14_D130InputIndex       INTEGER,
        b14_D130InputName        DisplayString,
        b14_D130InputValue       DisplayString
    }

b14_D130InputIndex   OBJECT-TYPE
    SYNTAX           INTEGER(0..2147483647)
    ACCESS           read-only
    STATUS           mandatory
    DESCRIPTION
    "The index in the b14_D130Input table for a particular snmp b14_D130Input
	 object.  Used to address table entries."
    ::=   { b14_D130InputTableEntry 1 }


b14_D130InputName    OBJECT-TYPE
    SYNTAX           DisplayString
    ACCESS           read-only
    STATUS           mandatory
    DESCRIPTION
    "Name of station object."
    ::=   { b14_D130InputTableEntry 2 }

b14_D130InputValue    OBJECT-TYPE
    SYNTAX           DisplayString
    ACCESS           read-write
    STATUS           mandatory
    DESCRIPTION
    "Current value of station object. Is read-write ."
    ::=   { b14_D130InputTableEntry 3 }



-- ***********************************
-- *
-- *  B14_D130Output table declarations
-- *
-- ***********************************

b14_D130OutputTable   OBJECT-TYPE
    SYNTAX                SEQUENCE OF B14_D130OutputTableEntry
    ACCESS                not-accessible
    STATUS                mandatory
    DESCRIPTION
    "A list of snmp b14_D130Output (read-only) object values."
    ::=  { b14_D130 2 }

b14_D130OutputTableEntry  OBJECT-TYPE
    SYNTAX                B14_D130OutputTableEntry
    ACCESS                not-accessible
    STATUS                mandatory
    DESCRIPTION
    "An b14_D130Output table entry containing data for a specific b14_D130Output."
    INDEX  { b14_D130OutputIndex }  ::=   { b14_D130OutputTable 1 }

B14_D130OutputTableEntry ::= SEQUENCE {
        b14_D130OutputIndex       INTEGER,
        b14_D130OutputName        DisplayString,
        b14_D130OutputValue       DisplayString
    }

b14_D130OutputIndex   OBJECT-TYPE
    SYNTAX           INTEGER(0..2147483647)
    ACCESS           read-only
    STATUS           mandatory
    DESCRIPTION
    "The index in the b14_D130Output table for a particular snmp b14_D130Output
	 object.  Used to address table entries."
    ::=   { b14_D130OutputTableEntry 1 }


b14_D130OutputName    OBJECT-TYPE
    SYNTAX           DisplayString
    ACCESS           read-only
    STATUS           mandatory
    DESCRIPTION
    "Name of station object."
    ::=   { b14_D130OutputTableEntry 2 }

b14_D130OutputValue    OBJECT-TYPE
    SYNTAX           DisplayString
    ACCESS           read-only
    STATUS           mandatory
    DESCRIPTION
    "Current value of station object. Is read-only ."
    ::=   { b14_D130OutputTableEntry 3 }


-- ***********************************
-- *
-- *  B14_D66
-- *
-- ***********************************
    b14_D66    OBJECT IDENTIFIER ::= { exportTables 145 }

-- ***********************************
-- *
-- *  B14_D66Input table declarations
-- *
-- ***********************************

b14_D66InputTable   OBJECT-TYPE
    SYNTAX                SEQUENCE OF B14_D66InputTableEntry
    ACCESS                not-accessible
    STATUS                mandatory
    DESCRIPTION
    "A list of snmp b14_D66Input (read-only) object values."
    ::=  { b14_D66 1 }

b14_D66InputTableEntry  OBJECT-TYPE
    SYNTAX                B14_D66InputTableEntry
    ACCESS                not-accessible
    STATUS                mandatory
    DESCRIPTION
    "An b14_D66Input table entry containing data for a specific b14_D66Input."
    INDEX  { b14_D66InputIndex }  ::=   { b14_D66InputTable 1 }

B14_D66InputTableEntry ::= SEQUENCE {
        b14_D66InputIndex       INTEGER,
        b14_D66InputName        DisplayString,
        b14_D66InputValue       DisplayString
    }

b14_D66InputIndex   OBJECT-TYPE
    SYNTAX           INTEGER(0..2147483647)
    ACCESS           read-only
    STATUS           mandatory
    DESCRIPTION
    "The index in the b14_D66Input table for a particular snmp b14_D66Input
	 object.  Used to address table entries."
    ::=   { b14_D66InputTableEntry 1 }


b14_D66InputName    OBJECT-TYPE
    SYNTAX           DisplayString
    ACCESS           read-only
    STATUS           mandatory
    DESCRIPTION
    "Name of station object."
    ::=   { b14_D66InputTableEntry 2 }

b14_D66InputValue    OBJECT-TYPE
    SYNTAX           DisplayString
    ACCESS           read-write
    STATUS           mandatory
    DESCRIPTION
    "Current value of station object. Is read-write ."
    ::=   { b14_D66InputTableEntry 3 }



-- ***********************************
-- *
-- *  B14_D66Output table declarations
-- *
-- ***********************************

b14_D66OutputTable   OBJECT-TYPE
    SYNTAX                SEQUENCE OF B14_D66OutputTableEntry
    ACCESS                not-accessible
    STATUS                mandatory
    DESCRIPTION
    "A list of snmp b14_D66Output (read-only) object values."
    ::=  { b14_D66 2 }

b14_D66OutputTableEntry  OBJECT-TYPE
    SYNTAX                B14_D66OutputTableEntry
    ACCESS                not-accessible
    STATUS                mandatory
    DESCRIPTION
    "An b14_D66Output table entry containing data for a specific b14_D66Output."
    INDEX  { b14_D66OutputIndex }  ::=   { b14_D66OutputTable 1 }

B14_D66OutputTableEntry ::= SEQUENCE {
        b14_D66OutputIndex       INTEGER,
        b14_D66OutputName        DisplayString,
        b14_D66OutputValue       DisplayString
    }

b14_D66OutputIndex   OBJECT-TYPE
    SYNTAX           INTEGER(0..2147483647)
    ACCESS           read-only
    STATUS           mandatory
    DESCRIPTION
    "The index in the b14_D66Output table for a particular snmp b14_D66Output
	 object.  Used to address table entries."
    ::=   { b14_D66OutputTableEntry 1 }


b14_D66OutputName    OBJECT-TYPE
    SYNTAX           DisplayString
    ACCESS           read-only
    STATUS           mandatory
    DESCRIPTION
    "Name of station object."
    ::=   { b14_D66OutputTableEntry 2 }

b14_D66OutputValue    OBJECT-TYPE
    SYNTAX           DisplayString
    ACCESS           read-only
    STATUS           mandatory
    DESCRIPTION
    "Current value of station object. Is read-only ."
    ::=   { b14_D66OutputTableEntry 3 }


-- ***********************************
-- *
-- *  Alarm trap declarations
-- *
-- ***********************************


stationAlarm TRAP-TYPE
-- Non-reverse mappable trap
    ENTERPRISE tridiumStation
    VARIABLES { timestamp,
                uuid,
                sourceState,
                ackState,
                ackRequired,
                source,
                alarmClass,
                priority,
                normalTime,
                ackTime,
                user,
                alarmData,
                alarmTransition,
                lastUpdate }
--  Status
--    mandatory
    DESCRIPTION
        "The stationAlarm trap is generated when a Niagara alarm is received
         by an snmp recipient which has routing alarms to a network manager
         enabled.  It contains useful information from the alarm record."
    ::= 1


END
