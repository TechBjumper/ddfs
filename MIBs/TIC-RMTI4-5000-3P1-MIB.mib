-- Toshiba MIB
-- UPS MIB for Toshiba Uninterruptible Power Supplies
--
--{ iso(1) org(3) dod(6) internet(1) private(4) enterprises(1) toshiba(186) 
-- equ(1) equups(19) ticups(2) rmti4 (5) ups50003P1(9) }

--=============================================================================
T50003P1MIB DEFINITIONS ::= BEGIN
--=============================================================================
-- Update : September 20, 2017
-- By     : Edwin Rubio, Toshiba International Corp.
-- For    : 5000 3P1 UPS
-- Revised: upsInputRatedLLVoltage chagned to read only
-- Revised: updated upsBatteryInstallationDate & upsStsCtlCfgPresentDate description
--=============================================================================
-- Update : January 23, 2017
-- By     : Edwin Rubio, Toshiba International Corp.
-- For    : 5000 3P1 First Draft Mib
--=============================================================================

IMPORTS
  DisplayString, TimeStamp, TimeInterval, TestAndIncr, AutonomousType
    FROM SNMPv2-TC
  enterprises
    FROM RFC1155-SMI
  OBJECT-TYPE
    FROM RFC-1212
  TRAP-TYPE
    FROM RFC-1215;

PositiveInteger    ::= INTEGER (0..2147483647)
NonNegativeInteger ::= INTEGER (0..2147483647)

toshiba         OBJECT IDENTIFIER ::= { enterprises 186 }
equ             OBJECT IDENTIFIER ::= { toshiba 1 }
equUPS          OBJECT IDENTIFIER ::= { equ 19 }
ticUPS          OBJECT IDENTIFIER ::= { equUPS 2 }
rmti4           OBJECT IDENTIFIER ::= { ticUPS 5 }
ups50003P1      OBJECT IDENTIFIER ::= { rmti4 9 }

upsIdent     OBJECT IDENTIFIER ::= { ups50003P1 1 }
upsInput     OBJECT IDENTIFIER ::= { ups50003P1 2 }
upsOutput    OBJECT IDENTIFIER ::= { ups50003P1 3 }
upsBypass    OBJECT IDENTIFIER ::= { ups50003P1 4 }
upsDCBus     OBJECT IDENTIFIER ::= { ups50003P1 5 }
upsBattery   OBJECT IDENTIFIER ::= { ups50003P1 6 }
upsStsCtlCfg OBJECT IDENTIFIER ::= { ups50003P1 7 }
upsHistory   OBJECT IDENTIFIER ::= { ups50003P1 8 }
upsDisplay   OBJECT IDENTIFIER ::= { ups50003P1 9 }
upsAlarm     OBJECT IDENTIFIER ::= { ups50003P1 10 }
upsPassword  OBJECT IDENTIFIER ::= { ups50003P1 11 }
upsTrap      OBJECT IDENTIFIER ::= { ups50003P1 12 }

-- ===========================================================================
-- upsIdent - RMTI4 Group 1
-- The UPS Identification Group
-- ===========================================================================

upsIdentManufacturer OBJECT-TYPE
    SYNTAX DisplayString (SIZE (0..16))
    ACCESS read-only
    STATUS mandatory
    DESCRIPTION
        "The name of the UPS manufacturer."
    ::= { upsIdent 1 }

upsIdentTypeform OBJECT-TYPE
    SYNTAX DisplayString (SIZE(0..16))
    ACCESS read-only
    STATUS mandatory
    DESCRIPTION
        "The UPS Typeform (model number)."
    ::= { upsIdent 2 }

upsIdentSerialNumber OBJECT-TYPE
    SYNTAX DisplayString (SIZE(0..16))
    ACCESS read-only
    STATUS mandatory
    DESCRIPTION
        "The UPS Serial Number."
    ::= { upsIdent 3 }

upsIdentSysName OBJECT-TYPE
    SYNTAX DisplayString (SIZE(0..16))
    ACCESS read-write
    STATUS mandatory
    DESCRIPTION
        "A string identifying the UPS. This object should be
         set by the administrator."
    ::= { upsIdent 4 }

upsIdentAttachedDevices OBJECT-TYPE
    SYNTAX DisplayString (SIZE(0..16))
    ACCESS read-write
    STATUS mandatory
    DESCRIPTION
        "A string identifying the devices attached to the
         output(s) of the UPS. This object should be set by
         the administrator."
    ::= { upsIdent 5 }

upsIdentInstallationDate OBJECT-TYPE
    SYNTAX DisplayString (SIZE(8))
    ACCESS read-write
    STATUS mandatory
    DESCRIPTION
        "The UPS installation date in YYYYMMDD format. This 
        object should be set by the administrator."
    ::= { upsIdent 6 }

-- ===========================================================================
-- upsInput - RMTI4 Group 2
-- The UPS Input Data Group 
-- ===========================================================================
	
upsInputLLVoltageAB OBJECT-TYPE
    SYNTAX INTEGER
    UNITS  "1 RMS Volts"
    ACCESS read-only
    STATUS mandatory
    DESCRIPTION
        "The input line to line voltage for AB in RMS volts."
    ::= { upsInput 1 }

upsInputLLVoltageBC OBJECT-TYPE
    SYNTAX INTEGER
    UNITS  "1 RMS Volts"
    ACCESS read-only
    STATUS mandatory
    DESCRIPTION
        "The input line to line voltage for BC in RMS volts."
    ::= { upsInput 2 }

upsInputLLVoltageCA OBJECT-TYPE
    SYNTAX INTEGER
    UNITS  "1 RMS Volts"
    ACCESS read-only
    STATUS mandatory
    DESCRIPTION
        "The input line to line voltage for CA in RMS volts."
    ::= { upsInput 3 }

upsInputFrequency OBJECT-TYPE
    SYNTAX INTEGER
    UNITS  "0.01 Hertz"
    ACCESS read-only
    STATUS mandatory
    DESCRIPTION
        "The input frequency in Hertz."
    ::= { upsInput 4 }
	
upsInputLLVoltagePercentA OBJECT-TYPE
    SYNTAX INTEGER
    UNITS  "Percent"
    ACCESS read-only
    STATUS mandatory
    DESCRIPTION
        "The input voltage for phase A in percent."
    ::= { upsInput 5 }

upsInputLLVoltagePercentB OBJECT-TYPE
    SYNTAX INTEGER
    UNITS  "Percent"
    ACCESS read-only
    STATUS mandatory
    DESCRIPTION
        "The input voltage for phase B in percent."
    ::= { upsInput 6 }

upsInputLLVoltagePercentC OBJECT-TYPE
    SYNTAX INTEGER
    UNITS  "Percent"
    ACCESS read-only
    STATUS mandatory
    DESCRIPTION
        "The input voltage for phase C in percent."
    ::= { upsInput 7 }

upsInputRatedLLVoltage OBJECT-TYPE
    SYNTAX INTEGER
    UNITS  "1 RMS Volts"
    ACCESS read-only
    STATUS mandatory
    DESCRIPTION
        "The rated input line to line voltage."
    ::= { upsInput 8 }

upsInputRatedFrequency OBJECT-TYPE
    SYNTAX INTEGER
    UNITS  "0.01 Hertz"
    ACCESS read-only
    STATUS mandatory
    DESCRIPTION
        "The input rated frequency in Hertz."
    ::= { upsInput 9 }

-- ===========================================================================
-- upsOutput - RMTI4 Group 3
-- The UPS Output Data Group
-- ===========================================================================

upsOutputVoltage OBJECT-TYPE
    SYNTAX INTEGER
    UNITS  "1 RMS Volts"
    ACCESS read-only
    STATUS mandatory
    DESCRIPTION
        "The Output voltage in RMS volts."
    ::= { upsOutput 1 }

upsOutputCurrent OBJECT-TYPE
    SYNTAX INTEGER
    UNITS  "1 Amp"
    ACCESS read-only
    STATUS mandatory
    DESCRIPTION
        "The Output current in amps."
    ::= { upsOutput 2 }

upsOutputFrequency OBJECT-TYPE
    SYNTAX INTEGER
    UNITS  "0.01 Hertz"
    ACCESS read-only
    STATUS mandatory
    DESCRIPTION
        "The Output frequency in Hertz."
    ::= { upsOutput 3 }

upsOutputPowerVATotal OBJECT-TYPE
    SYNTAX INTEGER
    UNITS "Volt-Amp"
    ACCESS read-only
    STATUS mandatory
    DESCRIPTION
        "The output power in VA (total)."
    ::= { upsOutput 4 }

upsOutputVoltagePercent OBJECT-TYPE
    SYNTAX INTEGER
    UNITS  "Percent"
    ACCESS read-only
    STATUS mandatory
    DESCRIPTION
        "The Output voltage in percent."
    ::= { upsOutput 5 }

upsOutputCurrentPercent OBJECT-TYPE
    SYNTAX INTEGER
    UNITS  "Percent"
    ACCESS read-only
    STATUS mandatory
    DESCRIPTION
        "The Output current in percent."
    ::= { upsOutput 6 }

upsOutputTotalActivePowerPercent  OBJECT-TYPE
    SYNTAX INTEGER
    UNITS  "Percent"
    ACCESS read-only
    STATUS mandatory
    DESCRIPTION
        "The total Output power (Watt) in percent."
    ::= { upsOutput 7 }

upsOutputRatedVoltage OBJECT-TYPE
    SYNTAX INTEGER
    UNITS  "1 RMS Voltage"
    ACCESS read-write
    STATUS mandatory
    DESCRIPTION
        "The rated output voltage."
    ::= { upsOutput 8 }

upsOutputRatedFrequency OBJECT-TYPE
    SYNTAX INTEGER
    UNITS  "0.01 Hertz"
    ACCESS read-only
    STATUS mandatory
    DESCRIPTION
        "The Output rated frequency in Hertz."
    ::= { upsOutput 9 }

upsOutputRatedApparentPower OBJECT-TYPE
    SYNTAX INTEGER
    UNITS  "Volt-Amp"
    ACCESS read-only
    STATUS mandatory
    DESCRIPTION
        "The rated output power in volt-amp."
    ::= { upsOutput 10 }

upsOutputVoltageAdjustment OBJECT-TYPE
    SYNTAX DisplayString (SIZE(4))
    ACCESS read-write
    STATUS mandatory
    DESCRIPTION
        "The Output voltage adjustment used to calibrate output voltage. Range: -5 to 5%."
    ::= { upsOutput 11 }

-- ===========================================================================
-- upsBypass - RMTI4 Group 4
-- The UPS Output Data Group
-- ===========================================================================

upsBypassVoltage OBJECT-TYPE
    SYNTAX INTEGER
    UNITS  "1 RMS Volts"
    ACCESS read-only
    STATUS mandatory
    DESCRIPTION
        "The Bypass in RMS volts."
    ::= { upsBypass 1 }

upsBypassCurrent OBJECT-TYPE
    SYNTAX INTEGER
    UNITS  "1 Amp"
    ACCESS read-only
    STATUS mandatory
    DESCRIPTION
        "The Bypass current in amps."
    ::= { upsBypass 2 }

upsBypassFrequency OBJECT-TYPE
    SYNTAX INTEGER
    UNITS  "0.01 Hertz"
    ACCESS read-only
    STATUS mandatory
    DESCRIPTION
        "The Bypass frequency for phase A in Hertz."
    ::= { upsBypass 3 }

upsBypassVoltagePercent OBJECT-TYPE
    SYNTAX INTEGER
    UNITS  "Percent"
    ACCESS read-only
    STATUS mandatory
    DESCRIPTION
        "The Bypass voltage in percent."
    ::= { upsBypass 4 }

upsBypassCurrentPercent OBJECT-TYPE
    SYNTAX INTEGER
    UNITS  "Percent"
    ACCESS read-only
    STATUS mandatory
    DESCRIPTION
        "The Bypass current in percent."
    ::= { upsBypass 5 }

upsBypassRatedVoltage OBJECT-TYPE
    SYNTAX INTEGER
    UNITS  "1 RMS Volts"
    ACCESS read-only
    STATUS mandatory
    DESCRIPTION
        "The rated bypass voltage."
    ::= { upsBypass 6 }

upsBypassRatedCurrent OBJECT-TYPE
    SYNTAX INTEGER
    UNITS  "1 Amp"
    ACCESS read-only
    STATUS mandatory
    DESCRIPTION
        "The rated bypass current."
    ::= { upsBypass 7 }

upsBypassRatedFrequency OBJECT-TYPE
    SYNTAX INTEGER
    UNITS  "0.01 Hertz"
    ACCESS read-only
    STATUS mandatory
    DESCRIPTION
        "The rated bypass frequency."
    ::= { upsBypass 8 }

-- ===========================================================================
-- upsDCBus - RMTI4 Group 5
-- The UPS DC Bus Data Group
-- ===========================================================================
upsDCBusTotalVoltage OBJECT-TYPE
    SYNTAX INTEGER
    UNITS  "DC Volts"
    ACCESS read-only
    STATUS mandatory
    DESCRIPTION
        "The Total DC Bus voltage in DC volts."
    ::= { upsDCBus 1 }

-- ===========================================================================
-- upsBattery RMTI4 Group 6
-- The UPS Battery Data Group
-- ===========================================================================

upsBatteryStatus OBJECT-TYPE
    SYNTAX INTEGER {
         unknown(1),
         batteryNormal(2),
         batteryLow(3),
         batteryDepleted(4),
         batteryDischarging(5)
    }
    ACCESS read-only
    STATUS mandatory
    DESCRIPTION
        "The indication of the capacity remaining in the UPS system's batteries. 
         A value of batteryNormal indicates that the remaining run-time sufficient 
         to handle the load. A value of batteryLow indicates the battery level is 
         low. Continued operation in battery mode will deplete batteries. A value 
         of batteryDepleted indicates that the UPS will be unable to sustain the 
         present load when and if the utility power is lost (including the 
         possibility that the utility power is currently absent and the UPS is 
         unable to sustain the output). A value of batteryDischarging indicates UPS 
         system is in Battery power."
    ::= { upsBattery 1 }

upsElapsedTimeOnBatteryPower OBJECT-TYPE
    SYNTAX NonNegativeInteger
    UNITS   "Second"
    ACCESS read-only
    STATUS mandatory
    DESCRIPTION
        "If the unit is on battery power, the elapsed time
         since the UPS on battery power, or the
         time since the network management subsystem was last
         restarted, whichever is less. Zero shall be returned
         if the unit is not on battery power."
    ::= { upsBattery 2 }
	
upsEstimatedBatteryRuntime OBJECT-TYPE
     SYNTAX PositiveInteger
     UNITS "minutes"
     ACCESS read-only
     STATUS mandatory
     DESCRIPTION
         "An estimate of the time to battery charge depletion 
		 under the present load conditions if the utility power 
		 is off and remains off, or if it were to be lost and 
		 remain off."
     ::= { upsBattery 3 }

upsBatteryVoltage OBJECT-TYPE
    SYNTAX INTEGER
    UNITS  "DC Volt"
    ACCESS read-only
    STATUS mandatory
    DESCRIPTION
        "The magnitude of the present battery voltage in DC Volt."
    ::= { upsBattery 4 }

upsBatteryCurrent OBJECT-TYPE
    SYNTAX INTEGER
    UNITS  "DC Amp"
    ACCESS read-only
    STATUS mandatory
    DESCRIPTION
        "The present battery current in DC Amp."
    ::= { upsBattery 5 }

upsBatteryCapacity OBJECT-TYPE
    SYNTAX INTEGER
    UNITS  "Percent"
    ACCESS read-only
    STATUS mandatory
    DESCRIPTION
        "The present battery capacity in Percent."
    ::= { upsBattery 6 }

upsBatteryChargeStatus OBJECT-TYPE
    SYNTAX INTEGER {
         charging(1),
         equalize(2),
         protective(3),
         discharging(4),
         stopped(5),
         unknown(6)
    }
    ACCESS read-only
    STATUS mandatory
    DESCRIPTION
        "The state of the battery charger."
    ::= { upsBattery 7 }

upsBatteryRatedVoltage OBJECT-TYPE
    SYNTAX INTEGER
    UNITS  "DC Volt"
    ACCESS read-only
    STATUS mandatory
    DESCRIPTION
        "The rated battery voltage in DC Volt."
    ::= { upsBattery 8 }

upsBatteryRatedDischargeCurrent OBJECT-TYPE
    SYNTAX INTEGER
    UNITS  "1 DC Amp"
    ACCESS read-only
    STATUS mandatory
    DESCRIPTION
        "The rated battery discharge current in DC Amp."
    ::= { upsBattery 9 }

upsBatteryEnableEqualizeChargeAfterBackup OBJECT-TYPE
    SYNTAX INTEGER {
        disable(1),
        enable(2)
    }
    ACCESS read-only
    STATUS mandatory
    DESCRIPTION
        "Equalize charge mode after backup."
    ::= { upsBattery 10 }

upsBatteryinSeries OBJECT-TYPE
    SYNTAX INTEGER
    ACCESS read-only
    STATUS mandatory
    DESCRIPTION
        "The number of battery in series."
    ::= { upsBattery 11 }

upsBatteryinParallel OBJECT-TYPE
    SYNTAX INTEGER
    ACCESS read-only
    STATUS mandatory
    DESCRIPTION
        "The number of battery in Parallel."
    ::= { upsBattery 12 }

upsBatteryInstallationDate OBJECT-TYPE
    SYNTAX DisplayString (SIZE(8))
    ACCESS read-write
    STATUS mandatory
    DESCRIPTION
        "The battery install date. This object should be 
        set by the administrator and entered as YYYYMMDD."
    ::= { upsBattery 13 }

-- ===========================================================================
-- upsStsCtlCfg RMTI4 Group 7
-- The UPS status, control and configuration
-- ===========================================================================

upsStsCtlCfgPresentDate OBJECT-TYPE
    SYNTAX INTEGER
    ACCESS read-write
    STATUS mandatory
    DESCRIPTION 
        "The present date of the UPS. This is configurable by Administrator. DDddmmyy, for example set 04160715 is Thursday July 16, 2015 (Note: DD 00 - Sunday)."
    ::= { upsStsCtlCfg 1 }

upsStsCtlCfgPresentTime OBJECT-TYPE
    SYNTAX NonNegativeInteger
    ACCESS read-write
    STATUS mandatory
    DESCRIPTION 
        "The present time of the UPS. This is configurable by Administrator. 24 Hour Format: HHMMSS. For example, 140600 is 02:06PM "
    ::= { upsStsCtlCfg 2 }

upsStsCtlCfgPresentMode OBJECT-TYPE
    SYNTAX INTEGER {
        bypassOnly(1),
        startInverter(2),
        bypassInverterOn(3),
        stopInverter(4),
        online(5),
        backup(6),
        transferring(7),
        unknown(8)
    }
    ACCESS read-only
    STATUS mandatory
    DESCRIPTION
        "The present mode of the UPS system."
    ::= { upsStsCtlCfg 3 }
	
upsStsCtlCfgUserDefinedOverloadSetPoint OBJECT-TYPE
    SYNTAX INTEGER
	UNITS "%"
    ACCESS read-write
    STATUS mandatory
    DESCRIPTION 
        "The maximum output load % defined by the user. This is configurable by Administrator."
    ::= { upsStsCtlCfg 4 }

-- ===========================================================================
-- upsHistory RMTI4 Group 8
-- The UPS History Data Group
-- ===========================================================================

upsHistorySysOperationTime OBJECT-TYPE
    SYNTAX NonNegativeInteger
    UNITS  "Minute"
    ACCESS read-only
    STATUS mandatory
    DESCRIPTION 
        "The amount of time the UPS has been ON."
    ::= { upsHistory 1 }

upsHistoryBackupOperationTime OBJECT-TYPE
    SYNTAX NonNegativeInteger
    UNITS  "Second"
    ACCESS read-only
    STATUS mandatory
    DESCRIPTION 
        "The amount of time the UPS has been in Backup Mode in seconds."
    ::= { upsHistory 2 }

upsHistoryTotalNumFaults OBJECT-TYPE
    SYNTAX NonNegativeInteger
    ACCESS read-only
    STATUS mandatory
    DESCRIPTION 
        "Total number of faults that has occurred on the UPS."
    ::= { upsHistory 3 }

upsHistoryTotalNumWarnings OBJECT-TYPE
    SYNTAX NonNegativeInteger
    ACCESS read-only
    STATUS mandatory
    DESCRIPTION 
        "Total number of warnings that has occurred on the UPS."
    ::= { upsHistory 4 }

upsHistoryTotalNumOperationRecords OBJECT-TYPE
    SYNTAX NonNegativeInteger
    ACCESS read-only
    STATUS mandatory
    DESCRIPTION 
        "The number of mode changes that has occurred."
    ::= { upsHistory 5 }

upsHistoryTotalNumSystemRecords OBJECT-TYPE
    SYNTAX NonNegativeInteger
    ACCESS read-only
    STATUS mandatory
    DESCRIPTION 
        "The number of system changes that has occurred."
    ::= { upsHistory 6 }

upsHistoryTotalNumBackup OBJECT-TYPE
    SYNTAX NonNegativeInteger
    ACCESS read-only
    STATUS mandatory
    DESCRIPTION 
        "Total number of times the UPS has been in Backup mode."
    ::= { upsHistory 7 }

-- ===========================================================================
-- upsDisplay RMTI4 Group 9
-- The UPS Display Data Group
-- ===========================================================================
upsDisplayFirmwareVersion OBJECT-TYPE
    SYNTAX DisplayString (SIZE(0..15))
    ACCESS read-only
    STATUS mandatory
    DESCRIPTION
        "The firmware version of the display."
    ::= { upsDisplay 1 }

upsDisplayFirmwareBuildDate OBJECT-TYPE
    SYNTAX DisplayString (SIZE(0..15))
    ACCESS read-only
    STATUS mandatory
    DESCRIPTION
        "The firmware build date of the display."
    ::= { upsDisplay 2 }

upsDisplayFirmwareBuiltTime OBJECT-TYPE
    SYNTAX DisplayString (SIZE(0..15))
    ACCESS read-only
    STATUS mandatory
    DESCRIPTION
        "The firmware build time of the display."
    ::= { upsDisplay 3 }

upsDisplayRMTIInstallDate OBJECT-TYPE
    SYNTAX DisplayString(SIZE(8))
    ACCESS read-only
    STATUS mandatory
    DESCRIPTION
        "The RMTI installation date."
    ::= { upsDisplay 4 }

upsDisplayRMTIVersion OBJECT-TYPE
    SYNTAX DisplayString(SIZE(0..15))
    ACCESS read-only
    STATUS mandatory
    DESCRIPTION
        "The RMTI installation date."
    ::= { upsDisplay 5 }

upsDisplayRMTIStatus OBJECT-TYPE
    SYNTAX INTEGER {
        uninstalled(1),
        installed(2)
    }          
    ACCESS read-only
    STATUS mandatory
    DESCRIPTION
        "Shows the installation status of the RMTI."
    ::= { upsDisplay 6 }

upsDisplayRMTIDataLink OBJECT-TYPE
    SYNTAX INTEGER {
        unknown(1),
        link-down(2),
        link-up(3)
    }          
    ACCESS read-only
    STATUS mandatory
    DESCRIPTION
        "Shows the data status of the RMTI."
    ::= { upsDisplay 7 }

upsDisplayRMTINetworkLink OBJECT-TYPE
    SYNTAX INTEGER {
        unknown(1),
        link-down(2),
        link-up(3)
    }          
    ACCESS read-only
    STATUS mandatory
    DESCRIPTION
        "Shows the network status of the RMTI."
    ::= { upsDisplay 8 }

-- ===========================================================================
-- upsAlarm RMTI4 Group 10
-- The UPS Alarm List
-- ===========================================================================
upsAlarmsPresent OBJECT-TYPE
    SYNTAX Gauge32
    ACCESS read-only
    STATUS mandatory
    DESCRIPTION
        "The present number of active alarm conditions."
    ::= { upsAlarm 1 }

upsAlarmTable OBJECT-TYPE
    SYNTAX SEQUENCE OF UpsAlarmEntry
    ACCESS not-accessible
    STATUS mandatory
    DESCRIPTION
        "A list of alarm table entries. The table contains
         zero, one, or many rows at any moment, depending upon
         the number of alarm conditions in effect. The table
         is initially empty at agent startup. The agent
         creates a row in the table each time a condition is
         detected and deletes that row when that condition no
         longer pertains. The agent creates the first row with
         upsAlarmId equal to 1, and increments the value of
         upsAlarmId each time a new row is created, wrapping to
         the first free value greater than or equal to 1 when
         the maximum value of upsAlarmId would otherwise be
         exceeded. Consequently, after multiple operations,
         the table may become sparse, e.g., containing entries
         for rows 95, 100, 101, and 203 and the entries should
         not be assumed to be in chronological order because
         upsAlarmId might have wrapped.

         Alarms are named by an OBJECT IDENTIFIER,
         upsAlarmDescr, to allow a single table to
         reflect well known alarms plus alarms defined by a
         particular implementation, i.e., as documented in the
         private enterprise MIB definition for the device. No
         two rows will have the same value of upsAlarmDescr,
         since alarms define conditions. In order to meet this
         requirement, care should be taken in the definition of
         alarm conditions to insure that a system cannot enter
         the same condition multiple times simultaneously.

         The number of rows in the table at any given time is
         reflected by the value of upsAlarmsPresent."
    ::= { upsAlarm  2 }

upsAlarmEntry OBJECT-TYPE
    SYNTAX UpsAlarmEntry
    ACCESS not-accessible
    STATUS mandatory
    DESCRIPTION
        "An entry containing information applicable to a
         particular alarm."
    INDEX { upsAlarmId }
    ::= { upsAlarmTable  1 }

UpsAlarmEntry ::=
    SEQUENCE {
        upsAlarmId              PositiveInteger,
        upsAlarmDescr           AutonomousType,
        upsAlarmTime            TimeStamp
    }

-- ===========================================================================
-- upsAlarmTable/upsAlarmEntry/upsAlarmId
-- ===========================================================================
upsAlarmId OBJECT-TYPE
    SYNTAX PositiveInteger
    ACCESS not-accessible
    STATUS mandatory
    DESCRIPTION
        "An unique identifier for an alarm condition. This
         value must remain constant."
    ::= { upsAlarmEntry 1 }

upsAlarmDescr OBJECT-TYPE
    SYNTAX AutonomousType
    ACCESS read-only
    STATUS mandatory
    DESCRIPTION
        "A reference to an alarm description object. The
         object referenced should not be accessible, but rather
         be used to provide a unique description of the alarm
         condition."
    ::= { upsAlarmEntry 2 }

-- ===========================================================================
-- .../upsAlarmTime
-- ===========================================================================
upsAlarmTime OBJECT-TYPE
    SYNTAX TimeStamp
    ACCESS read-only
    STATUS mandatory
    DESCRIPTION
        "The value of upsConfigSystemTime when the alarm condition was
          detected. If the alarm condition was detected at the
          time of agent startup and presumably existed before
          agent startup, the value of upsAlarmTime shall equal 0."
    ::= { upsAlarmEntry 3 }

upsWellKnownAlarms OBJECT IDENTIFIER ::= { upsAlarm  3 }

upsAlarmOpenFuseFault OBJECT-TYPE 
    SYNTAX INTEGER
    ACCESS read-only
    STATUS mandatory
    DESCRIPTION
        "Fault: An open fuse reported."
    ::= { upsWellKnownAlarms 1 }

upsAlarmUserFault OBJECT-TYPE 
    SYNTAX INTEGER
    ACCESS read-only
    STATUS mandatory
    DESCRIPTION
        "Fault: User fault."
    ::= { upsWellKnownAlarms 2 }

upsAlarmInverterUndervoltageStartupFault OBJECT-TYPE 
    SYNTAX INTEGER
    ACCESS read-only
    STATUS mandatory
    DESCRIPTION
        "Fault: Inverter Undervoltage during startup."
    ::= { upsWellKnownAlarms 3 }

upsAlarmEPOFault OBJECT-TYPE 
    SYNTAX INTEGER
    ACCESS read-only
    STATUS mandatory
    DESCRIPTION
        "Fault: EPO has tripped."
    ::= { upsWellKnownAlarms 4 }

upsAlarmControlPowerSupplyFault OBJECT-TYPE 
    SYNTAX INTEGER
    ACCESS read-only
    STATUS mandatory
    DESCRIPTION
        "Fault: Control Power Supply Fault."
    ::= { upsWellKnownAlarms 5 }

upsAlarmDCBusOvercurrentFault OBJECT-TYPE 
    SYNTAX INTEGER
    ACCESS read-only
    STATUS mandatory
    DESCRIPTION
        "Fault: A DC Bus Overcurrent has been reported."
    ::= { upsWellKnownAlarms 6 }

upsAlarmBatteryDepletedFault OBJECT-TYPE 
    SYNTAX INTEGER
    ACCESS read-only
    STATUS mandatory
    DESCRIPTION
        "Fault: A battery depleted fault reported."
    ::= { upsWellKnownAlarms 7 }

upsAlarmFrequentErrorsFault OBJECT-TYPE 
    SYNTAX INTEGER
    ACCESS read-only
    STATUS mandatory
    DESCRIPTION
        "Fault: Frequent Errors (Warnings Occurring Frequently)."
    ::= { upsWellKnownAlarms 8 }

upsAlarmUPSOverheatFault OBJECT-TYPE 
    SYNTAX INTEGER
    ACCESS read-only
    STATUS mandatory
    DESCRIPTION
        "Fault: A UPS Overhead fault reported."
    ::= { upsWellKnownAlarms 9 }

upsAlarmDCBusUndervoltageStartupFault OBJECT-TYPE 
    SYNTAX INTEGER
    ACCESS read-only
    STATUS mandatory
    DESCRIPTION
        "Fault: A DC Bus Undervoltage during startup fault reported."
    ::= { upsWellKnownAlarms 10 }

upsAlarmLoadedDefaultsFault OBJECT-TYPE 
    SYNTAX INTEGER
    ACCESS read-only
    STATUS mandatory
    DESCRIPTION
        "Fault: The Control Board Eeprom loaded default parameters fault."
    ::= { upsWellKnownAlarms 11 }

upsAlarmWatchdogResetFault OBJECT-TYPE 
    SYNTAX INTEGER
    ACCESS read-only
    STATUS mandatory
    DESCRIPTION
        "Fault: uC Watchdog Reset Occurred fault."
    ::= { upsWellKnownAlarms 12 }

upsAlarmChopperOvercurrentWarning OBJECT-TYPE 
    SYNTAX INTEGER
    ACCESS read-only
    STATUS mandatory
    DESCRIPTION
        "Warning: A chopper overcurrent warning reported."
    ::= { upsWellKnownAlarms 13 }

upsAlarmInverterUndervoltageWarning OBJECT-TYPE 
    SYNTAX INTEGER
    ACCESS read-only
    STATUS mandatory
    DESCRIPTION
        "Warning: An Inverter Undervoltage warning reported."
    ::= { upsWellKnownAlarms 14 }

upsAlarmInverterOvervoltageWarning OBJECT-TYPE 
    SYNTAX INTEGER
    ACCESS read-only
    STATUS mandatory
    DESCRIPTION
        "Warning: An Inverter Overvoltage warning reported."
    ::= { upsWellKnownAlarms 15 }

upsAlarmInverterOvercurrentWarning OBJECT-TYPE 
    SYNTAX INTEGER
    ACCESS read-only
    STATUS mandatory
    DESCRIPTION
        "Warning: An Inverter Overcurrent warning reported."
    ::= { upsWellKnownAlarms 16 }

upsAlarmDCOvervoltageWarning OBJECT-TYPE 
    SYNTAX INTEGER
    ACCESS read-only
    STATUS mandatory
    DESCRIPTION
        "Warning: DC Overvoltage warning reported."
    ::= { upsWellKnownAlarms 17 }

upsAlarmInverterOverloadWarning  OBJECT-TYPE 
    SYNTAX INTEGER
    ACCESS read-only
    STATUS mandatory
    DESCRIPTION
        "Warning: Inverter Overload warning reported."
    ::= { upsWellKnownAlarms 18 }

upsAlarmACInputUndervoltageStartupWarning OBJECT-TYPE 
    SYNTAX INTEGER
    ACCESS read-only
    STATUS mandatory
    DESCRIPTION
        "Warning: AC Input Undervoltage Startup warning reported."
    ::= { upsWellKnownAlarms 19 }

upsAlarmBatteryVoltageBelowShutdownWarning OBJECT-TYPE 
    SYNTAX INTEGER
    ACCESS read-only
    STATUS mandatory
    DESCRIPTION
        "Warning: Battery Voltage Below Shutdown warning reported."
    ::= { upsWellKnownAlarms 20 }

upsAlarmBypassOvervoltageWarning OBJECT-TYPE
    SYNTAX INTEGER
    ACCESS read-only
    STATUS mandatory
    DESCRIPTION
        "Warning: Bypass Overvoltage warning reported."
    ::= { upsWellKnownAlarms 21 }

upsAlarmChopperInverterOverheatWarning OBJECT-TYPE
    SYNTAX INTEGER
    ACCESS read-only
    STATUS mandatory
    DESCRIPTION
        "Warning: Chopper Inverter Overheat warning reported."
    ::= { upsWellKnownAlarms 22 }

upsAlarmBypassUndervoltageWarning OBJECT-TYPE
    SYNTAX INTEGER
    ACCESS read-only
    STATUS mandatory
    DESCRIPTION
        "Warning: Bypass Undervoltage warning reported."
    ::= { upsWellKnownAlarms 23 }

upsAlarmBypassFrequencyErrorWarning OBJECT-TYPE
    SYNTAX INTEGER
    ACCESS read-only
    STATUS mandatory
    DESCRIPTION
        "Warning: Bypass Frequency Error warning reported."
    ::= { upsWellKnownAlarms 24 }

upsAlarmBatteryLowWarning OBJECT-TYPE 
    SYNTAX INTEGER
    ACCESS read-only
    STATUS mandatory
    DESCRIPTION
        "Warning: Battery Low warning reported."
    ::= { upsWellKnownAlarms 25 }

upsAlarmBypassModeWarning OBJECT-TYPE 
    SYNTAX INTEGER
    ACCESS read-only
    STATUS mandatory
    DESCRIPTION
        "Warning: Bypass Mode warning reported."
    ::= { upsWellKnownAlarms 26 }

upsAlarmInputOvervoltageWarning OBJECT-TYPE 
    SYNTAX INTEGER
    ACCESS read-only
    STATUS mandatory
    DESCRIPTION
        "Warning: Input Overvoltage warning reported."
    ::= { upsWellKnownAlarms 27 }

upsAlarmInputUndervoltageWarning OBJECT-TYPE 
    SYNTAX INTEGER
    ACCESS read-only
    STATUS mandatory
    DESCRIPTION
        "Warning: Input Undervoltage warning reported."
    ::= { upsWellKnownAlarms 28 }

upsAlarmInputPhaseRotationErrorWarning OBJECT-TYPE 
    SYNTAX INTEGER
    ACCESS read-only
    STATUS mandatory
    DESCRIPTION
        "Warning: Input Phase Rotation Error warning reported."
    ::= { upsWellKnownAlarms 29 }

upsAlarmInputFrequencyErrorWarning OBJECT-TYPE 
    SYNTAX INTEGER
    ACCESS read-only
    STATUS mandatory
    DESCRIPTION
        "Warning: Input Frequency Error warning reported."
    ::= { upsWellKnownAlarms 30 }

upsAlarmBatteryOverheatWarning OBJECT-TYPE 
    SYNTAX INTEGER
    ACCESS read-only
    STATUS mandatory
    DESCRIPTION
        "Warning: Battery Overheat warning reported."
    ::= { upsWellKnownAlarms 31 }

upsAlarmASYNCWarning OBJECT-TYPE 
    SYNTAX INTEGER
    ACCESS read-only
    STATUS mandatory
    DESCRIPTION
        "Warning: Input and Output are asynchronous warning reported."
    ::= { upsWellKnownAlarms 32 }

upsAlarm72BBreakerOpenWarning OBJECT-TYPE 
    SYNTAX INTEGER
    ACCESS read-only
    STATUS mandatory
    DESCRIPTION
        "Warning: 72B Battery Breaker Open warning reported."
    ::= { upsWellKnownAlarms 33 }
	
upsAlarmUserWarning2Warning OBJECT-TYPE 
    SYNTAX INTEGER
    ACCESS read-only
    STATUS mandatory
    DESCRIPTION
        "Warning: User Warning Type 2 Warning (restart will  occur)."
    ::= { upsWellKnownAlarms 34 }

upsAlarmUserWarning3Warning OBJECT-TYPE 
    SYNTAX INTEGER
    ACCESS read-only
    STATUS mandatory
    DESCRIPTION
        "Warning: User Warning Type 3 Warning (restart will  not occur)."
    ::= { upsWellKnownAlarms 35 }

upsAlarmUserDefinedOverloadWarning OBJECT-TYPE 
    SYNTAX INTEGER
    ACCESS read-only
    STATUS mandatory
    DESCRIPTION
        "Warning: User Defined Overload warning reported."
    ::= { upsWellKnownAlarms 36 }

upsAlarmSYNCInfo OBJECT-TYPE 
    SYNTAX INTEGER
    ACCESS read-only
    STATUS mandatory
    DESCRIPTION
        "Info: Bypass and output are synchronous info reported."
    ::= { upsWellKnownAlarms 37 }

upsAlarmInverterOnInfo OBJECT-TYPE 
    SYNTAX INTEGER
    ACCESS read-only
    STATUS mandatory
    DESCRIPTION
        "Info: Inverter On info reported."
    ::= { upsWellKnownAlarms 38 }

upsAlarmBypassModeInfo OBJECT-TYPE 
    SYNTAX INTEGER
    ACCESS read-only
    STATUS mandatory
    DESCRIPTION
        "Info: Bypass Mode info reported."
    ::= { upsWellKnownAlarms 39 }

upsAlarmInputPowerFailureInfo OBJECT-TYPE 
    SYNTAX INTEGER
    ACCESS read-only
    STATUS mandatory
    DESCRIPTION
        "Info: Input Power Failure info reported."
    ::= { upsWellKnownAlarms 40 }

upsAlarmFaultInfo OBJECT-TYPE 
    SYNTAX INTEGER
    ACCESS read-only
    STATUS mandatory
    DESCRIPTION
        "Info: Fault info reported."
    ::= { upsWellKnownAlarms 41 }

upsAlarmWarningInfo OBJECT-TYPE 
    SYNTAX INTEGER
    ACCESS read-only
    STATUS mandatory
    DESCRIPTION
        "Info: Warning info reported."
    ::= { upsWellKnownAlarms 42 }

upsAlarmEPOInfo OBJECT-TYPE 
    SYNTAX INTEGER
    ACCESS read-only
    STATUS mandatory
    DESCRIPTION
        "Info: EPO info reported."
    ::= { upsWellKnownAlarms 43 }

upsAlarmGateCheckInfo OBJECT-TYPE 
    SYNTAX INTEGER
    ACCESS read-only
    STATUS mandatory
    DESCRIPTION
        "Info: Gate Check info reported."
    ::= { upsWellKnownAlarms 44 }

upsAlarmPrechargeTestModeInfo OBJECT-TYPE 
    SYNTAX INTEGER
    ACCESS read-only
    STATUS mandatory
    DESCRIPTION
        "Info: Precharge Test Mode info reported."
    ::= { upsWellKnownAlarms 45 }

upsAlarmEqualizeChargingInfo OBJECT-TYPE 
    SYNTAX INTEGER
    ACCESS read-only
    STATUS mandatory
    DESCRIPTION
        "Info: Equalize Charging info reported."
    ::= { upsWellKnownAlarms 46 }

upsAlarm72BBreakerClosedInfo OBJECT-TYPE 
    SYNTAX INTEGER
    ACCESS read-only
    STATUS mandatory
    DESCRIPTION
        "Info: 72B Battery Breaker Closed info reported."
    ::= { upsWellKnownAlarms 47 }

upsAlarmProtectionChargingInfo OBJECT-TYPE 
    SYNTAX INTEGER
    ACCESS read-only
    STATUS mandatory
    DESCRIPTION
        "Info: Protection Charging info reported."
    ::= { upsWellKnownAlarms 48 }

upsAlarmBackupModeInfo OBJECT-TYPE 
    SYNTAX INTEGER
    ACCESS read-only
    STATUS mandatory
    DESCRIPTION
        "Info: Backup Mode info reported."
    ::= { upsWellKnownAlarms 49 }

upsAlarmOnlineModeInfo OBJECT-TYPE 
    SYNTAX INTEGER
    ACCESS read-only
    STATUS mandatory
    DESCRIPTION
        "Info: Online Mode (normal) info reported."
    ::= { upsWellKnownAlarms 50 }

upsAlarmUPSOverload110PercentInfo OBJECT-TYPE 
    SYNTAX INTEGER
    ACCESS read-only
    STATUS mandatory
    DESCRIPTION
        "Info: UPS Overload 110 Percent info reported."
    ::= { upsWellKnownAlarms 51 }

upsAlarmRemoteOperationOccurredInfo OBJECT-TYPE 
    SYNTAX INTEGER
    ACCESS read-only
    STATUS mandatory
    DESCRIPTION
        "Info: Remote Operation Occurred info reported."
    ::= { upsWellKnownAlarms 52 }

upsAlarm52RInputOpenInfo OBJECT-TYPE 
    SYNTAX INTEGER
    ACCESS read-only
    STATUS mandatory
    DESCRIPTION
        "Info: 52R Input Contactor has not been commanded closed or has been commanded open."
    ::= { upsWellKnownAlarms 53 }

upsAlarmUserChopperDisabledInfo OBJECT-TYPE
    SYNTAX INTEGER
    ACCESS read-only
    STATUS mandatory
    DESCRIPTION
        "Info: User has disabled chopper through external I/O info reported."
    ::= { upsWellKnownAlarms 54 }
	
upsAlarmEEPROMDisabledInfo OBJECT-TYPE
    SYNTAX INTEGER
    ACCESS read-only
    STATUS mandatory
    DESCRIPTION
        "Info: Eprom Writes to the control board were disabled.  The user will not be able to change any control board parameters info reported."
    ::= { upsWellKnownAlarms 55 }

-- ===========================================================================
-- upsPassword  RMTI4 Group 11
-- The UPS Password group
-- ===========================================================================
upsPwdAdminCurrentAccessLevel OBJECT-TYPE
    SYNTAX DisplayString (SIZE (0..15))
    ACCESS read-only
    STATUS mandatory
    DESCRIPTION
        "The administrator access level."
    ::= { upsPassword 1 }

upsPwdAdminCurrentPswd OBJECT-TYPE
    SYNTAX DisplayString (SIZE (0..15))
    ACCESS read-write
    STATUS mandatory
    DESCRIPTION
        "The current password."
    ::= { upsPassword 2 }

upsPwdResetAdminPWD OBJECT-TYPE
    SYNTAX DisplayString (SIZE (0..7))
    ACCESS read-write
    STATUS mandatory
    DESCRIPTION
        "Reset admin password."
    ::= { upsPassword 3 }

-- ===========================================================================
-- upsTraps - Group 12
-- Traps group
-- ===========================================================================

upsTrapOpenFuseFault TRAP-TYPE
    ENTERPRISE ups50003P1
    DESCRIPTION
        "Fault: An open fuse reported."
    ::= 1

upsTrapOpenFuseFaultClear TRAP-TYPE
    ENTERPRISE ups50003P1
    DESCRIPTION
        "Fault Clear: An open fuse reported."
    ::= 2

upsTrapUserFault TRAP-TYPE
    ENTERPRISE ups50003P1
    DESCRIPTION
        "Fault: User fault."
    ::= 3

upsTrapUserFaultClear TRAP-TYPE
    ENTERPRISE ups50003P1
    DESCRIPTION
        "Fault Clear: User fault."
    ::= 4

upsTrapInverterUndervoltageStartupFault TRAP-TYPE
    ENTERPRISE ups50003P1
    DESCRIPTION
        "Fault: Inverter Undervoltage during startup."
    ::= 5

upsTrapInverterUndervoltageStartupFaultClear TRAP-TYPE
    ENTERPRISE ups50003P1
    DESCRIPTION
        "Fault Clear: Inverter Undervoltage during startup."
    ::= 6

upsTrapEPOFault TRAP-TYPE 
    ENTERPRISE ups50003P1
    DESCRIPTION
        "Fault: EPO has tripped."
    ::= 7

upsTrapEPOFaultClear TRAP-TYPE 
    ENTERPRISE ups50003P1
    DESCRIPTION
        "Fault Clear: EPO has tripped."
    ::= 8

upsTrapControlPowerSupplyFault TRAP-TYPE 
    ENTERPRISE ups50003P1
    DESCRIPTION
        "Fault: Control Power Supply Fault."
    ::= 9

upsTrapControlPowerSupplyFaultClear TRAP-TYPE 
    ENTERPRISE ups50003P1
    DESCRIPTION
        "Fault Clear: Control Power Supply Fault."
    ::= 10

upsTrapDCBusOvercurrentFault TRAP-TYPE 
    ENTERPRISE ups50003P1
    DESCRIPTION
        "Fault: A DC Bus Overcurrent has been reported."
    ::= 11

upsTrapDCBusOvercurrentFaultClear TRAP-TYPE 
    ENTERPRISE ups50003P1
    DESCRIPTION
        "Fault Clear: A DC Bus Overcurrent has been reported."
    ::= 12

upsTrapBatteryDepletedFault TRAP-TYPE 
    ENTERPRISE ups50003P1
    DESCRIPTION
        "Fault: A battery depleted fault reported."
    ::= 13

upsTrapBatteryDepletedFaultClear TRAP-TYPE 
    ENTERPRISE ups50003P1
    DESCRIPTION
        "Fault Clear: A battery depleted fault reported."
    ::= 14

upsTrapFrequentErrorsFault TRAP-TYPE 
    ENTERPRISE ups50003P1
    DESCRIPTION
        "Fault:Frequent Errors (Warnings Occurring Frequently)."
    ::= 15

upsTrapFrequentErrorsFaultClear TRAP-TYPE 
    ENTERPRISE ups50003P1
    DESCRIPTION
        "Fault Clear: Frequent Errors (Warnings Occurring Frequently)."
    ::= 16

upsTrapUPSOverheatFault TRAP-TYPE 
    ENTERPRISE ups50003P1
    DESCRIPTION
        "Fault: A UPS Overhead fault reported."
    ::= 17

upsTrapUPSOverheatFaultClear TRAP-TYPE 
    ENTERPRISE ups50003P1
    DESCRIPTION
        "Fault Clear: A UPS Overhead fault reported."
    ::= 18

upsTrapDCBusUndervoltageStartupFault TRAP-TYPE 
    ENTERPRISE ups50003P1
    DESCRIPTION
        "Fault: A DC Bus Undervoltage during startup fault reported."
    ::= 19

upsTrapDCBusUndervoltageStartupFaultClear TRAP-TYPE 
    ENTERPRISE ups50003P1
    DESCRIPTION
        "Fault Clear: A DC Bus Undervoltage during startup fault reported."
    ::= 20

upsTrapLoadedDefaultsFault TRAP-TYPE 
    ENTERPRISE ups50003P1
    DESCRIPTION
        "Fault: The Control Board Eeprom loaded default parameters fault."
    ::= 21

upsTrapLoadedDefaultsFaultClear TRAP-TYPE 
    ENTERPRISE ups50003P1
    DESCRIPTION
        "Fault Clear: The Control Board Eeprom loaded default parameters fault."
    ::= 22

upsTrapWatchdogResetFault TRAP-TYPE 
    ENTERPRISE ups50003P1
    DESCRIPTION
        "Fault: uC Watchdog Reset Occurred fault."
    ::= 23

upsTrapWatchdogResetFaultClear TRAP-TYPE 
    ENTERPRISE ups50003P1
    DESCRIPTION
        "Fault Clear: uC Watchdog Reset Occurred fault."
    ::= 24

upsTrapChopperOvercurrentWarning TRAP-TYPE 
    ENTERPRISE ups50003P1
    DESCRIPTION
        "Warning: A chopper overcurrent warning reported."
    ::= 25

upsTrapChopperOvercurrentWarningClear TRAP-TYPE 
    ENTERPRISE ups50003P1
    DESCRIPTION
        "Warning Clear: A chopper overcurrent warning reported."
    ::= 26

upsTrapInverterUndervoltageWarning TRAP-TYPE 
    ENTERPRISE ups50003P1
    DESCRIPTION
        "Warning: An Inverter Undervoltage warning reported."
    ::= 27

upsTrapInverterUndervoltageWarningClear TRAP-TYPE 
    ENTERPRISE ups50003P1
    DESCRIPTION
        "Warning Clear: An Inverter Undervoltage warning reported."
    ::= 28

upsTrapInverterOvervoltageWarning TRAP-TYPE
    ENTERPRISE ups50003P1
    DESCRIPTION
        "Warning: An Inverter Overvoltage warning reported."
    ::= 29

upsTrapInverterOvervoltageWarningClear TRAP-TYPE
    ENTERPRISE ups50003P1
    DESCRIPTION
        "Warning Clear: An Inverter Overvoltage warning reported."
    ::= 30

upsTrapInverterOvercurrentWarning TRAP-TYPE 
    ENTERPRISE ups50003P1
    DESCRIPTION
        "Warning: An Inverter Overcurrent warning reported."
    ::= 31

upsTrapInverterOvercurrentWarningClear TRAP-TYPE 
    ENTERPRISE ups50003P1
    DESCRIPTION
        "Warning Clear: An Inverter Overcurrent warning reported."
    ::= 32

upsTrapDCOvervoltageWarning TRAP-TYPE
    ENTERPRISE ups50003P1
    DESCRIPTION
        "Warning: DC Overvoltage warning reported."
    ::= 33

upsTrapDCOvervoltageWarningClear TRAP-TYPE
    ENTERPRISE ups50003P1
    DESCRIPTION
        "Warning Clear: DC Overvoltage warning reported."
    ::= 34

upsTrapInverterOverloadWarning TRAP-TYPE
    ENTERPRISE ups50003P1
    DESCRIPTION
        "Warning: Inverter Overload warning reported."
    ::= 35

upsTrapInverterOverloadWarningClear TRAP-TYPE
    ENTERPRISE ups50003P1
    DESCRIPTION
        "Warning Clear: Inverter Overload warning reported."
    ::= 36

upsTrapACInputUndervoltageStartupWarning TRAP-TYPE 
    ENTERPRISE ups50003P1
    DESCRIPTION
        "Warning: AC Input Undervoltage Startup warning reported."
    ::= 37

upsTrapACInputUndervoltageStartupWarningClear TRAP-TYPE 
    ENTERPRISE ups50003P1 
    DESCRIPTION
        "Warning Clear: AC Input Undervoltage Startup warning reported."
    ::= 38

upsTrapBatteryVoltageBelowShutdownWarning TRAP-TYPE 
    ENTERPRISE ups50003P1
    DESCRIPTION
        "Warning: Battery Voltage Below Shutdown warning reported."
    ::= 39

upsTrapBatteryVoltageBelowShutdownWarningClear TRAP-TYPE 
    ENTERPRISE ups50003P1
    DESCRIPTION
        "Warning Clear: Battery Voltage Below Shutdown warning reported."
    ::= 40

upsTrapBypassOvervoltageWarning TRAP-TYPE 
    ENTERPRISE ups50003P1 
    DESCRIPTION
        "Warning: Bypass Overvoltage warning reported."
    ::= 41

upsTrapBypassOvervoltageWarningClear TRAP-TYPE 
    ENTERPRISE ups50003P1 
    DESCRIPTION
        "Warning Clear: Bypass Overvoltage warning reported."
    ::= 42

upsTrapChopperInverterOverheatWarning TRAP-TYPE 
    ENTERPRISE ups50003P1
    DESCRIPTION
        "Warning: Chopper Inverter Overheat warning reported."
    ::= 43

upsTrapChopperInverterOverheatWarningClear TRAP-TYPE 
    ENTERPRISE ups50003P1
    DESCRIPTION
        "Warning Clear: Chopper Inverter Overheat warning reported."
    ::= 44

upsTrapBypassUndervoltageWarning TRAP-TYPE 
    ENTERPRISE ups50003P1
    DESCRIPTION
        "Warning: Bypass Undervoltage warning reported."
    ::= 45

upsTrapBypassUndervoltageWarningClear TRAP-TYPE 
    ENTERPRISE ups50003P1
    DESCRIPTION
        "Warning Clear: Bypass Undervoltage warning reported."
    ::= 46

upsTrapBypassFrequencyError TRAP-TYPE 
    ENTERPRISE ups50003P1
    DESCRIPTION
        "Warning: Bypass Frequency Error warning reported."
    ::= 47

upsTrapBypassFrequencyErrorClear TRAP-TYPE 
    ENTERPRISE ups50003P1
    DESCRIPTION
        "Warning Clear: Bypass Frequency Error warning reported."
    ::= 48

upsTrapBatteryLowWarning TRAP-TYPE 
    ENTERPRISE ups50003P1
    DESCRIPTION
        "Warning: Battery Low warning reported."
    ::= 49

upsTrapBatteryLowWarningClear TRAP-TYPE 
    ENTERPRISE ups50003P1
    DESCRIPTION
        "Warning Clear: Battery Low warning reported."
    ::= 50

upsTrapBypassModeWarning TRAP-TYPE 
    ENTERPRISE ups50003P1
    DESCRIPTION
        "Warning: Bypass Mode warning reported."
    ::= 51

upsTrapBypassModeWarningClear TRAP-TYPE 
    ENTERPRISE ups50003P1
    DESCRIPTION
        "Warning Clear: Bypass Mode warning reported."
    ::= 52

upsTrapInputOvervoltageWarning TRAP-TYPE 
    ENTERPRISE ups50003P1
    DESCRIPTION
        "Warning: Input Overvoltage warning reported."
    ::= 53

upsTrapInputOvervoltageWarningClear TRAP-TYPE 
    ENTERPRISE ups50003P1
    DESCRIPTION
        "Warning Clear: Input Overvoltage warning reported."
    ::= 54

upsTrapInputUndervoltageWarning TRAP-TYPE 
    ENTERPRISE ups50003P1
    DESCRIPTION
        "Warning: Input Undervoltage warning reported."
    ::= 55

upsTrapInputUndervoltageWarningClear TRAP-TYPE 
    ENTERPRISE ups50003P1
    DESCRIPTION
        "Warning Clear: Input Undervoltage warning reported."
    ::= 56

upsTrapInputPhaseRotationErrorWarning TRAP-TYPE 
    ENTERPRISE ups50003P1
    DESCRIPTION
        "Warning: Input Phase Rotation Error warning reported."
    ::= 57

upsTrapInputPhaseRotationErrorWarningClear TRAP-TYPE 
    ENTERPRISE ups50003P1
    DESCRIPTION
        "Warning Clear: Input Phase Rotation Error warning reported."
    ::= 58

upsTrapInputFrequencyErrorWarning TRAP-TYPE 
    ENTERPRISE ups50003P1
    DESCRIPTION
        "Warning: Input Frequency Error warning reported."
    ::= 59

upsTrapInputFrequencyErrorWarningClear TRAP-TYPE 
    ENTERPRISE ups50003P1
    DESCRIPTION
        "Warning Clear: Input Frequency Error warning reported."
    ::= 60

upsTrapBatteryOverheatWarning TRAP-TYPE 
    ENTERPRISE ups50003P1
    DESCRIPTION
        "Warning: Battery Overheat warning reported."
    ::= 61

upsTrapBatteryOverheatWarningClear TRAP-TYPE 
    ENTERPRISE ups50003P1
    DESCRIPTION
        "Warning Clear: Battery Overheat warning reported."
    ::= 62

upsTrapASYNCWarning TRAP-TYPE 
    ENTERPRISE ups50003P1
    DESCRIPTION
        "Warning: Input and Output are asynchronous warning reported."
    ::= 63

upsTrapASYNCWarningClear TRAP-TYPE 
    ENTERPRISE ups50003P1
    DESCRIPTION
        "Warning Clear: Input and Output are asynchronous warning reported."
    ::= 64

upsTrap72BBreakerOpenWarning TRAP-TYPE 
    ENTERPRISE ups50003P1
    DESCRIPTION
        "Warning: 72B Battery Breaker Open warning reported."
    ::= 65

upsTrap72BBreakerOpenWarningClear TRAP-TYPE 
    ENTERPRISE ups50003P1
    DESCRIPTION
        "Warning Clear: 72B Battery Breaker Open warning reported."
    ::= 66

upsTrapUserWarning2Warning TRAP-TYPE 
    ENTERPRISE ups50003P1
    DESCRIPTION
        "Warning: User Warning Type 2 Warning (restart will  occur)."
    ::= 67

upsTrapUserWarning2WarningClear TRAP-TYPE 
    ENTERPRISE ups50003P1
    DESCRIPTION
        "Warning Clear: User Warning Type 2 Warning (restart will  occur)."
    ::= 68

upsTrapUserWarning3Warning TRAP-TYPE 
    ENTERPRISE ups50003P1
    DESCRIPTION
        "Warning: User Warning Type 3 Warning (restart will  not occur)."
    ::= 69

upsTrapUserWarning3WarningClear TRAP-TYPE 
    ENTERPRISE ups50003P1
    DESCRIPTION
        "Warning Clear: User Warning Type 3 Warning (restart will  not occur)."
    ::= 70

upsTrapUserDefinedOverloadWarning TRAP-TYPE 
    ENTERPRISE ups50003P1
    DESCRIPTION
        "Warning: User Defined Overload warning reported."
    ::= 71

upsTrapUserDefinedOverloadWarningClear TRAP-TYPE 
    ENTERPRISE ups50003P1
    DESCRIPTION
        "Warning Clear: User Defined Overload warning reported."
    ::= 72

upsTrapSYNCInfo TRAP-TYPE 
    ENTERPRISE ups50003P1
    DESCRIPTION
        "Warning: Bypass and output are synchronous info reported."
    ::= 73

upsTrapSYNCInfoClear TRAP-TYPE 
    ENTERPRISE ups50003P1
    DESCRIPTION
        "Warning Clear: Bypass and output are synchronous info reported."
    ::= 74

upsTrapInverterOnInfo TRAP-TYPE
    ENTERPRISE ups50003P1
    DESCRIPTION
        "Info: Inverter On info reported."
    ::= 75

upsTrapInverterOnInfoClear TRAP-TYPE
    ENTERPRISE ups50003P1
    DESCRIPTION
        "Info Clear: Inverter On info reported."
    ::= 76

upsTrapBypassModeInfo TRAP-TYPE
    ENTERPRISE ups50003P1
    DESCRIPTION
        "Info: Bypass Mode info reported."
    ::= 77

upsTrapBypassModeInfoClear TRAP-TYPE
    ENTERPRISE ups50003P1
    DESCRIPTION
        "Info Clear: Bypass Mode info reported."
    ::= 78

upsTrapInputPowerFailureInfo TRAP-TYPE
    ENTERPRISE ups50003P1
    DESCRIPTION
        "Info: Input Power Failure info reported."
    ::= 79

upsTrapInputPowerFailureInfoClear TRAP-TYPE
    ENTERPRISE ups50003P1
    DESCRIPTION
        "Info Clear: Input Power Failure info reported."
    ::= 80

upsTrapFaultInfo TRAP-TYPE
    ENTERPRISE ups50003P1
    DESCRIPTION
        "Info: Fault info reported."
    ::= 81

upsTrapFaultInfoClear TRAP-TYPE
    ENTERPRISE ups50003P1
    DESCRIPTION
        "Info Clear: Fault info reported."
    ::= 82

upsTrapWarningInfo TRAP-TYPE
    ENTERPRISE ups50003P1
    DESCRIPTION
        "Info: Warning info reported."
    ::= 83

upsTrapWarningInfoClear TRAP-TYPE
    ENTERPRISE ups50003P1
    DESCRIPTION
        "Info Clear: Warning info reported."
    ::= 84

upsTrapEPOInfo TRAP-TYPE 
    ENTERPRISE ups50003P1
    DESCRIPTION
        "Info: EPO info reported."
    ::= 85

upsTrapEPOInfoClear TRAP-TYPE 
    ENTERPRISE ups50003P1
    DESCRIPTION
        "Info Clear: EPO info reported."
    ::= 86

upsTrapGateCheckInfo TRAP-TYPE
    ENTERPRISE ups50003P1
    DESCRIPTION
        "Info: Gate Check info reported."
    ::= 87

upsTrapGateCheckInfoClear TRAP-TYPE
    ENTERPRISE ups50003P1
    DESCRIPTION
        "Info Clear: Gate Check info reported."
    ::= 88

upsTrapPrechargeTestModeInfo TRAP-TYPE 
    ENTERPRISE ups50003P1
    DESCRIPTION
        "Info: Precharge Test Mode info reported."
    ::= 89

upsTrapPrechargeTestModeInfoClear TRAP-TYPE 
    ENTERPRISE ups50003P1
    DESCRIPTION
        "Info Clear: Precharge Test Mode info reported."
    ::= 90

upsTrapEqualizeChargingInfo TRAP-TYPE 
    ENTERPRISE ups50003P1
    DESCRIPTION
        "Info: Equalize Charging info reported."
    ::= 91

upsTrapEqualizeChargingInfoClear TRAP-TYPE 
    ENTERPRISE ups50003P1
    DESCRIPTION
        "Info Clear: Equalize Charging info reported."
    ::= 92

upsTrap72BBreakerClosedInfo TRAP-TYPE
    ENTERPRISE ups50003P1
    DESCRIPTION
        "Info: 72B Battery Breaker Closed info reported."
    ::= 93

upsTrap72BBreakerClosedInfoClear TRAP-TYPE
    ENTERPRISE ups50003P1
    DESCRIPTION
        "Info Clear: 72B Battery Breaker Closed info reported."
    ::= 94

upsTrapProtectionChargingInfo TRAP-TYPE
    ENTERPRISE ups50003P1
    DESCRIPTION
        "Info: Protection Charging info reported."
    ::= 95

upsTrapProtectionChargingInfoClear TRAP-TYPE
    ENTERPRISE ups50003P1
    DESCRIPTION
        "Info Clear: Protection Charging info reported."
    ::= 96

upsTrapBackupModeInfo TRAP-TYPE 
    ENTERPRISE ups50003P1
    DESCRIPTION
        "Info: Backup Mode info reported."
    ::= 97

upsTrapBackupModeInfoClear TRAP-TYPE 
    ENTERPRISE ups50003P1
    DESCRIPTION
        "Info Clear: Backup Mode info reported."
    ::= 98

upsTrapOnlineModeInfo TRAP-TYPE
    ENTERPRISE ups50003P1
    DESCRIPTION
        "Info: Online Mode (normal) info reported."
    ::= 99

upsTrapOnlineModeInfoClear TRAP-TYPE
    ENTERPRISE ups50003P1
    DESCRIPTION
        "Info Clear: Online Mode (normal) info reported."
    ::= 100
	
upsTrapUPSOverload110PercentInfo TRAP-TYPE 
    ENTERPRISE ups50003P1
    DESCRIPTION
        "Info: UPS Overload 110 Percent info reported."
    ::= 101
	
upsTrapUPSOverload110PercentInfoClear TRAP-TYPE 
    ENTERPRISE ups50003P1
    DESCRIPTION
        "Info Clear: UPS Overload 110 Percent info reported.."
    ::= 102

upsTrapRemoteOperationOccurredInfo TRAP-TYPE
    ENTERPRISE ups50003P1
    DESCRIPTION
        "Info: Remote Operation Occurred info reported."
    ::= 103

upsTrapRemoteOperationOccurredInfoClear TRAP-TYPE
    ENTERPRISE ups50003P1
    DESCRIPTION
        "Info Clear: Remote Operation Occurred info reported."
    ::= 104

upsTrap52RInputOpenInfo TRAP-TYPE
    ENTERPRISE ups50003P1
    DESCRIPTION
        "Info: 52R Input Contactor has not been commanded closed or has been commanded open."
    ::= 105

upsTrap52RInputOpenInfoClear TRAP-TYPE
    ENTERPRISE ups50003P1
    DESCRIPTION
        "Info Clear: 52R Input Contactor has not been commanded closed or has been commanded open."
    ::= 106

upsTrapUserChopperDisabledInfo TRAP-TYPE
    ENTERPRISE ups50003P1
    DESCRIPTION
        "Info: User has disabled chopper through external I/O info reported."
    ::= 107

upsTrapUserChopperDisabledInfoClear TRAP-TYPE
    ENTERPRISE ups50003P1
    DESCRIPTION
        "Info Clear: User has disabled chopper through external I/O info reported."
    ::= 108

upsTrapEEPROMDisabledInfo TRAP-TYPE
    ENTERPRISE ups50003P1
    DESCRIPTION
        "Info: Eprom Writes to the control board were disabled.  The user will not be able to change any control board parameters info reported."
    ::= 109

upsTrapEEPROMDisabledInfoClear TRAP-TYPE
    ENTERPRISE ups50003P1
    DESCRIPTION
        "Info Clear: Eprom Writes to the control board were disabled.  The user will not be able to change any control board parameters info reported."
    ::= 110
	
END
