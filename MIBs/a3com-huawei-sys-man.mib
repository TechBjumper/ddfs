-- ===========================================================================================================
-- Copyright (C) 2003 by  HUAWEI-3COM TECHNOLOGIES. All rights reserved.
--
-- Description:Huawei-3COM Configuration management MIB
-- Reference:HUAWEI-3COM Enterprise MIB
-- Version: V1.8
-- History:  
--  revision 1.0 2002-12-20 created by xuqingwei
--  revision 1.1 2004-4-16  added the support for XRN  by xuqingwei
--  revision 1.2 2004-4-16  added 'h3cSysImageType' in h3cSysImageTable for dual image  by changxiangqing 
--  revision 1.3 2004-5-14  convert MIB object name from hwXXX to h3c, etc.     
--  revision 1.31 2004-7-16 1. modified 'h3cSysImageSize' in h3cSysImageTable by zhaolina     
--  		            2.modified SYNTAX of 'h3cSysReloadImage','h3cSysImageIndex','h3cSysCFGFileIndex' 
--                           from (1..2147483647) to (0..2147483647) by zhaolina     
--  revision 1.5 2004-8-1  1. added 'secure' attribute for h3cSysImageType in h3cSysImageTable by zhaolina
--                         2.modified 'MAX-ACCESS' of h3cSysReloadTag from 'read-create' to 'read-write' by zhaolina
--                         3.modified DESCRIPTION of h3cSysReloadNotification by zhaolina
--                         4.modified DESCRIPTION of h3cSysImageType,h3cSysImageIndex,h3cSysImageTable and h3cSysReloadImage by zhaolina
--  revision 1.6 2004-9-8  1.modified DESCRIPTION of h3cSysImageType by wangyingxia
--                         2.added the trap object h3cSysStartUpNotification by wangyingxia 
--                         3.added h3cSysStartUpNotification into the NOTIFICATION OF h3cSystemManMIBNotifications        
--  revision 1.7 2004-10-12 updated by gaolong
--               Change all underscore('_') characters to hyphen characters('-') because underscore character is not allowed in MIB module.
--               Remove h3cSysCurEntPhysicalIndex from h3cSysCurGroup because this object is not accessible.
--  revision 1.8 2004-11-08 Change the description of h3cSysReloadScheduleIndex by gaolong
-- ============================================================================================================
A3COM-HUAWEI-SYS-MAN-MIB DEFINITIONS ::= BEGIN
 
		IMPORTS
			PhysicalIndex			
				FROM ENTITY-MIB			
			OBJECT-GROUP, MODULE-COMPLIANCE, NOTIFICATION-GROUP			
				FROM SNMPv2-CONF			
			Integer32, OBJECT-TYPE, MODULE-IDENTITY, NOTIFICATION-TYPE			
				FROM SNMPv2-SMI			
			RowPointer, DateAndTime, DisplayString, RowStatus			
				FROM SNMPv2-TC
			SnmpTagList, SnmpTagValue
				FROM SNMP-TARGET-MIB
			huaweiDatacomm
			        FROM A3COM-HUAWEI-OID-MIB;
	
	
		h3cSystemMan MODULE-IDENTITY 
			LAST-UPDATED "200212200000Z"		-- December 20, 2002  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				"This MIB contains objects to manage the system.
				 It focuses on the display of current configure file and image 
				 file,and the definition of reloading image.
				 Add the support for XRN.
				"
			REVISION "200404081345Z"		-- April 08, 2004 at 13:45 GMT
			DESCRIPTION 
				""
			::= { huaweiDatacomm 19 }
			

--XRN brief introduction:
--    Expandable resilient networking (XRN) is a technology to construct expandable
--    resilient networks. With XRN feature, you can connect several devices into a
--    combined device and treat them as a single one. The combined device is called
--    Fabric, while the member devices are units. 		

		
	
	
--
-- Node definitions
--
	
		h3cSystemManMIBObjects OBJECT IDENTIFIER ::= { h3cSystemMan 1 }

		
		h3cSysClock OBJECT IDENTIFIER ::= { h3cSystemManMIBObjects 1 }

		
		h3cSysLocalClock OBJECT-TYPE
			SYNTAX DateAndTime
			MAX-ACCESS read-only
			STATUS current
			DESCRIPTION
				"
				This node gives the current local time of the system.
				The unit of it is DateAndTime.
				"
			::= { h3cSysClock 1 }

		
		h3cSysCurrent OBJECT IDENTIFIER ::= { h3cSystemManMIBObjects 2 }

		
		h3cSysCurTable OBJECT-TYPE
			SYNTAX SEQUENCE OF H3cSysCurEntry
			MAX-ACCESS not-accessible
			STATUS current
			DESCRIPTION
				"
				The current status of system. A configuration file and an image 
				file are used to describe the current status.
				"
			::= { h3cSysCurrent 1 }

		
		h3cSysCurEntry OBJECT-TYPE
			SYNTAX H3cSysCurEntry
			MAX-ACCESS not-accessible
			STATUS current
			DESCRIPTION
				"
				An entry of h3cSysCurTable. 
				"
			INDEX { h3cSysCurEntPhysicalIndex }
			::= { h3cSysCurTable 1 }

		
		H3cSysCurEntry ::=
			SEQUENCE { 
				h3cSysCurEntPhysicalIndex
					Integer32,
				h3cSysCurCFGFileIndex
					Integer32,
				h3cSysCurImageIndex
					Integer32
			 }

		h3cSysCurEntPhysicalIndex OBJECT-TYPE
			SYNTAX Integer32 (0..2147483647)
			MAX-ACCESS not-accessible
			STATUS current
			DESCRIPTION
				"The value of this object is the entity index
				 which depends on the implementation of ENTITY-MIB. 
				 If ENTITY-MIB is not supported, the value for this object is the unit ID for XRN devices ,
				 0 for non-XRN device which has only one mainboard,
				 the board number for non-XRN device which have several mainboards.
                "
			::= { h3cSysCurEntry 1 }

		
		h3cSysCurCFGFileIndex OBJECT-TYPE
			SYNTAX Integer32 (0..2147483647)
			MAX-ACCESS read-only
			STATUS current
			DESCRIPTION
				"
				The startup configuration file currently used by the specified entity.
				If the value of it is zero, no configuration file is used.It will be 
				the value of corresponding h3cSysCFGFileIndex in h3cSysCFGFileTable.
				"
			::= { h3cSysCurEntry 2 }

		
		h3cSysCurImageIndex OBJECT-TYPE
			SYNTAX Integer32 (0..2147483647)
			MAX-ACCESS read-only
			STATUS current
			DESCRIPTION
				"The image file currently used by the specified entity.
				It will be the value of corresponding h3cSysImageIndex 
				in h3cSysImageTable."
			::= { h3cSysCurEntry 3 }

		
-- Bengin define reload group
		h3cSysReload OBJECT IDENTIFIER ::= { h3cSystemManMIBObjects 3 }

		
		h3cSysReloadSchedule OBJECT-TYPE
			SYNTAX Integer32 (0..2147483647)
			MAX-ACCESS read-write
			STATUS current
			DESCRIPTION
				"
				The object points one row in h3cSysReloadScheduleTable.
				Its value is equal to the value of h3cSysReloadScheduleIndex.
				When a reload aciton is finished, the value of it
				would be zero which means no any reload schedule is selected.
				"
			::= { h3cSysReload 1 }

		
		h3cSysReloadAction OBJECT-TYPE
			SYNTAX INTEGER
				{
				reloadUnavailable(1),
				reloadOnSchedule(2),
				reloadAtOnce(3),
				reloadCancel(4)
				}
			MAX-ACCESS read-write
			STATUS current
			DESCRIPTION
				"
				Writing reloadOnSchedule(2) to this object perform the reload operation on schedule. 
				if h3cSysReloadScheduleTime is not set,the value of h3cSysReloadAction can't be set to
				'reloadOnSchedule(2)'.
				
				Writing reloadAtOnce(3)to this object perform the reload operation at once, 
				regardless of the h3cSysReloadScheduleTime.  
				
				When reloadcancel(4)is set, the scheduled reload action will be canceled and the value of
				h3cSysReloadAction will be 'reloadUnavailable(1)',the value of h3cSysReloadSchedule will be
				0,h3cSysReloadTag will be given a value of zero length,but the content of 
				h3cSysReloadScheduleTable will remain.
				
				
				The h3cSysReloadSchedule and h3cSysReloadTag  determine the reload entity(ies) in mutually 
				exclusive way.And the h3cSysReloadSchedule will be handled at first.If the value of 
				h3cSysReloadSchedule is invalid,then the h3cSysReloadTag will be handled.
				
				If the value of h3cSysReloadSchedule is valid, the value of h3cSysReloadTag is ignored and a 
				reload action will be implemented to the entity specified by h3cSysReloadEntity in the entry 
				pointed by h3cSysReloadSchedule.
				
				If h3cSysReloadSchedule is valid, but the entry h3cSysReloadSchedule pointing to is not active, 
				the reload action will be ignored , and an inconsistent value will be returned.  
						
				
				If multiple entities are required to be reloaded at the same time, the value of h3cSysReloadTag 
				must be specified to select the reload parameters in the h3cSysReloadSceduelTable, and 
				h3cSysReloadSchedule must have the vlaue of '0'.
				
				If the whole fabric is to be reloaded in an XRN device, all the units in the fabric must 
				have at least one entry in the h3cSysReloadSceduelTable with the same tag in h3cSysReloadSceduelTagList.
				
				When a reload aciton is done, or there is no reload action, the value
				should be reloadUnavailable(1).
				"
			::= { h3cSysReload 2 }

		
		h3cSysReloadScheduleTable OBJECT-TYPE
			SYNTAX SEQUENCE OF H3cSysReloadScheduleEntry
			MAX-ACCESS not-accessible
			STATUS current
			DESCRIPTION
				"
				A reload parameters set table.
				
				The table is exclusively used for reloading.
				
				When reloading action finished,the value of the table may be empty or still exist.
				If the mainboard in non-XRN device or all the units of the fabric in XRN device are
				reloaded,then the table will be refreshed.
				"
			::= { h3cSysReload 3 }

		
		h3cSysReloadScheduleEntry OBJECT-TYPE
			SYNTAX H3cSysReloadScheduleEntry
			MAX-ACCESS not-accessible
			STATUS current
			DESCRIPTION
				"Entry of h3cSysReloadScheduleTable."
			INDEX { h3cSysReloadScheduleIndex }
			::= { h3cSysReloadScheduleTable 1 }

		
		H3cSysReloadScheduleEntry ::=
			SEQUENCE { 
				h3cSysReloadScheduleIndex
					Integer32,
				h3cSysReloadEntity
					Integer32,
				h3cSysReloadCfgFile
					Integer32,
				h3cSysReloadImage
					Integer32,
				h3cSysReloadReason
					DisplayString,
				h3cSysReloadScheduleTime
					DateAndTime,
				h3cSysReloadRowStatus
					RowStatus,
				h3cSysReloadScheduleTagList
					SnmpTagList
			 }

		h3cSysReloadScheduleIndex OBJECT-TYPE
			SYNTAX Integer32 (1..2147483647)
			MAX-ACCESS not-accessible
			STATUS current
			DESCRIPTION
				"The index of h3cSysReloadScheduleTable. There are two parts 
				for this index depicted as follows:
                                             																																												
				31                  15                  0    																																												
				+++++++++++++++++++++++++++++++++++++++++       																																												
				+ physical index     +     random index +   																																												
				( bit 16..31 )              ( bit 0..15 )																																												
				+++++++++++++++++++++++++++++++++++++++++         																																												
				From bit0 to bit15 (two bytes), if the row is automatic created,
				the value is zero, and if the row is created by users, then the 
				value is determined by the users.
                                
				From bit16 to bit31 (two bytes) is the physical index the same as the
				entPhysicalIndex specified in ENTITY-MIB(RFC2737). For XRN devices,
				physical index is the value of a chassis entPhysicalIndex. 0 for non-XRN 
				device which has only one main board, the board number for non-XRN device 
				which have multiple main boards. "
			::= { h3cSysReloadScheduleEntry 1 }

		
		h3cSysReloadEntity OBJECT-TYPE
			SYNTAX Integer32 (0..2147483647)
			MAX-ACCESS read-create
			STATUS current
			DESCRIPTION
				"
				The value of h3cSysReloadEntity indicates an entry in entPhysicalTable,
				which is the physical entity to be reloaded. 
				 
				If ENTITY-MIB is not supported,the value for this object is the unit ID for XRN devices ,
				0 for non-XRN device which has only one mainboard,
				the board number for non-XRN device which have several mainboards.

				Each entity has only one row in h3cSysReloadScheduleTable.  
				"
			::= { h3cSysReloadScheduleEntry 2 }

		
		h3cSysReloadCfgFile OBJECT-TYPE
			SYNTAX Integer32 (0..2147483647)
			MAX-ACCESS read-create
			STATUS current
			DESCRIPTION
				"
				The value indicates an entry in h3cSysCFGFileTable.
				It defines a configuration file for reload action.
				It is the value of corresponding h3cSysCFGFileIndex in h3cSysCFGFileTable.
				The zero value means no configuration file has been set for this entry, and
				no configuration file is used during system reloading.
				"
			::= { h3cSysReloadScheduleEntry 3 }

		
		h3cSysReloadImage OBJECT-TYPE
			SYNTAX Integer32 (0..2147483647)
			MAX-ACCESS read-create
			STATUS current
			DESCRIPTION
				"
				The value indicates an entry in h3cSysImageTable.
				It defines an image file for reload action.
				It is the value of corresponding h3cSysImageIndex in h3cSysImageTable.
				
				If dual image is supported, the main image attribute can be
				set through this object or by h3cSysImageType of h3cSysImageTable 
				of the entity. It is strongly suggested to set this attribute by 
				the latter.

				If main image attribute is set here, the h3cSysImageType in h3cSysImageTable 
				of the corresponding entity will be updated, and vice versa.
				
				Before reboot, the device will check the validation of the entry.If the file does
				not exist, the device will not reboot and a trap will be send to NMS.                                
				"
			::= { h3cSysReloadScheduleEntry 4 }

		
		h3cSysReloadReason OBJECT-TYPE
			SYNTAX DisplayString (SIZE (0..255))
			MAX-ACCESS read-create
			STATUS current
			DESCRIPTION
				"
				The reason of system's reloading. 
				It is a zero length octet string when not set.
				"
			::= { h3cSysReloadScheduleEntry 5 }

		
		h3cSysReloadScheduleTime OBJECT-TYPE
			SYNTAX DateAndTime (SIZE(8))
			MAX-ACCESS read-create
			STATUS current
			DESCRIPTION				
				"
				Specify the local time at which the reload action will
				occur. we will only take octet strings 
				with length 8 for this object which indicates the   
				local time of the switch. The maximum scheduled     
				interval between the specified time and the current
				system clock time is 24 days . 
				
					field  octets  contents                  range
 	                -----  ------  --------                  -----
 	                  1      1-2   year                      0..65536
 	                  2       3    month                     1..12
 	                  3       4    day                       1..31
 	                  4       5    hour                      0..23
 	                  5       6    minutes                   0..59
 	                  6       7    seconds                   0..60

                 For example, Tuesday May 26, 1992 at 1:30:15 PM would be
 	             displayed as:
 	
 	                        1992-5-26,13:30:15
				
				If the set value is less than the value of hwSysLocalClock
				or beyond the maximum scheduled time limit, a bad value error
				occurred.                                                 
				The value of all-zero octet strings indicates system reload 
				at once if the reload action is reloadOnSchedule(1).
				"				
			::= { h3cSysReloadScheduleEntry 6 }

		
		h3cSysReloadRowStatus OBJECT-TYPE
			SYNTAX RowStatus
			MAX-ACCESS read-create
			STATUS current
			DESCRIPTION
				"
				If one of the value of h3cSysReloadEntity,h3cSysReloadImage
				is invalid, the value of h3cSysReloadRowStatus can not be set to the value
				of ACTIVE.
				
				A valid entry means the specified element is available in current system.
				"
			::= { h3cSysReloadScheduleEntry 7 }
		
		h3cSysReloadScheduleTagList OBJECT-TYPE
			SYNTAX SnmpTagList
			MAX-ACCESS read-create
			STATUS current
			DESCRIPTION			 
			"
			It specifies a tag list for the entry.
			"
			::= { h3cSysReloadScheduleEntry 8 }
		
		h3cSysReloadTag OBJECT-TYPE
			SYNTAX SnmpTagValue
			MAX-ACCESS read-write
			STATUS current
			DESCRIPTION
				"This object contains a single tag value which is used
				to select entries in the h3cSysReloadScheduleTable.  
				
				In the h3cSysReloadScheduleTable,any entry that contains 
				a tag value which is equal to the value of this object is
				selected.   
				
				For example, the value of h3cSysReloadTag is 'TOM',and the
				h3cSysReloadScheduleTagList of each h3cSysReloadScheduleTable
                entry are as follows:
                1)'TOM,ROBERT,MARY'
                2)'TOM,DAVE'
                3)'DAVE,MARY'
                Since there are 'TOM' in 1) and 2),so 1) and 2) are selected.				
				
				
				If this object contains a value of zero length, no entries
				are selected.
				"
			::= { h3cSysReload 4 }
-- End define reload group		
		h3cSysImage OBJECT IDENTIFIER ::= { h3cSystemManMIBObjects 4 }

		
		h3cSysImageNum OBJECT-TYPE
			SYNTAX Integer32 (0..2147483647)
			MAX-ACCESS read-only
			STATUS current
			DESCRIPTION
				"
				The number of system images. It indicates the
				total entries of h3cSysImageTable.
				"
			::= { h3cSysImage 1 }

		
		h3cSysImageTable OBJECT-TYPE
			SYNTAX SEQUENCE OF H3cSysImageEntry
			MAX-ACCESS not-accessible
			STATUS current
			DESCRIPTION
				"The system image management table.
				
								
				When 'copy srcfile destfile' is executed via the CLI, if destfile is not existed, 
				then h3cSysImageType of the new file will be 'none'; otherwise h3cSysImageType keeps its current value. 
				When 'move srcfile destfile' is executed via the CLI, h3cSysImageType and h3cSysImageIndex 
				 remain the same while h3cSysImageLocation changes. 
				When 'rename srcfile' is executed via the CLI,h3cSysImageType and h3cSysImageIndex remain the same 
				while h3cSysImageName changes. 
				When 'delete srcfile' is executed via the CLI, the file is deleted from h3cSysImageTable 
				while index of the file keeps and will not be allocated.
				"
			::= { h3cSysImage 2 }

		
		h3cSysImageEntry OBJECT-TYPE
			SYNTAX H3cSysImageEntry
			MAX-ACCESS not-accessible
			STATUS current
			DESCRIPTION
				"
				A entity image entry. Each entry consists of information of a entity image.
				The h3cSysImageIndex exclusively defines an image file.
				"
			INDEX { h3cSysImageIndex }
			::= { h3cSysImageTable 1 }

		
		H3cSysImageEntry ::=
			SEQUENCE { 
				h3cSysImageIndex
					Integer32,
				h3cSysImageName
					DisplayString,
				h3cSysImageSize
					Integer32,
				h3cSysImageLocation
					DisplayString,
				h3cSysImageType 
					INTEGER
			 }

		h3cSysImageIndex OBJECT-TYPE
			SYNTAX Integer32 (0..2147483647)
			MAX-ACCESS not-accessible
			STATUS current
			DESCRIPTION
				"There are two parts for the index depicted as follows:
				
				31                15             0
				+++++++++++++++++++++++++++++++++++
				+ physical index   +  image index +
				+++++++++++++++++++++++++++++++++++
				
				From bit0 to bit15 (two bytes) is the image index;Image file Index
				is a monotonically increasing integer for the sole purpose of indexing 
				events.  When it reaches the maximum value,an  extremely unlikely event, 
				the agent wraps the value back to 1 and may flush existing entries.

				From bit16 to bit31 (two bytes) is the physical index the same as the 
				entPhysicalIndex specified in ENTITY-MIB(RFC2737). 
				If ENTITY-MIB is not supported,the value for this object is the unit ID for XRN
				devices ,0 for non-XRN device which has only one main board,the board number for
				non-XRN device which have several main boards.

				
				Any index beyond the above range will not be supported.
				
				If a file is added in, its h3cSysImageIndex will be the maximum image index plus one.
                                If the image file is removed, renamed, or moved from one place to another, 
                                its h3cSysImageIndex is not reallocated.
                                If the image file's content is replaced, its h3cSysImageIndex will not change.

				"
			::= { h3cSysImageEntry 1 }

		
		h3cSysImageName OBJECT-TYPE
			SYNTAX DisplayString
			MAX-ACCESS read-only
			STATUS current
			DESCRIPTION
				"The file name of the image. It MUST NOT contain the path of the file."
			::= { h3cSysImageEntry 2 }

		
		h3cSysImageSize OBJECT-TYPE
			SYNTAX Integer32 (1..2147483647)
			MAX-ACCESS read-only
			STATUS current
			DESCRIPTION
				"
				Size of the file in bytes.
				"
			::= { h3cSysImageEntry 3 }

		
		h3cSysImageLocation OBJECT-TYPE
			SYNTAX DisplayString
			MAX-ACCESS read-only
			STATUS current
			DESCRIPTION
				"
				The directory path of the image. 
				It's form should be the same as what defined in file system. 
				Currently it is defined as follows:
				For mainboard:   flash:/
				For slave mainboard and subboards: slotN#flash:/ 
				For XRN devices: unitN>slotN#flash:/				
				"
			::= { h3cSysImageEntry 4 }  
			
		h3cSysImageType OBJECT-TYPE
			SYNTAX INTEGER
				{
				main(1),
				backup(2),
				none(3),
				secure(4),
				main-backup(5),
				main-secure(6),
				backup-secure(7),
				main-backup-secure(8)
				}
			MAX-ACCESS read-write
			STATUS current
			DESCRIPTION
				"
				It indicates the reloading sequence attribute of the image.
				
				For devices which support dual image:
				
				If the value is 'main(1)',the image will be the first image
				in the next reloading procedure. If the value is 'backup(2)',
				the image will be used if the main image fails. If the value 
				is 'secure(4)',	the image will be used if the main image and 
				backup image both fail.	If the value is 'none(3)',the image will 
				not be used in the next reloading procedure.
				
				At the same time,you also can specify the main image by 
				h3cSysReloadImage in h3cSysReloadScheduleTable. If the
				image is diffrent from previous main image,the previous main image
				will not be main image again. And the image table will update with
				this variation. Vice versa, if you have defined the reload schedule
				, and then you define a new main image through h3cSysImageType when you 
				are waiting the reload schedule to be executed, the real main image
				will be the latest one.
				
				
				It is strongly suggested to define the main image here, not by h3cSysReloadImage
				in h3cSysReloadScheduleTable. 
				
				There are some rules for setting the value of h3cSysImageType: 
				
				a)When a new image file is defined as 'main' or 'backup' file,the h3cSysImageType
				  of old 'main' or 'backup' file will automatically be 'none'.   
				b)It is forbidden to set 'none' attribute manually. 
				c)It is forbidden to set 'secure' attribute manually.				 
				d)If 'main' image is set to 'backup', the file keeps 'main'. And vice versa. 
				  At this time, the file has 'main-backup' property.
				e)If the Secure image is set to 'main' or 'backup', the file has 'main-secure' or 'backup-secure'property.
				f)If the secure image is set to 'main' and 'backup', the file has the 'main-backup-secure' property.
				g)If the none image is set to 'main' or 'backup', the file has the 'mian' or 'backup' property.
				
				The following table describes whether it is ok to set to another state 
				directly from original state.			
							                        
			 	                +--------------+-----------+-------------+-------------+
			 	                |   set to     | set to    |  set to     |   set to    |
			 	                |              |           |             |             |
			 	     original   |    'main'    | 'backup'  |  'none'     |  'secure'   |
			 	     state      |              |           |             |             |
			 	  --------------+--------------+-----------+-------------+-------------+
			 	                |              |           |             |             |
			 	     main       |     ---      |   yes     |   no        |   no        |
			 	                |              |           |             |             |
			 	                |              |           |             |             |
			 	  --------------+--------------+-----------+-------------|-------------+
			 	                |              |           |             |             |
			 	     backup     |     yes      |   ---     |   no        |   no        |
			 	                |              |           |             |             |
			 	  --------------+--------------+-----------+-------------|-------------+
			 	                |              |           |             |             |
			 	                |              |           |             |             |
			 	      none      |     yes      |   yes     |   ---       |   no        |
			 	                |              |           |             |             |
			 	  --------------+--------------+-----------+-------------+-------------+
			 	                |              |           |             |             |
			 	      secure    |     yes      |   yes     |   no        |   ---       |
			 	                |              |           |             |             |
			 	                |              |           |             |             |
			 	  --------------+--------------+-----------+-------------+-------------+
							
				If there is one main image in the sytem,one row of H3cSysReloadScheduleEntry
				whose  h3cSysReloadImage is equal to the main image's h3cSysImageIndex will be
				created automatically. But if any row is deleted, it will not be created 
				automatically in h3cSysReloadScheduleTable.   
				
				
				
				
				For the device which doesn't support dual image(main/backup): 
				
				Only 'main' and 'none' is supported and it only can be set from none to main. 
				When a new image file is defined as 'main' file,the h3cSysImageType of old 'main' 
				file will automatically be 'none'.            
				"
			::= { h3cSysImageEntry 5 }

-- End define sysImage group
		
		h3cSysCFGFile OBJECT IDENTIFIER ::= { h3cSystemManMIBObjects 5 }

		
		h3cSysCFGFileNum OBJECT-TYPE
			SYNTAX Integer32 (0..2147483647)
			MAX-ACCESS read-only
			STATUS current
			DESCRIPTION
				"
				The number of the configuration files in the system. It indicates the
				total entries of h3cSysCFGFileTable.
				"
			::= { h3cSysCFGFile 1 }

		
		h3cSysCFGFileTable OBJECT-TYPE
			SYNTAX SEQUENCE OF H3cSysCFGFileEntry
			MAX-ACCESS not-accessible
			STATUS current
			DESCRIPTION
				"A table of configuration files in this system.
				 At present,the system doesn't support dual configure file,
				 it should act as 'dual image' if dual configure file is 
				 supported.
				"
			::= { h3cSysCFGFile 2 }

		
		h3cSysCFGFileEntry OBJECT-TYPE
			SYNTAX H3cSysCFGFileEntry
			MAX-ACCESS not-accessible
			STATUS current
			DESCRIPTION
				"
				A configuration file entry. Each entry consists of information of
				a configuration file.
				h3cSysCFGFileIndex exclusively decides a configuration file.
				"
			INDEX { h3cSysCFGFileIndex }
			::= { h3cSysCFGFileTable 1 }

		
		H3cSysCFGFileEntry ::=
			SEQUENCE { 
				h3cSysCFGFileIndex
					Integer32,
				h3cSysCFGFileName
					DisplayString,
				h3cSysCFGFileSize
					Integer32,
				h3cSysCFGFileLocation
					DisplayString
			 }

		h3cSysCFGFileIndex OBJECT-TYPE
			SYNTAX Integer32 (0..2147483647)
			MAX-ACCESS not-accessible
			STATUS current
			DESCRIPTION 
			   "There are two parts for the index depicted as follows:
				
				31                15             0
				+++++++++++++++++++++++++++++++++++
				+ physical index  + cfgFile index +
				+++++++++++++++++++++++++++++++++++

				From bit0 to bit15 (two bytes) is the configuration file index;The 
				configuration file index is a monotonically increasing integer for 
				the sole purpose of indexing events.  When it reaches the maximum 
				value,an  extremely unlikely event, the agent wraps the value back 
				to 1 and may flush existing entries.

				From bit16 to bit31 (two bytes) is the physical index the same 
				as the entPhysicalIndex specified in ENTITY-MIB(RFC2737). 
				If ENTITY-MIB is not supported,the value for this object is the unit ID for XRN
				devices ,0 for non-XRN device which has only one slot,the board number for
				non-XRN device which have several slots.
				
				Any index beyond the above range will not be supported.
				"
			::= { h3cSysCFGFileEntry 1 }

		
		h3cSysCFGFileName OBJECT-TYPE
			SYNTAX DisplayString
			MAX-ACCESS read-only
			STATUS current
			DESCRIPTION
				"
				Configuration file name. The name should not include the colon (:)
				character as it is a special separator character used
				to delineate the device name, partition name and the
				file name.
				"
			::= { h3cSysCFGFileEntry 2 }

		
		h3cSysCFGFileSize OBJECT-TYPE
			SYNTAX Integer32 (1..2147483647)
			MAX-ACCESS read-only
			STATUS current
			DESCRIPTION
				"
				Size of the file in bytes. Note that it does 
				not include the size of the filesystem file header.
				File size will always be non-zero.
				"
			::= { h3cSysCFGFileEntry 3 }

		
		h3cSysCFGFileLocation OBJECT-TYPE
			SYNTAX DisplayString
			MAX-ACCESS read-only
			STATUS current
			DESCRIPTION
				"
				The directory path of the image. 
				It's form should be the same as what defined in filesystem. 
				Currently it is defined as follows:
				For mainboard:   flash:/
				For slave mainboard and subboards: slotN#flash:/ 
				For XRN devices: unitN>slotN#flash:/				
				"
			::= { h3cSysCFGFileEntry 4 }
-- End define CFGFile group
		
		h3cSystemManMIBNotifications OBJECT IDENTIFIER ::= { h3cSystemMan 2 }

		
		h3cSysClockChangedNotification NOTIFICATION-TYPE
			OBJECTS { h3cSysLocalClock }
			STATUS current
			DESCRIPTION 
				"
				A clock changed notification is generated when the current
				local date and time for the system has been manually changed.
				The value of h3cSysLocalClock reflects new date and time.
				"
			::= { h3cSystemManMIBNotifications 1 }

		
		h3cSysReloadNotification NOTIFICATION-TYPE
			OBJECTS { h3cSysReloadImage, h3cSysReloadCfgFile, h3cSysReloadReason, h3cSysReloadScheduleTime, h3cSysReloadAction
				 }
			STATUS current
			DESCRIPTION 
				"
				A h3cSysReloadNotification will be sent before the corresponding entity is
                                rebooted. It will also be sent if the entity fails to reboot because the clock
                                has changed.
				"
			::= { h3cSystemManMIBNotifications 2 }

	    	
	    	h3cSysStartUpNotification NOTIFICATION-TYPE
	    	        OBJECTS { h3cSysImageType }
	    	        STATUS current
	    	        DESCRIPTION 
	    	        "
	    	        a h3cSysStartUpNotification trap will be sent when the system starts up with 'main' image file failed, 
	    	        a trap will be sent to indicate which type the current image file (I.e backup or secure)is.
	    	        "
	    	        ::={ h3cSystemManMIBNotifications 3}
	    	        
	    	        
-- conformance and Compliance define 
		h3cSystemManMIBConformance OBJECT IDENTIFIER ::= { h3cSystemMan 3 }

		
		h3cSystemManMIBCompliances OBJECT IDENTIFIER ::= { h3cSystemManMIBConformance 1 }

		
		h3cSystemManMIBCompliance MODULE-COMPLIANCE
			STATUS current
			DESCRIPTION 
				"
				The compliance statement for entities which implement
				the Huawei 3Com system management MIB.
				"
			MODULE -- this module
				MANDATORY-GROUPS { h3cSysClockGroup, h3cSysReloadGroup, h3cSysImageGroup, h3cSysCFGFileGroup, h3cSystemManNotificationGroup
					 }
			::= { h3cSystemManMIBCompliances 1 }

		
		h3cSystemManMIBGroups OBJECT IDENTIFIER ::= { h3cSystemManMIBConformance 2 }

		
		h3cSysClockGroup OBJECT-GROUP
			OBJECTS { h3cSysLocalClock }
			STATUS current
			DESCRIPTION 
				"A collection of objects providing mandatory system clock information."
			::= { h3cSystemManMIBGroups 1 }

		
-- A collection of objects providing mandatory system image
-- information.
		h3cSysReloadGroup OBJECT-GROUP
			OBJECTS { h3cSysReloadSchedule, h3cSysReloadAction, h3cSysReloadImage, h3cSysReloadCfgFile, h3cSysReloadReason, 
				h3cSysReloadScheduleTagList,h3cSysReloadTag,h3cSysReloadScheduleTime, h3cSysReloadEntity, h3cSysReloadRowStatus }
			STATUS current
			DESCRIPTION 
				"A collection of objects providing mandatory system reload."
			::= { h3cSystemManMIBGroups 2 }

		
		h3cSysImageGroup OBJECT-GROUP
			OBJECTS { h3cSysImageNum, h3cSysImageName, h3cSysImageSize, h3cSysImageLocation }
			STATUS current
			DESCRIPTION 
				"A collection of objects providing mandatory system image information."
			::= { h3cSystemManMIBGroups 3 }

		
		h3cSysCFGFileGroup OBJECT-GROUP
			OBJECTS { h3cSysCFGFileNum, h3cSysCFGFileName, h3cSysCFGFileSize, h3cSysCFGFileLocation }
			STATUS current
			DESCRIPTION 
				"
				A collection of objects providing mandatory system 
				configuration file information.
				"
			::= { h3cSystemManMIBGroups 4 }

		
		h3cSysCurGroup OBJECT-GROUP
			OBJECTS { h3cSysCurCFGFileIndex, h3cSysCurImageIndex }
			STATUS current
			DESCRIPTION 
				"A collection of system current status."
			::= { h3cSystemManMIBGroups 5 }

		
		h3cSystemManNotificationGroup NOTIFICATION-GROUP
			NOTIFICATIONS { h3cSysClockChangedNotification, h3cSysReloadNotification, h3cSysStartUpNotification }
			STATUS current
			DESCRIPTION 
				"A collection of notifications."
			::= { h3cSystemManMIBGroups 6 }

		
	
	END
