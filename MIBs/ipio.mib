DATAPROBE-IPIO-8 DEFINITIONS ::= BEGIN

IMPORTS
	NOTIFICATION-TYPE, OBJECT-TYPE, MODULE-IDENTITY, 
	enterprises, IpAddress, Integer32
		FROM SNMPv2-SMI
	NOTIFICATION-GROUP
		FROM SNMPv2-CONF
	DisplayString
		FROM SNMPv2-TC;

ipio MODULE-IDENTITY
	LAST-UPDATED "201306061429Z"
	ORGANIZATION 
		""
	CONTACT-INFO 
		""
	DESCRIPTION 
		""

	REVISION "201306061429Z"
	DESCRIPTION 
		"Changed name from ipio8 to ipio to support 2, 8 & 16 versions.
		Changed input and relay indexes from 8 to 16 to handle the max case."

	REVISION "201106211619Z"
	DESCRIPTION 
		"Minor corrections (added by PD)."

	REVISION "201106211510Z"
	DESCRIPTION 
		"Corrected case in variables as per Sam"

	REVISION "201106141331Z"
	DESCRIPTION 
		"Corrected spelling"
::= { dataprobe 5 }

dataprobe            OBJECT IDENTIFIER ::= { enterprises 1418 }
device               OBJECT IDENTIFIER ::= { ipio 1 }
users                OBJECT IDENTIFIER ::= { ipio 2 }
network              OBJECT IDENTIFIER ::= { ipio 3 }
email                OBJECT IDENTIFIER ::= { ipio 4 }
snmp                 OBJECT IDENTIFIER ::= { ipio 5 }
traps                OBJECT IDENTIFIER ::= { ipio 10 }

locationID  OBJECT-TYPE
	SYNTAX     DisplayString (SIZE(1..20))
	MAX-ACCESS read-write
	STATUS     current
	DESCRIPTION 
		""
	::= { device 1 }

autoUpdate  OBJECT-TYPE
	SYNTAX     Integer32 (0..99)
	MAX-ACCESS read-write
	STATUS     current
	DESCRIPTION 
		""
	::= { device 2 }

onReconnect  OBJECT-TYPE
	SYNTAX     INTEGER {
		no (0),
		yes (1)
	}
	MAX-ACCESS read-write
	STATUS     current
	DESCRIPTION 
		""
	::= { device 3 }

addRemote  OBJECT-TYPE
	SYNTAX     INTEGER {
		no (0),
		yes (1)
	}
	MAX-ACCESS read-write
	STATUS     current
	DESCRIPTION 
		""
	::= { device 4 }

deleteRemote  OBJECT-TYPE
	SYNTAX     Integer32 (1..32)
	MAX-ACCESS read-write
	STATUS     current
	DESCRIPTION 
		""
	::= { device 5 }

reboot  OBJECT-TYPE
	SYNTAX     INTEGER {
		no (0),
		yes (1)
	}
	MAX-ACCESS read-write
	STATUS     current
	DESCRIPTION 
		""
	::= { device 6 }

adminName  OBJECT-TYPE
	SYNTAX     DisplayString (SIZE(1..20))
	MAX-ACCESS read-write
	STATUS     current
	DESCRIPTION 
		""
	::= { users 1 }

adminPassword  OBJECT-TYPE
	SYNTAX     DisplayString (SIZE(1..20))
	MAX-ACCESS read-write
	STATUS     current
	DESCRIPTION 
		""
	::= { users 2 }

userName  OBJECT-TYPE
	SYNTAX     DisplayString (SIZE(1..20))
	MAX-ACCESS read-write
	STATUS     current
	DESCRIPTION 
		""
	::= { users 3 }

userPassword  OBJECT-TYPE
	SYNTAX     DisplayString (SIZE(1..20))
	MAX-ACCESS read-write
	STATUS     current
	DESCRIPTION 
		""
	::= { users 4 }

ipMode  OBJECT-TYPE
	SYNTAX     INTEGER {
		static (1),
		dhcp (2)
	}
	MAX-ACCESS read-write
	STATUS     current
	DESCRIPTION 
		""
	::= { network 1 }

ipAddress  OBJECT-TYPE
	SYNTAX     IpAddress
	MAX-ACCESS read-write
	STATUS     current
	DESCRIPTION 
		""
	::= { network 2 }

subnet  OBJECT-TYPE
	SYNTAX     IpAddress
	MAX-ACCESS read-write
	STATUS     current
	DESCRIPTION 
		""
	::= { network 3 }

gateway  OBJECT-TYPE
	SYNTAX     IpAddress
	MAX-ACCESS read-write
	STATUS     current
	DESCRIPTION 
		""
	::= { network 4 }

httpPort  OBJECT-TYPE
	SYNTAX     Integer32 (1..65535)
	MAX-ACCESS read-write
	STATUS     current
	DESCRIPTION 
		""
	::= { network 5 }

useSSL  OBJECT-TYPE
	SYNTAX     INTEGER {
		no (0),
		yes (1)
	}
	MAX-ACCESS read-write
	STATUS     current
	DESCRIPTION 
		""
	::= { network 6 }

httpsPort  OBJECT-TYPE
	SYNTAX     Integer32
	MAX-ACCESS read-write
	STATUS     current
	DESCRIPTION 
		""
	::= { network 7 }

dxpPort  OBJECT-TYPE
	SYNTAX     Integer32 (1..65535)
	MAX-ACCESS read-write
	STATUS     current
	DESCRIPTION 
		""
	::= { network 8 }

useAES  OBJECT-TYPE
	SYNTAX     INTEGER {
		no (0),
		yes (1)
	}
	MAX-ACCESS read-write
	STATUS     current
	DESCRIPTION 
		""
	::= { network 9 }

aesPassPhrase  OBJECT-TYPE
	SYNTAX     DisplayString (SIZE(1..20))
	MAX-ACCESS read-write
	STATUS     current
	DESCRIPTION 
		""
	::= { network 10 }

useDxPUserPass  OBJECT-TYPE
	SYNTAX     INTEGER {
		no (0),
		yes (1)
	}
	MAX-ACCESS read-write
	STATUS     current
	DESCRIPTION 
		""
	::= { network 11 }

connectionTimeout  OBJECT-TYPE
	SYNTAX     Integer32 (0..99)
	MAX-ACCESS read-write
	STATUS     current
	DESCRIPTION 
		""
	::= { network 12 }

smtpServer  OBJECT-TYPE
	SYNTAX     IpAddress
	MAX-ACCESS read-write
	STATUS     current
	DESCRIPTION 
		""
	::= { email 1 }

accountName  OBJECT-TYPE
	SYNTAX     DisplayString (SIZE(1..120))
	MAX-ACCESS read-write
	STATUS     current
	DESCRIPTION 
		""
	::= { email 2 }

accountPassword  OBJECT-TYPE
	SYNTAX     DisplayString (SIZE(1..32))
	MAX-ACCESS read-write
	STATUS     current
	DESCRIPTION 
		""
	::= { email 3 }

returnAddress  OBJECT-TYPE
	SYNTAX     DisplayString (SIZE(1..120))
	MAX-ACCESS read-write
	STATUS     current
	DESCRIPTION 
		""
	::= { email 4 }

destAddress1  OBJECT-TYPE
	SYNTAX     DisplayString (SIZE(0..120))
	MAX-ACCESS read-write
	STATUS     current
	DESCRIPTION 
		""
	::= { email 5 }

destAddress2  OBJECT-TYPE
	SYNTAX     DisplayString (SIZE(0..120))
	MAX-ACCESS read-write
	STATUS     current
	DESCRIPTION 
		""
	::= { email 6 }

sendInputChanged  OBJECT-TYPE
	SYNTAX     INTEGER {
		no (0),
		yes (1)
	}
	MAX-ACCESS read-write
	STATUS     current
	DESCRIPTION 
		""
	::= { email 7 }

sendOutputChanged  OBJECT-TYPE
	SYNTAX     INTEGER {
		no (0),
		yes (1)
	}
	MAX-ACCESS read-write
	STATUS     current
	DESCRIPTION 
		""
	::= { email 8 }

sendCommStatusChanged  OBJECT-TYPE
	SYNTAX     INTEGER {
		no (0),
		yes (1)
	}
	MAX-ACCESS read-write
	STATUS     current
	DESCRIPTION 
		""
	::= { email 9 }

sendConfigChanged  OBJECT-TYPE
	SYNTAX     INTEGER {
		no (0),
		yes (1)
	}
	MAX-ACCESS read-write
	STATUS     current
	DESCRIPTION 
		""
	::= { email 10 }

manager1  OBJECT-TYPE
	SYNTAX     IpAddress
	MAX-ACCESS read-write
	STATUS     current
	DESCRIPTION 
		""
	::= { snmp 1 }

manager2  OBJECT-TYPE
	SYNTAX     IpAddress
	MAX-ACCESS read-write
	STATUS     current
	DESCRIPTION 
		""
	::= { snmp 2 }

manager3  OBJECT-TYPE
	SYNTAX     IpAddress
	MAX-ACCESS read-write
	STATUS     current
	DESCRIPTION 
		""
	::= { snmp 3 }

manager4  OBJECT-TYPE
	SYNTAX     IpAddress
	MAX-ACCESS read-write
	STATUS     current
	DESCRIPTION 
		""
	::= { snmp 4 }

readCommunity  OBJECT-TYPE
	SYNTAX     DisplayString (SIZE(1..20))
	MAX-ACCESS read-write
	STATUS     current
	DESCRIPTION 
		""
	::= { snmp 5 }

writeCommunity  OBJECT-TYPE
	SYNTAX     DisplayString (SIZE(1..20))
	MAX-ACCESS read-write
	STATUS     current
	DESCRIPTION 
		""
	::= { snmp 6 }

sendInputChangedTrap  OBJECT-TYPE
	SYNTAX     INTEGER {
		no (0),
		yes (1)
	}
	MAX-ACCESS read-write
	STATUS     current
	DESCRIPTION 
		""
	::= { snmp 7 }

sendOutputChangedTrap  OBJECT-TYPE
	SYNTAX     INTEGER {
		no (0),
		yes (1)
	}
	MAX-ACCESS read-write
	STATUS     current
	DESCRIPTION 
		""
	::= { snmp 8 }

sendCommStatusChangedTrap  OBJECT-TYPE
	SYNTAX     INTEGER {
		no (0),
		yes (1)
	}
	MAX-ACCESS read-write
	STATUS     current
	DESCRIPTION 
		""
	::= { snmp 9 }

sendConfigChangedTrap  OBJECT-TYPE
	SYNTAX     INTEGER {
		no (0),
		yes (1)
	}
	MAX-ACCESS read-write
	STATUS     current
	DESCRIPTION 
		""
	::= { snmp 10 }

inputTable  OBJECT-TYPE
	SYNTAX SEQUENCE OF InputEntry
	MAX-ACCESS not-accessible
	STATUS     current
	DESCRIPTION 
		""
	::= { ipio 6 }

inputEntry  OBJECT-TYPE
	SYNTAX 	InputEntry
	MAX-ACCESS not-accessible
	STATUS     current
	DESCRIPTION 
		""
	INDEX { inputID }
	::= { inputTable 1 }

InputEntry ::= SEQUENCE {
	inputID
		Integer32,
	inputName
		DisplayString,
	inputOpenName
		DisplayString,
	inputClosedName
		DisplayString,
	inputOpenTextColor
		INTEGER,
	inputOpenBackGroundColor
		INTEGER,
	inputClosedTextColor
		INTEGER,
	inputClosedBackGroundColor
		INTEGER,
	inputLedControl
		INTEGER,
	inputQualifyingTime
		Integer32,
	inputStatus
		INTEGER
}

inputID  OBJECT-TYPE
	SYNTAX     Integer32 (1..16)
	MAX-ACCESS read-only
	STATUS     current
	DESCRIPTION 
		""
	::= { inputEntry 1 }

inputName  OBJECT-TYPE
	SYNTAX     DisplayString (SIZE(0..20))
	MAX-ACCESS read-write
	STATUS     current
	DESCRIPTION 
		""
	::= { inputEntry 2 }

inputOpenName  OBJECT-TYPE
	SYNTAX     DisplayString (SIZE(0..20))
	MAX-ACCESS read-write
	STATUS     current
	DESCRIPTION 
		""
	::= { inputEntry 3 }

inputClosedName  OBJECT-TYPE
	SYNTAX     DisplayString (SIZE(0..20))
	MAX-ACCESS read-write
	STATUS     current
	DESCRIPTION 
		""
	::= { inputEntry 4 }

inputOpenTextColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { inputEntry 5 }

inputOpenBackGroundColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { inputEntry 6 }

inputClosedTextColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { inputEntry 7 }

inputClosedBackGroundColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { inputEntry 8 }

inputLedControl  OBJECT-TYPE
	SYNTAX     INTEGER {
		closedLightLED (0),
		openLightLED (1)
	}
	MAX-ACCESS read-write
	STATUS     current
	DESCRIPTION 
		""
	::= { inputEntry 9 }

inputQualifyingTime  OBJECT-TYPE
	SYNTAX     Integer32 (0..99)
	MAX-ACCESS read-write
	STATUS     current
	DESCRIPTION 
		""
	::= { inputEntry 10 }

inputStatus  OBJECT-TYPE
	SYNTAX     INTEGER {
		open (0),
		closed (1)
	}
	MAX-ACCESS read-only
	STATUS     current
	DESCRIPTION 
		""
	::= { inputEntry 11 }

relayTable  OBJECT-TYPE
	SYNTAX SEQUENCE OF RelayEntry
	MAX-ACCESS not-accessible
	STATUS     current
	DESCRIPTION 
		""
	::= { ipio 7 }

relayEntry  OBJECT-TYPE
	SYNTAX 	RelayEntry
	MAX-ACCESS not-accessible
	STATUS     current
	DESCRIPTION 
		""
	INDEX { relayID }
	::= { relayTable 1 }

RelayEntry ::= SEQUENCE {
	relayID
		Integer32,
	relayName
		DisplayString,
	relayOpenName
		DisplayString,
	relayClosedName
		DisplayString,
	relayOpenTextColor
		INTEGER,
	relayOpenBackGroundColor
		INTEGER,
	relayClosedTextColor
		INTEGER,
	relayClosedBackGroundColor
		INTEGER,
	relayLedControl
		INTEGER,
	relayStatus
		INTEGER
}

relayID  OBJECT-TYPE
	SYNTAX     Integer32 (1..16)
	MAX-ACCESS read-only
	STATUS     current
	DESCRIPTION 
		""
	::= { relayEntry 1 }

relayName  OBJECT-TYPE
	SYNTAX     DisplayString (SIZE(0..20))
	MAX-ACCESS read-write
	STATUS     current
	DESCRIPTION 
		""
	::= { relayEntry 2 }

relayOpenName  OBJECT-TYPE
	SYNTAX     DisplayString (SIZE(0..20))
	MAX-ACCESS read-write
	STATUS     current
	DESCRIPTION 
		""
	::= { relayEntry 3 }

relayClosedName  OBJECT-TYPE
	SYNTAX     DisplayString (SIZE(0..20))
	MAX-ACCESS read-write
	STATUS     current
	DESCRIPTION 
		""
	::= { relayEntry 4 }

relayOpenTextColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { relayEntry 5 }

relayOpenBackGroundColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { relayEntry 6 }

relayClosedTextColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { relayEntry 7 }

relayClosedBackGroundColor  OBJECT-TYPE
	SYNTAX     INTEGER {
		black (0),
		grey (1),
		silver (2),
		white (3),
		maroon (4),
		red (5),
		orange (6),
		yellow (7),
		navy (8),
		blue (9),
		cyan (10),
		skyBlue (11),
		green (12),
		limeGreen (13),
		lime (14),
		yellowGreen (15)
	}
	MAX-ACCESS read-write
	STATUS     current
	DESCRIPTION 
		""
	::= { relayEntry 8 }

relayLedControl  OBJECT-TYPE
	SYNTAX     INTEGER {
		closedLightsLed (0),
		openLightsLed (1)
	}
	MAX-ACCESS read-write
	STATUS     current
	DESCRIPTION 
		""
	::= { relayEntry 9 }

relayStatus  OBJECT-TYPE
	SYNTAX     INTEGER {
		open (0),
		closed (1)
	}
	MAX-ACCESS read-write
	STATUS     current
	DESCRIPTION 
		""
	::= { relayEntry 10 }

remoteTable  OBJECT-TYPE
	SYNTAX SEQUENCE OF RemoteEntry
	MAX-ACCESS not-accessible
	STATUS     current
	DESCRIPTION 
		""
	::= { ipio 8 }

remoteEntry  OBJECT-TYPE
	SYNTAX 	RemoteEntry
	MAX-ACCESS not-accessible
	STATUS     current
	DESCRIPTION 
		""
	INDEX { remoteID }
	::= { remoteTable 1 }

RemoteEntry ::= SEQUENCE {
	remoteID
		Integer32,
	remoteName
		DisplayString,
	remoteCommunicationStatus
		INTEGER,
	remoteAlarmRelay
		Integer32,
	remoteIpAddress
		IpAddress,
	remotePort
		Integer32,
	remoteUseAES
		INTEGER,
	remotePassPhrase
		DisplayString
}

remoteID  OBJECT-TYPE
	SYNTAX     Integer32 (1..32)
	MAX-ACCESS read-only
	STATUS     current
	DESCRIPTION 
		""
	::= { remoteEntry 1 }

remoteName  OBJECT-TYPE
	SYNTAX     DisplayString (SIZE(0..20))
	MAX-ACCESS read-write
	STATUS     current
	DESCRIPTION 
		""
	::= { remoteEntry 2 }

remoteCommunicationStatus  OBJECT-TYPE
	SYNTAX     INTEGER {
		failed (0),
		ok (1)
	}
	MAX-ACCESS read-only
	STATUS     current
	DESCRIPTION 
		""
	::= { remoteEntry 3 }

remoteAlarmRelay  OBJECT-TYPE
	SYNTAX     Integer32 (0..16)
	MAX-ACCESS read-write
	STATUS     current
	DESCRIPTION 
		""
	::= { remoteEntry 4 }

remoteIpAddress  OBJECT-TYPE
	SYNTAX     IpAddress
	MAX-ACCESS read-write
	STATUS     current
	DESCRIPTION 
		""
	::= { remoteEntry 5 }

remotePort  OBJECT-TYPE
	SYNTAX     Integer32 (1..65535)
	MAX-ACCESS read-write
	STATUS     current
	DESCRIPTION 
		""
	::= { remoteEntry 6 }

remoteUseAES  OBJECT-TYPE
	SYNTAX     INTEGER {
		no (0),
		yes (1)
	}
	MAX-ACCESS read-write
	STATUS     current
	DESCRIPTION 
		""
	::= { remoteEntry 7 }

remotePassPhrase  OBJECT-TYPE
	SYNTAX     DisplayString (SIZE(0..20))
	MAX-ACCESS read-write
	STATUS     current
	DESCRIPTION 
		""
	::= { remoteEntry 8 }

relayMapTable  OBJECT-TYPE
	SYNTAX SEQUENCE OF RelayMapEntry
	MAX-ACCESS not-accessible
	STATUS     current
	DESCRIPTION 
		""
	::= { ipio 9 }

relayMapEntry  OBJECT-TYPE
	SYNTAX 	RelayMapEntry
	MAX-ACCESS not-accessible
	STATUS     current
	DESCRIPTION 
		""
	INDEX { remote, 
		input }
	::= { relayMapTable 1 }

RelayMapEntry ::= SEQUENCE {
	remote
		Integer32,
	input
		Integer32,
	relay
		Integer32,
	onInputOpen
		INTEGER,
	onInputClose
		INTEGER,
	pulseWidth
		Integer32
}

remote  OBJECT-TYPE
	SYNTAX     Integer32 (1..32)
	MAX-ACCESS read-only
	STATUS     current
	DESCRIPTION 
		""
	::= { relayMapEntry 1 }

input  OBJECT-TYPE
	SYNTAX     Integer32 (1..16)
	MAX-ACCESS read-only
	STATUS     current
	DESCRIPTION 
		""
	::= { relayMapEntry 2 }

relay  OBJECT-TYPE
	SYNTAX     Integer32 (0..16)
	MAX-ACCESS read-write
	STATUS     current
	DESCRIPTION 
		""
	::= { relayMapEntry 3 }

onInputOpen  OBJECT-TYPE
	SYNTAX     INTEGER {
		none (1),
		open (2),
		close (3),
		pulseOpen (4),
		pulseClose (5)
	}
	MAX-ACCESS read-write
	STATUS     current
	DESCRIPTION 
		""
	::= { relayMapEntry 4 }

onInputClose  OBJECT-TYPE
	SYNTAX     INTEGER {
		none (1),
		open (2),
		close (3),
		pulseOpen (4),
		pulseClose (5)
	}
	MAX-ACCESS read-write
	STATUS     current
	DESCRIPTION 
		""
	::= { relayMapEntry 5 }

pulseWidth  OBJECT-TYPE
	SYNTAX     Integer32
	MAX-ACCESS read-write
	STATUS     current
	DESCRIPTION 
		""
	::= { relayMapEntry 6 }

inputChanged  NOTIFICATION-TYPE
	OBJECTS { inputID, 
		inputName, 
		inputStatus }
	STATUS     current
	DESCRIPTION 
		""
	::= { traps 1 }

relayChanged  NOTIFICATION-TYPE
	OBJECTS { relayID, 
		relayName, 
		relayStatus }
	STATUS     current
	DESCRIPTION 
		""
	::= { traps 2 }

commStatusChanged  NOTIFICATION-TYPE
	OBJECTS { remoteID, 
		remoteName, 
		remoteCommunicationStatus }
	STATUS     current
	DESCRIPTION 
		""
	::= { traps 3 }

configChanged  NOTIFICATION-TYPE
	STATUS     current
	DESCRIPTION 
		""
	::= { traps 4 }

notifyGroup  NOTIFICATION-GROUP
	NOTIFICATIONS { commStatusChanged, 
		configChanged, 
		inputChanged, 
		relayChanged }
	STATUS     current
	DESCRIPTION 
		""
	::= { ipio 11 }
END


-- This MIB was created using NuDesign Team's Visual MIBuilder (Ver 4.4).
