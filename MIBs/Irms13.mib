-- IRMS-MIB { iso org(3) dod(6) internet(1) private(4)
-- enterprises(1) riello(5491) }

IRMS-MIB DEFINITIONS ::= BEGIN

-- Title: IRMS MIB    - vars for UPS types: IRMS
-- Version: 1.3 by Michele Marcon
-- Date: 30.10.2009

IMPORTS
     enterprises, IpAddress, TimeTicks, Gauge
         FROM RFC1155-SMI
     DisplayString
         FROM RFC1213-MIB
     OBJECT-TYPE
         FROM RFC-1212
     TRAP-TYPE
         FROM RFC-1215
     rielloMIB
             FROM RIELLO-MIB;


irmsgroup              OBJECT IDENTIFIER ::= { rielloMIB 5 }
                                    
irms                  OBJECT IDENTIFIER ::= { irmsgroup 1 }

multiswitchConfig      OBJECT IDENTIFIER ::= { irms 1 }

multiswitchIdentManufacturer OBJECT-TYPE
    SYNTAX     DisplayString
    ACCESS     read-only
    STATUS     mandatory
    DESCRIPTION
            "The name of the switch manufacturer."
    ::= { multiswitchConfig 1 }

multiswitchIdentModel OBJECT-TYPE
    SYNTAX     DisplayString 
    ACCESS     read-only
    STATUS     mandatory
    DESCRIPTION
            "The switch Model designation."
    ::= { multiswitchConfig 2 }

multiswitchIdentSoftwareVersion OBJECT-TYPE
    SYNTAX     DisplayString 
    ACCESS     read-only
    STATUS     mandatory
    DESCRIPTION
            "The switch Software version."
    ::= { multiswitchConfig 3 }

multiswitchIdentNunits OBJECT-TYPE
    SYNTAX     INTEGER
    ACCESS     read-only
    STATUS     mandatory
    DESCRIPTION
            "The Number of stacked units."
    ::= { multiswitchConfig 4 }
    
multiswitchConfigNlines OBJECT-TYPE
    SYNTAX     INTEGER
    ACCESS     read-only
    STATUS     mandatory
    DESCRIPTION
            "The Number of handled lines (=Nunits*8)."
    ::= { multiswitchConfig 5 }

multiswitchThresholdI OBJECT-TYPE
    SYNTAX     INTEGER
    ACCESS     read-write
    STATUS     mandatory
    DESCRIPTION
            "The Threshold (in VA?) for considering a line in overload status."
    ::= { multiswitchConfig 6 }

multiswitchThresholdHole OBJECT-TYPE
    SYNTAX     INTEGER
    ACCESS     read-write
    STATUS     mandatory
    DESCRIPTION
            "The number of time slices (625 us) for considering a line in blackout state."
    ::= { multiswitchConfig 7 }

multiswitchDeviceName OBJECT-TYPE
    SYNTAX     DisplayString
    ACCESS     read-only
    STATUS     mandatory
    DESCRIPTION
            "The identification name of the device"
    ::= { multiswitchConfig 8 }

multiswitchStatus OBJECT IDENTIFIER ::= { irms 2 }

multiswitchStatusMonitoredMachine OBJECT-TYPE
    SYNTAX     INTEGER
    ACCESS     read-write
    STATUS     mandatory
    DESCRIPTION
            "The Number (0..31) of the machine that is monitored. After it is set, wait until monitoredisok is 1, and check if monitoredispresent=1 before reading other values"
    ::= { multiswitchStatus 1 }
    
multiswitchStatusMonitoredIsPresent OBJECT-TYPE
    SYNTAX     INTEGER
    ACCESS     read-only
    STATUS     mandatory
    DESCRIPTION
            "1 if the selected unit in stack is present"
    ::= { multiswitchStatus 2 }
    
multiswitchStatusMonitoredIsOk OBJECT-TYPE
    SYNTAX     INTEGER
    ACCESS     read-only
    STATUS     mandatory
    DESCRIPTION
            "1 if the status of the selected unit in stack is checked, of 0 until it is not ckecked"
    ::= { multiswitchStatus 3 }

multiswitchReleaseVersion OBJECT-TYPE
    SYNTAX     DisplayString
    ACCESS     read-only
    STATUS     mandatory
    DESCRIPTION
            "The model of the monitored unit, as returned by the unit RELEASEV command"
    ::= { multiswitchStatus 4 }
    
multiswitchInput OBJECT IDENTIFIER ::= { multiswitchStatus 5 }

lineAStatus OBJECT-TYPE
    SYNTAX  INTEGER {
    ok (0),
    blackout (1)
}
    ACCESS     read-only
    STATUS     mandatory
    DESCRIPTION
            "0 for line OK, 1 for black-out"
    ::= { multiswitchInput 1 }

lineBStatus OBJECT-TYPE
    SYNTAX  INTEGER {
    ok (0),
    blackout (1)
}
    ACCESS     read-only
    STATUS     mandatory
    DESCRIPTION
            "0 for line OK, 1 for black-out"
    ::= { multiswitchInput 2 }

lineAFrequency OBJECT-TYPE
    SYNTAX     INTEGER
    ACCESS     read-only
    STATUS     mandatory
    DESCRIPTION
            "Input Frequency for line A (0.1 Hz)"
    ::= { multiswitchInput 3 }

lineBFrequency OBJECT-TYPE
    SYNTAX     INTEGER
    ACCESS     read-only
    STATUS     mandatory
    DESCRIPTION
            "Input Frequency for line B (0.1 Hz)"
    ::= { multiswitchInput 4 }

lineAVoltage OBJECT-TYPE
    SYNTAX     INTEGER
    ACCESS     read-only
    STATUS     mandatory
    DESCRIPTION
            "Output Voltage for line A, 0.1 V"
    ::= { multiswitchInput 5 }

lineBVoltage OBJECT-TYPE
    SYNTAX     INTEGER
    ACCESS     read-only
    STATUS     mandatory
    DESCRIPTION
            "Output Voltage for line B, 0.1 V"
    ::= { multiswitchInput 6 }

linePhaseDifference OBJECT-TYPE
    SYNTAX     INTEGER
    ACCESS     read-only
    STATUS     mandatory
    DESCRIPTION
            "Difference in phase between the two lines, in degrees (0..360)"
    ::= { multiswitchInput 7 }

lineAHole OBJECT-TYPE
    SYNTAX     INTEGER
    ACCESS     read-only
    STATUS     mandatory
    DESCRIPTION
            "Number of timeslices for blackout state, line A (0 means line OK)"
    ::= { multiswitchInput 8 }

lineBHole OBJECT-TYPE
    SYNTAX     INTEGER
    ACCESS     read-only
    STATUS     mandatory
    DESCRIPTION
            "Number of timeslices for blackout state, line B (0 means line OK)"
    ::= { multiswitchInput 9 }

multiswitchOutput OBJECT IDENTIFIER ::= { multiswitchStatus 6 }
	
multiswitchOutputTable OBJECT-TYPE
    SYNTAX  SEQUENCE OF OutputSockets
    ACCESS  not-accessible
    STATUS  mandatory
    DESCRIPTION
           "A list of input table entries.  The number of entries
               is given by the value of upsInputNumLines."
    ::= { multiswitchOutput  1 }

outputSockets OBJECT-TYPE
    SYNTAX  OutputSockets
    ACCESS  not-accessible
    STATUS  mandatory
    DESCRIPTION
           "An entry containing information applicable to a
               particular output line."
    INDEX   { outputLineIndex }
    ::= { multiswitchOutputTable  1 }

OutputSockets ::=
    SEQUENCE {
        outputLineIndex
            INTEGER,
                        
        outputCurrent
            INTEGER,

        outputLoad
            INTEGER,

        outputDisabled
            INTEGER,

        outputSource
            INTEGER,

        outputOverload
            INTEGER,

        outputName
            DisplayString,

        outputReboot
            INTEGER
    }

outputLineIndex OBJECT-TYPE
    SYNTAX  INTEGER
    ACCESS  not-accessible
    STATUS  mandatory
    DESCRIPTION
           "The line identifier."
    ::= { outputSockets  1 }	
	
outputCurrent OBJECT-TYPE
    SYNTAX     INTEGER
    ACCESS     read-only
    STATUS     mandatory
    DESCRIPTION
            "Output current (0.1 A)"
    ::= { outputSockets 2 }

outputLoad OBJECT-TYPE
    SYNTAX     INTEGER
    ACCESS     read-only
    STATUS     mandatory
    DESCRIPTION
            "Output Load (VA)"
    ::= { outputSockets 3 }

outputDisabled OBJECT-TYPE
    SYNTAX  INTEGER {
    no(0),
    yes(1)
}
    ACCESS     read-write
    STATUS     mandatory
    DESCRIPTION
            "0->line active, 1->line deactivated"
    ::= { outputSockets 4 }

outputSource OBJECT-TYPE
        SYNTAX  INTEGER {
    lineA(0),
    lineB(1)
}
    ACCESS     read-write
    STATUS     mandatory
    DESCRIPTION
            "0-> power from line A; 1-> power from line B"
    ::= { outputSockets 5 }

outputOverload OBJECT-TYPE
    SYNTAX     INTEGER
    ACCESS     read-only
    STATUS     mandatory
    DESCRIPTION
            "0->line ok, 1->line deactivated for overload"
    ::= { outputSockets 6 }

outputName OBJECT-TYPE
    SYNTAX     DisplayString
    ACCESS     read-only
    STATUS     mandatory
    DESCRIPTION
            "The name for the socket"
    ::= { outputSockets 7 }

outputReboot OBJECT-TYPE
        SYNTAX  INTEGER {
    none(0),
    reboot(1)
}
    ACCESS     read-write
    STATUS     mandatory
    DESCRIPTION
            "0-> None; 1-> Reboot"
    ::= { outputSockets 8 }



irmsTrapInfoGroup OBJECT IDENTIFIER ::= { rielloMIB 7 }

irmsTrapInfo  OBJECT IDENTIFIER ::= { irmsTrapInfoGroup 1 }

multiswitchAlarmId OBJECT-TYPE
    SYNTAX     INTEGER
    ACCESS     read-only
    STATUS     mandatory
    DESCRIPTION
            "Alarm ID"
    ::= { irmsTrapInfo 1 }
    
multiswitchAlarmOutputLine OBJECT-TYPE
    SYNTAX     INTEGER
    ACCESS read-only
    STATUS     mandatory
    DESCRIPTION
            "Output line that caused the alarm (0..7; 8 means ALL)"
    ::= { irmsTrapInfo 2 }

multiswitchAlarmInputLine OBJECT-TYPE
    SYNTAX     INTEGER
    ACCESS     read-only
    STATUS     mandatory
    DESCRIPTION
            "Input line that caused the alarm (0=A; 1=B)"
    ::= { irmsTrapInfo 3 }

multiswitchAlarmDescr OBJECT-TYPE
    SYNTAX     DisplayString
    ACCESS     read-only
    STATUS     mandatory
    DESCRIPTION
            "Textual description of the alarm"
    ::= { irmsTrapInfo 4 }
    
multiswitchAlarmUnit OBJECT-TYPE
    SYNTAX     INTEGER
    ACCESS     read-only
    STATUS     mandatory
    DESCRIPTION
            "The IRMS unit, in stack (0..31) which generated the alarm; -1 means that the alarm was not caused by the IRMS"
    ::= { irmsTrapInfo 5 }

irmsTrapGroup OBJECT IDENTIFIER ::= { rielloMIB 8 }


irmsTrapColdStart TRAP-TYPE
       ENTERPRISE  irmsTrapGroup
       VARIABLES { multiswitchAlarmId, multiswitchAlarmDescr, multiswitchAlarmUnit  }
       DESCRIPTION "This trap is sent each time the MPU boots"     
       ::= 1

multiswitchTrapInOverload TRAP-TYPE
       ENTERPRISE  irmsTrapGroup
       VARIABLES { multiswitchAlarmId, multiswitchAlarmDescr, multiswitchAlarmOutputLine  }
       DESCRIPTION "This trap is sent each time a line is in overload condition"     
       ::= 2

multiswitchTrapInOverloadRemoved TRAP-TYPE
       ENTERPRISE  irmsTrapGroup
       VARIABLES { multiswitchAlarmId, multiswitchAlarmDescr, multiswitchAlarmOutputLine  }
       DESCRIPTION "This trap is sent each time a line leaves the overload condition"     
       ::= 3

multiswitchTrapInBlackout TRAP-TYPE
       ENTERPRISE  irmsTrapGroup
       VARIABLES { multiswitchAlarmId, multiswitchAlarmDescr, multiswitchAlarmInputLine  }
       DESCRIPTION "This trap is sent each time a line is in blackout condition"     
       ::= 4

multiswitchTrapInBlackoutRemoved TRAP-TYPE
       ENTERPRISE  irmsTrapGroup
       VARIABLES { multiswitchAlarmId, multiswitchAlarmDescr, multiswitchAlarmInputLine  }
       DESCRIPTION "This trap is sent each time a line leaves the blackout condition"     
       ::= 5


END
