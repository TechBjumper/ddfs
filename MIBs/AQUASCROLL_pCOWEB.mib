--
-- CAREL-aquascroll.MIB
-- MIB generated by CAREL
-- Friday, 21 November 2014
--

    CAREL-aquascroll-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI
			DisplayString
				FROM SNMPv2-TC;
		
        aquascrollMIB MODULE-IDENTITY
      		LAST-UPDATED  "201411211541Z"		-- November 21, 2014 at 15:41 GMT
      		ORGANIZATION  "CAREL Industries S.r.l."
      		CONTACT-INFO
                "
                        Carel Industries S.r.l.
                        Via dell'Industria, 11
                        35020 Brugine (PD) Italy
                        Tel: +39 049 9716611
                        E-mail: carel@carel.com
                "
      		DESCRIPTION
                "This is the MIB module for the aquascroll device."
			REVISION "201411211541Z"
			DESCRIPTION
				"version4pCOweb"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { aquascrollMIB 1 }

        -- 1.3.6.1.4.1.9839.2.1.1.1
        pump-on OBJECT-TYPE
                    SYNTAX Integer32 (0..1)
                    UNITS "N/A"
                    MAX-ACCESS read-only
                    STATUS current
                    DESCRIPTION "System On"
                    ::= { digitalObjects 1 }

        -- 1.3.6.1.4.1.9839.2.1.1.2
        compress1 OBJECT-TYPE
                    SYNTAX Integer32 (0..1)
                    UNITS "N/A"
                    MAX-ACCESS read-only
                    STATUS current
                    DESCRIPTION "Compressor 1"
                    ::= { digitalObjects 2 }

        -- 1.3.6.1.4.1.9839.2.1.1.3
        compress2 OBJECT-TYPE
                    SYNTAX Integer32 (0..1)
                    UNITS "N/A"
                    MAX-ACCESS read-only
                    STATUS current
                    DESCRIPTION "Compressor 2"
                    ::= { digitalObjects 3 }

        -- 1.3.6.1.4.1.9839.2.1.1.4
        compress3 OBJECT-TYPE
                    SYNTAX Integer32 (0..1)
                    UNITS "N/A"
                    MAX-ACCESS read-only
                    STATUS current
                    DESCRIPTION "Compressor 3"
                    ::= { digitalObjects 4 }

        -- 1.3.6.1.4.1.9839.2.1.1.5
        compress4 OBJECT-TYPE
                    SYNTAX Integer32 (0..1)
                    UNITS "N/A"
                    MAX-ACCESS read-only
                    STATUS current
                    DESCRIPTION "Compressor 4"
                    ::= { digitalObjects 5 }

        -- 1.3.6.1.4.1.9839.2.1.1.6
        pompa1 OBJECT-TYPE
                    SYNTAX Integer32 (0..1)
                    UNITS "N/A"
                    MAX-ACCESS read-only
                    STATUS current
                    DESCRIPTION "Circulating Pump 1"
                    ::= { digitalObjects 6 }

        -- 1.3.6.1.4.1.9839.2.1.1.7
        pompa2 OBJECT-TYPE
                    SYNTAX Integer32 (0..1)
                    UNITS "N/A"
                    MAX-ACCESS read-only
                    STATUS current
                    DESCRIPTION "Circulating Pump 2"
                    ::= { digitalObjects 7 }

        -- 1.3.6.1.4.1.9839.2.1.1.8
        etvl-circ1 OBJECT-TYPE
                    SYNTAX Integer32 (0..1)
                    UNITS "N/A"
                    MAX-ACCESS read-only
                    STATUS current
                    DESCRIPTION "Circ. 1 Refrigerant shut-off valve"
                    ::= { digitalObjects 8 }

        -- 1.3.6.1.4.1.9839.2.1.1.9
        etvl-circ2 OBJECT-TYPE
                    SYNTAX Integer32 (0..1)
                    UNITS "N/A"
                    MAX-ACCESS read-only
                    STATUS current
                    DESCRIPTION "Circ. 2 Refrigerant shut-off valve"
                    ::= { digitalObjects 9 }

        -- 1.3.6.1.4.1.9839.2.1.1.10
        pump-hr OBJECT-TYPE
                    SYNTAX Integer32 (0..1)
                    UNITS "N/A"
                    MAX-ACCESS read-only
                    STATUS current
                    DESCRIPTION "Heat recovery Pump "
                    ::= { digitalObjects 10 }

        -- 1.3.6.1.4.1.9839.2.1.1.11
        heat-rec-on1 OBJECT-TYPE
                    SYNTAX Integer32 (0..1)
                    UNITS "N/A"
                    MAX-ACCESS read-only
                    STATUS current
                    DESCRIPTION "Heat recovery Circuit 1  "
                    ::= { digitalObjects 11 }

        -- 1.3.6.1.4.1.9839.2.1.1.12
        heat-rec-on2 OBJECT-TYPE
                    SYNTAX Integer32 (0..1)
                    UNITS "N/A"
                    MAX-ACCESS read-only
                    STATUS current
                    DESCRIPTION "Heat recovery Circuit 2  "
                    ::= { digitalObjects 12 }

        -- 1.3.6.1.4.1.9839.2.1.1.13
        heater OBJECT-TYPE
                    SYNTAX Integer32 (0..1)
                    UNITS "N/A"
                    MAX-ACCESS read-only
                    STATUS current
                    DESCRIPTION "Antifreeze heaters"
                    ::= { digitalObjects 13 }

        -- 1.3.6.1.4.1.9839.2.1.1.14
        xdef-circ1 OBJECT-TYPE
                    SYNTAX Integer32 (0..1)
                    UNITS "N/A"
                    MAX-ACCESS read-only
                    STATUS current
                    DESCRIPTION "Circuit 1 Defrost"
                    ::= { digitalObjects 14 }

        -- 1.3.6.1.4.1.9839.2.1.1.15
        xdef-circ2 OBJECT-TYPE
                    SYNTAX Integer32 (0..1)
                    UNITS "N/A"
                    MAX-ACCESS read-only
                    STATUS current
                    DESCRIPTION "Circuit 2 Defrost"
                    ::= { digitalObjects 15 }

        -- 1.3.6.1.4.1.9839.2.1.1.16
        low-pw-req OBJECT-TYPE
                    SYNTAX Integer32 (0..1)
                    UNITS "N/A"
                    MAX-ACCESS read-only
                    STATUS current
                    DESCRIPTION "Low power consumption mode"
                    ::= { digitalObjects 16 }

        -- 1.3.6.1.4.1.9839.2.1.1.17
        inverno OBJECT-TYPE
                    SYNTAX Integer32 (0..1)
                    UNITS "N/A"
                    MAX-ACCESS read-only
                    STATUS current
                    DESCRIPTION "Winter mode"
                    ::= { digitalObjects 17 }

        -- 1.3.6.1.4.1.9839.2.1.1.18
        req-pompa-fc OBJECT-TYPE
                    SYNTAX Integer32 (0..1)
                    UNITS "N/A"
                    MAX-ACCESS read-only
                    STATUS current
                    DESCRIPTION "Free-cooling valve"
                    ::= { digitalObjects 18 }

        -- 1.3.6.1.4.1.9839.2.1.1.19
        pompa-fc OBJECT-TYPE
                    SYNTAX Integer32 (0..1)
                    UNITS "N/A"
                    MAX-ACCESS read-only
                    STATUS current
                    DESCRIPTION "Free-cooling pump"
                    ::= { digitalObjects 19 }

        -- 1.3.6.1.4.1.9839.2.1.1.21
        go-ucap OBJECT-TYPE
                    SYNTAX Integer32 (0..1)
                    UNITS "N/A"
                    MAX-ACCESS read-only
                    STATUS current
                    DESCRIPTION "Ucap working"
                    ::= { digitalObjects 21 }

        -- 1.3.6.1.4.1.9839.2.1.1.22
        reduct-pump OBJECT-TYPE
                    SYNTAX Integer32 (0..1)
                    UNITS "N/A"
                    MAX-ACCESS read-only
                    STATUS current
                    DESCRIPTION "Inverter pump reduced speed"
                    ::= { digitalObjects 22 }

        -- 1.3.6.1.4.1.9839.2.1.1.31
        preal-flux OBJECT-TYPE
                    SYNTAX Integer32 (0..1)
                    UNITS "N/A"
                    MAX-ACCESS read-only
                    STATUS current
                    DESCRIPTION "Loss of water flow prealarm (Autom.Reset)"
                    ::= { digitalObjects 31 }

        -- 1.3.6.1.4.1.9839.2.1.1.32
        al-flux OBJECT-TYPE
                    SYNTAX Integer32 (0..1)
                    UNITS "N/A"
                    MAX-ACCESS read-only
                    STATUS current
                    DESCRIPTION "Loss of water flow alarm (Autom.Reset)"
                    ::= { digitalObjects 32 }

        -- 1.3.6.1.4.1.9839.2.1.1.33
        preal-bp1 OBJECT-TYPE
                    SYNTAX Integer32 (0..1)
                    UNITS "N/A"
                    MAX-ACCESS read-only
                    STATUS current
                    DESCRIPTION "Low Pressure 1 PreAlarm (Autom.Reset)"
                    ::= { digitalObjects 33 }

        -- 1.3.6.1.4.1.9839.2.1.1.34
        preal-bp2 OBJECT-TYPE
                    SYNTAX Integer32 (0..1)
                    UNITS "N/A"
                    MAX-ACCESS read-only
                    STATUS current
                    DESCRIPTION "Low Pressure 2 PreAlarm (Autom.Reset)"
                    ::= { digitalObjects 34 }

        -- 1.3.6.1.4.1.9839.2.1.1.35
        al-bp1 OBJECT-TYPE
                    SYNTAX Integer32 (0..1)
                    UNITS "N/A"
                    MAX-ACCESS read-only
                    STATUS current
                    DESCRIPTION "Low Pressure 1 Alarm"
                    ::= { digitalObjects 35 }

        -- 1.3.6.1.4.1.9839.2.1.1.36
        al-bp2 OBJECT-TYPE
                    SYNTAX Integer32 (0..1)
                    UNITS "N/A"
                    MAX-ACCESS read-only
                    STATUS current
                    DESCRIPTION "Low Pressure 2 Alarm"
                    ::= { digitalObjects 36 }

        -- 1.3.6.1.4.1.9839.2.1.1.37
        mal-ap1 OBJECT-TYPE
                    SYNTAX Integer32 (0..1)
                    UNITS "N/A"
                    MAX-ACCESS read-only
                    STATUS current
                    DESCRIPTION "High Pressure 1 Alarm"
                    ::= { digitalObjects 37 }

        -- 1.3.6.1.4.1.9839.2.1.1.38
        mal-ap2 OBJECT-TYPE
                    SYNTAX Integer32 (0..1)
                    UNITS "N/A"
                    MAX-ACCESS read-only
                    STATUS current
                    DESCRIPTION "High Pressure 2 Alarm"
                    ::= { digitalObjects 38 }

        -- 1.3.6.1.4.1.9839.2.1.1.39
        preal-td-dgt1 OBJECT-TYPE
                    SYNTAX Integer32 (0..1)
                    UNITS "N/A"
                    MAX-ACCESS read-only
                    STATUS current
                    DESCRIPTION "Compressor 1 Overload Prealarm (Autom.Reset)"
                    ::= { digitalObjects 39 }

        -- 1.3.6.1.4.1.9839.2.1.1.40
        preal-td-dgt2 OBJECT-TYPE
                    SYNTAX Integer32 (0..1)
                    UNITS "N/A"
                    MAX-ACCESS read-only
                    STATUS current
                    DESCRIPTION "Compressor 2 Overload Prealarm (Autom.Reset)"
                    ::= { digitalObjects 40 }

        -- 1.3.6.1.4.1.9839.2.1.1.41
        preal-td-dgt3 OBJECT-TYPE
                    SYNTAX Integer32 (0..1)
                    UNITS "N/A"
                    MAX-ACCESS read-only
                    STATUS current
                    DESCRIPTION "Compressor 3 Overload Prealarm (Autom.Reset)"
                    ::= { digitalObjects 41 }

        -- 1.3.6.1.4.1.9839.2.1.1.42
        preal-td-dgt4 OBJECT-TYPE
                    SYNTAX Integer32 (0..1)
                    UNITS "N/A"
                    MAX-ACCESS read-only
                    STATUS current
                    DESCRIPTION "Compressor 4 Overload Prealarm (Autom.Reset)"
                    ::= { digitalObjects 42 }

        -- 1.3.6.1.4.1.9839.2.1.1.43
        al-tp-dgt1 OBJECT-TYPE
                    SYNTAX Integer32 (0..1)
                    UNITS "N/A"
                    MAX-ACCESS read-only
                    STATUS current
                    DESCRIPTION "Compressor 1 Overload Alarm"
                    ::= { digitalObjects 43 }

        -- 1.3.6.1.4.1.9839.2.1.1.44
        al-tp-dgt2 OBJECT-TYPE
                    SYNTAX Integer32 (0..1)
                    UNITS "N/A"
                    MAX-ACCESS read-only
                    STATUS current
                    DESCRIPTION "Compressor 2 Overload Alarm"
                    ::= { digitalObjects 44 }

        -- 1.3.6.1.4.1.9839.2.1.1.45
        al-tp-dgt3 OBJECT-TYPE
                    SYNTAX Integer32 (0..1)
                    UNITS "N/A"
                    MAX-ACCESS read-only
                    STATUS current
                    DESCRIPTION "Compressor 3 Overload Alarm"
                    ::= { digitalObjects 45 }

        -- 1.3.6.1.4.1.9839.2.1.1.46
        al-tp-dgt4 OBJECT-TYPE
                    SYNTAX Integer32 (0..1)
                    UNITS "N/A"
                    MAX-ACCESS read-only
                    STATUS current
                    DESCRIPTION "Compressor 4 Overload Alarm"
                    ::= { digitalObjects 46 }

        -- 1.3.6.1.4.1.9839.2.1.1.47
        mal-pompa1 OBJECT-TYPE
                    SYNTAX Integer32 (0..1)
                    UNITS "N/A"
                    MAX-ACCESS read-only
                    STATUS current
                    DESCRIPTION "Circulating Pump 1 Overload Alarm"
                    ::= { digitalObjects 47 }

        -- 1.3.6.1.4.1.9839.2.1.1.48
        mal-pompa2 OBJECT-TYPE
                    SYNTAX Integer32 (0..1)
                    UNITS "N/A"
                    MAX-ACCESS read-only
                    STATUS current
                    DESCRIPTION "Circulating Pump 2 Overload Alarm"
                    ::= { digitalObjects 48 }

        -- 1.3.6.1.4.1.9839.2.1.1.49
        mal-pompafc OBJECT-TYPE
                    SYNTAX Integer32 (0..1)
                    UNITS "N/A"
                    MAX-ACCESS read-only
                    STATUS current
                    DESCRIPTION "Free-cooling Pump Overload Alarm"
                    ::= { digitalObjects 49 }

        -- 1.3.6.1.4.1.9839.2.1.1.50
        preal-af1 OBJECT-TYPE
                    SYNTAX Integer32 (0..1)
                    UNITS "N/A"
                    MAX-ACCESS read-only
                    STATUS current
                    DESCRIPTION "Antifreeze 1 Prealarm (Automatic Reset)"
                    ::= { digitalObjects 50 }

        -- 1.3.6.1.4.1.9839.2.1.1.51
        preal-af2 OBJECT-TYPE
                    SYNTAX Integer32 (0..1)
                    UNITS "N/A"
                    MAX-ACCESS read-only
                    STATUS current
                    DESCRIPTION "Antifreeze 2 Prealarm (Automatic Reset)"
                    ::= { digitalObjects 51 }

        -- 1.3.6.1.4.1.9839.2.1.1.52
        al-af1 OBJECT-TYPE
                    SYNTAX Integer32 (0..1)
                    UNITS "N/A"
                    MAX-ACCESS read-only
                    STATUS current
                    DESCRIPTION "Antifreeze 1 Alarm"
                    ::= { digitalObjects 52 }

        -- 1.3.6.1.4.1.9839.2.1.1.53
        al-af2 OBJECT-TYPE
                    SYNTAX Integer32 (0..1)
                    UNITS "N/A"
                    MAX-ACCESS read-only
                    STATUS current
                    DESCRIPTION "Antifreeze 2 Alarm"
                    ::= { digitalObjects 53 }

        -- 1.3.6.1.4.1.9839.2.1.1.54
        preal-fase OBJECT-TYPE
                    SYNTAX Integer32 (0..1)
                    UNITS "N/A"
                    MAX-ACCESS read-only
                    STATUS current
                    DESCRIPTION "Fase sequence alarm (Automatic Reset)"
                    ::= { digitalObjects 54 }

        -- 1.3.6.1.4.1.9839.2.1.1.55
        al-fase OBJECT-TYPE
                    SYNTAX Integer32 (0..1)
                    UNITS "N/A"
                    MAX-ACCESS read-only
                    STATUS current
                    DESCRIPTION "Fase sequence alarm"
                    ::= { digitalObjects 55 }

        -- 1.3.6.1.4.1.9839.2.1.1.56
        preal-tp-fan OBJECT-TYPE
                    SYNTAX Integer32 (0..1)
                    UNITS "N/A"
                    MAX-ACCESS read-only
                    STATUS current
                    DESCRIPTION "Fans thermal Prealarm (Automatic Reset)"
                    ::= { digitalObjects 56 }

        -- 1.3.6.1.4.1.9839.2.1.1.57
        al-tp-fan OBJECT-TYPE
                    SYNTAX Integer32 (0..1)
                    UNITS "N/A"
                    MAX-ACCESS read-only
                    STATUS current
                    DESCRIPTION "Fans thermal alarm"
                    ::= { digitalObjects 57 }

        -- 1.3.6.1.4.1.9839.2.1.1.58
        mal-freq-rilev OBJECT-TYPE
                    SYNTAX Integer32 (0..1)
                    UNITS "N/A"
                    MAX-ACCESS read-only
                    STATUS current
                    DESCRIPTION "Net frequency error"
                    ::= { digitalObjects 58 }

        -- 1.3.6.1.4.1.9839.2.1.1.59
        mal-ht-win OBJECT-TYPE
                    SYNTAX Integer32 (0..1)
                    UNITS "N/A"
                    MAX-ACCESS read-only
                    STATUS current
                    DESCRIPTION "Water inlet High Temperature Alarm"
                    ::= { digitalObjects 59 }

        -- 1.3.6.1.4.1.9839.2.1.1.60
        mal-lt-win OBJECT-TYPE
                    SYNTAX Integer32 (0..1)
                    UNITS "N/A"
                    MAX-ACCESS read-only
                    STATUS current
                    DESCRIPTION "Water inlet Low Temperature Alarm"
                    ::= { digitalObjects 60 }

        -- 1.3.6.1.4.1.9839.2.1.1.61
        mal-sonda-twin OBJECT-TYPE
                    SYNTAX Integer32 (0..1)
                    UNITS "N/A"
                    MAX-ACCESS read-only
                    STATUS current
                    DESCRIPTION "Water Inlet Temp. Sensor Failure/Disconnected"
                    ::= { digitalObjects 61 }

        -- 1.3.6.1.4.1.9839.2.1.1.62
        mal-sonda-twout OBJECT-TYPE
                    SYNTAX Integer32 (0..1)
                    UNITS "N/A"
                    MAX-ACCESS read-only
                    STATUS current
                    DESCRIPTION "Water Outlet Temp. Sensor Failure/Disconnected"
                    ::= { digitalObjects 62 }

        -- 1.3.6.1.4.1.9839.2.1.1.63
        mal-sonda-twaccu OBJECT-TYPE
                    SYNTAX Integer32 (0..1)
                    UNITS "N/A"
                    MAX-ACCESS read-only
                    STATUS current
                    DESCRIPTION "Water Tank Temp. Sensor Failure/Disconnected"
                    ::= { digitalObjects 63 }

        -- 1.3.6.1.4.1.9839.2.1.1.64
        mal-sonda-te OBJECT-TYPE
                    SYNTAX Integer32 (0..1)
                    UNITS "N/A"
                    MAX-ACCESS read-only
                    STATUS current
                    DESCRIPTION "Outdoor air Temp. Sensor Failure/Disconnected"
                    ::= { digitalObjects 64 }

        -- 1.3.6.1.4.1.9839.2.1.1.65
        mal-sonda-pc1 OBJECT-TYPE
                    SYNTAX Integer32 (0..1)
                    UNITS "N/A"
                    MAX-ACCESS read-only
                    STATUS current
                    DESCRIPTION "Condensing 1 Press. Sensor Failure/Disconnected"
                    ::= { digitalObjects 65 }

        -- 1.3.6.1.4.1.9839.2.1.1.66
        mal-sonda-pc2 OBJECT-TYPE
                    SYNTAX Integer32 (0..1)
                    UNITS "N/A"
                    MAX-ACCESS read-only
                    STATUS current
                    DESCRIPTION "Condensing 2 Press. Sensor Failure/Disconnected"
                    ::= { digitalObjects 66 }

        -- 1.3.6.1.4.1.9839.2.1.1.67
        mal-sonda-pev1 OBJECT-TYPE
                    SYNTAX Integer32 (0..1)
                    UNITS "N/A"
                    MAX-ACCESS read-only
                    STATUS current
                    DESCRIPTION "Evaporating 1 Press. Sensor Failure/Disconnected"
                    ::= { digitalObjects 67 }

        -- 1.3.6.1.4.1.9839.2.1.1.68
        mal-sonda-pev2 OBJECT-TYPE
                    SYNTAX Integer32 (0..1)
                    UNITS "N/A"
                    MAX-ACCESS read-only
                    STATUS current
                    DESCRIPTION "Evaporating 2 Press. Sensor Failure/Disconnected"
                    ::= { digitalObjects 68 }

        -- 1.3.6.1.4.1.9839.2.1.1.69
        mal-sonda-pin OBJECT-TYPE
                    SYNTAX Integer32 (0..1)
                    UNITS "N/A"
                    MAX-ACCESS read-only
                    STATUS current
                    DESCRIPTION "Water Inlet Press. Sensor Failure/Disconnected"
                    ::= { digitalObjects 69 }

        -- 1.3.6.1.4.1.9839.2.1.1.70
        mal-sonda-pout OBJECT-TYPE
                    SYNTAX Integer32 (0..1)
                    UNITS "N/A"
                    MAX-ACCESS read-only
                    STATUS current
                    DESCRIPTION "Water Outlet Press. Sensor Failure/Disconnected"
                    ::= { digitalObjects 70 }

        -- 1.3.6.1.4.1.9839.2.1.1.71
        mal-probe-s2-c1 OBJECT-TYPE
                    SYNTAX Integer32 (0..1)
                    UNITS "N/A"
                    MAX-ACCESS read-only
                    STATUS current
                    DESCRIPTION "EXV 1 Temp. Sensor Failure/Disconnected"
                    ::= { digitalObjects 71 }

        -- 1.3.6.1.4.1.9839.2.1.1.72
        mal-probe-s2-c2 OBJECT-TYPE
                    SYNTAX Integer32 (0..1)
                    UNITS "N/A"
                    MAX-ACCESS read-only
                    STATUS current
                    DESCRIPTION "EXV 2 Temp. Sensor Failure/Disconnected"
                    ::= { digitalObjects 72 }

        -- 1.3.6.1.4.1.9839.2.1.1.73
        malarm-s4-c1 OBJECT-TYPE
                    SYNTAX Integer32 (0..1)
                    UNITS "N/A"
                    MAX-ACCESS read-only
                    STATUS current
                    DESCRIPTION "EXV 1 Press. Sensor Failure/Disconnected"
                    ::= { digitalObjects 73 }

        -- 1.3.6.1.4.1.9839.2.1.1.74
        malarm-s4-c2 OBJECT-TYPE
                    SYNTAX Integer32 (0..1)
                    UNITS "N/A"
                    MAX-ACCESS read-only
                    STATUS current
                    DESCRIPTION "EXV 2 Press. Sensor Failure/Disconnected"
                    ::= { digitalObjects 74 }

        -- 1.3.6.1.4.1.9839.2.1.1.75
        mod-pcoe-1-al-ainch1 OBJECT-TYPE
                    SYNTAX Integer32 (0..1)
                    UNITS "N/A"
                    MAX-ACCESS read-only
                    STATUS current
                    DESCRIPTION "Heat recovery Water Input Temp. Sensor Failure/Disconnected"
                    ::= { digitalObjects 75 }

        -- 1.3.6.1.4.1.9839.2.1.1.76
        mod-pcoe-1-al-ainch2 OBJECT-TYPE
                    SYNTAX Integer32 (0..1)
                    UNITS "N/A"
                    MAX-ACCESS read-only
                    STATUS current
                    DESCRIPTION "Heat recovery Water Output Temp. Sensor Failure/Disconnected"
                    ::= { digitalObjects 76 }

        -- 1.3.6.1.4.1.9839.2.1.1.77
        mod-pcoe-1-al-ainch3 OBJECT-TYPE
                    SYNTAX Integer32 (0..1)
                    UNITS "N/A"
                    MAX-ACCESS read-only
                    STATUS current
                    DESCRIPTION "Water Tank Temp. Sensor Failure/Disconnected"
                    ::= { digitalObjects 77 }

        -- 1.3.6.1.4.1.9839.2.1.1.78
        mod-pcoe-1-al-ainch4 OBJECT-TYPE
                    SYNTAX Integer32 (0..1)
                    UNITS "N/A"
                    MAX-ACCESS read-only
                    STATUS current
                    DESCRIPTION "Additional Temp. Sensor Failure/Disconnected"
                    ::= { digitalObjects 78 }

        -- 1.3.6.1.4.1.9839.2.1.1.79
        mod-pcoe-1al-i-o-mismatch OBJECT-TYPE
                    SYNTAX Integer32 (0..1)
                    UNITS "N/A"
                    MAX-ACCESS read-only
                    STATUS current
                    DESCRIPTION "Reserved"
                    ::= { digitalObjects 79 }

        -- 1.3.6.1.4.1.9839.2.1.1.80
        pcoe-al-offline OBJECT-TYPE
                    SYNTAX Integer32 (0..1)
                    UNITS "N/A"
                    MAX-ACCESS read-only
                    STATUS current
                    DESCRIPTION "pCOe (address 3) expansion board offline"
                    ::= { digitalObjects 80 }

        -- 1.3.6.1.4.1.9839.2.1.1.81
        mal-ore-compr1 OBJECT-TYPE
                    SYNTAX Integer32 (0..1)
                    UNITS "N/A"
                    MAX-ACCESS read-only
                    STATUS current
                    DESCRIPTION "Compressor 1: hour counter threshold Alarm "
                    ::= { digitalObjects 81 }

        -- 1.3.6.1.4.1.9839.2.1.1.82
        mal-ore-compr2 OBJECT-TYPE
                    SYNTAX Integer32 (0..1)
                    UNITS "N/A"
                    MAX-ACCESS read-only
                    STATUS current
                    DESCRIPTION "Compressor 2: hour counter threshold Alarm "
                    ::= { digitalObjects 82 }

        -- 1.3.6.1.4.1.9839.2.1.1.83
        mal-ore-compr3 OBJECT-TYPE
                    SYNTAX Integer32 (0..1)
                    UNITS "N/A"
                    MAX-ACCESS read-only
                    STATUS current
                    DESCRIPTION "Compressor 3: hour counter threshold Alarm "
                    ::= { digitalObjects 83 }

        -- 1.3.6.1.4.1.9839.2.1.1.84
        mal-ore-compr4 OBJECT-TYPE
                    SYNTAX Integer32 (0..1)
                    UNITS "N/A"
                    MAX-ACCESS read-only
                    STATUS current
                    DESCRIPTION "Compressor 4: hour counter threshold Alarm "
                    ::= { digitalObjects 84 }

        -- 1.3.6.1.4.1.9839.2.1.1.85
        mal-ore-pump1 OBJECT-TYPE
                    SYNTAX Integer32 (0..1)
                    UNITS "N/A"
                    MAX-ACCESS read-only
                    STATUS current
                    DESCRIPTION "Circulating Pump 1: hour counter threshold Alarm"
                    ::= { digitalObjects 85 }

        -- 1.3.6.1.4.1.9839.2.1.1.86
        mal-ore-pump2 OBJECT-TYPE
                    SYNTAX Integer32 (0..1)
                    UNITS "N/A"
                    MAX-ACCESS read-only
                    STATUS current
                    DESCRIPTION "Circulating Pump 2: hour counter threshold Alarm"
                    ::= { digitalObjects 86 }

        -- 1.3.6.1.4.1.9839.2.1.1.87
        mal-ore-pumpfc OBJECT-TYPE
                    SYNTAX Integer32 (0..1)
                    UNITS "N/A"
                    MAX-ACCESS read-only
                    STATUS current
                    DESCRIPTION "Free-Cooling Pump: hour counter threshold Alarm"
                    ::= { digitalObjects 87 }

        -- 1.3.6.1.4.1.9839.2.1.1.88
        mal-access OBJECT-TYPE
                    SYNTAX Integer32 (0..1)
                    UNITS "N/A"
                    MAX-ACCESS read-only
                    STATUS current
                    DESCRIPTION "Wrong password Alarm"
                    ::= { digitalObjects 88 }

        -- 1.3.6.1.4.1.9839.2.1.1.89
        perm-mem-error OBJECT-TYPE
                    SYNTAX Integer32 (0..1)
                    UNITS "N/A"
                    MAX-ACCESS read-only
                    STATUS current
                    DESCRIPTION "Main Board EEPROM failure"
                    ::= { digitalObjects 89 }

        -- 1.3.6.1.4.1.9839.2.1.1.90
        al-lan OBJECT-TYPE
                    SYNTAX Integer32 (0..1)
                    UNITS "N/A"
                    MAX-ACCESS read-only
                    STATUS current
                    DESCRIPTION "Interrupted LAN Alarm"
                    ::= { digitalObjects 90 }

        -- 1.3.6.1.4.1.9839.2.1.1.91
        preal-hr1 OBJECT-TYPE
                    SYNTAX Integer32 (0..1)
                    UNITS "N/A"
                    MAX-ACCESS read-only
                    STATUS current
                    DESCRIPTION "Heat recovery 1 limit PreAlarm (Autom.Reset)"
                    ::= { digitalObjects 91 }

        -- 1.3.6.1.4.1.9839.2.1.1.92
        preal-hr2 OBJECT-TYPE
                    SYNTAX Integer32 (0..1)
                    UNITS "N/A"
                    MAX-ACCESS read-only
                    STATUS current
                    DESCRIPTION "Heat recovery 2 limit PreAlarm (Autom.Reset)"
                    ::= { digitalObjects 92 }

        -- 1.3.6.1.4.1.9839.2.1.1.93
        al-hr1 OBJECT-TYPE
                    SYNTAX Integer32 (0..1)
                    UNITS "N/A"
                    MAX-ACCESS read-only
                    STATUS current
                    DESCRIPTION "Heat recovery 1 limit Alarm"
                    ::= { digitalObjects 93 }

        -- 1.3.6.1.4.1.9839.2.1.1.94
        al-hr2 OBJECT-TYPE
                    SYNTAX Integer32 (0..1)
                    UNITS "N/A"
                    MAX-ACCESS read-only
                    STATUS current
                    DESCRIPTION "Heat recovery 2 limit Alarm"
                    ::= { digitalObjects 94 }

        -- 1.3.6.1.4.1.9839.2.1.1.95
        mal-valve-c1 OBJECT-TYPE
                    SYNTAX Integer32 (0..1)
                    UNITS "N/A"
                    MAX-ACCESS read-only
                    STATUS current
                    DESCRIPTION "Expansion valve 1 alarm"
                    ::= { digitalObjects 95 }

        -- 1.3.6.1.4.1.9839.2.1.1.96
        mal-valve-c2 OBJECT-TYPE
                    SYNTAX Integer32 (0..1)
                    UNITS "N/A"
                    MAX-ACCESS read-only
                    STATUS current
                    DESCRIPTION "Expansion valve 2 alarm"
                    ::= { digitalObjects 96 }

        -- 1.3.6.1.4.1.9839.2.1.1.97
        mal-low-sheat-c1 OBJECT-TYPE
                    SYNTAX Integer32 (0..1)
                    UNITS "N/A"
                    MAX-ACCESS read-only
                    STATUS current
                    DESCRIPTION "Expansion valve 1 Low Superheat"
                    ::= { digitalObjects 97 }

        -- 1.3.6.1.4.1.9839.2.1.1.98
        mal-low-sheat-c2 OBJECT-TYPE
                    SYNTAX Integer32 (0..1)
                    UNITS "N/A"
                    MAX-ACCESS read-only
                    STATUS current
                    DESCRIPTION "Expansion valve 2 Low Superheat"
                    ::= { digitalObjects 98 }

        -- 1.3.6.1.4.1.9839.2.1.1.99
        mal-lop-c1 OBJECT-TYPE
                    SYNTAX Integer32 (0..1)
                    UNITS "N/A"
                    MAX-ACCESS read-only
                    STATUS current
                    DESCRIPTION "Expansion valve 1 LOP protection alarm"
                    ::= { digitalObjects 99 }

        -- 1.3.6.1.4.1.9839.2.1.1.100
        mal-lop-c2 OBJECT-TYPE
                    SYNTAX Integer32 (0..1)
                    UNITS "N/A"
                    MAX-ACCESS read-only
                    STATUS current
                    DESCRIPTION "Expansion valve 2 LOP protection alarm"
                    ::= { digitalObjects 100 }

        -- 1.3.6.1.4.1.9839.2.1.1.101
        mal-mop-c1 OBJECT-TYPE
                    SYNTAX Integer32 (0..1)
                    UNITS "N/A"
                    MAX-ACCESS read-only
                    STATUS current
                    DESCRIPTION "Expansion valve 1 MOP protection alarm"
                    ::= { digitalObjects 101 }

        -- 1.3.6.1.4.1.9839.2.1.1.102
        mal-mop-c2 OBJECT-TYPE
                    SYNTAX Integer32 (0..1)
                    UNITS "N/A"
                    MAX-ACCESS read-only
                    STATUS current
                    DESCRIPTION "Expansion valve 2 MOP protection alarm"
                    ::= { digitalObjects 102 }

        -- 1.3.6.1.4.1.9839.2.1.1.103
        mal-mot-c1 OBJECT-TYPE
                    SYNTAX Integer32 (0..1)
                    UNITS "N/A"
                    MAX-ACCESS read-only
                    STATUS current
                    DESCRIPTION "Expansion valve 1 motor alarm"
                    ::= { digitalObjects 103 }

        -- 1.3.6.1.4.1.9839.2.1.1.104
        mal-mot-c2 OBJECT-TYPE
                    SYNTAX Integer32 (0..1)
                    UNITS "N/A"
                    MAX-ACCESS read-only
                    STATUS current
                    DESCRIPTION "Expansion valve 2 motor alarm"
                    ::= { digitalObjects 104 }

        -- 1.3.6.1.4.1.9839.2.1.1.105
        mal-eeprom-c1 OBJECT-TYPE
                    SYNTAX Integer32 (0..1)
                    UNITS "N/A"
                    MAX-ACCESS read-only
                    STATUS current
                    DESCRIPTION "Expansion valve 1 driver EEPROM failure"
                    ::= { digitalObjects 105 }

        -- 1.3.6.1.4.1.9839.2.1.1.106
        mal-eeprom-c2 OBJECT-TYPE
                    SYNTAX Integer32 (0..1)
                    UNITS "N/A"
                    MAX-ACCESS read-only
                    STATUS current
                    DESCRIPTION "Expansion valve 2 driver EEPROM failure"
                    ::= { digitalObjects 106 }

        -- 1.3.6.1.4.1.9839.2.1.1.107
        mal-exv-no-line-c1 OBJECT-TYPE
                    SYNTAX Integer32 (0..1)
                    UNITS "N/A"
                    MAX-ACCESS read-only
                    STATUS current
                    DESCRIPTION "Expansion valve 1 driver offline"
                    ::= { digitalObjects 107 }

        -- 1.3.6.1.4.1.9839.2.1.1.108
        mal-exv-no-line-c2 OBJECT-TYPE
                    SYNTAX Integer32 (0..1)
                    UNITS "N/A"
                    MAX-ACCESS read-only
                    STATUS current
                    DESCRIPTION "Expansion valve 2 driver offline"
                    ::= { digitalObjects 108 }

        -- 1.3.6.1.4.1.9839.2.1.1.109
        mbattery-alarm1 OBJECT-TYPE
                    SYNTAX Integer32 (0..1)
                    UNITS "N/A"
                    MAX-ACCESS read-only
                    STATUS current
                    DESCRIPTION "Reserved"
                    ::= { digitalObjects 109 }

        -- 1.3.6.1.4.1.9839.2.1.1.110
        mbattery-alarm2 OBJECT-TYPE
                    SYNTAX Integer32 (0..1)
                    UNITS "N/A"
                    MAX-ACCESS read-only
                    STATUS current
                    DESCRIPTION "Reserved"
                    ::= { digitalObjects 110 }

        -- 1.3.6.1.4.1.9839.2.1.1.111
        or-al-firm-evd OBJECT-TYPE
                    SYNTAX Integer32 (0..1)
                    UNITS "N/A"
                    MAX-ACCESS read-only
                    STATUS current
                    DESCRIPTION "Expansion valve driver firmware failure"
                    ::= { digitalObjects 111 }

        -- 1.3.6.1.4.1.9839.2.1.1.112
        mal-valvola-fc OBJECT-TYPE
                    SYNTAX Integer32 (0..1)
                    UNITS "N/A"
                    MAX-ACCESS read-only
                    STATUS current
                    DESCRIPTION "Freecooling motorized valve blocked"
                    ::= { digitalObjects 112 }

        -- 1.3.6.1.4.1.9839.2.1.1.113
        mal-hi-wat-pres OBJECT-TYPE
                    SYNTAX Integer32 (0..1)
                    UNITS "N/A"
                    MAX-ACCESS read-only
                    STATUS current
                    DESCRIPTION "Water High Pressure Alarm"
                    ::= { digitalObjects 113 }

        -- 1.3.6.1.4.1.9839.2.1.1.114
        mal-low-wat-pres OBJECT-TYPE
                    SYNTAX Integer32 (0..1)
                    UNITS "N/A"
                    MAX-ACCESS read-only
                    STATUS current
                    DESCRIPTION "Water Low Pressure Alarm"
                    ::= { digitalObjects 114 }

        -- 1.3.6.1.4.1.9839.2.1.1.115
        al-offline-pump OBJECT-TYPE
                    SYNTAX Integer32 (0..1)
                    UNITS "N/A"
                    MAX-ACCESS read-only
                    STATUS current
                    DESCRIPTION "Inverter pump driver offline"
                    ::= { digitalObjects 115 }

        -- 1.3.6.1.4.1.9839.2.1.1.116
        reserved-dig OBJECT-TYPE
                    SYNTAX Integer32 (0..1)
                    UNITS "N/A"
                    MAX-ACCESS read-only
                    STATUS current
                    DESCRIPTION "Reserved"
                    ::= { digitalObjects 116 }

        -- 1.3.6.1.4.1.9839.2.1.1.117
        al-inverter-pump OBJECT-TYPE
                    SYNTAX Integer32 (0..1)
                    UNITS "N/A"
                    MAX-ACCESS read-only
                    STATUS current
                    DESCRIPTION "Inverter pump driver alarm"
                    ::= { digitalObjects 117 }

        -- 1.3.6.1.4.1.9839.2.1.1.118
        mal-powersupply-failure OBJECT-TYPE
                    SYNTAX Integer32 (0..1)
                    UNITS "N/A"
                    MAX-ACCESS read-only
                    STATUS current
                    DESCRIPTION "Powersupply failure"
                    ::= { digitalObjects 118 }

        -- 1.3.6.1.4.1.9839.2.1.1.120
        mal-flux-pump-hr OBJECT-TYPE
                    SYNTAX Integer32 (0..1)
                    UNITS "N/A"
                    MAX-ACCESS read-only
                    STATUS current
                    DESCRIPTION "Heat recovery Loss of water flow alarm"
                    ::= { digitalObjects 120 }

        -- 1.3.6.1.4.1.9839.2.1.1.121
        mal-offline-pms OBJECT-TYPE
                    SYNTAX Integer32 (0..1)
                    UNITS "N/A"
                    MAX-ACCESS read-only
                    STATUS current
                    DESCRIPTION "Energy meter offline"
                    ::= { digitalObjects 121 }

        -- 1.3.6.1.4.1.9839.2.1.1.122
        mal-offline-sez-mot OBJECT-TYPE
                    SYNTAX Integer32 (0..1)
                    UNITS "N/A"
                    MAX-ACCESS read-only
                    STATUS current
                    DESCRIPTION "Motorized switch offline"
                    ::= { digitalObjects 122 }

        -- 1.3.6.1.4.1.9839.2.1.1.123
        mal-fuse-fault OBJECT-TYPE
                    SYNTAX Integer32 (0..1)
                    UNITS "N/A"
                    MAX-ACCESS read-only
                    STATUS current
                    DESCRIPTION "Electric Heaters Fuse Fault"
                    ::= { digitalObjects 123 }

        -- 1.3.6.1.4.1.9839.2.1.1.127
        mal-gas-leak OBJECT-TYPE
                    SYNTAX Integer32 (0..1)
                    UNITS "N/A"
                    MAX-ACCESS read-only
                    STATUS current
                    DESCRIPTION "Gas Leakage Detection"
                    ::= { digitalObjects 127 }

        -- 1.3.6.1.4.1.9839.2.1.1.128
        mal-ore-gas-leak OBJECT-TYPE
                    SYNTAX Integer32 (0..1)
                    UNITS "N/A"
                    MAX-ACCESS read-only
                    STATUS current
                    DESCRIPTION "Gas Leakage Detection: hour counter threshold Alarm"
                    ::= { digitalObjects 128 }

        -- 1.3.6.1.4.1.9839.2.1.1.129
        mal-sonda-tmand OBJECT-TYPE
                    SYNTAX Integer32 (0..1)
                    UNITS "N/A"
                    MAX-ACCESS read-only
                    STATUS current
                    DESCRIPTION "Compressor inverter discharge Temp. Sensor Failure/Disconnected"
                    ::= { digitalObjects 129 }

        -- 1.3.6.1.4.1.9839.2.1.1.130
        mal-preal-oil-circ1 OBJECT-TYPE
                    SYNTAX Integer32 (0..1)
                    UNITS "N/A"
                    MAX-ACCESS read-only
                    STATUS current
                    DESCRIPTION "Compressor inverter low oil level"
                    ::= { digitalObjects 130 }

        -- 1.3.6.1.4.1.9839.2.1.1.131
        or-al-trip-c1-inv OBJECT-TYPE
                    SYNTAX Integer32 (0..1)
                    UNITS "N/A"
                    MAX-ACCESS read-only
                    STATUS current
                    DESCRIPTION "Compressor inverter trip alarm"
                    ::= { digitalObjects 131 }

        -- 1.3.6.1.4.1.9839.2.1.1.132
        or-al-no-trip-c1-inv OBJECT-TYPE
                    SYNTAX Integer32 (0..1)
                    UNITS "N/A"
                    MAX-ACCESS read-only
                    STATUS current
                    DESCRIPTION "Compressor inverter no trip alarm"
                    ::= { digitalObjects 132 }

        -- 1.3.6.1.4.1.9839.2.1.1.133
        al-configerr-evd1-2 OBJECT-TYPE
                    SYNTAX Integer32 (0..1)
                    UNITS "N/A"
                    MAX-ACCESS read-only
                    STATUS current
                    DESCRIPTION "EVD Driver Error trasmission parameters"
                    ::= { digitalObjects 133 }

        -- 1.3.6.1.4.1.9839.2.1.1.134
        mal-sonda-twout2 OBJECT-TYPE
                    SYNTAX Integer32 (0..1)
                    UNITS "N/A"
                    MAX-ACCESS read-only
                    STATUS current
                    DESCRIPTION "Water circuit 2 Outlet Temp. Sensor Failure/Disconnected (ERA bicircuit)"
                    ::= { digitalObjects 134 }

        -- 1.3.6.1.4.1.9839.2.1.1.135
        pcoe4-al-offline OBJECT-TYPE
                    SYNTAX Integer32 (0..1)
                    UNITS "N/A"
                    MAX-ACCESS read-only
                    STATUS current
                    DESCRIPTION "pCOe (address 4) expansion board offline"
                    ::= { digitalObjects 135 }

        -- 1.3.6.1.4.1.9839.2.1.1.136
        mal-ht-disch-c1 OBJECT-TYPE
                    SYNTAX Integer32 (0..1)
                    UNITS "N/A"
                    MAX-ACCESS read-only
                    STATUS current
                    DESCRIPTION "Compressor inverter hi discharge temperature"
                    ::= { digitalObjects 136 }

        -- 1.3.6.1.4.1.9839.2.1.1.137
        al-out-limit-c1 OBJECT-TYPE
                    SYNTAX Integer32 (0..1)
                    UNITS "N/A"
                    MAX-ACCESS read-only
                    STATUS current
                    DESCRIPTION "Compressor inverter operative limits"
                    ::= { digitalObjects 137 }

        -- 1.3.6.1.4.1.9839.2.1.1.147
        global-alarm OBJECT-TYPE
                    SYNTAX Integer32 (0..1)
                    UNITS "N/A"
                    MAX-ACCESS read-only
                    STATUS current
                    DESCRIPTION "General Alarm State"
                    ::= { digitalObjects 147 }

        -- 1.3.6.1.4.1.9839.2.1.1.148
        or-al-2lev OBJECT-TYPE
                    SYNTAX Integer32 (0..1)
                    UNITS "N/A"
                    MAX-ACCESS read-only
                    STATUS current
                    DESCRIPTION "Alarm Rotation"
                    ::= { digitalObjects 148 }

        -- 1.3.6.1.4.1.9839.2.1.1.149
        alarm-a OBJECT-TYPE
                    SYNTAX Integer32 (0..1)
                    UNITS "N/A"
                    MAX-ACCESS read-only
                    STATUS current
                    DESCRIPTION "Type A Alarm"
                    ::= { digitalObjects 149 }

        -- 1.3.6.1.4.1.9839.2.1.1.150
        alarm-b OBJECT-TYPE
                    SYNTAX Integer32 (0..1)
                    UNITS "N/A"
                    MAX-ACCESS read-only
                    STATUS current
                    DESCRIPTION "Type B Alarm"
                    ::= { digitalObjects 150 }

        -- 1.3.6.1.4.1.9839.2.1.1.151
        etv-cond1 OBJECT-TYPE
                    SYNTAX Integer32 (0..1)
                    UNITS "N/A"
                    MAX-ACCESS read-only
                    STATUS current
                    DESCRIPTION "Condensing coil 1 Refrigerant shut-off valve"
                    ::= { digitalObjects 151 }

        -- 1.3.6.1.4.1.9839.2.1.1.152
        etv-cond2 OBJECT-TYPE
                    SYNTAX Integer32 (0..1)
                    UNITS "N/A"
                    MAX-ACCESS read-only
                    STATUS current
                    DESCRIPTION "Condensing coil 2 Refrigerant shut-off valve"
                    ::= { digitalObjects 152 }

        -- 1.3.6.1.4.1.9839.2.1.1.201
        k-syson OBJECT-TYPE
                    SYNTAX Integer32 (0..1)
                    UNITS "N/A"
                    MAX-ACCESS read-write
                    STATUS current
                    DESCRIPTION "Unit Remote Switch-On/Off Control"
                    ::= { digitalObjects 201 }

        -- 1.3.6.1.4.1.9839.2.1.1.202
        k-est-inv OBJECT-TYPE
                    SYNTAX Integer32 (0..1)
                    UNITS "N/A"
                    MAX-ACCESS read-write
                    STATUS current
                    DESCRIPTION "Summer/Winter mode remote control"
                    ::= { digitalObjects 202 }

        -- 1.3.6.1.4.1.9839.2.1.1.203
        xs-res-al OBJECT-TYPE
                    SYNTAX Integer32 (0..1)
                    UNITS "N/A"
                    MAX-ACCESS read-write
                    STATUS current
                    DESCRIPTION "Buzzer and Alarm Remote Reset Control"
                    ::= { digitalObjects 203 }

        -- 1.3.6.1.4.1.9839.2.1.1.205
        lowp-sp OBJECT-TYPE
                    SYNTAX Integer32 (0..1)
                    UNITS "N/A"
                    MAX-ACCESS read-write
                    STATUS current
                    DESCRIPTION "Low power consumption enable"
                    ::= { digitalObjects 205 }

        -- 1.3.6.1.4.1.9839.2.1.1.207
        sleeo-mode OBJECT-TYPE
                    SYNTAX Integer32 (0..1)
                    UNITS "N/A"
                    MAX-ACCESS read-write
                    STATUS current
                    DESCRIPTION "Set Back Mode (Sleep Mode)"
                    ::= { digitalObjects 207 }



        -- 1.3.6.1.4.1.9839.2.1.2
        analogObjects OBJECT IDENTIFIER ::= { aquascrollMIB 2 }

        -- 1.3.6.1.4.1.9839.2.1.2.1
        temp-wout OBJECT-TYPE
                    SYNTAX Integer32 (12345..12345)
                    UNITS "C x10"
                    MAX-ACCESS read-only
                    STATUS current
                    DESCRIPTION "Water Outlet Temperature"
                    ::= { analogObjects 1 }

        -- 1.3.6.1.4.1.9839.2.1.2.2
        t-wout-regol OBJECT-TYPE
                    SYNTAX Integer32 (12345..12345)
                    UNITS "C x10"
                    MAX-ACCESS read-only
                    STATUS current
                    DESCRIPTION "Water Outlet Temp. used by regulator"
                    ::= { analogObjects 2 }

        -- 1.3.6.1.4.1.9839.2.1.2.3
        temp-win OBJECT-TYPE
                    SYNTAX Integer32 (12345..12345)
                    UNITS "C x10"
                    MAX-ACCESS read-only
                    STATUS current
                    DESCRIPTION "Water Inlet Temperature"
                    ::= { analogObjects 3 }

        -- 1.3.6.1.4.1.9839.2.1.2.4
        temp-waccu OBJECT-TYPE
                    SYNTAX Integer32 (12345..12345)
                    UNITS "C x10"
                    MAX-ACCESS read-only
                    STATUS current
                    DESCRIPTION "Water Tank Temperature"
                    ::= { analogObjects 4 }

        -- 1.3.6.1.4.1.9839.2.1.2.5
        temp-ext OBJECT-TYPE
                    SYNTAX Integer32 (12345..12345)
                    UNITS "C x10"
                    MAX-ACCESS read-only
                    STATUS current
                    DESCRIPTION "Outdoor Air Temperature"
                    ::= { analogObjects 5 }

        -- 1.3.6.1.4.1.9839.2.1.2.6
        temp-cond1 OBJECT-TYPE
                    SYNTAX Integer32 (12345..12345)
                    UNITS "C x10"
                    MAX-ACCESS read-only
                    STATUS current
                    DESCRIPTION "Circuit 1 Condensing Temperature"
                    ::= { analogObjects 6 }

        -- 1.3.6.1.4.1.9839.2.1.2.7
        temp-cond2 OBJECT-TYPE
                    SYNTAX Integer32 (12345..12345)
                    UNITS "C x10"
                    MAX-ACCESS read-only
                    STATUS current
                    DESCRIPTION "Circuit 2 Condensing Temperature"
                    ::= { analogObjects 7 }

        -- 1.3.6.1.4.1.9839.2.1.2.8
        temp-evap1 OBJECT-TYPE
                    SYNTAX Integer32 (12345..12345)
                    UNITS "C x10"
                    MAX-ACCESS read-only
                    STATUS current
                    DESCRIPTION "Circuit 1 Evaporating Temperature"
                    ::= { analogObjects 8 }

        -- 1.3.6.1.4.1.9839.2.1.2.9
        temp-evap2 OBJECT-TYPE
                    SYNTAX Integer32 (12345..12345)
                    UNITS "C x10"
                    MAX-ACCESS read-only
                    STATUS current
                    DESCRIPTION "Circuit 2 Evaporating Temperature"
                    ::= { analogObjects 9 }

        -- 1.3.6.1.4.1.9839.2.1.2.10
        press-cond1 OBJECT-TYPE
                    SYNTAX Integer32 (12345..12345)
                    UNITS "bar x10"
                    MAX-ACCESS read-only
                    STATUS current
                    DESCRIPTION "Circuit 1 Condensing Pressure "
                    ::= { analogObjects 10 }

        -- 1.3.6.1.4.1.9839.2.1.2.11
        press-cond2 OBJECT-TYPE
                    SYNTAX Integer32 (12345..12345)
                    UNITS "bar x10"
                    MAX-ACCESS read-only
                    STATUS current
                    DESCRIPTION "Circuit 2 Condensing Pressure"
                    ::= { analogObjects 11 }

        -- 1.3.6.1.4.1.9839.2.1.2.12
        press-evap1 OBJECT-TYPE
                    SYNTAX Integer32 (12345..12345)
                    UNITS "bar x10"
                    MAX-ACCESS read-only
                    STATUS current
                    DESCRIPTION "Circuit 1 Evaporating Pressure"
                    ::= { analogObjects 12 }

        -- 1.3.6.1.4.1.9839.2.1.2.13
        press-evap2 OBJECT-TYPE
                    SYNTAX Integer32 (12345..12345)
                    UNITS "bar x10"
                    MAX-ACCESS read-only
                    STATUS current
                    DESCRIPTION "Circuit 2 Evaporating Pressure"
                    ::= { analogObjects 13 }

        -- 1.3.6.1.4.1.9839.2.1.2.14
        rampa-vent OBJECT-TYPE
                    SYNTAX Integer32 (12345..12345)
                    UNITS "% x10"
                    MAX-ACCESS read-only
                    STATUS current
                    DESCRIPTION "Fan Speed Modul.Ramp (0-100,0%)"
                    ::= { analogObjects 14 }

        -- 1.3.6.1.4.1.9839.2.1.2.15
        t-set-regol OBJECT-TYPE
                    SYNTAX Integer32 (12345..12345)
                    UNITS "C x10"
                    MAX-ACCESS read-only
                    STATUS current
                    DESCRIPTION "Delivery Water Temp. Actual Set Point"
                    ::= { analogObjects 15 }

        -- 1.3.6.1.4.1.9839.2.1.2.16
        zona-neutra OBJECT-TYPE
                    SYNTAX Integer32 (12345..12345)
                    UNITS "C x10"
                    MAX-ACCESS read-only
                    STATUS current
                    DESCRIPTION "Delivery Water Temp. Max. Hysteresi"
                    ::= { analogObjects 16 }

        -- 1.3.6.1.4.1.9839.2.1.2.17
        ofs-spv OBJECT-TYPE
                    SYNTAX Integer32 (1..30)
                    UNITS "N/A"
                    MAX-ACCESS read-write
                    STATUS current
                    DESCRIPTION "Offset supervisor"
                    ::= { analogObjects 17 }

        -- 1.3.6.1.4.1.9839.2.1.2.18
        t-set-e OBJECT-TYPE
                    SYNTAX Integer32 (60..130)
                    UNITS "C x10"
                    MAX-ACCESS read-write
                    STATUS current
                    DESCRIPTION "Delivery Water Temp. Summer STD Set Point"
                    ::= { analogObjects 18 }

        -- 1.3.6.1.4.1.9839.2.1.2.19
        t-set-d OBJECT-TYPE
                    SYNTAX Integer32 (60..130)
                    UNITS "C x10"
                    MAX-ACCESS read-write
                    STATUS current
                    DESCRIPTION "Delivery Water Temp. Summer OPT Set Point"
                    ::= { analogObjects 19 }

        -- 1.3.6.1.4.1.9839.2.1.2.20
        t-set-sm OBJECT-TYPE
                    SYNTAX Integer32 (60..130)
                    UNITS "C x10"
                    MAX-ACCESS read-write
                    STATUS current
                    DESCRIPTION "Del.Water T. Summer SetBack mode SetP."
                    ::= { analogObjects 20 }

        -- 1.3.6.1.4.1.9839.2.1.2.21
        t-set-i OBJECT-TYPE
                    SYNTAX Integer32 (280..530)
                    UNITS "C x10"
                    MAX-ACCESS read-write
                    STATUS current
                    DESCRIPTION "Delivery Water Temp. Winter Set Point"
                    ::= { analogObjects 21 }

        -- 1.3.6.1.4.1.9839.2.1.2.22
        t-set-c-sm OBJECT-TYPE
                    SYNTAX Integer32 (280..530)
                    UNITS "C x10"
                    MAX-ACCESS read-write
                    STATUS current
                    DESCRIPTION "Del.Water T. Winter SetBack mode SetP"
                    ::= { analogObjects 22 }

        -- 1.3.6.1.4.1.9839.2.1.2.23
        set-ht-win-e OBJECT-TYPE
                    SYNTAX Integer32 (-150..250)
                    UNITS "C x10"
                    MAX-ACCESS read-write
                    STATUS current
                    DESCRIPTION "CW inlet High Temp.Summer Alarm Threshold"
                    DEFVAL { 0 }
                    ::= { analogObjects 23 }

        -- 1.3.6.1.4.1.9839.2.1.2.24
        set-lt-win-e OBJECT-TYPE
                    SYNTAX Integer32 (-150..250)
                    UNITS "C x10"
                    MAX-ACCESS read-write
                    STATUS current
                    DESCRIPTION "CW inlet Low Temp.Summer Alarm Threshold"
                    DEFVAL { 0 }
                    ::= { analogObjects 24 }

        -- 1.3.6.1.4.1.9839.2.1.2.25
        set-ht-win-i OBJECT-TYPE
                    SYNTAX Integer32 (300..580)
                    UNITS "C x10"
                    MAX-ACCESS read-write
                    STATUS current
                    DESCRIPTION "CW inlet High Temp. Alarm Winter Threshold"
                    ::= { analogObjects 25 }

        -- 1.3.6.1.4.1.9839.2.1.2.26
        set-lt-win-i OBJECT-TYPE
                    SYNTAX Integer32 (200..500)
                    UNITS "C x10"
                    MAX-ACCESS read-write
                    STATUS current
                    DESCRIPTION "CW inlet Low Temp. Alarm Winter Threshold"
                    ::= { analogObjects 26 }

        -- 1.3.6.1.4.1.9839.2.1.2.27
        te-set-e OBJECT-TYPE
                    SYNTAX Integer32 (-100..450)
                    UNITS "C x10"
                    MAX-ACCESS read-write
                    STATUS current
                    DESCRIPTION "Summer T.ext Compens.: P1 T.ext SetP."
                    DEFVAL { 0 }
                    ::= { analogObjects 27 }

        -- 1.3.6.1.4.1.9839.2.1.2.28
        t-set-e2 OBJECT-TYPE
                    SYNTAX Integer32 (60..130)
                    UNITS "C x10"
                    MAX-ACCESS read-write
                    STATUS current
                    DESCRIPTION "Summer T.ext Compens.: P2 T.wout SetP."
                    ::= { analogObjects 28 }

        -- 1.3.6.1.4.1.9839.2.1.2.29
        te-set-e2 OBJECT-TYPE
                    SYNTAX Integer32 (-100..450)
                    UNITS "C x10"
                    MAX-ACCESS read-write
                    STATUS current
                    DESCRIPTION "Summer T.ext Compens.: P2 T.ext SetP."
                    DEFVAL { 0 }
                    ::= { analogObjects 29 }

        -- 1.3.6.1.4.1.9839.2.1.2.30
        te-set-i OBJECT-TYPE
                    SYNTAX Integer32 (-100..150)
                    UNITS "C x10"
                    MAX-ACCESS read-write
                    STATUS current
                    DESCRIPTION "Winter T.ext Compens.: P1 T.ext SetP."
                    DEFVAL { 0 }
                    ::= { analogObjects 30 }

        -- 1.3.6.1.4.1.9839.2.1.2.31
        t-set-i2 OBJECT-TYPE
                    SYNTAX Integer32 (280..530)
                    UNITS "C x10"
                    MAX-ACCESS read-write
                    STATUS current
                    DESCRIPTION "Winter T.ext Compens.: P2 T.wout SetP."
                    ::= { analogObjects 31 }

        -- 1.3.6.1.4.1.9839.2.1.2.32
        te-set-i2 OBJECT-TYPE
                    SYNTAX Integer32 (-100..150)
                    UNITS "C x10"
                    MAX-ACCESS read-write
                    STATUS current
                    DESCRIPTION "Winter T.ext Compens.: P2 T.ext SetP."
                    DEFVAL { 0 }
                    ::= { analogObjects 32 }

        -- 1.3.6.1.4.1.9839.2.1.2.33
        set-delta-fc OBJECT-TYPE
                    SYNTAX Integer32 (30..100)
                    UNITS "C x10"
                    MAX-ACCESS read-write
                    STATUS current
                    DESCRIPTION "Free-Cooling Activation Set Point"
                    ::= { analogObjects 33 }

        -- 1.3.6.1.4.1.9839.2.1.2.34
        actual-sheat-c1 OBJECT-TYPE
                    SYNTAX Integer32 (12345..12345)
                    UNITS "C x10"
                    MAX-ACCESS read-only
                    STATUS current
                    DESCRIPTION "Circuit 1 superheating"
                    ::= { analogObjects 34 }

        -- 1.3.6.1.4.1.9839.2.1.2.35
        actual-sheat-c2 OBJECT-TYPE
                    SYNTAX Integer32 (12345..12345)
                    UNITS "C x10"
                    MAX-ACCESS read-only
                    STATUS current
                    DESCRIPTION "Circuit 2 superheating"
                    ::= { analogObjects 35 }

        -- 1.3.6.1.4.1.9839.2.1.2.36
        t-set-i-d OBJECT-TYPE
                    SYNTAX Integer32 (280..530)
                    UNITS "C x10"
                    MAX-ACCESS read-write
                    STATUS current
                    DESCRIPTION "Delivery Water Temp. Winter OPT Set Point"
                    ::= { analogObjects 36 }

        -- 1.3.6.1.4.1.9839.2.1.2.37
        sp-caldo-on OBJECT-TYPE
                    SYNTAX Integer32 (-150..180)
                    UNITS "C x10"
                    MAX-ACCESS read-write
                    STATUS current
                    DESCRIPTION "Summer/Winter Autom.Switch On Winter"
                    DEFVAL { 0 }
                    ::= { analogObjects 37 }

        -- 1.3.6.1.4.1.9839.2.1.2.38
        sp-freddo-on OBJECT-TYPE
                    SYNTAX Integer32 (80..180)
                    UNITS "C x10"
                    MAX-ACCESS read-write
                    STATUS current
                    DESCRIPTION "Summer/Winter Autom.Switch On Summer"
                    ::= { analogObjects 38 }

        -- 1.3.6.1.4.1.9839.2.1.2.39
        s4-probe-value-c1 OBJECT-TYPE
                    SYNTAX Integer32 (12345..12345)
                    UNITS "C x10"
                    MAX-ACCESS read-only
                    STATUS current
                    DESCRIPTION "Circuit 1 liquid refrigerant temperature"
                    ::= { analogObjects 39 }

        -- 1.3.6.1.4.1.9839.2.1.2.40
        s4-probe-value-c2 OBJECT-TYPE
                    SYNTAX Integer32 (12345..12345)
                    UNITS "C x10"
                    MAX-ACCESS read-only
                    STATUS current
                    DESCRIPTION "Circuit 2 liquid refrigerant temperature"
                    ::= { analogObjects 40 }

        -- 1.3.6.1.4.1.9839.2.1.2.41
        sbc-c1 OBJECT-TYPE
                    SYNTAX Integer32 (12345..12345)
                    UNITS "C x10"
                    MAX-ACCESS read-only
                    STATUS current
                    DESCRIPTION "Circuit 1 subcooling"
                    ::= { analogObjects 41 }

        -- 1.3.6.1.4.1.9839.2.1.2.42
        sbc-c2 OBJECT-TYPE
                    SYNTAX Integer32 (12345..12345)
                    UNITS "C x10"
                    MAX-ACCESS read-only
                    STATUS current
                    DESCRIPTION "Circuit 2 subcooling"
                    ::= { analogObjects 42 }

        -- 1.3.6.1.4.1.9839.2.1.2.43
        evd-c1-a17-eev-position-percent OBJECT-TYPE
                    SYNTAX Integer32 (12345..12345)
                    UNITS "% x10"
                    MAX-ACCESS read-only
                    STATUS current
                    DESCRIPTION "Expansion valve 1 position percentage"
                    ::= { analogObjects 43 }

        -- 1.3.6.1.4.1.9839.2.1.2.44
        evd-c2-a17-eev-position-percent OBJECT-TYPE
                    SYNTAX Integer32 (12345..12345)
                    UNITS "% x10"
                    MAX-ACCESS read-only
                    STATUS current
                    DESCRIPTION "Expansion valve 2 position percentage"
                    ::= { analogObjects 44 }

        -- 1.3.6.1.4.1.9839.2.1.2.45
        actual-superheat-set-c1 OBJECT-TYPE
                    SYNTAX Integer32 (12345..12345)
                    UNITS "C x10"
                    MAX-ACCESS read-only
                    STATUS current
                    DESCRIPTION "Circuit 1 superheating setpoint"
                    ::= { analogObjects 45 }

        -- 1.3.6.1.4.1.9839.2.1.2.46
        actual-superheat-set-c2 OBJECT-TYPE
                    SYNTAX Integer32 (12345..12345)
                    UNITS "C x10"
                    MAX-ACCESS read-only
                    STATUS current
                    DESCRIPTION "Circuit 2 superheating setpoint"
                    ::= { analogObjects 46 }

        -- 1.3.6.1.4.1.9839.2.1.2.47
        temp-hrin OBJECT-TYPE
                    SYNTAX Integer32 (12345..12345)
                    UNITS "C x10"
                    MAX-ACCESS read-only
                    STATUS current
                    DESCRIPTION "Heat recovery  water inlet temperature"
                    ::= { analogObjects 47 }

        -- 1.3.6.1.4.1.9839.2.1.2.48
        temp-hrout OBJECT-TYPE
                    SYNTAX Integer32 (12345..12345)
                    UNITS "C x10"
                    MAX-ACCESS read-only
                    STATUS current
                    DESCRIPTION "Heat recovery  water outlet temperature"
                    ::= { analogObjects 48 }

        -- 1.3.6.1.4.1.9839.2.1.2.49
        reg-ramp OBJECT-TYPE
                    SYNTAX Integer32 (12345..12345)
                    UNITS "% x10"
                    MAX-ACCESS read-only
                    STATUS current
                    DESCRIPTION "Regulation Ramp"
                    ::= { analogObjects 49 }

        -- 1.3.6.1.4.1.9839.2.1.2.50
        pump-inv-max OBJECT-TYPE
                    SYNTAX Integer32 (0..1000)
                    UNITS "N/A"
                    MAX-ACCESS read-write
                    STATUS current
                    DESCRIPTION "Inverter Pump speed max"
                    DEFVAL { 0 }
                    ::= { analogObjects 50 }

        -- 1.3.6.1.4.1.9839.2.1.2.51
        pump-inv-min OBJECT-TYPE
                    SYNTAX Integer32 (0..1000)
                    UNITS "N/A"
                    MAX-ACCESS read-write
                    STATUS current
                    DESCRIPTION "Inverter Pump speed min"
                    DEFVAL { 0 }
                    ::= { analogObjects 51 }

        -- 1.3.6.1.4.1.9839.2.1.2.61
        temp-wout-1 OBJECT-TYPE
                    SYNTAX Integer32 (12345..12345)
                    UNITS "C x10"
                    MAX-ACCESS read-only
                    STATUS current
                    DESCRIPTION "Water Circuit 1 Outlet Temperature"
                    ::= { analogObjects 61 }

        -- 1.3.6.1.4.1.9839.2.1.2.62
        temp-wout-2 OBJECT-TYPE
                    SYNTAX Integer32 (12345..12345)
                    UNITS "C x10"
                    MAX-ACCESS read-only
                    STATUS current
                    DESCRIPTION "Water Circuit 2 Outlet Temperature"
                    ::= { analogObjects 62 }

        -- 1.3.6.1.4.1.9839.2.1.2.63
        temp-mand OBJECT-TYPE
                    SYNTAX Integer32 (12345..12345)
                    UNITS "C x10"
                    MAX-ACCESS read-only
                    STATUS current
                    DESCRIPTION "Compressor 1 discharge temperature"
                    ::= { analogObjects 63 }

        -- 1.3.6.1.4.1.9839.2.1.2.64
        freq-c1 OBJECT-TYPE
                    SYNTAX Integer32 (12345..12345)
                    UNITS "N/A"
                    MAX-ACCESS read-only
                    STATUS current
                    DESCRIPTION "Compressor 1 Frequency"
                    ::= { analogObjects 64 }



        -- 1.3.6.1.4.1.9839.2.1.3
        integerObjects OBJECT IDENTIFIER ::= { aquascrollMIB 3 }

        -- 1.3.6.1.4.1.9839.2.1.3.1
        ore-compr1 OBJECT-TYPE
                    SYNTAX Integer32 (12345..12345)
                    UNITS "hour"
                    MAX-ACCESS read-only
                    STATUS current
                    DESCRIPTION "Compressor 1 hour counter"
                    ::= { integerObjects 1 }

        -- 1.3.6.1.4.1.9839.2.1.3.2
        ore-compr2 OBJECT-TYPE
                    SYNTAX Integer32 (12345..12345)
                    UNITS "hour"
                    MAX-ACCESS read-only
                    STATUS current
                    DESCRIPTION "Compressor 2 hour counter"
                    ::= { integerObjects 2 }

        -- 1.3.6.1.4.1.9839.2.1.3.3
        ore-compr3 OBJECT-TYPE
                    SYNTAX Integer32 (12345..12345)
                    UNITS "hour"
                    MAX-ACCESS read-only
                    STATUS current
                    DESCRIPTION "Compressor 3 hour counter"
                    ::= { integerObjects 3 }

        -- 1.3.6.1.4.1.9839.2.1.3.4
        ore-compr4 OBJECT-TYPE
                    SYNTAX Integer32 (12345..12345)
                    UNITS "hour"
                    MAX-ACCESS read-only
                    STATUS current
                    DESCRIPTION "Compressor 4 hour counter"
                    ::= { integerObjects 4 }

        -- 1.3.6.1.4.1.9839.2.1.3.5
        ore-pump1 OBJECT-TYPE
                    SYNTAX Integer32 (12345..12345)
                    UNITS "hour"
                    MAX-ACCESS read-only
                    STATUS current
                    DESCRIPTION "Circulating Pump 1 hour counter"
                    ::= { integerObjects 5 }

        -- 1.3.6.1.4.1.9839.2.1.3.6
        ore-pump2 OBJECT-TYPE
                    SYNTAX Integer32 (12345..12345)
                    UNITS "hour"
                    MAX-ACCESS read-only
                    STATUS current
                    DESCRIPTION "Circulating Pump 2 hour counter"
                    ::= { integerObjects 6 }

        -- 1.3.6.1.4.1.9839.2.1.3.7
        ore-pumpfc OBJECT-TYPE
                    SYNTAX Integer32 (12345..12345)
                    UNITS "hour"
                    MAX-ACCESS read-only
                    STATUS current
                    DESCRIPTION "Free-cooling Pump hour counter"
                    ::= { integerObjects 7 }

        -- 1.3.6.1.4.1.9839.2.1.3.8
        spunti-c1 OBJECT-TYPE
                    SYNTAX Integer32 (12345..12345)
                    UNITS "hour"
                    MAX-ACCESS read-only
                    STATUS current
                    DESCRIPTION "Compressor 1 Starting counter"
                    ::= { integerObjects 8 }

        -- 1.3.6.1.4.1.9839.2.1.3.9
        spunti10k-c1 OBJECT-TYPE
                    SYNTAX Integer32 (12345..12345)
                    UNITS "N/A"
                    MAX-ACCESS read-only
                    STATUS current
                    DESCRIPTION "Compressor 1 Starting counter x10.000"
                    ::= { integerObjects 9 }

        -- 1.3.6.1.4.1.9839.2.1.3.10
        spunti-c2 OBJECT-TYPE
                    SYNTAX Integer32 (12345..12345)
                    UNITS "N/A"
                    MAX-ACCESS read-only
                    STATUS current
                    DESCRIPTION "Compressor 2 Starting counter"
                    ::= { integerObjects 10 }

        -- 1.3.6.1.4.1.9839.2.1.3.11
        spunti10k-c2 OBJECT-TYPE
                    SYNTAX Integer32 (12345..12345)
                    UNITS "N/A"
                    MAX-ACCESS read-only
                    STATUS current
                    DESCRIPTION "Compressor 2 Starting counter x10.000"
                    ::= { integerObjects 11 }

        -- 1.3.6.1.4.1.9839.2.1.3.12
        spunti-c3 OBJECT-TYPE
                    SYNTAX Integer32 (12345..12345)
                    UNITS "N/A"
                    MAX-ACCESS read-only
                    STATUS current
                    DESCRIPTION "Compressor 3 Starting counter"
                    ::= { integerObjects 12 }

        -- 1.3.6.1.4.1.9839.2.1.3.13
        spunti10k-c3 OBJECT-TYPE
                    SYNTAX Integer32 (12345..12345)
                    UNITS "N/A"
                    MAX-ACCESS read-only
                    STATUS current
                    DESCRIPTION "Compressor 3 Starting counter x10.000"
                    ::= { integerObjects 13 }

        -- 1.3.6.1.4.1.9839.2.1.3.14
        spunti-c4 OBJECT-TYPE
                    SYNTAX Integer32 (12345..12345)
                    UNITS "N/A"
                    MAX-ACCESS read-only
                    STATUS current
                    DESCRIPTION "Compressor 4 Starting counter"
                    ::= { integerObjects 14 }

        -- 1.3.6.1.4.1.9839.2.1.3.15
        spunti10k-c4 OBJECT-TYPE
                    SYNTAX Integer32 (12345..12345)
                    UNITS "N/A"
                    MAX-ACCESS read-only
                    STATUS current
                    DESCRIPTION "Compressor 4 Starting counter x10.000"
                    ::= { integerObjects 15 }

        -- 1.3.6.1.4.1.9839.2.1.3.16
        num-def-c1 OBJECT-TYPE
                    SYNTAX Integer32 (12345..12345)
                    UNITS "N/A"
                    MAX-ACCESS read-only
                    STATUS current
                    DESCRIPTION "Circuit 1 Defrost counter"
                    ::= { integerObjects 16 }

        -- 1.3.6.1.4.1.9839.2.1.3.17
        n10k-def-c1 OBJECT-TYPE
                    SYNTAX Integer32 (12345..12345)
                    UNITS "N/A"
                    MAX-ACCESS read-only
                    STATUS current
                    DESCRIPTION "Circuit 1 Defrost counter x10.000"
                    ::= { integerObjects 17 }

        -- 1.3.6.1.4.1.9839.2.1.3.18
        num-def-c2 OBJECT-TYPE
                    SYNTAX Integer32 (12345..12345)
                    UNITS "N/A"
                    MAX-ACCESS read-only
                    STATUS current
                    DESCRIPTION "Circuit 2 Defrost counter"
                    ::= { integerObjects 18 }

        -- 1.3.6.1.4.1.9839.2.1.3.19
        n10k-def-c2 OBJECT-TYPE
                    SYNTAX Integer32 (12345..12345)
                    UNITS "N/A"
                    MAX-ACCESS read-only
                    STATUS current
                    DESCRIPTION "Circuit 2 Defrost counter x10.000"
                    ::= { integerObjects 19 }

        -- 1.3.6.1.4.1.9839.2.1.3.20
        num-def-both OBJECT-TYPE
                    SYNTAX Integer32 (12345..12345)
                    UNITS "N/A"
                    MAX-ACCESS read-only
                    STATUS current
                    DESCRIPTION "Both Circuit Defrost counter"
                    ::= { integerObjects 20 }

        -- 1.3.6.1.4.1.9839.2.1.3.21
        n10k-def-both OBJECT-TYPE
                    SYNTAX Integer32 (12345..12345)
                    UNITS "N/A"
                    MAX-ACCESS read-only
                    STATUS current
                    DESCRIPTION "Both Circuit Defrost counter x10.000"
                    ::= { integerObjects 21 }

        -- 1.3.6.1.4.1.9839.2.1.3.22
        num-def-np OBJECT-TYPE
                    SYNTAX Integer32 (12345..12345)
                    UNITS "N/A"
                    MAX-ACCESS read-only
                    STATUS current
                    DESCRIPTION "Non Performing Defrost counter"
                    ::= { integerObjects 22 }

        -- 1.3.6.1.4.1.9839.2.1.3.23
        n10k-def-np OBJECT-TYPE
                    SYNTAX Integer32 (12345..12345)
                    UNITS "N/A"
                    MAX-ACCESS read-only
                    STATUS current
                    DESCRIPTION "Non Performing Defrost counter x10.000"
                    ::= { integerObjects 23 }

        -- 1.3.6.1.4.1.9839.2.1.3.25
        pump-conf OBJECT-TYPE
                    SYNTAX Integer32 (12345..12345)
                    UNITS "N/A"
                    MAX-ACCESS read-only
                    STATUS current
                    DESCRIPTION "Circulating Pump Config."
                    ::= { integerObjects 25 }

        -- 1.3.6.1.4.1.9839.2.1.3.26
        lan-unit OBJECT-TYPE
                    SYNTAX Integer32 (12345..12345)
                    UNITS "N/A"
                    MAX-ACCESS read-only
                    STATUS current
                    DESCRIPTION "Total of units connected in LAN"
                    ::= { integerObjects 26 }

        -- 1.3.6.1.4.1.9839.2.1.3.27
        stato-comp1 OBJECT-TYPE
                    SYNTAX Integer32 (12345..12345)
                    UNITS "N/A"
                    MAX-ACCESS read-only
                    STATUS current
                    DESCRIPTION "Comp.1 Status"
                    ::= { integerObjects 27 }

        -- 1.3.6.1.4.1.9839.2.1.3.28
        stato-comp2 OBJECT-TYPE
                    SYNTAX Integer32 (12345..12345)
                    UNITS "N/A"
                    MAX-ACCESS read-only
                    STATUS current
                    DESCRIPTION "Comp.2 Status"
                    ::= { integerObjects 28 }

        -- 1.3.6.1.4.1.9839.2.1.3.29
        stato-comp3 OBJECT-TYPE
                    SYNTAX Integer32 (12345..12345)
                    UNITS "N/A"
                    MAX-ACCESS read-only
                    STATUS current
                    DESCRIPTION "Comp.3 Status"
                    ::= { integerObjects 29 }

        -- 1.3.6.1.4.1.9839.2.1.3.30
        stato-comp4 OBJECT-TYPE
                    SYNTAX Integer32 (12345..12345)
                    UNITS "N/A"
                    MAX-ACCESS read-only
                    STATUS current
                    DESCRIPTION "Comp.4 Status"
                    ::= { integerObjects 30 }

        -- 1.3.6.1.4.1.9839.2.1.3.31
        stato-pompa1 OBJECT-TYPE
                    SYNTAX Integer32 (12345..12345)
                    UNITS "N/A"
                    MAX-ACCESS read-only
                    STATUS current
                    DESCRIPTION "Pump 1 Status"
                    ::= { integerObjects 31 }

        -- 1.3.6.1.4.1.9839.2.1.3.32
        stato-pompa2 OBJECT-TYPE
                    SYNTAX Integer32 (12345..12345)
                    UNITS "N/A"
                    MAX-ACCESS read-only
                    STATUS current
                    DESCRIPTION "Pump 2 Status"
                    ::= { integerObjects 32 }

        -- 1.3.6.1.4.1.9839.2.1.3.33
        stato-pompafc OBJECT-TYPE
                    SYNTAX Integer32 (12345..12345)
                    UNITS "N/A"
                    MAX-ACCESS read-only
                    STATUS current
                    DESCRIPTION "FC Pump Status"
                    ::= { integerObjects 33 }

        -- 1.3.6.1.4.1.9839.2.1.3.34
        show-setmode OBJECT-TYPE
                    SYNTAX Integer32 (12345..12345)
                    UNITS "N/A"
                    MAX-ACCESS read-only
                    STATUS current
                    DESCRIPTION "Actual set Point mode"
                    ::= { integerObjects 34 }

        -- 1.3.6.1.4.1.9839.2.1.3.35
        xdsp-dresa1 OBJECT-TYPE
                    SYNTAX Integer32 (12345..12345)
                    UNITS "N/A"
                    MAX-ACCESS read-only
                    STATUS current
                    DESCRIPTION "Reserved"
                    ::= { integerObjects 35 }

        -- 1.3.6.1.4.1.9839.2.1.3.36
        xdsp-dresa2 OBJECT-TYPE
                    SYNTAX Integer32 (12345..12345)
                    UNITS "N/A"
                    MAX-ACCESS read-only
                    STATUS current
                    DESCRIPTION "Reserved"
                    ::= { integerObjects 36 }

        -- 1.3.6.1.4.1.9839.2.1.3.37
        durata-defrost OBJECT-TYPE
                    SYNTAX Integer32 (12345..12345)
                    UNITS "N/A"
                    MAX-ACCESS read-only
                    STATUS current
                    DESCRIPTION "Last Defrost Lenght"
                    ::= { integerObjects 37 }

        -- 1.3.6.1.4.1.9839.2.1.3.38
        restar-delay OBJECT-TYPE
                    SYNTAX Integer32 (12345..12345)
                    UNITS "N/A"
                    MAX-ACCESS read-write
                    STATUS current
                    DESCRIPTION "Restart Delay"
                    ::= { integerObjects 38 }

        -- 1.3.6.1.4.1.9839.2.1.3.39
        regul-delay OBJECT-TYPE
                    SYNTAX Integer32 (12345..12345)
                    UNITS "N/A"
                    MAX-ACCESS read-write
                    STATUS current
                    DESCRIPTION "Regulation Start Transitory"
                    ::= { integerObjects 39 }

        -- 1.3.6.1.4.1.9839.2.1.3.40
        time-lowp OBJECT-TYPE
                    SYNTAX Integer32 (0..180)
                    UNITS "N/A"
                    MAX-ACCESS read-write
                    STATUS current
                    DESCRIPTION "Low Pressure Delay"
                    DEFVAL { 0 }
                    ::= { integerObjects 40 }

        -- 1.3.6.1.4.1.9839.2.1.3.41
        alarm-delay OBJECT-TYPE
                    SYNTAX Integer32 (12345..12345)
                    UNITS "min"
                    MAX-ACCESS read-write
                    STATUS current
                    DESCRIPTION "Water High/Low Temp. Alarm Delay"
                    ::= { integerObjects 41 }

        -- 1.3.6.1.4.1.9839.2.1.3.43
        t-std-by OBJECT-TYPE
                    SYNTAX Integer32 (12345..12345)
                    UNITS "hour"
                    MAX-ACCESS read-write
                    STATUS current
                    DESCRIPTION "Stand-by Unit Switch-over time"
                    ::= { integerObjects 43 }

        -- 1.3.6.1.4.1.9839.2.1.3.44
        ore-rot-pompe OBJECT-TYPE
                    SYNTAX Integer32 (12345..12345)
                    UNITS "hour"
                    MAX-ACCESS read-only
                    STATUS current
                    DESCRIPTION "Run-Stand-by pump switch-over time"
                    ::= { integerObjects 44 }

        -- 1.3.6.1.4.1.9839.2.1.3.45
        ciclo-sm OBJECT-TYPE
                    SYNTAX Integer32 (12345..12345)
                    UNITS "min"
                    MAX-ACCESS read-only
                    STATUS current
                    DESCRIPTION "Setback Mode Cyclical start"
                    ::= { integerObjects 45 }

        -- 1.3.6.1.4.1.9839.2.1.3.46
        set-hm100-c1 OBJECT-TYPE
                    SYNTAX Integer32 (12345..12345)
                    UNITS "N/A"
                    MAX-ACCESS read-write
                    STATUS current
                    DESCRIPTION "Compr.1 working hours threshold"
                    ::= { integerObjects 46 }

        -- 1.3.6.1.4.1.9839.2.1.3.47
        set-hm100-c2 OBJECT-TYPE
                    SYNTAX Integer32 (12345..12345)
                    UNITS "N/A"
                    MAX-ACCESS read-write
                    STATUS current
                    DESCRIPTION "Compr.2 working hours threshold"
                    ::= { integerObjects 47 }

        -- 1.3.6.1.4.1.9839.2.1.3.48
        set-hm100-c3 OBJECT-TYPE
                    SYNTAX Integer32 (12345..12345)
                    UNITS "N/A"
                    MAX-ACCESS read-write
                    STATUS current
                    DESCRIPTION "Compr.3 working hours threshold"
                    ::= { integerObjects 48 }

        -- 1.3.6.1.4.1.9839.2.1.3.49
        set-hm100-c4 OBJECT-TYPE
                    SYNTAX Integer32 (12345..12345)
                    UNITS "N/A"
                    MAX-ACCESS read-write
                    STATUS current
                    DESCRIPTION "Compr.4 working hours threshold"
                    ::= { integerObjects 49 }

        -- 1.3.6.1.4.1.9839.2.1.3.50
        set-hm100-p1 OBJECT-TYPE
                    SYNTAX Integer32 (12345..12345)
                    UNITS "N/A"
                    MAX-ACCESS read-write
                    STATUS current
                    DESCRIPTION "Pump 1 working hours threshold"
                    ::= { integerObjects 50 }

        -- 1.3.6.1.4.1.9839.2.1.3.51
        set-hm100-p2 OBJECT-TYPE
                    SYNTAX Integer32 (12345..12345)
                    UNITS "N/A"
                    MAX-ACCESS read-write
                    STATUS current
                    DESCRIPTION "Pump 2 working hours threshold"
                    ::= { integerObjects 51 }

        -- 1.3.6.1.4.1.9839.2.1.3.52
        set-hm100-pfc OBJECT-TYPE
                    SYNTAX Integer32 (12345..12345)
                    UNITS "N/A"
                    MAX-ACCESS read-write
                    STATUS current
                    DESCRIPTION "FC Pump working hours threshold"
                    ::= { integerObjects 52 }

        -- 1.3.6.1.4.1.9839.2.1.3.55
        evd-c1-i4-eev-position-steps OBJECT-TYPE
                    SYNTAX Integer32 (12345..12345)
                    UNITS "steps"
                    MAX-ACCESS read-only
                    STATUS current
                    DESCRIPTION "Expansion valve 1 position steps"
                    ::= { integerObjects 55 }

        -- 1.3.6.1.4.1.9839.2.1.3.56
        evd-c2-i4-eev-position-steps OBJECT-TYPE
                    SYNTAX Integer32 (12345..12345)
                    UNITS "steps"
                    MAX-ACCESS read-only
                    STATUS current
                    DESCRIPTION "Expansion valve 2 position steps"
                    ::= { integerObjects 56 }

        -- 1.3.6.1.4.1.9839.2.1.3.57
        water-press-max-x OBJECT-TYPE
                    SYNTAX Integer32 (12345..12345)
                    UNITS "N/A"
                    MAX-ACCESS read-only
                    STATUS current
                    DESCRIPTION "Water pressure: max. pressure recorded"
                    ::= { integerObjects 57 }

        -- 1.3.6.1.4.1.9839.2.1.3.59
        current-hour OBJECT-TYPE
                    SYNTAX Integer32 (12345..12345)
                    UNITS "N/A"
                    MAX-ACCESS read-only
                    STATUS current
                    DESCRIPTION "Current hour"
                    ::= { integerObjects 59 }

        -- 1.3.6.1.4.1.9839.2.1.3.60
        current-minute OBJECT-TYPE
                    SYNTAX Integer32 (12345..12345)
                    UNITS "N/A"
                    MAX-ACCESS read-only
                    STATUS current
                    DESCRIPTION "current minute"
                    ::= { integerObjects 60 }

        -- 1.3.6.1.4.1.9839.2.1.3.61
        current-day OBJECT-TYPE
                    SYNTAX Integer32 (12345..12345)
                    UNITS "N/A"
                    MAX-ACCESS read-only
                    STATUS current
                    DESCRIPTION "current day"
                    ::= { integerObjects 61 }

        -- 1.3.6.1.4.1.9839.2.1.3.62
        current-month OBJECT-TYPE
                    SYNTAX Integer32 (12345..12345)
                    UNITS "N/A"
                    MAX-ACCESS read-only
                    STATUS current
                    DESCRIPTION "current month"
                    ::= { integerObjects 62 }

        -- 1.3.6.1.4.1.9839.2.1.3.63
        current-year OBJECT-TYPE
                    SYNTAX Integer32 (12345..12345)
                    UNITS "N/A"
                    MAX-ACCESS read-only
                    STATUS current
                    DESCRIPTION "current year"
                    ::= { integerObjects 63 }

        -- 1.3.6.1.4.1.9839.2.1.3.64
        unit-series OBJECT-TYPE
                    SYNTAX Integer32 (12345..12345)
                    UNITS "N/A"
                    MAX-ACCESS read-only
                    STATUS current
                    DESCRIPTION "Unit series"
                    ::= { integerObjects 64 }

        -- 1.3.6.1.4.1.9839.2.1.3.65
        unit-type OBJECT-TYPE
                    SYNTAX Integer32 (12345..12345)
                    UNITS "N/A"
                    MAX-ACCESS read-only
                    STATUS current
                    DESCRIPTION "Unit type"
                    ::= { integerObjects 65 }

        -- 1.3.6.1.4.1.9839.2.1.3.66
        unit-model OBJECT-TYPE
                    SYNTAX Integer32 (12345..12345)
                    UNITS "N/A"
                    MAX-ACCESS read-only
                    STATUS current
                    DESCRIPTION "Unit model"
                    ::= { integerObjects 66 }

        -- 1.3.6.1.4.1.9839.2.1.3.67
        gas-type OBJECT-TYPE
                    SYNTAX Integer32 (12345..12345)
                    UNITS "N/A"
                    MAX-ACCESS read-only
                    STATUS current
                    DESCRIPTION "Gas type"
                    ::= { integerObjects 67 }

        -- 1.3.6.1.4.1.9839.2.1.3.70
        matricola-i OBJECT-TYPE
                    SYNTAX Integer32 (12345..12345)
                    UNITS "N/A"
                    MAX-ACCESS read-only
                    STATUS current
                    DESCRIPTION "Unit serial number Part 1"
                    ::= { integerObjects 70 }

        -- 1.3.6.1.4.1.9839.2.1.3.71
        matricola-hn OBJECT-TYPE
                    SYNTAX Integer32 (12345..12345)
                    UNITS "N/A"
                    MAX-ACCESS read-only
                    STATUS current
                    DESCRIPTION "Unit serial number Part 2"
                    ::= { integerObjects 71 }

        -- 1.3.6.1.4.1.9839.2.1.3.72
        matricola-ln OBJECT-TYPE
                    SYNTAX Integer32 (12345..12345)
                    UNITS "N/A"
                    MAX-ACCESS read-only
                    STATUS current
                    DESCRIPTION "Unit serial number Part 3"
                    ::= { integerObjects 72 }

        -- 1.3.6.1.4.1.9839.2.1.3.75
        bms-sw-ver OBJECT-TYPE
                    SYNTAX Integer32 (12345..12345)
                    UNITS "N/A"
                    MAX-ACCESS read-only
                    STATUS current
                    DESCRIPTION "Software versione"
                    ::= { integerObjects 75 }

        -- 1.3.6.1.4.1.9839.2.1.3.76
        bms-sw-date OBJECT-TYPE
                    SYNTAX Integer32 (12345..12345)
                    UNITS "N/A"
                    MAX-ACCESS read-only
                    STATUS current
                    DESCRIPTION "Software date"
                    ::= { integerObjects 76 }

        -- 1.3.6.1.4.1.9839.2.1.3.77
        rit-caldo-on OBJECT-TYPE
                    SYNTAX Integer32 (12345..12345)
                    UNITS "N/A"
                    MAX-ACCESS read-write
                    STATUS current
                    DESCRIPTION "Summer/Winter Autom.Switch Delay on Winter"
                    ::= { integerObjects 77 }

        -- 1.3.6.1.4.1.9839.2.1.3.78
        rit-freddo-on OBJECT-TYPE
                    SYNTAX Integer32 (12345..12345)
                    UNITS "N/A"
                    MAX-ACCESS read-write
                    STATUS current
                    DESCRIPTION "Summer/Winter Autom.Switch Delay on Summer"
                    ::= { integerObjects 78 }

        -- 1.3.6.1.4.1.9839.2.1.3.79
        prev-set OBJECT-TYPE
                    SYNTAX Integer32 (5..400)
                    UNITS "N/A"
                    MAX-ACCESS read-write
                    STATUS current
                    DESCRIPTION "Inverter Pump Total head setpoint"
                    ::= { integerObjects 79 }


	
	END

--
-- CAREL-aquascroll.MIB
--
