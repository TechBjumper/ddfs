--------------------------------------------------------------------------------
--  Avocent PM TRAP MIB
--  Copyright 2009 Avocent Corporation
--  Revision: 2.0.0
--  Last Modified: Nov 30, 2009
--------------------------------------------------------------------------------

PM-TRAP-MIB DEFINITIONS ::= BEGIN

IMPORTS
  enterprises, MODULE-IDENTITY, OBJECT-TYPE
      FROM SNMPv2-SMI
  TRAP-TYPE
      FROM RFC-1215;


--------------------------------------------------------------------------------
-- Object Groupings
-- Familyoid 17
-- Productoid 1
-- Managementoid 2
-- TrapObjectoid 6
--------------------------------------------------------------------------------

-- avocent                 OBJECT IDENTIFIER ::= { enterprises 10418 }

pm    MODULE-IDENTITY
        LAST-UPDATED    "200911300000Z"
        ORGANIZATION    "Avocent Corporation"
        CONTACT-INFO    "postal : Avocent Corporation
                                  3541 Gateway Boulevard
                                  Fremont, CA 94538, USA
                         e-mail : Technical Support
                                  techsupport@avocent.com"
        DESCRIPTION      
        "This module defines the Avocent TRAP MIB extensions to
         pm products."
        REVISION        "200911300000Z"
		DESCRIPTION     "Updating traps"
::= { enterprises 10418 17 }

pmProducts             OBJECT IDENTIFIER ::= { pm 1 }
pmManagement           OBJECT IDENTIFIER ::= { pm 2 }
pmTrapObject           OBJECT IDENTIFIER ::= { pmManagement 6 }  -- 10418.16.2.6

-------------------------------------------------------------------------------
-- PM Trap Object
-------------------------------------------------------------------------------
pmTrapObjectUserName OBJECT-TYPE
    SYNTAX OCTET STRING
    MAX-ACCESS accessible-for-notify
    STATUS current
    --% AVAILABILITY public
    DESCRIPTION 
    "This object is sent in a trap to identify the name of the user
     for which the trap condition occurred."
::= { pmTrapObject 1 }

pmTrapObjectDaemonName OBJECT-TYPE
    SYNTAX OCTET STRING
    MAX-ACCESS accessible-for-notify
    STATUS current            
    DESCRIPTION     
    "This object is sent in a trap to indicate the Daemon name
     that has started/stopped."
    --% AVAILABILITY public          
::= { pmTrapObject 2 }

pmTrapObjectTargetUserName OBJECT-TYPE
    SYNTAX OCTET STRING
    MAX-ACCESS accessible-for-notify
    STATUS current
    --% AVAILABILITY public
    DESCRIPTION 
    "This object is sent in a trap to identify the name of the user
     for which the trap condition occurred."
::= { pmTrapObject 3 }

pmTrapObjectFileName OBJECT-TYPE
    SYNTAX OCTET STRING
    MAX-ACCESS accessible-for-notify
    STATUS current
    --% AVAILABILITY public
    DESCRIPTION 
    "This object is sent in a trap to identify the name of the file
     that was used."
::= { pmTrapObject 4 }

pmTrapFirmwareVersion OBJECT-TYPE
    SYNTAX OCTET STRING
    MAX-ACCESS accessible-for-notify
    STATUS current            
    DESCRIPTION
    "This object is sent in a trap to identify current Firmware version."
    --% AVAILABILITY public  
::= { pmTrapObject 5 }

pmTrapNewFirmwareVersion OBJECT-TYPE
    SYNTAX OCTET STRING
    MAX-ACCESS accessible-for-notify
    STATUS current            
    DESCRIPTION
    "This object is sent in a trap to identify new Firmware version."
    --% AVAILABILITY public  
::= { pmTrapObject 6 }
        
pmTrapFirmwareUpgradeResult OBJECT-TYPE
    SYNTAX INTEGER  {
               imageUpgradeSuccess(1),
               imageUpgradeInternalError(2)
           }
    MAX-ACCESS accessible-for-notify
    STATUS current            
    DESCRIPTION     
    "This object is sent in a trap to identify the firmware upgrade result."
    --% AVAILABILITY public  
::= { pmTrapObject 7 }        

pmTrapObjectAlertIndex OBJECT-TYPE
    SYNTAX INTEGER
    MAX-ACCESS accessible-for-notify
    STATUS current
    DESCRIPTION       
    "This object is sent in a trap to identify the alert string 
     that matched in the alert message."
    --% AVAILABILITY public                         
::= { pmTrapObject 8 }

pmTrapObjectAlertMessage OBJECT-TYPE
    SYNTAX OCTET STRING
    MAX-ACCESS accessible-for-notify
    STATUS current
    --% AVAILABILITY public
    DESCRIPTION
    "This object is sent in a trap to identify the line text where 
     the alert string was detected."
::= { pmTrapObject 9 }

pmTrapObjectAlertString OBJECT-TYPE
    SYNTAX OCTET STRING
    MAX-ACCESS accessible-for-notify
    STATUS current
    DESCRIPTION       
    "This object is sent in a trap to identify the alert string 
     that matched in the alert message."
    --% AVAILABILITY public                         
::= { pmTrapObject 10 }


pmTrapObjectSessionType OBJECT-TYPE
    SYNTAX INTEGER {
                    ssh(0),
                    telnet(1),
                    console(2),
                    http(4),
		    https(5)
                    }
    MAX-ACCESS accessible-for-notify
    STATUS current
    DESCRIPTION 
    "This object is sent in a trap to identify type of Session 
     for access to appliance."
     --% AVAILABILITY public                         
::= { pmTrapObject 11 }  

pmTrapObjectSerialPortNumber OBJECT-TYPE
    SYNTAX INTEGER
    MAX-ACCESS accessible-for-notify
    STATUS current
    DESCRIPTION       
    "This object is sent in a trap to identify which serial port number 
     the trap condition occurred."
     --% AVAILABILITY public                         
::= { pmTrapObject 13 }

pmTrapObjectDataBufferSize OBJECT-TYPE
    SYNTAX INTEGER
    MAX-ACCESS accessible-for-notify
    STATUS current
    DESCRIPTION       
    "This object is sent in a trap to identify current size of 
     global buffer."
    --% AVAILABILITY public                         
::= { pmTrapObject 15 }

pmTrapObjectPduId OBJECT-TYPE
    SYNTAX OCTET STRING
    MAX-ACCESS accessible-for-notify
    STATUS current            
    DESCRIPTION
    "This object is sent in a trap to identify the ID of the PDU
     where the trap occurred."
    --% AVAILABILITY public  
::= { pmTrapObject 16 }
               
pmTrapObjectPduNumber OBJECT-TYPE
    SYNTAX INTEGER
    MAX-ACCESS accessible-for-notify
    STATUS current
    --% AVAILABILITY public          
    DESCRIPTION       
    "This object is sent in a trap to identify the index of the PDU the trap 
     condition occurred on."         
::= { pmTrapObject 17 }

pmTrapObjectPduSocket OBJECT-TYPE
    SYNTAX INTEGER
    MAX-ACCESS accessible-for-notify
    STATUS current
  --% AVAILABILITY public      
    DESCRIPTION
    "This object is sent in a trap to identify number of outlets of the PDU."
::= { pmTrapObject 18 }
                       
pmTrapObjectPduVendor OBJECT-TYPE
    SYNTAX INTEGER {
                cyclades(1),
                spc(2),
                serverTech(3)
           }
    MAX-ACCESS accessible-for-notify
    STATUS current            
    DESCRIPTION
    "This object is sent in a trap to identify the vendor of the IPDU
     where the trap occurred."
  --% AVAILABILITY public  
::= { pmTrapObject 19 }

pmTrapObjectPduIdOld OBJECT-TYPE
    SYNTAX OCTET STRING
    MAX-ACCESS accessible-for-notify
    STATUS current            
    DESCRIPTION
    "This object is sent in a trap to identify the old ID of the PDU
     where the trap occurred."
    --% AVAILABILITY public  
::= { pmTrapObject 20 }

-- this may now be redundant - objects 40 and 41 replacing it.
pmTrapObjectPduCurrentValue OBJECT-TYPE
    SYNTAX OCTET STRING
    MAX-ACCESS accessible-for-notify
    STATUS current            
    DESCRIPTION     
    "This object is sent in a trap to detected current value of the PDU."
    --% AVAILABILITY public               
::= { pmTrapObject 22 }

pmTrapObjectSocketNumber OBJECT-TYPE
    SYNTAX INTEGER
    MAX-ACCESS accessible-for-notify
    STATUS current
    DESCRIPTION       
    "This object is sent in a trap to identify outlet number the trap
     condition occurred on."
  --% AVAILABILITY public   
::= { pmTrapObject 23 }

pmTrapObjectSocketName OBJECT-TYPE
    SYNTAX OCTET STRING
    MAX-ACCESS accessible-for-notify
    STATUS current
    DESCRIPTION       
    "This object is sent in a trap to identify outlet name stored in the PM."
  --% AVAILABILITY public   
::= { pmTrapObject 24 }

pmTrapObjectSocketOldName OBJECT-TYPE
    SYNTAX OCTET STRING
    MAX-ACCESS accessible-for-notify
    STATUS current
    DESCRIPTION       
    "This object is sent in a trap to identify the old outlet  
     name stored in the PM."
  --% AVAILABILITY public   
::= { pmTrapObject 25 }

pmTrapObjectPduElementName OBJECT-TYPE
    SYNTAX OCTET STRING
    MAX-ACCESS accessible-for-notify
    STATUS current            
    DESCRIPTION
    "This object is sent in a trap to identify the Element of the PDU
     where the trap occurred."
    --% AVAILABILITY public  
::= { pmTrapObject 40 }

pmTrapObjectPduElementType OBJECT-TYPE
    SYNTAX OCTET STRING
    MAX-ACCESS accessible-for-notify
    STATUS current            
    DESCRIPTION
    "This object is sent in a trap to identify the Element Type of the PDU
     where the trap occurred."
    --% AVAILABILITY public  
::= { pmTrapObject 41 }

-- PM Object Types
pmTrapObjectPduFuseStatus OBJECT-TYPE
    SYNTAX OCTET STRING
    MAX-ACCESS accessible-for-notify
    STATUS current 
    DESCRIPTION     
    "This object is sent in a trap for blown fuse detection in the PDU."
    --% AVAILABILITY public
::= { pmTrapObject 112 }

      
--
-- the PM Products is used as the Enterprise ID for the PM familiy.
-- This corresponds to the same OID as pmProducts in the PM-MIB.
--

--------------------------------------------------------------------------------
-- Enterprise Traps
--------------------------------------------------------------------------------

-- Appliance Management Traps
avctPmRebootStartedTrap TRAP-TYPE
    ENTERPRISE  pmProducts
    VARIABLES   { 
                  pmTrapObjectUserName 
                }
    DESCRIPTION
    "PM is in process of rebooting.
     The name of the user who issued the command is contained
     in pmTrapObjectUserName."
    --#SUMMARY     "The appliance is rebooting. Command issued by user: %s."
    --#ARGUMENTS   { 0 }
    --#SEVERITY    INFORMATIONAL
    --#CATEGORY    "Status Events"
    --NAME      "Appliance Rebooting"
    --SHORT     "appliance rebooting"
    --EVENT evt_reboot
    --% TrapTypeEnum=15 
::= 1

avctPmDaemonStarted TRAP-TYPE
    ENTERPRISE  pmProducts
    VARIABLES   { 
                  pmTrapObjectUserName, 
                  pmTrapObjectDaemonName 
                }
    DESCRIPTION
    "This trap is generated when daemon in the appliance started.
     The daemon name is contained in pmTrapObjectDaemonName.
     The name of the user who start the daemon is contained in pmTrapObjectUserName.
    "
    --#SUMMARY     "A daemon started. User: %s. Daemon name: %s."
    --#ARGUMENTS   { 0, 1 }
    --#SEVERITY    INFORMATIONAL
    --#CATEGORY    "Status Events"
    --NAME      "Appliance Daemon Started"
    --SHORT     "appliance daemon started"
    --EVENT evt_daemon_start
    --% TrapTypeEnum=9
::= 2

avctPmDaemonStoped TRAP-TYPE
    ENTERPRISE  pmProducts
    VARIABLES   { 
                  pmTrapObjectUserName, 
                  pmTrapObjectDaemonName 
                }
    DESCRIPTION
    "This trap is generated when daemon in the appliance stopped.
     The daemon name is contained in pmTrapObjectDaemonName.
     The name of the user who stop the daemon is contained in pmTrapObjectUserName.
    "
    --#SUMMARY     "A daemon stopped. User: %s. Daemon name: %s."
    --#ARGUMENTS   { 0, 1 }
    --#SEVERITY    INFORMATIONAL
    --#CATEGORY    "Status Events"
    --NAME      "Appliance Daemon Stopped"
    --SHORT     "appliance daemon stopped"
    --EVENT evt_daemon_stop
    --% TrapTypeEnum=9
::= 3     

avctPmSessionTerminatedTrap TRAP-TYPE
   ENTERPRISE  pmProducts
   VARIABLES   { 
                 pmTrapObjectUserName, 
                 pmTrapObjectTargetUserName
               }
   DESCRIPTION
   "This trap is generated when one previous session is 
    terminated by another user.
    The name of the user who terminated the session is contained in pmTrapObjectUserName.
    The name of the user who was terminated from the session is contained 
    in pmTrapObjectTargetUserName."
   --#SUMMARY     "Session terminated. Command issued by user: %s. Terminated user: %s."
   --#ARGUMENTS   { 0, 1 }
   --#SEVERITY    INFORMATIONAL
   --#CATEGORY    "Status Events"
   --NAME       "Appliance Session Terminated"
   --SHORT      "appliance session terminated"
   --EVENT evt_session_term
   --% TrapTypeEnum=9
::= 4
        
avctPmConfigurationStoredTrap TRAP-TYPE
   ENTERPRISE  pmProducts
   VARIABLES   {     
                 pmTrapObjectUserName,
                 pmTrapObjectFileName
               }
   DESCRIPTION            
   "This trap is generated when 'store backup configuration' command is successful.
    pmTrapObjectUserName is name of the user who executed the command.
    pmTrapObjectFileName is name of the file where the configuration was stored."         
   --#SUMMARY     "Backup configuration was stored. User: %s. Filename: %s."
   --#ARGUMENTS   {0, 1}
   --#SEVERITY    INFORMATIONAL
   --#CATEGORY    "Configuration Events"
   --NAME       "Appliance Backup Configuration Stored"
   --SHORT      "appliance backup configuration stored"
   --EVENT evt_config_store
   --% TrapTypeEnum=9
::= 5

avctPmConfigurationRestoredTrap TRAP-TYPE
   ENTERPRISE  pmProducts
   VARIABLES   {     
                 pmTrapObjectUserName,
                 pmTrapObjectFileName
               }
   DESCRIPTION            
   "This trap is generated when 'restore backup configuration' command is successful.
    pmTrapObjectUserName is name of the user who executed the command.
    pmTrapObjectFileName is name of the file used to restored the configuration."         
   --#SUMMARY     "Backup configuration was restored. User: %s. Filename: %s."
   --#ARGUMENTS   {0, 1}
   --#SEVERITY    INFORMATIONAL
   --#CATEGORY    "Configuration Events"
   --NAME       "Appliance Backup Configuration Restored"
   --SHORT      "appliance backup configuration restored"
   --EVENT evt_config_restore
   --% TrapTypeEnum=9
::= 6

avctPmLocalUserAddedTrap TRAP-TYPE
   ENTERPRISE  pmProducts
   VARIABLES   {     
                pmTrapObjectUserName,
                pmTrapObjectTargetUserName 
               }
   DESCRIPTION
   "A new user has been added to the local user database.
    The name of the user who added the new user is contained in pmTrapObjectUserName.
    The name of the new user is contained in pmTrapObjectTargetUserName."
   --#SUMMARY     "A user was added to the local user database. Command issued by user: %s. New user: %s."
   --#ARGUMENTS   { 0, 1}
   --#SEVERITY    INFORMATIONAL
   --#CATEGORY    "Configuration Events"
   --NAME       "Appliance User Added to Local User Database"
   --SHORT      "appliance user added to local user database"
   --EVENT evt_user_add
   --% TrapTypeEnum=9
::= 8   
      
avctPmLocalUserDeletedTrap TRAP-TYPE
   ENTERPRISE  pmProducts
   VARIABLES   {     
                pmTrapObjectUserName,
                pmTrapObjectTargetUserName 
               }
   DESCRIPTION
   "A user has been deleted from the local user database.
    The name of the user who deleted the user is contained in pmTrapObjectUserName.
    The name of the user who was deleted is contained in pmTrapObjectTargetUserName."
   --#SUMMARY     "A user was deleted from the local user database. Command issued by user: %s. Deleted user: %s."
   --#ARGUMENTS   {0,1}
   --#SEVERITY    INFORMATIONAL
   --#CATEGORY    "Configuration Events"
   --NAME       "Appliance User Deleted from Local User Database"
   --SHORT      "appliance user deleted from local user database"
   --EVENT evt_user_del
   --% TrapTypeEnum=9
::= 9

avctPmLocalUserModifiedTrap TRAP-TYPE
   ENTERPRISE  pmProducts
   VARIABLES   {     
                pmTrapObjectUserName,
                pmTrapObjectTargetUserName 
               }
   DESCRIPTION
   "A user has been modified in the local user database.
    The name of the user who modified the data is contained in pmTrapObjectUserName.
    The name of the user who was modified is contained in pmTrapObjectTargetUserName."
   --#SUMMARY     "A user was modified in the local user database. Command issued by user: %s. Modified user: %s."
   --#ARGUMENTS   {0,1}
   --#SEVERITY    INFORMATIONAL
   --#CATEGORY    "Configuration Events"
   --NAME       "Appliance User Modified in Local User Database"
   --SHORT      "appliance user modified in local user database"
   --EVENT evt_user_mod
   --% TrapTypeEnum=9
::= 10

avctPmFirmwareUpgradeStarted TRAP-TYPE
   ENTERPRISE  pmProducts
   VARIABLES   {     
                pmTrapObjectUserName,
                pmTrapFirmwareVersion,
                pmTrapNewFirmwareVersion
               }
   DESCRIPTION
   "The appliance has started an upgrade of a software image.
    The name of the user who initiate the process is contained 
    in pmTrapObjectUserName.
    The current firmware version is contained in pmTrapFirmwareVersion.
    The new firmware version is contained in pmTrapNewFirmwareVersion."
   --#SUMMARY     "Image upgrade started. User: %s. Current version: %s. New version: %s."
   --#ARGUMENTS   { 0, 1, 2}
   --#SEVERITY    INFORMATIONAL
   --#CATEGORY    "Status Events"
   --NAME       "Appliance Image Upgrade Started"
   --SHORT      "appliance image upgrade started"
   --EVENT evt_imgup_start
   --% TrapTypeEnum=9
::= 11

avctPmFirmwareUpgradeResultsTrap TRAP-TYPE
    ENTERPRISE  pmProducts
    VARIABLES   {     
                 pmTrapFirmwareUpgradeResult ,                        
                 pmTrapNewFirmwareVersion
                }
    DESCRIPTION
    "This trap is generated when Firmware upgraded is done to indicate the result.
     The new FW version is contained in pmTrapNewFirmwareVersion.
     The result of the process is contained in pmTrapFirmwareUpgradeResult."
    --#SUMMARY     "Image upgrade result. Result: %d. New firmware version: %s."
    --#ARGUMENTS   {0,1}
    --#SEVERITY    INFORMATIONAL
    --#CATEGORY    "Status Events"
    --NAME      "Appliance Image Upgrade Result"
    --SHORT     "appliance image upgrade result"
    --EVENT evt_imgup_result
    --% TrapTypeEnum=9
::= 12        

avctPmApplianceAlertTrap TRAP-TYPE
    ENTERPRISE  pmProducts
    VARIABLES   { 
                 pmTrapObjectUserName,
                 pmTrapObjectAlertIndex,
                 pmTrapObjectAlertString,
                 pmTrapObjectAlertMessage
                }
    DESCRIPTION
    "An appliance alert was detected on a ssh or telnet session.
     The name of user who was logged into the appliance when 
     trap occurred is contained in pmTrapObjectUserName.
     The index of the appliance alert that was detected in the message is 
     contained in pmTrapObjectAlertIndex.
     The appliance alert that was detected is contained in pmTrapObjectAlertString.
     The line text where the appliance alert was detected is contained 
     in pmTrapObjectAlertMessage."
    --#SUMMARY     "An appliance alert was detected. User: %s. Alert index: %d. Alert string: %s. Line text: %s." 
    --#ARGUMENTS   { 0, 1, 2, 3}
    --#SEVERITY    CRITICAL
    --#CATEGORY    "Error Events"           
    --NAME      "Appliance Alert Detected"
    --SHORT     "appliance alert detected"
    --EVENT evt_alert_detect
    --% TrapTypeEnum=9
::= 13      

avctAcsApplianceStartedTrap TRAP-TYPE
    ENTERPRISE  pmProducts
    DESCRIPTION
    "This trap is generated when the appliance is started."
    --#SUMMARY     "The appliance has started."
    --#SEVERITY    ALERT
    --#CATEGORY    "Error Events"
    --NAME      "Appliance Started"
    --SHORT     "appliance started"
    --EVENT evt_app_start
    --% TrapTypeEnum=9
::= 14      
      
avctPmUserLoginTrap TRAP-TYPE
    ENTERPRISE  pmProducts
    VARIABLES   { 
                  pmTrapObjectUserName, 
                  pmTrapObjectSessionType 
                }
    DESCRIPTION
    "This trap is sent when user logged into the appliance.
     The name of the user who logged in is contained in 
     pmTrapObjectUserName and the method used to log into appliance 
     is contained in pmTrapObjectSessionType."
    --#SUMMARY     "A user logged into the appliance. User: %s. Session type: %d."
    --#ARGUMENTS   { 0, 1 }
    --#SEVERITY    INFORMATIONAL
    --#CATEGORY    "Status Events"
    --NAME      "Appliance User Logged In"
    --SHORT     "appliance user logged in"
    --EVENT evt_usr_login
    --% TrapTypeEnum=15
::= 50

avctPmUserLogoutTrap TRAP-TYPE
    ENTERPRISE  pmProducts
    VARIABLES   { 
                  pmTrapObjectUserName, 
                  pmTrapObjectSessionType 
                }
    DESCRIPTION
    "A user logged out of the appliance.
     The name of the user who logged in is contained in 
     pmTrapObjectUserName and the method used to log into appliance 
     is contained in pmTrapObjectSessionType."
    --#SUMMARY     "A user logged out of the appliance. User: %s. Session type: %d."
    --#ARGUMENTS   { 0, 1}
    --#SEVERITY    INFORMATIONAL
    --#CATEGORY    "Status Events"
    --NAME      "Appliance User Logged Out"
    --SHORT     "appliance user logged out"
    --EVENT evt_usr_logout
    --% TrapTypeEnum=15
::= 51

avctPmAuthenticationFailureTrap TRAP-TYPE
    ENTERPRISE  pmProducts
    VARIABLES   {
                 pmTrapObjectUserName 
                }
    DESCRIPTION
    "A user failed to authenticate with the appliance.
     The name of the user who failed to authenticate is contained in pmTrapObjectUserName."
    --#SUMMARY     "User authentication failed. User: %s."
    --#ARGUMENTS   {0}
    --#SEVERITY    NON-CRITICAL
    --#CATEGORY    "Error Events"
    --NAME      "Appliance Authentication Failure"
    --SHORT     "appliance authentication failure"
    --EVENT evt_authe_fail
    --% TrapTypeEnum=15 
::= 52

avctPmDataBufferNFSFailure TRAP-TYPE
    ENTERPRISE  pmProducts
    DESCRIPTION
    "This trap is generated when the appliance is sending data buffering data to a NFS server 
     and the write operation fails."
    --#SUMMARY     "Data Buffering could not be written to NFS server."
    --#SEVERITY    ALERT
    --#CATEGORY    "Error Events"
    --NAME      "Appliance NFS Failure"
    --SHORT     "appliance NFS failure"
    --EVENT evt_nfs_failure
    --% TrapTypeEnum=9
::= 153      
 
avctPmDataBufferNFSRecovery TRAP-TYPE
    ENTERPRISE  pmProducts
    DESCRIPTION
    "This trap is generated when the NFS server is back online after a failure in a 
     Data Buffering write operation."
    --#SUMMARY     "NFS Server is back online after a failure."
    --#SEVERITY    ALERT
    --#CATEGORY    "Error Events"
    --NAME      "Appliance NFS Recovery"
    --SHORT     "appliance NFS recovery"
    --EVENT evt_nfs_recovery
    --% TrapTypeEnum=9
::= 154      

--
-- DSView Integration traps                                  
-- start # 200
avctPmDataBufferFullThresholdLowTrap TRAP-TYPE
    ENTERPRISE  pmProducts
    VARIABLES   { 
                 pmTrapObjectDataBufferSize 
                }
    DESCRIPTION
    "This trap is generated when the appliance is managed by DSView and 
     global data buffer has reached configured Low level Threshold.
     pmTrapObjectDataBufferSize is current size of the buffer."
    --#SUMMARY     "Data Buffering for DSView data log is getting full (low threshold). Buffer size: %d."
    --#ARGUMENTS   {0}
    --#SEVERITY    NON-CRITICAL
    --#CATEGORY    "Error Events"
    --NAME      "Appliance DSView Data Log Buffer Full First Warning"
    --SHORT     "appliance DSView data log buffer full first warning"
    --EVENT evt_dsview_loglow
    --% TrapTypeEnum=9
::= 200      
      
avctPmDataBufferFullThresholdMedTrap TRAP-TYPE
    ENTERPRISE  pmProducts
    VARIABLES   { 
                 pmTrapObjectDataBufferSize 
                }
    DESCRIPTION
    "This trap is generated when the appliance is managed by DSView and 
     global data buffer has reached configured Med level Threshold.
     pmTrapObjectDataBufferSize is current size of the buffer."
    --#SUMMARY     "Data Buffering for DSView data log is almost full (medium threshold). Buffer size: %d."
    --#ARGUMENTS   {0}
    --#SEVERITY    NON-CRITICAL
    --#CATEGORY    "Error Events"
    --NAME      "Appliance DSView Data Log Buffer Full Second Warning"
    --SHORT     "appliance DSView data log buffer full second warning"
    --EVENT evt_dsview_logmed
    --% TrapTypeEnum=9
::= 201      

avctPmDataBufferFullLostDataTrap TRAP-TYPE
    ENTERPRISE  pmProducts
    DESCRIPTION
    "This trap is generated when the appliance is managed by DSView and 
     global data buffer has exceeded beyond the size of buffer and data lost has occurred."
    --#SUMMARY     "Data Buffering for DSView data log had data loss because buffer full."
    --#SEVERITY    NON-CRITICAL
    --#CATEGORY    "Error Events"
    --NAME      "Appliance DSView Log Data loss"
    --SHORT     "appliance DSView log data loss"
    --EVENT evt_dsview_loss
    --% TrapTypeEnum=9
::= 202      
      
--------------------------------------------------------------------------------
-- Power Management Enterprise Traps
--------------------------------------------------------------------------------
--
-- PDU Traps
-- start # 300
avctPmPduOnlineTrap TRAP-TYPE
    ENTERPRISE  pmProducts
    VARIABLES   { 
                  pmTrapObjectSerialPortNumber,
                  pmTrapObjectPduNumber,
                  pmTrapObjectPduId,
                  pmTrapObjectPduSocket,                        
                  pmTrapObjectPduVendor
                }
    DESCRIPTION
    "A power device unit(PDU) attached to the appliance is online. 
     The port number on the appliance that the power device is attached to is contained in pmTrapObjectSerialPortNumber.
     The power device number in the chain is contained in pmTrapObjectPduNumber.
     The power device ID is contained in pmTrapObjectPduId.
     The number of outlets of the power device is contained in pmTrapObjectPduSocket.
     The vendor of the power device is contained in pmTrapObjectPduVendor"      
    --#SUMMARY     "A power device is online. Serial port number: %d. PDU number: %d. PDU ID: %s. Number of sockets: %d. Vendor: %d."
    --#ARGUMENTS   { 0, 1, 2, 3, 4}
    --#SEVERITY    INFORMATIONAL
    --#CATEGORY    "Status Events"
    --NAME      "Appliance Power Device Online"
    --SHORT     "appliance power device online"
    --EVENT evt_powdev_on
    --% TrapTypeEnum=9
::= 300

avctPmPduOfflineTrap TRAP-TYPE
    ENTERPRISE  pmProducts
    VARIABLES   {     
                  pmTrapObjectSerialPortNumber,
                  pmTrapObjectPduNumber,
                  pmTrapObjectPduId,
                  pmTrapObjectPduSocket,                        
                  pmTrapObjectPduVendor
                }
    DESCRIPTION
    "A power device attached to the appliance is offline.
     The port number on the appliance that the power device is attached to is contained in pmTrapObjectSerialPortNumber.
     The power device number in the chain is contained in pmTrapObjectPduNumber.
     The power device ID is contained in pmTrapObjectPduId.
     The number of outlets of the power device is contained in pmTrapObjectPduSocket.
     The vendor of the power device is contained in pmTrapObjectPduVendor."      
    --#SUMMARY     "A power device is offline. Serial port number: %d. PDU number: %d. PDU ID: %s. Number of sockets: %d. Vendor: %d."
    --#ARGUMENTS   { 0, 1, 2, 3, 4}
    --#SEVERITY    CRITICAL
    --#CATEGORY    "Error Events"
    --NAME      "Appliance Power Device Offline"
    --SHORT     "appliance power device offline"
    --EVENT evt_powdev_off
    --% TrapTypeEnum=9
::= 301

avctPmPduIdChangedTrap TRAP-TYPE
    ENTERPRISE  pmProducts
    VARIABLES   {     
                  pmTrapObjectSerialPortNumber,
                  pmTrapObjectPduNumber,
                  pmTrapObjectPduIdOld,
                  pmTrapObjectPduId,                    
                  pmTrapObjectPduVendor
                }
    DESCRIPTION
    "The ID of the PDU was changed.
     The port number on the appliance that the power device is attached to is contained in pmTrapObjectSerialPortNumber.
     The power device number in the chain is contained in pmTrapObjectPduNumber.
     The old power device ID is contained in pmTrapObjectPduIdOld.
     The new power device ID is contained in pmTrapObjectPduId.
     The vendor of the power device is contained in pmTrapObjectPduVendor."    
    --#SUMMARY  "Power device ID was changed. Serial port number: %d. PDU number: %d. PDU old ID: %s. PDU new ID: %s. Vendor: %d."
    --#ARGUMENTS   { 0, 1, 2, 3, 4}
    --#SEVERITY    MINOR
    --#CATEGORY    "Status Events"
    --NAME      "Appliance Power Device ID Changed"
    --SHORT     "appliance power device id changed"
    --EVENT evt_powid_chng
    --% TrapTypeEnum=9
::= 302

avctPmPduMaxLoadHighTrap TRAP-TYPE
    ENTERPRISE  pmProducts
    VARIABLES   { 
                  pmTrapObjectSerialPortNumber,
                  pmTrapObjectPduNumber,
                  pmTrapObjectPduId,
                  pmTrapObjectPduElementType,
                  pmTrapObjectPduElementName,
                  pmTrapObjectPduCurrentValue  
                 }
    DESCRIPTION
    "The current on a power device attached to the appliance is above its high critical threshold.
     The port number on the appliance that the power device is attached to is contained in the pmTrapObjectSerialPortNumber.
     The PDU# that detected the problem is contained in the pmTrapObjectPduNumber.
     The ID of the PDU that detected the problem is contained in the pmTrapObjectPduId.
     The Type of the PDU Element that detected the problem is contained in the pmTrapObjectPduElementType.
     The Name of the Pdu Element that detected the problem is contained in the pmTrapObjectPduElementName.
     The current value detected when this trap was originated is contained in pmTrapObjectPduCurrentValue."
    --#SUMMARY     "Appliance power device current is above its high critical threshold. Serial port number: %d. PDU number: %d. PDU ID: %s. Elem Type: %s. Elem Name: %s. Current detected: %s amps."
    --#ARGUMENTS   { 0, 1, 2, 3, 4, 5}
    --#SEVERITY    NON-CRITICAL
    --#CATEGORY    "Status Events"
    --NAME      "Appliance Power Device Current Above High Critical Threshold"
    --SHORT     "appliance power device current above high critical threshold"
    --EVENT evt_pow_maxload
    --% TrapTypeEnum=9
::= 303
      
avctPmPduMinLoadLowTrap TRAP-TYPE
    ENTERPRISE  pmProducts
    VARIABLES   { 
                  pmTrapObjectSerialPortNumber,
                  pmTrapObjectPduNumber,
                  pmTrapObjectPduId,
                  pmTrapObjectPduElementType,
                  pmTrapObjectPduElementName,
                  pmTrapObjectPduCurrentValue  
                }
    DESCRIPTION
    "The current on a power device attached to the appliance is below its low critical threshold.
     The port number on the appliance that the power device is attached to is contained in the pmTrapObjectSerialPortNumber.
     The PDU# that detected the problem is contained in the pmTrapObjectPduNumber.
     The ID of the PDU that detected the problem is contained in the pmTrapObjectPduId.
     The Type of the PDU Element that detected the problem is contained in the pmTrapObjectPduElementType.
     The Name of the Pdu Element that detected the problem is contained in the pmTrapObjectPduElementName.
     The current value detected when this trap was originated is contained in pmTrapObjectPduCurrentValue."
    --#SUMMARY     "Appliance power device current is below its low critical threshold. Serial port number: %d. PDU number: %d. PDU ID: %s. Elem Type: %s. Elem Name: %s. Current detected: %s amps."
    --#ARGUMENTS   { 0, 1, 2, 3, 4, 5}
    --#SEVERITY    NON-CRITICAL
    --#CATEGORY    "Status Events"
    --NAME      "Appliance Power Device Current Below Low Critical Threshold"
    --SHORT     "appliance power device current below low critical threshold"
    --EVENT evt_pow_minload
    --% TrapTypeEnum=9
::= 304

avctPmPduFirmwareUpgradeStarted TRAP-TYPE
    ENTERPRISE  pmProducts
    VARIABLES   {     
                  pmTrapObjectUserName,
                  pmTrapObjectSerialPortNumber,
                  pmTrapObjectPduNumber,
                  pmTrapFirmwareVersion,
                  pmTrapNewFirmwareVersion              
                }
    DESCRIPTION
    "The appliance has started an upgrade of the PM software.
     The name of the user who initiate the process is contained in pmTrapObjectUserName.
     The port number on the appliance that the power device is attached to is contained in the pmTrapObjectSerialPortNumber.
     The PDU# that detected the problem is contained in the pmTrapObjectPduNumber.
     The current firmware version is contained in pmTrapFirmwareVersion.
     The new firmware version is contained in pmTrapNewFirmwareVersion."
    --#SUMMARY     "PDU image upgrade started. User: %s. Serial port number: %d. PDU number: %d. Current version: %s. New version: %s."
    --#ARGUMENTS   { 0, 1, 2, 3, 4}
    --#SEVERITY    INFORMATIONAL
    --#CATEGORY    "Status Events"
    --NAME      "Appliance PDU Image Upgrade Started"
    --SHORT     "appliance pdu image upgrade started"
    --EVENT evt_pdup_start
    --% TrapTypeEnum=9
::= 307

avctPmPduFirmwareUpgradeResultsTrap TRAP-TYPE
    ENTERPRISE  pmProducts
    VARIABLES   {     
                  pmTrapObjectSerialPortNumber,
                  pmTrapObjectPduNumber,
                  pmTrapFirmwareUpgradeResult,                        
                  pmTrapNewFirmwareVersion
                }
    DESCRIPTION
    "This trap is generated when Firmware upgraded is done to indicate the result.
     The port number on the appliance that the power device is attached to is contained in the pmTrapObjectSerialPortNumber.
     The PDU# that gone beneath the minimum threshold is contained in the pmTrapObjectPduNumber.
     The new FW version is contained in pmTrapNewFirmwareVersion.
     The result of the process is contained in pmTrapFirmwareUpgradeResult."
    --#SUMMARY     "PDU image upgrade result. Serial port number:%d. PDU number: %d. Result: %d. New firmware version: %s."
    --#ARGUMENTS   {0, 1, 2, 3}
    --#SEVERITY    INFORMATIONAL
    --#CATEGORY    "Status Events"
    --NAME      "Appliance PDU Image Upgrade Result"
    --SHORT     "appliance pdu image upgrade result"
    --EVENT evt_pdup_rslt
    --% TrapTypeEnum=9
::= 308            

avctPmPduHwOcpTripped TRAP-TYPE
    ENTERPRISE  pmProducts
    VARIABLES   {     
                  pmTrapObjectSerialPortNumber,
                  pmTrapObjectPduNumber,
                  pmTrapObjectPduId,
                  pmTrapObjectPduElementType,
                  pmTrapObjectPduElementName
                }
    DESCRIPTION
    "This trap is generated when the HW overcurrent protection mechanism is tripped.
     The port number on the appliance that the power device is attached to is contained in the pmTrapObjectSerialPortNumber.
     The number of the PDU that was tripped is contained in the pmTrapObjectPduNumber.
     The ID of the PDU that was tripped is contained in the pmTrapObjectPduId. 
     The Type of the PDU Element that detected the event is contained in the pmTrapObjectPduElementType.
     The Name of the Pdu Element that detected the event is contained in the pmTrapObjectPduElementName."
    --#SUMMARY     "HW overcurrent protection was tripped. Serial port number:%d. PDU number: %d. PDU ID: %s. Elem Type: %s. Elem Name: %s."
    --#ARGUMENTS   {0, 1, 2, 3, 4}
    --#SEVERITY    INFORMATIONAL
    --#CATEGORY    "Status Events"
    --NAME      "Appliance PDU HW Overcurrent Protection tripped"
    --SHORT     "appliance pdu hwocp tripped"
    --EVENT evt_hwocp_tripped
    --% TrapTypeEnum=9
::= 309

avctPmPduHwOcpReset TRAP-TYPE
    ENTERPRISE  pmProducts
    VARIABLES   {     
                  pmTrapObjectSerialPortNumber,
                  pmTrapObjectPduNumber,
                  pmTrapObjectPduId,
                  pmTrapObjectPduElementType,
                  pmTrapObjectPduElementName
                }
    DESCRIPTION
    "This trap is generated when the HW overcurrent protection mechanism is reset.
     The port number on the appliance that the power device is attached to is contained in the pmTrapObjectSerialPortNumber.
     The number of the PDU whose HW OCP was reset is contained in the pmTrapObjectPduNumber.
     The ID of the PDU ID whose HW OCP was reset is contained in the pmTrapObjectPduId. 
     The Type of the PDU Element that detected the event is contained in the pmTrapObjectPduElementType.
     The Name of the Pdu Element that detected the event is contained in the pmTrapObjectPduElementName."
    --#SUMMARY     "HW overcurrent protection was reset. Serial port number:%d. PDU number: %d. PDU ID: %s. Elem Type: %s. Elem Name: %s."
    --#ARGUMENTS   {0, 1, 2, 3, 4}
    --#SEVERITY    INFORMATIONAL
    --#CATEGORY    "Status Events"
    --NAME      "Appliance PDU HW Overcurrent Protection reset"
    --SHORT     "appliance pdu hwocp reset"
    --EVENT evt_hwocp_reset
    --% TrapTypeEnum=9
::= 310

avctPmPduMaxLoadBackTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "The current on a power device attached to the appliance is back to normal.
     The port number on the appliance that the power device is attached to is contained in the pmTrapObjectSerialPortNumber.
     The PDU# that detected the event is contained in the pmTrapObjectPduNumber.
     The ID of the PDU that detected the event is contained in the pmTrapObjectPduId.
     The Type of the PDU Element that detected the event is contained in the pmTrapObjectPduElementType.
     The Name of the Pdu Element that detected the event is contained in the pmTrapObjectPduElementName.
     The current value detected when this trap was originated is contained in pmTrapObjectPduCurrentValue."
    --#SUMMARY     "Appliance power device normal current restored. Serial port number: %d. PDU number: %d. PDU ID: %s. Elem Type: %s. Elem Name: %s. Current detected: %s amps."
    --#ARGUMENTS   { 0, 1, 2, 3, 4, 5}
    --#SEVERITY    NON-CRITICAL
    --#CATEGORY    "Status Events"
    --NAME      "Appliance Power Device Normal Current Restored"
    --SHORT     "appliance power device normal current restored"
    --EVENT evt_pow_normload
    --% TrapTypeEnum=9
::= 311

avctPmPduWarnLoadTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "The current on a power device attached to the appliance is above its high warning threshold.
     The port number on the appliance that the power device is attached to is contained in the pmTrapObjectSerialPortNumber.
     The PDU# that detected the problem is contained in the pmTrapObjectPduNumber.
     The ID of the PDU that detected the problem is contained in the pmTrapObjectPduId.
     The Type of the PDU Element that detected the problem is contained in the pmTrapObjectPduElementType.
     The Name of the Pdu Element that detected the problem is contained in the pmTrapObjectPduElementName.
     The current value detected when this trap was originated is contained in pmTrapObjectPduCurrentValue."
    --#SUMMARY     "Appliance power device current is above its high warning threshold. Serial port number: %d. PDU number: %d. PDU ID: %s. Elem Type: %s. Elem Name: %s. Current detected: %s amps."
    --#ARGUMENTS   { 0, 1, 2, 3, 4, 5}
    --#SEVERITY    NON-CRITICAL
    --#CATEGORY    "Status Events"
    --NAME      "Appliance Power Device Current Above High Warning Threshold"
    --SHORT     "appliance power device current above high warning threshold"
    --EVENT evt_pow_warnload
    --% TrapTypeEnum=9
::= 312

avctPmPduLowLoadLowTrap TRAP-TYPE
    ENTERPRISE  pmProducts
    VARIABLES   { 
                  pmTrapObjectSerialPortNumber,
                  pmTrapObjectPduNumber,
                  pmTrapObjectPduId,
                  pmTrapObjectPduElementType,
                  pmTrapObjectPduElementName,
                  pmTrapObjectPduCurrentValue  
                }
    DESCRIPTION
    "The current on a power device attached to the appliance is below its low warning threshold.
     The port number on the appliance that the power device is attached to is contained in the pmTrapObjectSerialPortNumber.
     The PDU# that detected the problem is contained in the pmTrapObjectPduNumber.
     The ID of the PDU that detected the problem is contained in the pmTrapObjectPduId.
     The Type of the PDU Element that detected the problem is contained in the pmTrapObjectPduElementType.
     The Name of the Pdu Element that detected the problem is contained in the pmTrapObjectPduElementName.
     The current value detected when this trap was originated is contained in pmTrapObjectPduCurrentValue."
    --#SUMMARY     "Appliance power device current is below its low warning threshold. Serial port number: %d. PDU number: %d. PDU ID: %s. Elem Type: %s. Elem Name: %s. Current detected: %s amps."
    --#ARGUMENTS   { 0, 1, 2, 3, 4, 5}
    --#SEVERITY    NON-CRITICAL
    --#CATEGORY    "Status Events"
    --NAME      "Appliance Power Device Current Below Low Warning Threshold"
    --SHORT     "appliance power device current below low warning threshold"
    --EVENT evt_pow_lowload
    --% TrapTypeEnum=9
::= 313

avctPmPduBlownFuseTrap TRAP-TYPE
    ENTERPRISE  pmProducts
    VARIABLES   { 
                  pmTrapObjectSerialPortNumber,
                  pmTrapObjectPduNumber,
                  pmTrapObjectPduId,
                  pmTrapObjectPduElementType,
                  pmTrapObjectPduElementName,
                  pmTrapObjectPduFuseStatus  
                }
    DESCRIPTION
    "Blown fuse detection in one circuit of the PDU.
     The port number on the appliance that the power device is attached to is contained in the pmTrapObjectSerialPortNumber.
     The PDU# that detected the problem is contained in the pmTrapObjectPduNumber.
     The ID of the PDU that detected the problem is contained in the pmTrapObjectPduId.
     The Type of the PDU Element that detected the problem is contained in the pmTrapObjectPduElementType.
     The Name of the Pdu Element that detected the problem is contained in the pmTrapObjectPduElementName.
     The status detected when this trap was originated is contained in pmTrapObjectPduFuseStatus."
    --#SUMMARY     "Fuse status change. Serial port number: %d. PDU number: %d. PDU ID: %s. Elem Type: %s. Elem Name: %s. Fuse status: %s."
    --#ARGUMENTS   { 0, 1, 2, 3, 4, 5}
    --#SEVERITY    INFORMATIONAL
    --#CATEGORY    "Status Events"
    --NAME      "Appliance Power Device Blown Fuse Detection"
    --SHORT     "appliance power device blown fuse detection"
    --EVENT evt_blown_fuse
    --% TrapTypeEnum=9
::= 314

--
--
-- Outlet traps
-- start # 350
avctPmOutletNameChangedTrap TRAP-TYPE
    ENTERPRISE  pmProducts
    VARIABLES   { 
                  pmTrapObjectSerialPortNumber,
                  pmTrapObjectPduNumber,
                  pmTrapObjectPduId,
                  pmTrapObjectSocketNumber,
                  pmTrapObjectSocketOldName,
                  pmTrapObjectSocketName
                }
    DESCRIPTION
    "The name of socket was changed.
     The port number on the appliance that the chain of power device is attached to is contained in pmTrapObjectSerialPortNumber.
     The number of the power device is contained in the pmTrapObjectPduNumber.
     The ID of the power device is contained in pmTrapObjectPduId.
     The socket number that has changed the name is contained in pmTrapObjectSocketNumber.
     The old socket name is contained in pmTrapObjectSocketOldName.
     The socket name that has changed to the on state is contained in pmTrapObjectSocketName."      
    --#SUMMARY  "Power device socket name was changed. Serial port number: %d. PDU number: %d. PDU ID: %s. Socket number: %d. Old socket name: %s. New socket name: %s."
    --#ARGUMENTS   { 0, 1, 2, 3, 4, 5}
    --#SEVERITY    MINOR
    --#CATEGORY    "Status Events"
    --NAME      "Appliance Power Device Socket Name Changed"
    --SHORT     "appliance power device socket name changed"
    --EVENT evt_pdsock_chng
    --% TrapTypeEnum=9
::= 350

avctPmOutletCmdOnTrap TRAP-TYPE
    ENTERPRISE  pmProducts
    VARIABLES   { 
                  pmTrapObjectUserName, 
                  pmTrapObjectSerialPortNumber,
                  pmTrapObjectPduNumber,
                  pmTrapObjectPduId,
                  pmTrapObjectSocketNumber,
                  pmTrapObjectSocketName
                }
    DESCRIPTION
    "An outlet on a chain of power device has been issued the on command.
     The name of the user who issued the on command is contained in pmTrapObjectUserName.      
     The port number on the appliance that the chain of power device is attached to is contained in pmTrapObjectSerialPortNumber.
     The power device number in the chain is contained in pmTrapObjectPduNumber.
     The ID of the power device is contained in pmTrapObjectPduId.
     The socket number that was issued the on command is contained in pmTrapObjectSocketNumber.
     The socket name that was issued the on command is contained in pmTrapObjectSocketName."      
    --#SUMMARY  "The on command was issued to a power device socket. Command issued by user: %s. Serial port number: %d. PDU number: %d. PDU ID: %s. Socket number: %d. Socket name: %s."
    --#ARGUMENTS   { 0, 1, 2, 3, 4, 5}
    --#SEVERITY    MINOR
    --#CATEGORY    "Status Events"
    --NAME      "Appliance Power Device Socket On Command"
    --SHORT     "appliance power device socket on command"
    --EVENT evt_pdsock_oncmd
    --% TrapTypeEnum=9
::= 351

avctPmOutletStatusOnTrap TRAP-TYPE
    ENTERPRISE  pmProducts
    VARIABLES   { 
                  pmTrapObjectSerialPortNumber,
                  pmTrapObjectPduNumber,
                  pmTrapObjectPduId,
                  pmTrapObjectSocketNumber,
                  pmTrapObjectSocketName
                }
    DESCRIPTION
    "An outlet on a chain of power device has changed to the on state.
     The port number on the appliance that the chain of power device is attached to is contained in pmTrapObjectSerialPortNumber.
     The ID of the power device is contained in pmTrapObjectPduId.
     The socket number that has changed to the on state is contained pmTrapObjectSocketNumber.
     The number of the power device is contained in the pmTrapObjectPduNumber.
     The socket name that has changed to the on state is contained in pmTrapObjectSocketName."      
    --#SUMMARY  "Power device socket state changed to on. Serial port number: %d. PDU number: %d. PDU ID: %s. Socket number: %d. Socket name: %s."
    --#ARGUMENTS   { 0, 1, 2, 3, 4}
    --#SEVERITY    MINOR
    --#CATEGORY    "Status Events"
    --NAME      "Appliance Power Device Socket State On"
    --SHORT     "appliance power device socket state on"
    --EVENT evt_pdsock_onst
    --% TrapTypeEnum=9
::= 352

avctPmOutletCmdOffTrap TRAP-TYPE
    ENTERPRISE  pmProducts
    VARIABLES   { 
                  pmTrapObjectUserName, 
                  pmTrapObjectSerialPortNumber,
                  pmTrapObjectPduNumber,
                  pmTrapObjectPduId,
                  pmTrapObjectSocketNumber,
                  pmTrapObjectSocketName
                }
    DESCRIPTION
    "An outlet on a chain of power device has been issued the off command.
     The port number on the appliance that the chain of power device is attached to is contained in pmTrapObjectSerialPortNumber.
     The power device number in the chain is contained in pmTrapObjectPduNumber.
     The ID of the power device is contained in pmTrapObjectPduId.
     The socket number that was issued the off command is contained in pmTrapObjectSocketNumber.
     The socket name that was issued the off command is contained in pmTrapObjectSocketName.
     The name of the user who issued the off command is contained in pmTrapObjectUserName."      
    --#SUMMARY     "The off command was issued to a power device socket. Command issued by user: %s. Serial port number: %d. PDU number: %d. PDU ID: %s. Socket number: %d. Socket name: %s."
    --#ARGUMENTS   { 0, 1, 2, 3, 4, 5}
    --#SEVERITY    MINOR
    --#CATEGORY    "Status Events"
    --NAME      "Appliance Power Device Socket Off Command"
    --SHORT     "appliance power device socket off command"
    --EVENT evt_pdsock_offcmd
    --% TrapTypeEnum=9
::= 353
    
avctPmOutletStatusOffTrap TRAP-TYPE
    ENTERPRISE  pmProducts
    VARIABLES   { 
                  pmTrapObjectSerialPortNumber,
                  pmTrapObjectPduNumber,
                  pmTrapObjectPduId,
                  pmTrapObjectSocketNumber,
                  pmTrapObjectSocketName
                }
    DESCRIPTION
    "An outlet on a chain of power device has changed to the off state.
     The port number on the appliance that the chain of power device is attached to is contained in pmTrapObjectSerialPortNumber.
     The number of the power device is contained in the pmTrapObjectPduNumber.
     The ID of the power device is contained in pmTrapObjectPduId.
     The socket number that has changed to the off state is contained in pmTrapObjectSocketNumber.
     The socket name that has changed to the off state is contained in pmTrapObjectSocketName."      
    --#SUMMARY  "Power device socket state changed to off. Serial port number: %d. PDU number: %d. PDU ID: %s. Socket number: %d. Socket name: %s."
    --#ARGUMENTS   { 0, 1, 2, 3, 4}
    --#SEVERITY    MINOR
    --#CATEGORY    "Status Events"
    --NAME      "Appliance Power Device Socket State Off"
    --SHORT     "appliance power device socket state off"
    --EVENT evt_pdsock_offst
    --% TrapTypeEnum=9
::= 354

avctPmOutletCmdCycleTrap TRAP-TYPE
    ENTERPRISE  pmProducts
    VARIABLES   { 
                  pmTrapObjectUserName, 
                  pmTrapObjectSerialPortNumber,
                  pmTrapObjectPduNumber,
                  pmTrapObjectPduId,
                  pmTrapObjectSocketNumber,
                  pmTrapObjectSocketName
                }
    DESCRIPTION
    "An outlet on a chain of power device has been issued the cycle command.
     The port number on the appliance that the chain of power device is attached to is contained in pmTrapObjectSerialPortNumber.
     The power device number in the chain is contained in pmTrapObjectPduNumber.
     The ID of the power device is contained in pmTrapObjectPduId.
     The socket number that was issued the cycle command is contained in pmTrapObjectSocketNumber.
     The socket name that was issued the cycle command is contained in pmTrapObjectSocketName.
     The name of the user who issued the cycle command is contained in pmTrapObjectUserName."      
    --#SUMMARY     "The cycle command was issued to a power device socket. Command issued by user: %s. Serial port number: %d. PDU number: %d. PDU ID: %s. Socket number: %d. Socket name: %s."
    --#ARGUMENTS   { 0, 1, 2, 3, 4, 5}
    --#SEVERITY    MINOR
    --#CATEGORY    "Status Events"
    --NAME      "Appliance Power Device Socket Cycle Command"
    --SHORT     "appliance power device socket cycle command"
    --EVENT evt_pdsock_cycmd
    --% TrapTypeEnum=9
::= 355

avctPmOutletCycleFinishedTrap TRAP-TYPE
    ENTERPRISE  pmProducts
    VARIABLES   { 
                  pmTrapObjectSerialPortNumber,
                  pmTrapObjectPduNumber,
                  pmTrapObjectPduId,
                  pmTrapObjectSocketNumber,
                  pmTrapObjectSocketName
                }
    DESCRIPTION
    "An outlet on a chain of power device has completed the cycle command.
     The port number on the appliance that the chain of power device is attached to is contained in pmTrapObjectSerialPortNumber.
     The power device number in the chain is contained in pmTrapObjectPduNumber.
     The ID of the power device is contained in pmTrapObjectPduId.
     The socket number that was issued the cycle command is contained in pmTrapObjectSocketNumber.
     The socket name that was issued the cycle command is contained in pmTrapObjectSocketName."
    --#SUMMARY     "The cycle command has completed to a power device socket.  Serial port number: %d. PDU number: %d. PDU ID: %s. Socket number: %d. Socket name: %s."
    --#ARGUMENTS   { 0, 1, 2, 3, 4}
    --#SEVERITY    MINOR
    --#CATEGORY    "Status Events"
    --NAME      "Appliance Power Device Socket Cycle Command Completed"
    --SHORT     "appliance power device socket cycle command completed"
    --EVENT evt_pdsock_cycom
    --% TrapTypeEnum=9
::= 356 
     
avctPmOutletOnSenseFailTrap TRAP-TYPE
    ENTERPRISE  pmProducts
    VARIABLES   { 
                  pmTrapObjectSerialPortNumber,
                  pmTrapObjectPduNumber,
                  pmTrapObjectPduId,
                  pmTrapObjectSocketNumber,
                  pmTrapObjectSocketName
                }
    DESCRIPTION
    "A power device attached to the appliance has detected an on sense failure for a socket.
     An on sense failure occurs when a socket should be in the on state but is actually in the off state.
     The port number on the appliance that the chain of power device is attached to is contained in pmTrapObjectSerialPortNumber.
     The number of the power device is contained in the pmTrapObjectPduNumber.
     The ID of the power device is contained in pmTrapObjectPduId.
     The socket number that has changed to the on state is contained in pmTrapObjectSocketNumber.
     The socket name that has changed to the on state is contained in pmTrapObjectSocketName."      
    --#SUMMARY  "Power device socket on sense failure. Serial port number: %d. PDU number: %d. PDU ID: %s. Socket number: %d. Socket name: %s."
    --#ARGUMENTS   { 0, 1, 2, 3, 4}
    --#SEVERITY    MINOR
    --#CATEGORY    "Status Events"
    --NAME      "Appliance Power Device On Sense Failure"
    --SHORT     "appliance power device on sense failure"
    --EVENT evt_pd_onfail
    --% TrapTypeEnum=9
::= 357

avctPmOutletOffSenseFailTrap TRAP-TYPE
    ENTERPRISE  pmProducts
    VARIABLES   { 
                  pmTrapObjectSerialPortNumber,
                  pmTrapObjectPduNumber,
                  pmTrapObjectPduId,
                  pmTrapObjectSocketNumber,
                  pmTrapObjectSocketName
                }
    DESCRIPTION
    "A power device attached to the appliance has detected an off sense failure for a socket.
     An off sense failure occurs when a socket should be in the off state but is actually in the on state.
     The port number on the appliance that the chain of power device is attached to is contained in pmTrapObjectSerialPortNumber.
     The number of the power device is contained in the pmTrapObjectPduNumber.
     The ID of the power device is contained in pmTrapObjectPduId.
     The socket number that has changed to the on state is contained in pmTrapObjectSocketNumber.
     The socket name that has changed to the on state is contained in pmTrapObjectSocketName."      
    --#SUMMARY  "Power device socket off sense failure. Serial port number: %d. PDU number: %d. PDU ID: %s. Socket number: %d. Socket name: %s."
    --#ARGUMENTS   { 0, 1, 2, 3, 4}
    --#SEVERITY    MINOR
    --#CATEGORY    "Status Events"
    --NAME      "Appliance Power Device Off Sense Failure"
    --SHORT     "appliance power device off sense failure"
    --EVENT evt_pd_offail
    --% TrapTypeEnum=9
::= 358
  
--
-- ACS 6000 Appliance Specifics TRAPS
-- 500
avctPmSensorThresholdNormalTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "A sensor attached to the appliance cleared its alarm.
     The port number of the appliance where the sensor is attached to is contained in pmTrapObjectSerialPortNumber.
     The number of the PDU where the sensor is attached is contained in pmTrapObjectPduNumber.
     The ID of the PDU where the sensor is attached is contained in pmTrapObjectPduId.
     The Type of the sensor is contained in pmTrapObjectPduElementType.
     The Name of the sensor is contained in pmTrapObjectPduElementName.
     The current value detected when this trap was originated is contained in pmTrapObjectPduCurrentValue."
    --#SUMMARY     "Sensor alarm was cleared. Serial port number: %d. PDU number: %d. PDU ID: %s. Sensor Type: %s. Sensor Name: %s. Current value: %s."
    --#ARGUMENTS   { 0, 1, 2, 3, 4, 5}
    --#SEVERITY    NON-CRITICAL
    --#CATEGORY    "Status Events"
    --NAME      "Sensor Alarm Cleared"
    --SHORT     "sensor alarm cleared"
    --EVENT evt_sensor_alarm_normal
    --% TrapTypeEnum=9
::= 507

avctPmSensorThresholdHighCriticalTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "A sensor attached to the appliance is above its high critical threshold.
     The port number of the appliance where the sensor is attached to is contained in pmTrapObjectSerialPortNumber.
     The number of the PDU where the sensor is attached is contained in pmTrapObjectPduNumber.
     The ID of the PDU where the sensor is attached is contained in pmTrapObjectPduId.
     The Type of the sensor is contained in pmTrapObjectPduElementType.
     The Name of the sensor is contained in pmTrapObjectPduElementName.
     The current value detected when this trap was originated is contained in pmTrapObjectPduCurrentValue."
    --#SUMMARY     "Sensor is above its high critical threshold. Serial port number: %d. PDU number: %d. PDU ID: %s. Sensor Type: %s. Sensor Name: %s. Current value: %s."
    --#ARGUMENTS   { 0, 1, 2, 3, 4, 5}
    --#SEVERITY    NON-CRITICAL
    --#CATEGORY    "Status Events"
    --NAME      "Sensor Alarm High Critical"
    --SHORT     "sensor alarm high critical"
    --EVENT evt_sensor_alarm_high_crit
    --% TrapTypeEnum=9
::= 508

avctPmSensorThresholdHighWarningTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "A sensor attached to the appliance is above its high warning threshold.
     The port number of the appliance where the sensor is attached to is contained in pmTrapObjectSerialPortNumber.
     The number of the PDU where the sensor is attached is contained in pmTrapObjectPduNumber.
     The ID of the PDU where the sensor is attached is contained in pmTrapObjectPduId.
     The Type of the sensor is contained in pmTrapObjectPduElementType.
     The Name of the sensor is contained in pmTrapObjectPduElementName.
     The current value detected when this trap was originated is contained in pmTrapObjectPduCurrentValue."
    --#SUMMARY     "Sensor is above its high warning threshold. Serial port number: %d. PDU number: %d. PDU ID: %s. Sensor Type: %s. Sensor Name: %s. Current value: %s."
    --#ARGUMENTS   { 0, 1, 2, 3, 4, 5}
    --#SEVERITY    NON-CRITICAL
    --#CATEGORY    "Status Events"
    --NAME      "Sensor Alarm High Warning"
    --SHORT     "sensor alarm high warning"
    --EVENT evt_sensor_alarm_high_warn
    --% TrapTypeEnum=9
::= 509

avctPmSensorThresholdLowWarningTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "A sensor attached to the appliance is below its low warning threshold.
     The port number of the appliance where the sensor is attached to is contained in pmTrapObjectSerialPortNumber.
     The number of the PDU where the sensor is attached is contained in pmTrapObjectPduNumber.
     The ID of the PDU where the sensor is attached is contained in pmTrapObjectPduId.
     The Type of the sensor is contained in pmTrapObjectPduElementType.
     The Name of the sensor is contained in pmTrapObjectPduElementName.
     The current value detected when this trap was originated is contained in pmTrapObjectPduCurrentValue."
    --#SUMMARY     "Sensor is below its low warning threshold. Serial port number: %d. PDU number: %d. PDU ID: %s. Sensor Type: %s. Sensor Name: %s. Current value: %s."
    --#ARGUMENTS   { 0, 1, 2, 3, 4, 5}
    --#SEVERITY    NON-CRITICAL
    --#CATEGORY    "Status Events"
    --NAME      "Sensor Alarm Low Warning"
    --SHORT     "sensor alarm low warning"
    --EVENT evt_sensor_alarm_low_warn
    --% TrapTypeEnum=9
::= 510

avctPmSensorThresholdLowCriticalTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "A sensor attached to the appliance is below its low critical threshold.
     The port number of the appliance where the sensor is attached to is contained in pmTrapObjectSerialPortNumber.
     The number of the PDU where the sensor is attached is contained in pmTrapObjectPduNumber.
     The ID of the PDU where the sensor is attached is contained in pmTrapObjectPduId.
     The Type of the sensor is contained in pmTrapObjectPduElementType.
     The Name of the sensor is contained in pmTrapObjectPduElementName.
     The current value detected when this trap was originated is contained in pmTrapObjectPduCurrentValue."
    --#SUMMARY     "Sensor is below its low critical threshold. Serial port number: %d. PDU number: %d. PDU ID: %s. Sensor Type: %s. Sensor Name: %s. Current value: %s."
    --#ARGUMENTS   { 0, 1, 2, 3, 4, 5}
    --#SEVERITY    NON-CRITICAL
    --#CATEGORY    "Status Events"
    --NAME      "Sensor Alarm Low Critical"
    --SHORT     "sensor alarm low critical"
    --EVENT evt_sensor_alarm_low_crit
    --% TrapTypeEnum=9
::= 511
   
avctPmSensorThresholdDigitalSensorAlarmTrap TRAP-TYPE
    ENTERPRISE  pmProducts
    VARIABLES   {
                  pmTrapObjectSerialPortNumber,
                  pmTrapObjectPduNumber,
                  pmTrapObjectPduId,
                  pmTrapObjectPduElementType,
                  pmTrapObjectPduElementName,
                  pmTrapObjectPduCurrentValue
                }
    DESCRIPTION
    "A digital sensor attached to the appliance is in its alarm state.
     The port number of the appliance where the sensor is attached to is contained in pmTrapObjectSerialPortNumber.
     The number of the PDU where the sensor is attached is contained in pmTrapObjectPduNumber.
     The ID of the PDU where the sensor is attached is contained in pmTrapObjectPduId.
     The Type of the sensor is contained in pmTrapObjectPduElementType.
     The Name of the sensor is contained in pmTrapObjectPduElementName.
     The current value detected when this trap was originated is contained in pmTrapObjectPduCurrentValue."
    --#SUMMARY     "Digital sensor changed to alarm state. Serial port number: %d. PDU number: %d. PDU ID: %s. Sensor Type: %s. Sensor Name: %s. Current value: %s."
    --#ARGUMENTS   { 0, 1, 2, 3, 4, 5}
    --#SEVERITY    NON-CRITICAL
    --#CATEGORY    "Status Events"
    --NAME      "Digital Sensor Alarm"
    --SHORT     "digital sensor alarm"
    --EVENT evt_digital_sensor_alarm
    --% TrapTypeEnum=9
::= 512

END
