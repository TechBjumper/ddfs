FIELDSERVER-MIB DEFINITIONS ::= BEGIN

IMPORTS
enterprises, OBJECT-TYPE, MODULE-IDENTITY
FROM SNMPv2-SMI
TRAP-TYPE
FROM RFC-1215;

fieldserver_technologies MODULE-IDENTITY
LAST-UPDATED "200308121338Z"
ORGANIZATION
"FieldServer Technologies"
CONTACT-INFO
"info@fieldserver.com"
DESCRIPTION
"FieldServer Technologies"
::= { enterprises 6347 }

cc08255400_v1_00a OBJECT IDENTIFIER ::= { fieldserver_technologies  1 }

dataArray1 OBJECT IDENTIFIER ::= { cc08255400_v1_00a 1 }

dataValue1_0 OBJECT-TYPE
SYNTAX INTEGER
MAX-ACCESS read-write
STATUS current
DESCRIPTION
"Data value."
::= { dataArray1 0 }

dataValue1_1 OBJECT-TYPE
SYNTAX INTEGER
MAX-ACCESS read-write
STATUS current
DESCRIPTION
"Data value."
::= { dataArray1 1 }

dataValue1_2 OBJECT-TYPE
SYNTAX INTEGER
MAX-ACCESS read-write
STATUS current
DESCRIPTION
"Data value."
::= { dataArray1 2 }

dataValue1_3 OBJECT-TYPE
SYNTAX INTEGER
MAX-ACCESS read-write
STATUS current
DESCRIPTION
"Data value."
::= { dataArray1 3 }

dataValue1_4 OBJECT-TYPE
SYNTAX INTEGER
MAX-ACCESS read-write
STATUS current
DESCRIPTION
"Data value."
::= { dataArray1 4 }

dataValue1_5 OBJECT-TYPE
SYNTAX INTEGER
MAX-ACCESS read-write
STATUS current
DESCRIPTION
"Data value."
::= { dataArray1 5 }

dataValue1_6 OBJECT-TYPE
SYNTAX INTEGER
MAX-ACCESS read-write
STATUS current
DESCRIPTION
"Data value."
::= { dataArray1 6 }

dataValue1_7 OBJECT-TYPE
SYNTAX INTEGER
MAX-ACCESS read-write
STATUS current
DESCRIPTION
"Data value."
::= { dataArray1 7 }

dataValue1_8 OBJECT-TYPE
SYNTAX INTEGER
MAX-ACCESS read-write
STATUS current
DESCRIPTION
"Data value."
::= { dataArray1 8 }

dataValue1_9 OBJECT-TYPE
SYNTAX INTEGER
MAX-ACCESS read-write
STATUS current
DESCRIPTION
"Data value."
::= { dataArray1 9 }

dataValue1_10 OBJECT-TYPE
SYNTAX INTEGER
MAX-ACCESS read-write
STATUS current
DESCRIPTION
"Data value."
::= { dataArray1 10 }

dataValue1_11 OBJECT-TYPE
SYNTAX INTEGER
MAX-ACCESS read-write
STATUS current
DESCRIPTION
"Data value."
::= { dataArray1 11 }

dataValue1_12 OBJECT-TYPE
SYNTAX INTEGER
MAX-ACCESS read-write
STATUS current
DESCRIPTION
"Data value."
::= { dataArray1 12 }

dataValue1_13 OBJECT-TYPE
SYNTAX INTEGER
MAX-ACCESS read-write
STATUS current
DESCRIPTION
"Data value."
::= { dataArray1 13 }

dataValue1_14 OBJECT-TYPE
SYNTAX INTEGER
MAX-ACCESS read-write
STATUS current
DESCRIPTION
"Data value."
::= { dataArray1 14 }

dataValue1_15 OBJECT-TYPE
SYNTAX INTEGER
MAX-ACCESS read-write
STATUS current
DESCRIPTION
"Data value."
::= { dataArray1 15 }

dataValue1_16 OBJECT-TYPE
SYNTAX INTEGER
MAX-ACCESS read-write
STATUS current
DESCRIPTION
"Data value."
::= { dataArray1 16 }

dataValue1_17 OBJECT-TYPE
SYNTAX INTEGER
MAX-ACCESS read-write
STATUS current
DESCRIPTION
"Data value."
::= { dataArray1 17 }

dataValue1_18 OBJECT-TYPE
SYNTAX INTEGER
MAX-ACCESS read-write
STATUS current
DESCRIPTION
"Data value."
::= { dataArray1 18 }

dataValue1_19 OBJECT-TYPE
SYNTAX INTEGER
MAX-ACCESS read-write
STATUS current
DESCRIPTION
"Data value."
::= { dataArray1 19 }

dataValue1_20 OBJECT-TYPE
SYNTAX INTEGER
MAX-ACCESS read-write
STATUS current
DESCRIPTION
"Data value."
::= { dataArray1 20 }

dataValue1_21 OBJECT-TYPE
SYNTAX INTEGER
MAX-ACCESS read-write
STATUS current
DESCRIPTION
"Data value."
::= { dataArray1 21 }

dataValue1_22 OBJECT-TYPE
SYNTAX INTEGER
MAX-ACCESS read-write
STATUS current
DESCRIPTION
"Data value."
::= { dataArray1 22 }

dataValue1_23 OBJECT-TYPE
SYNTAX INTEGER
MAX-ACCESS read-write
STATUS current
DESCRIPTION
"Data value."
::= { dataArray1 23 }

dataValue1_24 OBJECT-TYPE
SYNTAX INTEGER
MAX-ACCESS read-write
STATUS current
DESCRIPTION
"Data value."
::= { dataArray1 24 }

dataValue1_25 OBJECT-TYPE
SYNTAX INTEGER
MAX-ACCESS read-write
STATUS current
DESCRIPTION
"Data value."
::= { dataArray1 25 }

dataValue1_26 OBJECT-TYPE
SYNTAX INTEGER
MAX-ACCESS read-write
STATUS current
DESCRIPTION
"Data value."
::= { dataArray1 26 }

dataValue1_27 OBJECT-TYPE
SYNTAX INTEGER
MAX-ACCESS read-write
STATUS current
DESCRIPTION
"Data value."
::= { dataArray1 27 }

dataValue1_28 OBJECT-TYPE
SYNTAX INTEGER
MAX-ACCESS read-write
STATUS current
DESCRIPTION
"Data value."
::= { dataArray1 28 }

dataValue1_29 OBJECT-TYPE
SYNTAX INTEGER
MAX-ACCESS read-write
STATUS current
DESCRIPTION
"Data value."
::= { dataArray1 29 }

dataValue1_30 OBJECT-TYPE
SYNTAX INTEGER
MAX-ACCESS read-write
STATUS current
DESCRIPTION
"Data value."
::= { dataArray1 30 }

dataValue1_31 OBJECT-TYPE
SYNTAX INTEGER
MAX-ACCESS read-write
STATUS current
DESCRIPTION
"Data value."
::= { dataArray1 31 }

dataValue1_32 OBJECT-TYPE
SYNTAX INTEGER
MAX-ACCESS read-write
STATUS current
DESCRIPTION
"Data value."
::= { dataArray1 32 }

dataValue1_33 OBJECT-TYPE
SYNTAX INTEGER
MAX-ACCESS read-write
STATUS current
DESCRIPTION
"Data value."
::= { dataArray1 33 }

dataValue1_34 OBJECT-TYPE
SYNTAX INTEGER
MAX-ACCESS read-write
STATUS current
DESCRIPTION
"Data value."
::= { dataArray1 34 }

dataValue1_35 OBJECT-TYPE
SYNTAX INTEGER
MAX-ACCESS read-write
STATUS current
DESCRIPTION
"Data value."
::= { dataArray1 35 }

dataValue1_36 OBJECT-TYPE
SYNTAX INTEGER
MAX-ACCESS read-write
STATUS current
DESCRIPTION
"Data value."
::= { dataArray1 36 }

dataValue1_37 OBJECT-TYPE
SYNTAX INTEGER
MAX-ACCESS read-write
STATUS current
DESCRIPTION
"Data value."
::= { dataArray1 37 }

dataValue1_38 OBJECT-TYPE
SYNTAX INTEGER
MAX-ACCESS read-write
STATUS current
DESCRIPTION
"Data value."
::= { dataArray1 38 }

dataValue1_39 OBJECT-TYPE
SYNTAX INTEGER
MAX-ACCESS read-write
STATUS current
DESCRIPTION
"Data value."
::= { dataArray1 39 }

dataValue1_40 OBJECT-TYPE
SYNTAX INTEGER
MAX-ACCESS read-write
STATUS current
DESCRIPTION
"Data value."
::= { dataArray1 40 }

dataValue1_41 OBJECT-TYPE
SYNTAX INTEGER
MAX-ACCESS read-write
STATUS current
DESCRIPTION
"Data value."
::= { dataArray1 41 }

dataValue1_42 OBJECT-TYPE
SYNTAX INTEGER
MAX-ACCESS read-write
STATUS current
DESCRIPTION
"Data value."
::= { dataArray1 42 }

dataValue1_43 OBJECT-TYPE
SYNTAX INTEGER
MAX-ACCESS read-write
STATUS current
DESCRIPTION
"Data value."
::= { dataArray1 43 }

dataValue1_44 OBJECT-TYPE
SYNTAX INTEGER
MAX-ACCESS read-write
STATUS current
DESCRIPTION
"Data value."
::= { dataArray1 44 }

dataValue1_45 OBJECT-TYPE
SYNTAX INTEGER
MAX-ACCESS read-write
STATUS current
DESCRIPTION
"Data value."
::= { dataArray1 45 }

dataValue1_46 OBJECT-TYPE
SYNTAX INTEGER
MAX-ACCESS read-write
STATUS current
DESCRIPTION
"Data value."
::= { dataArray1 46 }

dataValue1_47 OBJECT-TYPE
SYNTAX INTEGER
MAX-ACCESS read-write
STATUS current
DESCRIPTION
"Data value."
::= { dataArray1 47 }

dataValue1_48 OBJECT-TYPE
SYNTAX INTEGER
MAX-ACCESS read-write
STATUS current
DESCRIPTION
"Data value."
::= { dataArray1 48 }

dataValue1_49 OBJECT-TYPE
SYNTAX INTEGER
MAX-ACCESS read-write
STATUS current
DESCRIPTION
"Data value."
::= { dataArray1 49 }

dataValue1_50 OBJECT-TYPE
SYNTAX INTEGER
MAX-ACCESS read-write
STATUS current
DESCRIPTION
"Data value."
::= { dataArray1 50 }

dataValue1_51 OBJECT-TYPE
SYNTAX INTEGER
MAX-ACCESS read-write
STATUS current
DESCRIPTION
"Data value."
::= { dataArray1 51 }

dataValue1_52 OBJECT-TYPE
SYNTAX INTEGER
MAX-ACCESS read-write
STATUS current
DESCRIPTION
"Data value."
::= { dataArray1 52 }

dataValue1_53 OBJECT-TYPE
SYNTAX INTEGER
MAX-ACCESS read-write
STATUS current
DESCRIPTION
"Data value."
::= { dataArray1 53 }

dataValue1_54 OBJECT-TYPE
SYNTAX INTEGER
MAX-ACCESS read-write
STATUS current
DESCRIPTION
"Data value."
::= { dataArray1 54 }

dataValue1_55 OBJECT-TYPE
SYNTAX INTEGER
MAX-ACCESS read-write
STATUS current
DESCRIPTION
"Data value."
::= { dataArray1 55 }

dataValue1_56 OBJECT-TYPE
SYNTAX INTEGER
MAX-ACCESS read-write
STATUS current
DESCRIPTION
"Data value."
::= { dataArray1 56 }

dataValue1_57 OBJECT-TYPE
SYNTAX INTEGER
MAX-ACCESS read-write
STATUS current
DESCRIPTION
"Data value."
::= { dataArray1 57 }

dataValue1_58 OBJECT-TYPE
SYNTAX INTEGER
MAX-ACCESS read-write
STATUS current
DESCRIPTION
"Data value."
::= { dataArray1 58 }

dataValue1_59 OBJECT-TYPE
SYNTAX INTEGER
MAX-ACCESS read-write
STATUS current
DESCRIPTION
"Data value."
::= { dataArray1 59 }

dataValue1_60 OBJECT-TYPE
SYNTAX INTEGER
MAX-ACCESS read-write
STATUS current
DESCRIPTION
"Data value."
::= { dataArray1 60 }

dataValue1_61 OBJECT-TYPE
SYNTAX INTEGER
MAX-ACCESS read-write
STATUS current
DESCRIPTION
"Data value."
::= { dataArray1 61 }

dataValue1_62 OBJECT-TYPE
SYNTAX INTEGER
MAX-ACCESS read-write
STATUS current
DESCRIPTION
"Data value."
::= { dataArray1 62 }

dataValue1_63 OBJECT-TYPE
SYNTAX INTEGER
MAX-ACCESS read-write
STATUS current
DESCRIPTION
"Data value."
::= { dataArray1 63 }

dataValue1_64 OBJECT-TYPE
SYNTAX INTEGER
MAX-ACCESS read-write
STATUS current
DESCRIPTION
"Data value."
::= { dataArray1 64 }

dataValue1_65 OBJECT-TYPE
SYNTAX INTEGER
MAX-ACCESS read-write
STATUS current
DESCRIPTION
"Data value."
::= { dataArray1 65 }

dataValue1_66 OBJECT-TYPE
SYNTAX INTEGER
MAX-ACCESS read-write
STATUS current
DESCRIPTION
"Data value."
::= { dataArray1 66 }

dataValue1_67 OBJECT-TYPE
SYNTAX INTEGER
MAX-ACCESS read-write
STATUS current
DESCRIPTION
"Data value."
::= { dataArray1 67 }

dataValue1_68 OBJECT-TYPE
SYNTAX INTEGER
MAX-ACCESS read-write
STATUS current
DESCRIPTION
"Data value."
::= { dataArray1 68 }

dataValue1_69 OBJECT-TYPE
SYNTAX INTEGER
MAX-ACCESS read-write
STATUS current
DESCRIPTION
"Data value."
::= { dataArray1 69 }

dataValue1_70 OBJECT-TYPE
SYNTAX INTEGER
MAX-ACCESS read-write
STATUS current
DESCRIPTION
"Data value."
::= { dataArray1 70 }

dataValue1_71 OBJECT-TYPE
SYNTAX INTEGER
MAX-ACCESS read-write
STATUS current
DESCRIPTION
"Data value."
::= { dataArray1 71 }

dataValue1_72 OBJECT-TYPE
SYNTAX INTEGER
MAX-ACCESS read-write
STATUS current
DESCRIPTION
"Data value."
::= { dataArray1 72 }

dataValue1_73 OBJECT-TYPE
SYNTAX INTEGER
MAX-ACCESS read-write
STATUS current
DESCRIPTION
"Data value."
::= { dataArray1 73 }

dataValue1_74 OBJECT-TYPE
SYNTAX INTEGER
MAX-ACCESS read-write
STATUS current
DESCRIPTION
"Data value."
::= { dataArray1 74 }

dataValue1_75 OBJECT-TYPE
SYNTAX INTEGER
MAX-ACCESS read-write
STATUS current
DESCRIPTION
"Data value."
::= { dataArray1 75 }

dataValue1_76 OBJECT-TYPE
SYNTAX INTEGER
MAX-ACCESS read-write
STATUS current
DESCRIPTION
"Data value."
::= { dataArray1 76 }

dataValue1_77 OBJECT-TYPE
SYNTAX INTEGER
MAX-ACCESS read-write
STATUS current
DESCRIPTION
"Data value."
::= { dataArray1 77 }

dataValue1_78 OBJECT-TYPE
SYNTAX INTEGER
MAX-ACCESS read-write
STATUS current
DESCRIPTION
"Data value."
::= { dataArray1 78 }

dataValue1_79 OBJECT-TYPE
SYNTAX INTEGER
MAX-ACCESS read-write
STATUS current
DESCRIPTION
"Data value."
::= { dataArray1 79 }

dataValue1_80 OBJECT-TYPE
SYNTAX INTEGER
MAX-ACCESS read-write
STATUS current
DESCRIPTION
"Data value."
::= { dataArray1 80 }

dataValue1_81 OBJECT-TYPE
SYNTAX INTEGER
MAX-ACCESS read-write
STATUS current
DESCRIPTION
"Data value."
::= { dataArray1 81 }

dataValue1_82 OBJECT-TYPE
SYNTAX INTEGER
MAX-ACCESS read-write
STATUS current
DESCRIPTION
"Data value."
::= { dataArray1 82 }

dataValue1_83 OBJECT-TYPE
SYNTAX INTEGER
MAX-ACCESS read-write
STATUS current
DESCRIPTION
"Data value."
::= { dataArray1 83 }

dataValue1_84 OBJECT-TYPE
SYNTAX INTEGER
MAX-ACCESS read-write
STATUS current
DESCRIPTION
"Data value."
::= { dataArray1 84 }

dataValue1_85 OBJECT-TYPE
SYNTAX INTEGER
MAX-ACCESS read-write
STATUS current
DESCRIPTION
"Data value."
::= { dataArray1 85 }

dataValue1_86 OBJECT-TYPE
SYNTAX INTEGER
MAX-ACCESS read-write
STATUS current
DESCRIPTION
"Data value."
::= { dataArray1 86 }

dataValue1_87 OBJECT-TYPE
SYNTAX INTEGER
MAX-ACCESS read-write
STATUS current
DESCRIPTION
"Data value."
::= { dataArray1 87 }

dataValue1_88 OBJECT-TYPE
SYNTAX INTEGER
MAX-ACCESS read-write
STATUS current
DESCRIPTION
"Data value."
::= { dataArray1 88 }

dataValue1_89 OBJECT-TYPE
SYNTAX INTEGER
MAX-ACCESS read-write
STATUS current
DESCRIPTION
"Data value."
::= { dataArray1 89 }

dataValue1_90 OBJECT-TYPE
SYNTAX INTEGER
MAX-ACCESS read-write
STATUS current
DESCRIPTION
"Data value."
::= { dataArray1 90 }

dataValue1_91 OBJECT-TYPE
SYNTAX INTEGER
MAX-ACCESS read-write
STATUS current
DESCRIPTION
"Data value."
::= { dataArray1 91 }

dataValue1_92 OBJECT-TYPE
SYNTAX INTEGER
MAX-ACCESS read-write
STATUS current
DESCRIPTION
"Data value."
::= { dataArray1 92 }

dataValue1_93 OBJECT-TYPE
SYNTAX INTEGER
MAX-ACCESS read-write
STATUS current
DESCRIPTION
"Data value."
::= { dataArray1 93 }

dataValue1_94 OBJECT-TYPE
SYNTAX INTEGER
MAX-ACCESS read-write
STATUS current
DESCRIPTION
"Data value."
::= { dataArray1 94 }

dataValue1_95 OBJECT-TYPE
SYNTAX INTEGER
MAX-ACCESS read-write
STATUS current
DESCRIPTION
"Data value."
::= { dataArray1 95 }

dataValue1_96 OBJECT-TYPE
SYNTAX INTEGER
MAX-ACCESS read-write
STATUS current
DESCRIPTION
"Data value."
::= { dataArray1 96 }

dataValue1_97 OBJECT-TYPE
SYNTAX INTEGER
MAX-ACCESS read-write
STATUS current
DESCRIPTION
"Data value."
::= { dataArray1 97 }

dataValue1_98 OBJECT-TYPE
SYNTAX INTEGER
MAX-ACCESS read-write
STATUS current
DESCRIPTION
"Data value."
::= { dataArray1 98 }

dataValue1_99 OBJECT-TYPE
SYNTAX INTEGER
MAX-ACCESS read-write
STATUS current
DESCRIPTION
"Data value."
::= { dataArray1 99 }

dataValue1_100 OBJECT-TYPE
SYNTAX INTEGER
MAX-ACCESS read-write
STATUS current
DESCRIPTION
"Data value."
::= { dataArray1 100 }

dataValue1_101 OBJECT-TYPE
SYNTAX INTEGER
MAX-ACCESS read-write
STATUS current
DESCRIPTION
"Data value."
::= { dataArray1 101 }

dataValue1_102 OBJECT-TYPE
SYNTAX INTEGER
MAX-ACCESS read-write
STATUS current
DESCRIPTION
"Data value."
::= { dataArray1 102 }

dataValue1_103 OBJECT-TYPE
SYNTAX INTEGER
MAX-ACCESS read-write
STATUS current
DESCRIPTION
"Data value."
::= { dataArray1 103 }

dataValue1_104 OBJECT-TYPE
SYNTAX INTEGER
MAX-ACCESS read-write
STATUS current
DESCRIPTION
"Data value."
::= { dataArray1 104 }

dataValue1_105 OBJECT-TYPE
SYNTAX INTEGER
MAX-ACCESS read-write
STATUS current
DESCRIPTION
"Data value."
::= { dataArray1 105 }

dataValue1_106 OBJECT-TYPE
SYNTAX INTEGER
MAX-ACCESS read-write
STATUS current
DESCRIPTION
"Data value."
::= { dataArray1 106 }

dataValue1_107 OBJECT-TYPE
SYNTAX INTEGER
MAX-ACCESS read-write
STATUS current
DESCRIPTION
"Data value."
::= { dataArray1 107 }

dataValue1_108 OBJECT-TYPE
SYNTAX INTEGER
MAX-ACCESS read-write
STATUS current
DESCRIPTION
"Data value."
::= { dataArray1 108 }

dataValue1_109 OBJECT-TYPE
SYNTAX INTEGER
MAX-ACCESS read-write
STATUS current
DESCRIPTION
"Data value."
::= { dataArray1 109 }

dataValue1_110 OBJECT-TYPE
SYNTAX INTEGER
MAX-ACCESS read-write
STATUS current
DESCRIPTION
"Data value."
::= { dataArray1 110 }

dataValue1_111 OBJECT-TYPE
SYNTAX INTEGER
MAX-ACCESS read-write
STATUS current
DESCRIPTION
"Data value."
::= { dataArray1 111 }

dataValue1_112 OBJECT-TYPE
SYNTAX INTEGER
MAX-ACCESS read-write
STATUS current
DESCRIPTION
"Data value."
::= { dataArray1 112 }

dataValue1_113 OBJECT-TYPE
SYNTAX INTEGER
MAX-ACCESS read-write
STATUS current
DESCRIPTION
"Data value."
::= { dataArray1 113 }

dataValue1_114 OBJECT-TYPE
SYNTAX INTEGER
MAX-ACCESS read-write
STATUS current
DESCRIPTION
"Data value."
::= { dataArray1 114 }

dataValue1_115 OBJECT-TYPE
SYNTAX INTEGER
MAX-ACCESS read-write
STATUS current
DESCRIPTION
"Data value."
::= { dataArray1 115 }

dataValue1_116 OBJECT-TYPE
SYNTAX INTEGER
MAX-ACCESS read-write
STATUS current
DESCRIPTION
"Data value."
::= { dataArray1 116 }

dataValue1_117 OBJECT-TYPE
SYNTAX INTEGER
MAX-ACCESS read-write
STATUS current
DESCRIPTION
"Data value."
::= { dataArray1 117 }

dataValue1_118 OBJECT-TYPE
SYNTAX INTEGER
MAX-ACCESS read-write
STATUS current
DESCRIPTION
"Data value."
::= { dataArray1 118 }

dataValue1_119 OBJECT-TYPE
SYNTAX INTEGER
MAX-ACCESS read-write
STATUS current
DESCRIPTION
"Data value."
::= { dataArray1 119 }

dataValue1_120 OBJECT-TYPE
SYNTAX INTEGER
MAX-ACCESS read-write
STATUS current
DESCRIPTION
"Data value."
::= { dataArray1 120 }

dataValue1_121 OBJECT-TYPE
SYNTAX INTEGER
MAX-ACCESS read-write
STATUS current
DESCRIPTION
"Data value."
::= { dataArray1 121 }

dataValue1_122 OBJECT-TYPE
SYNTAX INTEGER
MAX-ACCESS read-write
STATUS current
DESCRIPTION
"Data value."
::= { dataArray1 122 }

dataValue1_123 OBJECT-TYPE
SYNTAX INTEGER
MAX-ACCESS read-write
STATUS current
DESCRIPTION
"Data value."
::= { dataArray1 123 }

dataValue1_124 OBJECT-TYPE
SYNTAX INTEGER
MAX-ACCESS read-write
STATUS current
DESCRIPTION
"Data value."
::= { dataArray1 124 }

dataValue1_125 OBJECT-TYPE
SYNTAX INTEGER
MAX-ACCESS read-write
STATUS current
DESCRIPTION
"Data value."
::= { dataArray1 125 }

dataValue1_126 OBJECT-TYPE
SYNTAX INTEGER
MAX-ACCESS read-write
STATUS current
DESCRIPTION
"Data value."
::= { dataArray1 126 }

dataValue1_127 OBJECT-TYPE
SYNTAX INTEGER
MAX-ACCESS read-write
STATUS current
DESCRIPTION
"Data value."
::= { dataArray1 127 }

dataValue1_128 OBJECT-TYPE
SYNTAX INTEGER
MAX-ACCESS read-write
STATUS current
DESCRIPTION
"Data value."
::= { dataArray1 128 }

dataValue1_129 OBJECT-TYPE
SYNTAX INTEGER
MAX-ACCESS read-write
STATUS current
DESCRIPTION
"Data value."
::= { dataArray1 129 }

dataValue1_130 OBJECT-TYPE
SYNTAX INTEGER
MAX-ACCESS read-write
STATUS current
DESCRIPTION
"Data value."
::= { dataArray1 130 }

dataValue1_131 OBJECT-TYPE
SYNTAX INTEGER
MAX-ACCESS read-write
STATUS current
DESCRIPTION
"Data value."
::= { dataArray1 131 }

dataValue1_132 OBJECT-TYPE
SYNTAX INTEGER
MAX-ACCESS read-write
STATUS current
DESCRIPTION
"Data value."
::= { dataArray1 132 }

dataValue1_133 OBJECT-TYPE
SYNTAX INTEGER
MAX-ACCESS read-write
STATUS current
DESCRIPTION
"Data value."
::= { dataArray1 133 }

dataValue1_134 OBJECT-TYPE
SYNTAX INTEGER
MAX-ACCESS read-write
STATUS current
DESCRIPTION
"Data value."
::= { dataArray1 134 }

dataValue1_135 OBJECT-TYPE
SYNTAX INTEGER
MAX-ACCESS read-write
STATUS current
DESCRIPTION
"Data value."
::= { dataArray1 135 }

dataValue1_136 OBJECT-TYPE
SYNTAX INTEGER
MAX-ACCESS read-write
STATUS current
DESCRIPTION
"Data value."
::= { dataArray1 136 }

dataValue1_137 OBJECT-TYPE
SYNTAX INTEGER
MAX-ACCESS read-write
STATUS current
DESCRIPTION
"Data value."
::= { dataArray1 137 }

dataValue1_138 OBJECT-TYPE
SYNTAX INTEGER
MAX-ACCESS read-write
STATUS current
DESCRIPTION
"Data value."
::= { dataArray1 138 }

dataValue1_139 OBJECT-TYPE
SYNTAX INTEGER
MAX-ACCESS read-write
STATUS current
DESCRIPTION
"Data value."
::= { dataArray1 139 }

dataValue1_140 OBJECT-TYPE
SYNTAX INTEGER
MAX-ACCESS read-write
STATUS current
DESCRIPTION
"Data value."
::= { dataArray1 140 }

dataValue1_141 OBJECT-TYPE
SYNTAX INTEGER
MAX-ACCESS read-write
STATUS current
DESCRIPTION
"Data value."
::= { dataArray1 141 }

dataValue1_142 OBJECT-TYPE
SYNTAX INTEGER
MAX-ACCESS read-write
STATUS current
DESCRIPTION
"Data value."
::= { dataArray1 142 }

dataValue1_143 OBJECT-TYPE
SYNTAX INTEGER
MAX-ACCESS read-write
STATUS current
DESCRIPTION
"Data value."
::= { dataArray1 143 }

dataValue1_144 OBJECT-TYPE
SYNTAX INTEGER
MAX-ACCESS read-write
STATUS current
DESCRIPTION
"Data value."
::= { dataArray1 144 }

dataValue1_145 OBJECT-TYPE
SYNTAX INTEGER
MAX-ACCESS read-write
STATUS current
DESCRIPTION
"Data value."
::= { dataArray1 145 }

dataValue1_146 OBJECT-TYPE
SYNTAX INTEGER
MAX-ACCESS read-write
STATUS current
DESCRIPTION
"Data value."
::= { dataArray1 146 }

dataValue1_147 OBJECT-TYPE
SYNTAX INTEGER
MAX-ACCESS read-write
STATUS current
DESCRIPTION
"Data value."
::= { dataArray1 147 }

dataValue1_148 OBJECT-TYPE
SYNTAX INTEGER
MAX-ACCESS read-write
STATUS current
DESCRIPTION
"Data value."
::= { dataArray1 148 }

dataValue1_149 OBJECT-TYPE
SYNTAX INTEGER
MAX-ACCESS read-write
STATUS current
DESCRIPTION
"Data value."
::= { dataArray1 149 }

dataValue1_150 OBJECT-TYPE
SYNTAX INTEGER
MAX-ACCESS read-write
STATUS current
DESCRIPTION
"Data value."
::= { dataArray1 150 }

dataValue1_151 OBJECT-TYPE
SYNTAX INTEGER
MAX-ACCESS read-write
STATUS current
DESCRIPTION
"Data value."
::= { dataArray1 151 }

dataValue1_152 OBJECT-TYPE
SYNTAX INTEGER
MAX-ACCESS read-write
STATUS current
DESCRIPTION
"Data value."
::= { dataArray1 152 }

dataValue1_153 OBJECT-TYPE
SYNTAX INTEGER
MAX-ACCESS read-write
STATUS current
DESCRIPTION
"Data value."
::= { dataArray1 153 }

dataValue1_154 OBJECT-TYPE
SYNTAX INTEGER
MAX-ACCESS read-write
STATUS current
DESCRIPTION
"Data value."
::= { dataArray1 154 }

dataValue1_155 OBJECT-TYPE
SYNTAX INTEGER
MAX-ACCESS read-write
STATUS current
DESCRIPTION
"Data value."
::= { dataArray1 155 }

dataValue1_156 OBJECT-TYPE
SYNTAX INTEGER
MAX-ACCESS read-write
STATUS current
DESCRIPTION
"Data value."
::= { dataArray1 156 }

dataValue1_157 OBJECT-TYPE
SYNTAX INTEGER
MAX-ACCESS read-write
STATUS current
DESCRIPTION
"Data value."
::= { dataArray1 157 }

dataValue1_158 OBJECT-TYPE
SYNTAX INTEGER
MAX-ACCESS read-write
STATUS current
DESCRIPTION
"Data value."
::= { dataArray1 158 }

dataValue1_159 OBJECT-TYPE
SYNTAX INTEGER
MAX-ACCESS read-write
STATUS current
DESCRIPTION
"Data value."
::= { dataArray1 159 }

dataValue1_160 OBJECT-TYPE
SYNTAX INTEGER
MAX-ACCESS read-write
STATUS current
DESCRIPTION
"Data value."
::= { dataArray1 160 }

dataValue1_161 OBJECT-TYPE
SYNTAX INTEGER
MAX-ACCESS read-write
STATUS current
DESCRIPTION
"Data value."
::= { dataArray1 161 }

dataValue1_162 OBJECT-TYPE
SYNTAX INTEGER
MAX-ACCESS read-write
STATUS current
DESCRIPTION
"Data value."
::= { dataArray1 162 }

dataValue1_163 OBJECT-TYPE
SYNTAX INTEGER
MAX-ACCESS read-write
STATUS current
DESCRIPTION
"Data value."
::= { dataArray1 163 }

dataValue1_164 OBJECT-TYPE
SYNTAX INTEGER
MAX-ACCESS read-write
STATUS current
DESCRIPTION
"Data value."
::= { dataArray1 164 }

dataValue1_165 OBJECT-TYPE
SYNTAX INTEGER
MAX-ACCESS read-write
STATUS current
DESCRIPTION
"Data value."
::= { dataArray1 165 }

dataValue1_166 OBJECT-TYPE
SYNTAX INTEGER
MAX-ACCESS read-write
STATUS current
DESCRIPTION
"Data value."
::= { dataArray1 166 }

dataValue1_167 OBJECT-TYPE
SYNTAX INTEGER
MAX-ACCESS read-write
STATUS current
DESCRIPTION
"Data value."
::= { dataArray1 167 }

dataValue1_168 OBJECT-TYPE
SYNTAX INTEGER
MAX-ACCESS read-write
STATUS current
DESCRIPTION
"Data value."
::= { dataArray1 168 }

dataValue1_169 OBJECT-TYPE
SYNTAX INTEGER
MAX-ACCESS read-write
STATUS current
DESCRIPTION
"Data value."
::= { dataArray1 169 }

dataValue1_170 OBJECT-TYPE
SYNTAX INTEGER
MAX-ACCESS read-write
STATUS current
DESCRIPTION
"Data value."
::= { dataArray1 170 }

dataValue1_171 OBJECT-TYPE
SYNTAX INTEGER
MAX-ACCESS read-write
STATUS current
DESCRIPTION
"Data value."
::= { dataArray1 171 }

dataValue1_172 OBJECT-TYPE
SYNTAX INTEGER
MAX-ACCESS read-write
STATUS current
DESCRIPTION
"Data value."
::= { dataArray1 172 }

dataValue1_173 OBJECT-TYPE
SYNTAX INTEGER
MAX-ACCESS read-write
STATUS current
DESCRIPTION
"Data value."
::= { dataArray1 173 }

dataValue1_174 OBJECT-TYPE
SYNTAX INTEGER
MAX-ACCESS read-write
STATUS current
DESCRIPTION
"Data value."
::= { dataArray1 174 }

dataValue1_175 OBJECT-TYPE
SYNTAX INTEGER
MAX-ACCESS read-write
STATUS current
DESCRIPTION
"Data value."
::= { dataArray1 175 }

dataValue1_176 OBJECT-TYPE
SYNTAX INTEGER
MAX-ACCESS read-write
STATUS current
DESCRIPTION
"Data value."
::= { dataArray1 176 }

dataValue1_177 OBJECT-TYPE
SYNTAX INTEGER
MAX-ACCESS read-write
STATUS current
DESCRIPTION
"Data value."
::= { dataArray1 177 }

dataValue1_178 OBJECT-TYPE
SYNTAX INTEGER
MAX-ACCESS read-write
STATUS current
DESCRIPTION
"Data value."
::= { dataArray1 178 }

dataValue1_179 OBJECT-TYPE
SYNTAX INTEGER
MAX-ACCESS read-write
STATUS current
DESCRIPTION
"Data value."
::= { dataArray1 179 }

dataValue1_180 OBJECT-TYPE
SYNTAX INTEGER
MAX-ACCESS read-write
STATUS current
DESCRIPTION
"Data value."
::= { dataArray1 180 }

dataValue1_181 OBJECT-TYPE
SYNTAX INTEGER
MAX-ACCESS read-write
STATUS current
DESCRIPTION
"Data value."
::= { dataArray1 181 }

dataValue1_182 OBJECT-TYPE
SYNTAX INTEGER
MAX-ACCESS read-write
STATUS current
DESCRIPTION
"Data value."
::= { dataArray1 182 }

dataValue1_183 OBJECT-TYPE
SYNTAX INTEGER
MAX-ACCESS read-write
STATUS current
DESCRIPTION
"Data value."
::= { dataArray1 183 }

dataValue1_184 OBJECT-TYPE
SYNTAX INTEGER
MAX-ACCESS read-write
STATUS current
DESCRIPTION
"Data value."
::= { dataArray1 184 }

dataValue1_185 OBJECT-TYPE
SYNTAX INTEGER
MAX-ACCESS read-write
STATUS current
DESCRIPTION
"Data value."
::= { dataArray1 185 }

dataValue1_186 OBJECT-TYPE
SYNTAX INTEGER
MAX-ACCESS read-write
STATUS current
DESCRIPTION
"Data value."
::= { dataArray1 186 }

dataValue1_187 OBJECT-TYPE
SYNTAX INTEGER
MAX-ACCESS read-write
STATUS current
DESCRIPTION
"Data value."
::= { dataArray1 187 }

dataValue1_188 OBJECT-TYPE
SYNTAX INTEGER
MAX-ACCESS read-write
STATUS current
DESCRIPTION
"Data value."
::= { dataArray1 188 }

dataValue1_189 OBJECT-TYPE
SYNTAX INTEGER
MAX-ACCESS read-write
STATUS current
DESCRIPTION
"Data value."
::= { dataArray1 189 }

dataValue1_190 OBJECT-TYPE
SYNTAX INTEGER
MAX-ACCESS read-write
STATUS current
DESCRIPTION
"Data value."
::= { dataArray1 190 }

dataValue1_191 OBJECT-TYPE
SYNTAX INTEGER
MAX-ACCESS read-write
STATUS current
DESCRIPTION
"Data value."
::= { dataArray1 191 }

dataValue1_192 OBJECT-TYPE
SYNTAX INTEGER
MAX-ACCESS read-write
STATUS current
DESCRIPTION
"Data value."
::= { dataArray1 192 }

dataValue1_193 OBJECT-TYPE
SYNTAX INTEGER
MAX-ACCESS read-write
STATUS current
DESCRIPTION
"Data value."
::= { dataArray1 193 }

dataValue1_194 OBJECT-TYPE
SYNTAX INTEGER
MAX-ACCESS read-write
STATUS current
DESCRIPTION
"Data value."
::= { dataArray1 194 }

dataValue1_195 OBJECT-TYPE
SYNTAX INTEGER
MAX-ACCESS read-write
STATUS current
DESCRIPTION
"Data value."
::= { dataArray1 195 }

dataValue1_196 OBJECT-TYPE
SYNTAX INTEGER
MAX-ACCESS read-write
STATUS current
DESCRIPTION
"Data value."
::= { dataArray1 196 }

dataValue1_197 OBJECT-TYPE
SYNTAX INTEGER
MAX-ACCESS read-write
STATUS current
DESCRIPTION
"Data value."
::= { dataArray1 197 }

dataValue1_198 OBJECT-TYPE
SYNTAX INTEGER
MAX-ACCESS read-write
STATUS current
DESCRIPTION
"Data value."
::= { dataArray1 198 }

dataValue1_199 OBJECT-TYPE
SYNTAX INTEGER
MAX-ACCESS read-write
STATUS current
DESCRIPTION
"Data value."
::= { dataArray1 199 }

dataValue1_200 OBJECT-TYPE
SYNTAX INTEGER
MAX-ACCESS read-write
STATUS current
DESCRIPTION
"Data value."
::= { dataArray1 200 }

dataValue1_201 OBJECT-TYPE
SYNTAX INTEGER
MAX-ACCESS read-write
STATUS current
DESCRIPTION
"Data value."
::= { dataArray1 201 }

dataValue1_202 OBJECT-TYPE
SYNTAX INTEGER
MAX-ACCESS read-write
STATUS current
DESCRIPTION
"Data value."
::= { dataArray1 202 }

dataValue1_203 OBJECT-TYPE
SYNTAX INTEGER
MAX-ACCESS read-write
STATUS current
DESCRIPTION
"Data value."
::= { dataArray1 203 }

dataValue1_204 OBJECT-TYPE
SYNTAX INTEGER
MAX-ACCESS read-write
STATUS current
DESCRIPTION
"Data value."
::= { dataArray1 204 }

dataValue1_205 OBJECT-TYPE
SYNTAX INTEGER
MAX-ACCESS read-write
STATUS current
DESCRIPTION
"Data value."
::= { dataArray1 205 }

dataValue1_206 OBJECT-TYPE
SYNTAX INTEGER
MAX-ACCESS read-write
STATUS current
DESCRIPTION
"Data value."
::= { dataArray1 206 }

dataValue1_207 OBJECT-TYPE
SYNTAX INTEGER
MAX-ACCESS read-write
STATUS current
DESCRIPTION
"Data value."
::= { dataArray1 207 }

dataValue1_208 OBJECT-TYPE
SYNTAX INTEGER
MAX-ACCESS read-write
STATUS current
DESCRIPTION
"Data value."
::= { dataArray1 208 }

dataValue1_209 OBJECT-TYPE
SYNTAX INTEGER
MAX-ACCESS read-write
STATUS current
DESCRIPTION
"Data value."
::= { dataArray1 209 }

dataValue1_210 OBJECT-TYPE
SYNTAX INTEGER
MAX-ACCESS read-write
STATUS current
DESCRIPTION
"Data value."
::= { dataArray1 210 }

dataValue1_211 OBJECT-TYPE
SYNTAX INTEGER
MAX-ACCESS read-write
STATUS current
DESCRIPTION
"Data value."
::= { dataArray1 211 }

dataValue1_212 OBJECT-TYPE
SYNTAX INTEGER
MAX-ACCESS read-write
STATUS current
DESCRIPTION
"Data value."
::= { dataArray1 212 }

dataValue1_213 OBJECT-TYPE
SYNTAX INTEGER
MAX-ACCESS read-write
STATUS current
DESCRIPTION
"Data value."
::= { dataArray1 213 }

dataValue1_214 OBJECT-TYPE
SYNTAX INTEGER
MAX-ACCESS read-write
STATUS current
DESCRIPTION
"Data value."
::= { dataArray1 214 }

dataValue1_215 OBJECT-TYPE
SYNTAX INTEGER
MAX-ACCESS read-write
STATUS current
DESCRIPTION
"Data value."
::= { dataArray1 215 }

dataValue1_216 OBJECT-TYPE
SYNTAX INTEGER
MAX-ACCESS read-write
STATUS current
DESCRIPTION
"Data value."
::= { dataArray1 216 }

dataValue1_217 OBJECT-TYPE
SYNTAX INTEGER
MAX-ACCESS read-write
STATUS current
DESCRIPTION
"Data value."
::= { dataArray1 217 }

dataValue1_218 OBJECT-TYPE
SYNTAX INTEGER
MAX-ACCESS read-write
STATUS current
DESCRIPTION
"Data value."
::= { dataArray1 218 }

dataValue1_219 OBJECT-TYPE
SYNTAX INTEGER
MAX-ACCESS read-write
STATUS current
DESCRIPTION
"Data value."
::= { dataArray1 219 }

dataValue1_220 OBJECT-TYPE
SYNTAX INTEGER
MAX-ACCESS read-write
STATUS current
DESCRIPTION
"Data value."
::= { dataArray1 220 }

dataValue1_221 OBJECT-TYPE
SYNTAX INTEGER
MAX-ACCESS read-write
STATUS current
DESCRIPTION
"Data value."
::= { dataArray1 221 }

dataValue1_222 OBJECT-TYPE
SYNTAX INTEGER
MAX-ACCESS read-write
STATUS current
DESCRIPTION
"Data value."
::= { dataArray1 222 }

dataValue1_223 OBJECT-TYPE
SYNTAX INTEGER
MAX-ACCESS read-write
STATUS current
DESCRIPTION
"Data value."
::= { dataArray1 223 }

dataValue1_224 OBJECT-TYPE
SYNTAX INTEGER
MAX-ACCESS read-write
STATUS current
DESCRIPTION
"Data value."
::= { dataArray1 224 }

dataValue1_225 OBJECT-TYPE
SYNTAX INTEGER
MAX-ACCESS read-write
STATUS current
DESCRIPTION
"Data value."
::= { dataArray1 225 }

dataValue1_226 OBJECT-TYPE
SYNTAX INTEGER
MAX-ACCESS read-write
STATUS current
DESCRIPTION
"Data value."
::= { dataArray1 226 }

dataValue1_227 OBJECT-TYPE
SYNTAX INTEGER
MAX-ACCESS read-write
STATUS current
DESCRIPTION
"Data value."
::= { dataArray1 227 }

dataValue1_228 OBJECT-TYPE
SYNTAX INTEGER
MAX-ACCESS read-write
STATUS current
DESCRIPTION
"Data value."
::= { dataArray1 228 }

dataValue1_229 OBJECT-TYPE
SYNTAX INTEGER
MAX-ACCESS read-write
STATUS current
DESCRIPTION
"Data value."
::= { dataArray1 229 }

dataValue1_230 OBJECT-TYPE
SYNTAX INTEGER
MAX-ACCESS read-write
STATUS current
DESCRIPTION
"Data value."
::= { dataArray1 230 }

dataValue1_231 OBJECT-TYPE
SYNTAX INTEGER
MAX-ACCESS read-write
STATUS current
DESCRIPTION
"Data value."
::= { dataArray1 231 }

dataValue1_232 OBJECT-TYPE
SYNTAX INTEGER
MAX-ACCESS read-write
STATUS current
DESCRIPTION
"Data value."
::= { dataArray1 232 }

dataValue1_233 OBJECT-TYPE
SYNTAX INTEGER
MAX-ACCESS read-write
STATUS current
DESCRIPTION
"Data value."
::= { dataArray1 233 }

dataValue1_234 OBJECT-TYPE
SYNTAX INTEGER
MAX-ACCESS read-write
STATUS current
DESCRIPTION
"Data value."
::= { dataArray1 234 }

dataValue1_235 OBJECT-TYPE
SYNTAX INTEGER
MAX-ACCESS read-write
STATUS current
DESCRIPTION
"Data value."
::= { dataArray1 235 }

dataValue1_236 OBJECT-TYPE
SYNTAX INTEGER
MAX-ACCESS read-write
STATUS current
DESCRIPTION
"Data value."
::= { dataArray1 236 }

dataValue1_237 OBJECT-TYPE
SYNTAX INTEGER
MAX-ACCESS read-write
STATUS current
DESCRIPTION
"Data value."
::= { dataArray1 237 }

dataValue1_238 OBJECT-TYPE
SYNTAX INTEGER
MAX-ACCESS read-write
STATUS current
DESCRIPTION
"Data value."
::= { dataArray1 238 }

dataValue1_239 OBJECT-TYPE
SYNTAX INTEGER
MAX-ACCESS read-write
STATUS current
DESCRIPTION
"Data value."
::= { dataArray1 239 }

dataValue1_240 OBJECT-TYPE
SYNTAX INTEGER
MAX-ACCESS read-write
STATUS current
DESCRIPTION
"Data value."
::= { dataArray1 240 }

dataValue1_241 OBJECT-TYPE
SYNTAX INTEGER
MAX-ACCESS read-write
STATUS current
DESCRIPTION
"Data value."
::= { dataArray1 241 }

dataValue1_242 OBJECT-TYPE
SYNTAX INTEGER
MAX-ACCESS read-write
STATUS current
DESCRIPTION
"Data value."
::= { dataArray1 242 }

dataValue1_243 OBJECT-TYPE
SYNTAX INTEGER
MAX-ACCESS read-write
STATUS current
DESCRIPTION
"Data value."
::= { dataArray1 243 }

dataValue1_244 OBJECT-TYPE
SYNTAX INTEGER
MAX-ACCESS read-write
STATUS current
DESCRIPTION
"Data value."
::= { dataArray1 244 }

dataValue1_245 OBJECT-TYPE
SYNTAX INTEGER
MAX-ACCESS read-write
STATUS current
DESCRIPTION
"Data value."
::= { dataArray1 245 }

dataValue1_246 OBJECT-TYPE
SYNTAX INTEGER
MAX-ACCESS read-write
STATUS current
DESCRIPTION
"Data value."
::= { dataArray1 246 }

dataValue1_247 OBJECT-TYPE
SYNTAX INTEGER
MAX-ACCESS read-write
STATUS current
DESCRIPTION
"Data value."
::= { dataArray1 247 }

dataValue1_248 OBJECT-TYPE
SYNTAX INTEGER
MAX-ACCESS read-write
STATUS current
DESCRIPTION
"Data value."
::= { dataArray1 248 }

dataValue1_249 OBJECT-TYPE
SYNTAX INTEGER
MAX-ACCESS read-write
STATUS current
DESCRIPTION
"Data value."
::= { dataArray1 249 }

dataValue1_250 OBJECT-TYPE
SYNTAX INTEGER
MAX-ACCESS read-write
STATUS current
DESCRIPTION
"Data value."
::= { dataArray1 250 }

dataValue1_251 OBJECT-TYPE
SYNTAX INTEGER
MAX-ACCESS read-write
STATUS current
DESCRIPTION
"Data value."
::= { dataArray1 251 }

dataValue1_252 OBJECT-TYPE
SYNTAX INTEGER
MAX-ACCESS read-write
STATUS current
DESCRIPTION
"Data value."
::= { dataArray1 252 }

dataValue1_253 OBJECT-TYPE
SYNTAX INTEGER
MAX-ACCESS read-write
STATUS current
DESCRIPTION
"Data value."
::= { dataArray1 253 }

dataValue1_254 OBJECT-TYPE
SYNTAX INTEGER
MAX-ACCESS read-write
STATUS current
DESCRIPTION
"Data value."
::= { dataArray1 254 }

dataValue1_255 OBJECT-TYPE
SYNTAX INTEGER
MAX-ACCESS read-write
STATUS current
DESCRIPTION
"Data value."
::= { dataArray1 255 }

dataValue1_256 OBJECT-TYPE
SYNTAX INTEGER
MAX-ACCESS read-write
STATUS current
DESCRIPTION
"Data value."
::= { dataArray1 256 }

dataValue1_257 OBJECT-TYPE
SYNTAX INTEGER
MAX-ACCESS read-write
STATUS current
DESCRIPTION
"Data value."
::= { dataArray1 257 }

dataValue1_258 OBJECT-TYPE
SYNTAX INTEGER
MAX-ACCESS read-write
STATUS current
DESCRIPTION
"Data value."
::= { dataArray1 258 }

dataValue1_259 OBJECT-TYPE
SYNTAX INTEGER
MAX-ACCESS read-write
STATUS current
DESCRIPTION
"Data value."
::= { dataArray1 259 }

dataValue1_260 OBJECT-TYPE
SYNTAX INTEGER
MAX-ACCESS read-write
STATUS current
DESCRIPTION
"Data value."
::= { dataArray1 260 }

dataValue1_261 OBJECT-TYPE
SYNTAX INTEGER
MAX-ACCESS read-write
STATUS current
DESCRIPTION
"Data value."
::= { dataArray1 261 }

dataValue1_262 OBJECT-TYPE
SYNTAX INTEGER
MAX-ACCESS read-write
STATUS current
DESCRIPTION
"Data value."
::= { dataArray1 262 }

dataValue1_263 OBJECT-TYPE
SYNTAX INTEGER
MAX-ACCESS read-write
STATUS current
DESCRIPTION
"Data value."
::= { dataArray1 263 }

dataValue1_264 OBJECT-TYPE
SYNTAX INTEGER
MAX-ACCESS read-write
STATUS current
DESCRIPTION
"Data value."
::= { dataArray1 264 }

dataValue1_265 OBJECT-TYPE
SYNTAX INTEGER
MAX-ACCESS read-write
STATUS current
DESCRIPTION
"Data value."
::= { dataArray1 265 }

dataValue1_266 OBJECT-TYPE
SYNTAX INTEGER
MAX-ACCESS read-write
STATUS current
DESCRIPTION
"Data value."
::= { dataArray1 266 }

dataValue1_267 OBJECT-TYPE
SYNTAX INTEGER
MAX-ACCESS read-write
STATUS current
DESCRIPTION
"Data value."
::= { dataArray1 267 }

dataValue1_268 OBJECT-TYPE
SYNTAX INTEGER
MAX-ACCESS read-write
STATUS current
DESCRIPTION
"Data value."
::= { dataArray1 268 }

dataValue1_269 OBJECT-TYPE
SYNTAX INTEGER
MAX-ACCESS read-write
STATUS current
DESCRIPTION
"Data value."
::= { dataArray1 269 }

dataValue1_270 OBJECT-TYPE
SYNTAX INTEGER
MAX-ACCESS read-write
STATUS current
DESCRIPTION
"Data value."
::= { dataArray1 270 }

dataValue1_271 OBJECT-TYPE
SYNTAX INTEGER
MAX-ACCESS read-write
STATUS current
DESCRIPTION
"Data value."
::= { dataArray1 271 }

dataValue1_272 OBJECT-TYPE
SYNTAX INTEGER
MAX-ACCESS read-write
STATUS current
DESCRIPTION
"Data value."
::= { dataArray1 272 }

dataValue1_273 OBJECT-TYPE
SYNTAX INTEGER
MAX-ACCESS read-write
STATUS current
DESCRIPTION
"Data value."
::= { dataArray1 273 }

dataValue1_274 OBJECT-TYPE
SYNTAX INTEGER
MAX-ACCESS read-write
STATUS current
DESCRIPTION
"Data value."
::= { dataArray1 274 }

dataValue1_275 OBJECT-TYPE
SYNTAX INTEGER
MAX-ACCESS read-write
STATUS current
DESCRIPTION
"Data value."
::= { dataArray1 275 }

dataValue1_276 OBJECT-TYPE
SYNTAX INTEGER
MAX-ACCESS read-write
STATUS current
DESCRIPTION
"Data value."
::= { dataArray1 276 }

dataValue1_277 OBJECT-TYPE
SYNTAX INTEGER
MAX-ACCESS read-write
STATUS current
DESCRIPTION
"Data value."
::= { dataArray1 277 }

dataValue1_278 OBJECT-TYPE
SYNTAX INTEGER
MAX-ACCESS read-write
STATUS current
DESCRIPTION
"Data value."
::= { dataArray1 278 }

dataValue1_279 OBJECT-TYPE
SYNTAX INTEGER
MAX-ACCESS read-write
STATUS current
DESCRIPTION
"Data value."
::= { dataArray1 279 }

dataValue1_280 OBJECT-TYPE
SYNTAX INTEGER
MAX-ACCESS read-write
STATUS current
DESCRIPTION
"Data value."
::= { dataArray1 280 }

dataValue1_281 OBJECT-TYPE
SYNTAX INTEGER
MAX-ACCESS read-write
STATUS current
DESCRIPTION
"Data value."
::= { dataArray1 281 }

dataValue1_282 OBJECT-TYPE
SYNTAX INTEGER
MAX-ACCESS read-write
STATUS current
DESCRIPTION
"Data value."
::= { dataArray1 282 }

dataValue1_283 OBJECT-TYPE
SYNTAX INTEGER
MAX-ACCESS read-write
STATUS current
DESCRIPTION
"Data value."
::= { dataArray1 283 }

dataValue1_284 OBJECT-TYPE
SYNTAX INTEGER
MAX-ACCESS read-write
STATUS current
DESCRIPTION
"Data value."
::= { dataArray1 284 }

dataValue1_285 OBJECT-TYPE
SYNTAX INTEGER
MAX-ACCESS read-write
STATUS current
DESCRIPTION
"Data value."
::= { dataArray1 285 }

dataValue1_286 OBJECT-TYPE
SYNTAX INTEGER
MAX-ACCESS read-write
STATUS current
DESCRIPTION
"Data value."
::= { dataArray1 286 }

dataValue1_287 OBJECT-TYPE
SYNTAX INTEGER
MAX-ACCESS read-write
STATUS current
DESCRIPTION
"Data value."
::= { dataArray1 287 }

dataValue1_288 OBJECT-TYPE
SYNTAX INTEGER
MAX-ACCESS read-write
STATUS current
DESCRIPTION
"Data value."
::= { dataArray1 288 }

dataValue1_289 OBJECT-TYPE
SYNTAX INTEGER
MAX-ACCESS read-write
STATUS current
DESCRIPTION
"Data value."
::= { dataArray1 289 }

dataValue1_290 OBJECT-TYPE
SYNTAX INTEGER
MAX-ACCESS read-write
STATUS current
DESCRIPTION
"Data value."
::= { dataArray1 290 }

dataValue1_291 OBJECT-TYPE
SYNTAX INTEGER
MAX-ACCESS read-write
STATUS current
DESCRIPTION
"Data value."
::= { dataArray1 291 }

dataValue1_292 OBJECT-TYPE
SYNTAX INTEGER
MAX-ACCESS read-write
STATUS current
DESCRIPTION
"Data value."
::= { dataArray1 292 }

dataValue1_293 OBJECT-TYPE
SYNTAX INTEGER
MAX-ACCESS read-write
STATUS current
DESCRIPTION
"Data value."
::= { dataArray1 293 }

dataValue1_294 OBJECT-TYPE
SYNTAX INTEGER
MAX-ACCESS read-write
STATUS current
DESCRIPTION
"Data value."
::= { dataArray1 294 }

dataValue1_295 OBJECT-TYPE
SYNTAX INTEGER
MAX-ACCESS read-write
STATUS current
DESCRIPTION
"Data value."
::= { dataArray1 295 }

dataValue1_296 OBJECT-TYPE
SYNTAX INTEGER
MAX-ACCESS read-write
STATUS current
DESCRIPTION
"Data value."
::= { dataArray1 296 }

dataValue1_297 OBJECT-TYPE
SYNTAX INTEGER
MAX-ACCESS read-write
STATUS current
DESCRIPTION
"Data value."
::= { dataArray1 297 }

dataValue1_298 OBJECT-TYPE
SYNTAX INTEGER
MAX-ACCESS read-write
STATUS current
DESCRIPTION
"Data value."
::= { dataArray1 298 }

dataValue1_299 OBJECT-TYPE
SYNTAX INTEGER
MAX-ACCESS read-write
STATUS current
DESCRIPTION
"Data value."
::= { dataArray1 299 }

dataValue1_300 OBJECT-TYPE
SYNTAX INTEGER
MAX-ACCESS read-write
STATUS current
DESCRIPTION
"Data value."
::= { dataArray1 300 }

dataValue1_301 OBJECT-TYPE
SYNTAX INTEGER
MAX-ACCESS read-write
STATUS current
DESCRIPTION
"Data value."
::= { dataArray1 301 }

dataValue1_302 OBJECT-TYPE
SYNTAX INTEGER
MAX-ACCESS read-write
STATUS current
DESCRIPTION
"Data value."
::= { dataArray1 302 }

dataValue1_303 OBJECT-TYPE
SYNTAX INTEGER
MAX-ACCESS read-write
STATUS current
DESCRIPTION
"Data value."
::= { dataArray1 303 }

dataValue1_304 OBJECT-TYPE
SYNTAX INTEGER
MAX-ACCESS read-write
STATUS current
DESCRIPTION
"Data value."
::= { dataArray1 304 }

dataValue1_305 OBJECT-TYPE
SYNTAX INTEGER
MAX-ACCESS read-write
STATUS current
DESCRIPTION
"Data value."
::= { dataArray1 305 }

dataValue1_306 OBJECT-TYPE
SYNTAX INTEGER
MAX-ACCESS read-write
STATUS current
DESCRIPTION
"Data value."
::= { dataArray1 306 }

dataValue1_307 OBJECT-TYPE
SYNTAX INTEGER
MAX-ACCESS read-write
STATUS current
DESCRIPTION
"Data value."
::= { dataArray1 307 }

dataValue1_308 OBJECT-TYPE
SYNTAX INTEGER
MAX-ACCESS read-write
STATUS current
DESCRIPTION
"Data value."
::= { dataArray1 308 }

dataValue1_309 OBJECT-TYPE
SYNTAX INTEGER
MAX-ACCESS read-write
STATUS current
DESCRIPTION
"Data value."
::= { dataArray1 309 }

dataValue1_310 OBJECT-TYPE
SYNTAX INTEGER
MAX-ACCESS read-write
STATUS current
DESCRIPTION
"Data value."
::= { dataArray1 310 }

dataValue1_311 OBJECT-TYPE
SYNTAX INTEGER
MAX-ACCESS read-write
STATUS current
DESCRIPTION
"Data value."
::= { dataArray1 311 }

dataValue1_312 OBJECT-TYPE
SYNTAX INTEGER
MAX-ACCESS read-write
STATUS current
DESCRIPTION
"Data value."
::= { dataArray1 312 }

dataValue1_313 OBJECT-TYPE
SYNTAX INTEGER
MAX-ACCESS read-write
STATUS current
DESCRIPTION
"Data value."
::= { dataArray1 313 }

dataValue1_314 OBJECT-TYPE
SYNTAX INTEGER
MAX-ACCESS read-write
STATUS current
DESCRIPTION
"Data value."
::= { dataArray1 314 }

dataValue1_315 OBJECT-TYPE
SYNTAX INTEGER
MAX-ACCESS read-write
STATUS current
DESCRIPTION
"Data value."
::= { dataArray1 315 }

dataValue1_316 OBJECT-TYPE
SYNTAX INTEGER
MAX-ACCESS read-write
STATUS current
DESCRIPTION
"Data value."
::= { dataArray1 316 }

dataValue1_317 OBJECT-TYPE
SYNTAX INTEGER
MAX-ACCESS read-write
STATUS current
DESCRIPTION
"Data value."
::= { dataArray1 317 }

dataValue1_318 OBJECT-TYPE
SYNTAX INTEGER
MAX-ACCESS read-write
STATUS current
DESCRIPTION
"Data value."
::= { dataArray1 318 }

dataValue1_319 OBJECT-TYPE
SYNTAX INTEGER
MAX-ACCESS read-write
STATUS current
DESCRIPTION
"Data value."
::= { dataArray1 319 }

dataValue1_320 OBJECT-TYPE
SYNTAX INTEGER
MAX-ACCESS read-write
STATUS current
DESCRIPTION
"Data value."
::= { dataArray1 320 }

dataValue1_321 OBJECT-TYPE
SYNTAX INTEGER
MAX-ACCESS read-write
STATUS current
DESCRIPTION
"Data value."
::= { dataArray1 321 }

dataValue1_322 OBJECT-TYPE
SYNTAX INTEGER
MAX-ACCESS read-write
STATUS current
DESCRIPTION
"Data value."
::= { dataArray1 322 }

dataValue1_323 OBJECT-TYPE
SYNTAX INTEGER
MAX-ACCESS read-write
STATUS current
DESCRIPTION
"Data value."
::= { dataArray1 323 }

dataValue1_324 OBJECT-TYPE
SYNTAX INTEGER
MAX-ACCESS read-write
STATUS current
DESCRIPTION
"Data value."
::= { dataArray1 324 }

dataValue1_325 OBJECT-TYPE
SYNTAX INTEGER
MAX-ACCESS read-write
STATUS current
DESCRIPTION
"Data value."
::= { dataArray1 325 }

dataValue1_326 OBJECT-TYPE
SYNTAX INTEGER
MAX-ACCESS read-write
STATUS current
DESCRIPTION
"Data value."
::= { dataArray1 326 }

dataValue1_327 OBJECT-TYPE
SYNTAX INTEGER
MAX-ACCESS read-write
STATUS current
DESCRIPTION
"Data value."
::= { dataArray1 327 }

dataValue1_328 OBJECT-TYPE
SYNTAX INTEGER
MAX-ACCESS read-write
STATUS current
DESCRIPTION
"Data value."
::= { dataArray1 328 }

dataValue1_329 OBJECT-TYPE
SYNTAX INTEGER
MAX-ACCESS read-write
STATUS current
DESCRIPTION
"Data value."
::= { dataArray1 329 }

dataValue1_330 OBJECT-TYPE
SYNTAX INTEGER
MAX-ACCESS read-write
STATUS current
DESCRIPTION
"Data value."
::= { dataArray1 330 }

dataValue1_331 OBJECT-TYPE
SYNTAX INTEGER
MAX-ACCESS read-write
STATUS current
DESCRIPTION
"Data value."
::= { dataArray1 331 }

dataValue1_332 OBJECT-TYPE
SYNTAX INTEGER
MAX-ACCESS read-write
STATUS current
DESCRIPTION
"Data value."
::= { dataArray1 332 }

dataValue1_333 OBJECT-TYPE
SYNTAX INTEGER
MAX-ACCESS read-write
STATUS current
DESCRIPTION
"Data value."
::= { dataArray1 333 }

dataValue1_334 OBJECT-TYPE
SYNTAX INTEGER
MAX-ACCESS read-write
STATUS current
DESCRIPTION
"Data value."
::= { dataArray1 334 }

dataValue1_335 OBJECT-TYPE
SYNTAX INTEGER
MAX-ACCESS read-write
STATUS current
DESCRIPTION
"Data value."
::= { dataArray1 335 }

dataValue1_336 OBJECT-TYPE
SYNTAX INTEGER
MAX-ACCESS read-write
STATUS current
DESCRIPTION
"Data value."
::= { dataArray1 336 }

dataValue1_337 OBJECT-TYPE
SYNTAX INTEGER
MAX-ACCESS read-write
STATUS current
DESCRIPTION
"Data value."
::= { dataArray1 337 }

dataValue1_338 OBJECT-TYPE
SYNTAX INTEGER
MAX-ACCESS read-write
STATUS current
DESCRIPTION
"Data value."
::= { dataArray1 338 }

dataValue1_339 OBJECT-TYPE
SYNTAX INTEGER
MAX-ACCESS read-write
STATUS current
DESCRIPTION
"Data value."
::= { dataArray1 339 }

dataValue1_340 OBJECT-TYPE
SYNTAX INTEGER
MAX-ACCESS read-write
STATUS current
DESCRIPTION
"Data value."
::= { dataArray1 340 }

dataValue1_341 OBJECT-TYPE
SYNTAX INTEGER
MAX-ACCESS read-write
STATUS current
DESCRIPTION
"Data value."
::= { dataArray1 341 }

dataValue1_342 OBJECT-TYPE
SYNTAX INTEGER
MAX-ACCESS read-write
STATUS current
DESCRIPTION
"Data value."
::= { dataArray1 342 }

dataValue1_343 OBJECT-TYPE
SYNTAX INTEGER
MAX-ACCESS read-write
STATUS current
DESCRIPTION
"Data value."
::= { dataArray1 343 }

dataValue1_344 OBJECT-TYPE
SYNTAX INTEGER
MAX-ACCESS read-write
STATUS current
DESCRIPTION
"Data value."
::= { dataArray1 344 }

dataValue1_345 OBJECT-TYPE
SYNTAX INTEGER
MAX-ACCESS read-write
STATUS current
DESCRIPTION
"Data value."
::= { dataArray1 345 }

dataValue1_346 OBJECT-TYPE
SYNTAX INTEGER
MAX-ACCESS read-write
STATUS current
DESCRIPTION
"Data value."
::= { dataArray1 346 }

dataValue1_347 OBJECT-TYPE
SYNTAX INTEGER
MAX-ACCESS read-write
STATUS current
DESCRIPTION
"Data value."
::= { dataArray1 347 }

dataValue1_348 OBJECT-TYPE
SYNTAX INTEGER
MAX-ACCESS read-write
STATUS current
DESCRIPTION
"Data value."
::= { dataArray1 348 }

dataValue1_349 OBJECT-TYPE
SYNTAX INTEGER
MAX-ACCESS read-write
STATUS current
DESCRIPTION
"Data value."
::= { dataArray1 349 }

dataValue1_350 OBJECT-TYPE
SYNTAX INTEGER
MAX-ACCESS read-write
STATUS current
DESCRIPTION
"Data value."
::= { dataArray1 350 }

dataValue1_351 OBJECT-TYPE
SYNTAX INTEGER
MAX-ACCESS read-write
STATUS current
DESCRIPTION
"Data value."
::= { dataArray1 351 }

dataValue1_352 OBJECT-TYPE
SYNTAX INTEGER
MAX-ACCESS read-write
STATUS current
DESCRIPTION
"Data value."
::= { dataArray1 352 }

dataValue1_353 OBJECT-TYPE
SYNTAX INTEGER
MAX-ACCESS read-write
STATUS current
DESCRIPTION
"Data value."
::= { dataArray1 353 }

dataValue1_354 OBJECT-TYPE
SYNTAX INTEGER
MAX-ACCESS read-write
STATUS current
DESCRIPTION
"Data value."
::= { dataArray1 354 }

dataValue1_355 OBJECT-TYPE
SYNTAX INTEGER
MAX-ACCESS read-write
STATUS current
DESCRIPTION
"Data value."
::= { dataArray1 355 }

dataValue1_356 OBJECT-TYPE
SYNTAX INTEGER
MAX-ACCESS read-write
STATUS current
DESCRIPTION
"Data value."
::= { dataArray1 356 }

dataValue1_357 OBJECT-TYPE
SYNTAX INTEGER
MAX-ACCESS read-write
STATUS current
DESCRIPTION
"Data value."
::= { dataArray1 357 }

dataValue1_358 OBJECT-TYPE
SYNTAX INTEGER
MAX-ACCESS read-write
STATUS current
DESCRIPTION
"Data value."
::= { dataArray1 358 }

dataValue1_359 OBJECT-TYPE
SYNTAX INTEGER
MAX-ACCESS read-write
STATUS current
DESCRIPTION
"Data value."
::= { dataArray1 359 }

dataValue1_360 OBJECT-TYPE
SYNTAX INTEGER
MAX-ACCESS read-write
STATUS current
DESCRIPTION
"Data value."
::= { dataArray1 360 }

dataValue1_361 OBJECT-TYPE
SYNTAX INTEGER
MAX-ACCESS read-write
STATUS current
DESCRIPTION
"Data value."
::= { dataArray1 361 }

dataValue1_362 OBJECT-TYPE
SYNTAX INTEGER
MAX-ACCESS read-write
STATUS current
DESCRIPTION
"Data value."
::= { dataArray1 362 }

dataValue1_363 OBJECT-TYPE
SYNTAX INTEGER
MAX-ACCESS read-write
STATUS current
DESCRIPTION
"Data value."
::= { dataArray1 363 }

dataValue1_364 OBJECT-TYPE
SYNTAX INTEGER
MAX-ACCESS read-write
STATUS current
DESCRIPTION
"Data value."
::= { dataArray1 364 }

dataValue1_365 OBJECT-TYPE
SYNTAX INTEGER
MAX-ACCESS read-write
STATUS current
DESCRIPTION
"Data value."
::= { dataArray1 365 }

dataValue1_366 OBJECT-TYPE
SYNTAX INTEGER
MAX-ACCESS read-write
STATUS current
DESCRIPTION
"Data value."
::= { dataArray1 366 }

dataValue1_367 OBJECT-TYPE
SYNTAX INTEGER
MAX-ACCESS read-write
STATUS current
DESCRIPTION
"Data value."
::= { dataArray1 367 }

dataValue1_368 OBJECT-TYPE
SYNTAX INTEGER
MAX-ACCESS read-write
STATUS current
DESCRIPTION
"Data value."
::= { dataArray1 368 }

dataValue1_369 OBJECT-TYPE
SYNTAX INTEGER
MAX-ACCESS read-write
STATUS current
DESCRIPTION
"Data value."
::= { dataArray1 369 }

dataValue1_370 OBJECT-TYPE
SYNTAX INTEGER
MAX-ACCESS read-write
STATUS current
DESCRIPTION
"Data value."
::= { dataArray1 370 }

dataValue1_371 OBJECT-TYPE
SYNTAX INTEGER
MAX-ACCESS read-write
STATUS current
DESCRIPTION
"Data value."
::= { dataArray1 371 }

dataValue1_372 OBJECT-TYPE
SYNTAX INTEGER
MAX-ACCESS read-write
STATUS current
DESCRIPTION
"Data value."
::= { dataArray1 372 }

dataValue1_373 OBJECT-TYPE
SYNTAX INTEGER
MAX-ACCESS read-write
STATUS current
DESCRIPTION
"Data value."
::= { dataArray1 373 }

dataValue1_374 OBJECT-TYPE
SYNTAX INTEGER
MAX-ACCESS read-write
STATUS current
DESCRIPTION
"Data value."
::= { dataArray1 374 }

dataValue1_375 OBJECT-TYPE
SYNTAX INTEGER
MAX-ACCESS read-write
STATUS current
DESCRIPTION
"Data value."
::= { dataArray1 375 }

dataValue1_376 OBJECT-TYPE
SYNTAX INTEGER
MAX-ACCESS read-write
STATUS current
DESCRIPTION
"Data value."
::= { dataArray1 376 }

dataValue1_377 OBJECT-TYPE
SYNTAX INTEGER
MAX-ACCESS read-write
STATUS current
DESCRIPTION
"Data value."
::= { dataArray1 377 }

dataValue1_378 OBJECT-TYPE
SYNTAX INTEGER
MAX-ACCESS read-write
STATUS current
DESCRIPTION
"Data value."
::= { dataArray1 378 }

dataValue1_379 OBJECT-TYPE
SYNTAX INTEGER
MAX-ACCESS read-write
STATUS current
DESCRIPTION
"Data value."
::= { dataArray1 379 }

dataValue1_380 OBJECT-TYPE
SYNTAX INTEGER
MAX-ACCESS read-write
STATUS current
DESCRIPTION
"Data value."
::= { dataArray1 380 }

dataValue1_381 OBJECT-TYPE
SYNTAX INTEGER
MAX-ACCESS read-write
STATUS current
DESCRIPTION
"Data value."
::= { dataArray1 381 }

dataValue1_382 OBJECT-TYPE
SYNTAX INTEGER
MAX-ACCESS read-write
STATUS current
DESCRIPTION
"Data value."
::= { dataArray1 382 }

dataValue1_383 OBJECT-TYPE
SYNTAX INTEGER
MAX-ACCESS read-write
STATUS current
DESCRIPTION
"Data value."
::= { dataArray1 383 }

dataValue1_384 OBJECT-TYPE
SYNTAX INTEGER
MAX-ACCESS read-write
STATUS current
DESCRIPTION
"Data value."
::= { dataArray1 384 }

dataValue1_385 OBJECT-TYPE
SYNTAX INTEGER
MAX-ACCESS read-write
STATUS current
DESCRIPTION
"Data value."
::= { dataArray1 385 }

dataValue1_386 OBJECT-TYPE
SYNTAX INTEGER
MAX-ACCESS read-write
STATUS current
DESCRIPTION
"Data value."
::= { dataArray1 386 }

dataValue1_387 OBJECT-TYPE
SYNTAX INTEGER
MAX-ACCESS read-write
STATUS current
DESCRIPTION
"Data value."
::= { dataArray1 387 }

dataValue1_388 OBJECT-TYPE
SYNTAX INTEGER
MAX-ACCESS read-write
STATUS current
DESCRIPTION
"Data value."
::= { dataArray1 388 }

dataValue1_389 OBJECT-TYPE
SYNTAX INTEGER
MAX-ACCESS read-write
STATUS current
DESCRIPTION
"Data value."
::= { dataArray1 389 }

dataValue1_390 OBJECT-TYPE
SYNTAX INTEGER
MAX-ACCESS read-write
STATUS current
DESCRIPTION
"Data value."
::= { dataArray1 390 }

dataValue1_391 OBJECT-TYPE
SYNTAX INTEGER
MAX-ACCESS read-write
STATUS current
DESCRIPTION
"Data value."
::= { dataArray1 391 }

dataValue1_392 OBJECT-TYPE
SYNTAX INTEGER
MAX-ACCESS read-write
STATUS current
DESCRIPTION
"Data value."
::= { dataArray1 392 }

dataValue1_393 OBJECT-TYPE
SYNTAX INTEGER
MAX-ACCESS read-write
STATUS current
DESCRIPTION
"Data value."
::= { dataArray1 393 }

dataValue1_394 OBJECT-TYPE
SYNTAX INTEGER
MAX-ACCESS read-write
STATUS current
DESCRIPTION
"Data value."
::= { dataArray1 394 }

dataValue1_395 OBJECT-TYPE
SYNTAX INTEGER
MAX-ACCESS read-write
STATUS current
DESCRIPTION
"Data value."
::= { dataArray1 395 }

dataValue1_396 OBJECT-TYPE
SYNTAX INTEGER
MAX-ACCESS read-write
STATUS current
DESCRIPTION
"Data value."
::= { dataArray1 396 }

dataValue1_397 OBJECT-TYPE
SYNTAX INTEGER
MAX-ACCESS read-write
STATUS current
DESCRIPTION
"Data value."
::= { dataArray1 397 }

dataValue1_398 OBJECT-TYPE
SYNTAX INTEGER
MAX-ACCESS read-write
STATUS current
DESCRIPTION
"Data value."
::= { dataArray1 398 }

dataValue1_399 OBJECT-TYPE
SYNTAX INTEGER
MAX-ACCESS read-write
STATUS current
DESCRIPTION
"Data value."
::= { dataArray1 399 }

dataArray2 OBJECT IDENTIFIER ::= { cc08255400_v1_00a 2 }

dataValue2_0 OBJECT-TYPE
SYNTAX INTEGER
MAX-ACCESS read-write
STATUS current
DESCRIPTION
"Data value."
::= { dataArray2 0 }

dataValue2_1 OBJECT-TYPE
SYNTAX INTEGER
MAX-ACCESS read-write
STATUS current
DESCRIPTION
"Data value."
::= { dataArray2 1 }

dataValue2_2 OBJECT-TYPE
SYNTAX INTEGER
MAX-ACCESS read-write
STATUS current
DESCRIPTION
"Data value."
::= { dataArray2 2 }

dataValue2_3 OBJECT-TYPE
SYNTAX INTEGER
MAX-ACCESS read-write
STATUS current
DESCRIPTION
"Data value."
::= { dataArray2 3 }

dataValue2_4 OBJECT-TYPE
SYNTAX INTEGER
MAX-ACCESS read-write
STATUS current
DESCRIPTION
"Data value."
::= { dataArray2 4 }

dataValue2_5 OBJECT-TYPE
SYNTAX INTEGER
MAX-ACCESS read-write
STATUS current
DESCRIPTION
"Data value."
::= { dataArray2 5 }

dataValue2_6 OBJECT-TYPE
SYNTAX INTEGER
MAX-ACCESS read-write
STATUS current
DESCRIPTION
"Data value."
::= { dataArray2 6 }

dataValue2_7 OBJECT-TYPE
SYNTAX INTEGER
MAX-ACCESS read-write
STATUS current
DESCRIPTION
"Data value."
::= { dataArray2 7 }

dataValue2_8 OBJECT-TYPE
SYNTAX INTEGER
MAX-ACCESS read-write
STATUS current
DESCRIPTION
"Data value."
::= { dataArray2 8 }

dataValue2_9 OBJECT-TYPE
SYNTAX INTEGER
MAX-ACCESS read-write
STATUS current
DESCRIPTION
"Data value."
::= { dataArray2 9 }

dataValue2_10 OBJECT-TYPE
SYNTAX INTEGER
MAX-ACCESS read-write
STATUS current
DESCRIPTION
"Data value."
::= { dataArray2 10 }

dataValue2_11 OBJECT-TYPE
SYNTAX INTEGER
MAX-ACCESS read-write
STATUS current
DESCRIPTION
"Data value."
::= { dataArray2 11 }

dataValue2_12 OBJECT-TYPE
SYNTAX INTEGER
MAX-ACCESS read-write
STATUS current
DESCRIPTION
"Data value."
::= { dataArray2 12 }

dataValue2_13 OBJECT-TYPE
SYNTAX INTEGER
MAX-ACCESS read-write
STATUS current
DESCRIPTION
"Data value."
::= { dataArray2 13 }

dataValue2_14 OBJECT-TYPE
SYNTAX INTEGER
MAX-ACCESS read-write
STATUS current
DESCRIPTION
"Data value."
::= { dataArray2 14 }

dataValue2_15 OBJECT-TYPE
SYNTAX INTEGER
MAX-ACCESS read-write
STATUS current
DESCRIPTION
"Data value."
::= { dataArray2 15 }

dataValue2_16 OBJECT-TYPE
SYNTAX INTEGER
MAX-ACCESS read-write
STATUS current
DESCRIPTION
"Data value."
::= { dataArray2 16 }

dataValue2_17 OBJECT-TYPE
SYNTAX INTEGER
MAX-ACCESS read-write
STATUS current
DESCRIPTION
"Data value."
::= { dataArray2 17 }

dataValue2_18 OBJECT-TYPE
SYNTAX INTEGER
MAX-ACCESS read-write
STATUS current
DESCRIPTION
"Data value."
::= { dataArray2 18 }

dataValue2_19 OBJECT-TYPE
SYNTAX INTEGER
MAX-ACCESS read-write
STATUS current
DESCRIPTION
"Data value."
::= { dataArray2 19 }

dataValue2_20 OBJECT-TYPE
SYNTAX INTEGER
MAX-ACCESS read-write
STATUS current
DESCRIPTION
"Data value."
::= { dataArray2 20 }

dataValue2_21 OBJECT-TYPE
SYNTAX INTEGER
MAX-ACCESS read-write
STATUS current
DESCRIPTION
"Data value."
::= { dataArray2 21 }

dataValue2_22 OBJECT-TYPE
SYNTAX INTEGER
MAX-ACCESS read-write
STATUS current
DESCRIPTION
"Data value."
::= { dataArray2 22 }

dataValue2_23 OBJECT-TYPE
SYNTAX INTEGER
MAX-ACCESS read-write
STATUS current
DESCRIPTION
"Data value."
::= { dataArray2 23 }

dataValue2_24 OBJECT-TYPE
SYNTAX INTEGER
MAX-ACCESS read-write
STATUS current
DESCRIPTION
"Data value."
::= { dataArray2 24 }

dataValue2_25 OBJECT-TYPE
SYNTAX INTEGER
MAX-ACCESS read-write
STATUS current
DESCRIPTION
"Data value."
::= { dataArray2 25 }

dataValue2_26 OBJECT-TYPE
SYNTAX INTEGER
MAX-ACCESS read-write
STATUS current
DESCRIPTION
"Data value."
::= { dataArray2 26 }

dataValue2_27 OBJECT-TYPE
SYNTAX INTEGER
MAX-ACCESS read-write
STATUS current
DESCRIPTION
"Data value."
::= { dataArray2 27 }

dataValue2_28 OBJECT-TYPE
SYNTAX INTEGER
MAX-ACCESS read-write
STATUS current
DESCRIPTION
"Data value."
::= { dataArray2 28 }

dataValue2_29 OBJECT-TYPE
SYNTAX INTEGER
MAX-ACCESS read-write
STATUS current
DESCRIPTION
"Data value."
::= { dataArray2 29 }

dataValue2_30 OBJECT-TYPE
SYNTAX INTEGER
MAX-ACCESS read-write
STATUS current
DESCRIPTION
"Data value."
::= { dataArray2 30 }

dataValue2_31 OBJECT-TYPE
SYNTAX INTEGER
MAX-ACCESS read-write
STATUS current
DESCRIPTION
"Data value."
::= { dataArray2 31 }

dataValue2_32 OBJECT-TYPE
SYNTAX INTEGER
MAX-ACCESS read-write
STATUS current
DESCRIPTION
"Data value."
::= { dataArray2 32 }

dataValue2_33 OBJECT-TYPE
SYNTAX INTEGER
MAX-ACCESS read-write
STATUS current
DESCRIPTION
"Data value."
::= { dataArray2 33 }

dataValue2_34 OBJECT-TYPE
SYNTAX INTEGER
MAX-ACCESS read-write
STATUS current
DESCRIPTION
"Data value."
::= { dataArray2 34 }

dataValue2_35 OBJECT-TYPE
SYNTAX INTEGER
MAX-ACCESS read-write
STATUS current
DESCRIPTION
"Data value."
::= { dataArray2 35 }

dataValue2_36 OBJECT-TYPE
SYNTAX INTEGER
MAX-ACCESS read-write
STATUS current
DESCRIPTION
"Data value."
::= { dataArray2 36 }

dataValue2_37 OBJECT-TYPE
SYNTAX INTEGER
MAX-ACCESS read-write
STATUS current
DESCRIPTION
"Data value."
::= { dataArray2 37 }

dataValue2_38 OBJECT-TYPE
SYNTAX INTEGER
MAX-ACCESS read-write
STATUS current
DESCRIPTION
"Data value."
::= { dataArray2 38 }

dataValue2_39 OBJECT-TYPE
SYNTAX INTEGER
MAX-ACCESS read-write
STATUS current
DESCRIPTION
"Data value."
::= { dataArray2 39 }

dataValue2_40 OBJECT-TYPE
SYNTAX INTEGER
MAX-ACCESS read-write
STATUS current
DESCRIPTION
"Data value."
::= { dataArray2 40 }

dataValue2_41 OBJECT-TYPE
SYNTAX INTEGER
MAX-ACCESS read-write
STATUS current
DESCRIPTION
"Data value."
::= { dataArray2 41 }

dataValue2_42 OBJECT-TYPE
SYNTAX INTEGER
MAX-ACCESS read-write
STATUS current
DESCRIPTION
"Data value."
::= { dataArray2 42 }

dataValue2_43 OBJECT-TYPE
SYNTAX INTEGER
MAX-ACCESS read-write
STATUS current
DESCRIPTION
"Data value."
::= { dataArray2 43 }

dataValue2_44 OBJECT-TYPE
SYNTAX INTEGER
MAX-ACCESS read-write
STATUS current
DESCRIPTION
"Data value."
::= { dataArray2 44 }

dataValue2_45 OBJECT-TYPE
SYNTAX INTEGER
MAX-ACCESS read-write
STATUS current
DESCRIPTION
"Data value."
::= { dataArray2 45 }

dataValue2_46 OBJECT-TYPE
SYNTAX INTEGER
MAX-ACCESS read-write
STATUS current
DESCRIPTION
"Data value."
::= { dataArray2 46 }

dataValue2_47 OBJECT-TYPE
SYNTAX INTEGER
MAX-ACCESS read-write
STATUS current
DESCRIPTION
"Data value."
::= { dataArray2 47 }

dataValue2_48 OBJECT-TYPE
SYNTAX INTEGER
MAX-ACCESS read-write
STATUS current
DESCRIPTION
"Data value."
::= { dataArray2 48 }

dataValue2_49 OBJECT-TYPE
SYNTAX INTEGER
MAX-ACCESS read-write
STATUS current
DESCRIPTION
"Data value."
::= { dataArray2 49 }

dataValue2_50 OBJECT-TYPE
SYNTAX INTEGER
MAX-ACCESS read-write
STATUS current
DESCRIPTION
"Data value."
::= { dataArray2 50 }

dataValue2_51 OBJECT-TYPE
SYNTAX INTEGER
MAX-ACCESS read-write
STATUS current
DESCRIPTION
"Data value."
::= { dataArray2 51 }

dataValue2_52 OBJECT-TYPE
SYNTAX INTEGER
MAX-ACCESS read-write
STATUS current
DESCRIPTION
"Data value."
::= { dataArray2 52 }

dataValue2_53 OBJECT-TYPE
SYNTAX INTEGER
MAX-ACCESS read-write
STATUS current
DESCRIPTION
"Data value."
::= { dataArray2 53 }

dataValue2_54 OBJECT-TYPE
SYNTAX INTEGER
MAX-ACCESS read-write
STATUS current
DESCRIPTION
"Data value."
::= { dataArray2 54 }

dataValue2_55 OBJECT-TYPE
SYNTAX INTEGER
MAX-ACCESS read-write
STATUS current
DESCRIPTION
"Data value."
::= { dataArray2 55 }

dataValue2_56 OBJECT-TYPE
SYNTAX INTEGER
MAX-ACCESS read-write
STATUS current
DESCRIPTION
"Data value."
::= { dataArray2 56 }

dataValue2_57 OBJECT-TYPE
SYNTAX INTEGER
MAX-ACCESS read-write
STATUS current
DESCRIPTION
"Data value."
::= { dataArray2 57 }

dataValue2_58 OBJECT-TYPE
SYNTAX INTEGER
MAX-ACCESS read-write
STATUS current
DESCRIPTION
"Data value."
::= { dataArray2 58 }

dataValue2_59 OBJECT-TYPE
SYNTAX INTEGER
MAX-ACCESS read-write
STATUS current
DESCRIPTION
"Data value."
::= { dataArray2 59 }

dataValue2_60 OBJECT-TYPE
SYNTAX INTEGER
MAX-ACCESS read-write
STATUS current
DESCRIPTION
"Data value."
::= { dataArray2 60 }

dataValue2_61 OBJECT-TYPE
SYNTAX INTEGER
MAX-ACCESS read-write
STATUS current
DESCRIPTION
"Data value."
::= { dataArray2 61 }

dataValue2_62 OBJECT-TYPE
SYNTAX INTEGER
MAX-ACCESS read-write
STATUS current
DESCRIPTION
"Data value."
::= { dataArray2 62 }

dataValue2_63 OBJECT-TYPE
SYNTAX INTEGER
MAX-ACCESS read-write
STATUS current
DESCRIPTION
"Data value."
::= { dataArray2 63 }

dataValue2_64 OBJECT-TYPE
SYNTAX INTEGER
MAX-ACCESS read-write
STATUS current
DESCRIPTION
"Data value."
::= { dataArray2 64 }

dataValue2_65 OBJECT-TYPE
SYNTAX INTEGER
MAX-ACCESS read-write
STATUS current
DESCRIPTION
"Data value."
::= { dataArray2 65 }

dataValue2_66 OBJECT-TYPE
SYNTAX INTEGER
MAX-ACCESS read-write
STATUS current
DESCRIPTION
"Data value."
::= { dataArray2 66 }

dataValue2_67 OBJECT-TYPE
SYNTAX INTEGER
MAX-ACCESS read-write
STATUS current
DESCRIPTION
"Data value."
::= { dataArray2 67 }

dataValue2_68 OBJECT-TYPE
SYNTAX INTEGER
MAX-ACCESS read-write
STATUS current
DESCRIPTION
"Data value."
::= { dataArray2 68 }

dataValue2_69 OBJECT-TYPE
SYNTAX INTEGER
MAX-ACCESS read-write
STATUS current
DESCRIPTION
"Data value."
::= { dataArray2 69 }

dataValue2_70 OBJECT-TYPE
SYNTAX INTEGER
MAX-ACCESS read-write
STATUS current
DESCRIPTION
"Data value."
::= { dataArray2 70 }

dataValue2_71 OBJECT-TYPE
SYNTAX INTEGER
MAX-ACCESS read-write
STATUS current
DESCRIPTION
"Data value."
::= { dataArray2 71 }

dataValue2_72 OBJECT-TYPE
SYNTAX INTEGER
MAX-ACCESS read-write
STATUS current
DESCRIPTION
"Data value."
::= { dataArray2 72 }

dataValue2_73 OBJECT-TYPE
SYNTAX INTEGER
MAX-ACCESS read-write
STATUS current
DESCRIPTION
"Data value."
::= { dataArray2 73 }

dataValue2_74 OBJECT-TYPE
SYNTAX INTEGER
MAX-ACCESS read-write
STATUS current
DESCRIPTION
"Data value."
::= { dataArray2 74 }

dataValue2_75 OBJECT-TYPE
SYNTAX INTEGER
MAX-ACCESS read-write
STATUS current
DESCRIPTION
"Data value."
::= { dataArray2 75 }

dataValue2_76 OBJECT-TYPE
SYNTAX INTEGER
MAX-ACCESS read-write
STATUS current
DESCRIPTION
"Data value."
::= { dataArray2 76 }

dataValue2_77 OBJECT-TYPE
SYNTAX INTEGER
MAX-ACCESS read-write
STATUS current
DESCRIPTION
"Data value."
::= { dataArray2 77 }

dataValue2_78 OBJECT-TYPE
SYNTAX INTEGER
MAX-ACCESS read-write
STATUS current
DESCRIPTION
"Data value."
::= { dataArray2 78 }

dataValue2_79 OBJECT-TYPE
SYNTAX INTEGER
MAX-ACCESS read-write
STATUS current
DESCRIPTION
"Data value."
::= { dataArray2 79 }

dataValue2_80 OBJECT-TYPE
SYNTAX INTEGER
MAX-ACCESS read-write
STATUS current
DESCRIPTION
"Data value."
::= { dataArray2 80 }

dataValue2_81 OBJECT-TYPE
SYNTAX INTEGER
MAX-ACCESS read-write
STATUS current
DESCRIPTION
"Data value."
::= { dataArray2 81 }

dataValue2_82 OBJECT-TYPE
SYNTAX INTEGER
MAX-ACCESS read-write
STATUS current
DESCRIPTION
"Data value."
::= { dataArray2 82 }

dataValue2_83 OBJECT-TYPE
SYNTAX INTEGER
MAX-ACCESS read-write
STATUS current
DESCRIPTION
"Data value."
::= { dataArray2 83 }

dataValue2_84 OBJECT-TYPE
SYNTAX INTEGER
MAX-ACCESS read-write
STATUS current
DESCRIPTION
"Data value."
::= { dataArray2 84 }

dataValue2_85 OBJECT-TYPE
SYNTAX INTEGER
MAX-ACCESS read-write
STATUS current
DESCRIPTION
"Data value."
::= { dataArray2 85 }

dataValue2_86 OBJECT-TYPE
SYNTAX INTEGER
MAX-ACCESS read-write
STATUS current
DESCRIPTION
"Data value."
::= { dataArray2 86 }

dataValue2_87 OBJECT-TYPE
SYNTAX INTEGER
MAX-ACCESS read-write
STATUS current
DESCRIPTION
"Data value."
::= { dataArray2 87 }

dataValue2_88 OBJECT-TYPE
SYNTAX INTEGER
MAX-ACCESS read-write
STATUS current
DESCRIPTION
"Data value."
::= { dataArray2 88 }

dataValue2_89 OBJECT-TYPE
SYNTAX INTEGER
MAX-ACCESS read-write
STATUS current
DESCRIPTION
"Data value."
::= { dataArray2 89 }

dataValue2_90 OBJECT-TYPE
SYNTAX INTEGER
MAX-ACCESS read-write
STATUS current
DESCRIPTION
"Data value."
::= { dataArray2 90 }

dataValue2_91 OBJECT-TYPE
SYNTAX INTEGER
MAX-ACCESS read-write
STATUS current
DESCRIPTION
"Data value."
::= { dataArray2 91 }

dataValue2_92 OBJECT-TYPE
SYNTAX INTEGER
MAX-ACCESS read-write
STATUS current
DESCRIPTION
"Data value."
::= { dataArray2 92 }

dataValue2_93 OBJECT-TYPE
SYNTAX INTEGER
MAX-ACCESS read-write
STATUS current
DESCRIPTION
"Data value."
::= { dataArray2 93 }

dataValue2_94 OBJECT-TYPE
SYNTAX INTEGER
MAX-ACCESS read-write
STATUS current
DESCRIPTION
"Data value."
::= { dataArray2 94 }

dataValue2_95 OBJECT-TYPE
SYNTAX INTEGER
MAX-ACCESS read-write
STATUS current
DESCRIPTION
"Data value."
::= { dataArray2 95 }

dataValue2_96 OBJECT-TYPE
SYNTAX INTEGER
MAX-ACCESS read-write
STATUS current
DESCRIPTION
"Data value."
::= { dataArray2 96 }

dataValue2_97 OBJECT-TYPE
SYNTAX INTEGER
MAX-ACCESS read-write
STATUS current
DESCRIPTION
"Data value."
::= { dataArray2 97 }

dataValue2_98 OBJECT-TYPE
SYNTAX INTEGER
MAX-ACCESS read-write
STATUS current
DESCRIPTION
"Data value."
::= { dataArray2 98 }

dataValue2_99 OBJECT-TYPE
SYNTAX INTEGER
MAX-ACCESS read-write
STATUS current
DESCRIPTION
"Data value."
::= { dataArray2 99 }

dataValue2_100 OBJECT-TYPE
SYNTAX INTEGER
MAX-ACCESS read-write
STATUS current
DESCRIPTION
"Data value."
::= { dataArray2 100 }

dataValue2_101 OBJECT-TYPE
SYNTAX INTEGER
MAX-ACCESS read-write
STATUS current
DESCRIPTION
"Data value."
::= { dataArray2 101 }

dataValue2_102 OBJECT-TYPE
SYNTAX INTEGER
MAX-ACCESS read-write
STATUS current
DESCRIPTION
"Data value."
::= { dataArray2 102 }

dataValue2_103 OBJECT-TYPE
SYNTAX INTEGER
MAX-ACCESS read-write
STATUS current
DESCRIPTION
"Data value."
::= { dataArray2 103 }

dataValue2_104 OBJECT-TYPE
SYNTAX INTEGER
MAX-ACCESS read-write
STATUS current
DESCRIPTION
"Data value."
::= { dataArray2 104 }

dataValue2_105 OBJECT-TYPE
SYNTAX INTEGER
MAX-ACCESS read-write
STATUS current
DESCRIPTION
"Data value."
::= { dataArray2 105 }

dataValue2_106 OBJECT-TYPE
SYNTAX INTEGER
MAX-ACCESS read-write
STATUS current
DESCRIPTION
"Data value."
::= { dataArray2 106 }

dataValue2_107 OBJECT-TYPE
SYNTAX INTEGER
MAX-ACCESS read-write
STATUS current
DESCRIPTION
"Data value."
::= { dataArray2 107 }

dataValue2_108 OBJECT-TYPE
SYNTAX INTEGER
MAX-ACCESS read-write
STATUS current
DESCRIPTION
"Data value."
::= { dataArray2 108 }

dataValue2_109 OBJECT-TYPE
SYNTAX INTEGER
MAX-ACCESS read-write
STATUS current
DESCRIPTION
"Data value."
::= { dataArray2 109 }

dataValue2_110 OBJECT-TYPE
SYNTAX INTEGER
MAX-ACCESS read-write
STATUS current
DESCRIPTION
"Data value."
::= { dataArray2 110 }

dataValue2_111 OBJECT-TYPE
SYNTAX INTEGER
MAX-ACCESS read-write
STATUS current
DESCRIPTION
"Data value."
::= { dataArray2 111 }

dataValue2_112 OBJECT-TYPE
SYNTAX INTEGER
MAX-ACCESS read-write
STATUS current
DESCRIPTION
"Data value."
::= { dataArray2 112 }

dataValue2_113 OBJECT-TYPE
SYNTAX INTEGER
MAX-ACCESS read-write
STATUS current
DESCRIPTION
"Data value."
::= { dataArray2 113 }

dataValue2_114 OBJECT-TYPE
SYNTAX INTEGER
MAX-ACCESS read-write
STATUS current
DESCRIPTION
"Data value."
::= { dataArray2 114 }

dataValue2_115 OBJECT-TYPE
SYNTAX INTEGER
MAX-ACCESS read-write
STATUS current
DESCRIPTION
"Data value."
::= { dataArray2 115 }

dataValue2_116 OBJECT-TYPE
SYNTAX INTEGER
MAX-ACCESS read-write
STATUS current
DESCRIPTION
"Data value."
::= { dataArray2 116 }

dataValue2_117 OBJECT-TYPE
SYNTAX INTEGER
MAX-ACCESS read-write
STATUS current
DESCRIPTION
"Data value."
::= { dataArray2 117 }

dataValue2_118 OBJECT-TYPE
SYNTAX INTEGER
MAX-ACCESS read-write
STATUS current
DESCRIPTION
"Data value."
::= { dataArray2 118 }

dataValue2_119 OBJECT-TYPE
SYNTAX INTEGER
MAX-ACCESS read-write
STATUS current
DESCRIPTION
"Data value."
::= { dataArray2 119 }

dataValue2_120 OBJECT-TYPE
SYNTAX INTEGER
MAX-ACCESS read-write
STATUS current
DESCRIPTION
"Data value."
::= { dataArray2 120 }

dataValue2_121 OBJECT-TYPE
SYNTAX INTEGER
MAX-ACCESS read-write
STATUS current
DESCRIPTION
"Data value."
::= { dataArray2 121 }

dataValue2_122 OBJECT-TYPE
SYNTAX INTEGER
MAX-ACCESS read-write
STATUS current
DESCRIPTION
"Data value."
::= { dataArray2 122 }

dataValue2_123 OBJECT-TYPE
SYNTAX INTEGER
MAX-ACCESS read-write
STATUS current
DESCRIPTION
"Data value."
::= { dataArray2 123 }

dataValue2_124 OBJECT-TYPE
SYNTAX INTEGER
MAX-ACCESS read-write
STATUS current
DESCRIPTION
"Data value."
::= { dataArray2 124 }

dataValue2_125 OBJECT-TYPE
SYNTAX INTEGER
MAX-ACCESS read-write
STATUS current
DESCRIPTION
"Data value."
::= { dataArray2 125 }

dataValue2_126 OBJECT-TYPE
SYNTAX INTEGER
MAX-ACCESS read-write
STATUS current
DESCRIPTION
"Data value."
::= { dataArray2 126 }

dataValue2_127 OBJECT-TYPE
SYNTAX INTEGER
MAX-ACCESS read-write
STATUS current
DESCRIPTION
"Data value."
::= { dataArray2 127 }

dataValue2_128 OBJECT-TYPE
SYNTAX INTEGER
MAX-ACCESS read-write
STATUS current
DESCRIPTION
"Data value."
::= { dataArray2 128 }

dataValue2_129 OBJECT-TYPE
SYNTAX INTEGER
MAX-ACCESS read-write
STATUS current
DESCRIPTION
"Data value."
::= { dataArray2 129 }

dataValue2_130 OBJECT-TYPE
SYNTAX INTEGER
MAX-ACCESS read-write
STATUS current
DESCRIPTION
"Data value."
::= { dataArray2 130 }

dataValue2_131 OBJECT-TYPE
SYNTAX INTEGER
MAX-ACCESS read-write
STATUS current
DESCRIPTION
"Data value."
::= { dataArray2 131 }

dataValue2_132 OBJECT-TYPE
SYNTAX INTEGER
MAX-ACCESS read-write
STATUS current
DESCRIPTION
"Data value."
::= { dataArray2 132 }

dataValue2_133 OBJECT-TYPE
SYNTAX INTEGER
MAX-ACCESS read-write
STATUS current
DESCRIPTION
"Data value."
::= { dataArray2 133 }

dataValue2_134 OBJECT-TYPE
SYNTAX INTEGER
MAX-ACCESS read-write
STATUS current
DESCRIPTION
"Data value."
::= { dataArray2 134 }

dataValue2_135 OBJECT-TYPE
SYNTAX INTEGER
MAX-ACCESS read-write
STATUS current
DESCRIPTION
"Data value."
::= { dataArray2 135 }

dataValue2_136 OBJECT-TYPE
SYNTAX INTEGER
MAX-ACCESS read-write
STATUS current
DESCRIPTION
"Data value."
::= { dataArray2 136 }

dataValue2_137 OBJECT-TYPE
SYNTAX INTEGER
MAX-ACCESS read-write
STATUS current
DESCRIPTION
"Data value."
::= { dataArray2 137 }

dataValue2_138 OBJECT-TYPE
SYNTAX INTEGER
MAX-ACCESS read-write
STATUS current
DESCRIPTION
"Data value."
::= { dataArray2 138 }

dataValue2_139 OBJECT-TYPE
SYNTAX INTEGER
MAX-ACCESS read-write
STATUS current
DESCRIPTION
"Data value."
::= { dataArray2 139 }

dataValue2_140 OBJECT-TYPE
SYNTAX INTEGER
MAX-ACCESS read-write
STATUS current
DESCRIPTION
"Data value."
::= { dataArray2 140 }

dataValue2_141 OBJECT-TYPE
SYNTAX INTEGER
MAX-ACCESS read-write
STATUS current
DESCRIPTION
"Data value."
::= { dataArray2 141 }

dataValue2_142 OBJECT-TYPE
SYNTAX INTEGER
MAX-ACCESS read-write
STATUS current
DESCRIPTION
"Data value."
::= { dataArray2 142 }

dataValue2_143 OBJECT-TYPE
SYNTAX INTEGER
MAX-ACCESS read-write
STATUS current
DESCRIPTION
"Data value."
::= { dataArray2 143 }

dataValue2_144 OBJECT-TYPE
SYNTAX INTEGER
MAX-ACCESS read-write
STATUS current
DESCRIPTION
"Data value."
::= { dataArray2 144 }

dataValue2_145 OBJECT-TYPE
SYNTAX INTEGER
MAX-ACCESS read-write
STATUS current
DESCRIPTION
"Data value."
::= { dataArray2 145 }

dataValue2_146 OBJECT-TYPE
SYNTAX INTEGER
MAX-ACCESS read-write
STATUS current
DESCRIPTION
"Data value."
::= { dataArray2 146 }

dataValue2_147 OBJECT-TYPE
SYNTAX INTEGER
MAX-ACCESS read-write
STATUS current
DESCRIPTION
"Data value."
::= { dataArray2 147 }

dataValue2_148 OBJECT-TYPE
SYNTAX INTEGER
MAX-ACCESS read-write
STATUS current
DESCRIPTION
"Data value."
::= { dataArray2 148 }

dataValue2_149 OBJECT-TYPE
SYNTAX INTEGER
MAX-ACCESS read-write
STATUS current
DESCRIPTION
"Data value."
::= { dataArray2 149 }

dataValue2_150 OBJECT-TYPE
SYNTAX INTEGER
MAX-ACCESS read-write
STATUS current
DESCRIPTION
"Data value."
::= { dataArray2 150 }

dataValue2_151 OBJECT-TYPE
SYNTAX INTEGER
MAX-ACCESS read-write
STATUS current
DESCRIPTION
"Data value."
::= { dataArray2 151 }

dataValue2_152 OBJECT-TYPE
SYNTAX INTEGER
MAX-ACCESS read-write
STATUS current
DESCRIPTION
"Data value."
::= { dataArray2 152 }

dataValue2_153 OBJECT-TYPE
SYNTAX INTEGER
MAX-ACCESS read-write
STATUS current
DESCRIPTION
"Data value."
::= { dataArray2 153 }

dataValue2_154 OBJECT-TYPE
SYNTAX INTEGER
MAX-ACCESS read-write
STATUS current
DESCRIPTION
"Data value."
::= { dataArray2 154 }

dataValue2_155 OBJECT-TYPE
SYNTAX INTEGER
MAX-ACCESS read-write
STATUS current
DESCRIPTION
"Data value."
::= { dataArray2 155 }

dataValue2_156 OBJECT-TYPE
SYNTAX INTEGER
MAX-ACCESS read-write
STATUS current
DESCRIPTION
"Data value."
::= { dataArray2 156 }

dataValue2_157 OBJECT-TYPE
SYNTAX INTEGER
MAX-ACCESS read-write
STATUS current
DESCRIPTION
"Data value."
::= { dataArray2 157 }

dataValue2_158 OBJECT-TYPE
SYNTAX INTEGER
MAX-ACCESS read-write
STATUS current
DESCRIPTION
"Data value."
::= { dataArray2 158 }

dataValue2_159 OBJECT-TYPE
SYNTAX INTEGER
MAX-ACCESS read-write
STATUS current
DESCRIPTION
"Data value."
::= { dataArray2 159 }

dataValue2_160 OBJECT-TYPE
SYNTAX INTEGER
MAX-ACCESS read-write
STATUS current
DESCRIPTION
"Data value."
::= { dataArray2 160 }

dataValue2_161 OBJECT-TYPE
SYNTAX INTEGER
MAX-ACCESS read-write
STATUS current
DESCRIPTION
"Data value."
::= { dataArray2 161 }

dataValue2_162 OBJECT-TYPE
SYNTAX INTEGER
MAX-ACCESS read-write
STATUS current
DESCRIPTION
"Data value."
::= { dataArray2 162 }

dataValue2_163 OBJECT-TYPE
SYNTAX INTEGER
MAX-ACCESS read-write
STATUS current
DESCRIPTION
"Data value."
::= { dataArray2 163 }

dataValue2_164 OBJECT-TYPE
SYNTAX INTEGER
MAX-ACCESS read-write
STATUS current
DESCRIPTION
"Data value."
::= { dataArray2 164 }

dataValue2_165 OBJECT-TYPE
SYNTAX INTEGER
MAX-ACCESS read-write
STATUS current
DESCRIPTION
"Data value."
::= { dataArray2 165 }

dataValue2_166 OBJECT-TYPE
SYNTAX INTEGER
MAX-ACCESS read-write
STATUS current
DESCRIPTION
"Data value."
::= { dataArray2 166 }

dataValue2_167 OBJECT-TYPE
SYNTAX INTEGER
MAX-ACCESS read-write
STATUS current
DESCRIPTION
"Data value."
::= { dataArray2 167 }

dataValue2_168 OBJECT-TYPE
SYNTAX INTEGER
MAX-ACCESS read-write
STATUS current
DESCRIPTION
"Data value."
::= { dataArray2 168 }

dataValue2_169 OBJECT-TYPE
SYNTAX INTEGER
MAX-ACCESS read-write
STATUS current
DESCRIPTION
"Data value."
::= { dataArray2 169 }

dataValue2_170 OBJECT-TYPE
SYNTAX INTEGER
MAX-ACCESS read-write
STATUS current
DESCRIPTION
"Data value."
::= { dataArray2 170 }

dataValue2_171 OBJECT-TYPE
SYNTAX INTEGER
MAX-ACCESS read-write
STATUS current
DESCRIPTION
"Data value."
::= { dataArray2 171 }

dataValue2_172 OBJECT-TYPE
SYNTAX INTEGER
MAX-ACCESS read-write
STATUS current
DESCRIPTION
"Data value."
::= { dataArray2 172 }

dataValue2_173 OBJECT-TYPE
SYNTAX INTEGER
MAX-ACCESS read-write
STATUS current
DESCRIPTION
"Data value."
::= { dataArray2 173 }

dataValue2_174 OBJECT-TYPE
SYNTAX INTEGER
MAX-ACCESS read-write
STATUS current
DESCRIPTION
"Data value."
::= { dataArray2 174 }

dataValue2_175 OBJECT-TYPE
SYNTAX INTEGER
MAX-ACCESS read-write
STATUS current
DESCRIPTION
"Data value."
::= { dataArray2 175 }

dataValue2_176 OBJECT-TYPE
SYNTAX INTEGER
MAX-ACCESS read-write
STATUS current
DESCRIPTION
"Data value."
::= { dataArray2 176 }

dataValue2_177 OBJECT-TYPE
SYNTAX INTEGER
MAX-ACCESS read-write
STATUS current
DESCRIPTION
"Data value."
::= { dataArray2 177 }

dataValue2_178 OBJECT-TYPE
SYNTAX INTEGER
MAX-ACCESS read-write
STATUS current
DESCRIPTION
"Data value."
::= { dataArray2 178 }

dataValue2_179 OBJECT-TYPE
SYNTAX INTEGER
MAX-ACCESS read-write
STATUS current
DESCRIPTION
"Data value."
::= { dataArray2 179 }

dataValue2_180 OBJECT-TYPE
SYNTAX INTEGER
MAX-ACCESS read-write
STATUS current
DESCRIPTION
"Data value."
::= { dataArray2 180 }

dataValue2_181 OBJECT-TYPE
SYNTAX INTEGER
MAX-ACCESS read-write
STATUS current
DESCRIPTION
"Data value."
::= { dataArray2 181 }

dataValue2_182 OBJECT-TYPE
SYNTAX INTEGER
MAX-ACCESS read-write
STATUS current
DESCRIPTION
"Data value."
::= { dataArray2 182 }

dataValue2_183 OBJECT-TYPE
SYNTAX INTEGER
MAX-ACCESS read-write
STATUS current
DESCRIPTION
"Data value."
::= { dataArray2 183 }

dataValue2_184 OBJECT-TYPE
SYNTAX INTEGER
MAX-ACCESS read-write
STATUS current
DESCRIPTION
"Data value."
::= { dataArray2 184 }

dataValue2_185 OBJECT-TYPE
SYNTAX INTEGER
MAX-ACCESS read-write
STATUS current
DESCRIPTION
"Data value."
::= { dataArray2 185 }

dataValue2_186 OBJECT-TYPE
SYNTAX INTEGER
MAX-ACCESS read-write
STATUS current
DESCRIPTION
"Data value."
::= { dataArray2 186 }

dataValue2_187 OBJECT-TYPE
SYNTAX INTEGER
MAX-ACCESS read-write
STATUS current
DESCRIPTION
"Data value."
::= { dataArray2 187 }

dataValue2_188 OBJECT-TYPE
SYNTAX INTEGER
MAX-ACCESS read-write
STATUS current
DESCRIPTION
"Data value."
::= { dataArray2 188 }

dataValue2_189 OBJECT-TYPE
SYNTAX INTEGER
MAX-ACCESS read-write
STATUS current
DESCRIPTION
"Data value."
::= { dataArray2 189 }

dataValue2_190 OBJECT-TYPE
SYNTAX INTEGER
MAX-ACCESS read-write
STATUS current
DESCRIPTION
"Data value."
::= { dataArray2 190 }

dataValue2_191 OBJECT-TYPE
SYNTAX INTEGER
MAX-ACCESS read-write
STATUS current
DESCRIPTION
"Data value."
::= { dataArray2 191 }

dataValue2_192 OBJECT-TYPE
SYNTAX INTEGER
MAX-ACCESS read-write
STATUS current
DESCRIPTION
"Data value."
::= { dataArray2 192 }

dataValue2_193 OBJECT-TYPE
SYNTAX INTEGER
MAX-ACCESS read-write
STATUS current
DESCRIPTION
"Data value."
::= { dataArray2 193 }

dataValue2_194 OBJECT-TYPE
SYNTAX INTEGER
MAX-ACCESS read-write
STATUS current
DESCRIPTION
"Data value."
::= { dataArray2 194 }

dataValue2_195 OBJECT-TYPE
SYNTAX INTEGER
MAX-ACCESS read-write
STATUS current
DESCRIPTION
"Data value."
::= { dataArray2 195 }

dataValue2_196 OBJECT-TYPE
SYNTAX INTEGER
MAX-ACCESS read-write
STATUS current
DESCRIPTION
"Data value."
::= { dataArray2 196 }

dataValue2_197 OBJECT-TYPE
SYNTAX INTEGER
MAX-ACCESS read-write
STATUS current
DESCRIPTION
"Data value."
::= { dataArray2 197 }

dataValue2_198 OBJECT-TYPE
SYNTAX INTEGER
MAX-ACCESS read-write
STATUS current
DESCRIPTION
"Data value."
::= { dataArray2 198 }

dataValue2_199 OBJECT-TYPE
SYNTAX INTEGER
MAX-ACCESS read-write
STATUS current
DESCRIPTION
"Data value."
::= { dataArray2 199 }

dataValue2_200 OBJECT-TYPE
SYNTAX INTEGER
MAX-ACCESS read-write
STATUS current
DESCRIPTION
"Data value."
::= { dataArray2 200 }

dataValue2_201 OBJECT-TYPE
SYNTAX INTEGER
MAX-ACCESS read-write
STATUS current
DESCRIPTION
"Data value."
::= { dataArray2 201 }

dataValue2_202 OBJECT-TYPE
SYNTAX INTEGER
MAX-ACCESS read-write
STATUS current
DESCRIPTION
"Data value."
::= { dataArray2 202 }

dataValue2_203 OBJECT-TYPE
SYNTAX INTEGER
MAX-ACCESS read-write
STATUS current
DESCRIPTION
"Data value."
::= { dataArray2 203 }

dataValue2_204 OBJECT-TYPE
SYNTAX INTEGER
MAX-ACCESS read-write
STATUS current
DESCRIPTION
"Data value."
::= { dataArray2 204 }

dataValue2_205 OBJECT-TYPE
SYNTAX INTEGER
MAX-ACCESS read-write
STATUS current
DESCRIPTION
"Data value."
::= { dataArray2 205 }

dataValue2_206 OBJECT-TYPE
SYNTAX INTEGER
MAX-ACCESS read-write
STATUS current
DESCRIPTION
"Data value."
::= { dataArray2 206 }

dataValue2_207 OBJECT-TYPE
SYNTAX INTEGER
MAX-ACCESS read-write
STATUS current
DESCRIPTION
"Data value."
::= { dataArray2 207 }

dataValue2_208 OBJECT-TYPE
SYNTAX INTEGER
MAX-ACCESS read-write
STATUS current
DESCRIPTION
"Data value."
::= { dataArray2 208 }

dataValue2_209 OBJECT-TYPE
SYNTAX INTEGER
MAX-ACCESS read-write
STATUS current
DESCRIPTION
"Data value."
::= { dataArray2 209 }

dataValue2_210 OBJECT-TYPE
SYNTAX INTEGER
MAX-ACCESS read-write
STATUS current
DESCRIPTION
"Data value."
::= { dataArray2 210 }

dataValue2_211 OBJECT-TYPE
SYNTAX INTEGER
MAX-ACCESS read-write
STATUS current
DESCRIPTION
"Data value."
::= { dataArray2 211 }

dataValue2_212 OBJECT-TYPE
SYNTAX INTEGER
MAX-ACCESS read-write
STATUS current
DESCRIPTION
"Data value."
::= { dataArray2 212 }

dataValue2_213 OBJECT-TYPE
SYNTAX INTEGER
MAX-ACCESS read-write
STATUS current
DESCRIPTION
"Data value."
::= { dataArray2 213 }

dataValue2_214 OBJECT-TYPE
SYNTAX INTEGER
MAX-ACCESS read-write
STATUS current
DESCRIPTION
"Data value."
::= { dataArray2 214 }

dataValue2_215 OBJECT-TYPE
SYNTAX INTEGER
MAX-ACCESS read-write
STATUS current
DESCRIPTION
"Data value."
::= { dataArray2 215 }

dataValue2_216 OBJECT-TYPE
SYNTAX INTEGER
MAX-ACCESS read-write
STATUS current
DESCRIPTION
"Data value."
::= { dataArray2 216 }

dataValue2_217 OBJECT-TYPE
SYNTAX INTEGER
MAX-ACCESS read-write
STATUS current
DESCRIPTION
"Data value."
::= { dataArray2 217 }

dataValue2_218 OBJECT-TYPE
SYNTAX INTEGER
MAX-ACCESS read-write
STATUS current
DESCRIPTION
"Data value."
::= { dataArray2 218 }

dataValue2_219 OBJECT-TYPE
SYNTAX INTEGER
MAX-ACCESS read-write
STATUS current
DESCRIPTION
"Data value."
::= { dataArray2 219 }

dataValue2_220 OBJECT-TYPE
SYNTAX INTEGER
MAX-ACCESS read-write
STATUS current
DESCRIPTION
"Data value."
::= { dataArray2 220 }

dataValue2_221 OBJECT-TYPE
SYNTAX INTEGER
MAX-ACCESS read-write
STATUS current
DESCRIPTION
"Data value."
::= { dataArray2 221 }

dataValue2_222 OBJECT-TYPE
SYNTAX INTEGER
MAX-ACCESS read-write
STATUS current
DESCRIPTION
"Data value."
::= { dataArray2 222 }

dataValue2_223 OBJECT-TYPE
SYNTAX INTEGER
MAX-ACCESS read-write
STATUS current
DESCRIPTION
"Data value."
::= { dataArray2 223 }

dataValue2_224 OBJECT-TYPE
SYNTAX INTEGER
MAX-ACCESS read-write
STATUS current
DESCRIPTION
"Data value."
::= { dataArray2 224 }

dataValue2_225 OBJECT-TYPE
SYNTAX INTEGER
MAX-ACCESS read-write
STATUS current
DESCRIPTION
"Data value."
::= { dataArray2 225 }

dataValue2_226 OBJECT-TYPE
SYNTAX INTEGER
MAX-ACCESS read-write
STATUS current
DESCRIPTION
"Data value."
::= { dataArray2 226 }

dataValue2_227 OBJECT-TYPE
SYNTAX INTEGER
MAX-ACCESS read-write
STATUS current
DESCRIPTION
"Data value."
::= { dataArray2 227 }

dataValue2_228 OBJECT-TYPE
SYNTAX INTEGER
MAX-ACCESS read-write
STATUS current
DESCRIPTION
"Data value."
::= { dataArray2 228 }

dataValue2_229 OBJECT-TYPE
SYNTAX INTEGER
MAX-ACCESS read-write
STATUS current
DESCRIPTION
"Data value."
::= { dataArray2 229 }

dataValue2_230 OBJECT-TYPE
SYNTAX INTEGER
MAX-ACCESS read-write
STATUS current
DESCRIPTION
"Data value."
::= { dataArray2 230 }

dataValue2_231 OBJECT-TYPE
SYNTAX INTEGER
MAX-ACCESS read-write
STATUS current
DESCRIPTION
"Data value."
::= { dataArray2 231 }

dataValue2_232 OBJECT-TYPE
SYNTAX INTEGER
MAX-ACCESS read-write
STATUS current
DESCRIPTION
"Data value."
::= { dataArray2 232 }

dataValue2_233 OBJECT-TYPE
SYNTAX INTEGER
MAX-ACCESS read-write
STATUS current
DESCRIPTION
"Data value."
::= { dataArray2 233 }

dataValue2_234 OBJECT-TYPE
SYNTAX INTEGER
MAX-ACCESS read-write
STATUS current
DESCRIPTION
"Data value."
::= { dataArray2 234 }

dataValue2_235 OBJECT-TYPE
SYNTAX INTEGER
MAX-ACCESS read-write
STATUS current
DESCRIPTION
"Data value."
::= { dataArray2 235 }

dataValue2_236 OBJECT-TYPE
SYNTAX INTEGER
MAX-ACCESS read-write
STATUS current
DESCRIPTION
"Data value."
::= { dataArray2 236 }

dataValue2_237 OBJECT-TYPE
SYNTAX INTEGER
MAX-ACCESS read-write
STATUS current
DESCRIPTION
"Data value."
::= { dataArray2 237 }

dataValue2_238 OBJECT-TYPE
SYNTAX INTEGER
MAX-ACCESS read-write
STATUS current
DESCRIPTION
"Data value."
::= { dataArray2 238 }

dataValue2_239 OBJECT-TYPE
SYNTAX INTEGER
MAX-ACCESS read-write
STATUS current
DESCRIPTION
"Data value."
::= { dataArray2 239 }

dataValue2_240 OBJECT-TYPE
SYNTAX INTEGER
MAX-ACCESS read-write
STATUS current
DESCRIPTION
"Data value."
::= { dataArray2 240 }

dataValue2_241 OBJECT-TYPE
SYNTAX INTEGER
MAX-ACCESS read-write
STATUS current
DESCRIPTION
"Data value."
::= { dataArray2 241 }

dataValue2_242 OBJECT-TYPE
SYNTAX INTEGER
MAX-ACCESS read-write
STATUS current
DESCRIPTION
"Data value."
::= { dataArray2 242 }

dataValue2_243 OBJECT-TYPE
SYNTAX INTEGER
MAX-ACCESS read-write
STATUS current
DESCRIPTION
"Data value."
::= { dataArray2 243 }

dataValue2_244 OBJECT-TYPE
SYNTAX INTEGER
MAX-ACCESS read-write
STATUS current
DESCRIPTION
"Data value."
::= { dataArray2 244 }

dataValue2_245 OBJECT-TYPE
SYNTAX INTEGER
MAX-ACCESS read-write
STATUS current
DESCRIPTION
"Data value."
::= { dataArray2 245 }

dataValue2_246 OBJECT-TYPE
SYNTAX INTEGER
MAX-ACCESS read-write
STATUS current
DESCRIPTION
"Data value."
::= { dataArray2 246 }

dataValue2_247 OBJECT-TYPE
SYNTAX INTEGER
MAX-ACCESS read-write
STATUS current
DESCRIPTION
"Data value."
::= { dataArray2 247 }

dataValue2_248 OBJECT-TYPE
SYNTAX INTEGER
MAX-ACCESS read-write
STATUS current
DESCRIPTION
"Data value."
::= { dataArray2 248 }

dataValue2_249 OBJECT-TYPE
SYNTAX INTEGER
MAX-ACCESS read-write
STATUS current
DESCRIPTION
"Data value."
::= { dataArray2 249 }

dataValue2_250 OBJECT-TYPE
SYNTAX INTEGER
MAX-ACCESS read-write
STATUS current
DESCRIPTION
"Data value."
::= { dataArray2 250 }

dataValue2_251 OBJECT-TYPE
SYNTAX INTEGER
MAX-ACCESS read-write
STATUS current
DESCRIPTION
"Data value."
::= { dataArray2 251 }

dataValue2_252 OBJECT-TYPE
SYNTAX INTEGER
MAX-ACCESS read-write
STATUS current
DESCRIPTION
"Data value."
::= { dataArray2 252 }

dataValue2_253 OBJECT-TYPE
SYNTAX INTEGER
MAX-ACCESS read-write
STATUS current
DESCRIPTION
"Data value."
::= { dataArray2 253 }

dataValue2_254 OBJECT-TYPE
SYNTAX INTEGER
MAX-ACCESS read-write
STATUS current
DESCRIPTION
"Data value."
::= { dataArray2 254 }

dataValue2_255 OBJECT-TYPE
SYNTAX INTEGER
MAX-ACCESS read-write
STATUS current
DESCRIPTION
"Data value."
::= { dataArray2 255 }

dataValue2_256 OBJECT-TYPE
SYNTAX INTEGER
MAX-ACCESS read-write
STATUS current
DESCRIPTION
"Data value."
::= { dataArray2 256 }

dataValue2_257 OBJECT-TYPE
SYNTAX INTEGER
MAX-ACCESS read-write
STATUS current
DESCRIPTION
"Data value."
::= { dataArray2 257 }

dataValue2_258 OBJECT-TYPE
SYNTAX INTEGER
MAX-ACCESS read-write
STATUS current
DESCRIPTION
"Data value."
::= { dataArray2 258 }

dataValue2_259 OBJECT-TYPE
SYNTAX INTEGER
MAX-ACCESS read-write
STATUS current
DESCRIPTION
"Data value."
::= { dataArray2 259 }

dataValue2_260 OBJECT-TYPE
SYNTAX INTEGER
MAX-ACCESS read-write
STATUS current
DESCRIPTION
"Data value."
::= { dataArray2 260 }

dataValue2_261 OBJECT-TYPE
SYNTAX INTEGER
MAX-ACCESS read-write
STATUS current
DESCRIPTION
"Data value."
::= { dataArray2 261 }

dataValue2_262 OBJECT-TYPE
SYNTAX INTEGER
MAX-ACCESS read-write
STATUS current
DESCRIPTION
"Data value."
::= { dataArray2 262 }

dataValue2_263 OBJECT-TYPE
SYNTAX INTEGER
MAX-ACCESS read-write
STATUS current
DESCRIPTION
"Data value."
::= { dataArray2 263 }

dataValue2_264 OBJECT-TYPE
SYNTAX INTEGER
MAX-ACCESS read-write
STATUS current
DESCRIPTION
"Data value."
::= { dataArray2 264 }

dataValue2_265 OBJECT-TYPE
SYNTAX INTEGER
MAX-ACCESS read-write
STATUS current
DESCRIPTION
"Data value."
::= { dataArray2 265 }

dataValue2_266 OBJECT-TYPE
SYNTAX INTEGER
MAX-ACCESS read-write
STATUS current
DESCRIPTION
"Data value."
::= { dataArray2 266 }

dataValue2_267 OBJECT-TYPE
SYNTAX INTEGER
MAX-ACCESS read-write
STATUS current
DESCRIPTION
"Data value."
::= { dataArray2 267 }

dataValue2_268 OBJECT-TYPE
SYNTAX INTEGER
MAX-ACCESS read-write
STATUS current
DESCRIPTION
"Data value."
::= { dataArray2 268 }

dataValue2_269 OBJECT-TYPE
SYNTAX INTEGER
MAX-ACCESS read-write
STATUS current
DESCRIPTION
"Data value."
::= { dataArray2 269 }

dataValue2_270 OBJECT-TYPE
SYNTAX INTEGER
MAX-ACCESS read-write
STATUS current
DESCRIPTION
"Data value."
::= { dataArray2 270 }

dataValue2_271 OBJECT-TYPE
SYNTAX INTEGER
MAX-ACCESS read-write
STATUS current
DESCRIPTION
"Data value."
::= { dataArray2 271 }

dataValue2_272 OBJECT-TYPE
SYNTAX INTEGER
MAX-ACCESS read-write
STATUS current
DESCRIPTION
"Data value."
::= { dataArray2 272 }

dataValue2_273 OBJECT-TYPE
SYNTAX INTEGER
MAX-ACCESS read-write
STATUS current
DESCRIPTION
"Data value."
::= { dataArray2 273 }

dataValue2_274 OBJECT-TYPE
SYNTAX INTEGER
MAX-ACCESS read-write
STATUS current
DESCRIPTION
"Data value."
::= { dataArray2 274 }

dataValue2_275 OBJECT-TYPE
SYNTAX INTEGER
MAX-ACCESS read-write
STATUS current
DESCRIPTION
"Data value."
::= { dataArray2 275 }

dataValue2_276 OBJECT-TYPE
SYNTAX INTEGER
MAX-ACCESS read-write
STATUS current
DESCRIPTION
"Data value."
::= { dataArray2 276 }

dataValue2_277 OBJECT-TYPE
SYNTAX INTEGER
MAX-ACCESS read-write
STATUS current
DESCRIPTION
"Data value."
::= { dataArray2 277 }

dataValue2_278 OBJECT-TYPE
SYNTAX INTEGER
MAX-ACCESS read-write
STATUS current
DESCRIPTION
"Data value."
::= { dataArray2 278 }

dataValue2_279 OBJECT-TYPE
SYNTAX INTEGER
MAX-ACCESS read-write
STATUS current
DESCRIPTION
"Data value."
::= { dataArray2 279 }

dataValue2_280 OBJECT-TYPE
SYNTAX INTEGER
MAX-ACCESS read-write
STATUS current
DESCRIPTION
"Data value."
::= { dataArray2 280 }

dataValue2_281 OBJECT-TYPE
SYNTAX INTEGER
MAX-ACCESS read-write
STATUS current
DESCRIPTION
"Data value."
::= { dataArray2 281 }

dataValue2_282 OBJECT-TYPE
SYNTAX INTEGER
MAX-ACCESS read-write
STATUS current
DESCRIPTION
"Data value."
::= { dataArray2 282 }

dataValue2_283 OBJECT-TYPE
SYNTAX INTEGER
MAX-ACCESS read-write
STATUS current
DESCRIPTION
"Data value."
::= { dataArray2 283 }

dataValue2_284 OBJECT-TYPE
SYNTAX INTEGER
MAX-ACCESS read-write
STATUS current
DESCRIPTION
"Data value."
::= { dataArray2 284 }

dataValue2_285 OBJECT-TYPE
SYNTAX INTEGER
MAX-ACCESS read-write
STATUS current
DESCRIPTION
"Data value."
::= { dataArray2 285 }

dataValue2_286 OBJECT-TYPE
SYNTAX INTEGER
MAX-ACCESS read-write
STATUS current
DESCRIPTION
"Data value."
::= { dataArray2 286 }

dataValue2_287 OBJECT-TYPE
SYNTAX INTEGER
MAX-ACCESS read-write
STATUS current
DESCRIPTION
"Data value."
::= { dataArray2 287 }

dataValue2_288 OBJECT-TYPE
SYNTAX INTEGER
MAX-ACCESS read-write
STATUS current
DESCRIPTION
"Data value."
::= { dataArray2 288 }

dataValue2_289 OBJECT-TYPE
SYNTAX INTEGER
MAX-ACCESS read-write
STATUS current
DESCRIPTION
"Data value."
::= { dataArray2 289 }

dataValue2_290 OBJECT-TYPE
SYNTAX INTEGER
MAX-ACCESS read-write
STATUS current
DESCRIPTION
"Data value."
::= { dataArray2 290 }

dataValue2_291 OBJECT-TYPE
SYNTAX INTEGER
MAX-ACCESS read-write
STATUS current
DESCRIPTION
"Data value."
::= { dataArray2 291 }

dataValue2_292 OBJECT-TYPE
SYNTAX INTEGER
MAX-ACCESS read-write
STATUS current
DESCRIPTION
"Data value."
::= { dataArray2 292 }

dataValue2_293 OBJECT-TYPE
SYNTAX INTEGER
MAX-ACCESS read-write
STATUS current
DESCRIPTION
"Data value."
::= { dataArray2 293 }

dataValue2_294 OBJECT-TYPE
SYNTAX INTEGER
MAX-ACCESS read-write
STATUS current
DESCRIPTION
"Data value."
::= { dataArray2 294 }

dataValue2_295 OBJECT-TYPE
SYNTAX INTEGER
MAX-ACCESS read-write
STATUS current
DESCRIPTION
"Data value."
::= { dataArray2 295 }

dataValue2_296 OBJECT-TYPE
SYNTAX INTEGER
MAX-ACCESS read-write
STATUS current
DESCRIPTION
"Data value."
::= { dataArray2 296 }

dataValue2_297 OBJECT-TYPE
SYNTAX INTEGER
MAX-ACCESS read-write
STATUS current
DESCRIPTION
"Data value."
::= { dataArray2 297 }

dataValue2_298 OBJECT-TYPE
SYNTAX INTEGER
MAX-ACCESS read-write
STATUS current
DESCRIPTION
"Data value."
::= { dataArray2 298 }

dataValue2_299 OBJECT-TYPE
SYNTAX INTEGER
MAX-ACCESS read-write
STATUS current
DESCRIPTION
"Data value."
::= { dataArray2 299 }

dataValue2_300 OBJECT-TYPE
SYNTAX INTEGER
MAX-ACCESS read-write
STATUS current
DESCRIPTION
"Data value."
::= { dataArray2 300 }

dataValue2_301 OBJECT-TYPE
SYNTAX INTEGER
MAX-ACCESS read-write
STATUS current
DESCRIPTION
"Data value."
::= { dataArray2 301 }

dataValue2_302 OBJECT-TYPE
SYNTAX INTEGER
MAX-ACCESS read-write
STATUS current
DESCRIPTION
"Data value."
::= { dataArray2 302 }

dataValue2_303 OBJECT-TYPE
SYNTAX INTEGER
MAX-ACCESS read-write
STATUS current
DESCRIPTION
"Data value."
::= { dataArray2 303 }

dataValue2_304 OBJECT-TYPE
SYNTAX INTEGER
MAX-ACCESS read-write
STATUS current
DESCRIPTION
"Data value."
::= { dataArray2 304 }

dataValue2_305 OBJECT-TYPE
SYNTAX INTEGER
MAX-ACCESS read-write
STATUS current
DESCRIPTION
"Data value."
::= { dataArray2 305 }

dataValue2_306 OBJECT-TYPE
SYNTAX INTEGER
MAX-ACCESS read-write
STATUS current
DESCRIPTION
"Data value."
::= { dataArray2 306 }

dataValue2_307 OBJECT-TYPE
SYNTAX INTEGER
MAX-ACCESS read-write
STATUS current
DESCRIPTION
"Data value."
::= { dataArray2 307 }

dataValue2_308 OBJECT-TYPE
SYNTAX INTEGER
MAX-ACCESS read-write
STATUS current
DESCRIPTION
"Data value."
::= { dataArray2 308 }

dataValue2_309 OBJECT-TYPE
SYNTAX INTEGER
MAX-ACCESS read-write
STATUS current
DESCRIPTION
"Data value."
::= { dataArray2 309 }

dataValue2_310 OBJECT-TYPE
SYNTAX INTEGER
MAX-ACCESS read-write
STATUS current
DESCRIPTION
"Data value."
::= { dataArray2 310 }

dataValue2_311 OBJECT-TYPE
SYNTAX INTEGER
MAX-ACCESS read-write
STATUS current
DESCRIPTION
"Data value."
::= { dataArray2 311 }

dataValue2_312 OBJECT-TYPE
SYNTAX INTEGER
MAX-ACCESS read-write
STATUS current
DESCRIPTION
"Data value."
::= { dataArray2 312 }

dataValue2_313 OBJECT-TYPE
SYNTAX INTEGER
MAX-ACCESS read-write
STATUS current
DESCRIPTION
"Data value."
::= { dataArray2 313 }

dataValue2_314 OBJECT-TYPE
SYNTAX INTEGER
MAX-ACCESS read-write
STATUS current
DESCRIPTION
"Data value."
::= { dataArray2 314 }

dataValue2_315 OBJECT-TYPE
SYNTAX INTEGER
MAX-ACCESS read-write
STATUS current
DESCRIPTION
"Data value."
::= { dataArray2 315 }

dataValue2_316 OBJECT-TYPE
SYNTAX INTEGER
MAX-ACCESS read-write
STATUS current
DESCRIPTION
"Data value."
::= { dataArray2 316 }

dataValue2_317 OBJECT-TYPE
SYNTAX INTEGER
MAX-ACCESS read-write
STATUS current
DESCRIPTION
"Data value."
::= { dataArray2 317 }

dataValue2_318 OBJECT-TYPE
SYNTAX INTEGER
MAX-ACCESS read-write
STATUS current
DESCRIPTION
"Data value."
::= { dataArray2 318 }

dataValue2_319 OBJECT-TYPE
SYNTAX INTEGER
MAX-ACCESS read-write
STATUS current
DESCRIPTION
"Data value."
::= { dataArray2 319 }

dataValue2_320 OBJECT-TYPE
SYNTAX INTEGER
MAX-ACCESS read-write
STATUS current
DESCRIPTION
"Data value."
::= { dataArray2 320 }

dataValue2_321 OBJECT-TYPE
SYNTAX INTEGER
MAX-ACCESS read-write
STATUS current
DESCRIPTION
"Data value."
::= { dataArray2 321 }

dataValue2_322 OBJECT-TYPE
SYNTAX INTEGER
MAX-ACCESS read-write
STATUS current
DESCRIPTION
"Data value."
::= { dataArray2 322 }

dataValue2_323 OBJECT-TYPE
SYNTAX INTEGER
MAX-ACCESS read-write
STATUS current
DESCRIPTION
"Data value."
::= { dataArray2 323 }

dataValue2_324 OBJECT-TYPE
SYNTAX INTEGER
MAX-ACCESS read-write
STATUS current
DESCRIPTION
"Data value."
::= { dataArray2 324 }

dataValue2_325 OBJECT-TYPE
SYNTAX INTEGER
MAX-ACCESS read-write
STATUS current
DESCRIPTION
"Data value."
::= { dataArray2 325 }

dataValue2_326 OBJECT-TYPE
SYNTAX INTEGER
MAX-ACCESS read-write
STATUS current
DESCRIPTION
"Data value."
::= { dataArray2 326 }

dataValue2_327 OBJECT-TYPE
SYNTAX INTEGER
MAX-ACCESS read-write
STATUS current
DESCRIPTION
"Data value."
::= { dataArray2 327 }

dataValue2_328 OBJECT-TYPE
SYNTAX INTEGER
MAX-ACCESS read-write
STATUS current
DESCRIPTION
"Data value."
::= { dataArray2 328 }

dataValue2_329 OBJECT-TYPE
SYNTAX INTEGER
MAX-ACCESS read-write
STATUS current
DESCRIPTION
"Data value."
::= { dataArray2 329 }

dataValue2_330 OBJECT-TYPE
SYNTAX INTEGER
MAX-ACCESS read-write
STATUS current
DESCRIPTION
"Data value."
::= { dataArray2 330 }

dataValue2_331 OBJECT-TYPE
SYNTAX INTEGER
MAX-ACCESS read-write
STATUS current
DESCRIPTION
"Data value."
::= { dataArray2 331 }

dataValue2_332 OBJECT-TYPE
SYNTAX INTEGER
MAX-ACCESS read-write
STATUS current
DESCRIPTION
"Data value."
::= { dataArray2 332 }

dataValue2_333 OBJECT-TYPE
SYNTAX INTEGER
MAX-ACCESS read-write
STATUS current
DESCRIPTION
"Data value."
::= { dataArray2 333 }

dataValue2_334 OBJECT-TYPE
SYNTAX INTEGER
MAX-ACCESS read-write
STATUS current
DESCRIPTION
"Data value."
::= { dataArray2 334 }

dataValue2_335 OBJECT-TYPE
SYNTAX INTEGER
MAX-ACCESS read-write
STATUS current
DESCRIPTION
"Data value."
::= { dataArray2 335 }

dataValue2_336 OBJECT-TYPE
SYNTAX INTEGER
MAX-ACCESS read-write
STATUS current
DESCRIPTION
"Data value."
::= { dataArray2 336 }

dataValue2_337 OBJECT-TYPE
SYNTAX INTEGER
MAX-ACCESS read-write
STATUS current
DESCRIPTION
"Data value."
::= { dataArray2 337 }

dataValue2_338 OBJECT-TYPE
SYNTAX INTEGER
MAX-ACCESS read-write
STATUS current
DESCRIPTION
"Data value."
::= { dataArray2 338 }

dataValue2_339 OBJECT-TYPE
SYNTAX INTEGER
MAX-ACCESS read-write
STATUS current
DESCRIPTION
"Data value."
::= { dataArray2 339 }

dataValue2_340 OBJECT-TYPE
SYNTAX INTEGER
MAX-ACCESS read-write
STATUS current
DESCRIPTION
"Data value."
::= { dataArray2 340 }

dataValue2_341 OBJECT-TYPE
SYNTAX INTEGER
MAX-ACCESS read-write
STATUS current
DESCRIPTION
"Data value."
::= { dataArray2 341 }

dataValue2_342 OBJECT-TYPE
SYNTAX INTEGER
MAX-ACCESS read-write
STATUS current
DESCRIPTION
"Data value."
::= { dataArray2 342 }

dataValue2_343 OBJECT-TYPE
SYNTAX INTEGER
MAX-ACCESS read-write
STATUS current
DESCRIPTION
"Data value."
::= { dataArray2 343 }

dataValue2_344 OBJECT-TYPE
SYNTAX INTEGER
MAX-ACCESS read-write
STATUS current
DESCRIPTION
"Data value."
::= { dataArray2 344 }

dataValue2_345 OBJECT-TYPE
SYNTAX INTEGER
MAX-ACCESS read-write
STATUS current
DESCRIPTION
"Data value."
::= { dataArray2 345 }

dataValue2_346 OBJECT-TYPE
SYNTAX INTEGER
MAX-ACCESS read-write
STATUS current
DESCRIPTION
"Data value."
::= { dataArray2 346 }

dataValue2_347 OBJECT-TYPE
SYNTAX INTEGER
MAX-ACCESS read-write
STATUS current
DESCRIPTION
"Data value."
::= { dataArray2 347 }

dataValue2_348 OBJECT-TYPE
SYNTAX INTEGER
MAX-ACCESS read-write
STATUS current
DESCRIPTION
"Data value."
::= { dataArray2 348 }

dataValue2_349 OBJECT-TYPE
SYNTAX INTEGER
MAX-ACCESS read-write
STATUS current
DESCRIPTION
"Data value."
::= { dataArray2 349 }

dataValue2_350 OBJECT-TYPE
SYNTAX INTEGER
MAX-ACCESS read-write
STATUS current
DESCRIPTION
"Data value."
::= { dataArray2 350 }

dataValue2_351 OBJECT-TYPE
SYNTAX INTEGER
MAX-ACCESS read-write
STATUS current
DESCRIPTION
"Data value."
::= { dataArray2 351 }

dataValue2_352 OBJECT-TYPE
SYNTAX INTEGER
MAX-ACCESS read-write
STATUS current
DESCRIPTION
"Data value."
::= { dataArray2 352 }

dataValue2_353 OBJECT-TYPE
SYNTAX INTEGER
MAX-ACCESS read-write
STATUS current
DESCRIPTION
"Data value."
::= { dataArray2 353 }

dataValue2_354 OBJECT-TYPE
SYNTAX INTEGER
MAX-ACCESS read-write
STATUS current
DESCRIPTION
"Data value."
::= { dataArray2 354 }

dataValue2_355 OBJECT-TYPE
SYNTAX INTEGER
MAX-ACCESS read-write
STATUS current
DESCRIPTION
"Data value."
::= { dataArray2 355 }

dataValue2_356 OBJECT-TYPE
SYNTAX INTEGER
MAX-ACCESS read-write
STATUS current
DESCRIPTION
"Data value."
::= { dataArray2 356 }

dataValue2_357 OBJECT-TYPE
SYNTAX INTEGER
MAX-ACCESS read-write
STATUS current
DESCRIPTION
"Data value."
::= { dataArray2 357 }

dataValue2_358 OBJECT-TYPE
SYNTAX INTEGER
MAX-ACCESS read-write
STATUS current
DESCRIPTION
"Data value."
::= { dataArray2 358 }

dataValue2_359 OBJECT-TYPE
SYNTAX INTEGER
MAX-ACCESS read-write
STATUS current
DESCRIPTION
"Data value."
::= { dataArray2 359 }

dataValue2_360 OBJECT-TYPE
SYNTAX INTEGER
MAX-ACCESS read-write
STATUS current
DESCRIPTION
"Data value."
::= { dataArray2 360 }

dataValue2_361 OBJECT-TYPE
SYNTAX INTEGER
MAX-ACCESS read-write
STATUS current
DESCRIPTION
"Data value."
::= { dataArray2 361 }

dataValue2_362 OBJECT-TYPE
SYNTAX INTEGER
MAX-ACCESS read-write
STATUS current
DESCRIPTION
"Data value."
::= { dataArray2 362 }

dataValue2_363 OBJECT-TYPE
SYNTAX INTEGER
MAX-ACCESS read-write
STATUS current
DESCRIPTION
"Data value."
::= { dataArray2 363 }

dataValue2_364 OBJECT-TYPE
SYNTAX INTEGER
MAX-ACCESS read-write
STATUS current
DESCRIPTION
"Data value."
::= { dataArray2 364 }

dataValue2_365 OBJECT-TYPE
SYNTAX INTEGER
MAX-ACCESS read-write
STATUS current
DESCRIPTION
"Data value."
::= { dataArray2 365 }

dataValue2_366 OBJECT-TYPE
SYNTAX INTEGER
MAX-ACCESS read-write
STATUS current
DESCRIPTION
"Data value."
::= { dataArray2 366 }

dataValue2_367 OBJECT-TYPE
SYNTAX INTEGER
MAX-ACCESS read-write
STATUS current
DESCRIPTION
"Data value."
::= { dataArray2 367 }

dataValue2_368 OBJECT-TYPE
SYNTAX INTEGER
MAX-ACCESS read-write
STATUS current
DESCRIPTION
"Data value."
::= { dataArray2 368 }

dataValue2_369 OBJECT-TYPE
SYNTAX INTEGER
MAX-ACCESS read-write
STATUS current
DESCRIPTION
"Data value."
::= { dataArray2 369 }

dataValue2_370 OBJECT-TYPE
SYNTAX INTEGER
MAX-ACCESS read-write
STATUS current
DESCRIPTION
"Data value."
::= { dataArray2 370 }

dataValue2_371 OBJECT-TYPE
SYNTAX INTEGER
MAX-ACCESS read-write
STATUS current
DESCRIPTION
"Data value."
::= { dataArray2 371 }

dataValue2_372 OBJECT-TYPE
SYNTAX INTEGER
MAX-ACCESS read-write
STATUS current
DESCRIPTION
"Data value."
::= { dataArray2 372 }

dataValue2_373 OBJECT-TYPE
SYNTAX INTEGER
MAX-ACCESS read-write
STATUS current
DESCRIPTION
"Data value."
::= { dataArray2 373 }

dataValue2_374 OBJECT-TYPE
SYNTAX INTEGER
MAX-ACCESS read-write
STATUS current
DESCRIPTION
"Data value."
::= { dataArray2 374 }

dataValue2_375 OBJECT-TYPE
SYNTAX INTEGER
MAX-ACCESS read-write
STATUS current
DESCRIPTION
"Data value."
::= { dataArray2 375 }

dataValue2_376 OBJECT-TYPE
SYNTAX INTEGER
MAX-ACCESS read-write
STATUS current
DESCRIPTION
"Data value."
::= { dataArray2 376 }

dataValue2_377 OBJECT-TYPE
SYNTAX INTEGER
MAX-ACCESS read-write
STATUS current
DESCRIPTION
"Data value."
::= { dataArray2 377 }

dataValue2_378 OBJECT-TYPE
SYNTAX INTEGER
MAX-ACCESS read-write
STATUS current
DESCRIPTION
"Data value."
::= { dataArray2 378 }

dataValue2_379 OBJECT-TYPE
SYNTAX INTEGER
MAX-ACCESS read-write
STATUS current
DESCRIPTION
"Data value."
::= { dataArray2 379 }

dataValue2_380 OBJECT-TYPE
SYNTAX INTEGER
MAX-ACCESS read-write
STATUS current
DESCRIPTION
"Data value."
::= { dataArray2 380 }

dataValue2_381 OBJECT-TYPE
SYNTAX INTEGER
MAX-ACCESS read-write
STATUS current
DESCRIPTION
"Data value."
::= { dataArray2 381 }

dataValue2_382 OBJECT-TYPE
SYNTAX INTEGER
MAX-ACCESS read-write
STATUS current
DESCRIPTION
"Data value."
::= { dataArray2 382 }

dataValue2_383 OBJECT-TYPE
SYNTAX INTEGER
MAX-ACCESS read-write
STATUS current
DESCRIPTION
"Data value."
::= { dataArray2 383 }

dataValue2_384 OBJECT-TYPE
SYNTAX INTEGER
MAX-ACCESS read-write
STATUS current
DESCRIPTION
"Data value."
::= { dataArray2 384 }

dataValue2_385 OBJECT-TYPE
SYNTAX INTEGER
MAX-ACCESS read-write
STATUS current
DESCRIPTION
"Data value."
::= { dataArray2 385 }

dataValue2_386 OBJECT-TYPE
SYNTAX INTEGER
MAX-ACCESS read-write
STATUS current
DESCRIPTION
"Data value."
::= { dataArray2 386 }

dataValue2_387 OBJECT-TYPE
SYNTAX INTEGER
MAX-ACCESS read-write
STATUS current
DESCRIPTION
"Data value."
::= { dataArray2 387 }

dataValue2_388 OBJECT-TYPE
SYNTAX INTEGER
MAX-ACCESS read-write
STATUS current
DESCRIPTION
"Data value."
::= { dataArray2 388 }

dataValue2_389 OBJECT-TYPE
SYNTAX INTEGER
MAX-ACCESS read-write
STATUS current
DESCRIPTION
"Data value."
::= { dataArray2 389 }

dataValue2_390 OBJECT-TYPE
SYNTAX INTEGER
MAX-ACCESS read-write
STATUS current
DESCRIPTION
"Data value."
::= { dataArray2 390 }

dataValue2_391 OBJECT-TYPE
SYNTAX INTEGER
MAX-ACCESS read-write
STATUS current
DESCRIPTION
"Data value."
::= { dataArray2 391 }

dataValue2_392 OBJECT-TYPE
SYNTAX INTEGER
MAX-ACCESS read-write
STATUS current
DESCRIPTION
"Data value."
::= { dataArray2 392 }

dataValue2_393 OBJECT-TYPE
SYNTAX INTEGER
MAX-ACCESS read-write
STATUS current
DESCRIPTION
"Data value."
::= { dataArray2 393 }

dataValue2_394 OBJECT-TYPE
SYNTAX INTEGER
MAX-ACCESS read-write
STATUS current
DESCRIPTION
"Data value."
::= { dataArray2 394 }

dataValue2_395 OBJECT-TYPE
SYNTAX INTEGER
MAX-ACCESS read-write
STATUS current
DESCRIPTION
"Data value."
::= { dataArray2 395 }

dataValue2_396 OBJECT-TYPE
SYNTAX INTEGER
MAX-ACCESS read-write
STATUS current
DESCRIPTION
"Data value."
::= { dataArray2 396 }

dataValue2_397 OBJECT-TYPE
SYNTAX INTEGER
MAX-ACCESS read-write
STATUS current
DESCRIPTION
"Data value."
::= { dataArray2 397 }

dataValue2_398 OBJECT-TYPE
SYNTAX INTEGER
MAX-ACCESS read-write
STATUS current
DESCRIPTION
"Data value."
::= { dataArray2 398 }

dataValue2_399 OBJECT-TYPE
SYNTAX INTEGER
MAX-ACCESS read-write
STATUS current
DESCRIPTION
"Data value."
::= { dataArray2 399 }

dataArray3 OBJECT IDENTIFIER ::= { cc08255400_v1_00a 3 }

dataValue3_0 OBJECT-TYPE
SYNTAX INTEGER
MAX-ACCESS read-write
STATUS current
DESCRIPTION
"Data value."
::= { dataArray3 0 }

dataValue3_1 OBJECT-TYPE
SYNTAX INTEGER
MAX-ACCESS read-write
STATUS current
DESCRIPTION
"Data value."
::= { dataArray3 1 }

dataValue3_2 OBJECT-TYPE
SYNTAX INTEGER
MAX-ACCESS read-write
STATUS current
DESCRIPTION
"Data value."
::= { dataArray3 2 }

dataValue3_3 OBJECT-TYPE
SYNTAX INTEGER
MAX-ACCESS read-write
STATUS current
DESCRIPTION
"Data value."
::= { dataArray3 3 }

dataValue3_4 OBJECT-TYPE
SYNTAX INTEGER
MAX-ACCESS read-write
STATUS current
DESCRIPTION
"Data value."
::= { dataArray3 4 }

dataValue3_5 OBJECT-TYPE
SYNTAX INTEGER
MAX-ACCESS read-write
STATUS current
DESCRIPTION
"Data value."
::= { dataArray3 5 }

dataValue3_6 OBJECT-TYPE
SYNTAX INTEGER
MAX-ACCESS read-write
STATUS current
DESCRIPTION
"Data value."
::= { dataArray3 6 }

dataValue3_7 OBJECT-TYPE
SYNTAX INTEGER
MAX-ACCESS read-write
STATUS current
DESCRIPTION
"Data value."
::= { dataArray3 7 }

dataValue3_8 OBJECT-TYPE
SYNTAX INTEGER
MAX-ACCESS read-write
STATUS current
DESCRIPTION
"Data value."
::= { dataArray3 8 }

dataValue3_9 OBJECT-TYPE
SYNTAX INTEGER
MAX-ACCESS read-write
STATUS current
DESCRIPTION
"Data value."
::= { dataArray3 9 }

dataValue3_10 OBJECT-TYPE
SYNTAX INTEGER
MAX-ACCESS read-write
STATUS current
DESCRIPTION
"Data value."
::= { dataArray3 10 }

dataValue3_11 OBJECT-TYPE
SYNTAX INTEGER
MAX-ACCESS read-write
STATUS current
DESCRIPTION
"Data value."
::= { dataArray3 11 }

dataValue3_12 OBJECT-TYPE
SYNTAX INTEGER
MAX-ACCESS read-write
STATUS current
DESCRIPTION
"Data value."
::= { dataArray3 12 }

dataValue3_13 OBJECT-TYPE
SYNTAX INTEGER
MAX-ACCESS read-write
STATUS current
DESCRIPTION
"Data value."
::= { dataArray3 13 }

dataValue3_14 OBJECT-TYPE
SYNTAX INTEGER
MAX-ACCESS read-write
STATUS current
DESCRIPTION
"Data value."
::= { dataArray3 14 }

dataValue3_15 OBJECT-TYPE
SYNTAX INTEGER
MAX-ACCESS read-write
STATUS current
DESCRIPTION
"Data value."
::= { dataArray3 15 }

dataValue3_16 OBJECT-TYPE
SYNTAX INTEGER
MAX-ACCESS read-write
STATUS current
DESCRIPTION
"Data value."
::= { dataArray3 16 }

dataValue3_17 OBJECT-TYPE
SYNTAX INTEGER
MAX-ACCESS read-write
STATUS current
DESCRIPTION
"Data value."
::= { dataArray3 17 }

dataValue3_18 OBJECT-TYPE
SYNTAX INTEGER
MAX-ACCESS read-write
STATUS current
DESCRIPTION
"Data value."
::= { dataArray3 18 }

dataValue3_19 OBJECT-TYPE
SYNTAX INTEGER
MAX-ACCESS read-write
STATUS current
DESCRIPTION
"Data value."
::= { dataArray3 19 }

dataValue3_20 OBJECT-TYPE
SYNTAX INTEGER
MAX-ACCESS read-write
STATUS current
DESCRIPTION
"Data value."
::= { dataArray3 20 }

dataValue3_21 OBJECT-TYPE
SYNTAX INTEGER
MAX-ACCESS read-write
STATUS current
DESCRIPTION
"Data value."
::= { dataArray3 21 }

dataValue3_22 OBJECT-TYPE
SYNTAX INTEGER
MAX-ACCESS read-write
STATUS current
DESCRIPTION
"Data value."
::= { dataArray3 22 }

dataValue3_23 OBJECT-TYPE
SYNTAX INTEGER
MAX-ACCESS read-write
STATUS current
DESCRIPTION
"Data value."
::= { dataArray3 23 }

dataValue3_24 OBJECT-TYPE
SYNTAX INTEGER
MAX-ACCESS read-write
STATUS current
DESCRIPTION
"Data value."
::= { dataArray3 24 }

dataValue3_25 OBJECT-TYPE
SYNTAX INTEGER
MAX-ACCESS read-write
STATUS current
DESCRIPTION
"Data value."
::= { dataArray3 25 }

dataValue3_26 OBJECT-TYPE
SYNTAX INTEGER
MAX-ACCESS read-write
STATUS current
DESCRIPTION
"Data value."
::= { dataArray3 26 }

dataValue3_27 OBJECT-TYPE
SYNTAX INTEGER
MAX-ACCESS read-write
STATUS current
DESCRIPTION
"Data value."
::= { dataArray3 27 }

dataValue3_28 OBJECT-TYPE
SYNTAX INTEGER
MAX-ACCESS read-write
STATUS current
DESCRIPTION
"Data value."
::= { dataArray3 28 }

dataValue3_29 OBJECT-TYPE
SYNTAX INTEGER
MAX-ACCESS read-write
STATUS current
DESCRIPTION
"Data value."
::= { dataArray3 29 }

dataValue3_30 OBJECT-TYPE
SYNTAX INTEGER
MAX-ACCESS read-write
STATUS current
DESCRIPTION
"Data value."
::= { dataArray3 30 }

dataValue3_31 OBJECT-TYPE
SYNTAX INTEGER
MAX-ACCESS read-write
STATUS current
DESCRIPTION
"Data value."
::= { dataArray3 31 }

dataValue3_32 OBJECT-TYPE
SYNTAX INTEGER
MAX-ACCESS read-write
STATUS current
DESCRIPTION
"Data value."
::= { dataArray3 32 }

dataValue3_33 OBJECT-TYPE
SYNTAX INTEGER
MAX-ACCESS read-write
STATUS current
DESCRIPTION
"Data value."
::= { dataArray3 33 }

dataValue3_34 OBJECT-TYPE
SYNTAX INTEGER
MAX-ACCESS read-write
STATUS current
DESCRIPTION
"Data value."
::= { dataArray3 34 }

dataValue3_35 OBJECT-TYPE
SYNTAX INTEGER
MAX-ACCESS read-write
STATUS current
DESCRIPTION
"Data value."
::= { dataArray3 35 }

dataValue3_36 OBJECT-TYPE
SYNTAX INTEGER
MAX-ACCESS read-write
STATUS current
DESCRIPTION
"Data value."
::= { dataArray3 36 }

dataValue3_37 OBJECT-TYPE
SYNTAX INTEGER
MAX-ACCESS read-write
STATUS current
DESCRIPTION
"Data value."
::= { dataArray3 37 }

dataValue3_38 OBJECT-TYPE
SYNTAX INTEGER
MAX-ACCESS read-write
STATUS current
DESCRIPTION
"Data value."
::= { dataArray3 38 }

dataValue3_39 OBJECT-TYPE
SYNTAX INTEGER
MAX-ACCESS read-write
STATUS current
DESCRIPTION
"Data value."
::= { dataArray3 39 }

dataValue3_40 OBJECT-TYPE
SYNTAX INTEGER
MAX-ACCESS read-write
STATUS current
DESCRIPTION
"Data value."
::= { dataArray3 40 }

dataValue3_41 OBJECT-TYPE
SYNTAX INTEGER
MAX-ACCESS read-write
STATUS current
DESCRIPTION
"Data value."
::= { dataArray3 41 }

dataValue3_42 OBJECT-TYPE
SYNTAX INTEGER
MAX-ACCESS read-write
STATUS current
DESCRIPTION
"Data value."
::= { dataArray3 42 }

dataValue3_43 OBJECT-TYPE
SYNTAX INTEGER
MAX-ACCESS read-write
STATUS current
DESCRIPTION
"Data value."
::= { dataArray3 43 }

dataValue3_44 OBJECT-TYPE
SYNTAX INTEGER
MAX-ACCESS read-write
STATUS current
DESCRIPTION
"Data value."
::= { dataArray3 44 }

dataValue3_45 OBJECT-TYPE
SYNTAX INTEGER
MAX-ACCESS read-write
STATUS current
DESCRIPTION
"Data value."
::= { dataArray3 45 }

dataValue3_46 OBJECT-TYPE
SYNTAX INTEGER
MAX-ACCESS read-write
STATUS current
DESCRIPTION
"Data value."
::= { dataArray3 46 }

dataValue3_47 OBJECT-TYPE
SYNTAX INTEGER
MAX-ACCESS read-write
STATUS current
DESCRIPTION
"Data value."
::= { dataArray3 47 }

dataValue3_48 OBJECT-TYPE
SYNTAX INTEGER
MAX-ACCESS read-write
STATUS current
DESCRIPTION
"Data value."
::= { dataArray3 48 }

dataValue3_49 OBJECT-TYPE
SYNTAX INTEGER
MAX-ACCESS read-write
STATUS current
DESCRIPTION
"Data value."
::= { dataArray3 49 }

dataValue3_50 OBJECT-TYPE
SYNTAX INTEGER
MAX-ACCESS read-write
STATUS current
DESCRIPTION
"Data value."
::= { dataArray3 50 }

dataValue3_51 OBJECT-TYPE
SYNTAX INTEGER
MAX-ACCESS read-write
STATUS current
DESCRIPTION
"Data value."
::= { dataArray3 51 }

dataValue3_52 OBJECT-TYPE
SYNTAX INTEGER
MAX-ACCESS read-write
STATUS current
DESCRIPTION
"Data value."
::= { dataArray3 52 }

dataValue3_53 OBJECT-TYPE
SYNTAX INTEGER
MAX-ACCESS read-write
STATUS current
DESCRIPTION
"Data value."
::= { dataArray3 53 }

dataValue3_54 OBJECT-TYPE
SYNTAX INTEGER
MAX-ACCESS read-write
STATUS current
DESCRIPTION
"Data value."
::= { dataArray3 54 }

dataValue3_55 OBJECT-TYPE
SYNTAX INTEGER
MAX-ACCESS read-write
STATUS current
DESCRIPTION
"Data value."
::= { dataArray3 55 }

dataValue3_56 OBJECT-TYPE
SYNTAX INTEGER
MAX-ACCESS read-write
STATUS current
DESCRIPTION
"Data value."
::= { dataArray3 56 }

dataValue3_57 OBJECT-TYPE
SYNTAX INTEGER
MAX-ACCESS read-write
STATUS current
DESCRIPTION
"Data value."
::= { dataArray3 57 }

dataValue3_58 OBJECT-TYPE
SYNTAX INTEGER
MAX-ACCESS read-write
STATUS current
DESCRIPTION
"Data value."
::= { dataArray3 58 }

dataValue3_59 OBJECT-TYPE
SYNTAX INTEGER
MAX-ACCESS read-write
STATUS current
DESCRIPTION
"Data value."
::= { dataArray3 59 }

dataValue3_60 OBJECT-TYPE
SYNTAX INTEGER
MAX-ACCESS read-write
STATUS current
DESCRIPTION
"Data value."
::= { dataArray3 60 }

dataValue3_61 OBJECT-TYPE
SYNTAX INTEGER
MAX-ACCESS read-write
STATUS current
DESCRIPTION
"Data value."
::= { dataArray3 61 }

dataValue3_62 OBJECT-TYPE
SYNTAX INTEGER
MAX-ACCESS read-write
STATUS current
DESCRIPTION
"Data value."
::= { dataArray3 62 }

dataValue3_63 OBJECT-TYPE
SYNTAX INTEGER
MAX-ACCESS read-write
STATUS current
DESCRIPTION
"Data value."
::= { dataArray3 63 }

dataValue3_64 OBJECT-TYPE
SYNTAX INTEGER
MAX-ACCESS read-write
STATUS current
DESCRIPTION
"Data value."
::= { dataArray3 64 }

dataValue3_65 OBJECT-TYPE
SYNTAX INTEGER
MAX-ACCESS read-write
STATUS current
DESCRIPTION
"Data value."
::= { dataArray3 65 }

dataValue3_66 OBJECT-TYPE
SYNTAX INTEGER
MAX-ACCESS read-write
STATUS current
DESCRIPTION
"Data value."
::= { dataArray3 66 }

dataValue3_67 OBJECT-TYPE
SYNTAX INTEGER
MAX-ACCESS read-write
STATUS current
DESCRIPTION
"Data value."
::= { dataArray3 67 }

dataValue3_68 OBJECT-TYPE
SYNTAX INTEGER
MAX-ACCESS read-write
STATUS current
DESCRIPTION
"Data value."
::= { dataArray3 68 }

dataValue3_69 OBJECT-TYPE
SYNTAX INTEGER
MAX-ACCESS read-write
STATUS current
DESCRIPTION
"Data value."
::= { dataArray3 69 }

dataValue3_70 OBJECT-TYPE
SYNTAX INTEGER
MAX-ACCESS read-write
STATUS current
DESCRIPTION
"Data value."
::= { dataArray3 70 }

dataValue3_71 OBJECT-TYPE
SYNTAX INTEGER
MAX-ACCESS read-write
STATUS current
DESCRIPTION
"Data value."
::= { dataArray3 71 }

dataValue3_72 OBJECT-TYPE
SYNTAX INTEGER
MAX-ACCESS read-write
STATUS current
DESCRIPTION
"Data value."
::= { dataArray3 72 }

dataValue3_73 OBJECT-TYPE
SYNTAX INTEGER
MAX-ACCESS read-write
STATUS current
DESCRIPTION
"Data value."
::= { dataArray3 73 }

dataValue3_74 OBJECT-TYPE
SYNTAX INTEGER
MAX-ACCESS read-write
STATUS current
DESCRIPTION
"Data value."
::= { dataArray3 74 }

dataValue3_75 OBJECT-TYPE
SYNTAX INTEGER
MAX-ACCESS read-write
STATUS current
DESCRIPTION
"Data value."
::= { dataArray3 75 }

dataValue3_76 OBJECT-TYPE
SYNTAX INTEGER
MAX-ACCESS read-write
STATUS current
DESCRIPTION
"Data value."
::= { dataArray3 76 }

dataValue3_77 OBJECT-TYPE
SYNTAX INTEGER
MAX-ACCESS read-write
STATUS current
DESCRIPTION
"Data value."
::= { dataArray3 77 }

dataValue3_78 OBJECT-TYPE
SYNTAX INTEGER
MAX-ACCESS read-write
STATUS current
DESCRIPTION
"Data value."
::= { dataArray3 78 }

dataValue3_79 OBJECT-TYPE
SYNTAX INTEGER
MAX-ACCESS read-write
STATUS current
DESCRIPTION
"Data value."
::= { dataArray3 79 }

dataValue3_80 OBJECT-TYPE
SYNTAX INTEGER
MAX-ACCESS read-write
STATUS current
DESCRIPTION
"Data value."
::= { dataArray3 80 }

dataValue3_81 OBJECT-TYPE
SYNTAX INTEGER
MAX-ACCESS read-write
STATUS current
DESCRIPTION
"Data value."
::= { dataArray3 81 }

dataValue3_82 OBJECT-TYPE
SYNTAX INTEGER
MAX-ACCESS read-write
STATUS current
DESCRIPTION
"Data value."
::= { dataArray3 82 }

dataValue3_83 OBJECT-TYPE
SYNTAX INTEGER
MAX-ACCESS read-write
STATUS current
DESCRIPTION
"Data value."
::= { dataArray3 83 }

dataValue3_84 OBJECT-TYPE
SYNTAX INTEGER
MAX-ACCESS read-write
STATUS current
DESCRIPTION
"Data value."
::= { dataArray3 84 }

dataValue3_85 OBJECT-TYPE
SYNTAX INTEGER
MAX-ACCESS read-write
STATUS current
DESCRIPTION
"Data value."
::= { dataArray3 85 }

dataValue3_86 OBJECT-TYPE
SYNTAX INTEGER
MAX-ACCESS read-write
STATUS current
DESCRIPTION
"Data value."
::= { dataArray3 86 }

dataValue3_87 OBJECT-TYPE
SYNTAX INTEGER
MAX-ACCESS read-write
STATUS current
DESCRIPTION
"Data value."
::= { dataArray3 87 }

dataValue3_88 OBJECT-TYPE
SYNTAX INTEGER
MAX-ACCESS read-write
STATUS current
DESCRIPTION
"Data value."
::= { dataArray3 88 }

dataValue3_89 OBJECT-TYPE
SYNTAX INTEGER
MAX-ACCESS read-write
STATUS current
DESCRIPTION
"Data value."
::= { dataArray3 89 }

dataValue3_90 OBJECT-TYPE
SYNTAX INTEGER
MAX-ACCESS read-write
STATUS current
DESCRIPTION
"Data value."
::= { dataArray3 90 }

dataValue3_91 OBJECT-TYPE
SYNTAX INTEGER
MAX-ACCESS read-write
STATUS current
DESCRIPTION
"Data value."
::= { dataArray3 91 }

dataValue3_92 OBJECT-TYPE
SYNTAX INTEGER
MAX-ACCESS read-write
STATUS current
DESCRIPTION
"Data value."
::= { dataArray3 92 }

dataValue3_93 OBJECT-TYPE
SYNTAX INTEGER
MAX-ACCESS read-write
STATUS current
DESCRIPTION
"Data value."
::= { dataArray3 93 }

dataValue3_94 OBJECT-TYPE
SYNTAX INTEGER
MAX-ACCESS read-write
STATUS current
DESCRIPTION
"Data value."
::= { dataArray3 94 }

dataValue3_95 OBJECT-TYPE
SYNTAX INTEGER
MAX-ACCESS read-write
STATUS current
DESCRIPTION
"Data value."
::= { dataArray3 95 }

dataValue3_96 OBJECT-TYPE
SYNTAX INTEGER
MAX-ACCESS read-write
STATUS current
DESCRIPTION
"Data value."
::= { dataArray3 96 }

dataValue3_97 OBJECT-TYPE
SYNTAX INTEGER
MAX-ACCESS read-write
STATUS current
DESCRIPTION
"Data value."
::= { dataArray3 97 }

dataValue3_98 OBJECT-TYPE
SYNTAX INTEGER
MAX-ACCESS read-write
STATUS current
DESCRIPTION
"Data value."
::= { dataArray3 98 }

dataValue3_99 OBJECT-TYPE
SYNTAX INTEGER
MAX-ACCESS read-write
STATUS current
DESCRIPTION
"Data value."
::= { dataArray3 99 }

dataValue3_100 OBJECT-TYPE
SYNTAX INTEGER
MAX-ACCESS read-write
STATUS current
DESCRIPTION
"Data value."
::= { dataArray3 100 }

dataValue3_101 OBJECT-TYPE
SYNTAX INTEGER
MAX-ACCESS read-write
STATUS current
DESCRIPTION
"Data value."
::= { dataArray3 101 }

dataValue3_102 OBJECT-TYPE
SYNTAX INTEGER
MAX-ACCESS read-write
STATUS current
DESCRIPTION
"Data value."
::= { dataArray3 102 }

dataValue3_103 OBJECT-TYPE
SYNTAX INTEGER
MAX-ACCESS read-write
STATUS current
DESCRIPTION
"Data value."
::= { dataArray3 103 }

dataValue3_104 OBJECT-TYPE
SYNTAX INTEGER
MAX-ACCESS read-write
STATUS current
DESCRIPTION
"Data value."
::= { dataArray3 104 }

dataValue3_105 OBJECT-TYPE
SYNTAX INTEGER
MAX-ACCESS read-write
STATUS current
DESCRIPTION
"Data value."
::= { dataArray3 105 }

dataValue3_106 OBJECT-TYPE
SYNTAX INTEGER
MAX-ACCESS read-write
STATUS current
DESCRIPTION
"Data value."
::= { dataArray3 106 }

dataValue3_107 OBJECT-TYPE
SYNTAX INTEGER
MAX-ACCESS read-write
STATUS current
DESCRIPTION
"Data value."
::= { dataArray3 107 }

dataValue3_108 OBJECT-TYPE
SYNTAX INTEGER
MAX-ACCESS read-write
STATUS current
DESCRIPTION
"Data value."
::= { dataArray3 108 }

dataValue3_109 OBJECT-TYPE
SYNTAX INTEGER
MAX-ACCESS read-write
STATUS current
DESCRIPTION
"Data value."
::= { dataArray3 109 }

dataValue3_110 OBJECT-TYPE
SYNTAX INTEGER
MAX-ACCESS read-write
STATUS current
DESCRIPTION
"Data value."
::= { dataArray3 110 }

dataValue3_111 OBJECT-TYPE
SYNTAX INTEGER
MAX-ACCESS read-write
STATUS current
DESCRIPTION
"Data value."
::= { dataArray3 111 }

dataValue3_112 OBJECT-TYPE
SYNTAX INTEGER
MAX-ACCESS read-write
STATUS current
DESCRIPTION
"Data value."
::= { dataArray3 112 }

dataValue3_113 OBJECT-TYPE
SYNTAX INTEGER
MAX-ACCESS read-write
STATUS current
DESCRIPTION
"Data value."
::= { dataArray3 113 }

dataValue3_114 OBJECT-TYPE
SYNTAX INTEGER
MAX-ACCESS read-write
STATUS current
DESCRIPTION
"Data value."
::= { dataArray3 114 }

dataValue3_115 OBJECT-TYPE
SYNTAX INTEGER
MAX-ACCESS read-write
STATUS current
DESCRIPTION
"Data value."
::= { dataArray3 115 }

dataValue3_116 OBJECT-TYPE
SYNTAX INTEGER
MAX-ACCESS read-write
STATUS current
DESCRIPTION
"Data value."
::= { dataArray3 116 }

dataValue3_117 OBJECT-TYPE
SYNTAX INTEGER
MAX-ACCESS read-write
STATUS current
DESCRIPTION
"Data value."
::= { dataArray3 117 }

dataValue3_118 OBJECT-TYPE
SYNTAX INTEGER
MAX-ACCESS read-write
STATUS current
DESCRIPTION
"Data value."
::= { dataArray3 118 }

dataValue3_119 OBJECT-TYPE
SYNTAX INTEGER
MAX-ACCESS read-write
STATUS current
DESCRIPTION
"Data value."
::= { dataArray3 119 }

dataValue3_120 OBJECT-TYPE
SYNTAX INTEGER
MAX-ACCESS read-write
STATUS current
DESCRIPTION
"Data value."
::= { dataArray3 120 }

dataValue3_121 OBJECT-TYPE
SYNTAX INTEGER
MAX-ACCESS read-write
STATUS current
DESCRIPTION
"Data value."
::= { dataArray3 121 }

dataValue3_122 OBJECT-TYPE
SYNTAX INTEGER
MAX-ACCESS read-write
STATUS current
DESCRIPTION
"Data value."
::= { dataArray3 122 }

dataValue3_123 OBJECT-TYPE
SYNTAX INTEGER
MAX-ACCESS read-write
STATUS current
DESCRIPTION
"Data value."
::= { dataArray3 123 }

dataValue3_124 OBJECT-TYPE
SYNTAX INTEGER
MAX-ACCESS read-write
STATUS current
DESCRIPTION
"Data value."
::= { dataArray3 124 }

dataValue3_125 OBJECT-TYPE
SYNTAX INTEGER
MAX-ACCESS read-write
STATUS current
DESCRIPTION
"Data value."
::= { dataArray3 125 }

dataValue3_126 OBJECT-TYPE
SYNTAX INTEGER
MAX-ACCESS read-write
STATUS current
DESCRIPTION
"Data value."
::= { dataArray3 126 }

dataValue3_127 OBJECT-TYPE
SYNTAX INTEGER
MAX-ACCESS read-write
STATUS current
DESCRIPTION
"Data value."
::= { dataArray3 127 }

dataValue3_128 OBJECT-TYPE
SYNTAX INTEGER
MAX-ACCESS read-write
STATUS current
DESCRIPTION
"Data value."
::= { dataArray3 128 }

dataValue3_129 OBJECT-TYPE
SYNTAX INTEGER
MAX-ACCESS read-write
STATUS current
DESCRIPTION
"Data value."
::= { dataArray3 129 }

dataValue3_130 OBJECT-TYPE
SYNTAX INTEGER
MAX-ACCESS read-write
STATUS current
DESCRIPTION
"Data value."
::= { dataArray3 130 }

dataValue3_131 OBJECT-TYPE
SYNTAX INTEGER
MAX-ACCESS read-write
STATUS current
DESCRIPTION
"Data value."
::= { dataArray3 131 }

dataValue3_132 OBJECT-TYPE
SYNTAX INTEGER
MAX-ACCESS read-write
STATUS current
DESCRIPTION
"Data value."
::= { dataArray3 132 }

dataValue3_133 OBJECT-TYPE
SYNTAX INTEGER
MAX-ACCESS read-write
STATUS current
DESCRIPTION
"Data value."
::= { dataArray3 133 }

dataValue3_134 OBJECT-TYPE
SYNTAX INTEGER
MAX-ACCESS read-write
STATUS current
DESCRIPTION
"Data value."
::= { dataArray3 134 }

dataValue3_135 OBJECT-TYPE
SYNTAX INTEGER
MAX-ACCESS read-write
STATUS current
DESCRIPTION
"Data value."
::= { dataArray3 135 }

dataValue3_136 OBJECT-TYPE
SYNTAX INTEGER
MAX-ACCESS read-write
STATUS current
DESCRIPTION
"Data value."
::= { dataArray3 136 }

dataValue3_137 OBJECT-TYPE
SYNTAX INTEGER
MAX-ACCESS read-write
STATUS current
DESCRIPTION
"Data value."
::= { dataArray3 137 }

dataValue3_138 OBJECT-TYPE
SYNTAX INTEGER
MAX-ACCESS read-write
STATUS current
DESCRIPTION
"Data value."
::= { dataArray3 138 }

dataValue3_139 OBJECT-TYPE
SYNTAX INTEGER
MAX-ACCESS read-write
STATUS current
DESCRIPTION
"Data value."
::= { dataArray3 139 }

dataValue3_140 OBJECT-TYPE
SYNTAX INTEGER
MAX-ACCESS read-write
STATUS current
DESCRIPTION
"Data value."
::= { dataArray3 140 }

dataValue3_141 OBJECT-TYPE
SYNTAX INTEGER
MAX-ACCESS read-write
STATUS current
DESCRIPTION
"Data value."
::= { dataArray3 141 }

dataValue3_142 OBJECT-TYPE
SYNTAX INTEGER
MAX-ACCESS read-write
STATUS current
DESCRIPTION
"Data value."
::= { dataArray3 142 }

dataValue3_143 OBJECT-TYPE
SYNTAX INTEGER
MAX-ACCESS read-write
STATUS current
DESCRIPTION
"Data value."
::= { dataArray3 143 }

dataValue3_144 OBJECT-TYPE
SYNTAX INTEGER
MAX-ACCESS read-write
STATUS current
DESCRIPTION
"Data value."
::= { dataArray3 144 }

dataValue3_145 OBJECT-TYPE
SYNTAX INTEGER
MAX-ACCESS read-write
STATUS current
DESCRIPTION
"Data value."
::= { dataArray3 145 }

dataValue3_146 OBJECT-TYPE
SYNTAX INTEGER
MAX-ACCESS read-write
STATUS current
DESCRIPTION
"Data value."
::= { dataArray3 146 }

dataValue3_147 OBJECT-TYPE
SYNTAX INTEGER
MAX-ACCESS read-write
STATUS current
DESCRIPTION
"Data value."
::= { dataArray3 147 }

dataValue3_148 OBJECT-TYPE
SYNTAX INTEGER
MAX-ACCESS read-write
STATUS current
DESCRIPTION
"Data value."
::= { dataArray3 148 }

dataValue3_149 OBJECT-TYPE
SYNTAX INTEGER
MAX-ACCESS read-write
STATUS current
DESCRIPTION
"Data value."
::= { dataArray3 149 }

dataValue3_150 OBJECT-TYPE
SYNTAX INTEGER
MAX-ACCESS read-write
STATUS current
DESCRIPTION
"Data value."
::= { dataArray3 150 }

dataValue3_151 OBJECT-TYPE
SYNTAX INTEGER
MAX-ACCESS read-write
STATUS current
DESCRIPTION
"Data value."
::= { dataArray3 151 }

dataValue3_152 OBJECT-TYPE
SYNTAX INTEGER
MAX-ACCESS read-write
STATUS current
DESCRIPTION
"Data value."
::= { dataArray3 152 }

dataValue3_153 OBJECT-TYPE
SYNTAX INTEGER
MAX-ACCESS read-write
STATUS current
DESCRIPTION
"Data value."
::= { dataArray3 153 }

dataValue3_154 OBJECT-TYPE
SYNTAX INTEGER
MAX-ACCESS read-write
STATUS current
DESCRIPTION
"Data value."
::= { dataArray3 154 }

dataValue3_155 OBJECT-TYPE
SYNTAX INTEGER
MAX-ACCESS read-write
STATUS current
DESCRIPTION
"Data value."
::= { dataArray3 155 }

dataValue3_156 OBJECT-TYPE
SYNTAX INTEGER
MAX-ACCESS read-write
STATUS current
DESCRIPTION
"Data value."
::= { dataArray3 156 }

dataValue3_157 OBJECT-TYPE
SYNTAX INTEGER
MAX-ACCESS read-write
STATUS current
DESCRIPTION
"Data value."
::= { dataArray3 157 }

dataValue3_158 OBJECT-TYPE
SYNTAX INTEGER
MAX-ACCESS read-write
STATUS current
DESCRIPTION
"Data value."
::= { dataArray3 158 }

dataValue3_159 OBJECT-TYPE
SYNTAX INTEGER
MAX-ACCESS read-write
STATUS current
DESCRIPTION
"Data value."
::= { dataArray3 159 }

dataValue3_160 OBJECT-TYPE
SYNTAX INTEGER
MAX-ACCESS read-write
STATUS current
DESCRIPTION
"Data value."
::= { dataArray3 160 }

dataValue3_161 OBJECT-TYPE
SYNTAX INTEGER
MAX-ACCESS read-write
STATUS current
DESCRIPTION
"Data value."
::= { dataArray3 161 }

dataValue3_162 OBJECT-TYPE
SYNTAX INTEGER
MAX-ACCESS read-write
STATUS current
DESCRIPTION
"Data value."
::= { dataArray3 162 }

dataValue3_163 OBJECT-TYPE
SYNTAX INTEGER
MAX-ACCESS read-write
STATUS current
DESCRIPTION
"Data value."
::= { dataArray3 163 }

dataValue3_164 OBJECT-TYPE
SYNTAX INTEGER
MAX-ACCESS read-write
STATUS current
DESCRIPTION
"Data value."
::= { dataArray3 164 }

dataValue3_165 OBJECT-TYPE
SYNTAX INTEGER
MAX-ACCESS read-write
STATUS current
DESCRIPTION
"Data value."
::= { dataArray3 165 }

dataValue3_166 OBJECT-TYPE
SYNTAX INTEGER
MAX-ACCESS read-write
STATUS current
DESCRIPTION
"Data value."
::= { dataArray3 166 }

dataValue3_167 OBJECT-TYPE
SYNTAX INTEGER
MAX-ACCESS read-write
STATUS current
DESCRIPTION
"Data value."
::= { dataArray3 167 }

dataValue3_168 OBJECT-TYPE
SYNTAX INTEGER
MAX-ACCESS read-write
STATUS current
DESCRIPTION
"Data value."
::= { dataArray3 168 }

dataValue3_169 OBJECT-TYPE
SYNTAX INTEGER
MAX-ACCESS read-write
STATUS current
DESCRIPTION
"Data value."
::= { dataArray3 169 }

dataValue3_170 OBJECT-TYPE
SYNTAX INTEGER
MAX-ACCESS read-write
STATUS current
DESCRIPTION
"Data value."
::= { dataArray3 170 }

dataValue3_171 OBJECT-TYPE
SYNTAX INTEGER
MAX-ACCESS read-write
STATUS current
DESCRIPTION
"Data value."
::= { dataArray3 171 }

dataValue3_172 OBJECT-TYPE
SYNTAX INTEGER
MAX-ACCESS read-write
STATUS current
DESCRIPTION
"Data value."
::= { dataArray3 172 }

dataValue3_173 OBJECT-TYPE
SYNTAX INTEGER
MAX-ACCESS read-write
STATUS current
DESCRIPTION
"Data value."
::= { dataArray3 173 }

dataValue3_174 OBJECT-TYPE
SYNTAX INTEGER
MAX-ACCESS read-write
STATUS current
DESCRIPTION
"Data value."
::= { dataArray3 174 }

dataValue3_175 OBJECT-TYPE
SYNTAX INTEGER
MAX-ACCESS read-write
STATUS current
DESCRIPTION
"Data value."
::= { dataArray3 175 }

dataValue3_176 OBJECT-TYPE
SYNTAX INTEGER
MAX-ACCESS read-write
STATUS current
DESCRIPTION
"Data value."
::= { dataArray3 176 }

dataValue3_177 OBJECT-TYPE
SYNTAX INTEGER
MAX-ACCESS read-write
STATUS current
DESCRIPTION
"Data value."
::= { dataArray3 177 }

dataValue3_178 OBJECT-TYPE
SYNTAX INTEGER
MAX-ACCESS read-write
STATUS current
DESCRIPTION
"Data value."
::= { dataArray3 178 }

dataValue3_179 OBJECT-TYPE
SYNTAX INTEGER
MAX-ACCESS read-write
STATUS current
DESCRIPTION
"Data value."
::= { dataArray3 179 }

dataValue3_180 OBJECT-TYPE
SYNTAX INTEGER
MAX-ACCESS read-write
STATUS current
DESCRIPTION
"Data value."
::= { dataArray3 180 }

dataValue3_181 OBJECT-TYPE
SYNTAX INTEGER
MAX-ACCESS read-write
STATUS current
DESCRIPTION
"Data value."
::= { dataArray3 181 }

dataValue3_182 OBJECT-TYPE
SYNTAX INTEGER
MAX-ACCESS read-write
STATUS current
DESCRIPTION
"Data value."
::= { dataArray3 182 }

dataValue3_183 OBJECT-TYPE
SYNTAX INTEGER
MAX-ACCESS read-write
STATUS current
DESCRIPTION
"Data value."
::= { dataArray3 183 }

dataValue3_184 OBJECT-TYPE
SYNTAX INTEGER
MAX-ACCESS read-write
STATUS current
DESCRIPTION
"Data value."
::= { dataArray3 184 }

dataValue3_185 OBJECT-TYPE
SYNTAX INTEGER
MAX-ACCESS read-write
STATUS current
DESCRIPTION
"Data value."
::= { dataArray3 185 }

dataValue3_186 OBJECT-TYPE
SYNTAX INTEGER
MAX-ACCESS read-write
STATUS current
DESCRIPTION
"Data value."
::= { dataArray3 186 }

dataValue3_187 OBJECT-TYPE
SYNTAX INTEGER
MAX-ACCESS read-write
STATUS current
DESCRIPTION
"Data value."
::= { dataArray3 187 }

dataValue3_188 OBJECT-TYPE
SYNTAX INTEGER
MAX-ACCESS read-write
STATUS current
DESCRIPTION
"Data value."
::= { dataArray3 188 }

dataValue3_189 OBJECT-TYPE
SYNTAX INTEGER
MAX-ACCESS read-write
STATUS current
DESCRIPTION
"Data value."
::= { dataArray3 189 }

dataValue3_190 OBJECT-TYPE
SYNTAX INTEGER
MAX-ACCESS read-write
STATUS current
DESCRIPTION
"Data value."
::= { dataArray3 190 }

dataValue3_191 OBJECT-TYPE
SYNTAX INTEGER
MAX-ACCESS read-write
STATUS current
DESCRIPTION
"Data value."
::= { dataArray3 191 }

dataValue3_192 OBJECT-TYPE
SYNTAX INTEGER
MAX-ACCESS read-write
STATUS current
DESCRIPTION
"Data value."
::= { dataArray3 192 }

dataValue3_193 OBJECT-TYPE
SYNTAX INTEGER
MAX-ACCESS read-write
STATUS current
DESCRIPTION
"Data value."
::= { dataArray3 193 }

dataValue3_194 OBJECT-TYPE
SYNTAX INTEGER
MAX-ACCESS read-write
STATUS current
DESCRIPTION
"Data value."
::= { dataArray3 194 }

dataValue3_195 OBJECT-TYPE
SYNTAX INTEGER
MAX-ACCESS read-write
STATUS current
DESCRIPTION
"Data value."
::= { dataArray3 195 }

dataValue3_196 OBJECT-TYPE
SYNTAX INTEGER
MAX-ACCESS read-write
STATUS current
DESCRIPTION
"Data value."
::= { dataArray3 196 }

dataValue3_197 OBJECT-TYPE
SYNTAX INTEGER
MAX-ACCESS read-write
STATUS current
DESCRIPTION
"Data value."
::= { dataArray3 197 }

dataValue3_198 OBJECT-TYPE
SYNTAX INTEGER
MAX-ACCESS read-write
STATUS current
DESCRIPTION
"Data value."
::= { dataArray3 198 }

dataValue3_199 OBJECT-TYPE
SYNTAX INTEGER
MAX-ACCESS read-write
STATUS current
DESCRIPTION
"Data value."
::= { dataArray3 199 }

dataValue3_200 OBJECT-TYPE
SYNTAX INTEGER
MAX-ACCESS read-write
STATUS current
DESCRIPTION
"Data value."
::= { dataArray3 200 }

dataValue3_201 OBJECT-TYPE
SYNTAX INTEGER
MAX-ACCESS read-write
STATUS current
DESCRIPTION
"Data value."
::= { dataArray3 201 }

dataValue3_202 OBJECT-TYPE
SYNTAX INTEGER
MAX-ACCESS read-write
STATUS current
DESCRIPTION
"Data value."
::= { dataArray3 202 }

dataValue3_203 OBJECT-TYPE
SYNTAX INTEGER
MAX-ACCESS read-write
STATUS current
DESCRIPTION
"Data value."
::= { dataArray3 203 }

dataValue3_204 OBJECT-TYPE
SYNTAX INTEGER
MAX-ACCESS read-write
STATUS current
DESCRIPTION
"Data value."
::= { dataArray3 204 }

dataValue3_205 OBJECT-TYPE
SYNTAX INTEGER
MAX-ACCESS read-write
STATUS current
DESCRIPTION
"Data value."
::= { dataArray3 205 }

dataValue3_206 OBJECT-TYPE
SYNTAX INTEGER
MAX-ACCESS read-write
STATUS current
DESCRIPTION
"Data value."
::= { dataArray3 206 }

dataValue3_207 OBJECT-TYPE
SYNTAX INTEGER
MAX-ACCESS read-write
STATUS current
DESCRIPTION
"Data value."
::= { dataArray3 207 }

dataValue3_208 OBJECT-TYPE
SYNTAX INTEGER
MAX-ACCESS read-write
STATUS current
DESCRIPTION
"Data value."
::= { dataArray3 208 }

dataValue3_209 OBJECT-TYPE
SYNTAX INTEGER
MAX-ACCESS read-write
STATUS current
DESCRIPTION
"Data value."
::= { dataArray3 209 }

dataValue3_210 OBJECT-TYPE
SYNTAX INTEGER
MAX-ACCESS read-write
STATUS current
DESCRIPTION
"Data value."
::= { dataArray3 210 }

dataValue3_211 OBJECT-TYPE
SYNTAX INTEGER
MAX-ACCESS read-write
STATUS current
DESCRIPTION
"Data value."
::= { dataArray3 211 }

dataValue3_212 OBJECT-TYPE
SYNTAX INTEGER
MAX-ACCESS read-write
STATUS current
DESCRIPTION
"Data value."
::= { dataArray3 212 }

dataValue3_213 OBJECT-TYPE
SYNTAX INTEGER
MAX-ACCESS read-write
STATUS current
DESCRIPTION
"Data value."
::= { dataArray3 213 }

dataValue3_214 OBJECT-TYPE
SYNTAX INTEGER
MAX-ACCESS read-write
STATUS current
DESCRIPTION
"Data value."
::= { dataArray3 214 }

dataValue3_215 OBJECT-TYPE
SYNTAX INTEGER
MAX-ACCESS read-write
STATUS current
DESCRIPTION
"Data value."
::= { dataArray3 215 }

dataValue3_216 OBJECT-TYPE
SYNTAX INTEGER
MAX-ACCESS read-write
STATUS current
DESCRIPTION
"Data value."
::= { dataArray3 216 }

dataValue3_217 OBJECT-TYPE
SYNTAX INTEGER
MAX-ACCESS read-write
STATUS current
DESCRIPTION
"Data value."
::= { dataArray3 217 }

dataValue3_218 OBJECT-TYPE
SYNTAX INTEGER
MAX-ACCESS read-write
STATUS current
DESCRIPTION
"Data value."
::= { dataArray3 218 }

dataValue3_219 OBJECT-TYPE
SYNTAX INTEGER
MAX-ACCESS read-write
STATUS current
DESCRIPTION
"Data value."
::= { dataArray3 219 }

dataValue3_220 OBJECT-TYPE
SYNTAX INTEGER
MAX-ACCESS read-write
STATUS current
DESCRIPTION
"Data value."
::= { dataArray3 220 }

dataValue3_221 OBJECT-TYPE
SYNTAX INTEGER
MAX-ACCESS read-write
STATUS current
DESCRIPTION
"Data value."
::= { dataArray3 221 }

dataValue3_222 OBJECT-TYPE
SYNTAX INTEGER
MAX-ACCESS read-write
STATUS current
DESCRIPTION
"Data value."
::= { dataArray3 222 }

dataValue3_223 OBJECT-TYPE
SYNTAX INTEGER
MAX-ACCESS read-write
STATUS current
DESCRIPTION
"Data value."
::= { dataArray3 223 }

dataValue3_224 OBJECT-TYPE
SYNTAX INTEGER
MAX-ACCESS read-write
STATUS current
DESCRIPTION
"Data value."
::= { dataArray3 224 }

dataValue3_225 OBJECT-TYPE
SYNTAX INTEGER
MAX-ACCESS read-write
STATUS current
DESCRIPTION
"Data value."
::= { dataArray3 225 }

dataValue3_226 OBJECT-TYPE
SYNTAX INTEGER
MAX-ACCESS read-write
STATUS current
DESCRIPTION
"Data value."
::= { dataArray3 226 }

dataValue3_227 OBJECT-TYPE
SYNTAX INTEGER
MAX-ACCESS read-write
STATUS current
DESCRIPTION
"Data value."
::= { dataArray3 227 }

dataValue3_228 OBJECT-TYPE
SYNTAX INTEGER
MAX-ACCESS read-write
STATUS current
DESCRIPTION
"Data value."
::= { dataArray3 228 }

dataValue3_229 OBJECT-TYPE
SYNTAX INTEGER
MAX-ACCESS read-write
STATUS current
DESCRIPTION
"Data value."
::= { dataArray3 229 }

dataValue3_230 OBJECT-TYPE
SYNTAX INTEGER
MAX-ACCESS read-write
STATUS current
DESCRIPTION
"Data value."
::= { dataArray3 230 }

dataValue3_231 OBJECT-TYPE
SYNTAX INTEGER
MAX-ACCESS read-write
STATUS current
DESCRIPTION
"Data value."
::= { dataArray3 231 }

dataValue3_232 OBJECT-TYPE
SYNTAX INTEGER
MAX-ACCESS read-write
STATUS current
DESCRIPTION
"Data value."
::= { dataArray3 232 }

dataValue3_233 OBJECT-TYPE
SYNTAX INTEGER
MAX-ACCESS read-write
STATUS current
DESCRIPTION
"Data value."
::= { dataArray3 233 }

dataValue3_234 OBJECT-TYPE
SYNTAX INTEGER
MAX-ACCESS read-write
STATUS current
DESCRIPTION
"Data value."
::= { dataArray3 234 }

dataValue3_235 OBJECT-TYPE
SYNTAX INTEGER
MAX-ACCESS read-write
STATUS current
DESCRIPTION
"Data value."
::= { dataArray3 235 }

dataValue3_236 OBJECT-TYPE
SYNTAX INTEGER
MAX-ACCESS read-write
STATUS current
DESCRIPTION
"Data value."
::= { dataArray3 236 }

dataValue3_237 OBJECT-TYPE
SYNTAX INTEGER
MAX-ACCESS read-write
STATUS current
DESCRIPTION
"Data value."
::= { dataArray3 237 }

dataValue3_238 OBJECT-TYPE
SYNTAX INTEGER
MAX-ACCESS read-write
STATUS current
DESCRIPTION
"Data value."
::= { dataArray3 238 }

dataValue3_239 OBJECT-TYPE
SYNTAX INTEGER
MAX-ACCESS read-write
STATUS current
DESCRIPTION
"Data value."
::= { dataArray3 239 }

dataValue3_240 OBJECT-TYPE
SYNTAX INTEGER
MAX-ACCESS read-write
STATUS current
DESCRIPTION
"Data value."
::= { dataArray3 240 }

dataValue3_241 OBJECT-TYPE
SYNTAX INTEGER
MAX-ACCESS read-write
STATUS current
DESCRIPTION
"Data value."
::= { dataArray3 241 }

dataValue3_242 OBJECT-TYPE
SYNTAX INTEGER
MAX-ACCESS read-write
STATUS current
DESCRIPTION
"Data value."
::= { dataArray3 242 }

dataValue3_243 OBJECT-TYPE
SYNTAX INTEGER
MAX-ACCESS read-write
STATUS current
DESCRIPTION
"Data value."
::= { dataArray3 243 }

dataValue3_244 OBJECT-TYPE
SYNTAX INTEGER
MAX-ACCESS read-write
STATUS current
DESCRIPTION
"Data value."
::= { dataArray3 244 }

dataValue3_245 OBJECT-TYPE
SYNTAX INTEGER
MAX-ACCESS read-write
STATUS current
DESCRIPTION
"Data value."
::= { dataArray3 245 }

dataValue3_246 OBJECT-TYPE
SYNTAX INTEGER
MAX-ACCESS read-write
STATUS current
DESCRIPTION
"Data value."
::= { dataArray3 246 }

dataValue3_247 OBJECT-TYPE
SYNTAX INTEGER
MAX-ACCESS read-write
STATUS current
DESCRIPTION
"Data value."
::= { dataArray3 247 }

dataValue3_248 OBJECT-TYPE
SYNTAX INTEGER
MAX-ACCESS read-write
STATUS current
DESCRIPTION
"Data value."
::= { dataArray3 248 }

dataValue3_249 OBJECT-TYPE
SYNTAX INTEGER
MAX-ACCESS read-write
STATUS current
DESCRIPTION
"Data value."
::= { dataArray3 249 }

dataValue3_250 OBJECT-TYPE
SYNTAX INTEGER
MAX-ACCESS read-write
STATUS current
DESCRIPTION
"Data value."
::= { dataArray3 250 }

dataValue3_251 OBJECT-TYPE
SYNTAX INTEGER
MAX-ACCESS read-write
STATUS current
DESCRIPTION
"Data value."
::= { dataArray3 251 }

dataValue3_252 OBJECT-TYPE
SYNTAX INTEGER
MAX-ACCESS read-write
STATUS current
DESCRIPTION
"Data value."
::= { dataArray3 252 }

dataValue3_253 OBJECT-TYPE
SYNTAX INTEGER
MAX-ACCESS read-write
STATUS current
DESCRIPTION
"Data value."
::= { dataArray3 253 }

dataValue3_254 OBJECT-TYPE
SYNTAX INTEGER
MAX-ACCESS read-write
STATUS current
DESCRIPTION
"Data value."
::= { dataArray3 254 }

dataValue3_255 OBJECT-TYPE
SYNTAX INTEGER
MAX-ACCESS read-write
STATUS current
DESCRIPTION
"Data value."
::= { dataArray3 255 }

dataValue3_256 OBJECT-TYPE
SYNTAX INTEGER
MAX-ACCESS read-write
STATUS current
DESCRIPTION
"Data value."
::= { dataArray3 256 }

dataValue3_257 OBJECT-TYPE
SYNTAX INTEGER
MAX-ACCESS read-write
STATUS current
DESCRIPTION
"Data value."
::= { dataArray3 257 }

dataValue3_258 OBJECT-TYPE
SYNTAX INTEGER
MAX-ACCESS read-write
STATUS current
DESCRIPTION
"Data value."
::= { dataArray3 258 }

dataValue3_259 OBJECT-TYPE
SYNTAX INTEGER
MAX-ACCESS read-write
STATUS current
DESCRIPTION
"Data value."
::= { dataArray3 259 }

dataValue3_260 OBJECT-TYPE
SYNTAX INTEGER
MAX-ACCESS read-write
STATUS current
DESCRIPTION
"Data value."
::= { dataArray3 260 }

dataValue3_261 OBJECT-TYPE
SYNTAX INTEGER
MAX-ACCESS read-write
STATUS current
DESCRIPTION
"Data value."
::= { dataArray3 261 }

dataValue3_262 OBJECT-TYPE
SYNTAX INTEGER
MAX-ACCESS read-write
STATUS current
DESCRIPTION
"Data value."
::= { dataArray3 262 }

dataValue3_263 OBJECT-TYPE
SYNTAX INTEGER
MAX-ACCESS read-write
STATUS current
DESCRIPTION
"Data value."
::= { dataArray3 263 }

dataValue3_264 OBJECT-TYPE
SYNTAX INTEGER
MAX-ACCESS read-write
STATUS current
DESCRIPTION
"Data value."
::= { dataArray3 264 }

dataValue3_265 OBJECT-TYPE
SYNTAX INTEGER
MAX-ACCESS read-write
STATUS current
DESCRIPTION
"Data value."
::= { dataArray3 265 }

dataValue3_266 OBJECT-TYPE
SYNTAX INTEGER
MAX-ACCESS read-write
STATUS current
DESCRIPTION
"Data value."
::= { dataArray3 266 }

dataValue3_267 OBJECT-TYPE
SYNTAX INTEGER
MAX-ACCESS read-write
STATUS current
DESCRIPTION
"Data value."
::= { dataArray3 267 }

dataValue3_268 OBJECT-TYPE
SYNTAX INTEGER
MAX-ACCESS read-write
STATUS current
DESCRIPTION
"Data value."
::= { dataArray3 268 }

dataValue3_269 OBJECT-TYPE
SYNTAX INTEGER
MAX-ACCESS read-write
STATUS current
DESCRIPTION
"Data value."
::= { dataArray3 269 }

dataValue3_270 OBJECT-TYPE
SYNTAX INTEGER
MAX-ACCESS read-write
STATUS current
DESCRIPTION
"Data value."
::= { dataArray3 270 }

dataValue3_271 OBJECT-TYPE
SYNTAX INTEGER
MAX-ACCESS read-write
STATUS current
DESCRIPTION
"Data value."
::= { dataArray3 271 }

dataValue3_272 OBJECT-TYPE
SYNTAX INTEGER
MAX-ACCESS read-write
STATUS current
DESCRIPTION
"Data value."
::= { dataArray3 272 }

dataValue3_273 OBJECT-TYPE
SYNTAX INTEGER
MAX-ACCESS read-write
STATUS current
DESCRIPTION
"Data value."
::= { dataArray3 273 }

dataValue3_274 OBJECT-TYPE
SYNTAX INTEGER
MAX-ACCESS read-write
STATUS current
DESCRIPTION
"Data value."
::= { dataArray3 274 }

dataValue3_275 OBJECT-TYPE
SYNTAX INTEGER
MAX-ACCESS read-write
STATUS current
DESCRIPTION
"Data value."
::= { dataArray3 275 }

dataValue3_276 OBJECT-TYPE
SYNTAX INTEGER
MAX-ACCESS read-write
STATUS current
DESCRIPTION
"Data value."
::= { dataArray3 276 }

dataValue3_277 OBJECT-TYPE
SYNTAX INTEGER
MAX-ACCESS read-write
STATUS current
DESCRIPTION
"Data value."
::= { dataArray3 277 }

dataValue3_278 OBJECT-TYPE
SYNTAX INTEGER
MAX-ACCESS read-write
STATUS current
DESCRIPTION
"Data value."
::= { dataArray3 278 }

dataValue3_279 OBJECT-TYPE
SYNTAX INTEGER
MAX-ACCESS read-write
STATUS current
DESCRIPTION
"Data value."
::= { dataArray3 279 }

dataValue3_280 OBJECT-TYPE
SYNTAX INTEGER
MAX-ACCESS read-write
STATUS current
DESCRIPTION
"Data value."
::= { dataArray3 280 }

dataValue3_281 OBJECT-TYPE
SYNTAX INTEGER
MAX-ACCESS read-write
STATUS current
DESCRIPTION
"Data value."
::= { dataArray3 281 }

dataValue3_282 OBJECT-TYPE
SYNTAX INTEGER
MAX-ACCESS read-write
STATUS current
DESCRIPTION
"Data value."
::= { dataArray3 282 }

dataValue3_283 OBJECT-TYPE
SYNTAX INTEGER
MAX-ACCESS read-write
STATUS current
DESCRIPTION
"Data value."
::= { dataArray3 283 }

dataValue3_284 OBJECT-TYPE
SYNTAX INTEGER
MAX-ACCESS read-write
STATUS current
DESCRIPTION
"Data value."
::= { dataArray3 284 }

dataValue3_285 OBJECT-TYPE
SYNTAX INTEGER
MAX-ACCESS read-write
STATUS current
DESCRIPTION
"Data value."
::= { dataArray3 285 }

dataValue3_286 OBJECT-TYPE
SYNTAX INTEGER
MAX-ACCESS read-write
STATUS current
DESCRIPTION
"Data value."
::= { dataArray3 286 }

dataValue3_287 OBJECT-TYPE
SYNTAX INTEGER
MAX-ACCESS read-write
STATUS current
DESCRIPTION
"Data value."
::= { dataArray3 287 }

dataValue3_288 OBJECT-TYPE
SYNTAX INTEGER
MAX-ACCESS read-write
STATUS current
DESCRIPTION
"Data value."
::= { dataArray3 288 }

dataValue3_289 OBJECT-TYPE
SYNTAX INTEGER
MAX-ACCESS read-write
STATUS current
DESCRIPTION
"Data value."
::= { dataArray3 289 }

dataValue3_290 OBJECT-TYPE
SYNTAX INTEGER
MAX-ACCESS read-write
STATUS current
DESCRIPTION
"Data value."
::= { dataArray3 290 }

dataValue3_291 OBJECT-TYPE
SYNTAX INTEGER
MAX-ACCESS read-write
STATUS current
DESCRIPTION
"Data value."
::= { dataArray3 291 }

dataValue3_292 OBJECT-TYPE
SYNTAX INTEGER
MAX-ACCESS read-write
STATUS current
DESCRIPTION
"Data value."
::= { dataArray3 292 }

dataValue3_293 OBJECT-TYPE
SYNTAX INTEGER
MAX-ACCESS read-write
STATUS current
DESCRIPTION
"Data value."
::= { dataArray3 293 }

dataValue3_294 OBJECT-TYPE
SYNTAX INTEGER
MAX-ACCESS read-write
STATUS current
DESCRIPTION
"Data value."
::= { dataArray3 294 }

dataValue3_295 OBJECT-TYPE
SYNTAX INTEGER
MAX-ACCESS read-write
STATUS current
DESCRIPTION
"Data value."
::= { dataArray3 295 }

dataValue3_296 OBJECT-TYPE
SYNTAX INTEGER
MAX-ACCESS read-write
STATUS current
DESCRIPTION
"Data value."
::= { dataArray3 296 }

dataValue3_297 OBJECT-TYPE
SYNTAX INTEGER
MAX-ACCESS read-write
STATUS current
DESCRIPTION
"Data value."
::= { dataArray3 297 }

dataValue3_298 OBJECT-TYPE
SYNTAX INTEGER
MAX-ACCESS read-write
STATUS current
DESCRIPTION
"Data value."
::= { dataArray3 298 }

dataValue3_299 OBJECT-TYPE
SYNTAX INTEGER
MAX-ACCESS read-write
STATUS current
DESCRIPTION
"Data value."
::= { dataArray3 299 }

dataValue3_300 OBJECT-TYPE
SYNTAX INTEGER
MAX-ACCESS read-write
STATUS current
DESCRIPTION
"Data value."
::= { dataArray3 300 }

dataValue3_301 OBJECT-TYPE
SYNTAX INTEGER
MAX-ACCESS read-write
STATUS current
DESCRIPTION
"Data value."
::= { dataArray3 301 }

dataValue3_302 OBJECT-TYPE
SYNTAX INTEGER
MAX-ACCESS read-write
STATUS current
DESCRIPTION
"Data value."
::= { dataArray3 302 }

dataValue3_303 OBJECT-TYPE
SYNTAX INTEGER
MAX-ACCESS read-write
STATUS current
DESCRIPTION
"Data value."
::= { dataArray3 303 }

dataValue3_304 OBJECT-TYPE
SYNTAX INTEGER
MAX-ACCESS read-write
STATUS current
DESCRIPTION
"Data value."
::= { dataArray3 304 }

dataValue3_305 OBJECT-TYPE
SYNTAX INTEGER
MAX-ACCESS read-write
STATUS current
DESCRIPTION
"Data value."
::= { dataArray3 305 }

dataValue3_306 OBJECT-TYPE
SYNTAX INTEGER
MAX-ACCESS read-write
STATUS current
DESCRIPTION
"Data value."
::= { dataArray3 306 }

dataValue3_307 OBJECT-TYPE
SYNTAX INTEGER
MAX-ACCESS read-write
STATUS current
DESCRIPTION
"Data value."
::= { dataArray3 307 }

dataValue3_308 OBJECT-TYPE
SYNTAX INTEGER
MAX-ACCESS read-write
STATUS current
DESCRIPTION
"Data value."
::= { dataArray3 308 }

dataValue3_309 OBJECT-TYPE
SYNTAX INTEGER
MAX-ACCESS read-write
STATUS current
DESCRIPTION
"Data value."
::= { dataArray3 309 }

dataValue3_310 OBJECT-TYPE
SYNTAX INTEGER
MAX-ACCESS read-write
STATUS current
DESCRIPTION
"Data value."
::= { dataArray3 310 }

dataValue3_311 OBJECT-TYPE
SYNTAX INTEGER
MAX-ACCESS read-write
STATUS current
DESCRIPTION
"Data value."
::= { dataArray3 311 }

dataValue3_312 OBJECT-TYPE
SYNTAX INTEGER
MAX-ACCESS read-write
STATUS current
DESCRIPTION
"Data value."
::= { dataArray3 312 }

dataValue3_313 OBJECT-TYPE
SYNTAX INTEGER
MAX-ACCESS read-write
STATUS current
DESCRIPTION
"Data value."
::= { dataArray3 313 }

dataValue3_314 OBJECT-TYPE
SYNTAX INTEGER
MAX-ACCESS read-write
STATUS current
DESCRIPTION
"Data value."
::= { dataArray3 314 }

dataValue3_315 OBJECT-TYPE
SYNTAX INTEGER
MAX-ACCESS read-write
STATUS current
DESCRIPTION
"Data value."
::= { dataArray3 315 }

dataValue3_316 OBJECT-TYPE
SYNTAX INTEGER
MAX-ACCESS read-write
STATUS current
DESCRIPTION
"Data value."
::= { dataArray3 316 }

dataValue3_317 OBJECT-TYPE
SYNTAX INTEGER
MAX-ACCESS read-write
STATUS current
DESCRIPTION
"Data value."
::= { dataArray3 317 }

dataValue3_318 OBJECT-TYPE
SYNTAX INTEGER
MAX-ACCESS read-write
STATUS current
DESCRIPTION
"Data value."
::= { dataArray3 318 }

dataValue3_319 OBJECT-TYPE
SYNTAX INTEGER
MAX-ACCESS read-write
STATUS current
DESCRIPTION
"Data value."
::= { dataArray3 319 }

dataValue3_320 OBJECT-TYPE
SYNTAX INTEGER
MAX-ACCESS read-write
STATUS current
DESCRIPTION
"Data value."
::= { dataArray3 320 }

dataValue3_321 OBJECT-TYPE
SYNTAX INTEGER
MAX-ACCESS read-write
STATUS current
DESCRIPTION
"Data value."
::= { dataArray3 321 }

dataValue3_322 OBJECT-TYPE
SYNTAX INTEGER
MAX-ACCESS read-write
STATUS current
DESCRIPTION
"Data value."
::= { dataArray3 322 }

dataValue3_323 OBJECT-TYPE
SYNTAX INTEGER
MAX-ACCESS read-write
STATUS current
DESCRIPTION
"Data value."
::= { dataArray3 323 }

dataValue3_324 OBJECT-TYPE
SYNTAX INTEGER
MAX-ACCESS read-write
STATUS current
DESCRIPTION
"Data value."
::= { dataArray3 324 }

dataValue3_325 OBJECT-TYPE
SYNTAX INTEGER
MAX-ACCESS read-write
STATUS current
DESCRIPTION
"Data value."
::= { dataArray3 325 }

dataValue3_326 OBJECT-TYPE
SYNTAX INTEGER
MAX-ACCESS read-write
STATUS current
DESCRIPTION
"Data value."
::= { dataArray3 326 }

dataValue3_327 OBJECT-TYPE
SYNTAX INTEGER
MAX-ACCESS read-write
STATUS current
DESCRIPTION
"Data value."
::= { dataArray3 327 }

dataValue3_328 OBJECT-TYPE
SYNTAX INTEGER
MAX-ACCESS read-write
STATUS current
DESCRIPTION
"Data value."
::= { dataArray3 328 }

dataValue3_329 OBJECT-TYPE
SYNTAX INTEGER
MAX-ACCESS read-write
STATUS current
DESCRIPTION
"Data value."
::= { dataArray3 329 }

dataValue3_330 OBJECT-TYPE
SYNTAX INTEGER
MAX-ACCESS read-write
STATUS current
DESCRIPTION
"Data value."
::= { dataArray3 330 }

dataValue3_331 OBJECT-TYPE
SYNTAX INTEGER
MAX-ACCESS read-write
STATUS current
DESCRIPTION
"Data value."
::= { dataArray3 331 }

dataValue3_332 OBJECT-TYPE
SYNTAX INTEGER
MAX-ACCESS read-write
STATUS current
DESCRIPTION
"Data value."
::= { dataArray3 332 }

dataValue3_333 OBJECT-TYPE
SYNTAX INTEGER
MAX-ACCESS read-write
STATUS current
DESCRIPTION
"Data value."
::= { dataArray3 333 }

dataValue3_334 OBJECT-TYPE
SYNTAX INTEGER
MAX-ACCESS read-write
STATUS current
DESCRIPTION
"Data value."
::= { dataArray3 334 }

dataValue3_335 OBJECT-TYPE
SYNTAX INTEGER
MAX-ACCESS read-write
STATUS current
DESCRIPTION
"Data value."
::= { dataArray3 335 }

dataValue3_336 OBJECT-TYPE
SYNTAX INTEGER
MAX-ACCESS read-write
STATUS current
DESCRIPTION
"Data value."
::= { dataArray3 336 }

dataValue3_337 OBJECT-TYPE
SYNTAX INTEGER
MAX-ACCESS read-write
STATUS current
DESCRIPTION
"Data value."
::= { dataArray3 337 }

dataValue3_338 OBJECT-TYPE
SYNTAX INTEGER
MAX-ACCESS read-write
STATUS current
DESCRIPTION
"Data value."
::= { dataArray3 338 }

dataValue3_339 OBJECT-TYPE
SYNTAX INTEGER
MAX-ACCESS read-write
STATUS current
DESCRIPTION
"Data value."
::= { dataArray3 339 }

dataValue3_340 OBJECT-TYPE
SYNTAX INTEGER
MAX-ACCESS read-write
STATUS current
DESCRIPTION
"Data value."
::= { dataArray3 340 }

dataValue3_341 OBJECT-TYPE
SYNTAX INTEGER
MAX-ACCESS read-write
STATUS current
DESCRIPTION
"Data value."
::= { dataArray3 341 }

dataValue3_342 OBJECT-TYPE
SYNTAX INTEGER
MAX-ACCESS read-write
STATUS current
DESCRIPTION
"Data value."
::= { dataArray3 342 }

dataValue3_343 OBJECT-TYPE
SYNTAX INTEGER
MAX-ACCESS read-write
STATUS current
DESCRIPTION
"Data value."
::= { dataArray3 343 }

dataValue3_344 OBJECT-TYPE
SYNTAX INTEGER
MAX-ACCESS read-write
STATUS current
DESCRIPTION
"Data value."
::= { dataArray3 344 }

dataValue3_345 OBJECT-TYPE
SYNTAX INTEGER
MAX-ACCESS read-write
STATUS current
DESCRIPTION
"Data value."
::= { dataArray3 345 }

dataValue3_346 OBJECT-TYPE
SYNTAX INTEGER
MAX-ACCESS read-write
STATUS current
DESCRIPTION
"Data value."
::= { dataArray3 346 }

dataValue3_347 OBJECT-TYPE
SYNTAX INTEGER
MAX-ACCESS read-write
STATUS current
DESCRIPTION
"Data value."
::= { dataArray3 347 }

dataValue3_348 OBJECT-TYPE
SYNTAX INTEGER
MAX-ACCESS read-write
STATUS current
DESCRIPTION
"Data value."
::= { dataArray3 348 }

dataValue3_349 OBJECT-TYPE
SYNTAX INTEGER
MAX-ACCESS read-write
STATUS current
DESCRIPTION
"Data value."
::= { dataArray3 349 }

dataValue3_350 OBJECT-TYPE
SYNTAX INTEGER
MAX-ACCESS read-write
STATUS current
DESCRIPTION
"Data value."
::= { dataArray3 350 }

dataValue3_351 OBJECT-TYPE
SYNTAX INTEGER
MAX-ACCESS read-write
STATUS current
DESCRIPTION
"Data value."
::= { dataArray3 351 }

dataValue3_352 OBJECT-TYPE
SYNTAX INTEGER
MAX-ACCESS read-write
STATUS current
DESCRIPTION
"Data value."
::= { dataArray3 352 }

dataValue3_353 OBJECT-TYPE
SYNTAX INTEGER
MAX-ACCESS read-write
STATUS current
DESCRIPTION
"Data value."
::= { dataArray3 353 }

dataValue3_354 OBJECT-TYPE
SYNTAX INTEGER
MAX-ACCESS read-write
STATUS current
DESCRIPTION
"Data value."
::= { dataArray3 354 }

dataValue3_355 OBJECT-TYPE
SYNTAX INTEGER
MAX-ACCESS read-write
STATUS current
DESCRIPTION
"Data value."
::= { dataArray3 355 }

dataValue3_356 OBJECT-TYPE
SYNTAX INTEGER
MAX-ACCESS read-write
STATUS current
DESCRIPTION
"Data value."
::= { dataArray3 356 }

dataValue3_357 OBJECT-TYPE
SYNTAX INTEGER
MAX-ACCESS read-write
STATUS current
DESCRIPTION
"Data value."
::= { dataArray3 357 }

dataValue3_358 OBJECT-TYPE
SYNTAX INTEGER
MAX-ACCESS read-write
STATUS current
DESCRIPTION
"Data value."
::= { dataArray3 358 }

dataValue3_359 OBJECT-TYPE
SYNTAX INTEGER
MAX-ACCESS read-write
STATUS current
DESCRIPTION
"Data value."
::= { dataArray3 359 }

dataValue3_360 OBJECT-TYPE
SYNTAX INTEGER
MAX-ACCESS read-write
STATUS current
DESCRIPTION
"Data value."
::= { dataArray3 360 }

dataValue3_361 OBJECT-TYPE
SYNTAX INTEGER
MAX-ACCESS read-write
STATUS current
DESCRIPTION
"Data value."
::= { dataArray3 361 }

dataValue3_362 OBJECT-TYPE
SYNTAX INTEGER
MAX-ACCESS read-write
STATUS current
DESCRIPTION
"Data value."
::= { dataArray3 362 }

dataValue3_363 OBJECT-TYPE
SYNTAX INTEGER
MAX-ACCESS read-write
STATUS current
DESCRIPTION
"Data value."
::= { dataArray3 363 }

dataValue3_364 OBJECT-TYPE
SYNTAX INTEGER
MAX-ACCESS read-write
STATUS current
DESCRIPTION
"Data value."
::= { dataArray3 364 }

dataValue3_365 OBJECT-TYPE
SYNTAX INTEGER
MAX-ACCESS read-write
STATUS current
DESCRIPTION
"Data value."
::= { dataArray3 365 }

dataValue3_366 OBJECT-TYPE
SYNTAX INTEGER
MAX-ACCESS read-write
STATUS current
DESCRIPTION
"Data value."
::= { dataArray3 366 }

dataValue3_367 OBJECT-TYPE
SYNTAX INTEGER
MAX-ACCESS read-write
STATUS current
DESCRIPTION
"Data value."
::= { dataArray3 367 }

dataValue3_368 OBJECT-TYPE
SYNTAX INTEGER
MAX-ACCESS read-write
STATUS current
DESCRIPTION
"Data value."
::= { dataArray3 368 }

dataValue3_369 OBJECT-TYPE
SYNTAX INTEGER
MAX-ACCESS read-write
STATUS current
DESCRIPTION
"Data value."
::= { dataArray3 369 }

dataValue3_370 OBJECT-TYPE
SYNTAX INTEGER
MAX-ACCESS read-write
STATUS current
DESCRIPTION
"Data value."
::= { dataArray3 370 }

dataValue3_371 OBJECT-TYPE
SYNTAX INTEGER
MAX-ACCESS read-write
STATUS current
DESCRIPTION
"Data value."
::= { dataArray3 371 }

dataValue3_372 OBJECT-TYPE
SYNTAX INTEGER
MAX-ACCESS read-write
STATUS current
DESCRIPTION
"Data value."
::= { dataArray3 372 }

dataValue3_373 OBJECT-TYPE
SYNTAX INTEGER
MAX-ACCESS read-write
STATUS current
DESCRIPTION
"Data value."
::= { dataArray3 373 }

dataValue3_374 OBJECT-TYPE
SYNTAX INTEGER
MAX-ACCESS read-write
STATUS current
DESCRIPTION
"Data value."
::= { dataArray3 374 }

dataValue3_375 OBJECT-TYPE
SYNTAX INTEGER
MAX-ACCESS read-write
STATUS current
DESCRIPTION
"Data value."
::= { dataArray3 375 }

dataValue3_376 OBJECT-TYPE
SYNTAX INTEGER
MAX-ACCESS read-write
STATUS current
DESCRIPTION
"Data value."
::= { dataArray3 376 }

dataValue3_377 OBJECT-TYPE
SYNTAX INTEGER
MAX-ACCESS read-write
STATUS current
DESCRIPTION
"Data value."
::= { dataArray3 377 }

dataValue3_378 OBJECT-TYPE
SYNTAX INTEGER
MAX-ACCESS read-write
STATUS current
DESCRIPTION
"Data value."
::= { dataArray3 378 }

dataValue3_379 OBJECT-TYPE
SYNTAX INTEGER
MAX-ACCESS read-write
STATUS current
DESCRIPTION
"Data value."
::= { dataArray3 379 }

dataValue3_380 OBJECT-TYPE
SYNTAX INTEGER
MAX-ACCESS read-write
STATUS current
DESCRIPTION
"Data value."
::= { dataArray3 380 }

dataValue3_381 OBJECT-TYPE
SYNTAX INTEGER
MAX-ACCESS read-write
STATUS current
DESCRIPTION
"Data value."
::= { dataArray3 381 }

dataValue3_382 OBJECT-TYPE
SYNTAX INTEGER
MAX-ACCESS read-write
STATUS current
DESCRIPTION
"Data value."
::= { dataArray3 382 }

dataValue3_383 OBJECT-TYPE
SYNTAX INTEGER
MAX-ACCESS read-write
STATUS current
DESCRIPTION
"Data value."
::= { dataArray3 383 }

dataValue3_384 OBJECT-TYPE
SYNTAX INTEGER
MAX-ACCESS read-write
STATUS current
DESCRIPTION
"Data value."
::= { dataArray3 384 }

dataValue3_385 OBJECT-TYPE
SYNTAX INTEGER
MAX-ACCESS read-write
STATUS current
DESCRIPTION
"Data value."
::= { dataArray3 385 }

dataValue3_386 OBJECT-TYPE
SYNTAX INTEGER
MAX-ACCESS read-write
STATUS current
DESCRIPTION
"Data value."
::= { dataArray3 386 }

dataValue3_387 OBJECT-TYPE
SYNTAX INTEGER
MAX-ACCESS read-write
STATUS current
DESCRIPTION
"Data value."
::= { dataArray3 387 }

dataValue3_388 OBJECT-TYPE
SYNTAX INTEGER
MAX-ACCESS read-write
STATUS current
DESCRIPTION
"Data value."
::= { dataArray3 388 }

dataValue3_389 OBJECT-TYPE
SYNTAX INTEGER
MAX-ACCESS read-write
STATUS current
DESCRIPTION
"Data value."
::= { dataArray3 389 }

dataValue3_390 OBJECT-TYPE
SYNTAX INTEGER
MAX-ACCESS read-write
STATUS current
DESCRIPTION
"Data value."
::= { dataArray3 390 }

dataValue3_391 OBJECT-TYPE
SYNTAX INTEGER
MAX-ACCESS read-write
STATUS current
DESCRIPTION
"Data value."
::= { dataArray3 391 }

dataValue3_392 OBJECT-TYPE
SYNTAX INTEGER
MAX-ACCESS read-write
STATUS current
DESCRIPTION
"Data value."
::= { dataArray3 392 }

dataValue3_393 OBJECT-TYPE
SYNTAX INTEGER
MAX-ACCESS read-write
STATUS current
DESCRIPTION
"Data value."
::= { dataArray3 393 }

dataValue3_394 OBJECT-TYPE
SYNTAX INTEGER
MAX-ACCESS read-write
STATUS current
DESCRIPTION
"Data value."
::= { dataArray3 394 }

dataValue3_395 OBJECT-TYPE
SYNTAX INTEGER
MAX-ACCESS read-write
STATUS current
DESCRIPTION
"Data value."
::= { dataArray3 395 }

dataValue3_396 OBJECT-TYPE
SYNTAX INTEGER
MAX-ACCESS read-write
STATUS current
DESCRIPTION
"Data value."
::= { dataArray3 396 }

dataValue3_397 OBJECT-TYPE
SYNTAX INTEGER
MAX-ACCESS read-write
STATUS current
DESCRIPTION
"Data value."
::= { dataArray3 397 }

dataValue3_398 OBJECT-TYPE
SYNTAX INTEGER
MAX-ACCESS read-write
STATUS current
DESCRIPTION
"Data value."
::= { dataArray3 398 }

dataValue3_399 OBJECT-TYPE
SYNTAX INTEGER
MAX-ACCESS read-write
STATUS current
DESCRIPTION
"Data value."
::= { dataArray3 399 }

dataArray4 OBJECT IDENTIFIER ::= { cc08255400_v1_00a 4 }

dataValue4_0 OBJECT-TYPE
SYNTAX INTEGER
MAX-ACCESS read-write
STATUS current
DESCRIPTION
"Data value."
::= { dataArray4 0 }

dataValue4_1 OBJECT-TYPE
SYNTAX INTEGER
MAX-ACCESS read-write
STATUS current
DESCRIPTION
"Data value."
::= { dataArray4 1 }

dataValue4_2 OBJECT-TYPE
SYNTAX INTEGER
MAX-ACCESS read-write
STATUS current
DESCRIPTION
"Data value."
::= { dataArray4 2 }

dataValue4_3 OBJECT-TYPE
SYNTAX INTEGER
MAX-ACCESS read-write
STATUS current
DESCRIPTION
"Data value."
::= { dataArray4 3 }

dataValue4_4 OBJECT-TYPE
SYNTAX INTEGER
MAX-ACCESS read-write
STATUS current
DESCRIPTION
"Data value."
::= { dataArray4 4 }

dataValue4_5 OBJECT-TYPE
SYNTAX INTEGER
MAX-ACCESS read-write
STATUS current
DESCRIPTION
"Data value."
::= { dataArray4 5 }

dataValue4_6 OBJECT-TYPE
SYNTAX INTEGER
MAX-ACCESS read-write
STATUS current
DESCRIPTION
"Data value."
::= { dataArray4 6 }

dataValue4_7 OBJECT-TYPE
SYNTAX INTEGER
MAX-ACCESS read-write
STATUS current
DESCRIPTION
"Data value."
::= { dataArray4 7 }

dataValue4_8 OBJECT-TYPE
SYNTAX INTEGER
MAX-ACCESS read-write
STATUS current
DESCRIPTION
"Data value."
::= { dataArray4 8 }

dataValue4_9 OBJECT-TYPE
SYNTAX INTEGER
MAX-ACCESS read-write
STATUS current
DESCRIPTION
"Data value."
::= { dataArray4 9 }

dataValue4_10 OBJECT-TYPE
SYNTAX INTEGER
MAX-ACCESS read-write
STATUS current
DESCRIPTION
"Data value."
::= { dataArray4 10 }

dataValue4_11 OBJECT-TYPE
SYNTAX INTEGER
MAX-ACCESS read-write
STATUS current
DESCRIPTION
"Data value."
::= { dataArray4 11 }

dataValue4_12 OBJECT-TYPE
SYNTAX INTEGER
MAX-ACCESS read-write
STATUS current
DESCRIPTION
"Data value."
::= { dataArray4 12 }

dataValue4_13 OBJECT-TYPE
SYNTAX INTEGER
MAX-ACCESS read-write
STATUS current
DESCRIPTION
"Data value."
::= { dataArray4 13 }

dataValue4_14 OBJECT-TYPE
SYNTAX INTEGER
MAX-ACCESS read-write
STATUS current
DESCRIPTION
"Data value."
::= { dataArray4 14 }

dataValue4_15 OBJECT-TYPE
SYNTAX INTEGER
MAX-ACCESS read-write
STATUS current
DESCRIPTION
"Data value."
::= { dataArray4 15 }

dataValue4_16 OBJECT-TYPE
SYNTAX INTEGER
MAX-ACCESS read-write
STATUS current
DESCRIPTION
"Data value."
::= { dataArray4 16 }

dataValue4_17 OBJECT-TYPE
SYNTAX INTEGER
MAX-ACCESS read-write
STATUS current
DESCRIPTION
"Data value."
::= { dataArray4 17 }

dataValue4_18 OBJECT-TYPE
SYNTAX INTEGER
MAX-ACCESS read-write
STATUS current
DESCRIPTION
"Data value."
::= { dataArray4 18 }

dataValue4_19 OBJECT-TYPE
SYNTAX INTEGER
MAX-ACCESS read-write
STATUS current
DESCRIPTION
"Data value."
::= { dataArray4 19 }

dataValue4_20 OBJECT-TYPE
SYNTAX INTEGER
MAX-ACCESS read-write
STATUS current
DESCRIPTION
"Data value."
::= { dataArray4 20 }

dataValue4_21 OBJECT-TYPE
SYNTAX INTEGER
MAX-ACCESS read-write
STATUS current
DESCRIPTION
"Data value."
::= { dataArray4 21 }

dataValue4_22 OBJECT-TYPE
SYNTAX INTEGER
MAX-ACCESS read-write
STATUS current
DESCRIPTION
"Data value."
::= { dataArray4 22 }

dataValue4_23 OBJECT-TYPE
SYNTAX INTEGER
MAX-ACCESS read-write
STATUS current
DESCRIPTION
"Data value."
::= { dataArray4 23 }

dataValue4_24 OBJECT-TYPE
SYNTAX INTEGER
MAX-ACCESS read-write
STATUS current
DESCRIPTION
"Data value."
::= { dataArray4 24 }

dataValue4_25 OBJECT-TYPE
SYNTAX INTEGER
MAX-ACCESS read-write
STATUS current
DESCRIPTION
"Data value."
::= { dataArray4 25 }

dataValue4_26 OBJECT-TYPE
SYNTAX INTEGER
MAX-ACCESS read-write
STATUS current
DESCRIPTION
"Data value."
::= { dataArray4 26 }

dataValue4_27 OBJECT-TYPE
SYNTAX INTEGER
MAX-ACCESS read-write
STATUS current
DESCRIPTION
"Data value."
::= { dataArray4 27 }

dataValue4_28 OBJECT-TYPE
SYNTAX INTEGER
MAX-ACCESS read-write
STATUS current
DESCRIPTION
"Data value."
::= { dataArray4 28 }

dataValue4_29 OBJECT-TYPE
SYNTAX INTEGER
MAX-ACCESS read-write
STATUS current
DESCRIPTION
"Data value."
::= { dataArray4 29 }

dataValue4_30 OBJECT-TYPE
SYNTAX INTEGER
MAX-ACCESS read-write
STATUS current
DESCRIPTION
"Data value."
::= { dataArray4 30 }

dataValue4_31 OBJECT-TYPE
SYNTAX INTEGER
MAX-ACCESS read-write
STATUS current
DESCRIPTION
"Data value."
::= { dataArray4 31 }

dataValue4_32 OBJECT-TYPE
SYNTAX INTEGER
MAX-ACCESS read-write
STATUS current
DESCRIPTION
"Data value."
::= { dataArray4 32 }

dataValue4_33 OBJECT-TYPE
SYNTAX INTEGER
MAX-ACCESS read-write
STATUS current
DESCRIPTION
"Data value."
::= { dataArray4 33 }

dataValue4_34 OBJECT-TYPE
SYNTAX INTEGER
MAX-ACCESS read-write
STATUS current
DESCRIPTION
"Data value."
::= { dataArray4 34 }

dataValue4_35 OBJECT-TYPE
SYNTAX INTEGER
MAX-ACCESS read-write
STATUS current
DESCRIPTION
"Data value."
::= { dataArray4 35 }

dataValue4_36 OBJECT-TYPE
SYNTAX INTEGER
MAX-ACCESS read-write
STATUS current
DESCRIPTION
"Data value."
::= { dataArray4 36 }

dataValue4_37 OBJECT-TYPE
SYNTAX INTEGER
MAX-ACCESS read-write
STATUS current
DESCRIPTION
"Data value."
::= { dataArray4 37 }

dataValue4_38 OBJECT-TYPE
SYNTAX INTEGER
MAX-ACCESS read-write
STATUS current
DESCRIPTION
"Data value."
::= { dataArray4 38 }

dataValue4_39 OBJECT-TYPE
SYNTAX INTEGER
MAX-ACCESS read-write
STATUS current
DESCRIPTION
"Data value."
::= { dataArray4 39 }

dataValue4_40 OBJECT-TYPE
SYNTAX INTEGER
MAX-ACCESS read-write
STATUS current
DESCRIPTION
"Data value."
::= { dataArray4 40 }

dataValue4_41 OBJECT-TYPE
SYNTAX INTEGER
MAX-ACCESS read-write
STATUS current
DESCRIPTION
"Data value."
::= { dataArray4 41 }

dataValue4_42 OBJECT-TYPE
SYNTAX INTEGER
MAX-ACCESS read-write
STATUS current
DESCRIPTION
"Data value."
::= { dataArray4 42 }

dataValue4_43 OBJECT-TYPE
SYNTAX INTEGER
MAX-ACCESS read-write
STATUS current
DESCRIPTION
"Data value."
::= { dataArray4 43 }

dataValue4_44 OBJECT-TYPE
SYNTAX INTEGER
MAX-ACCESS read-write
STATUS current
DESCRIPTION
"Data value."
::= { dataArray4 44 }

dataValue4_45 OBJECT-TYPE
SYNTAX INTEGER
MAX-ACCESS read-write
STATUS current
DESCRIPTION
"Data value."
::= { dataArray4 45 }

dataValue4_46 OBJECT-TYPE
SYNTAX INTEGER
MAX-ACCESS read-write
STATUS current
DESCRIPTION
"Data value."
::= { dataArray4 46 }

dataValue4_47 OBJECT-TYPE
SYNTAX INTEGER
MAX-ACCESS read-write
STATUS current
DESCRIPTION
"Data value."
::= { dataArray4 47 }

dataValue4_48 OBJECT-TYPE
SYNTAX INTEGER
MAX-ACCESS read-write
STATUS current
DESCRIPTION
"Data value."
::= { dataArray4 48 }

dataValue4_49 OBJECT-TYPE
SYNTAX INTEGER
MAX-ACCESS read-write
STATUS current
DESCRIPTION
"Data value."
::= { dataArray4 49 }

dataValue4_50 OBJECT-TYPE
SYNTAX INTEGER
MAX-ACCESS read-write
STATUS current
DESCRIPTION
"Data value."
::= { dataArray4 50 }

dataValue4_51 OBJECT-TYPE
SYNTAX INTEGER
MAX-ACCESS read-write
STATUS current
DESCRIPTION
"Data value."
::= { dataArray4 51 }

dataValue4_52 OBJECT-TYPE
SYNTAX INTEGER
MAX-ACCESS read-write
STATUS current
DESCRIPTION
"Data value."
::= { dataArray4 52 }

dataValue4_53 OBJECT-TYPE
SYNTAX INTEGER
MAX-ACCESS read-write
STATUS current
DESCRIPTION
"Data value."
::= { dataArray4 53 }

dataValue4_54 OBJECT-TYPE
SYNTAX INTEGER
MAX-ACCESS read-write
STATUS current
DESCRIPTION
"Data value."
::= { dataArray4 54 }

dataValue4_55 OBJECT-TYPE
SYNTAX INTEGER
MAX-ACCESS read-write
STATUS current
DESCRIPTION
"Data value."
::= { dataArray4 55 }

dataValue4_56 OBJECT-TYPE
SYNTAX INTEGER
MAX-ACCESS read-write
STATUS current
DESCRIPTION
"Data value."
::= { dataArray4 56 }

dataValue4_57 OBJECT-TYPE
SYNTAX INTEGER
MAX-ACCESS read-write
STATUS current
DESCRIPTION
"Data value."
::= { dataArray4 57 }

dataValue4_58 OBJECT-TYPE
SYNTAX INTEGER
MAX-ACCESS read-write
STATUS current
DESCRIPTION
"Data value."
::= { dataArray4 58 }

dataValue4_59 OBJECT-TYPE
SYNTAX INTEGER
MAX-ACCESS read-write
STATUS current
DESCRIPTION
"Data value."
::= { dataArray4 59 }

dataValue4_60 OBJECT-TYPE
SYNTAX INTEGER
MAX-ACCESS read-write
STATUS current
DESCRIPTION
"Data value."
::= { dataArray4 60 }

dataValue4_61 OBJECT-TYPE
SYNTAX INTEGER
MAX-ACCESS read-write
STATUS current
DESCRIPTION
"Data value."
::= { dataArray4 61 }

dataValue4_62 OBJECT-TYPE
SYNTAX INTEGER
MAX-ACCESS read-write
STATUS current
DESCRIPTION
"Data value."
::= { dataArray4 62 }

dataValue4_63 OBJECT-TYPE
SYNTAX INTEGER
MAX-ACCESS read-write
STATUS current
DESCRIPTION
"Data value."
::= { dataArray4 63 }

dataValue4_64 OBJECT-TYPE
SYNTAX INTEGER
MAX-ACCESS read-write
STATUS current
DESCRIPTION
"Data value."
::= { dataArray4 64 }

dataValue4_65 OBJECT-TYPE
SYNTAX INTEGER
MAX-ACCESS read-write
STATUS current
DESCRIPTION
"Data value."
::= { dataArray4 65 }

dataValue4_66 OBJECT-TYPE
SYNTAX INTEGER
MAX-ACCESS read-write
STATUS current
DESCRIPTION
"Data value."
::= { dataArray4 66 }

dataValue4_67 OBJECT-TYPE
SYNTAX INTEGER
MAX-ACCESS read-write
STATUS current
DESCRIPTION
"Data value."
::= { dataArray4 67 }

dataValue4_68 OBJECT-TYPE
SYNTAX INTEGER
MAX-ACCESS read-write
STATUS current
DESCRIPTION
"Data value."
::= { dataArray4 68 }

dataValue4_69 OBJECT-TYPE
SYNTAX INTEGER
MAX-ACCESS read-write
STATUS current
DESCRIPTION
"Data value."
::= { dataArray4 69 }

dataValue4_70 OBJECT-TYPE
SYNTAX INTEGER
MAX-ACCESS read-write
STATUS current
DESCRIPTION
"Data value."
::= { dataArray4 70 }

dataValue4_71 OBJECT-TYPE
SYNTAX INTEGER
MAX-ACCESS read-write
STATUS current
DESCRIPTION
"Data value."
::= { dataArray4 71 }

dataValue4_72 OBJECT-TYPE
SYNTAX INTEGER
MAX-ACCESS read-write
STATUS current
DESCRIPTION
"Data value."
::= { dataArray4 72 }

dataValue4_73 OBJECT-TYPE
SYNTAX INTEGER
MAX-ACCESS read-write
STATUS current
DESCRIPTION
"Data value."
::= { dataArray4 73 }

dataValue4_74 OBJECT-TYPE
SYNTAX INTEGER
MAX-ACCESS read-write
STATUS current
DESCRIPTION
"Data value."
::= { dataArray4 74 }

dataValue4_75 OBJECT-TYPE
SYNTAX INTEGER
MAX-ACCESS read-write
STATUS current
DESCRIPTION
"Data value."
::= { dataArray4 75 }

dataValue4_76 OBJECT-TYPE
SYNTAX INTEGER
MAX-ACCESS read-write
STATUS current
DESCRIPTION
"Data value."
::= { dataArray4 76 }

dataValue4_77 OBJECT-TYPE
SYNTAX INTEGER
MAX-ACCESS read-write
STATUS current
DESCRIPTION
"Data value."
::= { dataArray4 77 }

dataValue4_78 OBJECT-TYPE
SYNTAX INTEGER
MAX-ACCESS read-write
STATUS current
DESCRIPTION
"Data value."
::= { dataArray4 78 }

dataValue4_79 OBJECT-TYPE
SYNTAX INTEGER
MAX-ACCESS read-write
STATUS current
DESCRIPTION
"Data value."
::= { dataArray4 79 }

dataValue4_80 OBJECT-TYPE
SYNTAX INTEGER
MAX-ACCESS read-write
STATUS current
DESCRIPTION
"Data value."
::= { dataArray4 80 }

dataValue4_81 OBJECT-TYPE
SYNTAX INTEGER
MAX-ACCESS read-write
STATUS current
DESCRIPTION
"Data value."
::= { dataArray4 81 }

dataValue4_82 OBJECT-TYPE
SYNTAX INTEGER
MAX-ACCESS read-write
STATUS current
DESCRIPTION
"Data value."
::= { dataArray4 82 }

dataValue4_83 OBJECT-TYPE
SYNTAX INTEGER
MAX-ACCESS read-write
STATUS current
DESCRIPTION
"Data value."
::= { dataArray4 83 }

dataValue4_84 OBJECT-TYPE
SYNTAX INTEGER
MAX-ACCESS read-write
STATUS current
DESCRIPTION
"Data value."
::= { dataArray4 84 }

dataValue4_85 OBJECT-TYPE
SYNTAX INTEGER
MAX-ACCESS read-write
STATUS current
DESCRIPTION
"Data value."
::= { dataArray4 85 }

dataValue4_86 OBJECT-TYPE
SYNTAX INTEGER
MAX-ACCESS read-write
STATUS current
DESCRIPTION
"Data value."
::= { dataArray4 86 }

dataValue4_87 OBJECT-TYPE
SYNTAX INTEGER
MAX-ACCESS read-write
STATUS current
DESCRIPTION
"Data value."
::= { dataArray4 87 }

dataValue4_88 OBJECT-TYPE
SYNTAX INTEGER
MAX-ACCESS read-write
STATUS current
DESCRIPTION
"Data value."
::= { dataArray4 88 }

dataValue4_89 OBJECT-TYPE
SYNTAX INTEGER
MAX-ACCESS read-write
STATUS current
DESCRIPTION
"Data value."
::= { dataArray4 89 }

dataValue4_90 OBJECT-TYPE
SYNTAX INTEGER
MAX-ACCESS read-write
STATUS current
DESCRIPTION
"Data value."
::= { dataArray4 90 }

dataValue4_91 OBJECT-TYPE
SYNTAX INTEGER
MAX-ACCESS read-write
STATUS current
DESCRIPTION
"Data value."
::= { dataArray4 91 }

dataValue4_92 OBJECT-TYPE
SYNTAX INTEGER
MAX-ACCESS read-write
STATUS current
DESCRIPTION
"Data value."
::= { dataArray4 92 }

dataValue4_93 OBJECT-TYPE
SYNTAX INTEGER
MAX-ACCESS read-write
STATUS current
DESCRIPTION
"Data value."
::= { dataArray4 93 }

dataValue4_94 OBJECT-TYPE
SYNTAX INTEGER
MAX-ACCESS read-write
STATUS current
DESCRIPTION
"Data value."
::= { dataArray4 94 }

dataValue4_95 OBJECT-TYPE
SYNTAX INTEGER
MAX-ACCESS read-write
STATUS current
DESCRIPTION
"Data value."
::= { dataArray4 95 }

dataValue4_96 OBJECT-TYPE
SYNTAX INTEGER
MAX-ACCESS read-write
STATUS current
DESCRIPTION
"Data value."
::= { dataArray4 96 }

dataValue4_97 OBJECT-TYPE
SYNTAX INTEGER
MAX-ACCESS read-write
STATUS current
DESCRIPTION
"Data value."
::= { dataArray4 97 }

dataValue4_98 OBJECT-TYPE
SYNTAX INTEGER
MAX-ACCESS read-write
STATUS current
DESCRIPTION
"Data value."
::= { dataArray4 98 }

dataValue4_99 OBJECT-TYPE
SYNTAX INTEGER
MAX-ACCESS read-write
STATUS current
DESCRIPTION
"Data value."
::= { dataArray4 99 }

dataValue4_100 OBJECT-TYPE
SYNTAX INTEGER
MAX-ACCESS read-write
STATUS current
DESCRIPTION
"Data value."
::= { dataArray4 100 }

dataValue4_101 OBJECT-TYPE
SYNTAX INTEGER
MAX-ACCESS read-write
STATUS current
DESCRIPTION
"Data value."
::= { dataArray4 101 }

dataValue4_102 OBJECT-TYPE
SYNTAX INTEGER
MAX-ACCESS read-write
STATUS current
DESCRIPTION
"Data value."
::= { dataArray4 102 }

dataValue4_103 OBJECT-TYPE
SYNTAX INTEGER
MAX-ACCESS read-write
STATUS current
DESCRIPTION
"Data value."
::= { dataArray4 103 }

dataValue4_104 OBJECT-TYPE
SYNTAX INTEGER
MAX-ACCESS read-write
STATUS current
DESCRIPTION
"Data value."
::= { dataArray4 104 }

dataValue4_105 OBJECT-TYPE
SYNTAX INTEGER
MAX-ACCESS read-write
STATUS current
DESCRIPTION
"Data value."
::= { dataArray4 105 }

dataValue4_106 OBJECT-TYPE
SYNTAX INTEGER
MAX-ACCESS read-write
STATUS current
DESCRIPTION
"Data value."
::= { dataArray4 106 }

dataValue4_107 OBJECT-TYPE
SYNTAX INTEGER
MAX-ACCESS read-write
STATUS current
DESCRIPTION
"Data value."
::= { dataArray4 107 }

dataValue4_108 OBJECT-TYPE
SYNTAX INTEGER
MAX-ACCESS read-write
STATUS current
DESCRIPTION
"Data value."
::= { dataArray4 108 }

dataValue4_109 OBJECT-TYPE
SYNTAX INTEGER
MAX-ACCESS read-write
STATUS current
DESCRIPTION
"Data value."
::= { dataArray4 109 }

dataValue4_110 OBJECT-TYPE
SYNTAX INTEGER
MAX-ACCESS read-write
STATUS current
DESCRIPTION
"Data value."
::= { dataArray4 110 }

dataValue4_111 OBJECT-TYPE
SYNTAX INTEGER
MAX-ACCESS read-write
STATUS current
DESCRIPTION
"Data value."
::= { dataArray4 111 }

dataValue4_112 OBJECT-TYPE
SYNTAX INTEGER
MAX-ACCESS read-write
STATUS current
DESCRIPTION
"Data value."
::= { dataArray4 112 }

dataValue4_113 OBJECT-TYPE
SYNTAX INTEGER
MAX-ACCESS read-write
STATUS current
DESCRIPTION
"Data value."
::= { dataArray4 113 }

dataValue4_114 OBJECT-TYPE
SYNTAX INTEGER
MAX-ACCESS read-write
STATUS current
DESCRIPTION
"Data value."
::= { dataArray4 114 }

dataValue4_115 OBJECT-TYPE
SYNTAX INTEGER
MAX-ACCESS read-write
STATUS current
DESCRIPTION
"Data value."
::= { dataArray4 115 }

dataValue4_116 OBJECT-TYPE
SYNTAX INTEGER
MAX-ACCESS read-write
STATUS current
DESCRIPTION
"Data value."
::= { dataArray4 116 }

dataValue4_117 OBJECT-TYPE
SYNTAX INTEGER
MAX-ACCESS read-write
STATUS current
DESCRIPTION
"Data value."
::= { dataArray4 117 }

dataValue4_118 OBJECT-TYPE
SYNTAX INTEGER
MAX-ACCESS read-write
STATUS current
DESCRIPTION
"Data value."
::= { dataArray4 118 }

dataValue4_119 OBJECT-TYPE
SYNTAX INTEGER
MAX-ACCESS read-write
STATUS current
DESCRIPTION
"Data value."
::= { dataArray4 119 }

dataValue4_120 OBJECT-TYPE
SYNTAX INTEGER
MAX-ACCESS read-write
STATUS current
DESCRIPTION
"Data value."
::= { dataArray4 120 }

dataValue4_121 OBJECT-TYPE
SYNTAX INTEGER
MAX-ACCESS read-write
STATUS current
DESCRIPTION
"Data value."
::= { dataArray4 121 }

dataValue4_122 OBJECT-TYPE
SYNTAX INTEGER
MAX-ACCESS read-write
STATUS current
DESCRIPTION
"Data value."
::= { dataArray4 122 }

dataValue4_123 OBJECT-TYPE
SYNTAX INTEGER
MAX-ACCESS read-write
STATUS current
DESCRIPTION
"Data value."
::= { dataArray4 123 }

dataValue4_124 OBJECT-TYPE
SYNTAX INTEGER
MAX-ACCESS read-write
STATUS current
DESCRIPTION
"Data value."
::= { dataArray4 124 }

dataValue4_125 OBJECT-TYPE
SYNTAX INTEGER
MAX-ACCESS read-write
STATUS current
DESCRIPTION
"Data value."
::= { dataArray4 125 }

dataValue4_126 OBJECT-TYPE
SYNTAX INTEGER
MAX-ACCESS read-write
STATUS current
DESCRIPTION
"Data value."
::= { dataArray4 126 }

dataValue4_127 OBJECT-TYPE
SYNTAX INTEGER
MAX-ACCESS read-write
STATUS current
DESCRIPTION
"Data value."
::= { dataArray4 127 }

dataValue4_128 OBJECT-TYPE
SYNTAX INTEGER
MAX-ACCESS read-write
STATUS current
DESCRIPTION
"Data value."
::= { dataArray4 128 }

dataValue4_129 OBJECT-TYPE
SYNTAX INTEGER
MAX-ACCESS read-write
STATUS current
DESCRIPTION
"Data value."
::= { dataArray4 129 }

dataValue4_130 OBJECT-TYPE
SYNTAX INTEGER
MAX-ACCESS read-write
STATUS current
DESCRIPTION
"Data value."
::= { dataArray4 130 }

dataValue4_131 OBJECT-TYPE
SYNTAX INTEGER
MAX-ACCESS read-write
STATUS current
DESCRIPTION
"Data value."
::= { dataArray4 131 }

dataValue4_132 OBJECT-TYPE
SYNTAX INTEGER
MAX-ACCESS read-write
STATUS current
DESCRIPTION
"Data value."
::= { dataArray4 132 }

dataValue4_133 OBJECT-TYPE
SYNTAX INTEGER
MAX-ACCESS read-write
STATUS current
DESCRIPTION
"Data value."
::= { dataArray4 133 }

dataValue4_134 OBJECT-TYPE
SYNTAX INTEGER
MAX-ACCESS read-write
STATUS current
DESCRIPTION
"Data value."
::= { dataArray4 134 }

dataValue4_135 OBJECT-TYPE
SYNTAX INTEGER
MAX-ACCESS read-write
STATUS current
DESCRIPTION
"Data value."
::= { dataArray4 135 }

dataValue4_136 OBJECT-TYPE
SYNTAX INTEGER
MAX-ACCESS read-write
STATUS current
DESCRIPTION
"Data value."
::= { dataArray4 136 }

dataValue4_137 OBJECT-TYPE
SYNTAX INTEGER
MAX-ACCESS read-write
STATUS current
DESCRIPTION
"Data value."
::= { dataArray4 137 }

dataValue4_138 OBJECT-TYPE
SYNTAX INTEGER
MAX-ACCESS read-write
STATUS current
DESCRIPTION
"Data value."
::= { dataArray4 138 }

dataValue4_139 OBJECT-TYPE
SYNTAX INTEGER
MAX-ACCESS read-write
STATUS current
DESCRIPTION
"Data value."
::= { dataArray4 139 }

dataValue4_140 OBJECT-TYPE
SYNTAX INTEGER
MAX-ACCESS read-write
STATUS current
DESCRIPTION
"Data value."
::= { dataArray4 140 }

dataValue4_141 OBJECT-TYPE
SYNTAX INTEGER
MAX-ACCESS read-write
STATUS current
DESCRIPTION
"Data value."
::= { dataArray4 141 }

dataValue4_142 OBJECT-TYPE
SYNTAX INTEGER
MAX-ACCESS read-write
STATUS current
DESCRIPTION
"Data value."
::= { dataArray4 142 }

dataValue4_143 OBJECT-TYPE
SYNTAX INTEGER
MAX-ACCESS read-write
STATUS current
DESCRIPTION
"Data value."
::= { dataArray4 143 }

dataValue4_144 OBJECT-TYPE
SYNTAX INTEGER
MAX-ACCESS read-write
STATUS current
DESCRIPTION
"Data value."
::= { dataArray4 144 }

dataValue4_145 OBJECT-TYPE
SYNTAX INTEGER
MAX-ACCESS read-write
STATUS current
DESCRIPTION
"Data value."
::= { dataArray4 145 }

dataValue4_146 OBJECT-TYPE
SYNTAX INTEGER
MAX-ACCESS read-write
STATUS current
DESCRIPTION
"Data value."
::= { dataArray4 146 }

dataValue4_147 OBJECT-TYPE
SYNTAX INTEGER
MAX-ACCESS read-write
STATUS current
DESCRIPTION
"Data value."
::= { dataArray4 147 }

dataValue4_148 OBJECT-TYPE
SYNTAX INTEGER
MAX-ACCESS read-write
STATUS current
DESCRIPTION
"Data value."
::= { dataArray4 148 }

dataValue4_149 OBJECT-TYPE
SYNTAX INTEGER
MAX-ACCESS read-write
STATUS current
DESCRIPTION
"Data value."
::= { dataArray4 149 }

dataValue4_150 OBJECT-TYPE
SYNTAX INTEGER
MAX-ACCESS read-write
STATUS current
DESCRIPTION
"Data value."
::= { dataArray4 150 }

dataValue4_151 OBJECT-TYPE
SYNTAX INTEGER
MAX-ACCESS read-write
STATUS current
DESCRIPTION
"Data value."
::= { dataArray4 151 }

dataValue4_152 OBJECT-TYPE
SYNTAX INTEGER
MAX-ACCESS read-write
STATUS current
DESCRIPTION
"Data value."
::= { dataArray4 152 }

dataValue4_153 OBJECT-TYPE
SYNTAX INTEGER
MAX-ACCESS read-write
STATUS current
DESCRIPTION
"Data value."
::= { dataArray4 153 }

dataValue4_154 OBJECT-TYPE
SYNTAX INTEGER
MAX-ACCESS read-write
STATUS current
DESCRIPTION
"Data value."
::= { dataArray4 154 }

dataValue4_155 OBJECT-TYPE
SYNTAX INTEGER
MAX-ACCESS read-write
STATUS current
DESCRIPTION
"Data value."
::= { dataArray4 155 }

dataValue4_156 OBJECT-TYPE
SYNTAX INTEGER
MAX-ACCESS read-write
STATUS current
DESCRIPTION
"Data value."
::= { dataArray4 156 }

dataValue4_157 OBJECT-TYPE
SYNTAX INTEGER
MAX-ACCESS read-write
STATUS current
DESCRIPTION
"Data value."
::= { dataArray4 157 }

dataValue4_158 OBJECT-TYPE
SYNTAX INTEGER
MAX-ACCESS read-write
STATUS current
DESCRIPTION
"Data value."
::= { dataArray4 158 }

dataValue4_159 OBJECT-TYPE
SYNTAX INTEGER
MAX-ACCESS read-write
STATUS current
DESCRIPTION
"Data value."
::= { dataArray4 159 }

dataValue4_160 OBJECT-TYPE
SYNTAX INTEGER
MAX-ACCESS read-write
STATUS current
DESCRIPTION
"Data value."
::= { dataArray4 160 }

dataValue4_161 OBJECT-TYPE
SYNTAX INTEGER
MAX-ACCESS read-write
STATUS current
DESCRIPTION
"Data value."
::= { dataArray4 161 }

dataValue4_162 OBJECT-TYPE
SYNTAX INTEGER
MAX-ACCESS read-write
STATUS current
DESCRIPTION
"Data value."
::= { dataArray4 162 }

dataValue4_163 OBJECT-TYPE
SYNTAX INTEGER
MAX-ACCESS read-write
STATUS current
DESCRIPTION
"Data value."
::= { dataArray4 163 }

dataValue4_164 OBJECT-TYPE
SYNTAX INTEGER
MAX-ACCESS read-write
STATUS current
DESCRIPTION
"Data value."
::= { dataArray4 164 }

dataValue4_165 OBJECT-TYPE
SYNTAX INTEGER
MAX-ACCESS read-write
STATUS current
DESCRIPTION
"Data value."
::= { dataArray4 165 }

dataValue4_166 OBJECT-TYPE
SYNTAX INTEGER
MAX-ACCESS read-write
STATUS current
DESCRIPTION
"Data value."
::= { dataArray4 166 }

dataValue4_167 OBJECT-TYPE
SYNTAX INTEGER
MAX-ACCESS read-write
STATUS current
DESCRIPTION
"Data value."
::= { dataArray4 167 }

dataValue4_168 OBJECT-TYPE
SYNTAX INTEGER
MAX-ACCESS read-write
STATUS current
DESCRIPTION
"Data value."
::= { dataArray4 168 }

dataValue4_169 OBJECT-TYPE
SYNTAX INTEGER
MAX-ACCESS read-write
STATUS current
DESCRIPTION
"Data value."
::= { dataArray4 169 }

dataValue4_170 OBJECT-TYPE
SYNTAX INTEGER
MAX-ACCESS read-write
STATUS current
DESCRIPTION
"Data value."
::= { dataArray4 170 }

dataValue4_171 OBJECT-TYPE
SYNTAX INTEGER
MAX-ACCESS read-write
STATUS current
DESCRIPTION
"Data value."
::= { dataArray4 171 }

dataValue4_172 OBJECT-TYPE
SYNTAX INTEGER
MAX-ACCESS read-write
STATUS current
DESCRIPTION
"Data value."
::= { dataArray4 172 }

dataValue4_173 OBJECT-TYPE
SYNTAX INTEGER
MAX-ACCESS read-write
STATUS current
DESCRIPTION
"Data value."
::= { dataArray4 173 }

dataValue4_174 OBJECT-TYPE
SYNTAX INTEGER
MAX-ACCESS read-write
STATUS current
DESCRIPTION
"Data value."
::= { dataArray4 174 }

dataValue4_175 OBJECT-TYPE
SYNTAX INTEGER
MAX-ACCESS read-write
STATUS current
DESCRIPTION
"Data value."
::= { dataArray4 175 }

dataValue4_176 OBJECT-TYPE
SYNTAX INTEGER
MAX-ACCESS read-write
STATUS current
DESCRIPTION
"Data value."
::= { dataArray4 176 }

dataValue4_177 OBJECT-TYPE
SYNTAX INTEGER
MAX-ACCESS read-write
STATUS current
DESCRIPTION
"Data value."
::= { dataArray4 177 }

dataValue4_178 OBJECT-TYPE
SYNTAX INTEGER
MAX-ACCESS read-write
STATUS current
DESCRIPTION
"Data value."
::= { dataArray4 178 }

dataValue4_179 OBJECT-TYPE
SYNTAX INTEGER
MAX-ACCESS read-write
STATUS current
DESCRIPTION
"Data value."
::= { dataArray4 179 }

dataValue4_180 OBJECT-TYPE
SYNTAX INTEGER
MAX-ACCESS read-write
STATUS current
DESCRIPTION
"Data value."
::= { dataArray4 180 }

dataValue4_181 OBJECT-TYPE
SYNTAX INTEGER
MAX-ACCESS read-write
STATUS current
DESCRIPTION
"Data value."
::= { dataArray4 181 }

dataValue4_182 OBJECT-TYPE
SYNTAX INTEGER
MAX-ACCESS read-write
STATUS current
DESCRIPTION
"Data value."
::= { dataArray4 182 }

dataValue4_183 OBJECT-TYPE
SYNTAX INTEGER
MAX-ACCESS read-write
STATUS current
DESCRIPTION
"Data value."
::= { dataArray4 183 }

dataValue4_184 OBJECT-TYPE
SYNTAX INTEGER
MAX-ACCESS read-write
STATUS current
DESCRIPTION
"Data value."
::= { dataArray4 184 }

dataValue4_185 OBJECT-TYPE
SYNTAX INTEGER
MAX-ACCESS read-write
STATUS current
DESCRIPTION
"Data value."
::= { dataArray4 185 }

dataValue4_186 OBJECT-TYPE
SYNTAX INTEGER
MAX-ACCESS read-write
STATUS current
DESCRIPTION
"Data value."
::= { dataArray4 186 }

dataValue4_187 OBJECT-TYPE
SYNTAX INTEGER
MAX-ACCESS read-write
STATUS current
DESCRIPTION
"Data value."
::= { dataArray4 187 }

dataValue4_188 OBJECT-TYPE
SYNTAX INTEGER
MAX-ACCESS read-write
STATUS current
DESCRIPTION
"Data value."
::= { dataArray4 188 }

dataValue4_189 OBJECT-TYPE
SYNTAX INTEGER
MAX-ACCESS read-write
STATUS current
DESCRIPTION
"Data value."
::= { dataArray4 189 }

dataValue4_190 OBJECT-TYPE
SYNTAX INTEGER
MAX-ACCESS read-write
STATUS current
DESCRIPTION
"Data value."
::= { dataArray4 190 }

dataValue4_191 OBJECT-TYPE
SYNTAX INTEGER
MAX-ACCESS read-write
STATUS current
DESCRIPTION
"Data value."
::= { dataArray4 191 }

dataValue4_192 OBJECT-TYPE
SYNTAX INTEGER
MAX-ACCESS read-write
STATUS current
DESCRIPTION
"Data value."
::= { dataArray4 192 }

dataValue4_193 OBJECT-TYPE
SYNTAX INTEGER
MAX-ACCESS read-write
STATUS current
DESCRIPTION
"Data value."
::= { dataArray4 193 }

dataValue4_194 OBJECT-TYPE
SYNTAX INTEGER
MAX-ACCESS read-write
STATUS current
DESCRIPTION
"Data value."
::= { dataArray4 194 }

dataValue4_195 OBJECT-TYPE
SYNTAX INTEGER
MAX-ACCESS read-write
STATUS current
DESCRIPTION
"Data value."
::= { dataArray4 195 }

dataValue4_196 OBJECT-TYPE
SYNTAX INTEGER
MAX-ACCESS read-write
STATUS current
DESCRIPTION
"Data value."
::= { dataArray4 196 }

dataValue4_197 OBJECT-TYPE
SYNTAX INTEGER
MAX-ACCESS read-write
STATUS current
DESCRIPTION
"Data value."
::= { dataArray4 197 }

dataValue4_198 OBJECT-TYPE
SYNTAX INTEGER
MAX-ACCESS read-write
STATUS current
DESCRIPTION
"Data value."
::= { dataArray4 198 }

dataValue4_199 OBJECT-TYPE
SYNTAX INTEGER
MAX-ACCESS read-write
STATUS current
DESCRIPTION
"Data value."
::= { dataArray4 199 }

dataValue4_200 OBJECT-TYPE
SYNTAX INTEGER
MAX-ACCESS read-write
STATUS current
DESCRIPTION
"Data value."
::= { dataArray4 200 }

dataValue4_201 OBJECT-TYPE
SYNTAX INTEGER
MAX-ACCESS read-write
STATUS current
DESCRIPTION
"Data value."
::= { dataArray4 201 }

dataValue4_202 OBJECT-TYPE
SYNTAX INTEGER
MAX-ACCESS read-write
STATUS current
DESCRIPTION
"Data value."
::= { dataArray4 202 }

dataValue4_203 OBJECT-TYPE
SYNTAX INTEGER
MAX-ACCESS read-write
STATUS current
DESCRIPTION
"Data value."
::= { dataArray4 203 }

dataValue4_204 OBJECT-TYPE
SYNTAX INTEGER
MAX-ACCESS read-write
STATUS current
DESCRIPTION
"Data value."
::= { dataArray4 204 }

dataValue4_205 OBJECT-TYPE
SYNTAX INTEGER
MAX-ACCESS read-write
STATUS current
DESCRIPTION
"Data value."
::= { dataArray4 205 }

dataValue4_206 OBJECT-TYPE
SYNTAX INTEGER
MAX-ACCESS read-write
STATUS current
DESCRIPTION
"Data value."
::= { dataArray4 206 }

dataValue4_207 OBJECT-TYPE
SYNTAX INTEGER
MAX-ACCESS read-write
STATUS current
DESCRIPTION
"Data value."
::= { dataArray4 207 }

dataValue4_208 OBJECT-TYPE
SYNTAX INTEGER
MAX-ACCESS read-write
STATUS current
DESCRIPTION
"Data value."
::= { dataArray4 208 }

dataValue4_209 OBJECT-TYPE
SYNTAX INTEGER
MAX-ACCESS read-write
STATUS current
DESCRIPTION
"Data value."
::= { dataArray4 209 }

dataValue4_210 OBJECT-TYPE
SYNTAX INTEGER
MAX-ACCESS read-write
STATUS current
DESCRIPTION
"Data value."
::= { dataArray4 210 }

dataValue4_211 OBJECT-TYPE
SYNTAX INTEGER
MAX-ACCESS read-write
STATUS current
DESCRIPTION
"Data value."
::= { dataArray4 211 }

dataValue4_212 OBJECT-TYPE
SYNTAX INTEGER
MAX-ACCESS read-write
STATUS current
DESCRIPTION
"Data value."
::= { dataArray4 212 }

dataValue4_213 OBJECT-TYPE
SYNTAX INTEGER
MAX-ACCESS read-write
STATUS current
DESCRIPTION
"Data value."
::= { dataArray4 213 }

dataValue4_214 OBJECT-TYPE
SYNTAX INTEGER
MAX-ACCESS read-write
STATUS current
DESCRIPTION
"Data value."
::= { dataArray4 214 }

dataValue4_215 OBJECT-TYPE
SYNTAX INTEGER
MAX-ACCESS read-write
STATUS current
DESCRIPTION
"Data value."
::= { dataArray4 215 }

dataValue4_216 OBJECT-TYPE
SYNTAX INTEGER
MAX-ACCESS read-write
STATUS current
DESCRIPTION
"Data value."
::= { dataArray4 216 }

dataValue4_217 OBJECT-TYPE
SYNTAX INTEGER
MAX-ACCESS read-write
STATUS current
DESCRIPTION
"Data value."
::= { dataArray4 217 }

dataValue4_218 OBJECT-TYPE
SYNTAX INTEGER
MAX-ACCESS read-write
STATUS current
DESCRIPTION
"Data value."
::= { dataArray4 218 }

dataValue4_219 OBJECT-TYPE
SYNTAX INTEGER
MAX-ACCESS read-write
STATUS current
DESCRIPTION
"Data value."
::= { dataArray4 219 }

dataValue4_220 OBJECT-TYPE
SYNTAX INTEGER
MAX-ACCESS read-write
STATUS current
DESCRIPTION
"Data value."
::= { dataArray4 220 }

dataValue4_221 OBJECT-TYPE
SYNTAX INTEGER
MAX-ACCESS read-write
STATUS current
DESCRIPTION
"Data value."
::= { dataArray4 221 }

dataValue4_222 OBJECT-TYPE
SYNTAX INTEGER
MAX-ACCESS read-write
STATUS current
DESCRIPTION
"Data value."
::= { dataArray4 222 }

dataValue4_223 OBJECT-TYPE
SYNTAX INTEGER
MAX-ACCESS read-write
STATUS current
DESCRIPTION
"Data value."
::= { dataArray4 223 }

dataValue4_224 OBJECT-TYPE
SYNTAX INTEGER
MAX-ACCESS read-write
STATUS current
DESCRIPTION
"Data value."
::= { dataArray4 224 }

dataValue4_225 OBJECT-TYPE
SYNTAX INTEGER
MAX-ACCESS read-write
STATUS current
DESCRIPTION
"Data value."
::= { dataArray4 225 }

dataValue4_226 OBJECT-TYPE
SYNTAX INTEGER
MAX-ACCESS read-write
STATUS current
DESCRIPTION
"Data value."
::= { dataArray4 226 }

dataValue4_227 OBJECT-TYPE
SYNTAX INTEGER
MAX-ACCESS read-write
STATUS current
DESCRIPTION
"Data value."
::= { dataArray4 227 }

dataValue4_228 OBJECT-TYPE
SYNTAX INTEGER
MAX-ACCESS read-write
STATUS current
DESCRIPTION
"Data value."
::= { dataArray4 228 }

dataValue4_229 OBJECT-TYPE
SYNTAX INTEGER
MAX-ACCESS read-write
STATUS current
DESCRIPTION
"Data value."
::= { dataArray4 229 }

dataValue4_230 OBJECT-TYPE
SYNTAX INTEGER
MAX-ACCESS read-write
STATUS current
DESCRIPTION
"Data value."
::= { dataArray4 230 }

dataValue4_231 OBJECT-TYPE
SYNTAX INTEGER
MAX-ACCESS read-write
STATUS current
DESCRIPTION
"Data value."
::= { dataArray4 231 }

dataValue4_232 OBJECT-TYPE
SYNTAX INTEGER
MAX-ACCESS read-write
STATUS current
DESCRIPTION
"Data value."
::= { dataArray4 232 }

dataValue4_233 OBJECT-TYPE
SYNTAX INTEGER
MAX-ACCESS read-write
STATUS current
DESCRIPTION
"Data value."
::= { dataArray4 233 }

dataValue4_234 OBJECT-TYPE
SYNTAX INTEGER
MAX-ACCESS read-write
STATUS current
DESCRIPTION
"Data value."
::= { dataArray4 234 }

dataValue4_235 OBJECT-TYPE
SYNTAX INTEGER
MAX-ACCESS read-write
STATUS current
DESCRIPTION
"Data value."
::= { dataArray4 235 }

dataValue4_236 OBJECT-TYPE
SYNTAX INTEGER
MAX-ACCESS read-write
STATUS current
DESCRIPTION
"Data value."
::= { dataArray4 236 }

dataValue4_237 OBJECT-TYPE
SYNTAX INTEGER
MAX-ACCESS read-write
STATUS current
DESCRIPTION
"Data value."
::= { dataArray4 237 }

dataValue4_238 OBJECT-TYPE
SYNTAX INTEGER
MAX-ACCESS read-write
STATUS current
DESCRIPTION
"Data value."
::= { dataArray4 238 }

dataValue4_239 OBJECT-TYPE
SYNTAX INTEGER
MAX-ACCESS read-write
STATUS current
DESCRIPTION
"Data value."
::= { dataArray4 239 }

dataValue4_240 OBJECT-TYPE
SYNTAX INTEGER
MAX-ACCESS read-write
STATUS current
DESCRIPTION
"Data value."
::= { dataArray4 240 }

dataValue4_241 OBJECT-TYPE
SYNTAX INTEGER
MAX-ACCESS read-write
STATUS current
DESCRIPTION
"Data value."
::= { dataArray4 241 }

dataValue4_242 OBJECT-TYPE
SYNTAX INTEGER
MAX-ACCESS read-write
STATUS current
DESCRIPTION
"Data value."
::= { dataArray4 242 }

dataValue4_243 OBJECT-TYPE
SYNTAX INTEGER
MAX-ACCESS read-write
STATUS current
DESCRIPTION
"Data value."
::= { dataArray4 243 }

dataValue4_244 OBJECT-TYPE
SYNTAX INTEGER
MAX-ACCESS read-write
STATUS current
DESCRIPTION
"Data value."
::= { dataArray4 244 }

dataValue4_245 OBJECT-TYPE
SYNTAX INTEGER
MAX-ACCESS read-write
STATUS current
DESCRIPTION
"Data value."
::= { dataArray4 245 }

dataValue4_246 OBJECT-TYPE
SYNTAX INTEGER
MAX-ACCESS read-write
STATUS current
DESCRIPTION
"Data value."
::= { dataArray4 246 }

dataValue4_247 OBJECT-TYPE
SYNTAX INTEGER
MAX-ACCESS read-write
STATUS current
DESCRIPTION
"Data value."
::= { dataArray4 247 }

dataValue4_248 OBJECT-TYPE
SYNTAX INTEGER
MAX-ACCESS read-write
STATUS current
DESCRIPTION
"Data value."
::= { dataArray4 248 }

dataValue4_249 OBJECT-TYPE
SYNTAX INTEGER
MAX-ACCESS read-write
STATUS current
DESCRIPTION
"Data value."
::= { dataArray4 249 }

dataValue4_250 OBJECT-TYPE
SYNTAX INTEGER
MAX-ACCESS read-write
STATUS current
DESCRIPTION
"Data value."
::= { dataArray4 250 }

dataValue4_251 OBJECT-TYPE
SYNTAX INTEGER
MAX-ACCESS read-write
STATUS current
DESCRIPTION
"Data value."
::= { dataArray4 251 }

dataValue4_252 OBJECT-TYPE
SYNTAX INTEGER
MAX-ACCESS read-write
STATUS current
DESCRIPTION
"Data value."
::= { dataArray4 252 }

dataValue4_253 OBJECT-TYPE
SYNTAX INTEGER
MAX-ACCESS read-write
STATUS current
DESCRIPTION
"Data value."
::= { dataArray4 253 }

dataValue4_254 OBJECT-TYPE
SYNTAX INTEGER
MAX-ACCESS read-write
STATUS current
DESCRIPTION
"Data value."
::= { dataArray4 254 }

dataValue4_255 OBJECT-TYPE
SYNTAX INTEGER
MAX-ACCESS read-write
STATUS current
DESCRIPTION
"Data value."
::= { dataArray4 255 }

dataValue4_256 OBJECT-TYPE
SYNTAX INTEGER
MAX-ACCESS read-write
STATUS current
DESCRIPTION
"Data value."
::= { dataArray4 256 }

dataValue4_257 OBJECT-TYPE
SYNTAX INTEGER
MAX-ACCESS read-write
STATUS current
DESCRIPTION
"Data value."
::= { dataArray4 257 }

dataValue4_258 OBJECT-TYPE
SYNTAX INTEGER
MAX-ACCESS read-write
STATUS current
DESCRIPTION
"Data value."
::= { dataArray4 258 }

dataValue4_259 OBJECT-TYPE
SYNTAX INTEGER
MAX-ACCESS read-write
STATUS current
DESCRIPTION
"Data value."
::= { dataArray4 259 }

dataValue4_260 OBJECT-TYPE
SYNTAX INTEGER
MAX-ACCESS read-write
STATUS current
DESCRIPTION
"Data value."
::= { dataArray4 260 }

dataValue4_261 OBJECT-TYPE
SYNTAX INTEGER
MAX-ACCESS read-write
STATUS current
DESCRIPTION
"Data value."
::= { dataArray4 261 }

dataValue4_262 OBJECT-TYPE
SYNTAX INTEGER
MAX-ACCESS read-write
STATUS current
DESCRIPTION
"Data value."
::= { dataArray4 262 }

dataValue4_263 OBJECT-TYPE
SYNTAX INTEGER
MAX-ACCESS read-write
STATUS current
DESCRIPTION
"Data value."
::= { dataArray4 263 }

dataValue4_264 OBJECT-TYPE
SYNTAX INTEGER
MAX-ACCESS read-write
STATUS current
DESCRIPTION
"Data value."
::= { dataArray4 264 }

dataValue4_265 OBJECT-TYPE
SYNTAX INTEGER
MAX-ACCESS read-write
STATUS current
DESCRIPTION
"Data value."
::= { dataArray4 265 }

dataValue4_266 OBJECT-TYPE
SYNTAX INTEGER
MAX-ACCESS read-write
STATUS current
DESCRIPTION
"Data value."
::= { dataArray4 266 }

dataValue4_267 OBJECT-TYPE
SYNTAX INTEGER
MAX-ACCESS read-write
STATUS current
DESCRIPTION
"Data value."
::= { dataArray4 267 }

dataValue4_268 OBJECT-TYPE
SYNTAX INTEGER
MAX-ACCESS read-write
STATUS current
DESCRIPTION
"Data value."
::= { dataArray4 268 }

dataValue4_269 OBJECT-TYPE
SYNTAX INTEGER
MAX-ACCESS read-write
STATUS current
DESCRIPTION
"Data value."
::= { dataArray4 269 }

dataValue4_270 OBJECT-TYPE
SYNTAX INTEGER
MAX-ACCESS read-write
STATUS current
DESCRIPTION
"Data value."
::= { dataArray4 270 }

dataValue4_271 OBJECT-TYPE
SYNTAX INTEGER
MAX-ACCESS read-write
STATUS current
DESCRIPTION
"Data value."
::= { dataArray4 271 }

dataValue4_272 OBJECT-TYPE
SYNTAX INTEGER
MAX-ACCESS read-write
STATUS current
DESCRIPTION
"Data value."
::= { dataArray4 272 }

dataValue4_273 OBJECT-TYPE
SYNTAX INTEGER
MAX-ACCESS read-write
STATUS current
DESCRIPTION
"Data value."
::= { dataArray4 273 }

dataValue4_274 OBJECT-TYPE
SYNTAX INTEGER
MAX-ACCESS read-write
STATUS current
DESCRIPTION
"Data value."
::= { dataArray4 274 }

dataValue4_275 OBJECT-TYPE
SYNTAX INTEGER
MAX-ACCESS read-write
STATUS current
DESCRIPTION
"Data value."
::= { dataArray4 275 }

dataValue4_276 OBJECT-TYPE
SYNTAX INTEGER
MAX-ACCESS read-write
STATUS current
DESCRIPTION
"Data value."
::= { dataArray4 276 }

dataValue4_277 OBJECT-TYPE
SYNTAX INTEGER
MAX-ACCESS read-write
STATUS current
DESCRIPTION
"Data value."
::= { dataArray4 277 }

dataValue4_278 OBJECT-TYPE
SYNTAX INTEGER
MAX-ACCESS read-write
STATUS current
DESCRIPTION
"Data value."
::= { dataArray4 278 }

dataValue4_279 OBJECT-TYPE
SYNTAX INTEGER
MAX-ACCESS read-write
STATUS current
DESCRIPTION
"Data value."
::= { dataArray4 279 }

dataValue4_280 OBJECT-TYPE
SYNTAX INTEGER
MAX-ACCESS read-write
STATUS current
DESCRIPTION
"Data value."
::= { dataArray4 280 }

dataValue4_281 OBJECT-TYPE
SYNTAX INTEGER
MAX-ACCESS read-write
STATUS current
DESCRIPTION
"Data value."
::= { dataArray4 281 }

dataValue4_282 OBJECT-TYPE
SYNTAX INTEGER
MAX-ACCESS read-write
STATUS current
DESCRIPTION
"Data value."
::= { dataArray4 282 }

dataValue4_283 OBJECT-TYPE
SYNTAX INTEGER
MAX-ACCESS read-write
STATUS current
DESCRIPTION
"Data value."
::= { dataArray4 283 }

dataValue4_284 OBJECT-TYPE
SYNTAX INTEGER
MAX-ACCESS read-write
STATUS current
DESCRIPTION
"Data value."
::= { dataArray4 284 }

dataValue4_285 OBJECT-TYPE
SYNTAX INTEGER
MAX-ACCESS read-write
STATUS current
DESCRIPTION
"Data value."
::= { dataArray4 285 }

dataValue4_286 OBJECT-TYPE
SYNTAX INTEGER
MAX-ACCESS read-write
STATUS current
DESCRIPTION
"Data value."
::= { dataArray4 286 }

dataValue4_287 OBJECT-TYPE
SYNTAX INTEGER
MAX-ACCESS read-write
STATUS current
DESCRIPTION
"Data value."
::= { dataArray4 287 }

dataValue4_288 OBJECT-TYPE
SYNTAX INTEGER
MAX-ACCESS read-write
STATUS current
DESCRIPTION
"Data value."
::= { dataArray4 288 }

dataValue4_289 OBJECT-TYPE
SYNTAX INTEGER
MAX-ACCESS read-write
STATUS current
DESCRIPTION
"Data value."
::= { dataArray4 289 }

dataValue4_290 OBJECT-TYPE
SYNTAX INTEGER
MAX-ACCESS read-write
STATUS current
DESCRIPTION
"Data value."
::= { dataArray4 290 }

dataValue4_291 OBJECT-TYPE
SYNTAX INTEGER
MAX-ACCESS read-write
STATUS current
DESCRIPTION
"Data value."
::= { dataArray4 291 }

dataValue4_292 OBJECT-TYPE
SYNTAX INTEGER
MAX-ACCESS read-write
STATUS current
DESCRIPTION
"Data value."
::= { dataArray4 292 }

dataValue4_293 OBJECT-TYPE
SYNTAX INTEGER
MAX-ACCESS read-write
STATUS current
DESCRIPTION
"Data value."
::= { dataArray4 293 }

dataValue4_294 OBJECT-TYPE
SYNTAX INTEGER
MAX-ACCESS read-write
STATUS current
DESCRIPTION
"Data value."
::= { dataArray4 294 }

dataValue4_295 OBJECT-TYPE
SYNTAX INTEGER
MAX-ACCESS read-write
STATUS current
DESCRIPTION
"Data value."
::= { dataArray4 295 }

dataValue4_296 OBJECT-TYPE
SYNTAX INTEGER
MAX-ACCESS read-write
STATUS current
DESCRIPTION
"Data value."
::= { dataArray4 296 }

dataValue4_297 OBJECT-TYPE
SYNTAX INTEGER
MAX-ACCESS read-write
STATUS current
DESCRIPTION
"Data value."
::= { dataArray4 297 }

dataValue4_298 OBJECT-TYPE
SYNTAX INTEGER
MAX-ACCESS read-write
STATUS current
DESCRIPTION
"Data value."
::= { dataArray4 298 }

dataValue4_299 OBJECT-TYPE
SYNTAX INTEGER
MAX-ACCESS read-write
STATUS current
DESCRIPTION
"Data value."
::= { dataArray4 299 }

dataValue4_300 OBJECT-TYPE
SYNTAX INTEGER
MAX-ACCESS read-write
STATUS current
DESCRIPTION
"Data value."
::= { dataArray4 300 }

dataValue4_301 OBJECT-TYPE
SYNTAX INTEGER
MAX-ACCESS read-write
STATUS current
DESCRIPTION
"Data value."
::= { dataArray4 301 }

dataValue4_302 OBJECT-TYPE
SYNTAX INTEGER
MAX-ACCESS read-write
STATUS current
DESCRIPTION
"Data value."
::= { dataArray4 302 }

dataValue4_303 OBJECT-TYPE
SYNTAX INTEGER
MAX-ACCESS read-write
STATUS current
DESCRIPTION
"Data value."
::= { dataArray4 303 }

dataValue4_304 OBJECT-TYPE
SYNTAX INTEGER
MAX-ACCESS read-write
STATUS current
DESCRIPTION
"Data value."
::= { dataArray4 304 }

dataValue4_305 OBJECT-TYPE
SYNTAX INTEGER
MAX-ACCESS read-write
STATUS current
DESCRIPTION
"Data value."
::= { dataArray4 305 }

dataValue4_306 OBJECT-TYPE
SYNTAX INTEGER
MAX-ACCESS read-write
STATUS current
DESCRIPTION
"Data value."
::= { dataArray4 306 }

dataValue4_307 OBJECT-TYPE
SYNTAX INTEGER
MAX-ACCESS read-write
STATUS current
DESCRIPTION
"Data value."
::= { dataArray4 307 }

dataValue4_308 OBJECT-TYPE
SYNTAX INTEGER
MAX-ACCESS read-write
STATUS current
DESCRIPTION
"Data value."
::= { dataArray4 308 }

dataValue4_309 OBJECT-TYPE
SYNTAX INTEGER
MAX-ACCESS read-write
STATUS current
DESCRIPTION
"Data value."
::= { dataArray4 309 }

dataValue4_310 OBJECT-TYPE
SYNTAX INTEGER
MAX-ACCESS read-write
STATUS current
DESCRIPTION
"Data value."
::= { dataArray4 310 }

dataValue4_311 OBJECT-TYPE
SYNTAX INTEGER
MAX-ACCESS read-write
STATUS current
DESCRIPTION
"Data value."
::= { dataArray4 311 }

dataValue4_312 OBJECT-TYPE
SYNTAX INTEGER
MAX-ACCESS read-write
STATUS current
DESCRIPTION
"Data value."
::= { dataArray4 312 }

dataValue4_313 OBJECT-TYPE
SYNTAX INTEGER
MAX-ACCESS read-write
STATUS current
DESCRIPTION
"Data value."
::= { dataArray4 313 }

dataValue4_314 OBJECT-TYPE
SYNTAX INTEGER
MAX-ACCESS read-write
STATUS current
DESCRIPTION
"Data value."
::= { dataArray4 314 }

dataValue4_315 OBJECT-TYPE
SYNTAX INTEGER
MAX-ACCESS read-write
STATUS current
DESCRIPTION
"Data value."
::= { dataArray4 315 }

dataValue4_316 OBJECT-TYPE
SYNTAX INTEGER
MAX-ACCESS read-write
STATUS current
DESCRIPTION
"Data value."
::= { dataArray4 316 }

dataValue4_317 OBJECT-TYPE
SYNTAX INTEGER
MAX-ACCESS read-write
STATUS current
DESCRIPTION
"Data value."
::= { dataArray4 317 }

dataValue4_318 OBJECT-TYPE
SYNTAX INTEGER
MAX-ACCESS read-write
STATUS current
DESCRIPTION
"Data value."
::= { dataArray4 318 }

dataValue4_319 OBJECT-TYPE
SYNTAX INTEGER
MAX-ACCESS read-write
STATUS current
DESCRIPTION
"Data value."
::= { dataArray4 319 }

dataValue4_320 OBJECT-TYPE
SYNTAX INTEGER
MAX-ACCESS read-write
STATUS current
DESCRIPTION
"Data value."
::= { dataArray4 320 }

dataValue4_321 OBJECT-TYPE
SYNTAX INTEGER
MAX-ACCESS read-write
STATUS current
DESCRIPTION
"Data value."
::= { dataArray4 321 }

dataValue4_322 OBJECT-TYPE
SYNTAX INTEGER
MAX-ACCESS read-write
STATUS current
DESCRIPTION
"Data value."
::= { dataArray4 322 }

dataValue4_323 OBJECT-TYPE
SYNTAX INTEGER
MAX-ACCESS read-write
STATUS current
DESCRIPTION
"Data value."
::= { dataArray4 323 }

dataValue4_324 OBJECT-TYPE
SYNTAX INTEGER
MAX-ACCESS read-write
STATUS current
DESCRIPTION
"Data value."
::= { dataArray4 324 }

dataValue4_325 OBJECT-TYPE
SYNTAX INTEGER
MAX-ACCESS read-write
STATUS current
DESCRIPTION
"Data value."
::= { dataArray4 325 }

dataValue4_326 OBJECT-TYPE
SYNTAX INTEGER
MAX-ACCESS read-write
STATUS current
DESCRIPTION
"Data value."
::= { dataArray4 326 }

dataValue4_327 OBJECT-TYPE
SYNTAX INTEGER
MAX-ACCESS read-write
STATUS current
DESCRIPTION
"Data value."
::= { dataArray4 327 }

dataValue4_328 OBJECT-TYPE
SYNTAX INTEGER
MAX-ACCESS read-write
STATUS current
DESCRIPTION
"Data value."
::= { dataArray4 328 }

dataValue4_329 OBJECT-TYPE
SYNTAX INTEGER
MAX-ACCESS read-write
STATUS current
DESCRIPTION
"Data value."
::= { dataArray4 329 }

dataValue4_330 OBJECT-TYPE
SYNTAX INTEGER
MAX-ACCESS read-write
STATUS current
DESCRIPTION
"Data value."
::= { dataArray4 330 }

dataValue4_331 OBJECT-TYPE
SYNTAX INTEGER
MAX-ACCESS read-write
STATUS current
DESCRIPTION
"Data value."
::= { dataArray4 331 }

dataValue4_332 OBJECT-TYPE
SYNTAX INTEGER
MAX-ACCESS read-write
STATUS current
DESCRIPTION
"Data value."
::= { dataArray4 332 }

dataValue4_333 OBJECT-TYPE
SYNTAX INTEGER
MAX-ACCESS read-write
STATUS current
DESCRIPTION
"Data value."
::= { dataArray4 333 }

dataValue4_334 OBJECT-TYPE
SYNTAX INTEGER
MAX-ACCESS read-write
STATUS current
DESCRIPTION
"Data value."
::= { dataArray4 334 }

dataValue4_335 OBJECT-TYPE
SYNTAX INTEGER
MAX-ACCESS read-write
STATUS current
DESCRIPTION
"Data value."
::= { dataArray4 335 }

dataValue4_336 OBJECT-TYPE
SYNTAX INTEGER
MAX-ACCESS read-write
STATUS current
DESCRIPTION
"Data value."
::= { dataArray4 336 }

dataValue4_337 OBJECT-TYPE
SYNTAX INTEGER
MAX-ACCESS read-write
STATUS current
DESCRIPTION
"Data value."
::= { dataArray4 337 }

dataValue4_338 OBJECT-TYPE
SYNTAX INTEGER
MAX-ACCESS read-write
STATUS current
DESCRIPTION
"Data value."
::= { dataArray4 338 }

dataValue4_339 OBJECT-TYPE
SYNTAX INTEGER
MAX-ACCESS read-write
STATUS current
DESCRIPTION
"Data value."
::= { dataArray4 339 }

dataValue4_340 OBJECT-TYPE
SYNTAX INTEGER
MAX-ACCESS read-write
STATUS current
DESCRIPTION
"Data value."
::= { dataArray4 340 }

dataValue4_341 OBJECT-TYPE
SYNTAX INTEGER
MAX-ACCESS read-write
STATUS current
DESCRIPTION
"Data value."
::= { dataArray4 341 }

dataValue4_342 OBJECT-TYPE
SYNTAX INTEGER
MAX-ACCESS read-write
STATUS current
DESCRIPTION
"Data value."
::= { dataArray4 342 }

dataValue4_343 OBJECT-TYPE
SYNTAX INTEGER
MAX-ACCESS read-write
STATUS current
DESCRIPTION
"Data value."
::= { dataArray4 343 }

dataValue4_344 OBJECT-TYPE
SYNTAX INTEGER
MAX-ACCESS read-write
STATUS current
DESCRIPTION
"Data value."
::= { dataArray4 344 }

dataValue4_345 OBJECT-TYPE
SYNTAX INTEGER
MAX-ACCESS read-write
STATUS current
DESCRIPTION
"Data value."
::= { dataArray4 345 }

dataValue4_346 OBJECT-TYPE
SYNTAX INTEGER
MAX-ACCESS read-write
STATUS current
DESCRIPTION
"Data value."
::= { dataArray4 346 }

dataValue4_347 OBJECT-TYPE
SYNTAX INTEGER
MAX-ACCESS read-write
STATUS current
DESCRIPTION
"Data value."
::= { dataArray4 347 }

dataValue4_348 OBJECT-TYPE
SYNTAX INTEGER
MAX-ACCESS read-write
STATUS current
DESCRIPTION
"Data value."
::= { dataArray4 348 }

dataValue4_349 OBJECT-TYPE
SYNTAX INTEGER
MAX-ACCESS read-write
STATUS current
DESCRIPTION
"Data value."
::= { dataArray4 349 }

dataValue4_350 OBJECT-TYPE
SYNTAX INTEGER
MAX-ACCESS read-write
STATUS current
DESCRIPTION
"Data value."
::= { dataArray4 350 }

dataValue4_351 OBJECT-TYPE
SYNTAX INTEGER
MAX-ACCESS read-write
STATUS current
DESCRIPTION
"Data value."
::= { dataArray4 351 }

dataValue4_352 OBJECT-TYPE
SYNTAX INTEGER
MAX-ACCESS read-write
STATUS current
DESCRIPTION
"Data value."
::= { dataArray4 352 }

dataValue4_353 OBJECT-TYPE
SYNTAX INTEGER
MAX-ACCESS read-write
STATUS current
DESCRIPTION
"Data value."
::= { dataArray4 353 }

dataValue4_354 OBJECT-TYPE
SYNTAX INTEGER
MAX-ACCESS read-write
STATUS current
DESCRIPTION
"Data value."
::= { dataArray4 354 }

dataValue4_355 OBJECT-TYPE
SYNTAX INTEGER
MAX-ACCESS read-write
STATUS current
DESCRIPTION
"Data value."
::= { dataArray4 355 }

dataValue4_356 OBJECT-TYPE
SYNTAX INTEGER
MAX-ACCESS read-write
STATUS current
DESCRIPTION
"Data value."
::= { dataArray4 356 }

dataValue4_357 OBJECT-TYPE
SYNTAX INTEGER
MAX-ACCESS read-write
STATUS current
DESCRIPTION
"Data value."
::= { dataArray4 357 }

dataValue4_358 OBJECT-TYPE
SYNTAX INTEGER
MAX-ACCESS read-write
STATUS current
DESCRIPTION
"Data value."
::= { dataArray4 358 }

dataValue4_359 OBJECT-TYPE
SYNTAX INTEGER
MAX-ACCESS read-write
STATUS current
DESCRIPTION
"Data value."
::= { dataArray4 359 }

dataValue4_360 OBJECT-TYPE
SYNTAX INTEGER
MAX-ACCESS read-write
STATUS current
DESCRIPTION
"Data value."
::= { dataArray4 360 }

dataValue4_361 OBJECT-TYPE
SYNTAX INTEGER
MAX-ACCESS read-write
STATUS current
DESCRIPTION
"Data value."
::= { dataArray4 361 }

dataValue4_362 OBJECT-TYPE
SYNTAX INTEGER
MAX-ACCESS read-write
STATUS current
DESCRIPTION
"Data value."
::= { dataArray4 362 }

dataValue4_363 OBJECT-TYPE
SYNTAX INTEGER
MAX-ACCESS read-write
STATUS current
DESCRIPTION
"Data value."
::= { dataArray4 363 }

dataValue4_364 OBJECT-TYPE
SYNTAX INTEGER
MAX-ACCESS read-write
STATUS current
DESCRIPTION
"Data value."
::= { dataArray4 364 }

dataValue4_365 OBJECT-TYPE
SYNTAX INTEGER
MAX-ACCESS read-write
STATUS current
DESCRIPTION
"Data value."
::= { dataArray4 365 }

dataValue4_366 OBJECT-TYPE
SYNTAX INTEGER
MAX-ACCESS read-write
STATUS current
DESCRIPTION
"Data value."
::= { dataArray4 366 }

dataValue4_367 OBJECT-TYPE
SYNTAX INTEGER
MAX-ACCESS read-write
STATUS current
DESCRIPTION
"Data value."
::= { dataArray4 367 }

dataValue4_368 OBJECT-TYPE
SYNTAX INTEGER
MAX-ACCESS read-write
STATUS current
DESCRIPTION
"Data value."
::= { dataArray4 368 }

dataValue4_369 OBJECT-TYPE
SYNTAX INTEGER
MAX-ACCESS read-write
STATUS current
DESCRIPTION
"Data value."
::= { dataArray4 369 }

dataValue4_370 OBJECT-TYPE
SYNTAX INTEGER
MAX-ACCESS read-write
STATUS current
DESCRIPTION
"Data value."
::= { dataArray4 370 }

dataValue4_371 OBJECT-TYPE
SYNTAX INTEGER
MAX-ACCESS read-write
STATUS current
DESCRIPTION
"Data value."
::= { dataArray4 371 }

dataValue4_372 OBJECT-TYPE
SYNTAX INTEGER
MAX-ACCESS read-write
STATUS current
DESCRIPTION
"Data value."
::= { dataArray4 372 }

dataValue4_373 OBJECT-TYPE
SYNTAX INTEGER
MAX-ACCESS read-write
STATUS current
DESCRIPTION
"Data value."
::= { dataArray4 373 }

dataValue4_374 OBJECT-TYPE
SYNTAX INTEGER
MAX-ACCESS read-write
STATUS current
DESCRIPTION
"Data value."
::= { dataArray4 374 }

dataValue4_375 OBJECT-TYPE
SYNTAX INTEGER
MAX-ACCESS read-write
STATUS current
DESCRIPTION
"Data value."
::= { dataArray4 375 }

dataValue4_376 OBJECT-TYPE
SYNTAX INTEGER
MAX-ACCESS read-write
STATUS current
DESCRIPTION
"Data value."
::= { dataArray4 376 }

dataValue4_377 OBJECT-TYPE
SYNTAX INTEGER
MAX-ACCESS read-write
STATUS current
DESCRIPTION
"Data value."
::= { dataArray4 377 }

dataValue4_378 OBJECT-TYPE
SYNTAX INTEGER
MAX-ACCESS read-write
STATUS current
DESCRIPTION
"Data value."
::= { dataArray4 378 }

dataValue4_379 OBJECT-TYPE
SYNTAX INTEGER
MAX-ACCESS read-write
STATUS current
DESCRIPTION
"Data value."
::= { dataArray4 379 }

dataValue4_380 OBJECT-TYPE
SYNTAX INTEGER
MAX-ACCESS read-write
STATUS current
DESCRIPTION
"Data value."
::= { dataArray4 380 }

dataValue4_381 OBJECT-TYPE
SYNTAX INTEGER
MAX-ACCESS read-write
STATUS current
DESCRIPTION
"Data value."
::= { dataArray4 381 }

dataValue4_382 OBJECT-TYPE
SYNTAX INTEGER
MAX-ACCESS read-write
STATUS current
DESCRIPTION
"Data value."
::= { dataArray4 382 }

dataValue4_383 OBJECT-TYPE
SYNTAX INTEGER
MAX-ACCESS read-write
STATUS current
DESCRIPTION
"Data value."
::= { dataArray4 383 }

dataValue4_384 OBJECT-TYPE
SYNTAX INTEGER
MAX-ACCESS read-write
STATUS current
DESCRIPTION
"Data value."
::= { dataArray4 384 }

dataValue4_385 OBJECT-TYPE
SYNTAX INTEGER
MAX-ACCESS read-write
STATUS current
DESCRIPTION
"Data value."
::= { dataArray4 385 }

dataValue4_386 OBJECT-TYPE
SYNTAX INTEGER
MAX-ACCESS read-write
STATUS current
DESCRIPTION
"Data value."
::= { dataArray4 386 }

dataValue4_387 OBJECT-TYPE
SYNTAX INTEGER
MAX-ACCESS read-write
STATUS current
DESCRIPTION
"Data value."
::= { dataArray4 387 }

dataValue4_388 OBJECT-TYPE
SYNTAX INTEGER
MAX-ACCESS read-write
STATUS current
DESCRIPTION
"Data value."
::= { dataArray4 388 }

dataValue4_389 OBJECT-TYPE
SYNTAX INTEGER
MAX-ACCESS read-write
STATUS current
DESCRIPTION
"Data value."
::= { dataArray4 389 }

dataValue4_390 OBJECT-TYPE
SYNTAX INTEGER
MAX-ACCESS read-write
STATUS current
DESCRIPTION
"Data value."
::= { dataArray4 390 }

dataValue4_391 OBJECT-TYPE
SYNTAX INTEGER
MAX-ACCESS read-write
STATUS current
DESCRIPTION
"Data value."
::= { dataArray4 391 }

dataValue4_392 OBJECT-TYPE
SYNTAX INTEGER
MAX-ACCESS read-write
STATUS current
DESCRIPTION
"Data value."
::= { dataArray4 392 }

dataValue4_393 OBJECT-TYPE
SYNTAX INTEGER
MAX-ACCESS read-write
STATUS current
DESCRIPTION
"Data value."
::= { dataArray4 393 }

dataValue4_394 OBJECT-TYPE
SYNTAX INTEGER
MAX-ACCESS read-write
STATUS current
DESCRIPTION
"Data value."
::= { dataArray4 394 }

dataValue4_395 OBJECT-TYPE
SYNTAX INTEGER
MAX-ACCESS read-write
STATUS current
DESCRIPTION
"Data value."
::= { dataArray4 395 }

dataValue4_396 OBJECT-TYPE
SYNTAX INTEGER
MAX-ACCESS read-write
STATUS current
DESCRIPTION
"Data value."
::= { dataArray4 396 }

dataValue4_397 OBJECT-TYPE
SYNTAX INTEGER
MAX-ACCESS read-write
STATUS current
DESCRIPTION
"Data value."
::= { dataArray4 397 }

dataValue4_398 OBJECT-TYPE
SYNTAX INTEGER
MAX-ACCESS read-write
STATUS current
DESCRIPTION
"Data value."
::= { dataArray4 398 }

dataValue4_399 OBJECT-TYPE
SYNTAX INTEGER
MAX-ACCESS read-write
STATUS current
DESCRIPTION
"Data value."
::= { dataArray4 399 }

dataArray5 OBJECT IDENTIFIER ::= { cc08255400_v1_00a 5 }

dataValue5_0 OBJECT-TYPE
SYNTAX INTEGER
MAX-ACCESS read-write
STATUS current
DESCRIPTION
"Data value."
::= { dataArray5 0 }

dataValue5_1 OBJECT-TYPE
SYNTAX INTEGER
MAX-ACCESS read-write
STATUS current
DESCRIPTION
"Data value."
::= { dataArray5 1 }

dataValue5_2 OBJECT-TYPE
SYNTAX INTEGER
MAX-ACCESS read-write
STATUS current
DESCRIPTION
"Data value."
::= { dataArray5 2 }

dataValue5_3 OBJECT-TYPE
SYNTAX INTEGER
MAX-ACCESS read-write
STATUS current
DESCRIPTION
"Data value."
::= { dataArray5 3 }

dataValue5_4 OBJECT-TYPE
SYNTAX INTEGER
MAX-ACCESS read-write
STATUS current
DESCRIPTION
"Data value."
::= { dataArray5 4 }

dataValue5_5 OBJECT-TYPE
SYNTAX INTEGER
MAX-ACCESS read-write
STATUS current
DESCRIPTION
"Data value."
::= { dataArray5 5 }

dataValue5_6 OBJECT-TYPE
SYNTAX INTEGER
MAX-ACCESS read-write
STATUS current
DESCRIPTION
"Data value."
::= { dataArray5 6 }

dataValue5_7 OBJECT-TYPE
SYNTAX INTEGER
MAX-ACCESS read-write
STATUS current
DESCRIPTION
"Data value."
::= { dataArray5 7 }

dataValue5_8 OBJECT-TYPE
SYNTAX INTEGER
MAX-ACCESS read-write
STATUS current
DESCRIPTION
"Data value."
::= { dataArray5 8 }

dataValue5_9 OBJECT-TYPE
SYNTAX INTEGER
MAX-ACCESS read-write
STATUS current
DESCRIPTION
"Data value."
::= { dataArray5 9 }

dataValue5_10 OBJECT-TYPE
SYNTAX INTEGER
MAX-ACCESS read-write
STATUS current
DESCRIPTION
"Data value."
::= { dataArray5 10 }

dataValue5_11 OBJECT-TYPE
SYNTAX INTEGER
MAX-ACCESS read-write
STATUS current
DESCRIPTION
"Data value."
::= { dataArray5 11 }

dataValue5_12 OBJECT-TYPE
SYNTAX INTEGER
MAX-ACCESS read-write
STATUS current
DESCRIPTION
"Data value."
::= { dataArray5 12 }

dataValue5_13 OBJECT-TYPE
SYNTAX INTEGER
MAX-ACCESS read-write
STATUS current
DESCRIPTION
"Data value."
::= { dataArray5 13 }

dataValue5_14 OBJECT-TYPE
SYNTAX INTEGER
MAX-ACCESS read-write
STATUS current
DESCRIPTION
"Data value."
::= { dataArray5 14 }

dataValue5_15 OBJECT-TYPE
SYNTAX INTEGER
MAX-ACCESS read-write
STATUS current
DESCRIPTION
"Data value."
::= { dataArray5 15 }

dataValue5_16 OBJECT-TYPE
SYNTAX INTEGER
MAX-ACCESS read-write
STATUS current
DESCRIPTION
"Data value."
::= { dataArray5 16 }

dataValue5_17 OBJECT-TYPE
SYNTAX INTEGER
MAX-ACCESS read-write
STATUS current
DESCRIPTION
"Data value."
::= { dataArray5 17 }

dataValue5_18 OBJECT-TYPE
SYNTAX INTEGER
MAX-ACCESS read-write
STATUS current
DESCRIPTION
"Data value."
::= { dataArray5 18 }

dataValue5_19 OBJECT-TYPE
SYNTAX INTEGER
MAX-ACCESS read-write
STATUS current
DESCRIPTION
"Data value."
::= { dataArray5 19 }

dataValue5_20 OBJECT-TYPE
SYNTAX INTEGER
MAX-ACCESS read-write
STATUS current
DESCRIPTION
"Data value."
::= { dataArray5 20 }

dataValue5_21 OBJECT-TYPE
SYNTAX INTEGER
MAX-ACCESS read-write
STATUS current
DESCRIPTION
"Data value."
::= { dataArray5 21 }

dataValue5_22 OBJECT-TYPE
SYNTAX INTEGER
MAX-ACCESS read-write
STATUS current
DESCRIPTION
"Data value."
::= { dataArray5 22 }

dataValue5_23 OBJECT-TYPE
SYNTAX INTEGER
MAX-ACCESS read-write
STATUS current
DESCRIPTION
"Data value."
::= { dataArray5 23 }

dataValue5_24 OBJECT-TYPE
SYNTAX INTEGER
MAX-ACCESS read-write
STATUS current
DESCRIPTION
"Data value."
::= { dataArray5 24 }

dataValue5_25 OBJECT-TYPE
SYNTAX INTEGER
MAX-ACCESS read-write
STATUS current
DESCRIPTION
"Data value."
::= { dataArray5 25 }

dataValue5_26 OBJECT-TYPE
SYNTAX INTEGER
MAX-ACCESS read-write
STATUS current
DESCRIPTION
"Data value."
::= { dataArray5 26 }

dataValue5_27 OBJECT-TYPE
SYNTAX INTEGER
MAX-ACCESS read-write
STATUS current
DESCRIPTION
"Data value."
::= { dataArray5 27 }

dataValue5_28 OBJECT-TYPE
SYNTAX INTEGER
MAX-ACCESS read-write
STATUS current
DESCRIPTION
"Data value."
::= { dataArray5 28 }

dataValue5_29 OBJECT-TYPE
SYNTAX INTEGER
MAX-ACCESS read-write
STATUS current
DESCRIPTION
"Data value."
::= { dataArray5 29 }

dataValue5_30 OBJECT-TYPE
SYNTAX INTEGER
MAX-ACCESS read-write
STATUS current
DESCRIPTION
"Data value."
::= { dataArray5 30 }

dataValue5_31 OBJECT-TYPE
SYNTAX INTEGER
MAX-ACCESS read-write
STATUS current
DESCRIPTION
"Data value."
::= { dataArray5 31 }

dataValue5_32 OBJECT-TYPE
SYNTAX INTEGER
MAX-ACCESS read-write
STATUS current
DESCRIPTION
"Data value."
::= { dataArray5 32 }

dataValue5_33 OBJECT-TYPE
SYNTAX INTEGER
MAX-ACCESS read-write
STATUS current
DESCRIPTION
"Data value."
::= { dataArray5 33 }

dataValue5_34 OBJECT-TYPE
SYNTAX INTEGER
MAX-ACCESS read-write
STATUS current
DESCRIPTION
"Data value."
::= { dataArray5 34 }

dataValue5_35 OBJECT-TYPE
SYNTAX INTEGER
MAX-ACCESS read-write
STATUS current
DESCRIPTION
"Data value."
::= { dataArray5 35 }

dataValue5_36 OBJECT-TYPE
SYNTAX INTEGER
MAX-ACCESS read-write
STATUS current
DESCRIPTION
"Data value."
::= { dataArray5 36 }

dataValue5_37 OBJECT-TYPE
SYNTAX INTEGER
MAX-ACCESS read-write
STATUS current
DESCRIPTION
"Data value."
::= { dataArray5 37 }

dataValue5_38 OBJECT-TYPE
SYNTAX INTEGER
MAX-ACCESS read-write
STATUS current
DESCRIPTION
"Data value."
::= { dataArray5 38 }

dataValue5_39 OBJECT-TYPE
SYNTAX INTEGER
MAX-ACCESS read-write
STATUS current
DESCRIPTION
"Data value."
::= { dataArray5 39 }

dataValue5_40 OBJECT-TYPE
SYNTAX INTEGER
MAX-ACCESS read-write
STATUS current
DESCRIPTION
"Data value."
::= { dataArray5 40 }

dataValue5_41 OBJECT-TYPE
SYNTAX INTEGER
MAX-ACCESS read-write
STATUS current
DESCRIPTION
"Data value."
::= { dataArray5 41 }

dataValue5_42 OBJECT-TYPE
SYNTAX INTEGER
MAX-ACCESS read-write
STATUS current
DESCRIPTION
"Data value."
::= { dataArray5 42 }

dataValue5_43 OBJECT-TYPE
SYNTAX INTEGER
MAX-ACCESS read-write
STATUS current
DESCRIPTION
"Data value."
::= { dataArray5 43 }

dataValue5_44 OBJECT-TYPE
SYNTAX INTEGER
MAX-ACCESS read-write
STATUS current
DESCRIPTION
"Data value."
::= { dataArray5 44 }

dataValue5_45 OBJECT-TYPE
SYNTAX INTEGER
MAX-ACCESS read-write
STATUS current
DESCRIPTION
"Data value."
::= { dataArray5 45 }

dataValue5_46 OBJECT-TYPE
SYNTAX INTEGER
MAX-ACCESS read-write
STATUS current
DESCRIPTION
"Data value."
::= { dataArray5 46 }

dataValue5_47 OBJECT-TYPE
SYNTAX INTEGER
MAX-ACCESS read-write
STATUS current
DESCRIPTION
"Data value."
::= { dataArray5 47 }

dataValue5_48 OBJECT-TYPE
SYNTAX INTEGER
MAX-ACCESS read-write
STATUS current
DESCRIPTION
"Data value."
::= { dataArray5 48 }

dataValue5_49 OBJECT-TYPE
SYNTAX INTEGER
MAX-ACCESS read-write
STATUS current
DESCRIPTION
"Data value."
::= { dataArray5 49 }

dataValue5_50 OBJECT-TYPE
SYNTAX INTEGER
MAX-ACCESS read-write
STATUS current
DESCRIPTION
"Data value."
::= { dataArray5 50 }

dataValue5_51 OBJECT-TYPE
SYNTAX INTEGER
MAX-ACCESS read-write
STATUS current
DESCRIPTION
"Data value."
::= { dataArray5 51 }

dataValue5_52 OBJECT-TYPE
SYNTAX INTEGER
MAX-ACCESS read-write
STATUS current
DESCRIPTION
"Data value."
::= { dataArray5 52 }

dataValue5_53 OBJECT-TYPE
SYNTAX INTEGER
MAX-ACCESS read-write
STATUS current
DESCRIPTION
"Data value."
::= { dataArray5 53 }

dataValue5_54 OBJECT-TYPE
SYNTAX INTEGER
MAX-ACCESS read-write
STATUS current
DESCRIPTION
"Data value."
::= { dataArray5 54 }

dataValue5_55 OBJECT-TYPE
SYNTAX INTEGER
MAX-ACCESS read-write
STATUS current
DESCRIPTION
"Data value."
::= { dataArray5 55 }

dataValue5_56 OBJECT-TYPE
SYNTAX INTEGER
MAX-ACCESS read-write
STATUS current
DESCRIPTION
"Data value."
::= { dataArray5 56 }

dataValue5_57 OBJECT-TYPE
SYNTAX INTEGER
MAX-ACCESS read-write
STATUS current
DESCRIPTION
"Data value."
::= { dataArray5 57 }

dataValue5_58 OBJECT-TYPE
SYNTAX INTEGER
MAX-ACCESS read-write
STATUS current
DESCRIPTION
"Data value."
::= { dataArray5 58 }

dataValue5_59 OBJECT-TYPE
SYNTAX INTEGER
MAX-ACCESS read-write
STATUS current
DESCRIPTION
"Data value."
::= { dataArray5 59 }

dataValue5_60 OBJECT-TYPE
SYNTAX INTEGER
MAX-ACCESS read-write
STATUS current
DESCRIPTION
"Data value."
::= { dataArray5 60 }

dataValue5_61 OBJECT-TYPE
SYNTAX INTEGER
MAX-ACCESS read-write
STATUS current
DESCRIPTION
"Data value."
::= { dataArray5 61 }

dataValue5_62 OBJECT-TYPE
SYNTAX INTEGER
MAX-ACCESS read-write
STATUS current
DESCRIPTION
"Data value."
::= { dataArray5 62 }

dataValue5_63 OBJECT-TYPE
SYNTAX INTEGER
MAX-ACCESS read-write
STATUS current
DESCRIPTION
"Data value."
::= { dataArray5 63 }

dataValue5_64 OBJECT-TYPE
SYNTAX INTEGER
MAX-ACCESS read-write
STATUS current
DESCRIPTION
"Data value."
::= { dataArray5 64 }

dataValue5_65 OBJECT-TYPE
SYNTAX INTEGER
MAX-ACCESS read-write
STATUS current
DESCRIPTION
"Data value."
::= { dataArray5 65 }

dataValue5_66 OBJECT-TYPE
SYNTAX INTEGER
MAX-ACCESS read-write
STATUS current
DESCRIPTION
"Data value."
::= { dataArray5 66 }

dataValue5_67 OBJECT-TYPE
SYNTAX INTEGER
MAX-ACCESS read-write
STATUS current
DESCRIPTION
"Data value."
::= { dataArray5 67 }

dataValue5_68 OBJECT-TYPE
SYNTAX INTEGER
MAX-ACCESS read-write
STATUS current
DESCRIPTION
"Data value."
::= { dataArray5 68 }

dataValue5_69 OBJECT-TYPE
SYNTAX INTEGER
MAX-ACCESS read-write
STATUS current
DESCRIPTION
"Data value."
::= { dataArray5 69 }

dataValue5_70 OBJECT-TYPE
SYNTAX INTEGER
MAX-ACCESS read-write
STATUS current
DESCRIPTION
"Data value."
::= { dataArray5 70 }

dataValue5_71 OBJECT-TYPE
SYNTAX INTEGER
MAX-ACCESS read-write
STATUS current
DESCRIPTION
"Data value."
::= { dataArray5 71 }

dataValue5_72 OBJECT-TYPE
SYNTAX INTEGER
MAX-ACCESS read-write
STATUS current
DESCRIPTION
"Data value."
::= { dataArray5 72 }

dataValue5_73 OBJECT-TYPE
SYNTAX INTEGER
MAX-ACCESS read-write
STATUS current
DESCRIPTION
"Data value."
::= { dataArray5 73 }

dataValue5_74 OBJECT-TYPE
SYNTAX INTEGER
MAX-ACCESS read-write
STATUS current
DESCRIPTION
"Data value."
::= { dataArray5 74 }

dataValue5_75 OBJECT-TYPE
SYNTAX INTEGER
MAX-ACCESS read-write
STATUS current
DESCRIPTION
"Data value."
::= { dataArray5 75 }

dataValue5_76 OBJECT-TYPE
SYNTAX INTEGER
MAX-ACCESS read-write
STATUS current
DESCRIPTION
"Data value."
::= { dataArray5 76 }

dataValue5_77 OBJECT-TYPE
SYNTAX INTEGER
MAX-ACCESS read-write
STATUS current
DESCRIPTION
"Data value."
::= { dataArray5 77 }

dataValue5_78 OBJECT-TYPE
SYNTAX INTEGER
MAX-ACCESS read-write
STATUS current
DESCRIPTION
"Data value."
::= { dataArray5 78 }

dataValue5_79 OBJECT-TYPE
SYNTAX INTEGER
MAX-ACCESS read-write
STATUS current
DESCRIPTION
"Data value."
::= { dataArray5 79 }

dataValue5_80 OBJECT-TYPE
SYNTAX INTEGER
MAX-ACCESS read-write
STATUS current
DESCRIPTION
"Data value."
::= { dataArray5 80 }

dataValue5_81 OBJECT-TYPE
SYNTAX INTEGER
MAX-ACCESS read-write
STATUS current
DESCRIPTION
"Data value."
::= { dataArray5 81 }

dataValue5_82 OBJECT-TYPE
SYNTAX INTEGER
MAX-ACCESS read-write
STATUS current
DESCRIPTION
"Data value."
::= { dataArray5 82 }

dataValue5_83 OBJECT-TYPE
SYNTAX INTEGER
MAX-ACCESS read-write
STATUS current
DESCRIPTION
"Data value."
::= { dataArray5 83 }

dataValue5_84 OBJECT-TYPE
SYNTAX INTEGER
MAX-ACCESS read-write
STATUS current
DESCRIPTION
"Data value."
::= { dataArray5 84 }

dataValue5_85 OBJECT-TYPE
SYNTAX INTEGER
MAX-ACCESS read-write
STATUS current
DESCRIPTION
"Data value."
::= { dataArray5 85 }

dataValue5_86 OBJECT-TYPE
SYNTAX INTEGER
MAX-ACCESS read-write
STATUS current
DESCRIPTION
"Data value."
::= { dataArray5 86 }

dataValue5_87 OBJECT-TYPE
SYNTAX INTEGER
MAX-ACCESS read-write
STATUS current
DESCRIPTION
"Data value."
::= { dataArray5 87 }

dataValue5_88 OBJECT-TYPE
SYNTAX INTEGER
MAX-ACCESS read-write
STATUS current
DESCRIPTION
"Data value."
::= { dataArray5 88 }

dataValue5_89 OBJECT-TYPE
SYNTAX INTEGER
MAX-ACCESS read-write
STATUS current
DESCRIPTION
"Data value."
::= { dataArray5 89 }

dataValue5_90 OBJECT-TYPE
SYNTAX INTEGER
MAX-ACCESS read-write
STATUS current
DESCRIPTION
"Data value."
::= { dataArray5 90 }

dataValue5_91 OBJECT-TYPE
SYNTAX INTEGER
MAX-ACCESS read-write
STATUS current
DESCRIPTION
"Data value."
::= { dataArray5 91 }

dataValue5_92 OBJECT-TYPE
SYNTAX INTEGER
MAX-ACCESS read-write
STATUS current
DESCRIPTION
"Data value."
::= { dataArray5 92 }

dataValue5_93 OBJECT-TYPE
SYNTAX INTEGER
MAX-ACCESS read-write
STATUS current
DESCRIPTION
"Data value."
::= { dataArray5 93 }

dataValue5_94 OBJECT-TYPE
SYNTAX INTEGER
MAX-ACCESS read-write
STATUS current
DESCRIPTION
"Data value."
::= { dataArray5 94 }

dataValue5_95 OBJECT-TYPE
SYNTAX INTEGER
MAX-ACCESS read-write
STATUS current
DESCRIPTION
"Data value."
::= { dataArray5 95 }

dataValue5_96 OBJECT-TYPE
SYNTAX INTEGER
MAX-ACCESS read-write
STATUS current
DESCRIPTION
"Data value."
::= { dataArray5 96 }

dataValue5_97 OBJECT-TYPE
SYNTAX INTEGER
MAX-ACCESS read-write
STATUS current
DESCRIPTION
"Data value."
::= { dataArray5 97 }

dataValue5_98 OBJECT-TYPE
SYNTAX INTEGER
MAX-ACCESS read-write
STATUS current
DESCRIPTION
"Data value."
::= { dataArray5 98 }

dataValue5_99 OBJECT-TYPE
SYNTAX INTEGER
MAX-ACCESS read-write
STATUS current
DESCRIPTION
"Data value."
::= { dataArray5 99 }

dataValue5_100 OBJECT-TYPE
SYNTAX INTEGER
MAX-ACCESS read-write
STATUS current
DESCRIPTION
"Data value."
::= { dataArray5 100 }

dataValue5_101 OBJECT-TYPE
SYNTAX INTEGER
MAX-ACCESS read-write
STATUS current
DESCRIPTION
"Data value."
::= { dataArray5 101 }

dataValue5_102 OBJECT-TYPE
SYNTAX INTEGER
MAX-ACCESS read-write
STATUS current
DESCRIPTION
"Data value."
::= { dataArray5 102 }

dataValue5_103 OBJECT-TYPE
SYNTAX INTEGER
MAX-ACCESS read-write
STATUS current
DESCRIPTION
"Data value."
::= { dataArray5 103 }

dataValue5_104 OBJECT-TYPE
SYNTAX INTEGER
MAX-ACCESS read-write
STATUS current
DESCRIPTION
"Data value."
::= { dataArray5 104 }

dataValue5_105 OBJECT-TYPE
SYNTAX INTEGER
MAX-ACCESS read-write
STATUS current
DESCRIPTION
"Data value."
::= { dataArray5 105 }

dataValue5_106 OBJECT-TYPE
SYNTAX INTEGER
MAX-ACCESS read-write
STATUS current
DESCRIPTION
"Data value."
::= { dataArray5 106 }

dataValue5_107 OBJECT-TYPE
SYNTAX INTEGER
MAX-ACCESS read-write
STATUS current
DESCRIPTION
"Data value."
::= { dataArray5 107 }

dataValue5_108 OBJECT-TYPE
SYNTAX INTEGER
MAX-ACCESS read-write
STATUS current
DESCRIPTION
"Data value."
::= { dataArray5 108 }

dataValue5_109 OBJECT-TYPE
SYNTAX INTEGER
MAX-ACCESS read-write
STATUS current
DESCRIPTION
"Data value."
::= { dataArray5 109 }

dataValue5_110 OBJECT-TYPE
SYNTAX INTEGER
MAX-ACCESS read-write
STATUS current
DESCRIPTION
"Data value."
::= { dataArray5 110 }

dataValue5_111 OBJECT-TYPE
SYNTAX INTEGER
MAX-ACCESS read-write
STATUS current
DESCRIPTION
"Data value."
::= { dataArray5 111 }

dataValue5_112 OBJECT-TYPE
SYNTAX INTEGER
MAX-ACCESS read-write
STATUS current
DESCRIPTION
"Data value."
::= { dataArray5 112 }

dataValue5_113 OBJECT-TYPE
SYNTAX INTEGER
MAX-ACCESS read-write
STATUS current
DESCRIPTION
"Data value."
::= { dataArray5 113 }

dataValue5_114 OBJECT-TYPE
SYNTAX INTEGER
MAX-ACCESS read-write
STATUS current
DESCRIPTION
"Data value."
::= { dataArray5 114 }

dataValue5_115 OBJECT-TYPE
SYNTAX INTEGER
MAX-ACCESS read-write
STATUS current
DESCRIPTION
"Data value."
::= { dataArray5 115 }

dataValue5_116 OBJECT-TYPE
SYNTAX INTEGER
MAX-ACCESS read-write
STATUS current
DESCRIPTION
"Data value."
::= { dataArray5 116 }

dataValue5_117 OBJECT-TYPE
SYNTAX INTEGER
MAX-ACCESS read-write
STATUS current
DESCRIPTION
"Data value."
::= { dataArray5 117 }

dataValue5_118 OBJECT-TYPE
SYNTAX INTEGER
MAX-ACCESS read-write
STATUS current
DESCRIPTION
"Data value."
::= { dataArray5 118 }

dataValue5_119 OBJECT-TYPE
SYNTAX INTEGER
MAX-ACCESS read-write
STATUS current
DESCRIPTION
"Data value."
::= { dataArray5 119 }

dataValue5_120 OBJECT-TYPE
SYNTAX INTEGER
MAX-ACCESS read-write
STATUS current
DESCRIPTION
"Data value."
::= { dataArray5 120 }

dataValue5_121 OBJECT-TYPE
SYNTAX INTEGER
MAX-ACCESS read-write
STATUS current
DESCRIPTION
"Data value."
::= { dataArray5 121 }

dataValue5_122 OBJECT-TYPE
SYNTAX INTEGER
MAX-ACCESS read-write
STATUS current
DESCRIPTION
"Data value."
::= { dataArray5 122 }

dataValue5_123 OBJECT-TYPE
SYNTAX INTEGER
MAX-ACCESS read-write
STATUS current
DESCRIPTION
"Data value."
::= { dataArray5 123 }

dataValue5_124 OBJECT-TYPE
SYNTAX INTEGER
MAX-ACCESS read-write
STATUS current
DESCRIPTION
"Data value."
::= { dataArray5 124 }

dataValue5_125 OBJECT-TYPE
SYNTAX INTEGER
MAX-ACCESS read-write
STATUS current
DESCRIPTION
"Data value."
::= { dataArray5 125 }

dataValue5_126 OBJECT-TYPE
SYNTAX INTEGER
MAX-ACCESS read-write
STATUS current
DESCRIPTION
"Data value."
::= { dataArray5 126 }

dataValue5_127 OBJECT-TYPE
SYNTAX INTEGER
MAX-ACCESS read-write
STATUS current
DESCRIPTION
"Data value."
::= { dataArray5 127 }

dataValue5_128 OBJECT-TYPE
SYNTAX INTEGER
MAX-ACCESS read-write
STATUS current
DESCRIPTION
"Data value."
::= { dataArray5 128 }

dataValue5_129 OBJECT-TYPE
SYNTAX INTEGER
MAX-ACCESS read-write
STATUS current
DESCRIPTION
"Data value."
::= { dataArray5 129 }

dataValue5_130 OBJECT-TYPE
SYNTAX INTEGER
MAX-ACCESS read-write
STATUS current
DESCRIPTION
"Data value."
::= { dataArray5 130 }

dataValue5_131 OBJECT-TYPE
SYNTAX INTEGER
MAX-ACCESS read-write
STATUS current
DESCRIPTION
"Data value."
::= { dataArray5 131 }

dataValue5_132 OBJECT-TYPE
SYNTAX INTEGER
MAX-ACCESS read-write
STATUS current
DESCRIPTION
"Data value."
::= { dataArray5 132 }

dataValue5_133 OBJECT-TYPE
SYNTAX INTEGER
MAX-ACCESS read-write
STATUS current
DESCRIPTION
"Data value."
::= { dataArray5 133 }

dataValue5_134 OBJECT-TYPE
SYNTAX INTEGER
MAX-ACCESS read-write
STATUS current
DESCRIPTION
"Data value."
::= { dataArray5 134 }

dataValue5_135 OBJECT-TYPE
SYNTAX INTEGER
MAX-ACCESS read-write
STATUS current
DESCRIPTION
"Data value."
::= { dataArray5 135 }

dataValue5_136 OBJECT-TYPE
SYNTAX INTEGER
MAX-ACCESS read-write
STATUS current
DESCRIPTION
"Data value."
::= { dataArray5 136 }

dataValue5_137 OBJECT-TYPE
SYNTAX INTEGER
MAX-ACCESS read-write
STATUS current
DESCRIPTION
"Data value."
::= { dataArray5 137 }

dataValue5_138 OBJECT-TYPE
SYNTAX INTEGER
MAX-ACCESS read-write
STATUS current
DESCRIPTION
"Data value."
::= { dataArray5 138 }

dataValue5_139 OBJECT-TYPE
SYNTAX INTEGER
MAX-ACCESS read-write
STATUS current
DESCRIPTION
"Data value."
::= { dataArray5 139 }

dataValue5_140 OBJECT-TYPE
SYNTAX INTEGER
MAX-ACCESS read-write
STATUS current
DESCRIPTION
"Data value."
::= { dataArray5 140 }

dataValue5_141 OBJECT-TYPE
SYNTAX INTEGER
MAX-ACCESS read-write
STATUS current
DESCRIPTION
"Data value."
::= { dataArray5 141 }

dataValue5_142 OBJECT-TYPE
SYNTAX INTEGER
MAX-ACCESS read-write
STATUS current
DESCRIPTION
"Data value."
::= { dataArray5 142 }

dataValue5_143 OBJECT-TYPE
SYNTAX INTEGER
MAX-ACCESS read-write
STATUS current
DESCRIPTION
"Data value."
::= { dataArray5 143 }

dataValue5_144 OBJECT-TYPE
SYNTAX INTEGER
MAX-ACCESS read-write
STATUS current
DESCRIPTION
"Data value."
::= { dataArray5 144 }

dataValue5_145 OBJECT-TYPE
SYNTAX INTEGER
MAX-ACCESS read-write
STATUS current
DESCRIPTION
"Data value."
::= { dataArray5 145 }

dataValue5_146 OBJECT-TYPE
SYNTAX INTEGER
MAX-ACCESS read-write
STATUS current
DESCRIPTION
"Data value."
::= { dataArray5 146 }

dataValue5_147 OBJECT-TYPE
SYNTAX INTEGER
MAX-ACCESS read-write
STATUS current
DESCRIPTION
"Data value."
::= { dataArray5 147 }

dataValue5_148 OBJECT-TYPE
SYNTAX INTEGER
MAX-ACCESS read-write
STATUS current
DESCRIPTION
"Data value."
::= { dataArray5 148 }

dataValue5_149 OBJECT-TYPE
SYNTAX INTEGER
MAX-ACCESS read-write
STATUS current
DESCRIPTION
"Data value."
::= { dataArray5 149 }

dataValue5_150 OBJECT-TYPE
SYNTAX INTEGER
MAX-ACCESS read-write
STATUS current
DESCRIPTION
"Data value."
::= { dataArray5 150 }

dataValue5_151 OBJECT-TYPE
SYNTAX INTEGER
MAX-ACCESS read-write
STATUS current
DESCRIPTION
"Data value."
::= { dataArray5 151 }

dataValue5_152 OBJECT-TYPE
SYNTAX INTEGER
MAX-ACCESS read-write
STATUS current
DESCRIPTION
"Data value."
::= { dataArray5 152 }

dataValue5_153 OBJECT-TYPE
SYNTAX INTEGER
MAX-ACCESS read-write
STATUS current
DESCRIPTION
"Data value."
::= { dataArray5 153 }

dataValue5_154 OBJECT-TYPE
SYNTAX INTEGER
MAX-ACCESS read-write
STATUS current
DESCRIPTION
"Data value."
::= { dataArray5 154 }

dataValue5_155 OBJECT-TYPE
SYNTAX INTEGER
MAX-ACCESS read-write
STATUS current
DESCRIPTION
"Data value."
::= { dataArray5 155 }

dataValue5_156 OBJECT-TYPE
SYNTAX INTEGER
MAX-ACCESS read-write
STATUS current
DESCRIPTION
"Data value."
::= { dataArray5 156 }

dataValue5_157 OBJECT-TYPE
SYNTAX INTEGER
MAX-ACCESS read-write
STATUS current
DESCRIPTION
"Data value."
::= { dataArray5 157 }

dataValue5_158 OBJECT-TYPE
SYNTAX INTEGER
MAX-ACCESS read-write
STATUS current
DESCRIPTION
"Data value."
::= { dataArray5 158 }

dataValue5_159 OBJECT-TYPE
SYNTAX INTEGER
MAX-ACCESS read-write
STATUS current
DESCRIPTION
"Data value."
::= { dataArray5 159 }

dataValue5_160 OBJECT-TYPE
SYNTAX INTEGER
MAX-ACCESS read-write
STATUS current
DESCRIPTION
"Data value."
::= { dataArray5 160 }

dataValue5_161 OBJECT-TYPE
SYNTAX INTEGER
MAX-ACCESS read-write
STATUS current
DESCRIPTION
"Data value."
::= { dataArray5 161 }

dataValue5_162 OBJECT-TYPE
SYNTAX INTEGER
MAX-ACCESS read-write
STATUS current
DESCRIPTION
"Data value."
::= { dataArray5 162 }

dataValue5_163 OBJECT-TYPE
SYNTAX INTEGER
MAX-ACCESS read-write
STATUS current
DESCRIPTION
"Data value."
::= { dataArray5 163 }

dataValue5_164 OBJECT-TYPE
SYNTAX INTEGER
MAX-ACCESS read-write
STATUS current
DESCRIPTION
"Data value."
::= { dataArray5 164 }

dataValue5_165 OBJECT-TYPE
SYNTAX INTEGER
MAX-ACCESS read-write
STATUS current
DESCRIPTION
"Data value."
::= { dataArray5 165 }

dataValue5_166 OBJECT-TYPE
SYNTAX INTEGER
MAX-ACCESS read-write
STATUS current
DESCRIPTION
"Data value."
::= { dataArray5 166 }

dataValue5_167 OBJECT-TYPE
SYNTAX INTEGER
MAX-ACCESS read-write
STATUS current
DESCRIPTION
"Data value."
::= { dataArray5 167 }

dataValue5_168 OBJECT-TYPE
SYNTAX INTEGER
MAX-ACCESS read-write
STATUS current
DESCRIPTION
"Data value."
::= { dataArray5 168 }

dataValue5_169 OBJECT-TYPE
SYNTAX INTEGER
MAX-ACCESS read-write
STATUS current
DESCRIPTION
"Data value."
::= { dataArray5 169 }

dataValue5_170 OBJECT-TYPE
SYNTAX INTEGER
MAX-ACCESS read-write
STATUS current
DESCRIPTION
"Data value."
::= { dataArray5 170 }

dataValue5_171 OBJECT-TYPE
SYNTAX INTEGER
MAX-ACCESS read-write
STATUS current
DESCRIPTION
"Data value."
::= { dataArray5 171 }

dataValue5_172 OBJECT-TYPE
SYNTAX INTEGER
MAX-ACCESS read-write
STATUS current
DESCRIPTION
"Data value."
::= { dataArray5 172 }

dataValue5_173 OBJECT-TYPE
SYNTAX INTEGER
MAX-ACCESS read-write
STATUS current
DESCRIPTION
"Data value."
::= { dataArray5 173 }

dataValue5_174 OBJECT-TYPE
SYNTAX INTEGER
MAX-ACCESS read-write
STATUS current
DESCRIPTION
"Data value."
::= { dataArray5 174 }

dataValue5_175 OBJECT-TYPE
SYNTAX INTEGER
MAX-ACCESS read-write
STATUS current
DESCRIPTION
"Data value."
::= { dataArray5 175 }

dataValue5_176 OBJECT-TYPE
SYNTAX INTEGER
MAX-ACCESS read-write
STATUS current
DESCRIPTION
"Data value."
::= { dataArray5 176 }

dataValue5_177 OBJECT-TYPE
SYNTAX INTEGER
MAX-ACCESS read-write
STATUS current
DESCRIPTION
"Data value."
::= { dataArray5 177 }

dataValue5_178 OBJECT-TYPE
SYNTAX INTEGER
MAX-ACCESS read-write
STATUS current
DESCRIPTION
"Data value."
::= { dataArray5 178 }

dataValue5_179 OBJECT-TYPE
SYNTAX INTEGER
MAX-ACCESS read-write
STATUS current
DESCRIPTION
"Data value."
::= { dataArray5 179 }

dataValue5_180 OBJECT-TYPE
SYNTAX INTEGER
MAX-ACCESS read-write
STATUS current
DESCRIPTION
"Data value."
::= { dataArray5 180 }

dataValue5_181 OBJECT-TYPE
SYNTAX INTEGER
MAX-ACCESS read-write
STATUS current
DESCRIPTION
"Data value."
::= { dataArray5 181 }

dataValue5_182 OBJECT-TYPE
SYNTAX INTEGER
MAX-ACCESS read-write
STATUS current
DESCRIPTION
"Data value."
::= { dataArray5 182 }

dataValue5_183 OBJECT-TYPE
SYNTAX INTEGER
MAX-ACCESS read-write
STATUS current
DESCRIPTION
"Data value."
::= { dataArray5 183 }

dataValue5_184 OBJECT-TYPE
SYNTAX INTEGER
MAX-ACCESS read-write
STATUS current
DESCRIPTION
"Data value."
::= { dataArray5 184 }

dataValue5_185 OBJECT-TYPE
SYNTAX INTEGER
MAX-ACCESS read-write
STATUS current
DESCRIPTION
"Data value."
::= { dataArray5 185 }

dataValue5_186 OBJECT-TYPE
SYNTAX INTEGER
MAX-ACCESS read-write
STATUS current
DESCRIPTION
"Data value."
::= { dataArray5 186 }

dataValue5_187 OBJECT-TYPE
SYNTAX INTEGER
MAX-ACCESS read-write
STATUS current
DESCRIPTION
"Data value."
::= { dataArray5 187 }

dataValue5_188 OBJECT-TYPE
SYNTAX INTEGER
MAX-ACCESS read-write
STATUS current
DESCRIPTION
"Data value."
::= { dataArray5 188 }

dataValue5_189 OBJECT-TYPE
SYNTAX INTEGER
MAX-ACCESS read-write
STATUS current
DESCRIPTION
"Data value."
::= { dataArray5 189 }

dataValue5_190 OBJECT-TYPE
SYNTAX INTEGER
MAX-ACCESS read-write
STATUS current
DESCRIPTION
"Data value."
::= { dataArray5 190 }

dataValue5_191 OBJECT-TYPE
SYNTAX INTEGER
MAX-ACCESS read-write
STATUS current
DESCRIPTION
"Data value."
::= { dataArray5 191 }

dataValue5_192 OBJECT-TYPE
SYNTAX INTEGER
MAX-ACCESS read-write
STATUS current
DESCRIPTION
"Data value."
::= { dataArray5 192 }

dataValue5_193 OBJECT-TYPE
SYNTAX INTEGER
MAX-ACCESS read-write
STATUS current
DESCRIPTION
"Data value."
::= { dataArray5 193 }

dataValue5_194 OBJECT-TYPE
SYNTAX INTEGER
MAX-ACCESS read-write
STATUS current
DESCRIPTION
"Data value."
::= { dataArray5 194 }

dataValue5_195 OBJECT-TYPE
SYNTAX INTEGER
MAX-ACCESS read-write
STATUS current
DESCRIPTION
"Data value."
::= { dataArray5 195 }

dataValue5_196 OBJECT-TYPE
SYNTAX INTEGER
MAX-ACCESS read-write
STATUS current
DESCRIPTION
"Data value."
::= { dataArray5 196 }

dataValue5_197 OBJECT-TYPE
SYNTAX INTEGER
MAX-ACCESS read-write
STATUS current
DESCRIPTION
"Data value."
::= { dataArray5 197 }

dataValue5_198 OBJECT-TYPE
SYNTAX INTEGER
MAX-ACCESS read-write
STATUS current
DESCRIPTION
"Data value."
::= { dataArray5 198 }

dataValue5_199 OBJECT-TYPE
SYNTAX INTEGER
MAX-ACCESS read-write
STATUS current
DESCRIPTION
"Data value."
::= { dataArray5 199 }

dataValue5_200 OBJECT-TYPE
SYNTAX INTEGER
MAX-ACCESS read-write
STATUS current
DESCRIPTION
"Data value."
::= { dataArray5 200 }

dataValue5_201 OBJECT-TYPE
SYNTAX INTEGER
MAX-ACCESS read-write
STATUS current
DESCRIPTION
"Data value."
::= { dataArray5 201 }

dataValue5_202 OBJECT-TYPE
SYNTAX INTEGER
MAX-ACCESS read-write
STATUS current
DESCRIPTION
"Data value."
::= { dataArray5 202 }

dataValue5_203 OBJECT-TYPE
SYNTAX INTEGER
MAX-ACCESS read-write
STATUS current
DESCRIPTION
"Data value."
::= { dataArray5 203 }

dataValue5_204 OBJECT-TYPE
SYNTAX INTEGER
MAX-ACCESS read-write
STATUS current
DESCRIPTION
"Data value."
::= { dataArray5 204 }

dataValue5_205 OBJECT-TYPE
SYNTAX INTEGER
MAX-ACCESS read-write
STATUS current
DESCRIPTION
"Data value."
::= { dataArray5 205 }

dataValue5_206 OBJECT-TYPE
SYNTAX INTEGER
MAX-ACCESS read-write
STATUS current
DESCRIPTION
"Data value."
::= { dataArray5 206 }

dataValue5_207 OBJECT-TYPE
SYNTAX INTEGER
MAX-ACCESS read-write
STATUS current
DESCRIPTION
"Data value."
::= { dataArray5 207 }

dataValue5_208 OBJECT-TYPE
SYNTAX INTEGER
MAX-ACCESS read-write
STATUS current
DESCRIPTION
"Data value."
::= { dataArray5 208 }

dataValue5_209 OBJECT-TYPE
SYNTAX INTEGER
MAX-ACCESS read-write
STATUS current
DESCRIPTION
"Data value."
::= { dataArray5 209 }

dataValue5_210 OBJECT-TYPE
SYNTAX INTEGER
MAX-ACCESS read-write
STATUS current
DESCRIPTION
"Data value."
::= { dataArray5 210 }

dataValue5_211 OBJECT-TYPE
SYNTAX INTEGER
MAX-ACCESS read-write
STATUS current
DESCRIPTION
"Data value."
::= { dataArray5 211 }

dataValue5_212 OBJECT-TYPE
SYNTAX INTEGER
MAX-ACCESS read-write
STATUS current
DESCRIPTION
"Data value."
::= { dataArray5 212 }

dataValue5_213 OBJECT-TYPE
SYNTAX INTEGER
MAX-ACCESS read-write
STATUS current
DESCRIPTION
"Data value."
::= { dataArray5 213 }

dataValue5_214 OBJECT-TYPE
SYNTAX INTEGER
MAX-ACCESS read-write
STATUS current
DESCRIPTION
"Data value."
::= { dataArray5 214 }

dataValue5_215 OBJECT-TYPE
SYNTAX INTEGER
MAX-ACCESS read-write
STATUS current
DESCRIPTION
"Data value."
::= { dataArray5 215 }

dataValue5_216 OBJECT-TYPE
SYNTAX INTEGER
MAX-ACCESS read-write
STATUS current
DESCRIPTION
"Data value."
::= { dataArray5 216 }

dataValue5_217 OBJECT-TYPE
SYNTAX INTEGER
MAX-ACCESS read-write
STATUS current
DESCRIPTION
"Data value."
::= { dataArray5 217 }

dataValue5_218 OBJECT-TYPE
SYNTAX INTEGER
MAX-ACCESS read-write
STATUS current
DESCRIPTION
"Data value."
::= { dataArray5 218 }

dataValue5_219 OBJECT-TYPE
SYNTAX INTEGER
MAX-ACCESS read-write
STATUS current
DESCRIPTION
"Data value."
::= { dataArray5 219 }

dataValue5_220 OBJECT-TYPE
SYNTAX INTEGER
MAX-ACCESS read-write
STATUS current
DESCRIPTION
"Data value."
::= { dataArray5 220 }

dataValue5_221 OBJECT-TYPE
SYNTAX INTEGER
MAX-ACCESS read-write
STATUS current
DESCRIPTION
"Data value."
::= { dataArray5 221 }

dataValue5_222 OBJECT-TYPE
SYNTAX INTEGER
MAX-ACCESS read-write
STATUS current
DESCRIPTION
"Data value."
::= { dataArray5 222 }

dataValue5_223 OBJECT-TYPE
SYNTAX INTEGER
MAX-ACCESS read-write
STATUS current
DESCRIPTION
"Data value."
::= { dataArray5 223 }

dataValue5_224 OBJECT-TYPE
SYNTAX INTEGER
MAX-ACCESS read-write
STATUS current
DESCRIPTION
"Data value."
::= { dataArray5 224 }

dataValue5_225 OBJECT-TYPE
SYNTAX INTEGER
MAX-ACCESS read-write
STATUS current
DESCRIPTION
"Data value."
::= { dataArray5 225 }

dataValue5_226 OBJECT-TYPE
SYNTAX INTEGER
MAX-ACCESS read-write
STATUS current
DESCRIPTION
"Data value."
::= { dataArray5 226 }

dataValue5_227 OBJECT-TYPE
SYNTAX INTEGER
MAX-ACCESS read-write
STATUS current
DESCRIPTION
"Data value."
::= { dataArray5 227 }

dataValue5_228 OBJECT-TYPE
SYNTAX INTEGER
MAX-ACCESS read-write
STATUS current
DESCRIPTION
"Data value."
::= { dataArray5 228 }

dataValue5_229 OBJECT-TYPE
SYNTAX INTEGER
MAX-ACCESS read-write
STATUS current
DESCRIPTION
"Data value."
::= { dataArray5 229 }

dataValue5_230 OBJECT-TYPE
SYNTAX INTEGER
MAX-ACCESS read-write
STATUS current
DESCRIPTION
"Data value."
::= { dataArray5 230 }

dataValue5_231 OBJECT-TYPE
SYNTAX INTEGER
MAX-ACCESS read-write
STATUS current
DESCRIPTION
"Data value."
::= { dataArray5 231 }

dataValue5_232 OBJECT-TYPE
SYNTAX INTEGER
MAX-ACCESS read-write
STATUS current
DESCRIPTION
"Data value."
::= { dataArray5 232 }

dataValue5_233 OBJECT-TYPE
SYNTAX INTEGER
MAX-ACCESS read-write
STATUS current
DESCRIPTION
"Data value."
::= { dataArray5 233 }

dataValue5_234 OBJECT-TYPE
SYNTAX INTEGER
MAX-ACCESS read-write
STATUS current
DESCRIPTION
"Data value."
::= { dataArray5 234 }

dataValue5_235 OBJECT-TYPE
SYNTAX INTEGER
MAX-ACCESS read-write
STATUS current
DESCRIPTION
"Data value."
::= { dataArray5 235 }

dataValue5_236 OBJECT-TYPE
SYNTAX INTEGER
MAX-ACCESS read-write
STATUS current
DESCRIPTION
"Data value."
::= { dataArray5 236 }

dataValue5_237 OBJECT-TYPE
SYNTAX INTEGER
MAX-ACCESS read-write
STATUS current
DESCRIPTION
"Data value."
::= { dataArray5 237 }

dataValue5_238 OBJECT-TYPE
SYNTAX INTEGER
MAX-ACCESS read-write
STATUS current
DESCRIPTION
"Data value."
::= { dataArray5 238 }

dataValue5_239 OBJECT-TYPE
SYNTAX INTEGER
MAX-ACCESS read-write
STATUS current
DESCRIPTION
"Data value."
::= { dataArray5 239 }

dataValue5_240 OBJECT-TYPE
SYNTAX INTEGER
MAX-ACCESS read-write
STATUS current
DESCRIPTION
"Data value."
::= { dataArray5 240 }

dataValue5_241 OBJECT-TYPE
SYNTAX INTEGER
MAX-ACCESS read-write
STATUS current
DESCRIPTION
"Data value."
::= { dataArray5 241 }

dataValue5_242 OBJECT-TYPE
SYNTAX INTEGER
MAX-ACCESS read-write
STATUS current
DESCRIPTION
"Data value."
::= { dataArray5 242 }

dataValue5_243 OBJECT-TYPE
SYNTAX INTEGER
MAX-ACCESS read-write
STATUS current
DESCRIPTION
"Data value."
::= { dataArray5 243 }

dataValue5_244 OBJECT-TYPE
SYNTAX INTEGER
MAX-ACCESS read-write
STATUS current
DESCRIPTION
"Data value."
::= { dataArray5 244 }

dataValue5_245 OBJECT-TYPE
SYNTAX INTEGER
MAX-ACCESS read-write
STATUS current
DESCRIPTION
"Data value."
::= { dataArray5 245 }

dataValue5_246 OBJECT-TYPE
SYNTAX INTEGER
MAX-ACCESS read-write
STATUS current
DESCRIPTION
"Data value."
::= { dataArray5 246 }

dataValue5_247 OBJECT-TYPE
SYNTAX INTEGER
MAX-ACCESS read-write
STATUS current
DESCRIPTION
"Data value."
::= { dataArray5 247 }

dataValue5_248 OBJECT-TYPE
SYNTAX INTEGER
MAX-ACCESS read-write
STATUS current
DESCRIPTION
"Data value."
::= { dataArray5 248 }

dataValue5_249 OBJECT-TYPE
SYNTAX INTEGER
MAX-ACCESS read-write
STATUS current
DESCRIPTION
"Data value."
::= { dataArray5 249 }

dataValue5_250 OBJECT-TYPE
SYNTAX INTEGER
MAX-ACCESS read-write
STATUS current
DESCRIPTION
"Data value."
::= { dataArray5 250 }

dataValue5_251 OBJECT-TYPE
SYNTAX INTEGER
MAX-ACCESS read-write
STATUS current
DESCRIPTION
"Data value."
::= { dataArray5 251 }

dataValue5_252 OBJECT-TYPE
SYNTAX INTEGER
MAX-ACCESS read-write
STATUS current
DESCRIPTION
"Data value."
::= { dataArray5 252 }

dataValue5_253 OBJECT-TYPE
SYNTAX INTEGER
MAX-ACCESS read-write
STATUS current
DESCRIPTION
"Data value."
::= { dataArray5 253 }

dataValue5_254 OBJECT-TYPE
SYNTAX INTEGER
MAX-ACCESS read-write
STATUS current
DESCRIPTION
"Data value."
::= { dataArray5 254 }

dataValue5_255 OBJECT-TYPE
SYNTAX INTEGER
MAX-ACCESS read-write
STATUS current
DESCRIPTION
"Data value."
::= { dataArray5 255 }

dataValue5_256 OBJECT-TYPE
SYNTAX INTEGER
MAX-ACCESS read-write
STATUS current
DESCRIPTION
"Data value."
::= { dataArray5 256 }

dataValue5_257 OBJECT-TYPE
SYNTAX INTEGER
MAX-ACCESS read-write
STATUS current
DESCRIPTION
"Data value."
::= { dataArray5 257 }

dataValue5_258 OBJECT-TYPE
SYNTAX INTEGER
MAX-ACCESS read-write
STATUS current
DESCRIPTION
"Data value."
::= { dataArray5 258 }

dataValue5_259 OBJECT-TYPE
SYNTAX INTEGER
MAX-ACCESS read-write
STATUS current
DESCRIPTION
"Data value."
::= { dataArray5 259 }

dataValue5_260 OBJECT-TYPE
SYNTAX INTEGER
MAX-ACCESS read-write
STATUS current
DESCRIPTION
"Data value."
::= { dataArray5 260 }

dataValue5_261 OBJECT-TYPE
SYNTAX INTEGER
MAX-ACCESS read-write
STATUS current
DESCRIPTION
"Data value."
::= { dataArray5 261 }

dataValue5_262 OBJECT-TYPE
SYNTAX INTEGER
MAX-ACCESS read-write
STATUS current
DESCRIPTION
"Data value."
::= { dataArray5 262 }

dataValue5_263 OBJECT-TYPE
SYNTAX INTEGER
MAX-ACCESS read-write
STATUS current
DESCRIPTION
"Data value."
::= { dataArray5 263 }

dataValue5_264 OBJECT-TYPE
SYNTAX INTEGER
MAX-ACCESS read-write
STATUS current
DESCRIPTION
"Data value."
::= { dataArray5 264 }

dataValue5_265 OBJECT-TYPE
SYNTAX INTEGER
MAX-ACCESS read-write
STATUS current
DESCRIPTION
"Data value."
::= { dataArray5 265 }

dataValue5_266 OBJECT-TYPE
SYNTAX INTEGER
MAX-ACCESS read-write
STATUS current
DESCRIPTION
"Data value."
::= { dataArray5 266 }

dataValue5_267 OBJECT-TYPE
SYNTAX INTEGER
MAX-ACCESS read-write
STATUS current
DESCRIPTION
"Data value."
::= { dataArray5 267 }

dataValue5_268 OBJECT-TYPE
SYNTAX INTEGER
MAX-ACCESS read-write
STATUS current
DESCRIPTION
"Data value."
::= { dataArray5 268 }

dataValue5_269 OBJECT-TYPE
SYNTAX INTEGER
MAX-ACCESS read-write
STATUS current
DESCRIPTION
"Data value."
::= { dataArray5 269 }

dataValue5_270 OBJECT-TYPE
SYNTAX INTEGER
MAX-ACCESS read-write
STATUS current
DESCRIPTION
"Data value."
::= { dataArray5 270 }

dataValue5_271 OBJECT-TYPE
SYNTAX INTEGER
MAX-ACCESS read-write
STATUS current
DESCRIPTION
"Data value."
::= { dataArray5 271 }

dataValue5_272 OBJECT-TYPE
SYNTAX INTEGER
MAX-ACCESS read-write
STATUS current
DESCRIPTION
"Data value."
::= { dataArray5 272 }

dataValue5_273 OBJECT-TYPE
SYNTAX INTEGER
MAX-ACCESS read-write
STATUS current
DESCRIPTION
"Data value."
::= { dataArray5 273 }

dataValue5_274 OBJECT-TYPE
SYNTAX INTEGER
MAX-ACCESS read-write
STATUS current
DESCRIPTION
"Data value."
::= { dataArray5 274 }

dataValue5_275 OBJECT-TYPE
SYNTAX INTEGER
MAX-ACCESS read-write
STATUS current
DESCRIPTION
"Data value."
::= { dataArray5 275 }

dataValue5_276 OBJECT-TYPE
SYNTAX INTEGER
MAX-ACCESS read-write
STATUS current
DESCRIPTION
"Data value."
::= { dataArray5 276 }

dataValue5_277 OBJECT-TYPE
SYNTAX INTEGER
MAX-ACCESS read-write
STATUS current
DESCRIPTION
"Data value."
::= { dataArray5 277 }

dataValue5_278 OBJECT-TYPE
SYNTAX INTEGER
MAX-ACCESS read-write
STATUS current
DESCRIPTION
"Data value."
::= { dataArray5 278 }

dataValue5_279 OBJECT-TYPE
SYNTAX INTEGER
MAX-ACCESS read-write
STATUS current
DESCRIPTION
"Data value."
::= { dataArray5 279 }

dataValue5_280 OBJECT-TYPE
SYNTAX INTEGER
MAX-ACCESS read-write
STATUS current
DESCRIPTION
"Data value."
::= { dataArray5 280 }

dataValue5_281 OBJECT-TYPE
SYNTAX INTEGER
MAX-ACCESS read-write
STATUS current
DESCRIPTION
"Data value."
::= { dataArray5 281 }

dataValue5_282 OBJECT-TYPE
SYNTAX INTEGER
MAX-ACCESS read-write
STATUS current
DESCRIPTION
"Data value."
::= { dataArray5 282 }

dataValue5_283 OBJECT-TYPE
SYNTAX INTEGER
MAX-ACCESS read-write
STATUS current
DESCRIPTION
"Data value."
::= { dataArray5 283 }

dataValue5_284 OBJECT-TYPE
SYNTAX INTEGER
MAX-ACCESS read-write
STATUS current
DESCRIPTION
"Data value."
::= { dataArray5 284 }

dataValue5_285 OBJECT-TYPE
SYNTAX INTEGER
MAX-ACCESS read-write
STATUS current
DESCRIPTION
"Data value."
::= { dataArray5 285 }

dataValue5_286 OBJECT-TYPE
SYNTAX INTEGER
MAX-ACCESS read-write
STATUS current
DESCRIPTION
"Data value."
::= { dataArray5 286 }

dataValue5_287 OBJECT-TYPE
SYNTAX INTEGER
MAX-ACCESS read-write
STATUS current
DESCRIPTION
"Data value."
::= { dataArray5 287 }

dataValue5_288 OBJECT-TYPE
SYNTAX INTEGER
MAX-ACCESS read-write
STATUS current
DESCRIPTION
"Data value."
::= { dataArray5 288 }

dataValue5_289 OBJECT-TYPE
SYNTAX INTEGER
MAX-ACCESS read-write
STATUS current
DESCRIPTION
"Data value."
::= { dataArray5 289 }

dataValue5_290 OBJECT-TYPE
SYNTAX INTEGER
MAX-ACCESS read-write
STATUS current
DESCRIPTION
"Data value."
::= { dataArray5 290 }

dataValue5_291 OBJECT-TYPE
SYNTAX INTEGER
MAX-ACCESS read-write
STATUS current
DESCRIPTION
"Data value."
::= { dataArray5 291 }

dataValue5_292 OBJECT-TYPE
SYNTAX INTEGER
MAX-ACCESS read-write
STATUS current
DESCRIPTION
"Data value."
::= { dataArray5 292 }

dataValue5_293 OBJECT-TYPE
SYNTAX INTEGER
MAX-ACCESS read-write
STATUS current
DESCRIPTION
"Data value."
::= { dataArray5 293 }

dataValue5_294 OBJECT-TYPE
SYNTAX INTEGER
MAX-ACCESS read-write
STATUS current
DESCRIPTION
"Data value."
::= { dataArray5 294 }

dataValue5_295 OBJECT-TYPE
SYNTAX INTEGER
MAX-ACCESS read-write
STATUS current
DESCRIPTION
"Data value."
::= { dataArray5 295 }

dataValue5_296 OBJECT-TYPE
SYNTAX INTEGER
MAX-ACCESS read-write
STATUS current
DESCRIPTION
"Data value."
::= { dataArray5 296 }

dataValue5_297 OBJECT-TYPE
SYNTAX INTEGER
MAX-ACCESS read-write
STATUS current
DESCRIPTION
"Data value."
::= { dataArray5 297 }

dataValue5_298 OBJECT-TYPE
SYNTAX INTEGER
MAX-ACCESS read-write
STATUS current
DESCRIPTION
"Data value."
::= { dataArray5 298 }

dataValue5_299 OBJECT-TYPE
SYNTAX INTEGER
MAX-ACCESS read-write
STATUS current
DESCRIPTION
"Data value."
::= { dataArray5 299 }

dataValue5_300 OBJECT-TYPE
SYNTAX INTEGER
MAX-ACCESS read-write
STATUS current
DESCRIPTION
"Data value."
::= { dataArray5 300 }

dataValue5_301 OBJECT-TYPE
SYNTAX INTEGER
MAX-ACCESS read-write
STATUS current
DESCRIPTION
"Data value."
::= { dataArray5 301 }

dataValue5_302 OBJECT-TYPE
SYNTAX INTEGER
MAX-ACCESS read-write
STATUS current
DESCRIPTION
"Data value."
::= { dataArray5 302 }

dataValue5_303 OBJECT-TYPE
SYNTAX INTEGER
MAX-ACCESS read-write
STATUS current
DESCRIPTION
"Data value."
::= { dataArray5 303 }

dataValue5_304 OBJECT-TYPE
SYNTAX INTEGER
MAX-ACCESS read-write
STATUS current
DESCRIPTION
"Data value."
::= { dataArray5 304 }

dataValue5_305 OBJECT-TYPE
SYNTAX INTEGER
MAX-ACCESS read-write
STATUS current
DESCRIPTION
"Data value."
::= { dataArray5 305 }

dataValue5_306 OBJECT-TYPE
SYNTAX INTEGER
MAX-ACCESS read-write
STATUS current
DESCRIPTION
"Data value."
::= { dataArray5 306 }

dataValue5_307 OBJECT-TYPE
SYNTAX INTEGER
MAX-ACCESS read-write
STATUS current
DESCRIPTION
"Data value."
::= { dataArray5 307 }

dataValue5_308 OBJECT-TYPE
SYNTAX INTEGER
MAX-ACCESS read-write
STATUS current
DESCRIPTION
"Data value."
::= { dataArray5 308 }

dataValue5_309 OBJECT-TYPE
SYNTAX INTEGER
MAX-ACCESS read-write
STATUS current
DESCRIPTION
"Data value."
::= { dataArray5 309 }

dataValue5_310 OBJECT-TYPE
SYNTAX INTEGER
MAX-ACCESS read-write
STATUS current
DESCRIPTION
"Data value."
::= { dataArray5 310 }

dataValue5_311 OBJECT-TYPE
SYNTAX INTEGER
MAX-ACCESS read-write
STATUS current
DESCRIPTION
"Data value."
::= { dataArray5 311 }

dataValue5_312 OBJECT-TYPE
SYNTAX INTEGER
MAX-ACCESS read-write
STATUS current
DESCRIPTION
"Data value."
::= { dataArray5 312 }

dataValue5_313 OBJECT-TYPE
SYNTAX INTEGER
MAX-ACCESS read-write
STATUS current
DESCRIPTION
"Data value."
::= { dataArray5 313 }

dataValue5_314 OBJECT-TYPE
SYNTAX INTEGER
MAX-ACCESS read-write
STATUS current
DESCRIPTION
"Data value."
::= { dataArray5 314 }

dataValue5_315 OBJECT-TYPE
SYNTAX INTEGER
MAX-ACCESS read-write
STATUS current
DESCRIPTION
"Data value."
::= { dataArray5 315 }

dataValue5_316 OBJECT-TYPE
SYNTAX INTEGER
MAX-ACCESS read-write
STATUS current
DESCRIPTION
"Data value."
::= { dataArray5 316 }

dataValue5_317 OBJECT-TYPE
SYNTAX INTEGER
MAX-ACCESS read-write
STATUS current
DESCRIPTION
"Data value."
::= { dataArray5 317 }

dataValue5_318 OBJECT-TYPE
SYNTAX INTEGER
MAX-ACCESS read-write
STATUS current
DESCRIPTION
"Data value."
::= { dataArray5 318 }

dataValue5_319 OBJECT-TYPE
SYNTAX INTEGER
MAX-ACCESS read-write
STATUS current
DESCRIPTION
"Data value."
::= { dataArray5 319 }

dataValue5_320 OBJECT-TYPE
SYNTAX INTEGER
MAX-ACCESS read-write
STATUS current
DESCRIPTION
"Data value."
::= { dataArray5 320 }

dataValue5_321 OBJECT-TYPE
SYNTAX INTEGER
MAX-ACCESS read-write
STATUS current
DESCRIPTION
"Data value."
::= { dataArray5 321 }

dataValue5_322 OBJECT-TYPE
SYNTAX INTEGER
MAX-ACCESS read-write
STATUS current
DESCRIPTION
"Data value."
::= { dataArray5 322 }

dataValue5_323 OBJECT-TYPE
SYNTAX INTEGER
MAX-ACCESS read-write
STATUS current
DESCRIPTION
"Data value."
::= { dataArray5 323 }

dataValue5_324 OBJECT-TYPE
SYNTAX INTEGER
MAX-ACCESS read-write
STATUS current
DESCRIPTION
"Data value."
::= { dataArray5 324 }

dataValue5_325 OBJECT-TYPE
SYNTAX INTEGER
MAX-ACCESS read-write
STATUS current
DESCRIPTION
"Data value."
::= { dataArray5 325 }

dataValue5_326 OBJECT-TYPE
SYNTAX INTEGER
MAX-ACCESS read-write
STATUS current
DESCRIPTION
"Data value."
::= { dataArray5 326 }

dataValue5_327 OBJECT-TYPE
SYNTAX INTEGER
MAX-ACCESS read-write
STATUS current
DESCRIPTION
"Data value."
::= { dataArray5 327 }

dataValue5_328 OBJECT-TYPE
SYNTAX INTEGER
MAX-ACCESS read-write
STATUS current
DESCRIPTION
"Data value."
::= { dataArray5 328 }

dataValue5_329 OBJECT-TYPE
SYNTAX INTEGER
MAX-ACCESS read-write
STATUS current
DESCRIPTION
"Data value."
::= { dataArray5 329 }

dataValue5_330 OBJECT-TYPE
SYNTAX INTEGER
MAX-ACCESS read-write
STATUS current
DESCRIPTION
"Data value."
::= { dataArray5 330 }

dataValue5_331 OBJECT-TYPE
SYNTAX INTEGER
MAX-ACCESS read-write
STATUS current
DESCRIPTION
"Data value."
::= { dataArray5 331 }

dataValue5_332 OBJECT-TYPE
SYNTAX INTEGER
MAX-ACCESS read-write
STATUS current
DESCRIPTION
"Data value."
::= { dataArray5 332 }

dataValue5_333 OBJECT-TYPE
SYNTAX INTEGER
MAX-ACCESS read-write
STATUS current
DESCRIPTION
"Data value."
::= { dataArray5 333 }

dataValue5_334 OBJECT-TYPE
SYNTAX INTEGER
MAX-ACCESS read-write
STATUS current
DESCRIPTION
"Data value."
::= { dataArray5 334 }

dataValue5_335 OBJECT-TYPE
SYNTAX INTEGER
MAX-ACCESS read-write
STATUS current
DESCRIPTION
"Data value."
::= { dataArray5 335 }

dataValue5_336 OBJECT-TYPE
SYNTAX INTEGER
MAX-ACCESS read-write
STATUS current
DESCRIPTION
"Data value."
::= { dataArray5 336 }

dataValue5_337 OBJECT-TYPE
SYNTAX INTEGER
MAX-ACCESS read-write
STATUS current
DESCRIPTION
"Data value."
::= { dataArray5 337 }

dataValue5_338 OBJECT-TYPE
SYNTAX INTEGER
MAX-ACCESS read-write
STATUS current
DESCRIPTION
"Data value."
::= { dataArray5 338 }

dataValue5_339 OBJECT-TYPE
SYNTAX INTEGER
MAX-ACCESS read-write
STATUS current
DESCRIPTION
"Data value."
::= { dataArray5 339 }

dataValue5_340 OBJECT-TYPE
SYNTAX INTEGER
MAX-ACCESS read-write
STATUS current
DESCRIPTION
"Data value."
::= { dataArray5 340 }

dataValue5_341 OBJECT-TYPE
SYNTAX INTEGER
MAX-ACCESS read-write
STATUS current
DESCRIPTION
"Data value."
::= { dataArray5 341 }

dataValue5_342 OBJECT-TYPE
SYNTAX INTEGER
MAX-ACCESS read-write
STATUS current
DESCRIPTION
"Data value."
::= { dataArray5 342 }

dataValue5_343 OBJECT-TYPE
SYNTAX INTEGER
MAX-ACCESS read-write
STATUS current
DESCRIPTION
"Data value."
::= { dataArray5 343 }

dataValue5_344 OBJECT-TYPE
SYNTAX INTEGER
MAX-ACCESS read-write
STATUS current
DESCRIPTION
"Data value."
::= { dataArray5 344 }

dataValue5_345 OBJECT-TYPE
SYNTAX INTEGER
MAX-ACCESS read-write
STATUS current
DESCRIPTION
"Data value."
::= { dataArray5 345 }

dataValue5_346 OBJECT-TYPE
SYNTAX INTEGER
MAX-ACCESS read-write
STATUS current
DESCRIPTION
"Data value."
::= { dataArray5 346 }

dataValue5_347 OBJECT-TYPE
SYNTAX INTEGER
MAX-ACCESS read-write
STATUS current
DESCRIPTION
"Data value."
::= { dataArray5 347 }

dataValue5_348 OBJECT-TYPE
SYNTAX INTEGER
MAX-ACCESS read-write
STATUS current
DESCRIPTION
"Data value."
::= { dataArray5 348 }

dataValue5_349 OBJECT-TYPE
SYNTAX INTEGER
MAX-ACCESS read-write
STATUS current
DESCRIPTION
"Data value."
::= { dataArray5 349 }

dataValue5_350 OBJECT-TYPE
SYNTAX INTEGER
MAX-ACCESS read-write
STATUS current
DESCRIPTION
"Data value."
::= { dataArray5 350 }

dataValue5_351 OBJECT-TYPE
SYNTAX INTEGER
MAX-ACCESS read-write
STATUS current
DESCRIPTION
"Data value."
::= { dataArray5 351 }

dataValue5_352 OBJECT-TYPE
SYNTAX INTEGER
MAX-ACCESS read-write
STATUS current
DESCRIPTION
"Data value."
::= { dataArray5 352 }

dataValue5_353 OBJECT-TYPE
SYNTAX INTEGER
MAX-ACCESS read-write
STATUS current
DESCRIPTION
"Data value."
::= { dataArray5 353 }

dataValue5_354 OBJECT-TYPE
SYNTAX INTEGER
MAX-ACCESS read-write
STATUS current
DESCRIPTION
"Data value."
::= { dataArray5 354 }

dataValue5_355 OBJECT-TYPE
SYNTAX INTEGER
MAX-ACCESS read-write
STATUS current
DESCRIPTION
"Data value."
::= { dataArray5 355 }

dataValue5_356 OBJECT-TYPE
SYNTAX INTEGER
MAX-ACCESS read-write
STATUS current
DESCRIPTION
"Data value."
::= { dataArray5 356 }

dataValue5_357 OBJECT-TYPE
SYNTAX INTEGER
MAX-ACCESS read-write
STATUS current
DESCRIPTION
"Data value."
::= { dataArray5 357 }

dataValue5_358 OBJECT-TYPE
SYNTAX INTEGER
MAX-ACCESS read-write
STATUS current
DESCRIPTION
"Data value."
::= { dataArray5 358 }

dataValue5_359 OBJECT-TYPE
SYNTAX INTEGER
MAX-ACCESS read-write
STATUS current
DESCRIPTION
"Data value."
::= { dataArray5 359 }

dataValue5_360 OBJECT-TYPE
SYNTAX INTEGER
MAX-ACCESS read-write
STATUS current
DESCRIPTION
"Data value."
::= { dataArray5 360 }

dataValue5_361 OBJECT-TYPE
SYNTAX INTEGER
MAX-ACCESS read-write
STATUS current
DESCRIPTION
"Data value."
::= { dataArray5 361 }

dataValue5_362 OBJECT-TYPE
SYNTAX INTEGER
MAX-ACCESS read-write
STATUS current
DESCRIPTION
"Data value."
::= { dataArray5 362 }

dataValue5_363 OBJECT-TYPE
SYNTAX INTEGER
MAX-ACCESS read-write
STATUS current
DESCRIPTION
"Data value."
::= { dataArray5 363 }

dataValue5_364 OBJECT-TYPE
SYNTAX INTEGER
MAX-ACCESS read-write
STATUS current
DESCRIPTION
"Data value."
::= { dataArray5 364 }

dataValue5_365 OBJECT-TYPE
SYNTAX INTEGER
MAX-ACCESS read-write
STATUS current
DESCRIPTION
"Data value."
::= { dataArray5 365 }

dataValue5_366 OBJECT-TYPE
SYNTAX INTEGER
MAX-ACCESS read-write
STATUS current
DESCRIPTION
"Data value."
::= { dataArray5 366 }

dataValue5_367 OBJECT-TYPE
SYNTAX INTEGER
MAX-ACCESS read-write
STATUS current
DESCRIPTION
"Data value."
::= { dataArray5 367 }

dataValue5_368 OBJECT-TYPE
SYNTAX INTEGER
MAX-ACCESS read-write
STATUS current
DESCRIPTION
"Data value."
::= { dataArray5 368 }

dataValue5_369 OBJECT-TYPE
SYNTAX INTEGER
MAX-ACCESS read-write
STATUS current
DESCRIPTION
"Data value."
::= { dataArray5 369 }

dataValue5_370 OBJECT-TYPE
SYNTAX INTEGER
MAX-ACCESS read-write
STATUS current
DESCRIPTION
"Data value."
::= { dataArray5 370 }

dataValue5_371 OBJECT-TYPE
SYNTAX INTEGER
MAX-ACCESS read-write
STATUS current
DESCRIPTION
"Data value."
::= { dataArray5 371 }

dataValue5_372 OBJECT-TYPE
SYNTAX INTEGER
MAX-ACCESS read-write
STATUS current
DESCRIPTION
"Data value."
::= { dataArray5 372 }

dataValue5_373 OBJECT-TYPE
SYNTAX INTEGER
MAX-ACCESS read-write
STATUS current
DESCRIPTION
"Data value."
::= { dataArray5 373 }

dataValue5_374 OBJECT-TYPE
SYNTAX INTEGER
MAX-ACCESS read-write
STATUS current
DESCRIPTION
"Data value."
::= { dataArray5 374 }

dataValue5_375 OBJECT-TYPE
SYNTAX INTEGER
MAX-ACCESS read-write
STATUS current
DESCRIPTION
"Data value."
::= { dataArray5 375 }

dataValue5_376 OBJECT-TYPE
SYNTAX INTEGER
MAX-ACCESS read-write
STATUS current
DESCRIPTION
"Data value."
::= { dataArray5 376 }

dataValue5_377 OBJECT-TYPE
SYNTAX INTEGER
MAX-ACCESS read-write
STATUS current
DESCRIPTION
"Data value."
::= { dataArray5 377 }

dataValue5_378 OBJECT-TYPE
SYNTAX INTEGER
MAX-ACCESS read-write
STATUS current
DESCRIPTION
"Data value."
::= { dataArray5 378 }

dataValue5_379 OBJECT-TYPE
SYNTAX INTEGER
MAX-ACCESS read-write
STATUS current
DESCRIPTION
"Data value."
::= { dataArray5 379 }

dataValue5_380 OBJECT-TYPE
SYNTAX INTEGER
MAX-ACCESS read-write
STATUS current
DESCRIPTION
"Data value."
::= { dataArray5 380 }

dataValue5_381 OBJECT-TYPE
SYNTAX INTEGER
MAX-ACCESS read-write
STATUS current
DESCRIPTION
"Data value."
::= { dataArray5 381 }

dataValue5_382 OBJECT-TYPE
SYNTAX INTEGER
MAX-ACCESS read-write
STATUS current
DESCRIPTION
"Data value."
::= { dataArray5 382 }

dataValue5_383 OBJECT-TYPE
SYNTAX INTEGER
MAX-ACCESS read-write
STATUS current
DESCRIPTION
"Data value."
::= { dataArray5 383 }

dataValue5_384 OBJECT-TYPE
SYNTAX INTEGER
MAX-ACCESS read-write
STATUS current
DESCRIPTION
"Data value."
::= { dataArray5 384 }

dataValue5_385 OBJECT-TYPE
SYNTAX INTEGER
MAX-ACCESS read-write
STATUS current
DESCRIPTION
"Data value."
::= { dataArray5 385 }

dataValue5_386 OBJECT-TYPE
SYNTAX INTEGER
MAX-ACCESS read-write
STATUS current
DESCRIPTION
"Data value."
::= { dataArray5 386 }

dataValue5_387 OBJECT-TYPE
SYNTAX INTEGER
MAX-ACCESS read-write
STATUS current
DESCRIPTION
"Data value."
::= { dataArray5 387 }

dataValue5_388 OBJECT-TYPE
SYNTAX INTEGER
MAX-ACCESS read-write
STATUS current
DESCRIPTION
"Data value."
::= { dataArray5 388 }

dataValue5_389 OBJECT-TYPE
SYNTAX INTEGER
MAX-ACCESS read-write
STATUS current
DESCRIPTION
"Data value."
::= { dataArray5 389 }

dataValue5_390 OBJECT-TYPE
SYNTAX INTEGER
MAX-ACCESS read-write
STATUS current
DESCRIPTION
"Data value."
::= { dataArray5 390 }

dataValue5_391 OBJECT-TYPE
SYNTAX INTEGER
MAX-ACCESS read-write
STATUS current
DESCRIPTION
"Data value."
::= { dataArray5 391 }

dataValue5_392 OBJECT-TYPE
SYNTAX INTEGER
MAX-ACCESS read-write
STATUS current
DESCRIPTION
"Data value."
::= { dataArray5 392 }

dataValue5_393 OBJECT-TYPE
SYNTAX INTEGER
MAX-ACCESS read-write
STATUS current
DESCRIPTION
"Data value."
::= { dataArray5 393 }

dataValue5_394 OBJECT-TYPE
SYNTAX INTEGER
MAX-ACCESS read-write
STATUS current
DESCRIPTION
"Data value."
::= { dataArray5 394 }

dataValue5_395 OBJECT-TYPE
SYNTAX INTEGER
MAX-ACCESS read-write
STATUS current
DESCRIPTION
"Data value."
::= { dataArray5 395 }

dataValue5_396 OBJECT-TYPE
SYNTAX INTEGER
MAX-ACCESS read-write
STATUS current
DESCRIPTION
"Data value."
::= { dataArray5 396 }

dataValue5_397 OBJECT-TYPE
SYNTAX INTEGER
MAX-ACCESS read-write
STATUS current
DESCRIPTION
"Data value."
::= { dataArray5 397 }

dataValue5_398 OBJECT-TYPE
SYNTAX INTEGER
MAX-ACCESS read-write
STATUS current
DESCRIPTION
"Data value."
::= { dataArray5 398 }

dataValue5_399 OBJECT-TYPE
SYNTAX INTEGER
MAX-ACCESS read-write
STATUS current
DESCRIPTION
"Data value."
::= { dataArray5 399 }

dataArray6 OBJECT IDENTIFIER ::= { cc08255400_v1_00a 6 }

dataValue6_0 OBJECT-TYPE
SYNTAX INTEGER
MAX-ACCESS read-write
STATUS current
DESCRIPTION
"Data value."
::= { dataArray6 0 }

dataValue6_1 OBJECT-TYPE
SYNTAX INTEGER
MAX-ACCESS read-write
STATUS current
DESCRIPTION
"Data value."
::= { dataArray6 1 }

dataValue6_2 OBJECT-TYPE
SYNTAX INTEGER
MAX-ACCESS read-write
STATUS current
DESCRIPTION
"Data value."
::= { dataArray6 2 }

dataValue6_3 OBJECT-TYPE
SYNTAX INTEGER
MAX-ACCESS read-write
STATUS current
DESCRIPTION
"Data value."
::= { dataArray6 3 }

dataValue6_4 OBJECT-TYPE
SYNTAX INTEGER
MAX-ACCESS read-write
STATUS current
DESCRIPTION
"Data value."
::= { dataArray6 4 }

dataValue6_5 OBJECT-TYPE
SYNTAX INTEGER
MAX-ACCESS read-write
STATUS current
DESCRIPTION
"Data value."
::= { dataArray6 5 }

dataValue6_6 OBJECT-TYPE
SYNTAX INTEGER
MAX-ACCESS read-write
STATUS current
DESCRIPTION
"Data value."
::= { dataArray6 6 }

dataValue6_7 OBJECT-TYPE
SYNTAX INTEGER
MAX-ACCESS read-write
STATUS current
DESCRIPTION
"Data value."
::= { dataArray6 7 }

dataValue6_8 OBJECT-TYPE
SYNTAX INTEGER
MAX-ACCESS read-write
STATUS current
DESCRIPTION
"Data value."
::= { dataArray6 8 }

dataValue6_9 OBJECT-TYPE
SYNTAX INTEGER
MAX-ACCESS read-write
STATUS current
DESCRIPTION
"Data value."
::= { dataArray6 9 }

dataValue6_10 OBJECT-TYPE
SYNTAX INTEGER
MAX-ACCESS read-write
STATUS current
DESCRIPTION
"Data value."
::= { dataArray6 10 }

dataValue6_11 OBJECT-TYPE
SYNTAX INTEGER
MAX-ACCESS read-write
STATUS current
DESCRIPTION
"Data value."
::= { dataArray6 11 }

dataValue6_12 OBJECT-TYPE
SYNTAX INTEGER
MAX-ACCESS read-write
STATUS current
DESCRIPTION
"Data value."
::= { dataArray6 12 }

dataValue6_13 OBJECT-TYPE
SYNTAX INTEGER
MAX-ACCESS read-write
STATUS current
DESCRIPTION
"Data value."
::= { dataArray6 13 }

dataValue6_14 OBJECT-TYPE
SYNTAX INTEGER
MAX-ACCESS read-write
STATUS current
DESCRIPTION
"Data value."
::= { dataArray6 14 }

dataValue6_15 OBJECT-TYPE
SYNTAX INTEGER
MAX-ACCESS read-write
STATUS current
DESCRIPTION
"Data value."
::= { dataArray6 15 }

dataValue6_16 OBJECT-TYPE
SYNTAX INTEGER
MAX-ACCESS read-write
STATUS current
DESCRIPTION
"Data value."
::= { dataArray6 16 }

dataValue6_17 OBJECT-TYPE
SYNTAX INTEGER
MAX-ACCESS read-write
STATUS current
DESCRIPTION
"Data value."
::= { dataArray6 17 }

dataValue6_18 OBJECT-TYPE
SYNTAX INTEGER
MAX-ACCESS read-write
STATUS current
DESCRIPTION
"Data value."
::= { dataArray6 18 }

dataValue6_19 OBJECT-TYPE
SYNTAX INTEGER
MAX-ACCESS read-write
STATUS current
DESCRIPTION
"Data value."
::= { dataArray6 19 }

dataValue6_20 OBJECT-TYPE
SYNTAX INTEGER
MAX-ACCESS read-write
STATUS current
DESCRIPTION
"Data value."
::= { dataArray6 20 }

dataValue6_21 OBJECT-TYPE
SYNTAX INTEGER
MAX-ACCESS read-write
STATUS current
DESCRIPTION
"Data value."
::= { dataArray6 21 }

dataValue6_22 OBJECT-TYPE
SYNTAX INTEGER
MAX-ACCESS read-write
STATUS current
DESCRIPTION
"Data value."
::= { dataArray6 22 }

dataValue6_23 OBJECT-TYPE
SYNTAX INTEGER
MAX-ACCESS read-write
STATUS current
DESCRIPTION
"Data value."
::= { dataArray6 23 }

dataValue6_24 OBJECT-TYPE
SYNTAX INTEGER
MAX-ACCESS read-write
STATUS current
DESCRIPTION
"Data value."
::= { dataArray6 24 }

dataValue6_25 OBJECT-TYPE
SYNTAX INTEGER
MAX-ACCESS read-write
STATUS current
DESCRIPTION
"Data value."
::= { dataArray6 25 }

dataValue6_26 OBJECT-TYPE
SYNTAX INTEGER
MAX-ACCESS read-write
STATUS current
DESCRIPTION
"Data value."
::= { dataArray6 26 }

dataValue6_27 OBJECT-TYPE
SYNTAX INTEGER
MAX-ACCESS read-write
STATUS current
DESCRIPTION
"Data value."
::= { dataArray6 27 }

dataValue6_28 OBJECT-TYPE
SYNTAX INTEGER
MAX-ACCESS read-write
STATUS current
DESCRIPTION
"Data value."
::= { dataArray6 28 }

dataValue6_29 OBJECT-TYPE
SYNTAX INTEGER
MAX-ACCESS read-write
STATUS current
DESCRIPTION
"Data value."
::= { dataArray6 29 }

dataValue6_30 OBJECT-TYPE
SYNTAX INTEGER
MAX-ACCESS read-write
STATUS current
DESCRIPTION
"Data value."
::= { dataArray6 30 }

dataValue6_31 OBJECT-TYPE
SYNTAX INTEGER
MAX-ACCESS read-write
STATUS current
DESCRIPTION
"Data value."
::= { dataArray6 31 }

dataValue6_32 OBJECT-TYPE
SYNTAX INTEGER
MAX-ACCESS read-write
STATUS current
DESCRIPTION
"Data value."
::= { dataArray6 32 }

dataValue6_33 OBJECT-TYPE
SYNTAX INTEGER
MAX-ACCESS read-write
STATUS current
DESCRIPTION
"Data value."
::= { dataArray6 33 }

dataValue6_34 OBJECT-TYPE
SYNTAX INTEGER
MAX-ACCESS read-write
STATUS current
DESCRIPTION
"Data value."
::= { dataArray6 34 }

dataValue6_35 OBJECT-TYPE
SYNTAX INTEGER
MAX-ACCESS read-write
STATUS current
DESCRIPTION
"Data value."
::= { dataArray6 35 }

dataValue6_36 OBJECT-TYPE
SYNTAX INTEGER
MAX-ACCESS read-write
STATUS current
DESCRIPTION
"Data value."
::= { dataArray6 36 }

dataValue6_37 OBJECT-TYPE
SYNTAX INTEGER
MAX-ACCESS read-write
STATUS current
DESCRIPTION
"Data value."
::= { dataArray6 37 }

dataValue6_38 OBJECT-TYPE
SYNTAX INTEGER
MAX-ACCESS read-write
STATUS current
DESCRIPTION
"Data value."
::= { dataArray6 38 }

dataValue6_39 OBJECT-TYPE
SYNTAX INTEGER
MAX-ACCESS read-write
STATUS current
DESCRIPTION
"Data value."
::= { dataArray6 39 }

dataValue6_40 OBJECT-TYPE
SYNTAX INTEGER
MAX-ACCESS read-write
STATUS current
DESCRIPTION
"Data value."
::= { dataArray6 40 }

dataValue6_41 OBJECT-TYPE
SYNTAX INTEGER
MAX-ACCESS read-write
STATUS current
DESCRIPTION
"Data value."
::= { dataArray6 41 }

dataValue6_42 OBJECT-TYPE
SYNTAX INTEGER
MAX-ACCESS read-write
STATUS current
DESCRIPTION
"Data value."
::= { dataArray6 42 }

dataValue6_43 OBJECT-TYPE
SYNTAX INTEGER
MAX-ACCESS read-write
STATUS current
DESCRIPTION
"Data value."
::= { dataArray6 43 }

dataValue6_44 OBJECT-TYPE
SYNTAX INTEGER
MAX-ACCESS read-write
STATUS current
DESCRIPTION
"Data value."
::= { dataArray6 44 }

dataValue6_45 OBJECT-TYPE
SYNTAX INTEGER
MAX-ACCESS read-write
STATUS current
DESCRIPTION
"Data value."
::= { dataArray6 45 }

dataValue6_46 OBJECT-TYPE
SYNTAX INTEGER
MAX-ACCESS read-write
STATUS current
DESCRIPTION
"Data value."
::= { dataArray6 46 }

dataValue6_47 OBJECT-TYPE
SYNTAX INTEGER
MAX-ACCESS read-write
STATUS current
DESCRIPTION
"Data value."
::= { dataArray6 47 }

dataValue6_48 OBJECT-TYPE
SYNTAX INTEGER
MAX-ACCESS read-write
STATUS current
DESCRIPTION
"Data value."
::= { dataArray6 48 }

dataValue6_49 OBJECT-TYPE
SYNTAX INTEGER
MAX-ACCESS read-write
STATUS current
DESCRIPTION
"Data value."
::= { dataArray6 49 }

dataValue6_50 OBJECT-TYPE
SYNTAX INTEGER
MAX-ACCESS read-write
STATUS current
DESCRIPTION
"Data value."
::= { dataArray6 50 }

dataValue6_51 OBJECT-TYPE
SYNTAX INTEGER
MAX-ACCESS read-write
STATUS current
DESCRIPTION
"Data value."
::= { dataArray6 51 }

dataValue6_52 OBJECT-TYPE
SYNTAX INTEGER
MAX-ACCESS read-write
STATUS current
DESCRIPTION
"Data value."
::= { dataArray6 52 }

dataValue6_53 OBJECT-TYPE
SYNTAX INTEGER
MAX-ACCESS read-write
STATUS current
DESCRIPTION
"Data value."
::= { dataArray6 53 }

dataValue6_54 OBJECT-TYPE
SYNTAX INTEGER
MAX-ACCESS read-write
STATUS current
DESCRIPTION
"Data value."
::= { dataArray6 54 }

dataValue6_55 OBJECT-TYPE
SYNTAX INTEGER
MAX-ACCESS read-write
STATUS current
DESCRIPTION
"Data value."
::= { dataArray6 55 }

dataValue6_56 OBJECT-TYPE
SYNTAX INTEGER
MAX-ACCESS read-write
STATUS current
DESCRIPTION
"Data value."
::= { dataArray6 56 }

dataValue6_57 OBJECT-TYPE
SYNTAX INTEGER
MAX-ACCESS read-write
STATUS current
DESCRIPTION
"Data value."
::= { dataArray6 57 }

dataValue6_58 OBJECT-TYPE
SYNTAX INTEGER
MAX-ACCESS read-write
STATUS current
DESCRIPTION
"Data value."
::= { dataArray6 58 }

dataValue6_59 OBJECT-TYPE
SYNTAX INTEGER
MAX-ACCESS read-write
STATUS current
DESCRIPTION
"Data value."
::= { dataArray6 59 }

dataValue6_60 OBJECT-TYPE
SYNTAX INTEGER
MAX-ACCESS read-write
STATUS current
DESCRIPTION
"Data value."
::= { dataArray6 60 }

dataValue6_61 OBJECT-TYPE
SYNTAX INTEGER
MAX-ACCESS read-write
STATUS current
DESCRIPTION
"Data value."
::= { dataArray6 61 }

dataValue6_62 OBJECT-TYPE
SYNTAX INTEGER
MAX-ACCESS read-write
STATUS current
DESCRIPTION
"Data value."
::= { dataArray6 62 }

dataValue6_63 OBJECT-TYPE
SYNTAX INTEGER
MAX-ACCESS read-write
STATUS current
DESCRIPTION
"Data value."
::= { dataArray6 63 }

dataValue6_64 OBJECT-TYPE
SYNTAX INTEGER
MAX-ACCESS read-write
STATUS current
DESCRIPTION
"Data value."
::= { dataArray6 64 }

dataValue6_65 OBJECT-TYPE
SYNTAX INTEGER
MAX-ACCESS read-write
STATUS current
DESCRIPTION
"Data value."
::= { dataArray6 65 }

dataValue6_66 OBJECT-TYPE
SYNTAX INTEGER
MAX-ACCESS read-write
STATUS current
DESCRIPTION
"Data value."
::= { dataArray6 66 }

dataValue6_67 OBJECT-TYPE
SYNTAX INTEGER
MAX-ACCESS read-write
STATUS current
DESCRIPTION
"Data value."
::= { dataArray6 67 }

dataValue6_68 OBJECT-TYPE
SYNTAX INTEGER
MAX-ACCESS read-write
STATUS current
DESCRIPTION
"Data value."
::= { dataArray6 68 }

dataValue6_69 OBJECT-TYPE
SYNTAX INTEGER
MAX-ACCESS read-write
STATUS current
DESCRIPTION
"Data value."
::= { dataArray6 69 }

dataValue6_70 OBJECT-TYPE
SYNTAX INTEGER
MAX-ACCESS read-write
STATUS current
DESCRIPTION
"Data value."
::= { dataArray6 70 }

dataValue6_71 OBJECT-TYPE
SYNTAX INTEGER
MAX-ACCESS read-write
STATUS current
DESCRIPTION
"Data value."
::= { dataArray6 71 }

dataValue6_72 OBJECT-TYPE
SYNTAX INTEGER
MAX-ACCESS read-write
STATUS current
DESCRIPTION
"Data value."
::= { dataArray6 72 }

dataValue6_73 OBJECT-TYPE
SYNTAX INTEGER
MAX-ACCESS read-write
STATUS current
DESCRIPTION
"Data value."
::= { dataArray6 73 }

dataValue6_74 OBJECT-TYPE
SYNTAX INTEGER
MAX-ACCESS read-write
STATUS current
DESCRIPTION
"Data value."
::= { dataArray6 74 }

dataValue6_75 OBJECT-TYPE
SYNTAX INTEGER
MAX-ACCESS read-write
STATUS current
DESCRIPTION
"Data value."
::= { dataArray6 75 }

dataValue6_76 OBJECT-TYPE
SYNTAX INTEGER
MAX-ACCESS read-write
STATUS current
DESCRIPTION
"Data value."
::= { dataArray6 76 }

dataValue6_77 OBJECT-TYPE
SYNTAX INTEGER
MAX-ACCESS read-write
STATUS current
DESCRIPTION
"Data value."
::= { dataArray6 77 }

dataValue6_78 OBJECT-TYPE
SYNTAX INTEGER
MAX-ACCESS read-write
STATUS current
DESCRIPTION
"Data value."
::= { dataArray6 78 }

dataValue6_79 OBJECT-TYPE
SYNTAX INTEGER
MAX-ACCESS read-write
STATUS current
DESCRIPTION
"Data value."
::= { dataArray6 79 }

dataValue6_80 OBJECT-TYPE
SYNTAX INTEGER
MAX-ACCESS read-write
STATUS current
DESCRIPTION
"Data value."
::= { dataArray6 80 }

dataValue6_81 OBJECT-TYPE
SYNTAX INTEGER
MAX-ACCESS read-write
STATUS current
DESCRIPTION
"Data value."
::= { dataArray6 81 }

dataValue6_82 OBJECT-TYPE
SYNTAX INTEGER
MAX-ACCESS read-write
STATUS current
DESCRIPTION
"Data value."
::= { dataArray6 82 }

dataValue6_83 OBJECT-TYPE
SYNTAX INTEGER
MAX-ACCESS read-write
STATUS current
DESCRIPTION
"Data value."
::= { dataArray6 83 }

dataValue6_84 OBJECT-TYPE
SYNTAX INTEGER
MAX-ACCESS read-write
STATUS current
DESCRIPTION
"Data value."
::= { dataArray6 84 }

dataValue6_85 OBJECT-TYPE
SYNTAX INTEGER
MAX-ACCESS read-write
STATUS current
DESCRIPTION
"Data value."
::= { dataArray6 85 }

dataValue6_86 OBJECT-TYPE
SYNTAX INTEGER
MAX-ACCESS read-write
STATUS current
DESCRIPTION
"Data value."
::= { dataArray6 86 }

dataValue6_87 OBJECT-TYPE
SYNTAX INTEGER
MAX-ACCESS read-write
STATUS current
DESCRIPTION
"Data value."
::= { dataArray6 87 }

dataValue6_88 OBJECT-TYPE
SYNTAX INTEGER
MAX-ACCESS read-write
STATUS current
DESCRIPTION
"Data value."
::= { dataArray6 88 }

dataValue6_89 OBJECT-TYPE
SYNTAX INTEGER
MAX-ACCESS read-write
STATUS current
DESCRIPTION
"Data value."
::= { dataArray6 89 }

dataValue6_90 OBJECT-TYPE
SYNTAX INTEGER
MAX-ACCESS read-write
STATUS current
DESCRIPTION
"Data value."
::= { dataArray6 90 }

dataValue6_91 OBJECT-TYPE
SYNTAX INTEGER
MAX-ACCESS read-write
STATUS current
DESCRIPTION
"Data value."
::= { dataArray6 91 }

dataValue6_92 OBJECT-TYPE
SYNTAX INTEGER
MAX-ACCESS read-write
STATUS current
DESCRIPTION
"Data value."
::= { dataArray6 92 }

dataValue6_93 OBJECT-TYPE
SYNTAX INTEGER
MAX-ACCESS read-write
STATUS current
DESCRIPTION
"Data value."
::= { dataArray6 93 }

dataValue6_94 OBJECT-TYPE
SYNTAX INTEGER
MAX-ACCESS read-write
STATUS current
DESCRIPTION
"Data value."
::= { dataArray6 94 }

dataValue6_95 OBJECT-TYPE
SYNTAX INTEGER
MAX-ACCESS read-write
STATUS current
DESCRIPTION
"Data value."
::= { dataArray6 95 }

dataValue6_96 OBJECT-TYPE
SYNTAX INTEGER
MAX-ACCESS read-write
STATUS current
DESCRIPTION
"Data value."
::= { dataArray6 96 }

dataValue6_97 OBJECT-TYPE
SYNTAX INTEGER
MAX-ACCESS read-write
STATUS current
DESCRIPTION
"Data value."
::= { dataArray6 97 }

dataValue6_98 OBJECT-TYPE
SYNTAX INTEGER
MAX-ACCESS read-write
STATUS current
DESCRIPTION
"Data value."
::= { dataArray6 98 }

dataValue6_99 OBJECT-TYPE
SYNTAX INTEGER
MAX-ACCESS read-write
STATUS current
DESCRIPTION
"Data value."
::= { dataArray6 99 }

dataValue6_100 OBJECT-TYPE
SYNTAX INTEGER
MAX-ACCESS read-write
STATUS current
DESCRIPTION
"Data value."
::= { dataArray6 100 }

dataValue6_101 OBJECT-TYPE
SYNTAX INTEGER
MAX-ACCESS read-write
STATUS current
DESCRIPTION
"Data value."
::= { dataArray6 101 }

dataValue6_102 OBJECT-TYPE
SYNTAX INTEGER
MAX-ACCESS read-write
STATUS current
DESCRIPTION
"Data value."
::= { dataArray6 102 }

dataValue6_103 OBJECT-TYPE
SYNTAX INTEGER
MAX-ACCESS read-write
STATUS current
DESCRIPTION
"Data value."
::= { dataArray6 103 }

dataValue6_104 OBJECT-TYPE
SYNTAX INTEGER
MAX-ACCESS read-write
STATUS current
DESCRIPTION
"Data value."
::= { dataArray6 104 }

dataValue6_105 OBJECT-TYPE
SYNTAX INTEGER
MAX-ACCESS read-write
STATUS current
DESCRIPTION
"Data value."
::= { dataArray6 105 }

dataValue6_106 OBJECT-TYPE
SYNTAX INTEGER
MAX-ACCESS read-write
STATUS current
DESCRIPTION
"Data value."
::= { dataArray6 106 }

dataValue6_107 OBJECT-TYPE
SYNTAX INTEGER
MAX-ACCESS read-write
STATUS current
DESCRIPTION
"Data value."
::= { dataArray6 107 }

dataValue6_108 OBJECT-TYPE
SYNTAX INTEGER
MAX-ACCESS read-write
STATUS current
DESCRIPTION
"Data value."
::= { dataArray6 108 }

dataValue6_109 OBJECT-TYPE
SYNTAX INTEGER
MAX-ACCESS read-write
STATUS current
DESCRIPTION
"Data value."
::= { dataArray6 109 }

dataValue6_110 OBJECT-TYPE
SYNTAX INTEGER
MAX-ACCESS read-write
STATUS current
DESCRIPTION
"Data value."
::= { dataArray6 110 }

dataValue6_111 OBJECT-TYPE
SYNTAX INTEGER
MAX-ACCESS read-write
STATUS current
DESCRIPTION
"Data value."
::= { dataArray6 111 }

dataValue6_112 OBJECT-TYPE
SYNTAX INTEGER
MAX-ACCESS read-write
STATUS current
DESCRIPTION
"Data value."
::= { dataArray6 112 }

dataValue6_113 OBJECT-TYPE
SYNTAX INTEGER
MAX-ACCESS read-write
STATUS current
DESCRIPTION
"Data value."
::= { dataArray6 113 }

dataValue6_114 OBJECT-TYPE
SYNTAX INTEGER
MAX-ACCESS read-write
STATUS current
DESCRIPTION
"Data value."
::= { dataArray6 114 }

dataValue6_115 OBJECT-TYPE
SYNTAX INTEGER
MAX-ACCESS read-write
STATUS current
DESCRIPTION
"Data value."
::= { dataArray6 115 }

dataValue6_116 OBJECT-TYPE
SYNTAX INTEGER
MAX-ACCESS read-write
STATUS current
DESCRIPTION
"Data value."
::= { dataArray6 116 }

dataValue6_117 OBJECT-TYPE
SYNTAX INTEGER
MAX-ACCESS read-write
STATUS current
DESCRIPTION
"Data value."
::= { dataArray6 117 }

dataValue6_118 OBJECT-TYPE
SYNTAX INTEGER
MAX-ACCESS read-write
STATUS current
DESCRIPTION
"Data value."
::= { dataArray6 118 }

dataValue6_119 OBJECT-TYPE
SYNTAX INTEGER
MAX-ACCESS read-write
STATUS current
DESCRIPTION
"Data value."
::= { dataArray6 119 }

dataValue6_120 OBJECT-TYPE
SYNTAX INTEGER
MAX-ACCESS read-write
STATUS current
DESCRIPTION
"Data value."
::= { dataArray6 120 }

dataValue6_121 OBJECT-TYPE
SYNTAX INTEGER
MAX-ACCESS read-write
STATUS current
DESCRIPTION
"Data value."
::= { dataArray6 121 }

dataValue6_122 OBJECT-TYPE
SYNTAX INTEGER
MAX-ACCESS read-write
STATUS current
DESCRIPTION
"Data value."
::= { dataArray6 122 }

dataValue6_123 OBJECT-TYPE
SYNTAX INTEGER
MAX-ACCESS read-write
STATUS current
DESCRIPTION
"Data value."
::= { dataArray6 123 }

dataValue6_124 OBJECT-TYPE
SYNTAX INTEGER
MAX-ACCESS read-write
STATUS current
DESCRIPTION
"Data value."
::= { dataArray6 124 }

dataValue6_125 OBJECT-TYPE
SYNTAX INTEGER
MAX-ACCESS read-write
STATUS current
DESCRIPTION
"Data value."
::= { dataArray6 125 }

dataValue6_126 OBJECT-TYPE
SYNTAX INTEGER
MAX-ACCESS read-write
STATUS current
DESCRIPTION
"Data value."
::= { dataArray6 126 }

dataValue6_127 OBJECT-TYPE
SYNTAX INTEGER
MAX-ACCESS read-write
STATUS current
DESCRIPTION
"Data value."
::= { dataArray6 127 }

dataValue6_128 OBJECT-TYPE
SYNTAX INTEGER
MAX-ACCESS read-write
STATUS current
DESCRIPTION
"Data value."
::= { dataArray6 128 }

dataValue6_129 OBJECT-TYPE
SYNTAX INTEGER
MAX-ACCESS read-write
STATUS current
DESCRIPTION
"Data value."
::= { dataArray6 129 }

dataValue6_130 OBJECT-TYPE
SYNTAX INTEGER
MAX-ACCESS read-write
STATUS current
DESCRIPTION
"Data value."
::= { dataArray6 130 }

dataValue6_131 OBJECT-TYPE
SYNTAX INTEGER
MAX-ACCESS read-write
STATUS current
DESCRIPTION
"Data value."
::= { dataArray6 131 }

dataValue6_132 OBJECT-TYPE
SYNTAX INTEGER
MAX-ACCESS read-write
STATUS current
DESCRIPTION
"Data value."
::= { dataArray6 132 }

dataValue6_133 OBJECT-TYPE
SYNTAX INTEGER
MAX-ACCESS read-write
STATUS current
DESCRIPTION
"Data value."
::= { dataArray6 133 }

dataValue6_134 OBJECT-TYPE
SYNTAX INTEGER
MAX-ACCESS read-write
STATUS current
DESCRIPTION
"Data value."
::= { dataArray6 134 }

dataValue6_135 OBJECT-TYPE
SYNTAX INTEGER
MAX-ACCESS read-write
STATUS current
DESCRIPTION
"Data value."
::= { dataArray6 135 }

dataValue6_136 OBJECT-TYPE
SYNTAX INTEGER
MAX-ACCESS read-write
STATUS current
DESCRIPTION
"Data value."
::= { dataArray6 136 }

dataValue6_137 OBJECT-TYPE
SYNTAX INTEGER
MAX-ACCESS read-write
STATUS current
DESCRIPTION
"Data value."
::= { dataArray6 137 }

dataValue6_138 OBJECT-TYPE
SYNTAX INTEGER
MAX-ACCESS read-write
STATUS current
DESCRIPTION
"Data value."
::= { dataArray6 138 }

dataValue6_139 OBJECT-TYPE
SYNTAX INTEGER
MAX-ACCESS read-write
STATUS current
DESCRIPTION
"Data value."
::= { dataArray6 139 }

dataValue6_140 OBJECT-TYPE
SYNTAX INTEGER
MAX-ACCESS read-write
STATUS current
DESCRIPTION
"Data value."
::= { dataArray6 140 }

dataValue6_141 OBJECT-TYPE
SYNTAX INTEGER
MAX-ACCESS read-write
STATUS current
DESCRIPTION
"Data value."
::= { dataArray6 141 }

dataValue6_142 OBJECT-TYPE
SYNTAX INTEGER
MAX-ACCESS read-write
STATUS current
DESCRIPTION
"Data value."
::= { dataArray6 142 }

dataValue6_143 OBJECT-TYPE
SYNTAX INTEGER
MAX-ACCESS read-write
STATUS current
DESCRIPTION
"Data value."
::= { dataArray6 143 }

dataValue6_144 OBJECT-TYPE
SYNTAX INTEGER
MAX-ACCESS read-write
STATUS current
DESCRIPTION
"Data value."
::= { dataArray6 144 }

dataValue6_145 OBJECT-TYPE
SYNTAX INTEGER
MAX-ACCESS read-write
STATUS current
DESCRIPTION
"Data value."
::= { dataArray6 145 }

dataValue6_146 OBJECT-TYPE
SYNTAX INTEGER
MAX-ACCESS read-write
STATUS current
DESCRIPTION
"Data value."
::= { dataArray6 146 }

dataValue6_147 OBJECT-TYPE
SYNTAX INTEGER
MAX-ACCESS read-write
STATUS current
DESCRIPTION
"Data value."
::= { dataArray6 147 }

dataValue6_148 OBJECT-TYPE
SYNTAX INTEGER
MAX-ACCESS read-write
STATUS current
DESCRIPTION
"Data value."
::= { dataArray6 148 }

dataValue6_149 OBJECT-TYPE
SYNTAX INTEGER
MAX-ACCESS read-write
STATUS current
DESCRIPTION
"Data value."
::= { dataArray6 149 }

dataValue6_150 OBJECT-TYPE
SYNTAX INTEGER
MAX-ACCESS read-write
STATUS current
DESCRIPTION
"Data value."
::= { dataArray6 150 }

dataValue6_151 OBJECT-TYPE
SYNTAX INTEGER
MAX-ACCESS read-write
STATUS current
DESCRIPTION
"Data value."
::= { dataArray6 151 }

dataValue6_152 OBJECT-TYPE
SYNTAX INTEGER
MAX-ACCESS read-write
STATUS current
DESCRIPTION
"Data value."
::= { dataArray6 152 }

dataValue6_153 OBJECT-TYPE
SYNTAX INTEGER
MAX-ACCESS read-write
STATUS current
DESCRIPTION
"Data value."
::= { dataArray6 153 }

dataValue6_154 OBJECT-TYPE
SYNTAX INTEGER
MAX-ACCESS read-write
STATUS current
DESCRIPTION
"Data value."
::= { dataArray6 154 }

dataValue6_155 OBJECT-TYPE
SYNTAX INTEGER
MAX-ACCESS read-write
STATUS current
DESCRIPTION
"Data value."
::= { dataArray6 155 }

dataValue6_156 OBJECT-TYPE
SYNTAX INTEGER
MAX-ACCESS read-write
STATUS current
DESCRIPTION
"Data value."
::= { dataArray6 156 }

dataValue6_157 OBJECT-TYPE
SYNTAX INTEGER
MAX-ACCESS read-write
STATUS current
DESCRIPTION
"Data value."
::= { dataArray6 157 }

dataValue6_158 OBJECT-TYPE
SYNTAX INTEGER
MAX-ACCESS read-write
STATUS current
DESCRIPTION
"Data value."
::= { dataArray6 158 }

dataValue6_159 OBJECT-TYPE
SYNTAX INTEGER
MAX-ACCESS read-write
STATUS current
DESCRIPTION
"Data value."
::= { dataArray6 159 }

dataValue6_160 OBJECT-TYPE
SYNTAX INTEGER
MAX-ACCESS read-write
STATUS current
DESCRIPTION
"Data value."
::= { dataArray6 160 }

dataValue6_161 OBJECT-TYPE
SYNTAX INTEGER
MAX-ACCESS read-write
STATUS current
DESCRIPTION
"Data value."
::= { dataArray6 161 }

dataValue6_162 OBJECT-TYPE
SYNTAX INTEGER
MAX-ACCESS read-write
STATUS current
DESCRIPTION
"Data value."
::= { dataArray6 162 }

dataValue6_163 OBJECT-TYPE
SYNTAX INTEGER
MAX-ACCESS read-write
STATUS current
DESCRIPTION
"Data value."
::= { dataArray6 163 }

dataValue6_164 OBJECT-TYPE
SYNTAX INTEGER
MAX-ACCESS read-write
STATUS current
DESCRIPTION
"Data value."
::= { dataArray6 164 }

dataValue6_165 OBJECT-TYPE
SYNTAX INTEGER
MAX-ACCESS read-write
STATUS current
DESCRIPTION
"Data value."
::= { dataArray6 165 }

dataValue6_166 OBJECT-TYPE
SYNTAX INTEGER
MAX-ACCESS read-write
STATUS current
DESCRIPTION
"Data value."
::= { dataArray6 166 }

dataValue6_167 OBJECT-TYPE
SYNTAX INTEGER
MAX-ACCESS read-write
STATUS current
DESCRIPTION
"Data value."
::= { dataArray6 167 }

dataValue6_168 OBJECT-TYPE
SYNTAX INTEGER
MAX-ACCESS read-write
STATUS current
DESCRIPTION
"Data value."
::= { dataArray6 168 }

dataValue6_169 OBJECT-TYPE
SYNTAX INTEGER
MAX-ACCESS read-write
STATUS current
DESCRIPTION
"Data value."
::= { dataArray6 169 }

dataValue6_170 OBJECT-TYPE
SYNTAX INTEGER
MAX-ACCESS read-write
STATUS current
DESCRIPTION
"Data value."
::= { dataArray6 170 }

dataValue6_171 OBJECT-TYPE
SYNTAX INTEGER
MAX-ACCESS read-write
STATUS current
DESCRIPTION
"Data value."
::= { dataArray6 171 }

dataValue6_172 OBJECT-TYPE
SYNTAX INTEGER
MAX-ACCESS read-write
STATUS current
DESCRIPTION
"Data value."
::= { dataArray6 172 }

dataValue6_173 OBJECT-TYPE
SYNTAX INTEGER
MAX-ACCESS read-write
STATUS current
DESCRIPTION
"Data value."
::= { dataArray6 173 }

dataValue6_174 OBJECT-TYPE
SYNTAX INTEGER
MAX-ACCESS read-write
STATUS current
DESCRIPTION
"Data value."
::= { dataArray6 174 }

dataValue6_175 OBJECT-TYPE
SYNTAX INTEGER
MAX-ACCESS read-write
STATUS current
DESCRIPTION
"Data value."
::= { dataArray6 175 }

dataValue6_176 OBJECT-TYPE
SYNTAX INTEGER
MAX-ACCESS read-write
STATUS current
DESCRIPTION
"Data value."
::= { dataArray6 176 }

dataValue6_177 OBJECT-TYPE
SYNTAX INTEGER
MAX-ACCESS read-write
STATUS current
DESCRIPTION
"Data value."
::= { dataArray6 177 }

dataValue6_178 OBJECT-TYPE
SYNTAX INTEGER
MAX-ACCESS read-write
STATUS current
DESCRIPTION
"Data value."
::= { dataArray6 178 }

dataValue6_179 OBJECT-TYPE
SYNTAX INTEGER
MAX-ACCESS read-write
STATUS current
DESCRIPTION
"Data value."
::= { dataArray6 179 }

dataValue6_180 OBJECT-TYPE
SYNTAX INTEGER
MAX-ACCESS read-write
STATUS current
DESCRIPTION
"Data value."
::= { dataArray6 180 }

dataValue6_181 OBJECT-TYPE
SYNTAX INTEGER
MAX-ACCESS read-write
STATUS current
DESCRIPTION
"Data value."
::= { dataArray6 181 }

dataValue6_182 OBJECT-TYPE
SYNTAX INTEGER
MAX-ACCESS read-write
STATUS current
DESCRIPTION
"Data value."
::= { dataArray6 182 }

dataValue6_183 OBJECT-TYPE
SYNTAX INTEGER
MAX-ACCESS read-write
STATUS current
DESCRIPTION
"Data value."
::= { dataArray6 183 }

dataValue6_184 OBJECT-TYPE
SYNTAX INTEGER
MAX-ACCESS read-write
STATUS current
DESCRIPTION
"Data value."
::= { dataArray6 184 }

dataValue6_185 OBJECT-TYPE
SYNTAX INTEGER
MAX-ACCESS read-write
STATUS current
DESCRIPTION
"Data value."
::= { dataArray6 185 }

dataValue6_186 OBJECT-TYPE
SYNTAX INTEGER
MAX-ACCESS read-write
STATUS current
DESCRIPTION
"Data value."
::= { dataArray6 186 }

dataValue6_187 OBJECT-TYPE
SYNTAX INTEGER
MAX-ACCESS read-write
STATUS current
DESCRIPTION
"Data value."
::= { dataArray6 187 }

dataValue6_188 OBJECT-TYPE
SYNTAX INTEGER
MAX-ACCESS read-write
STATUS current
DESCRIPTION
"Data value."
::= { dataArray6 188 }

dataValue6_189 OBJECT-TYPE
SYNTAX INTEGER
MAX-ACCESS read-write
STATUS current
DESCRIPTION
"Data value."
::= { dataArray6 189 }

dataValue6_190 OBJECT-TYPE
SYNTAX INTEGER
MAX-ACCESS read-write
STATUS current
DESCRIPTION
"Data value."
::= { dataArray6 190 }

dataValue6_191 OBJECT-TYPE
SYNTAX INTEGER
MAX-ACCESS read-write
STATUS current
DESCRIPTION
"Data value."
::= { dataArray6 191 }

dataValue6_192 OBJECT-TYPE
SYNTAX INTEGER
MAX-ACCESS read-write
STATUS current
DESCRIPTION
"Data value."
::= { dataArray6 192 }

dataValue6_193 OBJECT-TYPE
SYNTAX INTEGER
MAX-ACCESS read-write
STATUS current
DESCRIPTION
"Data value."
::= { dataArray6 193 }

dataValue6_194 OBJECT-TYPE
SYNTAX INTEGER
MAX-ACCESS read-write
STATUS current
DESCRIPTION
"Data value."
::= { dataArray6 194 }

dataValue6_195 OBJECT-TYPE
SYNTAX INTEGER
MAX-ACCESS read-write
STATUS current
DESCRIPTION
"Data value."
::= { dataArray6 195 }

dataValue6_196 OBJECT-TYPE
SYNTAX INTEGER
MAX-ACCESS read-write
STATUS current
DESCRIPTION
"Data value."
::= { dataArray6 196 }

dataValue6_197 OBJECT-TYPE
SYNTAX INTEGER
MAX-ACCESS read-write
STATUS current
DESCRIPTION
"Data value."
::= { dataArray6 197 }

dataValue6_198 OBJECT-TYPE
SYNTAX INTEGER
MAX-ACCESS read-write
STATUS current
DESCRIPTION
"Data value."
::= { dataArray6 198 }

dataValue6_199 OBJECT-TYPE
SYNTAX INTEGER
MAX-ACCESS read-write
STATUS current
DESCRIPTION
"Data value."
::= { dataArray6 199 }

dataValue6_200 OBJECT-TYPE
SYNTAX INTEGER
MAX-ACCESS read-write
STATUS current
DESCRIPTION
"Data value."
::= { dataArray6 200 }

dataValue6_201 OBJECT-TYPE
SYNTAX INTEGER
MAX-ACCESS read-write
STATUS current
DESCRIPTION
"Data value."
::= { dataArray6 201 }

dataValue6_202 OBJECT-TYPE
SYNTAX INTEGER
MAX-ACCESS read-write
STATUS current
DESCRIPTION
"Data value."
::= { dataArray6 202 }

dataValue6_203 OBJECT-TYPE
SYNTAX INTEGER
MAX-ACCESS read-write
STATUS current
DESCRIPTION
"Data value."
::= { dataArray6 203 }

dataValue6_204 OBJECT-TYPE
SYNTAX INTEGER
MAX-ACCESS read-write
STATUS current
DESCRIPTION
"Data value."
::= { dataArray6 204 }

dataValue6_205 OBJECT-TYPE
SYNTAX INTEGER
MAX-ACCESS read-write
STATUS current
DESCRIPTION
"Data value."
::= { dataArray6 205 }

dataValue6_206 OBJECT-TYPE
SYNTAX INTEGER
MAX-ACCESS read-write
STATUS current
DESCRIPTION
"Data value."
::= { dataArray6 206 }

dataValue6_207 OBJECT-TYPE
SYNTAX INTEGER
MAX-ACCESS read-write
STATUS current
DESCRIPTION
"Data value."
::= { dataArray6 207 }

dataValue6_208 OBJECT-TYPE
SYNTAX INTEGER
MAX-ACCESS read-write
STATUS current
DESCRIPTION
"Data value."
::= { dataArray6 208 }

dataValue6_209 OBJECT-TYPE
SYNTAX INTEGER
MAX-ACCESS read-write
STATUS current
DESCRIPTION
"Data value."
::= { dataArray6 209 }

dataValue6_210 OBJECT-TYPE
SYNTAX INTEGER
MAX-ACCESS read-write
STATUS current
DESCRIPTION
"Data value."
::= { dataArray6 210 }

dataValue6_211 OBJECT-TYPE
SYNTAX INTEGER
MAX-ACCESS read-write
STATUS current
DESCRIPTION
"Data value."
::= { dataArray6 211 }

dataValue6_212 OBJECT-TYPE
SYNTAX INTEGER
MAX-ACCESS read-write
STATUS current
DESCRIPTION
"Data value."
::= { dataArray6 212 }

dataValue6_213 OBJECT-TYPE
SYNTAX INTEGER
MAX-ACCESS read-write
STATUS current
DESCRIPTION
"Data value."
::= { dataArray6 213 }

dataValue6_214 OBJECT-TYPE
SYNTAX INTEGER
MAX-ACCESS read-write
STATUS current
DESCRIPTION
"Data value."
::= { dataArray6 214 }

dataValue6_215 OBJECT-TYPE
SYNTAX INTEGER
MAX-ACCESS read-write
STATUS current
DESCRIPTION
"Data value."
::= { dataArray6 215 }

dataValue6_216 OBJECT-TYPE
SYNTAX INTEGER
MAX-ACCESS read-write
STATUS current
DESCRIPTION
"Data value."
::= { dataArray6 216 }

dataValue6_217 OBJECT-TYPE
SYNTAX INTEGER
MAX-ACCESS read-write
STATUS current
DESCRIPTION
"Data value."
::= { dataArray6 217 }

dataValue6_218 OBJECT-TYPE
SYNTAX INTEGER
MAX-ACCESS read-write
STATUS current
DESCRIPTION
"Data value."
::= { dataArray6 218 }

dataValue6_219 OBJECT-TYPE
SYNTAX INTEGER
MAX-ACCESS read-write
STATUS current
DESCRIPTION
"Data value."
::= { dataArray6 219 }

dataValue6_220 OBJECT-TYPE
SYNTAX INTEGER
MAX-ACCESS read-write
STATUS current
DESCRIPTION
"Data value."
::= { dataArray6 220 }

dataValue6_221 OBJECT-TYPE
SYNTAX INTEGER
MAX-ACCESS read-write
STATUS current
DESCRIPTION
"Data value."
::= { dataArray6 221 }

dataValue6_222 OBJECT-TYPE
SYNTAX INTEGER
MAX-ACCESS read-write
STATUS current
DESCRIPTION
"Data value."
::= { dataArray6 222 }

dataValue6_223 OBJECT-TYPE
SYNTAX INTEGER
MAX-ACCESS read-write
STATUS current
DESCRIPTION
"Data value."
::= { dataArray6 223 }

dataValue6_224 OBJECT-TYPE
SYNTAX INTEGER
MAX-ACCESS read-write
STATUS current
DESCRIPTION
"Data value."
::= { dataArray6 224 }

dataValue6_225 OBJECT-TYPE
SYNTAX INTEGER
MAX-ACCESS read-write
STATUS current
DESCRIPTION
"Data value."
::= { dataArray6 225 }

dataValue6_226 OBJECT-TYPE
SYNTAX INTEGER
MAX-ACCESS read-write
STATUS current
DESCRIPTION
"Data value."
::= { dataArray6 226 }

dataValue6_227 OBJECT-TYPE
SYNTAX INTEGER
MAX-ACCESS read-write
STATUS current
DESCRIPTION
"Data value."
::= { dataArray6 227 }

dataValue6_228 OBJECT-TYPE
SYNTAX INTEGER
MAX-ACCESS read-write
STATUS current
DESCRIPTION
"Data value."
::= { dataArray6 228 }

dataValue6_229 OBJECT-TYPE
SYNTAX INTEGER
MAX-ACCESS read-write
STATUS current
DESCRIPTION
"Data value."
::= { dataArray6 229 }

dataValue6_230 OBJECT-TYPE
SYNTAX INTEGER
MAX-ACCESS read-write
STATUS current
DESCRIPTION
"Data value."
::= { dataArray6 230 }

dataValue6_231 OBJECT-TYPE
SYNTAX INTEGER
MAX-ACCESS read-write
STATUS current
DESCRIPTION
"Data value."
::= { dataArray6 231 }

dataValue6_232 OBJECT-TYPE
SYNTAX INTEGER
MAX-ACCESS read-write
STATUS current
DESCRIPTION
"Data value."
::= { dataArray6 232 }

dataValue6_233 OBJECT-TYPE
SYNTAX INTEGER
MAX-ACCESS read-write
STATUS current
DESCRIPTION
"Data value."
::= { dataArray6 233 }

dataValue6_234 OBJECT-TYPE
SYNTAX INTEGER
MAX-ACCESS read-write
STATUS current
DESCRIPTION
"Data value."
::= { dataArray6 234 }

dataValue6_235 OBJECT-TYPE
SYNTAX INTEGER
MAX-ACCESS read-write
STATUS current
DESCRIPTION
"Data value."
::= { dataArray6 235 }

dataValue6_236 OBJECT-TYPE
SYNTAX INTEGER
MAX-ACCESS read-write
STATUS current
DESCRIPTION
"Data value."
::= { dataArray6 236 }

dataValue6_237 OBJECT-TYPE
SYNTAX INTEGER
MAX-ACCESS read-write
STATUS current
DESCRIPTION
"Data value."
::= { dataArray6 237 }

dataValue6_238 OBJECT-TYPE
SYNTAX INTEGER
MAX-ACCESS read-write
STATUS current
DESCRIPTION
"Data value."
::= { dataArray6 238 }

dataValue6_239 OBJECT-TYPE
SYNTAX INTEGER
MAX-ACCESS read-write
STATUS current
DESCRIPTION
"Data value."
::= { dataArray6 239 }

dataValue6_240 OBJECT-TYPE
SYNTAX INTEGER
MAX-ACCESS read-write
STATUS current
DESCRIPTION
"Data value."
::= { dataArray6 240 }

dataValue6_241 OBJECT-TYPE
SYNTAX INTEGER
MAX-ACCESS read-write
STATUS current
DESCRIPTION
"Data value."
::= { dataArray6 241 }

dataValue6_242 OBJECT-TYPE
SYNTAX INTEGER
MAX-ACCESS read-write
STATUS current
DESCRIPTION
"Data value."
::= { dataArray6 242 }

dataValue6_243 OBJECT-TYPE
SYNTAX INTEGER
MAX-ACCESS read-write
STATUS current
DESCRIPTION
"Data value."
::= { dataArray6 243 }

dataValue6_244 OBJECT-TYPE
SYNTAX INTEGER
MAX-ACCESS read-write
STATUS current
DESCRIPTION
"Data value."
::= { dataArray6 244 }

dataValue6_245 OBJECT-TYPE
SYNTAX INTEGER
MAX-ACCESS read-write
STATUS current
DESCRIPTION
"Data value."
::= { dataArray6 245 }

dataValue6_246 OBJECT-TYPE
SYNTAX INTEGER
MAX-ACCESS read-write
STATUS current
DESCRIPTION
"Data value."
::= { dataArray6 246 }

dataValue6_247 OBJECT-TYPE
SYNTAX INTEGER
MAX-ACCESS read-write
STATUS current
DESCRIPTION
"Data value."
::= { dataArray6 247 }

dataValue6_248 OBJECT-TYPE
SYNTAX INTEGER
MAX-ACCESS read-write
STATUS current
DESCRIPTION
"Data value."
::= { dataArray6 248 }

dataValue6_249 OBJECT-TYPE
SYNTAX INTEGER
MAX-ACCESS read-write
STATUS current
DESCRIPTION
"Data value."
::= { dataArray6 249 }

dataValue6_250 OBJECT-TYPE
SYNTAX INTEGER
MAX-ACCESS read-write
STATUS current
DESCRIPTION
"Data value."
::= { dataArray6 250 }

dataValue6_251 OBJECT-TYPE
SYNTAX INTEGER
MAX-ACCESS read-write
STATUS current
DESCRIPTION
"Data value."
::= { dataArray6 251 }

dataValue6_252 OBJECT-TYPE
SYNTAX INTEGER
MAX-ACCESS read-write
STATUS current
DESCRIPTION
"Data value."
::= { dataArray6 252 }

dataValue6_253 OBJECT-TYPE
SYNTAX INTEGER
MAX-ACCESS read-write
STATUS current
DESCRIPTION
"Data value."
::= { dataArray6 253 }

dataValue6_254 OBJECT-TYPE
SYNTAX INTEGER
MAX-ACCESS read-write
STATUS current
DESCRIPTION
"Data value."
::= { dataArray6 254 }

dataValue6_255 OBJECT-TYPE
SYNTAX INTEGER
MAX-ACCESS read-write
STATUS current
DESCRIPTION
"Data value."
::= { dataArray6 255 }

dataValue6_256 OBJECT-TYPE
SYNTAX INTEGER
MAX-ACCESS read-write
STATUS current
DESCRIPTION
"Data value."
::= { dataArray6 256 }

dataValue6_257 OBJECT-TYPE
SYNTAX INTEGER
MAX-ACCESS read-write
STATUS current
DESCRIPTION
"Data value."
::= { dataArray6 257 }

dataValue6_258 OBJECT-TYPE
SYNTAX INTEGER
MAX-ACCESS read-write
STATUS current
DESCRIPTION
"Data value."
::= { dataArray6 258 }

dataValue6_259 OBJECT-TYPE
SYNTAX INTEGER
MAX-ACCESS read-write
STATUS current
DESCRIPTION
"Data value."
::= { dataArray6 259 }

dataValue6_260 OBJECT-TYPE
SYNTAX INTEGER
MAX-ACCESS read-write
STATUS current
DESCRIPTION
"Data value."
::= { dataArray6 260 }

dataValue6_261 OBJECT-TYPE
SYNTAX INTEGER
MAX-ACCESS read-write
STATUS current
DESCRIPTION
"Data value."
::= { dataArray6 261 }

dataValue6_262 OBJECT-TYPE
SYNTAX INTEGER
MAX-ACCESS read-write
STATUS current
DESCRIPTION
"Data value."
::= { dataArray6 262 }

dataValue6_263 OBJECT-TYPE
SYNTAX INTEGER
MAX-ACCESS read-write
STATUS current
DESCRIPTION
"Data value."
::= { dataArray6 263 }

dataValue6_264 OBJECT-TYPE
SYNTAX INTEGER
MAX-ACCESS read-write
STATUS current
DESCRIPTION
"Data value."
::= { dataArray6 264 }

dataValue6_265 OBJECT-TYPE
SYNTAX INTEGER
MAX-ACCESS read-write
STATUS current
DESCRIPTION
"Data value."
::= { dataArray6 265 }

dataValue6_266 OBJECT-TYPE
SYNTAX INTEGER
MAX-ACCESS read-write
STATUS current
DESCRIPTION
"Data value."
::= { dataArray6 266 }

dataValue6_267 OBJECT-TYPE
SYNTAX INTEGER
MAX-ACCESS read-write
STATUS current
DESCRIPTION
"Data value."
::= { dataArray6 267 }

dataValue6_268 OBJECT-TYPE
SYNTAX INTEGER
MAX-ACCESS read-write
STATUS current
DESCRIPTION
"Data value."
::= { dataArray6 268 }

dataValue6_269 OBJECT-TYPE
SYNTAX INTEGER
MAX-ACCESS read-write
STATUS current
DESCRIPTION
"Data value."
::= { dataArray6 269 }

dataValue6_270 OBJECT-TYPE
SYNTAX INTEGER
MAX-ACCESS read-write
STATUS current
DESCRIPTION
"Data value."
::= { dataArray6 270 }

dataValue6_271 OBJECT-TYPE
SYNTAX INTEGER
MAX-ACCESS read-write
STATUS current
DESCRIPTION
"Data value."
::= { dataArray6 271 }

dataValue6_272 OBJECT-TYPE
SYNTAX INTEGER
MAX-ACCESS read-write
STATUS current
DESCRIPTION
"Data value."
::= { dataArray6 272 }

dataValue6_273 OBJECT-TYPE
SYNTAX INTEGER
MAX-ACCESS read-write
STATUS current
DESCRIPTION
"Data value."
::= { dataArray6 273 }

dataValue6_274 OBJECT-TYPE
SYNTAX INTEGER
MAX-ACCESS read-write
STATUS current
DESCRIPTION
"Data value."
::= { dataArray6 274 }

dataValue6_275 OBJECT-TYPE
SYNTAX INTEGER
MAX-ACCESS read-write
STATUS current
DESCRIPTION
"Data value."
::= { dataArray6 275 }

dataValue6_276 OBJECT-TYPE
SYNTAX INTEGER
MAX-ACCESS read-write
STATUS current
DESCRIPTION
"Data value."
::= { dataArray6 276 }

dataValue6_277 OBJECT-TYPE
SYNTAX INTEGER
MAX-ACCESS read-write
STATUS current
DESCRIPTION
"Data value."
::= { dataArray6 277 }

dataValue6_278 OBJECT-TYPE
SYNTAX INTEGER
MAX-ACCESS read-write
STATUS current
DESCRIPTION
"Data value."
::= { dataArray6 278 }

dataValue6_279 OBJECT-TYPE
SYNTAX INTEGER
MAX-ACCESS read-write
STATUS current
DESCRIPTION
"Data value."
::= { dataArray6 279 }

dataValue6_280 OBJECT-TYPE
SYNTAX INTEGER
MAX-ACCESS read-write
STATUS current
DESCRIPTION
"Data value."
::= { dataArray6 280 }

dataValue6_281 OBJECT-TYPE
SYNTAX INTEGER
MAX-ACCESS read-write
STATUS current
DESCRIPTION
"Data value."
::= { dataArray6 281 }

dataValue6_282 OBJECT-TYPE
SYNTAX INTEGER
MAX-ACCESS read-write
STATUS current
DESCRIPTION
"Data value."
::= { dataArray6 282 }

dataValue6_283 OBJECT-TYPE
SYNTAX INTEGER
MAX-ACCESS read-write
STATUS current
DESCRIPTION
"Data value."
::= { dataArray6 283 }

dataValue6_284 OBJECT-TYPE
SYNTAX INTEGER
MAX-ACCESS read-write
STATUS current
DESCRIPTION
"Data value."
::= { dataArray6 284 }

dataValue6_285 OBJECT-TYPE
SYNTAX INTEGER
MAX-ACCESS read-write
STATUS current
DESCRIPTION
"Data value."
::= { dataArray6 285 }

dataValue6_286 OBJECT-TYPE
SYNTAX INTEGER
MAX-ACCESS read-write
STATUS current
DESCRIPTION
"Data value."
::= { dataArray6 286 }

dataValue6_287 OBJECT-TYPE
SYNTAX INTEGER
MAX-ACCESS read-write
STATUS current
DESCRIPTION
"Data value."
::= { dataArray6 287 }

dataValue6_288 OBJECT-TYPE
SYNTAX INTEGER
MAX-ACCESS read-write
STATUS current
DESCRIPTION
"Data value."
::= { dataArray6 288 }

dataValue6_289 OBJECT-TYPE
SYNTAX INTEGER
MAX-ACCESS read-write
STATUS current
DESCRIPTION
"Data value."
::= { dataArray6 289 }

dataValue6_290 OBJECT-TYPE
SYNTAX INTEGER
MAX-ACCESS read-write
STATUS current
DESCRIPTION
"Data value."
::= { dataArray6 290 }

dataValue6_291 OBJECT-TYPE
SYNTAX INTEGER
MAX-ACCESS read-write
STATUS current
DESCRIPTION
"Data value."
::= { dataArray6 291 }

dataValue6_292 OBJECT-TYPE
SYNTAX INTEGER
MAX-ACCESS read-write
STATUS current
DESCRIPTION
"Data value."
::= { dataArray6 292 }

dataValue6_293 OBJECT-TYPE
SYNTAX INTEGER
MAX-ACCESS read-write
STATUS current
DESCRIPTION
"Data value."
::= { dataArray6 293 }

dataValue6_294 OBJECT-TYPE
SYNTAX INTEGER
MAX-ACCESS read-write
STATUS current
DESCRIPTION
"Data value."
::= { dataArray6 294 }

dataValue6_295 OBJECT-TYPE
SYNTAX INTEGER
MAX-ACCESS read-write
STATUS current
DESCRIPTION
"Data value."
::= { dataArray6 295 }

dataValue6_296 OBJECT-TYPE
SYNTAX INTEGER
MAX-ACCESS read-write
STATUS current
DESCRIPTION
"Data value."
::= { dataArray6 296 }

dataValue6_297 OBJECT-TYPE
SYNTAX INTEGER
MAX-ACCESS read-write
STATUS current
DESCRIPTION
"Data value."
::= { dataArray6 297 }

dataValue6_298 OBJECT-TYPE
SYNTAX INTEGER
MAX-ACCESS read-write
STATUS current
DESCRIPTION
"Data value."
::= { dataArray6 298 }

dataValue6_299 OBJECT-TYPE
SYNTAX INTEGER
MAX-ACCESS read-write
STATUS current
DESCRIPTION
"Data value."
::= { dataArray6 299 }

dataValue6_300 OBJECT-TYPE
SYNTAX INTEGER
MAX-ACCESS read-write
STATUS current
DESCRIPTION
"Data value."
::= { dataArray6 300 }

dataValue6_301 OBJECT-TYPE
SYNTAX INTEGER
MAX-ACCESS read-write
STATUS current
DESCRIPTION
"Data value."
::= { dataArray6 301 }

dataValue6_302 OBJECT-TYPE
SYNTAX INTEGER
MAX-ACCESS read-write
STATUS current
DESCRIPTION
"Data value."
::= { dataArray6 302 }

dataValue6_303 OBJECT-TYPE
SYNTAX INTEGER
MAX-ACCESS read-write
STATUS current
DESCRIPTION
"Data value."
::= { dataArray6 303 }

dataValue6_304 OBJECT-TYPE
SYNTAX INTEGER
MAX-ACCESS read-write
STATUS current
DESCRIPTION
"Data value."
::= { dataArray6 304 }

dataValue6_305 OBJECT-TYPE
SYNTAX INTEGER
MAX-ACCESS read-write
STATUS current
DESCRIPTION
"Data value."
::= { dataArray6 305 }

dataValue6_306 OBJECT-TYPE
SYNTAX INTEGER
MAX-ACCESS read-write
STATUS current
DESCRIPTION
"Data value."
::= { dataArray6 306 }

dataValue6_307 OBJECT-TYPE
SYNTAX INTEGER
MAX-ACCESS read-write
STATUS current
DESCRIPTION
"Data value."
::= { dataArray6 307 }

dataValue6_308 OBJECT-TYPE
SYNTAX INTEGER
MAX-ACCESS read-write
STATUS current
DESCRIPTION
"Data value."
::= { dataArray6 308 }

dataValue6_309 OBJECT-TYPE
SYNTAX INTEGER
MAX-ACCESS read-write
STATUS current
DESCRIPTION
"Data value."
::= { dataArray6 309 }

dataValue6_310 OBJECT-TYPE
SYNTAX INTEGER
MAX-ACCESS read-write
STATUS current
DESCRIPTION
"Data value."
::= { dataArray6 310 }

dataValue6_311 OBJECT-TYPE
SYNTAX INTEGER
MAX-ACCESS read-write
STATUS current
DESCRIPTION
"Data value."
::= { dataArray6 311 }

dataValue6_312 OBJECT-TYPE
SYNTAX INTEGER
MAX-ACCESS read-write
STATUS current
DESCRIPTION
"Data value."
::= { dataArray6 312 }

dataValue6_313 OBJECT-TYPE
SYNTAX INTEGER
MAX-ACCESS read-write
STATUS current
DESCRIPTION
"Data value."
::= { dataArray6 313 }

dataValue6_314 OBJECT-TYPE
SYNTAX INTEGER
MAX-ACCESS read-write
STATUS current
DESCRIPTION
"Data value."
::= { dataArray6 314 }

dataValue6_315 OBJECT-TYPE
SYNTAX INTEGER
MAX-ACCESS read-write
STATUS current
DESCRIPTION
"Data value."
::= { dataArray6 315 }

dataValue6_316 OBJECT-TYPE
SYNTAX INTEGER
MAX-ACCESS read-write
STATUS current
DESCRIPTION
"Data value."
::= { dataArray6 316 }

dataValue6_317 OBJECT-TYPE
SYNTAX INTEGER
MAX-ACCESS read-write
STATUS current
DESCRIPTION
"Data value."
::= { dataArray6 317 }

dataValue6_318 OBJECT-TYPE
SYNTAX INTEGER
MAX-ACCESS read-write
STATUS current
DESCRIPTION
"Data value."
::= { dataArray6 318 }

dataValue6_319 OBJECT-TYPE
SYNTAX INTEGER
MAX-ACCESS read-write
STATUS current
DESCRIPTION
"Data value."
::= { dataArray6 319 }

dataValue6_320 OBJECT-TYPE
SYNTAX INTEGER
MAX-ACCESS read-write
STATUS current
DESCRIPTION
"Data value."
::= { dataArray6 320 }

dataValue6_321 OBJECT-TYPE
SYNTAX INTEGER
MAX-ACCESS read-write
STATUS current
DESCRIPTION
"Data value."
::= { dataArray6 321 }

dataValue6_322 OBJECT-TYPE
SYNTAX INTEGER
MAX-ACCESS read-write
STATUS current
DESCRIPTION
"Data value."
::= { dataArray6 322 }

dataValue6_323 OBJECT-TYPE
SYNTAX INTEGER
MAX-ACCESS read-write
STATUS current
DESCRIPTION
"Data value."
::= { dataArray6 323 }

dataValue6_324 OBJECT-TYPE
SYNTAX INTEGER
MAX-ACCESS read-write
STATUS current
DESCRIPTION
"Data value."
::= { dataArray6 324 }

dataValue6_325 OBJECT-TYPE
SYNTAX INTEGER
MAX-ACCESS read-write
STATUS current
DESCRIPTION
"Data value."
::= { dataArray6 325 }

dataValue6_326 OBJECT-TYPE
SYNTAX INTEGER
MAX-ACCESS read-write
STATUS current
DESCRIPTION
"Data value."
::= { dataArray6 326 }

dataValue6_327 OBJECT-TYPE
SYNTAX INTEGER
MAX-ACCESS read-write
STATUS current
DESCRIPTION
"Data value."
::= { dataArray6 327 }

dataValue6_328 OBJECT-TYPE
SYNTAX INTEGER
MAX-ACCESS read-write
STATUS current
DESCRIPTION
"Data value."
::= { dataArray6 328 }

dataValue6_329 OBJECT-TYPE
SYNTAX INTEGER
MAX-ACCESS read-write
STATUS current
DESCRIPTION
"Data value."
::= { dataArray6 329 }

dataValue6_330 OBJECT-TYPE
SYNTAX INTEGER
MAX-ACCESS read-write
STATUS current
DESCRIPTION
"Data value."
::= { dataArray6 330 }

dataValue6_331 OBJECT-TYPE
SYNTAX INTEGER
MAX-ACCESS read-write
STATUS current
DESCRIPTION
"Data value."
::= { dataArray6 331 }

dataValue6_332 OBJECT-TYPE
SYNTAX INTEGER
MAX-ACCESS read-write
STATUS current
DESCRIPTION
"Data value."
::= { dataArray6 332 }

dataValue6_333 OBJECT-TYPE
SYNTAX INTEGER
MAX-ACCESS read-write
STATUS current
DESCRIPTION
"Data value."
::= { dataArray6 333 }

dataValue6_334 OBJECT-TYPE
SYNTAX INTEGER
MAX-ACCESS read-write
STATUS current
DESCRIPTION
"Data value."
::= { dataArray6 334 }

dataValue6_335 OBJECT-TYPE
SYNTAX INTEGER
MAX-ACCESS read-write
STATUS current
DESCRIPTION
"Data value."
::= { dataArray6 335 }

dataValue6_336 OBJECT-TYPE
SYNTAX INTEGER
MAX-ACCESS read-write
STATUS current
DESCRIPTION
"Data value."
::= { dataArray6 336 }

dataValue6_337 OBJECT-TYPE
SYNTAX INTEGER
MAX-ACCESS read-write
STATUS current
DESCRIPTION
"Data value."
::= { dataArray6 337 }

dataValue6_338 OBJECT-TYPE
SYNTAX INTEGER
MAX-ACCESS read-write
STATUS current
DESCRIPTION
"Data value."
::= { dataArray6 338 }

dataValue6_339 OBJECT-TYPE
SYNTAX INTEGER
MAX-ACCESS read-write
STATUS current
DESCRIPTION
"Data value."
::= { dataArray6 339 }

dataValue6_340 OBJECT-TYPE
SYNTAX INTEGER
MAX-ACCESS read-write
STATUS current
DESCRIPTION
"Data value."
::= { dataArray6 340 }

dataValue6_341 OBJECT-TYPE
SYNTAX INTEGER
MAX-ACCESS read-write
STATUS current
DESCRIPTION
"Data value."
::= { dataArray6 341 }

dataValue6_342 OBJECT-TYPE
SYNTAX INTEGER
MAX-ACCESS read-write
STATUS current
DESCRIPTION
"Data value."
::= { dataArray6 342 }

dataValue6_343 OBJECT-TYPE
SYNTAX INTEGER
MAX-ACCESS read-write
STATUS current
DESCRIPTION
"Data value."
::= { dataArray6 343 }

dataValue6_344 OBJECT-TYPE
SYNTAX INTEGER
MAX-ACCESS read-write
STATUS current
DESCRIPTION
"Data value."
::= { dataArray6 344 }

dataValue6_345 OBJECT-TYPE
SYNTAX INTEGER
MAX-ACCESS read-write
STATUS current
DESCRIPTION
"Data value."
::= { dataArray6 345 }

dataValue6_346 OBJECT-TYPE
SYNTAX INTEGER
MAX-ACCESS read-write
STATUS current
DESCRIPTION
"Data value."
::= { dataArray6 346 }

dataValue6_347 OBJECT-TYPE
SYNTAX INTEGER
MAX-ACCESS read-write
STATUS current
DESCRIPTION
"Data value."
::= { dataArray6 347 }

dataValue6_348 OBJECT-TYPE
SYNTAX INTEGER
MAX-ACCESS read-write
STATUS current
DESCRIPTION
"Data value."
::= { dataArray6 348 }

dataValue6_349 OBJECT-TYPE
SYNTAX INTEGER
MAX-ACCESS read-write
STATUS current
DESCRIPTION
"Data value."
::= { dataArray6 349 }

dataValue6_350 OBJECT-TYPE
SYNTAX INTEGER
MAX-ACCESS read-write
STATUS current
DESCRIPTION
"Data value."
::= { dataArray6 350 }

dataValue6_351 OBJECT-TYPE
SYNTAX INTEGER
MAX-ACCESS read-write
STATUS current
DESCRIPTION
"Data value."
::= { dataArray6 351 }

dataValue6_352 OBJECT-TYPE
SYNTAX INTEGER
MAX-ACCESS read-write
STATUS current
DESCRIPTION
"Data value."
::= { dataArray6 352 }

dataValue6_353 OBJECT-TYPE
SYNTAX INTEGER
MAX-ACCESS read-write
STATUS current
DESCRIPTION
"Data value."
::= { dataArray6 353 }

dataValue6_354 OBJECT-TYPE
SYNTAX INTEGER
MAX-ACCESS read-write
STATUS current
DESCRIPTION
"Data value."
::= { dataArray6 354 }

dataValue6_355 OBJECT-TYPE
SYNTAX INTEGER
MAX-ACCESS read-write
STATUS current
DESCRIPTION
"Data value."
::= { dataArray6 355 }

dataValue6_356 OBJECT-TYPE
SYNTAX INTEGER
MAX-ACCESS read-write
STATUS current
DESCRIPTION
"Data value."
::= { dataArray6 356 }

dataValue6_357 OBJECT-TYPE
SYNTAX INTEGER
MAX-ACCESS read-write
STATUS current
DESCRIPTION
"Data value."
::= { dataArray6 357 }

dataValue6_358 OBJECT-TYPE
SYNTAX INTEGER
MAX-ACCESS read-write
STATUS current
DESCRIPTION
"Data value."
::= { dataArray6 358 }

dataValue6_359 OBJECT-TYPE
SYNTAX INTEGER
MAX-ACCESS read-write
STATUS current
DESCRIPTION
"Data value."
::= { dataArray6 359 }

dataValue6_360 OBJECT-TYPE
SYNTAX INTEGER
MAX-ACCESS read-write
STATUS current
DESCRIPTION
"Data value."
::= { dataArray6 360 }

dataValue6_361 OBJECT-TYPE
SYNTAX INTEGER
MAX-ACCESS read-write
STATUS current
DESCRIPTION
"Data value."
::= { dataArray6 361 }

dataValue6_362 OBJECT-TYPE
SYNTAX INTEGER
MAX-ACCESS read-write
STATUS current
DESCRIPTION
"Data value."
::= { dataArray6 362 }

dataValue6_363 OBJECT-TYPE
SYNTAX INTEGER
MAX-ACCESS read-write
STATUS current
DESCRIPTION
"Data value."
::= { dataArray6 363 }

dataValue6_364 OBJECT-TYPE
SYNTAX INTEGER
MAX-ACCESS read-write
STATUS current
DESCRIPTION
"Data value."
::= { dataArray6 364 }

dataValue6_365 OBJECT-TYPE
SYNTAX INTEGER
MAX-ACCESS read-write
STATUS current
DESCRIPTION
"Data value."
::= { dataArray6 365 }

dataValue6_366 OBJECT-TYPE
SYNTAX INTEGER
MAX-ACCESS read-write
STATUS current
DESCRIPTION
"Data value."
::= { dataArray6 366 }

dataValue6_367 OBJECT-TYPE
SYNTAX INTEGER
MAX-ACCESS read-write
STATUS current
DESCRIPTION
"Data value."
::= { dataArray6 367 }

dataValue6_368 OBJECT-TYPE
SYNTAX INTEGER
MAX-ACCESS read-write
STATUS current
DESCRIPTION
"Data value."
::= { dataArray6 368 }

dataValue6_369 OBJECT-TYPE
SYNTAX INTEGER
MAX-ACCESS read-write
STATUS current
DESCRIPTION
"Data value."
::= { dataArray6 369 }

dataValue6_370 OBJECT-TYPE
SYNTAX INTEGER
MAX-ACCESS read-write
STATUS current
DESCRIPTION
"Data value."
::= { dataArray6 370 }

dataValue6_371 OBJECT-TYPE
SYNTAX INTEGER
MAX-ACCESS read-write
STATUS current
DESCRIPTION
"Data value."
::= { dataArray6 371 }

dataValue6_372 OBJECT-TYPE
SYNTAX INTEGER
MAX-ACCESS read-write
STATUS current
DESCRIPTION
"Data value."
::= { dataArray6 372 }

dataValue6_373 OBJECT-TYPE
SYNTAX INTEGER
MAX-ACCESS read-write
STATUS current
DESCRIPTION
"Data value."
::= { dataArray6 373 }

dataValue6_374 OBJECT-TYPE
SYNTAX INTEGER
MAX-ACCESS read-write
STATUS current
DESCRIPTION
"Data value."
::= { dataArray6 374 }

dataValue6_375 OBJECT-TYPE
SYNTAX INTEGER
MAX-ACCESS read-write
STATUS current
DESCRIPTION
"Data value."
::= { dataArray6 375 }

dataValue6_376 OBJECT-TYPE
SYNTAX INTEGER
MAX-ACCESS read-write
STATUS current
DESCRIPTION
"Data value."
::= { dataArray6 376 }

dataValue6_377 OBJECT-TYPE
SYNTAX INTEGER
MAX-ACCESS read-write
STATUS current
DESCRIPTION
"Data value."
::= { dataArray6 377 }

dataValue6_378 OBJECT-TYPE
SYNTAX INTEGER
MAX-ACCESS read-write
STATUS current
DESCRIPTION
"Data value."
::= { dataArray6 378 }

dataValue6_379 OBJECT-TYPE
SYNTAX INTEGER
MAX-ACCESS read-write
STATUS current
DESCRIPTION
"Data value."
::= { dataArray6 379 }

dataValue6_380 OBJECT-TYPE
SYNTAX INTEGER
MAX-ACCESS read-write
STATUS current
DESCRIPTION
"Data value."
::= { dataArray6 380 }

dataValue6_381 OBJECT-TYPE
SYNTAX INTEGER
MAX-ACCESS read-write
STATUS current
DESCRIPTION
"Data value."
::= { dataArray6 381 }

dataValue6_382 OBJECT-TYPE
SYNTAX INTEGER
MAX-ACCESS read-write
STATUS current
DESCRIPTION
"Data value."
::= { dataArray6 382 }

dataValue6_383 OBJECT-TYPE
SYNTAX INTEGER
MAX-ACCESS read-write
STATUS current
DESCRIPTION
"Data value."
::= { dataArray6 383 }

dataValue6_384 OBJECT-TYPE
SYNTAX INTEGER
MAX-ACCESS read-write
STATUS current
DESCRIPTION
"Data value."
::= { dataArray6 384 }

dataValue6_385 OBJECT-TYPE
SYNTAX INTEGER
MAX-ACCESS read-write
STATUS current
DESCRIPTION
"Data value."
::= { dataArray6 385 }

dataValue6_386 OBJECT-TYPE
SYNTAX INTEGER
MAX-ACCESS read-write
STATUS current
DESCRIPTION
"Data value."
::= { dataArray6 386 }

dataValue6_387 OBJECT-TYPE
SYNTAX INTEGER
MAX-ACCESS read-write
STATUS current
DESCRIPTION
"Data value."
::= { dataArray6 387 }

dataValue6_388 OBJECT-TYPE
SYNTAX INTEGER
MAX-ACCESS read-write
STATUS current
DESCRIPTION
"Data value."
::= { dataArray6 388 }

dataValue6_389 OBJECT-TYPE
SYNTAX INTEGER
MAX-ACCESS read-write
STATUS current
DESCRIPTION
"Data value."
::= { dataArray6 389 }

dataValue6_390 OBJECT-TYPE
SYNTAX INTEGER
MAX-ACCESS read-write
STATUS current
DESCRIPTION
"Data value."
::= { dataArray6 390 }

dataValue6_391 OBJECT-TYPE
SYNTAX INTEGER
MAX-ACCESS read-write
STATUS current
DESCRIPTION
"Data value."
::= { dataArray6 391 }

dataValue6_392 OBJECT-TYPE
SYNTAX INTEGER
MAX-ACCESS read-write
STATUS current
DESCRIPTION
"Data value."
::= { dataArray6 392 }

dataValue6_393 OBJECT-TYPE
SYNTAX INTEGER
MAX-ACCESS read-write
STATUS current
DESCRIPTION
"Data value."
::= { dataArray6 393 }

dataValue6_394 OBJECT-TYPE
SYNTAX INTEGER
MAX-ACCESS read-write
STATUS current
DESCRIPTION
"Data value."
::= { dataArray6 394 }

dataValue6_395 OBJECT-TYPE
SYNTAX INTEGER
MAX-ACCESS read-write
STATUS current
DESCRIPTION
"Data value."
::= { dataArray6 395 }

dataValue6_396 OBJECT-TYPE
SYNTAX INTEGER
MAX-ACCESS read-write
STATUS current
DESCRIPTION
"Data value."
::= { dataArray6 396 }

dataValue6_397 OBJECT-TYPE
SYNTAX INTEGER
MAX-ACCESS read-write
STATUS current
DESCRIPTION
"Data value."
::= { dataArray6 397 }

dataValue6_398 OBJECT-TYPE
SYNTAX INTEGER
MAX-ACCESS read-write
STATUS current
DESCRIPTION
"Data value."
::= { dataArray6 398 }

dataValue6_399 OBJECT-TYPE
SYNTAX INTEGER
MAX-ACCESS read-write
STATUS current
DESCRIPTION
"Data value."
::= { dataArray6 399 }

dataArray7 OBJECT IDENTIFIER ::= { cc08255400_v1_00a 7 }

dataValue7_0 OBJECT-TYPE
SYNTAX INTEGER
MAX-ACCESS read-write
STATUS current
DESCRIPTION
"Data value."
::= { dataArray7 0 }

dataValue7_1 OBJECT-TYPE
SYNTAX INTEGER
MAX-ACCESS read-write
STATUS current
DESCRIPTION
"Data value."
::= { dataArray7 1 }

dataValue7_2 OBJECT-TYPE
SYNTAX INTEGER
MAX-ACCESS read-write
STATUS current
DESCRIPTION
"Data value."
::= { dataArray7 2 }

dataValue7_3 OBJECT-TYPE
SYNTAX INTEGER
MAX-ACCESS read-write
STATUS current
DESCRIPTION
"Data value."
::= { dataArray7 3 }

dataValue7_4 OBJECT-TYPE
SYNTAX INTEGER
MAX-ACCESS read-write
STATUS current
DESCRIPTION
"Data value."
::= { dataArray7 4 }

dataValue7_5 OBJECT-TYPE
SYNTAX INTEGER
MAX-ACCESS read-write
STATUS current
DESCRIPTION
"Data value."
::= { dataArray7 5 }

dataValue7_6 OBJECT-TYPE
SYNTAX INTEGER
MAX-ACCESS read-write
STATUS current
DESCRIPTION
"Data value."
::= { dataArray7 6 }

dataValue7_7 OBJECT-TYPE
SYNTAX INTEGER
MAX-ACCESS read-write
STATUS current
DESCRIPTION
"Data value."
::= { dataArray7 7 }

dataValue7_8 OBJECT-TYPE
SYNTAX INTEGER
MAX-ACCESS read-write
STATUS current
DESCRIPTION
"Data value."
::= { dataArray7 8 }

dataValue7_9 OBJECT-TYPE
SYNTAX INTEGER
MAX-ACCESS read-write
STATUS current
DESCRIPTION
"Data value."
::= { dataArray7 9 }

dataValue7_10 OBJECT-TYPE
SYNTAX INTEGER
MAX-ACCESS read-write
STATUS current
DESCRIPTION
"Data value."
::= { dataArray7 10 }

dataValue7_11 OBJECT-TYPE
SYNTAX INTEGER
MAX-ACCESS read-write
STATUS current
DESCRIPTION
"Data value."
::= { dataArray7 11 }

dataValue7_12 OBJECT-TYPE
SYNTAX INTEGER
MAX-ACCESS read-write
STATUS current
DESCRIPTION
"Data value."
::= { dataArray7 12 }

dataValue7_13 OBJECT-TYPE
SYNTAX INTEGER
MAX-ACCESS read-write
STATUS current
DESCRIPTION
"Data value."
::= { dataArray7 13 }

dataValue7_14 OBJECT-TYPE
SYNTAX INTEGER
MAX-ACCESS read-write
STATUS current
DESCRIPTION
"Data value."
::= { dataArray7 14 }

dataValue7_15 OBJECT-TYPE
SYNTAX INTEGER
MAX-ACCESS read-write
STATUS current
DESCRIPTION
"Data value."
::= { dataArray7 15 }

dataValue7_16 OBJECT-TYPE
SYNTAX INTEGER
MAX-ACCESS read-write
STATUS current
DESCRIPTION
"Data value."
::= { dataArray7 16 }

dataValue7_17 OBJECT-TYPE
SYNTAX INTEGER
MAX-ACCESS read-write
STATUS current
DESCRIPTION
"Data value."
::= { dataArray7 17 }

dataValue7_18 OBJECT-TYPE
SYNTAX INTEGER
MAX-ACCESS read-write
STATUS current
DESCRIPTION
"Data value."
::= { dataArray7 18 }

dataValue7_19 OBJECT-TYPE
SYNTAX INTEGER
MAX-ACCESS read-write
STATUS current
DESCRIPTION
"Data value."
::= { dataArray7 19 }

dataValue7_20 OBJECT-TYPE
SYNTAX INTEGER
MAX-ACCESS read-write
STATUS current
DESCRIPTION
"Data value."
::= { dataArray7 20 }

dataValue7_21 OBJECT-TYPE
SYNTAX INTEGER
MAX-ACCESS read-write
STATUS current
DESCRIPTION
"Data value."
::= { dataArray7 21 }

dataValue7_22 OBJECT-TYPE
SYNTAX INTEGER
MAX-ACCESS read-write
STATUS current
DESCRIPTION
"Data value."
::= { dataArray7 22 }

dataValue7_23 OBJECT-TYPE
SYNTAX INTEGER
MAX-ACCESS read-write
STATUS current
DESCRIPTION
"Data value."
::= { dataArray7 23 }

dataValue7_24 OBJECT-TYPE
SYNTAX INTEGER
MAX-ACCESS read-write
STATUS current
DESCRIPTION
"Data value."
::= { dataArray7 24 }

dataValue7_25 OBJECT-TYPE
SYNTAX INTEGER
MAX-ACCESS read-write
STATUS current
DESCRIPTION
"Data value."
::= { dataArray7 25 }

dataValue7_26 OBJECT-TYPE
SYNTAX INTEGER
MAX-ACCESS read-write
STATUS current
DESCRIPTION
"Data value."
::= { dataArray7 26 }

dataValue7_27 OBJECT-TYPE
SYNTAX INTEGER
MAX-ACCESS read-write
STATUS current
DESCRIPTION
"Data value."
::= { dataArray7 27 }

dataValue7_28 OBJECT-TYPE
SYNTAX INTEGER
MAX-ACCESS read-write
STATUS current
DESCRIPTION
"Data value."
::= { dataArray7 28 }

dataValue7_29 OBJECT-TYPE
SYNTAX INTEGER
MAX-ACCESS read-write
STATUS current
DESCRIPTION
"Data value."
::= { dataArray7 29 }

dataValue7_30 OBJECT-TYPE
SYNTAX INTEGER
MAX-ACCESS read-write
STATUS current
DESCRIPTION
"Data value."
::= { dataArray7 30 }

dataValue7_31 OBJECT-TYPE
SYNTAX INTEGER
MAX-ACCESS read-write
STATUS current
DESCRIPTION
"Data value."
::= { dataArray7 31 }

dataValue7_32 OBJECT-TYPE
SYNTAX INTEGER
MAX-ACCESS read-write
STATUS current
DESCRIPTION
"Data value."
::= { dataArray7 32 }

dataValue7_33 OBJECT-TYPE
SYNTAX INTEGER
MAX-ACCESS read-write
STATUS current
DESCRIPTION
"Data value."
::= { dataArray7 33 }

dataValue7_34 OBJECT-TYPE
SYNTAX INTEGER
MAX-ACCESS read-write
STATUS current
DESCRIPTION
"Data value."
::= { dataArray7 34 }

dataValue7_35 OBJECT-TYPE
SYNTAX INTEGER
MAX-ACCESS read-write
STATUS current
DESCRIPTION
"Data value."
::= { dataArray7 35 }

dataValue7_36 OBJECT-TYPE
SYNTAX INTEGER
MAX-ACCESS read-write
STATUS current
DESCRIPTION
"Data value."
::= { dataArray7 36 }

dataValue7_37 OBJECT-TYPE
SYNTAX INTEGER
MAX-ACCESS read-write
STATUS current
DESCRIPTION
"Data value."
::= { dataArray7 37 }

dataValue7_38 OBJECT-TYPE
SYNTAX INTEGER
MAX-ACCESS read-write
STATUS current
DESCRIPTION
"Data value."
::= { dataArray7 38 }

dataValue7_39 OBJECT-TYPE
SYNTAX INTEGER
MAX-ACCESS read-write
STATUS current
DESCRIPTION
"Data value."
::= { dataArray7 39 }

dataValue7_40 OBJECT-TYPE
SYNTAX INTEGER
MAX-ACCESS read-write
STATUS current
DESCRIPTION
"Data value."
::= { dataArray7 40 }

dataValue7_41 OBJECT-TYPE
SYNTAX INTEGER
MAX-ACCESS read-write
STATUS current
DESCRIPTION
"Data value."
::= { dataArray7 41 }

dataValue7_42 OBJECT-TYPE
SYNTAX INTEGER
MAX-ACCESS read-write
STATUS current
DESCRIPTION
"Data value."
::= { dataArray7 42 }

dataValue7_43 OBJECT-TYPE
SYNTAX INTEGER
MAX-ACCESS read-write
STATUS current
DESCRIPTION
"Data value."
::= { dataArray7 43 }

dataValue7_44 OBJECT-TYPE
SYNTAX INTEGER
MAX-ACCESS read-write
STATUS current
DESCRIPTION
"Data value."
::= { dataArray7 44 }

dataValue7_45 OBJECT-TYPE
SYNTAX INTEGER
MAX-ACCESS read-write
STATUS current
DESCRIPTION
"Data value."
::= { dataArray7 45 }

dataValue7_46 OBJECT-TYPE
SYNTAX INTEGER
MAX-ACCESS read-write
STATUS current
DESCRIPTION
"Data value."
::= { dataArray7 46 }

dataValue7_47 OBJECT-TYPE
SYNTAX INTEGER
MAX-ACCESS read-write
STATUS current
DESCRIPTION
"Data value."
::= { dataArray7 47 }

dataValue7_48 OBJECT-TYPE
SYNTAX INTEGER
MAX-ACCESS read-write
STATUS current
DESCRIPTION
"Data value."
::= { dataArray7 48 }

dataValue7_49 OBJECT-TYPE
SYNTAX INTEGER
MAX-ACCESS read-write
STATUS current
DESCRIPTION
"Data value."
::= { dataArray7 49 }

dataValue7_50 OBJECT-TYPE
SYNTAX INTEGER
MAX-ACCESS read-write
STATUS current
DESCRIPTION
"Data value."
::= { dataArray7 50 }

dataValue7_51 OBJECT-TYPE
SYNTAX INTEGER
MAX-ACCESS read-write
STATUS current
DESCRIPTION
"Data value."
::= { dataArray7 51 }

dataValue7_52 OBJECT-TYPE
SYNTAX INTEGER
MAX-ACCESS read-write
STATUS current
DESCRIPTION
"Data value."
::= { dataArray7 52 }

dataValue7_53 OBJECT-TYPE
SYNTAX INTEGER
MAX-ACCESS read-write
STATUS current
DESCRIPTION
"Data value."
::= { dataArray7 53 }

dataValue7_54 OBJECT-TYPE
SYNTAX INTEGER
MAX-ACCESS read-write
STATUS current
DESCRIPTION
"Data value."
::= { dataArray7 54 }

dataValue7_55 OBJECT-TYPE
SYNTAX INTEGER
MAX-ACCESS read-write
STATUS current
DESCRIPTION
"Data value."
::= { dataArray7 55 }

dataValue7_56 OBJECT-TYPE
SYNTAX INTEGER
MAX-ACCESS read-write
STATUS current
DESCRIPTION
"Data value."
::= { dataArray7 56 }

dataValue7_57 OBJECT-TYPE
SYNTAX INTEGER
MAX-ACCESS read-write
STATUS current
DESCRIPTION
"Data value."
::= { dataArray7 57 }

dataValue7_58 OBJECT-TYPE
SYNTAX INTEGER
MAX-ACCESS read-write
STATUS current
DESCRIPTION
"Data value."
::= { dataArray7 58 }

dataValue7_59 OBJECT-TYPE
SYNTAX INTEGER
MAX-ACCESS read-write
STATUS current
DESCRIPTION
"Data value."
::= { dataArray7 59 }

dataValue7_60 OBJECT-TYPE
SYNTAX INTEGER
MAX-ACCESS read-write
STATUS current
DESCRIPTION
"Data value."
::= { dataArray7 60 }

dataValue7_61 OBJECT-TYPE
SYNTAX INTEGER
MAX-ACCESS read-write
STATUS current
DESCRIPTION
"Data value."
::= { dataArray7 61 }

dataValue7_62 OBJECT-TYPE
SYNTAX INTEGER
MAX-ACCESS read-write
STATUS current
DESCRIPTION
"Data value."
::= { dataArray7 62 }

dataValue7_63 OBJECT-TYPE
SYNTAX INTEGER
MAX-ACCESS read-write
STATUS current
DESCRIPTION
"Data value."
::= { dataArray7 63 }

dataValue7_64 OBJECT-TYPE
SYNTAX INTEGER
MAX-ACCESS read-write
STATUS current
DESCRIPTION
"Data value."
::= { dataArray7 64 }

dataValue7_65 OBJECT-TYPE
SYNTAX INTEGER
MAX-ACCESS read-write
STATUS current
DESCRIPTION
"Data value."
::= { dataArray7 65 }

dataValue7_66 OBJECT-TYPE
SYNTAX INTEGER
MAX-ACCESS read-write
STATUS current
DESCRIPTION
"Data value."
::= { dataArray7 66 }

dataValue7_67 OBJECT-TYPE
SYNTAX INTEGER
MAX-ACCESS read-write
STATUS current
DESCRIPTION
"Data value."
::= { dataArray7 67 }

dataValue7_68 OBJECT-TYPE
SYNTAX INTEGER
MAX-ACCESS read-write
STATUS current
DESCRIPTION
"Data value."
::= { dataArray7 68 }

dataValue7_69 OBJECT-TYPE
SYNTAX INTEGER
MAX-ACCESS read-write
STATUS current
DESCRIPTION
"Data value."
::= { dataArray7 69 }

dataValue7_70 OBJECT-TYPE
SYNTAX INTEGER
MAX-ACCESS read-write
STATUS current
DESCRIPTION
"Data value."
::= { dataArray7 70 }

dataValue7_71 OBJECT-TYPE
SYNTAX INTEGER
MAX-ACCESS read-write
STATUS current
DESCRIPTION
"Data value."
::= { dataArray7 71 }

dataValue7_72 OBJECT-TYPE
SYNTAX INTEGER
MAX-ACCESS read-write
STATUS current
DESCRIPTION
"Data value."
::= { dataArray7 72 }

dataValue7_73 OBJECT-TYPE
SYNTAX INTEGER
MAX-ACCESS read-write
STATUS current
DESCRIPTION
"Data value."
::= { dataArray7 73 }

dataValue7_74 OBJECT-TYPE
SYNTAX INTEGER
MAX-ACCESS read-write
STATUS current
DESCRIPTION
"Data value."
::= { dataArray7 74 }

dataValue7_75 OBJECT-TYPE
SYNTAX INTEGER
MAX-ACCESS read-write
STATUS current
DESCRIPTION
"Data value."
::= { dataArray7 75 }

dataValue7_76 OBJECT-TYPE
SYNTAX INTEGER
MAX-ACCESS read-write
STATUS current
DESCRIPTION
"Data value."
::= { dataArray7 76 }

dataValue7_77 OBJECT-TYPE
SYNTAX INTEGER
MAX-ACCESS read-write
STATUS current
DESCRIPTION
"Data value."
::= { dataArray7 77 }

dataValue7_78 OBJECT-TYPE
SYNTAX INTEGER
MAX-ACCESS read-write
STATUS current
DESCRIPTION
"Data value."
::= { dataArray7 78 }

dataValue7_79 OBJECT-TYPE
SYNTAX INTEGER
MAX-ACCESS read-write
STATUS current
DESCRIPTION
"Data value."
::= { dataArray7 79 }

dataValue7_80 OBJECT-TYPE
SYNTAX INTEGER
MAX-ACCESS read-write
STATUS current
DESCRIPTION
"Data value."
::= { dataArray7 80 }

dataValue7_81 OBJECT-TYPE
SYNTAX INTEGER
MAX-ACCESS read-write
STATUS current
DESCRIPTION
"Data value."
::= { dataArray7 81 }

dataValue7_82 OBJECT-TYPE
SYNTAX INTEGER
MAX-ACCESS read-write
STATUS current
DESCRIPTION
"Data value."
::= { dataArray7 82 }

dataValue7_83 OBJECT-TYPE
SYNTAX INTEGER
MAX-ACCESS read-write
STATUS current
DESCRIPTION
"Data value."
::= { dataArray7 83 }

dataValue7_84 OBJECT-TYPE
SYNTAX INTEGER
MAX-ACCESS read-write
STATUS current
DESCRIPTION
"Data value."
::= { dataArray7 84 }

dataValue7_85 OBJECT-TYPE
SYNTAX INTEGER
MAX-ACCESS read-write
STATUS current
DESCRIPTION
"Data value."
::= { dataArray7 85 }

dataValue7_86 OBJECT-TYPE
SYNTAX INTEGER
MAX-ACCESS read-write
STATUS current
DESCRIPTION
"Data value."
::= { dataArray7 86 }

dataValue7_87 OBJECT-TYPE
SYNTAX INTEGER
MAX-ACCESS read-write
STATUS current
DESCRIPTION
"Data value."
::= { dataArray7 87 }

dataValue7_88 OBJECT-TYPE
SYNTAX INTEGER
MAX-ACCESS read-write
STATUS current
DESCRIPTION
"Data value."
::= { dataArray7 88 }

dataValue7_89 OBJECT-TYPE
SYNTAX INTEGER
MAX-ACCESS read-write
STATUS current
DESCRIPTION
"Data value."
::= { dataArray7 89 }

dataValue7_90 OBJECT-TYPE
SYNTAX INTEGER
MAX-ACCESS read-write
STATUS current
DESCRIPTION
"Data value."
::= { dataArray7 90 }

dataValue7_91 OBJECT-TYPE
SYNTAX INTEGER
MAX-ACCESS read-write
STATUS current
DESCRIPTION
"Data value."
::= { dataArray7 91 }

dataValue7_92 OBJECT-TYPE
SYNTAX INTEGER
MAX-ACCESS read-write
STATUS current
DESCRIPTION
"Data value."
::= { dataArray7 92 }

dataValue7_93 OBJECT-TYPE
SYNTAX INTEGER
MAX-ACCESS read-write
STATUS current
DESCRIPTION
"Data value."
::= { dataArray7 93 }

dataValue7_94 OBJECT-TYPE
SYNTAX INTEGER
MAX-ACCESS read-write
STATUS current
DESCRIPTION
"Data value."
::= { dataArray7 94 }

dataValue7_95 OBJECT-TYPE
SYNTAX INTEGER
MAX-ACCESS read-write
STATUS current
DESCRIPTION
"Data value."
::= { dataArray7 95 }

dataValue7_96 OBJECT-TYPE
SYNTAX INTEGER
MAX-ACCESS read-write
STATUS current
DESCRIPTION
"Data value."
::= { dataArray7 96 }

dataValue7_97 OBJECT-TYPE
SYNTAX INTEGER
MAX-ACCESS read-write
STATUS current
DESCRIPTION
"Data value."
::= { dataArray7 97 }

dataValue7_98 OBJECT-TYPE
SYNTAX INTEGER
MAX-ACCESS read-write
STATUS current
DESCRIPTION
"Data value."
::= { dataArray7 98 }

dataValue7_99 OBJECT-TYPE
SYNTAX INTEGER
MAX-ACCESS read-write
STATUS current
DESCRIPTION
"Data value."
::= { dataArray7 99 }

dataValue7_100 OBJECT-TYPE
SYNTAX INTEGER
MAX-ACCESS read-write
STATUS current
DESCRIPTION
"Data value."
::= { dataArray7 100 }

dataValue7_101 OBJECT-TYPE
SYNTAX INTEGER
MAX-ACCESS read-write
STATUS current
DESCRIPTION
"Data value."
::= { dataArray7 101 }

dataValue7_102 OBJECT-TYPE
SYNTAX INTEGER
MAX-ACCESS read-write
STATUS current
DESCRIPTION
"Data value."
::= { dataArray7 102 }

dataValue7_103 OBJECT-TYPE
SYNTAX INTEGER
MAX-ACCESS read-write
STATUS current
DESCRIPTION
"Data value."
::= { dataArray7 103 }

dataValue7_104 OBJECT-TYPE
SYNTAX INTEGER
MAX-ACCESS read-write
STATUS current
DESCRIPTION
"Data value."
::= { dataArray7 104 }

dataValue7_105 OBJECT-TYPE
SYNTAX INTEGER
MAX-ACCESS read-write
STATUS current
DESCRIPTION
"Data value."
::= { dataArray7 105 }

dataValue7_106 OBJECT-TYPE
SYNTAX INTEGER
MAX-ACCESS read-write
STATUS current
DESCRIPTION
"Data value."
::= { dataArray7 106 }

dataValue7_107 OBJECT-TYPE
SYNTAX INTEGER
MAX-ACCESS read-write
STATUS current
DESCRIPTION
"Data value."
::= { dataArray7 107 }

dataValue7_108 OBJECT-TYPE
SYNTAX INTEGER
MAX-ACCESS read-write
STATUS current
DESCRIPTION
"Data value."
::= { dataArray7 108 }

dataValue7_109 OBJECT-TYPE
SYNTAX INTEGER
MAX-ACCESS read-write
STATUS current
DESCRIPTION
"Data value."
::= { dataArray7 109 }

dataValue7_110 OBJECT-TYPE
SYNTAX INTEGER
MAX-ACCESS read-write
STATUS current
DESCRIPTION
"Data value."
::= { dataArray7 110 }

dataValue7_111 OBJECT-TYPE
SYNTAX INTEGER
MAX-ACCESS read-write
STATUS current
DESCRIPTION
"Data value."
::= { dataArray7 111 }

dataValue7_112 OBJECT-TYPE
SYNTAX INTEGER
MAX-ACCESS read-write
STATUS current
DESCRIPTION
"Data value."
::= { dataArray7 112 }

dataValue7_113 OBJECT-TYPE
SYNTAX INTEGER
MAX-ACCESS read-write
STATUS current
DESCRIPTION
"Data value."
::= { dataArray7 113 }

dataValue7_114 OBJECT-TYPE
SYNTAX INTEGER
MAX-ACCESS read-write
STATUS current
DESCRIPTION
"Data value."
::= { dataArray7 114 }

dataValue7_115 OBJECT-TYPE
SYNTAX INTEGER
MAX-ACCESS read-write
STATUS current
DESCRIPTION
"Data value."
::= { dataArray7 115 }

dataValue7_116 OBJECT-TYPE
SYNTAX INTEGER
MAX-ACCESS read-write
STATUS current
DESCRIPTION
"Data value."
::= { dataArray7 116 }

dataValue7_117 OBJECT-TYPE
SYNTAX INTEGER
MAX-ACCESS read-write
STATUS current
DESCRIPTION
"Data value."
::= { dataArray7 117 }

dataValue7_118 OBJECT-TYPE
SYNTAX INTEGER
MAX-ACCESS read-write
STATUS current
DESCRIPTION
"Data value."
::= { dataArray7 118 }

dataValue7_119 OBJECT-TYPE
SYNTAX INTEGER
MAX-ACCESS read-write
STATUS current
DESCRIPTION
"Data value."
::= { dataArray7 119 }

dataValue7_120 OBJECT-TYPE
SYNTAX INTEGER
MAX-ACCESS read-write
STATUS current
DESCRIPTION
"Data value."
::= { dataArray7 120 }

dataValue7_121 OBJECT-TYPE
SYNTAX INTEGER
MAX-ACCESS read-write
STATUS current
DESCRIPTION
"Data value."
::= { dataArray7 121 }

dataValue7_122 OBJECT-TYPE
SYNTAX INTEGER
MAX-ACCESS read-write
STATUS current
DESCRIPTION
"Data value."
::= { dataArray7 122 }

dataValue7_123 OBJECT-TYPE
SYNTAX INTEGER
MAX-ACCESS read-write
STATUS current
DESCRIPTION
"Data value."
::= { dataArray7 123 }

dataValue7_124 OBJECT-TYPE
SYNTAX INTEGER
MAX-ACCESS read-write
STATUS current
DESCRIPTION
"Data value."
::= { dataArray7 124 }

dataValue7_125 OBJECT-TYPE
SYNTAX INTEGER
MAX-ACCESS read-write
STATUS current
DESCRIPTION
"Data value."
::= { dataArray7 125 }

dataValue7_126 OBJECT-TYPE
SYNTAX INTEGER
MAX-ACCESS read-write
STATUS current
DESCRIPTION
"Data value."
::= { dataArray7 126 }

dataValue7_127 OBJECT-TYPE
SYNTAX INTEGER
MAX-ACCESS read-write
STATUS current
DESCRIPTION
"Data value."
::= { dataArray7 127 }

dataValue7_128 OBJECT-TYPE
SYNTAX INTEGER
MAX-ACCESS read-write
STATUS current
DESCRIPTION
"Data value."
::= { dataArray7 128 }

dataValue7_129 OBJECT-TYPE
SYNTAX INTEGER
MAX-ACCESS read-write
STATUS current
DESCRIPTION
"Data value."
::= { dataArray7 129 }

dataValue7_130 OBJECT-TYPE
SYNTAX INTEGER
MAX-ACCESS read-write
STATUS current
DESCRIPTION
"Data value."
::= { dataArray7 130 }

dataValue7_131 OBJECT-TYPE
SYNTAX INTEGER
MAX-ACCESS read-write
STATUS current
DESCRIPTION
"Data value."
::= { dataArray7 131 }

dataValue7_132 OBJECT-TYPE
SYNTAX INTEGER
MAX-ACCESS read-write
STATUS current
DESCRIPTION
"Data value."
::= { dataArray7 132 }

dataValue7_133 OBJECT-TYPE
SYNTAX INTEGER
MAX-ACCESS read-write
STATUS current
DESCRIPTION
"Data value."
::= { dataArray7 133 }

dataValue7_134 OBJECT-TYPE
SYNTAX INTEGER
MAX-ACCESS read-write
STATUS current
DESCRIPTION
"Data value."
::= { dataArray7 134 }

dataValue7_135 OBJECT-TYPE
SYNTAX INTEGER
MAX-ACCESS read-write
STATUS current
DESCRIPTION
"Data value."
::= { dataArray7 135 }

dataValue7_136 OBJECT-TYPE
SYNTAX INTEGER
MAX-ACCESS read-write
STATUS current
DESCRIPTION
"Data value."
::= { dataArray7 136 }

dataValue7_137 OBJECT-TYPE
SYNTAX INTEGER
MAX-ACCESS read-write
STATUS current
DESCRIPTION
"Data value."
::= { dataArray7 137 }

dataValue7_138 OBJECT-TYPE
SYNTAX INTEGER
MAX-ACCESS read-write
STATUS current
DESCRIPTION
"Data value."
::= { dataArray7 138 }

dataValue7_139 OBJECT-TYPE
SYNTAX INTEGER
MAX-ACCESS read-write
STATUS current
DESCRIPTION
"Data value."
::= { dataArray7 139 }

dataValue7_140 OBJECT-TYPE
SYNTAX INTEGER
MAX-ACCESS read-write
STATUS current
DESCRIPTION
"Data value."
::= { dataArray7 140 }

dataValue7_141 OBJECT-TYPE
SYNTAX INTEGER
MAX-ACCESS read-write
STATUS current
DESCRIPTION
"Data value."
::= { dataArray7 141 }

dataValue7_142 OBJECT-TYPE
SYNTAX INTEGER
MAX-ACCESS read-write
STATUS current
DESCRIPTION
"Data value."
::= { dataArray7 142 }

dataValue7_143 OBJECT-TYPE
SYNTAX INTEGER
MAX-ACCESS read-write
STATUS current
DESCRIPTION
"Data value."
::= { dataArray7 143 }

dataValue7_144 OBJECT-TYPE
SYNTAX INTEGER
MAX-ACCESS read-write
STATUS current
DESCRIPTION
"Data value."
::= { dataArray7 144 }

dataValue7_145 OBJECT-TYPE
SYNTAX INTEGER
MAX-ACCESS read-write
STATUS current
DESCRIPTION
"Data value."
::= { dataArray7 145 }

dataValue7_146 OBJECT-TYPE
SYNTAX INTEGER
MAX-ACCESS read-write
STATUS current
DESCRIPTION
"Data value."
::= { dataArray7 146 }

dataValue7_147 OBJECT-TYPE
SYNTAX INTEGER
MAX-ACCESS read-write
STATUS current
DESCRIPTION
"Data value."
::= { dataArray7 147 }

dataValue7_148 OBJECT-TYPE
SYNTAX INTEGER
MAX-ACCESS read-write
STATUS current
DESCRIPTION
"Data value."
::= { dataArray7 148 }

dataValue7_149 OBJECT-TYPE
SYNTAX INTEGER
MAX-ACCESS read-write
STATUS current
DESCRIPTION
"Data value."
::= { dataArray7 149 }

dataValue7_150 OBJECT-TYPE
SYNTAX INTEGER
MAX-ACCESS read-write
STATUS current
DESCRIPTION
"Data value."
::= { dataArray7 150 }

dataValue7_151 OBJECT-TYPE
SYNTAX INTEGER
MAX-ACCESS read-write
STATUS current
DESCRIPTION
"Data value."
::= { dataArray7 151 }

dataValue7_152 OBJECT-TYPE
SYNTAX INTEGER
MAX-ACCESS read-write
STATUS current
DESCRIPTION
"Data value."
::= { dataArray7 152 }

dataValue7_153 OBJECT-TYPE
SYNTAX INTEGER
MAX-ACCESS read-write
STATUS current
DESCRIPTION
"Data value."
::= { dataArray7 153 }

dataValue7_154 OBJECT-TYPE
SYNTAX INTEGER
MAX-ACCESS read-write
STATUS current
DESCRIPTION
"Data value."
::= { dataArray7 154 }

dataValue7_155 OBJECT-TYPE
SYNTAX INTEGER
MAX-ACCESS read-write
STATUS current
DESCRIPTION
"Data value."
::= { dataArray7 155 }

dataValue7_156 OBJECT-TYPE
SYNTAX INTEGER
MAX-ACCESS read-write
STATUS current
DESCRIPTION
"Data value."
::= { dataArray7 156 }

dataValue7_157 OBJECT-TYPE
SYNTAX INTEGER
MAX-ACCESS read-write
STATUS current
DESCRIPTION
"Data value."
::= { dataArray7 157 }

dataValue7_158 OBJECT-TYPE
SYNTAX INTEGER
MAX-ACCESS read-write
STATUS current
DESCRIPTION
"Data value."
::= { dataArray7 158 }

dataValue7_159 OBJECT-TYPE
SYNTAX INTEGER
MAX-ACCESS read-write
STATUS current
DESCRIPTION
"Data value."
::= { dataArray7 159 }

dataValue7_160 OBJECT-TYPE
SYNTAX INTEGER
MAX-ACCESS read-write
STATUS current
DESCRIPTION
"Data value."
::= { dataArray7 160 }

dataValue7_161 OBJECT-TYPE
SYNTAX INTEGER
MAX-ACCESS read-write
STATUS current
DESCRIPTION
"Data value."
::= { dataArray7 161 }

dataValue7_162 OBJECT-TYPE
SYNTAX INTEGER
MAX-ACCESS read-write
STATUS current
DESCRIPTION
"Data value."
::= { dataArray7 162 }

dataValue7_163 OBJECT-TYPE
SYNTAX INTEGER
MAX-ACCESS read-write
STATUS current
DESCRIPTION
"Data value."
::= { dataArray7 163 }

dataValue7_164 OBJECT-TYPE
SYNTAX INTEGER
MAX-ACCESS read-write
STATUS current
DESCRIPTION
"Data value."
::= { dataArray7 164 }

dataValue7_165 OBJECT-TYPE
SYNTAX INTEGER
MAX-ACCESS read-write
STATUS current
DESCRIPTION
"Data value."
::= { dataArray7 165 }

dataValue7_166 OBJECT-TYPE
SYNTAX INTEGER
MAX-ACCESS read-write
STATUS current
DESCRIPTION
"Data value."
::= { dataArray7 166 }

dataValue7_167 OBJECT-TYPE
SYNTAX INTEGER
MAX-ACCESS read-write
STATUS current
DESCRIPTION
"Data value."
::= { dataArray7 167 }

dataValue7_168 OBJECT-TYPE
SYNTAX INTEGER
MAX-ACCESS read-write
STATUS current
DESCRIPTION
"Data value."
::= { dataArray7 168 }

dataValue7_169 OBJECT-TYPE
SYNTAX INTEGER
MAX-ACCESS read-write
STATUS current
DESCRIPTION
"Data value."
::= { dataArray7 169 }

dataValue7_170 OBJECT-TYPE
SYNTAX INTEGER
MAX-ACCESS read-write
STATUS current
DESCRIPTION
"Data value."
::= { dataArray7 170 }

dataValue7_171 OBJECT-TYPE
SYNTAX INTEGER
MAX-ACCESS read-write
STATUS current
DESCRIPTION
"Data value."
::= { dataArray7 171 }

dataValue7_172 OBJECT-TYPE
SYNTAX INTEGER
MAX-ACCESS read-write
STATUS current
DESCRIPTION
"Data value."
::= { dataArray7 172 }

dataValue7_173 OBJECT-TYPE
SYNTAX INTEGER
MAX-ACCESS read-write
STATUS current
DESCRIPTION
"Data value."
::= { dataArray7 173 }

dataValue7_174 OBJECT-TYPE
SYNTAX INTEGER
MAX-ACCESS read-write
STATUS current
DESCRIPTION
"Data value."
::= { dataArray7 174 }

dataValue7_175 OBJECT-TYPE
SYNTAX INTEGER
MAX-ACCESS read-write
STATUS current
DESCRIPTION
"Data value."
::= { dataArray7 175 }

dataValue7_176 OBJECT-TYPE
SYNTAX INTEGER
MAX-ACCESS read-write
STATUS current
DESCRIPTION
"Data value."
::= { dataArray7 176 }

dataValue7_177 OBJECT-TYPE
SYNTAX INTEGER
MAX-ACCESS read-write
STATUS current
DESCRIPTION
"Data value."
::= { dataArray7 177 }

dataValue7_178 OBJECT-TYPE
SYNTAX INTEGER
MAX-ACCESS read-write
STATUS current
DESCRIPTION
"Data value."
::= { dataArray7 178 }

dataValue7_179 OBJECT-TYPE
SYNTAX INTEGER
MAX-ACCESS read-write
STATUS current
DESCRIPTION
"Data value."
::= { dataArray7 179 }

dataValue7_180 OBJECT-TYPE
SYNTAX INTEGER
MAX-ACCESS read-write
STATUS current
DESCRIPTION
"Data value."
::= { dataArray7 180 }

dataValue7_181 OBJECT-TYPE
SYNTAX INTEGER
MAX-ACCESS read-write
STATUS current
DESCRIPTION
"Data value."
::= { dataArray7 181 }

dataValue7_182 OBJECT-TYPE
SYNTAX INTEGER
MAX-ACCESS read-write
STATUS current
DESCRIPTION
"Data value."
::= { dataArray7 182 }

dataValue7_183 OBJECT-TYPE
SYNTAX INTEGER
MAX-ACCESS read-write
STATUS current
DESCRIPTION
"Data value."
::= { dataArray7 183 }

dataValue7_184 OBJECT-TYPE
SYNTAX INTEGER
MAX-ACCESS read-write
STATUS current
DESCRIPTION
"Data value."
::= { dataArray7 184 }

dataValue7_185 OBJECT-TYPE
SYNTAX INTEGER
MAX-ACCESS read-write
STATUS current
DESCRIPTION
"Data value."
::= { dataArray7 185 }

dataValue7_186 OBJECT-TYPE
SYNTAX INTEGER
MAX-ACCESS read-write
STATUS current
DESCRIPTION
"Data value."
::= { dataArray7 186 }

dataValue7_187 OBJECT-TYPE
SYNTAX INTEGER
MAX-ACCESS read-write
STATUS current
DESCRIPTION
"Data value."
::= { dataArray7 187 }

dataValue7_188 OBJECT-TYPE
SYNTAX INTEGER
MAX-ACCESS read-write
STATUS current
DESCRIPTION
"Data value."
::= { dataArray7 188 }

dataValue7_189 OBJECT-TYPE
SYNTAX INTEGER
MAX-ACCESS read-write
STATUS current
DESCRIPTION
"Data value."
::= { dataArray7 189 }

dataValue7_190 OBJECT-TYPE
SYNTAX INTEGER
MAX-ACCESS read-write
STATUS current
DESCRIPTION
"Data value."
::= { dataArray7 190 }

dataValue7_191 OBJECT-TYPE
SYNTAX INTEGER
MAX-ACCESS read-write
STATUS current
DESCRIPTION
"Data value."
::= { dataArray7 191 }

dataValue7_192 OBJECT-TYPE
SYNTAX INTEGER
MAX-ACCESS read-write
STATUS current
DESCRIPTION
"Data value."
::= { dataArray7 192 }

dataValue7_193 OBJECT-TYPE
SYNTAX INTEGER
MAX-ACCESS read-write
STATUS current
DESCRIPTION
"Data value."
::= { dataArray7 193 }

dataValue7_194 OBJECT-TYPE
SYNTAX INTEGER
MAX-ACCESS read-write
STATUS current
DESCRIPTION
"Data value."
::= { dataArray7 194 }

dataValue7_195 OBJECT-TYPE
SYNTAX INTEGER
MAX-ACCESS read-write
STATUS current
DESCRIPTION
"Data value."
::= { dataArray7 195 }

dataValue7_196 OBJECT-TYPE
SYNTAX INTEGER
MAX-ACCESS read-write
STATUS current
DESCRIPTION
"Data value."
::= { dataArray7 196 }

dataValue7_197 OBJECT-TYPE
SYNTAX INTEGER
MAX-ACCESS read-write
STATUS current
DESCRIPTION
"Data value."
::= { dataArray7 197 }

dataValue7_198 OBJECT-TYPE
SYNTAX INTEGER
MAX-ACCESS read-write
STATUS current
DESCRIPTION
"Data value."
::= { dataArray7 198 }

dataValue7_199 OBJECT-TYPE
SYNTAX INTEGER
MAX-ACCESS read-write
STATUS current
DESCRIPTION
"Data value."
::= { dataArray7 199 }

dataValue7_200 OBJECT-TYPE
SYNTAX INTEGER
MAX-ACCESS read-write
STATUS current
DESCRIPTION
"Data value."
::= { dataArray7 200 }

dataValue7_201 OBJECT-TYPE
SYNTAX INTEGER
MAX-ACCESS read-write
STATUS current
DESCRIPTION
"Data value."
::= { dataArray7 201 }

dataValue7_202 OBJECT-TYPE
SYNTAX INTEGER
MAX-ACCESS read-write
STATUS current
DESCRIPTION
"Data value."
::= { dataArray7 202 }

dataValue7_203 OBJECT-TYPE
SYNTAX INTEGER
MAX-ACCESS read-write
STATUS current
DESCRIPTION
"Data value."
::= { dataArray7 203 }

dataValue7_204 OBJECT-TYPE
SYNTAX INTEGER
MAX-ACCESS read-write
STATUS current
DESCRIPTION
"Data value."
::= { dataArray7 204 }

dataValue7_205 OBJECT-TYPE
SYNTAX INTEGER
MAX-ACCESS read-write
STATUS current
DESCRIPTION
"Data value."
::= { dataArray7 205 }

dataValue7_206 OBJECT-TYPE
SYNTAX INTEGER
MAX-ACCESS read-write
STATUS current
DESCRIPTION
"Data value."
::= { dataArray7 206 }

dataValue7_207 OBJECT-TYPE
SYNTAX INTEGER
MAX-ACCESS read-write
STATUS current
DESCRIPTION
"Data value."
::= { dataArray7 207 }

dataValue7_208 OBJECT-TYPE
SYNTAX INTEGER
MAX-ACCESS read-write
STATUS current
DESCRIPTION
"Data value."
::= { dataArray7 208 }

dataValue7_209 OBJECT-TYPE
SYNTAX INTEGER
MAX-ACCESS read-write
STATUS current
DESCRIPTION
"Data value."
::= { dataArray7 209 }

dataValue7_210 OBJECT-TYPE
SYNTAX INTEGER
MAX-ACCESS read-write
STATUS current
DESCRIPTION
"Data value."
::= { dataArray7 210 }

dataValue7_211 OBJECT-TYPE
SYNTAX INTEGER
MAX-ACCESS read-write
STATUS current
DESCRIPTION
"Data value."
::= { dataArray7 211 }

dataValue7_212 OBJECT-TYPE
SYNTAX INTEGER
MAX-ACCESS read-write
STATUS current
DESCRIPTION
"Data value."
::= { dataArray7 212 }

dataValue7_213 OBJECT-TYPE
SYNTAX INTEGER
MAX-ACCESS read-write
STATUS current
DESCRIPTION
"Data value."
::= { dataArray7 213 }

dataValue7_214 OBJECT-TYPE
SYNTAX INTEGER
MAX-ACCESS read-write
STATUS current
DESCRIPTION
"Data value."
::= { dataArray7 214 }

dataValue7_215 OBJECT-TYPE
SYNTAX INTEGER
MAX-ACCESS read-write
STATUS current
DESCRIPTION
"Data value."
::= { dataArray7 215 }

dataValue7_216 OBJECT-TYPE
SYNTAX INTEGER
MAX-ACCESS read-write
STATUS current
DESCRIPTION
"Data value."
::= { dataArray7 216 }

dataValue7_217 OBJECT-TYPE
SYNTAX INTEGER
MAX-ACCESS read-write
STATUS current
DESCRIPTION
"Data value."
::= { dataArray7 217 }

dataValue7_218 OBJECT-TYPE
SYNTAX INTEGER
MAX-ACCESS read-write
STATUS current
DESCRIPTION
"Data value."
::= { dataArray7 218 }

dataValue7_219 OBJECT-TYPE
SYNTAX INTEGER
MAX-ACCESS read-write
STATUS current
DESCRIPTION
"Data value."
::= { dataArray7 219 }

dataValue7_220 OBJECT-TYPE
SYNTAX INTEGER
MAX-ACCESS read-write
STATUS current
DESCRIPTION
"Data value."
::= { dataArray7 220 }

dataValue7_221 OBJECT-TYPE
SYNTAX INTEGER
MAX-ACCESS read-write
STATUS current
DESCRIPTION
"Data value."
::= { dataArray7 221 }

dataValue7_222 OBJECT-TYPE
SYNTAX INTEGER
MAX-ACCESS read-write
STATUS current
DESCRIPTION
"Data value."
::= { dataArray7 222 }

dataValue7_223 OBJECT-TYPE
SYNTAX INTEGER
MAX-ACCESS read-write
STATUS current
DESCRIPTION
"Data value."
::= { dataArray7 223 }

dataValue7_224 OBJECT-TYPE
SYNTAX INTEGER
MAX-ACCESS read-write
STATUS current
DESCRIPTION
"Data value."
::= { dataArray7 224 }

dataValue7_225 OBJECT-TYPE
SYNTAX INTEGER
MAX-ACCESS read-write
STATUS current
DESCRIPTION
"Data value."
::= { dataArray7 225 }

dataValue7_226 OBJECT-TYPE
SYNTAX INTEGER
MAX-ACCESS read-write
STATUS current
DESCRIPTION
"Data value."
::= { dataArray7 226 }

dataValue7_227 OBJECT-TYPE
SYNTAX INTEGER
MAX-ACCESS read-write
STATUS current
DESCRIPTION
"Data value."
::= { dataArray7 227 }

dataValue7_228 OBJECT-TYPE
SYNTAX INTEGER
MAX-ACCESS read-write
STATUS current
DESCRIPTION
"Data value."
::= { dataArray7 228 }

dataValue7_229 OBJECT-TYPE
SYNTAX INTEGER
MAX-ACCESS read-write
STATUS current
DESCRIPTION
"Data value."
::= { dataArray7 229 }

dataValue7_230 OBJECT-TYPE
SYNTAX INTEGER
MAX-ACCESS read-write
STATUS current
DESCRIPTION
"Data value."
::= { dataArray7 230 }

dataValue7_231 OBJECT-TYPE
SYNTAX INTEGER
MAX-ACCESS read-write
STATUS current
DESCRIPTION
"Data value."
::= { dataArray7 231 }

dataValue7_232 OBJECT-TYPE
SYNTAX INTEGER
MAX-ACCESS read-write
STATUS current
DESCRIPTION
"Data value."
::= { dataArray7 232 }

dataValue7_233 OBJECT-TYPE
SYNTAX INTEGER
MAX-ACCESS read-write
STATUS current
DESCRIPTION
"Data value."
::= { dataArray7 233 }

dataValue7_234 OBJECT-TYPE
SYNTAX INTEGER
MAX-ACCESS read-write
STATUS current
DESCRIPTION
"Data value."
::= { dataArray7 234 }

dataValue7_235 OBJECT-TYPE
SYNTAX INTEGER
MAX-ACCESS read-write
STATUS current
DESCRIPTION
"Data value."
::= { dataArray7 235 }

dataValue7_236 OBJECT-TYPE
SYNTAX INTEGER
MAX-ACCESS read-write
STATUS current
DESCRIPTION
"Data value."
::= { dataArray7 236 }

dataValue7_237 OBJECT-TYPE
SYNTAX INTEGER
MAX-ACCESS read-write
STATUS current
DESCRIPTION
"Data value."
::= { dataArray7 237 }

dataValue7_238 OBJECT-TYPE
SYNTAX INTEGER
MAX-ACCESS read-write
STATUS current
DESCRIPTION
"Data value."
::= { dataArray7 238 }

dataValue7_239 OBJECT-TYPE
SYNTAX INTEGER
MAX-ACCESS read-write
STATUS current
DESCRIPTION
"Data value."
::= { dataArray7 239 }

dataValue7_240 OBJECT-TYPE
SYNTAX INTEGER
MAX-ACCESS read-write
STATUS current
DESCRIPTION
"Data value."
::= { dataArray7 240 }

dataValue7_241 OBJECT-TYPE
SYNTAX INTEGER
MAX-ACCESS read-write
STATUS current
DESCRIPTION
"Data value."
::= { dataArray7 241 }

dataValue7_242 OBJECT-TYPE
SYNTAX INTEGER
MAX-ACCESS read-write
STATUS current
DESCRIPTION
"Data value."
::= { dataArray7 242 }

dataValue7_243 OBJECT-TYPE
SYNTAX INTEGER
MAX-ACCESS read-write
STATUS current
DESCRIPTION
"Data value."
::= { dataArray7 243 }

dataValue7_244 OBJECT-TYPE
SYNTAX INTEGER
MAX-ACCESS read-write
STATUS current
DESCRIPTION
"Data value."
::= { dataArray7 244 }

dataValue7_245 OBJECT-TYPE
SYNTAX INTEGER
MAX-ACCESS read-write
STATUS current
DESCRIPTION
"Data value."
::= { dataArray7 245 }

dataValue7_246 OBJECT-TYPE
SYNTAX INTEGER
MAX-ACCESS read-write
STATUS current
DESCRIPTION
"Data value."
::= { dataArray7 246 }

dataValue7_247 OBJECT-TYPE
SYNTAX INTEGER
MAX-ACCESS read-write
STATUS current
DESCRIPTION
"Data value."
::= { dataArray7 247 }

dataValue7_248 OBJECT-TYPE
SYNTAX INTEGER
MAX-ACCESS read-write
STATUS current
DESCRIPTION
"Data value."
::= { dataArray7 248 }

dataValue7_249 OBJECT-TYPE
SYNTAX INTEGER
MAX-ACCESS read-write
STATUS current
DESCRIPTION
"Data value."
::= { dataArray7 249 }

dataValue7_250 OBJECT-TYPE
SYNTAX INTEGER
MAX-ACCESS read-write
STATUS current
DESCRIPTION
"Data value."
::= { dataArray7 250 }

dataValue7_251 OBJECT-TYPE
SYNTAX INTEGER
MAX-ACCESS read-write
STATUS current
DESCRIPTION
"Data value."
::= { dataArray7 251 }

dataValue7_252 OBJECT-TYPE
SYNTAX INTEGER
MAX-ACCESS read-write
STATUS current
DESCRIPTION
"Data value."
::= { dataArray7 252 }

dataValue7_253 OBJECT-TYPE
SYNTAX INTEGER
MAX-ACCESS read-write
STATUS current
DESCRIPTION
"Data value."
::= { dataArray7 253 }

dataValue7_254 OBJECT-TYPE
SYNTAX INTEGER
MAX-ACCESS read-write
STATUS current
DESCRIPTION
"Data value."
::= { dataArray7 254 }

dataValue7_255 OBJECT-TYPE
SYNTAX INTEGER
MAX-ACCESS read-write
STATUS current
DESCRIPTION
"Data value."
::= { dataArray7 255 }

dataValue7_256 OBJECT-TYPE
SYNTAX INTEGER
MAX-ACCESS read-write
STATUS current
DESCRIPTION
"Data value."
::= { dataArray7 256 }

dataValue7_257 OBJECT-TYPE
SYNTAX INTEGER
MAX-ACCESS read-write
STATUS current
DESCRIPTION
"Data value."
::= { dataArray7 257 }

dataValue7_258 OBJECT-TYPE
SYNTAX INTEGER
MAX-ACCESS read-write
STATUS current
DESCRIPTION
"Data value."
::= { dataArray7 258 }

dataValue7_259 OBJECT-TYPE
SYNTAX INTEGER
MAX-ACCESS read-write
STATUS current
DESCRIPTION
"Data value."
::= { dataArray7 259 }

dataValue7_260 OBJECT-TYPE
SYNTAX INTEGER
MAX-ACCESS read-write
STATUS current
DESCRIPTION
"Data value."
::= { dataArray7 260 }

dataValue7_261 OBJECT-TYPE
SYNTAX INTEGER
MAX-ACCESS read-write
STATUS current
DESCRIPTION
"Data value."
::= { dataArray7 261 }

dataValue7_262 OBJECT-TYPE
SYNTAX INTEGER
MAX-ACCESS read-write
STATUS current
DESCRIPTION
"Data value."
::= { dataArray7 262 }

dataValue7_263 OBJECT-TYPE
SYNTAX INTEGER
MAX-ACCESS read-write
STATUS current
DESCRIPTION
"Data value."
::= { dataArray7 263 }

dataValue7_264 OBJECT-TYPE
SYNTAX INTEGER
MAX-ACCESS read-write
STATUS current
DESCRIPTION
"Data value."
::= { dataArray7 264 }

dataValue7_265 OBJECT-TYPE
SYNTAX INTEGER
MAX-ACCESS read-write
STATUS current
DESCRIPTION
"Data value."
::= { dataArray7 265 }

dataValue7_266 OBJECT-TYPE
SYNTAX INTEGER
MAX-ACCESS read-write
STATUS current
DESCRIPTION
"Data value."
::= { dataArray7 266 }

dataValue7_267 OBJECT-TYPE
SYNTAX INTEGER
MAX-ACCESS read-write
STATUS current
DESCRIPTION
"Data value."
::= { dataArray7 267 }

dataValue7_268 OBJECT-TYPE
SYNTAX INTEGER
MAX-ACCESS read-write
STATUS current
DESCRIPTION
"Data value."
::= { dataArray7 268 }

dataValue7_269 OBJECT-TYPE
SYNTAX INTEGER
MAX-ACCESS read-write
STATUS current
DESCRIPTION
"Data value."
::= { dataArray7 269 }

dataValue7_270 OBJECT-TYPE
SYNTAX INTEGER
MAX-ACCESS read-write
STATUS current
DESCRIPTION
"Data value."
::= { dataArray7 270 }

dataValue7_271 OBJECT-TYPE
SYNTAX INTEGER
MAX-ACCESS read-write
STATUS current
DESCRIPTION
"Data value."
::= { dataArray7 271 }

dataValue7_272 OBJECT-TYPE
SYNTAX INTEGER
MAX-ACCESS read-write
STATUS current
DESCRIPTION
"Data value."
::= { dataArray7 272 }

dataValue7_273 OBJECT-TYPE
SYNTAX INTEGER
MAX-ACCESS read-write
STATUS current
DESCRIPTION
"Data value."
::= { dataArray7 273 }

dataValue7_274 OBJECT-TYPE
SYNTAX INTEGER
MAX-ACCESS read-write
STATUS current
DESCRIPTION
"Data value."
::= { dataArray7 274 }

dataValue7_275 OBJECT-TYPE
SYNTAX INTEGER
MAX-ACCESS read-write
STATUS current
DESCRIPTION
"Data value."
::= { dataArray7 275 }

dataValue7_276 OBJECT-TYPE
SYNTAX INTEGER
MAX-ACCESS read-write
STATUS current
DESCRIPTION
"Data value."
::= { dataArray7 276 }

dataValue7_277 OBJECT-TYPE
SYNTAX INTEGER
MAX-ACCESS read-write
STATUS current
DESCRIPTION
"Data value."
::= { dataArray7 277 }

dataValue7_278 OBJECT-TYPE
SYNTAX INTEGER
MAX-ACCESS read-write
STATUS current
DESCRIPTION
"Data value."
::= { dataArray7 278 }

dataValue7_279 OBJECT-TYPE
SYNTAX INTEGER
MAX-ACCESS read-write
STATUS current
DESCRIPTION
"Data value."
::= { dataArray7 279 }

dataValue7_280 OBJECT-TYPE
SYNTAX INTEGER
MAX-ACCESS read-write
STATUS current
DESCRIPTION
"Data value."
::= { dataArray7 280 }

dataValue7_281 OBJECT-TYPE
SYNTAX INTEGER
MAX-ACCESS read-write
STATUS current
DESCRIPTION
"Data value."
::= { dataArray7 281 }

dataValue7_282 OBJECT-TYPE
SYNTAX INTEGER
MAX-ACCESS read-write
STATUS current
DESCRIPTION
"Data value."
::= { dataArray7 282 }

dataValue7_283 OBJECT-TYPE
SYNTAX INTEGER
MAX-ACCESS read-write
STATUS current
DESCRIPTION
"Data value."
::= { dataArray7 283 }

dataValue7_284 OBJECT-TYPE
SYNTAX INTEGER
MAX-ACCESS read-write
STATUS current
DESCRIPTION
"Data value."
::= { dataArray7 284 }

dataValue7_285 OBJECT-TYPE
SYNTAX INTEGER
MAX-ACCESS read-write
STATUS current
DESCRIPTION
"Data value."
::= { dataArray7 285 }

dataValue7_286 OBJECT-TYPE
SYNTAX INTEGER
MAX-ACCESS read-write
STATUS current
DESCRIPTION
"Data value."
::= { dataArray7 286 }

dataValue7_287 OBJECT-TYPE
SYNTAX INTEGER
MAX-ACCESS read-write
STATUS current
DESCRIPTION
"Data value."
::= { dataArray7 287 }

dataValue7_288 OBJECT-TYPE
SYNTAX INTEGER
MAX-ACCESS read-write
STATUS current
DESCRIPTION
"Data value."
::= { dataArray7 288 }

dataValue7_289 OBJECT-TYPE
SYNTAX INTEGER
MAX-ACCESS read-write
STATUS current
DESCRIPTION
"Data value."
::= { dataArray7 289 }

dataValue7_290 OBJECT-TYPE
SYNTAX INTEGER
MAX-ACCESS read-write
STATUS current
DESCRIPTION
"Data value."
::= { dataArray7 290 }

dataValue7_291 OBJECT-TYPE
SYNTAX INTEGER
MAX-ACCESS read-write
STATUS current
DESCRIPTION
"Data value."
::= { dataArray7 291 }

dataValue7_292 OBJECT-TYPE
SYNTAX INTEGER
MAX-ACCESS read-write
STATUS current
DESCRIPTION
"Data value."
::= { dataArray7 292 }

dataValue7_293 OBJECT-TYPE
SYNTAX INTEGER
MAX-ACCESS read-write
STATUS current
DESCRIPTION
"Data value."
::= { dataArray7 293 }

dataValue7_294 OBJECT-TYPE
SYNTAX INTEGER
MAX-ACCESS read-write
STATUS current
DESCRIPTION
"Data value."
::= { dataArray7 294 }

dataValue7_295 OBJECT-TYPE
SYNTAX INTEGER
MAX-ACCESS read-write
STATUS current
DESCRIPTION
"Data value."
::= { dataArray7 295 }

dataValue7_296 OBJECT-TYPE
SYNTAX INTEGER
MAX-ACCESS read-write
STATUS current
DESCRIPTION
"Data value."
::= { dataArray7 296 }

dataValue7_297 OBJECT-TYPE
SYNTAX INTEGER
MAX-ACCESS read-write
STATUS current
DESCRIPTION
"Data value."
::= { dataArray7 297 }

dataValue7_298 OBJECT-TYPE
SYNTAX INTEGER
MAX-ACCESS read-write
STATUS current
DESCRIPTION
"Data value."
::= { dataArray7 298 }

dataValue7_299 OBJECT-TYPE
SYNTAX INTEGER
MAX-ACCESS read-write
STATUS current
DESCRIPTION
"Data value."
::= { dataArray7 299 }

dataValue7_300 OBJECT-TYPE
SYNTAX INTEGER
MAX-ACCESS read-write
STATUS current
DESCRIPTION
"Data value."
::= { dataArray7 300 }

dataValue7_301 OBJECT-TYPE
SYNTAX INTEGER
MAX-ACCESS read-write
STATUS current
DESCRIPTION
"Data value."
::= { dataArray7 301 }

dataValue7_302 OBJECT-TYPE
SYNTAX INTEGER
MAX-ACCESS read-write
STATUS current
DESCRIPTION
"Data value."
::= { dataArray7 302 }

dataValue7_303 OBJECT-TYPE
SYNTAX INTEGER
MAX-ACCESS read-write
STATUS current
DESCRIPTION
"Data value."
::= { dataArray7 303 }

dataValue7_304 OBJECT-TYPE
SYNTAX INTEGER
MAX-ACCESS read-write
STATUS current
DESCRIPTION
"Data value."
::= { dataArray7 304 }

dataValue7_305 OBJECT-TYPE
SYNTAX INTEGER
MAX-ACCESS read-write
STATUS current
DESCRIPTION
"Data value."
::= { dataArray7 305 }

dataValue7_306 OBJECT-TYPE
SYNTAX INTEGER
MAX-ACCESS read-write
STATUS current
DESCRIPTION
"Data value."
::= { dataArray7 306 }

dataValue7_307 OBJECT-TYPE
SYNTAX INTEGER
MAX-ACCESS read-write
STATUS current
DESCRIPTION
"Data value."
::= { dataArray7 307 }

dataValue7_308 OBJECT-TYPE
SYNTAX INTEGER
MAX-ACCESS read-write
STATUS current
DESCRIPTION
"Data value."
::= { dataArray7 308 }

dataValue7_309 OBJECT-TYPE
SYNTAX INTEGER
MAX-ACCESS read-write
STATUS current
DESCRIPTION
"Data value."
::= { dataArray7 309 }

dataValue7_310 OBJECT-TYPE
SYNTAX INTEGER
MAX-ACCESS read-write
STATUS current
DESCRIPTION
"Data value."
::= { dataArray7 310 }

dataValue7_311 OBJECT-TYPE
SYNTAX INTEGER
MAX-ACCESS read-write
STATUS current
DESCRIPTION
"Data value."
::= { dataArray7 311 }

dataValue7_312 OBJECT-TYPE
SYNTAX INTEGER
MAX-ACCESS read-write
STATUS current
DESCRIPTION
"Data value."
::= { dataArray7 312 }

dataValue7_313 OBJECT-TYPE
SYNTAX INTEGER
MAX-ACCESS read-write
STATUS current
DESCRIPTION
"Data value."
::= { dataArray7 313 }

dataValue7_314 OBJECT-TYPE
SYNTAX INTEGER
MAX-ACCESS read-write
STATUS current
DESCRIPTION
"Data value."
::= { dataArray7 314 }

dataValue7_315 OBJECT-TYPE
SYNTAX INTEGER
MAX-ACCESS read-write
STATUS current
DESCRIPTION
"Data value."
::= { dataArray7 315 }

dataValue7_316 OBJECT-TYPE
SYNTAX INTEGER
MAX-ACCESS read-write
STATUS current
DESCRIPTION
"Data value."
::= { dataArray7 316 }

dataValue7_317 OBJECT-TYPE
SYNTAX INTEGER
MAX-ACCESS read-write
STATUS current
DESCRIPTION
"Data value."
::= { dataArray7 317 }

dataValue7_318 OBJECT-TYPE
SYNTAX INTEGER
MAX-ACCESS read-write
STATUS current
DESCRIPTION
"Data value."
::= { dataArray7 318 }

dataValue7_319 OBJECT-TYPE
SYNTAX INTEGER
MAX-ACCESS read-write
STATUS current
DESCRIPTION
"Data value."
::= { dataArray7 319 }

dataValue7_320 OBJECT-TYPE
SYNTAX INTEGER
MAX-ACCESS read-write
STATUS current
DESCRIPTION
"Data value."
::= { dataArray7 320 }

dataValue7_321 OBJECT-TYPE
SYNTAX INTEGER
MAX-ACCESS read-write
STATUS current
DESCRIPTION
"Data value."
::= { dataArray7 321 }

dataValue7_322 OBJECT-TYPE
SYNTAX INTEGER
MAX-ACCESS read-write
STATUS current
DESCRIPTION
"Data value."
::= { dataArray7 322 }

dataValue7_323 OBJECT-TYPE
SYNTAX INTEGER
MAX-ACCESS read-write
STATUS current
DESCRIPTION
"Data value."
::= { dataArray7 323 }

dataValue7_324 OBJECT-TYPE
SYNTAX INTEGER
MAX-ACCESS read-write
STATUS current
DESCRIPTION
"Data value."
::= { dataArray7 324 }

dataValue7_325 OBJECT-TYPE
SYNTAX INTEGER
MAX-ACCESS read-write
STATUS current
DESCRIPTION
"Data value."
::= { dataArray7 325 }

dataValue7_326 OBJECT-TYPE
SYNTAX INTEGER
MAX-ACCESS read-write
STATUS current
DESCRIPTION
"Data value."
::= { dataArray7 326 }

dataValue7_327 OBJECT-TYPE
SYNTAX INTEGER
MAX-ACCESS read-write
STATUS current
DESCRIPTION
"Data value."
::= { dataArray7 327 }

dataValue7_328 OBJECT-TYPE
SYNTAX INTEGER
MAX-ACCESS read-write
STATUS current
DESCRIPTION
"Data value."
::= { dataArray7 328 }

dataValue7_329 OBJECT-TYPE
SYNTAX INTEGER
MAX-ACCESS read-write
STATUS current
DESCRIPTION
"Data value."
::= { dataArray7 329 }

dataValue7_330 OBJECT-TYPE
SYNTAX INTEGER
MAX-ACCESS read-write
STATUS current
DESCRIPTION
"Data value."
::= { dataArray7 330 }

dataValue7_331 OBJECT-TYPE
SYNTAX INTEGER
MAX-ACCESS read-write
STATUS current
DESCRIPTION
"Data value."
::= { dataArray7 331 }

dataValue7_332 OBJECT-TYPE
SYNTAX INTEGER
MAX-ACCESS read-write
STATUS current
DESCRIPTION
"Data value."
::= { dataArray7 332 }

dataValue7_333 OBJECT-TYPE
SYNTAX INTEGER
MAX-ACCESS read-write
STATUS current
DESCRIPTION
"Data value."
::= { dataArray7 333 }

dataValue7_334 OBJECT-TYPE
SYNTAX INTEGER
MAX-ACCESS read-write
STATUS current
DESCRIPTION
"Data value."
::= { dataArray7 334 }

dataValue7_335 OBJECT-TYPE
SYNTAX INTEGER
MAX-ACCESS read-write
STATUS current
DESCRIPTION
"Data value."
::= { dataArray7 335 }

dataValue7_336 OBJECT-TYPE
SYNTAX INTEGER
MAX-ACCESS read-write
STATUS current
DESCRIPTION
"Data value."
::= { dataArray7 336 }

dataValue7_337 OBJECT-TYPE
SYNTAX INTEGER
MAX-ACCESS read-write
STATUS current
DESCRIPTION
"Data value."
::= { dataArray7 337 }

dataValue7_338 OBJECT-TYPE
SYNTAX INTEGER
MAX-ACCESS read-write
STATUS current
DESCRIPTION
"Data value."
::= { dataArray7 338 }

dataValue7_339 OBJECT-TYPE
SYNTAX INTEGER
MAX-ACCESS read-write
STATUS current
DESCRIPTION
"Data value."
::= { dataArray7 339 }

dataValue7_340 OBJECT-TYPE
SYNTAX INTEGER
MAX-ACCESS read-write
STATUS current
DESCRIPTION
"Data value."
::= { dataArray7 340 }

dataValue7_341 OBJECT-TYPE
SYNTAX INTEGER
MAX-ACCESS read-write
STATUS current
DESCRIPTION
"Data value."
::= { dataArray7 341 }

dataValue7_342 OBJECT-TYPE
SYNTAX INTEGER
MAX-ACCESS read-write
STATUS current
DESCRIPTION
"Data value."
::= { dataArray7 342 }

dataValue7_343 OBJECT-TYPE
SYNTAX INTEGER
MAX-ACCESS read-write
STATUS current
DESCRIPTION
"Data value."
::= { dataArray7 343 }

dataValue7_344 OBJECT-TYPE
SYNTAX INTEGER
MAX-ACCESS read-write
STATUS current
DESCRIPTION
"Data value."
::= { dataArray7 344 }

dataValue7_345 OBJECT-TYPE
SYNTAX INTEGER
MAX-ACCESS read-write
STATUS current
DESCRIPTION
"Data value."
::= { dataArray7 345 }

dataValue7_346 OBJECT-TYPE
SYNTAX INTEGER
MAX-ACCESS read-write
STATUS current
DESCRIPTION
"Data value."
::= { dataArray7 346 }

dataValue7_347 OBJECT-TYPE
SYNTAX INTEGER
MAX-ACCESS read-write
STATUS current
DESCRIPTION
"Data value."
::= { dataArray7 347 }

dataValue7_348 OBJECT-TYPE
SYNTAX INTEGER
MAX-ACCESS read-write
STATUS current
DESCRIPTION
"Data value."
::= { dataArray7 348 }

dataValue7_349 OBJECT-TYPE
SYNTAX INTEGER
MAX-ACCESS read-write
STATUS current
DESCRIPTION
"Data value."
::= { dataArray7 349 }

dataValue7_350 OBJECT-TYPE
SYNTAX INTEGER
MAX-ACCESS read-write
STATUS current
DESCRIPTION
"Data value."
::= { dataArray7 350 }

dataValue7_351 OBJECT-TYPE
SYNTAX INTEGER
MAX-ACCESS read-write
STATUS current
DESCRIPTION
"Data value."
::= { dataArray7 351 }

dataValue7_352 OBJECT-TYPE
SYNTAX INTEGER
MAX-ACCESS read-write
STATUS current
DESCRIPTION
"Data value."
::= { dataArray7 352 }

dataValue7_353 OBJECT-TYPE
SYNTAX INTEGER
MAX-ACCESS read-write
STATUS current
DESCRIPTION
"Data value."
::= { dataArray7 353 }

dataValue7_354 OBJECT-TYPE
SYNTAX INTEGER
MAX-ACCESS read-write
STATUS current
DESCRIPTION
"Data value."
::= { dataArray7 354 }

dataValue7_355 OBJECT-TYPE
SYNTAX INTEGER
MAX-ACCESS read-write
STATUS current
DESCRIPTION
"Data value."
::= { dataArray7 355 }

dataValue7_356 OBJECT-TYPE
SYNTAX INTEGER
MAX-ACCESS read-write
STATUS current
DESCRIPTION
"Data value."
::= { dataArray7 356 }

dataValue7_357 OBJECT-TYPE
SYNTAX INTEGER
MAX-ACCESS read-write
STATUS current
DESCRIPTION
"Data value."
::= { dataArray7 357 }

dataValue7_358 OBJECT-TYPE
SYNTAX INTEGER
MAX-ACCESS read-write
STATUS current
DESCRIPTION
"Data value."
::= { dataArray7 358 }

dataValue7_359 OBJECT-TYPE
SYNTAX INTEGER
MAX-ACCESS read-write
STATUS current
DESCRIPTION
"Data value."
::= { dataArray7 359 }

dataValue7_360 OBJECT-TYPE
SYNTAX INTEGER
MAX-ACCESS read-write
STATUS current
DESCRIPTION
"Data value."
::= { dataArray7 360 }

dataValue7_361 OBJECT-TYPE
SYNTAX INTEGER
MAX-ACCESS read-write
STATUS current
DESCRIPTION
"Data value."
::= { dataArray7 361 }

dataValue7_362 OBJECT-TYPE
SYNTAX INTEGER
MAX-ACCESS read-write
STATUS current
DESCRIPTION
"Data value."
::= { dataArray7 362 }

dataValue7_363 OBJECT-TYPE
SYNTAX INTEGER
MAX-ACCESS read-write
STATUS current
DESCRIPTION
"Data value."
::= { dataArray7 363 }

dataValue7_364 OBJECT-TYPE
SYNTAX INTEGER
MAX-ACCESS read-write
STATUS current
DESCRIPTION
"Data value."
::= { dataArray7 364 }

dataValue7_365 OBJECT-TYPE
SYNTAX INTEGER
MAX-ACCESS read-write
STATUS current
DESCRIPTION
"Data value."
::= { dataArray7 365 }

dataValue7_366 OBJECT-TYPE
SYNTAX INTEGER
MAX-ACCESS read-write
STATUS current
DESCRIPTION
"Data value."
::= { dataArray7 366 }

dataValue7_367 OBJECT-TYPE
SYNTAX INTEGER
MAX-ACCESS read-write
STATUS current
DESCRIPTION
"Data value."
::= { dataArray7 367 }

dataValue7_368 OBJECT-TYPE
SYNTAX INTEGER
MAX-ACCESS read-write
STATUS current
DESCRIPTION
"Data value."
::= { dataArray7 368 }

dataValue7_369 OBJECT-TYPE
SYNTAX INTEGER
MAX-ACCESS read-write
STATUS current
DESCRIPTION
"Data value."
::= { dataArray7 369 }

dataValue7_370 OBJECT-TYPE
SYNTAX INTEGER
MAX-ACCESS read-write
STATUS current
DESCRIPTION
"Data value."
::= { dataArray7 370 }

dataValue7_371 OBJECT-TYPE
SYNTAX INTEGER
MAX-ACCESS read-write
STATUS current
DESCRIPTION
"Data value."
::= { dataArray7 371 }

dataValue7_372 OBJECT-TYPE
SYNTAX INTEGER
MAX-ACCESS read-write
STATUS current
DESCRIPTION
"Data value."
::= { dataArray7 372 }

dataValue7_373 OBJECT-TYPE
SYNTAX INTEGER
MAX-ACCESS read-write
STATUS current
DESCRIPTION
"Data value."
::= { dataArray7 373 }

dataValue7_374 OBJECT-TYPE
SYNTAX INTEGER
MAX-ACCESS read-write
STATUS current
DESCRIPTION
"Data value."
::= { dataArray7 374 }

dataValue7_375 OBJECT-TYPE
SYNTAX INTEGER
MAX-ACCESS read-write
STATUS current
DESCRIPTION
"Data value."
::= { dataArray7 375 }

dataValue7_376 OBJECT-TYPE
SYNTAX INTEGER
MAX-ACCESS read-write
STATUS current
DESCRIPTION
"Data value."
::= { dataArray7 376 }

dataValue7_377 OBJECT-TYPE
SYNTAX INTEGER
MAX-ACCESS read-write
STATUS current
DESCRIPTION
"Data value."
::= { dataArray7 377 }

dataValue7_378 OBJECT-TYPE
SYNTAX INTEGER
MAX-ACCESS read-write
STATUS current
DESCRIPTION
"Data value."
::= { dataArray7 378 }

dataValue7_379 OBJECT-TYPE
SYNTAX INTEGER
MAX-ACCESS read-write
STATUS current
DESCRIPTION
"Data value."
::= { dataArray7 379 }

dataValue7_380 OBJECT-TYPE
SYNTAX INTEGER
MAX-ACCESS read-write
STATUS current
DESCRIPTION
"Data value."
::= { dataArray7 380 }

dataValue7_381 OBJECT-TYPE
SYNTAX INTEGER
MAX-ACCESS read-write
STATUS current
DESCRIPTION
"Data value."
::= { dataArray7 381 }

dataValue7_382 OBJECT-TYPE
SYNTAX INTEGER
MAX-ACCESS read-write
STATUS current
DESCRIPTION
"Data value."
::= { dataArray7 382 }

dataValue7_383 OBJECT-TYPE
SYNTAX INTEGER
MAX-ACCESS read-write
STATUS current
DESCRIPTION
"Data value."
::= { dataArray7 383 }

dataValue7_384 OBJECT-TYPE
SYNTAX INTEGER
MAX-ACCESS read-write
STATUS current
DESCRIPTION
"Data value."
::= { dataArray7 384 }

dataValue7_385 OBJECT-TYPE
SYNTAX INTEGER
MAX-ACCESS read-write
STATUS current
DESCRIPTION
"Data value."
::= { dataArray7 385 }

dataValue7_386 OBJECT-TYPE
SYNTAX INTEGER
MAX-ACCESS read-write
STATUS current
DESCRIPTION
"Data value."
::= { dataArray7 386 }

dataValue7_387 OBJECT-TYPE
SYNTAX INTEGER
MAX-ACCESS read-write
STATUS current
DESCRIPTION
"Data value."
::= { dataArray7 387 }

dataValue7_388 OBJECT-TYPE
SYNTAX INTEGER
MAX-ACCESS read-write
STATUS current
DESCRIPTION
"Data value."
::= { dataArray7 388 }

dataValue7_389 OBJECT-TYPE
SYNTAX INTEGER
MAX-ACCESS read-write
STATUS current
DESCRIPTION
"Data value."
::= { dataArray7 389 }

dataValue7_390 OBJECT-TYPE
SYNTAX INTEGER
MAX-ACCESS read-write
STATUS current
DESCRIPTION
"Data value."
::= { dataArray7 390 }

dataValue7_391 OBJECT-TYPE
SYNTAX INTEGER
MAX-ACCESS read-write
STATUS current
DESCRIPTION
"Data value."
::= { dataArray7 391 }

dataValue7_392 OBJECT-TYPE
SYNTAX INTEGER
MAX-ACCESS read-write
STATUS current
DESCRIPTION
"Data value."
::= { dataArray7 392 }

dataValue7_393 OBJECT-TYPE
SYNTAX INTEGER
MAX-ACCESS read-write
STATUS current
DESCRIPTION
"Data value."
::= { dataArray7 393 }

dataValue7_394 OBJECT-TYPE
SYNTAX INTEGER
MAX-ACCESS read-write
STATUS current
DESCRIPTION
"Data value."
::= { dataArray7 394 }

dataValue7_395 OBJECT-TYPE
SYNTAX INTEGER
MAX-ACCESS read-write
STATUS current
DESCRIPTION
"Data value."
::= { dataArray7 395 }

dataValue7_396 OBJECT-TYPE
SYNTAX INTEGER
MAX-ACCESS read-write
STATUS current
DESCRIPTION
"Data value."
::= { dataArray7 396 }

dataValue7_397 OBJECT-TYPE
SYNTAX INTEGER
MAX-ACCESS read-write
STATUS current
DESCRIPTION
"Data value."
::= { dataArray7 397 }

dataValue7_398 OBJECT-TYPE
SYNTAX INTEGER
MAX-ACCESS read-write
STATUS current
DESCRIPTION
"Data value."
::= { dataArray7 398 }

dataValue7_399 OBJECT-TYPE
SYNTAX INTEGER
MAX-ACCESS read-write
STATUS current
DESCRIPTION
"Data value."
::= { dataArray7 399 }

dataArray8 OBJECT IDENTIFIER ::= { cc08255400_v1_00a 8 }

dataValue8_0 OBJECT-TYPE
SYNTAX INTEGER
MAX-ACCESS read-write
STATUS current
DESCRIPTION
"Data value."
::= { dataArray8 0 }

dataValue8_1 OBJECT-TYPE
SYNTAX INTEGER
MAX-ACCESS read-write
STATUS current
DESCRIPTION
"Data value."
::= { dataArray8 1 }

dataValue8_2 OBJECT-TYPE
SYNTAX INTEGER
MAX-ACCESS read-write
STATUS current
DESCRIPTION
"Data value."
::= { dataArray8 2 }

dataValue8_3 OBJECT-TYPE
SYNTAX INTEGER
MAX-ACCESS read-write
STATUS current
DESCRIPTION
"Data value."
::= { dataArray8 3 }

dataValue8_4 OBJECT-TYPE
SYNTAX INTEGER
MAX-ACCESS read-write
STATUS current
DESCRIPTION
"Data value."
::= { dataArray8 4 }

dataValue8_5 OBJECT-TYPE
SYNTAX INTEGER
MAX-ACCESS read-write
STATUS current
DESCRIPTION
"Data value."
::= { dataArray8 5 }

dataValue8_6 OBJECT-TYPE
SYNTAX INTEGER
MAX-ACCESS read-write
STATUS current
DESCRIPTION
"Data value."
::= { dataArray8 6 }

dataValue8_7 OBJECT-TYPE
SYNTAX INTEGER
MAX-ACCESS read-write
STATUS current
DESCRIPTION
"Data value."
::= { dataArray8 7 }

dataValue8_8 OBJECT-TYPE
SYNTAX INTEGER
MAX-ACCESS read-write
STATUS current
DESCRIPTION
"Data value."
::= { dataArray8 8 }

dataValue8_9 OBJECT-TYPE
SYNTAX INTEGER
MAX-ACCESS read-write
STATUS current
DESCRIPTION
"Data value."
::= { dataArray8 9 }

dataValue8_10 OBJECT-TYPE
SYNTAX INTEGER
MAX-ACCESS read-write
STATUS current
DESCRIPTION
"Data value."
::= { dataArray8 10 }

dataValue8_11 OBJECT-TYPE
SYNTAX INTEGER
MAX-ACCESS read-write
STATUS current
DESCRIPTION
"Data value."
::= { dataArray8 11 }

dataValue8_12 OBJECT-TYPE
SYNTAX INTEGER
MAX-ACCESS read-write
STATUS current
DESCRIPTION
"Data value."
::= { dataArray8 12 }

dataValue8_13 OBJECT-TYPE
SYNTAX INTEGER
MAX-ACCESS read-write
STATUS current
DESCRIPTION
"Data value."
::= { dataArray8 13 }

dataValue8_14 OBJECT-TYPE
SYNTAX INTEGER
MAX-ACCESS read-write
STATUS current
DESCRIPTION
"Data value."
::= { dataArray8 14 }

dataValue8_15 OBJECT-TYPE
SYNTAX INTEGER
MAX-ACCESS read-write
STATUS current
DESCRIPTION
"Data value."
::= { dataArray8 15 }

dataValue8_16 OBJECT-TYPE
SYNTAX INTEGER
MAX-ACCESS read-write
STATUS current
DESCRIPTION
"Data value."
::= { dataArray8 16 }

dataValue8_17 OBJECT-TYPE
SYNTAX INTEGER
MAX-ACCESS read-write
STATUS current
DESCRIPTION
"Data value."
::= { dataArray8 17 }

dataValue8_18 OBJECT-TYPE
SYNTAX INTEGER
MAX-ACCESS read-write
STATUS current
DESCRIPTION
"Data value."
::= { dataArray8 18 }

dataValue8_19 OBJECT-TYPE
SYNTAX INTEGER
MAX-ACCESS read-write
STATUS current
DESCRIPTION
"Data value."
::= { dataArray8 19 }

dataValue8_20 OBJECT-TYPE
SYNTAX INTEGER
MAX-ACCESS read-write
STATUS current
DESCRIPTION
"Data value."
::= { dataArray8 20 }

dataValue8_21 OBJECT-TYPE
SYNTAX INTEGER
MAX-ACCESS read-write
STATUS current
DESCRIPTION
"Data value."
::= { dataArray8 21 }

dataValue8_22 OBJECT-TYPE
SYNTAX INTEGER
MAX-ACCESS read-write
STATUS current
DESCRIPTION
"Data value."
::= { dataArray8 22 }

dataValue8_23 OBJECT-TYPE
SYNTAX INTEGER
MAX-ACCESS read-write
STATUS current
DESCRIPTION
"Data value."
::= { dataArray8 23 }

dataValue8_24 OBJECT-TYPE
SYNTAX INTEGER
MAX-ACCESS read-write
STATUS current
DESCRIPTION
"Data value."
::= { dataArray8 24 }

dataValue8_25 OBJECT-TYPE
SYNTAX INTEGER
MAX-ACCESS read-write
STATUS current
DESCRIPTION
"Data value."
::= { dataArray8 25 }

dataValue8_26 OBJECT-TYPE
SYNTAX INTEGER
MAX-ACCESS read-write
STATUS current
DESCRIPTION
"Data value."
::= { dataArray8 26 }

dataValue8_27 OBJECT-TYPE
SYNTAX INTEGER
MAX-ACCESS read-write
STATUS current
DESCRIPTION
"Data value."
::= { dataArray8 27 }

dataValue8_28 OBJECT-TYPE
SYNTAX INTEGER
MAX-ACCESS read-write
STATUS current
DESCRIPTION
"Data value."
::= { dataArray8 28 }

dataValue8_29 OBJECT-TYPE
SYNTAX INTEGER
MAX-ACCESS read-write
STATUS current
DESCRIPTION
"Data value."
::= { dataArray8 29 }

dataValue8_30 OBJECT-TYPE
SYNTAX INTEGER
MAX-ACCESS read-write
STATUS current
DESCRIPTION
"Data value."
::= { dataArray8 30 }

dataValue8_31 OBJECT-TYPE
SYNTAX INTEGER
MAX-ACCESS read-write
STATUS current
DESCRIPTION
"Data value."
::= { dataArray8 31 }

dataValue8_32 OBJECT-TYPE
SYNTAX INTEGER
MAX-ACCESS read-write
STATUS current
DESCRIPTION
"Data value."
::= { dataArray8 32 }

dataValue8_33 OBJECT-TYPE
SYNTAX INTEGER
MAX-ACCESS read-write
STATUS current
DESCRIPTION
"Data value."
::= { dataArray8 33 }

dataValue8_34 OBJECT-TYPE
SYNTAX INTEGER
MAX-ACCESS read-write
STATUS current
DESCRIPTION
"Data value."
::= { dataArray8 34 }

dataValue8_35 OBJECT-TYPE
SYNTAX INTEGER
MAX-ACCESS read-write
STATUS current
DESCRIPTION
"Data value."
::= { dataArray8 35 }

dataValue8_36 OBJECT-TYPE
SYNTAX INTEGER
MAX-ACCESS read-write
STATUS current
DESCRIPTION
"Data value."
::= { dataArray8 36 }

dataValue8_37 OBJECT-TYPE
SYNTAX INTEGER
MAX-ACCESS read-write
STATUS current
DESCRIPTION
"Data value."
::= { dataArray8 37 }

dataValue8_38 OBJECT-TYPE
SYNTAX INTEGER
MAX-ACCESS read-write
STATUS current
DESCRIPTION
"Data value."
::= { dataArray8 38 }

dataValue8_39 OBJECT-TYPE
SYNTAX INTEGER
MAX-ACCESS read-write
STATUS current
DESCRIPTION
"Data value."
::= { dataArray8 39 }

dataValue8_40 OBJECT-TYPE
SYNTAX INTEGER
MAX-ACCESS read-write
STATUS current
DESCRIPTION
"Data value."
::= { dataArray8 40 }

dataValue8_41 OBJECT-TYPE
SYNTAX INTEGER
MAX-ACCESS read-write
STATUS current
DESCRIPTION
"Data value."
::= { dataArray8 41 }

dataValue8_42 OBJECT-TYPE
SYNTAX INTEGER
MAX-ACCESS read-write
STATUS current
DESCRIPTION
"Data value."
::= { dataArray8 42 }

dataValue8_43 OBJECT-TYPE
SYNTAX INTEGER
MAX-ACCESS read-write
STATUS current
DESCRIPTION
"Data value."
::= { dataArray8 43 }

dataValue8_44 OBJECT-TYPE
SYNTAX INTEGER
MAX-ACCESS read-write
STATUS current
DESCRIPTION
"Data value."
::= { dataArray8 44 }

dataValue8_45 OBJECT-TYPE
SYNTAX INTEGER
MAX-ACCESS read-write
STATUS current
DESCRIPTION
"Data value."
::= { dataArray8 45 }

dataValue8_46 OBJECT-TYPE
SYNTAX INTEGER
MAX-ACCESS read-write
STATUS current
DESCRIPTION
"Data value."
::= { dataArray8 46 }

dataValue8_47 OBJECT-TYPE
SYNTAX INTEGER
MAX-ACCESS read-write
STATUS current
DESCRIPTION
"Data value."
::= { dataArray8 47 }

dataValue8_48 OBJECT-TYPE
SYNTAX INTEGER
MAX-ACCESS read-write
STATUS current
DESCRIPTION
"Data value."
::= { dataArray8 48 }

dataValue8_49 OBJECT-TYPE
SYNTAX INTEGER
MAX-ACCESS read-write
STATUS current
DESCRIPTION
"Data value."
::= { dataArray8 49 }

dataValue8_50 OBJECT-TYPE
SYNTAX INTEGER
MAX-ACCESS read-write
STATUS current
DESCRIPTION
"Data value."
::= { dataArray8 50 }

dataValue8_51 OBJECT-TYPE
SYNTAX INTEGER
MAX-ACCESS read-write
STATUS current
DESCRIPTION
"Data value."
::= { dataArray8 51 }

dataValue8_52 OBJECT-TYPE
SYNTAX INTEGER
MAX-ACCESS read-write
STATUS current
DESCRIPTION
"Data value."
::= { dataArray8 52 }

dataValue8_53 OBJECT-TYPE
SYNTAX INTEGER
MAX-ACCESS read-write
STATUS current
DESCRIPTION
"Data value."
::= { dataArray8 53 }

dataValue8_54 OBJECT-TYPE
SYNTAX INTEGER
MAX-ACCESS read-write
STATUS current
DESCRIPTION
"Data value."
::= { dataArray8 54 }

dataValue8_55 OBJECT-TYPE
SYNTAX INTEGER
MAX-ACCESS read-write
STATUS current
DESCRIPTION
"Data value."
::= { dataArray8 55 }

dataValue8_56 OBJECT-TYPE
SYNTAX INTEGER
MAX-ACCESS read-write
STATUS current
DESCRIPTION
"Data value."
::= { dataArray8 56 }

dataValue8_57 OBJECT-TYPE
SYNTAX INTEGER
MAX-ACCESS read-write
STATUS current
DESCRIPTION
"Data value."
::= { dataArray8 57 }

dataValue8_58 OBJECT-TYPE
SYNTAX INTEGER
MAX-ACCESS read-write
STATUS current
DESCRIPTION
"Data value."
::= { dataArray8 58 }

dataValue8_59 OBJECT-TYPE
SYNTAX INTEGER
MAX-ACCESS read-write
STATUS current
DESCRIPTION
"Data value."
::= { dataArray8 59 }

dataValue8_60 OBJECT-TYPE
SYNTAX INTEGER
MAX-ACCESS read-write
STATUS current
DESCRIPTION
"Data value."
::= { dataArray8 60 }

dataValue8_61 OBJECT-TYPE
SYNTAX INTEGER
MAX-ACCESS read-write
STATUS current
DESCRIPTION
"Data value."
::= { dataArray8 61 }

dataValue8_62 OBJECT-TYPE
SYNTAX INTEGER
MAX-ACCESS read-write
STATUS current
DESCRIPTION
"Data value."
::= { dataArray8 62 }

dataValue8_63 OBJECT-TYPE
SYNTAX INTEGER
MAX-ACCESS read-write
STATUS current
DESCRIPTION
"Data value."
::= { dataArray8 63 }

dataValue8_64 OBJECT-TYPE
SYNTAX INTEGER
MAX-ACCESS read-write
STATUS current
DESCRIPTION
"Data value."
::= { dataArray8 64 }

dataValue8_65 OBJECT-TYPE
SYNTAX INTEGER
MAX-ACCESS read-write
STATUS current
DESCRIPTION
"Data value."
::= { dataArray8 65 }

dataValue8_66 OBJECT-TYPE
SYNTAX INTEGER
MAX-ACCESS read-write
STATUS current
DESCRIPTION
"Data value."
::= { dataArray8 66 }

dataValue8_67 OBJECT-TYPE
SYNTAX INTEGER
MAX-ACCESS read-write
STATUS current
DESCRIPTION
"Data value."
::= { dataArray8 67 }

dataValue8_68 OBJECT-TYPE
SYNTAX INTEGER
MAX-ACCESS read-write
STATUS current
DESCRIPTION
"Data value."
::= { dataArray8 68 }

dataValue8_69 OBJECT-TYPE
SYNTAX INTEGER
MAX-ACCESS read-write
STATUS current
DESCRIPTION
"Data value."
::= { dataArray8 69 }

dataValue8_70 OBJECT-TYPE
SYNTAX INTEGER
MAX-ACCESS read-write
STATUS current
DESCRIPTION
"Data value."
::= { dataArray8 70 }

dataValue8_71 OBJECT-TYPE
SYNTAX INTEGER
MAX-ACCESS read-write
STATUS current
DESCRIPTION
"Data value."
::= { dataArray8 71 }

dataValue8_72 OBJECT-TYPE
SYNTAX INTEGER
MAX-ACCESS read-write
STATUS current
DESCRIPTION
"Data value."
::= { dataArray8 72 }

dataValue8_73 OBJECT-TYPE
SYNTAX INTEGER
MAX-ACCESS read-write
STATUS current
DESCRIPTION
"Data value."
::= { dataArray8 73 }

dataValue8_74 OBJECT-TYPE
SYNTAX INTEGER
MAX-ACCESS read-write
STATUS current
DESCRIPTION
"Data value."
::= { dataArray8 74 }

dataValue8_75 OBJECT-TYPE
SYNTAX INTEGER
MAX-ACCESS read-write
STATUS current
DESCRIPTION
"Data value."
::= { dataArray8 75 }

dataValue8_76 OBJECT-TYPE
SYNTAX INTEGER
MAX-ACCESS read-write
STATUS current
DESCRIPTION
"Data value."
::= { dataArray8 76 }

dataValue8_77 OBJECT-TYPE
SYNTAX INTEGER
MAX-ACCESS read-write
STATUS current
DESCRIPTION
"Data value."
::= { dataArray8 77 }

dataValue8_78 OBJECT-TYPE
SYNTAX INTEGER
MAX-ACCESS read-write
STATUS current
DESCRIPTION
"Data value."
::= { dataArray8 78 }

dataValue8_79 OBJECT-TYPE
SYNTAX INTEGER
MAX-ACCESS read-write
STATUS current
DESCRIPTION
"Data value."
::= { dataArray8 79 }

dataValue8_80 OBJECT-TYPE
SYNTAX INTEGER
MAX-ACCESS read-write
STATUS current
DESCRIPTION
"Data value."
::= { dataArray8 80 }

dataValue8_81 OBJECT-TYPE
SYNTAX INTEGER
MAX-ACCESS read-write
STATUS current
DESCRIPTION
"Data value."
::= { dataArray8 81 }

dataValue8_82 OBJECT-TYPE
SYNTAX INTEGER
MAX-ACCESS read-write
STATUS current
DESCRIPTION
"Data value."
::= { dataArray8 82 }

dataValue8_83 OBJECT-TYPE
SYNTAX INTEGER
MAX-ACCESS read-write
STATUS current
DESCRIPTION
"Data value."
::= { dataArray8 83 }

dataValue8_84 OBJECT-TYPE
SYNTAX INTEGER
MAX-ACCESS read-write
STATUS current
DESCRIPTION
"Data value."
::= { dataArray8 84 }

dataValue8_85 OBJECT-TYPE
SYNTAX INTEGER
MAX-ACCESS read-write
STATUS current
DESCRIPTION
"Data value."
::= { dataArray8 85 }

dataValue8_86 OBJECT-TYPE
SYNTAX INTEGER
MAX-ACCESS read-write
STATUS current
DESCRIPTION
"Data value."
::= { dataArray8 86 }

dataValue8_87 OBJECT-TYPE
SYNTAX INTEGER
MAX-ACCESS read-write
STATUS current
DESCRIPTION
"Data value."
::= { dataArray8 87 }

dataValue8_88 OBJECT-TYPE
SYNTAX INTEGER
MAX-ACCESS read-write
STATUS current
DESCRIPTION
"Data value."
::= { dataArray8 88 }

dataValue8_89 OBJECT-TYPE
SYNTAX INTEGER
MAX-ACCESS read-write
STATUS current
DESCRIPTION
"Data value."
::= { dataArray8 89 }

dataValue8_90 OBJECT-TYPE
SYNTAX INTEGER
MAX-ACCESS read-write
STATUS current
DESCRIPTION
"Data value."
::= { dataArray8 90 }

dataValue8_91 OBJECT-TYPE
SYNTAX INTEGER
MAX-ACCESS read-write
STATUS current
DESCRIPTION
"Data value."
::= { dataArray8 91 }

dataValue8_92 OBJECT-TYPE
SYNTAX INTEGER
MAX-ACCESS read-write
STATUS current
DESCRIPTION
"Data value."
::= { dataArray8 92 }

dataValue8_93 OBJECT-TYPE
SYNTAX INTEGER
MAX-ACCESS read-write
STATUS current
DESCRIPTION
"Data value."
::= { dataArray8 93 }

dataValue8_94 OBJECT-TYPE
SYNTAX INTEGER
MAX-ACCESS read-write
STATUS current
DESCRIPTION
"Data value."
::= { dataArray8 94 }

dataValue8_95 OBJECT-TYPE
SYNTAX INTEGER
MAX-ACCESS read-write
STATUS current
DESCRIPTION
"Data value."
::= { dataArray8 95 }

dataValue8_96 OBJECT-TYPE
SYNTAX INTEGER
MAX-ACCESS read-write
STATUS current
DESCRIPTION
"Data value."
::= { dataArray8 96 }

dataValue8_97 OBJECT-TYPE
SYNTAX INTEGER
MAX-ACCESS read-write
STATUS current
DESCRIPTION
"Data value."
::= { dataArray8 97 }

dataValue8_98 OBJECT-TYPE
SYNTAX INTEGER
MAX-ACCESS read-write
STATUS current
DESCRIPTION
"Data value."
::= { dataArray8 98 }

dataValue8_99 OBJECT-TYPE
SYNTAX INTEGER
MAX-ACCESS read-write
STATUS current
DESCRIPTION
"Data value."
::= { dataArray8 99 }

dataValue8_100 OBJECT-TYPE
SYNTAX INTEGER
MAX-ACCESS read-write
STATUS current
DESCRIPTION
"Data value."
::= { dataArray8 100 }

dataValue8_101 OBJECT-TYPE
SYNTAX INTEGER
MAX-ACCESS read-write
STATUS current
DESCRIPTION
"Data value."
::= { dataArray8 101 }

dataValue8_102 OBJECT-TYPE
SYNTAX INTEGER
MAX-ACCESS read-write
STATUS current
DESCRIPTION
"Data value."
::= { dataArray8 102 }

dataValue8_103 OBJECT-TYPE
SYNTAX INTEGER
MAX-ACCESS read-write
STATUS current
DESCRIPTION
"Data value."
::= { dataArray8 103 }

dataValue8_104 OBJECT-TYPE
SYNTAX INTEGER
MAX-ACCESS read-write
STATUS current
DESCRIPTION
"Data value."
::= { dataArray8 104 }

dataValue8_105 OBJECT-TYPE
SYNTAX INTEGER
MAX-ACCESS read-write
STATUS current
DESCRIPTION
"Data value."
::= { dataArray8 105 }

dataValue8_106 OBJECT-TYPE
SYNTAX INTEGER
MAX-ACCESS read-write
STATUS current
DESCRIPTION
"Data value."
::= { dataArray8 106 }

dataValue8_107 OBJECT-TYPE
SYNTAX INTEGER
MAX-ACCESS read-write
STATUS current
DESCRIPTION
"Data value."
::= { dataArray8 107 }

dataValue8_108 OBJECT-TYPE
SYNTAX INTEGER
MAX-ACCESS read-write
STATUS current
DESCRIPTION
"Data value."
::= { dataArray8 108 }

dataValue8_109 OBJECT-TYPE
SYNTAX INTEGER
MAX-ACCESS read-write
STATUS current
DESCRIPTION
"Data value."
::= { dataArray8 109 }

dataValue8_110 OBJECT-TYPE
SYNTAX INTEGER
MAX-ACCESS read-write
STATUS current
DESCRIPTION
"Data value."
::= { dataArray8 110 }

dataValue8_111 OBJECT-TYPE
SYNTAX INTEGER
MAX-ACCESS read-write
STATUS current
DESCRIPTION
"Data value."
::= { dataArray8 111 }

dataValue8_112 OBJECT-TYPE
SYNTAX INTEGER
MAX-ACCESS read-write
STATUS current
DESCRIPTION
"Data value."
::= { dataArray8 112 }

dataValue8_113 OBJECT-TYPE
SYNTAX INTEGER
MAX-ACCESS read-write
STATUS current
DESCRIPTION
"Data value."
::= { dataArray8 113 }

dataValue8_114 OBJECT-TYPE
SYNTAX INTEGER
MAX-ACCESS read-write
STATUS current
DESCRIPTION
"Data value."
::= { dataArray8 114 }

dataValue8_115 OBJECT-TYPE
SYNTAX INTEGER
MAX-ACCESS read-write
STATUS current
DESCRIPTION
"Data value."
::= { dataArray8 115 }

dataValue8_116 OBJECT-TYPE
SYNTAX INTEGER
MAX-ACCESS read-write
STATUS current
DESCRIPTION
"Data value."
::= { dataArray8 116 }

dataValue8_117 OBJECT-TYPE
SYNTAX INTEGER
MAX-ACCESS read-write
STATUS current
DESCRIPTION
"Data value."
::= { dataArray8 117 }

dataValue8_118 OBJECT-TYPE
SYNTAX INTEGER
MAX-ACCESS read-write
STATUS current
DESCRIPTION
"Data value."
::= { dataArray8 118 }

dataValue8_119 OBJECT-TYPE
SYNTAX INTEGER
MAX-ACCESS read-write
STATUS current
DESCRIPTION
"Data value."
::= { dataArray8 119 }

dataValue8_120 OBJECT-TYPE
SYNTAX INTEGER
MAX-ACCESS read-write
STATUS current
DESCRIPTION
"Data value."
::= { dataArray8 120 }

dataValue8_121 OBJECT-TYPE
SYNTAX INTEGER
MAX-ACCESS read-write
STATUS current
DESCRIPTION
"Data value."
::= { dataArray8 121 }

dataValue8_122 OBJECT-TYPE
SYNTAX INTEGER
MAX-ACCESS read-write
STATUS current
DESCRIPTION
"Data value."
::= { dataArray8 122 }

dataValue8_123 OBJECT-TYPE
SYNTAX INTEGER
MAX-ACCESS read-write
STATUS current
DESCRIPTION
"Data value."
::= { dataArray8 123 }

dataValue8_124 OBJECT-TYPE
SYNTAX INTEGER
MAX-ACCESS read-write
STATUS current
DESCRIPTION
"Data value."
::= { dataArray8 124 }

dataValue8_125 OBJECT-TYPE
SYNTAX INTEGER
MAX-ACCESS read-write
STATUS current
DESCRIPTION
"Data value."
::= { dataArray8 125 }

dataValue8_126 OBJECT-TYPE
SYNTAX INTEGER
MAX-ACCESS read-write
STATUS current
DESCRIPTION
"Data value."
::= { dataArray8 126 }

dataValue8_127 OBJECT-TYPE
SYNTAX INTEGER
MAX-ACCESS read-write
STATUS current
DESCRIPTION
"Data value."
::= { dataArray8 127 }

dataValue8_128 OBJECT-TYPE
SYNTAX INTEGER
MAX-ACCESS read-write
STATUS current
DESCRIPTION
"Data value."
::= { dataArray8 128 }

dataValue8_129 OBJECT-TYPE
SYNTAX INTEGER
MAX-ACCESS read-write
STATUS current
DESCRIPTION
"Data value."
::= { dataArray8 129 }

dataValue8_130 OBJECT-TYPE
SYNTAX INTEGER
MAX-ACCESS read-write
STATUS current
DESCRIPTION
"Data value."
::= { dataArray8 130 }

dataValue8_131 OBJECT-TYPE
SYNTAX INTEGER
MAX-ACCESS read-write
STATUS current
DESCRIPTION
"Data value."
::= { dataArray8 131 }

dataValue8_132 OBJECT-TYPE
SYNTAX INTEGER
MAX-ACCESS read-write
STATUS current
DESCRIPTION
"Data value."
::= { dataArray8 132 }

dataValue8_133 OBJECT-TYPE
SYNTAX INTEGER
MAX-ACCESS read-write
STATUS current
DESCRIPTION
"Data value."
::= { dataArray8 133 }

dataValue8_134 OBJECT-TYPE
SYNTAX INTEGER
MAX-ACCESS read-write
STATUS current
DESCRIPTION
"Data value."
::= { dataArray8 134 }

dataValue8_135 OBJECT-TYPE
SYNTAX INTEGER
MAX-ACCESS read-write
STATUS current
DESCRIPTION
"Data value."
::= { dataArray8 135 }

dataValue8_136 OBJECT-TYPE
SYNTAX INTEGER
MAX-ACCESS read-write
STATUS current
DESCRIPTION
"Data value."
::= { dataArray8 136 }

dataValue8_137 OBJECT-TYPE
SYNTAX INTEGER
MAX-ACCESS read-write
STATUS current
DESCRIPTION
"Data value."
::= { dataArray8 137 }

dataValue8_138 OBJECT-TYPE
SYNTAX INTEGER
MAX-ACCESS read-write
STATUS current
DESCRIPTION
"Data value."
::= { dataArray8 138 }

dataValue8_139 OBJECT-TYPE
SYNTAX INTEGER
MAX-ACCESS read-write
STATUS current
DESCRIPTION
"Data value."
::= { dataArray8 139 }

dataValue8_140 OBJECT-TYPE
SYNTAX INTEGER
MAX-ACCESS read-write
STATUS current
DESCRIPTION
"Data value."
::= { dataArray8 140 }

dataValue8_141 OBJECT-TYPE
SYNTAX INTEGER
MAX-ACCESS read-write
STATUS current
DESCRIPTION
"Data value."
::= { dataArray8 141 }

dataValue8_142 OBJECT-TYPE
SYNTAX INTEGER
MAX-ACCESS read-write
STATUS current
DESCRIPTION
"Data value."
::= { dataArray8 142 }

dataValue8_143 OBJECT-TYPE
SYNTAX INTEGER
MAX-ACCESS read-write
STATUS current
DESCRIPTION
"Data value."
::= { dataArray8 143 }

dataValue8_144 OBJECT-TYPE
SYNTAX INTEGER
MAX-ACCESS read-write
STATUS current
DESCRIPTION
"Data value."
::= { dataArray8 144 }

dataValue8_145 OBJECT-TYPE
SYNTAX INTEGER
MAX-ACCESS read-write
STATUS current
DESCRIPTION
"Data value."
::= { dataArray8 145 }

dataValue8_146 OBJECT-TYPE
SYNTAX INTEGER
MAX-ACCESS read-write
STATUS current
DESCRIPTION
"Data value."
::= { dataArray8 146 }

dataValue8_147 OBJECT-TYPE
SYNTAX INTEGER
MAX-ACCESS read-write
STATUS current
DESCRIPTION
"Data value."
::= { dataArray8 147 }

dataValue8_148 OBJECT-TYPE
SYNTAX INTEGER
MAX-ACCESS read-write
STATUS current
DESCRIPTION
"Data value."
::= { dataArray8 148 }

dataValue8_149 OBJECT-TYPE
SYNTAX INTEGER
MAX-ACCESS read-write
STATUS current
DESCRIPTION
"Data value."
::= { dataArray8 149 }

dataValue8_150 OBJECT-TYPE
SYNTAX INTEGER
MAX-ACCESS read-write
STATUS current
DESCRIPTION
"Data value."
::= { dataArray8 150 }

dataValue8_151 OBJECT-TYPE
SYNTAX INTEGER
MAX-ACCESS read-write
STATUS current
DESCRIPTION
"Data value."
::= { dataArray8 151 }

dataValue8_152 OBJECT-TYPE
SYNTAX INTEGER
MAX-ACCESS read-write
STATUS current
DESCRIPTION
"Data value."
::= { dataArray8 152 }

dataValue8_153 OBJECT-TYPE
SYNTAX INTEGER
MAX-ACCESS read-write
STATUS current
DESCRIPTION
"Data value."
::= { dataArray8 153 }

dataValue8_154 OBJECT-TYPE
SYNTAX INTEGER
MAX-ACCESS read-write
STATUS current
DESCRIPTION
"Data value."
::= { dataArray8 154 }

dataValue8_155 OBJECT-TYPE
SYNTAX INTEGER
MAX-ACCESS read-write
STATUS current
DESCRIPTION
"Data value."
::= { dataArray8 155 }

dataValue8_156 OBJECT-TYPE
SYNTAX INTEGER
MAX-ACCESS read-write
STATUS current
DESCRIPTION
"Data value."
::= { dataArray8 156 }

dataValue8_157 OBJECT-TYPE
SYNTAX INTEGER
MAX-ACCESS read-write
STATUS current
DESCRIPTION
"Data value."
::= { dataArray8 157 }

dataValue8_158 OBJECT-TYPE
SYNTAX INTEGER
MAX-ACCESS read-write
STATUS current
DESCRIPTION
"Data value."
::= { dataArray8 158 }

dataValue8_159 OBJECT-TYPE
SYNTAX INTEGER
MAX-ACCESS read-write
STATUS current
DESCRIPTION
"Data value."
::= { dataArray8 159 }

dataValue8_160 OBJECT-TYPE
SYNTAX INTEGER
MAX-ACCESS read-write
STATUS current
DESCRIPTION
"Data value."
::= { dataArray8 160 }

dataValue8_161 OBJECT-TYPE
SYNTAX INTEGER
MAX-ACCESS read-write
STATUS current
DESCRIPTION
"Data value."
::= { dataArray8 161 }

dataValue8_162 OBJECT-TYPE
SYNTAX INTEGER
MAX-ACCESS read-write
STATUS current
DESCRIPTION
"Data value."
::= { dataArray8 162 }

dataValue8_163 OBJECT-TYPE
SYNTAX INTEGER
MAX-ACCESS read-write
STATUS current
DESCRIPTION
"Data value."
::= { dataArray8 163 }

dataValue8_164 OBJECT-TYPE
SYNTAX INTEGER
MAX-ACCESS read-write
STATUS current
DESCRIPTION
"Data value."
::= { dataArray8 164 }

dataValue8_165 OBJECT-TYPE
SYNTAX INTEGER
MAX-ACCESS read-write
STATUS current
DESCRIPTION
"Data value."
::= { dataArray8 165 }

dataValue8_166 OBJECT-TYPE
SYNTAX INTEGER
MAX-ACCESS read-write
STATUS current
DESCRIPTION
"Data value."
::= { dataArray8 166 }

dataValue8_167 OBJECT-TYPE
SYNTAX INTEGER
MAX-ACCESS read-write
STATUS current
DESCRIPTION
"Data value."
::= { dataArray8 167 }

dataValue8_168 OBJECT-TYPE
SYNTAX INTEGER
MAX-ACCESS read-write
STATUS current
DESCRIPTION
"Data value."
::= { dataArray8 168 }

dataValue8_169 OBJECT-TYPE
SYNTAX INTEGER
MAX-ACCESS read-write
STATUS current
DESCRIPTION
"Data value."
::= { dataArray8 169 }

dataValue8_170 OBJECT-TYPE
SYNTAX INTEGER
MAX-ACCESS read-write
STATUS current
DESCRIPTION
"Data value."
::= { dataArray8 170 }

dataValue8_171 OBJECT-TYPE
SYNTAX INTEGER
MAX-ACCESS read-write
STATUS current
DESCRIPTION
"Data value."
::= { dataArray8 171 }

dataValue8_172 OBJECT-TYPE
SYNTAX INTEGER
MAX-ACCESS read-write
STATUS current
DESCRIPTION
"Data value."
::= { dataArray8 172 }

dataValue8_173 OBJECT-TYPE
SYNTAX INTEGER
MAX-ACCESS read-write
STATUS current
DESCRIPTION
"Data value."
::= { dataArray8 173 }

dataValue8_174 OBJECT-TYPE
SYNTAX INTEGER
MAX-ACCESS read-write
STATUS current
DESCRIPTION
"Data value."
::= { dataArray8 174 }

dataValue8_175 OBJECT-TYPE
SYNTAX INTEGER
MAX-ACCESS read-write
STATUS current
DESCRIPTION
"Data value."
::= { dataArray8 175 }

dataValue8_176 OBJECT-TYPE
SYNTAX INTEGER
MAX-ACCESS read-write
STATUS current
DESCRIPTION
"Data value."
::= { dataArray8 176 }

dataValue8_177 OBJECT-TYPE
SYNTAX INTEGER
MAX-ACCESS read-write
STATUS current
DESCRIPTION
"Data value."
::= { dataArray8 177 }

dataValue8_178 OBJECT-TYPE
SYNTAX INTEGER
MAX-ACCESS read-write
STATUS current
DESCRIPTION
"Data value."
::= { dataArray8 178 }

dataValue8_179 OBJECT-TYPE
SYNTAX INTEGER
MAX-ACCESS read-write
STATUS current
DESCRIPTION
"Data value."
::= { dataArray8 179 }

dataValue8_180 OBJECT-TYPE
SYNTAX INTEGER
MAX-ACCESS read-write
STATUS current
DESCRIPTION
"Data value."
::= { dataArray8 180 }

dataValue8_181 OBJECT-TYPE
SYNTAX INTEGER
MAX-ACCESS read-write
STATUS current
DESCRIPTION
"Data value."
::= { dataArray8 181 }

dataValue8_182 OBJECT-TYPE
SYNTAX INTEGER
MAX-ACCESS read-write
STATUS current
DESCRIPTION
"Data value."
::= { dataArray8 182 }

dataValue8_183 OBJECT-TYPE
SYNTAX INTEGER
MAX-ACCESS read-write
STATUS current
DESCRIPTION
"Data value."
::= { dataArray8 183 }

dataValue8_184 OBJECT-TYPE
SYNTAX INTEGER
MAX-ACCESS read-write
STATUS current
DESCRIPTION
"Data value."
::= { dataArray8 184 }

dataValue8_185 OBJECT-TYPE
SYNTAX INTEGER
MAX-ACCESS read-write
STATUS current
DESCRIPTION
"Data value."
::= { dataArray8 185 }

dataValue8_186 OBJECT-TYPE
SYNTAX INTEGER
MAX-ACCESS read-write
STATUS current
DESCRIPTION
"Data value."
::= { dataArray8 186 }

dataValue8_187 OBJECT-TYPE
SYNTAX INTEGER
MAX-ACCESS read-write
STATUS current
DESCRIPTION
"Data value."
::= { dataArray8 187 }

dataValue8_188 OBJECT-TYPE
SYNTAX INTEGER
MAX-ACCESS read-write
STATUS current
DESCRIPTION
"Data value."
::= { dataArray8 188 }

dataValue8_189 OBJECT-TYPE
SYNTAX INTEGER
MAX-ACCESS read-write
STATUS current
DESCRIPTION
"Data value."
::= { dataArray8 189 }

dataValue8_190 OBJECT-TYPE
SYNTAX INTEGER
MAX-ACCESS read-write
STATUS current
DESCRIPTION
"Data value."
::= { dataArray8 190 }

dataValue8_191 OBJECT-TYPE
SYNTAX INTEGER
MAX-ACCESS read-write
STATUS current
DESCRIPTION
"Data value."
::= { dataArray8 191 }

dataValue8_192 OBJECT-TYPE
SYNTAX INTEGER
MAX-ACCESS read-write
STATUS current
DESCRIPTION
"Data value."
::= { dataArray8 192 }

dataValue8_193 OBJECT-TYPE
SYNTAX INTEGER
MAX-ACCESS read-write
STATUS current
DESCRIPTION
"Data value."
::= { dataArray8 193 }

dataValue8_194 OBJECT-TYPE
SYNTAX INTEGER
MAX-ACCESS read-write
STATUS current
DESCRIPTION
"Data value."
::= { dataArray8 194 }

dataValue8_195 OBJECT-TYPE
SYNTAX INTEGER
MAX-ACCESS read-write
STATUS current
DESCRIPTION
"Data value."
::= { dataArray8 195 }

dataValue8_196 OBJECT-TYPE
SYNTAX INTEGER
MAX-ACCESS read-write
STATUS current
DESCRIPTION
"Data value."
::= { dataArray8 196 }

dataValue8_197 OBJECT-TYPE
SYNTAX INTEGER
MAX-ACCESS read-write
STATUS current
DESCRIPTION
"Data value."
::= { dataArray8 197 }

dataValue8_198 OBJECT-TYPE
SYNTAX INTEGER
MAX-ACCESS read-write
STATUS current
DESCRIPTION
"Data value."
::= { dataArray8 198 }

dataValue8_199 OBJECT-TYPE
SYNTAX INTEGER
MAX-ACCESS read-write
STATUS current
DESCRIPTION
"Data value."
::= { dataArray8 199 }

dataValue8_200 OBJECT-TYPE
SYNTAX INTEGER
MAX-ACCESS read-write
STATUS current
DESCRIPTION
"Data value."
::= { dataArray8 200 }

dataValue8_201 OBJECT-TYPE
SYNTAX INTEGER
MAX-ACCESS read-write
STATUS current
DESCRIPTION
"Data value."
::= { dataArray8 201 }

dataValue8_202 OBJECT-TYPE
SYNTAX INTEGER
MAX-ACCESS read-write
STATUS current
DESCRIPTION
"Data value."
::= { dataArray8 202 }

dataValue8_203 OBJECT-TYPE
SYNTAX INTEGER
MAX-ACCESS read-write
STATUS current
DESCRIPTION
"Data value."
::= { dataArray8 203 }

dataValue8_204 OBJECT-TYPE
SYNTAX INTEGER
MAX-ACCESS read-write
STATUS current
DESCRIPTION
"Data value."
::= { dataArray8 204 }

dataValue8_205 OBJECT-TYPE
SYNTAX INTEGER
MAX-ACCESS read-write
STATUS current
DESCRIPTION
"Data value."
::= { dataArray8 205 }

dataValue8_206 OBJECT-TYPE
SYNTAX INTEGER
MAX-ACCESS read-write
STATUS current
DESCRIPTION
"Data value."
::= { dataArray8 206 }

dataValue8_207 OBJECT-TYPE
SYNTAX INTEGER
MAX-ACCESS read-write
STATUS current
DESCRIPTION
"Data value."
::= { dataArray8 207 }

dataValue8_208 OBJECT-TYPE
SYNTAX INTEGER
MAX-ACCESS read-write
STATUS current
DESCRIPTION
"Data value."
::= { dataArray8 208 }

dataValue8_209 OBJECT-TYPE
SYNTAX INTEGER
MAX-ACCESS read-write
STATUS current
DESCRIPTION
"Data value."
::= { dataArray8 209 }

dataValue8_210 OBJECT-TYPE
SYNTAX INTEGER
MAX-ACCESS read-write
STATUS current
DESCRIPTION
"Data value."
::= { dataArray8 210 }

dataValue8_211 OBJECT-TYPE
SYNTAX INTEGER
MAX-ACCESS read-write
STATUS current
DESCRIPTION
"Data value."
::= { dataArray8 211 }

dataValue8_212 OBJECT-TYPE
SYNTAX INTEGER
MAX-ACCESS read-write
STATUS current
DESCRIPTION
"Data value."
::= { dataArray8 212 }

dataValue8_213 OBJECT-TYPE
SYNTAX INTEGER
MAX-ACCESS read-write
STATUS current
DESCRIPTION
"Data value."
::= { dataArray8 213 }

dataValue8_214 OBJECT-TYPE
SYNTAX INTEGER
MAX-ACCESS read-write
STATUS current
DESCRIPTION
"Data value."
::= { dataArray8 214 }

dataValue8_215 OBJECT-TYPE
SYNTAX INTEGER
MAX-ACCESS read-write
STATUS current
DESCRIPTION
"Data value."
::= { dataArray8 215 }

dataValue8_216 OBJECT-TYPE
SYNTAX INTEGER
MAX-ACCESS read-write
STATUS current
DESCRIPTION
"Data value."
::= { dataArray8 216 }

dataValue8_217 OBJECT-TYPE
SYNTAX INTEGER
MAX-ACCESS read-write
STATUS current
DESCRIPTION
"Data value."
::= { dataArray8 217 }

dataValue8_218 OBJECT-TYPE
SYNTAX INTEGER
MAX-ACCESS read-write
STATUS current
DESCRIPTION
"Data value."
::= { dataArray8 218 }

dataValue8_219 OBJECT-TYPE
SYNTAX INTEGER
MAX-ACCESS read-write
STATUS current
DESCRIPTION
"Data value."
::= { dataArray8 219 }

dataValue8_220 OBJECT-TYPE
SYNTAX INTEGER
MAX-ACCESS read-write
STATUS current
DESCRIPTION
"Data value."
::= { dataArray8 220 }

dataValue8_221 OBJECT-TYPE
SYNTAX INTEGER
MAX-ACCESS read-write
STATUS current
DESCRIPTION
"Data value."
::= { dataArray8 221 }

dataValue8_222 OBJECT-TYPE
SYNTAX INTEGER
MAX-ACCESS read-write
STATUS current
DESCRIPTION
"Data value."
::= { dataArray8 222 }

dataValue8_223 OBJECT-TYPE
SYNTAX INTEGER
MAX-ACCESS read-write
STATUS current
DESCRIPTION
"Data value."
::= { dataArray8 223 }

dataValue8_224 OBJECT-TYPE
SYNTAX INTEGER
MAX-ACCESS read-write
STATUS current
DESCRIPTION
"Data value."
::= { dataArray8 224 }

dataValue8_225 OBJECT-TYPE
SYNTAX INTEGER
MAX-ACCESS read-write
STATUS current
DESCRIPTION
"Data value."
::= { dataArray8 225 }

dataValue8_226 OBJECT-TYPE
SYNTAX INTEGER
MAX-ACCESS read-write
STATUS current
DESCRIPTION
"Data value."
::= { dataArray8 226 }

dataValue8_227 OBJECT-TYPE
SYNTAX INTEGER
MAX-ACCESS read-write
STATUS current
DESCRIPTION
"Data value."
::= { dataArray8 227 }

dataValue8_228 OBJECT-TYPE
SYNTAX INTEGER
MAX-ACCESS read-write
STATUS current
DESCRIPTION
"Data value."
::= { dataArray8 228 }

dataValue8_229 OBJECT-TYPE
SYNTAX INTEGER
MAX-ACCESS read-write
STATUS current
DESCRIPTION
"Data value."
::= { dataArray8 229 }

dataValue8_230 OBJECT-TYPE
SYNTAX INTEGER
MAX-ACCESS read-write
STATUS current
DESCRIPTION
"Data value."
::= { dataArray8 230 }

dataValue8_231 OBJECT-TYPE
SYNTAX INTEGER
MAX-ACCESS read-write
STATUS current
DESCRIPTION
"Data value."
::= { dataArray8 231 }

dataValue8_232 OBJECT-TYPE
SYNTAX INTEGER
MAX-ACCESS read-write
STATUS current
DESCRIPTION
"Data value."
::= { dataArray8 232 }

dataValue8_233 OBJECT-TYPE
SYNTAX INTEGER
MAX-ACCESS read-write
STATUS current
DESCRIPTION
"Data value."
::= { dataArray8 233 }

dataValue8_234 OBJECT-TYPE
SYNTAX INTEGER
MAX-ACCESS read-write
STATUS current
DESCRIPTION
"Data value."
::= { dataArray8 234 }

dataValue8_235 OBJECT-TYPE
SYNTAX INTEGER
MAX-ACCESS read-write
STATUS current
DESCRIPTION
"Data value."
::= { dataArray8 235 }

dataValue8_236 OBJECT-TYPE
SYNTAX INTEGER
MAX-ACCESS read-write
STATUS current
DESCRIPTION
"Data value."
::= { dataArray8 236 }

dataValue8_237 OBJECT-TYPE
SYNTAX INTEGER
MAX-ACCESS read-write
STATUS current
DESCRIPTION
"Data value."
::= { dataArray8 237 }

dataValue8_238 OBJECT-TYPE
SYNTAX INTEGER
MAX-ACCESS read-write
STATUS current
DESCRIPTION
"Data value."
::= { dataArray8 238 }

dataValue8_239 OBJECT-TYPE
SYNTAX INTEGER
MAX-ACCESS read-write
STATUS current
DESCRIPTION
"Data value."
::= { dataArray8 239 }

dataValue8_240 OBJECT-TYPE
SYNTAX INTEGER
MAX-ACCESS read-write
STATUS current
DESCRIPTION
"Data value."
::= { dataArray8 240 }

dataValue8_241 OBJECT-TYPE
SYNTAX INTEGER
MAX-ACCESS read-write
STATUS current
DESCRIPTION
"Data value."
::= { dataArray8 241 }

dataValue8_242 OBJECT-TYPE
SYNTAX INTEGER
MAX-ACCESS read-write
STATUS current
DESCRIPTION
"Data value."
::= { dataArray8 242 }

dataValue8_243 OBJECT-TYPE
SYNTAX INTEGER
MAX-ACCESS read-write
STATUS current
DESCRIPTION
"Data value."
::= { dataArray8 243 }

dataValue8_244 OBJECT-TYPE
SYNTAX INTEGER
MAX-ACCESS read-write
STATUS current
DESCRIPTION
"Data value."
::= { dataArray8 244 }

dataValue8_245 OBJECT-TYPE
SYNTAX INTEGER
MAX-ACCESS read-write
STATUS current
DESCRIPTION
"Data value."
::= { dataArray8 245 }

dataValue8_246 OBJECT-TYPE
SYNTAX INTEGER
MAX-ACCESS read-write
STATUS current
DESCRIPTION
"Data value."
::= { dataArray8 246 }

dataValue8_247 OBJECT-TYPE
SYNTAX INTEGER
MAX-ACCESS read-write
STATUS current
DESCRIPTION
"Data value."
::= { dataArray8 247 }

dataValue8_248 OBJECT-TYPE
SYNTAX INTEGER
MAX-ACCESS read-write
STATUS current
DESCRIPTION
"Data value."
::= { dataArray8 248 }

dataValue8_249 OBJECT-TYPE
SYNTAX INTEGER
MAX-ACCESS read-write
STATUS current
DESCRIPTION
"Data value."
::= { dataArray8 249 }

dataValue8_250 OBJECT-TYPE
SYNTAX INTEGER
MAX-ACCESS read-write
STATUS current
DESCRIPTION
"Data value."
::= { dataArray8 250 }

dataValue8_251 OBJECT-TYPE
SYNTAX INTEGER
MAX-ACCESS read-write
STATUS current
DESCRIPTION
"Data value."
::= { dataArray8 251 }

dataValue8_252 OBJECT-TYPE
SYNTAX INTEGER
MAX-ACCESS read-write
STATUS current
DESCRIPTION
"Data value."
::= { dataArray8 252 }

dataValue8_253 OBJECT-TYPE
SYNTAX INTEGER
MAX-ACCESS read-write
STATUS current
DESCRIPTION
"Data value."
::= { dataArray8 253 }

dataValue8_254 OBJECT-TYPE
SYNTAX INTEGER
MAX-ACCESS read-write
STATUS current
DESCRIPTION
"Data value."
::= { dataArray8 254 }

dataValue8_255 OBJECT-TYPE
SYNTAX INTEGER
MAX-ACCESS read-write
STATUS current
DESCRIPTION
"Data value."
::= { dataArray8 255 }

dataValue8_256 OBJECT-TYPE
SYNTAX INTEGER
MAX-ACCESS read-write
STATUS current
DESCRIPTION
"Data value."
::= { dataArray8 256 }

dataValue8_257 OBJECT-TYPE
SYNTAX INTEGER
MAX-ACCESS read-write
STATUS current
DESCRIPTION
"Data value."
::= { dataArray8 257 }

dataValue8_258 OBJECT-TYPE
SYNTAX INTEGER
MAX-ACCESS read-write
STATUS current
DESCRIPTION
"Data value."
::= { dataArray8 258 }

dataValue8_259 OBJECT-TYPE
SYNTAX INTEGER
MAX-ACCESS read-write
STATUS current
DESCRIPTION
"Data value."
::= { dataArray8 259 }

dataValue8_260 OBJECT-TYPE
SYNTAX INTEGER
MAX-ACCESS read-write
STATUS current
DESCRIPTION
"Data value."
::= { dataArray8 260 }

dataValue8_261 OBJECT-TYPE
SYNTAX INTEGER
MAX-ACCESS read-write
STATUS current
DESCRIPTION
"Data value."
::= { dataArray8 261 }

dataValue8_262 OBJECT-TYPE
SYNTAX INTEGER
MAX-ACCESS read-write
STATUS current
DESCRIPTION
"Data value."
::= { dataArray8 262 }

dataValue8_263 OBJECT-TYPE
SYNTAX INTEGER
MAX-ACCESS read-write
STATUS current
DESCRIPTION
"Data value."
::= { dataArray8 263 }

dataValue8_264 OBJECT-TYPE
SYNTAX INTEGER
MAX-ACCESS read-write
STATUS current
DESCRIPTION
"Data value."
::= { dataArray8 264 }

dataValue8_265 OBJECT-TYPE
SYNTAX INTEGER
MAX-ACCESS read-write
STATUS current
DESCRIPTION
"Data value."
::= { dataArray8 265 }

dataValue8_266 OBJECT-TYPE
SYNTAX INTEGER
MAX-ACCESS read-write
STATUS current
DESCRIPTION
"Data value."
::= { dataArray8 266 }

dataValue8_267 OBJECT-TYPE
SYNTAX INTEGER
MAX-ACCESS read-write
STATUS current
DESCRIPTION
"Data value."
::= { dataArray8 267 }

dataValue8_268 OBJECT-TYPE
SYNTAX INTEGER
MAX-ACCESS read-write
STATUS current
DESCRIPTION
"Data value."
::= { dataArray8 268 }

dataValue8_269 OBJECT-TYPE
SYNTAX INTEGER
MAX-ACCESS read-write
STATUS current
DESCRIPTION
"Data value."
::= { dataArray8 269 }

dataValue8_270 OBJECT-TYPE
SYNTAX INTEGER
MAX-ACCESS read-write
STATUS current
DESCRIPTION
"Data value."
::= { dataArray8 270 }

dataValue8_271 OBJECT-TYPE
SYNTAX INTEGER
MAX-ACCESS read-write
STATUS current
DESCRIPTION
"Data value."
::= { dataArray8 271 }

dataValue8_272 OBJECT-TYPE
SYNTAX INTEGER
MAX-ACCESS read-write
STATUS current
DESCRIPTION
"Data value."
::= { dataArray8 272 }

dataValue8_273 OBJECT-TYPE
SYNTAX INTEGER
MAX-ACCESS read-write
STATUS current
DESCRIPTION
"Data value."
::= { dataArray8 273 }

dataValue8_274 OBJECT-TYPE
SYNTAX INTEGER
MAX-ACCESS read-write
STATUS current
DESCRIPTION
"Data value."
::= { dataArray8 274 }

dataValue8_275 OBJECT-TYPE
SYNTAX INTEGER
MAX-ACCESS read-write
STATUS current
DESCRIPTION
"Data value."
::= { dataArray8 275 }

dataValue8_276 OBJECT-TYPE
SYNTAX INTEGER
MAX-ACCESS read-write
STATUS current
DESCRIPTION
"Data value."
::= { dataArray8 276 }

dataValue8_277 OBJECT-TYPE
SYNTAX INTEGER
MAX-ACCESS read-write
STATUS current
DESCRIPTION
"Data value."
::= { dataArray8 277 }

dataValue8_278 OBJECT-TYPE
SYNTAX INTEGER
MAX-ACCESS read-write
STATUS current
DESCRIPTION
"Data value."
::= { dataArray8 278 }

dataValue8_279 OBJECT-TYPE
SYNTAX INTEGER
MAX-ACCESS read-write
STATUS current
DESCRIPTION
"Data value."
::= { dataArray8 279 }

dataValue8_280 OBJECT-TYPE
SYNTAX INTEGER
MAX-ACCESS read-write
STATUS current
DESCRIPTION
"Data value."
::= { dataArray8 280 }

dataValue8_281 OBJECT-TYPE
SYNTAX INTEGER
MAX-ACCESS read-write
STATUS current
DESCRIPTION
"Data value."
::= { dataArray8 281 }

dataValue8_282 OBJECT-TYPE
SYNTAX INTEGER
MAX-ACCESS read-write
STATUS current
DESCRIPTION
"Data value."
::= { dataArray8 282 }

dataValue8_283 OBJECT-TYPE
SYNTAX INTEGER
MAX-ACCESS read-write
STATUS current
DESCRIPTION
"Data value."
::= { dataArray8 283 }

dataValue8_284 OBJECT-TYPE
SYNTAX INTEGER
MAX-ACCESS read-write
STATUS current
DESCRIPTION
"Data value."
::= { dataArray8 284 }

dataValue8_285 OBJECT-TYPE
SYNTAX INTEGER
MAX-ACCESS read-write
STATUS current
DESCRIPTION
"Data value."
::= { dataArray8 285 }

dataValue8_286 OBJECT-TYPE
SYNTAX INTEGER
MAX-ACCESS read-write
STATUS current
DESCRIPTION
"Data value."
::= { dataArray8 286 }

dataValue8_287 OBJECT-TYPE
SYNTAX INTEGER
MAX-ACCESS read-write
STATUS current
DESCRIPTION
"Data value."
::= { dataArray8 287 }

dataValue8_288 OBJECT-TYPE
SYNTAX INTEGER
MAX-ACCESS read-write
STATUS current
DESCRIPTION
"Data value."
::= { dataArray8 288 }

dataValue8_289 OBJECT-TYPE
SYNTAX INTEGER
MAX-ACCESS read-write
STATUS current
DESCRIPTION
"Data value."
::= { dataArray8 289 }

dataValue8_290 OBJECT-TYPE
SYNTAX INTEGER
MAX-ACCESS read-write
STATUS current
DESCRIPTION
"Data value."
::= { dataArray8 290 }

dataValue8_291 OBJECT-TYPE
SYNTAX INTEGER
MAX-ACCESS read-write
STATUS current
DESCRIPTION
"Data value."
::= { dataArray8 291 }

dataValue8_292 OBJECT-TYPE
SYNTAX INTEGER
MAX-ACCESS read-write
STATUS current
DESCRIPTION
"Data value."
::= { dataArray8 292 }

dataValue8_293 OBJECT-TYPE
SYNTAX INTEGER
MAX-ACCESS read-write
STATUS current
DESCRIPTION
"Data value."
::= { dataArray8 293 }

dataValue8_294 OBJECT-TYPE
SYNTAX INTEGER
MAX-ACCESS read-write
STATUS current
DESCRIPTION
"Data value."
::= { dataArray8 294 }

dataValue8_295 OBJECT-TYPE
SYNTAX INTEGER
MAX-ACCESS read-write
STATUS current
DESCRIPTION
"Data value."
::= { dataArray8 295 }

dataValue8_296 OBJECT-TYPE
SYNTAX INTEGER
MAX-ACCESS read-write
STATUS current
DESCRIPTION
"Data value."
::= { dataArray8 296 }

dataValue8_297 OBJECT-TYPE
SYNTAX INTEGER
MAX-ACCESS read-write
STATUS current
DESCRIPTION
"Data value."
::= { dataArray8 297 }

dataValue8_298 OBJECT-TYPE
SYNTAX INTEGER
MAX-ACCESS read-write
STATUS current
DESCRIPTION
"Data value."
::= { dataArray8 298 }

dataValue8_299 OBJECT-TYPE
SYNTAX INTEGER
MAX-ACCESS read-write
STATUS current
DESCRIPTION
"Data value."
::= { dataArray8 299 }

dataValue8_300 OBJECT-TYPE
SYNTAX INTEGER
MAX-ACCESS read-write
STATUS current
DESCRIPTION
"Data value."
::= { dataArray8 300 }

dataValue8_301 OBJECT-TYPE
SYNTAX INTEGER
MAX-ACCESS read-write
STATUS current
DESCRIPTION
"Data value."
::= { dataArray8 301 }

dataValue8_302 OBJECT-TYPE
SYNTAX INTEGER
MAX-ACCESS read-write
STATUS current
DESCRIPTION
"Data value."
::= { dataArray8 302 }

dataValue8_303 OBJECT-TYPE
SYNTAX INTEGER
MAX-ACCESS read-write
STATUS current
DESCRIPTION
"Data value."
::= { dataArray8 303 }

dataValue8_304 OBJECT-TYPE
SYNTAX INTEGER
MAX-ACCESS read-write
STATUS current
DESCRIPTION
"Data value."
::= { dataArray8 304 }

dataValue8_305 OBJECT-TYPE
SYNTAX INTEGER
MAX-ACCESS read-write
STATUS current
DESCRIPTION
"Data value."
::= { dataArray8 305 }

dataValue8_306 OBJECT-TYPE
SYNTAX INTEGER
MAX-ACCESS read-write
STATUS current
DESCRIPTION
"Data value."
::= { dataArray8 306 }

dataValue8_307 OBJECT-TYPE
SYNTAX INTEGER
MAX-ACCESS read-write
STATUS current
DESCRIPTION
"Data value."
::= { dataArray8 307 }

dataValue8_308 OBJECT-TYPE
SYNTAX INTEGER
MAX-ACCESS read-write
STATUS current
DESCRIPTION
"Data value."
::= { dataArray8 308 }

dataValue8_309 OBJECT-TYPE
SYNTAX INTEGER
MAX-ACCESS read-write
STATUS current
DESCRIPTION
"Data value."
::= { dataArray8 309 }

dataValue8_310 OBJECT-TYPE
SYNTAX INTEGER
MAX-ACCESS read-write
STATUS current
DESCRIPTION
"Data value."
::= { dataArray8 310 }

dataValue8_311 OBJECT-TYPE
SYNTAX INTEGER
MAX-ACCESS read-write
STATUS current
DESCRIPTION
"Data value."
::= { dataArray8 311 }

dataValue8_312 OBJECT-TYPE
SYNTAX INTEGER
MAX-ACCESS read-write
STATUS current
DESCRIPTION
"Data value."
::= { dataArray8 312 }

dataValue8_313 OBJECT-TYPE
SYNTAX INTEGER
MAX-ACCESS read-write
STATUS current
DESCRIPTION
"Data value."
::= { dataArray8 313 }

dataValue8_314 OBJECT-TYPE
SYNTAX INTEGER
MAX-ACCESS read-write
STATUS current
DESCRIPTION
"Data value."
::= { dataArray8 314 }

dataValue8_315 OBJECT-TYPE
SYNTAX INTEGER
MAX-ACCESS read-write
STATUS current
DESCRIPTION
"Data value."
::= { dataArray8 315 }

dataValue8_316 OBJECT-TYPE
SYNTAX INTEGER
MAX-ACCESS read-write
STATUS current
DESCRIPTION
"Data value."
::= { dataArray8 316 }

dataValue8_317 OBJECT-TYPE
SYNTAX INTEGER
MAX-ACCESS read-write
STATUS current
DESCRIPTION
"Data value."
::= { dataArray8 317 }

dataValue8_318 OBJECT-TYPE
SYNTAX INTEGER
MAX-ACCESS read-write
STATUS current
DESCRIPTION
"Data value."
::= { dataArray8 318 }

dataValue8_319 OBJECT-TYPE
SYNTAX INTEGER
MAX-ACCESS read-write
STATUS current
DESCRIPTION
"Data value."
::= { dataArray8 319 }

dataValue8_320 OBJECT-TYPE
SYNTAX INTEGER
MAX-ACCESS read-write
STATUS current
DESCRIPTION
"Data value."
::= { dataArray8 320 }

dataValue8_321 OBJECT-TYPE
SYNTAX INTEGER
MAX-ACCESS read-write
STATUS current
DESCRIPTION
"Data value."
::= { dataArray8 321 }

dataValue8_322 OBJECT-TYPE
SYNTAX INTEGER
MAX-ACCESS read-write
STATUS current
DESCRIPTION
"Data value."
::= { dataArray8 322 }

dataValue8_323 OBJECT-TYPE
SYNTAX INTEGER
MAX-ACCESS read-write
STATUS current
DESCRIPTION
"Data value."
::= { dataArray8 323 }

dataValue8_324 OBJECT-TYPE
SYNTAX INTEGER
MAX-ACCESS read-write
STATUS current
DESCRIPTION
"Data value."
::= { dataArray8 324 }

dataValue8_325 OBJECT-TYPE
SYNTAX INTEGER
MAX-ACCESS read-write
STATUS current
DESCRIPTION
"Data value."
::= { dataArray8 325 }

dataValue8_326 OBJECT-TYPE
SYNTAX INTEGER
MAX-ACCESS read-write
STATUS current
DESCRIPTION
"Data value."
::= { dataArray8 326 }

dataValue8_327 OBJECT-TYPE
SYNTAX INTEGER
MAX-ACCESS read-write
STATUS current
DESCRIPTION
"Data value."
::= { dataArray8 327 }

dataValue8_328 OBJECT-TYPE
SYNTAX INTEGER
MAX-ACCESS read-write
STATUS current
DESCRIPTION
"Data value."
::= { dataArray8 328 }

dataValue8_329 OBJECT-TYPE
SYNTAX INTEGER
MAX-ACCESS read-write
STATUS current
DESCRIPTION
"Data value."
::= { dataArray8 329 }

dataValue8_330 OBJECT-TYPE
SYNTAX INTEGER
MAX-ACCESS read-write
STATUS current
DESCRIPTION
"Data value."
::= { dataArray8 330 }

dataValue8_331 OBJECT-TYPE
SYNTAX INTEGER
MAX-ACCESS read-write
STATUS current
DESCRIPTION
"Data value."
::= { dataArray8 331 }

dataValue8_332 OBJECT-TYPE
SYNTAX INTEGER
MAX-ACCESS read-write
STATUS current
DESCRIPTION
"Data value."
::= { dataArray8 332 }

dataValue8_333 OBJECT-TYPE
SYNTAX INTEGER
MAX-ACCESS read-write
STATUS current
DESCRIPTION
"Data value."
::= { dataArray8 333 }

dataValue8_334 OBJECT-TYPE
SYNTAX INTEGER
MAX-ACCESS read-write
STATUS current
DESCRIPTION
"Data value."
::= { dataArray8 334 }

dataValue8_335 OBJECT-TYPE
SYNTAX INTEGER
MAX-ACCESS read-write
STATUS current
DESCRIPTION
"Data value."
::= { dataArray8 335 }

dataValue8_336 OBJECT-TYPE
SYNTAX INTEGER
MAX-ACCESS read-write
STATUS current
DESCRIPTION
"Data value."
::= { dataArray8 336 }

dataValue8_337 OBJECT-TYPE
SYNTAX INTEGER
MAX-ACCESS read-write
STATUS current
DESCRIPTION
"Data value."
::= { dataArray8 337 }

dataValue8_338 OBJECT-TYPE
SYNTAX INTEGER
MAX-ACCESS read-write
STATUS current
DESCRIPTION
"Data value."
::= { dataArray8 338 }

dataValue8_339 OBJECT-TYPE
SYNTAX INTEGER
MAX-ACCESS read-write
STATUS current
DESCRIPTION
"Data value."
::= { dataArray8 339 }

dataValue8_340 OBJECT-TYPE
SYNTAX INTEGER
MAX-ACCESS read-write
STATUS current
DESCRIPTION
"Data value."
::= { dataArray8 340 }

dataValue8_341 OBJECT-TYPE
SYNTAX INTEGER
MAX-ACCESS read-write
STATUS current
DESCRIPTION
"Data value."
::= { dataArray8 341 }

dataValue8_342 OBJECT-TYPE
SYNTAX INTEGER
MAX-ACCESS read-write
STATUS current
DESCRIPTION
"Data value."
::= { dataArray8 342 }

dataValue8_343 OBJECT-TYPE
SYNTAX INTEGER
MAX-ACCESS read-write
STATUS current
DESCRIPTION
"Data value."
::= { dataArray8 343 }

dataValue8_344 OBJECT-TYPE
SYNTAX INTEGER
MAX-ACCESS read-write
STATUS current
DESCRIPTION
"Data value."
::= { dataArray8 344 }

dataValue8_345 OBJECT-TYPE
SYNTAX INTEGER
MAX-ACCESS read-write
STATUS current
DESCRIPTION
"Data value."
::= { dataArray8 345 }

dataValue8_346 OBJECT-TYPE
SYNTAX INTEGER
MAX-ACCESS read-write
STATUS current
DESCRIPTION
"Data value."
::= { dataArray8 346 }

dataValue8_347 OBJECT-TYPE
SYNTAX INTEGER
MAX-ACCESS read-write
STATUS current
DESCRIPTION
"Data value."
::= { dataArray8 347 }

dataValue8_348 OBJECT-TYPE
SYNTAX INTEGER
MAX-ACCESS read-write
STATUS current
DESCRIPTION
"Data value."
::= { dataArray8 348 }

dataValue8_349 OBJECT-TYPE
SYNTAX INTEGER
MAX-ACCESS read-write
STATUS current
DESCRIPTION
"Data value."
::= { dataArray8 349 }

dataValue8_350 OBJECT-TYPE
SYNTAX INTEGER
MAX-ACCESS read-write
STATUS current
DESCRIPTION
"Data value."
::= { dataArray8 350 }

dataValue8_351 OBJECT-TYPE
SYNTAX INTEGER
MAX-ACCESS read-write
STATUS current
DESCRIPTION
"Data value."
::= { dataArray8 351 }

dataValue8_352 OBJECT-TYPE
SYNTAX INTEGER
MAX-ACCESS read-write
STATUS current
DESCRIPTION
"Data value."
::= { dataArray8 352 }

dataValue8_353 OBJECT-TYPE
SYNTAX INTEGER
MAX-ACCESS read-write
STATUS current
DESCRIPTION
"Data value."
::= { dataArray8 353 }

dataValue8_354 OBJECT-TYPE
SYNTAX INTEGER
MAX-ACCESS read-write
STATUS current
DESCRIPTION
"Data value."
::= { dataArray8 354 }

dataValue8_355 OBJECT-TYPE
SYNTAX INTEGER
MAX-ACCESS read-write
STATUS current
DESCRIPTION
"Data value."
::= { dataArray8 355 }

dataValue8_356 OBJECT-TYPE
SYNTAX INTEGER
MAX-ACCESS read-write
STATUS current
DESCRIPTION
"Data value."
::= { dataArray8 356 }

dataValue8_357 OBJECT-TYPE
SYNTAX INTEGER
MAX-ACCESS read-write
STATUS current
DESCRIPTION
"Data value."
::= { dataArray8 357 }

dataValue8_358 OBJECT-TYPE
SYNTAX INTEGER
MAX-ACCESS read-write
STATUS current
DESCRIPTION
"Data value."
::= { dataArray8 358 }

dataValue8_359 OBJECT-TYPE
SYNTAX INTEGER
MAX-ACCESS read-write
STATUS current
DESCRIPTION
"Data value."
::= { dataArray8 359 }

dataValue8_360 OBJECT-TYPE
SYNTAX INTEGER
MAX-ACCESS read-write
STATUS current
DESCRIPTION
"Data value."
::= { dataArray8 360 }

dataValue8_361 OBJECT-TYPE
SYNTAX INTEGER
MAX-ACCESS read-write
STATUS current
DESCRIPTION
"Data value."
::= { dataArray8 361 }

dataValue8_362 OBJECT-TYPE
SYNTAX INTEGER
MAX-ACCESS read-write
STATUS current
DESCRIPTION
"Data value."
::= { dataArray8 362 }

dataValue8_363 OBJECT-TYPE
SYNTAX INTEGER
MAX-ACCESS read-write
STATUS current
DESCRIPTION
"Data value."
::= { dataArray8 363 }

dataValue8_364 OBJECT-TYPE
SYNTAX INTEGER
MAX-ACCESS read-write
STATUS current
DESCRIPTION
"Data value."
::= { dataArray8 364 }

dataValue8_365 OBJECT-TYPE
SYNTAX INTEGER
MAX-ACCESS read-write
STATUS current
DESCRIPTION
"Data value."
::= { dataArray8 365 }

dataValue8_366 OBJECT-TYPE
SYNTAX INTEGER
MAX-ACCESS read-write
STATUS current
DESCRIPTION
"Data value."
::= { dataArray8 366 }

dataValue8_367 OBJECT-TYPE
SYNTAX INTEGER
MAX-ACCESS read-write
STATUS current
DESCRIPTION
"Data value."
::= { dataArray8 367 }

dataValue8_368 OBJECT-TYPE
SYNTAX INTEGER
MAX-ACCESS read-write
STATUS current
DESCRIPTION
"Data value."
::= { dataArray8 368 }

dataValue8_369 OBJECT-TYPE
SYNTAX INTEGER
MAX-ACCESS read-write
STATUS current
DESCRIPTION
"Data value."
::= { dataArray8 369 }

dataValue8_370 OBJECT-TYPE
SYNTAX INTEGER
MAX-ACCESS read-write
STATUS current
DESCRIPTION
"Data value."
::= { dataArray8 370 }

dataValue8_371 OBJECT-TYPE
SYNTAX INTEGER
MAX-ACCESS read-write
STATUS current
DESCRIPTION
"Data value."
::= { dataArray8 371 }

dataValue8_372 OBJECT-TYPE
SYNTAX INTEGER
MAX-ACCESS read-write
STATUS current
DESCRIPTION
"Data value."
::= { dataArray8 372 }

dataValue8_373 OBJECT-TYPE
SYNTAX INTEGER
MAX-ACCESS read-write
STATUS current
DESCRIPTION
"Data value."
::= { dataArray8 373 }

dataValue8_374 OBJECT-TYPE
SYNTAX INTEGER
MAX-ACCESS read-write
STATUS current
DESCRIPTION
"Data value."
::= { dataArray8 374 }

dataValue8_375 OBJECT-TYPE
SYNTAX INTEGER
MAX-ACCESS read-write
STATUS current
DESCRIPTION
"Data value."
::= { dataArray8 375 }

dataValue8_376 OBJECT-TYPE
SYNTAX INTEGER
MAX-ACCESS read-write
STATUS current
DESCRIPTION
"Data value."
::= { dataArray8 376 }

dataValue8_377 OBJECT-TYPE
SYNTAX INTEGER
MAX-ACCESS read-write
STATUS current
DESCRIPTION
"Data value."
::= { dataArray8 377 }

dataValue8_378 OBJECT-TYPE
SYNTAX INTEGER
MAX-ACCESS read-write
STATUS current
DESCRIPTION
"Data value."
::= { dataArray8 378 }

dataValue8_379 OBJECT-TYPE
SYNTAX INTEGER
MAX-ACCESS read-write
STATUS current
DESCRIPTION
"Data value."
::= { dataArray8 379 }

dataValue8_380 OBJECT-TYPE
SYNTAX INTEGER
MAX-ACCESS read-write
STATUS current
DESCRIPTION
"Data value."
::= { dataArray8 380 }

dataValue8_381 OBJECT-TYPE
SYNTAX INTEGER
MAX-ACCESS read-write
STATUS current
DESCRIPTION
"Data value."
::= { dataArray8 381 }

dataValue8_382 OBJECT-TYPE
SYNTAX INTEGER
MAX-ACCESS read-write
STATUS current
DESCRIPTION
"Data value."
::= { dataArray8 382 }

dataValue8_383 OBJECT-TYPE
SYNTAX INTEGER
MAX-ACCESS read-write
STATUS current
DESCRIPTION
"Data value."
::= { dataArray8 383 }

dataValue8_384 OBJECT-TYPE
SYNTAX INTEGER
MAX-ACCESS read-write
STATUS current
DESCRIPTION
"Data value."
::= { dataArray8 384 }

dataValue8_385 OBJECT-TYPE
SYNTAX INTEGER
MAX-ACCESS read-write
STATUS current
DESCRIPTION
"Data value."
::= { dataArray8 385 }

dataValue8_386 OBJECT-TYPE
SYNTAX INTEGER
MAX-ACCESS read-write
STATUS current
DESCRIPTION
"Data value."
::= { dataArray8 386 }

dataValue8_387 OBJECT-TYPE
SYNTAX INTEGER
MAX-ACCESS read-write
STATUS current
DESCRIPTION
"Data value."
::= { dataArray8 387 }

dataValue8_388 OBJECT-TYPE
SYNTAX INTEGER
MAX-ACCESS read-write
STATUS current
DESCRIPTION
"Data value."
::= { dataArray8 388 }

dataValue8_389 OBJECT-TYPE
SYNTAX INTEGER
MAX-ACCESS read-write
STATUS current
DESCRIPTION
"Data value."
::= { dataArray8 389 }

dataValue8_390 OBJECT-TYPE
SYNTAX INTEGER
MAX-ACCESS read-write
STATUS current
DESCRIPTION
"Data value."
::= { dataArray8 390 }

dataValue8_391 OBJECT-TYPE
SYNTAX INTEGER
MAX-ACCESS read-write
STATUS current
DESCRIPTION
"Data value."
::= { dataArray8 391 }

dataValue8_392 OBJECT-TYPE
SYNTAX INTEGER
MAX-ACCESS read-write
STATUS current
DESCRIPTION
"Data value."
::= { dataArray8 392 }

dataValue8_393 OBJECT-TYPE
SYNTAX INTEGER
MAX-ACCESS read-write
STATUS current
DESCRIPTION
"Data value."
::= { dataArray8 393 }

dataValue8_394 OBJECT-TYPE
SYNTAX INTEGER
MAX-ACCESS read-write
STATUS current
DESCRIPTION
"Data value."
::= { dataArray8 394 }

dataValue8_395 OBJECT-TYPE
SYNTAX INTEGER
MAX-ACCESS read-write
STATUS current
DESCRIPTION
"Data value."
::= { dataArray8 395 }

dataValue8_396 OBJECT-TYPE
SYNTAX INTEGER
MAX-ACCESS read-write
STATUS current
DESCRIPTION
"Data value."
::= { dataArray8 396 }

dataValue8_397 OBJECT-TYPE
SYNTAX INTEGER
MAX-ACCESS read-write
STATUS current
DESCRIPTION
"Data value."
::= { dataArray8 397 }

dataValue8_398 OBJECT-TYPE
SYNTAX INTEGER
MAX-ACCESS read-write
STATUS current
DESCRIPTION
"Data value."
::= { dataArray8 398 }

dataValue8_399 OBJECT-TYPE
SYNTAX INTEGER
MAX-ACCESS read-write
STATUS current
DESCRIPTION
"Data value."
::= { dataArray8 399 }

dataArray9 OBJECT IDENTIFIER ::= { cc08255400_v1_00a 9 }

dataValue9_0 OBJECT-TYPE
SYNTAX INTEGER
MAX-ACCESS read-write
STATUS current
DESCRIPTION
"Data value."
::= { dataArray9 0 }

dataValue9_1 OBJECT-TYPE
SYNTAX INTEGER
MAX-ACCESS read-write
STATUS current
DESCRIPTION
"Data value."
::= { dataArray9 1 }

dataValue9_2 OBJECT-TYPE
SYNTAX INTEGER
MAX-ACCESS read-write
STATUS current
DESCRIPTION
"Data value."
::= { dataArray9 2 }

dataValue9_3 OBJECT-TYPE
SYNTAX INTEGER
MAX-ACCESS read-write
STATUS current
DESCRIPTION
"Data value."
::= { dataArray9 3 }

dataValue9_4 OBJECT-TYPE
SYNTAX INTEGER
MAX-ACCESS read-write
STATUS current
DESCRIPTION
"Data value."
::= { dataArray9 4 }

dataValue9_5 OBJECT-TYPE
SYNTAX INTEGER
MAX-ACCESS read-write
STATUS current
DESCRIPTION
"Data value."
::= { dataArray9 5 }

dataValue9_6 OBJECT-TYPE
SYNTAX INTEGER
MAX-ACCESS read-write
STATUS current
DESCRIPTION
"Data value."
::= { dataArray9 6 }

dataValue9_7 OBJECT-TYPE
SYNTAX INTEGER
MAX-ACCESS read-write
STATUS current
DESCRIPTION
"Data value."
::= { dataArray9 7 }

dataValue9_8 OBJECT-TYPE
SYNTAX INTEGER
MAX-ACCESS read-write
STATUS current
DESCRIPTION
"Data value."
::= { dataArray9 8 }

dataValue9_9 OBJECT-TYPE
SYNTAX INTEGER
MAX-ACCESS read-write
STATUS current
DESCRIPTION
"Data value."
::= { dataArray9 9 }

dataValue9_10 OBJECT-TYPE
SYNTAX INTEGER
MAX-ACCESS read-write
STATUS current
DESCRIPTION
"Data value."
::= { dataArray9 10 }

dataValue9_11 OBJECT-TYPE
SYNTAX INTEGER
MAX-ACCESS read-write
STATUS current
DESCRIPTION
"Data value."
::= { dataArray9 11 }

dataValue9_12 OBJECT-TYPE
SYNTAX INTEGER
MAX-ACCESS read-write
STATUS current
DESCRIPTION
"Data value."
::= { dataArray9 12 }

dataValue9_13 OBJECT-TYPE
SYNTAX INTEGER
MAX-ACCESS read-write
STATUS current
DESCRIPTION
"Data value."
::= { dataArray9 13 }

dataValue9_14 OBJECT-TYPE
SYNTAX INTEGER
MAX-ACCESS read-write
STATUS current
DESCRIPTION
"Data value."
::= { dataArray9 14 }

dataValue9_15 OBJECT-TYPE
SYNTAX INTEGER
MAX-ACCESS read-write
STATUS current
DESCRIPTION
"Data value."
::= { dataArray9 15 }

dataValue9_16 OBJECT-TYPE
SYNTAX INTEGER
MAX-ACCESS read-write
STATUS current
DESCRIPTION
"Data value."
::= { dataArray9 16 }

dataValue9_17 OBJECT-TYPE
SYNTAX INTEGER
MAX-ACCESS read-write
STATUS current
DESCRIPTION
"Data value."
::= { dataArray9 17 }

dataValue9_18 OBJECT-TYPE
SYNTAX INTEGER
MAX-ACCESS read-write
STATUS current
DESCRIPTION
"Data value."
::= { dataArray9 18 }

dataValue9_19 OBJECT-TYPE
SYNTAX INTEGER
MAX-ACCESS read-write
STATUS current
DESCRIPTION
"Data value."
::= { dataArray9 19 }

dataValue9_20 OBJECT-TYPE
SYNTAX INTEGER
MAX-ACCESS read-write
STATUS current
DESCRIPTION
"Data value."
::= { dataArray9 20 }

dataValue9_21 OBJECT-TYPE
SYNTAX INTEGER
MAX-ACCESS read-write
STATUS current
DESCRIPTION
"Data value."
::= { dataArray9 21 }

dataValue9_22 OBJECT-TYPE
SYNTAX INTEGER
MAX-ACCESS read-write
STATUS current
DESCRIPTION
"Data value."
::= { dataArray9 22 }

dataValue9_23 OBJECT-TYPE
SYNTAX INTEGER
MAX-ACCESS read-write
STATUS current
DESCRIPTION
"Data value."
::= { dataArray9 23 }

dataValue9_24 OBJECT-TYPE
SYNTAX INTEGER
MAX-ACCESS read-write
STATUS current
DESCRIPTION
"Data value."
::= { dataArray9 24 }

dataValue9_25 OBJECT-TYPE
SYNTAX INTEGER
MAX-ACCESS read-write
STATUS current
DESCRIPTION
"Data value."
::= { dataArray9 25 }

dataValue9_26 OBJECT-TYPE
SYNTAX INTEGER
MAX-ACCESS read-write
STATUS current
DESCRIPTION
"Data value."
::= { dataArray9 26 }

dataValue9_27 OBJECT-TYPE
SYNTAX INTEGER
MAX-ACCESS read-write
STATUS current
DESCRIPTION
"Data value."
::= { dataArray9 27 }

dataValue9_28 OBJECT-TYPE
SYNTAX INTEGER
MAX-ACCESS read-write
STATUS current
DESCRIPTION
"Data value."
::= { dataArray9 28 }

dataValue9_29 OBJECT-TYPE
SYNTAX INTEGER
MAX-ACCESS read-write
STATUS current
DESCRIPTION
"Data value."
::= { dataArray9 29 }

dataValue9_30 OBJECT-TYPE
SYNTAX INTEGER
MAX-ACCESS read-write
STATUS current
DESCRIPTION
"Data value."
::= { dataArray9 30 }

dataValue9_31 OBJECT-TYPE
SYNTAX INTEGER
MAX-ACCESS read-write
STATUS current
DESCRIPTION
"Data value."
::= { dataArray9 31 }

dataValue9_32 OBJECT-TYPE
SYNTAX INTEGER
MAX-ACCESS read-write
STATUS current
DESCRIPTION
"Data value."
::= { dataArray9 32 }

dataValue9_33 OBJECT-TYPE
SYNTAX INTEGER
MAX-ACCESS read-write
STATUS current
DESCRIPTION
"Data value."
::= { dataArray9 33 }

dataValue9_34 OBJECT-TYPE
SYNTAX INTEGER
MAX-ACCESS read-write
STATUS current
DESCRIPTION
"Data value."
::= { dataArray9 34 }

dataValue9_35 OBJECT-TYPE
SYNTAX INTEGER
MAX-ACCESS read-write
STATUS current
DESCRIPTION
"Data value."
::= { dataArray9 35 }

dataValue9_36 OBJECT-TYPE
SYNTAX INTEGER
MAX-ACCESS read-write
STATUS current
DESCRIPTION
"Data value."
::= { dataArray9 36 }

dataValue9_37 OBJECT-TYPE
SYNTAX INTEGER
MAX-ACCESS read-write
STATUS current
DESCRIPTION
"Data value."
::= { dataArray9 37 }

dataValue9_38 OBJECT-TYPE
SYNTAX INTEGER
MAX-ACCESS read-write
STATUS current
DESCRIPTION
"Data value."
::= { dataArray9 38 }

dataValue9_39 OBJECT-TYPE
SYNTAX INTEGER
MAX-ACCESS read-write
STATUS current
DESCRIPTION
"Data value."
::= { dataArray9 39 }

dataValue9_40 OBJECT-TYPE
SYNTAX INTEGER
MAX-ACCESS read-write
STATUS current
DESCRIPTION
"Data value."
::= { dataArray9 40 }

dataValue9_41 OBJECT-TYPE
SYNTAX INTEGER
MAX-ACCESS read-write
STATUS current
DESCRIPTION
"Data value."
::= { dataArray9 41 }

dataValue9_42 OBJECT-TYPE
SYNTAX INTEGER
MAX-ACCESS read-write
STATUS current
DESCRIPTION
"Data value."
::= { dataArray9 42 }

dataValue9_43 OBJECT-TYPE
SYNTAX INTEGER
MAX-ACCESS read-write
STATUS current
DESCRIPTION
"Data value."
::= { dataArray9 43 }

dataValue9_44 OBJECT-TYPE
SYNTAX INTEGER
MAX-ACCESS read-write
STATUS current
DESCRIPTION
"Data value."
::= { dataArray9 44 }

dataValue9_45 OBJECT-TYPE
SYNTAX INTEGER
MAX-ACCESS read-write
STATUS current
DESCRIPTION
"Data value."
::= { dataArray9 45 }

dataValue9_46 OBJECT-TYPE
SYNTAX INTEGER
MAX-ACCESS read-write
STATUS current
DESCRIPTION
"Data value."
::= { dataArray9 46 }

dataValue9_47 OBJECT-TYPE
SYNTAX INTEGER
MAX-ACCESS read-write
STATUS current
DESCRIPTION
"Data value."
::= { dataArray9 47 }

dataValue9_48 OBJECT-TYPE
SYNTAX INTEGER
MAX-ACCESS read-write
STATUS current
DESCRIPTION
"Data value."
::= { dataArray9 48 }

dataValue9_49 OBJECT-TYPE
SYNTAX INTEGER
MAX-ACCESS read-write
STATUS current
DESCRIPTION
"Data value."
::= { dataArray9 49 }

dataValue9_50 OBJECT-TYPE
SYNTAX INTEGER
MAX-ACCESS read-write
STATUS current
DESCRIPTION
"Data value."
::= { dataArray9 50 }

dataValue9_51 OBJECT-TYPE
SYNTAX INTEGER
MAX-ACCESS read-write
STATUS current
DESCRIPTION
"Data value."
::= { dataArray9 51 }

dataValue9_52 OBJECT-TYPE
SYNTAX INTEGER
MAX-ACCESS read-write
STATUS current
DESCRIPTION
"Data value."
::= { dataArray9 52 }

dataValue9_53 OBJECT-TYPE
SYNTAX INTEGER
MAX-ACCESS read-write
STATUS current
DESCRIPTION
"Data value."
::= { dataArray9 53 }

dataValue9_54 OBJECT-TYPE
SYNTAX INTEGER
MAX-ACCESS read-write
STATUS current
DESCRIPTION
"Data value."
::= { dataArray9 54 }

dataValue9_55 OBJECT-TYPE
SYNTAX INTEGER
MAX-ACCESS read-write
STATUS current
DESCRIPTION
"Data value."
::= { dataArray9 55 }

dataValue9_56 OBJECT-TYPE
SYNTAX INTEGER
MAX-ACCESS read-write
STATUS current
DESCRIPTION
"Data value."
::= { dataArray9 56 }

dataValue9_57 OBJECT-TYPE
SYNTAX INTEGER
MAX-ACCESS read-write
STATUS current
DESCRIPTION
"Data value."
::= { dataArray9 57 }

dataValue9_58 OBJECT-TYPE
SYNTAX INTEGER
MAX-ACCESS read-write
STATUS current
DESCRIPTION
"Data value."
::= { dataArray9 58 }

dataValue9_59 OBJECT-TYPE
SYNTAX INTEGER
MAX-ACCESS read-write
STATUS current
DESCRIPTION
"Data value."
::= { dataArray9 59 }

dataValue9_60 OBJECT-TYPE
SYNTAX INTEGER
MAX-ACCESS read-write
STATUS current
DESCRIPTION
"Data value."
::= { dataArray9 60 }

dataValue9_61 OBJECT-TYPE
SYNTAX INTEGER
MAX-ACCESS read-write
STATUS current
DESCRIPTION
"Data value."
::= { dataArray9 61 }

dataValue9_62 OBJECT-TYPE
SYNTAX INTEGER
MAX-ACCESS read-write
STATUS current
DESCRIPTION
"Data value."
::= { dataArray9 62 }

dataValue9_63 OBJECT-TYPE
SYNTAX INTEGER
MAX-ACCESS read-write
STATUS current
DESCRIPTION
"Data value."
::= { dataArray9 63 }

dataValue9_64 OBJECT-TYPE
SYNTAX INTEGER
MAX-ACCESS read-write
STATUS current
DESCRIPTION
"Data value."
::= { dataArray9 64 }

dataValue9_65 OBJECT-TYPE
SYNTAX INTEGER
MAX-ACCESS read-write
STATUS current
DESCRIPTION
"Data value."
::= { dataArray9 65 }

dataValue9_66 OBJECT-TYPE
SYNTAX INTEGER
MAX-ACCESS read-write
STATUS current
DESCRIPTION
"Data value."
::= { dataArray9 66 }

dataValue9_67 OBJECT-TYPE
SYNTAX INTEGER
MAX-ACCESS read-write
STATUS current
DESCRIPTION
"Data value."
::= { dataArray9 67 }

dataValue9_68 OBJECT-TYPE
SYNTAX INTEGER
MAX-ACCESS read-write
STATUS current
DESCRIPTION
"Data value."
::= { dataArray9 68 }

dataValue9_69 OBJECT-TYPE
SYNTAX INTEGER
MAX-ACCESS read-write
STATUS current
DESCRIPTION
"Data value."
::= { dataArray9 69 }

dataValue9_70 OBJECT-TYPE
SYNTAX INTEGER
MAX-ACCESS read-write
STATUS current
DESCRIPTION
"Data value."
::= { dataArray9 70 }

dataValue9_71 OBJECT-TYPE
SYNTAX INTEGER
MAX-ACCESS read-write
STATUS current
DESCRIPTION
"Data value."
::= { dataArray9 71 }

dataValue9_72 OBJECT-TYPE
SYNTAX INTEGER
MAX-ACCESS read-write
STATUS current
DESCRIPTION
"Data value."
::= { dataArray9 72 }

dataValue9_73 OBJECT-TYPE
SYNTAX INTEGER
MAX-ACCESS read-write
STATUS current
DESCRIPTION
"Data value."
::= { dataArray9 73 }

dataValue9_74 OBJECT-TYPE
SYNTAX INTEGER
MAX-ACCESS read-write
STATUS current
DESCRIPTION
"Data value."
::= { dataArray9 74 }

dataValue9_75 OBJECT-TYPE
SYNTAX INTEGER
MAX-ACCESS read-write
STATUS current
DESCRIPTION
"Data value."
::= { dataArray9 75 }

dataValue9_76 OBJECT-TYPE
SYNTAX INTEGER
MAX-ACCESS read-write
STATUS current
DESCRIPTION
"Data value."
::= { dataArray9 76 }

dataValue9_77 OBJECT-TYPE
SYNTAX INTEGER
MAX-ACCESS read-write
STATUS current
DESCRIPTION
"Data value."
::= { dataArray9 77 }

dataValue9_78 OBJECT-TYPE
SYNTAX INTEGER
MAX-ACCESS read-write
STATUS current
DESCRIPTION
"Data value."
::= { dataArray9 78 }

dataValue9_79 OBJECT-TYPE
SYNTAX INTEGER
MAX-ACCESS read-write
STATUS current
DESCRIPTION
"Data value."
::= { dataArray9 79 }

dataValue9_80 OBJECT-TYPE
SYNTAX INTEGER
MAX-ACCESS read-write
STATUS current
DESCRIPTION
"Data value."
::= { dataArray9 80 }

dataValue9_81 OBJECT-TYPE
SYNTAX INTEGER
MAX-ACCESS read-write
STATUS current
DESCRIPTION
"Data value."
::= { dataArray9 81 }

dataValue9_82 OBJECT-TYPE
SYNTAX INTEGER
MAX-ACCESS read-write
STATUS current
DESCRIPTION
"Data value."
::= { dataArray9 82 }

dataValue9_83 OBJECT-TYPE
SYNTAX INTEGER
MAX-ACCESS read-write
STATUS current
DESCRIPTION
"Data value."
::= { dataArray9 83 }

dataValue9_84 OBJECT-TYPE
SYNTAX INTEGER
MAX-ACCESS read-write
STATUS current
DESCRIPTION
"Data value."
::= { dataArray9 84 }

dataValue9_85 OBJECT-TYPE
SYNTAX INTEGER
MAX-ACCESS read-write
STATUS current
DESCRIPTION
"Data value."
::= { dataArray9 85 }

dataValue9_86 OBJECT-TYPE
SYNTAX INTEGER
MAX-ACCESS read-write
STATUS current
DESCRIPTION
"Data value."
::= { dataArray9 86 }

dataValue9_87 OBJECT-TYPE
SYNTAX INTEGER
MAX-ACCESS read-write
STATUS current
DESCRIPTION
"Data value."
::= { dataArray9 87 }

dataValue9_88 OBJECT-TYPE
SYNTAX INTEGER
MAX-ACCESS read-write
STATUS current
DESCRIPTION
"Data value."
::= { dataArray9 88 }

dataValue9_89 OBJECT-TYPE
SYNTAX INTEGER
MAX-ACCESS read-write
STATUS current
DESCRIPTION
"Data value."
::= { dataArray9 89 }

dataValue9_90 OBJECT-TYPE
SYNTAX INTEGER
MAX-ACCESS read-write
STATUS current
DESCRIPTION
"Data value."
::= { dataArray9 90 }

dataValue9_91 OBJECT-TYPE
SYNTAX INTEGER
MAX-ACCESS read-write
STATUS current
DESCRIPTION
"Data value."
::= { dataArray9 91 }

dataValue9_92 OBJECT-TYPE
SYNTAX INTEGER
MAX-ACCESS read-write
STATUS current
DESCRIPTION
"Data value."
::= { dataArray9 92 }

dataValue9_93 OBJECT-TYPE
SYNTAX INTEGER
MAX-ACCESS read-write
STATUS current
DESCRIPTION
"Data value."
::= { dataArray9 93 }

dataValue9_94 OBJECT-TYPE
SYNTAX INTEGER
MAX-ACCESS read-write
STATUS current
DESCRIPTION
"Data value."
::= { dataArray9 94 }

dataValue9_95 OBJECT-TYPE
SYNTAX INTEGER
MAX-ACCESS read-write
STATUS current
DESCRIPTION
"Data value."
::= { dataArray9 95 }

dataValue9_96 OBJECT-TYPE
SYNTAX INTEGER
MAX-ACCESS read-write
STATUS current
DESCRIPTION
"Data value."
::= { dataArray9 96 }

dataValue9_97 OBJECT-TYPE
SYNTAX INTEGER
MAX-ACCESS read-write
STATUS current
DESCRIPTION
"Data value."
::= { dataArray9 97 }

dataValue9_98 OBJECT-TYPE
SYNTAX INTEGER
MAX-ACCESS read-write
STATUS current
DESCRIPTION
"Data value."
::= { dataArray9 98 }

dataValue9_99 OBJECT-TYPE
SYNTAX INTEGER
MAX-ACCESS read-write
STATUS current
DESCRIPTION
"Data value."
::= { dataArray9 99 }

dataValue9_100 OBJECT-TYPE
SYNTAX INTEGER
MAX-ACCESS read-write
STATUS current
DESCRIPTION
"Data value."
::= { dataArray9 100 }

dataValue9_101 OBJECT-TYPE
SYNTAX INTEGER
MAX-ACCESS read-write
STATUS current
DESCRIPTION
"Data value."
::= { dataArray9 101 }

dataValue9_102 OBJECT-TYPE
SYNTAX INTEGER
MAX-ACCESS read-write
STATUS current
DESCRIPTION
"Data value."
::= { dataArray9 102 }

dataValue9_103 OBJECT-TYPE
SYNTAX INTEGER
MAX-ACCESS read-write
STATUS current
DESCRIPTION
"Data value."
::= { dataArray9 103 }

dataValue9_104 OBJECT-TYPE
SYNTAX INTEGER
MAX-ACCESS read-write
STATUS current
DESCRIPTION
"Data value."
::= { dataArray9 104 }

dataValue9_105 OBJECT-TYPE
SYNTAX INTEGER
MAX-ACCESS read-write
STATUS current
DESCRIPTION
"Data value."
::= { dataArray9 105 }

dataValue9_106 OBJECT-TYPE
SYNTAX INTEGER
MAX-ACCESS read-write
STATUS current
DESCRIPTION
"Data value."
::= { dataArray9 106 }

dataValue9_107 OBJECT-TYPE
SYNTAX INTEGER
MAX-ACCESS read-write
STATUS current
DESCRIPTION
"Data value."
::= { dataArray9 107 }

dataValue9_108 OBJECT-TYPE
SYNTAX INTEGER
MAX-ACCESS read-write
STATUS current
DESCRIPTION
"Data value."
::= { dataArray9 108 }

dataValue9_109 OBJECT-TYPE
SYNTAX INTEGER
MAX-ACCESS read-write
STATUS current
DESCRIPTION
"Data value."
::= { dataArray9 109 }

dataValue9_110 OBJECT-TYPE
SYNTAX INTEGER
MAX-ACCESS read-write
STATUS current
DESCRIPTION
"Data value."
::= { dataArray9 110 }

dataValue9_111 OBJECT-TYPE
SYNTAX INTEGER
MAX-ACCESS read-write
STATUS current
DESCRIPTION
"Data value."
::= { dataArray9 111 }

dataValue9_112 OBJECT-TYPE
SYNTAX INTEGER
MAX-ACCESS read-write
STATUS current
DESCRIPTION
"Data value."
::= { dataArray9 112 }

dataValue9_113 OBJECT-TYPE
SYNTAX INTEGER
MAX-ACCESS read-write
STATUS current
DESCRIPTION
"Data value."
::= { dataArray9 113 }

dataValue9_114 OBJECT-TYPE
SYNTAX INTEGER
MAX-ACCESS read-write
STATUS current
DESCRIPTION
"Data value."
::= { dataArray9 114 }

dataValue9_115 OBJECT-TYPE
SYNTAX INTEGER
MAX-ACCESS read-write
STATUS current
DESCRIPTION
"Data value."
::= { dataArray9 115 }

dataValue9_116 OBJECT-TYPE
SYNTAX INTEGER
MAX-ACCESS read-write
STATUS current
DESCRIPTION
"Data value."
::= { dataArray9 116 }

dataValue9_117 OBJECT-TYPE
SYNTAX INTEGER
MAX-ACCESS read-write
STATUS current
DESCRIPTION
"Data value."
::= { dataArray9 117 }

dataValue9_118 OBJECT-TYPE
SYNTAX INTEGER
MAX-ACCESS read-write
STATUS current
DESCRIPTION
"Data value."
::= { dataArray9 118 }

dataValue9_119 OBJECT-TYPE
SYNTAX INTEGER
MAX-ACCESS read-write
STATUS current
DESCRIPTION
"Data value."
::= { dataArray9 119 }

dataValue9_120 OBJECT-TYPE
SYNTAX INTEGER
MAX-ACCESS read-write
STATUS current
DESCRIPTION
"Data value."
::= { dataArray9 120 }

dataValue9_121 OBJECT-TYPE
SYNTAX INTEGER
MAX-ACCESS read-write
STATUS current
DESCRIPTION
"Data value."
::= { dataArray9 121 }

dataValue9_122 OBJECT-TYPE
SYNTAX INTEGER
MAX-ACCESS read-write
STATUS current
DESCRIPTION
"Data value."
::= { dataArray9 122 }

dataValue9_123 OBJECT-TYPE
SYNTAX INTEGER
MAX-ACCESS read-write
STATUS current
DESCRIPTION
"Data value."
::= { dataArray9 123 }

dataValue9_124 OBJECT-TYPE
SYNTAX INTEGER
MAX-ACCESS read-write
STATUS current
DESCRIPTION
"Data value."
::= { dataArray9 124 }

dataValue9_125 OBJECT-TYPE
SYNTAX INTEGER
MAX-ACCESS read-write
STATUS current
DESCRIPTION
"Data value."
::= { dataArray9 125 }

dataValue9_126 OBJECT-TYPE
SYNTAX INTEGER
MAX-ACCESS read-write
STATUS current
DESCRIPTION
"Data value."
::= { dataArray9 126 }

dataValue9_127 OBJECT-TYPE
SYNTAX INTEGER
MAX-ACCESS read-write
STATUS current
DESCRIPTION
"Data value."
::= { dataArray9 127 }

dataValue9_128 OBJECT-TYPE
SYNTAX INTEGER
MAX-ACCESS read-write
STATUS current
DESCRIPTION
"Data value."
::= { dataArray9 128 }

dataValue9_129 OBJECT-TYPE
SYNTAX INTEGER
MAX-ACCESS read-write
STATUS current
DESCRIPTION
"Data value."
::= { dataArray9 129 }

dataValue9_130 OBJECT-TYPE
SYNTAX INTEGER
MAX-ACCESS read-write
STATUS current
DESCRIPTION
"Data value."
::= { dataArray9 130 }

dataValue9_131 OBJECT-TYPE
SYNTAX INTEGER
MAX-ACCESS read-write
STATUS current
DESCRIPTION
"Data value."
::= { dataArray9 131 }

dataValue9_132 OBJECT-TYPE
SYNTAX INTEGER
MAX-ACCESS read-write
STATUS current
DESCRIPTION
"Data value."
::= { dataArray9 132 }

dataValue9_133 OBJECT-TYPE
SYNTAX INTEGER
MAX-ACCESS read-write
STATUS current
DESCRIPTION
"Data value."
::= { dataArray9 133 }

dataValue9_134 OBJECT-TYPE
SYNTAX INTEGER
MAX-ACCESS read-write
STATUS current
DESCRIPTION
"Data value."
::= { dataArray9 134 }

dataValue9_135 OBJECT-TYPE
SYNTAX INTEGER
MAX-ACCESS read-write
STATUS current
DESCRIPTION
"Data value."
::= { dataArray9 135 }

dataValue9_136 OBJECT-TYPE
SYNTAX INTEGER
MAX-ACCESS read-write
STATUS current
DESCRIPTION
"Data value."
::= { dataArray9 136 }

dataValue9_137 OBJECT-TYPE
SYNTAX INTEGER
MAX-ACCESS read-write
STATUS current
DESCRIPTION
"Data value."
::= { dataArray9 137 }

dataValue9_138 OBJECT-TYPE
SYNTAX INTEGER
MAX-ACCESS read-write
STATUS current
DESCRIPTION
"Data value."
::= { dataArray9 138 }

dataValue9_139 OBJECT-TYPE
SYNTAX INTEGER
MAX-ACCESS read-write
STATUS current
DESCRIPTION
"Data value."
::= { dataArray9 139 }

dataValue9_140 OBJECT-TYPE
SYNTAX INTEGER
MAX-ACCESS read-write
STATUS current
DESCRIPTION
"Data value."
::= { dataArray9 140 }

dataValue9_141 OBJECT-TYPE
SYNTAX INTEGER
MAX-ACCESS read-write
STATUS current
DESCRIPTION
"Data value."
::= { dataArray9 141 }

dataValue9_142 OBJECT-TYPE
SYNTAX INTEGER
MAX-ACCESS read-write
STATUS current
DESCRIPTION
"Data value."
::= { dataArray9 142 }

dataValue9_143 OBJECT-TYPE
SYNTAX INTEGER
MAX-ACCESS read-write
STATUS current
DESCRIPTION
"Data value."
::= { dataArray9 143 }

dataValue9_144 OBJECT-TYPE
SYNTAX INTEGER
MAX-ACCESS read-write
STATUS current
DESCRIPTION
"Data value."
::= { dataArray9 144 }

dataValue9_145 OBJECT-TYPE
SYNTAX INTEGER
MAX-ACCESS read-write
STATUS current
DESCRIPTION
"Data value."
::= { dataArray9 145 }

dataValue9_146 OBJECT-TYPE
SYNTAX INTEGER
MAX-ACCESS read-write
STATUS current
DESCRIPTION
"Data value."
::= { dataArray9 146 }

dataValue9_147 OBJECT-TYPE
SYNTAX INTEGER
MAX-ACCESS read-write
STATUS current
DESCRIPTION
"Data value."
::= { dataArray9 147 }

dataValue9_148 OBJECT-TYPE
SYNTAX INTEGER
MAX-ACCESS read-write
STATUS current
DESCRIPTION
"Data value."
::= { dataArray9 148 }

dataValue9_149 OBJECT-TYPE
SYNTAX INTEGER
MAX-ACCESS read-write
STATUS current
DESCRIPTION
"Data value."
::= { dataArray9 149 }

dataValue9_150 OBJECT-TYPE
SYNTAX INTEGER
MAX-ACCESS read-write
STATUS current
DESCRIPTION
"Data value."
::= { dataArray9 150 }

dataValue9_151 OBJECT-TYPE
SYNTAX INTEGER
MAX-ACCESS read-write
STATUS current
DESCRIPTION
"Data value."
::= { dataArray9 151 }

dataValue9_152 OBJECT-TYPE
SYNTAX INTEGER
MAX-ACCESS read-write
STATUS current
DESCRIPTION
"Data value."
::= { dataArray9 152 }

dataValue9_153 OBJECT-TYPE
SYNTAX INTEGER
MAX-ACCESS read-write
STATUS current
DESCRIPTION
"Data value."
::= { dataArray9 153 }

dataValue9_154 OBJECT-TYPE
SYNTAX INTEGER
MAX-ACCESS read-write
STATUS current
DESCRIPTION
"Data value."
::= { dataArray9 154 }

dataValue9_155 OBJECT-TYPE
SYNTAX INTEGER
MAX-ACCESS read-write
STATUS current
DESCRIPTION
"Data value."
::= { dataArray9 155 }

dataValue9_156 OBJECT-TYPE
SYNTAX INTEGER
MAX-ACCESS read-write
STATUS current
DESCRIPTION
"Data value."
::= { dataArray9 156 }

dataValue9_157 OBJECT-TYPE
SYNTAX INTEGER
MAX-ACCESS read-write
STATUS current
DESCRIPTION
"Data value."
::= { dataArray9 157 }

dataValue9_158 OBJECT-TYPE
SYNTAX INTEGER
MAX-ACCESS read-write
STATUS current
DESCRIPTION
"Data value."
::= { dataArray9 158 }

dataValue9_159 OBJECT-TYPE
SYNTAX INTEGER
MAX-ACCESS read-write
STATUS current
DESCRIPTION
"Data value."
::= { dataArray9 159 }

dataValue9_160 OBJECT-TYPE
SYNTAX INTEGER
MAX-ACCESS read-write
STATUS current
DESCRIPTION
"Data value."
::= { dataArray9 160 }

dataValue9_161 OBJECT-TYPE
SYNTAX INTEGER
MAX-ACCESS read-write
STATUS current
DESCRIPTION
"Data value."
::= { dataArray9 161 }

dataValue9_162 OBJECT-TYPE
SYNTAX INTEGER
MAX-ACCESS read-write
STATUS current
DESCRIPTION
"Data value."
::= { dataArray9 162 }

dataValue9_163 OBJECT-TYPE
SYNTAX INTEGER
MAX-ACCESS read-write
STATUS current
DESCRIPTION
"Data value."
::= { dataArray9 163 }

dataValue9_164 OBJECT-TYPE
SYNTAX INTEGER
MAX-ACCESS read-write
STATUS current
DESCRIPTION
"Data value."
::= { dataArray9 164 }

dataValue9_165 OBJECT-TYPE
SYNTAX INTEGER
MAX-ACCESS read-write
STATUS current
DESCRIPTION
"Data value."
::= { dataArray9 165 }

dataValue9_166 OBJECT-TYPE
SYNTAX INTEGER
MAX-ACCESS read-write
STATUS current
DESCRIPTION
"Data value."
::= { dataArray9 166 }

dataValue9_167 OBJECT-TYPE
SYNTAX INTEGER
MAX-ACCESS read-write
STATUS current
DESCRIPTION
"Data value."
::= { dataArray9 167 }

dataValue9_168 OBJECT-TYPE
SYNTAX INTEGER
MAX-ACCESS read-write
STATUS current
DESCRIPTION
"Data value."
::= { dataArray9 168 }

dataValue9_169 OBJECT-TYPE
SYNTAX INTEGER
MAX-ACCESS read-write
STATUS current
DESCRIPTION
"Data value."
::= { dataArray9 169 }

dataValue9_170 OBJECT-TYPE
SYNTAX INTEGER
MAX-ACCESS read-write
STATUS current
DESCRIPTION
"Data value."
::= { dataArray9 170 }

dataValue9_171 OBJECT-TYPE
SYNTAX INTEGER
MAX-ACCESS read-write
STATUS current
DESCRIPTION
"Data value."
::= { dataArray9 171 }

dataValue9_172 OBJECT-TYPE
SYNTAX INTEGER
MAX-ACCESS read-write
STATUS current
DESCRIPTION
"Data value."
::= { dataArray9 172 }

dataValue9_173 OBJECT-TYPE
SYNTAX INTEGER
MAX-ACCESS read-write
STATUS current
DESCRIPTION
"Data value."
::= { dataArray9 173 }

dataValue9_174 OBJECT-TYPE
SYNTAX INTEGER
MAX-ACCESS read-write
STATUS current
DESCRIPTION
"Data value."
::= { dataArray9 174 }

dataValue9_175 OBJECT-TYPE
SYNTAX INTEGER
MAX-ACCESS read-write
STATUS current
DESCRIPTION
"Data value."
::= { dataArray9 175 }

dataValue9_176 OBJECT-TYPE
SYNTAX INTEGER
MAX-ACCESS read-write
STATUS current
DESCRIPTION
"Data value."
::= { dataArray9 176 }

dataValue9_177 OBJECT-TYPE
SYNTAX INTEGER
MAX-ACCESS read-write
STATUS current
DESCRIPTION
"Data value."
::= { dataArray9 177 }

dataValue9_178 OBJECT-TYPE
SYNTAX INTEGER
MAX-ACCESS read-write
STATUS current
DESCRIPTION
"Data value."
::= { dataArray9 178 }

dataValue9_179 OBJECT-TYPE
SYNTAX INTEGER
MAX-ACCESS read-write
STATUS current
DESCRIPTION
"Data value."
::= { dataArray9 179 }

dataValue9_180 OBJECT-TYPE
SYNTAX INTEGER
MAX-ACCESS read-write
STATUS current
DESCRIPTION
"Data value."
::= { dataArray9 180 }

dataValue9_181 OBJECT-TYPE
SYNTAX INTEGER
MAX-ACCESS read-write
STATUS current
DESCRIPTION
"Data value."
::= { dataArray9 181 }

dataValue9_182 OBJECT-TYPE
SYNTAX INTEGER
MAX-ACCESS read-write
STATUS current
DESCRIPTION
"Data value."
::= { dataArray9 182 }

dataValue9_183 OBJECT-TYPE
SYNTAX INTEGER
MAX-ACCESS read-write
STATUS current
DESCRIPTION
"Data value."
::= { dataArray9 183 }

dataValue9_184 OBJECT-TYPE
SYNTAX INTEGER
MAX-ACCESS read-write
STATUS current
DESCRIPTION
"Data value."
::= { dataArray9 184 }

dataValue9_185 OBJECT-TYPE
SYNTAX INTEGER
MAX-ACCESS read-write
STATUS current
DESCRIPTION
"Data value."
::= { dataArray9 185 }

dataValue9_186 OBJECT-TYPE
SYNTAX INTEGER
MAX-ACCESS read-write
STATUS current
DESCRIPTION
"Data value."
::= { dataArray9 186 }

dataValue9_187 OBJECT-TYPE
SYNTAX INTEGER
MAX-ACCESS read-write
STATUS current
DESCRIPTION
"Data value."
::= { dataArray9 187 }

dataValue9_188 OBJECT-TYPE
SYNTAX INTEGER
MAX-ACCESS read-write
STATUS current
DESCRIPTION
"Data value."
::= { dataArray9 188 }

dataValue9_189 OBJECT-TYPE
SYNTAX INTEGER
MAX-ACCESS read-write
STATUS current
DESCRIPTION
"Data value."
::= { dataArray9 189 }

dataValue9_190 OBJECT-TYPE
SYNTAX INTEGER
MAX-ACCESS read-write
STATUS current
DESCRIPTION
"Data value."
::= { dataArray9 190 }

dataValue9_191 OBJECT-TYPE
SYNTAX INTEGER
MAX-ACCESS read-write
STATUS current
DESCRIPTION
"Data value."
::= { dataArray9 191 }

dataValue9_192 OBJECT-TYPE
SYNTAX INTEGER
MAX-ACCESS read-write
STATUS current
DESCRIPTION
"Data value."
::= { dataArray9 192 }

dataValue9_193 OBJECT-TYPE
SYNTAX INTEGER
MAX-ACCESS read-write
STATUS current
DESCRIPTION
"Data value."
::= { dataArray9 193 }

dataValue9_194 OBJECT-TYPE
SYNTAX INTEGER
MAX-ACCESS read-write
STATUS current
DESCRIPTION
"Data value."
::= { dataArray9 194 }

dataValue9_195 OBJECT-TYPE
SYNTAX INTEGER
MAX-ACCESS read-write
STATUS current
DESCRIPTION
"Data value."
::= { dataArray9 195 }

dataValue9_196 OBJECT-TYPE
SYNTAX INTEGER
MAX-ACCESS read-write
STATUS current
DESCRIPTION
"Data value."
::= { dataArray9 196 }

dataValue9_197 OBJECT-TYPE
SYNTAX INTEGER
MAX-ACCESS read-write
STATUS current
DESCRIPTION
"Data value."
::= { dataArray9 197 }

dataValue9_198 OBJECT-TYPE
SYNTAX INTEGER
MAX-ACCESS read-write
STATUS current
DESCRIPTION
"Data value."
::= { dataArray9 198 }

dataValue9_199 OBJECT-TYPE
SYNTAX INTEGER
MAX-ACCESS read-write
STATUS current
DESCRIPTION
"Data value."
::= { dataArray9 199 }

dataValue9_200 OBJECT-TYPE
SYNTAX INTEGER
MAX-ACCESS read-write
STATUS current
DESCRIPTION
"Data value."
::= { dataArray9 200 }

dataValue9_201 OBJECT-TYPE
SYNTAX INTEGER
MAX-ACCESS read-write
STATUS current
DESCRIPTION
"Data value."
::= { dataArray9 201 }

dataValue9_202 OBJECT-TYPE
SYNTAX INTEGER
MAX-ACCESS read-write
STATUS current
DESCRIPTION
"Data value."
::= { dataArray9 202 }

dataValue9_203 OBJECT-TYPE
SYNTAX INTEGER
MAX-ACCESS read-write
STATUS current
DESCRIPTION
"Data value."
::= { dataArray9 203 }

dataValue9_204 OBJECT-TYPE
SYNTAX INTEGER
MAX-ACCESS read-write
STATUS current
DESCRIPTION
"Data value."
::= { dataArray9 204 }

dataValue9_205 OBJECT-TYPE
SYNTAX INTEGER
MAX-ACCESS read-write
STATUS current
DESCRIPTION
"Data value."
::= { dataArray9 205 }

dataValue9_206 OBJECT-TYPE
SYNTAX INTEGER
MAX-ACCESS read-write
STATUS current
DESCRIPTION
"Data value."
::= { dataArray9 206 }

dataValue9_207 OBJECT-TYPE
SYNTAX INTEGER
MAX-ACCESS read-write
STATUS current
DESCRIPTION
"Data value."
::= { dataArray9 207 }

dataValue9_208 OBJECT-TYPE
SYNTAX INTEGER
MAX-ACCESS read-write
STATUS current
DESCRIPTION
"Data value."
::= { dataArray9 208 }

dataValue9_209 OBJECT-TYPE
SYNTAX INTEGER
MAX-ACCESS read-write
STATUS current
DESCRIPTION
"Data value."
::= { dataArray9 209 }

dataValue9_210 OBJECT-TYPE
SYNTAX INTEGER
MAX-ACCESS read-write
STATUS current
DESCRIPTION
"Data value."
::= { dataArray9 210 }

dataValue9_211 OBJECT-TYPE
SYNTAX INTEGER
MAX-ACCESS read-write
STATUS current
DESCRIPTION
"Data value."
::= { dataArray9 211 }

dataValue9_212 OBJECT-TYPE
SYNTAX INTEGER
MAX-ACCESS read-write
STATUS current
DESCRIPTION
"Data value."
::= { dataArray9 212 }

dataValue9_213 OBJECT-TYPE
SYNTAX INTEGER
MAX-ACCESS read-write
STATUS current
DESCRIPTION
"Data value."
::= { dataArray9 213 }

dataValue9_214 OBJECT-TYPE
SYNTAX INTEGER
MAX-ACCESS read-write
STATUS current
DESCRIPTION
"Data value."
::= { dataArray9 214 }

dataValue9_215 OBJECT-TYPE
SYNTAX INTEGER
MAX-ACCESS read-write
STATUS current
DESCRIPTION
"Data value."
::= { dataArray9 215 }

dataValue9_216 OBJECT-TYPE
SYNTAX INTEGER
MAX-ACCESS read-write
STATUS current
DESCRIPTION
"Data value."
::= { dataArray9 216 }

dataValue9_217 OBJECT-TYPE
SYNTAX INTEGER
MAX-ACCESS read-write
STATUS current
DESCRIPTION
"Data value."
::= { dataArray9 217 }

dataValue9_218 OBJECT-TYPE
SYNTAX INTEGER
MAX-ACCESS read-write
STATUS current
DESCRIPTION
"Data value."
::= { dataArray9 218 }

dataValue9_219 OBJECT-TYPE
SYNTAX INTEGER
MAX-ACCESS read-write
STATUS current
DESCRIPTION
"Data value."
::= { dataArray9 219 }

dataValue9_220 OBJECT-TYPE
SYNTAX INTEGER
MAX-ACCESS read-write
STATUS current
DESCRIPTION
"Data value."
::= { dataArray9 220 }

dataValue9_221 OBJECT-TYPE
SYNTAX INTEGER
MAX-ACCESS read-write
STATUS current
DESCRIPTION
"Data value."
::= { dataArray9 221 }

dataValue9_222 OBJECT-TYPE
SYNTAX INTEGER
MAX-ACCESS read-write
STATUS current
DESCRIPTION
"Data value."
::= { dataArray9 222 }

dataValue9_223 OBJECT-TYPE
SYNTAX INTEGER
MAX-ACCESS read-write
STATUS current
DESCRIPTION
"Data value."
::= { dataArray9 223 }

dataValue9_224 OBJECT-TYPE
SYNTAX INTEGER
MAX-ACCESS read-write
STATUS current
DESCRIPTION
"Data value."
::= { dataArray9 224 }

dataValue9_225 OBJECT-TYPE
SYNTAX INTEGER
MAX-ACCESS read-write
STATUS current
DESCRIPTION
"Data value."
::= { dataArray9 225 }

dataValue9_226 OBJECT-TYPE
SYNTAX INTEGER
MAX-ACCESS read-write
STATUS current
DESCRIPTION
"Data value."
::= { dataArray9 226 }

dataValue9_227 OBJECT-TYPE
SYNTAX INTEGER
MAX-ACCESS read-write
STATUS current
DESCRIPTION
"Data value."
::= { dataArray9 227 }

dataValue9_228 OBJECT-TYPE
SYNTAX INTEGER
MAX-ACCESS read-write
STATUS current
DESCRIPTION
"Data value."
::= { dataArray9 228 }

dataValue9_229 OBJECT-TYPE
SYNTAX INTEGER
MAX-ACCESS read-write
STATUS current
DESCRIPTION
"Data value."
::= { dataArray9 229 }

dataValue9_230 OBJECT-TYPE
SYNTAX INTEGER
MAX-ACCESS read-write
STATUS current
DESCRIPTION
"Data value."
::= { dataArray9 230 }

dataValue9_231 OBJECT-TYPE
SYNTAX INTEGER
MAX-ACCESS read-write
STATUS current
DESCRIPTION
"Data value."
::= { dataArray9 231 }

dataValue9_232 OBJECT-TYPE
SYNTAX INTEGER
MAX-ACCESS read-write
STATUS current
DESCRIPTION
"Data value."
::= { dataArray9 232 }

dataValue9_233 OBJECT-TYPE
SYNTAX INTEGER
MAX-ACCESS read-write
STATUS current
DESCRIPTION
"Data value."
::= { dataArray9 233 }

dataValue9_234 OBJECT-TYPE
SYNTAX INTEGER
MAX-ACCESS read-write
STATUS current
DESCRIPTION
"Data value."
::= { dataArray9 234 }

dataValue9_235 OBJECT-TYPE
SYNTAX INTEGER
MAX-ACCESS read-write
STATUS current
DESCRIPTION
"Data value."
::= { dataArray9 235 }

dataValue9_236 OBJECT-TYPE
SYNTAX INTEGER
MAX-ACCESS read-write
STATUS current
DESCRIPTION
"Data value."
::= { dataArray9 236 }

dataValue9_237 OBJECT-TYPE
SYNTAX INTEGER
MAX-ACCESS read-write
STATUS current
DESCRIPTION
"Data value."
::= { dataArray9 237 }

dataValue9_238 OBJECT-TYPE
SYNTAX INTEGER
MAX-ACCESS read-write
STATUS current
DESCRIPTION
"Data value."
::= { dataArray9 238 }

dataValue9_239 OBJECT-TYPE
SYNTAX INTEGER
MAX-ACCESS read-write
STATUS current
DESCRIPTION
"Data value."
::= { dataArray9 239 }

dataValue9_240 OBJECT-TYPE
SYNTAX INTEGER
MAX-ACCESS read-write
STATUS current
DESCRIPTION
"Data value."
::= { dataArray9 240 }

dataValue9_241 OBJECT-TYPE
SYNTAX INTEGER
MAX-ACCESS read-write
STATUS current
DESCRIPTION
"Data value."
::= { dataArray9 241 }

dataValue9_242 OBJECT-TYPE
SYNTAX INTEGER
MAX-ACCESS read-write
STATUS current
DESCRIPTION
"Data value."
::= { dataArray9 242 }

dataValue9_243 OBJECT-TYPE
SYNTAX INTEGER
MAX-ACCESS read-write
STATUS current
DESCRIPTION
"Data value."
::= { dataArray9 243 }

dataValue9_244 OBJECT-TYPE
SYNTAX INTEGER
MAX-ACCESS read-write
STATUS current
DESCRIPTION
"Data value."
::= { dataArray9 244 }

dataValue9_245 OBJECT-TYPE
SYNTAX INTEGER
MAX-ACCESS read-write
STATUS current
DESCRIPTION
"Data value."
::= { dataArray9 245 }

dataValue9_246 OBJECT-TYPE
SYNTAX INTEGER
MAX-ACCESS read-write
STATUS current
DESCRIPTION
"Data value."
::= { dataArray9 246 }

dataValue9_247 OBJECT-TYPE
SYNTAX INTEGER
MAX-ACCESS read-write
STATUS current
DESCRIPTION
"Data value."
::= { dataArray9 247 }

dataValue9_248 OBJECT-TYPE
SYNTAX INTEGER
MAX-ACCESS read-write
STATUS current
DESCRIPTION
"Data value."
::= { dataArray9 248 }

dataValue9_249 OBJECT-TYPE
SYNTAX INTEGER
MAX-ACCESS read-write
STATUS current
DESCRIPTION
"Data value."
::= { dataArray9 249 }

dataValue9_250 OBJECT-TYPE
SYNTAX INTEGER
MAX-ACCESS read-write
STATUS current
DESCRIPTION
"Data value."
::= { dataArray9 250 }

dataValue9_251 OBJECT-TYPE
SYNTAX INTEGER
MAX-ACCESS read-write
STATUS current
DESCRIPTION
"Data value."
::= { dataArray9 251 }

dataValue9_252 OBJECT-TYPE
SYNTAX INTEGER
MAX-ACCESS read-write
STATUS current
DESCRIPTION
"Data value."
::= { dataArray9 252 }

dataValue9_253 OBJECT-TYPE
SYNTAX INTEGER
MAX-ACCESS read-write
STATUS current
DESCRIPTION
"Data value."
::= { dataArray9 253 }

dataValue9_254 OBJECT-TYPE
SYNTAX INTEGER
MAX-ACCESS read-write
STATUS current
DESCRIPTION
"Data value."
::= { dataArray9 254 }

dataValue9_255 OBJECT-TYPE
SYNTAX INTEGER
MAX-ACCESS read-write
STATUS current
DESCRIPTION
"Data value."
::= { dataArray9 255 }

dataValue9_256 OBJECT-TYPE
SYNTAX INTEGER
MAX-ACCESS read-write
STATUS current
DESCRIPTION
"Data value."
::= { dataArray9 256 }

dataValue9_257 OBJECT-TYPE
SYNTAX INTEGER
MAX-ACCESS read-write
STATUS current
DESCRIPTION
"Data value."
::= { dataArray9 257 }

dataValue9_258 OBJECT-TYPE
SYNTAX INTEGER
MAX-ACCESS read-write
STATUS current
DESCRIPTION
"Data value."
::= { dataArray9 258 }

dataValue9_259 OBJECT-TYPE
SYNTAX INTEGER
MAX-ACCESS read-write
STATUS current
DESCRIPTION
"Data value."
::= { dataArray9 259 }

dataValue9_260 OBJECT-TYPE
SYNTAX INTEGER
MAX-ACCESS read-write
STATUS current
DESCRIPTION
"Data value."
::= { dataArray9 260 }

dataValue9_261 OBJECT-TYPE
SYNTAX INTEGER
MAX-ACCESS read-write
STATUS current
DESCRIPTION
"Data value."
::= { dataArray9 261 }

dataValue9_262 OBJECT-TYPE
SYNTAX INTEGER
MAX-ACCESS read-write
STATUS current
DESCRIPTION
"Data value."
::= { dataArray9 262 }

dataValue9_263 OBJECT-TYPE
SYNTAX INTEGER
MAX-ACCESS read-write
STATUS current
DESCRIPTION
"Data value."
::= { dataArray9 263 }

dataValue9_264 OBJECT-TYPE
SYNTAX INTEGER
MAX-ACCESS read-write
STATUS current
DESCRIPTION
"Data value."
::= { dataArray9 264 }

dataValue9_265 OBJECT-TYPE
SYNTAX INTEGER
MAX-ACCESS read-write
STATUS current
DESCRIPTION
"Data value."
::= { dataArray9 265 }

dataValue9_266 OBJECT-TYPE
SYNTAX INTEGER
MAX-ACCESS read-write
STATUS current
DESCRIPTION
"Data value."
::= { dataArray9 266 }

dataValue9_267 OBJECT-TYPE
SYNTAX INTEGER
MAX-ACCESS read-write
STATUS current
DESCRIPTION
"Data value."
::= { dataArray9 267 }

dataValue9_268 OBJECT-TYPE
SYNTAX INTEGER
MAX-ACCESS read-write
STATUS current
DESCRIPTION
"Data value."
::= { dataArray9 268 }

dataValue9_269 OBJECT-TYPE
SYNTAX INTEGER
MAX-ACCESS read-write
STATUS current
DESCRIPTION
"Data value."
::= { dataArray9 269 }

dataValue9_270 OBJECT-TYPE
SYNTAX INTEGER
MAX-ACCESS read-write
STATUS current
DESCRIPTION
"Data value."
::= { dataArray9 270 }

dataValue9_271 OBJECT-TYPE
SYNTAX INTEGER
MAX-ACCESS read-write
STATUS current
DESCRIPTION
"Data value."
::= { dataArray9 271 }

dataValue9_272 OBJECT-TYPE
SYNTAX INTEGER
MAX-ACCESS read-write
STATUS current
DESCRIPTION
"Data value."
::= { dataArray9 272 }

dataValue9_273 OBJECT-TYPE
SYNTAX INTEGER
MAX-ACCESS read-write
STATUS current
DESCRIPTION
"Data value."
::= { dataArray9 273 }

dataValue9_274 OBJECT-TYPE
SYNTAX INTEGER
MAX-ACCESS read-write
STATUS current
DESCRIPTION
"Data value."
::= { dataArray9 274 }

dataValue9_275 OBJECT-TYPE
SYNTAX INTEGER
MAX-ACCESS read-write
STATUS current
DESCRIPTION
"Data value."
::= { dataArray9 275 }

dataValue9_276 OBJECT-TYPE
SYNTAX INTEGER
MAX-ACCESS read-write
STATUS current
DESCRIPTION
"Data value."
::= { dataArray9 276 }

dataValue9_277 OBJECT-TYPE
SYNTAX INTEGER
MAX-ACCESS read-write
STATUS current
DESCRIPTION
"Data value."
::= { dataArray9 277 }

dataValue9_278 OBJECT-TYPE
SYNTAX INTEGER
MAX-ACCESS read-write
STATUS current
DESCRIPTION
"Data value."
::= { dataArray9 278 }

dataValue9_279 OBJECT-TYPE
SYNTAX INTEGER
MAX-ACCESS read-write
STATUS current
DESCRIPTION
"Data value."
::= { dataArray9 279 }

dataValue9_280 OBJECT-TYPE
SYNTAX INTEGER
MAX-ACCESS read-write
STATUS current
DESCRIPTION
"Data value."
::= { dataArray9 280 }

dataValue9_281 OBJECT-TYPE
SYNTAX INTEGER
MAX-ACCESS read-write
STATUS current
DESCRIPTION
"Data value."
::= { dataArray9 281 }

dataValue9_282 OBJECT-TYPE
SYNTAX INTEGER
MAX-ACCESS read-write
STATUS current
DESCRIPTION
"Data value."
::= { dataArray9 282 }

dataValue9_283 OBJECT-TYPE
SYNTAX INTEGER
MAX-ACCESS read-write
STATUS current
DESCRIPTION
"Data value."
::= { dataArray9 283 }

dataValue9_284 OBJECT-TYPE
SYNTAX INTEGER
MAX-ACCESS read-write
STATUS current
DESCRIPTION
"Data value."
::= { dataArray9 284 }

dataValue9_285 OBJECT-TYPE
SYNTAX INTEGER
MAX-ACCESS read-write
STATUS current
DESCRIPTION
"Data value."
::= { dataArray9 285 }

dataValue9_286 OBJECT-TYPE
SYNTAX INTEGER
MAX-ACCESS read-write
STATUS current
DESCRIPTION
"Data value."
::= { dataArray9 286 }

dataValue9_287 OBJECT-TYPE
SYNTAX INTEGER
MAX-ACCESS read-write
STATUS current
DESCRIPTION
"Data value."
::= { dataArray9 287 }

dataValue9_288 OBJECT-TYPE
SYNTAX INTEGER
MAX-ACCESS read-write
STATUS current
DESCRIPTION
"Data value."
::= { dataArray9 288 }

dataValue9_289 OBJECT-TYPE
SYNTAX INTEGER
MAX-ACCESS read-write
STATUS current
DESCRIPTION
"Data value."
::= { dataArray9 289 }

dataValue9_290 OBJECT-TYPE
SYNTAX INTEGER
MAX-ACCESS read-write
STATUS current
DESCRIPTION
"Data value."
::= { dataArray9 290 }

dataValue9_291 OBJECT-TYPE
SYNTAX INTEGER
MAX-ACCESS read-write
STATUS current
DESCRIPTION
"Data value."
::= { dataArray9 291 }

dataValue9_292 OBJECT-TYPE
SYNTAX INTEGER
MAX-ACCESS read-write
STATUS current
DESCRIPTION
"Data value."
::= { dataArray9 292 }

dataValue9_293 OBJECT-TYPE
SYNTAX INTEGER
MAX-ACCESS read-write
STATUS current
DESCRIPTION
"Data value."
::= { dataArray9 293 }

dataValue9_294 OBJECT-TYPE
SYNTAX INTEGER
MAX-ACCESS read-write
STATUS current
DESCRIPTION
"Data value."
::= { dataArray9 294 }

dataValue9_295 OBJECT-TYPE
SYNTAX INTEGER
MAX-ACCESS read-write
STATUS current
DESCRIPTION
"Data value."
::= { dataArray9 295 }

dataValue9_296 OBJECT-TYPE
SYNTAX INTEGER
MAX-ACCESS read-write
STATUS current
DESCRIPTION
"Data value."
::= { dataArray9 296 }

dataValue9_297 OBJECT-TYPE
SYNTAX INTEGER
MAX-ACCESS read-write
STATUS current
DESCRIPTION
"Data value."
::= { dataArray9 297 }

dataValue9_298 OBJECT-TYPE
SYNTAX INTEGER
MAX-ACCESS read-write
STATUS current
DESCRIPTION
"Data value."
::= { dataArray9 298 }

dataValue9_299 OBJECT-TYPE
SYNTAX INTEGER
MAX-ACCESS read-write
STATUS current
DESCRIPTION
"Data value."
::= { dataArray9 299 }

dataValue9_300 OBJECT-TYPE
SYNTAX INTEGER
MAX-ACCESS read-write
STATUS current
DESCRIPTION
"Data value."
::= { dataArray9 300 }

dataValue9_301 OBJECT-TYPE
SYNTAX INTEGER
MAX-ACCESS read-write
STATUS current
DESCRIPTION
"Data value."
::= { dataArray9 301 }

dataValue9_302 OBJECT-TYPE
SYNTAX INTEGER
MAX-ACCESS read-write
STATUS current
DESCRIPTION
"Data value."
::= { dataArray9 302 }

dataValue9_303 OBJECT-TYPE
SYNTAX INTEGER
MAX-ACCESS read-write
STATUS current
DESCRIPTION
"Data value."
::= { dataArray9 303 }

dataValue9_304 OBJECT-TYPE
SYNTAX INTEGER
MAX-ACCESS read-write
STATUS current
DESCRIPTION
"Data value."
::= { dataArray9 304 }

dataValue9_305 OBJECT-TYPE
SYNTAX INTEGER
MAX-ACCESS read-write
STATUS current
DESCRIPTION
"Data value."
::= { dataArray9 305 }

dataValue9_306 OBJECT-TYPE
SYNTAX INTEGER
MAX-ACCESS read-write
STATUS current
DESCRIPTION
"Data value."
::= { dataArray9 306 }

dataValue9_307 OBJECT-TYPE
SYNTAX INTEGER
MAX-ACCESS read-write
STATUS current
DESCRIPTION
"Data value."
::= { dataArray9 307 }

dataValue9_308 OBJECT-TYPE
SYNTAX INTEGER
MAX-ACCESS read-write
STATUS current
DESCRIPTION
"Data value."
::= { dataArray9 308 }

dataValue9_309 OBJECT-TYPE
SYNTAX INTEGER
MAX-ACCESS read-write
STATUS current
DESCRIPTION
"Data value."
::= { dataArray9 309 }

dataValue9_310 OBJECT-TYPE
SYNTAX INTEGER
MAX-ACCESS read-write
STATUS current
DESCRIPTION
"Data value."
::= { dataArray9 310 }

dataValue9_311 OBJECT-TYPE
SYNTAX INTEGER
MAX-ACCESS read-write
STATUS current
DESCRIPTION
"Data value."
::= { dataArray9 311 }

dataValue9_312 OBJECT-TYPE
SYNTAX INTEGER
MAX-ACCESS read-write
STATUS current
DESCRIPTION
"Data value."
::= { dataArray9 312 }

dataValue9_313 OBJECT-TYPE
SYNTAX INTEGER
MAX-ACCESS read-write
STATUS current
DESCRIPTION
"Data value."
::= { dataArray9 313 }

dataValue9_314 OBJECT-TYPE
SYNTAX INTEGER
MAX-ACCESS read-write
STATUS current
DESCRIPTION
"Data value."
::= { dataArray9 314 }

dataValue9_315 OBJECT-TYPE
SYNTAX INTEGER
MAX-ACCESS read-write
STATUS current
DESCRIPTION
"Data value."
::= { dataArray9 315 }

dataValue9_316 OBJECT-TYPE
SYNTAX INTEGER
MAX-ACCESS read-write
STATUS current
DESCRIPTION
"Data value."
::= { dataArray9 316 }

dataValue9_317 OBJECT-TYPE
SYNTAX INTEGER
MAX-ACCESS read-write
STATUS current
DESCRIPTION
"Data value."
::= { dataArray9 317 }

dataValue9_318 OBJECT-TYPE
SYNTAX INTEGER
MAX-ACCESS read-write
STATUS current
DESCRIPTION
"Data value."
::= { dataArray9 318 }

dataValue9_319 OBJECT-TYPE
SYNTAX INTEGER
MAX-ACCESS read-write
STATUS current
DESCRIPTION
"Data value."
::= { dataArray9 319 }

dataValue9_320 OBJECT-TYPE
SYNTAX INTEGER
MAX-ACCESS read-write
STATUS current
DESCRIPTION
"Data value."
::= { dataArray9 320 }

dataValue9_321 OBJECT-TYPE
SYNTAX INTEGER
MAX-ACCESS read-write
STATUS current
DESCRIPTION
"Data value."
::= { dataArray9 321 }

dataValue9_322 OBJECT-TYPE
SYNTAX INTEGER
MAX-ACCESS read-write
STATUS current
DESCRIPTION
"Data value."
::= { dataArray9 322 }

dataValue9_323 OBJECT-TYPE
SYNTAX INTEGER
MAX-ACCESS read-write
STATUS current
DESCRIPTION
"Data value."
::= { dataArray9 323 }

dataValue9_324 OBJECT-TYPE
SYNTAX INTEGER
MAX-ACCESS read-write
STATUS current
DESCRIPTION
"Data value."
::= { dataArray9 324 }

dataValue9_325 OBJECT-TYPE
SYNTAX INTEGER
MAX-ACCESS read-write
STATUS current
DESCRIPTION
"Data value."
::= { dataArray9 325 }

dataValue9_326 OBJECT-TYPE
SYNTAX INTEGER
MAX-ACCESS read-write
STATUS current
DESCRIPTION
"Data value."
::= { dataArray9 326 }

dataValue9_327 OBJECT-TYPE
SYNTAX INTEGER
MAX-ACCESS read-write
STATUS current
DESCRIPTION
"Data value."
::= { dataArray9 327 }

dataValue9_328 OBJECT-TYPE
SYNTAX INTEGER
MAX-ACCESS read-write
STATUS current
DESCRIPTION
"Data value."
::= { dataArray9 328 }

dataValue9_329 OBJECT-TYPE
SYNTAX INTEGER
MAX-ACCESS read-write
STATUS current
DESCRIPTION
"Data value."
::= { dataArray9 329 }

dataValue9_330 OBJECT-TYPE
SYNTAX INTEGER
MAX-ACCESS read-write
STATUS current
DESCRIPTION
"Data value."
::= { dataArray9 330 }

dataValue9_331 OBJECT-TYPE
SYNTAX INTEGER
MAX-ACCESS read-write
STATUS current
DESCRIPTION
"Data value."
::= { dataArray9 331 }

dataValue9_332 OBJECT-TYPE
SYNTAX INTEGER
MAX-ACCESS read-write
STATUS current
DESCRIPTION
"Data value."
::= { dataArray9 332 }

dataValue9_333 OBJECT-TYPE
SYNTAX INTEGER
MAX-ACCESS read-write
STATUS current
DESCRIPTION
"Data value."
::= { dataArray9 333 }

dataValue9_334 OBJECT-TYPE
SYNTAX INTEGER
MAX-ACCESS read-write
STATUS current
DESCRIPTION
"Data value."
::= { dataArray9 334 }

dataValue9_335 OBJECT-TYPE
SYNTAX INTEGER
MAX-ACCESS read-write
STATUS current
DESCRIPTION
"Data value."
::= { dataArray9 335 }

dataValue9_336 OBJECT-TYPE
SYNTAX INTEGER
MAX-ACCESS read-write
STATUS current
DESCRIPTION
"Data value."
::= { dataArray9 336 }

dataValue9_337 OBJECT-TYPE
SYNTAX INTEGER
MAX-ACCESS read-write
STATUS current
DESCRIPTION
"Data value."
::= { dataArray9 337 }

dataValue9_338 OBJECT-TYPE
SYNTAX INTEGER
MAX-ACCESS read-write
STATUS current
DESCRIPTION
"Data value."
::= { dataArray9 338 }

dataValue9_339 OBJECT-TYPE
SYNTAX INTEGER
MAX-ACCESS read-write
STATUS current
DESCRIPTION
"Data value."
::= { dataArray9 339 }

dataValue9_340 OBJECT-TYPE
SYNTAX INTEGER
MAX-ACCESS read-write
STATUS current
DESCRIPTION
"Data value."
::= { dataArray9 340 }

dataValue9_341 OBJECT-TYPE
SYNTAX INTEGER
MAX-ACCESS read-write
STATUS current
DESCRIPTION
"Data value."
::= { dataArray9 341 }

dataValue9_342 OBJECT-TYPE
SYNTAX INTEGER
MAX-ACCESS read-write
STATUS current
DESCRIPTION
"Data value."
::= { dataArray9 342 }

dataValue9_343 OBJECT-TYPE
SYNTAX INTEGER
MAX-ACCESS read-write
STATUS current
DESCRIPTION
"Data value."
::= { dataArray9 343 }

dataValue9_344 OBJECT-TYPE
SYNTAX INTEGER
MAX-ACCESS read-write
STATUS current
DESCRIPTION
"Data value."
::= { dataArray9 344 }

dataValue9_345 OBJECT-TYPE
SYNTAX INTEGER
MAX-ACCESS read-write
STATUS current
DESCRIPTION
"Data value."
::= { dataArray9 345 }

dataValue9_346 OBJECT-TYPE
SYNTAX INTEGER
MAX-ACCESS read-write
STATUS current
DESCRIPTION
"Data value."
::= { dataArray9 346 }

dataValue9_347 OBJECT-TYPE
SYNTAX INTEGER
MAX-ACCESS read-write
STATUS current
DESCRIPTION
"Data value."
::= { dataArray9 347 }

dataValue9_348 OBJECT-TYPE
SYNTAX INTEGER
MAX-ACCESS read-write
STATUS current
DESCRIPTION
"Data value."
::= { dataArray9 348 }

dataValue9_349 OBJECT-TYPE
SYNTAX INTEGER
MAX-ACCESS read-write
STATUS current
DESCRIPTION
"Data value."
::= { dataArray9 349 }

dataValue9_350 OBJECT-TYPE
SYNTAX INTEGER
MAX-ACCESS read-write
STATUS current
DESCRIPTION
"Data value."
::= { dataArray9 350 }

dataValue9_351 OBJECT-TYPE
SYNTAX INTEGER
MAX-ACCESS read-write
STATUS current
DESCRIPTION
"Data value."
::= { dataArray9 351 }

dataValue9_352 OBJECT-TYPE
SYNTAX INTEGER
MAX-ACCESS read-write
STATUS current
DESCRIPTION
"Data value."
::= { dataArray9 352 }

dataValue9_353 OBJECT-TYPE
SYNTAX INTEGER
MAX-ACCESS read-write
STATUS current
DESCRIPTION
"Data value."
::= { dataArray9 353 }

dataValue9_354 OBJECT-TYPE
SYNTAX INTEGER
MAX-ACCESS read-write
STATUS current
DESCRIPTION
"Data value."
::= { dataArray9 354 }

dataValue9_355 OBJECT-TYPE
SYNTAX INTEGER
MAX-ACCESS read-write
STATUS current
DESCRIPTION
"Data value."
::= { dataArray9 355 }

dataValue9_356 OBJECT-TYPE
SYNTAX INTEGER
MAX-ACCESS read-write
STATUS current
DESCRIPTION
"Data value."
::= { dataArray9 356 }

dataValue9_357 OBJECT-TYPE
SYNTAX INTEGER
MAX-ACCESS read-write
STATUS current
DESCRIPTION
"Data value."
::= { dataArray9 357 }

dataValue9_358 OBJECT-TYPE
SYNTAX INTEGER
MAX-ACCESS read-write
STATUS current
DESCRIPTION
"Data value."
::= { dataArray9 358 }

dataValue9_359 OBJECT-TYPE
SYNTAX INTEGER
MAX-ACCESS read-write
STATUS current
DESCRIPTION
"Data value."
::= { dataArray9 359 }

dataValue9_360 OBJECT-TYPE
SYNTAX INTEGER
MAX-ACCESS read-write
STATUS current
DESCRIPTION
"Data value."
::= { dataArray9 360 }

dataValue9_361 OBJECT-TYPE
SYNTAX INTEGER
MAX-ACCESS read-write
STATUS current
DESCRIPTION
"Data value."
::= { dataArray9 361 }

dataValue9_362 OBJECT-TYPE
SYNTAX INTEGER
MAX-ACCESS read-write
STATUS current
DESCRIPTION
"Data value."
::= { dataArray9 362 }

dataValue9_363 OBJECT-TYPE
SYNTAX INTEGER
MAX-ACCESS read-write
STATUS current
DESCRIPTION
"Data value."
::= { dataArray9 363 }

dataValue9_364 OBJECT-TYPE
SYNTAX INTEGER
MAX-ACCESS read-write
STATUS current
DESCRIPTION
"Data value."
::= { dataArray9 364 }

dataValue9_365 OBJECT-TYPE
SYNTAX INTEGER
MAX-ACCESS read-write
STATUS current
DESCRIPTION
"Data value."
::= { dataArray9 365 }

dataValue9_366 OBJECT-TYPE
SYNTAX INTEGER
MAX-ACCESS read-write
STATUS current
DESCRIPTION
"Data value."
::= { dataArray9 366 }

dataValue9_367 OBJECT-TYPE
SYNTAX INTEGER
MAX-ACCESS read-write
STATUS current
DESCRIPTION
"Data value."
::= { dataArray9 367 }

dataValue9_368 OBJECT-TYPE
SYNTAX INTEGER
MAX-ACCESS read-write
STATUS current
DESCRIPTION
"Data value."
::= { dataArray9 368 }

dataValue9_369 OBJECT-TYPE
SYNTAX INTEGER
MAX-ACCESS read-write
STATUS current
DESCRIPTION
"Data value."
::= { dataArray9 369 }

dataValue9_370 OBJECT-TYPE
SYNTAX INTEGER
MAX-ACCESS read-write
STATUS current
DESCRIPTION
"Data value."
::= { dataArray9 370 }

dataValue9_371 OBJECT-TYPE
SYNTAX INTEGER
MAX-ACCESS read-write
STATUS current
DESCRIPTION
"Data value."
::= { dataArray9 371 }

dataValue9_372 OBJECT-TYPE
SYNTAX INTEGER
MAX-ACCESS read-write
STATUS current
DESCRIPTION
"Data value."
::= { dataArray9 372 }

dataValue9_373 OBJECT-TYPE
SYNTAX INTEGER
MAX-ACCESS read-write
STATUS current
DESCRIPTION
"Data value."
::= { dataArray9 373 }

dataValue9_374 OBJECT-TYPE
SYNTAX INTEGER
MAX-ACCESS read-write
STATUS current
DESCRIPTION
"Data value."
::= { dataArray9 374 }

dataValue9_375 OBJECT-TYPE
SYNTAX INTEGER
MAX-ACCESS read-write
STATUS current
DESCRIPTION
"Data value."
::= { dataArray9 375 }

dataValue9_376 OBJECT-TYPE
SYNTAX INTEGER
MAX-ACCESS read-write
STATUS current
DESCRIPTION
"Data value."
::= { dataArray9 376 }

dataValue9_377 OBJECT-TYPE
SYNTAX INTEGER
MAX-ACCESS read-write
STATUS current
DESCRIPTION
"Data value."
::= { dataArray9 377 }

dataValue9_378 OBJECT-TYPE
SYNTAX INTEGER
MAX-ACCESS read-write
STATUS current
DESCRIPTION
"Data value."
::= { dataArray9 378 }

dataValue9_379 OBJECT-TYPE
SYNTAX INTEGER
MAX-ACCESS read-write
STATUS current
DESCRIPTION
"Data value."
::= { dataArray9 379 }

dataValue9_380 OBJECT-TYPE
SYNTAX INTEGER
MAX-ACCESS read-write
STATUS current
DESCRIPTION
"Data value."
::= { dataArray9 380 }

dataValue9_381 OBJECT-TYPE
SYNTAX INTEGER
MAX-ACCESS read-write
STATUS current
DESCRIPTION
"Data value."
::= { dataArray9 381 }

dataValue9_382 OBJECT-TYPE
SYNTAX INTEGER
MAX-ACCESS read-write
STATUS current
DESCRIPTION
"Data value."
::= { dataArray9 382 }

dataValue9_383 OBJECT-TYPE
SYNTAX INTEGER
MAX-ACCESS read-write
STATUS current
DESCRIPTION
"Data value."
::= { dataArray9 383 }

dataValue9_384 OBJECT-TYPE
SYNTAX INTEGER
MAX-ACCESS read-write
STATUS current
DESCRIPTION
"Data value."
::= { dataArray9 384 }

dataValue9_385 OBJECT-TYPE
SYNTAX INTEGER
MAX-ACCESS read-write
STATUS current
DESCRIPTION
"Data value."
::= { dataArray9 385 }

dataValue9_386 OBJECT-TYPE
SYNTAX INTEGER
MAX-ACCESS read-write
STATUS current
DESCRIPTION
"Data value."
::= { dataArray9 386 }

dataValue9_387 OBJECT-TYPE
SYNTAX INTEGER
MAX-ACCESS read-write
STATUS current
DESCRIPTION
"Data value."
::= { dataArray9 387 }

dataValue9_388 OBJECT-TYPE
SYNTAX INTEGER
MAX-ACCESS read-write
STATUS current
DESCRIPTION
"Data value."
::= { dataArray9 388 }

dataValue9_389 OBJECT-TYPE
SYNTAX INTEGER
MAX-ACCESS read-write
STATUS current
DESCRIPTION
"Data value."
::= { dataArray9 389 }

dataValue9_390 OBJECT-TYPE
SYNTAX INTEGER
MAX-ACCESS read-write
STATUS current
DESCRIPTION
"Data value."
::= { dataArray9 390 }

dataValue9_391 OBJECT-TYPE
SYNTAX INTEGER
MAX-ACCESS read-write
STATUS current
DESCRIPTION
"Data value."
::= { dataArray9 391 }

dataValue9_392 OBJECT-TYPE
SYNTAX INTEGER
MAX-ACCESS read-write
STATUS current
DESCRIPTION
"Data value."
::= { dataArray9 392 }

dataValue9_393 OBJECT-TYPE
SYNTAX INTEGER
MAX-ACCESS read-write
STATUS current
DESCRIPTION
"Data value."
::= { dataArray9 393 }

dataValue9_394 OBJECT-TYPE
SYNTAX INTEGER
MAX-ACCESS read-write
STATUS current
DESCRIPTION
"Data value."
::= { dataArray9 394 }

dataValue9_395 OBJECT-TYPE
SYNTAX INTEGER
MAX-ACCESS read-write
STATUS current
DESCRIPTION
"Data value."
::= { dataArray9 395 }

dataValue9_396 OBJECT-TYPE
SYNTAX INTEGER
MAX-ACCESS read-write
STATUS current
DESCRIPTION
"Data value."
::= { dataArray9 396 }

dataValue9_397 OBJECT-TYPE
SYNTAX INTEGER
MAX-ACCESS read-write
STATUS current
DESCRIPTION
"Data value."
::= { dataArray9 397 }

dataValue9_398 OBJECT-TYPE
SYNTAX INTEGER
MAX-ACCESS read-write
STATUS current
DESCRIPTION
"Data value."
::= { dataArray9 398 }

dataValue9_399 OBJECT-TYPE
SYNTAX INTEGER
MAX-ACCESS read-write
STATUS current
DESCRIPTION
"Data value."
::= { dataArray9 399 }

dataArray10 OBJECT IDENTIFIER ::= { cc08255400_v1_00a 10 }

dataValue10_0 OBJECT-TYPE
SYNTAX INTEGER
MAX-ACCESS read-write
STATUS current
DESCRIPTION
"Data value."
::= { dataArray10 0 }

dataValue10_1 OBJECT-TYPE
SYNTAX INTEGER
MAX-ACCESS read-write
STATUS current
DESCRIPTION
"Data value."
::= { dataArray10 1 }

dataValue10_2 OBJECT-TYPE
SYNTAX INTEGER
MAX-ACCESS read-write
STATUS current
DESCRIPTION
"Data value."
::= { dataArray10 2 }

dataValue10_3 OBJECT-TYPE
SYNTAX INTEGER
MAX-ACCESS read-write
STATUS current
DESCRIPTION
"Data value."
::= { dataArray10 3 }

dataValue10_4 OBJECT-TYPE
SYNTAX INTEGER
MAX-ACCESS read-write
STATUS current
DESCRIPTION
"Data value."
::= { dataArray10 4 }

dataValue10_5 OBJECT-TYPE
SYNTAX INTEGER
MAX-ACCESS read-write
STATUS current
DESCRIPTION
"Data value."
::= { dataArray10 5 }

dataValue10_6 OBJECT-TYPE
SYNTAX INTEGER
MAX-ACCESS read-write
STATUS current
DESCRIPTION
"Data value."
::= { dataArray10 6 }

dataValue10_7 OBJECT-TYPE
SYNTAX INTEGER
MAX-ACCESS read-write
STATUS current
DESCRIPTION
"Data value."
::= { dataArray10 7 }

dataValue10_8 OBJECT-TYPE
SYNTAX INTEGER
MAX-ACCESS read-write
STATUS current
DESCRIPTION
"Data value."
::= { dataArray10 8 }

dataValue10_9 OBJECT-TYPE
SYNTAX INTEGER
MAX-ACCESS read-write
STATUS current
DESCRIPTION
"Data value."
::= { dataArray10 9 }

dataValue10_10 OBJECT-TYPE
SYNTAX INTEGER
MAX-ACCESS read-write
STATUS current
DESCRIPTION
"Data value."
::= { dataArray10 10 }

dataValue10_11 OBJECT-TYPE
SYNTAX INTEGER
MAX-ACCESS read-write
STATUS current
DESCRIPTION
"Data value."
::= { dataArray10 11 }

dataValue10_12 OBJECT-TYPE
SYNTAX INTEGER
MAX-ACCESS read-write
STATUS current
DESCRIPTION
"Data value."
::= { dataArray10 12 }

dataValue10_13 OBJECT-TYPE
SYNTAX INTEGER
MAX-ACCESS read-write
STATUS current
DESCRIPTION
"Data value."
::= { dataArray10 13 }

dataValue10_14 OBJECT-TYPE
SYNTAX INTEGER
MAX-ACCESS read-write
STATUS current
DESCRIPTION
"Data value."
::= { dataArray10 14 }

dataValue10_15 OBJECT-TYPE
SYNTAX INTEGER
MAX-ACCESS read-write
STATUS current
DESCRIPTION
"Data value."
::= { dataArray10 15 }

dataValue10_16 OBJECT-TYPE
SYNTAX INTEGER
MAX-ACCESS read-write
STATUS current
DESCRIPTION
"Data value."
::= { dataArray10 16 }

dataValue10_17 OBJECT-TYPE
SYNTAX INTEGER
MAX-ACCESS read-write
STATUS current
DESCRIPTION
"Data value."
::= { dataArray10 17 }

dataValue10_18 OBJECT-TYPE
SYNTAX INTEGER
MAX-ACCESS read-write
STATUS current
DESCRIPTION
"Data value."
::= { dataArray10 18 }

dataValue10_19 OBJECT-TYPE
SYNTAX INTEGER
MAX-ACCESS read-write
STATUS current
DESCRIPTION
"Data value."
::= { dataArray10 19 }

dataValue10_20 OBJECT-TYPE
SYNTAX INTEGER
MAX-ACCESS read-write
STATUS current
DESCRIPTION
"Data value."
::= { dataArray10 20 }

dataValue10_21 OBJECT-TYPE
SYNTAX INTEGER
MAX-ACCESS read-write
STATUS current
DESCRIPTION
"Data value."
::= { dataArray10 21 }

dataValue10_22 OBJECT-TYPE
SYNTAX INTEGER
MAX-ACCESS read-write
STATUS current
DESCRIPTION
"Data value."
::= { dataArray10 22 }

dataValue10_23 OBJECT-TYPE
SYNTAX INTEGER
MAX-ACCESS read-write
STATUS current
DESCRIPTION
"Data value."
::= { dataArray10 23 }

dataValue10_24 OBJECT-TYPE
SYNTAX INTEGER
MAX-ACCESS read-write
STATUS current
DESCRIPTION
"Data value."
::= { dataArray10 24 }

dataValue10_25 OBJECT-TYPE
SYNTAX INTEGER
MAX-ACCESS read-write
STATUS current
DESCRIPTION
"Data value."
::= { dataArray10 25 }

dataValue10_26 OBJECT-TYPE
SYNTAX INTEGER
MAX-ACCESS read-write
STATUS current
DESCRIPTION
"Data value."
::= { dataArray10 26 }

dataValue10_27 OBJECT-TYPE
SYNTAX INTEGER
MAX-ACCESS read-write
STATUS current
DESCRIPTION
"Data value."
::= { dataArray10 27 }

dataValue10_28 OBJECT-TYPE
SYNTAX INTEGER
MAX-ACCESS read-write
STATUS current
DESCRIPTION
"Data value."
::= { dataArray10 28 }

dataValue10_29 OBJECT-TYPE
SYNTAX INTEGER
MAX-ACCESS read-write
STATUS current
DESCRIPTION
"Data value."
::= { dataArray10 29 }

dataValue10_30 OBJECT-TYPE
SYNTAX INTEGER
MAX-ACCESS read-write
STATUS current
DESCRIPTION
"Data value."
::= { dataArray10 30 }

dataValue10_31 OBJECT-TYPE
SYNTAX INTEGER
MAX-ACCESS read-write
STATUS current
DESCRIPTION
"Data value."
::= { dataArray10 31 }

dataValue10_32 OBJECT-TYPE
SYNTAX INTEGER
MAX-ACCESS read-write
STATUS current
DESCRIPTION
"Data value."
::= { dataArray10 32 }

dataValue10_33 OBJECT-TYPE
SYNTAX INTEGER
MAX-ACCESS read-write
STATUS current
DESCRIPTION
"Data value."
::= { dataArray10 33 }

dataValue10_34 OBJECT-TYPE
SYNTAX INTEGER
MAX-ACCESS read-write
STATUS current
DESCRIPTION
"Data value."
::= { dataArray10 34 }

dataValue10_35 OBJECT-TYPE
SYNTAX INTEGER
MAX-ACCESS read-write
STATUS current
DESCRIPTION
"Data value."
::= { dataArray10 35 }

dataValue10_36 OBJECT-TYPE
SYNTAX INTEGER
MAX-ACCESS read-write
STATUS current
DESCRIPTION
"Data value."
::= { dataArray10 36 }

dataValue10_37 OBJECT-TYPE
SYNTAX INTEGER
MAX-ACCESS read-write
STATUS current
DESCRIPTION
"Data value."
::= { dataArray10 37 }

dataValue10_38 OBJECT-TYPE
SYNTAX INTEGER
MAX-ACCESS read-write
STATUS current
DESCRIPTION
"Data value."
::= { dataArray10 38 }

dataValue10_39 OBJECT-TYPE
SYNTAX INTEGER
MAX-ACCESS read-write
STATUS current
DESCRIPTION
"Data value."
::= { dataArray10 39 }

dataValue10_40 OBJECT-TYPE
SYNTAX INTEGER
MAX-ACCESS read-write
STATUS current
DESCRIPTION
"Data value."
::= { dataArray10 40 }

dataValue10_41 OBJECT-TYPE
SYNTAX INTEGER
MAX-ACCESS read-write
STATUS current
DESCRIPTION
"Data value."
::= { dataArray10 41 }

dataValue10_42 OBJECT-TYPE
SYNTAX INTEGER
MAX-ACCESS read-write
STATUS current
DESCRIPTION
"Data value."
::= { dataArray10 42 }

dataValue10_43 OBJECT-TYPE
SYNTAX INTEGER
MAX-ACCESS read-write
STATUS current
DESCRIPTION
"Data value."
::= { dataArray10 43 }

dataValue10_44 OBJECT-TYPE
SYNTAX INTEGER
MAX-ACCESS read-write
STATUS current
DESCRIPTION
"Data value."
::= { dataArray10 44 }

dataValue10_45 OBJECT-TYPE
SYNTAX INTEGER
MAX-ACCESS read-write
STATUS current
DESCRIPTION
"Data value."
::= { dataArray10 45 }

dataValue10_46 OBJECT-TYPE
SYNTAX INTEGER
MAX-ACCESS read-write
STATUS current
DESCRIPTION
"Data value."
::= { dataArray10 46 }

dataValue10_47 OBJECT-TYPE
SYNTAX INTEGER
MAX-ACCESS read-write
STATUS current
DESCRIPTION
"Data value."
::= { dataArray10 47 }

dataValue10_48 OBJECT-TYPE
SYNTAX INTEGER
MAX-ACCESS read-write
STATUS current
DESCRIPTION
"Data value."
::= { dataArray10 48 }

dataValue10_49 OBJECT-TYPE
SYNTAX INTEGER
MAX-ACCESS read-write
STATUS current
DESCRIPTION
"Data value."
::= { dataArray10 49 }

dataValue10_50 OBJECT-TYPE
SYNTAX INTEGER
MAX-ACCESS read-write
STATUS current
DESCRIPTION
"Data value."
::= { dataArray10 50 }

dataValue10_51 OBJECT-TYPE
SYNTAX INTEGER
MAX-ACCESS read-write
STATUS current
DESCRIPTION
"Data value."
::= { dataArray10 51 }

dataValue10_52 OBJECT-TYPE
SYNTAX INTEGER
MAX-ACCESS read-write
STATUS current
DESCRIPTION
"Data value."
::= { dataArray10 52 }

dataValue10_53 OBJECT-TYPE
SYNTAX INTEGER
MAX-ACCESS read-write
STATUS current
DESCRIPTION
"Data value."
::= { dataArray10 53 }

dataValue10_54 OBJECT-TYPE
SYNTAX INTEGER
MAX-ACCESS read-write
STATUS current
DESCRIPTION
"Data value."
::= { dataArray10 54 }

dataValue10_55 OBJECT-TYPE
SYNTAX INTEGER
MAX-ACCESS read-write
STATUS current
DESCRIPTION
"Data value."
::= { dataArray10 55 }

dataValue10_56 OBJECT-TYPE
SYNTAX INTEGER
MAX-ACCESS read-write
STATUS current
DESCRIPTION
"Data value."
::= { dataArray10 56 }

dataValue10_57 OBJECT-TYPE
SYNTAX INTEGER
MAX-ACCESS read-write
STATUS current
DESCRIPTION
"Data value."
::= { dataArray10 57 }

dataValue10_58 OBJECT-TYPE
SYNTAX INTEGER
MAX-ACCESS read-write
STATUS current
DESCRIPTION
"Data value."
::= { dataArray10 58 }

dataValue10_59 OBJECT-TYPE
SYNTAX INTEGER
MAX-ACCESS read-write
STATUS current
DESCRIPTION
"Data value."
::= { dataArray10 59 }

dataValue10_60 OBJECT-TYPE
SYNTAX INTEGER
MAX-ACCESS read-write
STATUS current
DESCRIPTION
"Data value."
::= { dataArray10 60 }

dataValue10_61 OBJECT-TYPE
SYNTAX INTEGER
MAX-ACCESS read-write
STATUS current
DESCRIPTION
"Data value."
::= { dataArray10 61 }

dataValue10_62 OBJECT-TYPE
SYNTAX INTEGER
MAX-ACCESS read-write
STATUS current
DESCRIPTION
"Data value."
::= { dataArray10 62 }

dataValue10_63 OBJECT-TYPE
SYNTAX INTEGER
MAX-ACCESS read-write
STATUS current
DESCRIPTION
"Data value."
::= { dataArray10 63 }

dataValue10_64 OBJECT-TYPE
SYNTAX INTEGER
MAX-ACCESS read-write
STATUS current
DESCRIPTION
"Data value."
::= { dataArray10 64 }

dataValue10_65 OBJECT-TYPE
SYNTAX INTEGER
MAX-ACCESS read-write
STATUS current
DESCRIPTION
"Data value."
::= { dataArray10 65 }

dataValue10_66 OBJECT-TYPE
SYNTAX INTEGER
MAX-ACCESS read-write
STATUS current
DESCRIPTION
"Data value."
::= { dataArray10 66 }

dataValue10_67 OBJECT-TYPE
SYNTAX INTEGER
MAX-ACCESS read-write
STATUS current
DESCRIPTION
"Data value."
::= { dataArray10 67 }

dataValue10_68 OBJECT-TYPE
SYNTAX INTEGER
MAX-ACCESS read-write
STATUS current
DESCRIPTION
"Data value."
::= { dataArray10 68 }

dataValue10_69 OBJECT-TYPE
SYNTAX INTEGER
MAX-ACCESS read-write
STATUS current
DESCRIPTION
"Data value."
::= { dataArray10 69 }

dataValue10_70 OBJECT-TYPE
SYNTAX INTEGER
MAX-ACCESS read-write
STATUS current
DESCRIPTION
"Data value."
::= { dataArray10 70 }

dataValue10_71 OBJECT-TYPE
SYNTAX INTEGER
MAX-ACCESS read-write
STATUS current
DESCRIPTION
"Data value."
::= { dataArray10 71 }

dataValue10_72 OBJECT-TYPE
SYNTAX INTEGER
MAX-ACCESS read-write
STATUS current
DESCRIPTION
"Data value."
::= { dataArray10 72 }

dataValue10_73 OBJECT-TYPE
SYNTAX INTEGER
MAX-ACCESS read-write
STATUS current
DESCRIPTION
"Data value."
::= { dataArray10 73 }

dataValue10_74 OBJECT-TYPE
SYNTAX INTEGER
MAX-ACCESS read-write
STATUS current
DESCRIPTION
"Data value."
::= { dataArray10 74 }

dataValue10_75 OBJECT-TYPE
SYNTAX INTEGER
MAX-ACCESS read-write
STATUS current
DESCRIPTION
"Data value."
::= { dataArray10 75 }

dataValue10_76 OBJECT-TYPE
SYNTAX INTEGER
MAX-ACCESS read-write
STATUS current
DESCRIPTION
"Data value."
::= { dataArray10 76 }

dataValue10_77 OBJECT-TYPE
SYNTAX INTEGER
MAX-ACCESS read-write
STATUS current
DESCRIPTION
"Data value."
::= { dataArray10 77 }

dataValue10_78 OBJECT-TYPE
SYNTAX INTEGER
MAX-ACCESS read-write
STATUS current
DESCRIPTION
"Data value."
::= { dataArray10 78 }

dataValue10_79 OBJECT-TYPE
SYNTAX INTEGER
MAX-ACCESS read-write
STATUS current
DESCRIPTION
"Data value."
::= { dataArray10 79 }

dataValue10_80 OBJECT-TYPE
SYNTAX INTEGER
MAX-ACCESS read-write
STATUS current
DESCRIPTION
"Data value."
::= { dataArray10 80 }

dataValue10_81 OBJECT-TYPE
SYNTAX INTEGER
MAX-ACCESS read-write
STATUS current
DESCRIPTION
"Data value."
::= { dataArray10 81 }

dataValue10_82 OBJECT-TYPE
SYNTAX INTEGER
MAX-ACCESS read-write
STATUS current
DESCRIPTION
"Data value."
::= { dataArray10 82 }

dataValue10_83 OBJECT-TYPE
SYNTAX INTEGER
MAX-ACCESS read-write
STATUS current
DESCRIPTION
"Data value."
::= { dataArray10 83 }

dataValue10_84 OBJECT-TYPE
SYNTAX INTEGER
MAX-ACCESS read-write
STATUS current
DESCRIPTION
"Data value."
::= { dataArray10 84 }

dataValue10_85 OBJECT-TYPE
SYNTAX INTEGER
MAX-ACCESS read-write
STATUS current
DESCRIPTION
"Data value."
::= { dataArray10 85 }

dataValue10_86 OBJECT-TYPE
SYNTAX INTEGER
MAX-ACCESS read-write
STATUS current
DESCRIPTION
"Data value."
::= { dataArray10 86 }

dataValue10_87 OBJECT-TYPE
SYNTAX INTEGER
MAX-ACCESS read-write
STATUS current
DESCRIPTION
"Data value."
::= { dataArray10 87 }

dataValue10_88 OBJECT-TYPE
SYNTAX INTEGER
MAX-ACCESS read-write
STATUS current
DESCRIPTION
"Data value."
::= { dataArray10 88 }

dataValue10_89 OBJECT-TYPE
SYNTAX INTEGER
MAX-ACCESS read-write
STATUS current
DESCRIPTION
"Data value."
::= { dataArray10 89 }

dataValue10_90 OBJECT-TYPE
SYNTAX INTEGER
MAX-ACCESS read-write
STATUS current
DESCRIPTION
"Data value."
::= { dataArray10 90 }

dataValue10_91 OBJECT-TYPE
SYNTAX INTEGER
MAX-ACCESS read-write
STATUS current
DESCRIPTION
"Data value."
::= { dataArray10 91 }

dataValue10_92 OBJECT-TYPE
SYNTAX INTEGER
MAX-ACCESS read-write
STATUS current
DESCRIPTION
"Data value."
::= { dataArray10 92 }

dataValue10_93 OBJECT-TYPE
SYNTAX INTEGER
MAX-ACCESS read-write
STATUS current
DESCRIPTION
"Data value."
::= { dataArray10 93 }

dataValue10_94 OBJECT-TYPE
SYNTAX INTEGER
MAX-ACCESS read-write
STATUS current
DESCRIPTION
"Data value."
::= { dataArray10 94 }

dataValue10_95 OBJECT-TYPE
SYNTAX INTEGER
MAX-ACCESS read-write
STATUS current
DESCRIPTION
"Data value."
::= { dataArray10 95 }

dataValue10_96 OBJECT-TYPE
SYNTAX INTEGER
MAX-ACCESS read-write
STATUS current
DESCRIPTION
"Data value."
::= { dataArray10 96 }

dataValue10_97 OBJECT-TYPE
SYNTAX INTEGER
MAX-ACCESS read-write
STATUS current
DESCRIPTION
"Data value."
::= { dataArray10 97 }

dataValue10_98 OBJECT-TYPE
SYNTAX INTEGER
MAX-ACCESS read-write
STATUS current
DESCRIPTION
"Data value."
::= { dataArray10 98 }

dataValue10_99 OBJECT-TYPE
SYNTAX INTEGER
MAX-ACCESS read-write
STATUS current
DESCRIPTION
"Data value."
::= { dataArray10 99 }

dataValue10_100 OBJECT-TYPE
SYNTAX INTEGER
MAX-ACCESS read-write
STATUS current
DESCRIPTION
"Data value."
::= { dataArray10 100 }

dataValue10_101 OBJECT-TYPE
SYNTAX INTEGER
MAX-ACCESS read-write
STATUS current
DESCRIPTION
"Data value."
::= { dataArray10 101 }

dataValue10_102 OBJECT-TYPE
SYNTAX INTEGER
MAX-ACCESS read-write
STATUS current
DESCRIPTION
"Data value."
::= { dataArray10 102 }

dataValue10_103 OBJECT-TYPE
SYNTAX INTEGER
MAX-ACCESS read-write
STATUS current
DESCRIPTION
"Data value."
::= { dataArray10 103 }

dataValue10_104 OBJECT-TYPE
SYNTAX INTEGER
MAX-ACCESS read-write
STATUS current
DESCRIPTION
"Data value."
::= { dataArray10 104 }

dataValue10_105 OBJECT-TYPE
SYNTAX INTEGER
MAX-ACCESS read-write
STATUS current
DESCRIPTION
"Data value."
::= { dataArray10 105 }

dataValue10_106 OBJECT-TYPE
SYNTAX INTEGER
MAX-ACCESS read-write
STATUS current
DESCRIPTION
"Data value."
::= { dataArray10 106 }

dataValue10_107 OBJECT-TYPE
SYNTAX INTEGER
MAX-ACCESS read-write
STATUS current
DESCRIPTION
"Data value."
::= { dataArray10 107 }

dataValue10_108 OBJECT-TYPE
SYNTAX INTEGER
MAX-ACCESS read-write
STATUS current
DESCRIPTION
"Data value."
::= { dataArray10 108 }

dataValue10_109 OBJECT-TYPE
SYNTAX INTEGER
MAX-ACCESS read-write
STATUS current
DESCRIPTION
"Data value."
::= { dataArray10 109 }

dataValue10_110 OBJECT-TYPE
SYNTAX INTEGER
MAX-ACCESS read-write
STATUS current
DESCRIPTION
"Data value."
::= { dataArray10 110 }

dataValue10_111 OBJECT-TYPE
SYNTAX INTEGER
MAX-ACCESS read-write
STATUS current
DESCRIPTION
"Data value."
::= { dataArray10 111 }

dataValue10_112 OBJECT-TYPE
SYNTAX INTEGER
MAX-ACCESS read-write
STATUS current
DESCRIPTION
"Data value."
::= { dataArray10 112 }

dataValue10_113 OBJECT-TYPE
SYNTAX INTEGER
MAX-ACCESS read-write
STATUS current
DESCRIPTION
"Data value."
::= { dataArray10 113 }

dataValue10_114 OBJECT-TYPE
SYNTAX INTEGER
MAX-ACCESS read-write
STATUS current
DESCRIPTION
"Data value."
::= { dataArray10 114 }

dataValue10_115 OBJECT-TYPE
SYNTAX INTEGER
MAX-ACCESS read-write
STATUS current
DESCRIPTION
"Data value."
::= { dataArray10 115 }

dataValue10_116 OBJECT-TYPE
SYNTAX INTEGER
MAX-ACCESS read-write
STATUS current
DESCRIPTION
"Data value."
::= { dataArray10 116 }

dataValue10_117 OBJECT-TYPE
SYNTAX INTEGER
MAX-ACCESS read-write
STATUS current
DESCRIPTION
"Data value."
::= { dataArray10 117 }

dataValue10_118 OBJECT-TYPE
SYNTAX INTEGER
MAX-ACCESS read-write
STATUS current
DESCRIPTION
"Data value."
::= { dataArray10 118 }

dataValue10_119 OBJECT-TYPE
SYNTAX INTEGER
MAX-ACCESS read-write
STATUS current
DESCRIPTION
"Data value."
::= { dataArray10 119 }

dataValue10_120 OBJECT-TYPE
SYNTAX INTEGER
MAX-ACCESS read-write
STATUS current
DESCRIPTION
"Data value."
::= { dataArray10 120 }

dataValue10_121 OBJECT-TYPE
SYNTAX INTEGER
MAX-ACCESS read-write
STATUS current
DESCRIPTION
"Data value."
::= { dataArray10 121 }

dataValue10_122 OBJECT-TYPE
SYNTAX INTEGER
MAX-ACCESS read-write
STATUS current
DESCRIPTION
"Data value."
::= { dataArray10 122 }

dataValue10_123 OBJECT-TYPE
SYNTAX INTEGER
MAX-ACCESS read-write
STATUS current
DESCRIPTION
"Data value."
::= { dataArray10 123 }

dataValue10_124 OBJECT-TYPE
SYNTAX INTEGER
MAX-ACCESS read-write
STATUS current
DESCRIPTION
"Data value."
::= { dataArray10 124 }

dataValue10_125 OBJECT-TYPE
SYNTAX INTEGER
MAX-ACCESS read-write
STATUS current
DESCRIPTION
"Data value."
::= { dataArray10 125 }

dataValue10_126 OBJECT-TYPE
SYNTAX INTEGER
MAX-ACCESS read-write
STATUS current
DESCRIPTION
"Data value."
::= { dataArray10 126 }

dataValue10_127 OBJECT-TYPE
SYNTAX INTEGER
MAX-ACCESS read-write
STATUS current
DESCRIPTION
"Data value."
::= { dataArray10 127 }

dataValue10_128 OBJECT-TYPE
SYNTAX INTEGER
MAX-ACCESS read-write
STATUS current
DESCRIPTION
"Data value."
::= { dataArray10 128 }

dataValue10_129 OBJECT-TYPE
SYNTAX INTEGER
MAX-ACCESS read-write
STATUS current
DESCRIPTION
"Data value."
::= { dataArray10 129 }

dataValue10_130 OBJECT-TYPE
SYNTAX INTEGER
MAX-ACCESS read-write
STATUS current
DESCRIPTION
"Data value."
::= { dataArray10 130 }

dataValue10_131 OBJECT-TYPE
SYNTAX INTEGER
MAX-ACCESS read-write
STATUS current
DESCRIPTION
"Data value."
::= { dataArray10 131 }

dataValue10_132 OBJECT-TYPE
SYNTAX INTEGER
MAX-ACCESS read-write
STATUS current
DESCRIPTION
"Data value."
::= { dataArray10 132 }

dataValue10_133 OBJECT-TYPE
SYNTAX INTEGER
MAX-ACCESS read-write
STATUS current
DESCRIPTION
"Data value."
::= { dataArray10 133 }

dataValue10_134 OBJECT-TYPE
SYNTAX INTEGER
MAX-ACCESS read-write
STATUS current
DESCRIPTION
"Data value."
::= { dataArray10 134 }

dataValue10_135 OBJECT-TYPE
SYNTAX INTEGER
MAX-ACCESS read-write
STATUS current
DESCRIPTION
"Data value."
::= { dataArray10 135 }

dataValue10_136 OBJECT-TYPE
SYNTAX INTEGER
MAX-ACCESS read-write
STATUS current
DESCRIPTION
"Data value."
::= { dataArray10 136 }

dataValue10_137 OBJECT-TYPE
SYNTAX INTEGER
MAX-ACCESS read-write
STATUS current
DESCRIPTION
"Data value."
::= { dataArray10 137 }

dataValue10_138 OBJECT-TYPE
SYNTAX INTEGER
MAX-ACCESS read-write
STATUS current
DESCRIPTION
"Data value."
::= { dataArray10 138 }

dataValue10_139 OBJECT-TYPE
SYNTAX INTEGER
MAX-ACCESS read-write
STATUS current
DESCRIPTION
"Data value."
::= { dataArray10 139 }

dataValue10_140 OBJECT-TYPE
SYNTAX INTEGER
MAX-ACCESS read-write
STATUS current
DESCRIPTION
"Data value."
::= { dataArray10 140 }

dataValue10_141 OBJECT-TYPE
SYNTAX INTEGER
MAX-ACCESS read-write
STATUS current
DESCRIPTION
"Data value."
::= { dataArray10 141 }

dataValue10_142 OBJECT-TYPE
SYNTAX INTEGER
MAX-ACCESS read-write
STATUS current
DESCRIPTION
"Data value."
::= { dataArray10 142 }

dataValue10_143 OBJECT-TYPE
SYNTAX INTEGER
MAX-ACCESS read-write
STATUS current
DESCRIPTION
"Data value."
::= { dataArray10 143 }

dataValue10_144 OBJECT-TYPE
SYNTAX INTEGER
MAX-ACCESS read-write
STATUS current
DESCRIPTION
"Data value."
::= { dataArray10 144 }

dataValue10_145 OBJECT-TYPE
SYNTAX INTEGER
MAX-ACCESS read-write
STATUS current
DESCRIPTION
"Data value."
::= { dataArray10 145 }

dataValue10_146 OBJECT-TYPE
SYNTAX INTEGER
MAX-ACCESS read-write
STATUS current
DESCRIPTION
"Data value."
::= { dataArray10 146 }

dataValue10_147 OBJECT-TYPE
SYNTAX INTEGER
MAX-ACCESS read-write
STATUS current
DESCRIPTION
"Data value."
::= { dataArray10 147 }

dataValue10_148 OBJECT-TYPE
SYNTAX INTEGER
MAX-ACCESS read-write
STATUS current
DESCRIPTION
"Data value."
::= { dataArray10 148 }

dataValue10_149 OBJECT-TYPE
SYNTAX INTEGER
MAX-ACCESS read-write
STATUS current
DESCRIPTION
"Data value."
::= { dataArray10 149 }

dataValue10_150 OBJECT-TYPE
SYNTAX INTEGER
MAX-ACCESS read-write
STATUS current
DESCRIPTION
"Data value."
::= { dataArray10 150 }

dataValue10_151 OBJECT-TYPE
SYNTAX INTEGER
MAX-ACCESS read-write
STATUS current
DESCRIPTION
"Data value."
::= { dataArray10 151 }

dataValue10_152 OBJECT-TYPE
SYNTAX INTEGER
MAX-ACCESS read-write
STATUS current
DESCRIPTION
"Data value."
::= { dataArray10 152 }

dataValue10_153 OBJECT-TYPE
SYNTAX INTEGER
MAX-ACCESS read-write
STATUS current
DESCRIPTION
"Data value."
::= { dataArray10 153 }

dataValue10_154 OBJECT-TYPE
SYNTAX INTEGER
MAX-ACCESS read-write
STATUS current
DESCRIPTION
"Data value."
::= { dataArray10 154 }

dataValue10_155 OBJECT-TYPE
SYNTAX INTEGER
MAX-ACCESS read-write
STATUS current
DESCRIPTION
"Data value."
::= { dataArray10 155 }

dataValue10_156 OBJECT-TYPE
SYNTAX INTEGER
MAX-ACCESS read-write
STATUS current
DESCRIPTION
"Data value."
::= { dataArray10 156 }

dataValue10_157 OBJECT-TYPE
SYNTAX INTEGER
MAX-ACCESS read-write
STATUS current
DESCRIPTION
"Data value."
::= { dataArray10 157 }

dataValue10_158 OBJECT-TYPE
SYNTAX INTEGER
MAX-ACCESS read-write
STATUS current
DESCRIPTION
"Data value."
::= { dataArray10 158 }

dataValue10_159 OBJECT-TYPE
SYNTAX INTEGER
MAX-ACCESS read-write
STATUS current
DESCRIPTION
"Data value."
::= { dataArray10 159 }

dataValue10_160 OBJECT-TYPE
SYNTAX INTEGER
MAX-ACCESS read-write
STATUS current
DESCRIPTION
"Data value."
::= { dataArray10 160 }

dataValue10_161 OBJECT-TYPE
SYNTAX INTEGER
MAX-ACCESS read-write
STATUS current
DESCRIPTION
"Data value."
::= { dataArray10 161 }

dataValue10_162 OBJECT-TYPE
SYNTAX INTEGER
MAX-ACCESS read-write
STATUS current
DESCRIPTION
"Data value."
::= { dataArray10 162 }

dataValue10_163 OBJECT-TYPE
SYNTAX INTEGER
MAX-ACCESS read-write
STATUS current
DESCRIPTION
"Data value."
::= { dataArray10 163 }

dataValue10_164 OBJECT-TYPE
SYNTAX INTEGER
MAX-ACCESS read-write
STATUS current
DESCRIPTION
"Data value."
::= { dataArray10 164 }

dataValue10_165 OBJECT-TYPE
SYNTAX INTEGER
MAX-ACCESS read-write
STATUS current
DESCRIPTION
"Data value."
::= { dataArray10 165 }

dataValue10_166 OBJECT-TYPE
SYNTAX INTEGER
MAX-ACCESS read-write
STATUS current
DESCRIPTION
"Data value."
::= { dataArray10 166 }

dataValue10_167 OBJECT-TYPE
SYNTAX INTEGER
MAX-ACCESS read-write
STATUS current
DESCRIPTION
"Data value."
::= { dataArray10 167 }

dataValue10_168 OBJECT-TYPE
SYNTAX INTEGER
MAX-ACCESS read-write
STATUS current
DESCRIPTION
"Data value."
::= { dataArray10 168 }

dataValue10_169 OBJECT-TYPE
SYNTAX INTEGER
MAX-ACCESS read-write
STATUS current
DESCRIPTION
"Data value."
::= { dataArray10 169 }

dataValue10_170 OBJECT-TYPE
SYNTAX INTEGER
MAX-ACCESS read-write
STATUS current
DESCRIPTION
"Data value."
::= { dataArray10 170 }

dataValue10_171 OBJECT-TYPE
SYNTAX INTEGER
MAX-ACCESS read-write
STATUS current
DESCRIPTION
"Data value."
::= { dataArray10 171 }

dataValue10_172 OBJECT-TYPE
SYNTAX INTEGER
MAX-ACCESS read-write
STATUS current
DESCRIPTION
"Data value."
::= { dataArray10 172 }

dataValue10_173 OBJECT-TYPE
SYNTAX INTEGER
MAX-ACCESS read-write
STATUS current
DESCRIPTION
"Data value."
::= { dataArray10 173 }

dataValue10_174 OBJECT-TYPE
SYNTAX INTEGER
MAX-ACCESS read-write
STATUS current
DESCRIPTION
"Data value."
::= { dataArray10 174 }

dataValue10_175 OBJECT-TYPE
SYNTAX INTEGER
MAX-ACCESS read-write
STATUS current
DESCRIPTION
"Data value."
::= { dataArray10 175 }

dataValue10_176 OBJECT-TYPE
SYNTAX INTEGER
MAX-ACCESS read-write
STATUS current
DESCRIPTION
"Data value."
::= { dataArray10 176 }

dataValue10_177 OBJECT-TYPE
SYNTAX INTEGER
MAX-ACCESS read-write
STATUS current
DESCRIPTION
"Data value."
::= { dataArray10 177 }

dataValue10_178 OBJECT-TYPE
SYNTAX INTEGER
MAX-ACCESS read-write
STATUS current
DESCRIPTION
"Data value."
::= { dataArray10 178 }

dataValue10_179 OBJECT-TYPE
SYNTAX INTEGER
MAX-ACCESS read-write
STATUS current
DESCRIPTION
"Data value."
::= { dataArray10 179 }

dataValue10_180 OBJECT-TYPE
SYNTAX INTEGER
MAX-ACCESS read-write
STATUS current
DESCRIPTION
"Data value."
::= { dataArray10 180 }

dataValue10_181 OBJECT-TYPE
SYNTAX INTEGER
MAX-ACCESS read-write
STATUS current
DESCRIPTION
"Data value."
::= { dataArray10 181 }

dataValue10_182 OBJECT-TYPE
SYNTAX INTEGER
MAX-ACCESS read-write
STATUS current
DESCRIPTION
"Data value."
::= { dataArray10 182 }

dataValue10_183 OBJECT-TYPE
SYNTAX INTEGER
MAX-ACCESS read-write
STATUS current
DESCRIPTION
"Data value."
::= { dataArray10 183 }

dataValue10_184 OBJECT-TYPE
SYNTAX INTEGER
MAX-ACCESS read-write
STATUS current
DESCRIPTION
"Data value."
::= { dataArray10 184 }

dataValue10_185 OBJECT-TYPE
SYNTAX INTEGER
MAX-ACCESS read-write
STATUS current
DESCRIPTION
"Data value."
::= { dataArray10 185 }

dataValue10_186 OBJECT-TYPE
SYNTAX INTEGER
MAX-ACCESS read-write
STATUS current
DESCRIPTION
"Data value."
::= { dataArray10 186 }

dataValue10_187 OBJECT-TYPE
SYNTAX INTEGER
MAX-ACCESS read-write
STATUS current
DESCRIPTION
"Data value."
::= { dataArray10 187 }

dataValue10_188 OBJECT-TYPE
SYNTAX INTEGER
MAX-ACCESS read-write
STATUS current
DESCRIPTION
"Data value."
::= { dataArray10 188 }

dataValue10_189 OBJECT-TYPE
SYNTAX INTEGER
MAX-ACCESS read-write
STATUS current
DESCRIPTION
"Data value."
::= { dataArray10 189 }

dataValue10_190 OBJECT-TYPE
SYNTAX INTEGER
MAX-ACCESS read-write
STATUS current
DESCRIPTION
"Data value."
::= { dataArray10 190 }

dataValue10_191 OBJECT-TYPE
SYNTAX INTEGER
MAX-ACCESS read-write
STATUS current
DESCRIPTION
"Data value."
::= { dataArray10 191 }

dataValue10_192 OBJECT-TYPE
SYNTAX INTEGER
MAX-ACCESS read-write
STATUS current
DESCRIPTION
"Data value."
::= { dataArray10 192 }

dataValue10_193 OBJECT-TYPE
SYNTAX INTEGER
MAX-ACCESS read-write
STATUS current
DESCRIPTION
"Data value."
::= { dataArray10 193 }

dataValue10_194 OBJECT-TYPE
SYNTAX INTEGER
MAX-ACCESS read-write
STATUS current
DESCRIPTION
"Data value."
::= { dataArray10 194 }

dataValue10_195 OBJECT-TYPE
SYNTAX INTEGER
MAX-ACCESS read-write
STATUS current
DESCRIPTION
"Data value."
::= { dataArray10 195 }

dataValue10_196 OBJECT-TYPE
SYNTAX INTEGER
MAX-ACCESS read-write
STATUS current
DESCRIPTION
"Data value."
::= { dataArray10 196 }

dataValue10_197 OBJECT-TYPE
SYNTAX INTEGER
MAX-ACCESS read-write
STATUS current
DESCRIPTION
"Data value."
::= { dataArray10 197 }

dataValue10_198 OBJECT-TYPE
SYNTAX INTEGER
MAX-ACCESS read-write
STATUS current
DESCRIPTION
"Data value."
::= { dataArray10 198 }

dataValue10_199 OBJECT-TYPE
SYNTAX INTEGER
MAX-ACCESS read-write
STATUS current
DESCRIPTION
"Data value."
::= { dataArray10 199 }

dataValue10_200 OBJECT-TYPE
SYNTAX INTEGER
MAX-ACCESS read-write
STATUS current
DESCRIPTION
"Data value."
::= { dataArray10 200 }

dataValue10_201 OBJECT-TYPE
SYNTAX INTEGER
MAX-ACCESS read-write
STATUS current
DESCRIPTION
"Data value."
::= { dataArray10 201 }

dataValue10_202 OBJECT-TYPE
SYNTAX INTEGER
MAX-ACCESS read-write
STATUS current
DESCRIPTION
"Data value."
::= { dataArray10 202 }

dataValue10_203 OBJECT-TYPE
SYNTAX INTEGER
MAX-ACCESS read-write
STATUS current
DESCRIPTION
"Data value."
::= { dataArray10 203 }

dataValue10_204 OBJECT-TYPE
SYNTAX INTEGER
MAX-ACCESS read-write
STATUS current
DESCRIPTION
"Data value."
::= { dataArray10 204 }

dataValue10_205 OBJECT-TYPE
SYNTAX INTEGER
MAX-ACCESS read-write
STATUS current
DESCRIPTION
"Data value."
::= { dataArray10 205 }

dataValue10_206 OBJECT-TYPE
SYNTAX INTEGER
MAX-ACCESS read-write
STATUS current
DESCRIPTION
"Data value."
::= { dataArray10 206 }

dataValue10_207 OBJECT-TYPE
SYNTAX INTEGER
MAX-ACCESS read-write
STATUS current
DESCRIPTION
"Data value."
::= { dataArray10 207 }

dataValue10_208 OBJECT-TYPE
SYNTAX INTEGER
MAX-ACCESS read-write
STATUS current
DESCRIPTION
"Data value."
::= { dataArray10 208 }

dataValue10_209 OBJECT-TYPE
SYNTAX INTEGER
MAX-ACCESS read-write
STATUS current
DESCRIPTION
"Data value."
::= { dataArray10 209 }

dataValue10_210 OBJECT-TYPE
SYNTAX INTEGER
MAX-ACCESS read-write
STATUS current
DESCRIPTION
"Data value."
::= { dataArray10 210 }

dataValue10_211 OBJECT-TYPE
SYNTAX INTEGER
MAX-ACCESS read-write
STATUS current
DESCRIPTION
"Data value."
::= { dataArray10 211 }

dataValue10_212 OBJECT-TYPE
SYNTAX INTEGER
MAX-ACCESS read-write
STATUS current
DESCRIPTION
"Data value."
::= { dataArray10 212 }

dataValue10_213 OBJECT-TYPE
SYNTAX INTEGER
MAX-ACCESS read-write
STATUS current
DESCRIPTION
"Data value."
::= { dataArray10 213 }

dataValue10_214 OBJECT-TYPE
SYNTAX INTEGER
MAX-ACCESS read-write
STATUS current
DESCRIPTION
"Data value."
::= { dataArray10 214 }

dataValue10_215 OBJECT-TYPE
SYNTAX INTEGER
MAX-ACCESS read-write
STATUS current
DESCRIPTION
"Data value."
::= { dataArray10 215 }

dataValue10_216 OBJECT-TYPE
SYNTAX INTEGER
MAX-ACCESS read-write
STATUS current
DESCRIPTION
"Data value."
::= { dataArray10 216 }

dataValue10_217 OBJECT-TYPE
SYNTAX INTEGER
MAX-ACCESS read-write
STATUS current
DESCRIPTION
"Data value."
::= { dataArray10 217 }

dataValue10_218 OBJECT-TYPE
SYNTAX INTEGER
MAX-ACCESS read-write
STATUS current
DESCRIPTION
"Data value."
::= { dataArray10 218 }

dataValue10_219 OBJECT-TYPE
SYNTAX INTEGER
MAX-ACCESS read-write
STATUS current
DESCRIPTION
"Data value."
::= { dataArray10 219 }

dataValue10_220 OBJECT-TYPE
SYNTAX INTEGER
MAX-ACCESS read-write
STATUS current
DESCRIPTION
"Data value."
::= { dataArray10 220 }

dataValue10_221 OBJECT-TYPE
SYNTAX INTEGER
MAX-ACCESS read-write
STATUS current
DESCRIPTION
"Data value."
::= { dataArray10 221 }

dataValue10_222 OBJECT-TYPE
SYNTAX INTEGER
MAX-ACCESS read-write
STATUS current
DESCRIPTION
"Data value."
::= { dataArray10 222 }

dataValue10_223 OBJECT-TYPE
SYNTAX INTEGER
MAX-ACCESS read-write
STATUS current
DESCRIPTION
"Data value."
::= { dataArray10 223 }

dataValue10_224 OBJECT-TYPE
SYNTAX INTEGER
MAX-ACCESS read-write
STATUS current
DESCRIPTION
"Data value."
::= { dataArray10 224 }

dataValue10_225 OBJECT-TYPE
SYNTAX INTEGER
MAX-ACCESS read-write
STATUS current
DESCRIPTION
"Data value."
::= { dataArray10 225 }

dataValue10_226 OBJECT-TYPE
SYNTAX INTEGER
MAX-ACCESS read-write
STATUS current
DESCRIPTION
"Data value."
::= { dataArray10 226 }

dataValue10_227 OBJECT-TYPE
SYNTAX INTEGER
MAX-ACCESS read-write
STATUS current
DESCRIPTION
"Data value."
::= { dataArray10 227 }

dataValue10_228 OBJECT-TYPE
SYNTAX INTEGER
MAX-ACCESS read-write
STATUS current
DESCRIPTION
"Data value."
::= { dataArray10 228 }

dataValue10_229 OBJECT-TYPE
SYNTAX INTEGER
MAX-ACCESS read-write
STATUS current
DESCRIPTION
"Data value."
::= { dataArray10 229 }

dataValue10_230 OBJECT-TYPE
SYNTAX INTEGER
MAX-ACCESS read-write
STATUS current
DESCRIPTION
"Data value."
::= { dataArray10 230 }

dataValue10_231 OBJECT-TYPE
SYNTAX INTEGER
MAX-ACCESS read-write
STATUS current
DESCRIPTION
"Data value."
::= { dataArray10 231 }

dataValue10_232 OBJECT-TYPE
SYNTAX INTEGER
MAX-ACCESS read-write
STATUS current
DESCRIPTION
"Data value."
::= { dataArray10 232 }

dataValue10_233 OBJECT-TYPE
SYNTAX INTEGER
MAX-ACCESS read-write
STATUS current
DESCRIPTION
"Data value."
::= { dataArray10 233 }

dataValue10_234 OBJECT-TYPE
SYNTAX INTEGER
MAX-ACCESS read-write
STATUS current
DESCRIPTION
"Data value."
::= { dataArray10 234 }

dataValue10_235 OBJECT-TYPE
SYNTAX INTEGER
MAX-ACCESS read-write
STATUS current
DESCRIPTION
"Data value."
::= { dataArray10 235 }

dataValue10_236 OBJECT-TYPE
SYNTAX INTEGER
MAX-ACCESS read-write
STATUS current
DESCRIPTION
"Data value."
::= { dataArray10 236 }

dataValue10_237 OBJECT-TYPE
SYNTAX INTEGER
MAX-ACCESS read-write
STATUS current
DESCRIPTION
"Data value."
::= { dataArray10 237 }

dataValue10_238 OBJECT-TYPE
SYNTAX INTEGER
MAX-ACCESS read-write
STATUS current
DESCRIPTION
"Data value."
::= { dataArray10 238 }

dataValue10_239 OBJECT-TYPE
SYNTAX INTEGER
MAX-ACCESS read-write
STATUS current
DESCRIPTION
"Data value."
::= { dataArray10 239 }

dataValue10_240 OBJECT-TYPE
SYNTAX INTEGER
MAX-ACCESS read-write
STATUS current
DESCRIPTION
"Data value."
::= { dataArray10 240 }

dataValue10_241 OBJECT-TYPE
SYNTAX INTEGER
MAX-ACCESS read-write
STATUS current
DESCRIPTION
"Data value."
::= { dataArray10 241 }

dataValue10_242 OBJECT-TYPE
SYNTAX INTEGER
MAX-ACCESS read-write
STATUS current
DESCRIPTION
"Data value."
::= { dataArray10 242 }

dataValue10_243 OBJECT-TYPE
SYNTAX INTEGER
MAX-ACCESS read-write
STATUS current
DESCRIPTION
"Data value."
::= { dataArray10 243 }

dataValue10_244 OBJECT-TYPE
SYNTAX INTEGER
MAX-ACCESS read-write
STATUS current
DESCRIPTION
"Data value."
::= { dataArray10 244 }

dataValue10_245 OBJECT-TYPE
SYNTAX INTEGER
MAX-ACCESS read-write
STATUS current
DESCRIPTION
"Data value."
::= { dataArray10 245 }

dataValue10_246 OBJECT-TYPE
SYNTAX INTEGER
MAX-ACCESS read-write
STATUS current
DESCRIPTION
"Data value."
::= { dataArray10 246 }

dataValue10_247 OBJECT-TYPE
SYNTAX INTEGER
MAX-ACCESS read-write
STATUS current
DESCRIPTION
"Data value."
::= { dataArray10 247 }

dataValue10_248 OBJECT-TYPE
SYNTAX INTEGER
MAX-ACCESS read-write
STATUS current
DESCRIPTION
"Data value."
::= { dataArray10 248 }

dataValue10_249 OBJECT-TYPE
SYNTAX INTEGER
MAX-ACCESS read-write
STATUS current
DESCRIPTION
"Data value."
::= { dataArray10 249 }

dataValue10_250 OBJECT-TYPE
SYNTAX INTEGER
MAX-ACCESS read-write
STATUS current
DESCRIPTION
"Data value."
::= { dataArray10 250 }

dataValue10_251 OBJECT-TYPE
SYNTAX INTEGER
MAX-ACCESS read-write
STATUS current
DESCRIPTION
"Data value."
::= { dataArray10 251 }

dataValue10_252 OBJECT-TYPE
SYNTAX INTEGER
MAX-ACCESS read-write
STATUS current
DESCRIPTION
"Data value."
::= { dataArray10 252 }

dataValue10_253 OBJECT-TYPE
SYNTAX INTEGER
MAX-ACCESS read-write
STATUS current
DESCRIPTION
"Data value."
::= { dataArray10 253 }

dataValue10_254 OBJECT-TYPE
SYNTAX INTEGER
MAX-ACCESS read-write
STATUS current
DESCRIPTION
"Data value."
::= { dataArray10 254 }

dataValue10_255 OBJECT-TYPE
SYNTAX INTEGER
MAX-ACCESS read-write
STATUS current
DESCRIPTION
"Data value."
::= { dataArray10 255 }

dataValue10_256 OBJECT-TYPE
SYNTAX INTEGER
MAX-ACCESS read-write
STATUS current
DESCRIPTION
"Data value."
::= { dataArray10 256 }

dataValue10_257 OBJECT-TYPE
SYNTAX INTEGER
MAX-ACCESS read-write
STATUS current
DESCRIPTION
"Data value."
::= { dataArray10 257 }

dataValue10_258 OBJECT-TYPE
SYNTAX INTEGER
MAX-ACCESS read-write
STATUS current
DESCRIPTION
"Data value."
::= { dataArray10 258 }

dataValue10_259 OBJECT-TYPE
SYNTAX INTEGER
MAX-ACCESS read-write
STATUS current
DESCRIPTION
"Data value."
::= { dataArray10 259 }

dataValue10_260 OBJECT-TYPE
SYNTAX INTEGER
MAX-ACCESS read-write
STATUS current
DESCRIPTION
"Data value."
::= { dataArray10 260 }

dataValue10_261 OBJECT-TYPE
SYNTAX INTEGER
MAX-ACCESS read-write
STATUS current
DESCRIPTION
"Data value."
::= { dataArray10 261 }

dataValue10_262 OBJECT-TYPE
SYNTAX INTEGER
MAX-ACCESS read-write
STATUS current
DESCRIPTION
"Data value."
::= { dataArray10 262 }

dataValue10_263 OBJECT-TYPE
SYNTAX INTEGER
MAX-ACCESS read-write
STATUS current
DESCRIPTION
"Data value."
::= { dataArray10 263 }

dataValue10_264 OBJECT-TYPE
SYNTAX INTEGER
MAX-ACCESS read-write
STATUS current
DESCRIPTION
"Data value."
::= { dataArray10 264 }

dataValue10_265 OBJECT-TYPE
SYNTAX INTEGER
MAX-ACCESS read-write
STATUS current
DESCRIPTION
"Data value."
::= { dataArray10 265 }

dataValue10_266 OBJECT-TYPE
SYNTAX INTEGER
MAX-ACCESS read-write
STATUS current
DESCRIPTION
"Data value."
::= { dataArray10 266 }

dataValue10_267 OBJECT-TYPE
SYNTAX INTEGER
MAX-ACCESS read-write
STATUS current
DESCRIPTION
"Data value."
::= { dataArray10 267 }

dataValue10_268 OBJECT-TYPE
SYNTAX INTEGER
MAX-ACCESS read-write
STATUS current
DESCRIPTION
"Data value."
::= { dataArray10 268 }

dataValue10_269 OBJECT-TYPE
SYNTAX INTEGER
MAX-ACCESS read-write
STATUS current
DESCRIPTION
"Data value."
::= { dataArray10 269 }

dataValue10_270 OBJECT-TYPE
SYNTAX INTEGER
MAX-ACCESS read-write
STATUS current
DESCRIPTION
"Data value."
::= { dataArray10 270 }

dataValue10_271 OBJECT-TYPE
SYNTAX INTEGER
MAX-ACCESS read-write
STATUS current
DESCRIPTION
"Data value."
::= { dataArray10 271 }

dataValue10_272 OBJECT-TYPE
SYNTAX INTEGER
MAX-ACCESS read-write
STATUS current
DESCRIPTION
"Data value."
::= { dataArray10 272 }

dataValue10_273 OBJECT-TYPE
SYNTAX INTEGER
MAX-ACCESS read-write
STATUS current
DESCRIPTION
"Data value."
::= { dataArray10 273 }

dataValue10_274 OBJECT-TYPE
SYNTAX INTEGER
MAX-ACCESS read-write
STATUS current
DESCRIPTION
"Data value."
::= { dataArray10 274 }

dataValue10_275 OBJECT-TYPE
SYNTAX INTEGER
MAX-ACCESS read-write
STATUS current
DESCRIPTION
"Data value."
::= { dataArray10 275 }

dataValue10_276 OBJECT-TYPE
SYNTAX INTEGER
MAX-ACCESS read-write
STATUS current
DESCRIPTION
"Data value."
::= { dataArray10 276 }

dataValue10_277 OBJECT-TYPE
SYNTAX INTEGER
MAX-ACCESS read-write
STATUS current
DESCRIPTION
"Data value."
::= { dataArray10 277 }

dataValue10_278 OBJECT-TYPE
SYNTAX INTEGER
MAX-ACCESS read-write
STATUS current
DESCRIPTION
"Data value."
::= { dataArray10 278 }

dataValue10_279 OBJECT-TYPE
SYNTAX INTEGER
MAX-ACCESS read-write
STATUS current
DESCRIPTION
"Data value."
::= { dataArray10 279 }

dataValue10_280 OBJECT-TYPE
SYNTAX INTEGER
MAX-ACCESS read-write
STATUS current
DESCRIPTION
"Data value."
::= { dataArray10 280 }

dataValue10_281 OBJECT-TYPE
SYNTAX INTEGER
MAX-ACCESS read-write
STATUS current
DESCRIPTION
"Data value."
::= { dataArray10 281 }

dataValue10_282 OBJECT-TYPE
SYNTAX INTEGER
MAX-ACCESS read-write
STATUS current
DESCRIPTION
"Data value."
::= { dataArray10 282 }

dataValue10_283 OBJECT-TYPE
SYNTAX INTEGER
MAX-ACCESS read-write
STATUS current
DESCRIPTION
"Data value."
::= { dataArray10 283 }

dataValue10_284 OBJECT-TYPE
SYNTAX INTEGER
MAX-ACCESS read-write
STATUS current
DESCRIPTION
"Data value."
::= { dataArray10 284 }

dataValue10_285 OBJECT-TYPE
SYNTAX INTEGER
MAX-ACCESS read-write
STATUS current
DESCRIPTION
"Data value."
::= { dataArray10 285 }

dataValue10_286 OBJECT-TYPE
SYNTAX INTEGER
MAX-ACCESS read-write
STATUS current
DESCRIPTION
"Data value."
::= { dataArray10 286 }

dataValue10_287 OBJECT-TYPE
SYNTAX INTEGER
MAX-ACCESS read-write
STATUS current
DESCRIPTION
"Data value."
::= { dataArray10 287 }

dataValue10_288 OBJECT-TYPE
SYNTAX INTEGER
MAX-ACCESS read-write
STATUS current
DESCRIPTION
"Data value."
::= { dataArray10 288 }

dataValue10_289 OBJECT-TYPE
SYNTAX INTEGER
MAX-ACCESS read-write
STATUS current
DESCRIPTION
"Data value."
::= { dataArray10 289 }

dataValue10_290 OBJECT-TYPE
SYNTAX INTEGER
MAX-ACCESS read-write
STATUS current
DESCRIPTION
"Data value."
::= { dataArray10 290 }

dataValue10_291 OBJECT-TYPE
SYNTAX INTEGER
MAX-ACCESS read-write
STATUS current
DESCRIPTION
"Data value."
::= { dataArray10 291 }

dataValue10_292 OBJECT-TYPE
SYNTAX INTEGER
MAX-ACCESS read-write
STATUS current
DESCRIPTION
"Data value."
::= { dataArray10 292 }

dataValue10_293 OBJECT-TYPE
SYNTAX INTEGER
MAX-ACCESS read-write
STATUS current
DESCRIPTION
"Data value."
::= { dataArray10 293 }

dataValue10_294 OBJECT-TYPE
SYNTAX INTEGER
MAX-ACCESS read-write
STATUS current
DESCRIPTION
"Data value."
::= { dataArray10 294 }

dataValue10_295 OBJECT-TYPE
SYNTAX INTEGER
MAX-ACCESS read-write
STATUS current
DESCRIPTION
"Data value."
::= { dataArray10 295 }

dataValue10_296 OBJECT-TYPE
SYNTAX INTEGER
MAX-ACCESS read-write
STATUS current
DESCRIPTION
"Data value."
::= { dataArray10 296 }

dataValue10_297 OBJECT-TYPE
SYNTAX INTEGER
MAX-ACCESS read-write
STATUS current
DESCRIPTION
"Data value."
::= { dataArray10 297 }

dataValue10_298 OBJECT-TYPE
SYNTAX INTEGER
MAX-ACCESS read-write
STATUS current
DESCRIPTION
"Data value."
::= { dataArray10 298 }

dataValue10_299 OBJECT-TYPE
SYNTAX INTEGER
MAX-ACCESS read-write
STATUS current
DESCRIPTION
"Data value."
::= { dataArray10 299 }

dataValue10_300 OBJECT-TYPE
SYNTAX INTEGER
MAX-ACCESS read-write
STATUS current
DESCRIPTION
"Data value."
::= { dataArray10 300 }

dataValue10_301 OBJECT-TYPE
SYNTAX INTEGER
MAX-ACCESS read-write
STATUS current
DESCRIPTION
"Data value."
::= { dataArray10 301 }

dataValue10_302 OBJECT-TYPE
SYNTAX INTEGER
MAX-ACCESS read-write
STATUS current
DESCRIPTION
"Data value."
::= { dataArray10 302 }

dataValue10_303 OBJECT-TYPE
SYNTAX INTEGER
MAX-ACCESS read-write
STATUS current
DESCRIPTION
"Data value."
::= { dataArray10 303 }

dataValue10_304 OBJECT-TYPE
SYNTAX INTEGER
MAX-ACCESS read-write
STATUS current
DESCRIPTION
"Data value."
::= { dataArray10 304 }

dataValue10_305 OBJECT-TYPE
SYNTAX INTEGER
MAX-ACCESS read-write
STATUS current
DESCRIPTION
"Data value."
::= { dataArray10 305 }

dataValue10_306 OBJECT-TYPE
SYNTAX INTEGER
MAX-ACCESS read-write
STATUS current
DESCRIPTION
"Data value."
::= { dataArray10 306 }

dataValue10_307 OBJECT-TYPE
SYNTAX INTEGER
MAX-ACCESS read-write
STATUS current
DESCRIPTION
"Data value."
::= { dataArray10 307 }

dataValue10_308 OBJECT-TYPE
SYNTAX INTEGER
MAX-ACCESS read-write
STATUS current
DESCRIPTION
"Data value."
::= { dataArray10 308 }

dataValue10_309 OBJECT-TYPE
SYNTAX INTEGER
MAX-ACCESS read-write
STATUS current
DESCRIPTION
"Data value."
::= { dataArray10 309 }

dataValue10_310 OBJECT-TYPE
SYNTAX INTEGER
MAX-ACCESS read-write
STATUS current
DESCRIPTION
"Data value."
::= { dataArray10 310 }

dataValue10_311 OBJECT-TYPE
SYNTAX INTEGER
MAX-ACCESS read-write
STATUS current
DESCRIPTION
"Data value."
::= { dataArray10 311 }

dataValue10_312 OBJECT-TYPE
SYNTAX INTEGER
MAX-ACCESS read-write
STATUS current
DESCRIPTION
"Data value."
::= { dataArray10 312 }

dataValue10_313 OBJECT-TYPE
SYNTAX INTEGER
MAX-ACCESS read-write
STATUS current
DESCRIPTION
"Data value."
::= { dataArray10 313 }

dataValue10_314 OBJECT-TYPE
SYNTAX INTEGER
MAX-ACCESS read-write
STATUS current
DESCRIPTION
"Data value."
::= { dataArray10 314 }

dataValue10_315 OBJECT-TYPE
SYNTAX INTEGER
MAX-ACCESS read-write
STATUS current
DESCRIPTION
"Data value."
::= { dataArray10 315 }

dataValue10_316 OBJECT-TYPE
SYNTAX INTEGER
MAX-ACCESS read-write
STATUS current
DESCRIPTION
"Data value."
::= { dataArray10 316 }

dataValue10_317 OBJECT-TYPE
SYNTAX INTEGER
MAX-ACCESS read-write
STATUS current
DESCRIPTION
"Data value."
::= { dataArray10 317 }

dataValue10_318 OBJECT-TYPE
SYNTAX INTEGER
MAX-ACCESS read-write
STATUS current
DESCRIPTION
"Data value."
::= { dataArray10 318 }

dataValue10_319 OBJECT-TYPE
SYNTAX INTEGER
MAX-ACCESS read-write
STATUS current
DESCRIPTION
"Data value."
::= { dataArray10 319 }

dataValue10_320 OBJECT-TYPE
SYNTAX INTEGER
MAX-ACCESS read-write
STATUS current
DESCRIPTION
"Data value."
::= { dataArray10 320 }

dataValue10_321 OBJECT-TYPE
SYNTAX INTEGER
MAX-ACCESS read-write
STATUS current
DESCRIPTION
"Data value."
::= { dataArray10 321 }

dataValue10_322 OBJECT-TYPE
SYNTAX INTEGER
MAX-ACCESS read-write
STATUS current
DESCRIPTION
"Data value."
::= { dataArray10 322 }

dataValue10_323 OBJECT-TYPE
SYNTAX INTEGER
MAX-ACCESS read-write
STATUS current
DESCRIPTION
"Data value."
::= { dataArray10 323 }

dataValue10_324 OBJECT-TYPE
SYNTAX INTEGER
MAX-ACCESS read-write
STATUS current
DESCRIPTION
"Data value."
::= { dataArray10 324 }

dataValue10_325 OBJECT-TYPE
SYNTAX INTEGER
MAX-ACCESS read-write
STATUS current
DESCRIPTION
"Data value."
::= { dataArray10 325 }

dataValue10_326 OBJECT-TYPE
SYNTAX INTEGER
MAX-ACCESS read-write
STATUS current
DESCRIPTION
"Data value."
::= { dataArray10 326 }

dataValue10_327 OBJECT-TYPE
SYNTAX INTEGER
MAX-ACCESS read-write
STATUS current
DESCRIPTION
"Data value."
::= { dataArray10 327 }

dataValue10_328 OBJECT-TYPE
SYNTAX INTEGER
MAX-ACCESS read-write
STATUS current
DESCRIPTION
"Data value."
::= { dataArray10 328 }

dataValue10_329 OBJECT-TYPE
SYNTAX INTEGER
MAX-ACCESS read-write
STATUS current
DESCRIPTION
"Data value."
::= { dataArray10 329 }

dataValue10_330 OBJECT-TYPE
SYNTAX INTEGER
MAX-ACCESS read-write
STATUS current
DESCRIPTION
"Data value."
::= { dataArray10 330 }

dataValue10_331 OBJECT-TYPE
SYNTAX INTEGER
MAX-ACCESS read-write
STATUS current
DESCRIPTION
"Data value."
::= { dataArray10 331 }

dataValue10_332 OBJECT-TYPE
SYNTAX INTEGER
MAX-ACCESS read-write
STATUS current
DESCRIPTION
"Data value."
::= { dataArray10 332 }

dataValue10_333 OBJECT-TYPE
SYNTAX INTEGER
MAX-ACCESS read-write
STATUS current
DESCRIPTION
"Data value."
::= { dataArray10 333 }

dataValue10_334 OBJECT-TYPE
SYNTAX INTEGER
MAX-ACCESS read-write
STATUS current
DESCRIPTION
"Data value."
::= { dataArray10 334 }

dataValue10_335 OBJECT-TYPE
SYNTAX INTEGER
MAX-ACCESS read-write
STATUS current
DESCRIPTION
"Data value."
::= { dataArray10 335 }

dataValue10_336 OBJECT-TYPE
SYNTAX INTEGER
MAX-ACCESS read-write
STATUS current
DESCRIPTION
"Data value."
::= { dataArray10 336 }

dataValue10_337 OBJECT-TYPE
SYNTAX INTEGER
MAX-ACCESS read-write
STATUS current
DESCRIPTION
"Data value."
::= { dataArray10 337 }

dataValue10_338 OBJECT-TYPE
SYNTAX INTEGER
MAX-ACCESS read-write
STATUS current
DESCRIPTION
"Data value."
::= { dataArray10 338 }

dataValue10_339 OBJECT-TYPE
SYNTAX INTEGER
MAX-ACCESS read-write
STATUS current
DESCRIPTION
"Data value."
::= { dataArray10 339 }

dataValue10_340 OBJECT-TYPE
SYNTAX INTEGER
MAX-ACCESS read-write
STATUS current
DESCRIPTION
"Data value."
::= { dataArray10 340 }

dataValue10_341 OBJECT-TYPE
SYNTAX INTEGER
MAX-ACCESS read-write
STATUS current
DESCRIPTION
"Data value."
::= { dataArray10 341 }

dataValue10_342 OBJECT-TYPE
SYNTAX INTEGER
MAX-ACCESS read-write
STATUS current
DESCRIPTION
"Data value."
::= { dataArray10 342 }

dataValue10_343 OBJECT-TYPE
SYNTAX INTEGER
MAX-ACCESS read-write
STATUS current
DESCRIPTION
"Data value."
::= { dataArray10 343 }

dataValue10_344 OBJECT-TYPE
SYNTAX INTEGER
MAX-ACCESS read-write
STATUS current
DESCRIPTION
"Data value."
::= { dataArray10 344 }

dataValue10_345 OBJECT-TYPE
SYNTAX INTEGER
MAX-ACCESS read-write
STATUS current
DESCRIPTION
"Data value."
::= { dataArray10 345 }

dataValue10_346 OBJECT-TYPE
SYNTAX INTEGER
MAX-ACCESS read-write
STATUS current
DESCRIPTION
"Data value."
::= { dataArray10 346 }

dataValue10_347 OBJECT-TYPE
SYNTAX INTEGER
MAX-ACCESS read-write
STATUS current
DESCRIPTION
"Data value."
::= { dataArray10 347 }

dataValue10_348 OBJECT-TYPE
SYNTAX INTEGER
MAX-ACCESS read-write
STATUS current
DESCRIPTION
"Data value."
::= { dataArray10 348 }

dataValue10_349 OBJECT-TYPE
SYNTAX INTEGER
MAX-ACCESS read-write
STATUS current
DESCRIPTION
"Data value."
::= { dataArray10 349 }

dataValue10_350 OBJECT-TYPE
SYNTAX INTEGER
MAX-ACCESS read-write
STATUS current
DESCRIPTION
"Data value."
::= { dataArray10 350 }

dataValue10_351 OBJECT-TYPE
SYNTAX INTEGER
MAX-ACCESS read-write
STATUS current
DESCRIPTION
"Data value."
::= { dataArray10 351 }

dataValue10_352 OBJECT-TYPE
SYNTAX INTEGER
MAX-ACCESS read-write
STATUS current
DESCRIPTION
"Data value."
::= { dataArray10 352 }

dataValue10_353 OBJECT-TYPE
SYNTAX INTEGER
MAX-ACCESS read-write
STATUS current
DESCRIPTION
"Data value."
::= { dataArray10 353 }

dataValue10_354 OBJECT-TYPE
SYNTAX INTEGER
MAX-ACCESS read-write
STATUS current
DESCRIPTION
"Data value."
::= { dataArray10 354 }

dataValue10_355 OBJECT-TYPE
SYNTAX INTEGER
MAX-ACCESS read-write
STATUS current
DESCRIPTION
"Data value."
::= { dataArray10 355 }

dataValue10_356 OBJECT-TYPE
SYNTAX INTEGER
MAX-ACCESS read-write
STATUS current
DESCRIPTION
"Data value."
::= { dataArray10 356 }

dataValue10_357 OBJECT-TYPE
SYNTAX INTEGER
MAX-ACCESS read-write
STATUS current
DESCRIPTION
"Data value."
::= { dataArray10 357 }

dataValue10_358 OBJECT-TYPE
SYNTAX INTEGER
MAX-ACCESS read-write
STATUS current
DESCRIPTION
"Data value."
::= { dataArray10 358 }

dataValue10_359 OBJECT-TYPE
SYNTAX INTEGER
MAX-ACCESS read-write
STATUS current
DESCRIPTION
"Data value."
::= { dataArray10 359 }

dataValue10_360 OBJECT-TYPE
SYNTAX INTEGER
MAX-ACCESS read-write
STATUS current
DESCRIPTION
"Data value."
::= { dataArray10 360 }

dataValue10_361 OBJECT-TYPE
SYNTAX INTEGER
MAX-ACCESS read-write
STATUS current
DESCRIPTION
"Data value."
::= { dataArray10 361 }

dataValue10_362 OBJECT-TYPE
SYNTAX INTEGER
MAX-ACCESS read-write
STATUS current
DESCRIPTION
"Data value."
::= { dataArray10 362 }

dataValue10_363 OBJECT-TYPE
SYNTAX INTEGER
MAX-ACCESS read-write
STATUS current
DESCRIPTION
"Data value."
::= { dataArray10 363 }

dataValue10_364 OBJECT-TYPE
SYNTAX INTEGER
MAX-ACCESS read-write
STATUS current
DESCRIPTION
"Data value."
::= { dataArray10 364 }

dataValue10_365 OBJECT-TYPE
SYNTAX INTEGER
MAX-ACCESS read-write
STATUS current
DESCRIPTION
"Data value."
::= { dataArray10 365 }

dataValue10_366 OBJECT-TYPE
SYNTAX INTEGER
MAX-ACCESS read-write
STATUS current
DESCRIPTION
"Data value."
::= { dataArray10 366 }

dataValue10_367 OBJECT-TYPE
SYNTAX INTEGER
MAX-ACCESS read-write
STATUS current
DESCRIPTION
"Data value."
::= { dataArray10 367 }

dataValue10_368 OBJECT-TYPE
SYNTAX INTEGER
MAX-ACCESS read-write
STATUS current
DESCRIPTION
"Data value."
::= { dataArray10 368 }

dataValue10_369 OBJECT-TYPE
SYNTAX INTEGER
MAX-ACCESS read-write
STATUS current
DESCRIPTION
"Data value."
::= { dataArray10 369 }

dataValue10_370 OBJECT-TYPE
SYNTAX INTEGER
MAX-ACCESS read-write
STATUS current
DESCRIPTION
"Data value."
::= { dataArray10 370 }

dataValue10_371 OBJECT-TYPE
SYNTAX INTEGER
MAX-ACCESS read-write
STATUS current
DESCRIPTION
"Data value."
::= { dataArray10 371 }

dataValue10_372 OBJECT-TYPE
SYNTAX INTEGER
MAX-ACCESS read-write
STATUS current
DESCRIPTION
"Data value."
::= { dataArray10 372 }

dataValue10_373 OBJECT-TYPE
SYNTAX INTEGER
MAX-ACCESS read-write
STATUS current
DESCRIPTION
"Data value."
::= { dataArray10 373 }

dataValue10_374 OBJECT-TYPE
SYNTAX INTEGER
MAX-ACCESS read-write
STATUS current
DESCRIPTION
"Data value."
::= { dataArray10 374 }

dataValue10_375 OBJECT-TYPE
SYNTAX INTEGER
MAX-ACCESS read-write
STATUS current
DESCRIPTION
"Data value."
::= { dataArray10 375 }

dataValue10_376 OBJECT-TYPE
SYNTAX INTEGER
MAX-ACCESS read-write
STATUS current
DESCRIPTION
"Data value."
::= { dataArray10 376 }

dataValue10_377 OBJECT-TYPE
SYNTAX INTEGER
MAX-ACCESS read-write
STATUS current
DESCRIPTION
"Data value."
::= { dataArray10 377 }

dataValue10_378 OBJECT-TYPE
SYNTAX INTEGER
MAX-ACCESS read-write
STATUS current
DESCRIPTION
"Data value."
::= { dataArray10 378 }

dataValue10_379 OBJECT-TYPE
SYNTAX INTEGER
MAX-ACCESS read-write
STATUS current
DESCRIPTION
"Data value."
::= { dataArray10 379 }

dataValue10_380 OBJECT-TYPE
SYNTAX INTEGER
MAX-ACCESS read-write
STATUS current
DESCRIPTION
"Data value."
::= { dataArray10 380 }

dataValue10_381 OBJECT-TYPE
SYNTAX INTEGER
MAX-ACCESS read-write
STATUS current
DESCRIPTION
"Data value."
::= { dataArray10 381 }

dataValue10_382 OBJECT-TYPE
SYNTAX INTEGER
MAX-ACCESS read-write
STATUS current
DESCRIPTION
"Data value."
::= { dataArray10 382 }

dataValue10_383 OBJECT-TYPE
SYNTAX INTEGER
MAX-ACCESS read-write
STATUS current
DESCRIPTION
"Data value."
::= { dataArray10 383 }

dataValue10_384 OBJECT-TYPE
SYNTAX INTEGER
MAX-ACCESS read-write
STATUS current
DESCRIPTION
"Data value."
::= { dataArray10 384 }

dataValue10_385 OBJECT-TYPE
SYNTAX INTEGER
MAX-ACCESS read-write
STATUS current
DESCRIPTION
"Data value."
::= { dataArray10 385 }

dataValue10_386 OBJECT-TYPE
SYNTAX INTEGER
MAX-ACCESS read-write
STATUS current
DESCRIPTION
"Data value."
::= { dataArray10 386 }

dataValue10_387 OBJECT-TYPE
SYNTAX INTEGER
MAX-ACCESS read-write
STATUS current
DESCRIPTION
"Data value."
::= { dataArray10 387 }

dataValue10_388 OBJECT-TYPE
SYNTAX INTEGER
MAX-ACCESS read-write
STATUS current
DESCRIPTION
"Data value."
::= { dataArray10 388 }

dataValue10_389 OBJECT-TYPE
SYNTAX INTEGER
MAX-ACCESS read-write
STATUS current
DESCRIPTION
"Data value."
::= { dataArray10 389 }

dataValue10_390 OBJECT-TYPE
SYNTAX INTEGER
MAX-ACCESS read-write
STATUS current
DESCRIPTION
"Data value."
::= { dataArray10 390 }

dataValue10_391 OBJECT-TYPE
SYNTAX INTEGER
MAX-ACCESS read-write
STATUS current
DESCRIPTION
"Data value."
::= { dataArray10 391 }

dataValue10_392 OBJECT-TYPE
SYNTAX INTEGER
MAX-ACCESS read-write
STATUS current
DESCRIPTION
"Data value."
::= { dataArray10 392 }

dataValue10_393 OBJECT-TYPE
SYNTAX INTEGER
MAX-ACCESS read-write
STATUS current
DESCRIPTION
"Data value."
::= { dataArray10 393 }

dataValue10_394 OBJECT-TYPE
SYNTAX INTEGER
MAX-ACCESS read-write
STATUS current
DESCRIPTION
"Data value."
::= { dataArray10 394 }

dataValue10_395 OBJECT-TYPE
SYNTAX INTEGER
MAX-ACCESS read-write
STATUS current
DESCRIPTION
"Data value."
::= { dataArray10 395 }

dataValue10_396 OBJECT-TYPE
SYNTAX INTEGER
MAX-ACCESS read-write
STATUS current
DESCRIPTION
"Data value."
::= { dataArray10 396 }

dataValue10_397 OBJECT-TYPE
SYNTAX INTEGER
MAX-ACCESS read-write
STATUS current
DESCRIPTION
"Data value."
::= { dataArray10 397 }

dataValue10_398 OBJECT-TYPE
SYNTAX INTEGER
MAX-ACCESS read-write
STATUS current
DESCRIPTION
"Data value."
::= { dataArray10 398 }

dataValue10_399 OBJECT-TYPE
SYNTAX INTEGER
MAX-ACCESS read-write
STATUS current
DESCRIPTION
"Data value."
::= { dataArray10 399 }

dataArray11 OBJECT IDENTIFIER ::= { cc08255400_v1_00a 11 }

dataValue11_0 OBJECT-TYPE
SYNTAX INTEGER
MAX-ACCESS read-write
STATUS current
DESCRIPTION
"Data value."
::= { dataArray11 0 }

dataValue11_1 OBJECT-TYPE
SYNTAX INTEGER
MAX-ACCESS read-write
STATUS current
DESCRIPTION
"Data value."
::= { dataArray11 1 }

dataValue11_2 OBJECT-TYPE
SYNTAX INTEGER
MAX-ACCESS read-write
STATUS current
DESCRIPTION
"Data value."
::= { dataArray11 2 }

dataValue11_3 OBJECT-TYPE
SYNTAX INTEGER
MAX-ACCESS read-write
STATUS current
DESCRIPTION
"Data value."
::= { dataArray11 3 }

dataValue11_4 OBJECT-TYPE
SYNTAX INTEGER
MAX-ACCESS read-write
STATUS current
DESCRIPTION
"Data value."
::= { dataArray11 4 }

dataValue11_5 OBJECT-TYPE
SYNTAX INTEGER
MAX-ACCESS read-write
STATUS current
DESCRIPTION
"Data value."
::= { dataArray11 5 }

dataValue11_6 OBJECT-TYPE
SYNTAX INTEGER
MAX-ACCESS read-write
STATUS current
DESCRIPTION
"Data value."
::= { dataArray11 6 }

dataValue11_7 OBJECT-TYPE
SYNTAX INTEGER
MAX-ACCESS read-write
STATUS current
DESCRIPTION
"Data value."
::= { dataArray11 7 }

dataValue11_8 OBJECT-TYPE
SYNTAX INTEGER
MAX-ACCESS read-write
STATUS current
DESCRIPTION
"Data value."
::= { dataArray11 8 }

dataValue11_9 OBJECT-TYPE
SYNTAX INTEGER
MAX-ACCESS read-write
STATUS current
DESCRIPTION
"Data value."
::= { dataArray11 9 }

dataValue11_10 OBJECT-TYPE
SYNTAX INTEGER
MAX-ACCESS read-write
STATUS current
DESCRIPTION
"Data value."
::= { dataArray11 10 }

dataValue11_11 OBJECT-TYPE
SYNTAX INTEGER
MAX-ACCESS read-write
STATUS current
DESCRIPTION
"Data value."
::= { dataArray11 11 }

dataValue11_12 OBJECT-TYPE
SYNTAX INTEGER
MAX-ACCESS read-write
STATUS current
DESCRIPTION
"Data value."
::= { dataArray11 12 }

dataValue11_13 OBJECT-TYPE
SYNTAX INTEGER
MAX-ACCESS read-write
STATUS current
DESCRIPTION
"Data value."
::= { dataArray11 13 }

dataValue11_14 OBJECT-TYPE
SYNTAX INTEGER
MAX-ACCESS read-write
STATUS current
DESCRIPTION
"Data value."
::= { dataArray11 14 }

dataValue11_15 OBJECT-TYPE
SYNTAX INTEGER
MAX-ACCESS read-write
STATUS current
DESCRIPTION
"Data value."
::= { dataArray11 15 }

dataValue11_16 OBJECT-TYPE
SYNTAX INTEGER
MAX-ACCESS read-write
STATUS current
DESCRIPTION
"Data value."
::= { dataArray11 16 }

dataValue11_17 OBJECT-TYPE
SYNTAX INTEGER
MAX-ACCESS read-write
STATUS current
DESCRIPTION
"Data value."
::= { dataArray11 17 }

dataValue11_18 OBJECT-TYPE
SYNTAX INTEGER
MAX-ACCESS read-write
STATUS current
DESCRIPTION
"Data value."
::= { dataArray11 18 }

dataValue11_19 OBJECT-TYPE
SYNTAX INTEGER
MAX-ACCESS read-write
STATUS current
DESCRIPTION
"Data value."
::= { dataArray11 19 }

dataValue11_20 OBJECT-TYPE
SYNTAX INTEGER
MAX-ACCESS read-write
STATUS current
DESCRIPTION
"Data value."
::= { dataArray11 20 }

dataValue11_21 OBJECT-TYPE
SYNTAX INTEGER
MAX-ACCESS read-write
STATUS current
DESCRIPTION
"Data value."
::= { dataArray11 21 }

dataValue11_22 OBJECT-TYPE
SYNTAX INTEGER
MAX-ACCESS read-write
STATUS current
DESCRIPTION
"Data value."
::= { dataArray11 22 }

dataValue11_23 OBJECT-TYPE
SYNTAX INTEGER
MAX-ACCESS read-write
STATUS current
DESCRIPTION
"Data value."
::= { dataArray11 23 }

dataValue11_24 OBJECT-TYPE
SYNTAX INTEGER
MAX-ACCESS read-write
STATUS current
DESCRIPTION
"Data value."
::= { dataArray11 24 }

dataValue11_25 OBJECT-TYPE
SYNTAX INTEGER
MAX-ACCESS read-write
STATUS current
DESCRIPTION
"Data value."
::= { dataArray11 25 }

dataValue11_26 OBJECT-TYPE
SYNTAX INTEGER
MAX-ACCESS read-write
STATUS current
DESCRIPTION
"Data value."
::= { dataArray11 26 }

dataValue11_27 OBJECT-TYPE
SYNTAX INTEGER
MAX-ACCESS read-write
STATUS current
DESCRIPTION
"Data value."
::= { dataArray11 27 }

dataValue11_28 OBJECT-TYPE
SYNTAX INTEGER
MAX-ACCESS read-write
STATUS current
DESCRIPTION
"Data value."
::= { dataArray11 28 }

dataValue11_29 OBJECT-TYPE
SYNTAX INTEGER
MAX-ACCESS read-write
STATUS current
DESCRIPTION
"Data value."
::= { dataArray11 29 }

dataValue11_30 OBJECT-TYPE
SYNTAX INTEGER
MAX-ACCESS read-write
STATUS current
DESCRIPTION
"Data value."
::= { dataArray11 30 }

dataValue11_31 OBJECT-TYPE
SYNTAX INTEGER
MAX-ACCESS read-write
STATUS current
DESCRIPTION
"Data value."
::= { dataArray11 31 }

dataValue11_32 OBJECT-TYPE
SYNTAX INTEGER
MAX-ACCESS read-write
STATUS current
DESCRIPTION
"Data value."
::= { dataArray11 32 }

dataValue11_33 OBJECT-TYPE
SYNTAX INTEGER
MAX-ACCESS read-write
STATUS current
DESCRIPTION
"Data value."
::= { dataArray11 33 }

dataValue11_34 OBJECT-TYPE
SYNTAX INTEGER
MAX-ACCESS read-write
STATUS current
DESCRIPTION
"Data value."
::= { dataArray11 34 }

dataValue11_35 OBJECT-TYPE
SYNTAX INTEGER
MAX-ACCESS read-write
STATUS current
DESCRIPTION
"Data value."
::= { dataArray11 35 }

dataValue11_36 OBJECT-TYPE
SYNTAX INTEGER
MAX-ACCESS read-write
STATUS current
DESCRIPTION
"Data value."
::= { dataArray11 36 }

dataValue11_37 OBJECT-TYPE
SYNTAX INTEGER
MAX-ACCESS read-write
STATUS current
DESCRIPTION
"Data value."
::= { dataArray11 37 }

dataValue11_38 OBJECT-TYPE
SYNTAX INTEGER
MAX-ACCESS read-write
STATUS current
DESCRIPTION
"Data value."
::= { dataArray11 38 }

dataValue11_39 OBJECT-TYPE
SYNTAX INTEGER
MAX-ACCESS read-write
STATUS current
DESCRIPTION
"Data value."
::= { dataArray11 39 }

dataValue11_40 OBJECT-TYPE
SYNTAX INTEGER
MAX-ACCESS read-write
STATUS current
DESCRIPTION
"Data value."
::= { dataArray11 40 }

dataValue11_41 OBJECT-TYPE
SYNTAX INTEGER
MAX-ACCESS read-write
STATUS current
DESCRIPTION
"Data value."
::= { dataArray11 41 }

dataValue11_42 OBJECT-TYPE
SYNTAX INTEGER
MAX-ACCESS read-write
STATUS current
DESCRIPTION
"Data value."
::= { dataArray11 42 }

dataValue11_43 OBJECT-TYPE
SYNTAX INTEGER
MAX-ACCESS read-write
STATUS current
DESCRIPTION
"Data value."
::= { dataArray11 43 }

dataValue11_44 OBJECT-TYPE
SYNTAX INTEGER
MAX-ACCESS read-write
STATUS current
DESCRIPTION
"Data value."
::= { dataArray11 44 }

dataValue11_45 OBJECT-TYPE
SYNTAX INTEGER
MAX-ACCESS read-write
STATUS current
DESCRIPTION
"Data value."
::= { dataArray11 45 }

dataValue11_46 OBJECT-TYPE
SYNTAX INTEGER
MAX-ACCESS read-write
STATUS current
DESCRIPTION
"Data value."
::= { dataArray11 46 }

dataValue11_47 OBJECT-TYPE
SYNTAX INTEGER
MAX-ACCESS read-write
STATUS current
DESCRIPTION
"Data value."
::= { dataArray11 47 }

dataValue11_48 OBJECT-TYPE
SYNTAX INTEGER
MAX-ACCESS read-write
STATUS current
DESCRIPTION
"Data value."
::= { dataArray11 48 }

dataValue11_49 OBJECT-TYPE
SYNTAX INTEGER
MAX-ACCESS read-write
STATUS current
DESCRIPTION
"Data value."
::= { dataArray11 49 }

dataValue11_50 OBJECT-TYPE
SYNTAX INTEGER
MAX-ACCESS read-write
STATUS current
DESCRIPTION
"Data value."
::= { dataArray11 50 }

dataValue11_51 OBJECT-TYPE
SYNTAX INTEGER
MAX-ACCESS read-write
STATUS current
DESCRIPTION
"Data value."
::= { dataArray11 51 }

dataValue11_52 OBJECT-TYPE
SYNTAX INTEGER
MAX-ACCESS read-write
STATUS current
DESCRIPTION
"Data value."
::= { dataArray11 52 }

dataValue11_53 OBJECT-TYPE
SYNTAX INTEGER
MAX-ACCESS read-write
STATUS current
DESCRIPTION
"Data value."
::= { dataArray11 53 }

dataValue11_54 OBJECT-TYPE
SYNTAX INTEGER
MAX-ACCESS read-write
STATUS current
DESCRIPTION
"Data value."
::= { dataArray11 54 }

dataValue11_55 OBJECT-TYPE
SYNTAX INTEGER
MAX-ACCESS read-write
STATUS current
DESCRIPTION
"Data value."
::= { dataArray11 55 }

dataValue11_56 OBJECT-TYPE
SYNTAX INTEGER
MAX-ACCESS read-write
STATUS current
DESCRIPTION
"Data value."
::= { dataArray11 56 }

dataValue11_57 OBJECT-TYPE
SYNTAX INTEGER
MAX-ACCESS read-write
STATUS current
DESCRIPTION
"Data value."
::= { dataArray11 57 }

dataValue11_58 OBJECT-TYPE
SYNTAX INTEGER
MAX-ACCESS read-write
STATUS current
DESCRIPTION
"Data value."
::= { dataArray11 58 }

dataValue11_59 OBJECT-TYPE
SYNTAX INTEGER
MAX-ACCESS read-write
STATUS current
DESCRIPTION
"Data value."
::= { dataArray11 59 }

dataValue11_60 OBJECT-TYPE
SYNTAX INTEGER
MAX-ACCESS read-write
STATUS current
DESCRIPTION
"Data value."
::= { dataArray11 60 }

dataValue11_61 OBJECT-TYPE
SYNTAX INTEGER
MAX-ACCESS read-write
STATUS current
DESCRIPTION
"Data value."
::= { dataArray11 61 }

dataValue11_62 OBJECT-TYPE
SYNTAX INTEGER
MAX-ACCESS read-write
STATUS current
DESCRIPTION
"Data value."
::= { dataArray11 62 }

dataValue11_63 OBJECT-TYPE
SYNTAX INTEGER
MAX-ACCESS read-write
STATUS current
DESCRIPTION
"Data value."
::= { dataArray11 63 }

dataValue11_64 OBJECT-TYPE
SYNTAX INTEGER
MAX-ACCESS read-write
STATUS current
DESCRIPTION
"Data value."
::= { dataArray11 64 }

dataValue11_65 OBJECT-TYPE
SYNTAX INTEGER
MAX-ACCESS read-write
STATUS current
DESCRIPTION
"Data value."
::= { dataArray11 65 }

dataValue11_66 OBJECT-TYPE
SYNTAX INTEGER
MAX-ACCESS read-write
STATUS current
DESCRIPTION
"Data value."
::= { dataArray11 66 }

dataValue11_67 OBJECT-TYPE
SYNTAX INTEGER
MAX-ACCESS read-write
STATUS current
DESCRIPTION
"Data value."
::= { dataArray11 67 }

dataValue11_68 OBJECT-TYPE
SYNTAX INTEGER
MAX-ACCESS read-write
STATUS current
DESCRIPTION
"Data value."
::= { dataArray11 68 }

dataValue11_69 OBJECT-TYPE
SYNTAX INTEGER
MAX-ACCESS read-write
STATUS current
DESCRIPTION
"Data value."
::= { dataArray11 69 }

dataValue11_70 OBJECT-TYPE
SYNTAX INTEGER
MAX-ACCESS read-write
STATUS current
DESCRIPTION
"Data value."
::= { dataArray11 70 }

dataValue11_71 OBJECT-TYPE
SYNTAX INTEGER
MAX-ACCESS read-write
STATUS current
DESCRIPTION
"Data value."
::= { dataArray11 71 }

dataValue11_72 OBJECT-TYPE
SYNTAX INTEGER
MAX-ACCESS read-write
STATUS current
DESCRIPTION
"Data value."
::= { dataArray11 72 }

dataValue11_73 OBJECT-TYPE
SYNTAX INTEGER
MAX-ACCESS read-write
STATUS current
DESCRIPTION
"Data value."
::= { dataArray11 73 }

dataValue11_74 OBJECT-TYPE
SYNTAX INTEGER
MAX-ACCESS read-write
STATUS current
DESCRIPTION
"Data value."
::= { dataArray11 74 }

dataValue11_75 OBJECT-TYPE
SYNTAX INTEGER
MAX-ACCESS read-write
STATUS current
DESCRIPTION
"Data value."
::= { dataArray11 75 }

dataValue11_76 OBJECT-TYPE
SYNTAX INTEGER
MAX-ACCESS read-write
STATUS current
DESCRIPTION
"Data value."
::= { dataArray11 76 }

dataValue11_77 OBJECT-TYPE
SYNTAX INTEGER
MAX-ACCESS read-write
STATUS current
DESCRIPTION
"Data value."
::= { dataArray11 77 }

dataValue11_78 OBJECT-TYPE
SYNTAX INTEGER
MAX-ACCESS read-write
STATUS current
DESCRIPTION
"Data value."
::= { dataArray11 78 }

dataValue11_79 OBJECT-TYPE
SYNTAX INTEGER
MAX-ACCESS read-write
STATUS current
DESCRIPTION
"Data value."
::= { dataArray11 79 }

dataValue11_80 OBJECT-TYPE
SYNTAX INTEGER
MAX-ACCESS read-write
STATUS current
DESCRIPTION
"Data value."
::= { dataArray11 80 }

dataValue11_81 OBJECT-TYPE
SYNTAX INTEGER
MAX-ACCESS read-write
STATUS current
DESCRIPTION
"Data value."
::= { dataArray11 81 }

dataValue11_82 OBJECT-TYPE
SYNTAX INTEGER
MAX-ACCESS read-write
STATUS current
DESCRIPTION
"Data value."
::= { dataArray11 82 }

dataValue11_83 OBJECT-TYPE
SYNTAX INTEGER
MAX-ACCESS read-write
STATUS current
DESCRIPTION
"Data value."
::= { dataArray11 83 }

dataValue11_84 OBJECT-TYPE
SYNTAX INTEGER
MAX-ACCESS read-write
STATUS current
DESCRIPTION
"Data value."
::= { dataArray11 84 }

dataValue11_85 OBJECT-TYPE
SYNTAX INTEGER
MAX-ACCESS read-write
STATUS current
DESCRIPTION
"Data value."
::= { dataArray11 85 }

dataValue11_86 OBJECT-TYPE
SYNTAX INTEGER
MAX-ACCESS read-write
STATUS current
DESCRIPTION
"Data value."
::= { dataArray11 86 }

dataValue11_87 OBJECT-TYPE
SYNTAX INTEGER
MAX-ACCESS read-write
STATUS current
DESCRIPTION
"Data value."
::= { dataArray11 87 }

dataValue11_88 OBJECT-TYPE
SYNTAX INTEGER
MAX-ACCESS read-write
STATUS current
DESCRIPTION
"Data value."
::= { dataArray11 88 }

dataValue11_89 OBJECT-TYPE
SYNTAX INTEGER
MAX-ACCESS read-write
STATUS current
DESCRIPTION
"Data value."
::= { dataArray11 89 }

dataValue11_90 OBJECT-TYPE
SYNTAX INTEGER
MAX-ACCESS read-write
STATUS current
DESCRIPTION
"Data value."
::= { dataArray11 90 }

dataValue11_91 OBJECT-TYPE
SYNTAX INTEGER
MAX-ACCESS read-write
STATUS current
DESCRIPTION
"Data value."
::= { dataArray11 91 }

dataValue11_92 OBJECT-TYPE
SYNTAX INTEGER
MAX-ACCESS read-write
STATUS current
DESCRIPTION
"Data value."
::= { dataArray11 92 }

dataValue11_93 OBJECT-TYPE
SYNTAX INTEGER
MAX-ACCESS read-write
STATUS current
DESCRIPTION
"Data value."
::= { dataArray11 93 }

dataValue11_94 OBJECT-TYPE
SYNTAX INTEGER
MAX-ACCESS read-write
STATUS current
DESCRIPTION
"Data value."
::= { dataArray11 94 }

dataValue11_95 OBJECT-TYPE
SYNTAX INTEGER
MAX-ACCESS read-write
STATUS current
DESCRIPTION
"Data value."
::= { dataArray11 95 }

dataValue11_96 OBJECT-TYPE
SYNTAX INTEGER
MAX-ACCESS read-write
STATUS current
DESCRIPTION
"Data value."
::= { dataArray11 96 }

dataValue11_97 OBJECT-TYPE
SYNTAX INTEGER
MAX-ACCESS read-write
STATUS current
DESCRIPTION
"Data value."
::= { dataArray11 97 }

dataValue11_98 OBJECT-TYPE
SYNTAX INTEGER
MAX-ACCESS read-write
STATUS current
DESCRIPTION
"Data value."
::= { dataArray11 98 }

dataValue11_99 OBJECT-TYPE
SYNTAX INTEGER
MAX-ACCESS read-write
STATUS current
DESCRIPTION
"Data value."
::= { dataArray11 99 }

dataValue11_100 OBJECT-TYPE
SYNTAX INTEGER
MAX-ACCESS read-write
STATUS current
DESCRIPTION
"Data value."
::= { dataArray11 100 }

dataValue11_101 OBJECT-TYPE
SYNTAX INTEGER
MAX-ACCESS read-write
STATUS current
DESCRIPTION
"Data value."
::= { dataArray11 101 }

dataValue11_102 OBJECT-TYPE
SYNTAX INTEGER
MAX-ACCESS read-write
STATUS current
DESCRIPTION
"Data value."
::= { dataArray11 102 }

dataValue11_103 OBJECT-TYPE
SYNTAX INTEGER
MAX-ACCESS read-write
STATUS current
DESCRIPTION
"Data value."
::= { dataArray11 103 }

dataValue11_104 OBJECT-TYPE
SYNTAX INTEGER
MAX-ACCESS read-write
STATUS current
DESCRIPTION
"Data value."
::= { dataArray11 104 }

dataValue11_105 OBJECT-TYPE
SYNTAX INTEGER
MAX-ACCESS read-write
STATUS current
DESCRIPTION
"Data value."
::= { dataArray11 105 }

dataValue11_106 OBJECT-TYPE
SYNTAX INTEGER
MAX-ACCESS read-write
STATUS current
DESCRIPTION
"Data value."
::= { dataArray11 106 }

dataValue11_107 OBJECT-TYPE
SYNTAX INTEGER
MAX-ACCESS read-write
STATUS current
DESCRIPTION
"Data value."
::= { dataArray11 107 }

dataValue11_108 OBJECT-TYPE
SYNTAX INTEGER
MAX-ACCESS read-write
STATUS current
DESCRIPTION
"Data value."
::= { dataArray11 108 }

dataValue11_109 OBJECT-TYPE
SYNTAX INTEGER
MAX-ACCESS read-write
STATUS current
DESCRIPTION
"Data value."
::= { dataArray11 109 }

dataValue11_110 OBJECT-TYPE
SYNTAX INTEGER
MAX-ACCESS read-write
STATUS current
DESCRIPTION
"Data value."
::= { dataArray11 110 }

dataValue11_111 OBJECT-TYPE
SYNTAX INTEGER
MAX-ACCESS read-write
STATUS current
DESCRIPTION
"Data value."
::= { dataArray11 111 }

dataValue11_112 OBJECT-TYPE
SYNTAX INTEGER
MAX-ACCESS read-write
STATUS current
DESCRIPTION
"Data value."
::= { dataArray11 112 }

dataValue11_113 OBJECT-TYPE
SYNTAX INTEGER
MAX-ACCESS read-write
STATUS current
DESCRIPTION
"Data value."
::= { dataArray11 113 }

dataValue11_114 OBJECT-TYPE
SYNTAX INTEGER
MAX-ACCESS read-write
STATUS current
DESCRIPTION
"Data value."
::= { dataArray11 114 }

dataValue11_115 OBJECT-TYPE
SYNTAX INTEGER
MAX-ACCESS read-write
STATUS current
DESCRIPTION
"Data value."
::= { dataArray11 115 }

dataValue11_116 OBJECT-TYPE
SYNTAX INTEGER
MAX-ACCESS read-write
STATUS current
DESCRIPTION
"Data value."
::= { dataArray11 116 }

dataValue11_117 OBJECT-TYPE
SYNTAX INTEGER
MAX-ACCESS read-write
STATUS current
DESCRIPTION
"Data value."
::= { dataArray11 117 }

dataValue11_118 OBJECT-TYPE
SYNTAX INTEGER
MAX-ACCESS read-write
STATUS current
DESCRIPTION
"Data value."
::= { dataArray11 118 }

dataValue11_119 OBJECT-TYPE
SYNTAX INTEGER
MAX-ACCESS read-write
STATUS current
DESCRIPTION
"Data value."
::= { dataArray11 119 }

dataValue11_120 OBJECT-TYPE
SYNTAX INTEGER
MAX-ACCESS read-write
STATUS current
DESCRIPTION
"Data value."
::= { dataArray11 120 }

dataValue11_121 OBJECT-TYPE
SYNTAX INTEGER
MAX-ACCESS read-write
STATUS current
DESCRIPTION
"Data value."
::= { dataArray11 121 }

dataValue11_122 OBJECT-TYPE
SYNTAX INTEGER
MAX-ACCESS read-write
STATUS current
DESCRIPTION
"Data value."
::= { dataArray11 122 }

dataValue11_123 OBJECT-TYPE
SYNTAX INTEGER
MAX-ACCESS read-write
STATUS current
DESCRIPTION
"Data value."
::= { dataArray11 123 }

dataValue11_124 OBJECT-TYPE
SYNTAX INTEGER
MAX-ACCESS read-write
STATUS current
DESCRIPTION
"Data value."
::= { dataArray11 124 }

dataValue11_125 OBJECT-TYPE
SYNTAX INTEGER
MAX-ACCESS read-write
STATUS current
DESCRIPTION
"Data value."
::= { dataArray11 125 }

dataValue11_126 OBJECT-TYPE
SYNTAX INTEGER
MAX-ACCESS read-write
STATUS current
DESCRIPTION
"Data value."
::= { dataArray11 126 }

dataValue11_127 OBJECT-TYPE
SYNTAX INTEGER
MAX-ACCESS read-write
STATUS current
DESCRIPTION
"Data value."
::= { dataArray11 127 }

dataValue11_128 OBJECT-TYPE
SYNTAX INTEGER
MAX-ACCESS read-write
STATUS current
DESCRIPTION
"Data value."
::= { dataArray11 128 }

dataValue11_129 OBJECT-TYPE
SYNTAX INTEGER
MAX-ACCESS read-write
STATUS current
DESCRIPTION
"Data value."
::= { dataArray11 129 }

dataValue11_130 OBJECT-TYPE
SYNTAX INTEGER
MAX-ACCESS read-write
STATUS current
DESCRIPTION
"Data value."
::= { dataArray11 130 }

dataValue11_131 OBJECT-TYPE
SYNTAX INTEGER
MAX-ACCESS read-write
STATUS current
DESCRIPTION
"Data value."
::= { dataArray11 131 }

dataValue11_132 OBJECT-TYPE
SYNTAX INTEGER
MAX-ACCESS read-write
STATUS current
DESCRIPTION
"Data value."
::= { dataArray11 132 }

dataValue11_133 OBJECT-TYPE
SYNTAX INTEGER
MAX-ACCESS read-write
STATUS current
DESCRIPTION
"Data value."
::= { dataArray11 133 }

dataValue11_134 OBJECT-TYPE
SYNTAX INTEGER
MAX-ACCESS read-write
STATUS current
DESCRIPTION
"Data value."
::= { dataArray11 134 }

dataValue11_135 OBJECT-TYPE
SYNTAX INTEGER
MAX-ACCESS read-write
STATUS current
DESCRIPTION
"Data value."
::= { dataArray11 135 }

dataValue11_136 OBJECT-TYPE
SYNTAX INTEGER
MAX-ACCESS read-write
STATUS current
DESCRIPTION
"Data value."
::= { dataArray11 136 }

dataValue11_137 OBJECT-TYPE
SYNTAX INTEGER
MAX-ACCESS read-write
STATUS current
DESCRIPTION
"Data value."
::= { dataArray11 137 }

dataValue11_138 OBJECT-TYPE
SYNTAX INTEGER
MAX-ACCESS read-write
STATUS current
DESCRIPTION
"Data value."
::= { dataArray11 138 }

dataValue11_139 OBJECT-TYPE
SYNTAX INTEGER
MAX-ACCESS read-write
STATUS current
DESCRIPTION
"Data value."
::= { dataArray11 139 }

dataValue11_140 OBJECT-TYPE
SYNTAX INTEGER
MAX-ACCESS read-write
STATUS current
DESCRIPTION
"Data value."
::= { dataArray11 140 }

dataValue11_141 OBJECT-TYPE
SYNTAX INTEGER
MAX-ACCESS read-write
STATUS current
DESCRIPTION
"Data value."
::= { dataArray11 141 }

dataValue11_142 OBJECT-TYPE
SYNTAX INTEGER
MAX-ACCESS read-write
STATUS current
DESCRIPTION
"Data value."
::= { dataArray11 142 }

dataValue11_143 OBJECT-TYPE
SYNTAX INTEGER
MAX-ACCESS read-write
STATUS current
DESCRIPTION
"Data value."
::= { dataArray11 143 }

dataValue11_144 OBJECT-TYPE
SYNTAX INTEGER
MAX-ACCESS read-write
STATUS current
DESCRIPTION
"Data value."
::= { dataArray11 144 }

dataValue11_145 OBJECT-TYPE
SYNTAX INTEGER
MAX-ACCESS read-write
STATUS current
DESCRIPTION
"Data value."
::= { dataArray11 145 }

dataValue11_146 OBJECT-TYPE
SYNTAX INTEGER
MAX-ACCESS read-write
STATUS current
DESCRIPTION
"Data value."
::= { dataArray11 146 }

dataValue11_147 OBJECT-TYPE
SYNTAX INTEGER
MAX-ACCESS read-write
STATUS current
DESCRIPTION
"Data value."
::= { dataArray11 147 }

dataValue11_148 OBJECT-TYPE
SYNTAX INTEGER
MAX-ACCESS read-write
STATUS current
DESCRIPTION
"Data value."
::= { dataArray11 148 }

dataValue11_149 OBJECT-TYPE
SYNTAX INTEGER
MAX-ACCESS read-write
STATUS current
DESCRIPTION
"Data value."
::= { dataArray11 149 }

dataValue11_150 OBJECT-TYPE
SYNTAX INTEGER
MAX-ACCESS read-write
STATUS current
DESCRIPTION
"Data value."
::= { dataArray11 150 }

dataValue11_151 OBJECT-TYPE
SYNTAX INTEGER
MAX-ACCESS read-write
STATUS current
DESCRIPTION
"Data value."
::= { dataArray11 151 }

dataValue11_152 OBJECT-TYPE
SYNTAX INTEGER
MAX-ACCESS read-write
STATUS current
DESCRIPTION
"Data value."
::= { dataArray11 152 }

dataValue11_153 OBJECT-TYPE
SYNTAX INTEGER
MAX-ACCESS read-write
STATUS current
DESCRIPTION
"Data value."
::= { dataArray11 153 }

dataValue11_154 OBJECT-TYPE
SYNTAX INTEGER
MAX-ACCESS read-write
STATUS current
DESCRIPTION
"Data value."
::= { dataArray11 154 }

dataValue11_155 OBJECT-TYPE
SYNTAX INTEGER
MAX-ACCESS read-write
STATUS current
DESCRIPTION
"Data value."
::= { dataArray11 155 }

dataValue11_156 OBJECT-TYPE
SYNTAX INTEGER
MAX-ACCESS read-write
STATUS current
DESCRIPTION
"Data value."
::= { dataArray11 156 }

dataValue11_157 OBJECT-TYPE
SYNTAX INTEGER
MAX-ACCESS read-write
STATUS current
DESCRIPTION
"Data value."
::= { dataArray11 157 }

dataValue11_158 OBJECT-TYPE
SYNTAX INTEGER
MAX-ACCESS read-write
STATUS current
DESCRIPTION
"Data value."
::= { dataArray11 158 }

dataValue11_159 OBJECT-TYPE
SYNTAX INTEGER
MAX-ACCESS read-write
STATUS current
DESCRIPTION
"Data value."
::= { dataArray11 159 }

dataValue11_160 OBJECT-TYPE
SYNTAX INTEGER
MAX-ACCESS read-write
STATUS current
DESCRIPTION
"Data value."
::= { dataArray11 160 }

dataValue11_161 OBJECT-TYPE
SYNTAX INTEGER
MAX-ACCESS read-write
STATUS current
DESCRIPTION
"Data value."
::= { dataArray11 161 }

dataValue11_162 OBJECT-TYPE
SYNTAX INTEGER
MAX-ACCESS read-write
STATUS current
DESCRIPTION
"Data value."
::= { dataArray11 162 }

dataValue11_163 OBJECT-TYPE
SYNTAX INTEGER
MAX-ACCESS read-write
STATUS current
DESCRIPTION
"Data value."
::= { dataArray11 163 }

dataValue11_164 OBJECT-TYPE
SYNTAX INTEGER
MAX-ACCESS read-write
STATUS current
DESCRIPTION
"Data value."
::= { dataArray11 164 }

dataValue11_165 OBJECT-TYPE
SYNTAX INTEGER
MAX-ACCESS read-write
STATUS current
DESCRIPTION
"Data value."
::= { dataArray11 165 }

dataValue11_166 OBJECT-TYPE
SYNTAX INTEGER
MAX-ACCESS read-write
STATUS current
DESCRIPTION
"Data value."
::= { dataArray11 166 }

dataValue11_167 OBJECT-TYPE
SYNTAX INTEGER
MAX-ACCESS read-write
STATUS current
DESCRIPTION
"Data value."
::= { dataArray11 167 }

dataValue11_168 OBJECT-TYPE
SYNTAX INTEGER
MAX-ACCESS read-write
STATUS current
DESCRIPTION
"Data value."
::= { dataArray11 168 }

dataValue11_169 OBJECT-TYPE
SYNTAX INTEGER
MAX-ACCESS read-write
STATUS current
DESCRIPTION
"Data value."
::= { dataArray11 169 }

dataValue11_170 OBJECT-TYPE
SYNTAX INTEGER
MAX-ACCESS read-write
STATUS current
DESCRIPTION
"Data value."
::= { dataArray11 170 }

dataValue11_171 OBJECT-TYPE
SYNTAX INTEGER
MAX-ACCESS read-write
STATUS current
DESCRIPTION
"Data value."
::= { dataArray11 171 }

dataValue11_172 OBJECT-TYPE
SYNTAX INTEGER
MAX-ACCESS read-write
STATUS current
DESCRIPTION
"Data value."
::= { dataArray11 172 }

dataValue11_173 OBJECT-TYPE
SYNTAX INTEGER
MAX-ACCESS read-write
STATUS current
DESCRIPTION
"Data value."
::= { dataArray11 173 }

dataValue11_174 OBJECT-TYPE
SYNTAX INTEGER
MAX-ACCESS read-write
STATUS current
DESCRIPTION
"Data value."
::= { dataArray11 174 }

dataValue11_175 OBJECT-TYPE
SYNTAX INTEGER
MAX-ACCESS read-write
STATUS current
DESCRIPTION
"Data value."
::= { dataArray11 175 }

dataValue11_176 OBJECT-TYPE
SYNTAX INTEGER
MAX-ACCESS read-write
STATUS current
DESCRIPTION
"Data value."
::= { dataArray11 176 }

dataValue11_177 OBJECT-TYPE
SYNTAX INTEGER
MAX-ACCESS read-write
STATUS current
DESCRIPTION
"Data value."
::= { dataArray11 177 }

dataValue11_178 OBJECT-TYPE
SYNTAX INTEGER
MAX-ACCESS read-write
STATUS current
DESCRIPTION
"Data value."
::= { dataArray11 178 }

dataValue11_179 OBJECT-TYPE
SYNTAX INTEGER
MAX-ACCESS read-write
STATUS current
DESCRIPTION
"Data value."
::= { dataArray11 179 }

dataValue11_180 OBJECT-TYPE
SYNTAX INTEGER
MAX-ACCESS read-write
STATUS current
DESCRIPTION
"Data value."
::= { dataArray11 180 }

dataValue11_181 OBJECT-TYPE
SYNTAX INTEGER
MAX-ACCESS read-write
STATUS current
DESCRIPTION
"Data value."
::= { dataArray11 181 }

dataValue11_182 OBJECT-TYPE
SYNTAX INTEGER
MAX-ACCESS read-write
STATUS current
DESCRIPTION
"Data value."
::= { dataArray11 182 }

dataValue11_183 OBJECT-TYPE
SYNTAX INTEGER
MAX-ACCESS read-write
STATUS current
DESCRIPTION
"Data value."
::= { dataArray11 183 }

dataValue11_184 OBJECT-TYPE
SYNTAX INTEGER
MAX-ACCESS read-write
STATUS current
DESCRIPTION
"Data value."
::= { dataArray11 184 }

dataValue11_185 OBJECT-TYPE
SYNTAX INTEGER
MAX-ACCESS read-write
STATUS current
DESCRIPTION
"Data value."
::= { dataArray11 185 }

dataValue11_186 OBJECT-TYPE
SYNTAX INTEGER
MAX-ACCESS read-write
STATUS current
DESCRIPTION
"Data value."
::= { dataArray11 186 }

dataValue11_187 OBJECT-TYPE
SYNTAX INTEGER
MAX-ACCESS read-write
STATUS current
DESCRIPTION
"Data value."
::= { dataArray11 187 }

dataValue11_188 OBJECT-TYPE
SYNTAX INTEGER
MAX-ACCESS read-write
STATUS current
DESCRIPTION
"Data value."
::= { dataArray11 188 }

dataValue11_189 OBJECT-TYPE
SYNTAX INTEGER
MAX-ACCESS read-write
STATUS current
DESCRIPTION
"Data value."
::= { dataArray11 189 }

dataValue11_190 OBJECT-TYPE
SYNTAX INTEGER
MAX-ACCESS read-write
STATUS current
DESCRIPTION
"Data value."
::= { dataArray11 190 }

dataValue11_191 OBJECT-TYPE
SYNTAX INTEGER
MAX-ACCESS read-write
STATUS current
DESCRIPTION
"Data value."
::= { dataArray11 191 }

dataValue11_192 OBJECT-TYPE
SYNTAX INTEGER
MAX-ACCESS read-write
STATUS current
DESCRIPTION
"Data value."
::= { dataArray11 192 }

dataValue11_193 OBJECT-TYPE
SYNTAX INTEGER
MAX-ACCESS read-write
STATUS current
DESCRIPTION
"Data value."
::= { dataArray11 193 }

dataValue11_194 OBJECT-TYPE
SYNTAX INTEGER
MAX-ACCESS read-write
STATUS current
DESCRIPTION
"Data value."
::= { dataArray11 194 }

dataValue11_195 OBJECT-TYPE
SYNTAX INTEGER
MAX-ACCESS read-write
STATUS current
DESCRIPTION
"Data value."
::= { dataArray11 195 }

dataValue11_196 OBJECT-TYPE
SYNTAX INTEGER
MAX-ACCESS read-write
STATUS current
DESCRIPTION
"Data value."
::= { dataArray11 196 }

dataValue11_197 OBJECT-TYPE
SYNTAX INTEGER
MAX-ACCESS read-write
STATUS current
DESCRIPTION
"Data value."
::= { dataArray11 197 }

dataValue11_198 OBJECT-TYPE
SYNTAX INTEGER
MAX-ACCESS read-write
STATUS current
DESCRIPTION
"Data value."
::= { dataArray11 198 }

dataValue11_199 OBJECT-TYPE
SYNTAX INTEGER
MAX-ACCESS read-write
STATUS current
DESCRIPTION
"Data value."
::= { dataArray11 199 }

dataValue11_200 OBJECT-TYPE
SYNTAX INTEGER
MAX-ACCESS read-write
STATUS current
DESCRIPTION
"Data value."
::= { dataArray11 200 }

dataValue11_201 OBJECT-TYPE
SYNTAX INTEGER
MAX-ACCESS read-write
STATUS current
DESCRIPTION
"Data value."
::= { dataArray11 201 }

dataValue11_202 OBJECT-TYPE
SYNTAX INTEGER
MAX-ACCESS read-write
STATUS current
DESCRIPTION
"Data value."
::= { dataArray11 202 }

dataValue11_203 OBJECT-TYPE
SYNTAX INTEGER
MAX-ACCESS read-write
STATUS current
DESCRIPTION
"Data value."
::= { dataArray11 203 }

dataValue11_204 OBJECT-TYPE
SYNTAX INTEGER
MAX-ACCESS read-write
STATUS current
DESCRIPTION
"Data value."
::= { dataArray11 204 }

dataValue11_205 OBJECT-TYPE
SYNTAX INTEGER
MAX-ACCESS read-write
STATUS current
DESCRIPTION
"Data value."
::= { dataArray11 205 }

dataValue11_206 OBJECT-TYPE
SYNTAX INTEGER
MAX-ACCESS read-write
STATUS current
DESCRIPTION
"Data value."
::= { dataArray11 206 }

dataValue11_207 OBJECT-TYPE
SYNTAX INTEGER
MAX-ACCESS read-write
STATUS current
DESCRIPTION
"Data value."
::= { dataArray11 207 }

dataValue11_208 OBJECT-TYPE
SYNTAX INTEGER
MAX-ACCESS read-write
STATUS current
DESCRIPTION
"Data value."
::= { dataArray11 208 }

dataValue11_209 OBJECT-TYPE
SYNTAX INTEGER
MAX-ACCESS read-write
STATUS current
DESCRIPTION
"Data value."
::= { dataArray11 209 }

dataValue11_210 OBJECT-TYPE
SYNTAX INTEGER
MAX-ACCESS read-write
STATUS current
DESCRIPTION
"Data value."
::= { dataArray11 210 }

dataValue11_211 OBJECT-TYPE
SYNTAX INTEGER
MAX-ACCESS read-write
STATUS current
DESCRIPTION
"Data value."
::= { dataArray11 211 }

dataValue11_212 OBJECT-TYPE
SYNTAX INTEGER
MAX-ACCESS read-write
STATUS current
DESCRIPTION
"Data value."
::= { dataArray11 212 }

dataValue11_213 OBJECT-TYPE
SYNTAX INTEGER
MAX-ACCESS read-write
STATUS current
DESCRIPTION
"Data value."
::= { dataArray11 213 }

dataValue11_214 OBJECT-TYPE
SYNTAX INTEGER
MAX-ACCESS read-write
STATUS current
DESCRIPTION
"Data value."
::= { dataArray11 214 }

dataValue11_215 OBJECT-TYPE
SYNTAX INTEGER
MAX-ACCESS read-write
STATUS current
DESCRIPTION
"Data value."
::= { dataArray11 215 }

dataValue11_216 OBJECT-TYPE
SYNTAX INTEGER
MAX-ACCESS read-write
STATUS current
DESCRIPTION
"Data value."
::= { dataArray11 216 }

dataValue11_217 OBJECT-TYPE
SYNTAX INTEGER
MAX-ACCESS read-write
STATUS current
DESCRIPTION
"Data value."
::= { dataArray11 217 }

dataValue11_218 OBJECT-TYPE
SYNTAX INTEGER
MAX-ACCESS read-write
STATUS current
DESCRIPTION
"Data value."
::= { dataArray11 218 }

dataValue11_219 OBJECT-TYPE
SYNTAX INTEGER
MAX-ACCESS read-write
STATUS current
DESCRIPTION
"Data value."
::= { dataArray11 219 }

dataValue11_220 OBJECT-TYPE
SYNTAX INTEGER
MAX-ACCESS read-write
STATUS current
DESCRIPTION
"Data value."
::= { dataArray11 220 }

dataValue11_221 OBJECT-TYPE
SYNTAX INTEGER
MAX-ACCESS read-write
STATUS current
DESCRIPTION
"Data value."
::= { dataArray11 221 }

dataValue11_222 OBJECT-TYPE
SYNTAX INTEGER
MAX-ACCESS read-write
STATUS current
DESCRIPTION
"Data value."
::= { dataArray11 222 }

dataValue11_223 OBJECT-TYPE
SYNTAX INTEGER
MAX-ACCESS read-write
STATUS current
DESCRIPTION
"Data value."
::= { dataArray11 223 }

dataValue11_224 OBJECT-TYPE
SYNTAX INTEGER
MAX-ACCESS read-write
STATUS current
DESCRIPTION
"Data value."
::= { dataArray11 224 }

dataValue11_225 OBJECT-TYPE
SYNTAX INTEGER
MAX-ACCESS read-write
STATUS current
DESCRIPTION
"Data value."
::= { dataArray11 225 }

dataValue11_226 OBJECT-TYPE
SYNTAX INTEGER
MAX-ACCESS read-write
STATUS current
DESCRIPTION
"Data value."
::= { dataArray11 226 }

dataValue11_227 OBJECT-TYPE
SYNTAX INTEGER
MAX-ACCESS read-write
STATUS current
DESCRIPTION
"Data value."
::= { dataArray11 227 }

dataValue11_228 OBJECT-TYPE
SYNTAX INTEGER
MAX-ACCESS read-write
STATUS current
DESCRIPTION
"Data value."
::= { dataArray11 228 }

dataValue11_229 OBJECT-TYPE
SYNTAX INTEGER
MAX-ACCESS read-write
STATUS current
DESCRIPTION
"Data value."
::= { dataArray11 229 }

dataValue11_230 OBJECT-TYPE
SYNTAX INTEGER
MAX-ACCESS read-write
STATUS current
DESCRIPTION
"Data value."
::= { dataArray11 230 }

dataValue11_231 OBJECT-TYPE
SYNTAX INTEGER
MAX-ACCESS read-write
STATUS current
DESCRIPTION
"Data value."
::= { dataArray11 231 }

dataValue11_232 OBJECT-TYPE
SYNTAX INTEGER
MAX-ACCESS read-write
STATUS current
DESCRIPTION
"Data value."
::= { dataArray11 232 }

dataValue11_233 OBJECT-TYPE
SYNTAX INTEGER
MAX-ACCESS read-write
STATUS current
DESCRIPTION
"Data value."
::= { dataArray11 233 }

dataValue11_234 OBJECT-TYPE
SYNTAX INTEGER
MAX-ACCESS read-write
STATUS current
DESCRIPTION
"Data value."
::= { dataArray11 234 }

dataValue11_235 OBJECT-TYPE
SYNTAX INTEGER
MAX-ACCESS read-write
STATUS current
DESCRIPTION
"Data value."
::= { dataArray11 235 }

dataValue11_236 OBJECT-TYPE
SYNTAX INTEGER
MAX-ACCESS read-write
STATUS current
DESCRIPTION
"Data value."
::= { dataArray11 236 }

dataValue11_237 OBJECT-TYPE
SYNTAX INTEGER
MAX-ACCESS read-write
STATUS current
DESCRIPTION
"Data value."
::= { dataArray11 237 }

dataValue11_238 OBJECT-TYPE
SYNTAX INTEGER
MAX-ACCESS read-write
STATUS current
DESCRIPTION
"Data value."
::= { dataArray11 238 }

dataValue11_239 OBJECT-TYPE
SYNTAX INTEGER
MAX-ACCESS read-write
STATUS current
DESCRIPTION
"Data value."
::= { dataArray11 239 }

dataValue11_240 OBJECT-TYPE
SYNTAX INTEGER
MAX-ACCESS read-write
STATUS current
DESCRIPTION
"Data value."
::= { dataArray11 240 }

dataValue11_241 OBJECT-TYPE
SYNTAX INTEGER
MAX-ACCESS read-write
STATUS current
DESCRIPTION
"Data value."
::= { dataArray11 241 }

dataValue11_242 OBJECT-TYPE
SYNTAX INTEGER
MAX-ACCESS read-write
STATUS current
DESCRIPTION
"Data value."
::= { dataArray11 242 }

dataValue11_243 OBJECT-TYPE
SYNTAX INTEGER
MAX-ACCESS read-write
STATUS current
DESCRIPTION
"Data value."
::= { dataArray11 243 }

dataValue11_244 OBJECT-TYPE
SYNTAX INTEGER
MAX-ACCESS read-write
STATUS current
DESCRIPTION
"Data value."
::= { dataArray11 244 }

dataValue11_245 OBJECT-TYPE
SYNTAX INTEGER
MAX-ACCESS read-write
STATUS current
DESCRIPTION
"Data value."
::= { dataArray11 245 }

dataValue11_246 OBJECT-TYPE
SYNTAX INTEGER
MAX-ACCESS read-write
STATUS current
DESCRIPTION
"Data value."
::= { dataArray11 246 }

dataValue11_247 OBJECT-TYPE
SYNTAX INTEGER
MAX-ACCESS read-write
STATUS current
DESCRIPTION
"Data value."
::= { dataArray11 247 }

dataValue11_248 OBJECT-TYPE
SYNTAX INTEGER
MAX-ACCESS read-write
STATUS current
DESCRIPTION
"Data value."
::= { dataArray11 248 }

dataValue11_249 OBJECT-TYPE
SYNTAX INTEGER
MAX-ACCESS read-write
STATUS current
DESCRIPTION
"Data value."
::= { dataArray11 249 }

dataValue11_250 OBJECT-TYPE
SYNTAX INTEGER
MAX-ACCESS read-write
STATUS current
DESCRIPTION
"Data value."
::= { dataArray11 250 }

dataValue11_251 OBJECT-TYPE
SYNTAX INTEGER
MAX-ACCESS read-write
STATUS current
DESCRIPTION
"Data value."
::= { dataArray11 251 }

dataValue11_252 OBJECT-TYPE
SYNTAX INTEGER
MAX-ACCESS read-write
STATUS current
DESCRIPTION
"Data value."
::= { dataArray11 252 }

dataValue11_253 OBJECT-TYPE
SYNTAX INTEGER
MAX-ACCESS read-write
STATUS current
DESCRIPTION
"Data value."
::= { dataArray11 253 }

dataValue11_254 OBJECT-TYPE
SYNTAX INTEGER
MAX-ACCESS read-write
STATUS current
DESCRIPTION
"Data value."
::= { dataArray11 254 }

dataValue11_255 OBJECT-TYPE
SYNTAX INTEGER
MAX-ACCESS read-write
STATUS current
DESCRIPTION
"Data value."
::= { dataArray11 255 }

dataValue11_256 OBJECT-TYPE
SYNTAX INTEGER
MAX-ACCESS read-write
STATUS current
DESCRIPTION
"Data value."
::= { dataArray11 256 }

dataValue11_257 OBJECT-TYPE
SYNTAX INTEGER
MAX-ACCESS read-write
STATUS current
DESCRIPTION
"Data value."
::= { dataArray11 257 }

dataValue11_258 OBJECT-TYPE
SYNTAX INTEGER
MAX-ACCESS read-write
STATUS current
DESCRIPTION
"Data value."
::= { dataArray11 258 }

dataValue11_259 OBJECT-TYPE
SYNTAX INTEGER
MAX-ACCESS read-write
STATUS current
DESCRIPTION
"Data value."
::= { dataArray11 259 }

dataValue11_260 OBJECT-TYPE
SYNTAX INTEGER
MAX-ACCESS read-write
STATUS current
DESCRIPTION
"Data value."
::= { dataArray11 260 }

dataValue11_261 OBJECT-TYPE
SYNTAX INTEGER
MAX-ACCESS read-write
STATUS current
DESCRIPTION
"Data value."
::= { dataArray11 261 }

dataValue11_262 OBJECT-TYPE
SYNTAX INTEGER
MAX-ACCESS read-write
STATUS current
DESCRIPTION
"Data value."
::= { dataArray11 262 }

dataValue11_263 OBJECT-TYPE
SYNTAX INTEGER
MAX-ACCESS read-write
STATUS current
DESCRIPTION
"Data value."
::= { dataArray11 263 }

dataValue11_264 OBJECT-TYPE
SYNTAX INTEGER
MAX-ACCESS read-write
STATUS current
DESCRIPTION
"Data value."
::= { dataArray11 264 }

dataValue11_265 OBJECT-TYPE
SYNTAX INTEGER
MAX-ACCESS read-write
STATUS current
DESCRIPTION
"Data value."
::= { dataArray11 265 }

dataValue11_266 OBJECT-TYPE
SYNTAX INTEGER
MAX-ACCESS read-write
STATUS current
DESCRIPTION
"Data value."
::= { dataArray11 266 }

dataValue11_267 OBJECT-TYPE
SYNTAX INTEGER
MAX-ACCESS read-write
STATUS current
DESCRIPTION
"Data value."
::= { dataArray11 267 }

dataValue11_268 OBJECT-TYPE
SYNTAX INTEGER
MAX-ACCESS read-write
STATUS current
DESCRIPTION
"Data value."
::= { dataArray11 268 }

dataValue11_269 OBJECT-TYPE
SYNTAX INTEGER
MAX-ACCESS read-write
STATUS current
DESCRIPTION
"Data value."
::= { dataArray11 269 }

dataValue11_270 OBJECT-TYPE
SYNTAX INTEGER
MAX-ACCESS read-write
STATUS current
DESCRIPTION
"Data value."
::= { dataArray11 270 }

dataValue11_271 OBJECT-TYPE
SYNTAX INTEGER
MAX-ACCESS read-write
STATUS current
DESCRIPTION
"Data value."
::= { dataArray11 271 }

dataValue11_272 OBJECT-TYPE
SYNTAX INTEGER
MAX-ACCESS read-write
STATUS current
DESCRIPTION
"Data value."
::= { dataArray11 272 }

dataValue11_273 OBJECT-TYPE
SYNTAX INTEGER
MAX-ACCESS read-write
STATUS current
DESCRIPTION
"Data value."
::= { dataArray11 273 }

dataValue11_274 OBJECT-TYPE
SYNTAX INTEGER
MAX-ACCESS read-write
STATUS current
DESCRIPTION
"Data value."
::= { dataArray11 274 }

dataValue11_275 OBJECT-TYPE
SYNTAX INTEGER
MAX-ACCESS read-write
STATUS current
DESCRIPTION
"Data value."
::= { dataArray11 275 }

dataValue11_276 OBJECT-TYPE
SYNTAX INTEGER
MAX-ACCESS read-write
STATUS current
DESCRIPTION
"Data value."
::= { dataArray11 276 }

dataValue11_277 OBJECT-TYPE
SYNTAX INTEGER
MAX-ACCESS read-write
STATUS current
DESCRIPTION
"Data value."
::= { dataArray11 277 }

dataValue11_278 OBJECT-TYPE
SYNTAX INTEGER
MAX-ACCESS read-write
STATUS current
DESCRIPTION
"Data value."
::= { dataArray11 278 }

dataValue11_279 OBJECT-TYPE
SYNTAX INTEGER
MAX-ACCESS read-write
STATUS current
DESCRIPTION
"Data value."
::= { dataArray11 279 }

dataValue11_280 OBJECT-TYPE
SYNTAX INTEGER
MAX-ACCESS read-write
STATUS current
DESCRIPTION
"Data value."
::= { dataArray11 280 }

dataValue11_281 OBJECT-TYPE
SYNTAX INTEGER
MAX-ACCESS read-write
STATUS current
DESCRIPTION
"Data value."
::= { dataArray11 281 }

dataValue11_282 OBJECT-TYPE
SYNTAX INTEGER
MAX-ACCESS read-write
STATUS current
DESCRIPTION
"Data value."
::= { dataArray11 282 }

dataValue11_283 OBJECT-TYPE
SYNTAX INTEGER
MAX-ACCESS read-write
STATUS current
DESCRIPTION
"Data value."
::= { dataArray11 283 }

dataValue11_284 OBJECT-TYPE
SYNTAX INTEGER
MAX-ACCESS read-write
STATUS current
DESCRIPTION
"Data value."
::= { dataArray11 284 }

dataValue11_285 OBJECT-TYPE
SYNTAX INTEGER
MAX-ACCESS read-write
STATUS current
DESCRIPTION
"Data value."
::= { dataArray11 285 }

dataValue11_286 OBJECT-TYPE
SYNTAX INTEGER
MAX-ACCESS read-write
STATUS current
DESCRIPTION
"Data value."
::= { dataArray11 286 }

dataValue11_287 OBJECT-TYPE
SYNTAX INTEGER
MAX-ACCESS read-write
STATUS current
DESCRIPTION
"Data value."
::= { dataArray11 287 }

dataValue11_288 OBJECT-TYPE
SYNTAX INTEGER
MAX-ACCESS read-write
STATUS current
DESCRIPTION
"Data value."
::= { dataArray11 288 }

dataValue11_289 OBJECT-TYPE
SYNTAX INTEGER
MAX-ACCESS read-write
STATUS current
DESCRIPTION
"Data value."
::= { dataArray11 289 }

dataValue11_290 OBJECT-TYPE
SYNTAX INTEGER
MAX-ACCESS read-write
STATUS current
DESCRIPTION
"Data value."
::= { dataArray11 290 }

dataValue11_291 OBJECT-TYPE
SYNTAX INTEGER
MAX-ACCESS read-write
STATUS current
DESCRIPTION
"Data value."
::= { dataArray11 291 }

dataValue11_292 OBJECT-TYPE
SYNTAX INTEGER
MAX-ACCESS read-write
STATUS current
DESCRIPTION
"Data value."
::= { dataArray11 292 }

dataValue11_293 OBJECT-TYPE
SYNTAX INTEGER
MAX-ACCESS read-write
STATUS current
DESCRIPTION
"Data value."
::= { dataArray11 293 }

dataValue11_294 OBJECT-TYPE
SYNTAX INTEGER
MAX-ACCESS read-write
STATUS current
DESCRIPTION
"Data value."
::= { dataArray11 294 }

dataValue11_295 OBJECT-TYPE
SYNTAX INTEGER
MAX-ACCESS read-write
STATUS current
DESCRIPTION
"Data value."
::= { dataArray11 295 }

dataValue11_296 OBJECT-TYPE
SYNTAX INTEGER
MAX-ACCESS read-write
STATUS current
DESCRIPTION
"Data value."
::= { dataArray11 296 }

dataValue11_297 OBJECT-TYPE
SYNTAX INTEGER
MAX-ACCESS read-write
STATUS current
DESCRIPTION
"Data value."
::= { dataArray11 297 }

dataValue11_298 OBJECT-TYPE
SYNTAX INTEGER
MAX-ACCESS read-write
STATUS current
DESCRIPTION
"Data value."
::= { dataArray11 298 }

dataValue11_299 OBJECT-TYPE
SYNTAX INTEGER
MAX-ACCESS read-write
STATUS current
DESCRIPTION
"Data value."
::= { dataArray11 299 }

dataValue11_300 OBJECT-TYPE
SYNTAX INTEGER
MAX-ACCESS read-write
STATUS current
DESCRIPTION
"Data value."
::= { dataArray11 300 }

dataValue11_301 OBJECT-TYPE
SYNTAX INTEGER
MAX-ACCESS read-write
STATUS current
DESCRIPTION
"Data value."
::= { dataArray11 301 }

dataValue11_302 OBJECT-TYPE
SYNTAX INTEGER
MAX-ACCESS read-write
STATUS current
DESCRIPTION
"Data value."
::= { dataArray11 302 }

dataValue11_303 OBJECT-TYPE
SYNTAX INTEGER
MAX-ACCESS read-write
STATUS current
DESCRIPTION
"Data value."
::= { dataArray11 303 }

dataValue11_304 OBJECT-TYPE
SYNTAX INTEGER
MAX-ACCESS read-write
STATUS current
DESCRIPTION
"Data value."
::= { dataArray11 304 }

dataValue11_305 OBJECT-TYPE
SYNTAX INTEGER
MAX-ACCESS read-write
STATUS current
DESCRIPTION
"Data value."
::= { dataArray11 305 }

dataValue11_306 OBJECT-TYPE
SYNTAX INTEGER
MAX-ACCESS read-write
STATUS current
DESCRIPTION
"Data value."
::= { dataArray11 306 }

dataValue11_307 OBJECT-TYPE
SYNTAX INTEGER
MAX-ACCESS read-write
STATUS current
DESCRIPTION
"Data value."
::= { dataArray11 307 }

dataValue11_308 OBJECT-TYPE
SYNTAX INTEGER
MAX-ACCESS read-write
STATUS current
DESCRIPTION
"Data value."
::= { dataArray11 308 }

dataValue11_309 OBJECT-TYPE
SYNTAX INTEGER
MAX-ACCESS read-write
STATUS current
DESCRIPTION
"Data value."
::= { dataArray11 309 }

dataValue11_310 OBJECT-TYPE
SYNTAX INTEGER
MAX-ACCESS read-write
STATUS current
DESCRIPTION
"Data value."
::= { dataArray11 310 }

dataValue11_311 OBJECT-TYPE
SYNTAX INTEGER
MAX-ACCESS read-write
STATUS current
DESCRIPTION
"Data value."
::= { dataArray11 311 }

dataValue11_312 OBJECT-TYPE
SYNTAX INTEGER
MAX-ACCESS read-write
STATUS current
DESCRIPTION
"Data value."
::= { dataArray11 312 }

dataValue11_313 OBJECT-TYPE
SYNTAX INTEGER
MAX-ACCESS read-write
STATUS current
DESCRIPTION
"Data value."
::= { dataArray11 313 }

dataValue11_314 OBJECT-TYPE
SYNTAX INTEGER
MAX-ACCESS read-write
STATUS current
DESCRIPTION
"Data value."
::= { dataArray11 314 }

dataValue11_315 OBJECT-TYPE
SYNTAX INTEGER
MAX-ACCESS read-write
STATUS current
DESCRIPTION
"Data value."
::= { dataArray11 315 }

dataValue11_316 OBJECT-TYPE
SYNTAX INTEGER
MAX-ACCESS read-write
STATUS current
DESCRIPTION
"Data value."
::= { dataArray11 316 }

dataValue11_317 OBJECT-TYPE
SYNTAX INTEGER
MAX-ACCESS read-write
STATUS current
DESCRIPTION
"Data value."
::= { dataArray11 317 }

dataValue11_318 OBJECT-TYPE
SYNTAX INTEGER
MAX-ACCESS read-write
STATUS current
DESCRIPTION
"Data value."
::= { dataArray11 318 }

dataValue11_319 OBJECT-TYPE
SYNTAX INTEGER
MAX-ACCESS read-write
STATUS current
DESCRIPTION
"Data value."
::= { dataArray11 319 }

dataValue11_320 OBJECT-TYPE
SYNTAX INTEGER
MAX-ACCESS read-write
STATUS current
DESCRIPTION
"Data value."
::= { dataArray11 320 }

dataValue11_321 OBJECT-TYPE
SYNTAX INTEGER
MAX-ACCESS read-write
STATUS current
DESCRIPTION
"Data value."
::= { dataArray11 321 }

dataValue11_322 OBJECT-TYPE
SYNTAX INTEGER
MAX-ACCESS read-write
STATUS current
DESCRIPTION
"Data value."
::= { dataArray11 322 }

dataValue11_323 OBJECT-TYPE
SYNTAX INTEGER
MAX-ACCESS read-write
STATUS current
DESCRIPTION
"Data value."
::= { dataArray11 323 }

dataValue11_324 OBJECT-TYPE
SYNTAX INTEGER
MAX-ACCESS read-write
STATUS current
DESCRIPTION
"Data value."
::= { dataArray11 324 }

dataValue11_325 OBJECT-TYPE
SYNTAX INTEGER
MAX-ACCESS read-write
STATUS current
DESCRIPTION
"Data value."
::= { dataArray11 325 }

dataValue11_326 OBJECT-TYPE
SYNTAX INTEGER
MAX-ACCESS read-write
STATUS current
DESCRIPTION
"Data value."
::= { dataArray11 326 }

dataValue11_327 OBJECT-TYPE
SYNTAX INTEGER
MAX-ACCESS read-write
STATUS current
DESCRIPTION
"Data value."
::= { dataArray11 327 }

dataValue11_328 OBJECT-TYPE
SYNTAX INTEGER
MAX-ACCESS read-write
STATUS current
DESCRIPTION
"Data value."
::= { dataArray11 328 }

dataValue11_329 OBJECT-TYPE
SYNTAX INTEGER
MAX-ACCESS read-write
STATUS current
DESCRIPTION
"Data value."
::= { dataArray11 329 }

dataValue11_330 OBJECT-TYPE
SYNTAX INTEGER
MAX-ACCESS read-write
STATUS current
DESCRIPTION
"Data value."
::= { dataArray11 330 }

dataValue11_331 OBJECT-TYPE
SYNTAX INTEGER
MAX-ACCESS read-write
STATUS current
DESCRIPTION
"Data value."
::= { dataArray11 331 }

dataValue11_332 OBJECT-TYPE
SYNTAX INTEGER
MAX-ACCESS read-write
STATUS current
DESCRIPTION
"Data value."
::= { dataArray11 332 }

dataValue11_333 OBJECT-TYPE
SYNTAX INTEGER
MAX-ACCESS read-write
STATUS current
DESCRIPTION
"Data value."
::= { dataArray11 333 }

dataValue11_334 OBJECT-TYPE
SYNTAX INTEGER
MAX-ACCESS read-write
STATUS current
DESCRIPTION
"Data value."
::= { dataArray11 334 }

dataValue11_335 OBJECT-TYPE
SYNTAX INTEGER
MAX-ACCESS read-write
STATUS current
DESCRIPTION
"Data value."
::= { dataArray11 335 }

dataValue11_336 OBJECT-TYPE
SYNTAX INTEGER
MAX-ACCESS read-write
STATUS current
DESCRIPTION
"Data value."
::= { dataArray11 336 }

dataValue11_337 OBJECT-TYPE
SYNTAX INTEGER
MAX-ACCESS read-write
STATUS current
DESCRIPTION
"Data value."
::= { dataArray11 337 }

dataValue11_338 OBJECT-TYPE
SYNTAX INTEGER
MAX-ACCESS read-write
STATUS current
DESCRIPTION
"Data value."
::= { dataArray11 338 }

dataValue11_339 OBJECT-TYPE
SYNTAX INTEGER
MAX-ACCESS read-write
STATUS current
DESCRIPTION
"Data value."
::= { dataArray11 339 }

dataValue11_340 OBJECT-TYPE
SYNTAX INTEGER
MAX-ACCESS read-write
STATUS current
DESCRIPTION
"Data value."
::= { dataArray11 340 }

dataValue11_341 OBJECT-TYPE
SYNTAX INTEGER
MAX-ACCESS read-write
STATUS current
DESCRIPTION
"Data value."
::= { dataArray11 341 }

dataValue11_342 OBJECT-TYPE
SYNTAX INTEGER
MAX-ACCESS read-write
STATUS current
DESCRIPTION
"Data value."
::= { dataArray11 342 }

dataValue11_343 OBJECT-TYPE
SYNTAX INTEGER
MAX-ACCESS read-write
STATUS current
DESCRIPTION
"Data value."
::= { dataArray11 343 }

dataValue11_344 OBJECT-TYPE
SYNTAX INTEGER
MAX-ACCESS read-write
STATUS current
DESCRIPTION
"Data value."
::= { dataArray11 344 }

dataValue11_345 OBJECT-TYPE
SYNTAX INTEGER
MAX-ACCESS read-write
STATUS current
DESCRIPTION
"Data value."
::= { dataArray11 345 }

dataValue11_346 OBJECT-TYPE
SYNTAX INTEGER
MAX-ACCESS read-write
STATUS current
DESCRIPTION
"Data value."
::= { dataArray11 346 }

dataValue11_347 OBJECT-TYPE
SYNTAX INTEGER
MAX-ACCESS read-write
STATUS current
DESCRIPTION
"Data value."
::= { dataArray11 347 }

dataValue11_348 OBJECT-TYPE
SYNTAX INTEGER
MAX-ACCESS read-write
STATUS current
DESCRIPTION
"Data value."
::= { dataArray11 348 }

dataValue11_349 OBJECT-TYPE
SYNTAX INTEGER
MAX-ACCESS read-write
STATUS current
DESCRIPTION
"Data value."
::= { dataArray11 349 }

dataValue11_350 OBJECT-TYPE
SYNTAX INTEGER
MAX-ACCESS read-write
STATUS current
DESCRIPTION
"Data value."
::= { dataArray11 350 }

dataValue11_351 OBJECT-TYPE
SYNTAX INTEGER
MAX-ACCESS read-write
STATUS current
DESCRIPTION
"Data value."
::= { dataArray11 351 }

dataValue11_352 OBJECT-TYPE
SYNTAX INTEGER
MAX-ACCESS read-write
STATUS current
DESCRIPTION
"Data value."
::= { dataArray11 352 }

dataValue11_353 OBJECT-TYPE
SYNTAX INTEGER
MAX-ACCESS read-write
STATUS current
DESCRIPTION
"Data value."
::= { dataArray11 353 }

dataValue11_354 OBJECT-TYPE
SYNTAX INTEGER
MAX-ACCESS read-write
STATUS current
DESCRIPTION
"Data value."
::= { dataArray11 354 }

dataValue11_355 OBJECT-TYPE
SYNTAX INTEGER
MAX-ACCESS read-write
STATUS current
DESCRIPTION
"Data value."
::= { dataArray11 355 }

dataValue11_356 OBJECT-TYPE
SYNTAX INTEGER
MAX-ACCESS read-write
STATUS current
DESCRIPTION
"Data value."
::= { dataArray11 356 }

dataValue11_357 OBJECT-TYPE
SYNTAX INTEGER
MAX-ACCESS read-write
STATUS current
DESCRIPTION
"Data value."
::= { dataArray11 357 }

dataValue11_358 OBJECT-TYPE
SYNTAX INTEGER
MAX-ACCESS read-write
STATUS current
DESCRIPTION
"Data value."
::= { dataArray11 358 }

dataValue11_359 OBJECT-TYPE
SYNTAX INTEGER
MAX-ACCESS read-write
STATUS current
DESCRIPTION
"Data value."
::= { dataArray11 359 }

dataValue11_360 OBJECT-TYPE
SYNTAX INTEGER
MAX-ACCESS read-write
STATUS current
DESCRIPTION
"Data value."
::= { dataArray11 360 }

dataValue11_361 OBJECT-TYPE
SYNTAX INTEGER
MAX-ACCESS read-write
STATUS current
DESCRIPTION
"Data value."
::= { dataArray11 361 }

dataValue11_362 OBJECT-TYPE
SYNTAX INTEGER
MAX-ACCESS read-write
STATUS current
DESCRIPTION
"Data value."
::= { dataArray11 362 }

dataValue11_363 OBJECT-TYPE
SYNTAX INTEGER
MAX-ACCESS read-write
STATUS current
DESCRIPTION
"Data value."
::= { dataArray11 363 }

dataValue11_364 OBJECT-TYPE
SYNTAX INTEGER
MAX-ACCESS read-write
STATUS current
DESCRIPTION
"Data value."
::= { dataArray11 364 }

dataValue11_365 OBJECT-TYPE
SYNTAX INTEGER
MAX-ACCESS read-write
STATUS current
DESCRIPTION
"Data value."
::= { dataArray11 365 }

dataValue11_366 OBJECT-TYPE
SYNTAX INTEGER
MAX-ACCESS read-write
STATUS current
DESCRIPTION
"Data value."
::= { dataArray11 366 }

dataValue11_367 OBJECT-TYPE
SYNTAX INTEGER
MAX-ACCESS read-write
STATUS current
DESCRIPTION
"Data value."
::= { dataArray11 367 }

dataValue11_368 OBJECT-TYPE
SYNTAX INTEGER
MAX-ACCESS read-write
STATUS current
DESCRIPTION
"Data value."
::= { dataArray11 368 }

dataValue11_369 OBJECT-TYPE
SYNTAX INTEGER
MAX-ACCESS read-write
STATUS current
DESCRIPTION
"Data value."
::= { dataArray11 369 }

dataValue11_370 OBJECT-TYPE
SYNTAX INTEGER
MAX-ACCESS read-write
STATUS current
DESCRIPTION
"Data value."
::= { dataArray11 370 }

dataValue11_371 OBJECT-TYPE
SYNTAX INTEGER
MAX-ACCESS read-write
STATUS current
DESCRIPTION
"Data value."
::= { dataArray11 371 }

dataValue11_372 OBJECT-TYPE
SYNTAX INTEGER
MAX-ACCESS read-write
STATUS current
DESCRIPTION
"Data value."
::= { dataArray11 372 }

dataValue11_373 OBJECT-TYPE
SYNTAX INTEGER
MAX-ACCESS read-write
STATUS current
DESCRIPTION
"Data value."
::= { dataArray11 373 }

dataValue11_374 OBJECT-TYPE
SYNTAX INTEGER
MAX-ACCESS read-write
STATUS current
DESCRIPTION
"Data value."
::= { dataArray11 374 }

dataValue11_375 OBJECT-TYPE
SYNTAX INTEGER
MAX-ACCESS read-write
STATUS current
DESCRIPTION
"Data value."
::= { dataArray11 375 }

dataValue11_376 OBJECT-TYPE
SYNTAX INTEGER
MAX-ACCESS read-write
STATUS current
DESCRIPTION
"Data value."
::= { dataArray11 376 }

dataValue11_377 OBJECT-TYPE
SYNTAX INTEGER
MAX-ACCESS read-write
STATUS current
DESCRIPTION
"Data value."
::= { dataArray11 377 }

dataValue11_378 OBJECT-TYPE
SYNTAX INTEGER
MAX-ACCESS read-write
STATUS current
DESCRIPTION
"Data value."
::= { dataArray11 378 }

dataValue11_379 OBJECT-TYPE
SYNTAX INTEGER
MAX-ACCESS read-write
STATUS current
DESCRIPTION
"Data value."
::= { dataArray11 379 }

dataValue11_380 OBJECT-TYPE
SYNTAX INTEGER
MAX-ACCESS read-write
STATUS current
DESCRIPTION
"Data value."
::= { dataArray11 380 }

dataValue11_381 OBJECT-TYPE
SYNTAX INTEGER
MAX-ACCESS read-write
STATUS current
DESCRIPTION
"Data value."
::= { dataArray11 381 }

dataValue11_382 OBJECT-TYPE
SYNTAX INTEGER
MAX-ACCESS read-write
STATUS current
DESCRIPTION
"Data value."
::= { dataArray11 382 }

dataValue11_383 OBJECT-TYPE
SYNTAX INTEGER
MAX-ACCESS read-write
STATUS current
DESCRIPTION
"Data value."
::= { dataArray11 383 }

dataValue11_384 OBJECT-TYPE
SYNTAX INTEGER
MAX-ACCESS read-write
STATUS current
DESCRIPTION
"Data value."
::= { dataArray11 384 }

dataValue11_385 OBJECT-TYPE
SYNTAX INTEGER
MAX-ACCESS read-write
STATUS current
DESCRIPTION
"Data value."
::= { dataArray11 385 }

dataValue11_386 OBJECT-TYPE
SYNTAX INTEGER
MAX-ACCESS read-write
STATUS current
DESCRIPTION
"Data value."
::= { dataArray11 386 }

dataValue11_387 OBJECT-TYPE
SYNTAX INTEGER
MAX-ACCESS read-write
STATUS current
DESCRIPTION
"Data value."
::= { dataArray11 387 }

dataValue11_388 OBJECT-TYPE
SYNTAX INTEGER
MAX-ACCESS read-write
STATUS current
DESCRIPTION
"Data value."
::= { dataArray11 388 }

dataValue11_389 OBJECT-TYPE
SYNTAX INTEGER
MAX-ACCESS read-write
STATUS current
DESCRIPTION
"Data value."
::= { dataArray11 389 }

dataValue11_390 OBJECT-TYPE
SYNTAX INTEGER
MAX-ACCESS read-write
STATUS current
DESCRIPTION
"Data value."
::= { dataArray11 390 }

dataValue11_391 OBJECT-TYPE
SYNTAX INTEGER
MAX-ACCESS read-write
STATUS current
DESCRIPTION
"Data value."
::= { dataArray11 391 }

dataValue11_392 OBJECT-TYPE
SYNTAX INTEGER
MAX-ACCESS read-write
STATUS current
DESCRIPTION
"Data value."
::= { dataArray11 392 }

dataValue11_393 OBJECT-TYPE
SYNTAX INTEGER
MAX-ACCESS read-write
STATUS current
DESCRIPTION
"Data value."
::= { dataArray11 393 }

dataValue11_394 OBJECT-TYPE
SYNTAX INTEGER
MAX-ACCESS read-write
STATUS current
DESCRIPTION
"Data value."
::= { dataArray11 394 }

dataValue11_395 OBJECT-TYPE
SYNTAX INTEGER
MAX-ACCESS read-write
STATUS current
DESCRIPTION
"Data value."
::= { dataArray11 395 }

dataValue11_396 OBJECT-TYPE
SYNTAX INTEGER
MAX-ACCESS read-write
STATUS current
DESCRIPTION
"Data value."
::= { dataArray11 396 }

dataValue11_397 OBJECT-TYPE
SYNTAX INTEGER
MAX-ACCESS read-write
STATUS current
DESCRIPTION
"Data value."
::= { dataArray11 397 }

dataValue11_398 OBJECT-TYPE
SYNTAX INTEGER
MAX-ACCESS read-write
STATUS current
DESCRIPTION
"Data value."
::= { dataArray11 398 }

dataValue11_399 OBJECT-TYPE
SYNTAX INTEGER
MAX-ACCESS read-write
STATUS current
DESCRIPTION
"Data value."
::= { dataArray11 399 }

dataArray12 OBJECT IDENTIFIER ::= { cc08255400_v1_00a 12 }

dataValue12_0 OBJECT-TYPE
SYNTAX INTEGER
MAX-ACCESS read-write
STATUS current
DESCRIPTION
"Data value."
::= { dataArray12 0 }

dataValue12_1 OBJECT-TYPE
SYNTAX INTEGER
MAX-ACCESS read-write
STATUS current
DESCRIPTION
"Data value."
::= { dataArray12 1 }

dataValue12_2 OBJECT-TYPE
SYNTAX INTEGER
MAX-ACCESS read-write
STATUS current
DESCRIPTION
"Data value."
::= { dataArray12 2 }

dataValue12_3 OBJECT-TYPE
SYNTAX INTEGER
MAX-ACCESS read-write
STATUS current
DESCRIPTION
"Data value."
::= { dataArray12 3 }

dataValue12_4 OBJECT-TYPE
SYNTAX INTEGER
MAX-ACCESS read-write
STATUS current
DESCRIPTION
"Data value."
::= { dataArray12 4 }

dataValue12_5 OBJECT-TYPE
SYNTAX INTEGER
MAX-ACCESS read-write
STATUS current
DESCRIPTION
"Data value."
::= { dataArray12 5 }

dataValue12_6 OBJECT-TYPE
SYNTAX INTEGER
MAX-ACCESS read-write
STATUS current
DESCRIPTION
"Data value."
::= { dataArray12 6 }

dataValue12_7 OBJECT-TYPE
SYNTAX INTEGER
MAX-ACCESS read-write
STATUS current
DESCRIPTION
"Data value."
::= { dataArray12 7 }

dataValue12_8 OBJECT-TYPE
SYNTAX INTEGER
MAX-ACCESS read-write
STATUS current
DESCRIPTION
"Data value."
::= { dataArray12 8 }

dataValue12_9 OBJECT-TYPE
SYNTAX INTEGER
MAX-ACCESS read-write
STATUS current
DESCRIPTION
"Data value."
::= { dataArray12 9 }

dataValue12_10 OBJECT-TYPE
SYNTAX INTEGER
MAX-ACCESS read-write
STATUS current
DESCRIPTION
"Data value."
::= { dataArray12 10 }

dataValue12_11 OBJECT-TYPE
SYNTAX INTEGER
MAX-ACCESS read-write
STATUS current
DESCRIPTION
"Data value."
::= { dataArray12 11 }

dataValue12_12 OBJECT-TYPE
SYNTAX INTEGER
MAX-ACCESS read-write
STATUS current
DESCRIPTION
"Data value."
::= { dataArray12 12 }

dataValue12_13 OBJECT-TYPE
SYNTAX INTEGER
MAX-ACCESS read-write
STATUS current
DESCRIPTION
"Data value."
::= { dataArray12 13 }

dataValue12_14 OBJECT-TYPE
SYNTAX INTEGER
MAX-ACCESS read-write
STATUS current
DESCRIPTION
"Data value."
::= { dataArray12 14 }

dataValue12_15 OBJECT-TYPE
SYNTAX INTEGER
MAX-ACCESS read-write
STATUS current
DESCRIPTION
"Data value."
::= { dataArray12 15 }

dataValue12_16 OBJECT-TYPE
SYNTAX INTEGER
MAX-ACCESS read-write
STATUS current
DESCRIPTION
"Data value."
::= { dataArray12 16 }

dataValue12_17 OBJECT-TYPE
SYNTAX INTEGER
MAX-ACCESS read-write
STATUS current
DESCRIPTION
"Data value."
::= { dataArray12 17 }

dataValue12_18 OBJECT-TYPE
SYNTAX INTEGER
MAX-ACCESS read-write
STATUS current
DESCRIPTION
"Data value."
::= { dataArray12 18 }

dataValue12_19 OBJECT-TYPE
SYNTAX INTEGER
MAX-ACCESS read-write
STATUS current
DESCRIPTION
"Data value."
::= { dataArray12 19 }

dataValue12_20 OBJECT-TYPE
SYNTAX INTEGER
MAX-ACCESS read-write
STATUS current
DESCRIPTION
"Data value."
::= { dataArray12 20 }

dataValue12_21 OBJECT-TYPE
SYNTAX INTEGER
MAX-ACCESS read-write
STATUS current
DESCRIPTION
"Data value."
::= { dataArray12 21 }

dataValue12_22 OBJECT-TYPE
SYNTAX INTEGER
MAX-ACCESS read-write
STATUS current
DESCRIPTION
"Data value."
::= { dataArray12 22 }

dataValue12_23 OBJECT-TYPE
SYNTAX INTEGER
MAX-ACCESS read-write
STATUS current
DESCRIPTION
"Data value."
::= { dataArray12 23 }

dataValue12_24 OBJECT-TYPE
SYNTAX INTEGER
MAX-ACCESS read-write
STATUS current
DESCRIPTION
"Data value."
::= { dataArray12 24 }

dataValue12_25 OBJECT-TYPE
SYNTAX INTEGER
MAX-ACCESS read-write
STATUS current
DESCRIPTION
"Data value."
::= { dataArray12 25 }

dataValue12_26 OBJECT-TYPE
SYNTAX INTEGER
MAX-ACCESS read-write
STATUS current
DESCRIPTION
"Data value."
::= { dataArray12 26 }

dataValue12_27 OBJECT-TYPE
SYNTAX INTEGER
MAX-ACCESS read-write
STATUS current
DESCRIPTION
"Data value."
::= { dataArray12 27 }

dataValue12_28 OBJECT-TYPE
SYNTAX INTEGER
MAX-ACCESS read-write
STATUS current
DESCRIPTION
"Data value."
::= { dataArray12 28 }

dataValue12_29 OBJECT-TYPE
SYNTAX INTEGER
MAX-ACCESS read-write
STATUS current
DESCRIPTION
"Data value."
::= { dataArray12 29 }

dataValue12_30 OBJECT-TYPE
SYNTAX INTEGER
MAX-ACCESS read-write
STATUS current
DESCRIPTION
"Data value."
::= { dataArray12 30 }

dataValue12_31 OBJECT-TYPE
SYNTAX INTEGER
MAX-ACCESS read-write
STATUS current
DESCRIPTION
"Data value."
::= { dataArray12 31 }

dataValue12_32 OBJECT-TYPE
SYNTAX INTEGER
MAX-ACCESS read-write
STATUS current
DESCRIPTION
"Data value."
::= { dataArray12 32 }

dataValue12_33 OBJECT-TYPE
SYNTAX INTEGER
MAX-ACCESS read-write
STATUS current
DESCRIPTION
"Data value."
::= { dataArray12 33 }

dataValue12_34 OBJECT-TYPE
SYNTAX INTEGER
MAX-ACCESS read-write
STATUS current
DESCRIPTION
"Data value."
::= { dataArray12 34 }

dataValue12_35 OBJECT-TYPE
SYNTAX INTEGER
MAX-ACCESS read-write
STATUS current
DESCRIPTION
"Data value."
::= { dataArray12 35 }

dataValue12_36 OBJECT-TYPE
SYNTAX INTEGER
MAX-ACCESS read-write
STATUS current
DESCRIPTION
"Data value."
::= { dataArray12 36 }

dataValue12_37 OBJECT-TYPE
SYNTAX INTEGER
MAX-ACCESS read-write
STATUS current
DESCRIPTION
"Data value."
::= { dataArray12 37 }

dataValue12_38 OBJECT-TYPE
SYNTAX INTEGER
MAX-ACCESS read-write
STATUS current
DESCRIPTION
"Data value."
::= { dataArray12 38 }

dataValue12_39 OBJECT-TYPE
SYNTAX INTEGER
MAX-ACCESS read-write
STATUS current
DESCRIPTION
"Data value."
::= { dataArray12 39 }

dataValue12_40 OBJECT-TYPE
SYNTAX INTEGER
MAX-ACCESS read-write
STATUS current
DESCRIPTION
"Data value."
::= { dataArray12 40 }

dataValue12_41 OBJECT-TYPE
SYNTAX INTEGER
MAX-ACCESS read-write
STATUS current
DESCRIPTION
"Data value."
::= { dataArray12 41 }

dataValue12_42 OBJECT-TYPE
SYNTAX INTEGER
MAX-ACCESS read-write
STATUS current
DESCRIPTION
"Data value."
::= { dataArray12 42 }

dataValue12_43 OBJECT-TYPE
SYNTAX INTEGER
MAX-ACCESS read-write
STATUS current
DESCRIPTION
"Data value."
::= { dataArray12 43 }

dataValue12_44 OBJECT-TYPE
SYNTAX INTEGER
MAX-ACCESS read-write
STATUS current
DESCRIPTION
"Data value."
::= { dataArray12 44 }

dataValue12_45 OBJECT-TYPE
SYNTAX INTEGER
MAX-ACCESS read-write
STATUS current
DESCRIPTION
"Data value."
::= { dataArray12 45 }

dataValue12_46 OBJECT-TYPE
SYNTAX INTEGER
MAX-ACCESS read-write
STATUS current
DESCRIPTION
"Data value."
::= { dataArray12 46 }

dataValue12_47 OBJECT-TYPE
SYNTAX INTEGER
MAX-ACCESS read-write
STATUS current
DESCRIPTION
"Data value."
::= { dataArray12 47 }

dataValue12_48 OBJECT-TYPE
SYNTAX INTEGER
MAX-ACCESS read-write
STATUS current
DESCRIPTION
"Data value."
::= { dataArray12 48 }

dataValue12_49 OBJECT-TYPE
SYNTAX INTEGER
MAX-ACCESS read-write
STATUS current
DESCRIPTION
"Data value."
::= { dataArray12 49 }

dataValue12_50 OBJECT-TYPE
SYNTAX INTEGER
MAX-ACCESS read-write
STATUS current
DESCRIPTION
"Data value."
::= { dataArray12 50 }

dataValue12_51 OBJECT-TYPE
SYNTAX INTEGER
MAX-ACCESS read-write
STATUS current
DESCRIPTION
"Data value."
::= { dataArray12 51 }

dataValue12_52 OBJECT-TYPE
SYNTAX INTEGER
MAX-ACCESS read-write
STATUS current
DESCRIPTION
"Data value."
::= { dataArray12 52 }

dataValue12_53 OBJECT-TYPE
SYNTAX INTEGER
MAX-ACCESS read-write
STATUS current
DESCRIPTION
"Data value."
::= { dataArray12 53 }

dataValue12_54 OBJECT-TYPE
SYNTAX INTEGER
MAX-ACCESS read-write
STATUS current
DESCRIPTION
"Data value."
::= { dataArray12 54 }

dataValue12_55 OBJECT-TYPE
SYNTAX INTEGER
MAX-ACCESS read-write
STATUS current
DESCRIPTION
"Data value."
::= { dataArray12 55 }

dataValue12_56 OBJECT-TYPE
SYNTAX INTEGER
MAX-ACCESS read-write
STATUS current
DESCRIPTION
"Data value."
::= { dataArray12 56 }

dataValue12_57 OBJECT-TYPE
SYNTAX INTEGER
MAX-ACCESS read-write
STATUS current
DESCRIPTION
"Data value."
::= { dataArray12 57 }

dataValue12_58 OBJECT-TYPE
SYNTAX INTEGER
MAX-ACCESS read-write
STATUS current
DESCRIPTION
"Data value."
::= { dataArray12 58 }

dataValue12_59 OBJECT-TYPE
SYNTAX INTEGER
MAX-ACCESS read-write
STATUS current
DESCRIPTION
"Data value."
::= { dataArray12 59 }

dataValue12_60 OBJECT-TYPE
SYNTAX INTEGER
MAX-ACCESS read-write
STATUS current
DESCRIPTION
"Data value."
::= { dataArray12 60 }

dataValue12_61 OBJECT-TYPE
SYNTAX INTEGER
MAX-ACCESS read-write
STATUS current
DESCRIPTION
"Data value."
::= { dataArray12 61 }

dataValue12_62 OBJECT-TYPE
SYNTAX INTEGER
MAX-ACCESS read-write
STATUS current
DESCRIPTION
"Data value."
::= { dataArray12 62 }

dataValue12_63 OBJECT-TYPE
SYNTAX INTEGER
MAX-ACCESS read-write
STATUS current
DESCRIPTION
"Data value."
::= { dataArray12 63 }

dataValue12_64 OBJECT-TYPE
SYNTAX INTEGER
MAX-ACCESS read-write
STATUS current
DESCRIPTION
"Data value."
::= { dataArray12 64 }

dataValue12_65 OBJECT-TYPE
SYNTAX INTEGER
MAX-ACCESS read-write
STATUS current
DESCRIPTION
"Data value."
::= { dataArray12 65 }

dataValue12_66 OBJECT-TYPE
SYNTAX INTEGER
MAX-ACCESS read-write
STATUS current
DESCRIPTION
"Data value."
::= { dataArray12 66 }

dataValue12_67 OBJECT-TYPE
SYNTAX INTEGER
MAX-ACCESS read-write
STATUS current
DESCRIPTION
"Data value."
::= { dataArray12 67 }

dataValue12_68 OBJECT-TYPE
SYNTAX INTEGER
MAX-ACCESS read-write
STATUS current
DESCRIPTION
"Data value."
::= { dataArray12 68 }

dataValue12_69 OBJECT-TYPE
SYNTAX INTEGER
MAX-ACCESS read-write
STATUS current
DESCRIPTION
"Data value."
::= { dataArray12 69 }

dataValue12_70 OBJECT-TYPE
SYNTAX INTEGER
MAX-ACCESS read-write
STATUS current
DESCRIPTION
"Data value."
::= { dataArray12 70 }

dataValue12_71 OBJECT-TYPE
SYNTAX INTEGER
MAX-ACCESS read-write
STATUS current
DESCRIPTION
"Data value."
::= { dataArray12 71 }

dataValue12_72 OBJECT-TYPE
SYNTAX INTEGER
MAX-ACCESS read-write
STATUS current
DESCRIPTION
"Data value."
::= { dataArray12 72 }

dataValue12_73 OBJECT-TYPE
SYNTAX INTEGER
MAX-ACCESS read-write
STATUS current
DESCRIPTION
"Data value."
::= { dataArray12 73 }

dataValue12_74 OBJECT-TYPE
SYNTAX INTEGER
MAX-ACCESS read-write
STATUS current
DESCRIPTION
"Data value."
::= { dataArray12 74 }

dataValue12_75 OBJECT-TYPE
SYNTAX INTEGER
MAX-ACCESS read-write
STATUS current
DESCRIPTION
"Data value."
::= { dataArray12 75 }

dataValue12_76 OBJECT-TYPE
SYNTAX INTEGER
MAX-ACCESS read-write
STATUS current
DESCRIPTION
"Data value."
::= { dataArray12 76 }

dataValue12_77 OBJECT-TYPE
SYNTAX INTEGER
MAX-ACCESS read-write
STATUS current
DESCRIPTION
"Data value."
::= { dataArray12 77 }

dataValue12_78 OBJECT-TYPE
SYNTAX INTEGER
MAX-ACCESS read-write
STATUS current
DESCRIPTION
"Data value."
::= { dataArray12 78 }

dataValue12_79 OBJECT-TYPE
SYNTAX INTEGER
MAX-ACCESS read-write
STATUS current
DESCRIPTION
"Data value."
::= { dataArray12 79 }

dataValue12_80 OBJECT-TYPE
SYNTAX INTEGER
MAX-ACCESS read-write
STATUS current
DESCRIPTION
"Data value."
::= { dataArray12 80 }

dataValue12_81 OBJECT-TYPE
SYNTAX INTEGER
MAX-ACCESS read-write
STATUS current
DESCRIPTION
"Data value."
::= { dataArray12 81 }

dataValue12_82 OBJECT-TYPE
SYNTAX INTEGER
MAX-ACCESS read-write
STATUS current
DESCRIPTION
"Data value."
::= { dataArray12 82 }

dataValue12_83 OBJECT-TYPE
SYNTAX INTEGER
MAX-ACCESS read-write
STATUS current
DESCRIPTION
"Data value."
::= { dataArray12 83 }

dataValue12_84 OBJECT-TYPE
SYNTAX INTEGER
MAX-ACCESS read-write
STATUS current
DESCRIPTION
"Data value."
::= { dataArray12 84 }

dataValue12_85 OBJECT-TYPE
SYNTAX INTEGER
MAX-ACCESS read-write
STATUS current
DESCRIPTION
"Data value."
::= { dataArray12 85 }

dataValue12_86 OBJECT-TYPE
SYNTAX INTEGER
MAX-ACCESS read-write
STATUS current
DESCRIPTION
"Data value."
::= { dataArray12 86 }

dataValue12_87 OBJECT-TYPE
SYNTAX INTEGER
MAX-ACCESS read-write
STATUS current
DESCRIPTION
"Data value."
::= { dataArray12 87 }

dataValue12_88 OBJECT-TYPE
SYNTAX INTEGER
MAX-ACCESS read-write
STATUS current
DESCRIPTION
"Data value."
::= { dataArray12 88 }

dataValue12_89 OBJECT-TYPE
SYNTAX INTEGER
MAX-ACCESS read-write
STATUS current
DESCRIPTION
"Data value."
::= { dataArray12 89 }

dataValue12_90 OBJECT-TYPE
SYNTAX INTEGER
MAX-ACCESS read-write
STATUS current
DESCRIPTION
"Data value."
::= { dataArray12 90 }

dataValue12_91 OBJECT-TYPE
SYNTAX INTEGER
MAX-ACCESS read-write
STATUS current
DESCRIPTION
"Data value."
::= { dataArray12 91 }

dataValue12_92 OBJECT-TYPE
SYNTAX INTEGER
MAX-ACCESS read-write
STATUS current
DESCRIPTION
"Data value."
::= { dataArray12 92 }

dataValue12_93 OBJECT-TYPE
SYNTAX INTEGER
MAX-ACCESS read-write
STATUS current
DESCRIPTION
"Data value."
::= { dataArray12 93 }

dataValue12_94 OBJECT-TYPE
SYNTAX INTEGER
MAX-ACCESS read-write
STATUS current
DESCRIPTION
"Data value."
::= { dataArray12 94 }

dataValue12_95 OBJECT-TYPE
SYNTAX INTEGER
MAX-ACCESS read-write
STATUS current
DESCRIPTION
"Data value."
::= { dataArray12 95 }

dataValue12_96 OBJECT-TYPE
SYNTAX INTEGER
MAX-ACCESS read-write
STATUS current
DESCRIPTION
"Data value."
::= { dataArray12 96 }

dataValue12_97 OBJECT-TYPE
SYNTAX INTEGER
MAX-ACCESS read-write
STATUS current
DESCRIPTION
"Data value."
::= { dataArray12 97 }

dataValue12_98 OBJECT-TYPE
SYNTAX INTEGER
MAX-ACCESS read-write
STATUS current
DESCRIPTION
"Data value."
::= { dataArray12 98 }

dataValue12_99 OBJECT-TYPE
SYNTAX INTEGER
MAX-ACCESS read-write
STATUS current
DESCRIPTION
"Data value."
::= { dataArray12 99 }

dataValue12_100 OBJECT-TYPE
SYNTAX INTEGER
MAX-ACCESS read-write
STATUS current
DESCRIPTION
"Data value."
::= { dataArray12 100 }

dataValue12_101 OBJECT-TYPE
SYNTAX INTEGER
MAX-ACCESS read-write
STATUS current
DESCRIPTION
"Data value."
::= { dataArray12 101 }

dataValue12_102 OBJECT-TYPE
SYNTAX INTEGER
MAX-ACCESS read-write
STATUS current
DESCRIPTION
"Data value."
::= { dataArray12 102 }

dataValue12_103 OBJECT-TYPE
SYNTAX INTEGER
MAX-ACCESS read-write
STATUS current
DESCRIPTION
"Data value."
::= { dataArray12 103 }

dataValue12_104 OBJECT-TYPE
SYNTAX INTEGER
MAX-ACCESS read-write
STATUS current
DESCRIPTION
"Data value."
::= { dataArray12 104 }

dataValue12_105 OBJECT-TYPE
SYNTAX INTEGER
MAX-ACCESS read-write
STATUS current
DESCRIPTION
"Data value."
::= { dataArray12 105 }

dataValue12_106 OBJECT-TYPE
SYNTAX INTEGER
MAX-ACCESS read-write
STATUS current
DESCRIPTION
"Data value."
::= { dataArray12 106 }

dataValue12_107 OBJECT-TYPE
SYNTAX INTEGER
MAX-ACCESS read-write
STATUS current
DESCRIPTION
"Data value."
::= { dataArray12 107 }

dataValue12_108 OBJECT-TYPE
SYNTAX INTEGER
MAX-ACCESS read-write
STATUS current
DESCRIPTION
"Data value."
::= { dataArray12 108 }

dataValue12_109 OBJECT-TYPE
SYNTAX INTEGER
MAX-ACCESS read-write
STATUS current
DESCRIPTION
"Data value."
::= { dataArray12 109 }

dataValue12_110 OBJECT-TYPE
SYNTAX INTEGER
MAX-ACCESS read-write
STATUS current
DESCRIPTION
"Data value."
::= { dataArray12 110 }

dataValue12_111 OBJECT-TYPE
SYNTAX INTEGER
MAX-ACCESS read-write
STATUS current
DESCRIPTION
"Data value."
::= { dataArray12 111 }

dataValue12_112 OBJECT-TYPE
SYNTAX INTEGER
MAX-ACCESS read-write
STATUS current
DESCRIPTION
"Data value."
::= { dataArray12 112 }

dataValue12_113 OBJECT-TYPE
SYNTAX INTEGER
MAX-ACCESS read-write
STATUS current
DESCRIPTION
"Data value."
::= { dataArray12 113 }

dataValue12_114 OBJECT-TYPE
SYNTAX INTEGER
MAX-ACCESS read-write
STATUS current
DESCRIPTION
"Data value."
::= { dataArray12 114 }

dataValue12_115 OBJECT-TYPE
SYNTAX INTEGER
MAX-ACCESS read-write
STATUS current
DESCRIPTION
"Data value."
::= { dataArray12 115 }

dataValue12_116 OBJECT-TYPE
SYNTAX INTEGER
MAX-ACCESS read-write
STATUS current
DESCRIPTION
"Data value."
::= { dataArray12 116 }

dataValue12_117 OBJECT-TYPE
SYNTAX INTEGER
MAX-ACCESS read-write
STATUS current
DESCRIPTION
"Data value."
::= { dataArray12 117 }

dataValue12_118 OBJECT-TYPE
SYNTAX INTEGER
MAX-ACCESS read-write
STATUS current
DESCRIPTION
"Data value."
::= { dataArray12 118 }

dataValue12_119 OBJECT-TYPE
SYNTAX INTEGER
MAX-ACCESS read-write
STATUS current
DESCRIPTION
"Data value."
::= { dataArray12 119 }

dataValue12_120 OBJECT-TYPE
SYNTAX INTEGER
MAX-ACCESS read-write
STATUS current
DESCRIPTION
"Data value."
::= { dataArray12 120 }

dataValue12_121 OBJECT-TYPE
SYNTAX INTEGER
MAX-ACCESS read-write
STATUS current
DESCRIPTION
"Data value."
::= { dataArray12 121 }

dataValue12_122 OBJECT-TYPE
SYNTAX INTEGER
MAX-ACCESS read-write
STATUS current
DESCRIPTION
"Data value."
::= { dataArray12 122 }

dataValue12_123 OBJECT-TYPE
SYNTAX INTEGER
MAX-ACCESS read-write
STATUS current
DESCRIPTION
"Data value."
::= { dataArray12 123 }

dataValue12_124 OBJECT-TYPE
SYNTAX INTEGER
MAX-ACCESS read-write
STATUS current
DESCRIPTION
"Data value."
::= { dataArray12 124 }

dataValue12_125 OBJECT-TYPE
SYNTAX INTEGER
MAX-ACCESS read-write
STATUS current
DESCRIPTION
"Data value."
::= { dataArray12 125 }

dataValue12_126 OBJECT-TYPE
SYNTAX INTEGER
MAX-ACCESS read-write
STATUS current
DESCRIPTION
"Data value."
::= { dataArray12 126 }

dataValue12_127 OBJECT-TYPE
SYNTAX INTEGER
MAX-ACCESS read-write
STATUS current
DESCRIPTION
"Data value."
::= { dataArray12 127 }

dataValue12_128 OBJECT-TYPE
SYNTAX INTEGER
MAX-ACCESS read-write
STATUS current
DESCRIPTION
"Data value."
::= { dataArray12 128 }

dataValue12_129 OBJECT-TYPE
SYNTAX INTEGER
MAX-ACCESS read-write
STATUS current
DESCRIPTION
"Data value."
::= { dataArray12 129 }

dataValue12_130 OBJECT-TYPE
SYNTAX INTEGER
MAX-ACCESS read-write
STATUS current
DESCRIPTION
"Data value."
::= { dataArray12 130 }

dataValue12_131 OBJECT-TYPE
SYNTAX INTEGER
MAX-ACCESS read-write
STATUS current
DESCRIPTION
"Data value."
::= { dataArray12 131 }

dataValue12_132 OBJECT-TYPE
SYNTAX INTEGER
MAX-ACCESS read-write
STATUS current
DESCRIPTION
"Data value."
::= { dataArray12 132 }

dataValue12_133 OBJECT-TYPE
SYNTAX INTEGER
MAX-ACCESS read-write
STATUS current
DESCRIPTION
"Data value."
::= { dataArray12 133 }

dataValue12_134 OBJECT-TYPE
SYNTAX INTEGER
MAX-ACCESS read-write
STATUS current
DESCRIPTION
"Data value."
::= { dataArray12 134 }

dataValue12_135 OBJECT-TYPE
SYNTAX INTEGER
MAX-ACCESS read-write
STATUS current
DESCRIPTION
"Data value."
::= { dataArray12 135 }

dataValue12_136 OBJECT-TYPE
SYNTAX INTEGER
MAX-ACCESS read-write
STATUS current
DESCRIPTION
"Data value."
::= { dataArray12 136 }

dataValue12_137 OBJECT-TYPE
SYNTAX INTEGER
MAX-ACCESS read-write
STATUS current
DESCRIPTION
"Data value."
::= { dataArray12 137 }

dataValue12_138 OBJECT-TYPE
SYNTAX INTEGER
MAX-ACCESS read-write
STATUS current
DESCRIPTION
"Data value."
::= { dataArray12 138 }

dataValue12_139 OBJECT-TYPE
SYNTAX INTEGER
MAX-ACCESS read-write
STATUS current
DESCRIPTION
"Data value."
::= { dataArray12 139 }

dataValue12_140 OBJECT-TYPE
SYNTAX INTEGER
MAX-ACCESS read-write
STATUS current
DESCRIPTION
"Data value."
::= { dataArray12 140 }

dataValue12_141 OBJECT-TYPE
SYNTAX INTEGER
MAX-ACCESS read-write
STATUS current
DESCRIPTION
"Data value."
::= { dataArray12 141 }

dataValue12_142 OBJECT-TYPE
SYNTAX INTEGER
MAX-ACCESS read-write
STATUS current
DESCRIPTION
"Data value."
::= { dataArray12 142 }

dataValue12_143 OBJECT-TYPE
SYNTAX INTEGER
MAX-ACCESS read-write
STATUS current
DESCRIPTION
"Data value."
::= { dataArray12 143 }

dataValue12_144 OBJECT-TYPE
SYNTAX INTEGER
MAX-ACCESS read-write
STATUS current
DESCRIPTION
"Data value."
::= { dataArray12 144 }

dataValue12_145 OBJECT-TYPE
SYNTAX INTEGER
MAX-ACCESS read-write
STATUS current
DESCRIPTION
"Data value."
::= { dataArray12 145 }

dataValue12_146 OBJECT-TYPE
SYNTAX INTEGER
MAX-ACCESS read-write
STATUS current
DESCRIPTION
"Data value."
::= { dataArray12 146 }

dataValue12_147 OBJECT-TYPE
SYNTAX INTEGER
MAX-ACCESS read-write
STATUS current
DESCRIPTION
"Data value."
::= { dataArray12 147 }

dataValue12_148 OBJECT-TYPE
SYNTAX INTEGER
MAX-ACCESS read-write
STATUS current
DESCRIPTION
"Data value."
::= { dataArray12 148 }

dataValue12_149 OBJECT-TYPE
SYNTAX INTEGER
MAX-ACCESS read-write
STATUS current
DESCRIPTION
"Data value."
::= { dataArray12 149 }

dataValue12_150 OBJECT-TYPE
SYNTAX INTEGER
MAX-ACCESS read-write
STATUS current
DESCRIPTION
"Data value."
::= { dataArray12 150 }

dataValue12_151 OBJECT-TYPE
SYNTAX INTEGER
MAX-ACCESS read-write
STATUS current
DESCRIPTION
"Data value."
::= { dataArray12 151 }

dataValue12_152 OBJECT-TYPE
SYNTAX INTEGER
MAX-ACCESS read-write
STATUS current
DESCRIPTION
"Data value."
::= { dataArray12 152 }

dataValue12_153 OBJECT-TYPE
SYNTAX INTEGER
MAX-ACCESS read-write
STATUS current
DESCRIPTION
"Data value."
::= { dataArray12 153 }

dataValue12_154 OBJECT-TYPE
SYNTAX INTEGER
MAX-ACCESS read-write
STATUS current
DESCRIPTION
"Data value."
::= { dataArray12 154 }

dataValue12_155 OBJECT-TYPE
SYNTAX INTEGER
MAX-ACCESS read-write
STATUS current
DESCRIPTION
"Data value."
::= { dataArray12 155 }

dataValue12_156 OBJECT-TYPE
SYNTAX INTEGER
MAX-ACCESS read-write
STATUS current
DESCRIPTION
"Data value."
::= { dataArray12 156 }

dataValue12_157 OBJECT-TYPE
SYNTAX INTEGER
MAX-ACCESS read-write
STATUS current
DESCRIPTION
"Data value."
::= { dataArray12 157 }

dataValue12_158 OBJECT-TYPE
SYNTAX INTEGER
MAX-ACCESS read-write
STATUS current
DESCRIPTION
"Data value."
::= { dataArray12 158 }

dataValue12_159 OBJECT-TYPE
SYNTAX INTEGER
MAX-ACCESS read-write
STATUS current
DESCRIPTION
"Data value."
::= { dataArray12 159 }

dataValue12_160 OBJECT-TYPE
SYNTAX INTEGER
MAX-ACCESS read-write
STATUS current
DESCRIPTION
"Data value."
::= { dataArray12 160 }

dataValue12_161 OBJECT-TYPE
SYNTAX INTEGER
MAX-ACCESS read-write
STATUS current
DESCRIPTION
"Data value."
::= { dataArray12 161 }

dataValue12_162 OBJECT-TYPE
SYNTAX INTEGER
MAX-ACCESS read-write
STATUS current
DESCRIPTION
"Data value."
::= { dataArray12 162 }

dataValue12_163 OBJECT-TYPE
SYNTAX INTEGER
MAX-ACCESS read-write
STATUS current
DESCRIPTION
"Data value."
::= { dataArray12 163 }

dataValue12_164 OBJECT-TYPE
SYNTAX INTEGER
MAX-ACCESS read-write
STATUS current
DESCRIPTION
"Data value."
::= { dataArray12 164 }

dataValue12_165 OBJECT-TYPE
SYNTAX INTEGER
MAX-ACCESS read-write
STATUS current
DESCRIPTION
"Data value."
::= { dataArray12 165 }

dataValue12_166 OBJECT-TYPE
SYNTAX INTEGER
MAX-ACCESS read-write
STATUS current
DESCRIPTION
"Data value."
::= { dataArray12 166 }

dataValue12_167 OBJECT-TYPE
SYNTAX INTEGER
MAX-ACCESS read-write
STATUS current
DESCRIPTION
"Data value."
::= { dataArray12 167 }

dataValue12_168 OBJECT-TYPE
SYNTAX INTEGER
MAX-ACCESS read-write
STATUS current
DESCRIPTION
"Data value."
::= { dataArray12 168 }

dataValue12_169 OBJECT-TYPE
SYNTAX INTEGER
MAX-ACCESS read-write
STATUS current
DESCRIPTION
"Data value."
::= { dataArray12 169 }

dataValue12_170 OBJECT-TYPE
SYNTAX INTEGER
MAX-ACCESS read-write
STATUS current
DESCRIPTION
"Data value."
::= { dataArray12 170 }

dataValue12_171 OBJECT-TYPE
SYNTAX INTEGER
MAX-ACCESS read-write
STATUS current
DESCRIPTION
"Data value."
::= { dataArray12 171 }

dataValue12_172 OBJECT-TYPE
SYNTAX INTEGER
MAX-ACCESS read-write
STATUS current
DESCRIPTION
"Data value."
::= { dataArray12 172 }

dataValue12_173 OBJECT-TYPE
SYNTAX INTEGER
MAX-ACCESS read-write
STATUS current
DESCRIPTION
"Data value."
::= { dataArray12 173 }

dataValue12_174 OBJECT-TYPE
SYNTAX INTEGER
MAX-ACCESS read-write
STATUS current
DESCRIPTION
"Data value."
::= { dataArray12 174 }

dataValue12_175 OBJECT-TYPE
SYNTAX INTEGER
MAX-ACCESS read-write
STATUS current
DESCRIPTION
"Data value."
::= { dataArray12 175 }

dataValue12_176 OBJECT-TYPE
SYNTAX INTEGER
MAX-ACCESS read-write
STATUS current
DESCRIPTION
"Data value."
::= { dataArray12 176 }

dataValue12_177 OBJECT-TYPE
SYNTAX INTEGER
MAX-ACCESS read-write
STATUS current
DESCRIPTION
"Data value."
::= { dataArray12 177 }

dataValue12_178 OBJECT-TYPE
SYNTAX INTEGER
MAX-ACCESS read-write
STATUS current
DESCRIPTION
"Data value."
::= { dataArray12 178 }

dataValue12_179 OBJECT-TYPE
SYNTAX INTEGER
MAX-ACCESS read-write
STATUS current
DESCRIPTION
"Data value."
::= { dataArray12 179 }

dataValue12_180 OBJECT-TYPE
SYNTAX INTEGER
MAX-ACCESS read-write
STATUS current
DESCRIPTION
"Data value."
::= { dataArray12 180 }

dataValue12_181 OBJECT-TYPE
SYNTAX INTEGER
MAX-ACCESS read-write
STATUS current
DESCRIPTION
"Data value."
::= { dataArray12 181 }

dataValue12_182 OBJECT-TYPE
SYNTAX INTEGER
MAX-ACCESS read-write
STATUS current
DESCRIPTION
"Data value."
::= { dataArray12 182 }

dataValue12_183 OBJECT-TYPE
SYNTAX INTEGER
MAX-ACCESS read-write
STATUS current
DESCRIPTION
"Data value."
::= { dataArray12 183 }

dataValue12_184 OBJECT-TYPE
SYNTAX INTEGER
MAX-ACCESS read-write
STATUS current
DESCRIPTION
"Data value."
::= { dataArray12 184 }

dataValue12_185 OBJECT-TYPE
SYNTAX INTEGER
MAX-ACCESS read-write
STATUS current
DESCRIPTION
"Data value."
::= { dataArray12 185 }

dataValue12_186 OBJECT-TYPE
SYNTAX INTEGER
MAX-ACCESS read-write
STATUS current
DESCRIPTION
"Data value."
::= { dataArray12 186 }

dataValue12_187 OBJECT-TYPE
SYNTAX INTEGER
MAX-ACCESS read-write
STATUS current
DESCRIPTION
"Data value."
::= { dataArray12 187 }

dataValue12_188 OBJECT-TYPE
SYNTAX INTEGER
MAX-ACCESS read-write
STATUS current
DESCRIPTION
"Data value."
::= { dataArray12 188 }

dataValue12_189 OBJECT-TYPE
SYNTAX INTEGER
MAX-ACCESS read-write
STATUS current
DESCRIPTION
"Data value."
::= { dataArray12 189 }

dataValue12_190 OBJECT-TYPE
SYNTAX INTEGER
MAX-ACCESS read-write
STATUS current
DESCRIPTION
"Data value."
::= { dataArray12 190 }

dataValue12_191 OBJECT-TYPE
SYNTAX INTEGER
MAX-ACCESS read-write
STATUS current
DESCRIPTION
"Data value."
::= { dataArray12 191 }

dataValue12_192 OBJECT-TYPE
SYNTAX INTEGER
MAX-ACCESS read-write
STATUS current
DESCRIPTION
"Data value."
::= { dataArray12 192 }

dataValue12_193 OBJECT-TYPE
SYNTAX INTEGER
MAX-ACCESS read-write
STATUS current
DESCRIPTION
"Data value."
::= { dataArray12 193 }

dataValue12_194 OBJECT-TYPE
SYNTAX INTEGER
MAX-ACCESS read-write
STATUS current
DESCRIPTION
"Data value."
::= { dataArray12 194 }

dataValue12_195 OBJECT-TYPE
SYNTAX INTEGER
MAX-ACCESS read-write
STATUS current
DESCRIPTION
"Data value."
::= { dataArray12 195 }

dataValue12_196 OBJECT-TYPE
SYNTAX INTEGER
MAX-ACCESS read-write
STATUS current
DESCRIPTION
"Data value."
::= { dataArray12 196 }

dataValue12_197 OBJECT-TYPE
SYNTAX INTEGER
MAX-ACCESS read-write
STATUS current
DESCRIPTION
"Data value."
::= { dataArray12 197 }

dataValue12_198 OBJECT-TYPE
SYNTAX INTEGER
MAX-ACCESS read-write
STATUS current
DESCRIPTION
"Data value."
::= { dataArray12 198 }

dataValue12_199 OBJECT-TYPE
SYNTAX INTEGER
MAX-ACCESS read-write
STATUS current
DESCRIPTION
"Data value."
::= { dataArray12 199 }

dataValue12_200 OBJECT-TYPE
SYNTAX INTEGER
MAX-ACCESS read-write
STATUS current
DESCRIPTION
"Data value."
::= { dataArray12 200 }

dataValue12_201 OBJECT-TYPE
SYNTAX INTEGER
MAX-ACCESS read-write
STATUS current
DESCRIPTION
"Data value."
::= { dataArray12 201 }

dataValue12_202 OBJECT-TYPE
SYNTAX INTEGER
MAX-ACCESS read-write
STATUS current
DESCRIPTION
"Data value."
::= { dataArray12 202 }

dataValue12_203 OBJECT-TYPE
SYNTAX INTEGER
MAX-ACCESS read-write
STATUS current
DESCRIPTION
"Data value."
::= { dataArray12 203 }

dataValue12_204 OBJECT-TYPE
SYNTAX INTEGER
MAX-ACCESS read-write
STATUS current
DESCRIPTION
"Data value."
::= { dataArray12 204 }

dataValue12_205 OBJECT-TYPE
SYNTAX INTEGER
MAX-ACCESS read-write
STATUS current
DESCRIPTION
"Data value."
::= { dataArray12 205 }

dataValue12_206 OBJECT-TYPE
SYNTAX INTEGER
MAX-ACCESS read-write
STATUS current
DESCRIPTION
"Data value."
::= { dataArray12 206 }

dataValue12_207 OBJECT-TYPE
SYNTAX INTEGER
MAX-ACCESS read-write
STATUS current
DESCRIPTION
"Data value."
::= { dataArray12 207 }

dataValue12_208 OBJECT-TYPE
SYNTAX INTEGER
MAX-ACCESS read-write
STATUS current
DESCRIPTION
"Data value."
::= { dataArray12 208 }

dataValue12_209 OBJECT-TYPE
SYNTAX INTEGER
MAX-ACCESS read-write
STATUS current
DESCRIPTION
"Data value."
::= { dataArray12 209 }

dataValue12_210 OBJECT-TYPE
SYNTAX INTEGER
MAX-ACCESS read-write
STATUS current
DESCRIPTION
"Data value."
::= { dataArray12 210 }

dataValue12_211 OBJECT-TYPE
SYNTAX INTEGER
MAX-ACCESS read-write
STATUS current
DESCRIPTION
"Data value."
::= { dataArray12 211 }

dataValue12_212 OBJECT-TYPE
SYNTAX INTEGER
MAX-ACCESS read-write
STATUS current
DESCRIPTION
"Data value."
::= { dataArray12 212 }

dataValue12_213 OBJECT-TYPE
SYNTAX INTEGER
MAX-ACCESS read-write
STATUS current
DESCRIPTION
"Data value."
::= { dataArray12 213 }

dataValue12_214 OBJECT-TYPE
SYNTAX INTEGER
MAX-ACCESS read-write
STATUS current
DESCRIPTION
"Data value."
::= { dataArray12 214 }

dataValue12_215 OBJECT-TYPE
SYNTAX INTEGER
MAX-ACCESS read-write
STATUS current
DESCRIPTION
"Data value."
::= { dataArray12 215 }

dataValue12_216 OBJECT-TYPE
SYNTAX INTEGER
MAX-ACCESS read-write
STATUS current
DESCRIPTION
"Data value."
::= { dataArray12 216 }

dataValue12_217 OBJECT-TYPE
SYNTAX INTEGER
MAX-ACCESS read-write
STATUS current
DESCRIPTION
"Data value."
::= { dataArray12 217 }

dataValue12_218 OBJECT-TYPE
SYNTAX INTEGER
MAX-ACCESS read-write
STATUS current
DESCRIPTION
"Data value."
::= { dataArray12 218 }

dataValue12_219 OBJECT-TYPE
SYNTAX INTEGER
MAX-ACCESS read-write
STATUS current
DESCRIPTION
"Data value."
::= { dataArray12 219 }

dataValue12_220 OBJECT-TYPE
SYNTAX INTEGER
MAX-ACCESS read-write
STATUS current
DESCRIPTION
"Data value."
::= { dataArray12 220 }

dataValue12_221 OBJECT-TYPE
SYNTAX INTEGER
MAX-ACCESS read-write
STATUS current
DESCRIPTION
"Data value."
::= { dataArray12 221 }

dataValue12_222 OBJECT-TYPE
SYNTAX INTEGER
MAX-ACCESS read-write
STATUS current
DESCRIPTION
"Data value."
::= { dataArray12 222 }

dataValue12_223 OBJECT-TYPE
SYNTAX INTEGER
MAX-ACCESS read-write
STATUS current
DESCRIPTION
"Data value."
::= { dataArray12 223 }

dataValue12_224 OBJECT-TYPE
SYNTAX INTEGER
MAX-ACCESS read-write
STATUS current
DESCRIPTION
"Data value."
::= { dataArray12 224 }

dataValue12_225 OBJECT-TYPE
SYNTAX INTEGER
MAX-ACCESS read-write
STATUS current
DESCRIPTION
"Data value."
::= { dataArray12 225 }

dataValue12_226 OBJECT-TYPE
SYNTAX INTEGER
MAX-ACCESS read-write
STATUS current
DESCRIPTION
"Data value."
::= { dataArray12 226 }

dataValue12_227 OBJECT-TYPE
SYNTAX INTEGER
MAX-ACCESS read-write
STATUS current
DESCRIPTION
"Data value."
::= { dataArray12 227 }

dataValue12_228 OBJECT-TYPE
SYNTAX INTEGER
MAX-ACCESS read-write
STATUS current
DESCRIPTION
"Data value."
::= { dataArray12 228 }

dataValue12_229 OBJECT-TYPE
SYNTAX INTEGER
MAX-ACCESS read-write
STATUS current
DESCRIPTION
"Data value."
::= { dataArray12 229 }

dataValue12_230 OBJECT-TYPE
SYNTAX INTEGER
MAX-ACCESS read-write
STATUS current
DESCRIPTION
"Data value."
::= { dataArray12 230 }

dataValue12_231 OBJECT-TYPE
SYNTAX INTEGER
MAX-ACCESS read-write
STATUS current
DESCRIPTION
"Data value."
::= { dataArray12 231 }

dataValue12_232 OBJECT-TYPE
SYNTAX INTEGER
MAX-ACCESS read-write
STATUS current
DESCRIPTION
"Data value."
::= { dataArray12 232 }

dataValue12_233 OBJECT-TYPE
SYNTAX INTEGER
MAX-ACCESS read-write
STATUS current
DESCRIPTION
"Data value."
::= { dataArray12 233 }

dataValue12_234 OBJECT-TYPE
SYNTAX INTEGER
MAX-ACCESS read-write
STATUS current
DESCRIPTION
"Data value."
::= { dataArray12 234 }

dataValue12_235 OBJECT-TYPE
SYNTAX INTEGER
MAX-ACCESS read-write
STATUS current
DESCRIPTION
"Data value."
::= { dataArray12 235 }

dataValue12_236 OBJECT-TYPE
SYNTAX INTEGER
MAX-ACCESS read-write
STATUS current
DESCRIPTION
"Data value."
::= { dataArray12 236 }

dataValue12_237 OBJECT-TYPE
SYNTAX INTEGER
MAX-ACCESS read-write
STATUS current
DESCRIPTION
"Data value."
::= { dataArray12 237 }

dataValue12_238 OBJECT-TYPE
SYNTAX INTEGER
MAX-ACCESS read-write
STATUS current
DESCRIPTION
"Data value."
::= { dataArray12 238 }

dataValue12_239 OBJECT-TYPE
SYNTAX INTEGER
MAX-ACCESS read-write
STATUS current
DESCRIPTION
"Data value."
::= { dataArray12 239 }

dataValue12_240 OBJECT-TYPE
SYNTAX INTEGER
MAX-ACCESS read-write
STATUS current
DESCRIPTION
"Data value."
::= { dataArray12 240 }

dataValue12_241 OBJECT-TYPE
SYNTAX INTEGER
MAX-ACCESS read-write
STATUS current
DESCRIPTION
"Data value."
::= { dataArray12 241 }

dataValue12_242 OBJECT-TYPE
SYNTAX INTEGER
MAX-ACCESS read-write
STATUS current
DESCRIPTION
"Data value."
::= { dataArray12 242 }

dataValue12_243 OBJECT-TYPE
SYNTAX INTEGER
MAX-ACCESS read-write
STATUS current
DESCRIPTION
"Data value."
::= { dataArray12 243 }

dataValue12_244 OBJECT-TYPE
SYNTAX INTEGER
MAX-ACCESS read-write
STATUS current
DESCRIPTION
"Data value."
::= { dataArray12 244 }

dataValue12_245 OBJECT-TYPE
SYNTAX INTEGER
MAX-ACCESS read-write
STATUS current
DESCRIPTION
"Data value."
::= { dataArray12 245 }

dataValue12_246 OBJECT-TYPE
SYNTAX INTEGER
MAX-ACCESS read-write
STATUS current
DESCRIPTION
"Data value."
::= { dataArray12 246 }

dataValue12_247 OBJECT-TYPE
SYNTAX INTEGER
MAX-ACCESS read-write
STATUS current
DESCRIPTION
"Data value."
::= { dataArray12 247 }

dataValue12_248 OBJECT-TYPE
SYNTAX INTEGER
MAX-ACCESS read-write
STATUS current
DESCRIPTION
"Data value."
::= { dataArray12 248 }

dataValue12_249 OBJECT-TYPE
SYNTAX INTEGER
MAX-ACCESS read-write
STATUS current
DESCRIPTION
"Data value."
::= { dataArray12 249 }

dataValue12_250 OBJECT-TYPE
SYNTAX INTEGER
MAX-ACCESS read-write
STATUS current
DESCRIPTION
"Data value."
::= { dataArray12 250 }

dataValue12_251 OBJECT-TYPE
SYNTAX INTEGER
MAX-ACCESS read-write
STATUS current
DESCRIPTION
"Data value."
::= { dataArray12 251 }

dataValue12_252 OBJECT-TYPE
SYNTAX INTEGER
MAX-ACCESS read-write
STATUS current
DESCRIPTION
"Data value."
::= { dataArray12 252 }

dataValue12_253 OBJECT-TYPE
SYNTAX INTEGER
MAX-ACCESS read-write
STATUS current
DESCRIPTION
"Data value."
::= { dataArray12 253 }

dataValue12_254 OBJECT-TYPE
SYNTAX INTEGER
MAX-ACCESS read-write
STATUS current
DESCRIPTION
"Data value."
::= { dataArray12 254 }

dataValue12_255 OBJECT-TYPE
SYNTAX INTEGER
MAX-ACCESS read-write
STATUS current
DESCRIPTION
"Data value."
::= { dataArray12 255 }

dataValue12_256 OBJECT-TYPE
SYNTAX INTEGER
MAX-ACCESS read-write
STATUS current
DESCRIPTION
"Data value."
::= { dataArray12 256 }

dataValue12_257 OBJECT-TYPE
SYNTAX INTEGER
MAX-ACCESS read-write
STATUS current
DESCRIPTION
"Data value."
::= { dataArray12 257 }

dataValue12_258 OBJECT-TYPE
SYNTAX INTEGER
MAX-ACCESS read-write
STATUS current
DESCRIPTION
"Data value."
::= { dataArray12 258 }

dataValue12_259 OBJECT-TYPE
SYNTAX INTEGER
MAX-ACCESS read-write
STATUS current
DESCRIPTION
"Data value."
::= { dataArray12 259 }

dataValue12_260 OBJECT-TYPE
SYNTAX INTEGER
MAX-ACCESS read-write
STATUS current
DESCRIPTION
"Data value."
::= { dataArray12 260 }

dataValue12_261 OBJECT-TYPE
SYNTAX INTEGER
MAX-ACCESS read-write
STATUS current
DESCRIPTION
"Data value."
::= { dataArray12 261 }

dataValue12_262 OBJECT-TYPE
SYNTAX INTEGER
MAX-ACCESS read-write
STATUS current
DESCRIPTION
"Data value."
::= { dataArray12 262 }

dataValue12_263 OBJECT-TYPE
SYNTAX INTEGER
MAX-ACCESS read-write
STATUS current
DESCRIPTION
"Data value."
::= { dataArray12 263 }

dataValue12_264 OBJECT-TYPE
SYNTAX INTEGER
MAX-ACCESS read-write
STATUS current
DESCRIPTION
"Data value."
::= { dataArray12 264 }

dataValue12_265 OBJECT-TYPE
SYNTAX INTEGER
MAX-ACCESS read-write
STATUS current
DESCRIPTION
"Data value."
::= { dataArray12 265 }

dataValue12_266 OBJECT-TYPE
SYNTAX INTEGER
MAX-ACCESS read-write
STATUS current
DESCRIPTION
"Data value."
::= { dataArray12 266 }

dataValue12_267 OBJECT-TYPE
SYNTAX INTEGER
MAX-ACCESS read-write
STATUS current
DESCRIPTION
"Data value."
::= { dataArray12 267 }

dataValue12_268 OBJECT-TYPE
SYNTAX INTEGER
MAX-ACCESS read-write
STATUS current
DESCRIPTION
"Data value."
::= { dataArray12 268 }

dataValue12_269 OBJECT-TYPE
SYNTAX INTEGER
MAX-ACCESS read-write
STATUS current
DESCRIPTION
"Data value."
::= { dataArray12 269 }

dataValue12_270 OBJECT-TYPE
SYNTAX INTEGER
MAX-ACCESS read-write
STATUS current
DESCRIPTION
"Data value."
::= { dataArray12 270 }

dataValue12_271 OBJECT-TYPE
SYNTAX INTEGER
MAX-ACCESS read-write
STATUS current
DESCRIPTION
"Data value."
::= { dataArray12 271 }

dataValue12_272 OBJECT-TYPE
SYNTAX INTEGER
MAX-ACCESS read-write
STATUS current
DESCRIPTION
"Data value."
::= { dataArray12 272 }

dataValue12_273 OBJECT-TYPE
SYNTAX INTEGER
MAX-ACCESS read-write
STATUS current
DESCRIPTION
"Data value."
::= { dataArray12 273 }

dataValue12_274 OBJECT-TYPE
SYNTAX INTEGER
MAX-ACCESS read-write
STATUS current
DESCRIPTION
"Data value."
::= { dataArray12 274 }

dataValue12_275 OBJECT-TYPE
SYNTAX INTEGER
MAX-ACCESS read-write
STATUS current
DESCRIPTION
"Data value."
::= { dataArray12 275 }

dataValue12_276 OBJECT-TYPE
SYNTAX INTEGER
MAX-ACCESS read-write
STATUS current
DESCRIPTION
"Data value."
::= { dataArray12 276 }

dataValue12_277 OBJECT-TYPE
SYNTAX INTEGER
MAX-ACCESS read-write
STATUS current
DESCRIPTION
"Data value."
::= { dataArray12 277 }

dataValue12_278 OBJECT-TYPE
SYNTAX INTEGER
MAX-ACCESS read-write
STATUS current
DESCRIPTION
"Data value."
::= { dataArray12 278 }

dataValue12_279 OBJECT-TYPE
SYNTAX INTEGER
MAX-ACCESS read-write
STATUS current
DESCRIPTION
"Data value."
::= { dataArray12 279 }

dataValue12_280 OBJECT-TYPE
SYNTAX INTEGER
MAX-ACCESS read-write
STATUS current
DESCRIPTION
"Data value."
::= { dataArray12 280 }

dataValue12_281 OBJECT-TYPE
SYNTAX INTEGER
MAX-ACCESS read-write
STATUS current
DESCRIPTION
"Data value."
::= { dataArray12 281 }

dataValue12_282 OBJECT-TYPE
SYNTAX INTEGER
MAX-ACCESS read-write
STATUS current
DESCRIPTION
"Data value."
::= { dataArray12 282 }

dataValue12_283 OBJECT-TYPE
SYNTAX INTEGER
MAX-ACCESS read-write
STATUS current
DESCRIPTION
"Data value."
::= { dataArray12 283 }

dataValue12_284 OBJECT-TYPE
SYNTAX INTEGER
MAX-ACCESS read-write
STATUS current
DESCRIPTION
"Data value."
::= { dataArray12 284 }

dataValue12_285 OBJECT-TYPE
SYNTAX INTEGER
MAX-ACCESS read-write
STATUS current
DESCRIPTION
"Data value."
::= { dataArray12 285 }

dataValue12_286 OBJECT-TYPE
SYNTAX INTEGER
MAX-ACCESS read-write
STATUS current
DESCRIPTION
"Data value."
::= { dataArray12 286 }

dataValue12_287 OBJECT-TYPE
SYNTAX INTEGER
MAX-ACCESS read-write
STATUS current
DESCRIPTION
"Data value."
::= { dataArray12 287 }

dataValue12_288 OBJECT-TYPE
SYNTAX INTEGER
MAX-ACCESS read-write
STATUS current
DESCRIPTION
"Data value."
::= { dataArray12 288 }

dataValue12_289 OBJECT-TYPE
SYNTAX INTEGER
MAX-ACCESS read-write
STATUS current
DESCRIPTION
"Data value."
::= { dataArray12 289 }

dataValue12_290 OBJECT-TYPE
SYNTAX INTEGER
MAX-ACCESS read-write
STATUS current
DESCRIPTION
"Data value."
::= { dataArray12 290 }

dataValue12_291 OBJECT-TYPE
SYNTAX INTEGER
MAX-ACCESS read-write
STATUS current
DESCRIPTION
"Data value."
::= { dataArray12 291 }

dataValue12_292 OBJECT-TYPE
SYNTAX INTEGER
MAX-ACCESS read-write
STATUS current
DESCRIPTION
"Data value."
::= { dataArray12 292 }

dataValue12_293 OBJECT-TYPE
SYNTAX INTEGER
MAX-ACCESS read-write
STATUS current
DESCRIPTION
"Data value."
::= { dataArray12 293 }

dataValue12_294 OBJECT-TYPE
SYNTAX INTEGER
MAX-ACCESS read-write
STATUS current
DESCRIPTION
"Data value."
::= { dataArray12 294 }

dataValue12_295 OBJECT-TYPE
SYNTAX INTEGER
MAX-ACCESS read-write
STATUS current
DESCRIPTION
"Data value."
::= { dataArray12 295 }

dataValue12_296 OBJECT-TYPE
SYNTAX INTEGER
MAX-ACCESS read-write
STATUS current
DESCRIPTION
"Data value."
::= { dataArray12 296 }

dataValue12_297 OBJECT-TYPE
SYNTAX INTEGER
MAX-ACCESS read-write
STATUS current
DESCRIPTION
"Data value."
::= { dataArray12 297 }

dataValue12_298 OBJECT-TYPE
SYNTAX INTEGER
MAX-ACCESS read-write
STATUS current
DESCRIPTION
"Data value."
::= { dataArray12 298 }

dataValue12_299 OBJECT-TYPE
SYNTAX INTEGER
MAX-ACCESS read-write
STATUS current
DESCRIPTION
"Data value."
::= { dataArray12 299 }

dataValue12_300 OBJECT-TYPE
SYNTAX INTEGER
MAX-ACCESS read-write
STATUS current
DESCRIPTION
"Data value."
::= { dataArray12 300 }

dataValue12_301 OBJECT-TYPE
SYNTAX INTEGER
MAX-ACCESS read-write
STATUS current
DESCRIPTION
"Data value."
::= { dataArray12 301 }

dataValue12_302 OBJECT-TYPE
SYNTAX INTEGER
MAX-ACCESS read-write
STATUS current
DESCRIPTION
"Data value."
::= { dataArray12 302 }

dataValue12_303 OBJECT-TYPE
SYNTAX INTEGER
MAX-ACCESS read-write
STATUS current
DESCRIPTION
"Data value."
::= { dataArray12 303 }

dataValue12_304 OBJECT-TYPE
SYNTAX INTEGER
MAX-ACCESS read-write
STATUS current
DESCRIPTION
"Data value."
::= { dataArray12 304 }

dataValue12_305 OBJECT-TYPE
SYNTAX INTEGER
MAX-ACCESS read-write
STATUS current
DESCRIPTION
"Data value."
::= { dataArray12 305 }

dataValue12_306 OBJECT-TYPE
SYNTAX INTEGER
MAX-ACCESS read-write
STATUS current
DESCRIPTION
"Data value."
::= { dataArray12 306 }

dataValue12_307 OBJECT-TYPE
SYNTAX INTEGER
MAX-ACCESS read-write
STATUS current
DESCRIPTION
"Data value."
::= { dataArray12 307 }

dataValue12_308 OBJECT-TYPE
SYNTAX INTEGER
MAX-ACCESS read-write
STATUS current
DESCRIPTION
"Data value."
::= { dataArray12 308 }

dataValue12_309 OBJECT-TYPE
SYNTAX INTEGER
MAX-ACCESS read-write
STATUS current
DESCRIPTION
"Data value."
::= { dataArray12 309 }

dataValue12_310 OBJECT-TYPE
SYNTAX INTEGER
MAX-ACCESS read-write
STATUS current
DESCRIPTION
"Data value."
::= { dataArray12 310 }

dataValue12_311 OBJECT-TYPE
SYNTAX INTEGER
MAX-ACCESS read-write
STATUS current
DESCRIPTION
"Data value."
::= { dataArray12 311 }

dataValue12_312 OBJECT-TYPE
SYNTAX INTEGER
MAX-ACCESS read-write
STATUS current
DESCRIPTION
"Data value."
::= { dataArray12 312 }

dataValue12_313 OBJECT-TYPE
SYNTAX INTEGER
MAX-ACCESS read-write
STATUS current
DESCRIPTION
"Data value."
::= { dataArray12 313 }

dataValue12_314 OBJECT-TYPE
SYNTAX INTEGER
MAX-ACCESS read-write
STATUS current
DESCRIPTION
"Data value."
::= { dataArray12 314 }

dataValue12_315 OBJECT-TYPE
SYNTAX INTEGER
MAX-ACCESS read-write
STATUS current
DESCRIPTION
"Data value."
::= { dataArray12 315 }

dataValue12_316 OBJECT-TYPE
SYNTAX INTEGER
MAX-ACCESS read-write
STATUS current
DESCRIPTION
"Data value."
::= { dataArray12 316 }

dataValue12_317 OBJECT-TYPE
SYNTAX INTEGER
MAX-ACCESS read-write
STATUS current
DESCRIPTION
"Data value."
::= { dataArray12 317 }

dataValue12_318 OBJECT-TYPE
SYNTAX INTEGER
MAX-ACCESS read-write
STATUS current
DESCRIPTION
"Data value."
::= { dataArray12 318 }

dataValue12_319 OBJECT-TYPE
SYNTAX INTEGER
MAX-ACCESS read-write
STATUS current
DESCRIPTION
"Data value."
::= { dataArray12 319 }

dataValue12_320 OBJECT-TYPE
SYNTAX INTEGER
MAX-ACCESS read-write
STATUS current
DESCRIPTION
"Data value."
::= { dataArray12 320 }

dataValue12_321 OBJECT-TYPE
SYNTAX INTEGER
MAX-ACCESS read-write
STATUS current
DESCRIPTION
"Data value."
::= { dataArray12 321 }

dataValue12_322 OBJECT-TYPE
SYNTAX INTEGER
MAX-ACCESS read-write
STATUS current
DESCRIPTION
"Data value."
::= { dataArray12 322 }

dataValue12_323 OBJECT-TYPE
SYNTAX INTEGER
MAX-ACCESS read-write
STATUS current
DESCRIPTION
"Data value."
::= { dataArray12 323 }

dataValue12_324 OBJECT-TYPE
SYNTAX INTEGER
MAX-ACCESS read-write
STATUS current
DESCRIPTION
"Data value."
::= { dataArray12 324 }

dataValue12_325 OBJECT-TYPE
SYNTAX INTEGER
MAX-ACCESS read-write
STATUS current
DESCRIPTION
"Data value."
::= { dataArray12 325 }

dataValue12_326 OBJECT-TYPE
SYNTAX INTEGER
MAX-ACCESS read-write
STATUS current
DESCRIPTION
"Data value."
::= { dataArray12 326 }

dataValue12_327 OBJECT-TYPE
SYNTAX INTEGER
MAX-ACCESS read-write
STATUS current
DESCRIPTION
"Data value."
::= { dataArray12 327 }

dataValue12_328 OBJECT-TYPE
SYNTAX INTEGER
MAX-ACCESS read-write
STATUS current
DESCRIPTION
"Data value."
::= { dataArray12 328 }

dataValue12_329 OBJECT-TYPE
SYNTAX INTEGER
MAX-ACCESS read-write
STATUS current
DESCRIPTION
"Data value."
::= { dataArray12 329 }

dataValue12_330 OBJECT-TYPE
SYNTAX INTEGER
MAX-ACCESS read-write
STATUS current
DESCRIPTION
"Data value."
::= { dataArray12 330 }

dataValue12_331 OBJECT-TYPE
SYNTAX INTEGER
MAX-ACCESS read-write
STATUS current
DESCRIPTION
"Data value."
::= { dataArray12 331 }

dataValue12_332 OBJECT-TYPE
SYNTAX INTEGER
MAX-ACCESS read-write
STATUS current
DESCRIPTION
"Data value."
::= { dataArray12 332 }

dataValue12_333 OBJECT-TYPE
SYNTAX INTEGER
MAX-ACCESS read-write
STATUS current
DESCRIPTION
"Data value."
::= { dataArray12 333 }

dataValue12_334 OBJECT-TYPE
SYNTAX INTEGER
MAX-ACCESS read-write
STATUS current
DESCRIPTION
"Data value."
::= { dataArray12 334 }

dataValue12_335 OBJECT-TYPE
SYNTAX INTEGER
MAX-ACCESS read-write
STATUS current
DESCRIPTION
"Data value."
::= { dataArray12 335 }

dataValue12_336 OBJECT-TYPE
SYNTAX INTEGER
MAX-ACCESS read-write
STATUS current
DESCRIPTION
"Data value."
::= { dataArray12 336 }

dataValue12_337 OBJECT-TYPE
SYNTAX INTEGER
MAX-ACCESS read-write
STATUS current
DESCRIPTION
"Data value."
::= { dataArray12 337 }

dataValue12_338 OBJECT-TYPE
SYNTAX INTEGER
MAX-ACCESS read-write
STATUS current
DESCRIPTION
"Data value."
::= { dataArray12 338 }

dataValue12_339 OBJECT-TYPE
SYNTAX INTEGER
MAX-ACCESS read-write
STATUS current
DESCRIPTION
"Data value."
::= { dataArray12 339 }

dataValue12_340 OBJECT-TYPE
SYNTAX INTEGER
MAX-ACCESS read-write
STATUS current
DESCRIPTION
"Data value."
::= { dataArray12 340 }

dataValue12_341 OBJECT-TYPE
SYNTAX INTEGER
MAX-ACCESS read-write
STATUS current
DESCRIPTION
"Data value."
::= { dataArray12 341 }

dataValue12_342 OBJECT-TYPE
SYNTAX INTEGER
MAX-ACCESS read-write
STATUS current
DESCRIPTION
"Data value."
::= { dataArray12 342 }

dataValue12_343 OBJECT-TYPE
SYNTAX INTEGER
MAX-ACCESS read-write
STATUS current
DESCRIPTION
"Data value."
::= { dataArray12 343 }

dataValue12_344 OBJECT-TYPE
SYNTAX INTEGER
MAX-ACCESS read-write
STATUS current
DESCRIPTION
"Data value."
::= { dataArray12 344 }

dataValue12_345 OBJECT-TYPE
SYNTAX INTEGER
MAX-ACCESS read-write
STATUS current
DESCRIPTION
"Data value."
::= { dataArray12 345 }

dataValue12_346 OBJECT-TYPE
SYNTAX INTEGER
MAX-ACCESS read-write
STATUS current
DESCRIPTION
"Data value."
::= { dataArray12 346 }

dataValue12_347 OBJECT-TYPE
SYNTAX INTEGER
MAX-ACCESS read-write
STATUS current
DESCRIPTION
"Data value."
::= { dataArray12 347 }

dataValue12_348 OBJECT-TYPE
SYNTAX INTEGER
MAX-ACCESS read-write
STATUS current
DESCRIPTION
"Data value."
::= { dataArray12 348 }

dataValue12_349 OBJECT-TYPE
SYNTAX INTEGER
MAX-ACCESS read-write
STATUS current
DESCRIPTION
"Data value."
::= { dataArray12 349 }

dataValue12_350 OBJECT-TYPE
SYNTAX INTEGER
MAX-ACCESS read-write
STATUS current
DESCRIPTION
"Data value."
::= { dataArray12 350 }

dataValue12_351 OBJECT-TYPE
SYNTAX INTEGER
MAX-ACCESS read-write
STATUS current
DESCRIPTION
"Data value."
::= { dataArray12 351 }

dataValue12_352 OBJECT-TYPE
SYNTAX INTEGER
MAX-ACCESS read-write
STATUS current
DESCRIPTION
"Data value."
::= { dataArray12 352 }

dataValue12_353 OBJECT-TYPE
SYNTAX INTEGER
MAX-ACCESS read-write
STATUS current
DESCRIPTION
"Data value."
::= { dataArray12 353 }

dataValue12_354 OBJECT-TYPE
SYNTAX INTEGER
MAX-ACCESS read-write
STATUS current
DESCRIPTION
"Data value."
::= { dataArray12 354 }

dataValue12_355 OBJECT-TYPE
SYNTAX INTEGER
MAX-ACCESS read-write
STATUS current
DESCRIPTION
"Data value."
::= { dataArray12 355 }

dataValue12_356 OBJECT-TYPE
SYNTAX INTEGER
MAX-ACCESS read-write
STATUS current
DESCRIPTION
"Data value."
::= { dataArray12 356 }

dataValue12_357 OBJECT-TYPE
SYNTAX INTEGER
MAX-ACCESS read-write
STATUS current
DESCRIPTION
"Data value."
::= { dataArray12 357 }

dataValue12_358 OBJECT-TYPE
SYNTAX INTEGER
MAX-ACCESS read-write
STATUS current
DESCRIPTION
"Data value."
::= { dataArray12 358 }

dataValue12_359 OBJECT-TYPE
SYNTAX INTEGER
MAX-ACCESS read-write
STATUS current
DESCRIPTION
"Data value."
::= { dataArray12 359 }

dataValue12_360 OBJECT-TYPE
SYNTAX INTEGER
MAX-ACCESS read-write
STATUS current
DESCRIPTION
"Data value."
::= { dataArray12 360 }

dataValue12_361 OBJECT-TYPE
SYNTAX INTEGER
MAX-ACCESS read-write
STATUS current
DESCRIPTION
"Data value."
::= { dataArray12 361 }

dataValue12_362 OBJECT-TYPE
SYNTAX INTEGER
MAX-ACCESS read-write
STATUS current
DESCRIPTION
"Data value."
::= { dataArray12 362 }

dataValue12_363 OBJECT-TYPE
SYNTAX INTEGER
MAX-ACCESS read-write
STATUS current
DESCRIPTION
"Data value."
::= { dataArray12 363 }

dataValue12_364 OBJECT-TYPE
SYNTAX INTEGER
MAX-ACCESS read-write
STATUS current
DESCRIPTION
"Data value."
::= { dataArray12 364 }

dataValue12_365 OBJECT-TYPE
SYNTAX INTEGER
MAX-ACCESS read-write
STATUS current
DESCRIPTION
"Data value."
::= { dataArray12 365 }

dataValue12_366 OBJECT-TYPE
SYNTAX INTEGER
MAX-ACCESS read-write
STATUS current
DESCRIPTION
"Data value."
::= { dataArray12 366 }

dataValue12_367 OBJECT-TYPE
SYNTAX INTEGER
MAX-ACCESS read-write
STATUS current
DESCRIPTION
"Data value."
::= { dataArray12 367 }

dataValue12_368 OBJECT-TYPE
SYNTAX INTEGER
MAX-ACCESS read-write
STATUS current
DESCRIPTION
"Data value."
::= { dataArray12 368 }

dataValue12_369 OBJECT-TYPE
SYNTAX INTEGER
MAX-ACCESS read-write
STATUS current
DESCRIPTION
"Data value."
::= { dataArray12 369 }

dataValue12_370 OBJECT-TYPE
SYNTAX INTEGER
MAX-ACCESS read-write
STATUS current
DESCRIPTION
"Data value."
::= { dataArray12 370 }

dataValue12_371 OBJECT-TYPE
SYNTAX INTEGER
MAX-ACCESS read-write
STATUS current
DESCRIPTION
"Data value."
::= { dataArray12 371 }

dataValue12_372 OBJECT-TYPE
SYNTAX INTEGER
MAX-ACCESS read-write
STATUS current
DESCRIPTION
"Data value."
::= { dataArray12 372 }

dataValue12_373 OBJECT-TYPE
SYNTAX INTEGER
MAX-ACCESS read-write
STATUS current
DESCRIPTION
"Data value."
::= { dataArray12 373 }

dataValue12_374 OBJECT-TYPE
SYNTAX INTEGER
MAX-ACCESS read-write
STATUS current
DESCRIPTION
"Data value."
::= { dataArray12 374 }

dataValue12_375 OBJECT-TYPE
SYNTAX INTEGER
MAX-ACCESS read-write
STATUS current
DESCRIPTION
"Data value."
::= { dataArray12 375 }

dataValue12_376 OBJECT-TYPE
SYNTAX INTEGER
MAX-ACCESS read-write
STATUS current
DESCRIPTION
"Data value."
::= { dataArray12 376 }

dataValue12_377 OBJECT-TYPE
SYNTAX INTEGER
MAX-ACCESS read-write
STATUS current
DESCRIPTION
"Data value."
::= { dataArray12 377 }

dataValue12_378 OBJECT-TYPE
SYNTAX INTEGER
MAX-ACCESS read-write
STATUS current
DESCRIPTION
"Data value."
::= { dataArray12 378 }

dataValue12_379 OBJECT-TYPE
SYNTAX INTEGER
MAX-ACCESS read-write
STATUS current
DESCRIPTION
"Data value."
::= { dataArray12 379 }

dataValue12_380 OBJECT-TYPE
SYNTAX INTEGER
MAX-ACCESS read-write
STATUS current
DESCRIPTION
"Data value."
::= { dataArray12 380 }

dataValue12_381 OBJECT-TYPE
SYNTAX INTEGER
MAX-ACCESS read-write
STATUS current
DESCRIPTION
"Data value."
::= { dataArray12 381 }

dataValue12_382 OBJECT-TYPE
SYNTAX INTEGER
MAX-ACCESS read-write
STATUS current
DESCRIPTION
"Data value."
::= { dataArray12 382 }

dataValue12_383 OBJECT-TYPE
SYNTAX INTEGER
MAX-ACCESS read-write
STATUS current
DESCRIPTION
"Data value."
::= { dataArray12 383 }

dataValue12_384 OBJECT-TYPE
SYNTAX INTEGER
MAX-ACCESS read-write
STATUS current
DESCRIPTION
"Data value."
::= { dataArray12 384 }

dataValue12_385 OBJECT-TYPE
SYNTAX INTEGER
MAX-ACCESS read-write
STATUS current
DESCRIPTION
"Data value."
::= { dataArray12 385 }

dataValue12_386 OBJECT-TYPE
SYNTAX INTEGER
MAX-ACCESS read-write
STATUS current
DESCRIPTION
"Data value."
::= { dataArray12 386 }

dataValue12_387 OBJECT-TYPE
SYNTAX INTEGER
MAX-ACCESS read-write
STATUS current
DESCRIPTION
"Data value."
::= { dataArray12 387 }

dataValue12_388 OBJECT-TYPE
SYNTAX INTEGER
MAX-ACCESS read-write
STATUS current
DESCRIPTION
"Data value."
::= { dataArray12 388 }

dataValue12_389 OBJECT-TYPE
SYNTAX INTEGER
MAX-ACCESS read-write
STATUS current
DESCRIPTION
"Data value."
::= { dataArray12 389 }

dataValue12_390 OBJECT-TYPE
SYNTAX INTEGER
MAX-ACCESS read-write
STATUS current
DESCRIPTION
"Data value."
::= { dataArray12 390 }

dataValue12_391 OBJECT-TYPE
SYNTAX INTEGER
MAX-ACCESS read-write
STATUS current
DESCRIPTION
"Data value."
::= { dataArray12 391 }

dataValue12_392 OBJECT-TYPE
SYNTAX INTEGER
MAX-ACCESS read-write
STATUS current
DESCRIPTION
"Data value."
::= { dataArray12 392 }

dataValue12_393 OBJECT-TYPE
SYNTAX INTEGER
MAX-ACCESS read-write
STATUS current
DESCRIPTION
"Data value."
::= { dataArray12 393 }

dataValue12_394 OBJECT-TYPE
SYNTAX INTEGER
MAX-ACCESS read-write
STATUS current
DESCRIPTION
"Data value."
::= { dataArray12 394 }

dataValue12_395 OBJECT-TYPE
SYNTAX INTEGER
MAX-ACCESS read-write
STATUS current
DESCRIPTION
"Data value."
::= { dataArray12 395 }

dataValue12_396 OBJECT-TYPE
SYNTAX INTEGER
MAX-ACCESS read-write
STATUS current
DESCRIPTION
"Data value."
::= { dataArray12 396 }

dataValue12_397 OBJECT-TYPE
SYNTAX INTEGER
MAX-ACCESS read-write
STATUS current
DESCRIPTION
"Data value."
::= { dataArray12 397 }

dataValue12_398 OBJECT-TYPE
SYNTAX INTEGER
MAX-ACCESS read-write
STATUS current
DESCRIPTION
"Data value."
::= { dataArray12 398 }

dataValue12_399 OBJECT-TYPE
SYNTAX INTEGER
MAX-ACCESS read-write
STATUS current
DESCRIPTION
"Data value."
::= { dataArray12 399 }

dataArray13 OBJECT IDENTIFIER ::= { cc08255400_v1_00a 13 }

dataValue13_0 OBJECT-TYPE
SYNTAX INTEGER
MAX-ACCESS read-write
STATUS current
DESCRIPTION
"Data value."
::= { dataArray13 0 }

dataValue13_1 OBJECT-TYPE
SYNTAX INTEGER
MAX-ACCESS read-write
STATUS current
DESCRIPTION
"Data value."
::= { dataArray13 1 }

dataValue13_2 OBJECT-TYPE
SYNTAX INTEGER
MAX-ACCESS read-write
STATUS current
DESCRIPTION
"Data value."
::= { dataArray13 2 }

dataValue13_3 OBJECT-TYPE
SYNTAX INTEGER
MAX-ACCESS read-write
STATUS current
DESCRIPTION
"Data value."
::= { dataArray13 3 }

dataValue13_4 OBJECT-TYPE
SYNTAX INTEGER
MAX-ACCESS read-write
STATUS current
DESCRIPTION
"Data value."
::= { dataArray13 4 }

dataValue13_5 OBJECT-TYPE
SYNTAX INTEGER
MAX-ACCESS read-write
STATUS current
DESCRIPTION
"Data value."
::= { dataArray13 5 }

dataValue13_6 OBJECT-TYPE
SYNTAX INTEGER
MAX-ACCESS read-write
STATUS current
DESCRIPTION
"Data value."
::= { dataArray13 6 }

dataValue13_7 OBJECT-TYPE
SYNTAX INTEGER
MAX-ACCESS read-write
STATUS current
DESCRIPTION
"Data value."
::= { dataArray13 7 }

dataValue13_8 OBJECT-TYPE
SYNTAX INTEGER
MAX-ACCESS read-write
STATUS current
DESCRIPTION
"Data value."
::= { dataArray13 8 }

dataValue13_9 OBJECT-TYPE
SYNTAX INTEGER
MAX-ACCESS read-write
STATUS current
DESCRIPTION
"Data value."
::= { dataArray13 9 }

dataValue13_10 OBJECT-TYPE
SYNTAX INTEGER
MAX-ACCESS read-write
STATUS current
DESCRIPTION
"Data value."
::= { dataArray13 10 }

dataValue13_11 OBJECT-TYPE
SYNTAX INTEGER
MAX-ACCESS read-write
STATUS current
DESCRIPTION
"Data value."
::= { dataArray13 11 }

dataValue13_12 OBJECT-TYPE
SYNTAX INTEGER
MAX-ACCESS read-write
STATUS current
DESCRIPTION
"Data value."
::= { dataArray13 12 }

dataValue13_13 OBJECT-TYPE
SYNTAX INTEGER
MAX-ACCESS read-write
STATUS current
DESCRIPTION
"Data value."
::= { dataArray13 13 }

dataValue13_14 OBJECT-TYPE
SYNTAX INTEGER
MAX-ACCESS read-write
STATUS current
DESCRIPTION
"Data value."
::= { dataArray13 14 }

dataValue13_15 OBJECT-TYPE
SYNTAX INTEGER
MAX-ACCESS read-write
STATUS current
DESCRIPTION
"Data value."
::= { dataArray13 15 }

dataValue13_16 OBJECT-TYPE
SYNTAX INTEGER
MAX-ACCESS read-write
STATUS current
DESCRIPTION
"Data value."
::= { dataArray13 16 }

dataValue13_17 OBJECT-TYPE
SYNTAX INTEGER
MAX-ACCESS read-write
STATUS current
DESCRIPTION
"Data value."
::= { dataArray13 17 }

dataValue13_18 OBJECT-TYPE
SYNTAX INTEGER
MAX-ACCESS read-write
STATUS current
DESCRIPTION
"Data value."
::= { dataArray13 18 }

dataValue13_19 OBJECT-TYPE
SYNTAX INTEGER
MAX-ACCESS read-write
STATUS current
DESCRIPTION
"Data value."
::= { dataArray13 19 }

dataValue13_20 OBJECT-TYPE
SYNTAX INTEGER
MAX-ACCESS read-write
STATUS current
DESCRIPTION
"Data value."
::= { dataArray13 20 }

dataValue13_21 OBJECT-TYPE
SYNTAX INTEGER
MAX-ACCESS read-write
STATUS current
DESCRIPTION
"Data value."
::= { dataArray13 21 }

dataValue13_22 OBJECT-TYPE
SYNTAX INTEGER
MAX-ACCESS read-write
STATUS current
DESCRIPTION
"Data value."
::= { dataArray13 22 }

dataValue13_23 OBJECT-TYPE
SYNTAX INTEGER
MAX-ACCESS read-write
STATUS current
DESCRIPTION
"Data value."
::= { dataArray13 23 }

dataValue13_24 OBJECT-TYPE
SYNTAX INTEGER
MAX-ACCESS read-write
STATUS current
DESCRIPTION
"Data value."
::= { dataArray13 24 }

dataValue13_25 OBJECT-TYPE
SYNTAX INTEGER
MAX-ACCESS read-write
STATUS current
DESCRIPTION
"Data value."
::= { dataArray13 25 }

dataValue13_26 OBJECT-TYPE
SYNTAX INTEGER
MAX-ACCESS read-write
STATUS current
DESCRIPTION
"Data value."
::= { dataArray13 26 }

dataValue13_27 OBJECT-TYPE
SYNTAX INTEGER
MAX-ACCESS read-write
STATUS current
DESCRIPTION
"Data value."
::= { dataArray13 27 }

dataValue13_28 OBJECT-TYPE
SYNTAX INTEGER
MAX-ACCESS read-write
STATUS current
DESCRIPTION
"Data value."
::= { dataArray13 28 }

dataValue13_29 OBJECT-TYPE
SYNTAX INTEGER
MAX-ACCESS read-write
STATUS current
DESCRIPTION
"Data value."
::= { dataArray13 29 }

dataValue13_30 OBJECT-TYPE
SYNTAX INTEGER
MAX-ACCESS read-write
STATUS current
DESCRIPTION
"Data value."
::= { dataArray13 30 }

dataValue13_31 OBJECT-TYPE
SYNTAX INTEGER
MAX-ACCESS read-write
STATUS current
DESCRIPTION
"Data value."
::= { dataArray13 31 }

dataValue13_32 OBJECT-TYPE
SYNTAX INTEGER
MAX-ACCESS read-write
STATUS current
DESCRIPTION
"Data value."
::= { dataArray13 32 }

dataValue13_33 OBJECT-TYPE
SYNTAX INTEGER
MAX-ACCESS read-write
STATUS current
DESCRIPTION
"Data value."
::= { dataArray13 33 }

dataValue13_34 OBJECT-TYPE
SYNTAX INTEGER
MAX-ACCESS read-write
STATUS current
DESCRIPTION
"Data value."
::= { dataArray13 34 }

dataValue13_35 OBJECT-TYPE
SYNTAX INTEGER
MAX-ACCESS read-write
STATUS current
DESCRIPTION
"Data value."
::= { dataArray13 35 }

dataValue13_36 OBJECT-TYPE
SYNTAX INTEGER
MAX-ACCESS read-write
STATUS current
DESCRIPTION
"Data value."
::= { dataArray13 36 }

dataValue13_37 OBJECT-TYPE
SYNTAX INTEGER
MAX-ACCESS read-write
STATUS current
DESCRIPTION
"Data value."
::= { dataArray13 37 }

dataValue13_38 OBJECT-TYPE
SYNTAX INTEGER
MAX-ACCESS read-write
STATUS current
DESCRIPTION
"Data value."
::= { dataArray13 38 }

dataValue13_39 OBJECT-TYPE
SYNTAX INTEGER
MAX-ACCESS read-write
STATUS current
DESCRIPTION
"Data value."
::= { dataArray13 39 }

dataValue13_40 OBJECT-TYPE
SYNTAX INTEGER
MAX-ACCESS read-write
STATUS current
DESCRIPTION
"Data value."
::= { dataArray13 40 }

dataValue13_41 OBJECT-TYPE
SYNTAX INTEGER
MAX-ACCESS read-write
STATUS current
DESCRIPTION
"Data value."
::= { dataArray13 41 }

dataValue13_42 OBJECT-TYPE
SYNTAX INTEGER
MAX-ACCESS read-write
STATUS current
DESCRIPTION
"Data value."
::= { dataArray13 42 }

dataValue13_43 OBJECT-TYPE
SYNTAX INTEGER
MAX-ACCESS read-write
STATUS current
DESCRIPTION
"Data value."
::= { dataArray13 43 }

dataValue13_44 OBJECT-TYPE
SYNTAX INTEGER
MAX-ACCESS read-write
STATUS current
DESCRIPTION
"Data value."
::= { dataArray13 44 }

dataValue13_45 OBJECT-TYPE
SYNTAX INTEGER
MAX-ACCESS read-write
STATUS current
DESCRIPTION
"Data value."
::= { dataArray13 45 }

dataValue13_46 OBJECT-TYPE
SYNTAX INTEGER
MAX-ACCESS read-write
STATUS current
DESCRIPTION
"Data value."
::= { dataArray13 46 }

dataValue13_47 OBJECT-TYPE
SYNTAX INTEGER
MAX-ACCESS read-write
STATUS current
DESCRIPTION
"Data value."
::= { dataArray13 47 }

dataValue13_48 OBJECT-TYPE
SYNTAX INTEGER
MAX-ACCESS read-write
STATUS current
DESCRIPTION
"Data value."
::= { dataArray13 48 }

dataValue13_49 OBJECT-TYPE
SYNTAX INTEGER
MAX-ACCESS read-write
STATUS current
DESCRIPTION
"Data value."
::= { dataArray13 49 }

dataValue13_50 OBJECT-TYPE
SYNTAX INTEGER
MAX-ACCESS read-write
STATUS current
DESCRIPTION
"Data value."
::= { dataArray13 50 }

dataValue13_51 OBJECT-TYPE
SYNTAX INTEGER
MAX-ACCESS read-write
STATUS current
DESCRIPTION
"Data value."
::= { dataArray13 51 }

dataValue13_52 OBJECT-TYPE
SYNTAX INTEGER
MAX-ACCESS read-write
STATUS current
DESCRIPTION
"Data value."
::= { dataArray13 52 }

dataValue13_53 OBJECT-TYPE
SYNTAX INTEGER
MAX-ACCESS read-write
STATUS current
DESCRIPTION
"Data value."
::= { dataArray13 53 }

dataValue13_54 OBJECT-TYPE
SYNTAX INTEGER
MAX-ACCESS read-write
STATUS current
DESCRIPTION
"Data value."
::= { dataArray13 54 }

dataValue13_55 OBJECT-TYPE
SYNTAX INTEGER
MAX-ACCESS read-write
STATUS current
DESCRIPTION
"Data value."
::= { dataArray13 55 }

dataValue13_56 OBJECT-TYPE
SYNTAX INTEGER
MAX-ACCESS read-write
STATUS current
DESCRIPTION
"Data value."
::= { dataArray13 56 }

dataValue13_57 OBJECT-TYPE
SYNTAX INTEGER
MAX-ACCESS read-write
STATUS current
DESCRIPTION
"Data value."
::= { dataArray13 57 }

dataValue13_58 OBJECT-TYPE
SYNTAX INTEGER
MAX-ACCESS read-write
STATUS current
DESCRIPTION
"Data value."
::= { dataArray13 58 }

dataValue13_59 OBJECT-TYPE
SYNTAX INTEGER
MAX-ACCESS read-write
STATUS current
DESCRIPTION
"Data value."
::= { dataArray13 59 }

dataValue13_60 OBJECT-TYPE
SYNTAX INTEGER
MAX-ACCESS read-write
STATUS current
DESCRIPTION
"Data value."
::= { dataArray13 60 }

dataValue13_61 OBJECT-TYPE
SYNTAX INTEGER
MAX-ACCESS read-write
STATUS current
DESCRIPTION
"Data value."
::= { dataArray13 61 }

dataValue13_62 OBJECT-TYPE
SYNTAX INTEGER
MAX-ACCESS read-write
STATUS current
DESCRIPTION
"Data value."
::= { dataArray13 62 }

dataValue13_63 OBJECT-TYPE
SYNTAX INTEGER
MAX-ACCESS read-write
STATUS current
DESCRIPTION
"Data value."
::= { dataArray13 63 }

dataValue13_64 OBJECT-TYPE
SYNTAX INTEGER
MAX-ACCESS read-write
STATUS current
DESCRIPTION
"Data value."
::= { dataArray13 64 }

dataValue13_65 OBJECT-TYPE
SYNTAX INTEGER
MAX-ACCESS read-write
STATUS current
DESCRIPTION
"Data value."
::= { dataArray13 65 }

dataValue13_66 OBJECT-TYPE
SYNTAX INTEGER
MAX-ACCESS read-write
STATUS current
DESCRIPTION
"Data value."
::= { dataArray13 66 }

dataValue13_67 OBJECT-TYPE
SYNTAX INTEGER
MAX-ACCESS read-write
STATUS current
DESCRIPTION
"Data value."
::= { dataArray13 67 }

dataValue13_68 OBJECT-TYPE
SYNTAX INTEGER
MAX-ACCESS read-write
STATUS current
DESCRIPTION
"Data value."
::= { dataArray13 68 }

dataValue13_69 OBJECT-TYPE
SYNTAX INTEGER
MAX-ACCESS read-write
STATUS current
DESCRIPTION
"Data value."
::= { dataArray13 69 }

dataValue13_70 OBJECT-TYPE
SYNTAX INTEGER
MAX-ACCESS read-write
STATUS current
DESCRIPTION
"Data value."
::= { dataArray13 70 }

dataValue13_71 OBJECT-TYPE
SYNTAX INTEGER
MAX-ACCESS read-write
STATUS current
DESCRIPTION
"Data value."
::= { dataArray13 71 }

dataValue13_72 OBJECT-TYPE
SYNTAX INTEGER
MAX-ACCESS read-write
STATUS current
DESCRIPTION
"Data value."
::= { dataArray13 72 }

dataValue13_73 OBJECT-TYPE
SYNTAX INTEGER
MAX-ACCESS read-write
STATUS current
DESCRIPTION
"Data value."
::= { dataArray13 73 }

dataValue13_74 OBJECT-TYPE
SYNTAX INTEGER
MAX-ACCESS read-write
STATUS current
DESCRIPTION
"Data value."
::= { dataArray13 74 }

dataValue13_75 OBJECT-TYPE
SYNTAX INTEGER
MAX-ACCESS read-write
STATUS current
DESCRIPTION
"Data value."
::= { dataArray13 75 }

dataValue13_76 OBJECT-TYPE
SYNTAX INTEGER
MAX-ACCESS read-write
STATUS current
DESCRIPTION
"Data value."
::= { dataArray13 76 }

dataValue13_77 OBJECT-TYPE
SYNTAX INTEGER
MAX-ACCESS read-write
STATUS current
DESCRIPTION
"Data value."
::= { dataArray13 77 }

dataValue13_78 OBJECT-TYPE
SYNTAX INTEGER
MAX-ACCESS read-write
STATUS current
DESCRIPTION
"Data value."
::= { dataArray13 78 }

dataValue13_79 OBJECT-TYPE
SYNTAX INTEGER
MAX-ACCESS read-write
STATUS current
DESCRIPTION
"Data value."
::= { dataArray13 79 }

dataValue13_80 OBJECT-TYPE
SYNTAX INTEGER
MAX-ACCESS read-write
STATUS current
DESCRIPTION
"Data value."
::= { dataArray13 80 }

dataValue13_81 OBJECT-TYPE
SYNTAX INTEGER
MAX-ACCESS read-write
STATUS current
DESCRIPTION
"Data value."
::= { dataArray13 81 }

dataValue13_82 OBJECT-TYPE
SYNTAX INTEGER
MAX-ACCESS read-write
STATUS current
DESCRIPTION
"Data value."
::= { dataArray13 82 }

dataValue13_83 OBJECT-TYPE
SYNTAX INTEGER
MAX-ACCESS read-write
STATUS current
DESCRIPTION
"Data value."
::= { dataArray13 83 }

dataValue13_84 OBJECT-TYPE
SYNTAX INTEGER
MAX-ACCESS read-write
STATUS current
DESCRIPTION
"Data value."
::= { dataArray13 84 }

dataValue13_85 OBJECT-TYPE
SYNTAX INTEGER
MAX-ACCESS read-write
STATUS current
DESCRIPTION
"Data value."
::= { dataArray13 85 }

dataValue13_86 OBJECT-TYPE
SYNTAX INTEGER
MAX-ACCESS read-write
STATUS current
DESCRIPTION
"Data value."
::= { dataArray13 86 }

dataValue13_87 OBJECT-TYPE
SYNTAX INTEGER
MAX-ACCESS read-write
STATUS current
DESCRIPTION
"Data value."
::= { dataArray13 87 }

dataValue13_88 OBJECT-TYPE
SYNTAX INTEGER
MAX-ACCESS read-write
STATUS current
DESCRIPTION
"Data value."
::= { dataArray13 88 }

dataValue13_89 OBJECT-TYPE
SYNTAX INTEGER
MAX-ACCESS read-write
STATUS current
DESCRIPTION
"Data value."
::= { dataArray13 89 }

dataValue13_90 OBJECT-TYPE
SYNTAX INTEGER
MAX-ACCESS read-write
STATUS current
DESCRIPTION
"Data value."
::= { dataArray13 90 }

dataValue13_91 OBJECT-TYPE
SYNTAX INTEGER
MAX-ACCESS read-write
STATUS current
DESCRIPTION
"Data value."
::= { dataArray13 91 }

dataValue13_92 OBJECT-TYPE
SYNTAX INTEGER
MAX-ACCESS read-write
STATUS current
DESCRIPTION
"Data value."
::= { dataArray13 92 }

dataValue13_93 OBJECT-TYPE
SYNTAX INTEGER
MAX-ACCESS read-write
STATUS current
DESCRIPTION
"Data value."
::= { dataArray13 93 }

dataValue13_94 OBJECT-TYPE
SYNTAX INTEGER
MAX-ACCESS read-write
STATUS current
DESCRIPTION
"Data value."
::= { dataArray13 94 }

dataValue13_95 OBJECT-TYPE
SYNTAX INTEGER
MAX-ACCESS read-write
STATUS current
DESCRIPTION
"Data value."
::= { dataArray13 95 }

dataValue13_96 OBJECT-TYPE
SYNTAX INTEGER
MAX-ACCESS read-write
STATUS current
DESCRIPTION
"Data value."
::= { dataArray13 96 }

dataValue13_97 OBJECT-TYPE
SYNTAX INTEGER
MAX-ACCESS read-write
STATUS current
DESCRIPTION
"Data value."
::= { dataArray13 97 }

dataValue13_98 OBJECT-TYPE
SYNTAX INTEGER
MAX-ACCESS read-write
STATUS current
DESCRIPTION
"Data value."
::= { dataArray13 98 }

dataValue13_99 OBJECT-TYPE
SYNTAX INTEGER
MAX-ACCESS read-write
STATUS current
DESCRIPTION
"Data value."
::= { dataArray13 99 }

dataValue13_100 OBJECT-TYPE
SYNTAX INTEGER
MAX-ACCESS read-write
STATUS current
DESCRIPTION
"Data value."
::= { dataArray13 100 }

dataValue13_101 OBJECT-TYPE
SYNTAX INTEGER
MAX-ACCESS read-write
STATUS current
DESCRIPTION
"Data value."
::= { dataArray13 101 }

dataValue13_102 OBJECT-TYPE
SYNTAX INTEGER
MAX-ACCESS read-write
STATUS current
DESCRIPTION
"Data value."
::= { dataArray13 102 }

dataValue13_103 OBJECT-TYPE
SYNTAX INTEGER
MAX-ACCESS read-write
STATUS current
DESCRIPTION
"Data value."
::= { dataArray13 103 }

dataValue13_104 OBJECT-TYPE
SYNTAX INTEGER
MAX-ACCESS read-write
STATUS current
DESCRIPTION
"Data value."
::= { dataArray13 104 }

dataValue13_105 OBJECT-TYPE
SYNTAX INTEGER
MAX-ACCESS read-write
STATUS current
DESCRIPTION
"Data value."
::= { dataArray13 105 }

dataValue13_106 OBJECT-TYPE
SYNTAX INTEGER
MAX-ACCESS read-write
STATUS current
DESCRIPTION
"Data value."
::= { dataArray13 106 }

dataValue13_107 OBJECT-TYPE
SYNTAX INTEGER
MAX-ACCESS read-write
STATUS current
DESCRIPTION
"Data value."
::= { dataArray13 107 }

dataValue13_108 OBJECT-TYPE
SYNTAX INTEGER
MAX-ACCESS read-write
STATUS current
DESCRIPTION
"Data value."
::= { dataArray13 108 }

dataValue13_109 OBJECT-TYPE
SYNTAX INTEGER
MAX-ACCESS read-write
STATUS current
DESCRIPTION
"Data value."
::= { dataArray13 109 }

dataValue13_110 OBJECT-TYPE
SYNTAX INTEGER
MAX-ACCESS read-write
STATUS current
DESCRIPTION
"Data value."
::= { dataArray13 110 }

dataValue13_111 OBJECT-TYPE
SYNTAX INTEGER
MAX-ACCESS read-write
STATUS current
DESCRIPTION
"Data value."
::= { dataArray13 111 }

dataValue13_112 OBJECT-TYPE
SYNTAX INTEGER
MAX-ACCESS read-write
STATUS current
DESCRIPTION
"Data value."
::= { dataArray13 112 }

dataValue13_113 OBJECT-TYPE
SYNTAX INTEGER
MAX-ACCESS read-write
STATUS current
DESCRIPTION
"Data value."
::= { dataArray13 113 }

dataValue13_114 OBJECT-TYPE
SYNTAX INTEGER
MAX-ACCESS read-write
STATUS current
DESCRIPTION
"Data value."
::= { dataArray13 114 }

dataValue13_115 OBJECT-TYPE
SYNTAX INTEGER
MAX-ACCESS read-write
STATUS current
DESCRIPTION
"Data value."
::= { dataArray13 115 }

dataValue13_116 OBJECT-TYPE
SYNTAX INTEGER
MAX-ACCESS read-write
STATUS current
DESCRIPTION
"Data value."
::= { dataArray13 116 }

dataValue13_117 OBJECT-TYPE
SYNTAX INTEGER
MAX-ACCESS read-write
STATUS current
DESCRIPTION
"Data value."
::= { dataArray13 117 }

dataValue13_118 OBJECT-TYPE
SYNTAX INTEGER
MAX-ACCESS read-write
STATUS current
DESCRIPTION
"Data value."
::= { dataArray13 118 }

dataValue13_119 OBJECT-TYPE
SYNTAX INTEGER
MAX-ACCESS read-write
STATUS current
DESCRIPTION
"Data value."
::= { dataArray13 119 }

dataValue13_120 OBJECT-TYPE
SYNTAX INTEGER
MAX-ACCESS read-write
STATUS current
DESCRIPTION
"Data value."
::= { dataArray13 120 }

dataValue13_121 OBJECT-TYPE
SYNTAX INTEGER
MAX-ACCESS read-write
STATUS current
DESCRIPTION
"Data value."
::= { dataArray13 121 }

dataValue13_122 OBJECT-TYPE
SYNTAX INTEGER
MAX-ACCESS read-write
STATUS current
DESCRIPTION
"Data value."
::= { dataArray13 122 }

dataValue13_123 OBJECT-TYPE
SYNTAX INTEGER
MAX-ACCESS read-write
STATUS current
DESCRIPTION
"Data value."
::= { dataArray13 123 }

dataValue13_124 OBJECT-TYPE
SYNTAX INTEGER
MAX-ACCESS read-write
STATUS current
DESCRIPTION
"Data value."
::= { dataArray13 124 }

dataValue13_125 OBJECT-TYPE
SYNTAX INTEGER
MAX-ACCESS read-write
STATUS current
DESCRIPTION
"Data value."
::= { dataArray13 125 }

dataValue13_126 OBJECT-TYPE
SYNTAX INTEGER
MAX-ACCESS read-write
STATUS current
DESCRIPTION
"Data value."
::= { dataArray13 126 }

dataValue13_127 OBJECT-TYPE
SYNTAX INTEGER
MAX-ACCESS read-write
STATUS current
DESCRIPTION
"Data value."
::= { dataArray13 127 }

dataValue13_128 OBJECT-TYPE
SYNTAX INTEGER
MAX-ACCESS read-write
STATUS current
DESCRIPTION
"Data value."
::= { dataArray13 128 }

dataValue13_129 OBJECT-TYPE
SYNTAX INTEGER
MAX-ACCESS read-write
STATUS current
DESCRIPTION
"Data value."
::= { dataArray13 129 }

dataValue13_130 OBJECT-TYPE
SYNTAX INTEGER
MAX-ACCESS read-write
STATUS current
DESCRIPTION
"Data value."
::= { dataArray13 130 }

dataValue13_131 OBJECT-TYPE
SYNTAX INTEGER
MAX-ACCESS read-write
STATUS current
DESCRIPTION
"Data value."
::= { dataArray13 131 }

dataValue13_132 OBJECT-TYPE
SYNTAX INTEGER
MAX-ACCESS read-write
STATUS current
DESCRIPTION
"Data value."
::= { dataArray13 132 }

dataValue13_133 OBJECT-TYPE
SYNTAX INTEGER
MAX-ACCESS read-write
STATUS current
DESCRIPTION
"Data value."
::= { dataArray13 133 }

dataValue13_134 OBJECT-TYPE
SYNTAX INTEGER
MAX-ACCESS read-write
STATUS current
DESCRIPTION
"Data value."
::= { dataArray13 134 }

dataValue13_135 OBJECT-TYPE
SYNTAX INTEGER
MAX-ACCESS read-write
STATUS current
DESCRIPTION
"Data value."
::= { dataArray13 135 }

dataValue13_136 OBJECT-TYPE
SYNTAX INTEGER
MAX-ACCESS read-write
STATUS current
DESCRIPTION
"Data value."
::= { dataArray13 136 }

dataValue13_137 OBJECT-TYPE
SYNTAX INTEGER
MAX-ACCESS read-write
STATUS current
DESCRIPTION
"Data value."
::= { dataArray13 137 }

dataValue13_138 OBJECT-TYPE
SYNTAX INTEGER
MAX-ACCESS read-write
STATUS current
DESCRIPTION
"Data value."
::= { dataArray13 138 }

dataValue13_139 OBJECT-TYPE
SYNTAX INTEGER
MAX-ACCESS read-write
STATUS current
DESCRIPTION
"Data value."
::= { dataArray13 139 }

dataValue13_140 OBJECT-TYPE
SYNTAX INTEGER
MAX-ACCESS read-write
STATUS current
DESCRIPTION
"Data value."
::= { dataArray13 140 }

dataValue13_141 OBJECT-TYPE
SYNTAX INTEGER
MAX-ACCESS read-write
STATUS current
DESCRIPTION
"Data value."
::= { dataArray13 141 }

dataValue13_142 OBJECT-TYPE
SYNTAX INTEGER
MAX-ACCESS read-write
STATUS current
DESCRIPTION
"Data value."
::= { dataArray13 142 }

dataValue13_143 OBJECT-TYPE
SYNTAX INTEGER
MAX-ACCESS read-write
STATUS current
DESCRIPTION
"Data value."
::= { dataArray13 143 }

dataValue13_144 OBJECT-TYPE
SYNTAX INTEGER
MAX-ACCESS read-write
STATUS current
DESCRIPTION
"Data value."
::= { dataArray13 144 }

dataValue13_145 OBJECT-TYPE
SYNTAX INTEGER
MAX-ACCESS read-write
STATUS current
DESCRIPTION
"Data value."
::= { dataArray13 145 }

dataValue13_146 OBJECT-TYPE
SYNTAX INTEGER
MAX-ACCESS read-write
STATUS current
DESCRIPTION
"Data value."
::= { dataArray13 146 }

dataValue13_147 OBJECT-TYPE
SYNTAX INTEGER
MAX-ACCESS read-write
STATUS current
DESCRIPTION
"Data value."
::= { dataArray13 147 }

dataValue13_148 OBJECT-TYPE
SYNTAX INTEGER
MAX-ACCESS read-write
STATUS current
DESCRIPTION
"Data value."
::= { dataArray13 148 }

dataValue13_149 OBJECT-TYPE
SYNTAX INTEGER
MAX-ACCESS read-write
STATUS current
DESCRIPTION
"Data value."
::= { dataArray13 149 }

dataValue13_150 OBJECT-TYPE
SYNTAX INTEGER
MAX-ACCESS read-write
STATUS current
DESCRIPTION
"Data value."
::= { dataArray13 150 }

dataValue13_151 OBJECT-TYPE
SYNTAX INTEGER
MAX-ACCESS read-write
STATUS current
DESCRIPTION
"Data value."
::= { dataArray13 151 }

dataValue13_152 OBJECT-TYPE
SYNTAX INTEGER
MAX-ACCESS read-write
STATUS current
DESCRIPTION
"Data value."
::= { dataArray13 152 }

dataValue13_153 OBJECT-TYPE
SYNTAX INTEGER
MAX-ACCESS read-write
STATUS current
DESCRIPTION
"Data value."
::= { dataArray13 153 }

dataValue13_154 OBJECT-TYPE
SYNTAX INTEGER
MAX-ACCESS read-write
STATUS current
DESCRIPTION
"Data value."
::= { dataArray13 154 }

dataValue13_155 OBJECT-TYPE
SYNTAX INTEGER
MAX-ACCESS read-write
STATUS current
DESCRIPTION
"Data value."
::= { dataArray13 155 }

dataValue13_156 OBJECT-TYPE
SYNTAX INTEGER
MAX-ACCESS read-write
STATUS current
DESCRIPTION
"Data value."
::= { dataArray13 156 }

dataValue13_157 OBJECT-TYPE
SYNTAX INTEGER
MAX-ACCESS read-write
STATUS current
DESCRIPTION
"Data value."
::= { dataArray13 157 }

dataValue13_158 OBJECT-TYPE
SYNTAX INTEGER
MAX-ACCESS read-write
STATUS current
DESCRIPTION
"Data value."
::= { dataArray13 158 }

dataValue13_159 OBJECT-TYPE
SYNTAX INTEGER
MAX-ACCESS read-write
STATUS current
DESCRIPTION
"Data value."
::= { dataArray13 159 }

dataValue13_160 OBJECT-TYPE
SYNTAX INTEGER
MAX-ACCESS read-write
STATUS current
DESCRIPTION
"Data value."
::= { dataArray13 160 }

dataValue13_161 OBJECT-TYPE
SYNTAX INTEGER
MAX-ACCESS read-write
STATUS current
DESCRIPTION
"Data value."
::= { dataArray13 161 }

dataValue13_162 OBJECT-TYPE
SYNTAX INTEGER
MAX-ACCESS read-write
STATUS current
DESCRIPTION
"Data value."
::= { dataArray13 162 }

dataValue13_163 OBJECT-TYPE
SYNTAX INTEGER
MAX-ACCESS read-write
STATUS current
DESCRIPTION
"Data value."
::= { dataArray13 163 }

dataValue13_164 OBJECT-TYPE
SYNTAX INTEGER
MAX-ACCESS read-write
STATUS current
DESCRIPTION
"Data value."
::= { dataArray13 164 }

dataValue13_165 OBJECT-TYPE
SYNTAX INTEGER
MAX-ACCESS read-write
STATUS current
DESCRIPTION
"Data value."
::= { dataArray13 165 }

dataValue13_166 OBJECT-TYPE
SYNTAX INTEGER
MAX-ACCESS read-write
STATUS current
DESCRIPTION
"Data value."
::= { dataArray13 166 }

dataValue13_167 OBJECT-TYPE
SYNTAX INTEGER
MAX-ACCESS read-write
STATUS current
DESCRIPTION
"Data value."
::= { dataArray13 167 }

dataValue13_168 OBJECT-TYPE
SYNTAX INTEGER
MAX-ACCESS read-write
STATUS current
DESCRIPTION
"Data value."
::= { dataArray13 168 }

dataValue13_169 OBJECT-TYPE
SYNTAX INTEGER
MAX-ACCESS read-write
STATUS current
DESCRIPTION
"Data value."
::= { dataArray13 169 }

dataValue13_170 OBJECT-TYPE
SYNTAX INTEGER
MAX-ACCESS read-write
STATUS current
DESCRIPTION
"Data value."
::= { dataArray13 170 }

dataValue13_171 OBJECT-TYPE
SYNTAX INTEGER
MAX-ACCESS read-write
STATUS current
DESCRIPTION
"Data value."
::= { dataArray13 171 }

dataValue13_172 OBJECT-TYPE
SYNTAX INTEGER
MAX-ACCESS read-write
STATUS current
DESCRIPTION
"Data value."
::= { dataArray13 172 }

dataValue13_173 OBJECT-TYPE
SYNTAX INTEGER
MAX-ACCESS read-write
STATUS current
DESCRIPTION
"Data value."
::= { dataArray13 173 }

dataValue13_174 OBJECT-TYPE
SYNTAX INTEGER
MAX-ACCESS read-write
STATUS current
DESCRIPTION
"Data value."
::= { dataArray13 174 }

dataValue13_175 OBJECT-TYPE
SYNTAX INTEGER
MAX-ACCESS read-write
STATUS current
DESCRIPTION
"Data value."
::= { dataArray13 175 }

dataValue13_176 OBJECT-TYPE
SYNTAX INTEGER
MAX-ACCESS read-write
STATUS current
DESCRIPTION
"Data value."
::= { dataArray13 176 }

dataValue13_177 OBJECT-TYPE
SYNTAX INTEGER
MAX-ACCESS read-write
STATUS current
DESCRIPTION
"Data value."
::= { dataArray13 177 }

dataValue13_178 OBJECT-TYPE
SYNTAX INTEGER
MAX-ACCESS read-write
STATUS current
DESCRIPTION
"Data value."
::= { dataArray13 178 }

dataValue13_179 OBJECT-TYPE
SYNTAX INTEGER
MAX-ACCESS read-write
STATUS current
DESCRIPTION
"Data value."
::= { dataArray13 179 }

dataValue13_180 OBJECT-TYPE
SYNTAX INTEGER
MAX-ACCESS read-write
STATUS current
DESCRIPTION
"Data value."
::= { dataArray13 180 }

dataValue13_181 OBJECT-TYPE
SYNTAX INTEGER
MAX-ACCESS read-write
STATUS current
DESCRIPTION
"Data value."
::= { dataArray13 181 }

dataValue13_182 OBJECT-TYPE
SYNTAX INTEGER
MAX-ACCESS read-write
STATUS current
DESCRIPTION
"Data value."
::= { dataArray13 182 }

dataValue13_183 OBJECT-TYPE
SYNTAX INTEGER
MAX-ACCESS read-write
STATUS current
DESCRIPTION
"Data value."
::= { dataArray13 183 }

dataValue13_184 OBJECT-TYPE
SYNTAX INTEGER
MAX-ACCESS read-write
STATUS current
DESCRIPTION
"Data value."
::= { dataArray13 184 }

dataValue13_185 OBJECT-TYPE
SYNTAX INTEGER
MAX-ACCESS read-write
STATUS current
DESCRIPTION
"Data value."
::= { dataArray13 185 }

dataValue13_186 OBJECT-TYPE
SYNTAX INTEGER
MAX-ACCESS read-write
STATUS current
DESCRIPTION
"Data value."
::= { dataArray13 186 }

dataValue13_187 OBJECT-TYPE
SYNTAX INTEGER
MAX-ACCESS read-write
STATUS current
DESCRIPTION
"Data value."
::= { dataArray13 187 }

dataValue13_188 OBJECT-TYPE
SYNTAX INTEGER
MAX-ACCESS read-write
STATUS current
DESCRIPTION
"Data value."
::= { dataArray13 188 }

dataValue13_189 OBJECT-TYPE
SYNTAX INTEGER
MAX-ACCESS read-write
STATUS current
DESCRIPTION
"Data value."
::= { dataArray13 189 }

dataValue13_190 OBJECT-TYPE
SYNTAX INTEGER
MAX-ACCESS read-write
STATUS current
DESCRIPTION
"Data value."
::= { dataArray13 190 }

dataValue13_191 OBJECT-TYPE
SYNTAX INTEGER
MAX-ACCESS read-write
STATUS current
DESCRIPTION
"Data value."
::= { dataArray13 191 }

dataValue13_192 OBJECT-TYPE
SYNTAX INTEGER
MAX-ACCESS read-write
STATUS current
DESCRIPTION
"Data value."
::= { dataArray13 192 }

dataValue13_193 OBJECT-TYPE
SYNTAX INTEGER
MAX-ACCESS read-write
STATUS current
DESCRIPTION
"Data value."
::= { dataArray13 193 }

dataValue13_194 OBJECT-TYPE
SYNTAX INTEGER
MAX-ACCESS read-write
STATUS current
DESCRIPTION
"Data value."
::= { dataArray13 194 }

dataValue13_195 OBJECT-TYPE
SYNTAX INTEGER
MAX-ACCESS read-write
STATUS current
DESCRIPTION
"Data value."
::= { dataArray13 195 }

dataValue13_196 OBJECT-TYPE
SYNTAX INTEGER
MAX-ACCESS read-write
STATUS current
DESCRIPTION
"Data value."
::= { dataArray13 196 }

dataValue13_197 OBJECT-TYPE
SYNTAX INTEGER
MAX-ACCESS read-write
STATUS current
DESCRIPTION
"Data value."
::= { dataArray13 197 }

dataValue13_198 OBJECT-TYPE
SYNTAX INTEGER
MAX-ACCESS read-write
STATUS current
DESCRIPTION
"Data value."
::= { dataArray13 198 }

dataValue13_199 OBJECT-TYPE
SYNTAX INTEGER
MAX-ACCESS read-write
STATUS current
DESCRIPTION
"Data value."
::= { dataArray13 199 }

dataValue13_200 OBJECT-TYPE
SYNTAX INTEGER
MAX-ACCESS read-write
STATUS current
DESCRIPTION
"Data value."
::= { dataArray13 200 }

dataValue13_201 OBJECT-TYPE
SYNTAX INTEGER
MAX-ACCESS read-write
STATUS current
DESCRIPTION
"Data value."
::= { dataArray13 201 }

dataValue13_202 OBJECT-TYPE
SYNTAX INTEGER
MAX-ACCESS read-write
STATUS current
DESCRIPTION
"Data value."
::= { dataArray13 202 }

dataValue13_203 OBJECT-TYPE
SYNTAX INTEGER
MAX-ACCESS read-write
STATUS current
DESCRIPTION
"Data value."
::= { dataArray13 203 }

dataValue13_204 OBJECT-TYPE
SYNTAX INTEGER
MAX-ACCESS read-write
STATUS current
DESCRIPTION
"Data value."
::= { dataArray13 204 }

dataValue13_205 OBJECT-TYPE
SYNTAX INTEGER
MAX-ACCESS read-write
STATUS current
DESCRIPTION
"Data value."
::= { dataArray13 205 }

dataValue13_206 OBJECT-TYPE
SYNTAX INTEGER
MAX-ACCESS read-write
STATUS current
DESCRIPTION
"Data value."
::= { dataArray13 206 }

dataValue13_207 OBJECT-TYPE
SYNTAX INTEGER
MAX-ACCESS read-write
STATUS current
DESCRIPTION
"Data value."
::= { dataArray13 207 }

dataValue13_208 OBJECT-TYPE
SYNTAX INTEGER
MAX-ACCESS read-write
STATUS current
DESCRIPTION
"Data value."
::= { dataArray13 208 }

dataValue13_209 OBJECT-TYPE
SYNTAX INTEGER
MAX-ACCESS read-write
STATUS current
DESCRIPTION
"Data value."
::= { dataArray13 209 }

dataValue13_210 OBJECT-TYPE
SYNTAX INTEGER
MAX-ACCESS read-write
STATUS current
DESCRIPTION
"Data value."
::= { dataArray13 210 }

dataValue13_211 OBJECT-TYPE
SYNTAX INTEGER
MAX-ACCESS read-write
STATUS current
DESCRIPTION
"Data value."
::= { dataArray13 211 }

dataValue13_212 OBJECT-TYPE
SYNTAX INTEGER
MAX-ACCESS read-write
STATUS current
DESCRIPTION
"Data value."
::= { dataArray13 212 }

dataValue13_213 OBJECT-TYPE
SYNTAX INTEGER
MAX-ACCESS read-write
STATUS current
DESCRIPTION
"Data value."
::= { dataArray13 213 }

dataValue13_214 OBJECT-TYPE
SYNTAX INTEGER
MAX-ACCESS read-write
STATUS current
DESCRIPTION
"Data value."
::= { dataArray13 214 }

dataValue13_215 OBJECT-TYPE
SYNTAX INTEGER
MAX-ACCESS read-write
STATUS current
DESCRIPTION
"Data value."
::= { dataArray13 215 }

dataValue13_216 OBJECT-TYPE
SYNTAX INTEGER
MAX-ACCESS read-write
STATUS current
DESCRIPTION
"Data value."
::= { dataArray13 216 }

dataValue13_217 OBJECT-TYPE
SYNTAX INTEGER
MAX-ACCESS read-write
STATUS current
DESCRIPTION
"Data value."
::= { dataArray13 217 }

dataValue13_218 OBJECT-TYPE
SYNTAX INTEGER
MAX-ACCESS read-write
STATUS current
DESCRIPTION
"Data value."
::= { dataArray13 218 }

dataValue13_219 OBJECT-TYPE
SYNTAX INTEGER
MAX-ACCESS read-write
STATUS current
DESCRIPTION
"Data value."
::= { dataArray13 219 }

dataValue13_220 OBJECT-TYPE
SYNTAX INTEGER
MAX-ACCESS read-write
STATUS current
DESCRIPTION
"Data value."
::= { dataArray13 220 }

dataValue13_221 OBJECT-TYPE
SYNTAX INTEGER
MAX-ACCESS read-write
STATUS current
DESCRIPTION
"Data value."
::= { dataArray13 221 }

dataValue13_222 OBJECT-TYPE
SYNTAX INTEGER
MAX-ACCESS read-write
STATUS current
DESCRIPTION
"Data value."
::= { dataArray13 222 }

dataValue13_223 OBJECT-TYPE
SYNTAX INTEGER
MAX-ACCESS read-write
STATUS current
DESCRIPTION
"Data value."
::= { dataArray13 223 }

dataValue13_224 OBJECT-TYPE
SYNTAX INTEGER
MAX-ACCESS read-write
STATUS current
DESCRIPTION
"Data value."
::= { dataArray13 224 }

dataValue13_225 OBJECT-TYPE
SYNTAX INTEGER
MAX-ACCESS read-write
STATUS current
DESCRIPTION
"Data value."
::= { dataArray13 225 }

dataValue13_226 OBJECT-TYPE
SYNTAX INTEGER
MAX-ACCESS read-write
STATUS current
DESCRIPTION
"Data value."
::= { dataArray13 226 }

dataValue13_227 OBJECT-TYPE
SYNTAX INTEGER
MAX-ACCESS read-write
STATUS current
DESCRIPTION
"Data value."
::= { dataArray13 227 }

dataValue13_228 OBJECT-TYPE
SYNTAX INTEGER
MAX-ACCESS read-write
STATUS current
DESCRIPTION
"Data value."
::= { dataArray13 228 }

dataValue13_229 OBJECT-TYPE
SYNTAX INTEGER
MAX-ACCESS read-write
STATUS current
DESCRIPTION
"Data value."
::= { dataArray13 229 }

dataValue13_230 OBJECT-TYPE
SYNTAX INTEGER
MAX-ACCESS read-write
STATUS current
DESCRIPTION
"Data value."
::= { dataArray13 230 }

dataValue13_231 OBJECT-TYPE
SYNTAX INTEGER
MAX-ACCESS read-write
STATUS current
DESCRIPTION
"Data value."
::= { dataArray13 231 }

dataValue13_232 OBJECT-TYPE
SYNTAX INTEGER
MAX-ACCESS read-write
STATUS current
DESCRIPTION
"Data value."
::= { dataArray13 232 }

dataValue13_233 OBJECT-TYPE
SYNTAX INTEGER
MAX-ACCESS read-write
STATUS current
DESCRIPTION
"Data value."
::= { dataArray13 233 }

dataValue13_234 OBJECT-TYPE
SYNTAX INTEGER
MAX-ACCESS read-write
STATUS current
DESCRIPTION
"Data value."
::= { dataArray13 234 }

dataValue13_235 OBJECT-TYPE
SYNTAX INTEGER
MAX-ACCESS read-write
STATUS current
DESCRIPTION
"Data value."
::= { dataArray13 235 }

dataValue13_236 OBJECT-TYPE
SYNTAX INTEGER
MAX-ACCESS read-write
STATUS current
DESCRIPTION
"Data value."
::= { dataArray13 236 }

dataValue13_237 OBJECT-TYPE
SYNTAX INTEGER
MAX-ACCESS read-write
STATUS current
DESCRIPTION
"Data value."
::= { dataArray13 237 }

dataValue13_238 OBJECT-TYPE
SYNTAX INTEGER
MAX-ACCESS read-write
STATUS current
DESCRIPTION
"Data value."
::= { dataArray13 238 }

dataValue13_239 OBJECT-TYPE
SYNTAX INTEGER
MAX-ACCESS read-write
STATUS current
DESCRIPTION
"Data value."
::= { dataArray13 239 }

dataValue13_240 OBJECT-TYPE
SYNTAX INTEGER
MAX-ACCESS read-write
STATUS current
DESCRIPTION
"Data value."
::= { dataArray13 240 }

dataValue13_241 OBJECT-TYPE
SYNTAX INTEGER
MAX-ACCESS read-write
STATUS current
DESCRIPTION
"Data value."
::= { dataArray13 241 }

dataValue13_242 OBJECT-TYPE
SYNTAX INTEGER
MAX-ACCESS read-write
STATUS current
DESCRIPTION
"Data value."
::= { dataArray13 242 }

dataValue13_243 OBJECT-TYPE
SYNTAX INTEGER
MAX-ACCESS read-write
STATUS current
DESCRIPTION
"Data value."
::= { dataArray13 243 }

dataValue13_244 OBJECT-TYPE
SYNTAX INTEGER
MAX-ACCESS read-write
STATUS current
DESCRIPTION
"Data value."
::= { dataArray13 244 }

dataValue13_245 OBJECT-TYPE
SYNTAX INTEGER
MAX-ACCESS read-write
STATUS current
DESCRIPTION
"Data value."
::= { dataArray13 245 }

dataValue13_246 OBJECT-TYPE
SYNTAX INTEGER
MAX-ACCESS read-write
STATUS current
DESCRIPTION
"Data value."
::= { dataArray13 246 }

dataValue13_247 OBJECT-TYPE
SYNTAX INTEGER
MAX-ACCESS read-write
STATUS current
DESCRIPTION
"Data value."
::= { dataArray13 247 }

dataValue13_248 OBJECT-TYPE
SYNTAX INTEGER
MAX-ACCESS read-write
STATUS current
DESCRIPTION
"Data value."
::= { dataArray13 248 }

dataValue13_249 OBJECT-TYPE
SYNTAX INTEGER
MAX-ACCESS read-write
STATUS current
DESCRIPTION
"Data value."
::= { dataArray13 249 }

dataValue13_250 OBJECT-TYPE
SYNTAX INTEGER
MAX-ACCESS read-write
STATUS current
DESCRIPTION
"Data value."
::= { dataArray13 250 }

dataValue13_251 OBJECT-TYPE
SYNTAX INTEGER
MAX-ACCESS read-write
STATUS current
DESCRIPTION
"Data value."
::= { dataArray13 251 }

dataValue13_252 OBJECT-TYPE
SYNTAX INTEGER
MAX-ACCESS read-write
STATUS current
DESCRIPTION
"Data value."
::= { dataArray13 252 }

dataValue13_253 OBJECT-TYPE
SYNTAX INTEGER
MAX-ACCESS read-write
STATUS current
DESCRIPTION
"Data value."
::= { dataArray13 253 }

dataValue13_254 OBJECT-TYPE
SYNTAX INTEGER
MAX-ACCESS read-write
STATUS current
DESCRIPTION
"Data value."
::= { dataArray13 254 }

dataValue13_255 OBJECT-TYPE
SYNTAX INTEGER
MAX-ACCESS read-write
STATUS current
DESCRIPTION
"Data value."
::= { dataArray13 255 }

dataValue13_256 OBJECT-TYPE
SYNTAX INTEGER
MAX-ACCESS read-write
STATUS current
DESCRIPTION
"Data value."
::= { dataArray13 256 }

dataValue13_257 OBJECT-TYPE
SYNTAX INTEGER
MAX-ACCESS read-write
STATUS current
DESCRIPTION
"Data value."
::= { dataArray13 257 }

dataValue13_258 OBJECT-TYPE
SYNTAX INTEGER
MAX-ACCESS read-write
STATUS current
DESCRIPTION
"Data value."
::= { dataArray13 258 }

dataValue13_259 OBJECT-TYPE
SYNTAX INTEGER
MAX-ACCESS read-write
STATUS current
DESCRIPTION
"Data value."
::= { dataArray13 259 }

dataValue13_260 OBJECT-TYPE
SYNTAX INTEGER
MAX-ACCESS read-write
STATUS current
DESCRIPTION
"Data value."
::= { dataArray13 260 }

dataValue13_261 OBJECT-TYPE
SYNTAX INTEGER
MAX-ACCESS read-write
STATUS current
DESCRIPTION
"Data value."
::= { dataArray13 261 }

dataValue13_262 OBJECT-TYPE
SYNTAX INTEGER
MAX-ACCESS read-write
STATUS current
DESCRIPTION
"Data value."
::= { dataArray13 262 }

dataValue13_263 OBJECT-TYPE
SYNTAX INTEGER
MAX-ACCESS read-write
STATUS current
DESCRIPTION
"Data value."
::= { dataArray13 263 }

dataValue13_264 OBJECT-TYPE
SYNTAX INTEGER
MAX-ACCESS read-write
STATUS current
DESCRIPTION
"Data value."
::= { dataArray13 264 }

dataValue13_265 OBJECT-TYPE
SYNTAX INTEGER
MAX-ACCESS read-write
STATUS current
DESCRIPTION
"Data value."
::= { dataArray13 265 }

dataValue13_266 OBJECT-TYPE
SYNTAX INTEGER
MAX-ACCESS read-write
STATUS current
DESCRIPTION
"Data value."
::= { dataArray13 266 }

dataValue13_267 OBJECT-TYPE
SYNTAX INTEGER
MAX-ACCESS read-write
STATUS current
DESCRIPTION
"Data value."
::= { dataArray13 267 }

dataValue13_268 OBJECT-TYPE
SYNTAX INTEGER
MAX-ACCESS read-write
STATUS current
DESCRIPTION
"Data value."
::= { dataArray13 268 }

dataValue13_269 OBJECT-TYPE
SYNTAX INTEGER
MAX-ACCESS read-write
STATUS current
DESCRIPTION
"Data value."
::= { dataArray13 269 }

dataValue13_270 OBJECT-TYPE
SYNTAX INTEGER
MAX-ACCESS read-write
STATUS current
DESCRIPTION
"Data value."
::= { dataArray13 270 }

dataValue13_271 OBJECT-TYPE
SYNTAX INTEGER
MAX-ACCESS read-write
STATUS current
DESCRIPTION
"Data value."
::= { dataArray13 271 }

dataValue13_272 OBJECT-TYPE
SYNTAX INTEGER
MAX-ACCESS read-write
STATUS current
DESCRIPTION
"Data value."
::= { dataArray13 272 }

dataValue13_273 OBJECT-TYPE
SYNTAX INTEGER
MAX-ACCESS read-write
STATUS current
DESCRIPTION
"Data value."
::= { dataArray13 273 }

dataValue13_274 OBJECT-TYPE
SYNTAX INTEGER
MAX-ACCESS read-write
STATUS current
DESCRIPTION
"Data value."
::= { dataArray13 274 }

dataValue13_275 OBJECT-TYPE
SYNTAX INTEGER
MAX-ACCESS read-write
STATUS current
DESCRIPTION
"Data value."
::= { dataArray13 275 }

dataValue13_276 OBJECT-TYPE
SYNTAX INTEGER
MAX-ACCESS read-write
STATUS current
DESCRIPTION
"Data value."
::= { dataArray13 276 }

dataValue13_277 OBJECT-TYPE
SYNTAX INTEGER
MAX-ACCESS read-write
STATUS current
DESCRIPTION
"Data value."
::= { dataArray13 277 }

dataValue13_278 OBJECT-TYPE
SYNTAX INTEGER
MAX-ACCESS read-write
STATUS current
DESCRIPTION
"Data value."
::= { dataArray13 278 }

dataValue13_279 OBJECT-TYPE
SYNTAX INTEGER
MAX-ACCESS read-write
STATUS current
DESCRIPTION
"Data value."
::= { dataArray13 279 }

dataValue13_280 OBJECT-TYPE
SYNTAX INTEGER
MAX-ACCESS read-write
STATUS current
DESCRIPTION
"Data value."
::= { dataArray13 280 }

dataValue13_281 OBJECT-TYPE
SYNTAX INTEGER
MAX-ACCESS read-write
STATUS current
DESCRIPTION
"Data value."
::= { dataArray13 281 }

dataValue13_282 OBJECT-TYPE
SYNTAX INTEGER
MAX-ACCESS read-write
STATUS current
DESCRIPTION
"Data value."
::= { dataArray13 282 }

dataValue13_283 OBJECT-TYPE
SYNTAX INTEGER
MAX-ACCESS read-write
STATUS current
DESCRIPTION
"Data value."
::= { dataArray13 283 }

dataValue13_284 OBJECT-TYPE
SYNTAX INTEGER
MAX-ACCESS read-write
STATUS current
DESCRIPTION
"Data value."
::= { dataArray13 284 }

dataValue13_285 OBJECT-TYPE
SYNTAX INTEGER
MAX-ACCESS read-write
STATUS current
DESCRIPTION
"Data value."
::= { dataArray13 285 }

dataValue13_286 OBJECT-TYPE
SYNTAX INTEGER
MAX-ACCESS read-write
STATUS current
DESCRIPTION
"Data value."
::= { dataArray13 286 }

dataValue13_287 OBJECT-TYPE
SYNTAX INTEGER
MAX-ACCESS read-write
STATUS current
DESCRIPTION
"Data value."
::= { dataArray13 287 }

dataValue13_288 OBJECT-TYPE
SYNTAX INTEGER
MAX-ACCESS read-write
STATUS current
DESCRIPTION
"Data value."
::= { dataArray13 288 }

dataValue13_289 OBJECT-TYPE
SYNTAX INTEGER
MAX-ACCESS read-write
STATUS current
DESCRIPTION
"Data value."
::= { dataArray13 289 }

dataValue13_290 OBJECT-TYPE
SYNTAX INTEGER
MAX-ACCESS read-write
STATUS current
DESCRIPTION
"Data value."
::= { dataArray13 290 }

dataValue13_291 OBJECT-TYPE
SYNTAX INTEGER
MAX-ACCESS read-write
STATUS current
DESCRIPTION
"Data value."
::= { dataArray13 291 }

dataValue13_292 OBJECT-TYPE
SYNTAX INTEGER
MAX-ACCESS read-write
STATUS current
DESCRIPTION
"Data value."
::= { dataArray13 292 }

dataValue13_293 OBJECT-TYPE
SYNTAX INTEGER
MAX-ACCESS read-write
STATUS current
DESCRIPTION
"Data value."
::= { dataArray13 293 }

dataValue13_294 OBJECT-TYPE
SYNTAX INTEGER
MAX-ACCESS read-write
STATUS current
DESCRIPTION
"Data value."
::= { dataArray13 294 }

dataValue13_295 OBJECT-TYPE
SYNTAX INTEGER
MAX-ACCESS read-write
STATUS current
DESCRIPTION
"Data value."
::= { dataArray13 295 }

dataValue13_296 OBJECT-TYPE
SYNTAX INTEGER
MAX-ACCESS read-write
STATUS current
DESCRIPTION
"Data value."
::= { dataArray13 296 }

dataValue13_297 OBJECT-TYPE
SYNTAX INTEGER
MAX-ACCESS read-write
STATUS current
DESCRIPTION
"Data value."
::= { dataArray13 297 }

dataValue13_298 OBJECT-TYPE
SYNTAX INTEGER
MAX-ACCESS read-write
STATUS current
DESCRIPTION
"Data value."
::= { dataArray13 298 }

dataValue13_299 OBJECT-TYPE
SYNTAX INTEGER
MAX-ACCESS read-write
STATUS current
DESCRIPTION
"Data value."
::= { dataArray13 299 }

dataValue13_300 OBJECT-TYPE
SYNTAX INTEGER
MAX-ACCESS read-write
STATUS current
DESCRIPTION
"Data value."
::= { dataArray13 300 }

dataValue13_301 OBJECT-TYPE
SYNTAX INTEGER
MAX-ACCESS read-write
STATUS current
DESCRIPTION
"Data value."
::= { dataArray13 301 }

dataValue13_302 OBJECT-TYPE
SYNTAX INTEGER
MAX-ACCESS read-write
STATUS current
DESCRIPTION
"Data value."
::= { dataArray13 302 }

dataValue13_303 OBJECT-TYPE
SYNTAX INTEGER
MAX-ACCESS read-write
STATUS current
DESCRIPTION
"Data value."
::= { dataArray13 303 }

dataValue13_304 OBJECT-TYPE
SYNTAX INTEGER
MAX-ACCESS read-write
STATUS current
DESCRIPTION
"Data value."
::= { dataArray13 304 }

dataValue13_305 OBJECT-TYPE
SYNTAX INTEGER
MAX-ACCESS read-write
STATUS current
DESCRIPTION
"Data value."
::= { dataArray13 305 }

dataValue13_306 OBJECT-TYPE
SYNTAX INTEGER
MAX-ACCESS read-write
STATUS current
DESCRIPTION
"Data value."
::= { dataArray13 306 }

dataValue13_307 OBJECT-TYPE
SYNTAX INTEGER
MAX-ACCESS read-write
STATUS current
DESCRIPTION
"Data value."
::= { dataArray13 307 }

dataValue13_308 OBJECT-TYPE
SYNTAX INTEGER
MAX-ACCESS read-write
STATUS current
DESCRIPTION
"Data value."
::= { dataArray13 308 }

dataValue13_309 OBJECT-TYPE
SYNTAX INTEGER
MAX-ACCESS read-write
STATUS current
DESCRIPTION
"Data value."
::= { dataArray13 309 }

dataValue13_310 OBJECT-TYPE
SYNTAX INTEGER
MAX-ACCESS read-write
STATUS current
DESCRIPTION
"Data value."
::= { dataArray13 310 }

dataValue13_311 OBJECT-TYPE
SYNTAX INTEGER
MAX-ACCESS read-write
STATUS current
DESCRIPTION
"Data value."
::= { dataArray13 311 }

dataValue13_312 OBJECT-TYPE
SYNTAX INTEGER
MAX-ACCESS read-write
STATUS current
DESCRIPTION
"Data value."
::= { dataArray13 312 }

dataValue13_313 OBJECT-TYPE
SYNTAX INTEGER
MAX-ACCESS read-write
STATUS current
DESCRIPTION
"Data value."
::= { dataArray13 313 }

dataValue13_314 OBJECT-TYPE
SYNTAX INTEGER
MAX-ACCESS read-write
STATUS current
DESCRIPTION
"Data value."
::= { dataArray13 314 }

dataValue13_315 OBJECT-TYPE
SYNTAX INTEGER
MAX-ACCESS read-write
STATUS current
DESCRIPTION
"Data value."
::= { dataArray13 315 }

dataValue13_316 OBJECT-TYPE
SYNTAX INTEGER
MAX-ACCESS read-write
STATUS current
DESCRIPTION
"Data value."
::= { dataArray13 316 }

dataValue13_317 OBJECT-TYPE
SYNTAX INTEGER
MAX-ACCESS read-write
STATUS current
DESCRIPTION
"Data value."
::= { dataArray13 317 }

dataValue13_318 OBJECT-TYPE
SYNTAX INTEGER
MAX-ACCESS read-write
STATUS current
DESCRIPTION
"Data value."
::= { dataArray13 318 }

dataValue13_319 OBJECT-TYPE
SYNTAX INTEGER
MAX-ACCESS read-write
STATUS current
DESCRIPTION
"Data value."
::= { dataArray13 319 }

dataValue13_320 OBJECT-TYPE
SYNTAX INTEGER
MAX-ACCESS read-write
STATUS current
DESCRIPTION
"Data value."
::= { dataArray13 320 }

dataValue13_321 OBJECT-TYPE
SYNTAX INTEGER
MAX-ACCESS read-write
STATUS current
DESCRIPTION
"Data value."
::= { dataArray13 321 }

dataValue13_322 OBJECT-TYPE
SYNTAX INTEGER
MAX-ACCESS read-write
STATUS current
DESCRIPTION
"Data value."
::= { dataArray13 322 }

dataValue13_323 OBJECT-TYPE
SYNTAX INTEGER
MAX-ACCESS read-write
STATUS current
DESCRIPTION
"Data value."
::= { dataArray13 323 }

dataValue13_324 OBJECT-TYPE
SYNTAX INTEGER
MAX-ACCESS read-write
STATUS current
DESCRIPTION
"Data value."
::= { dataArray13 324 }

dataValue13_325 OBJECT-TYPE
SYNTAX INTEGER
MAX-ACCESS read-write
STATUS current
DESCRIPTION
"Data value."
::= { dataArray13 325 }

dataValue13_326 OBJECT-TYPE
SYNTAX INTEGER
MAX-ACCESS read-write
STATUS current
DESCRIPTION
"Data value."
::= { dataArray13 326 }

dataValue13_327 OBJECT-TYPE
SYNTAX INTEGER
MAX-ACCESS read-write
STATUS current
DESCRIPTION
"Data value."
::= { dataArray13 327 }

dataValue13_328 OBJECT-TYPE
SYNTAX INTEGER
MAX-ACCESS read-write
STATUS current
DESCRIPTION
"Data value."
::= { dataArray13 328 }

dataValue13_329 OBJECT-TYPE
SYNTAX INTEGER
MAX-ACCESS read-write
STATUS current
DESCRIPTION
"Data value."
::= { dataArray13 329 }

dataValue13_330 OBJECT-TYPE
SYNTAX INTEGER
MAX-ACCESS read-write
STATUS current
DESCRIPTION
"Data value."
::= { dataArray13 330 }

dataValue13_331 OBJECT-TYPE
SYNTAX INTEGER
MAX-ACCESS read-write
STATUS current
DESCRIPTION
"Data value."
::= { dataArray13 331 }

dataValue13_332 OBJECT-TYPE
SYNTAX INTEGER
MAX-ACCESS read-write
STATUS current
DESCRIPTION
"Data value."
::= { dataArray13 332 }

dataValue13_333 OBJECT-TYPE
SYNTAX INTEGER
MAX-ACCESS read-write
STATUS current
DESCRIPTION
"Data value."
::= { dataArray13 333 }

dataValue13_334 OBJECT-TYPE
SYNTAX INTEGER
MAX-ACCESS read-write
STATUS current
DESCRIPTION
"Data value."
::= { dataArray13 334 }

dataValue13_335 OBJECT-TYPE
SYNTAX INTEGER
MAX-ACCESS read-write
STATUS current
DESCRIPTION
"Data value."
::= { dataArray13 335 }

dataValue13_336 OBJECT-TYPE
SYNTAX INTEGER
MAX-ACCESS read-write
STATUS current
DESCRIPTION
"Data value."
::= { dataArray13 336 }

dataValue13_337 OBJECT-TYPE
SYNTAX INTEGER
MAX-ACCESS read-write
STATUS current
DESCRIPTION
"Data value."
::= { dataArray13 337 }

dataValue13_338 OBJECT-TYPE
SYNTAX INTEGER
MAX-ACCESS read-write
STATUS current
DESCRIPTION
"Data value."
::= { dataArray13 338 }

dataValue13_339 OBJECT-TYPE
SYNTAX INTEGER
MAX-ACCESS read-write
STATUS current
DESCRIPTION
"Data value."
::= { dataArray13 339 }

dataValue13_340 OBJECT-TYPE
SYNTAX INTEGER
MAX-ACCESS read-write
STATUS current
DESCRIPTION
"Data value."
::= { dataArray13 340 }

dataValue13_341 OBJECT-TYPE
SYNTAX INTEGER
MAX-ACCESS read-write
STATUS current
DESCRIPTION
"Data value."
::= { dataArray13 341 }

dataValue13_342 OBJECT-TYPE
SYNTAX INTEGER
MAX-ACCESS read-write
STATUS current
DESCRIPTION
"Data value."
::= { dataArray13 342 }

dataValue13_343 OBJECT-TYPE
SYNTAX INTEGER
MAX-ACCESS read-write
STATUS current
DESCRIPTION
"Data value."
::= { dataArray13 343 }

dataValue13_344 OBJECT-TYPE
SYNTAX INTEGER
MAX-ACCESS read-write
STATUS current
DESCRIPTION
"Data value."
::= { dataArray13 344 }

dataValue13_345 OBJECT-TYPE
SYNTAX INTEGER
MAX-ACCESS read-write
STATUS current
DESCRIPTION
"Data value."
::= { dataArray13 345 }

dataValue13_346 OBJECT-TYPE
SYNTAX INTEGER
MAX-ACCESS read-write
STATUS current
DESCRIPTION
"Data value."
::= { dataArray13 346 }

dataValue13_347 OBJECT-TYPE
SYNTAX INTEGER
MAX-ACCESS read-write
STATUS current
DESCRIPTION
"Data value."
::= { dataArray13 347 }

dataValue13_348 OBJECT-TYPE
SYNTAX INTEGER
MAX-ACCESS read-write
STATUS current
DESCRIPTION
"Data value."
::= { dataArray13 348 }

dataValue13_349 OBJECT-TYPE
SYNTAX INTEGER
MAX-ACCESS read-write
STATUS current
DESCRIPTION
"Data value."
::= { dataArray13 349 }

dataValue13_350 OBJECT-TYPE
SYNTAX INTEGER
MAX-ACCESS read-write
STATUS current
DESCRIPTION
"Data value."
::= { dataArray13 350 }

dataValue13_351 OBJECT-TYPE
SYNTAX INTEGER
MAX-ACCESS read-write
STATUS current
DESCRIPTION
"Data value."
::= { dataArray13 351 }

dataValue13_352 OBJECT-TYPE
SYNTAX INTEGER
MAX-ACCESS read-write
STATUS current
DESCRIPTION
"Data value."
::= { dataArray13 352 }

dataValue13_353 OBJECT-TYPE
SYNTAX INTEGER
MAX-ACCESS read-write
STATUS current
DESCRIPTION
"Data value."
::= { dataArray13 353 }

dataValue13_354 OBJECT-TYPE
SYNTAX INTEGER
MAX-ACCESS read-write
STATUS current
DESCRIPTION
"Data value."
::= { dataArray13 354 }

dataValue13_355 OBJECT-TYPE
SYNTAX INTEGER
MAX-ACCESS read-write
STATUS current
DESCRIPTION
"Data value."
::= { dataArray13 355 }

dataValue13_356 OBJECT-TYPE
SYNTAX INTEGER
MAX-ACCESS read-write
STATUS current
DESCRIPTION
"Data value."
::= { dataArray13 356 }

dataValue13_357 OBJECT-TYPE
SYNTAX INTEGER
MAX-ACCESS read-write
STATUS current
DESCRIPTION
"Data value."
::= { dataArray13 357 }

dataValue13_358 OBJECT-TYPE
SYNTAX INTEGER
MAX-ACCESS read-write
STATUS current
DESCRIPTION
"Data value."
::= { dataArray13 358 }

dataValue13_359 OBJECT-TYPE
SYNTAX INTEGER
MAX-ACCESS read-write
STATUS current
DESCRIPTION
"Data value."
::= { dataArray13 359 }

dataValue13_360 OBJECT-TYPE
SYNTAX INTEGER
MAX-ACCESS read-write
STATUS current
DESCRIPTION
"Data value."
::= { dataArray13 360 }

dataValue13_361 OBJECT-TYPE
SYNTAX INTEGER
MAX-ACCESS read-write
STATUS current
DESCRIPTION
"Data value."
::= { dataArray13 361 }

dataValue13_362 OBJECT-TYPE
SYNTAX INTEGER
MAX-ACCESS read-write
STATUS current
DESCRIPTION
"Data value."
::= { dataArray13 362 }

dataValue13_363 OBJECT-TYPE
SYNTAX INTEGER
MAX-ACCESS read-write
STATUS current
DESCRIPTION
"Data value."
::= { dataArray13 363 }

dataValue13_364 OBJECT-TYPE
SYNTAX INTEGER
MAX-ACCESS read-write
STATUS current
DESCRIPTION
"Data value."
::= { dataArray13 364 }

dataValue13_365 OBJECT-TYPE
SYNTAX INTEGER
MAX-ACCESS read-write
STATUS current
DESCRIPTION
"Data value."
::= { dataArray13 365 }

dataValue13_366 OBJECT-TYPE
SYNTAX INTEGER
MAX-ACCESS read-write
STATUS current
DESCRIPTION
"Data value."
::= { dataArray13 366 }

dataValue13_367 OBJECT-TYPE
SYNTAX INTEGER
MAX-ACCESS read-write
STATUS current
DESCRIPTION
"Data value."
::= { dataArray13 367 }

dataValue13_368 OBJECT-TYPE
SYNTAX INTEGER
MAX-ACCESS read-write
STATUS current
DESCRIPTION
"Data value."
::= { dataArray13 368 }

dataValue13_369 OBJECT-TYPE
SYNTAX INTEGER
MAX-ACCESS read-write
STATUS current
DESCRIPTION
"Data value."
::= { dataArray13 369 }

dataValue13_370 OBJECT-TYPE
SYNTAX INTEGER
MAX-ACCESS read-write
STATUS current
DESCRIPTION
"Data value."
::= { dataArray13 370 }

dataValue13_371 OBJECT-TYPE
SYNTAX INTEGER
MAX-ACCESS read-write
STATUS current
DESCRIPTION
"Data value."
::= { dataArray13 371 }

dataValue13_372 OBJECT-TYPE
SYNTAX INTEGER
MAX-ACCESS read-write
STATUS current
DESCRIPTION
"Data value."
::= { dataArray13 372 }

dataValue13_373 OBJECT-TYPE
SYNTAX INTEGER
MAX-ACCESS read-write
STATUS current
DESCRIPTION
"Data value."
::= { dataArray13 373 }

dataValue13_374 OBJECT-TYPE
SYNTAX INTEGER
MAX-ACCESS read-write
STATUS current
DESCRIPTION
"Data value."
::= { dataArray13 374 }

dataValue13_375 OBJECT-TYPE
SYNTAX INTEGER
MAX-ACCESS read-write
STATUS current
DESCRIPTION
"Data value."
::= { dataArray13 375 }

dataValue13_376 OBJECT-TYPE
SYNTAX INTEGER
MAX-ACCESS read-write
STATUS current
DESCRIPTION
"Data value."
::= { dataArray13 376 }

dataValue13_377 OBJECT-TYPE
SYNTAX INTEGER
MAX-ACCESS read-write
STATUS current
DESCRIPTION
"Data value."
::= { dataArray13 377 }

dataValue13_378 OBJECT-TYPE
SYNTAX INTEGER
MAX-ACCESS read-write
STATUS current
DESCRIPTION
"Data value."
::= { dataArray13 378 }

dataValue13_379 OBJECT-TYPE
SYNTAX INTEGER
MAX-ACCESS read-write
STATUS current
DESCRIPTION
"Data value."
::= { dataArray13 379 }

dataValue13_380 OBJECT-TYPE
SYNTAX INTEGER
MAX-ACCESS read-write
STATUS current
DESCRIPTION
"Data value."
::= { dataArray13 380 }

dataValue13_381 OBJECT-TYPE
SYNTAX INTEGER
MAX-ACCESS read-write
STATUS current
DESCRIPTION
"Data value."
::= { dataArray13 381 }

dataValue13_382 OBJECT-TYPE
SYNTAX INTEGER
MAX-ACCESS read-write
STATUS current
DESCRIPTION
"Data value."
::= { dataArray13 382 }

dataValue13_383 OBJECT-TYPE
SYNTAX INTEGER
MAX-ACCESS read-write
STATUS current
DESCRIPTION
"Data value."
::= { dataArray13 383 }

dataValue13_384 OBJECT-TYPE
SYNTAX INTEGER
MAX-ACCESS read-write
STATUS current
DESCRIPTION
"Data value."
::= { dataArray13 384 }

dataValue13_385 OBJECT-TYPE
SYNTAX INTEGER
MAX-ACCESS read-write
STATUS current
DESCRIPTION
"Data value."
::= { dataArray13 385 }

dataValue13_386 OBJECT-TYPE
SYNTAX INTEGER
MAX-ACCESS read-write
STATUS current
DESCRIPTION
"Data value."
::= { dataArray13 386 }

dataValue13_387 OBJECT-TYPE
SYNTAX INTEGER
MAX-ACCESS read-write
STATUS current
DESCRIPTION
"Data value."
::= { dataArray13 387 }

dataValue13_388 OBJECT-TYPE
SYNTAX INTEGER
MAX-ACCESS read-write
STATUS current
DESCRIPTION
"Data value."
::= { dataArray13 388 }

dataValue13_389 OBJECT-TYPE
SYNTAX INTEGER
MAX-ACCESS read-write
STATUS current
DESCRIPTION
"Data value."
::= { dataArray13 389 }

dataValue13_390 OBJECT-TYPE
SYNTAX INTEGER
MAX-ACCESS read-write
STATUS current
DESCRIPTION
"Data value."
::= { dataArray13 390 }

dataValue13_391 OBJECT-TYPE
SYNTAX INTEGER
MAX-ACCESS read-write
STATUS current
DESCRIPTION
"Data value."
::= { dataArray13 391 }

dataValue13_392 OBJECT-TYPE
SYNTAX INTEGER
MAX-ACCESS read-write
STATUS current
DESCRIPTION
"Data value."
::= { dataArray13 392 }

dataValue13_393 OBJECT-TYPE
SYNTAX INTEGER
MAX-ACCESS read-write
STATUS current
DESCRIPTION
"Data value."
::= { dataArray13 393 }

dataValue13_394 OBJECT-TYPE
SYNTAX INTEGER
MAX-ACCESS read-write
STATUS current
DESCRIPTION
"Data value."
::= { dataArray13 394 }

dataValue13_395 OBJECT-TYPE
SYNTAX INTEGER
MAX-ACCESS read-write
STATUS current
DESCRIPTION
"Data value."
::= { dataArray13 395 }

dataValue13_396 OBJECT-TYPE
SYNTAX INTEGER
MAX-ACCESS read-write
STATUS current
DESCRIPTION
"Data value."
::= { dataArray13 396 }

dataValue13_397 OBJECT-TYPE
SYNTAX INTEGER
MAX-ACCESS read-write
STATUS current
DESCRIPTION
"Data value."
::= { dataArray13 397 }

dataValue13_398 OBJECT-TYPE
SYNTAX INTEGER
MAX-ACCESS read-write
STATUS current
DESCRIPTION
"Data value."
::= { dataArray13 398 }

dataValue13_399 OBJECT-TYPE
SYNTAX INTEGER
MAX-ACCESS read-write
STATUS current
DESCRIPTION
"Data value."
::= { dataArray13 399 }

dataArray14 OBJECT IDENTIFIER ::= { cc08255400_v1_00a 14 }

dataValue14_0 OBJECT-TYPE
SYNTAX INTEGER
MAX-ACCESS read-write
STATUS current
DESCRIPTION
"Data value."
::= { dataArray14 0 }

dataValue14_1 OBJECT-TYPE
SYNTAX INTEGER
MAX-ACCESS read-write
STATUS current
DESCRIPTION
"Data value."
::= { dataArray14 1 }

dataValue14_2 OBJECT-TYPE
SYNTAX INTEGER
MAX-ACCESS read-write
STATUS current
DESCRIPTION
"Data value."
::= { dataArray14 2 }

dataValue14_3 OBJECT-TYPE
SYNTAX INTEGER
MAX-ACCESS read-write
STATUS current
DESCRIPTION
"Data value."
::= { dataArray14 3 }

dataValue14_4 OBJECT-TYPE
SYNTAX INTEGER
MAX-ACCESS read-write
STATUS current
DESCRIPTION
"Data value."
::= { dataArray14 4 }

dataValue14_5 OBJECT-TYPE
SYNTAX INTEGER
MAX-ACCESS read-write
STATUS current
DESCRIPTION
"Data value."
::= { dataArray14 5 }

dataValue14_6 OBJECT-TYPE
SYNTAX INTEGER
MAX-ACCESS read-write
STATUS current
DESCRIPTION
"Data value."
::= { dataArray14 6 }

dataValue14_7 OBJECT-TYPE
SYNTAX INTEGER
MAX-ACCESS read-write
STATUS current
DESCRIPTION
"Data value."
::= { dataArray14 7 }

dataValue14_8 OBJECT-TYPE
SYNTAX INTEGER
MAX-ACCESS read-write
STATUS current
DESCRIPTION
"Data value."
::= { dataArray14 8 }

dataValue14_9 OBJECT-TYPE
SYNTAX INTEGER
MAX-ACCESS read-write
STATUS current
DESCRIPTION
"Data value."
::= { dataArray14 9 }

dataValue14_10 OBJECT-TYPE
SYNTAX INTEGER
MAX-ACCESS read-write
STATUS current
DESCRIPTION
"Data value."
::= { dataArray14 10 }

dataValue14_11 OBJECT-TYPE
SYNTAX INTEGER
MAX-ACCESS read-write
STATUS current
DESCRIPTION
"Data value."
::= { dataArray14 11 }

dataValue14_12 OBJECT-TYPE
SYNTAX INTEGER
MAX-ACCESS read-write
STATUS current
DESCRIPTION
"Data value."
::= { dataArray14 12 }

dataValue14_13 OBJECT-TYPE
SYNTAX INTEGER
MAX-ACCESS read-write
STATUS current
DESCRIPTION
"Data value."
::= { dataArray14 13 }

dataValue14_14 OBJECT-TYPE
SYNTAX INTEGER
MAX-ACCESS read-write
STATUS current
DESCRIPTION
"Data value."
::= { dataArray14 14 }

dataValue14_15 OBJECT-TYPE
SYNTAX INTEGER
MAX-ACCESS read-write
STATUS current
DESCRIPTION
"Data value."
::= { dataArray14 15 }

dataValue14_16 OBJECT-TYPE
SYNTAX INTEGER
MAX-ACCESS read-write
STATUS current
DESCRIPTION
"Data value."
::= { dataArray14 16 }

dataValue14_17 OBJECT-TYPE
SYNTAX INTEGER
MAX-ACCESS read-write
STATUS current
DESCRIPTION
"Data value."
::= { dataArray14 17 }

dataValue14_18 OBJECT-TYPE
SYNTAX INTEGER
MAX-ACCESS read-write
STATUS current
DESCRIPTION
"Data value."
::= { dataArray14 18 }

dataValue14_19 OBJECT-TYPE
SYNTAX INTEGER
MAX-ACCESS read-write
STATUS current
DESCRIPTION
"Data value."
::= { dataArray14 19 }

dataValue14_20 OBJECT-TYPE
SYNTAX INTEGER
MAX-ACCESS read-write
STATUS current
DESCRIPTION
"Data value."
::= { dataArray14 20 }

dataValue14_21 OBJECT-TYPE
SYNTAX INTEGER
MAX-ACCESS read-write
STATUS current
DESCRIPTION
"Data value."
::= { dataArray14 21 }

dataValue14_22 OBJECT-TYPE
SYNTAX INTEGER
MAX-ACCESS read-write
STATUS current
DESCRIPTION
"Data value."
::= { dataArray14 22 }

dataValue14_23 OBJECT-TYPE
SYNTAX INTEGER
MAX-ACCESS read-write
STATUS current
DESCRIPTION
"Data value."
::= { dataArray14 23 }

dataValue14_24 OBJECT-TYPE
SYNTAX INTEGER
MAX-ACCESS read-write
STATUS current
DESCRIPTION
"Data value."
::= { dataArray14 24 }

dataValue14_25 OBJECT-TYPE
SYNTAX INTEGER
MAX-ACCESS read-write
STATUS current
DESCRIPTION
"Data value."
::= { dataArray14 25 }

dataValue14_26 OBJECT-TYPE
SYNTAX INTEGER
MAX-ACCESS read-write
STATUS current
DESCRIPTION
"Data value."
::= { dataArray14 26 }

dataValue14_27 OBJECT-TYPE
SYNTAX INTEGER
MAX-ACCESS read-write
STATUS current
DESCRIPTION
"Data value."
::= { dataArray14 27 }

dataValue14_28 OBJECT-TYPE
SYNTAX INTEGER
MAX-ACCESS read-write
STATUS current
DESCRIPTION
"Data value."
::= { dataArray14 28 }

dataValue14_29 OBJECT-TYPE
SYNTAX INTEGER
MAX-ACCESS read-write
STATUS current
DESCRIPTION
"Data value."
::= { dataArray14 29 }

dataValue14_30 OBJECT-TYPE
SYNTAX INTEGER
MAX-ACCESS read-write
STATUS current
DESCRIPTION
"Data value."
::= { dataArray14 30 }

dataValue14_31 OBJECT-TYPE
SYNTAX INTEGER
MAX-ACCESS read-write
STATUS current
DESCRIPTION
"Data value."
::= { dataArray14 31 }

dataValue14_32 OBJECT-TYPE
SYNTAX INTEGER
MAX-ACCESS read-write
STATUS current
DESCRIPTION
"Data value."
::= { dataArray14 32 }

dataValue14_33 OBJECT-TYPE
SYNTAX INTEGER
MAX-ACCESS read-write
STATUS current
DESCRIPTION
"Data value."
::= { dataArray14 33 }

dataValue14_34 OBJECT-TYPE
SYNTAX INTEGER
MAX-ACCESS read-write
STATUS current
DESCRIPTION
"Data value."
::= { dataArray14 34 }

dataValue14_35 OBJECT-TYPE
SYNTAX INTEGER
MAX-ACCESS read-write
STATUS current
DESCRIPTION
"Data value."
::= { dataArray14 35 }

dataValue14_36 OBJECT-TYPE
SYNTAX INTEGER
MAX-ACCESS read-write
STATUS current
DESCRIPTION
"Data value."
::= { dataArray14 36 }

dataValue14_37 OBJECT-TYPE
SYNTAX INTEGER
MAX-ACCESS read-write
STATUS current
DESCRIPTION
"Data value."
::= { dataArray14 37 }

dataValue14_38 OBJECT-TYPE
SYNTAX INTEGER
MAX-ACCESS read-write
STATUS current
DESCRIPTION
"Data value."
::= { dataArray14 38 }

dataValue14_39 OBJECT-TYPE
SYNTAX INTEGER
MAX-ACCESS read-write
STATUS current
DESCRIPTION
"Data value."
::= { dataArray14 39 }

dataValue14_40 OBJECT-TYPE
SYNTAX INTEGER
MAX-ACCESS read-write
STATUS current
DESCRIPTION
"Data value."
::= { dataArray14 40 }

dataValue14_41 OBJECT-TYPE
SYNTAX INTEGER
MAX-ACCESS read-write
STATUS current
DESCRIPTION
"Data value."
::= { dataArray14 41 }

dataValue14_42 OBJECT-TYPE
SYNTAX INTEGER
MAX-ACCESS read-write
STATUS current
DESCRIPTION
"Data value."
::= { dataArray14 42 }

dataValue14_43 OBJECT-TYPE
SYNTAX INTEGER
MAX-ACCESS read-write
STATUS current
DESCRIPTION
"Data value."
::= { dataArray14 43 }

dataValue14_44 OBJECT-TYPE
SYNTAX INTEGER
MAX-ACCESS read-write
STATUS current
DESCRIPTION
"Data value."
::= { dataArray14 44 }

dataValue14_45 OBJECT-TYPE
SYNTAX INTEGER
MAX-ACCESS read-write
STATUS current
DESCRIPTION
"Data value."
::= { dataArray14 45 }

dataValue14_46 OBJECT-TYPE
SYNTAX INTEGER
MAX-ACCESS read-write
STATUS current
DESCRIPTION
"Data value."
::= { dataArray14 46 }

dataValue14_47 OBJECT-TYPE
SYNTAX INTEGER
MAX-ACCESS read-write
STATUS current
DESCRIPTION
"Data value."
::= { dataArray14 47 }

dataValue14_48 OBJECT-TYPE
SYNTAX INTEGER
MAX-ACCESS read-write
STATUS current
DESCRIPTION
"Data value."
::= { dataArray14 48 }

dataValue14_49 OBJECT-TYPE
SYNTAX INTEGER
MAX-ACCESS read-write
STATUS current
DESCRIPTION
"Data value."
::= { dataArray14 49 }

dataValue14_50 OBJECT-TYPE
SYNTAX INTEGER
MAX-ACCESS read-write
STATUS current
DESCRIPTION
"Data value."
::= { dataArray14 50 }

dataValue14_51 OBJECT-TYPE
SYNTAX INTEGER
MAX-ACCESS read-write
STATUS current
DESCRIPTION
"Data value."
::= { dataArray14 51 }

dataValue14_52 OBJECT-TYPE
SYNTAX INTEGER
MAX-ACCESS read-write
STATUS current
DESCRIPTION
"Data value."
::= { dataArray14 52 }

dataValue14_53 OBJECT-TYPE
SYNTAX INTEGER
MAX-ACCESS read-write
STATUS current
DESCRIPTION
"Data value."
::= { dataArray14 53 }

dataValue14_54 OBJECT-TYPE
SYNTAX INTEGER
MAX-ACCESS read-write
STATUS current
DESCRIPTION
"Data value."
::= { dataArray14 54 }

dataValue14_55 OBJECT-TYPE
SYNTAX INTEGER
MAX-ACCESS read-write
STATUS current
DESCRIPTION
"Data value."
::= { dataArray14 55 }

dataValue14_56 OBJECT-TYPE
SYNTAX INTEGER
MAX-ACCESS read-write
STATUS current
DESCRIPTION
"Data value."
::= { dataArray14 56 }

dataValue14_57 OBJECT-TYPE
SYNTAX INTEGER
MAX-ACCESS read-write
STATUS current
DESCRIPTION
"Data value."
::= { dataArray14 57 }

dataValue14_58 OBJECT-TYPE
SYNTAX INTEGER
MAX-ACCESS read-write
STATUS current
DESCRIPTION
"Data value."
::= { dataArray14 58 }

dataValue14_59 OBJECT-TYPE
SYNTAX INTEGER
MAX-ACCESS read-write
STATUS current
DESCRIPTION
"Data value."
::= { dataArray14 59 }

dataValue14_60 OBJECT-TYPE
SYNTAX INTEGER
MAX-ACCESS read-write
STATUS current
DESCRIPTION
"Data value."
::= { dataArray14 60 }

dataValue14_61 OBJECT-TYPE
SYNTAX INTEGER
MAX-ACCESS read-write
STATUS current
DESCRIPTION
"Data value."
::= { dataArray14 61 }

dataValue14_62 OBJECT-TYPE
SYNTAX INTEGER
MAX-ACCESS read-write
STATUS current
DESCRIPTION
"Data value."
::= { dataArray14 62 }

dataValue14_63 OBJECT-TYPE
SYNTAX INTEGER
MAX-ACCESS read-write
STATUS current
DESCRIPTION
"Data value."
::= { dataArray14 63 }

dataValue14_64 OBJECT-TYPE
SYNTAX INTEGER
MAX-ACCESS read-write
STATUS current
DESCRIPTION
"Data value."
::= { dataArray14 64 }

dataValue14_65 OBJECT-TYPE
SYNTAX INTEGER
MAX-ACCESS read-write
STATUS current
DESCRIPTION
"Data value."
::= { dataArray14 65 }

dataValue14_66 OBJECT-TYPE
SYNTAX INTEGER
MAX-ACCESS read-write
STATUS current
DESCRIPTION
"Data value."
::= { dataArray14 66 }

dataValue14_67 OBJECT-TYPE
SYNTAX INTEGER
MAX-ACCESS read-write
STATUS current
DESCRIPTION
"Data value."
::= { dataArray14 67 }

dataValue14_68 OBJECT-TYPE
SYNTAX INTEGER
MAX-ACCESS read-write
STATUS current
DESCRIPTION
"Data value."
::= { dataArray14 68 }

dataValue14_69 OBJECT-TYPE
SYNTAX INTEGER
MAX-ACCESS read-write
STATUS current
DESCRIPTION
"Data value."
::= { dataArray14 69 }

dataValue14_70 OBJECT-TYPE
SYNTAX INTEGER
MAX-ACCESS read-write
STATUS current
DESCRIPTION
"Data value."
::= { dataArray14 70 }

dataValue14_71 OBJECT-TYPE
SYNTAX INTEGER
MAX-ACCESS read-write
STATUS current
DESCRIPTION
"Data value."
::= { dataArray14 71 }

dataValue14_72 OBJECT-TYPE
SYNTAX INTEGER
MAX-ACCESS read-write
STATUS current
DESCRIPTION
"Data value."
::= { dataArray14 72 }

dataValue14_73 OBJECT-TYPE
SYNTAX INTEGER
MAX-ACCESS read-write
STATUS current
DESCRIPTION
"Data value."
::= { dataArray14 73 }

dataValue14_74 OBJECT-TYPE
SYNTAX INTEGER
MAX-ACCESS read-write
STATUS current
DESCRIPTION
"Data value."
::= { dataArray14 74 }

dataValue14_75 OBJECT-TYPE
SYNTAX INTEGER
MAX-ACCESS read-write
STATUS current
DESCRIPTION
"Data value."
::= { dataArray14 75 }

dataValue14_76 OBJECT-TYPE
SYNTAX INTEGER
MAX-ACCESS read-write
STATUS current
DESCRIPTION
"Data value."
::= { dataArray14 76 }

dataValue14_77 OBJECT-TYPE
SYNTAX INTEGER
MAX-ACCESS read-write
STATUS current
DESCRIPTION
"Data value."
::= { dataArray14 77 }

dataValue14_78 OBJECT-TYPE
SYNTAX INTEGER
MAX-ACCESS read-write
STATUS current
DESCRIPTION
"Data value."
::= { dataArray14 78 }

dataValue14_79 OBJECT-TYPE
SYNTAX INTEGER
MAX-ACCESS read-write
STATUS current
DESCRIPTION
"Data value."
::= { dataArray14 79 }

dataValue14_80 OBJECT-TYPE
SYNTAX INTEGER
MAX-ACCESS read-write
STATUS current
DESCRIPTION
"Data value."
::= { dataArray14 80 }

dataValue14_81 OBJECT-TYPE
SYNTAX INTEGER
MAX-ACCESS read-write
STATUS current
DESCRIPTION
"Data value."
::= { dataArray14 81 }

dataValue14_82 OBJECT-TYPE
SYNTAX INTEGER
MAX-ACCESS read-write
STATUS current
DESCRIPTION
"Data value."
::= { dataArray14 82 }

dataValue14_83 OBJECT-TYPE
SYNTAX INTEGER
MAX-ACCESS read-write
STATUS current
DESCRIPTION
"Data value."
::= { dataArray14 83 }

dataValue14_84 OBJECT-TYPE
SYNTAX INTEGER
MAX-ACCESS read-write
STATUS current
DESCRIPTION
"Data value."
::= { dataArray14 84 }

dataValue14_85 OBJECT-TYPE
SYNTAX INTEGER
MAX-ACCESS read-write
STATUS current
DESCRIPTION
"Data value."
::= { dataArray14 85 }

dataValue14_86 OBJECT-TYPE
SYNTAX INTEGER
MAX-ACCESS read-write
STATUS current
DESCRIPTION
"Data value."
::= { dataArray14 86 }

dataValue14_87 OBJECT-TYPE
SYNTAX INTEGER
MAX-ACCESS read-write
STATUS current
DESCRIPTION
"Data value."
::= { dataArray14 87 }

dataValue14_88 OBJECT-TYPE
SYNTAX INTEGER
MAX-ACCESS read-write
STATUS current
DESCRIPTION
"Data value."
::= { dataArray14 88 }

dataValue14_89 OBJECT-TYPE
SYNTAX INTEGER
MAX-ACCESS read-write
STATUS current
DESCRIPTION
"Data value."
::= { dataArray14 89 }

dataValue14_90 OBJECT-TYPE
SYNTAX INTEGER
MAX-ACCESS read-write
STATUS current
DESCRIPTION
"Data value."
::= { dataArray14 90 }

dataValue14_91 OBJECT-TYPE
SYNTAX INTEGER
MAX-ACCESS read-write
STATUS current
DESCRIPTION
"Data value."
::= { dataArray14 91 }

dataValue14_92 OBJECT-TYPE
SYNTAX INTEGER
MAX-ACCESS read-write
STATUS current
DESCRIPTION
"Data value."
::= { dataArray14 92 }

dataValue14_93 OBJECT-TYPE
SYNTAX INTEGER
MAX-ACCESS read-write
STATUS current
DESCRIPTION
"Data value."
::= { dataArray14 93 }

dataValue14_94 OBJECT-TYPE
SYNTAX INTEGER
MAX-ACCESS read-write
STATUS current
DESCRIPTION
"Data value."
::= { dataArray14 94 }

dataValue14_95 OBJECT-TYPE
SYNTAX INTEGER
MAX-ACCESS read-write
STATUS current
DESCRIPTION
"Data value."
::= { dataArray14 95 }

dataValue14_96 OBJECT-TYPE
SYNTAX INTEGER
MAX-ACCESS read-write
STATUS current
DESCRIPTION
"Data value."
::= { dataArray14 96 }

dataValue14_97 OBJECT-TYPE
SYNTAX INTEGER
MAX-ACCESS read-write
STATUS current
DESCRIPTION
"Data value."
::= { dataArray14 97 }

dataValue14_98 OBJECT-TYPE
SYNTAX INTEGER
MAX-ACCESS read-write
STATUS current
DESCRIPTION
"Data value."
::= { dataArray14 98 }

dataValue14_99 OBJECT-TYPE
SYNTAX INTEGER
MAX-ACCESS read-write
STATUS current
DESCRIPTION
"Data value."
::= { dataArray14 99 }

dataValue14_100 OBJECT-TYPE
SYNTAX INTEGER
MAX-ACCESS read-write
STATUS current
DESCRIPTION
"Data value."
::= { dataArray14 100 }

dataValue14_101 OBJECT-TYPE
SYNTAX INTEGER
MAX-ACCESS read-write
STATUS current
DESCRIPTION
"Data value."
::= { dataArray14 101 }

dataValue14_102 OBJECT-TYPE
SYNTAX INTEGER
MAX-ACCESS read-write
STATUS current
DESCRIPTION
"Data value."
::= { dataArray14 102 }

dataValue14_103 OBJECT-TYPE
SYNTAX INTEGER
MAX-ACCESS read-write
STATUS current
DESCRIPTION
"Data value."
::= { dataArray14 103 }

dataValue14_104 OBJECT-TYPE
SYNTAX INTEGER
MAX-ACCESS read-write
STATUS current
DESCRIPTION
"Data value."
::= { dataArray14 104 }

dataValue14_105 OBJECT-TYPE
SYNTAX INTEGER
MAX-ACCESS read-write
STATUS current
DESCRIPTION
"Data value."
::= { dataArray14 105 }

dataValue14_106 OBJECT-TYPE
SYNTAX INTEGER
MAX-ACCESS read-write
STATUS current
DESCRIPTION
"Data value."
::= { dataArray14 106 }

dataValue14_107 OBJECT-TYPE
SYNTAX INTEGER
MAX-ACCESS read-write
STATUS current
DESCRIPTION
"Data value."
::= { dataArray14 107 }

dataValue14_108 OBJECT-TYPE
SYNTAX INTEGER
MAX-ACCESS read-write
STATUS current
DESCRIPTION
"Data value."
::= { dataArray14 108 }

dataValue14_109 OBJECT-TYPE
SYNTAX INTEGER
MAX-ACCESS read-write
STATUS current
DESCRIPTION
"Data value."
::= { dataArray14 109 }

dataValue14_110 OBJECT-TYPE
SYNTAX INTEGER
MAX-ACCESS read-write
STATUS current
DESCRIPTION
"Data value."
::= { dataArray14 110 }

dataValue14_111 OBJECT-TYPE
SYNTAX INTEGER
MAX-ACCESS read-write
STATUS current
DESCRIPTION
"Data value."
::= { dataArray14 111 }

dataValue14_112 OBJECT-TYPE
SYNTAX INTEGER
MAX-ACCESS read-write
STATUS current
DESCRIPTION
"Data value."
::= { dataArray14 112 }

dataValue14_113 OBJECT-TYPE
SYNTAX INTEGER
MAX-ACCESS read-write
STATUS current
DESCRIPTION
"Data value."
::= { dataArray14 113 }

dataValue14_114 OBJECT-TYPE
SYNTAX INTEGER
MAX-ACCESS read-write
STATUS current
DESCRIPTION
"Data value."
::= { dataArray14 114 }

dataValue14_115 OBJECT-TYPE
SYNTAX INTEGER
MAX-ACCESS read-write
STATUS current
DESCRIPTION
"Data value."
::= { dataArray14 115 }

dataValue14_116 OBJECT-TYPE
SYNTAX INTEGER
MAX-ACCESS read-write
STATUS current
DESCRIPTION
"Data value."
::= { dataArray14 116 }

dataValue14_117 OBJECT-TYPE
SYNTAX INTEGER
MAX-ACCESS read-write
STATUS current
DESCRIPTION
"Data value."
::= { dataArray14 117 }

dataValue14_118 OBJECT-TYPE
SYNTAX INTEGER
MAX-ACCESS read-write
STATUS current
DESCRIPTION
"Data value."
::= { dataArray14 118 }

dataValue14_119 OBJECT-TYPE
SYNTAX INTEGER
MAX-ACCESS read-write
STATUS current
DESCRIPTION
"Data value."
::= { dataArray14 119 }

dataValue14_120 OBJECT-TYPE
SYNTAX INTEGER
MAX-ACCESS read-write
STATUS current
DESCRIPTION
"Data value."
::= { dataArray14 120 }

dataValue14_121 OBJECT-TYPE
SYNTAX INTEGER
MAX-ACCESS read-write
STATUS current
DESCRIPTION
"Data value."
::= { dataArray14 121 }

dataValue14_122 OBJECT-TYPE
SYNTAX INTEGER
MAX-ACCESS read-write
STATUS current
DESCRIPTION
"Data value."
::= { dataArray14 122 }

dataValue14_123 OBJECT-TYPE
SYNTAX INTEGER
MAX-ACCESS read-write
STATUS current
DESCRIPTION
"Data value."
::= { dataArray14 123 }

dataValue14_124 OBJECT-TYPE
SYNTAX INTEGER
MAX-ACCESS read-write
STATUS current
DESCRIPTION
"Data value."
::= { dataArray14 124 }

dataValue14_125 OBJECT-TYPE
SYNTAX INTEGER
MAX-ACCESS read-write
STATUS current
DESCRIPTION
"Data value."
::= { dataArray14 125 }

dataValue14_126 OBJECT-TYPE
SYNTAX INTEGER
MAX-ACCESS read-write
STATUS current
DESCRIPTION
"Data value."
::= { dataArray14 126 }

dataValue14_127 OBJECT-TYPE
SYNTAX INTEGER
MAX-ACCESS read-write
STATUS current
DESCRIPTION
"Data value."
::= { dataArray14 127 }

dataValue14_128 OBJECT-TYPE
SYNTAX INTEGER
MAX-ACCESS read-write
STATUS current
DESCRIPTION
"Data value."
::= { dataArray14 128 }

dataValue14_129 OBJECT-TYPE
SYNTAX INTEGER
MAX-ACCESS read-write
STATUS current
DESCRIPTION
"Data value."
::= { dataArray14 129 }

dataValue14_130 OBJECT-TYPE
SYNTAX INTEGER
MAX-ACCESS read-write
STATUS current
DESCRIPTION
"Data value."
::= { dataArray14 130 }

dataValue14_131 OBJECT-TYPE
SYNTAX INTEGER
MAX-ACCESS read-write
STATUS current
DESCRIPTION
"Data value."
::= { dataArray14 131 }

dataValue14_132 OBJECT-TYPE
SYNTAX INTEGER
MAX-ACCESS read-write
STATUS current
DESCRIPTION
"Data value."
::= { dataArray14 132 }

dataValue14_133 OBJECT-TYPE
SYNTAX INTEGER
MAX-ACCESS read-write
STATUS current
DESCRIPTION
"Data value."
::= { dataArray14 133 }

dataValue14_134 OBJECT-TYPE
SYNTAX INTEGER
MAX-ACCESS read-write
STATUS current
DESCRIPTION
"Data value."
::= { dataArray14 134 }

dataValue14_135 OBJECT-TYPE
SYNTAX INTEGER
MAX-ACCESS read-write
STATUS current
DESCRIPTION
"Data value."
::= { dataArray14 135 }

dataValue14_136 OBJECT-TYPE
SYNTAX INTEGER
MAX-ACCESS read-write
STATUS current
DESCRIPTION
"Data value."
::= { dataArray14 136 }

dataValue14_137 OBJECT-TYPE
SYNTAX INTEGER
MAX-ACCESS read-write
STATUS current
DESCRIPTION
"Data value."
::= { dataArray14 137 }

dataValue14_138 OBJECT-TYPE
SYNTAX INTEGER
MAX-ACCESS read-write
STATUS current
DESCRIPTION
"Data value."
::= { dataArray14 138 }

dataValue14_139 OBJECT-TYPE
SYNTAX INTEGER
MAX-ACCESS read-write
STATUS current
DESCRIPTION
"Data value."
::= { dataArray14 139 }

dataValue14_140 OBJECT-TYPE
SYNTAX INTEGER
MAX-ACCESS read-write
STATUS current
DESCRIPTION
"Data value."
::= { dataArray14 140 }

dataValue14_141 OBJECT-TYPE
SYNTAX INTEGER
MAX-ACCESS read-write
STATUS current
DESCRIPTION
"Data value."
::= { dataArray14 141 }

dataValue14_142 OBJECT-TYPE
SYNTAX INTEGER
MAX-ACCESS read-write
STATUS current
DESCRIPTION
"Data value."
::= { dataArray14 142 }

dataValue14_143 OBJECT-TYPE
SYNTAX INTEGER
MAX-ACCESS read-write
STATUS current
DESCRIPTION
"Data value."
::= { dataArray14 143 }

dataValue14_144 OBJECT-TYPE
SYNTAX INTEGER
MAX-ACCESS read-write
STATUS current
DESCRIPTION
"Data value."
::= { dataArray14 144 }

dataValue14_145 OBJECT-TYPE
SYNTAX INTEGER
MAX-ACCESS read-write
STATUS current
DESCRIPTION
"Data value."
::= { dataArray14 145 }

dataValue14_146 OBJECT-TYPE
SYNTAX INTEGER
MAX-ACCESS read-write
STATUS current
DESCRIPTION
"Data value."
::= { dataArray14 146 }

dataValue14_147 OBJECT-TYPE
SYNTAX INTEGER
MAX-ACCESS read-write
STATUS current
DESCRIPTION
"Data value."
::= { dataArray14 147 }

dataValue14_148 OBJECT-TYPE
SYNTAX INTEGER
MAX-ACCESS read-write
STATUS current
DESCRIPTION
"Data value."
::= { dataArray14 148 }

dataValue14_149 OBJECT-TYPE
SYNTAX INTEGER
MAX-ACCESS read-write
STATUS current
DESCRIPTION
"Data value."
::= { dataArray14 149 }

dataValue14_150 OBJECT-TYPE
SYNTAX INTEGER
MAX-ACCESS read-write
STATUS current
DESCRIPTION
"Data value."
::= { dataArray14 150 }

dataValue14_151 OBJECT-TYPE
SYNTAX INTEGER
MAX-ACCESS read-write
STATUS current
DESCRIPTION
"Data value."
::= { dataArray14 151 }

dataValue14_152 OBJECT-TYPE
SYNTAX INTEGER
MAX-ACCESS read-write
STATUS current
DESCRIPTION
"Data value."
::= { dataArray14 152 }

dataValue14_153 OBJECT-TYPE
SYNTAX INTEGER
MAX-ACCESS read-write
STATUS current
DESCRIPTION
"Data value."
::= { dataArray14 153 }

dataValue14_154 OBJECT-TYPE
SYNTAX INTEGER
MAX-ACCESS read-write
STATUS current
DESCRIPTION
"Data value."
::= { dataArray14 154 }

dataValue14_155 OBJECT-TYPE
SYNTAX INTEGER
MAX-ACCESS read-write
STATUS current
DESCRIPTION
"Data value."
::= { dataArray14 155 }

dataValue14_156 OBJECT-TYPE
SYNTAX INTEGER
MAX-ACCESS read-write
STATUS current
DESCRIPTION
"Data value."
::= { dataArray14 156 }

dataValue14_157 OBJECT-TYPE
SYNTAX INTEGER
MAX-ACCESS read-write
STATUS current
DESCRIPTION
"Data value."
::= { dataArray14 157 }

dataValue14_158 OBJECT-TYPE
SYNTAX INTEGER
MAX-ACCESS read-write
STATUS current
DESCRIPTION
"Data value."
::= { dataArray14 158 }

dataValue14_159 OBJECT-TYPE
SYNTAX INTEGER
MAX-ACCESS read-write
STATUS current
DESCRIPTION
"Data value."
::= { dataArray14 159 }

dataValue14_160 OBJECT-TYPE
SYNTAX INTEGER
MAX-ACCESS read-write
STATUS current
DESCRIPTION
"Data value."
::= { dataArray14 160 }

dataValue14_161 OBJECT-TYPE
SYNTAX INTEGER
MAX-ACCESS read-write
STATUS current
DESCRIPTION
"Data value."
::= { dataArray14 161 }

dataValue14_162 OBJECT-TYPE
SYNTAX INTEGER
MAX-ACCESS read-write
STATUS current
DESCRIPTION
"Data value."
::= { dataArray14 162 }

dataValue14_163 OBJECT-TYPE
SYNTAX INTEGER
MAX-ACCESS read-write
STATUS current
DESCRIPTION
"Data value."
::= { dataArray14 163 }

dataValue14_164 OBJECT-TYPE
SYNTAX INTEGER
MAX-ACCESS read-write
STATUS current
DESCRIPTION
"Data value."
::= { dataArray14 164 }

dataValue14_165 OBJECT-TYPE
SYNTAX INTEGER
MAX-ACCESS read-write
STATUS current
DESCRIPTION
"Data value."
::= { dataArray14 165 }

dataValue14_166 OBJECT-TYPE
SYNTAX INTEGER
MAX-ACCESS read-write
STATUS current
DESCRIPTION
"Data value."
::= { dataArray14 166 }

dataValue14_167 OBJECT-TYPE
SYNTAX INTEGER
MAX-ACCESS read-write
STATUS current
DESCRIPTION
"Data value."
::= { dataArray14 167 }

dataValue14_168 OBJECT-TYPE
SYNTAX INTEGER
MAX-ACCESS read-write
STATUS current
DESCRIPTION
"Data value."
::= { dataArray14 168 }

dataValue14_169 OBJECT-TYPE
SYNTAX INTEGER
MAX-ACCESS read-write
STATUS current
DESCRIPTION
"Data value."
::= { dataArray14 169 }

dataValue14_170 OBJECT-TYPE
SYNTAX INTEGER
MAX-ACCESS read-write
STATUS current
DESCRIPTION
"Data value."
::= { dataArray14 170 }

dataValue14_171 OBJECT-TYPE
SYNTAX INTEGER
MAX-ACCESS read-write
STATUS current
DESCRIPTION
"Data value."
::= { dataArray14 171 }

dataValue14_172 OBJECT-TYPE
SYNTAX INTEGER
MAX-ACCESS read-write
STATUS current
DESCRIPTION
"Data value."
::= { dataArray14 172 }

dataValue14_173 OBJECT-TYPE
SYNTAX INTEGER
MAX-ACCESS read-write
STATUS current
DESCRIPTION
"Data value."
::= { dataArray14 173 }

dataValue14_174 OBJECT-TYPE
SYNTAX INTEGER
MAX-ACCESS read-write
STATUS current
DESCRIPTION
"Data value."
::= { dataArray14 174 }

dataValue14_175 OBJECT-TYPE
SYNTAX INTEGER
MAX-ACCESS read-write
STATUS current
DESCRIPTION
"Data value."
::= { dataArray14 175 }

dataValue14_176 OBJECT-TYPE
SYNTAX INTEGER
MAX-ACCESS read-write
STATUS current
DESCRIPTION
"Data value."
::= { dataArray14 176 }

dataValue14_177 OBJECT-TYPE
SYNTAX INTEGER
MAX-ACCESS read-write
STATUS current
DESCRIPTION
"Data value."
::= { dataArray14 177 }

dataValue14_178 OBJECT-TYPE
SYNTAX INTEGER
MAX-ACCESS read-write
STATUS current
DESCRIPTION
"Data value."
::= { dataArray14 178 }

dataValue14_179 OBJECT-TYPE
SYNTAX INTEGER
MAX-ACCESS read-write
STATUS current
DESCRIPTION
"Data value."
::= { dataArray14 179 }

dataValue14_180 OBJECT-TYPE
SYNTAX INTEGER
MAX-ACCESS read-write
STATUS current
DESCRIPTION
"Data value."
::= { dataArray14 180 }

dataValue14_181 OBJECT-TYPE
SYNTAX INTEGER
MAX-ACCESS read-write
STATUS current
DESCRIPTION
"Data value."
::= { dataArray14 181 }

dataValue14_182 OBJECT-TYPE
SYNTAX INTEGER
MAX-ACCESS read-write
STATUS current
DESCRIPTION
"Data value."
::= { dataArray14 182 }

dataValue14_183 OBJECT-TYPE
SYNTAX INTEGER
MAX-ACCESS read-write
STATUS current
DESCRIPTION
"Data value."
::= { dataArray14 183 }

dataValue14_184 OBJECT-TYPE
SYNTAX INTEGER
MAX-ACCESS read-write
STATUS current
DESCRIPTION
"Data value."
::= { dataArray14 184 }

dataValue14_185 OBJECT-TYPE
SYNTAX INTEGER
MAX-ACCESS read-write
STATUS current
DESCRIPTION
"Data value."
::= { dataArray14 185 }

dataValue14_186 OBJECT-TYPE
SYNTAX INTEGER
MAX-ACCESS read-write
STATUS current
DESCRIPTION
"Data value."
::= { dataArray14 186 }

dataValue14_187 OBJECT-TYPE
SYNTAX INTEGER
MAX-ACCESS read-write
STATUS current
DESCRIPTION
"Data value."
::= { dataArray14 187 }

dataValue14_188 OBJECT-TYPE
SYNTAX INTEGER
MAX-ACCESS read-write
STATUS current
DESCRIPTION
"Data value."
::= { dataArray14 188 }

dataValue14_189 OBJECT-TYPE
SYNTAX INTEGER
MAX-ACCESS read-write
STATUS current
DESCRIPTION
"Data value."
::= { dataArray14 189 }

dataValue14_190 OBJECT-TYPE
SYNTAX INTEGER
MAX-ACCESS read-write
STATUS current
DESCRIPTION
"Data value."
::= { dataArray14 190 }

dataValue14_191 OBJECT-TYPE
SYNTAX INTEGER
MAX-ACCESS read-write
STATUS current
DESCRIPTION
"Data value."
::= { dataArray14 191 }

dataValue14_192 OBJECT-TYPE
SYNTAX INTEGER
MAX-ACCESS read-write
STATUS current
DESCRIPTION
"Data value."
::= { dataArray14 192 }

dataValue14_193 OBJECT-TYPE
SYNTAX INTEGER
MAX-ACCESS read-write
STATUS current
DESCRIPTION
"Data value."
::= { dataArray14 193 }

dataValue14_194 OBJECT-TYPE
SYNTAX INTEGER
MAX-ACCESS read-write
STATUS current
DESCRIPTION
"Data value."
::= { dataArray14 194 }

dataValue14_195 OBJECT-TYPE
SYNTAX INTEGER
MAX-ACCESS read-write
STATUS current
DESCRIPTION
"Data value."
::= { dataArray14 195 }

dataValue14_196 OBJECT-TYPE
SYNTAX INTEGER
MAX-ACCESS read-write
STATUS current
DESCRIPTION
"Data value."
::= { dataArray14 196 }

dataValue14_197 OBJECT-TYPE
SYNTAX INTEGER
MAX-ACCESS read-write
STATUS current
DESCRIPTION
"Data value."
::= { dataArray14 197 }

dataValue14_198 OBJECT-TYPE
SYNTAX INTEGER
MAX-ACCESS read-write
STATUS current
DESCRIPTION
"Data value."
::= { dataArray14 198 }

dataValue14_199 OBJECT-TYPE
SYNTAX INTEGER
MAX-ACCESS read-write
STATUS current
DESCRIPTION
"Data value."
::= { dataArray14 199 }

dataValue14_200 OBJECT-TYPE
SYNTAX INTEGER
MAX-ACCESS read-write
STATUS current
DESCRIPTION
"Data value."
::= { dataArray14 200 }

dataValue14_201 OBJECT-TYPE
SYNTAX INTEGER
MAX-ACCESS read-write
STATUS current
DESCRIPTION
"Data value."
::= { dataArray14 201 }

dataValue14_202 OBJECT-TYPE
SYNTAX INTEGER
MAX-ACCESS read-write
STATUS current
DESCRIPTION
"Data value."
::= { dataArray14 202 }

dataValue14_203 OBJECT-TYPE
SYNTAX INTEGER
MAX-ACCESS read-write
STATUS current
DESCRIPTION
"Data value."
::= { dataArray14 203 }

dataValue14_204 OBJECT-TYPE
SYNTAX INTEGER
MAX-ACCESS read-write
STATUS current
DESCRIPTION
"Data value."
::= { dataArray14 204 }

dataValue14_205 OBJECT-TYPE
SYNTAX INTEGER
MAX-ACCESS read-write
STATUS current
DESCRIPTION
"Data value."
::= { dataArray14 205 }

dataValue14_206 OBJECT-TYPE
SYNTAX INTEGER
MAX-ACCESS read-write
STATUS current
DESCRIPTION
"Data value."
::= { dataArray14 206 }

dataValue14_207 OBJECT-TYPE
SYNTAX INTEGER
MAX-ACCESS read-write
STATUS current
DESCRIPTION
"Data value."
::= { dataArray14 207 }

dataValue14_208 OBJECT-TYPE
SYNTAX INTEGER
MAX-ACCESS read-write
STATUS current
DESCRIPTION
"Data value."
::= { dataArray14 208 }

dataValue14_209 OBJECT-TYPE
SYNTAX INTEGER
MAX-ACCESS read-write
STATUS current
DESCRIPTION
"Data value."
::= { dataArray14 209 }

dataValue14_210 OBJECT-TYPE
SYNTAX INTEGER
MAX-ACCESS read-write
STATUS current
DESCRIPTION
"Data value."
::= { dataArray14 210 }

dataValue14_211 OBJECT-TYPE
SYNTAX INTEGER
MAX-ACCESS read-write
STATUS current
DESCRIPTION
"Data value."
::= { dataArray14 211 }

dataValue14_212 OBJECT-TYPE
SYNTAX INTEGER
MAX-ACCESS read-write
STATUS current
DESCRIPTION
"Data value."
::= { dataArray14 212 }

dataValue14_213 OBJECT-TYPE
SYNTAX INTEGER
MAX-ACCESS read-write
STATUS current
DESCRIPTION
"Data value."
::= { dataArray14 213 }

dataValue14_214 OBJECT-TYPE
SYNTAX INTEGER
MAX-ACCESS read-write
STATUS current
DESCRIPTION
"Data value."
::= { dataArray14 214 }

dataValue14_215 OBJECT-TYPE
SYNTAX INTEGER
MAX-ACCESS read-write
STATUS current
DESCRIPTION
"Data value."
::= { dataArray14 215 }

dataValue14_216 OBJECT-TYPE
SYNTAX INTEGER
MAX-ACCESS read-write
STATUS current
DESCRIPTION
"Data value."
::= { dataArray14 216 }

dataValue14_217 OBJECT-TYPE
SYNTAX INTEGER
MAX-ACCESS read-write
STATUS current
DESCRIPTION
"Data value."
::= { dataArray14 217 }

dataValue14_218 OBJECT-TYPE
SYNTAX INTEGER
MAX-ACCESS read-write
STATUS current
DESCRIPTION
"Data value."
::= { dataArray14 218 }

dataValue14_219 OBJECT-TYPE
SYNTAX INTEGER
MAX-ACCESS read-write
STATUS current
DESCRIPTION
"Data value."
::= { dataArray14 219 }

dataValue14_220 OBJECT-TYPE
SYNTAX INTEGER
MAX-ACCESS read-write
STATUS current
DESCRIPTION
"Data value."
::= { dataArray14 220 }

dataValue14_221 OBJECT-TYPE
SYNTAX INTEGER
MAX-ACCESS read-write
STATUS current
DESCRIPTION
"Data value."
::= { dataArray14 221 }

dataValue14_222 OBJECT-TYPE
SYNTAX INTEGER
MAX-ACCESS read-write
STATUS current
DESCRIPTION
"Data value."
::= { dataArray14 222 }

dataValue14_223 OBJECT-TYPE
SYNTAX INTEGER
MAX-ACCESS read-write
STATUS current
DESCRIPTION
"Data value."
::= { dataArray14 223 }

dataValue14_224 OBJECT-TYPE
SYNTAX INTEGER
MAX-ACCESS read-write
STATUS current
DESCRIPTION
"Data value."
::= { dataArray14 224 }

dataValue14_225 OBJECT-TYPE
SYNTAX INTEGER
MAX-ACCESS read-write
STATUS current
DESCRIPTION
"Data value."
::= { dataArray14 225 }

dataValue14_226 OBJECT-TYPE
SYNTAX INTEGER
MAX-ACCESS read-write
STATUS current
DESCRIPTION
"Data value."
::= { dataArray14 226 }

dataValue14_227 OBJECT-TYPE
SYNTAX INTEGER
MAX-ACCESS read-write
STATUS current
DESCRIPTION
"Data value."
::= { dataArray14 227 }

dataValue14_228 OBJECT-TYPE
SYNTAX INTEGER
MAX-ACCESS read-write
STATUS current
DESCRIPTION
"Data value."
::= { dataArray14 228 }

dataValue14_229 OBJECT-TYPE
SYNTAX INTEGER
MAX-ACCESS read-write
STATUS current
DESCRIPTION
"Data value."
::= { dataArray14 229 }

dataValue14_230 OBJECT-TYPE
SYNTAX INTEGER
MAX-ACCESS read-write
STATUS current
DESCRIPTION
"Data value."
::= { dataArray14 230 }

dataValue14_231 OBJECT-TYPE
SYNTAX INTEGER
MAX-ACCESS read-write
STATUS current
DESCRIPTION
"Data value."
::= { dataArray14 231 }

dataValue14_232 OBJECT-TYPE
SYNTAX INTEGER
MAX-ACCESS read-write
STATUS current
DESCRIPTION
"Data value."
::= { dataArray14 232 }

dataValue14_233 OBJECT-TYPE
SYNTAX INTEGER
MAX-ACCESS read-write
STATUS current
DESCRIPTION
"Data value."
::= { dataArray14 233 }

dataValue14_234 OBJECT-TYPE
SYNTAX INTEGER
MAX-ACCESS read-write
STATUS current
DESCRIPTION
"Data value."
::= { dataArray14 234 }

dataValue14_235 OBJECT-TYPE
SYNTAX INTEGER
MAX-ACCESS read-write
STATUS current
DESCRIPTION
"Data value."
::= { dataArray14 235 }

dataValue14_236 OBJECT-TYPE
SYNTAX INTEGER
MAX-ACCESS read-write
STATUS current
DESCRIPTION
"Data value."
::= { dataArray14 236 }

dataValue14_237 OBJECT-TYPE
SYNTAX INTEGER
MAX-ACCESS read-write
STATUS current
DESCRIPTION
"Data value."
::= { dataArray14 237 }

dataValue14_238 OBJECT-TYPE
SYNTAX INTEGER
MAX-ACCESS read-write
STATUS current
DESCRIPTION
"Data value."
::= { dataArray14 238 }

dataValue14_239 OBJECT-TYPE
SYNTAX INTEGER
MAX-ACCESS read-write
STATUS current
DESCRIPTION
"Data value."
::= { dataArray14 239 }

dataValue14_240 OBJECT-TYPE
SYNTAX INTEGER
MAX-ACCESS read-write
STATUS current
DESCRIPTION
"Data value."
::= { dataArray14 240 }

dataValue14_241 OBJECT-TYPE
SYNTAX INTEGER
MAX-ACCESS read-write
STATUS current
DESCRIPTION
"Data value."
::= { dataArray14 241 }

dataValue14_242 OBJECT-TYPE
SYNTAX INTEGER
MAX-ACCESS read-write
STATUS current
DESCRIPTION
"Data value."
::= { dataArray14 242 }

dataValue14_243 OBJECT-TYPE
SYNTAX INTEGER
MAX-ACCESS read-write
STATUS current
DESCRIPTION
"Data value."
::= { dataArray14 243 }

dataValue14_244 OBJECT-TYPE
SYNTAX INTEGER
MAX-ACCESS read-write
STATUS current
DESCRIPTION
"Data value."
::= { dataArray14 244 }

dataValue14_245 OBJECT-TYPE
SYNTAX INTEGER
MAX-ACCESS read-write
STATUS current
DESCRIPTION
"Data value."
::= { dataArray14 245 }

dataValue14_246 OBJECT-TYPE
SYNTAX INTEGER
MAX-ACCESS read-write
STATUS current
DESCRIPTION
"Data value."
::= { dataArray14 246 }

dataValue14_247 OBJECT-TYPE
SYNTAX INTEGER
MAX-ACCESS read-write
STATUS current
DESCRIPTION
"Data value."
::= { dataArray14 247 }

dataValue14_248 OBJECT-TYPE
SYNTAX INTEGER
MAX-ACCESS read-write
STATUS current
DESCRIPTION
"Data value."
::= { dataArray14 248 }

dataValue14_249 OBJECT-TYPE
SYNTAX INTEGER
MAX-ACCESS read-write
STATUS current
DESCRIPTION
"Data value."
::= { dataArray14 249 }

dataValue14_250 OBJECT-TYPE
SYNTAX INTEGER
MAX-ACCESS read-write
STATUS current
DESCRIPTION
"Data value."
::= { dataArray14 250 }

dataValue14_251 OBJECT-TYPE
SYNTAX INTEGER
MAX-ACCESS read-write
STATUS current
DESCRIPTION
"Data value."
::= { dataArray14 251 }

dataValue14_252 OBJECT-TYPE
SYNTAX INTEGER
MAX-ACCESS read-write
STATUS current
DESCRIPTION
"Data value."
::= { dataArray14 252 }

dataValue14_253 OBJECT-TYPE
SYNTAX INTEGER
MAX-ACCESS read-write
STATUS current
DESCRIPTION
"Data value."
::= { dataArray14 253 }

dataValue14_254 OBJECT-TYPE
SYNTAX INTEGER
MAX-ACCESS read-write
STATUS current
DESCRIPTION
"Data value."
::= { dataArray14 254 }

dataValue14_255 OBJECT-TYPE
SYNTAX INTEGER
MAX-ACCESS read-write
STATUS current
DESCRIPTION
"Data value."
::= { dataArray14 255 }

dataValue14_256 OBJECT-TYPE
SYNTAX INTEGER
MAX-ACCESS read-write
STATUS current
DESCRIPTION
"Data value."
::= { dataArray14 256 }

dataValue14_257 OBJECT-TYPE
SYNTAX INTEGER
MAX-ACCESS read-write
STATUS current
DESCRIPTION
"Data value."
::= { dataArray14 257 }

dataValue14_258 OBJECT-TYPE
SYNTAX INTEGER
MAX-ACCESS read-write
STATUS current
DESCRIPTION
"Data value."
::= { dataArray14 258 }

dataValue14_259 OBJECT-TYPE
SYNTAX INTEGER
MAX-ACCESS read-write
STATUS current
DESCRIPTION
"Data value."
::= { dataArray14 259 }

dataValue14_260 OBJECT-TYPE
SYNTAX INTEGER
MAX-ACCESS read-write
STATUS current
DESCRIPTION
"Data value."
::= { dataArray14 260 }

dataValue14_261 OBJECT-TYPE
SYNTAX INTEGER
MAX-ACCESS read-write
STATUS current
DESCRIPTION
"Data value."
::= { dataArray14 261 }

dataValue14_262 OBJECT-TYPE
SYNTAX INTEGER
MAX-ACCESS read-write
STATUS current
DESCRIPTION
"Data value."
::= { dataArray14 262 }

dataValue14_263 OBJECT-TYPE
SYNTAX INTEGER
MAX-ACCESS read-write
STATUS current
DESCRIPTION
"Data value."
::= { dataArray14 263 }

dataValue14_264 OBJECT-TYPE
SYNTAX INTEGER
MAX-ACCESS read-write
STATUS current
DESCRIPTION
"Data value."
::= { dataArray14 264 }

dataValue14_265 OBJECT-TYPE
SYNTAX INTEGER
MAX-ACCESS read-write
STATUS current
DESCRIPTION
"Data value."
::= { dataArray14 265 }

dataValue14_266 OBJECT-TYPE
SYNTAX INTEGER
MAX-ACCESS read-write
STATUS current
DESCRIPTION
"Data value."
::= { dataArray14 266 }

dataValue14_267 OBJECT-TYPE
SYNTAX INTEGER
MAX-ACCESS read-write
STATUS current
DESCRIPTION
"Data value."
::= { dataArray14 267 }

dataValue14_268 OBJECT-TYPE
SYNTAX INTEGER
MAX-ACCESS read-write
STATUS current
DESCRIPTION
"Data value."
::= { dataArray14 268 }

dataValue14_269 OBJECT-TYPE
SYNTAX INTEGER
MAX-ACCESS read-write
STATUS current
DESCRIPTION
"Data value."
::= { dataArray14 269 }

dataValue14_270 OBJECT-TYPE
SYNTAX INTEGER
MAX-ACCESS read-write
STATUS current
DESCRIPTION
"Data value."
::= { dataArray14 270 }

dataValue14_271 OBJECT-TYPE
SYNTAX INTEGER
MAX-ACCESS read-write
STATUS current
DESCRIPTION
"Data value."
::= { dataArray14 271 }

dataValue14_272 OBJECT-TYPE
SYNTAX INTEGER
MAX-ACCESS read-write
STATUS current
DESCRIPTION
"Data value."
::= { dataArray14 272 }

dataValue14_273 OBJECT-TYPE
SYNTAX INTEGER
MAX-ACCESS read-write
STATUS current
DESCRIPTION
"Data value."
::= { dataArray14 273 }

dataValue14_274 OBJECT-TYPE
SYNTAX INTEGER
MAX-ACCESS read-write
STATUS current
DESCRIPTION
"Data value."
::= { dataArray14 274 }

dataValue14_275 OBJECT-TYPE
SYNTAX INTEGER
MAX-ACCESS read-write
STATUS current
DESCRIPTION
"Data value."
::= { dataArray14 275 }

dataValue14_276 OBJECT-TYPE
SYNTAX INTEGER
MAX-ACCESS read-write
STATUS current
DESCRIPTION
"Data value."
::= { dataArray14 276 }

dataValue14_277 OBJECT-TYPE
SYNTAX INTEGER
MAX-ACCESS read-write
STATUS current
DESCRIPTION
"Data value."
::= { dataArray14 277 }

dataValue14_278 OBJECT-TYPE
SYNTAX INTEGER
MAX-ACCESS read-write
STATUS current
DESCRIPTION
"Data value."
::= { dataArray14 278 }

dataValue14_279 OBJECT-TYPE
SYNTAX INTEGER
MAX-ACCESS read-write
STATUS current
DESCRIPTION
"Data value."
::= { dataArray14 279 }

dataValue14_280 OBJECT-TYPE
SYNTAX INTEGER
MAX-ACCESS read-write
STATUS current
DESCRIPTION
"Data value."
::= { dataArray14 280 }

dataValue14_281 OBJECT-TYPE
SYNTAX INTEGER
MAX-ACCESS read-write
STATUS current
DESCRIPTION
"Data value."
::= { dataArray14 281 }

dataValue14_282 OBJECT-TYPE
SYNTAX INTEGER
MAX-ACCESS read-write
STATUS current
DESCRIPTION
"Data value."
::= { dataArray14 282 }

dataValue14_283 OBJECT-TYPE
SYNTAX INTEGER
MAX-ACCESS read-write
STATUS current
DESCRIPTION
"Data value."
::= { dataArray14 283 }

dataValue14_284 OBJECT-TYPE
SYNTAX INTEGER
MAX-ACCESS read-write
STATUS current
DESCRIPTION
"Data value."
::= { dataArray14 284 }

dataValue14_285 OBJECT-TYPE
SYNTAX INTEGER
MAX-ACCESS read-write
STATUS current
DESCRIPTION
"Data value."
::= { dataArray14 285 }

dataValue14_286 OBJECT-TYPE
SYNTAX INTEGER
MAX-ACCESS read-write
STATUS current
DESCRIPTION
"Data value."
::= { dataArray14 286 }

dataValue14_287 OBJECT-TYPE
SYNTAX INTEGER
MAX-ACCESS read-write
STATUS current
DESCRIPTION
"Data value."
::= { dataArray14 287 }

dataValue14_288 OBJECT-TYPE
SYNTAX INTEGER
MAX-ACCESS read-write
STATUS current
DESCRIPTION
"Data value."
::= { dataArray14 288 }

dataValue14_289 OBJECT-TYPE
SYNTAX INTEGER
MAX-ACCESS read-write
STATUS current
DESCRIPTION
"Data value."
::= { dataArray14 289 }

dataValue14_290 OBJECT-TYPE
SYNTAX INTEGER
MAX-ACCESS read-write
STATUS current
DESCRIPTION
"Data value."
::= { dataArray14 290 }

dataValue14_291 OBJECT-TYPE
SYNTAX INTEGER
MAX-ACCESS read-write
STATUS current
DESCRIPTION
"Data value."
::= { dataArray14 291 }

dataValue14_292 OBJECT-TYPE
SYNTAX INTEGER
MAX-ACCESS read-write
STATUS current
DESCRIPTION
"Data value."
::= { dataArray14 292 }

dataValue14_293 OBJECT-TYPE
SYNTAX INTEGER
MAX-ACCESS read-write
STATUS current
DESCRIPTION
"Data value."
::= { dataArray14 293 }

dataValue14_294 OBJECT-TYPE
SYNTAX INTEGER
MAX-ACCESS read-write
STATUS current
DESCRIPTION
"Data value."
::= { dataArray14 294 }

dataValue14_295 OBJECT-TYPE
SYNTAX INTEGER
MAX-ACCESS read-write
STATUS current
DESCRIPTION
"Data value."
::= { dataArray14 295 }

dataValue14_296 OBJECT-TYPE
SYNTAX INTEGER
MAX-ACCESS read-write
STATUS current
DESCRIPTION
"Data value."
::= { dataArray14 296 }

dataValue14_297 OBJECT-TYPE
SYNTAX INTEGER
MAX-ACCESS read-write
STATUS current
DESCRIPTION
"Data value."
::= { dataArray14 297 }

dataValue14_298 OBJECT-TYPE
SYNTAX INTEGER
MAX-ACCESS read-write
STATUS current
DESCRIPTION
"Data value."
::= { dataArray14 298 }

dataValue14_299 OBJECT-TYPE
SYNTAX INTEGER
MAX-ACCESS read-write
STATUS current
DESCRIPTION
"Data value."
::= { dataArray14 299 }

dataValue14_300 OBJECT-TYPE
SYNTAX INTEGER
MAX-ACCESS read-write
STATUS current
DESCRIPTION
"Data value."
::= { dataArray14 300 }

dataValue14_301 OBJECT-TYPE
SYNTAX INTEGER
MAX-ACCESS read-write
STATUS current
DESCRIPTION
"Data value."
::= { dataArray14 301 }

dataValue14_302 OBJECT-TYPE
SYNTAX INTEGER
MAX-ACCESS read-write
STATUS current
DESCRIPTION
"Data value."
::= { dataArray14 302 }

dataValue14_303 OBJECT-TYPE
SYNTAX INTEGER
MAX-ACCESS read-write
STATUS current
DESCRIPTION
"Data value."
::= { dataArray14 303 }

dataValue14_304 OBJECT-TYPE
SYNTAX INTEGER
MAX-ACCESS read-write
STATUS current
DESCRIPTION
"Data value."
::= { dataArray14 304 }

dataValue14_305 OBJECT-TYPE
SYNTAX INTEGER
MAX-ACCESS read-write
STATUS current
DESCRIPTION
"Data value."
::= { dataArray14 305 }

dataValue14_306 OBJECT-TYPE
SYNTAX INTEGER
MAX-ACCESS read-write
STATUS current
DESCRIPTION
"Data value."
::= { dataArray14 306 }

dataValue14_307 OBJECT-TYPE
SYNTAX INTEGER
MAX-ACCESS read-write
STATUS current
DESCRIPTION
"Data value."
::= { dataArray14 307 }

dataValue14_308 OBJECT-TYPE
SYNTAX INTEGER
MAX-ACCESS read-write
STATUS current
DESCRIPTION
"Data value."
::= { dataArray14 308 }

dataValue14_309 OBJECT-TYPE
SYNTAX INTEGER
MAX-ACCESS read-write
STATUS current
DESCRIPTION
"Data value."
::= { dataArray14 309 }

dataValue14_310 OBJECT-TYPE
SYNTAX INTEGER
MAX-ACCESS read-write
STATUS current
DESCRIPTION
"Data value."
::= { dataArray14 310 }

dataValue14_311 OBJECT-TYPE
SYNTAX INTEGER
MAX-ACCESS read-write
STATUS current
DESCRIPTION
"Data value."
::= { dataArray14 311 }

dataValue14_312 OBJECT-TYPE
SYNTAX INTEGER
MAX-ACCESS read-write
STATUS current
DESCRIPTION
"Data value."
::= { dataArray14 312 }

dataValue14_313 OBJECT-TYPE
SYNTAX INTEGER
MAX-ACCESS read-write
STATUS current
DESCRIPTION
"Data value."
::= { dataArray14 313 }

dataValue14_314 OBJECT-TYPE
SYNTAX INTEGER
MAX-ACCESS read-write
STATUS current
DESCRIPTION
"Data value."
::= { dataArray14 314 }

dataValue14_315 OBJECT-TYPE
SYNTAX INTEGER
MAX-ACCESS read-write
STATUS current
DESCRIPTION
"Data value."
::= { dataArray14 315 }

dataValue14_316 OBJECT-TYPE
SYNTAX INTEGER
MAX-ACCESS read-write
STATUS current
DESCRIPTION
"Data value."
::= { dataArray14 316 }

dataValue14_317 OBJECT-TYPE
SYNTAX INTEGER
MAX-ACCESS read-write
STATUS current
DESCRIPTION
"Data value."
::= { dataArray14 317 }

dataValue14_318 OBJECT-TYPE
SYNTAX INTEGER
MAX-ACCESS read-write
STATUS current
DESCRIPTION
"Data value."
::= { dataArray14 318 }

dataValue14_319 OBJECT-TYPE
SYNTAX INTEGER
MAX-ACCESS read-write
STATUS current
DESCRIPTION
"Data value."
::= { dataArray14 319 }

dataValue14_320 OBJECT-TYPE
SYNTAX INTEGER
MAX-ACCESS read-write
STATUS current
DESCRIPTION
"Data value."
::= { dataArray14 320 }

dataValue14_321 OBJECT-TYPE
SYNTAX INTEGER
MAX-ACCESS read-write
STATUS current
DESCRIPTION
"Data value."
::= { dataArray14 321 }

dataValue14_322 OBJECT-TYPE
SYNTAX INTEGER
MAX-ACCESS read-write
STATUS current
DESCRIPTION
"Data value."
::= { dataArray14 322 }

dataValue14_323 OBJECT-TYPE
SYNTAX INTEGER
MAX-ACCESS read-write
STATUS current
DESCRIPTION
"Data value."
::= { dataArray14 323 }

dataValue14_324 OBJECT-TYPE
SYNTAX INTEGER
MAX-ACCESS read-write
STATUS current
DESCRIPTION
"Data value."
::= { dataArray14 324 }

dataValue14_325 OBJECT-TYPE
SYNTAX INTEGER
MAX-ACCESS read-write
STATUS current
DESCRIPTION
"Data value."
::= { dataArray14 325 }

dataValue14_326 OBJECT-TYPE
SYNTAX INTEGER
MAX-ACCESS read-write
STATUS current
DESCRIPTION
"Data value."
::= { dataArray14 326 }

dataValue14_327 OBJECT-TYPE
SYNTAX INTEGER
MAX-ACCESS read-write
STATUS current
DESCRIPTION
"Data value."
::= { dataArray14 327 }

dataValue14_328 OBJECT-TYPE
SYNTAX INTEGER
MAX-ACCESS read-write
STATUS current
DESCRIPTION
"Data value."
::= { dataArray14 328 }

dataValue14_329 OBJECT-TYPE
SYNTAX INTEGER
MAX-ACCESS read-write
STATUS current
DESCRIPTION
"Data value."
::= { dataArray14 329 }

dataValue14_330 OBJECT-TYPE
SYNTAX INTEGER
MAX-ACCESS read-write
STATUS current
DESCRIPTION
"Data value."
::= { dataArray14 330 }

dataValue14_331 OBJECT-TYPE
SYNTAX INTEGER
MAX-ACCESS read-write
STATUS current
DESCRIPTION
"Data value."
::= { dataArray14 331 }

dataValue14_332 OBJECT-TYPE
SYNTAX INTEGER
MAX-ACCESS read-write
STATUS current
DESCRIPTION
"Data value."
::= { dataArray14 332 }

dataValue14_333 OBJECT-TYPE
SYNTAX INTEGER
MAX-ACCESS read-write
STATUS current
DESCRIPTION
"Data value."
::= { dataArray14 333 }

dataValue14_334 OBJECT-TYPE
SYNTAX INTEGER
MAX-ACCESS read-write
STATUS current
DESCRIPTION
"Data value."
::= { dataArray14 334 }

dataValue14_335 OBJECT-TYPE
SYNTAX INTEGER
MAX-ACCESS read-write
STATUS current
DESCRIPTION
"Data value."
::= { dataArray14 335 }

dataValue14_336 OBJECT-TYPE
SYNTAX INTEGER
MAX-ACCESS read-write
STATUS current
DESCRIPTION
"Data value."
::= { dataArray14 336 }

dataValue14_337 OBJECT-TYPE
SYNTAX INTEGER
MAX-ACCESS read-write
STATUS current
DESCRIPTION
"Data value."
::= { dataArray14 337 }

dataValue14_338 OBJECT-TYPE
SYNTAX INTEGER
MAX-ACCESS read-write
STATUS current
DESCRIPTION
"Data value."
::= { dataArray14 338 }

dataValue14_339 OBJECT-TYPE
SYNTAX INTEGER
MAX-ACCESS read-write
STATUS current
DESCRIPTION
"Data value."
::= { dataArray14 339 }

dataValue14_340 OBJECT-TYPE
SYNTAX INTEGER
MAX-ACCESS read-write
STATUS current
DESCRIPTION
"Data value."
::= { dataArray14 340 }

dataValue14_341 OBJECT-TYPE
SYNTAX INTEGER
MAX-ACCESS read-write
STATUS current
DESCRIPTION
"Data value."
::= { dataArray14 341 }

dataValue14_342 OBJECT-TYPE
SYNTAX INTEGER
MAX-ACCESS read-write
STATUS current
DESCRIPTION
"Data value."
::= { dataArray14 342 }

dataValue14_343 OBJECT-TYPE
SYNTAX INTEGER
MAX-ACCESS read-write
STATUS current
DESCRIPTION
"Data value."
::= { dataArray14 343 }

dataValue14_344 OBJECT-TYPE
SYNTAX INTEGER
MAX-ACCESS read-write
STATUS current
DESCRIPTION
"Data value."
::= { dataArray14 344 }

dataValue14_345 OBJECT-TYPE
SYNTAX INTEGER
MAX-ACCESS read-write
STATUS current
DESCRIPTION
"Data value."
::= { dataArray14 345 }

dataValue14_346 OBJECT-TYPE
SYNTAX INTEGER
MAX-ACCESS read-write
STATUS current
DESCRIPTION
"Data value."
::= { dataArray14 346 }

dataValue14_347 OBJECT-TYPE
SYNTAX INTEGER
MAX-ACCESS read-write
STATUS current
DESCRIPTION
"Data value."
::= { dataArray14 347 }

dataValue14_348 OBJECT-TYPE
SYNTAX INTEGER
MAX-ACCESS read-write
STATUS current
DESCRIPTION
"Data value."
::= { dataArray14 348 }

dataValue14_349 OBJECT-TYPE
SYNTAX INTEGER
MAX-ACCESS read-write
STATUS current
DESCRIPTION
"Data value."
::= { dataArray14 349 }

dataValue14_350 OBJECT-TYPE
SYNTAX INTEGER
MAX-ACCESS read-write
STATUS current
DESCRIPTION
"Data value."
::= { dataArray14 350 }

dataValue14_351 OBJECT-TYPE
SYNTAX INTEGER
MAX-ACCESS read-write
STATUS current
DESCRIPTION
"Data value."
::= { dataArray14 351 }

dataValue14_352 OBJECT-TYPE
SYNTAX INTEGER
MAX-ACCESS read-write
STATUS current
DESCRIPTION
"Data value."
::= { dataArray14 352 }

dataValue14_353 OBJECT-TYPE
SYNTAX INTEGER
MAX-ACCESS read-write
STATUS current
DESCRIPTION
"Data value."
::= { dataArray14 353 }

dataValue14_354 OBJECT-TYPE
SYNTAX INTEGER
MAX-ACCESS read-write
STATUS current
DESCRIPTION
"Data value."
::= { dataArray14 354 }

dataValue14_355 OBJECT-TYPE
SYNTAX INTEGER
MAX-ACCESS read-write
STATUS current
DESCRIPTION
"Data value."
::= { dataArray14 355 }

dataValue14_356 OBJECT-TYPE
SYNTAX INTEGER
MAX-ACCESS read-write
STATUS current
DESCRIPTION
"Data value."
::= { dataArray14 356 }

dataValue14_357 OBJECT-TYPE
SYNTAX INTEGER
MAX-ACCESS read-write
STATUS current
DESCRIPTION
"Data value."
::= { dataArray14 357 }

dataValue14_358 OBJECT-TYPE
SYNTAX INTEGER
MAX-ACCESS read-write
STATUS current
DESCRIPTION
"Data value."
::= { dataArray14 358 }

dataValue14_359 OBJECT-TYPE
SYNTAX INTEGER
MAX-ACCESS read-write
STATUS current
DESCRIPTION
"Data value."
::= { dataArray14 359 }

dataValue14_360 OBJECT-TYPE
SYNTAX INTEGER
MAX-ACCESS read-write
STATUS current
DESCRIPTION
"Data value."
::= { dataArray14 360 }

dataValue14_361 OBJECT-TYPE
SYNTAX INTEGER
MAX-ACCESS read-write
STATUS current
DESCRIPTION
"Data value."
::= { dataArray14 361 }

dataValue14_362 OBJECT-TYPE
SYNTAX INTEGER
MAX-ACCESS read-write
STATUS current
DESCRIPTION
"Data value."
::= { dataArray14 362 }

dataValue14_363 OBJECT-TYPE
SYNTAX INTEGER
MAX-ACCESS read-write
STATUS current
DESCRIPTION
"Data value."
::= { dataArray14 363 }

dataValue14_364 OBJECT-TYPE
SYNTAX INTEGER
MAX-ACCESS read-write
STATUS current
DESCRIPTION
"Data value."
::= { dataArray14 364 }

dataValue14_365 OBJECT-TYPE
SYNTAX INTEGER
MAX-ACCESS read-write
STATUS current
DESCRIPTION
"Data value."
::= { dataArray14 365 }

dataValue14_366 OBJECT-TYPE
SYNTAX INTEGER
MAX-ACCESS read-write
STATUS current
DESCRIPTION
"Data value."
::= { dataArray14 366 }

dataValue14_367 OBJECT-TYPE
SYNTAX INTEGER
MAX-ACCESS read-write
STATUS current
DESCRIPTION
"Data value."
::= { dataArray14 367 }

dataValue14_368 OBJECT-TYPE
SYNTAX INTEGER
MAX-ACCESS read-write
STATUS current
DESCRIPTION
"Data value."
::= { dataArray14 368 }

dataValue14_369 OBJECT-TYPE
SYNTAX INTEGER
MAX-ACCESS read-write
STATUS current
DESCRIPTION
"Data value."
::= { dataArray14 369 }

dataValue14_370 OBJECT-TYPE
SYNTAX INTEGER
MAX-ACCESS read-write
STATUS current
DESCRIPTION
"Data value."
::= { dataArray14 370 }

dataValue14_371 OBJECT-TYPE
SYNTAX INTEGER
MAX-ACCESS read-write
STATUS current
DESCRIPTION
"Data value."
::= { dataArray14 371 }

dataValue14_372 OBJECT-TYPE
SYNTAX INTEGER
MAX-ACCESS read-write
STATUS current
DESCRIPTION
"Data value."
::= { dataArray14 372 }

dataValue14_373 OBJECT-TYPE
SYNTAX INTEGER
MAX-ACCESS read-write
STATUS current
DESCRIPTION
"Data value."
::= { dataArray14 373 }

dataValue14_374 OBJECT-TYPE
SYNTAX INTEGER
MAX-ACCESS read-write
STATUS current
DESCRIPTION
"Data value."
::= { dataArray14 374 }

dataValue14_375 OBJECT-TYPE
SYNTAX INTEGER
MAX-ACCESS read-write
STATUS current
DESCRIPTION
"Data value."
::= { dataArray14 375 }

dataValue14_376 OBJECT-TYPE
SYNTAX INTEGER
MAX-ACCESS read-write
STATUS current
DESCRIPTION
"Data value."
::= { dataArray14 376 }

dataValue14_377 OBJECT-TYPE
SYNTAX INTEGER
MAX-ACCESS read-write
STATUS current
DESCRIPTION
"Data value."
::= { dataArray14 377 }

dataValue14_378 OBJECT-TYPE
SYNTAX INTEGER
MAX-ACCESS read-write
STATUS current
DESCRIPTION
"Data value."
::= { dataArray14 378 }

dataValue14_379 OBJECT-TYPE
SYNTAX INTEGER
MAX-ACCESS read-write
STATUS current
DESCRIPTION
"Data value."
::= { dataArray14 379 }

dataValue14_380 OBJECT-TYPE
SYNTAX INTEGER
MAX-ACCESS read-write
STATUS current
DESCRIPTION
"Data value."
::= { dataArray14 380 }

dataValue14_381 OBJECT-TYPE
SYNTAX INTEGER
MAX-ACCESS read-write
STATUS current
DESCRIPTION
"Data value."
::= { dataArray14 381 }

dataValue14_382 OBJECT-TYPE
SYNTAX INTEGER
MAX-ACCESS read-write
STATUS current
DESCRIPTION
"Data value."
::= { dataArray14 382 }

dataValue14_383 OBJECT-TYPE
SYNTAX INTEGER
MAX-ACCESS read-write
STATUS current
DESCRIPTION
"Data value."
::= { dataArray14 383 }

dataValue14_384 OBJECT-TYPE
SYNTAX INTEGER
MAX-ACCESS read-write
STATUS current
DESCRIPTION
"Data value."
::= { dataArray14 384 }

dataValue14_385 OBJECT-TYPE
SYNTAX INTEGER
MAX-ACCESS read-write
STATUS current
DESCRIPTION
"Data value."
::= { dataArray14 385 }

dataValue14_386 OBJECT-TYPE
SYNTAX INTEGER
MAX-ACCESS read-write
STATUS current
DESCRIPTION
"Data value."
::= { dataArray14 386 }

dataValue14_387 OBJECT-TYPE
SYNTAX INTEGER
MAX-ACCESS read-write
STATUS current
DESCRIPTION
"Data value."
::= { dataArray14 387 }

dataValue14_388 OBJECT-TYPE
SYNTAX INTEGER
MAX-ACCESS read-write
STATUS current
DESCRIPTION
"Data value."
::= { dataArray14 388 }

dataValue14_389 OBJECT-TYPE
SYNTAX INTEGER
MAX-ACCESS read-write
STATUS current
DESCRIPTION
"Data value."
::= { dataArray14 389 }

dataValue14_390 OBJECT-TYPE
SYNTAX INTEGER
MAX-ACCESS read-write
STATUS current
DESCRIPTION
"Data value."
::= { dataArray14 390 }

dataValue14_391 OBJECT-TYPE
SYNTAX INTEGER
MAX-ACCESS read-write
STATUS current
DESCRIPTION
"Data value."
::= { dataArray14 391 }

dataValue14_392 OBJECT-TYPE
SYNTAX INTEGER
MAX-ACCESS read-write
STATUS current
DESCRIPTION
"Data value."
::= { dataArray14 392 }

dataValue14_393 OBJECT-TYPE
SYNTAX INTEGER
MAX-ACCESS read-write
STATUS current
DESCRIPTION
"Data value."
::= { dataArray14 393 }

dataValue14_394 OBJECT-TYPE
SYNTAX INTEGER
MAX-ACCESS read-write
STATUS current
DESCRIPTION
"Data value."
::= { dataArray14 394 }

dataValue14_395 OBJECT-TYPE
SYNTAX INTEGER
MAX-ACCESS read-write
STATUS current
DESCRIPTION
"Data value."
::= { dataArray14 395 }

dataValue14_396 OBJECT-TYPE
SYNTAX INTEGER
MAX-ACCESS read-write
STATUS current
DESCRIPTION
"Data value."
::= { dataArray14 396 }

dataValue14_397 OBJECT-TYPE
SYNTAX INTEGER
MAX-ACCESS read-write
STATUS current
DESCRIPTION
"Data value."
::= { dataArray14 397 }

dataValue14_398 OBJECT-TYPE
SYNTAX INTEGER
MAX-ACCESS read-write
STATUS current
DESCRIPTION
"Data value."
::= { dataArray14 398 }

dataValue14_399 OBJECT-TYPE
SYNTAX INTEGER
MAX-ACCESS read-write
STATUS current
DESCRIPTION
"Data value."
::= { dataArray14 399 }

dataArray15 OBJECT IDENTIFIER ::= { cc08255400_v1_00a 15 }

dataValue15_0 OBJECT-TYPE
SYNTAX INTEGER
MAX-ACCESS read-write
STATUS current
DESCRIPTION
"Data value."
::= { dataArray15 0 }

dataValue15_1 OBJECT-TYPE
SYNTAX INTEGER
MAX-ACCESS read-write
STATUS current
DESCRIPTION
"Data value."
::= { dataArray15 1 }

dataValue15_2 OBJECT-TYPE
SYNTAX INTEGER
MAX-ACCESS read-write
STATUS current
DESCRIPTION
"Data value."
::= { dataArray15 2 }

dataValue15_3 OBJECT-TYPE
SYNTAX INTEGER
MAX-ACCESS read-write
STATUS current
DESCRIPTION
"Data value."
::= { dataArray15 3 }

dataValue15_4 OBJECT-TYPE
SYNTAX INTEGER
MAX-ACCESS read-write
STATUS current
DESCRIPTION
"Data value."
::= { dataArray15 4 }

dataValue15_5 OBJECT-TYPE
SYNTAX INTEGER
MAX-ACCESS read-write
STATUS current
DESCRIPTION
"Data value."
::= { dataArray15 5 }

dataValue15_6 OBJECT-TYPE
SYNTAX INTEGER
MAX-ACCESS read-write
STATUS current
DESCRIPTION
"Data value."
::= { dataArray15 6 }

dataValue15_7 OBJECT-TYPE
SYNTAX INTEGER
MAX-ACCESS read-write
STATUS current
DESCRIPTION
"Data value."
::= { dataArray15 7 }

dataValue15_8 OBJECT-TYPE
SYNTAX INTEGER
MAX-ACCESS read-write
STATUS current
DESCRIPTION
"Data value."
::= { dataArray15 8 }

dataValue15_9 OBJECT-TYPE
SYNTAX INTEGER
MAX-ACCESS read-write
STATUS current
DESCRIPTION
"Data value."
::= { dataArray15 9 }

dataValue15_10 OBJECT-TYPE
SYNTAX INTEGER
MAX-ACCESS read-write
STATUS current
DESCRIPTION
"Data value."
::= { dataArray15 10 }

dataValue15_11 OBJECT-TYPE
SYNTAX INTEGER
MAX-ACCESS read-write
STATUS current
DESCRIPTION
"Data value."
::= { dataArray15 11 }

dataValue15_12 OBJECT-TYPE
SYNTAX INTEGER
MAX-ACCESS read-write
STATUS current
DESCRIPTION
"Data value."
::= { dataArray15 12 }

dataValue15_13 OBJECT-TYPE
SYNTAX INTEGER
MAX-ACCESS read-write
STATUS current
DESCRIPTION
"Data value."
::= { dataArray15 13 }

dataValue15_14 OBJECT-TYPE
SYNTAX INTEGER
MAX-ACCESS read-write
STATUS current
DESCRIPTION
"Data value."
::= { dataArray15 14 }

dataValue15_15 OBJECT-TYPE
SYNTAX INTEGER
MAX-ACCESS read-write
STATUS current
DESCRIPTION
"Data value."
::= { dataArray15 15 }

dataValue15_16 OBJECT-TYPE
SYNTAX INTEGER
MAX-ACCESS read-write
STATUS current
DESCRIPTION
"Data value."
::= { dataArray15 16 }

dataValue15_17 OBJECT-TYPE
SYNTAX INTEGER
MAX-ACCESS read-write
STATUS current
DESCRIPTION
"Data value."
::= { dataArray15 17 }

dataValue15_18 OBJECT-TYPE
SYNTAX INTEGER
MAX-ACCESS read-write
STATUS current
DESCRIPTION
"Data value."
::= { dataArray15 18 }

dataValue15_19 OBJECT-TYPE
SYNTAX INTEGER
MAX-ACCESS read-write
STATUS current
DESCRIPTION
"Data value."
::= { dataArray15 19 }

dataValue15_20 OBJECT-TYPE
SYNTAX INTEGER
MAX-ACCESS read-write
STATUS current
DESCRIPTION
"Data value."
::= { dataArray15 20 }

dataValue15_21 OBJECT-TYPE
SYNTAX INTEGER
MAX-ACCESS read-write
STATUS current
DESCRIPTION
"Data value."
::= { dataArray15 21 }

dataValue15_22 OBJECT-TYPE
SYNTAX INTEGER
MAX-ACCESS read-write
STATUS current
DESCRIPTION
"Data value."
::= { dataArray15 22 }

dataValue15_23 OBJECT-TYPE
SYNTAX INTEGER
MAX-ACCESS read-write
STATUS current
DESCRIPTION
"Data value."
::= { dataArray15 23 }

dataValue15_24 OBJECT-TYPE
SYNTAX INTEGER
MAX-ACCESS read-write
STATUS current
DESCRIPTION
"Data value."
::= { dataArray15 24 }

dataValue15_25 OBJECT-TYPE
SYNTAX INTEGER
MAX-ACCESS read-write
STATUS current
DESCRIPTION
"Data value."
::= { dataArray15 25 }

dataValue15_26 OBJECT-TYPE
SYNTAX INTEGER
MAX-ACCESS read-write
STATUS current
DESCRIPTION
"Data value."
::= { dataArray15 26 }

dataValue15_27 OBJECT-TYPE
SYNTAX INTEGER
MAX-ACCESS read-write
STATUS current
DESCRIPTION
"Data value."
::= { dataArray15 27 }

dataValue15_28 OBJECT-TYPE
SYNTAX INTEGER
MAX-ACCESS read-write
STATUS current
DESCRIPTION
"Data value."
::= { dataArray15 28 }

dataValue15_29 OBJECT-TYPE
SYNTAX INTEGER
MAX-ACCESS read-write
STATUS current
DESCRIPTION
"Data value."
::= { dataArray15 29 }

dataValue15_30 OBJECT-TYPE
SYNTAX INTEGER
MAX-ACCESS read-write
STATUS current
DESCRIPTION
"Data value."
::= { dataArray15 30 }

dataValue15_31 OBJECT-TYPE
SYNTAX INTEGER
MAX-ACCESS read-write
STATUS current
DESCRIPTION
"Data value."
::= { dataArray15 31 }

dataValue15_32 OBJECT-TYPE
SYNTAX INTEGER
MAX-ACCESS read-write
STATUS current
DESCRIPTION
"Data value."
::= { dataArray15 32 }

dataValue15_33 OBJECT-TYPE
SYNTAX INTEGER
MAX-ACCESS read-write
STATUS current
DESCRIPTION
"Data value."
::= { dataArray15 33 }

dataValue15_34 OBJECT-TYPE
SYNTAX INTEGER
MAX-ACCESS read-write
STATUS current
DESCRIPTION
"Data value."
::= { dataArray15 34 }

dataValue15_35 OBJECT-TYPE
SYNTAX INTEGER
MAX-ACCESS read-write
STATUS current
DESCRIPTION
"Data value."
::= { dataArray15 35 }

dataValue15_36 OBJECT-TYPE
SYNTAX INTEGER
MAX-ACCESS read-write
STATUS current
DESCRIPTION
"Data value."
::= { dataArray15 36 }

dataValue15_37 OBJECT-TYPE
SYNTAX INTEGER
MAX-ACCESS read-write
STATUS current
DESCRIPTION
"Data value."
::= { dataArray15 37 }

dataValue15_38 OBJECT-TYPE
SYNTAX INTEGER
MAX-ACCESS read-write
STATUS current
DESCRIPTION
"Data value."
::= { dataArray15 38 }

dataValue15_39 OBJECT-TYPE
SYNTAX INTEGER
MAX-ACCESS read-write
STATUS current
DESCRIPTION
"Data value."
::= { dataArray15 39 }

dataValue15_40 OBJECT-TYPE
SYNTAX INTEGER
MAX-ACCESS read-write
STATUS current
DESCRIPTION
"Data value."
::= { dataArray15 40 }

dataValue15_41 OBJECT-TYPE
SYNTAX INTEGER
MAX-ACCESS read-write
STATUS current
DESCRIPTION
"Data value."
::= { dataArray15 41 }

dataValue15_42 OBJECT-TYPE
SYNTAX INTEGER
MAX-ACCESS read-write
STATUS current
DESCRIPTION
"Data value."
::= { dataArray15 42 }

dataValue15_43 OBJECT-TYPE
SYNTAX INTEGER
MAX-ACCESS read-write
STATUS current
DESCRIPTION
"Data value."
::= { dataArray15 43 }

dataValue15_44 OBJECT-TYPE
SYNTAX INTEGER
MAX-ACCESS read-write
STATUS current
DESCRIPTION
"Data value."
::= { dataArray15 44 }

dataValue15_45 OBJECT-TYPE
SYNTAX INTEGER
MAX-ACCESS read-write
STATUS current
DESCRIPTION
"Data value."
::= { dataArray15 45 }

dataValue15_46 OBJECT-TYPE
SYNTAX INTEGER
MAX-ACCESS read-write
STATUS current
DESCRIPTION
"Data value."
::= { dataArray15 46 }

dataValue15_47 OBJECT-TYPE
SYNTAX INTEGER
MAX-ACCESS read-write
STATUS current
DESCRIPTION
"Data value."
::= { dataArray15 47 }

dataValue15_48 OBJECT-TYPE
SYNTAX INTEGER
MAX-ACCESS read-write
STATUS current
DESCRIPTION
"Data value."
::= { dataArray15 48 }

dataValue15_49 OBJECT-TYPE
SYNTAX INTEGER
MAX-ACCESS read-write
STATUS current
DESCRIPTION
"Data value."
::= { dataArray15 49 }

dataValue15_50 OBJECT-TYPE
SYNTAX INTEGER
MAX-ACCESS read-write
STATUS current
DESCRIPTION
"Data value."
::= { dataArray15 50 }

dataValue15_51 OBJECT-TYPE
SYNTAX INTEGER
MAX-ACCESS read-write
STATUS current
DESCRIPTION
"Data value."
::= { dataArray15 51 }

dataValue15_52 OBJECT-TYPE
SYNTAX INTEGER
MAX-ACCESS read-write
STATUS current
DESCRIPTION
"Data value."
::= { dataArray15 52 }

dataValue15_53 OBJECT-TYPE
SYNTAX INTEGER
MAX-ACCESS read-write
STATUS current
DESCRIPTION
"Data value."
::= { dataArray15 53 }

dataValue15_54 OBJECT-TYPE
SYNTAX INTEGER
MAX-ACCESS read-write
STATUS current
DESCRIPTION
"Data value."
::= { dataArray15 54 }

dataValue15_55 OBJECT-TYPE
SYNTAX INTEGER
MAX-ACCESS read-write
STATUS current
DESCRIPTION
"Data value."
::= { dataArray15 55 }

dataValue15_56 OBJECT-TYPE
SYNTAX INTEGER
MAX-ACCESS read-write
STATUS current
DESCRIPTION
"Data value."
::= { dataArray15 56 }

dataValue15_57 OBJECT-TYPE
SYNTAX INTEGER
MAX-ACCESS read-write
STATUS current
DESCRIPTION
"Data value."
::= { dataArray15 57 }

dataValue15_58 OBJECT-TYPE
SYNTAX INTEGER
MAX-ACCESS read-write
STATUS current
DESCRIPTION
"Data value."
::= { dataArray15 58 }

dataValue15_59 OBJECT-TYPE
SYNTAX INTEGER
MAX-ACCESS read-write
STATUS current
DESCRIPTION
"Data value."
::= { dataArray15 59 }

dataValue15_60 OBJECT-TYPE
SYNTAX INTEGER
MAX-ACCESS read-write
STATUS current
DESCRIPTION
"Data value."
::= { dataArray15 60 }

dataValue15_61 OBJECT-TYPE
SYNTAX INTEGER
MAX-ACCESS read-write
STATUS current
DESCRIPTION
"Data value."
::= { dataArray15 61 }

dataValue15_62 OBJECT-TYPE
SYNTAX INTEGER
MAX-ACCESS read-write
STATUS current
DESCRIPTION
"Data value."
::= { dataArray15 62 }

dataValue15_63 OBJECT-TYPE
SYNTAX INTEGER
MAX-ACCESS read-write
STATUS current
DESCRIPTION
"Data value."
::= { dataArray15 63 }

dataValue15_64 OBJECT-TYPE
SYNTAX INTEGER
MAX-ACCESS read-write
STATUS current
DESCRIPTION
"Data value."
::= { dataArray15 64 }

dataValue15_65 OBJECT-TYPE
SYNTAX INTEGER
MAX-ACCESS read-write
STATUS current
DESCRIPTION
"Data value."
::= { dataArray15 65 }

dataValue15_66 OBJECT-TYPE
SYNTAX INTEGER
MAX-ACCESS read-write
STATUS current
DESCRIPTION
"Data value."
::= { dataArray15 66 }

dataValue15_67 OBJECT-TYPE
SYNTAX INTEGER
MAX-ACCESS read-write
STATUS current
DESCRIPTION
"Data value."
::= { dataArray15 67 }

dataValue15_68 OBJECT-TYPE
SYNTAX INTEGER
MAX-ACCESS read-write
STATUS current
DESCRIPTION
"Data value."
::= { dataArray15 68 }

dataValue15_69 OBJECT-TYPE
SYNTAX INTEGER
MAX-ACCESS read-write
STATUS current
DESCRIPTION
"Data value."
::= { dataArray15 69 }

dataValue15_70 OBJECT-TYPE
SYNTAX INTEGER
MAX-ACCESS read-write
STATUS current
DESCRIPTION
"Data value."
::= { dataArray15 70 }

dataValue15_71 OBJECT-TYPE
SYNTAX INTEGER
MAX-ACCESS read-write
STATUS current
DESCRIPTION
"Data value."
::= { dataArray15 71 }

dataValue15_72 OBJECT-TYPE
SYNTAX INTEGER
MAX-ACCESS read-write
STATUS current
DESCRIPTION
"Data value."
::= { dataArray15 72 }

dataValue15_73 OBJECT-TYPE
SYNTAX INTEGER
MAX-ACCESS read-write
STATUS current
DESCRIPTION
"Data value."
::= { dataArray15 73 }

dataValue15_74 OBJECT-TYPE
SYNTAX INTEGER
MAX-ACCESS read-write
STATUS current
DESCRIPTION
"Data value."
::= { dataArray15 74 }

dataValue15_75 OBJECT-TYPE
SYNTAX INTEGER
MAX-ACCESS read-write
STATUS current
DESCRIPTION
"Data value."
::= { dataArray15 75 }

dataValue15_76 OBJECT-TYPE
SYNTAX INTEGER
MAX-ACCESS read-write
STATUS current
DESCRIPTION
"Data value."
::= { dataArray15 76 }

dataValue15_77 OBJECT-TYPE
SYNTAX INTEGER
MAX-ACCESS read-write
STATUS current
DESCRIPTION
"Data value."
::= { dataArray15 77 }

dataValue15_78 OBJECT-TYPE
SYNTAX INTEGER
MAX-ACCESS read-write
STATUS current
DESCRIPTION
"Data value."
::= { dataArray15 78 }

dataValue15_79 OBJECT-TYPE
SYNTAX INTEGER
MAX-ACCESS read-write
STATUS current
DESCRIPTION
"Data value."
::= { dataArray15 79 }

dataValue15_80 OBJECT-TYPE
SYNTAX INTEGER
MAX-ACCESS read-write
STATUS current
DESCRIPTION
"Data value."
::= { dataArray15 80 }

dataValue15_81 OBJECT-TYPE
SYNTAX INTEGER
MAX-ACCESS read-write
STATUS current
DESCRIPTION
"Data value."
::= { dataArray15 81 }

dataValue15_82 OBJECT-TYPE
SYNTAX INTEGER
MAX-ACCESS read-write
STATUS current
DESCRIPTION
"Data value."
::= { dataArray15 82 }

dataValue15_83 OBJECT-TYPE
SYNTAX INTEGER
MAX-ACCESS read-write
STATUS current
DESCRIPTION
"Data value."
::= { dataArray15 83 }

dataValue15_84 OBJECT-TYPE
SYNTAX INTEGER
MAX-ACCESS read-write
STATUS current
DESCRIPTION
"Data value."
::= { dataArray15 84 }

dataValue15_85 OBJECT-TYPE
SYNTAX INTEGER
MAX-ACCESS read-write
STATUS current
DESCRIPTION
"Data value."
::= { dataArray15 85 }

dataValue15_86 OBJECT-TYPE
SYNTAX INTEGER
MAX-ACCESS read-write
STATUS current
DESCRIPTION
"Data value."
::= { dataArray15 86 }

dataValue15_87 OBJECT-TYPE
SYNTAX INTEGER
MAX-ACCESS read-write
STATUS current
DESCRIPTION
"Data value."
::= { dataArray15 87 }

dataValue15_88 OBJECT-TYPE
SYNTAX INTEGER
MAX-ACCESS read-write
STATUS current
DESCRIPTION
"Data value."
::= { dataArray15 88 }

dataValue15_89 OBJECT-TYPE
SYNTAX INTEGER
MAX-ACCESS read-write
STATUS current
DESCRIPTION
"Data value."
::= { dataArray15 89 }

dataValue15_90 OBJECT-TYPE
SYNTAX INTEGER
MAX-ACCESS read-write
STATUS current
DESCRIPTION
"Data value."
::= { dataArray15 90 }

dataValue15_91 OBJECT-TYPE
SYNTAX INTEGER
MAX-ACCESS read-write
STATUS current
DESCRIPTION
"Data value."
::= { dataArray15 91 }

dataValue15_92 OBJECT-TYPE
SYNTAX INTEGER
MAX-ACCESS read-write
STATUS current
DESCRIPTION
"Data value."
::= { dataArray15 92 }

dataValue15_93 OBJECT-TYPE
SYNTAX INTEGER
MAX-ACCESS read-write
STATUS current
DESCRIPTION
"Data value."
::= { dataArray15 93 }

dataValue15_94 OBJECT-TYPE
SYNTAX INTEGER
MAX-ACCESS read-write
STATUS current
DESCRIPTION
"Data value."
::= { dataArray15 94 }

dataValue15_95 OBJECT-TYPE
SYNTAX INTEGER
MAX-ACCESS read-write
STATUS current
DESCRIPTION
"Data value."
::= { dataArray15 95 }

dataValue15_96 OBJECT-TYPE
SYNTAX INTEGER
MAX-ACCESS read-write
STATUS current
DESCRIPTION
"Data value."
::= { dataArray15 96 }

dataValue15_97 OBJECT-TYPE
SYNTAX INTEGER
MAX-ACCESS read-write
STATUS current
DESCRIPTION
"Data value."
::= { dataArray15 97 }

dataValue15_98 OBJECT-TYPE
SYNTAX INTEGER
MAX-ACCESS read-write
STATUS current
DESCRIPTION
"Data value."
::= { dataArray15 98 }

dataValue15_99 OBJECT-TYPE
SYNTAX INTEGER
MAX-ACCESS read-write
STATUS current
DESCRIPTION
"Data value."
::= { dataArray15 99 }

dataValue15_100 OBJECT-TYPE
SYNTAX INTEGER
MAX-ACCESS read-write
STATUS current
DESCRIPTION
"Data value."
::= { dataArray15 100 }

dataValue15_101 OBJECT-TYPE
SYNTAX INTEGER
MAX-ACCESS read-write
STATUS current
DESCRIPTION
"Data value."
::= { dataArray15 101 }

dataValue15_102 OBJECT-TYPE
SYNTAX INTEGER
MAX-ACCESS read-write
STATUS current
DESCRIPTION
"Data value."
::= { dataArray15 102 }

dataValue15_103 OBJECT-TYPE
SYNTAX INTEGER
MAX-ACCESS read-write
STATUS current
DESCRIPTION
"Data value."
::= { dataArray15 103 }

dataValue15_104 OBJECT-TYPE
SYNTAX INTEGER
MAX-ACCESS read-write
STATUS current
DESCRIPTION
"Data value."
::= { dataArray15 104 }

dataValue15_105 OBJECT-TYPE
SYNTAX INTEGER
MAX-ACCESS read-write
STATUS current
DESCRIPTION
"Data value."
::= { dataArray15 105 }

dataValue15_106 OBJECT-TYPE
SYNTAX INTEGER
MAX-ACCESS read-write
STATUS current
DESCRIPTION
"Data value."
::= { dataArray15 106 }

dataValue15_107 OBJECT-TYPE
SYNTAX INTEGER
MAX-ACCESS read-write
STATUS current
DESCRIPTION
"Data value."
::= { dataArray15 107 }

dataValue15_108 OBJECT-TYPE
SYNTAX INTEGER
MAX-ACCESS read-write
STATUS current
DESCRIPTION
"Data value."
::= { dataArray15 108 }

dataValue15_109 OBJECT-TYPE
SYNTAX INTEGER
MAX-ACCESS read-write
STATUS current
DESCRIPTION
"Data value."
::= { dataArray15 109 }

dataValue15_110 OBJECT-TYPE
SYNTAX INTEGER
MAX-ACCESS read-write
STATUS current
DESCRIPTION
"Data value."
::= { dataArray15 110 }

dataValue15_111 OBJECT-TYPE
SYNTAX INTEGER
MAX-ACCESS read-write
STATUS current
DESCRIPTION
"Data value."
::= { dataArray15 111 }

dataValue15_112 OBJECT-TYPE
SYNTAX INTEGER
MAX-ACCESS read-write
STATUS current
DESCRIPTION
"Data value."
::= { dataArray15 112 }

dataValue15_113 OBJECT-TYPE
SYNTAX INTEGER
MAX-ACCESS read-write
STATUS current
DESCRIPTION
"Data value."
::= { dataArray15 113 }

dataValue15_114 OBJECT-TYPE
SYNTAX INTEGER
MAX-ACCESS read-write
STATUS current
DESCRIPTION
"Data value."
::= { dataArray15 114 }

dataValue15_115 OBJECT-TYPE
SYNTAX INTEGER
MAX-ACCESS read-write
STATUS current
DESCRIPTION
"Data value."
::= { dataArray15 115 }

dataValue15_116 OBJECT-TYPE
SYNTAX INTEGER
MAX-ACCESS read-write
STATUS current
DESCRIPTION
"Data value."
::= { dataArray15 116 }

dataValue15_117 OBJECT-TYPE
SYNTAX INTEGER
MAX-ACCESS read-write
STATUS current
DESCRIPTION
"Data value."
::= { dataArray15 117 }

dataValue15_118 OBJECT-TYPE
SYNTAX INTEGER
MAX-ACCESS read-write
STATUS current
DESCRIPTION
"Data value."
::= { dataArray15 118 }

dataValue15_119 OBJECT-TYPE
SYNTAX INTEGER
MAX-ACCESS read-write
STATUS current
DESCRIPTION
"Data value."
::= { dataArray15 119 }

dataValue15_120 OBJECT-TYPE
SYNTAX INTEGER
MAX-ACCESS read-write
STATUS current
DESCRIPTION
"Data value."
::= { dataArray15 120 }

dataValue15_121 OBJECT-TYPE
SYNTAX INTEGER
MAX-ACCESS read-write
STATUS current
DESCRIPTION
"Data value."
::= { dataArray15 121 }

dataValue15_122 OBJECT-TYPE
SYNTAX INTEGER
MAX-ACCESS read-write
STATUS current
DESCRIPTION
"Data value."
::= { dataArray15 122 }

dataValue15_123 OBJECT-TYPE
SYNTAX INTEGER
MAX-ACCESS read-write
STATUS current
DESCRIPTION
"Data value."
::= { dataArray15 123 }

dataValue15_124 OBJECT-TYPE
SYNTAX INTEGER
MAX-ACCESS read-write
STATUS current
DESCRIPTION
"Data value."
::= { dataArray15 124 }

dataValue15_125 OBJECT-TYPE
SYNTAX INTEGER
MAX-ACCESS read-write
STATUS current
DESCRIPTION
"Data value."
::= { dataArray15 125 }

dataValue15_126 OBJECT-TYPE
SYNTAX INTEGER
MAX-ACCESS read-write
STATUS current
DESCRIPTION
"Data value."
::= { dataArray15 126 }

dataValue15_127 OBJECT-TYPE
SYNTAX INTEGER
MAX-ACCESS read-write
STATUS current
DESCRIPTION
"Data value."
::= { dataArray15 127 }

dataValue15_128 OBJECT-TYPE
SYNTAX INTEGER
MAX-ACCESS read-write
STATUS current
DESCRIPTION
"Data value."
::= { dataArray15 128 }

dataValue15_129 OBJECT-TYPE
SYNTAX INTEGER
MAX-ACCESS read-write
STATUS current
DESCRIPTION
"Data value."
::= { dataArray15 129 }

dataValue15_130 OBJECT-TYPE
SYNTAX INTEGER
MAX-ACCESS read-write
STATUS current
DESCRIPTION
"Data value."
::= { dataArray15 130 }

dataValue15_131 OBJECT-TYPE
SYNTAX INTEGER
MAX-ACCESS read-write
STATUS current
DESCRIPTION
"Data value."
::= { dataArray15 131 }

dataValue15_132 OBJECT-TYPE
SYNTAX INTEGER
MAX-ACCESS read-write
STATUS current
DESCRIPTION
"Data value."
::= { dataArray15 132 }

dataValue15_133 OBJECT-TYPE
SYNTAX INTEGER
MAX-ACCESS read-write
STATUS current
DESCRIPTION
"Data value."
::= { dataArray15 133 }

dataValue15_134 OBJECT-TYPE
SYNTAX INTEGER
MAX-ACCESS read-write
STATUS current
DESCRIPTION
"Data value."
::= { dataArray15 134 }

dataValue15_135 OBJECT-TYPE
SYNTAX INTEGER
MAX-ACCESS read-write
STATUS current
DESCRIPTION
"Data value."
::= { dataArray15 135 }

dataValue15_136 OBJECT-TYPE
SYNTAX INTEGER
MAX-ACCESS read-write
STATUS current
DESCRIPTION
"Data value."
::= { dataArray15 136 }

dataValue15_137 OBJECT-TYPE
SYNTAX INTEGER
MAX-ACCESS read-write
STATUS current
DESCRIPTION
"Data value."
::= { dataArray15 137 }

dataValue15_138 OBJECT-TYPE
SYNTAX INTEGER
MAX-ACCESS read-write
STATUS current
DESCRIPTION
"Data value."
::= { dataArray15 138 }

dataValue15_139 OBJECT-TYPE
SYNTAX INTEGER
MAX-ACCESS read-write
STATUS current
DESCRIPTION
"Data value."
::= { dataArray15 139 }

dataValue15_140 OBJECT-TYPE
SYNTAX INTEGER
MAX-ACCESS read-write
STATUS current
DESCRIPTION
"Data value."
::= { dataArray15 140 }

dataValue15_141 OBJECT-TYPE
SYNTAX INTEGER
MAX-ACCESS read-write
STATUS current
DESCRIPTION
"Data value."
::= { dataArray15 141 }

dataValue15_142 OBJECT-TYPE
SYNTAX INTEGER
MAX-ACCESS read-write
STATUS current
DESCRIPTION
"Data value."
::= { dataArray15 142 }

dataValue15_143 OBJECT-TYPE
SYNTAX INTEGER
MAX-ACCESS read-write
STATUS current
DESCRIPTION
"Data value."
::= { dataArray15 143 }

dataValue15_144 OBJECT-TYPE
SYNTAX INTEGER
MAX-ACCESS read-write
STATUS current
DESCRIPTION
"Data value."
::= { dataArray15 144 }

dataValue15_145 OBJECT-TYPE
SYNTAX INTEGER
MAX-ACCESS read-write
STATUS current
DESCRIPTION
"Data value."
::= { dataArray15 145 }

dataValue15_146 OBJECT-TYPE
SYNTAX INTEGER
MAX-ACCESS read-write
STATUS current
DESCRIPTION
"Data value."
::= { dataArray15 146 }

dataValue15_147 OBJECT-TYPE
SYNTAX INTEGER
MAX-ACCESS read-write
STATUS current
DESCRIPTION
"Data value."
::= { dataArray15 147 }

dataValue15_148 OBJECT-TYPE
SYNTAX INTEGER
MAX-ACCESS read-write
STATUS current
DESCRIPTION
"Data value."
::= { dataArray15 148 }

dataValue15_149 OBJECT-TYPE
SYNTAX INTEGER
MAX-ACCESS read-write
STATUS current
DESCRIPTION
"Data value."
::= { dataArray15 149 }

dataValue15_150 OBJECT-TYPE
SYNTAX INTEGER
MAX-ACCESS read-write
STATUS current
DESCRIPTION
"Data value."
::= { dataArray15 150 }

dataValue15_151 OBJECT-TYPE
SYNTAX INTEGER
MAX-ACCESS read-write
STATUS current
DESCRIPTION
"Data value."
::= { dataArray15 151 }

dataValue15_152 OBJECT-TYPE
SYNTAX INTEGER
MAX-ACCESS read-write
STATUS current
DESCRIPTION
"Data value."
::= { dataArray15 152 }

dataValue15_153 OBJECT-TYPE
SYNTAX INTEGER
MAX-ACCESS read-write
STATUS current
DESCRIPTION
"Data value."
::= { dataArray15 153 }

dataValue15_154 OBJECT-TYPE
SYNTAX INTEGER
MAX-ACCESS read-write
STATUS current
DESCRIPTION
"Data value."
::= { dataArray15 154 }

dataValue15_155 OBJECT-TYPE
SYNTAX INTEGER
MAX-ACCESS read-write
STATUS current
DESCRIPTION
"Data value."
::= { dataArray15 155 }

dataValue15_156 OBJECT-TYPE
SYNTAX INTEGER
MAX-ACCESS read-write
STATUS current
DESCRIPTION
"Data value."
::= { dataArray15 156 }

dataValue15_157 OBJECT-TYPE
SYNTAX INTEGER
MAX-ACCESS read-write
STATUS current
DESCRIPTION
"Data value."
::= { dataArray15 157 }

dataValue15_158 OBJECT-TYPE
SYNTAX INTEGER
MAX-ACCESS read-write
STATUS current
DESCRIPTION
"Data value."
::= { dataArray15 158 }

dataValue15_159 OBJECT-TYPE
SYNTAX INTEGER
MAX-ACCESS read-write
STATUS current
DESCRIPTION
"Data value."
::= { dataArray15 159 }

dataValue15_160 OBJECT-TYPE
SYNTAX INTEGER
MAX-ACCESS read-write
STATUS current
DESCRIPTION
"Data value."
::= { dataArray15 160 }

dataValue15_161 OBJECT-TYPE
SYNTAX INTEGER
MAX-ACCESS read-write
STATUS current
DESCRIPTION
"Data value."
::= { dataArray15 161 }

dataValue15_162 OBJECT-TYPE
SYNTAX INTEGER
MAX-ACCESS read-write
STATUS current
DESCRIPTION
"Data value."
::= { dataArray15 162 }

dataValue15_163 OBJECT-TYPE
SYNTAX INTEGER
MAX-ACCESS read-write
STATUS current
DESCRIPTION
"Data value."
::= { dataArray15 163 }

dataValue15_164 OBJECT-TYPE
SYNTAX INTEGER
MAX-ACCESS read-write
STATUS current
DESCRIPTION
"Data value."
::= { dataArray15 164 }

dataValue15_165 OBJECT-TYPE
SYNTAX INTEGER
MAX-ACCESS read-write
STATUS current
DESCRIPTION
"Data value."
::= { dataArray15 165 }

dataValue15_166 OBJECT-TYPE
SYNTAX INTEGER
MAX-ACCESS read-write
STATUS current
DESCRIPTION
"Data value."
::= { dataArray15 166 }

dataValue15_167 OBJECT-TYPE
SYNTAX INTEGER
MAX-ACCESS read-write
STATUS current
DESCRIPTION
"Data value."
::= { dataArray15 167 }

dataValue15_168 OBJECT-TYPE
SYNTAX INTEGER
MAX-ACCESS read-write
STATUS current
DESCRIPTION
"Data value."
::= { dataArray15 168 }

dataValue15_169 OBJECT-TYPE
SYNTAX INTEGER
MAX-ACCESS read-write
STATUS current
DESCRIPTION
"Data value."
::= { dataArray15 169 }

dataValue15_170 OBJECT-TYPE
SYNTAX INTEGER
MAX-ACCESS read-write
STATUS current
DESCRIPTION
"Data value."
::= { dataArray15 170 }

dataValue15_171 OBJECT-TYPE
SYNTAX INTEGER
MAX-ACCESS read-write
STATUS current
DESCRIPTION
"Data value."
::= { dataArray15 171 }

dataValue15_172 OBJECT-TYPE
SYNTAX INTEGER
MAX-ACCESS read-write
STATUS current
DESCRIPTION
"Data value."
::= { dataArray15 172 }

dataValue15_173 OBJECT-TYPE
SYNTAX INTEGER
MAX-ACCESS read-write
STATUS current
DESCRIPTION
"Data value."
::= { dataArray15 173 }

dataValue15_174 OBJECT-TYPE
SYNTAX INTEGER
MAX-ACCESS read-write
STATUS current
DESCRIPTION
"Data value."
::= { dataArray15 174 }

dataValue15_175 OBJECT-TYPE
SYNTAX INTEGER
MAX-ACCESS read-write
STATUS current
DESCRIPTION
"Data value."
::= { dataArray15 175 }

dataValue15_176 OBJECT-TYPE
SYNTAX INTEGER
MAX-ACCESS read-write
STATUS current
DESCRIPTION
"Data value."
::= { dataArray15 176 }

dataValue15_177 OBJECT-TYPE
SYNTAX INTEGER
MAX-ACCESS read-write
STATUS current
DESCRIPTION
"Data value."
::= { dataArray15 177 }

dataValue15_178 OBJECT-TYPE
SYNTAX INTEGER
MAX-ACCESS read-write
STATUS current
DESCRIPTION
"Data value."
::= { dataArray15 178 }

dataValue15_179 OBJECT-TYPE
SYNTAX INTEGER
MAX-ACCESS read-write
STATUS current
DESCRIPTION
"Data value."
::= { dataArray15 179 }

dataValue15_180 OBJECT-TYPE
SYNTAX INTEGER
MAX-ACCESS read-write
STATUS current
DESCRIPTION
"Data value."
::= { dataArray15 180 }

dataValue15_181 OBJECT-TYPE
SYNTAX INTEGER
MAX-ACCESS read-write
STATUS current
DESCRIPTION
"Data value."
::= { dataArray15 181 }

dataValue15_182 OBJECT-TYPE
SYNTAX INTEGER
MAX-ACCESS read-write
STATUS current
DESCRIPTION
"Data value."
::= { dataArray15 182 }

dataValue15_183 OBJECT-TYPE
SYNTAX INTEGER
MAX-ACCESS read-write
STATUS current
DESCRIPTION
"Data value."
::= { dataArray15 183 }

dataValue15_184 OBJECT-TYPE
SYNTAX INTEGER
MAX-ACCESS read-write
STATUS current
DESCRIPTION
"Data value."
::= { dataArray15 184 }

dataValue15_185 OBJECT-TYPE
SYNTAX INTEGER
MAX-ACCESS read-write
STATUS current
DESCRIPTION
"Data value."
::= { dataArray15 185 }

dataValue15_186 OBJECT-TYPE
SYNTAX INTEGER
MAX-ACCESS read-write
STATUS current
DESCRIPTION
"Data value."
::= { dataArray15 186 }

dataValue15_187 OBJECT-TYPE
SYNTAX INTEGER
MAX-ACCESS read-write
STATUS current
DESCRIPTION
"Data value."
::= { dataArray15 187 }

dataValue15_188 OBJECT-TYPE
SYNTAX INTEGER
MAX-ACCESS read-write
STATUS current
DESCRIPTION
"Data value."
::= { dataArray15 188 }

dataValue15_189 OBJECT-TYPE
SYNTAX INTEGER
MAX-ACCESS read-write
STATUS current
DESCRIPTION
"Data value."
::= { dataArray15 189 }

dataValue15_190 OBJECT-TYPE
SYNTAX INTEGER
MAX-ACCESS read-write
STATUS current
DESCRIPTION
"Data value."
::= { dataArray15 190 }

dataValue15_191 OBJECT-TYPE
SYNTAX INTEGER
MAX-ACCESS read-write
STATUS current
DESCRIPTION
"Data value."
::= { dataArray15 191 }

dataValue15_192 OBJECT-TYPE
SYNTAX INTEGER
MAX-ACCESS read-write
STATUS current
DESCRIPTION
"Data value."
::= { dataArray15 192 }

dataValue15_193 OBJECT-TYPE
SYNTAX INTEGER
MAX-ACCESS read-write
STATUS current
DESCRIPTION
"Data value."
::= { dataArray15 193 }

dataValue15_194 OBJECT-TYPE
SYNTAX INTEGER
MAX-ACCESS read-write
STATUS current
DESCRIPTION
"Data value."
::= { dataArray15 194 }

dataValue15_195 OBJECT-TYPE
SYNTAX INTEGER
MAX-ACCESS read-write
STATUS current
DESCRIPTION
"Data value."
::= { dataArray15 195 }

dataValue15_196 OBJECT-TYPE
SYNTAX INTEGER
MAX-ACCESS read-write
STATUS current
DESCRIPTION
"Data value."
::= { dataArray15 196 }

dataValue15_197 OBJECT-TYPE
SYNTAX INTEGER
MAX-ACCESS read-write
STATUS current
DESCRIPTION
"Data value."
::= { dataArray15 197 }

dataValue15_198 OBJECT-TYPE
SYNTAX INTEGER
MAX-ACCESS read-write
STATUS current
DESCRIPTION
"Data value."
::= { dataArray15 198 }

dataValue15_199 OBJECT-TYPE
SYNTAX INTEGER
MAX-ACCESS read-write
STATUS current
DESCRIPTION
"Data value."
::= { dataArray15 199 }

dataValue15_200 OBJECT-TYPE
SYNTAX INTEGER
MAX-ACCESS read-write
STATUS current
DESCRIPTION
"Data value."
::= { dataArray15 200 }

dataValue15_201 OBJECT-TYPE
SYNTAX INTEGER
MAX-ACCESS read-write
STATUS current
DESCRIPTION
"Data value."
::= { dataArray15 201 }

dataValue15_202 OBJECT-TYPE
SYNTAX INTEGER
MAX-ACCESS read-write
STATUS current
DESCRIPTION
"Data value."
::= { dataArray15 202 }

dataValue15_203 OBJECT-TYPE
SYNTAX INTEGER
MAX-ACCESS read-write
STATUS current
DESCRIPTION
"Data value."
::= { dataArray15 203 }

dataValue15_204 OBJECT-TYPE
SYNTAX INTEGER
MAX-ACCESS read-write
STATUS current
DESCRIPTION
"Data value."
::= { dataArray15 204 }

dataValue15_205 OBJECT-TYPE
SYNTAX INTEGER
MAX-ACCESS read-write
STATUS current
DESCRIPTION
"Data value."
::= { dataArray15 205 }

dataValue15_206 OBJECT-TYPE
SYNTAX INTEGER
MAX-ACCESS read-write
STATUS current
DESCRIPTION
"Data value."
::= { dataArray15 206 }

dataValue15_207 OBJECT-TYPE
SYNTAX INTEGER
MAX-ACCESS read-write
STATUS current
DESCRIPTION
"Data value."
::= { dataArray15 207 }

dataValue15_208 OBJECT-TYPE
SYNTAX INTEGER
MAX-ACCESS read-write
STATUS current
DESCRIPTION
"Data value."
::= { dataArray15 208 }

dataValue15_209 OBJECT-TYPE
SYNTAX INTEGER
MAX-ACCESS read-write
STATUS current
DESCRIPTION
"Data value."
::= { dataArray15 209 }

dataValue15_210 OBJECT-TYPE
SYNTAX INTEGER
MAX-ACCESS read-write
STATUS current
DESCRIPTION
"Data value."
::= { dataArray15 210 }

dataValue15_211 OBJECT-TYPE
SYNTAX INTEGER
MAX-ACCESS read-write
STATUS current
DESCRIPTION
"Data value."
::= { dataArray15 211 }

dataValue15_212 OBJECT-TYPE
SYNTAX INTEGER
MAX-ACCESS read-write
STATUS current
DESCRIPTION
"Data value."
::= { dataArray15 212 }

dataValue15_213 OBJECT-TYPE
SYNTAX INTEGER
MAX-ACCESS read-write
STATUS current
DESCRIPTION
"Data value."
::= { dataArray15 213 }

dataValue15_214 OBJECT-TYPE
SYNTAX INTEGER
MAX-ACCESS read-write
STATUS current
DESCRIPTION
"Data value."
::= { dataArray15 214 }

dataValue15_215 OBJECT-TYPE
SYNTAX INTEGER
MAX-ACCESS read-write
STATUS current
DESCRIPTION
"Data value."
::= { dataArray15 215 }

dataValue15_216 OBJECT-TYPE
SYNTAX INTEGER
MAX-ACCESS read-write
STATUS current
DESCRIPTION
"Data value."
::= { dataArray15 216 }

dataValue15_217 OBJECT-TYPE
SYNTAX INTEGER
MAX-ACCESS read-write
STATUS current
DESCRIPTION
"Data value."
::= { dataArray15 217 }

dataValue15_218 OBJECT-TYPE
SYNTAX INTEGER
MAX-ACCESS read-write
STATUS current
DESCRIPTION
"Data value."
::= { dataArray15 218 }

dataValue15_219 OBJECT-TYPE
SYNTAX INTEGER
MAX-ACCESS read-write
STATUS current
DESCRIPTION
"Data value."
::= { dataArray15 219 }

dataValue15_220 OBJECT-TYPE
SYNTAX INTEGER
MAX-ACCESS read-write
STATUS current
DESCRIPTION
"Data value."
::= { dataArray15 220 }

dataValue15_221 OBJECT-TYPE
SYNTAX INTEGER
MAX-ACCESS read-write
STATUS current
DESCRIPTION
"Data value."
::= { dataArray15 221 }

dataValue15_222 OBJECT-TYPE
SYNTAX INTEGER
MAX-ACCESS read-write
STATUS current
DESCRIPTION
"Data value."
::= { dataArray15 222 }

dataValue15_223 OBJECT-TYPE
SYNTAX INTEGER
MAX-ACCESS read-write
STATUS current
DESCRIPTION
"Data value."
::= { dataArray15 223 }

dataValue15_224 OBJECT-TYPE
SYNTAX INTEGER
MAX-ACCESS read-write
STATUS current
DESCRIPTION
"Data value."
::= { dataArray15 224 }

dataValue15_225 OBJECT-TYPE
SYNTAX INTEGER
MAX-ACCESS read-write
STATUS current
DESCRIPTION
"Data value."
::= { dataArray15 225 }

dataValue15_226 OBJECT-TYPE
SYNTAX INTEGER
MAX-ACCESS read-write
STATUS current
DESCRIPTION
"Data value."
::= { dataArray15 226 }

dataValue15_227 OBJECT-TYPE
SYNTAX INTEGER
MAX-ACCESS read-write
STATUS current
DESCRIPTION
"Data value."
::= { dataArray15 227 }

dataValue15_228 OBJECT-TYPE
SYNTAX INTEGER
MAX-ACCESS read-write
STATUS current
DESCRIPTION
"Data value."
::= { dataArray15 228 }

dataValue15_229 OBJECT-TYPE
SYNTAX INTEGER
MAX-ACCESS read-write
STATUS current
DESCRIPTION
"Data value."
::= { dataArray15 229 }

dataValue15_230 OBJECT-TYPE
SYNTAX INTEGER
MAX-ACCESS read-write
STATUS current
DESCRIPTION
"Data value."
::= { dataArray15 230 }

dataValue15_231 OBJECT-TYPE
SYNTAX INTEGER
MAX-ACCESS read-write
STATUS current
DESCRIPTION
"Data value."
::= { dataArray15 231 }

dataValue15_232 OBJECT-TYPE
SYNTAX INTEGER
MAX-ACCESS read-write
STATUS current
DESCRIPTION
"Data value."
::= { dataArray15 232 }

dataValue15_233 OBJECT-TYPE
SYNTAX INTEGER
MAX-ACCESS read-write
STATUS current
DESCRIPTION
"Data value."
::= { dataArray15 233 }

dataValue15_234 OBJECT-TYPE
SYNTAX INTEGER
MAX-ACCESS read-write
STATUS current
DESCRIPTION
"Data value."
::= { dataArray15 234 }

dataValue15_235 OBJECT-TYPE
SYNTAX INTEGER
MAX-ACCESS read-write
STATUS current
DESCRIPTION
"Data value."
::= { dataArray15 235 }

dataValue15_236 OBJECT-TYPE
SYNTAX INTEGER
MAX-ACCESS read-write
STATUS current
DESCRIPTION
"Data value."
::= { dataArray15 236 }

dataValue15_237 OBJECT-TYPE
SYNTAX INTEGER
MAX-ACCESS read-write
STATUS current
DESCRIPTION
"Data value."
::= { dataArray15 237 }

dataValue15_238 OBJECT-TYPE
SYNTAX INTEGER
MAX-ACCESS read-write
STATUS current
DESCRIPTION
"Data value."
::= { dataArray15 238 }

dataValue15_239 OBJECT-TYPE
SYNTAX INTEGER
MAX-ACCESS read-write
STATUS current
DESCRIPTION
"Data value."
::= { dataArray15 239 }

dataValue15_240 OBJECT-TYPE
SYNTAX INTEGER
MAX-ACCESS read-write
STATUS current
DESCRIPTION
"Data value."
::= { dataArray15 240 }

dataValue15_241 OBJECT-TYPE
SYNTAX INTEGER
MAX-ACCESS read-write
STATUS current
DESCRIPTION
"Data value."
::= { dataArray15 241 }

dataValue15_242 OBJECT-TYPE
SYNTAX INTEGER
MAX-ACCESS read-write
STATUS current
DESCRIPTION
"Data value."
::= { dataArray15 242 }

dataValue15_243 OBJECT-TYPE
SYNTAX INTEGER
MAX-ACCESS read-write
STATUS current
DESCRIPTION
"Data value."
::= { dataArray15 243 }

dataValue15_244 OBJECT-TYPE
SYNTAX INTEGER
MAX-ACCESS read-write
STATUS current
DESCRIPTION
"Data value."
::= { dataArray15 244 }

dataValue15_245 OBJECT-TYPE
SYNTAX INTEGER
MAX-ACCESS read-write
STATUS current
DESCRIPTION
"Data value."
::= { dataArray15 245 }

dataValue15_246 OBJECT-TYPE
SYNTAX INTEGER
MAX-ACCESS read-write
STATUS current
DESCRIPTION
"Data value."
::= { dataArray15 246 }

dataValue15_247 OBJECT-TYPE
SYNTAX INTEGER
MAX-ACCESS read-write
STATUS current
DESCRIPTION
"Data value."
::= { dataArray15 247 }

dataValue15_248 OBJECT-TYPE
SYNTAX INTEGER
MAX-ACCESS read-write
STATUS current
DESCRIPTION
"Data value."
::= { dataArray15 248 }

dataValue15_249 OBJECT-TYPE
SYNTAX INTEGER
MAX-ACCESS read-write
STATUS current
DESCRIPTION
"Data value."
::= { dataArray15 249 }

dataValue15_250 OBJECT-TYPE
SYNTAX INTEGER
MAX-ACCESS read-write
STATUS current
DESCRIPTION
"Data value."
::= { dataArray15 250 }

dataValue15_251 OBJECT-TYPE
SYNTAX INTEGER
MAX-ACCESS read-write
STATUS current
DESCRIPTION
"Data value."
::= { dataArray15 251 }

dataValue15_252 OBJECT-TYPE
SYNTAX INTEGER
MAX-ACCESS read-write
STATUS current
DESCRIPTION
"Data value."
::= { dataArray15 252 }

dataValue15_253 OBJECT-TYPE
SYNTAX INTEGER
MAX-ACCESS read-write
STATUS current
DESCRIPTION
"Data value."
::= { dataArray15 253 }

dataValue15_254 OBJECT-TYPE
SYNTAX INTEGER
MAX-ACCESS read-write
STATUS current
DESCRIPTION
"Data value."
::= { dataArray15 254 }

dataValue15_255 OBJECT-TYPE
SYNTAX INTEGER
MAX-ACCESS read-write
STATUS current
DESCRIPTION
"Data value."
::= { dataArray15 255 }

dataValue15_256 OBJECT-TYPE
SYNTAX INTEGER
MAX-ACCESS read-write
STATUS current
DESCRIPTION
"Data value."
::= { dataArray15 256 }

dataValue15_257 OBJECT-TYPE
SYNTAX INTEGER
MAX-ACCESS read-write
STATUS current
DESCRIPTION
"Data value."
::= { dataArray15 257 }

dataValue15_258 OBJECT-TYPE
SYNTAX INTEGER
MAX-ACCESS read-write
STATUS current
DESCRIPTION
"Data value."
::= { dataArray15 258 }

dataValue15_259 OBJECT-TYPE
SYNTAX INTEGER
MAX-ACCESS read-write
STATUS current
DESCRIPTION
"Data value."
::= { dataArray15 259 }

dataValue15_260 OBJECT-TYPE
SYNTAX INTEGER
MAX-ACCESS read-write
STATUS current
DESCRIPTION
"Data value."
::= { dataArray15 260 }

dataValue15_261 OBJECT-TYPE
SYNTAX INTEGER
MAX-ACCESS read-write
STATUS current
DESCRIPTION
"Data value."
::= { dataArray15 261 }

dataValue15_262 OBJECT-TYPE
SYNTAX INTEGER
MAX-ACCESS read-write
STATUS current
DESCRIPTION
"Data value."
::= { dataArray15 262 }

dataValue15_263 OBJECT-TYPE
SYNTAX INTEGER
MAX-ACCESS read-write
STATUS current
DESCRIPTION
"Data value."
::= { dataArray15 263 }

dataValue15_264 OBJECT-TYPE
SYNTAX INTEGER
MAX-ACCESS read-write
STATUS current
DESCRIPTION
"Data value."
::= { dataArray15 264 }

dataValue15_265 OBJECT-TYPE
SYNTAX INTEGER
MAX-ACCESS read-write
STATUS current
DESCRIPTION
"Data value."
::= { dataArray15 265 }

dataValue15_266 OBJECT-TYPE
SYNTAX INTEGER
MAX-ACCESS read-write
STATUS current
DESCRIPTION
"Data value."
::= { dataArray15 266 }

dataValue15_267 OBJECT-TYPE
SYNTAX INTEGER
MAX-ACCESS read-write
STATUS current
DESCRIPTION
"Data value."
::= { dataArray15 267 }

dataValue15_268 OBJECT-TYPE
SYNTAX INTEGER
MAX-ACCESS read-write
STATUS current
DESCRIPTION
"Data value."
::= { dataArray15 268 }

dataValue15_269 OBJECT-TYPE
SYNTAX INTEGER
MAX-ACCESS read-write
STATUS current
DESCRIPTION
"Data value."
::= { dataArray15 269 }

dataValue15_270 OBJECT-TYPE
SYNTAX INTEGER
MAX-ACCESS read-write
STATUS current
DESCRIPTION
"Data value."
::= { dataArray15 270 }

dataValue15_271 OBJECT-TYPE
SYNTAX INTEGER
MAX-ACCESS read-write
STATUS current
DESCRIPTION
"Data value."
::= { dataArray15 271 }

dataValue15_272 OBJECT-TYPE
SYNTAX INTEGER
MAX-ACCESS read-write
STATUS current
DESCRIPTION
"Data value."
::= { dataArray15 272 }

dataValue15_273 OBJECT-TYPE
SYNTAX INTEGER
MAX-ACCESS read-write
STATUS current
DESCRIPTION
"Data value."
::= { dataArray15 273 }

dataValue15_274 OBJECT-TYPE
SYNTAX INTEGER
MAX-ACCESS read-write
STATUS current
DESCRIPTION
"Data value."
::= { dataArray15 274 }

dataValue15_275 OBJECT-TYPE
SYNTAX INTEGER
MAX-ACCESS read-write
STATUS current
DESCRIPTION
"Data value."
::= { dataArray15 275 }

dataValue15_276 OBJECT-TYPE
SYNTAX INTEGER
MAX-ACCESS read-write
STATUS current
DESCRIPTION
"Data value."
::= { dataArray15 276 }

dataValue15_277 OBJECT-TYPE
SYNTAX INTEGER
MAX-ACCESS read-write
STATUS current
DESCRIPTION
"Data value."
::= { dataArray15 277 }

dataValue15_278 OBJECT-TYPE
SYNTAX INTEGER
MAX-ACCESS read-write
STATUS current
DESCRIPTION
"Data value."
::= { dataArray15 278 }

dataValue15_279 OBJECT-TYPE
SYNTAX INTEGER
MAX-ACCESS read-write
STATUS current
DESCRIPTION
"Data value."
::= { dataArray15 279 }

dataValue15_280 OBJECT-TYPE
SYNTAX INTEGER
MAX-ACCESS read-write
STATUS current
DESCRIPTION
"Data value."
::= { dataArray15 280 }

dataValue15_281 OBJECT-TYPE
SYNTAX INTEGER
MAX-ACCESS read-write
STATUS current
DESCRIPTION
"Data value."
::= { dataArray15 281 }

dataValue15_282 OBJECT-TYPE
SYNTAX INTEGER
MAX-ACCESS read-write
STATUS current
DESCRIPTION
"Data value."
::= { dataArray15 282 }

dataValue15_283 OBJECT-TYPE
SYNTAX INTEGER
MAX-ACCESS read-write
STATUS current
DESCRIPTION
"Data value."
::= { dataArray15 283 }

dataValue15_284 OBJECT-TYPE
SYNTAX INTEGER
MAX-ACCESS read-write
STATUS current
DESCRIPTION
"Data value."
::= { dataArray15 284 }

dataValue15_285 OBJECT-TYPE
SYNTAX INTEGER
MAX-ACCESS read-write
STATUS current
DESCRIPTION
"Data value."
::= { dataArray15 285 }

dataValue15_286 OBJECT-TYPE
SYNTAX INTEGER
MAX-ACCESS read-write
STATUS current
DESCRIPTION
"Data value."
::= { dataArray15 286 }

dataValue15_287 OBJECT-TYPE
SYNTAX INTEGER
MAX-ACCESS read-write
STATUS current
DESCRIPTION
"Data value."
::= { dataArray15 287 }

dataValue15_288 OBJECT-TYPE
SYNTAX INTEGER
MAX-ACCESS read-write
STATUS current
DESCRIPTION
"Data value."
::= { dataArray15 288 }

dataValue15_289 OBJECT-TYPE
SYNTAX INTEGER
MAX-ACCESS read-write
STATUS current
DESCRIPTION
"Data value."
::= { dataArray15 289 }

dataValue15_290 OBJECT-TYPE
SYNTAX INTEGER
MAX-ACCESS read-write
STATUS current
DESCRIPTION
"Data value."
::= { dataArray15 290 }

dataValue15_291 OBJECT-TYPE
SYNTAX INTEGER
MAX-ACCESS read-write
STATUS current
DESCRIPTION
"Data value."
::= { dataArray15 291 }

dataValue15_292 OBJECT-TYPE
SYNTAX INTEGER
MAX-ACCESS read-write
STATUS current
DESCRIPTION
"Data value."
::= { dataArray15 292 }

dataValue15_293 OBJECT-TYPE
SYNTAX INTEGER
MAX-ACCESS read-write
STATUS current
DESCRIPTION
"Data value."
::= { dataArray15 293 }

dataValue15_294 OBJECT-TYPE
SYNTAX INTEGER
MAX-ACCESS read-write
STATUS current
DESCRIPTION
"Data value."
::= { dataArray15 294 }

dataValue15_295 OBJECT-TYPE
SYNTAX INTEGER
MAX-ACCESS read-write
STATUS current
DESCRIPTION
"Data value."
::= { dataArray15 295 }

dataValue15_296 OBJECT-TYPE
SYNTAX INTEGER
MAX-ACCESS read-write
STATUS current
DESCRIPTION
"Data value."
::= { dataArray15 296 }

dataValue15_297 OBJECT-TYPE
SYNTAX INTEGER
MAX-ACCESS read-write
STATUS current
DESCRIPTION
"Data value."
::= { dataArray15 297 }

dataValue15_298 OBJECT-TYPE
SYNTAX INTEGER
MAX-ACCESS read-write
STATUS current
DESCRIPTION
"Data value."
::= { dataArray15 298 }

dataValue15_299 OBJECT-TYPE
SYNTAX INTEGER
MAX-ACCESS read-write
STATUS current
DESCRIPTION
"Data value."
::= { dataArray15 299 }

dataValue15_300 OBJECT-TYPE
SYNTAX INTEGER
MAX-ACCESS read-write
STATUS current
DESCRIPTION
"Data value."
::= { dataArray15 300 }

dataValue15_301 OBJECT-TYPE
SYNTAX INTEGER
MAX-ACCESS read-write
STATUS current
DESCRIPTION
"Data value."
::= { dataArray15 301 }

dataValue15_302 OBJECT-TYPE
SYNTAX INTEGER
MAX-ACCESS read-write
STATUS current
DESCRIPTION
"Data value."
::= { dataArray15 302 }

dataValue15_303 OBJECT-TYPE
SYNTAX INTEGER
MAX-ACCESS read-write
STATUS current
DESCRIPTION
"Data value."
::= { dataArray15 303 }

dataValue15_304 OBJECT-TYPE
SYNTAX INTEGER
MAX-ACCESS read-write
STATUS current
DESCRIPTION
"Data value."
::= { dataArray15 304 }

dataValue15_305 OBJECT-TYPE
SYNTAX INTEGER
MAX-ACCESS read-write
STATUS current
DESCRIPTION
"Data value."
::= { dataArray15 305 }

dataValue15_306 OBJECT-TYPE
SYNTAX INTEGER
MAX-ACCESS read-write
STATUS current
DESCRIPTION
"Data value."
::= { dataArray15 306 }

dataValue15_307 OBJECT-TYPE
SYNTAX INTEGER
MAX-ACCESS read-write
STATUS current
DESCRIPTION
"Data value."
::= { dataArray15 307 }

dataValue15_308 OBJECT-TYPE
SYNTAX INTEGER
MAX-ACCESS read-write
STATUS current
DESCRIPTION
"Data value."
::= { dataArray15 308 }

dataValue15_309 OBJECT-TYPE
SYNTAX INTEGER
MAX-ACCESS read-write
STATUS current
DESCRIPTION
"Data value."
::= { dataArray15 309 }

dataValue15_310 OBJECT-TYPE
SYNTAX INTEGER
MAX-ACCESS read-write
STATUS current
DESCRIPTION
"Data value."
::= { dataArray15 310 }

dataValue15_311 OBJECT-TYPE
SYNTAX INTEGER
MAX-ACCESS read-write
STATUS current
DESCRIPTION
"Data value."
::= { dataArray15 311 }

dataValue15_312 OBJECT-TYPE
SYNTAX INTEGER
MAX-ACCESS read-write
STATUS current
DESCRIPTION
"Data value."
::= { dataArray15 312 }

dataValue15_313 OBJECT-TYPE
SYNTAX INTEGER
MAX-ACCESS read-write
STATUS current
DESCRIPTION
"Data value."
::= { dataArray15 313 }

dataValue15_314 OBJECT-TYPE
SYNTAX INTEGER
MAX-ACCESS read-write
STATUS current
DESCRIPTION
"Data value."
::= { dataArray15 314 }

dataValue15_315 OBJECT-TYPE
SYNTAX INTEGER
MAX-ACCESS read-write
STATUS current
DESCRIPTION
"Data value."
::= { dataArray15 315 }

dataValue15_316 OBJECT-TYPE
SYNTAX INTEGER
MAX-ACCESS read-write
STATUS current
DESCRIPTION
"Data value."
::= { dataArray15 316 }

dataValue15_317 OBJECT-TYPE
SYNTAX INTEGER
MAX-ACCESS read-write
STATUS current
DESCRIPTION
"Data value."
::= { dataArray15 317 }

dataValue15_318 OBJECT-TYPE
SYNTAX INTEGER
MAX-ACCESS read-write
STATUS current
DESCRIPTION
"Data value."
::= { dataArray15 318 }

dataValue15_319 OBJECT-TYPE
SYNTAX INTEGER
MAX-ACCESS read-write
STATUS current
DESCRIPTION
"Data value."
::= { dataArray15 319 }

dataValue15_320 OBJECT-TYPE
SYNTAX INTEGER
MAX-ACCESS read-write
STATUS current
DESCRIPTION
"Data value."
::= { dataArray15 320 }

dataValue15_321 OBJECT-TYPE
SYNTAX INTEGER
MAX-ACCESS read-write
STATUS current
DESCRIPTION
"Data value."
::= { dataArray15 321 }

dataValue15_322 OBJECT-TYPE
SYNTAX INTEGER
MAX-ACCESS read-write
STATUS current
DESCRIPTION
"Data value."
::= { dataArray15 322 }

dataValue15_323 OBJECT-TYPE
SYNTAX INTEGER
MAX-ACCESS read-write
STATUS current
DESCRIPTION
"Data value."
::= { dataArray15 323 }

dataValue15_324 OBJECT-TYPE
SYNTAX INTEGER
MAX-ACCESS read-write
STATUS current
DESCRIPTION
"Data value."
::= { dataArray15 324 }

dataValue15_325 OBJECT-TYPE
SYNTAX INTEGER
MAX-ACCESS read-write
STATUS current
DESCRIPTION
"Data value."
::= { dataArray15 325 }

dataValue15_326 OBJECT-TYPE
SYNTAX INTEGER
MAX-ACCESS read-write
STATUS current
DESCRIPTION
"Data value."
::= { dataArray15 326 }

dataValue15_327 OBJECT-TYPE
SYNTAX INTEGER
MAX-ACCESS read-write
STATUS current
DESCRIPTION
"Data value."
::= { dataArray15 327 }

dataValue15_328 OBJECT-TYPE
SYNTAX INTEGER
MAX-ACCESS read-write
STATUS current
DESCRIPTION
"Data value."
::= { dataArray15 328 }

dataValue15_329 OBJECT-TYPE
SYNTAX INTEGER
MAX-ACCESS read-write
STATUS current
DESCRIPTION
"Data value."
::= { dataArray15 329 }

dataValue15_330 OBJECT-TYPE
SYNTAX INTEGER
MAX-ACCESS read-write
STATUS current
DESCRIPTION
"Data value."
::= { dataArray15 330 }

dataValue15_331 OBJECT-TYPE
SYNTAX INTEGER
MAX-ACCESS read-write
STATUS current
DESCRIPTION
"Data value."
::= { dataArray15 331 }

dataValue15_332 OBJECT-TYPE
SYNTAX INTEGER
MAX-ACCESS read-write
STATUS current
DESCRIPTION
"Data value."
::= { dataArray15 332 }

dataValue15_333 OBJECT-TYPE
SYNTAX INTEGER
MAX-ACCESS read-write
STATUS current
DESCRIPTION
"Data value."
::= { dataArray15 333 }

dataValue15_334 OBJECT-TYPE
SYNTAX INTEGER
MAX-ACCESS read-write
STATUS current
DESCRIPTION
"Data value."
::= { dataArray15 334 }

dataValue15_335 OBJECT-TYPE
SYNTAX INTEGER
MAX-ACCESS read-write
STATUS current
DESCRIPTION
"Data value."
::= { dataArray15 335 }

dataValue15_336 OBJECT-TYPE
SYNTAX INTEGER
MAX-ACCESS read-write
STATUS current
DESCRIPTION
"Data value."
::= { dataArray15 336 }

dataValue15_337 OBJECT-TYPE
SYNTAX INTEGER
MAX-ACCESS read-write
STATUS current
DESCRIPTION
"Data value."
::= { dataArray15 337 }

dataValue15_338 OBJECT-TYPE
SYNTAX INTEGER
MAX-ACCESS read-write
STATUS current
DESCRIPTION
"Data value."
::= { dataArray15 338 }

dataValue15_339 OBJECT-TYPE
SYNTAX INTEGER
MAX-ACCESS read-write
STATUS current
DESCRIPTION
"Data value."
::= { dataArray15 339 }

dataValue15_340 OBJECT-TYPE
SYNTAX INTEGER
MAX-ACCESS read-write
STATUS current
DESCRIPTION
"Data value."
::= { dataArray15 340 }

dataValue15_341 OBJECT-TYPE
SYNTAX INTEGER
MAX-ACCESS read-write
STATUS current
DESCRIPTION
"Data value."
::= { dataArray15 341 }

dataValue15_342 OBJECT-TYPE
SYNTAX INTEGER
MAX-ACCESS read-write
STATUS current
DESCRIPTION
"Data value."
::= { dataArray15 342 }

dataValue15_343 OBJECT-TYPE
SYNTAX INTEGER
MAX-ACCESS read-write
STATUS current
DESCRIPTION
"Data value."
::= { dataArray15 343 }

dataValue15_344 OBJECT-TYPE
SYNTAX INTEGER
MAX-ACCESS read-write
STATUS current
DESCRIPTION
"Data value."
::= { dataArray15 344 }

dataValue15_345 OBJECT-TYPE
SYNTAX INTEGER
MAX-ACCESS read-write
STATUS current
DESCRIPTION
"Data value."
::= { dataArray15 345 }

dataValue15_346 OBJECT-TYPE
SYNTAX INTEGER
MAX-ACCESS read-write
STATUS current
DESCRIPTION
"Data value."
::= { dataArray15 346 }

dataValue15_347 OBJECT-TYPE
SYNTAX INTEGER
MAX-ACCESS read-write
STATUS current
DESCRIPTION
"Data value."
::= { dataArray15 347 }

dataValue15_348 OBJECT-TYPE
SYNTAX INTEGER
MAX-ACCESS read-write
STATUS current
DESCRIPTION
"Data value."
::= { dataArray15 348 }

dataValue15_349 OBJECT-TYPE
SYNTAX INTEGER
MAX-ACCESS read-write
STATUS current
DESCRIPTION
"Data value."
::= { dataArray15 349 }

dataValue15_350 OBJECT-TYPE
SYNTAX INTEGER
MAX-ACCESS read-write
STATUS current
DESCRIPTION
"Data value."
::= { dataArray15 350 }

dataValue15_351 OBJECT-TYPE
SYNTAX INTEGER
MAX-ACCESS read-write
STATUS current
DESCRIPTION
"Data value."
::= { dataArray15 351 }

dataValue15_352 OBJECT-TYPE
SYNTAX INTEGER
MAX-ACCESS read-write
STATUS current
DESCRIPTION
"Data value."
::= { dataArray15 352 }

dataValue15_353 OBJECT-TYPE
SYNTAX INTEGER
MAX-ACCESS read-write
STATUS current
DESCRIPTION
"Data value."
::= { dataArray15 353 }

dataValue15_354 OBJECT-TYPE
SYNTAX INTEGER
MAX-ACCESS read-write
STATUS current
DESCRIPTION
"Data value."
::= { dataArray15 354 }

dataValue15_355 OBJECT-TYPE
SYNTAX INTEGER
MAX-ACCESS read-write
STATUS current
DESCRIPTION
"Data value."
::= { dataArray15 355 }

dataValue15_356 OBJECT-TYPE
SYNTAX INTEGER
MAX-ACCESS read-write
STATUS current
DESCRIPTION
"Data value."
::= { dataArray15 356 }

dataValue15_357 OBJECT-TYPE
SYNTAX INTEGER
MAX-ACCESS read-write
STATUS current
DESCRIPTION
"Data value."
::= { dataArray15 357 }

dataValue15_358 OBJECT-TYPE
SYNTAX INTEGER
MAX-ACCESS read-write
STATUS current
DESCRIPTION
"Data value."
::= { dataArray15 358 }

dataValue15_359 OBJECT-TYPE
SYNTAX INTEGER
MAX-ACCESS read-write
STATUS current
DESCRIPTION
"Data value."
::= { dataArray15 359 }

dataValue15_360 OBJECT-TYPE
SYNTAX INTEGER
MAX-ACCESS read-write
STATUS current
DESCRIPTION
"Data value."
::= { dataArray15 360 }

dataValue15_361 OBJECT-TYPE
SYNTAX INTEGER
MAX-ACCESS read-write
STATUS current
DESCRIPTION
"Data value."
::= { dataArray15 361 }

dataValue15_362 OBJECT-TYPE
SYNTAX INTEGER
MAX-ACCESS read-write
STATUS current
DESCRIPTION
"Data value."
::= { dataArray15 362 }

dataValue15_363 OBJECT-TYPE
SYNTAX INTEGER
MAX-ACCESS read-write
STATUS current
DESCRIPTION
"Data value."
::= { dataArray15 363 }

dataValue15_364 OBJECT-TYPE
SYNTAX INTEGER
MAX-ACCESS read-write
STATUS current
DESCRIPTION
"Data value."
::= { dataArray15 364 }

dataValue15_365 OBJECT-TYPE
SYNTAX INTEGER
MAX-ACCESS read-write
STATUS current
DESCRIPTION
"Data value."
::= { dataArray15 365 }

dataValue15_366 OBJECT-TYPE
SYNTAX INTEGER
MAX-ACCESS read-write
STATUS current
DESCRIPTION
"Data value."
::= { dataArray15 366 }

dataValue15_367 OBJECT-TYPE
SYNTAX INTEGER
MAX-ACCESS read-write
STATUS current
DESCRIPTION
"Data value."
::= { dataArray15 367 }

dataValue15_368 OBJECT-TYPE
SYNTAX INTEGER
MAX-ACCESS read-write
STATUS current
DESCRIPTION
"Data value."
::= { dataArray15 368 }

dataValue15_369 OBJECT-TYPE
SYNTAX INTEGER
MAX-ACCESS read-write
STATUS current
DESCRIPTION
"Data value."
::= { dataArray15 369 }

dataValue15_370 OBJECT-TYPE
SYNTAX INTEGER
MAX-ACCESS read-write
STATUS current
DESCRIPTION
"Data value."
::= { dataArray15 370 }

dataValue15_371 OBJECT-TYPE
SYNTAX INTEGER
MAX-ACCESS read-write
STATUS current
DESCRIPTION
"Data value."
::= { dataArray15 371 }

dataValue15_372 OBJECT-TYPE
SYNTAX INTEGER
MAX-ACCESS read-write
STATUS current
DESCRIPTION
"Data value."
::= { dataArray15 372 }

dataValue15_373 OBJECT-TYPE
SYNTAX INTEGER
MAX-ACCESS read-write
STATUS current
DESCRIPTION
"Data value."
::= { dataArray15 373 }

dataValue15_374 OBJECT-TYPE
SYNTAX INTEGER
MAX-ACCESS read-write
STATUS current
DESCRIPTION
"Data value."
::= { dataArray15 374 }

dataValue15_375 OBJECT-TYPE
SYNTAX INTEGER
MAX-ACCESS read-write
STATUS current
DESCRIPTION
"Data value."
::= { dataArray15 375 }

dataValue15_376 OBJECT-TYPE
SYNTAX INTEGER
MAX-ACCESS read-write
STATUS current
DESCRIPTION
"Data value."
::= { dataArray15 376 }

dataValue15_377 OBJECT-TYPE
SYNTAX INTEGER
MAX-ACCESS read-write
STATUS current
DESCRIPTION
"Data value."
::= { dataArray15 377 }

dataValue15_378 OBJECT-TYPE
SYNTAX INTEGER
MAX-ACCESS read-write
STATUS current
DESCRIPTION
"Data value."
::= { dataArray15 378 }

dataValue15_379 OBJECT-TYPE
SYNTAX INTEGER
MAX-ACCESS read-write
STATUS current
DESCRIPTION
"Data value."
::= { dataArray15 379 }

dataValue15_380 OBJECT-TYPE
SYNTAX INTEGER
MAX-ACCESS read-write
STATUS current
DESCRIPTION
"Data value."
::= { dataArray15 380 }

dataValue15_381 OBJECT-TYPE
SYNTAX INTEGER
MAX-ACCESS read-write
STATUS current
DESCRIPTION
"Data value."
::= { dataArray15 381 }

dataValue15_382 OBJECT-TYPE
SYNTAX INTEGER
MAX-ACCESS read-write
STATUS current
DESCRIPTION
"Data value."
::= { dataArray15 382 }

dataValue15_383 OBJECT-TYPE
SYNTAX INTEGER
MAX-ACCESS read-write
STATUS current
DESCRIPTION
"Data value."
::= { dataArray15 383 }

dataValue15_384 OBJECT-TYPE
SYNTAX INTEGER
MAX-ACCESS read-write
STATUS current
DESCRIPTION
"Data value."
::= { dataArray15 384 }

dataValue15_385 OBJECT-TYPE
SYNTAX INTEGER
MAX-ACCESS read-write
STATUS current
DESCRIPTION
"Data value."
::= { dataArray15 385 }

dataValue15_386 OBJECT-TYPE
SYNTAX INTEGER
MAX-ACCESS read-write
STATUS current
DESCRIPTION
"Data value."
::= { dataArray15 386 }

dataValue15_387 OBJECT-TYPE
SYNTAX INTEGER
MAX-ACCESS read-write
STATUS current
DESCRIPTION
"Data value."
::= { dataArray15 387 }

dataValue15_388 OBJECT-TYPE
SYNTAX INTEGER
MAX-ACCESS read-write
STATUS current
DESCRIPTION
"Data value."
::= { dataArray15 388 }

dataValue15_389 OBJECT-TYPE
SYNTAX INTEGER
MAX-ACCESS read-write
STATUS current
DESCRIPTION
"Data value."
::= { dataArray15 389 }

dataValue15_390 OBJECT-TYPE
SYNTAX INTEGER
MAX-ACCESS read-write
STATUS current
DESCRIPTION
"Data value."
::= { dataArray15 390 }

dataValue15_391 OBJECT-TYPE
SYNTAX INTEGER
MAX-ACCESS read-write
STATUS current
DESCRIPTION
"Data value."
::= { dataArray15 391 }

dataValue15_392 OBJECT-TYPE
SYNTAX INTEGER
MAX-ACCESS read-write
STATUS current
DESCRIPTION
"Data value."
::= { dataArray15 392 }

dataValue15_393 OBJECT-TYPE
SYNTAX INTEGER
MAX-ACCESS read-write
STATUS current
DESCRIPTION
"Data value."
::= { dataArray15 393 }

dataValue15_394 OBJECT-TYPE
SYNTAX INTEGER
MAX-ACCESS read-write
STATUS current
DESCRIPTION
"Data value."
::= { dataArray15 394 }

dataValue15_395 OBJECT-TYPE
SYNTAX INTEGER
MAX-ACCESS read-write
STATUS current
DESCRIPTION
"Data value."
::= { dataArray15 395 }

dataValue15_396 OBJECT-TYPE
SYNTAX INTEGER
MAX-ACCESS read-write
STATUS current
DESCRIPTION
"Data value."
::= { dataArray15 396 }

dataValue15_397 OBJECT-TYPE
SYNTAX INTEGER
MAX-ACCESS read-write
STATUS current
DESCRIPTION
"Data value."
::= { dataArray15 397 }

dataValue15_398 OBJECT-TYPE
SYNTAX INTEGER
MAX-ACCESS read-write
STATUS current
DESCRIPTION
"Data value."
::= { dataArray15 398 }

dataValue15_399 OBJECT-TYPE
SYNTAX INTEGER
MAX-ACCESS read-write
STATUS current
DESCRIPTION
"Data value."
::= { dataArray15 399 }

dataArray16 OBJECT IDENTIFIER ::= { cc08255400_v1_00a 16 }

dataValue16_0 OBJECT-TYPE
SYNTAX INTEGER
MAX-ACCESS read-write
STATUS current
DESCRIPTION
"Data value."
::= { dataArray16 0 }

dataValue16_1 OBJECT-TYPE
SYNTAX INTEGER
MAX-ACCESS read-write
STATUS current
DESCRIPTION
"Data value."
::= { dataArray16 1 }

dataValue16_2 OBJECT-TYPE
SYNTAX INTEGER
MAX-ACCESS read-write
STATUS current
DESCRIPTION
"Data value."
::= { dataArray16 2 }

dataValue16_3 OBJECT-TYPE
SYNTAX INTEGER
MAX-ACCESS read-write
STATUS current
DESCRIPTION
"Data value."
::= { dataArray16 3 }

dataValue16_4 OBJECT-TYPE
SYNTAX INTEGER
MAX-ACCESS read-write
STATUS current
DESCRIPTION
"Data value."
::= { dataArray16 4 }

dataValue16_5 OBJECT-TYPE
SYNTAX INTEGER
MAX-ACCESS read-write
STATUS current
DESCRIPTION
"Data value."
::= { dataArray16 5 }

dataValue16_6 OBJECT-TYPE
SYNTAX INTEGER
MAX-ACCESS read-write
STATUS current
DESCRIPTION
"Data value."
::= { dataArray16 6 }

dataValue16_7 OBJECT-TYPE
SYNTAX INTEGER
MAX-ACCESS read-write
STATUS current
DESCRIPTION
"Data value."
::= { dataArray16 7 }

dataValue16_8 OBJECT-TYPE
SYNTAX INTEGER
MAX-ACCESS read-write
STATUS current
DESCRIPTION
"Data value."
::= { dataArray16 8 }

dataValue16_9 OBJECT-TYPE
SYNTAX INTEGER
MAX-ACCESS read-write
STATUS current
DESCRIPTION
"Data value."
::= { dataArray16 9 }

dataValue16_10 OBJECT-TYPE
SYNTAX INTEGER
MAX-ACCESS read-write
STATUS current
DESCRIPTION
"Data value."
::= { dataArray16 10 }

dataValue16_11 OBJECT-TYPE
SYNTAX INTEGER
MAX-ACCESS read-write
STATUS current
DESCRIPTION
"Data value."
::= { dataArray16 11 }

dataValue16_12 OBJECT-TYPE
SYNTAX INTEGER
MAX-ACCESS read-write
STATUS current
DESCRIPTION
"Data value."
::= { dataArray16 12 }

dataValue16_13 OBJECT-TYPE
SYNTAX INTEGER
MAX-ACCESS read-write
STATUS current
DESCRIPTION
"Data value."
::= { dataArray16 13 }

dataValue16_14 OBJECT-TYPE
SYNTAX INTEGER
MAX-ACCESS read-write
STATUS current
DESCRIPTION
"Data value."
::= { dataArray16 14 }

dataValue16_15 OBJECT-TYPE
SYNTAX INTEGER
MAX-ACCESS read-write
STATUS current
DESCRIPTION
"Data value."
::= { dataArray16 15 }

dataValue16_16 OBJECT-TYPE
SYNTAX INTEGER
MAX-ACCESS read-write
STATUS current
DESCRIPTION
"Data value."
::= { dataArray16 16 }

dataValue16_17 OBJECT-TYPE
SYNTAX INTEGER
MAX-ACCESS read-write
STATUS current
DESCRIPTION
"Data value."
::= { dataArray16 17 }

dataValue16_18 OBJECT-TYPE
SYNTAX INTEGER
MAX-ACCESS read-write
STATUS current
DESCRIPTION
"Data value."
::= { dataArray16 18 }

dataValue16_19 OBJECT-TYPE
SYNTAX INTEGER
MAX-ACCESS read-write
STATUS current
DESCRIPTION
"Data value."
::= { dataArray16 19 }

dataValue16_20 OBJECT-TYPE
SYNTAX INTEGER
MAX-ACCESS read-write
STATUS current
DESCRIPTION
"Data value."
::= { dataArray16 20 }

dataValue16_21 OBJECT-TYPE
SYNTAX INTEGER
MAX-ACCESS read-write
STATUS current
DESCRIPTION
"Data value."
::= { dataArray16 21 }

dataValue16_22 OBJECT-TYPE
SYNTAX INTEGER
MAX-ACCESS read-write
STATUS current
DESCRIPTION
"Data value."
::= { dataArray16 22 }

dataValue16_23 OBJECT-TYPE
SYNTAX INTEGER
MAX-ACCESS read-write
STATUS current
DESCRIPTION
"Data value."
::= { dataArray16 23 }

dataValue16_24 OBJECT-TYPE
SYNTAX INTEGER
MAX-ACCESS read-write
STATUS current
DESCRIPTION
"Data value."
::= { dataArray16 24 }

dataValue16_25 OBJECT-TYPE
SYNTAX INTEGER
MAX-ACCESS read-write
STATUS current
DESCRIPTION
"Data value."
::= { dataArray16 25 }

dataValue16_26 OBJECT-TYPE
SYNTAX INTEGER
MAX-ACCESS read-write
STATUS current
DESCRIPTION
"Data value."
::= { dataArray16 26 }

dataValue16_27 OBJECT-TYPE
SYNTAX INTEGER
MAX-ACCESS read-write
STATUS current
DESCRIPTION
"Data value."
::= { dataArray16 27 }

dataValue16_28 OBJECT-TYPE
SYNTAX INTEGER
MAX-ACCESS read-write
STATUS current
DESCRIPTION
"Data value."
::= { dataArray16 28 }

dataValue16_29 OBJECT-TYPE
SYNTAX INTEGER
MAX-ACCESS read-write
STATUS current
DESCRIPTION
"Data value."
::= { dataArray16 29 }

dataValue16_30 OBJECT-TYPE
SYNTAX INTEGER
MAX-ACCESS read-write
STATUS current
DESCRIPTION
"Data value."
::= { dataArray16 30 }

dataValue16_31 OBJECT-TYPE
SYNTAX INTEGER
MAX-ACCESS read-write
STATUS current
DESCRIPTION
"Data value."
::= { dataArray16 31 }

dataValue16_32 OBJECT-TYPE
SYNTAX INTEGER
MAX-ACCESS read-write
STATUS current
DESCRIPTION
"Data value."
::= { dataArray16 32 }

dataValue16_33 OBJECT-TYPE
SYNTAX INTEGER
MAX-ACCESS read-write
STATUS current
DESCRIPTION
"Data value."
::= { dataArray16 33 }

dataValue16_34 OBJECT-TYPE
SYNTAX INTEGER
MAX-ACCESS read-write
STATUS current
DESCRIPTION
"Data value."
::= { dataArray16 34 }

dataValue16_35 OBJECT-TYPE
SYNTAX INTEGER
MAX-ACCESS read-write
STATUS current
DESCRIPTION
"Data value."
::= { dataArray16 35 }

dataValue16_36 OBJECT-TYPE
SYNTAX INTEGER
MAX-ACCESS read-write
STATUS current
DESCRIPTION
"Data value."
::= { dataArray16 36 }

dataValue16_37 OBJECT-TYPE
SYNTAX INTEGER
MAX-ACCESS read-write
STATUS current
DESCRIPTION
"Data value."
::= { dataArray16 37 }

dataValue16_38 OBJECT-TYPE
SYNTAX INTEGER
MAX-ACCESS read-write
STATUS current
DESCRIPTION
"Data value."
::= { dataArray16 38 }

dataValue16_39 OBJECT-TYPE
SYNTAX INTEGER
MAX-ACCESS read-write
STATUS current
DESCRIPTION
"Data value."
::= { dataArray16 39 }

dataValue16_40 OBJECT-TYPE
SYNTAX INTEGER
MAX-ACCESS read-write
STATUS current
DESCRIPTION
"Data value."
::= { dataArray16 40 }

dataValue16_41 OBJECT-TYPE
SYNTAX INTEGER
MAX-ACCESS read-write
STATUS current
DESCRIPTION
"Data value."
::= { dataArray16 41 }

dataValue16_42 OBJECT-TYPE
SYNTAX INTEGER
MAX-ACCESS read-write
STATUS current
DESCRIPTION
"Data value."
::= { dataArray16 42 }

dataValue16_43 OBJECT-TYPE
SYNTAX INTEGER
MAX-ACCESS read-write
STATUS current
DESCRIPTION
"Data value."
::= { dataArray16 43 }

dataValue16_44 OBJECT-TYPE
SYNTAX INTEGER
MAX-ACCESS read-write
STATUS current
DESCRIPTION
"Data value."
::= { dataArray16 44 }

dataValue16_45 OBJECT-TYPE
SYNTAX INTEGER
MAX-ACCESS read-write
STATUS current
DESCRIPTION
"Data value."
::= { dataArray16 45 }

dataValue16_46 OBJECT-TYPE
SYNTAX INTEGER
MAX-ACCESS read-write
STATUS current
DESCRIPTION
"Data value."
::= { dataArray16 46 }

dataValue16_47 OBJECT-TYPE
SYNTAX INTEGER
MAX-ACCESS read-write
STATUS current
DESCRIPTION
"Data value."
::= { dataArray16 47 }

dataValue16_48 OBJECT-TYPE
SYNTAX INTEGER
MAX-ACCESS read-write
STATUS current
DESCRIPTION
"Data value."
::= { dataArray16 48 }

dataValue16_49 OBJECT-TYPE
SYNTAX INTEGER
MAX-ACCESS read-write
STATUS current
DESCRIPTION
"Data value."
::= { dataArray16 49 }

dataValue16_50 OBJECT-TYPE
SYNTAX INTEGER
MAX-ACCESS read-write
STATUS current
DESCRIPTION
"Data value."
::= { dataArray16 50 }

dataValue16_51 OBJECT-TYPE
SYNTAX INTEGER
MAX-ACCESS read-write
STATUS current
DESCRIPTION
"Data value."
::= { dataArray16 51 }

dataValue16_52 OBJECT-TYPE
SYNTAX INTEGER
MAX-ACCESS read-write
STATUS current
DESCRIPTION
"Data value."
::= { dataArray16 52 }

dataValue16_53 OBJECT-TYPE
SYNTAX INTEGER
MAX-ACCESS read-write
STATUS current
DESCRIPTION
"Data value."
::= { dataArray16 53 }

dataValue16_54 OBJECT-TYPE
SYNTAX INTEGER
MAX-ACCESS read-write
STATUS current
DESCRIPTION
"Data value."
::= { dataArray16 54 }

dataValue16_55 OBJECT-TYPE
SYNTAX INTEGER
MAX-ACCESS read-write
STATUS current
DESCRIPTION
"Data value."
::= { dataArray16 55 }

dataValue16_56 OBJECT-TYPE
SYNTAX INTEGER
MAX-ACCESS read-write
STATUS current
DESCRIPTION
"Data value."
::= { dataArray16 56 }

dataValue16_57 OBJECT-TYPE
SYNTAX INTEGER
MAX-ACCESS read-write
STATUS current
DESCRIPTION
"Data value."
::= { dataArray16 57 }

dataValue16_58 OBJECT-TYPE
SYNTAX INTEGER
MAX-ACCESS read-write
STATUS current
DESCRIPTION
"Data value."
::= { dataArray16 58 }

dataValue16_59 OBJECT-TYPE
SYNTAX INTEGER
MAX-ACCESS read-write
STATUS current
DESCRIPTION
"Data value."
::= { dataArray16 59 }

dataValue16_60 OBJECT-TYPE
SYNTAX INTEGER
MAX-ACCESS read-write
STATUS current
DESCRIPTION
"Data value."
::= { dataArray16 60 }

dataValue16_61 OBJECT-TYPE
SYNTAX INTEGER
MAX-ACCESS read-write
STATUS current
DESCRIPTION
"Data value."
::= { dataArray16 61 }

dataValue16_62 OBJECT-TYPE
SYNTAX INTEGER
MAX-ACCESS read-write
STATUS current
DESCRIPTION
"Data value."
::= { dataArray16 62 }

dataValue16_63 OBJECT-TYPE
SYNTAX INTEGER
MAX-ACCESS read-write
STATUS current
DESCRIPTION
"Data value."
::= { dataArray16 63 }

dataValue16_64 OBJECT-TYPE
SYNTAX INTEGER
MAX-ACCESS read-write
STATUS current
DESCRIPTION
"Data value."
::= { dataArray16 64 }

dataValue16_65 OBJECT-TYPE
SYNTAX INTEGER
MAX-ACCESS read-write
STATUS current
DESCRIPTION
"Data value."
::= { dataArray16 65 }

dataValue16_66 OBJECT-TYPE
SYNTAX INTEGER
MAX-ACCESS read-write
STATUS current
DESCRIPTION
"Data value."
::= { dataArray16 66 }

dataValue16_67 OBJECT-TYPE
SYNTAX INTEGER
MAX-ACCESS read-write
STATUS current
DESCRIPTION
"Data value."
::= { dataArray16 67 }

dataValue16_68 OBJECT-TYPE
SYNTAX INTEGER
MAX-ACCESS read-write
STATUS current
DESCRIPTION
"Data value."
::= { dataArray16 68 }

dataValue16_69 OBJECT-TYPE
SYNTAX INTEGER
MAX-ACCESS read-write
STATUS current
DESCRIPTION
"Data value."
::= { dataArray16 69 }

dataValue16_70 OBJECT-TYPE
SYNTAX INTEGER
MAX-ACCESS read-write
STATUS current
DESCRIPTION
"Data value."
::= { dataArray16 70 }

dataValue16_71 OBJECT-TYPE
SYNTAX INTEGER
MAX-ACCESS read-write
STATUS current
DESCRIPTION
"Data value."
::= { dataArray16 71 }

dataValue16_72 OBJECT-TYPE
SYNTAX INTEGER
MAX-ACCESS read-write
STATUS current
DESCRIPTION
"Data value."
::= { dataArray16 72 }

dataValue16_73 OBJECT-TYPE
SYNTAX INTEGER
MAX-ACCESS read-write
STATUS current
DESCRIPTION
"Data value."
::= { dataArray16 73 }

dataValue16_74 OBJECT-TYPE
SYNTAX INTEGER
MAX-ACCESS read-write
STATUS current
DESCRIPTION
"Data value."
::= { dataArray16 74 }

dataValue16_75 OBJECT-TYPE
SYNTAX INTEGER
MAX-ACCESS read-write
STATUS current
DESCRIPTION
"Data value."
::= { dataArray16 75 }

dataValue16_76 OBJECT-TYPE
SYNTAX INTEGER
MAX-ACCESS read-write
STATUS current
DESCRIPTION
"Data value."
::= { dataArray16 76 }

dataValue16_77 OBJECT-TYPE
SYNTAX INTEGER
MAX-ACCESS read-write
STATUS current
DESCRIPTION
"Data value."
::= { dataArray16 77 }

dataValue16_78 OBJECT-TYPE
SYNTAX INTEGER
MAX-ACCESS read-write
STATUS current
DESCRIPTION
"Data value."
::= { dataArray16 78 }

dataValue16_79 OBJECT-TYPE
SYNTAX INTEGER
MAX-ACCESS read-write
STATUS current
DESCRIPTION
"Data value."
::= { dataArray16 79 }

dataValue16_80 OBJECT-TYPE
SYNTAX INTEGER
MAX-ACCESS read-write
STATUS current
DESCRIPTION
"Data value."
::= { dataArray16 80 }

dataValue16_81 OBJECT-TYPE
SYNTAX INTEGER
MAX-ACCESS read-write
STATUS current
DESCRIPTION
"Data value."
::= { dataArray16 81 }

dataValue16_82 OBJECT-TYPE
SYNTAX INTEGER
MAX-ACCESS read-write
STATUS current
DESCRIPTION
"Data value."
::= { dataArray16 82 }

dataValue16_83 OBJECT-TYPE
SYNTAX INTEGER
MAX-ACCESS read-write
STATUS current
DESCRIPTION
"Data value."
::= { dataArray16 83 }

dataValue16_84 OBJECT-TYPE
SYNTAX INTEGER
MAX-ACCESS read-write
STATUS current
DESCRIPTION
"Data value."
::= { dataArray16 84 }

dataValue16_85 OBJECT-TYPE
SYNTAX INTEGER
MAX-ACCESS read-write
STATUS current
DESCRIPTION
"Data value."
::= { dataArray16 85 }

dataValue16_86 OBJECT-TYPE
SYNTAX INTEGER
MAX-ACCESS read-write
STATUS current
DESCRIPTION
"Data value."
::= { dataArray16 86 }

dataValue16_87 OBJECT-TYPE
SYNTAX INTEGER
MAX-ACCESS read-write
STATUS current
DESCRIPTION
"Data value."
::= { dataArray16 87 }

dataValue16_88 OBJECT-TYPE
SYNTAX INTEGER
MAX-ACCESS read-write
STATUS current
DESCRIPTION
"Data value."
::= { dataArray16 88 }

dataValue16_89 OBJECT-TYPE
SYNTAX INTEGER
MAX-ACCESS read-write
STATUS current
DESCRIPTION
"Data value."
::= { dataArray16 89 }

dataValue16_90 OBJECT-TYPE
SYNTAX INTEGER
MAX-ACCESS read-write
STATUS current
DESCRIPTION
"Data value."
::= { dataArray16 90 }

dataValue16_91 OBJECT-TYPE
SYNTAX INTEGER
MAX-ACCESS read-write
STATUS current
DESCRIPTION
"Data value."
::= { dataArray16 91 }

dataValue16_92 OBJECT-TYPE
SYNTAX INTEGER
MAX-ACCESS read-write
STATUS current
DESCRIPTION
"Data value."
::= { dataArray16 92 }

dataValue16_93 OBJECT-TYPE
SYNTAX INTEGER
MAX-ACCESS read-write
STATUS current
DESCRIPTION
"Data value."
::= { dataArray16 93 }

dataValue16_94 OBJECT-TYPE
SYNTAX INTEGER
MAX-ACCESS read-write
STATUS current
DESCRIPTION
"Data value."
::= { dataArray16 94 }

dataValue16_95 OBJECT-TYPE
SYNTAX INTEGER
MAX-ACCESS read-write
STATUS current
DESCRIPTION
"Data value."
::= { dataArray16 95 }

dataValue16_96 OBJECT-TYPE
SYNTAX INTEGER
MAX-ACCESS read-write
STATUS current
DESCRIPTION
"Data value."
::= { dataArray16 96 }

dataValue16_97 OBJECT-TYPE
SYNTAX INTEGER
MAX-ACCESS read-write
STATUS current
DESCRIPTION
"Data value."
::= { dataArray16 97 }

dataValue16_98 OBJECT-TYPE
SYNTAX INTEGER
MAX-ACCESS read-write
STATUS current
DESCRIPTION
"Data value."
::= { dataArray16 98 }

dataValue16_99 OBJECT-TYPE
SYNTAX INTEGER
MAX-ACCESS read-write
STATUS current
DESCRIPTION
"Data value."
::= { dataArray16 99 }

dataValue16_100 OBJECT-TYPE
SYNTAX INTEGER
MAX-ACCESS read-write
STATUS current
DESCRIPTION
"Data value."
::= { dataArray16 100 }

dataValue16_101 OBJECT-TYPE
SYNTAX INTEGER
MAX-ACCESS read-write
STATUS current
DESCRIPTION
"Data value."
::= { dataArray16 101 }

dataValue16_102 OBJECT-TYPE
SYNTAX INTEGER
MAX-ACCESS read-write
STATUS current
DESCRIPTION
"Data value."
::= { dataArray16 102 }

dataValue16_103 OBJECT-TYPE
SYNTAX INTEGER
MAX-ACCESS read-write
STATUS current
DESCRIPTION
"Data value."
::= { dataArray16 103 }

dataValue16_104 OBJECT-TYPE
SYNTAX INTEGER
MAX-ACCESS read-write
STATUS current
DESCRIPTION
"Data value."
::= { dataArray16 104 }

dataValue16_105 OBJECT-TYPE
SYNTAX INTEGER
MAX-ACCESS read-write
STATUS current
DESCRIPTION
"Data value."
::= { dataArray16 105 }

dataValue16_106 OBJECT-TYPE
SYNTAX INTEGER
MAX-ACCESS read-write
STATUS current
DESCRIPTION
"Data value."
::= { dataArray16 106 }

dataValue16_107 OBJECT-TYPE
SYNTAX INTEGER
MAX-ACCESS read-write
STATUS current
DESCRIPTION
"Data value."
::= { dataArray16 107 }

dataValue16_108 OBJECT-TYPE
SYNTAX INTEGER
MAX-ACCESS read-write
STATUS current
DESCRIPTION
"Data value."
::= { dataArray16 108 }

dataValue16_109 OBJECT-TYPE
SYNTAX INTEGER
MAX-ACCESS read-write
STATUS current
DESCRIPTION
"Data value."
::= { dataArray16 109 }

dataValue16_110 OBJECT-TYPE
SYNTAX INTEGER
MAX-ACCESS read-write
STATUS current
DESCRIPTION
"Data value."
::= { dataArray16 110 }

dataValue16_111 OBJECT-TYPE
SYNTAX INTEGER
MAX-ACCESS read-write
STATUS current
DESCRIPTION
"Data value."
::= { dataArray16 111 }

dataValue16_112 OBJECT-TYPE
SYNTAX INTEGER
MAX-ACCESS read-write
STATUS current
DESCRIPTION
"Data value."
::= { dataArray16 112 }

dataValue16_113 OBJECT-TYPE
SYNTAX INTEGER
MAX-ACCESS read-write
STATUS current
DESCRIPTION
"Data value."
::= { dataArray16 113 }

dataValue16_114 OBJECT-TYPE
SYNTAX INTEGER
MAX-ACCESS read-write
STATUS current
DESCRIPTION
"Data value."
::= { dataArray16 114 }

dataValue16_115 OBJECT-TYPE
SYNTAX INTEGER
MAX-ACCESS read-write
STATUS current
DESCRIPTION
"Data value."
::= { dataArray16 115 }

dataValue16_116 OBJECT-TYPE
SYNTAX INTEGER
MAX-ACCESS read-write
STATUS current
DESCRIPTION
"Data value."
::= { dataArray16 116 }

dataValue16_117 OBJECT-TYPE
SYNTAX INTEGER
MAX-ACCESS read-write
STATUS current
DESCRIPTION
"Data value."
::= { dataArray16 117 }

dataValue16_118 OBJECT-TYPE
SYNTAX INTEGER
MAX-ACCESS read-write
STATUS current
DESCRIPTION
"Data value."
::= { dataArray16 118 }

dataValue16_119 OBJECT-TYPE
SYNTAX INTEGER
MAX-ACCESS read-write
STATUS current
DESCRIPTION
"Data value."
::= { dataArray16 119 }

dataValue16_120 OBJECT-TYPE
SYNTAX INTEGER
MAX-ACCESS read-write
STATUS current
DESCRIPTION
"Data value."
::= { dataArray16 120 }

dataValue16_121 OBJECT-TYPE
SYNTAX INTEGER
MAX-ACCESS read-write
STATUS current
DESCRIPTION
"Data value."
::= { dataArray16 121 }

dataValue16_122 OBJECT-TYPE
SYNTAX INTEGER
MAX-ACCESS read-write
STATUS current
DESCRIPTION
"Data value."
::= { dataArray16 122 }

dataValue16_123 OBJECT-TYPE
SYNTAX INTEGER
MAX-ACCESS read-write
STATUS current
DESCRIPTION
"Data value."
::= { dataArray16 123 }

dataValue16_124 OBJECT-TYPE
SYNTAX INTEGER
MAX-ACCESS read-write
STATUS current
DESCRIPTION
"Data value."
::= { dataArray16 124 }

dataValue16_125 OBJECT-TYPE
SYNTAX INTEGER
MAX-ACCESS read-write
STATUS current
DESCRIPTION
"Data value."
::= { dataArray16 125 }

dataValue16_126 OBJECT-TYPE
SYNTAX INTEGER
MAX-ACCESS read-write
STATUS current
DESCRIPTION
"Data value."
::= { dataArray16 126 }

dataValue16_127 OBJECT-TYPE
SYNTAX INTEGER
MAX-ACCESS read-write
STATUS current
DESCRIPTION
"Data value."
::= { dataArray16 127 }

dataValue16_128 OBJECT-TYPE
SYNTAX INTEGER
MAX-ACCESS read-write
STATUS current
DESCRIPTION
"Data value."
::= { dataArray16 128 }

dataValue16_129 OBJECT-TYPE
SYNTAX INTEGER
MAX-ACCESS read-write
STATUS current
DESCRIPTION
"Data value."
::= { dataArray16 129 }

dataValue16_130 OBJECT-TYPE
SYNTAX INTEGER
MAX-ACCESS read-write
STATUS current
DESCRIPTION
"Data value."
::= { dataArray16 130 }

dataValue16_131 OBJECT-TYPE
SYNTAX INTEGER
MAX-ACCESS read-write
STATUS current
DESCRIPTION
"Data value."
::= { dataArray16 131 }

dataValue16_132 OBJECT-TYPE
SYNTAX INTEGER
MAX-ACCESS read-write
STATUS current
DESCRIPTION
"Data value."
::= { dataArray16 132 }

dataValue16_133 OBJECT-TYPE
SYNTAX INTEGER
MAX-ACCESS read-write
STATUS current
DESCRIPTION
"Data value."
::= { dataArray16 133 }

dataValue16_134 OBJECT-TYPE
SYNTAX INTEGER
MAX-ACCESS read-write
STATUS current
DESCRIPTION
"Data value."
::= { dataArray16 134 }

dataValue16_135 OBJECT-TYPE
SYNTAX INTEGER
MAX-ACCESS read-write
STATUS current
DESCRIPTION
"Data value."
::= { dataArray16 135 }

dataValue16_136 OBJECT-TYPE
SYNTAX INTEGER
MAX-ACCESS read-write
STATUS current
DESCRIPTION
"Data value."
::= { dataArray16 136 }

dataValue16_137 OBJECT-TYPE
SYNTAX INTEGER
MAX-ACCESS read-write
STATUS current
DESCRIPTION
"Data value."
::= { dataArray16 137 }

dataValue16_138 OBJECT-TYPE
SYNTAX INTEGER
MAX-ACCESS read-write
STATUS current
DESCRIPTION
"Data value."
::= { dataArray16 138 }

dataValue16_139 OBJECT-TYPE
SYNTAX INTEGER
MAX-ACCESS read-write
STATUS current
DESCRIPTION
"Data value."
::= { dataArray16 139 }

dataValue16_140 OBJECT-TYPE
SYNTAX INTEGER
MAX-ACCESS read-write
STATUS current
DESCRIPTION
"Data value."
::= { dataArray16 140 }

dataValue16_141 OBJECT-TYPE
SYNTAX INTEGER
MAX-ACCESS read-write
STATUS current
DESCRIPTION
"Data value."
::= { dataArray16 141 }

dataValue16_142 OBJECT-TYPE
SYNTAX INTEGER
MAX-ACCESS read-write
STATUS current
DESCRIPTION
"Data value."
::= { dataArray16 142 }

dataValue16_143 OBJECT-TYPE
SYNTAX INTEGER
MAX-ACCESS read-write
STATUS current
DESCRIPTION
"Data value."
::= { dataArray16 143 }

dataValue16_144 OBJECT-TYPE
SYNTAX INTEGER
MAX-ACCESS read-write
STATUS current
DESCRIPTION
"Data value."
::= { dataArray16 144 }

dataValue16_145 OBJECT-TYPE
SYNTAX INTEGER
MAX-ACCESS read-write
STATUS current
DESCRIPTION
"Data value."
::= { dataArray16 145 }

dataValue16_146 OBJECT-TYPE
SYNTAX INTEGER
MAX-ACCESS read-write
STATUS current
DESCRIPTION
"Data value."
::= { dataArray16 146 }

dataValue16_147 OBJECT-TYPE
SYNTAX INTEGER
MAX-ACCESS read-write
STATUS current
DESCRIPTION
"Data value."
::= { dataArray16 147 }

dataValue16_148 OBJECT-TYPE
SYNTAX INTEGER
MAX-ACCESS read-write
STATUS current
DESCRIPTION
"Data value."
::= { dataArray16 148 }

dataValue16_149 OBJECT-TYPE
SYNTAX INTEGER
MAX-ACCESS read-write
STATUS current
DESCRIPTION
"Data value."
::= { dataArray16 149 }

dataValue16_150 OBJECT-TYPE
SYNTAX INTEGER
MAX-ACCESS read-write
STATUS current
DESCRIPTION
"Data value."
::= { dataArray16 150 }

dataValue16_151 OBJECT-TYPE
SYNTAX INTEGER
MAX-ACCESS read-write
STATUS current
DESCRIPTION
"Data value."
::= { dataArray16 151 }

dataValue16_152 OBJECT-TYPE
SYNTAX INTEGER
MAX-ACCESS read-write
STATUS current
DESCRIPTION
"Data value."
::= { dataArray16 152 }

dataValue16_153 OBJECT-TYPE
SYNTAX INTEGER
MAX-ACCESS read-write
STATUS current
DESCRIPTION
"Data value."
::= { dataArray16 153 }

dataValue16_154 OBJECT-TYPE
SYNTAX INTEGER
MAX-ACCESS read-write
STATUS current
DESCRIPTION
"Data value."
::= { dataArray16 154 }

dataValue16_155 OBJECT-TYPE
SYNTAX INTEGER
MAX-ACCESS read-write
STATUS current
DESCRIPTION
"Data value."
::= { dataArray16 155 }

dataValue16_156 OBJECT-TYPE
SYNTAX INTEGER
MAX-ACCESS read-write
STATUS current
DESCRIPTION
"Data value."
::= { dataArray16 156 }

dataValue16_157 OBJECT-TYPE
SYNTAX INTEGER
MAX-ACCESS read-write
STATUS current
DESCRIPTION
"Data value."
::= { dataArray16 157 }

dataValue16_158 OBJECT-TYPE
SYNTAX INTEGER
MAX-ACCESS read-write
STATUS current
DESCRIPTION
"Data value."
::= { dataArray16 158 }

dataValue16_159 OBJECT-TYPE
SYNTAX INTEGER
MAX-ACCESS read-write
STATUS current
DESCRIPTION
"Data value."
::= { dataArray16 159 }

dataValue16_160 OBJECT-TYPE
SYNTAX INTEGER
MAX-ACCESS read-write
STATUS current
DESCRIPTION
"Data value."
::= { dataArray16 160 }

dataValue16_161 OBJECT-TYPE
SYNTAX INTEGER
MAX-ACCESS read-write
STATUS current
DESCRIPTION
"Data value."
::= { dataArray16 161 }

dataValue16_162 OBJECT-TYPE
SYNTAX INTEGER
MAX-ACCESS read-write
STATUS current
DESCRIPTION
"Data value."
::= { dataArray16 162 }

dataValue16_163 OBJECT-TYPE
SYNTAX INTEGER
MAX-ACCESS read-write
STATUS current
DESCRIPTION
"Data value."
::= { dataArray16 163 }

dataValue16_164 OBJECT-TYPE
SYNTAX INTEGER
MAX-ACCESS read-write
STATUS current
DESCRIPTION
"Data value."
::= { dataArray16 164 }

dataValue16_165 OBJECT-TYPE
SYNTAX INTEGER
MAX-ACCESS read-write
STATUS current
DESCRIPTION
"Data value."
::= { dataArray16 165 }

dataValue16_166 OBJECT-TYPE
SYNTAX INTEGER
MAX-ACCESS read-write
STATUS current
DESCRIPTION
"Data value."
::= { dataArray16 166 }

dataValue16_167 OBJECT-TYPE
SYNTAX INTEGER
MAX-ACCESS read-write
STATUS current
DESCRIPTION
"Data value."
::= { dataArray16 167 }

dataValue16_168 OBJECT-TYPE
SYNTAX INTEGER
MAX-ACCESS read-write
STATUS current
DESCRIPTION
"Data value."
::= { dataArray16 168 }

dataValue16_169 OBJECT-TYPE
SYNTAX INTEGER
MAX-ACCESS read-write
STATUS current
DESCRIPTION
"Data value."
::= { dataArray16 169 }

dataValue16_170 OBJECT-TYPE
SYNTAX INTEGER
MAX-ACCESS read-write
STATUS current
DESCRIPTION
"Data value."
::= { dataArray16 170 }

dataValue16_171 OBJECT-TYPE
SYNTAX INTEGER
MAX-ACCESS read-write
STATUS current
DESCRIPTION
"Data value."
::= { dataArray16 171 }

dataValue16_172 OBJECT-TYPE
SYNTAX INTEGER
MAX-ACCESS read-write
STATUS current
DESCRIPTION
"Data value."
::= { dataArray16 172 }

dataValue16_173 OBJECT-TYPE
SYNTAX INTEGER
MAX-ACCESS read-write
STATUS current
DESCRIPTION
"Data value."
::= { dataArray16 173 }

dataValue16_174 OBJECT-TYPE
SYNTAX INTEGER
MAX-ACCESS read-write
STATUS current
DESCRIPTION
"Data value."
::= { dataArray16 174 }

dataValue16_175 OBJECT-TYPE
SYNTAX INTEGER
MAX-ACCESS read-write
STATUS current
DESCRIPTION
"Data value."
::= { dataArray16 175 }

dataValue16_176 OBJECT-TYPE
SYNTAX INTEGER
MAX-ACCESS read-write
STATUS current
DESCRIPTION
"Data value."
::= { dataArray16 176 }

dataValue16_177 OBJECT-TYPE
SYNTAX INTEGER
MAX-ACCESS read-write
STATUS current
DESCRIPTION
"Data value."
::= { dataArray16 177 }

dataValue16_178 OBJECT-TYPE
SYNTAX INTEGER
MAX-ACCESS read-write
STATUS current
DESCRIPTION
"Data value."
::= { dataArray16 178 }

dataValue16_179 OBJECT-TYPE
SYNTAX INTEGER
MAX-ACCESS read-write
STATUS current
DESCRIPTION
"Data value."
::= { dataArray16 179 }

dataValue16_180 OBJECT-TYPE
SYNTAX INTEGER
MAX-ACCESS read-write
STATUS current
DESCRIPTION
"Data value."
::= { dataArray16 180 }

dataValue16_181 OBJECT-TYPE
SYNTAX INTEGER
MAX-ACCESS read-write
STATUS current
DESCRIPTION
"Data value."
::= { dataArray16 181 }

dataValue16_182 OBJECT-TYPE
SYNTAX INTEGER
MAX-ACCESS read-write
STATUS current
DESCRIPTION
"Data value."
::= { dataArray16 182 }

dataValue16_183 OBJECT-TYPE
SYNTAX INTEGER
MAX-ACCESS read-write
STATUS current
DESCRIPTION
"Data value."
::= { dataArray16 183 }

dataValue16_184 OBJECT-TYPE
SYNTAX INTEGER
MAX-ACCESS read-write
STATUS current
DESCRIPTION
"Data value."
::= { dataArray16 184 }

dataValue16_185 OBJECT-TYPE
SYNTAX INTEGER
MAX-ACCESS read-write
STATUS current
DESCRIPTION
"Data value."
::= { dataArray16 185 }

dataValue16_186 OBJECT-TYPE
SYNTAX INTEGER
MAX-ACCESS read-write
STATUS current
DESCRIPTION
"Data value."
::= { dataArray16 186 }

dataValue16_187 OBJECT-TYPE
SYNTAX INTEGER
MAX-ACCESS read-write
STATUS current
DESCRIPTION
"Data value."
::= { dataArray16 187 }

dataValue16_188 OBJECT-TYPE
SYNTAX INTEGER
MAX-ACCESS read-write
STATUS current
DESCRIPTION
"Data value."
::= { dataArray16 188 }

dataValue16_189 OBJECT-TYPE
SYNTAX INTEGER
MAX-ACCESS read-write
STATUS current
DESCRIPTION
"Data value."
::= { dataArray16 189 }

dataValue16_190 OBJECT-TYPE
SYNTAX INTEGER
MAX-ACCESS read-write
STATUS current
DESCRIPTION
"Data value."
::= { dataArray16 190 }

dataValue16_191 OBJECT-TYPE
SYNTAX INTEGER
MAX-ACCESS read-write
STATUS current
DESCRIPTION
"Data value."
::= { dataArray16 191 }

dataValue16_192 OBJECT-TYPE
SYNTAX INTEGER
MAX-ACCESS read-write
STATUS current
DESCRIPTION
"Data value."
::= { dataArray16 192 }

dataValue16_193 OBJECT-TYPE
SYNTAX INTEGER
MAX-ACCESS read-write
STATUS current
DESCRIPTION
"Data value."
::= { dataArray16 193 }

dataValue16_194 OBJECT-TYPE
SYNTAX INTEGER
MAX-ACCESS read-write
STATUS current
DESCRIPTION
"Data value."
::= { dataArray16 194 }

dataValue16_195 OBJECT-TYPE
SYNTAX INTEGER
MAX-ACCESS read-write
STATUS current
DESCRIPTION
"Data value."
::= { dataArray16 195 }

dataValue16_196 OBJECT-TYPE
SYNTAX INTEGER
MAX-ACCESS read-write
STATUS current
DESCRIPTION
"Data value."
::= { dataArray16 196 }

dataValue16_197 OBJECT-TYPE
SYNTAX INTEGER
MAX-ACCESS read-write
STATUS current
DESCRIPTION
"Data value."
::= { dataArray16 197 }

dataValue16_198 OBJECT-TYPE
SYNTAX INTEGER
MAX-ACCESS read-write
STATUS current
DESCRIPTION
"Data value."
::= { dataArray16 198 }

dataValue16_199 OBJECT-TYPE
SYNTAX INTEGER
MAX-ACCESS read-write
STATUS current
DESCRIPTION
"Data value."
::= { dataArray16 199 }

dataValue16_200 OBJECT-TYPE
SYNTAX INTEGER
MAX-ACCESS read-write
STATUS current
DESCRIPTION
"Data value."
::= { dataArray16 200 }

dataValue16_201 OBJECT-TYPE
SYNTAX INTEGER
MAX-ACCESS read-write
STATUS current
DESCRIPTION
"Data value."
::= { dataArray16 201 }

dataValue16_202 OBJECT-TYPE
SYNTAX INTEGER
MAX-ACCESS read-write
STATUS current
DESCRIPTION
"Data value."
::= { dataArray16 202 }

dataValue16_203 OBJECT-TYPE
SYNTAX INTEGER
MAX-ACCESS read-write
STATUS current
DESCRIPTION
"Data value."
::= { dataArray16 203 }

dataValue16_204 OBJECT-TYPE
SYNTAX INTEGER
MAX-ACCESS read-write
STATUS current
DESCRIPTION
"Data value."
::= { dataArray16 204 }

dataValue16_205 OBJECT-TYPE
SYNTAX INTEGER
MAX-ACCESS read-write
STATUS current
DESCRIPTION
"Data value."
::= { dataArray16 205 }

dataValue16_206 OBJECT-TYPE
SYNTAX INTEGER
MAX-ACCESS read-write
STATUS current
DESCRIPTION
"Data value."
::= { dataArray16 206 }

dataValue16_207 OBJECT-TYPE
SYNTAX INTEGER
MAX-ACCESS read-write
STATUS current
DESCRIPTION
"Data value."
::= { dataArray16 207 }

dataValue16_208 OBJECT-TYPE
SYNTAX INTEGER
MAX-ACCESS read-write
STATUS current
DESCRIPTION
"Data value."
::= { dataArray16 208 }

dataValue16_209 OBJECT-TYPE
SYNTAX INTEGER
MAX-ACCESS read-write
STATUS current
DESCRIPTION
"Data value."
::= { dataArray16 209 }

dataValue16_210 OBJECT-TYPE
SYNTAX INTEGER
MAX-ACCESS read-write
STATUS current
DESCRIPTION
"Data value."
::= { dataArray16 210 }

dataValue16_211 OBJECT-TYPE
SYNTAX INTEGER
MAX-ACCESS read-write
STATUS current
DESCRIPTION
"Data value."
::= { dataArray16 211 }

dataValue16_212 OBJECT-TYPE
SYNTAX INTEGER
MAX-ACCESS read-write
STATUS current
DESCRIPTION
"Data value."
::= { dataArray16 212 }

dataValue16_213 OBJECT-TYPE
SYNTAX INTEGER
MAX-ACCESS read-write
STATUS current
DESCRIPTION
"Data value."
::= { dataArray16 213 }

dataValue16_214 OBJECT-TYPE
SYNTAX INTEGER
MAX-ACCESS read-write
STATUS current
DESCRIPTION
"Data value."
::= { dataArray16 214 }

dataValue16_215 OBJECT-TYPE
SYNTAX INTEGER
MAX-ACCESS read-write
STATUS current
DESCRIPTION
"Data value."
::= { dataArray16 215 }

dataValue16_216 OBJECT-TYPE
SYNTAX INTEGER
MAX-ACCESS read-write
STATUS current
DESCRIPTION
"Data value."
::= { dataArray16 216 }

dataValue16_217 OBJECT-TYPE
SYNTAX INTEGER
MAX-ACCESS read-write
STATUS current
DESCRIPTION
"Data value."
::= { dataArray16 217 }

dataValue16_218 OBJECT-TYPE
SYNTAX INTEGER
MAX-ACCESS read-write
STATUS current
DESCRIPTION
"Data value."
::= { dataArray16 218 }

dataValue16_219 OBJECT-TYPE
SYNTAX INTEGER
MAX-ACCESS read-write
STATUS current
DESCRIPTION
"Data value."
::= { dataArray16 219 }

dataValue16_220 OBJECT-TYPE
SYNTAX INTEGER
MAX-ACCESS read-write
STATUS current
DESCRIPTION
"Data value."
::= { dataArray16 220 }

dataValue16_221 OBJECT-TYPE
SYNTAX INTEGER
MAX-ACCESS read-write
STATUS current
DESCRIPTION
"Data value."
::= { dataArray16 221 }

dataValue16_222 OBJECT-TYPE
SYNTAX INTEGER
MAX-ACCESS read-write
STATUS current
DESCRIPTION
"Data value."
::= { dataArray16 222 }

dataValue16_223 OBJECT-TYPE
SYNTAX INTEGER
MAX-ACCESS read-write
STATUS current
DESCRIPTION
"Data value."
::= { dataArray16 223 }

dataValue16_224 OBJECT-TYPE
SYNTAX INTEGER
MAX-ACCESS read-write
STATUS current
DESCRIPTION
"Data value."
::= { dataArray16 224 }

dataValue16_225 OBJECT-TYPE
SYNTAX INTEGER
MAX-ACCESS read-write
STATUS current
DESCRIPTION
"Data value."
::= { dataArray16 225 }

dataValue16_226 OBJECT-TYPE
SYNTAX INTEGER
MAX-ACCESS read-write
STATUS current
DESCRIPTION
"Data value."
::= { dataArray16 226 }

dataValue16_227 OBJECT-TYPE
SYNTAX INTEGER
MAX-ACCESS read-write
STATUS current
DESCRIPTION
"Data value."
::= { dataArray16 227 }

dataValue16_228 OBJECT-TYPE
SYNTAX INTEGER
MAX-ACCESS read-write
STATUS current
DESCRIPTION
"Data value."
::= { dataArray16 228 }

dataValue16_229 OBJECT-TYPE
SYNTAX INTEGER
MAX-ACCESS read-write
STATUS current
DESCRIPTION
"Data value."
::= { dataArray16 229 }

dataValue16_230 OBJECT-TYPE
SYNTAX INTEGER
MAX-ACCESS read-write
STATUS current
DESCRIPTION
"Data value."
::= { dataArray16 230 }

dataValue16_231 OBJECT-TYPE
SYNTAX INTEGER
MAX-ACCESS read-write
STATUS current
DESCRIPTION
"Data value."
::= { dataArray16 231 }

dataValue16_232 OBJECT-TYPE
SYNTAX INTEGER
MAX-ACCESS read-write
STATUS current
DESCRIPTION
"Data value."
::= { dataArray16 232 }

dataValue16_233 OBJECT-TYPE
SYNTAX INTEGER
MAX-ACCESS read-write
STATUS current
DESCRIPTION
"Data value."
::= { dataArray16 233 }

dataValue16_234 OBJECT-TYPE
SYNTAX INTEGER
MAX-ACCESS read-write
STATUS current
DESCRIPTION
"Data value."
::= { dataArray16 234 }

dataValue16_235 OBJECT-TYPE
SYNTAX INTEGER
MAX-ACCESS read-write
STATUS current
DESCRIPTION
"Data value."
::= { dataArray16 235 }

dataValue16_236 OBJECT-TYPE
SYNTAX INTEGER
MAX-ACCESS read-write
STATUS current
DESCRIPTION
"Data value."
::= { dataArray16 236 }

dataValue16_237 OBJECT-TYPE
SYNTAX INTEGER
MAX-ACCESS read-write
STATUS current
DESCRIPTION
"Data value."
::= { dataArray16 237 }

dataValue16_238 OBJECT-TYPE
SYNTAX INTEGER
MAX-ACCESS read-write
STATUS current
DESCRIPTION
"Data value."
::= { dataArray16 238 }

dataValue16_239 OBJECT-TYPE
SYNTAX INTEGER
MAX-ACCESS read-write
STATUS current
DESCRIPTION
"Data value."
::= { dataArray16 239 }

dataValue16_240 OBJECT-TYPE
SYNTAX INTEGER
MAX-ACCESS read-write
STATUS current
DESCRIPTION
"Data value."
::= { dataArray16 240 }

dataValue16_241 OBJECT-TYPE
SYNTAX INTEGER
MAX-ACCESS read-write
STATUS current
DESCRIPTION
"Data value."
::= { dataArray16 241 }

dataValue16_242 OBJECT-TYPE
SYNTAX INTEGER
MAX-ACCESS read-write
STATUS current
DESCRIPTION
"Data value."
::= { dataArray16 242 }

dataValue16_243 OBJECT-TYPE
SYNTAX INTEGER
MAX-ACCESS read-write
STATUS current
DESCRIPTION
"Data value."
::= { dataArray16 243 }

dataValue16_244 OBJECT-TYPE
SYNTAX INTEGER
MAX-ACCESS read-write
STATUS current
DESCRIPTION
"Data value."
::= { dataArray16 244 }

dataValue16_245 OBJECT-TYPE
SYNTAX INTEGER
MAX-ACCESS read-write
STATUS current
DESCRIPTION
"Data value."
::= { dataArray16 245 }

dataValue16_246 OBJECT-TYPE
SYNTAX INTEGER
MAX-ACCESS read-write
STATUS current
DESCRIPTION
"Data value."
::= { dataArray16 246 }

dataValue16_247 OBJECT-TYPE
SYNTAX INTEGER
MAX-ACCESS read-write
STATUS current
DESCRIPTION
"Data value."
::= { dataArray16 247 }

dataValue16_248 OBJECT-TYPE
SYNTAX INTEGER
MAX-ACCESS read-write
STATUS current
DESCRIPTION
"Data value."
::= { dataArray16 248 }

dataValue16_249 OBJECT-TYPE
SYNTAX INTEGER
MAX-ACCESS read-write
STATUS current
DESCRIPTION
"Data value."
::= { dataArray16 249 }

dataValue16_250 OBJECT-TYPE
SYNTAX INTEGER
MAX-ACCESS read-write
STATUS current
DESCRIPTION
"Data value."
::= { dataArray16 250 }

dataValue16_251 OBJECT-TYPE
SYNTAX INTEGER
MAX-ACCESS read-write
STATUS current
DESCRIPTION
"Data value."
::= { dataArray16 251 }

dataValue16_252 OBJECT-TYPE
SYNTAX INTEGER
MAX-ACCESS read-write
STATUS current
DESCRIPTION
"Data value."
::= { dataArray16 252 }

dataValue16_253 OBJECT-TYPE
SYNTAX INTEGER
MAX-ACCESS read-write
STATUS current
DESCRIPTION
"Data value."
::= { dataArray16 253 }

dataValue16_254 OBJECT-TYPE
SYNTAX INTEGER
MAX-ACCESS read-write
STATUS current
DESCRIPTION
"Data value."
::= { dataArray16 254 }

dataValue16_255 OBJECT-TYPE
SYNTAX INTEGER
MAX-ACCESS read-write
STATUS current
DESCRIPTION
"Data value."
::= { dataArray16 255 }

dataValue16_256 OBJECT-TYPE
SYNTAX INTEGER
MAX-ACCESS read-write
STATUS current
DESCRIPTION
"Data value."
::= { dataArray16 256 }

dataValue16_257 OBJECT-TYPE
SYNTAX INTEGER
MAX-ACCESS read-write
STATUS current
DESCRIPTION
"Data value."
::= { dataArray16 257 }

dataValue16_258 OBJECT-TYPE
SYNTAX INTEGER
MAX-ACCESS read-write
STATUS current
DESCRIPTION
"Data value."
::= { dataArray16 258 }

dataValue16_259 OBJECT-TYPE
SYNTAX INTEGER
MAX-ACCESS read-write
STATUS current
DESCRIPTION
"Data value."
::= { dataArray16 259 }

dataValue16_260 OBJECT-TYPE
SYNTAX INTEGER
MAX-ACCESS read-write
STATUS current
DESCRIPTION
"Data value."
::= { dataArray16 260 }

dataValue16_261 OBJECT-TYPE
SYNTAX INTEGER
MAX-ACCESS read-write
STATUS current
DESCRIPTION
"Data value."
::= { dataArray16 261 }

dataValue16_262 OBJECT-TYPE
SYNTAX INTEGER
MAX-ACCESS read-write
STATUS current
DESCRIPTION
"Data value."
::= { dataArray16 262 }

dataValue16_263 OBJECT-TYPE
SYNTAX INTEGER
MAX-ACCESS read-write
STATUS current
DESCRIPTION
"Data value."
::= { dataArray16 263 }

dataValue16_264 OBJECT-TYPE
SYNTAX INTEGER
MAX-ACCESS read-write
STATUS current
DESCRIPTION
"Data value."
::= { dataArray16 264 }

dataValue16_265 OBJECT-TYPE
SYNTAX INTEGER
MAX-ACCESS read-write
STATUS current
DESCRIPTION
"Data value."
::= { dataArray16 265 }

dataValue16_266 OBJECT-TYPE
SYNTAX INTEGER
MAX-ACCESS read-write
STATUS current
DESCRIPTION
"Data value."
::= { dataArray16 266 }

dataValue16_267 OBJECT-TYPE
SYNTAX INTEGER
MAX-ACCESS read-write
STATUS current
DESCRIPTION
"Data value."
::= { dataArray16 267 }

dataValue16_268 OBJECT-TYPE
SYNTAX INTEGER
MAX-ACCESS read-write
STATUS current
DESCRIPTION
"Data value."
::= { dataArray16 268 }

dataValue16_269 OBJECT-TYPE
SYNTAX INTEGER
MAX-ACCESS read-write
STATUS current
DESCRIPTION
"Data value."
::= { dataArray16 269 }

dataValue16_270 OBJECT-TYPE
SYNTAX INTEGER
MAX-ACCESS read-write
STATUS current
DESCRIPTION
"Data value."
::= { dataArray16 270 }

dataValue16_271 OBJECT-TYPE
SYNTAX INTEGER
MAX-ACCESS read-write
STATUS current
DESCRIPTION
"Data value."
::= { dataArray16 271 }

dataValue16_272 OBJECT-TYPE
SYNTAX INTEGER
MAX-ACCESS read-write
STATUS current
DESCRIPTION
"Data value."
::= { dataArray16 272 }

dataValue16_273 OBJECT-TYPE
SYNTAX INTEGER
MAX-ACCESS read-write
STATUS current
DESCRIPTION
"Data value."
::= { dataArray16 273 }

dataValue16_274 OBJECT-TYPE
SYNTAX INTEGER
MAX-ACCESS read-write
STATUS current
DESCRIPTION
"Data value."
::= { dataArray16 274 }

dataValue16_275 OBJECT-TYPE
SYNTAX INTEGER
MAX-ACCESS read-write
STATUS current
DESCRIPTION
"Data value."
::= { dataArray16 275 }

dataValue16_276 OBJECT-TYPE
SYNTAX INTEGER
MAX-ACCESS read-write
STATUS current
DESCRIPTION
"Data value."
::= { dataArray16 276 }

dataValue16_277 OBJECT-TYPE
SYNTAX INTEGER
MAX-ACCESS read-write
STATUS current
DESCRIPTION
"Data value."
::= { dataArray16 277 }

dataValue16_278 OBJECT-TYPE
SYNTAX INTEGER
MAX-ACCESS read-write
STATUS current
DESCRIPTION
"Data value."
::= { dataArray16 278 }

dataValue16_279 OBJECT-TYPE
SYNTAX INTEGER
MAX-ACCESS read-write
STATUS current
DESCRIPTION
"Data value."
::= { dataArray16 279 }

dataValue16_280 OBJECT-TYPE
SYNTAX INTEGER
MAX-ACCESS read-write
STATUS current
DESCRIPTION
"Data value."
::= { dataArray16 280 }

dataValue16_281 OBJECT-TYPE
SYNTAX INTEGER
MAX-ACCESS read-write
STATUS current
DESCRIPTION
"Data value."
::= { dataArray16 281 }

dataValue16_282 OBJECT-TYPE
SYNTAX INTEGER
MAX-ACCESS read-write
STATUS current
DESCRIPTION
"Data value."
::= { dataArray16 282 }

dataValue16_283 OBJECT-TYPE
SYNTAX INTEGER
MAX-ACCESS read-write
STATUS current
DESCRIPTION
"Data value."
::= { dataArray16 283 }

dataValue16_284 OBJECT-TYPE
SYNTAX INTEGER
MAX-ACCESS read-write
STATUS current
DESCRIPTION
"Data value."
::= { dataArray16 284 }

dataValue16_285 OBJECT-TYPE
SYNTAX INTEGER
MAX-ACCESS read-write
STATUS current
DESCRIPTION
"Data value."
::= { dataArray16 285 }

dataValue16_286 OBJECT-TYPE
SYNTAX INTEGER
MAX-ACCESS read-write
STATUS current
DESCRIPTION
"Data value."
::= { dataArray16 286 }

dataValue16_287 OBJECT-TYPE
SYNTAX INTEGER
MAX-ACCESS read-write
STATUS current
DESCRIPTION
"Data value."
::= { dataArray16 287 }

dataValue16_288 OBJECT-TYPE
SYNTAX INTEGER
MAX-ACCESS read-write
STATUS current
DESCRIPTION
"Data value."
::= { dataArray16 288 }

dataValue16_289 OBJECT-TYPE
SYNTAX INTEGER
MAX-ACCESS read-write
STATUS current
DESCRIPTION
"Data value."
::= { dataArray16 289 }

dataValue16_290 OBJECT-TYPE
SYNTAX INTEGER
MAX-ACCESS read-write
STATUS current
DESCRIPTION
"Data value."
::= { dataArray16 290 }

dataValue16_291 OBJECT-TYPE
SYNTAX INTEGER
MAX-ACCESS read-write
STATUS current
DESCRIPTION
"Data value."
::= { dataArray16 291 }

dataValue16_292 OBJECT-TYPE
SYNTAX INTEGER
MAX-ACCESS read-write
STATUS current
DESCRIPTION
"Data value."
::= { dataArray16 292 }

dataValue16_293 OBJECT-TYPE
SYNTAX INTEGER
MAX-ACCESS read-write
STATUS current
DESCRIPTION
"Data value."
::= { dataArray16 293 }

dataValue16_294 OBJECT-TYPE
SYNTAX INTEGER
MAX-ACCESS read-write
STATUS current
DESCRIPTION
"Data value."
::= { dataArray16 294 }

dataValue16_295 OBJECT-TYPE
SYNTAX INTEGER
MAX-ACCESS read-write
STATUS current
DESCRIPTION
"Data value."
::= { dataArray16 295 }

dataValue16_296 OBJECT-TYPE
SYNTAX INTEGER
MAX-ACCESS read-write
STATUS current
DESCRIPTION
"Data value."
::= { dataArray16 296 }

dataValue16_297 OBJECT-TYPE
SYNTAX INTEGER
MAX-ACCESS read-write
STATUS current
DESCRIPTION
"Data value."
::= { dataArray16 297 }

dataValue16_298 OBJECT-TYPE
SYNTAX INTEGER
MAX-ACCESS read-write
STATUS current
DESCRIPTION
"Data value."
::= { dataArray16 298 }

dataValue16_299 OBJECT-TYPE
SYNTAX INTEGER
MAX-ACCESS read-write
STATUS current
DESCRIPTION
"Data value."
::= { dataArray16 299 }

dataValue16_300 OBJECT-TYPE
SYNTAX INTEGER
MAX-ACCESS read-write
STATUS current
DESCRIPTION
"Data value."
::= { dataArray16 300 }

dataValue16_301 OBJECT-TYPE
SYNTAX INTEGER
MAX-ACCESS read-write
STATUS current
DESCRIPTION
"Data value."
::= { dataArray16 301 }

dataValue16_302 OBJECT-TYPE
SYNTAX INTEGER
MAX-ACCESS read-write
STATUS current
DESCRIPTION
"Data value."
::= { dataArray16 302 }

dataValue16_303 OBJECT-TYPE
SYNTAX INTEGER
MAX-ACCESS read-write
STATUS current
DESCRIPTION
"Data value."
::= { dataArray16 303 }

dataValue16_304 OBJECT-TYPE
SYNTAX INTEGER
MAX-ACCESS read-write
STATUS current
DESCRIPTION
"Data value."
::= { dataArray16 304 }

dataValue16_305 OBJECT-TYPE
SYNTAX INTEGER
MAX-ACCESS read-write
STATUS current
DESCRIPTION
"Data value."
::= { dataArray16 305 }

dataValue16_306 OBJECT-TYPE
SYNTAX INTEGER
MAX-ACCESS read-write
STATUS current
DESCRIPTION
"Data value."
::= { dataArray16 306 }

dataValue16_307 OBJECT-TYPE
SYNTAX INTEGER
MAX-ACCESS read-write
STATUS current
DESCRIPTION
"Data value."
::= { dataArray16 307 }

dataValue16_308 OBJECT-TYPE
SYNTAX INTEGER
MAX-ACCESS read-write
STATUS current
DESCRIPTION
"Data value."
::= { dataArray16 308 }

dataValue16_309 OBJECT-TYPE
SYNTAX INTEGER
MAX-ACCESS read-write
STATUS current
DESCRIPTION
"Data value."
::= { dataArray16 309 }

dataValue16_310 OBJECT-TYPE
SYNTAX INTEGER
MAX-ACCESS read-write
STATUS current
DESCRIPTION
"Data value."
::= { dataArray16 310 }

dataValue16_311 OBJECT-TYPE
SYNTAX INTEGER
MAX-ACCESS read-write
STATUS current
DESCRIPTION
"Data value."
::= { dataArray16 311 }

dataValue16_312 OBJECT-TYPE
SYNTAX INTEGER
MAX-ACCESS read-write
STATUS current
DESCRIPTION
"Data value."
::= { dataArray16 312 }

dataValue16_313 OBJECT-TYPE
SYNTAX INTEGER
MAX-ACCESS read-write
STATUS current
DESCRIPTION
"Data value."
::= { dataArray16 313 }

dataValue16_314 OBJECT-TYPE
SYNTAX INTEGER
MAX-ACCESS read-write
STATUS current
DESCRIPTION
"Data value."
::= { dataArray16 314 }

dataValue16_315 OBJECT-TYPE
SYNTAX INTEGER
MAX-ACCESS read-write
STATUS current
DESCRIPTION
"Data value."
::= { dataArray16 315 }

dataValue16_316 OBJECT-TYPE
SYNTAX INTEGER
MAX-ACCESS read-write
STATUS current
DESCRIPTION
"Data value."
::= { dataArray16 316 }

dataValue16_317 OBJECT-TYPE
SYNTAX INTEGER
MAX-ACCESS read-write
STATUS current
DESCRIPTION
"Data value."
::= { dataArray16 317 }

dataValue16_318 OBJECT-TYPE
SYNTAX INTEGER
MAX-ACCESS read-write
STATUS current
DESCRIPTION
"Data value."
::= { dataArray16 318 }

dataValue16_319 OBJECT-TYPE
SYNTAX INTEGER
MAX-ACCESS read-write
STATUS current
DESCRIPTION
"Data value."
::= { dataArray16 319 }

dataValue16_320 OBJECT-TYPE
SYNTAX INTEGER
MAX-ACCESS read-write
STATUS current
DESCRIPTION
"Data value."
::= { dataArray16 320 }

dataValue16_321 OBJECT-TYPE
SYNTAX INTEGER
MAX-ACCESS read-write
STATUS current
DESCRIPTION
"Data value."
::= { dataArray16 321 }

dataValue16_322 OBJECT-TYPE
SYNTAX INTEGER
MAX-ACCESS read-write
STATUS current
DESCRIPTION
"Data value."
::= { dataArray16 322 }

dataValue16_323 OBJECT-TYPE
SYNTAX INTEGER
MAX-ACCESS read-write
STATUS current
DESCRIPTION
"Data value."
::= { dataArray16 323 }

dataValue16_324 OBJECT-TYPE
SYNTAX INTEGER
MAX-ACCESS read-write
STATUS current
DESCRIPTION
"Data value."
::= { dataArray16 324 }

dataValue16_325 OBJECT-TYPE
SYNTAX INTEGER
MAX-ACCESS read-write
STATUS current
DESCRIPTION
"Data value."
::= { dataArray16 325 }

dataValue16_326 OBJECT-TYPE
SYNTAX INTEGER
MAX-ACCESS read-write
STATUS current
DESCRIPTION
"Data value."
::= { dataArray16 326 }

dataValue16_327 OBJECT-TYPE
SYNTAX INTEGER
MAX-ACCESS read-write
STATUS current
DESCRIPTION
"Data value."
::= { dataArray16 327 }

dataValue16_328 OBJECT-TYPE
SYNTAX INTEGER
MAX-ACCESS read-write
STATUS current
DESCRIPTION
"Data value."
::= { dataArray16 328 }

dataValue16_329 OBJECT-TYPE
SYNTAX INTEGER
MAX-ACCESS read-write
STATUS current
DESCRIPTION
"Data value."
::= { dataArray16 329 }

dataValue16_330 OBJECT-TYPE
SYNTAX INTEGER
MAX-ACCESS read-write
STATUS current
DESCRIPTION
"Data value."
::= { dataArray16 330 }

dataValue16_331 OBJECT-TYPE
SYNTAX INTEGER
MAX-ACCESS read-write
STATUS current
DESCRIPTION
"Data value."
::= { dataArray16 331 }

dataValue16_332 OBJECT-TYPE
SYNTAX INTEGER
MAX-ACCESS read-write
STATUS current
DESCRIPTION
"Data value."
::= { dataArray16 332 }

dataValue16_333 OBJECT-TYPE
SYNTAX INTEGER
MAX-ACCESS read-write
STATUS current
DESCRIPTION
"Data value."
::= { dataArray16 333 }

dataValue16_334 OBJECT-TYPE
SYNTAX INTEGER
MAX-ACCESS read-write
STATUS current
DESCRIPTION
"Data value."
::= { dataArray16 334 }

dataValue16_335 OBJECT-TYPE
SYNTAX INTEGER
MAX-ACCESS read-write
STATUS current
DESCRIPTION
"Data value."
::= { dataArray16 335 }

dataValue16_336 OBJECT-TYPE
SYNTAX INTEGER
MAX-ACCESS read-write
STATUS current
DESCRIPTION
"Data value."
::= { dataArray16 336 }

dataValue16_337 OBJECT-TYPE
SYNTAX INTEGER
MAX-ACCESS read-write
STATUS current
DESCRIPTION
"Data value."
::= { dataArray16 337 }

dataValue16_338 OBJECT-TYPE
SYNTAX INTEGER
MAX-ACCESS read-write
STATUS current
DESCRIPTION
"Data value."
::= { dataArray16 338 }

dataValue16_339 OBJECT-TYPE
SYNTAX INTEGER
MAX-ACCESS read-write
STATUS current
DESCRIPTION
"Data value."
::= { dataArray16 339 }

dataValue16_340 OBJECT-TYPE
SYNTAX INTEGER
MAX-ACCESS read-write
STATUS current
DESCRIPTION
"Data value."
::= { dataArray16 340 }

dataValue16_341 OBJECT-TYPE
SYNTAX INTEGER
MAX-ACCESS read-write
STATUS current
DESCRIPTION
"Data value."
::= { dataArray16 341 }

dataValue16_342 OBJECT-TYPE
SYNTAX INTEGER
MAX-ACCESS read-write
STATUS current
DESCRIPTION
"Data value."
::= { dataArray16 342 }

dataValue16_343 OBJECT-TYPE
SYNTAX INTEGER
MAX-ACCESS read-write
STATUS current
DESCRIPTION
"Data value."
::= { dataArray16 343 }

dataValue16_344 OBJECT-TYPE
SYNTAX INTEGER
MAX-ACCESS read-write
STATUS current
DESCRIPTION
"Data value."
::= { dataArray16 344 }

dataValue16_345 OBJECT-TYPE
SYNTAX INTEGER
MAX-ACCESS read-write
STATUS current
DESCRIPTION
"Data value."
::= { dataArray16 345 }

dataValue16_346 OBJECT-TYPE
SYNTAX INTEGER
MAX-ACCESS read-write
STATUS current
DESCRIPTION
"Data value."
::= { dataArray16 346 }

dataValue16_347 OBJECT-TYPE
SYNTAX INTEGER
MAX-ACCESS read-write
STATUS current
DESCRIPTION
"Data value."
::= { dataArray16 347 }

dataValue16_348 OBJECT-TYPE
SYNTAX INTEGER
MAX-ACCESS read-write
STATUS current
DESCRIPTION
"Data value."
::= { dataArray16 348 }

dataValue16_349 OBJECT-TYPE
SYNTAX INTEGER
MAX-ACCESS read-write
STATUS current
DESCRIPTION
"Data value."
::= { dataArray16 349 }

dataValue16_350 OBJECT-TYPE
SYNTAX INTEGER
MAX-ACCESS read-write
STATUS current
DESCRIPTION
"Data value."
::= { dataArray16 350 }

dataValue16_351 OBJECT-TYPE
SYNTAX INTEGER
MAX-ACCESS read-write
STATUS current
DESCRIPTION
"Data value."
::= { dataArray16 351 }

dataValue16_352 OBJECT-TYPE
SYNTAX INTEGER
MAX-ACCESS read-write
STATUS current
DESCRIPTION
"Data value."
::= { dataArray16 352 }

dataValue16_353 OBJECT-TYPE
SYNTAX INTEGER
MAX-ACCESS read-write
STATUS current
DESCRIPTION
"Data value."
::= { dataArray16 353 }

dataValue16_354 OBJECT-TYPE
SYNTAX INTEGER
MAX-ACCESS read-write
STATUS current
DESCRIPTION
"Data value."
::= { dataArray16 354 }

dataValue16_355 OBJECT-TYPE
SYNTAX INTEGER
MAX-ACCESS read-write
STATUS current
DESCRIPTION
"Data value."
::= { dataArray16 355 }

dataValue16_356 OBJECT-TYPE
SYNTAX INTEGER
MAX-ACCESS read-write
STATUS current
DESCRIPTION
"Data value."
::= { dataArray16 356 }

dataValue16_357 OBJECT-TYPE
SYNTAX INTEGER
MAX-ACCESS read-write
STATUS current
DESCRIPTION
"Data value."
::= { dataArray16 357 }

dataValue16_358 OBJECT-TYPE
SYNTAX INTEGER
MAX-ACCESS read-write
STATUS current
DESCRIPTION
"Data value."
::= { dataArray16 358 }

dataValue16_359 OBJECT-TYPE
SYNTAX INTEGER
MAX-ACCESS read-write
STATUS current
DESCRIPTION
"Data value."
::= { dataArray16 359 }

dataValue16_360 OBJECT-TYPE
SYNTAX INTEGER
MAX-ACCESS read-write
STATUS current
DESCRIPTION
"Data value."
::= { dataArray16 360 }

dataValue16_361 OBJECT-TYPE
SYNTAX INTEGER
MAX-ACCESS read-write
STATUS current
DESCRIPTION
"Data value."
::= { dataArray16 361 }

dataValue16_362 OBJECT-TYPE
SYNTAX INTEGER
MAX-ACCESS read-write
STATUS current
DESCRIPTION
"Data value."
::= { dataArray16 362 }

dataValue16_363 OBJECT-TYPE
SYNTAX INTEGER
MAX-ACCESS read-write
STATUS current
DESCRIPTION
"Data value."
::= { dataArray16 363 }

dataValue16_364 OBJECT-TYPE
SYNTAX INTEGER
MAX-ACCESS read-write
STATUS current
DESCRIPTION
"Data value."
::= { dataArray16 364 }

dataValue16_365 OBJECT-TYPE
SYNTAX INTEGER
MAX-ACCESS read-write
STATUS current
DESCRIPTION
"Data value."
::= { dataArray16 365 }

dataValue16_366 OBJECT-TYPE
SYNTAX INTEGER
MAX-ACCESS read-write
STATUS current
DESCRIPTION
"Data value."
::= { dataArray16 366 }

dataValue16_367 OBJECT-TYPE
SYNTAX INTEGER
MAX-ACCESS read-write
STATUS current
DESCRIPTION
"Data value."
::= { dataArray16 367 }

dataValue16_368 OBJECT-TYPE
SYNTAX INTEGER
MAX-ACCESS read-write
STATUS current
DESCRIPTION
"Data value."
::= { dataArray16 368 }

dataValue16_369 OBJECT-TYPE
SYNTAX INTEGER
MAX-ACCESS read-write
STATUS current
DESCRIPTION
"Data value."
::= { dataArray16 369 }

dataValue16_370 OBJECT-TYPE
SYNTAX INTEGER
MAX-ACCESS read-write
STATUS current
DESCRIPTION
"Data value."
::= { dataArray16 370 }

dataValue16_371 OBJECT-TYPE
SYNTAX INTEGER
MAX-ACCESS read-write
STATUS current
DESCRIPTION
"Data value."
::= { dataArray16 371 }

dataValue16_372 OBJECT-TYPE
SYNTAX INTEGER
MAX-ACCESS read-write
STATUS current
DESCRIPTION
"Data value."
::= { dataArray16 372 }

dataValue16_373 OBJECT-TYPE
SYNTAX INTEGER
MAX-ACCESS read-write
STATUS current
DESCRIPTION
"Data value."
::= { dataArray16 373 }

dataValue16_374 OBJECT-TYPE
SYNTAX INTEGER
MAX-ACCESS read-write
STATUS current
DESCRIPTION
"Data value."
::= { dataArray16 374 }

dataValue16_375 OBJECT-TYPE
SYNTAX INTEGER
MAX-ACCESS read-write
STATUS current
DESCRIPTION
"Data value."
::= { dataArray16 375 }

dataValue16_376 OBJECT-TYPE
SYNTAX INTEGER
MAX-ACCESS read-write
STATUS current
DESCRIPTION
"Data value."
::= { dataArray16 376 }

dataValue16_377 OBJECT-TYPE
SYNTAX INTEGER
MAX-ACCESS read-write
STATUS current
DESCRIPTION
"Data value."
::= { dataArray16 377 }

dataValue16_378 OBJECT-TYPE
SYNTAX INTEGER
MAX-ACCESS read-write
STATUS current
DESCRIPTION
"Data value."
::= { dataArray16 378 }

dataValue16_379 OBJECT-TYPE
SYNTAX INTEGER
MAX-ACCESS read-write
STATUS current
DESCRIPTION
"Data value."
::= { dataArray16 379 }

dataValue16_380 OBJECT-TYPE
SYNTAX INTEGER
MAX-ACCESS read-write
STATUS current
DESCRIPTION
"Data value."
::= { dataArray16 380 }

dataValue16_381 OBJECT-TYPE
SYNTAX INTEGER
MAX-ACCESS read-write
STATUS current
DESCRIPTION
"Data value."
::= { dataArray16 381 }

dataValue16_382 OBJECT-TYPE
SYNTAX INTEGER
MAX-ACCESS read-write
STATUS current
DESCRIPTION
"Data value."
::= { dataArray16 382 }

dataValue16_383 OBJECT-TYPE
SYNTAX INTEGER
MAX-ACCESS read-write
STATUS current
DESCRIPTION
"Data value."
::= { dataArray16 383 }

dataValue16_384 OBJECT-TYPE
SYNTAX INTEGER
MAX-ACCESS read-write
STATUS current
DESCRIPTION
"Data value."
::= { dataArray16 384 }

dataValue16_385 OBJECT-TYPE
SYNTAX INTEGER
MAX-ACCESS read-write
STATUS current
DESCRIPTION
"Data value."
::= { dataArray16 385 }

dataValue16_386 OBJECT-TYPE
SYNTAX INTEGER
MAX-ACCESS read-write
STATUS current
DESCRIPTION
"Data value."
::= { dataArray16 386 }

dataValue16_387 OBJECT-TYPE
SYNTAX INTEGER
MAX-ACCESS read-write
STATUS current
DESCRIPTION
"Data value."
::= { dataArray16 387 }

dataValue16_388 OBJECT-TYPE
SYNTAX INTEGER
MAX-ACCESS read-write
STATUS current
DESCRIPTION
"Data value."
::= { dataArray16 388 }

dataValue16_389 OBJECT-TYPE
SYNTAX INTEGER
MAX-ACCESS read-write
STATUS current
DESCRIPTION
"Data value."
::= { dataArray16 389 }

dataValue16_390 OBJECT-TYPE
SYNTAX INTEGER
MAX-ACCESS read-write
STATUS current
DESCRIPTION
"Data value."
::= { dataArray16 390 }

dataValue16_391 OBJECT-TYPE
SYNTAX INTEGER
MAX-ACCESS read-write
STATUS current
DESCRIPTION
"Data value."
::= { dataArray16 391 }

dataValue16_392 OBJECT-TYPE
SYNTAX INTEGER
MAX-ACCESS read-write
STATUS current
DESCRIPTION
"Data value."
::= { dataArray16 392 }

dataValue16_393 OBJECT-TYPE
SYNTAX INTEGER
MAX-ACCESS read-write
STATUS current
DESCRIPTION
"Data value."
::= { dataArray16 393 }

dataValue16_394 OBJECT-TYPE
SYNTAX INTEGER
MAX-ACCESS read-write
STATUS current
DESCRIPTION
"Data value."
::= { dataArray16 394 }

dataValue16_395 OBJECT-TYPE
SYNTAX INTEGER
MAX-ACCESS read-write
STATUS current
DESCRIPTION
"Data value."
::= { dataArray16 395 }

dataValue16_396 OBJECT-TYPE
SYNTAX INTEGER
MAX-ACCESS read-write
STATUS current
DESCRIPTION
"Data value."
::= { dataArray16 396 }

dataValue16_397 OBJECT-TYPE
SYNTAX INTEGER
MAX-ACCESS read-write
STATUS current
DESCRIPTION
"Data value."
::= { dataArray16 397 }

dataValue16_398 OBJECT-TYPE
SYNTAX INTEGER
MAX-ACCESS read-write
STATUS current
DESCRIPTION
"Data value."
::= { dataArray16 398 }

dataValue16_399 OBJECT-TYPE
SYNTAX INTEGER
MAX-ACCESS read-write
STATUS current
DESCRIPTION
"Data value."
::= { dataArray16 399 }

dataArray17 OBJECT IDENTIFIER ::= { cc08255400_v1_00a 17 }

dataValue17_0 OBJECT-TYPE
SYNTAX INTEGER
MAX-ACCESS read-write
STATUS current
DESCRIPTION
"Data value."
::= { dataArray17 0 }

dataValue17_1 OBJECT-TYPE
SYNTAX INTEGER
MAX-ACCESS read-write
STATUS current
DESCRIPTION
"Data value."
::= { dataArray17 1 }

dataValue17_2 OBJECT-TYPE
SYNTAX INTEGER
MAX-ACCESS read-write
STATUS current
DESCRIPTION
"Data value."
::= { dataArray17 2 }

dataValue17_3 OBJECT-TYPE
SYNTAX INTEGER
MAX-ACCESS read-write
STATUS current
DESCRIPTION
"Data value."
::= { dataArray17 3 }

dataValue17_4 OBJECT-TYPE
SYNTAX INTEGER
MAX-ACCESS read-write
STATUS current
DESCRIPTION
"Data value."
::= { dataArray17 4 }

dataValue17_5 OBJECT-TYPE
SYNTAX INTEGER
MAX-ACCESS read-write
STATUS current
DESCRIPTION
"Data value."
::= { dataArray17 5 }

dataValue17_6 OBJECT-TYPE
SYNTAX INTEGER
MAX-ACCESS read-write
STATUS current
DESCRIPTION
"Data value."
::= { dataArray17 6 }

dataValue17_7 OBJECT-TYPE
SYNTAX INTEGER
MAX-ACCESS read-write
STATUS current
DESCRIPTION
"Data value."
::= { dataArray17 7 }

dataValue17_8 OBJECT-TYPE
SYNTAX INTEGER
MAX-ACCESS read-write
STATUS current
DESCRIPTION
"Data value."
::= { dataArray17 8 }

dataValue17_9 OBJECT-TYPE
SYNTAX INTEGER
MAX-ACCESS read-write
STATUS current
DESCRIPTION
"Data value."
::= { dataArray17 9 }

dataValue17_10 OBJECT-TYPE
SYNTAX INTEGER
MAX-ACCESS read-write
STATUS current
DESCRIPTION
"Data value."
::= { dataArray17 10 }

dataValue17_11 OBJECT-TYPE
SYNTAX INTEGER
MAX-ACCESS read-write
STATUS current
DESCRIPTION
"Data value."
::= { dataArray17 11 }

dataValue17_12 OBJECT-TYPE
SYNTAX INTEGER
MAX-ACCESS read-write
STATUS current
DESCRIPTION
"Data value."
::= { dataArray17 12 }

dataValue17_13 OBJECT-TYPE
SYNTAX INTEGER
MAX-ACCESS read-write
STATUS current
DESCRIPTION
"Data value."
::= { dataArray17 13 }

dataValue17_14 OBJECT-TYPE
SYNTAX INTEGER
MAX-ACCESS read-write
STATUS current
DESCRIPTION
"Data value."
::= { dataArray17 14 }

dataValue17_15 OBJECT-TYPE
SYNTAX INTEGER
MAX-ACCESS read-write
STATUS current
DESCRIPTION
"Data value."
::= { dataArray17 15 }

dataValue17_16 OBJECT-TYPE
SYNTAX INTEGER
MAX-ACCESS read-write
STATUS current
DESCRIPTION
"Data value."
::= { dataArray17 16 }

dataValue17_17 OBJECT-TYPE
SYNTAX INTEGER
MAX-ACCESS read-write
STATUS current
DESCRIPTION
"Data value."
::= { dataArray17 17 }

dataValue17_18 OBJECT-TYPE
SYNTAX INTEGER
MAX-ACCESS read-write
STATUS current
DESCRIPTION
"Data value."
::= { dataArray17 18 }

dataValue17_19 OBJECT-TYPE
SYNTAX INTEGER
MAX-ACCESS read-write
STATUS current
DESCRIPTION
"Data value."
::= { dataArray17 19 }

dataValue17_20 OBJECT-TYPE
SYNTAX INTEGER
MAX-ACCESS read-write
STATUS current
DESCRIPTION
"Data value."
::= { dataArray17 20 }

dataValue17_21 OBJECT-TYPE
SYNTAX INTEGER
MAX-ACCESS read-write
STATUS current
DESCRIPTION
"Data value."
::= { dataArray17 21 }

dataValue17_22 OBJECT-TYPE
SYNTAX INTEGER
MAX-ACCESS read-write
STATUS current
DESCRIPTION
"Data value."
::= { dataArray17 22 }

dataValue17_23 OBJECT-TYPE
SYNTAX INTEGER
MAX-ACCESS read-write
STATUS current
DESCRIPTION
"Data value."
::= { dataArray17 23 }

dataValue17_24 OBJECT-TYPE
SYNTAX INTEGER
MAX-ACCESS read-write
STATUS current
DESCRIPTION
"Data value."
::= { dataArray17 24 }

dataValue17_25 OBJECT-TYPE
SYNTAX INTEGER
MAX-ACCESS read-write
STATUS current
DESCRIPTION
"Data value."
::= { dataArray17 25 }

dataValue17_26 OBJECT-TYPE
SYNTAX INTEGER
MAX-ACCESS read-write
STATUS current
DESCRIPTION
"Data value."
::= { dataArray17 26 }

dataValue17_27 OBJECT-TYPE
SYNTAX INTEGER
MAX-ACCESS read-write
STATUS current
DESCRIPTION
"Data value."
::= { dataArray17 27 }

dataValue17_28 OBJECT-TYPE
SYNTAX INTEGER
MAX-ACCESS read-write
STATUS current
DESCRIPTION
"Data value."
::= { dataArray17 28 }

dataValue17_29 OBJECT-TYPE
SYNTAX INTEGER
MAX-ACCESS read-write
STATUS current
DESCRIPTION
"Data value."
::= { dataArray17 29 }

dataValue17_30 OBJECT-TYPE
SYNTAX INTEGER
MAX-ACCESS read-write
STATUS current
DESCRIPTION
"Data value."
::= { dataArray17 30 }

dataValue17_31 OBJECT-TYPE
SYNTAX INTEGER
MAX-ACCESS read-write
STATUS current
DESCRIPTION
"Data value."
::= { dataArray17 31 }

dataValue17_32 OBJECT-TYPE
SYNTAX INTEGER
MAX-ACCESS read-write
STATUS current
DESCRIPTION
"Data value."
::= { dataArray17 32 }

dataValue17_33 OBJECT-TYPE
SYNTAX INTEGER
MAX-ACCESS read-write
STATUS current
DESCRIPTION
"Data value."
::= { dataArray17 33 }

dataValue17_34 OBJECT-TYPE
SYNTAX INTEGER
MAX-ACCESS read-write
STATUS current
DESCRIPTION
"Data value."
::= { dataArray17 34 }

dataValue17_35 OBJECT-TYPE
SYNTAX INTEGER
MAX-ACCESS read-write
STATUS current
DESCRIPTION
"Data value."
::= { dataArray17 35 }

dataValue17_36 OBJECT-TYPE
SYNTAX INTEGER
MAX-ACCESS read-write
STATUS current
DESCRIPTION
"Data value."
::= { dataArray17 36 }

dataValue17_37 OBJECT-TYPE
SYNTAX INTEGER
MAX-ACCESS read-write
STATUS current
DESCRIPTION
"Data value."
::= { dataArray17 37 }

dataValue17_38 OBJECT-TYPE
SYNTAX INTEGER
MAX-ACCESS read-write
STATUS current
DESCRIPTION
"Data value."
::= { dataArray17 38 }

dataValue17_39 OBJECT-TYPE
SYNTAX INTEGER
MAX-ACCESS read-write
STATUS current
DESCRIPTION
"Data value."
::= { dataArray17 39 }

dataValue17_40 OBJECT-TYPE
SYNTAX INTEGER
MAX-ACCESS read-write
STATUS current
DESCRIPTION
"Data value."
::= { dataArray17 40 }

dataValue17_41 OBJECT-TYPE
SYNTAX INTEGER
MAX-ACCESS read-write
STATUS current
DESCRIPTION
"Data value."
::= { dataArray17 41 }

dataValue17_42 OBJECT-TYPE
SYNTAX INTEGER
MAX-ACCESS read-write
STATUS current
DESCRIPTION
"Data value."
::= { dataArray17 42 }

dataValue17_43 OBJECT-TYPE
SYNTAX INTEGER
MAX-ACCESS read-write
STATUS current
DESCRIPTION
"Data value."
::= { dataArray17 43 }

dataValue17_44 OBJECT-TYPE
SYNTAX INTEGER
MAX-ACCESS read-write
STATUS current
DESCRIPTION
"Data value."
::= { dataArray17 44 }

dataValue17_45 OBJECT-TYPE
SYNTAX INTEGER
MAX-ACCESS read-write
STATUS current
DESCRIPTION
"Data value."
::= { dataArray17 45 }

dataValue17_46 OBJECT-TYPE
SYNTAX INTEGER
MAX-ACCESS read-write
STATUS current
DESCRIPTION
"Data value."
::= { dataArray17 46 }

dataValue17_47 OBJECT-TYPE
SYNTAX INTEGER
MAX-ACCESS read-write
STATUS current
DESCRIPTION
"Data value."
::= { dataArray17 47 }

dataValue17_48 OBJECT-TYPE
SYNTAX INTEGER
MAX-ACCESS read-write
STATUS current
DESCRIPTION
"Data value."
::= { dataArray17 48 }

dataValue17_49 OBJECT-TYPE
SYNTAX INTEGER
MAX-ACCESS read-write
STATUS current
DESCRIPTION
"Data value."
::= { dataArray17 49 }

dataValue17_50 OBJECT-TYPE
SYNTAX INTEGER
MAX-ACCESS read-write
STATUS current
DESCRIPTION
"Data value."
::= { dataArray17 50 }

dataValue17_51 OBJECT-TYPE
SYNTAX INTEGER
MAX-ACCESS read-write
STATUS current
DESCRIPTION
"Data value."
::= { dataArray17 51 }

dataValue17_52 OBJECT-TYPE
SYNTAX INTEGER
MAX-ACCESS read-write
STATUS current
DESCRIPTION
"Data value."
::= { dataArray17 52 }

dataValue17_53 OBJECT-TYPE
SYNTAX INTEGER
MAX-ACCESS read-write
STATUS current
DESCRIPTION
"Data value."
::= { dataArray17 53 }

dataValue17_54 OBJECT-TYPE
SYNTAX INTEGER
MAX-ACCESS read-write
STATUS current
DESCRIPTION
"Data value."
::= { dataArray17 54 }

dataValue17_55 OBJECT-TYPE
SYNTAX INTEGER
MAX-ACCESS read-write
STATUS current
DESCRIPTION
"Data value."
::= { dataArray17 55 }

dataValue17_56 OBJECT-TYPE
SYNTAX INTEGER
MAX-ACCESS read-write
STATUS current
DESCRIPTION
"Data value."
::= { dataArray17 56 }

dataValue17_57 OBJECT-TYPE
SYNTAX INTEGER
MAX-ACCESS read-write
STATUS current
DESCRIPTION
"Data value."
::= { dataArray17 57 }

dataValue17_58 OBJECT-TYPE
SYNTAX INTEGER
MAX-ACCESS read-write
STATUS current
DESCRIPTION
"Data value."
::= { dataArray17 58 }

dataValue17_59 OBJECT-TYPE
SYNTAX INTEGER
MAX-ACCESS read-write
STATUS current
DESCRIPTION
"Data value."
::= { dataArray17 59 }

dataValue17_60 OBJECT-TYPE
SYNTAX INTEGER
MAX-ACCESS read-write
STATUS current
DESCRIPTION
"Data value."
::= { dataArray17 60 }

dataValue17_61 OBJECT-TYPE
SYNTAX INTEGER
MAX-ACCESS read-write
STATUS current
DESCRIPTION
"Data value."
::= { dataArray17 61 }

dataValue17_62 OBJECT-TYPE
SYNTAX INTEGER
MAX-ACCESS read-write
STATUS current
DESCRIPTION
"Data value."
::= { dataArray17 62 }

dataValue17_63 OBJECT-TYPE
SYNTAX INTEGER
MAX-ACCESS read-write
STATUS current
DESCRIPTION
"Data value."
::= { dataArray17 63 }

dataValue17_64 OBJECT-TYPE
SYNTAX INTEGER
MAX-ACCESS read-write
STATUS current
DESCRIPTION
"Data value."
::= { dataArray17 64 }

dataValue17_65 OBJECT-TYPE
SYNTAX INTEGER
MAX-ACCESS read-write
STATUS current
DESCRIPTION
"Data value."
::= { dataArray17 65 }

dataValue17_66 OBJECT-TYPE
SYNTAX INTEGER
MAX-ACCESS read-write
STATUS current
DESCRIPTION
"Data value."
::= { dataArray17 66 }

dataValue17_67 OBJECT-TYPE
SYNTAX INTEGER
MAX-ACCESS read-write
STATUS current
DESCRIPTION
"Data value."
::= { dataArray17 67 }

dataValue17_68 OBJECT-TYPE
SYNTAX INTEGER
MAX-ACCESS read-write
STATUS current
DESCRIPTION
"Data value."
::= { dataArray17 68 }

dataValue17_69 OBJECT-TYPE
SYNTAX INTEGER
MAX-ACCESS read-write
STATUS current
DESCRIPTION
"Data value."
::= { dataArray17 69 }

dataValue17_70 OBJECT-TYPE
SYNTAX INTEGER
MAX-ACCESS read-write
STATUS current
DESCRIPTION
"Data value."
::= { dataArray17 70 }

dataValue17_71 OBJECT-TYPE
SYNTAX INTEGER
MAX-ACCESS read-write
STATUS current
DESCRIPTION
"Data value."
::= { dataArray17 71 }

dataValue17_72 OBJECT-TYPE
SYNTAX INTEGER
MAX-ACCESS read-write
STATUS current
DESCRIPTION
"Data value."
::= { dataArray17 72 }

dataValue17_73 OBJECT-TYPE
SYNTAX INTEGER
MAX-ACCESS read-write
STATUS current
DESCRIPTION
"Data value."
::= { dataArray17 73 }

dataValue17_74 OBJECT-TYPE
SYNTAX INTEGER
MAX-ACCESS read-write
STATUS current
DESCRIPTION
"Data value."
::= { dataArray17 74 }

dataValue17_75 OBJECT-TYPE
SYNTAX INTEGER
MAX-ACCESS read-write
STATUS current
DESCRIPTION
"Data value."
::= { dataArray17 75 }

dataValue17_76 OBJECT-TYPE
SYNTAX INTEGER
MAX-ACCESS read-write
STATUS current
DESCRIPTION
"Data value."
::= { dataArray17 76 }

dataValue17_77 OBJECT-TYPE
SYNTAX INTEGER
MAX-ACCESS read-write
STATUS current
DESCRIPTION
"Data value."
::= { dataArray17 77 }

dataValue17_78 OBJECT-TYPE
SYNTAX INTEGER
MAX-ACCESS read-write
STATUS current
DESCRIPTION
"Data value."
::= { dataArray17 78 }

dataValue17_79 OBJECT-TYPE
SYNTAX INTEGER
MAX-ACCESS read-write
STATUS current
DESCRIPTION
"Data value."
::= { dataArray17 79 }

dataValue17_80 OBJECT-TYPE
SYNTAX INTEGER
MAX-ACCESS read-write
STATUS current
DESCRIPTION
"Data value."
::= { dataArray17 80 }

dataValue17_81 OBJECT-TYPE
SYNTAX INTEGER
MAX-ACCESS read-write
STATUS current
DESCRIPTION
"Data value."
::= { dataArray17 81 }

dataValue17_82 OBJECT-TYPE
SYNTAX INTEGER
MAX-ACCESS read-write
STATUS current
DESCRIPTION
"Data value."
::= { dataArray17 82 }

dataValue17_83 OBJECT-TYPE
SYNTAX INTEGER
MAX-ACCESS read-write
STATUS current
DESCRIPTION
"Data value."
::= { dataArray17 83 }

dataValue17_84 OBJECT-TYPE
SYNTAX INTEGER
MAX-ACCESS read-write
STATUS current
DESCRIPTION
"Data value."
::= { dataArray17 84 }

dataValue17_85 OBJECT-TYPE
SYNTAX INTEGER
MAX-ACCESS read-write
STATUS current
DESCRIPTION
"Data value."
::= { dataArray17 85 }

dataValue17_86 OBJECT-TYPE
SYNTAX INTEGER
MAX-ACCESS read-write
STATUS current
DESCRIPTION
"Data value."
::= { dataArray17 86 }

dataValue17_87 OBJECT-TYPE
SYNTAX INTEGER
MAX-ACCESS read-write
STATUS current
DESCRIPTION
"Data value."
::= { dataArray17 87 }

dataValue17_88 OBJECT-TYPE
SYNTAX INTEGER
MAX-ACCESS read-write
STATUS current
DESCRIPTION
"Data value."
::= { dataArray17 88 }

dataValue17_89 OBJECT-TYPE
SYNTAX INTEGER
MAX-ACCESS read-write
STATUS current
DESCRIPTION
"Data value."
::= { dataArray17 89 }

dataValue17_90 OBJECT-TYPE
SYNTAX INTEGER
MAX-ACCESS read-write
STATUS current
DESCRIPTION
"Data value."
::= { dataArray17 90 }

dataValue17_91 OBJECT-TYPE
SYNTAX INTEGER
MAX-ACCESS read-write
STATUS current
DESCRIPTION
"Data value."
::= { dataArray17 91 }

dataValue17_92 OBJECT-TYPE
SYNTAX INTEGER
MAX-ACCESS read-write
STATUS current
DESCRIPTION
"Data value."
::= { dataArray17 92 }

dataValue17_93 OBJECT-TYPE
SYNTAX INTEGER
MAX-ACCESS read-write
STATUS current
DESCRIPTION
"Data value."
::= { dataArray17 93 }

dataValue17_94 OBJECT-TYPE
SYNTAX INTEGER
MAX-ACCESS read-write
STATUS current
DESCRIPTION
"Data value."
::= { dataArray17 94 }

dataValue17_95 OBJECT-TYPE
SYNTAX INTEGER
MAX-ACCESS read-write
STATUS current
DESCRIPTION
"Data value."
::= { dataArray17 95 }

dataValue17_96 OBJECT-TYPE
SYNTAX INTEGER
MAX-ACCESS read-write
STATUS current
DESCRIPTION
"Data value."
::= { dataArray17 96 }

dataValue17_97 OBJECT-TYPE
SYNTAX INTEGER
MAX-ACCESS read-write
STATUS current
DESCRIPTION
"Data value."
::= { dataArray17 97 }

dataValue17_98 OBJECT-TYPE
SYNTAX INTEGER
MAX-ACCESS read-write
STATUS current
DESCRIPTION
"Data value."
::= { dataArray17 98 }

dataValue17_99 OBJECT-TYPE
SYNTAX INTEGER
MAX-ACCESS read-write
STATUS current
DESCRIPTION
"Data value."
::= { dataArray17 99 }

dataValue17_100 OBJECT-TYPE
SYNTAX INTEGER
MAX-ACCESS read-write
STATUS current
DESCRIPTION
"Data value."
::= { dataArray17 100 }

dataValue17_101 OBJECT-TYPE
SYNTAX INTEGER
MAX-ACCESS read-write
STATUS current
DESCRIPTION
"Data value."
::= { dataArray17 101 }

dataValue17_102 OBJECT-TYPE
SYNTAX INTEGER
MAX-ACCESS read-write
STATUS current
DESCRIPTION
"Data value."
::= { dataArray17 102 }

dataValue17_103 OBJECT-TYPE
SYNTAX INTEGER
MAX-ACCESS read-write
STATUS current
DESCRIPTION
"Data value."
::= { dataArray17 103 }

dataValue17_104 OBJECT-TYPE
SYNTAX INTEGER
MAX-ACCESS read-write
STATUS current
DESCRIPTION
"Data value."
::= { dataArray17 104 }

dataValue17_105 OBJECT-TYPE
SYNTAX INTEGER
MAX-ACCESS read-write
STATUS current
DESCRIPTION
"Data value."
::= { dataArray17 105 }

dataValue17_106 OBJECT-TYPE
SYNTAX INTEGER
MAX-ACCESS read-write
STATUS current
DESCRIPTION
"Data value."
::= { dataArray17 106 }

dataValue17_107 OBJECT-TYPE
SYNTAX INTEGER
MAX-ACCESS read-write
STATUS current
DESCRIPTION
"Data value."
::= { dataArray17 107 }

dataValue17_108 OBJECT-TYPE
SYNTAX INTEGER
MAX-ACCESS read-write
STATUS current
DESCRIPTION
"Data value."
::= { dataArray17 108 }

dataValue17_109 OBJECT-TYPE
SYNTAX INTEGER
MAX-ACCESS read-write
STATUS current
DESCRIPTION
"Data value."
::= { dataArray17 109 }

dataValue17_110 OBJECT-TYPE
SYNTAX INTEGER
MAX-ACCESS read-write
STATUS current
DESCRIPTION
"Data value."
::= { dataArray17 110 }

dataValue17_111 OBJECT-TYPE
SYNTAX INTEGER
MAX-ACCESS read-write
STATUS current
DESCRIPTION
"Data value."
::= { dataArray17 111 }

dataValue17_112 OBJECT-TYPE
SYNTAX INTEGER
MAX-ACCESS read-write
STATUS current
DESCRIPTION
"Data value."
::= { dataArray17 112 }

dataValue17_113 OBJECT-TYPE
SYNTAX INTEGER
MAX-ACCESS read-write
STATUS current
DESCRIPTION
"Data value."
::= { dataArray17 113 }

dataValue17_114 OBJECT-TYPE
SYNTAX INTEGER
MAX-ACCESS read-write
STATUS current
DESCRIPTION
"Data value."
::= { dataArray17 114 }

dataValue17_115 OBJECT-TYPE
SYNTAX INTEGER
MAX-ACCESS read-write
STATUS current
DESCRIPTION
"Data value."
::= { dataArray17 115 }

dataValue17_116 OBJECT-TYPE
SYNTAX INTEGER
MAX-ACCESS read-write
STATUS current
DESCRIPTION
"Data value."
::= { dataArray17 116 }

dataValue17_117 OBJECT-TYPE
SYNTAX INTEGER
MAX-ACCESS read-write
STATUS current
DESCRIPTION
"Data value."
::= { dataArray17 117 }

dataValue17_118 OBJECT-TYPE
SYNTAX INTEGER
MAX-ACCESS read-write
STATUS current
DESCRIPTION
"Data value."
::= { dataArray17 118 }

dataValue17_119 OBJECT-TYPE
SYNTAX INTEGER
MAX-ACCESS read-write
STATUS current
DESCRIPTION
"Data value."
::= { dataArray17 119 }

dataValue17_120 OBJECT-TYPE
SYNTAX INTEGER
MAX-ACCESS read-write
STATUS current
DESCRIPTION
"Data value."
::= { dataArray17 120 }

dataValue17_121 OBJECT-TYPE
SYNTAX INTEGER
MAX-ACCESS read-write
STATUS current
DESCRIPTION
"Data value."
::= { dataArray17 121 }

dataValue17_122 OBJECT-TYPE
SYNTAX INTEGER
MAX-ACCESS read-write
STATUS current
DESCRIPTION
"Data value."
::= { dataArray17 122 }

dataValue17_123 OBJECT-TYPE
SYNTAX INTEGER
MAX-ACCESS read-write
STATUS current
DESCRIPTION
"Data value."
::= { dataArray17 123 }

dataValue17_124 OBJECT-TYPE
SYNTAX INTEGER
MAX-ACCESS read-write
STATUS current
DESCRIPTION
"Data value."
::= { dataArray17 124 }

dataValue17_125 OBJECT-TYPE
SYNTAX INTEGER
MAX-ACCESS read-write
STATUS current
DESCRIPTION
"Data value."
::= { dataArray17 125 }

dataValue17_126 OBJECT-TYPE
SYNTAX INTEGER
MAX-ACCESS read-write
STATUS current
DESCRIPTION
"Data value."
::= { dataArray17 126 }

dataValue17_127 OBJECT-TYPE
SYNTAX INTEGER
MAX-ACCESS read-write
STATUS current
DESCRIPTION
"Data value."
::= { dataArray17 127 }

dataValue17_128 OBJECT-TYPE
SYNTAX INTEGER
MAX-ACCESS read-write
STATUS current
DESCRIPTION
"Data value."
::= { dataArray17 128 }

dataValue17_129 OBJECT-TYPE
SYNTAX INTEGER
MAX-ACCESS read-write
STATUS current
DESCRIPTION
"Data value."
::= { dataArray17 129 }

dataValue17_130 OBJECT-TYPE
SYNTAX INTEGER
MAX-ACCESS read-write
STATUS current
DESCRIPTION
"Data value."
::= { dataArray17 130 }

dataValue17_131 OBJECT-TYPE
SYNTAX INTEGER
MAX-ACCESS read-write
STATUS current
DESCRIPTION
"Data value."
::= { dataArray17 131 }

dataValue17_132 OBJECT-TYPE
SYNTAX INTEGER
MAX-ACCESS read-write
STATUS current
DESCRIPTION
"Data value."
::= { dataArray17 132 }

dataValue17_133 OBJECT-TYPE
SYNTAX INTEGER
MAX-ACCESS read-write
STATUS current
DESCRIPTION
"Data value."
::= { dataArray17 133 }

dataValue17_134 OBJECT-TYPE
SYNTAX INTEGER
MAX-ACCESS read-write
STATUS current
DESCRIPTION
"Data value."
::= { dataArray17 134 }

dataValue17_135 OBJECT-TYPE
SYNTAX INTEGER
MAX-ACCESS read-write
STATUS current
DESCRIPTION
"Data value."
::= { dataArray17 135 }

dataValue17_136 OBJECT-TYPE
SYNTAX INTEGER
MAX-ACCESS read-write
STATUS current
DESCRIPTION
"Data value."
::= { dataArray17 136 }

dataValue17_137 OBJECT-TYPE
SYNTAX INTEGER
MAX-ACCESS read-write
STATUS current
DESCRIPTION
"Data value."
::= { dataArray17 137 }

dataValue17_138 OBJECT-TYPE
SYNTAX INTEGER
MAX-ACCESS read-write
STATUS current
DESCRIPTION
"Data value."
::= { dataArray17 138 }

dataValue17_139 OBJECT-TYPE
SYNTAX INTEGER
MAX-ACCESS read-write
STATUS current
DESCRIPTION
"Data value."
::= { dataArray17 139 }

dataValue17_140 OBJECT-TYPE
SYNTAX INTEGER
MAX-ACCESS read-write
STATUS current
DESCRIPTION
"Data value."
::= { dataArray17 140 }

dataValue17_141 OBJECT-TYPE
SYNTAX INTEGER
MAX-ACCESS read-write
STATUS current
DESCRIPTION
"Data value."
::= { dataArray17 141 }

dataValue17_142 OBJECT-TYPE
SYNTAX INTEGER
MAX-ACCESS read-write
STATUS current
DESCRIPTION
"Data value."
::= { dataArray17 142 }

dataValue17_143 OBJECT-TYPE
SYNTAX INTEGER
MAX-ACCESS read-write
STATUS current
DESCRIPTION
"Data value."
::= { dataArray17 143 }

dataValue17_144 OBJECT-TYPE
SYNTAX INTEGER
MAX-ACCESS read-write
STATUS current
DESCRIPTION
"Data value."
::= { dataArray17 144 }

dataValue17_145 OBJECT-TYPE
SYNTAX INTEGER
MAX-ACCESS read-write
STATUS current
DESCRIPTION
"Data value."
::= { dataArray17 145 }

dataValue17_146 OBJECT-TYPE
SYNTAX INTEGER
MAX-ACCESS read-write
STATUS current
DESCRIPTION
"Data value."
::= { dataArray17 146 }

dataValue17_147 OBJECT-TYPE
SYNTAX INTEGER
MAX-ACCESS read-write
STATUS current
DESCRIPTION
"Data value."
::= { dataArray17 147 }

dataValue17_148 OBJECT-TYPE
SYNTAX INTEGER
MAX-ACCESS read-write
STATUS current
DESCRIPTION
"Data value."
::= { dataArray17 148 }

dataValue17_149 OBJECT-TYPE
SYNTAX INTEGER
MAX-ACCESS read-write
STATUS current
DESCRIPTION
"Data value."
::= { dataArray17 149 }

dataValue17_150 OBJECT-TYPE
SYNTAX INTEGER
MAX-ACCESS read-write
STATUS current
DESCRIPTION
"Data value."
::= { dataArray17 150 }

dataValue17_151 OBJECT-TYPE
SYNTAX INTEGER
MAX-ACCESS read-write
STATUS current
DESCRIPTION
"Data value."
::= { dataArray17 151 }

dataValue17_152 OBJECT-TYPE
SYNTAX INTEGER
MAX-ACCESS read-write
STATUS current
DESCRIPTION
"Data value."
::= { dataArray17 152 }

dataValue17_153 OBJECT-TYPE
SYNTAX INTEGER
MAX-ACCESS read-write
STATUS current
DESCRIPTION
"Data value."
::= { dataArray17 153 }

dataValue17_154 OBJECT-TYPE
SYNTAX INTEGER
MAX-ACCESS read-write
STATUS current
DESCRIPTION
"Data value."
::= { dataArray17 154 }

dataValue17_155 OBJECT-TYPE
SYNTAX INTEGER
MAX-ACCESS read-write
STATUS current
DESCRIPTION
"Data value."
::= { dataArray17 155 }

dataValue17_156 OBJECT-TYPE
SYNTAX INTEGER
MAX-ACCESS read-write
STATUS current
DESCRIPTION
"Data value."
::= { dataArray17 156 }

dataValue17_157 OBJECT-TYPE
SYNTAX INTEGER
MAX-ACCESS read-write
STATUS current
DESCRIPTION
"Data value."
::= { dataArray17 157 }

dataValue17_158 OBJECT-TYPE
SYNTAX INTEGER
MAX-ACCESS read-write
STATUS current
DESCRIPTION
"Data value."
::= { dataArray17 158 }

dataValue17_159 OBJECT-TYPE
SYNTAX INTEGER
MAX-ACCESS read-write
STATUS current
DESCRIPTION
"Data value."
::= { dataArray17 159 }

dataValue17_160 OBJECT-TYPE
SYNTAX INTEGER
MAX-ACCESS read-write
STATUS current
DESCRIPTION
"Data value."
::= { dataArray17 160 }

dataValue17_161 OBJECT-TYPE
SYNTAX INTEGER
MAX-ACCESS read-write
STATUS current
DESCRIPTION
"Data value."
::= { dataArray17 161 }

dataValue17_162 OBJECT-TYPE
SYNTAX INTEGER
MAX-ACCESS read-write
STATUS current
DESCRIPTION
"Data value."
::= { dataArray17 162 }

dataValue17_163 OBJECT-TYPE
SYNTAX INTEGER
MAX-ACCESS read-write
STATUS current
DESCRIPTION
"Data value."
::= { dataArray17 163 }

dataValue17_164 OBJECT-TYPE
SYNTAX INTEGER
MAX-ACCESS read-write
STATUS current
DESCRIPTION
"Data value."
::= { dataArray17 164 }

dataValue17_165 OBJECT-TYPE
SYNTAX INTEGER
MAX-ACCESS read-write
STATUS current
DESCRIPTION
"Data value."
::= { dataArray17 165 }

dataValue17_166 OBJECT-TYPE
SYNTAX INTEGER
MAX-ACCESS read-write
STATUS current
DESCRIPTION
"Data value."
::= { dataArray17 166 }

dataValue17_167 OBJECT-TYPE
SYNTAX INTEGER
MAX-ACCESS read-write
STATUS current
DESCRIPTION
"Data value."
::= { dataArray17 167 }

dataValue17_168 OBJECT-TYPE
SYNTAX INTEGER
MAX-ACCESS read-write
STATUS current
DESCRIPTION
"Data value."
::= { dataArray17 168 }

dataValue17_169 OBJECT-TYPE
SYNTAX INTEGER
MAX-ACCESS read-write
STATUS current
DESCRIPTION
"Data value."
::= { dataArray17 169 }

dataValue17_170 OBJECT-TYPE
SYNTAX INTEGER
MAX-ACCESS read-write
STATUS current
DESCRIPTION
"Data value."
::= { dataArray17 170 }

dataValue17_171 OBJECT-TYPE
SYNTAX INTEGER
MAX-ACCESS read-write
STATUS current
DESCRIPTION
"Data value."
::= { dataArray17 171 }

dataValue17_172 OBJECT-TYPE
SYNTAX INTEGER
MAX-ACCESS read-write
STATUS current
DESCRIPTION
"Data value."
::= { dataArray17 172 }

dataValue17_173 OBJECT-TYPE
SYNTAX INTEGER
MAX-ACCESS read-write
STATUS current
DESCRIPTION
"Data value."
::= { dataArray17 173 }

dataValue17_174 OBJECT-TYPE
SYNTAX INTEGER
MAX-ACCESS read-write
STATUS current
DESCRIPTION
"Data value."
::= { dataArray17 174 }

dataValue17_175 OBJECT-TYPE
SYNTAX INTEGER
MAX-ACCESS read-write
STATUS current
DESCRIPTION
"Data value."
::= { dataArray17 175 }

dataValue17_176 OBJECT-TYPE
SYNTAX INTEGER
MAX-ACCESS read-write
STATUS current
DESCRIPTION
"Data value."
::= { dataArray17 176 }

dataValue17_177 OBJECT-TYPE
SYNTAX INTEGER
MAX-ACCESS read-write
STATUS current
DESCRIPTION
"Data value."
::= { dataArray17 177 }

dataValue17_178 OBJECT-TYPE
SYNTAX INTEGER
MAX-ACCESS read-write
STATUS current
DESCRIPTION
"Data value."
::= { dataArray17 178 }

dataValue17_179 OBJECT-TYPE
SYNTAX INTEGER
MAX-ACCESS read-write
STATUS current
DESCRIPTION
"Data value."
::= { dataArray17 179 }

dataValue17_180 OBJECT-TYPE
SYNTAX INTEGER
MAX-ACCESS read-write
STATUS current
DESCRIPTION
"Data value."
::= { dataArray17 180 }

dataValue17_181 OBJECT-TYPE
SYNTAX INTEGER
MAX-ACCESS read-write
STATUS current
DESCRIPTION
"Data value."
::= { dataArray17 181 }

dataValue17_182 OBJECT-TYPE
SYNTAX INTEGER
MAX-ACCESS read-write
STATUS current
DESCRIPTION
"Data value."
::= { dataArray17 182 }

dataValue17_183 OBJECT-TYPE
SYNTAX INTEGER
MAX-ACCESS read-write
STATUS current
DESCRIPTION
"Data value."
::= { dataArray17 183 }

dataValue17_184 OBJECT-TYPE
SYNTAX INTEGER
MAX-ACCESS read-write
STATUS current
DESCRIPTION
"Data value."
::= { dataArray17 184 }

dataValue17_185 OBJECT-TYPE
SYNTAX INTEGER
MAX-ACCESS read-write
STATUS current
DESCRIPTION
"Data value."
::= { dataArray17 185 }

dataValue17_186 OBJECT-TYPE
SYNTAX INTEGER
MAX-ACCESS read-write
STATUS current
DESCRIPTION
"Data value."
::= { dataArray17 186 }

dataValue17_187 OBJECT-TYPE
SYNTAX INTEGER
MAX-ACCESS read-write
STATUS current
DESCRIPTION
"Data value."
::= { dataArray17 187 }

dataValue17_188 OBJECT-TYPE
SYNTAX INTEGER
MAX-ACCESS read-write
STATUS current
DESCRIPTION
"Data value."
::= { dataArray17 188 }

dataValue17_189 OBJECT-TYPE
SYNTAX INTEGER
MAX-ACCESS read-write
STATUS current
DESCRIPTION
"Data value."
::= { dataArray17 189 }

dataValue17_190 OBJECT-TYPE
SYNTAX INTEGER
MAX-ACCESS read-write
STATUS current
DESCRIPTION
"Data value."
::= { dataArray17 190 }

dataValue17_191 OBJECT-TYPE
SYNTAX INTEGER
MAX-ACCESS read-write
STATUS current
DESCRIPTION
"Data value."
::= { dataArray17 191 }

dataValue17_192 OBJECT-TYPE
SYNTAX INTEGER
MAX-ACCESS read-write
STATUS current
DESCRIPTION
"Data value."
::= { dataArray17 192 }

dataValue17_193 OBJECT-TYPE
SYNTAX INTEGER
MAX-ACCESS read-write
STATUS current
DESCRIPTION
"Data value."
::= { dataArray17 193 }

dataValue17_194 OBJECT-TYPE
SYNTAX INTEGER
MAX-ACCESS read-write
STATUS current
DESCRIPTION
"Data value."
::= { dataArray17 194 }

dataValue17_195 OBJECT-TYPE
SYNTAX INTEGER
MAX-ACCESS read-write
STATUS current
DESCRIPTION
"Data value."
::= { dataArray17 195 }

dataValue17_196 OBJECT-TYPE
SYNTAX INTEGER
MAX-ACCESS read-write
STATUS current
DESCRIPTION
"Data value."
::= { dataArray17 196 }

dataValue17_197 OBJECT-TYPE
SYNTAX INTEGER
MAX-ACCESS read-write
STATUS current
DESCRIPTION
"Data value."
::= { dataArray17 197 }

dataValue17_198 OBJECT-TYPE
SYNTAX INTEGER
MAX-ACCESS read-write
STATUS current
DESCRIPTION
"Data value."
::= { dataArray17 198 }

dataValue17_199 OBJECT-TYPE
SYNTAX INTEGER
MAX-ACCESS read-write
STATUS current
DESCRIPTION
"Data value."
::= { dataArray17 199 }

dataValue17_200 OBJECT-TYPE
SYNTAX INTEGER
MAX-ACCESS read-write
STATUS current
DESCRIPTION
"Data value."
::= { dataArray17 200 }

dataValue17_201 OBJECT-TYPE
SYNTAX INTEGER
MAX-ACCESS read-write
STATUS current
DESCRIPTION
"Data value."
::= { dataArray17 201 }

dataValue17_202 OBJECT-TYPE
SYNTAX INTEGER
MAX-ACCESS read-write
STATUS current
DESCRIPTION
"Data value."
::= { dataArray17 202 }

dataValue17_203 OBJECT-TYPE
SYNTAX INTEGER
MAX-ACCESS read-write
STATUS current
DESCRIPTION
"Data value."
::= { dataArray17 203 }

dataValue17_204 OBJECT-TYPE
SYNTAX INTEGER
MAX-ACCESS read-write
STATUS current
DESCRIPTION
"Data value."
::= { dataArray17 204 }

dataValue17_205 OBJECT-TYPE
SYNTAX INTEGER
MAX-ACCESS read-write
STATUS current
DESCRIPTION
"Data value."
::= { dataArray17 205 }

dataValue17_206 OBJECT-TYPE
SYNTAX INTEGER
MAX-ACCESS read-write
STATUS current
DESCRIPTION
"Data value."
::= { dataArray17 206 }

dataValue17_207 OBJECT-TYPE
SYNTAX INTEGER
MAX-ACCESS read-write
STATUS current
DESCRIPTION
"Data value."
::= { dataArray17 207 }

dataValue17_208 OBJECT-TYPE
SYNTAX INTEGER
MAX-ACCESS read-write
STATUS current
DESCRIPTION
"Data value."
::= { dataArray17 208 }

dataValue17_209 OBJECT-TYPE
SYNTAX INTEGER
MAX-ACCESS read-write
STATUS current
DESCRIPTION
"Data value."
::= { dataArray17 209 }

dataValue17_210 OBJECT-TYPE
SYNTAX INTEGER
MAX-ACCESS read-write
STATUS current
DESCRIPTION
"Data value."
::= { dataArray17 210 }

dataValue17_211 OBJECT-TYPE
SYNTAX INTEGER
MAX-ACCESS read-write
STATUS current
DESCRIPTION
"Data value."
::= { dataArray17 211 }

dataValue17_212 OBJECT-TYPE
SYNTAX INTEGER
MAX-ACCESS read-write
STATUS current
DESCRIPTION
"Data value."
::= { dataArray17 212 }

dataValue17_213 OBJECT-TYPE
SYNTAX INTEGER
MAX-ACCESS read-write
STATUS current
DESCRIPTION
"Data value."
::= { dataArray17 213 }

dataValue17_214 OBJECT-TYPE
SYNTAX INTEGER
MAX-ACCESS read-write
STATUS current
DESCRIPTION
"Data value."
::= { dataArray17 214 }

dataValue17_215 OBJECT-TYPE
SYNTAX INTEGER
MAX-ACCESS read-write
STATUS current
DESCRIPTION
"Data value."
::= { dataArray17 215 }

dataValue17_216 OBJECT-TYPE
SYNTAX INTEGER
MAX-ACCESS read-write
STATUS current
DESCRIPTION
"Data value."
::= { dataArray17 216 }

dataValue17_217 OBJECT-TYPE
SYNTAX INTEGER
MAX-ACCESS read-write
STATUS current
DESCRIPTION
"Data value."
::= { dataArray17 217 }

dataValue17_218 OBJECT-TYPE
SYNTAX INTEGER
MAX-ACCESS read-write
STATUS current
DESCRIPTION
"Data value."
::= { dataArray17 218 }

dataValue17_219 OBJECT-TYPE
SYNTAX INTEGER
MAX-ACCESS read-write
STATUS current
DESCRIPTION
"Data value."
::= { dataArray17 219 }

dataValue17_220 OBJECT-TYPE
SYNTAX INTEGER
MAX-ACCESS read-write
STATUS current
DESCRIPTION
"Data value."
::= { dataArray17 220 }

dataValue17_221 OBJECT-TYPE
SYNTAX INTEGER
MAX-ACCESS read-write
STATUS current
DESCRIPTION
"Data value."
::= { dataArray17 221 }

dataValue17_222 OBJECT-TYPE
SYNTAX INTEGER
MAX-ACCESS read-write
STATUS current
DESCRIPTION
"Data value."
::= { dataArray17 222 }

dataValue17_223 OBJECT-TYPE
SYNTAX INTEGER
MAX-ACCESS read-write
STATUS current
DESCRIPTION
"Data value."
::= { dataArray17 223 }

dataValue17_224 OBJECT-TYPE
SYNTAX INTEGER
MAX-ACCESS read-write
STATUS current
DESCRIPTION
"Data value."
::= { dataArray17 224 }

dataValue17_225 OBJECT-TYPE
SYNTAX INTEGER
MAX-ACCESS read-write
STATUS current
DESCRIPTION
"Data value."
::= { dataArray17 225 }

dataValue17_226 OBJECT-TYPE
SYNTAX INTEGER
MAX-ACCESS read-write
STATUS current
DESCRIPTION
"Data value."
::= { dataArray17 226 }

dataValue17_227 OBJECT-TYPE
SYNTAX INTEGER
MAX-ACCESS read-write
STATUS current
DESCRIPTION
"Data value."
::= { dataArray17 227 }

dataValue17_228 OBJECT-TYPE
SYNTAX INTEGER
MAX-ACCESS read-write
STATUS current
DESCRIPTION
"Data value."
::= { dataArray17 228 }

dataValue17_229 OBJECT-TYPE
SYNTAX INTEGER
MAX-ACCESS read-write
STATUS current
DESCRIPTION
"Data value."
::= { dataArray17 229 }

dataValue17_230 OBJECT-TYPE
SYNTAX INTEGER
MAX-ACCESS read-write
STATUS current
DESCRIPTION
"Data value."
::= { dataArray17 230 }

dataValue17_231 OBJECT-TYPE
SYNTAX INTEGER
MAX-ACCESS read-write
STATUS current
DESCRIPTION
"Data value."
::= { dataArray17 231 }

dataValue17_232 OBJECT-TYPE
SYNTAX INTEGER
MAX-ACCESS read-write
STATUS current
DESCRIPTION
"Data value."
::= { dataArray17 232 }

dataValue17_233 OBJECT-TYPE
SYNTAX INTEGER
MAX-ACCESS read-write
STATUS current
DESCRIPTION
"Data value."
::= { dataArray17 233 }

dataValue17_234 OBJECT-TYPE
SYNTAX INTEGER
MAX-ACCESS read-write
STATUS current
DESCRIPTION
"Data value."
::= { dataArray17 234 }

dataValue17_235 OBJECT-TYPE
SYNTAX INTEGER
MAX-ACCESS read-write
STATUS current
DESCRIPTION
"Data value."
::= { dataArray17 235 }

dataValue17_236 OBJECT-TYPE
SYNTAX INTEGER
MAX-ACCESS read-write
STATUS current
DESCRIPTION
"Data value."
::= { dataArray17 236 }

dataValue17_237 OBJECT-TYPE
SYNTAX INTEGER
MAX-ACCESS read-write
STATUS current
DESCRIPTION
"Data value."
::= { dataArray17 237 }

dataValue17_238 OBJECT-TYPE
SYNTAX INTEGER
MAX-ACCESS read-write
STATUS current
DESCRIPTION
"Data value."
::= { dataArray17 238 }

dataValue17_239 OBJECT-TYPE
SYNTAX INTEGER
MAX-ACCESS read-write
STATUS current
DESCRIPTION
"Data value."
::= { dataArray17 239 }

dataValue17_240 OBJECT-TYPE
SYNTAX INTEGER
MAX-ACCESS read-write
STATUS current
DESCRIPTION
"Data value."
::= { dataArray17 240 }

dataValue17_241 OBJECT-TYPE
SYNTAX INTEGER
MAX-ACCESS read-write
STATUS current
DESCRIPTION
"Data value."
::= { dataArray17 241 }

dataValue17_242 OBJECT-TYPE
SYNTAX INTEGER
MAX-ACCESS read-write
STATUS current
DESCRIPTION
"Data value."
::= { dataArray17 242 }

dataValue17_243 OBJECT-TYPE
SYNTAX INTEGER
MAX-ACCESS read-write
STATUS current
DESCRIPTION
"Data value."
::= { dataArray17 243 }

dataValue17_244 OBJECT-TYPE
SYNTAX INTEGER
MAX-ACCESS read-write
STATUS current
DESCRIPTION
"Data value."
::= { dataArray17 244 }

dataValue17_245 OBJECT-TYPE
SYNTAX INTEGER
MAX-ACCESS read-write
STATUS current
DESCRIPTION
"Data value."
::= { dataArray17 245 }

dataValue17_246 OBJECT-TYPE
SYNTAX INTEGER
MAX-ACCESS read-write
STATUS current
DESCRIPTION
"Data value."
::= { dataArray17 246 }

dataValue17_247 OBJECT-TYPE
SYNTAX INTEGER
MAX-ACCESS read-write
STATUS current
DESCRIPTION
"Data value."
::= { dataArray17 247 }

dataValue17_248 OBJECT-TYPE
SYNTAX INTEGER
MAX-ACCESS read-write
STATUS current
DESCRIPTION
"Data value."
::= { dataArray17 248 }

dataValue17_249 OBJECT-TYPE
SYNTAX INTEGER
MAX-ACCESS read-write
STATUS current
DESCRIPTION
"Data value."
::= { dataArray17 249 }

dataValue17_250 OBJECT-TYPE
SYNTAX INTEGER
MAX-ACCESS read-write
STATUS current
DESCRIPTION
"Data value."
::= { dataArray17 250 }

dataValue17_251 OBJECT-TYPE
SYNTAX INTEGER
MAX-ACCESS read-write
STATUS current
DESCRIPTION
"Data value."
::= { dataArray17 251 }

dataValue17_252 OBJECT-TYPE
SYNTAX INTEGER
MAX-ACCESS read-write
STATUS current
DESCRIPTION
"Data value."
::= { dataArray17 252 }

dataValue17_253 OBJECT-TYPE
SYNTAX INTEGER
MAX-ACCESS read-write
STATUS current
DESCRIPTION
"Data value."
::= { dataArray17 253 }

dataValue17_254 OBJECT-TYPE
SYNTAX INTEGER
MAX-ACCESS read-write
STATUS current
DESCRIPTION
"Data value."
::= { dataArray17 254 }

dataValue17_255 OBJECT-TYPE
SYNTAX INTEGER
MAX-ACCESS read-write
STATUS current
DESCRIPTION
"Data value."
::= { dataArray17 255 }

dataValue17_256 OBJECT-TYPE
SYNTAX INTEGER
MAX-ACCESS read-write
STATUS current
DESCRIPTION
"Data value."
::= { dataArray17 256 }

dataValue17_257 OBJECT-TYPE
SYNTAX INTEGER
MAX-ACCESS read-write
STATUS current
DESCRIPTION
"Data value."
::= { dataArray17 257 }

dataValue17_258 OBJECT-TYPE
SYNTAX INTEGER
MAX-ACCESS read-write
STATUS current
DESCRIPTION
"Data value."
::= { dataArray17 258 }

dataValue17_259 OBJECT-TYPE
SYNTAX INTEGER
MAX-ACCESS read-write
STATUS current
DESCRIPTION
"Data value."
::= { dataArray17 259 }

dataValue17_260 OBJECT-TYPE
SYNTAX INTEGER
MAX-ACCESS read-write
STATUS current
DESCRIPTION
"Data value."
::= { dataArray17 260 }

dataValue17_261 OBJECT-TYPE
SYNTAX INTEGER
MAX-ACCESS read-write
STATUS current
DESCRIPTION
"Data value."
::= { dataArray17 261 }

dataValue17_262 OBJECT-TYPE
SYNTAX INTEGER
MAX-ACCESS read-write
STATUS current
DESCRIPTION
"Data value."
::= { dataArray17 262 }

dataValue17_263 OBJECT-TYPE
SYNTAX INTEGER
MAX-ACCESS read-write
STATUS current
DESCRIPTION
"Data value."
::= { dataArray17 263 }

dataValue17_264 OBJECT-TYPE
SYNTAX INTEGER
MAX-ACCESS read-write
STATUS current
DESCRIPTION
"Data value."
::= { dataArray17 264 }

dataValue17_265 OBJECT-TYPE
SYNTAX INTEGER
MAX-ACCESS read-write
STATUS current
DESCRIPTION
"Data value."
::= { dataArray17 265 }

dataValue17_266 OBJECT-TYPE
SYNTAX INTEGER
MAX-ACCESS read-write
STATUS current
DESCRIPTION
"Data value."
::= { dataArray17 266 }

dataValue17_267 OBJECT-TYPE
SYNTAX INTEGER
MAX-ACCESS read-write
STATUS current
DESCRIPTION
"Data value."
::= { dataArray17 267 }

dataValue17_268 OBJECT-TYPE
SYNTAX INTEGER
MAX-ACCESS read-write
STATUS current
DESCRIPTION
"Data value."
::= { dataArray17 268 }

dataValue17_269 OBJECT-TYPE
SYNTAX INTEGER
MAX-ACCESS read-write
STATUS current
DESCRIPTION
"Data value."
::= { dataArray17 269 }

dataValue17_270 OBJECT-TYPE
SYNTAX INTEGER
MAX-ACCESS read-write
STATUS current
DESCRIPTION
"Data value."
::= { dataArray17 270 }

dataValue17_271 OBJECT-TYPE
SYNTAX INTEGER
MAX-ACCESS read-write
STATUS current
DESCRIPTION
"Data value."
::= { dataArray17 271 }

dataValue17_272 OBJECT-TYPE
SYNTAX INTEGER
MAX-ACCESS read-write
STATUS current
DESCRIPTION
"Data value."
::= { dataArray17 272 }

dataValue17_273 OBJECT-TYPE
SYNTAX INTEGER
MAX-ACCESS read-write
STATUS current
DESCRIPTION
"Data value."
::= { dataArray17 273 }

dataValue17_274 OBJECT-TYPE
SYNTAX INTEGER
MAX-ACCESS read-write
STATUS current
DESCRIPTION
"Data value."
::= { dataArray17 274 }

dataValue17_275 OBJECT-TYPE
SYNTAX INTEGER
MAX-ACCESS read-write
STATUS current
DESCRIPTION
"Data value."
::= { dataArray17 275 }

dataValue17_276 OBJECT-TYPE
SYNTAX INTEGER
MAX-ACCESS read-write
STATUS current
DESCRIPTION
"Data value."
::= { dataArray17 276 }

dataValue17_277 OBJECT-TYPE
SYNTAX INTEGER
MAX-ACCESS read-write
STATUS current
DESCRIPTION
"Data value."
::= { dataArray17 277 }

dataValue17_278 OBJECT-TYPE
SYNTAX INTEGER
MAX-ACCESS read-write
STATUS current
DESCRIPTION
"Data value."
::= { dataArray17 278 }

dataValue17_279 OBJECT-TYPE
SYNTAX INTEGER
MAX-ACCESS read-write
STATUS current
DESCRIPTION
"Data value."
::= { dataArray17 279 }

dataValue17_280 OBJECT-TYPE
SYNTAX INTEGER
MAX-ACCESS read-write
STATUS current
DESCRIPTION
"Data value."
::= { dataArray17 280 }

dataValue17_281 OBJECT-TYPE
SYNTAX INTEGER
MAX-ACCESS read-write
STATUS current
DESCRIPTION
"Data value."
::= { dataArray17 281 }

dataValue17_282 OBJECT-TYPE
SYNTAX INTEGER
MAX-ACCESS read-write
STATUS current
DESCRIPTION
"Data value."
::= { dataArray17 282 }

dataValue17_283 OBJECT-TYPE
SYNTAX INTEGER
MAX-ACCESS read-write
STATUS current
DESCRIPTION
"Data value."
::= { dataArray17 283 }

dataValue17_284 OBJECT-TYPE
SYNTAX INTEGER
MAX-ACCESS read-write
STATUS current
DESCRIPTION
"Data value."
::= { dataArray17 284 }

dataValue17_285 OBJECT-TYPE
SYNTAX INTEGER
MAX-ACCESS read-write
STATUS current
DESCRIPTION
"Data value."
::= { dataArray17 285 }

dataValue17_286 OBJECT-TYPE
SYNTAX INTEGER
MAX-ACCESS read-write
STATUS current
DESCRIPTION
"Data value."
::= { dataArray17 286 }

dataValue17_287 OBJECT-TYPE
SYNTAX INTEGER
MAX-ACCESS read-write
STATUS current
DESCRIPTION
"Data value."
::= { dataArray17 287 }

dataValue17_288 OBJECT-TYPE
SYNTAX INTEGER
MAX-ACCESS read-write
STATUS current
DESCRIPTION
"Data value."
::= { dataArray17 288 }

dataValue17_289 OBJECT-TYPE
SYNTAX INTEGER
MAX-ACCESS read-write
STATUS current
DESCRIPTION
"Data value."
::= { dataArray17 289 }

dataValue17_290 OBJECT-TYPE
SYNTAX INTEGER
MAX-ACCESS read-write
STATUS current
DESCRIPTION
"Data value."
::= { dataArray17 290 }

dataValue17_291 OBJECT-TYPE
SYNTAX INTEGER
MAX-ACCESS read-write
STATUS current
DESCRIPTION
"Data value."
::= { dataArray17 291 }

dataValue17_292 OBJECT-TYPE
SYNTAX INTEGER
MAX-ACCESS read-write
STATUS current
DESCRIPTION
"Data value."
::= { dataArray17 292 }

dataValue17_293 OBJECT-TYPE
SYNTAX INTEGER
MAX-ACCESS read-write
STATUS current
DESCRIPTION
"Data value."
::= { dataArray17 293 }

dataValue17_294 OBJECT-TYPE
SYNTAX INTEGER
MAX-ACCESS read-write
STATUS current
DESCRIPTION
"Data value."
::= { dataArray17 294 }

dataValue17_295 OBJECT-TYPE
SYNTAX INTEGER
MAX-ACCESS read-write
STATUS current
DESCRIPTION
"Data value."
::= { dataArray17 295 }

dataValue17_296 OBJECT-TYPE
SYNTAX INTEGER
MAX-ACCESS read-write
STATUS current
DESCRIPTION
"Data value."
::= { dataArray17 296 }

dataValue17_297 OBJECT-TYPE
SYNTAX INTEGER
MAX-ACCESS read-write
STATUS current
DESCRIPTION
"Data value."
::= { dataArray17 297 }

dataValue17_298 OBJECT-TYPE
SYNTAX INTEGER
MAX-ACCESS read-write
STATUS current
DESCRIPTION
"Data value."
::= { dataArray17 298 }

dataValue17_299 OBJECT-TYPE
SYNTAX INTEGER
MAX-ACCESS read-write
STATUS current
DESCRIPTION
"Data value."
::= { dataArray17 299 }

dataValue17_300 OBJECT-TYPE
SYNTAX INTEGER
MAX-ACCESS read-write
STATUS current
DESCRIPTION
"Data value."
::= { dataArray17 300 }

dataValue17_301 OBJECT-TYPE
SYNTAX INTEGER
MAX-ACCESS read-write
STATUS current
DESCRIPTION
"Data value."
::= { dataArray17 301 }

dataValue17_302 OBJECT-TYPE
SYNTAX INTEGER
MAX-ACCESS read-write
STATUS current
DESCRIPTION
"Data value."
::= { dataArray17 302 }

dataValue17_303 OBJECT-TYPE
SYNTAX INTEGER
MAX-ACCESS read-write
STATUS current
DESCRIPTION
"Data value."
::= { dataArray17 303 }

dataValue17_304 OBJECT-TYPE
SYNTAX INTEGER
MAX-ACCESS read-write
STATUS current
DESCRIPTION
"Data value."
::= { dataArray17 304 }

dataValue17_305 OBJECT-TYPE
SYNTAX INTEGER
MAX-ACCESS read-write
STATUS current
DESCRIPTION
"Data value."
::= { dataArray17 305 }

dataValue17_306 OBJECT-TYPE
SYNTAX INTEGER
MAX-ACCESS read-write
STATUS current
DESCRIPTION
"Data value."
::= { dataArray17 306 }

dataValue17_307 OBJECT-TYPE
SYNTAX INTEGER
MAX-ACCESS read-write
STATUS current
DESCRIPTION
"Data value."
::= { dataArray17 307 }

dataValue17_308 OBJECT-TYPE
SYNTAX INTEGER
MAX-ACCESS read-write
STATUS current
DESCRIPTION
"Data value."
::= { dataArray17 308 }

dataValue17_309 OBJECT-TYPE
SYNTAX INTEGER
MAX-ACCESS read-write
STATUS current
DESCRIPTION
"Data value."
::= { dataArray17 309 }

dataValue17_310 OBJECT-TYPE
SYNTAX INTEGER
MAX-ACCESS read-write
STATUS current
DESCRIPTION
"Data value."
::= { dataArray17 310 }

dataValue17_311 OBJECT-TYPE
SYNTAX INTEGER
MAX-ACCESS read-write
STATUS current
DESCRIPTION
"Data value."
::= { dataArray17 311 }

dataValue17_312 OBJECT-TYPE
SYNTAX INTEGER
MAX-ACCESS read-write
STATUS current
DESCRIPTION
"Data value."
::= { dataArray17 312 }

dataValue17_313 OBJECT-TYPE
SYNTAX INTEGER
MAX-ACCESS read-write
STATUS current
DESCRIPTION
"Data value."
::= { dataArray17 313 }

dataValue17_314 OBJECT-TYPE
SYNTAX INTEGER
MAX-ACCESS read-write
STATUS current
DESCRIPTION
"Data value."
::= { dataArray17 314 }

dataValue17_315 OBJECT-TYPE
SYNTAX INTEGER
MAX-ACCESS read-write
STATUS current
DESCRIPTION
"Data value."
::= { dataArray17 315 }

dataValue17_316 OBJECT-TYPE
SYNTAX INTEGER
MAX-ACCESS read-write
STATUS current
DESCRIPTION
"Data value."
::= { dataArray17 316 }

dataValue17_317 OBJECT-TYPE
SYNTAX INTEGER
MAX-ACCESS read-write
STATUS current
DESCRIPTION
"Data value."
::= { dataArray17 317 }

dataValue17_318 OBJECT-TYPE
SYNTAX INTEGER
MAX-ACCESS read-write
STATUS current
DESCRIPTION
"Data value."
::= { dataArray17 318 }

dataValue17_319 OBJECT-TYPE
SYNTAX INTEGER
MAX-ACCESS read-write
STATUS current
DESCRIPTION
"Data value."
::= { dataArray17 319 }

dataValue17_320 OBJECT-TYPE
SYNTAX INTEGER
MAX-ACCESS read-write
STATUS current
DESCRIPTION
"Data value."
::= { dataArray17 320 }

dataValue17_321 OBJECT-TYPE
SYNTAX INTEGER
MAX-ACCESS read-write
STATUS current
DESCRIPTION
"Data value."
::= { dataArray17 321 }

dataValue17_322 OBJECT-TYPE
SYNTAX INTEGER
MAX-ACCESS read-write
STATUS current
DESCRIPTION
"Data value."
::= { dataArray17 322 }

dataValue17_323 OBJECT-TYPE
SYNTAX INTEGER
MAX-ACCESS read-write
STATUS current
DESCRIPTION
"Data value."
::= { dataArray17 323 }

dataValue17_324 OBJECT-TYPE
SYNTAX INTEGER
MAX-ACCESS read-write
STATUS current
DESCRIPTION
"Data value."
::= { dataArray17 324 }

dataValue17_325 OBJECT-TYPE
SYNTAX INTEGER
MAX-ACCESS read-write
STATUS current
DESCRIPTION
"Data value."
::= { dataArray17 325 }

dataValue17_326 OBJECT-TYPE
SYNTAX INTEGER
MAX-ACCESS read-write
STATUS current
DESCRIPTION
"Data value."
::= { dataArray17 326 }

dataValue17_327 OBJECT-TYPE
SYNTAX INTEGER
MAX-ACCESS read-write
STATUS current
DESCRIPTION
"Data value."
::= { dataArray17 327 }

dataValue17_328 OBJECT-TYPE
SYNTAX INTEGER
MAX-ACCESS read-write
STATUS current
DESCRIPTION
"Data value."
::= { dataArray17 328 }

dataValue17_329 OBJECT-TYPE
SYNTAX INTEGER
MAX-ACCESS read-write
STATUS current
DESCRIPTION
"Data value."
::= { dataArray17 329 }

dataValue17_330 OBJECT-TYPE
SYNTAX INTEGER
MAX-ACCESS read-write
STATUS current
DESCRIPTION
"Data value."
::= { dataArray17 330 }

dataValue17_331 OBJECT-TYPE
SYNTAX INTEGER
MAX-ACCESS read-write
STATUS current
DESCRIPTION
"Data value."
::= { dataArray17 331 }

dataValue17_332 OBJECT-TYPE
SYNTAX INTEGER
MAX-ACCESS read-write
STATUS current
DESCRIPTION
"Data value."
::= { dataArray17 332 }

dataValue17_333 OBJECT-TYPE
SYNTAX INTEGER
MAX-ACCESS read-write
STATUS current
DESCRIPTION
"Data value."
::= { dataArray17 333 }

dataValue17_334 OBJECT-TYPE
SYNTAX INTEGER
MAX-ACCESS read-write
STATUS current
DESCRIPTION
"Data value."
::= { dataArray17 334 }

dataValue17_335 OBJECT-TYPE
SYNTAX INTEGER
MAX-ACCESS read-write
STATUS current
DESCRIPTION
"Data value."
::= { dataArray17 335 }

dataValue17_336 OBJECT-TYPE
SYNTAX INTEGER
MAX-ACCESS read-write
STATUS current
DESCRIPTION
"Data value."
::= { dataArray17 336 }

dataValue17_337 OBJECT-TYPE
SYNTAX INTEGER
MAX-ACCESS read-write
STATUS current
DESCRIPTION
"Data value."
::= { dataArray17 337 }

dataValue17_338 OBJECT-TYPE
SYNTAX INTEGER
MAX-ACCESS read-write
STATUS current
DESCRIPTION
"Data value."
::= { dataArray17 338 }

dataValue17_339 OBJECT-TYPE
SYNTAX INTEGER
MAX-ACCESS read-write
STATUS current
DESCRIPTION
"Data value."
::= { dataArray17 339 }

dataValue17_340 OBJECT-TYPE
SYNTAX INTEGER
MAX-ACCESS read-write
STATUS current
DESCRIPTION
"Data value."
::= { dataArray17 340 }

dataValue17_341 OBJECT-TYPE
SYNTAX INTEGER
MAX-ACCESS read-write
STATUS current
DESCRIPTION
"Data value."
::= { dataArray17 341 }

dataValue17_342 OBJECT-TYPE
SYNTAX INTEGER
MAX-ACCESS read-write
STATUS current
DESCRIPTION
"Data value."
::= { dataArray17 342 }

dataValue17_343 OBJECT-TYPE
SYNTAX INTEGER
MAX-ACCESS read-write
STATUS current
DESCRIPTION
"Data value."
::= { dataArray17 343 }

dataValue17_344 OBJECT-TYPE
SYNTAX INTEGER
MAX-ACCESS read-write
STATUS current
DESCRIPTION
"Data value."
::= { dataArray17 344 }

dataValue17_345 OBJECT-TYPE
SYNTAX INTEGER
MAX-ACCESS read-write
STATUS current
DESCRIPTION
"Data value."
::= { dataArray17 345 }

dataValue17_346 OBJECT-TYPE
SYNTAX INTEGER
MAX-ACCESS read-write
STATUS current
DESCRIPTION
"Data value."
::= { dataArray17 346 }

dataValue17_347 OBJECT-TYPE
SYNTAX INTEGER
MAX-ACCESS read-write
STATUS current
DESCRIPTION
"Data value."
::= { dataArray17 347 }

dataValue17_348 OBJECT-TYPE
SYNTAX INTEGER
MAX-ACCESS read-write
STATUS current
DESCRIPTION
"Data value."
::= { dataArray17 348 }

dataValue17_349 OBJECT-TYPE
SYNTAX INTEGER
MAX-ACCESS read-write
STATUS current
DESCRIPTION
"Data value."
::= { dataArray17 349 }

dataValue17_350 OBJECT-TYPE
SYNTAX INTEGER
MAX-ACCESS read-write
STATUS current
DESCRIPTION
"Data value."
::= { dataArray17 350 }

dataValue17_351 OBJECT-TYPE
SYNTAX INTEGER
MAX-ACCESS read-write
STATUS current
DESCRIPTION
"Data value."
::= { dataArray17 351 }

dataValue17_352 OBJECT-TYPE
SYNTAX INTEGER
MAX-ACCESS read-write
STATUS current
DESCRIPTION
"Data value."
::= { dataArray17 352 }

dataValue17_353 OBJECT-TYPE
SYNTAX INTEGER
MAX-ACCESS read-write
STATUS current
DESCRIPTION
"Data value."
::= { dataArray17 353 }

dataValue17_354 OBJECT-TYPE
SYNTAX INTEGER
MAX-ACCESS read-write
STATUS current
DESCRIPTION
"Data value."
::= { dataArray17 354 }

dataValue17_355 OBJECT-TYPE
SYNTAX INTEGER
MAX-ACCESS read-write
STATUS current
DESCRIPTION
"Data value."
::= { dataArray17 355 }

dataValue17_356 OBJECT-TYPE
SYNTAX INTEGER
MAX-ACCESS read-write
STATUS current
DESCRIPTION
"Data value."
::= { dataArray17 356 }

dataValue17_357 OBJECT-TYPE
SYNTAX INTEGER
MAX-ACCESS read-write
STATUS current
DESCRIPTION
"Data value."
::= { dataArray17 357 }

dataValue17_358 OBJECT-TYPE
SYNTAX INTEGER
MAX-ACCESS read-write
STATUS current
DESCRIPTION
"Data value."
::= { dataArray17 358 }

dataValue17_359 OBJECT-TYPE
SYNTAX INTEGER
MAX-ACCESS read-write
STATUS current
DESCRIPTION
"Data value."
::= { dataArray17 359 }

dataValue17_360 OBJECT-TYPE
SYNTAX INTEGER
MAX-ACCESS read-write
STATUS current
DESCRIPTION
"Data value."
::= { dataArray17 360 }

dataValue17_361 OBJECT-TYPE
SYNTAX INTEGER
MAX-ACCESS read-write
STATUS current
DESCRIPTION
"Data value."
::= { dataArray17 361 }

dataValue17_362 OBJECT-TYPE
SYNTAX INTEGER
MAX-ACCESS read-write
STATUS current
DESCRIPTION
"Data value."
::= { dataArray17 362 }

dataValue17_363 OBJECT-TYPE
SYNTAX INTEGER
MAX-ACCESS read-write
STATUS current
DESCRIPTION
"Data value."
::= { dataArray17 363 }

dataValue17_364 OBJECT-TYPE
SYNTAX INTEGER
MAX-ACCESS read-write
STATUS current
DESCRIPTION
"Data value."
::= { dataArray17 364 }

dataValue17_365 OBJECT-TYPE
SYNTAX INTEGER
MAX-ACCESS read-write
STATUS current
DESCRIPTION
"Data value."
::= { dataArray17 365 }

dataValue17_366 OBJECT-TYPE
SYNTAX INTEGER
MAX-ACCESS read-write
STATUS current
DESCRIPTION
"Data value."
::= { dataArray17 366 }

dataValue17_367 OBJECT-TYPE
SYNTAX INTEGER
MAX-ACCESS read-write
STATUS current
DESCRIPTION
"Data value."
::= { dataArray17 367 }

dataValue17_368 OBJECT-TYPE
SYNTAX INTEGER
MAX-ACCESS read-write
STATUS current
DESCRIPTION
"Data value."
::= { dataArray17 368 }

dataValue17_369 OBJECT-TYPE
SYNTAX INTEGER
MAX-ACCESS read-write
STATUS current
DESCRIPTION
"Data value."
::= { dataArray17 369 }

dataValue17_370 OBJECT-TYPE
SYNTAX INTEGER
MAX-ACCESS read-write
STATUS current
DESCRIPTION
"Data value."
::= { dataArray17 370 }

dataValue17_371 OBJECT-TYPE
SYNTAX INTEGER
MAX-ACCESS read-write
STATUS current
DESCRIPTION
"Data value."
::= { dataArray17 371 }

dataValue17_372 OBJECT-TYPE
SYNTAX INTEGER
MAX-ACCESS read-write
STATUS current
DESCRIPTION
"Data value."
::= { dataArray17 372 }

dataValue17_373 OBJECT-TYPE
SYNTAX INTEGER
MAX-ACCESS read-write
STATUS current
DESCRIPTION
"Data value."
::= { dataArray17 373 }

dataValue17_374 OBJECT-TYPE
SYNTAX INTEGER
MAX-ACCESS read-write
STATUS current
DESCRIPTION
"Data value."
::= { dataArray17 374 }

dataValue17_375 OBJECT-TYPE
SYNTAX INTEGER
MAX-ACCESS read-write
STATUS current
DESCRIPTION
"Data value."
::= { dataArray17 375 }

dataValue17_376 OBJECT-TYPE
SYNTAX INTEGER
MAX-ACCESS read-write
STATUS current
DESCRIPTION
"Data value."
::= { dataArray17 376 }

dataValue17_377 OBJECT-TYPE
SYNTAX INTEGER
MAX-ACCESS read-write
STATUS current
DESCRIPTION
"Data value."
::= { dataArray17 377 }

dataValue17_378 OBJECT-TYPE
SYNTAX INTEGER
MAX-ACCESS read-write
STATUS current
DESCRIPTION
"Data value."
::= { dataArray17 378 }

dataValue17_379 OBJECT-TYPE
SYNTAX INTEGER
MAX-ACCESS read-write
STATUS current
DESCRIPTION
"Data value."
::= { dataArray17 379 }

dataValue17_380 OBJECT-TYPE
SYNTAX INTEGER
MAX-ACCESS read-write
STATUS current
DESCRIPTION
"Data value."
::= { dataArray17 380 }

dataValue17_381 OBJECT-TYPE
SYNTAX INTEGER
MAX-ACCESS read-write
STATUS current
DESCRIPTION
"Data value."
::= { dataArray17 381 }

dataValue17_382 OBJECT-TYPE
SYNTAX INTEGER
MAX-ACCESS read-write
STATUS current
DESCRIPTION
"Data value."
::= { dataArray17 382 }

dataValue17_383 OBJECT-TYPE
SYNTAX INTEGER
MAX-ACCESS read-write
STATUS current
DESCRIPTION
"Data value."
::= { dataArray17 383 }

dataValue17_384 OBJECT-TYPE
SYNTAX INTEGER
MAX-ACCESS read-write
STATUS current
DESCRIPTION
"Data value."
::= { dataArray17 384 }

dataValue17_385 OBJECT-TYPE
SYNTAX INTEGER
MAX-ACCESS read-write
STATUS current
DESCRIPTION
"Data value."
::= { dataArray17 385 }

dataValue17_386 OBJECT-TYPE
SYNTAX INTEGER
MAX-ACCESS read-write
STATUS current
DESCRIPTION
"Data value."
::= { dataArray17 386 }

dataValue17_387 OBJECT-TYPE
SYNTAX INTEGER
MAX-ACCESS read-write
STATUS current
DESCRIPTION
"Data value."
::= { dataArray17 387 }

dataValue17_388 OBJECT-TYPE
SYNTAX INTEGER
MAX-ACCESS read-write
STATUS current
DESCRIPTION
"Data value."
::= { dataArray17 388 }

dataValue17_389 OBJECT-TYPE
SYNTAX INTEGER
MAX-ACCESS read-write
STATUS current
DESCRIPTION
"Data value."
::= { dataArray17 389 }

dataValue17_390 OBJECT-TYPE
SYNTAX INTEGER
MAX-ACCESS read-write
STATUS current
DESCRIPTION
"Data value."
::= { dataArray17 390 }

dataValue17_391 OBJECT-TYPE
SYNTAX INTEGER
MAX-ACCESS read-write
STATUS current
DESCRIPTION
"Data value."
::= { dataArray17 391 }

dataValue17_392 OBJECT-TYPE
SYNTAX INTEGER
MAX-ACCESS read-write
STATUS current
DESCRIPTION
"Data value."
::= { dataArray17 392 }

dataValue17_393 OBJECT-TYPE
SYNTAX INTEGER
MAX-ACCESS read-write
STATUS current
DESCRIPTION
"Data value."
::= { dataArray17 393 }

dataValue17_394 OBJECT-TYPE
SYNTAX INTEGER
MAX-ACCESS read-write
STATUS current
DESCRIPTION
"Data value."
::= { dataArray17 394 }

dataValue17_395 OBJECT-TYPE
SYNTAX INTEGER
MAX-ACCESS read-write
STATUS current
DESCRIPTION
"Data value."
::= { dataArray17 395 }

dataValue17_396 OBJECT-TYPE
SYNTAX INTEGER
MAX-ACCESS read-write
STATUS current
DESCRIPTION
"Data value."
::= { dataArray17 396 }

dataValue17_397 OBJECT-TYPE
SYNTAX INTEGER
MAX-ACCESS read-write
STATUS current
DESCRIPTION
"Data value."
::= { dataArray17 397 }

dataValue17_398 OBJECT-TYPE
SYNTAX INTEGER
MAX-ACCESS read-write
STATUS current
DESCRIPTION
"Data value."
::= { dataArray17 398 }

dataValue17_399 OBJECT-TYPE
SYNTAX INTEGER
MAX-ACCESS read-write
STATUS current
DESCRIPTION
"Data value."
::= { dataArray17 399 }

dataArray18 OBJECT IDENTIFIER ::= { cc08255400_v1_00a 18 }

dataValue18_0 OBJECT-TYPE
SYNTAX INTEGER
MAX-ACCESS read-write
STATUS current
DESCRIPTION
"Data value."
::= { dataArray18 0 }

dataValue18_1 OBJECT-TYPE
SYNTAX INTEGER
MAX-ACCESS read-write
STATUS current
DESCRIPTION
"Data value."
::= { dataArray18 1 }

dataValue18_2 OBJECT-TYPE
SYNTAX INTEGER
MAX-ACCESS read-write
STATUS current
DESCRIPTION
"Data value."
::= { dataArray18 2 }

dataValue18_3 OBJECT-TYPE
SYNTAX INTEGER
MAX-ACCESS read-write
STATUS current
DESCRIPTION
"Data value."
::= { dataArray18 3 }

dataValue18_4 OBJECT-TYPE
SYNTAX INTEGER
MAX-ACCESS read-write
STATUS current
DESCRIPTION
"Data value."
::= { dataArray18 4 }

dataValue18_5 OBJECT-TYPE
SYNTAX INTEGER
MAX-ACCESS read-write
STATUS current
DESCRIPTION
"Data value."
::= { dataArray18 5 }

dataValue18_6 OBJECT-TYPE
SYNTAX INTEGER
MAX-ACCESS read-write
STATUS current
DESCRIPTION
"Data value."
::= { dataArray18 6 }

dataValue18_7 OBJECT-TYPE
SYNTAX INTEGER
MAX-ACCESS read-write
STATUS current
DESCRIPTION
"Data value."
::= { dataArray18 7 }

dataValue18_8 OBJECT-TYPE
SYNTAX INTEGER
MAX-ACCESS read-write
STATUS current
DESCRIPTION
"Data value."
::= { dataArray18 8 }

dataValue18_9 OBJECT-TYPE
SYNTAX INTEGER
MAX-ACCESS read-write
STATUS current
DESCRIPTION
"Data value."
::= { dataArray18 9 }

dataValue18_10 OBJECT-TYPE
SYNTAX INTEGER
MAX-ACCESS read-write
STATUS current
DESCRIPTION
"Data value."
::= { dataArray18 10 }

dataValue18_11 OBJECT-TYPE
SYNTAX INTEGER
MAX-ACCESS read-write
STATUS current
DESCRIPTION
"Data value."
::= { dataArray18 11 }

dataValue18_12 OBJECT-TYPE
SYNTAX INTEGER
MAX-ACCESS read-write
STATUS current
DESCRIPTION
"Data value."
::= { dataArray18 12 }

dataValue18_13 OBJECT-TYPE
SYNTAX INTEGER
MAX-ACCESS read-write
STATUS current
DESCRIPTION
"Data value."
::= { dataArray18 13 }

dataValue18_14 OBJECT-TYPE
SYNTAX INTEGER
MAX-ACCESS read-write
STATUS current
DESCRIPTION
"Data value."
::= { dataArray18 14 }

dataValue18_15 OBJECT-TYPE
SYNTAX INTEGER
MAX-ACCESS read-write
STATUS current
DESCRIPTION
"Data value."
::= { dataArray18 15 }

dataValue18_16 OBJECT-TYPE
SYNTAX INTEGER
MAX-ACCESS read-write
STATUS current
DESCRIPTION
"Data value."
::= { dataArray18 16 }

dataValue18_17 OBJECT-TYPE
SYNTAX INTEGER
MAX-ACCESS read-write
STATUS current
DESCRIPTION
"Data value."
::= { dataArray18 17 }

dataValue18_18 OBJECT-TYPE
SYNTAX INTEGER
MAX-ACCESS read-write
STATUS current
DESCRIPTION
"Data value."
::= { dataArray18 18 }

dataValue18_19 OBJECT-TYPE
SYNTAX INTEGER
MAX-ACCESS read-write
STATUS current
DESCRIPTION
"Data value."
::= { dataArray18 19 }

dataValue18_20 OBJECT-TYPE
SYNTAX INTEGER
MAX-ACCESS read-write
STATUS current
DESCRIPTION
"Data value."
::= { dataArray18 20 }

dataValue18_21 OBJECT-TYPE
SYNTAX INTEGER
MAX-ACCESS read-write
STATUS current
DESCRIPTION
"Data value."
::= { dataArray18 21 }

dataValue18_22 OBJECT-TYPE
SYNTAX INTEGER
MAX-ACCESS read-write
STATUS current
DESCRIPTION
"Data value."
::= { dataArray18 22 }

dataValue18_23 OBJECT-TYPE
SYNTAX INTEGER
MAX-ACCESS read-write
STATUS current
DESCRIPTION
"Data value."
::= { dataArray18 23 }

dataValue18_24 OBJECT-TYPE
SYNTAX INTEGER
MAX-ACCESS read-write
STATUS current
DESCRIPTION
"Data value."
::= { dataArray18 24 }

dataValue18_25 OBJECT-TYPE
SYNTAX INTEGER
MAX-ACCESS read-write
STATUS current
DESCRIPTION
"Data value."
::= { dataArray18 25 }

dataValue18_26 OBJECT-TYPE
SYNTAX INTEGER
MAX-ACCESS read-write
STATUS current
DESCRIPTION
"Data value."
::= { dataArray18 26 }

dataValue18_27 OBJECT-TYPE
SYNTAX INTEGER
MAX-ACCESS read-write
STATUS current
DESCRIPTION
"Data value."
::= { dataArray18 27 }

dataValue18_28 OBJECT-TYPE
SYNTAX INTEGER
MAX-ACCESS read-write
STATUS current
DESCRIPTION
"Data value."
::= { dataArray18 28 }

dataValue18_29 OBJECT-TYPE
SYNTAX INTEGER
MAX-ACCESS read-write
STATUS current
DESCRIPTION
"Data value."
::= { dataArray18 29 }

dataValue18_30 OBJECT-TYPE
SYNTAX INTEGER
MAX-ACCESS read-write
STATUS current
DESCRIPTION
"Data value."
::= { dataArray18 30 }

dataValue18_31 OBJECT-TYPE
SYNTAX INTEGER
MAX-ACCESS read-write
STATUS current
DESCRIPTION
"Data value."
::= { dataArray18 31 }

dataValue18_32 OBJECT-TYPE
SYNTAX INTEGER
MAX-ACCESS read-write
STATUS current
DESCRIPTION
"Data value."
::= { dataArray18 32 }

dataValue18_33 OBJECT-TYPE
SYNTAX INTEGER
MAX-ACCESS read-write
STATUS current
DESCRIPTION
"Data value."
::= { dataArray18 33 }

dataValue18_34 OBJECT-TYPE
SYNTAX INTEGER
MAX-ACCESS read-write
STATUS current
DESCRIPTION
"Data value."
::= { dataArray18 34 }

dataValue18_35 OBJECT-TYPE
SYNTAX INTEGER
MAX-ACCESS read-write
STATUS current
DESCRIPTION
"Data value."
::= { dataArray18 35 }

dataValue18_36 OBJECT-TYPE
SYNTAX INTEGER
MAX-ACCESS read-write
STATUS current
DESCRIPTION
"Data value."
::= { dataArray18 36 }

dataValue18_37 OBJECT-TYPE
SYNTAX INTEGER
MAX-ACCESS read-write
STATUS current
DESCRIPTION
"Data value."
::= { dataArray18 37 }

dataValue18_38 OBJECT-TYPE
SYNTAX INTEGER
MAX-ACCESS read-write
STATUS current
DESCRIPTION
"Data value."
::= { dataArray18 38 }

dataValue18_39 OBJECT-TYPE
SYNTAX INTEGER
MAX-ACCESS read-write
STATUS current
DESCRIPTION
"Data value."
::= { dataArray18 39 }

dataValue18_40 OBJECT-TYPE
SYNTAX INTEGER
MAX-ACCESS read-write
STATUS current
DESCRIPTION
"Data value."
::= { dataArray18 40 }

dataValue18_41 OBJECT-TYPE
SYNTAX INTEGER
MAX-ACCESS read-write
STATUS current
DESCRIPTION
"Data value."
::= { dataArray18 41 }

dataValue18_42 OBJECT-TYPE
SYNTAX INTEGER
MAX-ACCESS read-write
STATUS current
DESCRIPTION
"Data value."
::= { dataArray18 42 }

dataValue18_43 OBJECT-TYPE
SYNTAX INTEGER
MAX-ACCESS read-write
STATUS current
DESCRIPTION
"Data value."
::= { dataArray18 43 }

dataValue18_44 OBJECT-TYPE
SYNTAX INTEGER
MAX-ACCESS read-write
STATUS current
DESCRIPTION
"Data value."
::= { dataArray18 44 }

dataValue18_45 OBJECT-TYPE
SYNTAX INTEGER
MAX-ACCESS read-write
STATUS current
DESCRIPTION
"Data value."
::= { dataArray18 45 }

dataValue18_46 OBJECT-TYPE
SYNTAX INTEGER
MAX-ACCESS read-write
STATUS current
DESCRIPTION
"Data value."
::= { dataArray18 46 }

dataValue18_47 OBJECT-TYPE
SYNTAX INTEGER
MAX-ACCESS read-write
STATUS current
DESCRIPTION
"Data value."
::= { dataArray18 47 }

dataValue18_48 OBJECT-TYPE
SYNTAX INTEGER
MAX-ACCESS read-write
STATUS current
DESCRIPTION
"Data value."
::= { dataArray18 48 }

dataValue18_49 OBJECT-TYPE
SYNTAX INTEGER
MAX-ACCESS read-write
STATUS current
DESCRIPTION
"Data value."
::= { dataArray18 49 }

dataValue18_50 OBJECT-TYPE
SYNTAX INTEGER
MAX-ACCESS read-write
STATUS current
DESCRIPTION
"Data value."
::= { dataArray18 50 }

dataValue18_51 OBJECT-TYPE
SYNTAX INTEGER
MAX-ACCESS read-write
STATUS current
DESCRIPTION
"Data value."
::= { dataArray18 51 }

dataValue18_52 OBJECT-TYPE
SYNTAX INTEGER
MAX-ACCESS read-write
STATUS current
DESCRIPTION
"Data value."
::= { dataArray18 52 }

dataValue18_53 OBJECT-TYPE
SYNTAX INTEGER
MAX-ACCESS read-write
STATUS current
DESCRIPTION
"Data value."
::= { dataArray18 53 }

dataValue18_54 OBJECT-TYPE
SYNTAX INTEGER
MAX-ACCESS read-write
STATUS current
DESCRIPTION
"Data value."
::= { dataArray18 54 }

dataValue18_55 OBJECT-TYPE
SYNTAX INTEGER
MAX-ACCESS read-write
STATUS current
DESCRIPTION
"Data value."
::= { dataArray18 55 }

dataValue18_56 OBJECT-TYPE
SYNTAX INTEGER
MAX-ACCESS read-write
STATUS current
DESCRIPTION
"Data value."
::= { dataArray18 56 }

dataValue18_57 OBJECT-TYPE
SYNTAX INTEGER
MAX-ACCESS read-write
STATUS current
DESCRIPTION
"Data value."
::= { dataArray18 57 }

dataValue18_58 OBJECT-TYPE
SYNTAX INTEGER
MAX-ACCESS read-write
STATUS current
DESCRIPTION
"Data value."
::= { dataArray18 58 }

dataValue18_59 OBJECT-TYPE
SYNTAX INTEGER
MAX-ACCESS read-write
STATUS current
DESCRIPTION
"Data value."
::= { dataArray18 59 }

dataValue18_60 OBJECT-TYPE
SYNTAX INTEGER
MAX-ACCESS read-write
STATUS current
DESCRIPTION
"Data value."
::= { dataArray18 60 }

dataValue18_61 OBJECT-TYPE
SYNTAX INTEGER
MAX-ACCESS read-write
STATUS current
DESCRIPTION
"Data value."
::= { dataArray18 61 }

dataValue18_62 OBJECT-TYPE
SYNTAX INTEGER
MAX-ACCESS read-write
STATUS current
DESCRIPTION
"Data value."
::= { dataArray18 62 }

dataValue18_63 OBJECT-TYPE
SYNTAX INTEGER
MAX-ACCESS read-write
STATUS current
DESCRIPTION
"Data value."
::= { dataArray18 63 }

dataValue18_64 OBJECT-TYPE
SYNTAX INTEGER
MAX-ACCESS read-write
STATUS current
DESCRIPTION
"Data value."
::= { dataArray18 64 }

dataValue18_65 OBJECT-TYPE
SYNTAX INTEGER
MAX-ACCESS read-write
STATUS current
DESCRIPTION
"Data value."
::= { dataArray18 65 }

dataValue18_66 OBJECT-TYPE
SYNTAX INTEGER
MAX-ACCESS read-write
STATUS current
DESCRIPTION
"Data value."
::= { dataArray18 66 }

dataValue18_67 OBJECT-TYPE
SYNTAX INTEGER
MAX-ACCESS read-write
STATUS current
DESCRIPTION
"Data value."
::= { dataArray18 67 }

dataValue18_68 OBJECT-TYPE
SYNTAX INTEGER
MAX-ACCESS read-write
STATUS current
DESCRIPTION
"Data value."
::= { dataArray18 68 }

dataValue18_69 OBJECT-TYPE
SYNTAX INTEGER
MAX-ACCESS read-write
STATUS current
DESCRIPTION
"Data value."
::= { dataArray18 69 }

dataValue18_70 OBJECT-TYPE
SYNTAX INTEGER
MAX-ACCESS read-write
STATUS current
DESCRIPTION
"Data value."
::= { dataArray18 70 }

dataValue18_71 OBJECT-TYPE
SYNTAX INTEGER
MAX-ACCESS read-write
STATUS current
DESCRIPTION
"Data value."
::= { dataArray18 71 }

dataValue18_72 OBJECT-TYPE
SYNTAX INTEGER
MAX-ACCESS read-write
STATUS current
DESCRIPTION
"Data value."
::= { dataArray18 72 }

dataValue18_73 OBJECT-TYPE
SYNTAX INTEGER
MAX-ACCESS read-write
STATUS current
DESCRIPTION
"Data value."
::= { dataArray18 73 }

dataValue18_74 OBJECT-TYPE
SYNTAX INTEGER
MAX-ACCESS read-write
STATUS current
DESCRIPTION
"Data value."
::= { dataArray18 74 }

dataValue18_75 OBJECT-TYPE
SYNTAX INTEGER
MAX-ACCESS read-write
STATUS current
DESCRIPTION
"Data value."
::= { dataArray18 75 }

dataValue18_76 OBJECT-TYPE
SYNTAX INTEGER
MAX-ACCESS read-write
STATUS current
DESCRIPTION
"Data value."
::= { dataArray18 76 }

dataValue18_77 OBJECT-TYPE
SYNTAX INTEGER
MAX-ACCESS read-write
STATUS current
DESCRIPTION
"Data value."
::= { dataArray18 77 }

dataValue18_78 OBJECT-TYPE
SYNTAX INTEGER
MAX-ACCESS read-write
STATUS current
DESCRIPTION
"Data value."
::= { dataArray18 78 }

dataValue18_79 OBJECT-TYPE
SYNTAX INTEGER
MAX-ACCESS read-write
STATUS current
DESCRIPTION
"Data value."
::= { dataArray18 79 }

dataValue18_80 OBJECT-TYPE
SYNTAX INTEGER
MAX-ACCESS read-write
STATUS current
DESCRIPTION
"Data value."
::= { dataArray18 80 }

dataValue18_81 OBJECT-TYPE
SYNTAX INTEGER
MAX-ACCESS read-write
STATUS current
DESCRIPTION
"Data value."
::= { dataArray18 81 }

dataValue18_82 OBJECT-TYPE
SYNTAX INTEGER
MAX-ACCESS read-write
STATUS current
DESCRIPTION
"Data value."
::= { dataArray18 82 }

dataValue18_83 OBJECT-TYPE
SYNTAX INTEGER
MAX-ACCESS read-write
STATUS current
DESCRIPTION
"Data value."
::= { dataArray18 83 }

dataValue18_84 OBJECT-TYPE
SYNTAX INTEGER
MAX-ACCESS read-write
STATUS current
DESCRIPTION
"Data value."
::= { dataArray18 84 }

dataValue18_85 OBJECT-TYPE
SYNTAX INTEGER
MAX-ACCESS read-write
STATUS current
DESCRIPTION
"Data value."
::= { dataArray18 85 }

dataValue18_86 OBJECT-TYPE
SYNTAX INTEGER
MAX-ACCESS read-write
STATUS current
DESCRIPTION
"Data value."
::= { dataArray18 86 }

dataValue18_87 OBJECT-TYPE
SYNTAX INTEGER
MAX-ACCESS read-write
STATUS current
DESCRIPTION
"Data value."
::= { dataArray18 87 }

dataValue18_88 OBJECT-TYPE
SYNTAX INTEGER
MAX-ACCESS read-write
STATUS current
DESCRIPTION
"Data value."
::= { dataArray18 88 }

dataValue18_89 OBJECT-TYPE
SYNTAX INTEGER
MAX-ACCESS read-write
STATUS current
DESCRIPTION
"Data value."
::= { dataArray18 89 }

dataValue18_90 OBJECT-TYPE
SYNTAX INTEGER
MAX-ACCESS read-write
STATUS current
DESCRIPTION
"Data value."
::= { dataArray18 90 }

dataValue18_91 OBJECT-TYPE
SYNTAX INTEGER
MAX-ACCESS read-write
STATUS current
DESCRIPTION
"Data value."
::= { dataArray18 91 }

dataValue18_92 OBJECT-TYPE
SYNTAX INTEGER
MAX-ACCESS read-write
STATUS current
DESCRIPTION
"Data value."
::= { dataArray18 92 }

dataValue18_93 OBJECT-TYPE
SYNTAX INTEGER
MAX-ACCESS read-write
STATUS current
DESCRIPTION
"Data value."
::= { dataArray18 93 }

dataValue18_94 OBJECT-TYPE
SYNTAX INTEGER
MAX-ACCESS read-write
STATUS current
DESCRIPTION
"Data value."
::= { dataArray18 94 }

dataValue18_95 OBJECT-TYPE
SYNTAX INTEGER
MAX-ACCESS read-write
STATUS current
DESCRIPTION
"Data value."
::= { dataArray18 95 }

dataValue18_96 OBJECT-TYPE
SYNTAX INTEGER
MAX-ACCESS read-write
STATUS current
DESCRIPTION
"Data value."
::= { dataArray18 96 }

dataValue18_97 OBJECT-TYPE
SYNTAX INTEGER
MAX-ACCESS read-write
STATUS current
DESCRIPTION
"Data value."
::= { dataArray18 97 }

dataValue18_98 OBJECT-TYPE
SYNTAX INTEGER
MAX-ACCESS read-write
STATUS current
DESCRIPTION
"Data value."
::= { dataArray18 98 }

dataValue18_99 OBJECT-TYPE
SYNTAX INTEGER
MAX-ACCESS read-write
STATUS current
DESCRIPTION
"Data value."
::= { dataArray18 99 }

dataValue18_100 OBJECT-TYPE
SYNTAX INTEGER
MAX-ACCESS read-write
STATUS current
DESCRIPTION
"Data value."
::= { dataArray18 100 }

dataValue18_101 OBJECT-TYPE
SYNTAX INTEGER
MAX-ACCESS read-write
STATUS current
DESCRIPTION
"Data value."
::= { dataArray18 101 }

dataValue18_102 OBJECT-TYPE
SYNTAX INTEGER
MAX-ACCESS read-write
STATUS current
DESCRIPTION
"Data value."
::= { dataArray18 102 }

dataValue18_103 OBJECT-TYPE
SYNTAX INTEGER
MAX-ACCESS read-write
STATUS current
DESCRIPTION
"Data value."
::= { dataArray18 103 }

dataValue18_104 OBJECT-TYPE
SYNTAX INTEGER
MAX-ACCESS read-write
STATUS current
DESCRIPTION
"Data value."
::= { dataArray18 104 }

dataValue18_105 OBJECT-TYPE
SYNTAX INTEGER
MAX-ACCESS read-write
STATUS current
DESCRIPTION
"Data value."
::= { dataArray18 105 }

dataValue18_106 OBJECT-TYPE
SYNTAX INTEGER
MAX-ACCESS read-write
STATUS current
DESCRIPTION
"Data value."
::= { dataArray18 106 }

dataValue18_107 OBJECT-TYPE
SYNTAX INTEGER
MAX-ACCESS read-write
STATUS current
DESCRIPTION
"Data value."
::= { dataArray18 107 }

dataValue18_108 OBJECT-TYPE
SYNTAX INTEGER
MAX-ACCESS read-write
STATUS current
DESCRIPTION
"Data value."
::= { dataArray18 108 }

dataValue18_109 OBJECT-TYPE
SYNTAX INTEGER
MAX-ACCESS read-write
STATUS current
DESCRIPTION
"Data value."
::= { dataArray18 109 }

dataValue18_110 OBJECT-TYPE
SYNTAX INTEGER
MAX-ACCESS read-write
STATUS current
DESCRIPTION
"Data value."
::= { dataArray18 110 }

dataValue18_111 OBJECT-TYPE
SYNTAX INTEGER
MAX-ACCESS read-write
STATUS current
DESCRIPTION
"Data value."
::= { dataArray18 111 }

dataValue18_112 OBJECT-TYPE
SYNTAX INTEGER
MAX-ACCESS read-write
STATUS current
DESCRIPTION
"Data value."
::= { dataArray18 112 }

dataValue18_113 OBJECT-TYPE
SYNTAX INTEGER
MAX-ACCESS read-write
STATUS current
DESCRIPTION
"Data value."
::= { dataArray18 113 }

dataValue18_114 OBJECT-TYPE
SYNTAX INTEGER
MAX-ACCESS read-write
STATUS current
DESCRIPTION
"Data value."
::= { dataArray18 114 }

dataValue18_115 OBJECT-TYPE
SYNTAX INTEGER
MAX-ACCESS read-write
STATUS current
DESCRIPTION
"Data value."
::= { dataArray18 115 }

dataValue18_116 OBJECT-TYPE
SYNTAX INTEGER
MAX-ACCESS read-write
STATUS current
DESCRIPTION
"Data value."
::= { dataArray18 116 }

dataValue18_117 OBJECT-TYPE
SYNTAX INTEGER
MAX-ACCESS read-write
STATUS current
DESCRIPTION
"Data value."
::= { dataArray18 117 }

dataValue18_118 OBJECT-TYPE
SYNTAX INTEGER
MAX-ACCESS read-write
STATUS current
DESCRIPTION
"Data value."
::= { dataArray18 118 }

dataValue18_119 OBJECT-TYPE
SYNTAX INTEGER
MAX-ACCESS read-write
STATUS current
DESCRIPTION
"Data value."
::= { dataArray18 119 }

dataValue18_120 OBJECT-TYPE
SYNTAX INTEGER
MAX-ACCESS read-write
STATUS current
DESCRIPTION
"Data value."
::= { dataArray18 120 }

dataValue18_121 OBJECT-TYPE
SYNTAX INTEGER
MAX-ACCESS read-write
STATUS current
DESCRIPTION
"Data value."
::= { dataArray18 121 }

dataValue18_122 OBJECT-TYPE
SYNTAX INTEGER
MAX-ACCESS read-write
STATUS current
DESCRIPTION
"Data value."
::= { dataArray18 122 }

dataValue18_123 OBJECT-TYPE
SYNTAX INTEGER
MAX-ACCESS read-write
STATUS current
DESCRIPTION
"Data value."
::= { dataArray18 123 }

dataValue18_124 OBJECT-TYPE
SYNTAX INTEGER
MAX-ACCESS read-write
STATUS current
DESCRIPTION
"Data value."
::= { dataArray18 124 }

dataValue18_125 OBJECT-TYPE
SYNTAX INTEGER
MAX-ACCESS read-write
STATUS current
DESCRIPTION
"Data value."
::= { dataArray18 125 }

dataValue18_126 OBJECT-TYPE
SYNTAX INTEGER
MAX-ACCESS read-write
STATUS current
DESCRIPTION
"Data value."
::= { dataArray18 126 }

dataValue18_127 OBJECT-TYPE
SYNTAX INTEGER
MAX-ACCESS read-write
STATUS current
DESCRIPTION
"Data value."
::= { dataArray18 127 }

dataValue18_128 OBJECT-TYPE
SYNTAX INTEGER
MAX-ACCESS read-write
STATUS current
DESCRIPTION
"Data value."
::= { dataArray18 128 }

dataValue18_129 OBJECT-TYPE
SYNTAX INTEGER
MAX-ACCESS read-write
STATUS current
DESCRIPTION
"Data value."
::= { dataArray18 129 }

dataValue18_130 OBJECT-TYPE
SYNTAX INTEGER
MAX-ACCESS read-write
STATUS current
DESCRIPTION
"Data value."
::= { dataArray18 130 }

dataValue18_131 OBJECT-TYPE
SYNTAX INTEGER
MAX-ACCESS read-write
STATUS current
DESCRIPTION
"Data value."
::= { dataArray18 131 }

dataValue18_132 OBJECT-TYPE
SYNTAX INTEGER
MAX-ACCESS read-write
STATUS current
DESCRIPTION
"Data value."
::= { dataArray18 132 }

dataValue18_133 OBJECT-TYPE
SYNTAX INTEGER
MAX-ACCESS read-write
STATUS current
DESCRIPTION
"Data value."
::= { dataArray18 133 }

dataValue18_134 OBJECT-TYPE
SYNTAX INTEGER
MAX-ACCESS read-write
STATUS current
DESCRIPTION
"Data value."
::= { dataArray18 134 }

dataValue18_135 OBJECT-TYPE
SYNTAX INTEGER
MAX-ACCESS read-write
STATUS current
DESCRIPTION
"Data value."
::= { dataArray18 135 }

dataValue18_136 OBJECT-TYPE
SYNTAX INTEGER
MAX-ACCESS read-write
STATUS current
DESCRIPTION
"Data value."
::= { dataArray18 136 }

dataValue18_137 OBJECT-TYPE
SYNTAX INTEGER
MAX-ACCESS read-write
STATUS current
DESCRIPTION
"Data value."
::= { dataArray18 137 }

dataValue18_138 OBJECT-TYPE
SYNTAX INTEGER
MAX-ACCESS read-write
STATUS current
DESCRIPTION
"Data value."
::= { dataArray18 138 }

dataValue18_139 OBJECT-TYPE
SYNTAX INTEGER
MAX-ACCESS read-write
STATUS current
DESCRIPTION
"Data value."
::= { dataArray18 139 }

dataValue18_140 OBJECT-TYPE
SYNTAX INTEGER
MAX-ACCESS read-write
STATUS current
DESCRIPTION
"Data value."
::= { dataArray18 140 }

dataValue18_141 OBJECT-TYPE
SYNTAX INTEGER
MAX-ACCESS read-write
STATUS current
DESCRIPTION
"Data value."
::= { dataArray18 141 }

dataValue18_142 OBJECT-TYPE
SYNTAX INTEGER
MAX-ACCESS read-write
STATUS current
DESCRIPTION
"Data value."
::= { dataArray18 142 }

dataValue18_143 OBJECT-TYPE
SYNTAX INTEGER
MAX-ACCESS read-write
STATUS current
DESCRIPTION
"Data value."
::= { dataArray18 143 }

dataValue18_144 OBJECT-TYPE
SYNTAX INTEGER
MAX-ACCESS read-write
STATUS current
DESCRIPTION
"Data value."
::= { dataArray18 144 }

dataValue18_145 OBJECT-TYPE
SYNTAX INTEGER
MAX-ACCESS read-write
STATUS current
DESCRIPTION
"Data value."
::= { dataArray18 145 }

dataValue18_146 OBJECT-TYPE
SYNTAX INTEGER
MAX-ACCESS read-write
STATUS current
DESCRIPTION
"Data value."
::= { dataArray18 146 }

dataValue18_147 OBJECT-TYPE
SYNTAX INTEGER
MAX-ACCESS read-write
STATUS current
DESCRIPTION
"Data value."
::= { dataArray18 147 }

dataValue18_148 OBJECT-TYPE
SYNTAX INTEGER
MAX-ACCESS read-write
STATUS current
DESCRIPTION
"Data value."
::= { dataArray18 148 }

dataValue18_149 OBJECT-TYPE
SYNTAX INTEGER
MAX-ACCESS read-write
STATUS current
DESCRIPTION
"Data value."
::= { dataArray18 149 }

dataValue18_150 OBJECT-TYPE
SYNTAX INTEGER
MAX-ACCESS read-write
STATUS current
DESCRIPTION
"Data value."
::= { dataArray18 150 }

dataValue18_151 OBJECT-TYPE
SYNTAX INTEGER
MAX-ACCESS read-write
STATUS current
DESCRIPTION
"Data value."
::= { dataArray18 151 }

dataValue18_152 OBJECT-TYPE
SYNTAX INTEGER
MAX-ACCESS read-write
STATUS current
DESCRIPTION
"Data value."
::= { dataArray18 152 }

dataValue18_153 OBJECT-TYPE
SYNTAX INTEGER
MAX-ACCESS read-write
STATUS current
DESCRIPTION
"Data value."
::= { dataArray18 153 }

dataValue18_154 OBJECT-TYPE
SYNTAX INTEGER
MAX-ACCESS read-write
STATUS current
DESCRIPTION
"Data value."
::= { dataArray18 154 }

dataValue18_155 OBJECT-TYPE
SYNTAX INTEGER
MAX-ACCESS read-write
STATUS current
DESCRIPTION
"Data value."
::= { dataArray18 155 }

dataValue18_156 OBJECT-TYPE
SYNTAX INTEGER
MAX-ACCESS read-write
STATUS current
DESCRIPTION
"Data value."
::= { dataArray18 156 }

dataValue18_157 OBJECT-TYPE
SYNTAX INTEGER
MAX-ACCESS read-write
STATUS current
DESCRIPTION
"Data value."
::= { dataArray18 157 }

dataValue18_158 OBJECT-TYPE
SYNTAX INTEGER
MAX-ACCESS read-write
STATUS current
DESCRIPTION
"Data value."
::= { dataArray18 158 }

dataValue18_159 OBJECT-TYPE
SYNTAX INTEGER
MAX-ACCESS read-write
STATUS current
DESCRIPTION
"Data value."
::= { dataArray18 159 }

dataValue18_160 OBJECT-TYPE
SYNTAX INTEGER
MAX-ACCESS read-write
STATUS current
DESCRIPTION
"Data value."
::= { dataArray18 160 }

dataValue18_161 OBJECT-TYPE
SYNTAX INTEGER
MAX-ACCESS read-write
STATUS current
DESCRIPTION
"Data value."
::= { dataArray18 161 }

dataValue18_162 OBJECT-TYPE
SYNTAX INTEGER
MAX-ACCESS read-write
STATUS current
DESCRIPTION
"Data value."
::= { dataArray18 162 }

dataValue18_163 OBJECT-TYPE
SYNTAX INTEGER
MAX-ACCESS read-write
STATUS current
DESCRIPTION
"Data value."
::= { dataArray18 163 }

dataValue18_164 OBJECT-TYPE
SYNTAX INTEGER
MAX-ACCESS read-write
STATUS current
DESCRIPTION
"Data value."
::= { dataArray18 164 }

dataValue18_165 OBJECT-TYPE
SYNTAX INTEGER
MAX-ACCESS read-write
STATUS current
DESCRIPTION
"Data value."
::= { dataArray18 165 }

dataValue18_166 OBJECT-TYPE
SYNTAX INTEGER
MAX-ACCESS read-write
STATUS current
DESCRIPTION
"Data value."
::= { dataArray18 166 }

dataValue18_167 OBJECT-TYPE
SYNTAX INTEGER
MAX-ACCESS read-write
STATUS current
DESCRIPTION
"Data value."
::= { dataArray18 167 }

dataValue18_168 OBJECT-TYPE
SYNTAX INTEGER
MAX-ACCESS read-write
STATUS current
DESCRIPTION
"Data value."
::= { dataArray18 168 }

dataValue18_169 OBJECT-TYPE
SYNTAX INTEGER
MAX-ACCESS read-write
STATUS current
DESCRIPTION
"Data value."
::= { dataArray18 169 }

dataValue18_170 OBJECT-TYPE
SYNTAX INTEGER
MAX-ACCESS read-write
STATUS current
DESCRIPTION
"Data value."
::= { dataArray18 170 }

dataValue18_171 OBJECT-TYPE
SYNTAX INTEGER
MAX-ACCESS read-write
STATUS current
DESCRIPTION
"Data value."
::= { dataArray18 171 }

dataValue18_172 OBJECT-TYPE
SYNTAX INTEGER
MAX-ACCESS read-write
STATUS current
DESCRIPTION
"Data value."
::= { dataArray18 172 }

dataValue18_173 OBJECT-TYPE
SYNTAX INTEGER
MAX-ACCESS read-write
STATUS current
DESCRIPTION
"Data value."
::= { dataArray18 173 }

dataValue18_174 OBJECT-TYPE
SYNTAX INTEGER
MAX-ACCESS read-write
STATUS current
DESCRIPTION
"Data value."
::= { dataArray18 174 }

dataValue18_175 OBJECT-TYPE
SYNTAX INTEGER
MAX-ACCESS read-write
STATUS current
DESCRIPTION
"Data value."
::= { dataArray18 175 }

dataValue18_176 OBJECT-TYPE
SYNTAX INTEGER
MAX-ACCESS read-write
STATUS current
DESCRIPTION
"Data value."
::= { dataArray18 176 }

dataValue18_177 OBJECT-TYPE
SYNTAX INTEGER
MAX-ACCESS read-write
STATUS current
DESCRIPTION
"Data value."
::= { dataArray18 177 }

dataValue18_178 OBJECT-TYPE
SYNTAX INTEGER
MAX-ACCESS read-write
STATUS current
DESCRIPTION
"Data value."
::= { dataArray18 178 }

dataValue18_179 OBJECT-TYPE
SYNTAX INTEGER
MAX-ACCESS read-write
STATUS current
DESCRIPTION
"Data value."
::= { dataArray18 179 }

dataValue18_180 OBJECT-TYPE
SYNTAX INTEGER
MAX-ACCESS read-write
STATUS current
DESCRIPTION
"Data value."
::= { dataArray18 180 }

dataValue18_181 OBJECT-TYPE
SYNTAX INTEGER
MAX-ACCESS read-write
STATUS current
DESCRIPTION
"Data value."
::= { dataArray18 181 }

dataValue18_182 OBJECT-TYPE
SYNTAX INTEGER
MAX-ACCESS read-write
STATUS current
DESCRIPTION
"Data value."
::= { dataArray18 182 }

dataValue18_183 OBJECT-TYPE
SYNTAX INTEGER
MAX-ACCESS read-write
STATUS current
DESCRIPTION
"Data value."
::= { dataArray18 183 }

dataValue18_184 OBJECT-TYPE
SYNTAX INTEGER
MAX-ACCESS read-write
STATUS current
DESCRIPTION
"Data value."
::= { dataArray18 184 }

dataValue18_185 OBJECT-TYPE
SYNTAX INTEGER
MAX-ACCESS read-write
STATUS current
DESCRIPTION
"Data value."
::= { dataArray18 185 }

dataValue18_186 OBJECT-TYPE
SYNTAX INTEGER
MAX-ACCESS read-write
STATUS current
DESCRIPTION
"Data value."
::= { dataArray18 186 }

dataValue18_187 OBJECT-TYPE
SYNTAX INTEGER
MAX-ACCESS read-write
STATUS current
DESCRIPTION
"Data value."
::= { dataArray18 187 }

dataValue18_188 OBJECT-TYPE
SYNTAX INTEGER
MAX-ACCESS read-write
STATUS current
DESCRIPTION
"Data value."
::= { dataArray18 188 }

dataValue18_189 OBJECT-TYPE
SYNTAX INTEGER
MAX-ACCESS read-write
STATUS current
DESCRIPTION
"Data value."
::= { dataArray18 189 }

dataValue18_190 OBJECT-TYPE
SYNTAX INTEGER
MAX-ACCESS read-write
STATUS current
DESCRIPTION
"Data value."
::= { dataArray18 190 }

dataValue18_191 OBJECT-TYPE
SYNTAX INTEGER
MAX-ACCESS read-write
STATUS current
DESCRIPTION
"Data value."
::= { dataArray18 191 }

dataValue18_192 OBJECT-TYPE
SYNTAX INTEGER
MAX-ACCESS read-write
STATUS current
DESCRIPTION
"Data value."
::= { dataArray18 192 }

dataValue18_193 OBJECT-TYPE
SYNTAX INTEGER
MAX-ACCESS read-write
STATUS current
DESCRIPTION
"Data value."
::= { dataArray18 193 }

dataValue18_194 OBJECT-TYPE
SYNTAX INTEGER
MAX-ACCESS read-write
STATUS current
DESCRIPTION
"Data value."
::= { dataArray18 194 }

dataValue18_195 OBJECT-TYPE
SYNTAX INTEGER
MAX-ACCESS read-write
STATUS current
DESCRIPTION
"Data value."
::= { dataArray18 195 }

dataValue18_196 OBJECT-TYPE
SYNTAX INTEGER
MAX-ACCESS read-write
STATUS current
DESCRIPTION
"Data value."
::= { dataArray18 196 }

dataValue18_197 OBJECT-TYPE
SYNTAX INTEGER
MAX-ACCESS read-write
STATUS current
DESCRIPTION
"Data value."
::= { dataArray18 197 }

dataValue18_198 OBJECT-TYPE
SYNTAX INTEGER
MAX-ACCESS read-write
STATUS current
DESCRIPTION
"Data value."
::= { dataArray18 198 }

dataValue18_199 OBJECT-TYPE
SYNTAX INTEGER
MAX-ACCESS read-write
STATUS current
DESCRIPTION
"Data value."
::= { dataArray18 199 }

dataValue18_200 OBJECT-TYPE
SYNTAX INTEGER
MAX-ACCESS read-write
STATUS current
DESCRIPTION
"Data value."
::= { dataArray18 200 }

dataValue18_201 OBJECT-TYPE
SYNTAX INTEGER
MAX-ACCESS read-write
STATUS current
DESCRIPTION
"Data value."
::= { dataArray18 201 }

dataValue18_202 OBJECT-TYPE
SYNTAX INTEGER
MAX-ACCESS read-write
STATUS current
DESCRIPTION
"Data value."
::= { dataArray18 202 }

dataValue18_203 OBJECT-TYPE
SYNTAX INTEGER
MAX-ACCESS read-write
STATUS current
DESCRIPTION
"Data value."
::= { dataArray18 203 }

dataValue18_204 OBJECT-TYPE
SYNTAX INTEGER
MAX-ACCESS read-write
STATUS current
DESCRIPTION
"Data value."
::= { dataArray18 204 }

dataValue18_205 OBJECT-TYPE
SYNTAX INTEGER
MAX-ACCESS read-write
STATUS current
DESCRIPTION
"Data value."
::= { dataArray18 205 }

dataValue18_206 OBJECT-TYPE
SYNTAX INTEGER
MAX-ACCESS read-write
STATUS current
DESCRIPTION
"Data value."
::= { dataArray18 206 }

dataValue18_207 OBJECT-TYPE
SYNTAX INTEGER
MAX-ACCESS read-write
STATUS current
DESCRIPTION
"Data value."
::= { dataArray18 207 }

dataValue18_208 OBJECT-TYPE
SYNTAX INTEGER
MAX-ACCESS read-write
STATUS current
DESCRIPTION
"Data value."
::= { dataArray18 208 }

dataValue18_209 OBJECT-TYPE
SYNTAX INTEGER
MAX-ACCESS read-write
STATUS current
DESCRIPTION
"Data value."
::= { dataArray18 209 }

dataValue18_210 OBJECT-TYPE
SYNTAX INTEGER
MAX-ACCESS read-write
STATUS current
DESCRIPTION
"Data value."
::= { dataArray18 210 }

dataValue18_211 OBJECT-TYPE
SYNTAX INTEGER
MAX-ACCESS read-write
STATUS current
DESCRIPTION
"Data value."
::= { dataArray18 211 }

dataValue18_212 OBJECT-TYPE
SYNTAX INTEGER
MAX-ACCESS read-write
STATUS current
DESCRIPTION
"Data value."
::= { dataArray18 212 }

dataValue18_213 OBJECT-TYPE
SYNTAX INTEGER
MAX-ACCESS read-write
STATUS current
DESCRIPTION
"Data value."
::= { dataArray18 213 }

dataValue18_214 OBJECT-TYPE
SYNTAX INTEGER
MAX-ACCESS read-write
STATUS current
DESCRIPTION
"Data value."
::= { dataArray18 214 }

dataValue18_215 OBJECT-TYPE
SYNTAX INTEGER
MAX-ACCESS read-write
STATUS current
DESCRIPTION
"Data value."
::= { dataArray18 215 }

dataValue18_216 OBJECT-TYPE
SYNTAX INTEGER
MAX-ACCESS read-write
STATUS current
DESCRIPTION
"Data value."
::= { dataArray18 216 }

dataValue18_217 OBJECT-TYPE
SYNTAX INTEGER
MAX-ACCESS read-write
STATUS current
DESCRIPTION
"Data value."
::= { dataArray18 217 }

dataValue18_218 OBJECT-TYPE
SYNTAX INTEGER
MAX-ACCESS read-write
STATUS current
DESCRIPTION
"Data value."
::= { dataArray18 218 }

dataValue18_219 OBJECT-TYPE
SYNTAX INTEGER
MAX-ACCESS read-write
STATUS current
DESCRIPTION
"Data value."
::= { dataArray18 219 }

dataValue18_220 OBJECT-TYPE
SYNTAX INTEGER
MAX-ACCESS read-write
STATUS current
DESCRIPTION
"Data value."
::= { dataArray18 220 }

dataValue18_221 OBJECT-TYPE
SYNTAX INTEGER
MAX-ACCESS read-write
STATUS current
DESCRIPTION
"Data value."
::= { dataArray18 221 }

dataValue18_222 OBJECT-TYPE
SYNTAX INTEGER
MAX-ACCESS read-write
STATUS current
DESCRIPTION
"Data value."
::= { dataArray18 222 }

dataValue18_223 OBJECT-TYPE
SYNTAX INTEGER
MAX-ACCESS read-write
STATUS current
DESCRIPTION
"Data value."
::= { dataArray18 223 }

dataValue18_224 OBJECT-TYPE
SYNTAX INTEGER
MAX-ACCESS read-write
STATUS current
DESCRIPTION
"Data value."
::= { dataArray18 224 }

dataValue18_225 OBJECT-TYPE
SYNTAX INTEGER
MAX-ACCESS read-write
STATUS current
DESCRIPTION
"Data value."
::= { dataArray18 225 }

dataValue18_226 OBJECT-TYPE
SYNTAX INTEGER
MAX-ACCESS read-write
STATUS current
DESCRIPTION
"Data value."
::= { dataArray18 226 }

dataValue18_227 OBJECT-TYPE
SYNTAX INTEGER
MAX-ACCESS read-write
STATUS current
DESCRIPTION
"Data value."
::= { dataArray18 227 }

dataValue18_228 OBJECT-TYPE
SYNTAX INTEGER
MAX-ACCESS read-write
STATUS current
DESCRIPTION
"Data value."
::= { dataArray18 228 }

dataValue18_229 OBJECT-TYPE
SYNTAX INTEGER
MAX-ACCESS read-write
STATUS current
DESCRIPTION
"Data value."
::= { dataArray18 229 }

dataValue18_230 OBJECT-TYPE
SYNTAX INTEGER
MAX-ACCESS read-write
STATUS current
DESCRIPTION
"Data value."
::= { dataArray18 230 }

dataValue18_231 OBJECT-TYPE
SYNTAX INTEGER
MAX-ACCESS read-write
STATUS current
DESCRIPTION
"Data value."
::= { dataArray18 231 }

dataValue18_232 OBJECT-TYPE
SYNTAX INTEGER
MAX-ACCESS read-write
STATUS current
DESCRIPTION
"Data value."
::= { dataArray18 232 }

dataValue18_233 OBJECT-TYPE
SYNTAX INTEGER
MAX-ACCESS read-write
STATUS current
DESCRIPTION
"Data value."
::= { dataArray18 233 }

dataValue18_234 OBJECT-TYPE
SYNTAX INTEGER
MAX-ACCESS read-write
STATUS current
DESCRIPTION
"Data value."
::= { dataArray18 234 }

dataValue18_235 OBJECT-TYPE
SYNTAX INTEGER
MAX-ACCESS read-write
STATUS current
DESCRIPTION
"Data value."
::= { dataArray18 235 }

dataValue18_236 OBJECT-TYPE
SYNTAX INTEGER
MAX-ACCESS read-write
STATUS current
DESCRIPTION
"Data value."
::= { dataArray18 236 }

dataValue18_237 OBJECT-TYPE
SYNTAX INTEGER
MAX-ACCESS read-write
STATUS current
DESCRIPTION
"Data value."
::= { dataArray18 237 }

dataValue18_238 OBJECT-TYPE
SYNTAX INTEGER
MAX-ACCESS read-write
STATUS current
DESCRIPTION
"Data value."
::= { dataArray18 238 }

dataValue18_239 OBJECT-TYPE
SYNTAX INTEGER
MAX-ACCESS read-write
STATUS current
DESCRIPTION
"Data value."
::= { dataArray18 239 }

dataValue18_240 OBJECT-TYPE
SYNTAX INTEGER
MAX-ACCESS read-write
STATUS current
DESCRIPTION
"Data value."
::= { dataArray18 240 }

dataValue18_241 OBJECT-TYPE
SYNTAX INTEGER
MAX-ACCESS read-write
STATUS current
DESCRIPTION
"Data value."
::= { dataArray18 241 }

dataValue18_242 OBJECT-TYPE
SYNTAX INTEGER
MAX-ACCESS read-write
STATUS current
DESCRIPTION
"Data value."
::= { dataArray18 242 }

dataValue18_243 OBJECT-TYPE
SYNTAX INTEGER
MAX-ACCESS read-write
STATUS current
DESCRIPTION
"Data value."
::= { dataArray18 243 }

dataValue18_244 OBJECT-TYPE
SYNTAX INTEGER
MAX-ACCESS read-write
STATUS current
DESCRIPTION
"Data value."
::= { dataArray18 244 }

dataValue18_245 OBJECT-TYPE
SYNTAX INTEGER
MAX-ACCESS read-write
STATUS current
DESCRIPTION
"Data value."
::= { dataArray18 245 }

dataValue18_246 OBJECT-TYPE
SYNTAX INTEGER
MAX-ACCESS read-write
STATUS current
DESCRIPTION
"Data value."
::= { dataArray18 246 }

dataValue18_247 OBJECT-TYPE
SYNTAX INTEGER
MAX-ACCESS read-write
STATUS current
DESCRIPTION
"Data value."
::= { dataArray18 247 }

dataValue18_248 OBJECT-TYPE
SYNTAX INTEGER
MAX-ACCESS read-write
STATUS current
DESCRIPTION
"Data value."
::= { dataArray18 248 }

dataValue18_249 OBJECT-TYPE
SYNTAX INTEGER
MAX-ACCESS read-write
STATUS current
DESCRIPTION
"Data value."
::= { dataArray18 249 }

dataValue18_250 OBJECT-TYPE
SYNTAX INTEGER
MAX-ACCESS read-write
STATUS current
DESCRIPTION
"Data value."
::= { dataArray18 250 }

dataValue18_251 OBJECT-TYPE
SYNTAX INTEGER
MAX-ACCESS read-write
STATUS current
DESCRIPTION
"Data value."
::= { dataArray18 251 }

dataValue18_252 OBJECT-TYPE
SYNTAX INTEGER
MAX-ACCESS read-write
STATUS current
DESCRIPTION
"Data value."
::= { dataArray18 252 }

dataValue18_253 OBJECT-TYPE
SYNTAX INTEGER
MAX-ACCESS read-write
STATUS current
DESCRIPTION
"Data value."
::= { dataArray18 253 }

dataValue18_254 OBJECT-TYPE
SYNTAX INTEGER
MAX-ACCESS read-write
STATUS current
DESCRIPTION
"Data value."
::= { dataArray18 254 }

dataValue18_255 OBJECT-TYPE
SYNTAX INTEGER
MAX-ACCESS read-write
STATUS current
DESCRIPTION
"Data value."
::= { dataArray18 255 }

dataValue18_256 OBJECT-TYPE
SYNTAX INTEGER
MAX-ACCESS read-write
STATUS current
DESCRIPTION
"Data value."
::= { dataArray18 256 }

dataValue18_257 OBJECT-TYPE
SYNTAX INTEGER
MAX-ACCESS read-write
STATUS current
DESCRIPTION
"Data value."
::= { dataArray18 257 }

dataValue18_258 OBJECT-TYPE
SYNTAX INTEGER
MAX-ACCESS read-write
STATUS current
DESCRIPTION
"Data value."
::= { dataArray18 258 }

dataValue18_259 OBJECT-TYPE
SYNTAX INTEGER
MAX-ACCESS read-write
STATUS current
DESCRIPTION
"Data value."
::= { dataArray18 259 }

dataValue18_260 OBJECT-TYPE
SYNTAX INTEGER
MAX-ACCESS read-write
STATUS current
DESCRIPTION
"Data value."
::= { dataArray18 260 }

dataValue18_261 OBJECT-TYPE
SYNTAX INTEGER
MAX-ACCESS read-write
STATUS current
DESCRIPTION
"Data value."
::= { dataArray18 261 }

dataValue18_262 OBJECT-TYPE
SYNTAX INTEGER
MAX-ACCESS read-write
STATUS current
DESCRIPTION
"Data value."
::= { dataArray18 262 }

dataValue18_263 OBJECT-TYPE
SYNTAX INTEGER
MAX-ACCESS read-write
STATUS current
DESCRIPTION
"Data value."
::= { dataArray18 263 }

dataValue18_264 OBJECT-TYPE
SYNTAX INTEGER
MAX-ACCESS read-write
STATUS current
DESCRIPTION
"Data value."
::= { dataArray18 264 }

dataValue18_265 OBJECT-TYPE
SYNTAX INTEGER
MAX-ACCESS read-write
STATUS current
DESCRIPTION
"Data value."
::= { dataArray18 265 }

dataValue18_266 OBJECT-TYPE
SYNTAX INTEGER
MAX-ACCESS read-write
STATUS current
DESCRIPTION
"Data value."
::= { dataArray18 266 }

dataValue18_267 OBJECT-TYPE
SYNTAX INTEGER
MAX-ACCESS read-write
STATUS current
DESCRIPTION
"Data value."
::= { dataArray18 267 }

dataValue18_268 OBJECT-TYPE
SYNTAX INTEGER
MAX-ACCESS read-write
STATUS current
DESCRIPTION
"Data value."
::= { dataArray18 268 }

dataValue18_269 OBJECT-TYPE
SYNTAX INTEGER
MAX-ACCESS read-write
STATUS current
DESCRIPTION
"Data value."
::= { dataArray18 269 }

dataValue18_270 OBJECT-TYPE
SYNTAX INTEGER
MAX-ACCESS read-write
STATUS current
DESCRIPTION
"Data value."
::= { dataArray18 270 }

dataValue18_271 OBJECT-TYPE
SYNTAX INTEGER
MAX-ACCESS read-write
STATUS current
DESCRIPTION
"Data value."
::= { dataArray18 271 }

dataValue18_272 OBJECT-TYPE
SYNTAX INTEGER
MAX-ACCESS read-write
STATUS current
DESCRIPTION
"Data value."
::= { dataArray18 272 }

dataValue18_273 OBJECT-TYPE
SYNTAX INTEGER
MAX-ACCESS read-write
STATUS current
DESCRIPTION
"Data value."
::= { dataArray18 273 }

dataValue18_274 OBJECT-TYPE
SYNTAX INTEGER
MAX-ACCESS read-write
STATUS current
DESCRIPTION
"Data value."
::= { dataArray18 274 }

dataValue18_275 OBJECT-TYPE
SYNTAX INTEGER
MAX-ACCESS read-write
STATUS current
DESCRIPTION
"Data value."
::= { dataArray18 275 }

dataValue18_276 OBJECT-TYPE
SYNTAX INTEGER
MAX-ACCESS read-write
STATUS current
DESCRIPTION
"Data value."
::= { dataArray18 276 }

dataValue18_277 OBJECT-TYPE
SYNTAX INTEGER
MAX-ACCESS read-write
STATUS current
DESCRIPTION
"Data value."
::= { dataArray18 277 }

dataValue18_278 OBJECT-TYPE
SYNTAX INTEGER
MAX-ACCESS read-write
STATUS current
DESCRIPTION
"Data value."
::= { dataArray18 278 }

dataValue18_279 OBJECT-TYPE
SYNTAX INTEGER
MAX-ACCESS read-write
STATUS current
DESCRIPTION
"Data value."
::= { dataArray18 279 }

dataValue18_280 OBJECT-TYPE
SYNTAX INTEGER
MAX-ACCESS read-write
STATUS current
DESCRIPTION
"Data value."
::= { dataArray18 280 }

dataValue18_281 OBJECT-TYPE
SYNTAX INTEGER
MAX-ACCESS read-write
STATUS current
DESCRIPTION
"Data value."
::= { dataArray18 281 }

dataValue18_282 OBJECT-TYPE
SYNTAX INTEGER
MAX-ACCESS read-write
STATUS current
DESCRIPTION
"Data value."
::= { dataArray18 282 }

dataValue18_283 OBJECT-TYPE
SYNTAX INTEGER
MAX-ACCESS read-write
STATUS current
DESCRIPTION
"Data value."
::= { dataArray18 283 }

dataValue18_284 OBJECT-TYPE
SYNTAX INTEGER
MAX-ACCESS read-write
STATUS current
DESCRIPTION
"Data value."
::= { dataArray18 284 }

dataValue18_285 OBJECT-TYPE
SYNTAX INTEGER
MAX-ACCESS read-write
STATUS current
DESCRIPTION
"Data value."
::= { dataArray18 285 }

dataValue18_286 OBJECT-TYPE
SYNTAX INTEGER
MAX-ACCESS read-write
STATUS current
DESCRIPTION
"Data value."
::= { dataArray18 286 }

dataValue18_287 OBJECT-TYPE
SYNTAX INTEGER
MAX-ACCESS read-write
STATUS current
DESCRIPTION
"Data value."
::= { dataArray18 287 }

dataValue18_288 OBJECT-TYPE
SYNTAX INTEGER
MAX-ACCESS read-write
STATUS current
DESCRIPTION
"Data value."
::= { dataArray18 288 }

dataValue18_289 OBJECT-TYPE
SYNTAX INTEGER
MAX-ACCESS read-write
STATUS current
DESCRIPTION
"Data value."
::= { dataArray18 289 }

dataValue18_290 OBJECT-TYPE
SYNTAX INTEGER
MAX-ACCESS read-write
STATUS current
DESCRIPTION
"Data value."
::= { dataArray18 290 }

dataValue18_291 OBJECT-TYPE
SYNTAX INTEGER
MAX-ACCESS read-write
STATUS current
DESCRIPTION
"Data value."
::= { dataArray18 291 }

dataValue18_292 OBJECT-TYPE
SYNTAX INTEGER
MAX-ACCESS read-write
STATUS current
DESCRIPTION
"Data value."
::= { dataArray18 292 }

dataValue18_293 OBJECT-TYPE
SYNTAX INTEGER
MAX-ACCESS read-write
STATUS current
DESCRIPTION
"Data value."
::= { dataArray18 293 }

dataValue18_294 OBJECT-TYPE
SYNTAX INTEGER
MAX-ACCESS read-write
STATUS current
DESCRIPTION
"Data value."
::= { dataArray18 294 }

dataValue18_295 OBJECT-TYPE
SYNTAX INTEGER
MAX-ACCESS read-write
STATUS current
DESCRIPTION
"Data value."
::= { dataArray18 295 }

dataValue18_296 OBJECT-TYPE
SYNTAX INTEGER
MAX-ACCESS read-write
STATUS current
DESCRIPTION
"Data value."
::= { dataArray18 296 }

dataValue18_297 OBJECT-TYPE
SYNTAX INTEGER
MAX-ACCESS read-write
STATUS current
DESCRIPTION
"Data value."
::= { dataArray18 297 }

dataValue18_298 OBJECT-TYPE
SYNTAX INTEGER
MAX-ACCESS read-write
STATUS current
DESCRIPTION
"Data value."
::= { dataArray18 298 }

dataValue18_299 OBJECT-TYPE
SYNTAX INTEGER
MAX-ACCESS read-write
STATUS current
DESCRIPTION
"Data value."
::= { dataArray18 299 }

dataValue18_300 OBJECT-TYPE
SYNTAX INTEGER
MAX-ACCESS read-write
STATUS current
DESCRIPTION
"Data value."
::= { dataArray18 300 }

dataValue18_301 OBJECT-TYPE
SYNTAX INTEGER
MAX-ACCESS read-write
STATUS current
DESCRIPTION
"Data value."
::= { dataArray18 301 }

dataValue18_302 OBJECT-TYPE
SYNTAX INTEGER
MAX-ACCESS read-write
STATUS current
DESCRIPTION
"Data value."
::= { dataArray18 302 }

dataValue18_303 OBJECT-TYPE
SYNTAX INTEGER
MAX-ACCESS read-write
STATUS current
DESCRIPTION
"Data value."
::= { dataArray18 303 }

dataValue18_304 OBJECT-TYPE
SYNTAX INTEGER
MAX-ACCESS read-write
STATUS current
DESCRIPTION
"Data value."
::= { dataArray18 304 }

dataValue18_305 OBJECT-TYPE
SYNTAX INTEGER
MAX-ACCESS read-write
STATUS current
DESCRIPTION
"Data value."
::= { dataArray18 305 }

dataValue18_306 OBJECT-TYPE
SYNTAX INTEGER
MAX-ACCESS read-write
STATUS current
DESCRIPTION
"Data value."
::= { dataArray18 306 }

dataValue18_307 OBJECT-TYPE
SYNTAX INTEGER
MAX-ACCESS read-write
STATUS current
DESCRIPTION
"Data value."
::= { dataArray18 307 }

dataValue18_308 OBJECT-TYPE
SYNTAX INTEGER
MAX-ACCESS read-write
STATUS current
DESCRIPTION
"Data value."
::= { dataArray18 308 }

dataValue18_309 OBJECT-TYPE
SYNTAX INTEGER
MAX-ACCESS read-write
STATUS current
DESCRIPTION
"Data value."
::= { dataArray18 309 }

dataValue18_310 OBJECT-TYPE
SYNTAX INTEGER
MAX-ACCESS read-write
STATUS current
DESCRIPTION
"Data value."
::= { dataArray18 310 }

dataValue18_311 OBJECT-TYPE
SYNTAX INTEGER
MAX-ACCESS read-write
STATUS current
DESCRIPTION
"Data value."
::= { dataArray18 311 }

dataValue18_312 OBJECT-TYPE
SYNTAX INTEGER
MAX-ACCESS read-write
STATUS current
DESCRIPTION
"Data value."
::= { dataArray18 312 }

dataValue18_313 OBJECT-TYPE
SYNTAX INTEGER
MAX-ACCESS read-write
STATUS current
DESCRIPTION
"Data value."
::= { dataArray18 313 }

dataValue18_314 OBJECT-TYPE
SYNTAX INTEGER
MAX-ACCESS read-write
STATUS current
DESCRIPTION
"Data value."
::= { dataArray18 314 }

dataValue18_315 OBJECT-TYPE
SYNTAX INTEGER
MAX-ACCESS read-write
STATUS current
DESCRIPTION
"Data value."
::= { dataArray18 315 }

dataValue18_316 OBJECT-TYPE
SYNTAX INTEGER
MAX-ACCESS read-write
STATUS current
DESCRIPTION
"Data value."
::= { dataArray18 316 }

dataValue18_317 OBJECT-TYPE
SYNTAX INTEGER
MAX-ACCESS read-write
STATUS current
DESCRIPTION
"Data value."
::= { dataArray18 317 }

dataValue18_318 OBJECT-TYPE
SYNTAX INTEGER
MAX-ACCESS read-write
STATUS current
DESCRIPTION
"Data value."
::= { dataArray18 318 }

dataValue18_319 OBJECT-TYPE
SYNTAX INTEGER
MAX-ACCESS read-write
STATUS current
DESCRIPTION
"Data value."
::= { dataArray18 319 }

dataValue18_320 OBJECT-TYPE
SYNTAX INTEGER
MAX-ACCESS read-write
STATUS current
DESCRIPTION
"Data value."
::= { dataArray18 320 }

dataValue18_321 OBJECT-TYPE
SYNTAX INTEGER
MAX-ACCESS read-write
STATUS current
DESCRIPTION
"Data value."
::= { dataArray18 321 }

dataValue18_322 OBJECT-TYPE
SYNTAX INTEGER
MAX-ACCESS read-write
STATUS current
DESCRIPTION
"Data value."
::= { dataArray18 322 }

dataValue18_323 OBJECT-TYPE
SYNTAX INTEGER
MAX-ACCESS read-write
STATUS current
DESCRIPTION
"Data value."
::= { dataArray18 323 }

dataValue18_324 OBJECT-TYPE
SYNTAX INTEGER
MAX-ACCESS read-write
STATUS current
DESCRIPTION
"Data value."
::= { dataArray18 324 }

dataValue18_325 OBJECT-TYPE
SYNTAX INTEGER
MAX-ACCESS read-write
STATUS current
DESCRIPTION
"Data value."
::= { dataArray18 325 }

dataValue18_326 OBJECT-TYPE
SYNTAX INTEGER
MAX-ACCESS read-write
STATUS current
DESCRIPTION
"Data value."
::= { dataArray18 326 }

dataValue18_327 OBJECT-TYPE
SYNTAX INTEGER
MAX-ACCESS read-write
STATUS current
DESCRIPTION
"Data value."
::= { dataArray18 327 }

dataValue18_328 OBJECT-TYPE
SYNTAX INTEGER
MAX-ACCESS read-write
STATUS current
DESCRIPTION
"Data value."
::= { dataArray18 328 }

dataValue18_329 OBJECT-TYPE
SYNTAX INTEGER
MAX-ACCESS read-write
STATUS current
DESCRIPTION
"Data value."
::= { dataArray18 329 }

dataValue18_330 OBJECT-TYPE
SYNTAX INTEGER
MAX-ACCESS read-write
STATUS current
DESCRIPTION
"Data value."
::= { dataArray18 330 }

dataValue18_331 OBJECT-TYPE
SYNTAX INTEGER
MAX-ACCESS read-write
STATUS current
DESCRIPTION
"Data value."
::= { dataArray18 331 }

dataValue18_332 OBJECT-TYPE
SYNTAX INTEGER
MAX-ACCESS read-write
STATUS current
DESCRIPTION
"Data value."
::= { dataArray18 332 }

dataValue18_333 OBJECT-TYPE
SYNTAX INTEGER
MAX-ACCESS read-write
STATUS current
DESCRIPTION
"Data value."
::= { dataArray18 333 }

dataValue18_334 OBJECT-TYPE
SYNTAX INTEGER
MAX-ACCESS read-write
STATUS current
DESCRIPTION
"Data value."
::= { dataArray18 334 }

dataValue18_335 OBJECT-TYPE
SYNTAX INTEGER
MAX-ACCESS read-write
STATUS current
DESCRIPTION
"Data value."
::= { dataArray18 335 }

dataValue18_336 OBJECT-TYPE
SYNTAX INTEGER
MAX-ACCESS read-write
STATUS current
DESCRIPTION
"Data value."
::= { dataArray18 336 }

dataValue18_337 OBJECT-TYPE
SYNTAX INTEGER
MAX-ACCESS read-write
STATUS current
DESCRIPTION
"Data value."
::= { dataArray18 337 }

dataValue18_338 OBJECT-TYPE
SYNTAX INTEGER
MAX-ACCESS read-write
STATUS current
DESCRIPTION
"Data value."
::= { dataArray18 338 }

dataValue18_339 OBJECT-TYPE
SYNTAX INTEGER
MAX-ACCESS read-write
STATUS current
DESCRIPTION
"Data value."
::= { dataArray18 339 }

dataValue18_340 OBJECT-TYPE
SYNTAX INTEGER
MAX-ACCESS read-write
STATUS current
DESCRIPTION
"Data value."
::= { dataArray18 340 }

dataValue18_341 OBJECT-TYPE
SYNTAX INTEGER
MAX-ACCESS read-write
STATUS current
DESCRIPTION
"Data value."
::= { dataArray18 341 }

dataValue18_342 OBJECT-TYPE
SYNTAX INTEGER
MAX-ACCESS read-write
STATUS current
DESCRIPTION
"Data value."
::= { dataArray18 342 }

dataValue18_343 OBJECT-TYPE
SYNTAX INTEGER
MAX-ACCESS read-write
STATUS current
DESCRIPTION
"Data value."
::= { dataArray18 343 }

dataValue18_344 OBJECT-TYPE
SYNTAX INTEGER
MAX-ACCESS read-write
STATUS current
DESCRIPTION
"Data value."
::= { dataArray18 344 }

dataValue18_345 OBJECT-TYPE
SYNTAX INTEGER
MAX-ACCESS read-write
STATUS current
DESCRIPTION
"Data value."
::= { dataArray18 345 }

dataValue18_346 OBJECT-TYPE
SYNTAX INTEGER
MAX-ACCESS read-write
STATUS current
DESCRIPTION
"Data value."
::= { dataArray18 346 }

dataValue18_347 OBJECT-TYPE
SYNTAX INTEGER
MAX-ACCESS read-write
STATUS current
DESCRIPTION
"Data value."
::= { dataArray18 347 }

dataValue18_348 OBJECT-TYPE
SYNTAX INTEGER
MAX-ACCESS read-write
STATUS current
DESCRIPTION
"Data value."
::= { dataArray18 348 }

dataValue18_349 OBJECT-TYPE
SYNTAX INTEGER
MAX-ACCESS read-write
STATUS current
DESCRIPTION
"Data value."
::= { dataArray18 349 }

dataValue18_350 OBJECT-TYPE
SYNTAX INTEGER
MAX-ACCESS read-write
STATUS current
DESCRIPTION
"Data value."
::= { dataArray18 350 }

dataValue18_351 OBJECT-TYPE
SYNTAX INTEGER
MAX-ACCESS read-write
STATUS current
DESCRIPTION
"Data value."
::= { dataArray18 351 }

dataValue18_352 OBJECT-TYPE
SYNTAX INTEGER
MAX-ACCESS read-write
STATUS current
DESCRIPTION
"Data value."
::= { dataArray18 352 }

dataValue18_353 OBJECT-TYPE
SYNTAX INTEGER
MAX-ACCESS read-write
STATUS current
DESCRIPTION
"Data value."
::= { dataArray18 353 }

dataValue18_354 OBJECT-TYPE
SYNTAX INTEGER
MAX-ACCESS read-write
STATUS current
DESCRIPTION
"Data value."
::= { dataArray18 354 }

dataValue18_355 OBJECT-TYPE
SYNTAX INTEGER
MAX-ACCESS read-write
STATUS current
DESCRIPTION
"Data value."
::= { dataArray18 355 }

dataValue18_356 OBJECT-TYPE
SYNTAX INTEGER
MAX-ACCESS read-write
STATUS current
DESCRIPTION
"Data value."
::= { dataArray18 356 }

dataValue18_357 OBJECT-TYPE
SYNTAX INTEGER
MAX-ACCESS read-write
STATUS current
DESCRIPTION
"Data value."
::= { dataArray18 357 }

dataValue18_358 OBJECT-TYPE
SYNTAX INTEGER
MAX-ACCESS read-write
STATUS current
DESCRIPTION
"Data value."
::= { dataArray18 358 }

dataValue18_359 OBJECT-TYPE
SYNTAX INTEGER
MAX-ACCESS read-write
STATUS current
DESCRIPTION
"Data value."
::= { dataArray18 359 }

dataValue18_360 OBJECT-TYPE
SYNTAX INTEGER
MAX-ACCESS read-write
STATUS current
DESCRIPTION
"Data value."
::= { dataArray18 360 }

dataValue18_361 OBJECT-TYPE
SYNTAX INTEGER
MAX-ACCESS read-write
STATUS current
DESCRIPTION
"Data value."
::= { dataArray18 361 }

dataValue18_362 OBJECT-TYPE
SYNTAX INTEGER
MAX-ACCESS read-write
STATUS current
DESCRIPTION
"Data value."
::= { dataArray18 362 }

dataValue18_363 OBJECT-TYPE
SYNTAX INTEGER
MAX-ACCESS read-write
STATUS current
DESCRIPTION
"Data value."
::= { dataArray18 363 }

dataValue18_364 OBJECT-TYPE
SYNTAX INTEGER
MAX-ACCESS read-write
STATUS current
DESCRIPTION
"Data value."
::= { dataArray18 364 }

dataValue18_365 OBJECT-TYPE
SYNTAX INTEGER
MAX-ACCESS read-write
STATUS current
DESCRIPTION
"Data value."
::= { dataArray18 365 }

dataValue18_366 OBJECT-TYPE
SYNTAX INTEGER
MAX-ACCESS read-write
STATUS current
DESCRIPTION
"Data value."
::= { dataArray18 366 }

dataValue18_367 OBJECT-TYPE
SYNTAX INTEGER
MAX-ACCESS read-write
STATUS current
DESCRIPTION
"Data value."
::= { dataArray18 367 }

dataValue18_368 OBJECT-TYPE
SYNTAX INTEGER
MAX-ACCESS read-write
STATUS current
DESCRIPTION
"Data value."
::= { dataArray18 368 }

dataValue18_369 OBJECT-TYPE
SYNTAX INTEGER
MAX-ACCESS read-write
STATUS current
DESCRIPTION
"Data value."
::= { dataArray18 369 }

dataValue18_370 OBJECT-TYPE
SYNTAX INTEGER
MAX-ACCESS read-write
STATUS current
DESCRIPTION
"Data value."
::= { dataArray18 370 }

dataValue18_371 OBJECT-TYPE
SYNTAX INTEGER
MAX-ACCESS read-write
STATUS current
DESCRIPTION
"Data value."
::= { dataArray18 371 }

dataValue18_372 OBJECT-TYPE
SYNTAX INTEGER
MAX-ACCESS read-write
STATUS current
DESCRIPTION
"Data value."
::= { dataArray18 372 }

dataValue18_373 OBJECT-TYPE
SYNTAX INTEGER
MAX-ACCESS read-write
STATUS current
DESCRIPTION
"Data value."
::= { dataArray18 373 }

dataValue18_374 OBJECT-TYPE
SYNTAX INTEGER
MAX-ACCESS read-write
STATUS current
DESCRIPTION
"Data value."
::= { dataArray18 374 }

dataValue18_375 OBJECT-TYPE
SYNTAX INTEGER
MAX-ACCESS read-write
STATUS current
DESCRIPTION
"Data value."
::= { dataArray18 375 }

dataValue18_376 OBJECT-TYPE
SYNTAX INTEGER
MAX-ACCESS read-write
STATUS current
DESCRIPTION
"Data value."
::= { dataArray18 376 }

dataValue18_377 OBJECT-TYPE
SYNTAX INTEGER
MAX-ACCESS read-write
STATUS current
DESCRIPTION
"Data value."
::= { dataArray18 377 }

dataValue18_378 OBJECT-TYPE
SYNTAX INTEGER
MAX-ACCESS read-write
STATUS current
DESCRIPTION
"Data value."
::= { dataArray18 378 }

dataValue18_379 OBJECT-TYPE
SYNTAX INTEGER
MAX-ACCESS read-write
STATUS current
DESCRIPTION
"Data value."
::= { dataArray18 379 }

dataValue18_380 OBJECT-TYPE
SYNTAX INTEGER
MAX-ACCESS read-write
STATUS current
DESCRIPTION
"Data value."
::= { dataArray18 380 }

dataValue18_381 OBJECT-TYPE
SYNTAX INTEGER
MAX-ACCESS read-write
STATUS current
DESCRIPTION
"Data value."
::= { dataArray18 381 }

dataValue18_382 OBJECT-TYPE
SYNTAX INTEGER
MAX-ACCESS read-write
STATUS current
DESCRIPTION
"Data value."
::= { dataArray18 382 }

dataValue18_383 OBJECT-TYPE
SYNTAX INTEGER
MAX-ACCESS read-write
STATUS current
DESCRIPTION
"Data value."
::= { dataArray18 383 }

dataValue18_384 OBJECT-TYPE
SYNTAX INTEGER
MAX-ACCESS read-write
STATUS current
DESCRIPTION
"Data value."
::= { dataArray18 384 }

dataValue18_385 OBJECT-TYPE
SYNTAX INTEGER
MAX-ACCESS read-write
STATUS current
DESCRIPTION
"Data value."
::= { dataArray18 385 }

dataValue18_386 OBJECT-TYPE
SYNTAX INTEGER
MAX-ACCESS read-write
STATUS current
DESCRIPTION
"Data value."
::= { dataArray18 386 }

dataValue18_387 OBJECT-TYPE
SYNTAX INTEGER
MAX-ACCESS read-write
STATUS current
DESCRIPTION
"Data value."
::= { dataArray18 387 }

dataValue18_388 OBJECT-TYPE
SYNTAX INTEGER
MAX-ACCESS read-write
STATUS current
DESCRIPTION
"Data value."
::= { dataArray18 388 }

dataValue18_389 OBJECT-TYPE
SYNTAX INTEGER
MAX-ACCESS read-write
STATUS current
DESCRIPTION
"Data value."
::= { dataArray18 389 }

dataValue18_390 OBJECT-TYPE
SYNTAX INTEGER
MAX-ACCESS read-write
STATUS current
DESCRIPTION
"Data value."
::= { dataArray18 390 }

dataValue18_391 OBJECT-TYPE
SYNTAX INTEGER
MAX-ACCESS read-write
STATUS current
DESCRIPTION
"Data value."
::= { dataArray18 391 }

dataValue18_392 OBJECT-TYPE
SYNTAX INTEGER
MAX-ACCESS read-write
STATUS current
DESCRIPTION
"Data value."
::= { dataArray18 392 }

dataValue18_393 OBJECT-TYPE
SYNTAX INTEGER
MAX-ACCESS read-write
STATUS current
DESCRIPTION
"Data value."
::= { dataArray18 393 }

dataValue18_394 OBJECT-TYPE
SYNTAX INTEGER
MAX-ACCESS read-write
STATUS current
DESCRIPTION
"Data value."
::= { dataArray18 394 }

dataValue18_395 OBJECT-TYPE
SYNTAX INTEGER
MAX-ACCESS read-write
STATUS current
DESCRIPTION
"Data value."
::= { dataArray18 395 }

dataValue18_396 OBJECT-TYPE
SYNTAX INTEGER
MAX-ACCESS read-write
STATUS current
DESCRIPTION
"Data value."
::= { dataArray18 396 }

dataValue18_397 OBJECT-TYPE
SYNTAX INTEGER
MAX-ACCESS read-write
STATUS current
DESCRIPTION
"Data value."
::= { dataArray18 397 }

dataValue18_398 OBJECT-TYPE
SYNTAX INTEGER
MAX-ACCESS read-write
STATUS current
DESCRIPTION
"Data value."
::= { dataArray18 398 }

dataValue18_399 OBJECT-TYPE
SYNTAX INTEGER
MAX-ACCESS read-write
STATUS current
DESCRIPTION
"Data value."
::= { dataArray18 399 }

dataArray19 OBJECT IDENTIFIER ::= { cc08255400_v1_00a 19 }

dataValue19_0 OBJECT-TYPE
SYNTAX INTEGER
MAX-ACCESS read-write
STATUS current
DESCRIPTION
"Data value."
::= { dataArray19 0 }

dataValue19_1 OBJECT-TYPE
SYNTAX INTEGER
MAX-ACCESS read-write
STATUS current
DESCRIPTION
"Data value."
::= { dataArray19 1 }

dataValue19_2 OBJECT-TYPE
SYNTAX INTEGER
MAX-ACCESS read-write
STATUS current
DESCRIPTION
"Data value."
::= { dataArray19 2 }

dataValue19_3 OBJECT-TYPE
SYNTAX INTEGER
MAX-ACCESS read-write
STATUS current
DESCRIPTION
"Data value."
::= { dataArray19 3 }

dataValue19_4 OBJECT-TYPE
SYNTAX INTEGER
MAX-ACCESS read-write
STATUS current
DESCRIPTION
"Data value."
::= { dataArray19 4 }

dataValue19_5 OBJECT-TYPE
SYNTAX INTEGER
MAX-ACCESS read-write
STATUS current
DESCRIPTION
"Data value."
::= { dataArray19 5 }

dataValue19_6 OBJECT-TYPE
SYNTAX INTEGER
MAX-ACCESS read-write
STATUS current
DESCRIPTION
"Data value."
::= { dataArray19 6 }

dataValue19_7 OBJECT-TYPE
SYNTAX INTEGER
MAX-ACCESS read-write
STATUS current
DESCRIPTION
"Data value."
::= { dataArray19 7 }

dataValue19_8 OBJECT-TYPE
SYNTAX INTEGER
MAX-ACCESS read-write
STATUS current
DESCRIPTION
"Data value."
::= { dataArray19 8 }

dataValue19_9 OBJECT-TYPE
SYNTAX INTEGER
MAX-ACCESS read-write
STATUS current
DESCRIPTION
"Data value."
::= { dataArray19 9 }

dataValue19_10 OBJECT-TYPE
SYNTAX INTEGER
MAX-ACCESS read-write
STATUS current
DESCRIPTION
"Data value."
::= { dataArray19 10 }

dataValue19_11 OBJECT-TYPE
SYNTAX INTEGER
MAX-ACCESS read-write
STATUS current
DESCRIPTION
"Data value."
::= { dataArray19 11 }

dataValue19_12 OBJECT-TYPE
SYNTAX INTEGER
MAX-ACCESS read-write
STATUS current
DESCRIPTION
"Data value."
::= { dataArray19 12 }

dataValue19_13 OBJECT-TYPE
SYNTAX INTEGER
MAX-ACCESS read-write
STATUS current
DESCRIPTION
"Data value."
::= { dataArray19 13 }

dataValue19_14 OBJECT-TYPE
SYNTAX INTEGER
MAX-ACCESS read-write
STATUS current
DESCRIPTION
"Data value."
::= { dataArray19 14 }

dataValue19_15 OBJECT-TYPE
SYNTAX INTEGER
MAX-ACCESS read-write
STATUS current
DESCRIPTION
"Data value."
::= { dataArray19 15 }

dataValue19_16 OBJECT-TYPE
SYNTAX INTEGER
MAX-ACCESS read-write
STATUS current
DESCRIPTION
"Data value."
::= { dataArray19 16 }

dataValue19_17 OBJECT-TYPE
SYNTAX INTEGER
MAX-ACCESS read-write
STATUS current
DESCRIPTION
"Data value."
::= { dataArray19 17 }

dataValue19_18 OBJECT-TYPE
SYNTAX INTEGER
MAX-ACCESS read-write
STATUS current
DESCRIPTION
"Data value."
::= { dataArray19 18 }

dataValue19_19 OBJECT-TYPE
SYNTAX INTEGER
MAX-ACCESS read-write
STATUS current
DESCRIPTION
"Data value."
::= { dataArray19 19 }

dataValue19_20 OBJECT-TYPE
SYNTAX INTEGER
MAX-ACCESS read-write
STATUS current
DESCRIPTION
"Data value."
::= { dataArray19 20 }

dataValue19_21 OBJECT-TYPE
SYNTAX INTEGER
MAX-ACCESS read-write
STATUS current
DESCRIPTION
"Data value."
::= { dataArray19 21 }

dataValue19_22 OBJECT-TYPE
SYNTAX INTEGER
MAX-ACCESS read-write
STATUS current
DESCRIPTION
"Data value."
::= { dataArray19 22 }

dataValue19_23 OBJECT-TYPE
SYNTAX INTEGER
MAX-ACCESS read-write
STATUS current
DESCRIPTION
"Data value."
::= { dataArray19 23 }

dataValue19_24 OBJECT-TYPE
SYNTAX INTEGER
MAX-ACCESS read-write
STATUS current
DESCRIPTION
"Data value."
::= { dataArray19 24 }

dataValue19_25 OBJECT-TYPE
SYNTAX INTEGER
MAX-ACCESS read-write
STATUS current
DESCRIPTION
"Data value."
::= { dataArray19 25 }

dataValue19_26 OBJECT-TYPE
SYNTAX INTEGER
MAX-ACCESS read-write
STATUS current
DESCRIPTION
"Data value."
::= { dataArray19 26 }

dataValue19_27 OBJECT-TYPE
SYNTAX INTEGER
MAX-ACCESS read-write
STATUS current
DESCRIPTION
"Data value."
::= { dataArray19 27 }

dataValue19_28 OBJECT-TYPE
SYNTAX INTEGER
MAX-ACCESS read-write
STATUS current
DESCRIPTION
"Data value."
::= { dataArray19 28 }

dataValue19_29 OBJECT-TYPE
SYNTAX INTEGER
MAX-ACCESS read-write
STATUS current
DESCRIPTION
"Data value."
::= { dataArray19 29 }

dataValue19_30 OBJECT-TYPE
SYNTAX INTEGER
MAX-ACCESS read-write
STATUS current
DESCRIPTION
"Data value."
::= { dataArray19 30 }

dataValue19_31 OBJECT-TYPE
SYNTAX INTEGER
MAX-ACCESS read-write
STATUS current
DESCRIPTION
"Data value."
::= { dataArray19 31 }

dataValue19_32 OBJECT-TYPE
SYNTAX INTEGER
MAX-ACCESS read-write
STATUS current
DESCRIPTION
"Data value."
::= { dataArray19 32 }

dataValue19_33 OBJECT-TYPE
SYNTAX INTEGER
MAX-ACCESS read-write
STATUS current
DESCRIPTION
"Data value."
::= { dataArray19 33 }

dataValue19_34 OBJECT-TYPE
SYNTAX INTEGER
MAX-ACCESS read-write
STATUS current
DESCRIPTION
"Data value."
::= { dataArray19 34 }

dataValue19_35 OBJECT-TYPE
SYNTAX INTEGER
MAX-ACCESS read-write
STATUS current
DESCRIPTION
"Data value."
::= { dataArray19 35 }

dataValue19_36 OBJECT-TYPE
SYNTAX INTEGER
MAX-ACCESS read-write
STATUS current
DESCRIPTION
"Data value."
::= { dataArray19 36 }

dataValue19_37 OBJECT-TYPE
SYNTAX INTEGER
MAX-ACCESS read-write
STATUS current
DESCRIPTION
"Data value."
::= { dataArray19 37 }

dataValue19_38 OBJECT-TYPE
SYNTAX INTEGER
MAX-ACCESS read-write
STATUS current
DESCRIPTION
"Data value."
::= { dataArray19 38 }

dataValue19_39 OBJECT-TYPE
SYNTAX INTEGER
MAX-ACCESS read-write
STATUS current
DESCRIPTION
"Data value."
::= { dataArray19 39 }

dataValue19_40 OBJECT-TYPE
SYNTAX INTEGER
MAX-ACCESS read-write
STATUS current
DESCRIPTION
"Data value."
::= { dataArray19 40 }

dataValue19_41 OBJECT-TYPE
SYNTAX INTEGER
MAX-ACCESS read-write
STATUS current
DESCRIPTION
"Data value."
::= { dataArray19 41 }

dataValue19_42 OBJECT-TYPE
SYNTAX INTEGER
MAX-ACCESS read-write
STATUS current
DESCRIPTION
"Data value."
::= { dataArray19 42 }

dataValue19_43 OBJECT-TYPE
SYNTAX INTEGER
MAX-ACCESS read-write
STATUS current
DESCRIPTION
"Data value."
::= { dataArray19 43 }

dataValue19_44 OBJECT-TYPE
SYNTAX INTEGER
MAX-ACCESS read-write
STATUS current
DESCRIPTION
"Data value."
::= { dataArray19 44 }

dataValue19_45 OBJECT-TYPE
SYNTAX INTEGER
MAX-ACCESS read-write
STATUS current
DESCRIPTION
"Data value."
::= { dataArray19 45 }

dataValue19_46 OBJECT-TYPE
SYNTAX INTEGER
MAX-ACCESS read-write
STATUS current
DESCRIPTION
"Data value."
::= { dataArray19 46 }

dataValue19_47 OBJECT-TYPE
SYNTAX INTEGER
MAX-ACCESS read-write
STATUS current
DESCRIPTION
"Data value."
::= { dataArray19 47 }

dataValue19_48 OBJECT-TYPE
SYNTAX INTEGER
MAX-ACCESS read-write
STATUS current
DESCRIPTION
"Data value."
::= { dataArray19 48 }

dataValue19_49 OBJECT-TYPE
SYNTAX INTEGER
MAX-ACCESS read-write
STATUS current
DESCRIPTION
"Data value."
::= { dataArray19 49 }

dataValue19_50 OBJECT-TYPE
SYNTAX INTEGER
MAX-ACCESS read-write
STATUS current
DESCRIPTION
"Data value."
::= { dataArray19 50 }

dataValue19_51 OBJECT-TYPE
SYNTAX INTEGER
MAX-ACCESS read-write
STATUS current
DESCRIPTION
"Data value."
::= { dataArray19 51 }

dataValue19_52 OBJECT-TYPE
SYNTAX INTEGER
MAX-ACCESS read-write
STATUS current
DESCRIPTION
"Data value."
::= { dataArray19 52 }

dataValue19_53 OBJECT-TYPE
SYNTAX INTEGER
MAX-ACCESS read-write
STATUS current
DESCRIPTION
"Data value."
::= { dataArray19 53 }

dataValue19_54 OBJECT-TYPE
SYNTAX INTEGER
MAX-ACCESS read-write
STATUS current
DESCRIPTION
"Data value."
::= { dataArray19 54 }

dataValue19_55 OBJECT-TYPE
SYNTAX INTEGER
MAX-ACCESS read-write
STATUS current
DESCRIPTION
"Data value."
::= { dataArray19 55 }

dataValue19_56 OBJECT-TYPE
SYNTAX INTEGER
MAX-ACCESS read-write
STATUS current
DESCRIPTION
"Data value."
::= { dataArray19 56 }

dataValue19_57 OBJECT-TYPE
SYNTAX INTEGER
MAX-ACCESS read-write
STATUS current
DESCRIPTION
"Data value."
::= { dataArray19 57 }

dataValue19_58 OBJECT-TYPE
SYNTAX INTEGER
MAX-ACCESS read-write
STATUS current
DESCRIPTION
"Data value."
::= { dataArray19 58 }

dataValue19_59 OBJECT-TYPE
SYNTAX INTEGER
MAX-ACCESS read-write
STATUS current
DESCRIPTION
"Data value."
::= { dataArray19 59 }

dataValue19_60 OBJECT-TYPE
SYNTAX INTEGER
MAX-ACCESS read-write
STATUS current
DESCRIPTION
"Data value."
::= { dataArray19 60 }

dataValue19_61 OBJECT-TYPE
SYNTAX INTEGER
MAX-ACCESS read-write
STATUS current
DESCRIPTION
"Data value."
::= { dataArray19 61 }

dataValue19_62 OBJECT-TYPE
SYNTAX INTEGER
MAX-ACCESS read-write
STATUS current
DESCRIPTION
"Data value."
::= { dataArray19 62 }

dataValue19_63 OBJECT-TYPE
SYNTAX INTEGER
MAX-ACCESS read-write
STATUS current
DESCRIPTION
"Data value."
::= { dataArray19 63 }

dataValue19_64 OBJECT-TYPE
SYNTAX INTEGER
MAX-ACCESS read-write
STATUS current
DESCRIPTION
"Data value."
::= { dataArray19 64 }

dataValue19_65 OBJECT-TYPE
SYNTAX INTEGER
MAX-ACCESS read-write
STATUS current
DESCRIPTION
"Data value."
::= { dataArray19 65 }

dataValue19_66 OBJECT-TYPE
SYNTAX INTEGER
MAX-ACCESS read-write
STATUS current
DESCRIPTION
"Data value."
::= { dataArray19 66 }

dataValue19_67 OBJECT-TYPE
SYNTAX INTEGER
MAX-ACCESS read-write
STATUS current
DESCRIPTION
"Data value."
::= { dataArray19 67 }

dataValue19_68 OBJECT-TYPE
SYNTAX INTEGER
MAX-ACCESS read-write
STATUS current
DESCRIPTION
"Data value."
::= { dataArray19 68 }

dataValue19_69 OBJECT-TYPE
SYNTAX INTEGER
MAX-ACCESS read-write
STATUS current
DESCRIPTION
"Data value."
::= { dataArray19 69 }

dataValue19_70 OBJECT-TYPE
SYNTAX INTEGER
MAX-ACCESS read-write
STATUS current
DESCRIPTION
"Data value."
::= { dataArray19 70 }

dataValue19_71 OBJECT-TYPE
SYNTAX INTEGER
MAX-ACCESS read-write
STATUS current
DESCRIPTION
"Data value."
::= { dataArray19 71 }

dataValue19_72 OBJECT-TYPE
SYNTAX INTEGER
MAX-ACCESS read-write
STATUS current
DESCRIPTION
"Data value."
::= { dataArray19 72 }

dataValue19_73 OBJECT-TYPE
SYNTAX INTEGER
MAX-ACCESS read-write
STATUS current
DESCRIPTION
"Data value."
::= { dataArray19 73 }

dataValue19_74 OBJECT-TYPE
SYNTAX INTEGER
MAX-ACCESS read-write
STATUS current
DESCRIPTION
"Data value."
::= { dataArray19 74 }

dataValue19_75 OBJECT-TYPE
SYNTAX INTEGER
MAX-ACCESS read-write
STATUS current
DESCRIPTION
"Data value."
::= { dataArray19 75 }

dataValue19_76 OBJECT-TYPE
SYNTAX INTEGER
MAX-ACCESS read-write
STATUS current
DESCRIPTION
"Data value."
::= { dataArray19 76 }

dataValue19_77 OBJECT-TYPE
SYNTAX INTEGER
MAX-ACCESS read-write
STATUS current
DESCRIPTION
"Data value."
::= { dataArray19 77 }

dataValue19_78 OBJECT-TYPE
SYNTAX INTEGER
MAX-ACCESS read-write
STATUS current
DESCRIPTION
"Data value."
::= { dataArray19 78 }

dataValue19_79 OBJECT-TYPE
SYNTAX INTEGER
MAX-ACCESS read-write
STATUS current
DESCRIPTION
"Data value."
::= { dataArray19 79 }

dataValue19_80 OBJECT-TYPE
SYNTAX INTEGER
MAX-ACCESS read-write
STATUS current
DESCRIPTION
"Data value."
::= { dataArray19 80 }

dataValue19_81 OBJECT-TYPE
SYNTAX INTEGER
MAX-ACCESS read-write
STATUS current
DESCRIPTION
"Data value."
::= { dataArray19 81 }

dataValue19_82 OBJECT-TYPE
SYNTAX INTEGER
MAX-ACCESS read-write
STATUS current
DESCRIPTION
"Data value."
::= { dataArray19 82 }

dataValue19_83 OBJECT-TYPE
SYNTAX INTEGER
MAX-ACCESS read-write
STATUS current
DESCRIPTION
"Data value."
::= { dataArray19 83 }

dataValue19_84 OBJECT-TYPE
SYNTAX INTEGER
MAX-ACCESS read-write
STATUS current
DESCRIPTION
"Data value."
::= { dataArray19 84 }

dataValue19_85 OBJECT-TYPE
SYNTAX INTEGER
MAX-ACCESS read-write
STATUS current
DESCRIPTION
"Data value."
::= { dataArray19 85 }

dataValue19_86 OBJECT-TYPE
SYNTAX INTEGER
MAX-ACCESS read-write
STATUS current
DESCRIPTION
"Data value."
::= { dataArray19 86 }

dataValue19_87 OBJECT-TYPE
SYNTAX INTEGER
MAX-ACCESS read-write
STATUS current
DESCRIPTION
"Data value."
::= { dataArray19 87 }

dataValue19_88 OBJECT-TYPE
SYNTAX INTEGER
MAX-ACCESS read-write
STATUS current
DESCRIPTION
"Data value."
::= { dataArray19 88 }

dataValue19_89 OBJECT-TYPE
SYNTAX INTEGER
MAX-ACCESS read-write
STATUS current
DESCRIPTION
"Data value."
::= { dataArray19 89 }

dataValue19_90 OBJECT-TYPE
SYNTAX INTEGER
MAX-ACCESS read-write
STATUS current
DESCRIPTION
"Data value."
::= { dataArray19 90 }

dataValue19_91 OBJECT-TYPE
SYNTAX INTEGER
MAX-ACCESS read-write
STATUS current
DESCRIPTION
"Data value."
::= { dataArray19 91 }

dataValue19_92 OBJECT-TYPE
SYNTAX INTEGER
MAX-ACCESS read-write
STATUS current
DESCRIPTION
"Data value."
::= { dataArray19 92 }

dataValue19_93 OBJECT-TYPE
SYNTAX INTEGER
MAX-ACCESS read-write
STATUS current
DESCRIPTION
"Data value."
::= { dataArray19 93 }

dataValue19_94 OBJECT-TYPE
SYNTAX INTEGER
MAX-ACCESS read-write
STATUS current
DESCRIPTION
"Data value."
::= { dataArray19 94 }

dataValue19_95 OBJECT-TYPE
SYNTAX INTEGER
MAX-ACCESS read-write
STATUS current
DESCRIPTION
"Data value."
::= { dataArray19 95 }

dataValue19_96 OBJECT-TYPE
SYNTAX INTEGER
MAX-ACCESS read-write
STATUS current
DESCRIPTION
"Data value."
::= { dataArray19 96 }

dataValue19_97 OBJECT-TYPE
SYNTAX INTEGER
MAX-ACCESS read-write
STATUS current
DESCRIPTION
"Data value."
::= { dataArray19 97 }

dataValue19_98 OBJECT-TYPE
SYNTAX INTEGER
MAX-ACCESS read-write
STATUS current
DESCRIPTION
"Data value."
::= { dataArray19 98 }

dataValue19_99 OBJECT-TYPE
SYNTAX INTEGER
MAX-ACCESS read-write
STATUS current
DESCRIPTION
"Data value."
::= { dataArray19 99 }

dataValue19_100 OBJECT-TYPE
SYNTAX INTEGER
MAX-ACCESS read-write
STATUS current
DESCRIPTION
"Data value."
::= { dataArray19 100 }

dataValue19_101 OBJECT-TYPE
SYNTAX INTEGER
MAX-ACCESS read-write
STATUS current
DESCRIPTION
"Data value."
::= { dataArray19 101 }

dataValue19_102 OBJECT-TYPE
SYNTAX INTEGER
MAX-ACCESS read-write
STATUS current
DESCRIPTION
"Data value."
::= { dataArray19 102 }

dataValue19_103 OBJECT-TYPE
SYNTAX INTEGER
MAX-ACCESS read-write
STATUS current
DESCRIPTION
"Data value."
::= { dataArray19 103 }

dataValue19_104 OBJECT-TYPE
SYNTAX INTEGER
MAX-ACCESS read-write
STATUS current
DESCRIPTION
"Data value."
::= { dataArray19 104 }

dataValue19_105 OBJECT-TYPE
SYNTAX INTEGER
MAX-ACCESS read-write
STATUS current
DESCRIPTION
"Data value."
::= { dataArray19 105 }

dataValue19_106 OBJECT-TYPE
SYNTAX INTEGER
MAX-ACCESS read-write
STATUS current
DESCRIPTION
"Data value."
::= { dataArray19 106 }

dataValue19_107 OBJECT-TYPE
SYNTAX INTEGER
MAX-ACCESS read-write
STATUS current
DESCRIPTION
"Data value."
::= { dataArray19 107 }

dataValue19_108 OBJECT-TYPE
SYNTAX INTEGER
MAX-ACCESS read-write
STATUS current
DESCRIPTION
"Data value."
::= { dataArray19 108 }

dataValue19_109 OBJECT-TYPE
SYNTAX INTEGER
MAX-ACCESS read-write
STATUS current
DESCRIPTION
"Data value."
::= { dataArray19 109 }

dataValue19_110 OBJECT-TYPE
SYNTAX INTEGER
MAX-ACCESS read-write
STATUS current
DESCRIPTION
"Data value."
::= { dataArray19 110 }

dataValue19_111 OBJECT-TYPE
SYNTAX INTEGER
MAX-ACCESS read-write
STATUS current
DESCRIPTION
"Data value."
::= { dataArray19 111 }

dataValue19_112 OBJECT-TYPE
SYNTAX INTEGER
MAX-ACCESS read-write
STATUS current
DESCRIPTION
"Data value."
::= { dataArray19 112 }

dataValue19_113 OBJECT-TYPE
SYNTAX INTEGER
MAX-ACCESS read-write
STATUS current
DESCRIPTION
"Data value."
::= { dataArray19 113 }

dataValue19_114 OBJECT-TYPE
SYNTAX INTEGER
MAX-ACCESS read-write
STATUS current
DESCRIPTION
"Data value."
::= { dataArray19 114 }

dataValue19_115 OBJECT-TYPE
SYNTAX INTEGER
MAX-ACCESS read-write
STATUS current
DESCRIPTION
"Data value."
::= { dataArray19 115 }

dataValue19_116 OBJECT-TYPE
SYNTAX INTEGER
MAX-ACCESS read-write
STATUS current
DESCRIPTION
"Data value."
::= { dataArray19 116 }

dataValue19_117 OBJECT-TYPE
SYNTAX INTEGER
MAX-ACCESS read-write
STATUS current
DESCRIPTION
"Data value."
::= { dataArray19 117 }

dataValue19_118 OBJECT-TYPE
SYNTAX INTEGER
MAX-ACCESS read-write
STATUS current
DESCRIPTION
"Data value."
::= { dataArray19 118 }

dataValue19_119 OBJECT-TYPE
SYNTAX INTEGER
MAX-ACCESS read-write
STATUS current
DESCRIPTION
"Data value."
::= { dataArray19 119 }

dataValue19_120 OBJECT-TYPE
SYNTAX INTEGER
MAX-ACCESS read-write
STATUS current
DESCRIPTION
"Data value."
::= { dataArray19 120 }

dataValue19_121 OBJECT-TYPE
SYNTAX INTEGER
MAX-ACCESS read-write
STATUS current
DESCRIPTION
"Data value."
::= { dataArray19 121 }

dataValue19_122 OBJECT-TYPE
SYNTAX INTEGER
MAX-ACCESS read-write
STATUS current
DESCRIPTION
"Data value."
::= { dataArray19 122 }

dataValue19_123 OBJECT-TYPE
SYNTAX INTEGER
MAX-ACCESS read-write
STATUS current
DESCRIPTION
"Data value."
::= { dataArray19 123 }

dataValue19_124 OBJECT-TYPE
SYNTAX INTEGER
MAX-ACCESS read-write
STATUS current
DESCRIPTION
"Data value."
::= { dataArray19 124 }

dataValue19_125 OBJECT-TYPE
SYNTAX INTEGER
MAX-ACCESS read-write
STATUS current
DESCRIPTION
"Data value."
::= { dataArray19 125 }

dataValue19_126 OBJECT-TYPE
SYNTAX INTEGER
MAX-ACCESS read-write
STATUS current
DESCRIPTION
"Data value."
::= { dataArray19 126 }

dataValue19_127 OBJECT-TYPE
SYNTAX INTEGER
MAX-ACCESS read-write
STATUS current
DESCRIPTION
"Data value."
::= { dataArray19 127 }

dataValue19_128 OBJECT-TYPE
SYNTAX INTEGER
MAX-ACCESS read-write
STATUS current
DESCRIPTION
"Data value."
::= { dataArray19 128 }

dataValue19_129 OBJECT-TYPE
SYNTAX INTEGER
MAX-ACCESS read-write
STATUS current
DESCRIPTION
"Data value."
::= { dataArray19 129 }

dataValue19_130 OBJECT-TYPE
SYNTAX INTEGER
MAX-ACCESS read-write
STATUS current
DESCRIPTION
"Data value."
::= { dataArray19 130 }

dataValue19_131 OBJECT-TYPE
SYNTAX INTEGER
MAX-ACCESS read-write
STATUS current
DESCRIPTION
"Data value."
::= { dataArray19 131 }

dataValue19_132 OBJECT-TYPE
SYNTAX INTEGER
MAX-ACCESS read-write
STATUS current
DESCRIPTION
"Data value."
::= { dataArray19 132 }

dataValue19_133 OBJECT-TYPE
SYNTAX INTEGER
MAX-ACCESS read-write
STATUS current
DESCRIPTION
"Data value."
::= { dataArray19 133 }

dataValue19_134 OBJECT-TYPE
SYNTAX INTEGER
MAX-ACCESS read-write
STATUS current
DESCRIPTION
"Data value."
::= { dataArray19 134 }

dataValue19_135 OBJECT-TYPE
SYNTAX INTEGER
MAX-ACCESS read-write
STATUS current
DESCRIPTION
"Data value."
::= { dataArray19 135 }

dataValue19_136 OBJECT-TYPE
SYNTAX INTEGER
MAX-ACCESS read-write
STATUS current
DESCRIPTION
"Data value."
::= { dataArray19 136 }

dataValue19_137 OBJECT-TYPE
SYNTAX INTEGER
MAX-ACCESS read-write
STATUS current
DESCRIPTION
"Data value."
::= { dataArray19 137 }

dataValue19_138 OBJECT-TYPE
SYNTAX INTEGER
MAX-ACCESS read-write
STATUS current
DESCRIPTION
"Data value."
::= { dataArray19 138 }

dataValue19_139 OBJECT-TYPE
SYNTAX INTEGER
MAX-ACCESS read-write
STATUS current
DESCRIPTION
"Data value."
::= { dataArray19 139 }

dataValue19_140 OBJECT-TYPE
SYNTAX INTEGER
MAX-ACCESS read-write
STATUS current
DESCRIPTION
"Data value."
::= { dataArray19 140 }

dataValue19_141 OBJECT-TYPE
SYNTAX INTEGER
MAX-ACCESS read-write
STATUS current
DESCRIPTION
"Data value."
::= { dataArray19 141 }

dataValue19_142 OBJECT-TYPE
SYNTAX INTEGER
MAX-ACCESS read-write
STATUS current
DESCRIPTION
"Data value."
::= { dataArray19 142 }

dataValue19_143 OBJECT-TYPE
SYNTAX INTEGER
MAX-ACCESS read-write
STATUS current
DESCRIPTION
"Data value."
::= { dataArray19 143 }

dataValue19_144 OBJECT-TYPE
SYNTAX INTEGER
MAX-ACCESS read-write
STATUS current
DESCRIPTION
"Data value."
::= { dataArray19 144 }

dataValue19_145 OBJECT-TYPE
SYNTAX INTEGER
MAX-ACCESS read-write
STATUS current
DESCRIPTION
"Data value."
::= { dataArray19 145 }

dataValue19_146 OBJECT-TYPE
SYNTAX INTEGER
MAX-ACCESS read-write
STATUS current
DESCRIPTION
"Data value."
::= { dataArray19 146 }

dataValue19_147 OBJECT-TYPE
SYNTAX INTEGER
MAX-ACCESS read-write
STATUS current
DESCRIPTION
"Data value."
::= { dataArray19 147 }

dataValue19_148 OBJECT-TYPE
SYNTAX INTEGER
MAX-ACCESS read-write
STATUS current
DESCRIPTION
"Data value."
::= { dataArray19 148 }

dataValue19_149 OBJECT-TYPE
SYNTAX INTEGER
MAX-ACCESS read-write
STATUS current
DESCRIPTION
"Data value."
::= { dataArray19 149 }

dataValue19_150 OBJECT-TYPE
SYNTAX INTEGER
MAX-ACCESS read-write
STATUS current
DESCRIPTION
"Data value."
::= { dataArray19 150 }

dataValue19_151 OBJECT-TYPE
SYNTAX INTEGER
MAX-ACCESS read-write
STATUS current
DESCRIPTION
"Data value."
::= { dataArray19 151 }

dataValue19_152 OBJECT-TYPE
SYNTAX INTEGER
MAX-ACCESS read-write
STATUS current
DESCRIPTION
"Data value."
::= { dataArray19 152 }

dataValue19_153 OBJECT-TYPE
SYNTAX INTEGER
MAX-ACCESS read-write
STATUS current
DESCRIPTION
"Data value."
::= { dataArray19 153 }

dataValue19_154 OBJECT-TYPE
SYNTAX INTEGER
MAX-ACCESS read-write
STATUS current
DESCRIPTION
"Data value."
::= { dataArray19 154 }

dataValue19_155 OBJECT-TYPE
SYNTAX INTEGER
MAX-ACCESS read-write
STATUS current
DESCRIPTION
"Data value."
::= { dataArray19 155 }

dataValue19_156 OBJECT-TYPE
SYNTAX INTEGER
MAX-ACCESS read-write
STATUS current
DESCRIPTION
"Data value."
::= { dataArray19 156 }

dataValue19_157 OBJECT-TYPE
SYNTAX INTEGER
MAX-ACCESS read-write
STATUS current
DESCRIPTION
"Data value."
::= { dataArray19 157 }

dataValue19_158 OBJECT-TYPE
SYNTAX INTEGER
MAX-ACCESS read-write
STATUS current
DESCRIPTION
"Data value."
::= { dataArray19 158 }

dataValue19_159 OBJECT-TYPE
SYNTAX INTEGER
MAX-ACCESS read-write
STATUS current
DESCRIPTION
"Data value."
::= { dataArray19 159 }

dataValue19_160 OBJECT-TYPE
SYNTAX INTEGER
MAX-ACCESS read-write
STATUS current
DESCRIPTION
"Data value."
::= { dataArray19 160 }

dataValue19_161 OBJECT-TYPE
SYNTAX INTEGER
MAX-ACCESS read-write
STATUS current
DESCRIPTION
"Data value."
::= { dataArray19 161 }

dataValue19_162 OBJECT-TYPE
SYNTAX INTEGER
MAX-ACCESS read-write
STATUS current
DESCRIPTION
"Data value."
::= { dataArray19 162 }

dataValue19_163 OBJECT-TYPE
SYNTAX INTEGER
MAX-ACCESS read-write
STATUS current
DESCRIPTION
"Data value."
::= { dataArray19 163 }

dataValue19_164 OBJECT-TYPE
SYNTAX INTEGER
MAX-ACCESS read-write
STATUS current
DESCRIPTION
"Data value."
::= { dataArray19 164 }

dataValue19_165 OBJECT-TYPE
SYNTAX INTEGER
MAX-ACCESS read-write
STATUS current
DESCRIPTION
"Data value."
::= { dataArray19 165 }

dataValue19_166 OBJECT-TYPE
SYNTAX INTEGER
MAX-ACCESS read-write
STATUS current
DESCRIPTION
"Data value."
::= { dataArray19 166 }

dataValue19_167 OBJECT-TYPE
SYNTAX INTEGER
MAX-ACCESS read-write
STATUS current
DESCRIPTION
"Data value."
::= { dataArray19 167 }

dataValue19_168 OBJECT-TYPE
SYNTAX INTEGER
MAX-ACCESS read-write
STATUS current
DESCRIPTION
"Data value."
::= { dataArray19 168 }

dataValue19_169 OBJECT-TYPE
SYNTAX INTEGER
MAX-ACCESS read-write
STATUS current
DESCRIPTION
"Data value."
::= { dataArray19 169 }

dataValue19_170 OBJECT-TYPE
SYNTAX INTEGER
MAX-ACCESS read-write
STATUS current
DESCRIPTION
"Data value."
::= { dataArray19 170 }

dataValue19_171 OBJECT-TYPE
SYNTAX INTEGER
MAX-ACCESS read-write
STATUS current
DESCRIPTION
"Data value."
::= { dataArray19 171 }

dataValue19_172 OBJECT-TYPE
SYNTAX INTEGER
MAX-ACCESS read-write
STATUS current
DESCRIPTION
"Data value."
::= { dataArray19 172 }

dataValue19_173 OBJECT-TYPE
SYNTAX INTEGER
MAX-ACCESS read-write
STATUS current
DESCRIPTION
"Data value."
::= { dataArray19 173 }

dataValue19_174 OBJECT-TYPE
SYNTAX INTEGER
MAX-ACCESS read-write
STATUS current
DESCRIPTION
"Data value."
::= { dataArray19 174 }

dataValue19_175 OBJECT-TYPE
SYNTAX INTEGER
MAX-ACCESS read-write
STATUS current
DESCRIPTION
"Data value."
::= { dataArray19 175 }

dataValue19_176 OBJECT-TYPE
SYNTAX INTEGER
MAX-ACCESS read-write
STATUS current
DESCRIPTION
"Data value."
::= { dataArray19 176 }

dataValue19_177 OBJECT-TYPE
SYNTAX INTEGER
MAX-ACCESS read-write
STATUS current
DESCRIPTION
"Data value."
::= { dataArray19 177 }

dataValue19_178 OBJECT-TYPE
SYNTAX INTEGER
MAX-ACCESS read-write
STATUS current
DESCRIPTION
"Data value."
::= { dataArray19 178 }

dataValue19_179 OBJECT-TYPE
SYNTAX INTEGER
MAX-ACCESS read-write
STATUS current
DESCRIPTION
"Data value."
::= { dataArray19 179 }

dataValue19_180 OBJECT-TYPE
SYNTAX INTEGER
MAX-ACCESS read-write
STATUS current
DESCRIPTION
"Data value."
::= { dataArray19 180 }

dataValue19_181 OBJECT-TYPE
SYNTAX INTEGER
MAX-ACCESS read-write
STATUS current
DESCRIPTION
"Data value."
::= { dataArray19 181 }

dataValue19_182 OBJECT-TYPE
SYNTAX INTEGER
MAX-ACCESS read-write
STATUS current
DESCRIPTION
"Data value."
::= { dataArray19 182 }

dataValue19_183 OBJECT-TYPE
SYNTAX INTEGER
MAX-ACCESS read-write
STATUS current
DESCRIPTION
"Data value."
::= { dataArray19 183 }

dataValue19_184 OBJECT-TYPE
SYNTAX INTEGER
MAX-ACCESS read-write
STATUS current
DESCRIPTION
"Data value."
::= { dataArray19 184 }

dataValue19_185 OBJECT-TYPE
SYNTAX INTEGER
MAX-ACCESS read-write
STATUS current
DESCRIPTION
"Data value."
::= { dataArray19 185 }

dataValue19_186 OBJECT-TYPE
SYNTAX INTEGER
MAX-ACCESS read-write
STATUS current
DESCRIPTION
"Data value."
::= { dataArray19 186 }

dataValue19_187 OBJECT-TYPE
SYNTAX INTEGER
MAX-ACCESS read-write
STATUS current
DESCRIPTION
"Data value."
::= { dataArray19 187 }

dataValue19_188 OBJECT-TYPE
SYNTAX INTEGER
MAX-ACCESS read-write
STATUS current
DESCRIPTION
"Data value."
::= { dataArray19 188 }

dataValue19_189 OBJECT-TYPE
SYNTAX INTEGER
MAX-ACCESS read-write
STATUS current
DESCRIPTION
"Data value."
::= { dataArray19 189 }

dataValue19_190 OBJECT-TYPE
SYNTAX INTEGER
MAX-ACCESS read-write
STATUS current
DESCRIPTION
"Data value."
::= { dataArray19 190 }

dataValue19_191 OBJECT-TYPE
SYNTAX INTEGER
MAX-ACCESS read-write
STATUS current
DESCRIPTION
"Data value."
::= { dataArray19 191 }

dataValue19_192 OBJECT-TYPE
SYNTAX INTEGER
MAX-ACCESS read-write
STATUS current
DESCRIPTION
"Data value."
::= { dataArray19 192 }

dataValue19_193 OBJECT-TYPE
SYNTAX INTEGER
MAX-ACCESS read-write
STATUS current
DESCRIPTION
"Data value."
::= { dataArray19 193 }

dataValue19_194 OBJECT-TYPE
SYNTAX INTEGER
MAX-ACCESS read-write
STATUS current
DESCRIPTION
"Data value."
::= { dataArray19 194 }

dataValue19_195 OBJECT-TYPE
SYNTAX INTEGER
MAX-ACCESS read-write
STATUS current
DESCRIPTION
"Data value."
::= { dataArray19 195 }

dataValue19_196 OBJECT-TYPE
SYNTAX INTEGER
MAX-ACCESS read-write
STATUS current
DESCRIPTION
"Data value."
::= { dataArray19 196 }

dataValue19_197 OBJECT-TYPE
SYNTAX INTEGER
MAX-ACCESS read-write
STATUS current
DESCRIPTION
"Data value."
::= { dataArray19 197 }

dataValue19_198 OBJECT-TYPE
SYNTAX INTEGER
MAX-ACCESS read-write
STATUS current
DESCRIPTION
"Data value."
::= { dataArray19 198 }

dataValue19_199 OBJECT-TYPE
SYNTAX INTEGER
MAX-ACCESS read-write
STATUS current
DESCRIPTION
"Data value."
::= { dataArray19 199 }

dataValue19_200 OBJECT-TYPE
SYNTAX INTEGER
MAX-ACCESS read-write
STATUS current
DESCRIPTION
"Data value."
::= { dataArray19 200 }

dataValue19_201 OBJECT-TYPE
SYNTAX INTEGER
MAX-ACCESS read-write
STATUS current
DESCRIPTION
"Data value."
::= { dataArray19 201 }

dataValue19_202 OBJECT-TYPE
SYNTAX INTEGER
MAX-ACCESS read-write
STATUS current
DESCRIPTION
"Data value."
::= { dataArray19 202 }

dataValue19_203 OBJECT-TYPE
SYNTAX INTEGER
MAX-ACCESS read-write
STATUS current
DESCRIPTION
"Data value."
::= { dataArray19 203 }

dataValue19_204 OBJECT-TYPE
SYNTAX INTEGER
MAX-ACCESS read-write
STATUS current
DESCRIPTION
"Data value."
::= { dataArray19 204 }

dataValue19_205 OBJECT-TYPE
SYNTAX INTEGER
MAX-ACCESS read-write
STATUS current
DESCRIPTION
"Data value."
::= { dataArray19 205 }

dataValue19_206 OBJECT-TYPE
SYNTAX INTEGER
MAX-ACCESS read-write
STATUS current
DESCRIPTION
"Data value."
::= { dataArray19 206 }

dataValue19_207 OBJECT-TYPE
SYNTAX INTEGER
MAX-ACCESS read-write
STATUS current
DESCRIPTION
"Data value."
::= { dataArray19 207 }

dataValue19_208 OBJECT-TYPE
SYNTAX INTEGER
MAX-ACCESS read-write
STATUS current
DESCRIPTION
"Data value."
::= { dataArray19 208 }

dataValue19_209 OBJECT-TYPE
SYNTAX INTEGER
MAX-ACCESS read-write
STATUS current
DESCRIPTION
"Data value."
::= { dataArray19 209 }

dataValue19_210 OBJECT-TYPE
SYNTAX INTEGER
MAX-ACCESS read-write
STATUS current
DESCRIPTION
"Data value."
::= { dataArray19 210 }

dataValue19_211 OBJECT-TYPE
SYNTAX INTEGER
MAX-ACCESS read-write
STATUS current
DESCRIPTION
"Data value."
::= { dataArray19 211 }

dataValue19_212 OBJECT-TYPE
SYNTAX INTEGER
MAX-ACCESS read-write
STATUS current
DESCRIPTION
"Data value."
::= { dataArray19 212 }

dataValue19_213 OBJECT-TYPE
SYNTAX INTEGER
MAX-ACCESS read-write
STATUS current
DESCRIPTION
"Data value."
::= { dataArray19 213 }

dataValue19_214 OBJECT-TYPE
SYNTAX INTEGER
MAX-ACCESS read-write
STATUS current
DESCRIPTION
"Data value."
::= { dataArray19 214 }

dataValue19_215 OBJECT-TYPE
SYNTAX INTEGER
MAX-ACCESS read-write
STATUS current
DESCRIPTION
"Data value."
::= { dataArray19 215 }

dataValue19_216 OBJECT-TYPE
SYNTAX INTEGER
MAX-ACCESS read-write
STATUS current
DESCRIPTION
"Data value."
::= { dataArray19 216 }

dataValue19_217 OBJECT-TYPE
SYNTAX INTEGER
MAX-ACCESS read-write
STATUS current
DESCRIPTION
"Data value."
::= { dataArray19 217 }

dataValue19_218 OBJECT-TYPE
SYNTAX INTEGER
MAX-ACCESS read-write
STATUS current
DESCRIPTION
"Data value."
::= { dataArray19 218 }

dataValue19_219 OBJECT-TYPE
SYNTAX INTEGER
MAX-ACCESS read-write
STATUS current
DESCRIPTION
"Data value."
::= { dataArray19 219 }

dataValue19_220 OBJECT-TYPE
SYNTAX INTEGER
MAX-ACCESS read-write
STATUS current
DESCRIPTION
"Data value."
::= { dataArray19 220 }

dataValue19_221 OBJECT-TYPE
SYNTAX INTEGER
MAX-ACCESS read-write
STATUS current
DESCRIPTION
"Data value."
::= { dataArray19 221 }

dataValue19_222 OBJECT-TYPE
SYNTAX INTEGER
MAX-ACCESS read-write
STATUS current
DESCRIPTION
"Data value."
::= { dataArray19 222 }

dataValue19_223 OBJECT-TYPE
SYNTAX INTEGER
MAX-ACCESS read-write
STATUS current
DESCRIPTION
"Data value."
::= { dataArray19 223 }

dataValue19_224 OBJECT-TYPE
SYNTAX INTEGER
MAX-ACCESS read-write
STATUS current
DESCRIPTION
"Data value."
::= { dataArray19 224 }

dataValue19_225 OBJECT-TYPE
SYNTAX INTEGER
MAX-ACCESS read-write
STATUS current
DESCRIPTION
"Data value."
::= { dataArray19 225 }

dataValue19_226 OBJECT-TYPE
SYNTAX INTEGER
MAX-ACCESS read-write
STATUS current
DESCRIPTION
"Data value."
::= { dataArray19 226 }

dataValue19_227 OBJECT-TYPE
SYNTAX INTEGER
MAX-ACCESS read-write
STATUS current
DESCRIPTION
"Data value."
::= { dataArray19 227 }

dataValue19_228 OBJECT-TYPE
SYNTAX INTEGER
MAX-ACCESS read-write
STATUS current
DESCRIPTION
"Data value."
::= { dataArray19 228 }

dataValue19_229 OBJECT-TYPE
SYNTAX INTEGER
MAX-ACCESS read-write
STATUS current
DESCRIPTION
"Data value."
::= { dataArray19 229 }

dataValue19_230 OBJECT-TYPE
SYNTAX INTEGER
MAX-ACCESS read-write
STATUS current
DESCRIPTION
"Data value."
::= { dataArray19 230 }

dataValue19_231 OBJECT-TYPE
SYNTAX INTEGER
MAX-ACCESS read-write
STATUS current
DESCRIPTION
"Data value."
::= { dataArray19 231 }

dataValue19_232 OBJECT-TYPE
SYNTAX INTEGER
MAX-ACCESS read-write
STATUS current
DESCRIPTION
"Data value."
::= { dataArray19 232 }

dataValue19_233 OBJECT-TYPE
SYNTAX INTEGER
MAX-ACCESS read-write
STATUS current
DESCRIPTION
"Data value."
::= { dataArray19 233 }

dataValue19_234 OBJECT-TYPE
SYNTAX INTEGER
MAX-ACCESS read-write
STATUS current
DESCRIPTION
"Data value."
::= { dataArray19 234 }

dataValue19_235 OBJECT-TYPE
SYNTAX INTEGER
MAX-ACCESS read-write
STATUS current
DESCRIPTION
"Data value."
::= { dataArray19 235 }

dataValue19_236 OBJECT-TYPE
SYNTAX INTEGER
MAX-ACCESS read-write
STATUS current
DESCRIPTION
"Data value."
::= { dataArray19 236 }

dataValue19_237 OBJECT-TYPE
SYNTAX INTEGER
MAX-ACCESS read-write
STATUS current
DESCRIPTION
"Data value."
::= { dataArray19 237 }

dataValue19_238 OBJECT-TYPE
SYNTAX INTEGER
MAX-ACCESS read-write
STATUS current
DESCRIPTION
"Data value."
::= { dataArray19 238 }

dataValue19_239 OBJECT-TYPE
SYNTAX INTEGER
MAX-ACCESS read-write
STATUS current
DESCRIPTION
"Data value."
::= { dataArray19 239 }

dataValue19_240 OBJECT-TYPE
SYNTAX INTEGER
MAX-ACCESS read-write
STATUS current
DESCRIPTION
"Data value."
::= { dataArray19 240 }

dataValue19_241 OBJECT-TYPE
SYNTAX INTEGER
MAX-ACCESS read-write
STATUS current
DESCRIPTION
"Data value."
::= { dataArray19 241 }

dataValue19_242 OBJECT-TYPE
SYNTAX INTEGER
MAX-ACCESS read-write
STATUS current
DESCRIPTION
"Data value."
::= { dataArray19 242 }

dataValue19_243 OBJECT-TYPE
SYNTAX INTEGER
MAX-ACCESS read-write
STATUS current
DESCRIPTION
"Data value."
::= { dataArray19 243 }

dataValue19_244 OBJECT-TYPE
SYNTAX INTEGER
MAX-ACCESS read-write
STATUS current
DESCRIPTION
"Data value."
::= { dataArray19 244 }

dataValue19_245 OBJECT-TYPE
SYNTAX INTEGER
MAX-ACCESS read-write
STATUS current
DESCRIPTION
"Data value."
::= { dataArray19 245 }

dataValue19_246 OBJECT-TYPE
SYNTAX INTEGER
MAX-ACCESS read-write
STATUS current
DESCRIPTION
"Data value."
::= { dataArray19 246 }

dataValue19_247 OBJECT-TYPE
SYNTAX INTEGER
MAX-ACCESS read-write
STATUS current
DESCRIPTION
"Data value."
::= { dataArray19 247 }

dataValue19_248 OBJECT-TYPE
SYNTAX INTEGER
MAX-ACCESS read-write
STATUS current
DESCRIPTION
"Data value."
::= { dataArray19 248 }

dataValue19_249 OBJECT-TYPE
SYNTAX INTEGER
MAX-ACCESS read-write
STATUS current
DESCRIPTION
"Data value."
::= { dataArray19 249 }

dataValue19_250 OBJECT-TYPE
SYNTAX INTEGER
MAX-ACCESS read-write
STATUS current
DESCRIPTION
"Data value."
::= { dataArray19 250 }

dataValue19_251 OBJECT-TYPE
SYNTAX INTEGER
MAX-ACCESS read-write
STATUS current
DESCRIPTION
"Data value."
::= { dataArray19 251 }

dataValue19_252 OBJECT-TYPE
SYNTAX INTEGER
MAX-ACCESS read-write
STATUS current
DESCRIPTION
"Data value."
::= { dataArray19 252 }

dataValue19_253 OBJECT-TYPE
SYNTAX INTEGER
MAX-ACCESS read-write
STATUS current
DESCRIPTION
"Data value."
::= { dataArray19 253 }

dataValue19_254 OBJECT-TYPE
SYNTAX INTEGER
MAX-ACCESS read-write
STATUS current
DESCRIPTION
"Data value."
::= { dataArray19 254 }

dataValue19_255 OBJECT-TYPE
SYNTAX INTEGER
MAX-ACCESS read-write
STATUS current
DESCRIPTION
"Data value."
::= { dataArray19 255 }

dataValue19_256 OBJECT-TYPE
SYNTAX INTEGER
MAX-ACCESS read-write
STATUS current
DESCRIPTION
"Data value."
::= { dataArray19 256 }

dataValue19_257 OBJECT-TYPE
SYNTAX INTEGER
MAX-ACCESS read-write
STATUS current
DESCRIPTION
"Data value."
::= { dataArray19 257 }

dataValue19_258 OBJECT-TYPE
SYNTAX INTEGER
MAX-ACCESS read-write
STATUS current
DESCRIPTION
"Data value."
::= { dataArray19 258 }

dataValue19_259 OBJECT-TYPE
SYNTAX INTEGER
MAX-ACCESS read-write
STATUS current
DESCRIPTION
"Data value."
::= { dataArray19 259 }

dataValue19_260 OBJECT-TYPE
SYNTAX INTEGER
MAX-ACCESS read-write
STATUS current
DESCRIPTION
"Data value."
::= { dataArray19 260 }

dataValue19_261 OBJECT-TYPE
SYNTAX INTEGER
MAX-ACCESS read-write
STATUS current
DESCRIPTION
"Data value."
::= { dataArray19 261 }

dataValue19_262 OBJECT-TYPE
SYNTAX INTEGER
MAX-ACCESS read-write
STATUS current
DESCRIPTION
"Data value."
::= { dataArray19 262 }

dataValue19_263 OBJECT-TYPE
SYNTAX INTEGER
MAX-ACCESS read-write
STATUS current
DESCRIPTION
"Data value."
::= { dataArray19 263 }

dataValue19_264 OBJECT-TYPE
SYNTAX INTEGER
MAX-ACCESS read-write
STATUS current
DESCRIPTION
"Data value."
::= { dataArray19 264 }

dataValue19_265 OBJECT-TYPE
SYNTAX INTEGER
MAX-ACCESS read-write
STATUS current
DESCRIPTION
"Data value."
::= { dataArray19 265 }

dataValue19_266 OBJECT-TYPE
SYNTAX INTEGER
MAX-ACCESS read-write
STATUS current
DESCRIPTION
"Data value."
::= { dataArray19 266 }

dataValue19_267 OBJECT-TYPE
SYNTAX INTEGER
MAX-ACCESS read-write
STATUS current
DESCRIPTION
"Data value."
::= { dataArray19 267 }

dataValue19_268 OBJECT-TYPE
SYNTAX INTEGER
MAX-ACCESS read-write
STATUS current
DESCRIPTION
"Data value."
::= { dataArray19 268 }

dataValue19_269 OBJECT-TYPE
SYNTAX INTEGER
MAX-ACCESS read-write
STATUS current
DESCRIPTION
"Data value."
::= { dataArray19 269 }

dataValue19_270 OBJECT-TYPE
SYNTAX INTEGER
MAX-ACCESS read-write
STATUS current
DESCRIPTION
"Data value."
::= { dataArray19 270 }

dataValue19_271 OBJECT-TYPE
SYNTAX INTEGER
MAX-ACCESS read-write
STATUS current
DESCRIPTION
"Data value."
::= { dataArray19 271 }

dataValue19_272 OBJECT-TYPE
SYNTAX INTEGER
MAX-ACCESS read-write
STATUS current
DESCRIPTION
"Data value."
::= { dataArray19 272 }

dataValue19_273 OBJECT-TYPE
SYNTAX INTEGER
MAX-ACCESS read-write
STATUS current
DESCRIPTION
"Data value."
::= { dataArray19 273 }

dataValue19_274 OBJECT-TYPE
SYNTAX INTEGER
MAX-ACCESS read-write
STATUS current
DESCRIPTION
"Data value."
::= { dataArray19 274 }

dataValue19_275 OBJECT-TYPE
SYNTAX INTEGER
MAX-ACCESS read-write
STATUS current
DESCRIPTION
"Data value."
::= { dataArray19 275 }

dataValue19_276 OBJECT-TYPE
SYNTAX INTEGER
MAX-ACCESS read-write
STATUS current
DESCRIPTION
"Data value."
::= { dataArray19 276 }

dataValue19_277 OBJECT-TYPE
SYNTAX INTEGER
MAX-ACCESS read-write
STATUS current
DESCRIPTION
"Data value."
::= { dataArray19 277 }

dataValue19_278 OBJECT-TYPE
SYNTAX INTEGER
MAX-ACCESS read-write
STATUS current
DESCRIPTION
"Data value."
::= { dataArray19 278 }

dataValue19_279 OBJECT-TYPE
SYNTAX INTEGER
MAX-ACCESS read-write
STATUS current
DESCRIPTION
"Data value."
::= { dataArray19 279 }

dataValue19_280 OBJECT-TYPE
SYNTAX INTEGER
MAX-ACCESS read-write
STATUS current
DESCRIPTION
"Data value."
::= { dataArray19 280 }

dataValue19_281 OBJECT-TYPE
SYNTAX INTEGER
MAX-ACCESS read-write
STATUS current
DESCRIPTION
"Data value."
::= { dataArray19 281 }

dataValue19_282 OBJECT-TYPE
SYNTAX INTEGER
MAX-ACCESS read-write
STATUS current
DESCRIPTION
"Data value."
::= { dataArray19 282 }

dataValue19_283 OBJECT-TYPE
SYNTAX INTEGER
MAX-ACCESS read-write
STATUS current
DESCRIPTION
"Data value."
::= { dataArray19 283 }

dataValue19_284 OBJECT-TYPE
SYNTAX INTEGER
MAX-ACCESS read-write
STATUS current
DESCRIPTION
"Data value."
::= { dataArray19 284 }

dataValue19_285 OBJECT-TYPE
SYNTAX INTEGER
MAX-ACCESS read-write
STATUS current
DESCRIPTION
"Data value."
::= { dataArray19 285 }

dataValue19_286 OBJECT-TYPE
SYNTAX INTEGER
MAX-ACCESS read-write
STATUS current
DESCRIPTION
"Data value."
::= { dataArray19 286 }

dataValue19_287 OBJECT-TYPE
SYNTAX INTEGER
MAX-ACCESS read-write
STATUS current
DESCRIPTION
"Data value."
::= { dataArray19 287 }

dataValue19_288 OBJECT-TYPE
SYNTAX INTEGER
MAX-ACCESS read-write
STATUS current
DESCRIPTION
"Data value."
::= { dataArray19 288 }

dataValue19_289 OBJECT-TYPE
SYNTAX INTEGER
MAX-ACCESS read-write
STATUS current
DESCRIPTION
"Data value."
::= { dataArray19 289 }

dataValue19_290 OBJECT-TYPE
SYNTAX INTEGER
MAX-ACCESS read-write
STATUS current
DESCRIPTION
"Data value."
::= { dataArray19 290 }

dataValue19_291 OBJECT-TYPE
SYNTAX INTEGER
MAX-ACCESS read-write
STATUS current
DESCRIPTION
"Data value."
::= { dataArray19 291 }

dataValue19_292 OBJECT-TYPE
SYNTAX INTEGER
MAX-ACCESS read-write
STATUS current
DESCRIPTION
"Data value."
::= { dataArray19 292 }

dataValue19_293 OBJECT-TYPE
SYNTAX INTEGER
MAX-ACCESS read-write
STATUS current
DESCRIPTION
"Data value."
::= { dataArray19 293 }

dataValue19_294 OBJECT-TYPE
SYNTAX INTEGER
MAX-ACCESS read-write
STATUS current
DESCRIPTION
"Data value."
::= { dataArray19 294 }

dataValue19_295 OBJECT-TYPE
SYNTAX INTEGER
MAX-ACCESS read-write
STATUS current
DESCRIPTION
"Data value."
::= { dataArray19 295 }

dataValue19_296 OBJECT-TYPE
SYNTAX INTEGER
MAX-ACCESS read-write
STATUS current
DESCRIPTION
"Data value."
::= { dataArray19 296 }

dataValue19_297 OBJECT-TYPE
SYNTAX INTEGER
MAX-ACCESS read-write
STATUS current
DESCRIPTION
"Data value."
::= { dataArray19 297 }

dataValue19_298 OBJECT-TYPE
SYNTAX INTEGER
MAX-ACCESS read-write
STATUS current
DESCRIPTION
"Data value."
::= { dataArray19 298 }

dataValue19_299 OBJECT-TYPE
SYNTAX INTEGER
MAX-ACCESS read-write
STATUS current
DESCRIPTION
"Data value."
::= { dataArray19 299 }

dataValue19_300 OBJECT-TYPE
SYNTAX INTEGER
MAX-ACCESS read-write
STATUS current
DESCRIPTION
"Data value."
::= { dataArray19 300 }

dataValue19_301 OBJECT-TYPE
SYNTAX INTEGER
MAX-ACCESS read-write
STATUS current
DESCRIPTION
"Data value."
::= { dataArray19 301 }

dataValue19_302 OBJECT-TYPE
SYNTAX INTEGER
MAX-ACCESS read-write
STATUS current
DESCRIPTION
"Data value."
::= { dataArray19 302 }

dataValue19_303 OBJECT-TYPE
SYNTAX INTEGER
MAX-ACCESS read-write
STATUS current
DESCRIPTION
"Data value."
::= { dataArray19 303 }

dataValue19_304 OBJECT-TYPE
SYNTAX INTEGER
MAX-ACCESS read-write
STATUS current
DESCRIPTION
"Data value."
::= { dataArray19 304 }

dataValue19_305 OBJECT-TYPE
SYNTAX INTEGER
MAX-ACCESS read-write
STATUS current
DESCRIPTION
"Data value."
::= { dataArray19 305 }

dataValue19_306 OBJECT-TYPE
SYNTAX INTEGER
MAX-ACCESS read-write
STATUS current
DESCRIPTION
"Data value."
::= { dataArray19 306 }

dataValue19_307 OBJECT-TYPE
SYNTAX INTEGER
MAX-ACCESS read-write
STATUS current
DESCRIPTION
"Data value."
::= { dataArray19 307 }

dataValue19_308 OBJECT-TYPE
SYNTAX INTEGER
MAX-ACCESS read-write
STATUS current
DESCRIPTION
"Data value."
::= { dataArray19 308 }

dataValue19_309 OBJECT-TYPE
SYNTAX INTEGER
MAX-ACCESS read-write
STATUS current
DESCRIPTION
"Data value."
::= { dataArray19 309 }

dataValue19_310 OBJECT-TYPE
SYNTAX INTEGER
MAX-ACCESS read-write
STATUS current
DESCRIPTION
"Data value."
::= { dataArray19 310 }

dataValue19_311 OBJECT-TYPE
SYNTAX INTEGER
MAX-ACCESS read-write
STATUS current
DESCRIPTION
"Data value."
::= { dataArray19 311 }

dataValue19_312 OBJECT-TYPE
SYNTAX INTEGER
MAX-ACCESS read-write
STATUS current
DESCRIPTION
"Data value."
::= { dataArray19 312 }

dataValue19_313 OBJECT-TYPE
SYNTAX INTEGER
MAX-ACCESS read-write
STATUS current
DESCRIPTION
"Data value."
::= { dataArray19 313 }

dataValue19_314 OBJECT-TYPE
SYNTAX INTEGER
MAX-ACCESS read-write
STATUS current
DESCRIPTION
"Data value."
::= { dataArray19 314 }

dataValue19_315 OBJECT-TYPE
SYNTAX INTEGER
MAX-ACCESS read-write
STATUS current
DESCRIPTION
"Data value."
::= { dataArray19 315 }

dataValue19_316 OBJECT-TYPE
SYNTAX INTEGER
MAX-ACCESS read-write
STATUS current
DESCRIPTION
"Data value."
::= { dataArray19 316 }

dataValue19_317 OBJECT-TYPE
SYNTAX INTEGER
MAX-ACCESS read-write
STATUS current
DESCRIPTION
"Data value."
::= { dataArray19 317 }

dataValue19_318 OBJECT-TYPE
SYNTAX INTEGER
MAX-ACCESS read-write
STATUS current
DESCRIPTION
"Data value."
::= { dataArray19 318 }

dataValue19_319 OBJECT-TYPE
SYNTAX INTEGER
MAX-ACCESS read-write
STATUS current
DESCRIPTION
"Data value."
::= { dataArray19 319 }

dataValue19_320 OBJECT-TYPE
SYNTAX INTEGER
MAX-ACCESS read-write
STATUS current
DESCRIPTION
"Data value."
::= { dataArray19 320 }

dataValue19_321 OBJECT-TYPE
SYNTAX INTEGER
MAX-ACCESS read-write
STATUS current
DESCRIPTION
"Data value."
::= { dataArray19 321 }

dataValue19_322 OBJECT-TYPE
SYNTAX INTEGER
MAX-ACCESS read-write
STATUS current
DESCRIPTION
"Data value."
::= { dataArray19 322 }

dataValue19_323 OBJECT-TYPE
SYNTAX INTEGER
MAX-ACCESS read-write
STATUS current
DESCRIPTION
"Data value."
::= { dataArray19 323 }

dataValue19_324 OBJECT-TYPE
SYNTAX INTEGER
MAX-ACCESS read-write
STATUS current
DESCRIPTION
"Data value."
::= { dataArray19 324 }

dataValue19_325 OBJECT-TYPE
SYNTAX INTEGER
MAX-ACCESS read-write
STATUS current
DESCRIPTION
"Data value."
::= { dataArray19 325 }

dataValue19_326 OBJECT-TYPE
SYNTAX INTEGER
MAX-ACCESS read-write
STATUS current
DESCRIPTION
"Data value."
::= { dataArray19 326 }

dataValue19_327 OBJECT-TYPE
SYNTAX INTEGER
MAX-ACCESS read-write
STATUS current
DESCRIPTION
"Data value."
::= { dataArray19 327 }

dataValue19_328 OBJECT-TYPE
SYNTAX INTEGER
MAX-ACCESS read-write
STATUS current
DESCRIPTION
"Data value."
::= { dataArray19 328 }

dataValue19_329 OBJECT-TYPE
SYNTAX INTEGER
MAX-ACCESS read-write
STATUS current
DESCRIPTION
"Data value."
::= { dataArray19 329 }

dataValue19_330 OBJECT-TYPE
SYNTAX INTEGER
MAX-ACCESS read-write
STATUS current
DESCRIPTION
"Data value."
::= { dataArray19 330 }

dataValue19_331 OBJECT-TYPE
SYNTAX INTEGER
MAX-ACCESS read-write
STATUS current
DESCRIPTION
"Data value."
::= { dataArray19 331 }

dataValue19_332 OBJECT-TYPE
SYNTAX INTEGER
MAX-ACCESS read-write
STATUS current
DESCRIPTION
"Data value."
::= { dataArray19 332 }

dataValue19_333 OBJECT-TYPE
SYNTAX INTEGER
MAX-ACCESS read-write
STATUS current
DESCRIPTION
"Data value."
::= { dataArray19 333 }

dataValue19_334 OBJECT-TYPE
SYNTAX INTEGER
MAX-ACCESS read-write
STATUS current
DESCRIPTION
"Data value."
::= { dataArray19 334 }

dataValue19_335 OBJECT-TYPE
SYNTAX INTEGER
MAX-ACCESS read-write
STATUS current
DESCRIPTION
"Data value."
::= { dataArray19 335 }

dataValue19_336 OBJECT-TYPE
SYNTAX INTEGER
MAX-ACCESS read-write
STATUS current
DESCRIPTION
"Data value."
::= { dataArray19 336 }

dataValue19_337 OBJECT-TYPE
SYNTAX INTEGER
MAX-ACCESS read-write
STATUS current
DESCRIPTION
"Data value."
::= { dataArray19 337 }

dataValue19_338 OBJECT-TYPE
SYNTAX INTEGER
MAX-ACCESS read-write
STATUS current
DESCRIPTION
"Data value."
::= { dataArray19 338 }

dataValue19_339 OBJECT-TYPE
SYNTAX INTEGER
MAX-ACCESS read-write
STATUS current
DESCRIPTION
"Data value."
::= { dataArray19 339 }

dataValue19_340 OBJECT-TYPE
SYNTAX INTEGER
MAX-ACCESS read-write
STATUS current
DESCRIPTION
"Data value."
::= { dataArray19 340 }

dataValue19_341 OBJECT-TYPE
SYNTAX INTEGER
MAX-ACCESS read-write
STATUS current
DESCRIPTION
"Data value."
::= { dataArray19 341 }

dataValue19_342 OBJECT-TYPE
SYNTAX INTEGER
MAX-ACCESS read-write
STATUS current
DESCRIPTION
"Data value."
::= { dataArray19 342 }

dataValue19_343 OBJECT-TYPE
SYNTAX INTEGER
MAX-ACCESS read-write
STATUS current
DESCRIPTION
"Data value."
::= { dataArray19 343 }

dataValue19_344 OBJECT-TYPE
SYNTAX INTEGER
MAX-ACCESS read-write
STATUS current
DESCRIPTION
"Data value."
::= { dataArray19 344 }

dataValue19_345 OBJECT-TYPE
SYNTAX INTEGER
MAX-ACCESS read-write
STATUS current
DESCRIPTION
"Data value."
::= { dataArray19 345 }

dataValue19_346 OBJECT-TYPE
SYNTAX INTEGER
MAX-ACCESS read-write
STATUS current
DESCRIPTION
"Data value."
::= { dataArray19 346 }

dataValue19_347 OBJECT-TYPE
SYNTAX INTEGER
MAX-ACCESS read-write
STATUS current
DESCRIPTION
"Data value."
::= { dataArray19 347 }

dataValue19_348 OBJECT-TYPE
SYNTAX INTEGER
MAX-ACCESS read-write
STATUS current
DESCRIPTION
"Data value."
::= { dataArray19 348 }

dataValue19_349 OBJECT-TYPE
SYNTAX INTEGER
MAX-ACCESS read-write
STATUS current
DESCRIPTION
"Data value."
::= { dataArray19 349 }

dataValue19_350 OBJECT-TYPE
SYNTAX INTEGER
MAX-ACCESS read-write
STATUS current
DESCRIPTION
"Data value."
::= { dataArray19 350 }

dataValue19_351 OBJECT-TYPE
SYNTAX INTEGER
MAX-ACCESS read-write
STATUS current
DESCRIPTION
"Data value."
::= { dataArray19 351 }

dataValue19_352 OBJECT-TYPE
SYNTAX INTEGER
MAX-ACCESS read-write
STATUS current
DESCRIPTION
"Data value."
::= { dataArray19 352 }

dataValue19_353 OBJECT-TYPE
SYNTAX INTEGER
MAX-ACCESS read-write
STATUS current
DESCRIPTION
"Data value."
::= { dataArray19 353 }

dataValue19_354 OBJECT-TYPE
SYNTAX INTEGER
MAX-ACCESS read-write
STATUS current
DESCRIPTION
"Data value."
::= { dataArray19 354 }

dataValue19_355 OBJECT-TYPE
SYNTAX INTEGER
MAX-ACCESS read-write
STATUS current
DESCRIPTION
"Data value."
::= { dataArray19 355 }

dataValue19_356 OBJECT-TYPE
SYNTAX INTEGER
MAX-ACCESS read-write
STATUS current
DESCRIPTION
"Data value."
::= { dataArray19 356 }

dataValue19_357 OBJECT-TYPE
SYNTAX INTEGER
MAX-ACCESS read-write
STATUS current
DESCRIPTION
"Data value."
::= { dataArray19 357 }

dataValue19_358 OBJECT-TYPE
SYNTAX INTEGER
MAX-ACCESS read-write
STATUS current
DESCRIPTION
"Data value."
::= { dataArray19 358 }

dataValue19_359 OBJECT-TYPE
SYNTAX INTEGER
MAX-ACCESS read-write
STATUS current
DESCRIPTION
"Data value."
::= { dataArray19 359 }

dataValue19_360 OBJECT-TYPE
SYNTAX INTEGER
MAX-ACCESS read-write
STATUS current
DESCRIPTION
"Data value."
::= { dataArray19 360 }

dataValue19_361 OBJECT-TYPE
SYNTAX INTEGER
MAX-ACCESS read-write
STATUS current
DESCRIPTION
"Data value."
::= { dataArray19 361 }

dataValue19_362 OBJECT-TYPE
SYNTAX INTEGER
MAX-ACCESS read-write
STATUS current
DESCRIPTION
"Data value."
::= { dataArray19 362 }

dataValue19_363 OBJECT-TYPE
SYNTAX INTEGER
MAX-ACCESS read-write
STATUS current
DESCRIPTION
"Data value."
::= { dataArray19 363 }

dataValue19_364 OBJECT-TYPE
SYNTAX INTEGER
MAX-ACCESS read-write
STATUS current
DESCRIPTION
"Data value."
::= { dataArray19 364 }

dataValue19_365 OBJECT-TYPE
SYNTAX INTEGER
MAX-ACCESS read-write
STATUS current
DESCRIPTION
"Data value."
::= { dataArray19 365 }

dataValue19_366 OBJECT-TYPE
SYNTAX INTEGER
MAX-ACCESS read-write
STATUS current
DESCRIPTION
"Data value."
::= { dataArray19 366 }

dataValue19_367 OBJECT-TYPE
SYNTAX INTEGER
MAX-ACCESS read-write
STATUS current
DESCRIPTION
"Data value."
::= { dataArray19 367 }

dataValue19_368 OBJECT-TYPE
SYNTAX INTEGER
MAX-ACCESS read-write
STATUS current
DESCRIPTION
"Data value."
::= { dataArray19 368 }

dataValue19_369 OBJECT-TYPE
SYNTAX INTEGER
MAX-ACCESS read-write
STATUS current
DESCRIPTION
"Data value."
::= { dataArray19 369 }

dataValue19_370 OBJECT-TYPE
SYNTAX INTEGER
MAX-ACCESS read-write
STATUS current
DESCRIPTION
"Data value."
::= { dataArray19 370 }

dataValue19_371 OBJECT-TYPE
SYNTAX INTEGER
MAX-ACCESS read-write
STATUS current
DESCRIPTION
"Data value."
::= { dataArray19 371 }

dataValue19_372 OBJECT-TYPE
SYNTAX INTEGER
MAX-ACCESS read-write
STATUS current
DESCRIPTION
"Data value."
::= { dataArray19 372 }

dataValue19_373 OBJECT-TYPE
SYNTAX INTEGER
MAX-ACCESS read-write
STATUS current
DESCRIPTION
"Data value."
::= { dataArray19 373 }

dataValue19_374 OBJECT-TYPE
SYNTAX INTEGER
MAX-ACCESS read-write
STATUS current
DESCRIPTION
"Data value."
::= { dataArray19 374 }

dataValue19_375 OBJECT-TYPE
SYNTAX INTEGER
MAX-ACCESS read-write
STATUS current
DESCRIPTION
"Data value."
::= { dataArray19 375 }

dataValue19_376 OBJECT-TYPE
SYNTAX INTEGER
MAX-ACCESS read-write
STATUS current
DESCRIPTION
"Data value."
::= { dataArray19 376 }

dataValue19_377 OBJECT-TYPE
SYNTAX INTEGER
MAX-ACCESS read-write
STATUS current
DESCRIPTION
"Data value."
::= { dataArray19 377 }

dataValue19_378 OBJECT-TYPE
SYNTAX INTEGER
MAX-ACCESS read-write
STATUS current
DESCRIPTION
"Data value."
::= { dataArray19 378 }

dataValue19_379 OBJECT-TYPE
SYNTAX INTEGER
MAX-ACCESS read-write
STATUS current
DESCRIPTION
"Data value."
::= { dataArray19 379 }

dataValue19_380 OBJECT-TYPE
SYNTAX INTEGER
MAX-ACCESS read-write
STATUS current
DESCRIPTION
"Data value."
::= { dataArray19 380 }

dataValue19_381 OBJECT-TYPE
SYNTAX INTEGER
MAX-ACCESS read-write
STATUS current
DESCRIPTION
"Data value."
::= { dataArray19 381 }

dataValue19_382 OBJECT-TYPE
SYNTAX INTEGER
MAX-ACCESS read-write
STATUS current
DESCRIPTION
"Data value."
::= { dataArray19 382 }

dataValue19_383 OBJECT-TYPE
SYNTAX INTEGER
MAX-ACCESS read-write
STATUS current
DESCRIPTION
"Data value."
::= { dataArray19 383 }

dataValue19_384 OBJECT-TYPE
SYNTAX INTEGER
MAX-ACCESS read-write
STATUS current
DESCRIPTION
"Data value."
::= { dataArray19 384 }

dataValue19_385 OBJECT-TYPE
SYNTAX INTEGER
MAX-ACCESS read-write
STATUS current
DESCRIPTION
"Data value."
::= { dataArray19 385 }

dataValue19_386 OBJECT-TYPE
SYNTAX INTEGER
MAX-ACCESS read-write
STATUS current
DESCRIPTION
"Data value."
::= { dataArray19 386 }

dataValue19_387 OBJECT-TYPE
SYNTAX INTEGER
MAX-ACCESS read-write
STATUS current
DESCRIPTION
"Data value."
::= { dataArray19 387 }

dataValue19_388 OBJECT-TYPE
SYNTAX INTEGER
MAX-ACCESS read-write
STATUS current
DESCRIPTION
"Data value."
::= { dataArray19 388 }

dataValue19_389 OBJECT-TYPE
SYNTAX INTEGER
MAX-ACCESS read-write
STATUS current
DESCRIPTION
"Data value."
::= { dataArray19 389 }

dataValue19_390 OBJECT-TYPE
SYNTAX INTEGER
MAX-ACCESS read-write
STATUS current
DESCRIPTION
"Data value."
::= { dataArray19 390 }

dataValue19_391 OBJECT-TYPE
SYNTAX INTEGER
MAX-ACCESS read-write
STATUS current
DESCRIPTION
"Data value."
::= { dataArray19 391 }

dataValue19_392 OBJECT-TYPE
SYNTAX INTEGER
MAX-ACCESS read-write
STATUS current
DESCRIPTION
"Data value."
::= { dataArray19 392 }

dataValue19_393 OBJECT-TYPE
SYNTAX INTEGER
MAX-ACCESS read-write
STATUS current
DESCRIPTION
"Data value."
::= { dataArray19 393 }

dataValue19_394 OBJECT-TYPE
SYNTAX INTEGER
MAX-ACCESS read-write
STATUS current
DESCRIPTION
"Data value."
::= { dataArray19 394 }

dataValue19_395 OBJECT-TYPE
SYNTAX INTEGER
MAX-ACCESS read-write
STATUS current
DESCRIPTION
"Data value."
::= { dataArray19 395 }

dataValue19_396 OBJECT-TYPE
SYNTAX INTEGER
MAX-ACCESS read-write
STATUS current
DESCRIPTION
"Data value."
::= { dataArray19 396 }

dataValue19_397 OBJECT-TYPE
SYNTAX INTEGER
MAX-ACCESS read-write
STATUS current
DESCRIPTION
"Data value."
::= { dataArray19 397 }

dataValue19_398 OBJECT-TYPE
SYNTAX INTEGER
MAX-ACCESS read-write
STATUS current
DESCRIPTION
"Data value."
::= { dataArray19 398 }

dataValue19_399 OBJECT-TYPE
SYNTAX INTEGER
MAX-ACCESS read-write
STATUS current
DESCRIPTION
"Data value."
::= { dataArray19 399 }

dataArray20 OBJECT IDENTIFIER ::= { cc08255400_v1_00a 20 }

dataValue20_0 OBJECT-TYPE
SYNTAX INTEGER
MAX-ACCESS read-write
STATUS current
DESCRIPTION
"Data value."
::= { dataArray20 0 }

dataValue20_1 OBJECT-TYPE
SYNTAX INTEGER
MAX-ACCESS read-write
STATUS current
DESCRIPTION
"Data value."
::= { dataArray20 1 }

dataValue20_2 OBJECT-TYPE
SYNTAX INTEGER
MAX-ACCESS read-write
STATUS current
DESCRIPTION
"Data value."
::= { dataArray20 2 }

dataValue20_3 OBJECT-TYPE
SYNTAX INTEGER
MAX-ACCESS read-write
STATUS current
DESCRIPTION
"Data value."
::= { dataArray20 3 }

dataValue20_4 OBJECT-TYPE
SYNTAX INTEGER
MAX-ACCESS read-write
STATUS current
DESCRIPTION
"Data value."
::= { dataArray20 4 }

dataValue20_5 OBJECT-TYPE
SYNTAX INTEGER
MAX-ACCESS read-write
STATUS current
DESCRIPTION
"Data value."
::= { dataArray20 5 }

dataValue20_6 OBJECT-TYPE
SYNTAX INTEGER
MAX-ACCESS read-write
STATUS current
DESCRIPTION
"Data value."
::= { dataArray20 6 }

dataValue20_7 OBJECT-TYPE
SYNTAX INTEGER
MAX-ACCESS read-write
STATUS current
DESCRIPTION
"Data value."
::= { dataArray20 7 }

dataValue20_8 OBJECT-TYPE
SYNTAX INTEGER
MAX-ACCESS read-write
STATUS current
DESCRIPTION
"Data value."
::= { dataArray20 8 }

dataValue20_9 OBJECT-TYPE
SYNTAX INTEGER
MAX-ACCESS read-write
STATUS current
DESCRIPTION
"Data value."
::= { dataArray20 9 }

dataValue20_10 OBJECT-TYPE
SYNTAX INTEGER
MAX-ACCESS read-write
STATUS current
DESCRIPTION
"Data value."
::= { dataArray20 10 }

dataValue20_11 OBJECT-TYPE
SYNTAX INTEGER
MAX-ACCESS read-write
STATUS current
DESCRIPTION
"Data value."
::= { dataArray20 11 }

dataValue20_12 OBJECT-TYPE
SYNTAX INTEGER
MAX-ACCESS read-write
STATUS current
DESCRIPTION
"Data value."
::= { dataArray20 12 }

dataValue20_13 OBJECT-TYPE
SYNTAX INTEGER
MAX-ACCESS read-write
STATUS current
DESCRIPTION
"Data value."
::= { dataArray20 13 }

dataValue20_14 OBJECT-TYPE
SYNTAX INTEGER
MAX-ACCESS read-write
STATUS current
DESCRIPTION
"Data value."
::= { dataArray20 14 }

dataValue20_15 OBJECT-TYPE
SYNTAX INTEGER
MAX-ACCESS read-write
STATUS current
DESCRIPTION
"Data value."
::= { dataArray20 15 }

dataValue20_16 OBJECT-TYPE
SYNTAX INTEGER
MAX-ACCESS read-write
STATUS current
DESCRIPTION
"Data value."
::= { dataArray20 16 }

dataValue20_17 OBJECT-TYPE
SYNTAX INTEGER
MAX-ACCESS read-write
STATUS current
DESCRIPTION
"Data value."
::= { dataArray20 17 }

dataValue20_18 OBJECT-TYPE
SYNTAX INTEGER
MAX-ACCESS read-write
STATUS current
DESCRIPTION
"Data value."
::= { dataArray20 18 }

dataValue20_19 OBJECT-TYPE
SYNTAX INTEGER
MAX-ACCESS read-write
STATUS current
DESCRIPTION
"Data value."
::= { dataArray20 19 }

dataValue20_20 OBJECT-TYPE
SYNTAX INTEGER
MAX-ACCESS read-write
STATUS current
DESCRIPTION
"Data value."
::= { dataArray20 20 }

dataValue20_21 OBJECT-TYPE
SYNTAX INTEGER
MAX-ACCESS read-write
STATUS current
DESCRIPTION
"Data value."
::= { dataArray20 21 }

dataValue20_22 OBJECT-TYPE
SYNTAX INTEGER
MAX-ACCESS read-write
STATUS current
DESCRIPTION
"Data value."
::= { dataArray20 22 }

dataValue20_23 OBJECT-TYPE
SYNTAX INTEGER
MAX-ACCESS read-write
STATUS current
DESCRIPTION
"Data value."
::= { dataArray20 23 }

dataValue20_24 OBJECT-TYPE
SYNTAX INTEGER
MAX-ACCESS read-write
STATUS current
DESCRIPTION
"Data value."
::= { dataArray20 24 }

dataValue20_25 OBJECT-TYPE
SYNTAX INTEGER
MAX-ACCESS read-write
STATUS current
DESCRIPTION
"Data value."
::= { dataArray20 25 }

dataValue20_26 OBJECT-TYPE
SYNTAX INTEGER
MAX-ACCESS read-write
STATUS current
DESCRIPTION
"Data value."
::= { dataArray20 26 }

dataValue20_27 OBJECT-TYPE
SYNTAX INTEGER
MAX-ACCESS read-write
STATUS current
DESCRIPTION
"Data value."
::= { dataArray20 27 }

dataValue20_28 OBJECT-TYPE
SYNTAX INTEGER
MAX-ACCESS read-write
STATUS current
DESCRIPTION
"Data value."
::= { dataArray20 28 }

dataValue20_29 OBJECT-TYPE
SYNTAX INTEGER
MAX-ACCESS read-write
STATUS current
DESCRIPTION
"Data value."
::= { dataArray20 29 }

dataValue20_30 OBJECT-TYPE
SYNTAX INTEGER
MAX-ACCESS read-write
STATUS current
DESCRIPTION
"Data value."
::= { dataArray20 30 }

dataValue20_31 OBJECT-TYPE
SYNTAX INTEGER
MAX-ACCESS read-write
STATUS current
DESCRIPTION
"Data value."
::= { dataArray20 31 }

dataValue20_32 OBJECT-TYPE
SYNTAX INTEGER
MAX-ACCESS read-write
STATUS current
DESCRIPTION
"Data value."
::= { dataArray20 32 }

dataValue20_33 OBJECT-TYPE
SYNTAX INTEGER
MAX-ACCESS read-write
STATUS current
DESCRIPTION
"Data value."
::= { dataArray20 33 }

dataValue20_34 OBJECT-TYPE
SYNTAX INTEGER
MAX-ACCESS read-write
STATUS current
DESCRIPTION
"Data value."
::= { dataArray20 34 }

dataValue20_35 OBJECT-TYPE
SYNTAX INTEGER
MAX-ACCESS read-write
STATUS current
DESCRIPTION
"Data value."
::= { dataArray20 35 }

dataValue20_36 OBJECT-TYPE
SYNTAX INTEGER
MAX-ACCESS read-write
STATUS current
DESCRIPTION
"Data value."
::= { dataArray20 36 }

dataValue20_37 OBJECT-TYPE
SYNTAX INTEGER
MAX-ACCESS read-write
STATUS current
DESCRIPTION
"Data value."
::= { dataArray20 37 }

dataValue20_38 OBJECT-TYPE
SYNTAX INTEGER
MAX-ACCESS read-write
STATUS current
DESCRIPTION
"Data value."
::= { dataArray20 38 }

dataValue20_39 OBJECT-TYPE
SYNTAX INTEGER
MAX-ACCESS read-write
STATUS current
DESCRIPTION
"Data value."
::= { dataArray20 39 }

dataValue20_40 OBJECT-TYPE
SYNTAX INTEGER
MAX-ACCESS read-write
STATUS current
DESCRIPTION
"Data value."
::= { dataArray20 40 }

dataValue20_41 OBJECT-TYPE
SYNTAX INTEGER
MAX-ACCESS read-write
STATUS current
DESCRIPTION
"Data value."
::= { dataArray20 41 }

dataValue20_42 OBJECT-TYPE
SYNTAX INTEGER
MAX-ACCESS read-write
STATUS current
DESCRIPTION
"Data value."
::= { dataArray20 42 }

dataValue20_43 OBJECT-TYPE
SYNTAX INTEGER
MAX-ACCESS read-write
STATUS current
DESCRIPTION
"Data value."
::= { dataArray20 43 }

dataValue20_44 OBJECT-TYPE
SYNTAX INTEGER
MAX-ACCESS read-write
STATUS current
DESCRIPTION
"Data value."
::= { dataArray20 44 }

dataValue20_45 OBJECT-TYPE
SYNTAX INTEGER
MAX-ACCESS read-write
STATUS current
DESCRIPTION
"Data value."
::= { dataArray20 45 }

dataValue20_46 OBJECT-TYPE
SYNTAX INTEGER
MAX-ACCESS read-write
STATUS current
DESCRIPTION
"Data value."
::= { dataArray20 46 }

dataValue20_47 OBJECT-TYPE
SYNTAX INTEGER
MAX-ACCESS read-write
STATUS current
DESCRIPTION
"Data value."
::= { dataArray20 47 }

dataValue20_48 OBJECT-TYPE
SYNTAX INTEGER
MAX-ACCESS read-write
STATUS current
DESCRIPTION
"Data value."
::= { dataArray20 48 }

dataValue20_49 OBJECT-TYPE
SYNTAX INTEGER
MAX-ACCESS read-write
STATUS current
DESCRIPTION
"Data value."
::= { dataArray20 49 }

dataValue20_50 OBJECT-TYPE
SYNTAX INTEGER
MAX-ACCESS read-write
STATUS current
DESCRIPTION
"Data value."
::= { dataArray20 50 }

dataValue20_51 OBJECT-TYPE
SYNTAX INTEGER
MAX-ACCESS read-write
STATUS current
DESCRIPTION
"Data value."
::= { dataArray20 51 }

dataValue20_52 OBJECT-TYPE
SYNTAX INTEGER
MAX-ACCESS read-write
STATUS current
DESCRIPTION
"Data value."
::= { dataArray20 52 }

dataValue20_53 OBJECT-TYPE
SYNTAX INTEGER
MAX-ACCESS read-write
STATUS current
DESCRIPTION
"Data value."
::= { dataArray20 53 }

dataValue20_54 OBJECT-TYPE
SYNTAX INTEGER
MAX-ACCESS read-write
STATUS current
DESCRIPTION
"Data value."
::= { dataArray20 54 }

dataValue20_55 OBJECT-TYPE
SYNTAX INTEGER
MAX-ACCESS read-write
STATUS current
DESCRIPTION
"Data value."
::= { dataArray20 55 }

dataValue20_56 OBJECT-TYPE
SYNTAX INTEGER
MAX-ACCESS read-write
STATUS current
DESCRIPTION
"Data value."
::= { dataArray20 56 }

dataValue20_57 OBJECT-TYPE
SYNTAX INTEGER
MAX-ACCESS read-write
STATUS current
DESCRIPTION
"Data value."
::= { dataArray20 57 }

dataValue20_58 OBJECT-TYPE
SYNTAX INTEGER
MAX-ACCESS read-write
STATUS current
DESCRIPTION
"Data value."
::= { dataArray20 58 }

dataValue20_59 OBJECT-TYPE
SYNTAX INTEGER
MAX-ACCESS read-write
STATUS current
DESCRIPTION
"Data value."
::= { dataArray20 59 }

dataValue20_60 OBJECT-TYPE
SYNTAX INTEGER
MAX-ACCESS read-write
STATUS current
DESCRIPTION
"Data value."
::= { dataArray20 60 }

dataValue20_61 OBJECT-TYPE
SYNTAX INTEGER
MAX-ACCESS read-write
STATUS current
DESCRIPTION
"Data value."
::= { dataArray20 61 }

dataValue20_62 OBJECT-TYPE
SYNTAX INTEGER
MAX-ACCESS read-write
STATUS current
DESCRIPTION
"Data value."
::= { dataArray20 62 }

dataValue20_63 OBJECT-TYPE
SYNTAX INTEGER
MAX-ACCESS read-write
STATUS current
DESCRIPTION
"Data value."
::= { dataArray20 63 }

dataValue20_64 OBJECT-TYPE
SYNTAX INTEGER
MAX-ACCESS read-write
STATUS current
DESCRIPTION
"Data value."
::= { dataArray20 64 }

dataValue20_65 OBJECT-TYPE
SYNTAX INTEGER
MAX-ACCESS read-write
STATUS current
DESCRIPTION
"Data value."
::= { dataArray20 65 }

dataValue20_66 OBJECT-TYPE
SYNTAX INTEGER
MAX-ACCESS read-write
STATUS current
DESCRIPTION
"Data value."
::= { dataArray20 66 }

dataValue20_67 OBJECT-TYPE
SYNTAX INTEGER
MAX-ACCESS read-write
STATUS current
DESCRIPTION
"Data value."
::= { dataArray20 67 }

dataValue20_68 OBJECT-TYPE
SYNTAX INTEGER
MAX-ACCESS read-write
STATUS current
DESCRIPTION
"Data value."
::= { dataArray20 68 }

dataValue20_69 OBJECT-TYPE
SYNTAX INTEGER
MAX-ACCESS read-write
STATUS current
DESCRIPTION
"Data value."
::= { dataArray20 69 }

dataValue20_70 OBJECT-TYPE
SYNTAX INTEGER
MAX-ACCESS read-write
STATUS current
DESCRIPTION
"Data value."
::= { dataArray20 70 }

dataValue20_71 OBJECT-TYPE
SYNTAX INTEGER
MAX-ACCESS read-write
STATUS current
DESCRIPTION
"Data value."
::= { dataArray20 71 }

dataValue20_72 OBJECT-TYPE
SYNTAX INTEGER
MAX-ACCESS read-write
STATUS current
DESCRIPTION
"Data value."
::= { dataArray20 72 }

dataValue20_73 OBJECT-TYPE
SYNTAX INTEGER
MAX-ACCESS read-write
STATUS current
DESCRIPTION
"Data value."
::= { dataArray20 73 }

dataValue20_74 OBJECT-TYPE
SYNTAX INTEGER
MAX-ACCESS read-write
STATUS current
DESCRIPTION
"Data value."
::= { dataArray20 74 }

dataValue20_75 OBJECT-TYPE
SYNTAX INTEGER
MAX-ACCESS read-write
STATUS current
DESCRIPTION
"Data value."
::= { dataArray20 75 }

dataValue20_76 OBJECT-TYPE
SYNTAX INTEGER
MAX-ACCESS read-write
STATUS current
DESCRIPTION
"Data value."
::= { dataArray20 76 }

dataValue20_77 OBJECT-TYPE
SYNTAX INTEGER
MAX-ACCESS read-write
STATUS current
DESCRIPTION
"Data value."
::= { dataArray20 77 }

dataValue20_78 OBJECT-TYPE
SYNTAX INTEGER
MAX-ACCESS read-write
STATUS current
DESCRIPTION
"Data value."
::= { dataArray20 78 }

dataValue20_79 OBJECT-TYPE
SYNTAX INTEGER
MAX-ACCESS read-write
STATUS current
DESCRIPTION
"Data value."
::= { dataArray20 79 }

dataValue20_80 OBJECT-TYPE
SYNTAX INTEGER
MAX-ACCESS read-write
STATUS current
DESCRIPTION
"Data value."
::= { dataArray20 80 }

dataValue20_81 OBJECT-TYPE
SYNTAX INTEGER
MAX-ACCESS read-write
STATUS current
DESCRIPTION
"Data value."
::= { dataArray20 81 }

dataValue20_82 OBJECT-TYPE
SYNTAX INTEGER
MAX-ACCESS read-write
STATUS current
DESCRIPTION
"Data value."
::= { dataArray20 82 }

dataValue20_83 OBJECT-TYPE
SYNTAX INTEGER
MAX-ACCESS read-write
STATUS current
DESCRIPTION
"Data value."
::= { dataArray20 83 }

dataValue20_84 OBJECT-TYPE
SYNTAX INTEGER
MAX-ACCESS read-write
STATUS current
DESCRIPTION
"Data value."
::= { dataArray20 84 }

dataValue20_85 OBJECT-TYPE
SYNTAX INTEGER
MAX-ACCESS read-write
STATUS current
DESCRIPTION
"Data value."
::= { dataArray20 85 }

dataValue20_86 OBJECT-TYPE
SYNTAX INTEGER
MAX-ACCESS read-write
STATUS current
DESCRIPTION
"Data value."
::= { dataArray20 86 }

dataValue20_87 OBJECT-TYPE
SYNTAX INTEGER
MAX-ACCESS read-write
STATUS current
DESCRIPTION
"Data value."
::= { dataArray20 87 }

dataValue20_88 OBJECT-TYPE
SYNTAX INTEGER
MAX-ACCESS read-write
STATUS current
DESCRIPTION
"Data value."
::= { dataArray20 88 }

dataValue20_89 OBJECT-TYPE
SYNTAX INTEGER
MAX-ACCESS read-write
STATUS current
DESCRIPTION
"Data value."
::= { dataArray20 89 }

dataValue20_90 OBJECT-TYPE
SYNTAX INTEGER
MAX-ACCESS read-write
STATUS current
DESCRIPTION
"Data value."
::= { dataArray20 90 }

dataValue20_91 OBJECT-TYPE
SYNTAX INTEGER
MAX-ACCESS read-write
STATUS current
DESCRIPTION
"Data value."
::= { dataArray20 91 }

dataValue20_92 OBJECT-TYPE
SYNTAX INTEGER
MAX-ACCESS read-write
STATUS current
DESCRIPTION
"Data value."
::= { dataArray20 92 }

dataValue20_93 OBJECT-TYPE
SYNTAX INTEGER
MAX-ACCESS read-write
STATUS current
DESCRIPTION
"Data value."
::= { dataArray20 93 }

dataValue20_94 OBJECT-TYPE
SYNTAX INTEGER
MAX-ACCESS read-write
STATUS current
DESCRIPTION
"Data value."
::= { dataArray20 94 }

dataValue20_95 OBJECT-TYPE
SYNTAX INTEGER
MAX-ACCESS read-write
STATUS current
DESCRIPTION
"Data value."
::= { dataArray20 95 }

dataValue20_96 OBJECT-TYPE
SYNTAX INTEGER
MAX-ACCESS read-write
STATUS current
DESCRIPTION
"Data value."
::= { dataArray20 96 }

dataValue20_97 OBJECT-TYPE
SYNTAX INTEGER
MAX-ACCESS read-write
STATUS current
DESCRIPTION
"Data value."
::= { dataArray20 97 }

dataValue20_98 OBJECT-TYPE
SYNTAX INTEGER
MAX-ACCESS read-write
STATUS current
DESCRIPTION
"Data value."
::= { dataArray20 98 }

dataValue20_99 OBJECT-TYPE
SYNTAX INTEGER
MAX-ACCESS read-write
STATUS current
DESCRIPTION
"Data value."
::= { dataArray20 99 }

dataValue20_100 OBJECT-TYPE
SYNTAX INTEGER
MAX-ACCESS read-write
STATUS current
DESCRIPTION
"Data value."
::= { dataArray20 100 }

dataValue20_101 OBJECT-TYPE
SYNTAX INTEGER
MAX-ACCESS read-write
STATUS current
DESCRIPTION
"Data value."
::= { dataArray20 101 }

dataValue20_102 OBJECT-TYPE
SYNTAX INTEGER
MAX-ACCESS read-write
STATUS current
DESCRIPTION
"Data value."
::= { dataArray20 102 }

dataValue20_103 OBJECT-TYPE
SYNTAX INTEGER
MAX-ACCESS read-write
STATUS current
DESCRIPTION
"Data value."
::= { dataArray20 103 }

dataValue20_104 OBJECT-TYPE
SYNTAX INTEGER
MAX-ACCESS read-write
STATUS current
DESCRIPTION
"Data value."
::= { dataArray20 104 }

dataValue20_105 OBJECT-TYPE
SYNTAX INTEGER
MAX-ACCESS read-write
STATUS current
DESCRIPTION
"Data value."
::= { dataArray20 105 }

dataValue20_106 OBJECT-TYPE
SYNTAX INTEGER
MAX-ACCESS read-write
STATUS current
DESCRIPTION
"Data value."
::= { dataArray20 106 }

dataValue20_107 OBJECT-TYPE
SYNTAX INTEGER
MAX-ACCESS read-write
STATUS current
DESCRIPTION
"Data value."
::= { dataArray20 107 }

dataValue20_108 OBJECT-TYPE
SYNTAX INTEGER
MAX-ACCESS read-write
STATUS current
DESCRIPTION
"Data value."
::= { dataArray20 108 }

dataValue20_109 OBJECT-TYPE
SYNTAX INTEGER
MAX-ACCESS read-write
STATUS current
DESCRIPTION
"Data value."
::= { dataArray20 109 }

dataValue20_110 OBJECT-TYPE
SYNTAX INTEGER
MAX-ACCESS read-write
STATUS current
DESCRIPTION
"Data value."
::= { dataArray20 110 }

dataValue20_111 OBJECT-TYPE
SYNTAX INTEGER
MAX-ACCESS read-write
STATUS current
DESCRIPTION
"Data value."
::= { dataArray20 111 }

dataValue20_112 OBJECT-TYPE
SYNTAX INTEGER
MAX-ACCESS read-write
STATUS current
DESCRIPTION
"Data value."
::= { dataArray20 112 }

dataValue20_113 OBJECT-TYPE
SYNTAX INTEGER
MAX-ACCESS read-write
STATUS current
DESCRIPTION
"Data value."
::= { dataArray20 113 }

dataValue20_114 OBJECT-TYPE
SYNTAX INTEGER
MAX-ACCESS read-write
STATUS current
DESCRIPTION
"Data value."
::= { dataArray20 114 }

dataValue20_115 OBJECT-TYPE
SYNTAX INTEGER
MAX-ACCESS read-write
STATUS current
DESCRIPTION
"Data value."
::= { dataArray20 115 }

dataValue20_116 OBJECT-TYPE
SYNTAX INTEGER
MAX-ACCESS read-write
STATUS current
DESCRIPTION
"Data value."
::= { dataArray20 116 }

dataValue20_117 OBJECT-TYPE
SYNTAX INTEGER
MAX-ACCESS read-write
STATUS current
DESCRIPTION
"Data value."
::= { dataArray20 117 }

dataValue20_118 OBJECT-TYPE
SYNTAX INTEGER
MAX-ACCESS read-write
STATUS current
DESCRIPTION
"Data value."
::= { dataArray20 118 }

dataValue20_119 OBJECT-TYPE
SYNTAX INTEGER
MAX-ACCESS read-write
STATUS current
DESCRIPTION
"Data value."
::= { dataArray20 119 }

dataValue20_120 OBJECT-TYPE
SYNTAX INTEGER
MAX-ACCESS read-write
STATUS current
DESCRIPTION
"Data value."
::= { dataArray20 120 }

dataValue20_121 OBJECT-TYPE
SYNTAX INTEGER
MAX-ACCESS read-write
STATUS current
DESCRIPTION
"Data value."
::= { dataArray20 121 }

dataValue20_122 OBJECT-TYPE
SYNTAX INTEGER
MAX-ACCESS read-write
STATUS current
DESCRIPTION
"Data value."
::= { dataArray20 122 }

dataValue20_123 OBJECT-TYPE
SYNTAX INTEGER
MAX-ACCESS read-write
STATUS current
DESCRIPTION
"Data value."
::= { dataArray20 123 }

dataValue20_124 OBJECT-TYPE
SYNTAX INTEGER
MAX-ACCESS read-write
STATUS current
DESCRIPTION
"Data value."
::= { dataArray20 124 }

dataValue20_125 OBJECT-TYPE
SYNTAX INTEGER
MAX-ACCESS read-write
STATUS current
DESCRIPTION
"Data value."
::= { dataArray20 125 }

dataValue20_126 OBJECT-TYPE
SYNTAX INTEGER
MAX-ACCESS read-write
STATUS current
DESCRIPTION
"Data value."
::= { dataArray20 126 }

dataValue20_127 OBJECT-TYPE
SYNTAX INTEGER
MAX-ACCESS read-write
STATUS current
DESCRIPTION
"Data value."
::= { dataArray20 127 }

dataValue20_128 OBJECT-TYPE
SYNTAX INTEGER
MAX-ACCESS read-write
STATUS current
DESCRIPTION
"Data value."
::= { dataArray20 128 }

dataValue20_129 OBJECT-TYPE
SYNTAX INTEGER
MAX-ACCESS read-write
STATUS current
DESCRIPTION
"Data value."
::= { dataArray20 129 }

dataValue20_130 OBJECT-TYPE
SYNTAX INTEGER
MAX-ACCESS read-write
STATUS current
DESCRIPTION
"Data value."
::= { dataArray20 130 }

dataValue20_131 OBJECT-TYPE
SYNTAX INTEGER
MAX-ACCESS read-write
STATUS current
DESCRIPTION
"Data value."
::= { dataArray20 131 }

dataValue20_132 OBJECT-TYPE
SYNTAX INTEGER
MAX-ACCESS read-write
STATUS current
DESCRIPTION
"Data value."
::= { dataArray20 132 }

dataValue20_133 OBJECT-TYPE
SYNTAX INTEGER
MAX-ACCESS read-write
STATUS current
DESCRIPTION
"Data value."
::= { dataArray20 133 }

dataValue20_134 OBJECT-TYPE
SYNTAX INTEGER
MAX-ACCESS read-write
STATUS current
DESCRIPTION
"Data value."
::= { dataArray20 134 }

dataValue20_135 OBJECT-TYPE
SYNTAX INTEGER
MAX-ACCESS read-write
STATUS current
DESCRIPTION
"Data value."
::= { dataArray20 135 }

dataValue20_136 OBJECT-TYPE
SYNTAX INTEGER
MAX-ACCESS read-write
STATUS current
DESCRIPTION
"Data value."
::= { dataArray20 136 }

dataValue20_137 OBJECT-TYPE
SYNTAX INTEGER
MAX-ACCESS read-write
STATUS current
DESCRIPTION
"Data value."
::= { dataArray20 137 }

dataValue20_138 OBJECT-TYPE
SYNTAX INTEGER
MAX-ACCESS read-write
STATUS current
DESCRIPTION
"Data value."
::= { dataArray20 138 }

dataValue20_139 OBJECT-TYPE
SYNTAX INTEGER
MAX-ACCESS read-write
STATUS current
DESCRIPTION
"Data value."
::= { dataArray20 139 }

dataValue20_140 OBJECT-TYPE
SYNTAX INTEGER
MAX-ACCESS read-write
STATUS current
DESCRIPTION
"Data value."
::= { dataArray20 140 }

dataValue20_141 OBJECT-TYPE
SYNTAX INTEGER
MAX-ACCESS read-write
STATUS current
DESCRIPTION
"Data value."
::= { dataArray20 141 }

dataValue20_142 OBJECT-TYPE
SYNTAX INTEGER
MAX-ACCESS read-write
STATUS current
DESCRIPTION
"Data value."
::= { dataArray20 142 }

dataValue20_143 OBJECT-TYPE
SYNTAX INTEGER
MAX-ACCESS read-write
STATUS current
DESCRIPTION
"Data value."
::= { dataArray20 143 }

dataValue20_144 OBJECT-TYPE
SYNTAX INTEGER
MAX-ACCESS read-write
STATUS current
DESCRIPTION
"Data value."
::= { dataArray20 144 }

dataValue20_145 OBJECT-TYPE
SYNTAX INTEGER
MAX-ACCESS read-write
STATUS current
DESCRIPTION
"Data value."
::= { dataArray20 145 }

dataValue20_146 OBJECT-TYPE
SYNTAX INTEGER
MAX-ACCESS read-write
STATUS current
DESCRIPTION
"Data value."
::= { dataArray20 146 }

dataValue20_147 OBJECT-TYPE
SYNTAX INTEGER
MAX-ACCESS read-write
STATUS current
DESCRIPTION
"Data value."
::= { dataArray20 147 }

dataValue20_148 OBJECT-TYPE
SYNTAX INTEGER
MAX-ACCESS read-write
STATUS current
DESCRIPTION
"Data value."
::= { dataArray20 148 }

dataValue20_149 OBJECT-TYPE
SYNTAX INTEGER
MAX-ACCESS read-write
STATUS current
DESCRIPTION
"Data value."
::= { dataArray20 149 }

dataValue20_150 OBJECT-TYPE
SYNTAX INTEGER
MAX-ACCESS read-write
STATUS current
DESCRIPTION
"Data value."
::= { dataArray20 150 }

dataValue20_151 OBJECT-TYPE
SYNTAX INTEGER
MAX-ACCESS read-write
STATUS current
DESCRIPTION
"Data value."
::= { dataArray20 151 }

dataValue20_152 OBJECT-TYPE
SYNTAX INTEGER
MAX-ACCESS read-write
STATUS current
DESCRIPTION
"Data value."
::= { dataArray20 152 }

dataValue20_153 OBJECT-TYPE
SYNTAX INTEGER
MAX-ACCESS read-write
STATUS current
DESCRIPTION
"Data value."
::= { dataArray20 153 }

dataValue20_154 OBJECT-TYPE
SYNTAX INTEGER
MAX-ACCESS read-write
STATUS current
DESCRIPTION
"Data value."
::= { dataArray20 154 }

dataValue20_155 OBJECT-TYPE
SYNTAX INTEGER
MAX-ACCESS read-write
STATUS current
DESCRIPTION
"Data value."
::= { dataArray20 155 }

dataValue20_156 OBJECT-TYPE
SYNTAX INTEGER
MAX-ACCESS read-write
STATUS current
DESCRIPTION
"Data value."
::= { dataArray20 156 }

dataValue20_157 OBJECT-TYPE
SYNTAX INTEGER
MAX-ACCESS read-write
STATUS current
DESCRIPTION
"Data value."
::= { dataArray20 157 }

dataValue20_158 OBJECT-TYPE
SYNTAX INTEGER
MAX-ACCESS read-write
STATUS current
DESCRIPTION
"Data value."
::= { dataArray20 158 }

dataValue20_159 OBJECT-TYPE
SYNTAX INTEGER
MAX-ACCESS read-write
STATUS current
DESCRIPTION
"Data value."
::= { dataArray20 159 }

dataValue20_160 OBJECT-TYPE
SYNTAX INTEGER
MAX-ACCESS read-write
STATUS current
DESCRIPTION
"Data value."
::= { dataArray20 160 }

dataValue20_161 OBJECT-TYPE
SYNTAX INTEGER
MAX-ACCESS read-write
STATUS current
DESCRIPTION
"Data value."
::= { dataArray20 161 }

dataValue20_162 OBJECT-TYPE
SYNTAX INTEGER
MAX-ACCESS read-write
STATUS current
DESCRIPTION
"Data value."
::= { dataArray20 162 }

dataValue20_163 OBJECT-TYPE
SYNTAX INTEGER
MAX-ACCESS read-write
STATUS current
DESCRIPTION
"Data value."
::= { dataArray20 163 }

dataValue20_164 OBJECT-TYPE
SYNTAX INTEGER
MAX-ACCESS read-write
STATUS current
DESCRIPTION
"Data value."
::= { dataArray20 164 }

dataValue20_165 OBJECT-TYPE
SYNTAX INTEGER
MAX-ACCESS read-write
STATUS current
DESCRIPTION
"Data value."
::= { dataArray20 165 }

dataValue20_166 OBJECT-TYPE
SYNTAX INTEGER
MAX-ACCESS read-write
STATUS current
DESCRIPTION
"Data value."
::= { dataArray20 166 }

dataValue20_167 OBJECT-TYPE
SYNTAX INTEGER
MAX-ACCESS read-write
STATUS current
DESCRIPTION
"Data value."
::= { dataArray20 167 }

dataValue20_168 OBJECT-TYPE
SYNTAX INTEGER
MAX-ACCESS read-write
STATUS current
DESCRIPTION
"Data value."
::= { dataArray20 168 }

dataValue20_169 OBJECT-TYPE
SYNTAX INTEGER
MAX-ACCESS read-write
STATUS current
DESCRIPTION
"Data value."
::= { dataArray20 169 }

dataValue20_170 OBJECT-TYPE
SYNTAX INTEGER
MAX-ACCESS read-write
STATUS current
DESCRIPTION
"Data value."
::= { dataArray20 170 }

dataValue20_171 OBJECT-TYPE
SYNTAX INTEGER
MAX-ACCESS read-write
STATUS current
DESCRIPTION
"Data value."
::= { dataArray20 171 }

dataValue20_172 OBJECT-TYPE
SYNTAX INTEGER
MAX-ACCESS read-write
STATUS current
DESCRIPTION
"Data value."
::= { dataArray20 172 }

dataValue20_173 OBJECT-TYPE
SYNTAX INTEGER
MAX-ACCESS read-write
STATUS current
DESCRIPTION
"Data value."
::= { dataArray20 173 }

dataValue20_174 OBJECT-TYPE
SYNTAX INTEGER
MAX-ACCESS read-write
STATUS current
DESCRIPTION
"Data value."
::= { dataArray20 174 }

dataValue20_175 OBJECT-TYPE
SYNTAX INTEGER
MAX-ACCESS read-write
STATUS current
DESCRIPTION
"Data value."
::= { dataArray20 175 }

dataValue20_176 OBJECT-TYPE
SYNTAX INTEGER
MAX-ACCESS read-write
STATUS current
DESCRIPTION
"Data value."
::= { dataArray20 176 }

dataValue20_177 OBJECT-TYPE
SYNTAX INTEGER
MAX-ACCESS read-write
STATUS current
DESCRIPTION
"Data value."
::= { dataArray20 177 }

dataValue20_178 OBJECT-TYPE
SYNTAX INTEGER
MAX-ACCESS read-write
STATUS current
DESCRIPTION
"Data value."
::= { dataArray20 178 }

dataValue20_179 OBJECT-TYPE
SYNTAX INTEGER
MAX-ACCESS read-write
STATUS current
DESCRIPTION
"Data value."
::= { dataArray20 179 }

dataValue20_180 OBJECT-TYPE
SYNTAX INTEGER
MAX-ACCESS read-write
STATUS current
DESCRIPTION
"Data value."
::= { dataArray20 180 }

dataValue20_181 OBJECT-TYPE
SYNTAX INTEGER
MAX-ACCESS read-write
STATUS current
DESCRIPTION
"Data value."
::= { dataArray20 181 }

dataValue20_182 OBJECT-TYPE
SYNTAX INTEGER
MAX-ACCESS read-write
STATUS current
DESCRIPTION
"Data value."
::= { dataArray20 182 }

dataValue20_183 OBJECT-TYPE
SYNTAX INTEGER
MAX-ACCESS read-write
STATUS current
DESCRIPTION
"Data value."
::= { dataArray20 183 }

dataValue20_184 OBJECT-TYPE
SYNTAX INTEGER
MAX-ACCESS read-write
STATUS current
DESCRIPTION
"Data value."
::= { dataArray20 184 }

dataValue20_185 OBJECT-TYPE
SYNTAX INTEGER
MAX-ACCESS read-write
STATUS current
DESCRIPTION
"Data value."
::= { dataArray20 185 }

dataValue20_186 OBJECT-TYPE
SYNTAX INTEGER
MAX-ACCESS read-write
STATUS current
DESCRIPTION
"Data value."
::= { dataArray20 186 }

dataValue20_187 OBJECT-TYPE
SYNTAX INTEGER
MAX-ACCESS read-write
STATUS current
DESCRIPTION
"Data value."
::= { dataArray20 187 }

dataValue20_188 OBJECT-TYPE
SYNTAX INTEGER
MAX-ACCESS read-write
STATUS current
DESCRIPTION
"Data value."
::= { dataArray20 188 }

dataValue20_189 OBJECT-TYPE
SYNTAX INTEGER
MAX-ACCESS read-write
STATUS current
DESCRIPTION
"Data value."
::= { dataArray20 189 }

dataValue20_190 OBJECT-TYPE
SYNTAX INTEGER
MAX-ACCESS read-write
STATUS current
DESCRIPTION
"Data value."
::= { dataArray20 190 }

dataValue20_191 OBJECT-TYPE
SYNTAX INTEGER
MAX-ACCESS read-write
STATUS current
DESCRIPTION
"Data value."
::= { dataArray20 191 }

dataValue20_192 OBJECT-TYPE
SYNTAX INTEGER
MAX-ACCESS read-write
STATUS current
DESCRIPTION
"Data value."
::= { dataArray20 192 }

dataValue20_193 OBJECT-TYPE
SYNTAX INTEGER
MAX-ACCESS read-write
STATUS current
DESCRIPTION
"Data value."
::= { dataArray20 193 }

dataValue20_194 OBJECT-TYPE
SYNTAX INTEGER
MAX-ACCESS read-write
STATUS current
DESCRIPTION
"Data value."
::= { dataArray20 194 }

dataValue20_195 OBJECT-TYPE
SYNTAX INTEGER
MAX-ACCESS read-write
STATUS current
DESCRIPTION
"Data value."
::= { dataArray20 195 }

dataValue20_196 OBJECT-TYPE
SYNTAX INTEGER
MAX-ACCESS read-write
STATUS current
DESCRIPTION
"Data value."
::= { dataArray20 196 }

dataValue20_197 OBJECT-TYPE
SYNTAX INTEGER
MAX-ACCESS read-write
STATUS current
DESCRIPTION
"Data value."
::= { dataArray20 197 }

dataValue20_198 OBJECT-TYPE
SYNTAX INTEGER
MAX-ACCESS read-write
STATUS current
DESCRIPTION
"Data value."
::= { dataArray20 198 }

dataValue20_199 OBJECT-TYPE
SYNTAX INTEGER
MAX-ACCESS read-write
STATUS current
DESCRIPTION
"Data value."
::= { dataArray20 199 }

dataValue20_200 OBJECT-TYPE
SYNTAX INTEGER
MAX-ACCESS read-write
STATUS current
DESCRIPTION
"Data value."
::= { dataArray20 200 }

dataValue20_201 OBJECT-TYPE
SYNTAX INTEGER
MAX-ACCESS read-write
STATUS current
DESCRIPTION
"Data value."
::= { dataArray20 201 }

dataValue20_202 OBJECT-TYPE
SYNTAX INTEGER
MAX-ACCESS read-write
STATUS current
DESCRIPTION
"Data value."
::= { dataArray20 202 }

dataValue20_203 OBJECT-TYPE
SYNTAX INTEGER
MAX-ACCESS read-write
STATUS current
DESCRIPTION
"Data value."
::= { dataArray20 203 }

dataValue20_204 OBJECT-TYPE
SYNTAX INTEGER
MAX-ACCESS read-write
STATUS current
DESCRIPTION
"Data value."
::= { dataArray20 204 }

dataValue20_205 OBJECT-TYPE
SYNTAX INTEGER
MAX-ACCESS read-write
STATUS current
DESCRIPTION
"Data value."
::= { dataArray20 205 }

dataValue20_206 OBJECT-TYPE
SYNTAX INTEGER
MAX-ACCESS read-write
STATUS current
DESCRIPTION
"Data value."
::= { dataArray20 206 }

dataValue20_207 OBJECT-TYPE
SYNTAX INTEGER
MAX-ACCESS read-write
STATUS current
DESCRIPTION
"Data value."
::= { dataArray20 207 }

dataValue20_208 OBJECT-TYPE
SYNTAX INTEGER
MAX-ACCESS read-write
STATUS current
DESCRIPTION
"Data value."
::= { dataArray20 208 }

dataValue20_209 OBJECT-TYPE
SYNTAX INTEGER
MAX-ACCESS read-write
STATUS current
DESCRIPTION
"Data value."
::= { dataArray20 209 }

dataValue20_210 OBJECT-TYPE
SYNTAX INTEGER
MAX-ACCESS read-write
STATUS current
DESCRIPTION
"Data value."
::= { dataArray20 210 }

dataValue20_211 OBJECT-TYPE
SYNTAX INTEGER
MAX-ACCESS read-write
STATUS current
DESCRIPTION
"Data value."
::= { dataArray20 211 }

dataValue20_212 OBJECT-TYPE
SYNTAX INTEGER
MAX-ACCESS read-write
STATUS current
DESCRIPTION
"Data value."
::= { dataArray20 212 }

dataValue20_213 OBJECT-TYPE
SYNTAX INTEGER
MAX-ACCESS read-write
STATUS current
DESCRIPTION
"Data value."
::= { dataArray20 213 }

dataValue20_214 OBJECT-TYPE
SYNTAX INTEGER
MAX-ACCESS read-write
STATUS current
DESCRIPTION
"Data value."
::= { dataArray20 214 }

dataValue20_215 OBJECT-TYPE
SYNTAX INTEGER
MAX-ACCESS read-write
STATUS current
DESCRIPTION
"Data value."
::= { dataArray20 215 }

dataValue20_216 OBJECT-TYPE
SYNTAX INTEGER
MAX-ACCESS read-write
STATUS current
DESCRIPTION
"Data value."
::= { dataArray20 216 }

dataValue20_217 OBJECT-TYPE
SYNTAX INTEGER
MAX-ACCESS read-write
STATUS current
DESCRIPTION
"Data value."
::= { dataArray20 217 }

dataValue20_218 OBJECT-TYPE
SYNTAX INTEGER
MAX-ACCESS read-write
STATUS current
DESCRIPTION
"Data value."
::= { dataArray20 218 }

dataValue20_219 OBJECT-TYPE
SYNTAX INTEGER
MAX-ACCESS read-write
STATUS current
DESCRIPTION
"Data value."
::= { dataArray20 219 }

dataValue20_220 OBJECT-TYPE
SYNTAX INTEGER
MAX-ACCESS read-write
STATUS current
DESCRIPTION
"Data value."
::= { dataArray20 220 }

dataValue20_221 OBJECT-TYPE
SYNTAX INTEGER
MAX-ACCESS read-write
STATUS current
DESCRIPTION
"Data value."
::= { dataArray20 221 }

dataValue20_222 OBJECT-TYPE
SYNTAX INTEGER
MAX-ACCESS read-write
STATUS current
DESCRIPTION
"Data value."
::= { dataArray20 222 }

dataValue20_223 OBJECT-TYPE
SYNTAX INTEGER
MAX-ACCESS read-write
STATUS current
DESCRIPTION
"Data value."
::= { dataArray20 223 }

dataValue20_224 OBJECT-TYPE
SYNTAX INTEGER
MAX-ACCESS read-write
STATUS current
DESCRIPTION
"Data value."
::= { dataArray20 224 }

dataValue20_225 OBJECT-TYPE
SYNTAX INTEGER
MAX-ACCESS read-write
STATUS current
DESCRIPTION
"Data value."
::= { dataArray20 225 }

dataValue20_226 OBJECT-TYPE
SYNTAX INTEGER
MAX-ACCESS read-write
STATUS current
DESCRIPTION
"Data value."
::= { dataArray20 226 }

dataValue20_227 OBJECT-TYPE
SYNTAX INTEGER
MAX-ACCESS read-write
STATUS current
DESCRIPTION
"Data value."
::= { dataArray20 227 }

dataValue20_228 OBJECT-TYPE
SYNTAX INTEGER
MAX-ACCESS read-write
STATUS current
DESCRIPTION
"Data value."
::= { dataArray20 228 }

dataValue20_229 OBJECT-TYPE
SYNTAX INTEGER
MAX-ACCESS read-write
STATUS current
DESCRIPTION
"Data value."
::= { dataArray20 229 }

dataValue20_230 OBJECT-TYPE
SYNTAX INTEGER
MAX-ACCESS read-write
STATUS current
DESCRIPTION
"Data value."
::= { dataArray20 230 }

dataValue20_231 OBJECT-TYPE
SYNTAX INTEGER
MAX-ACCESS read-write
STATUS current
DESCRIPTION
"Data value."
::= { dataArray20 231 }

dataValue20_232 OBJECT-TYPE
SYNTAX INTEGER
MAX-ACCESS read-write
STATUS current
DESCRIPTION
"Data value."
::= { dataArray20 232 }

dataValue20_233 OBJECT-TYPE
SYNTAX INTEGER
MAX-ACCESS read-write
STATUS current
DESCRIPTION
"Data value."
::= { dataArray20 233 }

dataValue20_234 OBJECT-TYPE
SYNTAX INTEGER
MAX-ACCESS read-write
STATUS current
DESCRIPTION
"Data value."
::= { dataArray20 234 }

dataValue20_235 OBJECT-TYPE
SYNTAX INTEGER
MAX-ACCESS read-write
STATUS current
DESCRIPTION
"Data value."
::= { dataArray20 235 }

dataValue20_236 OBJECT-TYPE
SYNTAX INTEGER
MAX-ACCESS read-write
STATUS current
DESCRIPTION
"Data value."
::= { dataArray20 236 }

dataValue20_237 OBJECT-TYPE
SYNTAX INTEGER
MAX-ACCESS read-write
STATUS current
DESCRIPTION
"Data value."
::= { dataArray20 237 }

dataValue20_238 OBJECT-TYPE
SYNTAX INTEGER
MAX-ACCESS read-write
STATUS current
DESCRIPTION
"Data value."
::= { dataArray20 238 }

dataValue20_239 OBJECT-TYPE
SYNTAX INTEGER
MAX-ACCESS read-write
STATUS current
DESCRIPTION
"Data value."
::= { dataArray20 239 }

dataValue20_240 OBJECT-TYPE
SYNTAX INTEGER
MAX-ACCESS read-write
STATUS current
DESCRIPTION
"Data value."
::= { dataArray20 240 }

dataValue20_241 OBJECT-TYPE
SYNTAX INTEGER
MAX-ACCESS read-write
STATUS current
DESCRIPTION
"Data value."
::= { dataArray20 241 }

dataValue20_242 OBJECT-TYPE
SYNTAX INTEGER
MAX-ACCESS read-write
STATUS current
DESCRIPTION
"Data value."
::= { dataArray20 242 }

dataValue20_243 OBJECT-TYPE
SYNTAX INTEGER
MAX-ACCESS read-write
STATUS current
DESCRIPTION
"Data value."
::= { dataArray20 243 }

dataValue20_244 OBJECT-TYPE
SYNTAX INTEGER
MAX-ACCESS read-write
STATUS current
DESCRIPTION
"Data value."
::= { dataArray20 244 }

dataValue20_245 OBJECT-TYPE
SYNTAX INTEGER
MAX-ACCESS read-write
STATUS current
DESCRIPTION
"Data value."
::= { dataArray20 245 }

dataValue20_246 OBJECT-TYPE
SYNTAX INTEGER
MAX-ACCESS read-write
STATUS current
DESCRIPTION
"Data value."
::= { dataArray20 246 }

dataValue20_247 OBJECT-TYPE
SYNTAX INTEGER
MAX-ACCESS read-write
STATUS current
DESCRIPTION
"Data value."
::= { dataArray20 247 }

dataValue20_248 OBJECT-TYPE
SYNTAX INTEGER
MAX-ACCESS read-write
STATUS current
DESCRIPTION
"Data value."
::= { dataArray20 248 }

dataValue20_249 OBJECT-TYPE
SYNTAX INTEGER
MAX-ACCESS read-write
STATUS current
DESCRIPTION
"Data value."
::= { dataArray20 249 }

dataValue20_250 OBJECT-TYPE
SYNTAX INTEGER
MAX-ACCESS read-write
STATUS current
DESCRIPTION
"Data value."
::= { dataArray20 250 }

dataValue20_251 OBJECT-TYPE
SYNTAX INTEGER
MAX-ACCESS read-write
STATUS current
DESCRIPTION
"Data value."
::= { dataArray20 251 }

dataValue20_252 OBJECT-TYPE
SYNTAX INTEGER
MAX-ACCESS read-write
STATUS current
DESCRIPTION
"Data value."
::= { dataArray20 252 }

dataValue20_253 OBJECT-TYPE
SYNTAX INTEGER
MAX-ACCESS read-write
STATUS current
DESCRIPTION
"Data value."
::= { dataArray20 253 }

dataValue20_254 OBJECT-TYPE
SYNTAX INTEGER
MAX-ACCESS read-write
STATUS current
DESCRIPTION
"Data value."
::= { dataArray20 254 }

dataValue20_255 OBJECT-TYPE
SYNTAX INTEGER
MAX-ACCESS read-write
STATUS current
DESCRIPTION
"Data value."
::= { dataArray20 255 }

dataValue20_256 OBJECT-TYPE
SYNTAX INTEGER
MAX-ACCESS read-write
STATUS current
DESCRIPTION
"Data value."
::= { dataArray20 256 }

dataValue20_257 OBJECT-TYPE
SYNTAX INTEGER
MAX-ACCESS read-write
STATUS current
DESCRIPTION
"Data value."
::= { dataArray20 257 }

dataValue20_258 OBJECT-TYPE
SYNTAX INTEGER
MAX-ACCESS read-write
STATUS current
DESCRIPTION
"Data value."
::= { dataArray20 258 }

dataValue20_259 OBJECT-TYPE
SYNTAX INTEGER
MAX-ACCESS read-write
STATUS current
DESCRIPTION
"Data value."
::= { dataArray20 259 }

dataValue20_260 OBJECT-TYPE
SYNTAX INTEGER
MAX-ACCESS read-write
STATUS current
DESCRIPTION
"Data value."
::= { dataArray20 260 }

dataValue20_261 OBJECT-TYPE
SYNTAX INTEGER
MAX-ACCESS read-write
STATUS current
DESCRIPTION
"Data value."
::= { dataArray20 261 }

dataValue20_262 OBJECT-TYPE
SYNTAX INTEGER
MAX-ACCESS read-write
STATUS current
DESCRIPTION
"Data value."
::= { dataArray20 262 }

dataValue20_263 OBJECT-TYPE
SYNTAX INTEGER
MAX-ACCESS read-write
STATUS current
DESCRIPTION
"Data value."
::= { dataArray20 263 }

dataValue20_264 OBJECT-TYPE
SYNTAX INTEGER
MAX-ACCESS read-write
STATUS current
DESCRIPTION
"Data value."
::= { dataArray20 264 }

dataValue20_265 OBJECT-TYPE
SYNTAX INTEGER
MAX-ACCESS read-write
STATUS current
DESCRIPTION
"Data value."
::= { dataArray20 265 }

dataValue20_266 OBJECT-TYPE
SYNTAX INTEGER
MAX-ACCESS read-write
STATUS current
DESCRIPTION
"Data value."
::= { dataArray20 266 }

dataValue20_267 OBJECT-TYPE
SYNTAX INTEGER
MAX-ACCESS read-write
STATUS current
DESCRIPTION
"Data value."
::= { dataArray20 267 }

dataValue20_268 OBJECT-TYPE
SYNTAX INTEGER
MAX-ACCESS read-write
STATUS current
DESCRIPTION
"Data value."
::= { dataArray20 268 }

dataValue20_269 OBJECT-TYPE
SYNTAX INTEGER
MAX-ACCESS read-write
STATUS current
DESCRIPTION
"Data value."
::= { dataArray20 269 }

dataValue20_270 OBJECT-TYPE
SYNTAX INTEGER
MAX-ACCESS read-write
STATUS current
DESCRIPTION
"Data value."
::= { dataArray20 270 }

dataValue20_271 OBJECT-TYPE
SYNTAX INTEGER
MAX-ACCESS read-write
STATUS current
DESCRIPTION
"Data value."
::= { dataArray20 271 }

dataValue20_272 OBJECT-TYPE
SYNTAX INTEGER
MAX-ACCESS read-write
STATUS current
DESCRIPTION
"Data value."
::= { dataArray20 272 }

dataValue20_273 OBJECT-TYPE
SYNTAX INTEGER
MAX-ACCESS read-write
STATUS current
DESCRIPTION
"Data value."
::= { dataArray20 273 }

dataValue20_274 OBJECT-TYPE
SYNTAX INTEGER
MAX-ACCESS read-write
STATUS current
DESCRIPTION
"Data value."
::= { dataArray20 274 }

dataValue20_275 OBJECT-TYPE
SYNTAX INTEGER
MAX-ACCESS read-write
STATUS current
DESCRIPTION
"Data value."
::= { dataArray20 275 }

dataValue20_276 OBJECT-TYPE
SYNTAX INTEGER
MAX-ACCESS read-write
STATUS current
DESCRIPTION
"Data value."
::= { dataArray20 276 }

dataValue20_277 OBJECT-TYPE
SYNTAX INTEGER
MAX-ACCESS read-write
STATUS current
DESCRIPTION
"Data value."
::= { dataArray20 277 }

dataValue20_278 OBJECT-TYPE
SYNTAX INTEGER
MAX-ACCESS read-write
STATUS current
DESCRIPTION
"Data value."
::= { dataArray20 278 }

dataValue20_279 OBJECT-TYPE
SYNTAX INTEGER
MAX-ACCESS read-write
STATUS current
DESCRIPTION
"Data value."
::= { dataArray20 279 }

dataValue20_280 OBJECT-TYPE
SYNTAX INTEGER
MAX-ACCESS read-write
STATUS current
DESCRIPTION
"Data value."
::= { dataArray20 280 }

dataValue20_281 OBJECT-TYPE
SYNTAX INTEGER
MAX-ACCESS read-write
STATUS current
DESCRIPTION
"Data value."
::= { dataArray20 281 }

dataValue20_282 OBJECT-TYPE
SYNTAX INTEGER
MAX-ACCESS read-write
STATUS current
DESCRIPTION
"Data value."
::= { dataArray20 282 }

dataValue20_283 OBJECT-TYPE
SYNTAX INTEGER
MAX-ACCESS read-write
STATUS current
DESCRIPTION
"Data value."
::= { dataArray20 283 }

dataValue20_284 OBJECT-TYPE
SYNTAX INTEGER
MAX-ACCESS read-write
STATUS current
DESCRIPTION
"Data value."
::= { dataArray20 284 }

dataValue20_285 OBJECT-TYPE
SYNTAX INTEGER
MAX-ACCESS read-write
STATUS current
DESCRIPTION
"Data value."
::= { dataArray20 285 }

dataValue20_286 OBJECT-TYPE
SYNTAX INTEGER
MAX-ACCESS read-write
STATUS current
DESCRIPTION
"Data value."
::= { dataArray20 286 }

dataValue20_287 OBJECT-TYPE
SYNTAX INTEGER
MAX-ACCESS read-write
STATUS current
DESCRIPTION
"Data value."
::= { dataArray20 287 }

dataValue20_288 OBJECT-TYPE
SYNTAX INTEGER
MAX-ACCESS read-write
STATUS current
DESCRIPTION
"Data value."
::= { dataArray20 288 }

dataValue20_289 OBJECT-TYPE
SYNTAX INTEGER
MAX-ACCESS read-write
STATUS current
DESCRIPTION
"Data value."
::= { dataArray20 289 }

dataValue20_290 OBJECT-TYPE
SYNTAX INTEGER
MAX-ACCESS read-write
STATUS current
DESCRIPTION
"Data value."
::= { dataArray20 290 }

dataValue20_291 OBJECT-TYPE
SYNTAX INTEGER
MAX-ACCESS read-write
STATUS current
DESCRIPTION
"Data value."
::= { dataArray20 291 }

dataValue20_292 OBJECT-TYPE
SYNTAX INTEGER
MAX-ACCESS read-write
STATUS current
DESCRIPTION
"Data value."
::= { dataArray20 292 }

dataValue20_293 OBJECT-TYPE
SYNTAX INTEGER
MAX-ACCESS read-write
STATUS current
DESCRIPTION
"Data value."
::= { dataArray20 293 }

dataValue20_294 OBJECT-TYPE
SYNTAX INTEGER
MAX-ACCESS read-write
STATUS current
DESCRIPTION
"Data value."
::= { dataArray20 294 }

dataValue20_295 OBJECT-TYPE
SYNTAX INTEGER
MAX-ACCESS read-write
STATUS current
DESCRIPTION
"Data value."
::= { dataArray20 295 }

dataValue20_296 OBJECT-TYPE
SYNTAX INTEGER
MAX-ACCESS read-write
STATUS current
DESCRIPTION
"Data value."
::= { dataArray20 296 }

dataValue20_297 OBJECT-TYPE
SYNTAX INTEGER
MAX-ACCESS read-write
STATUS current
DESCRIPTION
"Data value."
::= { dataArray20 297 }

dataValue20_298 OBJECT-TYPE
SYNTAX INTEGER
MAX-ACCESS read-write
STATUS current
DESCRIPTION
"Data value."
::= { dataArray20 298 }

dataValue20_299 OBJECT-TYPE
SYNTAX INTEGER
MAX-ACCESS read-write
STATUS current
DESCRIPTION
"Data value."
::= { dataArray20 299 }

dataValue20_300 OBJECT-TYPE
SYNTAX INTEGER
MAX-ACCESS read-write
STATUS current
DESCRIPTION
"Data value."
::= { dataArray20 300 }

dataValue20_301 OBJECT-TYPE
SYNTAX INTEGER
MAX-ACCESS read-write
STATUS current
DESCRIPTION
"Data value."
::= { dataArray20 301 }

dataValue20_302 OBJECT-TYPE
SYNTAX INTEGER
MAX-ACCESS read-write
STATUS current
DESCRIPTION
"Data value."
::= { dataArray20 302 }

dataValue20_303 OBJECT-TYPE
SYNTAX INTEGER
MAX-ACCESS read-write
STATUS current
DESCRIPTION
"Data value."
::= { dataArray20 303 }

dataValue20_304 OBJECT-TYPE
SYNTAX INTEGER
MAX-ACCESS read-write
STATUS current
DESCRIPTION
"Data value."
::= { dataArray20 304 }

dataValue20_305 OBJECT-TYPE
SYNTAX INTEGER
MAX-ACCESS read-write
STATUS current
DESCRIPTION
"Data value."
::= { dataArray20 305 }

dataValue20_306 OBJECT-TYPE
SYNTAX INTEGER
MAX-ACCESS read-write
STATUS current
DESCRIPTION
"Data value."
::= { dataArray20 306 }

dataValue20_307 OBJECT-TYPE
SYNTAX INTEGER
MAX-ACCESS read-write
STATUS current
DESCRIPTION
"Data value."
::= { dataArray20 307 }

dataValue20_308 OBJECT-TYPE
SYNTAX INTEGER
MAX-ACCESS read-write
STATUS current
DESCRIPTION
"Data value."
::= { dataArray20 308 }

dataValue20_309 OBJECT-TYPE
SYNTAX INTEGER
MAX-ACCESS read-write
STATUS current
DESCRIPTION
"Data value."
::= { dataArray20 309 }

dataValue20_310 OBJECT-TYPE
SYNTAX INTEGER
MAX-ACCESS read-write
STATUS current
DESCRIPTION
"Data value."
::= { dataArray20 310 }

dataValue20_311 OBJECT-TYPE
SYNTAX INTEGER
MAX-ACCESS read-write
STATUS current
DESCRIPTION
"Data value."
::= { dataArray20 311 }

dataValue20_312 OBJECT-TYPE
SYNTAX INTEGER
MAX-ACCESS read-write
STATUS current
DESCRIPTION
"Data value."
::= { dataArray20 312 }

dataValue20_313 OBJECT-TYPE
SYNTAX INTEGER
MAX-ACCESS read-write
STATUS current
DESCRIPTION
"Data value."
::= { dataArray20 313 }

dataValue20_314 OBJECT-TYPE
SYNTAX INTEGER
MAX-ACCESS read-write
STATUS current
DESCRIPTION
"Data value."
::= { dataArray20 314 }

dataValue20_315 OBJECT-TYPE
SYNTAX INTEGER
MAX-ACCESS read-write
STATUS current
DESCRIPTION
"Data value."
::= { dataArray20 315 }

dataValue20_316 OBJECT-TYPE
SYNTAX INTEGER
MAX-ACCESS read-write
STATUS current
DESCRIPTION
"Data value."
::= { dataArray20 316 }

dataValue20_317 OBJECT-TYPE
SYNTAX INTEGER
MAX-ACCESS read-write
STATUS current
DESCRIPTION
"Data value."
::= { dataArray20 317 }

dataValue20_318 OBJECT-TYPE
SYNTAX INTEGER
MAX-ACCESS read-write
STATUS current
DESCRIPTION
"Data value."
::= { dataArray20 318 }

dataValue20_319 OBJECT-TYPE
SYNTAX INTEGER
MAX-ACCESS read-write
STATUS current
DESCRIPTION
"Data value."
::= { dataArray20 319 }

dataValue20_320 OBJECT-TYPE
SYNTAX INTEGER
MAX-ACCESS read-write
STATUS current
DESCRIPTION
"Data value."
::= { dataArray20 320 }

dataValue20_321 OBJECT-TYPE
SYNTAX INTEGER
MAX-ACCESS read-write
STATUS current
DESCRIPTION
"Data value."
::= { dataArray20 321 }

dataValue20_322 OBJECT-TYPE
SYNTAX INTEGER
MAX-ACCESS read-write
STATUS current
DESCRIPTION
"Data value."
::= { dataArray20 322 }

dataValue20_323 OBJECT-TYPE
SYNTAX INTEGER
MAX-ACCESS read-write
STATUS current
DESCRIPTION
"Data value."
::= { dataArray20 323 }

dataValue20_324 OBJECT-TYPE
SYNTAX INTEGER
MAX-ACCESS read-write
STATUS current
DESCRIPTION
"Data value."
::= { dataArray20 324 }

dataValue20_325 OBJECT-TYPE
SYNTAX INTEGER
MAX-ACCESS read-write
STATUS current
DESCRIPTION
"Data value."
::= { dataArray20 325 }

dataValue20_326 OBJECT-TYPE
SYNTAX INTEGER
MAX-ACCESS read-write
STATUS current
DESCRIPTION
"Data value."
::= { dataArray20 326 }

dataValue20_327 OBJECT-TYPE
SYNTAX INTEGER
MAX-ACCESS read-write
STATUS current
DESCRIPTION
"Data value."
::= { dataArray20 327 }

dataValue20_328 OBJECT-TYPE
SYNTAX INTEGER
MAX-ACCESS read-write
STATUS current
DESCRIPTION
"Data value."
::= { dataArray20 328 }

dataValue20_329 OBJECT-TYPE
SYNTAX INTEGER
MAX-ACCESS read-write
STATUS current
DESCRIPTION
"Data value."
::= { dataArray20 329 }

dataValue20_330 OBJECT-TYPE
SYNTAX INTEGER
MAX-ACCESS read-write
STATUS current
DESCRIPTION
"Data value."
::= { dataArray20 330 }

dataValue20_331 OBJECT-TYPE
SYNTAX INTEGER
MAX-ACCESS read-write
STATUS current
DESCRIPTION
"Data value."
::= { dataArray20 331 }

dataValue20_332 OBJECT-TYPE
SYNTAX INTEGER
MAX-ACCESS read-write
STATUS current
DESCRIPTION
"Data value."
::= { dataArray20 332 }

dataValue20_333 OBJECT-TYPE
SYNTAX INTEGER
MAX-ACCESS read-write
STATUS current
DESCRIPTION
"Data value."
::= { dataArray20 333 }

dataValue20_334 OBJECT-TYPE
SYNTAX INTEGER
MAX-ACCESS read-write
STATUS current
DESCRIPTION
"Data value."
::= { dataArray20 334 }

dataValue20_335 OBJECT-TYPE
SYNTAX INTEGER
MAX-ACCESS read-write
STATUS current
DESCRIPTION
"Data value."
::= { dataArray20 335 }

dataValue20_336 OBJECT-TYPE
SYNTAX INTEGER
MAX-ACCESS read-write
STATUS current
DESCRIPTION
"Data value."
::= { dataArray20 336 }

dataValue20_337 OBJECT-TYPE
SYNTAX INTEGER
MAX-ACCESS read-write
STATUS current
DESCRIPTION
"Data value."
::= { dataArray20 337 }

dataValue20_338 OBJECT-TYPE
SYNTAX INTEGER
MAX-ACCESS read-write
STATUS current
DESCRIPTION
"Data value."
::= { dataArray20 338 }

dataValue20_339 OBJECT-TYPE
SYNTAX INTEGER
MAX-ACCESS read-write
STATUS current
DESCRIPTION
"Data value."
::= { dataArray20 339 }

dataValue20_340 OBJECT-TYPE
SYNTAX INTEGER
MAX-ACCESS read-write
STATUS current
DESCRIPTION
"Data value."
::= { dataArray20 340 }

dataValue20_341 OBJECT-TYPE
SYNTAX INTEGER
MAX-ACCESS read-write
STATUS current
DESCRIPTION
"Data value."
::= { dataArray20 341 }

dataValue20_342 OBJECT-TYPE
SYNTAX INTEGER
MAX-ACCESS read-write
STATUS current
DESCRIPTION
"Data value."
::= { dataArray20 342 }

dataValue20_343 OBJECT-TYPE
SYNTAX INTEGER
MAX-ACCESS read-write
STATUS current
DESCRIPTION
"Data value."
::= { dataArray20 343 }

dataValue20_344 OBJECT-TYPE
SYNTAX INTEGER
MAX-ACCESS read-write
STATUS current
DESCRIPTION
"Data value."
::= { dataArray20 344 }

dataValue20_345 OBJECT-TYPE
SYNTAX INTEGER
MAX-ACCESS read-write
STATUS current
DESCRIPTION
"Data value."
::= { dataArray20 345 }

dataValue20_346 OBJECT-TYPE
SYNTAX INTEGER
MAX-ACCESS read-write
STATUS current
DESCRIPTION
"Data value."
::= { dataArray20 346 }

dataValue20_347 OBJECT-TYPE
SYNTAX INTEGER
MAX-ACCESS read-write
STATUS current
DESCRIPTION
"Data value."
::= { dataArray20 347 }

dataValue20_348 OBJECT-TYPE
SYNTAX INTEGER
MAX-ACCESS read-write
STATUS current
DESCRIPTION
"Data value."
::= { dataArray20 348 }

dataValue20_349 OBJECT-TYPE
SYNTAX INTEGER
MAX-ACCESS read-write
STATUS current
DESCRIPTION
"Data value."
::= { dataArray20 349 }

dataValue20_350 OBJECT-TYPE
SYNTAX INTEGER
MAX-ACCESS read-write
STATUS current
DESCRIPTION
"Data value."
::= { dataArray20 350 }

dataValue20_351 OBJECT-TYPE
SYNTAX INTEGER
MAX-ACCESS read-write
STATUS current
DESCRIPTION
"Data value."
::= { dataArray20 351 }

dataValue20_352 OBJECT-TYPE
SYNTAX INTEGER
MAX-ACCESS read-write
STATUS current
DESCRIPTION
"Data value."
::= { dataArray20 352 }

dataValue20_353 OBJECT-TYPE
SYNTAX INTEGER
MAX-ACCESS read-write
STATUS current
DESCRIPTION
"Data value."
::= { dataArray20 353 }

dataValue20_354 OBJECT-TYPE
SYNTAX INTEGER
MAX-ACCESS read-write
STATUS current
DESCRIPTION
"Data value."
::= { dataArray20 354 }

dataValue20_355 OBJECT-TYPE
SYNTAX INTEGER
MAX-ACCESS read-write
STATUS current
DESCRIPTION
"Data value."
::= { dataArray20 355 }

dataValue20_356 OBJECT-TYPE
SYNTAX INTEGER
MAX-ACCESS read-write
STATUS current
DESCRIPTION
"Data value."
::= { dataArray20 356 }

dataValue20_357 OBJECT-TYPE
SYNTAX INTEGER
MAX-ACCESS read-write
STATUS current
DESCRIPTION
"Data value."
::= { dataArray20 357 }

dataValue20_358 OBJECT-TYPE
SYNTAX INTEGER
MAX-ACCESS read-write
STATUS current
DESCRIPTION
"Data value."
::= { dataArray20 358 }

dataValue20_359 OBJECT-TYPE
SYNTAX INTEGER
MAX-ACCESS read-write
STATUS current
DESCRIPTION
"Data value."
::= { dataArray20 359 }

dataValue20_360 OBJECT-TYPE
SYNTAX INTEGER
MAX-ACCESS read-write
STATUS current
DESCRIPTION
"Data value."
::= { dataArray20 360 }

dataValue20_361 OBJECT-TYPE
SYNTAX INTEGER
MAX-ACCESS read-write
STATUS current
DESCRIPTION
"Data value."
::= { dataArray20 361 }

dataValue20_362 OBJECT-TYPE
SYNTAX INTEGER
MAX-ACCESS read-write
STATUS current
DESCRIPTION
"Data value."
::= { dataArray20 362 }

dataValue20_363 OBJECT-TYPE
SYNTAX INTEGER
MAX-ACCESS read-write
STATUS current
DESCRIPTION
"Data value."
::= { dataArray20 363 }

dataValue20_364 OBJECT-TYPE
SYNTAX INTEGER
MAX-ACCESS read-write
STATUS current
DESCRIPTION
"Data value."
::= { dataArray20 364 }

dataValue20_365 OBJECT-TYPE
SYNTAX INTEGER
MAX-ACCESS read-write
STATUS current
DESCRIPTION
"Data value."
::= { dataArray20 365 }

dataValue20_366 OBJECT-TYPE
SYNTAX INTEGER
MAX-ACCESS read-write
STATUS current
DESCRIPTION
"Data value."
::= { dataArray20 366 }

dataValue20_367 OBJECT-TYPE
SYNTAX INTEGER
MAX-ACCESS read-write
STATUS current
DESCRIPTION
"Data value."
::= { dataArray20 367 }

dataValue20_368 OBJECT-TYPE
SYNTAX INTEGER
MAX-ACCESS read-write
STATUS current
DESCRIPTION
"Data value."
::= { dataArray20 368 }

dataValue20_369 OBJECT-TYPE
SYNTAX INTEGER
MAX-ACCESS read-write
STATUS current
DESCRIPTION
"Data value."
::= { dataArray20 369 }

dataValue20_370 OBJECT-TYPE
SYNTAX INTEGER
MAX-ACCESS read-write
STATUS current
DESCRIPTION
"Data value."
::= { dataArray20 370 }

dataValue20_371 OBJECT-TYPE
SYNTAX INTEGER
MAX-ACCESS read-write
STATUS current
DESCRIPTION
"Data value."
::= { dataArray20 371 }

dataValue20_372 OBJECT-TYPE
SYNTAX INTEGER
MAX-ACCESS read-write
STATUS current
DESCRIPTION
"Data value."
::= { dataArray20 372 }

dataValue20_373 OBJECT-TYPE
SYNTAX INTEGER
MAX-ACCESS read-write
STATUS current
DESCRIPTION
"Data value."
::= { dataArray20 373 }

dataValue20_374 OBJECT-TYPE
SYNTAX INTEGER
MAX-ACCESS read-write
STATUS current
DESCRIPTION
"Data value."
::= { dataArray20 374 }

dataValue20_375 OBJECT-TYPE
SYNTAX INTEGER
MAX-ACCESS read-write
STATUS current
DESCRIPTION
"Data value."
::= { dataArray20 375 }

dataValue20_376 OBJECT-TYPE
SYNTAX INTEGER
MAX-ACCESS read-write
STATUS current
DESCRIPTION
"Data value."
::= { dataArray20 376 }

dataValue20_377 OBJECT-TYPE
SYNTAX INTEGER
MAX-ACCESS read-write
STATUS current
DESCRIPTION
"Data value."
::= { dataArray20 377 }

dataValue20_378 OBJECT-TYPE
SYNTAX INTEGER
MAX-ACCESS read-write
STATUS current
DESCRIPTION
"Data value."
::= { dataArray20 378 }

dataValue20_379 OBJECT-TYPE
SYNTAX INTEGER
MAX-ACCESS read-write
STATUS current
DESCRIPTION
"Data value."
::= { dataArray20 379 }

dataValue20_380 OBJECT-TYPE
SYNTAX INTEGER
MAX-ACCESS read-write
STATUS current
DESCRIPTION
"Data value."
::= { dataArray20 380 }

dataValue20_381 OBJECT-TYPE
SYNTAX INTEGER
MAX-ACCESS read-write
STATUS current
DESCRIPTION
"Data value."
::= { dataArray20 381 }

dataValue20_382 OBJECT-TYPE
SYNTAX INTEGER
MAX-ACCESS read-write
STATUS current
DESCRIPTION
"Data value."
::= { dataArray20 382 }

dataValue20_383 OBJECT-TYPE
SYNTAX INTEGER
MAX-ACCESS read-write
STATUS current
DESCRIPTION
"Data value."
::= { dataArray20 383 }

dataValue20_384 OBJECT-TYPE
SYNTAX INTEGER
MAX-ACCESS read-write
STATUS current
DESCRIPTION
"Data value."
::= { dataArray20 384 }

dataValue20_385 OBJECT-TYPE
SYNTAX INTEGER
MAX-ACCESS read-write
STATUS current
DESCRIPTION
"Data value."
::= { dataArray20 385 }

dataValue20_386 OBJECT-TYPE
SYNTAX INTEGER
MAX-ACCESS read-write
STATUS current
DESCRIPTION
"Data value."
::= { dataArray20 386 }

dataValue20_387 OBJECT-TYPE
SYNTAX INTEGER
MAX-ACCESS read-write
STATUS current
DESCRIPTION
"Data value."
::= { dataArray20 387 }

dataValue20_388 OBJECT-TYPE
SYNTAX INTEGER
MAX-ACCESS read-write
STATUS current
DESCRIPTION
"Data value."
::= { dataArray20 388 }

dataValue20_389 OBJECT-TYPE
SYNTAX INTEGER
MAX-ACCESS read-write
STATUS current
DESCRIPTION
"Data value."
::= { dataArray20 389 }

dataValue20_390 OBJECT-TYPE
SYNTAX INTEGER
MAX-ACCESS read-write
STATUS current
DESCRIPTION
"Data value."
::= { dataArray20 390 }

dataValue20_391 OBJECT-TYPE
SYNTAX INTEGER
MAX-ACCESS read-write
STATUS current
DESCRIPTION
"Data value."
::= { dataArray20 391 }

dataValue20_392 OBJECT-TYPE
SYNTAX INTEGER
MAX-ACCESS read-write
STATUS current
DESCRIPTION
"Data value."
::= { dataArray20 392 }

dataValue20_393 OBJECT-TYPE
SYNTAX INTEGER
MAX-ACCESS read-write
STATUS current
DESCRIPTION
"Data value."
::= { dataArray20 393 }

dataValue20_394 OBJECT-TYPE
SYNTAX INTEGER
MAX-ACCESS read-write
STATUS current
DESCRIPTION
"Data value."
::= { dataArray20 394 }

dataValue20_395 OBJECT-TYPE
SYNTAX INTEGER
MAX-ACCESS read-write
STATUS current
DESCRIPTION
"Data value."
::= { dataArray20 395 }

dataValue20_396 OBJECT-TYPE
SYNTAX INTEGER
MAX-ACCESS read-write
STATUS current
DESCRIPTION
"Data value."
::= { dataArray20 396 }

dataValue20_397 OBJECT-TYPE
SYNTAX INTEGER
MAX-ACCESS read-write
STATUS current
DESCRIPTION
"Data value."
::= { dataArray20 397 }

dataValue20_398 OBJECT-TYPE
SYNTAX INTEGER
MAX-ACCESS read-write
STATUS current
DESCRIPTION
"Data value."
::= { dataArray20 398 }

dataValue20_399 OBJECT-TYPE
SYNTAX INTEGER
MAX-ACCESS read-write
STATUS current
DESCRIPTION
"Data value."
::= { dataArray20 399 }

dataArray21 OBJECT IDENTIFIER ::= { cc08255400_v1_00a 21 }

dataValue21_0 OBJECT-TYPE
SYNTAX INTEGER
MAX-ACCESS read-write
STATUS current
DESCRIPTION
"Data value."
::= { dataArray21 0 }

dataValue21_1 OBJECT-TYPE
SYNTAX INTEGER
MAX-ACCESS read-write
STATUS current
DESCRIPTION
"Data value."
::= { dataArray21 1 }

dataValue21_2 OBJECT-TYPE
SYNTAX INTEGER
MAX-ACCESS read-write
STATUS current
DESCRIPTION
"Data value."
::= { dataArray21 2 }

dataValue21_3 OBJECT-TYPE
SYNTAX INTEGER
MAX-ACCESS read-write
STATUS current
DESCRIPTION
"Data value."
::= { dataArray21 3 }

dataValue21_4 OBJECT-TYPE
SYNTAX INTEGER
MAX-ACCESS read-write
STATUS current
DESCRIPTION
"Data value."
::= { dataArray21 4 }

dataValue21_5 OBJECT-TYPE
SYNTAX INTEGER
MAX-ACCESS read-write
STATUS current
DESCRIPTION
"Data value."
::= { dataArray21 5 }

dataValue21_6 OBJECT-TYPE
SYNTAX INTEGER
MAX-ACCESS read-write
STATUS current
DESCRIPTION
"Data value."
::= { dataArray21 6 }

dataValue21_7 OBJECT-TYPE
SYNTAX INTEGER
MAX-ACCESS read-write
STATUS current
DESCRIPTION
"Data value."
::= { dataArray21 7 }

dataValue21_8 OBJECT-TYPE
SYNTAX INTEGER
MAX-ACCESS read-write
STATUS current
DESCRIPTION
"Data value."
::= { dataArray21 8 }

dataValue21_9 OBJECT-TYPE
SYNTAX INTEGER
MAX-ACCESS read-write
STATUS current
DESCRIPTION
"Data value."
::= { dataArray21 9 }

dataValue21_10 OBJECT-TYPE
SYNTAX INTEGER
MAX-ACCESS read-write
STATUS current
DESCRIPTION
"Data value."
::= { dataArray21 10 }

dataValue21_11 OBJECT-TYPE
SYNTAX INTEGER
MAX-ACCESS read-write
STATUS current
DESCRIPTION
"Data value."
::= { dataArray21 11 }

dataValue21_12 OBJECT-TYPE
SYNTAX INTEGER
MAX-ACCESS read-write
STATUS current
DESCRIPTION
"Data value."
::= { dataArray21 12 }

dataValue21_13 OBJECT-TYPE
SYNTAX INTEGER
MAX-ACCESS read-write
STATUS current
DESCRIPTION
"Data value."
::= { dataArray21 13 }

dataValue21_14 OBJECT-TYPE
SYNTAX INTEGER
MAX-ACCESS read-write
STATUS current
DESCRIPTION
"Data value."
::= { dataArray21 14 }

dataValue21_15 OBJECT-TYPE
SYNTAX INTEGER
MAX-ACCESS read-write
STATUS current
DESCRIPTION
"Data value."
::= { dataArray21 15 }

dataValue21_16 OBJECT-TYPE
SYNTAX INTEGER
MAX-ACCESS read-write
STATUS current
DESCRIPTION
"Data value."
::= { dataArray21 16 }

dataValue21_17 OBJECT-TYPE
SYNTAX INTEGER
MAX-ACCESS read-write
STATUS current
DESCRIPTION
"Data value."
::= { dataArray21 17 }

dataValue21_18 OBJECT-TYPE
SYNTAX INTEGER
MAX-ACCESS read-write
STATUS current
DESCRIPTION
"Data value."
::= { dataArray21 18 }

dataValue21_19 OBJECT-TYPE
SYNTAX INTEGER
MAX-ACCESS read-write
STATUS current
DESCRIPTION
"Data value."
::= { dataArray21 19 }

dataValue21_20 OBJECT-TYPE
SYNTAX INTEGER
MAX-ACCESS read-write
STATUS current
DESCRIPTION
"Data value."
::= { dataArray21 20 }

dataValue21_21 OBJECT-TYPE
SYNTAX INTEGER
MAX-ACCESS read-write
STATUS current
DESCRIPTION
"Data value."
::= { dataArray21 21 }

dataValue21_22 OBJECT-TYPE
SYNTAX INTEGER
MAX-ACCESS read-write
STATUS current
DESCRIPTION
"Data value."
::= { dataArray21 22 }

dataValue21_23 OBJECT-TYPE
SYNTAX INTEGER
MAX-ACCESS read-write
STATUS current
DESCRIPTION
"Data value."
::= { dataArray21 23 }

dataValue21_24 OBJECT-TYPE
SYNTAX INTEGER
MAX-ACCESS read-write
STATUS current
DESCRIPTION
"Data value."
::= { dataArray21 24 }

dataValue21_25 OBJECT-TYPE
SYNTAX INTEGER
MAX-ACCESS read-write
STATUS current
DESCRIPTION
"Data value."
::= { dataArray21 25 }

dataValue21_26 OBJECT-TYPE
SYNTAX INTEGER
MAX-ACCESS read-write
STATUS current
DESCRIPTION
"Data value."
::= { dataArray21 26 }

dataValue21_27 OBJECT-TYPE
SYNTAX INTEGER
MAX-ACCESS read-write
STATUS current
DESCRIPTION
"Data value."
::= { dataArray21 27 }

dataValue21_28 OBJECT-TYPE
SYNTAX INTEGER
MAX-ACCESS read-write
STATUS current
DESCRIPTION
"Data value."
::= { dataArray21 28 }

dataValue21_29 OBJECT-TYPE
SYNTAX INTEGER
MAX-ACCESS read-write
STATUS current
DESCRIPTION
"Data value."
::= { dataArray21 29 }

dataValue21_30 OBJECT-TYPE
SYNTAX INTEGER
MAX-ACCESS read-write
STATUS current
DESCRIPTION
"Data value."
::= { dataArray21 30 }

dataValue21_31 OBJECT-TYPE
SYNTAX INTEGER
MAX-ACCESS read-write
STATUS current
DESCRIPTION
"Data value."
::= { dataArray21 31 }

dataValue21_32 OBJECT-TYPE
SYNTAX INTEGER
MAX-ACCESS read-write
STATUS current
DESCRIPTION
"Data value."
::= { dataArray21 32 }

dataValue21_33 OBJECT-TYPE
SYNTAX INTEGER
MAX-ACCESS read-write
STATUS current
DESCRIPTION
"Data value."
::= { dataArray21 33 }

dataValue21_34 OBJECT-TYPE
SYNTAX INTEGER
MAX-ACCESS read-write
STATUS current
DESCRIPTION
"Data value."
::= { dataArray21 34 }

dataValue21_35 OBJECT-TYPE
SYNTAX INTEGER
MAX-ACCESS read-write
STATUS current
DESCRIPTION
"Data value."
::= { dataArray21 35 }

dataValue21_36 OBJECT-TYPE
SYNTAX INTEGER
MAX-ACCESS read-write
STATUS current
DESCRIPTION
"Data value."
::= { dataArray21 36 }

dataValue21_37 OBJECT-TYPE
SYNTAX INTEGER
MAX-ACCESS read-write
STATUS current
DESCRIPTION
"Data value."
::= { dataArray21 37 }

dataValue21_38 OBJECT-TYPE
SYNTAX INTEGER
MAX-ACCESS read-write
STATUS current
DESCRIPTION
"Data value."
::= { dataArray21 38 }

dataValue21_39 OBJECT-TYPE
SYNTAX INTEGER
MAX-ACCESS read-write
STATUS current
DESCRIPTION
"Data value."
::= { dataArray21 39 }

dataValue21_40 OBJECT-TYPE
SYNTAX INTEGER
MAX-ACCESS read-write
STATUS current
DESCRIPTION
"Data value."
::= { dataArray21 40 }

dataValue21_41 OBJECT-TYPE
SYNTAX INTEGER
MAX-ACCESS read-write
STATUS current
DESCRIPTION
"Data value."
::= { dataArray21 41 }

dataValue21_42 OBJECT-TYPE
SYNTAX INTEGER
MAX-ACCESS read-write
STATUS current
DESCRIPTION
"Data value."
::= { dataArray21 42 }

dataValue21_43 OBJECT-TYPE
SYNTAX INTEGER
MAX-ACCESS read-write
STATUS current
DESCRIPTION
"Data value."
::= { dataArray21 43 }

dataValue21_44 OBJECT-TYPE
SYNTAX INTEGER
MAX-ACCESS read-write
STATUS current
DESCRIPTION
"Data value."
::= { dataArray21 44 }

dataValue21_45 OBJECT-TYPE
SYNTAX INTEGER
MAX-ACCESS read-write
STATUS current
DESCRIPTION
"Data value."
::= { dataArray21 45 }

dataValue21_46 OBJECT-TYPE
SYNTAX INTEGER
MAX-ACCESS read-write
STATUS current
DESCRIPTION
"Data value."
::= { dataArray21 46 }

dataValue21_47 OBJECT-TYPE
SYNTAX INTEGER
MAX-ACCESS read-write
STATUS current
DESCRIPTION
"Data value."
::= { dataArray21 47 }

dataValue21_48 OBJECT-TYPE
SYNTAX INTEGER
MAX-ACCESS read-write
STATUS current
DESCRIPTION
"Data value."
::= { dataArray21 48 }

dataValue21_49 OBJECT-TYPE
SYNTAX INTEGER
MAX-ACCESS read-write
STATUS current
DESCRIPTION
"Data value."
::= { dataArray21 49 }

dataValue21_50 OBJECT-TYPE
SYNTAX INTEGER
MAX-ACCESS read-write
STATUS current
DESCRIPTION
"Data value."
::= { dataArray21 50 }

dataValue21_51 OBJECT-TYPE
SYNTAX INTEGER
MAX-ACCESS read-write
STATUS current
DESCRIPTION
"Data value."
::= { dataArray21 51 }

dataValue21_52 OBJECT-TYPE
SYNTAX INTEGER
MAX-ACCESS read-write
STATUS current
DESCRIPTION
"Data value."
::= { dataArray21 52 }

dataValue21_53 OBJECT-TYPE
SYNTAX INTEGER
MAX-ACCESS read-write
STATUS current
DESCRIPTION
"Data value."
::= { dataArray21 53 }

dataValue21_54 OBJECT-TYPE
SYNTAX INTEGER
MAX-ACCESS read-write
STATUS current
DESCRIPTION
"Data value."
::= { dataArray21 54 }

dataValue21_55 OBJECT-TYPE
SYNTAX INTEGER
MAX-ACCESS read-write
STATUS current
DESCRIPTION
"Data value."
::= { dataArray21 55 }

dataValue21_56 OBJECT-TYPE
SYNTAX INTEGER
MAX-ACCESS read-write
STATUS current
DESCRIPTION
"Data value."
::= { dataArray21 56 }

dataValue21_57 OBJECT-TYPE
SYNTAX INTEGER
MAX-ACCESS read-write
STATUS current
DESCRIPTION
"Data value."
::= { dataArray21 57 }

dataValue21_58 OBJECT-TYPE
SYNTAX INTEGER
MAX-ACCESS read-write
STATUS current
DESCRIPTION
"Data value."
::= { dataArray21 58 }

dataValue21_59 OBJECT-TYPE
SYNTAX INTEGER
MAX-ACCESS read-write
STATUS current
DESCRIPTION
"Data value."
::= { dataArray21 59 }

dataValue21_60 OBJECT-TYPE
SYNTAX INTEGER
MAX-ACCESS read-write
STATUS current
DESCRIPTION
"Data value."
::= { dataArray21 60 }

dataValue21_61 OBJECT-TYPE
SYNTAX INTEGER
MAX-ACCESS read-write
STATUS current
DESCRIPTION
"Data value."
::= { dataArray21 61 }

dataValue21_62 OBJECT-TYPE
SYNTAX INTEGER
MAX-ACCESS read-write
STATUS current
DESCRIPTION
"Data value."
::= { dataArray21 62 }

dataValue21_63 OBJECT-TYPE
SYNTAX INTEGER
MAX-ACCESS read-write
STATUS current
DESCRIPTION
"Data value."
::= { dataArray21 63 }

dataValue21_64 OBJECT-TYPE
SYNTAX INTEGER
MAX-ACCESS read-write
STATUS current
DESCRIPTION
"Data value."
::= { dataArray21 64 }

dataValue21_65 OBJECT-TYPE
SYNTAX INTEGER
MAX-ACCESS read-write
STATUS current
DESCRIPTION
"Data value."
::= { dataArray21 65 }

dataValue21_66 OBJECT-TYPE
SYNTAX INTEGER
MAX-ACCESS read-write
STATUS current
DESCRIPTION
"Data value."
::= { dataArray21 66 }

dataValue21_67 OBJECT-TYPE
SYNTAX INTEGER
MAX-ACCESS read-write
STATUS current
DESCRIPTION
"Data value."
::= { dataArray21 67 }

dataValue21_68 OBJECT-TYPE
SYNTAX INTEGER
MAX-ACCESS read-write
STATUS current
DESCRIPTION
"Data value."
::= { dataArray21 68 }

dataValue21_69 OBJECT-TYPE
SYNTAX INTEGER
MAX-ACCESS read-write
STATUS current
DESCRIPTION
"Data value."
::= { dataArray21 69 }

dataValue21_70 OBJECT-TYPE
SYNTAX INTEGER
MAX-ACCESS read-write
STATUS current
DESCRIPTION
"Data value."
::= { dataArray21 70 }

dataValue21_71 OBJECT-TYPE
SYNTAX INTEGER
MAX-ACCESS read-write
STATUS current
DESCRIPTION
"Data value."
::= { dataArray21 71 }

dataValue21_72 OBJECT-TYPE
SYNTAX INTEGER
MAX-ACCESS read-write
STATUS current
DESCRIPTION
"Data value."
::= { dataArray21 72 }

dataValue21_73 OBJECT-TYPE
SYNTAX INTEGER
MAX-ACCESS read-write
STATUS current
DESCRIPTION
"Data value."
::= { dataArray21 73 }

dataValue21_74 OBJECT-TYPE
SYNTAX INTEGER
MAX-ACCESS read-write
STATUS current
DESCRIPTION
"Data value."
::= { dataArray21 74 }

dataValue21_75 OBJECT-TYPE
SYNTAX INTEGER
MAX-ACCESS read-write
STATUS current
DESCRIPTION
"Data value."
::= { dataArray21 75 }

dataValue21_76 OBJECT-TYPE
SYNTAX INTEGER
MAX-ACCESS read-write
STATUS current
DESCRIPTION
"Data value."
::= { dataArray21 76 }

dataValue21_77 OBJECT-TYPE
SYNTAX INTEGER
MAX-ACCESS read-write
STATUS current
DESCRIPTION
"Data value."
::= { dataArray21 77 }

dataValue21_78 OBJECT-TYPE
SYNTAX INTEGER
MAX-ACCESS read-write
STATUS current
DESCRIPTION
"Data value."
::= { dataArray21 78 }

dataValue21_79 OBJECT-TYPE
SYNTAX INTEGER
MAX-ACCESS read-write
STATUS current
DESCRIPTION
"Data value."
::= { dataArray21 79 }

dataValue21_80 OBJECT-TYPE
SYNTAX INTEGER
MAX-ACCESS read-write
STATUS current
DESCRIPTION
"Data value."
::= { dataArray21 80 }

dataValue21_81 OBJECT-TYPE
SYNTAX INTEGER
MAX-ACCESS read-write
STATUS current
DESCRIPTION
"Data value."
::= { dataArray21 81 }

dataValue21_82 OBJECT-TYPE
SYNTAX INTEGER
MAX-ACCESS read-write
STATUS current
DESCRIPTION
"Data value."
::= { dataArray21 82 }

dataValue21_83 OBJECT-TYPE
SYNTAX INTEGER
MAX-ACCESS read-write
STATUS current
DESCRIPTION
"Data value."
::= { dataArray21 83 }

dataValue21_84 OBJECT-TYPE
SYNTAX INTEGER
MAX-ACCESS read-write
STATUS current
DESCRIPTION
"Data value."
::= { dataArray21 84 }

dataValue21_85 OBJECT-TYPE
SYNTAX INTEGER
MAX-ACCESS read-write
STATUS current
DESCRIPTION
"Data value."
::= { dataArray21 85 }

dataValue21_86 OBJECT-TYPE
SYNTAX INTEGER
MAX-ACCESS read-write
STATUS current
DESCRIPTION
"Data value."
::= { dataArray21 86 }

dataValue21_87 OBJECT-TYPE
SYNTAX INTEGER
MAX-ACCESS read-write
STATUS current
DESCRIPTION
"Data value."
::= { dataArray21 87 }

dataValue21_88 OBJECT-TYPE
SYNTAX INTEGER
MAX-ACCESS read-write
STATUS current
DESCRIPTION
"Data value."
::= { dataArray21 88 }

dataValue21_89 OBJECT-TYPE
SYNTAX INTEGER
MAX-ACCESS read-write
STATUS current
DESCRIPTION
"Data value."
::= { dataArray21 89 }

dataValue21_90 OBJECT-TYPE
SYNTAX INTEGER
MAX-ACCESS read-write
STATUS current
DESCRIPTION
"Data value."
::= { dataArray21 90 }

dataValue21_91 OBJECT-TYPE
SYNTAX INTEGER
MAX-ACCESS read-write
STATUS current
DESCRIPTION
"Data value."
::= { dataArray21 91 }

dataValue21_92 OBJECT-TYPE
SYNTAX INTEGER
MAX-ACCESS read-write
STATUS current
DESCRIPTION
"Data value."
::= { dataArray21 92 }

dataValue21_93 OBJECT-TYPE
SYNTAX INTEGER
MAX-ACCESS read-write
STATUS current
DESCRIPTION
"Data value."
::= { dataArray21 93 }

dataValue21_94 OBJECT-TYPE
SYNTAX INTEGER
MAX-ACCESS read-write
STATUS current
DESCRIPTION
"Data value."
::= { dataArray21 94 }

dataValue21_95 OBJECT-TYPE
SYNTAX INTEGER
MAX-ACCESS read-write
STATUS current
DESCRIPTION
"Data value."
::= { dataArray21 95 }

dataValue21_96 OBJECT-TYPE
SYNTAX INTEGER
MAX-ACCESS read-write
STATUS current
DESCRIPTION
"Data value."
::= { dataArray21 96 }

dataValue21_97 OBJECT-TYPE
SYNTAX INTEGER
MAX-ACCESS read-write
STATUS current
DESCRIPTION
"Data value."
::= { dataArray21 97 }

dataValue21_98 OBJECT-TYPE
SYNTAX INTEGER
MAX-ACCESS read-write
STATUS current
DESCRIPTION
"Data value."
::= { dataArray21 98 }

dataValue21_99 OBJECT-TYPE
SYNTAX INTEGER
MAX-ACCESS read-write
STATUS current
DESCRIPTION
"Data value."
::= { dataArray21 99 }

dataValue21_100 OBJECT-TYPE
SYNTAX INTEGER
MAX-ACCESS read-write
STATUS current
DESCRIPTION
"Data value."
::= { dataArray21 100 }

dataValue21_101 OBJECT-TYPE
SYNTAX INTEGER
MAX-ACCESS read-write
STATUS current
DESCRIPTION
"Data value."
::= { dataArray21 101 }

dataValue21_102 OBJECT-TYPE
SYNTAX INTEGER
MAX-ACCESS read-write
STATUS current
DESCRIPTION
"Data value."
::= { dataArray21 102 }

dataValue21_103 OBJECT-TYPE
SYNTAX INTEGER
MAX-ACCESS read-write
STATUS current
DESCRIPTION
"Data value."
::= { dataArray21 103 }

dataValue21_104 OBJECT-TYPE
SYNTAX INTEGER
MAX-ACCESS read-write
STATUS current
DESCRIPTION
"Data value."
::= { dataArray21 104 }

dataValue21_105 OBJECT-TYPE
SYNTAX INTEGER
MAX-ACCESS read-write
STATUS current
DESCRIPTION
"Data value."
::= { dataArray21 105 }

dataValue21_106 OBJECT-TYPE
SYNTAX INTEGER
MAX-ACCESS read-write
STATUS current
DESCRIPTION
"Data value."
::= { dataArray21 106 }

dataValue21_107 OBJECT-TYPE
SYNTAX INTEGER
MAX-ACCESS read-write
STATUS current
DESCRIPTION
"Data value."
::= { dataArray21 107 }

dataValue21_108 OBJECT-TYPE
SYNTAX INTEGER
MAX-ACCESS read-write
STATUS current
DESCRIPTION
"Data value."
::= { dataArray21 108 }

dataValue21_109 OBJECT-TYPE
SYNTAX INTEGER
MAX-ACCESS read-write
STATUS current
DESCRIPTION
"Data value."
::= { dataArray21 109 }

dataValue21_110 OBJECT-TYPE
SYNTAX INTEGER
MAX-ACCESS read-write
STATUS current
DESCRIPTION
"Data value."
::= { dataArray21 110 }

dataValue21_111 OBJECT-TYPE
SYNTAX INTEGER
MAX-ACCESS read-write
STATUS current
DESCRIPTION
"Data value."
::= { dataArray21 111 }

dataValue21_112 OBJECT-TYPE
SYNTAX INTEGER
MAX-ACCESS read-write
STATUS current
DESCRIPTION
"Data value."
::= { dataArray21 112 }

dataValue21_113 OBJECT-TYPE
SYNTAX INTEGER
MAX-ACCESS read-write
STATUS current
DESCRIPTION
"Data value."
::= { dataArray21 113 }

dataValue21_114 OBJECT-TYPE
SYNTAX INTEGER
MAX-ACCESS read-write
STATUS current
DESCRIPTION
"Data value."
::= { dataArray21 114 }

dataValue21_115 OBJECT-TYPE
SYNTAX INTEGER
MAX-ACCESS read-write
STATUS current
DESCRIPTION
"Data value."
::= { dataArray21 115 }

dataValue21_116 OBJECT-TYPE
SYNTAX INTEGER
MAX-ACCESS read-write
STATUS current
DESCRIPTION
"Data value."
::= { dataArray21 116 }

dataValue21_117 OBJECT-TYPE
SYNTAX INTEGER
MAX-ACCESS read-write
STATUS current
DESCRIPTION
"Data value."
::= { dataArray21 117 }

dataValue21_118 OBJECT-TYPE
SYNTAX INTEGER
MAX-ACCESS read-write
STATUS current
DESCRIPTION
"Data value."
::= { dataArray21 118 }

dataValue21_119 OBJECT-TYPE
SYNTAX INTEGER
MAX-ACCESS read-write
STATUS current
DESCRIPTION
"Data value."
::= { dataArray21 119 }

dataValue21_120 OBJECT-TYPE
SYNTAX INTEGER
MAX-ACCESS read-write
STATUS current
DESCRIPTION
"Data value."
::= { dataArray21 120 }

dataValue21_121 OBJECT-TYPE
SYNTAX INTEGER
MAX-ACCESS read-write
STATUS current
DESCRIPTION
"Data value."
::= { dataArray21 121 }

dataValue21_122 OBJECT-TYPE
SYNTAX INTEGER
MAX-ACCESS read-write
STATUS current
DESCRIPTION
"Data value."
::= { dataArray21 122 }

dataValue21_123 OBJECT-TYPE
SYNTAX INTEGER
MAX-ACCESS read-write
STATUS current
DESCRIPTION
"Data value."
::= { dataArray21 123 }

dataValue21_124 OBJECT-TYPE
SYNTAX INTEGER
MAX-ACCESS read-write
STATUS current
DESCRIPTION
"Data value."
::= { dataArray21 124 }

dataValue21_125 OBJECT-TYPE
SYNTAX INTEGER
MAX-ACCESS read-write
STATUS current
DESCRIPTION
"Data value."
::= { dataArray21 125 }

dataValue21_126 OBJECT-TYPE
SYNTAX INTEGER
MAX-ACCESS read-write
STATUS current
DESCRIPTION
"Data value."
::= { dataArray21 126 }

dataValue21_127 OBJECT-TYPE
SYNTAX INTEGER
MAX-ACCESS read-write
STATUS current
DESCRIPTION
"Data value."
::= { dataArray21 127 }

dataValue21_128 OBJECT-TYPE
SYNTAX INTEGER
MAX-ACCESS read-write
STATUS current
DESCRIPTION
"Data value."
::= { dataArray21 128 }

dataValue21_129 OBJECT-TYPE
SYNTAX INTEGER
MAX-ACCESS read-write
STATUS current
DESCRIPTION
"Data value."
::= { dataArray21 129 }

dataValue21_130 OBJECT-TYPE
SYNTAX INTEGER
MAX-ACCESS read-write
STATUS current
DESCRIPTION
"Data value."
::= { dataArray21 130 }

dataValue21_131 OBJECT-TYPE
SYNTAX INTEGER
MAX-ACCESS read-write
STATUS current
DESCRIPTION
"Data value."
::= { dataArray21 131 }

dataValue21_132 OBJECT-TYPE
SYNTAX INTEGER
MAX-ACCESS read-write
STATUS current
DESCRIPTION
"Data value."
::= { dataArray21 132 }

dataValue21_133 OBJECT-TYPE
SYNTAX INTEGER
MAX-ACCESS read-write
STATUS current
DESCRIPTION
"Data value."
::= { dataArray21 133 }

dataValue21_134 OBJECT-TYPE
SYNTAX INTEGER
MAX-ACCESS read-write
STATUS current
DESCRIPTION
"Data value."
::= { dataArray21 134 }

dataValue21_135 OBJECT-TYPE
SYNTAX INTEGER
MAX-ACCESS read-write
STATUS current
DESCRIPTION
"Data value."
::= { dataArray21 135 }

dataValue21_136 OBJECT-TYPE
SYNTAX INTEGER
MAX-ACCESS read-write
STATUS current
DESCRIPTION
"Data value."
::= { dataArray21 136 }

dataValue21_137 OBJECT-TYPE
SYNTAX INTEGER
MAX-ACCESS read-write
STATUS current
DESCRIPTION
"Data value."
::= { dataArray21 137 }

dataValue21_138 OBJECT-TYPE
SYNTAX INTEGER
MAX-ACCESS read-write
STATUS current
DESCRIPTION
"Data value."
::= { dataArray21 138 }

dataValue21_139 OBJECT-TYPE
SYNTAX INTEGER
MAX-ACCESS read-write
STATUS current
DESCRIPTION
"Data value."
::= { dataArray21 139 }

dataValue21_140 OBJECT-TYPE
SYNTAX INTEGER
MAX-ACCESS read-write
STATUS current
DESCRIPTION
"Data value."
::= { dataArray21 140 }

dataValue21_141 OBJECT-TYPE
SYNTAX INTEGER
MAX-ACCESS read-write
STATUS current
DESCRIPTION
"Data value."
::= { dataArray21 141 }

dataValue21_142 OBJECT-TYPE
SYNTAX INTEGER
MAX-ACCESS read-write
STATUS current
DESCRIPTION
"Data value."
::= { dataArray21 142 }

dataValue21_143 OBJECT-TYPE
SYNTAX INTEGER
MAX-ACCESS read-write
STATUS current
DESCRIPTION
"Data value."
::= { dataArray21 143 }

dataValue21_144 OBJECT-TYPE
SYNTAX INTEGER
MAX-ACCESS read-write
STATUS current
DESCRIPTION
"Data value."
::= { dataArray21 144 }

dataValue21_145 OBJECT-TYPE
SYNTAX INTEGER
MAX-ACCESS read-write
STATUS current
DESCRIPTION
"Data value."
::= { dataArray21 145 }

dataValue21_146 OBJECT-TYPE
SYNTAX INTEGER
MAX-ACCESS read-write
STATUS current
DESCRIPTION
"Data value."
::= { dataArray21 146 }

dataValue21_147 OBJECT-TYPE
SYNTAX INTEGER
MAX-ACCESS read-write
STATUS current
DESCRIPTION
"Data value."
::= { dataArray21 147 }

dataValue21_148 OBJECT-TYPE
SYNTAX INTEGER
MAX-ACCESS read-write
STATUS current
DESCRIPTION
"Data value."
::= { dataArray21 148 }

dataValue21_149 OBJECT-TYPE
SYNTAX INTEGER
MAX-ACCESS read-write
STATUS current
DESCRIPTION
"Data value."
::= { dataArray21 149 }

dataValue21_150 OBJECT-TYPE
SYNTAX INTEGER
MAX-ACCESS read-write
STATUS current
DESCRIPTION
"Data value."
::= { dataArray21 150 }

dataValue21_151 OBJECT-TYPE
SYNTAX INTEGER
MAX-ACCESS read-write
STATUS current
DESCRIPTION
"Data value."
::= { dataArray21 151 }

dataValue21_152 OBJECT-TYPE
SYNTAX INTEGER
MAX-ACCESS read-write
STATUS current
DESCRIPTION
"Data value."
::= { dataArray21 152 }

dataValue21_153 OBJECT-TYPE
SYNTAX INTEGER
MAX-ACCESS read-write
STATUS current
DESCRIPTION
"Data value."
::= { dataArray21 153 }

dataValue21_154 OBJECT-TYPE
SYNTAX INTEGER
MAX-ACCESS read-write
STATUS current
DESCRIPTION
"Data value."
::= { dataArray21 154 }

dataValue21_155 OBJECT-TYPE
SYNTAX INTEGER
MAX-ACCESS read-write
STATUS current
DESCRIPTION
"Data value."
::= { dataArray21 155 }

dataValue21_156 OBJECT-TYPE
SYNTAX INTEGER
MAX-ACCESS read-write
STATUS current
DESCRIPTION
"Data value."
::= { dataArray21 156 }

dataValue21_157 OBJECT-TYPE
SYNTAX INTEGER
MAX-ACCESS read-write
STATUS current
DESCRIPTION
"Data value."
::= { dataArray21 157 }

dataValue21_158 OBJECT-TYPE
SYNTAX INTEGER
MAX-ACCESS read-write
STATUS current
DESCRIPTION
"Data value."
::= { dataArray21 158 }

dataValue21_159 OBJECT-TYPE
SYNTAX INTEGER
MAX-ACCESS read-write
STATUS current
DESCRIPTION
"Data value."
::= { dataArray21 159 }

dataValue21_160 OBJECT-TYPE
SYNTAX INTEGER
MAX-ACCESS read-write
STATUS current
DESCRIPTION
"Data value."
::= { dataArray21 160 }

dataValue21_161 OBJECT-TYPE
SYNTAX INTEGER
MAX-ACCESS read-write
STATUS current
DESCRIPTION
"Data value."
::= { dataArray21 161 }

dataValue21_162 OBJECT-TYPE
SYNTAX INTEGER
MAX-ACCESS read-write
STATUS current
DESCRIPTION
"Data value."
::= { dataArray21 162 }

dataValue21_163 OBJECT-TYPE
SYNTAX INTEGER
MAX-ACCESS read-write
STATUS current
DESCRIPTION
"Data value."
::= { dataArray21 163 }

dataValue21_164 OBJECT-TYPE
SYNTAX INTEGER
MAX-ACCESS read-write
STATUS current
DESCRIPTION
"Data value."
::= { dataArray21 164 }

dataValue21_165 OBJECT-TYPE
SYNTAX INTEGER
MAX-ACCESS read-write
STATUS current
DESCRIPTION
"Data value."
::= { dataArray21 165 }

dataValue21_166 OBJECT-TYPE
SYNTAX INTEGER
MAX-ACCESS read-write
STATUS current
DESCRIPTION
"Data value."
::= { dataArray21 166 }

dataValue21_167 OBJECT-TYPE
SYNTAX INTEGER
MAX-ACCESS read-write
STATUS current
DESCRIPTION
"Data value."
::= { dataArray21 167 }

dataValue21_168 OBJECT-TYPE
SYNTAX INTEGER
MAX-ACCESS read-write
STATUS current
DESCRIPTION
"Data value."
::= { dataArray21 168 }

dataValue21_169 OBJECT-TYPE
SYNTAX INTEGER
MAX-ACCESS read-write
STATUS current
DESCRIPTION
"Data value."
::= { dataArray21 169 }

dataValue21_170 OBJECT-TYPE
SYNTAX INTEGER
MAX-ACCESS read-write
STATUS current
DESCRIPTION
"Data value."
::= { dataArray21 170 }

dataValue21_171 OBJECT-TYPE
SYNTAX INTEGER
MAX-ACCESS read-write
STATUS current
DESCRIPTION
"Data value."
::= { dataArray21 171 }

dataValue21_172 OBJECT-TYPE
SYNTAX INTEGER
MAX-ACCESS read-write
STATUS current
DESCRIPTION
"Data value."
::= { dataArray21 172 }

dataValue21_173 OBJECT-TYPE
SYNTAX INTEGER
MAX-ACCESS read-write
STATUS current
DESCRIPTION
"Data value."
::= { dataArray21 173 }

dataValue21_174 OBJECT-TYPE
SYNTAX INTEGER
MAX-ACCESS read-write
STATUS current
DESCRIPTION
"Data value."
::= { dataArray21 174 }

dataValue21_175 OBJECT-TYPE
SYNTAX INTEGER
MAX-ACCESS read-write
STATUS current
DESCRIPTION
"Data value."
::= { dataArray21 175 }

dataValue21_176 OBJECT-TYPE
SYNTAX INTEGER
MAX-ACCESS read-write
STATUS current
DESCRIPTION
"Data value."
::= { dataArray21 176 }

dataValue21_177 OBJECT-TYPE
SYNTAX INTEGER
MAX-ACCESS read-write
STATUS current
DESCRIPTION
"Data value."
::= { dataArray21 177 }

dataValue21_178 OBJECT-TYPE
SYNTAX INTEGER
MAX-ACCESS read-write
STATUS current
DESCRIPTION
"Data value."
::= { dataArray21 178 }

dataValue21_179 OBJECT-TYPE
SYNTAX INTEGER
MAX-ACCESS read-write
STATUS current
DESCRIPTION
"Data value."
::= { dataArray21 179 }

dataValue21_180 OBJECT-TYPE
SYNTAX INTEGER
MAX-ACCESS read-write
STATUS current
DESCRIPTION
"Data value."
::= { dataArray21 180 }

dataValue21_181 OBJECT-TYPE
SYNTAX INTEGER
MAX-ACCESS read-write
STATUS current
DESCRIPTION
"Data value."
::= { dataArray21 181 }

dataValue21_182 OBJECT-TYPE
SYNTAX INTEGER
MAX-ACCESS read-write
STATUS current
DESCRIPTION
"Data value."
::= { dataArray21 182 }

dataValue21_183 OBJECT-TYPE
SYNTAX INTEGER
MAX-ACCESS read-write
STATUS current
DESCRIPTION
"Data value."
::= { dataArray21 183 }

dataValue21_184 OBJECT-TYPE
SYNTAX INTEGER
MAX-ACCESS read-write
STATUS current
DESCRIPTION
"Data value."
::= { dataArray21 184 }

dataValue21_185 OBJECT-TYPE
SYNTAX INTEGER
MAX-ACCESS read-write
STATUS current
DESCRIPTION
"Data value."
::= { dataArray21 185 }

dataValue21_186 OBJECT-TYPE
SYNTAX INTEGER
MAX-ACCESS read-write
STATUS current
DESCRIPTION
"Data value."
::= { dataArray21 186 }

dataValue21_187 OBJECT-TYPE
SYNTAX INTEGER
MAX-ACCESS read-write
STATUS current
DESCRIPTION
"Data value."
::= { dataArray21 187 }

dataValue21_188 OBJECT-TYPE
SYNTAX INTEGER
MAX-ACCESS read-write
STATUS current
DESCRIPTION
"Data value."
::= { dataArray21 188 }

dataValue21_189 OBJECT-TYPE
SYNTAX INTEGER
MAX-ACCESS read-write
STATUS current
DESCRIPTION
"Data value."
::= { dataArray21 189 }

dataValue21_190 OBJECT-TYPE
SYNTAX INTEGER
MAX-ACCESS read-write
STATUS current
DESCRIPTION
"Data value."
::= { dataArray21 190 }

dataValue21_191 OBJECT-TYPE
SYNTAX INTEGER
MAX-ACCESS read-write
STATUS current
DESCRIPTION
"Data value."
::= { dataArray21 191 }

dataValue21_192 OBJECT-TYPE
SYNTAX INTEGER
MAX-ACCESS read-write
STATUS current
DESCRIPTION
"Data value."
::= { dataArray21 192 }

dataValue21_193 OBJECT-TYPE
SYNTAX INTEGER
MAX-ACCESS read-write
STATUS current
DESCRIPTION
"Data value."
::= { dataArray21 193 }

dataValue21_194 OBJECT-TYPE
SYNTAX INTEGER
MAX-ACCESS read-write
STATUS current
DESCRIPTION
"Data value."
::= { dataArray21 194 }

dataValue21_195 OBJECT-TYPE
SYNTAX INTEGER
MAX-ACCESS read-write
STATUS current
DESCRIPTION
"Data value."
::= { dataArray21 195 }

dataValue21_196 OBJECT-TYPE
SYNTAX INTEGER
MAX-ACCESS read-write
STATUS current
DESCRIPTION
"Data value."
::= { dataArray21 196 }

dataValue21_197 OBJECT-TYPE
SYNTAX INTEGER
MAX-ACCESS read-write
STATUS current
DESCRIPTION
"Data value."
::= { dataArray21 197 }

dataValue21_198 OBJECT-TYPE
SYNTAX INTEGER
MAX-ACCESS read-write
STATUS current
DESCRIPTION
"Data value."
::= { dataArray21 198 }

dataValue21_199 OBJECT-TYPE
SYNTAX INTEGER
MAX-ACCESS read-write
STATUS current
DESCRIPTION
"Data value."
::= { dataArray21 199 }

dataValue21_200 OBJECT-TYPE
SYNTAX INTEGER
MAX-ACCESS read-write
STATUS current
DESCRIPTION
"Data value."
::= { dataArray21 200 }

dataValue21_201 OBJECT-TYPE
SYNTAX INTEGER
MAX-ACCESS read-write
STATUS current
DESCRIPTION
"Data value."
::= { dataArray21 201 }

dataValue21_202 OBJECT-TYPE
SYNTAX INTEGER
MAX-ACCESS read-write
STATUS current
DESCRIPTION
"Data value."
::= { dataArray21 202 }

dataValue21_203 OBJECT-TYPE
SYNTAX INTEGER
MAX-ACCESS read-write
STATUS current
DESCRIPTION
"Data value."
::= { dataArray21 203 }

dataValue21_204 OBJECT-TYPE
SYNTAX INTEGER
MAX-ACCESS read-write
STATUS current
DESCRIPTION
"Data value."
::= { dataArray21 204 }

dataValue21_205 OBJECT-TYPE
SYNTAX INTEGER
MAX-ACCESS read-write
STATUS current
DESCRIPTION
"Data value."
::= { dataArray21 205 }

dataValue21_206 OBJECT-TYPE
SYNTAX INTEGER
MAX-ACCESS read-write
STATUS current
DESCRIPTION
"Data value."
::= { dataArray21 206 }

dataValue21_207 OBJECT-TYPE
SYNTAX INTEGER
MAX-ACCESS read-write
STATUS current
DESCRIPTION
"Data value."
::= { dataArray21 207 }

dataValue21_208 OBJECT-TYPE
SYNTAX INTEGER
MAX-ACCESS read-write
STATUS current
DESCRIPTION
"Data value."
::= { dataArray21 208 }

dataValue21_209 OBJECT-TYPE
SYNTAX INTEGER
MAX-ACCESS read-write
STATUS current
DESCRIPTION
"Data value."
::= { dataArray21 209 }

dataValue21_210 OBJECT-TYPE
SYNTAX INTEGER
MAX-ACCESS read-write
STATUS current
DESCRIPTION
"Data value."
::= { dataArray21 210 }

dataValue21_211 OBJECT-TYPE
SYNTAX INTEGER
MAX-ACCESS read-write
STATUS current
DESCRIPTION
"Data value."
::= { dataArray21 211 }

dataValue21_212 OBJECT-TYPE
SYNTAX INTEGER
MAX-ACCESS read-write
STATUS current
DESCRIPTION
"Data value."
::= { dataArray21 212 }

dataValue21_213 OBJECT-TYPE
SYNTAX INTEGER
MAX-ACCESS read-write
STATUS current
DESCRIPTION
"Data value."
::= { dataArray21 213 }

dataValue21_214 OBJECT-TYPE
SYNTAX INTEGER
MAX-ACCESS read-write
STATUS current
DESCRIPTION
"Data value."
::= { dataArray21 214 }

dataValue21_215 OBJECT-TYPE
SYNTAX INTEGER
MAX-ACCESS read-write
STATUS current
DESCRIPTION
"Data value."
::= { dataArray21 215 }

dataValue21_216 OBJECT-TYPE
SYNTAX INTEGER
MAX-ACCESS read-write
STATUS current
DESCRIPTION
"Data value."
::= { dataArray21 216 }

dataValue21_217 OBJECT-TYPE
SYNTAX INTEGER
MAX-ACCESS read-write
STATUS current
DESCRIPTION
"Data value."
::= { dataArray21 217 }

dataValue21_218 OBJECT-TYPE
SYNTAX INTEGER
MAX-ACCESS read-write
STATUS current
DESCRIPTION
"Data value."
::= { dataArray21 218 }

dataValue21_219 OBJECT-TYPE
SYNTAX INTEGER
MAX-ACCESS read-write
STATUS current
DESCRIPTION
"Data value."
::= { dataArray21 219 }

dataValue21_220 OBJECT-TYPE
SYNTAX INTEGER
MAX-ACCESS read-write
STATUS current
DESCRIPTION
"Data value."
::= { dataArray21 220 }

dataValue21_221 OBJECT-TYPE
SYNTAX INTEGER
MAX-ACCESS read-write
STATUS current
DESCRIPTION
"Data value."
::= { dataArray21 221 }

dataValue21_222 OBJECT-TYPE
SYNTAX INTEGER
MAX-ACCESS read-write
STATUS current
DESCRIPTION
"Data value."
::= { dataArray21 222 }

dataValue21_223 OBJECT-TYPE
SYNTAX INTEGER
MAX-ACCESS read-write
STATUS current
DESCRIPTION
"Data value."
::= { dataArray21 223 }

dataValue21_224 OBJECT-TYPE
SYNTAX INTEGER
MAX-ACCESS read-write
STATUS current
DESCRIPTION
"Data value."
::= { dataArray21 224 }

dataValue21_225 OBJECT-TYPE
SYNTAX INTEGER
MAX-ACCESS read-write
STATUS current
DESCRIPTION
"Data value."
::= { dataArray21 225 }

dataValue21_226 OBJECT-TYPE
SYNTAX INTEGER
MAX-ACCESS read-write
STATUS current
DESCRIPTION
"Data value."
::= { dataArray21 226 }

dataValue21_227 OBJECT-TYPE
SYNTAX INTEGER
MAX-ACCESS read-write
STATUS current
DESCRIPTION
"Data value."
::= { dataArray21 227 }

dataValue21_228 OBJECT-TYPE
SYNTAX INTEGER
MAX-ACCESS read-write
STATUS current
DESCRIPTION
"Data value."
::= { dataArray21 228 }

dataValue21_229 OBJECT-TYPE
SYNTAX INTEGER
MAX-ACCESS read-write
STATUS current
DESCRIPTION
"Data value."
::= { dataArray21 229 }

dataValue21_230 OBJECT-TYPE
SYNTAX INTEGER
MAX-ACCESS read-write
STATUS current
DESCRIPTION
"Data value."
::= { dataArray21 230 }

dataValue21_231 OBJECT-TYPE
SYNTAX INTEGER
MAX-ACCESS read-write
STATUS current
DESCRIPTION
"Data value."
::= { dataArray21 231 }

dataValue21_232 OBJECT-TYPE
SYNTAX INTEGER
MAX-ACCESS read-write
STATUS current
DESCRIPTION
"Data value."
::= { dataArray21 232 }

dataValue21_233 OBJECT-TYPE
SYNTAX INTEGER
MAX-ACCESS read-write
STATUS current
DESCRIPTION
"Data value."
::= { dataArray21 233 }

dataValue21_234 OBJECT-TYPE
SYNTAX INTEGER
MAX-ACCESS read-write
STATUS current
DESCRIPTION
"Data value."
::= { dataArray21 234 }

dataValue21_235 OBJECT-TYPE
SYNTAX INTEGER
MAX-ACCESS read-write
STATUS current
DESCRIPTION
"Data value."
::= { dataArray21 235 }

dataValue21_236 OBJECT-TYPE
SYNTAX INTEGER
MAX-ACCESS read-write
STATUS current
DESCRIPTION
"Data value."
::= { dataArray21 236 }

dataValue21_237 OBJECT-TYPE
SYNTAX INTEGER
MAX-ACCESS read-write
STATUS current
DESCRIPTION
"Data value."
::= { dataArray21 237 }

dataValue21_238 OBJECT-TYPE
SYNTAX INTEGER
MAX-ACCESS read-write
STATUS current
DESCRIPTION
"Data value."
::= { dataArray21 238 }

dataValue21_239 OBJECT-TYPE
SYNTAX INTEGER
MAX-ACCESS read-write
STATUS current
DESCRIPTION
"Data value."
::= { dataArray21 239 }

dataValue21_240 OBJECT-TYPE
SYNTAX INTEGER
MAX-ACCESS read-write
STATUS current
DESCRIPTION
"Data value."
::= { dataArray21 240 }

dataValue21_241 OBJECT-TYPE
SYNTAX INTEGER
MAX-ACCESS read-write
STATUS current
DESCRIPTION
"Data value."
::= { dataArray21 241 }

dataValue21_242 OBJECT-TYPE
SYNTAX INTEGER
MAX-ACCESS read-write
STATUS current
DESCRIPTION
"Data value."
::= { dataArray21 242 }

dataValue21_243 OBJECT-TYPE
SYNTAX INTEGER
MAX-ACCESS read-write
STATUS current
DESCRIPTION
"Data value."
::= { dataArray21 243 }

dataValue21_244 OBJECT-TYPE
SYNTAX INTEGER
MAX-ACCESS read-write
STATUS current
DESCRIPTION
"Data value."
::= { dataArray21 244 }

dataValue21_245 OBJECT-TYPE
SYNTAX INTEGER
MAX-ACCESS read-write
STATUS current
DESCRIPTION
"Data value."
::= { dataArray21 245 }

dataValue21_246 OBJECT-TYPE
SYNTAX INTEGER
MAX-ACCESS read-write
STATUS current
DESCRIPTION
"Data value."
::= { dataArray21 246 }

dataValue21_247 OBJECT-TYPE
SYNTAX INTEGER
MAX-ACCESS read-write
STATUS current
DESCRIPTION
"Data value."
::= { dataArray21 247 }

dataValue21_248 OBJECT-TYPE
SYNTAX INTEGER
MAX-ACCESS read-write
STATUS current
DESCRIPTION
"Data value."
::= { dataArray21 248 }

dataValue21_249 OBJECT-TYPE
SYNTAX INTEGER
MAX-ACCESS read-write
STATUS current
DESCRIPTION
"Data value."
::= { dataArray21 249 }

dataValue21_250 OBJECT-TYPE
SYNTAX INTEGER
MAX-ACCESS read-write
STATUS current
DESCRIPTION
"Data value."
::= { dataArray21 250 }

dataValue21_251 OBJECT-TYPE
SYNTAX INTEGER
MAX-ACCESS read-write
STATUS current
DESCRIPTION
"Data value."
::= { dataArray21 251 }

dataValue21_252 OBJECT-TYPE
SYNTAX INTEGER
MAX-ACCESS read-write
STATUS current
DESCRIPTION
"Data value."
::= { dataArray21 252 }

dataValue21_253 OBJECT-TYPE
SYNTAX INTEGER
MAX-ACCESS read-write
STATUS current
DESCRIPTION
"Data value."
::= { dataArray21 253 }

dataValue21_254 OBJECT-TYPE
SYNTAX INTEGER
MAX-ACCESS read-write
STATUS current
DESCRIPTION
"Data value."
::= { dataArray21 254 }

dataValue21_255 OBJECT-TYPE
SYNTAX INTEGER
MAX-ACCESS read-write
STATUS current
DESCRIPTION
"Data value."
::= { dataArray21 255 }

dataValue21_256 OBJECT-TYPE
SYNTAX INTEGER
MAX-ACCESS read-write
STATUS current
DESCRIPTION
"Data value."
::= { dataArray21 256 }

dataValue21_257 OBJECT-TYPE
SYNTAX INTEGER
MAX-ACCESS read-write
STATUS current
DESCRIPTION
"Data value."
::= { dataArray21 257 }

dataValue21_258 OBJECT-TYPE
SYNTAX INTEGER
MAX-ACCESS read-write
STATUS current
DESCRIPTION
"Data value."
::= { dataArray21 258 }

dataValue21_259 OBJECT-TYPE
SYNTAX INTEGER
MAX-ACCESS read-write
STATUS current
DESCRIPTION
"Data value."
::= { dataArray21 259 }

dataValue21_260 OBJECT-TYPE
SYNTAX INTEGER
MAX-ACCESS read-write
STATUS current
DESCRIPTION
"Data value."
::= { dataArray21 260 }

dataValue21_261 OBJECT-TYPE
SYNTAX INTEGER
MAX-ACCESS read-write
STATUS current
DESCRIPTION
"Data value."
::= { dataArray21 261 }

dataValue21_262 OBJECT-TYPE
SYNTAX INTEGER
MAX-ACCESS read-write
STATUS current
DESCRIPTION
"Data value."
::= { dataArray21 262 }

dataValue21_263 OBJECT-TYPE
SYNTAX INTEGER
MAX-ACCESS read-write
STATUS current
DESCRIPTION
"Data value."
::= { dataArray21 263 }

dataValue21_264 OBJECT-TYPE
SYNTAX INTEGER
MAX-ACCESS read-write
STATUS current
DESCRIPTION
"Data value."
::= { dataArray21 264 }

dataValue21_265 OBJECT-TYPE
SYNTAX INTEGER
MAX-ACCESS read-write
STATUS current
DESCRIPTION
"Data value."
::= { dataArray21 265 }

dataValue21_266 OBJECT-TYPE
SYNTAX INTEGER
MAX-ACCESS read-write
STATUS current
DESCRIPTION
"Data value."
::= { dataArray21 266 }

dataValue21_267 OBJECT-TYPE
SYNTAX INTEGER
MAX-ACCESS read-write
STATUS current
DESCRIPTION
"Data value."
::= { dataArray21 267 }

dataValue21_268 OBJECT-TYPE
SYNTAX INTEGER
MAX-ACCESS read-write
STATUS current
DESCRIPTION
"Data value."
::= { dataArray21 268 }

dataValue21_269 OBJECT-TYPE
SYNTAX INTEGER
MAX-ACCESS read-write
STATUS current
DESCRIPTION
"Data value."
::= { dataArray21 269 }

dataValue21_270 OBJECT-TYPE
SYNTAX INTEGER
MAX-ACCESS read-write
STATUS current
DESCRIPTION
"Data value."
::= { dataArray21 270 }

dataValue21_271 OBJECT-TYPE
SYNTAX INTEGER
MAX-ACCESS read-write
STATUS current
DESCRIPTION
"Data value."
::= { dataArray21 271 }

dataValue21_272 OBJECT-TYPE
SYNTAX INTEGER
MAX-ACCESS read-write
STATUS current
DESCRIPTION
"Data value."
::= { dataArray21 272 }

dataValue21_273 OBJECT-TYPE
SYNTAX INTEGER
MAX-ACCESS read-write
STATUS current
DESCRIPTION
"Data value."
::= { dataArray21 273 }

dataValue21_274 OBJECT-TYPE
SYNTAX INTEGER
MAX-ACCESS read-write
STATUS current
DESCRIPTION
"Data value."
::= { dataArray21 274 }

dataValue21_275 OBJECT-TYPE
SYNTAX INTEGER
MAX-ACCESS read-write
STATUS current
DESCRIPTION
"Data value."
::= { dataArray21 275 }

dataValue21_276 OBJECT-TYPE
SYNTAX INTEGER
MAX-ACCESS read-write
STATUS current
DESCRIPTION
"Data value."
::= { dataArray21 276 }

dataValue21_277 OBJECT-TYPE
SYNTAX INTEGER
MAX-ACCESS read-write
STATUS current
DESCRIPTION
"Data value."
::= { dataArray21 277 }

dataValue21_278 OBJECT-TYPE
SYNTAX INTEGER
MAX-ACCESS read-write
STATUS current
DESCRIPTION
"Data value."
::= { dataArray21 278 }

dataValue21_279 OBJECT-TYPE
SYNTAX INTEGER
MAX-ACCESS read-write
STATUS current
DESCRIPTION
"Data value."
::= { dataArray21 279 }

dataValue21_280 OBJECT-TYPE
SYNTAX INTEGER
MAX-ACCESS read-write
STATUS current
DESCRIPTION
"Data value."
::= { dataArray21 280 }

dataValue21_281 OBJECT-TYPE
SYNTAX INTEGER
MAX-ACCESS read-write
STATUS current
DESCRIPTION
"Data value."
::= { dataArray21 281 }

dataValue21_282 OBJECT-TYPE
SYNTAX INTEGER
MAX-ACCESS read-write
STATUS current
DESCRIPTION
"Data value."
::= { dataArray21 282 }

dataValue21_283 OBJECT-TYPE
SYNTAX INTEGER
MAX-ACCESS read-write
STATUS current
DESCRIPTION
"Data value."
::= { dataArray21 283 }

dataValue21_284 OBJECT-TYPE
SYNTAX INTEGER
MAX-ACCESS read-write
STATUS current
DESCRIPTION
"Data value."
::= { dataArray21 284 }

dataValue21_285 OBJECT-TYPE
SYNTAX INTEGER
MAX-ACCESS read-write
STATUS current
DESCRIPTION
"Data value."
::= { dataArray21 285 }

dataValue21_286 OBJECT-TYPE
SYNTAX INTEGER
MAX-ACCESS read-write
STATUS current
DESCRIPTION
"Data value."
::= { dataArray21 286 }

dataValue21_287 OBJECT-TYPE
SYNTAX INTEGER
MAX-ACCESS read-write
STATUS current
DESCRIPTION
"Data value."
::= { dataArray21 287 }

dataValue21_288 OBJECT-TYPE
SYNTAX INTEGER
MAX-ACCESS read-write
STATUS current
DESCRIPTION
"Data value."
::= { dataArray21 288 }

dataValue21_289 OBJECT-TYPE
SYNTAX INTEGER
MAX-ACCESS read-write
STATUS current
DESCRIPTION
"Data value."
::= { dataArray21 289 }

dataValue21_290 OBJECT-TYPE
SYNTAX INTEGER
MAX-ACCESS read-write
STATUS current
DESCRIPTION
"Data value."
::= { dataArray21 290 }

dataValue21_291 OBJECT-TYPE
SYNTAX INTEGER
MAX-ACCESS read-write
STATUS current
DESCRIPTION
"Data value."
::= { dataArray21 291 }

dataValue21_292 OBJECT-TYPE
SYNTAX INTEGER
MAX-ACCESS read-write
STATUS current
DESCRIPTION
"Data value."
::= { dataArray21 292 }

dataValue21_293 OBJECT-TYPE
SYNTAX INTEGER
MAX-ACCESS read-write
STATUS current
DESCRIPTION
"Data value."
::= { dataArray21 293 }

dataValue21_294 OBJECT-TYPE
SYNTAX INTEGER
MAX-ACCESS read-write
STATUS current
DESCRIPTION
"Data value."
::= { dataArray21 294 }

dataValue21_295 OBJECT-TYPE
SYNTAX INTEGER
MAX-ACCESS read-write
STATUS current
DESCRIPTION
"Data value."
::= { dataArray21 295 }

dataValue21_296 OBJECT-TYPE
SYNTAX INTEGER
MAX-ACCESS read-write
STATUS current
DESCRIPTION
"Data value."
::= { dataArray21 296 }

dataValue21_297 OBJECT-TYPE
SYNTAX INTEGER
MAX-ACCESS read-write
STATUS current
DESCRIPTION
"Data value."
::= { dataArray21 297 }

dataValue21_298 OBJECT-TYPE
SYNTAX INTEGER
MAX-ACCESS read-write
STATUS current
DESCRIPTION
"Data value."
::= { dataArray21 298 }

dataValue21_299 OBJECT-TYPE
SYNTAX INTEGER
MAX-ACCESS read-write
STATUS current
DESCRIPTION
"Data value."
::= { dataArray21 299 }

dataValue21_300 OBJECT-TYPE
SYNTAX INTEGER
MAX-ACCESS read-write
STATUS current
DESCRIPTION
"Data value."
::= { dataArray21 300 }

dataValue21_301 OBJECT-TYPE
SYNTAX INTEGER
MAX-ACCESS read-write
STATUS current
DESCRIPTION
"Data value."
::= { dataArray21 301 }

dataValue21_302 OBJECT-TYPE
SYNTAX INTEGER
MAX-ACCESS read-write
STATUS current
DESCRIPTION
"Data value."
::= { dataArray21 302 }

dataValue21_303 OBJECT-TYPE
SYNTAX INTEGER
MAX-ACCESS read-write
STATUS current
DESCRIPTION
"Data value."
::= { dataArray21 303 }

dataValue21_304 OBJECT-TYPE
SYNTAX INTEGER
MAX-ACCESS read-write
STATUS current
DESCRIPTION
"Data value."
::= { dataArray21 304 }

dataValue21_305 OBJECT-TYPE
SYNTAX INTEGER
MAX-ACCESS read-write
STATUS current
DESCRIPTION
"Data value."
::= { dataArray21 305 }

dataValue21_306 OBJECT-TYPE
SYNTAX INTEGER
MAX-ACCESS read-write
STATUS current
DESCRIPTION
"Data value."
::= { dataArray21 306 }

dataValue21_307 OBJECT-TYPE
SYNTAX INTEGER
MAX-ACCESS read-write
STATUS current
DESCRIPTION
"Data value."
::= { dataArray21 307 }

dataValue21_308 OBJECT-TYPE
SYNTAX INTEGER
MAX-ACCESS read-write
STATUS current
DESCRIPTION
"Data value."
::= { dataArray21 308 }

dataValue21_309 OBJECT-TYPE
SYNTAX INTEGER
MAX-ACCESS read-write
STATUS current
DESCRIPTION
"Data value."
::= { dataArray21 309 }

dataValue21_310 OBJECT-TYPE
SYNTAX INTEGER
MAX-ACCESS read-write
STATUS current
DESCRIPTION
"Data value."
::= { dataArray21 310 }

dataValue21_311 OBJECT-TYPE
SYNTAX INTEGER
MAX-ACCESS read-write
STATUS current
DESCRIPTION
"Data value."
::= { dataArray21 311 }

dataValue21_312 OBJECT-TYPE
SYNTAX INTEGER
MAX-ACCESS read-write
STATUS current
DESCRIPTION
"Data value."
::= { dataArray21 312 }

dataValue21_313 OBJECT-TYPE
SYNTAX INTEGER
MAX-ACCESS read-write
STATUS current
DESCRIPTION
"Data value."
::= { dataArray21 313 }

dataValue21_314 OBJECT-TYPE
SYNTAX INTEGER
MAX-ACCESS read-write
STATUS current
DESCRIPTION
"Data value."
::= { dataArray21 314 }

dataValue21_315 OBJECT-TYPE
SYNTAX INTEGER
MAX-ACCESS read-write
STATUS current
DESCRIPTION
"Data value."
::= { dataArray21 315 }

dataValue21_316 OBJECT-TYPE
SYNTAX INTEGER
MAX-ACCESS read-write
STATUS current
DESCRIPTION
"Data value."
::= { dataArray21 316 }

dataValue21_317 OBJECT-TYPE
SYNTAX INTEGER
MAX-ACCESS read-write
STATUS current
DESCRIPTION
"Data value."
::= { dataArray21 317 }

dataValue21_318 OBJECT-TYPE
SYNTAX INTEGER
MAX-ACCESS read-write
STATUS current
DESCRIPTION
"Data value."
::= { dataArray21 318 }

dataValue21_319 OBJECT-TYPE
SYNTAX INTEGER
MAX-ACCESS read-write
STATUS current
DESCRIPTION
"Data value."
::= { dataArray21 319 }

dataValue21_320 OBJECT-TYPE
SYNTAX INTEGER
MAX-ACCESS read-write
STATUS current
DESCRIPTION
"Data value."
::= { dataArray21 320 }

dataValue21_321 OBJECT-TYPE
SYNTAX INTEGER
MAX-ACCESS read-write
STATUS current
DESCRIPTION
"Data value."
::= { dataArray21 321 }

dataValue21_322 OBJECT-TYPE
SYNTAX INTEGER
MAX-ACCESS read-write
STATUS current
DESCRIPTION
"Data value."
::= { dataArray21 322 }

dataValue21_323 OBJECT-TYPE
SYNTAX INTEGER
MAX-ACCESS read-write
STATUS current
DESCRIPTION
"Data value."
::= { dataArray21 323 }

dataValue21_324 OBJECT-TYPE
SYNTAX INTEGER
MAX-ACCESS read-write
STATUS current
DESCRIPTION
"Data value."
::= { dataArray21 324 }

dataValue21_325 OBJECT-TYPE
SYNTAX INTEGER
MAX-ACCESS read-write
STATUS current
DESCRIPTION
"Data value."
::= { dataArray21 325 }

dataValue21_326 OBJECT-TYPE
SYNTAX INTEGER
MAX-ACCESS read-write
STATUS current
DESCRIPTION
"Data value."
::= { dataArray21 326 }

dataValue21_327 OBJECT-TYPE
SYNTAX INTEGER
MAX-ACCESS read-write
STATUS current
DESCRIPTION
"Data value."
::= { dataArray21 327 }

dataValue21_328 OBJECT-TYPE
SYNTAX INTEGER
MAX-ACCESS read-write
STATUS current
DESCRIPTION
"Data value."
::= { dataArray21 328 }

dataValue21_329 OBJECT-TYPE
SYNTAX INTEGER
MAX-ACCESS read-write
STATUS current
DESCRIPTION
"Data value."
::= { dataArray21 329 }

dataValue21_330 OBJECT-TYPE
SYNTAX INTEGER
MAX-ACCESS read-write
STATUS current
DESCRIPTION
"Data value."
::= { dataArray21 330 }

dataValue21_331 OBJECT-TYPE
SYNTAX INTEGER
MAX-ACCESS read-write
STATUS current
DESCRIPTION
"Data value."
::= { dataArray21 331 }

dataValue21_332 OBJECT-TYPE
SYNTAX INTEGER
MAX-ACCESS read-write
STATUS current
DESCRIPTION
"Data value."
::= { dataArray21 332 }

dataValue21_333 OBJECT-TYPE
SYNTAX INTEGER
MAX-ACCESS read-write
STATUS current
DESCRIPTION
"Data value."
::= { dataArray21 333 }

dataValue21_334 OBJECT-TYPE
SYNTAX INTEGER
MAX-ACCESS read-write
STATUS current
DESCRIPTION
"Data value."
::= { dataArray21 334 }

dataValue21_335 OBJECT-TYPE
SYNTAX INTEGER
MAX-ACCESS read-write
STATUS current
DESCRIPTION
"Data value."
::= { dataArray21 335 }

dataValue21_336 OBJECT-TYPE
SYNTAX INTEGER
MAX-ACCESS read-write
STATUS current
DESCRIPTION
"Data value."
::= { dataArray21 336 }

dataValue21_337 OBJECT-TYPE
SYNTAX INTEGER
MAX-ACCESS read-write
STATUS current
DESCRIPTION
"Data value."
::= { dataArray21 337 }

dataValue21_338 OBJECT-TYPE
SYNTAX INTEGER
MAX-ACCESS read-write
STATUS current
DESCRIPTION
"Data value."
::= { dataArray21 338 }

dataValue21_339 OBJECT-TYPE
SYNTAX INTEGER
MAX-ACCESS read-write
STATUS current
DESCRIPTION
"Data value."
::= { dataArray21 339 }

dataValue21_340 OBJECT-TYPE
SYNTAX INTEGER
MAX-ACCESS read-write
STATUS current
DESCRIPTION
"Data value."
::= { dataArray21 340 }

dataValue21_341 OBJECT-TYPE
SYNTAX INTEGER
MAX-ACCESS read-write
STATUS current
DESCRIPTION
"Data value."
::= { dataArray21 341 }

dataValue21_342 OBJECT-TYPE
SYNTAX INTEGER
MAX-ACCESS read-write
STATUS current
DESCRIPTION
"Data value."
::= { dataArray21 342 }

dataValue21_343 OBJECT-TYPE
SYNTAX INTEGER
MAX-ACCESS read-write
STATUS current
DESCRIPTION
"Data value."
::= { dataArray21 343 }

dataValue21_344 OBJECT-TYPE
SYNTAX INTEGER
MAX-ACCESS read-write
STATUS current
DESCRIPTION
"Data value."
::= { dataArray21 344 }

dataValue21_345 OBJECT-TYPE
SYNTAX INTEGER
MAX-ACCESS read-write
STATUS current
DESCRIPTION
"Data value."
::= { dataArray21 345 }

dataValue21_346 OBJECT-TYPE
SYNTAX INTEGER
MAX-ACCESS read-write
STATUS current
DESCRIPTION
"Data value."
::= { dataArray21 346 }

dataValue21_347 OBJECT-TYPE
SYNTAX INTEGER
MAX-ACCESS read-write
STATUS current
DESCRIPTION
"Data value."
::= { dataArray21 347 }

dataValue21_348 OBJECT-TYPE
SYNTAX INTEGER
MAX-ACCESS read-write
STATUS current
DESCRIPTION
"Data value."
::= { dataArray21 348 }

dataValue21_349 OBJECT-TYPE
SYNTAX INTEGER
MAX-ACCESS read-write
STATUS current
DESCRIPTION
"Data value."
::= { dataArray21 349 }

dataValue21_350 OBJECT-TYPE
SYNTAX INTEGER
MAX-ACCESS read-write
STATUS current
DESCRIPTION
"Data value."
::= { dataArray21 350 }

dataValue21_351 OBJECT-TYPE
SYNTAX INTEGER
MAX-ACCESS read-write
STATUS current
DESCRIPTION
"Data value."
::= { dataArray21 351 }

dataValue21_352 OBJECT-TYPE
SYNTAX INTEGER
MAX-ACCESS read-write
STATUS current
DESCRIPTION
"Data value."
::= { dataArray21 352 }

dataValue21_353 OBJECT-TYPE
SYNTAX INTEGER
MAX-ACCESS read-write
STATUS current
DESCRIPTION
"Data value."
::= { dataArray21 353 }

dataValue21_354 OBJECT-TYPE
SYNTAX INTEGER
MAX-ACCESS read-write
STATUS current
DESCRIPTION
"Data value."
::= { dataArray21 354 }

dataValue21_355 OBJECT-TYPE
SYNTAX INTEGER
MAX-ACCESS read-write
STATUS current
DESCRIPTION
"Data value."
::= { dataArray21 355 }

dataValue21_356 OBJECT-TYPE
SYNTAX INTEGER
MAX-ACCESS read-write
STATUS current
DESCRIPTION
"Data value."
::= { dataArray21 356 }

dataValue21_357 OBJECT-TYPE
SYNTAX INTEGER
MAX-ACCESS read-write
STATUS current
DESCRIPTION
"Data value."
::= { dataArray21 357 }

dataValue21_358 OBJECT-TYPE
SYNTAX INTEGER
MAX-ACCESS read-write
STATUS current
DESCRIPTION
"Data value."
::= { dataArray21 358 }

dataValue21_359 OBJECT-TYPE
SYNTAX INTEGER
MAX-ACCESS read-write
STATUS current
DESCRIPTION
"Data value."
::= { dataArray21 359 }

dataValue21_360 OBJECT-TYPE
SYNTAX INTEGER
MAX-ACCESS read-write
STATUS current
DESCRIPTION
"Data value."
::= { dataArray21 360 }

dataValue21_361 OBJECT-TYPE
SYNTAX INTEGER
MAX-ACCESS read-write
STATUS current
DESCRIPTION
"Data value."
::= { dataArray21 361 }

dataValue21_362 OBJECT-TYPE
SYNTAX INTEGER
MAX-ACCESS read-write
STATUS current
DESCRIPTION
"Data value."
::= { dataArray21 362 }

dataValue21_363 OBJECT-TYPE
SYNTAX INTEGER
MAX-ACCESS read-write
STATUS current
DESCRIPTION
"Data value."
::= { dataArray21 363 }

dataValue21_364 OBJECT-TYPE
SYNTAX INTEGER
MAX-ACCESS read-write
STATUS current
DESCRIPTION
"Data value."
::= { dataArray21 364 }

dataValue21_365 OBJECT-TYPE
SYNTAX INTEGER
MAX-ACCESS read-write
STATUS current
DESCRIPTION
"Data value."
::= { dataArray21 365 }

dataValue21_366 OBJECT-TYPE
SYNTAX INTEGER
MAX-ACCESS read-write
STATUS current
DESCRIPTION
"Data value."
::= { dataArray21 366 }

dataValue21_367 OBJECT-TYPE
SYNTAX INTEGER
MAX-ACCESS read-write
STATUS current
DESCRIPTION
"Data value."
::= { dataArray21 367 }

dataValue21_368 OBJECT-TYPE
SYNTAX INTEGER
MAX-ACCESS read-write
STATUS current
DESCRIPTION
"Data value."
::= { dataArray21 368 }

dataValue21_369 OBJECT-TYPE
SYNTAX INTEGER
MAX-ACCESS read-write
STATUS current
DESCRIPTION
"Data value."
::= { dataArray21 369 }

dataValue21_370 OBJECT-TYPE
SYNTAX INTEGER
MAX-ACCESS read-write
STATUS current
DESCRIPTION
"Data value."
::= { dataArray21 370 }

dataValue21_371 OBJECT-TYPE
SYNTAX INTEGER
MAX-ACCESS read-write
STATUS current
DESCRIPTION
"Data value."
::= { dataArray21 371 }

dataValue21_372 OBJECT-TYPE
SYNTAX INTEGER
MAX-ACCESS read-write
STATUS current
DESCRIPTION
"Data value."
::= { dataArray21 372 }

dataValue21_373 OBJECT-TYPE
SYNTAX INTEGER
MAX-ACCESS read-write
STATUS current
DESCRIPTION
"Data value."
::= { dataArray21 373 }

dataValue21_374 OBJECT-TYPE
SYNTAX INTEGER
MAX-ACCESS read-write
STATUS current
DESCRIPTION
"Data value."
::= { dataArray21 374 }

dataValue21_375 OBJECT-TYPE
SYNTAX INTEGER
MAX-ACCESS read-write
STATUS current
DESCRIPTION
"Data value."
::= { dataArray21 375 }

dataValue21_376 OBJECT-TYPE
SYNTAX INTEGER
MAX-ACCESS read-write
STATUS current
DESCRIPTION
"Data value."
::= { dataArray21 376 }

dataValue21_377 OBJECT-TYPE
SYNTAX INTEGER
MAX-ACCESS read-write
STATUS current
DESCRIPTION
"Data value."
::= { dataArray21 377 }

dataValue21_378 OBJECT-TYPE
SYNTAX INTEGER
MAX-ACCESS read-write
STATUS current
DESCRIPTION
"Data value."
::= { dataArray21 378 }

dataValue21_379 OBJECT-TYPE
SYNTAX INTEGER
MAX-ACCESS read-write
STATUS current
DESCRIPTION
"Data value."
::= { dataArray21 379 }

dataValue21_380 OBJECT-TYPE
SYNTAX INTEGER
MAX-ACCESS read-write
STATUS current
DESCRIPTION
"Data value."
::= { dataArray21 380 }

dataValue21_381 OBJECT-TYPE
SYNTAX INTEGER
MAX-ACCESS read-write
STATUS current
DESCRIPTION
"Data value."
::= { dataArray21 381 }

dataValue21_382 OBJECT-TYPE
SYNTAX INTEGER
MAX-ACCESS read-write
STATUS current
DESCRIPTION
"Data value."
::= { dataArray21 382 }

dataValue21_383 OBJECT-TYPE
SYNTAX INTEGER
MAX-ACCESS read-write
STATUS current
DESCRIPTION
"Data value."
::= { dataArray21 383 }

dataValue21_384 OBJECT-TYPE
SYNTAX INTEGER
MAX-ACCESS read-write
STATUS current
DESCRIPTION
"Data value."
::= { dataArray21 384 }

dataValue21_385 OBJECT-TYPE
SYNTAX INTEGER
MAX-ACCESS read-write
STATUS current
DESCRIPTION
"Data value."
::= { dataArray21 385 }

dataValue21_386 OBJECT-TYPE
SYNTAX INTEGER
MAX-ACCESS read-write
STATUS current
DESCRIPTION
"Data value."
::= { dataArray21 386 }

dataValue21_387 OBJECT-TYPE
SYNTAX INTEGER
MAX-ACCESS read-write
STATUS current
DESCRIPTION
"Data value."
::= { dataArray21 387 }

dataValue21_388 OBJECT-TYPE
SYNTAX INTEGER
MAX-ACCESS read-write
STATUS current
DESCRIPTION
"Data value."
::= { dataArray21 388 }

dataValue21_389 OBJECT-TYPE
SYNTAX INTEGER
MAX-ACCESS read-write
STATUS current
DESCRIPTION
"Data value."
::= { dataArray21 389 }

dataValue21_390 OBJECT-TYPE
SYNTAX INTEGER
MAX-ACCESS read-write
STATUS current
DESCRIPTION
"Data value."
::= { dataArray21 390 }

dataValue21_391 OBJECT-TYPE
SYNTAX INTEGER
MAX-ACCESS read-write
STATUS current
DESCRIPTION
"Data value."
::= { dataArray21 391 }

dataValue21_392 OBJECT-TYPE
SYNTAX INTEGER
MAX-ACCESS read-write
STATUS current
DESCRIPTION
"Data value."
::= { dataArray21 392 }

dataValue21_393 OBJECT-TYPE
SYNTAX INTEGER
MAX-ACCESS read-write
STATUS current
DESCRIPTION
"Data value."
::= { dataArray21 393 }

dataValue21_394 OBJECT-TYPE
SYNTAX INTEGER
MAX-ACCESS read-write
STATUS current
DESCRIPTION
"Data value."
::= { dataArray21 394 }

dataValue21_395 OBJECT-TYPE
SYNTAX INTEGER
MAX-ACCESS read-write
STATUS current
DESCRIPTION
"Data value."
::= { dataArray21 395 }

dataValue21_396 OBJECT-TYPE
SYNTAX INTEGER
MAX-ACCESS read-write
STATUS current
DESCRIPTION
"Data value."
::= { dataArray21 396 }

dataValue21_397 OBJECT-TYPE
SYNTAX INTEGER
MAX-ACCESS read-write
STATUS current
DESCRIPTION
"Data value."
::= { dataArray21 397 }

dataValue21_398 OBJECT-TYPE
SYNTAX INTEGER
MAX-ACCESS read-write
STATUS current
DESCRIPTION
"Data value."
::= { dataArray21 398 }

dataValue21_399 OBJECT-TYPE
SYNTAX INTEGER
MAX-ACCESS read-write
STATUS current
DESCRIPTION
"Data value."
::= { dataArray21 399 }

dataArray22 OBJECT IDENTIFIER ::= { cc08255400_v1_00a 22 }

dataValue22_0 OBJECT-TYPE
SYNTAX INTEGER
MAX-ACCESS read-write
STATUS current
DESCRIPTION
"Data value."
::= { dataArray22 0 }

dataValue22_1 OBJECT-TYPE
SYNTAX INTEGER
MAX-ACCESS read-write
STATUS current
DESCRIPTION
"Data value."
::= { dataArray22 1 }

dataValue22_2 OBJECT-TYPE
SYNTAX INTEGER
MAX-ACCESS read-write
STATUS current
DESCRIPTION
"Data value."
::= { dataArray22 2 }

dataValue22_3 OBJECT-TYPE
SYNTAX INTEGER
MAX-ACCESS read-write
STATUS current
DESCRIPTION
"Data value."
::= { dataArray22 3 }

dataValue22_4 OBJECT-TYPE
SYNTAX INTEGER
MAX-ACCESS read-write
STATUS current
DESCRIPTION
"Data value."
::= { dataArray22 4 }

dataValue22_5 OBJECT-TYPE
SYNTAX INTEGER
MAX-ACCESS read-write
STATUS current
DESCRIPTION
"Data value."
::= { dataArray22 5 }

dataValue22_6 OBJECT-TYPE
SYNTAX INTEGER
MAX-ACCESS read-write
STATUS current
DESCRIPTION
"Data value."
::= { dataArray22 6 }

dataValue22_7 OBJECT-TYPE
SYNTAX INTEGER
MAX-ACCESS read-write
STATUS current
DESCRIPTION
"Data value."
::= { dataArray22 7 }

dataValue22_8 OBJECT-TYPE
SYNTAX INTEGER
MAX-ACCESS read-write
STATUS current
DESCRIPTION
"Data value."
::= { dataArray22 8 }

dataValue22_9 OBJECT-TYPE
SYNTAX INTEGER
MAX-ACCESS read-write
STATUS current
DESCRIPTION
"Data value."
::= { dataArray22 9 }

dataValue22_10 OBJECT-TYPE
SYNTAX INTEGER
MAX-ACCESS read-write
STATUS current
DESCRIPTION
"Data value."
::= { dataArray22 10 }

dataValue22_11 OBJECT-TYPE
SYNTAX INTEGER
MAX-ACCESS read-write
STATUS current
DESCRIPTION
"Data value."
::= { dataArray22 11 }

dataValue22_12 OBJECT-TYPE
SYNTAX INTEGER
MAX-ACCESS read-write
STATUS current
DESCRIPTION
"Data value."
::= { dataArray22 12 }

dataValue22_13 OBJECT-TYPE
SYNTAX INTEGER
MAX-ACCESS read-write
STATUS current
DESCRIPTION
"Data value."
::= { dataArray22 13 }

dataValue22_14 OBJECT-TYPE
SYNTAX INTEGER
MAX-ACCESS read-write
STATUS current
DESCRIPTION
"Data value."
::= { dataArray22 14 }

dataValue22_15 OBJECT-TYPE
SYNTAX INTEGER
MAX-ACCESS read-write
STATUS current
DESCRIPTION
"Data value."
::= { dataArray22 15 }

dataValue22_16 OBJECT-TYPE
SYNTAX INTEGER
MAX-ACCESS read-write
STATUS current
DESCRIPTION
"Data value."
::= { dataArray22 16 }

dataValue22_17 OBJECT-TYPE
SYNTAX INTEGER
MAX-ACCESS read-write
STATUS current
DESCRIPTION
"Data value."
::= { dataArray22 17 }

dataValue22_18 OBJECT-TYPE
SYNTAX INTEGER
MAX-ACCESS read-write
STATUS current
DESCRIPTION
"Data value."
::= { dataArray22 18 }

dataValue22_19 OBJECT-TYPE
SYNTAX INTEGER
MAX-ACCESS read-write
STATUS current
DESCRIPTION
"Data value."
::= { dataArray22 19 }

dataValue22_20 OBJECT-TYPE
SYNTAX INTEGER
MAX-ACCESS read-write
STATUS current
DESCRIPTION
"Data value."
::= { dataArray22 20 }

dataValue22_21 OBJECT-TYPE
SYNTAX INTEGER
MAX-ACCESS read-write
STATUS current
DESCRIPTION
"Data value."
::= { dataArray22 21 }

dataValue22_22 OBJECT-TYPE
SYNTAX INTEGER
MAX-ACCESS read-write
STATUS current
DESCRIPTION
"Data value."
::= { dataArray22 22 }

dataValue22_23 OBJECT-TYPE
SYNTAX INTEGER
MAX-ACCESS read-write
STATUS current
DESCRIPTION
"Data value."
::= { dataArray22 23 }

dataValue22_24 OBJECT-TYPE
SYNTAX INTEGER
MAX-ACCESS read-write
STATUS current
DESCRIPTION
"Data value."
::= { dataArray22 24 }

dataValue22_25 OBJECT-TYPE
SYNTAX INTEGER
MAX-ACCESS read-write
STATUS current
DESCRIPTION
"Data value."
::= { dataArray22 25 }

dataValue22_26 OBJECT-TYPE
SYNTAX INTEGER
MAX-ACCESS read-write
STATUS current
DESCRIPTION
"Data value."
::= { dataArray22 26 }

dataValue22_27 OBJECT-TYPE
SYNTAX INTEGER
MAX-ACCESS read-write
STATUS current
DESCRIPTION
"Data value."
::= { dataArray22 27 }

dataValue22_28 OBJECT-TYPE
SYNTAX INTEGER
MAX-ACCESS read-write
STATUS current
DESCRIPTION
"Data value."
::= { dataArray22 28 }

dataValue22_29 OBJECT-TYPE
SYNTAX INTEGER
MAX-ACCESS read-write
STATUS current
DESCRIPTION
"Data value."
::= { dataArray22 29 }

dataValue22_30 OBJECT-TYPE
SYNTAX INTEGER
MAX-ACCESS read-write
STATUS current
DESCRIPTION
"Data value."
::= { dataArray22 30 }

dataValue22_31 OBJECT-TYPE
SYNTAX INTEGER
MAX-ACCESS read-write
STATUS current
DESCRIPTION
"Data value."
::= { dataArray22 31 }

dataValue22_32 OBJECT-TYPE
SYNTAX INTEGER
MAX-ACCESS read-write
STATUS current
DESCRIPTION
"Data value."
::= { dataArray22 32 }

dataValue22_33 OBJECT-TYPE
SYNTAX INTEGER
MAX-ACCESS read-write
STATUS current
DESCRIPTION
"Data value."
::= { dataArray22 33 }

dataValue22_34 OBJECT-TYPE
SYNTAX INTEGER
MAX-ACCESS read-write
STATUS current
DESCRIPTION
"Data value."
::= { dataArray22 34 }

dataValue22_35 OBJECT-TYPE
SYNTAX INTEGER
MAX-ACCESS read-write
STATUS current
DESCRIPTION
"Data value."
::= { dataArray22 35 }

dataValue22_36 OBJECT-TYPE
SYNTAX INTEGER
MAX-ACCESS read-write
STATUS current
DESCRIPTION
"Data value."
::= { dataArray22 36 }

dataValue22_37 OBJECT-TYPE
SYNTAX INTEGER
MAX-ACCESS read-write
STATUS current
DESCRIPTION
"Data value."
::= { dataArray22 37 }

dataValue22_38 OBJECT-TYPE
SYNTAX INTEGER
MAX-ACCESS read-write
STATUS current
DESCRIPTION
"Data value."
::= { dataArray22 38 }

dataValue22_39 OBJECT-TYPE
SYNTAX INTEGER
MAX-ACCESS read-write
STATUS current
DESCRIPTION
"Data value."
::= { dataArray22 39 }

dataValue22_40 OBJECT-TYPE
SYNTAX INTEGER
MAX-ACCESS read-write
STATUS current
DESCRIPTION
"Data value."
::= { dataArray22 40 }

dataValue22_41 OBJECT-TYPE
SYNTAX INTEGER
MAX-ACCESS read-write
STATUS current
DESCRIPTION
"Data value."
::= { dataArray22 41 }

dataValue22_42 OBJECT-TYPE
SYNTAX INTEGER
MAX-ACCESS read-write
STATUS current
DESCRIPTION
"Data value."
::= { dataArray22 42 }

dataValue22_43 OBJECT-TYPE
SYNTAX INTEGER
MAX-ACCESS read-write
STATUS current
DESCRIPTION
"Data value."
::= { dataArray22 43 }

dataValue22_44 OBJECT-TYPE
SYNTAX INTEGER
MAX-ACCESS read-write
STATUS current
DESCRIPTION
"Data value."
::= { dataArray22 44 }

dataValue22_45 OBJECT-TYPE
SYNTAX INTEGER
MAX-ACCESS read-write
STATUS current
DESCRIPTION
"Data value."
::= { dataArray22 45 }

dataValue22_46 OBJECT-TYPE
SYNTAX INTEGER
MAX-ACCESS read-write
STATUS current
DESCRIPTION
"Data value."
::= { dataArray22 46 }

dataValue22_47 OBJECT-TYPE
SYNTAX INTEGER
MAX-ACCESS read-write
STATUS current
DESCRIPTION
"Data value."
::= { dataArray22 47 }

dataValue22_48 OBJECT-TYPE
SYNTAX INTEGER
MAX-ACCESS read-write
STATUS current
DESCRIPTION
"Data value."
::= { dataArray22 48 }

dataValue22_49 OBJECT-TYPE
SYNTAX INTEGER
MAX-ACCESS read-write
STATUS current
DESCRIPTION
"Data value."
::= { dataArray22 49 }

dataValue22_50 OBJECT-TYPE
SYNTAX INTEGER
MAX-ACCESS read-write
STATUS current
DESCRIPTION
"Data value."
::= { dataArray22 50 }

dataValue22_51 OBJECT-TYPE
SYNTAX INTEGER
MAX-ACCESS read-write
STATUS current
DESCRIPTION
"Data value."
::= { dataArray22 51 }

dataValue22_52 OBJECT-TYPE
SYNTAX INTEGER
MAX-ACCESS read-write
STATUS current
DESCRIPTION
"Data value."
::= { dataArray22 52 }

dataValue22_53 OBJECT-TYPE
SYNTAX INTEGER
MAX-ACCESS read-write
STATUS current
DESCRIPTION
"Data value."
::= { dataArray22 53 }

dataValue22_54 OBJECT-TYPE
SYNTAX INTEGER
MAX-ACCESS read-write
STATUS current
DESCRIPTION
"Data value."
::= { dataArray22 54 }

dataValue22_55 OBJECT-TYPE
SYNTAX INTEGER
MAX-ACCESS read-write
STATUS current
DESCRIPTION
"Data value."
::= { dataArray22 55 }

dataValue22_56 OBJECT-TYPE
SYNTAX INTEGER
MAX-ACCESS read-write
STATUS current
DESCRIPTION
"Data value."
::= { dataArray22 56 }

dataValue22_57 OBJECT-TYPE
SYNTAX INTEGER
MAX-ACCESS read-write
STATUS current
DESCRIPTION
"Data value."
::= { dataArray22 57 }

dataValue22_58 OBJECT-TYPE
SYNTAX INTEGER
MAX-ACCESS read-write
STATUS current
DESCRIPTION
"Data value."
::= { dataArray22 58 }

dataValue22_59 OBJECT-TYPE
SYNTAX INTEGER
MAX-ACCESS read-write
STATUS current
DESCRIPTION
"Data value."
::= { dataArray22 59 }

dataValue22_60 OBJECT-TYPE
SYNTAX INTEGER
MAX-ACCESS read-write
STATUS current
DESCRIPTION
"Data value."
::= { dataArray22 60 }

dataValue22_61 OBJECT-TYPE
SYNTAX INTEGER
MAX-ACCESS read-write
STATUS current
DESCRIPTION
"Data value."
::= { dataArray22 61 }

dataValue22_62 OBJECT-TYPE
SYNTAX INTEGER
MAX-ACCESS read-write
STATUS current
DESCRIPTION
"Data value."
::= { dataArray22 62 }

dataValue22_63 OBJECT-TYPE
SYNTAX INTEGER
MAX-ACCESS read-write
STATUS current
DESCRIPTION
"Data value."
::= { dataArray22 63 }

dataValue22_64 OBJECT-TYPE
SYNTAX INTEGER
MAX-ACCESS read-write
STATUS current
DESCRIPTION
"Data value."
::= { dataArray22 64 }

dataValue22_65 OBJECT-TYPE
SYNTAX INTEGER
MAX-ACCESS read-write
STATUS current
DESCRIPTION
"Data value."
::= { dataArray22 65 }

dataValue22_66 OBJECT-TYPE
SYNTAX INTEGER
MAX-ACCESS read-write
STATUS current
DESCRIPTION
"Data value."
::= { dataArray22 66 }

dataValue22_67 OBJECT-TYPE
SYNTAX INTEGER
MAX-ACCESS read-write
STATUS current
DESCRIPTION
"Data value."
::= { dataArray22 67 }

dataValue22_68 OBJECT-TYPE
SYNTAX INTEGER
MAX-ACCESS read-write
STATUS current
DESCRIPTION
"Data value."
::= { dataArray22 68 }

dataValue22_69 OBJECT-TYPE
SYNTAX INTEGER
MAX-ACCESS read-write
STATUS current
DESCRIPTION
"Data value."
::= { dataArray22 69 }

dataValue22_70 OBJECT-TYPE
SYNTAX INTEGER
MAX-ACCESS read-write
STATUS current
DESCRIPTION
"Data value."
::= { dataArray22 70 }

dataValue22_71 OBJECT-TYPE
SYNTAX INTEGER
MAX-ACCESS read-write
STATUS current
DESCRIPTION
"Data value."
::= { dataArray22 71 }

dataValue22_72 OBJECT-TYPE
SYNTAX INTEGER
MAX-ACCESS read-write
STATUS current
DESCRIPTION
"Data value."
::= { dataArray22 72 }

dataValue22_73 OBJECT-TYPE
SYNTAX INTEGER
MAX-ACCESS read-write
STATUS current
DESCRIPTION
"Data value."
::= { dataArray22 73 }

dataValue22_74 OBJECT-TYPE
SYNTAX INTEGER
MAX-ACCESS read-write
STATUS current
DESCRIPTION
"Data value."
::= { dataArray22 74 }

dataValue22_75 OBJECT-TYPE
SYNTAX INTEGER
MAX-ACCESS read-write
STATUS current
DESCRIPTION
"Data value."
::= { dataArray22 75 }

dataValue22_76 OBJECT-TYPE
SYNTAX INTEGER
MAX-ACCESS read-write
STATUS current
DESCRIPTION
"Data value."
::= { dataArray22 76 }

dataValue22_77 OBJECT-TYPE
SYNTAX INTEGER
MAX-ACCESS read-write
STATUS current
DESCRIPTION
"Data value."
::= { dataArray22 77 }

dataValue22_78 OBJECT-TYPE
SYNTAX INTEGER
MAX-ACCESS read-write
STATUS current
DESCRIPTION
"Data value."
::= { dataArray22 78 }

dataValue22_79 OBJECT-TYPE
SYNTAX INTEGER
MAX-ACCESS read-write
STATUS current
DESCRIPTION
"Data value."
::= { dataArray22 79 }

dataValue22_80 OBJECT-TYPE
SYNTAX INTEGER
MAX-ACCESS read-write
STATUS current
DESCRIPTION
"Data value."
::= { dataArray22 80 }

dataValue22_81 OBJECT-TYPE
SYNTAX INTEGER
MAX-ACCESS read-write
STATUS current
DESCRIPTION
"Data value."
::= { dataArray22 81 }

dataValue22_82 OBJECT-TYPE
SYNTAX INTEGER
MAX-ACCESS read-write
STATUS current
DESCRIPTION
"Data value."
::= { dataArray22 82 }

dataValue22_83 OBJECT-TYPE
SYNTAX INTEGER
MAX-ACCESS read-write
STATUS current
DESCRIPTION
"Data value."
::= { dataArray22 83 }

dataValue22_84 OBJECT-TYPE
SYNTAX INTEGER
MAX-ACCESS read-write
STATUS current
DESCRIPTION
"Data value."
::= { dataArray22 84 }

dataValue22_85 OBJECT-TYPE
SYNTAX INTEGER
MAX-ACCESS read-write
STATUS current
DESCRIPTION
"Data value."
::= { dataArray22 85 }

dataValue22_86 OBJECT-TYPE
SYNTAX INTEGER
MAX-ACCESS read-write
STATUS current
DESCRIPTION
"Data value."
::= { dataArray22 86 }

dataValue22_87 OBJECT-TYPE
SYNTAX INTEGER
MAX-ACCESS read-write
STATUS current
DESCRIPTION
"Data value."
::= { dataArray22 87 }

dataValue22_88 OBJECT-TYPE
SYNTAX INTEGER
MAX-ACCESS read-write
STATUS current
DESCRIPTION
"Data value."
::= { dataArray22 88 }

dataValue22_89 OBJECT-TYPE
SYNTAX INTEGER
MAX-ACCESS read-write
STATUS current
DESCRIPTION
"Data value."
::= { dataArray22 89 }

dataValue22_90 OBJECT-TYPE
SYNTAX INTEGER
MAX-ACCESS read-write
STATUS current
DESCRIPTION
"Data value."
::= { dataArray22 90 }

dataValue22_91 OBJECT-TYPE
SYNTAX INTEGER
MAX-ACCESS read-write
STATUS current
DESCRIPTION
"Data value."
::= { dataArray22 91 }

dataValue22_92 OBJECT-TYPE
SYNTAX INTEGER
MAX-ACCESS read-write
STATUS current
DESCRIPTION
"Data value."
::= { dataArray22 92 }

dataValue22_93 OBJECT-TYPE
SYNTAX INTEGER
MAX-ACCESS read-write
STATUS current
DESCRIPTION
"Data value."
::= { dataArray22 93 }

dataValue22_94 OBJECT-TYPE
SYNTAX INTEGER
MAX-ACCESS read-write
STATUS current
DESCRIPTION
"Data value."
::= { dataArray22 94 }

dataValue22_95 OBJECT-TYPE
SYNTAX INTEGER
MAX-ACCESS read-write
STATUS current
DESCRIPTION
"Data value."
::= { dataArray22 95 }

dataValue22_96 OBJECT-TYPE
SYNTAX INTEGER
MAX-ACCESS read-write
STATUS current
DESCRIPTION
"Data value."
::= { dataArray22 96 }

dataValue22_97 OBJECT-TYPE
SYNTAX INTEGER
MAX-ACCESS read-write
STATUS current
DESCRIPTION
"Data value."
::= { dataArray22 97 }

dataValue22_98 OBJECT-TYPE
SYNTAX INTEGER
MAX-ACCESS read-write
STATUS current
DESCRIPTION
"Data value."
::= { dataArray22 98 }

dataValue22_99 OBJECT-TYPE
SYNTAX INTEGER
MAX-ACCESS read-write
STATUS current
DESCRIPTION
"Data value."
::= { dataArray22 99 }

dataValue22_100 OBJECT-TYPE
SYNTAX INTEGER
MAX-ACCESS read-write
STATUS current
DESCRIPTION
"Data value."
::= { dataArray22 100 }

dataValue22_101 OBJECT-TYPE
SYNTAX INTEGER
MAX-ACCESS read-write
STATUS current
DESCRIPTION
"Data value."
::= { dataArray22 101 }

dataValue22_102 OBJECT-TYPE
SYNTAX INTEGER
MAX-ACCESS read-write
STATUS current
DESCRIPTION
"Data value."
::= { dataArray22 102 }

dataValue22_103 OBJECT-TYPE
SYNTAX INTEGER
MAX-ACCESS read-write
STATUS current
DESCRIPTION
"Data value."
::= { dataArray22 103 }

dataValue22_104 OBJECT-TYPE
SYNTAX INTEGER
MAX-ACCESS read-write
STATUS current
DESCRIPTION
"Data value."
::= { dataArray22 104 }

dataValue22_105 OBJECT-TYPE
SYNTAX INTEGER
MAX-ACCESS read-write
STATUS current
DESCRIPTION
"Data value."
::= { dataArray22 105 }

dataValue22_106 OBJECT-TYPE
SYNTAX INTEGER
MAX-ACCESS read-write
STATUS current
DESCRIPTION
"Data value."
::= { dataArray22 106 }

dataValue22_107 OBJECT-TYPE
SYNTAX INTEGER
MAX-ACCESS read-write
STATUS current
DESCRIPTION
"Data value."
::= { dataArray22 107 }

dataValue22_108 OBJECT-TYPE
SYNTAX INTEGER
MAX-ACCESS read-write
STATUS current
DESCRIPTION
"Data value."
::= { dataArray22 108 }

dataValue22_109 OBJECT-TYPE
SYNTAX INTEGER
MAX-ACCESS read-write
STATUS current
DESCRIPTION
"Data value."
::= { dataArray22 109 }

dataValue22_110 OBJECT-TYPE
SYNTAX INTEGER
MAX-ACCESS read-write
STATUS current
DESCRIPTION
"Data value."
::= { dataArray22 110 }

dataValue22_111 OBJECT-TYPE
SYNTAX INTEGER
MAX-ACCESS read-write
STATUS current
DESCRIPTION
"Data value."
::= { dataArray22 111 }

dataValue22_112 OBJECT-TYPE
SYNTAX INTEGER
MAX-ACCESS read-write
STATUS current
DESCRIPTION
"Data value."
::= { dataArray22 112 }

dataValue22_113 OBJECT-TYPE
SYNTAX INTEGER
MAX-ACCESS read-write
STATUS current
DESCRIPTION
"Data value."
::= { dataArray22 113 }

dataValue22_114 OBJECT-TYPE
SYNTAX INTEGER
MAX-ACCESS read-write
STATUS current
DESCRIPTION
"Data value."
::= { dataArray22 114 }

dataValue22_115 OBJECT-TYPE
SYNTAX INTEGER
MAX-ACCESS read-write
STATUS current
DESCRIPTION
"Data value."
::= { dataArray22 115 }

dataValue22_116 OBJECT-TYPE
SYNTAX INTEGER
MAX-ACCESS read-write
STATUS current
DESCRIPTION
"Data value."
::= { dataArray22 116 }

dataValue22_117 OBJECT-TYPE
SYNTAX INTEGER
MAX-ACCESS read-write
STATUS current
DESCRIPTION
"Data value."
::= { dataArray22 117 }

dataValue22_118 OBJECT-TYPE
SYNTAX INTEGER
MAX-ACCESS read-write
STATUS current
DESCRIPTION
"Data value."
::= { dataArray22 118 }

dataValue22_119 OBJECT-TYPE
SYNTAX INTEGER
MAX-ACCESS read-write
STATUS current
DESCRIPTION
"Data value."
::= { dataArray22 119 }

dataValue22_120 OBJECT-TYPE
SYNTAX INTEGER
MAX-ACCESS read-write
STATUS current
DESCRIPTION
"Data value."
::= { dataArray22 120 }

dataValue22_121 OBJECT-TYPE
SYNTAX INTEGER
MAX-ACCESS read-write
STATUS current
DESCRIPTION
"Data value."
::= { dataArray22 121 }

dataValue22_122 OBJECT-TYPE
SYNTAX INTEGER
MAX-ACCESS read-write
STATUS current
DESCRIPTION
"Data value."
::= { dataArray22 122 }

dataValue22_123 OBJECT-TYPE
SYNTAX INTEGER
MAX-ACCESS read-write
STATUS current
DESCRIPTION
"Data value."
::= { dataArray22 123 }

dataValue22_124 OBJECT-TYPE
SYNTAX INTEGER
MAX-ACCESS read-write
STATUS current
DESCRIPTION
"Data value."
::= { dataArray22 124 }

dataValue22_125 OBJECT-TYPE
SYNTAX INTEGER
MAX-ACCESS read-write
STATUS current
DESCRIPTION
"Data value."
::= { dataArray22 125 }

dataValue22_126 OBJECT-TYPE
SYNTAX INTEGER
MAX-ACCESS read-write
STATUS current
DESCRIPTION
"Data value."
::= { dataArray22 126 }

dataValue22_127 OBJECT-TYPE
SYNTAX INTEGER
MAX-ACCESS read-write
STATUS current
DESCRIPTION
"Data value."
::= { dataArray22 127 }

dataValue22_128 OBJECT-TYPE
SYNTAX INTEGER
MAX-ACCESS read-write
STATUS current
DESCRIPTION
"Data value."
::= { dataArray22 128 }

dataValue22_129 OBJECT-TYPE
SYNTAX INTEGER
MAX-ACCESS read-write
STATUS current
DESCRIPTION
"Data value."
::= { dataArray22 129 }

dataValue22_130 OBJECT-TYPE
SYNTAX INTEGER
MAX-ACCESS read-write
STATUS current
DESCRIPTION
"Data value."
::= { dataArray22 130 }

dataValue22_131 OBJECT-TYPE
SYNTAX INTEGER
MAX-ACCESS read-write
STATUS current
DESCRIPTION
"Data value."
::= { dataArray22 131 }

dataValue22_132 OBJECT-TYPE
SYNTAX INTEGER
MAX-ACCESS read-write
STATUS current
DESCRIPTION
"Data value."
::= { dataArray22 132 }

dataValue22_133 OBJECT-TYPE
SYNTAX INTEGER
MAX-ACCESS read-write
STATUS current
DESCRIPTION
"Data value."
::= { dataArray22 133 }

dataValue22_134 OBJECT-TYPE
SYNTAX INTEGER
MAX-ACCESS read-write
STATUS current
DESCRIPTION
"Data value."
::= { dataArray22 134 }

dataValue22_135 OBJECT-TYPE
SYNTAX INTEGER
MAX-ACCESS read-write
STATUS current
DESCRIPTION
"Data value."
::= { dataArray22 135 }

dataValue22_136 OBJECT-TYPE
SYNTAX INTEGER
MAX-ACCESS read-write
STATUS current
DESCRIPTION
"Data value."
::= { dataArray22 136 }

dataValue22_137 OBJECT-TYPE
SYNTAX INTEGER
MAX-ACCESS read-write
STATUS current
DESCRIPTION
"Data value."
::= { dataArray22 137 }

dataValue22_138 OBJECT-TYPE
SYNTAX INTEGER
MAX-ACCESS read-write
STATUS current
DESCRIPTION
"Data value."
::= { dataArray22 138 }

dataValue22_139 OBJECT-TYPE
SYNTAX INTEGER
MAX-ACCESS read-write
STATUS current
DESCRIPTION
"Data value."
::= { dataArray22 139 }

dataValue22_140 OBJECT-TYPE
SYNTAX INTEGER
MAX-ACCESS read-write
STATUS current
DESCRIPTION
"Data value."
::= { dataArray22 140 }

dataValue22_141 OBJECT-TYPE
SYNTAX INTEGER
MAX-ACCESS read-write
STATUS current
DESCRIPTION
"Data value."
::= { dataArray22 141 }

dataValue22_142 OBJECT-TYPE
SYNTAX INTEGER
MAX-ACCESS read-write
STATUS current
DESCRIPTION
"Data value."
::= { dataArray22 142 }

dataValue22_143 OBJECT-TYPE
SYNTAX INTEGER
MAX-ACCESS read-write
STATUS current
DESCRIPTION
"Data value."
::= { dataArray22 143 }

dataValue22_144 OBJECT-TYPE
SYNTAX INTEGER
MAX-ACCESS read-write
STATUS current
DESCRIPTION
"Data value."
::= { dataArray22 144 }

dataValue22_145 OBJECT-TYPE
SYNTAX INTEGER
MAX-ACCESS read-write
STATUS current
DESCRIPTION
"Data value."
::= { dataArray22 145 }

dataValue22_146 OBJECT-TYPE
SYNTAX INTEGER
MAX-ACCESS read-write
STATUS current
DESCRIPTION
"Data value."
::= { dataArray22 146 }

dataValue22_147 OBJECT-TYPE
SYNTAX INTEGER
MAX-ACCESS read-write
STATUS current
DESCRIPTION
"Data value."
::= { dataArray22 147 }

dataValue22_148 OBJECT-TYPE
SYNTAX INTEGER
MAX-ACCESS read-write
STATUS current
DESCRIPTION
"Data value."
::= { dataArray22 148 }

dataValue22_149 OBJECT-TYPE
SYNTAX INTEGER
MAX-ACCESS read-write
STATUS current
DESCRIPTION
"Data value."
::= { dataArray22 149 }

dataValue22_150 OBJECT-TYPE
SYNTAX INTEGER
MAX-ACCESS read-write
STATUS current
DESCRIPTION
"Data value."
::= { dataArray22 150 }

dataValue22_151 OBJECT-TYPE
SYNTAX INTEGER
MAX-ACCESS read-write
STATUS current
DESCRIPTION
"Data value."
::= { dataArray22 151 }

dataValue22_152 OBJECT-TYPE
SYNTAX INTEGER
MAX-ACCESS read-write
STATUS current
DESCRIPTION
"Data value."
::= { dataArray22 152 }

dataValue22_153 OBJECT-TYPE
SYNTAX INTEGER
MAX-ACCESS read-write
STATUS current
DESCRIPTION
"Data value."
::= { dataArray22 153 }

dataValue22_154 OBJECT-TYPE
SYNTAX INTEGER
MAX-ACCESS read-write
STATUS current
DESCRIPTION
"Data value."
::= { dataArray22 154 }

dataValue22_155 OBJECT-TYPE
SYNTAX INTEGER
MAX-ACCESS read-write
STATUS current
DESCRIPTION
"Data value."
::= { dataArray22 155 }

dataValue22_156 OBJECT-TYPE
SYNTAX INTEGER
MAX-ACCESS read-write
STATUS current
DESCRIPTION
"Data value."
::= { dataArray22 156 }

dataValue22_157 OBJECT-TYPE
SYNTAX INTEGER
MAX-ACCESS read-write
STATUS current
DESCRIPTION
"Data value."
::= { dataArray22 157 }

dataValue22_158 OBJECT-TYPE
SYNTAX INTEGER
MAX-ACCESS read-write
STATUS current
DESCRIPTION
"Data value."
::= { dataArray22 158 }

dataValue22_159 OBJECT-TYPE
SYNTAX INTEGER
MAX-ACCESS read-write
STATUS current
DESCRIPTION
"Data value."
::= { dataArray22 159 }

dataValue22_160 OBJECT-TYPE
SYNTAX INTEGER
MAX-ACCESS read-write
STATUS current
DESCRIPTION
"Data value."
::= { dataArray22 160 }

dataValue22_161 OBJECT-TYPE
SYNTAX INTEGER
MAX-ACCESS read-write
STATUS current
DESCRIPTION
"Data value."
::= { dataArray22 161 }

dataValue22_162 OBJECT-TYPE
SYNTAX INTEGER
MAX-ACCESS read-write
STATUS current
DESCRIPTION
"Data value."
::= { dataArray22 162 }

dataValue22_163 OBJECT-TYPE
SYNTAX INTEGER
MAX-ACCESS read-write
STATUS current
DESCRIPTION
"Data value."
::= { dataArray22 163 }

dataValue22_164 OBJECT-TYPE
SYNTAX INTEGER
MAX-ACCESS read-write
STATUS current
DESCRIPTION
"Data value."
::= { dataArray22 164 }

dataValue22_165 OBJECT-TYPE
SYNTAX INTEGER
MAX-ACCESS read-write
STATUS current
DESCRIPTION
"Data value."
::= { dataArray22 165 }

dataValue22_166 OBJECT-TYPE
SYNTAX INTEGER
MAX-ACCESS read-write
STATUS current
DESCRIPTION
"Data value."
::= { dataArray22 166 }

dataValue22_167 OBJECT-TYPE
SYNTAX INTEGER
MAX-ACCESS read-write
STATUS current
DESCRIPTION
"Data value."
::= { dataArray22 167 }

dataValue22_168 OBJECT-TYPE
SYNTAX INTEGER
MAX-ACCESS read-write
STATUS current
DESCRIPTION
"Data value."
::= { dataArray22 168 }

dataValue22_169 OBJECT-TYPE
SYNTAX INTEGER
MAX-ACCESS read-write
STATUS current
DESCRIPTION
"Data value."
::= { dataArray22 169 }

dataValue22_170 OBJECT-TYPE
SYNTAX INTEGER
MAX-ACCESS read-write
STATUS current
DESCRIPTION
"Data value."
::= { dataArray22 170 }

dataValue22_171 OBJECT-TYPE
SYNTAX INTEGER
MAX-ACCESS read-write
STATUS current
DESCRIPTION
"Data value."
::= { dataArray22 171 }

dataValue22_172 OBJECT-TYPE
SYNTAX INTEGER
MAX-ACCESS read-write
STATUS current
DESCRIPTION
"Data value."
::= { dataArray22 172 }

dataValue22_173 OBJECT-TYPE
SYNTAX INTEGER
MAX-ACCESS read-write
STATUS current
DESCRIPTION
"Data value."
::= { dataArray22 173 }

dataValue22_174 OBJECT-TYPE
SYNTAX INTEGER
MAX-ACCESS read-write
STATUS current
DESCRIPTION
"Data value."
::= { dataArray22 174 }

dataValue22_175 OBJECT-TYPE
SYNTAX INTEGER
MAX-ACCESS read-write
STATUS current
DESCRIPTION
"Data value."
::= { dataArray22 175 }

dataValue22_176 OBJECT-TYPE
SYNTAX INTEGER
MAX-ACCESS read-write
STATUS current
DESCRIPTION
"Data value."
::= { dataArray22 176 }

dataValue22_177 OBJECT-TYPE
SYNTAX INTEGER
MAX-ACCESS read-write
STATUS current
DESCRIPTION
"Data value."
::= { dataArray22 177 }

dataValue22_178 OBJECT-TYPE
SYNTAX INTEGER
MAX-ACCESS read-write
STATUS current
DESCRIPTION
"Data value."
::= { dataArray22 178 }

dataValue22_179 OBJECT-TYPE
SYNTAX INTEGER
MAX-ACCESS read-write
STATUS current
DESCRIPTION
"Data value."
::= { dataArray22 179 }

dataValue22_180 OBJECT-TYPE
SYNTAX INTEGER
MAX-ACCESS read-write
STATUS current
DESCRIPTION
"Data value."
::= { dataArray22 180 }

dataValue22_181 OBJECT-TYPE
SYNTAX INTEGER
MAX-ACCESS read-write
STATUS current
DESCRIPTION
"Data value."
::= { dataArray22 181 }

dataValue22_182 OBJECT-TYPE
SYNTAX INTEGER
MAX-ACCESS read-write
STATUS current
DESCRIPTION
"Data value."
::= { dataArray22 182 }

dataValue22_183 OBJECT-TYPE
SYNTAX INTEGER
MAX-ACCESS read-write
STATUS current
DESCRIPTION
"Data value."
::= { dataArray22 183 }

dataValue22_184 OBJECT-TYPE
SYNTAX INTEGER
MAX-ACCESS read-write
STATUS current
DESCRIPTION
"Data value."
::= { dataArray22 184 }

dataValue22_185 OBJECT-TYPE
SYNTAX INTEGER
MAX-ACCESS read-write
STATUS current
DESCRIPTION
"Data value."
::= { dataArray22 185 }

dataValue22_186 OBJECT-TYPE
SYNTAX INTEGER
MAX-ACCESS read-write
STATUS current
DESCRIPTION
"Data value."
::= { dataArray22 186 }

dataValue22_187 OBJECT-TYPE
SYNTAX INTEGER
MAX-ACCESS read-write
STATUS current
DESCRIPTION
"Data value."
::= { dataArray22 187 }

dataValue22_188 OBJECT-TYPE
SYNTAX INTEGER
MAX-ACCESS read-write
STATUS current
DESCRIPTION
"Data value."
::= { dataArray22 188 }

dataValue22_189 OBJECT-TYPE
SYNTAX INTEGER
MAX-ACCESS read-write
STATUS current
DESCRIPTION
"Data value."
::= { dataArray22 189 }

dataValue22_190 OBJECT-TYPE
SYNTAX INTEGER
MAX-ACCESS read-write
STATUS current
DESCRIPTION
"Data value."
::= { dataArray22 190 }

dataValue22_191 OBJECT-TYPE
SYNTAX INTEGER
MAX-ACCESS read-write
STATUS current
DESCRIPTION
"Data value."
::= { dataArray22 191 }

dataValue22_192 OBJECT-TYPE
SYNTAX INTEGER
MAX-ACCESS read-write
STATUS current
DESCRIPTION
"Data value."
::= { dataArray22 192 }

dataValue22_193 OBJECT-TYPE
SYNTAX INTEGER
MAX-ACCESS read-write
STATUS current
DESCRIPTION
"Data value."
::= { dataArray22 193 }

dataValue22_194 OBJECT-TYPE
SYNTAX INTEGER
MAX-ACCESS read-write
STATUS current
DESCRIPTION
"Data value."
::= { dataArray22 194 }

dataValue22_195 OBJECT-TYPE
SYNTAX INTEGER
MAX-ACCESS read-write
STATUS current
DESCRIPTION
"Data value."
::= { dataArray22 195 }

dataValue22_196 OBJECT-TYPE
SYNTAX INTEGER
MAX-ACCESS read-write
STATUS current
DESCRIPTION
"Data value."
::= { dataArray22 196 }

dataValue22_197 OBJECT-TYPE
SYNTAX INTEGER
MAX-ACCESS read-write
STATUS current
DESCRIPTION
"Data value."
::= { dataArray22 197 }

dataValue22_198 OBJECT-TYPE
SYNTAX INTEGER
MAX-ACCESS read-write
STATUS current
DESCRIPTION
"Data value."
::= { dataArray22 198 }

dataValue22_199 OBJECT-TYPE
SYNTAX INTEGER
MAX-ACCESS read-write
STATUS current
DESCRIPTION
"Data value."
::= { dataArray22 199 }

dataValue22_200 OBJECT-TYPE
SYNTAX INTEGER
MAX-ACCESS read-write
STATUS current
DESCRIPTION
"Data value."
::= { dataArray22 200 }

dataValue22_201 OBJECT-TYPE
SYNTAX INTEGER
MAX-ACCESS read-write
STATUS current
DESCRIPTION
"Data value."
::= { dataArray22 201 }

dataValue22_202 OBJECT-TYPE
SYNTAX INTEGER
MAX-ACCESS read-write
STATUS current
DESCRIPTION
"Data value."
::= { dataArray22 202 }

dataValue22_203 OBJECT-TYPE
SYNTAX INTEGER
MAX-ACCESS read-write
STATUS current
DESCRIPTION
"Data value."
::= { dataArray22 203 }

dataValue22_204 OBJECT-TYPE
SYNTAX INTEGER
MAX-ACCESS read-write
STATUS current
DESCRIPTION
"Data value."
::= { dataArray22 204 }

dataValue22_205 OBJECT-TYPE
SYNTAX INTEGER
MAX-ACCESS read-write
STATUS current
DESCRIPTION
"Data value."
::= { dataArray22 205 }

dataValue22_206 OBJECT-TYPE
SYNTAX INTEGER
MAX-ACCESS read-write
STATUS current
DESCRIPTION
"Data value."
::= { dataArray22 206 }

dataValue22_207 OBJECT-TYPE
SYNTAX INTEGER
MAX-ACCESS read-write
STATUS current
DESCRIPTION
"Data value."
::= { dataArray22 207 }

dataValue22_208 OBJECT-TYPE
SYNTAX INTEGER
MAX-ACCESS read-write
STATUS current
DESCRIPTION
"Data value."
::= { dataArray22 208 }

dataValue22_209 OBJECT-TYPE
SYNTAX INTEGER
MAX-ACCESS read-write
STATUS current
DESCRIPTION
"Data value."
::= { dataArray22 209 }

dataValue22_210 OBJECT-TYPE
SYNTAX INTEGER
MAX-ACCESS read-write
STATUS current
DESCRIPTION
"Data value."
::= { dataArray22 210 }

dataValue22_211 OBJECT-TYPE
SYNTAX INTEGER
MAX-ACCESS read-write
STATUS current
DESCRIPTION
"Data value."
::= { dataArray22 211 }

dataValue22_212 OBJECT-TYPE
SYNTAX INTEGER
MAX-ACCESS read-write
STATUS current
DESCRIPTION
"Data value."
::= { dataArray22 212 }

dataValue22_213 OBJECT-TYPE
SYNTAX INTEGER
MAX-ACCESS read-write
STATUS current
DESCRIPTION
"Data value."
::= { dataArray22 213 }

dataValue22_214 OBJECT-TYPE
SYNTAX INTEGER
MAX-ACCESS read-write
STATUS current
DESCRIPTION
"Data value."
::= { dataArray22 214 }

dataValue22_215 OBJECT-TYPE
SYNTAX INTEGER
MAX-ACCESS read-write
STATUS current
DESCRIPTION
"Data value."
::= { dataArray22 215 }

dataValue22_216 OBJECT-TYPE
SYNTAX INTEGER
MAX-ACCESS read-write
STATUS current
DESCRIPTION
"Data value."
::= { dataArray22 216 }

dataValue22_217 OBJECT-TYPE
SYNTAX INTEGER
MAX-ACCESS read-write
STATUS current
DESCRIPTION
"Data value."
::= { dataArray22 217 }

dataValue22_218 OBJECT-TYPE
SYNTAX INTEGER
MAX-ACCESS read-write
STATUS current
DESCRIPTION
"Data value."
::= { dataArray22 218 }

dataValue22_219 OBJECT-TYPE
SYNTAX INTEGER
MAX-ACCESS read-write
STATUS current
DESCRIPTION
"Data value."
::= { dataArray22 219 }

dataValue22_220 OBJECT-TYPE
SYNTAX INTEGER
MAX-ACCESS read-write
STATUS current
DESCRIPTION
"Data value."
::= { dataArray22 220 }

dataValue22_221 OBJECT-TYPE
SYNTAX INTEGER
MAX-ACCESS read-write
STATUS current
DESCRIPTION
"Data value."
::= { dataArray22 221 }

dataValue22_222 OBJECT-TYPE
SYNTAX INTEGER
MAX-ACCESS read-write
STATUS current
DESCRIPTION
"Data value."
::= { dataArray22 222 }

dataValue22_223 OBJECT-TYPE
SYNTAX INTEGER
MAX-ACCESS read-write
STATUS current
DESCRIPTION
"Data value."
::= { dataArray22 223 }

dataValue22_224 OBJECT-TYPE
SYNTAX INTEGER
MAX-ACCESS read-write
STATUS current
DESCRIPTION
"Data value."
::= { dataArray22 224 }

dataValue22_225 OBJECT-TYPE
SYNTAX INTEGER
MAX-ACCESS read-write
STATUS current
DESCRIPTION
"Data value."
::= { dataArray22 225 }

dataValue22_226 OBJECT-TYPE
SYNTAX INTEGER
MAX-ACCESS read-write
STATUS current
DESCRIPTION
"Data value."
::= { dataArray22 226 }

dataValue22_227 OBJECT-TYPE
SYNTAX INTEGER
MAX-ACCESS read-write
STATUS current
DESCRIPTION
"Data value."
::= { dataArray22 227 }

dataValue22_228 OBJECT-TYPE
SYNTAX INTEGER
MAX-ACCESS read-write
STATUS current
DESCRIPTION
"Data value."
::= { dataArray22 228 }

dataValue22_229 OBJECT-TYPE
SYNTAX INTEGER
MAX-ACCESS read-write
STATUS current
DESCRIPTION
"Data value."
::= { dataArray22 229 }

dataValue22_230 OBJECT-TYPE
SYNTAX INTEGER
MAX-ACCESS read-write
STATUS current
DESCRIPTION
"Data value."
::= { dataArray22 230 }

dataValue22_231 OBJECT-TYPE
SYNTAX INTEGER
MAX-ACCESS read-write
STATUS current
DESCRIPTION
"Data value."
::= { dataArray22 231 }

dataValue22_232 OBJECT-TYPE
SYNTAX INTEGER
MAX-ACCESS read-write
STATUS current
DESCRIPTION
"Data value."
::= { dataArray22 232 }

dataValue22_233 OBJECT-TYPE
SYNTAX INTEGER
MAX-ACCESS read-write
STATUS current
DESCRIPTION
"Data value."
::= { dataArray22 233 }

dataValue22_234 OBJECT-TYPE
SYNTAX INTEGER
MAX-ACCESS read-write
STATUS current
DESCRIPTION
"Data value."
::= { dataArray22 234 }

dataValue22_235 OBJECT-TYPE
SYNTAX INTEGER
MAX-ACCESS read-write
STATUS current
DESCRIPTION
"Data value."
::= { dataArray22 235 }

dataValue22_236 OBJECT-TYPE
SYNTAX INTEGER
MAX-ACCESS read-write
STATUS current
DESCRIPTION
"Data value."
::= { dataArray22 236 }

dataValue22_237 OBJECT-TYPE
SYNTAX INTEGER
MAX-ACCESS read-write
STATUS current
DESCRIPTION
"Data value."
::= { dataArray22 237 }

dataValue22_238 OBJECT-TYPE
SYNTAX INTEGER
MAX-ACCESS read-write
STATUS current
DESCRIPTION
"Data value."
::= { dataArray22 238 }

dataValue22_239 OBJECT-TYPE
SYNTAX INTEGER
MAX-ACCESS read-write
STATUS current
DESCRIPTION
"Data value."
::= { dataArray22 239 }

dataValue22_240 OBJECT-TYPE
SYNTAX INTEGER
MAX-ACCESS read-write
STATUS current
DESCRIPTION
"Data value."
::= { dataArray22 240 }

dataValue22_241 OBJECT-TYPE
SYNTAX INTEGER
MAX-ACCESS read-write
STATUS current
DESCRIPTION
"Data value."
::= { dataArray22 241 }

dataValue22_242 OBJECT-TYPE
SYNTAX INTEGER
MAX-ACCESS read-write
STATUS current
DESCRIPTION
"Data value."
::= { dataArray22 242 }

dataValue22_243 OBJECT-TYPE
SYNTAX INTEGER
MAX-ACCESS read-write
STATUS current
DESCRIPTION
"Data value."
::= { dataArray22 243 }

dataValue22_244 OBJECT-TYPE
SYNTAX INTEGER
MAX-ACCESS read-write
STATUS current
DESCRIPTION
"Data value."
::= { dataArray22 244 }

dataValue22_245 OBJECT-TYPE
SYNTAX INTEGER
MAX-ACCESS read-write
STATUS current
DESCRIPTION
"Data value."
::= { dataArray22 245 }

dataValue22_246 OBJECT-TYPE
SYNTAX INTEGER
MAX-ACCESS read-write
STATUS current
DESCRIPTION
"Data value."
::= { dataArray22 246 }

dataValue22_247 OBJECT-TYPE
SYNTAX INTEGER
MAX-ACCESS read-write
STATUS current
DESCRIPTION
"Data value."
::= { dataArray22 247 }

dataValue22_248 OBJECT-TYPE
SYNTAX INTEGER
MAX-ACCESS read-write
STATUS current
DESCRIPTION
"Data value."
::= { dataArray22 248 }

dataValue22_249 OBJECT-TYPE
SYNTAX INTEGER
MAX-ACCESS read-write
STATUS current
DESCRIPTION
"Data value."
::= { dataArray22 249 }

dataValue22_250 OBJECT-TYPE
SYNTAX INTEGER
MAX-ACCESS read-write
STATUS current
DESCRIPTION
"Data value."
::= { dataArray22 250 }

dataValue22_251 OBJECT-TYPE
SYNTAX INTEGER
MAX-ACCESS read-write
STATUS current
DESCRIPTION
"Data value."
::= { dataArray22 251 }

dataValue22_252 OBJECT-TYPE
SYNTAX INTEGER
MAX-ACCESS read-write
STATUS current
DESCRIPTION
"Data value."
::= { dataArray22 252 }

dataValue22_253 OBJECT-TYPE
SYNTAX INTEGER
MAX-ACCESS read-write
STATUS current
DESCRIPTION
"Data value."
::= { dataArray22 253 }

dataValue22_254 OBJECT-TYPE
SYNTAX INTEGER
MAX-ACCESS read-write
STATUS current
DESCRIPTION
"Data value."
::= { dataArray22 254 }

dataValue22_255 OBJECT-TYPE
SYNTAX INTEGER
MAX-ACCESS read-write
STATUS current
DESCRIPTION
"Data value."
::= { dataArray22 255 }

dataValue22_256 OBJECT-TYPE
SYNTAX INTEGER
MAX-ACCESS read-write
STATUS current
DESCRIPTION
"Data value."
::= { dataArray22 256 }

dataValue22_257 OBJECT-TYPE
SYNTAX INTEGER
MAX-ACCESS read-write
STATUS current
DESCRIPTION
"Data value."
::= { dataArray22 257 }

dataValue22_258 OBJECT-TYPE
SYNTAX INTEGER
MAX-ACCESS read-write
STATUS current
DESCRIPTION
"Data value."
::= { dataArray22 258 }

dataValue22_259 OBJECT-TYPE
SYNTAX INTEGER
MAX-ACCESS read-write
STATUS current
DESCRIPTION
"Data value."
::= { dataArray22 259 }

dataValue22_260 OBJECT-TYPE
SYNTAX INTEGER
MAX-ACCESS read-write
STATUS current
DESCRIPTION
"Data value."
::= { dataArray22 260 }

dataValue22_261 OBJECT-TYPE
SYNTAX INTEGER
MAX-ACCESS read-write
STATUS current
DESCRIPTION
"Data value."
::= { dataArray22 261 }

dataValue22_262 OBJECT-TYPE
SYNTAX INTEGER
MAX-ACCESS read-write
STATUS current
DESCRIPTION
"Data value."
::= { dataArray22 262 }

dataValue22_263 OBJECT-TYPE
SYNTAX INTEGER
MAX-ACCESS read-write
STATUS current
DESCRIPTION
"Data value."
::= { dataArray22 263 }

dataValue22_264 OBJECT-TYPE
SYNTAX INTEGER
MAX-ACCESS read-write
STATUS current
DESCRIPTION
"Data value."
::= { dataArray22 264 }

dataValue22_265 OBJECT-TYPE
SYNTAX INTEGER
MAX-ACCESS read-write
STATUS current
DESCRIPTION
"Data value."
::= { dataArray22 265 }

dataValue22_266 OBJECT-TYPE
SYNTAX INTEGER
MAX-ACCESS read-write
STATUS current
DESCRIPTION
"Data value."
::= { dataArray22 266 }

dataValue22_267 OBJECT-TYPE
SYNTAX INTEGER
MAX-ACCESS read-write
STATUS current
DESCRIPTION
"Data value."
::= { dataArray22 267 }

dataValue22_268 OBJECT-TYPE
SYNTAX INTEGER
MAX-ACCESS read-write
STATUS current
DESCRIPTION
"Data value."
::= { dataArray22 268 }

dataValue22_269 OBJECT-TYPE
SYNTAX INTEGER
MAX-ACCESS read-write
STATUS current
DESCRIPTION
"Data value."
::= { dataArray22 269 }

dataValue22_270 OBJECT-TYPE
SYNTAX INTEGER
MAX-ACCESS read-write
STATUS current
DESCRIPTION
"Data value."
::= { dataArray22 270 }

dataValue22_271 OBJECT-TYPE
SYNTAX INTEGER
MAX-ACCESS read-write
STATUS current
DESCRIPTION
"Data value."
::= { dataArray22 271 }

dataValue22_272 OBJECT-TYPE
SYNTAX INTEGER
MAX-ACCESS read-write
STATUS current
DESCRIPTION
"Data value."
::= { dataArray22 272 }

dataValue22_273 OBJECT-TYPE
SYNTAX INTEGER
MAX-ACCESS read-write
STATUS current
DESCRIPTION
"Data value."
::= { dataArray22 273 }

dataValue22_274 OBJECT-TYPE
SYNTAX INTEGER
MAX-ACCESS read-write
STATUS current
DESCRIPTION
"Data value."
::= { dataArray22 274 }

dataValue22_275 OBJECT-TYPE
SYNTAX INTEGER
MAX-ACCESS read-write
STATUS current
DESCRIPTION
"Data value."
::= { dataArray22 275 }

dataValue22_276 OBJECT-TYPE
SYNTAX INTEGER
MAX-ACCESS read-write
STATUS current
DESCRIPTION
"Data value."
::= { dataArray22 276 }

dataValue22_277 OBJECT-TYPE
SYNTAX INTEGER
MAX-ACCESS read-write
STATUS current
DESCRIPTION
"Data value."
::= { dataArray22 277 }

dataValue22_278 OBJECT-TYPE
SYNTAX INTEGER
MAX-ACCESS read-write
STATUS current
DESCRIPTION
"Data value."
::= { dataArray22 278 }

dataValue22_279 OBJECT-TYPE
SYNTAX INTEGER
MAX-ACCESS read-write
STATUS current
DESCRIPTION
"Data value."
::= { dataArray22 279 }

dataValue22_280 OBJECT-TYPE
SYNTAX INTEGER
MAX-ACCESS read-write
STATUS current
DESCRIPTION
"Data value."
::= { dataArray22 280 }

dataValue22_281 OBJECT-TYPE
SYNTAX INTEGER
MAX-ACCESS read-write
STATUS current
DESCRIPTION
"Data value."
::= { dataArray22 281 }

dataValue22_282 OBJECT-TYPE
SYNTAX INTEGER
MAX-ACCESS read-write
STATUS current
DESCRIPTION
"Data value."
::= { dataArray22 282 }

dataValue22_283 OBJECT-TYPE
SYNTAX INTEGER
MAX-ACCESS read-write
STATUS current
DESCRIPTION
"Data value."
::= { dataArray22 283 }

dataValue22_284 OBJECT-TYPE
SYNTAX INTEGER
MAX-ACCESS read-write
STATUS current
DESCRIPTION
"Data value."
::= { dataArray22 284 }

dataValue22_285 OBJECT-TYPE
SYNTAX INTEGER
MAX-ACCESS read-write
STATUS current
DESCRIPTION
"Data value."
::= { dataArray22 285 }

dataValue22_286 OBJECT-TYPE
SYNTAX INTEGER
MAX-ACCESS read-write
STATUS current
DESCRIPTION
"Data value."
::= { dataArray22 286 }

dataValue22_287 OBJECT-TYPE
SYNTAX INTEGER
MAX-ACCESS read-write
STATUS current
DESCRIPTION
"Data value."
::= { dataArray22 287 }

dataValue22_288 OBJECT-TYPE
SYNTAX INTEGER
MAX-ACCESS read-write
STATUS current
DESCRIPTION
"Data value."
::= { dataArray22 288 }

dataValue22_289 OBJECT-TYPE
SYNTAX INTEGER
MAX-ACCESS read-write
STATUS current
DESCRIPTION
"Data value."
::= { dataArray22 289 }

dataValue22_290 OBJECT-TYPE
SYNTAX INTEGER
MAX-ACCESS read-write
STATUS current
DESCRIPTION
"Data value."
::= { dataArray22 290 }

dataValue22_291 OBJECT-TYPE
SYNTAX INTEGER
MAX-ACCESS read-write
STATUS current
DESCRIPTION
"Data value."
::= { dataArray22 291 }

dataValue22_292 OBJECT-TYPE
SYNTAX INTEGER
MAX-ACCESS read-write
STATUS current
DESCRIPTION
"Data value."
::= { dataArray22 292 }

dataValue22_293 OBJECT-TYPE
SYNTAX INTEGER
MAX-ACCESS read-write
STATUS current
DESCRIPTION
"Data value."
::= { dataArray22 293 }

dataValue22_294 OBJECT-TYPE
SYNTAX INTEGER
MAX-ACCESS read-write
STATUS current
DESCRIPTION
"Data value."
::= { dataArray22 294 }

dataValue22_295 OBJECT-TYPE
SYNTAX INTEGER
MAX-ACCESS read-write
STATUS current
DESCRIPTION
"Data value."
::= { dataArray22 295 }

dataValue22_296 OBJECT-TYPE
SYNTAX INTEGER
MAX-ACCESS read-write
STATUS current
DESCRIPTION
"Data value."
::= { dataArray22 296 }

dataValue22_297 OBJECT-TYPE
SYNTAX INTEGER
MAX-ACCESS read-write
STATUS current
DESCRIPTION
"Data value."
::= { dataArray22 297 }

dataValue22_298 OBJECT-TYPE
SYNTAX INTEGER
MAX-ACCESS read-write
STATUS current
DESCRIPTION
"Data value."
::= { dataArray22 298 }

dataValue22_299 OBJECT-TYPE
SYNTAX INTEGER
MAX-ACCESS read-write
STATUS current
DESCRIPTION
"Data value."
::= { dataArray22 299 }

dataValue22_300 OBJECT-TYPE
SYNTAX INTEGER
MAX-ACCESS read-write
STATUS current
DESCRIPTION
"Data value."
::= { dataArray22 300 }

dataValue22_301 OBJECT-TYPE
SYNTAX INTEGER
MAX-ACCESS read-write
STATUS current
DESCRIPTION
"Data value."
::= { dataArray22 301 }

dataValue22_302 OBJECT-TYPE
SYNTAX INTEGER
MAX-ACCESS read-write
STATUS current
DESCRIPTION
"Data value."
::= { dataArray22 302 }

dataValue22_303 OBJECT-TYPE
SYNTAX INTEGER
MAX-ACCESS read-write
STATUS current
DESCRIPTION
"Data value."
::= { dataArray22 303 }

dataValue22_304 OBJECT-TYPE
SYNTAX INTEGER
MAX-ACCESS read-write
STATUS current
DESCRIPTION
"Data value."
::= { dataArray22 304 }

dataValue22_305 OBJECT-TYPE
SYNTAX INTEGER
MAX-ACCESS read-write
STATUS current
DESCRIPTION
"Data value."
::= { dataArray22 305 }

dataValue22_306 OBJECT-TYPE
SYNTAX INTEGER
MAX-ACCESS read-write
STATUS current
DESCRIPTION
"Data value."
::= { dataArray22 306 }

dataValue22_307 OBJECT-TYPE
SYNTAX INTEGER
MAX-ACCESS read-write
STATUS current
DESCRIPTION
"Data value."
::= { dataArray22 307 }

dataValue22_308 OBJECT-TYPE
SYNTAX INTEGER
MAX-ACCESS read-write
STATUS current
DESCRIPTION
"Data value."
::= { dataArray22 308 }

dataValue22_309 OBJECT-TYPE
SYNTAX INTEGER
MAX-ACCESS read-write
STATUS current
DESCRIPTION
"Data value."
::= { dataArray22 309 }

dataValue22_310 OBJECT-TYPE
SYNTAX INTEGER
MAX-ACCESS read-write
STATUS current
DESCRIPTION
"Data value."
::= { dataArray22 310 }

dataValue22_311 OBJECT-TYPE
SYNTAX INTEGER
MAX-ACCESS read-write
STATUS current
DESCRIPTION
"Data value."
::= { dataArray22 311 }

dataValue22_312 OBJECT-TYPE
SYNTAX INTEGER
MAX-ACCESS read-write
STATUS current
DESCRIPTION
"Data value."
::= { dataArray22 312 }

dataValue22_313 OBJECT-TYPE
SYNTAX INTEGER
MAX-ACCESS read-write
STATUS current
DESCRIPTION
"Data value."
::= { dataArray22 313 }

dataValue22_314 OBJECT-TYPE
SYNTAX INTEGER
MAX-ACCESS read-write
STATUS current
DESCRIPTION
"Data value."
::= { dataArray22 314 }

dataValue22_315 OBJECT-TYPE
SYNTAX INTEGER
MAX-ACCESS read-write
STATUS current
DESCRIPTION
"Data value."
::= { dataArray22 315 }

dataValue22_316 OBJECT-TYPE
SYNTAX INTEGER
MAX-ACCESS read-write
STATUS current
DESCRIPTION
"Data value."
::= { dataArray22 316 }

dataValue22_317 OBJECT-TYPE
SYNTAX INTEGER
MAX-ACCESS read-write
STATUS current
DESCRIPTION
"Data value."
::= { dataArray22 317 }

dataValue22_318 OBJECT-TYPE
SYNTAX INTEGER
MAX-ACCESS read-write
STATUS current
DESCRIPTION
"Data value."
::= { dataArray22 318 }

dataValue22_319 OBJECT-TYPE
SYNTAX INTEGER
MAX-ACCESS read-write
STATUS current
DESCRIPTION
"Data value."
::= { dataArray22 319 }

dataValue22_320 OBJECT-TYPE
SYNTAX INTEGER
MAX-ACCESS read-write
STATUS current
DESCRIPTION
"Data value."
::= { dataArray22 320 }

dataValue22_321 OBJECT-TYPE
SYNTAX INTEGER
MAX-ACCESS read-write
STATUS current
DESCRIPTION
"Data value."
::= { dataArray22 321 }

dataValue22_322 OBJECT-TYPE
SYNTAX INTEGER
MAX-ACCESS read-write
STATUS current
DESCRIPTION
"Data value."
::= { dataArray22 322 }

dataValue22_323 OBJECT-TYPE
SYNTAX INTEGER
MAX-ACCESS read-write
STATUS current
DESCRIPTION
"Data value."
::= { dataArray22 323 }

dataValue22_324 OBJECT-TYPE
SYNTAX INTEGER
MAX-ACCESS read-write
STATUS current
DESCRIPTION
"Data value."
::= { dataArray22 324 }

dataValue22_325 OBJECT-TYPE
SYNTAX INTEGER
MAX-ACCESS read-write
STATUS current
DESCRIPTION
"Data value."
::= { dataArray22 325 }

dataValue22_326 OBJECT-TYPE
SYNTAX INTEGER
MAX-ACCESS read-write
STATUS current
DESCRIPTION
"Data value."
::= { dataArray22 326 }

dataValue22_327 OBJECT-TYPE
SYNTAX INTEGER
MAX-ACCESS read-write
STATUS current
DESCRIPTION
"Data value."
::= { dataArray22 327 }

dataValue22_328 OBJECT-TYPE
SYNTAX INTEGER
MAX-ACCESS read-write
STATUS current
DESCRIPTION
"Data value."
::= { dataArray22 328 }

dataValue22_329 OBJECT-TYPE
SYNTAX INTEGER
MAX-ACCESS read-write
STATUS current
DESCRIPTION
"Data value."
::= { dataArray22 329 }

dataValue22_330 OBJECT-TYPE
SYNTAX INTEGER
MAX-ACCESS read-write
STATUS current
DESCRIPTION
"Data value."
::= { dataArray22 330 }

dataValue22_331 OBJECT-TYPE
SYNTAX INTEGER
MAX-ACCESS read-write
STATUS current
DESCRIPTION
"Data value."
::= { dataArray22 331 }

dataValue22_332 OBJECT-TYPE
SYNTAX INTEGER
MAX-ACCESS read-write
STATUS current
DESCRIPTION
"Data value."
::= { dataArray22 332 }

dataValue22_333 OBJECT-TYPE
SYNTAX INTEGER
MAX-ACCESS read-write
STATUS current
DESCRIPTION
"Data value."
::= { dataArray22 333 }

dataValue22_334 OBJECT-TYPE
SYNTAX INTEGER
MAX-ACCESS read-write
STATUS current
DESCRIPTION
"Data value."
::= { dataArray22 334 }

dataValue22_335 OBJECT-TYPE
SYNTAX INTEGER
MAX-ACCESS read-write
STATUS current
DESCRIPTION
"Data value."
::= { dataArray22 335 }

dataValue22_336 OBJECT-TYPE
SYNTAX INTEGER
MAX-ACCESS read-write
STATUS current
DESCRIPTION
"Data value."
::= { dataArray22 336 }

dataValue22_337 OBJECT-TYPE
SYNTAX INTEGER
MAX-ACCESS read-write
STATUS current
DESCRIPTION
"Data value."
::= { dataArray22 337 }

dataValue22_338 OBJECT-TYPE
SYNTAX INTEGER
MAX-ACCESS read-write
STATUS current
DESCRIPTION
"Data value."
::= { dataArray22 338 }

dataValue22_339 OBJECT-TYPE
SYNTAX INTEGER
MAX-ACCESS read-write
STATUS current
DESCRIPTION
"Data value."
::= { dataArray22 339 }

dataValue22_340 OBJECT-TYPE
SYNTAX INTEGER
MAX-ACCESS read-write
STATUS current
DESCRIPTION
"Data value."
::= { dataArray22 340 }

dataValue22_341 OBJECT-TYPE
SYNTAX INTEGER
MAX-ACCESS read-write
STATUS current
DESCRIPTION
"Data value."
::= { dataArray22 341 }

dataValue22_342 OBJECT-TYPE
SYNTAX INTEGER
MAX-ACCESS read-write
STATUS current
DESCRIPTION
"Data value."
::= { dataArray22 342 }

dataValue22_343 OBJECT-TYPE
SYNTAX INTEGER
MAX-ACCESS read-write
STATUS current
DESCRIPTION
"Data value."
::= { dataArray22 343 }

dataValue22_344 OBJECT-TYPE
SYNTAX INTEGER
MAX-ACCESS read-write
STATUS current
DESCRIPTION
"Data value."
::= { dataArray22 344 }

dataValue22_345 OBJECT-TYPE
SYNTAX INTEGER
MAX-ACCESS read-write
STATUS current
DESCRIPTION
"Data value."
::= { dataArray22 345 }

dataValue22_346 OBJECT-TYPE
SYNTAX INTEGER
MAX-ACCESS read-write
STATUS current
DESCRIPTION
"Data value."
::= { dataArray22 346 }

dataValue22_347 OBJECT-TYPE
SYNTAX INTEGER
MAX-ACCESS read-write
STATUS current
DESCRIPTION
"Data value."
::= { dataArray22 347 }

dataValue22_348 OBJECT-TYPE
SYNTAX INTEGER
MAX-ACCESS read-write
STATUS current
DESCRIPTION
"Data value."
::= { dataArray22 348 }

dataValue22_349 OBJECT-TYPE
SYNTAX INTEGER
MAX-ACCESS read-write
STATUS current
DESCRIPTION
"Data value."
::= { dataArray22 349 }

dataValue22_350 OBJECT-TYPE
SYNTAX INTEGER
MAX-ACCESS read-write
STATUS current
DESCRIPTION
"Data value."
::= { dataArray22 350 }

dataValue22_351 OBJECT-TYPE
SYNTAX INTEGER
MAX-ACCESS read-write
STATUS current
DESCRIPTION
"Data value."
::= { dataArray22 351 }

dataValue22_352 OBJECT-TYPE
SYNTAX INTEGER
MAX-ACCESS read-write
STATUS current
DESCRIPTION
"Data value."
::= { dataArray22 352 }

dataValue22_353 OBJECT-TYPE
SYNTAX INTEGER
MAX-ACCESS read-write
STATUS current
DESCRIPTION
"Data value."
::= { dataArray22 353 }

dataValue22_354 OBJECT-TYPE
SYNTAX INTEGER
MAX-ACCESS read-write
STATUS current
DESCRIPTION
"Data value."
::= { dataArray22 354 }

dataValue22_355 OBJECT-TYPE
SYNTAX INTEGER
MAX-ACCESS read-write
STATUS current
DESCRIPTION
"Data value."
::= { dataArray22 355 }

dataValue22_356 OBJECT-TYPE
SYNTAX INTEGER
MAX-ACCESS read-write
STATUS current
DESCRIPTION
"Data value."
::= { dataArray22 356 }

dataValue22_357 OBJECT-TYPE
SYNTAX INTEGER
MAX-ACCESS read-write
STATUS current
DESCRIPTION
"Data value."
::= { dataArray22 357 }

dataValue22_358 OBJECT-TYPE
SYNTAX INTEGER
MAX-ACCESS read-write
STATUS current
DESCRIPTION
"Data value."
::= { dataArray22 358 }

dataValue22_359 OBJECT-TYPE
SYNTAX INTEGER
MAX-ACCESS read-write
STATUS current
DESCRIPTION
"Data value."
::= { dataArray22 359 }

dataValue22_360 OBJECT-TYPE
SYNTAX INTEGER
MAX-ACCESS read-write
STATUS current
DESCRIPTION
"Data value."
::= { dataArray22 360 }

dataValue22_361 OBJECT-TYPE
SYNTAX INTEGER
MAX-ACCESS read-write
STATUS current
DESCRIPTION
"Data value."
::= { dataArray22 361 }

dataValue22_362 OBJECT-TYPE
SYNTAX INTEGER
MAX-ACCESS read-write
STATUS current
DESCRIPTION
"Data value."
::= { dataArray22 362 }

dataValue22_363 OBJECT-TYPE
SYNTAX INTEGER
MAX-ACCESS read-write
STATUS current
DESCRIPTION
"Data value."
::= { dataArray22 363 }

dataValue22_364 OBJECT-TYPE
SYNTAX INTEGER
MAX-ACCESS read-write
STATUS current
DESCRIPTION
"Data value."
::= { dataArray22 364 }

dataValue22_365 OBJECT-TYPE
SYNTAX INTEGER
MAX-ACCESS read-write
STATUS current
DESCRIPTION
"Data value."
::= { dataArray22 365 }

dataValue22_366 OBJECT-TYPE
SYNTAX INTEGER
MAX-ACCESS read-write
STATUS current
DESCRIPTION
"Data value."
::= { dataArray22 366 }

dataValue22_367 OBJECT-TYPE
SYNTAX INTEGER
MAX-ACCESS read-write
STATUS current
DESCRIPTION
"Data value."
::= { dataArray22 367 }

dataValue22_368 OBJECT-TYPE
SYNTAX INTEGER
MAX-ACCESS read-write
STATUS current
DESCRIPTION
"Data value."
::= { dataArray22 368 }

dataValue22_369 OBJECT-TYPE
SYNTAX INTEGER
MAX-ACCESS read-write
STATUS current
DESCRIPTION
"Data value."
::= { dataArray22 369 }

dataValue22_370 OBJECT-TYPE
SYNTAX INTEGER
MAX-ACCESS read-write
STATUS current
DESCRIPTION
"Data value."
::= { dataArray22 370 }

dataValue22_371 OBJECT-TYPE
SYNTAX INTEGER
MAX-ACCESS read-write
STATUS current
DESCRIPTION
"Data value."
::= { dataArray22 371 }

dataValue22_372 OBJECT-TYPE
SYNTAX INTEGER
MAX-ACCESS read-write
STATUS current
DESCRIPTION
"Data value."
::= { dataArray22 372 }

dataValue22_373 OBJECT-TYPE
SYNTAX INTEGER
MAX-ACCESS read-write
STATUS current
DESCRIPTION
"Data value."
::= { dataArray22 373 }

dataValue22_374 OBJECT-TYPE
SYNTAX INTEGER
MAX-ACCESS read-write
STATUS current
DESCRIPTION
"Data value."
::= { dataArray22 374 }

dataValue22_375 OBJECT-TYPE
SYNTAX INTEGER
MAX-ACCESS read-write
STATUS current
DESCRIPTION
"Data value."
::= { dataArray22 375 }

dataValue22_376 OBJECT-TYPE
SYNTAX INTEGER
MAX-ACCESS read-write
STATUS current
DESCRIPTION
"Data value."
::= { dataArray22 376 }

dataValue22_377 OBJECT-TYPE
SYNTAX INTEGER
MAX-ACCESS read-write
STATUS current
DESCRIPTION
"Data value."
::= { dataArray22 377 }

dataValue22_378 OBJECT-TYPE
SYNTAX INTEGER
MAX-ACCESS read-write
STATUS current
DESCRIPTION
"Data value."
::= { dataArray22 378 }

dataValue22_379 OBJECT-TYPE
SYNTAX INTEGER
MAX-ACCESS read-write
STATUS current
DESCRIPTION
"Data value."
::= { dataArray22 379 }

dataValue22_380 OBJECT-TYPE
SYNTAX INTEGER
MAX-ACCESS read-write
STATUS current
DESCRIPTION
"Data value."
::= { dataArray22 380 }

dataValue22_381 OBJECT-TYPE
SYNTAX INTEGER
MAX-ACCESS read-write
STATUS current
DESCRIPTION
"Data value."
::= { dataArray22 381 }

dataValue22_382 OBJECT-TYPE
SYNTAX INTEGER
MAX-ACCESS read-write
STATUS current
DESCRIPTION
"Data value."
::= { dataArray22 382 }

dataValue22_383 OBJECT-TYPE
SYNTAX INTEGER
MAX-ACCESS read-write
STATUS current
DESCRIPTION
"Data value."
::= { dataArray22 383 }

dataValue22_384 OBJECT-TYPE
SYNTAX INTEGER
MAX-ACCESS read-write
STATUS current
DESCRIPTION
"Data value."
::= { dataArray22 384 }

dataValue22_385 OBJECT-TYPE
SYNTAX INTEGER
MAX-ACCESS read-write
STATUS current
DESCRIPTION
"Data value."
::= { dataArray22 385 }

dataValue22_386 OBJECT-TYPE
SYNTAX INTEGER
MAX-ACCESS read-write
STATUS current
DESCRIPTION
"Data value."
::= { dataArray22 386 }

dataValue22_387 OBJECT-TYPE
SYNTAX INTEGER
MAX-ACCESS read-write
STATUS current
DESCRIPTION
"Data value."
::= { dataArray22 387 }

dataValue22_388 OBJECT-TYPE
SYNTAX INTEGER
MAX-ACCESS read-write
STATUS current
DESCRIPTION
"Data value."
::= { dataArray22 388 }

dataValue22_389 OBJECT-TYPE
SYNTAX INTEGER
MAX-ACCESS read-write
STATUS current
DESCRIPTION
"Data value."
::= { dataArray22 389 }

dataValue22_390 OBJECT-TYPE
SYNTAX INTEGER
MAX-ACCESS read-write
STATUS current
DESCRIPTION
"Data value."
::= { dataArray22 390 }

dataValue22_391 OBJECT-TYPE
SYNTAX INTEGER
MAX-ACCESS read-write
STATUS current
DESCRIPTION
"Data value."
::= { dataArray22 391 }

dataValue22_392 OBJECT-TYPE
SYNTAX INTEGER
MAX-ACCESS read-write
STATUS current
DESCRIPTION
"Data value."
::= { dataArray22 392 }

dataValue22_393 OBJECT-TYPE
SYNTAX INTEGER
MAX-ACCESS read-write
STATUS current
DESCRIPTION
"Data value."
::= { dataArray22 393 }

dataValue22_394 OBJECT-TYPE
SYNTAX INTEGER
MAX-ACCESS read-write
STATUS current
DESCRIPTION
"Data value."
::= { dataArray22 394 }

dataValue22_395 OBJECT-TYPE
SYNTAX INTEGER
MAX-ACCESS read-write
STATUS current
DESCRIPTION
"Data value."
::= { dataArray22 395 }

dataValue22_396 OBJECT-TYPE
SYNTAX INTEGER
MAX-ACCESS read-write
STATUS current
DESCRIPTION
"Data value."
::= { dataArray22 396 }

dataValue22_397 OBJECT-TYPE
SYNTAX INTEGER
MAX-ACCESS read-write
STATUS current
DESCRIPTION
"Data value."
::= { dataArray22 397 }

dataValue22_398 OBJECT-TYPE
SYNTAX INTEGER
MAX-ACCESS read-write
STATUS current
DESCRIPTION
"Data value."
::= { dataArray22 398 }

dataValue22_399 OBJECT-TYPE
SYNTAX INTEGER
MAX-ACCESS read-write
STATUS current
DESCRIPTION
"Data value."
::= { dataArray22 399 }

END
