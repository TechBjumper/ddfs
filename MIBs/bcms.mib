--------------------------------------------------------------------------------
-- PDI MODBUS/SNMP MIB FOR BCMS
--
-- Revision 1.00
-- June 7, 2004
--------------------------------------------------------------------------------
BCMS DEFINITIONS ::= BEGIN
IMPORTS
org, iso, dod, internet, directory, mgmt, experimental, private, enterprises
FROM RFC-1155-SMI
OBJECT-TYPE
FROM RFC-1212
DisplayString
FROM RFC-1213;
--------------------------------------------------------------------------------
-- OID hierarchy
--------------------------------------------------------------------------------
PDI OBJECT IDENTIFIER ::= { enterprises 11273 }
products OBJECT IDENTIFIER ::= { PDI 1 }
bcms OBJECT IDENTIFIER ::= { products 7 }
bcmsVars OBJECT IDENTIFIER ::= { bcms 1 }
bcmsTraps OBJECT IDENTIFIER ::= { bcms 9 }
--------------------------------------------------------------------------------
-- BCMS Variables
--------------------------------------------------------------------------------
ioFailCount OBJECT-TYPE
SYNTAX INTEGER
ACCESS read-only
STATUS mandatory
DESCRIPTION "Consectutive I/O failure count"
::= { bcmsVars 100 }
ioFailThreshold OBJECT-TYPE
SYNTAX INTEGER
ACCESS read-write
STATUS mandatory
DESCRIPTION "Number of consecutive I/O failures before trap"
::= { bcmsVars 101 }
--------------------------------------------------------------------------------
-- BCMS register values
--------------------------------------------------------------------------------
reg1A1 OBJECT-TYPE
SYNTAX INTEGER
ACCESS read-only
STATUS mandatory
DESCRIPTION "Register 1A1"
::= { bcmsVars 1 }

reg1B2 OBJECT-TYPE
SYNTAX INTEGER
ACCESS read-only
STATUS mandatory
DESCRIPTION "Register 1B2"
::= { bcmsVars 2 }
reg1A3 OBJECT-TYPE
SYNTAX INTEGER
ACCESS read-only
STATUS mandatory
DESCRIPTION "Register 1A3"
::= { bcmsVars 3 }
reg1B4 OBJECT-TYPE
SYNTAX INTEGER
ACCESS read-only
STATUS mandatory
DESCRIPTION "Register 1B4"
::= { bcmsVars 4 }
reg1A5 OBJECT-TYPE
SYNTAX INTEGER
ACCESS read-only
STATUS mandatory
DESCRIPTION "Register 1A5"
::= { bcmsVars 5 }
reg1B6 OBJECT-TYPE
SYNTAX INTEGER
ACCESS read-only
STATUS mandatory
DESCRIPTION "Register 1B6"
::= { bcmsVars 6 }
reg1A7 OBJECT-TYPE
SYNTAX INTEGER
ACCESS read-only
STATUS mandatory
DESCRIPTION "Register 1A7"
::= { bcmsVars 7 }
reg1B8 OBJECT-TYPE
SYNTAX INTEGER
ACCESS read-only
STATUS mandatory
DESCRIPTION "Register 1B8"
::= { bcmsVars 8 }
reg1A9 OBJECT-TYPE
SYNTAX INTEGER
ACCESS read-only
STATUS mandatory
DESCRIPTION "Register 1A9"
::= { bcmsVars 9 }

reg1B10 OBJECT-TYPE
SYNTAX INTEGER
ACCESS read-only
STATUS mandatory
DESCRIPTION "Register 1B10"
::= { bcmsVars 10 }
reg1A11 OBJECT-TYPE
SYNTAX INTEGER
ACCESS read-only
STATUS mandatory
DESCRIPTION "Register 1A11"
::= { bcmsVars 11 }
reg1B12 OBJECT-TYPE
SYNTAX INTEGER
ACCESS read-only
STATUS mandatory
DESCRIPTION "Register 1B12"
::= { bcmsVars 12 }
reg1A13 OBJECT-TYPE
SYNTAX INTEGER
ACCESS read-only
STATUS mandatory
DESCRIPTION "Register 1A13"
::= { bcmsVars 13 }
reg1B14 OBJECT-TYPE
SYNTAX INTEGER
ACCESS read-only
STATUS mandatory
DESCRIPTION "Register 1B14"
::= { bcmsVars 14 }
reg1A15 OBJECT-TYPE
SYNTAX INTEGER
ACCESS read-only
STATUS mandatory
DESCRIPTION "Register 1A15"
::= { bcmsVars 15 }
reg1B16 OBJECT-TYPE
SYNTAX INTEGER
ACCESS read-only
STATUS mandatory
DESCRIPTION "Register 1B16"
::= { bcmsVars 16 }
reg1A17 OBJECT-TYPE
SYNTAX INTEGER
ACCESS read-only
STATUS mandatory
DESCRIPTION "Register 1A17"
::= { bcmsVars 17 }

reg1B18 OBJECT-TYPE
SYNTAX INTEGER
ACCESS read-only
STATUS mandatory
DESCRIPTION "Register 1B18 "
::= { bcmsVars 18 }
reg1A19 OBJECT-TYPE
SYNTAX INTEGER
ACCESS read-only
STATUS mandatory
DESCRIPTION "Register 1A19"
::= { bcmsVars 19 }
reg1B20 OBJECT-TYPE
SYNTAX INTEGER
ACCESS read-only
STATUS mandatory
DESCRIPTION "Register 1B20"
::= { bcmsVars 20 }
reg1A21 OBJECT-TYPE
SYNTAX INTEGER
ACCESS read-only
STATUS mandatory
DESCRIPTION "Register 1A21"
::= { bcmsVars 21 }
reg1B22 OBJECT-TYPE
SYNTAX INTEGER
ACCESS read-only
STATUS mandatory
DESCRIPTION "Register 1B22"
::= { bcmsVars 22 }
reg1A23 OBJECT-TYPE
SYNTAX INTEGER
ACCESS read-only
STATUS mandatory
DESCRIPTION "Register 1A23"
::= { bcmsVars 23 }
reg1B24 OBJECT-TYPE
SYNTAX INTEGER
ACCESS read-only
STATUS mandatory
DESCRIPTION "Register 1B24"
::= { bcmsVars 24 }
reg1A25 OBJECT-TYPE
SYNTAX INTEGER
ACCESS read-only
STATUS mandatory
DESCRIPTION "Register 1A25"
::= { bcmsVars 25 }

reg1B26 OBJECT-TYPE
SYNTAX INTEGER
ACCESS read-only
STATUS mandatory
DESCRIPTION "Register 1B26"
::= { bcmsVars 26 }
reg1A27 OBJECT-TYPE
SYNTAX INTEGER
ACCESS read-only
STATUS mandatory
DESCRIPTION "Register 1A27"
::= { bcmsVars 27 }
reg1B28 OBJECT-TYPE
SYNTAX INTEGER
ACCESS read-only
STATUS mandatory
DESCRIPTION "Register 1B28"
::= { bcmsVars 28 }
reg1A29 OBJECT-TYPE
SYNTAX INTEGER
ACCESS read-only
STATUS mandatory
DESCRIPTION "Register 1A29"
::= { bcmsVars 29 }
reg1B30 OBJECT-TYPE
SYNTAX INTEGER
ACCESS read-only
STATUS mandatory
DESCRIPTION "Register 1B30"
::= { bcmsVars 30 }
reg1A31 OBJECT-TYPE
SYNTAX INTEGER
ACCESS read-only
STATUS mandatory
DESCRIPTION "Register 1A31"
::= { bcmsVars 31 }
reg1B32 OBJECT-TYPE
SYNTAX INTEGER
ACCESS read-only
STATUS mandatory
DESCRIPTION "Register 1B32"
::= { bcmsVars 32 }
reg1A33 OBJECT-TYPE
SYNTAX INTEGER
ACCESS read-only
STATUS mandatory
DESCRIPTION "Register 1A33"
::= { bcmsVars 33 }

reg1B34 OBJECT-TYPE
SYNTAX INTEGER
ACCESS read-only
STATUS mandatory
DESCRIPTION "Register 1B34"
::= { bcmsVars 34 }
reg1A35 OBJECT-TYPE
SYNTAX INTEGER
ACCESS read-only
STATUS mandatory
DESCRIPTION "Register 1A35"
::= { bcmsVars 35 }
reg1B36 OBJECT-TYPE
SYNTAX INTEGER
ACCESS read-only
STATUS mandatory
DESCRIPTION "Register 1B36"
::= { bcmsVars 36 }
reg1A37 OBJECT-TYPE
SYNTAX INTEGER
ACCESS read-only
STATUS mandatory
DESCRIPTION "Register 1A37"
::= { bcmsVars 37 }
reg1B38 OBJECT-TYPE
SYNTAX INTEGER
ACCESS read-only
STATUS mandatory
DESCRIPTION "Register 1B38"
::= { bcmsVars 38 }
reg1A39 OBJECT-TYPE
SYNTAX INTEGER
ACCESS read-only
STATUS mandatory
DESCRIPTION "Register 1A39"
::= { bcmsVars 39 }
reg1B40 OBJECT-TYPE
SYNTAX INTEGER
ACCESS read-only
STATUS mandatory
DESCRIPTION "Register 1B40"
::= { bcmsVars 40 }
reg1A41 OBJECT-TYPE
SYNTAX INTEGER
ACCESS read-only
STATUS mandatory
DESCRIPTION "Register 1A41"
::= { bcmsVars 41 }

reg1A42 OBJECT-TYPE
SYNTAX INTEGER
ACCESS read-only
STATUS mandatory
DESCRIPTION "Register 1A42"
::= { bcmsVars 42 }
reg2A1 OBJECT-TYPE
SYNTAX INTEGER
ACCESS read-only
STATUS mandatory
DESCRIPTION "Register 2A1"
::= { bcmsVars 43 }
reg2B2 OBJECT-TYPE
SYNTAX INTEGER
ACCESS read-only
STATUS mandatory
DESCRIPTION "Register 2B2"
::= { bcmsVars 44 }
reg2A3 OBJECT-TYPE
SYNTAX INTEGER
ACCESS read-only
STATUS mandatory
DESCRIPTION "Register 2A3"
::= { bcmsVars 45 }
reg2B4 OBJECT-TYPE
SYNTAX INTEGER
ACCESS read-only
STATUS mandatory
DESCRIPTION "Register 2B4"
::= { bcmsVars 46 }
reg2A5 OBJECT-TYPE
SYNTAX INTEGER
ACCESS read-only
STATUS mandatory
DESCRIPTION "Register 2A5"
::= { bcmsVars 47 }
reg2B6 OBJECT-TYPE
SYNTAX INTEGER
ACCESS read-only
STATUS mandatory
DESCRIPTION "Register 2B6"
::= { bcmsVars 48 }
reg2A7 OBJECT-TYPE
SYNTAX INTEGER
ACCESS read-only
STATUS mandatory
DESCRIPTION "Register 2A7"
::= { bcmsVars 49 }
reg2B8 OBJECT-TYPE
SYNTAX INTEGER
ACCESS read-only
STATUS mandatory
DESCRIPTION "Register 2B8"
::= { bcmsVars 50 }
reg2A9 OBJECT-TYPE
SYNTAX INTEGER
ACCESS read-only
STATUS mandatory
DESCRIPTION "Register 2A9"
::= { bcmsVars 51 }
reg2B10 OBJECT-TYPE
SYNTAX INTEGER
ACCESS read-only
STATUS mandatory
DESCRIPTION "Register 2B10"
::= { bcmsVars 52 }
reg2A11 OBJECT-TYPE
SYNTAX INTEGER
ACCESS read-only
STATUS mandatory
DESCRIPTION "Register 2A11"
::= { bcmsVars 53 }
reg2B12 OBJECT-TYPE
SYNTAX INTEGER
ACCESS read-only
STATUS mandatory
DESCRIPTION "Register 2B12"
::= { bcmsVars 54 }
reg2A13 OBJECT-TYPE
SYNTAX INTEGER
ACCESS read-only
STATUS mandatory
DESCRIPTION "Register 2A13"
::= { bcmsVars 55 }
reg2B14 OBJECT-TYPE
SYNTAX INTEGER
ACCESS read-only
STATUS mandatory
DESCRIPTION "Register 2B14"
::= { bcmsVars 56 }
reg2A15 OBJECT-TYPE
SYNTAX INTEGER
ACCESS read-only
STATUS mandatory
DESCRIPTION "Register 2A15"
::= { bcmsVars 57 }
reg2B16 OBJECT-TYPE
SYNTAX INTEGER
ACCESS read-only
STATUS mandatory
DESCRIPTION "Register 2B16"
::= { bcmsVars 58 }
reg2A17 OBJECT-TYPE
SYNTAX INTEGER
ACCESS read-only
STATUS mandatory
DESCRIPTION "Register 2A17"
::= { bcmsVars 59 }
reg2B18 OBJECT-TYPE
SYNTAX INTEGER
ACCESS read-only
STATUS mandatory
DESCRIPTION "Register 2B18"
::= { bcmsVars 60 }
reg2A19 OBJECT-TYPE
SYNTAX INTEGER
ACCESS read-only
STATUS mandatory
DESCRIPTION "Register 2A19"
::= { bcmsVars 61 }
reg2B20 OBJECT-TYPE
SYNTAX INTEGER
ACCESS read-only
STATUS mandatory
DESCRIPTION "Register 2B20"
::= { bcmsVars 62 }
reg2A21 OBJECT-TYPE
SYNTAX INTEGER
ACCESS read-only
STATUS mandatory
DESCRIPTION "Register 2A21"
::= { bcmsVars 63 }
reg2B22 OBJECT-TYPE
SYNTAX INTEGER
ACCESS read-only
STATUS mandatory
DESCRIPTION "Register 2B22"
::= { bcmsVars 64 }
reg2A23 OBJECT-TYPE
SYNTAX INTEGER
ACCESS read-only
STATUS mandatory
DESCRIPTION "Register 2A23"
::= { bcmsVars 65 }
reg2B24 OBJECT-TYPE
SYNTAX INTEGER
ACCESS read-only
STATUS mandatory
DESCRIPTION "Register 2B24"
::= { bcmsVars 66 }
reg2A25 OBJECT-TYPE
SYNTAX INTEGER
ACCESS read-only
STATUS mandatory
DESCRIPTION "Register 2A25"
::= { bcmsVars 67 }
reg2B26 OBJECT-TYPE
SYNTAX INTEGER
ACCESS read-only
STATUS mandatory
DESCRIPTION "Register 2B26"
::= { bcmsVars 68 }
reg2A27 OBJECT-TYPE
SYNTAX INTEGER
ACCESS read-only
STATUS mandatory
DESCRIPTION "Register 2A27"
::= { bcmsVars 69 }
reg2B28 OBJECT-TYPE
SYNTAX INTEGER
ACCESS read-only
STATUS mandatory
DESCRIPTION "Register 2B28"
::= { bcmsVars 70 }
reg2A29 OBJECT-TYPE
SYNTAX INTEGER
ACCESS read-only
STATUS mandatory
DESCRIPTION "Register 2A29"
::= { bcmsVars 71 }
reg2B30 OBJECT-TYPE
SYNTAX INTEGER
ACCESS read-only
STATUS mandatory
DESCRIPTION "Register 2B30"
::= { bcmsVars 72 }
reg2A31 OBJECT-TYPE
SYNTAX INTEGER
ACCESS read-only
STATUS mandatory
DESCRIPTION "Register 2A31"
::= { bcmsVars 73 }
reg2B32 OBJECT-TYPE
SYNTAX INTEGER
ACCESS read-only
STATUS mandatory
DESCRIPTION "Register 2B32"
::= { bcmsVars 74 }
reg2A33 OBJECT-TYPE
SYNTAX INTEGER
ACCESS read-only
STATUS mandatory
DESCRIPTION "Register 2A33"
::= { bcmsVars 75 }
reg2B34 OBJECT-TYPE
SYNTAX INTEGER
ACCESS read-only
STATUS mandatory
DESCRIPTION "Register 2B34"
::= { bcmsVars 76 }
reg2A35 OBJECT-TYPE
SYNTAX INTEGER
ACCESS read-only
STATUS mandatory
DESCRIPTION "Register 2A35"
::= { bcmsVars 77 }
reg2B36 OBJECT-TYPE
SYNTAX INTEGER
ACCESS read-only
STATUS mandatory
DESCRIPTION "Register 2B36"
::= { bcmsVars 78 }
reg2A37 OBJECT-TYPE
SYNTAX INTEGER
ACCESS read-only
STATUS mandatory
DESCRIPTION "Register 2A37"
::= { bcmsVars 79 }
reg2B38 OBJECT-TYPE
SYNTAX INTEGER
ACCESS read-only
STATUS mandatory
DESCRIPTION "Register 2B38"
::= { bcmsVars 80 }
reg2A39 OBJECT-TYPE
SYNTAX INTEGER
ACCESS read-only
STATUS mandatory
DESCRIPTION "Register 2A39"
::= { bcmsVars 81 }
reg2B40 OBJECT-TYPE
SYNTAX INTEGER
ACCESS read-only
STATUS mandatory
DESCRIPTION "Register 2B40"
::= { bcmsVars 82 }
reg2A41 OBJECT-TYPE
SYNTAX INTEGER
ACCESS read-only
STATUS mandatory
DESCRIPTION "Register 2A41"
::= { bcmsVars 83 }
reg2A42 OBJECT-TYPE
SYNTAX INTEGER
ACCESS read-only
STATUS mandatory
DESCRIPTION "Register 2A42"
::= { bcmsVars 84 }
--------------------------------------------------------------------------------
-- BCMS traps
--------------------------------------------------------------------------------
ioFail TRAP-TYPE
ENTERPRISE bcmsTraps
VARIABLES { ioFailCount }
DESCRIPTION "I/O failure count exceeds threshold"
::= 1
END
