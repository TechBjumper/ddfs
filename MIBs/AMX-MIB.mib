--
-- AMX-MIB.my
-- MIB generated by MG-SOFT Visual MIB Builder Version 5.0  Build 250
-- Tuesday, June 07, 2005 at 11:34:57
--

-- ------------------------------------------------------------------------------
-- Avocent AMX MIB
-- 
-- Copyright 2001 - 2005 Avocent Corporation
-- 
-- Revision: 0.19
-- 
-- Last Modified: June 7, 2005
-- 
-- ------------------------------------------------------------------------------

	AMX-MIB DEFINITIONS ::= BEGIN
 
		IMPORTS
			OBJECT-TYPE			
				FROM RFC-1212			
			enterprises, IpAddress, Counter			
				FROM RFC1155-SMI			
			DisplayString			
				FROM RFC1213-MIB;
	
	
--
-- Type definitions
--
	
-- A UTF8String represents a series of UTF-8 encoded characters. UTF-8 encoding
-- provides the ability to encode all characters defined in the Universal
-- Multiple-Octet Coded Character Set (UCS) and all characters defined in the
-- Unicode Standard. UCS is defined in international standard ISO 10646. Unicode
-- encompasses a subset of UCS. See http://www.unicode.org for more information
-- on Unicode. See RFC2279 for more information on UTF-8 encoding.
-- 
-- UTF8String should be assigned to the SYNTAX clause of objects that may
-- contain strings in other languages besides English. UTF-8 encoding
-- provides compatibility with 7-bit ASCII because the Unicode characters
-- U+0000 through U+007F (same as ASCII 0x00 through 0x7F) are encoded in
-- UTF-8 as bytes 0x00 through 0x7F. This means a 7-bit ASCII string encoded
-- in UTF-8 results in an octet string of the same length, and with the
-- same values as the original string.
-- 
-- Note that when SIZE is assigned to an object that has a SYNTAX of
-- UTF8String, the SIZE represents the number of characters and not the
-- number of octets. The number of octets needed to UTF-8 encode a character
-- depends upon the language. In UTF-8 encoding, a maximum of 6 octets
-- may be used to encode a single character.  For example, if an object
-- had a SIZE declaration of ( SIZE (0..32) ), and if every character
-- in the object requires 6 octets for UTF-8 encoding, then the maximum
-- number of octets the object could return would be 32 x 6 = 192. If the
-- language is English then SIZE would represent the actual number of octets.
		UTF8String ::= OCTET STRING

--  AccessEnum identifies the possible access rights of an AMIQ device
		RightsAccessEnum ::= INTEGER
			{
			rightaccessNONE(1),
			rightaccessVIEW(2),
			rightaccessNORMAL(3),
			rightaccessPOWER(4),
			rightaccessPREEMPTIVE(5)
			}

--  PortNum identifies a port number on the device
		PortEnum ::= INTEGER
			{
			portNumUserSide1(1),
			portNumUserSide2(2),
			portNumUserSide3(3),
			portNumUserSide4(4),
			portNumUserSide5(5),
			portNumUserSide6(6),
			portNumUserSide7(7),
			portNumUserSide8(8),
			portNumUserSide9(9),
			portNumUserSide10(10),
			portNumUserSide11(11),
			portNumUserSide12(12),
			portNumUserSide13(13),
			portNumUserSide14(14),
			portNumUserSide15(15),
			portNumUserSide16(16),
			portNumAmiqSide1(129),
			portNumAmiqSide2(130),
			portNumAmiqSide3(131),
			portNumAmiqSide4(132),
			portNumAmiqSide5(133),
			portNumAmiqSide6(134),
			portNumAmiqSide7(135),
			portNumAmiqSide8(136),
			portNumAmiqSide9(137),
			portNumAmiqSide10(138),
			portNumAmiqSide11(139),
			portNumAmiqSide12(140),
			portNumAmiqSide13(141),
			portNumAmiqSide14(142),
			portNumAmiqSide15(143),
			portNumAmiqSide16(144),
			portNumAmiqSide17(145),
			portNumAmiqSide18(146),
			portNumAmiqSide19(147),
			portNumAmiqSide20(148),
			portNumAmiqSide21(149),
			portNumAmiqSide22(150),
			portNumAmiqSide23(151),
			portNumAmiqSide24(152),
			portNumAmiqSide25(153),
			portNumAmiqSide26(154),
			portNumAmiqSide27(155),
			portNumAmiqSide28(156),
			portNumAmiqSide29(157),
			portNumAmiqSide30(158),
			portNumAmiqSide31(159),
			portNumAmiqSide32(160),
			portNumAmiqSide33(161),
			portNumAmiqSide34(162),
			portNumAmiqSide35(163),
			portNumAmiqSide36(164),
			portNumAmiqSide37(165),
			portNumAmiqSide38(166),
			portNumAmiqSide39(167),
			portNumAmiqSide40(168),
			portNumAmiqSide41(169),
			portNumAmiqSide42(170),
			portNumAmiqSide43(171),
			portNumAmiqSide44(172),
			portNumAmiqSide45(173),
			portNumAmiqSide46(174),
			portNumAmiqSide47(175),
			portNumAmiqSide48(176),
			portNumAmiqSide49(177),
			portNumAmiqSide50(178),
			portNumAmiqSide51(179),
			portNumAmiqSide52(180),
			portNumAmiqSide53(181),
			portNumAmiqSide54(182),
			portNumAmiqSide55(183),
			portNumAmiqSide56(184),
			portNumAmiqSide57(185),
			portNumAmiqSide58(186),
			portNumAmiqSide59(187),
			portNumAmiqSide60(188),
			portNumAmiqSidet61(189),
			portNumAmiqSide62(190),
			portNumAmiqSide63(191),
			portNumAmiqSide64(192),
			portNumNULL(255)
			}

--  NspEnum identifies the possible connection modes of a UserStation
		NspmEnum ::= INTEGER
			{
			nspmNONE(1),
			nspmSHARED(2),
			nspmPRIVATE(3),
			nspmMAINTAIN(4)
			}

		ConnectActionStatusEnum ::= INTEGER
			{
			connectActionStatusNONE(1),
			connectActionStatusPENDING(2)
			}

-- ------------------------------------------------------------------------------
--  Type Definitions
-- ------------------------------------------------------------------------------
--  TrapTypeEnum is used to enumerate the types of traps the appliance can
--  generate. The table includes the private enterprise traps. The enumeration is used as an index
--  into tables that contain trap information.
		TrapTypeEnum ::= INTEGER
			{
			rebootStarted(1),
			routeConnect(2),
			routeDisconnect(3),
			amiqConnected(4),
			amiqDisconnected(5),
			userStationConnected(6),
			userStationDisconnected(7),
			userStationLogin(8),
			userStationLogout(9)
			}

	
--
-- Node definitions
--
	
-- ------------------------------------------------------------------------------
-- Object Groupings
-- ------------------------------------------------------------------------------
-- Note: every product type should be uniquely identified underneath the
-- amxProducts object group. Each product should report its unique amxProducts
-- OBJECT IDENTIFIER in mib-2.system.sysObjectID. Please see the file
-- "_Avocent Enterprise Object Identifier Assignment.txt" for a list of the
-- IDs that have been assigned.
-- enterprises  .1.3.6.1.4.1
		-- 1.3.6.1.4.1.10418
		avocent OBJECT IDENTIFIER ::= { enterprises 10418 }

		
		-- 1.3.6.1.4.1.10418.10
		amx OBJECT IDENTIFIER ::= { avocent 10 }

		
		-- 1.3.6.1.4.1.10418.10.1
		amxProducts OBJECT IDENTIFIER ::= { amx 1 }

		
		-- 1.3.6.1.4.1.10418.10.2
		amxManagement OBJECT IDENTIFIER ::= { amx 2 }

		
		-- 1.3.6.1.4.1.10418.10.2.1
		amxAppliance OBJECT IDENTIFIER ::= { amxManagement 1 }

		
-- ------------------------------------------------------------------------------
-- Appliance Group (amxServer)                               10418.10.2.1
-- ------------------------------------------------------------------------------
		-- 1.3.6.1.4.1.10418.10.2.1.1
		amxMibMajorVersion OBJECT-TYPE
			SYNTAX INTEGER (0..65535)
			ACCESS read-only
			STATUS mandatory
			DESCRIPTION
				"The Major Revision level of the MIB.
				
				A change in the major revision of the MIB indicates that the
				architecture of the MIB has changed significantly.  At the time of
				product release, the values reported by the appliance for the major
				and minor MIB version objects shall match the version number
				specified at the top of the final released MIB file.
				
				Supported by the following appliance types:
				   amx5000
				   amx5010
				   amx5020
				   amx5030"
			::= { amxAppliance 1 }

		
		-- 1.3.6.1.4.1.10418.10.2.1.2
		amxMibMinorVersion OBJECT-TYPE
			SYNTAX INTEGER (0..65535)
			ACCESS read-only
			STATUS mandatory
			DESCRIPTION
				"The Minor Revision level of the MIB.
				
				A change in the minor revision of the MIB indicates some additional
				support was added. No changes were made to pre-existing information.
				At the time of product release, the values reported by the appliance
				for the major and minor MIB version objects shall match the version
				number specified at the top of the final released MIB file.
				
				Supported by the following appliance types:
				   amx5000
				   amx5010
				   amx5020
				   amx5030"
			::= { amxAppliance 2 }

		
		-- 1.3.6.1.4.1.10418.10.2.1.3
		amxHardwareBoard1RevNumber OBJECT-TYPE
			SYNTAX OCTET STRING (SIZE (0..16))
			ACCESS read-only
			STATUS mandatory
			DESCRIPTION
				"The revision number of Hardware board 1 as printed on the board.
				
				Supported by the following appliance types:
				   amx5000
				   amx5010
				   amx5020
				   amx5030"
			::= { amxAppliance 3 }

		
		-- 1.3.6.1.4.1.10418.10.2.1.4
		amxHardwareBoard2RevNumber OBJECT-TYPE
			SYNTAX OCTET STRING (SIZE (0..16))
			ACCESS read-only
			STATUS mandatory
			DESCRIPTION
				"The revision number of Hardware board 2 as printed on the board.
				Only the amx5010 has a second hardware board. 
				       For the amx5000 and amx5020 this will be 0
				
				      Supported by the following appliance types:
				         amx5010
				      "
			::= { amxAppliance 4 }

		
		-- 1.3.6.1.4.1.10418.10.2.1.5
		amxApplicationRevNumber OBJECT-TYPE
			SYNTAX OCTET STRING (SIZE (0..16))
			ACCESS read-only
			STATUS mandatory
			DESCRIPTION
				"The revision number of the Application Software.
				
				Supported by the following appliance types:
				   amx5000
				   amx5010
				   amx5020
				   amx5030"
			::= { amxAppliance 5 }

		
		-- 1.3.6.1.4.1.10418.10.2.1.6
		amxBootRevNumber OBJECT-TYPE
			SYNTAX OCTET STRING (SIZE (0..16))
			ACCESS read-only
			STATUS mandatory
			DESCRIPTION
				"The revision number of the Boot Software.
				
				Supported by the following appliance types:
				   amx5000
				   amx5010
				   amx5020
				   amx5030"
			::= { amxAppliance 6 }

		
		-- 1.3.6.1.4.1.10418.10.2.1.7
		amxFpga1RevNumber OBJECT-TYPE
			SYNTAX OCTET STRING (SIZE (0..16))
			ACCESS read-only
			STATUS mandatory
			DESCRIPTION
				"The revision number of the FPGA Sync Multiplexer.
				
				Supported by the following appliance types:
				   amx5000
				   amx5010
				   amx5020
				   amx5030"
			::= { amxAppliance 7 }

		
		-- 1.3.6.1.4.1.10418.10.2.1.8
		amxFpga2RevNumber OBJECT-TYPE
			SYNTAX OCTET STRING (SIZE (0..16))
			ACCESS read-only
			STATUS mandatory
			DESCRIPTION
				"The revision number of the FPGA Data Multiplexer.
				Only the amx5000 and amx5010 has a fpga data mux. 
				       For the amx5020 this will be 0
				Supported by the following appliance types:
				   amx5000
				   amx5010"
			::= { amxAppliance 8 }

		
		-- 1.3.6.1.4.1.10418.10.2.1.9
		amxFpga3RevNumber OBJECT-TYPE
			SYNTAX OCTET STRING (SIZE (0..16))
			ACCESS read-only
			STATUS mandatory
			DESCRIPTION
				"The revision number of the FPGA Data Link.
				
				Supported by the following appliance types:
				   amx5000
				   amx5010
				   amx5020
				   amx5030"
			::= { amxAppliance 9 }

		
		-- 1.3.6.1.4.1.10418.10.2.1.10
		amxUidNumber OBJECT-TYPE
			SYNTAX OCTET STRING (SIZE (0..16))
			ACCESS read-only
			STATUS mandatory
			DESCRIPTION
				"The Unique Identifier number (UID) of this appliance.
				
				Supported by the following appliance types:
				   amx5000
				   amx5010
				   amx5020
				   amx5030"
			::= { amxAppliance 10 }

		
		-- 1.3.6.1.4.1.10418.10.2.1.11
		amxConfigId OBJECT-TYPE
			SYNTAX INTEGER (0..65535)
			ACCESS read-only
			STATUS mandatory
			DESCRIPTION
				"The configuration ID is a six digit number that is 
				used to determine which networkable system components that
				should be considered to be a part of any given 
				configuration of AMX system. It can be set as a decimal 
				number but is displayed here as it's hexidecimal equivalent.
				
				Supported by the following appliance types:
				   amx5000
				   amx5010
				   amx5020
				   amx5030"
			::= { amxAppliance 11 }

		
		-- 1.3.6.1.4.1.10418.10.2.1.12
		amxReboot OBJECT-TYPE
			SYNTAX INTEGER
				{
				noAction(1),
				reboot(2)
				}
			ACCESS read-write
			STATUS mandatory
			DESCRIPTION
				"A set value of reboot(2) will reboot the appliance.
				
				noAction(1) = always returned in a GET. Does nothing if SET.
				
				reboot(2)   = when SET the appliance immediately reboots.
				
				Supported by the following appliance types:
				   amx5000
				   amx5010
				   amx5020
				   amx5030"
			::= { amxAppliance 12 }

		
		-- 1.3.6.1.4.1.10418.10.2.1.13
		amxName OBJECT-TYPE
			SYNTAX UTF8String (SIZE (0..15))
			ACCESS read-only
			STATUS mandatory
			DESCRIPTION
				"Specifies the name of this AMX device.
				
				Supported by the following appliance types:
				   amx5000
				   amx5010
				   amx5020
				   amx5030"
			::= { amxAppliance 13 }

		
		-- 1.3.6.1.4.1.10418.10.2.2
		amxAmiq OBJECT IDENTIFIER ::= { amxManagement 2 }

		
-- ------------------------------------------------------------------------------
-- AMIQ Group (amxAmiq)                                   10418.10.2.2
-- ------------------------------------------------------------------------------
		-- 1.3.6.1.4.1.10418.10.2.2.1
		amxAmiqTable OBJECT-TYPE
			SYNTAX SEQUENCE OF AmxAmiqEntry
			ACCESS not-accessible
			STATUS mandatory
			DESCRIPTION
				"This table defines the AMIQ devices that are currently connected.
				
				It is indexed by the UID of the AMIQs.
				
				Supported by the following appliance types:
				   amx5000
				   amx5010
				   amx5020
				   amx5030"
			::= { amxAmiq 1 }

		
		-- 1.3.6.1.4.1.10418.10.2.2.1.1
		amxAmiqEntry OBJECT-TYPE
			SYNTAX AmxAmiqEntry
			ACCESS not-accessible
			STATUS mandatory
			DESCRIPTION
				"An entry in the amxAmiqTable.
				
				Supported by the following appliance types:
				   amx5000
				   amx5010
				   amx5020
				   amx5030"
			INDEX { amxAmiqUid }
			::= { amxAmiqTable 1 }

		
		AmxAmiqEntry ::=
			SEQUENCE { 
				amxAmiqUid
					OCTET STRING,
				amxAmiqName
					UTF8String,
				amxAmiqRights
					RightsAccessEnum,
				amxAmiqPortNum
					PortEnum
			 }

		-- 1.3.6.1.4.1.10418.10.2.2.1.1.1
		amxAmiqUid OBJECT-TYPE
			SYNTAX OCTET STRING (SIZE (0..16))
			ACCESS read-only
			STATUS mandatory
			DESCRIPTION
				"Specifies the UID of the AMIQ device. It also represents a unique 
				index into this table. There can be a maximum number of 1024 in 
				the table.
				
				Supported by the following appliance types:
				   amx5000
				   amx5010
				   amx5020
				   amx5030"
			::= { amxAmiqEntry 1 }

		
		-- 1.3.6.1.4.1.10418.10.2.2.1.1.2
		amxAmiqName OBJECT-TYPE
			SYNTAX UTF8String (SIZE (0..15))
			ACCESS read-only
			STATUS mandatory
			DESCRIPTION
				"Specifies the name of this AMIQ device.
				
				Supported by the following appliance types:
				   amx5000
				   amx5010
				   amx5020
				   amx5030"
			::= { amxAmiqEntry 2 }

		
		-- 1.3.6.1.4.1.10418.10.2.2.1.1.3
		amxAmiqRights OBJECT-TYPE
			SYNTAX RightsAccessEnum
			ACCESS read-only
			STATUS mandatory
			DESCRIPTION
				"Specifies the access rights of this AMIQ device.
				
				Supported by the following appliance types:
				   amx5000
				   amx5010
				   amx5020
				   amx5030"
			::= { amxAmiqEntry 3 }

		
		-- 1.3.6.1.4.1.10418.10.2.2.1.1.4
		amxAmiqPortNum OBJECT-TYPE
			SYNTAX PortEnum
			ACCESS read-only
			STATUS mandatory
			DESCRIPTION
				"Specifies the Port Number the Amiq is connected to.
				
				Supported by the following appliance types:
				   amx5000
				   amx5010
				   amx5020
				   amx5030"
			::= { amxAmiqEntry 4 }

		
		-- 1.3.6.1.4.1.10418.10.2.3
		amxUserStation OBJECT IDENTIFIER ::= { amxManagement 3 }

		
-- ------------------------------------------------------------------------------
-- UserStation Group (amxUserStaion)                            10418.10.2.3
-- ------------------------------------------------------------------------------
		-- 1.3.6.1.4.1.10418.10.2.3.1
		amxUserStationTable OBJECT-TYPE
			SYNTAX SEQUENCE OF AmxUserStationEntry
			ACCESS not-accessible
			STATUS mandatory
			DESCRIPTION
				"This table defines the UserStation devices that are currently connected.
				
				It is indexed by the UID of the UserStations.
				
				Supported by the following appliance types:
				   amx5000
				   amx5010
				   amx5020
				   amx5030"
			::= { amxUserStation 1 }

		
		-- 1.3.6.1.4.1.10418.10.2.3.1.1
		amxUserStationEntry OBJECT-TYPE
			SYNTAX AmxUserStationEntry
			ACCESS not-accessible
			STATUS mandatory
			DESCRIPTION
				"An entry in the amxUserStationTable.
				
				Supported by the following appliance types:
				   amx5000
				   amx5010
				   amx5020
				   amx5030"
			INDEX { amxUserStationUid }
			::= { amxUserStationTable 1 }

		
		AmxUserStationEntry ::=
			SEQUENCE { 
				amxUserStationUid
					OCTET STRING,
				amxUserStationName
					UTF8String,
				amxConnectedAmiq
					OCTET STRING,
				amxConnectionMode
					NspmEnum,
				amxLoggedInUser
					UTF8String,
				amxUserStationPortNum
					PortEnum,
				amxNextConnectedAmiq
					OCTET STRING,
				amxNextConnectionMode
					NspmEnum,
				amxConnectActionStatus
					ConnectActionStatusEnum
			 }

		-- 1.3.6.1.4.1.10418.10.2.3.1.1.1
		amxUserStationUid OBJECT-TYPE
			SYNTAX OCTET STRING (SIZE (0..16))
			ACCESS read-only
			STATUS mandatory
			DESCRIPTION
				"Specifies the UID of the UserStation device. It also represents a 
				unique index into this table. There can be a maximum number of 16
				in the table.
				
				Supported by the following appliance types:
				   amx5000
				   amx5010
				   amx5020
				   amx5030"
			::= { amxUserStationEntry 1 }

		
		-- 1.3.6.1.4.1.10418.10.2.3.1.1.2
		amxUserStationName OBJECT-TYPE
			SYNTAX UTF8String (SIZE (0..15))
			ACCESS read-only
			STATUS mandatory
			DESCRIPTION
				"Specifies the name of this UserStation device.
				
				Supported by the following appliance types:
				   amx5000
				   amx5010
				   amx5020
				   amx5030"
			::= { amxUserStationEntry 2 }

		
		-- 1.3.6.1.4.1.10418.10.2.3.1.1.3
		amxConnectedAmiq OBJECT-TYPE
			SYNTAX OCTET STRING (SIZE (0..16))
			ACCESS read-only
			STATUS mandatory
			DESCRIPTION
				"Specifies the UID of the AMIQ device the UserStation is connected to.
				
				Supported by the following appliance types:
				   amx5000
				   amx5010
				   amx5020
				   amx5030"
			::= { amxUserStationEntry 3 }

		
		-- 1.3.6.1.4.1.10418.10.2.3.1.1.4
		amxConnectionMode OBJECT-TYPE
			SYNTAX NspmEnum
			ACCESS read-only
			STATUS mandatory
			DESCRIPTION
				"Specifies the connection mode being used by this UserStation.
				
				Supported by the following appliance types:
				   amx5000
				   amx5010
				   amx5020
				   amx5030"
			::= { amxUserStationEntry 4 }

		
		-- 1.3.6.1.4.1.10418.10.2.3.1.1.5
		amxLoggedInUser OBJECT-TYPE
			SYNTAX UTF8String (SIZE (0..15))
			ACCESS read-only
			STATUS mandatory
			DESCRIPTION
				"Specifies the user currently logged in to this UserStation.
				
				Supported by the following appliance types:
				   amx5000
				   amx5010
				   amx5020
				   amx5030"
			::= { amxUserStationEntry 5 }

		
		-- 1.3.6.1.4.1.10418.10.2.3.1.1.6
		amxUserStationPortNum OBJECT-TYPE
			SYNTAX PortEnum
			ACCESS read-only
			STATUS mandatory
			DESCRIPTION
				"Specifies the Port Number the User Station is connected to.
				
				Supported by the following appliance types:
				   amx5000
				   amx5010
				   amx5020
				   amx5030"
			::= { amxUserStationEntry 6 }

		
		-- 1.3.6.1.4.1.10418.10.2.3.1.1.7
		amxNextConnectedAmiq OBJECT-TYPE
			SYNTAX OCTET STRING (SIZE (0..16))
			ACCESS read-write
			STATUS mandatory
			DESCRIPTION
				"Specifies the UID of the AMIQ device the UserStation will be 
				connected to when amxConnectActionStatus is set to 
				connectActionStatus-PENDING.
				
				Supported by the following appliance types:
				   amx5000
				   amx5010
				   amx5020
				   amx5030"
			::= { amxUserStationEntry 7 }

		
		-- 1.3.6.1.4.1.10418.10.2.3.1.1.8
		amxNextConnectionMode OBJECT-TYPE
			SYNTAX NspmEnum
			ACCESS read-write
			STATUS mandatory
			DESCRIPTION
				"Specifies the connection mode to be used by this UserStation when 
				amxConnectActionStatus is set to connectActionStatus-PENDING.
				
				Supported by the following appliance types:
				   amx5000
				   amx5010
				   amx5020
				   amx5030"
			::= { amxUserStationEntry 8 }

		
		-- 1.3.6.1.4.1.10418.10.2.3.1.1.9
		amxConnectActionStatus OBJECT-TYPE
			SYNTAX ConnectActionStatusEnum
			ACCESS read-write
			STATUS mandatory
			DESCRIPTION
				"Initiates a connect action using values in amxNextConnectedAmiq and 
				amxNextConnectionMode when set to connectActionStatus-PENDING.
				If the connect action is not allowed then SNMP_ERR_AUTHORIZATION_ERROR
				is returned. Please check the amxAmiqTable to see if the snmpUser has
				rights to connect to the amxNextConnectedAmiq.
				
				Supported by the following appliance types:
				   amx5000
				   amx5010
				   amx5020
				   amx5030"
			::= { amxUserStationEntry 9 }

		
		-- 1.3.6.1.4.1.10418.10.2.4
		amxStats OBJECT IDENTIFIER ::= { amxManagement 4 }

		
-- ------------------------------------------------------------------------------
-- Stats Group (amxStats)                                   10418.10.2.4
-- ------------------------------------------------------------------------------
		-- 1.3.6.1.4.1.10418.10.2.4.4
		amxStatsTable OBJECT-TYPE
			SYNTAX SEQUENCE OF AmxStatsEntry
			ACCESS not-accessible
			STATUS mandatory
			DESCRIPTION
				"This table defines the port statistics which can be retrieved from 
				the system.
				
				It is indexed by port number.
				
				Supported by the following appliance types:
				   amx5000
				   amx5010
				   amx5020
				   amx5030"
			::= { amxStats 4 }

		
		-- 1.3.6.1.4.1.10418.10.2.4.4.1
		amxStatsEntry OBJECT-TYPE
			SYNTAX AmxStatsEntry
			ACCESS not-accessible
			STATUS mandatory
			DESCRIPTION
				"An entry in the amxStatsTable.
				
				Supported by the following appliance types:
				   amx5000
				   amx5010
				   amx5020
				   amx5030"
			INDEX { amxPortNum }
			::= { amxStatsTable 1 }

		
		AmxStatsEntry ::=
			SEQUENCE { 
				amxPortNum
					PortEnum,
				amxSentPackets
					Counter,
				amxRetryAttempts
					Counter,
				amxFailedAttempts
					Counter,
				amxReceivedPackets
					Counter,
				amxRxPacketErrors
					Counter
			 }

		-- 1.3.6.1.4.1.10418.10.2.4.4.1.1
		amxPortNum OBJECT-TYPE
			SYNTAX PortEnum
			ACCESS read-only
			STATUS mandatory
			DESCRIPTION
				"Specifies the Port Number the stats are associated with. It also 
				represents a unique index into this table.
				
				Supported by the following appliance types:
				   amx5000
				   amx5010
				   amx5020
				   amx5030"
			::= { amxStatsEntry 1 }

		
		-- 1.3.6.1.4.1.10418.10.2.4.4.1.2
		amxSentPackets OBJECT-TYPE
			SYNTAX Counter
			ACCESS read-only
			STATUS mandatory
			DESCRIPTION
				"Specifies the number of packets sent on this port.
				
				Supported by the following appliance types:
				   amx5000
				   amx5010
				   amx5020
				   amx5030"
			::= { amxStatsEntry 2 }

		
		-- 1.3.6.1.4.1.10418.10.2.4.4.1.3
		amxRetryAttempts OBJECT-TYPE
			SYNTAX Counter
			ACCESS read-only
			STATUS mandatory
			DESCRIPTION
				"Specifies the number of Retry Attempts performed on this port.
				
				Supported by the following appliance types:
				   amx5000
				   amx5010
				   amx5020
				   amx5030"
			::= { amxStatsEntry 3 }

		
		-- 1.3.6.1.4.1.10418.10.2.4.4.1.4
		amxFailedAttempts OBJECT-TYPE
			SYNTAX Counter
			ACCESS read-only
			STATUS mandatory
			DESCRIPTION
				"Specifies the number of Failed Attempts on this port.
				
				Supported by the following appliance types:
				   amx5000
				   amx5010
				   amx5020
				   amx5030"
			::= { amxStatsEntry 4 }

		
		-- 1.3.6.1.4.1.10418.10.2.4.4.1.5
		amxReceivedPackets OBJECT-TYPE
			SYNTAX Counter
			ACCESS read-only
			STATUS mandatory
			DESCRIPTION
				"Specifies the number of packets received on this port.
				
				Supported by the following appliance types:
				   amx5000
				   amx5010
				   amx5020
				   amx5030"
			::= { amxStatsEntry 5 }

		
		-- 1.3.6.1.4.1.10418.10.2.4.4.1.6
		amxRxPacketErrors OBJECT-TYPE
			SYNTAX Counter
			ACCESS read-only
			STATUS mandatory
			DESCRIPTION
				"Specifies the number of errored packets received on this port.
				
				Supported by the following appliance types:
				   amx5000
				   amx5010
				   amx5020
				   amx5030"
			::= { amxStatsEntry 6 }

		
		-- 1.3.6.1.4.1.10418.10.2.5
		amxSnmp OBJECT IDENTIFIER ::= { amxManagement 5 }

		
-- ------------------------------------------------------------------------------
-- SNMP Group (amxSnmp)                                   10418.10.2.5
-- ------------------------------------------------------------------------------
		-- 1.3.6.1.4.1.10418.10.2.5.1
		amxWriteCommunity OBJECT-TYPE
			SYNTAX DisplayString
			ACCESS read-only
			STATUS mandatory
			DESCRIPTION
				"Specifies the community string that must be used in SNMP writes
				(SET commands). This object only applies to standard SNMP over
				UDP port 161.
				
				Supported by the following appliance types:
				   amx5000
				   amx5010
				   amx5020
				   amx5030"
			::= { amxSnmp 1 }

		
		-- 1.3.6.1.4.1.10418.10.2.5.2
		amxReadCommunity OBJECT-TYPE
			SYNTAX DisplayString
			ACCESS read-only
			STATUS mandatory
			DESCRIPTION
				"Specifies the community string that must be used in SNMP reads
				(GET commands). This object only applies to standard SNMP over
				UDP port 161.
				
				Supported by the following appliance types:
				   amx5000
				   amx5010
				   amx5020
				   amx5030"
			::= { amxSnmp 2 }

		
		-- 1.3.6.1.4.1.10418.10.2.5.3
		amxTrapCommunity OBJECT-TYPE
			SYNTAX DisplayString
			ACCESS read-only
			STATUS mandatory
			DESCRIPTION
				"Specifies the community string that this appliance will send in
				SNMP traps.
				
				Supported by the following appliance types:
				   amx5000
				   amx5010
				   amx5020
				   amx5030"
			::= { amxSnmp 3 }

		
--  Trap Host Table 
		-- 1.3.6.1.4.1.10418.10.2.5.4
		amxTrapHostTable OBJECT-TYPE
			SYNTAX SEQUENCE OF AmxTrapHostEntry
			ACCESS not-accessible
			STATUS mandatory
			DESCRIPTION
				"This table defines the trap hosts this appliance should send
				its traps to. If there are not any hosts defined in this table, then
				this appliance will not send any traps.
				
				Supported by the following appliance types:
				   amx5000
				   amx5010
				   amx5020
				   amx5030"
			::= { amxSnmp 4 }

		
		-- 1.3.6.1.4.1.10418.10.2.5.4.1
		amxTrapHostEntry OBJECT-TYPE
			SYNTAX AmxTrapHostEntry
			ACCESS not-accessible
			STATUS mandatory
			DESCRIPTION
				"An entry in the amxTrapHostTable.
				
				Supported by the following appliance types:
				   amx5000
				   amx5010
				   amx5020
				   amx5030"
			INDEX { amxTrapHostTableIndex }
			::= { amxTrapHostTable 1 }

		
		AmxTrapHostEntry ::=
			SEQUENCE { 
				amxTrapHostTableIndex
					INTEGER,
				amxTrapHostTableIPAddress
					IpAddress
			 }

		-- 1.3.6.1.4.1.10418.10.2.5.4.1.1
		amxTrapHostTableIndex OBJECT-TYPE
			SYNTAX INTEGER (1..4)
			ACCESS read-only
			STATUS mandatory
			DESCRIPTION
				"The index into this table. The table will always contain 4 rows.
				Unused rows will have a value of 0.0.0.0 for the trap host address.
				
				Supported by the following appliance types:
				   amx5000
				   amx5010
				   amx5020
				   amx5030"
			::= { amxTrapHostEntry 1 }

		
		-- 1.3.6.1.4.1.10418.10.2.5.4.1.2
		amxTrapHostTableIPAddress OBJECT-TYPE
			SYNTAX IpAddress
			ACCESS read-write
			STATUS mandatory
			DESCRIPTION
				"The IP address of a trap host this appliance should send its
				traps to. To remove this trap host set the value of this object
				to 0.0.0.0.
				
				Supported by the following appliance types:
				   amx5000
				   amx5010
				   amx5020
				   amx5030"
			::= { amxTrapHostEntry 2 }

		
--  Trap Configuration Table
-- 
		-- 1.3.6.1.4.1.10418.10.2.5.5
		amxTrapCfgTable OBJECT-TYPE
			SYNTAX SEQUENCE OF AmxTrapCfgEntry
			ACCESS not-accessible
			STATUS mandatory
			DESCRIPTION
				"This table defines which traps are enabled in the appliance.
				
				Supported by the following appliance types:
				   amx5000
				   amx5010
				   amx5020
				   amx5030"
			::= { amxSnmp 5 }

		
		-- 1.3.6.1.4.1.10418.10.2.5.5.1
		amxTrapCfgEntry OBJECT-TYPE
			SYNTAX AmxTrapCfgEntry
			ACCESS not-accessible
			STATUS mandatory
			DESCRIPTION
				"An entry in the amxTrapCfgTable.
				
				Supported by the following appliance types:
				   amx5000
				   amx5010
				   amx5020
				   amx5030"
			INDEX { amxTrapCfgTableIndex }
			::= { amxTrapCfgTable 1 }

		
		AmxTrapCfgEntry ::=
			SEQUENCE { 
				amxTrapCfgTableIndex
					TrapTypeEnum,
				amxTrapCfgTableControl
					INTEGER
			 }

		-- 1.3.6.1.4.1.10418.10.2.5.5.1.1
		amxTrapCfgTableIndex OBJECT-TYPE
			SYNTAX TrapTypeEnum
			ACCESS read-only
			STATUS mandatory
			DESCRIPTION
				"The index into this table. Each index represents a trap type that
				can be enabled or disabled.
				
				Supported by the following appliance types:
				   amx5000
				   amx5010
				   amx5020
				   amx5030"
			::= { amxTrapCfgEntry 1 }

		
		-- 1.3.6.1.4.1.10418.10.2.5.5.1.2
		amxTrapCfgTableControl OBJECT-TYPE
			SYNTAX INTEGER
				{
				disabled(1),
				enabled(2)
				}
			ACCESS read-write
			STATUS mandatory
			DESCRIPTION
				"Specifies whether this trap is enabled or disabled.
				
				disabled(0) = This trap will not be sent.
				
				enabled(1) = This trap will be sent to
				             each trap host defined in
				             amxTrapHostTable.
				
				Supported by the following appliance types:
				   amx5000
				   amx5010
				   amx5020
				   amx5030"
			::= { amxTrapCfgEntry 2 }

		
-- Note that all traps are defined in each appliance's separate trap MIB
-- 
		-- 1.3.6.1.4.1.10418.10.2.6
		amxTrapObject OBJECT IDENTIFIER ::= { amxManagement 6 }

		
	
	END

--
-- AMX-MIB.my
--
