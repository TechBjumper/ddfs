--			CEC Enterprise MIB
--			    Version 5.10.2
--
--			Chuo Electronics Co., Ltd.
--			1-9-9, MOTOHONGO-CHO,
--			HACHIOUJI-SHI, TOKYO 192-8532
--			JAPAN
--			+81-42-623-1211
--			info@cec.co.jp
--
--		Copyright (c) 1997-2009 Chuo Electronics Co., Ltd.
--		All rights reserved.
--

CEC-MIB DEFINITIONS ::= BEGIN

    IMPORTS
	enterprises
	    FROM RFC1155-SMI
	OBJECT-TYPE
	    FROM RFC-1212
	TRAP-TYPE
	    FROM RFC-1215;

	-- Textual conventions
	Time ::=
	INTEGER (0 .. 3155759999)
	-- The date and time expressed as the number of seconds
	-- since midnight January 1, 1970 GMT

--
-- The Chuo Electronics enterprise OID.
--

    cec		OBJECT IDENTIFIER ::= {	 enterprises 2589 }


--
-- Groups in the Chuo Electronics mib
--

    products		OBJECT IDENTIFIER ::= { cec 1 }

-- CEC products.
--
-- Each CEC product family is Assigned an Object Identifier.
-- This is the identifier stored in the MIB-II system group
-- item sysObjectID to identify the product to a network manager.
-- If product family specific items need to be defined they should
-- be defined in the appropriate product family subtree

    spacetime		OBJECT IDENTIFIER ::= { products 1 }
    network-device	OBJECT IDENTIFIER ::= { products 2 }
    access-control	OBJECT IDENTIFIER ::= { products 3 }
    lanscope		OBJECT IDENTIFIER ::= { products 4 }
    image-system	OBJECT IDENTIFIER ::= { products 5 }


-- CEC network-device product family.
--
-- There are several products in the network-device family.  This is
-- the identifier that enumerates the individual products.

    ndType		OBJECT IDENTIFIER ::= { network-device 1 }
    ndMgmt		OBJECT IDENTIFIER ::= { network-device 2 }

-- CEC network-device product type

    nd01		OBJECT IDENTIFIER ::= { ndType 1 }
    nd02		OBJECT IDENTIFIER ::= { ndType 2 }
    nd-ew01		OBJECT IDENTIFIER ::= { ndType 3 }
    nd-pc01		OBJECT IDENTIFIER ::= { ndType 4 }
    nd-ts01		OBJECT IDENTIFIER ::= { ndType 5 }
    nd-ew02		OBJECT IDENTIFIER ::= { ndType 6 }
    nd-ts02		OBJECT IDENTIFIER ::= { ndType 7 }
    nd-ew03		OBJECT IDENTIFIER ::= { ndType 8 }
    nd-io01		OBJECT IDENTIFIER ::= { ndType 9 }
    nd-vw02		OBJECT IDENTIFIER ::= { ndType 10 }
    nd-vw03		OBJECT IDENTIFIER ::= { ndType 11 }
    nd-io01s		OBJECT IDENTIFIER ::= { ndType 12 }
    nd-vw04		OBJECT IDENTIFIER ::= { ndType 13 }
    nd-io01n		OBJECT IDENTIFIER ::= { ndType 14 }
    nmg2-opc01		OBJECT IDENTIFIER ::= { ndType 15 }
    nmg2-sys01		OBJECT IDENTIFIER ::= { ndType 16 }
    nd-io02		OBJECT IDENTIFIER ::= { ndType 17 }
    nd-vw03r		OBJECT IDENTIFIER ::= { ndType 18 }
    nd-vw01m		OBJECT IDENTIFIER ::= { ndType 20 }
    nd-vw05		OBJECT IDENTIFIER ::= { ndType 21 }
    nd-lm01		OBJECT IDENTIFIER ::= { ndType 22 }
    nd-ew04		OBJECT IDENTIFIER ::= { ndType 23 }
    nd-vd01		OBJECT IDENTIFIER ::= { ndType 24 }
    nd-vw14		OBJECT IDENTIFIER ::= { ndType 26 }
    nd-vw15		OBJECT IDENTIFIER ::= { ndType 27 }
    nd-vw14-type1	OBJECT IDENTIFIER ::= { ndType 28 }
    nd-vw15-type1	OBJECT IDENTIFIER ::= { ndType 29 }
    nd-vw15-type2	OBJECT IDENTIFIER ::= { ndType 30 }
    nd-vw15-type3	OBJECT IDENTIFIER ::= { ndType 31 }
    nd-ew05		OBJECT IDENTIFIER ::= { ndType 32 }
    nd-st01		OBJECT IDENTIFIER ::= { ndType 34 }
    nd-lm02		OBJECT IDENTIFIER ::= { ndType 35 }
    nd-vw22		OBJECT IDENTIFIER ::= { ndType 36 }
    nd-vw24		OBJECT IDENTIFIER ::= { ndType 37 }
    nd-vw21m		OBJECT IDENTIFIER ::= { ndType 38 }
    nd-vw14n		OBJECT IDENTIFIER ::= { ndType 39 }
    nd-st02di		OBJECT IDENTIFIER ::= { ndType 40 }
    nd-sw01		OBJECT IDENTIFIER ::= { ndType 41 }
    nd-sw02di		OBJECT IDENTIFIER ::= { ndType 42 }
    nd-ac64		OBJECT IDENTIFIER ::= { ndType 43 }

-- CEC network-device management group
--

-- The Administrative Group

    ndAdmin	OBJECT IDENTIFIER ::= { ndMgmt 1 }

    adminDateAndTime OBJECT-TYPE
	SYNTAX		Time
	ACCESS		read-write
	STATUS		mandatory
	DESCRIPTION	"The current date and time in use by this device."
	::={ ndAdmin 1 }

-- The ALARM LED Group

    adminAlarmLed	OBJECT IDENTIFIER ::= { ndAdmin 2 }

    alarmLedStatus	OBJECT-TYPE
	SYNTAX		INTEGER {
			    on(1),		-- ON
			    off(2)		-- OFF
			}
	ACCESS		read-write
	STATUS		optional
	DESCRIPTION	"This value indicates ALARM LED status.
			And, ALARM LED can be controlled by this value."
	::= { adminAlarmLed 1 }

    alarmLedAutoOnEnable OBJECT-TYPE
	SYNTAX		INTEGER {
			    enable(1),
			    disable(2)
			}
	ACCESS		read-write
	STATUS		optional
	DESCRIPTION	"Indicates whether the SNMP agent process is
			permitted to auto switch on the ALARM LED."
	::= { adminAlarmLed 2 }

    alarmLedAutoOnTriggerObjectID OBJECT-TYPE
	SYNTAX		OBJECT IDENTIFIER
	ACCESS		read-write
	STATUS		optional
	DESCRIPTION	"Watch ObjectID for ALARM LED on."
	::= { adminAlarmLed 3 }

    alarmLedAutoOnTriggerEventNo OBJECT-TYPE
	SYNTAX		INTEGER {
			    adExceedUpperThresholdIncrease(1),
			    adExceedUpperThresholdDecrease(2),
			    adExceedingUpperThreshold(3),
			    adExceedLowerThresholdIncrease(4),
			    adExceedLowerThresholdDecrease(5),
			    adExceedingLowerThreshold(6),
			    adNormalOld(7),
			    diChangeValue0(8),
			    diValue0(9),
			    diChangeValue1(10),
			    diValue1(11),
			    vcExceedUpperThresholdIncrease(13),
			    vcExceedUpperThresholdDecrease(14),
			    vcExceedingUpperThreshold(15),
			    vcExceedLowerThresholdIncrease(16),
			    vcExceedLowerThresholdDecrease(17),
			    vcExceedingLowerThreshold(18),
			    vcNormal(19),
			    adChangeToNormal(20),
			    adNormal(21),
			    adChangeToAbnormal(22),
			    adAbnormal(23),
			    motionDetect(79),
			    motionDetecting(80),
			    motionNotDetect(81),
			    motionNotDetecting(82),
			    diForwardError(101),
			    diForwardNormal(102),
			    diForwardReceiveTimeout(104),
			    diForwardReceiveTimeoutRecover(105),
			    diForwardSendReceiveError(106),
			    diForwardSendReceiveNormal(107),
			    subUnitNotConnected(108),
			    subUnitConnected(109),
			    multiMeterNotConnected(110),
			    multiMeterConnected(111),
			    conditionIsAlert(512),
			    conditionChangeToAlert(513),
			    conditionIsNormal(514),
			    conditionChangeToNormal(515),
			    network-deviceTraps(1024)
			}
	ACCESS		read-write
	STATUS		optional
	DESCRIPTION	"A trigger event for ALARM LED on."
	::= { adminAlarmLed 4 }


    alarmLedAutoOffEnable OBJECT-TYPE
	SYNTAX		INTEGER {
			    enable(1),
			    disable(2)
			}
	ACCESS		read-write
	STATUS		optional
	DESCRIPTION	"Indicates whether the SNMP agent process is
			permitted to auto switch off the ALARM LED."
	::= { adminAlarmLed 5 }

    alarmLedAutoOffTriggerObjectID OBJECT-TYPE
	SYNTAX		OBJECT IDENTIFIER
	ACCESS		read-write
	STATUS		optional
	DESCRIPTION	"Watch ObjectID for ALARM LED off."
	::= { adminAlarmLed 6 }

    alarmLedAutoOffTriggerEventNo OBJECT-TYPE
	SYNTAX		INTEGER {
			    adExceedUpperThresholdIncrease(1),
			    adExceedUpperThresholdDecrease(2),
			    adExceedingUpperThreshold(3),
			    adExceedLowerThresholdIncrease(4),
			    adExceedLowerThresholdDecrease(5),
			    adExceedingLowerThreshold(6),
			    adNormalOld(7),
			    diChangeValue0(8),
			    diValue0(9),
			    diChangeValue1(10),
			    diValue1(11),
			    vcExceedUpperThresholdIncrease(13),
			    vcExceedUpperThresholdDecrease(14),
			    vcExceedingUpperThreshold(15),
			    vcExceedLowerThresholdIncrease(16),
			    vcExceedLowerThresholdDecrease(17),
			    vcExceedingLowerThreshold(18),
			    vcNormal(19),
			    adChangeToNormal(20),
			    adNormal(21),
			    adChangeToAbnormal(22),
			    adAbnormal(23),
			    motionDetect(79),
			    motionDetecting(80),
			    motionNotDetect(81),
			    motionNotDetecting(82),
			    diForwardError(101),
			    diForwardNormal(102),
			    diForwardReceiveTimeout(104),
			    diForwardReceiveTimeoutRecover(105),
			    diForwardSendReceiveError(106),
			    diForwardSendReceiveNormal(107),
			    subUnitNotConnected(108),
			    subUnitConnected(109),
			    multiMeterNotConnected(110),
			    multiMeterConnected(111),
			    conditionIsAlert(512),
			    conditionChangeToAlert(513),
			    conditionIsNormal(514),
			    conditionChangeToNormal(515),
			    network-deviceTraps(1024)
			}
	ACCESS		read-write
	STATUS		optional
	DESCRIPTION	"A trigger event for ALARM LED off."
	::= { adminAlarmLed 7 }

-- The Network Device Traps Group

    adminNDTraps	OBJECT IDENTIFIER ::= { ndAdmin 3 }

    adminNDTrapSeqNo	OBJECT-TYPE
	SYNTAX		INTEGER
	ACCESS		read-only
	STATUS		optional
	DESCRIPTION	"This value is generated latest trap sequence number."
	::= { adminNDTraps 1 }

    adminNDTrapAck	OBJECT-TYPE
	SYNTAX		INTEGER
	ACCESS		read-write
	STATUS		optional
	DESCRIPTION	"This object is for the acknowledgment of trap.
			If a manager receive trap which set 'retry',
			it should set sequence number which attached on that
			trap to this object. Then, the SNMP agent will stop
			resending the trap which corresponded to that
			sequence number to this manager."
	::= { adminNDTraps 2 }

    ndTrapHostNumber OBJECT-TYPE
	SYNTAX		INTEGER
	ACCESS		read-only
	STATUS		optional
	DESCRIPTION	"The number of hosts which this device can send trap."
	::= { adminNDTraps 3 }

    ndTrapHostTable	OBJECT-TYPE
	SYNTAX		SEQUENCE OF NdTrapHostEntry
	ACCESS		not-accessible
	STATUS		optional
	DESCRIPTION	"A list of the destinations to which traps are sent."
	::= { adminNDTraps 4 }

    ndUserDefinedTrapControl OBJECT-TYPE
	SYNTAX		INTEGER {
			    enable(1),
			    disable(2),
			    retry(3)
			}
	ACCESS		read-write
	STATUS		mandatory
	DESCRIPTION	"Indicates whether the SNMP agent process is
			permitted to generate ndUserDefinedTrap traps."
	::= { adminNDTraps 5 }

    adminNDTrapEnable	OBJECT-TYPE
	SYNTAX		INTEGER {
			    enable(1),
			    disable(2)
			}
	ACCESS		read-write
	STATUS		optional
	DESCRIPTION	"Indicates whether the SNMP send is permitted."
	::= { adminNDTraps 6 }


    ndTrapHostEntry	OBJECT-TYPE
	SYNTAX		NdTrapHostEntry
	ACCESS		not-accessible
	STATUS		optional
	DESCRIPTION	"An entry for a station address to which traps are
			sent."
	INDEX		{ ndTrapHostIndex }
	::= { ndTrapHostTable 1 }

    NdTrapHostEntry ::=
	SEQUENCE {
	    ndTrapHostIndex
		INTEGER,
	    ndTrapHostAddress
		IpAddress,
	    ndTrapHostPort
		INTEGER,
	    ndTrapHostRetryCount
		INTEGER,
	    ndTrapHostRetryInterval
		INTEGER,
	    ndTrapHostCommunity
		DisplayString,
	    ndTrapHostAddressString
		DisplayString
	}

    ndTrapHostIndex	OBJECT-TYPE
	SYNTAX		INTEGER
	ACCESS		read-only
	STATUS		optional
	DESCRIPTION	"A unique value for each ndTrapHost entry.
			It's value ranges between 1 and the value
			ndTrapHostNumber."
	::= { ndTrapHostEntry 1 }

    ndTrapHostAddress	OBJECT-TYPE
	SYNTAX		IpAddress
	ACCESS		read-write
	STATUS		optional
	DESCRIPTION	"The IP address of a station to which traps are sent."
	::= { ndTrapHostEntry 2 }

    ndTrapHostPort	OBJECT-TYPE
	SYNTAX		INTEGER (1..65535)
	ACCESS		read-write
	STATUS		optional
	DESCRIPTION	"The port of a station to which traps are sent."
	::= { ndTrapHostEntry 3 }

    ndTrapHostRetryCount OBJECT-TYPE
	SYNTAX		INTEGER
	ACCESS		read-write
	STATUS		optional
	DESCRIPTION	"The number of times that this device will resend 
			traps which set 'retry'."
	::= { ndTrapHostEntry 4 }

    ndTrapHostRetryInterval OBJECT-TYPE
	SYNTAX		INTEGER
	ACCESS		read-write
	STATUS		optional
	DESCRIPTION	"The interval that this device will resend 
			traps which set 'retry'."
	::= { ndTrapHostEntry 5 }

    ndTrapHostCommunity	OBJECT-TYPE
	SYNTAX		DisplayString (SIZE (1..64))
	ACCESS		read-write
	STATUS		optional
	DESCRIPTION	"The community name to use when sending traps to this
			address."
	::= { ndTrapHostEntry 6 }

    ndTrapHostAddressString	OBJECT-TYPE
	SYNTAX		DisplayString (SIZE (0..63))
	ACCESS		read-write
	STATUS		optional
	DESCRIPTION	"The host of a station to which traps are sent."
	::= { ndTrapHostEntry 7 }

    adminPassword	OBJECT-TYPE
	SYNTAX		DisplayString (SIZE (1..64))
	ACCESS		read-write
	STATUS		optional
	DESCRIPTION	"The password used to gain access to the configuration.
			When read this will always return a NULL string."

	::={ ndAdmin 4 }

    adminSave		OBJECT-TYPE
	SYNTAX		INTEGER
	ACCESS		read-write
	STATUS		optional
	DESCRIPTION	"Setting to any value will save current configuration
			to non-volatile memory. When read this will always
			return 0."
	::={ ndAdmin 5 }

    adminReboot		OBJECT-TYPE
	SYNTAX		INTEGER
	ACCESS		read-write
	STATUS		optional
	DESCRIPTION	"Setting to any value will reboot the device.
			If the device succeed reboot, the ack of snmp set
			is not send the manager.
			When read this will always return 0."
	::={ ndAdmin 6 }


-- The Network Device Admin Network Group

    adminNetwork	OBJECT IDENTIFIER ::= { ndAdmin 7 }

    netIPaddress	OBJECT-TYPE
	SYNTAX		IpAddress
	ACCESS		read-write
	STATUS		optional
	DESCRIPTION	"The IP address of this device."
	::= { adminNetwork 1 }

    netIPnetmask	OBJECT-TYPE
	SYNTAX		IpAddress
	ACCESS		read-write
	STATUS		optional
	DESCRIPTION	"The IP netmask address of this device."
	::= { adminNetwork 2 }

    netIPbroadcast	OBJECT-TYPE
	SYNTAX		IpAddress
	ACCESS		read-write
	STATUS		optional
	DESCRIPTION	"The IP broadcast address of this device."
	::= { adminNetwork 3 }

    netIPgateway	OBJECT-TYPE
	SYNTAX		IpAddress
	ACCESS		read-write
	STATUS		optional
	DESCRIPTION	"The default gateway IP address of this device."
	::= { adminNetwork 4 }

    netHostname		OBJECT-TYPE
	SYNTAX		DisplayString (SIZE (1..32))
	ACCESS		read-write
	STATUS		optional
	DESCRIPTION	"The hostname of this device."
	::= { adminNetwork 5 }

    netDomainname	OBJECT-TYPE
	SYNTAX		DisplayString (SIZE (1..256))
	ACCESS		read-write
	STATUS		optional
	DESCRIPTION	"The domainname of this device."
	::= { adminNetwork 6 }

    netIPv6AutoConf	OBJECT-TYPE
	SYNTAX          INTEGER {
			    autoconf(1),
			    noautoconf(2)
			}
	ACCESS          read-write
	STATUS          optional
	DESCRIPTION     "IPv6 auto configuration on this device."
	::= { adminNetwork 7 }

    netIPv6SitelocalAddress	OBJECT-TYPE
	SYNTAX		DisplayString (SIZE (0..63))
	ACCESS		read-write
	STATUS		optional
	DESCRIPTION	"IPv6 site-local address of this device."
	::= { adminNetwork 8 }

    netIPv6GlobalAddress	OBJECT-TYPE
	SYNTAX		DisplayString (SIZE (0..63))
	ACCESS		read-write
	STATUS		optional
	DESCRIPTION	"IPv6 global address of this device."
	::= { adminNetwork 9 }

    netIPv6Gateway	OBJECT-TYPE
	SYNTAX		DisplayString (SIZE (0..63))
	ACCESS		read-write
	STATUS		optional
	DESCRIPTION	"IPv6 gateway address of this device."
	::= { adminNetwork 10 }

    netDNSServerNumber OBJECT-TYPE
	SYNTAX		INTEGER
	ACCESS		read-only
	STATUS		optional
	DESCRIPTION	"The number of server which this device set dns server."
	::= { adminNetwork 11 }

    netDNSServerTable  OBJECT-TYPE
	SYNTAX		SEQUENCE OF NetDNSServerEntry
	ACCESS		not-accessible
	STATUS		optional
	DESCRIPTION	"A list of DNS Server."
	::= { adminNetwork 12 }

    netDNSServerEntry	OBJECT-TYPE
	SYNTAX		NetDNSServerEntry
	ACCESS		not-accessible
	STATUS		optional
	DESCRIPTION	"An entry for a station address to which traps are
			sent."
	INDEX		{ netDNSServerIndex }
	::= { netDNSServerTable 1 }

    NetDNSServerEntry ::=
	SEQUENCE {
	    netDNSServerIndex
		INTEGER,
	    netDNSServerAddress
		DisplayString
	}

    netDNSServerIndex	OBJECT-TYPE
	SYNTAX		INTEGER
	ACCESS		read-only
	STATUS		optional
	DESCRIPTION	"A unique value for each netDNSServer entry.
			It's value ranges between 1 and the value
			netDNSServerNumber."
	::= { netDNSServerEntry 1 }

    netDNSServerAddress	OBJECT-TYPE
	SYNTAX		DisplayString (SIZE (0..63))
	ACCESS		read-write
	STATUS		optional
	DESCRIPTION	"The DNS Server of this device."
	::= { netDNSServerEntry 2 }

-- The Network Device Admin SNMP Group

    adminSNMP		OBJECT IDENTIFIER ::= { ndAdmin 8 }

    snmpROcommunity	OBJECT-TYPE
	SYNTAX		DisplayString (SIZE (1..64))
	ACCESS		read-write
	STATUS		optional
	DESCRIPTION	"The SNMP community name allowed to perform
			get-requests or get-next requests to this agent."
	::= { adminSNMP 1 }

    snmpRWcommunity	OBJECT-TYPE
	SYNTAX		DisplayString (SIZE (1..64))
	ACCESS		read-write
	STATUS		optional
	DESCRIPTION	"The SNMP community name allowed to perform
			set-requests or get-requests or get-next requests
			to this agent."
	::= { adminSNMP 2 }

    snmpGetNextSkip	OBJECT-TYPE
	SYNTAX		INTEGER {
			    enable(1),
			    disable(2)
			}
	ACCESS		read-write
	STATUS		optional
	DESCRIPTION	"Only no object is skipped
			when get-next requests sent to this agent."
	::= { adminSNMP 3 }


-- The Network Device AccessControl Group

    accessControlNumber OBJECT-TYPE
	SYNTAX		INTEGER
	ACCESS		read-only
	STATUS		optional
	DESCRIPTION	"The number of access control entries."
	::= { ndAdmin 9 }

    accessControlTempTable	OBJECT-TYPE
	SYNTAX		SEQUENCE OF AccessControlTempEntry
	ACCESS		not-accessible
	STATUS		optional
	DESCRIPTION	"A list of the temporary access control entries."
	::= { ndAdmin 10 }

    accessControlTempEntry	OBJECT-TYPE
	SYNTAX		AccessControlTempEntry
	ACCESS		not-accessible
	STATUS		optional
	DESCRIPTION	"An entry for the temporary access control."
	INDEX		{ accessControlTempIndex }
	::= { accessControlTempTable 1 }

    AccessControlTempEntry ::=
	SEQUENCE {
	    accessControlTempIndex
		INTEGER,
	    accessControlTempPermit
		INTEGER,
	    accessControlTempProtocol
		INTEGER,
	    accessControlTempIPaddress
		IpAddress,
	    accessControlTempMaskLength
		INTEGER
	}

    accessControlTempIndex	OBJECT-TYPE
	SYNTAX		INTEGER
	ACCESS		read-only
	STATUS		optional
	DESCRIPTION     "A unique value for each accessControlTemp entry.
			It's value ranges between 1 and the value
			accessControlNumber."
	::= { accessControlTempEntry 1 }

    accessControlTempPermit	OBJECT-TYPE
	SYNTAX		INTEGER {
			    allow(1),
			    deny(2),
			    unused(3)
			}
	ACCESS		read-write
	STATUS		optional
	DESCRIPTION	"The type of permission to specify with this entry."
	::= { accessControlTempEntry 2 }

    accessControlTempProtocol	OBJECT-TYPE
	SYNTAX		INTEGER {
			    any(1),
			    telnet(2),
			    http(3),
			    snmp(4),
			    ftp(5),
			    rsh(6)
			}
	ACCESS		read-write
	STATUS		optional
	DESCRIPTION	"This protocol is an object of the access control."
	::= { accessControlTempEntry 3 }

    accessControlTempIPaddress	OBJECT-TYPE
	SYNTAX		IpAddress
	ACCESS		read-write
	STATUS		optional
	DESCRIPTION	"This IP address is an object of the access control."
	::= { accessControlTempEntry 4 }

    accessControlTempMaskLength	OBJECT-TYPE
	SYNTAX		INTEGER
	ACCESS		read-write
	STATUS		optional
	DESCRIPTION	"This address mask length is an object of the access
			control."
	::= { accessControlTempEntry 5 }

    accessControlTable	OBJECT-TYPE
	SYNTAX		SEQUENCE OF AccessControlEntry
	ACCESS		not-accessible
	STATUS		optional
	DESCRIPTION	"A list of the access control entries."
	::= { ndAdmin 11 }

    accessControlEntry	OBJECT-TYPE
	SYNTAX		AccessControlEntry
	ACCESS		not-accessible
	STATUS		optional
	DESCRIPTION	"An entry for the access control."
	INDEX		{ accessControlIndex }
	::= { accessControlTable 1 }

    AccessControlEntry ::=
	SEQUENCE {
	    accessControlIndex
		INTEGER,
	    accessControlPermit
		INTEGER,
	    accessControlProtocol
		INTEGER,
	    accessControlIPaddress
		IpAddress,
	    accessControlMaskLength
		INTEGER
	}

    accessControlIndex	OBJECT-TYPE
	SYNTAX		INTEGER
	ACCESS		read-only
	STATUS		optional
	DESCRIPTION     "A unique value for each accessControl entry.
			It's value ranges between 1 and the value
			accessControlNumber."
	::= { accessControlEntry 1 }

    accessControlPermit	OBJECT-TYPE
	SYNTAX		INTEGER {
			    allow(1),
			    deny(2),
			    unused(3)
			}
	ACCESS		read-only
	STATUS		optional
	DESCRIPTION	"The type of permission to specify with this entry."
	::= { accessControlEntry 2 }

    accessControlProtocol	OBJECT-TYPE
	SYNTAX		INTEGER {
			    any(1),
			    telnet(2),
			    http(3),
			    snmp(4),
			    ftp(5),
			    rsh(6)
			}
	ACCESS		read-only
	STATUS		optional
	DESCRIPTION	"This protocol is an object of the access control."
	::= { accessControlEntry 3 }

    accessControlIPaddress	OBJECT-TYPE
	SYNTAX		IpAddress
	ACCESS		read-only
	STATUS		optional
	DESCRIPTION	"This IP address is an object of the access control."
	::= { accessControlEntry 4 }

    accessControlMaskLength	OBJECT-TYPE
	SYNTAX		INTEGER
	ACCESS		read-only
	STATUS		optional
	DESCRIPTION	"This address mask length is an object of the access
			control."
	::= { accessControlEntry 5 }

-- The Network Device Admin TimeZone Group
    adminTimeZone        OBJECT-TYPE
	SYNTAX		INTEGER
	ACCESS		read-write
	STATUS		optional
	DESCRIPTION	"This value indicates timezone."
	::= { ndAdmin 12 }

-- The Network Device Admin NTP Group (Ver 3.0 or Later support)

    adminNTP		OBJECT IDENTIFIER ::= { ndAdmin 13 }
    ntpClient		OBJECT-TYPE
	SYNTAX		INTEGER {
			    enable(1),
			    disable(2)
			}
	ACCESS		read-write
	STATUS		optional
	DESCRIPTION	"The NTP client function is permitted."
	::= { adminNTP 1 }

    ntpPollInterval	OBJECT-TYPE
	SYNTAX		INTEGER
	ACCESS		read-write
	STATUS		optional
	DESCRIPTION	"Interval of polling to NTP server."
	::= { adminNTP 2 }

    ntpCorrectTime	OBJECT-TYPE
	SYNTAX		INTEGER
	ACCESS		read-write
	STATUS		optional
	DESCRIPTION	"If the interval between NTP server's time and
			local time is larger than this value, 
			gradually local time is corrected."
	::= { adminNTP 3 }

    ntpModifyTime	OBJECT-TYPE
	SYNTAX		INTEGER
	ACCESS		read-write
	STATUS		optional
	DESCRIPTION	"If the interval between NTP server's time and
			local time is larger than this value, 
			immediately local time is modified."
	::= { adminNTP 4 }

    ntpCurrentSynchronizeServer	OBJECT-TYPE
	SYNTAX		IpAddress
	ACCESS		read-only
	STATUS		optional
	DESCRIPTION	"NTP server to which most nearest polling is sent."
	::= { adminNTP 5 }

    ntpPollingTime	OBJECT-TYPE
	SYNTAX		INTEGER
	ACCESS		read-only
	STATUS		optional
	DESCRIPTION	"Time till next polling."
	::= { adminNTP 6 }

    ntpDelay		OBJECT-TYPE
	SYNTAX		INTEGER
	ACCESS		read-only
	STATUS		optional
	DESCRIPTION	"Time took to send packet from Network device to
			 NTP server."
	::= { adminNTP 7 }

    ntpDifference	OBJECT-TYPE
	SYNTAX		INTEGER
	ACCESS		read-only
	STATUS		optional
	DESCRIPTION	"Difference between NTP server's time and local time."
	::= { adminNTP 8 }

    ntpServerNumber 	OBJECT-TYPE
	SYNTAX		INTEGER
	ACCESS		read-only
	STATUS		optional
	DESCRIPTION	"The number of NTP server."
	::= { adminNTP 9 }

    ntpServerTable	OBJECT-TYPE
	SYNTAX		SEQUENCE OF NtpServerEntry
	ACCESS		not-accessible
	STATUS		optional
	DESCRIPTION	"A list of NTP server."
	::= { adminNTP 10 }

    ntpCurrentSynchronizeServerString	OBJECT-TYPE
	SYNTAX		DisplayString (SIZE (0..63))
	ACCESS		read-only
	STATUS		optional
	DESCRIPTION	"NTP server to which most nearest polling is sent."
	::= { adminNTP 11 }


    ntpServerEntry	OBJECT-TYPE
	SYNTAX		NtpServerEntry
	ACCESS		not-accessible
	STATUS		optional
	DESCRIPTION	"An entry for NTP server."
	INDEX		{ ntpServerIndex }
	::= { ntpServerTable 1 }

    NtpServerEntry ::=
	SEQUENCE {
	    ntpServerIndex
		INTEGER,
	    ntpServerIPaddress
		IpAddress,
	    ntpServerTimeout
		INTEGER,
	    ntpServerIPaddressString
		DisplayString
	}

    ntpServerIndex	OBJECT-TYPE
	SYNTAX		INTEGER
	ACCESS		read-only
	STATUS		optional
	DESCRIPTION	"A unique value for each ntpServer entry.
			It's value ranges between 1 and the value
			ntpServerNumber."
	::= { ntpServerEntry 1 }

    ntpServerIPaddress	OBJECT-TYPE
	SYNTAX		IpAddress
	ACCESS		read-write
	STATUS		optional
	DESCRIPTION	"IP address of NTP server."
	::= { ntpServerEntry 2 }

    ntpServerTimeout	OBJECT-TYPE
	SYNTAX		INTEGER
	ACCESS		read-write
	STATUS		optional
	DESCRIPTION	"If there is no response from NTP server 
			for this value, next polling is done."
	::= { ntpServerEntry 3 }

    ntpServerIPaddressString	OBJECT-TYPE
	SYNTAX		DisplayString (SIZE (0..63))
	ACCESS		read-write
	STATUS		optional
	DESCRIPTION	"Host of NTP server."
	::= { ntpServerEntry 4 }

-- The Network Device Email Group (Ver 3.0 or Later support)

    adminElectricMail	OBJECT IDENTIFIER ::= { ndAdmin 14 }

    emailEnable		OBJECT-TYPE
	SYNTAX          INTEGER {
			    enable(1),
			    disable(2)
			}
	ACCESS          read-write
	STATUS          optional
	DESCRIPTION     "Indicates whether the SNMP agent process is
			permitted to ElectricMail future."
	::= { adminElectricMail 1 }

    emailSMTPServer	OBJECT-TYPE
	SYNTAX		IpAddress
	ACCESS		read-write
	STATUS		optional
	DESCRIPTION     "SMTP Server address for ElectricMail"
	::= { adminElectricMail 2 }

    emailFromUser	OBJECT-TYPE
	SYNTAX		DisplayString (SIZE (0..63))
	ACCESS		read-write
	STATUS		optional
	DESCRIPTION     "ElectricMail From Address"
	::= { adminElectricMail 3 }

    emailSendUserNumber	OBJECT-TYPE
	SYNTAX		INTEGER
	ACCESS		read-only
	STATUS		mandatory
	DESCRIPTION	"The number of send mail user entry supported by this device."
	::= { adminElectricMail 4 }

    emailSendUserTable OBJECT-TYPE
	    SYNTAX          SEQUENCE OF EmailSendUserEntry
	    ACCESS          not-accessible
	    STATUS          optional
	    DESCRIPTION     "A list of emailSendUser table."
	::= { adminElectricMail 5 }

    emailSendUserEntry	OBJECT-TYPE
	SYNTAX		EmailSendUserEntry
	ACCESS          not-accessible
	STATUS          optional
	DESCRIPTION     "An entry for Email address."
	INDEX		{ emailSendUserIndex }
	::= { emailSendUserTable 1 }

    EmailSendUserEntry ::=
        SEQUENCE {
	    emailSendUserIndex
		INTEGER,
	    emailSendUserAddress
		DisplayString
	}

    emailSendUserIndex	OBJECT-TYPE
	    SYNTAX          INTEGER
	    ACCESS          read-only
	    STATUS          optional
	    DESCRIPTION     "A unique value for each emailSendUser entry.
			    It's value ranges between 1 and the value
			    emailSendUserNumber."
    ::= { emailSendUserEntry 1 }

    emailSendUserAddress OBJECT-TYPE
	    SYNTAX          DisplayString (SIZE (0..255))
	    ACCESS          read-write
	    STATUS          optional
	    DESCRIPTION     "Send user E-Mail address."
    ::= { emailSendUserEntry 2 }

    emailSubject	OBJECT-TYPE
	SYNTAX		DisplayString (SIZE (0..31))
	ACCESS		read-write
	STATUS		optional
	DESCRIPTION     "Subject"
	::= { adminElectricMail 6 }

    emailBody		OBJECT-TYPE
	SYNTAX		DisplayString (SIZE (0..255))
	ACCESS		read-write
	STATUS		optional
	DESCRIPTION     "Mail Body"
	::= { adminElectricMail 7 }

    emailLogging	OBJECT-TYPE
	SYNTAX          INTEGER {
			    enable(1),
			    disable(2)
			}
	ACCESS          read-write
	STATUS          optional
	DESCRIPTION     "Indicates whether the SNMP agent process is
			permitted to ElectricMail logging future."
	::= { adminElectricMail 8 }

    emailAuthReport	OBJECT-TYPE
	SYNTAX          INTEGER {
			    enable(1),
			    disable(2)
			}
	ACCESS          read-write
	STATUS          optional
	DESCRIPTION     "Indicates whether the SNMP agent process is
			Send Email when Authentication failed"
	::= { adminElectricMail 9 }

    emailColdStartReport	OBJECT-TYPE
	SYNTAX          INTEGER {
			    enable(1),
			    disable(2)
			}
	ACCESS          read-write
	STATUS          optional
	DESCRIPTION     "Indicates whether the SNMP agent process is
			Send Email when Cold started."
	::= { adminElectricMail 10 }

    emailSMTPServerString	OBJECT-TYPE
	SYNTAX		DisplayString (SIZE (0..63))
	ACCESS		read-write
	STATUS		optional
	DESCRIPTION     "SMTP Server host for ElectricMail"
	::= { adminElectricMail 11 }

    emailSMTPPort	OBJECT-TYPE
	SYNTAX		INTEGER (1..65535)
	ACCESS		read-write
	STATUS		optional
	DESCRIPTION	"SMTP Server port."
	::= { adminElectricMail 12 }

    emailPOPBeforeSMTPEnable		OBJECT-TYPE
	SYNTAX          INTEGER {
			    enable(1),
			    disable(2)
			}
	ACCESS          read-write
	STATUS          optional
	DESCRIPTION     "Indicates whether the SNMP agent process is
			permitted to ElectricMail future."
	::= { adminElectricMail 13 }

    emailPOPBeforeSMTPServer	OBJECT-TYPE
	SYNTAX		DisplayString (SIZE (0..63))
	ACCESS		read-write
	STATUS		optional
	DESCRIPTION     "SMTP Server host for ElectricMail"
	::= { adminElectricMail 14 }

    emailPOPBeforeSMTPPort	OBJECT-TYPE
	SYNTAX		INTEGER (1..65535)
	ACCESS		read-write
	STATUS		optional
	DESCRIPTION	"SMTP Server port."
	::= { adminElectricMail 15 }

    emailPOPBeforeSMTPUser	OBJECT-TYPE
	SYNTAX		DisplayString (SIZE (0..63))
	ACCESS		read-write
	STATUS		optional
	DESCRIPTION     "SMTP Server host for ElectricMail"
	::= { adminElectricMail 16 }

    emailPOPBeforeSMTPPassword	OBJECT-TYPE
	SYNTAX		DisplayString (SIZE (0..63))
	ACCESS		read-write
	STATUS		optional
	DESCRIPTION     "SMTP Server host for ElectricMail"
	::= { adminElectricMail 17 }

    emailSMTPAuthEnable		OBJECT-TYPE
	SYNTAX          INTEGER {
			    enable(1),
			    disable(2)
			}
	ACCESS          read-write
	STATUS          optional
	DESCRIPTION     "Indicates whether the SNMP agent process is
			permitted to ElectricMail future."
	::= { adminElectricMail 18 }

    emailSMTPAuthUser	OBJECT-TYPE
	SYNTAX		DisplayString (SIZE (0..63))
	ACCESS		read-write
	STATUS		optional
	DESCRIPTION     "SMTP Server host for ElectricMail"
	::= { adminElectricMail 19 }

    emailSMTPAuthPassword	OBJECT-TYPE
	SYNTAX		DisplayString (SIZE (0..63))
	ACCESS		read-write
	STATUS		optional
	DESCRIPTION     "SMTP Server host for ElectricMail"
	::= { adminElectricMail 20 }


-- The Network Device Network Service Group (Ver 3.5 or Later support)

    adminService	OBJECT IDENTIFIER ::= { ndAdmin 15 }

    serviceSNMPPort	OBJECT-TYPE
	SYNTAX		INTEGER (1..65535)
	ACCESS		read-write
	STATUS		optional
	DESCRIPTION	"SNMP service port."
	::= { adminService 1 }

    serviceSNMPStart OBJECT-TYPE
	SYNTAX		INTEGER {
			    enable(1),
			    disable(2)
			}
	ACCESS		read-write
	STATUS		optional
	DESCRIPTION	"Indicates whther the SNMP service start up."
	::= { adminService 2 }

    serviceTELNETPort	OBJECT-TYPE
	SYNTAX		INTEGER (1..65535)
	ACCESS		read-write
	STATUS		optional
	DESCRIPTION	"TELNET service port."
	::= { adminService 3 }

    serviceTELNETStart OBJECT-TYPE
	SYNTAX		INTEGER {
			    enable(1),
			    disable(2)
			}
	ACCESS		read-write
	STATUS		optional
	DESCRIPTION	"Indicates whther the TELNET service start up."
	::= { adminService 4 }

    serviceHTTPPort	OBJECT-TYPE
	SYNTAX		INTEGER (1..65535)
	ACCESS		read-write
	STATUS		optional
	DESCRIPTION	"HTTP service port."
	::= { adminService 5 }

    serviceHTTPStart OBJECT-TYPE
	SYNTAX		INTEGER {
			    enable(1),
			    disable(2)
			}
	ACCESS		read-write
	STATUS		optional
	DESCRIPTION	"Indicates whther the HTTP service start up."
	::= { adminService 6 }

    serviceFTPPort	OBJECT-TYPE
	SYNTAX		INTEGER (1..65535)
	ACCESS		read-write
	STATUS		optional
	DESCRIPTION	"FTP service port."
	::= { adminService 7 }

    serviceFTPStart OBJECT-TYPE
	SYNTAX		INTEGER {
			    enable(1),
			    disable(2)
			}
	ACCESS		read-write
	STATUS		optional
	DESCRIPTION	"Indicates whther the FTP service start up."
	::= { adminService 8 }

    serviceRSHDPort	OBJECT-TYPE
	SYNTAX		INTEGER (1..65535)
	ACCESS		read-write
	STATUS		optional
	DESCRIPTION	"RSHD service port."
	::= { adminService 9 }

    serviceRSHDStart OBJECT-TYPE
	SYNTAX		INTEGER {
			    enable(1),
			    disable(2)
			}
	ACCESS		read-write
	STATUS		optional
	DESCRIPTION	"Indicates whther the RSHD service start up."
	::= { adminService 10 }

    serviceTELNETTimeout	OBJECT-TYPE
	SYNTAX		INTEGER
	ACCESS		read-write
	STATUS		optional
	DESCRIPTION	"Indicates timeout of telnet."
	::= { adminService 11 }

-- The Network Device WWW Authentication Group (Ver 3.5 or Later support)

    adminWWW		OBJECT IDENTIFIER ::= { ndAdmin 16 }

    wwwUserNumber	OBJECT-TYPE
	SYNTAX		INTEGER
	ACCESS		read-only
	STATUS		mandatory
	DESCRIPTION	"The number of www user entry supported by this device."
	::= { adminWWW 1 }

    wwwUserTable OBJECT-TYPE
	    SYNTAX          SEQUENCE OF WwwUserEntry
	    ACCESS          not-accessible
	    STATUS          optional
	    DESCRIPTION     "A list of wwwUser table."
	::= { adminWWW 2 }

    wwwUserEntry	OBJECT-TYPE
	SYNTAX		WwwUserEntry
	ACCESS          not-accessible
	STATUS          optional
	DESCRIPTION     "An entry for www user."
	INDEX		{ wwwUserIndex }
	::= { wwwUserTable 1 }

    WwwUserEntry ::=
        SEQUENCE {
	    wwwUserIndex
		INTEGER,
	    wwwUserName
		DisplayString,
	    wwwUserPassword
		DisplayString
	}

    wwwUserIndex	OBJECT-TYPE
	    SYNTAX          INTEGER
	    ACCESS          read-only
	    STATUS          optional
	    DESCRIPTION     "A unique value for each wwwUser entry.
			    It's value ranges between 1 and the value
			    wwwUserNumber."
    ::= { wwwUserEntry 1 }

    wwwUserName		OBJECT-TYPE
	    SYNTAX	    DisplayString (SIZE (0..64))
	    ACCESS	    read-write
	    STATUS          optional
	    DESCRIPTION     "User name is used to access a www page."
    ::= { wwwUserEntry 2 }

    wwwUserPassword	OBJECT-TYPE
	    SYNTAX	    DisplayString (SIZE (0..64))
	    ACCESS	    read-write
	    STATUS          optional
	    DESCRIPTION     "Password is used to access a www page."
    ::= { wwwUserEntry 3 }

    wwwAuthenticateNumber	OBJECT-TYPE
	SYNTAX		INTEGER
	ACCESS		read-only
	STATUS		mandatory
	DESCRIPTION	"The number of www authenticate page entry supported by this device."
	::= { adminWWW 3 }

    wwwAuthenticateTable 	OBJECT-TYPE
	    SYNTAX          SEQUENCE OF WwwAuthenticateEntry
	    ACCESS          not-accessible
	    STATUS          optional
	    DESCRIPTION     "A list of wwwAuthenticate table."
	::= { adminWWW 4 }

    wwwAuthenticateEntry	OBJECT-TYPE
	SYNTAX		WwwAuthenticateEntry
	ACCESS          not-accessible
	STATUS          optional
	DESCRIPTION     "An entry for www authenticate page."
	INDEX		{ wwwAuthenticateIndex }
	::= { wwwAuthenticateTable 1 }

    WwwAuthenticateEntry ::=
        SEQUENCE {
	    wwwAuthenticateIndex
		INTEGER,
	    wwwAuthenticatePath
		DisplayString,
	    wwwAuthenticateEnable
		INTEGER,
	    wwwAuthenticateUser1
		INTEGER,
	    wwwAuthenticateUser2
		INTEGER,
	    wwwAuthenticateUser3
		INTEGER
	}

    wwwAuthenticateIndex	OBJECT-TYPE
	    SYNTAX          INTEGER
	    ACCESS          read-only
	    STATUS          optional
	    DESCRIPTION     "A unique value for each wwwAuthenticate entry.
			    It's value ranges between 1 and the value
			    wwwAuthenticateNumber."
    ::= { wwwAuthenticateEntry 1 }

    wwwAuthenticatePath		OBJECT-TYPE
	    SYNTAX	    DisplayString (SIZE (0..128))
	    ACCESS	    read-only
	    STATUS          optional
	    DESCRIPTION     "Path of the www page."
    ::= { wwwAuthenticateEntry 2 }

    wwwAuthenticateEnable	OBJECT-TYPE
	    SYNTAX          INTEGER {
			    enable(1),
			    disable(2)
			    }
	    ACCESS          read-write
	    STATUS          optional
	    DESCRIPTION     "Indicates whether the www page is required authorization."
    ::= { wwwAuthenticateEntry 3 }

    wwwAuthenticateUser1	OBJECT-TYPE
	    SYNTAX          INTEGER {
			    enable(1),
			    disable(2)
			    }
	    ACCESS          read-write
	    STATUS          optional
	    DESCRIPTION     "Indicates whether user1 is permitted to the www page."
    ::= { wwwAuthenticateEntry 4 }

    wwwAuthenticateUser2	OBJECT-TYPE
	    SYNTAX          INTEGER {
			    enable(1),
			    disable(2)
			    }
	    ACCESS          read-write
	    STATUS          optional
	    DESCRIPTION     "Indicates whether user2 is permitted to the www page."
    ::= { wwwAuthenticateEntry 5 }

    wwwAuthenticateUser3	OBJECT-TYPE
	    SYNTAX          INTEGER {
			    enable(1),
			    disable(2)
			    }
	    ACCESS          read-write
	    STATUS          optional
	    DESCRIPTION     "Indicates whether user3 is permitted to the www page."
    ::= { wwwAuthenticateEntry 6 }


-- The Network Device Remote Command Group (Ver 3.6 or Later support)

    adminRemoteCommand	OBJECT IDENTIFIER ::= { ndAdmin 17 }

    remoteCommandEnable		OBJECT-TYPE
	SYNTAX          INTEGER {
			    enable(1),
			    disable(2)
			}
	ACCESS          read-write
	STATUS          optional
	DESCRIPTION     "Indicates whether the SNMP agent process is
			permitted to remote command future."
	::= { adminRemoteCommand 1 }

    remoteCommandLogging	OBJECT-TYPE
	SYNTAX          INTEGER {
			    enable(1),
			    disable(2)
			}
	ACCESS          read-write
	STATUS          optional
	DESCRIPTION     "Indicates whether the SNMP agent process is
			permitted to remote command logging future."
	::= { adminRemoteCommand 2 }

    remoteCommandSetNumber	OBJECT-TYPE
	SYNTAX		INTEGER
	ACCESS		read-only
	STATUS		mandatory
	DESCRIPTION	"The number of remote command set entry supported by this device."
	::= { adminRemoteCommand 3 }

    remoteCommandSetTable 	OBJECT-TYPE
	    SYNTAX          SEQUENCE OF RemoteCommandSetEntry
	    ACCESS          not-accessible
	    STATUS          optional
	    DESCRIPTION     "A list of remoteCommandSet table."
	::= { adminRemoteCommand 4 }

    remoteCommandSetEntry	OBJECT-TYPE
	SYNTAX		RemoteCommandSetEntry
	ACCESS          not-accessible
	STATUS          optional
	DESCRIPTION     "An entry for remote command set."
	INDEX		{ remoteCommandSetIndex }
	::= { remoteCommandSetTable 1 }

    RemoteCommandSetEntry ::=
        SEQUENCE {
	    remoteCommandSetIndex
		INTEGER,
	    remoteCommandSetHost
		IpAddress,
	    remoteCommandSetPort
		INTEGER,
	    remoteCommandSetUser
		DisplayString,
	    remoteCommandSetTimeout
		INTEGER,
	    remoteCommandSetTimeover
		INTEGER,
	    remoteCommandSetCommand
		DisplayString,
	    remoteCommandSetHostString
		DisplayString
	}

    remoteCommandSetIndex	OBJECT-TYPE
	    SYNTAX          INTEGER
	    ACCESS          read-only
	    STATUS          optional
	    DESCRIPTION     "A unique value for each remote command set entry.
			    It's value ranges between 1 and the value
			    remoteCommandSetNumber."
    ::= { remoteCommandSetEntry 1 }

    remoteCommandSetHost	OBJECT-TYPE
	    SYNTAX	    IpAddress
	    ACCESS	    read-write
	    STATUS          optional
	    DESCRIPTION     "The IP address of host which execute remote command."
    ::= { remoteCommandSetEntry 2 }

    remoteCommandSetPort	OBJECT-TYPE
	    SYNTAX          INTEGER (1..65535)
	    ACCESS          read-write
	    STATUS          optional
	    DESCRIPTION     "The port of host which execute remote command."
    ::= { remoteCommandSetEntry 3 }

    remoteCommandSetUser	OBJECT-TYPE
	    SYNTAX          DisplayString (SIZE (0..32))
	    ACCESS          read-write
	    STATUS          optional
	    DESCRIPTION     "The user of host which execute remote command."
    ::= { remoteCommandSetEntry 4 }

    remoteCommandSetTimeout	OBJECT-TYPE
	    SYNTAX          INTEGER
	    ACCESS          read-write
	    STATUS          optional
	    DESCRIPTION     "If there is no response from host for this value,
			    the session is left off."
    ::= { remoteCommandSetEntry 5 }

    remoteCommandSetTimeover	OBJECT-TYPE
	    SYNTAX          INTEGER
	    ACCESS          read-write
	    STATUS          optional
	    DESCRIPTION     "If execution of remote command isn't completed for 
			    this value, the session is left off."
    ::= { remoteCommandSetEntry 6 }

    remoteCommandSetCommand	OBJECT-TYPE
	    SYNTAX          DisplayString (SIZE (0..256))
	    ACCESS          read-write
	    STATUS          optional
	    DESCRIPTION     "Command which is executed by remote host."
    ::= { remoteCommandSetEntry 7 }

    remoteCommandSetHostString	OBJECT-TYPE
	    SYNTAX	    DisplayString (SIZE (0..64))
	    ACCESS	    read-write
	    STATUS          optional
	    DESCRIPTION     "The host which execute remote command."
    ::= { remoteCommandSetEntry 8 }

-- The Network Device Lock Group  (Ver 4.2 or Later support)

    adminLock            OBJECT IDENTIFIER ::= { ndAdmin 18 }

    lockMode             OBJECT-TYPE
        SYNTAX          INTEGER {
                            compatible-mode(1),
                            ipk-ml01orml02-mode(2),
                            uil-mode(3)
                        }
        ACCESS          read-write
        STATUS          optional
        DESCRIPTION     "Caution:
		A different definition in ND-EW04 and ND-LM01/02 was
		done to this OID. As a result of the conference,
		the definition of ND-LM01/02 is adopted. 
		Please note becoming an improper definition when
		using it by ND-EW04. 
		The in existence application doesn't use this definition. "
        ::= { adminLock 1 }

    lockHostResponse	OBJECT-TYPE
	SYNTAX          DisplayString
	ACCESS          read-write
	STATUS          optional
	DESCRIPTION     "The response from certification hosts."
	::= { adminLock 2 }

    lockOperationTimeout		OBJECT-TYPE
	SYNTAX          INTEGER
	ACCESS          read-write
	STATUS          optional
	DESCRIPTION     "The card reader ID which is allocated."
	::= { adminLock 3 }

    lockHostResponseTimeout		OBJECT-TYPE
	SYNTAX          INTEGER
	ACCESS          read-write
	STATUS          optional
	DESCRIPTION     "The tenkey data which is allocated."
	::= { adminLock 4 }

    lockUnlockingTimeout	OBJECT-TYPE
	SYNTAX          INTEGER
	ACCESS          read-write
	STATUS          optional
	DESCRIPTION     "The maximum time which maintains opening lock state."
	::= { adminLock 5 }



    lockLastCardData	OBJECT-TYPE
	SYNTAX		DisplayString (SIZE (0..256))
	ACCESS		read-only
	STATUS		mandatory
	DESCRIPTION	"The latest	card ID and time and the card reader ID of the card
                 which is read."
	::= { adminLock 8 }

    lockUserRegistration	OBJECT-TYPE
	SYNTAX		DisplayString (SIZE (0..30))
	ACCESS		read-write
	STATUS		mandatory
	DESCRIPTION	"Registration of new certification data.
                 Set string is 'xxxxx:XXXXXXXXXXXXXXXXXXXXXXXX'.
                 xxxxx is 00001 - 99999.
                 XXXXXXXXXXXXXXXXXXXXXXXX is 24 byte string."
	::= { adminLock 9 }

    lockUserErase	OBJECT-TYPE
	SYNTAX		INTEGER
	ACCESS		read-write
	STATUS		mandatory
	DESCRIPTION	"Erasion of the certification data."
	::= { adminLock 10 }

    lockCertifyNumber	OBJECT-TYPE
	SYNTAX		INTEGER
	ACCESS		read-only
	STATUS		mandatory
	DESCRIPTION	"The number of certifycation data which are registered."
	::= { adminLock 11 }

    lockCertifyTable 	OBJECT-TYPE
	    SYNTAX          SEQUENCE OF LockCertifyEntry
	    ACCESS          not-accessible
	    STATUS          optional
	    DESCRIPTION     "A list of certification data table."
	::= { adminLock 12 }

    lockCertifyEntry	OBJECT-TYPE
	SYNTAX				LockCertifyEntry
	ACCESS          not-accessible
	STATUS          optional
	DESCRIPTION     "An entry for certfification data."
	INDEX		{ lockCertifyIndex }
	::= { lockCertifyTable 1 }

    LockCertifyEntry ::=
        SEQUENCE {
	    lockCertifyIndex
		INTEGER,
	    lockCertifyUserID
		INTEGER,
	    lockCertifyCardID
		DisplayString,
	    lockCertifyDoChannel
		INTEGER
	}

    lockCertifyIndex	OBJECT-TYPE
	    SYNTAX          INTEGER
	    ACCESS          read-only
	    STATUS          optional
	    DESCRIPTION     "A unique value for each certification data entry.
			    It's value ranges between 1 and the value
			    lockCertifyNumber."
    ::= { lockCertifyEntry 1 }

    lockCertifyUserID	OBJECT-TYPE
	    SYNTAX	    INTEGER
	    ACCESS	    read-only
	    STATUS          optional
	    DESCRIPTION     "User ID of certification data."
    ::= { lockCertifyEntry 2 }

    lockCertifyCardID	OBJECT-TYPE
	    SYNTAX          DisplayString (SIZE (0..24))
	    ACCESS          read-only
	    STATUS          optional
	    DESCRIPTION     "Card ID of certification data."
    ::= { lockCertifyEntry 3 }

    lockCertifyDoChannel	OBJECT-TYPE
	    SYNTAX          DisplayString (SIZE (0..512))
	    ACCESS          read-write
	    STATUS          optional
	    DESCRIPTION     "State of DO channel of certification data."
    ::= { lockCertifyEntry 4 }

    lockAllocationCardReaderNumber	OBJECT-TYPE
	SYNTAX		INTEGER
	ACCESS		read-only
	STATUS		mandatory
	DESCRIPTION	"The maximum number of card readers."
	::= { adminLock 13 }

    lockAllocationTenkeyNumber	OBJECT-TYPE
	SYNTAX		INTEGER
	ACCESS		read-only
	STATUS		mandatory
	DESCRIPTION	"The maximum number of tenkeys."
	::= { adminLock 14 }

    lockAllocationTable 	OBJECT-TYPE
	    SYNTAX          SEQUENCE OF LockAllocationEntry
	    ACCESS          not-accessible
	    STATUS          optional
	    DESCRIPTION     "A list of allocation data table."
	::= { adminLock 15 }

    lockAllocationEntry	OBJECT-TYPE
	SYNTAX			LockAllocationEntry
	ACCESS          not-accessible
	STATUS          optional
	DESCRIPTION     "An entry for allocation data."
	INDEX		{ lockAllocationCardReaderIndex, lockAllocationTenkeyIndex }
	::= { lockAllocationTable 1 }

    LockAllocationEntry ::=
        SEQUENCE {
	    lockAllocationCardReaderIndex
		INTEGER,
	    lockAllocationTenkeyIndex
		INTEGER,
	    lockAllocationCardReaderID
		INTEGER,
	    lockAllocationTenkey
		DisplayString,
	    lockAllocationDoChannel
		DisplayString
	}

    lockAllocationCardReaderIndex	OBJECT-TYPE
	    SYNTAX          INTEGER
	    ACCESS          read-only
	    STATUS          optional
	    DESCRIPTION     "A unique value for each lock allocation entry.
                       It's value range between 1 and the value 
                       lockAllocationCardReaderNumber."
    ::= { lockAllocationEntry 1 }

    lockAllocationTenkeyIndex	OBJECT-TYPE
	    SYNTAX          INTEGER
	    ACCESS          read-only
	    STATUS          optional
	    DESCRIPTION     "A unique value for each lock allocation entry.
                       It's value range between 1 and the value 
                       lockAllocationTenkeyNumber."
    ::= { lockAllocationEntry 2 }

    lockAllocationCardReaderID	OBJECT-TYPE
	    SYNTAX          INTEGER
	    ACCESS          read-write
	    STATUS          optional
	    DESCRIPTION     "The ID of the card reader which allocated."
    ::= { lockAllocationEntry 3 }

    lockAllocationTenkey	OBJECT-TYPE
	    SYNTAX          DisplayString (SIZE (0..512))
	    ACCESS          read-write
	    STATUS          optional
	    DESCRIPTION     "The data for tenkey input which is allocated."
    ::= { lockAllocationEntry 4 }

    lockAllocationDoChannel	OBJECT-TYPE
	    SYNTAX          DisplayString (SIZE (0..512))
	    ACCESS          read-write
	    STATUS          optional
	    DESCRIPTION     "The DO channels wich can control locks."
    ::= { lockAllocationEntry 5 }

    lockDoorOpen	OBJECT-TYPE
	SYNTAX		INTEGER(0..999000)
	ACCESS		read-write
	STATUS		mandatory
	DESCRIPTION	"The time[ms] out of opening the door
                        0:invalid"
	::= { adminLock 16 }

    lockReaderType	OBJECT-TYPE
	SYNTAX		INTEGER
	ACCESS		read-write
	STATUS		mandatory
	DESCRIPTION	"The type of the cardreaderunit"
	::= { adminLock 17 }

    lockContinuousTable	OBJECT-TYPE
	SYNTAX		INTEGER
	ACCESS		read-write
	STATUS		mandatory
	DESCRIPTION	"The mode of continuous lock/unlock"
	::= { adminLock 19 }

    lockContinuousEntry	OBJECT-TYPE
	SYNTAX		LockContinuousEntry
	ACCESS          not-accessible
	STATUS          optional
	DESCRIPTION     "An entry for continuous lock/unlock data."
	INDEX		{ lockContinuousModeIndex, lockContinuousTimeIndex }
	::= { lockContinuousTable 1 }

    LockContinuousEntry ::=
        SEQUENCE {
	    lockContinuousModeIndex
		INTEGER,
	    lockContinuousTimeIndex
		INTEGER
	}

    lockContinuousModeIndex	OBJECT-TYPE
	SYNTAX          INTEGER {
				normal-mode(0),
				unlock-mode(1)
			}
	ACCESS          read-write
	STATUS          optional
	DESCRIPTION     "A unique value for each continuous lock/unlock mode entry."
	::= { lockContinuousEntry 1 }

    lockContinuousTimeIndex	OBJECT-TYPE
	SYNTAX          INTEGER(0..9999999)
	ACCESS          read-write
	STATUS          optional
	DESCRIPTION     "A unique value for each continuous lock/unlock time[s] entry."
	::= { lockContinuousEntry 2 }

    lockContinuousModeAll	OBJECT-TYPE
	SYNTAX		DisplayString
	ACCESS		read-write
	STATUS		mandatory
	DESCRIPTION	"The continuous lock/unlock mode for all channel."
	::= { adminLock 20 }

    lockContinuousTimeAll	OBJECT-TYPE
	SYNTAX		DisplayString
	ACCESS		read-write
	STATUS		mandatory
	DESCRIPTION	"The continuous lock/unlock time[s] for all channel."
	::= { adminLock 21 }

    lockReaderBuzzerControl	OBJECT-TYPE
        SYNTAX          INTEGER {
                            disable(0),
                            enable(1)
                        }
	ACCESS		read-write
	STATUS		mandatory
	DESCRIPTION	"The warning buzzer on cardreder can controll by internal."
	::= { adminLock 22 }

    lockReaderBuzzer	OBJECT-TYPE
        SYNTAX          INTEGER {
                            disable(0),
                            enable(1)
                        }
	ACCESS		read-write
	STATUS		mandatory
	DESCRIPTION	"The warning buzzer on cardreder can controll by external."
	::= { adminLock 23 }


-- The Network Device Remote Server User Group (Ver 4.0 or Later support)

    adminRemoteServer   OBJECT IDENTIFIER ::= { ndAdmin 19 }

    remoteServerUser    OBJECT-TYPE
        SYNTAX          DisplayString (SIZE (0..63))
        ACCESS          read-write
        STATUS          optional
        DESCRIPTION     "User-name for remote server authentication."
        ::= { adminRemoteServer 1 }


-- The Network Device IPsec Group (Ver 4.x or Later support)

    saNumber	OBJECT-TYPE
	SYNTAX		INTEGER
	ACCESS		read-only
	STATUS		optional
	DESCRIPTION	"The number of www Security Association entry
				supported by this device."
	::= { ndAdmin 20 }

    saTable			OBJECT-TYPE
    SYNTAX          SEQUENCE OF SaEntry
    ACCESS          not-accessible
    STATUS          optional
    DESCRIPTION     "A list of Security Association table."
	::= { ndAdmin 21 }

    saEntry		  OBJECT-TYPE
	SYNTAX		  SaEntry
	ACCESS        not-accessible
	STATUS        optional
	DESCRIPTION   "An entry for Security Association."
	INDEX		{ saIndex }
	::= { saTable 1 }

    SaEntry ::=
        SEQUENCE {
	    saIndex
		INTEGER,
	    saEnable
		INTEGER,
	    saSourceAddress
		DisplayString,
	    saDestinationAddress
		DisplayString,
	    saSPI
		INTEGER,
	    saProtocol
		INTEGER,
	    saEncryptionAlgorithm
		INTEGER,
	    saEncryptionKey
		DisplayString,
	    saHashAlgorithm
		INTEGER,
	    saHashKey
		DisplayString
	}

    saIndex				OBJECT-TYPE
	    SYNTAX          INTEGER
	    ACCESS          read-only
	    STATUS          optional
	    DESCRIPTION     "A unique value for each Security Association entry.
			    It's value ranges between 1 and the value
			    saNumber."
    ::= { saEntry 1 }

    saEnable		OBJECT-TYPE
	SYNTAX          INTEGER {
			    enable(1),
			    disable(2)
			}
	ACCESS          read-write
	STATUS          optional
	DESCRIPTION     "Indicates whether the SNMP agent process
			permitted to manage with this saEntry."
    ::= { saEntry 2 }

    saSourceAddress	OBJECT-TYPE
	SYNTAX		DisplayString (SIZE (0..63))
	ACCESS		read-write
	STATUS		optional
	DESCRIPTION	"Source IP(v6) address for Security Association."
    ::= { saEntry 3 }

    saDestinationAddress	OBJECT-TYPE
	SYNTAX		DisplayString (SIZE (0..63))
	ACCESS		read-write
	STATUS		optional
	DESCRIPTION	"Destination IP(v6) address for Security Association."
    ::= { saEntry 4 }

    saSPI		OBJECT-TYPE
	SYNTAX      INTEGER (256..2147483647)
	ACCESS          read-write
	STATUS          optional
	DESCRIPTION     "Parameter number of SPI(Security Paramters Index)."
    ::= { saEntry 5 }

    saProtocol		OBJECT-TYPE
	SYNTAX          INTEGER {
			    ah(2),
			    esp(3)
			}
	ACCESS          read-write
	STATUS          optional
	DESCRIPTION     "Security Protocol for Security Association."
    ::= { saEntry 6 }

    saEncryptionAlgorithm		OBJECT-TYPE
	SYNTAX          INTEGER {
			    none(1),
			    des(2),
			    triple-des(3),
			    cast128(6),
			    blowfish(7),
			    simple(11),
			    aes(12),
			    twofish(253)
			}
	ACCESS          read-write
	STATUS          optional
	DESCRIPTION     "Encryption Algorithm for Security Association."
    ::= { saEntry 7 }

    saEncryptionKey	OBJECT-TYPE
	SYNTAX		DisplayString (SIZE (0..256))
	ACCESS		read-write
	STATUS		optional
	DESCRIPTION	"Encryption Key for Encryption Algorithm."
    ::= { saEntry 8 }

    saHashAlgorithm		OBJECT-TYPE
	SYNTAX          INTEGER {
			    none(1),
			    hmac-md5(2),
			    hmac-sha1(3)
			}
	ACCESS          read-write
	STATUS          optional
	DESCRIPTION     "Hash Algorithm for Security Association."
    ::= { saEntry 9 }

    saHashKey	OBJECT-TYPE
	SYNTAX		DisplayString (SIZE (0..256))
	ACCESS		read-write
	STATUS		optional
	DESCRIPTION	"Hash Key for Hash Algorithm."
    ::= { saEntry 10 }

    spNumber	OBJECT-TYPE
	SYNTAX		INTEGER
	ACCESS		read-only
	STATUS		optional
	DESCRIPTION	"The number of www Security Policy entry
				supported by this device."
	::= { ndAdmin 22 }

    spTable			OBJECT-TYPE
    SYNTAX          SEQUENCE OF SpEntry
    ACCESS          not-accessible
    STATUS          optional
    DESCRIPTION     "A list of Security Policy table."
	::= { ndAdmin 23 }

    spEntry		  OBJECT-TYPE
	SYNTAX		  SpEntry
	ACCESS        not-accessible
	STATUS        optional
	DESCRIPTION   "An entry for Security Policy."
	INDEX		{ spIndex }
	::= { spTable 1 }

    SpEntry ::=
        SEQUENCE {
	    spIndex
		INTEGER,
	    spEnable
		INTEGER,
	    spSourceAddress
		DisplayString,
	    spSourcePrefix
		INTEGER,
	    spSourceProtocol
		INTEGER,
	    spDestinationAddress
		DisplayString,
	    spDestinationPrefix
		INTEGER,
	    spDestinationProtocol
		INTEGER,
	    spPacketProcess
		INTEGER,
	    spESP
		INTEGER,
	    spAH
		INTEGER
	}

    spIndex				OBJECT-TYPE
	    SYNTAX          INTEGER
	    ACCESS          read-only
	    STATUS          optional
	    DESCRIPTION     "A unique value for each Security Policy entry.
			    It's value ranges between 1 and the value
			    spNumber."
    ::= { spEntry 1 }

    spEnable		OBJECT-TYPE
	SYNTAX          INTEGER {
			    enable(1),
			    disable(2)
			}
	ACCESS          read-write
	STATUS          optional
	DESCRIPTION     "Indicates whether the SNMP agent process
			permitted to manage with this spEntry."
    ::= { spEntry 2 }

    spSourceAddress	OBJECT-TYPE
	SYNTAX		DisplayString (SIZE (0..63))
	ACCESS		read-write
	STATUS		optional
	DESCRIPTION	"Source IP(v6) address for Security Policy."
    ::= { spEntry 3 }

    spSourcePrefix	OBJECT-TYPE
	SYNTAX          INTEGER (-1..128)
	ACCESS          read-write
	STATUS          optional
	DESCRIPTION     "Source IP(v6) address's prefix size for Security Policy."
    ::= { spEntry 4 }

    spSourceProtocol	OBJECT-TYPE
	SYNTAX          INTEGER {
			    any(1),
			    icmp(2),
			    icmpv6(3),
			    ftp(4),
			    telnet(5),
			    smtp(6),
			    http(7),
			    rsh(8),
			    dns(9),
			    ntp(10),
			    snmp(11),
			    snmp-trap(12),
			    tcp(13),
			    udp(14)
			}
	ACCESS          read-write
	STATUS          optional
	DESCRIPTION     "Source IP(v6) address's protocol for Security Policy."
    ::= { spEntry 5 }

    spDestinationAddress	OBJECT-TYPE
	SYNTAX		DisplayString (SIZE (0..63))
	ACCESS		read-write
	STATUS		optional
	DESCRIPTION	"Destination IP(v6) address for Security Policy."
    ::= { spEntry 6 }

    spDestinationPrefix	OBJECT-TYPE
	SYNTAX          INTEGER (-1..128)
	ACCESS          read-write
	STATUS          optional
	DESCRIPTION     "Destination IP(v6) address's prefix size for Security Policy."
    ::= { spEntry 7 }

    spDestinationProtocol	OBJECT-TYPE
	SYNTAX          INTEGER {
			    any(1),
			    icmp(2),
			    icmpv6(3),
			    ftp(4),
			    telnet(5),
			    smtp(6),
			    http(7),
			    rsh(8),
			    dns(9),
			    ntp(10),
			    snmp(11),
			    snmp-trap(12),
			    tcp(13),
			    udp(14)
			}
	ACCESS          read-write
	STATUS          optional
	DESCRIPTION     "Destination IP(v6) address's protocol for Security Policy."
    ::= { spEntry 8 }

    spPacketProcess		OBJECT-TYPE
	SYNTAX          INTEGER {
			    through(1),
			    discard(2),
			    ipsec(3)
			}
	ACCESS          read-write
	STATUS          optional
	DESCRIPTION     "Packet processing method for Security Policy."
    ::= { spEntry 9 }

    spESP		OBJECT-TYPE
	SYNTAX          INTEGER {
			    none(1),
			    use(2),
			    require(3)
			}
	ACCESS          read-write
	STATUS          optional
	DESCRIPTION     "ESP(Encapsulating Security Payload)
					application method."
    ::= { spEntry 10 }

    spAH		OBJECT-TYPE
	SYNTAX          INTEGER {
			    none(1),
			    use(2),
			    require(3)
			}
	ACCESS          read-write
	STATUS          optional
	DESCRIPTION     "AH(Authentication Header) application method."
    ::= { spEntry 11 }

    ikePhase1Number	OBJECT-TYPE
	SYNTAX		INTEGER
	ACCESS		read-only
	STATUS		optional
	DESCRIPTION	"The number of www IKE(Internet Key
				Exchange) phase1 entry
				supported by this device."
	::= { ndAdmin 24 }

    ikePhase1Table			OBJECT-TYPE
    SYNTAX          SEQUENCE OF IkePhase1Entry
    ACCESS          not-accessible
    STATUS          optional
    DESCRIPTION     "A list of IKE(Internet Key Exchange) phase1 table."
	::= { ndAdmin 25 }

    ikePhase1Entry		  OBJECT-TYPE
	SYNTAX		  IkePhase1Entry
	ACCESS        not-accessible
	STATUS        optional
	DESCRIPTION   "An entry for IKE(Internet Key Exchange) phase1."
	INDEX		{ ikePhase1Index }
	::= { ikePhase1Table 1 }

    IkePhase1Entry ::=
        SEQUENCE {
	    ikePhase1Index
		INTEGER,
	    ikePhase1Enable
		INTEGER,
	    ikePhase1RemoteAddress
		DisplayString,
	    ikePhase1EncryptionAlgorithm
		INTEGER,
	    ikePhase1HashAlgorithm
		INTEGER,
	    ikePhase1DHGroup
		INTEGER,
	    ikePhase1LifeTime
		INTEGER,
	    ikePhase1PreSharedKey
		DisplayString
	}

    ikePhase1Index				OBJECT-TYPE
	    SYNTAX          INTEGER
	    ACCESS          read-only
	    STATUS          optional
	    DESCRIPTION     "A unique value for each 
						IKE(Internet Key Exchange) phase1 entry.
						It's value ranges between 1 and the value
						ikePhase1Number."
    ::= { ikePhase1Entry 1 }

    ikePhase1Enable		OBJECT-TYPE
	SYNTAX          INTEGER {
			    enable(1),
			    disable(2)
			}
	ACCESS          read-write
	STATUS          optional
	DESCRIPTION     "Indicates whether the SNMP agent process
			permitted to manage with this ikePhase1Entry."
    ::= { ikePhase1Entry 2 }

    ikePhase1RemoteAddress	OBJECT-TYPE
	SYNTAX		DisplayString (SIZE (0..63))
	ACCESS		read-write
	STATUS		optional
	DESCRIPTION	"Remote IP(v6) address for IKE(Internet Key Exchange) phase1."
    ::= { ikePhase1Entry 3 }

    ikePhase1EncryptionAlgorithm	OBJECT-TYPE
	SYNTAX          INTEGER {
			    des(2),
			    triple-des(3),
			    cast128(6),
			    blowfish(7)
			}
	ACCESS          read-write
	STATUS          optional
	DESCRIPTION     "Encryption Algorithm for 
					IKE(Internet Key Exchange) phase1."
    ::= { ikePhase1Entry 4 }

    ikePhase1HashAlgorithm	OBJECT-TYPE
	SYNTAX          INTEGER {
			    md5(25),
			    sha1(26)
			}
	ACCESS          read-write
	STATUS          optional
	DESCRIPTION     "Hash Algorithm for 
					IKE(Internet Key Exchange) phase1."
    ::= { ikePhase1Entry 5 }

    ikePhase1DHGroup	OBJECT-TYPE
	SYNTAX          INTEGER {
			    modp768(31),
			    modp1024(32),
			    modp1536(35)
			}
	ACCESS          read-write
	STATUS          optional
	DESCRIPTION     "Diffie Hellman Group for 
					IKE(Internet Key Exchange) phase1."
    ::= { ikePhase1Entry 6 }

    ikePhase1LifeTime	OBJECT-TYPE
	SYNTAX          INTEGER (1..2147483647)
	ACCESS          read-write
	STATUS          optional
	DESCRIPTION     "Life Time for IKE(Internet Key Exchange) phase1."
    ::= { ikePhase1Entry 7 }

    ikePhase1PreSharedKey	OBJECT-TYPE
	SYNTAX		DisplayString (SIZE (0..63))
	ACCESS		read-write
	STATUS		optional
	DESCRIPTION	"Pre-shared Key for IKE(Internet Key Exchange) phase1."
    ::= { ikePhase1Entry 8 }

    ikePhase2Number	OBJECT-TYPE
	SYNTAX		INTEGER
	ACCESS		read-only
	STATUS		optional
	DESCRIPTION	"The number of www IKE(Internet Key
				Exchange) phase2 entry
				supported by this device."
	::= { ndAdmin 26 }

    ikePhase2Table			OBJECT-TYPE
    SYNTAX          SEQUENCE OF IkePhase2Entry
    ACCESS          not-accessible
    STATUS          optional
    DESCRIPTION     "A list of IKE(Internet Key Exchange) phase2 table."
	::= { ndAdmin 27 }

    ikePhase2Entry		  OBJECT-TYPE
	SYNTAX		  IkePhase2Entry
	ACCESS        not-accessible
	STATUS        optional
	DESCRIPTION   "An entry for IKE(Internet Key Exchange) phase2."
	INDEX		{ ikePhase2Index }
	::= { ikePhase2Table 1 }

    IkePhase2Entry ::=
        SEQUENCE {
	    ikePhase2Index
		INTEGER,
	    ikePhase2Enable
		INTEGER,
	    ikePhase2LocalAddress
		DisplayString,
	    ikePhase2LocalProtocol
		INTEGER,
	    ikePhase2RemoteAddress
		DisplayString,
	    ikePhase2RemotePrefix
		INTEGER,
	    ikePhase2RemoteProtocol
		INTEGER,
	    ikePhase2EncryptionAlgorithm
		INTEGER,
	    ikePhase2HashAlgorithm
		INTEGER,
	    ikePhase2PFSGroup
		INTEGER,
	    ikePhase2LifeTime
		INTEGER
	}

    ikePhase2Index				OBJECT-TYPE
	    SYNTAX          INTEGER
	    ACCESS          read-only
	    STATUS          optional
	    DESCRIPTION     "A unique value for each 
						IKE(Internet Key Exchange) phase2 entry.
						It's value ranges between 1 and the value
						ikePhase2Number."
    ::= { ikePhase2Entry 1 }

    ikePhase2Enable		OBJECT-TYPE
	SYNTAX          INTEGER {
			    enable(1),
			    disable(2)
			}
	ACCESS          read-write
	STATUS          optional
	DESCRIPTION     "Indicates whether the SNMP agent process
			permitted to manage with this ikePhase2Entry."
    ::= { ikePhase2Entry 2 }

    ikePhase2LocalAddress	OBJECT-TYPE
	SYNTAX		DisplayString (SIZE (0..63))
	ACCESS		read-write
	STATUS		optional
	DESCRIPTION	"Local IP(v6) address for IKE(Internet Key Exchange) phase2."
    ::= { ikePhase2Entry 3 }

    ikePhase2LocalProtocol	OBJECT-TYPE
	SYNTAX          INTEGER {
			    any(1),
			    icmp(2),
			    icmpv6(3),
			    ftp(4),
			    telnet(5),
			    smtp(6),
			    http(7),
			    rsh(8),
			    dns(9),
			    ntp(10),
			    snmp(11),
			    snmp-trap(12),
			    tcp(13),
			    udp(14)
			}
	ACCESS          read-write
	STATUS          optional
	DESCRIPTION     "Local IP(v6) address's protocol for 
					IKE(Internet Key Exchange) phase2."
    ::= { ikePhase2Entry 4 }


    ikePhase2RemoteAddress	OBJECT-TYPE
	SYNTAX		DisplayString (SIZE (0..63))
	ACCESS		read-write
	STATUS		optional
	DESCRIPTION	"Remote IP(v6) address for IKE(Internet Key Exchange) phase2."
    ::= { ikePhase2Entry 5 }

    ikePhase2RemotePrefix	OBJECT-TYPE
	SYNTAX          INTEGER (-1..128)
	ACCESS          read-write
	STATUS          optional
	DESCRIPTION     "Remote IP(v6) address's prefix size for
					IKE(Internet Key Exchange) phase2."
    ::= { ikePhase2Entry 6 }

    ikePhase2RemoteProtocol	OBJECT-TYPE
	SYNTAX          INTEGER {
			    any(1),
			    icmp(2),
			    icmpv6(3),
			    ftp(4),
			    telnet(5),
			    smtp(6),
			    http(7),
			    rsh(8),
			    dns(9),
			    ntp(10),
			    snmp(11),
			    snmp-trap(12),
			    tcp(13),
			    udp(14)
			}
	ACCESS          read-write
	STATUS          optional
	DESCRIPTION     "Remote IP(v6) address's protocol for 
					IKE(Internet Key Exchange) phase2."
    ::= { ikePhase2Entry 7 }

    ikePhase2EncryptionAlgorithm	OBJECT-TYPE
	SYNTAX          INTEGER {
			    des(2),
			    triple-des(3),
			    cast128(6),
			    blowfish(7),
			    simple(11),
			    aes(12),
			    twofish(13)
			}
	ACCESS          read-write
	STATUS          optional
	DESCRIPTION     "Encryption Algorithm for 
					IKE(Internet Key Exchange) phase2."
    ::= { ikePhase2Entry 8 }

    ikePhase2HashAlgorithm	OBJECT-TYPE
	SYNTAX          INTEGER {
			    hmac-md5(14),
			    hmac-sha1(15)
			}
	ACCESS          read-write
	STATUS          optional
	DESCRIPTION     "Hash Algorithm for 
					IKE(Internet Key Exchange) phase2."
    ::= { ikePhase2Entry 9 }

    ikePhase2PFSGroup	OBJECT-TYPE
	SYNTAX          INTEGER {
			    none(1),
			    modp768(31),
			    modp1024(32),
			    modp1536(35)
			}
	ACCESS          read-write
	STATUS          optional
	DESCRIPTION     "Perfect Forward Secrecy Group for 
					IKE(Internet Key Exchange) phase2."
    ::= { ikePhase2Entry 10 }

    ikePhase2LifeTime	OBJECT-TYPE
	SYNTAX          INTEGER (1..2147483647)
	ACCESS          read-write
	STATUS          optional
	DESCRIPTION     "Life Time for IKE(Internet Key Exchange) phase2."
    ::= { ikePhase2Entry 11 }

-- The Network Device Top Page set Group (Ver 4.x or Later support)

    adminTopPage	OBJECT IDENTIFIER ::= { ndAdmin 28 }

    topPageName	OBJECT-TYPE
	SYNTAX		DisplayString (SIZE (1..255))
	ACCESS		read-write
	STATUS		optional
	DESCRIPTION	"This string is Top Page Title.
				It can acquire optional name to the ND-EW04."
	::= { adminTopPage 1 }

    topPageMode OBJECT-TYPE
	SYNTAX		INTEGER {
			    reload(1),
			    noreload(2)
			}
	ACCESS		read-write
	STATUS		optional
	DESCRIPTION     "Indicates whether the SNMP agent process
			permitted to manage with this Top Page reload control."
	::= { adminTopPage 2 }

    topPageInterval OBJECT-TYPE
	SYNTAX		INTEGER (5..2147483647)
	ACCESS		read-write
	STATUS		optional
	DESCRIPTION	"Interval number for Top Page reload."
	::= { adminTopPage 3 }

    topPageViewNumber	OBJECT-TYPE
	SYNTAX		INTEGER
	ACCESS		read-only
	STATUS		optional
	DESCRIPTION	"The number of camera view on Top Page."
	::= { adminTopPage 4 }

    topPageViewTable	OBJECT-TYPE
	SYNTAX          SEQUENCE OF TopPageViewEntry
	ACCESS          not-accessible
	STATUS          optional
	DESCRIPTION     "A list of Top Page camera view table."
	::= { adminTopPage 5 }

    topPageViewEntry	OBJECT-TYPE
	SYNTAX		TopPageViewEntry
	ACCESS          not-accessible
	STATUS          optional
	DESCRIPTION	"A top page entry containing objects to describe the
			top page camera view."
	INDEX		{ topPageViewIndex }
	::= { topPageViewTable 1 }

    TopPageViewEntry ::=
        SEQUENCE {
            topPageViewIndex
                INTEGER,
            topPageViewCamera
                INTEGER
	}    

    topPageViewIndex      OBJECT-TYPE
        SYNTAX          INTEGER
        ACCESS          read-only
        STATUS          optional
        DESCRIPTION     "A unique value for each topPageView entry.
                        It's value ranges between 1 and the value
                        topPageViewNumber."
        ::= { topPageViewEntry 1 }

    topPageViewCamera      OBJECT-TYPE
        SYNTAX          INTEGER
        ACCESS          read-write
        STATUS          optional
        DESCRIPTION     "Indicates camera number of image
				display on Top Page."
        ::= { topPageViewEntry 2 }

    topPageCameraControl OBJECT-TYPE
	SYNTAX		INTEGER {
			    enable(1),
			    disable(2)
			}
	ACCESS		read-write
	STATUS		optional
	DESCRIPTION     "Indicates whether camera control is
			permitted to display on Top Page."
	::= { adminTopPage 6 }


-- The Network Device Mpeg Group (Ver 4.x or Later support)

    adminMPEG		OBJECT IDENTIFIER ::= { ndAdmin 29 }

    mpegEnable		OBJECT-TYPE
	SYNTAX		INTEGER {
			    enable(1),
			    disable(2)
                        }
        ACCESS          read-write
        STATUS          optional
	DESCRIPTION     "Indicates whether the MPEG2 stream is
			permitted to mpegEnable future."
	::= { adminMPEG 1 }

    mpegHostAddress	OBJECT-TYPE
	SYNTAX		DisplayString (SIZE (0..63))
	ACCESS		read-write
	STATUS		optional
	DESCRIPTION	"MPEG2 stream send to host."
	::= { adminMPEG 2 }

    mpegHostPort	OBJECT-TYPE
	SYNTAX		INTEGER (1..65535)
	ACCESS		read-write
	STATUS		optional
	DESCRIPTION	"MPEG2 send port."
	::= { adminMPEG 3 }

    mpegMulticastTTL	OBJECT-TYPE
	SYNTAX		INTEGER (1..255)
	ACCESS		read-write
	STATUS		optional
	DESCRIPTION	"Time To Live or hoplimit (only multicast)."
	::= { adminMPEG 4 }

    mpegVideoIn		OBJECT-TYPE
	SYNTAX		INTEGER {
			    ntsc(1),
			    s-video(2)
			}
	ACCESS		read-write
	STATUS		optional
	DESCRIPTION	"Indicates what type of interface for video."
	::= { adminMPEG 5 }

    mpegBitrate		OBJECT-TYPE
	SYNTAX		INTEGER {
			    mpeg-bitrate-3000k(1),
			    mpeg-bitrate-4000k(2),
			    mpeg-bitrate-4500k(3),
			    mpeg-bitrate-6000k(4),
			    mpeg-bitrate-8000k(5)
			}
	ACCESS		read-write
	STATUS		optional
	DESCRIPTION	"Indicates bitrate for MPEG2 stream."
	::= { adminMPEG 6 }

    mpegAudioBitrate	OBJECT-TYPE
	SYNTAX		INTEGER {
			    mpeg-audio-bitrate-384k(1),
			    mpeg-audio-bitrate-256k(2),
			    mpeg-audio-bitrate-192k(3),
			    mpeg-audio-bitrate-128k(4)
			}
	ACCESS		read-write
	STATUS		optional
	DESCRIPTION	"Indicates audio bitrate for MPEG2 stream."
	::= { adminMPEG 7 }

-- The Network Device Admin Camera Bit Group (Ver 4.x or Later support)

    adminCameraBit		OBJECT IDENTIFIER ::= { ndAdmin 30 }

    cameraPanTilt	OBJECT-TYPE
	SYNTAX		INTEGER
	ACCESS		read-only
	STATUS		optional
	DESCRIPTION	"This value is pan tilt function bit."
	::= { adminCameraBit 1 }

    cameraEZoom		OBJECT-TYPE
	SYNTAX		INTEGER
	ACCESS		read-only
	STATUS		optional
	DESCRIPTION	"This value is electric zoom function bit."
	::= { adminCameraBit 2 }

    cameraSmoothMove	OBJECT-TYPE
	SYNTAX		INTEGER
	ACCESS		read-only
	STATUS		optional
	DESCRIPTION	"This value is smooth move function bit."
	::= { adminCameraBit 3 }

    cameraFuncList	OBJECT-TYPE
	SYNTAX		INTEGER
	ACCESS		read-only
	STATUS		optional
	DESCRIPTION	"This value is other function bit."
	::= { adminCameraBit 4 }

    cameraMenu		OBJECT-TYPE
	SYNTAX		INTEGER
	ACCESS		read-only
	STATUS		optional
	DESCRIPTION	"This value is MELOOK-G controller function bit."
	::= { adminCameraBit 5 }

    cameraExposureMode	OBJECT-TYPE
	SYNTAX		INTEGER
	ACCESS		read-only
	STATUS		optional
	DESCRIPTION	"This value is exposure mode bit."
	::= { adminCameraBit 6 }

    cameraExposureA	OBJECT-TYPE
	SYNTAX		INTEGER
	ACCESS		read-only
	STATUS		optional
	DESCRIPTION	"This value is exposure mode A detail bit."
	::= { adminCameraBit 7 }

    cameraExposureB	OBJECT-TYPE
	SYNTAX		INTEGER
	ACCESS		read-only
	STATUS		optional
	DESCRIPTION	"This value is exposure mode B detail bit."
	::= { adminCameraBit 8 }

    cameraAutopanSpd	OBJECT-TYPE
	SYNTAX		INTEGER
	ACCESS		read-only
	STATUS		optional
	DESCRIPTION	"This value is autopan speed bit."
	::= { adminCameraBit 9 }

    cameraAutopanTime	OBJECT-TYPE
	SYNTAX		INTEGER
	ACCESS		read-only
	STATUS		optional
	DESCRIPTION	"This value is autopan time bit."
	::= { adminCameraBit 10 }

    cameraPresettourSpd	OBJECT-TYPE
	SYNTAX		INTEGER
	ACCESS		read-only
	STATUS		optional
	DESCRIPTION	"This value is presettour speed bit."
	::= { adminCameraBit 11 }

    cameraPresettourTime	OBJECT-TYPE
	SYNTAX		INTEGER
	ACCESS		read-only
	STATUS		optional
	DESCRIPTION	"This value is presettour time bit."
	::= { adminCameraBit 12 }

    cameraPresettourNum	OBJECT-TYPE
	SYNTAX		INTEGER
	ACCESS		read-only
	STATUS		optional
	DESCRIPTION	"This value is presettour max number bit."
	::= { adminCameraBit 13 }


-- The Network Device Video Out Group (Ver 4.4 or Later support)

    videoOutNumber	OBJECT-TYPE
	SYNTAX		INTEGER
	ACCESS		read-only
	STATUS		optional
	DESCRIPTION	"The number of video output channel 
				supported by this device."
	::= { ndAdmin 31 }

    videoOutTable	OBJECT-TYPE
	SYNTAX          SEQUENCE OF VideoOutEntry
	ACCESS          not-accessible
	STATUS          optional
	DESCRIPTION     "A list of video output table."
	::= { ndAdmin 32 }

    videoOutEntry	OBJECT-TYPE
	SYNTAX		VideoOutEntry
	ACCESS          not-accessible
	STATUS          optional
	DESCRIPTION	"A video out entry containing objects to
			describe the video output."
	INDEX		{ videoOutIndex }
	::= { videoOutTable 1 }

    VideoOutEntry ::=
        SEQUENCE {
	    videoOutIndex
		INTEGER,
	    videoOutEnable
		INTEGER,
	    videoOutMode
		INTEGER,
	    videoOutLocalCamera
		INTEGER,
	    videoOutRemoteCamera
		INTEGER,
	    videoOutRemoteHost
		DisplayString,
	    videoOutRemotePort
		INTEGER,
	    videoOutRemoteUser
		DisplayString,
	    videoOutRemotePasswd
		DisplayString,
	    videoOutAutoEnable
		INTEGER,
	    videoOutAutoTriggerObjectID
		OBJECT IDENTIFIER,
	    videoOutAutoTriggerEventNo
		INTEGER
	}

    videoOutIndex	OBJECT-TYPE
	    SYNTAX          INTEGER
	    ACCESS          read-only
	    STATUS          optional
	    DESCRIPTION     "A unique value for each video output set entry.
			    It's value ranges between 1 and the value
			    videoOutNumber."
    ::= { videoOutEntry 1 }

    videoOutEnable	OBJECT-TYPE
	    SYNTAX	    INTEGER {
			        enable(1),
			        disable(2)
			    }
	    ACCESS          read-write
	    STATUS          optional
	    DESCRIPTION     "Indicates whether output video to video output."
    ::= { videoOutEntry 2 }

    videoOutMode	OBJECT-TYPE
	    SYNTAX	    INTEGER {
			        local(1),
			        remote(2),
			        colorbar(3)
			    }
	    ACCESS          read-write
	    STATUS          optional
	    DESCRIPTION     "Indicates whether output video from video input 
				or output video from remote server."
    ::= { videoOutEntry 3 }

    videoOutLocalCamera	OBJECT-TYPE
	    SYNTAX	    INTEGER
	    ACCESS	    read-write
	    STATUS	    optional
	    DESCRIPTION     "Camera number of image for video output."
    ::= { videoOutEntry 4 }

    videoOutRemoteCamera OBJECT-TYPE
	   SYNTAX	    INTEGER
	   ACCESS	    read-write
	   STATUS	    optional
	   DESCRIPTION      "Camera number of image for video output
				is requested to the remote server."
    ::= { videoOutEntry 5 }

    videoOutRemoteHost	 OBJECT-TYPE
	    SYNTAX	    DisplayString (SIZE (0..63))
	    ACCESS	    read-write
	    STATUS          optional
	    DESCRIPTION     "The IP address of remote server is requested 
				image to output to video output."
    ::= { videoOutEntry 6 }

    videoOutRemotePort	 OBJECT-TYPE
	   SYNTAX	    INTEGER (1..65535)
	   ACCESS	    read-write
	   STATUS	    optional
	   DESCRIPTION	"The port of remote server is requested image
				to output to video output."
    ::= { videoOutEntry 7 }

    videoOutRemoteUser	 OBJECT-TYPE
	    SYNTAX	    DisplayString (SIZE (0..64))
	    ACCESS	    read-write
	    STATUS          optional
	    DESCRIPTION     "User name is used to request image
				to the remote server."
    ::= { videoOutEntry 8 }

    videoOutRemotePasswd OBJECT-TYPE
	    SYNTAX	    DisplayString (SIZE (0..64))
	    ACCESS	    read-write
	    STATUS          optional
	    DESCRIPTION     "User password is used to request image 
				to the remote server."
    ::= { videoOutEntry 9 }

    videoOutAutoEnable       OBJECT-TYPE
        SYNTAX          INTEGER {
                            enable(1),
                            disable(2)
                        }
        ACCESS          read-write
        STATUS          mandatory
        DESCRIPTION     "Indicates whether auto video output is permitted."
    ::= { videoOutEntry 10 }

    videoOutAutoTriggerObjectID OBJECT-TYPE
        SYNTAX          OBJECT IDENTIFIER
        ACCESS          read-write
        STATUS          mandatory
        DESCRIPTION     "Watched ObjectID for video output to start/stop."
    ::= { videoOutEntry 11 }

    videoOutAutoTriggerEventNo OBJECT-TYPE
        SYNTAX          INTEGER {
                            diValue0(9),
                            diValue1(11)
                        }
        ACCESS          read-write
        STATUS          mandatory
        DESCRIPTION     "A Event trigger for video output.
                        When specific event is occured,
                        output to video output."
    ::= { videoOutEntry 12 }


-- The Network Device Voip Group (Ver 4.4 or Later support)

    voipNumber	OBJECT-TYPE
	SYNTAX		INTEGER
	ACCESS		read-only
	STATUS		optional
	DESCRIPTION	"The number of VoIP entry
				supported by this device."
	::= { ndAdmin 33 }

    voipTable	OBJECT-TYPE
	SYNTAX          SEQUENCE OF VoipEntry
	ACCESS          not-accessible
	STATUS          optional
	DESCRIPTION     "A list of VoIP table."
	::= { ndAdmin 34 }

    voipEntry	OBJECT-TYPE
	SYNTAX		VoipEntry
	ACCESS          not-accessible
	STATUS          optional
	DESCRIPTION	"A VoIP entry containing objects to describe the
			VoIP."
	INDEX		{ voipIndex }
	::= { voipTable 1 }

    VoipEntry ::=
        SEQUENCE {
	    voipIndex
		INTEGER,
	    voipEnable
		INTEGER,
	    voipPeerAddress
		DisplayString,
	    voipPort
		INTEGER,
	    voipCodec
		INTEGER,
	    voipEchoCancel
		INTEGER,
	    voipInputType
		INTEGER,
	    voipAutoEnable
		INTEGER,
	    voipAutoTriggerObjectID
		OBJECT IDENTIFIER,
	    voipAutoTriggerEventNo
		INTEGER,
	    voipOutputType
		INTEGER,
	    voipMicVol
		INTEGER
	}

    voipIndex		OBJECT-TYPE
	    SYNTAX          INTEGER
	    ACCESS          read-only
	    STATUS          optional
	    DESCRIPTION     "A unique value for each VoIP entry.
			    It's value ranges between 1 and the value
			    voipNumber."
    ::= { voipEntry 1 }

    voipEnable		OBJECT-TYPE
	    SYNTAX	    INTEGER {
			        enable(1),
			        disable(2)
			    }
	    ACCESS          read-write
	    STATUS          optional
	    DESCRIPTION     "Indicates whether the SNMP agent process
			permitted to start VoIP."
    ::= { voipEntry 2 }

    voipPeerAddress	OBJECT-TYPE
	    SYNTAX	    DisplayString (SIZE (0..63))
	    ACCESS	    read-write
	    STATUS          optional
	    DESCRIPTION     "The IP address of peer host sent by VoIP."
    ::= { voipEntry 3 }

    voipPort		OBJECT-TYPE
	    SYNTAX          INTEGER (1024..65535)
	    ACCESS          read-write
	    STATUS          optional
	    DESCRIPTION     "The port of host sent by VoIP."
    ::= { voipEntry 4 }

    voipCodec		OBJECT-TYPE
	    SYNTAX	    INTEGER {
			        pcmu(1),
			        pcma(2),
			        g726-32(3)
			    }
	    ACCESS          read-write
	    STATUS          optional
	    DESCRIPTION     "The codec used by VoIP."
    ::= { voipEntry 5 }

    voipEchoCancel	OBJECT-TYPE
	    SYNTAX	    INTEGER {
			        enable(1),
			        disable(2)
			    }
	    ACCESS          read-write
	    STATUS          optional
	    DESCRIPTION     "Indicates whether the Echo Canceler is enabled or not."
    ::= { voipEntry 6 }

    voipInputType	OBJECT-TYPE
        SYNTAX          INTEGER {
                            line(1),
                            mic(2)
                        }
        ACCESS          read-write
        STATUS          mandatory
        DESCRIPTION     "The input device used by VoIP."
    ::= { voipEntry 7 }

    voipAutoEnable       OBJECT-TYPE
        SYNTAX          INTEGER {
                            enable(1),
                            disable(2)
                        }
        ACCESS          read-write
        STATUS          mandatory
        DESCRIPTION     "Indicates whether auto start VoIP is permitted."
    ::= { voipEntry 8 }

    voipAutoTriggerObjectID OBJECT-TYPE
        SYNTAX          OBJECT IDENTIFIER
        ACCESS          read-write
        STATUS          mandatory
        DESCRIPTION     "Watched ObjectID for VoIP to start/stop."
    ::= { voipEntry 9 }

    voipAutoTriggerEventNo OBJECT-TYPE
        SYNTAX          INTEGER {
                            diValue0(9),
                            diValue1(11)
                        }
        ACCESS          read-write
        STATUS          mandatory
        DESCRIPTION     "A Event trigger for VoIP.
                        When specific event is occured,
                        VoIP start."
    ::= { voipEntry 10 }

    voipOutputType	OBJECT-TYPE
        SYNTAX          INTEGER {
                            line(1),
                            speaker(2)
                        }
        ACCESS          read-write
        STATUS          mandatory
        DESCRIPTION     "The output device used by VoIP."
    ::= { voipEntry 11 }

    voipMicVol		OBJECT-TYPE
        SYNTAX          INTEGER
        ACCESS          read-write
        STATUS          mandatory
        DESCRIPTION     "The volume of mic."
    ::= { voipEntry 12 }

-- The Network Device Signaling Group (Ver 4.4 or Later support)

    adminSignaling	OBJECT IDENTIFIER ::= { ndAdmin 35 }

    signalingEnable	OBJECT-TYPE
	SYNTAX		INTEGER {
			    enable(1),
			    disable(2)
			}
	ACCESS		read-write
	STATUS		optional
	DESCRIPTION     "Indicates whether the signaling used."
	::= { adminSignaling 1 }

    signalingMode	OBJECT-TYPE
	SYNTAX		INTEGER {
			    line(1),
			    tel-fix(2),
			    tel-select(3)
			}
	ACCESS		read-write
	STATUS		optional
	DESCRIPTION     "Indicates signaling mode."
	::= { adminSignaling 2 }

    signalingLocalPort	OBJECT-TYPE
	SYNTAX		INTEGER (1..65535)
	ACCESS		read-write
	STATUS		optional
	DESCRIPTION	"Indicates port used by signaling."
	::= { adminSignaling 3 }

    signalingVideo	OBJECT-TYPE
	SYNTAX		INTEGER {
			    enable(1),
			    disable(2)
			}
	ACCESS		read-write
	STATUS		optional
	DESCRIPTION	"Indicates whether start video by signaling."
	::= { adminSignaling 4 }

    signalingLocalCamera OBJECT-TYPE
	SYNTAX		INTEGER
	ACCESS		read-write
	STATUS		optional
	DESCRIPTION	"Indicates which camera's video send by signaling."
	::= { adminSignaling 5 }

    signalingPeerNumber	OBJECT-TYPE
	SYNTAX		INTEGER
	ACCESS		read-only
	STATUS		optional
	DESCRIPTION	"The number of signaling peer entry
				supported by this device."
	::= { adminSignaling 6 }

    signalingPeerTable	OBJECT-TYPE
	SYNTAX          SEQUENCE OF SignalingPeerEntry
	ACCESS          not-accessible
	STATUS          optional
	DESCRIPTION     "A list of Signaling peer table."
	::= { adminSignaling 7 }

    signalingPeerEntry	OBJECT-TYPE
	SYNTAX		SignalingPeerEntry
	ACCESS          not-accessible
	STATUS          optional
	DESCRIPTION	"A signaling peer entry containing objects to describe the
			Signaling."
	INDEX		{ signalingPeerIndex }
	::= { signalingPeerTable 1 }

    SignalingPeerEntry ::=
        SEQUENCE {
	    signalingPeerIndex
		INTEGER,
	    signalingPeerTel
		DisplayString,
	    signalingPeerAddress
		DisplayString,
	    signalingPeerPort
		INTEGER,
	    signalingPeerCamera
		INTEGER
	}

    signalingPeerIndex OBJECT-TYPE
	SYNTAX		INTEGER
	ACCESS		read-only
	STATUS		optional
	DESCRIPTION     "A unique value for each Signaling peer entry.
			It's value ranges between 1 and the value
			signalingPeerNumber."
	::= { signalingPeerEntry 1 }

    signalingPeerTel	OBJECT-TYPE
	SYNTAX	    DisplayString (SIZE (0..2))
	ACCESS	    read-write
	STATUS          optional
	DESCRIPTION     "The tel number starts signaling."
	::= { signalingPeerEntry 2 }

    signalingPeerAddress	OBJECT-TYPE
	SYNTAX	    DisplayString (SIZE (0..63))
	ACCESS	    read-write
	STATUS          optional
	DESCRIPTION     "The IP address of peer host sent by signaling."
	::= { signalingPeerEntry 3 }

    signalingPeerPort OBJECT-TYPE
	SYNTAX		INTEGER
	ACCESS		read-write
	STATUS		optional
	DESCRIPTION     "The port of peer host sent by signaling."
	::= { signalingPeerEntry 4 }

    signalingPeerCamera OBJECT-TYPE
	SYNTAX		INTEGER
	ACCESS		read-write
	STATUS		optional
	DESCRIPTION	"Indicates which camera's video show by signaling."
	::= { signalingPeerEntry 5 }

-- The Network Device Di Forward Group

    adminDiForward	OBJECT IDENTIFIER ::= { ndAdmin 36 }

    diForwardEnable	OBJECT-TYPE
	SYNTAX		INTEGER {
			    enable(1),
			    disable(2)
			}
	ACCESS		read-write
	STATUS		optional
	DESCRIPTION     "Indicates whether the di forwarding used."
	::= { adminDiForward 1 }

    diForwardPollInterval	OBJECT-TYPE
	SYNTAX		INTEGER (0..2147483600)
	ACCESS		read-write
	STATUS		optional
	DESCRIPTION     "Interval of polling to di forwarding."
	::= { adminDiForward 2 }

    diForwardCycleInterval	OBJECT-TYPE
	SYNTAX		INTEGER (0..2147483600)
	ACCESS		read-write
	STATUS		optional
	DESCRIPTION	"Interval of di forwarding cycle."
	::= { adminDiForward 3 }

    diForwardRetryCount  OBJECT-TYPE
	SYNTAX		INTEGER
	ACCESS		read-write
	STATUS		optional
	DESCRIPTION	"The number of times that this device will resend 
                        di forward which set 'retry'."
	::= { adminDiForward 4 }

    diForwardRetryInterval	OBJECT-TYPE
	SYNTAX		INTEGER (0..2147483600)
	ACCESS		read-write
	STATUS		optional
	DESCRIPTION	"Indicates timeout of di forwarding."
	::= { adminDiForward 5 }

    diForwardConfigHost		OBJECT-TYPE
	SYNTAX		INTEGER {
			    simple(1),
			    detail(2)
			}
	ACCESS		read-write
	STATUS		optional
	DESCRIPTION     "The type of host configuration used."
	::= { adminDiForward 6 }

    diForwardAddress	OBJECT-TYPE
	SYNTAX	    DisplayString (SIZE (0..63))
	ACCESS	    read-write
	STATUS          optional
	DESCRIPTION     "The IP address of peer host forwarded."
	::= { adminDiForward 7 }

    diForwardPort	OBJECT-TYPE
	SYNTAX		INTEGER (1..65535)
	ACCESS		read-write
	STATUS		optional
	DESCRIPTION	"Indicates port used by di forwarding."
	::= { adminDiForward 8 }

    diForwardCommunity	OBJECT-TYPE
	SYNTAX		DisplayString (SIZE (1..64))
	ACCESS		read-write
	STATUS		optional
	DESCRIPTION	"The community name to use when forwarding to this
			address."
	::= { adminDiForward 9 }

    diForwardHostNumber	OBJECT-TYPE
	SYNTAX		INTEGER
	ACCESS		read-only
	STATUS		optional
	DESCRIPTION	"The number of di forwarding peer entry
				supported by this device."
	::= { adminDiForward 10 }

    diForwardHostTable	OBJECT-TYPE
	SYNTAX          SEQUENCE OF DiForwardHostEntry
	ACCESS          not-accessible
	STATUS          optional
	DESCRIPTION     "A list of di forwarding peer table."
	::= { adminDiForward 11 }

    diForwardHostEntry	OBJECT-TYPE
	SYNTAX		DiForwardHostEntry
	ACCESS          not-accessible
	STATUS          optional
	DESCRIPTION	"A di forwarding peer entry."
	INDEX		{ diForwardHostIndex }
	::= { diForwardHostTable 1 }

    DiForwardHostEntry ::=
        SEQUENCE {
	    diForwardHostIndex
		INTEGER,
	    diForwardHostEnable
		INTEGER,
	    diForwardHostAddress
		DisplayString,
	    diForwardHostPort
		INTEGER,
	    diForwardHostCommunity
		DisplayString,
	    diForwardHostDoMax
		INTEGER,
	    diForwardHostErrorTrapControl
	    	INTEGER,
	    diForwardHostNormalTrapControl
	    	INTEGER,
	    diForwardHostCancelTrapControl
	    	INTEGER,
	    diForwardHostErrorEmail
	    	INTEGER,
	    diForwardHostNormalEmail
	    	INTEGER,
	    diForwardHostCancelEmail
	    	INTEGER,
	    diForwardHostErrorRemoteCommand
	    	INTEGER,
	    diForwardHostNormalRemoteCommand
	    	INTEGER,
	    diForwardHostCancelRemoteCommand
	    	INTEGER,
	    diForwardHostErrorRemoteCommandSet
	    	INTEGER,
	    diForwardHostNormalRemoteCommandSet
	    	INTEGER,
	    diForwardHostCancelRemoteCommandSet
	    	INTEGER
	}

    diForwardHostIndex OBJECT-TYPE
	SYNTAX		INTEGER
	ACCESS		read-only
	STATUS		optional
	DESCRIPTION     "A unique value for each di forwarding peer entry.
			It's value ranges between 1 and the value
			diForwardHostNumber."
	::= { diForwardHostEntry 1 }

    diForwardHostEnable	OBJECT-TYPE
	SYNTAX		INTEGER {
			    enable(1),
			    disable(2)
			}
	ACCESS	    read-write
	STATUS          optional
	DESCRIPTION     "Indicates whether the di forwarding peer used."
	::= { diForwardHostEntry 2 }

    diForwardHostAddress	OBJECT-TYPE
	SYNTAX	    DisplayString (SIZE (0..63))
	ACCESS	    read-write
	STATUS          optional
	DESCRIPTION     "The IP address of peer host di forwarded."
	::= { diForwardHostEntry 3 }

    diForwardHostPort OBJECT-TYPE
	SYNTAX		INTEGER
	ACCESS		read-write
	STATUS		optional
	DESCRIPTION     "The port of peer host di forwarded."
	::= { diForwardHostEntry 4 }

    diForwardHostCommunity OBJECT-TYPE
	SYNTAX		DisplayString (SIZE (1..64))
	ACCESS		read-write
	STATUS		optional
	DESCRIPTION	"The community name to use when di forwarding to this
                        address."
	::= { diForwardHostEntry 5 }

    diForwardHostDoMax OBJECT-TYPE
	SYNTAX		INTEGER
	ACCESS		read-write
	STATUS		optional
	DESCRIPTION     "The do number of peer host di forwarded."
	::= { diForwardHostEntry 6 }

    diForwardHostErrorTrapControl  OBJECT-TYPE
	SYNTAX		INTEGER {
			    enable(1),
			    disable(2),
			    retry(3)
			}
	ACCESS		read-write
	STATUS		optional
	DESCRIPTION	"Indicates whether the SNMP agent process is
                        permitted to generate diForwardError traps."
	::= { diForwardHostEntry 7 }

    diForwardHostNormalTrapControl  OBJECT-TYPE
	SYNTAX		INTEGER {
			    enable(1),
			    disable(2),
			    retry(3)
			}
	ACCESS		read-write
	STATUS		optional
	DESCRIPTION	"Indicates whether the SNMP agent process is
                        permitted to generate diForwardNormal traps."
	::= { diForwardHostEntry 8 }

    diForwardHostCancelTrapControl  OBJECT-TYPE
	SYNTAX		INTEGER {
			    enable(1),
			    disable(2),
			    retry(3)
			}
	ACCESS		read-write
	STATUS		optional
	DESCRIPTION	"Indicates whether the SNMP agent process is
                        permitted to generate diForwardCancel traps."
	::= { diForwardHostEntry 9 }

    diForwardHostErrorEmail  OBJECT-TYPE
	SYNTAX		INTEGER {
			    enable(1),
			    disable(2)
			}
	ACCESS		read-write
	STATUS		optional
	DESCRIPTION	"Indicates whether the SNMP agent process is
                        permitted to generate diForwardError's mail."
	::= { diForwardHostEntry 10 }

    diForwardHostNormalEmail  OBJECT-TYPE
	SYNTAX		INTEGER {
			    enable(1),
			    disable(2)
			}
	ACCESS		read-write
	STATUS		optional
	DESCRIPTION	"Indicates whether the SNMP agent process is
                        permitted to generate diForwardNormal's mail."
	::= { diForwardHostEntry 11 }

    diForwardHostCancelEmail  OBJECT-TYPE
	SYNTAX		INTEGER {
			    enable(1),
			    disable(2)
			}
	ACCESS		read-write
	STATUS		optional
	DESCRIPTION	"Indicates whether the SNMP agent process is
                        permitted to generate diForwardCancel's mail."
	::= { diForwardHostEntry 12 }

    diForwardHostErrorRemoteCommand  OBJECT-TYPE
	SYNTAX		INTEGER {
			    enable(1),
			    disable(2)
			}
	ACCESS		read-write
	STATUS		optional
	DESCRIPTION	"Indicates whether the SNMP agent process is
                        permitted to generate diForwardError's remote command."
	::= { diForwardHostEntry 13 }

    diForwardHostNormalRemoteCommand  OBJECT-TYPE
	SYNTAX		INTEGER {
			    enable(1),
			    disable(2)
			}
	ACCESS		read-write
	STATUS		optional
	DESCRIPTION	"Indicates whether the SNMP agent process is
                        permitted to generate diForwardNormal's remote command."
	::= { diForwardHostEntry 14 }

    diForwardHostCancelRemoteCommand  OBJECT-TYPE
	SYNTAX		INTEGER {
			    enable(1),
			    disable(2)
			}
	ACCESS		read-write
	STATUS		optional
	DESCRIPTION	"Indicates whether the SNMP agent process is
                        permitted to generate diForwardCancel's remote command."
	::= { diForwardHostEntry 15 }

    diForwardHostErrorRemoteCommandSet  OBJECT-TYPE
	SYNTAX          INTEGER (1..32)
	ACCESS		read-write
	STATUS		optional
	DESCRIPTION	"Indicates diForwardError's remote command set number generated."
	::= { diForwardHostEntry 16 }

    diForwardHostNormalRemoteCommandSet  OBJECT-TYPE
	SYNTAX          INTEGER (1..32)
	ACCESS		read-write
	STATUS		optional
	DESCRIPTION	"Indicates diForwardNormal's remote command set number generated."
	::= { diForwardHostEntry 17 }

    diForwardHostCancelRemoteCommandSet  OBJECT-TYPE
	SYNTAX          INTEGER (1..32)
	ACCESS		read-write
	STATUS		optional
	DESCRIPTION	"Indicates diForwardCancel's remote command set number generated."
	::= { diForwardHostEntry 18 }

    diForwardDoTable	OBJECT-TYPE
	SYNTAX          SEQUENCE OF DiForwardDoEntry
	ACCESS          not-accessible
	STATUS          optional
	DESCRIPTION     "A list of di forward peer do table."
	::= { adminDiForward 12 }

    diForwardDoEntry	OBJECT-TYPE
	SYNTAX		DiForwardDoEntry
	ACCESS          not-accessible
	STATUS          optional
	DESCRIPTION	"A di forward peer do entry."
	INDEX		{ diForwardDoHostIndex, diForwardDoDiIndex }
	::= { diForwardDoTable 1 }

    DiForwardDoEntry ::=
        SEQUENCE {
	    diForwardDoHostIndex
		INTEGER,
	    diForwardDoDiIndex
		INTEGER,
	    diForwardDoChannel
		INTEGER
	}

    diForwardDoHostIndex OBJECT-TYPE
	SYNTAX		INTEGER
	ACCESS		read-only
	STATUS		optional
	DESCRIPTION     "A unique value for each di forwarding peer entry.
			It's value ranges between 1 and the value
			diForwardHostNumber."
	::= { diForwardDoEntry 1 }

    diForwardDoDiIndex	OBJECT-TYPE
	SYNTAX		INTEGER
	ACCESS	    read-only
	STATUS          optional
	DESCRIPTION     "A unique value for each di forwarding di entry.
			It's value ranges between 1 and the value diNumber."
	::= { diForwardDoEntry 2 }

    diForwardDoChannel	OBJECT-TYPE
	SYNTAX		INTEGER
	ACCESS	    read-write
	STATUS          optional
	DESCRIPTION     "The do channel of peer host di forwarded."
	::= { diForwardDoEntry 3 }

    diForwardReceiveNumber	OBJECT-TYPE
	SYNTAX		INTEGER
	ACCESS		read-only
	STATUS		optional
	DESCRIPTION	"The number of receive peer entry
				supported by this device."
	::= { adminDiForward 13 }

    diForwardReceiveTable	OBJECT-TYPE
	SYNTAX          SEQUENCE OF DiForwardReceiveEntry
	ACCESS          not-accessible
	STATUS          optional
	DESCRIPTION     "A list of di forward receive peer table."
	::= { adminDiForward 14 }

    diForwardReceiveEntry	OBJECT-TYPE
	SYNTAX		DiForwardReceiveEntry
	ACCESS          not-accessible
	STATUS          optional
	DESCRIPTION	"A di forward receive peer entry."
	INDEX		{ diForwardReceiveTimeoutIndex }
	::= { diForwardReceiveTable 1 }

    DiForwardReceiveEntry ::=
        SEQUENCE {
    	    diForwardReceiveTimeoutIndex
	    	INTEGER,
    	    diForwardReceiveTimeoutEnable
		INTEGER,
	    diForwardReceiveTimeoutInterval
		INTEGER,
	    diForwardReceiveTimeoutErrorTrapControl
	    	INTEGER,
	    diForwardReceiveTimeoutNormalTrapControl
	    	INTEGER,
	    diForwardReceiveTimeoutErrorEmail
	    	INTEGER,
	    diForwardReceiveTimeoutNormalEmail
	    	INTEGER,
	    diForwardReceiveTimeoutErrorRemoteCommand
	    	INTEGER,
	    diForwardReceiveTimeoutNormalRemoteCommand
	    	INTEGER,
	    diForwardReceiveTimeoutErrorRemoteCommandSet
	    	INTEGER,
	    diForwardReceiveTimeoutNormalRemoteCommandSet
	    	INTEGER
	}

    diForwardReceiveTimeoutIndex OBJECT-TYPE
	SYNTAX		INTEGER
	ACCESS		read-only
	STATUS		optional
	DESCRIPTION     "A unique value for each di forwarding receive peer entry.
			It's value ranges between 1 and the value
			diForwardReceiveNumber."
	::= { diForwardReceiveEntry 1 }

    diForwardReceiveTimeoutEnable	OBJECT-TYPE
	SYNTAX		INTEGER {
			    enable(1),
			    disable(2)
			}
	ACCESS	    read-write
	STATUS          optional
	DESCRIPTION     "Indicates whether the di forwarding receive."
	::= { diForwardReceiveEntry 2 }

    diForwardReceiveTimeoutInterval	OBJECT-TYPE
	SYNTAX		INTEGER (0..2147483600)
	ACCESS		read-write
	STATUS		optional
	DESCRIPTION     "Interval of timeout to di forwarding receive."
	::= { diForwardReceiveEntry 3 }

    diForwardReceiveTimeoutErrorTrapControl  OBJECT-TYPE
	SYNTAX		INTEGER {
			    enable(1),
			    disable(2),
			    retry(3)
			}
	ACCESS		read-write
	STATUS		optional
	DESCRIPTION	"Indicates whether the SNMP agent process is
                        permitted to generate diForwardReceiveTimeout traps."
	::= { diForwardReceiveEntry 4 }

    diForwardReceiveTimeoutNormalTrapControl  OBJECT-TYPE
	SYNTAX		INTEGER {
			    enable(1),
			    disable(2),
			    retry(3)
			}
	ACCESS		read-write
	STATUS		optional
	DESCRIPTION	"Indicates whether the SNMP agent process is
                        permitted to generate diForwardReceiveTimeoutRecover traps."
	::= { diForwardReceiveEntry 5 }

    diForwardReceiveTimeoutErrorEmail  OBJECT-TYPE
	SYNTAX		INTEGER {
			    enable(1),
			    disable(2)
			}
	ACCESS		read-write
	STATUS		optional
	DESCRIPTION	"Indicates whether the SNMP agent process is
                        permitted to generate diForwardReceiveTimeoutError's mail."
	::= { diForwardReceiveEntry 6 }

    diForwardReceiveTimeoutNormalEmail  OBJECT-TYPE
	SYNTAX		INTEGER {
			    enable(1),
			    disable(2)
			}
	ACCESS		read-write
	STATUS		optional
	DESCRIPTION	"Indicates whether the SNMP agent process is
                        permitted to generate diForwardReceiveTimeoutNormal's mail."
	::= { diForwardReceiveEntry 7 }

    diForwardReceiveTimeoutErrorRemoteCommand  OBJECT-TYPE
	SYNTAX		INTEGER {
			    enable(1),
			    disable(2)
			}
	ACCESS		read-write
	STATUS		optional
	DESCRIPTION	"Indicates whether the SNMP agent process is
                        permitted to generate diForwardReceiveTimeoutError's remote command."
	::= { diForwardReceiveEntry 8 }

    diForwardReceiveTimeoutNormalRemoteCommand  OBJECT-TYPE
	SYNTAX		INTEGER {
			    enable(1),
			    disable(2)
			}
	ACCESS		read-write
	STATUS		optional
	DESCRIPTION	"Indicates whether the SNMP agent process is
                        permitted to generate diForwardReceiveTimeoutNormal's remote command."
	::= { diForwardReceiveEntry 9 }

    diForwardReceiveTimeoutErrorRemoteCommandSet  OBJECT-TYPE
	SYNTAX          INTEGER (1..32)
	ACCESS		read-write
	STATUS		optional
	DESCRIPTION	"Indicates whether the SNMP agent process is
                        permitted to generate diForwardReceiveTimeoutError's remote command."
	::= { diForwardReceiveEntry 10 }

    diForwardReceiveTimeoutNormalRemoteCommandSet  OBJECT-TYPE
	SYNTAX          INTEGER (1..32)
	ACCESS		read-write
	STATUS		optional
	DESCRIPTION	"Indicates whether the SNMP agent process is
                        permitted to generate diForwardReceiveTimeoutNormal's remote command."
	::= { diForwardReceiveEntry 11 }

    diForwardSendChangeLog  OBJECT-TYPE
	SYNTAX		INTEGER {
			    enable(1),
			    disable(2)
			}
	ACCESS		read-write
	STATUS		optional
	DESCRIPTION     "Indicates whether the SNMP agent process is
			permitted to di forwarding change logging future."
	::= { adminDiForward 15 }

    diForwardSendCycleLog  OBJECT-TYPE
	SYNTAX		INTEGER {
			    enable(1),
			    disable(2)
			}
	ACCESS		read-write
	STATUS		optional
	DESCRIPTION     "Indicates whether the SNMP agent process is
			permitted to di forwarding cycle logging future."
	::= { adminDiForward 16 }

    diForwardRecvLog  OBJECT-TYPE
	SYNTAX		INTEGER {
			    enable(1),
			    disable(2)
			}
	ACCESS		read-write
	STATUS		optional
	DESCRIPTION     "Indicates whether the SNMP agent process is
			permitted to di forwarding receive logging future."
	::= { adminDiForward 17 }

    diForwardErrorTrapControl  OBJECT-TYPE
	SYNTAX		INTEGER {
			    enable(1),
			    disable(2),
			    retry(3)
			}
	ACCESS		read-write
	STATUS		optional
	DESCRIPTION	"Indicates whether the SNMP agent process is
                        permitted to generate diForwardError traps."
	::= { adminDiForward 18 }

    diForwardNormalTrapControl  OBJECT-TYPE
	SYNTAX		INTEGER {
			    enable(1),
			    disable(2),
			    retry(3)
			}
	ACCESS		read-write
	STATUS		optional
	DESCRIPTION	"Indicates whether the SNMP agent process is
                        permitted to generate diForwardNormal traps."
	::= { adminDiForward 19 }

    diForwardCancelTrapControl  OBJECT-TYPE
	SYNTAX		INTEGER {
			    enable(1),
			    disable(2),
			    retry(3)
			}
	ACCESS		read-write
	STATUS		optional
	DESCRIPTION	"Indicates whether the SNMP agent process is
                        permitted to generate diForwardCancel traps."
	::= { adminDiForward 20 }

    diForwardErrorEmail  OBJECT-TYPE
	SYNTAX		INTEGER {
			    enable(1),
			    disable(2)
			}
	ACCESS		read-write
	STATUS		optional
	DESCRIPTION	"Indicates whether the SNMP agent process is
                        permitted to generate diForwardError's mail."
	::= { adminDiForward 21 }

    diForwardNormalEmail  OBJECT-TYPE
	SYNTAX		INTEGER {
			    enable(1),
			    disable(2)
			}
	ACCESS		read-write
	STATUS		optional
	DESCRIPTION	"Indicates whether the SNMP agent process is
                        permitted to generate diForwardNormal's mail."
	::= { adminDiForward 22 }

    diForwardCancelEmail  OBJECT-TYPE
	SYNTAX		INTEGER {
			    enable(1),
			    disable(2)
			}
	ACCESS		read-write
	STATUS		optional
	DESCRIPTION	"Indicates whether the SNMP agent process is
                        permitted to generate diForwardCancel's mail."
	::= { adminDiForward 23 }

    diForwardErrorRemoteCommand  OBJECT-TYPE
	SYNTAX		INTEGER {
			    enable(1),
			    disable(2)
			}
	ACCESS		read-write
	STATUS		optional
	DESCRIPTION	"Indicates whether the SNMP agent process is
                        permitted to generate diForwardError's remote command."
	::= { adminDiForward 24 }

    diForwardNormalRemoteCommand  OBJECT-TYPE
	SYNTAX		INTEGER {
			    enable(1),
			    disable(2)
			}
	ACCESS		read-write
	STATUS		optional
	DESCRIPTION	"Indicates whether the SNMP agent process is
                        permitted to generate diForwardNormal's remote command."
	::= { adminDiForward 25 }

    diForwardCancelRemoteCommand  OBJECT-TYPE
	SYNTAX		INTEGER {
			    enable(1),
			    disable(2)
			}
	ACCESS		read-write
	STATUS		optional
	DESCRIPTION	"Indicates whether the SNMP agent process is
                        permitted to generate diForwardCancel's remote command."
	::= { adminDiForward 26 }

    diForwardErrorRemoteCommandSet  OBJECT-TYPE
	SYNTAX          INTEGER (1..32)
	ACCESS		read-write
	STATUS		optional
	DESCRIPTION	"Indicates diForwardError's remote command set number generated."
	::= { adminDiForward 27 }

    diForwardNormalRemoteCommandSet  OBJECT-TYPE
	SYNTAX          INTEGER (1..32)
	ACCESS		read-write
	STATUS		optional
	DESCRIPTION	"Indicates diForwardNormal's remote command set number generated."
	::= { adminDiForward 28 }

    diForwardCancelRemoteCommandSet  OBJECT-TYPE
	SYNTAX          INTEGER (1..32)
	ACCESS		read-write
	STATUS		optional
	DESCRIPTION	"Indicates diForwardCancel's remote command set number generated."
	::= { adminDiForward 29 }

    diForwardErrorStatus  OBJECT-TYPE
	SYNTAX          INTEGER {
			    ok(0),
			    tooBig(1),
			    noSuchName(2),
			    badValue(3),
			    wrongType(7),
			    wrongLength(8),
			    wrongValue(10),
			    timeOut(127),
			    cancel(128),
			    hostDown(129),
			    noRoute(130),
			    refused(131),
			    noName(132),
			    otherError(255)
			}
	ACCESS		read-only
	STATUS		optional
	DESCRIPTION	"The error status of di forwarding."
	::= { adminDiForward 30 }

    diForwardErrorHost  OBJECT-TYPE
	SYNTAX		INTEGER
	ACCESS		read-only
	STATUS		optional
	DESCRIPTION	"The error peer of di forwarding."
	::= { adminDiForward 31 }

    diForwardReceiveHost  OBJECT-TYPE
	SYNTAX		DisplayString
	ACCESS		read-only
	STATUS		optional
	DESCRIPTION	"The receive peer of di forwarding."
	::= { adminDiForward 32 }


-- The Network Device Remote File Group (Ver 5.1 or Later support)

    adminRemoteFile	OBJECT IDENTIFIER ::= { ndAdmin 37 }

-- The CIFS items

    cifsNumber		OBJECT-TYPE
	SYNTAX		INTEGER
	ACCESS		read-only
	STATUS		mandatory
	DESCRIPTION	"The number of CIFS entries supported by this device."
	::= { adminRemoteFile 1 }

    cifsTable 		OBJECT-TYPE
	SYNTAX          SEQUENCE OF CifsEntry
	ACCESS          not-accessible
	STATUS          optional
	DESCRIPTION     "A list of CIFS table."
	::= { adminRemoteFile 2 }

    cifsEntry		OBJECT-TYPE
	SYNTAX		CifsEntry
	ACCESS          not-accessible
	STATUS          optional
	DESCRIPTION     "An entry for CIFS settings."
	INDEX		{ cifsIndex }
	::= { cifsTable 1 }

    CifsEntry ::=
        SEQUENCE {
	    cifsIndex
		INTEGER,
	    cifsEnable
		INTEGER,
	    cifsHost
		DisplayString,
	    cifsPort
		INTEGER,
	    cifsWorkgroup
		DisplayString,
	    cifsUserName
		DisplayString,
	    cifsPassword
		DisplayString,
	    cifsRootPath
		DisplayString,
	    cifsKeepAliveSec
		INTEGER,
	    cifsDeleteEnable
		INTEGER,
	    cifsExpireTime
		INTEGER,
	    cifsNormalLogEnable
		INTEGER,
	    cifsErrLogEnable
		INTEGER,
	    cifsRetryCount
		INTEGER,
	    cifsRetryInterval
		INTEGER,
	    cifsTrapConnectionError
		INTEGER,
	    cifsEmailConnectionError
		INTEGER,
	    cifsRemoteConnectionErrorCondition
		INTEGER,
	    cifsRemoteConnectionErrorSet
		INTEGER,
	    cifsTrapAuthenticationError
		INTEGER,
	    cifsEmailAuthenticationError
		INTEGER,
	    cifsRemoteAuthenticationErrorCondition
		INTEGER,
	    cifsRemoteAuthenticationErrorSet
		INTEGER,
	    cifsTrapReadError
		INTEGER,
	    cifsEmailReadError
		INTEGER,
	    cifsRemoteReadErrorCondition
		INTEGER,
	    cifsRemoteReadErrorSet
		INTEGER,
	    cifsTrapWriteError
		INTEGER,
	    cifsEmailWriteError
		INTEGER,
	    cifsRemoteWriteErrorCondition
		INTEGER,
	    cifsRemoteWriteErrorSet
		INTEGER,
	    cifsTrapDiskFull
		INTEGER,
	    cifsEmailDiskFull
		INTEGER,
	    cifsRemoteDiskFullCondition
		INTEGER,
	    cifsRemoteDiskFullSet
		INTEGER,
	    cifsTrapOtherError
		INTEGER,
	    cifsEmailOtherError
		INTEGER,
	    cifsRemoteOtherErrorCondition
		INTEGER,
	    cifsRemoteOtherErrorSet
		INTEGER,
	    cifsSceneID
		DisplayString,
	    cifsErrorCode
		INTEGER,
	    cifsErrorMessage
		DisplayString
	}

    cifsIndex		OBJECT-TYPE
	SYNTAX          INTEGER
	ACCESS          read-only
	STATUS          optional
	DESCRIPTION     "A unique value for each CIFS entry.
			It's value ranges between 1 and the value
			cifsNumber."
	::= { cifsEntry 1 }

    cifsEnable		OBJECT-TYPE
	SYNTAX          INTEGER {
			    enable(1),
			    disable(2)
			}
	ACCESS	        read-write
	STATUS          optional
	DESCRIPTION     "Indicates whether the CIFS will establish connection or not."
	::= { cifsEntry 2 }

    cifsHost		OBJECT-TYPE
	SYNTAX          DisplayString (SIZE (0..63))
	ACCESS	        read-write
	STATUS          optional
	DESCRIPTION     "The host name of CIFS server."
	::= { cifsEntry 3 }

    cifsPort		OBJECT-TYPE
	SYNTAX          INTEGER (1..65535)
	ACCESS          read-write
	STATUS          optional
	DESCRIPTION     "The CIFS port number of the host."
	::= { cifsEntry 4 }

    cifsWorkgroup	OBJECT-TYPE
	SYNTAX	        DisplayString (SIZE (0..127))
	ACCESS	        read-write
	STATUS          optional
	DESCRIPTION     "The WORKGROUP name for CIFS connection."
	::= { cifsEntry 5 }

    cifsUserName	OBJECT-TYPE
	SYNTAX          DisplayString (SIZE (0..63))
	ACCESS          read-write
	STATUS          optional
	DESCRIPTION     "The CIFS username of the host."
	::= { cifsEntry 6 }

    cifsPassword	OBJECT-TYPE
	SYNTAX          DisplayString (SIZE (0..63))
	ACCESS          read-write
	STATUS          optional
	DESCRIPTION     "The CIFS password of the user."
	::= { cifsEntry 7 }

    cifsRootPath	OBJECT-TYPE
	SYNTAX          DisplayString (SIZE (0..127))
	ACCESS          read-write
	STATUS          optional
	DESCRIPTION     "The root path of CIFS directory."
	::= { cifsEntry 8 }

    cifsKeepAliveSec	OBJECT-TYPE
	SYNTAX          INTEGER (0..86400)
	ACCESS	        read-write
	STATUS          optional
	DESCRIPTION     "The keepalive interval seconds.
			 The CIFS client sends packets every interval to keep the CIFS connection."
	::= { cifsEntry 9 }

    cifsDeleteEnable	OBJECT-TYPE
	SYNTAX          INTEGER {
			    enable(1),
			    disable(2)
			}
	ACCESS	        read-write
	STATUS          optional
	DESCRIPTION     "Indicates that disk-full-delete permission."
	::= { cifsEntry 10 }

    cifsExpireTime	OBJECT-TYPE
	SYNTAX          INTEGER (0..23)
	ACCESS	        read-write
	STATUS          optional
	DESCRIPTION     "The scene expiration time."
	::= { cifsEntry 11 }

    cifsNormalLogEnable	OBJECT-TYPE
	SYNTAX          INTEGER {
			    enable(1),
			    disable(2)
			}
	ACCESS	        read-write
	STATUS          optional
	DESCRIPTION	"Indicates whether CIFS normal logging or not."
	::= { cifsEntry 14 }

    cifsErrLogEnable	OBJECT-TYPE
	SYNTAX          INTEGER {
			    enable(1),
			    disable(2)
			}
	ACCESS	        read-write
	STATUS          optional
	DESCRIPTION	"Indicates whether CIFS error logging or not."
	::= { cifsEntry 15 }

    cifsRetryCount	OBJECT-TYPE
	SYNTAX          INTEGER (0..65535)
	ACCESS	        read-write
	STATUS          optional
	DESCRIPTION     "The number of retries for CIFS control command failure."
	::= { cifsEntry 16 }

    cifsRetryInterval	OBJECT-TYPE
	SYNTAX          INTEGER (1..65535)
	ACCESS	        read-write
	STATUS          optional
	DESCRIPTION     "The interval seconds between CIFS control command retries."
	::= { cifsEntry 17 }

    cifsTrapConnectionError	OBJECT-TYPE
	SYNTAX          INTEGER {
			    enable(1),
			    disable(2),
			    retry(3)
			}
	ACCESS	        read-write
	STATUS          optional
	DESCRIPTION	"Indicates the permission to generate 'Connection error' trap."
	::= { cifsEntry 18 }

    cifsEmailConnectionError	OBJECT-TYPE
	SYNTAX          INTEGER {
			    enable(1),
			    disable(2)
			}
	ACCESS	        read-write
	STATUS          optional
	DESCRIPTION	"Indicates the permission to generate 'Connection error' email."
	::= { cifsEntry 19 }

    cifsRemoteConnectionErrorCondition	OBJECT-TYPE
	SYNTAX          INTEGER {
			    enable(1),
			    disable(2)
			}
	ACCESS	        read-write
	STATUS          optional
	DESCRIPTION	"Indicates the permission to generate 'Connection error' remote command."
	::= { cifsEntry 20 }

    cifsRemoteConnectionErrorSet	OBJECT-TYPE
	SYNTAX          INTEGER (1..32)
	ACCESS	        read-write
	STATUS          optional
	DESCRIPTION	"Indicates the set number of 'Connection error' remote command."
	::= { cifsEntry 21 }

    cifsTrapAuthenticationError	OBJECT-TYPE
	SYNTAX          INTEGER {
			    enable(1),
			    disable(2),
			    retry(3)
			}
	ACCESS	        read-write
	STATUS          optional
	DESCRIPTION	"Indicates the permission to generate 'Authentication error' trap."
	::= { cifsEntry 22 }

    cifsEmailAuthenticationError	OBJECT-TYPE
	SYNTAX          INTEGER {
			    enable(1),
			    disable(2)
			}
	ACCESS	        read-write
	STATUS          optional
	DESCRIPTION	"Indicates the permission to generate 'Authentication error' email."
	::= { cifsEntry 23 }

    cifsRemoteAuthenticationErrorCondition	OBJECT-TYPE
	SYNTAX          INTEGER {
			    enable(1),
			    disable(2)
			}
	ACCESS	        read-write
	STATUS          optional
	DESCRIPTION	"Indicates the permission to generate 'Authentication error' remote command."
	::= { cifsEntry 24 }

    cifsRemoteAuthenticationErrorSet	OBJECT-TYPE
	SYNTAX          INTEGER (1..32)
	ACCESS	        read-write
	STATUS          optional
	DESCRIPTION	"Indicates the set number of 'Authentication error' remote command."
	::= { cifsEntry 25 }

    cifsTrapReadError	OBJECT-TYPE
	SYNTAX          INTEGER {
			    enable(1),
			    disable(2),
			    retry(3)
			}
	ACCESS	        read-write
	STATUS          optional
	DESCRIPTION	"Indicates the permission to generate 'Read error' trap."
	::= { cifsEntry 26 }

    cifsEmailReadError	OBJECT-TYPE
	SYNTAX          INTEGER {
			    enable(1),
			    disable(2)
			}
	ACCESS	        read-write
	STATUS          optional
	DESCRIPTION	"Indicates the permission to generate 'Read error' email."
	::= { cifsEntry 27 }

    cifsRemoteReadErrorCondition	OBJECT-TYPE
	SYNTAX          INTEGER {
			    enable(1),
			    disable(2)
			}
	ACCESS	        read-write
	STATUS          optional
	DESCRIPTION	"Indicates the permission to generate 'Read error' remote command."
	::= { cifsEntry 28 }

    cifsRemoteReadErrorSet	OBJECT-TYPE
	SYNTAX          INTEGER (1..32)
	ACCESS	        read-write
	STATUS          optional
	DESCRIPTION	"Indicates the set number of 'Read error' remote command."
	::= { cifsEntry 29 }

    cifsTrapWriteError	OBJECT-TYPE
	SYNTAX          INTEGER {
			    enable(1),
			    disable(2),
			    retry(3)
			}
	ACCESS	        read-write
	STATUS          optional
	DESCRIPTION	"Indicates the permission to generate 'Write error' trap."
	::= { cifsEntry 30 }

    cifsEmailWriteError	OBJECT-TYPE
	SYNTAX          INTEGER {
			    enable(1),
			    disable(2)
			}
	ACCESS	        read-write
	STATUS          optional
	DESCRIPTION	"Indicates the permission to generate 'Write error' email."
	::= { cifsEntry 31 }

    cifsRemoteWriteErrorCondition	OBJECT-TYPE
	SYNTAX          INTEGER {
			    enable(1),
			    disable(2)
			}
	ACCESS	        read-write
	STATUS          optional
	DESCRIPTION	"Indicates the permission to generate 'Write error' remote command."
	::= { cifsEntry 32 }

    cifsRemoteWriteErrorSet	OBJECT-TYPE
	SYNTAX          INTEGER (1..32)
	ACCESS	        read-write
	STATUS          optional
	DESCRIPTION	"Indicates the set number of 'Write error' remote command."
	::= { cifsEntry 33 }

    cifsTrapDiskFull	OBJECT-TYPE
	SYNTAX          INTEGER {
			    enable(1),
			    disable(2),
			    retry(3)
			}
	ACCESS	        read-write
	STATUS          optional
	DESCRIPTION	"Indicates the permission to generate 'Disk Full' trap."
	::= { cifsEntry 34 }

    cifsEmailDiskFull	OBJECT-TYPE
	SYNTAX          INTEGER {
			    enable(1),
			    disable(2)
			}
	ACCESS	        read-write
	STATUS          optional
	DESCRIPTION	"Indicates the permission to generate 'Disk Full' email."
	::= { cifsEntry 35 }

    cifsRemoteDiskFullCondition	OBJECT-TYPE
	SYNTAX          INTEGER {
			    enable(1),
			    disable(2)
			}
	ACCESS	        read-write
	STATUS          optional
	DESCRIPTION	"Indicates the permission to generate 'Disk Full' remote command."
	::= { cifsEntry 36 }

    cifsRemoteDiskFullSet	OBJECT-TYPE
	SYNTAX          INTEGER (1..32)
	ACCESS	        read-write
	STATUS          optional
	DESCRIPTION	"Indicates the set number of 'Disk Full' remote command."
	::= { cifsEntry 37 }

    cifsTrapOtherError	OBJECT-TYPE
	SYNTAX          INTEGER {
			    enable(1),
			    disable(2),
			    retry(3)
			}
	ACCESS	        read-write
	STATUS          optional
	DESCRIPTION	"Indicates the permission to generate 'Other error' trap."
	::= { cifsEntry 38 }

    cifsEmailOtherError	OBJECT-TYPE
	SYNTAX          INTEGER {
			    enable(1),
			    disable(2)
			}
	ACCESS	        read-write
	STATUS          optional
	DESCRIPTION	"Indicates the permission to generate 'Other error' email."
	::= { cifsEntry 39 }

    cifsRemoteOtherErrorCondition	OBJECT-TYPE
	SYNTAX          INTEGER {
			    enable(1),
			    disable(2)
			}
	ACCESS	        read-write
	STATUS          optional
	DESCRIPTION	"Indicates the permission to generate 'Other error' remote command."
	::= { cifsEntry 40 }

    cifsRemoteOtherErrorSet	OBJECT-TYPE
	SYNTAX          INTEGER (1..32)
	ACCESS	        read-write
	STATUS          optional
	DESCRIPTION	"Indicates the set number of 'Other error' remote command."
	::= { cifsEntry 41 }

    cifsSceneID		OBJECT-TYPE
	SYNTAX          DisplayString (SIZE (0..63))
	ACCESS		read-only
	STATUS          optional
	DESCRIPTION	"This string is ID of the newest stored scene by FTP.
			Initial value is NULL string."
	::= { cifsEntry 42 }

    cifsErrorCode	OBJECT-TYPE
	SYNTAX          INTEGER {
				timeout(1),
				fileNotFound(2),
				accessError(4),
				closeError(8),
				readError(16),
				renameError(32),
				writeError(64),
				deleteError(128),
				diskFull(256),
				readConnectionError(512),
				writeConnectionError(1024),
				rwConnectionError(1536),
				internalError(32768),
				connectionEstablished(65536),
				connectionClosed(65537),
				connecting(65538),
				connectFailed(65539),
				authenticationError(65540),
				rootDirectoryNotFound(65541),
				connectionError(65542),
				internalError(65543)
			}
	ACCESS		read-only
	STATUS          optional
	DESCRIPTION	"Error code when CIFS stored scene."
	::= { cifsEntry 43 }

    cifsErrorMessage	OBJECT-TYPE
	SYNTAX          DisplayString (SIZE (0..63))
	ACCESS		read-only
	STATUS          optional
	DESCRIPTION	"Error message when CIFS stored scene."
	::= { cifsEntry 44 }


-- The FTP Client items

    ftpcNumber		OBJECT-TYPE
	SYNTAX		INTEGER
	ACCESS		read-only
	STATUS		mandatory
	DESCRIPTION	"The number of FTP Client (FTPC) connection entries
			 supported by this device."
	::= { adminRemoteFile 3 }

    ftpcTable 		OBJECT-TYPE
	SYNTAX          SEQUENCE OF FtpcEntry
	ACCESS          not-accessible
	STATUS          optional
	DESCRIPTION     "A list of FTPC table."
	::= { adminRemoteFile 4 }

    ftpcEntry		OBJECT-TYPE
	SYNTAX		FtpcEntry
	ACCESS          not-accessible
	STATUS          optional
	DESCRIPTION     "An entry for FTPC."
	INDEX		{ ftpcIndex }
	::= { ftpcTable 1 }

    FtpcEntry ::=
        SEQUENCE {
	    ftpcIndex
		INTEGER,
	    ftpcEnable
		INTEGER,
	    ftpcHost
		DisplayString,
	    ftpcPort
		INTEGER,
	    ftpcOption
		INTEGER,
	    ftpcUserName
		DisplayString,
	    ftpcPassword
		DisplayString,
	    ftpcRootPath
		DisplayString,
	    ftpcKeepAliveSec
		INTEGER,
	    ftpcDeleteEnable
		INTEGER,
	    ftpcExpireTime
		INTEGER,
	    ftpcNormalLogEnable
		INTEGER,
	    ftpcErrLogEnable
		INTEGER,
	    ftpcRetryCount
		INTEGER,
	    ftpcRetryInterval
		INTEGER,
	    ftpcTrapConnectionError
		INTEGER,
	    ftpcEmailConnectionError
		INTEGER,
	    ftpcRemoteConnectionErrorCondition
		INTEGER,
	    ftpcRemoteConnectionErrorSet
		INTEGER,
	    ftpcTrapAuthenticationError
		INTEGER,
	    ftpcEmailAuthenticationError
		INTEGER,
	    ftpcRemoteAuthenticationErrorCondition
		INTEGER,
	    ftpcRemoteAuthenticationErrorSet
		INTEGER,
	    ftpcTrapReadError
		INTEGER,
	    ftpcEmailReadError
		INTEGER,
	    ftpcRemoteReadErrorCondition
		INTEGER,
	    ftpcRemoteReadErrorSet
		INTEGER,
	    ftpcTrapWriteError
		INTEGER,
	    ftpcEmailWriteError
		INTEGER,
	    ftpcRemoteWriteErrorCondition
		INTEGER,
	    ftpcRemoteWriteErrorSet
		INTEGER,
	    ftpcTrapOtherError
		INTEGER,
	    ftpcEmailOtherError
		INTEGER,
	    ftpcRemoteOtherErrorCondition
		INTEGER,
	    ftpcRemoteOtherErrorSet
		INTEGER,
	    ftpcSceneID
		DisplayString,
	    ftpcErrorCode
		INTEGER,
	    ftpcErrorMessage
		DisplayString
	}

    ftpcIndex		OBJECT-TYPE
	SYNTAX          INTEGER
	ACCESS          read-only
	STATUS          optional
	DESCRIPTION     "A unique value for each FTPC entry.
			It's value ranges between 1 and the value
			ftpcNumber."
	::= { ftpcEntry 1 }

    ftpcEnable		OBJECT-TYPE
	SYNTAX          INTEGER {
			    enable(1),
			    disable(2)
			}
	ACCESS	        read-write
	STATUS          optional
	DESCRIPTION     "Indicates whether the FTPC will establish connection or not."
	::= { ftpcEntry 2 }

    ftpcHost		OBJECT-TYPE
	SYNTAX          DisplayString (SIZE (0..63))
	ACCESS	        read-write
	STATUS          optional
	DESCRIPTION     "The host name of FTP server."
	::= { ftpcEntry 3 }

    ftpcPort		OBJECT-TYPE
	SYNTAX          INTEGER (1..65535)
	ACCESS          read-write
	STATUS          optional
	DESCRIPTION     "The FTP port number of the host."
	::= { ftpcEntry 4 }

    ftpcOption		OBJECT-TYPE
	SYNTAX          INTEGER {
			    active(1),
			    passive(2)
			}
	ACCESS	        read-write
	STATUS          optional
	DESCRIPTION     "The FTP data connection mode setting."
	::= { ftpcEntry 5 }

    ftpcUserName	OBJECT-TYPE
	SYNTAX          DisplayString (SIZE (0..63))
	ACCESS          read-write
	STATUS          optional
	DESCRIPTION     "The FTP username of the host."
	::= { ftpcEntry 6 }

    ftpcPassword	OBJECT-TYPE
	SYNTAX          DisplayString (SIZE (0..63))
	ACCESS          read-write
	STATUS          optional
	DESCRIPTION     "The FTP password of the user."
	::= { ftpcEntry 7 }

    ftpcRootPath	OBJECT-TYPE
	SYNTAX          DisplayString (SIZE (0..127))
	ACCESS          read-write
	STATUS          optional
	DESCRIPTION     "The root path of FTP directory."
	::= { ftpcEntry 8 }

    ftpcKeepAliveSec	OBJECT-TYPE
	SYNTAX          INTEGER (0..86400)
	ACCESS	        read-write
	STATUS          optional
	DESCRIPTION     "The keepalive interval seconds.
			 The FTP client sends packets every interval to keep the FTP connection."
	::= { ftpcEntry 9 }

    ftpcDeleteEnable	OBJECT-TYPE
	SYNTAX          INTEGER {
			    enable(1),
			    disable(2)
			}
	ACCESS	        read-write
	STATUS          optional
	DESCRIPTION     "Indicates that disk-full-delete permission."
	::= { ftpcEntry 10 }

    ftpcExpireTime	OBJECT-TYPE
	SYNTAX          INTEGER (0..23)
	ACCESS	        read-write
	STATUS          optional
	DESCRIPTION     "The scene expiration time."
	::= { ftpcEntry 11 }

    ftpcNormalLogEnable	OBJECT-TYPE
	SYNTAX          INTEGER {
			    enable(1),
			    disable(2)
			}
	ACCESS	        read-write
	STATUS          optional
	DESCRIPTION	"Indicates whether FTPC normal logging or not."
	::= { ftpcEntry 14 }

    ftpcErrLogEnable	OBJECT-TYPE
	SYNTAX          INTEGER {
			    enable(1),
			    disable(2)
			}
	ACCESS	        read-write
	STATUS          optional
	DESCRIPTION	"Indicates whether FTPC error logging or not."
	::= { ftpcEntry 15 }

    ftpcRetryCount	OBJECT-TYPE
	SYNTAX          INTEGER (0..65535)
	ACCESS	        read-write
	STATUS          optional
	DESCRIPTION     "The number of retries for FTP control command failure."
	::= { ftpcEntry 16 }

    ftpcRetryInterval	OBJECT-TYPE
	SYNTAX          INTEGER (1..65535)
	ACCESS	        read-write
	STATUS          optional
	DESCRIPTION     "The interval seconds between FTP control command retries."
	::= { ftpcEntry 17 }

    ftpcTrapConnectionError	OBJECT-TYPE
	SYNTAX          INTEGER {
			    enable(1),
			    disable(2),
			    retry(3)
			}
	ACCESS	        read-write
	STATUS          optional
	DESCRIPTION	"Indicates the permission to generate 'Connection error' trap."
	::= { ftpcEntry 18 }

    ftpcEmailConnectionError	OBJECT-TYPE
	SYNTAX          INTEGER {
			    enable(1),
			    disable(2)
			}
	ACCESS	        read-write
	STATUS          optional
	DESCRIPTION	"Indicates the permission to generate 'Connection error' email."
	::= { ftpcEntry 19 }

    ftpcRemoteConnectionErrorCondition	OBJECT-TYPE
	SYNTAX          INTEGER {
			    enable(1),
			    disable(2)
			}
	ACCESS	        read-write
	STATUS          optional
	DESCRIPTION	"Indicates the permission to generate 'Connection error' remote command."
	::= { ftpcEntry 20 }

    ftpcRemoteConnectionErrorSet	OBJECT-TYPE
	SYNTAX          INTEGER (1..32)
	ACCESS	        read-write
	STATUS          optional
	DESCRIPTION	"Indicates the set number of 'Connection error' remote command."
	::= { ftpcEntry 21 }

    ftpcTrapAuthenticationError	OBJECT-TYPE
	SYNTAX          INTEGER {
			    enable(1),
			    disable(2),
			    retry(3)
			}
	ACCESS	        read-write
	STATUS          optional
	DESCRIPTION	"Indicates the permission to generate 'Authentication error' trap."
	::= { ftpcEntry 22 }

    ftpcEmailAuthenticationError	OBJECT-TYPE
	SYNTAX          INTEGER {
			    enable(1),
			    disable(2)
			}
	ACCESS	        read-write
	STATUS          optional
	DESCRIPTION	"Indicates the permission to generate 'Authentication error' email."
	::= { ftpcEntry 23 }

    ftpcRemoteAuthenticationErrorCondition	OBJECT-TYPE
	SYNTAX          INTEGER {
			    enable(1),
			    disable(2)
			}
	ACCESS	        read-write
	STATUS          optional
	DESCRIPTION	"Indicates the permission to generate 'Authentication error' remote command."
	::= { ftpcEntry 24 }

    ftpcRemoteAuthenticationErrorSet	OBJECT-TYPE
	SYNTAX          INTEGER (1..32)
	ACCESS	        read-write
	STATUS          optional
	DESCRIPTION	"Indicates the set number of 'Authentication error' remote command."
	::= { ftpcEntry 25 }

    ftpcTrapReadError	OBJECT-TYPE
	SYNTAX          INTEGER {
			    enable(1),
			    disable(2),
			    retry(3)
			}
	ACCESS	        read-write
	STATUS          optional
	DESCRIPTION	"Indicates the permission to generate 'Read error' trap."
	::= { ftpcEntry 26 }

    ftpcEmailReadError	OBJECT-TYPE
	SYNTAX          INTEGER {
			    enable(1),
			    disable(2)
			}
	ACCESS	        read-write
	STATUS          optional
	DESCRIPTION	"Indicates the permission to generate 'Read error' email."
	::= { ftpcEntry 27 }

    ftpcRemoteReadErrorCondition	OBJECT-TYPE
	SYNTAX          INTEGER {
			    enable(1),
			    disable(2)
			}
	ACCESS	        read-write
	STATUS          optional
	DESCRIPTION	"Indicates the permission to generate 'Read error' remote command."
	::= { ftpcEntry 28 }

    ftpcRemoteReadErrorSet	OBJECT-TYPE
	SYNTAX          INTEGER (1..32)
	ACCESS	        read-write
	STATUS          optional
	DESCRIPTION	"Indicates the set number of 'Read error' remote command."
	::= { ftpcEntry 29 }

    ftpcTrapWriteError	OBJECT-TYPE
	SYNTAX          INTEGER {
			    enable(1),
			    disable(2),
			    retry(3)
			}
	ACCESS	        read-write
	STATUS          optional
	DESCRIPTION	"Indicates the permission to generate 'Write error' trap."
	::= { ftpcEntry 30 }

    ftpcEmailWriteError	OBJECT-TYPE
	SYNTAX          INTEGER {
			    enable(1),
			    disable(2)
			}
	ACCESS	        read-write
	STATUS          optional
	DESCRIPTION	"Indicates the permission to generate 'Write error' email."
	::= { ftpcEntry 31 }

    ftpcRemoteWriteErrorCondition	OBJECT-TYPE
	SYNTAX          INTEGER {
			    enable(1),
			    disable(2)
			}
	ACCESS	        read-write
	STATUS          optional
	DESCRIPTION	"Indicates the permission to generate 'Write error' remote command."
	::= { ftpcEntry 32 }

    ftpcRemoteWriteErrorSet	OBJECT-TYPE
	SYNTAX          INTEGER (1..32)
	ACCESS	        read-write
	STATUS          optional
	DESCRIPTION	"Indicates the set number of 'Write error' remote command."
	::= { ftpcEntry 33 }

    ftpcTrapOtherError	OBJECT-TYPE
	SYNTAX          INTEGER {
			    enable(1),
			    disable(2),
			    retry(3)
			}
	ACCESS	        read-write
	STATUS          optional
	DESCRIPTION	"Indicates the permission to generate 'Other error' trap."
	::= { ftpcEntry 34 }

    ftpcEmailOtherError	OBJECT-TYPE
	SYNTAX          INTEGER {
			    enable(1),
			    disable(2)
			}
	ACCESS	        read-write
	STATUS          optional
	DESCRIPTION	"Indicates the permission to generate 'Other error' email."
	::= { ftpcEntry 35 }

    ftpcRemoteOtherErrorCondition	OBJECT-TYPE
	SYNTAX          INTEGER {
			    enable(1),
			    disable(2)
			}
	ACCESS	        read-write
	STATUS          optional
	DESCRIPTION	"Indicates the permission to generate 'Other error' remote command."
	::= { ftpcEntry 36 }

    ftpcRemoteOtherErrorSet	OBJECT-TYPE
	SYNTAX          INTEGER (1..32)
	ACCESS	        read-write
	STATUS          optional
	DESCRIPTION	"Indicates the set number of 'Other error' remote command."
	::= { ftpcEntry 37 }

    ftpcSceneID		OBJECT-TYPE
	SYNTAX          DisplayString (SIZE (0..63))
	ACCESS		read-only
	STATUS          optional
	DESCRIPTION	"This string is ID of the newest stored scene by FTP.
			Initial value is NULL string."
	::= { ftpcEntry 38 }

    ftpcErrorCode	OBJECT-TYPE
	SYNTAX          INTEGER {
				timeout(1),
				fileNotFound(2),
				accessError(4),
				closeError(8),
				readError(16),
				renameError(32),
				writeError(64),
				deleteError(128),
				diskFull(256),
				readConnectionError(512),
				writeConnectionError(1024),
				rwConnectionError(1536),
				internalError(32768),
				connectionEstablished(65536),
				connectionClosed(65537),
				connecting(65538),
				connectFailed(65539),
				authenticationError(65540),
				rootDirectoryNotFound(65541),
				connectionError(65542),
				internalError(65543)
			}
	ACCESS		read-only
	STATUS          optional
	DESCRIPTION	"Error code when FTP stored scene."
	::= { ftpcEntry 39 }

    ftpcErrorMessage	OBJECT-TYPE
	SYNTAX          DisplayString (SIZE (0..63))
	ACCESS		read-only
	STATUS          optional
	DESCRIPTION	"Error message when FTP stored scene."
	::= { ftpcEntry 40 }

-- The CIFS expire entry

    cifsExpireNumber	OBJECT-TYPE
	SYNTAX		INTEGER
	ACCESS		read-only
	STATUS		mandatory
	DESCRIPTION	"The number of CIFS Expire entries supported by this device."
	::= { adminRemoteFile 5 }

    cifsExpireTable	OBJECT-TYPE
	SYNTAX          SEQUENCE OF CifsExpireEntry
	ACCESS          not-accessible
	STATUS          optional
	DESCRIPTION     "A list of cifs expire table."
	::= { adminRemoteFile 6 }

    cifsExpireEntry	OBJECT-TYPE
	SYNTAX		CifsExpireEntry
	ACCESS          not-accessible
	STATUS          optional
	DESCRIPTION	"A cifs expire entry."
	INDEX		{ cifsExpireIndex, cifsExpireCamera }
	::= { cifsExpireTable 1 }

    CifsExpireEntry ::=
	SEQUENCE {
	    cifsExpireIndex
		INTEGER,
	    cifsExpireCamera
		INTEGER,
	    cifsTimerTriggerExpireEnable
		INTEGER,
	    cifsTimerTriggerExpireLife
		INTEGER,
	    cifsDiTriggerExpireEnable
		INTEGER,
	    cifsDiTriggerExpireLife
		INTEGER,
	    cifsMultiMotionDetectTriggerExpireEnable
		INTEGER,
	    cifsMultiMotionDetectTriggerExpireLife
		INTEGER,
	    cifsMultiManualTriggerExpireEnable
		INTEGER,
	    cifsMultiManualTriggerExpireLife
		INTEGER
	}

    cifsExpireIndex	OBJECT-TYPE
	SYNTAX		INTEGER
	ACCESS		read-only
	STATUS		optional
	DESCRIPTION     "A unique value for trigger type entry.
			It's value ranges between 1 and the value
			cifsExpireNumber."
	::= { cifsExpireEntry 1 }

    cifsExpireCamera	OBJECT-TYPE
	SYNTAX		INTEGER
	ACCESS		read-only
	STATUS		optional
	DESCRIPTION     "A unique value for camera number entry.
			It's value ranges between 1 and the value
			cameraNumber."
	::= { cifsExpireEntry 2 }

    cifsTimerTriggerExpireEnable	OBJECT-TYPE
	SYNTAX		INTEGER {
			    enable(1),
			    disable(2)
			}
	ACCESS		read-write
	STATUS		optional
	DESCRIPTION     "Indicates whether this device to delete oldest
			scene by timer trigger."
	::= { cifsExpireEntry 3 }

    cifsTimerTriggerExpireLife	OBJECT-TYPE
	SYNTAX		INTEGER (0..36525)
	ACCESS		read-write
	STATUS		optional
	DESCRIPTION     "Indicates saved time of timer trigger."
	::= { cifsExpireEntry 4 }

    cifsDiTriggerExpireEnable	OBJECT-TYPE
	SYNTAX		INTEGER {
			    enable(1),
			    disable(2)
			}
	ACCESS		read-write
	STATUS		optional
	DESCRIPTION     "Indicates whether this device to delete oldest
			scene by di trigger."
	::= { cifsExpireEntry 5 }

    cifsDiTriggerExpireLife	OBJECT-TYPE
	SYNTAX		INTEGER (0..36525)
	ACCESS		read-write
	STATUS		optional
	DESCRIPTION     "Indicates saved time of di trigger."
	::= { cifsExpireEntry 6 }

    cifsMultiMotionDetectTriggerExpireEnable	OBJECT-TYPE
	SYNTAX		INTEGER {
			    enable(1),
			    disable(2)
			}
	ACCESS		read-write
	STATUS		optional
	DESCRIPTION     "Indicates whether this device to delete oldest
			scene by motion detect trigger."
	::= { cifsExpireEntry 7 }

    cifsMultiMotionDetectTriggerExpireLife	OBJECT-TYPE
	SYNTAX		INTEGER (0..36525)
	ACCESS		read-write
	STATUS		optional
	DESCRIPTION     "Indicates saved time of motion detect trigger."
	::= { cifsExpireEntry 8 }

    cifsMultiManualTriggerExpireEnable	OBJECT-TYPE
	SYNTAX		INTEGER {
			    enable(1),
			    disable(2)
			}
	ACCESS		read-write
	STATUS		optional
	DESCRIPTION     "Indicates whether this device to delete oldest
			scene by manual trigger."
	::= { cifsExpireEntry 9 }

    cifsMultiManualTriggerExpireLife	OBJECT-TYPE
	SYNTAX		INTEGER (0..36525)
	ACCESS		read-write
	STATUS		optional
	DESCRIPTION     "Indicates saved time of manual trigger."
	::= { cifsExpireEntry 10 }

-- The FTP Client expire entry

    ftpcExpireNumber	OBJECT-TYPE
	SYNTAX		INTEGER
	ACCESS		read-only
	STATUS		mandatory
	DESCRIPTION	"The number of FTP Client Expire entries supported by this device."
	::= { adminRemoteFile 7 }

    ftpcExpireTable	OBJECT-TYPE
	SYNTAX          SEQUENCE OF FtpcExpireEntry
	ACCESS          not-accessible
	STATUS          optional
	DESCRIPTION     "A list of ftp client expire table."
	::= { adminRemoteFile 8 }

    ftpcExpireEntry	OBJECT-TYPE
	SYNTAX		FtpcExpireEntry
	ACCESS          not-accessible
	STATUS          optional
	DESCRIPTION	"A ftp client expire entry."
	INDEX		{ ftpcExpireIndex, ftpcExpireCamera }
	::= { ftpcExpireTable 1 }

    FtpcExpireEntry ::=
	SEQUENCE {
	    ftpcExpireIndex
		INTEGER,
	    ftpcExpireCamera
		INTEGER,
	    ftpcTimerTriggerExpireEnable
		INTEGER,
	    ftpcTimerTriggerExpireLife
		INTEGER,
	    ftpcDiTriggerExpireEnable
		INTEGER,
	    ftpcDiTriggerExpireLife
		INTEGER,
	    ftpcMultiMotionDetectTriggerExpireEnable
		INTEGER,
	    ftpcMultiMotionDetectTriggerExpireLife
		INTEGER,
	    ftpcMultiManualTriggerExpireEnable
		INTEGER,
	    ftpcMultiManualTriggerExpireLife
		INTEGER
	}

    ftpcExpireIndex	OBJECT-TYPE
	SYNTAX		INTEGER
	ACCESS		read-only
	STATUS		optional
	DESCRIPTION     "A unique value for trigger type entry.
			It's value ranges between 1 and the value
			ftpcExpireNumber."
	::= { ftpcExpireEntry 1 }

    ftpcExpireCamera	OBJECT-TYPE
	SYNTAX		INTEGER
	ACCESS		read-only
	STATUS		optional
	DESCRIPTION     "A unique value for camera number entry.
			It's value ranges between 1 and the value
			cameraNumber."
	::= { ftpcExpireEntry 2 }

    ftpcTimerTriggerExpireEnable	OBJECT-TYPE
	SYNTAX		INTEGER {
			    enable(1),
			    disable(2)
			}
	ACCESS		read-write
	STATUS		optional
	DESCRIPTION     "Indicates whether this device to delete oldest
			scene by timer trigger."
	::= { ftpcExpireEntry 3 }

    ftpcTimerTriggerExpireLife	OBJECT-TYPE
	SYNTAX		INTEGER (0..36525)
	ACCESS		read-write
	STATUS		optional
	DESCRIPTION     "Indicates saved time of timer trigger."
	::= { ftpcExpireEntry 4 }

    ftpcDiTriggerExpireEnable	OBJECT-TYPE
	SYNTAX		INTEGER {
			    enable(1),
			    disable(2)
			}
	ACCESS		read-write
	STATUS		optional
	DESCRIPTION     "Indicates whether this device to delete oldest
			scene by di trigger."
	::= { ftpcExpireEntry 5 }

    ftpcDiTriggerExpireLife	OBJECT-TYPE
	SYNTAX		INTEGER (0..36525)
	ACCESS		read-write
	STATUS		optional
	DESCRIPTION     "Indicates saved time of di trigger."
	::= { ftpcExpireEntry 6 }

    ftpcMultiMotionDetectTriggerExpireEnable	OBJECT-TYPE
	SYNTAX		INTEGER {
			    enable(1),
			    disable(2)
			}
	ACCESS		read-write
	STATUS		optional
	DESCRIPTION     "Indicates whether this device to delete oldest
			scene by motion detect trigger."
	::= { ftpcExpireEntry 7 }

    ftpcMultiMotionDetectTriggerExpireLife	OBJECT-TYPE
	SYNTAX		INTEGER (0..36525)
	ACCESS		read-write
	STATUS		optional
	DESCRIPTION     "Indicates saved time of motion detect trigger."
	::= { ftpcExpireEntry 8 }

    ftpcMultiManualTriggerExpireEnable	OBJECT-TYPE
	SYNTAX		INTEGER {
			    enable(1),
			    disable(2)
			}
	ACCESS		read-write
	STATUS		optional
	DESCRIPTION     "Indicates whether this device to delete oldest
			scene by manual trigger."
	::= { ftpcExpireEntry 9 }

    ftpcMultiManualTriggerExpireLife	OBJECT-TYPE
	SYNTAX		INTEGER (0..36525)
	ACCESS		read-write
	STATUS		optional
	DESCRIPTION     "Indicates saved time of manual trigger."
	::= { ftpcExpireEntry 10 }

-- The I/O Group

    ndIO	OBJECT IDENTIFIER ::= { ndMgmt 2 }

-- CEC network-device A/D management group
--
-- This group contains the MIB variables used to determine the
-- number of A/D channels supported by the device and status of 
-- A/D channels.

    adNumber		OBJECT-TYPE
	SYNTAX		INTEGER
	ACCESS		read-only
	STATUS		mandatory
	DESCRIPTION	"The number of A/D channels supported by this device."
	::= { ndIO 1 }

-- The A/D table
--
-- This table contains adNumber entries describing each A/D channels
--

    adTable		OBJECT-TYPE
	SYNTAX		SEQUENCE OF AdEntry
	ACCESS		not-accessible
	STATUS		mandatory
	DESCRIPTION	"A list of A/D channel entries. The number of entries
			is given by the value adNumber."
	::= { ndIO 2 }

    adEntry		OBJECT-TYPE
	SYNTAX		AdEntry
	ACCESS		not-accessible
	STATUS		mandatory
	DESCRIPTION	"A A/D channel entry containing objects to describe the
			A/D channel."
	INDEX		{ adIndex }
	::= { adTable 1 }

    AdEntry ::=
	SEQUENCE {
	    adIndex
		INTEGER,
	    adType
		DisplayString,
	    adValue
		INTEGER,
	    adValueScale
		INTEGER,
	    adValueOffset
		INTEGER,
	    adLogInterval
		INTEGER,
	    adEventPollInterval
		INTEGER,
	    adEventUpperThreshold
		INTEGER,
	    adEventUpperHysteresis
		INTEGER,
	    adEventLowerThreshold
		INTEGER,
	    adEventLowerHysteresis
		INTEGER,

	    adTrapPollInterval
		INTEGER,
	    adTrapUpperThreshold
		INTEGER,
	    adTrapUpperHysteresis
		INTEGER,
	    adTrapLowerThreshold
		INTEGER,
	    adTrapLowerHysteresis
		INTEGER,
	    adEnableExUpThresholdIncreaseTrap
		INTEGER,
	    adEnableExUpThresholdDecreaseTrap
		INTEGER,
	    adEnableExUpThresholdTrap
		INTEGER,
	    adEnableExLoThresholdIncreaseTrap
		INTEGER,
	    adEnableExLoThresholdDecreaseTrap
		INTEGER,
	    adEnableExLoThresholdTrap
		INTEGER,
	    adAlertCondition
		INTEGER,
	    adRange
		INTEGER,
	    adEmailPollInterval
		INTEGER,
	    adEmailUpperThreshold
		INTEGER,
	    adEmailUpperHysteresis
		INTEGER,
	    adEmailLowerThreshold
		INTEGER,
	    adEmailLowerHysteresis
		INTEGER,
	    adEnableExUpThresholdIncreaseEmail
		INTEGER,
	    adEnableExUpThresholdDecreaseEmail
		INTEGER,
	    adEnableExUpThresholdEmail
		INTEGER,
	    adEnableExLoThresholdIncreaseEmail
		INTEGER,
	    adEnableExLoThresholdDecreaseEmail
		INTEGER,
	    adEnableExLoThresholdEmail
		INTEGER,
	    adExUpThresholdIncreaseTrapID
		INTEGER,
	    adExUpThresholdDecreaseTrapID
		INTEGER,
	    adExUpThresholdTrapID
		INTEGER,
	    adExLoThresholdIncreaseTrapID
		INTEGER,
	    adExLoThresholdDecreaseTrapID
		INTEGER,
	    adExLoThresholdTrapID
		INTEGER,

	    adRemoteCommandPollInterval
		INTEGER,
	    adRemoteCommandUpperThreshold
		INTEGER,
	    adRemoteCommandUpperHysteresis
		INTEGER,
	    adRemoteCommandLowerThreshold
		INTEGER,
	    adRemoteCommandLowerHysteresis
		INTEGER,
	    adEnableExUpThresholdIncreaseRemoteCommand
		INTEGER,
	    adEnableExUpThresholdDecreaseRemoteCommand
		INTEGER,
	    adEnableExUpThresholdRemoteCommand
		INTEGER,
	    adEnableExLoThresholdIncreaseRemoteCommand
		INTEGER,
	    adEnableExLoThresholdDecreaseRemoteCommand
		INTEGER,
	    adEnableExLoThresholdRemoteCommand
		INTEGER,
	    adEnableExUpThresholdIncreaseRemoteCommandSet
		INTEGER,
	    adEnableExUpThresholdDecreaseRemoteCommandSet
		INTEGER,
	    adEnableExUpThresholdRemoteCommandSet
		INTEGER,
	    adEnableExLoThresholdIncreaseRemoteCommandSet
		INTEGER,
	    adEnableExLoThresholdDecreaseRemoteCommandSet
		INTEGER,
	    adEnableExLoThresholdRemoteCommandSet
		INTEGER,

	    adValueString
		DisplayString,
	    adValueStringUnit
		DisplayString,
	    adValueStringAccurate
		INTEGER,
	    adValueStringExponent
		INTEGER,
	    adValueStringFilterTap
		INTEGER,

	    adSensorID
		INTEGER,

	    adMemo
		DisplayString,

	    adUpperString
		DisplayString,
	    adLowerString
		DisplayString,
	    adNormalString
		DisplayString,

	    adValue0Threshold
		INTEGER,

	    adValueStatisticsMin
		INTEGER,
	    adValueStatisticsMax
		INTEGER,
	    adValueOnlyString
		DisplayString,

	    adNotConnectedString
		DisplayString,

	    adConnectionStatus
		INTEGER,
	    adEventCurrentStatus
		INTEGER,
	    adTrapCurrentStatus
		INTEGER,
	    adEmailCurrentStatus
		INTEGER,
	    adRemoteCurrentStatus
		INTEGER,
	    adEventCurrentStatusString
		DisplayString,
	    adTrapCurrentStatusString
		DisplayString,
	    adEmailCurrentStatusString
		DisplayString,
	    adRemoteCurrentStatusString
		DisplayString
	}

    adIndex		OBJECT-TYPE
	SYNTAX		INTEGER
	ACCESS		read-only
	STATUS		mandatory
	DESCRIPTION	"A unique value for each A/D channel. It's value ranges
			between 1 and the value adNumber."
	::= { adEntry 1 }

    adType		OBJECT-TYPE
	SYNTAX		DisplayString (SIZE (1..32))
	ACCESS		read-write
	STATUS		mandatory
	DESCRIPTION	"The text string is type of A/D value."
	::= { adEntry 2 }

    adValue		OBJECT-TYPE
	SYNTAX		INTEGER
	ACCESS		read-only
	STATUS		mandatory
	DESCRIPTION	"The value of A/D channel is multiplied by adValueScale
			and adValueOffset. namely,
			adValue =
			 (value of A/D channel) * adValueScale + adValueOffset."
	::= { adEntry 3 }

    adValueScale	OBJECT-TYPE
	SYNTAX		INTEGER
	ACCESS		read-write
	STATUS		mandatory
	DESCRIPTION	"This value is coefficient of scale for adValue."
	::= { adEntry 4 }

    adValueOffset	OBJECT-TYPE
	SYNTAX		INTEGER
	ACCESS		read-write
	STATUS		mandatory
	DESCRIPTION	"This value is offset for adValue."
	::= { adEntry 5 }

    adLogInterval	OBJECT-TYPE
	SYNTAX		INTEGER (0..2147483600)
	ACCESS		read-write
	STATUS		mandatory
	DESCRIPTION	"The interval in milliseconds to log for the
			value of A/D channel. This value can be set on
			every 50ms. A fraction is raised and set."
	::= { adEntry 6 }

    adEventPollInterval	OBJECT-TYPE
	SYNTAX		INTEGER (0..2147483600)
	ACCESS		read-write
	STATUS		mandatory
	DESCRIPTION	"The interval in milliseconds to poll the value
			of A/D channel for Event. This value can be set on
			every 50ms. A fraction is raised and set."
	::= { adEntry 7 }

    adEventUpperThreshold OBJECT-TYPE
	SYNTAX		INTEGER
	ACCESS		read-write
	STATUS		mandatory
	DESCRIPTION	"A Event trigger for upper limit A/D value.
			If adValue is greater than this value then generate
			adExceedUpperThresholdIncrease event."
	::= { adEntry 8 }

    adEventUpperHysteresis OBJECT-TYPE
	SYNTAX		INTEGER
	ACCESS		read-write
	STATUS		mandatory
	DESCRIPTION	"A Event trigger for adEventUpperThreshold offset.
			If adValue is less equal adEventUpperThreshold minus
			this value after adExceedUpperThresholdIncrease event
			is generated, then generate 
			adExceedUpperThresholdDecrease event."
	::= { adEntry 9 }

    adEventLowerThreshold OBJECT-TYPE
	SYNTAX		INTEGER
	ACCESS		read-write
	STATUS		mandatory
	DESCRIPTION	"A Event trigger for lower limit A/D value.
			If adValue is less than this value then generate
			adExceedLowerThresholdDecrease event."
	::= { adEntry 10 }

    adEventLowerHysteresis OBJECT-TYPE
	SYNTAX		INTEGER
	ACCESS		read-write
	STATUS		mandatory
	DESCRIPTION	"A Event trigger for adEventLowerThreshold offset.
			If adValue is greater equal adEventLowerThreshold minus
			this value after adExceedLowerThresholdDecrease event
			is generated, then generate 
			adExceedLowerThresholdIncrease event."
	::= { adEntry 11 }

    adTrapPollInterval	OBJECT-TYPE
	SYNTAX		INTEGER (0..2147483600)
	ACCESS		read-write
	STATUS		mandatory
	DESCRIPTION	"The interval in milliseconds to poll the value
			of A/D channel for Trap. This value can be set on
			every 50ms. A fraction is raised and set."
	::= { adEntry 12 }

    adTrapUpperThreshold OBJECT-TYPE
	SYNTAX		INTEGER
	ACCESS		read-write
	STATUS		mandatory
	DESCRIPTION	"A trap trigger for upper limit A/D value.
			If adValue is greater than this value then generate
			adExceedUpperThresholdIncrease trap."
	::= { adEntry 13 }

    adTrapUpperHysteresis OBJECT-TYPE
	SYNTAX		INTEGER
	ACCESS		read-write
	STATUS		mandatory
	DESCRIPTION	"A Trap trigger for adEventUpperThreshold offset.
			If adValue is less equal adEventUpperThreshold minus
			this value after adExceedUpperThresholdIncrease trap
			is generated, then generate
			adExceedUpperThresholdDecrease trap."
	::= { adEntry 14 }

    adTrapLowerThreshold OBJECT-TYPE
	SYNTAX		INTEGER
	ACCESS		read-write
	STATUS		mandatory
	DESCRIPTION	"A Trap trigger for lower limit A/D value.
			If adValue is less than this value then generate
			adExceedLowerThresholdDecrease trap."
	::= { adEntry 15 }

    adTrapLowerHysteresis OBJECT-TYPE
	SYNTAX		INTEGER
	ACCESS		read-write
	STATUS		mandatory
	DESCRIPTION	"A Trap trigger for adEventLowerThreshold offset.
			If adValue is greater equal adEventLowerThreshold minus
			this value after adExceedLowerThresholdDecrease trap
			is generated, then generate
			adExceedLowerThresholdIncrease trap."
	::= { adEntry 16 }

    adEnableExUpThresholdIncreaseTrap OBJECT-TYPE
	SYNTAX		INTEGER {
			    enable(1),
			    disable(2),
			    retry(3)
			}
	ACCESS		read-write
	STATUS		mandatory
	DESCRIPTION	"Indicates whether the SNMP agent process is
			permitted to generate adExceedUpperThresholdIncrease
			traps."
	::= { adEntry 17 }

    adEnableExUpThresholdDecreaseTrap OBJECT-TYPE
	SYNTAX		INTEGER {
			    enable(1),
			    disable(2),
			    retry(3)
			}
	ACCESS		read-write
	STATUS		mandatory
	DESCRIPTION	"Indicates whether the SNMP agent process is
			permitted to generate adExceedUpperThresholdDecrease
			traps."
	::= { adEntry 18 }

    adEnableExUpThresholdTrap OBJECT-TYPE
	SYNTAX		INTEGER {
			    enable(1),
			    disable(2),
			    retry(3)
			}
	ACCESS		read-write
	STATUS		mandatory
	DESCRIPTION	"Indicates whether the SNMP agent process is
			permitted to generate adExceedingUpperThreshold
			traps."
	::= { adEntry 19 }

    adEnableExLoThresholdIncreaseTrap OBJECT-TYPE
	SYNTAX		INTEGER {
			    enable(1),
			    disable(2),
			    retry(3)
			}
	ACCESS		read-write
	STATUS		mandatory
	DESCRIPTION	"Indicates whether the SNMP agent process is
			permitted to generate adExceedLowerThresholdIncrease
			traps."
	::= { adEntry 20 }

    adEnableExLoThresholdDecreaseTrap OBJECT-TYPE
	SYNTAX		INTEGER {
			    enable(1),
			    disable(2),
			    retry(3)
			}
	ACCESS		read-write
	STATUS		mandatory
	DESCRIPTION	"Indicates whether the SNMP agent process is
			permitted to generate adExceedLowerThresholdDecrease
			traps."
	::= { adEntry 21 }

    adEnableExLoThresholdTrap OBJECT-TYPE
	SYNTAX		INTEGER {
			    enable(1),
			    disable(2),
			    retry(3)
			}
	ACCESS		read-write
	STATUS		mandatory
	DESCRIPTION	"Indicates whether the SNMP agent process is
			permitted to generate adExceedingLowerThreshold
			traps."
	::= { adEntry 22 }

    adAlertCondition	OBJECT-TYPE
	SYNTAX		INTEGER {
			    ignore(1),
			    upper(2),
			    lower(3),
			    upper-or-lower(4),
			    normal(5),
			    trap-upper(6),
			    trap-lower(7),
			    trap-upper-or-lower(8),
			    trap-normal(9)
			}
	ACCESS		read-write
	STATUS		optional
	DESCRIPTION	"Which condition shows whether it is alert condition."
	::= { adEntry 23 }

    adRange		OBJECT-TYPE
	SYNTAX		INTEGER {
			    all(1),
			    positive(2)
			}
	ACCESS		read-write
	STATUS		optional
	DESCRIPTION	"Select input formula for A/D value.
			The choice is 'ALL' or 'POSITIVE only'.
			'ALL' semantic permit positive and negative value. 
			else 'POSITIVE only' permit positive value only."
	::= { adEntry 24 }

 -- Following variable are support Ver 3.0 or Later
    adEmailPollInterval	OBJECT-TYPE
	SYNTAX		INTEGER (0..2147483600)
	ACCESS		read-write
	STATUS		mandatory
	DESCRIPTION	"The interval in milliseconds to poll the value
			of A/D channel for Email. This value can be set on
			every 50ms. A fraction is raised and set."
	::= { adEntry 25 }

    adEmailUpperThreshold OBJECT-TYPE
	SYNTAX		INTEGER
	ACCESS		read-write
	STATUS		mandatory
	DESCRIPTION	"A E-Mail trigger for upper limit A/D value.
			If adValue is greater than this value then generate
			adExceedUpperThresholdIncrease E-Mail."
	::= { adEntry 26 }

    adEmailUpperHysteresis OBJECT-TYPE
	SYNTAX		INTEGER
	ACCESS		read-write
	STATUS		mandatory
	DESCRIPTION	"A E-Mail trigger for adEventUpperThreshold offset.
			If adValue is less equal adEventUpperThreshold minus
			this value after adExceedUpperThresholdIncrease E-Mail
			is generated, then generate
			adExceedUpperThresholdDecrease."
	::= { adEntry 27 }

    adEmailLowerThreshold OBJECT-TYPE
	SYNTAX		INTEGER
	ACCESS		read-write
	STATUS		mandatory
	DESCRIPTION	"A Email trigger for lower limit A/D value.
			If adValue is less than this value then generate 
			adExceedLowerThresholdDecrease E-mail."
	::= { adEntry 28 }

    adEmailLowerHysteresis OBJECT-TYPE
	SYNTAX		INTEGER
	ACCESS		read-write
	STATUS		mandatory
	DESCRIPTION	"A Email trigger for adEventLowerThreshold offset.
			If adValue is greater equal adEventLowerThreshold minus
			this value after adExceedLowerThresholdDecrease's E-mail
			is generated, then generate
			adExceedLowerThresholdIncrease."
	::= { adEntry 29 }

    adEnableExUpThresholdIncreaseEmail OBJECT-TYPE
	SYNTAX		INTEGER {
			    enable(1),
			    disable(2),
			    retry(3)
			}
	ACCESS		read-write
	STATUS		mandatory
	DESCRIPTION	"Indicates whether the SNMP agent process is
			permitted to generate adExceedUpperThresholdIncrease
			Email."
	::= { adEntry 30 }

    adEnableExUpThresholdDecreaseEmail OBJECT-TYPE
	SYNTAX		INTEGER {
			    enable(1),
			    disable(2),
			    retry(3)
			}
	ACCESS		read-write
	STATUS		mandatory
	DESCRIPTION	"Indicates whether the SNMP agent process is
			permitted to generate adExceedUpperThresholdDecrease
			Email."
	::= { adEntry 31 }

    adEnableExUpThresholdEmail OBJECT-TYPE
	SYNTAX		INTEGER {
			    enable(1),
			    disable(2),
			    retry(3)
			}
	ACCESS		read-write
	STATUS		mandatory
	DESCRIPTION	"Indicates whether the SNMP agent process is
			permitted to generate adExceedingUpperThreshold
			Email."
	::= { adEntry 32 }

    adEnableExLoThresholdIncreaseEmail OBJECT-TYPE
	SYNTAX		INTEGER {
			    enable(1),
			    disable(2),
			    retry(3)
			}
	ACCESS		read-write
	STATUS		mandatory
	DESCRIPTION	"Indicates whether the SNMP agent process is
			permitted to generate adExceedLowerThresholdIncrease
			Email."
	::= { adEntry 33 }

    adEnableExLoThresholdDecreaseEmail OBJECT-TYPE
	SYNTAX		INTEGER {
			    enable(1),
			    disable(2),
			    retry(3)
			}
	ACCESS		read-write
	STATUS		mandatory
	DESCRIPTION	"Indicates whether the SNMP agent process is
			permitted to generate adExceedLowerThresholdDecrease
			Email."
	::= { adEntry 34 }

    adEnableExLoThresholdEmail OBJECT-TYPE
	SYNTAX		INTEGER {
			    enable(1),
			    disable(2),
			    retry(3)
			}
	ACCESS		read-write
	STATUS		mandatory
	DESCRIPTION	"Indicates whether the SNMP agent process is
			permitted to generate adExceedingLowerThreshold
			Email."
	::= { adEntry 35 }

    adExUpThresholdIncreaseTrapID OBJECT-TYPE
	SYNTAX		INTEGER
	ACCESS		read-write
	STATUS		mandatory
	DESCRIPTION	"Specifyed the SNMP agent generate 
			adExceedUpperThresholdIncrease specific Trap ID.
			When set zero generate adExceedUpperThresholdIncrease
			otherwise adExceedUpperThresholdIncrease[1-127]"
	::= { adEntry 36 }

    adExUpThresholdDecreaseTrapID OBJECT-TYPE
	SYNTAX		INTEGER
	ACCESS		read-write
	STATUS		mandatory
	DESCRIPTION	"Specifyed the SNMP agent generate 
			adExceedUpperThresholdDecrease specific Trap ID.
			When set zero generate adExceedUpperThresholdDecrease
			otherwise adExceedUpperThresholdDecrease[1-127]"
	::= { adEntry 37 }

    adExUpThresholdTrapID OBJECT-TYPE
	SYNTAX		INTEGER
	ACCESS		read-write
	STATUS		mandatory
	DESCRIPTION	"Specifyed the SNMP agent generate 
			adExceedingUpperThreshold specific Trap ID.
			When set zero generate adExceedingUpperThreshold
			otherwise adExceedingUpperThreshold[1-127]"
	::= { adEntry 38 }

    adExLoThresholdIncreaseTrapID OBJECT-TYPE
	SYNTAX		INTEGER
	ACCESS		read-write
	STATUS		mandatory
	DESCRIPTION	"Specifyed the SNMP agent generate 
			adExceedLowerThresholdIncrease specific Trap ID.
			When set zero generate adExceedLowerThresholdIncrease
			otherwise adExceedLowerThresholdIncrease[1-127]"
	::= { adEntry 39 }

    adExLoThresholdDecreaseTrapID OBJECT-TYPE
	SYNTAX		INTEGER
	ACCESS		read-write
	STATUS		mandatory
	DESCRIPTION	"Specifyed the SNMP agent generate 
			adExceedLowerThresholdDecrease specific Trap ID.
			When set zero generate adExceedLowerThresholdDecrease
			otherwise adExceedLowerThresholdDecrease[1-127]"
	::= { adEntry 40 }

    adExLoThresholdTrapID OBJECT-TYPE
	SYNTAX		INTEGER
	ACCESS		read-write
	STATUS		mandatory
	DESCRIPTION	"Specifyed the SNMP agent generate 
			adExceedingLowerThreshold specific Trap ID.
			When set zero generate adExceedingLowerThreshold
			otherwise adExceedingLowerThreshold[1-127]"
	::= { adEntry 41 }


 -- Following variable are support Ver 3.6 or Later
    adRemoteCommandPollInterval	OBJECT-TYPE
	SYNTAX		INTEGER (0..2147483600)
	ACCESS		read-write
	STATUS		mandatory
	DESCRIPTION	"The interval in milliseconds to poll the value
			of A/D channel for remote command. This value can be set on
			every 50ms. A fraction is raised and set."
	::= { adEntry 42 }

    adRemoteCommandUpperThreshold OBJECT-TYPE
	SYNTAX		INTEGER
	ACCESS		read-write
	STATUS		mandatory
	DESCRIPTION	"A remote command trigger for upper limit A/D value.
			If adValue is greater than this value then generate
			adExceedUpperThresholdIncrease remote command."
	::= { adEntry 43 }

    adRemoteCommandUpperHysteresis OBJECT-TYPE
	SYNTAX		INTEGER
	ACCESS		read-write
	STATUS		mandatory
	DESCRIPTION	"A remote command trigger for adEventUpperThreshold offset.
			If adValue is less equal adEventUpperThreshold minus
			this value after adExceedUpperThresholdIncrease remote command
			is generated, then generate
			adExceedUpperThresholdDecrease remote command."
	::= { adEntry 44 }

    adRemoteCommandLowerThreshold OBJECT-TYPE
	SYNTAX		INTEGER
	ACCESS		read-write
	STATUS		mandatory
	DESCRIPTION	"A remote command trigger for lower limit A/D value.
			If adValue is less than this value then generate 
			adExceedLowerThresholdDecrease remote command."
	::= { adEntry 45 }

    adRemoteCommandLowerHysteresis OBJECT-TYPE
	SYNTAX		INTEGER
	ACCESS		read-write
	STATUS		mandatory
	DESCRIPTION	"A remote command trigger for adEventLowerThreshold offset.
			If adValue is greater equal adEventLowerThreshold minus
			this value after adExceedLowerThresholdDecrease's remote command
			is generated, then generate
			adExceedLowerThresholdIncrease remote command."
	::= { adEntry 46 }

    adEnableExUpThresholdIncreaseRemoteCommand OBJECT-TYPE
	SYNTAX		INTEGER {
			    enable(1),
			    disable(2)
			}
	ACCESS		read-write
	STATUS		mandatory
	DESCRIPTION	"Indicates whether the SNMP agent process is
			permitted to generate adExceedUpperThresholdIncrease
			remote command."
	::= { adEntry 47 }

    adEnableExUpThresholdDecreaseRemoteCommand OBJECT-TYPE
	SYNTAX		INTEGER {
			    enable(1),
			    disable(2)
			}
	ACCESS		read-write
	STATUS		mandatory
	DESCRIPTION	"Indicates whether the SNMP agent process is
			permitted to generate adExceedUpperThresholdDecrease
			remote command."
	::= { adEntry 48 }

    adEnableExUpThresholdRemoteCommand OBJECT-TYPE
	SYNTAX		INTEGER {
			    enable(1),
			    disable(2)
			}
	ACCESS		read-write
	STATUS		mandatory
	DESCRIPTION	"Indicates whether the SNMP agent process is
			permitted to generate adExceedingUpperThreshold
			remote command."
	::= { adEntry 49 }

    adEnableExLoThresholdIncreaseRemoteCommand OBJECT-TYPE
	SYNTAX		INTEGER {
			    enable(1),
			    disable(2)
			}
	ACCESS		read-write
	STATUS		mandatory
	DESCRIPTION	"Indicates whether the SNMP agent process is
			permitted to generate adExceedLowerThresholdIncrease
			remote command."
	::= { adEntry 50 }

    adEnableExLoThresholdDecreaseRemoteCommand OBJECT-TYPE
	SYNTAX		INTEGER {
			    enable(1),
			    disable(2)
			}
	ACCESS		read-write
	STATUS		mandatory
	DESCRIPTION	"Indicates whether the SNMP agent process is
			permitted to generate adExceedLowerThresholdDecrease
			remote command."
	::= { adEntry 51 }

    adEnableExLoThresholdRemoteCommand OBJECT-TYPE
	SYNTAX		INTEGER {
			    enable(1),
			    disable(2)
			}
	ACCESS		read-write
	STATUS		mandatory
	DESCRIPTION	"Indicates whether the SNMP agent process is
			permitted to generate adExceedingLowerThreshold
			remote command."
	::= { adEntry 52 }


    adEnableExUpThresholdIncreaseRemoteCommandSet OBJECT-TYPE
	SYNTAX		INTEGER (1..32)
	ACCESS		read-write
	STATUS		mandatory
	DESCRIPTION	"Indicates adExceedUpperThresholdIncrease
			remote command set number generated."
	::= { adEntry 53 }

    adEnableExUpThresholdDecreaseRemoteCommandSet OBJECT-TYPE
	SYNTAX		INTEGER (1..32)
	ACCESS		read-write
	STATUS		mandatory
	DESCRIPTION	"Indicates adExceedUpperThresholdDecrease
			remote command set number generated."
	::= { adEntry 54 }

    adEnableExUpThresholdRemoteCommandSet OBJECT-TYPE
	SYNTAX		INTEGER (1..32)
	ACCESS		read-write
	STATUS		mandatory
	DESCRIPTION	"Indicates adExceedingUpperThreshold
			remote command set number generated."
	::= { adEntry 55 }

    adEnableExLoThresholdIncreaseRemoteCommandSet OBJECT-TYPE
	SYNTAX		INTEGER (1..32)
	ACCESS		read-write
	STATUS		mandatory
	DESCRIPTION	"Indicates adExceedLowerThresholdIncrease
			remote command set number generated."
	::= { adEntry 56 }

    adEnableExLoThresholdDecreaseRemoteCommandSet OBJECT-TYPE
	SYNTAX		INTEGER (1..32)
	ACCESS		read-write
	STATUS		mandatory
	DESCRIPTION	"Indicates adExceedLowerThresholdDecrease
			remote command set number generated."
	::= { adEntry 57 }

    adEnableExLoThresholdRemoteCommandSet OBJECT-TYPE
	SYNTAX		INTEGER (1..32)
	ACCESS		read-write
	STATUS		mandatory
	DESCRIPTION	"Indicates adExceedingLowerThreshold
			remote command set number generated."
	::= { adEntry 58 }

    adValueString		OBJECT-TYPE
	SYNTAX		DisplayString (SIZE (1..32))
	ACCESS		read-only
	STATUS		mandatory
	DESCRIPTION	"The value of A/D channel is multiplied by adValueScale
			and adValueOffset. namely,
			adValue =
			 (value of A/D channel) * adValueScale + adValueOffset."
	::= { adEntry 59 }

    adValueStringUnit		OBJECT-TYPE
	SYNTAX		DisplayString (SIZE (0..31))
	ACCESS		read-write
	STATUS		mandatory
	DESCRIPTION	"The text string is A/D value unit."
	::= { adEntry 60 }

    adValueStringAccurate	OBJECT-TYPE
	SYNTAX		INTEGER (1..6)
	ACCESS		read-write
	STATUS		mandatory
	DESCRIPTION	"This value is significant digits for adValue."
	::= { adEntry 61 }

    adValueStringExponent	OBJECT-TYPE
	SYNTAX		INTEGER (-9..9)
	ACCESS		read-write
	STATUS		mandatory
	DESCRIPTION	"This value is exponential for adValue."
	::= { adEntry 62 }

    adValueStringFilterTap	OBJECT-TYPE
	SYNTAX		INTEGER (1..32)
	ACCESS		read-write
	STATUS		mandatory
	DESCRIPTION	"This value is moving average for adValue."
	::= { adEntry 63 }

    adSensorID		OBJECT-TYPE
	SYNTAX		DisplayString (SIZE (1..17))
	ACCESS		read-write
	STATUS		mandatory
	DESCRIPTION	"This value is digital sensor ID allocated to Channel."
	::= { adEntry 64 }

    adMemo		OBJECT-TYPE
	SYNTAX		DisplayString (SIZE (1..32))
	ACCESS		read-write
	STATUS		mandatory
	DESCRIPTION	"The text string is memo of A/D."
	::= { adEntry 65 }

    adUpperString	OBJECT-TYPE
	SYNTAX		DisplayString (SIZE (1..32))
	ACCESS		read-write
	STATUS		mandatory
	DESCRIPTION	"The text string which expresses that the analog input
			 value is illegal state exceeding the upper threshold value."
	::= { adEntry 66 }

    adLowerString	OBJECT-TYPE
	SYNTAX		DisplayString (SIZE (1..32))
	ACCESS		read-write
	STATUS		mandatory
	DESCRIPTION	"The text string which expresses that the analog input
			 value is illegal state exceeding the lower threshold value."
	::= { adEntry 67 }

    adNormalString	OBJECT-TYPE
	SYNTAX		DisplayString (SIZE (1..32))
	ACCESS		read-write
	STATUS		mandatory
	DESCRIPTION	"The text string which expresses that the analog input
			 value is among normal state."
	::= { adEntry 68 }

    adValue0Threshold	OBJECT-TYPE
	SYNTAX		INTEGER
	ACCESS		read-write
	STATUS		mandatory
	DESCRIPTION	"The threshold which assumes the analog input value
			 to be 0."
	::= { adEntry 69 }

    adValueStatisticsMin	OBJECT-TYPE
	SYNTAX		INTEGER
	ACCESS		read-write
	STATUS		mandatory
	DESCRIPTION	"The minimum adValue since system power on"
	::= { adEntry 70 }

    adValueStatisticsMax	OBJECT-TYPE
	SYNTAX		INTEGER
	ACCESS		read-write
	STATUS		mandatory
	DESCRIPTION	"The maximum adValue since system power on"
	::= { adEntry 71 }

    adValueOnlyString	OBJECT-TYPE
	SYNTAX		DisplayString (SIZE (1..32))
	ACCESS		read-only
	STATUS		mandatory
	DESCRIPTION	"This was looks like adValueString  but no add to 
			unit strings."
	::= { adEntry 72 }

    adNotConnectedString	OBJECT-TYPE
	SYNTAX		DisplayString (SIZE (1..32))
	ACCESS		read-write
	STATUS		mandatory
	DESCRIPTION	"The text string which expresses that the analog input
			 value is among disconnected state."
	::= { adEntry 73 }

    adConnectionStatus		OBJECT-TYPE
	SYNTAX		INTEGER {
			    connected(40),
			    not-connected(60)
			}
	ACCESS		read-only
	STATUS		mandatory
	DESCRIPTION	"The current status of connection."
	::= { adEntry 74 }

    adEventCurrentStatus	OBJECT-TYPE
	SYNTAX		INTEGER {
			    lower-alert(10),
			    normal(50),
			    not-connected(60),
			    upper-alert(90)
			}
	ACCESS		read-only
	STATUS		mandatory
	DESCRIPTION	"The current status on event condition."
	::= { adEntry 75 }

    adTrapCurrentStatus		OBJECT-TYPE
	SYNTAX		INTEGER {
			    lower-alert(10),
			    normal(50),
			    not-connected(60),
			    upper-alert(90)
			}
	ACCESS		read-only
	STATUS		mandatory
	DESCRIPTION	"The current status on snmp condition."
	::= { adEntry 76 }

    adEmailCurrentStatus	OBJECT-TYPE
	SYNTAX		INTEGER {
			    lower-alert(10),
			    normal(50),
			    not-connected(60),
			    upper-alert(90)
			}
	ACCESS		read-only
	STATUS		mandatory
	DESCRIPTION	"The current status on mail condition."
	::= { adEntry 77 }

    adRemoteCommandCurrentStatus	OBJECT-TYPE
	SYNTAX		INTEGER {
			    lower-alert(10),
			    normal(50),
			    not-connected(60),
			    upper-alert(90)
			}
	ACCESS		read-only
	STATUS		mandatory
	DESCRIPTION	"The current status on remote command condition."
	::= { adEntry 78 }

    adEventCurrentStatusString	OBJECT-TYPE
	SYNTAX		DisplayString (SIZE (1..32))
	ACCESS		read-only
	STATUS		mandatory
	DESCRIPTION	"The current status string of event condition."
	::= { adEntry 79 }

    adTrapCurrentStatusString	OBJECT-TYPE
	SYNTAX		DisplayString (SIZE (1..32))
	ACCESS		read-only
	STATUS		mandatory
	DESCRIPTION	"The current status string of trap condition."
	::= { adEntry 80 }

    adEmailCurrentStatusString	OBJECT-TYPE
	SYNTAX		DisplayString (SIZE (1..32))
	ACCESS		read-only
	STATUS		mandatory
	DESCRIPTION	"The current status string of mail condition."
	::= { adEntry 81 }

    adRemoteCommandCurrentStatusString	OBJECT-TYPE
	SYNTAX		DisplayString (SIZE (1..32))
	ACCESS		read-only
	STATUS		mandatory
	DESCRIPTION	"The current status string of remote command condition."
	::= { adEntry 82 }

-- CEC network-device DI management group
--
-- This group contains the MIB variables used to determine the
-- number of DI channels supported by the device and the type of 
-- device currently connected.

    diNumber		OBJECT-TYPE
	SYNTAX		INTEGER
	ACCESS		read-only
	STATUS		mandatory
	DESCRIPTION	"The number of DI channels supported by this device."
	::= { ndIO 3 }

-- The DI table
--
-- This table contains diNumber entries describing each DI channels
--

    diTable		OBJECT-TYPE
	SYNTAX		SEQUENCE OF DiEntry
	ACCESS		not-accessible
	STATUS		mandatory
	DESCRIPTION	"A list of DI channel entries. The number of entries
			is given by the value diNumber."
	::= { ndIO 4 }

    diEntry		OBJECT-TYPE
	SYNTAX		DiEntry
	ACCESS		not-accessible
	STATUS		mandatory
	DESCRIPTION	"A DI channel entry containing objects to describe the
			DI channel."
	INDEX		{ diIndex }
	::= { diTable 1 }

    DiEntry ::=
	SEQUENCE {
	    diIndex
		INTEGER,
	    diType
		DisplayString,
	    diValue0String
		DisplayString,
	    diValue1String
		DisplayString,
	    diValue
		INTEGER,
	    diLogInterval
		INTEGER,
	    diEventPollInterval
		INTEGER,
	    diTrapPollInterval
		INTEGER,
	    diEnableChangeValue0Trap
		INTEGER,
	    diEnableValue0Trap
		INTEGER,
	    diEnableChangeValue1Trap
		INTEGER,
	    diEnableValue1Trap
		INTEGER,
	    diAlertCondition
		INTEGER,
	    diChannelMode
		INTEGER,
	    diPulseCount
		INTEGER,
	    diPulseInterval
		INTEGER,
	    diPulseCountPreserve
		INTEGER,
	    diPulseCondition
		INTEGER,
	    diPulseChatteringCheck
		INTEGER,
	    diPulseCountLimit
		INTEGER,
	    diEnablePulseCountTrap
  		INTEGER,
	    diEmailPollInterval
		INTEGER,
	    diEnableChangeValue0Email
		INTEGER,
	    diEnableValue0Email
		INTEGER,
	    diEnableChangeValue1Email
		INTEGER,
	    diEnableValue1Email
		INTEGER,
	    diEnablePulseCountEmail
		INTEGER,
	    diChangeValue0TrapID
		INTEGER,
	    diValue0TrapID
		INTEGER,
	    diChangeValue1TrapID
		INTEGER,
	    diValue1TrapID
		INTEGER,
	    diPulseCountTrapID
		INTEGER,
	    diRemoteCommandPollInterval
		INTEGER,
	    diEnableChangeValue0RemoteCommand
		INTEGER,
	    diEnableValue0RemoteCommand
		INTEGER,
	    diEnableChangeValue1RemoteCommand
		INTEGER,
	    diEnableValue1RemoteCommand
		INTEGER,
	    diEnableChangeValue0RemoteCommandSet
		INTEGER,
	    diEnableValue0RemoteCommandSet
		INTEGER,
	    diEnableChangeValue1RemoteCommandSet
		INTEGER,
	    diEnableValue1RemoteCommandSet
		INTEGER,
	    diEnablePulseCountRemoteCommand
		INTEGER,
	    diEnablePulseCountRemoteCommandSet
		INTEGER,
	    diValueInvert
		INTEGER,
	    diConnectionStatus
		INTEGER
	}

    diIndex		OBJECT-TYPE
	SYNTAX		INTEGER
	ACCESS		read-only
	STATUS		mandatory
	DESCRIPTION	"A unique value for each DI channel. It's value ranges
			between 1 and the value diNumber."
	::= { diEntry 1 }

    diType		OBJECT-TYPE
	SYNTAX		DisplayString (SIZE (1..32))
	ACCESS		read-write
	STATUS		mandatory
	DESCRIPTION	"The text string is type of device connected
			DI channel."
	::= { diEntry 2 }

    diValue0String	OBJECT-TYPE
	SYNTAX		DisplayString (SIZE (1..32))
	ACCESS		read-write
	STATUS		mandatory
	DESCRIPTION	"The text string is description of 0 Value of 
			the DI channel."
	::= { diEntry 3 }

    diValue1String	OBJECT-TYPE
	SYNTAX		DisplayString (SIZE (1..32))
	ACCESS		read-write
	STATUS		mandatory
	DESCRIPTION	"The text string is description of 1 Value of 
			the DI channel."
	::= { diEntry 4 }

    diValue		OBJECT-TYPE
	SYNTAX		INTEGER (0..1)
	ACCESS		read-only
	STATUS		mandatory
	DESCRIPTION	"The value of device connected DI channel."
	::= { diEntry 5 }

    diLogInterval	OBJECT-TYPE
	SYNTAX		INTEGER (0..2147483600)
	ACCESS		read-write
	STATUS		mandatory
	DESCRIPTION	"The interval in milliseconds to poll the value
			of DI channel for data logging.
			When DI value is changed, log diValue to dataLog.
			This value can be set on every 50ms.
			A fraction is raised and set."
	::= { diEntry 6 }

    diEventPollInterval	OBJECT-TYPE
	SYNTAX		INTEGER (0..2147483600)
	ACCESS		read-write
	STATUS		mandatory
	DESCRIPTION	"The interval in milliseconds to poll the value
			of DI channel for Event. This value can be set on
			every 50ms. A fraction is raised and set."
	::= { diEntry 7 }

    diTrapPollInterval	OBJECT-TYPE
	SYNTAX		INTEGER (0..2147483600)
	ACCESS		read-write
	STATUS		mandatory
	DESCRIPTION	"The interval in milliseconds to poll the value
			of DI channel for Trap. This value can be set on
			every 50ms. A fraction is raised and set."
	::= { diEntry 8 }

    diEnableChangeValue0Trap OBJECT-TYPE
	SYNTAX		INTEGER {
			    enable(1),
			    disable(2),
			    retry(3)
			}
	ACCESS		read-write
	STATUS		mandatory
	DESCRIPTION	"Indicates whether the SNMP agent process is
			permitted to generate diChangeValue0 traps."
	::= { diEntry 9 }

    diEnableValue0Trap OBJECT-TYPE
	SYNTAX		INTEGER {
			    enable(1),
			    disable(2),
			    retry(3)
			}
	ACCESS		read-write
	STATUS		mandatory
	DESCRIPTION	"Indicates whether the SNMP agent process is
			permitted to generate diValue0 traps."
	::= { diEntry 10 }

    diEnableChangeValue1Trap OBJECT-TYPE
	SYNTAX		INTEGER {
			    enable(1),
			    disable(2),
			    retry(3)
			}
	ACCESS		read-write
	STATUS		mandatory
	DESCRIPTION	"Indicates whether the SNMP agent process is
			permitted to generate diChangeValue1 traps."
	::= { diEntry 11 }

    diEnableValue1Trap OBJECT-TYPE
	SYNTAX		INTEGER {
			    enable(1),
			    disable(2),
			    retry(3)
			}
	ACCESS		read-write
	STATUS		mandatory
	DESCRIPTION	"Indicates whether the SNMP agent process is
			permitted to generate diValue1 traps."
	::= { diEntry 12 }

    diAlertCondition	OBJECT-TYPE
	SYNTAX		INTEGER {
			    ignore(1),
			    value0(2),
			    value1(3),
			    trap-value0(4),
			    trap-value1(5)
			}
	ACCESS		read-write
	STATUS		optional
	DESCRIPTION	"Which condition shows whether it is alert condition."
	::= { diEntry 13 }

    diChannelMode	OBJECT-TYPE
	SYNTAX		INTEGER {
			    normal(1),
			    pulse(2)
			}
	ACCESS		read-write
	STATUS		mandatory
	DESCRIPTION	"Indicates that the channel is normal mode or
			pulse count mode."
	::= { diEntry 14 }

    diPulseCount	OBJECT-TYPE
	SYNTAX		INTEGER
	ACCESS		read-write
	STATUS		mandatory
	DESCRIPTION	"Count value of pulse input to DI channel."
	::= { diEntry 15 }

    diPulseInterval	OBJECT-TYPE
	SYNTAX		INTEGER
	ACCESS		read-only
	STATUS		mandatory
	DESCRIPTION	"Interval(ms) between the latest pulse and the previous
			state pulse input to DI channel."
	::= { diEntry 16 }

    diPulseCountPreserve OBJECT-TYPE
	SYNTAX		INTEGER {
			    enable(1),
			    disable(2)
			}
	ACCESS		read-write
	STATUS		mandatory
	DESCRIPTION	"Indicates whether the SNMP agent is permitted to
			preserve diPulseCount in non-volatile memory so that it
			remains constant between re-initializations."
	::= { diEntry 17 }

    diPulseCondition	OBJECT-TYPE
	SYNTAX		INTEGER {
			    change0to1(1),
			    change1to0(2),
			    both(3)
			}
	ACCESS		read-write
	STATUS		optional
	DESCRIPTION	"Condition to count diPulseCount."
	::= { diEntry 18 }

    diPulseChatteringCheck OBJECT-TYPE
	SYNTAX		INTEGER {
			    enable(1),
			    disable(2)
			}
	ACCESS		read-write
	STATUS		mandatory
	DESCRIPTION	"Indicates whether to prevent chattering with
			pulse mode."
	::= { diEntry 19 }

    diPulseCountLimit	OBJECT-TYPE
	SYNTAX		INTEGER
	ACCESS		read-write
	STATUS		mandatory
	DESCRIPTION	"Upper limit of diPulseCount.
			If diPulseCount exceeds this value then generate
			diPulseCountTrap."
	::= { diEntry 20 }

    diEnablePulseCountTrap OBJECT-TYPE
	SYNTAX		INTEGER {
			    enable(1),
			    disable(2),
			    retry(3)
			}
	ACCESS		read-write
	STATUS		mandatory
	DESCRIPTION	"Indicates whether the SNMP agent process is
			permitted to generate diPulseCountTrap traps."
	::= { diEntry 21 }

 -- Following variable are support Ver 3.0 or Later

    diEmailPollInterval	OBJECT-TYPE
	SYNTAX		INTEGER (0..2147483600)
	ACCESS		read-write
	STATUS		mandatory
	DESCRIPTION	"The interval in milliseconds to poll the value
			of DI channel for Email. This value can be set on
			every 50ms. A fraction is raised and set."
	::= { diEntry 22 }

    diEnableChangeValue0Email OBJECT-TYPE
	SYNTAX		INTEGER {
			    enable(1),
			    disable(2)
			}
	ACCESS		read-write
	STATUS		mandatory
	DESCRIPTION	"Indicates whether the SNMP agent process is
			permitted to generate diChangeValue0's mail."
	::= { diEntry 23 }

    diEnableValue0Email OBJECT-TYPE
	SYNTAX		INTEGER {
			    enable(1),
			    disable(2)
			}
	ACCESS		read-write
	STATUS		mandatory
	DESCRIPTION	"Indicates whether the SNMP agent process is
			permitted to generate diValue0 's mail."
	::= { diEntry 24 }

    diEnableChangeValue1Email OBJECT-TYPE
	SYNTAX		INTEGER {
			    enable(1),
			    disable(2)
			}
	ACCESS		read-write
	STATUS		mandatory
	DESCRIPTION	"Indicates whether the SNMP agent process is
			permitted to generate diChangeValue1' mail."
	::= { diEntry 25 }

    diEnableValue1Email OBJECT-TYPE
	SYNTAX		INTEGER {
			    enable(1),
			    disable(2)
			}
	ACCESS		read-write
	STATUS		mandatory
	DESCRIPTION	"Indicates whether the SNMP agent process is
			permitted to generate diValue1's mail."
	::= { diEntry 26 }

    diEnablePulseCountEmail OBJECT-TYPE
	SYNTAX		INTEGER {
			    enable(1),
			    disable(2)
			}
	ACCESS		read-write
	STATUS		mandatory
	DESCRIPTION	"Indicates whether the SNMP agent process is
			permitted to generate PulseCount's mail."
	::= { diEntry 27 }

    diChangeValue0TrapID OBJECT-TYPE
	SYNTAX		INTEGER
	ACCESS		read-write
	STATUS		mandatory
	DESCRIPTION	"Specifyed the SNMP agent generate 
			diChangeValue0 specific Trap ID.
			When set zero generate diChangeValue0 
			otherwise diChangeValue0-[1-127]"
	::= { diEntry 28 }

    diValue0TrapID OBJECT-TYPE
	SYNTAX		INTEGER
	ACCESS		read-write
	STATUS		mandatory
	DESCRIPTION	"Specifyed the SNMP agent generate 
			diValue0 specific Trap ID.
			When set zero generate diValue0
			otherwise diValue0-[1-127]"
	::= { diEntry 29 }

    diChangeValue1TrapID OBJECT-TYPE
	SYNTAX		INTEGER
	ACCESS		read-write
	STATUS		mandatory
	DESCRIPTION	"Specifyed the SNMP agent generate 
			diChangeValue1 specific Trap ID.
			When set zero generate diChangeValue1
			otherwise diChangeValue1-[1-127]"
	::= { diEntry 30 }

    diValue1TrapID OBJECT-TYPE
	SYNTAX		INTEGER
	ACCESS		read-write
	STATUS		mandatory
	DESCRIPTION	"Specifyed the SNMP agent generate 
			diValue1 specific Trap ID.
			When set zero generate diValue1
			otherwise diValue1-[1-127]"
	::= { diEntry 31 }

    diPulseCountTrapID OBJECT-TYPE
	SYNTAX		INTEGER
	ACCESS		read-write
	STATUS		mandatory
	DESCRIPTION	"Specifyed the SNMP agent generate 
			diPulseCountTrap specific Trap ID.
			When set zero generate diPulseCountTrap
			otherwise diPulseCountTrap[1-127]"
	::= { diEntry 32 }


 -- Following variable are support Ver 3.6 or Later

    diRemoteCommandPollInterval	OBJECT-TYPE
	SYNTAX		INTEGER (0..2147483600)
	ACCESS		read-write
	STATUS		mandatory
	DESCRIPTION	"The interval in milliseconds to poll the value
			of DI channel for remote command. This value can be set on
			every 50ms. A fraction is raised and set."
	::= { diEntry 33 }

    diEnableChangeValue0RemoteCommand OBJECT-TYPE
	SYNTAX		INTEGER {
			    enable(1),
			    disable(2)
			}
	ACCESS		read-write
	STATUS		mandatory
	DESCRIPTION	"Indicates whether the SNMP agent process is
			permitted to generate diChangeValue0's remote command."
	::= { diEntry 34 }

    diEnableValue0RemoteCommand OBJECT-TYPE
	SYNTAX		INTEGER {
			    enable(1),
			    disable(2)
			}
	ACCESS		read-write
	STATUS		mandatory
	DESCRIPTION	"Indicates whether the SNMP agent process is
			permitted to generate diValue0's remote command."
	::= { diEntry 35 }

    diEnableChangeValue1RemoteCommand OBJECT-TYPE
	SYNTAX		INTEGER {
			    enable(1),
			    disable(2)
			}
	ACCESS		read-write
	STATUS		mandatory
	DESCRIPTION	"Indicates whether the SNMP agent process is
			permitted to generate diChangeValue1's remote command."
	::= { diEntry 36 }

    diEnableValue1RemoteCommand OBJECT-TYPE
	SYNTAX		INTEGER {
			    enable(1),
			    disable(2)
			}
	ACCESS		read-write
	STATUS		mandatory
	DESCRIPTION	"Indicates whether the SNMP agent process is
			permitted to generate diValue1's remote command."
	::= { diEntry 37 }

    diEnableChangeValue0RemoteCommandSet OBJECT-TYPE
	SYNTAX		INTEGER (1..32)
	ACCESS		read-write
	STATUS		mandatory
	DESCRIPTION	"Indicates diChangeValue0's remote command set number generated."
	::= { diEntry 38 }

    diEnableValue0RemoteCommandSet OBJECT-TYPE
	SYNTAX		INTEGER (1..32)
	ACCESS		read-write
	STATUS		mandatory
	DESCRIPTION	"Indicates diValue0's remote command set number generated."
	::= { diEntry 39 }

    diEnableChangeValue1RemoteCommandSet OBJECT-TYPE
	SYNTAX		INTEGER (1..32)
	ACCESS		read-write
	STATUS		mandatory
	DESCRIPTION	"Indicates diChangeValue1's remote command set number generated."
	::= { diEntry 40 }

    diEnableValue1RemoteCommandSet OBJECT-TYPE
	SYNTAX		INTEGER (1..32)
	ACCESS		read-write
	STATUS		mandatory
	DESCRIPTION	"Indicates diValue1's remote command set number generated."
	::= { diEntry 41 }

    diEnablePulseCountRemoteCommand OBJECT-TYPE
	SYNTAX		INTEGER {
			    enable(1),
			    disable(2)
			}
	ACCESS		read-write
	STATUS		mandatory
	DESCRIPTION	"Indicates whether the SNMP agent process is
			permitted to generate PulseCount's remote command."
	::= { diEntry 42 }

    diEnablePulseCountRemoteCommandSet OBJECT-TYPE
	SYNTAX		INTEGER (1..32)
	ACCESS		read-write
	STATUS		mandatory
	DESCRIPTION	"Indicates PulseCount's remote command set number 
			generated."
	::= { diEntry 43 }

    diValueInvert OBJECT-TYPE
	SYNTAX		INTEGER {
			    enable(1),
			    disable(2)
			}
	ACCESS		read-write
	STATUS		mandatory
	DESCRIPTION	"Indicates whether the contact input has inverted."
	::= { diEntry 44 }

    diConnectionStatus		OBJECT-TYPE
	SYNTAX		INTEGER {
			    connected(40),
			    not-connected(60)
			}
	ACCESS		read-only
	STATUS		mandatory
	DESCRIPTION	"The current status of DI connection."
	::= { diEntry 45 }

-- CEC network-device DO management group
--
-- This group contains the MIB variables used to determine the
-- number of DO channels supported by the device and the type of 
-- device currently connected.

    doNumber		OBJECT-TYPE
	SYNTAX		INTEGER
	ACCESS		read-only
	STATUS		mandatory
	DESCRIPTION	"The number of DO channels supported by this device."
	::= { ndIO 5 }

-- The DO table
--
-- This table contains doNumber entries describing each channels
--

    doTable		OBJECT-TYPE
	SYNTAX		SEQUENCE OF DoEntry
	ACCESS		not-accessible
	STATUS		mandatory
	DESCRIPTION	"A list of DO channel entries. The number of entries
			is given by the value doNumber."
	::= { ndIO 6 }

    doEntry		OBJECT-TYPE
	SYNTAX		DoEntry
	ACCESS		not-accessible
	STATUS		mandatory
	DESCRIPTION	"A DO channel entry containing objects to describe the
			DO channel."
	INDEX		{ doIndex }
	::= { doTable 1 }

    DoEntry ::=
	SEQUENCE {
	    doIndex
		INTEGER,
	    doType
		DisplayString,
	    doValue0String
		DisplayString,
	    doValue1String
		DisplayString,
	    doValue
		INTEGER,
	    doValuePreserve
		INTEGER,
	    doLogEnable
		INTEGER,
	    doAuto0Enable
		INTEGER,
	    doAuto0TriggerObjectID
		OBJECT IDENTIFIER,
	    doAuto0TriggerEventNo
		INTEGER,
	    doAuto1Enable
		INTEGER,
	    doAuto1TriggerObjectID
		OBJECT IDENTIFIER,
	    doAuto1TriggerEventNo
		INTEGER,
	    doChannelMode
		INTEGER,
	    doPulseInterval
		INTEGER,
	    doTrapPollInterval
		INTEGER,
	    doEnableChangeValue0Trap
		INTEGER,
	    doEnableValue0Trap
		INTEGER,
	    doEnableChangeValue1Trap
		INTEGER,
	    doEnableValue1Trap
		INTEGER,
	    doChangeValue0TrapID
		INTEGER,
	    doValue0TrapID
		INTEGER,
	    doChangeValue1TrapID
		INTEGER,
	    doValue1TrapID
		INTEGER,
	    doValueInvert
		INTEGER,
	    doConnectionStatus
		INTEGER
	}

    doIndex		OBJECT-TYPE
	SYNTAX		INTEGER
	ACCESS		read-only
	STATUS		mandatory
	DESCRIPTION	"A unique value for each DO channel. It's value ranges
			between 1 and the value doNumber."
	::= { doEntry 1 }

    doType		OBJECT-TYPE
	SYNTAX		DisplayString (SIZE (1..32))
	ACCESS		read-write
	STATUS		mandatory
	DESCRIPTION	"The text string is type of device connected
			DO channel."
	::= { doEntry 2 }

    doValue0String	OBJECT-TYPE
	SYNTAX		DisplayString (SIZE (1..32))
	ACCESS		read-write
	STATUS		mandatory
	DESCRIPTION	"The text string is description of 0 Value of 
			the DO channel."
	::= { doEntry 3 }

    doValue1String	OBJECT-TYPE
	SYNTAX		DisplayString (SIZE (1..32))
	ACCESS		read-write
	STATUS		mandatory
	DESCRIPTION	"The text string is description of 1 Value of 
			the DO channel."
	::= { doEntry 4 }

    doValue		OBJECT-TYPE
	SYNTAX		INTEGER (0..1)
	ACCESS		read-write
	STATUS		mandatory
	DESCRIPTION	"The value of DO channel."
	::= { doEntry 5 }

    doValuePreserve	OBJECT-TYPE
	SYNTAX		INTEGER {
			    enable(1),
			    disable(2)
			}
	ACCESS		read-write
	STATUS		mandatory
	DESCRIPTION	"Indicates whether the SNMP agent is permitted to
			preserve doValue in non-volatile memory so that it
			remains constant between re-initializations."
	::= { doEntry 6 }

    doLogEnable		OBJECT-TYPE
	SYNTAX		INTEGER {
			    enable(1),
			    disable(2)
			}
	ACCESS		read-write
	STATUS		mandatory
	DESCRIPTION	"Indicates whether the SNMP agent process is
			permitted to log doValue. When DO value is changed,
			log doValue to dataLog."
	::= { doEntry 7 }

    doAuto0Enable	OBJECT-TYPE
	SYNTAX		INTEGER {
			    enable(1),
			    disable(2)
			}
	ACCESS		read-write
	STATUS		mandatory
	DESCRIPTION	"Indicates whether the SNMP agent process is
			permitted to auto set 0 to the value of DO channel."
	::= { doEntry 8 }

    doAuto0TriggerObjectID OBJECT-TYPE
	SYNTAX		OBJECT IDENTIFIER
	ACCESS		read-write
	STATUS		mandatory
	DESCRIPTION	"Watch ObjectID for Digital Output value to Zero.
			If event is occured with specific ObjectID,
			Digital Output is drived to Zero."
	::= { doEntry 9 }

    doAuto0TriggerEventNo OBJECT-TYPE
	SYNTAX		INTEGER {
			    adExceedUpperThresholdIncrease(1),
			    adExceedUpperThresholdDecrease(2),
			    adExceedingUpperThreshold(3),
			    adExceedLowerThresholdIncrease(4),
			    adExceedLowerThresholdDecrease(5),
			    adExceedingLowerThreshold(6),
			    adNormalOld(7),
			    diChangeValue0(8),
			    diValue0(9),
			    diChangeValue1(10),
			    diValue1(11),
			    vcExceedUpperThresholdIncrease(13),
			    vcExceedUpperThresholdDecrease(14),
			    vcExceedingUpperThreshold(15),
			    vcExceedLowerThresholdIncrease(16),
			    vcExceedLowerThresholdDecrease(17),
			    vcExceedingLowerThreshold(18),
			    vcNormal(19),
			    adChangeToNormal(20),
			    adNormal(21),
			    adChangeToAbnormal(22),
			    adAbnormal(23),
			    motionDetect(79),
			    motionDetecting(80),
			    motionNotDetect(81),
			    motionNotDetecting(82),
			    diForwardError(101),
			    diForwardNormal(102),
			    diForwardReceiveTimeout(104),
			    diForwardReceiveTimeoutRecover(105),
			    diForwardSendReceiveError(106),
			    diForwardSendReceiveNormal(107),
			    subUnitNotConnected(108),
			    subUnitConnected(109),
			    multiMeterNotConnected(110),
			    multiMeterConnected(111),
			    conditionIsAlert(512),
			    conditionChangeToAlert(513),
			    conditionIsNormal(514),
			    conditionChangeToNormal(515),
			    network-deviceTraps(1024)
			}
	ACCESS		read-write
	STATUS		mandatory
	DESCRIPTION	"A Event trigger for Digital Output value Zero.
			When specific event is occured,
			Digital Output is drived to Zero."
	::= { doEntry 10 }

    doAuto1Enable	OBJECT-TYPE
	SYNTAX		INTEGER {
			    enable(1),
			    disable(2)
			}
	ACCESS		read-write
	STATUS		mandatory
	DESCRIPTION	"Indicates whether the SNMP agent process is
			permitted to auto set 1 to the value of DO channel."
	::= { doEntry 11 }

    doAuto1TriggerObjectID OBJECT-TYPE
	SYNTAX		OBJECT IDENTIFIER
	ACCESS		read-write
	STATUS		mandatory
	DESCRIPTION	"Watch ObjectID for Digital Output value to One.
			If event is occured with specific ObjectID,
			Digital Output is drived to One."
	::= { doEntry 12 }

    doAuto1TriggerEventNo OBJECT-TYPE
	SYNTAX		INTEGER {
			    adExceedUpperThresholdIncrease(1),
			    adExceedUpperThresholdDecrease(2),
			    adExceedingUpperThreshold(3),
			    adExceedLowerThresholdIncrease(4),
			    adExceedLowerThresholdDecrease(5),
			    adExceedingLowerThreshold(6),
			    adNormalOld(7),
			    diChangeValue0(8),
			    diValue0(9),
			    diChangeValue1(10),
			    diValue1(11),
			    vcExceedUpperThresholdIncrease(13),
			    vcExceedUpperThresholdDecrease(14),
			    vcExceedingUpperThreshold(15),
			    vcExceedLowerThresholdIncrease(16),
			    vcExceedLowerThresholdDecrease(17),
			    vcExceedingLowerThreshold(18),
			    vcNormal(19),
			    adChangeToNormal(20),
			    adNormal(21),
			    adChangeToAbnormal(22),
			    adAbnormal(23),
			    motionDetect(79),
			    motionDetecting(80),
			    motionNotDetect(81),
			    motionNotDetecting(82),
			    diForwardError(101),
			    diForwardNormal(102),
			    diForwardReceiveTimeout(104),
			    diForwardReceiveTimeoutRecover(105),
			    diForwardSendReceiveError(106),
			    diForwardSendReceiveNormal(107),
			    subUnitNotConnected(108),
			    subUnitConnected(109),
			    multiMeterNotConnected(110),
			    multiMeterConnected(111),
			    conditionIsAlert(512),
			    conditionChangeToAlert(513),
			    conditionIsNormal(514),
			    conditionChangeToNormal(515),
			    network-deviceTraps(1024)
			}
	ACCESS		read-write
	STATUS		mandatory
	DESCRIPTION	"A Event trigger for Digital Output value One.
			When specific event is occured, Digital Output is 
			drived to Zero."
	::= { doEntry 13 }

    doChannelMode	OBJECT-TYPE
	SYNTAX		INTEGER {
			    normal(1),
			    pulse(2)
			}
	ACCESS		read-write
	STATUS		optional
	DESCRIPTION	"Indicates that the channel is normal mode or
			pulse mode."
	::= { doEntry 14 }

    doPulseInterval	OBJECT-TYPE
	SYNTAX		INTEGER (500..2147483600)
	ACCESS		read-write
	STATUS		optional
	DESCRIPTION	"This value is the interval of the pulse outputted
			at the pulse mode. "
	::= { doEntry 15 }

    doTrapPollInterval	OBJECT-TYPE
	SYNTAX		INTEGER (0..2147483600)
	ACCESS		read-write
	STATUS		mandatory
	DESCRIPTION	"The interval in milliseconds to poll the value
			of DO channel for Trap. This value can be set on
			every 50ms. A fraction is raised and set."
	::= { doEntry 16 }

    doEnableChangeValue0Trap OBJECT-TYPE
	SYNTAX		INTEGER {
			    enable(1),
			    disable(2),
			    retry(3)
			}
	ACCESS		read-write
	STATUS		mandatory
	DESCRIPTION	"Indicates whether the SNMP agent process is
			permitted to generate doChangeValue0 traps."
	::= { doEntry 17 }

    doEnableValue0Trap OBJECT-TYPE
	SYNTAX		INTEGER {
			    enable(1),
			    disable(2),
			    retry(3)
			}
	ACCESS		read-write
	STATUS		mandatory
	DESCRIPTION	"Indicates whether the SNMP agent process is
			permitted to generate doValue0 traps."
	::= { doEntry 18 }

    doEnableChangeValue1Trap OBJECT-TYPE
	SYNTAX		INTEGER {
			    enable(1),
			    disable(2),
			    retry(3)
			}
	ACCESS		read-write
	STATUS		mandatory
	DESCRIPTION	"Indicates whether the SNMP agent process is
			permitted to generate doChangeValue1 traps."
	::= { doEntry 19 }

    doEnableValue1Trap OBJECT-TYPE
	SYNTAX		INTEGER {
			    enable(1),
			    disable(2),
			    retry(3)
			}
	ACCESS		read-write
	STATUS		mandatory
	DESCRIPTION	"Indicates whether the SNMP agent process is
			permitted to generate doValue1 traps."
	::= { doEntry 20 }


    doChangeValue0TrapID OBJECT-TYPE
	SYNTAX		INTEGER
	ACCESS		read-write
	STATUS		mandatory
	DESCRIPTION	"Specifyed the SNMP agent generate 
			doChangeValue0 specific Trap ID.
			When set zero generate doChangeValue0 
			otherwise doChangeValue0-[1-127]"
	::= { doEntry 21 }

    doValue0TrapID OBJECT-TYPE
	SYNTAX		INTEGER
	ACCESS		read-write
	STATUS		mandatory
	DESCRIPTION	"Specifyed the SNMP agent generate 
			doValue0 specific Trap ID.
			When set zero generate doValue0
			otherwise doValue0-[1-127]"
	::= { doEntry 22 }

    doChangeValue1TrapID OBJECT-TYPE
	SYNTAX		INTEGER
	ACCESS		read-write
	STATUS		mandatory
	DESCRIPTION	"Specifyed the SNMP agent generate 
			doChangeValue1 specific Trap ID.
			When set zero generate doChangeValue1
			otherwise doChangeValue1-[1-127]"
	::= { doEntry 23 }

    doValue1TrapID OBJECT-TYPE
	SYNTAX		INTEGER
	ACCESS		read-write
	STATUS		mandatory
	DESCRIPTION	"Specifyed the SNMP agent generate 
			doValue1 specific Trap ID.
			When set zero generate doValue1
			otherwise doValue1-[1-127]"
	::= { doEntry 24 }

    doValueInvert OBJECT-TYPE
	SYNTAX		INTEGER {
			    enable(1),
			    disable(2)
			}
	ACCESS		read-write
	STATUS		mandatory
	DESCRIPTION	"Indicates whether the contact output has inverted."
	::= { doEntry 25 }

    doConnectionStatus		OBJECT-TYPE
	SYNTAX		INTEGER {
			    connected(40),
			    not-connected(60)
			}
	ACCESS		read-only
	STATUS		mandatory
	DESCRIPTION	"The current status of DO connection."
	::= { doEntry 26 }

--
--

    diValues		OBJECT-TYPE
	SYNTAX		DisplayString
	ACCESS		read-only
	STATUS		optional
	DESCRIPTION	"The value of device connected all DI channels.
			This value contains '0', '1', '-'.
			'-' means that DI channel is not connected."
	::= { ndIO 7 }

    doValues		OBJECT-TYPE
	SYNTAX		DisplayString
	ACCESS		read-write
	STATUS		optional
	DESCRIPTION	"The value of device connected all DO channels.
			This value contains '0', '1', '-'.
			'-' means that DO channel is not connected and
			don't change status specified channel."
	::= { ndIO 8 }

-- V4.0 later
-- Digital Thermo-Sensor group
--
    dtsNumber	OBJECT-TYPE
	SYNTAX		INTEGER
	ACCESS		not-accessible
	STATUS		mandatory
	DESCRIPTION	"Number of Digital thermo sensor."
	::= { ndIO 10 }

    dtsTotalCount	OBJECT-TYPE
	SYNTAX		INTEGER
	ACCESS		read-only
	STATUS		mandatory
	DESCRIPTION	"The Size of dtsTable."
	::= { dtsNumber 1 }

    dtsFindIdCount	OBJECT-TYPE
	SYNTAX		INTEGER
	ACCESS		read-only
	STATUS		mandatory
	DESCRIPTION	"Number of Digital thermo sensor count on the bus."
	::= { dtsNumber 2 }

    dtsUnregistIdCount	OBJECT-TYPE
	SYNTAX		INTEGER
	ACCESS		read-only
	STATUS		mandatory
	DESCRIPTION	"Number of Digital thermo sensor not yet regist count."
	::= { dtsNumber 3 }


    dtsTable	OBJECT-TYPE
	SYNTAX		SEQUENCE OF DtsEntry
	ACCESS		not-accessible
	STATUS		mandatory
	DESCRIPTION	"A list of the igital thermo sensor entries."
	::= { ndIO 11 }

    dtsEntry	OBJECT-TYPE
	SYNTAX		DtsEntry
	ACCESS		not-accessible
	STATUS		mandatory
	DESCRIPTION	"An entry for Digital thermo sensor."
	INDEX		{ dtsIndex }
	::= { dtsTable 1 }

    DtsEntry ::=
	SEQUENCE {
    	    dtsIndex
    	    	INTEGER,
    	    dtsFindID
		DisplayString,
    	    dtsUnregistID
		DisplayString
	}

    dtsIndex	OBJECT-TYPE
	SYNTAX		INTEGER
	ACCESS		read-only
	STATUS		mandatory
	DESCRIPTION	"An entry for the Digital thermo sensor entries."
	::= { dtsEntry 1 }

    dtsFindID	OBJECT-TYPE
	SYNTAX		DisplayString (SIZE (1..64))
	ACCESS		read-only
	STATUS		mandatory
	DESCRIPTION	"Digital thermo sensor ID on the bus."
	::= { dtsEntry 2 }

    dtsUnregistID	OBJECT-TYPE
	SYNTAX		DisplayString (SIZE (1..64))
	ACCESS		read-only
	STATUS		mandatory
	DESCRIPTION	"Digital thermo sensor not yet regist count."
	::= { dtsEntry 3 }


-- Subunit group
--
    adValueStringsNumber	OBJECT-TYPE
	SYNTAX		INTEGER
	ACCESS		not-accessible
	STATUS		mandatory
	DESCRIPTION	"Number of adValueStrings."
	::= { ndIO 12 }

    adValueStringsTable		OBJECT-TYPE
	SYNTAX		SEQUENCE OF AdValueStringsEntry
	ACCESS		not-accessible
	STATUS		mandatory
	DESCRIPTION	"A list of the adValueStrings entries."
	::= { ndIO 13 }

    adValueStringsEntry	OBJECT-TYPE
	SYNTAX		AdValueStringsEntry
	ACCESS		not-accessible
	STATUS		mandatory
	DESCRIPTION	"An entry for adValueStrings."
	INDEX		{ adValueStringsIndex }
	::= { adValueStringsTable 1 }

    AdValueStringsEntry ::=
	SEQUENCE {
	    adValueStringsIndex
		INTEGER,
    	    adValueStringsValue
		DisplayString
	}

    adValueStringsIndex	OBJECT-TYPE
	SYNTAX		INTEGER
	ACCESS		read-only
	STATUS		mandatory
	DESCRIPTION	"An entry for the adValueStrings entries."
	::= { adValueStringsEntry 1 }

    adValueStringsValue	OBJECT-TYPE
	SYNTAX		DisplayString
	ACCESS		read-only
	STATUS		mandatory
	DESCRIPTION	"adValueStrings value."
	::= { adValueStringsEntry 2 }


-- Subunit group
--
    subUnitNumber	OBJECT-TYPE
	SYNTAX		INTEGER
	ACCESS		not-accessible
	STATUS		mandatory
	DESCRIPTION	"Number of Subunit."
	::= { ndIO 14 }

    subUnitTable	OBJECT-TYPE
	SYNTAX		SEQUENCE OF SubUnitEntry
	ACCESS		not-accessible
	STATUS		mandatory
	DESCRIPTION	"A list of the Subunit entries."
	::= { ndIO 15 }

    subUnitEntry	OBJECT-TYPE
	SYNTAX		SubUnitEntry
	ACCESS		not-accessible
	STATUS		mandatory
	DESCRIPTION	"An entry for Subunit."
	INDEX		{ subUnitIndex }
	::= { subUnitTable 1 }

    SubUnitEntry ::=
	SEQUENCE {
    	    subUnitIndex
    	    	INTEGER,
    	    subUnitStatus
    	    	INTEGER,
    	    subUnitType
    	    	INTEGER,
	    subUnitEnableNotConnectedTrap
    	    	INTEGER,
	    subUnitEnableConnectedTrap
    	    	INTEGER,
	    subUnitNotConnectedTrapID
    	    	INTEGER,
	    subUnitConnectedTrapID
    	    	INTEGER,
	    subUnitEnableNotConnectedEmail
    	    	INTEGER,
	    subUnitEnableConnectedEmail
    	    	INTEGER,
	    subUnitEnableNotConnectedRemoteCommand
    	    	INTEGER,
	    subUnitEnableConnectedRemoteCommand
    	    	INTEGER,
	    subUnitNotConnectedRemoteCommandSet
    	    	INTEGER,
	    subUnitConnectedRemoteCommandSet
    	    	INTEGER,
	    subUnitChangeTime
    	    	INTEGER,
	    subUnitSuccessCount
    	    	INTEGER,
	    subUnitErrorCount
    	    	INTEGER,
	    subUnitNoReplyCount
    	    	INTEGER,
	    subUnitLinkDownCount
    	    	INTEGER,
	    subunitDACUDistribution
    	    	INTEGER,
	    subunitDACUCurrentType
    	    	INTEGER,
	    subunitDACUCurrentRange
    	    	INTEGER,
	    subunitDACUVoltageRange
    	    	INTEGER,
	    subunitDACUStatusDistribution
    	    	INTEGER,
	    subunitDACUStatusCurrentType
    	    	INTEGER,
	    subunitDACUStatusCurrentRange
    	    	INTEGER,
	    subunitDACUStatusVoltageRange
    	    	INTEGER,
	    subunitDACUSave
    	    	INTEGER,
	    subunitDACUCountL1Active
    	    	INTEGER,
	    subunitDACUCountL1Apparent
    	    	INTEGER,
	    subunitDACUCountL1Reactive
    	    	INTEGER,
	    subunitDACUCountL2Active
    	    	INTEGER,
	    subunitDACUCountL2Apparent
    	    	INTEGER,
	    subunitDACUCountL2Reactive
    	    	INTEGER
	}

    subUnitIndex	OBJECT-TYPE
	SYNTAX		INTEGER
	ACCESS		read-only
	STATUS		mandatory
	DESCRIPTION	"An entry for the Subunit entries."
	::= { subUnitEntry 1 }

    subUnitStatus	OBJECT-TYPE
	SYNTAX		INTEGER {
			    connected(40),
			    not-connected(60)
			}
	ACCESS		read-only
	STATUS		mandatory
	DESCRIPTION	"Subunit status."
	::= { subUnitEntry 2 }

    subUnitType		OBJECT-TYPE
	SYNTAX		INTEGER {
			    other(0),
			    dthu(1),
			    dacu(2)
			}
	ACCESS		read-write
	STATUS		mandatory
	DESCRIPTION	"Subunit type."
	::= { subUnitEntry 3 }

    subUnitEnableNotConnectedTrap	OBJECT-TYPE
	SYNTAX		INTEGER {
			    enable(1),
			    disable(2),
			    retry(3)
			}
	ACCESS		read-write
	STATUS		mandatory
	DESCRIPTION	"Indicates whether the SNMP agent process is
			permitted to generate subUnitNotConnected traps."
	::= { subUnitEntry 4 }

    subUnitEnableConnectedTrap	 OBJECT-TYPE
	SYNTAX		INTEGER {
			    enable(1),
			    disable(2),
			    retry(3)
			}
	ACCESS		read-write
	STATUS		mandatory
	DESCRIPTION	"Indicates whether the SNMP agent process is
			permitted to generate subUnitConnected traps."
	::= { subUnitEntry 5 }

    subUnitNotConnectedTrapID	OBJECT-TYPE
	SYNTAX		INTEGER
	ACCESS		read-write
	STATUS		mandatory
	DESCRIPTION	"Specifyed the SNMP agent generate 
			subUnitNotConnected specific Trap ID.
			When set zero generate subUnitNotConnected
			otherwise subUnitNotConnected-[1-127]"
	::= { subUnitEntry 6 }

    subUnitConnectedTrapID	OBJECT-TYPE
	SYNTAX		INTEGER
	ACCESS		read-write
	STATUS		mandatory
	DESCRIPTION	"Specifyed the SNMP agent generate 
			subUnitConnected specific Trap ID.
			When set zero generate subUnitConnected
			otherwise subUnitConnected-[1-127]"
	::= { subUnitEntry 7 }

    subUnitEnableNotConnectedEmail	OBJECT-TYPE
	SYNTAX		INTEGER {
			    enable(1),
			    disable(2)
			}
	ACCESS		read-write
	STATUS		mandatory
	DESCRIPTION	"Indicates whether the SNMP agent process is
			permitted to generate subUnitNotConnected's mail."
	::= { subUnitEntry 8 }

    subUnitEnableConnectedEmail	OBJECT-TYPE
	SYNTAX		INTEGER {
			    enable(1),
			    disable(2)
			}
	ACCESS		read-write
	STATUS		mandatory
	DESCRIPTION	"Indicates whether the SNMP agent process is
			permitted to generate subUnitConnected's mail."
	::= { subUnitEntry 9 }

    subUnitEnableNotConnectedRemoteCommand	OBJECT-TYPE
	SYNTAX		INTEGER {
			    enable(1),
			    disable(2)
			}
	ACCESS		read-write
	STATUS		mandatory
	DESCRIPTION	"Indicates whether the SNMP agent process is
			permitted to generate subUnitNotConnected's
			remote command."
	::= { subUnitEntry 10 }

    subUnitEnableConnectedRemoteCommand	OBJECT-TYPE
	SYNTAX		INTEGER {
			    enable(1),
			    disable(2)
			}
	ACCESS		read-write
	STATUS		mandatory
	DESCRIPTION	"Indicates whether the SNMP agent process is
			permitted to generate subUnitConnected's
			remote command."
	::= { subUnitEntry 11 }

    subUnitNotConnectedRemoteCommandSet	OBJECT-TYPE
	SYNTAX		INTEGER (1..32)
	ACCESS		read-write
	STATUS		mandatory
	DESCRIPTION	"Indicates subUnitNotConnected's remote command set
			number generated."
	::= { subUnitEntry 12 }

    subUnitConnectedRemoteCommandSet OBJECT-TYPE
	SYNTAX		INTEGER (1..32)
	ACCESS		read-write
	STATUS		mandatory
	DESCRIPTION	"Indicates subUnitConnected's remote command set
			number generated."
	::= { subUnitEntry 13 }

    subUnitChangeTime OBJECT-TYPE
	SYNTAX		Time
	ACCESS		read-only
	STATUS		mandatory
	DESCRIPTION	"The date and time Subunit status changed."
	::= { subUnitEntry 14 }

    subUnitSuccessCount OBJECT-TYPE
	SYNTAX		INTEGER
	ACCESS		read-only
	STATUS		mandatory
	DESCRIPTION	"The count of subunit communication success."
	::= { subUnitEntry 15 }

    subUnitErrorCount OBJECT-TYPE
	SYNTAX		INTEGER
	ACCESS		read-only
	STATUS		mandatory
	DESCRIPTION	"The count of subunit communication error."
	::= { subUnitEntry 16 }

    subUnitNoReplyCount OBJECT-TYPE
	SYNTAX		INTEGER
	ACCESS		read-only
	STATUS		mandatory
	DESCRIPTION	"The count of subunit no reply."
	::= { subUnitEntry 17 }

    subUnitLinkDownCount OBJECT-TYPE
	SYNTAX		INTEGER
	ACCESS		read-only
	STATUS		mandatory
	DESCRIPTION	"The count of subunit linkdown."
	::= { subUnitEntry 18 }

    subUnitDACUDistribution OBJECT-TYPE
	SYNTAX		INTEGER {
			    single-two(0),
			    single-three(1),
			    three-three(2),
			    three-four(3)
			}
	ACCESS		read-write
	STATUS		mandatory
	DESCRIPTION     "Indicates saved distribution of DACU."
	::= { subUnitEntry 32 }

    subUnitDACUCurrentType OBJECT-TYPE
	SYNTAX		INTEGER {
			    general-ct(0),
			    ew05-ct(1)
			}
	ACCESS		read-write
	STATUS		mandatory
	DESCRIPTION     "Indicates saved current sensor type of DACU."
	::= { subUnitEntry 33 }

    subUnitDACUCurrentRange OBJECT-TYPE
	SYNTAX		INTEGER
	ACCESS		read-write
	STATUS		mandatory
	DESCRIPTION     "Indicates saved current range of DACU."
	::= { subUnitEntry 34 }

    subUnitDACUVoltageRange OBJECT-TYPE
	SYNTAX		INTEGER
	ACCESS		read-write
	STATUS		mandatory
	DESCRIPTION     "Indicates saved voltage range of DACU."
	::= { subUnitEntry 35 }

    subUnitDACUStatusDistribution OBJECT-TYPE
	SYNTAX		INTEGER {
			    single-two(0),
			    single-three(1),
			    three-three(2),
			    three-four(3)
			}
	ACCESS		read-only
	STATUS		mandatory
	DESCRIPTION     "Indicates distribution of DACU read from DACU."
	::= { subUnitEntry 36 }

    subUnitDACUStatusCurrentType OBJECT-TYPE
	SYNTAX		INTEGER {
			    general-ct(0),
			    ew05-ct(1)
			}
	ACCESS		read-only
	STATUS		mandatory
	DESCRIPTION     "Indicates current sensor type of DACU read from DACU."
	::= { subUnitEntry 37 }

    subUnitDACUStatusCurrentRange OBJECT-TYPE
	SYNTAX		INTEGER (1..32)
	ACCESS		read-only
	STATUS		mandatory
	DESCRIPTION     "Indicates current range of DACU read from DACU."
	::= { subUnitEntry 38 }

    subUnitDACUStatusVoltageRange OBJECT-TYPE
	SYNTAX		INTEGER (1..32)
	ACCESS		read-only
	STATUS		mandatory
	DESCRIPTION     "Indicates voltage range of DACU read from DACU."
	::= { subUnitEntry 39 }

    subUnitDACUSave OBJECT-TYPE
	SYNTAX		INTEGER
	ACCESS		read-write
	STATUS		mandatory
	DESCRIPTION	"Setting to any value will send current DACU
			parameter to DACU. When read this will always
			return 0."
	::= { subUnitEntry 40 }

    subUnitDACUCountL1Active OBJECT-TYPE
	SYNTAX		INTEGER
	ACCESS		read-write
	STATUS		mandatory
	DESCRIPTION	"Sending L1 integral active power consumption
			to DACU. When read this will always return 0."
	::= { subUnitEntry 41 }

    subUnitDACUCountL1Apparent OBJECT-TYPE
	SYNTAX		INTEGER
	ACCESS		read-write
	STATUS		mandatory
	DESCRIPTION	"Sending L1 integral apparent power consumption
			to DACU. When read this will always return 0."
	::= { subUnitEntry 42 }

    subUnitDACUCountL1Reactive OBJECT-TYPE
	SYNTAX		INTEGER
	ACCESS		read-write
	STATUS		mandatory
	DESCRIPTION	"Sending L1 integral reactive power consumption
			to DACU. When read this will always return 0."
	::= { subUnitEntry 43 }

    subUnitDACUCountL2Active OBJECT-TYPE
	SYNTAX		INTEGER
	ACCESS		read-write
	STATUS		mandatory
	DESCRIPTION	"Sending L2 integral active power consumption
			to DACU. When read this will always return 0."
	::= { subUnitEntry 44 }

    subUnitDACUCountL2Apparent OBJECT-TYPE
	SYNTAX		INTEGER
	ACCESS		read-write
	STATUS		mandatory
	DESCRIPTION	"Sending L2 integral apparent power consumption
			to DACU. When read this will always return 0."
	::= { subUnitEntry 45 }

    subUnitDACUCountL2Reactive OBJECT-TYPE
	SYNTAX		INTEGER
	ACCESS		read-write
	STATUS		mandatory
	DESCRIPTION	"Sending L2 integral reactive power consumption
			to DACU. When read this will always return 0."
	::= { subUnitEntry 46 }


-- MultiMeter group
--
    multiMeterNumber	OBJECT-TYPE
	SYNTAX		INTEGER
	ACCESS		not-accessible
	STATUS		mandatory
	DESCRIPTION	"Number of Multi meter."
	::= { ndIO 16 }

    multiMeterTable	OBJECT-TYPE
	SYNTAX		SEQUENCE OF MultiMeterEntry
	ACCESS		not-accessible
	STATUS		mandatory
	DESCRIPTION	"A list of the Multie meter entries."
	::= { ndIO 17 }

    multiMeterEntry	OBJECT-TYPE
	SYNTAX		MultiMeterEntry
	ACCESS		not-accessible
	STATUS		mandatory
	DESCRIPTION	"An entry for Multi meter."
	INDEX		{ multiMeterIndex }
	::= { multiMeterTable 1 }

    MultiMeterEntry ::=
	SEQUENCE {
    	    multiMeterIndex
    	    	INTEGER,
    	    multiMeterStatus
    	    	INTEGER,
	    multiMeterEnableNotConnectedTrap
    	    	INTEGER,
	    multiMeterEnableConnectedTrap
    	    	INTEGER,
	    multiMeterNotConnectedTrapID
    	    	INTEGER,
	    multiMeterConnectedTrapID
    	    	INTEGER,
	    multiMeterEnableNotConnectedEmail
    	    	INTEGER,
	    multiMeterEnableConnectedEmail
    	    	INTEGER,
	    multiMeterEnableNotConnectedRemoteCommand
    	    	INTEGER,
	    multiMeterEnableConnectedRemoteCommand
    	    	INTEGER,
	    multiMeterNotConnectedRemoteCommandSet
    	    	INTEGER,
	    multiMeterConnectedRemoteCommandSet
    	    	INTEGER,
	    multiMeterChangeTime
    	    	INTEGER,
	    multiMeterSuccessCount
    	    	INTEGER,
	    multiMeterErrorCount
    	    	INTEGER,
	    multiMeterNoReplyCount
    	    	INTEGER,
	    multiMeterType
    	    	INTEGER
	}

    multiMeterIndex	OBJECT-TYPE
	SYNTAX		INTEGER
	ACCESS		read-only
	STATUS		mandatory
	DESCRIPTION	"An entry for the Multi meter entries."
	::= { multiMeterEntry 1 }

    multiMeterStatus	OBJECT-TYPE
	SYNTAX		INTEGER {
			    connected(40),
			    not-connected(60)
			}
	ACCESS		read-only
	STATUS		mandatory
	DESCRIPTION	"Multi meter status."
	::= { multiMeterEntry 2 }

    multiMeterEnableNotConnectedTrap	OBJECT-TYPE
	SYNTAX		INTEGER {
			    enable(1),
			    disable(2),
			    retry(3)
			}
	ACCESS		read-write
	STATUS		mandatory
	DESCRIPTION	"Indicates whether the SNMP agent process is
			permitted to generate multiMeterNotConnected traps."
	::= { multiMeterEntry 3 }

    multiMeterEnableConnectedTrap	 OBJECT-TYPE
	SYNTAX		INTEGER {
			    enable(1),
			    disable(2),
			    retry(3)
			}
	ACCESS		read-write
	STATUS		mandatory
	DESCRIPTION	"Indicates whether the SNMP agent process is
			permitted to generate multiMeterConnected traps."
	::= { multiMeterEntry 4 }

    multiMeterNotConnectedTrapID	OBJECT-TYPE
	SYNTAX		INTEGER
	ACCESS		read-write
	STATUS		mandatory
	DESCRIPTION	"Specifyed the SNMP agent generate 
			multiMeterNotConnected specific Trap ID.
			When set zero generate multiMeterNotConnected
			otherwise multiMeterNotConnected-[1-127]"
	::= { multiMeterEntry 5 }

    multiMeterConnectedTrapID	OBJECT-TYPE
	SYNTAX		INTEGER
	ACCESS		read-write
	STATUS		mandatory
	DESCRIPTION	"Specifyed the SNMP agent generate 
			multiMeterConnected specific Trap ID.
			When set zero generate multiMeterConnected
			otherwise multiMeterConnected-[1-127]"
	::= { multiMeterEntry 6 }

    multiMeterEnableNotConnectedEmail	OBJECT-TYPE
	SYNTAX		INTEGER {
			    enable(1),
			    disable(2)
			}
	ACCESS		read-write
	STATUS		mandatory
	DESCRIPTION	"Indicates whether the SNMP agent process is
			permitted to generate multiMeterNotConnected's mail."
	::= { multiMeterEntry 7 }

    multiMeterEnableConnectedEmail	OBJECT-TYPE
	SYNTAX		INTEGER {
			    enable(1),
			    disable(2)
			}
	ACCESS		read-write
	STATUS		mandatory
	DESCRIPTION	"Indicates whether the SNMP agent process is
			permitted to generate multiMeterConnected's mail."
	::= { multiMeterEntry 8 }

    multiMeterEnableNotConnectedRemoteCommand	OBJECT-TYPE
	SYNTAX		INTEGER {
			    enable(1),
			    disable(2)
			}
	ACCESS		read-write
	STATUS		mandatory
	DESCRIPTION	"Indicates whether the SNMP agent process is
			permitted to generate multiMeterNotConnected's
			remote command."
	::= { multiMeterEntry 9 }

    multiMeterEnableConnectedRemoteCommand	OBJECT-TYPE
	SYNTAX		INTEGER {
			    enable(1),
			    disable(2)
			}
	ACCESS		read-write
	STATUS		mandatory
	DESCRIPTION	"Indicates whether the SNMP agent process is
			permitted to generate multiMeterConnected's
			remote command."
	::= { multiMeterEntry 10 }

    multiMeterNotConnectedRemoteCommandSet	OBJECT-TYPE
	SYNTAX		INTEGER (1..32)
	ACCESS		read-write
	STATUS		mandatory
	DESCRIPTION	"Indicates multiMeterNotConnected's remote command set
			number generated."
	::= { multiMeterEntry 11 }

    multiMeterConnectedRemoteCommandSet OBJECT-TYPE
	SYNTAX		INTEGER (1..32)
	ACCESS		read-write
	STATUS		mandatory
	DESCRIPTION	"Indicates multiMeterConnected's remote command set
			number generated."
	::= { multiMeterEntry 12 }

    multiMeterChangeTime OBJECT-TYPE
	SYNTAX		Time
	ACCESS		read-only
	STATUS		mandatory
	DESCRIPTION	"The date and time Multi meter status changed."
	::= { multiMeterEntry 13 }

    multiMeterSuccessCount OBJECT-TYPE
	SYNTAX		INTEGER
	ACCESS		read-only
	STATUS		mandatory
	DESCRIPTION	"The count of multimeter communication success."
	::= { multiMeterEntry 14 }

    multiMeterErrorCount OBJECT-TYPE
	SYNTAX		INTEGER
	ACCESS		read-only
	STATUS		mandatory
	DESCRIPTION	"The count of multimeter communication error."
	::= { multiMeterEntry 15 }

    multiMeterNoReplyCount OBJECT-TYPE
	SYNTAX		INTEGER
	ACCESS		read-only
	STATUS		mandatory
	DESCRIPTION	"The count of multimeter no reply."
	::= { multiMeterEntry 16 }

    multiMeterType	OBJECT-TYPE
	SYNTAX		INTEGER {
			    qlc(1),
			    mrlc(2)
			}
	ACCESS		read-write
	STATUS		mandatory
	DESCRIPTION	"Multi meter type."
	::= { multiMeterEntry 17 }


-- The ImageCapture Group
--
-- This group contains the MIB variables used to determine the
-- trigger for Image Capturing.

    imageCapture	OBJECT IDENTIFIER ::= { ndMgmt 3 }

-- Timer Trigger Group

    timerTrigger	OBJECT IDENTIFIER ::= { imageCapture 1 }

    timerTriggerEnable	OBJECT-TYPE
	SYNTAX		INTEGER {
			    enable(1),
			    disable(2)
			}
	ACCESS		read-write
	STATUS		optional
	DESCRIPTION	"Indicates whether this device is permitted to generate
			timer trigger."
	::= { timerTrigger 1 }

    timerTriggerSceneNo	OBJECT-TYPE
	SYNTAX		INTEGER (1..2)
	ACCESS		read-write
	STATUS		optional
	DESCRIPTION	"Indicates whether this device uses which ImageScene
			entry with timer trigger."
	::= { timerTrigger 2 }

    timerTriggerMaxScene OBJECT-TYPE
	SYNTAX		INTEGER
	ACCESS		read-write
	STATUS		optional
	DESCRIPTION	"The maximum number of scenes which saved by timer
			trigger."
	::= { timerTrigger 3 }

    timerTriggerOverwrite OBJECT-TYPE
	SYNTAX		INTEGER {
			    enable(1),
			    disable(2)
			}
	ACCESS		read-write
	STATUS		optional
	DESCRIPTION	"Indicates whether this device is permitted to overwrite
			new scene to oldest scene by timer trigger."
	::= { timerTrigger 4 }

    timerTriggerRemoteCommand OBJECT-TYPE
	SYNTAX		INTEGER {
			    enable(1),
			    disable(2)
			}
	ACCESS		read-write
	STATUS		optional
	DESCRIPTION	"Indicates whether the SNMP agent process is
			permitted to generate timerTrigger
			remote command."
	::= { timerTrigger 5 }

    timerTriggerRemoteCommandSet OBJECT-TYPE
	SYNTAX		INTEGER (1..32)
	ACCESS		read-write
	STATUS		optional
	DESCRIPTION	"Indicates timerTrigger
			remote command set number generated."
	::= { timerTrigger 6 }

    timerTriggerSound OBJECT-TYPE
	SYNTAX		INTEGER {
			    enable(1),
			    disable(2)
			}
	ACCESS		read-write
	STATUS		optional
	DESCRIPTION	"Indicates whether timerTrigger saves sound."
	::= { timerTrigger 7 }

    timerTriggerSoundCamera OBJECT-TYPE
	SYNTAX		INTEGER
	ACCESS		read-write
	STATUS		optional
	DESCRIPTION	"Indicates which camera sound timerTrigger saves."
	::= { timerTrigger 8 }

    timerTriggerTrapControl OBJECT-TYPE
	SYNTAX		INTEGER {
			    enable(1),
			    disable(2),
			    retry(3)
			}
	ACCESS		read-write
	STATUS		optional
	DESCRIPTION	"This value sets up action about the generation of
			the timerTriggerTrap. When the scene begins to be
			stored by the timer trigger,
			the timerTriggerTrap isn't generated(disable),
			is generated(enable),
			is continuously generated(retry)."
	::= { timerTrigger 32 }

    timerTriggerTrapCount	OBJECT-TYPE
	SYNTAX		INTEGER
	ACCESS		read-only
	STATUS		optional
	DESCRIPTION	"This value increases when the timerTriggerTrap
			generated."
	::= { timerTrigger 33 }

    timerTriggerSceneID	OBJECT-TYPE
	SYNTAX		DisplayString
	ACCESS		read-only
	STATUS		optional
	DESCRIPTION	"This string is ID of the newest stored scene.
			Initial value is NULL string."
	::= { timerTrigger 34 }

    timerTriggerEmail	OBJECT-TYPE
	SYNTAX		INTEGER {
			    enable(1),
			    disable(2)
			}
	ACCESS		read-write
	STATUS		optional
	DESCRIPTION	"This value sets up action about the generation of
			the timerTriggerEmail. When the scene begins to be
			stored by the timer trigger,
			the timerTriggerEmail isn't generated(disable),
			is generated(enable)."
	::= { timerTrigger 35 }

    timerTriggerAttachmentEmail OBJECT-TYPE
	SYNTAX		INTEGER {
			    none(1),
			    trigger(2),
			    scene(3)
			}
	ACCESS		read-write
	STATUS		optional
	DESCRIPTION	"This value sets up action about the attachment of
			the timerTriggerEmail. When the scene begins to be
			stored by the timer trigger,
			the timerTriggerEmail sent without picture(none),
			with triggered picture(trigger),
			with before and after triggered pictures(scene)."
	::= { timerTrigger 36 }

    timerTriggerCompleteTrapControl OBJECT-TYPE
	SYNTAX		INTEGER {
			    enable(1),
			    disable(2),
			    retry(3)
			}
	ACCESS		read-write
	STATUS		optional
	DESCRIPTION	"This value sets up action about the generation of
			the timerTriggerTrap. When the scene begins to be
			stored by the timer trigger,
			the timerTriggerTrap isn't generated(disable),
			is generated(enable),
			is continuously generated(retry)."
	::= { timerTrigger 37 }

    timerTriggerSceneBefore OBJECT-TYPE
	SYNTAX		INTEGER
	ACCESS		read-only
	STATUS		optional
	DESCRIPTION	"Indicates how many images saved after a trigger
			occurrence."
	::= { timerTrigger 38 }

    timerTriggerSceneAfter OBJECT-TYPE
	SYNTAX		INTEGER
	ACCESS		read-only
	STATUS		optional
	DESCRIPTION	"Indicates how many images saved after a trigger
			occurrence."
	::= { timerTrigger 39 }

    timerTriggerPeriodNumber OBJECT-TYPE
	SYNTAX		INTEGER
	ACCESS		read-only
	STATUS		optional
	DESCRIPTION	"The number of timerTriggerPeriod entries."
	::= { timerTrigger 64 }

-- The Period table for timerTrigger
--
-- This table contains timerTriggerPeriodNumber entries describing each Period.
--

    timerTriggerPeriodTable OBJECT-TYPE
	SYNTAX		SEQUENCE OF TimerTriggerPeriodEntry
	ACCESS		not-accessible
	STATUS		optional
	DESCRIPTION	"A list of timerTriggerPeriod table."
	::= { timerTrigger 65 }

    timerTriggerPeriodEntry OBJECT-TYPE
	SYNTAX		TimerTriggerPeriodEntry
	ACCESS		not-accessible
	STATUS		optional
	DESCRIPTION	"A timer trigger period entry containing objects to
			describe the timer period."
	INDEX		{ timerTriggerPeriodIndex }
	::= { timerTriggerPeriodTable 1 }

    TimerTriggerPeriodEntry ::=
	SEQUENCE {
	    timerTriggerPeriodIndex
		INTEGER,
	    timerTriggerPeriodEnable
		INTEGER,
	    timerTriggerPeriodDate
		DisplayString,
	    timerTriggerPeriodTime
		DisplayString,
	    timerTriggerPeriodCamera
		INTEGER,
	    timerTriggerPeriodPreset
		INTEGER
	}

    timerTriggerPeriodIndex OBJECT-TYPE
	SYNTAX		INTEGER
	ACCESS		read-only
	STATUS		optional
	DESCRIPTION	"A unique value for each timerTriggerPeriod entry.
			It's value ranges between 1 and the value
			timerTriggerPeriodNumber."
	::= { timerTriggerPeriodEntry 1 }

    timerTriggerPeriodEnable OBJECT-TYPE
	SYNTAX		INTEGER {
			    enable(1),
			    disable(2)
			}
	ACCESS		read-write
	STATUS		optional
	DESCRIPTION	"Indicates whether this device permitted to generate
			timer trigger with this timerTriggerPeriodEntry."
	::= { timerTriggerPeriodEntry 2 }

    timerTriggerPeriodDate OBJECT-TYPE
	SYNTAX		DisplayString (SIZE (1..32))
	ACCESS		read-write
	STATUS		optional
	DESCRIPTION	"The text string is date to generate timer trigger.
			read manual for more detail."
	::= { timerTriggerPeriodEntry 3 }

    timerTriggerPeriodTime OBJECT-TYPE
	SYNTAX		DisplayString (SIZE (1..32))
	ACCESS		read-write
	STATUS		optional
	DESCRIPTION	"The text string is time to generate timer trigger.
			read manual for more detail."
	::= { timerTriggerPeriodEntry 4 }

	timerTriggerPeriodCamera	OBJECT-TYPE
	SYNTAX		INTEGER
	ACCESS		read-write
	STATUS		optional
	DESCRIPTION	"Indicates which camera is used to capture image when this
			trigger is fired."
	::= { timerTriggerPeriodEntry 5 }

	timerTriggerPeriodPreset	OBJECT-TYPE
	SYNTAX		INTEGER
	ACCESS		read-write
	STATUS		optional
	DESCRIPTION	"Indicates the camera preset position number to move when
			this trigger fired."
	::= { timerTriggerPeriodEntry 6 }

-- DI Trigger Group

    singleDiTrigger	OBJECT IDENTIFIER ::= { imageCapture 2 }

    singleDiTriggerEnable	OBJECT-TYPE
	SYNTAX		INTEGER {
			    enable(1),
			    disable(2)
			}
	ACCESS		read-write
	STATUS		optional
	DESCRIPTION	"Indicates whether this device is permitted to generate
			di trigger."
	::= { singleDiTrigger 1 }

    singleDiTriggerSceneNo	OBJECT-TYPE
	SYNTAX		INTEGER (1..2)
	ACCESS		read-write
	STATUS		optional
	DESCRIPTION	"Indicates whether this device uses which ImageScene
			entry with di trigger."
	::= { singleDiTrigger 2 }

    singleDiTriggerMaxScene OBJECT-TYPE
	SYNTAX		INTEGER
	ACCESS		read-write
	STATUS		optional
	DESCRIPTION	"The maximum number of scenes which saved by di
			trigger."
	::= { singleDiTrigger 3 }

    singleDiTriggerOverwrite OBJECT-TYPE
	SYNTAX		INTEGER {
			    enable(1),
			    disable(2)
			}
	ACCESS		read-write
	STATUS		optional
	DESCRIPTION	"Indicates whether this device is permitted to overwrite
			new scene to oldest scene by di trigger."
	::= { singleDiTrigger 4 }

    singleDiTriggerCondition OBJECT-TYPE
	SYNTAX		INTEGER {
			    none(1),
			    change0to1(2),
			    change1to0(3),
			    both(4)
			}
	ACCESS		read-write
	STATUS		optional
	DESCRIPTION	"Condition to generate di trigger."
	::= { singleDiTrigger 8 }

    singleDiTriggerTrapControl OBJECT-TYPE
	SYNTAX		INTEGER {
			    enable(1),
			    disable(2),
			    retry(3)
			}
	ACCESS		read-write
	STATUS		optional
	DESCRIPTION	"This value sets up action about the generation of
			the diTriggerTrap. When the scene begins to be
			stored by the di trigger,
			the diTriggerTrap isn't generated(disable),
			is generated(enable),
			is continuously generated(retry)."
	::= { singleDiTrigger 32 }

    singleDiTriggerTrapCount	OBJECT-TYPE
	SYNTAX		INTEGER
	ACCESS		read-write
	STATUS		optional
	DESCRIPTION	"This value increases when the diTriggerTrap
			generated.
			And on ND-VW02/03/03R, 0 is set on this value to stop
			continuously the diTriggerTrap."
	::= { singleDiTrigger 33 }

    singleDiTriggerSceneID	OBJECT-TYPE
	SYNTAX		DisplayString
	ACCESS		read-only
	STATUS		optional
	DESCRIPTION	"This string is ID of the newest stored scene.
			Initial value is NULL string."
	::= { singleDiTrigger 34 }

	diTriggerNumber		OBJECT-TYPE
	SYNTAX				INTEGER
	ACCESS				read-only
	STATUS				optional
	DESCRIPTION	"The number of DI triggers supported by this device."
	::= { imageCapture 10 }

	diTriggerTable		OBJECT-TYPE
	SYNTAX				SEQUENCE OF DiTriggerEntry
	ACCESS				not-accessible
	STATUS				optional
	DESCRIPTION	"A list of DI trigger entries. The number of entries
			is given by the value diTriggerNumber."
	::= { imageCapture 11 }

	diTriggerEntry		OBJECT-TYPE
	SYNTAX			DiTriggerEntry
	ACCESS			not-accessible
	STATUS			optional
	DESCRIPTION	"A DI trigger entry containing objects to describe the
			DI trigger."
	INDEX			{ diTriggerIndex }
	::= { diTriggerTable 1 }

	DiTriggerEntry ::=
		SEQUENCE {
			diTriggerIndex
				INTEGER,
			diTriggerEnable
				INTEGER,
			diTriggerSceneNo
				INTEGER,
			diTriggerMaxScene
				INTEGER,
			diTriggerOverwrite
				INTEGER,
			diTriggerCondition
				INTEGER,
			diTriggerTrapControl
				INTEGER,
			diTriggerTrapCount
				INTEGER,
			diTriggerSceneID
				DisplayString,
			diTriggerPreset
				INTEGER,
			diTriggerEmail
				INTEGER,
			diTriggerAttachmentEmail
				INTEGER,
			diTriggerRemoteCommand
				INTEGER,
			diTriggerRemoteCommandSet
				INTEGER,
			diTriggerSound
				INTEGER,
			diTriggerCompleteTrapControl
				INTEGER,
			diTriggerSceneBefore
				INTEGER,
			diTriggerSceneAfter
				INTEGER
		}

	diTriggerIndex		OBJECT-TYPE
	SYNTAX		INTEGER
	ACCESS		read-only
	STATUS		optional
	DESCRIPTION	"A unique value for each DI trigger. Its value ranges
			between 1 and the value diTriggerNumber."
	::= { diTriggerEntry 1 }

	diTriggerEnable		OBJECT-TYPE
	SYNTAX		INTEGER {
			    enable(1),
			    disable(2)
			}
	ACCESS		read-write
	STATUS		optional
	DESCRIPTION	"Indicates whether this device is permitted to generate
			di trigger."
	::= { diTriggerEntry 2 }

    diTriggerSceneNo	OBJECT-TYPE
	SYNTAX		INTEGER (1..2)
	ACCESS		read-write
	STATUS		optional
	DESCRIPTION	"Indicates whether this device uses which ImageScene
			entry with di trigger."
	::= { diTriggerEntry 3 }

    diTriggerMaxScene	OBJECT-TYPE
	SYNTAX		INTEGER
	ACCESS		read-write
	STATUS		optional
	DESCRIPTION	"The maximum number of scenes which saved by di
			trigger."
	::= { diTriggerEntry 4 }

    diTriggerOverwrite	OBJECT-TYPE
	SYNTAX		INTEGER {
			    enable(1),
			    disable(2)
			}
	ACCESS		read-write
	STATUS		optional
	DESCRIPTION	"Indicates whether this device is permitted to overwrite
			new scene to oldest scene by di trigger."
	::= { diTriggerEntry  5 }

    diTriggerCondition	OBJECT-TYPE
	SYNTAX		INTEGER {
			    none(1),
			    change0to1(2),
			    change1to0(3),
			    both(4)
			}
	ACCESS		read-write
	STATUS		optional
	DESCRIPTION	"Condition to generate di trigger."
	::= { diTriggerEntry 6 }

    diTriggerTrapControl	OBJECT-TYPE
	SYNTAX		INTEGER {
			    enable(1),
			    disable(2),
			    retry(3)
			}
	ACCESS		read-write
	STATUS		optional
	DESCRIPTION	"This value sets up action about the generation of
			the diTriggerTrap. When the scene begins to be
			stored by the di trigger,
			the diTriggerTrap isn't generated(disable),
			is generated(enable),
			is continuously generated(retry)."
	::= { diTriggerEntry 7 }

    diTriggerTrapCount	OBJECT-TYPE
	SYNTAX		INTEGER
	ACCESS		read-only
	STATUS		optional
	DESCRIPTION	"This value increases when the diTriggerTrap
			generated."
	::= { diTriggerEntry 8 }

    diTriggerSceneID	OBJECT-TYPE
	SYNTAX		DisplayString
	ACCESS		read-only
	STATUS		optional
	DESCRIPTION	"This string is ID of the newest stored scene.
			Initial value is NULL string."
	::= { diTriggerEntry 9 }

    diTriggerPreset		OBJECT-TYPE
	SYNTAX		INTEGER
	ACCESS		read-write
	STATUS		optional
	DESCRIPTION	"Indicates the camera preset position number to move when
			this trigger fired."
	::= { diTriggerEntry 10 }

    diTriggerEmail	OBJECT-TYPE
	SYNTAX		INTEGER {
			    enable(1),
			    disable(2)
			}
	ACCESS		read-write
	STATUS		optional
	DESCRIPTION	"This value sets up action about the generation of
			the diTriggerTrap. When the scene begins to be
			stored by the di trigger,
			the diTriggerTrap isn't generated(disable),
			is generated(enable)."
	::= { diTriggerEntry 11 }

    diTriggerAttachmentEmail OBJECT-TYPE
	SYNTAX		INTEGER {
			    none(1),
			    trigger(2),
			    scene(3)
			}
	ACCESS		read-write
	STATUS		optional
	DESCRIPTION	"This value sets up action about the attachment of
			the diTriggerEmail. When the scene begins to be
			stored by the di trigger,
			the diTriggerEmail sent without picture(none),
			with triggered picture(trigger),
			with before and after triggered pictures(scene)."
	::= { diTriggerEntry 12 }

    diTriggerRemoteCommand OBJECT-TYPE
	SYNTAX		INTEGER {
			    enable(1),
			    disable(2)
			}
	ACCESS		read-write
	STATUS		optional
	DESCRIPTION	"Indicates whether the SNMP agent process is
			permitted to generate diTrigger
			remote command."
	::= { diTriggerEntry 13 }

    diTriggerRemoteCommandSet OBJECT-TYPE
	SYNTAX		INTEGER (1..32)
	ACCESS		read-write
	STATUS		optional
	DESCRIPTION	"Indicates diTrigger
			remote command set number generated."
	::= { diTriggerEntry 14 }

    diTriggerSound OBJECT-TYPE
	SYNTAX		INTEGER {
			    enable(1),
			    disable(2)
			}
	ACCESS		read-write
	STATUS		optional
	DESCRIPTION	"Indicates whether diTrigger saves sound."
	::= { diTriggerEntry 15 }

    diTriggerCompleteTrapControl	OBJECT-TYPE
	SYNTAX		INTEGER {
			    enable(1),
			    disable(2),
			    retry(3)
			}
	ACCESS		read-write
	STATUS		optional
	DESCRIPTION	"This value sets up action about the generation of
			the diTriggerTrap. When the scene begins to be
			stored by the di trigger,
			the diTriggerTrap isn't generated(disable),
			is generated(enable),
			is continuously generated(retry)."
	::= { diTriggerEntry 16 }

    diTriggerSceneBefore OBJECT-TYPE
	SYNTAX		INTEGER
	ACCESS		read-only
	STATUS		optional
	DESCRIPTION	"Indicates how many images saved after a trigger
			occurrence."
	::= { diTriggerEntry 17 }

    diTriggerSceneAfter OBJECT-TYPE
	SYNTAX		INTEGER
	ACCESS		read-only
	STATUS		optional
	DESCRIPTION	"Indicates how many images saved after a trigger
			occurrence."
	::= { diTriggerEntry 18 }


-- MotionDetect Trigger Group

    motionDetectTrigger	OBJECT IDENTIFIER ::= { imageCapture 3 }

    motionDetectTriggerEnable	OBJECT-TYPE
	SYNTAX		INTEGER {
			    enable(1),
			    disable(2)
			}
	ACCESS		read-write
	STATUS		optional
	DESCRIPTION	"Indicates whether this device is permitted to generate
			motion trigger."
	::= { motionDetectTrigger 1 }

    motionDetectTriggerSceneNo	OBJECT-TYPE
	SYNTAX		INTEGER (1..2)
	ACCESS		read-write
	STATUS		optional
	DESCRIPTION	"Indicates whether this device uses which ImageScene
			entry with motion trigger."
	::= { motionDetectTrigger 2 }

    motionDetectTriggerMaxScene OBJECT-TYPE
	SYNTAX		INTEGER
	ACCESS		read-write
	STATUS		optional
	DESCRIPTION	"The maximum number of scenes which saved by motion
			trigger."
	::= { motionDetectTrigger 3 }

    motionDetectTriggerOverwrite OBJECT-TYPE
	SYNTAX		INTEGER {
			    enable(1),
			    disable(2)
			}
	ACCESS		read-write
	STATUS		optional
	DESCRIPTION	"Indicates whether this device is permitted to overwrite
			new scene to oldest scene by motion trigger."
	::= { motionDetectTrigger 4 }

    motionDetectTriggerRemoteCommand OBJECT-TYPE
	SYNTAX		INTEGER {
			    enable(1),
			    disable(2)
			}
	ACCESS		read-write
	STATUS		optional
	DESCRIPTION	"Indicates whether the SNMP agent process is
			permitted to generate motionDetectTrigger
			remote command."
	::= { motionDetectTrigger 5 }

    motionDetectTriggerRemoteCommandSet OBJECT-TYPE
	SYNTAX		INTEGER (1..32)
	ACCESS		read-write
	STATUS		optional
	DESCRIPTION	"Indicates motionDetectTrigger
			remote command set number generated."
	::= { motionDetectTrigger 6 }

    motionDetectTriggerSensitivity OBJECT-TYPE
	SYNTAX		INTEGER (1..5)
	ACCESS		read-write
	STATUS		optional
	DESCRIPTION	"Sensitivity to generate motion detect trigger."
	::= { motionDetectTrigger 8 }

    motionDetectTriggerDetectLX OBJECT-TYPE
	SYNTAX		INTEGER
	ACCESS		read-write
	STATUS		optional
	DESCRIPTION	"Indicates whether the X coordinate on the upper left
			of the motion detection frame."
	::= { motionDetectTrigger 9 }

    motionDetectTriggerDetectLY OBJECT-TYPE
	SYNTAX		INTEGER
	ACCESS		read-write
	STATUS		optional
	DESCRIPTION	"Indicates whether the Y coordinate on the upper left
			of the motion detection frame."
	::= { motionDetectTrigger 10 }

    motionDetectTriggerDetectRX OBJECT-TYPE
	SYNTAX		INTEGER
	ACCESS		read-write
	STATUS		optional
	DESCRIPTION	"Indicates whether the X coordinate on the lower right
			of the motion detection frame."
	::= { motionDetectTrigger 11 }

    motionDetectTriggerDetectRY OBJECT-TYPE
	SYNTAX		INTEGER
	ACCESS		read-write
	STATUS		optional
	DESCRIPTION	"Indicates whether the Y coordinate on the lower right
			of the motion detection frame."
	::= { motionDetectTrigger 12 }

    motionDetectTriggerTrapControl OBJECT-TYPE
	SYNTAX		INTEGER {
			    enable(1),
			    disable(2),
			    retry(3)
			}
	ACCESS		read-write
	STATUS		optional
	DESCRIPTION	"This value sets up action about the generation of
			the motionDetectTriggerTrap. When the scene begins to be
			stored by the motionDetect trigger,
			the motionDetectTriggerTrap isn't generated(disable),
			is generated(enable),
			is continuously generated(retry)."
	::= { motionDetectTrigger 32 }

    motionDetectTriggerTrapCount	OBJECT-TYPE
	SYNTAX		INTEGER
	ACCESS		read-write
	STATUS		optional
	DESCRIPTION	"This value increases when the motionDetectTriggerTrap
			generated.
			And on ND-VW02/03/03R, 0 is set on this value to stop
			continuously the motionDetectTriggerTrap."
	::= { motionDetectTrigger 33 }

    motionDetectTriggerSceneID	OBJECT-TYPE
	SYNTAX		DisplayString
	ACCESS		read-only
	STATUS		optional
	DESCRIPTION	"This string is ID of the newest stored scene.
			Initial value is NULL string."
	::= { motionDetectTrigger 34 }

	motionDetectTriggerCamera	OBJECT-TYPE
	SYNTAX		INTEGER
	ACCESS		read-write
	STATUS		optional
	DESCRIPTION	"Indicates which camera is used to capture image when this
			trigger is fired."
	::= { motionDetectTrigger 35 }

    motionDetectTriggerEmail OBJECT-TYPE
	SYNTAX		INTEGER {
			    enable(1),
			    disable(2)
			}
	ACCESS		read-write
	STATUS		optional
	DESCRIPTION	"This value sets up action about the generation of
			the motionDetectTriggerEmail.  When the scene begins
			to be stored by the motionDetect trigger,
			the motionDetectTriggerEmail isn't generated(disable),
			is generated(enable)."
	::= { motionDetectTrigger 36 }

    motionDetectTriggerAttachmentEmail OBJECT-TYPE
	SYNTAX		INTEGER {
			    none(1),
			    trigger(2),
			    scene(3)
			}
	ACCESS		read-write
	STATUS		optional
	DESCRIPTION	"This value sets up action about the attachment of
			the motionDetectTriggerEmail. When the scene begins
			to be stored by the motionDetect trigger,
			the motionDetectTriggerEmail sent without picture(none),
			with triggered picture(trigger),
			with before and after triggered pictures(scene)."
	::= { motionDetectTrigger 37 }

	motionDetectTriggerCaptureCameraNumber	OBJECT-TYPE
	SYNTAX		INTEGER
	ACCESS		read-only
	STATUS		optional
	DESCRIPTION	"The number of motionDetectTriggerCaptureCamera entries."
	::= { motionDetectTrigger 40 }

	motionDetectTriggerCaptureCameraTable	OBJECT-TYPE
	SYNTAX		SEQUENCE OF MotionDetectTriggerCaptureCameraEntry
	ACCESS		not-accessible
	STATUS		optional
	DESCRIPTION	"A list of motionDetectTriggerCaptureCamera table."
	::= { motionDetectTrigger 41 }

	motionDetectTriggerCaptureCameraEntry	OBJECT-TYPE
	SYNTAX		MotionDetectTriggerCaptureCameraEntry
	ACCESS		not-accessible
	STATUS		optional
	DESCRIPTION	"A motion detect trigger capture camera entry containing
			objects to describe the capture camera."
	INDEX		{ motionDetectTriggerCaptureCameraIndex }
	::= { motionDetectTriggerCaptureCameraTable 1 }

	MotionDetectTriggerCaptureCameraEntry ::=
	SEQUENCE {
		motionDetectTriggerCaptureCameraIndex
			INTEGER,
		motionDetectTriggerCaptureCameraEnable
			INTEGER
	}

	motionDetectTriggerCaptureCameraIndex	OBJECT-TYPE
	SYNTAX		INTEGER
	ACCESS		read-only
	STATUS		optional
	DESCRIPTION	"A unique value for each motionDetectTriggerCaptureCamera
			entry. Its value ranges between 1 and the value
			motionDetectCaptureCameraNumber."
	::= { motionDetectTriggerCaptureCameraEntry 1 }

	motionDetectTriggerCaptureCameraEnable	OBJECT-TYPE
	SYNTAX		INTEGER {
					enable(1),
					disable(2)
				}
	ACCESS		read-write
	STATUS		optional
	DESCRIPTION	"Indicates whether this device permitted to capture
			images with this motionDetectTriggerCaptureCameraEntry."
	::= { motionDetectTriggerCaptureCameraEntry 2 }

-- Manual Trigger Group

    manualTrigger	OBJECT IDENTIFIER ::= { imageCapture 4 }

    manualTriggerEnable	OBJECT-TYPE
	SYNTAX		INTEGER {
			    enable(1),
			    disable(2)
			}
	ACCESS		read-write
	STATUS		optional
	DESCRIPTION	"Indicates whether this device is permitted to generate
			manual trigger."
	::= { manualTrigger 1 }

    manualTriggerSceneNo	OBJECT-TYPE
	SYNTAX		INTEGER (1..2)
	ACCESS		read-write
	STATUS		optional
	DESCRIPTION	"Indicates whether this device uses which ImageScene
			entry with manual trigger."
	::= { manualTrigger 2 }

    manualTriggerMaxScene OBJECT-TYPE
	SYNTAX		INTEGER
	ACCESS		read-write
	STATUS		optional
	DESCRIPTION	"The maximum number of scenes which saved by manual
			trigger."
	::= { manualTrigger 3 }

    manualTriggerOverwrite OBJECT-TYPE
	SYNTAX		INTEGER {
			    enable(1),
			    disable(2)
			}
	ACCESS		read-write
	STATUS		optional
	DESCRIPTION	"Indicates whether this device is permitted to overwrite
			new scene to oldest scene by manual trigger."
	::= { manualTrigger 4 }

    manualTriggerRemoteCommand OBJECT-TYPE
	SYNTAX		INTEGER {
			    enable(1),
			    disable(2)
			}
	ACCESS		read-write
	STATUS		optional
	DESCRIPTION	"Indicates whether the SNMP agent process is
			permitted to generate manualTrigger
			remote command."
	::= { manualTrigger 5 }

    manualTriggerRemoteCommandSet OBJECT-TYPE
	SYNTAX		INTEGER (1..32)
	ACCESS		read-write
	STATUS		optional
	DESCRIPTION	"Indicates singleManualTrigger
			remote command set number generated."
	::= { manualTrigger 6 }

    manualTriggerGenerate OBJECT-TYPE
	SYNTAX		INTEGER {
			    trigger(1)
			}
	ACCESS		read-write
	STATUS		optional
	DESCRIPTION	"Setting to any value will generate manual trigger.
			When read this will always return 0."
	::= { manualTrigger 8 }

    manualTriggerTrapControl OBJECT-TYPE
	SYNTAX		INTEGER {
			    enable(1),
			    disable(2),
			    retry(3)
			}
	ACCESS		read-write
	STATUS		optional
	DESCRIPTION	"This value sets up action about the generation of
			the manualTriggerTrap. When the scene begins to be
			stored by the manual trigger,
			the manualTriggerTrap isn't generated(disable),
			is generated(enable),
			is continuously generated(retry)."
	::= { manualTrigger 32 }

    manualTriggerTrapCount	OBJECT-TYPE
	SYNTAX		INTEGER
	ACCESS		read-write
	STATUS		optional
	DESCRIPTION	"This value increases when the manualTriggerTrap
			generated.
			And on ND-VW02/03/03R, 0 is set on this value to stop
			continuously the manualTriggerTrap."
	::= { manualTrigger 33 }

    manualTriggerSceneID	OBJECT-TYPE
	SYNTAX		DisplayString
	ACCESS		read-only
	STATUS		optional
	DESCRIPTION	"This string is ID of the newest stored scene.
			Initial value is NULL string."
	::= { manualTrigger 34 }

    manualTriggerCamera		OBJECT-TYPE
	SYNTAX		INTEGER
	ACCESS		read-write
	STATUS		optional
	DESCRIPTION	"Indicates which camera is used to capture image when this
			trigger is fired."
	::= { manualTrigger 35 }

    manualTriggerPreset		OBJECT-TYPE
	SYNTAX		INTEGER
	ACCESS		read-write
	STATUS		optional
	DESCRIPTION	"Indicates the camera preset position number to move when
			this trigger fired."
	::= { manualTrigger 36 }

    manualTriggerEmail OBJECT-TYPE
	SYNTAX		INTEGER {
			    enable(1),
			    disable(2)
			}
	ACCESS		read-write
	STATUS		optional
	DESCRIPTION	"This value sets up action about the generation of
			the manualTriggerEmail. When the scene begins to be
			stored by the manual trigger,
			the manualTriggerEmail isn't generated(disable),
			is generated(enable)."
	::= { manualTrigger 37 }

    manualTriggerAttachmentEmail OBJECT-TYPE
	SYNTAX		INTEGER {
			    none(1),
			    trigger(2),
			    scene(3)
			}
	ACCESS		read-write
	STATUS		optional
	DESCRIPTION	"This value sets up action about the attachment of
			the manualTriggerEmail. When the scene begins to be
			stored by the manual trigger,
			the manualTriggerEmail sent without picture(none),
			with triggered picture(trigger),
			with before and after triggered pictures(scene)."
	::= { manualTrigger 38 }


    multiManualTriggerNumber		OBJECT-TYPE
	SYNTAX				INTEGER
	ACCESS				read-only
	STATUS				optional
	DESCRIPTION	"The number of manual triggers supported by this device."
	::= { imageCapture 12 }

    multiManualTriggerTable		OBJECT-TYPE
	SYNTAX				SEQUENCE OF MultiManualTriggerEntry
	ACCESS				not-accessible
	STATUS				optional
	DESCRIPTION	"A list of manual trigger entries. The number of entries
			is given by the value multiManualTriggerNumber."
	::= { imageCapture 13 }

    multiManualTriggerEntry		OBJECT-TYPE
	SYNTAX			MultiManualTriggerEntry
	ACCESS			not-accessible
	STATUS			optional
	DESCRIPTION	"A manual trigger entry containing objects to describe the
			manual trigger."
	INDEX			{ multiManualTriggerIndex }
	::= { multiManualTriggerTable 1 }

	MultiManualTriggerEntry ::=
		SEQUENCE {
			multiManualTriggerIndex
				INTEGER,
			multiManualTriggerEnable
				INTEGER,
			multiManualTriggerSceneNo
				INTEGER,
			multiManualTriggerMaxScene
				INTEGER,
			multiManualTriggerOverwrite
				INTEGER,
			multiManualTriggerGenerate
				INTEGER,
			multiManualTriggerTrapControl
				INTEGER,
			multiManualTriggerTrapCount
				INTEGER,
			multiManualTriggerSceneID
				DisplayString,
			multiManualTriggerPreset
				INTEGER,
			multiManualTriggerEmail
				INTEGER,
			multiManualTriggerAttachmentEmail
				INTEGER,
			multiManualTriggerRemoteCommand
				INTEGER,
			multiManualTriggerRemoteCommandSet
				INTEGER,
			multiManualTriggerSound
				INTEGER,
			multiManualTriggerCompleteTrapControl
				INTEGER,
			multiManualTriggerSceneBefore
				INTEGER,
			multiManualTriggerSceneAfter
				INTEGER
		}

    multiManualTriggerIndex		OBJECT-TYPE
	SYNTAX		INTEGER
	ACCESS		read-only
	STATUS		optional
	DESCRIPTION	"A unique value for each manual trigger. Its value ranges
			between 1 and the value multiManualTriggerNumber."
	::= { multiManualTriggerEntry 1 }

    multiManualTriggerEnable	OBJECT-TYPE
	SYNTAX		INTEGER {
			    enable(1),
			    disable(2)
			}
	ACCESS		read-write
	STATUS		optional
	DESCRIPTION	"Indicates whether this device is permitted to generate
			manual trigger."
	::= { multiManualTriggerEntry 2 }

    multiManualTriggerSceneNo	OBJECT-TYPE
	SYNTAX		INTEGER (1..2)
	ACCESS		read-write
	STATUS		optional
	DESCRIPTION	"Indicates whether this device uses which ImageScene
			entry with manual trigger."
	::= { multiManualTriggerEntry 3 }

    multiManualTriggerMaxScene OBJECT-TYPE
	SYNTAX		INTEGER
	ACCESS		read-write
	STATUS		optional
	DESCRIPTION	"The maximum number of scenes which saved by manual
			trigger."
	::= { multiManualTriggerEntry 4 }

    multiManualTriggerOverwrite OBJECT-TYPE
	SYNTAX		INTEGER {
			    enable(1),
			    disable(2)
			}
	ACCESS		read-write
	STATUS		optional
	DESCRIPTION	"Indicates whether this device is permitted to overwrite
			new scene to oldest scene by manual trigger."
	::= { multiManualTriggerEntry 5 }

    multiManualTriggerGenerate OBJECT-TYPE
	SYNTAX		INTEGER {
			    trigger(1)
			}
	ACCESS		read-write
	STATUS		optional
	DESCRIPTION	"Setting to any value will generate manual trigger.
			When read this will always return 0."
	::= { multiManualTriggerEntry 6 }

    multiManualTriggerTrapControl OBJECT-TYPE
	SYNTAX		INTEGER {
			    enable(1),
			    disable(2),
			    retry(3)
			}
	ACCESS		read-write
	STATUS		optional
	DESCRIPTION	"This value sets up action about the generation of
			the manualTriggerTrap. When the scene begins to be
			stored by the manual trigger,
			the manualTriggerTrap isn't generated(disable),
			is generated(enable),
			is continuously generated(retry)."
	::= { multiManualTriggerEntry 7 }

    multiManualTriggerTrapCount	OBJECT-TYPE
	SYNTAX		INTEGER
	ACCESS		read-only
	STATUS		optional
	DESCRIPTION	"This value increases when the manualTriggerTrap
			generated."
	::= { multiManualTriggerEntry 8 }

    multiManualTriggerSceneID	OBJECT-TYPE
	SYNTAX		DisplayString
	ACCESS		read-only
	STATUS		optional
	DESCRIPTION	"This string is ID of the newest stored scene.
			Initial value is NULL string."
	::= { multiManualTriggerEntry 9 }

    multiManualTriggerPreset		OBJECT-TYPE
	SYNTAX		INTEGER
	ACCESS		read-write
	STATUS		optional
	DESCRIPTION	"Indicates the camera preset position number to move when
			this trigger fired."
	::= { multiManualTriggerEntry 10 }

    multiManualTriggerEmail 		OBJECT-TYPE
	SYNTAX		INTEGER {
			    enable(1),
			    disable(2)
			}
	ACCESS		read-write
	STATUS		optional
	DESCRIPTION	"This value sets up action about the generation of
			the manualTriggerEmail. When the scene begins to be
			stored by the manual trigger,
			the manualTriggerEmail isn't generated(disable),
			is generated(enable)."
	::= { multiManualTriggerEntry 11 }

    multiManualTriggerAttachmentEmail OBJECT-TYPE
	SYNTAX		INTEGER {
			    none(1),
			    trigger(2),
			    scene(3)
			}
	ACCESS		read-write
	STATUS		optional
	DESCRIPTION	"This value sets up action about the attachment of
			the manualTriggerEmail. When the scene begins to be
			stored by the manual trigger,
			the manualTriggerEmail sent without picture(none),
			with triggered picture(trigger),
			with before and after triggered pictures(scene)."
	::= { multiManualTriggerEntry 12 }

    multiManualTriggerRemoteCommand OBJECT-TYPE
	SYNTAX		INTEGER {
			    enable(1),
			    disable(2)
			}
	ACCESS		read-write
	STATUS		optional
	DESCRIPTION	"Indicates whether the SNMP agent process is
			permitted to generate manualTrigger
			remote command."
	::= { multiManualTriggerEntry 13 }

    multiManualTriggerRemoteCommandSet OBJECT-TYPE
	SYNTAX		INTEGER (1..32)
	ACCESS		read-write
	STATUS		optional
	DESCRIPTION	"Indicates manualTrigger
			remote command set number generated."
	::= { multiManualTriggerEntry 14 }

    multiManualTriggerSound OBJECT-TYPE
	SYNTAX		INTEGER {
			    enable(1),
			    disable(2)
			}
	ACCESS		read-write
	STATUS		optional
	DESCRIPTION	"Indicates whether manualTrigger saves sound."
	::= { multiManualTriggerEntry 15 }

    multiManualTriggerCompleteTrapControl OBJECT-TYPE
	SYNTAX		INTEGER {
			    enable(1),
			    disable(2),
			    retry(3)
			}
	ACCESS		read-write
	STATUS		optional
	DESCRIPTION	"This value sets up action about the generation of
			the manualTriggerTrap. When the scene begins to be
			stored by the manual trigger,
			the manualTriggerTrap isn't generated(disable),
			is generated(enable),
			is continuously generated(retry)."
	::= { multiManualTriggerEntry 16 }

    multiManualTriggerSceneBefore OBJECT-TYPE
	SYNTAX		INTEGER
	ACCESS		read-only
	STATUS		optional
	DESCRIPTION	"Indicates how many images saved after a trigger
			occurrence."
	::= { multiManualTriggerEntry 17 }

    multiManualTriggerSceneAfter OBJECT-TYPE
	SYNTAX		INTEGER
	ACCESS		read-only
	STATUS		optional
	DESCRIPTION	"Indicates how many images saved after a trigger
			occurrence."
	::= { multiManualTriggerEntry 18 }

    multiManualTriggerGenerateAll OBJECT-TYPE
	SYNTAX		INTEGER {
			    trigger(1)
			}
	ACCESS		read-write
	STATUS		optional
	DESCRIPTION	"Setting to any value will generate all manual trigger.
			When read this will always return 0."
	::= { imageCapture 14 }


-- Multi MotionDetect Trigger Group


    multiMotionDetectTriggerNumber		OBJECT-TYPE
	SYNTAX				INTEGER
	ACCESS				read-only
	STATUS				optional
	DESCRIPTION	"The number of motion detect triggers supported by this device."
	::= { imageCapture 15 }

    multiMotionDetectTriggerTable		OBJECT-TYPE
	SYNTAX				SEQUENCE OF MultiMotionDetectTriggerEntry
	ACCESS				not-accessible
	STATUS				optional
	DESCRIPTION	"A list of motion detect trigger entries. The number of entries
			is given by the value multiMotionDetectTriggerNumber."
	::= { imageCapture 16 }

    multiMotionDetectTriggerEntry		OBJECT-TYPE
	SYNTAX			MultiMotionDetectTriggerEntry
	ACCESS			not-accessible
	STATUS			optional
	DESCRIPTION	"A motion detect trigger entry containing objects to describe the
			motion detect trigger."
	INDEX			{ multiMotionDetectTriggerIndex }
	::= { multiMotionDetectTriggerTable 1 }

    MultiMotionDetectTriggerEntry ::=
		SEQUENCE {
			multiMotionDetectTriggerIndex
				INTEGER,
			multiMotionDetectTriggerEnable
				INTEGER,
			multiMotionDetectTriggerSceneNo
				INTEGER,
			multiMotionDetectTriggerMaxScene
				INTEGER,
			multiMotionDetectTriggerOverwrite
				INTEGER,
			multiMotionDetectTriggerSensitivity
				INTEGER,
			multiMotionDetectTriggerTrapControl
				INTEGER,
			multiMotionDetectTriggerTrapCount
				INTEGER,
			multiMotionDetectTriggerSceneID
				DisplayString,
			multiMotionDetectTriggerEmail
				INTEGER,
			multiMotionDetectTriggerAttachmentEmail
				INTEGER,
			multiMotionDetectTriggerRemoteCommand
				INTEGER,
			multiMotionDetectTriggerRemoteCommandSet
				INTEGER,
			multiMotionDetectTriggerSound
				INTEGER,
			multiMotionDetectTriggerCompleteTrapControl
				INTEGER,
			multiMotionDetectTriggerSceneBefore
				INTEGER,
			multiMotionDetectTriggerSceneAfter
				INTEGER,
			multiMotionDetectTriggerDetect1LX
				INTEGER,
			multiMotionDetectTriggerDetect1LY
				INTEGER,
			multiMotionDetectTriggerDetect1RX
				INTEGER,
			multiMotionDetectTriggerDetect1RY
				INTEGER,
			multiMotionDetectTriggerDetect2LX
				INTEGER,
			multiMotionDetectTriggerDetect2LY
				INTEGER,
			multiMotionDetectTriggerDetect2RX
				INTEGER,
			multiMotionDetectTriggerDetect2RY
				INTEGER,
			multiMotionDetectTriggerDetect3LX
				INTEGER,
			multiMotionDetectTriggerDetect3LY
				INTEGER,
			multiMotionDetectTriggerDetect3RX
				INTEGER,
			multiMotionDetectTriggerDetect3RY
				INTEGER,
			multiMotionDetectTriggerDetect4LX
				INTEGER,
			multiMotionDetectTriggerDetect4LY
				INTEGER,
			multiMotionDetectTriggerDetect4RX
				INTEGER,
			multiMotionDetectTriggerDetect4RY
				INTEGER
		}

    multiMotionDetectTriggerIndex	OBJECT-TYPE
	SYNTAX		INTEGER
	ACCESS		read-only
	STATUS		optional
	DESCRIPTION	"A unique value for each motion detect trigger. Its value ranges
			between 1 and the value multiMotionDetectTriggerNumber."
	::= { multiMotionDetectTriggerEntry 1 }

    multiMotionDetectTriggerEnable	OBJECT-TYPE
	SYNTAX		INTEGER {
			    enable(1),
			    disable(2)
			}
	ACCESS		read-write
	STATUS		optional
	DESCRIPTION	"Indicates whether this device is permitted to generate
			motion detect trigger."
	::= { multiMotionDetectTriggerEntry 2 }

    multiMotionDetectTriggerSceneNo	OBJECT-TYPE
	SYNTAX		INTEGER (1..2)
	ACCESS		read-write
	STATUS		optional
	DESCRIPTION	"Indicates whether this device uses which ImageScene
			entry with motion detect trigger."
	::= { multiMotionDetectTriggerEntry 3 }

    multiMotionDetectTriggerMaxScene OBJECT-TYPE
	SYNTAX		INTEGER
	ACCESS		read-write
	STATUS		optional
	DESCRIPTION	"The maximum number of scenes which saved by motion detect
			trigger."
	::= { multiMotionDetectTriggerEntry 4 }

    multiMotionDetectTriggerOverwrite OBJECT-TYPE
	SYNTAX		INTEGER {
			    enable(1),
			    disable(2)
			}
	ACCESS		read-write
	STATUS		optional
	DESCRIPTION	"Indicates whether this device is permitted to overwrite
			new scene to oldest scene by motion detect trigger."
	::= { multiMotionDetectTriggerEntry 5 }

    multiMotionDetectTriggerMode	OBJECT-TYPE
	SYNTAX		INTEGER {
			    move(1),
			    stop(2)
			}
	ACCESS		read-write
	STATUS		optional
	DESCRIPTION	"Sensitivity to generate motion detect trigger."
	::= { multiMotionDetectTriggerEntry 6 }

    multiMotionDetectTriggerSensitivity OBJECT-TYPE
	SYNTAX		INTEGER (1..16)
	ACCESS		read-write
	STATUS		optional
	DESCRIPTION	"Sensitivity to generate motion detect trigger."
	::= { multiMotionDetectTriggerEntry 7 }

    multiMotionDetectTriggerTrapControl OBJECT-TYPE
	SYNTAX		INTEGER {
			    enable(1),
			    disable(2),
			    retry(3)
			}
	ACCESS		read-write
	STATUS		optional
	DESCRIPTION	"This value sets up action about the generation of
			the motionDetectTriggerTrap. When the scene begins to be
			stored by the motionDetect trigger,
			the motionDetectTriggerTrap isn't generated(disable),
			is generated(enable),
			is continuously generated(retry)."
	::= { multiMotionDetectTriggerEntry 8 }

    multiMotionDetectTriggerTrapCount	OBJECT-TYPE
	SYNTAX		INTEGER
	ACCESS		read-only
	STATUS		optional
	DESCRIPTION	"This value increases when the motionDetectTriggerTrap
			generated."
	::= { multiMotionDetectTriggerEntry 9 }

    multiMotionDetectTriggerSceneID	OBJECT-TYPE
	SYNTAX		DisplayString
	ACCESS		read-only
	STATUS		optional
	DESCRIPTION	"This string is ID of the newest stored scene.
			Initial value is NULL string."
	::= { multiMotionDetectTriggerEntry 10 }

    multiMotionDetectTriggerEmail OBJECT-TYPE
	SYNTAX		INTEGER {
			    enable(1),
			    disable(2)
			}
	ACCESS		read-write
	STATUS		optional
	DESCRIPTION	"This value sets up action about the generation of
			the motionDetectTriggerEmail.  When the scene begins
			to be stored by the motionDetect trigger,
			the motionDetectTriggerEmail isn't generated(disable),
			is generated(enable)."
	::= { multiMotionDetectTriggerEntry 11 }

    multiMotionDetectTriggerAttachmentEmail OBJECT-TYPE
	SYNTAX		INTEGER {
			    none(1),
			    trigger(2),
			    scene(3)
			}
	ACCESS		read-write
	STATUS		optional
	DESCRIPTION	"This value sets up action about the attachment of
			the motionDetectTriggerEmail. When the scene begins
			to be stored by the motionDetect trigger,
			the motionDetectTriggerEmail sent without picture(none),
			with triggered picture(trigger),
			with before and after triggered pictures(scene)."
	::= { multiMotionDetectTriggerEntry 12 }

    multiMotionDetectTriggerRemoteCommand OBJECT-TYPE
	SYNTAX		INTEGER {
			    enable(1),
			    disable(2)
			}
	ACCESS		read-write
	STATUS		optional
	DESCRIPTION	"Indicates whether the SNMP agent process is
			permitted to generate motionDetectTrigger
			remote command."
	::= { multiMotionDetectTriggerEntry 13 }

    multiMotionDetectTriggerRemoteCommandSet OBJECT-TYPE
	SYNTAX		INTEGER (1..32)
	ACCESS		read-write
	STATUS		optional
	DESCRIPTION	"Indicates motionDetectTrigger
			remote command set number generated."
	::= { multiMotionDetectTriggerEntry 14 }

    multiMotionDetectTriggerSound OBJECT-TYPE
	SYNTAX		INTEGER {
			    enable(1),
			    disable(2)
			}
	ACCESS		read-write
	STATUS		optional
	DESCRIPTION	"Indicates whether motionDetectTrigger saves sound."
	::= { multiMotionDetectTriggerEntry 15 }

    multiMotionDetectTriggerCompleteTrapControl OBJECT-TYPE
	SYNTAX		INTEGER {
			    enable(1),
			    disable(2),
			    retry(3)
			}
	ACCESS		read-write
	STATUS		optional
	DESCRIPTION	"This value sets up action about the generation of
			the motionDetectTriggerTrap. When the scene begins to be
			stored by the motionDetect trigger,
			the motionDetectTriggerTrap isn't generated(disable),
			is generated(enable),
			is continuously generated(retry)."
	::= { multiMotionDetectTriggerEntry 16 }

    multiMotionDetectTriggerSceneBefore OBJECT-TYPE
	SYNTAX		INTEGER
	ACCESS		read-only
	STATUS		optional
	DESCRIPTION	"Indicates how many images saved after a trigger
			occurrence."
	::= { multiMotionDetectTriggerEntry 17 }

    multiMotionDetectTriggerSceneAfter OBJECT-TYPE
	SYNTAX		INTEGER
	ACCESS		read-only
	STATUS		optional
	DESCRIPTION	"Indicates how many images saved after a trigger
			occurrence."
	::= { multiMotionDetectTriggerEntry 18 }

    multiMotionDetectTriggerDetect1LX OBJECT-TYPE
	SYNTAX		INTEGER
	ACCESS		read-write
	STATUS		optional
	DESCRIPTION	"Indicates whether the X coordinate on the upper left
			of the motion detection frame 1."
	::= { multiMotionDetectTriggerEntry 63 }

    multiMotionDetectTriggerDetect1LY OBJECT-TYPE
	SYNTAX		INTEGER
	ACCESS		read-write
	STATUS		optional
	DESCRIPTION	"Indicates whether the Y coordinate on the upper left
			of the motion detection frame 1."
	::= { multiMotionDetectTriggerEntry 64 }

    multiMotionDetectTriggerDetect1RX OBJECT-TYPE
	SYNTAX		INTEGER
	ACCESS		read-write
	STATUS		optional
	DESCRIPTION	"Indicates whether the X coordinate on the lower right
			of the motion detection frame 1."
	::= { multiMotionDetectTriggerEntry 65 }

    multiMotionDetectTriggerDetect1RY OBJECT-TYPE
	SYNTAX		INTEGER
	ACCESS		read-write
	STATUS		optional
	DESCRIPTION	"Indicates whether the Y coordinate on the lower right
			of the motion detection frame 1."
	::= { multiMotionDetectTriggerEntry 66 }


    multiMotionDetectTriggerDetect2LX OBJECT-TYPE
	SYNTAX		INTEGER
	ACCESS		read-write
	STATUS		optional
	DESCRIPTION	"Indicates whether the X coordinate on the upper left
			of the motion detection frame 2."
	::= { multiMotionDetectTriggerEntry 67 }

    multiMotionDetectTriggerDetect2LY OBJECT-TYPE
	SYNTAX		INTEGER
	ACCESS		read-write
	STATUS		optional
	DESCRIPTION	"Indicates whether the Y coordinate on the upper left
			of the motion detection frame 2."
	::= { multiMotionDetectTriggerEntry 68 }

    multiMotionDetectTriggerDetect2RX OBJECT-TYPE
	SYNTAX		INTEGER
	ACCESS		read-write
	STATUS		optional
	DESCRIPTION	"Indicates whether the X coordinate on the lower right
			of the motion detection frame 2."
	::= { multiMotionDetectTriggerEntry 69 }

    multiMotionDetectTriggerDetect2RY OBJECT-TYPE
	SYNTAX		INTEGER
	ACCESS		read-write
	STATUS		optional
	DESCRIPTION	"Indicates whether the Y coordinate on the lower right
			of the motion detection frame 2."
	::= { multiMotionDetectTriggerEntry 70 }


    multiMotionDetectTriggerDetect3LX OBJECT-TYPE
	SYNTAX		INTEGER
	ACCESS		read-write
	STATUS		optional
	DESCRIPTION	"Indicates whether the X coordinate on the upper left
			of the motion detection frame 3."
	::= { multiMotionDetectTriggerEntry 71 }

    multiMotionDetectTriggerDetect3LY OBJECT-TYPE
	SYNTAX		INTEGER
	ACCESS		read-write
	STATUS		optional
	DESCRIPTION	"Indicates whether the Y coordinate on the upper left
			of the motion detection frame 3."
	::= { multiMotionDetectTriggerEntry 72 }

    multiMotionDetectTriggerDetect3RX OBJECT-TYPE
	SYNTAX		INTEGER
	ACCESS		read-write
	STATUS		optional
	DESCRIPTION	"Indicates whether the X coordinate on the lower right
			of the motion detection frame 3."
	::= { multiMotionDetectTriggerEntry 73 }

    multiMotionDetectTriggerDetect3RY OBJECT-TYPE
	SYNTAX		INTEGER
	ACCESS		read-write
	STATUS		optional
	DESCRIPTION	"Indicates whether the Y coordinate on the lower right
			of the motion detection frame 3."
	::= { multiMotionDetectTriggerEntry 74 }


    multiMotionDetectTriggerDetect4LX OBJECT-TYPE
	SYNTAX		INTEGER
	ACCESS		read-write
	STATUS		optional
	DESCRIPTION	"Indicates whether the X coordinate on the upper left
			of the motion detection frame 4."
	::= { multiMotionDetectTriggerEntry 75 }

    multiMotionDetectTriggerDetect4LY OBJECT-TYPE
	SYNTAX		INTEGER
	ACCESS		read-write
	STATUS		optional
	DESCRIPTION	"Indicates whether the Y coordinate on the upper left
			of the motion detection frame 4."
	::= { multiMotionDetectTriggerEntry 76 }

    multiMotionDetectTriggerDetect4RX OBJECT-TYPE
	SYNTAX		INTEGER
	ACCESS		read-write
	STATUS		optional
	DESCRIPTION	"Indicates whether the X coordinate on the lower right
			of the motion detection frame 4."
	::= { multiMotionDetectTriggerEntry 77 }

    multiMotionDetectTriggerDetect4RY OBJECT-TYPE
	SYNTAX		INTEGER
	ACCESS		read-write
	STATUS		optional
	DESCRIPTION	"Indicates whether the Y coordinate on the lower right
			of the motion detection frame 4."
	::= { multiMotionDetectTriggerEntry 78 }


-- Trigger Control

    triggerControl	OBJECT-TYPE
	SYNTAX		INTEGER {
			    enable(1),
			    at0-enable(2),
			    at1-enable(3),
			    disable(4)
			}
	ACCESS		read-write
	STATUS		optional
	DESCRIPTION	"Indicates whether this device is controlled to generate
			any trigger."
	::= { imageCapture 5 }

-- Image Scene Group

    imageSceneNumber	OBJECT-TYPE
	SYNTAX		INTEGER
	ACCESS		read-only
	STATUS		optional
	DESCRIPTION	"The number of imageScene entries."
	::= { imageCapture 6 }

-- The Image Scene table
--
-- This table contains imageSceneNumber entries describing each Image Scene.
--

    imageSceneTable	OBJECT-TYPE
	SYNTAX		SEQUENCE OF ImageSceneEntry
	ACCESS		not-accessible
	STATUS		optional
	DESCRIPTION	"A list of the imageScene entries."
	::= { imageCapture 7 }

    imageSceneEntry	OBJECT-TYPE
	SYNTAX		ImageSceneEntry
	ACCESS		not-accessible
	STATUS		optional
	DESCRIPTION	"A imageScene entry containing objects to
			describe the image scene."
	INDEX		{ imageSceneIndex }
	::= { imageSceneTable 1 }

    ImageSceneEntry ::=
	SEQUENCE {
	    imageSceneIndex
		INTEGER,
	    imageSceneSize
		INTEGER,
	    imageSceneQuality
		INTEGER,
	    imageSceneInterval
		INTEGER,
	    imageSceneTriggerBefore
		INTEGER,
	    imageSceneTriggerAfter
		INTEGER
        }

    imageSceneIndex	OBJECT-TYPE
	SYNTAX		INTEGER
	ACCESS		read-only
	STATUS		optional
	DESCRIPTION	"A unique value for each imageScene entry. It's value
			ranges between 1 and the value imageSceneNumber."
	::= { imageSceneEntry 1 }

    imageSceneSize	OBJECT-TYPE
	SYNTAX		INTEGER {
			    size640x480(1),
			    size320x240(2),
			    size160x120(3),
			    size640x240(4)
			}
	ACCESS		read-write
	STATUS		optional
	DESCRIPTION	"Indicates whether this device uses which image size."
	::= { imageSceneEntry 2 }

    imageSceneQuality	OBJECT-TYPE
	SYNTAX		INTEGER {
			    high(1),
			    middle(2),
			    low(3)
			}
	ACCESS		read-write
	STATUS		optional
	DESCRIPTION	"Indicates whether this device uses which image
			quality."
	::= { imageSceneEntry 3 }

    imageSceneInterval	OBJECT-TYPE
	SYNTAX		INTEGER
	ACCESS		read-write
	STATUS		optional
	DESCRIPTION	"The interval in 100 milliseconds(1 = 100ms) to
			save image."
	::= { imageSceneEntry 4 }

    imageSceneTriggerBefore OBJECT-TYPE
	SYNTAX		INTEGER
	ACCESS		read-write
	STATUS		optional
	DESCRIPTION	"Indicates how many images saved before a trigger
			occurrence."
	::= { imageSceneEntry 5 }

    imageSceneTriggerAfter OBJECT-TYPE
	SYNTAX		INTEGER
	ACCESS		read-write
	STATUS		optional
	DESCRIPTION	"Indicates how many images saved after a trigger
			occurrence."
	::= { imageSceneEntry 6 }

-- The Camera Control Group

    singleCameraControl	OBJECT IDENTIFIER ::= { imageCapture 8 }

    singleCameraInterface	OBJECT-TYPE
	SYNTAX		INTEGER {
			    ntsc(1),
			    s-video(2)
			}
	ACCESS		read-write
	STATUS		optional
	DESCRIPTION	"Indicates what type of interface for camera."
	::= { singleCameraControl 1 }

    singleCameraType		OBJECT-TYPE
	SYNTAX		INTEGER {
			    auto(1),
			    unknown(2),
			    sony-evi-g20(257),
			    sony-evi-d30(258),
			    canon-vc-c3(513),
			    canon-vc-c50i(514),
			    nisca-nc-2(769),
			    victor-tk-am200(1025),
			    mikami-ptc-107hu(1281),
			    mikami-camera(1282),
			    nec-nc-21d(1537)
			}
	ACCESS		read-write
	STATUS		optional
	DESCRIPTION	"Indicates what type of camera is connected.
			auto means that this device will auto detect the camera
			is connected."
	::= { singleCameraControl 2 }

    cameraNumber	OBJECT-TYPE
	SYNTAX			INTEGER
	ACCESS			read-only
	STATUS			optional
	DESCRIPTION	"The number of cameras supported by this device."
	::= { imageCapture 20 }

    cameraTable	OBJECT-TYPE
	SYNTAX		SEQUENCE OF CameraEntry
	ACCESS		not-accessible
	STATUS		optional
	DESCRIPTION	"A list of camera entries. The number of entries
			is given by the value cameraNumber."
	::= { imageCapture 21 }

    cameraEntry	OBJECT-TYPE
	SYNTAX		CameraEntry
	ACCESS		not-accessible
	STATUS		optional
	DESCRIPTION	"A camera entry containing objects to describe the
			camera."
	INDEX		{ cameraIndex }
	::= { cameraTable 1 }

	CameraEntry ::=
		SEQUENCE {
			cameraIndex
				INTEGER,
			cameraInterface
				INTEGER,
			cameraType
				INTEGER,
			cameraSIO
				INTEGER,
			cameraSyncWait
				INTEGER,
			cameraAGC
				INTEGER,
			cameraGain
				INTEGER,
			cameraHOffset
				INTEGER,
			cameraVOffset
				INTEGER,
			cameraTitle
				DisplayString,
			cameraSize
				INTEGER,
			cameraQuality
				INTEGER,
			cameraBright
				INTEGER,
			cameraID
				INTEGER,
			cameraDataSize640x480High
				INTEGER,
			cameraDataSize640x480Middle
				INTEGER,
			cameraDataSize640x480Low
				INTEGER,
			cameraDataSize320x240High
				INTEGER,
			cameraDataSize320x240Middle
				INTEGER,
			cameraDataSize320x240Low
				INTEGER,
			cameraDataSize160x120High
				INTEGER,
			cameraDataSize160x120Middle
				INTEGER,
			cameraDataSize160x120Low
				INTEGER,
			cameraDataSize640x480HalfHigh
				INTEGER,
			cameraDataSize640x480HalfMiddle
				INTEGER,
			cameraDataSize640x480HalfLow
				INTEGER
		}

    cameraIndex	OBJECT-TYPE
	SYNTAX		INTEGER
	ACCESS		read-only
	STATUS		optional
	DESCRIPTION	"A unique value for each camera. Its value ranges
			between 1 and the value cameraNumber."
	::= { cameraEntry 1 }

    cameraInterface	OBJECT-TYPE
	SYNTAX		INTEGER {
				    ntsc(1),
				    s-video(2)
			}
	ACCESS		read-write
	STATUS		optional
	DESCRIPTION	"Indicates what type of interface for camera."
	::= { cameraEntry 2 }

    cameraType	OBJECT-TYPE
	SYNTAX		INTEGER {
				auto(1),
				unknown(2),
				sony-evi-g20(257),
				sony-evi-d30(258),
				canon-vc-c3(513),
				canon-vc-c50i(514),
				nisca-nc-2(769),
				victor-tk-am200(1025),
				mikami-ptc-107hu(1281),
				mikami-camera(1282),
				nec-nc-21d(1537),
				mitsubishi-melook-g(1793)
			}
	ACCESS		read-write
	STATUS		optional
	DESCRIPTION	"Indicates what type of camera is connected.
			auto means that this device will auto detect the camera
			is connected."
	::= { cameraEntry 3 }

    cameraSIO	OBJECT-TYPE
	SYNTAX		INTEGER {
				sio1(1),
				sio2(2)
			}
	ACCESS		read-write
	STATUS		optional
	DESCRIPTION	"Indicates which SIO port is connected to the camera.
			The value 0 means that no SIO port is selected."
	::= { cameraEntry 4 }

    cameraSyncWait	OBJECT-TYPE
	SYNTAX			INTEGER (-1..1000)
	ACCESS			read-write
	STATUS			optional
	DESCRIPTION	"Indicates waiting time for VIDEO-INPUT stabled."
	::= { cameraEntry 5 }

    cameraAGC	OBJECT-TYPE
	SYNTAX		INTEGER {
					enable(1),
					disable(2)
				}
	ACCESS		read-write
	STATUS		optional
	DESCRIPTION	"Indicates whether the AGC facility is enabled."
	::= { cameraEntry 6 }

    cameraGain	OBJECT-TYPE
	SYNTAX		INTEGER (-1..63)
	ACCESS		read-write
	STATUS		optional
	DESCRIPTION	"Indicates the GAIN value."
	::= { cameraEntry 7 }

    cameraHOffset	OBJECT-TYPE
	SYNTAX			INTEGER (-1..1023)
	ACCESS			read-write
	STATUS			optional
	DESCRIPTION	"Indicates the horizontal offset of image output."
	::= { cameraEntry 8 }

    cameraVOffset	OBJECT-TYPE
	SYNTAX			INTEGER (-1..1023)
	ACCESS			read-write
	STATUS			optional
	DESCRIPTION	"Indicates the vertical offset of image output."
	::= { cameraEntry 9 }

    cameraTitle		OBJECT-TYPE
	SYNTAX			DisplayString (SIZE (1..31))
	ACCESS			read-write
	STATUS			optional
	DESCRIPTION	"Indicates the title of the camera."
	::= { cameraEntry 10 }

    cameraSize		OBJECT-TYPE
	SYNTAX		INTEGER {
			    size640x480(1),
			    size320x240(2),
			    size160x120(3),
			    size640x480-half(5)
			}
	ACCESS		read-write
	STATUS		optional
	DESCRIPTION	"Indicates whether this device uses which image size."
	::= { cameraEntry 11 }

    cameraQuality	OBJECT-TYPE
	SYNTAX		INTEGER {
			    high(1),
			    middle(2),
			    low(3),
			    extreme(4),
			    super(5)
			}
	ACCESS		read-write
	STATUS		optional
	DESCRIPTION	"Indicates whether this device uses which image
			quality."
	::= { cameraEntry 12 }

    cameraBright	OBJECT-TYPE
	SYNTAX		INTEGER (0..63)
	ACCESS		read-write
	STATUS		optional
	DESCRIPTION	"Indicates whether this device uses which image
			brightness."
	::= { cameraEntry 13 }

    cameraID	OBJECT-TYPE
	SYNTAX		INTEGER
	ACCESS		read-write
	STATUS		optional
	DESCRIPTION	"Indicates whether this device uses which camera ID."
	::= { cameraEntry 14 }

    cameraDataSize640x480High	OBJECT-TYPE
	SYNTAX		INTEGER (10..128)
	ACCESS		read-write
	STATUS		optional
	DESCRIPTION	"Indicates whether this device uses which image datasize."
	::= { cameraEntry 15 }

    cameraDataSize640x480Middle	OBJECT-TYPE
	SYNTAX		INTEGER (10..128)
	ACCESS		read-write
	STATUS		optional
	DESCRIPTION	"Indicates whether this device uses which image datasize."
	::= { cameraEntry 16 }

    cameraDataSize640x480Low	OBJECT-TYPE
	SYNTAX		INTEGER (10..128)
	ACCESS		read-write
	STATUS		optional
	DESCRIPTION	"Indicates whether this device uses which image datasize."
	::= { cameraEntry 17 }

    cameraDataSize320x240High	OBJECT-TYPE
	SYNTAX		INTEGER (5..32)
	ACCESS		read-write
	STATUS		optional
	DESCRIPTION	"Indicates whether this device uses which image datasize."
	::= { cameraEntry 18 }

    cameraDataSize320x240Middle	OBJECT-TYPE
	SYNTAX		INTEGER (5..32)
	ACCESS		read-write
	STATUS		optional
	DESCRIPTION	"Indicates whether this device uses which image datasize."
	::= { cameraEntry 19 }

    cameraDataSize320x240Low	OBJECT-TYPE
	SYNTAX		INTEGER (5..32)
	ACCESS		read-write
	STATUS		optional
	DESCRIPTION	"Indicates whether this device uses which image datasize."
	::= { cameraEntry 20 }

    cameraDataSize160x120High	OBJECT-TYPE
	SYNTAX		INTEGER (5..32)
	ACCESS		read-write
	STATUS		optional
	DESCRIPTION	"Indicates whether this device uses which image datasize."
	::= { cameraEntry 21 }

    cameraDataSize160x120Middle	OBJECT-TYPE
	SYNTAX		INTEGER (5..32)
	ACCESS		read-write
	STATUS		optional
	DESCRIPTION	"Indicates whether this device uses which image datasize."
	::= { cameraEntry 22 }

    cameraDataSize160x120Low	OBJECT-TYPE
	SYNTAX		INTEGER (5..32)
	ACCESS		read-write
	STATUS		optional
	DESCRIPTION	"Indicates whether this device uses which image datasize."
	::= { cameraEntry 23 }

    cameraDataSize640x480HalfHigh	OBJECT-TYPE
	SYNTAX		INTEGER (10..128)
	ACCESS		read-write
	STATUS		optional
	DESCRIPTION	"Indicates whether this device uses which image datasize."
	::= { cameraEntry 24 }

    cameraDataSize640x480HalfMiddle	OBJECT-TYPE
	SYNTAX		INTEGER (10..128)
	ACCESS		read-write
	STATUS		optional
	DESCRIPTION	"Indicates whether this device uses which image datasize."
	::= { cameraEntry 25 }

    cameraDataSize640x480HalfLow	OBJECT-TYPE
	SYNTAX		INTEGER (10..128)
	ACCESS		read-write
	STATUS		optional
	DESCRIPTION	"Indicates whether this device uses which image datasize."
	::= { cameraEntry 26 }

-- Movie Group

	execMovieEnable	OBJECT-TYPE
	SYNTAX		INTEGER {
					enable(1),
					disable(2)
				}
	ACCESS		read-write
	STATUS		optional
	DESCRIPTION "Indicates whether this device permits to capture image,
			store image and execute movie."
	::= { imageCapture 22 }

	execSPOMovieEnable OBJECT-TYPE
	SYNTAX		INTEGER {
					enable(1),
					disable(2)
				}
	ACCESS		read-write
	STATUS		optional
	DESCRIPTION	"Indicates whether this device permits to execute movie
			without storeing images."
	::= { imageCapture 23 }

-- Preset Wait Group

	presetWait OBJECT-TYPE
	SYNTAX		INTEGER
	ACCESS		read-write
	STATUS		optional
	DESCRIPTION	"Indicates whether wait time, before camera preset
			position move."
	::= { imageCapture 24 }

-- Server Push Connection Group

	execMaxServerPush OBJECT-TYPE
	SYNTAX		INTEGER
	ACCESS		read-only
	STATUS		optional
	DESCRIPTION	"Indicates whether maximum number of
			server push connection."
	::= { imageCapture 25 }

	execLimitServerPush OBJECT-TYPE
	SYNTAX		INTEGER
	ACCESS		read-write
	STATUS		optional
	DESCRIPTION	"Indicates whether setting limits number of
			server push connection."
	::= { imageCapture 26 }

	execCurServerPush OBJECT-TYPE
	SYNTAX		INTEGER
	ACCESS		read-only
	STATUS		optional
	DESCRIPTION	"Indicates whether current number of
			server push connection."
	::= { imageCapture 27 }

	extSceneID	OBJECT-TYPE
	SYNTAX		INTEGER {
			    enable(1),
			    disable(2)
			}
	ACCESS		read-write
	STATUS		optional
	DESCRIPTION	"Indicates whether scene ID of timer trigger
			is extended."
	::= { imageCapture 28 }

	execType	 OBJECT-TYPE
	SYNTAX		INTEGER {
			    spush(1),
			    cpull(2)
			}
	ACCESS		read-write
	STATUS		optional
	DESCRIPTION	"Indicates whether setting type of view connection."
	::= { imageCapture 64 }

	execInterval	 OBJECT-TYPE
	SYNTAX		DisplayString
	ACCESS		read-write
	STATUS		optional
	DESCRIPTION	"This string is ID of the newest stored scene.
			Initial value is NULL string."
	::= { imageCapture 65 }

	execLimitTime	 OBJECT-TYPE
	SYNTAX		INTEGER
	ACCESS		read-write
	STATUS		optional
	DESCRIPTION	"Indicates whether setting limits time of
			server push connection."
	::= { imageCapture 66 }

	execBackGroundColor	 OBJECT-TYPE
	SYNTAX		DisplayString
	ACCESS		read-write
	STATUS		optional
	DESCRIPTION	"Indicates whether setting limits time of
			server push connection."
	::= { imageCapture 67 }

	execErrorMessage	 OBJECT-TYPE
	SYNTAX		INTEGER {
			    enable(1),
			    disable(2)
			}
	ACCESS		read-write
	STATUS		optional
	DESCRIPTION	"Indicates whether setting limits time of
			server push connection."
	::= { imageCapture 68 }

	execRotateInterval	OBJECT-TYPE
	SYNTAX		INTEGER
	ACCESS		read-write
	STATUS		optional
	DESCRIPTION	"Indicates whether setting interval of rotation."
	::= { imageCapture 69 }

	execRotateCameras	OBJECT-TYPE
	SYNTAX		DisplayString
	ACCESS		read-write
	STATUS		optional
	DESCRIPTION	"Indicates whether setting camera of rotation."
	::= { imageCapture 70 }

	execViewNumber		OBJECT-TYPE
	SYNTAX		INTEGER
	ACCESS		read-write
	STATUS		optional
	DESCRIPTION	"Indicates whether setting number of view."
	::= { imageCapture 71 }

	exec2Multi1Position	OBJECT-TYPE
	SYNTAX		INTEGER
	ACCESS		read-write
	STATUS		optional
	DESCRIPTION	"Indicates whether setting camera of position 1
			in 2 views."
	::= { imageCapture 72 }

	exec2Multi2Position	OBJECT-TYPE
	SYNTAX		INTEGER
	ACCESS		read-write
	STATUS		optional
	DESCRIPTION	"Indicates whether setting camera of position 2
			in 2 views."
	::= { imageCapture 73 }

	exec4Multi1Position	OBJECT-TYPE
	SYNTAX		INTEGER
	ACCESS		read-write
	STATUS		optional
	DESCRIPTION	"Indicates whether setting camera of position 1
			in 4 views."
	::= { imageCapture 74 }

	exec4Multi2Position	OBJECT-TYPE
	SYNTAX		INTEGER
	ACCESS		read-write
	STATUS		optional
	DESCRIPTION	"Indicates whether setting camera of position 2
			in 4 views."
	::= { imageCapture 75 }

	exec4Multi3Position	OBJECT-TYPE
	SYNTAX		INTEGER
	ACCESS		read-write
	STATUS		optional
	DESCRIPTION	"Indicates whether setting camera of position 3
			in 4 views."
	::= { imageCapture 76 }

	exec4Multi4Position	OBJECT-TYPE
	SYNTAX		INTEGER
	ACCESS		read-write
	STATUS		optional
	DESCRIPTION	"Indicates whether setting camera of position 4
			in 4 views."
	::= { imageCapture 77 }

	exec3Multi1Position	OBJECT-TYPE
	SYNTAX		INTEGER
	ACCESS		read-write
	STATUS		optional
	DESCRIPTION	"Indicates whether setting camera of position 1
			in 3 views."
	::= { imageCapture 78 }

	exec3Multi2Position	OBJECT-TYPE
	SYNTAX		INTEGER
	ACCESS		read-write
	STATUS		optional
	DESCRIPTION	"Indicates whether setting camera of position 2
			in 3 views."
	::= { imageCapture 79 }

	exec3Multi3Position	OBJECT-TYPE
	SYNTAX		INTEGER
	ACCESS		read-write
	STATUS		optional
	DESCRIPTION	"Indicates whether setting camera of position 3
			in 3 views."
	::= { imageCapture 80 }

	exec6Multi1Position	OBJECT-TYPE
	SYNTAX		INTEGER
	ACCESS		read-write
	STATUS		optional
	DESCRIPTION	"Indicates whether setting camera of position 1
			in 6 views."
	::= { imageCapture 81 }

	exec6Multi2Position	OBJECT-TYPE
	SYNTAX		INTEGER
	ACCESS		read-write
	STATUS		optional
	DESCRIPTION	"Indicates whether setting camera of position 2
			in 6 views."
	::= { imageCapture 82 }

	exec6Multi3Position	OBJECT-TYPE
	SYNTAX		INTEGER
	ACCESS		read-write
	STATUS		optional
	DESCRIPTION	"Indicates whether setting camera of position 3
			in 6 views."
	::= { imageCapture 83 }

	exec6Multi4Position	OBJECT-TYPE
	SYNTAX		INTEGER
	ACCESS		read-write
	STATUS		optional
	DESCRIPTION	"Indicates whether setting camera of position 4
			in 6 views."
	::= { imageCapture 84 }

	exec6Multi5Position	OBJECT-TYPE
	SYNTAX		INTEGER
	ACCESS		read-write
	STATUS		optional
	DESCRIPTION	"Indicates whether setting camera of position 5
			in 6 views."
	::= { imageCapture 85 }

	exec6Multi6Position	OBJECT-TYPE
	SYNTAX		INTEGER
	ACCESS		read-write
	STATUS		optional
	DESCRIPTION	"Indicates whether setting camera of position 6
			in 6 views."
	::= { imageCapture 86 }

	exec9Multi1Position	OBJECT-TYPE
	SYNTAX		INTEGER
	ACCESS		read-write
	STATUS		optional
	DESCRIPTION	"Indicates whether setting camera of position 1
			in 9 views."
	::= { imageCapture 87 }

	exec9Multi2Position	OBJECT-TYPE
	SYNTAX		INTEGER
	ACCESS		read-write
	STATUS		optional
	DESCRIPTION	"Indicates whether setting camera of position 2
			in 9 views."
	::= { imageCapture 88 }

	exec9Multi3Position	OBJECT-TYPE
	SYNTAX		INTEGER
	ACCESS		read-write
	STATUS		optional
	DESCRIPTION	"Indicates whether setting camera of position 3
			in 9 views."
	::= { imageCapture 89 }

	exec9Multi4Position	OBJECT-TYPE
	SYNTAX		INTEGER
	ACCESS		read-write
	STATUS		optional
	DESCRIPTION	"Indicates whether setting camera of position 4
			in 9 views."
	::= { imageCapture 90 }

	exec9Multi5Position	OBJECT-TYPE
	SYNTAX		INTEGER
	ACCESS		read-write
	STATUS		optional
	DESCRIPTION	"Indicates whether setting camera of position 5
			in 9 views."
	::= { imageCapture 91 }

	exec9Multi6Position	OBJECT-TYPE
	SYNTAX		INTEGER
	ACCESS		read-write
	STATUS		optional
	DESCRIPTION	"Indicates whether setting camera of position 6
			in 9 views."
	::= { imageCapture 92 }

	exec9Multi7Position	OBJECT-TYPE
	SYNTAX		INTEGER
	ACCESS		read-write
	STATUS		optional
	DESCRIPTION	"Indicates whether setting camera of position 7
			in 9 views."
	::= { imageCapture 93 }

	exec9Multi8Position	OBJECT-TYPE
	SYNTAX		INTEGER
	ACCESS		read-write
	STATUS		optional
	DESCRIPTION	"Indicates whether setting camera of position 8
			in 9 views."
	::= { imageCapture 94 }

	exec9Multi9Position	OBJECT-TYPE
	SYNTAX		INTEGER
	ACCESS		read-write
	STATUS		optional
	DESCRIPTION	"Indicates whether setting camera of position 9
			in 9 views."
	::= { imageCapture 95 }

-- image Memory Group (Ver5.3.14)

    imageMemory		OBJECT IDENTIFIER ::= { imageCapture 100 }

    imageMemoryFullTrapControl	OBJECT-TYPE
	SYNTAX		INTEGER {
			    enable(1),
			    disable(2),
			    retry(3)
			}
	ACCESS		read-write
	STATUS		optional
	DESCRIPTION	"Indicates whether the SNMP agent process is
			permitted to generate imageMemoryFull traps."
	::= { imageMemory 1 }

    imageMemoryFullTrapCount	OBJECT-TYPE
	SYNTAX		INTEGER
	ACCESS		read-only
	STATUS		optional
	DESCRIPTION	"Count of imageMemoryFull trap generated."
	::= { imageMemory 2 }

    imageMemoryFullEmail	OBJECT-TYPE
	SYNTAX		INTEGER {
			    enable(1),
			    disable(2)
			}
	ACCESS		read-write
	STATUS		mandatory
	DESCRIPTION	"Indicates whether the SMTP process is
			permitted to generate imageMemoryFull Email."
	::= { imageMemory 3 }

    imageMemoryFullRemoteCommand	OBJECT-TYPE
	SYNTAX		INTEGER {
			    enable(1),
			    disable(2)
			}
	ACCESS		read-write
	STATUS		mandatory
	DESCRIPTION	"Indicates whether the RSH process is
			permitted to generate imageMemoryFull
			remote command."
	::= { imageMemory 4 }

    imageMemoryFullRemoteCommandSet OBJECT-TYPE
	SYNTAX		INTEGER (1..32)
	ACCESS		read-write
	STATUS		mandatory
	DESCRIPTION	"Indicates imageMemoryFull
			remote command set number generated."
	::= { imageMemory 5 }

-- end of image Memory Group

	exec1CameraInterval	 OBJECT-TYPE
	SYNTAX		DisplayString
	ACCESS		read-write
	STATUS		optional
	DESCRIPTION	"Interval of 1camera viewing."
	::= { imageCapture 101 }

	exec2CameraInterval	 OBJECT-TYPE
	SYNTAX		DisplayString
	ACCESS		read-write
	STATUS		optional
	DESCRIPTION	"Interval of 1camera viewing."
	::= { imageCapture 102 }

	exec3CameraInterval	 OBJECT-TYPE
	SYNTAX		DisplayString
	ACCESS		read-write
	STATUS		optional
	DESCRIPTION	"Interval of 1camera viewing."
	::= { imageCapture 103 }

	exec4CameraInterval	 OBJECT-TYPE
	SYNTAX		DisplayString
	ACCESS		read-write
	STATUS		optional
	DESCRIPTION	"Interval of 1camera viewing."
	::= { imageCapture 104 }

	exec5CameraInterval	 OBJECT-TYPE
	SYNTAX		DisplayString
	ACCESS		read-write
	STATUS		optional
	DESCRIPTION	"Interval of 1camera viewing."
	::= { imageCapture 105 }

	exec6CameraInterval	 OBJECT-TYPE
	SYNTAX		DisplayString
	ACCESS		read-write
	STATUS		optional
	DESCRIPTION	"Interval of 1camera viewing."
	::= { imageCapture 106 }

	exec7CameraInterval	 OBJECT-TYPE
	SYNTAX		DisplayString
	ACCESS		read-write
	STATUS		optional
	DESCRIPTION	"Interval of 1camera viewing."
	::= { imageCapture 107 }

	exec8CameraInterval	 OBJECT-TYPE
	SYNTAX		DisplayString
	ACCESS		read-write
	STATUS		optional
	DESCRIPTION	"Interval of 1camera viewing."
	::= { imageCapture 108 }

	exec9CameraInterval	 OBJECT-TYPE
	SYNTAX		DisplayString
	ACCESS		read-write
	STATUS		optional
	DESCRIPTION	"Interval of 1camera viewing."
	::= { imageCapture 109 }

-- Video Compress Data (VC) Group

    vcNumber		OBJECT-TYPE
	SYNTAX		INTEGER
	ACCESS		read-only
	STATUS		mandatory
	DESCRIPTION	"The number of VC channels supported by this device."
	::= { imageCapture 30 }

    vcTable		OBJECT-TYPE
	SYNTAX		SEQUENCE OF VcEntry
	ACCESS		not-accessible
	STATUS		mandatory
	DESCRIPTION	"A list of VC channel entries. The number of entries
			is given by the value vcNumber."
	::= { imageCapture 31 }

    vcEntry		OBJECT-TYPE
	SYNTAX		VcEntry
	ACCESS		not-accessible
	STATUS		mandatory
	DESCRIPTION	"A VC channel entry containing objects to describe the
			VC channel."
	INDEX		{ vcIndex }
	::= { vcTable 1 }

    VcEntry ::=
	SEQUENCE {
	    vcIndex
		INTEGER,
	    vcType
		DisplayString,
	    vcValue
		INTEGER,
	    vcValueScale
		INTEGER,
	    vcValueOffset
		INTEGER,
	    vcLogInterval
		INTEGER,
	    vcEventPollInterval
		INTEGER,
	    vcEventUpperThreshold
		INTEGER,
	    vcEventUpperHysteresis
		INTEGER,
	    vcEventLowerThreshold
		INTEGER,
	    vcEventLowerHysteresis
		INTEGER,

	    vcTrapPollInterval
		INTEGER,
	    vcTrapUpperThreshold
		INTEGER,
	    vcTrapUpperHysteresis
		INTEGER,
	    vcTrapLowerThreshold
		INTEGER,
	    vcTrapLowerHysteresis
		INTEGER,
	    vcEnableExUpThresholdIncreaseTrap
		INTEGER,
	    vcEnableExUpThresholdDecreaseTrap
		INTEGER,
	    vcEnableExUpThresholdTrap
		INTEGER,
	    vcEnableExLoThresholdIncreaseTrap
		INTEGER,
	    vcEnableExLoThresholdDecreaseTrap
		INTEGER,
	    vcEnableExLoThresholdTrap
		INTEGER,
	    vcAlertCondition
		INTEGER,
	    vcRange
		INTEGER,
	    vcEmailPollInterval
		INTEGER,
	    vcEmailUpperThreshold
		INTEGER,
	    vcEmailUpperHysteresis
		INTEGER,
	    vcEmailLowerThreshold
		INTEGER,
	    vcEmailLowerHysteresis
		INTEGER,
	    vcEnableExUpThresholdIncreaseEmail
		INTEGER,
	    vcEnableExUpThresholdDecreaseEmail
		INTEGER,
	    vcEnableExUpThresholdEmail
		INTEGER,
	    vcEnableExLoThresholdIncreaseEmail
		INTEGER,
	    vcEnableExLoThresholdDecreaseEmail
		INTEGER,
	    vcEnableExLoThresholdEmail
		INTEGER,
	    vcExUpThresholdIncreaseTrapID
		INTEGER,
	    vcExUpThresholdDecreaseTrapID
		INTEGER,
	    vcExUpThresholdTrapID
		INTEGER,
	    vcExLoThresholdIncreaseTrapID
		INTEGER,
	    vcExLoThresholdDecreaseTrapID
		INTEGER,
	    vcExLoThresholdTrapID
		INTEGER,

	    vcSyncTriggerPermit
		INTEGER,

	    vcRemoteCommandPollInterval
		INTEGER,
	    vcRemoteCommandUpperThreshold
		INTEGER,
	    vcRemoteCommandUpperHysteresis
		INTEGER,
	    vcRemoteCommandLowerThreshold
		INTEGER,
	    vcRemoteCommandLowerHysteresis
		INTEGER,
	    vcEnableExUpThresholdIncreaseRemoteCommand
		INTEGER,
	    vcEnableExUpThresholdDecreaseRemoteCommand
		INTEGER,
	    vcEnableExUpThresholdRemoteCommand
		INTEGER,
	    vcEnableExLoThresholdIncreaseRemoteCommand
		INTEGER,
	    vcEnableExLoThresholdDecreaseRemoteCommand
		INTEGER,
	    vcEnableExLoThresholdRemoteCommand
		INTEGER,
	    vcEnableExUpThresholdIncreaseRemoteCommandSet
		INTEGER,
	    vcEnableExUpThresholdDecreaseRemoteCommandSet
		INTEGER,
	    vcEnableExUpThresholdRemoteCommandSet
		INTEGER,
	    vcEnableExLoThresholdIncreaseRemoteCommandSet
		INTEGER,
	    vcEnableExLoThresholdDecreaseRemoteCommandSet
		INTEGER,
	    vcEnableExLoThresholdRemoteCommandSet
		INTEGER
	}

    vcIndex		OBJECT-TYPE
	SYNTAX		INTEGER
	ACCESS		read-only
	STATUS		mandatory
	DESCRIPTION	"A unique value for each VC channel. It's value ranges
			between 1 and the value vcNumber."
	::= { vcEntry 1 }

    vcType		OBJECT-TYPE
	SYNTAX		DisplayString (SIZE (1..32))
	ACCESS		read-write
	STATUS		mandatory
	DESCRIPTION	"The text string is type of VC value."
	::= { vcEntry 2 }

    vcValue		OBJECT-TYPE
	SYNTAX		INTEGER
	ACCESS		read-only
	STATUS		mandatory
	DESCRIPTION	"The value of VC channel is multiplied by vcValueScale
			and vcValueOffset. namely,
			vcValue =
			 (value of VC channel) * vcValueScale + vcValueOffset."
	::= { vcEntry 3 }

    vcValueScale	OBJECT-TYPE
	SYNTAX		INTEGER
	ACCESS		read-write
	STATUS		mandatory
	DESCRIPTION	"This value is coefficient of scale for vcValue."
	::= { vcEntry 4 }

    vcValueOffset	OBJECT-TYPE
	SYNTAX		INTEGER
	ACCESS		read-write
	STATUS		mandatory
	DESCRIPTION	"This value is offset for vcValue."
	::= { vcEntry 5 }

    vcLogInterval	OBJECT-TYPE
	SYNTAX		INTEGER (0..2147483600)
	ACCESS		read-write
	STATUS		mandatory
	DESCRIPTION	"The interval in milliseconds to log for the
			value of VC channel. This value can be set on
			every 50ms. A fraction is raised and set."
	::= { vcEntry 6 }

    vcEventPollInterval	OBJECT-TYPE
	SYNTAX		INTEGER (0..2147483600)
	ACCESS		read-write
	STATUS		mandatory
	DESCRIPTION	"The interval in milliseconds to poll the value
			of VC channel for Event. This value can be set on
			every 50ms. A fraction is raised and set."
	::= { vcEntry 7 }

    vcEventUpperThreshold OBJECT-TYPE
	SYNTAX		INTEGER
	ACCESS		read-write
	STATUS		mandatory
	DESCRIPTION	"A Event trigger for upper limit VC value.
			If vcValue is greater than this value then generate
			vcExceedUpperThresholdIncrease event."
	::= { vcEntry 8 }

    vcEventUpperHysteresis OBJECT-TYPE
	SYNTAX		INTEGER
	ACCESS		read-write
	STATUS		mandatory
	DESCRIPTION	"A Event trigger for vcEventUpperThreshold offset.
			If vcValue is less equal vcEventUpperThreshold minus
			this value after vcExceedUpperThresholdIncrease event
			is generated, then generate 
			vcExceedUpperThresholdDecrease event."
	::= { vcEntry 9 }

    vcEventLowerThreshold OBJECT-TYPE
	SYNTAX		INTEGER
	ACCESS		read-write
	STATUS		mandatory
	DESCRIPTION	"A Event trigger for lower limit VC value.
			If vcValue is less than this value then generate
			vcExceedLowerThresholdDecrease event."
	::= { vcEntry 10 }

    vcEventLowerHysteresis OBJECT-TYPE
	SYNTAX		INTEGER
	ACCESS		read-write
	STATUS		mandatory
	DESCRIPTION	"A Event trigger for vcEventLowerThreshold offset.
			If vcValue is greater equal vcEventLowerThreshold minus
			this value after vcExceedLowerThresholdDecrease event
			is generated, then generate 
			vcExceedLowerThresholdIncrease event."
	::= { vcEntry 11 }

    vcTrapPollInterval	OBJECT-TYPE
	SYNTAX		INTEGER (0..2147483600)
	ACCESS		read-write
	STATUS		mandatory
	DESCRIPTION	"The interval in milliseconds to poll the value
			of VC channel for Trap. This value can be set on
			every 50ms. A fraction is raised and set."
	::= { vcEntry 12 }

    vcTrapUpperThreshold OBJECT-TYPE
	SYNTAX		INTEGER
	ACCESS		read-write
	STATUS		mandatory
	DESCRIPTION	"A trap trigger for upper limit VC value.
			If vcValue is greater than this value then generate
			vcExceedUpperThresholdIncrease trap."
	::= { vcEntry 13 }

    vcTrapUpperHysteresis OBJECT-TYPE
	SYNTAX		INTEGER
	ACCESS		read-write
	STATUS		mandatory
	DESCRIPTION	"A Trap trigger for vcEventUpperThreshold offset.
			If vcValue is less equal vcEventUpperThreshold minus
			this value after vcExceedUpperThresholdIncrease trap
			is generated, then generate
			vcExceedUpperThresholdDecrease trap."
	::= { vcEntry 14 }

    vcTrapLowerThreshold OBJECT-TYPE
	SYNTAX		INTEGER
	ACCESS		read-write
	STATUS		mandatory
	DESCRIPTION	"A Trap trigger for lower limit VC value.
			If vcValue is less than this value then generate
			vcExceedLowerThresholdDecrease trap."
	::= { vcEntry 15 }

    vcTrapLowerHysteresis OBJECT-TYPE
	SYNTAX		INTEGER
	ACCESS		read-write
	STATUS		mandatory
	DESCRIPTION	"A Trap trigger for vcEventLowerThreshold offset.
			If vcValue is greater equal vcEventLowerThreshold minus
			this value after vcExceedLowerThresholdDecrease trap
			is generated, then generate
			vcExceedLowerThresholdIncrease trap."
	::= { vcEntry 16 }

    vcEnableExUpThresholdIncreaseTrap OBJECT-TYPE
	SYNTAX		INTEGER {
			    enable(1),
			    disable(2),
			    retry(3)
			}
	ACCESS		read-write
	STATUS		mandatory
	DESCRIPTION	"Indicates whether the SNMP agent process is
			permitted to generate vcExceedUpperThresholdIncrease
			traps."
	::= { vcEntry 17 }

    vcEnableExUpThresholdDecreaseTrap OBJECT-TYPE
	SYNTAX		INTEGER {
			    enable(1),
			    disable(2),
			    retry(3)
			}
	ACCESS		read-write
	STATUS		mandatory
	DESCRIPTION	"Indicates whether the SNMP agent process is
			permitted to generate vcExceedUpperThresholdDecrease
			traps."
	::= { vcEntry 18 }

    vcEnableExUpThresholdTrap OBJECT-TYPE
	SYNTAX		INTEGER {
			    enable(1),
			    disable(2),
			    retry(3)
			}
	ACCESS		read-write
	STATUS		mandatory
	DESCRIPTION	"Indicates whether the SNMP agent process is
			permitted to generate vcExceedingUpperThreshold
			traps."
	::= { vcEntry 19 }

    vcEnableExLoThresholdIncreaseTrap OBJECT-TYPE
	SYNTAX		INTEGER {
			    enable(1),
			    disable(2),
			    retry(3)
			}
	ACCESS		read-write
	STATUS		mandatory
	DESCRIPTION	"Indicates whether the SNMP agent process is
			permitted to generate vcExceedLowerThresholdIncrease
			traps."
	::= { vcEntry 20 }

    vcEnableExLoThresholdDecreaseTrap OBJECT-TYPE
	SYNTAX		INTEGER {
			    enable(1),
			    disable(2),
			    retry(3)
			}
	ACCESS		read-write
	STATUS		mandatory
	DESCRIPTION	"Indicates whether the SNMP agent process is
			permitted to generate vcExceedLowerThresholdDecrease
			traps."
	::= { vcEntry 21 }

    vcEnableExLoThresholdTrap OBJECT-TYPE
	SYNTAX		INTEGER {
			    enable(1),
			    disable(2),
			    retry(3)
			}
	ACCESS		read-write
	STATUS		mandatory
	DESCRIPTION	"Indicates whether the SNMP agent process is
			permitted to generate vcExceedingLowerThreshold
			traps."
	::= { vcEntry 22 }

    vcAlertCondition	OBJECT-TYPE
	SYNTAX		INTEGER {
			    ignore(1),
			    upper(2),
			    lower(3),
			    upper-or-lower(4),
			    normal(5),
			    trap-upper(6),
			    trap-lower(7),
			    trap-upper-or-lower(8),
			    trap-normal(9)
			}
	ACCESS		read-write
	STATUS		optional
	DESCRIPTION	"Which condition shows whether it is alert condition."
	::= { vcEntry 23 }

    vcRange		OBJECT-TYPE
	SYNTAX		INTEGER {
			    all(1),
			    positive(2)
			}
	ACCESS		not-accessible
	STATUS		optional
	DESCRIPTION	"Select input formula for VC value.
			The choice is 'ALL' or 'POSITIVE only'.
			'ALL' semantic permit positive and negative value. 
			else 'POSITIVE only' permit positive value only."
	::= { vcEntry 24 }

    vcEmailPollInterval	OBJECT-TYPE
	SYNTAX		INTEGER (0..2147483600)
	ACCESS		read-write
	STATUS		mandatory
	DESCRIPTION	"The interval in milliseconds to poll the value
			of VC channel for Email. This value can be set on
			every 50ms. A fraction is raised and set."
	::= { vcEntry 25 }

    vcEmailUpperThreshold OBJECT-TYPE
	SYNTAX		INTEGER
	ACCESS		read-write
	STATUS		mandatory
	DESCRIPTION	"A E-Mail trigger for upper limit VC value.
			If vcValue is greater than this value then generate
			vcExceedUpperThresholdIncrease E-Mail."
	::= { vcEntry 26 }

    vcEmailUpperHysteresis OBJECT-TYPE
	SYNTAX		INTEGER
	ACCESS		read-write
	STATUS		mandatory
	DESCRIPTION	"A E-Mail trigger for vcEventUpperThreshold offset.
			If vcValue is less equal vcEventUpperThreshold minus
			this value after vcExceedUpperThresholdIncrease E-Mail
			is generated, then generate
			vcExceedUpperThresholdDecrease."
	::= { vcEntry 27 }

    vcEmailLowerThreshold OBJECT-TYPE
	SYNTAX		INTEGER
	ACCESS		read-write
	STATUS		mandatory
	DESCRIPTION	"A Email trigger for lower limit VC value.
			If vcValue is less than this value then generate 
			vcExceedLowerThresholdDecrease E-mail."
	::= { vcEntry 28 }

    vcEmailLowerHysteresis OBJECT-TYPE
	SYNTAX		INTEGER
	ACCESS		read-write
	STATUS		mandatory
	DESCRIPTION	"A Email trigger for vcEventLowerThreshold offset.
			If vcValue is greater equal vcEventLowerThreshold minus
			this value after vcExceedLowerThresholdDecrease's E-mail
			is generated, then generate
			vcExceedLowerThresholdIncrease."
	::= { vcEntry 29 }

    vcEnableExUpThresholdIncreaseEmail OBJECT-TYPE
	SYNTAX		INTEGER {
			    enable(1),
			    disable(2),
			    retry(3)
			}
	ACCESS		read-write
	STATUS		mandatory
	DESCRIPTION	"Indicates whether the SNMP agent process is
			permitted to generate vcExceedUpperThresholdIncrease
			Email."
	::= { vcEntry 30 }

    vcEnableExUpThresholdDecreaseEmail OBJECT-TYPE
	SYNTAX		INTEGER {
			    enable(1),
			    disable(2),
			    retry(3)
			}
	ACCESS		read-write
	STATUS		mandatory
	DESCRIPTION	"Indicates whether the SNMP agent process is
			permitted to generate vcExceedUpperThresholdDecrease
			Email."
	::= { vcEntry 31 }

    vcEnableExUpThresholdEmail OBJECT-TYPE
	SYNTAX		INTEGER {
			    enable(1),
			    disable(2),
			    retry(3)
			}
	ACCESS		read-write
	STATUS		mandatory
	DESCRIPTION	"Indicates whether the SNMP agent process is
			permitted to generate vcExceedingUpperThreshold
			Email."
	::= { vcEntry 32 }

    vcEnableExLoThresholdIncreaseEmail OBJECT-TYPE
	SYNTAX		INTEGER {
			    enable(1),
			    disable(2),
			    retry(3)
			}
	ACCESS		read-write
	STATUS		mandatory
	DESCRIPTION	"Indicates whether the SNMP agent process is
			permitted to generate vcExceedLowerThresholdIncrease
			Email."
	::= { vcEntry 33 }

    vcEnableExLoThresholdDecreaseEmail OBJECT-TYPE
	SYNTAX		INTEGER {
			    enable(1),
			    disable(2),
			    retry(3)
			}
	ACCESS		read-write
	STATUS		mandatory
	DESCRIPTION	"Indicates whether the SNMP agent process is
			permitted to generate vcExceedLowerThresholdDecrease
			Email."
	::= { vcEntry 34 }

    vcEnableExLoThresholdEmail OBJECT-TYPE
	SYNTAX		INTEGER {
			    enable(1),
			    disable(2),
			    retry(3)
			}
	ACCESS		read-write
	STATUS		mandatory
	DESCRIPTION	"Indicates whether the SNMP agent process is
			permitted to generate vcExceedingLowerThreshold
			Email."
	::= { vcEntry 35 }

    vcExUpThresholdIncreaseTrapID OBJECT-TYPE
	SYNTAX		INTEGER
	ACCESS		read-write
	STATUS		mandatory
	DESCRIPTION	"Specifyed the SNMP agent generate 
			vcExceedUpperThresholdIncrease specific Trap ID.
			When set zero generate vcExceedUpperThresholdIncrease
			otherwise vcExceedUpperThresholdIncrease[1-127]"
	::= { vcEntry 36 }

    vcExUpThresholdDecreaseTrapID OBJECT-TYPE
	SYNTAX		INTEGER
	ACCESS		read-write
	STATUS		mandatory
	DESCRIPTION	"Specifyed the SNMP agent generate 
			vcExceedUpperThresholdDecrease specific Trap ID.
			When set zero generate vcExceedUpperThresholdDecrease
			otherwise vcExceedUpperThresholdDecrease[1-127]"
	::= { vcEntry 37 }

    vcExUpThresholdTrapID OBJECT-TYPE
	SYNTAX		INTEGER
	ACCESS		read-write
	STATUS		mandatory
	DESCRIPTION	"Specifyed the SNMP agent generate 
			vcExceedingUpperThreshold specific Trap ID.
			When set zero generate vcExceedingUpperThreshold
			otherwise vcExceedingUpperThreshold[1-127]"
	::= { vcEntry 38 }

    vcExLoThresholdIncreaseTrapID OBJECT-TYPE
	SYNTAX		INTEGER
	ACCESS		read-write
	STATUS		mandatory
	DESCRIPTION	"Specifyed the SNMP agent generate 
			vcExceedLowerThresholdIncrease specific Trap ID.
			When set zero generate vcExceedLowerThresholdIncrease
			otherwise vcExceedLowerThresholdIncrease[1-127]"
	::= { vcEntry 39 }

    vcExLoThresholdDecreaseTrapID OBJECT-TYPE
	SYNTAX		INTEGER
	ACCESS		read-write
	STATUS		mandatory
	DESCRIPTION	"Specifyed the SNMP agent generate 
			vcExceedLowerThresholdDecrease specific Trap ID.
			When set zero generate vcExceedLowerThresholdDecrease
			otherwise vcExceedLowerThresholdDecrease[1-127]"
	::= { vcEntry 40 }

    vcExLoThresholdTrapID OBJECT-TYPE
	SYNTAX		INTEGER
	ACCESS		read-write
	STATUS		mandatory
	DESCRIPTION	"Specifyed the SNMP agent generate 
			vcExceedingLowerThreshold specific Trap ID.
			When set zero generate vcExceedingLowerThreshold
			otherwise vcExceedingLowerThreshold[1-127]"
	::= { vcEntry 41 }

    vcSyncTriggerPermit OBJECT-TYPE
	SYNTAX		INTEGER {
			    enable(1),
			    disable(2)
			}
	ACCESS		read-write
	STATUS		mandatory
	DESCRIPTION	"The type of permission to specify with this entry."
	::= { vcEntry 42 }

 -- Following variable are support Ver 3.7 or Later
    vcRemoteCommandPollInterval	OBJECT-TYPE
	SYNTAX		INTEGER (0..2147483600)
	ACCESS		read-write
	STATUS		mandatory
	DESCRIPTION	"The interval in milliseconds to poll the value
			of VC channel for remote command. This value can be set on
			every 50ms. A fraction is raised and set."
	::= { vcEntry 43 }

    vcRemoteCommandUpperThreshold OBJECT-TYPE
	SYNTAX		INTEGER
	ACCESS		read-write
	STATUS		mandatory
	DESCRIPTION	"A remote command trigger for upper limit VC value.
			If vcValue is greater than this value then generate
			vcExceedUpperThresholdIncrease remote command."
	::= { vcEntry 44 }

    vcRemoteCommandUpperHysteresis OBJECT-TYPE
	SYNTAX		INTEGER
	ACCESS		read-write
	STATUS		mandatory
	DESCRIPTION	"A remote command trigger for vcEventUpperThreshold offset.
			If vcValue is less equal vcEventUpperThreshold minus
			this value after vcExceedUpperThresholdIncrease remote command
			is generated, then generate
			vcExceedUpperThresholdDecrease remote command."
	::= { vcEntry 45 }

    vcRemoteCommandLowerThreshold OBJECT-TYPE
	SYNTAX		INTEGER
	ACCESS		read-write
	STATUS		mandatory
	DESCRIPTION	"A remote command trigger for lower limit VC value.
			If vcValue is less than this value then generate 
			vcExceedLowerThresholdDecrease remote command."
	::= { vcEntry 46 }

    vcRemoteCommandLowerHysteresis OBJECT-TYPE
	SYNTAX		INTEGER
	ACCESS		read-write
	STATUS		mandatory
	DESCRIPTION	"A remote command trigger for vcEventLowerThreshold offset.
			If vcValue is greater equal vcEventLowerThreshold minus
			this value after vcExceedLowerThresholdDecrease's remote command
			is generated, then generate
			vcExceedLowerThresholdIncrease remote command."
	::= { vcEntry 47 }

    vcEnableExUpThresholdIncreaseRemoteCommand OBJECT-TYPE
	SYNTAX		INTEGER {
			    enable(1),
			    disable(2)
			}
	ACCESS		read-write
	STATUS		mandatory
	DESCRIPTION	"Indicates whether the SNMP agent process is
			permitted to generate vcExceedUpperThresholdIncrease
			remote command."
	::= { vcEntry 48 }

    vcEnableExUpThresholdDecreaseRemoteCommand OBJECT-TYPE
	SYNTAX		INTEGER {
			    enable(1),
			    disable(2)
			}
	ACCESS		read-write
	STATUS		mandatory
	DESCRIPTION	"Indicates whether the SNMP agent process is
			permitted to generate vcExceedUpperThresholdDecrease
			remote command."
	::= { vcEntry 49 }

    vcEnableExUpThresholdRemoteCommand OBJECT-TYPE
	SYNTAX		INTEGER {
			    enable(1),
			    disable(2)
			}
	ACCESS		read-write
	STATUS		mandatory
	DESCRIPTION	"Indicates whether the SNMP agent process is
			permitted to generate vcExceedingUpperThreshold
			remote command."
	::= { vcEntry 50 }

    vcEnableExLoThresholdIncreaseRemoteCommand OBJECT-TYPE
	SYNTAX		INTEGER {
			    enable(1),
			    disable(2)
			}
	ACCESS		read-write
	STATUS		mandatory
	DESCRIPTION	"Indicates whether the SNMP agent process is
			permitted to generate vcExceedLowerThresholdIncrease
			remote command."
	::= { vcEntry 51 }

    vcEnableExLoThresholdDecreaseRemoteCommand OBJECT-TYPE
	SYNTAX		INTEGER {
			    enable(1),
			    disable(2)
			}
	ACCESS		read-write
	STATUS		mandatory
	DESCRIPTION	"Indicates whether the SNMP agent process is
			permitted to generate vcExceedLowerThresholdDecrease
			remote command."
	::= { vcEntry 52 }

    vcEnableExLoThresholdRemoteCommand OBJECT-TYPE
	SYNTAX		INTEGER {
			    enable(1),
			    disable(2)
			}
	ACCESS		read-write
	STATUS		mandatory
	DESCRIPTION	"Indicates whether the SNMP agent process is
			permitted to generate vcExceedingLowerThreshold
			remote command."
	::= { vcEntry 53 }


    vcEnableExUpThresholdIncreaseRemoteCommandSet OBJECT-TYPE
	SYNTAX		INTEGER (1..4)
	ACCESS		read-write
	STATUS		mandatory
	DESCRIPTION	"Indicates vcExceedUpperThresholdIncrease
			remote command set number generated."
	::= { vcEntry 54 }

    vcEnableExUpThresholdDecreaseRemoteCommandSet OBJECT-TYPE
	SYNTAX		INTEGER (1..4)
	ACCESS		read-write
	STATUS		mandatory
	DESCRIPTION	"Indicates vcExceedUpperThresholdDecrease
			remote command set number generated."
	::= { vcEntry 55 }

    vcEnableExUpThresholdRemoteCommandSet OBJECT-TYPE
	SYNTAX		INTEGER (1..4)
	ACCESS		read-write
	STATUS		mandatory
	DESCRIPTION	"Indicates vcExceedingUpperThreshold
			remote command set number generated."
	::= { vcEntry 56 }

    vcEnableExLoThresholdIncreaseRemoteCommandSet OBJECT-TYPE
	SYNTAX		INTEGER (1..4)
	ACCESS		read-write
	STATUS		mandatory
	DESCRIPTION	"Indicates vcExceedLowerThresholdIncrease
			remote command set number generated."
	::= { vcEntry 57 }

    vcEnableExLoThresholdDecreaseRemoteCommandSet OBJECT-TYPE
	SYNTAX		INTEGER (1..4)
	ACCESS		read-write
	STATUS		mandatory
	DESCRIPTION	"Indicates vcExceedLowerThresholdDecrease
			remote command set number generated."
	::= { vcEntry 58 }

    vcEnableExLoThresholdRemoteCommandSet OBJECT-TYPE
	SYNTAX		INTEGER (1..4)
	ACCESS		read-write
	STATUS		mandatory
	DESCRIPTION	"Indicates vcExceedingLowerThreshold
			remote command set number generated."
	::= { vcEntry 59 }

-- The DISK Group
--
-- This group contains the MIB variables used to determine the DISK.

    disk	OBJECT IDENTIFIER ::= { ndMgmt 4 }

    diskCapacity	OBJECT-TYPE
	SYNTAX		INTEGER
	ACCESS		read-only
	STATUS		optional
	DESCRIPTION	"The size of the disk in kilobytes."
	::= { disk 1 }

    diskUsed		OBJECT-TYPE
	SYNTAX		INTEGER
	ACCESS		read-only
	STATUS		optional
	DESCRIPTION	"The used size of the disk in kilobytes."
	::= { disk 2 }

    diskId		OBJECT-TYPE
	SYNTAX		DisplayString (SIZE (1..32))
	ACCESS		read-only
	STATUS		optional
	DESCRIPTION	"This value indicates ID of the disk."
	::= { disk 3 }

    diskReadErrorCount	OBJECT-TYPE
	SYNTAX		INTEGER
	ACCESS		read-only
	STATUS		optional
	DESCRIPTION	"This value increases when a disk read error has
			occurred."
	::= { disk 4 }

    diskWriteErrorCount	OBJECT-TYPE
	SYNTAX		INTEGER
	ACCESS		read-only
	STATUS		optional
	DESCRIPTION	"This value increases when a disk write error has
			occurred."
	::= { disk 5 }

    diskMaxSwapSectorCount	OBJECT-TYPE
	SYNTAX		INTEGER
	ACCESS		read-only
	STATUS		optional
	DESCRIPTION	"Reserved maximum swap sectors."
	::= { disk 6 }

    diskSwapSectorCount	OBJECT-TYPE
	SYNTAX		INTEGER
	ACCESS		read-only
	STATUS		optional
	DESCRIPTION	"Count of swap sectors."
	::= { disk 7 }

    diskCriticalErrorTime	OBJECT-TYPE
	SYNTAX		DisplayString
	ACCESS		read-only
	STATUS		optional
	DESCRIPTION	"First CriticalError occurred time.
			If string are '---', dose not occured CriticalError."
	::= { disk 8 }

    diskCriticalErrorKind	OBJECT-TYPE
	SYNTAX		INTEGER
	ACCESS		read-only
	STATUS		optional
	DESCRIPTION	"Kind of CriticalError.
			If value is 0, dose not occured CriticalError."
	::= { disk 9 }

    diskFatalErrorTime	OBJECT-TYPE
	SYNTAX		DisplayString
	ACCESS		read-only
	STATUS		optional
	DESCRIPTION	"First FatalError occurred time.
			If string are '---', dose not occured FatalError."
	::= { disk 10 }

    diskFatalErrorKind	OBJECT-TYPE
	SYNTAX		INTEGER
	ACCESS		read-only
	STATUS		optional
	DESCRIPTION	"Kind of FatalError.
			If value is 0, dose not occured FatalError."
	::= { disk 11 }

    diskOverwrite OBJECT-TYPE
	SYNTAX		INTEGER {
			    enable(1),
			    disable(2)
			}
	ACCESS		read-write
	STATUS		optional
	DESCRIPTION	"Permit Overwrite when disk has full."
	::= { disk 16 }

    diskAccessControl OBJECT-TYPE
	SYNTAX		INTEGER {
			    enable(1),
			    readonly(2),
			    disable(3)
			}
	ACCESS		read-write
	STATUS		optional
	DESCRIPTION	"Disk access policy control."
	::= { disk 17 }

    diskSavedAccessControl OBJECT-TYPE
	SYNTAX		INTEGER {
			    enable(1),
			    readonly(2)
			}
	ACCESS		read-only
	STATUS		optional
	DESCRIPTION	"Disk access policy control when bootup."
	::= { disk 18 }

    diskReadFailureTrap OBJECT-TYPE
	SYNTAX		INTEGER {
			    enable(1),
			    disable(2),
			    retry(3)
			}
	ACCESS		read-write
	STATUS		mandatory
	DESCRIPTION	"Indicates whether the SNMP agent process is
			permitted to generate diskReadFailure traps."
	::= { disk 19 }

    diskWriteFailureTrap OBJECT-TYPE
	SYNTAX		INTEGER {
			    enable(1),
			    disable(2),
			    retry(3)
			}
	ACCESS		read-write
	STATUS		mandatory
	DESCRIPTION	"Indicates whether the SNMP agent process is
			permitted to generate diskWriteFailure traps."
	::= { disk 20 }

    diskFullTrap OBJECT-TYPE
	SYNTAX		INTEGER {
			    enable(1),
			    disable(2),
			    retry(3)
			}
	ACCESS		read-write
	STATUS		mandatory
	DESCRIPTION	"Indicates whether the SNMP agent process is
			permitted to generate diskFull traps."
	::= { disk 21 }

    diskRecoverableErrorTrap OBJECT-TYPE
	SYNTAX		INTEGER {
			    enable(1),
			    disable(2),
			    retry(3)
			}
	ACCESS		read-write
	STATUS		mandatory
	DESCRIPTION	"Indicates whether the SNMP agent process is
			permitted to generate diskRecoverableError traps."
	::= { disk 22 }

    diskCriticalErrorTrap OBJECT-TYPE
	SYNTAX		INTEGER {
			    enable(1),
			    disable(2),
			    retry(3)
			}
	ACCESS		read-write
	STATUS		mandatory
	DESCRIPTION	"Indicates whether the SNMP agent process is
			permitted to generate diskCriticalError traps."
	::= { disk 23 }

    diskFatalErrorTrap OBJECT-TYPE
	SYNTAX		INTEGER {
			    enable(1),
			    disable(2),
			    retry(3)
			}
	ACCESS		read-write
	STATUS		mandatory
	DESCRIPTION	"Indicates whether the SNMP agent process is
			permitted to generate diskFatalError traps."
	::= { disk 24 }

    diskReadFailureEmail OBJECT-TYPE
	SYNTAX		INTEGER {
			    enable(1),
			    disable(2)
			}
	ACCESS		read-write
	STATUS		mandatory
	DESCRIPTION	"Indicates whether the SMTP process is
			permitted to generate diskReadFailure Email."
	::= { disk 25 }

    diskWriteFailureEmail OBJECT-TYPE
	SYNTAX		INTEGER {
			    enable(1),
			    disable(2)
			}
	ACCESS		read-write
	STATUS		mandatory
	DESCRIPTION	"Indicates whether the SMTP process is
			permitted to generate diskWriteFailure Email."
	::= { disk 26 }

    diskFullEmail OBJECT-TYPE
	SYNTAX		INTEGER {
			    enable(1),
			    disable(2)
			}
	ACCESS		read-write
	STATUS		mandatory
	DESCRIPTION	"Indicates whether the SMTP process is
			permitted to generate diskFull Email."
	::= { disk 27 }

    diskRecoverableErrorEmail OBJECT-TYPE
	SYNTAX		INTEGER {
			    enable(1),
			    disable(2)
			}
	ACCESS		read-write
	STATUS		mandatory
	DESCRIPTION	"Indicates whether the SMTP process is
			permitted to generate diskRecoverableError Email."
	::= { disk 28 }

    diskCriticalErrorEmail OBJECT-TYPE
	SYNTAX		INTEGER {
			    enable(1),
			    disable(2)
			}
	ACCESS		read-write
	STATUS		mandatory
	DESCRIPTION	"Indicates whether the SMTP process is
			permitted to generate diskCriticalError Email."
	::= { disk 29 }

    diskFatalErrorEmail OBJECT-TYPE
	SYNTAX		INTEGER {
			    enable(1),
			    disable(2)
			}
	ACCESS		read-write
	STATUS		mandatory
	DESCRIPTION	"Indicates whether the SMTP process is
			permitted to generate diskCriticalError Email."
	::= { disk 30 }

    diskEraseAll OBJECT-TYPE
	SYNTAX		INTEGER
	ACCESS		read-write
	STATUS		optional
	DESCRIPTION	"When Set Zero then erase all disk images. 
			If access policy (diskAccessControl) was disable 
			then ignore request.
			when Get then return disk used kilobytes."
	::= { disk 32 }

    diskFormat OBJECT-TYPE
	SYNTAX		INTEGER
	ACCESS		read-write
	STATUS		optional
	DESCRIPTION	"When Set Zero then format disk,
			without depend on access policy (diskAccessControl).
			When Get then return disk used kilobytes."
	::= { disk 33 }

    diskSpaceLeastTrap OBJECT-TYPE
	SYNTAX		INTEGER {
			    enable(1),
			    disable(2),
			    onlyoverwriteoff(4)
			}
	ACCESS		read-write
	STATUS		mandatory
	DESCRIPTION	"Indicates whether the SMTP process is
			permitted to generate diskSpaceLeast traps."
	::= { disk 34 }

    diskQuota OBJECT-TYPE
	SYNTAX		INTEGER (0..99)
	ACCESS		read-write
	STATUS		mandatory
	DESCRIPTION	"The quota percent size of the disk."
	::= { disk 35 }

    diskSpaceLeastEmail OBJECT-TYPE
	SYNTAX		INTEGER {
			    enable(1),
			    disable(2)
			}
	ACCESS		read-write
	STATUS		mandatory
	DESCRIPTION	"Indicates whether the SMTP process is
			permitted to generate diskSpaceLeast Email."
	::= { disk 36 }

 -- Following variable are support Ver 3.7 or Later

    diskSpaceLeastRemoteCommand OBJECT-TYPE
	SYNTAX		INTEGER {
			    enable(1),
			    disable(2)
			}
	ACCESS		read-write
	STATUS		mandatory
	DESCRIPTION	"Indicates whether the SNMP agent process is
			permitted to generate diskSpaceLeast
			remote command."
	::= { disk 37 }

    diskReadFailureRemoteCommand OBJECT-TYPE
	SYNTAX		INTEGER {
			    enable(1),
			    disable(2)
			}
	ACCESS		read-write
	STATUS		mandatory
	DESCRIPTION	"Indicates whether the SNMP agent process is
			permitted to generate diskReadFailure
			remote command."
	::= { disk 38 }

    diskWriteFailureRemoteCommand OBJECT-TYPE
	SYNTAX		INTEGER {
			    enable(1),
			    disable(2)
			}
	ACCESS		read-write
	STATUS		mandatory
	DESCRIPTION	"Indicates whether the SNMP agent process is
			permitted to generate diskWriteFailure
			remote command."
	::= { disk 39 }

    diskFullRemoteCommand OBJECT-TYPE
	SYNTAX		INTEGER {
			    enable(1),
			    disable(2)
			}
	ACCESS		read-write
	STATUS		mandatory
	DESCRIPTION	"Indicates whether the SNMP agent process is
			permitted to generate diskFull
			remote command."
	::= { disk 40 }

    diskRecoverableErrorRemoteCommand OBJECT-TYPE
	SYNTAX		INTEGER {
			    enable(1),
			    disable(2)
			}
	ACCESS		read-write
	STATUS		mandatory
	DESCRIPTION	"Indicates whether the SNMP agent process is
			permitted to generate diskRecoverableError
			remote command."
	::= { disk 41 }

    diskCriticalErrorRemoteCommand OBJECT-TYPE
	SYNTAX		INTEGER {
			    enable(1),
			    disable(2)
			}
	ACCESS		read-write
	STATUS		mandatory
	DESCRIPTION	"Indicates whether the SNMP agent process is
			permitted to generate diskCriticalError
			remote command."
	::= { disk 42 }

    diskFatalErrorRemoteCommand OBJECT-TYPE
	SYNTAX		INTEGER {
			    enable(1),
			    disable(2)
			}
	ACCESS		read-write
	STATUS		mandatory
	DESCRIPTION	"Indicates whether the SNMP agent process is
			permitted to generate diskFatalError
			remote command."
	::= { disk 43 }

    diskSpaceLeastRemoteCommandSet OBJECT-TYPE

	SYNTAX		INTEGER (1..32)
	ACCESS		read-write
	STATUS		mandatory
	DESCRIPTION	"Indicates diskSpaceLeast
			remote command set number generated."
	::= { disk 44 }

    diskReadFailureRemoteCommandSet OBJECT-TYPE
	SYNTAX		INTEGER (1..32)
	ACCESS		read-write
	STATUS		mandatory
	DESCRIPTION	"Indicates diskReadFailure
			remote command set number generated."
	::= { disk 45 }

    diskWriteFailureRemoteCommandSet OBJECT-TYPE
	SYNTAX		INTEGER (1..32)
	ACCESS		read-write
	STATUS		mandatory
	DESCRIPTION	"Indicates diskWriteFailure
			remote command set number generated."
	::= { disk 46 }

    diskFullRemoteCommandSet OBJECT-TYPE
	SYNTAX		INTEGER (1..32)
	ACCESS		read-write
	STATUS		mandatory
	DESCRIPTION	"Indicates diskFull
			remote command set number generated."
	::= { disk 47 }

    diskRecoverableErrorRemoteCommandSet OBJECT-TYPE
	SYNTAX		INTEGER (1..32)
	ACCESS		read-write
	STATUS		mandatory
	DESCRIPTION	"Indicates diskRecoverableError
			remote command set number generated."
	::= { disk 48 }

    diskCriticalErrorRemoteCommandSet OBJECT-TYPE
	SYNTAX		INTEGER (1..32)
	ACCESS		read-write
	STATUS		mandatory
	DESCRIPTION	"Indicates diskCriticalError
			remote command set number generated."
	::= { disk 49 }

    diskFatalErrorRemoteCommandSet OBJECT-TYPE
	SYNTAX		INTEGER (1..32)
	ACCESS		read-write
	STATUS		mandatory
	DESCRIPTION	"Indicates diskFatalError
			remote command set number generated."
	::= { disk 50 }

-- The Timer Group

    timerNumber		OBJECT-TYPE
	SYNTAX		INTEGER
	ACCESS		read-only
	STATUS		mandatory
	DESCRIPTION	"The number of timer entry supported by this device."
	::= { ndMgmt 10 }

    timerTable		OBJECT-TYPE
	SYNTAX		SEQUENCE OF TimerEntry
	ACCESS		not-accessible
	STATUS		mandatory
	DESCRIPTION	"A list of timer entries. The number of entries
			is given by the value timerNumber."
	::= { ndMgmt 11 }

    timerEntry		OBJECT-TYPE
	SYNTAX		TimerEntry
	ACCESS		not-accessible
	STATUS		mandatory
	DESCRIPTION	"A timer entry containing objects to describe
			the timer."
	INDEX		{ timerIndex }
	::= { timerTable 1 }

    TimerEntry ::=
	SEQUENCE {
	    timerIndex
		INTEGER,
	    timerEntryEnable
		INTEGER,
	    timerDateTime
	        DisplayString,
	    timerSetObjectID
		OBJECT IDENTIFIER,
	    timerSetValue
		INTEGER
	}

    timerIndex		OBJECT-TYPE
	SYNTAX		INTEGER
	ACCESS		read-only
	STATUS		mandatory
	DESCRIPTION	"A unique value for each timer entry. It's value ranges
			between 1 and the value timerNumber."
	::= { timerEntry 1 }

    timerEntryEnable	OBJECT-TYPE
	SYNTAX		INTEGER {
			    enable(1),
			    disable(2)
			}
	ACCESS		read-write
	STATUS		mandatory
	DESCRIPTION	"Indicates whether the SNMP agent process
			permitted to manage with this timerEntry."
	::= { timerEntry 2 }

    timerDateTime	OBJECT-TYPE
	SYNTAX		DisplayString (SIZE (1..32))
	ACCESS		read-write
	STATUS		mandatory
	DESCRIPTION	"The text string is timer start date time.
			read manual for more detail."
	::= { timerEntry 3 }

    timerSetObjectID	OBJECT-TYPE
	SYNTAX		OBJECT IDENTIFIER
	ACCESS		read-write
	STATUS		mandatory
	DESCRIPTION	"The ObjectID is set the timerSetValue by timer."
	::= { timerEntry 4 }

    timerSetValue	OBJECT-TYPE
	SYNTAX		INTEGER
	ACCESS		read-write
	STATUS		mandatory
	DESCRIPTION	"The value is outputted via the timerSetObjectID
			by timer."
	::= { timerEntry 5 }

-- The Trap Log Group 

    trapLogNumber	OBJECT-TYPE
	SYNTAX		INTEGER
	ACCESS		read-only
	STATUS		mandatory
	DESCRIPTION	"The number of trap log preserved by this device."
	::= { ndMgmt 12 }

    trapLogEnable	OBJECT-TYPE
	SYNTAX		INTEGER {
			    enable(1),
			    disable(2)
			}
	ACCESS		read-write
	STATUS		mandatory
	DESCRIPTION	"Indicates whether the SNMP agent process is
			permitted to log SNMP trap."
	::= { ndMgmt 13 }

    trapLogTable	OBJECT-TYPE
	SYNTAX		SEQUENCE OF TrapLogEntry
	ACCESS		not-accessible
	STATUS		mandatory
	DESCRIPTION	"A list of trap log entries. The number of entries
			is given by the value trapLogNumber."
	::= { ndMgmt 14 }

    trapLogEntry	OBJECT-TYPE
	SYNTAX		TrapLogEntry
	ACCESS		not-accessible
	STATUS		mandatory
	DESCRIPTION	"A trap log entry containing objects to describe the
			trap log."
	INDEX		{ trapLogIndex }
	::= { trapLogTable 1 }

    TrapLogEntry ::=
	SEQUENCE {
	    trapLogIndex
		INTEGER,
	    trapLogDateTime
	        DisplayString,
	    trapLogGenericTrapNo
		INTEGER,
	    trapLogSpecificTrapNo
		INTEGER,
	    trapLogObjectID
		OBJECT IDENTIFIER,
	    trapLogValue
		INTEGER,
	    trapLogStringValue
	        DisplayString
	}

    trapLogIndex	OBJECT-TYPE
	SYNTAX		INTEGER
	ACCESS		read-only
	STATUS		mandatory
	DESCRIPTION	"A unique value for each trap log entry. It's value
			ranges between 1 and the value trapLogNumber."
	::= { trapLogEntry 1 }

    trapLogDateTime	OBJECT-TYPE
	SYNTAX		DisplayString
	ACCESS		read-only
	STATUS		mandatory
	DESCRIPTION	"The date and time when trap log was preserved."
	::= { trapLogEntry 2 }

    trapLogGenericTrapNo OBJECT-TYPE
	SYNTAX		INTEGER {
			    coldStart(0),
			    warmStart(1),
			    linkDown(2),
			    linkUp(3),
			    authenticationFailure(4),
			    egpNeighborLoss(5),
			    enterprise-specific(6)
			}
	ACCESS		read-only
	STATUS		mandatory
	DESCRIPTION	"This value is the generic trap number is occured."
	::= { trapLogEntry 3 }

    trapLogSpecificTrapNo OBJECT-TYPE
	SYNTAX		INTEGER
	ACCESS		read-only
	STATUS		mandatory
	DESCRIPTION	"This value is the specific trap number is occured."
	::= { trapLogEntry 4 }

    trapLogObjectID	OBJECT-TYPE
	SYNTAX		OBJECT IDENTIFIER
	ACCESS		read-only
	STATUS		mandatory
	DESCRIPTION	"This value is the ObjectID that trap is occured."
	::= { trapLogEntry 5 }

    trapLogValue	OBJECT-TYPE
	SYNTAX		INTEGER
	ACCESS		read-only
	STATUS		mandatory
	DESCRIPTION	"This value is the value when trap is occured."
	::= { trapLogEntry 6 }

    trapLogStringValue	OBJECT-TYPE
	SYNTAX		DisplayString
	ACCESS		read-only
	STATUS		mandatory
	DESCRIPTION	"This value is the value when trap is occured."
	::= { trapLogEntry 7 }

-- The Data Log Group

    dataLogNumber	OBJECT-TYPE
	SYNTAX		INTEGER
	ACCESS		read-only
	STATUS		mandatory
	DESCRIPTION	"The number of data log preserved by this device."
	::= { ndMgmt 15 }

    dataLogTable	OBJECT-TYPE
	SYNTAX		SEQUENCE OF DataLogEntry
	ACCESS		not-accessible
	STATUS		mandatory
	DESCRIPTION	"A list of data log entries. The number of entries
			is given by the value dataLogNumber."
	::= { ndMgmt 16 }

    dataLogEntry	OBJECT-TYPE
	SYNTAX		DataLogEntry
	ACCESS		not-accessible
	STATUS		mandatory
	DESCRIPTION	"A data log entry containing objects to describe the
			data log."
	INDEX		{ dataLogIndex }
	::= { dataLogTable 1 }

    DataLogEntry ::=
	SEQUENCE {
	    dataLogIndex
		INTEGER,
	    dataLogDateTime
	        DisplayString,
	    dataLogObjectID
		OBJECT IDENTIFIER,
	    dataLogValue
		INTEGER
	}

    dataLogIndex	OBJECT-TYPE
	SYNTAX		INTEGER
	ACCESS		read-only
	STATUS		mandatory
	DESCRIPTION	"A unique value for each data log entry. It's value
			ranges between 1 and the value dataLogNumber."
	::= { dataLogEntry 1 }

    dataLogDateTime	OBJECT-TYPE
	SYNTAX		DisplayString
	ACCESS		read-only
	STATUS		mandatory
	DESCRIPTION	"The date and time when data log was preserved."
	::= { dataLogEntry 2 }

    dataLogObjectID	OBJECT-TYPE
	SYNTAX		OBJECT IDENTIFIER
	ACCESS		read-only
	STATUS		mandatory
	DESCRIPTION	"This value is the ObjectID that
			data log was preserved."
	::= { dataLogEntry 3 }

    dataLogValue	OBJECT-TYPE
	SYNTAX		INTEGER
	ACCESS		read-only
	STATUS		mandatory
	DESCRIPTION	"This value is the value that
			data log was preserved."
	::= { dataLogEntry 4 }

-- The Mail Log Group (Ver 3.0 or Later support)

    mailLogNumber	OBJECT-TYPE
	SYNTAX		INTEGER
	ACCESS		read-only
	STATUS		mandatory
	DESCRIPTION	"The number of maillog log preserved by this device."
	::= { ndMgmt 17 }

    mailLogEnable	OBJECT-TYPE
	SYNTAX		INTEGER {
			    enable(1),
			    disable(2)
			}
	ACCESS		read-write
	STATUS		mandatory
	DESCRIPTION	"Indicates whether the email future
			permitted to log SNMP maillog."
	::= { ndMgmt 18 }

    mailLogTable	OBJECT-TYPE
	SYNTAX		SEQUENCE OF MailLogEntry
	ACCESS		not-accessible
	STATUS		mandatory
	DESCRIPTION	"A list of maillog log entries. The number of entries
			is given by the value mailLogNumber."
	::= { ndMgmt 19 }

    mailLogEntry	OBJECT-TYPE
	SYNTAX		MailLogEntry
	ACCESS		not-accessible
	STATUS		mandatory
	DESCRIPTION	"A maillog log entry containing objects to describe the
			mail log."
	INDEX		{ mailLogIndex }
	::= { mailLogTable 1 }

    MailLogEntry ::=
	SEQUENCE {
	    mailLogIndex
		INTEGER,
	    mailLogDateTime
	        DisplayString,
	    mailLogGenericTrapNo
		INTEGER,
	    mailLogSpecificTrapNo
		INTEGER,
	    mailLogObjectID
		OBJECT IDENTIFIER,
	    mailLogValue
		INTEGER,
	    mailLogStringValue
	        DisplayString,
	    mailLogDestination
		INTEGER,
	    mailLogStatus
		INTEGER
	}

    mailLogIndex	OBJECT-TYPE
	SYNTAX		INTEGER
	ACCESS		read-only
	STATUS		mandatory
	DESCRIPTION	"A unique value for each mail log entry. It's value
			ranges between 1 and the value mailLogNumber."
	::= { mailLogEntry 1 }

    mailLogDateTime	OBJECT-TYPE
	SYNTAX		DisplayString
	ACCESS		read-only
	STATUS		mandatory
	DESCRIPTION	"The date and time when mail log was preserved."
	::= { mailLogEntry 2 }

    mailLogGenericTrapNo OBJECT-TYPE
	SYNTAX		INTEGER {
			    coldStart(0),
			    warmStart(1),
			    linkDown(2),
			    linkUp(3),
			    authenticationFailure(4),
			    egpNeighborLoss(5),
			    enterprise-specific(6),
			    userMail(100)
			}
	ACCESS		read-only
	STATUS		mandatory
	DESCRIPTION	"This value is the generic trap number is occured."
	::= { mailLogEntry 3 }

    mailLogSpecificTrapNo OBJECT-TYPE
	SYNTAX		INTEGER
	ACCESS		read-only
	STATUS		mandatory
	DESCRIPTION	"This value is the specific trap number is occured."
	::= { mailLogEntry 4 }

    mailLogObjectID	OBJECT-TYPE
	SYNTAX		OBJECT IDENTIFIER
	ACCESS		read-only
	STATUS		mandatory
	DESCRIPTION	"This value is the ObjectID that mail is occured."
	::= { mailLogEntry 5 }

    mailLogValue	OBJECT-TYPE
	SYNTAX		INTEGER
	ACCESS		read-only
	STATUS		mandatory
	DESCRIPTION	"This value is the value when mail is occured."
	::= { mailLogEntry 6 }

    mailLogStringValue	OBJECT-TYPE
	SYNTAX		DisplayString
	ACCESS		read-only
	STATUS		mandatory
	DESCRIPTION	"This value is the value when mail is occured."
	::= { mailLogEntry 7 }

    mailLogDestination	OBJECT-TYPE
	SYNTAX		INTEGER
	ACCESS		read-only
	STATUS		mandatory
	DESCRIPTION	"This value is the destination table number."
	::= { mailLogEntry 8 }

    mailLogStatus	OBJECT-TYPE
			-- SMTP Error code RFC821 Section 4.2.2 for more detail.
			-- expect smtpTransactionCompleted(32767)
	SYNTAX		INTEGER {
				smtpConnectionError(-1),
				smtpTransactionCompleted(32767),
				smtpSystemReady(211), 
				smtpHelpMessage(214),
				smtpServiceReady(220), 
				smtpServiceClosingCh2(221), 
				smtpRequestMailOk(250), 
				smtpUserNotLocal(251), 
				smtpStartMailInput(354), 
				smtpServiceNotAvailable(421), 
				smtpMailBoxUnavailabl(450), 
				smtpAbortLocalError(451), 
				smtpStorageNotTaken(452), 
				smtpFatalSyntaxError(500), 	
				smtpFatalArgumentSyntaxError(501), 
				smtpFatalNotImplemented(502), 
				smtpFatalBadSequence(503), 
				smtpFatalParamNotImplemented(504), 
				smtpFatalMailBoxFatalUnavailable(550), 
				smtpFatalUserNotLocal(551), 
				smtpFatalStorageNotTaken(552), 
				smtpFatalMailBoxName(553), 
				smtpFatalTransactionError(554) 
			}
	ACCESS		read-only
	STATUS		mandatory
	DESCRIPTION	"This value is mail send status."
	::= { mailLogEntry 9 }

    ndUserDefinedTrapNumber	OBJECT-TYPE
	SYNTAX		INTEGER
	ACCESS		read-only
	STATUS		mandatory
	DESCRIPTION	"The number of ndUserDefinedTrap preserved
			by this device."
	::= { ndMgmt 20 }

    ndUserDefinedTrapTable	OBJECT-TYPE
	SYNTAX		SEQUENCE OF NdUserDefinedTrapEntry
	ACCESS		not-accessible
	STATUS		mandatory
	DESCRIPTION	"A list of ndUserDefinedTrap entries.
			The number of entries is given
			by the value ndUserDefinedTrapNumber."
	::= { ndMgmt 21 }

    ndUserDefinedTrapEntry	OBJECT-TYPE
	SYNTAX		NdUserDefinedTrapEntry
	ACCESS		not-accessible
	STATUS		mandatory
	DESCRIPTION	"A ndUserDefinedTrap entry containing objects
			to describe the ndUserDefinedTrap."
	INDEX		{ ndUserDefinedTrapIndex }
	::= { ndUserDefinedTrapTable 1 }

    NdUserDefinedTrapEntry ::=
	SEQUENCE {
	    ndUserDefinedTrapIndex
		INTEGER,
	    ndUserDefinedTrapType
	        DisplayString,
	    ndUserDefinedTrapValue
		INTEGER
	}

    ndUserDefinedTrapIndex	OBJECT-TYPE
	SYNTAX		INTEGER
	ACCESS		not-accessible
	STATUS		mandatory
	DESCRIPTION	"A unique value for each UserDefined channel."
	::= { ndUserDefinedTrapEntry 1 }

    ndUserDefinedTrapType	OBJECT-TYPE
	SYNTAX		DisplayString (SIZE (1..32))
	ACCESS		not-accessible
	STATUS		mandatory
	DESCRIPTION	"The text string is type of UserDefined value."
	::= { ndUserDefinedTrapEntry 2 }

    ndUserDefinedTrapValue	OBJECT-TYPE
	SYNTAX		INTEGER
	ACCESS		not-accessible
	STATUS		mandatory
	DESCRIPTION	"The value of UserDefined channel."
	::= { ndUserDefinedTrapEntry 3 }


-- Cron Run Timer Period Group

    cronRunTimerPeriodNumber OBJECT-TYPE
	SYNTAX		INTEGER
	ACCESS		read-only
	STATUS		optional
	DESCRIPTION	"The number of cronRunTimerPeriod entries."
	::= { ndMgmt 22 }

-- The Period table for cronRunTimerPeriod
--
-- This table contains cronRunTimerPeriodNumber entries describing each Period.
--

    cronRunTimerPeriodTable OBJECT-TYPE
	SYNTAX		SEQUENCE OF CronRunTimerPeriodEntry
	ACCESS		not-accessible
	STATUS		optional
	DESCRIPTION	"A list of cronRunTimerPeriod table. 
			The number of entries is given by the
			value cronRunTimerPeriodNumber."
	::= { ndMgmt 23 }

    cronRunTimerPeriodEntry OBJECT-TYPE
	SYNTAX		CronRunTimerPeriodEntry
	ACCESS		not-accessible
	STATUS		optional
	DESCRIPTION	"A cron run timer period entry containing objects to
			describe the cron run timer period."
	INDEX		{ cronRunTimerPeriodIndex }
	::= { cronRunTimerPeriodTable 1 }

    CronRunTimerPeriodEntry ::=
	SEQUENCE {
	    cronRunTimerPeriodIndex
		INTEGER,
	    cronRunTimerPeriodEnable
		INTEGER,
	    cronRunTimerPeriodDate
		DisplayString,
	    cronRunTimerPeriodTime
		DisplayString,
	    cronRunTimerPeriodFileName
		DisplayString
	}

    cronRunTimerPeriodIndex OBJECT-TYPE
	SYNTAX		INTEGER
	ACCESS		read-only
	STATUS		optional
	DESCRIPTION	"A unique value for each cronRunTimerPeriod entry.
			It's value ranges between 1 and the value
			cronRunTimerPeriodNumber."
	::= { cronRunTimerPeriodEntry 1 }

    cronRunTimerPeriodEnable OBJECT-TYPE
	SYNTAX		INTEGER {
			    enable(1),
			    disable(2)
			}
	ACCESS		read-write
	STATUS		optional
	DESCRIPTION	"Indicates whether the SNMP agent process
			permitted to manage with this cronRunTimerPeriodEntry."
	::= { cronRunTimerPeriodEntry 2 }

    cronRunTimerPeriodDate OBJECT-TYPE
	SYNTAX		DisplayString (SIZE (1..32))
	ACCESS		read-write
	STATUS		optional
	DESCRIPTION	"The text string is date to cron run timer period.
			read manual for more detail."
	::= { cronRunTimerPeriodEntry 3 }

    cronRunTimerPeriodTime OBJECT-TYPE
	SYNTAX		DisplayString (SIZE (1..32))
	ACCESS		read-write
	STATUS		optional
	DESCRIPTION	"The text string is time to cron run timer period.
			read manual for more detail."
	::= { cronRunTimerPeriodEntry 4 }

    cronRunTimerPeriodFileName OBJECT-TYPE
	SYNTAX		DisplayString (SIZE (1..63))
	ACCESS		read-write
	STATUS		optional
	DESCRIPTION	"The text string is executable file name to 
				cron run timer period.
				read manual for more detail."
	::= { cronRunTimerPeriodEntry 5 }

-- The Remote Command Log Group (Ver 3.6 or Later support)

    remoteCommandLogNumber	OBJECT-TYPE
	SYNTAX		INTEGER
	ACCESS		read-only
	STATUS		mandatory
	DESCRIPTION	"The number of remote command log preserved by this device."
	::= { ndMgmt 24 }

    remoteCommandLogTable	OBJECT-TYPE
	SYNTAX		SEQUENCE OF RemoteCommandLogEntry
	ACCESS		not-accessible
	STATUS		mandatory
	DESCRIPTION	"A list of remote command log entries. 
			The number of entries is given by the value remoteLogNumber."
	::= { ndMgmt 25 }

    remoteCommandLogEntry	OBJECT-TYPE
	SYNTAX		RemoteCommandLogEntry
	ACCESS		not-accessible
	STATUS		mandatory
	DESCRIPTION	"A remote command log entry containing objects to describe the
			remote command log."
	INDEX		{ remoteCommandLogIndex }
	::= { remoteCommandLogTable 1 }

    RemoteCommandLogEntry ::=
	SEQUENCE {
	    remoteCommandLogIndex
		INTEGER,
	    remoteCommandLogDateTime
	        DisplayString,
	    remoteCommandLogGenericTrapNo
		INTEGER,
	    remoteCommandLogSpecificTrapNo
		INTEGER,
	    remoteCommandLogObjectID
		OBJECT IDENTIFIER,
	    remoteCommandLogValue
		INTEGER,
	    remoteCommandLogStringValue
	        DisplayString,
	    remoteCommandLogCommandSet
		INTEGER,
	    remoteCommandLogStatus
		INTEGER
	}

    remoteCommandLogIndex	OBJECT-TYPE
	SYNTAX		INTEGER
	ACCESS		read-only
	STATUS		mandatory
	DESCRIPTION	"A unique value for each remote command log entry.
			It's value ranges between 1 and the value remoteCommandLogNumber."
	::= { remoteCommandLogEntry 1 }

    remoteCommandLogDateTime	OBJECT-TYPE
	SYNTAX		DisplayString
	ACCESS		read-only
	STATUS		mandatory
	DESCRIPTION	"The date and time when remote command log was preserved."
	::= { remoteCommandLogEntry 2 }

    remoteCommandLogGenericTrapNo OBJECT-TYPE
	SYNTAX		INTEGER {
			    coldStart(0),
			    warmStart(1),
			    linkDown(2),
			    linkUp(3),
			    authenticationFailure(4),
			    egpNeighborLoss(5),
			    enterprise-specific(6),
			    userCommand(101),
			    userFullCommand(102)
			}
	ACCESS		read-only
	STATUS		mandatory
	DESCRIPTION	"This value is the generic trap number is occured."
	::= { remoteCommandLogEntry 3 }

    remoteCommandLogSpecificTrapNo OBJECT-TYPE
	SYNTAX		INTEGER
	ACCESS		read-only
	STATUS		mandatory
	DESCRIPTION	"This value is the specific trap number is occured."
	::= { remoteCommandLogEntry 4 }

    remoteCommandLogObjectID	OBJECT-TYPE
	SYNTAX		OBJECT IDENTIFIER
	ACCESS		read-only
	STATUS		mandatory
	DESCRIPTION	"This value is the ObjectID that remote command is occured."
	::= { remoteCommandLogEntry 5 }

    remoteCommandLogValue	OBJECT-TYPE
	SYNTAX		INTEGER
	ACCESS		read-only
	STATUS		mandatory
	DESCRIPTION	"This value is the value when remote command is occured."
	::= { remoteCommandLogEntry 6 }

    remoteCommandLogStringValue	OBJECT-TYPE
	SYNTAX		DisplayString
	ACCESS		read-only
	STATUS		mandatory
	DESCRIPTION	"This value is the value when remote command is occured."
	::= { remoteCommandLogEntry 7 }

    remoteCommandLogCommandSet	OBJECT-TYPE
	SYNTAX		INTEGER (1..4)
	ACCESS		read-only
	STATUS		mandatory
	DESCRIPTION	"This value is the remote command set table number."
	::= { remoteCommandLogEntry 8 }

    remoteCommandLogStatus	OBJECT-TYPE
	SYNTAX		INTEGER {
				succeed(0),
				loginFail(1),
				timeOut(2), 
				timeOver(3),
				disable(4), 
				noHostAddress(5), 
				noUser(6), 
				noCommand(7)
			}
	ACCESS		read-only
	STATUS		mandatory
	DESCRIPTION	"This value is remote command execute status."
	::= { remoteCommandLogEntry 9 }

-- CEC network-device Period Log Timer Group (Ver 4.x or Later support)

    logTimerPeriodNumber	OBJECT-TYPE
	SYNTAX		INTEGER
	ACCESS		read-only
	STATUS		mandatory
	DESCRIPTION	"The number of fixed periodic log preserved by this device."
	::= { ndMgmt 26 }

    logTimerPeriodTable	OBJECT-TYPE
	SYNTAX		SEQUENCE OF LogTimerPeriodEntry
	ACCESS		not-accessible
	STATUS		mandatory
	DESCRIPTION	"A list of fixed periodic log entries. 
			The number of entries is given by the value logTimerPeriodNumber."
	::= { ndMgmt 27 }

    logTimerPeriodEntry	OBJECT-TYPE
	SYNTAX		LogTimerPeriodEntry
	ACCESS		not-accessible
	STATUS		mandatory
	DESCRIPTION	"Fixed periodic log entry containing objects to describe the
			data."
	INDEX		{ logTimerPeriodIndex }
	::= { logTimerPeriodTable 1 }

    LogTimerPeriodEntry ::=
	SEQUENCE {
	    logTimerPeriodIndex
		INTEGER,
	    logTimerPeriodEnable
		INTEGER,
	    logTimerPeriodDate
	    DisplayString,
	    logTimerPeriodTime
	    DisplayString,
	    logTimerPeriodADChannel
	    DisplayString,
	    logTimerPeriodDIChannel
	    DisplayString,
	    logTimerPeriodDOChannel
	    DisplayString
	}

    logTimerPeriodIndex	OBJECT-TYPE
	SYNTAX		INTEGER
	ACCESS		read-only
	STATUS		mandatory
	DESCRIPTION	"A unique value for each fixed periodic log entry.
			It's value ranges between 1 and the value logTimerPeriodNumber."
	::= { logTimerPeriodEntry 1 }

    logTimerPeriodEnable	OBJECT-TYPE
	SYNTAX		INTEGER {
					enable(1),
					disable(2)
				}
	ACCESS		read-write
	STATUS		mandatory
	DESCRIPTION	"Indicates whether the SNMP agent process
			permitted to manage with this logTiemerPeriodEntry."
	::= { logTimerPeriodEntry 2 }

    logTimerPeriodDate	OBJECT-TYPE
	SYNTAX		DisplayString (SIZE (0..32))
	ACCESS		read-write
	STATUS		mandatory
	DESCRIPTION	"The date when fixed periodic log was preserved."
	::= { logTimerPeriodEntry 3 }

    logTimerPeriodTime	OBJECT-TYPE
	SYNTAX		DisplayString (SIZE (0..32))
	ACCESS		read-write
	STATUS		mandatory
	DESCRIPTION	"The time when fixed periodic log was preserved."
	::= { logTimerPeriodEntry 4 }

    logTimerPeriodADChannel	OBJECT-TYPE
	SYNTAX		DisplayString (SIZE (0..512))
	ACCESS		read-write
	STATUS		mandatory
	DESCRIPTION	"It can setting of the AD channel when 
				fixed periodic log was preserved."
	::= { logTimerPeriodEntry 5 }

    logTimerPeriodDIChannel	OBJECT-TYPE
	SYNTAX		DisplayString (SIZE (0..512))
	ACCESS		read-write
	STATUS		mandatory
	DESCRIPTION	"It can setting of the DI channel when 
				fixed periodic log was preserved."
	::= { logTimerPeriodEntry 6 }

    logTimerPeriodDOChannel	OBJECT-TYPE
	SYNTAX		DisplayString (SIZE (0..512))
	ACCESS		read-write
	STATUS		mandatory
	DESCRIPTION	"It can setting of the DO channel when 
				fixed periodic log was preserved."
	::= { logTimerPeriodEntry 7 }

-- CEC network-device Lock Certify Log Group (Ver 4.2 or Later support)

    lockCertifyLogNumber	OBJECT-TYPE
	SYNTAX		INTEGER
	ACCESS		read-only
	STATUS		mandatory
	DESCRIPTION	"This value is the present number of certification logs."
	::= { ndMgmt 28 }

    lockCertifyLogTable	OBJECT-TYPE
	SYNTAX		SEQUENCE OF LockCertifyLogEntry
	ACCESS		not-accessible
	STATUS		mandatory
	DESCRIPTION	"The table of certification log."
	::= { ndMgmt 29 }

    lockCertifyLogEntry	OBJECT-TYPE
	SYNTAX		LockCertifyLogEntry
	ACCESS		not-accessible
	STATUS		mandatory
	DESCRIPTION	"The entry for certification log."
	INDEX		{ lockCertifyLogIndex }
	::= { lockCertifyLogTable 1 }

    LockCertifyLogEntry ::=
	SEQUENCE {
	    lockCertifyLogIndex
		INTEGER,
	    lockCertifyLogDateTime
	    	DisplayString,
	    lockCertifyLogUserID
		INTEGER,
	    lockCertifyLogEvent
	    	INTEGER,
	    lockCertifyLogResult
	    	INTEGER,
	    lockCertifyLogDO
	    	DisplayString,
	    lockCertifyLogDI
	    	DisplayString,
	    lockCertifyLogCardReaderID
	    	INTEGER
	}

    lockCertifyLogIndex	OBJECT-TYPE
	SYNTAX		INTEGER
	ACCESS		read-only
	STATUS		mandatory
	DESCRIPTION	"A unique value for each certification log entry. It's value
            ranges between 1 and the value certifyLogNumber."
	::= { lockCertifyLogEntry 1 }

    lockCertifyLogDateTime	OBJECT-TYPE
	SYNTAX		DisplayString (SIZE (0..32))
	ACCESS		read-only
	STATUS		mandatory
	DESCRIPTION	"The date and time in the certification log entry."
	::= { lockCertifyLogEntry 2 }

    lockCertifyLogUserID	OBJECT-TYPE
	SYNTAX		INTEGER
	ACCESS		read-only
	STATUS		mandatory
	DESCRIPTION	"The user ID in the certification log entry."
	::= { lockCertifyLogEntry 3 }

    lockCertifyLogEvent	OBJECT-TYPE
	SYNTAX		INTEGER {
					local-card-certification(1),
					local-tenkey-certification(2),
					remote-card-certification(3),
					remote-tenkey-certification(4),
					lock-selection(5),
					do-change(6),
					di-change(7),
					certification-data-clear(8)
				}
	ACCESS		read-only
	STATUS		mandatory
	DESCRIPTION	"The event which occurred in the certification log entry."
	::= { lockCertifyLogEntry 4 }

    lockCertifyLogResult	OBJECT-TYPE
	SYNTAX		INTEGER {
					ok(1),
					ng(2),
					timeout(3)
				}
	ACCESS		read-only
	STATUS		mandatory
	DESCRIPTION	"The certification result in the certification log entry."
	::= { lockCertifyLogEntry 5 }

    lockCertifyLogDO	OBJECT-TYPE
	SYNTAX		DisplayString (SIZE (0..32))
	ACCESS		read-only
	STATUS		mandatory
	DESCRIPTION	"The DO status in the certifaction log entry."
	::= { lockCertifyLogEntry 6 }

    lockCertifyLogDI	OBJECT-TYPE
	SYNTAX		DisplayString (SIZE (0..32))
	ACCESS		read-only
	STATUS		mandatory
	DESCRIPTION	"The DI status in the certifaction log entry."
	::= { lockCertifyLogEntry 7 }

    lockCertifyLogCardReaderID	OBJECT-TYPE
	SYNTAX		INTEGER (0..255)
	ACCESS		read-only
	STATUS		mandatory
	DESCRIPTION	"The card reader ID in the certification log entry."
	::= { lockCertifyLogEntry 8 }

-- CEC network-device Script Group (Ver 4.x or Later support)

    script	OBJECT IDENTIFIER ::= { ndMgmt 30 }

    integerVariableNumber	OBJECT-TYPE
	SYNTAX		INTEGER
	ACCESS		read-only
	STATUS		mandatory
	DESCRIPTION	"The number of integer script variables."
	::= { script 1 }

    integerVariableTable	OBJECT-TYPE
	SYNTAX		SEQUENCE OF IntegerVariableEntry
	ACCESS		not-accessible
	STATUS		mandatory
	DESCRIPTION	"The table of integer script variables."
	::= { script 2 }

    integerVariableEntry	OBJECT-TYPE
	SYNTAX		IntegerVariableEntry
	ACCESS		not-accessible
	STATUS		mandatory
	DESCRIPTION	"The entry of integer script variables."
	INDEX		{ integerVariableIndex }
	::= { integerVariableTable 1 }

    IntegerVariableEntry ::=
	SEQUENCE {
	    integerVariableIndex
		INTEGER,
	    integerVariableValue
	    	INTEGER
	}

    integerVariableIndex	OBJECT-TYPE
	SYNTAX		INTEGER
	ACCESS		read-only
	STATUS		mandatory
	DESCRIPTION	"An unique value for each integer script variable entry. It's value
            ranges between 1 and the value of integerVariableNumber."
	::= { integerVariableEntry 1 }

    integerVariableValue	OBJECT-TYPE
	SYNTAX		INTEGER
	ACCESS		read-write
	STATUS		mandatory
	DESCRIPTION	"A value of string integer variable."
	::= { integerVariableEntry 2 }

    stringVariableNumber	OBJECT-TYPE
	SYNTAX		INTEGER
	ACCESS		read-only
	STATUS		mandatory
	DESCRIPTION	"The number of string script variables."
	::= { script 3 }

    stringVariableTable	OBJECT-TYPE
	SYNTAX		SEQUENCE OF StringVariableEntry
	ACCESS		not-accessible
	STATUS		mandatory
	DESCRIPTION	"The table of string script variables."
	::= { script 4 }

    stringVariableEntry	OBJECT-TYPE
	SYNTAX		StringVariableEntry
	ACCESS		not-accessible
	STATUS		mandatory
	DESCRIPTION	"The entry of string script variables."
	INDEX		{ stringVariableIndex }
	::= { stringVariableTable 1 }

    StringVariableEntry ::=
	SEQUENCE {
	    stringVariableIndex
		INTEGER,
	    stringVariableValue
		DisplayString
	}

    stringVariableIndex	OBJECT-TYPE
	SYNTAX		INTEGER
	ACCESS		read-only
	STATUS		mandatory
	DESCRIPTION	"An unique value for each string script variable entry. It's value
            ranges between 1 and the value of stringVariableNumber."
	::= { stringVariableEntry 1 }

    stringVariableValue	OBJECT-TYPE
	SYNTAX		DisplayString
	ACCESS		read-write
	STATUS		mandatory
	DESCRIPTION	"A value of string script variable."
	::= { stringVariableEntry 2 }

    scriptVariableSave		OBJECT-TYPE
	SYNTAX		INTEGER
	ACCESS		read-write
	STATUS		optional
	DESCRIPTION	"Setting to any value will save current script variable
			to non-volatile memory. When read this will always
			return 0."
	::={ script 5 }

    scriptVariableLoad		OBJECT-TYPE
	SYNTAX		INTEGER
	ACCESS		read-write
	STATUS		optional
	DESCRIPTION	"Setting to any value will load current script variable
			from non-volatile memory. When read this will always
			return 0."
	::={ script 6 }

-- CEC network-device di Forward Send Change Log Group (Ver 5.x or Later support)

    diFwSendChangeLogNumber	OBJECT-TYPE
	SYNTAX		INTEGER
	ACCESS		read-only
	STATUS		mandatory
	DESCRIPTION	"The number of di forwarding change log preserved by this device."
	::= { ndMgmt 31 }

    diFwSendChangeLogTable	OBJECT-TYPE
	SYNTAX		SEQUENCE OF DiFwSendChangeLogEntry
	ACCESS		not-accessible
	STATUS		mandatory
	DESCRIPTION	"A list of di forwarding change log entries. The number of entries
			is given by the value diFwSendChangeLogNumber."
	::= { ndMgmt 32 }

    diFwSendChangeLogEntry	OBJECT-TYPE
	SYNTAX		DiFwSendChangeLogEntry
	ACCESS		not-accessible
	STATUS		mandatory
	DESCRIPTION	"A di forwarding change log entry containing objects to describe the
			di forwarding change log."
	INDEX		{ diFwSendChangeLogIndex }
	::= { diFwSendChangeLogTable 1 }

    DiFwSendChangeLogEntry ::=
	SEQUENCE {
	    diFwSendChangeLogIndex
		INTEGER,
	    diFwSendChangeLogDateTime
	        DisplayString,
	    diFwSendChangeLogIpAddress
	        DisplayString,
	    diFwSendChangeLogDoValues
	        DisplayString,
	    diFwSendChangeLogStatus
		INTEGER
	}

    diFwSendChangeLogIndex	OBJECT-TYPE
	SYNTAX		INTEGER
	ACCESS		read-only
	STATUS		mandatory
	DESCRIPTION	"A unique value for each di forwarding change log entry. It's value
			ranges between 1 and the value diFwSendChangeLogNumber."
	::= { diFwSendChangeLogEntry 1 }

    diFwSendChangeLogDateTime	OBJECT-TYPE
	SYNTAX		DisplayString
	ACCESS		read-only
	STATUS		mandatory
	DESCRIPTION	"The date and time when di forwarding change log was preserved."
	::= { diFwSendChangeLogEntry 2 }

    diFwSendChangeLogIpAddress	OBJECT-TYPE
	SYNTAX		DisplayString
	ACCESS		read-only
	STATUS		mandatory
	DESCRIPTION	"The peer host when di forwarding change log was preserved."
	::= { diFwSendChangeLogEntry 3 }

    diFwSendChangeLogDoValues	OBJECT-TYPE
	SYNTAX		DisplayString
	ACCESS		read-only
	STATUS		mandatory
	DESCRIPTION	"The doValues when di forwarding change log was preserved."
	::= { diFwSendChangeLogEntry 4 }

    diFwSendChangeLogStatus	OBJECT-TYPE
	SYNTAX          INTEGER {
			    ok(0),
			    tooBig(1),
			    noSuchName(2),
			    badValue(3),
			    wrongType(7),
			    wrongLength(8),
			    wrongValue(10),
			    timeOut(127),
			    cancel(128),
			    hostDown(129),
			    noRoute(130),
			    refused(131),
			    noName(132),
			    otherError(255)
			}
	ACCESS		read-only
	STATUS		mandatory
	DESCRIPTION	"A unique value for each di forwarding change log entry. It's value
			ranges between 1 and the value diFwSendChangeLogNumber."
	::= { diFwSendChangeLogEntry 5 }


-- CEC network-device di Forward Send Cycle Log Group (Ver 5.x or Later support)

    diFwSendCycleLogNumber	OBJECT-TYPE
	SYNTAX		INTEGER
	ACCESS		read-only
	STATUS		mandatory
	DESCRIPTION	"The number of di forwarding log preserved by this device."
	::= { ndMgmt 33 }

    diFwSendCycleLogTable	OBJECT-TYPE
	SYNTAX		SEQUENCE OF DiFwSendCycleLogEntry
	ACCESS		not-accessible
	STATUS		mandatory
	DESCRIPTION	"A list of di forwarding log entries. The number of entries
			is given by the value diFwSendCycleLogNumber."
	::= { ndMgmt 34 }

    diFwSendCycleLogEntry	OBJECT-TYPE
	SYNTAX		DiFwSendCycleLogEntry
	ACCESS		not-accessible
	STATUS		mandatory
	DESCRIPTION	"A di forwarding log entry containing objects to describe the
			di forwarding log."
	INDEX		{ diFwSendCycleLogIndex }
	::= { diFwSendCycleLogTable 1 }

    DiFwSendCycleLogEntry ::=
	SEQUENCE {
	    diFwSendCycleLogIndex
		INTEGER,
	    diFwSendCycleLogDateTime
	        DisplayString,
	    diFwSendCycleLogIpAddress
	        DisplayString,
	    diFwSendCycleLogDoValues
	        DisplayString,
	    diFwSendCycleLogStatus
		INTEGER
	}

    diFwSendCycleLogIndex	OBJECT-TYPE
	SYNTAX		INTEGER
	ACCESS		read-only
	STATUS		mandatory
	DESCRIPTION	"A unique value for each di forwarding cycle log entry. It's value
			ranges between 1 and the value diFwSendCycleLogNumber."
	::= { diFwSendCycleLogEntry 1 }

    diFwSendCycleLogDateTime	OBJECT-TYPE
	SYNTAX		DisplayString
	ACCESS		read-only
	STATUS		mandatory
	DESCRIPTION	"The date and time when di forwarding cycle log was preserved."
	::= { diFwSendCycleLogEntry 2 }

    diFwSendCycleLogIpAddress	OBJECT-TYPE
	SYNTAX		DisplayString
	ACCESS		read-only
	STATUS		mandatory
	DESCRIPTION	"The peer host when di forwarding cycle log was preserved."
	::= { diFwSendCycleLogEntry 3 }

    diFwSendCycleLogDoValues	OBJECT-TYPE
	SYNTAX		DisplayString
	ACCESS		read-only
	STATUS		mandatory
	DESCRIPTION	"The doValues when di forwarding cycle log was preserved."
	::= { diFwSendCycleLogEntry 4 }

    diFwSendCycleLogStatus	OBJECT-TYPE
	SYNTAX          INTEGER {
			    ok(0),
			    tooBig(1),
			    noSuchName(2),
			    badValue(3),
			    wrongType(7),
			    wrongLength(8),
			    wrongValue(10),
			    timeOut(127),
			    cancel(128),
			    hostDown(129),
			    noRoute(130),
			    refused(131),
			    noName(132),
			    otherError(255)
			}
	ACCESS		read-only
	STATUS		mandatory
	DESCRIPTION	"A unique value for each di forwarding cycle log entry. It's value
			ranges between 1 and the value diFwSendCycleLogNumber."
	::= { diFwSendCycleLogEntry 5 }


-- CEC network-device di Forward Recv Log Group (Ver 5.x or Later support)

    diFwRecvLogNumber	OBJECT-TYPE
	SYNTAX		INTEGER
	ACCESS		read-only
	STATUS		mandatory
	DESCRIPTION	"The number of di forwarding receive log preserved by this device."
	::= { ndMgmt 35 }

    diFwRecvLogTable	OBJECT-TYPE
	SYNTAX		SEQUENCE OF DiFwRecvLogEntry
	ACCESS		not-accessible
	STATUS		mandatory
	DESCRIPTION	"A list of di forwarding receive log entries. The number of entries
			is given by the value diFwRecvLogNumber."
	::= { ndMgmt 36 }

    diFwRecvLogEntry	OBJECT-TYPE
	SYNTAX		DiFwRecvLogEntry
	ACCESS		not-accessible
	STATUS		mandatory
	DESCRIPTION	"A di forwarding receive log entry containing objects to describe the
			di forwarding receive log."
	INDEX		{ diFwRecvLogIndex }
	::= { diFwRecvLogTable 1 }

    DiFwRecvLogEntry ::=
	SEQUENCE {
	    diFwRecvLogIndex
		INTEGER,
	    diFwRecvLogDateTime
	        DisplayString,
	    diFwRecvLogIpAddress
	        DisplayString,
	    diFwRecvLogDoValues
	        DisplayString,
	    diFwRecvLogChannel
		INTEGER,
	    diFwRecvLogStatus
		INTEGER
	}

    diFwRecvLogIndex	OBJECT-TYPE
	SYNTAX		INTEGER
	ACCESS		read-only
	STATUS		mandatory
	DESCRIPTION	"A unique value for each data log entry. It's value
			ranges between 1 and the value diFwRecvLogNumber."
	::= { diFwRecvLogEntry 1 }

    diFwRecvLogDateTime	OBJECT-TYPE
	SYNTAX		DisplayString
	ACCESS		read-only
	STATUS		mandatory
	DESCRIPTION	"The date and time when di forwarding receive log was preserved."
	::= { diFwRecvLogEntry 2 }

    diFwRecvLogIpAddress	OBJECT-TYPE
	SYNTAX		DisplayString
	ACCESS		read-only
	STATUS		mandatory
	DESCRIPTION	"The peer host when di forwarding receive log was preserved."
	::= { diFwRecvLogEntry 3 }

    diFwRecvLogDoValues	OBJECT-TYPE
	SYNTAX		DisplayString
	ACCESS		read-only
	STATUS		mandatory
	DESCRIPTION	"The doValues when di forwarding receive log was preserved."
	::= { diFwRecvLogEntry 4 }

    diFwRecvLogChannel	OBJECT-TYPE
	SYNTAX		INTEGER
	ACCESS		read-only
	STATUS		mandatory
	DESCRIPTION	"A unique value for each di forwarding receive log entry. It's value
			ranges between 1 and the value diFwRecvLogNumber."
	::= { diFwRecvLogEntry 5 }

    diFwRecvLogStatus	OBJECT-TYPE
	SYNTAX          INTEGER {
			    ok(0),
			    timeOut(1),
			    timeOutRecover(2)
			}
	ACCESS		read-only
	STATUS		mandatory
	DESCRIPTION	"A unique value for each di forwarding receive log entry. It's value
			ranges between 1 and the value diFwRecvLogNumber."
	::= { diFwRecvLogEntry 6 }


-- CEC network-device di Forward Recv Log Group (Ver 5.x or Later support)

    fileWriteLogNumber	OBJECT-TYPE
	SYNTAX		INTEGER
	ACCESS		read-only
	STATUS		mandatory
	DESCRIPTION	"The number of file write log preserved by this device."
	::= { ndMgmt 37 }

    fileWriteLogTable	OBJECT-TYPE
	SYNTAX		SEQUENCE OF FileWriteLogEntry
	ACCESS		not-accessible
	STATUS		mandatory
	DESCRIPTION	"A list of file write log entries. The number of entries
			is given by the value fileWriteLogNumber."
	::= { ndMgmt 38 }

    fileWriteLogEntry	OBJECT-TYPE
	SYNTAX		FileWriteLogEntry
	ACCESS		not-accessible
	STATUS		mandatory
	DESCRIPTION	"A file write log entry containing objects to describe the
			file write log."
	INDEX		{ fileWriteLogIndex }
	::= { fileWriteLogTable 1 }

    FileWriteLogEntry ::=
	SEQUENCE {
	    fileWriteLogIndex
		INTEGER,
	    fileWriteLogDateTime
	        DisplayString,
	    fileWriteLogSceneID
	        DisplayString,
	    fileWriteLogTriggerType
		INTEGER,
	    fileWriteLogProtocol
		INTEGER,
	    fileWriteLogConfigEntry
		INTEGER,
	    fileWriteLogErrorCode
		INTEGER,
	    fileWriteLogErrorMessage
	        DisplayString
	}

    fileWriteLogIndex	OBJECT-TYPE
	SYNTAX		INTEGER
	ACCESS		read-only
	STATUS		mandatory
	DESCRIPTION	"A unique value for each data log entry. It's value
			ranges between 1 and the value fileWriteLogNumber."
	::= { fileWriteLogEntry 1 }

    fileWriteLogDateTime	OBJECT-TYPE
	SYNTAX		DisplayString
	ACCESS		read-only
	STATUS		mandatory
	DESCRIPTION	"The date and time when file write log was preserved."
	::= { fileWriteLogEntry 2 }

    fileWriteLogSceneID	OBJECT-TYPE
	SYNTAX		DisplayString
	ACCESS		read-only
	STATUS		mandatory
	DESCRIPTION	"This string is ID of the newest stored scene."
	::= { fileWriteLogEntry 3 }

    fileWriteLogTriggerType	OBJECT-TYPE
	SYNTAX		INTEGER
	ACCESS		read-only
	STATUS		mandatory
	DESCRIPTION	"The trigger type that scene is stored."
	::= { fileWriteLogEntry 4 }

    fileWriteLogProtocol	OBJECT-TYPE
	SYNTAX          INTEGER {
			    cifs(1),
			    ftp(2)
			}
	ACCESS		read-only
	STATUS		mandatory
	DESCRIPTION	"The protocol that scene is stored."
	::= { fileWriteLogEntry 5 }

    fileWriteLogConfigEntry	OBJECT-TYPE
	SYNTAX		INTEGER
	ACCESS		read-only
	STATUS		mandatory
	DESCRIPTION	"The host entry that scene is stored."
	::= { fileWriteLogEntry 6 }

    fileWriteLogErrorCode	OBJECT-TYPE
	SYNTAX          INTEGER {
				timeout(1),
				fileNotFound(2),
				accessError(4),
				closeError(8),
				readError(16),
				renameError(32),
				writeError(64),
				deleteError(128),
				diskFull(256),
				readConnectionError(512),
				writeConnectionError(1024),
				rwConnectionError(1536),
				internalError(32768),
				connectionEstablished(65536),
				connectionClosed(65537),
				connecting(65538),
				connectFailed(65539),
				authenticationError(65540),
				rootDirectoryNotFound(65541),
				connectionError(65542),
				internalError(65543)
			}
	ACCESS		read-only
	STATUS		mandatory
	DESCRIPTION	"The error code that scene is stored."
	::= { fileWriteLogEntry 7 }

    fileWriteLogErrorMessage	OBJECT-TYPE
	SYNTAX		DisplayString
	ACCESS		read-only
	STATUS		mandatory
	DESCRIPTION	"The error message that scene is stored."
	::= { fileWriteLogEntry 8 }


-- CEC network-device Traps

    adExceedUpperThresholdIncrease TRAP-TYPE
	ENTERPRISE	network-device
	VARIABLES	{ adValue, adminDateAndTime, adminNDTrapSeqNo,
			  adIndex, adType, adValueOnlyString,
			  adTrapCurrentStatus }
	DESCRIPTION	"This trap is generated when adValue is greater than
			the upper threshold."
	::= 1

    adExceedUpperThresholdDecrease TRAP-TYPE
	ENTERPRISE	network-device
	VARIABLES	{ adValue, adminDateAndTime, adminNDTrapSeqNo,
			  adIndex, adType, adValueOnlyString,
			  adTrapCurrentStatus }
	DESCRIPTION	"This trap is generated when adValue is less equal
			the upper threshold minus the upper hysteresis
			after adExceedUpperThresholdIncrease is generated.
			namely, adValue <= (adTrapUpperThreshold - 
			adTrapUpperHysteresis)."
	::= 2

    adExceedingUpperThreshold	TRAP-TYPE
	ENTERPRISE	network-device
	VARIABLES	{ adValue, adminDateAndTime, adminNDTrapSeqNo,
			  adIndex, adType, adValueOnlyString,
			  adTrapCurrentStatus }
	DESCRIPTION	"This trap is generated until
			adExceedUpperThresholdDecrease is generated after
			adExceedUpperThresholdIncrease is generated."
	::= 3

    adExceedLowerThresholdIncrease TRAP-TYPE
	ENTERPRISE	network-device
	VARIABLES	{ adValue, adminDateAndTime, adminNDTrapSeqNo,
			  adIndex, adType, adValueOnlyString,
			  adTrapCurrentStatus }
	DESCRIPTION	"This trap is generated when adValue is greater equal
			the lower threshold plus the lower hysteresis
			after adExceedLowerThresholdDecrease is generated.
			namely, adValue >= (adTrapLowerThreshold +
			adTrapLowerHysteresis)."
	::= 4

    adExceedLowerThresholdDecrease TRAP-TYPE
	ENTERPRISE	network-device
	VARIABLES	{ adValue, adminDateAndTime, adminNDTrapSeqNo,
			  adIndex, adType, adValueOnlyString,
			  adTrapCurrentStatus }
	DESCRIPTION	"This trap is generated when adValue is less than
			the lower threshold."
	::= 5

    adExceedingLowerThreshold	TRAP-TYPE
	ENTERPRISE	network-device
	VARIABLES	{ adValue, adminDateAndTime, adminNDTrapSeqNo,
			  adIndex, adType, adValueOnlyString,
			  adTrapCurrentStatus }
	DESCRIPTION	"This trap is generated until
			adExceedLowerThresholdDecrease is generated after
			adExceedLowerThresholdIncrease is generated."
	::= 6

    diChangeValue0	TRAP-TYPE
	ENTERPRISE	network-device
	VARIABLES	{ diValue, adminDateAndTime, adminNDTrapSeqNo,
			  diIndex, diType, diValue0String }
	DESCRIPTION	"This trap is generated when the value of diValue
			change from 1 to 0."
	::= 8

    diValue0		TRAP-TYPE
	ENTERPRISE	network-device
	VARIABLES	{ diValue, adminDateAndTime, adminNDTrapSeqNo,
			  diIndex, diType, diValue0String }
	DESCRIPTION	"This trap is generated while the value of diValue
			is 0."
	::= 9

    diChangeValue1	TRAP-TYPE
	ENTERPRISE	network-device
	VARIABLES	{ diValue, adminDateAndTime, adminNDTrapSeqNo,
			  diIndex, diType, diValue1String }
	DESCRIPTION	"This trap is generated when the value of diValue
			change from 0 to 1."
	::= 10

    diValue1		TRAP-TYPE
	ENTERPRISE	network-device
	VARIABLES	{ diValue, adminDateAndTime, adminNDTrapSeqNo,
			  diIndex, diType, diValue1String }
	DESCRIPTION	"This trap is generated while the value of diValue
			is 1."
	::= 11

    diPulseCountTrap	TRAP-TYPE
	ENTERPRISE	network-device
	VARIABLES	{ diPulseCount, adminDateAndTime, adminNDTrapSeqNo,
			  diIndex, diType }
	DESCRIPTION	"This trap is generated when diPulseCount exceeds
			diPulseCountLimit."
	::= 12

    vcExceedUpperThresholdIncrease TRAP-TYPE
	ENTERPRISE	network-device
	VARIABLES	{ vcValue, adminDateAndTime, adminNDTrapSeqNo,
			  vcIndex, vcType }
	DESCRIPTION	"This trap is generated when vcValue is greater than
			the upper threshold."
	::= 13

    vcExceedUpperThresholdDecrease TRAP-TYPE
	ENTERPRISE	network-device
	VARIABLES	{ vcValue, adminDateAndTime, adminNDTrapSeqNo,
			  vcIndex, vcType }
	DESCRIPTION	"This trap is generated when vcValue is less equal
			the upper threshold minus the upper hysteresis
			after vcExceedUpperThresholdIncrease is generated.
			namely, vcValue <= (vcTrapUpperThreshold - 
			vcTrapUpperHysteresis)."
	::= 14

    vcExceedingUpperThreshold	TRAP-TYPE
	ENTERPRISE	network-device
	VARIABLES	{ vcValue, adminDateAndTime, adminNDTrapSeqNo,
			  vcIndex, vcType }
	DESCRIPTION	"This trap is generated until
			vcExceedUpperThresholdDecrease is generated after
			vcExceedUpperThresholdIncrease is generated."
	::= 15

    vcExceedLowerThresholdIncrease TRAP-TYPE
	ENTERPRISE	network-device
	VARIABLES	{ vcValue, adminDateAndTime, adminNDTrapSeqNo,
			  vcIndex, vcType }
	DESCRIPTION	"This trap is generated when vcValue is greater equal
			the lower threshold plus the lower hysteresis
			after vcExceedLowerThresholdDecrease is generated.
			namely, vcValue >= (vcTrapLowerThreshold +
			vcTrapLowerHysteresis)."
	::= 16

    vcExceedLowerThresholdDecrease TRAP-TYPE
	ENTERPRISE	network-device
	VARIABLES	{ vcValue, adminDateAndTime, adminNDTrapSeqNo,
			  vcIndex, vcType }
	DESCRIPTION	"This trap is generated when vcValue is less than
			the lower threshold."
	::= 17

    vcExceedingLowerThreshold	TRAP-TYPE
	ENTERPRISE	network-device
	VARIABLES	{ vcValue, adminDateAndTime, adminNDTrapSeqNo,
			  vcIndex, vcType }
	DESCRIPTION	"This trap is generated until
			vcExceedLowerThresholdDecrease is generated after
			vcExceedLowerThresholdIncrease is generated."
	::= 18

    doChangeValue0	TRAP-TYPE
	ENTERPRISE	network-device
	VARIABLES	{ doValue, adminDateAndTime, adminNDTrapSeqNo,
			  doIndex, doType, doValue0String }
	DESCRIPTION	"This trap is generated when the value of doValue
			change from 1 to 0."
	::= 24

    doValue0		TRAP-TYPE
	ENTERPRISE	network-device
	VARIABLES	{ doValue, adminDateAndTime, adminNDTrapSeqNo,
			  doIndex, doType, doValue0String }
	DESCRIPTION	"This trap is generated while the value of doValue
			is 0."
	::= 25

    doChangeValue1	TRAP-TYPE
	ENTERPRISE	network-device
	VARIABLES	{ doValue, adminDateAndTime, adminNDTrapSeqNo,
			  doIndex, doType, doValue1String }
	DESCRIPTION	"This trap is generated when the value of doValue
			change from 0 to 1."
	::= 26

    doValue1		TRAP-TYPE
	ENTERPRISE	network-device
	VARIABLES	{ doValue, adminDateAndTime, adminNDTrapSeqNo,
			  doIndex, doType, doValue1String }
	DESCRIPTION	"This trap is generated while the value of doValue
			is 1."
	::= 27

    timerTriggerTrap	TRAP-TYPE
	ENTERPRISE	network-device
	VARIABLES	{ timerTriggerSceneID,
			  adminDateAndTime, adminNDTrapSeqNo, cameraIndex,
			  timerTriggerPeriodIndex }
	DESCRIPTION	"This trap is generated when the scene begins to be
			stored by the timer trigger."
	::= 32

    diTriggerTrap	TRAP-TYPE
	ENTERPRISE	network-device
	VARIABLES	{ diTriggerSceneID,
			  adminDateAndTime, adminNDTrapSeqNo, cameraIndex }
	DESCRIPTION	"This trap is generated when the scene begins to be
			stored by the DI trigger."
	::= 33

    motionDetectTriggerTrap	TRAP-TYPE
	ENTERPRISE	network-device
	VARIABLES	{ multiMotionDetectTriggerSceneID,
			  adminDateAndTime, adminNDTrapSeqNo, cameraIndex }
	DESCRIPTION	"This trap is generated when the scene begins to be
			stored by the motion detect trigger."
	::= 34

    manualTriggerTrap	TRAP-TYPE
	ENTERPRISE	network-device
	VARIABLES	{ multiManualTriggerSceneID,
			  adminDateAndTime, adminNDTrapSeqNo, cameraIndex }
	DESCRIPTION	"This trap is generated when the scene begins to be
			stored by the manual trigger."
	::= 35

    motionStopTriggerTrap	TRAP-TYPE
	ENTERPRISE	network-device
	VARIABLES	{ multiMotionDetectTriggerSceneID,
			  adminDateAndTime, adminNDTrapSeqNo, cameraIndex }
	DESCRIPTION	"This trap is generated when the scene begins to be
			stored by the motion stop trigger."
	::= 36

    imageMemoryFull		TRAP-TYPE
	ENTERPRISE	network-device
	VARIABLES	{ imageMemoryFullTrapCount,
			  adminDateAndTime, adminNDTrapSeqNo }
	DESCRIPTION	"This trap is generated when the store memory will be full."
	::= 40

    timerTriggerCompleteTrap	TRAP-TYPE
	ENTERPRISE	network-device
	VARIABLES	{ timerTriggerSceneID,
			  adminDateAndTime, adminNDTrapSeqNo, cameraIndex,
			  timerTriggerSceneBefore, timerTriggerSceneAfter }
	DESCRIPTION	"This trap is generated when the scene completes to be
			stored by the timer trigger."
	::= 50

    diTriggerCompleteTrap	TRAP-TYPE
	ENTERPRISE	network-device
	VARIABLES	{ diTriggerSceneID,
			  adminDateAndTime, adminNDTrapSeqNo, cameraIndex,
			  diTriggerSceneBefore, diTriggerSceneAfter }
	DESCRIPTION	"This trap is generated when the scene completes to be
			stored by the DI trigger."
	::= 51

    motionDetectTriggerCompleteTrap	TRAP-TYPE
	ENTERPRISE	network-device
	VARIABLES	{ multiMotionDetectTriggerSceneID,
			  adminDateAndTime, adminNDTrapSeqNo, cameraIndex,
			  multiMotionDetectTriggerSceneBefore,
			  multiMotionDetectTriggerSceneAfter }
	DESCRIPTION	"This trap is generated when the scene completes to be
			stored by the motion detect trigger."
	::= 52

    manualTriggerCompleteTrap	TRAP-TYPE
	ENTERPRISE	network-device
	VARIABLES	{ multiManualTriggerSceneID,
			  adminDateAndTime, adminNDTrapSeqNo, cameraIndex,
			  multiManualTriggerSceneBefore,
			  multiManualTriggerSceneAfter }
	DESCRIPTION	"This trap is generated when the scene completes to be
			stored by the manual trigger."
	::= 53

    motionStopTriggerCompleteTrap	TRAP-TYPE
	ENTERPRISE	network-device
	VARIABLES	{ multiMotionDetectTriggerSceneID,
			  adminDateAndTime, adminNDTrapSeqNo, cameraIndex,
			  multiMotionDetectTriggerSceneBefore,
			  multiMotionDetectTriggerSceneAfter }
	DESCRIPTION	"This trap is generated when the scene completes to be
			stored by the motion stop trigger."
	::= 54

    ndUserDefinedTrap TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 0' command."
	::= 63

    fanFailure		TRAP-TYPE
	ENTERPRISE	network-device
	VARIABLES	{ adminDateAndTime, adminNDTrapSeqNo }
	DESCRIPTION	"This trap is generated when the FAN failure has
			occurred."
	::= 64

    flashMemoryFailure	TRAP-TYPE
	ENTERPRISE	network-device
	VARIABLES	{ adminDateAndTime, adminNDTrapSeqNo }
	DESCRIPTION	"This trap is generated when the flashmemory failure has
			occurred."
	::= 65

    nvramFailure	TRAP-TYPE
	ENTERPRISE	network-device
	VARIABLES	{ adminDateAndTime, adminNDTrapSeqNo }
	DESCRIPTION	"This trap is generated when the nvram failure has
			occurred."
	::= 66

    diskReadFailure	TRAP-TYPE
	ENTERPRISE	network-device
	VARIABLES	{ diskReadErrorCount,
			  adminDateAndTime, adminNDTrapSeqNo }
	DESCRIPTION	"This trap is generated when the disk read failure
			has occurred."
	::= 67

    diskWriteFailure	TRAP-TYPE
	ENTERPRISE	network-device
	VARIABLES	{ diskWriteErrorCount,
			  adminDateAndTime, adminNDTrapSeqNo }
	DESCRIPTION	"This trap is generated when the disk write failure
			has occurred."
	::= 68

    diskFull		TRAP-TYPE
	ENTERPRISE	network-device
	VARIABLES	{ diskUsed,
			  adminDateAndTime, adminNDTrapSeqNo }
	DESCRIPTION	"This trap is generated when the disk will be full."
	::= 69

    diskRecoverableError	TRAP-TYPE
	ENTERPRISE	network-device
	VARIABLES	{ diskSwapSectorCount,
			  adminDateAndTime, adminNDTrapSeqNo }
	DESCRIPTION	"This trap is generated when the disk swap sector use."
	::= 70

    diskCriticalError	TRAP-TYPE
	ENTERPRISE	network-device
	VARIABLES	{ diskCriticalErrorKind,
			  adminDateAndTime, adminNDTrapSeqNo }
	DESCRIPTION	"This trap is generated when the disk CriticalError
			has occurred."
	::= 71

    diskFatalError	TRAP-TYPE
	ENTERPRISE	network-device
	VARIABLES	{ diskFatalErrorKind,
			  adminDateAndTime, adminNDTrapSeqNo }
	DESCRIPTION	"This trap is generated when the disk FatalError
			has occurred."
	::= 72

    diskSpaceLeast	TRAP-TYPE
	ENTERPRISE	network-device
	VARIABLES	{ diskUsed,
			  adminDateAndTime, adminNDTrapSeqNo }
	DESCRIPTION	"This trap is generated when the disk SpaceLeast
			has occurred."
	::= 73

    diForwardError	TRAP-TYPE
	ENTERPRISE	network-device
	VARIABLES	{ diForwardErrorStatus,
			  adminDateAndTime, adminNDTrapSeqNo,
			  diForwardErrorHost, doValues }
	DESCRIPTION	"This trap is generated when the DI forward error
			has occurred."
	::= 101

    diForwardNormal	TRAP-TYPE
	ENTERPRISE	network-device
	VARIABLES	{ diForwardErrorStatus,
			  adminDateAndTime, adminNDTrapSeqNo,
			  diForwardErrorHost, doValues }
	DESCRIPTION	"This trap is generated when the DI forward normal
			has occurred."
	::= 102

    diForwardCancel	TRAP-TYPE
	ENTERPRISE	network-device
	VARIABLES	{ diForwardErrorStatus,
			  adminDateAndTime, adminNDTrapSeqNo,
			  diForwardErrorHost, doValues }
	DESCRIPTION	"This trap is generated when the DI forward cancel
			has occurred."
	::= 103

    diForwardReceiveTimeout	TRAP-TYPE
	ENTERPRISE	network-device
	VARIABLES	{ doIndex,
			  adminDateAndTime, adminNDTrapSeqNo,
			  diForwardReceiveHost }
	DESCRIPTION	"This trap is generated when the DI forward receive
			timeout has occurred."
	::= 104

    diForwardReceiveTimeoutRecover	TRAP-TYPE
	ENTERPRISE	network-device
	VARIABLES	{ doIndex,
			  adminDateAndTime, adminNDTrapSeqNo,
			  diForwardReceiveHost }
	DESCRIPTION	"This trap is generated when the DI forward receive
			timeout recover has occurred."
	::= 105

    subUnitNotConnected	TRAP-TYPE
	ENTERPRISE	network-device
	VARIABLES	{ subUnitStatus,
			  adminDateAndTime, adminNDTrapSeqNo,
			  subUnitIndex }
	DESCRIPTION	"This trap is generated when the subunit
			is disconnected."
	::= 108

    subUnitConnected	TRAP-TYPE
	ENTERPRISE	network-device
	VARIABLES	{ subUnitStatus,
			  adminDateAndTime, adminNDTrapSeqNo,
			  subUnitIndex }
	DESCRIPTION	"This trap is generated when the subunit
			is connected."
	::= 109

    multiMeterNotConnected	TRAP-TYPE
	ENTERPRISE	network-device
	VARIABLES	{ multiMeterStatus,
			  adminDateAndTime, adminNDTrapSeqNo,
			  multiMeterIndex }
	DESCRIPTION	"This trap is generated when the multimeter
			is disconnected."
	::= 110

    multiMeterConnected	TRAP-TYPE
	ENTERPRISE	network-device
	VARIABLES	{ multiMeterStatus,
			  adminDateAndTime, adminNDTrapSeqNo,
			  multiMeterIndex }
	DESCRIPTION	"This trap is generated when the multimeter
			is connected."
	::= 111

    cifsConnectionError	TRAP-TYPE
	ENTERPRISE	network-device
	VARIABLES	{ cifsSceneID,
			  adminDateAndTime, adminNDTrapSeqNo,
			  cifsErrorCode,
			  cifsErrorMessage,
			  cifsIndex }
	DESCRIPTION	"This trap is generated when CIFS connection error
			has occurred."
	::= 128

    cifsAuthenticationError	TRAP-TYPE
	ENTERPRISE	network-device
	VARIABLES	{ cifsSceneID,
			  adminDateAndTime, adminNDTrapSeqNo,
			  cifsErrorCode,
			  cifsErrorMessage,
			  cifsIndex }
	DESCRIPTION	"This trap is generated when CIFS authentication error
			has occurred."
	::= 129

    cifsReadError	TRAP-TYPE
	ENTERPRISE	network-device
	VARIABLES	{ cifsSceneID,
			  adminDateAndTime, adminNDTrapSeqNo,
			  cifsErrorCode,
			  cifsErrorMessage,
			  cifsIndex }
	DESCRIPTION	"This trap is generated when CIFS read error
			has occurred."
	::= 130

    cifsWriteError	TRAP-TYPE
	ENTERPRISE	network-device
	VARIABLES	{ cifsSceneID,
			  adminDateAndTime, adminNDTrapSeqNo,
			  cifsErrorCode,
			  cifsErrorMessage,
			  cifsIndex }
	DESCRIPTION	"This trap is generated when CIFS write error
			has occurred."
	::= 131

    cifsDiskFull	TRAP-TYPE
	ENTERPRISE	network-device
	VARIABLES	{ cifsSceneID,
			  adminDateAndTime, adminNDTrapSeqNo,
			  cifsErrorCode,
			  cifsErrorMessage,
			  cifsIndex }
	DESCRIPTION	"This trap is generated when CIFS disk full
			has occurred."
	::= 132

    cifsOtherError	TRAP-TYPE
	ENTERPRISE	network-device
	VARIABLES	{ cifsSceneID,
			  adminDateAndTime, adminNDTrapSeqNo,
			  cifsErrorCode,
			  cifsErrorMessage,
			  cifsIndex }
	DESCRIPTION	"This trap is generated when CIFS other error
			has occurred."
	::= 133

    ftpcConnectionError	TRAP-TYPE
	ENTERPRISE	network-device
	VARIABLES	{ ftpcSceneID,
			  adminDateAndTime, adminNDTrapSeqNo,
			  ftpcErrorCode,
			  ftpcErrorMessage,
			  ftpcIndex }
	DESCRIPTION	"This trap is generated when FTP connection error
			has occurred."
	::= 138

    ftpcAuthenticationError	TRAP-TYPE
	ENTERPRISE	network-device
	VARIABLES	{ ftpcSceneID,
			  adminDateAndTime, adminNDTrapSeqNo,
			  ftpcErrorCode,
			  ftpcErrorMessage,
			  ftpcIndex }
	DESCRIPTION	"This trap is generated when FTP authentication error
			has occurred."
	::= 139

    ftpcReadError	TRAP-TYPE
	ENTERPRISE	network-device
	VARIABLES	{ ftpcSceneID,
			  adminDateAndTime, adminNDTrapSeqNo,
			  ftpcErrorCode,
			  ftpcErrorMessage,
			  ftpcIndex }
	DESCRIPTION	"This trap is generated when FTP read error
			has occurred."
	::= 140

    ftpcWriteError	TRAP-TYPE
	ENTERPRISE	network-device
	VARIABLES	{ ftpcSceneID,
			  adminDateAndTime, adminNDTrapSeqNo,
			  ftpcErrorCode,
			  ftpcErrorMessage,
			  ftpcIndex }
	DESCRIPTION	"This trap is generated when FTP write error
			has occurred."
	::= 141

    ftpcOtherError	TRAP-TYPE
	ENTERPRISE	network-device
	VARIABLES	{ ftpcSceneID,
			  adminDateAndTime, adminNDTrapSeqNo,
			  ftpcErrorCode,
			  ftpcErrorMessage,
			  ftpcIndex }
	DESCRIPTION	"This trap is generated when FTP other error
			has occurred."
	::= 142

-- Following variable are support Ver 3.0 or Later

    adExceedUpperThresholdIncrease1 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 1 and 
			adValue is greater than the upper threshold."
	::= 2049

    adExceedUpperThresholdIncrease2 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 2 and 
			adValue is greater than the upper threshold."
	::= 2050

    adExceedUpperThresholdIncrease3 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 3 and 
			adValue is greater than the upper threshold."
	::= 2051

    adExceedUpperThresholdIncrease4 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 4 and 
			adValue is greater than the upper threshold."
	::= 2052

    adExceedUpperThresholdIncrease5 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 5 and 
			adValue is greater than the upper threshold."
	::= 2053

    adExceedUpperThresholdIncrease6 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 6 and 
			adValue is greater than the upper threshold."
	::= 2054

    adExceedUpperThresholdIncrease7 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 7 and 
			adValue is greater than the upper threshold."
	::= 2055

    adExceedUpperThresholdIncrease8 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 8 and 
			adValue is greater than the upper threshold."
	::= 2056

    adExceedUpperThresholdIncrease9 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 9 and 
			adValue is greater than the upper threshold."
	::= 2057

    adExceedUpperThresholdIncrease10 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 10 and 
			adValue is greater than the upper threshold."
	::= 2058

    adExceedUpperThresholdIncrease11 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 11 and 
			adValue is greater than the upper threshold."
	::= 2059

    adExceedUpperThresholdIncrease12 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 12 and 
			adValue is greater than the upper threshold."
	::= 2060

    adExceedUpperThresholdIncrease13 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 13 and 
			adValue is greater than the upper threshold."
	::= 2061

    adExceedUpperThresholdIncrease14 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 14 and 
			adValue is greater than the upper threshold."
	::= 2062

    adExceedUpperThresholdIncrease15 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 15 and 
			adValue is greater than the upper threshold."
	::= 2063

    adExceedUpperThresholdIncrease16 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 16 and 
			adValue is greater than the upper threshold."
	::= 2064

    adExceedUpperThresholdIncrease17 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 17 and 
			adValue is greater than the upper threshold."
	::= 2065

    adExceedUpperThresholdIncrease18 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 18 and 
			adValue is greater than the upper threshold."
	::= 2066

    adExceedUpperThresholdIncrease19 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 19 and 
			adValue is greater than the upper threshold."
	::= 2067

    adExceedUpperThresholdIncrease20 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 20 and 
			adValue is greater than the upper threshold."
	::= 2068

    adExceedUpperThresholdIncrease21 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 21 and 
			adValue is greater than the upper threshold."
	::= 2069

    adExceedUpperThresholdIncrease22 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 22 and 
			adValue is greater than the upper threshold."
	::= 2070

    adExceedUpperThresholdIncrease23 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 23 and 
			adValue is greater than the upper threshold."
	::= 2071

    adExceedUpperThresholdIncrease24 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 24 and 
			adValue is greater than the upper threshold."
	::= 2072

    adExceedUpperThresholdIncrease25 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 25 and 
			adValue is greater than the upper threshold."
	::= 2073

    adExceedUpperThresholdIncrease26 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 26 and 
			adValue is greater than the upper threshold."
	::= 2074

    adExceedUpperThresholdIncrease27 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 27 and 
			adValue is greater than the upper threshold."
	::= 2075

    adExceedUpperThresholdIncrease28 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 28 and 
			adValue is greater than the upper threshold."
	::= 2076

    adExceedUpperThresholdIncrease29 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 29 and 
			adValue is greater than the upper threshold."
	::= 2077

    adExceedUpperThresholdIncrease30 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 30 and 
			adValue is greater than the upper threshold."
	::= 2078

    adExceedUpperThresholdIncrease31 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 31 and 
			adValue is greater than the upper threshold."
	::= 2079

    adExceedUpperThresholdIncrease32 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 32 and 
			adValue is greater than the upper threshold."
	::= 2080

    adExceedUpperThresholdIncrease33 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 33 and 
			adValue is greater than the upper threshold."
	::= 2081

    adExceedUpperThresholdIncrease34 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 34 and 
			adValue is greater than the upper threshold."
	::= 2082

    adExceedUpperThresholdIncrease35 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 35 and 
			adValue is greater than the upper threshold."
	::= 2083

    adExceedUpperThresholdIncrease36 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 36 and 
			adValue is greater than the upper threshold."
	::= 2084

    adExceedUpperThresholdIncrease37 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 37 and 
			adValue is greater than the upper threshold."
	::= 2085

    adExceedUpperThresholdIncrease38 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 38 and 
			adValue is greater than the upper threshold."
	::= 2086

    adExceedUpperThresholdIncrease39 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 39 and 
			adValue is greater than the upper threshold."
	::= 2087

    adExceedUpperThresholdIncrease40 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 40 and 
			adValue is greater than the upper threshold."
	::= 2088

    adExceedUpperThresholdIncrease41 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 41 and 
			adValue is greater than the upper threshold."
	::= 2089

    adExceedUpperThresholdIncrease42 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 42 and 
			adValue is greater than the upper threshold."
	::= 2090

    adExceedUpperThresholdIncrease43 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 43 and 
			adValue is greater than the upper threshold."
	::= 2091

    adExceedUpperThresholdIncrease44 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 44 and 
			adValue is greater than the upper threshold."
	::= 2092

    adExceedUpperThresholdIncrease45 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 45 and 
			adValue is greater than the upper threshold."
	::= 2093

    adExceedUpperThresholdIncrease46 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 46 and 
			adValue is greater than the upper threshold."
	::= 2094

    adExceedUpperThresholdIncrease47 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 47 and 
			adValue is greater than the upper threshold."
	::= 2095

    adExceedUpperThresholdIncrease48 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 48 and 
			adValue is greater than the upper threshold."
	::= 2096

    adExceedUpperThresholdIncrease49 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 49 and 
			adValue is greater than the upper threshold."
	::= 2097

    adExceedUpperThresholdIncrease50 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 50 and 
			adValue is greater than the upper threshold."
	::= 2098

    adExceedUpperThresholdIncrease51 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 51 and 
			adValue is greater than the upper threshold."
	::= 2099

    adExceedUpperThresholdIncrease52 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 52 and 
			adValue is greater than the upper threshold."
	::= 2100

    adExceedUpperThresholdIncrease53 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 53 and 
			adValue is greater than the upper threshold."
	::= 2101

    adExceedUpperThresholdIncrease54 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 54 and 
			adValue is greater than the upper threshold."
	::= 2102

    adExceedUpperThresholdIncrease55 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 55 and 
			adValue is greater than the upper threshold."
	::= 2103

    adExceedUpperThresholdIncrease56 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 56 and 
			adValue is greater than the upper threshold."
	::= 2104

    adExceedUpperThresholdIncrease57 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 57 and 
			adValue is greater than the upper threshold."
	::= 2105

    adExceedUpperThresholdIncrease58 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 58 and 
			adValue is greater than the upper threshold."
	::= 2106

    adExceedUpperThresholdIncrease59 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 59 and 
			adValue is greater than the upper threshold."
	::= 2107

    adExceedUpperThresholdIncrease60 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 60 and 
			adValue is greater than the upper threshold."
	::= 2108

    adExceedUpperThresholdIncrease61 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 61 and 
			adValue is greater than the upper threshold."
	::= 2109

    adExceedUpperThresholdIncrease62 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 62 and 
			adValue is greater than the upper threshold."
	::= 2110

    adExceedUpperThresholdIncrease63 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 63 and 
			adValue is greater than the upper threshold."
	::= 2111

    adExceedUpperThresholdIncrease64 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 64 and 
			adValue is greater than the upper threshold."
	::= 2112

    adExceedUpperThresholdIncrease65 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 65 and 
			adValue is greater than the upper threshold."
	::= 2113

    adExceedUpperThresholdIncrease66 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 66 and 
			adValue is greater than the upper threshold."
	::= 2114

    adExceedUpperThresholdIncrease67 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 67 and 
			adValue is greater than the upper threshold."
	::= 2115

    adExceedUpperThresholdIncrease68 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 68 and 
			adValue is greater than the upper threshold."
	::= 2116

    adExceedUpperThresholdIncrease69 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 69 and 
			adValue is greater than the upper threshold."
	::= 2117

    adExceedUpperThresholdIncrease70 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 70 and 
			adValue is greater than the upper threshold."
	::= 2118

    adExceedUpperThresholdIncrease71 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 71 and 
			adValue is greater than the upper threshold."
	::= 2119

    adExceedUpperThresholdIncrease72 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 72 and 
			adValue is greater than the upper threshold."
	::= 2120

    adExceedUpperThresholdIncrease73 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 73 and 
			adValue is greater than the upper threshold."
	::= 2121

    adExceedUpperThresholdIncrease74 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 74 and 
			adValue is greater than the upper threshold."
	::= 2122

    adExceedUpperThresholdIncrease75 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 75 and 
			adValue is greater than the upper threshold."
	::= 2123

    adExceedUpperThresholdIncrease76 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 76 and 
			adValue is greater than the upper threshold."
	::= 2124

    adExceedUpperThresholdIncrease77 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 77 and 
			adValue is greater than the upper threshold."
	::= 2125

    adExceedUpperThresholdIncrease78 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 78 and 
			adValue is greater than the upper threshold."
	::= 2126

    adExceedUpperThresholdIncrease79 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 79 and 
			adValue is greater than the upper threshold."
	::= 2127

    adExceedUpperThresholdIncrease80 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 80 and 
			adValue is greater than the upper threshold."
	::= 2128

    adExceedUpperThresholdIncrease81 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 81 and 
			adValue is greater than the upper threshold."
	::= 2129

    adExceedUpperThresholdIncrease82 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 82 and 
			adValue is greater than the upper threshold."
	::= 2130

    adExceedUpperThresholdIncrease83 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 83 and 
			adValue is greater than the upper threshold."
	::= 2131

    adExceedUpperThresholdIncrease84 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 84 and 
			adValue is greater than the upper threshold."
	::= 2132

    adExceedUpperThresholdIncrease85 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 85 and 
			adValue is greater than the upper threshold."
	::= 2133

    adExceedUpperThresholdIncrease86 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 86 and 
			adValue is greater than the upper threshold."
	::= 2134

    adExceedUpperThresholdIncrease87 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 87 and 
			adValue is greater than the upper threshold."
	::= 2135

    adExceedUpperThresholdIncrease88 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 88 and 
			adValue is greater than the upper threshold."
	::= 2136

    adExceedUpperThresholdIncrease89 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 89 and 
			adValue is greater than the upper threshold."
	::= 2137

    adExceedUpperThresholdIncrease90 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 90 and 
			adValue is greater than the upper threshold."
	::= 2138

    adExceedUpperThresholdIncrease91 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 91 and 
			adValue is greater than the upper threshold."
	::= 2139

    adExceedUpperThresholdIncrease92 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 92 and 
			adValue is greater than the upper threshold."
	::= 2140

    adExceedUpperThresholdIncrease93 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 93 and 
			adValue is greater than the upper threshold."
	::= 2141

    adExceedUpperThresholdIncrease94 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 94 and 
			adValue is greater than the upper threshold."
	::= 2142

    adExceedUpperThresholdIncrease95 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 95 and 
			adValue is greater than the upper threshold."
	::= 2143

    adExceedUpperThresholdIncrease96 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 96 and 
			adValue is greater than the upper threshold."
	::= 2144

    adExceedUpperThresholdIncrease97 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 97 and 
			adValue is greater than the upper threshold."
	::= 2145

    adExceedUpperThresholdIncrease98 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 98 and 
			adValue is greater than the upper threshold."
	::= 2146

    adExceedUpperThresholdIncrease99 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 99 and 
			adValue is greater than the upper threshold."
	::= 2147

    adExceedUpperThresholdIncrease100 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 100 and 
			adValue is greater than the upper threshold."
	::= 2148

    adExceedUpperThresholdIncrease101 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 101 and 
			adValue is greater than the upper threshold."
	::= 2149

    adExceedUpperThresholdIncrease102 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 102 and 
			adValue is greater than the upper threshold."
	::= 2150

    adExceedUpperThresholdIncrease103 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 103 and 
			adValue is greater than the upper threshold."
	::= 2151

    adExceedUpperThresholdIncrease104 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 104 and 
			adValue is greater than the upper threshold."
	::= 2152

    adExceedUpperThresholdIncrease105 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 105 and 
			adValue is greater than the upper threshold."
	::= 2153

    adExceedUpperThresholdIncrease106 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 106 and 
			adValue is greater than the upper threshold."
	::= 2154

    adExceedUpperThresholdIncrease107 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 107 and 
			adValue is greater than the upper threshold."
	::= 2155

    adExceedUpperThresholdIncrease108 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 108 and 
			adValue is greater than the upper threshold."
	::= 2156

    adExceedUpperThresholdIncrease109 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 109 and 
			adValue is greater than the upper threshold."
	::= 2157

    adExceedUpperThresholdIncrease110 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 110 and 
			adValue is greater than the upper threshold."
	::= 2158

    adExceedUpperThresholdIncrease111 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 111 and 
			adValue is greater than the upper threshold."
	::= 2159

    adExceedUpperThresholdIncrease112 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 112 and 
			adValue is greater than the upper threshold."
	::= 2160

    adExceedUpperThresholdIncrease113 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 113 and 
			adValue is greater than the upper threshold."
	::= 2161

    adExceedUpperThresholdIncrease114 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 114 and 
			adValue is greater than the upper threshold."
	::= 2162

    adExceedUpperThresholdIncrease115 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 115 and 
			adValue is greater than the upper threshold."
	::= 2163

    adExceedUpperThresholdIncrease116 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 116 and 
			adValue is greater than the upper threshold."
	::= 2164

    adExceedUpperThresholdIncrease117 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 117 and 
			adValue is greater than the upper threshold."
	::= 2165

    adExceedUpperThresholdIncrease118 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 118 and 
			adValue is greater than the upper threshold."
	::= 2166

    adExceedUpperThresholdIncrease119 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 119 and 
			adValue is greater than the upper threshold."
	::= 2167

    adExceedUpperThresholdIncrease120 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 120 and 
			adValue is greater than the upper threshold."
	::= 2168

    adExceedUpperThresholdIncrease121 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 121 and 
			adValue is greater than the upper threshold."
	::= 2169

    adExceedUpperThresholdIncrease122 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 122 and 
			adValue is greater than the upper threshold."
	::= 2170

    adExceedUpperThresholdIncrease123 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 123 and 
			adValue is greater than the upper threshold."
	::= 2171

    adExceedUpperThresholdIncrease124 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 124 and 
			adValue is greater than the upper threshold."
	::= 2172

    adExceedUpperThresholdIncrease125 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 125 and 
			adValue is greater than the upper threshold."
	::= 2173

    adExceedUpperThresholdIncrease126 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 126 and 
			adValue is greater than the upper threshold."
	::= 2174

    adExceedUpperThresholdIncrease127 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdIncreaseTrapID equal 127 and 
			adValue is greater than the upper threshold."
	::= 2175

    adExceedUpperThresholdDecrease1 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 1 and 
			adValue is less equal the upper threshold minus 
			the upper hysteresis after 
			adExceedUpperThresholdIncrease is generated.
			namely, adValue <= (adTrapUpperThreshold - 
			adTrapUpperHysteresis)."
	::= 2561

    adExceedUpperThresholdDecrease2 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 2 and 
			adValue is less equal the upper threshold minus 
			the upper hysteresis after 
			adExceedUpperThresholdIncrease is generated.
			namely, adValue <= (adTrapUpperThreshold - 
			adTrapUpperHysteresis)."
	::= 2562

    adExceedUpperThresholdDecrease3 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 3 and 
			adValue is less equal the upper threshold minus 
			the upper hysteresis after 
			adExceedUpperThresholdIncrease is generated.
			namely, adValue <= (adTrapUpperThreshold - 
			adTrapUpperHysteresis)."
	::= 2563

    adExceedUpperThresholdDecrease4 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 4 and 
			adValue is less equal the upper threshold minus 
			the upper hysteresis after 
			adExceedUpperThresholdIncrease is generated.
			namely, adValue <= (adTrapUpperThreshold - 
			adTrapUpperHysteresis)."
	::= 2564

    adExceedUpperThresholdDecrease5 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 5 and 
			adValue is less equal the upper threshold minus 
			the upper hysteresis after 
			adExceedUpperThresholdIncrease is generated.
			namely, adValue <= (adTrapUpperThreshold - 
			adTrapUpperHysteresis)."
	::= 2565

    adExceedUpperThresholdDecrease6 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 6 and 
			adValue is less equal the upper threshold minus 
			the upper hysteresis after 
			adExceedUpperThresholdIncrease is generated.
			namely, adValue <= (adTrapUpperThreshold - 
			adTrapUpperHysteresis)."
	::= 2566

    adExceedUpperThresholdDecrease7 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 7 and 
			adValue is less equal the upper threshold minus 
			the upper hysteresis after 
			adExceedUpperThresholdIncrease is generated.
			namely, adValue <= (adTrapUpperThreshold - 
			adTrapUpperHysteresis)."
	::= 2567

    adExceedUpperThresholdDecrease8 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 8 and 
			adValue is less equal the upper threshold minus 
			the upper hysteresis after 
			adExceedUpperThresholdIncrease is generated.
			namely, adValue <= (adTrapUpperThreshold - 
			adTrapUpperHysteresis)."
	::= 2568

    adExceedUpperThresholdDecrease9 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 9 and 
			adValue is less equal the upper threshold minus 
			the upper hysteresis after 
			adExceedUpperThresholdIncrease is generated.
			namely, adValue <= (adTrapUpperThreshold - 
			adTrapUpperHysteresis)."
	::= 2569

    adExceedUpperThresholdDecrease10 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 10 and 
			adValue is less equal the upper threshold minus 
			the upper hysteresis after 
			adExceedUpperThresholdIncrease is generated.
			namely, adValue <= (adTrapUpperThreshold - 
			adTrapUpperHysteresis)."
	::= 2570

    adExceedUpperThresholdDecrease11 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 11 and 
			adValue is less equal the upper threshold minus 
			the upper hysteresis after 
			adExceedUpperThresholdIncrease is generated.
			namely, adValue <= (adTrapUpperThreshold - 
			adTrapUpperHysteresis)."
	::= 2571

    adExceedUpperThresholdDecrease12 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 12 and 
			adValue is less equal the upper threshold minus 
			the upper hysteresis after 
			adExceedUpperThresholdIncrease is generated.
			namely, adValue <= (adTrapUpperThreshold - 
			adTrapUpperHysteresis)."
	::= 2572

    adExceedUpperThresholdDecrease13 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 13 and 
			adValue is less equal the upper threshold minus 
			the upper hysteresis after 
			adExceedUpperThresholdIncrease is generated.
			namely, adValue <= (adTrapUpperThreshold - 
			adTrapUpperHysteresis)."
	::= 2573

    adExceedUpperThresholdDecrease14 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 14 and 
			adValue is less equal the upper threshold minus 
			the upper hysteresis after 
			adExceedUpperThresholdIncrease is generated.
			namely, adValue <= (adTrapUpperThreshold - 
			adTrapUpperHysteresis)."
	::= 2574

    adExceedUpperThresholdDecrease15 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 15 and 
			adValue is less equal the upper threshold minus 
			the upper hysteresis after 
			adExceedUpperThresholdIncrease is generated.
			namely, adValue <= (adTrapUpperThreshold - 
			adTrapUpperHysteresis)."
	::= 2575

    adExceedUpperThresholdDecrease16 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 16 and 
			adValue is less equal the upper threshold minus 
			the upper hysteresis after 
			adExceedUpperThresholdIncrease is generated.
			namely, adValue <= (adTrapUpperThreshold - 
			adTrapUpperHysteresis)."
	::= 2576

    adExceedUpperThresholdDecrease17 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 17 and 
			adValue is less equal the upper threshold minus 
			the upper hysteresis after 
			adExceedUpperThresholdIncrease is generated.
			namely, adValue <= (adTrapUpperThreshold - 
			adTrapUpperHysteresis)."
	::= 2577

    adExceedUpperThresholdDecrease18 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 18 and 
			adValue is less equal the upper threshold minus 
			the upper hysteresis after 
			adExceedUpperThresholdIncrease is generated.
			namely, adValue <= (adTrapUpperThreshold - 
			adTrapUpperHysteresis)."
	::= 2578

    adExceedUpperThresholdDecrease19 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 19 and 
			adValue is less equal the upper threshold minus 
			the upper hysteresis after 
			adExceedUpperThresholdIncrease is generated.
			namely, adValue <= (adTrapUpperThreshold - 
			adTrapUpperHysteresis)."
	::= 2579

    adExceedUpperThresholdDecrease20 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 20 and 
			adValue is less equal the upper threshold minus 
			the upper hysteresis after 
			adExceedUpperThresholdIncrease is generated.
			namely, adValue <= (adTrapUpperThreshold - 
			adTrapUpperHysteresis)."
	::= 2580

    adExceedUpperThresholdDecrease21 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 21 and 
			adValue is less equal the upper threshold minus 
			the upper hysteresis after 
			adExceedUpperThresholdIncrease is generated.
			namely, adValue <= (adTrapUpperThreshold - 
			adTrapUpperHysteresis)."
	::= 2581

    adExceedUpperThresholdDecrease22 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 22 and 
			adValue is less equal the upper threshold minus 
			the upper hysteresis after 
			adExceedUpperThresholdIncrease is generated.
			namely, adValue <= (adTrapUpperThreshold - 
			adTrapUpperHysteresis)."
	::= 2582

    adExceedUpperThresholdDecrease23 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 23 and 
			adValue is less equal the upper threshold minus 
			the upper hysteresis after 
			adExceedUpperThresholdIncrease is generated.
			namely, adValue <= (adTrapUpperThreshold - 
			adTrapUpperHysteresis)."
	::= 2583

    adExceedUpperThresholdDecrease24 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 24 and 
			adValue is less equal the upper threshold minus 
			the upper hysteresis after 
			adExceedUpperThresholdIncrease is generated.
			namely, adValue <= (adTrapUpperThreshold - 
			adTrapUpperHysteresis)."
	::= 2584

    adExceedUpperThresholdDecrease25 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 25 and 
			adValue is less equal the upper threshold minus 
			the upper hysteresis after 
			adExceedUpperThresholdIncrease is generated.
			namely, adValue <= (adTrapUpperThreshold - 
			adTrapUpperHysteresis)."
	::= 2585

    adExceedUpperThresholdDecrease26 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 26 and 
			adValue is less equal the upper threshold minus 
			the upper hysteresis after 
			adExceedUpperThresholdIncrease is generated.
			namely, adValue <= (adTrapUpperThreshold - 
			adTrapUpperHysteresis)."
	::= 2586

    adExceedUpperThresholdDecrease27 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 27 and 
			adValue is less equal the upper threshold minus 
			the upper hysteresis after 
			adExceedUpperThresholdIncrease is generated.
			namely, adValue <= (adTrapUpperThreshold - 
			adTrapUpperHysteresis)."
	::= 2587

    adExceedUpperThresholdDecrease28 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 28 and 
			adValue is less equal the upper threshold minus 
			the upper hysteresis after 
			adExceedUpperThresholdIncrease is generated.
			namely, adValue <= (adTrapUpperThreshold - 
			adTrapUpperHysteresis)."
	::= 2588

    adExceedUpperThresholdDecrease29 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 29 and 
			adValue is less equal the upper threshold minus 
			the upper hysteresis after 
			adExceedUpperThresholdIncrease is generated.
			namely, adValue <= (adTrapUpperThreshold - 
			adTrapUpperHysteresis)."
	::= 2589

    adExceedUpperThresholdDecrease30 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 30 and 
			adValue is less equal the upper threshold minus 
			the upper hysteresis after 
			adExceedUpperThresholdIncrease is generated.
			namely, adValue <= (adTrapUpperThreshold - 
			adTrapUpperHysteresis)."
	::= 2590

    adExceedUpperThresholdDecrease31 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 31 and 
			adValue is less equal the upper threshold minus 
			the upper hysteresis after 
			adExceedUpperThresholdIncrease is generated.
			namely, adValue <= (adTrapUpperThreshold - 
			adTrapUpperHysteresis)."
	::= 2591

    adExceedUpperThresholdDecrease32 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 32 and 
			adValue is less equal the upper threshold minus 
			the upper hysteresis after 
			adExceedUpperThresholdIncrease is generated.
			namely, adValue <= (adTrapUpperThreshold - 
			adTrapUpperHysteresis)."
	::= 2592

    adExceedUpperThresholdDecrease33 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 33 and 
			adValue is less equal the upper threshold minus 
			the upper hysteresis after 
			adExceedUpperThresholdIncrease is generated.
			namely, adValue <= (adTrapUpperThreshold - 
			adTrapUpperHysteresis)."
	::= 2593

    adExceedUpperThresholdDecrease34 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 34 and 
			adValue is less equal the upper threshold minus 
			the upper hysteresis after 
			adExceedUpperThresholdIncrease is generated.
			namely, adValue <= (adTrapUpperThreshold - 
			adTrapUpperHysteresis)."
	::= 2594

    adExceedUpperThresholdDecrease35 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 35 and 
			adValue is less equal the upper threshold minus 
			the upper hysteresis after 
			adExceedUpperThresholdIncrease is generated.
			namely, adValue <= (adTrapUpperThreshold - 
			adTrapUpperHysteresis)."
	::= 2595

    adExceedUpperThresholdDecrease36 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 36 and 
			adValue is less equal the upper threshold minus 
			the upper hysteresis after 
			adExceedUpperThresholdIncrease is generated.
			namely, adValue <= (adTrapUpperThreshold - 
			adTrapUpperHysteresis)."
	::= 2596

    adExceedUpperThresholdDecrease37 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 37 and 
			adValue is less equal the upper threshold minus 
			the upper hysteresis after 
			adExceedUpperThresholdIncrease is generated.
			namely, adValue <= (adTrapUpperThreshold - 
			adTrapUpperHysteresis)."
	::= 2597

    adExceedUpperThresholdDecrease38 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 38 and 
			adValue is less equal the upper threshold minus 
			the upper hysteresis after 
			adExceedUpperThresholdIncrease is generated.
			namely, adValue <= (adTrapUpperThreshold - 
			adTrapUpperHysteresis)."
	::= 2598

    adExceedUpperThresholdDecrease39 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 39 and 
			adValue is less equal the upper threshold minus 
			the upper hysteresis after 
			adExceedUpperThresholdIncrease is generated.
			namely, adValue <= (adTrapUpperThreshold - 
			adTrapUpperHysteresis)."
	::= 2599

    adExceedUpperThresholdDecrease40 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 40 and 
			adValue is less equal the upper threshold minus 
			the upper hysteresis after 
			adExceedUpperThresholdIncrease is generated.
			namely, adValue <= (adTrapUpperThreshold - 
			adTrapUpperHysteresis)."
	::= 2600

    adExceedUpperThresholdDecrease41 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 41 and 
			adValue is less equal the upper threshold minus 
			the upper hysteresis after 
			adExceedUpperThresholdIncrease is generated.
			namely, adValue <= (adTrapUpperThreshold - 
			adTrapUpperHysteresis)."
	::= 2601

    adExceedUpperThresholdDecrease42 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 42 and 
			adValue is less equal the upper threshold minus 
			the upper hysteresis after 
			adExceedUpperThresholdIncrease is generated.
			namely, adValue <= (adTrapUpperThreshold - 
			adTrapUpperHysteresis)."
	::= 2602

    adExceedUpperThresholdDecrease43 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 43 and 
			adValue is less equal the upper threshold minus 
			the upper hysteresis after 
			adExceedUpperThresholdIncrease is generated.
			namely, adValue <= (adTrapUpperThreshold - 
			adTrapUpperHysteresis)."
	::= 2603

    adExceedUpperThresholdDecrease44 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 44 and 
			adValue is less equal the upper threshold minus 
			the upper hysteresis after 
			adExceedUpperThresholdIncrease is generated.
			namely, adValue <= (adTrapUpperThreshold - 
			adTrapUpperHysteresis)."
	::= 2604

    adExceedUpperThresholdDecrease45 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 45 and 
			adValue is less equal the upper threshold minus 
			the upper hysteresis after 
			adExceedUpperThresholdIncrease is generated.
			namely, adValue <= (adTrapUpperThreshold - 
			adTrapUpperHysteresis)."
	::= 2605

    adExceedUpperThresholdDecrease46 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 46 and 
			adValue is less equal the upper threshold minus 
			the upper hysteresis after 
			adExceedUpperThresholdIncrease is generated.
			namely, adValue <= (adTrapUpperThreshold - 
			adTrapUpperHysteresis)."
	::= 2606

    adExceedUpperThresholdDecrease47 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 47 and 
			adValue is less equal the upper threshold minus 
			the upper hysteresis after 
			adExceedUpperThresholdIncrease is generated.
			namely, adValue <= (adTrapUpperThreshold - 
			adTrapUpperHysteresis)."
	::= 2607

    adExceedUpperThresholdDecrease48 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 48 and 
			adValue is less equal the upper threshold minus 
			the upper hysteresis after 
			adExceedUpperThresholdIncrease is generated.
			namely, adValue <= (adTrapUpperThreshold - 
			adTrapUpperHysteresis)."
	::= 2608

    adExceedUpperThresholdDecrease49 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 49 and 
			adValue is less equal the upper threshold minus 
			the upper hysteresis after 
			adExceedUpperThresholdIncrease is generated.
			namely, adValue <= (adTrapUpperThreshold - 
			adTrapUpperHysteresis)."
	::= 2609

    adExceedUpperThresholdDecrease50 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 50 and 
			adValue is less equal the upper threshold minus 
			the upper hysteresis after 
			adExceedUpperThresholdIncrease is generated.
			namely, adValue <= (adTrapUpperThreshold - 
			adTrapUpperHysteresis)."
	::= 2610

    adExceedUpperThresholdDecrease51 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 51 and 
			adValue is less equal the upper threshold minus 
			the upper hysteresis after 
			adExceedUpperThresholdIncrease is generated.
			namely, adValue <= (adTrapUpperThreshold - 
			adTrapUpperHysteresis)."
	::= 2611

    adExceedUpperThresholdDecrease52 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 52 and 
			adValue is less equal the upper threshold minus 
			the upper hysteresis after 
			adExceedUpperThresholdIncrease is generated.
			namely, adValue <= (adTrapUpperThreshold - 
			adTrapUpperHysteresis)."
	::= 2612

    adExceedUpperThresholdDecrease53 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 53 and 
			adValue is less equal the upper threshold minus 
			the upper hysteresis after 
			adExceedUpperThresholdIncrease is generated.
			namely, adValue <= (adTrapUpperThreshold - 
			adTrapUpperHysteresis)."
	::= 2613

    adExceedUpperThresholdDecrease54 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 54 and 
			adValue is less equal the upper threshold minus 
			the upper hysteresis after 
			adExceedUpperThresholdIncrease is generated.
			namely, adValue <= (adTrapUpperThreshold - 
			adTrapUpperHysteresis)."
	::= 2614

    adExceedUpperThresholdDecrease55 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 55 and 
			adValue is less equal the upper threshold minus 
			the upper hysteresis after 
			adExceedUpperThresholdIncrease is generated.
			namely, adValue <= (adTrapUpperThreshold - 
			adTrapUpperHysteresis)."
	::= 2615

    adExceedUpperThresholdDecrease56 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 56 and 
			adValue is less equal the upper threshold minus 
			the upper hysteresis after 
			adExceedUpperThresholdIncrease is generated.
			namely, adValue <= (adTrapUpperThreshold - 
			adTrapUpperHysteresis)."
	::= 2616

    adExceedUpperThresholdDecrease57 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 57 and 
			adValue is less equal the upper threshold minus 
			the upper hysteresis after 
			adExceedUpperThresholdIncrease is generated.
			namely, adValue <= (adTrapUpperThreshold - 
			adTrapUpperHysteresis)."
	::= 2617

    adExceedUpperThresholdDecrease58 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 58 and 
			adValue is less equal the upper threshold minus 
			the upper hysteresis after 
			adExceedUpperThresholdIncrease is generated.
			namely, adValue <= (adTrapUpperThreshold - 
			adTrapUpperHysteresis)."
	::= 2618

    adExceedUpperThresholdDecrease59 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 59 and 
			adValue is less equal the upper threshold minus 
			the upper hysteresis after 
			adExceedUpperThresholdIncrease is generated.
			namely, adValue <= (adTrapUpperThreshold - 
			adTrapUpperHysteresis)."
	::= 2619

    adExceedUpperThresholdDecrease60 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 60 and 
			adValue is less equal the upper threshold minus 
			the upper hysteresis after 
			adExceedUpperThresholdIncrease is generated.
			namely, adValue <= (adTrapUpperThreshold - 
			adTrapUpperHysteresis)."
	::= 2620

    adExceedUpperThresholdDecrease61 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 61 and 
			adValue is less equal the upper threshold minus 
			the upper hysteresis after 
			adExceedUpperThresholdIncrease is generated.
			namely, adValue <= (adTrapUpperThreshold - 
			adTrapUpperHysteresis)."
	::= 2621

    adExceedUpperThresholdDecrease62 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 62 and 
			adValue is less equal the upper threshold minus 
			the upper hysteresis after 
			adExceedUpperThresholdIncrease is generated.
			namely, adValue <= (adTrapUpperThreshold - 
			adTrapUpperHysteresis)."
	::= 2622

    adExceedUpperThresholdDecrease63 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 63 and 
			adValue is less equal the upper threshold minus 
			the upper hysteresis after 
			adExceedUpperThresholdIncrease is generated.
			namely, adValue <= (adTrapUpperThreshold - 
			adTrapUpperHysteresis)."
	::= 2623

    adExceedUpperThresholdDecrease64 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 64 and 
			adValue is less equal the upper threshold minus 
			the upper hysteresis after 
			adExceedUpperThresholdIncrease is generated.
			namely, adValue <= (adTrapUpperThreshold - 
			adTrapUpperHysteresis)."
	::= 2624

    adExceedUpperThresholdDecrease65 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 65 and 
			adValue is less equal the upper threshold minus 
			the upper hysteresis after 
			adExceedUpperThresholdIncrease is generated.
			namely, adValue <= (adTrapUpperThreshold - 
			adTrapUpperHysteresis)."
	::= 2625

    adExceedUpperThresholdDecrease66 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 66 and 
			adValue is less equal the upper threshold minus 
			the upper hysteresis after 
			adExceedUpperThresholdIncrease is generated.
			namely, adValue <= (adTrapUpperThreshold - 
			adTrapUpperHysteresis)."
	::= 2626

    adExceedUpperThresholdDecrease67 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 67 and 
			adValue is less equal the upper threshold minus 
			the upper hysteresis after 
			adExceedUpperThresholdIncrease is generated.
			namely, adValue <= (adTrapUpperThreshold - 
			adTrapUpperHysteresis)."
	::= 2627

    adExceedUpperThresholdDecrease68 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 68 and 
			adValue is less equal the upper threshold minus 
			the upper hysteresis after 
			adExceedUpperThresholdIncrease is generated.
			namely, adValue <= (adTrapUpperThreshold - 
			adTrapUpperHysteresis)."
	::= 2628

    adExceedUpperThresholdDecrease69 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 69 and 
			adValue is less equal the upper threshold minus 
			the upper hysteresis after 
			adExceedUpperThresholdIncrease is generated.
			namely, adValue <= (adTrapUpperThreshold - 
			adTrapUpperHysteresis)."
	::= 2629

    adExceedUpperThresholdDecrease70 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 70 and 
			adValue is less equal the upper threshold minus 
			the upper hysteresis after 
			adExceedUpperThresholdIncrease is generated.
			namely, adValue <= (adTrapUpperThreshold - 
			adTrapUpperHysteresis)."
	::= 2630

    adExceedUpperThresholdDecrease71 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 71 and 
			adValue is less equal the upper threshold minus 
			the upper hysteresis after 
			adExceedUpperThresholdIncrease is generated.
			namely, adValue <= (adTrapUpperThreshold - 
			adTrapUpperHysteresis)."
	::= 2631

    adExceedUpperThresholdDecrease72 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 72 and 
			adValue is less equal the upper threshold minus 
			the upper hysteresis after 
			adExceedUpperThresholdIncrease is generated.
			namely, adValue <= (adTrapUpperThreshold - 
			adTrapUpperHysteresis)."
	::= 2632

    adExceedUpperThresholdDecrease73 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 73 and 
			adValue is less equal the upper threshold minus 
			the upper hysteresis after 
			adExceedUpperThresholdIncrease is generated.
			namely, adValue <= (adTrapUpperThreshold - 
			adTrapUpperHysteresis)."
	::= 2633

    adExceedUpperThresholdDecrease74 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 74 and 
			adValue is less equal the upper threshold minus 
			the upper hysteresis after 
			adExceedUpperThresholdIncrease is generated.
			namely, adValue <= (adTrapUpperThreshold - 
			adTrapUpperHysteresis)."
	::= 2634

    adExceedUpperThresholdDecrease75 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 75 and 
			adValue is less equal the upper threshold minus 
			the upper hysteresis after 
			adExceedUpperThresholdIncrease is generated.
			namely, adValue <= (adTrapUpperThreshold - 
			adTrapUpperHysteresis)."
	::= 2635

    adExceedUpperThresholdDecrease76 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 76 and 
			adValue is less equal the upper threshold minus 
			the upper hysteresis after 
			adExceedUpperThresholdIncrease is generated.
			namely, adValue <= (adTrapUpperThreshold - 
			adTrapUpperHysteresis)."
	::= 2636

    adExceedUpperThresholdDecrease77 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 77 and 
			adValue is less equal the upper threshold minus 
			the upper hysteresis after 
			adExceedUpperThresholdIncrease is generated.
			namely, adValue <= (adTrapUpperThreshold - 
			adTrapUpperHysteresis)."
	::= 2637

    adExceedUpperThresholdDecrease78 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 78 and 
			adValue is less equal the upper threshold minus 
			the upper hysteresis after 
			adExceedUpperThresholdIncrease is generated.
			namely, adValue <= (adTrapUpperThreshold - 
			adTrapUpperHysteresis)."
	::= 2638

    adExceedUpperThresholdDecrease79 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 79 and 
			adValue is less equal the upper threshold minus 
			the upper hysteresis after 
			adExceedUpperThresholdIncrease is generated.
			namely, adValue <= (adTrapUpperThreshold - 
			adTrapUpperHysteresis)."
	::= 2639

    adExceedUpperThresholdDecrease80 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 80 and 
			adValue is less equal the upper threshold minus 
			the upper hysteresis after 
			adExceedUpperThresholdIncrease is generated.
			namely, adValue <= (adTrapUpperThreshold - 
			adTrapUpperHysteresis)."
	::= 2640

    adExceedUpperThresholdDecrease81 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 81 and 
			adValue is less equal the upper threshold minus 
			the upper hysteresis after 
			adExceedUpperThresholdIncrease is generated.
			namely, adValue <= (adTrapUpperThreshold - 
			adTrapUpperHysteresis)."
	::= 2641

    adExceedUpperThresholdDecrease82 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 82 and 
			adValue is less equal the upper threshold minus 
			the upper hysteresis after 
			adExceedUpperThresholdIncrease is generated.
			namely, adValue <= (adTrapUpperThreshold - 
			adTrapUpperHysteresis)."
	::= 2642

    adExceedUpperThresholdDecrease83 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 83 and 
			adValue is less equal the upper threshold minus 
			the upper hysteresis after 
			adExceedUpperThresholdIncrease is generated.
			namely, adValue <= (adTrapUpperThreshold - 
			adTrapUpperHysteresis)."
	::= 2643

    adExceedUpperThresholdDecrease84 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 84 and 
			adValue is less equal the upper threshold minus 
			the upper hysteresis after 
			adExceedUpperThresholdIncrease is generated.
			namely, adValue <= (adTrapUpperThreshold - 
			adTrapUpperHysteresis)."
	::= 2644

    adExceedUpperThresholdDecrease85 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 85 and 
			adValue is less equal the upper threshold minus 
			the upper hysteresis after 
			adExceedUpperThresholdIncrease is generated.
			namely, adValue <= (adTrapUpperThreshold - 
			adTrapUpperHysteresis)."
	::= 2645

    adExceedUpperThresholdDecrease86 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 86 and 
			adValue is less equal the upper threshold minus 
			the upper hysteresis after 
			adExceedUpperThresholdIncrease is generated.
			namely, adValue <= (adTrapUpperThreshold - 
			adTrapUpperHysteresis)."
	::= 2646

    adExceedUpperThresholdDecrease87 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 87 and 
			adValue is less equal the upper threshold minus 
			the upper hysteresis after 
			adExceedUpperThresholdIncrease is generated.
			namely, adValue <= (adTrapUpperThreshold - 
			adTrapUpperHysteresis)."
	::= 2647

    adExceedUpperThresholdDecrease88 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 88 and 
			adValue is less equal the upper threshold minus 
			the upper hysteresis after 
			adExceedUpperThresholdIncrease is generated.
			namely, adValue <= (adTrapUpperThreshold - 
			adTrapUpperHysteresis)."
	::= 2648

    adExceedUpperThresholdDecrease89 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 89 and 
			adValue is less equal the upper threshold minus 
			the upper hysteresis after 
			adExceedUpperThresholdIncrease is generated.
			namely, adValue <= (adTrapUpperThreshold - 
			adTrapUpperHysteresis)."
	::= 2649

    adExceedUpperThresholdDecrease90 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 90 and 
			adValue is less equal the upper threshold minus 
			the upper hysteresis after 
			adExceedUpperThresholdIncrease is generated.
			namely, adValue <= (adTrapUpperThreshold - 
			adTrapUpperHysteresis)."
	::= 2650

    adExceedUpperThresholdDecrease91 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 91 and 
			adValue is less equal the upper threshold minus 
			the upper hysteresis after 
			adExceedUpperThresholdIncrease is generated.
			namely, adValue <= (adTrapUpperThreshold - 
			adTrapUpperHysteresis)."
	::= 2651

    adExceedUpperThresholdDecrease92 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 92 and 
			adValue is less equal the upper threshold minus 
			the upper hysteresis after 
			adExceedUpperThresholdIncrease is generated.
			namely, adValue <= (adTrapUpperThreshold - 
			adTrapUpperHysteresis)."
	::= 2652

    adExceedUpperThresholdDecrease93 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 93 and 
			adValue is less equal the upper threshold minus 
			the upper hysteresis after 
			adExceedUpperThresholdIncrease is generated.
			namely, adValue <= (adTrapUpperThreshold - 
			adTrapUpperHysteresis)."
	::= 2653

    adExceedUpperThresholdDecrease94 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 94 and 
			adValue is less equal the upper threshold minus 
			the upper hysteresis after 
			adExceedUpperThresholdIncrease is generated.
			namely, adValue <= (adTrapUpperThreshold - 
			adTrapUpperHysteresis)."
	::= 2654

    adExceedUpperThresholdDecrease95 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 95 and 
			adValue is less equal the upper threshold minus 
			the upper hysteresis after 
			adExceedUpperThresholdIncrease is generated.
			namely, adValue <= (adTrapUpperThreshold - 
			adTrapUpperHysteresis)."
	::= 2655

    adExceedUpperThresholdDecrease96 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 96 and 
			adValue is less equal the upper threshold minus 
			the upper hysteresis after 
			adExceedUpperThresholdIncrease is generated.
			namely, adValue <= (adTrapUpperThreshold - 
			adTrapUpperHysteresis)."
	::= 2656

    adExceedUpperThresholdDecrease97 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 97 and 
			adValue is less equal the upper threshold minus 
			the upper hysteresis after 
			adExceedUpperThresholdIncrease is generated.
			namely, adValue <= (adTrapUpperThreshold - 
			adTrapUpperHysteresis)."
	::= 2657

    adExceedUpperThresholdDecrease98 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 98 and 
			adValue is less equal the upper threshold minus 
			the upper hysteresis after 
			adExceedUpperThresholdIncrease is generated.
			namely, adValue <= (adTrapUpperThreshold - 
			adTrapUpperHysteresis)."
	::= 2658

    adExceedUpperThresholdDecrease99 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 99 and 
			adValue is less equal the upper threshold minus 
			the upper hysteresis after 
			adExceedUpperThresholdIncrease is generated.
			namely, adValue <= (adTrapUpperThreshold - 
			adTrapUpperHysteresis)."
	::= 2659

    adExceedUpperThresholdDecrease100 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 100 and 
			adValue is less equal the upper threshold minus 
			the upper hysteresis after 
			adExceedUpperThresholdIncrease is generated.
			namely, adValue <= (adTrapUpperThreshold - 
			adTrapUpperHysteresis)."
	::= 2660

    adExceedUpperThresholdDecrease101 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 101 and 
			adValue is less equal the upper threshold minus 
			the upper hysteresis after 
			adExceedUpperThresholdIncrease is generated.
			namely, adValue <= (adTrapUpperThreshold - 
			adTrapUpperHysteresis)."
	::= 2661

    adExceedUpperThresholdDecrease102 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 102 and 
			adValue is less equal the upper threshold minus 
			the upper hysteresis after 
			adExceedUpperThresholdIncrease is generated.
			namely, adValue <= (adTrapUpperThreshold - 
			adTrapUpperHysteresis)."
	::= 2662

    adExceedUpperThresholdDecrease103 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 103 and 
			adValue is less equal the upper threshold minus 
			the upper hysteresis after 
			adExceedUpperThresholdIncrease is generated.
			namely, adValue <= (adTrapUpperThreshold - 
			adTrapUpperHysteresis)."
	::= 2663

    adExceedUpperThresholdDecrease104 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 104 and 
			adValue is less equal the upper threshold minus 
			the upper hysteresis after 
			adExceedUpperThresholdIncrease is generated.
			namely, adValue <= (adTrapUpperThreshold - 
			adTrapUpperHysteresis)."
	::= 2664

    adExceedUpperThresholdDecrease105 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 105 and 
			adValue is less equal the upper threshold minus 
			the upper hysteresis after 
			adExceedUpperThresholdIncrease is generated.
			namely, adValue <= (adTrapUpperThreshold - 
			adTrapUpperHysteresis)."
	::= 2665

    adExceedUpperThresholdDecrease106 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 106 and 
			adValue is less equal the upper threshold minus 
			the upper hysteresis after 
			adExceedUpperThresholdIncrease is generated.
			namely, adValue <= (adTrapUpperThreshold - 
			adTrapUpperHysteresis)."
	::= 2666

    adExceedUpperThresholdDecrease107 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 107 and 
			adValue is less equal the upper threshold minus 
			the upper hysteresis after 
			adExceedUpperThresholdIncrease is generated.
			namely, adValue <= (adTrapUpperThreshold - 
			adTrapUpperHysteresis)."
	::= 2667

    adExceedUpperThresholdDecrease108 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 108 and 
			adValue is less equal the upper threshold minus 
			the upper hysteresis after 
			adExceedUpperThresholdIncrease is generated.
			namely, adValue <= (adTrapUpperThreshold - 
			adTrapUpperHysteresis)."
	::= 2668

    adExceedUpperThresholdDecrease109 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 109 and 
			adValue is less equal the upper threshold minus 
			the upper hysteresis after 
			adExceedUpperThresholdIncrease is generated.
			namely, adValue <= (adTrapUpperThreshold - 
			adTrapUpperHysteresis)."
	::= 2669

    adExceedUpperThresholdDecrease110 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 110 and 
			adValue is less equal the upper threshold minus 
			the upper hysteresis after 
			adExceedUpperThresholdIncrease is generated.
			namely, adValue <= (adTrapUpperThreshold - 
			adTrapUpperHysteresis)."
	::= 2670

    adExceedUpperThresholdDecrease111 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 111 and 
			adValue is less equal the upper threshold minus 
			the upper hysteresis after 
			adExceedUpperThresholdIncrease is generated.
			namely, adValue <= (adTrapUpperThreshold - 
			adTrapUpperHysteresis)."
	::= 2671

    adExceedUpperThresholdDecrease112 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 112 and 
			adValue is less equal the upper threshold minus 
			the upper hysteresis after 
			adExceedUpperThresholdIncrease is generated.
			namely, adValue <= (adTrapUpperThreshold - 
			adTrapUpperHysteresis)."
	::= 2672

    adExceedUpperThresholdDecrease113 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 113 and 
			adValue is less equal the upper threshold minus 
			the upper hysteresis after 
			adExceedUpperThresholdIncrease is generated.
			namely, adValue <= (adTrapUpperThreshold - 
			adTrapUpperHysteresis)."
	::= 2673

    adExceedUpperThresholdDecrease114 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 114 and 
			adValue is less equal the upper threshold minus 
			the upper hysteresis after 
			adExceedUpperThresholdIncrease is generated.
			namely, adValue <= (adTrapUpperThreshold - 
			adTrapUpperHysteresis)."
	::= 2674

    adExceedUpperThresholdDecrease115 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 115 and 
			adValue is less equal the upper threshold minus 
			the upper hysteresis after 
			adExceedUpperThresholdIncrease is generated.
			namely, adValue <= (adTrapUpperThreshold - 
			adTrapUpperHysteresis)."
	::= 2675

    adExceedUpperThresholdDecrease116 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 116 and 
			adValue is less equal the upper threshold minus 
			the upper hysteresis after 
			adExceedUpperThresholdIncrease is generated.
			namely, adValue <= (adTrapUpperThreshold - 
			adTrapUpperHysteresis)."
	::= 2676

    adExceedUpperThresholdDecrease117 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 117 and 
			adValue is less equal the upper threshold minus 
			the upper hysteresis after 
			adExceedUpperThresholdIncrease is generated.
			namely, adValue <= (adTrapUpperThreshold - 
			adTrapUpperHysteresis)."
	::= 2677

    adExceedUpperThresholdDecrease118 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 118 and 
			adValue is less equal the upper threshold minus 
			the upper hysteresis after 
			adExceedUpperThresholdIncrease is generated.
			namely, adValue <= (adTrapUpperThreshold - 
			adTrapUpperHysteresis)."
	::= 2678

    adExceedUpperThresholdDecrease119 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 119 and 
			adValue is less equal the upper threshold minus 
			the upper hysteresis after 
			adExceedUpperThresholdIncrease is generated.
			namely, adValue <= (adTrapUpperThreshold - 
			adTrapUpperHysteresis)."
	::= 2679

    adExceedUpperThresholdDecrease120 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 120 and 
			adValue is less equal the upper threshold minus 
			the upper hysteresis after 
			adExceedUpperThresholdIncrease is generated.
			namely, adValue <= (adTrapUpperThreshold - 
			adTrapUpperHysteresis)."
	::= 2680

    adExceedUpperThresholdDecrease121 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 121 and 
			adValue is less equal the upper threshold minus 
			the upper hysteresis after 
			adExceedUpperThresholdIncrease is generated.
			namely, adValue <= (adTrapUpperThreshold - 
			adTrapUpperHysteresis)."
	::= 2681

    adExceedUpperThresholdDecrease122 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 122 and 
			adValue is less equal the upper threshold minus 
			the upper hysteresis after 
			adExceedUpperThresholdIncrease is generated.
			namely, adValue <= (adTrapUpperThreshold - 
			adTrapUpperHysteresis)."
	::= 2682

    adExceedUpperThresholdDecrease123 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 123 and 
			adValue is less equal the upper threshold minus 
			the upper hysteresis after 
			adExceedUpperThresholdIncrease is generated.
			namely, adValue <= (adTrapUpperThreshold - 
			adTrapUpperHysteresis)."
	::= 2683

    adExceedUpperThresholdDecrease124 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 124 and 
			adValue is less equal the upper threshold minus 
			the upper hysteresis after 
			adExceedUpperThresholdIncrease is generated.
			namely, adValue <= (adTrapUpperThreshold - 
			adTrapUpperHysteresis)."
	::= 2684

    adExceedUpperThresholdDecrease125 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 125 and 
			adValue is less equal the upper threshold minus 
			the upper hysteresis after 
			adExceedUpperThresholdIncrease is generated.
			namely, adValue <= (adTrapUpperThreshold - 
			adTrapUpperHysteresis)."
	::= 2685

    adExceedUpperThresholdDecrease126 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 126 and 
			adValue is less equal the upper threshold minus 
			the upper hysteresis after 
			adExceedUpperThresholdIncrease is generated.
			namely, adValue <= (adTrapUpperThreshold - 
			adTrapUpperHysteresis)."
	::= 2686

    adExceedUpperThresholdDecrease127 TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdDecreaseTrapID equal 127 and 
			adValue is less equal the upper threshold minus 
			the upper hysteresis after 
			adExceedUpperThresholdIncrease is generated.
			namely, adValue <= (adTrapUpperThreshold - 
			adTrapUpperHysteresis)."
	::= 2687

    adExceedingUpperThreshold1	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 1 and
			until adExceedUpperThresholdDecrease is generated after
			adExceedUpperThresholdIncrease is generated."
	::= 3073

    adExceedingUpperThreshold2	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 2 and
			until adExceedUpperThresholdDecrease is generated after
			adExceedUpperThresholdIncrease is generated."
	::= 3074

    adExceedingUpperThreshold3	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 3 and
			until adExceedUpperThresholdDecrease is generated after
			adExceedUpperThresholdIncrease is generated."
	::= 3075

    adExceedingUpperThreshold4	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 4 and
			until adExceedUpperThresholdDecrease is generated after
			adExceedUpperThresholdIncrease is generated."
	::= 3076

    adExceedingUpperThreshold5	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 5 and
			until adExceedUpperThresholdDecrease is generated after
			adExceedUpperThresholdIncrease is generated."
	::= 3077

    adExceedingUpperThreshold6	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 6 and
			until adExceedUpperThresholdDecrease is generated after
			adExceedUpperThresholdIncrease is generated."
	::= 3078

    adExceedingUpperThreshold7	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 7 and
			until adExceedUpperThresholdDecrease is generated after
			adExceedUpperThresholdIncrease is generated."
	::= 3079

    adExceedingUpperThreshold8	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 8 and
			until adExceedUpperThresholdDecrease is generated after
			adExceedUpperThresholdIncrease is generated."
	::= 3080

    adExceedingUpperThreshold9	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 9 and
			until adExceedUpperThresholdDecrease is generated after
			adExceedUpperThresholdIncrease is generated."
	::= 3081

    adExceedingUpperThreshold10	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 10 and
			until adExceedUpperThresholdDecrease is generated after
			adExceedUpperThresholdIncrease is generated."
	::= 3082

    adExceedingUpperThreshold11	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 11 and
			until adExceedUpperThresholdDecrease is generated after
			adExceedUpperThresholdIncrease is generated."
	::= 3083

    adExceedingUpperThreshold12	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 12 and
			until adExceedUpperThresholdDecrease is generated after
			adExceedUpperThresholdIncrease is generated."
	::= 3084

    adExceedingUpperThreshold13	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 13 and
			until adExceedUpperThresholdDecrease is generated after
			adExceedUpperThresholdIncrease is generated."
	::= 3085

    adExceedingUpperThreshold14	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 14 and
			until adExceedUpperThresholdDecrease is generated after
			adExceedUpperThresholdIncrease is generated."
	::= 3086

    adExceedingUpperThreshold15	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 15 and
			until adExceedUpperThresholdDecrease is generated after
			adExceedUpperThresholdIncrease is generated."
	::= 3087

    adExceedingUpperThreshold16	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 16 and
			until adExceedUpperThresholdDecrease is generated after
			adExceedUpperThresholdIncrease is generated."
	::= 3088

    adExceedingUpperThreshold17	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 17 and
			until adExceedUpperThresholdDecrease is generated after
			adExceedUpperThresholdIncrease is generated."
	::= 3089

    adExceedingUpperThreshold18	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 18 and
			until adExceedUpperThresholdDecrease is generated after
			adExceedUpperThresholdIncrease is generated."
	::= 3090

    adExceedingUpperThreshold19	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 19 and
			until adExceedUpperThresholdDecrease is generated after
			adExceedUpperThresholdIncrease is generated."
	::= 3091

    adExceedingUpperThreshold20	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 20 and
			until adExceedUpperThresholdDecrease is generated after
			adExceedUpperThresholdIncrease is generated."
	::= 3092

    adExceedingUpperThreshold21	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 21 and
			until adExceedUpperThresholdDecrease is generated after
			adExceedUpperThresholdIncrease is generated."
	::= 3093

    adExceedingUpperThreshold22	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 22 and
			until adExceedUpperThresholdDecrease is generated after
			adExceedUpperThresholdIncrease is generated."
	::= 3094

    adExceedingUpperThreshold23	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 23 and
			until adExceedUpperThresholdDecrease is generated after
			adExceedUpperThresholdIncrease is generated."
	::= 3095

    adExceedingUpperThreshold24	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 24 and
			until adExceedUpperThresholdDecrease is generated after
			adExceedUpperThresholdIncrease is generated."
	::= 3096

    adExceedingUpperThreshold25	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 25 and
			until adExceedUpperThresholdDecrease is generated after
			adExceedUpperThresholdIncrease is generated."
	::= 3097

    adExceedingUpperThreshold26	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 26 and
			until adExceedUpperThresholdDecrease is generated after
			adExceedUpperThresholdIncrease is generated."
	::= 3098

    adExceedingUpperThreshold27	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 27 and
			until adExceedUpperThresholdDecrease is generated after
			adExceedUpperThresholdIncrease is generated."
	::= 3099

    adExceedingUpperThreshold28	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 28 and
			until adExceedUpperThresholdDecrease is generated after
			adExceedUpperThresholdIncrease is generated."
	::= 3100

    adExceedingUpperThreshold29	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 29 and
			until adExceedUpperThresholdDecrease is generated after
			adExceedUpperThresholdIncrease is generated."
	::= 3101

    adExceedingUpperThreshold30	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 30 and
			until adExceedUpperThresholdDecrease is generated after
			adExceedUpperThresholdIncrease is generated."
	::= 3102

    adExceedingUpperThreshold31	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 31 and
			until adExceedUpperThresholdDecrease is generated after
			adExceedUpperThresholdIncrease is generated."
	::= 3103

    adExceedingUpperThreshold32	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 32 and
			until adExceedUpperThresholdDecrease is generated after
			adExceedUpperThresholdIncrease is generated."
	::= 3104

    adExceedingUpperThreshold33	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 33 and
			until adExceedUpperThresholdDecrease is generated after
			adExceedUpperThresholdIncrease is generated."
	::= 3105

    adExceedingUpperThreshold34	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 34 and
			until adExceedUpperThresholdDecrease is generated after
			adExceedUpperThresholdIncrease is generated."
	::= 3106

    adExceedingUpperThreshold35	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 35 and
			until adExceedUpperThresholdDecrease is generated after
			adExceedUpperThresholdIncrease is generated."
	::= 3107

    adExceedingUpperThreshold36	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 36 and
			until adExceedUpperThresholdDecrease is generated after
			adExceedUpperThresholdIncrease is generated."
	::= 3108

    adExceedingUpperThreshold37	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 37 and
			until adExceedUpperThresholdDecrease is generated after
			adExceedUpperThresholdIncrease is generated."
	::= 3109

    adExceedingUpperThreshold38	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 38 and
			until adExceedUpperThresholdDecrease is generated after
			adExceedUpperThresholdIncrease is generated."
	::= 3110

    adExceedingUpperThreshold39	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 39 and
			until adExceedUpperThresholdDecrease is generated after
			adExceedUpperThresholdIncrease is generated."
	::= 3111

    adExceedingUpperThreshold40	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 40 and
			until adExceedUpperThresholdDecrease is generated after
			adExceedUpperThresholdIncrease is generated."
	::= 3112

    adExceedingUpperThreshold41	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 41 and
			until adExceedUpperThresholdDecrease is generated after
			adExceedUpperThresholdIncrease is generated."
	::= 3113

    adExceedingUpperThreshold42	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 42 and
			until adExceedUpperThresholdDecrease is generated after
			adExceedUpperThresholdIncrease is generated."
	::= 3114

    adExceedingUpperThreshold43	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 43 and
			until adExceedUpperThresholdDecrease is generated after
			adExceedUpperThresholdIncrease is generated."
	::= 3115

    adExceedingUpperThreshold44	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 44 and
			until adExceedUpperThresholdDecrease is generated after
			adExceedUpperThresholdIncrease is generated."
	::= 3116

    adExceedingUpperThreshold45	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 45 and
			until adExceedUpperThresholdDecrease is generated after
			adExceedUpperThresholdIncrease is generated."
	::= 3117

    adExceedingUpperThreshold46	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 46 and
			until adExceedUpperThresholdDecrease is generated after
			adExceedUpperThresholdIncrease is generated."
	::= 3118

    adExceedingUpperThreshold47	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 47 and
			until adExceedUpperThresholdDecrease is generated after
			adExceedUpperThresholdIncrease is generated."
	::= 3119

    adExceedingUpperThreshold48	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 48 and
			until adExceedUpperThresholdDecrease is generated after
			adExceedUpperThresholdIncrease is generated."
	::= 3120

    adExceedingUpperThreshold49	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 49 and
			until adExceedUpperThresholdDecrease is generated after
			adExceedUpperThresholdIncrease is generated."
	::= 3121

    adExceedingUpperThreshold50	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 50 and
			until adExceedUpperThresholdDecrease is generated after
			adExceedUpperThresholdIncrease is generated."
	::= 3122

    adExceedingUpperThreshold51	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 51 and
			until adExceedUpperThresholdDecrease is generated after
			adExceedUpperThresholdIncrease is generated."
	::= 3123

    adExceedingUpperThreshold52	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 52 and
			until adExceedUpperThresholdDecrease is generated after
			adExceedUpperThresholdIncrease is generated."
	::= 3124

    adExceedingUpperThreshold53	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 53 and
			until adExceedUpperThresholdDecrease is generated after
			adExceedUpperThresholdIncrease is generated."
	::= 3125

    adExceedingUpperThreshold54	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 54 and
			until adExceedUpperThresholdDecrease is generated after
			adExceedUpperThresholdIncrease is generated."
	::= 3126

    adExceedingUpperThreshold55	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 55 and
			until adExceedUpperThresholdDecrease is generated after
			adExceedUpperThresholdIncrease is generated."
	::= 3127

    adExceedingUpperThreshold56	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 56 and
			until adExceedUpperThresholdDecrease is generated after
			adExceedUpperThresholdIncrease is generated."
	::= 3128

    adExceedingUpperThreshold57	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 57 and
			until adExceedUpperThresholdDecrease is generated after
			adExceedUpperThresholdIncrease is generated."
	::= 3129

    adExceedingUpperThreshold58	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 58 and
			until adExceedUpperThresholdDecrease is generated after
			adExceedUpperThresholdIncrease is generated."
	::= 3130

    adExceedingUpperThreshold59	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 59 and
			until adExceedUpperThresholdDecrease is generated after
			adExceedUpperThresholdIncrease is generated."
	::= 3131

    adExceedingUpperThreshold60	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 60 and
			until adExceedUpperThresholdDecrease is generated after
			adExceedUpperThresholdIncrease is generated."
	::= 3132

    adExceedingUpperThreshold61	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 61 and
			until adExceedUpperThresholdDecrease is generated after
			adExceedUpperThresholdIncrease is generated."
	::= 3133

    adExceedingUpperThreshold62	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 62 and
			until adExceedUpperThresholdDecrease is generated after
			adExceedUpperThresholdIncrease is generated."
	::= 3134

    adExceedingUpperThreshold63	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 63 and
			until adExceedUpperThresholdDecrease is generated after
			adExceedUpperThresholdIncrease is generated."
	::= 3135

    adExceedingUpperThreshold64	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 64 and
			until adExceedUpperThresholdDecrease is generated after
			adExceedUpperThresholdIncrease is generated."
	::= 3136

    adExceedingUpperThreshold65	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 65 and
			until adExceedUpperThresholdDecrease is generated after
			adExceedUpperThresholdIncrease is generated."
	::= 3137

    adExceedingUpperThreshold66	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 66 and
			until adExceedUpperThresholdDecrease is generated after
			adExceedUpperThresholdIncrease is generated."
	::= 3138

    adExceedingUpperThreshold67	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 67 and
			until adExceedUpperThresholdDecrease is generated after
			adExceedUpperThresholdIncrease is generated."
	::= 3139

    adExceedingUpperThreshold68	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 68 and
			until adExceedUpperThresholdDecrease is generated after
			adExceedUpperThresholdIncrease is generated."
	::= 3140

    adExceedingUpperThreshold69	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 69 and
			until adExceedUpperThresholdDecrease is generated after
			adExceedUpperThresholdIncrease is generated."
	::= 3141

    adExceedingUpperThreshold70	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 70 and
			until adExceedUpperThresholdDecrease is generated after
			adExceedUpperThresholdIncrease is generated."
	::= 3142

    adExceedingUpperThreshold71	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 71 and
			until adExceedUpperThresholdDecrease is generated after
			adExceedUpperThresholdIncrease is generated."
	::= 3143

    adExceedingUpperThreshold72	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 72 and
			until adExceedUpperThresholdDecrease is generated after
			adExceedUpperThresholdIncrease is generated."
	::= 3144

    adExceedingUpperThreshold73	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 73 and
			until adExceedUpperThresholdDecrease is generated after
			adExceedUpperThresholdIncrease is generated."
	::= 3145

    adExceedingUpperThreshold74	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 74 and
			until adExceedUpperThresholdDecrease is generated after
			adExceedUpperThresholdIncrease is generated."
	::= 3146

    adExceedingUpperThreshold75	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 75 and
			until adExceedUpperThresholdDecrease is generated after
			adExceedUpperThresholdIncrease is generated."
	::= 3147

    adExceedingUpperThreshold76	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 76 and
			until adExceedUpperThresholdDecrease is generated after
			adExceedUpperThresholdIncrease is generated."
	::= 3148

    adExceedingUpperThreshold77	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 77 and
			until adExceedUpperThresholdDecrease is generated after
			adExceedUpperThresholdIncrease is generated."
	::= 3149

    adExceedingUpperThreshold78	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 78 and
			until adExceedUpperThresholdDecrease is generated after
			adExceedUpperThresholdIncrease is generated."
	::= 3150

    adExceedingUpperThreshold79	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 79 and
			until adExceedUpperThresholdDecrease is generated after
			adExceedUpperThresholdIncrease is generated."
	::= 3151

    adExceedingUpperThreshold80	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 80 and
			until adExceedUpperThresholdDecrease is generated after
			adExceedUpperThresholdIncrease is generated."
	::= 3152

    adExceedingUpperThreshold81	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 81 and
			until adExceedUpperThresholdDecrease is generated after
			adExceedUpperThresholdIncrease is generated."
	::= 3153

    adExceedingUpperThreshold82	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 82 and
			until adExceedUpperThresholdDecrease is generated after
			adExceedUpperThresholdIncrease is generated."
	::= 3154

    adExceedingUpperThreshold83	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 83 and
			until adExceedUpperThresholdDecrease is generated after
			adExceedUpperThresholdIncrease is generated."
	::= 3155

    adExceedingUpperThreshold84	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 84 and
			until adExceedUpperThresholdDecrease is generated after
			adExceedUpperThresholdIncrease is generated."
	::= 3156

    adExceedingUpperThreshold85	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 85 and
			until adExceedUpperThresholdDecrease is generated after
			adExceedUpperThresholdIncrease is generated."
	::= 3157

    adExceedingUpperThreshold86	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 86 and
			until adExceedUpperThresholdDecrease is generated after
			adExceedUpperThresholdIncrease is generated."
	::= 3158

    adExceedingUpperThreshold87	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 87 and
			until adExceedUpperThresholdDecrease is generated after
			adExceedUpperThresholdIncrease is generated."
	::= 3159

    adExceedingUpperThreshold88	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 88 and
			until adExceedUpperThresholdDecrease is generated after
			adExceedUpperThresholdIncrease is generated."
	::= 3160

    adExceedingUpperThreshold89	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 89 and
			until adExceedUpperThresholdDecrease is generated after
			adExceedUpperThresholdIncrease is generated."
	::= 3161

    adExceedingUpperThreshold90	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 90 and
			until adExceedUpperThresholdDecrease is generated after
			adExceedUpperThresholdIncrease is generated."
	::= 3162

    adExceedingUpperThreshold91	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 91 and
			until adExceedUpperThresholdDecrease is generated after
			adExceedUpperThresholdIncrease is generated."
	::= 3163

    adExceedingUpperThreshold92	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 92 and
			until adExceedUpperThresholdDecrease is generated after
			adExceedUpperThresholdIncrease is generated."
	::= 3164

    adExceedingUpperThreshold93	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 93 and
			until adExceedUpperThresholdDecrease is generated after
			adExceedUpperThresholdIncrease is generated."
	::= 3165

    adExceedingUpperThreshold94	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 94 and
			until adExceedUpperThresholdDecrease is generated after
			adExceedUpperThresholdIncrease is generated."
	::= 3166

    adExceedingUpperThreshold95	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 95 and
			until adExceedUpperThresholdDecrease is generated after
			adExceedUpperThresholdIncrease is generated."
	::= 3167

    adExceedingUpperThreshold96	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 96 and
			until adExceedUpperThresholdDecrease is generated after
			adExceedUpperThresholdIncrease is generated."
	::= 3168

    adExceedingUpperThreshold97	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 97 and
			until adExceedUpperThresholdDecrease is generated after
			adExceedUpperThresholdIncrease is generated."
	::= 3169

    adExceedingUpperThreshold98	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 98 and
			until adExceedUpperThresholdDecrease is generated after
			adExceedUpperThresholdIncrease is generated."
	::= 3170

    adExceedingUpperThreshold99	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 99 and
			until adExceedUpperThresholdDecrease is generated after
			adExceedUpperThresholdIncrease is generated."
	::= 3171

    adExceedingUpperThreshold100	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 100 and
			until adExceedUpperThresholdDecrease is generated after
			adExceedUpperThresholdIncrease is generated."
	::= 3172

    adExceedingUpperThreshold101	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 101 and
			until adExceedUpperThresholdDecrease is generated after
			adExceedUpperThresholdIncrease is generated."
	::= 3173

    adExceedingUpperThreshold102	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 102 and
			until adExceedUpperThresholdDecrease is generated after
			adExceedUpperThresholdIncrease is generated."
	::= 3174

    adExceedingUpperThreshold103	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 103 and
			until adExceedUpperThresholdDecrease is generated after
			adExceedUpperThresholdIncrease is generated."
	::= 3175

    adExceedingUpperThreshold104	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 104 and
			until adExceedUpperThresholdDecrease is generated after
			adExceedUpperThresholdIncrease is generated."
	::= 3176

    adExceedingUpperThreshold105	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 105 and
			until adExceedUpperThresholdDecrease is generated after
			adExceedUpperThresholdIncrease is generated."
	::= 3177

    adExceedingUpperThreshold106	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 106 and
			until adExceedUpperThresholdDecrease is generated after
			adExceedUpperThresholdIncrease is generated."
	::= 3178

    adExceedingUpperThreshold107	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 107 and
			until adExceedUpperThresholdDecrease is generated after
			adExceedUpperThresholdIncrease is generated."
	::= 3179

    adExceedingUpperThreshold108	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 108 and
			until adExceedUpperThresholdDecrease is generated after
			adExceedUpperThresholdIncrease is generated."
	::= 3180

    adExceedingUpperThreshold109	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 109 and
			until adExceedUpperThresholdDecrease is generated after
			adExceedUpperThresholdIncrease is generated."
	::= 3181

    adExceedingUpperThreshold110	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 110 and
			until adExceedUpperThresholdDecrease is generated after
			adExceedUpperThresholdIncrease is generated."
	::= 3182

    adExceedingUpperThreshold111	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 111 and
			until adExceedUpperThresholdDecrease is generated after
			adExceedUpperThresholdIncrease is generated."
	::= 3183

    adExceedingUpperThreshold112	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 112 and
			until adExceedUpperThresholdDecrease is generated after
			adExceedUpperThresholdIncrease is generated."
	::= 3184

    adExceedingUpperThreshold113	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 113 and
			until adExceedUpperThresholdDecrease is generated after
			adExceedUpperThresholdIncrease is generated."
	::= 3185

    adExceedingUpperThreshold114	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 114 and
			until adExceedUpperThresholdDecrease is generated after
			adExceedUpperThresholdIncrease is generated."
	::= 3186

    adExceedingUpperThreshold115	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 115 and
			until adExceedUpperThresholdDecrease is generated after
			adExceedUpperThresholdIncrease is generated."
	::= 3187

    adExceedingUpperThreshold116	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 116 and
			until adExceedUpperThresholdDecrease is generated after
			adExceedUpperThresholdIncrease is generated."
	::= 3188

    adExceedingUpperThreshold117	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 117 and
			until adExceedUpperThresholdDecrease is generated after
			adExceedUpperThresholdIncrease is generated."
	::= 3189

    adExceedingUpperThreshold118	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 118 and
			until adExceedUpperThresholdDecrease is generated after
			adExceedUpperThresholdIncrease is generated."
	::= 3190

    adExceedingUpperThreshold119	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 119 and
			until adExceedUpperThresholdDecrease is generated after
			adExceedUpperThresholdIncrease is generated."
	::= 3191

    adExceedingUpperThreshold120	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 120 and
			until adExceedUpperThresholdDecrease is generated after
			adExceedUpperThresholdIncrease is generated."
	::= 3192

    adExceedingUpperThreshold121	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 121 and
			until adExceedUpperThresholdDecrease is generated after
			adExceedUpperThresholdIncrease is generated."
	::= 3193

    adExceedingUpperThreshold122	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 122 and
			until adExceedUpperThresholdDecrease is generated after
			adExceedUpperThresholdIncrease is generated."
	::= 3194

    adExceedingUpperThreshold123	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 123 and
			until adExceedUpperThresholdDecrease is generated after
			adExceedUpperThresholdIncrease is generated."
	::= 3195

    adExceedingUpperThreshold124	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 124 and
			until adExceedUpperThresholdDecrease is generated after
			adExceedUpperThresholdIncrease is generated."
	::= 3196

    adExceedingUpperThreshold125	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 125 and
			until adExceedUpperThresholdDecrease is generated after
			adExceedUpperThresholdIncrease is generated."
	::= 3197

    adExceedingUpperThreshold126	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 126 and
			until adExceedUpperThresholdDecrease is generated after
			adExceedUpperThresholdIncrease is generated."
	::= 3198

    adExceedingUpperThreshold127	TRAP-TYPE
	ENTERPRISE	network-device
	VARIABLES	{ adValue, adminDateAndTime, adminNDTrapSeqNo,
			  adIndex, adType, adValueOnlyString,
			  adTrapCurrentStatus }
	DESCRIPTION	"This trap is generated when set
			adExUpThresholdTrapID equal 127 and
			until adExceedUpperThresholdDecrease is generated after
			adExceedUpperThresholdIncrease is generated."
	::= 3199

    adExceedLowerThresholdIncrease1 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 1 and
			adValue is greater equal
			the lower threshold plus the lower hysteresis
			after adExceedLowerThresholdDecrease is generated.
			namely, adValue >= (adTrapLowerThreshold +
			adTrapLowerHysteresis)."
	::= 3585

    adExceedLowerThresholdIncrease2 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 2 and
			adValue is greater equal
			the lower threshold plus the lower hysteresis
			after adExceedLowerThresholdDecrease is generated.
			namely, adValue >= (adTrapLowerThreshold +
			adTrapLowerHysteresis)."
	::= 3586

    adExceedLowerThresholdIncrease3 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 3 and
			adValue is greater equal
			the lower threshold plus the lower hysteresis
			after adExceedLowerThresholdDecrease is generated.
			namely, adValue >= (adTrapLowerThreshold +
			adTrapLowerHysteresis)."
	::= 3587

    adExceedLowerThresholdIncrease4 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 4 and
			adValue is greater equal
			the lower threshold plus the lower hysteresis
			after adExceedLowerThresholdDecrease is generated.
			namely, adValue >= (adTrapLowerThreshold +
			adTrapLowerHysteresis)."
	::= 3588

    adExceedLowerThresholdIncrease5 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 5 and
			adValue is greater equal
			the lower threshold plus the lower hysteresis
			after adExceedLowerThresholdDecrease is generated.
			namely, adValue >= (adTrapLowerThreshold +
			adTrapLowerHysteresis)."
	::= 3589

    adExceedLowerThresholdIncrease6 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 6 and
			adValue is greater equal
			the lower threshold plus the lower hysteresis
			after adExceedLowerThresholdDecrease is generated.
			namely, adValue >= (adTrapLowerThreshold +
			adTrapLowerHysteresis)."
	::= 3590

    adExceedLowerThresholdIncrease7 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 7 and
			adValue is greater equal
			the lower threshold plus the lower hysteresis
			after adExceedLowerThresholdDecrease is generated.
			namely, adValue >= (adTrapLowerThreshold +
			adTrapLowerHysteresis)."
	::= 3591

    adExceedLowerThresholdIncrease8 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 8 and
			adValue is greater equal
			the lower threshold plus the lower hysteresis
			after adExceedLowerThresholdDecrease is generated.
			namely, adValue >= (adTrapLowerThreshold +
			adTrapLowerHysteresis)."
	::= 3592

    adExceedLowerThresholdIncrease9 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 9 and
			adValue is greater equal
			the lower threshold plus the lower hysteresis
			after adExceedLowerThresholdDecrease is generated.
			namely, adValue >= (adTrapLowerThreshold +
			adTrapLowerHysteresis)."
	::= 3593

    adExceedLowerThresholdIncrease10 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 10 and
			adValue is greater equal
			the lower threshold plus the lower hysteresis
			after adExceedLowerThresholdDecrease is generated.
			namely, adValue >= (adTrapLowerThreshold +
			adTrapLowerHysteresis)."
	::= 3594

    adExceedLowerThresholdIncrease11 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 11 and
			adValue is greater equal
			the lower threshold plus the lower hysteresis
			after adExceedLowerThresholdDecrease is generated.
			namely, adValue >= (adTrapLowerThreshold +
			adTrapLowerHysteresis)."
	::= 3595

    adExceedLowerThresholdIncrease12 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 12 and
			adValue is greater equal
			the lower threshold plus the lower hysteresis
			after adExceedLowerThresholdDecrease is generated.
			namely, adValue >= (adTrapLowerThreshold +
			adTrapLowerHysteresis)."
	::= 3596

    adExceedLowerThresholdIncrease13 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 13 and
			adValue is greater equal
			the lower threshold plus the lower hysteresis
			after adExceedLowerThresholdDecrease is generated.
			namely, adValue >= (adTrapLowerThreshold +
			adTrapLowerHysteresis)."
	::= 3597

    adExceedLowerThresholdIncrease14 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 14 and
			adValue is greater equal
			the lower threshold plus the lower hysteresis
			after adExceedLowerThresholdDecrease is generated.
			namely, adValue >= (adTrapLowerThreshold +
			adTrapLowerHysteresis)."
	::= 3598

    adExceedLowerThresholdIncrease15 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 15 and
			adValue is greater equal
			the lower threshold plus the lower hysteresis
			after adExceedLowerThresholdDecrease is generated.
			namely, adValue >= (adTrapLowerThreshold +
			adTrapLowerHysteresis)."
	::= 3599

    adExceedLowerThresholdIncrease16 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 16 and
			adValue is greater equal
			the lower threshold plus the lower hysteresis
			after adExceedLowerThresholdDecrease is generated.
			namely, adValue >= (adTrapLowerThreshold +
			adTrapLowerHysteresis)."
	::= 3600

    adExceedLowerThresholdIncrease17 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 17 and
			adValue is greater equal
			the lower threshold plus the lower hysteresis
			after adExceedLowerThresholdDecrease is generated.
			namely, adValue >= (adTrapLowerThreshold +
			adTrapLowerHysteresis)."
	::= 3601

    adExceedLowerThresholdIncrease18 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 18 and
			adValue is greater equal
			the lower threshold plus the lower hysteresis
			after adExceedLowerThresholdDecrease is generated.
			namely, adValue >= (adTrapLowerThreshold +
			adTrapLowerHysteresis)."
	::= 3602

    adExceedLowerThresholdIncrease19 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 19 and
			adValue is greater equal
			the lower threshold plus the lower hysteresis
			after adExceedLowerThresholdDecrease is generated.
			namely, adValue >= (adTrapLowerThreshold +
			adTrapLowerHysteresis)."
	::= 3603

    adExceedLowerThresholdIncrease20 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 20 and
			adValue is greater equal
			the lower threshold plus the lower hysteresis
			after adExceedLowerThresholdDecrease is generated.
			namely, adValue >= (adTrapLowerThreshold +
			adTrapLowerHysteresis)."
	::= 3604

    adExceedLowerThresholdIncrease21 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 21 and
			adValue is greater equal
			the lower threshold plus the lower hysteresis
			after adExceedLowerThresholdDecrease is generated.
			namely, adValue >= (adTrapLowerThreshold +
			adTrapLowerHysteresis)."
	::= 3605

    adExceedLowerThresholdIncrease22 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 22 and
			adValue is greater equal
			the lower threshold plus the lower hysteresis
			after adExceedLowerThresholdDecrease is generated.
			namely, adValue >= (adTrapLowerThreshold +
			adTrapLowerHysteresis)."
	::= 3606

    adExceedLowerThresholdIncrease23 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 23 and
			adValue is greater equal
			the lower threshold plus the lower hysteresis
			after adExceedLowerThresholdDecrease is generated.
			namely, adValue >= (adTrapLowerThreshold +
			adTrapLowerHysteresis)."
	::= 3607

    adExceedLowerThresholdIncrease24 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 24 and
			adValue is greater equal
			the lower threshold plus the lower hysteresis
			after adExceedLowerThresholdDecrease is generated.
			namely, adValue >= (adTrapLowerThreshold +
			adTrapLowerHysteresis)."
	::= 3608

    adExceedLowerThresholdIncrease25 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 25 and
			adValue is greater equal
			the lower threshold plus the lower hysteresis
			after adExceedLowerThresholdDecrease is generated.
			namely, adValue >= (adTrapLowerThreshold +
			adTrapLowerHysteresis)."
	::= 3609

    adExceedLowerThresholdIncrease26 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 26 and
			adValue is greater equal
			the lower threshold plus the lower hysteresis
			after adExceedLowerThresholdDecrease is generated.
			namely, adValue >= (adTrapLowerThreshold +
			adTrapLowerHysteresis)."
	::= 3610

    adExceedLowerThresholdIncrease27 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 27 and
			adValue is greater equal
			the lower threshold plus the lower hysteresis
			after adExceedLowerThresholdDecrease is generated.
			namely, adValue >= (adTrapLowerThreshold +
			adTrapLowerHysteresis)."
	::= 3611

    adExceedLowerThresholdIncrease28 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 28 and
			adValue is greater equal
			the lower threshold plus the lower hysteresis
			after adExceedLowerThresholdDecrease is generated.
			namely, adValue >= (adTrapLowerThreshold +
			adTrapLowerHysteresis)."
	::= 3612

    adExceedLowerThresholdIncrease29 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 29 and
			adValue is greater equal
			the lower threshold plus the lower hysteresis
			after adExceedLowerThresholdDecrease is generated.
			namely, adValue >= (adTrapLowerThreshold +
			adTrapLowerHysteresis)."
	::= 3613

    adExceedLowerThresholdIncrease30 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 30 and
			adValue is greater equal
			the lower threshold plus the lower hysteresis
			after adExceedLowerThresholdDecrease is generated.
			namely, adValue >= (adTrapLowerThreshold +
			adTrapLowerHysteresis)."
	::= 3614

    adExceedLowerThresholdIncrease31 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 31 and
			adValue is greater equal
			the lower threshold plus the lower hysteresis
			after adExceedLowerThresholdDecrease is generated.
			namely, adValue >= (adTrapLowerThreshold +
			adTrapLowerHysteresis)."
	::= 3615

    adExceedLowerThresholdIncrease32 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 32 and
			adValue is greater equal
			the lower threshold plus the lower hysteresis
			after adExceedLowerThresholdDecrease is generated.
			namely, adValue >= (adTrapLowerThreshold +
			adTrapLowerHysteresis)."
	::= 3616

    adExceedLowerThresholdIncrease33 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 33 and
			adValue is greater equal
			the lower threshold plus the lower hysteresis
			after adExceedLowerThresholdDecrease is generated.
			namely, adValue >= (adTrapLowerThreshold +
			adTrapLowerHysteresis)."
	::= 3617

    adExceedLowerThresholdIncrease34 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 34 and
			adValue is greater equal
			the lower threshold plus the lower hysteresis
			after adExceedLowerThresholdDecrease is generated.
			namely, adValue >= (adTrapLowerThreshold +
			adTrapLowerHysteresis)."
	::= 3618

    adExceedLowerThresholdIncrease35 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 35 and
			adValue is greater equal
			the lower threshold plus the lower hysteresis
			after adExceedLowerThresholdDecrease is generated.
			namely, adValue >= (adTrapLowerThreshold +
			adTrapLowerHysteresis)."
	::= 3619

    adExceedLowerThresholdIncrease36 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 36 and
			adValue is greater equal
			the lower threshold plus the lower hysteresis
			after adExceedLowerThresholdDecrease is generated.
			namely, adValue >= (adTrapLowerThreshold +
			adTrapLowerHysteresis)."
	::= 3620

    adExceedLowerThresholdIncrease37 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 37 and
			adValue is greater equal
			the lower threshold plus the lower hysteresis
			after adExceedLowerThresholdDecrease is generated.
			namely, adValue >= (adTrapLowerThreshold +
			adTrapLowerHysteresis)."
	::= 3621

    adExceedLowerThresholdIncrease38 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 38 and
			adValue is greater equal
			the lower threshold plus the lower hysteresis
			after adExceedLowerThresholdDecrease is generated.
			namely, adValue >= (adTrapLowerThreshold +
			adTrapLowerHysteresis)."
	::= 3622

    adExceedLowerThresholdIncrease39 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 39 and
			adValue is greater equal
			the lower threshold plus the lower hysteresis
			after adExceedLowerThresholdDecrease is generated.
			namely, adValue >= (adTrapLowerThreshold +
			adTrapLowerHysteresis)."
	::= 3623

    adExceedLowerThresholdIncrease40 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 40 and
			adValue is greater equal
			the lower threshold plus the lower hysteresis
			after adExceedLowerThresholdDecrease is generated.
			namely, adValue >= (adTrapLowerThreshold +
			adTrapLowerHysteresis)."
	::= 3624

    adExceedLowerThresholdIncrease41 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 41 and
			adValue is greater equal
			the lower threshold plus the lower hysteresis
			after adExceedLowerThresholdDecrease is generated.
			namely, adValue >= (adTrapLowerThreshold +
			adTrapLowerHysteresis)."
	::= 3625

    adExceedLowerThresholdIncrease42 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 42 and
			adValue is greater equal
			the lower threshold plus the lower hysteresis
			after adExceedLowerThresholdDecrease is generated.
			namely, adValue >= (adTrapLowerThreshold +
			adTrapLowerHysteresis)."
	::= 3626

    adExceedLowerThresholdIncrease43 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 43 and
			adValue is greater equal
			the lower threshold plus the lower hysteresis
			after adExceedLowerThresholdDecrease is generated.
			namely, adValue >= (adTrapLowerThreshold +
			adTrapLowerHysteresis)."
	::= 3627

    adExceedLowerThresholdIncrease44 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 44 and
			adValue is greater equal
			the lower threshold plus the lower hysteresis
			after adExceedLowerThresholdDecrease is generated.
			namely, adValue >= (adTrapLowerThreshold +
			adTrapLowerHysteresis)."
	::= 3628

    adExceedLowerThresholdIncrease45 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 45 and
			adValue is greater equal
			the lower threshold plus the lower hysteresis
			after adExceedLowerThresholdDecrease is generated.
			namely, adValue >= (adTrapLowerThreshold +
			adTrapLowerHysteresis)."
	::= 3629

    adExceedLowerThresholdIncrease46 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 46 and
			adValue is greater equal
			the lower threshold plus the lower hysteresis
			after adExceedLowerThresholdDecrease is generated.
			namely, adValue >= (adTrapLowerThreshold +
			adTrapLowerHysteresis)."
	::= 3630

    adExceedLowerThresholdIncrease47 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 47 and
			adValue is greater equal
			the lower threshold plus the lower hysteresis
			after adExceedLowerThresholdDecrease is generated.
			namely, adValue >= (adTrapLowerThreshold +
			adTrapLowerHysteresis)."
	::= 3631

    adExceedLowerThresholdIncrease48 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 48 and
			adValue is greater equal
			the lower threshold plus the lower hysteresis
			after adExceedLowerThresholdDecrease is generated.
			namely, adValue >= (adTrapLowerThreshold +
			adTrapLowerHysteresis)."
	::= 3632

    adExceedLowerThresholdIncrease49 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 49 and
			adValue is greater equal
			the lower threshold plus the lower hysteresis
			after adExceedLowerThresholdDecrease is generated.
			namely, adValue >= (adTrapLowerThreshold +
			adTrapLowerHysteresis)."
	::= 3633

    adExceedLowerThresholdIncrease50 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 50 and
			adValue is greater equal
			the lower threshold plus the lower hysteresis
			after adExceedLowerThresholdDecrease is generated.
			namely, adValue >= (adTrapLowerThreshold +
			adTrapLowerHysteresis)."
	::= 3634

    adExceedLowerThresholdIncrease51 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 51 and
			adValue is greater equal
			the lower threshold plus the lower hysteresis
			after adExceedLowerThresholdDecrease is generated.
			namely, adValue >= (adTrapLowerThreshold +
			adTrapLowerHysteresis)."
	::= 3635

    adExceedLowerThresholdIncrease52 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 52 and
			adValue is greater equal
			the lower threshold plus the lower hysteresis
			after adExceedLowerThresholdDecrease is generated.
			namely, adValue >= (adTrapLowerThreshold +
			adTrapLowerHysteresis)."
	::= 3636

    adExceedLowerThresholdIncrease53 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 53 and
			adValue is greater equal
			the lower threshold plus the lower hysteresis
			after adExceedLowerThresholdDecrease is generated.
			namely, adValue >= (adTrapLowerThreshold +
			adTrapLowerHysteresis)."
	::= 3637

    adExceedLowerThresholdIncrease54 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 54 and
			adValue is greater equal
			the lower threshold plus the lower hysteresis
			after adExceedLowerThresholdDecrease is generated.
			namely, adValue >= (adTrapLowerThreshold +
			adTrapLowerHysteresis)."
	::= 3638

    adExceedLowerThresholdIncrease55 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 55 and
			adValue is greater equal
			the lower threshold plus the lower hysteresis
			after adExceedLowerThresholdDecrease is generated.
			namely, adValue >= (adTrapLowerThreshold +
			adTrapLowerHysteresis)."
	::= 3639

    adExceedLowerThresholdIncrease56 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 56 and
			adValue is greater equal
			the lower threshold plus the lower hysteresis
			after adExceedLowerThresholdDecrease is generated.
			namely, adValue >= (adTrapLowerThreshold +
			adTrapLowerHysteresis)."
	::= 3640

    adExceedLowerThresholdIncrease57 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 57 and
			adValue is greater equal
			the lower threshold plus the lower hysteresis
			after adExceedLowerThresholdDecrease is generated.
			namely, adValue >= (adTrapLowerThreshold +
			adTrapLowerHysteresis)."
	::= 3641

    adExceedLowerThresholdIncrease58 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 58 and
			adValue is greater equal
			the lower threshold plus the lower hysteresis
			after adExceedLowerThresholdDecrease is generated.
			namely, adValue >= (adTrapLowerThreshold +
			adTrapLowerHysteresis)."
	::= 3642

    adExceedLowerThresholdIncrease59 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 59 and
			adValue is greater equal
			the lower threshold plus the lower hysteresis
			after adExceedLowerThresholdDecrease is generated.
			namely, adValue >= (adTrapLowerThreshold +
			adTrapLowerHysteresis)."
	::= 3643

    adExceedLowerThresholdIncrease60 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 60 and
			adValue is greater equal
			the lower threshold plus the lower hysteresis
			after adExceedLowerThresholdDecrease is generated.
			namely, adValue >= (adTrapLowerThreshold +
			adTrapLowerHysteresis)."
	::= 3644

    adExceedLowerThresholdIncrease61 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 61 and
			adValue is greater equal
			the lower threshold plus the lower hysteresis
			after adExceedLowerThresholdDecrease is generated.
			namely, adValue >= (adTrapLowerThreshold +
			adTrapLowerHysteresis)."
	::= 3645

    adExceedLowerThresholdIncrease62 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 62 and
			adValue is greater equal
			the lower threshold plus the lower hysteresis
			after adExceedLowerThresholdDecrease is generated.
			namely, adValue >= (adTrapLowerThreshold +
			adTrapLowerHysteresis)."
	::= 3646

    adExceedLowerThresholdIncrease63 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 63 and
			adValue is greater equal
			the lower threshold plus the lower hysteresis
			after adExceedLowerThresholdDecrease is generated.
			namely, adValue >= (adTrapLowerThreshold +
			adTrapLowerHysteresis)."
	::= 3647

    adExceedLowerThresholdIncrease64 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 64 and
			adValue is greater equal
			the lower threshold plus the lower hysteresis
			after adExceedLowerThresholdDecrease is generated.
			namely, adValue >= (adTrapLowerThreshold +
			adTrapLowerHysteresis)."
	::= 3648

    adExceedLowerThresholdIncrease65 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 65 and
			adValue is greater equal
			the lower threshold plus the lower hysteresis
			after adExceedLowerThresholdDecrease is generated.
			namely, adValue >= (adTrapLowerThreshold +
			adTrapLowerHysteresis)."
	::= 3649

    adExceedLowerThresholdIncrease66 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 66 and
			adValue is greater equal
			the lower threshold plus the lower hysteresis
			after adExceedLowerThresholdDecrease is generated.
			namely, adValue >= (adTrapLowerThreshold +
			adTrapLowerHysteresis)."
	::= 3650

    adExceedLowerThresholdIncrease67 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 67 and
			adValue is greater equal
			the lower threshold plus the lower hysteresis
			after adExceedLowerThresholdDecrease is generated.
			namely, adValue >= (adTrapLowerThreshold +
			adTrapLowerHysteresis)."
	::= 3651

    adExceedLowerThresholdIncrease68 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 68 and
			adValue is greater equal
			the lower threshold plus the lower hysteresis
			after adExceedLowerThresholdDecrease is generated.
			namely, adValue >= (adTrapLowerThreshold +
			adTrapLowerHysteresis)."
	::= 3652

    adExceedLowerThresholdIncrease69 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 69 and
			adValue is greater equal
			the lower threshold plus the lower hysteresis
			after adExceedLowerThresholdDecrease is generated.
			namely, adValue >= (adTrapLowerThreshold +
			adTrapLowerHysteresis)."
	::= 3653

    adExceedLowerThresholdIncrease70 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 70 and
			adValue is greater equal
			the lower threshold plus the lower hysteresis
			after adExceedLowerThresholdDecrease is generated.
			namely, adValue >= (adTrapLowerThreshold +
			adTrapLowerHysteresis)."
	::= 3654

    adExceedLowerThresholdIncrease71 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 71 and
			adValue is greater equal
			the lower threshold plus the lower hysteresis
			after adExceedLowerThresholdDecrease is generated.
			namely, adValue >= (adTrapLowerThreshold +
			adTrapLowerHysteresis)."
	::= 3655

    adExceedLowerThresholdIncrease72 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 72 and
			adValue is greater equal
			the lower threshold plus the lower hysteresis
			after adExceedLowerThresholdDecrease is generated.
			namely, adValue >= (adTrapLowerThreshold +
			adTrapLowerHysteresis)."
	::= 3656

    adExceedLowerThresholdIncrease73 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 73 and
			adValue is greater equal
			the lower threshold plus the lower hysteresis
			after adExceedLowerThresholdDecrease is generated.
			namely, adValue >= (adTrapLowerThreshold +
			adTrapLowerHysteresis)."
	::= 3657

    adExceedLowerThresholdIncrease74 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 74 and
			adValue is greater equal
			the lower threshold plus the lower hysteresis
			after adExceedLowerThresholdDecrease is generated.
			namely, adValue >= (adTrapLowerThreshold +
			adTrapLowerHysteresis)."
	::= 3658

    adExceedLowerThresholdIncrease75 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 75 and
			adValue is greater equal
			the lower threshold plus the lower hysteresis
			after adExceedLowerThresholdDecrease is generated.
			namely, adValue >= (adTrapLowerThreshold +
			adTrapLowerHysteresis)."
	::= 3659

    adExceedLowerThresholdIncrease76 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 76 and
			adValue is greater equal
			the lower threshold plus the lower hysteresis
			after adExceedLowerThresholdDecrease is generated.
			namely, adValue >= (adTrapLowerThreshold +
			adTrapLowerHysteresis)."
	::= 3660

    adExceedLowerThresholdIncrease77 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 77 and
			adValue is greater equal
			the lower threshold plus the lower hysteresis
			after adExceedLowerThresholdDecrease is generated.
			namely, adValue >= (adTrapLowerThreshold +
			adTrapLowerHysteresis)."
	::= 3661

    adExceedLowerThresholdIncrease78 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 78 and
			adValue is greater equal
			the lower threshold plus the lower hysteresis
			after adExceedLowerThresholdDecrease is generated.
			namely, adValue >= (adTrapLowerThreshold +
			adTrapLowerHysteresis)."
	::= 3662

    adExceedLowerThresholdIncrease79 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 79 and
			adValue is greater equal
			the lower threshold plus the lower hysteresis
			after adExceedLowerThresholdDecrease is generated.
			namely, adValue >= (adTrapLowerThreshold +
			adTrapLowerHysteresis)."
	::= 3663

    adExceedLowerThresholdIncrease80 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 80 and
			adValue is greater equal
			the lower threshold plus the lower hysteresis
			after adExceedLowerThresholdDecrease is generated.
			namely, adValue >= (adTrapLowerThreshold +
			adTrapLowerHysteresis)."
	::= 3664

    adExceedLowerThresholdIncrease81 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 81 and
			adValue is greater equal
			the lower threshold plus the lower hysteresis
			after adExceedLowerThresholdDecrease is generated.
			namely, adValue >= (adTrapLowerThreshold +
			adTrapLowerHysteresis)."
	::= 3665

    adExceedLowerThresholdIncrease82 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 82 and
			adValue is greater equal
			the lower threshold plus the lower hysteresis
			after adExceedLowerThresholdDecrease is generated.
			namely, adValue >= (adTrapLowerThreshold +
			adTrapLowerHysteresis)."
	::= 3666

    adExceedLowerThresholdIncrease83 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 83 and
			adValue is greater equal
			the lower threshold plus the lower hysteresis
			after adExceedLowerThresholdDecrease is generated.
			namely, adValue >= (adTrapLowerThreshold +
			adTrapLowerHysteresis)."
	::= 3667

    adExceedLowerThresholdIncrease84 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 84 and
			adValue is greater equal
			the lower threshold plus the lower hysteresis
			after adExceedLowerThresholdDecrease is generated.
			namely, adValue >= (adTrapLowerThreshold +
			adTrapLowerHysteresis)."
	::= 3668

    adExceedLowerThresholdIncrease85 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 85 and
			adValue is greater equal
			the lower threshold plus the lower hysteresis
			after adExceedLowerThresholdDecrease is generated.
			namely, adValue >= (adTrapLowerThreshold +
			adTrapLowerHysteresis)."
	::= 3669

    adExceedLowerThresholdIncrease86 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 86 and
			adValue is greater equal
			the lower threshold plus the lower hysteresis
			after adExceedLowerThresholdDecrease is generated.
			namely, adValue >= (adTrapLowerThreshold +
			adTrapLowerHysteresis)."
	::= 3670

    adExceedLowerThresholdIncrease87 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 87 and
			adValue is greater equal
			the lower threshold plus the lower hysteresis
			after adExceedLowerThresholdDecrease is generated.
			namely, adValue >= (adTrapLowerThreshold +
			adTrapLowerHysteresis)."
	::= 3671

    adExceedLowerThresholdIncrease88 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 88 and
			adValue is greater equal
			the lower threshold plus the lower hysteresis
			after adExceedLowerThresholdDecrease is generated.
			namely, adValue >= (adTrapLowerThreshold +
			adTrapLowerHysteresis)."
	::= 3672

    adExceedLowerThresholdIncrease89 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 89 and
			adValue is greater equal
			the lower threshold plus the lower hysteresis
			after adExceedLowerThresholdDecrease is generated.
			namely, adValue >= (adTrapLowerThreshold +
			adTrapLowerHysteresis)."
	::= 3673

    adExceedLowerThresholdIncrease90 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 90 and
			adValue is greater equal
			the lower threshold plus the lower hysteresis
			after adExceedLowerThresholdDecrease is generated.
			namely, adValue >= (adTrapLowerThreshold +
			adTrapLowerHysteresis)."
	::= 3674

    adExceedLowerThresholdIncrease91 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 91 and
			adValue is greater equal
			the lower threshold plus the lower hysteresis
			after adExceedLowerThresholdDecrease is generated.
			namely, adValue >= (adTrapLowerThreshold +
			adTrapLowerHysteresis)."
	::= 3675

    adExceedLowerThresholdIncrease92 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 92 and
			adValue is greater equal
			the lower threshold plus the lower hysteresis
			after adExceedLowerThresholdDecrease is generated.
			namely, adValue >= (adTrapLowerThreshold +
			adTrapLowerHysteresis)."
	::= 3676

    adExceedLowerThresholdIncrease93 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 93 and
			adValue is greater equal
			the lower threshold plus the lower hysteresis
			after adExceedLowerThresholdDecrease is generated.
			namely, adValue >= (adTrapLowerThreshold +
			adTrapLowerHysteresis)."
	::= 3677

    adExceedLowerThresholdIncrease94 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 94 and
			adValue is greater equal
			the lower threshold plus the lower hysteresis
			after adExceedLowerThresholdDecrease is generated.
			namely, adValue >= (adTrapLowerThreshold +
			adTrapLowerHysteresis)."
	::= 3678

    adExceedLowerThresholdIncrease95 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 95 and
			adValue is greater equal
			the lower threshold plus the lower hysteresis
			after adExceedLowerThresholdDecrease is generated.
			namely, adValue >= (adTrapLowerThreshold +
			adTrapLowerHysteresis)."
	::= 3679

    adExceedLowerThresholdIncrease96 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 96 and
			adValue is greater equal
			the lower threshold plus the lower hysteresis
			after adExceedLowerThresholdDecrease is generated.
			namely, adValue >= (adTrapLowerThreshold +
			adTrapLowerHysteresis)."
	::= 3680

    adExceedLowerThresholdIncrease97 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 97 and
			adValue is greater equal
			the lower threshold plus the lower hysteresis
			after adExceedLowerThresholdDecrease is generated.
			namely, adValue >= (adTrapLowerThreshold +
			adTrapLowerHysteresis)."
	::= 3681

    adExceedLowerThresholdIncrease98 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 98 and
			adValue is greater equal
			the lower threshold plus the lower hysteresis
			after adExceedLowerThresholdDecrease is generated.
			namely, adValue >= (adTrapLowerThreshold +
			adTrapLowerHysteresis)."
	::= 3682

    adExceedLowerThresholdIncrease99 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 99 and
			adValue is greater equal
			the lower threshold plus the lower hysteresis
			after adExceedLowerThresholdDecrease is generated.
			namely, adValue >= (adTrapLowerThreshold +
			adTrapLowerHysteresis)."
	::= 3683

    adExceedLowerThresholdIncrease100 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 100 and
			adValue is greater equal
			the lower threshold plus the lower hysteresis
			after adExceedLowerThresholdDecrease is generated.
			namely, adValue >= (adTrapLowerThreshold +
			adTrapLowerHysteresis)."
	::= 3684

    adExceedLowerThresholdIncrease101 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 101 and
			adValue is greater equal
			the lower threshold plus the lower hysteresis
			after adExceedLowerThresholdDecrease is generated.
			namely, adValue >= (adTrapLowerThreshold +
			adTrapLowerHysteresis)."
	::= 3685

    adExceedLowerThresholdIncrease102 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 102 and
			adValue is greater equal
			the lower threshold plus the lower hysteresis
			after adExceedLowerThresholdDecrease is generated.
			namely, adValue >= (adTrapLowerThreshold +
			adTrapLowerHysteresis)."
	::= 3686

    adExceedLowerThresholdIncrease103 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 103 and
			adValue is greater equal
			the lower threshold plus the lower hysteresis
			after adExceedLowerThresholdDecrease is generated.
			namely, adValue >= (adTrapLowerThreshold +
			adTrapLowerHysteresis)."
	::= 3687

    adExceedLowerThresholdIncrease104 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 104 and
			adValue is greater equal
			the lower threshold plus the lower hysteresis
			after adExceedLowerThresholdDecrease is generated.
			namely, adValue >= (adTrapLowerThreshold +
			adTrapLowerHysteresis)."
	::= 3688

    adExceedLowerThresholdIncrease105 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 105 and
			adValue is greater equal
			the lower threshold plus the lower hysteresis
			after adExceedLowerThresholdDecrease is generated.
			namely, adValue >= (adTrapLowerThreshold +
			adTrapLowerHysteresis)."
	::= 3689

    adExceedLowerThresholdIncrease106 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 106 and
			adValue is greater equal
			the lower threshold plus the lower hysteresis
			after adExceedLowerThresholdDecrease is generated.
			namely, adValue >= (adTrapLowerThreshold +
			adTrapLowerHysteresis)."
	::= 3690

    adExceedLowerThresholdIncrease107 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 107 and
			adValue is greater equal
			the lower threshold plus the lower hysteresis
			after adExceedLowerThresholdDecrease is generated.
			namely, adValue >= (adTrapLowerThreshold +
			adTrapLowerHysteresis)."
	::= 3691

    adExceedLowerThresholdIncrease108 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 108 and
			adValue is greater equal
			the lower threshold plus the lower hysteresis
			after adExceedLowerThresholdDecrease is generated.
			namely, adValue >= (adTrapLowerThreshold +
			adTrapLowerHysteresis)."
	::= 3692

    adExceedLowerThresholdIncrease109 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 109 and
			adValue is greater equal
			the lower threshold plus the lower hysteresis
			after adExceedLowerThresholdDecrease is generated.
			namely, adValue >= (adTrapLowerThreshold +
			adTrapLowerHysteresis)."
	::= 3693

    adExceedLowerThresholdIncrease110 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 110 and
			adValue is greater equal
			the lower threshold plus the lower hysteresis
			after adExceedLowerThresholdDecrease is generated.
			namely, adValue >= (adTrapLowerThreshold +
			adTrapLowerHysteresis)."
	::= 3694

    adExceedLowerThresholdIncrease111 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 111 and
			adValue is greater equal
			the lower threshold plus the lower hysteresis
			after adExceedLowerThresholdDecrease is generated.
			namely, adValue >= (adTrapLowerThreshold +
			adTrapLowerHysteresis)."
	::= 3695

    adExceedLowerThresholdIncrease112 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 112 and
			adValue is greater equal
			the lower threshold plus the lower hysteresis
			after adExceedLowerThresholdDecrease is generated.
			namely, adValue >= (adTrapLowerThreshold +
			adTrapLowerHysteresis)."
	::= 3696

    adExceedLowerThresholdIncrease113 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 113 and
			adValue is greater equal
			the lower threshold plus the lower hysteresis
			after adExceedLowerThresholdDecrease is generated.
			namely, adValue >= (adTrapLowerThreshold +
			adTrapLowerHysteresis)."
	::= 3697

    adExceedLowerThresholdIncrease114 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 114 and
			adValue is greater equal
			the lower threshold plus the lower hysteresis
			after adExceedLowerThresholdDecrease is generated.
			namely, adValue >= (adTrapLowerThreshold +
			adTrapLowerHysteresis)."
	::= 3698

    adExceedLowerThresholdIncrease115 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 115 and
			adValue is greater equal
			the lower threshold plus the lower hysteresis
			after adExceedLowerThresholdDecrease is generated.
			namely, adValue >= (adTrapLowerThreshold +
			adTrapLowerHysteresis)."
	::= 3699

    adExceedLowerThresholdIncrease116 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 116 and
			adValue is greater equal
			the lower threshold plus the lower hysteresis
			after adExceedLowerThresholdDecrease is generated.
			namely, adValue >= (adTrapLowerThreshold +
			adTrapLowerHysteresis)."
	::= 3700

    adExceedLowerThresholdIncrease117 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 117 and
			adValue is greater equal
			the lower threshold plus the lower hysteresis
			after adExceedLowerThresholdDecrease is generated.
			namely, adValue >= (adTrapLowerThreshold +
			adTrapLowerHysteresis)."
	::= 3701

    adExceedLowerThresholdIncrease118 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 118 and
			adValue is greater equal
			the lower threshold plus the lower hysteresis
			after adExceedLowerThresholdDecrease is generated.
			namely, adValue >= (adTrapLowerThreshold +
			adTrapLowerHysteresis)."
	::= 3702

    adExceedLowerThresholdIncrease119 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 119 and
			adValue is greater equal
			the lower threshold plus the lower hysteresis
			after adExceedLowerThresholdDecrease is generated.
			namely, adValue >= (adTrapLowerThreshold +
			adTrapLowerHysteresis)."
	::= 3703

    adExceedLowerThresholdIncrease120 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 120 and
			adValue is greater equal
			the lower threshold plus the lower hysteresis
			after adExceedLowerThresholdDecrease is generated.
			namely, adValue >= (adTrapLowerThreshold +
			adTrapLowerHysteresis)."
	::= 3704

    adExceedLowerThresholdIncrease121 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 121 and
			adValue is greater equal
			the lower threshold plus the lower hysteresis
			after adExceedLowerThresholdDecrease is generated.
			namely, adValue >= (adTrapLowerThreshold +
			adTrapLowerHysteresis)."
	::= 3705

    adExceedLowerThresholdIncrease122 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 122 and
			adValue is greater equal
			the lower threshold plus the lower hysteresis
			after adExceedLowerThresholdDecrease is generated.
			namely, adValue >= (adTrapLowerThreshold +
			adTrapLowerHysteresis)."
	::= 3706

    adExceedLowerThresholdIncrease123 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 123 and
			adValue is greater equal
			the lower threshold plus the lower hysteresis
			after adExceedLowerThresholdDecrease is generated.
			namely, adValue >= (adTrapLowerThreshold +
			adTrapLowerHysteresis)."
	::= 3707

    adExceedLowerThresholdIncrease124 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 124 and
			adValue is greater equal
			the lower threshold plus the lower hysteresis
			after adExceedLowerThresholdDecrease is generated.
			namely, adValue >= (adTrapLowerThreshold +
			adTrapLowerHysteresis)."
	::= 3708

    adExceedLowerThresholdIncrease125 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 125 and
			adValue is greater equal
			the lower threshold plus the lower hysteresis
			after adExceedLowerThresholdDecrease is generated.
			namely, adValue >= (adTrapLowerThreshold +
			adTrapLowerHysteresis)."
	::= 3709

    adExceedLowerThresholdIncrease126 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 126 and
			adValue is greater equal
			the lower threshold plus the lower hysteresis
			after adExceedLowerThresholdDecrease is generated.
			namely, adValue >= (adTrapLowerThreshold +
			adTrapLowerHysteresis)."
	::= 3710

    adExceedLowerThresholdIncrease127 TRAP-TYPE
	ENTERPRISE	network-device
	VARIABLES	{ adValue, adminDateAndTime, adminNDTrapSeqNo,
			  adIndex, adType, adValueOnlyString,
			  adTrapCurrentStatus }
	DESCRIPTION	"This trap is generated when set
			adExLoThresholdIncreaseTrapID equal 127 and
			adValue is greater equal
			the lower threshold plus the lower hysteresis
			after adExceedLowerThresholdDecrease is generated.
			namely, adValue >= (adTrapLowerThreshold +
			adTrapLowerHysteresis)."
	::= 3711

    adExceedLowerThresholdDecrease1 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 1 and
			adValue is less than the lower threshold."
	::= 4097

    adExceedLowerThresholdDecrease2 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 2 and
			adValue is less than the lower threshold."
	::= 4098

    adExceedLowerThresholdDecrease3 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 3 and
			adValue is less than the lower threshold."
	::= 4099

    adExceedLowerThresholdDecrease4 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 4 and
			adValue is less than the lower threshold."
	::= 4100

    adExceedLowerThresholdDecrease5 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 5 and
			adValue is less than the lower threshold."
	::= 4101

    adExceedLowerThresholdDecrease6 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 6 and
			adValue is less than the lower threshold."
	::= 4102

    adExceedLowerThresholdDecrease7 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 7 and
			adValue is less than the lower threshold."
	::= 4103

    adExceedLowerThresholdDecrease8 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 8 and
			adValue is less than the lower threshold."
	::= 4104

    adExceedLowerThresholdDecrease9 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 9 and
			adValue is less than the lower threshold."
	::= 4105

    adExceedLowerThresholdDecrease10 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 10 and
			adValue is less than the lower threshold."
	::= 4106

    adExceedLowerThresholdDecrease11 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 11 and
			adValue is less than the lower threshold."
	::= 4107

    adExceedLowerThresholdDecrease12 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 12 and
			adValue is less than the lower threshold."
	::= 4108

    adExceedLowerThresholdDecrease13 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 13 and
			adValue is less than the lower threshold."
	::= 4109

    adExceedLowerThresholdDecrease14 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 14 and
			adValue is less than the lower threshold."
	::= 4110

    adExceedLowerThresholdDecrease15 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 15 and
			adValue is less than the lower threshold."
	::= 4111

    adExceedLowerThresholdDecrease16 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 16 and
			adValue is less than the lower threshold."
	::= 4112

    adExceedLowerThresholdDecrease17 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 17 and
			adValue is less than the lower threshold."
	::= 4113

    adExceedLowerThresholdDecrease18 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 18 and
			adValue is less than the lower threshold."
	::= 4114

    adExceedLowerThresholdDecrease19 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 19 and
			adValue is less than the lower threshold."
	::= 4115

    adExceedLowerThresholdDecrease20 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 20 and
			adValue is less than the lower threshold."
	::= 4116

    adExceedLowerThresholdDecrease21 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 21 and
			adValue is less than the lower threshold."
	::= 4117

    adExceedLowerThresholdDecrease22 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 22 and
			adValue is less than the lower threshold."
	::= 4118

    adExceedLowerThresholdDecrease23 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 23 and
			adValue is less than the lower threshold."
	::= 4119

    adExceedLowerThresholdDecrease24 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 24 and
			adValue is less than the lower threshold."
	::= 4120

    adExceedLowerThresholdDecrease25 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 25 and
			adValue is less than the lower threshold."
	::= 4121

    adExceedLowerThresholdDecrease26 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 26 and
			adValue is less than the lower threshold."
	::= 4122

    adExceedLowerThresholdDecrease27 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 27 and
			adValue is less than the lower threshold."
	::= 4123

    adExceedLowerThresholdDecrease28 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 28 and
			adValue is less than the lower threshold."
	::= 4124

    adExceedLowerThresholdDecrease29 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 29 and
			adValue is less than the lower threshold."
	::= 4125

    adExceedLowerThresholdDecrease30 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 30 and
			adValue is less than the lower threshold."
	::= 4126

    adExceedLowerThresholdDecrease31 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 31 and
			adValue is less than the lower threshold."
	::= 4127

    adExceedLowerThresholdDecrease32 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 32 and
			adValue is less than the lower threshold."
	::= 4128

    adExceedLowerThresholdDecrease33 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 33 and
			adValue is less than the lower threshold."
	::= 4129

    adExceedLowerThresholdDecrease34 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 34 and
			adValue is less than the lower threshold."
	::= 4130

    adExceedLowerThresholdDecrease35 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 35 and
			adValue is less than the lower threshold."
	::= 4131

    adExceedLowerThresholdDecrease36 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 36 and
			adValue is less than the lower threshold."
	::= 4132

    adExceedLowerThresholdDecrease37 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 37 and
			adValue is less than the lower threshold."
	::= 4133

    adExceedLowerThresholdDecrease38 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 38 and
			adValue is less than the lower threshold."
	::= 4134

    adExceedLowerThresholdDecrease39 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 39 and
			adValue is less than the lower threshold."
	::= 4135

    adExceedLowerThresholdDecrease40 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 40 and
			adValue is less than the lower threshold."
	::= 4136

    adExceedLowerThresholdDecrease41 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 41 and
			adValue is less than the lower threshold."
	::= 4137

    adExceedLowerThresholdDecrease42 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 42 and
			adValue is less than the lower threshold."
	::= 4138

    adExceedLowerThresholdDecrease43 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 43 and
			adValue is less than the lower threshold."
	::= 4139

    adExceedLowerThresholdDecrease44 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 44 and
			adValue is less than the lower threshold."
	::= 4140

    adExceedLowerThresholdDecrease45 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 45 and
			adValue is less than the lower threshold."
	::= 4141

    adExceedLowerThresholdDecrease46 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 46 and
			adValue is less than the lower threshold."
	::= 4142

    adExceedLowerThresholdDecrease47 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 47 and
			adValue is less than the lower threshold."
	::= 4143

    adExceedLowerThresholdDecrease48 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 48 and
			adValue is less than the lower threshold."
	::= 4144

    adExceedLowerThresholdDecrease49 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 49 and
			adValue is less than the lower threshold."
	::= 4145

    adExceedLowerThresholdDecrease50 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 50 and
			adValue is less than the lower threshold."
	::= 4146

    adExceedLowerThresholdDecrease51 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 51 and
			adValue is less than the lower threshold."
	::= 4147

    adExceedLowerThresholdDecrease52 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 52 and
			adValue is less than the lower threshold."
	::= 4148

    adExceedLowerThresholdDecrease53 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 53 and
			adValue is less than the lower threshold."
	::= 4149

    adExceedLowerThresholdDecrease54 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 54 and
			adValue is less than the lower threshold."
	::= 4150

    adExceedLowerThresholdDecrease55 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 55 and
			adValue is less than the lower threshold."
	::= 4151

    adExceedLowerThresholdDecrease56 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 56 and
			adValue is less than the lower threshold."
	::= 4152

    adExceedLowerThresholdDecrease57 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 57 and
			adValue is less than the lower threshold."
	::= 4153

    adExceedLowerThresholdDecrease58 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 58 and
			adValue is less than the lower threshold."
	::= 4154

    adExceedLowerThresholdDecrease59 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 59 and
			adValue is less than the lower threshold."
	::= 4155

    adExceedLowerThresholdDecrease60 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 60 and
			adValue is less than the lower threshold."
	::= 4156

    adExceedLowerThresholdDecrease61 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 61 and
			adValue is less than the lower threshold."
	::= 4157

    adExceedLowerThresholdDecrease62 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 62 and
			adValue is less than the lower threshold."
	::= 4158

    adExceedLowerThresholdDecrease63 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 63 and
			adValue is less than the lower threshold."
	::= 4159

    adExceedLowerThresholdDecrease64 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 64 and
			adValue is less than the lower threshold."
	::= 4160

    adExceedLowerThresholdDecrease65 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 65 and
			adValue is less than the lower threshold."
	::= 4161

    adExceedLowerThresholdDecrease66 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 66 and
			adValue is less than the lower threshold."
	::= 4162

    adExceedLowerThresholdDecrease67 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 67 and
			adValue is less than the lower threshold."
	::= 4163

    adExceedLowerThresholdDecrease68 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 68 and
			adValue is less than the lower threshold."
	::= 4164

    adExceedLowerThresholdDecrease69 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 69 and
			adValue is less than the lower threshold."
	::= 4165

    adExceedLowerThresholdDecrease70 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 70 and
			adValue is less than the lower threshold."
	::= 4166

    adExceedLowerThresholdDecrease71 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 71 and
			adValue is less than the lower threshold."
	::= 4167

    adExceedLowerThresholdDecrease72 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 72 and
			adValue is less than the lower threshold."
	::= 4168

    adExceedLowerThresholdDecrease73 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 73 and
			adValue is less than the lower threshold."
	::= 4169

    adExceedLowerThresholdDecrease74 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 74 and
			adValue is less than the lower threshold."
	::= 4170

    adExceedLowerThresholdDecrease75 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 75 and
			adValue is less than the lower threshold."
	::= 4171

    adExceedLowerThresholdDecrease76 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 76 and
			adValue is less than the lower threshold."
	::= 4172

    adExceedLowerThresholdDecrease77 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 77 and
			adValue is less than the lower threshold."
	::= 4173

    adExceedLowerThresholdDecrease78 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 78 and
			adValue is less than the lower threshold."
	::= 4174

    adExceedLowerThresholdDecrease79 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 79 and
			adValue is less than the lower threshold."
	::= 4175

    adExceedLowerThresholdDecrease80 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 80 and
			adValue is less than the lower threshold."
	::= 4176

    adExceedLowerThresholdDecrease81 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 81 and
			adValue is less than the lower threshold."
	::= 4177

    adExceedLowerThresholdDecrease82 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 82 and
			adValue is less than the lower threshold."
	::= 4178

    adExceedLowerThresholdDecrease83 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 83 and
			adValue is less than the lower threshold."
	::= 4179

    adExceedLowerThresholdDecrease84 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 84 and
			adValue is less than the lower threshold."
	::= 4180

    adExceedLowerThresholdDecrease85 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 85 and
			adValue is less than the lower threshold."
	::= 4181

    adExceedLowerThresholdDecrease86 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 86 and
			adValue is less than the lower threshold."
	::= 4182

    adExceedLowerThresholdDecrease87 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 87 and
			adValue is less than the lower threshold."
	::= 4183

    adExceedLowerThresholdDecrease88 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 88 and
			adValue is less than the lower threshold."
	::= 4184

    adExceedLowerThresholdDecrease89 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 89 and
			adValue is less than the lower threshold."
	::= 4185

    adExceedLowerThresholdDecrease90 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 90 and
			adValue is less than the lower threshold."
	::= 4186

    adExceedLowerThresholdDecrease91 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 91 and
			adValue is less than the lower threshold."
	::= 4187

    adExceedLowerThresholdDecrease92 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 92 and
			adValue is less than the lower threshold."
	::= 4188

    adExceedLowerThresholdDecrease93 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 93 and
			adValue is less than the lower threshold."
	::= 4189

    adExceedLowerThresholdDecrease94 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 94 and
			adValue is less than the lower threshold."
	::= 4190

    adExceedLowerThresholdDecrease95 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 95 and
			adValue is less than the lower threshold."
	::= 4191

    adExceedLowerThresholdDecrease96 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 96 and
			adValue is less than the lower threshold."
	::= 4192

    adExceedLowerThresholdDecrease97 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 97 and
			adValue is less than the lower threshold."
	::= 4193

    adExceedLowerThresholdDecrease98 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 98 and
			adValue is less than the lower threshold."
	::= 4194

    adExceedLowerThresholdDecrease99 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 99 and
			adValue is less than the lower threshold."
	::= 4195

    adExceedLowerThresholdDecrease100 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 100 and
			adValue is less than the lower threshold."
	::= 4196

    adExceedLowerThresholdDecrease101 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 101 and
			adValue is less than the lower threshold."
	::= 4197

    adExceedLowerThresholdDecrease102 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 102 and
			adValue is less than the lower threshold."
	::= 4198

    adExceedLowerThresholdDecrease103 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 103 and
			adValue is less than the lower threshold."
	::= 4199

    adExceedLowerThresholdDecrease104 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 104 and
			adValue is less than the lower threshold."
	::= 4200

    adExceedLowerThresholdDecrease105 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 105 and
			adValue is less than the lower threshold."
	::= 4201

    adExceedLowerThresholdDecrease106 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 106 and
			adValue is less than the lower threshold."
	::= 4202

    adExceedLowerThresholdDecrease107 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 107 and
			adValue is less than the lower threshold."
	::= 4203

    adExceedLowerThresholdDecrease108 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 108 and
			adValue is less than the lower threshold."
	::= 4204

    adExceedLowerThresholdDecrease109 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 109 and
			adValue is less than the lower threshold."
	::= 4205

    adExceedLowerThresholdDecrease110 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 110 and
			adValue is less than the lower threshold."
	::= 4206

    adExceedLowerThresholdDecrease111 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 111 and
			adValue is less than the lower threshold."
	::= 4207

    adExceedLowerThresholdDecrease112 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 112 and
			adValue is less than the lower threshold."
	::= 4208

    adExceedLowerThresholdDecrease113 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 113 and
			adValue is less than the lower threshold."
	::= 4209

    adExceedLowerThresholdDecrease114 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 114 and
			adValue is less than the lower threshold."
	::= 4210

    adExceedLowerThresholdDecrease115 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 115 and
			adValue is less than the lower threshold."
	::= 4211

    adExceedLowerThresholdDecrease116 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 116 and
			adValue is less than the lower threshold."
	::= 4212

    adExceedLowerThresholdDecrease117 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 117 and
			adValue is less than the lower threshold."
	::= 4213

    adExceedLowerThresholdDecrease118 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 118 and
			adValue is less than the lower threshold."
	::= 4214

    adExceedLowerThresholdDecrease119 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 119 and
			adValue is less than the lower threshold."
	::= 4215

    adExceedLowerThresholdDecrease120 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 120 and
			adValue is less than the lower threshold."
	::= 4216

    adExceedLowerThresholdDecrease121 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 121 and
			adValue is less than the lower threshold."
	::= 4217

    adExceedLowerThresholdDecrease122 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 122 and
			adValue is less than the lower threshold."
	::= 4218

    adExceedLowerThresholdDecrease123 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 123 and
			adValue is less than the lower threshold."
	::= 4219

    adExceedLowerThresholdDecrease124 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 124 and
			adValue is less than the lower threshold."
	::= 4220

    adExceedLowerThresholdDecrease125 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 125 and
			adValue is less than the lower threshold."
	::= 4221

    adExceedLowerThresholdDecrease126 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 126 and
			adValue is less than the lower threshold."
	::= 4222

    adExceedLowerThresholdDecrease127 TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdDecreaseTrapID equal 127 and
			adValue is less than the lower threshold."
	::= 4223

    adExceedingLowerThreshold1	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 1 and
			until adExceedLowerThresholdDecrease is generated after
			adExceedLowerThresholdIncrease is generated."
	::= 4609

    adExceedingLowerThreshold2	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 2 and
			until adExceedLowerThresholdDecrease is generated after
			adExceedLowerThresholdIncrease is generated."
	::= 4610

    adExceedingLowerThreshold3	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 3 and
			until adExceedLowerThresholdDecrease is generated after
			adExceedLowerThresholdIncrease is generated."
	::= 4611

    adExceedingLowerThreshold4	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 4 and
			until adExceedLowerThresholdDecrease is generated after
			adExceedLowerThresholdIncrease is generated."
	::= 4612

    adExceedingLowerThreshold5	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 5 and
			until adExceedLowerThresholdDecrease is generated after
			adExceedLowerThresholdIncrease is generated."
	::= 4613

    adExceedingLowerThreshold6	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 6 and
			until adExceedLowerThresholdDecrease is generated after
			adExceedLowerThresholdIncrease is generated."
	::= 4614

    adExceedingLowerThreshold7	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 7 and
			until adExceedLowerThresholdDecrease is generated after
			adExceedLowerThresholdIncrease is generated."
	::= 4615

    adExceedingLowerThreshold8	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 8 and
			until adExceedLowerThresholdDecrease is generated after
			adExceedLowerThresholdIncrease is generated."
	::= 4616

    adExceedingLowerThreshold9	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 9 and
			until adExceedLowerThresholdDecrease is generated after
			adExceedLowerThresholdIncrease is generated."
	::= 4617

    adExceedingLowerThreshold10	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 10 and
			until adExceedLowerThresholdDecrease is generated after
			adExceedLowerThresholdIncrease is generated."
	::= 4618

    adExceedingLowerThreshold11	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 11 and
			until adExceedLowerThresholdDecrease is generated after
			adExceedLowerThresholdIncrease is generated."
	::= 4619

    adExceedingLowerThreshold12	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 12 and
			until adExceedLowerThresholdDecrease is generated after
			adExceedLowerThresholdIncrease is generated."
	::= 4620

    adExceedingLowerThreshold13	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 13 and
			until adExceedLowerThresholdDecrease is generated after
			adExceedLowerThresholdIncrease is generated."
	::= 4621

    adExceedingLowerThreshold14	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 14 and
			until adExceedLowerThresholdDecrease is generated after
			adExceedLowerThresholdIncrease is generated."
	::= 4622

    adExceedingLowerThreshold15	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 15 and
			until adExceedLowerThresholdDecrease is generated after
			adExceedLowerThresholdIncrease is generated."
	::= 4623

    adExceedingLowerThreshold16	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 16 and
			until adExceedLowerThresholdDecrease is generated after
			adExceedLowerThresholdIncrease is generated."
	::= 4624

    adExceedingLowerThreshold17	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 17 and
			until adExceedLowerThresholdDecrease is generated after
			adExceedLowerThresholdIncrease is generated."
	::= 4625

    adExceedingLowerThreshold18	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 18 and
			until adExceedLowerThresholdDecrease is generated after
			adExceedLowerThresholdIncrease is generated."
	::= 4626

    adExceedingLowerThreshold19	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 19 and
			until adExceedLowerThresholdDecrease is generated after
			adExceedLowerThresholdIncrease is generated."
	::= 4627

    adExceedingLowerThreshold20	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 20 and
			until adExceedLowerThresholdDecrease is generated after
			adExceedLowerThresholdIncrease is generated."
	::= 4628

    adExceedingLowerThreshold21	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 21 and
			until adExceedLowerThresholdDecrease is generated after
			adExceedLowerThresholdIncrease is generated."
	::= 4629

    adExceedingLowerThreshold22	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 22 and
			until adExceedLowerThresholdDecrease is generated after
			adExceedLowerThresholdIncrease is generated."
	::= 4630

    adExceedingLowerThreshold23	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 23 and
			until adExceedLowerThresholdDecrease is generated after
			adExceedLowerThresholdIncrease is generated."
	::= 4631

    adExceedingLowerThreshold24	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 24 and
			until adExceedLowerThresholdDecrease is generated after
			adExceedLowerThresholdIncrease is generated."
	::= 4632

    adExceedingLowerThreshold25	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 25 and
			until adExceedLowerThresholdDecrease is generated after
			adExceedLowerThresholdIncrease is generated."
	::= 4633

    adExceedingLowerThreshold26	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 26 and
			until adExceedLowerThresholdDecrease is generated after
			adExceedLowerThresholdIncrease is generated."
	::= 4634

    adExceedingLowerThreshold27	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 27 and
			until adExceedLowerThresholdDecrease is generated after
			adExceedLowerThresholdIncrease is generated."
	::= 4635

    adExceedingLowerThreshold28	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 28 and
			until adExceedLowerThresholdDecrease is generated after
			adExceedLowerThresholdIncrease is generated."
	::= 4636

    adExceedingLowerThreshold29	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 29 and
			until adExceedLowerThresholdDecrease is generated after
			adExceedLowerThresholdIncrease is generated."
	::= 4637

    adExceedingLowerThreshold30	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 30 and
			until adExceedLowerThresholdDecrease is generated after
			adExceedLowerThresholdIncrease is generated."
	::= 4638

    adExceedingLowerThreshold31	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 31 and
			until adExceedLowerThresholdDecrease is generated after
			adExceedLowerThresholdIncrease is generated."
	::= 4639

    adExceedingLowerThreshold32	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 32 and
			until adExceedLowerThresholdDecrease is generated after
			adExceedLowerThresholdIncrease is generated."
	::= 4640

    adExceedingLowerThreshold33	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 33 and
			until adExceedLowerThresholdDecrease is generated after
			adExceedLowerThresholdIncrease is generated."
	::= 4641

    adExceedingLowerThreshold34	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 34 and
			until adExceedLowerThresholdDecrease is generated after
			adExceedLowerThresholdIncrease is generated."
	::= 4642

    adExceedingLowerThreshold35	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 35 and
			until adExceedLowerThresholdDecrease is generated after
			adExceedLowerThresholdIncrease is generated."
	::= 4643

    adExceedingLowerThreshold36	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 36 and
			until adExceedLowerThresholdDecrease is generated after
			adExceedLowerThresholdIncrease is generated."
	::= 4644

    adExceedingLowerThreshold37	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 37 and
			until adExceedLowerThresholdDecrease is generated after
			adExceedLowerThresholdIncrease is generated."
	::= 4645

    adExceedingLowerThreshold38	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 38 and
			until adExceedLowerThresholdDecrease is generated after
			adExceedLowerThresholdIncrease is generated."
	::= 4646

    adExceedingLowerThreshold39	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 39 and
			until adExceedLowerThresholdDecrease is generated after
			adExceedLowerThresholdIncrease is generated."
	::= 4647

    adExceedingLowerThreshold40	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 40 and
			until adExceedLowerThresholdDecrease is generated after
			adExceedLowerThresholdIncrease is generated."
	::= 4648

    adExceedingLowerThreshold41	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 41 and
			until adExceedLowerThresholdDecrease is generated after
			adExceedLowerThresholdIncrease is generated."
	::= 4649

    adExceedingLowerThreshold42	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 42 and
			until adExceedLowerThresholdDecrease is generated after
			adExceedLowerThresholdIncrease is generated."
	::= 4650

    adExceedingLowerThreshold43	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 43 and
			until adExceedLowerThresholdDecrease is generated after
			adExceedLowerThresholdIncrease is generated."
	::= 4651

    adExceedingLowerThreshold44	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 44 and
			until adExceedLowerThresholdDecrease is generated after
			adExceedLowerThresholdIncrease is generated."
	::= 4652

    adExceedingLowerThreshold45	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 45 and
			until adExceedLowerThresholdDecrease is generated after
			adExceedLowerThresholdIncrease is generated."
	::= 4653

    adExceedingLowerThreshold46	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 46 and
			until adExceedLowerThresholdDecrease is generated after
			adExceedLowerThresholdIncrease is generated."
	::= 4654

    adExceedingLowerThreshold47	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 47 and
			until adExceedLowerThresholdDecrease is generated after
			adExceedLowerThresholdIncrease is generated."
	::= 4655

    adExceedingLowerThreshold48	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 48 and
			until adExceedLowerThresholdDecrease is generated after
			adExceedLowerThresholdIncrease is generated."
	::= 4656

    adExceedingLowerThreshold49	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 49 and
			until adExceedLowerThresholdDecrease is generated after
			adExceedLowerThresholdIncrease is generated."
	::= 4657

    adExceedingLowerThreshold50	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 50 and
			until adExceedLowerThresholdDecrease is generated after
			adExceedLowerThresholdIncrease is generated."
	::= 4658

    adExceedingLowerThreshold51	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 51 and
			until adExceedLowerThresholdDecrease is generated after
			adExceedLowerThresholdIncrease is generated."
	::= 4659

    adExceedingLowerThreshold52	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 52 and
			until adExceedLowerThresholdDecrease is generated after
			adExceedLowerThresholdIncrease is generated."
	::= 4660

    adExceedingLowerThreshold53	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 53 and
			until adExceedLowerThresholdDecrease is generated after
			adExceedLowerThresholdIncrease is generated."
	::= 4661

    adExceedingLowerThreshold54	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 54 and
			until adExceedLowerThresholdDecrease is generated after
			adExceedLowerThresholdIncrease is generated."
	::= 4662

    adExceedingLowerThreshold55	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 55 and
			until adExceedLowerThresholdDecrease is generated after
			adExceedLowerThresholdIncrease is generated."
	::= 4663

    adExceedingLowerThreshold56	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 56 and
			until adExceedLowerThresholdDecrease is generated after
			adExceedLowerThresholdIncrease is generated."
	::= 4664

    adExceedingLowerThreshold57	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 57 and
			until adExceedLowerThresholdDecrease is generated after
			adExceedLowerThresholdIncrease is generated."
	::= 4665

    adExceedingLowerThreshold58	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 58 and
			until adExceedLowerThresholdDecrease is generated after
			adExceedLowerThresholdIncrease is generated."
	::= 4666

    adExceedingLowerThreshold59	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 59 and
			until adExceedLowerThresholdDecrease is generated after
			adExceedLowerThresholdIncrease is generated."
	::= 4667

    adExceedingLowerThreshold60	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 60 and
			until adExceedLowerThresholdDecrease is generated after
			adExceedLowerThresholdIncrease is generated."
	::= 4668

    adExceedingLowerThreshold61	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 61 and
			until adExceedLowerThresholdDecrease is generated after
			adExceedLowerThresholdIncrease is generated."
	::= 4669

    adExceedingLowerThreshold62	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 62 and
			until adExceedLowerThresholdDecrease is generated after
			adExceedLowerThresholdIncrease is generated."
	::= 4670

    adExceedingLowerThreshold63	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 63 and
			until adExceedLowerThresholdDecrease is generated after
			adExceedLowerThresholdIncrease is generated."
	::= 4671

    adExceedingLowerThreshold64	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 64 and
			until adExceedLowerThresholdDecrease is generated after
			adExceedLowerThresholdIncrease is generated."
	::= 4672

    adExceedingLowerThreshold65	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 65 and
			until adExceedLowerThresholdDecrease is generated after
			adExceedLowerThresholdIncrease is generated."
	::= 4673

    adExceedingLowerThreshold66	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 66 and
			until adExceedLowerThresholdDecrease is generated after
			adExceedLowerThresholdIncrease is generated."
	::= 4674

    adExceedingLowerThreshold67	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 67 and
			until adExceedLowerThresholdDecrease is generated after
			adExceedLowerThresholdIncrease is generated."
	::= 4675

    adExceedingLowerThreshold68	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 68 and
			until adExceedLowerThresholdDecrease is generated after
			adExceedLowerThresholdIncrease is generated."
	::= 4676

    adExceedingLowerThreshold69	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 69 and
			until adExceedLowerThresholdDecrease is generated after
			adExceedLowerThresholdIncrease is generated."
	::= 4677

    adExceedingLowerThreshold70	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 70 and
			until adExceedLowerThresholdDecrease is generated after
			adExceedLowerThresholdIncrease is generated."
	::= 4678

    adExceedingLowerThreshold71	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 71 and
			until adExceedLowerThresholdDecrease is generated after
			adExceedLowerThresholdIncrease is generated."
	::= 4679

    adExceedingLowerThreshold72	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 72 and
			until adExceedLowerThresholdDecrease is generated after
			adExceedLowerThresholdIncrease is generated."
	::= 4680

    adExceedingLowerThreshold73	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 73 and
			until adExceedLowerThresholdDecrease is generated after
			adExceedLowerThresholdIncrease is generated."
	::= 4681

    adExceedingLowerThreshold74	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 74 and
			until adExceedLowerThresholdDecrease is generated after
			adExceedLowerThresholdIncrease is generated."
	::= 4682

    adExceedingLowerThreshold75	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 75 and
			until adExceedLowerThresholdDecrease is generated after
			adExceedLowerThresholdIncrease is generated."
	::= 4683

    adExceedingLowerThreshold76	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 76 and
			until adExceedLowerThresholdDecrease is generated after
			adExceedLowerThresholdIncrease is generated."
	::= 4684

    adExceedingLowerThreshold77	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 77 and
			until adExceedLowerThresholdDecrease is generated after
			adExceedLowerThresholdIncrease is generated."
	::= 4685

    adExceedingLowerThreshold78	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 78 and
			until adExceedLowerThresholdDecrease is generated after
			adExceedLowerThresholdIncrease is generated."
	::= 4686

    adExceedingLowerThreshold79	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 79 and
			until adExceedLowerThresholdDecrease is generated after
			adExceedLowerThresholdIncrease is generated."
	::= 4687

    adExceedingLowerThreshold80	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 80 and
			until adExceedLowerThresholdDecrease is generated after
			adExceedLowerThresholdIncrease is generated."
	::= 4688

    adExceedingLowerThreshold81	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 81 and
			until adExceedLowerThresholdDecrease is generated after
			adExceedLowerThresholdIncrease is generated."
	::= 4689

    adExceedingLowerThreshold82	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 82 and
			until adExceedLowerThresholdDecrease is generated after
			adExceedLowerThresholdIncrease is generated."
	::= 4690

    adExceedingLowerThreshold83	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 83 and
			until adExceedLowerThresholdDecrease is generated after
			adExceedLowerThresholdIncrease is generated."
	::= 4691

    adExceedingLowerThreshold84	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 84 and
			until adExceedLowerThresholdDecrease is generated after
			adExceedLowerThresholdIncrease is generated."
	::= 4692

    adExceedingLowerThreshold85	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 85 and
			until adExceedLowerThresholdDecrease is generated after
			adExceedLowerThresholdIncrease is generated."
	::= 4693

    adExceedingLowerThreshold86	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 86 and
			until adExceedLowerThresholdDecrease is generated after
			adExceedLowerThresholdIncrease is generated."
	::= 4694

    adExceedingLowerThreshold87	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 87 and
			until adExceedLowerThresholdDecrease is generated after
			adExceedLowerThresholdIncrease is generated."
	::= 4695

    adExceedingLowerThreshold88	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 88 and
			until adExceedLowerThresholdDecrease is generated after
			adExceedLowerThresholdIncrease is generated."
	::= 4696

    adExceedingLowerThreshold89	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 89 and
			until adExceedLowerThresholdDecrease is generated after
			adExceedLowerThresholdIncrease is generated."
	::= 4697

    adExceedingLowerThreshold90	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 90 and
			until adExceedLowerThresholdDecrease is generated after
			adExceedLowerThresholdIncrease is generated."
	::= 4698

    adExceedingLowerThreshold91	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 91 and
			until adExceedLowerThresholdDecrease is generated after
			adExceedLowerThresholdIncrease is generated."
	::= 4699

    adExceedingLowerThreshold92	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 92 and
			until adExceedLowerThresholdDecrease is generated after
			adExceedLowerThresholdIncrease is generated."
	::= 4700

    adExceedingLowerThreshold93	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 93 and
			until adExceedLowerThresholdDecrease is generated after
			adExceedLowerThresholdIncrease is generated."
	::= 4701

    adExceedingLowerThreshold94	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 94 and
			until adExceedLowerThresholdDecrease is generated after
			adExceedLowerThresholdIncrease is generated."
	::= 4702

    adExceedingLowerThreshold95	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 95 and
			until adExceedLowerThresholdDecrease is generated after
			adExceedLowerThresholdIncrease is generated."
	::= 4703

    adExceedingLowerThreshold96	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 96 and
			until adExceedLowerThresholdDecrease is generated after
			adExceedLowerThresholdIncrease is generated."
	::= 4704

    adExceedingLowerThreshold97	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 97 and
			until adExceedLowerThresholdDecrease is generated after
			adExceedLowerThresholdIncrease is generated."
	::= 4705

    adExceedingLowerThreshold98	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 98 and
			until adExceedLowerThresholdDecrease is generated after
			adExceedLowerThresholdIncrease is generated."
	::= 4706

    adExceedingLowerThreshold99	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 99 and
			until adExceedLowerThresholdDecrease is generated after
			adExceedLowerThresholdIncrease is generated."
	::= 4707

    adExceedingLowerThreshold100	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 100 and
			until adExceedLowerThresholdDecrease is generated after
			adExceedLowerThresholdIncrease is generated."
	::= 4708

    adExceedingLowerThreshold101	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 101 and
			until adExceedLowerThresholdDecrease is generated after
			adExceedLowerThresholdIncrease is generated."
	::= 4709

    adExceedingLowerThreshold102	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 102 and
			until adExceedLowerThresholdDecrease is generated after
			adExceedLowerThresholdIncrease is generated."
	::= 4710

    adExceedingLowerThreshold103	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 103 and
			until adExceedLowerThresholdDecrease is generated after
			adExceedLowerThresholdIncrease is generated."
	::= 4711

    adExceedingLowerThreshold104	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 104 and
			until adExceedLowerThresholdDecrease is generated after
			adExceedLowerThresholdIncrease is generated."
	::= 4712

    adExceedingLowerThreshold105	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 105 and
			until adExceedLowerThresholdDecrease is generated after
			adExceedLowerThresholdIncrease is generated."
	::= 4713

    adExceedingLowerThreshold106	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 106 and
			until adExceedLowerThresholdDecrease is generated after
			adExceedLowerThresholdIncrease is generated."
	::= 4714

    adExceedingLowerThreshold107	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 107 and
			until adExceedLowerThresholdDecrease is generated after
			adExceedLowerThresholdIncrease is generated."
	::= 4715

    adExceedingLowerThreshold108	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 108 and
			until adExceedLowerThresholdDecrease is generated after
			adExceedLowerThresholdIncrease is generated."
	::= 4716

    adExceedingLowerThreshold109	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 109 and
			until adExceedLowerThresholdDecrease is generated after
			adExceedLowerThresholdIncrease is generated."
	::= 4717

    adExceedingLowerThreshold110	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 110 and
			until adExceedLowerThresholdDecrease is generated after
			adExceedLowerThresholdIncrease is generated."
	::= 4718

    adExceedingLowerThreshold111	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 111 and
			until adExceedLowerThresholdDecrease is generated after
			adExceedLowerThresholdIncrease is generated."
	::= 4719

    adExceedingLowerThreshold112	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 112 and
			until adExceedLowerThresholdDecrease is generated after
			adExceedLowerThresholdIncrease is generated."
	::= 4720

    adExceedingLowerThreshold113	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 113 and
			until adExceedLowerThresholdDecrease is generated after
			adExceedLowerThresholdIncrease is generated."
	::= 4721

    adExceedingLowerThreshold114	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 114 and
			until adExceedLowerThresholdDecrease is generated after
			adExceedLowerThresholdIncrease is generated."
	::= 4722

    adExceedingLowerThreshold115	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 115 and
			until adExceedLowerThresholdDecrease is generated after
			adExceedLowerThresholdIncrease is generated."
	::= 4723

    adExceedingLowerThreshold116	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 116 and
			until adExceedLowerThresholdDecrease is generated after
			adExceedLowerThresholdIncrease is generated."
	::= 4724

    adExceedingLowerThreshold117	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 117 and
			until adExceedLowerThresholdDecrease is generated after
			adExceedLowerThresholdIncrease is generated."
	::= 4725

    adExceedingLowerThreshold118	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 118 and
			until adExceedLowerThresholdDecrease is generated after
			adExceedLowerThresholdIncrease is generated."
	::= 4726

    adExceedingLowerThreshold119	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 119 and
			until adExceedLowerThresholdDecrease is generated after
			adExceedLowerThresholdIncrease is generated."
	::= 4727

    adExceedingLowerThreshold120	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 120 and
			until adExceedLowerThresholdDecrease is generated after
			adExceedLowerThresholdIncrease is generated."
	::= 4728

    adExceedingLowerThreshold121	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 121 and
			until adExceedLowerThresholdDecrease is generated after
			adExceedLowerThresholdIncrease is generated."
	::= 4729

    adExceedingLowerThreshold122	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 122 and
			until adExceedLowerThresholdDecrease is generated after
			adExceedLowerThresholdIncrease is generated."
	::= 4730

    adExceedingLowerThreshold123	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 123 and
			until adExceedLowerThresholdDecrease is generated after
			adExceedLowerThresholdIncrease is generated."
	::= 4731

    adExceedingLowerThreshold124	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 124 and
			until adExceedLowerThresholdDecrease is generated after
			adExceedLowerThresholdIncrease is generated."
	::= 4732

    adExceedingLowerThreshold125	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 125 and
			until adExceedLowerThresholdDecrease is generated after
			adExceedLowerThresholdIncrease is generated."
	::= 4733

    adExceedingLowerThreshold126	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 126 and
			until adExceedLowerThresholdDecrease is generated after
			adExceedLowerThresholdIncrease is generated."
	::= 4734

    adExceedingLowerThreshold127	TRAP-TYPE
	ENTERPRISE	network-device
	VARIABLES	{ adValue, adminDateAndTime, adminNDTrapSeqNo,
			  adIndex, adType, adValueOnlyString,
			  adTrapCurrentStatus }
	DESCRIPTION	"This trap is generated when set
			 adExLoThresholdTrapID equal 127 and
			until adExceedLowerThresholdDecrease is generated after
			adExceedLowerThresholdIncrease is generated."
	::= 4735

    diChangeValue0-1	TRAP-TYPE
	ENTERPRISE	network-device
	VARIABLES	{ diValue, adminDateAndTime, adminNDTrapSeqNo,
			  diIndex, diType, diValue0String }
	DESCRIPTION	"This trap is generated when set
			 diChangeValue0TrapID equal 1 and
			the value of diValue change from 1 to 0."
	::= 8193

    diChangeValue0-2	TRAP-TYPE
	ENTERPRISE	network-device
	VARIABLES	{ diValue, adminDateAndTime, adminNDTrapSeqNo,
			  diIndex, diType, diValue0String }
	DESCRIPTION	"This trap is generated when set
			 diChangeValue0TrapID equal 2 and
			the value of diValue change from 1 to 0."
	::= 8194

    diChangeValue0-3	TRAP-TYPE
	ENTERPRISE	network-device
	VARIABLES	{ diValue, adminDateAndTime, adminNDTrapSeqNo,
			  diIndex, diType, diValue0String }
	DESCRIPTION	"This trap is generated when set
			 diChangeValue0TrapID equal 3 and
			the value of diValue change from 1 to 0."
	::= 8195

    diChangeValue0-4	TRAP-TYPE
	ENTERPRISE	network-device
	VARIABLES	{ diValue, adminDateAndTime, adminNDTrapSeqNo,
			  diIndex, diType, diValue0String }
	DESCRIPTION	"This trap is generated when set
			 diChangeValue0TrapID equal 4 and
			the value of diValue change from 1 to 0."
	::= 8196

    diChangeValue0-5	TRAP-TYPE
	ENTERPRISE	network-device
	VARIABLES	{ diValue, adminDateAndTime, adminNDTrapSeqNo,
			  diIndex, diType, diValue0String }
	DESCRIPTION	"This trap is generated when set
			 diChangeValue0TrapID equal 5 and
			the value of diValue change from 1 to 0."
	::= 8197

    diChangeValue0-6	TRAP-TYPE
	ENTERPRISE	network-device
	VARIABLES	{ diValue, adminDateAndTime, adminNDTrapSeqNo,
			  diIndex, diType, diValue0String }
	DESCRIPTION	"This trap is generated when set
			 diChangeValue0TrapID equal 6 and
			the value of diValue change from 1 to 0."
	::= 8198

    diChangeValue0-7	TRAP-TYPE
	ENTERPRISE	network-device
	VARIABLES	{ diValue, adminDateAndTime, adminNDTrapSeqNo,
			  diIndex, diType, diValue0String }
	DESCRIPTION	"This trap is generated when set
			 diChangeValue0TrapID equal 7 and
			the value of diValue change from 1 to 0."
	::= 8199

    diChangeValue0-8	TRAP-TYPE
	ENTERPRISE	network-device
	VARIABLES	{ diValue, adminDateAndTime, adminNDTrapSeqNo,
			  diIndex, diType, diValue0String }
	DESCRIPTION	"This trap is generated when set
			 diChangeValue0TrapID equal 8 and
			the value of diValue change from 1 to 0."
	::= 8200

    diChangeValue0-9	TRAP-TYPE
	ENTERPRISE	network-device
	VARIABLES	{ diValue, adminDateAndTime, adminNDTrapSeqNo,
			  diIndex, diType, diValue0String }
	DESCRIPTION	"This trap is generated when set
			 diChangeValue0TrapID equal 9 and
			the value of diValue change from 1 to 0."
	::= 8201

    diChangeValue0-10	TRAP-TYPE
	ENTERPRISE	network-device
	VARIABLES	{ diValue, adminDateAndTime, adminNDTrapSeqNo,
			  diIndex, diType, diValue0String }
	DESCRIPTION	"This trap is generated when set
			 diChangeValue0TrapID equal 10 and
			the value of diValue change from 1 to 0."
	::= 8202

    diChangeValue0-11	TRAP-TYPE
	ENTERPRISE	network-device
	VARIABLES	{ diValue, adminDateAndTime, adminNDTrapSeqNo,
			  diIndex, diType, diValue0String }
	DESCRIPTION	"This trap is generated when set
			 diChangeValue0TrapID equal 11 and
			the value of diValue change from 1 to 0."
	::= 8203

    diChangeValue0-12	TRAP-TYPE
	ENTERPRISE	network-device
	VARIABLES	{ diValue, adminDateAndTime, adminNDTrapSeqNo,
			  diIndex, diType, diValue0String }
	DESCRIPTION	"This trap is generated when set
			 diChangeValue0TrapID equal 12 and
			the value of diValue change from 1 to 0."
	::= 8204

    diChangeValue0-13	TRAP-TYPE
	ENTERPRISE	network-device
	VARIABLES	{ diValue, adminDateAndTime, adminNDTrapSeqNo,
			  diIndex, diType, diValue0String }
	DESCRIPTION	"This trap is generated when set
			 diChangeValue0TrapID equal 13 and
			the value of diValue change from 1 to 0."
	::= 8205

    diChangeValue0-14	TRAP-TYPE
	ENTERPRISE	network-device
	VARIABLES	{ diValue, adminDateAndTime, adminNDTrapSeqNo,
			  diIndex, diType, diValue0String }
	DESCRIPTION	"This trap is generated when set
			 diChangeValue0TrapID equal 14 and
			the value of diValue change from 1 to 0."
	::= 8206

    diChangeValue0-15	TRAP-TYPE
	ENTERPRISE	network-device
	VARIABLES	{ diValue, adminDateAndTime, adminNDTrapSeqNo,
			  diIndex, diType, diValue0String }
	DESCRIPTION	"This trap is generated when set
			 diChangeValue0TrapID equal 15 and
			the value of diValue change from 1 to 0."
	::= 8207

    diChangeValue0-16	TRAP-TYPE
	ENTERPRISE	network-device
	VARIABLES	{ diValue, adminDateAndTime, adminNDTrapSeqNo,
			  diIndex, diType, diValue0String }
	DESCRIPTION	"This trap is generated when set
			 diChangeValue0TrapID equal 16 and
			the value of diValue change from 1 to 0."
	::= 8208

    diChangeValue0-17	TRAP-TYPE
	ENTERPRISE	network-device
	VARIABLES	{ diValue, adminDateAndTime, adminNDTrapSeqNo,
			  diIndex, diType, diValue0String }
	DESCRIPTION	"This trap is generated when set
			 diChangeValue0TrapID equal 17 and
			the value of diValue change from 1 to 0."
	::= 8209

    diChangeValue0-18	TRAP-TYPE
	ENTERPRISE	network-device
	VARIABLES	{ diValue, adminDateAndTime, adminNDTrapSeqNo,
			  diIndex, diType, diValue0String }
	DESCRIPTION	"This trap is generated when set
			 diChangeValue0TrapID equal 18 and
			the value of diValue change from 1 to 0."
	::= 8210

    diChangeValue0-19	TRAP-TYPE
	ENTERPRISE	network-device
	VARIABLES	{ diValue, adminDateAndTime, adminNDTrapSeqNo,
			  diIndex, diType, diValue0String }
	DESCRIPTION	"This trap is generated when set
			 diChangeValue0TrapID equal 19 and
			the value of diValue change from 1 to 0."
	::= 8211

    diChangeValue0-20	TRAP-TYPE
	ENTERPRISE	network-device
	VARIABLES	{ diValue, adminDateAndTime, adminNDTrapSeqNo,
			  diIndex, diType, diValue0String }
	DESCRIPTION	"This trap is generated when set
			 diChangeValue0TrapID equal 20 and
			the value of diValue change from 1 to 0."
	::= 8212

    diChangeValue0-21	TRAP-TYPE
	ENTERPRISE	network-device
	VARIABLES	{ diValue, adminDateAndTime, adminNDTrapSeqNo,
			  diIndex, diType, diValue0String }
	DESCRIPTION	"This trap is generated when set
			 diChangeValue0TrapID equal 21 and
			the value of diValue change from 1 to 0."
	::= 8213

    diChangeValue0-22	TRAP-TYPE
	ENTERPRISE	network-device
	VARIABLES	{ diValue, adminDateAndTime, adminNDTrapSeqNo,
			  diIndex, diType, diValue0String }
	DESCRIPTION	"This trap is generated when set
			 diChangeValue0TrapID equal 22 and
			the value of diValue change from 1 to 0."
	::= 8214

    diChangeValue0-23	TRAP-TYPE
	ENTERPRISE	network-device
	VARIABLES	{ diValue, adminDateAndTime, adminNDTrapSeqNo,
			  diIndex, diType, diValue0String }
	DESCRIPTION	"This trap is generated when set
			 diChangeValue0TrapID equal 23 and
			the value of diValue change from 1 to 0."
	::= 8215

    diChangeValue0-24	TRAP-TYPE
	ENTERPRISE	network-device
	VARIABLES	{ diValue, adminDateAndTime, adminNDTrapSeqNo,
			  diIndex, diType, diValue0String }
	DESCRIPTION	"This trap is generated when set
			 diChangeValue0TrapID equal 24 and
			the value of diValue change from 1 to 0."
	::= 8216

    diChangeValue0-25	TRAP-TYPE
	ENTERPRISE	network-device
	VARIABLES	{ diValue, adminDateAndTime, adminNDTrapSeqNo,
			  diIndex, diType, diValue0String }
	DESCRIPTION	"This trap is generated when set
			 diChangeValue0TrapID equal 25 and
			the value of diValue change from 1 to 0."
	::= 8217

    diChangeValue0-26	TRAP-TYPE
	ENTERPRISE	network-device
	VARIABLES	{ diValue, adminDateAndTime, adminNDTrapSeqNo,
			  diIndex, diType, diValue0String }
	DESCRIPTION	"This trap is generated when set
			 diChangeValue0TrapID equal 26 and
			the value of diValue change from 1 to 0."
	::= 8218

    diChangeValue0-27	TRAP-TYPE
	ENTERPRISE	network-device
	VARIABLES	{ diValue, adminDateAndTime, adminNDTrapSeqNo,
			  diIndex, diType, diValue0String }
	DESCRIPTION	"This trap is generated when set
			 diChangeValue0TrapID equal 27 and
			the value of diValue change from 1 to 0."
	::= 8219

    diChangeValue0-28	TRAP-TYPE
	ENTERPRISE	network-device
	VARIABLES	{ diValue, adminDateAndTime, adminNDTrapSeqNo,
			  diIndex, diType, diValue0String }
	DESCRIPTION	"This trap is generated when set
			 diChangeValue0TrapID equal 28 and
			the value of diValue change from 1 to 0."
	::= 8220

    diChangeValue0-29	TRAP-TYPE
	ENTERPRISE	network-device
	VARIABLES	{ diValue, adminDateAndTime, adminNDTrapSeqNo,
			  diIndex, diType, diValue0String }
	DESCRIPTION	"This trap is generated when set
			 diChangeValue0TrapID equal 29 and
			the value of diValue change from 1 to 0."
	::= 8221

    diChangeValue0-30	TRAP-TYPE
	ENTERPRISE	network-device
	VARIABLES	{ diValue, adminDateAndTime, adminNDTrapSeqNo,
			  diIndex, diType, diValue0String }
	DESCRIPTION	"This trap is generated when set
			 diChangeValue0TrapID equal 30 and
			the value of diValue change from 1 to 0."
	::= 8222

    diChangeValue0-31	TRAP-TYPE
	ENTERPRISE	network-device
	VARIABLES	{ diValue, adminDateAndTime, adminNDTrapSeqNo,
			  diIndex, diType, diValue0String }
	DESCRIPTION	"This trap is generated when set
			 diChangeValue0TrapID equal 31 and
			the value of diValue change from 1 to 0."
	::= 8223

    diChangeValue0-32	TRAP-TYPE
	ENTERPRISE	network-device
	VARIABLES	{ diValue, adminDateAndTime, adminNDTrapSeqNo,
			  diIndex, diType, diValue0String }
	DESCRIPTION	"This trap is generated when set
			 diChangeValue0TrapID equal 32 and
			the value of diValue change from 1 to 0."
	::= 8224

    diChangeValue0-33	TRAP-TYPE
	ENTERPRISE	network-device
	VARIABLES	{ diValue, adminDateAndTime, adminNDTrapSeqNo,
			  diIndex, diType, diValue0String }
	DESCRIPTION	"This trap is generated when set
			 diChangeValue0TrapID equal 33 and
			the value of diValue change from 1 to 0."
	::= 8225

    diChangeValue0-34	TRAP-TYPE
	ENTERPRISE	network-device
	VARIABLES	{ diValue, adminDateAndTime, adminNDTrapSeqNo,
			  diIndex, diType, diValue0String }
	DESCRIPTION	"This trap is generated when set
			 diChangeValue0TrapID equal 34 and
			the value of diValue change from 1 to 0."
	::= 8226

    diChangeValue0-35	TRAP-TYPE
	ENTERPRISE	network-device
	VARIABLES	{ diValue, adminDateAndTime, adminNDTrapSeqNo,
			  diIndex, diType, diValue0String }
	DESCRIPTION	"This trap is generated when set
			 diChangeValue0TrapID equal 35 and
			the value of diValue change from 1 to 0."
	::= 8227

    diChangeValue0-36	TRAP-TYPE
	ENTERPRISE	network-device
	VARIABLES	{ diValue, adminDateAndTime, adminNDTrapSeqNo,
			  diIndex, diType, diValue0String }
	DESCRIPTION	"This trap is generated when set
			 diChangeValue0TrapID equal 36 and
			the value of diValue change from 1 to 0."
	::= 8228

    diChangeValue0-37	TRAP-TYPE
	ENTERPRISE	network-device
	VARIABLES	{ diValue, adminDateAndTime, adminNDTrapSeqNo,
			  diIndex, diType, diValue0String }
	DESCRIPTION	"This trap is generated when set
			 diChangeValue0TrapID equal 37 and
			the value of diValue change from 1 to 0."
	::= 8229

    diChangeValue0-38	TRAP-TYPE
	ENTERPRISE	network-device
	VARIABLES	{ diValue, adminDateAndTime, adminNDTrapSeqNo,
			  diIndex, diType, diValue0String }
	DESCRIPTION	"This trap is generated when set
			 diChangeValue0TrapID equal 38 and
			the value of diValue change from 1 to 0."
	::= 8230

    diChangeValue0-39	TRAP-TYPE
	ENTERPRISE	network-device
	VARIABLES	{ diValue, adminDateAndTime, adminNDTrapSeqNo,
			  diIndex, diType, diValue0String }
	DESCRIPTION	"This trap is generated when set
			 diChangeValue0TrapID equal 39 and
			the value of diValue change from 1 to 0."
	::= 8231

    diChangeValue0-40	TRAP-TYPE
	ENTERPRISE	network-device
	VARIABLES	{ diValue, adminDateAndTime, adminNDTrapSeqNo,
			  diIndex, diType, diValue0String }
	DESCRIPTION	"This trap is generated when set
			 diChangeValue0TrapID equal 40 and
			the value of diValue change from 1 to 0."
	::= 8232

    diChangeValue0-41	TRAP-TYPE
	ENTERPRISE	network-device
	VARIABLES	{ diValue, adminDateAndTime, adminNDTrapSeqNo,
			  diIndex, diType, diValue0String }
	DESCRIPTION	"This trap is generated when set
			 diChangeValue0TrapID equal 41 and
			the value of diValue change from 1 to 0."
	::= 8233

    diChangeValue0-42	TRAP-TYPE
	ENTERPRISE	network-device
	VARIABLES	{ diValue, adminDateAndTime, adminNDTrapSeqNo,
			  diIndex, diType, diValue0String }
	DESCRIPTION	"This trap is generated when set
			 diChangeValue0TrapID equal 42 and
			the value of diValue change from 1 to 0."
	::= 8234

    diChangeValue0-43	TRAP-TYPE
	ENTERPRISE	network-device
	VARIABLES	{ diValue, adminDateAndTime, adminNDTrapSeqNo,
			  diIndex, diType, diValue0String }
	DESCRIPTION	"This trap is generated when set
			 diChangeValue0TrapID equal 43 and
			the value of diValue change from 1 to 0."
	::= 8235

    diChangeValue0-44	TRAP-TYPE
	ENTERPRISE	network-device
	VARIABLES	{ diValue, adminDateAndTime, adminNDTrapSeqNo,
			  diIndex, diType, diValue0String }
	DESCRIPTION	"This trap is generated when set
			 diChangeValue0TrapID equal 44 and
			the value of diValue change from 1 to 0."
	::= 8236

    diChangeValue0-45	TRAP-TYPE
	ENTERPRISE	network-device
	VARIABLES	{ diValue, adminDateAndTime, adminNDTrapSeqNo,
			  diIndex, diType, diValue0String }
	DESCRIPTION	"This trap is generated when set
			 diChangeValue0TrapID equal 45 and
			the value of diValue change from 1 to 0."
	::= 8237

    diChangeValue0-46	TRAP-TYPE
	ENTERPRISE	network-device
	VARIABLES	{ diValue, adminDateAndTime, adminNDTrapSeqNo,
			  diIndex, diType, diValue0String }
	DESCRIPTION	"This trap is generated when set
			 diChangeValue0TrapID equal 46 and
			the value of diValue change from 1 to 0."
	::= 8238

    diChangeValue0-47	TRAP-TYPE
	ENTERPRISE	network-device
	VARIABLES	{ diValue, adminDateAndTime, adminNDTrapSeqNo,
			  diIndex, diType, diValue0String }
	DESCRIPTION	"This trap is generated when set
			 diChangeValue0TrapID equal 47 and
			the value of diValue change from 1 to 0."
	::= 8239

    diChangeValue0-48	TRAP-TYPE
	ENTERPRISE	network-device
	VARIABLES	{ diValue, adminDateAndTime, adminNDTrapSeqNo,
			  diIndex, diType, diValue0String }
	DESCRIPTION	"This trap is generated when set
			 diChangeValue0TrapID equal 48 and
			the value of diValue change from 1 to 0."
	::= 8240

    diChangeValue0-49	TRAP-TYPE
	ENTERPRISE	network-device
	VARIABLES	{ diValue, adminDateAndTime, adminNDTrapSeqNo,
			  diIndex, diType, diValue0String }
	DESCRIPTION	"This trap is generated when set
			 diChangeValue0TrapID equal 49 and
			the value of diValue change from 1 to 0."
	::= 8241

    diChangeValue0-50	TRAP-TYPE
	ENTERPRISE	network-device
	VARIABLES	{ diValue, adminDateAndTime, adminNDTrapSeqNo,
			  diIndex, diType, diValue0String }
	DESCRIPTION	"This trap is generated when set
			 diChangeValue0TrapID equal 50 and
			the value of diValue change from 1 to 0."
	::= 8242

    diChangeValue0-51	TRAP-TYPE
	ENTERPRISE	network-device
	VARIABLES	{ diValue, adminDateAndTime, adminNDTrapSeqNo,
			  diIndex, diType, diValue0String }
	DESCRIPTION	"This trap is generated when set
			 diChangeValue0TrapID equal 51 and
			the value of diValue change from 1 to 0."
	::= 8243

    diChangeValue0-52	TRAP-TYPE
	ENTERPRISE	network-device
	VARIABLES	{ diValue, adminDateAndTime, adminNDTrapSeqNo,
			  diIndex, diType, diValue0String }
	DESCRIPTION	"This trap is generated when set
			 diChangeValue0TrapID equal 52 and
			the value of diValue change from 1 to 0."
	::= 8244

    diChangeValue0-53	TRAP-TYPE
	ENTERPRISE	network-device
	VARIABLES	{ diValue, adminDateAndTime, adminNDTrapSeqNo,
			  diIndex, diType, diValue0String }
	DESCRIPTION	"This trap is generated when set
			 diChangeValue0TrapID equal 53 and
			the value of diValue change from 1 to 0."
	::= 8245

    diChangeValue0-54	TRAP-TYPE
	ENTERPRISE	network-device
	VARIABLES	{ diValue, adminDateAndTime, adminNDTrapSeqNo,
			  diIndex, diType, diValue0String }
	DESCRIPTION	"This trap is generated when set
			 diChangeValue0TrapID equal 54 and
			the value of diValue change from 1 to 0."
	::= 8246

    diChangeValue0-55	TRAP-TYPE
	ENTERPRISE	network-device
	VARIABLES	{ diValue, adminDateAndTime, adminNDTrapSeqNo,
			  diIndex, diType, diValue0String }
	DESCRIPTION	"This trap is generated when set
			 diChangeValue0TrapID equal 55 and
			the value of diValue change from 1 to 0."
	::= 8247

    diChangeValue0-56	TRAP-TYPE
	ENTERPRISE	network-device
	VARIABLES	{ diValue, adminDateAndTime, adminNDTrapSeqNo,
			  diIndex, diType, diValue0String }
	DESCRIPTION	"This trap is generated when set
			 diChangeValue0TrapID equal 56 and
			the value of diValue change from 1 to 0."
	::= 8248

    diChangeValue0-57	TRAP-TYPE
	ENTERPRISE	network-device
	VARIABLES	{ diValue, adminDateAndTime, adminNDTrapSeqNo,
			  diIndex, diType, diValue0String }
	DESCRIPTION	"This trap is generated when set
			 diChangeValue0TrapID equal 57 and
			the value of diValue change from 1 to 0."
	::= 8249

    diChangeValue0-58	TRAP-TYPE
	ENTERPRISE	network-device
	VARIABLES	{ diValue, adminDateAndTime, adminNDTrapSeqNo,
			  diIndex, diType, diValue0String }
	DESCRIPTION	"This trap is generated when set
			 diChangeValue0TrapID equal 58 and
			the value of diValue change from 1 to 0."
	::= 8250

    diChangeValue0-59	TRAP-TYPE
	ENTERPRISE	network-device
	VARIABLES	{ diValue, adminDateAndTime, adminNDTrapSeqNo,
			  diIndex, diType, diValue0String }
	DESCRIPTION	"This trap is generated when set
			 diChangeValue0TrapID equal 59 and
			the value of diValue change from 1 to 0."
	::= 8251

    diChangeValue0-60	TRAP-TYPE
	ENTERPRISE	network-device
	VARIABLES	{ diValue, adminDateAndTime, adminNDTrapSeqNo,
			  diIndex, diType, diValue0String }
	DESCRIPTION	"This trap is generated when set
			 diChangeValue0TrapID equal 60 and
			the value of diValue change from 1 to 0."
	::= 8252

    diChangeValue0-61	TRAP-TYPE
	ENTERPRISE	network-device
	VARIABLES	{ diValue, adminDateAndTime, adminNDTrapSeqNo,
			  diIndex, diType, diValue0String }
	DESCRIPTION	"This trap is generated when set
			 diChangeValue0TrapID equal 61 and
			the value of diValue change from 1 to 0."
	::= 8253

    diChangeValue0-62	TRAP-TYPE
	ENTERPRISE	network-device
	VARIABLES	{ diValue, adminDateAndTime, adminNDTrapSeqNo,
			  diIndex, diType, diValue0String }
	DESCRIPTION	"This trap is generated when set
			 diChangeValue0TrapID equal 62 and
			the value of diValue change from 1 to 0."
	::= 8254

    diChangeValue0-63	TRAP-TYPE
	ENTERPRISE	network-device
	VARIABLES	{ diValue, adminDateAndTime, adminNDTrapSeqNo,
			  diIndex, diType, diValue0String }
	DESCRIPTION	"This trap is generated when set
			 diChangeValue0TrapID equal 63 and
			the value of diValue change from 1 to 0."
	::= 8255

    diChangeValue0-64	TRAP-TYPE
	ENTERPRISE	network-device
	VARIABLES	{ diValue, adminDateAndTime, adminNDTrapSeqNo,
			  diIndex, diType, diValue0String }
	DESCRIPTION	"This trap is generated when set
			 diChangeValue0TrapID equal 64 and
			the value of diValue change from 1 to 0."
	::= 8256

    diChangeValue0-65	TRAP-TYPE
	ENTERPRISE	network-device
	VARIABLES	{ diValue, adminDateAndTime, adminNDTrapSeqNo,
			  diIndex, diType, diValue0String }
	DESCRIPTION	"This trap is generated when set
			 diChangeValue0TrapID equal 65 and
			the value of diValue change from 1 to 0."
	::= 8257

    diChangeValue0-66	TRAP-TYPE
	ENTERPRISE	network-device
	VARIABLES	{ diValue, adminDateAndTime, adminNDTrapSeqNo,
			  diIndex, diType, diValue0String }
	DESCRIPTION	"This trap is generated when set
			 diChangeValue0TrapID equal 66 and
			the value of diValue change from 1 to 0."
	::= 8258

    diChangeValue0-67	TRAP-TYPE
	ENTERPRISE	network-device
	VARIABLES	{ diValue, adminDateAndTime, adminNDTrapSeqNo,
			  diIndex, diType, diValue0String }
	DESCRIPTION	"This trap is generated when set
			 diChangeValue0TrapID equal 67 and
			the value of diValue change from 1 to 0."
	::= 8259

    diChangeValue0-68	TRAP-TYPE
	ENTERPRISE	network-device
	VARIABLES	{ diValue, adminDateAndTime, adminNDTrapSeqNo,
			  diIndex, diType, diValue0String }
	DESCRIPTION	"This trap is generated when set
			 diChangeValue0TrapID equal 68 and
			the value of diValue change from 1 to 0."
	::= 8260

    diChangeValue0-69	TRAP-TYPE
	ENTERPRISE	network-device
	VARIABLES	{ diValue, adminDateAndTime, adminNDTrapSeqNo,
			  diIndex, diType, diValue0String }
	DESCRIPTION	"This trap is generated when set
			 diChangeValue0TrapID equal 69 and
			the value of diValue change from 1 to 0."
	::= 8261

    diChangeValue0-70	TRAP-TYPE
	ENTERPRISE	network-device
	VARIABLES	{ diValue, adminDateAndTime, adminNDTrapSeqNo,
			  diIndex, diType, diValue0String }
	DESCRIPTION	"This trap is generated when set
			 diChangeValue0TrapID equal 70 and
			the value of diValue change from 1 to 0."
	::= 8262

    diChangeValue0-71	TRAP-TYPE
	ENTERPRISE	network-device
	VARIABLES	{ diValue, adminDateAndTime, adminNDTrapSeqNo,
			  diIndex, diType, diValue0String }
	DESCRIPTION	"This trap is generated when set
			 diChangeValue0TrapID equal 71 and
			the value of diValue change from 1 to 0."
	::= 8263

    diChangeValue0-72	TRAP-TYPE
	ENTERPRISE	network-device
	VARIABLES	{ diValue, adminDateAndTime, adminNDTrapSeqNo,
			  diIndex, diType, diValue0String }
	DESCRIPTION	"This trap is generated when set
			 diChangeValue0TrapID equal 72 and
			the value of diValue change from 1 to 0."
	::= 8264

    diChangeValue0-73	TRAP-TYPE
	ENTERPRISE	network-device
	VARIABLES	{ diValue, adminDateAndTime, adminNDTrapSeqNo,
			  diIndex, diType, diValue0String }
	DESCRIPTION	"This trap is generated when set
			 diChangeValue0TrapID equal 73 and
			the value of diValue change from 1 to 0."
	::= 8265

    diChangeValue0-74	TRAP-TYPE
	ENTERPRISE	network-device
	VARIABLES	{ diValue, adminDateAndTime, adminNDTrapSeqNo,
			  diIndex, diType, diValue0String }
	DESCRIPTION	"This trap is generated when set
			 diChangeValue0TrapID equal 74 and
			the value of diValue change from 1 to 0."
	::= 8266

    diChangeValue0-75	TRAP-TYPE
	ENTERPRISE	network-device
	VARIABLES	{ diValue, adminDateAndTime, adminNDTrapSeqNo,
			  diIndex, diType, diValue0String }
	DESCRIPTION	"This trap is generated when set
			 diChangeValue0TrapID equal 75 and
			the value of diValue change from 1 to 0."
	::= 8267

    diChangeValue0-76	TRAP-TYPE
	ENTERPRISE	network-device
	VARIABLES	{ diValue, adminDateAndTime, adminNDTrapSeqNo,
			  diIndex, diType, diValue0String }
	DESCRIPTION	"This trap is generated when set
			 diChangeValue0TrapID equal 76 and
			the value of diValue change from 1 to 0."
	::= 8268

    diChangeValue0-77	TRAP-TYPE
	ENTERPRISE	network-device
	VARIABLES	{ diValue, adminDateAndTime, adminNDTrapSeqNo,
			  diIndex, diType, diValue0String }
	DESCRIPTION	"This trap is generated when set
			 diChangeValue0TrapID equal 77 and
			the value of diValue change from 1 to 0."
	::= 8269

    diChangeValue0-78	TRAP-TYPE
	ENTERPRISE	network-device
	VARIABLES	{ diValue, adminDateAndTime, adminNDTrapSeqNo,
			  diIndex, diType, diValue0String }
	DESCRIPTION	"This trap is generated when set
			 diChangeValue0TrapID equal 78 and
			the value of diValue change from 1 to 0."
	::= 8270

    diChangeValue0-79	TRAP-TYPE
	ENTERPRISE	network-device
	VARIABLES	{ diValue, adminDateAndTime, adminNDTrapSeqNo,
			  diIndex, diType, diValue0String }
	DESCRIPTION	"This trap is generated when set
			 diChangeValue0TrapID equal 79 and
			the value of diValue change from 1 to 0."
	::= 8271

    diChangeValue0-80	TRAP-TYPE
	ENTERPRISE	network-device
	VARIABLES	{ diValue, adminDateAndTime, adminNDTrapSeqNo,
			  diIndex, diType, diValue0String }
	DESCRIPTION	"This trap is generated when set
			 diChangeValue0TrapID equal 80 and
			the value of diValue change from 1 to 0."
	::= 8272

    diChangeValue0-81	TRAP-TYPE
	ENTERPRISE	network-device
	VARIABLES	{ diValue, adminDateAndTime, adminNDTrapSeqNo,
			  diIndex, diType, diValue0String }
	DESCRIPTION	"This trap is generated when set
			 diChangeValue0TrapID equal 81 and
			the value of diValue change from 1 to 0."
	::= 8273

    diChangeValue0-82	TRAP-TYPE
	ENTERPRISE	network-device
	VARIABLES	{ diValue, adminDateAndTime, adminNDTrapSeqNo,
			  diIndex, diType, diValue0String }
	DESCRIPTION	"This trap is generated when set
			 diChangeValue0TrapID equal 82 and
			the value of diValue change from 1 to 0."
	::= 8274

    diChangeValue0-83	TRAP-TYPE
	ENTERPRISE	network-device
	VARIABLES	{ diValue, adminDateAndTime, adminNDTrapSeqNo,
			  diIndex, diType, diValue0String }
	DESCRIPTION	"This trap is generated when set
			 diChangeValue0TrapID equal 83 and
			the value of diValue change from 1 to 0."
	::= 8275

    diChangeValue0-84	TRAP-TYPE
	ENTERPRISE	network-device
	VARIABLES	{ diValue, adminDateAndTime, adminNDTrapSeqNo,
			  diIndex, diType, diValue0String }
	DESCRIPTION	"This trap is generated when set
			 diChangeValue0TrapID equal 84 and
			the value of diValue change from 1 to 0."
	::= 8276

    diChangeValue0-85	TRAP-TYPE
	ENTERPRISE	network-device
	VARIABLES	{ diValue, adminDateAndTime, adminNDTrapSeqNo,
			  diIndex, diType, diValue0String }
	DESCRIPTION	"This trap is generated when set
			 diChangeValue0TrapID equal 85 and
			the value of diValue change from 1 to 0."
	::= 8277

    diChangeValue0-86	TRAP-TYPE
	ENTERPRISE	network-device
	VARIABLES	{ diValue, adminDateAndTime, adminNDTrapSeqNo,
			  diIndex, diType, diValue0String }
	DESCRIPTION	"This trap is generated when set
			 diChangeValue0TrapID equal 86 and
			the value of diValue change from 1 to 0."
	::= 8278

    diChangeValue0-87	TRAP-TYPE
	ENTERPRISE	network-device
	VARIABLES	{ diValue, adminDateAndTime, adminNDTrapSeqNo,
			  diIndex, diType, diValue0String }
	DESCRIPTION	"This trap is generated when set
			 diChangeValue0TrapID equal 87 and
			the value of diValue change from 1 to 0."
	::= 8279

    diChangeValue0-88	TRAP-TYPE
	ENTERPRISE	network-device
	VARIABLES	{ diValue, adminDateAndTime, adminNDTrapSeqNo,
			  diIndex, diType, diValue0String }
	DESCRIPTION	"This trap is generated when set
			 diChangeValue0TrapID equal 88 and
			the value of diValue change from 1 to 0."
	::= 8280

    diChangeValue0-89	TRAP-TYPE
	ENTERPRISE	network-device
	VARIABLES	{ diValue, adminDateAndTime, adminNDTrapSeqNo,
			  diIndex, diType, diValue0String }
	DESCRIPTION	"This trap is generated when set
			 diChangeValue0TrapID equal 89 and
			the value of diValue change from 1 to 0."
	::= 8281

    diChangeValue0-90	TRAP-TYPE
	ENTERPRISE	network-device
	VARIABLES	{ diValue, adminDateAndTime, adminNDTrapSeqNo,
			  diIndex, diType, diValue0String }
	DESCRIPTION	"This trap is generated when set
			 diChangeValue0TrapID equal 90 and
			the value of diValue change from 1 to 0."
	::= 8282

    diChangeValue0-91	TRAP-TYPE
	ENTERPRISE	network-device
	VARIABLES	{ diValue, adminDateAndTime, adminNDTrapSeqNo,
			  diIndex, diType, diValue0String }
	DESCRIPTION	"This trap is generated when set
			 diChangeValue0TrapID equal 91 and
			the value of diValue change from 1 to 0."
	::= 8283

    diChangeValue0-92	TRAP-TYPE
	ENTERPRISE	network-device
	VARIABLES	{ diValue, adminDateAndTime, adminNDTrapSeqNo,
			  diIndex, diType, diValue0String }
	DESCRIPTION	"This trap is generated when set
			 diChangeValue0TrapID equal 92 and
			the value of diValue change from 1 to 0."
	::= 8284

    diChangeValue0-93	TRAP-TYPE
	ENTERPRISE	network-device
	VARIABLES	{ diValue, adminDateAndTime, adminNDTrapSeqNo,
			  diIndex, diType, diValue0String }
	DESCRIPTION	"This trap is generated when set
			 diChangeValue0TrapID equal 93 and
			the value of diValue change from 1 to 0."
	::= 8285

    diChangeValue0-94	TRAP-TYPE
	ENTERPRISE	network-device
	VARIABLES	{ diValue, adminDateAndTime, adminNDTrapSeqNo,
			  diIndex, diType, diValue0String }
	DESCRIPTION	"This trap is generated when set
			 diChangeValue0TrapID equal 94 and
			the value of diValue change from 1 to 0."
	::= 8286

    diChangeValue0-95	TRAP-TYPE
	ENTERPRISE	network-device
	VARIABLES	{ diValue, adminDateAndTime, adminNDTrapSeqNo,
			  diIndex, diType, diValue0String }
	DESCRIPTION	"This trap is generated when set
			 diChangeValue0TrapID equal 95 and
			the value of diValue change from 1 to 0."
	::= 8287

    diChangeValue0-96	TRAP-TYPE
	ENTERPRISE	network-device
	VARIABLES	{ diValue, adminDateAndTime, adminNDTrapSeqNo,
			  diIndex, diType, diValue0String }
	DESCRIPTION	"This trap is generated when set
			 diChangeValue0TrapID equal 96 and
			the value of diValue change from 1 to 0."
	::= 8288

    diChangeValue0-97	TRAP-TYPE
	ENTERPRISE	network-device
	VARIABLES	{ diValue, adminDateAndTime, adminNDTrapSeqNo,
			  diIndex, diType, diValue0String }
	DESCRIPTION	"This trap is generated when set
			 diChangeValue0TrapID equal 97 and
			the value of diValue change from 1 to 0."
	::= 8289

    diChangeValue0-98	TRAP-TYPE
	ENTERPRISE	network-device
	VARIABLES	{ diValue, adminDateAndTime, adminNDTrapSeqNo,
			  diIndex, diType, diValue0String }
	DESCRIPTION	"This trap is generated when set
			 diChangeValue0TrapID equal 98 and
			the value of diValue change from 1 to 0."
	::= 8290

    diChangeValue0-99	TRAP-TYPE
	ENTERPRISE	network-device
	VARIABLES	{ diValue, adminDateAndTime, adminNDTrapSeqNo,
			  diIndex, diType, diValue0String }
	DESCRIPTION	"This trap is generated when set
			 diChangeValue0TrapID equal 99 and
			the value of diValue change from 1 to 0."
	::= 8291

    diChangeValue0-100	TRAP-TYPE
	ENTERPRISE	network-device
	VARIABLES	{ diValue, adminDateAndTime, adminNDTrapSeqNo,
			  diIndex, diType, diValue0String }
	DESCRIPTION	"This trap is generated when set
			 diChangeValue0TrapID equal 100 and
			the value of diValue change from 1 to 0."
	::= 8292

    diChangeValue0-101	TRAP-TYPE
	ENTERPRISE	network-device
	VARIABLES	{ diValue, adminDateAndTime, adminNDTrapSeqNo,
			  diIndex, diType, diValue0String }
	DESCRIPTION	"This trap is generated when set
			 diChangeValue0TrapID equal 101 and
			the value of diValue change from 1 to 0."
	::= 8293

    diChangeValue0-102	TRAP-TYPE
	ENTERPRISE	network-device
	VARIABLES	{ diValue, adminDateAndTime, adminNDTrapSeqNo,
			  diIndex, diType, diValue0String }
	DESCRIPTION	"This trap is generated when set
			 diChangeValue0TrapID equal 102 and
			the value of diValue change from 1 to 0."
	::= 8294

    diChangeValue0-103	TRAP-TYPE
	ENTERPRISE	network-device
	VARIABLES	{ diValue, adminDateAndTime, adminNDTrapSeqNo,
			  diIndex, diType, diValue0String }
	DESCRIPTION	"This trap is generated when set
			 diChangeValue0TrapID equal 103 and
			the value of diValue change from 1 to 0."
	::= 8295

    diChangeValue0-104	TRAP-TYPE
	ENTERPRISE	network-device
	VARIABLES	{ diValue, adminDateAndTime, adminNDTrapSeqNo,
			  diIndex, diType, diValue0String }
	DESCRIPTION	"This trap is generated when set
			 diChangeValue0TrapID equal 104 and
			the value of diValue change from 1 to 0."
	::= 8296

    diChangeValue0-105	TRAP-TYPE
	ENTERPRISE	network-device
	VARIABLES	{ diValue, adminDateAndTime, adminNDTrapSeqNo,
			  diIndex, diType, diValue0String }
	DESCRIPTION	"This trap is generated when set
			 diChangeValue0TrapID equal 105 and
			the value of diValue change from 1 to 0."
	::= 8297

    diChangeValue0-106	TRAP-TYPE
	ENTERPRISE	network-device
	VARIABLES	{ diValue, adminDateAndTime, adminNDTrapSeqNo,
			  diIndex, diType, diValue0String }
	DESCRIPTION	"This trap is generated when set
			 diChangeValue0TrapID equal 106 and
			the value of diValue change from 1 to 0."
	::= 8298

    diChangeValue0-107	TRAP-TYPE
	ENTERPRISE	network-device
	VARIABLES	{ diValue, adminDateAndTime, adminNDTrapSeqNo,
			  diIndex, diType, diValue0String }
	DESCRIPTION	"This trap is generated when set
			 diChangeValue0TrapID equal 107 and
			the value of diValue change from 1 to 0."
	::= 8299

    diChangeValue0-108	TRAP-TYPE
	ENTERPRISE	network-device
	VARIABLES	{ diValue, adminDateAndTime, adminNDTrapSeqNo,
			  diIndex, diType, diValue0String }
	DESCRIPTION	"This trap is generated when set
			 diChangeValue0TrapID equal 108 and
			the value of diValue change from 1 to 0."
	::= 8300

    diChangeValue0-109	TRAP-TYPE
	ENTERPRISE	network-device
	VARIABLES	{ diValue, adminDateAndTime, adminNDTrapSeqNo,
			  diIndex, diType, diValue0String }
	DESCRIPTION	"This trap is generated when set
			 diChangeValue0TrapID equal 109 and
			the value of diValue change from 1 to 0."
	::= 8301

    diChangeValue0-110	TRAP-TYPE
	ENTERPRISE	network-device
	VARIABLES	{ diValue, adminDateAndTime, adminNDTrapSeqNo,
			  diIndex, diType, diValue0String }
	DESCRIPTION	"This trap is generated when set
			 diChangeValue0TrapID equal 110 and
			the value of diValue change from 1 to 0."
	::= 8302

    diChangeValue0-111	TRAP-TYPE
	ENTERPRISE	network-device
	VARIABLES	{ diValue, adminDateAndTime, adminNDTrapSeqNo,
			  diIndex, diType, diValue0String }
	DESCRIPTION	"This trap is generated when set
			 diChangeValue0TrapID equal 111 and
			the value of diValue change from 1 to 0."
	::= 8303

    diChangeValue0-112	TRAP-TYPE
	ENTERPRISE	network-device
	VARIABLES	{ diValue, adminDateAndTime, adminNDTrapSeqNo,
			  diIndex, diType, diValue0String }
	DESCRIPTION	"This trap is generated when set
			 diChangeValue0TrapID equal 112 and
			the value of diValue change from 1 to 0."
	::= 8304

    diChangeValue0-113	TRAP-TYPE
	ENTERPRISE	network-device
	VARIABLES	{ diValue, adminDateAndTime, adminNDTrapSeqNo,
			  diIndex, diType, diValue0String }
	DESCRIPTION	"This trap is generated when set
			 diChangeValue0TrapID equal 113 and
			the value of diValue change from 1 to 0."
	::= 8305

    diChangeValue0-114	TRAP-TYPE
	ENTERPRISE	network-device
	VARIABLES	{ diValue, adminDateAndTime, adminNDTrapSeqNo,
			  diIndex, diType, diValue0String }
	DESCRIPTION	"This trap is generated when set
			 diChangeValue0TrapID equal 114 and
			the value of diValue change from 1 to 0."
	::= 8306

    diChangeValue0-115	TRAP-TYPE
	ENTERPRISE	network-device
	VARIABLES	{ diValue, adminDateAndTime, adminNDTrapSeqNo,
			  diIndex, diType, diValue0String }
	DESCRIPTION	"This trap is generated when set
			 diChangeValue0TrapID equal 115 and
			the value of diValue change from 1 to 0."
	::= 8307

    diChangeValue0-116	TRAP-TYPE
	ENTERPRISE	network-device
	VARIABLES	{ diValue, adminDateAndTime, adminNDTrapSeqNo,
			  diIndex, diType, diValue0String }
	DESCRIPTION	"This trap is generated when set
			 diChangeValue0TrapID equal 116 and
			the value of diValue change from 1 to 0."
	::= 8308

    diChangeValue0-117	TRAP-TYPE
	ENTERPRISE	network-device
	VARIABLES	{ diValue, adminDateAndTime, adminNDTrapSeqNo,
			  diIndex, diType, diValue0String }
	DESCRIPTION	"This trap is generated when set
			 diChangeValue0TrapID equal 117 and
			the value of diValue change from 1 to 0."
	::= 8309

    diChangeValue0-118	TRAP-TYPE
	ENTERPRISE	network-device
	VARIABLES	{ diValue, adminDateAndTime, adminNDTrapSeqNo,
			  diIndex, diType, diValue0String }
	DESCRIPTION	"This trap is generated when set
			 diChangeValue0TrapID equal 118 and
			the value of diValue change from 1 to 0."
	::= 8310

    diChangeValue0-119	TRAP-TYPE
	ENTERPRISE	network-device
	VARIABLES	{ diValue, adminDateAndTime, adminNDTrapSeqNo,
			  diIndex, diType, diValue0String }
	DESCRIPTION	"This trap is generated when set
			 diChangeValue0TrapID equal 119 and
			the value of diValue change from 1 to 0."
	::= 8311

    diChangeValue0-120	TRAP-TYPE
	ENTERPRISE	network-device
	VARIABLES	{ diValue, adminDateAndTime, adminNDTrapSeqNo,
			  diIndex, diType, diValue0String }
	DESCRIPTION	"This trap is generated when set
			 diChangeValue0TrapID equal 120 and
			the value of diValue change from 1 to 0."
	::= 8312

    diChangeValue0-121	TRAP-TYPE
	ENTERPRISE	network-device
	VARIABLES	{ diValue, adminDateAndTime, adminNDTrapSeqNo,
			  diIndex, diType, diValue0String }
	DESCRIPTION	"This trap is generated when set
			 diChangeValue0TrapID equal 121 and
			the value of diValue change from 1 to 0."
	::= 8313

    diChangeValue0-122	TRAP-TYPE
	ENTERPRISE	network-device
	VARIABLES	{ diValue, adminDateAndTime, adminNDTrapSeqNo,
			  diIndex, diType, diValue0String }
	DESCRIPTION	"This trap is generated when set
			 diChangeValue0TrapID equal 122 and
			the value of diValue change from 1 to 0."
	::= 8314

    diChangeValue0-123	TRAP-TYPE
	ENTERPRISE	network-device
	VARIABLES	{ diValue, adminDateAndTime, adminNDTrapSeqNo,
			  diIndex, diType, diValue0String }
	DESCRIPTION	"This trap is generated when set
			 diChangeValue0TrapID equal 123 and
			the value of diValue change from 1 to 0."
	::= 8315

    diChangeValue0-124	TRAP-TYPE
	ENTERPRISE	network-device
	VARIABLES	{ diValue, adminDateAndTime, adminNDTrapSeqNo,
			  diIndex, diType, diValue0String }
	DESCRIPTION	"This trap is generated when set
			 diChangeValue0TrapID equal 124 and
			the value of diValue change from 1 to 0."
	::= 8316

    diChangeValue0-125	TRAP-TYPE
	ENTERPRISE	network-device
	VARIABLES	{ diValue, adminDateAndTime, adminNDTrapSeqNo,
			  diIndex, diType, diValue0String }
	DESCRIPTION	"This trap is generated when set
			 diChangeValue0TrapID equal 125 and
			the value of diValue change from 1 to 0."
	::= 8317

    diChangeValue0-126	TRAP-TYPE
	ENTERPRISE	network-device
	VARIABLES	{ diValue, adminDateAndTime, adminNDTrapSeqNo,
			  diIndex, diType, diValue0String }
	DESCRIPTION	"This trap is generated when set
			 diChangeValue0TrapID equal 126 and
			the value of diValue change from 1 to 0."
	::= 8318

    diChangeValue0-127	TRAP-TYPE
	ENTERPRISE	network-device
	VARIABLES	{ diValue, adminDateAndTime, adminNDTrapSeqNo,
			  diIndex, diType, diValue0String }
	DESCRIPTION	"This trap is generated when set
			 diChangeValue0TrapID equal 127 and
			the value of diValue change from 1 to 0."
	::= 8319

    diValue0-1		TRAP-TYPE
	ENTERPRISE	network-device
	VARIABLES	{ diValue, adminDateAndTime, adminNDTrapSeqNo,
			  diIndex, diType, diValue0String }
	DESCRIPTION	"This trap is generated when set
			 diValue0TrapID equal 1 and
			while the value of diValue is 0."
	::= 8705

    diValue0-2		TRAP-TYPE
	ENTERPRISE	network-device
	VARIABLES	{ diValue, adminDateAndTime, adminNDTrapSeqNo,
			  diIndex, diType, diValue0String }
	DESCRIPTION	"This trap is generated when set
			 diValue0TrapID equal 2 and
			while the value of diValue is 0."
	::= 8706

    diValue0-3		TRAP-TYPE
	ENTERPRISE	network-device
	VARIABLES	{ diValue, adminDateAndTime, adminNDTrapSeqNo,
			  diIndex, diType, diValue0String }
	DESCRIPTION	"This trap is generated when set
			 diValue0TrapID equal 3 and
			while the value of diValue is 0."
	::= 8707

    diValue0-4		TRAP-TYPE
	ENTERPRISE	network-device
	VARIABLES	{ diValue, adminDateAndTime, adminNDTrapSeqNo,
			  diIndex, diType, diValue0String }
	DESCRIPTION	"This trap is generated when set
			 diValue0TrapID equal 4 and
			while the value of diValue is 0."
	::= 8708

    diValue0-5		TRAP-TYPE
	ENTERPRISE	network-device
	VARIABLES	{ diValue, adminDateAndTime, adminNDTrapSeqNo,
			  diIndex, diType, diValue0String }
	DESCRIPTION	"This trap is generated when set
			 diValue0TrapID equal 5 and
			while the value of diValue is 0."
	::= 8709

    diValue0-6		TRAP-TYPE
	ENTERPRISE	network-device
	VARIABLES	{ diValue, adminDateAndTime, adminNDTrapSeqNo,
			  diIndex, diType, diValue0String }
	DESCRIPTION	"This trap is generated when set
			 diValue0TrapID equal 6 and
			while the value of diValue is 0."
	::= 8710

    diValue0-7		TRAP-TYPE
	ENTERPRISE	network-device
	VARIABLES	{ diValue, adminDateAndTime, adminNDTrapSeqNo,
			  diIndex, diType, diValue0String }
	DESCRIPTION	"This trap is generated when set
			 diValue0TrapID equal 7 and
			while the value of diValue is 0."
	::= 8711

    diValue0-8		TRAP-TYPE
	ENTERPRISE	network-device
	VARIABLES	{ diValue, adminDateAndTime, adminNDTrapSeqNo,
			  diIndex, diType, diValue0String }
	DESCRIPTION	"This trap is generated when set
			 diValue0TrapID equal 8 and
			while the value of diValue is 0."
	::= 8712

    diValue0-9		TRAP-TYPE
	ENTERPRISE	network-device
	VARIABLES	{ diValue, adminDateAndTime, adminNDTrapSeqNo,
			  diIndex, diType, diValue0String }
	DESCRIPTION	"This trap is generated when set
			 diValue0TrapID equal 9 and
			while the value of diValue is 0."
	::= 8713

    diValue0-10		TRAP-TYPE
	ENTERPRISE	network-device
	VARIABLES	{ diValue, adminDateAndTime, adminNDTrapSeqNo,
			  diIndex, diType, diValue0String }
	DESCRIPTION	"This trap is generated when set
			 diValue0TrapID equal 10 and
			while the value of diValue is 0."
	::= 8714

    diValue0-11		TRAP-TYPE
	ENTERPRISE	network-device
	VARIABLES	{ diValue, adminDateAndTime, adminNDTrapSeqNo,
			  diIndex, diType, diValue0String }
	DESCRIPTION	"This trap is generated when set
			 diValue0TrapID equal 11 and
			while the value of diValue is 0."
	::= 8715

    diValue0-12		TRAP-TYPE
	ENTERPRISE	network-device
	VARIABLES	{ diValue, adminDateAndTime, adminNDTrapSeqNo,
			  diIndex, diType, diValue0String }
	DESCRIPTION	"This trap is generated when set
			 diValue0TrapID equal 12 and
			while the value of diValue is 0."
	::= 8716

    diValue0-13		TRAP-TYPE
	ENTERPRISE	network-device
	VARIABLES	{ diValue, adminDateAndTime, adminNDTrapSeqNo,
			  diIndex, diType, diValue0String }
	DESCRIPTION	"This trap is generated when set
			 diValue0TrapID equal 13 and
			while the value of diValue is 0."
	::= 8717

    diValue0-14		TRAP-TYPE
	ENTERPRISE	network-device
	VARIABLES	{ diValue, adminDateAndTime, adminNDTrapSeqNo,
			  diIndex, diType, diValue0String }
	DESCRIPTION	"This trap is generated when set
			 diValue0TrapID equal 14 and
			while the value of diValue is 0."
	::= 8718

    diValue0-15		TRAP-TYPE
	ENTERPRISE	network-device
	VARIABLES	{ diValue, adminDateAndTime, adminNDTrapSeqNo,
			  diIndex, diType, diValue0String }
	DESCRIPTION	"This trap is generated when set
			 diValue0TrapID equal 15 and
			while the value of diValue is 0."
	::= 8719

    diValue0-16		TRAP-TYPE
	ENTERPRISE	network-device
	VARIABLES	{ diValue, adminDateAndTime, adminNDTrapSeqNo,
			  diIndex, diType, diValue0String }
	DESCRIPTION	"This trap is generated when set
			 diValue0TrapID equal 16 and
			while the value of diValue is 0."
	::= 8720

    diValue0-17		TRAP-TYPE
	ENTERPRISE	network-device
	VARIABLES	{ diValue, adminDateAndTime, adminNDTrapSeqNo,
			  diIndex, diType, diValue0String }
	DESCRIPTION	"This trap is generated when set
			 diValue0TrapID equal 17 and
			while the value of diValue is 0."
	::= 8721

    diValue0-18		TRAP-TYPE
	ENTERPRISE	network-device
	VARIABLES	{ diValue, adminDateAndTime, adminNDTrapSeqNo,
			  diIndex, diType, diValue0String }
	DESCRIPTION	"This trap is generated when set
			 diValue0TrapID equal 18 and
			while the value of diValue is 0."
	::= 8722

    diValue0-19		TRAP-TYPE
	ENTERPRISE	network-device
	VARIABLES	{ diValue, adminDateAndTime, adminNDTrapSeqNo,
			  diIndex, diType, diValue0String }
	DESCRIPTION	"This trap is generated when set
			 diValue0TrapID equal 19 and
			while the value of diValue is 0."
	::= 8723

    diValue0-20		TRAP-TYPE
	ENTERPRISE	network-device
	VARIABLES	{ diValue, adminDateAndTime, adminNDTrapSeqNo,
			  diIndex, diType, diValue0String }
	DESCRIPTION	"This trap is generated when set
			 diValue0TrapID equal 20 and
			while the value of diValue is 0."
	::= 8724

    diValue0-21		TRAP-TYPE
	ENTERPRISE	network-device
	VARIABLES	{ diValue, adminDateAndTime, adminNDTrapSeqNo,
			  diIndex, diType, diValue0String }
	DESCRIPTION	"This trap is generated when set
			 diValue0TrapID equal 21 and
			while the value of diValue is 0."
	::= 8725

    diValue0-22		TRAP-TYPE
	ENTERPRISE	network-device
	VARIABLES	{ diValue, adminDateAndTime, adminNDTrapSeqNo,
			  diIndex, diType, diValue0String }
	DESCRIPTION	"This trap is generated when set
			 diValue0TrapID equal 22 and
			while the value of diValue is 0."
	::= 8726

    diValue0-23		TRAP-TYPE
	ENTERPRISE	network-device
	VARIABLES	{ diValue, adminDateAndTime, adminNDTrapSeqNo,
			  diIndex, diType, diValue0String }
	DESCRIPTION	"This trap is generated when set
			 diValue0TrapID equal 23 and
			while the value of diValue is 0."
	::= 8727

    diValue0-24		TRAP-TYPE
	ENTERPRISE	network-device
	VARIABLES	{ diValue, adminDateAndTime, adminNDTrapSeqNo,
			  diIndex, diType, diValue0String }
	DESCRIPTION	"This trap is generated when set
			 diValue0TrapID equal 24 and
			while the value of diValue is 0."
	::= 8728

    diValue0-25		TRAP-TYPE
	ENTERPRISE	network-device
	VARIABLES	{ diValue, adminDateAndTime, adminNDTrapSeqNo,
			  diIndex, diType, diValue0String }
	DESCRIPTION	"This trap is generated when set
			 diValue0TrapID equal 25 and
			while the value of diValue is 0."
	::= 8729

    diValue0-26		TRAP-TYPE
	ENTERPRISE	network-device
	VARIABLES	{ diValue, adminDateAndTime, adminNDTrapSeqNo,
			  diIndex, diType, diValue0String }
	DESCRIPTION	"This trap is generated when set
			 diValue0TrapID equal 26 and
			while the value of diValue is 0."
	::= 8730

    diValue0-27		TRAP-TYPE
	ENTERPRISE	network-device
	VARIABLES	{ diValue, adminDateAndTime, adminNDTrapSeqNo,
			  diIndex, diType, diValue0String }
	DESCRIPTION	"This trap is generated when set
			 diValue0TrapID equal 27 and
			while the value of diValue is 0."
	::= 8731

    diValue0-28		TRAP-TYPE
	ENTERPRISE	network-device
	VARIABLES	{ diValue, adminDateAndTime, adminNDTrapSeqNo,
			  diIndex, diType, diValue0String }
	DESCRIPTION	"This trap is generated when set
			 diValue0TrapID equal 28 and
			while the value of diValue is 0."
	::= 8732

    diValue0-29		TRAP-TYPE
	ENTERPRISE	network-device
	VARIABLES	{ diValue, adminDateAndTime, adminNDTrapSeqNo,
			  diIndex, diType, diValue0String }
	DESCRIPTION	"This trap is generated when set
			 diValue0TrapID equal 29 and
			while the value of diValue is 0."
	::= 8733

    diValue0-30		TRAP-TYPE
	ENTERPRISE	network-device
	VARIABLES	{ diValue, adminDateAndTime, adminNDTrapSeqNo,
			  diIndex, diType, diValue0String }
	DESCRIPTION	"This trap is generated when set
			 diValue0TrapID equal 30 and
			while the value of diValue is 0."
	::= 8734

    diValue0-31		TRAP-TYPE
	ENTERPRISE	network-device
	VARIABLES	{ diValue, adminDateAndTime, adminNDTrapSeqNo,
			  diIndex, diType, diValue0String }
	DESCRIPTION	"This trap is generated when set
			 diValue0TrapID equal 31 and
			while the value of diValue is 0."
	::= 8735

    diValue0-32		TRAP-TYPE
	ENTERPRISE	network-device
	VARIABLES	{ diValue, adminDateAndTime, adminNDTrapSeqNo,
			  diIndex, diType, diValue0String }
	DESCRIPTION	"This trap is generated when set
			 diValue0TrapID equal 32 and
			while the value of diValue is 0."
	::= 8736

    diValue0-33		TRAP-TYPE
	ENTERPRISE	network-device
	VARIABLES	{ diValue, adminDateAndTime, adminNDTrapSeqNo,
			  diIndex, diType, diValue0String }
	DESCRIPTION	"This trap is generated when set
			 diValue0TrapID equal 33 and
			while the value of diValue is 0."
	::= 8737

    diValue0-34		TRAP-TYPE
	ENTERPRISE	network-device
	VARIABLES	{ diValue, adminDateAndTime, adminNDTrapSeqNo,
			  diIndex, diType, diValue0String }
	DESCRIPTION	"This trap is generated when set
			 diValue0TrapID equal 34 and
			while the value of diValue is 0."
	::= 8738

    diValue0-35		TRAP-TYPE
	ENTERPRISE	network-device
	VARIABLES	{ diValue, adminDateAndTime, adminNDTrapSeqNo,
			  diIndex, diType, diValue0String }
	DESCRIPTION	"This trap is generated when set
			 diValue0TrapID equal 35 and
			while the value of diValue is 0."
	::= 8739

    diValue0-36		TRAP-TYPE
	ENTERPRISE	network-device
	VARIABLES	{ diValue, adminDateAndTime, adminNDTrapSeqNo,
			  diIndex, diType, diValue0String }
	DESCRIPTION	"This trap is generated when set
			 diValue0TrapID equal 36 and
			while the value of diValue is 0."
	::= 8740

    diValue0-37		TRAP-TYPE
	ENTERPRISE	network-device
	VARIABLES	{ diValue, adminDateAndTime, adminNDTrapSeqNo,
			  diIndex, diType, diValue0String }
	DESCRIPTION	"This trap is generated when set
			 diValue0TrapID equal 37 and
			while the value of diValue is 0."
	::= 8741

    diValue0-38		TRAP-TYPE
	ENTERPRISE	network-device
	VARIABLES	{ diValue, adminDateAndTime, adminNDTrapSeqNo,
			  diIndex, diType, diValue0String }
	DESCRIPTION	"This trap is generated when set
			 diValue0TrapID equal 38 and
			while the value of diValue is 0."
	::= 8742

    diValue0-39		TRAP-TYPE
	ENTERPRISE	network-device
	VARIABLES	{ diValue, adminDateAndTime, adminNDTrapSeqNo,
			  diIndex, diType, diValue0String }
	DESCRIPTION	"This trap is generated when set
			 diValue0TrapID equal 39 and
			while the value of diValue is 0."
	::= 8743

    diValue0-40		TRAP-TYPE
	ENTERPRISE	network-device
	VARIABLES	{ diValue, adminDateAndTime, adminNDTrapSeqNo,
			  diIndex, diType, diValue0String }
	DESCRIPTION	"This trap is generated when set
			 diValue0TrapID equal 40 and
			while the value of diValue is 0."
	::= 8744

    diValue0-41		TRAP-TYPE
	ENTERPRISE	network-device
	VARIABLES	{ diValue, adminDateAndTime, adminNDTrapSeqNo,
			  diIndex, diType, diValue0String }
	DESCRIPTION	"This trap is generated when set
			 diValue0TrapID equal 41 and
			while the value of diValue is 0."
	::= 8745

    diValue0-42		TRAP-TYPE
	ENTERPRISE	network-device
	VARIABLES	{ diValue, adminDateAndTime, adminNDTrapSeqNo,
			  diIndex, diType, diValue0String }
	DESCRIPTION	"This trap is generated when set
			 diValue0TrapID equal 42 and
			while the value of diValue is 0."
	::= 8746

    diValue0-43		TRAP-TYPE
	ENTERPRISE	network-device
	VARIABLES	{ diValue, adminDateAndTime, adminNDTrapSeqNo,
			  diIndex, diType, diValue0String }
	DESCRIPTION	"This trap is generated when set
			 diValue0TrapID equal 43 and
			while the value of diValue is 0."
	::= 8747

    diValue0-44		TRAP-TYPE
	ENTERPRISE	network-device
	VARIABLES	{ diValue, adminDateAndTime, adminNDTrapSeqNo,
			  diIndex, diType, diValue0String }
	DESCRIPTION	"This trap is generated when set
			 diValue0TrapID equal 44 and
			while the value of diValue is 0."
	::= 8748

    diValue0-45		TRAP-TYPE
	ENTERPRISE	network-device
	VARIABLES	{ diValue, adminDateAndTime, adminNDTrapSeqNo,
			  diIndex, diType, diValue0String }
	DESCRIPTION	"This trap is generated when set
			 diValue0TrapID equal 45 and
			while the value of diValue is 0."
	::= 8749

    diValue0-46		TRAP-TYPE
	ENTERPRISE	network-device
	VARIABLES	{ diValue, adminDateAndTime, adminNDTrapSeqNo,
			  diIndex, diType, diValue0String }
	DESCRIPTION	"This trap is generated when set
			 diValue0TrapID equal 46 and
			while the value of diValue is 0."
	::= 8750

    diValue0-47		TRAP-TYPE
	ENTERPRISE	network-device
	VARIABLES	{ diValue, adminDateAndTime, adminNDTrapSeqNo,
			  diIndex, diType, diValue0String }
	DESCRIPTION	"This trap is generated when set
			 diValue0TrapID equal 47 and
			while the value of diValue is 0."
	::= 8751

    diValue0-48		TRAP-TYPE
	ENTERPRISE	network-device
	VARIABLES	{ diValue, adminDateAndTime, adminNDTrapSeqNo,
			  diIndex, diType, diValue0String }
	DESCRIPTION	"This trap is generated when set
			 diValue0TrapID equal 48 and
			while the value of diValue is 0."
	::= 8752

    diValue0-49		TRAP-TYPE
	ENTERPRISE	network-device
	VARIABLES	{ diValue, adminDateAndTime, adminNDTrapSeqNo,
			  diIndex, diType, diValue0String }
	DESCRIPTION	"This trap is generated when set
			 diValue0TrapID equal 49 and
			while the value of diValue is 0."
	::= 8753

    diValue0-50		TRAP-TYPE
	ENTERPRISE	network-device
	VARIABLES	{ diValue, adminDateAndTime, adminNDTrapSeqNo,
			  diIndex, diType, diValue0String }
	DESCRIPTION	"This trap is generated when set
			 diValue0TrapID equal 50 and
			while the value of diValue is 0."
	::= 8754

    diValue0-51		TRAP-TYPE
	ENTERPRISE	network-device
	VARIABLES	{ diValue, adminDateAndTime, adminNDTrapSeqNo,
			  diIndex, diType, diValue0String }
	DESCRIPTION	"This trap is generated when set
			 diValue0TrapID equal 51 and
			while the value of diValue is 0."
	::= 8755

    diValue0-52		TRAP-TYPE
	ENTERPRISE	network-device
	VARIABLES	{ diValue, adminDateAndTime, adminNDTrapSeqNo,
			  diIndex, diType, diValue0String }
	DESCRIPTION	"This trap is generated when set
			 diValue0TrapID equal 52 and
			while the value of diValue is 0."
	::= 8756

    diValue0-53		TRAP-TYPE
	ENTERPRISE	network-device
	VARIABLES	{ diValue, adminDateAndTime, adminNDTrapSeqNo,
			  diIndex, diType, diValue0String }
	DESCRIPTION	"This trap is generated when set
			 diValue0TrapID equal 53 and
			while the value of diValue is 0."
	::= 8757

    diValue0-54		TRAP-TYPE
	ENTERPRISE	network-device
	VARIABLES	{ diValue, adminDateAndTime, adminNDTrapSeqNo,
			  diIndex, diType, diValue0String }
	DESCRIPTION	"This trap is generated when set
			 diValue0TrapID equal 54 and
			while the value of diValue is 0."
	::= 8758

    diValue0-55		TRAP-TYPE
	ENTERPRISE	network-device
	VARIABLES	{ diValue, adminDateAndTime, adminNDTrapSeqNo,
			  diIndex, diType, diValue0String }
	DESCRIPTION	"This trap is generated when set
			 diValue0TrapID equal 55 and
			while the value of diValue is 0."
	::= 8759

    diValue0-56		TRAP-TYPE
	ENTERPRISE	network-device
	VARIABLES	{ diValue, adminDateAndTime, adminNDTrapSeqNo,
			  diIndex, diType, diValue0String }
	DESCRIPTION	"This trap is generated when set
			 diValue0TrapID equal 56 and
			while the value of diValue is 0."
	::= 8760

    diValue0-57		TRAP-TYPE
	ENTERPRISE	network-device
	VARIABLES	{ diValue, adminDateAndTime, adminNDTrapSeqNo,
			  diIndex, diType, diValue0String }
	DESCRIPTION	"This trap is generated when set
			 diValue0TrapID equal 57 and
			while the value of diValue is 0."
	::= 8761

    diValue0-58		TRAP-TYPE
	ENTERPRISE	network-device
	VARIABLES	{ diValue, adminDateAndTime, adminNDTrapSeqNo,
			  diIndex, diType, diValue0String }
	DESCRIPTION	"This trap is generated when set
			 diValue0TrapID equal 58 and
			while the value of diValue is 0."
	::= 8762

    diValue0-59		TRAP-TYPE
	ENTERPRISE	network-device
	VARIABLES	{ diValue, adminDateAndTime, adminNDTrapSeqNo,
			  diIndex, diType, diValue0String }
	DESCRIPTION	"This trap is generated when set
			 diValue0TrapID equal 59 and
			while the value of diValue is 0."
	::= 8763

    diValue0-60		TRAP-TYPE
	ENTERPRISE	network-device
	VARIABLES	{ diValue, adminDateAndTime, adminNDTrapSeqNo,
			  diIndex, diType, diValue0String }
	DESCRIPTION	"This trap is generated when set
			 diValue0TrapID equal 60 and
			while the value of diValue is 0."
	::= 8764

    diValue0-61		TRAP-TYPE
	ENTERPRISE	network-device
	VARIABLES	{ diValue, adminDateAndTime, adminNDTrapSeqNo,
			  diIndex, diType, diValue0String }
	DESCRIPTION	"This trap is generated when set
			 diValue0TrapID equal 61 and
			while the value of diValue is 0."
	::= 8765

    diValue0-62		TRAP-TYPE
	ENTERPRISE	network-device
	VARIABLES	{ diValue, adminDateAndTime, adminNDTrapSeqNo,
			  diIndex, diType, diValue0String }
	DESCRIPTION	"This trap is generated when set
			 diValue0TrapID equal 62 and
			while the value of diValue is 0."
	::= 8766

    diValue0-63		TRAP-TYPE
	ENTERPRISE	network-device
	VARIABLES	{ diValue, adminDateAndTime, adminNDTrapSeqNo,
			  diIndex, diType, diValue0String }
	DESCRIPTION	"This trap is generated when set
			 diValue0TrapID equal 63 and
			while the value of diValue is 0."
	::= 8767

    diValue0-64		TRAP-TYPE
	ENTERPRISE	network-device
	VARIABLES	{ diValue, adminDateAndTime, adminNDTrapSeqNo,
			  diIndex, diType, diValue0String }
	DESCRIPTION	"This trap is generated when set
			 diValue0TrapID equal 64 and
			while the value of diValue is 0."
	::= 8768

    diValue0-65		TRAP-TYPE
	ENTERPRISE	network-device
	VARIABLES	{ diValue, adminDateAndTime, adminNDTrapSeqNo,
			  diIndex, diType, diValue0String }
	DESCRIPTION	"This trap is generated when set
			 diValue0TrapID equal 65 and
			while the value of diValue is 0."
	::= 8769

    diValue0-66		TRAP-TYPE
	ENTERPRISE	network-device
	VARIABLES	{ diValue, adminDateAndTime, adminNDTrapSeqNo,
			  diIndex, diType, diValue0String }
	DESCRIPTION	"This trap is generated when set
			 diValue0TrapID equal 66 and
			while the value of diValue is 0."
	::= 8770

    diValue0-67		TRAP-TYPE
	ENTERPRISE	network-device
	VARIABLES	{ diValue, adminDateAndTime, adminNDTrapSeqNo,
			  diIndex, diType, diValue0String }
	DESCRIPTION	"This trap is generated when set
			 diValue0TrapID equal 67 and
			while the value of diValue is 0."
	::= 8771

    diValue0-68		TRAP-TYPE
	ENTERPRISE	network-device
	VARIABLES	{ diValue, adminDateAndTime, adminNDTrapSeqNo,
			  diIndex, diType, diValue0String }
	DESCRIPTION	"This trap is generated when set
			 diValue0TrapID equal 68 and
			while the value of diValue is 0."
	::= 8772

    diValue0-69		TRAP-TYPE
	ENTERPRISE	network-device
	VARIABLES	{ diValue, adminDateAndTime, adminNDTrapSeqNo,
			  diIndex, diType, diValue0String }
	DESCRIPTION	"This trap is generated when set
			 diValue0TrapID equal 69 and
			while the value of diValue is 0."
	::= 8773

    diValue0-70		TRAP-TYPE
	ENTERPRISE	network-device
	VARIABLES	{ diValue, adminDateAndTime, adminNDTrapSeqNo,
			  diIndex, diType, diValue0String }
	DESCRIPTION	"This trap is generated when set
			 diValue0TrapID equal 70 and
			while the value of diValue is 0."
	::= 8774

    diValue0-71		TRAP-TYPE
	ENTERPRISE	network-device
	VARIABLES	{ diValue, adminDateAndTime, adminNDTrapSeqNo,
			  diIndex, diType, diValue0String }
	DESCRIPTION	"This trap is generated when set
			 diValue0TrapID equal 71 and
			while the value of diValue is 0."
	::= 8775

    diValue0-72		TRAP-TYPE
	ENTERPRISE	network-device
	VARIABLES	{ diValue, adminDateAndTime, adminNDTrapSeqNo,
			  diIndex, diType, diValue0String }
	DESCRIPTION	"This trap is generated when set
			 diValue0TrapID equal 72 and
			while the value of diValue is 0."
	::= 8776

    diValue0-73		TRAP-TYPE
	ENTERPRISE	network-device
	VARIABLES	{ diValue, adminDateAndTime, adminNDTrapSeqNo,
			  diIndex, diType, diValue0String }
	DESCRIPTION	"This trap is generated when set
			 diValue0TrapID equal 73 and
			while the value of diValue is 0."
	::= 8777

    diValue0-74		TRAP-TYPE
	ENTERPRISE	network-device
	VARIABLES	{ diValue, adminDateAndTime, adminNDTrapSeqNo,
			  diIndex, diType, diValue0String }
	DESCRIPTION	"This trap is generated when set
			 diValue0TrapID equal 74 and
			while the value of diValue is 0."
	::= 8778

    diValue0-75		TRAP-TYPE
	ENTERPRISE	network-device
	VARIABLES	{ diValue, adminDateAndTime, adminNDTrapSeqNo,
			  diIndex, diType, diValue0String }
	DESCRIPTION	"This trap is generated when set
			 diValue0TrapID equal 75 and
			while the value of diValue is 0."
	::= 8779

    diValue0-76		TRAP-TYPE
	ENTERPRISE	network-device
	VARIABLES	{ diValue, adminDateAndTime, adminNDTrapSeqNo,
			  diIndex, diType, diValue0String }
	DESCRIPTION	"This trap is generated when set
			 diValue0TrapID equal 76 and
			while the value of diValue is 0."
	::= 8780

    diValue0-77		TRAP-TYPE
	ENTERPRISE	network-device
	VARIABLES	{ diValue, adminDateAndTime, adminNDTrapSeqNo,
			  diIndex, diType, diValue0String }
	DESCRIPTION	"This trap is generated when set
			 diValue0TrapID equal 77 and
			while the value of diValue is 0."
	::= 8781

    diValue0-78		TRAP-TYPE
	ENTERPRISE	network-device
	VARIABLES	{ diValue, adminDateAndTime, adminNDTrapSeqNo,
			  diIndex, diType, diValue0String }
	DESCRIPTION	"This trap is generated when set
			 diValue0TrapID equal 78 and
			while the value of diValue is 0."
	::= 8782

    diValue0-79		TRAP-TYPE
	ENTERPRISE	network-device
	VARIABLES	{ diValue, adminDateAndTime, adminNDTrapSeqNo,
			  diIndex, diType, diValue0String }
	DESCRIPTION	"This trap is generated when set
			 diValue0TrapID equal 79 and
			while the value of diValue is 0."
	::= 8783

    diValue0-80		TRAP-TYPE
	ENTERPRISE	network-device
	VARIABLES	{ diValue, adminDateAndTime, adminNDTrapSeqNo,
			  diIndex, diType, diValue0String }
	DESCRIPTION	"This trap is generated when set
			 diValue0TrapID equal 80 and
			while the value of diValue is 0."
	::= 8784

    diValue0-81		TRAP-TYPE
	ENTERPRISE	network-device
	VARIABLES	{ diValue, adminDateAndTime, adminNDTrapSeqNo,
			  diIndex, diType, diValue0String }
	DESCRIPTION	"This trap is generated when set
			 diValue0TrapID equal 81 and
			while the value of diValue is 0."
	::= 8785

    diValue0-82		TRAP-TYPE
	ENTERPRISE	network-device
	VARIABLES	{ diValue, adminDateAndTime, adminNDTrapSeqNo,
			  diIndex, diType, diValue0String }
	DESCRIPTION	"This trap is generated when set
			 diValue0TrapID equal 82 and
			while the value of diValue is 0."
	::= 8786

    diValue0-83		TRAP-TYPE
	ENTERPRISE	network-device
	VARIABLES	{ diValue, adminDateAndTime, adminNDTrapSeqNo,
			  diIndex, diType, diValue0String }
	DESCRIPTION	"This trap is generated when set
			 diValue0TrapID equal 83 and
			while the value of diValue is 0."
	::= 8787

    diValue0-84		TRAP-TYPE
	ENTERPRISE	network-device
	VARIABLES	{ diValue, adminDateAndTime, adminNDTrapSeqNo,
			  diIndex, diType, diValue0String }
	DESCRIPTION	"This trap is generated when set
			 diValue0TrapID equal 84 and
			while the value of diValue is 0."
	::= 8788

    diValue0-85		TRAP-TYPE
	ENTERPRISE	network-device
	VARIABLES	{ diValue, adminDateAndTime, adminNDTrapSeqNo,
			  diIndex, diType, diValue0String }
	DESCRIPTION	"This trap is generated when set
			 diValue0TrapID equal 85 and
			while the value of diValue is 0."
	::= 8789

    diValue0-86		TRAP-TYPE
	ENTERPRISE	network-device
	VARIABLES	{ diValue, adminDateAndTime, adminNDTrapSeqNo,
			  diIndex, diType, diValue0String }
	DESCRIPTION	"This trap is generated when set
			 diValue0TrapID equal 86 and
			while the value of diValue is 0."
	::= 8790

    diValue0-87		TRAP-TYPE
	ENTERPRISE	network-device
	VARIABLES	{ diValue, adminDateAndTime, adminNDTrapSeqNo,
			  diIndex, diType, diValue0String }
	DESCRIPTION	"This trap is generated when set
			 diValue0TrapID equal 87 and
			while the value of diValue is 0."
	::= 8791

    diValue0-88		TRAP-TYPE
	ENTERPRISE	network-device
	VARIABLES	{ diValue, adminDateAndTime, adminNDTrapSeqNo,
			  diIndex, diType, diValue0String }
	DESCRIPTION	"This trap is generated when set
			 diValue0TrapID equal 88 and
			while the value of diValue is 0."
	::= 8792

    diValue0-89		TRAP-TYPE
	ENTERPRISE	network-device
	VARIABLES	{ diValue, adminDateAndTime, adminNDTrapSeqNo,
			  diIndex, diType, diValue0String }
	DESCRIPTION	"This trap is generated when set
			 diValue0TrapID equal 89 and
			while the value of diValue is 0."
	::= 8793

    diValue0-90		TRAP-TYPE
	ENTERPRISE	network-device
	VARIABLES	{ diValue, adminDateAndTime, adminNDTrapSeqNo,
			  diIndex, diType, diValue0String }
	DESCRIPTION	"This trap is generated when set
			 diValue0TrapID equal 90 and
			while the value of diValue is 0."
	::= 8794

    diValue0-91		TRAP-TYPE
	ENTERPRISE	network-device
	VARIABLES	{ diValue, adminDateAndTime, adminNDTrapSeqNo,
			  diIndex, diType, diValue0String }
	DESCRIPTION	"This trap is generated when set
			 diValue0TrapID equal 91 and
			while the value of diValue is 0."
	::= 8795

    diValue0-92		TRAP-TYPE
	ENTERPRISE	network-device
	VARIABLES	{ diValue, adminDateAndTime, adminNDTrapSeqNo,
			  diIndex, diType, diValue0String }
	DESCRIPTION	"This trap is generated when set
			 diValue0TrapID equal 92 and
			while the value of diValue is 0."
	::= 8796

    diValue0-93		TRAP-TYPE
	ENTERPRISE	network-device
	VARIABLES	{ diValue, adminDateAndTime, adminNDTrapSeqNo,
			  diIndex, diType, diValue0String }
	DESCRIPTION	"This trap is generated when set
			 diValue0TrapID equal 93 and
			while the value of diValue is 0."
	::= 8797

    diValue0-94		TRAP-TYPE
	ENTERPRISE	network-device
	VARIABLES	{ diValue, adminDateAndTime, adminNDTrapSeqNo,
			  diIndex, diType, diValue0String }
	DESCRIPTION	"This trap is generated when set
			 diValue0TrapID equal 94 and
			while the value of diValue is 0."
	::= 8798

    diValue0-95		TRAP-TYPE
	ENTERPRISE	network-device
	VARIABLES	{ diValue, adminDateAndTime, adminNDTrapSeqNo,
			  diIndex, diType, diValue0String }
	DESCRIPTION	"This trap is generated when set
			 diValue0TrapID equal 95 and
			while the value of diValue is 0."
	::= 8799

    diValue0-96		TRAP-TYPE
	ENTERPRISE	network-device
	VARIABLES	{ diValue, adminDateAndTime, adminNDTrapSeqNo,
			  diIndex, diType, diValue0String }
	DESCRIPTION	"This trap is generated when set
			 diValue0TrapID equal 96 and
			while the value of diValue is 0."
	::= 8800

    diValue0-97		TRAP-TYPE
	ENTERPRISE	network-device
	VARIABLES	{ diValue, adminDateAndTime, adminNDTrapSeqNo,
			  diIndex, diType, diValue0String }
	DESCRIPTION	"This trap is generated when set
			 diValue0TrapID equal 97 and
			while the value of diValue is 0."
	::= 8801

    diValue0-98		TRAP-TYPE
	ENTERPRISE	network-device
	VARIABLES	{ diValue, adminDateAndTime, adminNDTrapSeqNo,
			  diIndex, diType, diValue0String }
	DESCRIPTION	"This trap is generated when set
			 diValue0TrapID equal 98 and
			while the value of diValue is 0."
	::= 8802

    diValue0-99		TRAP-TYPE
	ENTERPRISE	network-device
	VARIABLES	{ diValue, adminDateAndTime, adminNDTrapSeqNo,
			  diIndex, diType, diValue0String }
	DESCRIPTION	"This trap is generated when set
			 diValue0TrapID equal 99 and
			while the value of diValue is 0."
	::= 8803

    diValue0-100		TRAP-TYPE
	ENTERPRISE	network-device
	VARIABLES	{ diValue, adminDateAndTime, adminNDTrapSeqNo,
			  diIndex, diType, diValue0String }
	DESCRIPTION	"This trap is generated when set
			 diValue0TrapID equal 100 and
			while the value of diValue is 0."
	::= 8804

    diValue0-101		TRAP-TYPE
	ENTERPRISE	network-device
	VARIABLES	{ diValue, adminDateAndTime, adminNDTrapSeqNo,
			  diIndex, diType, diValue0String }
	DESCRIPTION	"This trap is generated when set
			 diValue0TrapID equal 101 and
			while the value of diValue is 0."
	::= 8805

    diValue0-102		TRAP-TYPE
	ENTERPRISE	network-device
	VARIABLES	{ diValue, adminDateAndTime, adminNDTrapSeqNo,
			  diIndex, diType, diValue0String }
	DESCRIPTION	"This trap is generated when set
			 diValue0TrapID equal 102 and
			while the value of diValue is 0."
	::= 8806

    diValue0-103		TRAP-TYPE
	ENTERPRISE	network-device
	VARIABLES	{ diValue, adminDateAndTime, adminNDTrapSeqNo,
			  diIndex, diType, diValue0String }
	DESCRIPTION	"This trap is generated when set
			 diValue0TrapID equal 103 and
			while the value of diValue is 0."
	::= 8807

    diValue0-104		TRAP-TYPE
	ENTERPRISE	network-device
	VARIABLES	{ diValue, adminDateAndTime, adminNDTrapSeqNo,
			  diIndex, diType, diValue0String }
	DESCRIPTION	"This trap is generated when set
			 diValue0TrapID equal 104 and
			while the value of diValue is 0."
	::= 8808

    diValue0-105		TRAP-TYPE
	ENTERPRISE	network-device
	VARIABLES	{ diValue, adminDateAndTime, adminNDTrapSeqNo,
			  diIndex, diType, diValue0String }
	DESCRIPTION	"This trap is generated when set
			 diValue0TrapID equal 105 and
			while the value of diValue is 0."
	::= 8809

    diValue0-106		TRAP-TYPE
	ENTERPRISE	network-device
	VARIABLES	{ diValue, adminDateAndTime, adminNDTrapSeqNo,
			  diIndex, diType, diValue0String }
	DESCRIPTION	"This trap is generated when set
			 diValue0TrapID equal 106 and
			while the value of diValue is 0."
	::= 8810

    diValue0-107		TRAP-TYPE
	ENTERPRISE	network-device
	VARIABLES	{ diValue, adminDateAndTime, adminNDTrapSeqNo,
			  diIndex, diType, diValue0String }
	DESCRIPTION	"This trap is generated when set
			 diValue0TrapID equal 107 and
			while the value of diValue is 0."
	::= 8811

    diValue0-108		TRAP-TYPE
	ENTERPRISE	network-device
	VARIABLES	{ diValue, adminDateAndTime, adminNDTrapSeqNo,
			  diIndex, diType, diValue0String }
	DESCRIPTION	"This trap is generated when set
			 diValue0TrapID equal 108 and
			while the value of diValue is 0."
	::= 8812

    diValue0-109		TRAP-TYPE
	ENTERPRISE	network-device
	VARIABLES	{ diValue, adminDateAndTime, adminNDTrapSeqNo,
			  diIndex, diType, diValue0String }
	DESCRIPTION	"This trap is generated when set
			 diValue0TrapID equal 109 and
			while the value of diValue is 0."
	::= 8813

    diValue0-110		TRAP-TYPE
	ENTERPRISE	network-device
	VARIABLES	{ diValue, adminDateAndTime, adminNDTrapSeqNo,
			  diIndex, diType, diValue0String }
	DESCRIPTION	"This trap is generated when set
			 diValue0TrapID equal 110 and
			while the value of diValue is 0."
	::= 8814

    diValue0-111		TRAP-TYPE
	ENTERPRISE	network-device
	VARIABLES	{ diValue, adminDateAndTime, adminNDTrapSeqNo,
			  diIndex, diType, diValue0String }
	DESCRIPTION	"This trap is generated when set
			 diValue0TrapID equal 111 and
			while the value of diValue is 0."
	::= 8815

    diValue0-112		TRAP-TYPE
	ENTERPRISE	network-device
	VARIABLES	{ diValue, adminDateAndTime, adminNDTrapSeqNo,
			  diIndex, diType, diValue0String }
	DESCRIPTION	"This trap is generated when set
			 diValue0TrapID equal 112 and
			while the value of diValue is 0."
	::= 8816

    diValue0-113		TRAP-TYPE
	ENTERPRISE	network-device
	VARIABLES	{ diValue, adminDateAndTime, adminNDTrapSeqNo,
			  diIndex, diType, diValue0String }
	DESCRIPTION	"This trap is generated when set
			 diValue0TrapID equal 113 and
			while the value of diValue is 0."
	::= 8817

    diValue0-114		TRAP-TYPE
	ENTERPRISE	network-device
	VARIABLES	{ diValue, adminDateAndTime, adminNDTrapSeqNo,
			  diIndex, diType, diValue0String }
	DESCRIPTION	"This trap is generated when set
			 diValue0TrapID equal 114 and
			while the value of diValue is 0."
	::= 8818

    diValue0-115		TRAP-TYPE
	ENTERPRISE	network-device
	VARIABLES	{ diValue, adminDateAndTime, adminNDTrapSeqNo,
			  diIndex, diType, diValue0String }
	DESCRIPTION	"This trap is generated when set
			 diValue0TrapID equal 115 and
			while the value of diValue is 0."
	::= 8819

    diValue0-116		TRAP-TYPE
	ENTERPRISE	network-device
	VARIABLES	{ diValue, adminDateAndTime, adminNDTrapSeqNo,
			  diIndex, diType, diValue0String }
	DESCRIPTION	"This trap is generated when set
			 diValue0TrapID equal 116 and
			while the value of diValue is 0."
	::= 8820

    diValue0-117		TRAP-TYPE
	ENTERPRISE	network-device
	VARIABLES	{ diValue, adminDateAndTime, adminNDTrapSeqNo,
			  diIndex, diType, diValue0String }
	DESCRIPTION	"This trap is generated when set
			 diValue0TrapID equal 117 and
			while the value of diValue is 0."
	::= 8821

    diValue0-118		TRAP-TYPE
	ENTERPRISE	network-device
	VARIABLES	{ diValue, adminDateAndTime, adminNDTrapSeqNo,
			  diIndex, diType, diValue0String }
	DESCRIPTION	"This trap is generated when set
			 diValue0TrapID equal 118 and
			while the value of diValue is 0."
	::= 8822

    diValue0-119		TRAP-TYPE
	ENTERPRISE	network-device
	VARIABLES	{ diValue, adminDateAndTime, adminNDTrapSeqNo,
			  diIndex, diType, diValue0String }
	DESCRIPTION	"This trap is generated when set
			 diValue0TrapID equal 119 and
			while the value of diValue is 0."
	::= 8823

    diValue0-120		TRAP-TYPE
	ENTERPRISE	network-device
	VARIABLES	{ diValue, adminDateAndTime, adminNDTrapSeqNo,
			  diIndex, diType, diValue0String }
	DESCRIPTION	"This trap is generated when set
			 diValue0TrapID equal 120 and
			while the value of diValue is 0."
	::= 8824

    diValue0-121		TRAP-TYPE
	ENTERPRISE	network-device
	VARIABLES	{ diValue, adminDateAndTime, adminNDTrapSeqNo,
			  diIndex, diType, diValue0String }
	DESCRIPTION	"This trap is generated when set
			 diValue0TrapID equal 121 and
			while the value of diValue is 0."
	::= 8825

    diValue0-122		TRAP-TYPE
	ENTERPRISE	network-device
	VARIABLES	{ diValue, adminDateAndTime, adminNDTrapSeqNo,
			  diIndex, diType, diValue0String }
	DESCRIPTION	"This trap is generated when set
			 diValue0TrapID equal 122 and
			while the value of diValue is 0."
	::= 8826

    diValue0-123		TRAP-TYPE
	ENTERPRISE	network-device
	VARIABLES	{ diValue, adminDateAndTime, adminNDTrapSeqNo,
			  diIndex, diType, diValue0String }
	DESCRIPTION	"This trap is generated when set
			 diValue0TrapID equal 123 and
			while the value of diValue is 0."
	::= 8827

    diValue0-124		TRAP-TYPE
	ENTERPRISE	network-device
	VARIABLES	{ diValue, adminDateAndTime, adminNDTrapSeqNo,
			  diIndex, diType, diValue0String }
	DESCRIPTION	"This trap is generated when set
			 diValue0TrapID equal 124 and
			while the value of diValue is 0."
	::= 8828

    diValue0-125		TRAP-TYPE
	ENTERPRISE	network-device
	VARIABLES	{ diValue, adminDateAndTime, adminNDTrapSeqNo,
			  diIndex, diType, diValue0String }
	DESCRIPTION	"This trap is generated when set
			 diValue0TrapID equal 125 and
			while the value of diValue is 0."
	::= 8829

    diValue0-126		TRAP-TYPE
	ENTERPRISE	network-device
	VARIABLES	{ diValue, adminDateAndTime, adminNDTrapSeqNo,
			  diIndex, diType, diValue0String }
	DESCRIPTION	"This trap is generated when set
			 diValue0TrapID equal 126 and
			while the value of diValue is 0."
	::= 8830

    diValue0-127		TRAP-TYPE
	ENTERPRISE	network-device
	VARIABLES	{ diValue, adminDateAndTime, adminNDTrapSeqNo,
			  diIndex, diType, diValue0String }
	DESCRIPTION	"This trap is generated when set
			 diValue0TrapID equal 127 and
			while the value of diValue is 0."
	::= 8831

    diChangeValue1-1	TRAP-TYPE
	ENTERPRISE	network-device
	VARIABLES	{ diValue, adminDateAndTime, adminNDTrapSeqNo,
			  diIndex, diType, diValue1String }
	DESCRIPTION	"This trap is generated when set
			 diChangeValue1TrapID equal 1 and
			the value of diValue change from 0 to 1."
	::= 9217

    diChangeValue1-2	TRAP-TYPE
	ENTERPRISE	network-device
	VARIABLES	{ diValue, adminDateAndTime, adminNDTrapSeqNo,
			  diIndex, diType, diValue1String }
	DESCRIPTION	"This trap is generated when set
			 diChangeValue1TrapID equal 2 and
			the value of diValue change from 0 to 1."
	::= 9218

    diChangeValue1-3	TRAP-TYPE
	ENTERPRISE	network-device
	VARIABLES	{ diValue, adminDateAndTime, adminNDTrapSeqNo,
			  diIndex, diType, diValue1String }
	DESCRIPTION	"This trap is generated when set
			 diChangeValue1TrapID equal 3 and
			the value of diValue change from 0 to 1."
	::= 9219

    diChangeValue1-4	TRAP-TYPE
	ENTERPRISE	network-device
	VARIABLES	{ diValue, adminDateAndTime, adminNDTrapSeqNo,
			  diIndex, diType, diValue1String }
	DESCRIPTION	"This trap is generated when set
			 diChangeValue1TrapID equal 4 and
			the value of diValue change from 0 to 1."
	::= 9220

    diChangeValue1-5	TRAP-TYPE
	ENTERPRISE	network-device
	VARIABLES	{ diValue, adminDateAndTime, adminNDTrapSeqNo,
			  diIndex, diType, diValue1String }
	DESCRIPTION	"This trap is generated when set
			 diChangeValue1TrapID equal 5 and
			the value of diValue change from 0 to 1."
	::= 9221

    diChangeValue1-6	TRAP-TYPE
	ENTERPRISE	network-device
	VARIABLES	{ diValue, adminDateAndTime, adminNDTrapSeqNo,
			  diIndex, diType, diValue1String }
	DESCRIPTION	"This trap is generated when set
			 diChangeValue1TrapID equal 6 and
			the value of diValue change from 0 to 1."
	::= 9222

    diChangeValue1-7	TRAP-TYPE
	ENTERPRISE	network-device
	VARIABLES	{ diValue, adminDateAndTime, adminNDTrapSeqNo,
			  diIndex, diType, diValue1String }
	DESCRIPTION	"This trap is generated when set
			 diChangeValue1TrapID equal 7 and
			the value of diValue change from 0 to 1."
	::= 9223

    diChangeValue1-8	TRAP-TYPE
	ENTERPRISE	network-device
	VARIABLES	{ diValue, adminDateAndTime, adminNDTrapSeqNo,
			  diIndex, diType, diValue1String }
	DESCRIPTION	"This trap is generated when set
			 diChangeValue1TrapID equal 8 and
			the value of diValue change from 0 to 1."
	::= 9224

    diChangeValue1-9	TRAP-TYPE
	ENTERPRISE	network-device
	VARIABLES	{ diValue, adminDateAndTime, adminNDTrapSeqNo,
			  diIndex, diType, diValue1String }
	DESCRIPTION	"This trap is generated when set
			 diChangeValue1TrapID equal 9 and
			the value of diValue change from 0 to 1."
	::= 9225

    diChangeValue1-10	TRAP-TYPE
	ENTERPRISE	network-device
	VARIABLES	{ diValue, adminDateAndTime, adminNDTrapSeqNo,
			  diIndex, diType, diValue1String }
	DESCRIPTION	"This trap is generated when set
			 diChangeValue1TrapID equal 10 and
			the value of diValue change from 0 to 1."
	::= 9226

    diChangeValue1-11	TRAP-TYPE
	ENTERPRISE	network-device
	VARIABLES	{ diValue, adminDateAndTime, adminNDTrapSeqNo,
			  diIndex, diType, diValue1String }
	DESCRIPTION	"This trap is generated when set
			 diChangeValue1TrapID equal 11 and
			the value of diValue change from 0 to 1."
	::= 9227

    diChangeValue1-12	TRAP-TYPE
	ENTERPRISE	network-device
	VARIABLES	{ diValue, adminDateAndTime, adminNDTrapSeqNo,
			  diIndex, diType, diValue1String }
	DESCRIPTION	"This trap is generated when set
			 diChangeValue1TrapID equal 12 and
			the value of diValue change from 0 to 1."
	::= 9228

    diChangeValue1-13	TRAP-TYPE
	ENTERPRISE	network-device
	VARIABLES	{ diValue, adminDateAndTime, adminNDTrapSeqNo,
			  diIndex, diType, diValue1String }
	DESCRIPTION	"This trap is generated when set
			 diChangeValue1TrapID equal 13 and
			the value of diValue change from 0 to 1."
	::= 9229

    diChangeValue1-14	TRAP-TYPE
	ENTERPRISE	network-device
	VARIABLES	{ diValue, adminDateAndTime, adminNDTrapSeqNo,
			  diIndex, diType, diValue1String }
	DESCRIPTION	"This trap is generated when set
			 diChangeValue1TrapID equal 14 and
			the value of diValue change from 0 to 1."
	::= 9230

    diChangeValue1-15	TRAP-TYPE
	ENTERPRISE	network-device
	VARIABLES	{ diValue, adminDateAndTime, adminNDTrapSeqNo,
			  diIndex, diType, diValue1String }
	DESCRIPTION	"This trap is generated when set
			 diChangeValue1TrapID equal 15 and
			the value of diValue change from 0 to 1."
	::= 9231

    diChangeValue1-16	TRAP-TYPE
	ENTERPRISE	network-device
	VARIABLES	{ diValue, adminDateAndTime, adminNDTrapSeqNo,
			  diIndex, diType, diValue1String }
	DESCRIPTION	"This trap is generated when set
			 diChangeValue1TrapID equal 16 and
			the value of diValue change from 0 to 1."
	::= 9232

    diChangeValue1-17	TRAP-TYPE
	ENTERPRISE	network-device
	VARIABLES	{ diValue, adminDateAndTime, adminNDTrapSeqNo,
			  diIndex, diType, diValue1String }
	DESCRIPTION	"This trap is generated when set
			 diChangeValue1TrapID equal 17 and
			the value of diValue change from 0 to 1."
	::= 9233

    diChangeValue1-18	TRAP-TYPE
	ENTERPRISE	network-device
	VARIABLES	{ diValue, adminDateAndTime, adminNDTrapSeqNo,
			  diIndex, diType, diValue1String }
	DESCRIPTION	"This trap is generated when set
			 diChangeValue1TrapID equal 18 and
			the value of diValue change from 0 to 1."
	::= 9234

    diChangeValue1-19	TRAP-TYPE
	ENTERPRISE	network-device
	VARIABLES	{ diValue, adminDateAndTime, adminNDTrapSeqNo,
			  diIndex, diType, diValue1String }
	DESCRIPTION	"This trap is generated when set
			 diChangeValue1TrapID equal 19 and
			the value of diValue change from 0 to 1."
	::= 9235

    diChangeValue1-20	TRAP-TYPE
	ENTERPRISE	network-device
	VARIABLES	{ diValue, adminDateAndTime, adminNDTrapSeqNo,
			  diIndex, diType, diValue1String }
	DESCRIPTION	"This trap is generated when set
			 diChangeValue1TrapID equal 20 and
			the value of diValue change from 0 to 1."
	::= 9236

    diChangeValue1-21	TRAP-TYPE
	ENTERPRISE	network-device
	VARIABLES	{ diValue, adminDateAndTime, adminNDTrapSeqNo,
			  diIndex, diType, diValue1String }
	DESCRIPTION	"This trap is generated when set
			 diChangeValue1TrapID equal 21 and
			the value of diValue change from 0 to 1."
	::= 9237

    diChangeValue1-22	TRAP-TYPE
	ENTERPRISE	network-device
	VARIABLES	{ diValue, adminDateAndTime, adminNDTrapSeqNo,
			  diIndex, diType, diValue1String }
	DESCRIPTION	"This trap is generated when set
			 diChangeValue1TrapID equal 22 and
			the value of diValue change from 0 to 1."
	::= 9238

    diChangeValue1-23	TRAP-TYPE
	ENTERPRISE	network-device
	VARIABLES	{ diValue, adminDateAndTime, adminNDTrapSeqNo,
			  diIndex, diType, diValue1String }
	DESCRIPTION	"This trap is generated when set
			 diChangeValue1TrapID equal 23 and
			the value of diValue change from 0 to 1."
	::= 9239

    diChangeValue1-24	TRAP-TYPE
	ENTERPRISE	network-device
	VARIABLES	{ diValue, adminDateAndTime, adminNDTrapSeqNo,
			  diIndex, diType, diValue1String }
	DESCRIPTION	"This trap is generated when set
			 diChangeValue1TrapID equal 24 and
			the value of diValue change from 0 to 1."
	::= 9240

    diChangeValue1-25	TRAP-TYPE
	ENTERPRISE	network-device
	VARIABLES	{ diValue, adminDateAndTime, adminNDTrapSeqNo,
			  diIndex, diType, diValue1String }
	DESCRIPTION	"This trap is generated when set
			 diChangeValue1TrapID equal 25 and
			the value of diValue change from 0 to 1."
	::= 9241

    diChangeValue1-26	TRAP-TYPE
	ENTERPRISE	network-device
	VARIABLES	{ diValue, adminDateAndTime, adminNDTrapSeqNo,
			  diIndex, diType, diValue1String }
	DESCRIPTION	"This trap is generated when set
			 diChangeValue1TrapID equal 26 and
			the value of diValue change from 0 to 1."
	::= 9242

    diChangeValue1-27	TRAP-TYPE
	ENTERPRISE	network-device
	VARIABLES	{ diValue, adminDateAndTime, adminNDTrapSeqNo,
			  diIndex, diType, diValue1String }
	DESCRIPTION	"This trap is generated when set
			 diChangeValue1TrapID equal 27 and
			the value of diValue change from 0 to 1."
	::= 9243

    diChangeValue1-28	TRAP-TYPE
	ENTERPRISE	network-device
	VARIABLES	{ diValue, adminDateAndTime, adminNDTrapSeqNo,
			  diIndex, diType, diValue1String }
	DESCRIPTION	"This trap is generated when set
			 diChangeValue1TrapID equal 28 and
			the value of diValue change from 0 to 1."
	::= 9244

    diChangeValue1-29	TRAP-TYPE
	ENTERPRISE	network-device
	VARIABLES	{ diValue, adminDateAndTime, adminNDTrapSeqNo,
			  diIndex, diType, diValue1String }
	DESCRIPTION	"This trap is generated when set
			 diChangeValue1TrapID equal 29 and
			the value of diValue change from 0 to 1."
	::= 9245

    diChangeValue1-30	TRAP-TYPE
	ENTERPRISE	network-device
	VARIABLES	{ diValue, adminDateAndTime, adminNDTrapSeqNo,
			  diIndex, diType, diValue1String }
	DESCRIPTION	"This trap is generated when set
			 diChangeValue1TrapID equal 30 and
			the value of diValue change from 0 to 1."
	::= 9246

    diChangeValue1-31	TRAP-TYPE
	ENTERPRISE	network-device
	VARIABLES	{ diValue, adminDateAndTime, adminNDTrapSeqNo,
			  diIndex, diType, diValue1String }
	DESCRIPTION	"This trap is generated when set
			 diChangeValue1TrapID equal 31 and
			the value of diValue change from 0 to 1."
	::= 9247

    diChangeValue1-32	TRAP-TYPE
	ENTERPRISE	network-device
	VARIABLES	{ diValue, adminDateAndTime, adminNDTrapSeqNo,
			  diIndex, diType, diValue1String }
	DESCRIPTION	"This trap is generated when set
			 diChangeValue1TrapID equal 32 and
			the value of diValue change from 0 to 1."
	::= 9248

    diChangeValue1-33	TRAP-TYPE
	ENTERPRISE	network-device
	VARIABLES	{ diValue, adminDateAndTime, adminNDTrapSeqNo,
			  diIndex, diType, diValue1String }
	DESCRIPTION	"This trap is generated when set
			 diChangeValue1TrapID equal 33 and
			the value of diValue change from 0 to 1."
	::= 9249

    diChangeValue1-34	TRAP-TYPE
	ENTERPRISE	network-device
	VARIABLES	{ diValue, adminDateAndTime, adminNDTrapSeqNo,
			  diIndex, diType, diValue1String }
	DESCRIPTION	"This trap is generated when set
			 diChangeValue1TrapID equal 34 and
			the value of diValue change from 0 to 1."
	::= 9250

    diChangeValue1-35	TRAP-TYPE
	ENTERPRISE	network-device
	VARIABLES	{ diValue, adminDateAndTime, adminNDTrapSeqNo,
			  diIndex, diType, diValue1String }
	DESCRIPTION	"This trap is generated when set
			 diChangeValue1TrapID equal 35 and
			the value of diValue change from 0 to 1."
	::= 9251

    diChangeValue1-36	TRAP-TYPE
	ENTERPRISE	network-device
	VARIABLES	{ diValue, adminDateAndTime, adminNDTrapSeqNo,
			  diIndex, diType, diValue1String }
	DESCRIPTION	"This trap is generated when set
			 diChangeValue1TrapID equal 36 and
			the value of diValue change from 0 to 1."
	::= 9252

    diChangeValue1-37	TRAP-TYPE
	ENTERPRISE	network-device
	VARIABLES	{ diValue, adminDateAndTime, adminNDTrapSeqNo,
			  diIndex, diType, diValue1String }
	DESCRIPTION	"This trap is generated when set
			 diChangeValue1TrapID equal 37 and
			the value of diValue change from 0 to 1."
	::= 9253

    diChangeValue1-38	TRAP-TYPE
	ENTERPRISE	network-device
	VARIABLES	{ diValue, adminDateAndTime, adminNDTrapSeqNo,
			  diIndex, diType, diValue1String }
	DESCRIPTION	"This trap is generated when set
			 diChangeValue1TrapID equal 38 and
			the value of diValue change from 0 to 1."
	::= 9254

    diChangeValue1-39	TRAP-TYPE
	ENTERPRISE	network-device
	VARIABLES	{ diValue, adminDateAndTime, adminNDTrapSeqNo,
			  diIndex, diType, diValue1String }
	DESCRIPTION	"This trap is generated when set
			 diChangeValue1TrapID equal 39 and
			the value of diValue change from 0 to 1."
	::= 9255

    diChangeValue1-40	TRAP-TYPE
	ENTERPRISE	network-device
	VARIABLES	{ diValue, adminDateAndTime, adminNDTrapSeqNo,
			  diIndex, diType, diValue1String }
	DESCRIPTION	"This trap is generated when set
			 diChangeValue1TrapID equal 40 and
			the value of diValue change from 0 to 1."
	::= 9256

    diChangeValue1-41	TRAP-TYPE
	ENTERPRISE	network-device
	VARIABLES	{ diValue, adminDateAndTime, adminNDTrapSeqNo,
			  diIndex, diType, diValue1String }
	DESCRIPTION	"This trap is generated when set
			 diChangeValue1TrapID equal 41 and
			the value of diValue change from 0 to 1."
	::= 9257

    diChangeValue1-42	TRAP-TYPE
	ENTERPRISE	network-device
	VARIABLES	{ diValue, adminDateAndTime, adminNDTrapSeqNo,
			  diIndex, diType, diValue1String }
	DESCRIPTION	"This trap is generated when set
			 diChangeValue1TrapID equal 42 and
			the value of diValue change from 0 to 1."
	::= 9258

    diChangeValue1-43	TRAP-TYPE
	ENTERPRISE	network-device
	VARIABLES	{ diValue, adminDateAndTime, adminNDTrapSeqNo,
			  diIndex, diType, diValue1String }
	DESCRIPTION	"This trap is generated when set
			 diChangeValue1TrapID equal 43 and
			the value of diValue change from 0 to 1."
	::= 9259

    diChangeValue1-44	TRAP-TYPE
	ENTERPRISE	network-device
	VARIABLES	{ diValue, adminDateAndTime, adminNDTrapSeqNo,
			  diIndex, diType, diValue1String }
	DESCRIPTION	"This trap is generated when set
			 diChangeValue1TrapID equal 44 and
			the value of diValue change from 0 to 1."
	::= 9260

    diChangeValue1-45	TRAP-TYPE
	ENTERPRISE	network-device
	VARIABLES	{ diValue, adminDateAndTime, adminNDTrapSeqNo,
			  diIndex, diType, diValue1String }
	DESCRIPTION	"This trap is generated when set
			 diChangeValue1TrapID equal 45 and
			the value of diValue change from 0 to 1."
	::= 9261

    diChangeValue1-46	TRAP-TYPE
	ENTERPRISE	network-device
	VARIABLES	{ diValue, adminDateAndTime, adminNDTrapSeqNo,
			  diIndex, diType, diValue1String }
	DESCRIPTION	"This trap is generated when set
			 diChangeValue1TrapID equal 46 and
			the value of diValue change from 0 to 1."
	::= 9262

    diChangeValue1-47	TRAP-TYPE
	ENTERPRISE	network-device
	VARIABLES	{ diValue, adminDateAndTime, adminNDTrapSeqNo,
			  diIndex, diType, diValue1String }
	DESCRIPTION	"This trap is generated when set
			 diChangeValue1TrapID equal 47 and
			the value of diValue change from 0 to 1."
	::= 9263

    diChangeValue1-48	TRAP-TYPE
	ENTERPRISE	network-device
	VARIABLES	{ diValue, adminDateAndTime, adminNDTrapSeqNo,
			  diIndex, diType, diValue1String }
	DESCRIPTION	"This trap is generated when set
			 diChangeValue1TrapID equal 48 and
			the value of diValue change from 0 to 1."
	::= 9264

    diChangeValue1-49	TRAP-TYPE
	ENTERPRISE	network-device
	VARIABLES	{ diValue, adminDateAndTime, adminNDTrapSeqNo,
			  diIndex, diType, diValue1String }
	DESCRIPTION	"This trap is generated when set
			 diChangeValue1TrapID equal 49 and
			the value of diValue change from 0 to 1."
	::= 9265

    diChangeValue1-50	TRAP-TYPE
	ENTERPRISE	network-device
	VARIABLES	{ diValue, adminDateAndTime, adminNDTrapSeqNo,
			  diIndex, diType, diValue1String }
	DESCRIPTION	"This trap is generated when set
			 diChangeValue1TrapID equal 50 and
			the value of diValue change from 0 to 1."
	::= 9266

    diChangeValue1-51	TRAP-TYPE
	ENTERPRISE	network-device
	VARIABLES	{ diValue, adminDateAndTime, adminNDTrapSeqNo,
			  diIndex, diType, diValue1String }
	DESCRIPTION	"This trap is generated when set
			 diChangeValue1TrapID equal 51 and
			the value of diValue change from 0 to 1."
	::= 9267

    diChangeValue1-52	TRAP-TYPE
	ENTERPRISE	network-device
	VARIABLES	{ diValue, adminDateAndTime, adminNDTrapSeqNo,
			  diIndex, diType, diValue1String }
	DESCRIPTION	"This trap is generated when set
			 diChangeValue1TrapID equal 52 and
			the value of diValue change from 0 to 1."
	::= 9268

    diChangeValue1-53	TRAP-TYPE
	ENTERPRISE	network-device
	VARIABLES	{ diValue, adminDateAndTime, adminNDTrapSeqNo,
			  diIndex, diType, diValue1String }
	DESCRIPTION	"This trap is generated when set
			 diChangeValue1TrapID equal 53 and
			the value of diValue change from 0 to 1."
	::= 9269

    diChangeValue1-54	TRAP-TYPE
	ENTERPRISE	network-device
	VARIABLES	{ diValue, adminDateAndTime, adminNDTrapSeqNo,
			  diIndex, diType, diValue1String }
	DESCRIPTION	"This trap is generated when set
			 diChangeValue1TrapID equal 54 and
			the value of diValue change from 0 to 1."
	::= 9270

    diChangeValue1-55	TRAP-TYPE
	ENTERPRISE	network-device
	VARIABLES	{ diValue, adminDateAndTime, adminNDTrapSeqNo,
			  diIndex, diType, diValue1String }
	DESCRIPTION	"This trap is generated when set
			 diChangeValue1TrapID equal 55 and
			the value of diValue change from 0 to 1."
	::= 9271

    diChangeValue1-56	TRAP-TYPE
	ENTERPRISE	network-device
	VARIABLES	{ diValue, adminDateAndTime, adminNDTrapSeqNo,
			  diIndex, diType, diValue1String }
	DESCRIPTION	"This trap is generated when set
			 diChangeValue1TrapID equal 56 and
			the value of diValue change from 0 to 1."
	::= 9272

    diChangeValue1-57	TRAP-TYPE
	ENTERPRISE	network-device
	VARIABLES	{ diValue, adminDateAndTime, adminNDTrapSeqNo,
			  diIndex, diType, diValue1String }
	DESCRIPTION	"This trap is generated when set
			 diChangeValue1TrapID equal 57 and
			the value of diValue change from 0 to 1."
	::= 9273

    diChangeValue1-58	TRAP-TYPE
	ENTERPRISE	network-device
	VARIABLES	{ diValue, adminDateAndTime, adminNDTrapSeqNo,
			  diIndex, diType, diValue1String }
	DESCRIPTION	"This trap is generated when set
			 diChangeValue1TrapID equal 58 and
			the value of diValue change from 0 to 1."
	::= 9274

    diChangeValue1-59	TRAP-TYPE
	ENTERPRISE	network-device
	VARIABLES	{ diValue, adminDateAndTime, adminNDTrapSeqNo,
			  diIndex, diType, diValue1String }
	DESCRIPTION	"This trap is generated when set
			 diChangeValue1TrapID equal 59 and
			the value of diValue change from 0 to 1."
	::= 9275

    diChangeValue1-60	TRAP-TYPE
	ENTERPRISE	network-device
	VARIABLES	{ diValue, adminDateAndTime, adminNDTrapSeqNo,
			  diIndex, diType, diValue1String }
	DESCRIPTION	"This trap is generated when set
			 diChangeValue1TrapID equal 60 and
			the value of diValue change from 0 to 1."
	::= 9276

    diChangeValue1-61	TRAP-TYPE
	ENTERPRISE	network-device
	VARIABLES	{ diValue, adminDateAndTime, adminNDTrapSeqNo,
			  diIndex, diType, diValue1String }
	DESCRIPTION	"This trap is generated when set
			 diChangeValue1TrapID equal 61 and
			the value of diValue change from 0 to 1."
	::= 9277

    diChangeValue1-62	TRAP-TYPE
	ENTERPRISE	network-device
	VARIABLES	{ diValue, adminDateAndTime, adminNDTrapSeqNo,
			  diIndex, diType, diValue1String }
	DESCRIPTION	"This trap is generated when set
			 diChangeValue1TrapID equal 62 and
			the value of diValue change from 0 to 1."
	::= 9278

    diChangeValue1-63	TRAP-TYPE
	ENTERPRISE	network-device
	VARIABLES	{ diValue, adminDateAndTime, adminNDTrapSeqNo,
			  diIndex, diType, diValue1String }
	DESCRIPTION	"This trap is generated when set
			 diChangeValue1TrapID equal 63 and
			the value of diValue change from 0 to 1."
	::= 9279

    diChangeValue1-64	TRAP-TYPE
	ENTERPRISE	network-device
	VARIABLES	{ diValue, adminDateAndTime, adminNDTrapSeqNo,
			  diIndex, diType, diValue1String }
	DESCRIPTION	"This trap is generated when set
			 diChangeValue1TrapID equal 64 and
			the value of diValue change from 0 to 1."
	::= 9280

    diChangeValue1-65	TRAP-TYPE
	ENTERPRISE	network-device
	VARIABLES	{ diValue, adminDateAndTime, adminNDTrapSeqNo,
			  diIndex, diType, diValue1String }
	DESCRIPTION	"This trap is generated when set
			 diChangeValue1TrapID equal 65 and
			the value of diValue change from 0 to 1."
	::= 9281

    diChangeValue1-66	TRAP-TYPE
	ENTERPRISE	network-device
	VARIABLES	{ diValue, adminDateAndTime, adminNDTrapSeqNo,
			  diIndex, diType, diValue1String }
	DESCRIPTION	"This trap is generated when set
			 diChangeValue1TrapID equal 66 and
			the value of diValue change from 0 to 1."
	::= 9282

    diChangeValue1-67	TRAP-TYPE
	ENTERPRISE	network-device
	VARIABLES	{ diValue, adminDateAndTime, adminNDTrapSeqNo,
			  diIndex, diType, diValue1String }
	DESCRIPTION	"This trap is generated when set
			 diChangeValue1TrapID equal 67 and
			the value of diValue change from 0 to 1."
	::= 9283

    diChangeValue1-68	TRAP-TYPE
	ENTERPRISE	network-device
	VARIABLES	{ diValue, adminDateAndTime, adminNDTrapSeqNo,
			  diIndex, diType, diValue1String }
	DESCRIPTION	"This trap is generated when set
			 diChangeValue1TrapID equal 68 and
			the value of diValue change from 0 to 1."
	::= 9284

    diChangeValue1-69	TRAP-TYPE
	ENTERPRISE	network-device
	VARIABLES	{ diValue, adminDateAndTime, adminNDTrapSeqNo,
			  diIndex, diType, diValue1String }
	DESCRIPTION	"This trap is generated when set
			 diChangeValue1TrapID equal 69 and
			the value of diValue change from 0 to 1."
	::= 9285

    diChangeValue1-70	TRAP-TYPE
	ENTERPRISE	network-device
	VARIABLES	{ diValue, adminDateAndTime, adminNDTrapSeqNo,
			  diIndex, diType, diValue1String }
	DESCRIPTION	"This trap is generated when set
			 diChangeValue1TrapID equal 70 and
			the value of diValue change from 0 to 1."
	::= 9286

    diChangeValue1-71	TRAP-TYPE
	ENTERPRISE	network-device
	VARIABLES	{ diValue, adminDateAndTime, adminNDTrapSeqNo,
			  diIndex, diType, diValue1String }
	DESCRIPTION	"This trap is generated when set
			 diChangeValue1TrapID equal 71 and
			the value of diValue change from 0 to 1."
	::= 9287

    diChangeValue1-72	TRAP-TYPE
	ENTERPRISE	network-device
	VARIABLES	{ diValue, adminDateAndTime, adminNDTrapSeqNo,
			  diIndex, diType, diValue1String }
	DESCRIPTION	"This trap is generated when set
			 diChangeValue1TrapID equal 72 and
			the value of diValue change from 0 to 1."
	::= 9288

    diChangeValue1-73	TRAP-TYPE
	ENTERPRISE	network-device
	VARIABLES	{ diValue, adminDateAndTime, adminNDTrapSeqNo,
			  diIndex, diType, diValue1String }
	DESCRIPTION	"This trap is generated when set
			 diChangeValue1TrapID equal 73 and
			the value of diValue change from 0 to 1."
	::= 9289

    diChangeValue1-74	TRAP-TYPE
	ENTERPRISE	network-device
	VARIABLES	{ diValue, adminDateAndTime, adminNDTrapSeqNo,
			  diIndex, diType, diValue1String }
	DESCRIPTION	"This trap is generated when set
			 diChangeValue1TrapID equal 74 and
			the value of diValue change from 0 to 1."
	::= 9290

    diChangeValue1-75	TRAP-TYPE
	ENTERPRISE	network-device
	VARIABLES	{ diValue, adminDateAndTime, adminNDTrapSeqNo,
			  diIndex, diType, diValue1String }
	DESCRIPTION	"This trap is generated when set
			 diChangeValue1TrapID equal 75 and
			the value of diValue change from 0 to 1."
	::= 9291

    diChangeValue1-76	TRAP-TYPE
	ENTERPRISE	network-device
	VARIABLES	{ diValue, adminDateAndTime, adminNDTrapSeqNo,
			  diIndex, diType, diValue1String }
	DESCRIPTION	"This trap is generated when set
			 diChangeValue1TrapID equal 76 and
			the value of diValue change from 0 to 1."
	::= 9292

    diChangeValue1-77	TRAP-TYPE
	ENTERPRISE	network-device
	VARIABLES	{ diValue, adminDateAndTime, adminNDTrapSeqNo,
			  diIndex, diType, diValue1String }
	DESCRIPTION	"This trap is generated when set
			 diChangeValue1TrapID equal 77 and
			the value of diValue change from 0 to 1."
	::= 9293

    diChangeValue1-78	TRAP-TYPE
	ENTERPRISE	network-device
	VARIABLES	{ diValue, adminDateAndTime, adminNDTrapSeqNo,
			  diIndex, diType, diValue1String }
	DESCRIPTION	"This trap is generated when set
			 diChangeValue1TrapID equal 78 and
			the value of diValue change from 0 to 1."
	::= 9294

    diChangeValue1-79	TRAP-TYPE
	ENTERPRISE	network-device
	VARIABLES	{ diValue, adminDateAndTime, adminNDTrapSeqNo,
			  diIndex, diType, diValue1String }
	DESCRIPTION	"This trap is generated when set
			 diChangeValue1TrapID equal 79 and
			the value of diValue change from 0 to 1."
	::= 9295

    diChangeValue1-80	TRAP-TYPE
	ENTERPRISE	network-device
	VARIABLES	{ diValue, adminDateAndTime, adminNDTrapSeqNo,
			  diIndex, diType, diValue1String }
	DESCRIPTION	"This trap is generated when set
			 diChangeValue1TrapID equal 80 and
			the value of diValue change from 0 to 1."
	::= 9296

    diChangeValue1-81	TRAP-TYPE
	ENTERPRISE	network-device
	VARIABLES	{ diValue, adminDateAndTime, adminNDTrapSeqNo,
			  diIndex, diType, diValue1String }
	DESCRIPTION	"This trap is generated when set
			 diChangeValue1TrapID equal 81 and
			the value of diValue change from 0 to 1."
	::= 9297

    diChangeValue1-82	TRAP-TYPE
	ENTERPRISE	network-device
	VARIABLES	{ diValue, adminDateAndTime, adminNDTrapSeqNo,
			  diIndex, diType, diValue1String }
	DESCRIPTION	"This trap is generated when set
			 diChangeValue1TrapID equal 82 and
			the value of diValue change from 0 to 1."
	::= 9298

    diChangeValue1-83	TRAP-TYPE
	ENTERPRISE	network-device
	VARIABLES	{ diValue, adminDateAndTime, adminNDTrapSeqNo,
			  diIndex, diType, diValue1String }
	DESCRIPTION	"This trap is generated when set
			 diChangeValue1TrapID equal 83 and
			the value of diValue change from 0 to 1."
	::= 9299

    diChangeValue1-84	TRAP-TYPE
	ENTERPRISE	network-device
	VARIABLES	{ diValue, adminDateAndTime, adminNDTrapSeqNo,
			  diIndex, diType, diValue1String }
	DESCRIPTION	"This trap is generated when set
			 diChangeValue1TrapID equal 84 and
			the value of diValue change from 0 to 1."
	::= 9300

    diChangeValue1-85	TRAP-TYPE
	ENTERPRISE	network-device
	VARIABLES	{ diValue, adminDateAndTime, adminNDTrapSeqNo,
			  diIndex, diType, diValue1String }
	DESCRIPTION	"This trap is generated when set
			 diChangeValue1TrapID equal 85 and
			the value of diValue change from 0 to 1."
	::= 9301

    diChangeValue1-86	TRAP-TYPE
	ENTERPRISE	network-device
	VARIABLES	{ diValue, adminDateAndTime, adminNDTrapSeqNo,
			  diIndex, diType, diValue1String }
	DESCRIPTION	"This trap is generated when set
			 diChangeValue1TrapID equal 86 and
			the value of diValue change from 0 to 1."
	::= 9302

    diChangeValue1-87	TRAP-TYPE
	ENTERPRISE	network-device
	VARIABLES	{ diValue, adminDateAndTime, adminNDTrapSeqNo,
			  diIndex, diType, diValue1String }
	DESCRIPTION	"This trap is generated when set
			 diChangeValue1TrapID equal 87 and
			the value of diValue change from 0 to 1."
	::= 9303

    diChangeValue1-88	TRAP-TYPE
	ENTERPRISE	network-device
	VARIABLES	{ diValue, adminDateAndTime, adminNDTrapSeqNo,
			  diIndex, diType, diValue1String }
	DESCRIPTION	"This trap is generated when set
			 diChangeValue1TrapID equal 88 and
			the value of diValue change from 0 to 1."
	::= 9304

    diChangeValue1-89	TRAP-TYPE
	ENTERPRISE	network-device
	VARIABLES	{ diValue, adminDateAndTime, adminNDTrapSeqNo,
			  diIndex, diType, diValue1String }
	DESCRIPTION	"This trap is generated when set
			 diChangeValue1TrapID equal 89 and
			the value of diValue change from 0 to 1."
	::= 9305

    diChangeValue1-90	TRAP-TYPE
	ENTERPRISE	network-device
	VARIABLES	{ diValue, adminDateAndTime, adminNDTrapSeqNo,
			  diIndex, diType, diValue1String }
	DESCRIPTION	"This trap is generated when set
			 diChangeValue1TrapID equal 90 and
			the value of diValue change from 0 to 1."
	::= 9306

    diChangeValue1-91	TRAP-TYPE
	ENTERPRISE	network-device
	VARIABLES	{ diValue, adminDateAndTime, adminNDTrapSeqNo,
			  diIndex, diType, diValue1String }
	DESCRIPTION	"This trap is generated when set
			 diChangeValue1TrapID equal 91 and
			the value of diValue change from 0 to 1."
	::= 9307

    diChangeValue1-92	TRAP-TYPE
	ENTERPRISE	network-device
	VARIABLES	{ diValue, adminDateAndTime, adminNDTrapSeqNo,
			  diIndex, diType, diValue1String }
	DESCRIPTION	"This trap is generated when set
			 diChangeValue1TrapID equal 92 and
			the value of diValue change from 0 to 1."
	::= 9308

    diChangeValue1-93	TRAP-TYPE
	ENTERPRISE	network-device
	VARIABLES	{ diValue, adminDateAndTime, adminNDTrapSeqNo,
			  diIndex, diType, diValue1String }
	DESCRIPTION	"This trap is generated when set
			 diChangeValue1TrapID equal 93 and
			the value of diValue change from 0 to 1."
	::= 9309

    diChangeValue1-94	TRAP-TYPE
	ENTERPRISE	network-device
	VARIABLES	{ diValue, adminDateAndTime, adminNDTrapSeqNo,
			  diIndex, diType, diValue1String }
	DESCRIPTION	"This trap is generated when set
			 diChangeValue1TrapID equal 94 and
			the value of diValue change from 0 to 1."
	::= 9310

    diChangeValue1-95	TRAP-TYPE
	ENTERPRISE	network-device
	VARIABLES	{ diValue, adminDateAndTime, adminNDTrapSeqNo,
			  diIndex, diType, diValue1String }
	DESCRIPTION	"This trap is generated when set
			 diChangeValue1TrapID equal 95 and
			the value of diValue change from 0 to 1."
	::= 9311

    diChangeValue1-96	TRAP-TYPE
	ENTERPRISE	network-device
	VARIABLES	{ diValue, adminDateAndTime, adminNDTrapSeqNo,
			  diIndex, diType, diValue1String }
	DESCRIPTION	"This trap is generated when set
			 diChangeValue1TrapID equal 96 and
			the value of diValue change from 0 to 1."
	::= 9312

    diChangeValue1-97	TRAP-TYPE
	ENTERPRISE	network-device
	VARIABLES	{ diValue, adminDateAndTime, adminNDTrapSeqNo,
			  diIndex, diType, diValue1String }
	DESCRIPTION	"This trap is generated when set
			 diChangeValue1TrapID equal 97 and
			the value of diValue change from 0 to 1."
	::= 9313

    diChangeValue1-98	TRAP-TYPE
	ENTERPRISE	network-device
	VARIABLES	{ diValue, adminDateAndTime, adminNDTrapSeqNo,
			  diIndex, diType, diValue1String }
	DESCRIPTION	"This trap is generated when set
			 diChangeValue1TrapID equal 98 and
			the value of diValue change from 0 to 1."
	::= 9314

    diChangeValue1-99	TRAP-TYPE
	ENTERPRISE	network-device
	VARIABLES	{ diValue, adminDateAndTime, adminNDTrapSeqNo,
			  diIndex, diType, diValue1String }
	DESCRIPTION	"This trap is generated when set
			 diChangeValue1TrapID equal 99 and
			the value of diValue change from 0 to 1."
	::= 9315

    diChangeValue1-100	TRAP-TYPE
	ENTERPRISE	network-device
	VARIABLES	{ diValue, adminDateAndTime, adminNDTrapSeqNo,
			  diIndex, diType, diValue1String }
	DESCRIPTION	"This trap is generated when set
			 diChangeValue1TrapID equal 100 and
			the value of diValue change from 0 to 1."
	::= 9316

    diChangeValue1-101	TRAP-TYPE
	ENTERPRISE	network-device
	VARIABLES	{ diValue, adminDateAndTime, adminNDTrapSeqNo,
			  diIndex, diType, diValue1String }
	DESCRIPTION	"This trap is generated when set
			 diChangeValue1TrapID equal 101 and
			the value of diValue change from 0 to 1."
	::= 9317

    diChangeValue1-102	TRAP-TYPE
	ENTERPRISE	network-device
	VARIABLES	{ diValue, adminDateAndTime, adminNDTrapSeqNo,
			  diIndex, diType, diValue1String }
	DESCRIPTION	"This trap is generated when set
			 diChangeValue1TrapID equal 102 and
			the value of diValue change from 0 to 1."
	::= 9318

    diChangeValue1-103	TRAP-TYPE
	ENTERPRISE	network-device
	VARIABLES	{ diValue, adminDateAndTime, adminNDTrapSeqNo,
			  diIndex, diType, diValue1String }
	DESCRIPTION	"This trap is generated when set
			 diChangeValue1TrapID equal 103 and
			the value of diValue change from 0 to 1."
	::= 9319

    diChangeValue1-104	TRAP-TYPE
	ENTERPRISE	network-device
	VARIABLES	{ diValue, adminDateAndTime, adminNDTrapSeqNo,
			  diIndex, diType, diValue1String }
	DESCRIPTION	"This trap is generated when set
			 diChangeValue1TrapID equal 104 and
			the value of diValue change from 0 to 1."
	::= 9320

    diChangeValue1-105	TRAP-TYPE
	ENTERPRISE	network-device
	VARIABLES	{ diValue, adminDateAndTime, adminNDTrapSeqNo,
			  diIndex, diType, diValue1String }
	DESCRIPTION	"This trap is generated when set
			 diChangeValue1TrapID equal 105 and
			the value of diValue change from 0 to 1."
	::= 9321

    diChangeValue1-106	TRAP-TYPE
	ENTERPRISE	network-device
	VARIABLES	{ diValue, adminDateAndTime, adminNDTrapSeqNo,
			  diIndex, diType, diValue1String }
	DESCRIPTION	"This trap is generated when set
			 diChangeValue1TrapID equal 106 and
			the value of diValue change from 0 to 1."
	::= 9322

    diChangeValue1-107	TRAP-TYPE
	ENTERPRISE	network-device
	VARIABLES	{ diValue, adminDateAndTime, adminNDTrapSeqNo,
			  diIndex, diType, diValue1String }
	DESCRIPTION	"This trap is generated when set
			 diChangeValue1TrapID equal 107 and
			the value of diValue change from 0 to 1."
	::= 9323

    diChangeValue1-108	TRAP-TYPE
	ENTERPRISE	network-device
	VARIABLES	{ diValue, adminDateAndTime, adminNDTrapSeqNo,
			  diIndex, diType, diValue1String }
	DESCRIPTION	"This trap is generated when set
			 diChangeValue1TrapID equal 108 and
			the value of diValue change from 0 to 1."
	::= 9324

    diChangeValue1-109	TRAP-TYPE
	ENTERPRISE	network-device
	VARIABLES	{ diValue, adminDateAndTime, adminNDTrapSeqNo,
			  diIndex, diType, diValue1String }
	DESCRIPTION	"This trap is generated when set
			 diChangeValue1TrapID equal 109 and
			the value of diValue change from 0 to 1."
	::= 9325

    diChangeValue1-110	TRAP-TYPE
	ENTERPRISE	network-device
	VARIABLES	{ diValue, adminDateAndTime, adminNDTrapSeqNo,
			  diIndex, diType, diValue1String }
	DESCRIPTION	"This trap is generated when set
			 diChangeValue1TrapID equal 110 and
			the value of diValue change from 0 to 1."
	::= 9326

    diChangeValue1-111	TRAP-TYPE
	ENTERPRISE	network-device
	VARIABLES	{ diValue, adminDateAndTime, adminNDTrapSeqNo,
			  diIndex, diType, diValue1String }
	DESCRIPTION	"This trap is generated when set
			 diChangeValue1TrapID equal 111 and
			the value of diValue change from 0 to 1."
	::= 9327

    diChangeValue1-112	TRAP-TYPE
	ENTERPRISE	network-device
	VARIABLES	{ diValue, adminDateAndTime, adminNDTrapSeqNo,
			  diIndex, diType, diValue1String }
	DESCRIPTION	"This trap is generated when set
			 diChangeValue1TrapID equal 112 and
			the value of diValue change from 0 to 1."
	::= 9328

    diChangeValue1-113	TRAP-TYPE
	ENTERPRISE	network-device
	VARIABLES	{ diValue, adminDateAndTime, adminNDTrapSeqNo,
			  diIndex, diType, diValue1String }
	DESCRIPTION	"This trap is generated when set
			 diChangeValue1TrapID equal 113 and
			the value of diValue change from 0 to 1."
	::= 9329

    diChangeValue1-114	TRAP-TYPE
	ENTERPRISE	network-device
	VARIABLES	{ diValue, adminDateAndTime, adminNDTrapSeqNo,
			  diIndex, diType, diValue1String }
	DESCRIPTION	"This trap is generated when set
			 diChangeValue1TrapID equal 114 and
			the value of diValue change from 0 to 1."
	::= 9330

    diChangeValue1-115	TRAP-TYPE
	ENTERPRISE	network-device
	VARIABLES	{ diValue, adminDateAndTime, adminNDTrapSeqNo,
			  diIndex, diType, diValue1String }
	DESCRIPTION	"This trap is generated when set
			 diChangeValue1TrapID equal 115 and
			the value of diValue change from 0 to 1."
	::= 9331

    diChangeValue1-116	TRAP-TYPE
	ENTERPRISE	network-device
	VARIABLES	{ diValue, adminDateAndTime, adminNDTrapSeqNo,
			  diIndex, diType, diValue1String }
	DESCRIPTION	"This trap is generated when set
			 diChangeValue1TrapID equal 116 and
			the value of diValue change from 0 to 1."
	::= 9332

    diChangeValue1-117	TRAP-TYPE
	ENTERPRISE	network-device
	VARIABLES	{ diValue, adminDateAndTime, adminNDTrapSeqNo,
			  diIndex, diType, diValue1String }
	DESCRIPTION	"This trap is generated when set
			 diChangeValue1TrapID equal 117 and
			the value of diValue change from 0 to 1."
	::= 9333

    diChangeValue1-118	TRAP-TYPE
	ENTERPRISE	network-device
	VARIABLES	{ diValue, adminDateAndTime, adminNDTrapSeqNo,
			  diIndex, diType, diValue1String }
	DESCRIPTION	"This trap is generated when set
			 diChangeValue1TrapID equal 118 and
			the value of diValue change from 0 to 1."
	::= 9334

    diChangeValue1-119	TRAP-TYPE
	ENTERPRISE	network-device
	VARIABLES	{ diValue, adminDateAndTime, adminNDTrapSeqNo,
			  diIndex, diType, diValue1String }
	DESCRIPTION	"This trap is generated when set
			 diChangeValue1TrapID equal 119 and
			the value of diValue change from 0 to 1."
	::= 9335

    diChangeValue1-120	TRAP-TYPE
	ENTERPRISE	network-device
	VARIABLES	{ diValue, adminDateAndTime, adminNDTrapSeqNo,
			  diIndex, diType, diValue1String }
	DESCRIPTION	"This trap is generated when set
			 diChangeValue1TrapID equal 120 and
			the value of diValue change from 0 to 1."
	::= 9336

    diChangeValue1-121	TRAP-TYPE
	ENTERPRISE	network-device
	VARIABLES	{ diValue, adminDateAndTime, adminNDTrapSeqNo,
			  diIndex, diType, diValue1String }
	DESCRIPTION	"This trap is generated when set
			 diChangeValue1TrapID equal 121 and
			the value of diValue change from 0 to 1."
	::= 9337

    diChangeValue1-122	TRAP-TYPE
	ENTERPRISE	network-device
	VARIABLES	{ diValue, adminDateAndTime, adminNDTrapSeqNo,
			  diIndex, diType, diValue1String }
	DESCRIPTION	"This trap is generated when set
			 diChangeValue1TrapID equal 122 and
			the value of diValue change from 0 to 1."
	::= 9338

    diChangeValue1-123	TRAP-TYPE
	ENTERPRISE	network-device
	VARIABLES	{ diValue, adminDateAndTime, adminNDTrapSeqNo,
			  diIndex, diType, diValue1String }
	DESCRIPTION	"This trap is generated when set
			 diChangeValue1TrapID equal 123 and
			the value of diValue change from 0 to 1."
	::= 9339

    diChangeValue1-124	TRAP-TYPE
	ENTERPRISE	network-device
	VARIABLES	{ diValue, adminDateAndTime, adminNDTrapSeqNo,
			  diIndex, diType, diValue1String }
	DESCRIPTION	"This trap is generated when set
			 diChangeValue1TrapID equal 124 and
			the value of diValue change from 0 to 1."
	::= 9340

    diChangeValue1-125	TRAP-TYPE
	ENTERPRISE	network-device
	VARIABLES	{ diValue, adminDateAndTime, adminNDTrapSeqNo,
			  diIndex, diType, diValue1String }
	DESCRIPTION	"This trap is generated when set
			 diChangeValue1TrapID equal 125 and
			the value of diValue change from 0 to 1."
	::= 9341

    diChangeValue1-126	TRAP-TYPE
	ENTERPRISE	network-device
	VARIABLES	{ diValue, adminDateAndTime, adminNDTrapSeqNo,
			  diIndex, diType, diValue1String }
	DESCRIPTION	"This trap is generated when set
			 diChangeValue1TrapID equal 126 and
			the value of diValue change from 0 to 1."
	::= 9342

    diChangeValue1-127	TRAP-TYPE
	ENTERPRISE	network-device
	VARIABLES	{ diValue, adminDateAndTime, adminNDTrapSeqNo,
			  diIndex, diType, diValue1String }
	DESCRIPTION	"This trap is generated when set
			 diChangeValue1TrapID equal 127 and
			the value of diValue change from 0 to 1."
	::= 9343

    diValue1-1		TRAP-TYPE
	ENTERPRISE	network-device
	VARIABLES	{ diValue, adminDateAndTime, adminNDTrapSeqNo,
			  diIndex, diType, diValue1String }
	DESCRIPTION	"This trap is generated when set
			 diValue1TrapID equal 1 and
			while the value of diValue is 1."
	::= 9729

    diValue1-2		TRAP-TYPE
	ENTERPRISE	network-device
	VARIABLES	{ diValue, adminDateAndTime, adminNDTrapSeqNo,
			  diIndex, diType, diValue1String }
	DESCRIPTION	"This trap is generated when set
			 diValue1TrapID equal 2 and
			while the value of diValue is 1."
	::= 9730

    diValue1-3		TRAP-TYPE
	ENTERPRISE	network-device
	VARIABLES	{ diValue, adminDateAndTime, adminNDTrapSeqNo,
			  diIndex, diType, diValue1String }
	DESCRIPTION	"This trap is generated when set
			 diValue1TrapID equal 3 and
			while the value of diValue is 1."
	::= 9731

    diValue1-4		TRAP-TYPE
	ENTERPRISE	network-device
	VARIABLES	{ diValue, adminDateAndTime, adminNDTrapSeqNo,
			  diIndex, diType, diValue1String }
	DESCRIPTION	"This trap is generated when set
			 diValue1TrapID equal 4 and
			while the value of diValue is 1."
	::= 9732

    diValue1-5		TRAP-TYPE
	ENTERPRISE	network-device
	VARIABLES	{ diValue, adminDateAndTime, adminNDTrapSeqNo,
			  diIndex, diType, diValue1String }
	DESCRIPTION	"This trap is generated when set
			 diValue1TrapID equal 5 and
			while the value of diValue is 1."
	::= 9733

    diValue1-6		TRAP-TYPE
	ENTERPRISE	network-device
	VARIABLES	{ diValue, adminDateAndTime, adminNDTrapSeqNo,
			  diIndex, diType, diValue1String }
	DESCRIPTION	"This trap is generated when set
			 diValue1TrapID equal 6 and
			while the value of diValue is 1."
	::= 9734

    diValue1-7		TRAP-TYPE
	ENTERPRISE	network-device
	VARIABLES	{ diValue, adminDateAndTime, adminNDTrapSeqNo,
			  diIndex, diType, diValue1String }
	DESCRIPTION	"This trap is generated when set
			 diValue1TrapID equal 7 and
			while the value of diValue is 1."
	::= 9735

    diValue1-8		TRAP-TYPE
	ENTERPRISE	network-device
	VARIABLES	{ diValue, adminDateAndTime, adminNDTrapSeqNo,
			  diIndex, diType, diValue1String }
	DESCRIPTION	"This trap is generated when set
			 diValue1TrapID equal 8 and
			while the value of diValue is 1."
	::= 9736

    diValue1-9		TRAP-TYPE
	ENTERPRISE	network-device
	VARIABLES	{ diValue, adminDateAndTime, adminNDTrapSeqNo,
			  diIndex, diType, diValue1String }
	DESCRIPTION	"This trap is generated when set
			 diValue1TrapID equal 9 and
			while the value of diValue is 1."
	::= 9737

    diValue1-10		TRAP-TYPE
	ENTERPRISE	network-device
	VARIABLES	{ diValue, adminDateAndTime, adminNDTrapSeqNo,
			  diIndex, diType, diValue1String }
	DESCRIPTION	"This trap is generated when set
			 diValue1TrapID equal 10 and
			while the value of diValue is 1."
	::= 9738

    diValue1-11		TRAP-TYPE
	ENTERPRISE	network-device
	VARIABLES	{ diValue, adminDateAndTime, adminNDTrapSeqNo,
			  diIndex, diType, diValue1String }
	DESCRIPTION	"This trap is generated when set
			 diValue1TrapID equal 11 and
			while the value of diValue is 1."
	::= 9739

    diValue1-12		TRAP-TYPE
	ENTERPRISE	network-device
	VARIABLES	{ diValue, adminDateAndTime, adminNDTrapSeqNo,
			  diIndex, diType, diValue1String }
	DESCRIPTION	"This trap is generated when set
			 diValue1TrapID equal 12 and
			while the value of diValue is 1."
	::= 9740

    diValue1-13		TRAP-TYPE
	ENTERPRISE	network-device
	VARIABLES	{ diValue, adminDateAndTime, adminNDTrapSeqNo,
			  diIndex, diType, diValue1String }
	DESCRIPTION	"This trap is generated when set
			 diValue1TrapID equal 13 and
			while the value of diValue is 1."
	::= 9741

    diValue1-14		TRAP-TYPE
	ENTERPRISE	network-device
	VARIABLES	{ diValue, adminDateAndTime, adminNDTrapSeqNo,
			  diIndex, diType, diValue1String }
	DESCRIPTION	"This trap is generated when set
			 diValue1TrapID equal 14 and
			while the value of diValue is 1."
	::= 9742

    diValue1-15		TRAP-TYPE
	ENTERPRISE	network-device
	VARIABLES	{ diValue, adminDateAndTime, adminNDTrapSeqNo,
			  diIndex, diType, diValue1String }
	DESCRIPTION	"This trap is generated when set
			 diValue1TrapID equal 15 and
			while the value of diValue is 1."
	::= 9743

    diValue1-16		TRAP-TYPE
	ENTERPRISE	network-device
	VARIABLES	{ diValue, adminDateAndTime, adminNDTrapSeqNo,
			  diIndex, diType, diValue1String }
	DESCRIPTION	"This trap is generated when set
			 diValue1TrapID equal 16 and
			while the value of diValue is 1."
	::= 9744

    diValue1-17		TRAP-TYPE
	ENTERPRISE	network-device
	VARIABLES	{ diValue, adminDateAndTime, adminNDTrapSeqNo,
			  diIndex, diType, diValue1String }
	DESCRIPTION	"This trap is generated when set
			 diValue1TrapID equal 17 and
			while the value of diValue is 1."
	::= 9745

    diValue1-18		TRAP-TYPE
	ENTERPRISE	network-device
	VARIABLES	{ diValue, adminDateAndTime, adminNDTrapSeqNo,
			  diIndex, diType, diValue1String }
	DESCRIPTION	"This trap is generated when set
			 diValue1TrapID equal 18 and
			while the value of diValue is 1."
	::= 9746

    diValue1-19		TRAP-TYPE
	ENTERPRISE	network-device
	VARIABLES	{ diValue, adminDateAndTime, adminNDTrapSeqNo,
			  diIndex, diType, diValue1String }
	DESCRIPTION	"This trap is generated when set
			 diValue1TrapID equal 19 and
			while the value of diValue is 1."
	::= 9747

    diValue1-20		TRAP-TYPE
	ENTERPRISE	network-device
	VARIABLES	{ diValue, adminDateAndTime, adminNDTrapSeqNo,
			  diIndex, diType, diValue1String }
	DESCRIPTION	"This trap is generated when set
			 diValue1TrapID equal 20 and
			while the value of diValue is 1."
	::= 9748

    diValue1-21		TRAP-TYPE
	ENTERPRISE	network-device
	VARIABLES	{ diValue, adminDateAndTime, adminNDTrapSeqNo,
			  diIndex, diType, diValue1String }
	DESCRIPTION	"This trap is generated when set
			 diValue1TrapID equal 21 and
			while the value of diValue is 1."
	::= 9749

    diValue1-22		TRAP-TYPE
	ENTERPRISE	network-device
	VARIABLES	{ diValue, adminDateAndTime, adminNDTrapSeqNo,
			  diIndex, diType, diValue1String }
	DESCRIPTION	"This trap is generated when set
			 diValue1TrapID equal 22 and
			while the value of diValue is 1."
	::= 9750

    diValue1-23		TRAP-TYPE
	ENTERPRISE	network-device
	VARIABLES	{ diValue, adminDateAndTime, adminNDTrapSeqNo,
			  diIndex, diType, diValue1String }
	DESCRIPTION	"This trap is generated when set
			 diValue1TrapID equal 23 and
			while the value of diValue is 1."
	::= 9751

    diValue1-24		TRAP-TYPE
	ENTERPRISE	network-device
	VARIABLES	{ diValue, adminDateAndTime, adminNDTrapSeqNo,
			  diIndex, diType, diValue1String }
	DESCRIPTION	"This trap is generated when set
			 diValue1TrapID equal 24 and
			while the value of diValue is 1."
	::= 9752

    diValue1-25		TRAP-TYPE
	ENTERPRISE	network-device
	VARIABLES	{ diValue, adminDateAndTime, adminNDTrapSeqNo,
			  diIndex, diType, diValue1String }
	DESCRIPTION	"This trap is generated when set
			 diValue1TrapID equal 25 and
			while the value of diValue is 1."
	::= 9753

    diValue1-26		TRAP-TYPE
	ENTERPRISE	network-device
	VARIABLES	{ diValue, adminDateAndTime, adminNDTrapSeqNo,
			  diIndex, diType, diValue1String }
	DESCRIPTION	"This trap is generated when set
			 diValue1TrapID equal 26 and
			while the value of diValue is 1."
	::= 9754

    diValue1-27		TRAP-TYPE
	ENTERPRISE	network-device
	VARIABLES	{ diValue, adminDateAndTime, adminNDTrapSeqNo,
			  diIndex, diType, diValue1String }
	DESCRIPTION	"This trap is generated when set
			 diValue1TrapID equal 27 and
			while the value of diValue is 1."
	::= 9755

    diValue1-28		TRAP-TYPE
	ENTERPRISE	network-device
	VARIABLES	{ diValue, adminDateAndTime, adminNDTrapSeqNo,
			  diIndex, diType, diValue1String }
	DESCRIPTION	"This trap is generated when set
			 diValue1TrapID equal 28 and
			while the value of diValue is 1."
	::= 9756

    diValue1-29		TRAP-TYPE
	ENTERPRISE	network-device
	VARIABLES	{ diValue, adminDateAndTime, adminNDTrapSeqNo,
			  diIndex, diType, diValue1String }
	DESCRIPTION	"This trap is generated when set
			 diValue1TrapID equal 29 and
			while the value of diValue is 1."
	::= 9757

    diValue1-30		TRAP-TYPE
	ENTERPRISE	network-device
	VARIABLES	{ diValue, adminDateAndTime, adminNDTrapSeqNo,
			  diIndex, diType, diValue1String }
	DESCRIPTION	"This trap is generated when set
			 diValue1TrapID equal 30 and
			while the value of diValue is 1."
	::= 9758

    diValue1-31		TRAP-TYPE
	ENTERPRISE	network-device
	VARIABLES	{ diValue, adminDateAndTime, adminNDTrapSeqNo,
			  diIndex, diType, diValue1String }
	DESCRIPTION	"This trap is generated when set
			 diValue1TrapID equal 31 and
			while the value of diValue is 1."
	::= 9759

    diValue1-32		TRAP-TYPE
	ENTERPRISE	network-device
	VARIABLES	{ diValue, adminDateAndTime, adminNDTrapSeqNo,
			  diIndex, diType, diValue1String }
	DESCRIPTION	"This trap is generated when set
			 diValue1TrapID equal 32 and
			while the value of diValue is 1."
	::= 9760

    diValue1-33		TRAP-TYPE
	ENTERPRISE	network-device
	VARIABLES	{ diValue, adminDateAndTime, adminNDTrapSeqNo,
			  diIndex, diType, diValue1String }
	DESCRIPTION	"This trap is generated when set
			 diValue1TrapID equal 33 and
			while the value of diValue is 1."
	::= 9761

    diValue1-34		TRAP-TYPE
	ENTERPRISE	network-device
	VARIABLES	{ diValue, adminDateAndTime, adminNDTrapSeqNo,
			  diIndex, diType, diValue1String }
	DESCRIPTION	"This trap is generated when set
			 diValue1TrapID equal 34 and
			while the value of diValue is 1."
	::= 9762

    diValue1-35		TRAP-TYPE
	ENTERPRISE	network-device
	VARIABLES	{ diValue, adminDateAndTime, adminNDTrapSeqNo,
			  diIndex, diType, diValue1String }
	DESCRIPTION	"This trap is generated when set
			 diValue1TrapID equal 35 and
			while the value of diValue is 1."
	::= 9763

    diValue1-36		TRAP-TYPE
	ENTERPRISE	network-device
	VARIABLES	{ diValue, adminDateAndTime, adminNDTrapSeqNo,
			  diIndex, diType, diValue1String }
	DESCRIPTION	"This trap is generated when set
			 diValue1TrapID equal 36 and
			while the value of diValue is 1."
	::= 9764

    diValue1-37		TRAP-TYPE
	ENTERPRISE	network-device
	VARIABLES	{ diValue, adminDateAndTime, adminNDTrapSeqNo,
			  diIndex, diType, diValue1String }
	DESCRIPTION	"This trap is generated when set
			 diValue1TrapID equal 37 and
			while the value of diValue is 1."
	::= 9765

    diValue1-38		TRAP-TYPE
	ENTERPRISE	network-device
	VARIABLES	{ diValue, adminDateAndTime, adminNDTrapSeqNo,
			  diIndex, diType, diValue1String }
	DESCRIPTION	"This trap is generated when set
			 diValue1TrapID equal 38 and
			while the value of diValue is 1."
	::= 9766

    diValue1-39		TRAP-TYPE
	ENTERPRISE	network-device
	VARIABLES	{ diValue, adminDateAndTime, adminNDTrapSeqNo,
			  diIndex, diType, diValue1String }
	DESCRIPTION	"This trap is generated when set
			 diValue1TrapID equal 39 and
			while the value of diValue is 1."
	::= 9767

    diValue1-40		TRAP-TYPE
	ENTERPRISE	network-device
	VARIABLES	{ diValue, adminDateAndTime, adminNDTrapSeqNo,
			  diIndex, diType, diValue1String }
	DESCRIPTION	"This trap is generated when set
			 diValue1TrapID equal 40 and
			while the value of diValue is 1."
	::= 9768

    diValue1-41		TRAP-TYPE
	ENTERPRISE	network-device
	VARIABLES	{ diValue, adminDateAndTime, adminNDTrapSeqNo,
			  diIndex, diType, diValue1String }
	DESCRIPTION	"This trap is generated when set
			 diValue1TrapID equal 41 and
			while the value of diValue is 1."
	::= 9769

    diValue1-42		TRAP-TYPE
	ENTERPRISE	network-device
	VARIABLES	{ diValue, adminDateAndTime, adminNDTrapSeqNo,
			  diIndex, diType, diValue1String }
	DESCRIPTION	"This trap is generated when set
			 diValue1TrapID equal 42 and
			while the value of diValue is 1."
	::= 9770

    diValue1-43		TRAP-TYPE
	ENTERPRISE	network-device
	VARIABLES	{ diValue, adminDateAndTime, adminNDTrapSeqNo,
			  diIndex, diType, diValue1String }
	DESCRIPTION	"This trap is generated when set
			 diValue1TrapID equal 43 and
			while the value of diValue is 1."
	::= 9771

    diValue1-44		TRAP-TYPE
	ENTERPRISE	network-device
	VARIABLES	{ diValue, adminDateAndTime, adminNDTrapSeqNo,
			  diIndex, diType, diValue1String }
	DESCRIPTION	"This trap is generated when set
			 diValue1TrapID equal 44 and
			while the value of diValue is 1."
	::= 9772

    diValue1-45		TRAP-TYPE
	ENTERPRISE	network-device
	VARIABLES	{ diValue, adminDateAndTime, adminNDTrapSeqNo,
			  diIndex, diType, diValue1String }
	DESCRIPTION	"This trap is generated when set
			 diValue1TrapID equal 45 and
			while the value of diValue is 1."
	::= 9773

    diValue1-46		TRAP-TYPE
	ENTERPRISE	network-device
	VARIABLES	{ diValue, adminDateAndTime, adminNDTrapSeqNo,
			  diIndex, diType, diValue1String }
	DESCRIPTION	"This trap is generated when set
			 diValue1TrapID equal 46 and
			while the value of diValue is 1."
	::= 9774

    diValue1-47		TRAP-TYPE
	ENTERPRISE	network-device
	VARIABLES	{ diValue, adminDateAndTime, adminNDTrapSeqNo,
			  diIndex, diType, diValue1String }
	DESCRIPTION	"This trap is generated when set
			 diValue1TrapID equal 47 and
			while the value of diValue is 1."
	::= 9775

    diValue1-48		TRAP-TYPE
	ENTERPRISE	network-device
	VARIABLES	{ diValue, adminDateAndTime, adminNDTrapSeqNo,
			  diIndex, diType, diValue1String }
	DESCRIPTION	"This trap is generated when set
			 diValue1TrapID equal 48 and
			while the value of diValue is 1."
	::= 9776

    diValue1-49		TRAP-TYPE
	ENTERPRISE	network-device
	VARIABLES	{ diValue, adminDateAndTime, adminNDTrapSeqNo,
			  diIndex, diType, diValue1String }
	DESCRIPTION	"This trap is generated when set
			 diValue1TrapID equal 49 and
			while the value of diValue is 1."
	::= 9777

    diValue1-50		TRAP-TYPE
	ENTERPRISE	network-device
	VARIABLES	{ diValue, adminDateAndTime, adminNDTrapSeqNo,
			  diIndex, diType, diValue1String }
	DESCRIPTION	"This trap is generated when set
			 diValue1TrapID equal 50 and
			while the value of diValue is 1."
	::= 9778

    diValue1-51		TRAP-TYPE
	ENTERPRISE	network-device
	VARIABLES	{ diValue, adminDateAndTime, adminNDTrapSeqNo,
			  diIndex, diType, diValue1String }
	DESCRIPTION	"This trap is generated when set
			 diValue1TrapID equal 51 and
			while the value of diValue is 1."
	::= 9779

    diValue1-52		TRAP-TYPE
	ENTERPRISE	network-device
	VARIABLES	{ diValue, adminDateAndTime, adminNDTrapSeqNo,
			  diIndex, diType, diValue1String }
	DESCRIPTION	"This trap is generated when set
			 diValue1TrapID equal 52 and
			while the value of diValue is 1."
	::= 9780

    diValue1-53		TRAP-TYPE
	ENTERPRISE	network-device
	VARIABLES	{ diValue, adminDateAndTime, adminNDTrapSeqNo,
			  diIndex, diType, diValue1String }
	DESCRIPTION	"This trap is generated when set
			 diValue1TrapID equal 53 and
			while the value of diValue is 1."
	::= 9781

    diValue1-54		TRAP-TYPE
	ENTERPRISE	network-device
	VARIABLES	{ diValue, adminDateAndTime, adminNDTrapSeqNo,
			  diIndex, diType, diValue1String }
	DESCRIPTION	"This trap is generated when set
			 diValue1TrapID equal 54 and
			while the value of diValue is 1."
	::= 9782

    diValue1-55		TRAP-TYPE
	ENTERPRISE	network-device
	VARIABLES	{ diValue, adminDateAndTime, adminNDTrapSeqNo,
			  diIndex, diType, diValue1String }
	DESCRIPTION	"This trap is generated when set
			 diValue1TrapID equal 55 and
			while the value of diValue is 1."
	::= 9783

    diValue1-56		TRAP-TYPE
	ENTERPRISE	network-device
	VARIABLES	{ diValue, adminDateAndTime, adminNDTrapSeqNo,
			  diIndex, diType, diValue1String }
	DESCRIPTION	"This trap is generated when set
			 diValue1TrapID equal 56 and
			while the value of diValue is 1."
	::= 9784

    diValue1-57		TRAP-TYPE
	ENTERPRISE	network-device
	VARIABLES	{ diValue, adminDateAndTime, adminNDTrapSeqNo,
			  diIndex, diType, diValue1String }
	DESCRIPTION	"This trap is generated when set
			 diValue1TrapID equal 57 and
			while the value of diValue is 1."
	::= 9785

    diValue1-58		TRAP-TYPE
	ENTERPRISE	network-device
	VARIABLES	{ diValue, adminDateAndTime, adminNDTrapSeqNo,
			  diIndex, diType, diValue1String }
	DESCRIPTION	"This trap is generated when set
			 diValue1TrapID equal 58 and
			while the value of diValue is 1."
	::= 9786

    diValue1-59		TRAP-TYPE
	ENTERPRISE	network-device
	VARIABLES	{ diValue, adminDateAndTime, adminNDTrapSeqNo,
			  diIndex, diType, diValue1String }
	DESCRIPTION	"This trap is generated when set
			 diValue1TrapID equal 59 and
			while the value of diValue is 1."
	::= 9787

    diValue1-60		TRAP-TYPE
	ENTERPRISE	network-device
	VARIABLES	{ diValue, adminDateAndTime, adminNDTrapSeqNo,
			  diIndex, diType, diValue1String }
	DESCRIPTION	"This trap is generated when set
			 diValue1TrapID equal 60 and
			while the value of diValue is 1."
	::= 9788

    diValue1-61		TRAP-TYPE
	ENTERPRISE	network-device
	VARIABLES	{ diValue, adminDateAndTime, adminNDTrapSeqNo,
			  diIndex, diType, diValue1String }
	DESCRIPTION	"This trap is generated when set
			 diValue1TrapID equal 61 and
			while the value of diValue is 1."
	::= 9789

    diValue1-62		TRAP-TYPE
	ENTERPRISE	network-device
	VARIABLES	{ diValue, adminDateAndTime, adminNDTrapSeqNo,
			  diIndex, diType, diValue1String }
	DESCRIPTION	"This trap is generated when set
			 diValue1TrapID equal 62 and
			while the value of diValue is 1."
	::= 9790

    diValue1-63		TRAP-TYPE
	ENTERPRISE	network-device
	VARIABLES	{ diValue, adminDateAndTime, adminNDTrapSeqNo,
			  diIndex, diType, diValue1String }
	DESCRIPTION	"This trap is generated when set
			 diValue1TrapID equal 63 and
			while the value of diValue is 1."
	::= 9791

    diValue1-64		TRAP-TYPE
	ENTERPRISE	network-device
	VARIABLES	{ diValue, adminDateAndTime, adminNDTrapSeqNo,
			  diIndex, diType, diValue1String }
	DESCRIPTION	"This trap is generated when set
			 diValue1TrapID equal 64 and
			while the value of diValue is 1."
	::= 9792

    diValue1-65		TRAP-TYPE
	ENTERPRISE	network-device
	VARIABLES	{ diValue, adminDateAndTime, adminNDTrapSeqNo,
			  diIndex, diType, diValue1String }
	DESCRIPTION	"This trap is generated when set
			 diValue1TrapID equal 65 and
			while the value of diValue is 1."
	::= 9793

    diValue1-66		TRAP-TYPE
	ENTERPRISE	network-device
	VARIABLES	{ diValue, adminDateAndTime, adminNDTrapSeqNo,
			  diIndex, diType, diValue1String }
	DESCRIPTION	"This trap is generated when set
			 diValue1TrapID equal 66 and
			while the value of diValue is 1."
	::= 9794

    diValue1-67		TRAP-TYPE
	ENTERPRISE	network-device
	VARIABLES	{ diValue, adminDateAndTime, adminNDTrapSeqNo,
			  diIndex, diType, diValue1String }
	DESCRIPTION	"This trap is generated when set
			 diValue1TrapID equal 67 and
			while the value of diValue is 1."
	::= 9795

    diValue1-68		TRAP-TYPE
	ENTERPRISE	network-device
	VARIABLES	{ diValue, adminDateAndTime, adminNDTrapSeqNo,
			  diIndex, diType, diValue1String }
	DESCRIPTION	"This trap is generated when set
			 diValue1TrapID equal 68 and
			while the value of diValue is 1."
	::= 9796

    diValue1-69		TRAP-TYPE
	ENTERPRISE	network-device
	VARIABLES	{ diValue, adminDateAndTime, adminNDTrapSeqNo,
			  diIndex, diType, diValue1String }
	DESCRIPTION	"This trap is generated when set
			 diValue1TrapID equal 69 and
			while the value of diValue is 1."
	::= 9797

    diValue1-70		TRAP-TYPE
	ENTERPRISE	network-device
	VARIABLES	{ diValue, adminDateAndTime, adminNDTrapSeqNo,
			  diIndex, diType, diValue1String }
	DESCRIPTION	"This trap is generated when set
			 diValue1TrapID equal 70 and
			while the value of diValue is 1."
	::= 9798

    diValue1-71		TRAP-TYPE
	ENTERPRISE	network-device
	VARIABLES	{ diValue, adminDateAndTime, adminNDTrapSeqNo,
			  diIndex, diType, diValue1String }
	DESCRIPTION	"This trap is generated when set
			 diValue1TrapID equal 71 and
			while the value of diValue is 1."
	::= 9799

    diValue1-72		TRAP-TYPE
	ENTERPRISE	network-device
	VARIABLES	{ diValue, adminDateAndTime, adminNDTrapSeqNo,
			  diIndex, diType, diValue1String }
	DESCRIPTION	"This trap is generated when set
			 diValue1TrapID equal 72 and
			while the value of diValue is 1."
	::= 9800

    diValue1-73		TRAP-TYPE
	ENTERPRISE	network-device
	VARIABLES	{ diValue, adminDateAndTime, adminNDTrapSeqNo,
			  diIndex, diType, diValue1String }
	DESCRIPTION	"This trap is generated when set
			 diValue1TrapID equal 73 and
			while the value of diValue is 1."
	::= 9801

    diValue1-74		TRAP-TYPE
	ENTERPRISE	network-device
	VARIABLES	{ diValue, adminDateAndTime, adminNDTrapSeqNo,
			  diIndex, diType, diValue1String }
	DESCRIPTION	"This trap is generated when set
			 diValue1TrapID equal 74 and
			while the value of diValue is 1."
	::= 9802

    diValue1-75		TRAP-TYPE
	ENTERPRISE	network-device
	VARIABLES	{ diValue, adminDateAndTime, adminNDTrapSeqNo,
			  diIndex, diType, diValue1String }
	DESCRIPTION	"This trap is generated when set
			 diValue1TrapID equal 75 and
			while the value of diValue is 1."
	::= 9803

    diValue1-76		TRAP-TYPE
	ENTERPRISE	network-device
	VARIABLES	{ diValue, adminDateAndTime, adminNDTrapSeqNo,
			  diIndex, diType, diValue1String }
	DESCRIPTION	"This trap is generated when set
			 diValue1TrapID equal 76 and
			while the value of diValue is 1."
	::= 9804

    diValue1-77		TRAP-TYPE
	ENTERPRISE	network-device
	VARIABLES	{ diValue, adminDateAndTime, adminNDTrapSeqNo,
			  diIndex, diType, diValue1String }
	DESCRIPTION	"This trap is generated when set
			 diValue1TrapID equal 77 and
			while the value of diValue is 1."
	::= 9805

    diValue1-78		TRAP-TYPE
	ENTERPRISE	network-device
	VARIABLES	{ diValue, adminDateAndTime, adminNDTrapSeqNo,
			  diIndex, diType, diValue1String }
	DESCRIPTION	"This trap is generated when set
			 diValue1TrapID equal 78 and
			while the value of diValue is 1."
	::= 9806

    diValue1-79		TRAP-TYPE
	ENTERPRISE	network-device
	VARIABLES	{ diValue, adminDateAndTime, adminNDTrapSeqNo,
			  diIndex, diType, diValue1String }
	DESCRIPTION	"This trap is generated when set
			 diValue1TrapID equal 79 and
			while the value of diValue is 1."
	::= 9807

    diValue1-80		TRAP-TYPE
	ENTERPRISE	network-device
	VARIABLES	{ diValue, adminDateAndTime, adminNDTrapSeqNo,
			  diIndex, diType, diValue1String }
	DESCRIPTION	"This trap is generated when set
			 diValue1TrapID equal 80 and
			while the value of diValue is 1."
	::= 9808

    diValue1-81		TRAP-TYPE
	ENTERPRISE	network-device
	VARIABLES	{ diValue, adminDateAndTime, adminNDTrapSeqNo,
			  diIndex, diType, diValue1String }
	DESCRIPTION	"This trap is generated when set
			 diValue1TrapID equal 81 and
			while the value of diValue is 1."
	::= 9809

    diValue1-82		TRAP-TYPE
	ENTERPRISE	network-device
	VARIABLES	{ diValue, adminDateAndTime, adminNDTrapSeqNo,
			  diIndex, diType, diValue1String }
	DESCRIPTION	"This trap is generated when set
			 diValue1TrapID equal 82 and
			while the value of diValue is 1."
	::= 9810

    diValue1-83		TRAP-TYPE
	ENTERPRISE	network-device
	VARIABLES	{ diValue, adminDateAndTime, adminNDTrapSeqNo,
			  diIndex, diType, diValue1String }
	DESCRIPTION	"This trap is generated when set
			 diValue1TrapID equal 83 and
			while the value of diValue is 1."
	::= 9811

    diValue1-84		TRAP-TYPE
	ENTERPRISE	network-device
	VARIABLES	{ diValue, adminDateAndTime, adminNDTrapSeqNo,
			  diIndex, diType, diValue1String }
	DESCRIPTION	"This trap is generated when set
			 diValue1TrapID equal 84 and
			while the value of diValue is 1."
	::= 9812

    diValue1-85		TRAP-TYPE
	ENTERPRISE	network-device
	VARIABLES	{ diValue, adminDateAndTime, adminNDTrapSeqNo,
			  diIndex, diType, diValue1String }
	DESCRIPTION	"This trap is generated when set
			 diValue1TrapID equal 85 and
			while the value of diValue is 1."
	::= 9813

    diValue1-86		TRAP-TYPE
	ENTERPRISE	network-device
	VARIABLES	{ diValue, adminDateAndTime, adminNDTrapSeqNo,
			  diIndex, diType, diValue1String }
	DESCRIPTION	"This trap is generated when set
			 diValue1TrapID equal 86 and
			while the value of diValue is 1."
	::= 9814

    diValue1-87		TRAP-TYPE
	ENTERPRISE	network-device
	VARIABLES	{ diValue, adminDateAndTime, adminNDTrapSeqNo,
			  diIndex, diType, diValue1String }
	DESCRIPTION	"This trap is generated when set
			 diValue1TrapID equal 87 and
			while the value of diValue is 1."
	::= 9815

    diValue1-88		TRAP-TYPE
	ENTERPRISE	network-device
	VARIABLES	{ diValue, adminDateAndTime, adminNDTrapSeqNo,
			  diIndex, diType, diValue1String }
	DESCRIPTION	"This trap is generated when set
			 diValue1TrapID equal 88 and
			while the value of diValue is 1."
	::= 9816

    diValue1-89		TRAP-TYPE
	ENTERPRISE	network-device
	VARIABLES	{ diValue, adminDateAndTime, adminNDTrapSeqNo,
			  diIndex, diType, diValue1String }
	DESCRIPTION	"This trap is generated when set
			 diValue1TrapID equal 89 and
			while the value of diValue is 1."
	::= 9817

    diValue1-90		TRAP-TYPE
	ENTERPRISE	network-device
	VARIABLES	{ diValue, adminDateAndTime, adminNDTrapSeqNo,
			  diIndex, diType, diValue1String }
	DESCRIPTION	"This trap is generated when set
			 diValue1TrapID equal 90 and
			while the value of diValue is 1."
	::= 9818

    diValue1-91		TRAP-TYPE
	ENTERPRISE	network-device
	VARIABLES	{ diValue, adminDateAndTime, adminNDTrapSeqNo,
			  diIndex, diType, diValue1String }
	DESCRIPTION	"This trap is generated when set
			 diValue1TrapID equal 91 and
			while the value of diValue is 1."
	::= 9819

    diValue1-92		TRAP-TYPE
	ENTERPRISE	network-device
	VARIABLES	{ diValue, adminDateAndTime, adminNDTrapSeqNo,
			  diIndex, diType, diValue1String }
	DESCRIPTION	"This trap is generated when set
			 diValue1TrapID equal 92 and
			while the value of diValue is 1."
	::= 9820

    diValue1-93		TRAP-TYPE
	ENTERPRISE	network-device
	VARIABLES	{ diValue, adminDateAndTime, adminNDTrapSeqNo,
			  diIndex, diType, diValue1String }
	DESCRIPTION	"This trap is generated when set
			 diValue1TrapID equal 93 and
			while the value of diValue is 1."
	::= 9821

    diValue1-94		TRAP-TYPE
	ENTERPRISE	network-device
	VARIABLES	{ diValue, adminDateAndTime, adminNDTrapSeqNo,
			  diIndex, diType, diValue1String }
	DESCRIPTION	"This trap is generated when set
			 diValue1TrapID equal 94 and
			while the value of diValue is 1."
	::= 9822

    diValue1-95		TRAP-TYPE
	ENTERPRISE	network-device
	VARIABLES	{ diValue, adminDateAndTime, adminNDTrapSeqNo,
			  diIndex, diType, diValue1String }
	DESCRIPTION	"This trap is generated when set
			 diValue1TrapID equal 95 and
			while the value of diValue is 1."
	::= 9823

    diValue1-96		TRAP-TYPE
	ENTERPRISE	network-device
	VARIABLES	{ diValue, adminDateAndTime, adminNDTrapSeqNo,
			  diIndex, diType, diValue1String }
	DESCRIPTION	"This trap is generated when set
			 diValue1TrapID equal 96 and
			while the value of diValue is 1."
	::= 9824

    diValue1-97		TRAP-TYPE
	ENTERPRISE	network-device
	VARIABLES	{ diValue, adminDateAndTime, adminNDTrapSeqNo,
			  diIndex, diType, diValue1String }
	DESCRIPTION	"This trap is generated when set
			 diValue1TrapID equal 97 and
			while the value of diValue is 1."
	::= 9825

    diValue1-98		TRAP-TYPE
	ENTERPRISE	network-device
	VARIABLES	{ diValue, adminDateAndTime, adminNDTrapSeqNo,
			  diIndex, diType, diValue1String }
	DESCRIPTION	"This trap is generated when set
			 diValue1TrapID equal 98 and
			while the value of diValue is 1."
	::= 9826

    diValue1-99		TRAP-TYPE
	ENTERPRISE	network-device
	VARIABLES	{ diValue, adminDateAndTime, adminNDTrapSeqNo,
			  diIndex, diType, diValue1String }
	DESCRIPTION	"This trap is generated when set
			 diValue1TrapID equal 99 and
			while the value of diValue is 1."
	::= 9827

    diValue1-100		TRAP-TYPE
	ENTERPRISE	network-device
	VARIABLES	{ diValue, adminDateAndTime, adminNDTrapSeqNo,
			  diIndex, diType, diValue1String }
	DESCRIPTION	"This trap is generated when set
			 diValue1TrapID equal 100 and
			while the value of diValue is 1."
	::= 9828

    diValue1-101		TRAP-TYPE
	ENTERPRISE	network-device
	VARIABLES	{ diValue, adminDateAndTime, adminNDTrapSeqNo,
			  diIndex, diType, diValue1String }
	DESCRIPTION	"This trap is generated when set
			 diValue1TrapID equal 101 and
			while the value of diValue is 1."
	::= 9829

    diValue1-102		TRAP-TYPE
	ENTERPRISE	network-device
	VARIABLES	{ diValue, adminDateAndTime, adminNDTrapSeqNo,
			  diIndex, diType, diValue1String }
	DESCRIPTION	"This trap is generated when set
			 diValue1TrapID equal 102 and
			while the value of diValue is 1."
	::= 9830

    diValue1-103		TRAP-TYPE
	ENTERPRISE	network-device
	VARIABLES	{ diValue, adminDateAndTime, adminNDTrapSeqNo,
			  diIndex, diType, diValue1String }
	DESCRIPTION	"This trap is generated when set
			 diValue1TrapID equal 103 and
			while the value of diValue is 1."
	::= 9831

    diValue1-104		TRAP-TYPE
	ENTERPRISE	network-device
	VARIABLES	{ diValue, adminDateAndTime, adminNDTrapSeqNo,
			  diIndex, diType, diValue1String }
	DESCRIPTION	"This trap is generated when set
			 diValue1TrapID equal 104 and
			while the value of diValue is 1."
	::= 9832

    diValue1-105		TRAP-TYPE
	ENTERPRISE	network-device
	VARIABLES	{ diValue, adminDateAndTime, adminNDTrapSeqNo,
			  diIndex, diType, diValue1String }
	DESCRIPTION	"This trap is generated when set
			 diValue1TrapID equal 105 and
			while the value of diValue is 1."
	::= 9833

    diValue1-106		TRAP-TYPE
	ENTERPRISE	network-device
	VARIABLES	{ diValue, adminDateAndTime, adminNDTrapSeqNo,
			  diIndex, diType, diValue1String }
	DESCRIPTION	"This trap is generated when set
			 diValue1TrapID equal 106 and
			while the value of diValue is 1."
	::= 9834

    diValue1-107		TRAP-TYPE
	ENTERPRISE	network-device
	VARIABLES	{ diValue, adminDateAndTime, adminNDTrapSeqNo,
			  diIndex, diType, diValue1String }
	DESCRIPTION	"This trap is generated when set
			 diValue1TrapID equal 107 and
			while the value of diValue is 1."
	::= 9835

    diValue1-108		TRAP-TYPE
	ENTERPRISE	network-device
	VARIABLES	{ diValue, adminDateAndTime, adminNDTrapSeqNo,
			  diIndex, diType, diValue1String }
	DESCRIPTION	"This trap is generated when set
			 diValue1TrapID equal 108 and
			while the value of diValue is 1."
	::= 9836

    diValue1-109		TRAP-TYPE
	ENTERPRISE	network-device
	VARIABLES	{ diValue, adminDateAndTime, adminNDTrapSeqNo,
			  diIndex, diType, diValue1String }
	DESCRIPTION	"This trap is generated when set
			 diValue1TrapID equal 109 and
			while the value of diValue is 1."
	::= 9837

    diValue1-110		TRAP-TYPE
	ENTERPRISE	network-device
	VARIABLES	{ diValue, adminDateAndTime, adminNDTrapSeqNo,
			  diIndex, diType, diValue1String }
	DESCRIPTION	"This trap is generated when set
			 diValue1TrapID equal 110 and
			while the value of diValue is 1."
	::= 9838

    diValue1-111		TRAP-TYPE
	ENTERPRISE	network-device
	VARIABLES	{ diValue, adminDateAndTime, adminNDTrapSeqNo,
			  diIndex, diType, diValue1String }
	DESCRIPTION	"This trap is generated when set
			 diValue1TrapID equal 111 and
			while the value of diValue is 1."
	::= 9839

    diValue1-112		TRAP-TYPE
	ENTERPRISE	network-device
	VARIABLES	{ diValue, adminDateAndTime, adminNDTrapSeqNo,
			  diIndex, diType, diValue1String }
	DESCRIPTION	"This trap is generated when set
			 diValue1TrapID equal 112 and
			while the value of diValue is 1."
	::= 9840

    diValue1-113		TRAP-TYPE
	ENTERPRISE	network-device
	VARIABLES	{ diValue, adminDateAndTime, adminNDTrapSeqNo,
			  diIndex, diType, diValue1String }
	DESCRIPTION	"This trap is generated when set
			 diValue1TrapID equal 113 and
			while the value of diValue is 1."
	::= 9841

    diValue1-114		TRAP-TYPE
	ENTERPRISE	network-device
	VARIABLES	{ diValue, adminDateAndTime, adminNDTrapSeqNo,
			  diIndex, diType, diValue1String }
	DESCRIPTION	"This trap is generated when set
			 diValue1TrapID equal 114 and
			while the value of diValue is 1."
	::= 9842

    diValue1-115		TRAP-TYPE
	ENTERPRISE	network-device
	VARIABLES	{ diValue, adminDateAndTime, adminNDTrapSeqNo,
			  diIndex, diType, diValue1String }
	DESCRIPTION	"This trap is generated when set
			 diValue1TrapID equal 115 and
			while the value of diValue is 1."
	::= 9843

    diValue1-116		TRAP-TYPE
	ENTERPRISE	network-device
	VARIABLES	{ diValue, adminDateAndTime, adminNDTrapSeqNo,
			  diIndex, diType, diValue1String }
	DESCRIPTION	"This trap is generated when set
			 diValue1TrapID equal 116 and
			while the value of diValue is 1."
	::= 9844

    diValue1-117		TRAP-TYPE
	ENTERPRISE	network-device
	VARIABLES	{ diValue, adminDateAndTime, adminNDTrapSeqNo,
			  diIndex, diType, diValue1String }
	DESCRIPTION	"This trap is generated when set
			 diValue1TrapID equal 117 and
			while the value of diValue is 1."
	::= 9845

    diValue1-118		TRAP-TYPE
	ENTERPRISE	network-device
	VARIABLES	{ diValue, adminDateAndTime, adminNDTrapSeqNo,
			  diIndex, diType, diValue1String }
	DESCRIPTION	"This trap is generated when set
			 diValue1TrapID equal 118 and
			while the value of diValue is 1."
	::= 9846

    diValue1-119		TRAP-TYPE
	ENTERPRISE	network-device
	VARIABLES	{ diValue, adminDateAndTime, adminNDTrapSeqNo,
			  diIndex, diType, diValue1String }
	DESCRIPTION	"This trap is generated when set
			 diValue1TrapID equal 119 and
			while the value of diValue is 1."
	::= 9847

    diValue1-120		TRAP-TYPE
	ENTERPRISE	network-device
	VARIABLES	{ diValue, adminDateAndTime, adminNDTrapSeqNo,
			  diIndex, diType, diValue1String }
	DESCRIPTION	"This trap is generated when set
			 diValue1TrapID equal 120 and
			while the value of diValue is 1."
	::= 9848

    diValue1-121		TRAP-TYPE
	ENTERPRISE	network-device
	VARIABLES	{ diValue, adminDateAndTime, adminNDTrapSeqNo,
			  diIndex, diType, diValue1String }
	DESCRIPTION	"This trap is generated when set
			 diValue1TrapID equal 121 and
			while the value of diValue is 1."
	::= 9849

    diValue1-122		TRAP-TYPE
	ENTERPRISE	network-device
	VARIABLES	{ diValue, adminDateAndTime, adminNDTrapSeqNo,
			  diIndex, diType, diValue1String }
	DESCRIPTION	"This trap is generated when set
			 diValue1TrapID equal 122 and
			while the value of diValue is 1."
	::= 9850

    diValue1-123		TRAP-TYPE
	ENTERPRISE	network-device
	VARIABLES	{ diValue, adminDateAndTime, adminNDTrapSeqNo,
			  diIndex, diType, diValue1String }
	DESCRIPTION	"This trap is generated when set
			 diValue1TrapID equal 123 and
			while the value of diValue is 1."
	::= 9851

    diValue1-124		TRAP-TYPE
	ENTERPRISE	network-device
	VARIABLES	{ diValue, adminDateAndTime, adminNDTrapSeqNo,
			  diIndex, diType, diValue1String }
	DESCRIPTION	"This trap is generated when set
			 diValue1TrapID equal 124 and
			while the value of diValue is 1."
	::= 9852

    diValue1-125		TRAP-TYPE
	ENTERPRISE	network-device
	VARIABLES	{ diValue, adminDateAndTime, adminNDTrapSeqNo,
			  diIndex, diType, diValue1String }
	DESCRIPTION	"This trap is generated when set
			 diValue1TrapID equal 125 and
			while the value of diValue is 1."
	::= 9853

    diValue1-126		TRAP-TYPE
	ENTERPRISE	network-device
	VARIABLES	{ diValue, adminDateAndTime, adminNDTrapSeqNo,
			  diIndex, diType, diValue1String }
	DESCRIPTION	"This trap is generated when set
			 diValue1TrapID equal 126 and
			while the value of diValue is 1."
	::= 9854

    diValue1-127		TRAP-TYPE
	ENTERPRISE	network-device
	VARIABLES	{ diValue, adminDateAndTime, adminNDTrapSeqNo,
			  diIndex, diType, diValue1String }
	DESCRIPTION	"This trap is generated when set
			 diValue1TrapID equal 127 and
			while the value of diValue is 1."
	::= 9855

    diPulseCountTrap1	TRAP-TYPE
	ENTERPRISE	network-device
	VARIABLES	{ diPulseCount, adminDateAndTime, adminNDTrapSeqNo,
			  diIndex, diType }
	DESCRIPTION	"This trap is generated when set
			 diPulseCountTrapID equal 1 and
			diPulseCount exceeds diPulseCountLimit."
	::= 10241

    diPulseCountTrap2	TRAP-TYPE
	ENTERPRISE	network-device
	VARIABLES	{ diPulseCount, adminDateAndTime, adminNDTrapSeqNo,
			  diIndex, diType }
	DESCRIPTION	"This trap is generated when set
			 diPulseCountTrapID equal 2 and
			diPulseCount exceeds diPulseCountLimit."
	::= 10242

    diPulseCountTrap3	TRAP-TYPE
	ENTERPRISE	network-device
	VARIABLES	{ diPulseCount, adminDateAndTime, adminNDTrapSeqNo,
			  diIndex, diType }
	DESCRIPTION	"This trap is generated when set
			 diPulseCountTrapID equal 3 and
			diPulseCount exceeds diPulseCountLimit."
	::= 10243

    diPulseCountTrap4	TRAP-TYPE
	ENTERPRISE	network-device
	VARIABLES	{ diPulseCount, adminDateAndTime, adminNDTrapSeqNo,
			  diIndex, diType }
	DESCRIPTION	"This trap is generated when set
			 diPulseCountTrapID equal 4 and
			diPulseCount exceeds diPulseCountLimit."
	::= 10244

    diPulseCountTrap5	TRAP-TYPE
	ENTERPRISE	network-device
	VARIABLES	{ diPulseCount, adminDateAndTime, adminNDTrapSeqNo,
			  diIndex, diType }
	DESCRIPTION	"This trap is generated when set
			 diPulseCountTrapID equal 5 and
			diPulseCount exceeds diPulseCountLimit."
	::= 10245

    diPulseCountTrap6	TRAP-TYPE
	ENTERPRISE	network-device
	VARIABLES	{ diPulseCount, adminDateAndTime, adminNDTrapSeqNo,
			  diIndex, diType }
	DESCRIPTION	"This trap is generated when set
			 diPulseCountTrapID equal 6 and
			diPulseCount exceeds diPulseCountLimit."
	::= 10246

    diPulseCountTrap7	TRAP-TYPE
	ENTERPRISE	network-device
	VARIABLES	{ diPulseCount, adminDateAndTime, adminNDTrapSeqNo,
			  diIndex, diType }
	DESCRIPTION	"This trap is generated when set
			 diPulseCountTrapID equal 7 and
			diPulseCount exceeds diPulseCountLimit."
	::= 10247

    diPulseCountTrap8	TRAP-TYPE
	ENTERPRISE	network-device
	VARIABLES	{ diPulseCount, adminDateAndTime, adminNDTrapSeqNo,
			  diIndex, diType }
	DESCRIPTION	"This trap is generated when set
			 diPulseCountTrapID equal 8 and
			diPulseCount exceeds diPulseCountLimit."
	::= 10248

    diPulseCountTrap9	TRAP-TYPE
	ENTERPRISE	network-device
	VARIABLES	{ diPulseCount, adminDateAndTime, adminNDTrapSeqNo,
			  diIndex, diType }
	DESCRIPTION	"This trap is generated when set
			 diPulseCountTrapID equal 9 and
			diPulseCount exceeds diPulseCountLimit."
	::= 10249

    diPulseCountTrap10	TRAP-TYPE
	ENTERPRISE	network-device
	VARIABLES	{ diPulseCount, adminDateAndTime, adminNDTrapSeqNo,
			  diIndex, diType }
	DESCRIPTION	"This trap is generated when set
			 diPulseCountTrapID equal 10 and
			diPulseCount exceeds diPulseCountLimit."
	::= 10250

    diPulseCountTrap11	TRAP-TYPE
	ENTERPRISE	network-device
	VARIABLES	{ diPulseCount, adminDateAndTime, adminNDTrapSeqNo,
			  diIndex, diType }
	DESCRIPTION	"This trap is generated when set
			 diPulseCountTrapID equal 11 and
			diPulseCount exceeds diPulseCountLimit."
	::= 10251

    diPulseCountTrap12	TRAP-TYPE
	ENTERPRISE	network-device
	VARIABLES	{ diPulseCount, adminDateAndTime, adminNDTrapSeqNo,
			  diIndex, diType }
	DESCRIPTION	"This trap is generated when set
			 diPulseCountTrapID equal 12 and
			diPulseCount exceeds diPulseCountLimit."
	::= 10252

    diPulseCountTrap13	TRAP-TYPE
	ENTERPRISE	network-device
	VARIABLES	{ diPulseCount, adminDateAndTime, adminNDTrapSeqNo,
			  diIndex, diType }
	DESCRIPTION	"This trap is generated when set
			 diPulseCountTrapID equal 13 and
			diPulseCount exceeds diPulseCountLimit."
	::= 10253

    diPulseCountTrap14	TRAP-TYPE
	ENTERPRISE	network-device
	VARIABLES	{ diPulseCount, adminDateAndTime, adminNDTrapSeqNo,
			  diIndex, diType }
	DESCRIPTION	"This trap is generated when set
			 diPulseCountTrapID equal 14 and
			diPulseCount exceeds diPulseCountLimit."
	::= 10254

    diPulseCountTrap15	TRAP-TYPE
	ENTERPRISE	network-device
	VARIABLES	{ diPulseCount, adminDateAndTime, adminNDTrapSeqNo,
			  diIndex, diType }
	DESCRIPTION	"This trap is generated when set
			 diPulseCountTrapID equal 15 and
			diPulseCount exceeds diPulseCountLimit."
	::= 10255

    diPulseCountTrap16	TRAP-TYPE
	ENTERPRISE	network-device
	VARIABLES	{ diPulseCount, adminDateAndTime, adminNDTrapSeqNo,
			  diIndex, diType }
	DESCRIPTION	"This trap is generated when set
			 diPulseCountTrapID equal 16 and
			diPulseCount exceeds diPulseCountLimit."
	::= 10256

    diPulseCountTrap17	TRAP-TYPE
	ENTERPRISE	network-device
	VARIABLES	{ diPulseCount, adminDateAndTime, adminNDTrapSeqNo,
			  diIndex, diType }
	DESCRIPTION	"This trap is generated when set
			 diPulseCountTrapID equal 17 and
			diPulseCount exceeds diPulseCountLimit."
	::= 10257

    diPulseCountTrap18	TRAP-TYPE
	ENTERPRISE	network-device
	VARIABLES	{ diPulseCount, adminDateAndTime, adminNDTrapSeqNo,
			  diIndex, diType }
	DESCRIPTION	"This trap is generated when set
			 diPulseCountTrapID equal 18 and
			diPulseCount exceeds diPulseCountLimit."
	::= 10258

    diPulseCountTrap19	TRAP-TYPE
	ENTERPRISE	network-device
	VARIABLES	{ diPulseCount, adminDateAndTime, adminNDTrapSeqNo,
			  diIndex, diType }
	DESCRIPTION	"This trap is generated when set
			 diPulseCountTrapID equal 19 and
			diPulseCount exceeds diPulseCountLimit."
	::= 10259

    diPulseCountTrap20	TRAP-TYPE
	ENTERPRISE	network-device
	VARIABLES	{ diPulseCount, adminDateAndTime, adminNDTrapSeqNo,
			  diIndex, diType }
	DESCRIPTION	"This trap is generated when set
			 diPulseCountTrapID equal 20 and
			diPulseCount exceeds diPulseCountLimit."
	::= 10260

    diPulseCountTrap21	TRAP-TYPE
	ENTERPRISE	network-device
	VARIABLES	{ diPulseCount, adminDateAndTime, adminNDTrapSeqNo,
			  diIndex, diType }
	DESCRIPTION	"This trap is generated when set
			 diPulseCountTrapID equal 21 and
			diPulseCount exceeds diPulseCountLimit."
	::= 10261

    diPulseCountTrap22	TRAP-TYPE
	ENTERPRISE	network-device
	VARIABLES	{ diPulseCount, adminDateAndTime, adminNDTrapSeqNo,
			  diIndex, diType }
	DESCRIPTION	"This trap is generated when set
			 diPulseCountTrapID equal 22 and
			diPulseCount exceeds diPulseCountLimit."
	::= 10262

    diPulseCountTrap23	TRAP-TYPE
	ENTERPRISE	network-device
	VARIABLES	{ diPulseCount, adminDateAndTime, adminNDTrapSeqNo,
			  diIndex, diType }
	DESCRIPTION	"This trap is generated when set
			 diPulseCountTrapID equal 23 and
			diPulseCount exceeds diPulseCountLimit."
	::= 10263

    diPulseCountTrap24	TRAP-TYPE
	ENTERPRISE	network-device
	VARIABLES	{ diPulseCount, adminDateAndTime, adminNDTrapSeqNo,
			  diIndex, diType }
	DESCRIPTION	"This trap is generated when set
			 diPulseCountTrapID equal 24 and
			diPulseCount exceeds diPulseCountLimit."
	::= 10264

    diPulseCountTrap25	TRAP-TYPE
	ENTERPRISE	network-device
	VARIABLES	{ diPulseCount, adminDateAndTime, adminNDTrapSeqNo,
			  diIndex, diType }
	DESCRIPTION	"This trap is generated when set
			 diPulseCountTrapID equal 25 and
			diPulseCount exceeds diPulseCountLimit."
	::= 10265

    diPulseCountTrap26	TRAP-TYPE
	ENTERPRISE	network-device
	VARIABLES	{ diPulseCount, adminDateAndTime, adminNDTrapSeqNo,
			  diIndex, diType }
	DESCRIPTION	"This trap is generated when set
			 diPulseCountTrapID equal 26 and
			diPulseCount exceeds diPulseCountLimit."
	::= 10266

    diPulseCountTrap27	TRAP-TYPE
	ENTERPRISE	network-device
	VARIABLES	{ diPulseCount, adminDateAndTime, adminNDTrapSeqNo,
			  diIndex, diType }
	DESCRIPTION	"This trap is generated when set
			 diPulseCountTrapID equal 27 and
			diPulseCount exceeds diPulseCountLimit."
	::= 10267

    diPulseCountTrap28	TRAP-TYPE
	ENTERPRISE	network-device
	VARIABLES	{ diPulseCount, adminDateAndTime, adminNDTrapSeqNo,
			  diIndex, diType }
	DESCRIPTION	"This trap is generated when set
			 diPulseCountTrapID equal 28 and
			diPulseCount exceeds diPulseCountLimit."
	::= 10268

    diPulseCountTrap29	TRAP-TYPE
	ENTERPRISE	network-device
	VARIABLES	{ diPulseCount, adminDateAndTime, adminNDTrapSeqNo,
			  diIndex, diType }
	DESCRIPTION	"This trap is generated when set
			 diPulseCountTrapID equal 29 and
			diPulseCount exceeds diPulseCountLimit."
	::= 10269

    diPulseCountTrap30	TRAP-TYPE
	ENTERPRISE	network-device
	VARIABLES	{ diPulseCount, adminDateAndTime, adminNDTrapSeqNo,
			  diIndex, diType }
	DESCRIPTION	"This trap is generated when set
			 diPulseCountTrapID equal 30 and
			diPulseCount exceeds diPulseCountLimit."
	::= 10270

    diPulseCountTrap31	TRAP-TYPE
	ENTERPRISE	network-device
	VARIABLES	{ diPulseCount, adminDateAndTime, adminNDTrapSeqNo,
			  diIndex, diType }
	DESCRIPTION	"This trap is generated when set
			 diPulseCountTrapID equal 31 and
			diPulseCount exceeds diPulseCountLimit."
	::= 10271

    diPulseCountTrap32	TRAP-TYPE
	ENTERPRISE	network-device
	VARIABLES	{ diPulseCount, adminDateAndTime, adminNDTrapSeqNo,
			  diIndex, diType }
	DESCRIPTION	"This trap is generated when set
			 diPulseCountTrapID equal 32 and
			diPulseCount exceeds diPulseCountLimit."
	::= 10272

    diPulseCountTrap33	TRAP-TYPE
	ENTERPRISE	network-device
	VARIABLES	{ diPulseCount, adminDateAndTime, adminNDTrapSeqNo,
			  diIndex, diType }
	DESCRIPTION	"This trap is generated when set
			 diPulseCountTrapID equal 33 and
			diPulseCount exceeds diPulseCountLimit."
	::= 10273

    diPulseCountTrap34	TRAP-TYPE
	ENTERPRISE	network-device
	VARIABLES	{ diPulseCount, adminDateAndTime, adminNDTrapSeqNo,
			  diIndex, diType }
	DESCRIPTION	"This trap is generated when set
			 diPulseCountTrapID equal 34 and
			diPulseCount exceeds diPulseCountLimit."
	::= 10274

    diPulseCountTrap35	TRAP-TYPE
	ENTERPRISE	network-device
	VARIABLES	{ diPulseCount, adminDateAndTime, adminNDTrapSeqNo,
			  diIndex, diType }
	DESCRIPTION	"This trap is generated when set
			 diPulseCountTrapID equal 35 and
			diPulseCount exceeds diPulseCountLimit."
	::= 10275

    diPulseCountTrap36	TRAP-TYPE
	ENTERPRISE	network-device
	VARIABLES	{ diPulseCount, adminDateAndTime, adminNDTrapSeqNo,
			  diIndex, diType }
	DESCRIPTION	"This trap is generated when set
			 diPulseCountTrapID equal 36 and
			diPulseCount exceeds diPulseCountLimit."
	::= 10276

    diPulseCountTrap37	TRAP-TYPE
	ENTERPRISE	network-device
	VARIABLES	{ diPulseCount, adminDateAndTime, adminNDTrapSeqNo,
			  diIndex, diType }
	DESCRIPTION	"This trap is generated when set
			 diPulseCountTrapID equal 37 and
			diPulseCount exceeds diPulseCountLimit."
	::= 10277

    diPulseCountTrap38	TRAP-TYPE
	ENTERPRISE	network-device
	VARIABLES	{ diPulseCount, adminDateAndTime, adminNDTrapSeqNo,
			  diIndex, diType }
	DESCRIPTION	"This trap is generated when set
			 diPulseCountTrapID equal 38 and
			diPulseCount exceeds diPulseCountLimit."
	::= 10278

    diPulseCountTrap39	TRAP-TYPE
	ENTERPRISE	network-device
	VARIABLES	{ diPulseCount, adminDateAndTime, adminNDTrapSeqNo,
			  diIndex, diType }
	DESCRIPTION	"This trap is generated when set
			 diPulseCountTrapID equal 39 and
			diPulseCount exceeds diPulseCountLimit."
	::= 10279

    diPulseCountTrap40	TRAP-TYPE
	ENTERPRISE	network-device
	VARIABLES	{ diPulseCount, adminDateAndTime, adminNDTrapSeqNo,
			  diIndex, diType }
	DESCRIPTION	"This trap is generated when set
			 diPulseCountTrapID equal 40 and
			diPulseCount exceeds diPulseCountLimit."
	::= 10280

    diPulseCountTrap41	TRAP-TYPE
	ENTERPRISE	network-device
	VARIABLES	{ diPulseCount, adminDateAndTime, adminNDTrapSeqNo,
			  diIndex, diType }
	DESCRIPTION	"This trap is generated when set
			 diPulseCountTrapID equal 41 and
			diPulseCount exceeds diPulseCountLimit."
	::= 10281

    diPulseCountTrap42	TRAP-TYPE
	ENTERPRISE	network-device
	VARIABLES	{ diPulseCount, adminDateAndTime, adminNDTrapSeqNo,
			  diIndex, diType }
	DESCRIPTION	"This trap is generated when set
			 diPulseCountTrapID equal 42 and
			diPulseCount exceeds diPulseCountLimit."
	::= 10282

    diPulseCountTrap43	TRAP-TYPE
	ENTERPRISE	network-device
	VARIABLES	{ diPulseCount, adminDateAndTime, adminNDTrapSeqNo,
			  diIndex, diType }
	DESCRIPTION	"This trap is generated when set
			 diPulseCountTrapID equal 43 and
			diPulseCount exceeds diPulseCountLimit."
	::= 10283

    diPulseCountTrap44	TRAP-TYPE
	ENTERPRISE	network-device
	VARIABLES	{ diPulseCount, adminDateAndTime, adminNDTrapSeqNo,
			  diIndex, diType }
	DESCRIPTION	"This trap is generated when set
			 diPulseCountTrapID equal 44 and
			diPulseCount exceeds diPulseCountLimit."
	::= 10284

    diPulseCountTrap45	TRAP-TYPE
	ENTERPRISE	network-device
	VARIABLES	{ diPulseCount, adminDateAndTime, adminNDTrapSeqNo,
			  diIndex, diType }
	DESCRIPTION	"This trap is generated when set
			 diPulseCountTrapID equal 45 and
			diPulseCount exceeds diPulseCountLimit."
	::= 10285

    diPulseCountTrap46	TRAP-TYPE
	ENTERPRISE	network-device
	VARIABLES	{ diPulseCount, adminDateAndTime, adminNDTrapSeqNo,
			  diIndex, diType }
	DESCRIPTION	"This trap is generated when set
			 diPulseCountTrapID equal 46 and
			diPulseCount exceeds diPulseCountLimit."
	::= 10286

    diPulseCountTrap47	TRAP-TYPE
	ENTERPRISE	network-device
	VARIABLES	{ diPulseCount, adminDateAndTime, adminNDTrapSeqNo,
			  diIndex, diType }
	DESCRIPTION	"This trap is generated when set
			 diPulseCountTrapID equal 47 and
			diPulseCount exceeds diPulseCountLimit."
	::= 10287

    diPulseCountTrap48	TRAP-TYPE
	ENTERPRISE	network-device
	VARIABLES	{ diPulseCount, adminDateAndTime, adminNDTrapSeqNo,
			  diIndex, diType }
	DESCRIPTION	"This trap is generated when set
			 diPulseCountTrapID equal 48 and
			diPulseCount exceeds diPulseCountLimit."
	::= 10288

    diPulseCountTrap49	TRAP-TYPE
	ENTERPRISE	network-device
	VARIABLES	{ diPulseCount, adminDateAndTime, adminNDTrapSeqNo,
			  diIndex, diType }
	DESCRIPTION	"This trap is generated when set
			 diPulseCountTrapID equal 49 and
			diPulseCount exceeds diPulseCountLimit."
	::= 10289

    diPulseCountTrap50	TRAP-TYPE
	ENTERPRISE	network-device
	VARIABLES	{ diPulseCount, adminDateAndTime, adminNDTrapSeqNo,
			  diIndex, diType }
	DESCRIPTION	"This trap is generated when set
			 diPulseCountTrapID equal 50 and
			diPulseCount exceeds diPulseCountLimit."
	::= 10290

    diPulseCountTrap51	TRAP-TYPE
	ENTERPRISE	network-device
	VARIABLES	{ diPulseCount, adminDateAndTime, adminNDTrapSeqNo,
			  diIndex, diType }
	DESCRIPTION	"This trap is generated when set
			 diPulseCountTrapID equal 51 and
			diPulseCount exceeds diPulseCountLimit."
	::= 10291

    diPulseCountTrap52	TRAP-TYPE
	ENTERPRISE	network-device
	VARIABLES	{ diPulseCount, adminDateAndTime, adminNDTrapSeqNo,
			  diIndex, diType }
	DESCRIPTION	"This trap is generated when set
			 diPulseCountTrapID equal 52 and
			diPulseCount exceeds diPulseCountLimit."
	::= 10292

    diPulseCountTrap53	TRAP-TYPE
	ENTERPRISE	network-device
	VARIABLES	{ diPulseCount, adminDateAndTime, adminNDTrapSeqNo,
			  diIndex, diType }
	DESCRIPTION	"This trap is generated when set
			 diPulseCountTrapID equal 53 and
			diPulseCount exceeds diPulseCountLimit."
	::= 10293

    diPulseCountTrap54	TRAP-TYPE
	ENTERPRISE	network-device
	VARIABLES	{ diPulseCount, adminDateAndTime, adminNDTrapSeqNo,
			  diIndex, diType }
	DESCRIPTION	"This trap is generated when set
			 diPulseCountTrapID equal 54 and
			diPulseCount exceeds diPulseCountLimit."
	::= 10294

    diPulseCountTrap55	TRAP-TYPE
	ENTERPRISE	network-device
	VARIABLES	{ diPulseCount, adminDateAndTime, adminNDTrapSeqNo,
			  diIndex, diType }
	DESCRIPTION	"This trap is generated when set
			 diPulseCountTrapID equal 55 and
			diPulseCount exceeds diPulseCountLimit."
	::= 10295

    diPulseCountTrap56	TRAP-TYPE
	ENTERPRISE	network-device
	VARIABLES	{ diPulseCount, adminDateAndTime, adminNDTrapSeqNo,
			  diIndex, diType }
	DESCRIPTION	"This trap is generated when set
			 diPulseCountTrapID equal 56 and
			diPulseCount exceeds diPulseCountLimit."
	::= 10296

    diPulseCountTrap57	TRAP-TYPE
	ENTERPRISE	network-device
	VARIABLES	{ diPulseCount, adminDateAndTime, adminNDTrapSeqNo,
			  diIndex, diType }
	DESCRIPTION	"This trap is generated when set
			 diPulseCountTrapID equal 57 and
			diPulseCount exceeds diPulseCountLimit."
	::= 10297

    diPulseCountTrap58	TRAP-TYPE
	ENTERPRISE	network-device
	VARIABLES	{ diPulseCount, adminDateAndTime, adminNDTrapSeqNo,
			  diIndex, diType }
	DESCRIPTION	"This trap is generated when set
			 diPulseCountTrapID equal 58 and
			diPulseCount exceeds diPulseCountLimit."
	::= 10298

    diPulseCountTrap59	TRAP-TYPE
	ENTERPRISE	network-device
	VARIABLES	{ diPulseCount, adminDateAndTime, adminNDTrapSeqNo,
			  diIndex, diType }
	DESCRIPTION	"This trap is generated when set
			 diPulseCountTrapID equal 59 and
			diPulseCount exceeds diPulseCountLimit."
	::= 10299

    diPulseCountTrap60	TRAP-TYPE
	ENTERPRISE	network-device
	VARIABLES	{ diPulseCount, adminDateAndTime, adminNDTrapSeqNo,
			  diIndex, diType }
	DESCRIPTION	"This trap is generated when set
			 diPulseCountTrapID equal 60 and
			diPulseCount exceeds diPulseCountLimit."
	::= 10300

    diPulseCountTrap61	TRAP-TYPE
	ENTERPRISE	network-device
	VARIABLES	{ diPulseCount, adminDateAndTime, adminNDTrapSeqNo,
			  diIndex, diType }
	DESCRIPTION	"This trap is generated when set
			 diPulseCountTrapID equal 61 and
			diPulseCount exceeds diPulseCountLimit."
	::= 10301

    diPulseCountTrap62	TRAP-TYPE
	ENTERPRISE	network-device
	VARIABLES	{ diPulseCount, adminDateAndTime, adminNDTrapSeqNo,
			  diIndex, diType }
	DESCRIPTION	"This trap is generated when set
			 diPulseCountTrapID equal 62 and
			diPulseCount exceeds diPulseCountLimit."
	::= 10302

    diPulseCountTrap63	TRAP-TYPE
	ENTERPRISE	network-device
	VARIABLES	{ diPulseCount, adminDateAndTime, adminNDTrapSeqNo,
			  diIndex, diType }
	DESCRIPTION	"This trap is generated when set
			 diPulseCountTrapID equal 63 and
			diPulseCount exceeds diPulseCountLimit."
	::= 10303

    diPulseCountTrap64	TRAP-TYPE
	ENTERPRISE	network-device
	VARIABLES	{ diPulseCount, adminDateAndTime, adminNDTrapSeqNo,
			  diIndex, diType }
	DESCRIPTION	"This trap is generated when set
			 diPulseCountTrapID equal 64 and
			diPulseCount exceeds diPulseCountLimit."
	::= 10304

    diPulseCountTrap65	TRAP-TYPE
	ENTERPRISE	network-device
	VARIABLES	{ diPulseCount, adminDateAndTime, adminNDTrapSeqNo,
			  diIndex, diType }
	DESCRIPTION	"This trap is generated when set
			 diPulseCountTrapID equal 65 and
			diPulseCount exceeds diPulseCountLimit."
	::= 10305

    diPulseCountTrap66	TRAP-TYPE
	ENTERPRISE	network-device
	VARIABLES	{ diPulseCount, adminDateAndTime, adminNDTrapSeqNo,
			  diIndex, diType }
	DESCRIPTION	"This trap is generated when set
			 diPulseCountTrapID equal 66 and
			diPulseCount exceeds diPulseCountLimit."
	::= 10306

    diPulseCountTrap67	TRAP-TYPE
	ENTERPRISE	network-device
	VARIABLES	{ diPulseCount, adminDateAndTime, adminNDTrapSeqNo,
			  diIndex, diType }
	DESCRIPTION	"This trap is generated when set
			 diPulseCountTrapID equal 67 and
			diPulseCount exceeds diPulseCountLimit."
	::= 10307

    diPulseCountTrap68	TRAP-TYPE
	ENTERPRISE	network-device
	VARIABLES	{ diPulseCount, adminDateAndTime, adminNDTrapSeqNo,
			  diIndex, diType }
	DESCRIPTION	"This trap is generated when set
			 diPulseCountTrapID equal 68 and
			diPulseCount exceeds diPulseCountLimit."
	::= 10308

    diPulseCountTrap69	TRAP-TYPE
	ENTERPRISE	network-device
	VARIABLES	{ diPulseCount, adminDateAndTime, adminNDTrapSeqNo,
			  diIndex, diType }
	DESCRIPTION	"This trap is generated when set
			 diPulseCountTrapID equal 69 and
			diPulseCount exceeds diPulseCountLimit."
	::= 10309

    diPulseCountTrap70	TRAP-TYPE
	ENTERPRISE	network-device
	VARIABLES	{ diPulseCount, adminDateAndTime, adminNDTrapSeqNo,
			  diIndex, diType }
	DESCRIPTION	"This trap is generated when set
			 diPulseCountTrapID equal 70 and
			diPulseCount exceeds diPulseCountLimit."
	::= 10310

    diPulseCountTrap71	TRAP-TYPE
	ENTERPRISE	network-device
	VARIABLES	{ diPulseCount, adminDateAndTime, adminNDTrapSeqNo,
			  diIndex, diType }
	DESCRIPTION	"This trap is generated when set
			 diPulseCountTrapID equal 71 and
			diPulseCount exceeds diPulseCountLimit."
	::= 10311

    diPulseCountTrap72	TRAP-TYPE
	ENTERPRISE	network-device
	VARIABLES	{ diPulseCount, adminDateAndTime, adminNDTrapSeqNo,
			  diIndex, diType }
	DESCRIPTION	"This trap is generated when set
			 diPulseCountTrapID equal 72 and
			diPulseCount exceeds diPulseCountLimit."
	::= 10312

    diPulseCountTrap73	TRAP-TYPE
	ENTERPRISE	network-device
	VARIABLES	{ diPulseCount, adminDateAndTime, adminNDTrapSeqNo,
			  diIndex, diType }
	DESCRIPTION	"This trap is generated when set
			 diPulseCountTrapID equal 73 and
			diPulseCount exceeds diPulseCountLimit."
	::= 10313

    diPulseCountTrap74	TRAP-TYPE
	ENTERPRISE	network-device
	VARIABLES	{ diPulseCount, adminDateAndTime, adminNDTrapSeqNo,
			  diIndex, diType }
	DESCRIPTION	"This trap is generated when set
			 diPulseCountTrapID equal 74 and
			diPulseCount exceeds diPulseCountLimit."
	::= 10314

    diPulseCountTrap75	TRAP-TYPE
	ENTERPRISE	network-device
	VARIABLES	{ diPulseCount, adminDateAndTime, adminNDTrapSeqNo,
			  diIndex, diType }
	DESCRIPTION	"This trap is generated when set
			 diPulseCountTrapID equal 75 and
			diPulseCount exceeds diPulseCountLimit."
	::= 10315

    diPulseCountTrap76	TRAP-TYPE
	ENTERPRISE	network-device
	VARIABLES	{ diPulseCount, adminDateAndTime, adminNDTrapSeqNo,
			  diIndex, diType }
	DESCRIPTION	"This trap is generated when set
			 diPulseCountTrapID equal 76 and
			diPulseCount exceeds diPulseCountLimit."
	::= 10316

    diPulseCountTrap77	TRAP-TYPE
	ENTERPRISE	network-device
	VARIABLES	{ diPulseCount, adminDateAndTime, adminNDTrapSeqNo,
			  diIndex, diType }
	DESCRIPTION	"This trap is generated when set
			 diPulseCountTrapID equal 77 and
			diPulseCount exceeds diPulseCountLimit."
	::= 10317

    diPulseCountTrap78	TRAP-TYPE
	ENTERPRISE	network-device
	VARIABLES	{ diPulseCount, adminDateAndTime, adminNDTrapSeqNo,
			  diIndex, diType }
	DESCRIPTION	"This trap is generated when set
			 diPulseCountTrapID equal 78 and
			diPulseCount exceeds diPulseCountLimit."
	::= 10318

    diPulseCountTrap79	TRAP-TYPE
	ENTERPRISE	network-device
	VARIABLES	{ diPulseCount, adminDateAndTime, adminNDTrapSeqNo,
			  diIndex, diType }
	DESCRIPTION	"This trap is generated when set
			 diPulseCountTrapID equal 79 and
			diPulseCount exceeds diPulseCountLimit."
	::= 10319

    diPulseCountTrap80	TRAP-TYPE
	ENTERPRISE	network-device
	VARIABLES	{ diPulseCount, adminDateAndTime, adminNDTrapSeqNo,
			  diIndex, diType }
	DESCRIPTION	"This trap is generated when set
			 diPulseCountTrapID equal 80 and
			diPulseCount exceeds diPulseCountLimit."
	::= 10320

    diPulseCountTrap81	TRAP-TYPE
	ENTERPRISE	network-device
	VARIABLES	{ diPulseCount, adminDateAndTime, adminNDTrapSeqNo,
			  diIndex, diType }
	DESCRIPTION	"This trap is generated when set
			 diPulseCountTrapID equal 81 and
			diPulseCount exceeds diPulseCountLimit."
	::= 10321

    diPulseCountTrap82	TRAP-TYPE
	ENTERPRISE	network-device
	VARIABLES	{ diPulseCount, adminDateAndTime, adminNDTrapSeqNo,
			  diIndex, diType }
	DESCRIPTION	"This trap is generated when set
			 diPulseCountTrapID equal 82 and
			diPulseCount exceeds diPulseCountLimit."
	::= 10322

    diPulseCountTrap83	TRAP-TYPE
	ENTERPRISE	network-device
	VARIABLES	{ diPulseCount, adminDateAndTime, adminNDTrapSeqNo,
			  diIndex, diType }
	DESCRIPTION	"This trap is generated when set
			 diPulseCountTrapID equal 83 and
			diPulseCount exceeds diPulseCountLimit."
	::= 10323

    diPulseCountTrap84	TRAP-TYPE
	ENTERPRISE	network-device
	VARIABLES	{ diPulseCount, adminDateAndTime, adminNDTrapSeqNo,
			  diIndex, diType }
	DESCRIPTION	"This trap is generated when set
			 diPulseCountTrapID equal 84 and
			diPulseCount exceeds diPulseCountLimit."
	::= 10324

    diPulseCountTrap85	TRAP-TYPE
	ENTERPRISE	network-device
	VARIABLES	{ diPulseCount, adminDateAndTime, adminNDTrapSeqNo,
			  diIndex, diType }
	DESCRIPTION	"This trap is generated when set
			 diPulseCountTrapID equal 85 and
			diPulseCount exceeds diPulseCountLimit."
	::= 10325

    diPulseCountTrap86	TRAP-TYPE
	ENTERPRISE	network-device
	VARIABLES	{ diPulseCount, adminDateAndTime, adminNDTrapSeqNo,
			  diIndex, diType }
	DESCRIPTION	"This trap is generated when set
			 diPulseCountTrapID equal 86 and
			diPulseCount exceeds diPulseCountLimit."
	::= 10326

    diPulseCountTrap87	TRAP-TYPE
	ENTERPRISE	network-device
	VARIABLES	{ diPulseCount, adminDateAndTime, adminNDTrapSeqNo,
			  diIndex, diType }
	DESCRIPTION	"This trap is generated when set
			 diPulseCountTrapID equal 87 and
			diPulseCount exceeds diPulseCountLimit."
	::= 10327

    diPulseCountTrap88	TRAP-TYPE
	ENTERPRISE	network-device
	VARIABLES	{ diPulseCount, adminDateAndTime, adminNDTrapSeqNo,
			  diIndex, diType }
	DESCRIPTION	"This trap is generated when set
			 diPulseCountTrapID equal 88 and
			diPulseCount exceeds diPulseCountLimit."
	::= 10328

    diPulseCountTrap89	TRAP-TYPE
	ENTERPRISE	network-device
	VARIABLES	{ diPulseCount, adminDateAndTime, adminNDTrapSeqNo,
			  diIndex, diType }
	DESCRIPTION	"This trap is generated when set
			 diPulseCountTrapID equal 89 and
			diPulseCount exceeds diPulseCountLimit."
	::= 10329

    diPulseCountTrap90	TRAP-TYPE
	ENTERPRISE	network-device
	VARIABLES	{ diPulseCount, adminDateAndTime, adminNDTrapSeqNo,
			  diIndex, diType }
	DESCRIPTION	"This trap is generated when set
			 diPulseCountTrapID equal 90 and
			diPulseCount exceeds diPulseCountLimit."
	::= 10330

    diPulseCountTrap91	TRAP-TYPE
	ENTERPRISE	network-device
	VARIABLES	{ diPulseCount, adminDateAndTime, adminNDTrapSeqNo,
			  diIndex, diType }
	DESCRIPTION	"This trap is generated when set
			 diPulseCountTrapID equal 91 and
			diPulseCount exceeds diPulseCountLimit."
	::= 10331

    diPulseCountTrap92	TRAP-TYPE
	ENTERPRISE	network-device
	VARIABLES	{ diPulseCount, adminDateAndTime, adminNDTrapSeqNo,
			  diIndex, diType }
	DESCRIPTION	"This trap is generated when set
			 diPulseCountTrapID equal 92 and
			diPulseCount exceeds diPulseCountLimit."
	::= 10332

    diPulseCountTrap93	TRAP-TYPE
	ENTERPRISE	network-device
	VARIABLES	{ diPulseCount, adminDateAndTime, adminNDTrapSeqNo,
			  diIndex, diType }
	DESCRIPTION	"This trap is generated when set
			 diPulseCountTrapID equal 93 and
			diPulseCount exceeds diPulseCountLimit."
	::= 10333

    diPulseCountTrap94	TRAP-TYPE
	ENTERPRISE	network-device
	VARIABLES	{ diPulseCount, adminDateAndTime, adminNDTrapSeqNo,
			  diIndex, diType }
	DESCRIPTION	"This trap is generated when set
			 diPulseCountTrapID equal 94 and
			diPulseCount exceeds diPulseCountLimit."
	::= 10334

    diPulseCountTrap95	TRAP-TYPE
	ENTERPRISE	network-device
	VARIABLES	{ diPulseCount, adminDateAndTime, adminNDTrapSeqNo,
			  diIndex, diType }
	DESCRIPTION	"This trap is generated when set
			 diPulseCountTrapID equal 95 and
			diPulseCount exceeds diPulseCountLimit."
	::= 10335

    diPulseCountTrap96	TRAP-TYPE
	ENTERPRISE	network-device
	VARIABLES	{ diPulseCount, adminDateAndTime, adminNDTrapSeqNo,
			  diIndex, diType }
	DESCRIPTION	"This trap is generated when set
			 diPulseCountTrapID equal 96 and
			diPulseCount exceeds diPulseCountLimit."
	::= 10336

    diPulseCountTrap97	TRAP-TYPE
	ENTERPRISE	network-device
	VARIABLES	{ diPulseCount, adminDateAndTime, adminNDTrapSeqNo,
			  diIndex, diType }
	DESCRIPTION	"This trap is generated when set
			 diPulseCountTrapID equal 97 and
			diPulseCount exceeds diPulseCountLimit."
	::= 10337

    diPulseCountTrap98	TRAP-TYPE
	ENTERPRISE	network-device
	VARIABLES	{ diPulseCount, adminDateAndTime, adminNDTrapSeqNo,
			  diIndex, diType }
	DESCRIPTION	"This trap is generated when set
			 diPulseCountTrapID equal 98 and
			diPulseCount exceeds diPulseCountLimit."
	::= 10338

    diPulseCountTrap99	TRAP-TYPE
	ENTERPRISE	network-device
	VARIABLES	{ diPulseCount, adminDateAndTime, adminNDTrapSeqNo,
			  diIndex, diType }
	DESCRIPTION	"This trap is generated when set
			 diPulseCountTrapID equal 99 and
			diPulseCount exceeds diPulseCountLimit."
	::= 10339

    diPulseCountTrap100	TRAP-TYPE
	ENTERPRISE	network-device
	VARIABLES	{ diPulseCount, adminDateAndTime, adminNDTrapSeqNo,
			  diIndex, diType }
	DESCRIPTION	"This trap is generated when set
			 diPulseCountTrapID equal 100 and
			diPulseCount exceeds diPulseCountLimit."
	::= 10340

    diPulseCountTrap101	TRAP-TYPE
	ENTERPRISE	network-device
	VARIABLES	{ diPulseCount, adminDateAndTime, adminNDTrapSeqNo,
			  diIndex, diType }
	DESCRIPTION	"This trap is generated when set
			 diPulseCountTrapID equal 101 and
			diPulseCount exceeds diPulseCountLimit."
	::= 10341

    diPulseCountTrap102	TRAP-TYPE
	ENTERPRISE	network-device
	VARIABLES	{ diPulseCount, adminDateAndTime, adminNDTrapSeqNo,
			  diIndex, diType }
	DESCRIPTION	"This trap is generated when set
			 diPulseCountTrapID equal 102 and
			diPulseCount exceeds diPulseCountLimit."
	::= 10342

    diPulseCountTrap103	TRAP-TYPE
	ENTERPRISE	network-device
	VARIABLES	{ diPulseCount, adminDateAndTime, adminNDTrapSeqNo,
			  diIndex, diType }
	DESCRIPTION	"This trap is generated when set
			 diPulseCountTrapID equal 103 and
			diPulseCount exceeds diPulseCountLimit."
	::= 10343

    diPulseCountTrap104	TRAP-TYPE
	ENTERPRISE	network-device
	VARIABLES	{ diPulseCount, adminDateAndTime, adminNDTrapSeqNo,
			  diIndex, diType }
	DESCRIPTION	"This trap is generated when set
			 diPulseCountTrapID equal 104 and
			diPulseCount exceeds diPulseCountLimit."
	::= 10344

    diPulseCountTrap105	TRAP-TYPE
	ENTERPRISE	network-device
	VARIABLES	{ diPulseCount, adminDateAndTime, adminNDTrapSeqNo,
			  diIndex, diType }
	DESCRIPTION	"This trap is generated when set
			 diPulseCountTrapID equal 105 and
			diPulseCount exceeds diPulseCountLimit."
	::= 10345

    diPulseCountTrap106	TRAP-TYPE
	ENTERPRISE	network-device
	VARIABLES	{ diPulseCount, adminDateAndTime, adminNDTrapSeqNo,
			  diIndex, diType }
	DESCRIPTION	"This trap is generated when set
			 diPulseCountTrapID equal 106 and
			diPulseCount exceeds diPulseCountLimit."
	::= 10346

    diPulseCountTrap107	TRAP-TYPE
	ENTERPRISE	network-device
	VARIABLES	{ diPulseCount, adminDateAndTime, adminNDTrapSeqNo,
			  diIndex, diType }
	DESCRIPTION	"This trap is generated when set
			 diPulseCountTrapID equal 107 and
			diPulseCount exceeds diPulseCountLimit."
	::= 10347

    diPulseCountTrap108	TRAP-TYPE
	ENTERPRISE	network-device
	VARIABLES	{ diPulseCount, adminDateAndTime, adminNDTrapSeqNo,
			  diIndex, diType }
	DESCRIPTION	"This trap is generated when set
			 diPulseCountTrapID equal 108 and
			diPulseCount exceeds diPulseCountLimit."
	::= 10348

    diPulseCountTrap109	TRAP-TYPE
	ENTERPRISE	network-device
	VARIABLES	{ diPulseCount, adminDateAndTime, adminNDTrapSeqNo,
			  diIndex, diType }
	DESCRIPTION	"This trap is generated when set
			 diPulseCountTrapID equal 109 and
			diPulseCount exceeds diPulseCountLimit."
	::= 10349

    diPulseCountTrap110	TRAP-TYPE
	ENTERPRISE	network-device
	VARIABLES	{ diPulseCount, adminDateAndTime, adminNDTrapSeqNo,
			  diIndex, diType }
	DESCRIPTION	"This trap is generated when set
			 diPulseCountTrapID equal 110 and
			diPulseCount exceeds diPulseCountLimit."
	::= 10350

    diPulseCountTrap111	TRAP-TYPE
	ENTERPRISE	network-device
	VARIABLES	{ diPulseCount, adminDateAndTime, adminNDTrapSeqNo,
			  diIndex, diType }
	DESCRIPTION	"This trap is generated when set
			 diPulseCountTrapID equal 111 and
			diPulseCount exceeds diPulseCountLimit."
	::= 10351

    diPulseCountTrap112	TRAP-TYPE
	ENTERPRISE	network-device
	VARIABLES	{ diPulseCount, adminDateAndTime, adminNDTrapSeqNo,
			  diIndex, diType }
	DESCRIPTION	"This trap is generated when set
			 diPulseCountTrapID equal 112 and
			diPulseCount exceeds diPulseCountLimit."
	::= 10352

    diPulseCountTrap113	TRAP-TYPE
	ENTERPRISE	network-device
	VARIABLES	{ diPulseCount, adminDateAndTime, adminNDTrapSeqNo,
			  diIndex, diType }
	DESCRIPTION	"This trap is generated when set
			 diPulseCountTrapID equal 113 and
			diPulseCount exceeds diPulseCountLimit."
	::= 10353

    diPulseCountTrap114	TRAP-TYPE
	ENTERPRISE	network-device
	VARIABLES	{ diPulseCount, adminDateAndTime, adminNDTrapSeqNo,
			  diIndex, diType }
	DESCRIPTION	"This trap is generated when set
			 diPulseCountTrapID equal 114 and
			diPulseCount exceeds diPulseCountLimit."
	::= 10354

    diPulseCountTrap115	TRAP-TYPE
	ENTERPRISE	network-device
	VARIABLES	{ diPulseCount, adminDateAndTime, adminNDTrapSeqNo,
			  diIndex, diType }
	DESCRIPTION	"This trap is generated when set
			 diPulseCountTrapID equal 115 and
			diPulseCount exceeds diPulseCountLimit."
	::= 10355

    diPulseCountTrap116	TRAP-TYPE
	ENTERPRISE	network-device
	VARIABLES	{ diPulseCount, adminDateAndTime, adminNDTrapSeqNo,
			  diIndex, diType }
	DESCRIPTION	"This trap is generated when set
			 diPulseCountTrapID equal 116 and
			diPulseCount exceeds diPulseCountLimit."
	::= 10356

    diPulseCountTrap117	TRAP-TYPE
	ENTERPRISE	network-device
	VARIABLES	{ diPulseCount, adminDateAndTime, adminNDTrapSeqNo,
			  diIndex, diType }
	DESCRIPTION	"This trap is generated when set
			 diPulseCountTrapID equal 117 and
			diPulseCount exceeds diPulseCountLimit."
	::= 10357

    diPulseCountTrap118	TRAP-TYPE
	ENTERPRISE	network-device
	VARIABLES	{ diPulseCount, adminDateAndTime, adminNDTrapSeqNo,
			  diIndex, diType }
	DESCRIPTION	"This trap is generated when set
			 diPulseCountTrapID equal 118 and
			diPulseCount exceeds diPulseCountLimit."
	::= 10358

    diPulseCountTrap119	TRAP-TYPE
	ENTERPRISE	network-device
	VARIABLES	{ diPulseCount, adminDateAndTime, adminNDTrapSeqNo,
			  diIndex, diType }
	DESCRIPTION	"This trap is generated when set
			 diPulseCountTrapID equal 119 and
			diPulseCount exceeds diPulseCountLimit."
	::= 10359

    diPulseCountTrap120	TRAP-TYPE
	ENTERPRISE	network-device
	VARIABLES	{ diPulseCount, adminDateAndTime, adminNDTrapSeqNo,
			  diIndex, diType }
	DESCRIPTION	"This trap is generated when set
			 diPulseCountTrapID equal 120 and
			diPulseCount exceeds diPulseCountLimit."
	::= 10360

    diPulseCountTrap121	TRAP-TYPE
	ENTERPRISE	network-device
	VARIABLES	{ diPulseCount, adminDateAndTime, adminNDTrapSeqNo,
			  diIndex, diType }
	DESCRIPTION	"This trap is generated when set
			 diPulseCountTrapID equal 121 and
			diPulseCount exceeds diPulseCountLimit."
	::= 10361

    diPulseCountTrap122	TRAP-TYPE
	ENTERPRISE	network-device
	VARIABLES	{ diPulseCount, adminDateAndTime, adminNDTrapSeqNo,
			  diIndex, diType }
	DESCRIPTION	"This trap is generated when set
			 diPulseCountTrapID equal 122 and
			diPulseCount exceeds diPulseCountLimit."
	::= 10362

    diPulseCountTrap123	TRAP-TYPE
	ENTERPRISE	network-device
	VARIABLES	{ diPulseCount, adminDateAndTime, adminNDTrapSeqNo,
			  diIndex, diType }
	DESCRIPTION	"This trap is generated when set
			 diPulseCountTrapID equal 123 and
			diPulseCount exceeds diPulseCountLimit."
	::= 10363

    diPulseCountTrap124	TRAP-TYPE
	ENTERPRISE	network-device
	VARIABLES	{ diPulseCount, adminDateAndTime, adminNDTrapSeqNo,
			  diIndex, diType }
	DESCRIPTION	"This trap is generated when set
			 diPulseCountTrapID equal 124 and
			diPulseCount exceeds diPulseCountLimit."
	::= 10364

    diPulseCountTrap125	TRAP-TYPE
	ENTERPRISE	network-device
	VARIABLES	{ diPulseCount, adminDateAndTime, adminNDTrapSeqNo,
			  diIndex, diType }
	DESCRIPTION	"This trap is generated when set
			 diPulseCountTrapID equal 125 and
			diPulseCount exceeds diPulseCountLimit."
	::= 10365

    diPulseCountTrap126	TRAP-TYPE
	ENTERPRISE	network-device
	VARIABLES	{ diPulseCount, adminDateAndTime, adminNDTrapSeqNo,
			  diIndex, diType }
	DESCRIPTION	"This trap is generated when set
			 diPulseCountTrapID equal 126 and
			diPulseCount exceeds diPulseCountLimit."
	::= 10366

    diPulseCountTrap127	TRAP-TYPE
	ENTERPRISE	network-device
	VARIABLES	{ diPulseCount, adminDateAndTime, adminNDTrapSeqNo,
			  diIndex, diType }
	DESCRIPTION	"This trap is generated when set
			 diPulseCountTrapID equal 127 and
			diPulseCount exceeds diPulseCountLimit."
	::= 10367

    vcExceedUpperThresholdIncrease1 TRAP-TYPE
	ENTERPRISE	network-device
	VARIABLES	{ vcValue, adminDateAndTime, adminNDTrapSeqNo,
			  vcIndex, vcType }
	DESCRIPTION	"This trap is generated when set
			vcExUpThresholdIncreaseTrapID equal 1 and 
			vcValue is greater than the upper threshold."
	::= 14337

    vcExceedUpperThresholdIncrease2 TRAP-TYPE
	ENTERPRISE	network-device
	VARIABLES	{ vcValue, adminDateAndTime, adminNDTrapSeqNo,
			  vcIndex, vcType }
	DESCRIPTION	"This trap is generated when set
			vcExUpThresholdIncreaseTrapID equal 2 and 
			vcValue is greater than the upper threshold."
	::= 14338

    vcExceedUpperThresholdIncrease3 TRAP-TYPE
	ENTERPRISE	network-device
	VARIABLES	{ vcValue, adminDateAndTime, adminNDTrapSeqNo,
			  vcIndex, vcType }
	DESCRIPTION	"This trap is generated when set
			vcExUpThresholdIncreaseTrapID equal 3 and 
			vcValue is greater than the upper threshold."
	::= 14339

    vcExceedUpperThresholdIncrease4 TRAP-TYPE
	ENTERPRISE	network-device
	VARIABLES	{ vcValue, adminDateAndTime, adminNDTrapSeqNo,
			  vcIndex, vcType }
	DESCRIPTION	"This trap is generated when set
			vcExUpThresholdIncreaseTrapID equal 4 and 
			vcValue is greater than the upper threshold."
	::= 14340

    vcExceedUpperThresholdIncrease5 TRAP-TYPE
	ENTERPRISE	network-device
	VARIABLES	{ vcValue, adminDateAndTime, adminNDTrapSeqNo,
			  vcIndex, vcType }
	DESCRIPTION	"This trap is generated when set
			vcExUpThresholdIncreaseTrapID equal 5 and 
			vcValue is greater than the upper threshold."
	::= 14341

    vcExceedUpperThresholdIncrease6 TRAP-TYPE
	ENTERPRISE	network-device
	VARIABLES	{ vcValue, adminDateAndTime, adminNDTrapSeqNo,
			  vcIndex, vcType }
	DESCRIPTION	"This trap is generated when set
			vcExUpThresholdIncreaseTrapID equal 6 and 
			vcValue is greater than the upper threshold."
	::= 14342

    vcExceedUpperThresholdIncrease7 TRAP-TYPE
	ENTERPRISE	network-device
	VARIABLES	{ vcValue, adminDateAndTime, adminNDTrapSeqNo,
			  vcIndex, vcType }
	DESCRIPTION	"This trap is generated when set
			vcExUpThresholdIncreaseTrapID equal 7 and 
			vcValue is greater than the upper threshold."
	::= 14343

    vcExceedUpperThresholdIncrease8 TRAP-TYPE
	ENTERPRISE	network-device
	VARIABLES	{ vcValue, adminDateAndTime, adminNDTrapSeqNo,
			  vcIndex, vcType }
	DESCRIPTION	"This trap is generated when set
			vcExUpThresholdIncreaseTrapID equal 8 and 
			vcValue is greater than the upper threshold."
	::= 14344

    vcExceedUpperThresholdIncrease9 TRAP-TYPE
	ENTERPRISE	network-device
	VARIABLES	{ vcValue, adminDateAndTime, adminNDTrapSeqNo,
			  vcIndex, vcType }
	DESCRIPTION	"This trap is generated when set
			vcExUpThresholdIncreaseTrapID equal 9 and 
			vcValue is greater than the upper threshold."
	::= 14345

    vcExceedUpperThresholdIncrease10 TRAP-TYPE
	ENTERPRISE	network-device
	VARIABLES	{ vcValue, adminDateAndTime, adminNDTrapSeqNo,
			  vcIndex, vcType }
	DESCRIPTION	"This trap is generated when set
			vcExUpThresholdIncreaseTrapID equal 10 and 
			vcValue is greater than the upper threshold."
	::= 14346

    vcExceedUpperThresholdIncrease11 TRAP-TYPE
	ENTERPRISE	network-device
	VARIABLES	{ vcValue, adminDateAndTime, adminNDTrapSeqNo,
			  vcIndex, vcType }
	DESCRIPTION	"This trap is generated when set
			vcExUpThresholdIncreaseTrapID equal 11 and 
			vcValue is greater than the upper threshold."
	::= 14347

    vcExceedUpperThresholdIncrease12 TRAP-TYPE
	ENTERPRISE	network-device
	VARIABLES	{ vcValue, adminDateAndTime, adminNDTrapSeqNo,
			  vcIndex, vcType }
	DESCRIPTION	"This trap is generated when set
			vcExUpThresholdIncreaseTrapID equal 12 and 
			vcValue is greater than the upper threshold."
	::= 14348

    vcExceedUpperThresholdIncrease13 TRAP-TYPE
	ENTERPRISE	network-device
	VARIABLES	{ vcValue, adminDateAndTime, adminNDTrapSeqNo,
			  vcIndex, vcType }
	DESCRIPTION	"This trap is generated when set
			vcExUpThresholdIncreaseTrapID equal 13 and 
			vcValue is greater than the upper threshold."
	::= 14349

    vcExceedUpperThresholdIncrease14 TRAP-TYPE
	ENTERPRISE	network-device
	VARIABLES	{ vcValue, adminDateAndTime, adminNDTrapSeqNo,
			  vcIndex, vcType }
	DESCRIPTION	"This trap is generated when set
			vcExUpThresholdIncreaseTrapID equal 14 and 
			vcValue is greater than the upper threshold."
	::= 14350

    vcExceedUpperThresholdIncrease15 TRAP-TYPE
	ENTERPRISE	network-device
	VARIABLES	{ vcValue, adminDateAndTime, adminNDTrapSeqNo,
			  vcIndex, vcType }
	DESCRIPTION	"This trap is generated when set
			vcExUpThresholdIncreaseTrapID equal 15 and 
			vcValue is greater than the upper threshold."
	::= 14351

    vcExceedUpperThresholdIncrease16 TRAP-TYPE
	ENTERPRISE	network-device
	VARIABLES	{ vcValue, adminDateAndTime, adminNDTrapSeqNo,
			  vcIndex, vcType }
	DESCRIPTION	"This trap is generated when set
			vcExUpThresholdIncreaseTrapID equal 16 and 
			vcValue is greater than the upper threshold."
	::= 14352

    vcExceedUpperThresholdIncrease17 TRAP-TYPE
	ENTERPRISE	network-device
	VARIABLES	{ vcValue, adminDateAndTime, adminNDTrapSeqNo,
			  vcIndex, vcType }
	DESCRIPTION	"This trap is generated when set
			vcExUpThresholdIncreaseTrapID equal 17 and 
			vcValue is greater than the upper threshold."
	::= 14353

    vcExceedUpperThresholdIncrease18 TRAP-TYPE
	ENTERPRISE	network-device
	VARIABLES	{ vcValue, adminDateAndTime, adminNDTrapSeqNo,
			  vcIndex, vcType }
	DESCRIPTION	"This trap is generated when set
			vcExUpThresholdIncreaseTrapID equal 18 and 
			vcValue is greater than the upper threshold."
	::= 14354

    vcExceedUpperThresholdIncrease19 TRAP-TYPE
	ENTERPRISE	network-device
	VARIABLES	{ vcValue, adminDateAndTime, adminNDTrapSeqNo,
			  vcIndex, vcType }
	DESCRIPTION	"This trap is generated when set
			vcExUpThresholdIncreaseTrapID equal 19 and 
			vcValue is greater than the upper threshold."
	::= 14355

    vcExceedUpperThresholdIncrease20 TRAP-TYPE
	ENTERPRISE	network-device
	VARIABLES	{ vcValue, adminDateAndTime, adminNDTrapSeqNo,
			  vcIndex, vcType }
	DESCRIPTION	"This trap is generated when set
			vcExUpThresholdIncreaseTrapID equal 20 and 
			vcValue is greater than the upper threshold."
	::= 14356

    vcExceedUpperThresholdIncrease21 TRAP-TYPE
	ENTERPRISE	network-device
	VARIABLES	{ vcValue, adminDateAndTime, adminNDTrapSeqNo,
			  vcIndex, vcType }
	DESCRIPTION	"This trap is generated when set
			vcExUpThresholdIncreaseTrapID equal 21 and 
			vcValue is greater than the upper threshold."
	::= 14357

    vcExceedUpperThresholdIncrease22 TRAP-TYPE
	ENTERPRISE	network-device
	VARIABLES	{ vcValue, adminDateAndTime, adminNDTrapSeqNo,
			  vcIndex, vcType }
	DESCRIPTION	"This trap is generated when set
			vcExUpThresholdIncreaseTrapID equal 22 and 
			vcValue is greater than the upper threshold."
	::= 14358

    vcExceedUpperThresholdIncrease23 TRAP-TYPE
	ENTERPRISE	network-device
	VARIABLES	{ vcValue, adminDateAndTime, adminNDTrapSeqNo,
			  vcIndex, vcType }
	DESCRIPTION	"This trap is generated when set
			vcExUpThresholdIncreaseTrapID equal 23 and 
			vcValue is greater than the upper threshold."
	::= 14359

    vcExceedUpperThresholdIncrease24 TRAP-TYPE
	ENTERPRISE	network-device
	VARIABLES	{ vcValue, adminDateAndTime, adminNDTrapSeqNo,
			  vcIndex, vcType }
	DESCRIPTION	"This trap is generated when set
			vcExUpThresholdIncreaseTrapID equal 24 and 
			vcValue is greater than the upper threshold."
	::= 14360

    vcExceedUpperThresholdIncrease25 TRAP-TYPE
	ENTERPRISE	network-device
	VARIABLES	{ vcValue, adminDateAndTime, adminNDTrapSeqNo,
			  vcIndex, vcType }
	DESCRIPTION	"This trap is generated when set
			vcExUpThresholdIncreaseTrapID equal 25 and 
			vcValue is greater than the upper threshold."
	::= 14361

    vcExceedUpperThresholdIncrease26 TRAP-TYPE
	ENTERPRISE	network-device
	VARIABLES	{ vcValue, adminDateAndTime, adminNDTrapSeqNo,
			  vcIndex, vcType }
	DESCRIPTION	"This trap is generated when set
			vcExUpThresholdIncreaseTrapID equal 26 and 
			vcValue is greater than the upper threshold."
	::= 14362

    vcExceedUpperThresholdIncrease27 TRAP-TYPE
	ENTERPRISE	network-device
	VARIABLES	{ vcValue, adminDateAndTime, adminNDTrapSeqNo,
			  vcIndex, vcType }
	DESCRIPTION	"This trap is generated when set
			vcExUpThresholdIncreaseTrapID equal 27 and 
			vcValue is greater than the upper threshold."
	::= 14363

    vcExceedUpperThresholdIncrease28 TRAP-TYPE
	ENTERPRISE	network-device
	VARIABLES	{ vcValue, adminDateAndTime, adminNDTrapSeqNo,
			  vcIndex, vcType }
	DESCRIPTION	"This trap is generated when set
			vcExUpThresholdIncreaseTrapID equal 28 and 
			vcValue is greater than the upper threshold."
	::= 14364

    vcExceedUpperThresholdIncrease29 TRAP-TYPE
	ENTERPRISE	network-device
	VARIABLES	{ vcValue, adminDateAndTime, adminNDTrapSeqNo,
			  vcIndex, vcType }
	DESCRIPTION	"This trap is generated when set
			vcExUpThresholdIncreaseTrapID equal 29 and 
			vcValue is greater than the upper threshold."
	::= 14365

    vcExceedUpperThresholdIncrease30 TRAP-TYPE
	ENTERPRISE	network-device
	VARIABLES	{ vcValue, adminDateAndTime, adminNDTrapSeqNo,
			  vcIndex, vcType }
	DESCRIPTION	"This trap is generated when set
			vcExUpThresholdIncreaseTrapID equal 30 and 
			vcValue is greater than the upper threshold."
	::= 14366

    vcExceedUpperThresholdIncrease31 TRAP-TYPE
	ENTERPRISE	network-device
	VARIABLES	{ vcValue, adminDateAndTime, adminNDTrapSeqNo,
			  vcIndex, vcType }
	DESCRIPTION	"This trap is generated when set
			vcExUpThresholdIncreaseTrapID equal 31 and 
			vcValue is greater than the upper threshold."
	::= 14367

    vcExceedUpperThresholdIncrease32 TRAP-TYPE
	ENTERPRISE	network-device
	VARIABLES	{ vcValue, adminDateAndTime, adminNDTrapSeqNo,
			  vcIndex, vcType }
	DESCRIPTION	"This trap is generated when set
			vcExUpThresholdIncreaseTrapID equal 32 and 
			vcValue is greater than the upper threshold."
	::= 14368

    vcExceedUpperThresholdIncrease33 TRAP-TYPE
	ENTERPRISE	network-device
	VARIABLES	{ vcValue, adminDateAndTime, adminNDTrapSeqNo,
			  vcIndex, vcType }
	DESCRIPTION	"This trap is generated when set
			vcExUpThresholdIncreaseTrapID equal 33 and 
			vcValue is greater than the upper threshold."
	::= 14369

    vcExceedUpperThresholdIncrease34 TRAP-TYPE
	ENTERPRISE	network-device
	VARIABLES	{ vcValue, adminDateAndTime, adminNDTrapSeqNo,
			  vcIndex, vcType }
	DESCRIPTION	"This trap is generated when set
			vcExUpThresholdIncreaseTrapID equal 34 and 
			vcValue is greater than the upper threshold."
	::= 14370

    vcExceedUpperThresholdIncrease35 TRAP-TYPE
	ENTERPRISE	network-device
	VARIABLES	{ vcValue, adminDateAndTime, adminNDTrapSeqNo,
			  vcIndex, vcType }
	DESCRIPTION	"This trap is generated when set
			vcExUpThresholdIncreaseTrapID equal 35 and 
			vcValue is greater than the upper threshold."
	::= 14371

    vcExceedUpperThresholdIncrease36 TRAP-TYPE
	ENTERPRISE	network-device
	VARIABLES	{ vcValue, adminDateAndTime, adminNDTrapSeqNo,
			  vcIndex, vcType }
	DESCRIPTION	"This trap is generated when set
			vcExUpThresholdIncreaseTrapID equal 36 and 
			vcValue is greater than the upper threshold."
	::= 14372

    vcExceedUpperThresholdIncrease37 TRAP-TYPE
	ENTERPRISE	network-device
	VARIABLES	{ vcValue, adminDateAndTime, adminNDTrapSeqNo,
			  vcIndex, vcType }
	DESCRIPTION	"This trap is generated when set
			vcExUpThresholdIncreaseTrapID equal 37 and 
			vcValue is greater than the upper threshold."
	::= 14373

    vcExceedUpperThresholdIncrease38 TRAP-TYPE
	ENTERPRISE	network-device
	VARIABLES	{ vcValue, adminDateAndTime, adminNDTrapSeqNo,
			  vcIndex, vcType }
	DESCRIPTION	"This trap is generated when set
			vcExUpThresholdIncreaseTrapID equal 38 and 
			vcValue is greater than the upper threshold."
	::= 14374

    vcExceedUpperThresholdIncrease39 TRAP-TYPE
	ENTERPRISE	network-device
	VARIABLES	{ vcValue, adminDateAndTime, adminNDTrapSeqNo,
			  vcIndex, vcType }
	DESCRIPTION	"This trap is generated when set
			vcExUpThresholdIncreaseTrapID equal 39 and 
			vcValue is greater than the upper threshold."
	::= 14375

    vcExceedUpperThresholdIncrease40 TRAP-TYPE
	ENTERPRISE	network-device
	VARIABLES	{ vcValue, adminDateAndTime, adminNDTrapSeqNo,
			  vcIndex, vcType }
	DESCRIPTION	"This trap is generated when set
			vcExUpThresholdIncreaseTrapID equal 40 and 
			vcValue is greater than the upper threshold."
	::= 14376

    vcExceedUpperThresholdIncrease41 TRAP-TYPE
	ENTERPRISE	network-device
	VARIABLES	{ vcValue, adminDateAndTime, adminNDTrapSeqNo,
			  vcIndex, vcType }
	DESCRIPTION	"This trap is generated when set
			vcExUpThresholdIncreaseTrapID equal 41 and 
			vcValue is greater than the upper threshold."
	::= 14377

    vcExceedUpperThresholdIncrease42 TRAP-TYPE
	ENTERPRISE	network-device
	VARIABLES	{ vcValue, adminDateAndTime, adminNDTrapSeqNo,
			  vcIndex, vcType }
	DESCRIPTION	"This trap is generated when set
			vcExUpThresholdIncreaseTrapID equal 42 and 
			vcValue is greater than the upper threshold."
	::= 14378

    vcExceedUpperThresholdIncrease43 TRAP-TYPE
	ENTERPRISE	network-device
	VARIABLES	{ vcValue, adminDateAndTime, adminNDTrapSeqNo,
			  vcIndex, vcType }
	DESCRIPTION	"This trap is generated when set
			vcExUpThresholdIncreaseTrapID equal 43 and 
			vcValue is greater than the upper threshold."
	::= 14379

    vcExceedUpperThresholdIncrease44 TRAP-TYPE
	ENTERPRISE	network-device
	VARIABLES	{ vcValue, adminDateAndTime, adminNDTrapSeqNo,
			  vcIndex, vcType }
	DESCRIPTION	"This trap is generated when set
			vcExUpThresholdIncreaseTrapID equal 44 and 
			vcValue is greater than the upper threshold."
	::= 14380

    vcExceedUpperThresholdIncrease45 TRAP-TYPE
	ENTERPRISE	network-device
	VARIABLES	{ vcValue, adminDateAndTime, adminNDTrapSeqNo,
			  vcIndex, vcType }
	DESCRIPTION	"This trap is generated when set
			vcExUpThresholdIncreaseTrapID equal 45 and 
			vcValue is greater than the upper threshold."
	::= 14381

    vcExceedUpperThresholdIncrease46 TRAP-TYPE
	ENTERPRISE	network-device
	VARIABLES	{ vcValue, adminDateAndTime, adminNDTrapSeqNo,
			  vcIndex, vcType }
	DESCRIPTION	"This trap is generated when set
			vcExUpThresholdIncreaseTrapID equal 46 and 
			vcValue is greater than the upper threshold."
	::= 14382

    vcExceedUpperThresholdIncrease47 TRAP-TYPE
	ENTERPRISE	network-device
	VARIABLES	{ vcValue, adminDateAndTime, adminNDTrapSeqNo,
			  vcIndex, vcType }
	DESCRIPTION	"This trap is generated when set
			vcExUpThresholdIncreaseTrapID equal 47 and 
			vcValue is greater than the upper threshold."
	::= 14383

    vcExceedUpperThresholdIncrease48 TRAP-TYPE
	ENTERPRISE	network-device
	VARIABLES	{ vcValue, adminDateAndTime, adminNDTrapSeqNo,
			  vcIndex, vcType }
	DESCRIPTION	"This trap is generated when set
			vcExUpThresholdIncreaseTrapID equal 48 and 
			vcValue is greater than the upper threshold."
	::= 14384

    vcExceedUpperThresholdIncrease49 TRAP-TYPE
	ENTERPRISE	network-device
	VARIABLES	{ vcValue, adminDateAndTime, adminNDTrapSeqNo,
			  vcIndex, vcType }
	DESCRIPTION	"This trap is generated when set
			vcExUpThresholdIncreaseTrapID equal 49 and 
			vcValue is greater than the upper threshold."
	::= 14385

    vcExceedUpperThresholdIncrease50 TRAP-TYPE
	ENTERPRISE	network-device
	VARIABLES	{ vcValue, adminDateAndTime, adminNDTrapSeqNo,
			  vcIndex, vcType }
	DESCRIPTION	"This trap is generated when set
			vcExUpThresholdIncreaseTrapID equal 50 and 
			vcValue is greater than the upper threshold."
	::= 14386

    vcExceedUpperThresholdIncrease51 TRAP-TYPE
	ENTERPRISE	network-device
	VARIABLES	{ vcValue, adminDateAndTime, adminNDTrapSeqNo,
			  vcIndex, vcType }
	DESCRIPTION	"This trap is generated when set
			vcExUpThresholdIncreaseTrapID equal 51 and 
			vcValue is greater than the upper threshold."
	::= 14387

    vcExceedUpperThresholdIncrease52 TRAP-TYPE
	ENTERPRISE	network-device
	VARIABLES	{ vcValue, adminDateAndTime, adminNDTrapSeqNo,
			  vcIndex, vcType }
	DESCRIPTION	"This trap is generated when set
			vcExUpThresholdIncreaseTrapID equal 52 and 
			vcValue is greater than the upper threshold."
	::= 14388

    vcExceedUpperThresholdIncrease53 TRAP-TYPE
	ENTERPRISE	network-device
	VARIABLES	{ vcValue, adminDateAndTime, adminNDTrapSeqNo,
			  vcIndex, vcType }
	DESCRIPTION	"This trap is generated when set
			vcExUpThresholdIncreaseTrapID equal 53 and 
			vcValue is greater than the upper threshold."
	::= 14389

    vcExceedUpperThresholdIncrease54 TRAP-TYPE
	ENTERPRISE	network-device
	VARIABLES	{ vcValue, adminDateAndTime, adminNDTrapSeqNo,
			  vcIndex, vcType }
	DESCRIPTION	"This trap is generated when set
			vcExUpThresholdIncreaseTrapID equal 54 and 
			vcValue is greater than the upper threshold."
	::= 14390

    vcExceedUpperThresholdIncrease55 TRAP-TYPE
	ENTERPRISE	network-device
	VARIABLES	{ vcValue, adminDateAndTime, adminNDTrapSeqNo,
			  vcIndex, vcType }
	DESCRIPTION	"This trap is generated when set
			vcExUpThresholdIncreaseTrapID equal 55 and 
			vcValue is greater than the upper threshold."
	::= 14391

    vcExceedUpperThresholdIncrease56 TRAP-TYPE
	ENTERPRISE	network-device
	VARIABLES	{ vcValue, adminDateAndTime, adminNDTrapSeqNo,
			  vcIndex, vcType }
	DESCRIPTION	"This trap is generated when set
			vcExUpThresholdIncreaseTrapID equal 56 and 
			vcValue is greater than the upper threshold."
	::= 14392

    vcExceedUpperThresholdIncrease57 TRAP-TYPE
	ENTERPRISE	network-device
	VARIABLES	{ vcValue, adminDateAndTime, adminNDTrapSeqNo,
			  vcIndex, vcType }
	DESCRIPTION	"This trap is generated when set
			vcExUpThresholdIncreaseTrapID equal 57 and 
			vcValue is greater than the upper threshold."
	::= 14393

    vcExceedUpperThresholdIncrease58 TRAP-TYPE
	ENTERPRISE	network-device
	VARIABLES	{ vcValue, adminDateAndTime, adminNDTrapSeqNo,
			  vcIndex, vcType }
	DESCRIPTION	"This trap is generated when set
			vcExUpThresholdIncreaseTrapID equal 58 and 
			vcValue is greater than the upper threshold."
	::= 14394

    vcExceedUpperThresholdIncrease59 TRAP-TYPE
	ENTERPRISE	network-device
	VARIABLES	{ vcValue, adminDateAndTime, adminNDTrapSeqNo,
			  vcIndex, vcType }
	DESCRIPTION	"This trap is generated when set
			vcExUpThresholdIncreaseTrapID equal 59 and 
			vcValue is greater than the upper threshold."
	::= 14395

    vcExceedUpperThresholdIncrease60 TRAP-TYPE
	ENTERPRISE	network-device
	VARIABLES	{ vcValue, adminDateAndTime, adminNDTrapSeqNo,
			  vcIndex, vcType }
	DESCRIPTION	"This trap is generated when set
			vcExUpThresholdIncreaseTrapID equal 60 and 
			vcValue is greater than the upper threshold."
	::= 14396

    vcExceedUpperThresholdIncrease61 TRAP-TYPE
	ENTERPRISE	network-device
	VARIABLES	{ vcValue, adminDateAndTime, adminNDTrapSeqNo,
			  vcIndex, vcType }
	DESCRIPTION	"This trap is generated when set
			vcExUpThresholdIncreaseTrapID equal 61 and 
			vcValue is greater than the upper threshold."
	::= 14397

    vcExceedUpperThresholdIncrease62 TRAP-TYPE
	ENTERPRISE	network-device
	VARIABLES	{ vcValue, adminDateAndTime, adminNDTrapSeqNo,
			  vcIndex, vcType }
	DESCRIPTION	"This trap is generated when set
			vcExUpThresholdIncreaseTrapID equal 62 and 
			vcValue is greater than the upper threshold."
	::= 14398

    vcExceedUpperThresholdIncrease63 TRAP-TYPE
	ENTERPRISE	network-device
	VARIABLES	{ vcValue, adminDateAndTime, adminNDTrapSeqNo,
			  vcIndex, vcType }
	DESCRIPTION	"This trap is generated when set
			vcExUpThresholdIncreaseTrapID equal 63 and 
			vcValue is greater than the upper threshold."
	::= 14399

    vcExceedUpperThresholdIncrease64 TRAP-TYPE
	ENTERPRISE	network-device
	VARIABLES	{ vcValue, adminDateAndTime, adminNDTrapSeqNo,
			  vcIndex, vcType }
	DESCRIPTION	"This trap is generated when set
			vcExUpThresholdIncreaseTrapID equal 64 and 
			vcValue is greater than the upper threshold."
	::= 14400

    vcExceedUpperThresholdIncrease65 TRAP-TYPE
	ENTERPRISE	network-device
	VARIABLES	{ vcValue, adminDateAndTime, adminNDTrapSeqNo,
			  vcIndex, vcType }
	DESCRIPTION	"This trap is generated when set
			vcExUpThresholdIncreaseTrapID equal 65 and 
			vcValue is greater than the upper threshold."
	::= 14401

    vcExceedUpperThresholdIncrease66 TRAP-TYPE
	ENTERPRISE	network-device
	VARIABLES	{ vcValue, adminDateAndTime, adminNDTrapSeqNo,
			  vcIndex, vcType }
	DESCRIPTION	"This trap is generated when set
			vcExUpThresholdIncreaseTrapID equal 66 and 
			vcValue is greater than the upper threshold."
	::= 14402

    vcExceedUpperThresholdIncrease67 TRAP-TYPE
	ENTERPRISE	network-device
	VARIABLES	{ vcValue, adminDateAndTime, adminNDTrapSeqNo,
			  vcIndex, vcType }
	DESCRIPTION	"This trap is generated when set
			vcExUpThresholdIncreaseTrapID equal 67 and 
			vcValue is greater than the upper threshold."
	::= 14403

    vcExceedUpperThresholdIncrease68 TRAP-TYPE
	ENTERPRISE	network-device
	VARIABLES	{ vcValue, adminDateAndTime, adminNDTrapSeqNo,
			  vcIndex, vcType }
	DESCRIPTION	"This trap is generated when set
			vcExUpThresholdIncreaseTrapID equal 68 and 
			vcValue is greater than the upper threshold."
	::= 14404

    vcExceedUpperThresholdIncrease69 TRAP-TYPE
	ENTERPRISE	network-device
	VARIABLES	{ vcValue, adminDateAndTime, adminNDTrapSeqNo,
			  vcIndex, vcType }
	DESCRIPTION	"This trap is generated when set
			vcExUpThresholdIncreaseTrapID equal 69 and 
			vcValue is greater than the upper threshold."
	::= 14405

    vcExceedUpperThresholdIncrease70 TRAP-TYPE
	ENTERPRISE	network-device
	VARIABLES	{ vcValue, adminDateAndTime, adminNDTrapSeqNo,
			  vcIndex, vcType }
	DESCRIPTION	"This trap is generated when set
			vcExUpThresholdIncreaseTrapID equal 70 and 
			vcValue is greater than the upper threshold."
	::= 14406

    vcExceedUpperThresholdIncrease71 TRAP-TYPE
	ENTERPRISE	network-device
	VARIABLES	{ vcValue, adminDateAndTime, adminNDTrapSeqNo,
			  vcIndex, vcType }
	DESCRIPTION	"This trap is generated when set
			vcExUpThresholdIncreaseTrapID equal 71 and 
			vcValue is greater than the upper threshold."
	::= 14407

    vcExceedUpperThresholdIncrease72 TRAP-TYPE
	ENTERPRISE	network-device
	VARIABLES	{ vcValue, adminDateAndTime, adminNDTrapSeqNo,
			  vcIndex, vcType }
	DESCRIPTION	"This trap is generated when set
			vcExUpThresholdIncreaseTrapID equal 72 and 
			vcValue is greater than the upper threshold."
	::= 14408

    vcExceedUpperThresholdIncrease73 TRAP-TYPE
	ENTERPRISE	network-device
	VARIABLES	{ vcValue, adminDateAndTime, adminNDTrapSeqNo,
			  vcIndex, vcType }
	DESCRIPTION	"This trap is generated when set
			vcExUpThresholdIncreaseTrapID equal 73 and 
			vcValue is greater than the upper threshold."
	::= 14409

    vcExceedUpperThresholdIncrease74 TRAP-TYPE
	ENTERPRISE	network-device
	VARIABLES	{ vcValue, adminDateAndTime, adminNDTrapSeqNo,
			  vcIndex, vcType }
	DESCRIPTION	"This trap is generated when set
			vcExUpThresholdIncreaseTrapID equal 74 and 
			vcValue is greater than the upper threshold."
	::= 14410

    vcExceedUpperThresholdIncrease75 TRAP-TYPE
	ENTERPRISE	network-device
	VARIABLES	{ vcValue, adminDateAndTime, adminNDTrapSeqNo,
			  vcIndex, vcType }
	DESCRIPTION	"This trap is generated when set
			vcExUpThresholdIncreaseTrapID equal 75 and 
			vcValue is greater than the upper threshold."
	::= 14411

    vcExceedUpperThresholdIncrease76 TRAP-TYPE
	ENTERPRISE	network-device
	VARIABLES	{ vcValue, adminDateAndTime, adminNDTrapSeqNo,
			  vcIndex, vcType }
	DESCRIPTION	"This trap is generated when set
			vcExUpThresholdIncreaseTrapID equal 76 and 
			vcValue is greater than the upper threshold."
	::= 14412

    vcExceedUpperThresholdIncrease77 TRAP-TYPE
	ENTERPRISE	network-device
	VARIABLES	{ vcValue, adminDateAndTime, adminNDTrapSeqNo,
			  vcIndex, vcType }
	DESCRIPTION	"This trap is generated when set
			vcExUpThresholdIncreaseTrapID equal 77 and 
			vcValue is greater than the upper threshold."
	::= 14413

    vcExceedUpperThresholdIncrease78 TRAP-TYPE
	ENTERPRISE	network-device
	VARIABLES	{ vcValue, adminDateAndTime, adminNDTrapSeqNo,
			  vcIndex, vcType }
	DESCRIPTION	"This trap is generated when set
			vcExUpThresholdIncreaseTrapID equal 78 and 
			vcValue is greater than the upper threshold."
	::= 14414

    vcExceedUpperThresholdIncrease79 TRAP-TYPE
	ENTERPRISE	network-device
	VARIABLES	{ vcValue, adminDateAndTime, adminNDTrapSeqNo,
			  vcIndex, vcType }
	DESCRIPTION	"This trap is generated when set
			vcExUpThresholdIncreaseTrapID equal 79 and 
			vcValue is greater than the upper threshold."
	::= 14415

    vcExceedUpperThresholdIncrease80 TRAP-TYPE
	ENTERPRISE	network-device
	VARIABLES	{ vcValue, adminDateAndTime, adminNDTrapSeqNo,
			  vcIndex, vcType }
	DESCRIPTION	"This trap is generated when set
			vcExUpThresholdIncreaseTrapID equal 80 and 
			vcValue is greater than the upper threshold."
	::= 14416

    vcExceedUpperThresholdIncrease81 TRAP-TYPE
	ENTERPRISE	network-device
	VARIABLES	{ vcValue, adminDateAndTime, adminNDTrapSeqNo,
			  vcIndex, vcType }
	DESCRIPTION	"This trap is generated when set
			vcExUpThresholdIncreaseTrapID equal 81 and 
			vcValue is greater than the upper threshold."
	::= 14417

    vcExceedUpperThresholdIncrease82 TRAP-TYPE
	ENTERPRISE	network-device
	VARIABLES	{ vcValue, adminDateAndTime, adminNDTrapSeqNo,
			  vcIndex, vcType }
	DESCRIPTION	"This trap is generated when set
			vcExUpThresholdIncreaseTrapID equal 82 and 
			vcValue is greater than the upper threshold."
	::= 14418

    vcExceedUpperThresholdIncrease83 TRAP-TYPE
	ENTERPRISE	network-device
	VARIABLES	{ vcValue, adminDateAndTime, adminNDTrapSeqNo,
			  vcIndex, vcType }
	DESCRIPTION	"This trap is generated when set
			vcExUpThresholdIncreaseTrapID equal 83 and 
			vcValue is greater than the upper threshold."
	::= 14419

    vcExceedUpperThresholdIncrease84 TRAP-TYPE
	ENTERPRISE	network-device
	VARIABLES	{ vcValue, adminDateAndTime, adminNDTrapSeqNo,
			  vcIndex, vcType }
	DESCRIPTION	"This trap is generated when set
			vcExUpThresholdIncreaseTrapID equal 84 and 
			vcValue is greater than the upper threshold."
	::= 14420

    vcExceedUpperThresholdIncrease85 TRAP-TYPE
	ENTERPRISE	network-device
	VARIABLES	{ vcValue, adminDateAndTime, adminNDTrapSeqNo,
			  vcIndex, vcType }
	DESCRIPTION	"This trap is generated when set
			vcExUpThresholdIncreaseTrapID equal 85 and 
			vcValue is greater than the upper threshold."
	::= 14421

    vcExceedUpperThresholdIncrease86 TRAP-TYPE
	ENTERPRISE	network-device
	VARIABLES	{ vcValue, adminDateAndTime, adminNDTrapSeqNo,
			  vcIndex, vcType }
	DESCRIPTION	"This trap is generated when set
			vcExUpThresholdIncreaseTrapID equal 86 and 
			vcValue is greater than the upper threshold."
	::= 14422

    vcExceedUpperThresholdIncrease87 TRAP-TYPE
	ENTERPRISE	network-device
	VARIABLES	{ vcValue, adminDateAndTime, adminNDTrapSeqNo,
			  vcIndex, vcType }
	DESCRIPTION	"This trap is generated when set
			vcExUpThresholdIncreaseTrapID equal 87 and 
			vcValue is greater than the upper threshold."
	::= 14423

    vcExceedUpperThresholdIncrease88 TRAP-TYPE
	ENTERPRISE	network-device
	VARIABLES	{ vcValue, adminDateAndTime, adminNDTrapSeqNo,
			  vcIndex, vcType }
	DESCRIPTION	"This trap is generated when set
			vcExUpThresholdIncreaseTrapID equal 88 and 
			vcValue is greater than the upper threshold."
	::= 14424

    vcExceedUpperThresholdIncrease89 TRAP-TYPE
	ENTERPRISE	network-device
	VARIABLES	{ vcValue, adminDateAndTime, adminNDTrapSeqNo,
			  vcIndex, vcType }
	DESCRIPTION	"This trap is generated when set
			vcExUpThresholdIncreaseTrapID equal 89 and 
			vcValue is greater than the upper threshold."
	::= 14425

    vcExceedUpperThresholdIncrease90 TRAP-TYPE
	ENTERPRISE	network-device
	VARIABLES	{ vcValue, adminDateAndTime, adminNDTrapSeqNo,
			  vcIndex, vcType }
	DESCRIPTION	"This trap is generated when set
			vcExUpThresholdIncreaseTrapID equal 90 and 
			vcValue is greater than the upper threshold."
	::= 14426

    vcExceedUpperThresholdIncrease91 TRAP-TYPE
	ENTERPRISE	network-device
	VARIABLES	{ vcValue, adminDateAndTime, adminNDTrapSeqNo,
			  vcIndex, vcType }
	DESCRIPTION	"This trap is generated when set
			vcExUpThresholdIncreaseTrapID equal 91 and 
			vcValue is greater than the upper threshold."
	::= 14427

    vcExceedUpperThresholdIncrease92 TRAP-TYPE
	ENTERPRISE	network-device
	VARIABLES	{ vcValue, adminDateAndTime, adminNDTrapSeqNo,
			  vcIndex, vcType }
	DESCRIPTION	"This trap is generated when set
			vcExUpThresholdIncreaseTrapID equal 92 and 
			vcValue is greater than the upper threshold."
	::= 14428

    vcExceedUpperThresholdIncrease93 TRAP-TYPE
	ENTERPRISE	network-device
	VARIABLES	{ vcValue, adminDateAndTime, adminNDTrapSeqNo,
			  vcIndex, vcType }
	DESCRIPTION	"This trap is generated when set
			vcExUpThresholdIncreaseTrapID equal 93 and 
			vcValue is greater than the upper threshold."
	::= 14429

    vcExceedUpperThresholdIncrease94 TRAP-TYPE
	ENTERPRISE	network-device
	VARIABLES	{ vcValue, adminDateAndTime, adminNDTrapSeqNo,
			  vcIndex, vcType }
	DESCRIPTION	"This trap is generated when set
			vcExUpThresholdIncreaseTrapID equal 94 and 
			vcValue is greater than the upper threshold."
	::= 14430

    vcExceedUpperThresholdIncrease95 TRAP-TYPE
	ENTERPRISE	network-device
	VARIABLES	{ vcValue, adminDateAndTime, adminNDTrapSeqNo,
			  vcIndex, vcType }
	DESCRIPTION	"This trap is generated when set
			vcExUpThresholdIncreaseTrapID equal 95 and 
			vcValue is greater than the upper threshold."
	::= 14431

    vcExceedUpperThresholdIncrease96 TRAP-TYPE
	ENTERPRISE	network-device
	VARIABLES	{ vcValue, adminDateAndTime, adminNDTrapSeqNo,
			  vcIndex, vcType }
	DESCRIPTION	"This trap is generated when set
			vcExUpThresholdIncreaseTrapID equal 96 and 
			vcValue is greater than the upper threshold."
	::= 14432

    vcExceedUpperThresholdIncrease97 TRAP-TYPE
	ENTERPRISE	network-device
	VARIABLES	{ vcValue, adminDateAndTime, adminNDTrapSeqNo,
			  vcIndex, vcType }
	DESCRIPTION	"This trap is generated when set
			vcExUpThresholdIncreaseTrapID equal 97 and 
			vcValue is greater than the upper threshold."
	::= 14433

    vcExceedUpperThresholdIncrease98 TRAP-TYPE
	ENTERPRISE	network-device
	VARIABLES	{ vcValue, adminDateAndTime, adminNDTrapSeqNo,
			  vcIndex, vcType }
	DESCRIPTION	"This trap is generated when set
			vcExUpThresholdIncreaseTrapID equal 98 and 
			vcValue is greater than the upper threshold."
	::= 14434

    vcExceedUpperThresholdIncrease99 TRAP-TYPE
	ENTERPRISE	network-device
	VARIABLES	{ vcValue, adminDateAndTime, adminNDTrapSeqNo,
			  vcIndex, vcType }
	DESCRIPTION	"This trap is generated when set
			vcExUpThresholdIncreaseTrapID equal 99 and 
			vcValue is greater than the upper threshold."
	::= 14435

    vcExceedUpperThresholdIncrease100 TRAP-TYPE
	ENTERPRISE	network-device
	VARIABLES	{ vcValue, adminDateAndTime, adminNDTrapSeqNo,
			  vcIndex, vcType }
	DESCRIPTION	"This trap is generated when set
			vcExUpThresholdIncreaseTrapID equal 100 and 
			vcValue is greater than the upper threshold."
	::= 14436

    vcExceedUpperThresholdIncrease101 TRAP-TYPE
	ENTERPRISE	network-device
	VARIABLES	{ vcValue, adminDateAndTime, adminNDTrapSeqNo,
			  vcIndex, vcType }
	DESCRIPTION	"This trap is generated when set
			vcExUpThresholdIncreaseTrapID equal 101 and 
			vcValue is greater than the upper threshold."
	::= 14437

    vcExceedUpperThresholdIncrease102 TRAP-TYPE
	ENTERPRISE	network-device
	VARIABLES	{ vcValue, adminDateAndTime, adminNDTrapSeqNo,
			  vcIndex, vcType }
	DESCRIPTION	"This trap is generated when set
			vcExUpThresholdIncreaseTrapID equal 102 and 
			vcValue is greater than the upper threshold."
	::= 14438

    vcExceedUpperThresholdIncrease103 TRAP-TYPE
	ENTERPRISE	network-device
	VARIABLES	{ vcValue, adminDateAndTime, adminNDTrapSeqNo,
			  vcIndex, vcType }
	DESCRIPTION	"This trap is generated when set
			vcExUpThresholdIncreaseTrapID equal 103 and 
			vcValue is greater than the upper threshold."
	::= 14439

    vcExceedUpperThresholdIncrease104 TRAP-TYPE
	ENTERPRISE	network-device
	VARIABLES	{ vcValue, adminDateAndTime, adminNDTrapSeqNo,
			  vcIndex, vcType }
	DESCRIPTION	"This trap is generated when set
			vcExUpThresholdIncreaseTrapID equal 104 and 
			vcValue is greater than the upper threshold."
	::= 14440

    vcExceedUpperThresholdIncrease105 TRAP-TYPE
	ENTERPRISE	network-device
	VARIABLES	{ vcValue, adminDateAndTime, adminNDTrapSeqNo,
			  vcIndex, vcType }
	DESCRIPTION	"This trap is generated when set
			vcExUpThresholdIncreaseTrapID equal 105 and 
			vcValue is greater than the upper threshold."
	::= 14441

    vcExceedUpperThresholdIncrease106 TRAP-TYPE
	ENTERPRISE	network-device
	VARIABLES	{ vcValue, adminDateAndTime, adminNDTrapSeqNo,
			  vcIndex, vcType }
	DESCRIPTION	"This trap is generated when set
			vcExUpThresholdIncreaseTrapID equal 106 and 
			vcValue is greater than the upper threshold."
	::= 14442

    vcExceedUpperThresholdIncrease107 TRAP-TYPE
	ENTERPRISE	network-device
	VARIABLES	{ vcValue, adminDateAndTime, adminNDTrapSeqNo,
			  vcIndex, vcType }
	DESCRIPTION	"This trap is generated when set
			vcExUpThresholdIncreaseTrapID equal 107 and 
			vcValue is greater than the upper threshold."
	::= 14443

    vcExceedUpperThresholdIncrease108 TRAP-TYPE
	ENTERPRISE	network-device
	VARIABLES	{ vcValue, adminDateAndTime, adminNDTrapSeqNo,
			  vcIndex, vcType }
	DESCRIPTION	"This trap is generated when set
			vcExUpThresholdIncreaseTrapID equal 108 and 
			vcValue is greater than the upper threshold."
	::= 14444

    vcExceedUpperThresholdIncrease109 TRAP-TYPE
	ENTERPRISE	network-device
	VARIABLES	{ vcValue, adminDateAndTime, adminNDTrapSeqNo,
			  vcIndex, vcType }
	DESCRIPTION	"This trap is generated when set
			vcExUpThresholdIncreaseTrapID equal 109 and 
			vcValue is greater than the upper threshold."
	::= 14445

    vcExceedUpperThresholdIncrease110 TRAP-TYPE
	ENTERPRISE	network-device
	VARIABLES	{ vcValue, adminDateAndTime, adminNDTrapSeqNo,
			  vcIndex, vcType }
	DESCRIPTION	"This trap is generated when set
			vcExUpThresholdIncreaseTrapID equal 110 and 
			vcValue is greater than the upper threshold."
	::= 14446

    vcExceedUpperThresholdIncrease111 TRAP-TYPE
	ENTERPRISE	network-device
	VARIABLES	{ vcValue, adminDateAndTime, adminNDTrapSeqNo,
			  vcIndex, vcType }
	DESCRIPTION	"This trap is generated when set
			vcExUpThresholdIncreaseTrapID equal 111 and 
			vcValue is greater than the upper threshold."
	::= 14447

    vcExceedUpperThresholdIncrease112 TRAP-TYPE
	ENTERPRISE	network-device
	VARIABLES	{ vcValue, adminDateAndTime, adminNDTrapSeqNo,
			  vcIndex, vcType }
	DESCRIPTION	"This trap is generated when set
			vcExUpThresholdIncreaseTrapID equal 112 and 
			vcValue is greater than the upper threshold."
	::= 14448

    vcExceedUpperThresholdIncrease113 TRAP-TYPE
	ENTERPRISE	network-device
	VARIABLES	{ vcValue, adminDateAndTime, adminNDTrapSeqNo,
			  vcIndex, vcType }
	DESCRIPTION	"This trap is generated when set
			vcExUpThresholdIncreaseTrapID equal 113 and 
			vcValue is greater than the upper threshold."
	::= 14449

    vcExceedUpperThresholdIncrease114 TRAP-TYPE
	ENTERPRISE	network-device
	VARIABLES	{ vcValue, adminDateAndTime, adminNDTrapSeqNo,
			  vcIndex, vcType }
	DESCRIPTION	"This trap is generated when set
			vcExUpThresholdIncreaseTrapID equal 114 and 
			vcValue is greater than the upper threshold."
	::= 14450

    vcExceedUpperThresholdIncrease115 TRAP-TYPE
	ENTERPRISE	network-device
	VARIABLES	{ vcValue, adminDateAndTime, adminNDTrapSeqNo,
			  vcIndex, vcType }
	DESCRIPTION	"This trap is generated when set
			vcExUpThresholdIncreaseTrapID equal 115 and 
			vcValue is greater than the upper threshold."
	::= 14451

    vcExceedUpperThresholdIncrease116 TRAP-TYPE
	ENTERPRISE	network-device
	VARIABLES	{ vcValue, adminDateAndTime, adminNDTrapSeqNo,
			  vcIndex, vcType }
	DESCRIPTION	"This trap is generated when set
			vcExUpThresholdIncreaseTrapID equal 116 and 
			vcValue is greater than the upper threshold."
	::= 14452

    vcExceedUpperThresholdIncrease117 TRAP-TYPE
	ENTERPRISE	network-device
	VARIABLES	{ vcValue, adminDateAndTime, adminNDTrapSeqNo,
			  vcIndex, vcType }
	DESCRIPTION	"This trap is generated when set
			vcExUpThresholdIncreaseTrapID equal 117 and 
			vcValue is greater than the upper threshold."
	::= 14453

    vcExceedUpperThresholdIncrease118 TRAP-TYPE
	ENTERPRISE	network-device
	VARIABLES	{ vcValue, adminDateAndTime, adminNDTrapSeqNo,
			  vcIndex, vcType }
	DESCRIPTION	"This trap is generated when set
			vcExUpThresholdIncreaseTrapID equal 118 and 
			vcValue is greater than the upper threshold."
	::= 14454

    vcExceedUpperThresholdIncrease119 TRAP-TYPE
	ENTERPRISE	network-device
	VARIABLES	{ vcValue, adminDateAndTime, adminNDTrapSeqNo,
			  vcIndex, vcType }
	DESCRIPTION	"This trap is generated when set
			vcExUpThresholdIncreaseTrapID equal 119 and 
			vcValue is greater than the upper threshold."
	::= 14455

    vcExceedUpperThresholdIncrease120 TRAP-TYPE
	ENTERPRISE	network-device
	VARIABLES	{ vcValue, adminDateAndTime, adminNDTrapSeqNo,
			  vcIndex, vcType }
	DESCRIPTION	"This trap is generated when set
			vcExUpThresholdIncreaseTrapID equal 120 and 
			vcValue is greater than the upper threshold."
	::= 14456

    vcExceedUpperThresholdIncrease121 TRAP-TYPE
	ENTERPRISE	network-device
	VARIABLES	{ vcValue, adminDateAndTime, adminNDTrapSeqNo,
			  vcIndex, vcType }
	DESCRIPTION	"This trap is generated when set
			vcExUpThresholdIncreaseTrapID equal 121 and 
			vcValue is greater than the upper threshold."
	::= 14457

    vcExceedUpperThresholdIncrease122 TRAP-TYPE
	ENTERPRISE	network-device
	VARIABLES	{ vcValue, adminDateAndTime, adminNDTrapSeqNo,
			  vcIndex, vcType }
	DESCRIPTION	"This trap is generated when set
			vcExUpThresholdIncreaseTrapID equal 122 and 
			vcValue is greater than the upper threshold."
	::= 14458

    vcExceedUpperThresholdIncrease123 TRAP-TYPE
	ENTERPRISE	network-device
	VARIABLES	{ vcValue, adminDateAndTime, adminNDTrapSeqNo,
			  vcIndex, vcType }
	DESCRIPTION	"This trap is generated when set
			vcExUpThresholdIncreaseTrapID equal 123 and 
			vcValue is greater than the upper threshold."
	::= 14459

    vcExceedUpperThresholdIncrease124 TRAP-TYPE
	ENTERPRISE	network-device
	VARIABLES	{ vcValue, adminDateAndTime, adminNDTrapSeqNo,
			  vcIndex, vcType }
	DESCRIPTION	"This trap is generated when set
			vcExUpThresholdIncreaseTrapID equal 124 and 
			vcValue is greater than the upper threshold."
	::= 14460

    vcExceedUpperThresholdIncrease125 TRAP-TYPE
	ENTERPRISE	network-device
	VARIABLES	{ vcValue, adminDateAndTime, adminNDTrapSeqNo,
			  vcIndex, vcType }
	DESCRIPTION	"This trap is generated when set
			vcExUpThresholdIncreaseTrapID equal 125 and 
			vcValue is greater than the upper threshold."
	::= 14461

    vcExceedUpperThresholdIncrease126 TRAP-TYPE
	ENTERPRISE	network-device
	VARIABLES	{ vcValue, adminDateAndTime, adminNDTrapSeqNo,
			  vcIndex, vcType }
	DESCRIPTION	"This trap is generated when set
			vcExUpThresholdIncreaseTrapID equal 126 and 
			vcValue is greater than the upper threshold."
	::= 14462

    vcExceedUpperThresholdIncrease127 TRAP-TYPE
	ENTERPRISE	network-device
	VARIABLES	{ vcValue, adminDateAndTime, adminNDTrapSeqNo,
			  vcIndex, vcType }
	DESCRIPTION	"This trap is generated when set
			vcExUpThresholdIncreaseTrapID equal 127 and 
			vcValue is greater than the upper threshold."
	::= 14463

    vcExceedUpperThresholdDecrease1 TRAP-TYPE
	ENTERPRISE	network-device
	VARIABLES	{ vcValue, adminDateAndTime, adminNDTrapSeqNo,
			  vcIndex, vcType }
	DESCRIPTION	"This trap is generated when set
			vcExUpThresholdDecreaseTrapID equal 1 and
			vcValue is less equal the upper threshold minus
			the upper hysteresis after
			vcExceedUpperThresholdIncrease is generated.
			namely, vcValue <= (vcTrapUpperThreshold -
			vcTrapUpperHysteresis)."
	::= 14849

    vcExceedUpperThresholdDecrease2 TRAP-TYPE
	ENTERPRISE	network-device
	VARIABLES	{ vcValue, adminDateAndTime, adminNDTrapSeqNo,
			  vcIndex, vcType }
	DESCRIPTION	"This trap is generated when set
			vcExUpThresholdDecreaseTrapID equal 2 and
			vcValue is less equal the upper threshold minus
			the upper hysteresis after
			vcExceedUpperThresholdIncrease is generated.
			namely, vcValue <= (vcTrapUpperThreshold -
			vcTrapUpperHysteresis)."
	::= 14850

    vcExceedUpperThresholdDecrease3 TRAP-TYPE
	ENTERPRISE	network-device
	VARIABLES	{ vcValue, adminDateAndTime, adminNDTrapSeqNo,
			  vcIndex, vcType }
	DESCRIPTION	"This trap is generated when set
			vcExUpThresholdDecreaseTrapID equal 3 and
			vcValue is less equal the upper threshold minus
			the upper hysteresis after
			vcExceedUpperThresholdIncrease is generated.
			namely, vcValue <= (vcTrapUpperThreshold -
			vcTrapUpperHysteresis)."
	::= 14851

    vcExceedUpperThresholdDecrease4 TRAP-TYPE
	ENTERPRISE	network-device
	VARIABLES	{ vcValue, adminDateAndTime, adminNDTrapSeqNo,
			  vcIndex, vcType }
	DESCRIPTION	"This trap is generated when set
			vcExUpThresholdDecreaseTrapID equal 4 and
			vcValue is less equal the upper threshold minus
			the upper hysteresis after
			vcExceedUpperThresholdIncrease is generated.
			namely, vcValue <= (vcTrapUpperThreshold -
			vcTrapUpperHysteresis)."
	::= 14852

    vcExceedUpperThresholdDecrease5 TRAP-TYPE
	ENTERPRISE	network-device
	VARIABLES	{ vcValue, adminDateAndTime, adminNDTrapSeqNo,
			  vcIndex, vcType }
	DESCRIPTION	"This trap is generated when set
			vcExUpThresholdDecreaseTrapID equal 5 and
			vcValue is less equal the upper threshold minus
			the upper hysteresis after
			vcExceedUpperThresholdIncrease is generated.
			namely, vcValue <= (vcTrapUpperThreshold -
			vcTrapUpperHysteresis)."
	::= 14853

    vcExceedUpperThresholdDecrease6 TRAP-TYPE
	ENTERPRISE	network-device
	VARIABLES	{ vcValue, adminDateAndTime, adminNDTrapSeqNo,
			  vcIndex, vcType }
	DESCRIPTION	"This trap is generated when set
			vcExUpThresholdDecreaseTrapID equal 6 and
			vcValue is less equal the upper threshold minus
			the upper hysteresis after
			vcExceedUpperThresholdIncrease is generated.
			namely, vcValue <= (vcTrapUpperThreshold -
			vcTrapUpperHysteresis)."
	::= 14854

    vcExceedUpperThresholdDecrease7 TRAP-TYPE
	ENTERPRISE	network-device
	VARIABLES	{ vcValue, adminDateAndTime, adminNDTrapSeqNo,
			  vcIndex, vcType }
	DESCRIPTION	"This trap is generated when set
			vcExUpThresholdDecreaseTrapID equal 7 and
			vcValue is less equal the upper threshold minus
			the upper hysteresis after
			vcExceedUpperThresholdIncrease is generated.
			namely, vcValue <= (vcTrapUpperThreshold -
			vcTrapUpperHysteresis)."
	::= 14855

    vcExceedUpperThresholdDecrease8 TRAP-TYPE
	ENTERPRISE	network-device
	VARIABLES	{ vcValue, adminDateAndTime, adminNDTrapSeqNo,
			  vcIndex, vcType }
	DESCRIPTION	"This trap is generated when set
			vcExUpThresholdDecreaseTrapID equal 8 and
			vcValue is less equal the upper threshold minus
			the upper hysteresis after
			vcExceedUpperThresholdIncrease is generated.
			namely, vcValue <= (vcTrapUpperThreshold -
			vcTrapUpperHysteresis)."
	::= 14856

    vcExceedUpperThresholdDecrease9 TRAP-TYPE
	ENTERPRISE	network-device
	VARIABLES	{ vcValue, adminDateAndTime, adminNDTrapSeqNo,
			  vcIndex, vcType }
	DESCRIPTION	"This trap is generated when set
			vcExUpThresholdDecreaseTrapID equal 9 and
			vcValue is less equal the upper threshold minus
			the upper hysteresis after
			vcExceedUpperThresholdIncrease is generated.
			namely, vcValue <= (vcTrapUpperThreshold -
			vcTrapUpperHysteresis)."
	::= 14857

    vcExceedUpperThresholdDecrease10 TRAP-TYPE
	ENTERPRISE	network-device
	VARIABLES	{ vcValue, adminDateAndTime, adminNDTrapSeqNo,
			  vcIndex, vcType }
	DESCRIPTION	"This trap is generated when set
			vcExUpThresholdDecreaseTrapID equal 10 and
			vcValue is less equal the upper threshold minus
			the upper hysteresis after
			vcExceedUpperThresholdIncrease is generated.
			namely, vcValue <= (vcTrapUpperThreshold -
			vcTrapUpperHysteresis)."
	::= 14858

    vcExceedUpperThresholdDecrease11 TRAP-TYPE
	ENTERPRISE	network-device
	VARIABLES	{ vcValue, adminDateAndTime, adminNDTrapSeqNo,
			  vcIndex, vcType }
	DESCRIPTION	"This trap is generated when set
			vcExUpThresholdDecreaseTrapID equal 11 and
			vcValue is less equal the upper threshold minus
			the upper hysteresis after
			vcExceedUpperThresholdIncrease is generated.
			namely, vcValue <= (vcTrapUpperThreshold -
			vcTrapUpperHysteresis)."
	::= 14859

    vcExceedUpperThresholdDecrease12 TRAP-TYPE
	ENTERPRISE	network-device
	VARIABLES	{ vcValue, adminDateAndTime, adminNDTrapSeqNo,
			  vcIndex, vcType }
	DESCRIPTION	"This trap is generated when set
			vcExUpThresholdDecreaseTrapID equal 12 and
			vcValue is less equal the upper threshold minus
			the upper hysteresis after
			vcExceedUpperThresholdIncrease is generated.
			namely, vcValue <= (vcTrapUpperThreshold -
			vcTrapUpperHysteresis)."
	::= 14860

    vcExceedUpperThresholdDecrease13 TRAP-TYPE
	ENTERPRISE	network-device
	VARIABLES	{ vcValue, adminDateAndTime, adminNDTrapSeqNo,
			  vcIndex, vcType }
	DESCRIPTION	"This trap is generated when set
			vcExUpThresholdDecreaseTrapID equal 13 and
			vcValue is less equal the upper threshold minus
			the upper hysteresis after
			vcExceedUpperThresholdIncrease is generated.
			namely, vcValue <= (vcTrapUpperThreshold -
			vcTrapUpperHysteresis)."
	::= 14861

    vcExceedUpperThresholdDecrease14 TRAP-TYPE
	ENTERPRISE	network-device
	VARIABLES	{ vcValue, adminDateAndTime, adminNDTrapSeqNo,
			  vcIndex, vcType }
	DESCRIPTION	"This trap is generated when set
			vcExUpThresholdDecreaseTrapID equal 14 and
			vcValue is less equal the upper threshold minus
			the upper hysteresis after
			vcExceedUpperThresholdIncrease is generated.
			namely, vcValue <= (vcTrapUpperThreshold -
			vcTrapUpperHysteresis)."
	::= 14862

    vcExceedUpperThresholdDecrease15 TRAP-TYPE
	ENTERPRISE	network-device
	VARIABLES	{ vcValue, adminDateAndTime, adminNDTrapSeqNo,
			  vcIndex, vcType }
	DESCRIPTION	"This trap is generated when set
			vcExUpThresholdDecreaseTrapID equal 15 and
			vcValue is less equal the upper threshold minus
			the upper hysteresis after
			vcExceedUpperThresholdIncrease is generated.
			namely, vcValue <= (vcTrapUpperThreshold -
			vcTrapUpperHysteresis)."
	::= 14863

    vcExceedUpperThresholdDecrease16 TRAP-TYPE
	ENTERPRISE	network-device
	VARIABLES	{ vcValue, adminDateAndTime, adminNDTrapSeqNo,
			  vcIndex, vcType }
	DESCRIPTION	"This trap is generated when set
			vcExUpThresholdDecreaseTrapID equal 16 and
			vcValue is less equal the upper threshold minus
			the upper hysteresis after
			vcExceedUpperThresholdIncrease is generated.
			namely, vcValue <= (vcTrapUpperThreshold -
			vcTrapUpperHysteresis)."
	::= 14864

    vcExceedUpperThresholdDecrease17 TRAP-TYPE
	ENTERPRISE	network-device
	VARIABLES	{ vcValue, adminDateAndTime, adminNDTrapSeqNo,
			  vcIndex, vcType }
	DESCRIPTION	"This trap is generated when set
			vcExUpThresholdDecreaseTrapID equal 17 and
			vcValue is less equal the upper threshold minus
			the upper hysteresis after
			vcExceedUpperThresholdIncrease is generated.
			namely, vcValue <= (vcTrapUpperThreshold -
			vcTrapUpperHysteresis)."
	::= 14865

    vcExceedUpperThresholdDecrease18 TRAP-TYPE
	ENTERPRISE	network-device
	VARIABLES	{ vcValue, adminDateAndTime, adminNDTrapSeqNo,
			  vcIndex, vcType }
	DESCRIPTION	"This trap is generated when set
			vcExUpThresholdDecreaseTrapID equal 18 and
			vcValue is less equal the upper threshold minus
			the upper hysteresis after
			vcExceedUpperThresholdIncrease is generated.
			namely, vcValue <= (vcTrapUpperThreshold -
			vcTrapUpperHysteresis)."
	::= 14866

    vcExceedUpperThresholdDecrease19 TRAP-TYPE
	ENTERPRISE	network-device
	VARIABLES	{ vcValue, adminDateAndTime, adminNDTrapSeqNo,
			  vcIndex, vcType }
	DESCRIPTION	"This trap is generated when set
			vcExUpThresholdDecreaseTrapID equal 19 and
			vcValue is less equal the upper threshold minus
			the upper hysteresis after
			vcExceedUpperThresholdIncrease is generated.
			namely, vcValue <= (vcTrapUpperThreshold -
			vcTrapUpperHysteresis)."
	::= 14867

    vcExceedUpperThresholdDecrease20 TRAP-TYPE
	ENTERPRISE	network-device
	VARIABLES	{ vcValue, adminDateAndTime, adminNDTrapSeqNo,
			  vcIndex, vcType }
	DESCRIPTION	"This trap is generated when set
			vcExUpThresholdDecreaseTrapID equal 20 and
			vcValue is less equal the upper threshold minus
			the upper hysteresis after
			vcExceedUpperThresholdIncrease is generated.
			namely, vcValue <= (vcTrapUpperThreshold -
			vcTrapUpperHysteresis)."
	::= 14868

    vcExceedUpperThresholdDecrease21 TRAP-TYPE
	ENTERPRISE	network-device
	VARIABLES	{ vcValue, adminDateAndTime, adminNDTrapSeqNo,
			  vcIndex, vcType }
	DESCRIPTION	"This trap is generated when set
			vcExUpThresholdDecreaseTrapID equal 21 and
			vcValue is less equal the upper threshold minus
			the upper hysteresis after
			vcExceedUpperThresholdIncrease is generated.
			namely, vcValue <= (vcTrapUpperThreshold -
			vcTrapUpperHysteresis)."
	::= 14869

    vcExceedUpperThresholdDecrease22 TRAP-TYPE
	ENTERPRISE	network-device
	VARIABLES	{ vcValue, adminDateAndTime, adminNDTrapSeqNo,
			  vcIndex, vcType }
	DESCRIPTION	"This trap is generated when set
			vcExUpThresholdDecreaseTrapID equal 22 and
			vcValue is less equal the upper threshold minus
			the upper hysteresis after
			vcExceedUpperThresholdIncrease is generated.
			namely, vcValue <= (vcTrapUpperThreshold -
			vcTrapUpperHysteresis)."
	::= 14870

    vcExceedUpperThresholdDecrease23 TRAP-TYPE
	ENTERPRISE	network-device
	VARIABLES	{ vcValue, adminDateAndTime, adminNDTrapSeqNo,
			  vcIndex, vcType }
	DESCRIPTION	"This trap is generated when set
			vcExUpThresholdDecreaseTrapID equal 23 and
			vcValue is less equal the upper threshold minus
			the upper hysteresis after
			vcExceedUpperThresholdIncrease is generated.
			namely, vcValue <= (vcTrapUpperThreshold -
			vcTrapUpperHysteresis)."
	::= 14871

    vcExceedUpperThresholdDecrease24 TRAP-TYPE
	ENTERPRISE	network-device
	VARIABLES	{ vcValue, adminDateAndTime, adminNDTrapSeqNo,
			  vcIndex, vcType }
	DESCRIPTION	"This trap is generated when set
			vcExUpThresholdDecreaseTrapID equal 24 and
			vcValue is less equal the upper threshold minus
			the upper hysteresis after
			vcExceedUpperThresholdIncrease is generated.
			namely, vcValue <= (vcTrapUpperThreshold -
			vcTrapUpperHysteresis)."
	::= 14872

    vcExceedUpperThresholdDecrease25 TRAP-TYPE
	ENTERPRISE	network-device
	VARIABLES	{ vcValue, adminDateAndTime, adminNDTrapSeqNo,
			  vcIndex, vcType }
	DESCRIPTION	"This trap is generated when set
			vcExUpThresholdDecreaseTrapID equal 25 and
			vcValue is less equal the upper threshold minus
			the upper hysteresis after
			vcExceedUpperThresholdIncrease is generated.
			namely, vcValue <= (vcTrapUpperThreshold -
			vcTrapUpperHysteresis)."
	::= 14873

    vcExceedUpperThresholdDecrease26 TRAP-TYPE
	ENTERPRISE	network-device
	VARIABLES	{ vcValue, adminDateAndTime, adminNDTrapSeqNo,
			  vcIndex, vcType }
	DESCRIPTION	"This trap is generated when set
			vcExUpThresholdDecreaseTrapID equal 26 and
			vcValue is less equal the upper threshold minus
			the upper hysteresis after
			vcExceedUpperThresholdIncrease is generated.
			namely, vcValue <= (vcTrapUpperThreshold -
			vcTrapUpperHysteresis)."
	::= 14874

    vcExceedUpperThresholdDecrease27 TRAP-TYPE
	ENTERPRISE	network-device
	VARIABLES	{ vcValue, adminDateAndTime, adminNDTrapSeqNo,
			  vcIndex, vcType }
	DESCRIPTION	"This trap is generated when set
			vcExUpThresholdDecreaseTrapID equal 27 and
			vcValue is less equal the upper threshold minus
			the upper hysteresis after
			vcExceedUpperThresholdIncrease is generated.
			namely, vcValue <= (vcTrapUpperThreshold -
			vcTrapUpperHysteresis)."
	::= 14875

    vcExceedUpperThresholdDecrease28 TRAP-TYPE
	ENTERPRISE	network-device
	VARIABLES	{ vcValue, adminDateAndTime, adminNDTrapSeqNo,
			  vcIndex, vcType }
	DESCRIPTION	"This trap is generated when set
			vcExUpThresholdDecreaseTrapID equal 28 and
			vcValue is less equal the upper threshold minus
			the upper hysteresis after
			vcExceedUpperThresholdIncrease is generated.
			namely, vcValue <= (vcTrapUpperThreshold -
			vcTrapUpperHysteresis)."
	::= 14876

    vcExceedUpperThresholdDecrease29 TRAP-TYPE
	ENTERPRISE	network-device
	VARIABLES	{ vcValue, adminDateAndTime, adminNDTrapSeqNo,
			  vcIndex, vcType }
	DESCRIPTION	"This trap is generated when set
			vcExUpThresholdDecreaseTrapID equal 29 and
			vcValue is less equal the upper threshold minus
			the upper hysteresis after
			vcExceedUpperThresholdIncrease is generated.
			namely, vcValue <= (vcTrapUpperThreshold -
			vcTrapUpperHysteresis)."
	::= 14877

    vcExceedUpperThresholdDecrease30 TRAP-TYPE
	ENTERPRISE	network-device
	VARIABLES	{ vcValue, adminDateAndTime, adminNDTrapSeqNo,
			  vcIndex, vcType }
	DESCRIPTION	"This trap is generated when set
			vcExUpThresholdDecreaseTrapID equal 30 and
			vcValue is less equal the upper threshold minus
			the upper hysteresis after
			vcExceedUpperThresholdIncrease is generated.
			namely, vcValue <= (vcTrapUpperThreshold -
			vcTrapUpperHysteresis)."
	::= 14878

    vcExceedUpperThresholdDecrease31 TRAP-TYPE
	ENTERPRISE	network-device
	VARIABLES	{ vcValue, adminDateAndTime, adminNDTrapSeqNo,
			  vcIndex, vcType }
	DESCRIPTION	"This trap is generated when set
			vcExUpThresholdDecreaseTrapID equal 31 and
			vcValue is less equal the upper threshold minus
			the upper hysteresis after
			vcExceedUpperThresholdIncrease is generated.
			namely, vcValue <= (vcTrapUpperThreshold -
			vcTrapUpperHysteresis)."
	::= 14879

    vcExceedUpperThresholdDecrease32 TRAP-TYPE
	ENTERPRISE	network-device
	VARIABLES	{ vcValue, adminDateAndTime, adminNDTrapSeqNo,
			  vcIndex, vcType }
	DESCRIPTION	"This trap is generated when set
			vcExUpThresholdDecreaseTrapID equal 32 and
			vcValue is less equal the upper threshold minus
			the upper hysteresis after
			vcExceedUpperThresholdIncrease is generated.
			namely, vcValue <= (vcTrapUpperThreshold -
			vcTrapUpperHysteresis)."
	::= 14880

    vcExceedUpperThresholdDecrease33 TRAP-TYPE
	ENTERPRISE	network-device
	VARIABLES	{ vcValue, adminDateAndTime, adminNDTrapSeqNo,
			  vcIndex, vcType }
	DESCRIPTION	"This trap is generated when set
			vcExUpThresholdDecreaseTrapID equal 33 and
			vcValue is less equal the upper threshold minus
			the upper hysteresis after
			vcExceedUpperThresholdIncrease is generated.
			namely, vcValue <= (vcTrapUpperThreshold -
			vcTrapUpperHysteresis)."
	::= 14881

    vcExceedUpperThresholdDecrease34 TRAP-TYPE
	ENTERPRISE	network-device
	VARIABLES	{ vcValue, adminDateAndTime, adminNDTrapSeqNo,
			  vcIndex, vcType }
	DESCRIPTION	"This trap is generated when set
			vcExUpThresholdDecreaseTrapID equal 34 and
			vcValue is less equal the upper threshold minus
			the upper hysteresis after
			vcExceedUpperThresholdIncrease is generated.
			namely, vcValue <= (vcTrapUpperThreshold -
			vcTrapUpperHysteresis)."
	::= 14882

    vcExceedUpperThresholdDecrease35 TRAP-TYPE
	ENTERPRISE	network-device
	VARIABLES	{ vcValue, adminDateAndTime, adminNDTrapSeqNo,
			  vcIndex, vcType }
	DESCRIPTION	"This trap is generated when set
			vcExUpThresholdDecreaseTrapID equal 35 and
			vcValue is less equal the upper threshold minus
			the upper hysteresis after
			vcExceedUpperThresholdIncrease is generated.
			namely, vcValue <= (vcTrapUpperThreshold -
			vcTrapUpperHysteresis)."
	::= 14883

    vcExceedUpperThresholdDecrease36 TRAP-TYPE
	ENTERPRISE	network-device
	VARIABLES	{ vcValue, adminDateAndTime, adminNDTrapSeqNo,
			  vcIndex, vcType }
	DESCRIPTION	"This trap is generated when set
			vcExUpThresholdDecreaseTrapID equal 36 and
			vcValue is less equal the upper threshold minus
			the upper hysteresis after
			vcExceedUpperThresholdIncrease is generated.
			namely, vcValue <= (vcTrapUpperThreshold -
			vcTrapUpperHysteresis)."
	::= 14884

    vcExceedUpperThresholdDecrease37 TRAP-TYPE
	ENTERPRISE	network-device
	VARIABLES	{ vcValue, adminDateAndTime, adminNDTrapSeqNo,
			  vcIndex, vcType }
	DESCRIPTION	"This trap is generated when set
			vcExUpThresholdDecreaseTrapID equal 37 and
			vcValue is less equal the upper threshold minus
			the upper hysteresis after
			vcExceedUpperThresholdIncrease is generated.
			namely, vcValue <= (vcTrapUpperThreshold -
			vcTrapUpperHysteresis)."
	::= 14885

    vcExceedUpperThresholdDecrease38 TRAP-TYPE
	ENTERPRISE	network-device
	VARIABLES	{ vcValue, adminDateAndTime, adminNDTrapSeqNo,
			  vcIndex, vcType }
	DESCRIPTION	"This trap is generated when set
			vcExUpThresholdDecreaseTrapID equal 38 and
			vcValue is less equal the upper threshold minus
			the upper hysteresis after
			vcExceedUpperThresholdIncrease is generated.
			namely, vcValue <= (vcTrapUpperThreshold -
			vcTrapUpperHysteresis)."
	::= 14886

    vcExceedUpperThresholdDecrease39 TRAP-TYPE
	ENTERPRISE	network-device
	VARIABLES	{ vcValue, adminDateAndTime, adminNDTrapSeqNo,
			  vcIndex, vcType }
	DESCRIPTION	"This trap is generated when set
			vcExUpThresholdDecreaseTrapID equal 39 and
			vcValue is less equal the upper threshold minus
			the upper hysteresis after
			vcExceedUpperThresholdIncrease is generated.
			namely, vcValue <= (vcTrapUpperThreshold -
			vcTrapUpperHysteresis)."
	::= 14887

    vcExceedUpperThresholdDecrease40 TRAP-TYPE
	ENTERPRISE	network-device
	VARIABLES	{ vcValue, adminDateAndTime, adminNDTrapSeqNo,
			  vcIndex, vcType }
	DESCRIPTION	"This trap is generated when set
			vcExUpThresholdDecreaseTrapID equal 40 and
			vcValue is less equal the upper threshold minus
			the upper hysteresis after
			vcExceedUpperThresholdIncrease is generated.
			namely, vcValue <= (vcTrapUpperThreshold -
			vcTrapUpperHysteresis)."
	::= 14888

    vcExceedUpperThresholdDecrease41 TRAP-TYPE
	ENTERPRISE	network-device
	VARIABLES	{ vcValue, adminDateAndTime, adminNDTrapSeqNo,
			  vcIndex, vcType }
	DESCRIPTION	"This trap is generated when set
			vcExUpThresholdDecreaseTrapID equal 41 and
			vcValue is less equal the upper threshold minus
			the upper hysteresis after
			vcExceedUpperThresholdIncrease is generated.
			namely, vcValue <= (vcTrapUpperThreshold -
			vcTrapUpperHysteresis)."
	::= 14889

    vcExceedUpperThresholdDecrease42 TRAP-TYPE
	ENTERPRISE	network-device
	VARIABLES	{ vcValue, adminDateAndTime, adminNDTrapSeqNo,
			  vcIndex, vcType }
	DESCRIPTION	"This trap is generated when set
			vcExUpThresholdDecreaseTrapID equal 42 and
			vcValue is less equal the upper threshold minus
			the upper hysteresis after
			vcExceedUpperThresholdIncrease is generated.
			namely, vcValue <= (vcTrapUpperThreshold -
			vcTrapUpperHysteresis)."
	::= 14890

    vcExceedUpperThresholdDecrease43 TRAP-TYPE
	ENTERPRISE	network-device
	VARIABLES	{ vcValue, adminDateAndTime, adminNDTrapSeqNo,
			  vcIndex, vcType }
	DESCRIPTION	"This trap is generated when set
			vcExUpThresholdDecreaseTrapID equal 43 and
			vcValue is less equal the upper threshold minus
			the upper hysteresis after
			vcExceedUpperThresholdIncrease is generated.
			namely, vcValue <= (vcTrapUpperThreshold -
			vcTrapUpperHysteresis)."
	::= 14891

    vcExceedUpperThresholdDecrease44 TRAP-TYPE
	ENTERPRISE	network-device
	VARIABLES	{ vcValue, adminDateAndTime, adminNDTrapSeqNo,
			  vcIndex, vcType }
	DESCRIPTION	"This trap is generated when set
			vcExUpThresholdDecreaseTrapID equal 44 and
			vcValue is less equal the upper threshold minus
			the upper hysteresis after
			vcExceedUpperThresholdIncrease is generated.
			namely, vcValue <= (vcTrapUpperThreshold -
			vcTrapUpperHysteresis)."
	::= 14892

    vcExceedUpperThresholdDecrease45 TRAP-TYPE
	ENTERPRISE	network-device
	VARIABLES	{ vcValue, adminDateAndTime, adminNDTrapSeqNo,
			  vcIndex, vcType }
	DESCRIPTION	"This trap is generated when set
			vcExUpThresholdDecreaseTrapID equal 45 and
			vcValue is less equal the upper threshold minus
			the upper hysteresis after
			vcExceedUpperThresholdIncrease is generated.
			namely, vcValue <= (vcTrapUpperThreshold -
			vcTrapUpperHysteresis)."
	::= 14893

    vcExceedUpperThresholdDecrease46 TRAP-TYPE
	ENTERPRISE	network-device
	VARIABLES	{ vcValue, adminDateAndTime, adminNDTrapSeqNo,
			  vcIndex, vcType }
	DESCRIPTION	"This trap is generated when set
			vcExUpThresholdDecreaseTrapID equal 46 and
			vcValue is less equal the upper threshold minus
			the upper hysteresis after
			vcExceedUpperThresholdIncrease is generated.
			namely, vcValue <= (vcTrapUpperThreshold -
			vcTrapUpperHysteresis)."
	::= 14894

    vcExceedUpperThresholdDecrease47 TRAP-TYPE
	ENTERPRISE	network-device
	VARIABLES	{ vcValue, adminDateAndTime, adminNDTrapSeqNo,
			  vcIndex, vcType }
	DESCRIPTION	"This trap is generated when set
			vcExUpThresholdDecreaseTrapID equal 47 and
			vcValue is less equal the upper threshold minus
			the upper hysteresis after
			vcExceedUpperThresholdIncrease is generated.
			namely, vcValue <= (vcTrapUpperThreshold -
			vcTrapUpperHysteresis)."
	::= 14895

    vcExceedUpperThresholdDecrease48 TRAP-TYPE
	ENTERPRISE	network-device
	VARIABLES	{ vcValue, adminDateAndTime, adminNDTrapSeqNo,
			  vcIndex, vcType }
	DESCRIPTION	"This trap is generated when set
			vcExUpThresholdDecreaseTrapID equal 48 and
			vcValue is less equal the upper threshold minus
			the upper hysteresis after
			vcExceedUpperThresholdIncrease is generated.
			namely, vcValue <= (vcTrapUpperThreshold -
			vcTrapUpperHysteresis)."
	::= 14896

    vcExceedUpperThresholdDecrease49 TRAP-TYPE
	ENTERPRISE	network-device
	VARIABLES	{ vcValue, adminDateAndTime, adminNDTrapSeqNo,
			  vcIndex, vcType }
	DESCRIPTION	"This trap is generated when set
			vcExUpThresholdDecreaseTrapID equal 49 and
			vcValue is less equal the upper threshold minus
			the upper hysteresis after
			vcExceedUpperThresholdIncrease is generated.
			namely, vcValue <= (vcTrapUpperThreshold -
			vcTrapUpperHysteresis)."
	::= 14897

    vcExceedUpperThresholdDecrease50 TRAP-TYPE
	ENTERPRISE	network-device
	VARIABLES	{ vcValue, adminDateAndTime, adminNDTrapSeqNo,
			  vcIndex, vcType }
	DESCRIPTION	"This trap is generated when set
			vcExUpThresholdDecreaseTrapID equal 50 and
			vcValue is less equal the upper threshold minus
			the upper hysteresis after
			vcExceedUpperThresholdIncrease is generated.
			namely, vcValue <= (vcTrapUpperThreshold -
			vcTrapUpperHysteresis)."
	::= 14898

    vcExceedUpperThresholdDecrease51 TRAP-TYPE
	ENTERPRISE	network-device
	VARIABLES	{ vcValue, adminDateAndTime, adminNDTrapSeqNo,
			  vcIndex, vcType }
	DESCRIPTION	"This trap is generated when set
			vcExUpThresholdDecreaseTrapID equal 51 and
			vcValue is less equal the upper threshold minus
			the upper hysteresis after
			vcExceedUpperThresholdIncrease is generated.
			namely, vcValue <= (vcTrapUpperThreshold -
			vcTrapUpperHysteresis)."
	::= 14899

    vcExceedUpperThresholdDecrease52 TRAP-TYPE
	ENTERPRISE	network-device
	VARIABLES	{ vcValue, adminDateAndTime, adminNDTrapSeqNo,
			  vcIndex, vcType }
	DESCRIPTION	"This trap is generated when set
			vcExUpThresholdDecreaseTrapID equal 52 and
			vcValue is less equal the upper threshold minus
			the upper hysteresis after
			vcExceedUpperThresholdIncrease is generated.
			namely, vcValue <= (vcTrapUpperThreshold -
			vcTrapUpperHysteresis)."
	::= 14900

    vcExceedUpperThresholdDecrease53 TRAP-TYPE
	ENTERPRISE	network-device
	VARIABLES	{ vcValue, adminDateAndTime, adminNDTrapSeqNo,
			  vcIndex, vcType }
	DESCRIPTION	"This trap is generated when set
			vcExUpThresholdDecreaseTrapID equal 53 and
			vcValue is less equal the upper threshold minus
			the upper hysteresis after
			vcExceedUpperThresholdIncrease is generated.
			namely, vcValue <= (vcTrapUpperThreshold -
			vcTrapUpperHysteresis)."
	::= 14901

    vcExceedUpperThresholdDecrease54 TRAP-TYPE
	ENTERPRISE	network-device
	VARIABLES	{ vcValue, adminDateAndTime, adminNDTrapSeqNo,
			  vcIndex, vcType }
	DESCRIPTION	"This trap is generated when set
			vcExUpThresholdDecreaseTrapID equal 54 and
			vcValue is less equal the upper threshold minus
			the upper hysteresis after
			vcExceedUpperThresholdIncrease is generated.
			namely, vcValue <= (vcTrapUpperThreshold -
			vcTrapUpperHysteresis)."
	::= 14902

    vcExceedUpperThresholdDecrease55 TRAP-TYPE
	ENTERPRISE	network-device
	VARIABLES	{ vcValue, adminDateAndTime, adminNDTrapSeqNo,
			  vcIndex, vcType }
	DESCRIPTION	"This trap is generated when set
			vcExUpThresholdDecreaseTrapID equal 55 and
			vcValue is less equal the upper threshold minus
			the upper hysteresis after
			vcExceedUpperThresholdIncrease is generated.
			namely, vcValue <= (vcTrapUpperThreshold -
			vcTrapUpperHysteresis)."
	::= 14903

    vcExceedUpperThresholdDecrease56 TRAP-TYPE
	ENTERPRISE	network-device
	VARIABLES	{ vcValue, adminDateAndTime, adminNDTrapSeqNo,
			  vcIndex, vcType }
	DESCRIPTION	"This trap is generated when set
			vcExUpThresholdDecreaseTrapID equal 56 and
			vcValue is less equal the upper threshold minus
			the upper hysteresis after
			vcExceedUpperThresholdIncrease is generated.
			namely, vcValue <= (vcTrapUpperThreshold -
			vcTrapUpperHysteresis)."
	::= 14904

    vcExceedUpperThresholdDecrease57 TRAP-TYPE
	ENTERPRISE	network-device
	VARIABLES	{ vcValue, adminDateAndTime, adminNDTrapSeqNo,
			  vcIndex, vcType }
	DESCRIPTION	"This trap is generated when set
			vcExUpThresholdDecreaseTrapID equal 57 and
			vcValue is less equal the upper threshold minus
			the upper hysteresis after
			vcExceedUpperThresholdIncrease is generated.
			namely, vcValue <= (vcTrapUpperThreshold -
			vcTrapUpperHysteresis)."
	::= 14905

    vcExceedUpperThresholdDecrease58 TRAP-TYPE
	ENTERPRISE	network-device
	VARIABLES	{ vcValue, adminDateAndTime, adminNDTrapSeqNo,
			  vcIndex, vcType }
	DESCRIPTION	"This trap is generated when set
			vcExUpThresholdDecreaseTrapID equal 58 and
			vcValue is less equal the upper threshold minus
			the upper hysteresis after
			vcExceedUpperThresholdIncrease is generated.
			namely, vcValue <= (vcTrapUpperThreshold -
			vcTrapUpperHysteresis)."
	::= 14906

    vcExceedUpperThresholdDecrease59 TRAP-TYPE
	ENTERPRISE	network-device
	VARIABLES	{ vcValue, adminDateAndTime, adminNDTrapSeqNo,
			  vcIndex, vcType }
	DESCRIPTION	"This trap is generated when set
			vcExUpThresholdDecreaseTrapID equal 59 and
			vcValue is less equal the upper threshold minus
			the upper hysteresis after
			vcExceedUpperThresholdIncrease is generated.
			namely, vcValue <= (vcTrapUpperThreshold -
			vcTrapUpperHysteresis)."
	::= 14907

    vcExceedUpperThresholdDecrease60 TRAP-TYPE
	ENTERPRISE	network-device
	VARIABLES	{ vcValue, adminDateAndTime, adminNDTrapSeqNo,
			  vcIndex, vcType }
	DESCRIPTION	"This trap is generated when set
			vcExUpThresholdDecreaseTrapID equal 60 and
			vcValue is less equal the upper threshold minus
			the upper hysteresis after
			vcExceedUpperThresholdIncrease is generated.
			namely, vcValue <= (vcTrapUpperThreshold -
			vcTrapUpperHysteresis)."
	::= 14908

    vcExceedUpperThresholdDecrease61 TRAP-TYPE
	ENTERPRISE	network-device
	VARIABLES	{ vcValue, adminDateAndTime, adminNDTrapSeqNo,
			  vcIndex, vcType }
	DESCRIPTION	"This trap is generated when set
			vcExUpThresholdDecreaseTrapID equal 61 and
			vcValue is less equal the upper threshold minus
			the upper hysteresis after
			vcExceedUpperThresholdIncrease is generated.
			namely, vcValue <= (vcTrapUpperThreshold -
			vcTrapUpperHysteresis)."
	::= 14909

    vcExceedUpperThresholdDecrease62 TRAP-TYPE
	ENTERPRISE	network-device
	VARIABLES	{ vcValue, adminDateAndTime, adminNDTrapSeqNo,
			  vcIndex, vcType }
	DESCRIPTION	"This trap is generated when set
			vcExUpThresholdDecreaseTrapID equal 62 and
			vcValue is less equal the upper threshold minus
			the upper hysteresis after
			vcExceedUpperThresholdIncrease is generated.
			namely, vcValue <= (vcTrapUpperThreshold -
			vcTrapUpperHysteresis)."
	::= 14910

    vcExceedUpperThresholdDecrease63 TRAP-TYPE
	ENTERPRISE	network-device
	VARIABLES	{ vcValue, adminDateAndTime, adminNDTrapSeqNo,
			  vcIndex, vcType }
	DESCRIPTION	"This trap is generated when set
			vcExUpThresholdDecreaseTrapID equal 63 and
			vcValue is less equal the upper threshold minus
			the upper hysteresis after
			vcExceedUpperThresholdIncrease is generated.
			namely, vcValue <= (vcTrapUpperThreshold -
			vcTrapUpperHysteresis)."
	::= 14911

    vcExceedUpperThresholdDecrease64 TRAP-TYPE
	ENTERPRISE	network-device
	VARIABLES	{ vcValue, adminDateAndTime, adminNDTrapSeqNo,
			  vcIndex, vcType }
	DESCRIPTION	"This trap is generated when set
			vcExUpThresholdDecreaseTrapID equal 64 and
			vcValue is less equal the upper threshold minus
			the upper hysteresis after
			vcExceedUpperThresholdIncrease is generated.
			namely, vcValue <= (vcTrapUpperThreshold -
			vcTrapUpperHysteresis)."
	::= 14912

    vcExceedUpperThresholdDecrease65 TRAP-TYPE
	ENTERPRISE	network-device
	VARIABLES	{ vcValue, adminDateAndTime, adminNDTrapSeqNo,
			  vcIndex, vcType }
	DESCRIPTION	"This trap is generated when set
			vcExUpThresholdDecreaseTrapID equal 65 and
			vcValue is less equal the upper threshold minus
			the upper hysteresis after
			vcExceedUpperThresholdIncrease is generated.
			namely, vcValue <= (vcTrapUpperThreshold -
			vcTrapUpperHysteresis)."
	::= 14913

    vcExceedUpperThresholdDecrease66 TRAP-TYPE
	ENTERPRISE	network-device
	VARIABLES	{ vcValue, adminDateAndTime, adminNDTrapSeqNo,
			  vcIndex, vcType }
	DESCRIPTION	"This trap is generated when set
			vcExUpThresholdDecreaseTrapID equal 66 and
			vcValue is less equal the upper threshold minus
			the upper hysteresis after
			vcExceedUpperThresholdIncrease is generated.
			namely, vcValue <= (vcTrapUpperThreshold -
			vcTrapUpperHysteresis)."
	::= 14914

    vcExceedUpperThresholdDecrease67 TRAP-TYPE
	ENTERPRISE	network-device
	VARIABLES	{ vcValue, adminDateAndTime, adminNDTrapSeqNo,
			  vcIndex, vcType }
	DESCRIPTION	"This trap is generated when set
			vcExUpThresholdDecreaseTrapID equal 67 and
			vcValue is less equal the upper threshold minus
			the upper hysteresis after
			vcExceedUpperThresholdIncrease is generated.
			namely, vcValue <= (vcTrapUpperThreshold -
			vcTrapUpperHysteresis)."
	::= 14915

    vcExceedUpperThresholdDecrease68 TRAP-TYPE
	ENTERPRISE	network-device
	VARIABLES	{ vcValue, adminDateAndTime, adminNDTrapSeqNo,
			  vcIndex, vcType }
	DESCRIPTION	"This trap is generated when set
			vcExUpThresholdDecreaseTrapID equal 68 and
			vcValue is less equal the upper threshold minus
			the upper hysteresis after
			vcExceedUpperThresholdIncrease is generated.
			namely, vcValue <= (vcTrapUpperThreshold -
			vcTrapUpperHysteresis)."
	::= 14916

    vcExceedUpperThresholdDecrease69 TRAP-TYPE
	ENTERPRISE	network-device
	VARIABLES	{ vcValue, adminDateAndTime, adminNDTrapSeqNo,
			  vcIndex, vcType }
	DESCRIPTION	"This trap is generated when set
			vcExUpThresholdDecreaseTrapID equal 69 and
			vcValue is less equal the upper threshold minus
			the upper hysteresis after
			vcExceedUpperThresholdIncrease is generated.
			namely, vcValue <= (vcTrapUpperThreshold -
			vcTrapUpperHysteresis)."
	::= 14917

    vcExceedUpperThresholdDecrease70 TRAP-TYPE
	ENTERPRISE	network-device
	VARIABLES	{ vcValue, adminDateAndTime, adminNDTrapSeqNo,
			  vcIndex, vcType }
	DESCRIPTION	"This trap is generated when set
			vcExUpThresholdDecreaseTrapID equal 70 and
			vcValue is less equal the upper threshold minus
			the upper hysteresis after
			vcExceedUpperThresholdIncrease is generated.
			namely, vcValue <= (vcTrapUpperThreshold -
			vcTrapUpperHysteresis)."
	::= 14918

    vcExceedUpperThresholdDecrease71 TRAP-TYPE
	ENTERPRISE	network-device
	VARIABLES	{ vcValue, adminDateAndTime, adminNDTrapSeqNo,
			  vcIndex, vcType }
	DESCRIPTION	"This trap is generated when set
			vcExUpThresholdDecreaseTrapID equal 71 and
			vcValue is less equal the upper threshold minus
			the upper hysteresis after
			vcExceedUpperThresholdIncrease is generated.
			namely, vcValue <= (vcTrapUpperThreshold -
			vcTrapUpperHysteresis)."
	::= 14919

    vcExceedUpperThresholdDecrease72 TRAP-TYPE
	ENTERPRISE	network-device
	VARIABLES	{ vcValue, adminDateAndTime, adminNDTrapSeqNo,
			  vcIndex, vcType }
	DESCRIPTION	"This trap is generated when set
			vcExUpThresholdDecreaseTrapID equal 72 and
			vcValue is less equal the upper threshold minus
			the upper hysteresis after
			vcExceedUpperThresholdIncrease is generated.
			namely, vcValue <= (vcTrapUpperThreshold -
			vcTrapUpperHysteresis)."
	::= 14920

    vcExceedUpperThresholdDecrease73 TRAP-TYPE
	ENTERPRISE	network-device
	VARIABLES	{ vcValue, adminDateAndTime, adminNDTrapSeqNo,
			  vcIndex, vcType }
	DESCRIPTION	"This trap is generated when set
			vcExUpThresholdDecreaseTrapID equal 73 and
			vcValue is less equal the upper threshold minus
			the upper hysteresis after
			vcExceedUpperThresholdIncrease is generated.
			namely, vcValue <= (vcTrapUpperThreshold -
			vcTrapUpperHysteresis)."
	::= 14921

    vcExceedUpperThresholdDecrease74 TRAP-TYPE
	ENTERPRISE	network-device
	VARIABLES	{ vcValue, adminDateAndTime, adminNDTrapSeqNo,
			  vcIndex, vcType }
	DESCRIPTION	"This trap is generated when set
			vcExUpThresholdDecreaseTrapID equal 74 and
			vcValue is less equal the upper threshold minus
			the upper hysteresis after
			vcExceedUpperThresholdIncrease is generated.
			namely, vcValue <= (vcTrapUpperThreshold -
			vcTrapUpperHysteresis)."
	::= 14922

    vcExceedUpperThresholdDecrease75 TRAP-TYPE
	ENTERPRISE	network-device
	VARIABLES	{ vcValue, adminDateAndTime, adminNDTrapSeqNo,
			  vcIndex, vcType }
	DESCRIPTION	"This trap is generated when set
			vcExUpThresholdDecreaseTrapID equal 75 and
			vcValue is less equal the upper threshold minus
			the upper hysteresis after
			vcExceedUpperThresholdIncrease is generated.
			namely, vcValue <= (vcTrapUpperThreshold -
			vcTrapUpperHysteresis)."
	::= 14923

    vcExceedUpperThresholdDecrease76 TRAP-TYPE
	ENTERPRISE	network-device
	VARIABLES	{ vcValue, adminDateAndTime, adminNDTrapSeqNo,
			  vcIndex, vcType }
	DESCRIPTION	"This trap is generated when set
			vcExUpThresholdDecreaseTrapID equal 76 and
			vcValue is less equal the upper threshold minus
			the upper hysteresis after
			vcExceedUpperThresholdIncrease is generated.
			namely, vcValue <= (vcTrapUpperThreshold -
			vcTrapUpperHysteresis)."
	::= 14924

    vcExceedUpperThresholdDecrease77 TRAP-TYPE
	ENTERPRISE	network-device
	VARIABLES	{ vcValue, adminDateAndTime, adminNDTrapSeqNo,
			  vcIndex, vcType }
	DESCRIPTION	"This trap is generated when set
			vcExUpThresholdDecreaseTrapID equal 77 and
			vcValue is less equal the upper threshold minus
			the upper hysteresis after
			vcExceedUpperThresholdIncrease is generated.
			namely, vcValue <= (vcTrapUpperThreshold -
			vcTrapUpperHysteresis)."
	::= 14925

    vcExceedUpperThresholdDecrease78 TRAP-TYPE
	ENTERPRISE	network-device
	VARIABLES	{ vcValue, adminDateAndTime, adminNDTrapSeqNo,
			  vcIndex, vcType }
	DESCRIPTION	"This trap is generated when set
			vcExUpThresholdDecreaseTrapID equal 78 and
			vcValue is less equal the upper threshold minus
			the upper hysteresis after
			vcExceedUpperThresholdIncrease is generated.
			namely, vcValue <= (vcTrapUpperThreshold -
			vcTrapUpperHysteresis)."
	::= 14926

    vcExceedUpperThresholdDecrease79 TRAP-TYPE
	ENTERPRISE	network-device
	VARIABLES	{ vcValue, adminDateAndTime, adminNDTrapSeqNo,
			  vcIndex, vcType }
	DESCRIPTION	"This trap is generated when set
			vcExUpThresholdDecreaseTrapID equal 79 and
			vcValue is less equal the upper threshold minus
			the upper hysteresis after
			vcExceedUpperThresholdIncrease is generated.
			namely, vcValue <= (vcTrapUpperThreshold -
			vcTrapUpperHysteresis)."
	::= 14927

    vcExceedUpperThresholdDecrease80 TRAP-TYPE
	ENTERPRISE	network-device
	VARIABLES	{ vcValue, adminDateAndTime, adminNDTrapSeqNo,
			  vcIndex, vcType }
	DESCRIPTION	"This trap is generated when set
			vcExUpThresholdDecreaseTrapID equal 80 and
			vcValue is less equal the upper threshold minus
			the upper hysteresis after
			vcExceedUpperThresholdIncrease is generated.
			namely, vcValue <= (vcTrapUpperThreshold -
			vcTrapUpperHysteresis)."
	::= 14928

    vcExceedUpperThresholdDecrease81 TRAP-TYPE
	ENTERPRISE	network-device
	VARIABLES	{ vcValue, adminDateAndTime, adminNDTrapSeqNo,
			  vcIndex, vcType }
	DESCRIPTION	"This trap is generated when set
			vcExUpThresholdDecreaseTrapID equal 81 and
			vcValue is less equal the upper threshold minus
			the upper hysteresis after
			vcExceedUpperThresholdIncrease is generated.
			namely, vcValue <= (vcTrapUpperThreshold -
			vcTrapUpperHysteresis)."
	::= 14929

    vcExceedUpperThresholdDecrease82 TRAP-TYPE
	ENTERPRISE	network-device
	VARIABLES	{ vcValue, adminDateAndTime, adminNDTrapSeqNo,
			  vcIndex, vcType }
	DESCRIPTION	"This trap is generated when set
			vcExUpThresholdDecreaseTrapID equal 82 and
			vcValue is less equal the upper threshold minus
			the upper hysteresis after
			vcExceedUpperThresholdIncrease is generated.
			namely, vcValue <= (vcTrapUpperThreshold -
			vcTrapUpperHysteresis)."
	::= 14930

    vcExceedUpperThresholdDecrease83 TRAP-TYPE
	ENTERPRISE	network-device
	VARIABLES	{ vcValue, adminDateAndTime, adminNDTrapSeqNo,
			  vcIndex, vcType }
	DESCRIPTION	"This trap is generated when set
			vcExUpThresholdDecreaseTrapID equal 83 and
			vcValue is less equal the upper threshold minus
			the upper hysteresis after
			vcExceedUpperThresholdIncrease is generated.
			namely, vcValue <= (vcTrapUpperThreshold -
			vcTrapUpperHysteresis)."
	::= 14931

    vcExceedUpperThresholdDecrease84 TRAP-TYPE
	ENTERPRISE	network-device
	VARIABLES	{ vcValue, adminDateAndTime, adminNDTrapSeqNo,
			  vcIndex, vcType }
	DESCRIPTION	"This trap is generated when set
			vcExUpThresholdDecreaseTrapID equal 84 and
			vcValue is less equal the upper threshold minus
			the upper hysteresis after
			vcExceedUpperThresholdIncrease is generated.
			namely, vcValue <= (vcTrapUpperThreshold -
			vcTrapUpperHysteresis)."
	::= 14932

    vcExceedUpperThresholdDecrease85 TRAP-TYPE
	ENTERPRISE	network-device
	VARIABLES	{ vcValue, adminDateAndTime, adminNDTrapSeqNo,
			  vcIndex, vcType }
	DESCRIPTION	"This trap is generated when set
			vcExUpThresholdDecreaseTrapID equal 85 and
			vcValue is less equal the upper threshold minus
			the upper hysteresis after
			vcExceedUpperThresholdIncrease is generated.
			namely, vcValue <= (vcTrapUpperThreshold -
			vcTrapUpperHysteresis)."
	::= 14933

    vcExceedUpperThresholdDecrease86 TRAP-TYPE
	ENTERPRISE	network-device
	VARIABLES	{ vcValue, adminDateAndTime, adminNDTrapSeqNo,
			  vcIndex, vcType }
	DESCRIPTION	"This trap is generated when set
			vcExUpThresholdDecreaseTrapID equal 86 and
			vcValue is less equal the upper threshold minus
			the upper hysteresis after
			vcExceedUpperThresholdIncrease is generated.
			namely, vcValue <= (vcTrapUpperThreshold -
			vcTrapUpperHysteresis)."
	::= 14934

    vcExceedUpperThresholdDecrease87 TRAP-TYPE
	ENTERPRISE	network-device
	VARIABLES	{ vcValue, adminDateAndTime, adminNDTrapSeqNo,
			  vcIndex, vcType }
	DESCRIPTION	"This trap is generated when set
			vcExUpThresholdDecreaseTrapID equal 87 and
			vcValue is less equal the upper threshold minus
			the upper hysteresis after
			vcExceedUpperThresholdIncrease is generated.
			namely, vcValue <= (vcTrapUpperThreshold -
			vcTrapUpperHysteresis)."
	::= 14935

    vcExceedUpperThresholdDecrease88 TRAP-TYPE
	ENTERPRISE	network-device
	VARIABLES	{ vcValue, adminDateAndTime, adminNDTrapSeqNo,
			  vcIndex, vcType }
	DESCRIPTION	"This trap is generated when set
			vcExUpThresholdDecreaseTrapID equal 88 and
			vcValue is less equal the upper threshold minus
			the upper hysteresis after
			vcExceedUpperThresholdIncrease is generated.
			namely, vcValue <= (vcTrapUpperThreshold -
			vcTrapUpperHysteresis)."
	::= 14936

    vcExceedUpperThresholdDecrease89 TRAP-TYPE
	ENTERPRISE	network-device
	VARIABLES	{ vcValue, adminDateAndTime, adminNDTrapSeqNo,
			  vcIndex, vcType }
	DESCRIPTION	"This trap is generated when set
			vcExUpThresholdDecreaseTrapID equal 89 and
			vcValue is less equal the upper threshold minus
			the upper hysteresis after
			vcExceedUpperThresholdIncrease is generated.
			namely, vcValue <= (vcTrapUpperThreshold -
			vcTrapUpperHysteresis)."
	::= 14937

    vcExceedUpperThresholdDecrease90 TRAP-TYPE
	ENTERPRISE	network-device
	VARIABLES	{ vcValue, adminDateAndTime, adminNDTrapSeqNo,
			  vcIndex, vcType }
	DESCRIPTION	"This trap is generated when set
			vcExUpThresholdDecreaseTrapID equal 90 and
			vcValue is less equal the upper threshold minus
			the upper hysteresis after
			vcExceedUpperThresholdIncrease is generated.
			namely, vcValue <= (vcTrapUpperThreshold -
			vcTrapUpperHysteresis)."
	::= 14938

    vcExceedUpperThresholdDecrease91 TRAP-TYPE
	ENTERPRISE	network-device
	VARIABLES	{ vcValue, adminDateAndTime, adminNDTrapSeqNo,
			  vcIndex, vcType }
	DESCRIPTION	"This trap is generated when set
			vcExUpThresholdDecreaseTrapID equal 91 and
			vcValue is less equal the upper threshold minus
			the upper hysteresis after
			vcExceedUpperThresholdIncrease is generated.
			namely, vcValue <= (vcTrapUpperThreshold -
			vcTrapUpperHysteresis)."
	::= 14939

    vcExceedUpperThresholdDecrease92 TRAP-TYPE
	ENTERPRISE	network-device
	VARIABLES	{ vcValue, adminDateAndTime, adminNDTrapSeqNo,
			  vcIndex, vcType }
	DESCRIPTION	"This trap is generated when set
			vcExUpThresholdDecreaseTrapID equal 92 and
			vcValue is less equal the upper threshold minus
			the upper hysteresis after
			vcExceedUpperThresholdIncrease is generated.
			namely, vcValue <= (vcTrapUpperThreshold -
			vcTrapUpperHysteresis)."
	::= 14940

    vcExceedUpperThresholdDecrease93 TRAP-TYPE
	ENTERPRISE	network-device
	VARIABLES	{ vcValue, adminDateAndTime, adminNDTrapSeqNo,
			  vcIndex, vcType }
	DESCRIPTION	"This trap is generated when set
			vcExUpThresholdDecreaseTrapID equal 93 and
			vcValue is less equal the upper threshold minus
			the upper hysteresis after
			vcExceedUpperThresholdIncrease is generated.
			namely, vcValue <= (vcTrapUpperThreshold -
			vcTrapUpperHysteresis)."
	::= 14941

    vcExceedUpperThresholdDecrease94 TRAP-TYPE
	ENTERPRISE	network-device
	VARIABLES	{ vcValue, adminDateAndTime, adminNDTrapSeqNo,
			  vcIndex, vcType }
	DESCRIPTION	"This trap is generated when set
			vcExUpThresholdDecreaseTrapID equal 94 and
			vcValue is less equal the upper threshold minus
			the upper hysteresis after
			vcExceedUpperThresholdIncrease is generated.
			namely, vcValue <= (vcTrapUpperThreshold -
			vcTrapUpperHysteresis)."
	::= 14942

    vcExceedUpperThresholdDecrease95 TRAP-TYPE
	ENTERPRISE	network-device
	VARIABLES	{ vcValue, adminDateAndTime, adminNDTrapSeqNo,
			  vcIndex, vcType }
	DESCRIPTION	"This trap is generated when set
			vcExUpThresholdDecreaseTrapID equal 95 and
			vcValue is less equal the upper threshold minus
			the upper hysteresis after
			vcExceedUpperThresholdIncrease is generated.
			namely, vcValue <= (vcTrapUpperThreshold -
			vcTrapUpperHysteresis)."
	::= 14943

    vcExceedUpperThresholdDecrease96 TRAP-TYPE
	ENTERPRISE	network-device
	VARIABLES	{ vcValue, adminDateAndTime, adminNDTrapSeqNo,
			  vcIndex, vcType }
	DESCRIPTION	"This trap is generated when set
			vcExUpThresholdDecreaseTrapID equal 96 and
			vcValue is less equal the upper threshold minus
			the upper hysteresis after
			vcExceedUpperThresholdIncrease is generated.
			namely, vcValue <= (vcTrapUpperThreshold -
			vcTrapUpperHysteresis)."
	::= 14944

    vcExceedUpperThresholdDecrease97 TRAP-TYPE
	ENTERPRISE	network-device
	VARIABLES	{ vcValue, adminDateAndTime, adminNDTrapSeqNo,
			  vcIndex, vcType }
	DESCRIPTION	"This trap is generated when set
			vcExUpThresholdDecreaseTrapID equal 97 and
			vcValue is less equal the upper threshold minus
			the upper hysteresis after
			vcExceedUpperThresholdIncrease is generated.
			namely, vcValue <= (vcTrapUpperThreshold -
			vcTrapUpperHysteresis)."
	::= 14945

    vcExceedUpperThresholdDecrease98 TRAP-TYPE
	ENTERPRISE	network-device
	VARIABLES	{ vcValue, adminDateAndTime, adminNDTrapSeqNo,
			  vcIndex, vcType }
	DESCRIPTION	"This trap is generated when set
			vcExUpThresholdDecreaseTrapID equal 98 and
			vcValue is less equal the upper threshold minus
			the upper hysteresis after
			vcExceedUpperThresholdIncrease is generated.
			namely, vcValue <= (vcTrapUpperThreshold -
			vcTrapUpperHysteresis)."
	::= 14946

    vcExceedUpperThresholdDecrease99 TRAP-TYPE
	ENTERPRISE	network-device
	VARIABLES	{ vcValue, adminDateAndTime, adminNDTrapSeqNo,
			  vcIndex, vcType }
	DESCRIPTION	"This trap is generated when set
			vcExUpThresholdDecreaseTrapID equal 99 and
			vcValue is less equal the upper threshold minus
			the upper hysteresis after
			vcExceedUpperThresholdIncrease is generated.
			namely, vcValue <= (vcTrapUpperThreshold -
			vcTrapUpperHysteresis)."
	::= 14947

    vcExceedUpperThresholdDecrease100 TRAP-TYPE
	ENTERPRISE	network-device
	VARIABLES	{ vcValue, adminDateAndTime, adminNDTrapSeqNo,
			  vcIndex, vcType }
	DESCRIPTION	"This trap is generated when set
			vcExUpThresholdDecreaseTrapID equal 100 and
			vcValue is less equal the upper threshold minus
			the upper hysteresis after
			vcExceedUpperThresholdIncrease is generated.
			namely, vcValue <= (vcTrapUpperThreshold -
			vcTrapUpperHysteresis)."
	::= 14948

    vcExceedUpperThresholdDecrease101 TRAP-TYPE
	ENTERPRISE	network-device
	VARIABLES	{ vcValue, adminDateAndTime, adminNDTrapSeqNo,
			  vcIndex, vcType }
	DESCRIPTION	"This trap is generated when set
			vcExUpThresholdDecreaseTrapID equal 101 and
			vcValue is less equal the upper threshold minus
			the upper hysteresis after
			vcExceedUpperThresholdIncrease is generated.
			namely, vcValue <= (vcTrapUpperThreshold -
			vcTrapUpperHysteresis)."
	::= 14949

    vcExceedUpperThresholdDecrease102 TRAP-TYPE
	ENTERPRISE	network-device
	VARIABLES	{ vcValue, adminDateAndTime, adminNDTrapSeqNo,
			  vcIndex, vcType }
	DESCRIPTION	"This trap is generated when set
			vcExUpThresholdDecreaseTrapID equal 102 and
			vcValue is less equal the upper threshold minus
			the upper hysteresis after
			vcExceedUpperThresholdIncrease is generated.
			namely, vcValue <= (vcTrapUpperThreshold -
			vcTrapUpperHysteresis)."
	::= 14950

    vcExceedUpperThresholdDecrease103 TRAP-TYPE
	ENTERPRISE	network-device
	VARIABLES	{ vcValue, adminDateAndTime, adminNDTrapSeqNo,
			  vcIndex, vcType }
	DESCRIPTION	"This trap is generated when set
			vcExUpThresholdDecreaseTrapID equal 103 and
			vcValue is less equal the upper threshold minus
			the upper hysteresis after
			vcExceedUpperThresholdIncrease is generated.
			namely, vcValue <= (vcTrapUpperThreshold -
			vcTrapUpperHysteresis)."
	::= 14951

    vcExceedUpperThresholdDecrease104 TRAP-TYPE
	ENTERPRISE	network-device
	VARIABLES	{ vcValue, adminDateAndTime, adminNDTrapSeqNo,
			  vcIndex, vcType }
	DESCRIPTION	"This trap is generated when set
			vcExUpThresholdDecreaseTrapID equal 104 and
			vcValue is less equal the upper threshold minus
			the upper hysteresis after
			vcExceedUpperThresholdIncrease is generated.
			namely, vcValue <= (vcTrapUpperThreshold -
			vcTrapUpperHysteresis)."
	::= 14952

    vcExceedUpperThresholdDecrease105 TRAP-TYPE
	ENTERPRISE	network-device
	VARIABLES	{ vcValue, adminDateAndTime, adminNDTrapSeqNo,
			  vcIndex, vcType }
	DESCRIPTION	"This trap is generated when set
			vcExUpThresholdDecreaseTrapID equal 105 and
			vcValue is less equal the upper threshold minus
			the upper hysteresis after
			vcExceedUpperThresholdIncrease is generated.
			namely, vcValue <= (vcTrapUpperThreshold -
			vcTrapUpperHysteresis)."
	::= 14953

    vcExceedUpperThresholdDecrease106 TRAP-TYPE
	ENTERPRISE	network-device
	VARIABLES	{ vcValue, adminDateAndTime, adminNDTrapSeqNo,
			  vcIndex, vcType }
	DESCRIPTION	"This trap is generated when set
			vcExUpThresholdDecreaseTrapID equal 106 and
			vcValue is less equal the upper threshold minus
			the upper hysteresis after
			vcExceedUpperThresholdIncrease is generated.
			namely, vcValue <= (vcTrapUpperThreshold -
			vcTrapUpperHysteresis)."
	::= 14954

    vcExceedUpperThresholdDecrease107 TRAP-TYPE
	ENTERPRISE	network-device
	VARIABLES	{ vcValue, adminDateAndTime, adminNDTrapSeqNo,
			  vcIndex, vcType }
	DESCRIPTION	"This trap is generated when set
			vcExUpThresholdDecreaseTrapID equal 107 and
			vcValue is less equal the upper threshold minus
			the upper hysteresis after
			vcExceedUpperThresholdIncrease is generated.
			namely, vcValue <= (vcTrapUpperThreshold -
			vcTrapUpperHysteresis)."
	::= 14955

    vcExceedUpperThresholdDecrease108 TRAP-TYPE
	ENTERPRISE	network-device
	VARIABLES	{ vcValue, adminDateAndTime, adminNDTrapSeqNo,
			  vcIndex, vcType }
	DESCRIPTION	"This trap is generated when set
			vcExUpThresholdDecreaseTrapID equal 108 and
			vcValue is less equal the upper threshold minus
			the upper hysteresis after
			vcExceedUpperThresholdIncrease is generated.
			namely, vcValue <= (vcTrapUpperThreshold -
			vcTrapUpperHysteresis)."
	::= 14956

    vcExceedUpperThresholdDecrease109 TRAP-TYPE
	ENTERPRISE	network-device
	VARIABLES	{ vcValue, adminDateAndTime, adminNDTrapSeqNo,
			  vcIndex, vcType }
	DESCRIPTION	"This trap is generated when set
			vcExUpThresholdDecreaseTrapID equal 109 and
			vcValue is less equal the upper threshold minus
			the upper hysteresis after
			vcExceedUpperThresholdIncrease is generated.
			namely, vcValue <= (vcTrapUpperThreshold -
			vcTrapUpperHysteresis)."
	::= 14957

    vcExceedUpperThresholdDecrease110 TRAP-TYPE
	ENTERPRISE	network-device
	VARIABLES	{ vcValue, adminDateAndTime, adminNDTrapSeqNo,
			  vcIndex, vcType }
	DESCRIPTION	"This trap is generated when set
			vcExUpThresholdDecreaseTrapID equal 110 and
			vcValue is less equal the upper threshold minus
			the upper hysteresis after
			vcExceedUpperThresholdIncrease is generated.
			namely, vcValue <= (vcTrapUpperThreshold -
			vcTrapUpperHysteresis)."
	::= 14958

    vcExceedUpperThresholdDecrease111 TRAP-TYPE
	ENTERPRISE	network-device
	VARIABLES	{ vcValue, adminDateAndTime, adminNDTrapSeqNo,
			  vcIndex, vcType }
	DESCRIPTION	"This trap is generated when set
			vcExUpThresholdDecreaseTrapID equal 111 and
			vcValue is less equal the upper threshold minus
			the upper hysteresis after
			vcExceedUpperThresholdIncrease is generated.
			namely, vcValue <= (vcTrapUpperThreshold -
			vcTrapUpperHysteresis)."
	::= 14959

    vcExceedUpperThresholdDecrease112 TRAP-TYPE
	ENTERPRISE	network-device
	VARIABLES	{ vcValue, adminDateAndTime, adminNDTrapSeqNo,
			  vcIndex, vcType }
	DESCRIPTION	"This trap is generated when set
			vcExUpThresholdDecreaseTrapID equal 112 and
			vcValue is less equal the upper threshold minus
			the upper hysteresis after
			vcExceedUpperThresholdIncrease is generated.
			namely, vcValue <= (vcTrapUpperThreshold -
			vcTrapUpperHysteresis)."
	::= 14960

    vcExceedUpperThresholdDecrease113 TRAP-TYPE
	ENTERPRISE	network-device
	VARIABLES	{ vcValue, adminDateAndTime, adminNDTrapSeqNo,
			  vcIndex, vcType }
	DESCRIPTION	"This trap is generated when set
			vcExUpThresholdDecreaseTrapID equal 113 and
			vcValue is less equal the upper threshold minus
			the upper hysteresis after
			vcExceedUpperThresholdIncrease is generated.
			namely, vcValue <= (vcTrapUpperThreshold -
			vcTrapUpperHysteresis)."
	::= 14961

    vcExceedUpperThresholdDecrease114 TRAP-TYPE
	ENTERPRISE	network-device
	VARIABLES	{ vcValue, adminDateAndTime, adminNDTrapSeqNo,
			  vcIndex, vcType }
	DESCRIPTION	"This trap is generated when set
			vcExUpThresholdDecreaseTrapID equal 114 and
			vcValue is less equal the upper threshold minus
			the upper hysteresis after
			vcExceedUpperThresholdIncrease is generated.
			namely, vcValue <= (vcTrapUpperThreshold -
			vcTrapUpperHysteresis)."
	::= 14962

    vcExceedUpperThresholdDecrease115 TRAP-TYPE
	ENTERPRISE	network-device
	VARIABLES	{ vcValue, adminDateAndTime, adminNDTrapSeqNo,
			  vcIndex, vcType }
	DESCRIPTION	"This trap is generated when set
			vcExUpThresholdDecreaseTrapID equal 115 and
			vcValue is less equal the upper threshold minus
			the upper hysteresis after
			vcExceedUpperThresholdIncrease is generated.
			namely, vcValue <= (vcTrapUpperThreshold -
			vcTrapUpperHysteresis)."
	::= 14963

    vcExceedUpperThresholdDecrease116 TRAP-TYPE
	ENTERPRISE	network-device
	VARIABLES	{ vcValue, adminDateAndTime, adminNDTrapSeqNo,
			  vcIndex, vcType }
	DESCRIPTION	"This trap is generated when set
			vcExUpThresholdDecreaseTrapID equal 116 and
			vcValue is less equal the upper threshold minus
			the upper hysteresis after
			vcExceedUpperThresholdIncrease is generated.
			namely, vcValue <= (vcTrapUpperThreshold -
			vcTrapUpperHysteresis)."
	::= 14964

    vcExceedUpperThresholdDecrease117 TRAP-TYPE
	ENTERPRISE	network-device
	VARIABLES	{ vcValue, adminDateAndTime, adminNDTrapSeqNo,
			  vcIndex, vcType }
	DESCRIPTION	"This trap is generated when set
			vcExUpThresholdDecreaseTrapID equal 117 and
			vcValue is less equal the upper threshold minus
			the upper hysteresis after
			vcExceedUpperThresholdIncrease is generated.
			namely, vcValue <= (vcTrapUpperThreshold -
			vcTrapUpperHysteresis)."
	::= 14965

    vcExceedUpperThresholdDecrease118 TRAP-TYPE
	ENTERPRISE	network-device
	VARIABLES	{ vcValue, adminDateAndTime, adminNDTrapSeqNo,
			  vcIndex, vcType }
	DESCRIPTION	"This trap is generated when set
			vcExUpThresholdDecreaseTrapID equal 118 and
			vcValue is less equal the upper threshold minus
			the upper hysteresis after
			vcExceedUpperThresholdIncrease is generated.
			namely, vcValue <= (vcTrapUpperThreshold -
			vcTrapUpperHysteresis)."
	::= 14966

    vcExceedUpperThresholdDecrease119 TRAP-TYPE
	ENTERPRISE	network-device
	VARIABLES	{ vcValue, adminDateAndTime, adminNDTrapSeqNo,
			  vcIndex, vcType }
	DESCRIPTION	"This trap is generated when set
			vcExUpThresholdDecreaseTrapID equal 119 and
			vcValue is less equal the upper threshold minus
			the upper hysteresis after
			vcExceedUpperThresholdIncrease is generated.
			namely, vcValue <= (vcTrapUpperThreshold -
			vcTrapUpperHysteresis)."
	::= 14967

    vcExceedUpperThresholdDecrease120 TRAP-TYPE
	ENTERPRISE	network-device
	VARIABLES	{ vcValue, adminDateAndTime, adminNDTrapSeqNo,
			  vcIndex, vcType }
	DESCRIPTION	"This trap is generated when set
			vcExUpThresholdDecreaseTrapID equal 120 and
			vcValue is less equal the upper threshold minus
			the upper hysteresis after
			vcExceedUpperThresholdIncrease is generated.
			namely, vcValue <= (vcTrapUpperThreshold -
			vcTrapUpperHysteresis)."
	::= 14968

    vcExceedUpperThresholdDecrease121 TRAP-TYPE
	ENTERPRISE	network-device
	VARIABLES	{ vcValue, adminDateAndTime, adminNDTrapSeqNo,
			  vcIndex, vcType }
	DESCRIPTION	"This trap is generated when set
			vcExUpThresholdDecreaseTrapID equal 121 and
			vcValue is less equal the upper threshold minus
			the upper hysteresis after
			vcExceedUpperThresholdIncrease is generated.
			namely, vcValue <= (vcTrapUpperThreshold -
			vcTrapUpperHysteresis)."
	::= 14969

    vcExceedUpperThresholdDecrease122 TRAP-TYPE
	ENTERPRISE	network-device
	VARIABLES	{ vcValue, adminDateAndTime, adminNDTrapSeqNo,
			  vcIndex, vcType }
	DESCRIPTION	"This trap is generated when set
			vcExUpThresholdDecreaseTrapID equal 122 and
			vcValue is less equal the upper threshold minus
			the upper hysteresis after
			vcExceedUpperThresholdIncrease is generated.
			namely, vcValue <= (vcTrapUpperThreshold -
			vcTrapUpperHysteresis)."
	::= 14970

    vcExceedUpperThresholdDecrease123 TRAP-TYPE
	ENTERPRISE	network-device
	VARIABLES	{ vcValue, adminDateAndTime, adminNDTrapSeqNo,
			  vcIndex, vcType }
	DESCRIPTION	"This trap is generated when set
			vcExUpThresholdDecreaseTrapID equal 123 and
			vcValue is less equal the upper threshold minus
			the upper hysteresis after
			vcExceedUpperThresholdIncrease is generated.
			namely, vcValue <= (vcTrapUpperThreshold -
			vcTrapUpperHysteresis)."
	::= 14971

    vcExceedUpperThresholdDecrease124 TRAP-TYPE
	ENTERPRISE	network-device
	VARIABLES	{ vcValue, adminDateAndTime, adminNDTrapSeqNo,
			  vcIndex, vcType }
	DESCRIPTION	"This trap is generated when set
			vcExUpThresholdDecreaseTrapID equal 124 and
			vcValue is less equal the upper threshold minus
			the upper hysteresis after
			vcExceedUpperThresholdIncrease is generated.
			namely, vcValue <= (vcTrapUpperThreshold -
			vcTrapUpperHysteresis)."
	::= 14972

    vcExceedUpperThresholdDecrease125 TRAP-TYPE
	ENTERPRISE	network-device
	VARIABLES	{ vcValue, adminDateAndTime, adminNDTrapSeqNo,
			  vcIndex, vcType }
	DESCRIPTION	"This trap is generated when set
			vcExUpThresholdDecreaseTrapID equal 125 and
			vcValue is less equal the upper threshold minus
			the upper hysteresis after
			vcExceedUpperThresholdIncrease is generated.
			namely, vcValue <= (vcTrapUpperThreshold -
			vcTrapUpperHysteresis)."
	::= 14973

    vcExceedUpperThresholdDecrease126 TRAP-TYPE
	ENTERPRISE	network-device
	VARIABLES	{ vcValue, adminDateAndTime, adminNDTrapSeqNo,
			  vcIndex, vcType }
	DESCRIPTION	"This trap is generated when set
			vcExUpThresholdDecreaseTrapID equal 126 and
			vcValue is less equal the upper threshold minus
			the upper hysteresis after
			vcExceedUpperThresholdIncrease is generated.
			namely, vcValue <= (vcTrapUpperThreshold -
			vcTrapUpperHysteresis)."
	::= 14974

    vcExceedUpperThresholdDecrease127 TRAP-TYPE
	ENTERPRISE	network-device
	VARIABLES	{ vcValue, adminDateAndTime, adminNDTrapSeqNo,
			  vcIndex, vcType }
	DESCRIPTION	"This trap is generated when set
			vcExUpThresholdDecreaseTrapID equal 127 and
			vcValue is less equal the upper threshold minus
			the upper hysteresis after
			vcExceedUpperThresholdIncrease is generated.
			namely, vcValue <= (vcTrapUpperThreshold -
			vcTrapUpperHysteresis)."
	::= 14975

    vcExceedingUpperThreshold1 TRAP-TYPE
	ENTERPRISE	network-device
	VARIABLES	{ vcValue, adminDateAndTime, adminNDTrapSeqNo,
			  vcIndex, vcType }
	DESCRIPTION	"This trap is generated when set
			vcExUpThresholdTrapID equal 1 and
			until vcExceedUpperThresholdDecrease is generated after
			vcExceedUpperThresholdIncrease is generated."
	::= 15361

    vcExceedingUpperThreshold2 TRAP-TYPE
	ENTERPRISE	network-device
	VARIABLES	{ vcValue, adminDateAndTime, adminNDTrapSeqNo,
			  vcIndex, vcType }
	DESCRIPTION	"This trap is generated when set
			vcExUpThresholdTrapID equal 2 and
			until vcExceedUpperThresholdDecrease is generated after
			vcExceedUpperThresholdIncrease is generated."
	::= 15362

    vcExceedingUpperThreshold3 TRAP-TYPE
	ENTERPRISE	network-device
	VARIABLES	{ vcValue, adminDateAndTime, adminNDTrapSeqNo,
			  vcIndex, vcType }
	DESCRIPTION	"This trap is generated when set
			vcExUpThresholdTrapID equal 3 and
			until vcExceedUpperThresholdDecrease is generated after
			vcExceedUpperThresholdIncrease is generated."
	::= 15363

    vcExceedingUpperThreshold4 TRAP-TYPE
	ENTERPRISE	network-device
	VARIABLES	{ vcValue, adminDateAndTime, adminNDTrapSeqNo,
			  vcIndex, vcType }
	DESCRIPTION	"This trap is generated when set
			vcExUpThresholdTrapID equal 4 and
			until vcExceedUpperThresholdDecrease is generated after
			vcExceedUpperThresholdIncrease is generated."
	::= 15364

    vcExceedingUpperThreshold5 TRAP-TYPE
	ENTERPRISE	network-device
	VARIABLES	{ vcValue, adminDateAndTime, adminNDTrapSeqNo,
			  vcIndex, vcType }
	DESCRIPTION	"This trap is generated when set
			vcExUpThresholdTrapID equal 5 and
			until vcExceedUpperThresholdDecrease is generated after
			vcExceedUpperThresholdIncrease is generated."
	::= 15365

    vcExceedingUpperThreshold6 TRAP-TYPE
	ENTERPRISE	network-device
	VARIABLES	{ vcValue, adminDateAndTime, adminNDTrapSeqNo,
			  vcIndex, vcType }
	DESCRIPTION	"This trap is generated when set
			vcExUpThresholdTrapID equal 6 and
			until vcExceedUpperThresholdDecrease is generated after
			vcExceedUpperThresholdIncrease is generated."
	::= 15366

    vcExceedingUpperThreshold7 TRAP-TYPE
	ENTERPRISE	network-device
	VARIABLES	{ vcValue, adminDateAndTime, adminNDTrapSeqNo,
			  vcIndex, vcType }
	DESCRIPTION	"This trap is generated when set
			vcExUpThresholdTrapID equal 7 and
			until vcExceedUpperThresholdDecrease is generated after
			vcExceedUpperThresholdIncrease is generated."
	::= 15367

    vcExceedingUpperThreshold8 TRAP-TYPE
	ENTERPRISE	network-device
	VARIABLES	{ vcValue, adminDateAndTime, adminNDTrapSeqNo,
			  vcIndex, vcType }
	DESCRIPTION	"This trap is generated when set
			vcExUpThresholdTrapID equal 8 and
			until vcExceedUpperThresholdDecrease is generated after
			vcExceedUpperThresholdIncrease is generated."
	::= 15368

    vcExceedingUpperThreshold9 TRAP-TYPE
	ENTERPRISE	network-device
	VARIABLES	{ vcValue, adminDateAndTime, adminNDTrapSeqNo,
			  vcIndex, vcType }
	DESCRIPTION	"This trap is generated when set
			vcExUpThresholdTrapID equal 9 and
			until vcExceedUpperThresholdDecrease is generated after
			vcExceedUpperThresholdIncrease is generated."
	::= 15369

    vcExceedingUpperThreshold10 TRAP-TYPE
	ENTERPRISE	network-device
	VARIABLES	{ vcValue, adminDateAndTime, adminNDTrapSeqNo,
			  vcIndex, vcType }
	DESCRIPTION	"This trap is generated when set
			vcExUpThresholdTrapID equal 10 and
			until vcExceedUpperThresholdDecrease is generated after
			vcExceedUpperThresholdIncrease is generated."
	::= 15370

    vcExceedingUpperThreshold11 TRAP-TYPE
	ENTERPRISE	network-device
	VARIABLES	{ vcValue, adminDateAndTime, adminNDTrapSeqNo,
			  vcIndex, vcType }
	DESCRIPTION	"This trap is generated when set
			vcExUpThresholdTrapID equal 11 and
			until vcExceedUpperThresholdDecrease is generated after
			vcExceedUpperThresholdIncrease is generated."
	::= 15371

    vcExceedingUpperThreshold12 TRAP-TYPE
	ENTERPRISE	network-device
	VARIABLES	{ vcValue, adminDateAndTime, adminNDTrapSeqNo,
			  vcIndex, vcType }
	DESCRIPTION	"This trap is generated when set
			vcExUpThresholdTrapID equal 12 and
			until vcExceedUpperThresholdDecrease is generated after
			vcExceedUpperThresholdIncrease is generated."
	::= 15372

    vcExceedingUpperThreshold13 TRAP-TYPE
	ENTERPRISE	network-device
	VARIABLES	{ vcValue, adminDateAndTime, adminNDTrapSeqNo,
			  vcIndex, vcType }
	DESCRIPTION	"This trap is generated when set
			vcExUpThresholdTrapID equal 13 and
			until vcExceedUpperThresholdDecrease is generated after
			vcExceedUpperThresholdIncrease is generated."
	::= 15373

    vcExceedingUpperThreshold14 TRAP-TYPE
	ENTERPRISE	network-device
	VARIABLES	{ vcValue, adminDateAndTime, adminNDTrapSeqNo,
			  vcIndex, vcType }
	DESCRIPTION	"This trap is generated when set
			vcExUpThresholdTrapID equal 14 and
			until vcExceedUpperThresholdDecrease is generated after
			vcExceedUpperThresholdIncrease is generated."
	::= 15374

    vcExceedingUpperThreshold15 TRAP-TYPE
	ENTERPRISE	network-device
	VARIABLES	{ vcValue, adminDateAndTime, adminNDTrapSeqNo,
			  vcIndex, vcType }
	DESCRIPTION	"This trap is generated when set
			vcExUpThresholdTrapID equal 15 and
			until vcExceedUpperThresholdDecrease is generated after
			vcExceedUpperThresholdIncrease is generated."
	::= 15375

    vcExceedingUpperThreshold16 TRAP-TYPE
	ENTERPRISE	network-device
	VARIABLES	{ vcValue, adminDateAndTime, adminNDTrapSeqNo,
			  vcIndex, vcType }
	DESCRIPTION	"This trap is generated when set
			vcExUpThresholdTrapID equal 16 and
			until vcExceedUpperThresholdDecrease is generated after
			vcExceedUpperThresholdIncrease is generated."
	::= 15376

    vcExceedingUpperThreshold17 TRAP-TYPE
	ENTERPRISE	network-device
	VARIABLES	{ vcValue, adminDateAndTime, adminNDTrapSeqNo,
			  vcIndex, vcType }
	DESCRIPTION	"This trap is generated when set
			vcExUpThresholdTrapID equal 17 and
			until vcExceedUpperThresholdDecrease is generated after
			vcExceedUpperThresholdIncrease is generated."
	::= 15377

    vcExceedingUpperThreshold18 TRAP-TYPE
	ENTERPRISE	network-device
	VARIABLES	{ vcValue, adminDateAndTime, adminNDTrapSeqNo,
			  vcIndex, vcType }
	DESCRIPTION	"This trap is generated when set
			vcExUpThresholdTrapID equal 18 and
			until vcExceedUpperThresholdDecrease is generated after
			vcExceedUpperThresholdIncrease is generated."
	::= 15378

    vcExceedingUpperThreshold19 TRAP-TYPE
	ENTERPRISE	network-device
	VARIABLES	{ vcValue, adminDateAndTime, adminNDTrapSeqNo,
			  vcIndex, vcType }
	DESCRIPTION	"This trap is generated when set
			vcExUpThresholdTrapID equal 19 and
			until vcExceedUpperThresholdDecrease is generated after
			vcExceedUpperThresholdIncrease is generated."
	::= 15379

    vcExceedingUpperThreshold20 TRAP-TYPE
	ENTERPRISE	network-device
	VARIABLES	{ vcValue, adminDateAndTime, adminNDTrapSeqNo,
			  vcIndex, vcType }
	DESCRIPTION	"This trap is generated when set
			vcExUpThresholdTrapID equal 20 and
			until vcExceedUpperThresholdDecrease is generated after
			vcExceedUpperThresholdIncrease is generated."
	::= 15380

    vcExceedingUpperThreshold21 TRAP-TYPE
	ENTERPRISE	network-device
	VARIABLES	{ vcValue, adminDateAndTime, adminNDTrapSeqNo,
			  vcIndex, vcType }
	DESCRIPTION	"This trap is generated when set
			vcExUpThresholdTrapID equal 21 and
			until vcExceedUpperThresholdDecrease is generated after
			vcExceedUpperThresholdIncrease is generated."
	::= 15381

    vcExceedingUpperThreshold22 TRAP-TYPE
	ENTERPRISE	network-device
	VARIABLES	{ vcValue, adminDateAndTime, adminNDTrapSeqNo,
			  vcIndex, vcType }
	DESCRIPTION	"This trap is generated when set
			vcExUpThresholdTrapID equal 22 and
			until vcExceedUpperThresholdDecrease is generated after
			vcExceedUpperThresholdIncrease is generated."
	::= 15382

    vcExceedingUpperThreshold23 TRAP-TYPE
	ENTERPRISE	network-device
	VARIABLES	{ vcValue, adminDateAndTime, adminNDTrapSeqNo,
			  vcIndex, vcType }
	DESCRIPTION	"This trap is generated when set
			vcExUpThresholdTrapID equal 23 and
			until vcExceedUpperThresholdDecrease is generated after
			vcExceedUpperThresholdIncrease is generated."
	::= 15383

    vcExceedingUpperThreshold24 TRAP-TYPE
	ENTERPRISE	network-device
	VARIABLES	{ vcValue, adminDateAndTime, adminNDTrapSeqNo,
			  vcIndex, vcType }
	DESCRIPTION	"This trap is generated when set
			vcExUpThresholdTrapID equal 24 and
			until vcExceedUpperThresholdDecrease is generated after
			vcExceedUpperThresholdIncrease is generated."
	::= 15384

    vcExceedingUpperThreshold25 TRAP-TYPE
	ENTERPRISE	network-device
	VARIABLES	{ vcValue, adminDateAndTime, adminNDTrapSeqNo,
			  vcIndex, vcType }
	DESCRIPTION	"This trap is generated when set
			vcExUpThresholdTrapID equal 25 and
			until vcExceedUpperThresholdDecrease is generated after
			vcExceedUpperThresholdIncrease is generated."
	::= 15385

    vcExceedingUpperThreshold26 TRAP-TYPE
	ENTERPRISE	network-device
	VARIABLES	{ vcValue, adminDateAndTime, adminNDTrapSeqNo,
			  vcIndex, vcType }
	DESCRIPTION	"This trap is generated when set
			vcExUpThresholdTrapID equal 26 and
			until vcExceedUpperThresholdDecrease is generated after
			vcExceedUpperThresholdIncrease is generated."
	::= 15386

    vcExceedingUpperThreshold27 TRAP-TYPE
	ENTERPRISE	network-device
	VARIABLES	{ vcValue, adminDateAndTime, adminNDTrapSeqNo,
			  vcIndex, vcType }
	DESCRIPTION	"This trap is generated when set
			vcExUpThresholdTrapID equal 27 and
			until vcExceedUpperThresholdDecrease is generated after
			vcExceedUpperThresholdIncrease is generated."
	::= 15387

    vcExceedingUpperThreshold28 TRAP-TYPE
	ENTERPRISE	network-device
	VARIABLES	{ vcValue, adminDateAndTime, adminNDTrapSeqNo,
			  vcIndex, vcType }
	DESCRIPTION	"This trap is generated when set
			vcExUpThresholdTrapID equal 28 and
			until vcExceedUpperThresholdDecrease is generated after
			vcExceedUpperThresholdIncrease is generated."
	::= 15388

    vcExceedingUpperThreshold29 TRAP-TYPE
	ENTERPRISE	network-device
	VARIABLES	{ vcValue, adminDateAndTime, adminNDTrapSeqNo,
			  vcIndex, vcType }
	DESCRIPTION	"This trap is generated when set
			vcExUpThresholdTrapID equal 29 and
			until vcExceedUpperThresholdDecrease is generated after
			vcExceedUpperThresholdIncrease is generated."
	::= 15389

    vcExceedingUpperThreshold30 TRAP-TYPE
	ENTERPRISE	network-device
	VARIABLES	{ vcValue, adminDateAndTime, adminNDTrapSeqNo,
			  vcIndex, vcType }
	DESCRIPTION	"This trap is generated when set
			vcExUpThresholdTrapID equal 30 and
			until vcExceedUpperThresholdDecrease is generated after
			vcExceedUpperThresholdIncrease is generated."
	::= 15390

    vcExceedingUpperThreshold31 TRAP-TYPE
	ENTERPRISE	network-device
	VARIABLES	{ vcValue, adminDateAndTime, adminNDTrapSeqNo,
			  vcIndex, vcType }
	DESCRIPTION	"This trap is generated when set
			vcExUpThresholdTrapID equal 31 and
			until vcExceedUpperThresholdDecrease is generated after
			vcExceedUpperThresholdIncrease is generated."
	::= 15391

    vcExceedingUpperThreshold32 TRAP-TYPE
	ENTERPRISE	network-device
	VARIABLES	{ vcValue, adminDateAndTime, adminNDTrapSeqNo,
			  vcIndex, vcType }
	DESCRIPTION	"This trap is generated when set
			vcExUpThresholdTrapID equal 32 and
			until vcExceedUpperThresholdDecrease is generated after
			vcExceedUpperThresholdIncrease is generated."
	::= 15392

    vcExceedingUpperThreshold33 TRAP-TYPE
	ENTERPRISE	network-device
	VARIABLES	{ vcValue, adminDateAndTime, adminNDTrapSeqNo,
			  vcIndex, vcType }
	DESCRIPTION	"This trap is generated when set
			vcExUpThresholdTrapID equal 33 and
			until vcExceedUpperThresholdDecrease is generated after
			vcExceedUpperThresholdIncrease is generated."
	::= 15393

    vcExceedingUpperThreshold34 TRAP-TYPE
	ENTERPRISE	network-device
	VARIABLES	{ vcValue, adminDateAndTime, adminNDTrapSeqNo,
			  vcIndex, vcType }
	DESCRIPTION	"This trap is generated when set
			vcExUpThresholdTrapID equal 34 and
			until vcExceedUpperThresholdDecrease is generated after
			vcExceedUpperThresholdIncrease is generated."
	::= 15394

    vcExceedingUpperThreshold35 TRAP-TYPE
	ENTERPRISE	network-device
	VARIABLES	{ vcValue, adminDateAndTime, adminNDTrapSeqNo,
			  vcIndex, vcType }
	DESCRIPTION	"This trap is generated when set
			vcExUpThresholdTrapID equal 35 and
			until vcExceedUpperThresholdDecrease is generated after
			vcExceedUpperThresholdIncrease is generated."
	::= 15395

    vcExceedingUpperThreshold36 TRAP-TYPE
	ENTERPRISE	network-device
	VARIABLES	{ vcValue, adminDateAndTime, adminNDTrapSeqNo,
			  vcIndex, vcType }
	DESCRIPTION	"This trap is generated when set
			vcExUpThresholdTrapID equal 36 and
			until vcExceedUpperThresholdDecrease is generated after
			vcExceedUpperThresholdIncrease is generated."
	::= 15396

    vcExceedingUpperThreshold37 TRAP-TYPE
	ENTERPRISE	network-device
	VARIABLES	{ vcValue, adminDateAndTime, adminNDTrapSeqNo,
			  vcIndex, vcType }
	DESCRIPTION	"This trap is generated when set
			vcExUpThresholdTrapID equal 37 and
			until vcExceedUpperThresholdDecrease is generated after
			vcExceedUpperThresholdIncrease is generated."
	::= 15397

    vcExceedingUpperThreshold38 TRAP-TYPE
	ENTERPRISE	network-device
	VARIABLES	{ vcValue, adminDateAndTime, adminNDTrapSeqNo,
			  vcIndex, vcType }
	DESCRIPTION	"This trap is generated when set
			vcExUpThresholdTrapID equal 38 and
			until vcExceedUpperThresholdDecrease is generated after
			vcExceedUpperThresholdIncrease is generated."
	::= 15398

    vcExceedingUpperThreshold39 TRAP-TYPE
	ENTERPRISE	network-device
	VARIABLES	{ vcValue, adminDateAndTime, adminNDTrapSeqNo,
			  vcIndex, vcType }
	DESCRIPTION	"This trap is generated when set
			vcExUpThresholdTrapID equal 39 and
			until vcExceedUpperThresholdDecrease is generated after
			vcExceedUpperThresholdIncrease is generated."
	::= 15399

    vcExceedingUpperThreshold40 TRAP-TYPE
	ENTERPRISE	network-device
	VARIABLES	{ vcValue, adminDateAndTime, adminNDTrapSeqNo,
			  vcIndex, vcType }
	DESCRIPTION	"This trap is generated when set
			vcExUpThresholdTrapID equal 40 and
			until vcExceedUpperThresholdDecrease is generated after
			vcExceedUpperThresholdIncrease is generated."
	::= 15400

    vcExceedingUpperThreshold41 TRAP-TYPE
	ENTERPRISE	network-device
	VARIABLES	{ vcValue, adminDateAndTime, adminNDTrapSeqNo,
			  vcIndex, vcType }
	DESCRIPTION	"This trap is generated when set
			vcExUpThresholdTrapID equal 41 and
			until vcExceedUpperThresholdDecrease is generated after
			vcExceedUpperThresholdIncrease is generated."
	::= 15401

    vcExceedingUpperThreshold42 TRAP-TYPE
	ENTERPRISE	network-device
	VARIABLES	{ vcValue, adminDateAndTime, adminNDTrapSeqNo,
			  vcIndex, vcType }
	DESCRIPTION	"This trap is generated when set
			vcExUpThresholdTrapID equal 42 and
			until vcExceedUpperThresholdDecrease is generated after
			vcExceedUpperThresholdIncrease is generated."
	::= 15402

    vcExceedingUpperThreshold43 TRAP-TYPE
	ENTERPRISE	network-device
	VARIABLES	{ vcValue, adminDateAndTime, adminNDTrapSeqNo,
			  vcIndex, vcType }
	DESCRIPTION	"This trap is generated when set
			vcExUpThresholdTrapID equal 43 and
			until vcExceedUpperThresholdDecrease is generated after
			vcExceedUpperThresholdIncrease is generated."
	::= 15403

    vcExceedingUpperThreshold44 TRAP-TYPE
	ENTERPRISE	network-device
	VARIABLES	{ vcValue, adminDateAndTime, adminNDTrapSeqNo,
			  vcIndex, vcType }
	DESCRIPTION	"This trap is generated when set
			vcExUpThresholdTrapID equal 44 and
			until vcExceedUpperThresholdDecrease is generated after
			vcExceedUpperThresholdIncrease is generated."
	::= 15404

    vcExceedingUpperThreshold45 TRAP-TYPE
	ENTERPRISE	network-device
	VARIABLES	{ vcValue, adminDateAndTime, adminNDTrapSeqNo,
			  vcIndex, vcType }
	DESCRIPTION	"This trap is generated when set
			vcExUpThresholdTrapID equal 45 and
			until vcExceedUpperThresholdDecrease is generated after
			vcExceedUpperThresholdIncrease is generated."
	::= 15405

    vcExceedingUpperThreshold46 TRAP-TYPE
	ENTERPRISE	network-device
	VARIABLES	{ vcValue, adminDateAndTime, adminNDTrapSeqNo,
			  vcIndex, vcType }
	DESCRIPTION	"This trap is generated when set
			vcExUpThresholdTrapID equal 46 and
			until vcExceedUpperThresholdDecrease is generated after
			vcExceedUpperThresholdIncrease is generated."
	::= 15406

    vcExceedingUpperThreshold47 TRAP-TYPE
	ENTERPRISE	network-device
	VARIABLES	{ vcValue, adminDateAndTime, adminNDTrapSeqNo,
			  vcIndex, vcType }
	DESCRIPTION	"This trap is generated when set
			vcExUpThresholdTrapID equal 47 and
			until vcExceedUpperThresholdDecrease is generated after
			vcExceedUpperThresholdIncrease is generated."
	::= 15407

    vcExceedingUpperThreshold48 TRAP-TYPE
	ENTERPRISE	network-device
	VARIABLES	{ vcValue, adminDateAndTime, adminNDTrapSeqNo,
			  vcIndex, vcType }
	DESCRIPTION	"This trap is generated when set
			vcExUpThresholdTrapID equal 48 and
			until vcExceedUpperThresholdDecrease is generated after
			vcExceedUpperThresholdIncrease is generated."
	::= 15408

    vcExceedingUpperThreshold49 TRAP-TYPE
	ENTERPRISE	network-device
	VARIABLES	{ vcValue, adminDateAndTime, adminNDTrapSeqNo,
			  vcIndex, vcType }
	DESCRIPTION	"This trap is generated when set
			vcExUpThresholdTrapID equal 49 and
			until vcExceedUpperThresholdDecrease is generated after
			vcExceedUpperThresholdIncrease is generated."
	::= 15409

    vcExceedingUpperThreshold50 TRAP-TYPE
	ENTERPRISE	network-device
	VARIABLES	{ vcValue, adminDateAndTime, adminNDTrapSeqNo,
			  vcIndex, vcType }
	DESCRIPTION	"This trap is generated when set
			vcExUpThresholdTrapID equal 50 and
			until vcExceedUpperThresholdDecrease is generated after
			vcExceedUpperThresholdIncrease is generated."
	::= 15410

    vcExceedingUpperThreshold51 TRAP-TYPE
	ENTERPRISE	network-device
	VARIABLES	{ vcValue, adminDateAndTime, adminNDTrapSeqNo,
			  vcIndex, vcType }
	DESCRIPTION	"This trap is generated when set
			vcExUpThresholdTrapID equal 51 and
			until vcExceedUpperThresholdDecrease is generated after
			vcExceedUpperThresholdIncrease is generated."
	::= 15411

    vcExceedingUpperThreshold52 TRAP-TYPE
	ENTERPRISE	network-device
	VARIABLES	{ vcValue, adminDateAndTime, adminNDTrapSeqNo,
			  vcIndex, vcType }
	DESCRIPTION	"This trap is generated when set
			vcExUpThresholdTrapID equal 52 and
			until vcExceedUpperThresholdDecrease is generated after
			vcExceedUpperThresholdIncrease is generated."
	::= 15412

    vcExceedingUpperThreshold53 TRAP-TYPE
	ENTERPRISE	network-device
	VARIABLES	{ vcValue, adminDateAndTime, adminNDTrapSeqNo,
			  vcIndex, vcType }
	DESCRIPTION	"This trap is generated when set
			vcExUpThresholdTrapID equal 53 and
			until vcExceedUpperThresholdDecrease is generated after
			vcExceedUpperThresholdIncrease is generated."
	::= 15413

    vcExceedingUpperThreshold54 TRAP-TYPE
	ENTERPRISE	network-device
	VARIABLES	{ vcValue, adminDateAndTime, adminNDTrapSeqNo,
			  vcIndex, vcType }
	DESCRIPTION	"This trap is generated when set
			vcExUpThresholdTrapID equal 54 and
			until vcExceedUpperThresholdDecrease is generated after
			vcExceedUpperThresholdIncrease is generated."
	::= 15414

    vcExceedingUpperThreshold55 TRAP-TYPE
	ENTERPRISE	network-device
	VARIABLES	{ vcValue, adminDateAndTime, adminNDTrapSeqNo,
			  vcIndex, vcType }
	DESCRIPTION	"This trap is generated when set
			vcExUpThresholdTrapID equal 55 and
			until vcExceedUpperThresholdDecrease is generated after
			vcExceedUpperThresholdIncrease is generated."
	::= 15415

    vcExceedingUpperThreshold56 TRAP-TYPE
	ENTERPRISE	network-device
	VARIABLES	{ vcValue, adminDateAndTime, adminNDTrapSeqNo,
			  vcIndex, vcType }
	DESCRIPTION	"This trap is generated when set
			vcExUpThresholdTrapID equal 56 and
			until vcExceedUpperThresholdDecrease is generated after
			vcExceedUpperThresholdIncrease is generated."
	::= 15416

    vcExceedingUpperThreshold57 TRAP-TYPE
	ENTERPRISE	network-device
	VARIABLES	{ vcValue, adminDateAndTime, adminNDTrapSeqNo,
			  vcIndex, vcType }
	DESCRIPTION	"This trap is generated when set
			vcExUpThresholdTrapID equal 57 and
			until vcExceedUpperThresholdDecrease is generated after
			vcExceedUpperThresholdIncrease is generated."
	::= 15417

    vcExceedingUpperThreshold58 TRAP-TYPE
	ENTERPRISE	network-device
	VARIABLES	{ vcValue, adminDateAndTime, adminNDTrapSeqNo,
			  vcIndex, vcType }
	DESCRIPTION	"This trap is generated when set
			vcExUpThresholdTrapID equal 58 and
			until vcExceedUpperThresholdDecrease is generated after
			vcExceedUpperThresholdIncrease is generated."
	::= 15418

    vcExceedingUpperThreshold59 TRAP-TYPE
	ENTERPRISE	network-device
	VARIABLES	{ vcValue, adminDateAndTime, adminNDTrapSeqNo,
			  vcIndex, vcType }
	DESCRIPTION	"This trap is generated when set
			vcExUpThresholdTrapID equal 59 and
			until vcExceedUpperThresholdDecrease is generated after
			vcExceedUpperThresholdIncrease is generated."
	::= 15419

    vcExceedingUpperThreshold60 TRAP-TYPE
	ENTERPRISE	network-device
	VARIABLES	{ vcValue, adminDateAndTime, adminNDTrapSeqNo,
			  vcIndex, vcType }
	DESCRIPTION	"This trap is generated when set
			vcExUpThresholdTrapID equal 60 and
			until vcExceedUpperThresholdDecrease is generated after
			vcExceedUpperThresholdIncrease is generated."
	::= 15420

    vcExceedingUpperThreshold61 TRAP-TYPE
	ENTERPRISE	network-device
	VARIABLES	{ vcValue, adminDateAndTime, adminNDTrapSeqNo,
			  vcIndex, vcType }
	DESCRIPTION	"This trap is generated when set
			vcExUpThresholdTrapID equal 61 and
			until vcExceedUpperThresholdDecrease is generated after
			vcExceedUpperThresholdIncrease is generated."
	::= 15421

    vcExceedingUpperThreshold62 TRAP-TYPE
	ENTERPRISE	network-device
	VARIABLES	{ vcValue, adminDateAndTime, adminNDTrapSeqNo,
			  vcIndex, vcType }
	DESCRIPTION	"This trap is generated when set
			vcExUpThresholdTrapID equal 62 and
			until vcExceedUpperThresholdDecrease is generated after
			vcExceedUpperThresholdIncrease is generated."
	::= 15422

    vcExceedingUpperThreshold63 TRAP-TYPE
	ENTERPRISE	network-device
	VARIABLES	{ vcValue, adminDateAndTime, adminNDTrapSeqNo,
			  vcIndex, vcType }
	DESCRIPTION	"This trap is generated when set
			vcExUpThresholdTrapID equal 63 and
			until vcExceedUpperThresholdDecrease is generated after
			vcExceedUpperThresholdIncrease is generated."
	::= 15423

    vcExceedingUpperThreshold64 TRAP-TYPE
	ENTERPRISE	network-device
	VARIABLES	{ vcValue, adminDateAndTime, adminNDTrapSeqNo,
			  vcIndex, vcType }
	DESCRIPTION	"This trap is generated when set
			vcExUpThresholdTrapID equal 64 and
			until vcExceedUpperThresholdDecrease is generated after
			vcExceedUpperThresholdIncrease is generated."
	::= 15424

    vcExceedingUpperThreshold65 TRAP-TYPE
	ENTERPRISE	network-device
	VARIABLES	{ vcValue, adminDateAndTime, adminNDTrapSeqNo,
			  vcIndex, vcType }
	DESCRIPTION	"This trap is generated when set
			vcExUpThresholdTrapID equal 65 and
			until vcExceedUpperThresholdDecrease is generated after
			vcExceedUpperThresholdIncrease is generated."
	::= 15425

    vcExceedingUpperThreshold66 TRAP-TYPE
	ENTERPRISE	network-device
	VARIABLES	{ vcValue, adminDateAndTime, adminNDTrapSeqNo,
			  vcIndex, vcType }
	DESCRIPTION	"This trap is generated when set
			vcExUpThresholdTrapID equal 66 and
			until vcExceedUpperThresholdDecrease is generated after
			vcExceedUpperThresholdIncrease is generated."
	::= 15426

    vcExceedingUpperThreshold67 TRAP-TYPE
	ENTERPRISE	network-device
	VARIABLES	{ vcValue, adminDateAndTime, adminNDTrapSeqNo,
			  vcIndex, vcType }
	DESCRIPTION	"This trap is generated when set
			vcExUpThresholdTrapID equal 67 and
			until vcExceedUpperThresholdDecrease is generated after
			vcExceedUpperThresholdIncrease is generated."
	::= 15427

    vcExceedingUpperThreshold68 TRAP-TYPE
	ENTERPRISE	network-device
	VARIABLES	{ vcValue, adminDateAndTime, adminNDTrapSeqNo,
			  vcIndex, vcType }
	DESCRIPTION	"This trap is generated when set
			vcExUpThresholdTrapID equal 68 and
			until vcExceedUpperThresholdDecrease is generated after
			vcExceedUpperThresholdIncrease is generated."
	::= 15428

    vcExceedingUpperThreshold69 TRAP-TYPE
	ENTERPRISE	network-device
	VARIABLES	{ vcValue, adminDateAndTime, adminNDTrapSeqNo,
			  vcIndex, vcType }
	DESCRIPTION	"This trap is generated when set
			vcExUpThresholdTrapID equal 69 and
			until vcExceedUpperThresholdDecrease is generated after
			vcExceedUpperThresholdIncrease is generated."
	::= 15429

    vcExceedingUpperThreshold70 TRAP-TYPE
	ENTERPRISE	network-device
	VARIABLES	{ vcValue, adminDateAndTime, adminNDTrapSeqNo,
			  vcIndex, vcType }
	DESCRIPTION	"This trap is generated when set
			vcExUpThresholdTrapID equal 70 and
			until vcExceedUpperThresholdDecrease is generated after
			vcExceedUpperThresholdIncrease is generated."
	::= 15430

    vcExceedingUpperThreshold71 TRAP-TYPE
	ENTERPRISE	network-device
	VARIABLES	{ vcValue, adminDateAndTime, adminNDTrapSeqNo,
			  vcIndex, vcType }
	DESCRIPTION	"This trap is generated when set
			vcExUpThresholdTrapID equal 71 and
			until vcExceedUpperThresholdDecrease is generated after
			vcExceedUpperThresholdIncrease is generated."
	::= 15431

    vcExceedingUpperThreshold72 TRAP-TYPE
	ENTERPRISE	network-device
	VARIABLES	{ vcValue, adminDateAndTime, adminNDTrapSeqNo,
			  vcIndex, vcType }
	DESCRIPTION	"This trap is generated when set
			vcExUpThresholdTrapID equal 72 and
			until vcExceedUpperThresholdDecrease is generated after
			vcExceedUpperThresholdIncrease is generated."
	::= 15432

    vcExceedingUpperThreshold73 TRAP-TYPE
	ENTERPRISE	network-device
	VARIABLES	{ vcValue, adminDateAndTime, adminNDTrapSeqNo,
			  vcIndex, vcType }
	DESCRIPTION	"This trap is generated when set
			vcExUpThresholdTrapID equal 73 and
			until vcExceedUpperThresholdDecrease is generated after
			vcExceedUpperThresholdIncrease is generated."
	::= 15433

    vcExceedingUpperThreshold74 TRAP-TYPE
	ENTERPRISE	network-device
	VARIABLES	{ vcValue, adminDateAndTime, adminNDTrapSeqNo,
			  vcIndex, vcType }
	DESCRIPTION	"This trap is generated when set
			vcExUpThresholdTrapID equal 74 and
			until vcExceedUpperThresholdDecrease is generated after
			vcExceedUpperThresholdIncrease is generated."
	::= 15434

    vcExceedingUpperThreshold75 TRAP-TYPE
	ENTERPRISE	network-device
	VARIABLES	{ vcValue, adminDateAndTime, adminNDTrapSeqNo,
			  vcIndex, vcType }
	DESCRIPTION	"This trap is generated when set
			vcExUpThresholdTrapID equal 75 and
			until vcExceedUpperThresholdDecrease is generated after
			vcExceedUpperThresholdIncrease is generated."
	::= 15435

    vcExceedingUpperThreshold76 TRAP-TYPE
	ENTERPRISE	network-device
	VARIABLES	{ vcValue, adminDateAndTime, adminNDTrapSeqNo,
			  vcIndex, vcType }
	DESCRIPTION	"This trap is generated when set
			vcExUpThresholdTrapID equal 76 and
			until vcExceedUpperThresholdDecrease is generated after
			vcExceedUpperThresholdIncrease is generated."
	::= 15436

    vcExceedingUpperThreshold77 TRAP-TYPE
	ENTERPRISE	network-device
	VARIABLES	{ vcValue, adminDateAndTime, adminNDTrapSeqNo,
			  vcIndex, vcType }
	DESCRIPTION	"This trap is generated when set
			vcExUpThresholdTrapID equal 77 and
			until vcExceedUpperThresholdDecrease is generated after
			vcExceedUpperThresholdIncrease is generated."
	::= 15437

    vcExceedingUpperThreshold78 TRAP-TYPE
	ENTERPRISE	network-device
	VARIABLES	{ vcValue, adminDateAndTime, adminNDTrapSeqNo,
			  vcIndex, vcType }
	DESCRIPTION	"This trap is generated when set
			vcExUpThresholdTrapID equal 78 and
			until vcExceedUpperThresholdDecrease is generated after
			vcExceedUpperThresholdIncrease is generated."
	::= 15438

    vcExceedingUpperThreshold79 TRAP-TYPE
	ENTERPRISE	network-device
	VARIABLES	{ vcValue, adminDateAndTime, adminNDTrapSeqNo,
			  vcIndex, vcType }
	DESCRIPTION	"This trap is generated when set
			vcExUpThresholdTrapID equal 79 and
			until vcExceedUpperThresholdDecrease is generated after
			vcExceedUpperThresholdIncrease is generated."
	::= 15439

    vcExceedingUpperThreshold80 TRAP-TYPE
	ENTERPRISE	network-device
	VARIABLES	{ vcValue, adminDateAndTime, adminNDTrapSeqNo,
			  vcIndex, vcType }
	DESCRIPTION	"This trap is generated when set
			vcExUpThresholdTrapID equal 80 and
			until vcExceedUpperThresholdDecrease is generated after
			vcExceedUpperThresholdIncrease is generated."
	::= 15440

    vcExceedingUpperThreshold81 TRAP-TYPE
	ENTERPRISE	network-device
	VARIABLES	{ vcValue, adminDateAndTime, adminNDTrapSeqNo,
			  vcIndex, vcType }
	DESCRIPTION	"This trap is generated when set
			vcExUpThresholdTrapID equal 81 and
			until vcExceedUpperThresholdDecrease is generated after
			vcExceedUpperThresholdIncrease is generated."
	::= 15441

    vcExceedingUpperThreshold82 TRAP-TYPE
	ENTERPRISE	network-device
	VARIABLES	{ vcValue, adminDateAndTime, adminNDTrapSeqNo,
			  vcIndex, vcType }
	DESCRIPTION	"This trap is generated when set
			vcExUpThresholdTrapID equal 82 and
			until vcExceedUpperThresholdDecrease is generated after
			vcExceedUpperThresholdIncrease is generated."
	::= 15442

    vcExceedingUpperThreshold83 TRAP-TYPE
	ENTERPRISE	network-device
	VARIABLES	{ vcValue, adminDateAndTime, adminNDTrapSeqNo,
			  vcIndex, vcType }
	DESCRIPTION	"This trap is generated when set
			vcExUpThresholdTrapID equal 83 and
			until vcExceedUpperThresholdDecrease is generated after
			vcExceedUpperThresholdIncrease is generated."
	::= 15443

    vcExceedingUpperThreshold84 TRAP-TYPE
	ENTERPRISE	network-device
	VARIABLES	{ vcValue, adminDateAndTime, adminNDTrapSeqNo,
			  vcIndex, vcType }
	DESCRIPTION	"This trap is generated when set
			vcExUpThresholdTrapID equal 84 and
			until vcExceedUpperThresholdDecrease is generated after
			vcExceedUpperThresholdIncrease is generated."
	::= 15444

    vcExceedingUpperThreshold85 TRAP-TYPE
	ENTERPRISE	network-device
	VARIABLES	{ vcValue, adminDateAndTime, adminNDTrapSeqNo,
			  vcIndex, vcType }
	DESCRIPTION	"This trap is generated when set
			vcExUpThresholdTrapID equal 85 and
			until vcExceedUpperThresholdDecrease is generated after
			vcExceedUpperThresholdIncrease is generated."
	::= 15445

    vcExceedingUpperThreshold86 TRAP-TYPE
	ENTERPRISE	network-device
	VARIABLES	{ vcValue, adminDateAndTime, adminNDTrapSeqNo,
			  vcIndex, vcType }
	DESCRIPTION	"This trap is generated when set
			vcExUpThresholdTrapID equal 86 and
			until vcExceedUpperThresholdDecrease is generated after
			vcExceedUpperThresholdIncrease is generated."
	::= 15446

    vcExceedingUpperThreshold87 TRAP-TYPE
	ENTERPRISE	network-device
	VARIABLES	{ vcValue, adminDateAndTime, adminNDTrapSeqNo,
			  vcIndex, vcType }
	DESCRIPTION	"This trap is generated when set
			vcExUpThresholdTrapID equal 87 and
			until vcExceedUpperThresholdDecrease is generated after
			vcExceedUpperThresholdIncrease is generated."
	::= 15447

    vcExceedingUpperThreshold88 TRAP-TYPE
	ENTERPRISE	network-device
	VARIABLES	{ vcValue, adminDateAndTime, adminNDTrapSeqNo,
			  vcIndex, vcType }
	DESCRIPTION	"This trap is generated when set
			vcExUpThresholdTrapID equal 88 and
			until vcExceedUpperThresholdDecrease is generated after
			vcExceedUpperThresholdIncrease is generated."
	::= 15448

    vcExceedingUpperThreshold89 TRAP-TYPE
	ENTERPRISE	network-device
	VARIABLES	{ vcValue, adminDateAndTime, adminNDTrapSeqNo,
			  vcIndex, vcType }
	DESCRIPTION	"This trap is generated when set
			vcExUpThresholdTrapID equal 89 and
			until vcExceedUpperThresholdDecrease is generated after
			vcExceedUpperThresholdIncrease is generated."
	::= 15449

    vcExceedingUpperThreshold90 TRAP-TYPE
	ENTERPRISE	network-device
	VARIABLES	{ vcValue, adminDateAndTime, adminNDTrapSeqNo,
			  vcIndex, vcType }
	DESCRIPTION	"This trap is generated when set
			vcExUpThresholdTrapID equal 90 and
			until vcExceedUpperThresholdDecrease is generated after
			vcExceedUpperThresholdIncrease is generated."
	::= 15450

    vcExceedingUpperThreshold91 TRAP-TYPE
	ENTERPRISE	network-device
	VARIABLES	{ vcValue, adminDateAndTime, adminNDTrapSeqNo,
			  vcIndex, vcType }
	DESCRIPTION	"This trap is generated when set
			vcExUpThresholdTrapID equal 91 and
			until vcExceedUpperThresholdDecrease is generated after
			vcExceedUpperThresholdIncrease is generated."
	::= 15451

    vcExceedingUpperThreshold92 TRAP-TYPE
	ENTERPRISE	network-device
	VARIABLES	{ vcValue, adminDateAndTime, adminNDTrapSeqNo,
			  vcIndex, vcType }
	DESCRIPTION	"This trap is generated when set
			vcExUpThresholdTrapID equal 92 and
			until vcExceedUpperThresholdDecrease is generated after
			vcExceedUpperThresholdIncrease is generated."
	::= 15452

    vcExceedingUpperThreshold93 TRAP-TYPE
	ENTERPRISE	network-device
	VARIABLES	{ vcValue, adminDateAndTime, adminNDTrapSeqNo,
			  vcIndex, vcType }
	DESCRIPTION	"This trap is generated when set
			vcExUpThresholdTrapID equal 93 and
			until vcExceedUpperThresholdDecrease is generated after
			vcExceedUpperThresholdIncrease is generated."
	::= 15453

    vcExceedingUpperThreshold94 TRAP-TYPE
	ENTERPRISE	network-device
	VARIABLES	{ vcValue, adminDateAndTime, adminNDTrapSeqNo,
			  vcIndex, vcType }
	DESCRIPTION	"This trap is generated when set
			vcExUpThresholdTrapID equal 94 and
			until vcExceedUpperThresholdDecrease is generated after
			vcExceedUpperThresholdIncrease is generated."
	::= 15454

    vcExceedingUpperThreshold95 TRAP-TYPE
	ENTERPRISE	network-device
	VARIABLES	{ vcValue, adminDateAndTime, adminNDTrapSeqNo,
			  vcIndex, vcType }
	DESCRIPTION	"This trap is generated when set
			vcExUpThresholdTrapID equal 95 and
			until vcExceedUpperThresholdDecrease is generated after
			vcExceedUpperThresholdIncrease is generated."
	::= 15455

    vcExceedingUpperThreshold96 TRAP-TYPE
	ENTERPRISE	network-device
	VARIABLES	{ vcValue, adminDateAndTime, adminNDTrapSeqNo,
			  vcIndex, vcType }
	DESCRIPTION	"This trap is generated when set
			vcExUpThresholdTrapID equal 96 and
			until vcExceedUpperThresholdDecrease is generated after
			vcExceedUpperThresholdIncrease is generated."
	::= 15456

    vcExceedingUpperThreshold97 TRAP-TYPE
	ENTERPRISE	network-device
	VARIABLES	{ vcValue, adminDateAndTime, adminNDTrapSeqNo,
			  vcIndex, vcType }
	DESCRIPTION	"This trap is generated when set
			vcExUpThresholdTrapID equal 97 and
			until vcExceedUpperThresholdDecrease is generated after
			vcExceedUpperThresholdIncrease is generated."
	::= 15457

    vcExceedingUpperThreshold98 TRAP-TYPE
	ENTERPRISE	network-device
	VARIABLES	{ vcValue, adminDateAndTime, adminNDTrapSeqNo,
			  vcIndex, vcType }
	DESCRIPTION	"This trap is generated when set
			vcExUpThresholdTrapID equal 98 and
			until vcExceedUpperThresholdDecrease is generated after
			vcExceedUpperThresholdIncrease is generated."
	::= 15458

    vcExceedingUpperThreshold99 TRAP-TYPE
	ENTERPRISE	network-device
	VARIABLES	{ vcValue, adminDateAndTime, adminNDTrapSeqNo,
			  vcIndex, vcType }
	DESCRIPTION	"This trap is generated when set
			vcExUpThresholdTrapID equal 99 and
			until vcExceedUpperThresholdDecrease is generated after
			vcExceedUpperThresholdIncrease is generated."
	::= 15459

    vcExceedingUpperThreshold100 TRAP-TYPE
	ENTERPRISE	network-device
	VARIABLES	{ vcValue, adminDateAndTime, adminNDTrapSeqNo,
			  vcIndex, vcType }
	DESCRIPTION	"This trap is generated when set
			vcExUpThresholdTrapID equal 100 and
			until vcExceedUpperThresholdDecrease is generated after
			vcExceedUpperThresholdIncrease is generated."
	::= 15460

    vcExceedingUpperThreshold101 TRAP-TYPE
	ENTERPRISE	network-device
	VARIABLES	{ vcValue, adminDateAndTime, adminNDTrapSeqNo,
			  vcIndex, vcType }
	DESCRIPTION	"This trap is generated when set
			vcExUpThresholdTrapID equal 101 and
			until vcExceedUpperThresholdDecrease is generated after
			vcExceedUpperThresholdIncrease is generated."
	::= 15461

    vcExceedingUpperThreshold102 TRAP-TYPE
	ENTERPRISE	network-device
	VARIABLES	{ vcValue, adminDateAndTime, adminNDTrapSeqNo,
			  vcIndex, vcType }
	DESCRIPTION	"This trap is generated when set
			vcExUpThresholdTrapID equal 102 and
			until vcExceedUpperThresholdDecrease is generated after
			vcExceedUpperThresholdIncrease is generated."
	::= 15462

    vcExceedingUpperThreshold103 TRAP-TYPE
	ENTERPRISE	network-device
	VARIABLES	{ vcValue, adminDateAndTime, adminNDTrapSeqNo,
			  vcIndex, vcType }
	DESCRIPTION	"This trap is generated when set
			vcExUpThresholdTrapID equal 103 and
			until vcExceedUpperThresholdDecrease is generated after
			vcExceedUpperThresholdIncrease is generated."
	::= 15463

    vcExceedingUpperThreshold104 TRAP-TYPE
	ENTERPRISE	network-device
	VARIABLES	{ vcValue, adminDateAndTime, adminNDTrapSeqNo,
			  vcIndex, vcType }
	DESCRIPTION	"This trap is generated when set
			vcExUpThresholdTrapID equal 104 and
			until vcExceedUpperThresholdDecrease is generated after
			vcExceedUpperThresholdIncrease is generated."
	::= 15464

    vcExceedingUpperThreshold105 TRAP-TYPE
	ENTERPRISE	network-device
	VARIABLES	{ vcValue, adminDateAndTime, adminNDTrapSeqNo,
			  vcIndex, vcType }
	DESCRIPTION	"This trap is generated when set
			vcExUpThresholdTrapID equal 105 and
			until vcExceedUpperThresholdDecrease is generated after
			vcExceedUpperThresholdIncrease is generated."
	::= 15465

    vcExceedingUpperThreshold106 TRAP-TYPE
	ENTERPRISE	network-device
	VARIABLES	{ vcValue, adminDateAndTime, adminNDTrapSeqNo,
			  vcIndex, vcType }
	DESCRIPTION	"This trap is generated when set
			vcExUpThresholdTrapID equal 106 and
			until vcExceedUpperThresholdDecrease is generated after
			vcExceedUpperThresholdIncrease is generated."
	::= 15466

    vcExceedingUpperThreshold107 TRAP-TYPE
	ENTERPRISE	network-device
	VARIABLES	{ vcValue, adminDateAndTime, adminNDTrapSeqNo,
			  vcIndex, vcType }
	DESCRIPTION	"This trap is generated when set
			vcExUpThresholdTrapID equal 107 and
			until vcExceedUpperThresholdDecrease is generated after
			vcExceedUpperThresholdIncrease is generated."
	::= 15467

    vcExceedingUpperThreshold108 TRAP-TYPE
	ENTERPRISE	network-device
	VARIABLES	{ vcValue, adminDateAndTime, adminNDTrapSeqNo,
			  vcIndex, vcType }
	DESCRIPTION	"This trap is generated when set
			vcExUpThresholdTrapID equal 108 and
			until vcExceedUpperThresholdDecrease is generated after
			vcExceedUpperThresholdIncrease is generated."
	::= 15468

    vcExceedingUpperThreshold109 TRAP-TYPE
	ENTERPRISE	network-device
	VARIABLES	{ vcValue, adminDateAndTime, adminNDTrapSeqNo,
			  vcIndex, vcType }
	DESCRIPTION	"This trap is generated when set
			vcExUpThresholdTrapID equal 109 and
			until vcExceedUpperThresholdDecrease is generated after
			vcExceedUpperThresholdIncrease is generated."
	::= 15469

    vcExceedingUpperThreshold110 TRAP-TYPE
	ENTERPRISE	network-device
	VARIABLES	{ vcValue, adminDateAndTime, adminNDTrapSeqNo,
			  vcIndex, vcType }
	DESCRIPTION	"This trap is generated when set
			vcExUpThresholdTrapID equal 110 and
			until vcExceedUpperThresholdDecrease is generated after
			vcExceedUpperThresholdIncrease is generated."
	::= 15470

    vcExceedingUpperThreshold111 TRAP-TYPE
	ENTERPRISE	network-device
	VARIABLES	{ vcValue, adminDateAndTime, adminNDTrapSeqNo,
			  vcIndex, vcType }
	DESCRIPTION	"This trap is generated when set
			vcExUpThresholdTrapID equal 111 and
			until vcExceedUpperThresholdDecrease is generated after
			vcExceedUpperThresholdIncrease is generated."
	::= 15471

    vcExceedingUpperThreshold112 TRAP-TYPE
	ENTERPRISE	network-device
	VARIABLES	{ vcValue, adminDateAndTime, adminNDTrapSeqNo,
			  vcIndex, vcType }
	DESCRIPTION	"This trap is generated when set
			vcExUpThresholdTrapID equal 112 and
			until vcExceedUpperThresholdDecrease is generated after
			vcExceedUpperThresholdIncrease is generated."
	::= 15472

    vcExceedingUpperThreshold113 TRAP-TYPE
	ENTERPRISE	network-device
	VARIABLES	{ vcValue, adminDateAndTime, adminNDTrapSeqNo,
			  vcIndex, vcType }
	DESCRIPTION	"This trap is generated when set
			vcExUpThresholdTrapID equal 113 and
			until vcExceedUpperThresholdDecrease is generated after
			vcExceedUpperThresholdIncrease is generated."
	::= 15473

    vcExceedingUpperThreshold114 TRAP-TYPE
	ENTERPRISE	network-device
	VARIABLES	{ vcValue, adminDateAndTime, adminNDTrapSeqNo,
			  vcIndex, vcType }
	DESCRIPTION	"This trap is generated when set
			vcExUpThresholdTrapID equal 114 and
			until vcExceedUpperThresholdDecrease is generated after
			vcExceedUpperThresholdIncrease is generated."
	::= 15474

    vcExceedingUpperThreshold115 TRAP-TYPE
	ENTERPRISE	network-device
	VARIABLES	{ vcValue, adminDateAndTime, adminNDTrapSeqNo,
			  vcIndex, vcType }
	DESCRIPTION	"This trap is generated when set
			vcExUpThresholdTrapID equal 115 and
			until vcExceedUpperThresholdDecrease is generated after
			vcExceedUpperThresholdIncrease is generated."
	::= 15475

    vcExceedingUpperThreshold116 TRAP-TYPE
	ENTERPRISE	network-device
	VARIABLES	{ vcValue, adminDateAndTime, adminNDTrapSeqNo,
			  vcIndex, vcType }
	DESCRIPTION	"This trap is generated when set
			vcExUpThresholdTrapID equal 116 and
			until vcExceedUpperThresholdDecrease is generated after
			vcExceedUpperThresholdIncrease is generated."
	::= 15476

    vcExceedingUpperThreshold117 TRAP-TYPE
	ENTERPRISE	network-device
	VARIABLES	{ vcValue, adminDateAndTime, adminNDTrapSeqNo,
			  vcIndex, vcType }
	DESCRIPTION	"This trap is generated when set
			vcExUpThresholdTrapID equal 117 and
			until vcExceedUpperThresholdDecrease is generated after
			vcExceedUpperThresholdIncrease is generated."
	::= 15477

    vcExceedingUpperThreshold118 TRAP-TYPE
	ENTERPRISE	network-device
	VARIABLES	{ vcValue, adminDateAndTime, adminNDTrapSeqNo,
			  vcIndex, vcType }
	DESCRIPTION	"This trap is generated when set
			vcExUpThresholdTrapID equal 118 and
			until vcExceedUpperThresholdDecrease is generated after
			vcExceedUpperThresholdIncrease is generated."
	::= 15478

    vcExceedingUpperThreshold119 TRAP-TYPE
	ENTERPRISE	network-device
	VARIABLES	{ vcValue, adminDateAndTime, adminNDTrapSeqNo,
			  vcIndex, vcType }
	DESCRIPTION	"This trap is generated when set
			vcExUpThresholdTrapID equal 119 and
			until vcExceedUpperThresholdDecrease is generated after
			vcExceedUpperThresholdIncrease is generated."
	::= 15479

    vcExceedingUpperThreshold120 TRAP-TYPE
	ENTERPRISE	network-device
	VARIABLES	{ vcValue, adminDateAndTime, adminNDTrapSeqNo,
			  vcIndex, vcType }
	DESCRIPTION	"This trap is generated when set
			vcExUpThresholdTrapID equal 120 and
			until vcExceedUpperThresholdDecrease is generated after
			vcExceedUpperThresholdIncrease is generated."
	::= 15480

    vcExceedingUpperThreshold121 TRAP-TYPE
	ENTERPRISE	network-device
	VARIABLES	{ vcValue, adminDateAndTime, adminNDTrapSeqNo,
			  vcIndex, vcType }
	DESCRIPTION	"This trap is generated when set
			vcExUpThresholdTrapID equal 121 and
			until vcExceedUpperThresholdDecrease is generated after
			vcExceedUpperThresholdIncrease is generated."
	::= 15481

    vcExceedingUpperThreshold122 TRAP-TYPE
	ENTERPRISE	network-device
	VARIABLES	{ vcValue, adminDateAndTime, adminNDTrapSeqNo,
			  vcIndex, vcType }
	DESCRIPTION	"This trap is generated when set
			vcExUpThresholdTrapID equal 122 and
			until vcExceedUpperThresholdDecrease is generated after
			vcExceedUpperThresholdIncrease is generated."
	::= 15482

    vcExceedingUpperThreshold123 TRAP-TYPE
	ENTERPRISE	network-device
	VARIABLES	{ vcValue, adminDateAndTime, adminNDTrapSeqNo,
			  vcIndex, vcType }
	DESCRIPTION	"This trap is generated when set
			vcExUpThresholdTrapID equal 123 and
			until vcExceedUpperThresholdDecrease is generated after
			vcExceedUpperThresholdIncrease is generated."
	::= 15483

    vcExceedingUpperThreshold124 TRAP-TYPE
	ENTERPRISE	network-device
	VARIABLES	{ vcValue, adminDateAndTime, adminNDTrapSeqNo,
			  vcIndex, vcType }
	DESCRIPTION	"This trap is generated when set
			vcExUpThresholdTrapID equal 124 and
			until vcExceedUpperThresholdDecrease is generated after
			vcExceedUpperThresholdIncrease is generated."
	::= 15484

    vcExceedingUpperThreshold125 TRAP-TYPE
	ENTERPRISE	network-device
	VARIABLES	{ vcValue, adminDateAndTime, adminNDTrapSeqNo,
			  vcIndex, vcType }
	DESCRIPTION	"This trap is generated when set
			vcExUpThresholdTrapID equal 125 and
			until vcExceedUpperThresholdDecrease is generated after
			vcExceedUpperThresholdIncrease is generated."
	::= 15485

    vcExceedingUpperThreshold126 TRAP-TYPE
	ENTERPRISE	network-device
	VARIABLES	{ vcValue, adminDateAndTime, adminNDTrapSeqNo,
			  vcIndex, vcType }
	DESCRIPTION	"This trap is generated when set
			vcExUpThresholdTrapID equal 126 and
			until vcExceedUpperThresholdDecrease is generated after
			vcExceedUpperThresholdIncrease is generated."
	::= 15486

    vcExceedingUpperThreshold127 TRAP-TYPE
	ENTERPRISE	network-device
	VARIABLES	{ vcValue, adminDateAndTime, adminNDTrapSeqNo,
			  vcIndex, vcType }
	DESCRIPTION	"This trap is generated when set
			vcExUpThresholdTrapID equal 127 and
			until vcExceedUpperThresholdDecrease is generated after
			vcExceedUpperThresholdIncrease is generated."
	::= 15487

    vcExceedLowerThresholdIncrease1 TRAP-TYPE
	ENTERPRISE	network-device
	VARIABLES	{ vcValue, adminDateAndTime, adminNDTrapSeqNo,
			  vcIndex, vcType }
	DESCRIPTION	"This trap is generated when set
			vcExLoThresholdIncreaseTrapID equal 1 and
			vcValue is greater equal
			the lower threshold plus the lower hysteresis
			after vcExceedLowerThresholdDecrease is generated.
			namely, vcValue >= (vcTrapLowerThreshold +
			vcTrapLowerHysteresis)."
	::= 15873

    vcExceedLowerThresholdIncrease2 TRAP-TYPE
	ENTERPRISE	network-device
	VARIABLES	{ vcValue, adminDateAndTime, adminNDTrapSeqNo,
			  vcIndex, vcType }
	DESCRIPTION	"This trap is generated when set
			vcExLoThresholdIncreaseTrapID equal 2 and
			vcValue is greater equal
			the lower threshold plus the lower hysteresis
			after vcExceedLowerThresholdDecrease is generated.
			namely, vcValue >= (vcTrapLowerThreshold +
			vcTrapLowerHysteresis)."
	::= 15874

    vcExceedLowerThresholdIncrease3 TRAP-TYPE
	ENTERPRISE	network-device
	VARIABLES	{ vcValue, adminDateAndTime, adminNDTrapSeqNo,
			  vcIndex, vcType }
	DESCRIPTION	"This trap is generated when set
			vcExLoThresholdIncreaseTrapID equal 3 and
			vcValue is greater equal
			the lower threshold plus the lower hysteresis
			after vcExceedLowerThresholdDecrease is generated.
			namely, vcValue >= (vcTrapLowerThreshold +
			vcTrapLowerHysteresis)."
	::= 15875

    vcExceedLowerThresholdIncrease4 TRAP-TYPE
	ENTERPRISE	network-device
	VARIABLES	{ vcValue, adminDateAndTime, adminNDTrapSeqNo,
			  vcIndex, vcType }
	DESCRIPTION	"This trap is generated when set
			vcExLoThresholdIncreaseTrapID equal 4 and
			vcValue is greater equal
			the lower threshold plus the lower hysteresis
			after vcExceedLowerThresholdDecrease is generated.
			namely, vcValue >= (vcTrapLowerThreshold +
			vcTrapLowerHysteresis)."
	::= 15876

    vcExceedLowerThresholdIncrease5 TRAP-TYPE
	ENTERPRISE	network-device
	VARIABLES	{ vcValue, adminDateAndTime, adminNDTrapSeqNo,
			  vcIndex, vcType }
	DESCRIPTION	"This trap is generated when set
			vcExLoThresholdIncreaseTrapID equal 5 and
			vcValue is greater equal
			the lower threshold plus the lower hysteresis
			after vcExceedLowerThresholdDecrease is generated.
			namely, vcValue >= (vcTrapLowerThreshold +
			vcTrapLowerHysteresis)."
	::= 15877

    vcExceedLowerThresholdIncrease6 TRAP-TYPE
	ENTERPRISE	network-device
	VARIABLES	{ vcValue, adminDateAndTime, adminNDTrapSeqNo,
			  vcIndex, vcType }
	DESCRIPTION	"This trap is generated when set
			vcExLoThresholdIncreaseTrapID equal 6 and
			vcValue is greater equal
			the lower threshold plus the lower hysteresis
			after vcExceedLowerThresholdDecrease is generated.
			namely, vcValue >= (vcTrapLowerThreshold +
			vcTrapLowerHysteresis)."
	::= 15878

    vcExceedLowerThresholdIncrease7 TRAP-TYPE
	ENTERPRISE	network-device
	VARIABLES	{ vcValue, adminDateAndTime, adminNDTrapSeqNo,
			  vcIndex, vcType }
	DESCRIPTION	"This trap is generated when set
			vcExLoThresholdIncreaseTrapID equal 7 and
			vcValue is greater equal
			the lower threshold plus the lower hysteresis
			after vcExceedLowerThresholdDecrease is generated.
			namely, vcValue >= (vcTrapLowerThreshold +
			vcTrapLowerHysteresis)."
	::= 15879

    vcExceedLowerThresholdIncrease8 TRAP-TYPE
	ENTERPRISE	network-device
	VARIABLES	{ vcValue, adminDateAndTime, adminNDTrapSeqNo,
			  vcIndex, vcType }
	DESCRIPTION	"This trap is generated when set
			vcExLoThresholdIncreaseTrapID equal 8 and
			vcValue is greater equal
			the lower threshold plus the lower hysteresis
			after vcExceedLowerThresholdDecrease is generated.
			namely, vcValue >= (vcTrapLowerThreshold +
			vcTrapLowerHysteresis)."
	::= 15880

    vcExceedLowerThresholdIncrease9 TRAP-TYPE
	ENTERPRISE	network-device
	VARIABLES	{ vcValue, adminDateAndTime, adminNDTrapSeqNo,
			  vcIndex, vcType }
	DESCRIPTION	"This trap is generated when set
			vcExLoThresholdIncreaseTrapID equal 9 and
			vcValue is greater equal
			the lower threshold plus the lower hysteresis
			after vcExceedLowerThresholdDecrease is generated.
			namely, vcValue >= (vcTrapLowerThreshold +
			vcTrapLowerHysteresis)."
	::= 15881

    vcExceedLowerThresholdIncrease10 TRAP-TYPE
	ENTERPRISE	network-device
	VARIABLES	{ vcValue, adminDateAndTime, adminNDTrapSeqNo,
			  vcIndex, vcType }
	DESCRIPTION	"This trap is generated when set
			vcExLoThresholdIncreaseTrapID equal 10 and
			vcValue is greater equal
			the lower threshold plus the lower hysteresis
			after vcExceedLowerThresholdDecrease is generated.
			namely, vcValue >= (vcTrapLowerThreshold +
			vcTrapLowerHysteresis)."
	::= 15882

    vcExceedLowerThresholdIncrease11 TRAP-TYPE
	ENTERPRISE	network-device
	VARIABLES	{ vcValue, adminDateAndTime, adminNDTrapSeqNo,
			  vcIndex, vcType }
	DESCRIPTION	"This trap is generated when set
			vcExLoThresholdIncreaseTrapID equal 11 and
			vcValue is greater equal
			the lower threshold plus the lower hysteresis
			after vcExceedLowerThresholdDecrease is generated.
			namely, vcValue >= (vcTrapLowerThreshold +
			vcTrapLowerHysteresis)."
	::= 15883

    vcExceedLowerThresholdIncrease12 TRAP-TYPE
	ENTERPRISE	network-device
	VARIABLES	{ vcValue, adminDateAndTime, adminNDTrapSeqNo,
			  vcIndex, vcType }
	DESCRIPTION	"This trap is generated when set
			vcExLoThresholdIncreaseTrapID equal 12 and
			vcValue is greater equal
			the lower threshold plus the lower hysteresis
			after vcExceedLowerThresholdDecrease is generated.
			namely, vcValue >= (vcTrapLowerThreshold +
			vcTrapLowerHysteresis)."
	::= 15884

    vcExceedLowerThresholdIncrease13 TRAP-TYPE
	ENTERPRISE	network-device
	VARIABLES	{ vcValue, adminDateAndTime, adminNDTrapSeqNo,
			  vcIndex, vcType }
	DESCRIPTION	"This trap is generated when set
			vcExLoThresholdIncreaseTrapID equal 13 and
			vcValue is greater equal
			the lower threshold plus the lower hysteresis
			after vcExceedLowerThresholdDecrease is generated.
			namely, vcValue >= (vcTrapLowerThreshold +
			vcTrapLowerHysteresis)."
	::= 15885

    vcExceedLowerThresholdIncrease14 TRAP-TYPE
	ENTERPRISE	network-device
	VARIABLES	{ vcValue, adminDateAndTime, adminNDTrapSeqNo,
			  vcIndex, vcType }
	DESCRIPTION	"This trap is generated when set
			vcExLoThresholdIncreaseTrapID equal 14 and
			vcValue is greater equal
			the lower threshold plus the lower hysteresis
			after vcExceedLowerThresholdDecrease is generated.
			namely, vcValue >= (vcTrapLowerThreshold +
			vcTrapLowerHysteresis)."
	::= 15886

    vcExceedLowerThresholdIncrease15 TRAP-TYPE
	ENTERPRISE	network-device
	VARIABLES	{ vcValue, adminDateAndTime, adminNDTrapSeqNo,
			  vcIndex, vcType }
	DESCRIPTION	"This trap is generated when set
			vcExLoThresholdIncreaseTrapID equal 15 and
			vcValue is greater equal
			the lower threshold plus the lower hysteresis
			after vcExceedLowerThresholdDecrease is generated.
			namely, vcValue >= (vcTrapLowerThreshold +
			vcTrapLowerHysteresis)."
	::= 15887

    vcExceedLowerThresholdIncrease16 TRAP-TYPE
	ENTERPRISE	network-device
	VARIABLES	{ vcValue, adminDateAndTime, adminNDTrapSeqNo,
			  vcIndex, vcType }
	DESCRIPTION	"This trap is generated when set
			vcExLoThresholdIncreaseTrapID equal 16 and
			vcValue is greater equal
			the lower threshold plus the lower hysteresis
			after vcExceedLowerThresholdDecrease is generated.
			namely, vcValue >= (vcTrapLowerThreshold +
			vcTrapLowerHysteresis)."
	::= 15888

    vcExceedLowerThresholdIncrease17 TRAP-TYPE
	ENTERPRISE	network-device
	VARIABLES	{ vcValue, adminDateAndTime, adminNDTrapSeqNo,
			  vcIndex, vcType }
	DESCRIPTION	"This trap is generated when set
			vcExLoThresholdIncreaseTrapID equal 17 and
			vcValue is greater equal
			the lower threshold plus the lower hysteresis
			after vcExceedLowerThresholdDecrease is generated.
			namely, vcValue >= (vcTrapLowerThreshold +
			vcTrapLowerHysteresis)."
	::= 15889

    vcExceedLowerThresholdIncrease18 TRAP-TYPE
	ENTERPRISE	network-device
	VARIABLES	{ vcValue, adminDateAndTime, adminNDTrapSeqNo,
			  vcIndex, vcType }
	DESCRIPTION	"This trap is generated when set
			vcExLoThresholdIncreaseTrapID equal 18 and
			vcValue is greater equal
			the lower threshold plus the lower hysteresis
			after vcExceedLowerThresholdDecrease is generated.
			namely, vcValue >= (vcTrapLowerThreshold +
			vcTrapLowerHysteresis)."
	::= 15890

    vcExceedLowerThresholdIncrease19 TRAP-TYPE
	ENTERPRISE	network-device
	VARIABLES	{ vcValue, adminDateAndTime, adminNDTrapSeqNo,
			  vcIndex, vcType }
	DESCRIPTION	"This trap is generated when set
			vcExLoThresholdIncreaseTrapID equal 19 and
			vcValue is greater equal
			the lower threshold plus the lower hysteresis
			after vcExceedLowerThresholdDecrease is generated.
			namely, vcValue >= (vcTrapLowerThreshold +
			vcTrapLowerHysteresis)."
	::= 15891

    vcExceedLowerThresholdIncrease20 TRAP-TYPE
	ENTERPRISE	network-device
	VARIABLES	{ vcValue, adminDateAndTime, adminNDTrapSeqNo,
			  vcIndex, vcType }
	DESCRIPTION	"This trap is generated when set
			vcExLoThresholdIncreaseTrapID equal 20 and
			vcValue is greater equal
			the lower threshold plus the lower hysteresis
			after vcExceedLowerThresholdDecrease is generated.
			namely, vcValue >= (vcTrapLowerThreshold +
			vcTrapLowerHysteresis)."
	::= 15892

    vcExceedLowerThresholdIncrease21 TRAP-TYPE
	ENTERPRISE	network-device
	VARIABLES	{ vcValue, adminDateAndTime, adminNDTrapSeqNo,
			  vcIndex, vcType }
	DESCRIPTION	"This trap is generated when set
			vcExLoThresholdIncreaseTrapID equal 21 and
			vcValue is greater equal
			the lower threshold plus the lower hysteresis
			after vcExceedLowerThresholdDecrease is generated.
			namely, vcValue >= (vcTrapLowerThreshold +
			vcTrapLowerHysteresis)."
	::= 15893

    vcExceedLowerThresholdIncrease22 TRAP-TYPE
	ENTERPRISE	network-device
	VARIABLES	{ vcValue, adminDateAndTime, adminNDTrapSeqNo,
			  vcIndex, vcType }
	DESCRIPTION	"This trap is generated when set
			vcExLoThresholdIncreaseTrapID equal 22 and
			vcValue is greater equal
			the lower threshold plus the lower hysteresis
			after vcExceedLowerThresholdDecrease is generated.
			namely, vcValue >= (vcTrapLowerThreshold +
			vcTrapLowerHysteresis)."
	::= 15894

    vcExceedLowerThresholdIncrease23 TRAP-TYPE
	ENTERPRISE	network-device
	VARIABLES	{ vcValue, adminDateAndTime, adminNDTrapSeqNo,
			  vcIndex, vcType }
	DESCRIPTION	"This trap is generated when set
			vcExLoThresholdIncreaseTrapID equal 23 and
			vcValue is greater equal
			the lower threshold plus the lower hysteresis
			after vcExceedLowerThresholdDecrease is generated.
			namely, vcValue >= (vcTrapLowerThreshold +
			vcTrapLowerHysteresis)."
	::= 15895

    vcExceedLowerThresholdIncrease24 TRAP-TYPE
	ENTERPRISE	network-device
	VARIABLES	{ vcValue, adminDateAndTime, adminNDTrapSeqNo,
			  vcIndex, vcType }
	DESCRIPTION	"This trap is generated when set
			vcExLoThresholdIncreaseTrapID equal 24 and
			vcValue is greater equal
			the lower threshold plus the lower hysteresis
			after vcExceedLowerThresholdDecrease is generated.
			namely, vcValue >= (vcTrapLowerThreshold +
			vcTrapLowerHysteresis)."
	::= 15896

    vcExceedLowerThresholdIncrease25 TRAP-TYPE
	ENTERPRISE	network-device
	VARIABLES	{ vcValue, adminDateAndTime, adminNDTrapSeqNo,
			  vcIndex, vcType }
	DESCRIPTION	"This trap is generated when set
			vcExLoThresholdIncreaseTrapID equal 25 and
			vcValue is greater equal
			the lower threshold plus the lower hysteresis
			after vcExceedLowerThresholdDecrease is generated.
			namely, vcValue >= (vcTrapLowerThreshold +
			vcTrapLowerHysteresis)."
	::= 15897

    vcExceedLowerThresholdIncrease26 TRAP-TYPE
	ENTERPRISE	network-device
	VARIABLES	{ vcValue, adminDateAndTime, adminNDTrapSeqNo,
			  vcIndex, vcType }
	DESCRIPTION	"This trap is generated when set
			vcExLoThresholdIncreaseTrapID equal 26 and
			vcValue is greater equal
			the lower threshold plus the lower hysteresis
			after vcExceedLowerThresholdDecrease is generated.
			namely, vcValue >= (vcTrapLowerThreshold +
			vcTrapLowerHysteresis)."
	::= 15898

    vcExceedLowerThresholdIncrease27 TRAP-TYPE
	ENTERPRISE	network-device
	VARIABLES	{ vcValue, adminDateAndTime, adminNDTrapSeqNo,
			  vcIndex, vcType }
	DESCRIPTION	"This trap is generated when set
			vcExLoThresholdIncreaseTrapID equal 27 and
			vcValue is greater equal
			the lower threshold plus the lower hysteresis
			after vcExceedLowerThresholdDecrease is generated.
			namely, vcValue >= (vcTrapLowerThreshold +
			vcTrapLowerHysteresis)."
	::= 15899

    vcExceedLowerThresholdIncrease28 TRAP-TYPE
	ENTERPRISE	network-device
	VARIABLES	{ vcValue, adminDateAndTime, adminNDTrapSeqNo,
			  vcIndex, vcType }
	DESCRIPTION	"This trap is generated when set
			vcExLoThresholdIncreaseTrapID equal 28 and
			vcValue is greater equal
			the lower threshold plus the lower hysteresis
			after vcExceedLowerThresholdDecrease is generated.
			namely, vcValue >= (vcTrapLowerThreshold +
			vcTrapLowerHysteresis)."
	::= 15900

    vcExceedLowerThresholdIncrease29 TRAP-TYPE
	ENTERPRISE	network-device
	VARIABLES	{ vcValue, adminDateAndTime, adminNDTrapSeqNo,
			  vcIndex, vcType }
	DESCRIPTION	"This trap is generated when set
			vcExLoThresholdIncreaseTrapID equal 29 and
			vcValue is greater equal
			the lower threshold plus the lower hysteresis
			after vcExceedLowerThresholdDecrease is generated.
			namely, vcValue >= (vcTrapLowerThreshold +
			vcTrapLowerHysteresis)."
	::= 15901

    vcExceedLowerThresholdIncrease30 TRAP-TYPE
	ENTERPRISE	network-device
	VARIABLES	{ vcValue, adminDateAndTime, adminNDTrapSeqNo,
			  vcIndex, vcType }
	DESCRIPTION	"This trap is generated when set
			vcExLoThresholdIncreaseTrapID equal 30 and
			vcValue is greater equal
			the lower threshold plus the lower hysteresis
			after vcExceedLowerThresholdDecrease is generated.
			namely, vcValue >= (vcTrapLowerThreshold +
			vcTrapLowerHysteresis)."
	::= 15902

    vcExceedLowerThresholdIncrease31 TRAP-TYPE
	ENTERPRISE	network-device
	VARIABLES	{ vcValue, adminDateAndTime, adminNDTrapSeqNo,
			  vcIndex, vcType }
	DESCRIPTION	"This trap is generated when set
			vcExLoThresholdIncreaseTrapID equal 31 and
			vcValue is greater equal
			the lower threshold plus the lower hysteresis
			after vcExceedLowerThresholdDecrease is generated.
			namely, vcValue >= (vcTrapLowerThreshold +
			vcTrapLowerHysteresis)."
	::= 15903

    vcExceedLowerThresholdIncrease32 TRAP-TYPE
	ENTERPRISE	network-device
	VARIABLES	{ vcValue, adminDateAndTime, adminNDTrapSeqNo,
			  vcIndex, vcType }
	DESCRIPTION	"This trap is generated when set
			vcExLoThresholdIncreaseTrapID equal 32 and
			vcValue is greater equal
			the lower threshold plus the lower hysteresis
			after vcExceedLowerThresholdDecrease is generated.
			namely, vcValue >= (vcTrapLowerThreshold +
			vcTrapLowerHysteresis)."
	::= 15904

    vcExceedLowerThresholdIncrease33 TRAP-TYPE
	ENTERPRISE	network-device
	VARIABLES	{ vcValue, adminDateAndTime, adminNDTrapSeqNo,
			  vcIndex, vcType }
	DESCRIPTION	"This trap is generated when set
			vcExLoThresholdIncreaseTrapID equal 33 and
			vcValue is greater equal
			the lower threshold plus the lower hysteresis
			after vcExceedLowerThresholdDecrease is generated.
			namely, vcValue >= (vcTrapLowerThreshold +
			vcTrapLowerHysteresis)."
	::= 15905

    vcExceedLowerThresholdIncrease34 TRAP-TYPE
	ENTERPRISE	network-device
	VARIABLES	{ vcValue, adminDateAndTime, adminNDTrapSeqNo,
			  vcIndex, vcType }
	DESCRIPTION	"This trap is generated when set
			vcExLoThresholdIncreaseTrapID equal 34 and
			vcValue is greater equal
			the lower threshold plus the lower hysteresis
			after vcExceedLowerThresholdDecrease is generated.
			namely, vcValue >= (vcTrapLowerThreshold +
			vcTrapLowerHysteresis)."
	::= 15906

    vcExceedLowerThresholdIncrease35 TRAP-TYPE
	ENTERPRISE	network-device
	VARIABLES	{ vcValue, adminDateAndTime, adminNDTrapSeqNo,
			  vcIndex, vcType }
	DESCRIPTION	"This trap is generated when set
			vcExLoThresholdIncreaseTrapID equal 35 and
			vcValue is greater equal
			the lower threshold plus the lower hysteresis
			after vcExceedLowerThresholdDecrease is generated.
			namely, vcValue >= (vcTrapLowerThreshold +
			vcTrapLowerHysteresis)."
	::= 15907

    vcExceedLowerThresholdIncrease36 TRAP-TYPE
	ENTERPRISE	network-device
	VARIABLES	{ vcValue, adminDateAndTime, adminNDTrapSeqNo,
			  vcIndex, vcType }
	DESCRIPTION	"This trap is generated when set
			vcExLoThresholdIncreaseTrapID equal 36 and
			vcValue is greater equal
			the lower threshold plus the lower hysteresis
			after vcExceedLowerThresholdDecrease is generated.
			namely, vcValue >= (vcTrapLowerThreshold +
			vcTrapLowerHysteresis)."
	::= 15908

    vcExceedLowerThresholdIncrease37 TRAP-TYPE
	ENTERPRISE	network-device
	VARIABLES	{ vcValue, adminDateAndTime, adminNDTrapSeqNo,
			  vcIndex, vcType }
	DESCRIPTION	"This trap is generated when set
			vcExLoThresholdIncreaseTrapID equal 37 and
			vcValue is greater equal
			the lower threshold plus the lower hysteresis
			after vcExceedLowerThresholdDecrease is generated.
			namely, vcValue >= (vcTrapLowerThreshold +
			vcTrapLowerHysteresis)."
	::= 15909

    vcExceedLowerThresholdIncrease38 TRAP-TYPE
	ENTERPRISE	network-device
	VARIABLES	{ vcValue, adminDateAndTime, adminNDTrapSeqNo,
			  vcIndex, vcType }
	DESCRIPTION	"This trap is generated when set
			vcExLoThresholdIncreaseTrapID equal 38 and
			vcValue is greater equal
			the lower threshold plus the lower hysteresis
			after vcExceedLowerThresholdDecrease is generated.
			namely, vcValue >= (vcTrapLowerThreshold +
			vcTrapLowerHysteresis)."
	::= 15910

    vcExceedLowerThresholdIncrease39 TRAP-TYPE
	ENTERPRISE	network-device
	VARIABLES	{ vcValue, adminDateAndTime, adminNDTrapSeqNo,
			  vcIndex, vcType }
	DESCRIPTION	"This trap is generated when set
			vcExLoThresholdIncreaseTrapID equal 39 and
			vcValue is greater equal
			the lower threshold plus the lower hysteresis
			after vcExceedLowerThresholdDecrease is generated.
			namely, vcValue >= (vcTrapLowerThreshold +
			vcTrapLowerHysteresis)."
	::= 15911

    vcExceedLowerThresholdIncrease40 TRAP-TYPE
	ENTERPRISE	network-device
	VARIABLES	{ vcValue, adminDateAndTime, adminNDTrapSeqNo,
			  vcIndex, vcType }
	DESCRIPTION	"This trap is generated when set
			vcExLoThresholdIncreaseTrapID equal 40 and
			vcValue is greater equal
			the lower threshold plus the lower hysteresis
			after vcExceedLowerThresholdDecrease is generated.
			namely, vcValue >= (vcTrapLowerThreshold +
			vcTrapLowerHysteresis)."
	::= 15912

    vcExceedLowerThresholdIncrease41 TRAP-TYPE
	ENTERPRISE	network-device
	VARIABLES	{ vcValue, adminDateAndTime, adminNDTrapSeqNo,
			  vcIndex, vcType }
	DESCRIPTION	"This trap is generated when set
			vcExLoThresholdIncreaseTrapID equal 41 and
			vcValue is greater equal
			the lower threshold plus the lower hysteresis
			after vcExceedLowerThresholdDecrease is generated.
			namely, vcValue >= (vcTrapLowerThreshold +
			vcTrapLowerHysteresis)."
	::= 15913

    vcExceedLowerThresholdIncrease42 TRAP-TYPE
	ENTERPRISE	network-device
	VARIABLES	{ vcValue, adminDateAndTime, adminNDTrapSeqNo,
			  vcIndex, vcType }
	DESCRIPTION	"This trap is generated when set
			vcExLoThresholdIncreaseTrapID equal 42 and
			vcValue is greater equal
			the lower threshold plus the lower hysteresis
			after vcExceedLowerThresholdDecrease is generated.
			namely, vcValue >= (vcTrapLowerThreshold +
			vcTrapLowerHysteresis)."
	::= 15914

    vcExceedLowerThresholdIncrease43 TRAP-TYPE
	ENTERPRISE	network-device
	VARIABLES	{ vcValue, adminDateAndTime, adminNDTrapSeqNo,
			  vcIndex, vcType }
	DESCRIPTION	"This trap is generated when set
			vcExLoThresholdIncreaseTrapID equal 43 and
			vcValue is greater equal
			the lower threshold plus the lower hysteresis
			after vcExceedLowerThresholdDecrease is generated.
			namely, vcValue >= (vcTrapLowerThreshold +
			vcTrapLowerHysteresis)."
	::= 15915

    vcExceedLowerThresholdIncrease44 TRAP-TYPE
	ENTERPRISE	network-device
	VARIABLES	{ vcValue, adminDateAndTime, adminNDTrapSeqNo,
			  vcIndex, vcType }
	DESCRIPTION	"This trap is generated when set
			vcExLoThresholdIncreaseTrapID equal 44 and
			vcValue is greater equal
			the lower threshold plus the lower hysteresis
			after vcExceedLowerThresholdDecrease is generated.
			namely, vcValue >= (vcTrapLowerThreshold +
			vcTrapLowerHysteresis)."
	::= 15916

    vcExceedLowerThresholdIncrease45 TRAP-TYPE
	ENTERPRISE	network-device
	VARIABLES	{ vcValue, adminDateAndTime, adminNDTrapSeqNo,
			  vcIndex, vcType }
	DESCRIPTION	"This trap is generated when set
			vcExLoThresholdIncreaseTrapID equal 45 and
			vcValue is greater equal
			the lower threshold plus the lower hysteresis
			after vcExceedLowerThresholdDecrease is generated.
			namely, vcValue >= (vcTrapLowerThreshold +
			vcTrapLowerHysteresis)."
	::= 15917

    vcExceedLowerThresholdIncrease46 TRAP-TYPE
	ENTERPRISE	network-device
	VARIABLES	{ vcValue, adminDateAndTime, adminNDTrapSeqNo,
			  vcIndex, vcType }
	DESCRIPTION	"This trap is generated when set
			vcExLoThresholdIncreaseTrapID equal 46 and
			vcValue is greater equal
			the lower threshold plus the lower hysteresis
			after vcExceedLowerThresholdDecrease is generated.
			namely, vcValue >= (vcTrapLowerThreshold +
			vcTrapLowerHysteresis)."
	::= 15918

    vcExceedLowerThresholdIncrease47 TRAP-TYPE
	ENTERPRISE	network-device
	VARIABLES	{ vcValue, adminDateAndTime, adminNDTrapSeqNo,
			  vcIndex, vcType }
	DESCRIPTION	"This trap is generated when set
			vcExLoThresholdIncreaseTrapID equal 47 and
			vcValue is greater equal
			the lower threshold plus the lower hysteresis
			after vcExceedLowerThresholdDecrease is generated.
			namely, vcValue >= (vcTrapLowerThreshold +
			vcTrapLowerHysteresis)."
	::= 15919

    vcExceedLowerThresholdIncrease48 TRAP-TYPE
	ENTERPRISE	network-device
	VARIABLES	{ vcValue, adminDateAndTime, adminNDTrapSeqNo,
			  vcIndex, vcType }
	DESCRIPTION	"This trap is generated when set
			vcExLoThresholdIncreaseTrapID equal 48 and
			vcValue is greater equal
			the lower threshold plus the lower hysteresis
			after vcExceedLowerThresholdDecrease is generated.
			namely, vcValue >= (vcTrapLowerThreshold +
			vcTrapLowerHysteresis)."
	::= 15920

    vcExceedLowerThresholdIncrease49 TRAP-TYPE
	ENTERPRISE	network-device
	VARIABLES	{ vcValue, adminDateAndTime, adminNDTrapSeqNo,
			  vcIndex, vcType }
	DESCRIPTION	"This trap is generated when set
			vcExLoThresholdIncreaseTrapID equal 49 and
			vcValue is greater equal
			the lower threshold plus the lower hysteresis
			after vcExceedLowerThresholdDecrease is generated.
			namely, vcValue >= (vcTrapLowerThreshold +
			vcTrapLowerHysteresis)."
	::= 15921

    vcExceedLowerThresholdIncrease50 TRAP-TYPE
	ENTERPRISE	network-device
	VARIABLES	{ vcValue, adminDateAndTime, adminNDTrapSeqNo,
			  vcIndex, vcType }
	DESCRIPTION	"This trap is generated when set
			vcExLoThresholdIncreaseTrapID equal 50 and
			vcValue is greater equal
			the lower threshold plus the lower hysteresis
			after vcExceedLowerThresholdDecrease is generated.
			namely, vcValue >= (vcTrapLowerThreshold +
			vcTrapLowerHysteresis)."
	::= 15922

    vcExceedLowerThresholdIncrease51 TRAP-TYPE
	ENTERPRISE	network-device
	VARIABLES	{ vcValue, adminDateAndTime, adminNDTrapSeqNo,
			  vcIndex, vcType }
	DESCRIPTION	"This trap is generated when set
			vcExLoThresholdIncreaseTrapID equal 51 and
			vcValue is greater equal
			the lower threshold plus the lower hysteresis
			after vcExceedLowerThresholdDecrease is generated.
			namely, vcValue >= (vcTrapLowerThreshold +
			vcTrapLowerHysteresis)."
	::= 15923

    vcExceedLowerThresholdIncrease52 TRAP-TYPE
	ENTERPRISE	network-device
	VARIABLES	{ vcValue, adminDateAndTime, adminNDTrapSeqNo,
			  vcIndex, vcType }
	DESCRIPTION	"This trap is generated when set
			vcExLoThresholdIncreaseTrapID equal 52 and
			vcValue is greater equal
			the lower threshold plus the lower hysteresis
			after vcExceedLowerThresholdDecrease is generated.
			namely, vcValue >= (vcTrapLowerThreshold +
			vcTrapLowerHysteresis)."
	::= 15924

    vcExceedLowerThresholdIncrease53 TRAP-TYPE
	ENTERPRISE	network-device
	VARIABLES	{ vcValue, adminDateAndTime, adminNDTrapSeqNo,
			  vcIndex, vcType }
	DESCRIPTION	"This trap is generated when set
			vcExLoThresholdIncreaseTrapID equal 53 and
			vcValue is greater equal
			the lower threshold plus the lower hysteresis
			after vcExceedLowerThresholdDecrease is generated.
			namely, vcValue >= (vcTrapLowerThreshold +
			vcTrapLowerHysteresis)."
	::= 15925

    vcExceedLowerThresholdIncrease54 TRAP-TYPE
	ENTERPRISE	network-device
	VARIABLES	{ vcValue, adminDateAndTime, adminNDTrapSeqNo,
			  vcIndex, vcType }
	DESCRIPTION	"This trap is generated when set
			vcExLoThresholdIncreaseTrapID equal 54 and
			vcValue is greater equal
			the lower threshold plus the lower hysteresis
			after vcExceedLowerThresholdDecrease is generated.
			namely, vcValue >= (vcTrapLowerThreshold +
			vcTrapLowerHysteresis)."
	::= 15926

    vcExceedLowerThresholdIncrease55 TRAP-TYPE
	ENTERPRISE	network-device
	VARIABLES	{ vcValue, adminDateAndTime, adminNDTrapSeqNo,
			  vcIndex, vcType }
	DESCRIPTION	"This trap is generated when set
			vcExLoThresholdIncreaseTrapID equal 55 and
			vcValue is greater equal
			the lower threshold plus the lower hysteresis
			after vcExceedLowerThresholdDecrease is generated.
			namely, vcValue >= (vcTrapLowerThreshold +
			vcTrapLowerHysteresis)."
	::= 15927

    vcExceedLowerThresholdIncrease56 TRAP-TYPE
	ENTERPRISE	network-device
	VARIABLES	{ vcValue, adminDateAndTime, adminNDTrapSeqNo,
			  vcIndex, vcType }
	DESCRIPTION	"This trap is generated when set
			vcExLoThresholdIncreaseTrapID equal 56 and
			vcValue is greater equal
			the lower threshold plus the lower hysteresis
			after vcExceedLowerThresholdDecrease is generated.
			namely, vcValue >= (vcTrapLowerThreshold +
			vcTrapLowerHysteresis)."
	::= 15928

    vcExceedLowerThresholdIncrease57 TRAP-TYPE
	ENTERPRISE	network-device
	VARIABLES	{ vcValue, adminDateAndTime, adminNDTrapSeqNo,
			  vcIndex, vcType }
	DESCRIPTION	"This trap is generated when set
			vcExLoThresholdIncreaseTrapID equal 57 and
			vcValue is greater equal
			the lower threshold plus the lower hysteresis
			after vcExceedLowerThresholdDecrease is generated.
			namely, vcValue >= (vcTrapLowerThreshold +
			vcTrapLowerHysteresis)."
	::= 15929

    vcExceedLowerThresholdIncrease58 TRAP-TYPE
	ENTERPRISE	network-device
	VARIABLES	{ vcValue, adminDateAndTime, adminNDTrapSeqNo,
			  vcIndex, vcType }
	DESCRIPTION	"This trap is generated when set
			vcExLoThresholdIncreaseTrapID equal 58 and
			vcValue is greater equal
			the lower threshold plus the lower hysteresis
			after vcExceedLowerThresholdDecrease is generated.
			namely, vcValue >= (vcTrapLowerThreshold +
			vcTrapLowerHysteresis)."
	::= 15930

    vcExceedLowerThresholdIncrease59 TRAP-TYPE
	ENTERPRISE	network-device
	VARIABLES	{ vcValue, adminDateAndTime, adminNDTrapSeqNo,
			  vcIndex, vcType }
	DESCRIPTION	"This trap is generated when set
			vcExLoThresholdIncreaseTrapID equal 59 and
			vcValue is greater equal
			the lower threshold plus the lower hysteresis
			after vcExceedLowerThresholdDecrease is generated.
			namely, vcValue >= (vcTrapLowerThreshold +
			vcTrapLowerHysteresis)."
	::= 15931

    vcExceedLowerThresholdIncrease60 TRAP-TYPE
	ENTERPRISE	network-device
	VARIABLES	{ vcValue, adminDateAndTime, adminNDTrapSeqNo,
			  vcIndex, vcType }
	DESCRIPTION	"This trap is generated when set
			vcExLoThresholdIncreaseTrapID equal 60 and
			vcValue is greater equal
			the lower threshold plus the lower hysteresis
			after vcExceedLowerThresholdDecrease is generated.
			namely, vcValue >= (vcTrapLowerThreshold +
			vcTrapLowerHysteresis)."
	::= 15932

    vcExceedLowerThresholdIncrease61 TRAP-TYPE
	ENTERPRISE	network-device
	VARIABLES	{ vcValue, adminDateAndTime, adminNDTrapSeqNo,
			  vcIndex, vcType }
	DESCRIPTION	"This trap is generated when set
			vcExLoThresholdIncreaseTrapID equal 61 and
			vcValue is greater equal
			the lower threshold plus the lower hysteresis
			after vcExceedLowerThresholdDecrease is generated.
			namely, vcValue >= (vcTrapLowerThreshold +
			vcTrapLowerHysteresis)."
	::= 15933

    vcExceedLowerThresholdIncrease62 TRAP-TYPE
	ENTERPRISE	network-device
	VARIABLES	{ vcValue, adminDateAndTime, adminNDTrapSeqNo,
			  vcIndex, vcType }
	DESCRIPTION	"This trap is generated when set
			vcExLoThresholdIncreaseTrapID equal 62 and
			vcValue is greater equal
			the lower threshold plus the lower hysteresis
			after vcExceedLowerThresholdDecrease is generated.
			namely, vcValue >= (vcTrapLowerThreshold +
			vcTrapLowerHysteresis)."
	::= 15934

    vcExceedLowerThresholdIncrease63 TRAP-TYPE
	ENTERPRISE	network-device
	VARIABLES	{ vcValue, adminDateAndTime, adminNDTrapSeqNo,
			  vcIndex, vcType }
	DESCRIPTION	"This trap is generated when set
			vcExLoThresholdIncreaseTrapID equal 63 and
			vcValue is greater equal
			the lower threshold plus the lower hysteresis
			after vcExceedLowerThresholdDecrease is generated.
			namely, vcValue >= (vcTrapLowerThreshold +
			vcTrapLowerHysteresis)."
	::= 15935

    vcExceedLowerThresholdIncrease64 TRAP-TYPE
	ENTERPRISE	network-device
	VARIABLES	{ vcValue, adminDateAndTime, adminNDTrapSeqNo,
			  vcIndex, vcType }
	DESCRIPTION	"This trap is generated when set
			vcExLoThresholdIncreaseTrapID equal 64 and
			vcValue is greater equal
			the lower threshold plus the lower hysteresis
			after vcExceedLowerThresholdDecrease is generated.
			namely, vcValue >= (vcTrapLowerThreshold +
			vcTrapLowerHysteresis)."
	::= 15936

    vcExceedLowerThresholdIncrease65 TRAP-TYPE
	ENTERPRISE	network-device
	VARIABLES	{ vcValue, adminDateAndTime, adminNDTrapSeqNo,
			  vcIndex, vcType }
	DESCRIPTION	"This trap is generated when set
			vcExLoThresholdIncreaseTrapID equal 65 and
			vcValue is greater equal
			the lower threshold plus the lower hysteresis
			after vcExceedLowerThresholdDecrease is generated.
			namely, vcValue >= (vcTrapLowerThreshold +
			vcTrapLowerHysteresis)."
	::= 15937

    vcExceedLowerThresholdIncrease66 TRAP-TYPE
	ENTERPRISE	network-device
	VARIABLES	{ vcValue, adminDateAndTime, adminNDTrapSeqNo,
			  vcIndex, vcType }
	DESCRIPTION	"This trap is generated when set
			vcExLoThresholdIncreaseTrapID equal 66 and
			vcValue is greater equal
			the lower threshold plus the lower hysteresis
			after vcExceedLowerThresholdDecrease is generated.
			namely, vcValue >= (vcTrapLowerThreshold +
			vcTrapLowerHysteresis)."
	::= 15938

    vcExceedLowerThresholdIncrease67 TRAP-TYPE
	ENTERPRISE	network-device
	VARIABLES	{ vcValue, adminDateAndTime, adminNDTrapSeqNo,
			  vcIndex, vcType }
	DESCRIPTION	"This trap is generated when set
			vcExLoThresholdIncreaseTrapID equal 67 and
			vcValue is greater equal
			the lower threshold plus the lower hysteresis
			after vcExceedLowerThresholdDecrease is generated.
			namely, vcValue >= (vcTrapLowerThreshold +
			vcTrapLowerHysteresis)."
	::= 15939

    vcExceedLowerThresholdIncrease68 TRAP-TYPE
	ENTERPRISE	network-device
	VARIABLES	{ vcValue, adminDateAndTime, adminNDTrapSeqNo,
			  vcIndex, vcType }
	DESCRIPTION	"This trap is generated when set
			vcExLoThresholdIncreaseTrapID equal 68 and
			vcValue is greater equal
			the lower threshold plus the lower hysteresis
			after vcExceedLowerThresholdDecrease is generated.
			namely, vcValue >= (vcTrapLowerThreshold +
			vcTrapLowerHysteresis)."
	::= 15940

    vcExceedLowerThresholdIncrease69 TRAP-TYPE
	ENTERPRISE	network-device
	VARIABLES	{ vcValue, adminDateAndTime, adminNDTrapSeqNo,
			  vcIndex, vcType }
	DESCRIPTION	"This trap is generated when set
			vcExLoThresholdIncreaseTrapID equal 69 and
			vcValue is greater equal
			the lower threshold plus the lower hysteresis
			after vcExceedLowerThresholdDecrease is generated.
			namely, vcValue >= (vcTrapLowerThreshold +
			vcTrapLowerHysteresis)."
	::= 15941

    vcExceedLowerThresholdIncrease70 TRAP-TYPE
	ENTERPRISE	network-device
	VARIABLES	{ vcValue, adminDateAndTime, adminNDTrapSeqNo,
			  vcIndex, vcType }
	DESCRIPTION	"This trap is generated when set
			vcExLoThresholdIncreaseTrapID equal 70 and
			vcValue is greater equal
			the lower threshold plus the lower hysteresis
			after vcExceedLowerThresholdDecrease is generated.
			namely, vcValue >= (vcTrapLowerThreshold +
			vcTrapLowerHysteresis)."
	::= 15942

    vcExceedLowerThresholdIncrease71 TRAP-TYPE
	ENTERPRISE	network-device
	VARIABLES	{ vcValue, adminDateAndTime, adminNDTrapSeqNo,
			  vcIndex, vcType }
	DESCRIPTION	"This trap is generated when set
			vcExLoThresholdIncreaseTrapID equal 71 and
			vcValue is greater equal
			the lower threshold plus the lower hysteresis
			after vcExceedLowerThresholdDecrease is generated.
			namely, vcValue >= (vcTrapLowerThreshold +
			vcTrapLowerHysteresis)."
	::= 15943

    vcExceedLowerThresholdIncrease72 TRAP-TYPE
	ENTERPRISE	network-device
	VARIABLES	{ vcValue, adminDateAndTime, adminNDTrapSeqNo,
			  vcIndex, vcType }
	DESCRIPTION	"This trap is generated when set
			vcExLoThresholdIncreaseTrapID equal 72 and
			vcValue is greater equal
			the lower threshold plus the lower hysteresis
			after vcExceedLowerThresholdDecrease is generated.
			namely, vcValue >= (vcTrapLowerThreshold +
			vcTrapLowerHysteresis)."
	::= 15944

    vcExceedLowerThresholdIncrease73 TRAP-TYPE
	ENTERPRISE	network-device
	VARIABLES	{ vcValue, adminDateAndTime, adminNDTrapSeqNo,
			  vcIndex, vcType }
	DESCRIPTION	"This trap is generated when set
			vcExLoThresholdIncreaseTrapID equal 73 and
			vcValue is greater equal
			the lower threshold plus the lower hysteresis
			after vcExceedLowerThresholdDecrease is generated.
			namely, vcValue >= (vcTrapLowerThreshold +
			vcTrapLowerHysteresis)."
	::= 15945

    vcExceedLowerThresholdIncrease74 TRAP-TYPE
	ENTERPRISE	network-device
	VARIABLES	{ vcValue, adminDateAndTime, adminNDTrapSeqNo,
			  vcIndex, vcType }
	DESCRIPTION	"This trap is generated when set
			vcExLoThresholdIncreaseTrapID equal 74 and
			vcValue is greater equal
			the lower threshold plus the lower hysteresis
			after vcExceedLowerThresholdDecrease is generated.
			namely, vcValue >= (vcTrapLowerThreshold +
			vcTrapLowerHysteresis)."
	::= 15946

    vcExceedLowerThresholdIncrease75 TRAP-TYPE
	ENTERPRISE	network-device
	VARIABLES	{ vcValue, adminDateAndTime, adminNDTrapSeqNo,
			  vcIndex, vcType }
	DESCRIPTION	"This trap is generated when set
			vcExLoThresholdIncreaseTrapID equal 75 and
			vcValue is greater equal
			the lower threshold plus the lower hysteresis
			after vcExceedLowerThresholdDecrease is generated.
			namely, vcValue >= (vcTrapLowerThreshold +
			vcTrapLowerHysteresis)."
	::= 15947

    vcExceedLowerThresholdIncrease76 TRAP-TYPE
	ENTERPRISE	network-device
	VARIABLES	{ vcValue, adminDateAndTime, adminNDTrapSeqNo,
			  vcIndex, vcType }
	DESCRIPTION	"This trap is generated when set
			vcExLoThresholdIncreaseTrapID equal 76 and
			vcValue is greater equal
			the lower threshold plus the lower hysteresis
			after vcExceedLowerThresholdDecrease is generated.
			namely, vcValue >= (vcTrapLowerThreshold +
			vcTrapLowerHysteresis)."
	::= 15948

    vcExceedLowerThresholdIncrease77 TRAP-TYPE
	ENTERPRISE	network-device
	VARIABLES	{ vcValue, adminDateAndTime, adminNDTrapSeqNo,
			  vcIndex, vcType }
	DESCRIPTION	"This trap is generated when set
			vcExLoThresholdIncreaseTrapID equal 77 and
			vcValue is greater equal
			the lower threshold plus the lower hysteresis
			after vcExceedLowerThresholdDecrease is generated.
			namely, vcValue >= (vcTrapLowerThreshold +
			vcTrapLowerHysteresis)."
	::= 15949

    vcExceedLowerThresholdIncrease78 TRAP-TYPE
	ENTERPRISE	network-device
	VARIABLES	{ vcValue, adminDateAndTime, adminNDTrapSeqNo,
			  vcIndex, vcType }
	DESCRIPTION	"This trap is generated when set
			vcExLoThresholdIncreaseTrapID equal 78 and
			vcValue is greater equal
			the lower threshold plus the lower hysteresis
			after vcExceedLowerThresholdDecrease is generated.
			namely, vcValue >= (vcTrapLowerThreshold +
			vcTrapLowerHysteresis)."
	::= 15950

    vcExceedLowerThresholdIncrease79 TRAP-TYPE
	ENTERPRISE	network-device
	VARIABLES	{ vcValue, adminDateAndTime, adminNDTrapSeqNo,
			  vcIndex, vcType }
	DESCRIPTION	"This trap is generated when set
			vcExLoThresholdIncreaseTrapID equal 79 and
			vcValue is greater equal
			the lower threshold plus the lower hysteresis
			after vcExceedLowerThresholdDecrease is generated.
			namely, vcValue >= (vcTrapLowerThreshold +
			vcTrapLowerHysteresis)."
	::= 15951

    vcExceedLowerThresholdIncrease80 TRAP-TYPE
	ENTERPRISE	network-device
	VARIABLES	{ vcValue, adminDateAndTime, adminNDTrapSeqNo,
			  vcIndex, vcType }
	DESCRIPTION	"This trap is generated when set
			vcExLoThresholdIncreaseTrapID equal 80 and
			vcValue is greater equal
			the lower threshold plus the lower hysteresis
			after vcExceedLowerThresholdDecrease is generated.
			namely, vcValue >= (vcTrapLowerThreshold +
			vcTrapLowerHysteresis)."
	::= 15952

    vcExceedLowerThresholdIncrease81 TRAP-TYPE
	ENTERPRISE	network-device
	VARIABLES	{ vcValue, adminDateAndTime, adminNDTrapSeqNo,
			  vcIndex, vcType }
	DESCRIPTION	"This trap is generated when set
			vcExLoThresholdIncreaseTrapID equal 81 and
			vcValue is greater equal
			the lower threshold plus the lower hysteresis
			after vcExceedLowerThresholdDecrease is generated.
			namely, vcValue >= (vcTrapLowerThreshold +
			vcTrapLowerHysteresis)."
	::= 15953

    vcExceedLowerThresholdIncrease82 TRAP-TYPE
	ENTERPRISE	network-device
	VARIABLES	{ vcValue, adminDateAndTime, adminNDTrapSeqNo,
			  vcIndex, vcType }
	DESCRIPTION	"This trap is generated when set
			vcExLoThresholdIncreaseTrapID equal 82 and
			vcValue is greater equal
			the lower threshold plus the lower hysteresis
			after vcExceedLowerThresholdDecrease is generated.
			namely, vcValue >= (vcTrapLowerThreshold +
			vcTrapLowerHysteresis)."
	::= 15954

    vcExceedLowerThresholdIncrease83 TRAP-TYPE
	ENTERPRISE	network-device
	VARIABLES	{ vcValue, adminDateAndTime, adminNDTrapSeqNo,
			  vcIndex, vcType }
	DESCRIPTION	"This trap is generated when set
			vcExLoThresholdIncreaseTrapID equal 83 and
			vcValue is greater equal
			the lower threshold plus the lower hysteresis
			after vcExceedLowerThresholdDecrease is generated.
			namely, vcValue >= (vcTrapLowerThreshold +
			vcTrapLowerHysteresis)."
	::= 15955

    vcExceedLowerThresholdIncrease84 TRAP-TYPE
	ENTERPRISE	network-device
	VARIABLES	{ vcValue, adminDateAndTime, adminNDTrapSeqNo,
			  vcIndex, vcType }
	DESCRIPTION	"This trap is generated when set
			vcExLoThresholdIncreaseTrapID equal 84 and
			vcValue is greater equal
			the lower threshold plus the lower hysteresis
			after vcExceedLowerThresholdDecrease is generated.
			namely, vcValue >= (vcTrapLowerThreshold +
			vcTrapLowerHysteresis)."
	::= 15956

    vcExceedLowerThresholdIncrease85 TRAP-TYPE
	ENTERPRISE	network-device
	VARIABLES	{ vcValue, adminDateAndTime, adminNDTrapSeqNo,
			  vcIndex, vcType }
	DESCRIPTION	"This trap is generated when set
			vcExLoThresholdIncreaseTrapID equal 85 and
			vcValue is greater equal
			the lower threshold plus the lower hysteresis
			after vcExceedLowerThresholdDecrease is generated.
			namely, vcValue >= (vcTrapLowerThreshold +
			vcTrapLowerHysteresis)."
	::= 15957

    vcExceedLowerThresholdIncrease86 TRAP-TYPE
	ENTERPRISE	network-device
	VARIABLES	{ vcValue, adminDateAndTime, adminNDTrapSeqNo,
			  vcIndex, vcType }
	DESCRIPTION	"This trap is generated when set
			vcExLoThresholdIncreaseTrapID equal 86 and
			vcValue is greater equal
			the lower threshold plus the lower hysteresis
			after vcExceedLowerThresholdDecrease is generated.
			namely, vcValue >= (vcTrapLowerThreshold +
			vcTrapLowerHysteresis)."
	::= 15958

    vcExceedLowerThresholdIncrease87 TRAP-TYPE
	ENTERPRISE	network-device
	VARIABLES	{ vcValue, adminDateAndTime, adminNDTrapSeqNo,
			  vcIndex, vcType }
	DESCRIPTION	"This trap is generated when set
			vcExLoThresholdIncreaseTrapID equal 87 and
			vcValue is greater equal
			the lower threshold plus the lower hysteresis
			after vcExceedLowerThresholdDecrease is generated.
			namely, vcValue >= (vcTrapLowerThreshold +
			vcTrapLowerHysteresis)."
	::= 15959

    vcExceedLowerThresholdIncrease88 TRAP-TYPE
	ENTERPRISE	network-device
	VARIABLES	{ vcValue, adminDateAndTime, adminNDTrapSeqNo,
			  vcIndex, vcType }
	DESCRIPTION	"This trap is generated when set
			vcExLoThresholdIncreaseTrapID equal 88 and
			vcValue is greater equal
			the lower threshold plus the lower hysteresis
			after vcExceedLowerThresholdDecrease is generated.
			namely, vcValue >= (vcTrapLowerThreshold +
			vcTrapLowerHysteresis)."
	::= 15960

    vcExceedLowerThresholdIncrease89 TRAP-TYPE
	ENTERPRISE	network-device
	VARIABLES	{ vcValue, adminDateAndTime, adminNDTrapSeqNo,
			  vcIndex, vcType }
	DESCRIPTION	"This trap is generated when set
			vcExLoThresholdIncreaseTrapID equal 89 and
			vcValue is greater equal
			the lower threshold plus the lower hysteresis
			after vcExceedLowerThresholdDecrease is generated.
			namely, vcValue >= (vcTrapLowerThreshold +
			vcTrapLowerHysteresis)."
	::= 15961

    vcExceedLowerThresholdIncrease90 TRAP-TYPE
	ENTERPRISE	network-device
	VARIABLES	{ vcValue, adminDateAndTime, adminNDTrapSeqNo,
			  vcIndex, vcType }
	DESCRIPTION	"This trap is generated when set
			vcExLoThresholdIncreaseTrapID equal 90 and
			vcValue is greater equal
			the lower threshold plus the lower hysteresis
			after vcExceedLowerThresholdDecrease is generated.
			namely, vcValue >= (vcTrapLowerThreshold +
			vcTrapLowerHysteresis)."
	::= 15962

    vcExceedLowerThresholdIncrease91 TRAP-TYPE
	ENTERPRISE	network-device
	VARIABLES	{ vcValue, adminDateAndTime, adminNDTrapSeqNo,
			  vcIndex, vcType }
	DESCRIPTION	"This trap is generated when set
			vcExLoThresholdIncreaseTrapID equal 91 and
			vcValue is greater equal
			the lower threshold plus the lower hysteresis
			after vcExceedLowerThresholdDecrease is generated.
			namely, vcValue >= (vcTrapLowerThreshold +
			vcTrapLowerHysteresis)."
	::= 15963

    vcExceedLowerThresholdIncrease92 TRAP-TYPE
	ENTERPRISE	network-device
	VARIABLES	{ vcValue, adminDateAndTime, adminNDTrapSeqNo,
			  vcIndex, vcType }
	DESCRIPTION	"This trap is generated when set
			vcExLoThresholdIncreaseTrapID equal 92 and
			vcValue is greater equal
			the lower threshold plus the lower hysteresis
			after vcExceedLowerThresholdDecrease is generated.
			namely, vcValue >= (vcTrapLowerThreshold +
			vcTrapLowerHysteresis)."
	::= 15964

    vcExceedLowerThresholdIncrease93 TRAP-TYPE
	ENTERPRISE	network-device
	VARIABLES	{ vcValue, adminDateAndTime, adminNDTrapSeqNo,
			  vcIndex, vcType }
	DESCRIPTION	"This trap is generated when set
			vcExLoThresholdIncreaseTrapID equal 93 and
			vcValue is greater equal
			the lower threshold plus the lower hysteresis
			after vcExceedLowerThresholdDecrease is generated.
			namely, vcValue >= (vcTrapLowerThreshold +
			vcTrapLowerHysteresis)."
	::= 15965

    vcExceedLowerThresholdIncrease94 TRAP-TYPE
	ENTERPRISE	network-device
	VARIABLES	{ vcValue, adminDateAndTime, adminNDTrapSeqNo,
			  vcIndex, vcType }
	DESCRIPTION	"This trap is generated when set
			vcExLoThresholdIncreaseTrapID equal 94 and
			vcValue is greater equal
			the lower threshold plus the lower hysteresis
			after vcExceedLowerThresholdDecrease is generated.
			namely, vcValue >= (vcTrapLowerThreshold +
			vcTrapLowerHysteresis)."
	::= 15966

    vcExceedLowerThresholdIncrease95 TRAP-TYPE
	ENTERPRISE	network-device
	VARIABLES	{ vcValue, adminDateAndTime, adminNDTrapSeqNo,
			  vcIndex, vcType }
	DESCRIPTION	"This trap is generated when set
			vcExLoThresholdIncreaseTrapID equal 95 and
			vcValue is greater equal
			the lower threshold plus the lower hysteresis
			after vcExceedLowerThresholdDecrease is generated.
			namely, vcValue >= (vcTrapLowerThreshold +
			vcTrapLowerHysteresis)."
	::= 15967

    vcExceedLowerThresholdIncrease96 TRAP-TYPE
	ENTERPRISE	network-device
	VARIABLES	{ vcValue, adminDateAndTime, adminNDTrapSeqNo,
			  vcIndex, vcType }
	DESCRIPTION	"This trap is generated when set
			vcExLoThresholdIncreaseTrapID equal 96 and
			vcValue is greater equal
			the lower threshold plus the lower hysteresis
			after vcExceedLowerThresholdDecrease is generated.
			namely, vcValue >= (vcTrapLowerThreshold +
			vcTrapLowerHysteresis)."
	::= 15968

    vcExceedLowerThresholdIncrease97 TRAP-TYPE
	ENTERPRISE	network-device
	VARIABLES	{ vcValue, adminDateAndTime, adminNDTrapSeqNo,
			  vcIndex, vcType }
	DESCRIPTION	"This trap is generated when set
			vcExLoThresholdIncreaseTrapID equal 97 and
			vcValue is greater equal
			the lower threshold plus the lower hysteresis
			after vcExceedLowerThresholdDecrease is generated.
			namely, vcValue >= (vcTrapLowerThreshold +
			vcTrapLowerHysteresis)."
	::= 15969

    vcExceedLowerThresholdIncrease98 TRAP-TYPE
	ENTERPRISE	network-device
	VARIABLES	{ vcValue, adminDateAndTime, adminNDTrapSeqNo,
			  vcIndex, vcType }
	DESCRIPTION	"This trap is generated when set
			vcExLoThresholdIncreaseTrapID equal 98 and
			vcValue is greater equal
			the lower threshold plus the lower hysteresis
			after vcExceedLowerThresholdDecrease is generated.
			namely, vcValue >= (vcTrapLowerThreshold +
			vcTrapLowerHysteresis)."
	::= 15970

    vcExceedLowerThresholdIncrease99 TRAP-TYPE
	ENTERPRISE	network-device
	VARIABLES	{ vcValue, adminDateAndTime, adminNDTrapSeqNo,
			  vcIndex, vcType }
	DESCRIPTION	"This trap is generated when set
			vcExLoThresholdIncreaseTrapID equal 99 and
			vcValue is greater equal
			the lower threshold plus the lower hysteresis
			after vcExceedLowerThresholdDecrease is generated.
			namely, vcValue >= (vcTrapLowerThreshold +
			vcTrapLowerHysteresis)."
	::= 15971

    vcExceedLowerThresholdIncrease100 TRAP-TYPE
	ENTERPRISE	network-device
	VARIABLES	{ vcValue, adminDateAndTime, adminNDTrapSeqNo,
			  vcIndex, vcType }
	DESCRIPTION	"This trap is generated when set
			vcExLoThresholdIncreaseTrapID equal 100 and
			vcValue is greater equal
			the lower threshold plus the lower hysteresis
			after vcExceedLowerThresholdDecrease is generated.
			namely, vcValue >= (vcTrapLowerThreshold +
			vcTrapLowerHysteresis)."
	::= 15972

    vcExceedLowerThresholdIncrease101 TRAP-TYPE
	ENTERPRISE	network-device
	VARIABLES	{ vcValue, adminDateAndTime, adminNDTrapSeqNo,
			  vcIndex, vcType }
	DESCRIPTION	"This trap is generated when set
			vcExLoThresholdIncreaseTrapID equal 101 and
			vcValue is greater equal
			the lower threshold plus the lower hysteresis
			after vcExceedLowerThresholdDecrease is generated.
			namely, vcValue >= (vcTrapLowerThreshold +
			vcTrapLowerHysteresis)."
	::= 15973

    vcExceedLowerThresholdIncrease102 TRAP-TYPE
	ENTERPRISE	network-device
	VARIABLES	{ vcValue, adminDateAndTime, adminNDTrapSeqNo,
			  vcIndex, vcType }
	DESCRIPTION	"This trap is generated when set
			vcExLoThresholdIncreaseTrapID equal 102 and
			vcValue is greater equal
			the lower threshold plus the lower hysteresis
			after vcExceedLowerThresholdDecrease is generated.
			namely, vcValue >= (vcTrapLowerThreshold +
			vcTrapLowerHysteresis)."
	::= 15974

    vcExceedLowerThresholdIncrease103 TRAP-TYPE
	ENTERPRISE	network-device
	VARIABLES	{ vcValue, adminDateAndTime, adminNDTrapSeqNo,
			  vcIndex, vcType }
	DESCRIPTION	"This trap is generated when set
			vcExLoThresholdIncreaseTrapID equal 103 and
			vcValue is greater equal
			the lower threshold plus the lower hysteresis
			after vcExceedLowerThresholdDecrease is generated.
			namely, vcValue >= (vcTrapLowerThreshold +
			vcTrapLowerHysteresis)."
	::= 15975

    vcExceedLowerThresholdIncrease104 TRAP-TYPE
	ENTERPRISE	network-device
	VARIABLES	{ vcValue, adminDateAndTime, adminNDTrapSeqNo,
			  vcIndex, vcType }
	DESCRIPTION	"This trap is generated when set
			vcExLoThresholdIncreaseTrapID equal 104 and
			vcValue is greater equal
			the lower threshold plus the lower hysteresis
			after vcExceedLowerThresholdDecrease is generated.
			namely, vcValue >= (vcTrapLowerThreshold +
			vcTrapLowerHysteresis)."
	::= 15976

    vcExceedLowerThresholdIncrease105 TRAP-TYPE
	ENTERPRISE	network-device
	VARIABLES	{ vcValue, adminDateAndTime, adminNDTrapSeqNo,
			  vcIndex, vcType }
	DESCRIPTION	"This trap is generated when set
			vcExLoThresholdIncreaseTrapID equal 105 and
			vcValue is greater equal
			the lower threshold plus the lower hysteresis
			after vcExceedLowerThresholdDecrease is generated.
			namely, vcValue >= (vcTrapLowerThreshold +
			vcTrapLowerHysteresis)."
	::= 15977

    vcExceedLowerThresholdIncrease106 TRAP-TYPE
	ENTERPRISE	network-device
	VARIABLES	{ vcValue, adminDateAndTime, adminNDTrapSeqNo,
			  vcIndex, vcType }
	DESCRIPTION	"This trap is generated when set
			vcExLoThresholdIncreaseTrapID equal 106 and
			vcValue is greater equal
			the lower threshold plus the lower hysteresis
			after vcExceedLowerThresholdDecrease is generated.
			namely, vcValue >= (vcTrapLowerThreshold +
			vcTrapLowerHysteresis)."
	::= 15978

    vcExceedLowerThresholdIncrease107 TRAP-TYPE
	ENTERPRISE	network-device
	VARIABLES	{ vcValue, adminDateAndTime, adminNDTrapSeqNo,
			  vcIndex, vcType }
	DESCRIPTION	"This trap is generated when set
			vcExLoThresholdIncreaseTrapID equal 107 and
			vcValue is greater equal
			the lower threshold plus the lower hysteresis
			after vcExceedLowerThresholdDecrease is generated.
			namely, vcValue >= (vcTrapLowerThreshold +
			vcTrapLowerHysteresis)."
	::= 15979

    vcExceedLowerThresholdIncrease108 TRAP-TYPE
	ENTERPRISE	network-device
	VARIABLES	{ vcValue, adminDateAndTime, adminNDTrapSeqNo,
			  vcIndex, vcType }
	DESCRIPTION	"This trap is generated when set
			vcExLoThresholdIncreaseTrapID equal 108 and
			vcValue is greater equal
			the lower threshold plus the lower hysteresis
			after vcExceedLowerThresholdDecrease is generated.
			namely, vcValue >= (vcTrapLowerThreshold +
			vcTrapLowerHysteresis)."
	::= 15980

    vcExceedLowerThresholdIncrease109 TRAP-TYPE
	ENTERPRISE	network-device
	VARIABLES	{ vcValue, adminDateAndTime, adminNDTrapSeqNo,
			  vcIndex, vcType }
	DESCRIPTION	"This trap is generated when set
			vcExLoThresholdIncreaseTrapID equal 109 and
			vcValue is greater equal
			the lower threshold plus the lower hysteresis
			after vcExceedLowerThresholdDecrease is generated.
			namely, vcValue >= (vcTrapLowerThreshold +
			vcTrapLowerHysteresis)."
	::= 15981

    vcExceedLowerThresholdIncrease110 TRAP-TYPE
	ENTERPRISE	network-device
	VARIABLES	{ vcValue, adminDateAndTime, adminNDTrapSeqNo,
			  vcIndex, vcType }
	DESCRIPTION	"This trap is generated when set
			vcExLoThresholdIncreaseTrapID equal 110 and
			vcValue is greater equal
			the lower threshold plus the lower hysteresis
			after vcExceedLowerThresholdDecrease is generated.
			namely, vcValue >= (vcTrapLowerThreshold +
			vcTrapLowerHysteresis)."
	::= 15982

    vcExceedLowerThresholdIncrease111 TRAP-TYPE
	ENTERPRISE	network-device
	VARIABLES	{ vcValue, adminDateAndTime, adminNDTrapSeqNo,
			  vcIndex, vcType }
	DESCRIPTION	"This trap is generated when set
			vcExLoThresholdIncreaseTrapID equal 111 and
			vcValue is greater equal
			the lower threshold plus the lower hysteresis
			after vcExceedLowerThresholdDecrease is generated.
			namely, vcValue >= (vcTrapLowerThreshold +
			vcTrapLowerHysteresis)."
	::= 15983

    vcExceedLowerThresholdIncrease112 TRAP-TYPE
	ENTERPRISE	network-device
	VARIABLES	{ vcValue, adminDateAndTime, adminNDTrapSeqNo,
			  vcIndex, vcType }
	DESCRIPTION	"This trap is generated when set
			vcExLoThresholdIncreaseTrapID equal 112 and
			vcValue is greater equal
			the lower threshold plus the lower hysteresis
			after vcExceedLowerThresholdDecrease is generated.
			namely, vcValue >= (vcTrapLowerThreshold +
			vcTrapLowerHysteresis)."
	::= 15984

    vcExceedLowerThresholdIncrease113 TRAP-TYPE
	ENTERPRISE	network-device
	VARIABLES	{ vcValue, adminDateAndTime, adminNDTrapSeqNo,
			  vcIndex, vcType }
	DESCRIPTION	"This trap is generated when set
			vcExLoThresholdIncreaseTrapID equal 113 and
			vcValue is greater equal
			the lower threshold plus the lower hysteresis
			after vcExceedLowerThresholdDecrease is generated.
			namely, vcValue >= (vcTrapLowerThreshold +
			vcTrapLowerHysteresis)."
	::= 15985

    vcExceedLowerThresholdIncrease114 TRAP-TYPE
	ENTERPRISE	network-device
	VARIABLES	{ vcValue, adminDateAndTime, adminNDTrapSeqNo,
			  vcIndex, vcType }
	DESCRIPTION	"This trap is generated when set
			vcExLoThresholdIncreaseTrapID equal 114 and
			vcValue is greater equal
			the lower threshold plus the lower hysteresis
			after vcExceedLowerThresholdDecrease is generated.
			namely, vcValue >= (vcTrapLowerThreshold +
			vcTrapLowerHysteresis)."
	::= 15986

    vcExceedLowerThresholdIncrease115 TRAP-TYPE
	ENTERPRISE	network-device
	VARIABLES	{ vcValue, adminDateAndTime, adminNDTrapSeqNo,
			  vcIndex, vcType }
	DESCRIPTION	"This trap is generated when set
			vcExLoThresholdIncreaseTrapID equal 115 and
			vcValue is greater equal
			the lower threshold plus the lower hysteresis
			after vcExceedLowerThresholdDecrease is generated.
			namely, vcValue >= (vcTrapLowerThreshold +
			vcTrapLowerHysteresis)."
	::= 15987

    vcExceedLowerThresholdIncrease116 TRAP-TYPE
	ENTERPRISE	network-device
	VARIABLES	{ vcValue, adminDateAndTime, adminNDTrapSeqNo,
			  vcIndex, vcType }
	DESCRIPTION	"This trap is generated when set
			vcExLoThresholdIncreaseTrapID equal 116 and
			vcValue is greater equal
			the lower threshold plus the lower hysteresis
			after vcExceedLowerThresholdDecrease is generated.
			namely, vcValue >= (vcTrapLowerThreshold +
			vcTrapLowerHysteresis)."
	::= 15988

    vcExceedLowerThresholdIncrease117 TRAP-TYPE
	ENTERPRISE	network-device
	VARIABLES	{ vcValue, adminDateAndTime, adminNDTrapSeqNo,
			  vcIndex, vcType }
	DESCRIPTION	"This trap is generated when set
			vcExLoThresholdIncreaseTrapID equal 117 and
			vcValue is greater equal
			the lower threshold plus the lower hysteresis
			after vcExceedLowerThresholdDecrease is generated.
			namely, vcValue >= (vcTrapLowerThreshold +
			vcTrapLowerHysteresis)."
	::= 15989

    vcExceedLowerThresholdIncrease118 TRAP-TYPE
	ENTERPRISE	network-device
	VARIABLES	{ vcValue, adminDateAndTime, adminNDTrapSeqNo,
			  vcIndex, vcType }
	DESCRIPTION	"This trap is generated when set
			vcExLoThresholdIncreaseTrapID equal 118 and
			vcValue is greater equal
			the lower threshold plus the lower hysteresis
			after vcExceedLowerThresholdDecrease is generated.
			namely, vcValue >= (vcTrapLowerThreshold +
			vcTrapLowerHysteresis)."
	::= 15990

    vcExceedLowerThresholdIncrease119 TRAP-TYPE
	ENTERPRISE	network-device
	VARIABLES	{ vcValue, adminDateAndTime, adminNDTrapSeqNo,
			  vcIndex, vcType }
	DESCRIPTION	"This trap is generated when set
			vcExLoThresholdIncreaseTrapID equal 119 and
			vcValue is greater equal
			the lower threshold plus the lower hysteresis
			after vcExceedLowerThresholdDecrease is generated.
			namely, vcValue >= (vcTrapLowerThreshold +
			vcTrapLowerHysteresis)."
	::= 15991

    vcExceedLowerThresholdIncrease120 TRAP-TYPE
	ENTERPRISE	network-device
	VARIABLES	{ vcValue, adminDateAndTime, adminNDTrapSeqNo,
			  vcIndex, vcType }
	DESCRIPTION	"This trap is generated when set
			vcExLoThresholdIncreaseTrapID equal 120 and
			vcValue is greater equal
			the lower threshold plus the lower hysteresis
			after vcExceedLowerThresholdDecrease is generated.
			namely, vcValue >= (vcTrapLowerThreshold +
			vcTrapLowerHysteresis)."
	::= 15992

    vcExceedLowerThresholdIncrease121 TRAP-TYPE
	ENTERPRISE	network-device
	VARIABLES	{ vcValue, adminDateAndTime, adminNDTrapSeqNo,
			  vcIndex, vcType }
	DESCRIPTION	"This trap is generated when set
			vcExLoThresholdIncreaseTrapID equal 121 and
			vcValue is greater equal
			the lower threshold plus the lower hysteresis
			after vcExceedLowerThresholdDecrease is generated.
			namely, vcValue >= (vcTrapLowerThreshold +
			vcTrapLowerHysteresis)."
	::= 15993

    vcExceedLowerThresholdIncrease122 TRAP-TYPE
	ENTERPRISE	network-device
	VARIABLES	{ vcValue, adminDateAndTime, adminNDTrapSeqNo,
			  vcIndex, vcType }
	DESCRIPTION	"This trap is generated when set
			vcExLoThresholdIncreaseTrapID equal 122 and
			vcValue is greater equal
			the lower threshold plus the lower hysteresis
			after vcExceedLowerThresholdDecrease is generated.
			namely, vcValue >= (vcTrapLowerThreshold +
			vcTrapLowerHysteresis)."
	::= 15994

    vcExceedLowerThresholdIncrease123 TRAP-TYPE
	ENTERPRISE	network-device
	VARIABLES	{ vcValue, adminDateAndTime, adminNDTrapSeqNo,
			  vcIndex, vcType }
	DESCRIPTION	"This trap is generated when set
			vcExLoThresholdIncreaseTrapID equal 123 and
			vcValue is greater equal
			the lower threshold plus the lower hysteresis
			after vcExceedLowerThresholdDecrease is generated.
			namely, vcValue >= (vcTrapLowerThreshold +
			vcTrapLowerHysteresis)."
	::= 15995

    vcExceedLowerThresholdIncrease124 TRAP-TYPE
	ENTERPRISE	network-device
	VARIABLES	{ vcValue, adminDateAndTime, adminNDTrapSeqNo,
			  vcIndex, vcType }
	DESCRIPTION	"This trap is generated when set
			vcExLoThresholdIncreaseTrapID equal 124 and
			vcValue is greater equal
			the lower threshold plus the lower hysteresis
			after vcExceedLowerThresholdDecrease is generated.
			namely, vcValue >= (vcTrapLowerThreshold +
			vcTrapLowerHysteresis)."
	::= 15996

    vcExceedLowerThresholdIncrease125 TRAP-TYPE
	ENTERPRISE	network-device
	VARIABLES	{ vcValue, adminDateAndTime, adminNDTrapSeqNo,
			  vcIndex, vcType }
	DESCRIPTION	"This trap is generated when set
			vcExLoThresholdIncreaseTrapID equal 125 and
			vcValue is greater equal
			the lower threshold plus the lower hysteresis
			after vcExceedLowerThresholdDecrease is generated.
			namely, vcValue >= (vcTrapLowerThreshold +
			vcTrapLowerHysteresis)."
	::= 15997

    vcExceedLowerThresholdIncrease126 TRAP-TYPE
	ENTERPRISE	network-device
	VARIABLES	{ vcValue, adminDateAndTime, adminNDTrapSeqNo,
			  vcIndex, vcType }
	DESCRIPTION	"This trap is generated when set
			vcExLoThresholdIncreaseTrapID equal 126 and
			vcValue is greater equal
			the lower threshold plus the lower hysteresis
			after vcExceedLowerThresholdDecrease is generated.
			namely, vcValue >= (vcTrapLowerThreshold +
			vcTrapLowerHysteresis)."
	::= 15998

    vcExceedLowerThresholdIncrease127 TRAP-TYPE
	ENTERPRISE	network-device
	VARIABLES	{ vcValue, adminDateAndTime, adminNDTrapSeqNo,
			  vcIndex, vcType }
	DESCRIPTION	"This trap is generated when set
			vcExLoThresholdIncreaseTrapID equal 127 and
			vcValue is greater equal
			the lower threshold plus the lower hysteresis
			after vcExceedLowerThresholdDecrease is generated.
			namely, vcValue >= (vcTrapLowerThreshold +
			vcTrapLowerHysteresis)."
	::= 15999

    vcExceedLowerThresholdDecrease1 TRAP-TYPE
	ENTERPRISE	network-device
	VARIABLES	{ vcValue, adminDateAndTime, adminNDTrapSeqNo,
			  vcIndex, vcType }
	DESCRIPTION	"This trap is generated when set
			vcExLoThresholdDecreaseTrapID equal 1 and
			vcValue is less than the lower threshold."
	::= 16385

    vcExceedLowerThresholdDecrease2 TRAP-TYPE
	ENTERPRISE	network-device
	VARIABLES	{ vcValue, adminDateAndTime, adminNDTrapSeqNo,
			  vcIndex, vcType }
	DESCRIPTION	"This trap is generated when set
			vcExLoThresholdDecreaseTrapID equal 2 and
			vcValue is less than the lower threshold."
	::= 16386

    vcExceedLowerThresholdDecrease3 TRAP-TYPE
	ENTERPRISE	network-device
	VARIABLES	{ vcValue, adminDateAndTime, adminNDTrapSeqNo,
			  vcIndex, vcType }
	DESCRIPTION	"This trap is generated when set
			vcExLoThresholdDecreaseTrapID equal 3 and
			vcValue is less than the lower threshold."
	::= 16387

    vcExceedLowerThresholdDecrease4 TRAP-TYPE
	ENTERPRISE	network-device
	VARIABLES	{ vcValue, adminDateAndTime, adminNDTrapSeqNo,
			  vcIndex, vcType }
	DESCRIPTION	"This trap is generated when set
			vcExLoThresholdDecreaseTrapID equal 4 and
			vcValue is less than the lower threshold."
	::= 16388

    vcExceedLowerThresholdDecrease5 TRAP-TYPE
	ENTERPRISE	network-device
	VARIABLES	{ vcValue, adminDateAndTime, adminNDTrapSeqNo,
			  vcIndex, vcType }
	DESCRIPTION	"This trap is generated when set
			vcExLoThresholdDecreaseTrapID equal 5 and
			vcValue is less than the lower threshold."
	::= 16389

    vcExceedLowerThresholdDecrease6 TRAP-TYPE
	ENTERPRISE	network-device
	VARIABLES	{ vcValue, adminDateAndTime, adminNDTrapSeqNo,
			  vcIndex, vcType }
	DESCRIPTION	"This trap is generated when set
			vcExLoThresholdDecreaseTrapID equal 6 and
			vcValue is less than the lower threshold."
	::= 16390

    vcExceedLowerThresholdDecrease7 TRAP-TYPE
	ENTERPRISE	network-device
	VARIABLES	{ vcValue, adminDateAndTime, adminNDTrapSeqNo,
			  vcIndex, vcType }
	DESCRIPTION	"This trap is generated when set
			vcExLoThresholdDecreaseTrapID equal 7 and
			vcValue is less than the lower threshold."
	::= 16391

    vcExceedLowerThresholdDecrease8 TRAP-TYPE
	ENTERPRISE	network-device
	VARIABLES	{ vcValue, adminDateAndTime, adminNDTrapSeqNo,
			  vcIndex, vcType }
	DESCRIPTION	"This trap is generated when set
			vcExLoThresholdDecreaseTrapID equal 8 and
			vcValue is less than the lower threshold."
	::= 16392

    vcExceedLowerThresholdDecrease9 TRAP-TYPE
	ENTERPRISE	network-device
	VARIABLES	{ vcValue, adminDateAndTime, adminNDTrapSeqNo,
			  vcIndex, vcType }
	DESCRIPTION	"This trap is generated when set
			vcExLoThresholdDecreaseTrapID equal 9 and
			vcValue is less than the lower threshold."
	::= 16393

    vcExceedLowerThresholdDecrease10 TRAP-TYPE
	ENTERPRISE	network-device
	VARIABLES	{ vcValue, adminDateAndTime, adminNDTrapSeqNo,
			  vcIndex, vcType }
	DESCRIPTION	"This trap is generated when set
			vcExLoThresholdDecreaseTrapID equal 10 and
			vcValue is less than the lower threshold."
	::= 16394

    vcExceedLowerThresholdDecrease11 TRAP-TYPE
	ENTERPRISE	network-device
	VARIABLES	{ vcValue, adminDateAndTime, adminNDTrapSeqNo,
			  vcIndex, vcType }
	DESCRIPTION	"This trap is generated when set
			vcExLoThresholdDecreaseTrapID equal 11 and
			vcValue is less than the lower threshold."
	::= 16395

    vcExceedLowerThresholdDecrease12 TRAP-TYPE
	ENTERPRISE	network-device
	VARIABLES	{ vcValue, adminDateAndTime, adminNDTrapSeqNo,
			  vcIndex, vcType }
	DESCRIPTION	"This trap is generated when set
			vcExLoThresholdDecreaseTrapID equal 12 and
			vcValue is less than the lower threshold."
	::= 16396

    vcExceedLowerThresholdDecrease13 TRAP-TYPE
	ENTERPRISE	network-device
	VARIABLES	{ vcValue, adminDateAndTime, adminNDTrapSeqNo,
			  vcIndex, vcType }
	DESCRIPTION	"This trap is generated when set
			vcExLoThresholdDecreaseTrapID equal 13 and
			vcValue is less than the lower threshold."
	::= 16397

    vcExceedLowerThresholdDecrease14 TRAP-TYPE
	ENTERPRISE	network-device
	VARIABLES	{ vcValue, adminDateAndTime, adminNDTrapSeqNo,
			  vcIndex, vcType }
	DESCRIPTION	"This trap is generated when set
			vcExLoThresholdDecreaseTrapID equal 14 and
			vcValue is less than the lower threshold."
	::= 16398

    vcExceedLowerThresholdDecrease15 TRAP-TYPE
	ENTERPRISE	network-device
	VARIABLES	{ vcValue, adminDateAndTime, adminNDTrapSeqNo,
			  vcIndex, vcType }
	DESCRIPTION	"This trap is generated when set
			vcExLoThresholdDecreaseTrapID equal 15 and
			vcValue is less than the lower threshold."
	::= 16399

    vcExceedLowerThresholdDecrease16 TRAP-TYPE
	ENTERPRISE	network-device
	VARIABLES	{ vcValue, adminDateAndTime, adminNDTrapSeqNo,
			  vcIndex, vcType }
	DESCRIPTION	"This trap is generated when set
			vcExLoThresholdDecreaseTrapID equal 16 and
			vcValue is less than the lower threshold."
	::= 16400

    vcExceedLowerThresholdDecrease17 TRAP-TYPE
	ENTERPRISE	network-device
	VARIABLES	{ vcValue, adminDateAndTime, adminNDTrapSeqNo,
			  vcIndex, vcType }
	DESCRIPTION	"This trap is generated when set
			vcExLoThresholdDecreaseTrapID equal 17 and
			vcValue is less than the lower threshold."
	::= 16401

    vcExceedLowerThresholdDecrease18 TRAP-TYPE
	ENTERPRISE	network-device
	VARIABLES	{ vcValue, adminDateAndTime, adminNDTrapSeqNo,
			  vcIndex, vcType }
	DESCRIPTION	"This trap is generated when set
			vcExLoThresholdDecreaseTrapID equal 18 and
			vcValue is less than the lower threshold."
	::= 16402

    vcExceedLowerThresholdDecrease19 TRAP-TYPE
	ENTERPRISE	network-device
	VARIABLES	{ vcValue, adminDateAndTime, adminNDTrapSeqNo,
			  vcIndex, vcType }
	DESCRIPTION	"This trap is generated when set
			vcExLoThresholdDecreaseTrapID equal 19 and
			vcValue is less than the lower threshold."
	::= 16403

    vcExceedLowerThresholdDecrease20 TRAP-TYPE
	ENTERPRISE	network-device
	VARIABLES	{ vcValue, adminDateAndTime, adminNDTrapSeqNo,
			  vcIndex, vcType }
	DESCRIPTION	"This trap is generated when set
			vcExLoThresholdDecreaseTrapID equal 20 and
			vcValue is less than the lower threshold."
	::= 16404

    vcExceedLowerThresholdDecrease21 TRAP-TYPE
	ENTERPRISE	network-device
	VARIABLES	{ vcValue, adminDateAndTime, adminNDTrapSeqNo,
			  vcIndex, vcType }
	DESCRIPTION	"This trap is generated when set
			vcExLoThresholdDecreaseTrapID equal 21 and
			vcValue is less than the lower threshold."
	::= 16405

    vcExceedLowerThresholdDecrease22 TRAP-TYPE
	ENTERPRISE	network-device
	VARIABLES	{ vcValue, adminDateAndTime, adminNDTrapSeqNo,
			  vcIndex, vcType }
	DESCRIPTION	"This trap is generated when set
			vcExLoThresholdDecreaseTrapID equal 22 and
			vcValue is less than the lower threshold."
	::= 16406

    vcExceedLowerThresholdDecrease23 TRAP-TYPE
	ENTERPRISE	network-device
	VARIABLES	{ vcValue, adminDateAndTime, adminNDTrapSeqNo,
			  vcIndex, vcType }
	DESCRIPTION	"This trap is generated when set
			vcExLoThresholdDecreaseTrapID equal 23 and
			vcValue is less than the lower threshold."
	::= 16407

    vcExceedLowerThresholdDecrease24 TRAP-TYPE
	ENTERPRISE	network-device
	VARIABLES	{ vcValue, adminDateAndTime, adminNDTrapSeqNo,
			  vcIndex, vcType }
	DESCRIPTION	"This trap is generated when set
			vcExLoThresholdDecreaseTrapID equal 24 and
			vcValue is less than the lower threshold."
	::= 16408

    vcExceedLowerThresholdDecrease25 TRAP-TYPE
	ENTERPRISE	network-device
	VARIABLES	{ vcValue, adminDateAndTime, adminNDTrapSeqNo,
			  vcIndex, vcType }
	DESCRIPTION	"This trap is generated when set
			vcExLoThresholdDecreaseTrapID equal 25 and
			vcValue is less than the lower threshold."
	::= 16409

    vcExceedLowerThresholdDecrease26 TRAP-TYPE
	ENTERPRISE	network-device
	VARIABLES	{ vcValue, adminDateAndTime, adminNDTrapSeqNo,
			  vcIndex, vcType }
	DESCRIPTION	"This trap is generated when set
			vcExLoThresholdDecreaseTrapID equal 26 and
			vcValue is less than the lower threshold."
	::= 16410

    vcExceedLowerThresholdDecrease27 TRAP-TYPE
	ENTERPRISE	network-device
	VARIABLES	{ vcValue, adminDateAndTime, adminNDTrapSeqNo,
			  vcIndex, vcType }
	DESCRIPTION	"This trap is generated when set
			vcExLoThresholdDecreaseTrapID equal 27 and
			vcValue is less than the lower threshold."
	::= 16411

    vcExceedLowerThresholdDecrease28 TRAP-TYPE
	ENTERPRISE	network-device
	VARIABLES	{ vcValue, adminDateAndTime, adminNDTrapSeqNo,
			  vcIndex, vcType }
	DESCRIPTION	"This trap is generated when set
			vcExLoThresholdDecreaseTrapID equal 28 and
			vcValue is less than the lower threshold."
	::= 16412

    vcExceedLowerThresholdDecrease29 TRAP-TYPE
	ENTERPRISE	network-device
	VARIABLES	{ vcValue, adminDateAndTime, adminNDTrapSeqNo,
			  vcIndex, vcType }
	DESCRIPTION	"This trap is generated when set
			vcExLoThresholdDecreaseTrapID equal 29 and
			vcValue is less than the lower threshold."
	::= 16413

    vcExceedLowerThresholdDecrease30 TRAP-TYPE
	ENTERPRISE	network-device
	VARIABLES	{ vcValue, adminDateAndTime, adminNDTrapSeqNo,
			  vcIndex, vcType }
	DESCRIPTION	"This trap is generated when set
			vcExLoThresholdDecreaseTrapID equal 30 and
			vcValue is less than the lower threshold."
	::= 16414

    vcExceedLowerThresholdDecrease31 TRAP-TYPE
	ENTERPRISE	network-device
	VARIABLES	{ vcValue, adminDateAndTime, adminNDTrapSeqNo,
			  vcIndex, vcType }
	DESCRIPTION	"This trap is generated when set
			vcExLoThresholdDecreaseTrapID equal 31 and
			vcValue is less than the lower threshold."
	::= 16415

    vcExceedLowerThresholdDecrease32 TRAP-TYPE
	ENTERPRISE	network-device
	VARIABLES	{ vcValue, adminDateAndTime, adminNDTrapSeqNo,
			  vcIndex, vcType }
	DESCRIPTION	"This trap is generated when set
			vcExLoThresholdDecreaseTrapID equal 32 and
			vcValue is less than the lower threshold."
	::= 16416

    vcExceedLowerThresholdDecrease33 TRAP-TYPE
	ENTERPRISE	network-device
	VARIABLES	{ vcValue, adminDateAndTime, adminNDTrapSeqNo,
			  vcIndex, vcType }
	DESCRIPTION	"This trap is generated when set
			vcExLoThresholdDecreaseTrapID equal 33 and
			vcValue is less than the lower threshold."
	::= 16417

    vcExceedLowerThresholdDecrease34 TRAP-TYPE
	ENTERPRISE	network-device
	VARIABLES	{ vcValue, adminDateAndTime, adminNDTrapSeqNo,
			  vcIndex, vcType }
	DESCRIPTION	"This trap is generated when set
			vcExLoThresholdDecreaseTrapID equal 34 and
			vcValue is less than the lower threshold."
	::= 16418

    vcExceedLowerThresholdDecrease35 TRAP-TYPE
	ENTERPRISE	network-device
	VARIABLES	{ vcValue, adminDateAndTime, adminNDTrapSeqNo,
			  vcIndex, vcType }
	DESCRIPTION	"This trap is generated when set
			vcExLoThresholdDecreaseTrapID equal 35 and
			vcValue is less than the lower threshold."
	::= 16419

    vcExceedLowerThresholdDecrease36 TRAP-TYPE
	ENTERPRISE	network-device
	VARIABLES	{ vcValue, adminDateAndTime, adminNDTrapSeqNo,
			  vcIndex, vcType }
	DESCRIPTION	"This trap is generated when set
			vcExLoThresholdDecreaseTrapID equal 36 and
			vcValue is less than the lower threshold."
	::= 16420

    vcExceedLowerThresholdDecrease37 TRAP-TYPE
	ENTERPRISE	network-device
	VARIABLES	{ vcValue, adminDateAndTime, adminNDTrapSeqNo,
			  vcIndex, vcType }
	DESCRIPTION	"This trap is generated when set
			vcExLoThresholdDecreaseTrapID equal 37 and
			vcValue is less than the lower threshold."
	::= 16421

    vcExceedLowerThresholdDecrease38 TRAP-TYPE
	ENTERPRISE	network-device
	VARIABLES	{ vcValue, adminDateAndTime, adminNDTrapSeqNo,
			  vcIndex, vcType }
	DESCRIPTION	"This trap is generated when set
			vcExLoThresholdDecreaseTrapID equal 38 and
			vcValue is less than the lower threshold."
	::= 16422

    vcExceedLowerThresholdDecrease39 TRAP-TYPE
	ENTERPRISE	network-device
	VARIABLES	{ vcValue, adminDateAndTime, adminNDTrapSeqNo,
			  vcIndex, vcType }
	DESCRIPTION	"This trap is generated when set
			vcExLoThresholdDecreaseTrapID equal 39 and
			vcValue is less than the lower threshold."
	::= 16423

    vcExceedLowerThresholdDecrease40 TRAP-TYPE
	ENTERPRISE	network-device
	VARIABLES	{ vcValue, adminDateAndTime, adminNDTrapSeqNo,
			  vcIndex, vcType }
	DESCRIPTION	"This trap is generated when set
			vcExLoThresholdDecreaseTrapID equal 40 and
			vcValue is less than the lower threshold."
	::= 16424

    vcExceedLowerThresholdDecrease41 TRAP-TYPE
	ENTERPRISE	network-device
	VARIABLES	{ vcValue, adminDateAndTime, adminNDTrapSeqNo,
			  vcIndex, vcType }
	DESCRIPTION	"This trap is generated when set
			vcExLoThresholdDecreaseTrapID equal 41 and
			vcValue is less than the lower threshold."
	::= 16425

    vcExceedLowerThresholdDecrease42 TRAP-TYPE
	ENTERPRISE	network-device
	VARIABLES	{ vcValue, adminDateAndTime, adminNDTrapSeqNo,
			  vcIndex, vcType }
	DESCRIPTION	"This trap is generated when set
			vcExLoThresholdDecreaseTrapID equal 42 and
			vcValue is less than the lower threshold."
	::= 16426

    vcExceedLowerThresholdDecrease43 TRAP-TYPE
	ENTERPRISE	network-device
	VARIABLES	{ vcValue, adminDateAndTime, adminNDTrapSeqNo,
			  vcIndex, vcType }
	DESCRIPTION	"This trap is generated when set
			vcExLoThresholdDecreaseTrapID equal 43 and
			vcValue is less than the lower threshold."
	::= 16427

    vcExceedLowerThresholdDecrease44 TRAP-TYPE
	ENTERPRISE	network-device
	VARIABLES	{ vcValue, adminDateAndTime, adminNDTrapSeqNo,
			  vcIndex, vcType }
	DESCRIPTION	"This trap is generated when set
			vcExLoThresholdDecreaseTrapID equal 44 and
			vcValue is less than the lower threshold."
	::= 16428

    vcExceedLowerThresholdDecrease45 TRAP-TYPE
	ENTERPRISE	network-device
	VARIABLES	{ vcValue, adminDateAndTime, adminNDTrapSeqNo,
			  vcIndex, vcType }
	DESCRIPTION	"This trap is generated when set
			vcExLoThresholdDecreaseTrapID equal 45 and
			vcValue is less than the lower threshold."
	::= 16429

    vcExceedLowerThresholdDecrease46 TRAP-TYPE
	ENTERPRISE	network-device
	VARIABLES	{ vcValue, adminDateAndTime, adminNDTrapSeqNo,
			  vcIndex, vcType }
	DESCRIPTION	"This trap is generated when set
			vcExLoThresholdDecreaseTrapID equal 46 and
			vcValue is less than the lower threshold."
	::= 16430

    vcExceedLowerThresholdDecrease47 TRAP-TYPE
	ENTERPRISE	network-device
	VARIABLES	{ vcValue, adminDateAndTime, adminNDTrapSeqNo,
			  vcIndex, vcType }
	DESCRIPTION	"This trap is generated when set
			vcExLoThresholdDecreaseTrapID equal 47 and
			vcValue is less than the lower threshold."
	::= 16431

    vcExceedLowerThresholdDecrease48 TRAP-TYPE
	ENTERPRISE	network-device
	VARIABLES	{ vcValue, adminDateAndTime, adminNDTrapSeqNo,
			  vcIndex, vcType }
	DESCRIPTION	"This trap is generated when set
			vcExLoThresholdDecreaseTrapID equal 48 and
			vcValue is less than the lower threshold."
	::= 16432

    vcExceedLowerThresholdDecrease49 TRAP-TYPE
	ENTERPRISE	network-device
	VARIABLES	{ vcValue, adminDateAndTime, adminNDTrapSeqNo,
			  vcIndex, vcType }
	DESCRIPTION	"This trap is generated when set
			vcExLoThresholdDecreaseTrapID equal 49 and
			vcValue is less than the lower threshold."
	::= 16433

    vcExceedLowerThresholdDecrease50 TRAP-TYPE
	ENTERPRISE	network-device
	VARIABLES	{ vcValue, adminDateAndTime, adminNDTrapSeqNo,
			  vcIndex, vcType }
	DESCRIPTION	"This trap is generated when set
			vcExLoThresholdDecreaseTrapID equal 50 and
			vcValue is less than the lower threshold."
	::= 16434

    vcExceedLowerThresholdDecrease51 TRAP-TYPE
	ENTERPRISE	network-device
	VARIABLES	{ vcValue, adminDateAndTime, adminNDTrapSeqNo,
			  vcIndex, vcType }
	DESCRIPTION	"This trap is generated when set
			vcExLoThresholdDecreaseTrapID equal 51 and
			vcValue is less than the lower threshold."
	::= 16435

    vcExceedLowerThresholdDecrease52 TRAP-TYPE
	ENTERPRISE	network-device
	VARIABLES	{ vcValue, adminDateAndTime, adminNDTrapSeqNo,
			  vcIndex, vcType }
	DESCRIPTION	"This trap is generated when set
			vcExLoThresholdDecreaseTrapID equal 52 and
			vcValue is less than the lower threshold."
	::= 16436

    vcExceedLowerThresholdDecrease53 TRAP-TYPE
	ENTERPRISE	network-device
	VARIABLES	{ vcValue, adminDateAndTime, adminNDTrapSeqNo,
			  vcIndex, vcType }
	DESCRIPTION	"This trap is generated when set
			vcExLoThresholdDecreaseTrapID equal 53 and
			vcValue is less than the lower threshold."
	::= 16437

    vcExceedLowerThresholdDecrease54 TRAP-TYPE
	ENTERPRISE	network-device
	VARIABLES	{ vcValue, adminDateAndTime, adminNDTrapSeqNo,
			  vcIndex, vcType }
	DESCRIPTION	"This trap is generated when set
			vcExLoThresholdDecreaseTrapID equal 54 and
			vcValue is less than the lower threshold."
	::= 16438

    vcExceedLowerThresholdDecrease55 TRAP-TYPE
	ENTERPRISE	network-device
	VARIABLES	{ vcValue, adminDateAndTime, adminNDTrapSeqNo,
			  vcIndex, vcType }
	DESCRIPTION	"This trap is generated when set
			vcExLoThresholdDecreaseTrapID equal 55 and
			vcValue is less than the lower threshold."
	::= 16439

    vcExceedLowerThresholdDecrease56 TRAP-TYPE
	ENTERPRISE	network-device
	VARIABLES	{ vcValue, adminDateAndTime, adminNDTrapSeqNo,
			  vcIndex, vcType }
	DESCRIPTION	"This trap is generated when set
			vcExLoThresholdDecreaseTrapID equal 56 and
			vcValue is less than the lower threshold."
	::= 16440

    vcExceedLowerThresholdDecrease57 TRAP-TYPE
	ENTERPRISE	network-device
	VARIABLES	{ vcValue, adminDateAndTime, adminNDTrapSeqNo,
			  vcIndex, vcType }
	DESCRIPTION	"This trap is generated when set
			vcExLoThresholdDecreaseTrapID equal 57 and
			vcValue is less than the lower threshold."
	::= 16441

    vcExceedLowerThresholdDecrease58 TRAP-TYPE
	ENTERPRISE	network-device
	VARIABLES	{ vcValue, adminDateAndTime, adminNDTrapSeqNo,
			  vcIndex, vcType }
	DESCRIPTION	"This trap is generated when set
			vcExLoThresholdDecreaseTrapID equal 58 and
			vcValue is less than the lower threshold."
	::= 16442

    vcExceedLowerThresholdDecrease59 TRAP-TYPE
	ENTERPRISE	network-device
	VARIABLES	{ vcValue, adminDateAndTime, adminNDTrapSeqNo,
			  vcIndex, vcType }
	DESCRIPTION	"This trap is generated when set
			vcExLoThresholdDecreaseTrapID equal 59 and
			vcValue is less than the lower threshold."
	::= 16443

    vcExceedLowerThresholdDecrease60 TRAP-TYPE
	ENTERPRISE	network-device
	VARIABLES	{ vcValue, adminDateAndTime, adminNDTrapSeqNo,
			  vcIndex, vcType }
	DESCRIPTION	"This trap is generated when set
			vcExLoThresholdDecreaseTrapID equal 60 and
			vcValue is less than the lower threshold."
	::= 16444

    vcExceedLowerThresholdDecrease61 TRAP-TYPE
	ENTERPRISE	network-device
	VARIABLES	{ vcValue, adminDateAndTime, adminNDTrapSeqNo,
			  vcIndex, vcType }
	DESCRIPTION	"This trap is generated when set
			vcExLoThresholdDecreaseTrapID equal 61 and
			vcValue is less than the lower threshold."
	::= 16445

    vcExceedLowerThresholdDecrease62 TRAP-TYPE
	ENTERPRISE	network-device
	VARIABLES	{ vcValue, adminDateAndTime, adminNDTrapSeqNo,
			  vcIndex, vcType }
	DESCRIPTION	"This trap is generated when set
			vcExLoThresholdDecreaseTrapID equal 62 and
			vcValue is less than the lower threshold."
	::= 16446

    vcExceedLowerThresholdDecrease63 TRAP-TYPE
	ENTERPRISE	network-device
	VARIABLES	{ vcValue, adminDateAndTime, adminNDTrapSeqNo,
			  vcIndex, vcType }
	DESCRIPTION	"This trap is generated when set
			vcExLoThresholdDecreaseTrapID equal 63 and
			vcValue is less than the lower threshold."
	::= 16447

    vcExceedLowerThresholdDecrease64 TRAP-TYPE
	ENTERPRISE	network-device
	VARIABLES	{ vcValue, adminDateAndTime, adminNDTrapSeqNo,
			  vcIndex, vcType }
	DESCRIPTION	"This trap is generated when set
			vcExLoThresholdDecreaseTrapID equal 64 and
			vcValue is less than the lower threshold."
	::= 16448

    vcExceedLowerThresholdDecrease65 TRAP-TYPE
	ENTERPRISE	network-device
	VARIABLES	{ vcValue, adminDateAndTime, adminNDTrapSeqNo,
			  vcIndex, vcType }
	DESCRIPTION	"This trap is generated when set
			vcExLoThresholdDecreaseTrapID equal 65 and
			vcValue is less than the lower threshold."
	::= 16449

    vcExceedLowerThresholdDecrease66 TRAP-TYPE
	ENTERPRISE	network-device
	VARIABLES	{ vcValue, adminDateAndTime, adminNDTrapSeqNo,
			  vcIndex, vcType }
	DESCRIPTION	"This trap is generated when set
			vcExLoThresholdDecreaseTrapID equal 66 and
			vcValue is less than the lower threshold."
	::= 16450

    vcExceedLowerThresholdDecrease67 TRAP-TYPE
	ENTERPRISE	network-device
	VARIABLES	{ vcValue, adminDateAndTime, adminNDTrapSeqNo,
			  vcIndex, vcType }
	DESCRIPTION	"This trap is generated when set
			vcExLoThresholdDecreaseTrapID equal 67 and
			vcValue is less than the lower threshold."
	::= 16451

    vcExceedLowerThresholdDecrease68 TRAP-TYPE
	ENTERPRISE	network-device
	VARIABLES	{ vcValue, adminDateAndTime, adminNDTrapSeqNo,
			  vcIndex, vcType }
	DESCRIPTION	"This trap is generated when set
			vcExLoThresholdDecreaseTrapID equal 68 and
			vcValue is less than the lower threshold."
	::= 16452

    vcExceedLowerThresholdDecrease69 TRAP-TYPE
	ENTERPRISE	network-device
	VARIABLES	{ vcValue, adminDateAndTime, adminNDTrapSeqNo,
			  vcIndex, vcType }
	DESCRIPTION	"This trap is generated when set
			vcExLoThresholdDecreaseTrapID equal 69 and
			vcValue is less than the lower threshold."
	::= 16453

    vcExceedLowerThresholdDecrease70 TRAP-TYPE
	ENTERPRISE	network-device
	VARIABLES	{ vcValue, adminDateAndTime, adminNDTrapSeqNo,
			  vcIndex, vcType }
	DESCRIPTION	"This trap is generated when set
			vcExLoThresholdDecreaseTrapID equal 70 and
			vcValue is less than the lower threshold."
	::= 16454

    vcExceedLowerThresholdDecrease71 TRAP-TYPE
	ENTERPRISE	network-device
	VARIABLES	{ vcValue, adminDateAndTime, adminNDTrapSeqNo,
			  vcIndex, vcType }
	DESCRIPTION	"This trap is generated when set
			vcExLoThresholdDecreaseTrapID equal 71 and
			vcValue is less than the lower threshold."
	::= 16455

    vcExceedLowerThresholdDecrease72 TRAP-TYPE
	ENTERPRISE	network-device
	VARIABLES	{ vcValue, adminDateAndTime, adminNDTrapSeqNo,
			  vcIndex, vcType }
	DESCRIPTION	"This trap is generated when set
			vcExLoThresholdDecreaseTrapID equal 72 and
			vcValue is less than the lower threshold."
	::= 16456

    vcExceedLowerThresholdDecrease73 TRAP-TYPE
	ENTERPRISE	network-device
	VARIABLES	{ vcValue, adminDateAndTime, adminNDTrapSeqNo,
			  vcIndex, vcType }
	DESCRIPTION	"This trap is generated when set
			vcExLoThresholdDecreaseTrapID equal 73 and
			vcValue is less than the lower threshold."
	::= 16457

    vcExceedLowerThresholdDecrease74 TRAP-TYPE
	ENTERPRISE	network-device
	VARIABLES	{ vcValue, adminDateAndTime, adminNDTrapSeqNo,
			  vcIndex, vcType }
	DESCRIPTION	"This trap is generated when set
			vcExLoThresholdDecreaseTrapID equal 74 and
			vcValue is less than the lower threshold."
	::= 16458

    vcExceedLowerThresholdDecrease75 TRAP-TYPE
	ENTERPRISE	network-device
	VARIABLES	{ vcValue, adminDateAndTime, adminNDTrapSeqNo,
			  vcIndex, vcType }
	DESCRIPTION	"This trap is generated when set
			vcExLoThresholdDecreaseTrapID equal 75 and
			vcValue is less than the lower threshold."
	::= 16459

    vcExceedLowerThresholdDecrease76 TRAP-TYPE
	ENTERPRISE	network-device
	VARIABLES	{ vcValue, adminDateAndTime, adminNDTrapSeqNo,
			  vcIndex, vcType }
	DESCRIPTION	"This trap is generated when set
			vcExLoThresholdDecreaseTrapID equal 76 and
			vcValue is less than the lower threshold."
	::= 16460

    vcExceedLowerThresholdDecrease77 TRAP-TYPE
	ENTERPRISE	network-device
	VARIABLES	{ vcValue, adminDateAndTime, adminNDTrapSeqNo,
			  vcIndex, vcType }
	DESCRIPTION	"This trap is generated when set
			vcExLoThresholdDecreaseTrapID equal 77 and
			vcValue is less than the lower threshold."
	::= 16461

    vcExceedLowerThresholdDecrease78 TRAP-TYPE
	ENTERPRISE	network-device
	VARIABLES	{ vcValue, adminDateAndTime, adminNDTrapSeqNo,
			  vcIndex, vcType }
	DESCRIPTION	"This trap is generated when set
			vcExLoThresholdDecreaseTrapID equal 78 and
			vcValue is less than the lower threshold."
	::= 16462

    vcExceedLowerThresholdDecrease79 TRAP-TYPE
	ENTERPRISE	network-device
	VARIABLES	{ vcValue, adminDateAndTime, adminNDTrapSeqNo,
			  vcIndex, vcType }
	DESCRIPTION	"This trap is generated when set
			vcExLoThresholdDecreaseTrapID equal 79 and
			vcValue is less than the lower threshold."
	::= 16463

    vcExceedLowerThresholdDecrease80 TRAP-TYPE
	ENTERPRISE	network-device
	VARIABLES	{ vcValue, adminDateAndTime, adminNDTrapSeqNo,
			  vcIndex, vcType }
	DESCRIPTION	"This trap is generated when set
			vcExLoThresholdDecreaseTrapID equal 80 and
			vcValue is less than the lower threshold."
	::= 16464

    vcExceedLowerThresholdDecrease81 TRAP-TYPE
	ENTERPRISE	network-device
	VARIABLES	{ vcValue, adminDateAndTime, adminNDTrapSeqNo,
			  vcIndex, vcType }
	DESCRIPTION	"This trap is generated when set
			vcExLoThresholdDecreaseTrapID equal 81 and
			vcValue is less than the lower threshold."
	::= 16465

    vcExceedLowerThresholdDecrease82 TRAP-TYPE
	ENTERPRISE	network-device
	VARIABLES	{ vcValue, adminDateAndTime, adminNDTrapSeqNo,
			  vcIndex, vcType }
	DESCRIPTION	"This trap is generated when set
			vcExLoThresholdDecreaseTrapID equal 82 and
			vcValue is less than the lower threshold."
	::= 16466

    vcExceedLowerThresholdDecrease83 TRAP-TYPE
	ENTERPRISE	network-device
	VARIABLES	{ vcValue, adminDateAndTime, adminNDTrapSeqNo,
			  vcIndex, vcType }
	DESCRIPTION	"This trap is generated when set
			vcExLoThresholdDecreaseTrapID equal 83 and
			vcValue is less than the lower threshold."
	::= 16467

    vcExceedLowerThresholdDecrease84 TRAP-TYPE
	ENTERPRISE	network-device
	VARIABLES	{ vcValue, adminDateAndTime, adminNDTrapSeqNo,
			  vcIndex, vcType }
	DESCRIPTION	"This trap is generated when set
			vcExLoThresholdDecreaseTrapID equal 84 and
			vcValue is less than the lower threshold."
	::= 16468

    vcExceedLowerThresholdDecrease85 TRAP-TYPE
	ENTERPRISE	network-device
	VARIABLES	{ vcValue, adminDateAndTime, adminNDTrapSeqNo,
			  vcIndex, vcType }
	DESCRIPTION	"This trap is generated when set
			vcExLoThresholdDecreaseTrapID equal 85 and
			vcValue is less than the lower threshold."
	::= 16469

    vcExceedLowerThresholdDecrease86 TRAP-TYPE
	ENTERPRISE	network-device
	VARIABLES	{ vcValue, adminDateAndTime, adminNDTrapSeqNo,
			  vcIndex, vcType }
	DESCRIPTION	"This trap is generated when set
			vcExLoThresholdDecreaseTrapID equal 86 and
			vcValue is less than the lower threshold."
	::= 16470

    vcExceedLowerThresholdDecrease87 TRAP-TYPE
	ENTERPRISE	network-device
	VARIABLES	{ vcValue, adminDateAndTime, adminNDTrapSeqNo,
			  vcIndex, vcType }
	DESCRIPTION	"This trap is generated when set
			vcExLoThresholdDecreaseTrapID equal 87 and
			vcValue is less than the lower threshold."
	::= 16471

    vcExceedLowerThresholdDecrease88 TRAP-TYPE
	ENTERPRISE	network-device
	VARIABLES	{ vcValue, adminDateAndTime, adminNDTrapSeqNo,
			  vcIndex, vcType }
	DESCRIPTION	"This trap is generated when set
			vcExLoThresholdDecreaseTrapID equal 88 and
			vcValue is less than the lower threshold."
	::= 16472

    vcExceedLowerThresholdDecrease89 TRAP-TYPE
	ENTERPRISE	network-device
	VARIABLES	{ vcValue, adminDateAndTime, adminNDTrapSeqNo,
			  vcIndex, vcType }
	DESCRIPTION	"This trap is generated when set
			vcExLoThresholdDecreaseTrapID equal 89 and
			vcValue is less than the lower threshold."
	::= 16473

    vcExceedLowerThresholdDecrease90 TRAP-TYPE
	ENTERPRISE	network-device
	VARIABLES	{ vcValue, adminDateAndTime, adminNDTrapSeqNo,
			  vcIndex, vcType }
	DESCRIPTION	"This trap is generated when set
			vcExLoThresholdDecreaseTrapID equal 90 and
			vcValue is less than the lower threshold."
	::= 16474

    vcExceedLowerThresholdDecrease91 TRAP-TYPE
	ENTERPRISE	network-device
	VARIABLES	{ vcValue, adminDateAndTime, adminNDTrapSeqNo,
			  vcIndex, vcType }
	DESCRIPTION	"This trap is generated when set
			vcExLoThresholdDecreaseTrapID equal 91 and
			vcValue is less than the lower threshold."
	::= 16475

    vcExceedLowerThresholdDecrease92 TRAP-TYPE
	ENTERPRISE	network-device
	VARIABLES	{ vcValue, adminDateAndTime, adminNDTrapSeqNo,
			  vcIndex, vcType }
	DESCRIPTION	"This trap is generated when set
			vcExLoThresholdDecreaseTrapID equal 92 and
			vcValue is less than the lower threshold."
	::= 16476

    vcExceedLowerThresholdDecrease93 TRAP-TYPE
	ENTERPRISE	network-device
	VARIABLES	{ vcValue, adminDateAndTime, adminNDTrapSeqNo,
			  vcIndex, vcType }
	DESCRIPTION	"This trap is generated when set
			vcExLoThresholdDecreaseTrapID equal 93 and
			vcValue is less than the lower threshold."
	::= 16477

    vcExceedLowerThresholdDecrease94 TRAP-TYPE
	ENTERPRISE	network-device
	VARIABLES	{ vcValue, adminDateAndTime, adminNDTrapSeqNo,
			  vcIndex, vcType }
	DESCRIPTION	"This trap is generated when set
			vcExLoThresholdDecreaseTrapID equal 94 and
			vcValue is less than the lower threshold."
	::= 16478

    vcExceedLowerThresholdDecrease95 TRAP-TYPE
	ENTERPRISE	network-device
	VARIABLES	{ vcValue, adminDateAndTime, adminNDTrapSeqNo,
			  vcIndex, vcType }
	DESCRIPTION	"This trap is generated when set
			vcExLoThresholdDecreaseTrapID equal 95 and
			vcValue is less than the lower threshold."
	::= 16479

    vcExceedLowerThresholdDecrease96 TRAP-TYPE
	ENTERPRISE	network-device
	VARIABLES	{ vcValue, adminDateAndTime, adminNDTrapSeqNo,
			  vcIndex, vcType }
	DESCRIPTION	"This trap is generated when set
			vcExLoThresholdDecreaseTrapID equal 96 and
			vcValue is less than the lower threshold."
	::= 16480

    vcExceedLowerThresholdDecrease97 TRAP-TYPE
	ENTERPRISE	network-device
	VARIABLES	{ vcValue, adminDateAndTime, adminNDTrapSeqNo,
			  vcIndex, vcType }
	DESCRIPTION	"This trap is generated when set
			vcExLoThresholdDecreaseTrapID equal 97 and
			vcValue is less than the lower threshold."
	::= 16481

    vcExceedLowerThresholdDecrease98 TRAP-TYPE
	ENTERPRISE	network-device
	VARIABLES	{ vcValue, adminDateAndTime, adminNDTrapSeqNo,
			  vcIndex, vcType }
	DESCRIPTION	"This trap is generated when set
			vcExLoThresholdDecreaseTrapID equal 98 and
			vcValue is less than the lower threshold."
	::= 16482

    vcExceedLowerThresholdDecrease99 TRAP-TYPE
	ENTERPRISE	network-device
	VARIABLES	{ vcValue, adminDateAndTime, adminNDTrapSeqNo,
			  vcIndex, vcType }
	DESCRIPTION	"This trap is generated when set
			vcExLoThresholdDecreaseTrapID equal 99 and
			vcValue is less than the lower threshold."
	::= 16483

    vcExceedLowerThresholdDecrease100 TRAP-TYPE
	ENTERPRISE	network-device
	VARIABLES	{ vcValue, adminDateAndTime, adminNDTrapSeqNo,
			  vcIndex, vcType }
	DESCRIPTION	"This trap is generated when set
			vcExLoThresholdDecreaseTrapID equal 100 and
			vcValue is less than the lower threshold."
	::= 16484

    vcExceedLowerThresholdDecrease101 TRAP-TYPE
	ENTERPRISE	network-device
	VARIABLES	{ vcValue, adminDateAndTime, adminNDTrapSeqNo,
			  vcIndex, vcType }
	DESCRIPTION	"This trap is generated when set
			vcExLoThresholdDecreaseTrapID equal 101 and
			vcValue is less than the lower threshold."
	::= 16485

    vcExceedLowerThresholdDecrease102 TRAP-TYPE
	ENTERPRISE	network-device
	VARIABLES	{ vcValue, adminDateAndTime, adminNDTrapSeqNo,
			  vcIndex, vcType }
	DESCRIPTION	"This trap is generated when set
			vcExLoThresholdDecreaseTrapID equal 102 and
			vcValue is less than the lower threshold."
	::= 16486

    vcExceedLowerThresholdDecrease103 TRAP-TYPE
	ENTERPRISE	network-device
	VARIABLES	{ vcValue, adminDateAndTime, adminNDTrapSeqNo,
			  vcIndex, vcType }
	DESCRIPTION	"This trap is generated when set
			vcExLoThresholdDecreaseTrapID equal 103 and
			vcValue is less than the lower threshold."
	::= 16487

    vcExceedLowerThresholdDecrease104 TRAP-TYPE
	ENTERPRISE	network-device
	VARIABLES	{ vcValue, adminDateAndTime, adminNDTrapSeqNo,
			  vcIndex, vcType }
	DESCRIPTION	"This trap is generated when set
			vcExLoThresholdDecreaseTrapID equal 104 and
			vcValue is less than the lower threshold."
	::= 16488

    vcExceedLowerThresholdDecrease105 TRAP-TYPE
	ENTERPRISE	network-device
	VARIABLES	{ vcValue, adminDateAndTime, adminNDTrapSeqNo,
			  vcIndex, vcType }
	DESCRIPTION	"This trap is generated when set
			vcExLoThresholdDecreaseTrapID equal 105 and
			vcValue is less than the lower threshold."
	::= 16489

    vcExceedLowerThresholdDecrease106 TRAP-TYPE
	ENTERPRISE	network-device
	VARIABLES	{ vcValue, adminDateAndTime, adminNDTrapSeqNo,
			  vcIndex, vcType }
	DESCRIPTION	"This trap is generated when set
			vcExLoThresholdDecreaseTrapID equal 106 and
			vcValue is less than the lower threshold."
	::= 16490

    vcExceedLowerThresholdDecrease107 TRAP-TYPE
	ENTERPRISE	network-device
	VARIABLES	{ vcValue, adminDateAndTime, adminNDTrapSeqNo,
			  vcIndex, vcType }
	DESCRIPTION	"This trap is generated when set
			vcExLoThresholdDecreaseTrapID equal 107 and
			vcValue is less than the lower threshold."
	::= 16491

    vcExceedLowerThresholdDecrease108 TRAP-TYPE
	ENTERPRISE	network-device
	VARIABLES	{ vcValue, adminDateAndTime, adminNDTrapSeqNo,
			  vcIndex, vcType }
	DESCRIPTION	"This trap is generated when set
			vcExLoThresholdDecreaseTrapID equal 108 and
			vcValue is less than the lower threshold."
	::= 16492

    vcExceedLowerThresholdDecrease109 TRAP-TYPE
	ENTERPRISE	network-device
	VARIABLES	{ vcValue, adminDateAndTime, adminNDTrapSeqNo,
			  vcIndex, vcType }
	DESCRIPTION	"This trap is generated when set
			vcExLoThresholdDecreaseTrapID equal 109 and
			vcValue is less than the lower threshold."
	::= 16493

    vcExceedLowerThresholdDecrease110 TRAP-TYPE
	ENTERPRISE	network-device
	VARIABLES	{ vcValue, adminDateAndTime, adminNDTrapSeqNo,
			  vcIndex, vcType }
	DESCRIPTION	"This trap is generated when set
			vcExLoThresholdDecreaseTrapID equal 110 and
			vcValue is less than the lower threshold."
	::= 16494

    vcExceedLowerThresholdDecrease111 TRAP-TYPE
	ENTERPRISE	network-device
	VARIABLES	{ vcValue, adminDateAndTime, adminNDTrapSeqNo,
			  vcIndex, vcType }
	DESCRIPTION	"This trap is generated when set
			vcExLoThresholdDecreaseTrapID equal 111 and
			vcValue is less than the lower threshold."
	::= 16495

    vcExceedLowerThresholdDecrease112 TRAP-TYPE
	ENTERPRISE	network-device
	VARIABLES	{ vcValue, adminDateAndTime, adminNDTrapSeqNo,
			  vcIndex, vcType }
	DESCRIPTION	"This trap is generated when set
			vcExLoThresholdDecreaseTrapID equal 112 and
			vcValue is less than the lower threshold."
	::= 16496

    vcExceedLowerThresholdDecrease113 TRAP-TYPE
	ENTERPRISE	network-device
	VARIABLES	{ vcValue, adminDateAndTime, adminNDTrapSeqNo,
			  vcIndex, vcType }
	DESCRIPTION	"This trap is generated when set
			vcExLoThresholdDecreaseTrapID equal 113 and
			vcValue is less than the lower threshold."
	::= 16497

    vcExceedLowerThresholdDecrease114 TRAP-TYPE
	ENTERPRISE	network-device
	VARIABLES	{ vcValue, adminDateAndTime, adminNDTrapSeqNo,
			  vcIndex, vcType }
	DESCRIPTION	"This trap is generated when set
			vcExLoThresholdDecreaseTrapID equal 114 and
			vcValue is less than the lower threshold."
	::= 16498

    vcExceedLowerThresholdDecrease115 TRAP-TYPE
	ENTERPRISE	network-device
	VARIABLES	{ vcValue, adminDateAndTime, adminNDTrapSeqNo,
			  vcIndex, vcType }
	DESCRIPTION	"This trap is generated when set
			vcExLoThresholdDecreaseTrapID equal 115 and
			vcValue is less than the lower threshold."
	::= 16499

    vcExceedLowerThresholdDecrease116 TRAP-TYPE
	ENTERPRISE	network-device
	VARIABLES	{ vcValue, adminDateAndTime, adminNDTrapSeqNo,
			  vcIndex, vcType }
	DESCRIPTION	"This trap is generated when set
			vcExLoThresholdDecreaseTrapID equal 116 and
			vcValue is less than the lower threshold."
	::= 16500

    vcExceedLowerThresholdDecrease117 TRAP-TYPE
	ENTERPRISE	network-device
	VARIABLES	{ vcValue, adminDateAndTime, adminNDTrapSeqNo,
			  vcIndex, vcType }
	DESCRIPTION	"This trap is generated when set
			vcExLoThresholdDecreaseTrapID equal 117 and
			vcValue is less than the lower threshold."
	::= 16501

    vcExceedLowerThresholdDecrease118 TRAP-TYPE
	ENTERPRISE	network-device
	VARIABLES	{ vcValue, adminDateAndTime, adminNDTrapSeqNo,
			  vcIndex, vcType }
	DESCRIPTION	"This trap is generated when set
			vcExLoThresholdDecreaseTrapID equal 118 and
			vcValue is less than the lower threshold."
	::= 16502

    vcExceedLowerThresholdDecrease119 TRAP-TYPE
	ENTERPRISE	network-device
	VARIABLES	{ vcValue, adminDateAndTime, adminNDTrapSeqNo,
			  vcIndex, vcType }
	DESCRIPTION	"This trap is generated when set
			vcExLoThresholdDecreaseTrapID equal 119 and
			vcValue is less than the lower threshold."
	::= 16503

    vcExceedLowerThresholdDecrease120 TRAP-TYPE
	ENTERPRISE	network-device
	VARIABLES	{ vcValue, adminDateAndTime, adminNDTrapSeqNo,
			  vcIndex, vcType }
	DESCRIPTION	"This trap is generated when set
			vcExLoThresholdDecreaseTrapID equal 120 and
			vcValue is less than the lower threshold."
	::= 16504

    vcExceedLowerThresholdDecrease121 TRAP-TYPE
	ENTERPRISE	network-device
	VARIABLES	{ vcValue, adminDateAndTime, adminNDTrapSeqNo,
			  vcIndex, vcType }
	DESCRIPTION	"This trap is generated when set
			vcExLoThresholdDecreaseTrapID equal 121 and
			vcValue is less than the lower threshold."
	::= 16505

    vcExceedLowerThresholdDecrease122 TRAP-TYPE
	ENTERPRISE	network-device
	VARIABLES	{ vcValue, adminDateAndTime, adminNDTrapSeqNo,
			  vcIndex, vcType }
	DESCRIPTION	"This trap is generated when set
			vcExLoThresholdDecreaseTrapID equal 122 and
			vcValue is less than the lower threshold."
	::= 16506

    vcExceedLowerThresholdDecrease123 TRAP-TYPE
	ENTERPRISE	network-device
	VARIABLES	{ vcValue, adminDateAndTime, adminNDTrapSeqNo,
			  vcIndex, vcType }
	DESCRIPTION	"This trap is generated when set
			vcExLoThresholdDecreaseTrapID equal 123 and
			vcValue is less than the lower threshold."
	::= 16507

    vcExceedLowerThresholdDecrease124 TRAP-TYPE
	ENTERPRISE	network-device
	VARIABLES	{ vcValue, adminDateAndTime, adminNDTrapSeqNo,
			  vcIndex, vcType }
	DESCRIPTION	"This trap is generated when set
			vcExLoThresholdDecreaseTrapID equal 124 and
			vcValue is less than the lower threshold."
	::= 16508

    vcExceedLowerThresholdDecrease125 TRAP-TYPE
	ENTERPRISE	network-device
	VARIABLES	{ vcValue, adminDateAndTime, adminNDTrapSeqNo,
			  vcIndex, vcType }
	DESCRIPTION	"This trap is generated when set
			vcExLoThresholdDecreaseTrapID equal 125 and
			vcValue is less than the lower threshold."
	::= 16509

    vcExceedLowerThresholdDecrease126 TRAP-TYPE
	ENTERPRISE	network-device
	VARIABLES	{ vcValue, adminDateAndTime, adminNDTrapSeqNo,
			  vcIndex, vcType }
	DESCRIPTION	"This trap is generated when set
			vcExLoThresholdDecreaseTrapID equal 126 and
			vcValue is less than the lower threshold."
	::= 16510

    vcExceedLowerThresholdDecrease127 TRAP-TYPE
	ENTERPRISE	network-device
	VARIABLES	{ vcValue, adminDateAndTime, adminNDTrapSeqNo,
			  vcIndex, vcType }
	DESCRIPTION	"This trap is generated when set
			vcExLoThresholdDecreaseTrapID equal 127 and
			vcValue is less than the lower threshold."
	::= 16511

    vcExceedingLowerThreshold1 TRAP-TYPE
	ENTERPRISE	network-device
	VARIABLES	{ vcValue, adminDateAndTime, adminNDTrapSeqNo,
			  vcIndex, vcType }
	DESCRIPTION	"This trap is generated when set
			vcExLoThresholdTrapID equal 1 and
			until vcExceedLowerThresholdDecrease is generated after
			vcExceedLowerThresholdIncrease is generated."
	::= 16897

    vcExceedingLowerThreshold2 TRAP-TYPE
	ENTERPRISE	network-device
	VARIABLES	{ vcValue, adminDateAndTime, adminNDTrapSeqNo,
			  vcIndex, vcType }
	DESCRIPTION	"This trap is generated when set
			vcExLoThresholdTrapID equal 2 and
			until vcExceedLowerThresholdDecrease is generated after
			vcExceedLowerThresholdIncrease is generated."
	::= 16898

    vcExceedingLowerThreshold3 TRAP-TYPE
	ENTERPRISE	network-device
	VARIABLES	{ vcValue, adminDateAndTime, adminNDTrapSeqNo,
			  vcIndex, vcType }
	DESCRIPTION	"This trap is generated when set
			vcExLoThresholdTrapID equal 3 and
			until vcExceedLowerThresholdDecrease is generated after
			vcExceedLowerThresholdIncrease is generated."
	::= 16899

    vcExceedingLowerThreshold4 TRAP-TYPE
	ENTERPRISE	network-device
	VARIABLES	{ vcValue, adminDateAndTime, adminNDTrapSeqNo,
			  vcIndex, vcType }
	DESCRIPTION	"This trap is generated when set
			vcExLoThresholdTrapID equal 4 and
			until vcExceedLowerThresholdDecrease is generated after
			vcExceedLowerThresholdIncrease is generated."
	::= 16900

    vcExceedingLowerThreshold5 TRAP-TYPE
	ENTERPRISE	network-device
	VARIABLES	{ vcValue, adminDateAndTime, adminNDTrapSeqNo,
			  vcIndex, vcType }
	DESCRIPTION	"This trap is generated when set
			vcExLoThresholdTrapID equal 5 and
			until vcExceedLowerThresholdDecrease is generated after
			vcExceedLowerThresholdIncrease is generated."
	::= 16901

    vcExceedingLowerThreshold6 TRAP-TYPE
	ENTERPRISE	network-device
	VARIABLES	{ vcValue, adminDateAndTime, adminNDTrapSeqNo,
			  vcIndex, vcType }
	DESCRIPTION	"This trap is generated when set
			vcExLoThresholdTrapID equal 6 and
			until vcExceedLowerThresholdDecrease is generated after
			vcExceedLowerThresholdIncrease is generated."
	::= 16902

    vcExceedingLowerThreshold7 TRAP-TYPE
	ENTERPRISE	network-device
	VARIABLES	{ vcValue, adminDateAndTime, adminNDTrapSeqNo,
			  vcIndex, vcType }
	DESCRIPTION	"This trap is generated when set
			vcExLoThresholdTrapID equal 7 and
			until vcExceedLowerThresholdDecrease is generated after
			vcExceedLowerThresholdIncrease is generated."
	::= 16903

    vcExceedingLowerThreshold8 TRAP-TYPE
	ENTERPRISE	network-device
	VARIABLES	{ vcValue, adminDateAndTime, adminNDTrapSeqNo,
			  vcIndex, vcType }
	DESCRIPTION	"This trap is generated when set
			vcExLoThresholdTrapID equal 8 and
			until vcExceedLowerThresholdDecrease is generated after
			vcExceedLowerThresholdIncrease is generated."
	::= 16904

    vcExceedingLowerThreshold9 TRAP-TYPE
	ENTERPRISE	network-device
	VARIABLES	{ vcValue, adminDateAndTime, adminNDTrapSeqNo,
			  vcIndex, vcType }
	DESCRIPTION	"This trap is generated when set
			vcExLoThresholdTrapID equal 9 and
			until vcExceedLowerThresholdDecrease is generated after
			vcExceedLowerThresholdIncrease is generated."
	::= 16905

    vcExceedingLowerThreshold10 TRAP-TYPE
	ENTERPRISE	network-device
	VARIABLES	{ vcValue, adminDateAndTime, adminNDTrapSeqNo,
			  vcIndex, vcType }
	DESCRIPTION	"This trap is generated when set
			vcExLoThresholdTrapID equal 10 and
			until vcExceedLowerThresholdDecrease is generated after
			vcExceedLowerThresholdIncrease is generated."
	::= 16906

    vcExceedingLowerThreshold11 TRAP-TYPE
	ENTERPRISE	network-device
	VARIABLES	{ vcValue, adminDateAndTime, adminNDTrapSeqNo,
			  vcIndex, vcType }
	DESCRIPTION	"This trap is generated when set
			vcExLoThresholdTrapID equal 11 and
			until vcExceedLowerThresholdDecrease is generated after
			vcExceedLowerThresholdIncrease is generated."
	::= 16907

    vcExceedingLowerThreshold12 TRAP-TYPE
	ENTERPRISE	network-device
	VARIABLES	{ vcValue, adminDateAndTime, adminNDTrapSeqNo,
			  vcIndex, vcType }
	DESCRIPTION	"This trap is generated when set
			vcExLoThresholdTrapID equal 12 and
			until vcExceedLowerThresholdDecrease is generated after
			vcExceedLowerThresholdIncrease is generated."
	::= 16908

    vcExceedingLowerThreshold13 TRAP-TYPE
	ENTERPRISE	network-device
	VARIABLES	{ vcValue, adminDateAndTime, adminNDTrapSeqNo,
			  vcIndex, vcType }
	DESCRIPTION	"This trap is generated when set
			vcExLoThresholdTrapID equal 13 and
			until vcExceedLowerThresholdDecrease is generated after
			vcExceedLowerThresholdIncrease is generated."
	::= 16909

    vcExceedingLowerThreshold14 TRAP-TYPE
	ENTERPRISE	network-device
	VARIABLES	{ vcValue, adminDateAndTime, adminNDTrapSeqNo,
			  vcIndex, vcType }
	DESCRIPTION	"This trap is generated when set
			vcExLoThresholdTrapID equal 14 and
			until vcExceedLowerThresholdDecrease is generated after
			vcExceedLowerThresholdIncrease is generated."
	::= 16910

    vcExceedingLowerThreshold15 TRAP-TYPE
	ENTERPRISE	network-device
	VARIABLES	{ vcValue, adminDateAndTime, adminNDTrapSeqNo,
			  vcIndex, vcType }
	DESCRIPTION	"This trap is generated when set
			vcExLoThresholdTrapID equal 15 and
			until vcExceedLowerThresholdDecrease is generated after
			vcExceedLowerThresholdIncrease is generated."
	::= 16911

    vcExceedingLowerThreshold16 TRAP-TYPE
	ENTERPRISE	network-device
	VARIABLES	{ vcValue, adminDateAndTime, adminNDTrapSeqNo,
			  vcIndex, vcType }
	DESCRIPTION	"This trap is generated when set
			vcExLoThresholdTrapID equal 16 and
			until vcExceedLowerThresholdDecrease is generated after
			vcExceedLowerThresholdIncrease is generated."
	::= 16912

    vcExceedingLowerThreshold17 TRAP-TYPE
	ENTERPRISE	network-device
	VARIABLES	{ vcValue, adminDateAndTime, adminNDTrapSeqNo,
			  vcIndex, vcType }
	DESCRIPTION	"This trap is generated when set
			vcExLoThresholdTrapID equal 17 and
			until vcExceedLowerThresholdDecrease is generated after
			vcExceedLowerThresholdIncrease is generated."
	::= 16913

    vcExceedingLowerThreshold18 TRAP-TYPE
	ENTERPRISE	network-device
	VARIABLES	{ vcValue, adminDateAndTime, adminNDTrapSeqNo,
			  vcIndex, vcType }
	DESCRIPTION	"This trap is generated when set
			vcExLoThresholdTrapID equal 18 and
			until vcExceedLowerThresholdDecrease is generated after
			vcExceedLowerThresholdIncrease is generated."
	::= 16914

    vcExceedingLowerThreshold19 TRAP-TYPE
	ENTERPRISE	network-device
	VARIABLES	{ vcValue, adminDateAndTime, adminNDTrapSeqNo,
			  vcIndex, vcType }
	DESCRIPTION	"This trap is generated when set
			vcExLoThresholdTrapID equal 19 and
			until vcExceedLowerThresholdDecrease is generated after
			vcExceedLowerThresholdIncrease is generated."
	::= 16915

    vcExceedingLowerThreshold20 TRAP-TYPE
	ENTERPRISE	network-device
	VARIABLES	{ vcValue, adminDateAndTime, adminNDTrapSeqNo,
			  vcIndex, vcType }
	DESCRIPTION	"This trap is generated when set
			vcExLoThresholdTrapID equal 20 and
			until vcExceedLowerThresholdDecrease is generated after
			vcExceedLowerThresholdIncrease is generated."
	::= 16916

    vcExceedingLowerThreshold21 TRAP-TYPE
	ENTERPRISE	network-device
	VARIABLES	{ vcValue, adminDateAndTime, adminNDTrapSeqNo,
			  vcIndex, vcType }
	DESCRIPTION	"This trap is generated when set
			vcExLoThresholdTrapID equal 21 and
			until vcExceedLowerThresholdDecrease is generated after
			vcExceedLowerThresholdIncrease is generated."
	::= 16917

    vcExceedingLowerThreshold22 TRAP-TYPE
	ENTERPRISE	network-device
	VARIABLES	{ vcValue, adminDateAndTime, adminNDTrapSeqNo,
			  vcIndex, vcType }
	DESCRIPTION	"This trap is generated when set
			vcExLoThresholdTrapID equal 22 and
			until vcExceedLowerThresholdDecrease is generated after
			vcExceedLowerThresholdIncrease is generated."
	::= 16918

    vcExceedingLowerThreshold23 TRAP-TYPE
	ENTERPRISE	network-device
	VARIABLES	{ vcValue, adminDateAndTime, adminNDTrapSeqNo,
			  vcIndex, vcType }
	DESCRIPTION	"This trap is generated when set
			vcExLoThresholdTrapID equal 23 and
			until vcExceedLowerThresholdDecrease is generated after
			vcExceedLowerThresholdIncrease is generated."
	::= 16919

    vcExceedingLowerThreshold24 TRAP-TYPE
	ENTERPRISE	network-device
	VARIABLES	{ vcValue, adminDateAndTime, adminNDTrapSeqNo,
			  vcIndex, vcType }
	DESCRIPTION	"This trap is generated when set
			vcExLoThresholdTrapID equal 24 and
			until vcExceedLowerThresholdDecrease is generated after
			vcExceedLowerThresholdIncrease is generated."
	::= 16920

    vcExceedingLowerThreshold25 TRAP-TYPE
	ENTERPRISE	network-device
	VARIABLES	{ vcValue, adminDateAndTime, adminNDTrapSeqNo,
			  vcIndex, vcType }
	DESCRIPTION	"This trap is generated when set
			vcExLoThresholdTrapID equal 25 and
			until vcExceedLowerThresholdDecrease is generated after
			vcExceedLowerThresholdIncrease is generated."
	::= 16921

    vcExceedingLowerThreshold26 TRAP-TYPE
	ENTERPRISE	network-device
	VARIABLES	{ vcValue, adminDateAndTime, adminNDTrapSeqNo,
			  vcIndex, vcType }
	DESCRIPTION	"This trap is generated when set
			vcExLoThresholdTrapID equal 26 and
			until vcExceedLowerThresholdDecrease is generated after
			vcExceedLowerThresholdIncrease is generated."
	::= 16922

    vcExceedingLowerThreshold27 TRAP-TYPE
	ENTERPRISE	network-device
	VARIABLES	{ vcValue, adminDateAndTime, adminNDTrapSeqNo,
			  vcIndex, vcType }
	DESCRIPTION	"This trap is generated when set
			vcExLoThresholdTrapID equal 27 and
			until vcExceedLowerThresholdDecrease is generated after
			vcExceedLowerThresholdIncrease is generated."
	::= 16923

    vcExceedingLowerThreshold28 TRAP-TYPE
	ENTERPRISE	network-device
	VARIABLES	{ vcValue, adminDateAndTime, adminNDTrapSeqNo,
			  vcIndex, vcType }
	DESCRIPTION	"This trap is generated when set
			vcExLoThresholdTrapID equal 28 and
			until vcExceedLowerThresholdDecrease is generated after
			vcExceedLowerThresholdIncrease is generated."
	::= 16924

    vcExceedingLowerThreshold29 TRAP-TYPE
	ENTERPRISE	network-device
	VARIABLES	{ vcValue, adminDateAndTime, adminNDTrapSeqNo,
			  vcIndex, vcType }
	DESCRIPTION	"This trap is generated when set
			vcExLoThresholdTrapID equal 29 and
			until vcExceedLowerThresholdDecrease is generated after
			vcExceedLowerThresholdIncrease is generated."
	::= 16925

    vcExceedingLowerThreshold30 TRAP-TYPE
	ENTERPRISE	network-device
	VARIABLES	{ vcValue, adminDateAndTime, adminNDTrapSeqNo,
			  vcIndex, vcType }
	DESCRIPTION	"This trap is generated when set
			vcExLoThresholdTrapID equal 30 and
			until vcExceedLowerThresholdDecrease is generated after
			vcExceedLowerThresholdIncrease is generated."
	::= 16926

    vcExceedingLowerThreshold31 TRAP-TYPE
	ENTERPRISE	network-device
	VARIABLES	{ vcValue, adminDateAndTime, adminNDTrapSeqNo,
			  vcIndex, vcType }
	DESCRIPTION	"This trap is generated when set
			vcExLoThresholdTrapID equal 31 and
			until vcExceedLowerThresholdDecrease is generated after
			vcExceedLowerThresholdIncrease is generated."
	::= 16927

    vcExceedingLowerThreshold32 TRAP-TYPE
	ENTERPRISE	network-device
	VARIABLES	{ vcValue, adminDateAndTime, adminNDTrapSeqNo,
			  vcIndex, vcType }
	DESCRIPTION	"This trap is generated when set
			vcExLoThresholdTrapID equal 32 and
			until vcExceedLowerThresholdDecrease is generated after
			vcExceedLowerThresholdIncrease is generated."
	::= 16928

    vcExceedingLowerThreshold33 TRAP-TYPE
	ENTERPRISE	network-device
	VARIABLES	{ vcValue, adminDateAndTime, adminNDTrapSeqNo,
			  vcIndex, vcType }
	DESCRIPTION	"This trap is generated when set
			vcExLoThresholdTrapID equal 33 and
			until vcExceedLowerThresholdDecrease is generated after
			vcExceedLowerThresholdIncrease is generated."
	::= 16929

    vcExceedingLowerThreshold34 TRAP-TYPE
	ENTERPRISE	network-device
	VARIABLES	{ vcValue, adminDateAndTime, adminNDTrapSeqNo,
			  vcIndex, vcType }
	DESCRIPTION	"This trap is generated when set
			vcExLoThresholdTrapID equal 34 and
			until vcExceedLowerThresholdDecrease is generated after
			vcExceedLowerThresholdIncrease is generated."
	::= 16930

    vcExceedingLowerThreshold35 TRAP-TYPE
	ENTERPRISE	network-device
	VARIABLES	{ vcValue, adminDateAndTime, adminNDTrapSeqNo,
			  vcIndex, vcType }
	DESCRIPTION	"This trap is generated when set
			vcExLoThresholdTrapID equal 35 and
			until vcExceedLowerThresholdDecrease is generated after
			vcExceedLowerThresholdIncrease is generated."
	::= 16931

    vcExceedingLowerThreshold36 TRAP-TYPE
	ENTERPRISE	network-device
	VARIABLES	{ vcValue, adminDateAndTime, adminNDTrapSeqNo,
			  vcIndex, vcType }
	DESCRIPTION	"This trap is generated when set
			vcExLoThresholdTrapID equal 36 and
			until vcExceedLowerThresholdDecrease is generated after
			vcExceedLowerThresholdIncrease is generated."
	::= 16932

    vcExceedingLowerThreshold37 TRAP-TYPE
	ENTERPRISE	network-device
	VARIABLES	{ vcValue, adminDateAndTime, adminNDTrapSeqNo,
			  vcIndex, vcType }
	DESCRIPTION	"This trap is generated when set
			vcExLoThresholdTrapID equal 37 and
			until vcExceedLowerThresholdDecrease is generated after
			vcExceedLowerThresholdIncrease is generated."
	::= 16933

    vcExceedingLowerThreshold38 TRAP-TYPE
	ENTERPRISE	network-device
	VARIABLES	{ vcValue, adminDateAndTime, adminNDTrapSeqNo,
			  vcIndex, vcType }
	DESCRIPTION	"This trap is generated when set
			vcExLoThresholdTrapID equal 38 and
			until vcExceedLowerThresholdDecrease is generated after
			vcExceedLowerThresholdIncrease is generated."
	::= 16934

    vcExceedingLowerThreshold39 TRAP-TYPE
	ENTERPRISE	network-device
	VARIABLES	{ vcValue, adminDateAndTime, adminNDTrapSeqNo,
			  vcIndex, vcType }
	DESCRIPTION	"This trap is generated when set
			vcExLoThresholdTrapID equal 39 and
			until vcExceedLowerThresholdDecrease is generated after
			vcExceedLowerThresholdIncrease is generated."
	::= 16935

    vcExceedingLowerThreshold40 TRAP-TYPE
	ENTERPRISE	network-device
	VARIABLES	{ vcValue, adminDateAndTime, adminNDTrapSeqNo,
			  vcIndex, vcType }
	DESCRIPTION	"This trap is generated when set
			vcExLoThresholdTrapID equal 40 and
			until vcExceedLowerThresholdDecrease is generated after
			vcExceedLowerThresholdIncrease is generated."
	::= 16936

    vcExceedingLowerThreshold41 TRAP-TYPE
	ENTERPRISE	network-device
	VARIABLES	{ vcValue, adminDateAndTime, adminNDTrapSeqNo,
			  vcIndex, vcType }
	DESCRIPTION	"This trap is generated when set
			vcExLoThresholdTrapID equal 41 and
			until vcExceedLowerThresholdDecrease is generated after
			vcExceedLowerThresholdIncrease is generated."
	::= 16937

    vcExceedingLowerThreshold42 TRAP-TYPE
	ENTERPRISE	network-device
	VARIABLES	{ vcValue, adminDateAndTime, adminNDTrapSeqNo,
			  vcIndex, vcType }
	DESCRIPTION	"This trap is generated when set
			vcExLoThresholdTrapID equal 42 and
			until vcExceedLowerThresholdDecrease is generated after
			vcExceedLowerThresholdIncrease is generated."
	::= 16938

    vcExceedingLowerThreshold43 TRAP-TYPE
	ENTERPRISE	network-device
	VARIABLES	{ vcValue, adminDateAndTime, adminNDTrapSeqNo,
			  vcIndex, vcType }
	DESCRIPTION	"This trap is generated when set
			vcExLoThresholdTrapID equal 43 and
			until vcExceedLowerThresholdDecrease is generated after
			vcExceedLowerThresholdIncrease is generated."
	::= 16939

    vcExceedingLowerThreshold44 TRAP-TYPE
	ENTERPRISE	network-device
	VARIABLES	{ vcValue, adminDateAndTime, adminNDTrapSeqNo,
			  vcIndex, vcType }
	DESCRIPTION	"This trap is generated when set
			vcExLoThresholdTrapID equal 44 and
			until vcExceedLowerThresholdDecrease is generated after
			vcExceedLowerThresholdIncrease is generated."
	::= 16940

    vcExceedingLowerThreshold45 TRAP-TYPE
	ENTERPRISE	network-device
	VARIABLES	{ vcValue, adminDateAndTime, adminNDTrapSeqNo,
			  vcIndex, vcType }
	DESCRIPTION	"This trap is generated when set
			vcExLoThresholdTrapID equal 45 and
			until vcExceedLowerThresholdDecrease is generated after
			vcExceedLowerThresholdIncrease is generated."
	::= 16941

    vcExceedingLowerThreshold46 TRAP-TYPE
	ENTERPRISE	network-device
	VARIABLES	{ vcValue, adminDateAndTime, adminNDTrapSeqNo,
			  vcIndex, vcType }
	DESCRIPTION	"This trap is generated when set
			vcExLoThresholdTrapID equal 46 and
			until vcExceedLowerThresholdDecrease is generated after
			vcExceedLowerThresholdIncrease is generated."
	::= 16942

    vcExceedingLowerThreshold47 TRAP-TYPE
	ENTERPRISE	network-device
	VARIABLES	{ vcValue, adminDateAndTime, adminNDTrapSeqNo,
			  vcIndex, vcType }
	DESCRIPTION	"This trap is generated when set
			vcExLoThresholdTrapID equal 47 and
			until vcExceedLowerThresholdDecrease is generated after
			vcExceedLowerThresholdIncrease is generated."
	::= 16943

    vcExceedingLowerThreshold48 TRAP-TYPE
	ENTERPRISE	network-device
	VARIABLES	{ vcValue, adminDateAndTime, adminNDTrapSeqNo,
			  vcIndex, vcType }
	DESCRIPTION	"This trap is generated when set
			vcExLoThresholdTrapID equal 48 and
			until vcExceedLowerThresholdDecrease is generated after
			vcExceedLowerThresholdIncrease is generated."
	::= 16944

    vcExceedingLowerThreshold49 TRAP-TYPE
	ENTERPRISE	network-device
	VARIABLES	{ vcValue, adminDateAndTime, adminNDTrapSeqNo,
			  vcIndex, vcType }
	DESCRIPTION	"This trap is generated when set
			vcExLoThresholdTrapID equal 49 and
			until vcExceedLowerThresholdDecrease is generated after
			vcExceedLowerThresholdIncrease is generated."
	::= 16945

    vcExceedingLowerThreshold50 TRAP-TYPE
	ENTERPRISE	network-device
	VARIABLES	{ vcValue, adminDateAndTime, adminNDTrapSeqNo,
			  vcIndex, vcType }
	DESCRIPTION	"This trap is generated when set
			vcExLoThresholdTrapID equal 50 and
			until vcExceedLowerThresholdDecrease is generated after
			vcExceedLowerThresholdIncrease is generated."
	::= 16946

    vcExceedingLowerThreshold51 TRAP-TYPE
	ENTERPRISE	network-device
	VARIABLES	{ vcValue, adminDateAndTime, adminNDTrapSeqNo,
			  vcIndex, vcType }
	DESCRIPTION	"This trap is generated when set
			vcExLoThresholdTrapID equal 51 and
			until vcExceedLowerThresholdDecrease is generated after
			vcExceedLowerThresholdIncrease is generated."
	::= 16947

    vcExceedingLowerThreshold52 TRAP-TYPE
	ENTERPRISE	network-device
	VARIABLES	{ vcValue, adminDateAndTime, adminNDTrapSeqNo,
			  vcIndex, vcType }
	DESCRIPTION	"This trap is generated when set
			vcExLoThresholdTrapID equal 52 and
			until vcExceedLowerThresholdDecrease is generated after
			vcExceedLowerThresholdIncrease is generated."
	::= 16948

    vcExceedingLowerThreshold53 TRAP-TYPE
	ENTERPRISE	network-device
	VARIABLES	{ vcValue, adminDateAndTime, adminNDTrapSeqNo,
			  vcIndex, vcType }
	DESCRIPTION	"This trap is generated when set
			vcExLoThresholdTrapID equal 53 and
			until vcExceedLowerThresholdDecrease is generated after
			vcExceedLowerThresholdIncrease is generated."
	::= 16949

    vcExceedingLowerThreshold54 TRAP-TYPE
	ENTERPRISE	network-device
	VARIABLES	{ vcValue, adminDateAndTime, adminNDTrapSeqNo,
			  vcIndex, vcType }
	DESCRIPTION	"This trap is generated when set
			vcExLoThresholdTrapID equal 54 and
			until vcExceedLowerThresholdDecrease is generated after
			vcExceedLowerThresholdIncrease is generated."
	::= 16950

    vcExceedingLowerThreshold55 TRAP-TYPE
	ENTERPRISE	network-device
	VARIABLES	{ vcValue, adminDateAndTime, adminNDTrapSeqNo,
			  vcIndex, vcType }
	DESCRIPTION	"This trap is generated when set
			vcExLoThresholdTrapID equal 55 and
			until vcExceedLowerThresholdDecrease is generated after
			vcExceedLowerThresholdIncrease is generated."
	::= 16951

    vcExceedingLowerThreshold56 TRAP-TYPE
	ENTERPRISE	network-device
	VARIABLES	{ vcValue, adminDateAndTime, adminNDTrapSeqNo,
			  vcIndex, vcType }
	DESCRIPTION	"This trap is generated when set
			vcExLoThresholdTrapID equal 56 and
			until vcExceedLowerThresholdDecrease is generated after
			vcExceedLowerThresholdIncrease is generated."
	::= 16952

    vcExceedingLowerThreshold57 TRAP-TYPE
	ENTERPRISE	network-device
	VARIABLES	{ vcValue, adminDateAndTime, adminNDTrapSeqNo,
			  vcIndex, vcType }
	DESCRIPTION	"This trap is generated when set
			vcExLoThresholdTrapID equal 57 and
			until vcExceedLowerThresholdDecrease is generated after
			vcExceedLowerThresholdIncrease is generated."
	::= 16953

    vcExceedingLowerThreshold58 TRAP-TYPE
	ENTERPRISE	network-device
	VARIABLES	{ vcValue, adminDateAndTime, adminNDTrapSeqNo,
			  vcIndex, vcType }
	DESCRIPTION	"This trap is generated when set
			vcExLoThresholdTrapID equal 58 and
			until vcExceedLowerThresholdDecrease is generated after
			vcExceedLowerThresholdIncrease is generated."
	::= 16954

    vcExceedingLowerThreshold59 TRAP-TYPE
	ENTERPRISE	network-device
	VARIABLES	{ vcValue, adminDateAndTime, adminNDTrapSeqNo,
			  vcIndex, vcType }
	DESCRIPTION	"This trap is generated when set
			vcExLoThresholdTrapID equal 59 and
			until vcExceedLowerThresholdDecrease is generated after
			vcExceedLowerThresholdIncrease is generated."
	::= 16955

    vcExceedingLowerThreshold60 TRAP-TYPE
	ENTERPRISE	network-device
	VARIABLES	{ vcValue, adminDateAndTime, adminNDTrapSeqNo,
			  vcIndex, vcType }
	DESCRIPTION	"This trap is generated when set
			vcExLoThresholdTrapID equal 60 and
			until vcExceedLowerThresholdDecrease is generated after
			vcExceedLowerThresholdIncrease is generated."
	::= 16956

    vcExceedingLowerThreshold61 TRAP-TYPE
	ENTERPRISE	network-device
	VARIABLES	{ vcValue, adminDateAndTime, adminNDTrapSeqNo,
			  vcIndex, vcType }
	DESCRIPTION	"This trap is generated when set
			vcExLoThresholdTrapID equal 61 and
			until vcExceedLowerThresholdDecrease is generated after
			vcExceedLowerThresholdIncrease is generated."
	::= 16957

    vcExceedingLowerThreshold62 TRAP-TYPE
	ENTERPRISE	network-device
	VARIABLES	{ vcValue, adminDateAndTime, adminNDTrapSeqNo,
			  vcIndex, vcType }
	DESCRIPTION	"This trap is generated when set
			vcExLoThresholdTrapID equal 62 and
			until vcExceedLowerThresholdDecrease is generated after
			vcExceedLowerThresholdIncrease is generated."
	::= 16958

    vcExceedingLowerThreshold63 TRAP-TYPE
	ENTERPRISE	network-device
	VARIABLES	{ vcValue, adminDateAndTime, adminNDTrapSeqNo,
			  vcIndex, vcType }
	DESCRIPTION	"This trap is generated when set
			vcExLoThresholdTrapID equal 63 and
			until vcExceedLowerThresholdDecrease is generated after
			vcExceedLowerThresholdIncrease is generated."
	::= 16959

    vcExceedingLowerThreshold64 TRAP-TYPE
	ENTERPRISE	network-device
	VARIABLES	{ vcValue, adminDateAndTime, adminNDTrapSeqNo,
			  vcIndex, vcType }
	DESCRIPTION	"This trap is generated when set
			vcExLoThresholdTrapID equal 64 and
			until vcExceedLowerThresholdDecrease is generated after
			vcExceedLowerThresholdIncrease is generated."
	::= 16960

    vcExceedingLowerThreshold65 TRAP-TYPE
	ENTERPRISE	network-device
	VARIABLES	{ vcValue, adminDateAndTime, adminNDTrapSeqNo,
			  vcIndex, vcType }
	DESCRIPTION	"This trap is generated when set
			vcExLoThresholdTrapID equal 65 and
			until vcExceedLowerThresholdDecrease is generated after
			vcExceedLowerThresholdIncrease is generated."
	::= 16961

    vcExceedingLowerThreshold66 TRAP-TYPE
	ENTERPRISE	network-device
	VARIABLES	{ vcValue, adminDateAndTime, adminNDTrapSeqNo,
			  vcIndex, vcType }
	DESCRIPTION	"This trap is generated when set
			vcExLoThresholdTrapID equal 66 and
			until vcExceedLowerThresholdDecrease is generated after
			vcExceedLowerThresholdIncrease is generated."
	::= 16962

    vcExceedingLowerThreshold67 TRAP-TYPE
	ENTERPRISE	network-device
	VARIABLES	{ vcValue, adminDateAndTime, adminNDTrapSeqNo,
			  vcIndex, vcType }
	DESCRIPTION	"This trap is generated when set
			vcExLoThresholdTrapID equal 67 and
			until vcExceedLowerThresholdDecrease is generated after
			vcExceedLowerThresholdIncrease is generated."
	::= 16963

    vcExceedingLowerThreshold68 TRAP-TYPE
	ENTERPRISE	network-device
	VARIABLES	{ vcValue, adminDateAndTime, adminNDTrapSeqNo,
			  vcIndex, vcType }
	DESCRIPTION	"This trap is generated when set
			vcExLoThresholdTrapID equal 68 and
			until vcExceedLowerThresholdDecrease is generated after
			vcExceedLowerThresholdIncrease is generated."
	::= 16964

    vcExceedingLowerThreshold69 TRAP-TYPE
	ENTERPRISE	network-device
	VARIABLES	{ vcValue, adminDateAndTime, adminNDTrapSeqNo,
			  vcIndex, vcType }
	DESCRIPTION	"This trap is generated when set
			vcExLoThresholdTrapID equal 69 and
			until vcExceedLowerThresholdDecrease is generated after
			vcExceedLowerThresholdIncrease is generated."
	::= 16965

    vcExceedingLowerThreshold70 TRAP-TYPE
	ENTERPRISE	network-device
	VARIABLES	{ vcValue, adminDateAndTime, adminNDTrapSeqNo,
			  vcIndex, vcType }
	DESCRIPTION	"This trap is generated when set
			vcExLoThresholdTrapID equal 70 and
			until vcExceedLowerThresholdDecrease is generated after
			vcExceedLowerThresholdIncrease is generated."
	::= 16966

    vcExceedingLowerThreshold71 TRAP-TYPE
	ENTERPRISE	network-device
	VARIABLES	{ vcValue, adminDateAndTime, adminNDTrapSeqNo,
			  vcIndex, vcType }
	DESCRIPTION	"This trap is generated when set
			vcExLoThresholdTrapID equal 71 and
			until vcExceedLowerThresholdDecrease is generated after
			vcExceedLowerThresholdIncrease is generated."
	::= 16967

    vcExceedingLowerThreshold72 TRAP-TYPE
	ENTERPRISE	network-device
	VARIABLES	{ vcValue, adminDateAndTime, adminNDTrapSeqNo,
			  vcIndex, vcType }
	DESCRIPTION	"This trap is generated when set
			vcExLoThresholdTrapID equal 72 and
			until vcExceedLowerThresholdDecrease is generated after
			vcExceedLowerThresholdIncrease is generated."
	::= 16968

    vcExceedingLowerThreshold73 TRAP-TYPE
	ENTERPRISE	network-device
	VARIABLES	{ vcValue, adminDateAndTime, adminNDTrapSeqNo,
			  vcIndex, vcType }
	DESCRIPTION	"This trap is generated when set
			vcExLoThresholdTrapID equal 73 and
			until vcExceedLowerThresholdDecrease is generated after
			vcExceedLowerThresholdIncrease is generated."
	::= 16969

    vcExceedingLowerThreshold74 TRAP-TYPE
	ENTERPRISE	network-device
	VARIABLES	{ vcValue, adminDateAndTime, adminNDTrapSeqNo,
			  vcIndex, vcType }
	DESCRIPTION	"This trap is generated when set
			vcExLoThresholdTrapID equal 74 and
			until vcExceedLowerThresholdDecrease is generated after
			vcExceedLowerThresholdIncrease is generated."
	::= 16970

    vcExceedingLowerThreshold75 TRAP-TYPE
	ENTERPRISE	network-device
	VARIABLES	{ vcValue, adminDateAndTime, adminNDTrapSeqNo,
			  vcIndex, vcType }
	DESCRIPTION	"This trap is generated when set
			vcExLoThresholdTrapID equal 75 and
			until vcExceedLowerThresholdDecrease is generated after
			vcExceedLowerThresholdIncrease is generated."
	::= 16971

    vcExceedingLowerThreshold76 TRAP-TYPE
	ENTERPRISE	network-device
	VARIABLES	{ vcValue, adminDateAndTime, adminNDTrapSeqNo,
			  vcIndex, vcType }
	DESCRIPTION	"This trap is generated when set
			vcExLoThresholdTrapID equal 76 and
			until vcExceedLowerThresholdDecrease is generated after
			vcExceedLowerThresholdIncrease is generated."
	::= 16972

    vcExceedingLowerThreshold77 TRAP-TYPE
	ENTERPRISE	network-device
	VARIABLES	{ vcValue, adminDateAndTime, adminNDTrapSeqNo,
			  vcIndex, vcType }
	DESCRIPTION	"This trap is generated when set
			vcExLoThresholdTrapID equal 77 and
			until vcExceedLowerThresholdDecrease is generated after
			vcExceedLowerThresholdIncrease is generated."
	::= 16973

    vcExceedingLowerThreshold78 TRAP-TYPE
	ENTERPRISE	network-device
	VARIABLES	{ vcValue, adminDateAndTime, adminNDTrapSeqNo,
			  vcIndex, vcType }
	DESCRIPTION	"This trap is generated when set
			vcExLoThresholdTrapID equal 78 and
			until vcExceedLowerThresholdDecrease is generated after
			vcExceedLowerThresholdIncrease is generated."
	::= 16974

    vcExceedingLowerThreshold79 TRAP-TYPE
	ENTERPRISE	network-device
	VARIABLES	{ vcValue, adminDateAndTime, adminNDTrapSeqNo,
			  vcIndex, vcType }
	DESCRIPTION	"This trap is generated when set
			vcExLoThresholdTrapID equal 79 and
			until vcExceedLowerThresholdDecrease is generated after
			vcExceedLowerThresholdIncrease is generated."
	::= 16975

    vcExceedingLowerThreshold80 TRAP-TYPE
	ENTERPRISE	network-device
	VARIABLES	{ vcValue, adminDateAndTime, adminNDTrapSeqNo,
			  vcIndex, vcType }
	DESCRIPTION	"This trap is generated when set
			vcExLoThresholdTrapID equal 80 and
			until vcExceedLowerThresholdDecrease is generated after
			vcExceedLowerThresholdIncrease is generated."
	::= 16976

    vcExceedingLowerThreshold81 TRAP-TYPE
	ENTERPRISE	network-device
	VARIABLES	{ vcValue, adminDateAndTime, adminNDTrapSeqNo,
			  vcIndex, vcType }
	DESCRIPTION	"This trap is generated when set
			vcExLoThresholdTrapID equal 81 and
			until vcExceedLowerThresholdDecrease is generated after
			vcExceedLowerThresholdIncrease is generated."
	::= 16977

    vcExceedingLowerThreshold82 TRAP-TYPE
	ENTERPRISE	network-device
	VARIABLES	{ vcValue, adminDateAndTime, adminNDTrapSeqNo,
			  vcIndex, vcType }
	DESCRIPTION	"This trap is generated when set
			vcExLoThresholdTrapID equal 82 and
			until vcExceedLowerThresholdDecrease is generated after
			vcExceedLowerThresholdIncrease is generated."
	::= 16978

    vcExceedingLowerThreshold83 TRAP-TYPE
	ENTERPRISE	network-device
	VARIABLES	{ vcValue, adminDateAndTime, adminNDTrapSeqNo,
			  vcIndex, vcType }
	DESCRIPTION	"This trap is generated when set
			vcExLoThresholdTrapID equal 83 and
			until vcExceedLowerThresholdDecrease is generated after
			vcExceedLowerThresholdIncrease is generated."
	::= 16979

    vcExceedingLowerThreshold84 TRAP-TYPE
	ENTERPRISE	network-device
	VARIABLES	{ vcValue, adminDateAndTime, adminNDTrapSeqNo,
			  vcIndex, vcType }
	DESCRIPTION	"This trap is generated when set
			vcExLoThresholdTrapID equal 84 and
			until vcExceedLowerThresholdDecrease is generated after
			vcExceedLowerThresholdIncrease is generated."
	::= 16980

    vcExceedingLowerThreshold85 TRAP-TYPE
	ENTERPRISE	network-device
	VARIABLES	{ vcValue, adminDateAndTime, adminNDTrapSeqNo,
			  vcIndex, vcType }
	DESCRIPTION	"This trap is generated when set
			vcExLoThresholdTrapID equal 85 and
			until vcExceedLowerThresholdDecrease is generated after
			vcExceedLowerThresholdIncrease is generated."
	::= 16981

    vcExceedingLowerThreshold86 TRAP-TYPE
	ENTERPRISE	network-device
	VARIABLES	{ vcValue, adminDateAndTime, adminNDTrapSeqNo,
			  vcIndex, vcType }
	DESCRIPTION	"This trap is generated when set
			vcExLoThresholdTrapID equal 86 and
			until vcExceedLowerThresholdDecrease is generated after
			vcExceedLowerThresholdIncrease is generated."
	::= 16982

    vcExceedingLowerThreshold87 TRAP-TYPE
	ENTERPRISE	network-device
	VARIABLES	{ vcValue, adminDateAndTime, adminNDTrapSeqNo,
			  vcIndex, vcType }
	DESCRIPTION	"This trap is generated when set
			vcExLoThresholdTrapID equal 87 and
			until vcExceedLowerThresholdDecrease is generated after
			vcExceedLowerThresholdIncrease is generated."
	::= 16983

    vcExceedingLowerThreshold88 TRAP-TYPE
	ENTERPRISE	network-device
	VARIABLES	{ vcValue, adminDateAndTime, adminNDTrapSeqNo,
			  vcIndex, vcType }
	DESCRIPTION	"This trap is generated when set
			vcExLoThresholdTrapID equal 88 and
			until vcExceedLowerThresholdDecrease is generated after
			vcExceedLowerThresholdIncrease is generated."
	::= 16984

    vcExceedingLowerThreshold89 TRAP-TYPE
	ENTERPRISE	network-device
	VARIABLES	{ vcValue, adminDateAndTime, adminNDTrapSeqNo,
			  vcIndex, vcType }
	DESCRIPTION	"This trap is generated when set
			vcExLoThresholdTrapID equal 89 and
			until vcExceedLowerThresholdDecrease is generated after
			vcExceedLowerThresholdIncrease is generated."
	::= 16985

    vcExceedingLowerThreshold90 TRAP-TYPE
	ENTERPRISE	network-device
	VARIABLES	{ vcValue, adminDateAndTime, adminNDTrapSeqNo,
			  vcIndex, vcType }
	DESCRIPTION	"This trap is generated when set
			vcExLoThresholdTrapID equal 90 and
			until vcExceedLowerThresholdDecrease is generated after
			vcExceedLowerThresholdIncrease is generated."
	::= 16986

    vcExceedingLowerThreshold91 TRAP-TYPE
	ENTERPRISE	network-device
	VARIABLES	{ vcValue, adminDateAndTime, adminNDTrapSeqNo,
			  vcIndex, vcType }
	DESCRIPTION	"This trap is generated when set
			vcExLoThresholdTrapID equal 91 and
			until vcExceedLowerThresholdDecrease is generated after
			vcExceedLowerThresholdIncrease is generated."
	::= 16987

    vcExceedingLowerThreshold92 TRAP-TYPE
	ENTERPRISE	network-device
	VARIABLES	{ vcValue, adminDateAndTime, adminNDTrapSeqNo,
			  vcIndex, vcType }
	DESCRIPTION	"This trap is generated when set
			vcExLoThresholdTrapID equal 92 and
			until vcExceedLowerThresholdDecrease is generated after
			vcExceedLowerThresholdIncrease is generated."
	::= 16988

    vcExceedingLowerThreshold93 TRAP-TYPE
	ENTERPRISE	network-device
	VARIABLES	{ vcValue, adminDateAndTime, adminNDTrapSeqNo,
			  vcIndex, vcType }
	DESCRIPTION	"This trap is generated when set
			vcExLoThresholdTrapID equal 93 and
			until vcExceedLowerThresholdDecrease is generated after
			vcExceedLowerThresholdIncrease is generated."
	::= 16989

    vcExceedingLowerThreshold94 TRAP-TYPE
	ENTERPRISE	network-device
	VARIABLES	{ vcValue, adminDateAndTime, adminNDTrapSeqNo,
			  vcIndex, vcType }
	DESCRIPTION	"This trap is generated when set
			vcExLoThresholdTrapID equal 94 and
			until vcExceedLowerThresholdDecrease is generated after
			vcExceedLowerThresholdIncrease is generated."
	::= 16990

    vcExceedingLowerThreshold95 TRAP-TYPE
	ENTERPRISE	network-device
	VARIABLES	{ vcValue, adminDateAndTime, adminNDTrapSeqNo,
			  vcIndex, vcType }
	DESCRIPTION	"This trap is generated when set
			vcExLoThresholdTrapID equal 95 and
			until vcExceedLowerThresholdDecrease is generated after
			vcExceedLowerThresholdIncrease is generated."
	::= 16991

    vcExceedingLowerThreshold96 TRAP-TYPE
	ENTERPRISE	network-device
	VARIABLES	{ vcValue, adminDateAndTime, adminNDTrapSeqNo,
			  vcIndex, vcType }
	DESCRIPTION	"This trap is generated when set
			vcExLoThresholdTrapID equal 96 and
			until vcExceedLowerThresholdDecrease is generated after
			vcExceedLowerThresholdIncrease is generated."
	::= 16992

    vcExceedingLowerThreshold97 TRAP-TYPE
	ENTERPRISE	network-device
	VARIABLES	{ vcValue, adminDateAndTime, adminNDTrapSeqNo,
			  vcIndex, vcType }
	DESCRIPTION	"This trap is generated when set
			vcExLoThresholdTrapID equal 97 and
			until vcExceedLowerThresholdDecrease is generated after
			vcExceedLowerThresholdIncrease is generated."
	::= 16993

    vcExceedingLowerThreshold98 TRAP-TYPE
	ENTERPRISE	network-device
	VARIABLES	{ vcValue, adminDateAndTime, adminNDTrapSeqNo,
			  vcIndex, vcType }
	DESCRIPTION	"This trap is generated when set
			vcExLoThresholdTrapID equal 98 and
			until vcExceedLowerThresholdDecrease is generated after
			vcExceedLowerThresholdIncrease is generated."
	::= 16994

    vcExceedingLowerThreshold99 TRAP-TYPE
	ENTERPRISE	network-device
	VARIABLES	{ vcValue, adminDateAndTime, adminNDTrapSeqNo,
			  vcIndex, vcType }
	DESCRIPTION	"This trap is generated when set
			vcExLoThresholdTrapID equal 99 and
			until vcExceedLowerThresholdDecrease is generated after
			vcExceedLowerThresholdIncrease is generated."
	::= 16995

    vcExceedingLowerThreshold100 TRAP-TYPE
	ENTERPRISE	network-device
	VARIABLES	{ vcValue, adminDateAndTime, adminNDTrapSeqNo,
			  vcIndex, vcType }
	DESCRIPTION	"This trap is generated when set
			vcExLoThresholdTrapID equal 100 and
			until vcExceedLowerThresholdDecrease is generated after
			vcExceedLowerThresholdIncrease is generated."
	::= 16996

    vcExceedingLowerThreshold101 TRAP-TYPE
	ENTERPRISE	network-device
	VARIABLES	{ vcValue, adminDateAndTime, adminNDTrapSeqNo,
			  vcIndex, vcType }
	DESCRIPTION	"This trap is generated when set
			vcExLoThresholdTrapID equal 101 and
			until vcExceedLowerThresholdDecrease is generated after
			vcExceedLowerThresholdIncrease is generated."
	::= 16997

    vcExceedingLowerThreshold102 TRAP-TYPE
	ENTERPRISE	network-device
	VARIABLES	{ vcValue, adminDateAndTime, adminNDTrapSeqNo,
			  vcIndex, vcType }
	DESCRIPTION	"This trap is generated when set
			vcExLoThresholdTrapID equal 102 and
			until vcExceedLowerThresholdDecrease is generated after
			vcExceedLowerThresholdIncrease is generated."
	::= 16998

    vcExceedingLowerThreshold103 TRAP-TYPE
	ENTERPRISE	network-device
	VARIABLES	{ vcValue, adminDateAndTime, adminNDTrapSeqNo,
			  vcIndex, vcType }
	DESCRIPTION	"This trap is generated when set
			vcExLoThresholdTrapID equal 103 and
			until vcExceedLowerThresholdDecrease is generated after
			vcExceedLowerThresholdIncrease is generated."
	::= 16999

    vcExceedingLowerThreshold104 TRAP-TYPE
	ENTERPRISE	network-device
	VARIABLES	{ vcValue, adminDateAndTime, adminNDTrapSeqNo,
			  vcIndex, vcType }
	DESCRIPTION	"This trap is generated when set
			vcExLoThresholdTrapID equal 104 and
			until vcExceedLowerThresholdDecrease is generated after
			vcExceedLowerThresholdIncrease is generated."
	::= 17000

    vcExceedingLowerThreshold105 TRAP-TYPE
	ENTERPRISE	network-device
	VARIABLES	{ vcValue, adminDateAndTime, adminNDTrapSeqNo,
			  vcIndex, vcType }
	DESCRIPTION	"This trap is generated when set
			vcExLoThresholdTrapID equal 105 and
			until vcExceedLowerThresholdDecrease is generated after
			vcExceedLowerThresholdIncrease is generated."
	::= 17001

    vcExceedingLowerThreshold106 TRAP-TYPE
	ENTERPRISE	network-device
	VARIABLES	{ vcValue, adminDateAndTime, adminNDTrapSeqNo,
			  vcIndex, vcType }
	DESCRIPTION	"This trap is generated when set
			vcExLoThresholdTrapID equal 106 and
			until vcExceedLowerThresholdDecrease is generated after
			vcExceedLowerThresholdIncrease is generated."
	::= 17002

    vcExceedingLowerThreshold107 TRAP-TYPE
	ENTERPRISE	network-device
	VARIABLES	{ vcValue, adminDateAndTime, adminNDTrapSeqNo,
			  vcIndex, vcType }
	DESCRIPTION	"This trap is generated when set
			vcExLoThresholdTrapID equal 107 and
			until vcExceedLowerThresholdDecrease is generated after
			vcExceedLowerThresholdIncrease is generated."
	::= 17003

    vcExceedingLowerThreshold108 TRAP-TYPE
	ENTERPRISE	network-device
	VARIABLES	{ vcValue, adminDateAndTime, adminNDTrapSeqNo,
			  vcIndex, vcType }
	DESCRIPTION	"This trap is generated when set
			vcExLoThresholdTrapID equal 108 and
			until vcExceedLowerThresholdDecrease is generated after
			vcExceedLowerThresholdIncrease is generated."
	::= 17004

    vcExceedingLowerThreshold109 TRAP-TYPE
	ENTERPRISE	network-device
	VARIABLES	{ vcValue, adminDateAndTime, adminNDTrapSeqNo,
			  vcIndex, vcType }
	DESCRIPTION	"This trap is generated when set
			vcExLoThresholdTrapID equal 109 and
			until vcExceedLowerThresholdDecrease is generated after
			vcExceedLowerThresholdIncrease is generated."
	::= 17005

    vcExceedingLowerThreshold110 TRAP-TYPE
	ENTERPRISE	network-device
	VARIABLES	{ vcValue, adminDateAndTime, adminNDTrapSeqNo,
			  vcIndex, vcType }
	DESCRIPTION	"This trap is generated when set
			vcExLoThresholdTrapID equal 110 and
			until vcExceedLowerThresholdDecrease is generated after
			vcExceedLowerThresholdIncrease is generated."
	::= 17006

    vcExceedingLowerThreshold111 TRAP-TYPE
	ENTERPRISE	network-device
	VARIABLES	{ vcValue, adminDateAndTime, adminNDTrapSeqNo,
			  vcIndex, vcType }
	DESCRIPTION	"This trap is generated when set
			vcExLoThresholdTrapID equal 111 and
			until vcExceedLowerThresholdDecrease is generated after
			vcExceedLowerThresholdIncrease is generated."
	::= 17007

    vcExceedingLowerThreshold112 TRAP-TYPE
	ENTERPRISE	network-device
	VARIABLES	{ vcValue, adminDateAndTime, adminNDTrapSeqNo,
			  vcIndex, vcType }
	DESCRIPTION	"This trap is generated when set
			vcExLoThresholdTrapID equal 112 and
			until vcExceedLowerThresholdDecrease is generated after
			vcExceedLowerThresholdIncrease is generated."
	::= 17008

    vcExceedingLowerThreshold113 TRAP-TYPE
	ENTERPRISE	network-device
	VARIABLES	{ vcValue, adminDateAndTime, adminNDTrapSeqNo,
			  vcIndex, vcType }
	DESCRIPTION	"This trap is generated when set
			vcExLoThresholdTrapID equal 113 and
			until vcExceedLowerThresholdDecrease is generated after
			vcExceedLowerThresholdIncrease is generated."
	::= 17009

    vcExceedingLowerThreshold114 TRAP-TYPE
	ENTERPRISE	network-device
	VARIABLES	{ vcValue, adminDateAndTime, adminNDTrapSeqNo,
			  vcIndex, vcType }
	DESCRIPTION	"This trap is generated when set
			vcExLoThresholdTrapID equal 114 and
			until vcExceedLowerThresholdDecrease is generated after
			vcExceedLowerThresholdIncrease is generated."
	::= 17010

    vcExceedingLowerThreshold115 TRAP-TYPE
	ENTERPRISE	network-device
	VARIABLES	{ vcValue, adminDateAndTime, adminNDTrapSeqNo,
			  vcIndex, vcType }
	DESCRIPTION	"This trap is generated when set
			vcExLoThresholdTrapID equal 115 and
			until vcExceedLowerThresholdDecrease is generated after
			vcExceedLowerThresholdIncrease is generated."
	::= 17011

    vcExceedingLowerThreshold116 TRAP-TYPE
	ENTERPRISE	network-device
	VARIABLES	{ vcValue, adminDateAndTime, adminNDTrapSeqNo,
			  vcIndex, vcType }
	DESCRIPTION	"This trap is generated when set
			vcExLoThresholdTrapID equal 116 and
			until vcExceedLowerThresholdDecrease is generated after
			vcExceedLowerThresholdIncrease is generated."
	::= 17012

    vcExceedingLowerThreshold117 TRAP-TYPE
	ENTERPRISE	network-device
	VARIABLES	{ vcValue, adminDateAndTime, adminNDTrapSeqNo,
			  vcIndex, vcType }
	DESCRIPTION	"This trap is generated when set
			vcExLoThresholdTrapID equal 117 and
			until vcExceedLowerThresholdDecrease is generated after
			vcExceedLowerThresholdIncrease is generated."
	::= 17013

    vcExceedingLowerThreshold118 TRAP-TYPE
	ENTERPRISE	network-device
	VARIABLES	{ vcValue, adminDateAndTime, adminNDTrapSeqNo,
			  vcIndex, vcType }
	DESCRIPTION	"This trap is generated when set
			vcExLoThresholdTrapID equal 118 and
			until vcExceedLowerThresholdDecrease is generated after
			vcExceedLowerThresholdIncrease is generated."
	::= 17014

    vcExceedingLowerThreshold119 TRAP-TYPE
	ENTERPRISE	network-device
	VARIABLES	{ vcValue, adminDateAndTime, adminNDTrapSeqNo,
			  vcIndex, vcType }
	DESCRIPTION	"This trap is generated when set
			vcExLoThresholdTrapID equal 119 and
			until vcExceedLowerThresholdDecrease is generated after
			vcExceedLowerThresholdIncrease is generated."
	::= 17015

    vcExceedingLowerThreshold120 TRAP-TYPE
	ENTERPRISE	network-device
	VARIABLES	{ vcValue, adminDateAndTime, adminNDTrapSeqNo,
			  vcIndex, vcType }
	DESCRIPTION	"This trap is generated when set
			vcExLoThresholdTrapID equal 120 and
			until vcExceedLowerThresholdDecrease is generated after
			vcExceedLowerThresholdIncrease is generated."
	::= 17016

    vcExceedingLowerThreshold121 TRAP-TYPE
	ENTERPRISE	network-device
	VARIABLES	{ vcValue, adminDateAndTime, adminNDTrapSeqNo,
			  vcIndex, vcType }
	DESCRIPTION	"This trap is generated when set
			vcExLoThresholdTrapID equal 121 and
			until vcExceedLowerThresholdDecrease is generated after
			vcExceedLowerThresholdIncrease is generated."
	::= 17017

    vcExceedingLowerThreshold122 TRAP-TYPE
	ENTERPRISE	network-device
	VARIABLES	{ vcValue, adminDateAndTime, adminNDTrapSeqNo,
			  vcIndex, vcType }
	DESCRIPTION	"This trap is generated when set
			vcExLoThresholdTrapID equal 122 and
			until vcExceedLowerThresholdDecrease is generated after
			vcExceedLowerThresholdIncrease is generated."
	::= 17018

    vcExceedingLowerThreshold123 TRAP-TYPE
	ENTERPRISE	network-device
	VARIABLES	{ vcValue, adminDateAndTime, adminNDTrapSeqNo,
			  vcIndex, vcType }
	DESCRIPTION	"This trap is generated when set
			vcExLoThresholdTrapID equal 123 and
			until vcExceedLowerThresholdDecrease is generated after
			vcExceedLowerThresholdIncrease is generated."
	::= 17019

    vcExceedingLowerThreshold124 TRAP-TYPE
	ENTERPRISE	network-device
	VARIABLES	{ vcValue, adminDateAndTime, adminNDTrapSeqNo,
			  vcIndex, vcType }
	DESCRIPTION	"This trap is generated when set
			vcExLoThresholdTrapID equal 124 and
			until vcExceedLowerThresholdDecrease is generated after
			vcExceedLowerThresholdIncrease is generated."
	::= 17020

    vcExceedingLowerThreshold125 TRAP-TYPE
	ENTERPRISE	network-device
	VARIABLES	{ vcValue, adminDateAndTime, adminNDTrapSeqNo,
			  vcIndex, vcType }
	DESCRIPTION	"This trap is generated when set
			vcExLoThresholdTrapID equal 125 and
			until vcExceedLowerThresholdDecrease is generated after
			vcExceedLowerThresholdIncrease is generated."
	::= 17021

    vcExceedingLowerThreshold126 TRAP-TYPE
	ENTERPRISE	network-device
	VARIABLES	{ vcValue, adminDateAndTime, adminNDTrapSeqNo,
			  vcIndex, vcType }
	DESCRIPTION	"This trap is generated when set
			vcExLoThresholdTrapID equal 126 and
			until vcExceedLowerThresholdDecrease is generated after
			vcExceedLowerThresholdIncrease is generated."
	::= 17022

    vcExceedingLowerThreshold127 TRAP-TYPE
	ENTERPRISE	network-device
	VARIABLES	{ vcValue, adminDateAndTime, adminNDTrapSeqNo,
			  vcIndex, vcType }
	DESCRIPTION	"This trap is generated when set
			vcExLoThresholdTrapID equal 127 and
			until vcExceedLowerThresholdDecrease is generated after
			vcExceedLowerThresholdIncrease is generated."
	::= 17023

    ndUserDefinedTrap1 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 1' command."
	::= 20481

    ndUserDefinedTrap2 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 2' command."
	::= 20482

    ndUserDefinedTrap3 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 3' command."
	::= 20483

    ndUserDefinedTrap4 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 4' command."
	::= 20484

    ndUserDefinedTrap5 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 5' command."
	::= 20485

    ndUserDefinedTrap6 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 6' command."
	::= 20486

    ndUserDefinedTrap7 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 7' command."
	::= 20487

    ndUserDefinedTrap8 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 8' command."
	::= 20488

    ndUserDefinedTrap9 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 9' command."
	::= 20489

    ndUserDefinedTrap10 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 10' command."
	::= 20490

    ndUserDefinedTrap11 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 11' command."
	::= 20491

    ndUserDefinedTrap12 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 12' command."
	::= 20492

    ndUserDefinedTrap13 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 13' command."
	::= 20493

    ndUserDefinedTrap14 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 14' command."
	::= 20494

    ndUserDefinedTrap15 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 15' command."
	::= 20495

    ndUserDefinedTrap16 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 16' command."
	::= 20496

    ndUserDefinedTrap17 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 17' command."
	::= 20497

    ndUserDefinedTrap18 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 18' command."
	::= 20498

    ndUserDefinedTrap19 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 19' command."
	::= 20499

    ndUserDefinedTrap20 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 20' command."
	::= 20500

    ndUserDefinedTrap21 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 21' command."
	::= 20501

    ndUserDefinedTrap22 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 22' command."
	::= 20502

    ndUserDefinedTrap23 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 23' command."
	::= 20503

    ndUserDefinedTrap24 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 24' command."
	::= 20504

    ndUserDefinedTrap25 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 25' command."
	::= 20505

    ndUserDefinedTrap26 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 26' command."
	::= 20506

    ndUserDefinedTrap27 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 27' command."
	::= 20507

    ndUserDefinedTrap28 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 28' command."
	::= 20508

    ndUserDefinedTrap29 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 29' command."
	::= 20509

    ndUserDefinedTrap30 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 30' command."
	::= 20510

    ndUserDefinedTrap31 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 31' command."
	::= 20511

    ndUserDefinedTrap32 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 32' command."
	::= 20512

    ndUserDefinedTrap33 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 33' command."
	::= 20513

    ndUserDefinedTrap34 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 34' command."
	::= 20514

    ndUserDefinedTrap35 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 35' command."
	::= 20515

    ndUserDefinedTrap36 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 36' command."
	::= 20516

    ndUserDefinedTrap37 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 37' command."
	::= 20517

    ndUserDefinedTrap38 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 38' command."
	::= 20518

    ndUserDefinedTrap39 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 39' command."
	::= 20519

    ndUserDefinedTrap40 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 40' command."
	::= 20520

    ndUserDefinedTrap41 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 41' command."
	::= 20521

    ndUserDefinedTrap42 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 42' command."
	::= 20522

    ndUserDefinedTrap43 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 43' command."
	::= 20523

    ndUserDefinedTrap44 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 44' command."
	::= 20524

    ndUserDefinedTrap45 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 45' command."
	::= 20525

    ndUserDefinedTrap46 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 46' command."
	::= 20526

    ndUserDefinedTrap47 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 47' command."
	::= 20527

    ndUserDefinedTrap48 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 48' command."
	::= 20528

    ndUserDefinedTrap49 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 49' command."
	::= 20529

    ndUserDefinedTrap50 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 50' command."
	::= 20530

    ndUserDefinedTrap51 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 51' command."
	::= 20531

    ndUserDefinedTrap52 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 52' command."
	::= 20532

    ndUserDefinedTrap53 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 53' command."
	::= 20533

    ndUserDefinedTrap54 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 54' command."
	::= 20534

    ndUserDefinedTrap55 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 55' command."
	::= 20535

    ndUserDefinedTrap56 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 56' command."
	::= 20536

    ndUserDefinedTrap57 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 57' command."
	::= 20537

    ndUserDefinedTrap58 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 58' command."
	::= 20538

    ndUserDefinedTrap59 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 59' command."
	::= 20539

    ndUserDefinedTrap60 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 60' command."
	::= 20540

    ndUserDefinedTrap61 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 61' command."
	::= 20541

    ndUserDefinedTrap62 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 62' command."
	::= 20542

    ndUserDefinedTrap63 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 63' command."
	::= 20543

    ndUserDefinedTrap64 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 64' command."
	::= 20544

    ndUserDefinedTrap65 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 65' command."
	::= 20545

    ndUserDefinedTrap66 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 66' command."
	::= 20546

    ndUserDefinedTrap67 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 67' command."
	::= 20547

    ndUserDefinedTrap68 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 68' command."
	::= 20548

    ndUserDefinedTrap69 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 69' command."
	::= 20549

    ndUserDefinedTrap70 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 70' command."
	::= 20550

    ndUserDefinedTrap71 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 71' command."
	::= 20551

    ndUserDefinedTrap72 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 72' command."
	::= 20552

    ndUserDefinedTrap73 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 73' command."
	::= 20553

    ndUserDefinedTrap74 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 74' command."
	::= 20554

    ndUserDefinedTrap75 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 75' command."
	::= 20555

    ndUserDefinedTrap76 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 76' command."
	::= 20556

    ndUserDefinedTrap77 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 77' command."
	::= 20557

    ndUserDefinedTrap78 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 78' command."
	::= 20558

    ndUserDefinedTrap79 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 79' command."
	::= 20559

    ndUserDefinedTrap80 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 80' command."
	::= 20560

    ndUserDefinedTrap81 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 81' command."
	::= 20561

    ndUserDefinedTrap82 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 82' command."
	::= 20562

    ndUserDefinedTrap83 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 83' command."
	::= 20563

    ndUserDefinedTrap84 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 84' command."
	::= 20564

    ndUserDefinedTrap85 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 85' command."
	::= 20565

    ndUserDefinedTrap86 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 86' command."
	::= 20566

    ndUserDefinedTrap87 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 87' command."
	::= 20567

    ndUserDefinedTrap88 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 88' command."
	::= 20568

    ndUserDefinedTrap89 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 89' command."
	::= 20569

    ndUserDefinedTrap90 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 90' command."
	::= 20570

    ndUserDefinedTrap91 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 91' command."
	::= 20571

    ndUserDefinedTrap92 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 92' command."
	::= 20572

    ndUserDefinedTrap93 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 93' command."
	::= 20573

    ndUserDefinedTrap94 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 94' command."
	::= 20574

    ndUserDefinedTrap95 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 95' command."
	::= 20575

    ndUserDefinedTrap96 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 96' command."
	::= 20576

    ndUserDefinedTrap97 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 97' command."
	::= 20577

    ndUserDefinedTrap98 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 98' command."
	::= 20578

    ndUserDefinedTrap99 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 99' command."
	::= 20579

    ndUserDefinedTrap100 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 100' command."
	::= 20580

    ndUserDefinedTrap101 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 101' command."
	::= 20581

    ndUserDefinedTrap102 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 102' command."
	::= 20582

    ndUserDefinedTrap103 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 103' command."
	::= 20583

    ndUserDefinedTrap104 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 104' command."
	::= 20584

    ndUserDefinedTrap105 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 105' command."
	::= 20585

    ndUserDefinedTrap106 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 106' command."
	::= 20586

    ndUserDefinedTrap107 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 107' command."
	::= 20587

    ndUserDefinedTrap108 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 108' command."
	::= 20588

    ndUserDefinedTrap109 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 109' command."
	::= 20589

    ndUserDefinedTrap110 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 110' command."
	::= 20590

    ndUserDefinedTrap111 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 111' command."
	::= 20591

    ndUserDefinedTrap112 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 112' command."
	::= 20592

    ndUserDefinedTrap113 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 113' command."
	::= 20593

    ndUserDefinedTrap114 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 114' command."
	::= 20594

    ndUserDefinedTrap115 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 115' command."
	::= 20595

    ndUserDefinedTrap116 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 116' command."
	::= 20596

    ndUserDefinedTrap117 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 117' command."
	::= 20597

    ndUserDefinedTrap118 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 118' command."
	::= 20598

    ndUserDefinedTrap119 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 119' command."
	::= 20599

    ndUserDefinedTrap120 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 120' command."
	::= 20600

    ndUserDefinedTrap121 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 121' command."
	::= 20601

    ndUserDefinedTrap122 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 122' command."
	::= 20602

    ndUserDefinedTrap123 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 123' command."
	::= 20603

    ndUserDefinedTrap124 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 124' command."
	::= 20604

    ndUserDefinedTrap125 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 125' command."
	::= 20605

    ndUserDefinedTrap126 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 126' command."
	::= 20606

    ndUserDefinedTrap127 TRAP-TYPE
	ENTERPRISE	network-device
	VARIABLES	{ ndUserDefinedTrapValue,
			  adminDateAndTime, adminNDTrapSeqNo,
			  ndUserDefinedTrapIndex,
			  ndUserDefinedTrapType }
	DESCRIPTION	"This trap is generated when use
			'send snmptrap 127' command."
	::= 20607


    doChangeValue0-1	TRAP-TYPE
	ENTERPRISE	network-device
	VARIABLES	{ doValue, adminDateAndTime, adminNDTrapSeqNo,
			  doIndex, doType, doValue1String }
	DESCRIPTION	"This trap is generated when set
			 doChangeValue0TrapID equal 1 and
			the value of doValue change from 1 to 0."
	::= 26625


    doChangeValue0-2	TRAP-TYPE
	ENTERPRISE	network-device
	VARIABLES	{ doValue, adminDateAndTime, adminNDTrapSeqNo,
			  doIndex, doType, doValue1String }
	DESCRIPTION	"This trap is generated when set
			 doChangeValue0TrapID equal 2 and
			the value of doValue change from 1 to 0."
	::= 26626


    doChangeValue0-3	TRAP-TYPE
	ENTERPRISE	network-device
	VARIABLES	{ doValue, adminDateAndTime, adminNDTrapSeqNo,
			  doIndex, doType, doValue1String }
	DESCRIPTION	"This trap is generated when set
			 doChangeValue0TrapID equal 3 and
			the value of doValue change from 1 to 0."
	::= 26627


    doChangeValue0-4	TRAP-TYPE
	ENTERPRISE	network-device
	VARIABLES	{ doValue, adminDateAndTime, adminNDTrapSeqNo,
			  doIndex, doType, doValue1String }
	DESCRIPTION	"This trap is generated when set
			 doChangeValue0TrapID equal 4 and
			the value of doValue change from 1 to 0."
	::= 26628


    doChangeValue0-5	TRAP-TYPE
	ENTERPRISE	network-device
	VARIABLES	{ doValue, adminDateAndTime, adminNDTrapSeqNo,
			  doIndex, doType, doValue1String }
	DESCRIPTION	"This trap is generated when set
			 doChangeValue0TrapID equal 5 and
			the value of doValue change from 1 to 0."
	::= 26629


    doChangeValue0-6	TRAP-TYPE
	ENTERPRISE	network-device
	VARIABLES	{ doValue, adminDateAndTime, adminNDTrapSeqNo,
			  doIndex, doType, doValue1String }
	DESCRIPTION	"This trap is generated when set
			 doChangeValue0TrapID equal 6 and
			the value of doValue change from 1 to 0."
	::= 26630


    doChangeValue0-7	TRAP-TYPE
	ENTERPRISE	network-device
	VARIABLES	{ doValue, adminDateAndTime, adminNDTrapSeqNo,
			  doIndex, doType, doValue1String }
	DESCRIPTION	"This trap is generated when set
			 doChangeValue0TrapID equal 7 and
			the value of doValue change from 1 to 0."
	::= 26631


    doChangeValue0-8	TRAP-TYPE
	ENTERPRISE	network-device
	VARIABLES	{ doValue, adminDateAndTime, adminNDTrapSeqNo,
			  doIndex, doType, doValue1String }
	DESCRIPTION	"This trap is generated when set
			 doChangeValue0TrapID equal 8 and
			the value of doValue change from 1 to 0."
	::= 26632


    doChangeValue0-9	TRAP-TYPE
	ENTERPRISE	network-device
	VARIABLES	{ doValue, adminDateAndTime, adminNDTrapSeqNo,
			  doIndex, doType, doValue1String }
	DESCRIPTION	"This trap is generated when set
			 doChangeValue0TrapID equal 9 and
			the value of doValue change from 1 to 0."
	::= 26633


    doChangeValue0-10	TRAP-TYPE
	ENTERPRISE	network-device
	VARIABLES	{ doValue, adminDateAndTime, adminNDTrapSeqNo,
			  doIndex, doType, doValue1String }
	DESCRIPTION	"This trap is generated when set
			 doChangeValue0TrapID equal 10 and
			the value of doValue change from 1 to 0."
	::= 26634


    doChangeValue0-11	TRAP-TYPE
	ENTERPRISE	network-device
	VARIABLES	{ doValue, adminDateAndTime, adminNDTrapSeqNo,
			  doIndex, doType, doValue1String }
	DESCRIPTION	"This trap is generated when set
			 doChangeValue0TrapID equal 11 and
			the value of doValue change from 1 to 0."
	::= 26635


    doChangeValue0-12	TRAP-TYPE
	ENTERPRISE	network-device
	VARIABLES	{ doValue, adminDateAndTime, adminNDTrapSeqNo,
			  doIndex, doType, doValue1String }
	DESCRIPTION	"This trap is generated when set
			 doChangeValue0TrapID equal 12 and
			the value of doValue change from 1 to 0."
	::= 26636


    doChangeValue0-13	TRAP-TYPE
	ENTERPRISE	network-device
	VARIABLES	{ doValue, adminDateAndTime, adminNDTrapSeqNo,
			  doIndex, doType, doValue1String }
	DESCRIPTION	"This trap is generated when set
			 doChangeValue0TrapID equal 13 and
			the value of doValue change from 1 to 0."
	::= 26637


    doChangeValue0-14	TRAP-TYPE
	ENTERPRISE	network-device
	VARIABLES	{ doValue, adminDateAndTime, adminNDTrapSeqNo,
			  doIndex, doType, doValue1String }
	DESCRIPTION	"This trap is generated when set
			 doChangeValue0TrapID equal 14 and
			the value of doValue change from 1 to 0."
	::= 26638


    doChangeValue0-15	TRAP-TYPE
	ENTERPRISE	network-device
	VARIABLES	{ doValue, adminDateAndTime, adminNDTrapSeqNo,
			  doIndex, doType, doValue1String }
	DESCRIPTION	"This trap is generated when set
			 doChangeValue0TrapID equal 15 and
			the value of doValue change from 1 to 0."
	::= 26639


    doChangeValue0-16	TRAP-TYPE
	ENTERPRISE	network-device
	VARIABLES	{ doValue, adminDateAndTime, adminNDTrapSeqNo,
			  doIndex, doType, doValue1String }
	DESCRIPTION	"This trap is generated when set
			 doChangeValue0TrapID equal 16 and
			the value of doValue change from 1 to 0."
	::= 26640


    doChangeValue0-17	TRAP-TYPE
	ENTERPRISE	network-device
	VARIABLES	{ doValue, adminDateAndTime, adminNDTrapSeqNo,
			  doIndex, doType, doValue1String }
	DESCRIPTION	"This trap is generated when set
			 doChangeValue0TrapID equal 17 and
			the value of doValue change from 1 to 0."
	::= 26641


    doChangeValue0-18	TRAP-TYPE
	ENTERPRISE	network-device
	VARIABLES	{ doValue, adminDateAndTime, adminNDTrapSeqNo,
			  doIndex, doType, doValue1String }
	DESCRIPTION	"This trap is generated when set
			 doChangeValue0TrapID equal 18 and
			the value of doValue change from 1 to 0."
	::= 26642


    doChangeValue0-19	TRAP-TYPE
	ENTERPRISE	network-device
	VARIABLES	{ doValue, adminDateAndTime, adminNDTrapSeqNo,
			  doIndex, doType, doValue1String }
	DESCRIPTION	"This trap is generated when set
			 doChangeValue0TrapID equal 19 and
			the value of doValue change from 1 to 0."
	::= 26643


    doChangeValue0-20	TRAP-TYPE
	ENTERPRISE	network-device
	VARIABLES	{ doValue, adminDateAndTime, adminNDTrapSeqNo,
			  doIndex, doType, doValue1String }
	DESCRIPTION	"This trap is generated when set
			 doChangeValue0TrapID equal 20 and
			the value of doValue change from 1 to 0."
	::= 26644


    doChangeValue0-21	TRAP-TYPE
	ENTERPRISE	network-device
	VARIABLES	{ doValue, adminDateAndTime, adminNDTrapSeqNo,
			  doIndex, doType, doValue1String }
	DESCRIPTION	"This trap is generated when set
			 doChangeValue0TrapID equal 21 and
			the value of doValue change from 1 to 0."
	::= 26645


    doChangeValue0-22	TRAP-TYPE
	ENTERPRISE	network-device
	VARIABLES	{ doValue, adminDateAndTime, adminNDTrapSeqNo,
			  doIndex, doType, doValue1String }
	DESCRIPTION	"This trap is generated when set
			 doChangeValue0TrapID equal 22 and
			the value of doValue change from 1 to 0."
	::= 26646


    doChangeValue0-23	TRAP-TYPE
	ENTERPRISE	network-device
	VARIABLES	{ doValue, adminDateAndTime, adminNDTrapSeqNo,
			  doIndex, doType, doValue1String }
	DESCRIPTION	"This trap is generated when set
			 doChangeValue0TrapID equal 23 and
			the value of doValue change from 1 to 0."
	::= 26647


    doChangeValue0-24	TRAP-TYPE
	ENTERPRISE	network-device
	VARIABLES	{ doValue, adminDateAndTime, adminNDTrapSeqNo,
			  doIndex, doType, doValue1String }
	DESCRIPTION	"This trap is generated when set
			 doChangeValue0TrapID equal 24 and
			the value of doValue change from 1 to 0."
	::= 26648


    doChangeValue0-25	TRAP-TYPE
	ENTERPRISE	network-device
	VARIABLES	{ doValue, adminDateAndTime, adminNDTrapSeqNo,
			  doIndex, doType, doValue1String }
	DESCRIPTION	"This trap is generated when set
			 doChangeValue0TrapID equal 25 and
			the value of doValue change from 1 to 0."
	::= 26649


    doChangeValue0-26	TRAP-TYPE
	ENTERPRISE	network-device
	VARIABLES	{ doValue, adminDateAndTime, adminNDTrapSeqNo,
			  doIndex, doType, doValue1String }
	DESCRIPTION	"This trap is generated when set
			 doChangeValue0TrapID equal 26 and
			the value of doValue change from 1 to 0."
	::= 26650


    doChangeValue0-27	TRAP-TYPE
	ENTERPRISE	network-device
	VARIABLES	{ doValue, adminDateAndTime, adminNDTrapSeqNo,
			  doIndex, doType, doValue1String }
	DESCRIPTION	"This trap is generated when set
			 doChangeValue0TrapID equal 27 and
			the value of doValue change from 1 to 0."
	::= 26651


    doChangeValue0-28	TRAP-TYPE
	ENTERPRISE	network-device
	VARIABLES	{ doValue, adminDateAndTime, adminNDTrapSeqNo,
			  doIndex, doType, doValue1String }
	DESCRIPTION	"This trap is generated when set
			 doChangeValue0TrapID equal 28 and
			the value of doValue change from 1 to 0."
	::= 26652


    doChangeValue0-29	TRAP-TYPE
	ENTERPRISE	network-device
	VARIABLES	{ doValue, adminDateAndTime, adminNDTrapSeqNo,
			  doIndex, doType, doValue1String }
	DESCRIPTION	"This trap is generated when set
			 doChangeValue0TrapID equal 29 and
			the value of doValue change from 1 to 0."
	::= 26653


    doChangeValue0-30	TRAP-TYPE
	ENTERPRISE	network-device
	VARIABLES	{ doValue, adminDateAndTime, adminNDTrapSeqNo,
			  doIndex, doType, doValue1String }
	DESCRIPTION	"This trap is generated when set
			 doChangeValue0TrapID equal 30 and
			the value of doValue change from 1 to 0."
	::= 26654


    doChangeValue0-31	TRAP-TYPE
	ENTERPRISE	network-device
	VARIABLES	{ doValue, adminDateAndTime, adminNDTrapSeqNo,
			  doIndex, doType, doValue1String }
	DESCRIPTION	"This trap is generated when set
			 doChangeValue0TrapID equal 31 and
			the value of doValue change from 1 to 0."
	::= 26655


    doChangeValue0-32	TRAP-TYPE
	ENTERPRISE	network-device
	VARIABLES	{ doValue, adminDateAndTime, adminNDTrapSeqNo,
			  doIndex, doType, doValue1String }
	DESCRIPTION	"This trap is generated when set
			 doChangeValue0TrapID equal 32 and
			the value of doValue change from 1 to 0."
	::= 26656


    doChangeValue0-33	TRAP-TYPE
	ENTERPRISE	network-device
	VARIABLES	{ doValue, adminDateAndTime, adminNDTrapSeqNo,
			  doIndex, doType, doValue1String }
	DESCRIPTION	"This trap is generated when set
			 doChangeValue0TrapID equal 33 and
			the value of doValue change from 1 to 0."
	::= 26657


    doChangeValue0-34	TRAP-TYPE
	ENTERPRISE	network-device
	VARIABLES	{ doValue, adminDateAndTime, adminNDTrapSeqNo,
			  doIndex, doType, doValue1String }
	DESCRIPTION	"This trap is generated when set
			 doChangeValue0TrapID equal 34 and
			the value of doValue change from 1 to 0."
	::= 26658


    doChangeValue0-35	TRAP-TYPE
	ENTERPRISE	network-device
	VARIABLES	{ doValue, adminDateAndTime, adminNDTrapSeqNo,
			  doIndex, doType, doValue1String }
	DESCRIPTION	"This trap is generated when set
			 doChangeValue0TrapID equal 35 and
			the value of doValue change from 1 to 0."
	::= 26659


    doChangeValue0-36	TRAP-TYPE
	ENTERPRISE	network-device
	VARIABLES	{ doValue, adminDateAndTime, adminNDTrapSeqNo,
			  doIndex, doType, doValue1String }
	DESCRIPTION	"This trap is generated when set
			 doChangeValue0TrapID equal 36 and
			the value of doValue change from 1 to 0."
	::= 26660


    doChangeValue0-37	TRAP-TYPE
	ENTERPRISE	network-device
	VARIABLES	{ doValue, adminDateAndTime, adminNDTrapSeqNo,
			  doIndex, doType, doValue1String }
	DESCRIPTION	"This trap is generated when set
			 doChangeValue0TrapID equal 37 and
			the value of doValue change from 1 to 0."
	::= 26661


    doChangeValue0-38	TRAP-TYPE
	ENTERPRISE	network-device
	VARIABLES	{ doValue, adminDateAndTime, adminNDTrapSeqNo,
			  doIndex, doType, doValue1String }
	DESCRIPTION	"This trap is generated when set
			 doChangeValue0TrapID equal 38 and
			the value of doValue change from 1 to 0."
	::= 26662


    doChangeValue0-39	TRAP-TYPE
	ENTERPRISE	network-device
	VARIABLES	{ doValue, adminDateAndTime, adminNDTrapSeqNo,
			  doIndex, doType, doValue1String }
	DESCRIPTION	"This trap is generated when set
			 doChangeValue0TrapID equal 39 and
			the value of doValue change from 1 to 0."
	::= 26663


    doChangeValue0-40	TRAP-TYPE
	ENTERPRISE	network-device
	VARIABLES	{ doValue, adminDateAndTime, adminNDTrapSeqNo,
			  doIndex, doType, doValue1String }
	DESCRIPTION	"This trap is generated when set
			 doChangeValue0TrapID equal 40 and
			the value of doValue change from 1 to 0."
	::= 26664


    doChangeValue0-41	TRAP-TYPE
	ENTERPRISE	network-device
	VARIABLES	{ doValue, adminDateAndTime, adminNDTrapSeqNo,
			  doIndex, doType, doValue1String }
	DESCRIPTION	"This trap is generated when set
			 doChangeValue0TrapID equal 41 and
			the value of doValue change from 1 to 0."
	::= 26665


    doChangeValue0-42	TRAP-TYPE
	ENTERPRISE	network-device
	VARIABLES	{ doValue, adminDateAndTime, adminNDTrapSeqNo,
			  doIndex, doType, doValue1String }
	DESCRIPTION	"This trap is generated when set
			 doChangeValue0TrapID equal 42 and
			the value of doValue change from 1 to 0."
	::= 26666


    doChangeValue0-43	TRAP-TYPE
	ENTERPRISE	network-device
	VARIABLES	{ doValue, adminDateAndTime, adminNDTrapSeqNo,
			  doIndex, doType, doValue1String }
	DESCRIPTION	"This trap is generated when set
			 doChangeValue0TrapID equal 43 and
			the value of doValue change from 1 to 0."
	::= 26667


    doChangeValue0-44	TRAP-TYPE
	ENTERPRISE	network-device
	VARIABLES	{ doValue, adminDateAndTime, adminNDTrapSeqNo,
			  doIndex, doType, doValue1String }
	DESCRIPTION	"This trap is generated when set
			 doChangeValue0TrapID equal 44 and
			the value of doValue change from 1 to 0."
	::= 26668


    doChangeValue0-45	TRAP-TYPE
	ENTERPRISE	network-device
	VARIABLES	{ doValue, adminDateAndTime, adminNDTrapSeqNo,
			  doIndex, doType, doValue1String }
	DESCRIPTION	"This trap is generated when set
			 doChangeValue0TrapID equal 45 and
			the value of doValue change from 1 to 0."
	::= 26669


    doChangeValue0-46	TRAP-TYPE
	ENTERPRISE	network-device
	VARIABLES	{ doValue, adminDateAndTime, adminNDTrapSeqNo,
			  doIndex, doType, doValue1String }
	DESCRIPTION	"This trap is generated when set
			 doChangeValue0TrapID equal 46 and
			the value of doValue change from 1 to 0."
	::= 26670


    doChangeValue0-47	TRAP-TYPE
	ENTERPRISE	network-device
	VARIABLES	{ doValue, adminDateAndTime, adminNDTrapSeqNo,
			  doIndex, doType, doValue1String }
	DESCRIPTION	"This trap is generated when set
			 doChangeValue0TrapID equal 47 and
			the value of doValue change from 1 to 0."
	::= 26671


    doChangeValue0-48	TRAP-TYPE
	ENTERPRISE	network-device
	VARIABLES	{ doValue, adminDateAndTime, adminNDTrapSeqNo,
			  doIndex, doType, doValue1String }
	DESCRIPTION	"This trap is generated when set
			 doChangeValue0TrapID equal 48 and
			the value of doValue change from 1 to 0."
	::= 26672


    doChangeValue0-49	TRAP-TYPE
	ENTERPRISE	network-device
	VARIABLES	{ doValue, adminDateAndTime, adminNDTrapSeqNo,
			  doIndex, doType, doValue1String }
	DESCRIPTION	"This trap is generated when set
			 doChangeValue0TrapID equal 49 and
			the value of doValue change from 1 to 0."
	::= 26673


    doChangeValue0-50	TRAP-TYPE
	ENTERPRISE	network-device
	VARIABLES	{ doValue, adminDateAndTime, adminNDTrapSeqNo,
			  doIndex, doType, doValue1String }
	DESCRIPTION	"This trap is generated when set
			 doChangeValue0TrapID equal 50 and
			the value of doValue change from 1 to 0."
	::= 26674


    doChangeValue0-51	TRAP-TYPE
	ENTERPRISE	network-device
	VARIABLES	{ doValue, adminDateAndTime, adminNDTrapSeqNo,
			  doIndex, doType, doValue1String }
	DESCRIPTION	"This trap is generated when set
			 doChangeValue0TrapID equal 51 and
			the value of doValue change from 1 to 0."
	::= 26675


    doChangeValue0-52	TRAP-TYPE
	ENTERPRISE	network-device
	VARIABLES	{ doValue, adminDateAndTime, adminNDTrapSeqNo,
			  doIndex, doType, doValue1String }
	DESCRIPTION	"This trap is generated when set
			 doChangeValue0TrapID equal 52 and
			the value of doValue change from 1 to 0."
	::= 26676


    doChangeValue0-53	TRAP-TYPE
	ENTERPRISE	network-device
	VARIABLES	{ doValue, adminDateAndTime, adminNDTrapSeqNo,
			  doIndex, doType, doValue1String }
	DESCRIPTION	"This trap is generated when set
			 doChangeValue0TrapID equal 53 and
			the value of doValue change from 1 to 0."
	::= 26677


    doChangeValue0-54	TRAP-TYPE
	ENTERPRISE	network-device
	VARIABLES	{ doValue, adminDateAndTime, adminNDTrapSeqNo,
			  doIndex, doType, doValue1String }
	DESCRIPTION	"This trap is generated when set
			 doChangeValue0TrapID equal 54 and
			the value of doValue change from 1 to 0."
	::= 26678


    doChangeValue0-55	TRAP-TYPE
	ENTERPRISE	network-device
	VARIABLES	{ doValue, adminDateAndTime, adminNDTrapSeqNo,
			  doIndex, doType, doValue1String }
	DESCRIPTION	"This trap is generated when set
			 doChangeValue0TrapID equal 55 and
			the value of doValue change from 1 to 0."
	::= 26679


    doChangeValue0-56	TRAP-TYPE
	ENTERPRISE	network-device
	VARIABLES	{ doValue, adminDateAndTime, adminNDTrapSeqNo,
			  doIndex, doType, doValue1String }
	DESCRIPTION	"This trap is generated when set
			 doChangeValue0TrapID equal 56 and
			the value of doValue change from 1 to 0."
	::= 26680


    doChangeValue0-57	TRAP-TYPE
	ENTERPRISE	network-device
	VARIABLES	{ doValue, adminDateAndTime, adminNDTrapSeqNo,
			  doIndex, doType, doValue1String }
	DESCRIPTION	"This trap is generated when set
			 doChangeValue0TrapID equal 57 and
			the value of doValue change from 1 to 0."
	::= 26681


    doChangeValue0-58	TRAP-TYPE
	ENTERPRISE	network-device
	VARIABLES	{ doValue, adminDateAndTime, adminNDTrapSeqNo,
			  doIndex, doType, doValue1String }
	DESCRIPTION	"This trap is generated when set
			 doChangeValue0TrapID equal 58 and
			the value of doValue change from 1 to 0."
	::= 26682


    doChangeValue0-59	TRAP-TYPE
	ENTERPRISE	network-device
	VARIABLES	{ doValue, adminDateAndTime, adminNDTrapSeqNo,
			  doIndex, doType, doValue1String }
	DESCRIPTION	"This trap is generated when set
			 doChangeValue0TrapID equal 59 and
			the value of doValue change from 1 to 0."
	::= 26683


    doChangeValue0-60	TRAP-TYPE
	ENTERPRISE	network-device
	VARIABLES	{ doValue, adminDateAndTime, adminNDTrapSeqNo,
			  doIndex, doType, doValue1String }
	DESCRIPTION	"This trap is generated when set
			 doChangeValue0TrapID equal 60 and
			the value of doValue change from 1 to 0."
	::= 26684


    doChangeValue0-61	TRAP-TYPE
	ENTERPRISE	network-device
	VARIABLES	{ doValue, adminDateAndTime, adminNDTrapSeqNo,
			  doIndex, doType, doValue1String }
	DESCRIPTION	"This trap is generated when set
			 doChangeValue0TrapID equal 61 and
			the value of doValue change from 1 to 0."
	::= 26685


    doChangeValue0-62	TRAP-TYPE
	ENTERPRISE	network-device
	VARIABLES	{ doValue, adminDateAndTime, adminNDTrapSeqNo,
			  doIndex, doType, doValue1String }
	DESCRIPTION	"This trap is generated when set
			 doChangeValue0TrapID equal 62 and
			the value of doValue change from 1 to 0."
	::= 26686


    doChangeValue0-63	TRAP-TYPE
	ENTERPRISE	network-device
	VARIABLES	{ doValue, adminDateAndTime, adminNDTrapSeqNo,
			  doIndex, doType, doValue1String }
	DESCRIPTION	"This trap is generated when set
			 doChangeValue0TrapID equal 63 and
			the value of doValue change from 1 to 0."
	::= 26687


    doChangeValue0-64	TRAP-TYPE
	ENTERPRISE	network-device
	VARIABLES	{ doValue, adminDateAndTime, adminNDTrapSeqNo,
			  doIndex, doType, doValue1String }
	DESCRIPTION	"This trap is generated when set
			 doChangeValue0TrapID equal 64 and
			the value of doValue change from 1 to 0."
	::= 26688


    doChangeValue0-65	TRAP-TYPE
	ENTERPRISE	network-device
	VARIABLES	{ doValue, adminDateAndTime, adminNDTrapSeqNo,
			  doIndex, doType, doValue1String }
	DESCRIPTION	"This trap is generated when set
			 doChangeValue0TrapID equal 65 and
			the value of doValue change from 1 to 0."
	::= 26689


    doChangeValue0-66	TRAP-TYPE
	ENTERPRISE	network-device
	VARIABLES	{ doValue, adminDateAndTime, adminNDTrapSeqNo,
			  doIndex, doType, doValue1String }
	DESCRIPTION	"This trap is generated when set
			 doChangeValue0TrapID equal 66 and
			the value of doValue change from 1 to 0."
	::= 26690


    doChangeValue0-67	TRAP-TYPE
	ENTERPRISE	network-device
	VARIABLES	{ doValue, adminDateAndTime, adminNDTrapSeqNo,
			  doIndex, doType, doValue1String }
	DESCRIPTION	"This trap is generated when set
			 doChangeValue0TrapID equal 67 and
			the value of doValue change from 1 to 0."
	::= 26691


    doChangeValue0-68	TRAP-TYPE
	ENTERPRISE	network-device
	VARIABLES	{ doValue, adminDateAndTime, adminNDTrapSeqNo,
			  doIndex, doType, doValue1String }
	DESCRIPTION	"This trap is generated when set
			 doChangeValue0TrapID equal 68 and
			the value of doValue change from 1 to 0."
	::= 26692


    doChangeValue0-69	TRAP-TYPE
	ENTERPRISE	network-device
	VARIABLES	{ doValue, adminDateAndTime, adminNDTrapSeqNo,
			  doIndex, doType, doValue1String }
	DESCRIPTION	"This trap is generated when set
			 doChangeValue0TrapID equal 69 and
			the value of doValue change from 1 to 0."
	::= 26693


    doChangeValue0-70	TRAP-TYPE
	ENTERPRISE	network-device
	VARIABLES	{ doValue, adminDateAndTime, adminNDTrapSeqNo,
			  doIndex, doType, doValue1String }
	DESCRIPTION	"This trap is generated when set
			 doChangeValue0TrapID equal 70 and
			the value of doValue change from 1 to 0."
	::= 26694


    doChangeValue0-71	TRAP-TYPE
	ENTERPRISE	network-device
	VARIABLES	{ doValue, adminDateAndTime, adminNDTrapSeqNo,
			  doIndex, doType, doValue1String }
	DESCRIPTION	"This trap is generated when set
			 doChangeValue0TrapID equal 71 and
			the value of doValue change from 1 to 0."
	::= 26695


    doChangeValue0-72	TRAP-TYPE
	ENTERPRISE	network-device
	VARIABLES	{ doValue, adminDateAndTime, adminNDTrapSeqNo,
			  doIndex, doType, doValue1String }
	DESCRIPTION	"This trap is generated when set
			 doChangeValue0TrapID equal 72 and
			the value of doValue change from 1 to 0."
	::= 26696


    doChangeValue0-73	TRAP-TYPE
	ENTERPRISE	network-device
	VARIABLES	{ doValue, adminDateAndTime, adminNDTrapSeqNo,
			  doIndex, doType, doValue1String }
	DESCRIPTION	"This trap is generated when set
			 doChangeValue0TrapID equal 73 and
			the value of doValue change from 1 to 0."
	::= 26697


    doChangeValue0-74	TRAP-TYPE
	ENTERPRISE	network-device
	VARIABLES	{ doValue, adminDateAndTime, adminNDTrapSeqNo,
			  doIndex, doType, doValue1String }
	DESCRIPTION	"This trap is generated when set
			 doChangeValue0TrapID equal 74 and
			the value of doValue change from 1 to 0."
	::= 26698


    doChangeValue0-75	TRAP-TYPE
	ENTERPRISE	network-device
	VARIABLES	{ doValue, adminDateAndTime, adminNDTrapSeqNo,
			  doIndex, doType, doValue1String }
	DESCRIPTION	"This trap is generated when set
			 doChangeValue0TrapID equal 75 and
			the value of doValue change from 1 to 0."
	::= 26699


    doChangeValue0-76	TRAP-TYPE
	ENTERPRISE	network-device
	VARIABLES	{ doValue, adminDateAndTime, adminNDTrapSeqNo,
			  doIndex, doType, doValue1String }
	DESCRIPTION	"This trap is generated when set
			 doChangeValue0TrapID equal 76 and
			the value of doValue change from 1 to 0."
	::= 26700


    doChangeValue0-77	TRAP-TYPE
	ENTERPRISE	network-device
	VARIABLES	{ doValue, adminDateAndTime, adminNDTrapSeqNo,
			  doIndex, doType, doValue1String }
	DESCRIPTION	"This trap is generated when set
			 doChangeValue0TrapID equal 77 and
			the value of doValue change from 1 to 0."
	::= 26701


    doChangeValue0-78	TRAP-TYPE
	ENTERPRISE	network-device
	VARIABLES	{ doValue, adminDateAndTime, adminNDTrapSeqNo,
			  doIndex, doType, doValue1String }
	DESCRIPTION	"This trap is generated when set
			 doChangeValue0TrapID equal 78 and
			the value of doValue change from 1 to 0."
	::= 26702


    doChangeValue0-79	TRAP-TYPE
	ENTERPRISE	network-device
	VARIABLES	{ doValue, adminDateAndTime, adminNDTrapSeqNo,
			  doIndex, doType, doValue1String }
	DESCRIPTION	"This trap is generated when set
			 doChangeValue0TrapID equal 79 and
			the value of doValue change from 1 to 0."
	::= 26703


    doChangeValue0-80	TRAP-TYPE
	ENTERPRISE	network-device
	VARIABLES	{ doValue, adminDateAndTime, adminNDTrapSeqNo,
			  doIndex, doType, doValue1String }
	DESCRIPTION	"This trap is generated when set
			 doChangeValue0TrapID equal 80 and
			the value of doValue change from 1 to 0."
	::= 26704


    doChangeValue0-81	TRAP-TYPE
	ENTERPRISE	network-device
	VARIABLES	{ doValue, adminDateAndTime, adminNDTrapSeqNo,
			  doIndex, doType, doValue1String }
	DESCRIPTION	"This trap is generated when set
			 doChangeValue0TrapID equal 81 and
			the value of doValue change from 1 to 0."
	::= 26705


    doChangeValue0-82	TRAP-TYPE
	ENTERPRISE	network-device
	VARIABLES	{ doValue, adminDateAndTime, adminNDTrapSeqNo,
			  doIndex, doType, doValue1String }
	DESCRIPTION	"This trap is generated when set
			 doChangeValue0TrapID equal 82 and
			the value of doValue change from 1 to 0."
	::= 26706


    doChangeValue0-83	TRAP-TYPE
	ENTERPRISE	network-device
	VARIABLES	{ doValue, adminDateAndTime, adminNDTrapSeqNo,
			  doIndex, doType, doValue1String }
	DESCRIPTION	"This trap is generated when set
			 doChangeValue0TrapID equal 83 and
			the value of doValue change from 1 to 0."
	::= 26707


    doChangeValue0-84	TRAP-TYPE
	ENTERPRISE	network-device
	VARIABLES	{ doValue, adminDateAndTime, adminNDTrapSeqNo,
			  doIndex, doType, doValue1String }
	DESCRIPTION	"This trap is generated when set
			 doChangeValue0TrapID equal 84 and
			the value of doValue change from 1 to 0."
	::= 26708


    doChangeValue0-85	TRAP-TYPE
	ENTERPRISE	network-device
	VARIABLES	{ doValue, adminDateAndTime, adminNDTrapSeqNo,
			  doIndex, doType, doValue1String }
	DESCRIPTION	"This trap is generated when set
			 doChangeValue0TrapID equal 85 and
			the value of doValue change from 1 to 0."
	::= 26709


    doChangeValue0-86	TRAP-TYPE
	ENTERPRISE	network-device
	VARIABLES	{ doValue, adminDateAndTime, adminNDTrapSeqNo,
			  doIndex, doType, doValue1String }
	DESCRIPTION	"This trap is generated when set
			 doChangeValue0TrapID equal 86 and
			the value of doValue change from 1 to 0."
	::= 26710


    doChangeValue0-87	TRAP-TYPE
	ENTERPRISE	network-device
	VARIABLES	{ doValue, adminDateAndTime, adminNDTrapSeqNo,
			  doIndex, doType, doValue1String }
	DESCRIPTION	"This trap is generated when set
			 doChangeValue0TrapID equal 87 and
			the value of doValue change from 1 to 0."
	::= 26711


    doChangeValue0-88	TRAP-TYPE
	ENTERPRISE	network-device
	VARIABLES	{ doValue, adminDateAndTime, adminNDTrapSeqNo,
			  doIndex, doType, doValue1String }
	DESCRIPTION	"This trap is generated when set
			 doChangeValue0TrapID equal 88 and
			the value of doValue change from 1 to 0."
	::= 26712


    doChangeValue0-89	TRAP-TYPE
	ENTERPRISE	network-device
	VARIABLES	{ doValue, adminDateAndTime, adminNDTrapSeqNo,
			  doIndex, doType, doValue1String }
	DESCRIPTION	"This trap is generated when set
			 doChangeValue0TrapID equal 89 and
			the value of doValue change from 1 to 0."
	::= 26713


    doChangeValue0-90	TRAP-TYPE
	ENTERPRISE	network-device
	VARIABLES	{ doValue, adminDateAndTime, adminNDTrapSeqNo,
			  doIndex, doType, doValue1String }
	DESCRIPTION	"This trap is generated when set
			 doChangeValue0TrapID equal 90 and
			the value of doValue change from 1 to 0."
	::= 26714


    doChangeValue0-91	TRAP-TYPE
	ENTERPRISE	network-device
	VARIABLES	{ doValue, adminDateAndTime, adminNDTrapSeqNo,
			  doIndex, doType, doValue1String }
	DESCRIPTION	"This trap is generated when set
			 doChangeValue0TrapID equal 91 and
			the value of doValue change from 1 to 0."
	::= 26715


    doChangeValue0-92	TRAP-TYPE
	ENTERPRISE	network-device
	VARIABLES	{ doValue, adminDateAndTime, adminNDTrapSeqNo,
			  doIndex, doType, doValue1String }
	DESCRIPTION	"This trap is generated when set
			 doChangeValue0TrapID equal 92 and
			the value of doValue change from 1 to 0."
	::= 26716


    doChangeValue0-93	TRAP-TYPE
	ENTERPRISE	network-device
	VARIABLES	{ doValue, adminDateAndTime, adminNDTrapSeqNo,
			  doIndex, doType, doValue1String }
	DESCRIPTION	"This trap is generated when set
			 doChangeValue0TrapID equal 93 and
			the value of doValue change from 1 to 0."
	::= 26717


    doChangeValue0-94	TRAP-TYPE
	ENTERPRISE	network-device
	VARIABLES	{ doValue, adminDateAndTime, adminNDTrapSeqNo,
			  doIndex, doType, doValue1String }
	DESCRIPTION	"This trap is generated when set
			 doChangeValue0TrapID equal 94 and
			the value of doValue change from 1 to 0."
	::= 26718


    doChangeValue0-95	TRAP-TYPE
	ENTERPRISE	network-device
	VARIABLES	{ doValue, adminDateAndTime, adminNDTrapSeqNo,
			  doIndex, doType, doValue1String }
	DESCRIPTION	"This trap is generated when set
			 doChangeValue0TrapID equal 95 and
			the value of doValue change from 1 to 0."
	::= 26719


    doChangeValue0-96	TRAP-TYPE
	ENTERPRISE	network-device
	VARIABLES	{ doValue, adminDateAndTime, adminNDTrapSeqNo,
			  doIndex, doType, doValue1String }
	DESCRIPTION	"This trap is generated when set
			 doChangeValue0TrapID equal 96 and
			the value of doValue change from 1 to 0."
	::= 26720


    doChangeValue0-97	TRAP-TYPE
	ENTERPRISE	network-device
	VARIABLES	{ doValue, adminDateAndTime, adminNDTrapSeqNo,
			  doIndex, doType, doValue1String }
	DESCRIPTION	"This trap is generated when set
			 doChangeValue0TrapID equal 97 and
			the value of doValue change from 1 to 0."
	::= 26721


    doChangeValue0-98	TRAP-TYPE
	ENTERPRISE	network-device
	VARIABLES	{ doValue, adminDateAndTime, adminNDTrapSeqNo,
			  doIndex, doType, doValue1String }
	DESCRIPTION	"This trap is generated when set
			 doChangeValue0TrapID equal 98 and
			the value of doValue change from 1 to 0."
	::= 26722


    doChangeValue0-99	TRAP-TYPE
	ENTERPRISE	network-device
	VARIABLES	{ doValue, adminDateAndTime, adminNDTrapSeqNo,
			  doIndex, doType, doValue1String }
	DESCRIPTION	"This trap is generated when set
			 doChangeValue0TrapID equal 99 and
			the value of doValue change from 1 to 0."
	::= 26723


    doChangeValue0-100	TRAP-TYPE
	ENTERPRISE	network-device
	VARIABLES	{ doValue, adminDateAndTime, adminNDTrapSeqNo,
			  doIndex, doType, doValue1String }
	DESCRIPTION	"This trap is generated when set
			 doChangeValue0TrapID equal 100 and
			the value of doValue change from 1 to 0."
	::= 26724


    doChangeValue0-101	TRAP-TYPE
	ENTERPRISE	network-device
	VARIABLES	{ doValue, adminDateAndTime, adminNDTrapSeqNo,
			  doIndex, doType, doValue1String }
	DESCRIPTION	"This trap is generated when set
			 doChangeValue0TrapID equal 101 and
			the value of doValue change from 1 to 0."
	::= 26725


    doChangeValue0-102	TRAP-TYPE
	ENTERPRISE	network-device
	VARIABLES	{ doValue, adminDateAndTime, adminNDTrapSeqNo,
			  doIndex, doType, doValue1String }
	DESCRIPTION	"This trap is generated when set
			 doChangeValue0TrapID equal 102 and
			the value of doValue change from 1 to 0."
	::= 26726


    doChangeValue0-103	TRAP-TYPE
	ENTERPRISE	network-device
	VARIABLES	{ doValue, adminDateAndTime, adminNDTrapSeqNo,
			  doIndex, doType, doValue1String }
	DESCRIPTION	"This trap is generated when set
			 doChangeValue0TrapID equal 103 and
			the value of doValue change from 1 to 0."
	::= 26727


    doChangeValue0-104	TRAP-TYPE
	ENTERPRISE	network-device
	VARIABLES	{ doValue, adminDateAndTime, adminNDTrapSeqNo,
			  doIndex, doType, doValue1String }
	DESCRIPTION	"This trap is generated when set
			 doChangeValue0TrapID equal 104 and
			the value of doValue change from 1 to 0."
	::= 26728


    doChangeValue0-105	TRAP-TYPE
	ENTERPRISE	network-device
	VARIABLES	{ doValue, adminDateAndTime, adminNDTrapSeqNo,
			  doIndex, doType, doValue1String }
	DESCRIPTION	"This trap is generated when set
			 doChangeValue0TrapID equal 105 and
			the value of doValue change from 1 to 0."
	::= 26729


    doChangeValue0-106	TRAP-TYPE
	ENTERPRISE	network-device
	VARIABLES	{ doValue, adminDateAndTime, adminNDTrapSeqNo,
			  doIndex, doType, doValue1String }
	DESCRIPTION	"This trap is generated when set
			 doChangeValue0TrapID equal 106 and
			the value of doValue change from 1 to 0."
	::= 26730


    doChangeValue0-107	TRAP-TYPE
	ENTERPRISE	network-device
	VARIABLES	{ doValue, adminDateAndTime, adminNDTrapSeqNo,
			  doIndex, doType, doValue1String }
	DESCRIPTION	"This trap is generated when set
			 doChangeValue0TrapID equal 107 and
			the value of doValue change from 1 to 0."
	::= 26731


    doChangeValue0-108	TRAP-TYPE
	ENTERPRISE	network-device
	VARIABLES	{ doValue, adminDateAndTime, adminNDTrapSeqNo,
			  doIndex, doType, doValue1String }
	DESCRIPTION	"This trap is generated when set
			 doChangeValue0TrapID equal 108 and
			the value of doValue change from 1 to 0."
	::= 26732


    doChangeValue0-109	TRAP-TYPE
	ENTERPRISE	network-device
	VARIABLES	{ doValue, adminDateAndTime, adminNDTrapSeqNo,
			  doIndex, doType, doValue1String }
	DESCRIPTION	"This trap is generated when set
			 doChangeValue0TrapID equal 109 and
			the value of doValue change from 1 to 0."
	::= 26733


    doChangeValue0-110	TRAP-TYPE
	ENTERPRISE	network-device
	VARIABLES	{ doValue, adminDateAndTime, adminNDTrapSeqNo,
			  doIndex, doType, doValue1String }
	DESCRIPTION	"This trap is generated when set
			 doChangeValue0TrapID equal 110 and
			the value of doValue change from 1 to 0."
	::= 26734


    doChangeValue0-111	TRAP-TYPE
	ENTERPRISE	network-device
	VARIABLES	{ doValue, adminDateAndTime, adminNDTrapSeqNo,
			  doIndex, doType, doValue1String }
	DESCRIPTION	"This trap is generated when set
			 doChangeValue0TrapID equal 111 and
			the value of doValue change from 1 to 0."
	::= 26735


    doChangeValue0-112	TRAP-TYPE
	ENTERPRISE	network-device
	VARIABLES	{ doValue, adminDateAndTime, adminNDTrapSeqNo,
			  doIndex, doType, doValue1String }
	DESCRIPTION	"This trap is generated when set
			 doChangeValue0TrapID equal 112 and
			the value of doValue change from 1 to 0."
	::= 26736


    doChangeValue0-113	TRAP-TYPE
	ENTERPRISE	network-device
	VARIABLES	{ doValue, adminDateAndTime, adminNDTrapSeqNo,
			  doIndex, doType, doValue1String }
	DESCRIPTION	"This trap is generated when set
			 doChangeValue0TrapID equal 113 and
			the value of doValue change from 1 to 0."
	::= 26737


    doChangeValue0-114	TRAP-TYPE
	ENTERPRISE	network-device
	VARIABLES	{ doValue, adminDateAndTime, adminNDTrapSeqNo,
			  doIndex, doType, doValue1String }
	DESCRIPTION	"This trap is generated when set
			 doChangeValue0TrapID equal 114 and
			the value of doValue change from 1 to 0."
	::= 26738


    doChangeValue0-115	TRAP-TYPE
	ENTERPRISE	network-device
	VARIABLES	{ doValue, adminDateAndTime, adminNDTrapSeqNo,
			  doIndex, doType, doValue1String }
	DESCRIPTION	"This trap is generated when set
			 doChangeValue0TrapID equal 115 and
			the value of doValue change from 1 to 0."
	::= 26739


    doChangeValue0-116	TRAP-TYPE
	ENTERPRISE	network-device
	VARIABLES	{ doValue, adminDateAndTime, adminNDTrapSeqNo,
			  doIndex, doType, doValue1String }
	DESCRIPTION	"This trap is generated when set
			 doChangeValue0TrapID equal 116 and
			the value of doValue change from 1 to 0."
	::= 26740


    doChangeValue0-117	TRAP-TYPE
	ENTERPRISE	network-device
	VARIABLES	{ doValue, adminDateAndTime, adminNDTrapSeqNo,
			  doIndex, doType, doValue1String }
	DESCRIPTION	"This trap is generated when set
			 doChangeValue0TrapID equal 117 and
			the value of doValue change from 1 to 0."
	::= 26741


    doChangeValue0-118	TRAP-TYPE
	ENTERPRISE	network-device
	VARIABLES	{ doValue, adminDateAndTime, adminNDTrapSeqNo,
			  doIndex, doType, doValue1String }
	DESCRIPTION	"This trap is generated when set
			 doChangeValue0TrapID equal 118 and
			the value of doValue change from 1 to 0."
	::= 26742


    doChangeValue0-119	TRAP-TYPE
	ENTERPRISE	network-device
	VARIABLES	{ doValue, adminDateAndTime, adminNDTrapSeqNo,
			  doIndex, doType, doValue1String }
	DESCRIPTION	"This trap is generated when set
			 doChangeValue0TrapID equal 119 and
			the value of doValue change from 1 to 0."
	::= 26743


    doChangeValue0-120	TRAP-TYPE
	ENTERPRISE	network-device
	VARIABLES	{ doValue, adminDateAndTime, adminNDTrapSeqNo,
			  doIndex, doType, doValue1String }
	DESCRIPTION	"This trap is generated when set
			 doChangeValue0TrapID equal 120 and
			the value of doValue change from 1 to 0."
	::= 26744


    doChangeValue0-121	TRAP-TYPE
	ENTERPRISE	network-device
	VARIABLES	{ doValue, adminDateAndTime, adminNDTrapSeqNo,
			  doIndex, doType, doValue1String }
	DESCRIPTION	"This trap is generated when set
			 doChangeValue0TrapID equal 121 and
			the value of doValue change from 1 to 0."
	::= 26745


    doChangeValue0-122	TRAP-TYPE
	ENTERPRISE	network-device
	VARIABLES	{ doValue, adminDateAndTime, adminNDTrapSeqNo,
			  doIndex, doType, doValue1String }
	DESCRIPTION	"This trap is generated when set
			 doChangeValue0TrapID equal 122 and
			the value of doValue change from 1 to 0."
	::= 26746


    doChangeValue0-123	TRAP-TYPE
	ENTERPRISE	network-device
	VARIABLES	{ doValue, adminDateAndTime, adminNDTrapSeqNo,
			  doIndex, doType, doValue1String }
	DESCRIPTION	"This trap is generated when set
			 doChangeValue0TrapID equal 123 and
			the value of doValue change from 1 to 0."
	::= 26747


    doChangeValue0-124	TRAP-TYPE
	ENTERPRISE	network-device
	VARIABLES	{ doValue, adminDateAndTime, adminNDTrapSeqNo,
			  doIndex, doType, doValue1String }
	DESCRIPTION	"This trap is generated when set
			 doChangeValue0TrapID equal 124 and
			the value of doValue change from 1 to 0."
	::= 26748


    doChangeValue0-125	TRAP-TYPE
	ENTERPRISE	network-device
	VARIABLES	{ doValue, adminDateAndTime, adminNDTrapSeqNo,
			  doIndex, doType, doValue1String }
	DESCRIPTION	"This trap is generated when set
			 doChangeValue0TrapID equal 125 and
			the value of doValue change from 1 to 0."
	::= 26749


    doChangeValue0-126	TRAP-TYPE
	ENTERPRISE	network-device
	VARIABLES	{ doValue, adminDateAndTime, adminNDTrapSeqNo,
			  doIndex, doType, doValue1String }
	DESCRIPTION	"This trap is generated when set
			 doChangeValue0TrapID equal 126 and
			the value of doValue change from 1 to 0."
	::= 26750


    doChangeValue0-127	TRAP-TYPE
	ENTERPRISE	network-device
	VARIABLES	{ doValue, adminDateAndTime, adminNDTrapSeqNo,
			  doIndex, doType, doValue1String }
	DESCRIPTION	"This trap is generated when set
			 doChangeValue0TrapID equal 127 and
			the value of doValue change from 1 to 0."
	::= 26751


    doValue0-1	TRAP-TYPE
	ENTERPRISE	network-device
	VARIABLES	{ doValue, adminDateAndTime, adminNDTrapSeqNo,
			  doIndex, doType, doValue1String }
	DESCRIPTION	"This trap is generated when set
			 doValue0TrapID equal 1 and
			while the value of doValue is 1."
	::= 27137


    doValue0-2	TRAP-TYPE
	ENTERPRISE	network-device
	VARIABLES	{ doValue, adminDateAndTime, adminNDTrapSeqNo,
			  doIndex, doType, doValue1String }
	DESCRIPTION	"This trap is generated when set
			 doValue0TrapID equal 2 and
			while the value of doValue is 1."
	::= 27138


    doValue0-3	TRAP-TYPE
	ENTERPRISE	network-device
	VARIABLES	{ doValue, adminDateAndTime, adminNDTrapSeqNo,
			  doIndex, doType, doValue1String }
	DESCRIPTION	"This trap is generated when set
			 doValue0TrapID equal 3 and
			while the value of doValue is 1."
	::= 27139


    doValue0-4	TRAP-TYPE
	ENTERPRISE	network-device
	VARIABLES	{ doValue, adminDateAndTime, adminNDTrapSeqNo,
			  doIndex, doType, doValue1String }
	DESCRIPTION	"This trap is generated when set
			 doValue0TrapID equal 4 and
			while the value of doValue is 1."
	::= 27140


    doValue0-5	TRAP-TYPE
	ENTERPRISE	network-device
	VARIABLES	{ doValue, adminDateAndTime, adminNDTrapSeqNo,
			  doIndex, doType, doValue1String }
	DESCRIPTION	"This trap is generated when set
			 doValue0TrapID equal 5 and
			while the value of doValue is 1."
	::= 27141


    doValue0-6	TRAP-TYPE
	ENTERPRISE	network-device
	VARIABLES	{ doValue, adminDateAndTime, adminNDTrapSeqNo,
			  doIndex, doType, doValue1String }
	DESCRIPTION	"This trap is generated when set
			 doValue0TrapID equal 6 and
			while the value of doValue is 1."
	::= 27142


    doValue0-7	TRAP-TYPE
	ENTERPRISE	network-device
	VARIABLES	{ doValue, adminDateAndTime, adminNDTrapSeqNo,
			  doIndex, doType, doValue1String }
	DESCRIPTION	"This trap is generated when set
			 doValue0TrapID equal 7 and
			while the value of doValue is 1."
	::= 27143


    doValue0-8	TRAP-TYPE
	ENTERPRISE	network-device
	VARIABLES	{ doValue, adminDateAndTime, adminNDTrapSeqNo,
			  doIndex, doType, doValue1String }
	DESCRIPTION	"This trap is generated when set
			 doValue0TrapID equal 8 and
			while the value of doValue is 1."
	::= 27144


    doValue0-9	TRAP-TYPE
	ENTERPRISE	network-device
	VARIABLES	{ doValue, adminDateAndTime, adminNDTrapSeqNo,
			  doIndex, doType, doValue1String }
	DESCRIPTION	"This trap is generated when set
			 doValue0TrapID equal 9 and
			while the value of doValue is 1."
	::= 27145


    doValue0-10	TRAP-TYPE
	ENTERPRISE	network-device
	VARIABLES	{ doValue, adminDateAndTime, adminNDTrapSeqNo,
			  doIndex, doType, doValue1String }
	DESCRIPTION	"This trap is generated when set
			 doValue0TrapID equal 10 and
			while the value of doValue is 1."
	::= 27146


    doValue0-11	TRAP-TYPE
	ENTERPRISE	network-device
	VARIABLES	{ doValue, adminDateAndTime, adminNDTrapSeqNo,
			  doIndex, doType, doValue1String }
	DESCRIPTION	"This trap is generated when set
			 doValue0TrapID equal 11 and
			while the value of doValue is 1."
	::= 27147


    doValue0-12	TRAP-TYPE
	ENTERPRISE	network-device
	VARIABLES	{ doValue, adminDateAndTime, adminNDTrapSeqNo,
			  doIndex, doType, doValue1String }
	DESCRIPTION	"This trap is generated when set
			 doValue0TrapID equal 12 and
			while the value of doValue is 1."
	::= 27148


    doValue0-13	TRAP-TYPE
	ENTERPRISE	network-device
	VARIABLES	{ doValue, adminDateAndTime, adminNDTrapSeqNo,
			  doIndex, doType, doValue1String }
	DESCRIPTION	"This trap is generated when set
			 doValue0TrapID equal 13 and
			while the value of doValue is 1."
	::= 27149


    doValue0-14	TRAP-TYPE
	ENTERPRISE	network-device
	VARIABLES	{ doValue, adminDateAndTime, adminNDTrapSeqNo,
			  doIndex, doType, doValue1String }
	DESCRIPTION	"This trap is generated when set
			 doValue0TrapID equal 14 and
			while the value of doValue is 1."
	::= 27150


    doValue0-15	TRAP-TYPE
	ENTERPRISE	network-device
	VARIABLES	{ doValue, adminDateAndTime, adminNDTrapSeqNo,
			  doIndex, doType, doValue1String }
	DESCRIPTION	"This trap is generated when set
			 doValue0TrapID equal 15 and
			while the value of doValue is 1."
	::= 27151


    doValue0-16	TRAP-TYPE
	ENTERPRISE	network-device
	VARIABLES	{ doValue, adminDateAndTime, adminNDTrapSeqNo,
			  doIndex, doType, doValue1String }
	DESCRIPTION	"This trap is generated when set
			 doValue0TrapID equal 16 and
			while the value of doValue is 1."
	::= 27152


    doValue0-17	TRAP-TYPE
	ENTERPRISE	network-device
	VARIABLES	{ doValue, adminDateAndTime, adminNDTrapSeqNo,
			  doIndex, doType, doValue1String }
	DESCRIPTION	"This trap is generated when set
			 doValue0TrapID equal 17 and
			while the value of doValue is 1."
	::= 27153


    doValue0-18	TRAP-TYPE
	ENTERPRISE	network-device
	VARIABLES	{ doValue, adminDateAndTime, adminNDTrapSeqNo,
			  doIndex, doType, doValue1String }
	DESCRIPTION	"This trap is generated when set
			 doValue0TrapID equal 18 and
			while the value of doValue is 1."
	::= 27154


    doValue0-19	TRAP-TYPE
	ENTERPRISE	network-device
	VARIABLES	{ doValue, adminDateAndTime, adminNDTrapSeqNo,
			  doIndex, doType, doValue1String }
	DESCRIPTION	"This trap is generated when set
			 doValue0TrapID equal 19 and
			while the value of doValue is 1."
	::= 27155


    doValue0-20	TRAP-TYPE
	ENTERPRISE	network-device
	VARIABLES	{ doValue, adminDateAndTime, adminNDTrapSeqNo,
			  doIndex, doType, doValue1String }
	DESCRIPTION	"This trap is generated when set
			 doValue0TrapID equal 20 and
			while the value of doValue is 1."
	::= 27156


    doValue0-21	TRAP-TYPE
	ENTERPRISE	network-device
	VARIABLES	{ doValue, adminDateAndTime, adminNDTrapSeqNo,
			  doIndex, doType, doValue1String }
	DESCRIPTION	"This trap is generated when set
			 doValue0TrapID equal 21 and
			while the value of doValue is 1."
	::= 27157


    doValue0-22	TRAP-TYPE
	ENTERPRISE	network-device
	VARIABLES	{ doValue, adminDateAndTime, adminNDTrapSeqNo,
			  doIndex, doType, doValue1String }
	DESCRIPTION	"This trap is generated when set
			 doValue0TrapID equal 22 and
			while the value of doValue is 1."
	::= 27158


    doValue0-23	TRAP-TYPE
	ENTERPRISE	network-device
	VARIABLES	{ doValue, adminDateAndTime, adminNDTrapSeqNo,
			  doIndex, doType, doValue1String }
	DESCRIPTION	"This trap is generated when set
			 doValue0TrapID equal 23 and
			while the value of doValue is 1."
	::= 27159


    doValue0-24	TRAP-TYPE
	ENTERPRISE	network-device
	VARIABLES	{ doValue, adminDateAndTime, adminNDTrapSeqNo,
			  doIndex, doType, doValue1String }
	DESCRIPTION	"This trap is generated when set
			 doValue0TrapID equal 24 and
			while the value of doValue is 1."
	::= 27160


    doValue0-25	TRAP-TYPE
	ENTERPRISE	network-device
	VARIABLES	{ doValue, adminDateAndTime, adminNDTrapSeqNo,
			  doIndex, doType, doValue1String }
	DESCRIPTION	"This trap is generated when set
			 doValue0TrapID equal 25 and
			while the value of doValue is 1."
	::= 27161


    doValue0-26	TRAP-TYPE
	ENTERPRISE	network-device
	VARIABLES	{ doValue, adminDateAndTime, adminNDTrapSeqNo,
			  doIndex, doType, doValue1String }
	DESCRIPTION	"This trap is generated when set
			 doValue0TrapID equal 26 and
			while the value of doValue is 1."
	::= 27162


    doValue0-27	TRAP-TYPE
	ENTERPRISE	network-device
	VARIABLES	{ doValue, adminDateAndTime, adminNDTrapSeqNo,
			  doIndex, doType, doValue1String }
	DESCRIPTION	"This trap is generated when set
			 doValue0TrapID equal 27 and
			while the value of doValue is 1."
	::= 27163


    doValue0-28	TRAP-TYPE
	ENTERPRISE	network-device
	VARIABLES	{ doValue, adminDateAndTime, adminNDTrapSeqNo,
			  doIndex, doType, doValue1String }
	DESCRIPTION	"This trap is generated when set
			 doValue0TrapID equal 28 and
			while the value of doValue is 1."
	::= 27164


    doValue0-29	TRAP-TYPE
	ENTERPRISE	network-device
	VARIABLES	{ doValue, adminDateAndTime, adminNDTrapSeqNo,
			  doIndex, doType, doValue1String }
	DESCRIPTION	"This trap is generated when set
			 doValue0TrapID equal 29 and
			while the value of doValue is 1."
	::= 27165


    doValue0-30	TRAP-TYPE
	ENTERPRISE	network-device
	VARIABLES	{ doValue, adminDateAndTime, adminNDTrapSeqNo,
			  doIndex, doType, doValue1String }
	DESCRIPTION	"This trap is generated when set
			 doValue0TrapID equal 30 and
			while the value of doValue is 1."
	::= 27166


    doValue0-31	TRAP-TYPE
	ENTERPRISE	network-device
	VARIABLES	{ doValue, adminDateAndTime, adminNDTrapSeqNo,
			  doIndex, doType, doValue1String }
	DESCRIPTION	"This trap is generated when set
			 doValue0TrapID equal 31 and
			while the value of doValue is 1."
	::= 27167


    doValue0-32	TRAP-TYPE
	ENTERPRISE	network-device
	VARIABLES	{ doValue, adminDateAndTime, adminNDTrapSeqNo,
			  doIndex, doType, doValue1String }
	DESCRIPTION	"This trap is generated when set
			 doValue0TrapID equal 32 and
			while the value of doValue is 1."
	::= 27168


    doValue0-33	TRAP-TYPE
	ENTERPRISE	network-device
	VARIABLES	{ doValue, adminDateAndTime, adminNDTrapSeqNo,
			  doIndex, doType, doValue1String }
	DESCRIPTION	"This trap is generated when set
			 doValue0TrapID equal 33 and
			while the value of doValue is 1."
	::= 27169


    doValue0-34	TRAP-TYPE
	ENTERPRISE	network-device
	VARIABLES	{ doValue, adminDateAndTime, adminNDTrapSeqNo,
			  doIndex, doType, doValue1String }
	DESCRIPTION	"This trap is generated when set
			 doValue0TrapID equal 34 and
			while the value of doValue is 1."
	::= 27170


    doValue0-35	TRAP-TYPE
	ENTERPRISE	network-device
	VARIABLES	{ doValue, adminDateAndTime, adminNDTrapSeqNo,
			  doIndex, doType, doValue1String }
	DESCRIPTION	"This trap is generated when set
			 doValue0TrapID equal 35 and
			while the value of doValue is 1."
	::= 27171


    doValue0-36	TRAP-TYPE
	ENTERPRISE	network-device
	VARIABLES	{ doValue, adminDateAndTime, adminNDTrapSeqNo,
			  doIndex, doType, doValue1String }
	DESCRIPTION	"This trap is generated when set
			 doValue0TrapID equal 36 and
			while the value of doValue is 1."
	::= 27172


    doValue0-37	TRAP-TYPE
	ENTERPRISE	network-device
	VARIABLES	{ doValue, adminDateAndTime, adminNDTrapSeqNo,
			  doIndex, doType, doValue1String }
	DESCRIPTION	"This trap is generated when set
			 doValue0TrapID equal 37 and
			while the value of doValue is 1."
	::= 27173


    doValue0-38	TRAP-TYPE
	ENTERPRISE	network-device
	VARIABLES	{ doValue, adminDateAndTime, adminNDTrapSeqNo,
			  doIndex, doType, doValue1String }
	DESCRIPTION	"This trap is generated when set
			 doValue0TrapID equal 38 and
			while the value of doValue is 1."
	::= 27174


    doValue0-39	TRAP-TYPE
	ENTERPRISE	network-device
	VARIABLES	{ doValue, adminDateAndTime, adminNDTrapSeqNo,
			  doIndex, doType, doValue1String }
	DESCRIPTION	"This trap is generated when set
			 doValue0TrapID equal 39 and
			while the value of doValue is 1."
	::= 27175


    doValue0-40	TRAP-TYPE
	ENTERPRISE	network-device
	VARIABLES	{ doValue, adminDateAndTime, adminNDTrapSeqNo,
			  doIndex, doType, doValue1String }
	DESCRIPTION	"This trap is generated when set
			 doValue0TrapID equal 40 and
			while the value of doValue is 1."
	::= 27176


    doValue0-41	TRAP-TYPE
	ENTERPRISE	network-device
	VARIABLES	{ doValue, adminDateAndTime, adminNDTrapSeqNo,
			  doIndex, doType, doValue1String }
	DESCRIPTION	"This trap is generated when set
			 doValue0TrapID equal 41 and
			while the value of doValue is 1."
	::= 27177


    doValue0-42	TRAP-TYPE
	ENTERPRISE	network-device
	VARIABLES	{ doValue, adminDateAndTime, adminNDTrapSeqNo,
			  doIndex, doType, doValue1String }
	DESCRIPTION	"This trap is generated when set
			 doValue0TrapID equal 42 and
			while the value of doValue is 1."
	::= 27178


    doValue0-43	TRAP-TYPE
	ENTERPRISE	network-device
	VARIABLES	{ doValue, adminDateAndTime, adminNDTrapSeqNo,
			  doIndex, doType, doValue1String }
	DESCRIPTION	"This trap is generated when set
			 doValue0TrapID equal 43 and
			while the value of doValue is 1."
	::= 27179


    doValue0-44	TRAP-TYPE
	ENTERPRISE	network-device
	VARIABLES	{ doValue, adminDateAndTime, adminNDTrapSeqNo,
			  doIndex, doType, doValue1String }
	DESCRIPTION	"This trap is generated when set
			 doValue0TrapID equal 44 and
			while the value of doValue is 1."
	::= 27180


    doValue0-45	TRAP-TYPE
	ENTERPRISE	network-device
	VARIABLES	{ doValue, adminDateAndTime, adminNDTrapSeqNo,
			  doIndex, doType, doValue1String }
	DESCRIPTION	"This trap is generated when set
			 doValue0TrapID equal 45 and
			while the value of doValue is 1."
	::= 27181


    doValue0-46	TRAP-TYPE
	ENTERPRISE	network-device
	VARIABLES	{ doValue, adminDateAndTime, adminNDTrapSeqNo,
			  doIndex, doType, doValue1String }
	DESCRIPTION	"This trap is generated when set
			 doValue0TrapID equal 46 and
			while the value of doValue is 1."
	::= 27182


    doValue0-47	TRAP-TYPE
	ENTERPRISE	network-device
	VARIABLES	{ doValue, adminDateAndTime, adminNDTrapSeqNo,
			  doIndex, doType, doValue1String }
	DESCRIPTION	"This trap is generated when set
			 doValue0TrapID equal 47 and
			while the value of doValue is 1."
	::= 27183


    doValue0-48	TRAP-TYPE
	ENTERPRISE	network-device
	VARIABLES	{ doValue, adminDateAndTime, adminNDTrapSeqNo,
			  doIndex, doType, doValue1String }
	DESCRIPTION	"This trap is generated when set
			 doValue0TrapID equal 48 and
			while the value of doValue is 1."
	::= 27184


    doValue0-49	TRAP-TYPE
	ENTERPRISE	network-device
	VARIABLES	{ doValue, adminDateAndTime, adminNDTrapSeqNo,
			  doIndex, doType, doValue1String }
	DESCRIPTION	"This trap is generated when set
			 doValue0TrapID equal 49 and
			while the value of doValue is 1."
	::= 27185


    doValue0-50	TRAP-TYPE
	ENTERPRISE	network-device
	VARIABLES	{ doValue, adminDateAndTime, adminNDTrapSeqNo,
			  doIndex, doType, doValue1String }
	DESCRIPTION	"This trap is generated when set
			 doValue0TrapID equal 50 and
			while the value of doValue is 1."
	::= 27186


    doValue0-51	TRAP-TYPE
	ENTERPRISE	network-device
	VARIABLES	{ doValue, adminDateAndTime, adminNDTrapSeqNo,
			  doIndex, doType, doValue1String }
	DESCRIPTION	"This trap is generated when set
			 doValue0TrapID equal 51 and
			while the value of doValue is 1."
	::= 27187


    doValue0-52	TRAP-TYPE
	ENTERPRISE	network-device
	VARIABLES	{ doValue, adminDateAndTime, adminNDTrapSeqNo,
			  doIndex, doType, doValue1String }
	DESCRIPTION	"This trap is generated when set
			 doValue0TrapID equal 52 and
			while the value of doValue is 1."
	::= 27188


    doValue0-53	TRAP-TYPE
	ENTERPRISE	network-device
	VARIABLES	{ doValue, adminDateAndTime, adminNDTrapSeqNo,
			  doIndex, doType, doValue1String }
	DESCRIPTION	"This trap is generated when set
			 doValue0TrapID equal 53 and
			while the value of doValue is 1."
	::= 27189


    doValue0-54	TRAP-TYPE
	ENTERPRISE	network-device
	VARIABLES	{ doValue, adminDateAndTime, adminNDTrapSeqNo,
			  doIndex, doType, doValue1String }
	DESCRIPTION	"This trap is generated when set
			 doValue0TrapID equal 54 and
			while the value of doValue is 1."
	::= 27190


    doValue0-55	TRAP-TYPE
	ENTERPRISE	network-device
	VARIABLES	{ doValue, adminDateAndTime, adminNDTrapSeqNo,
			  doIndex, doType, doValue1String }
	DESCRIPTION	"This trap is generated when set
			 doValue0TrapID equal 55 and
			while the value of doValue is 1."
	::= 27191


    doValue0-56	TRAP-TYPE
	ENTERPRISE	network-device
	VARIABLES	{ doValue, adminDateAndTime, adminNDTrapSeqNo,
			  doIndex, doType, doValue1String }
	DESCRIPTION	"This trap is generated when set
			 doValue0TrapID equal 56 and
			while the value of doValue is 1."
	::= 27192


    doValue0-57	TRAP-TYPE
	ENTERPRISE	network-device
	VARIABLES	{ doValue, adminDateAndTime, adminNDTrapSeqNo,
			  doIndex, doType, doValue1String }
	DESCRIPTION	"This trap is generated when set
			 doValue0TrapID equal 57 and
			while the value of doValue is 1."
	::= 27193


    doValue0-58	TRAP-TYPE
	ENTERPRISE	network-device
	VARIABLES	{ doValue, adminDateAndTime, adminNDTrapSeqNo,
			  doIndex, doType, doValue1String }
	DESCRIPTION	"This trap is generated when set
			 doValue0TrapID equal 58 and
			while the value of doValue is 1."
	::= 27194


    doValue0-59	TRAP-TYPE
	ENTERPRISE	network-device
	VARIABLES	{ doValue, adminDateAndTime, adminNDTrapSeqNo,
			  doIndex, doType, doValue1String }
	DESCRIPTION	"This trap is generated when set
			 doValue0TrapID equal 59 and
			while the value of doValue is 1."
	::= 27195


    doValue0-60	TRAP-TYPE
	ENTERPRISE	network-device
	VARIABLES	{ doValue, adminDateAndTime, adminNDTrapSeqNo,
			  doIndex, doType, doValue1String }
	DESCRIPTION	"This trap is generated when set
			 doValue0TrapID equal 60 and
			while the value of doValue is 1."
	::= 27196


    doValue0-61	TRAP-TYPE
	ENTERPRISE	network-device
	VARIABLES	{ doValue, adminDateAndTime, adminNDTrapSeqNo,
			  doIndex, doType, doValue1String }
	DESCRIPTION	"This trap is generated when set
			 doValue0TrapID equal 61 and
			while the value of doValue is 1."
	::= 27197


    doValue0-62	TRAP-TYPE
	ENTERPRISE	network-device
	VARIABLES	{ doValue, adminDateAndTime, adminNDTrapSeqNo,
			  doIndex, doType, doValue1String }
	DESCRIPTION	"This trap is generated when set
			 doValue0TrapID equal 62 and
			while the value of doValue is 1."
	::= 27198


    doValue0-63	TRAP-TYPE
	ENTERPRISE	network-device
	VARIABLES	{ doValue, adminDateAndTime, adminNDTrapSeqNo,
			  doIndex, doType, doValue1String }
	DESCRIPTION	"This trap is generated when set
			 doValue0TrapID equal 63 and
			while the value of doValue is 1."
	::= 27199


    doValue0-64	TRAP-TYPE
	ENTERPRISE	network-device
	VARIABLES	{ doValue, adminDateAndTime, adminNDTrapSeqNo,
			  doIndex, doType, doValue1String }
	DESCRIPTION	"This trap is generated when set
			 doValue0TrapID equal 64 and
			while the value of doValue is 1."
	::= 27200


    doValue0-65	TRAP-TYPE
	ENTERPRISE	network-device
	VARIABLES	{ doValue, adminDateAndTime, adminNDTrapSeqNo,
			  doIndex, doType, doValue1String }
	DESCRIPTION	"This trap is generated when set
			 doValue0TrapID equal 65 and
			while the value of doValue is 1."
	::= 27201


    doValue0-66	TRAP-TYPE
	ENTERPRISE	network-device
	VARIABLES	{ doValue, adminDateAndTime, adminNDTrapSeqNo,
			  doIndex, doType, doValue1String }
	DESCRIPTION	"This trap is generated when set
			 doValue0TrapID equal 66 and
			while the value of doValue is 1."
	::= 27202


    doValue0-67	TRAP-TYPE
	ENTERPRISE	network-device
	VARIABLES	{ doValue, adminDateAndTime, adminNDTrapSeqNo,
			  doIndex, doType, doValue1String }
	DESCRIPTION	"This trap is generated when set
			 doValue0TrapID equal 67 and
			while the value of doValue is 1."
	::= 27203


    doValue0-68	TRAP-TYPE
	ENTERPRISE	network-device
	VARIABLES	{ doValue, adminDateAndTime, adminNDTrapSeqNo,
			  doIndex, doType, doValue1String }
	DESCRIPTION	"This trap is generated when set
			 doValue0TrapID equal 68 and
			while the value of doValue is 1."
	::= 27204


    doValue0-69	TRAP-TYPE
	ENTERPRISE	network-device
	VARIABLES	{ doValue, adminDateAndTime, adminNDTrapSeqNo,
			  doIndex, doType, doValue1String }
	DESCRIPTION	"This trap is generated when set
			 doValue0TrapID equal 69 and
			while the value of doValue is 1."
	::= 27205


    doValue0-70	TRAP-TYPE
	ENTERPRISE	network-device
	VARIABLES	{ doValue, adminDateAndTime, adminNDTrapSeqNo,
			  doIndex, doType, doValue1String }
	DESCRIPTION	"This trap is generated when set
			 doValue0TrapID equal 70 and
			while the value of doValue is 1."
	::= 27206


    doValue0-71	TRAP-TYPE
	ENTERPRISE	network-device
	VARIABLES	{ doValue, adminDateAndTime, adminNDTrapSeqNo,
			  doIndex, doType, doValue1String }
	DESCRIPTION	"This trap is generated when set
			 doValue0TrapID equal 71 and
			while the value of doValue is 1."
	::= 27207


    doValue0-72	TRAP-TYPE
	ENTERPRISE	network-device
	VARIABLES	{ doValue, adminDateAndTime, adminNDTrapSeqNo,
			  doIndex, doType, doValue1String }
	DESCRIPTION	"This trap is generated when set
			 doValue0TrapID equal 72 and
			while the value of doValue is 1."
	::= 27208


    doValue0-73	TRAP-TYPE
	ENTERPRISE	network-device
	VARIABLES	{ doValue, adminDateAndTime, adminNDTrapSeqNo,
			  doIndex, doType, doValue1String }
	DESCRIPTION	"This trap is generated when set
			 doValue0TrapID equal 73 and
			while the value of doValue is 1."
	::= 27209


    doValue0-74	TRAP-TYPE
	ENTERPRISE	network-device
	VARIABLES	{ doValue, adminDateAndTime, adminNDTrapSeqNo,
			  doIndex, doType, doValue1String }
	DESCRIPTION	"This trap is generated when set
			 doValue0TrapID equal 74 and
			while the value of doValue is 1."
	::= 27210


    doValue0-75	TRAP-TYPE
	ENTERPRISE	network-device
	VARIABLES	{ doValue, adminDateAndTime, adminNDTrapSeqNo,
			  doIndex, doType, doValue1String }
	DESCRIPTION	"This trap is generated when set
			 doValue0TrapID equal 75 and
			while the value of doValue is 1."
	::= 27211


    doValue0-76	TRAP-TYPE
	ENTERPRISE	network-device
	VARIABLES	{ doValue, adminDateAndTime, adminNDTrapSeqNo,
			  doIndex, doType, doValue1String }
	DESCRIPTION	"This trap is generated when set
			 doValue0TrapID equal 76 and
			while the value of doValue is 1."
	::= 27212


    doValue0-77	TRAP-TYPE
	ENTERPRISE	network-device
	VARIABLES	{ doValue, adminDateAndTime, adminNDTrapSeqNo,
			  doIndex, doType, doValue1String }
	DESCRIPTION	"This trap is generated when set
			 doValue0TrapID equal 77 and
			while the value of doValue is 1."
	::= 27213


    doValue0-78	TRAP-TYPE
	ENTERPRISE	network-device
	VARIABLES	{ doValue, adminDateAndTime, adminNDTrapSeqNo,
			  doIndex, doType, doValue1String }
	DESCRIPTION	"This trap is generated when set
			 doValue0TrapID equal 78 and
			while the value of doValue is 1."
	::= 27214


    doValue0-79	TRAP-TYPE
	ENTERPRISE	network-device
	VARIABLES	{ doValue, adminDateAndTime, adminNDTrapSeqNo,
			  doIndex, doType, doValue1String }
	DESCRIPTION	"This trap is generated when set
			 doValue0TrapID equal 79 and
			while the value of doValue is 1."
	::= 27215


    doValue0-80	TRAP-TYPE
	ENTERPRISE	network-device
	VARIABLES	{ doValue, adminDateAndTime, adminNDTrapSeqNo,
			  doIndex, doType, doValue1String }
	DESCRIPTION	"This trap is generated when set
			 doValue0TrapID equal 80 and
			while the value of doValue is 1."
	::= 27216


    doValue0-81	TRAP-TYPE
	ENTERPRISE	network-device
	VARIABLES	{ doValue, adminDateAndTime, adminNDTrapSeqNo,
			  doIndex, doType, doValue1String }
	DESCRIPTION	"This trap is generated when set
			 doValue0TrapID equal 81 and
			while the value of doValue is 1."
	::= 27217


    doValue0-82	TRAP-TYPE
	ENTERPRISE	network-device
	VARIABLES	{ doValue, adminDateAndTime, adminNDTrapSeqNo,
			  doIndex, doType, doValue1String }
	DESCRIPTION	"This trap is generated when set
			 doValue0TrapID equal 82 and
			while the value of doValue is 1."
	::= 27218


    doValue0-83	TRAP-TYPE
	ENTERPRISE	network-device
	VARIABLES	{ doValue, adminDateAndTime, adminNDTrapSeqNo,
			  doIndex, doType, doValue1String }
	DESCRIPTION	"This trap is generated when set
			 doValue0TrapID equal 83 and
			while the value of doValue is 1."
	::= 27219


    doValue0-84	TRAP-TYPE
	ENTERPRISE	network-device
	VARIABLES	{ doValue, adminDateAndTime, adminNDTrapSeqNo,
			  doIndex, doType, doValue1String }
	DESCRIPTION	"This trap is generated when set
			 doValue0TrapID equal 84 and
			while the value of doValue is 1."
	::= 27220


    doValue0-85	TRAP-TYPE
	ENTERPRISE	network-device
	VARIABLES	{ doValue, adminDateAndTime, adminNDTrapSeqNo,
			  doIndex, doType, doValue1String }
	DESCRIPTION	"This trap is generated when set
			 doValue0TrapID equal 85 and
			while the value of doValue is 1."
	::= 27221


    doValue0-86	TRAP-TYPE
	ENTERPRISE	network-device
	VARIABLES	{ doValue, adminDateAndTime, adminNDTrapSeqNo,
			  doIndex, doType, doValue1String }
	DESCRIPTION	"This trap is generated when set
			 doValue0TrapID equal 86 and
			while the value of doValue is 1."
	::= 27222


    doValue0-87	TRAP-TYPE
	ENTERPRISE	network-device
	VARIABLES	{ doValue, adminDateAndTime, adminNDTrapSeqNo,
			  doIndex, doType, doValue1String }
	DESCRIPTION	"This trap is generated when set
			 doValue0TrapID equal 87 and
			while the value of doValue is 1."
	::= 27223


    doValue0-88	TRAP-TYPE
	ENTERPRISE	network-device
	VARIABLES	{ doValue, adminDateAndTime, adminNDTrapSeqNo,
			  doIndex, doType, doValue1String }
	DESCRIPTION	"This trap is generated when set
			 doValue0TrapID equal 88 and
			while the value of doValue is 1."
	::= 27224


    doValue0-89	TRAP-TYPE
	ENTERPRISE	network-device
	VARIABLES	{ doValue, adminDateAndTime, adminNDTrapSeqNo,
			  doIndex, doType, doValue1String }
	DESCRIPTION	"This trap is generated when set
			 doValue0TrapID equal 89 and
			while the value of doValue is 1."
	::= 27225


    doValue0-90	TRAP-TYPE
	ENTERPRISE	network-device
	VARIABLES	{ doValue, adminDateAndTime, adminNDTrapSeqNo,
			  doIndex, doType, doValue1String }
	DESCRIPTION	"This trap is generated when set
			 doValue0TrapID equal 90 and
			while the value of doValue is 1."
	::= 27226


    doValue0-91	TRAP-TYPE
	ENTERPRISE	network-device
	VARIABLES	{ doValue, adminDateAndTime, adminNDTrapSeqNo,
			  doIndex, doType, doValue1String }
	DESCRIPTION	"This trap is generated when set
			 doValue0TrapID equal 91 and
			while the value of doValue is 1."
	::= 27227


    doValue0-92	TRAP-TYPE
	ENTERPRISE	network-device
	VARIABLES	{ doValue, adminDateAndTime, adminNDTrapSeqNo,
			  doIndex, doType, doValue1String }
	DESCRIPTION	"This trap is generated when set
			 doValue0TrapID equal 92 and
			while the value of doValue is 1."
	::= 27228


    doValue0-93	TRAP-TYPE
	ENTERPRISE	network-device
	VARIABLES	{ doValue, adminDateAndTime, adminNDTrapSeqNo,
			  doIndex, doType, doValue1String }
	DESCRIPTION	"This trap is generated when set
			 doValue0TrapID equal 93 and
			while the value of doValue is 1."
	::= 27229


    doValue0-94	TRAP-TYPE
	ENTERPRISE	network-device
	VARIABLES	{ doValue, adminDateAndTime, adminNDTrapSeqNo,
			  doIndex, doType, doValue1String }
	DESCRIPTION	"This trap is generated when set
			 doValue0TrapID equal 94 and
			while the value of doValue is 1."
	::= 27230


    doValue0-95	TRAP-TYPE
	ENTERPRISE	network-device
	VARIABLES	{ doValue, adminDateAndTime, adminNDTrapSeqNo,
			  doIndex, doType, doValue1String }
	DESCRIPTION	"This trap is generated when set
			 doValue0TrapID equal 95 and
			while the value of doValue is 1."
	::= 27231


    doValue0-96	TRAP-TYPE
	ENTERPRISE	network-device
	VARIABLES	{ doValue, adminDateAndTime, adminNDTrapSeqNo,
			  doIndex, doType, doValue1String }
	DESCRIPTION	"This trap is generated when set
			 doValue0TrapID equal 96 and
			while the value of doValue is 1."
	::= 27232


    doValue0-97	TRAP-TYPE
	ENTERPRISE	network-device
	VARIABLES	{ doValue, adminDateAndTime, adminNDTrapSeqNo,
			  doIndex, doType, doValue1String }
	DESCRIPTION	"This trap is generated when set
			 doValue0TrapID equal 97 and
			while the value of doValue is 1."
	::= 27233


    doValue0-98	TRAP-TYPE
	ENTERPRISE	network-device
	VARIABLES	{ doValue, adminDateAndTime, adminNDTrapSeqNo,
			  doIndex, doType, doValue1String }
	DESCRIPTION	"This trap is generated when set
			 doValue0TrapID equal 98 and
			while the value of doValue is 1."
	::= 27234


    doValue0-99	TRAP-TYPE
	ENTERPRISE	network-device
	VARIABLES	{ doValue, adminDateAndTime, adminNDTrapSeqNo,
			  doIndex, doType, doValue1String }
	DESCRIPTION	"This trap is generated when set
			 doValue0TrapID equal 99 and
			while the value of doValue is 1."
	::= 27235


    doValue0-100	TRAP-TYPE
	ENTERPRISE	network-device
	VARIABLES	{ doValue, adminDateAndTime, adminNDTrapSeqNo,
			  doIndex, doType, doValue1String }
	DESCRIPTION	"This trap is generated when set
			 doValue0TrapID equal 100 and
			while the value of doValue is 1."
	::= 27236


    doValue0-101	TRAP-TYPE
	ENTERPRISE	network-device
	VARIABLES	{ doValue, adminDateAndTime, adminNDTrapSeqNo,
			  doIndex, doType, doValue1String }
	DESCRIPTION	"This trap is generated when set
			 doValue0TrapID equal 101 and
			while the value of doValue is 1."
	::= 27237


    doValue0-102	TRAP-TYPE
	ENTERPRISE	network-device
	VARIABLES	{ doValue, adminDateAndTime, adminNDTrapSeqNo,
			  doIndex, doType, doValue1String }
	DESCRIPTION	"This trap is generated when set
			 doValue0TrapID equal 102 and
			while the value of doValue is 1."
	::= 27238


    doValue0-103	TRAP-TYPE
	ENTERPRISE	network-device
	VARIABLES	{ doValue, adminDateAndTime, adminNDTrapSeqNo,
			  doIndex, doType, doValue1String }
	DESCRIPTION	"This trap is generated when set
			 doValue0TrapID equal 103 and
			while the value of doValue is 1."
	::= 27239


    doValue0-104	TRAP-TYPE
	ENTERPRISE	network-device
	VARIABLES	{ doValue, adminDateAndTime, adminNDTrapSeqNo,
			  doIndex, doType, doValue1String }
	DESCRIPTION	"This trap is generated when set
			 doValue0TrapID equal 104 and
			while the value of doValue is 1."
	::= 27240


    doValue0-105	TRAP-TYPE
	ENTERPRISE	network-device
	VARIABLES	{ doValue, adminDateAndTime, adminNDTrapSeqNo,
			  doIndex, doType, doValue1String }
	DESCRIPTION	"This trap is generated when set
			 doValue0TrapID equal 105 and
			while the value of doValue is 1."
	::= 27241


    doValue0-106	TRAP-TYPE
	ENTERPRISE	network-device
	VARIABLES	{ doValue, adminDateAndTime, adminNDTrapSeqNo,
			  doIndex, doType, doValue1String }
	DESCRIPTION	"This trap is generated when set
			 doValue0TrapID equal 106 and
			while the value of doValue is 1."
	::= 27242


    doValue0-107	TRAP-TYPE
	ENTERPRISE	network-device
	VARIABLES	{ doValue, adminDateAndTime, adminNDTrapSeqNo,
			  doIndex, doType, doValue1String }
	DESCRIPTION	"This trap is generated when set
			 doValue0TrapID equal 107 and
			while the value of doValue is 1."
	::= 27243


    doValue0-108	TRAP-TYPE
	ENTERPRISE	network-device
	VARIABLES	{ doValue, adminDateAndTime, adminNDTrapSeqNo,
			  doIndex, doType, doValue1String }
	DESCRIPTION	"This trap is generated when set
			 doValue0TrapID equal 108 and
			while the value of doValue is 1."
	::= 27244


    doValue0-109	TRAP-TYPE
	ENTERPRISE	network-device
	VARIABLES	{ doValue, adminDateAndTime, adminNDTrapSeqNo,
			  doIndex, doType, doValue1String }
	DESCRIPTION	"This trap is generated when set
			 doValue0TrapID equal 109 and
			while the value of doValue is 1."
	::= 27245


    doValue0-110	TRAP-TYPE
	ENTERPRISE	network-device
	VARIABLES	{ doValue, adminDateAndTime, adminNDTrapSeqNo,
			  doIndex, doType, doValue1String }
	DESCRIPTION	"This trap is generated when set
			 doValue0TrapID equal 110 and
			while the value of doValue is 1."
	::= 27246


    doValue0-111	TRAP-TYPE
	ENTERPRISE	network-device
	VARIABLES	{ doValue, adminDateAndTime, adminNDTrapSeqNo,
			  doIndex, doType, doValue1String }
	DESCRIPTION	"This trap is generated when set
			 doValue0TrapID equal 111 and
			while the value of doValue is 1."
	::= 27247


    doValue0-112	TRAP-TYPE
	ENTERPRISE	network-device
	VARIABLES	{ doValue, adminDateAndTime, adminNDTrapSeqNo,
			  doIndex, doType, doValue1String }
	DESCRIPTION	"This trap is generated when set
			 doValue0TrapID equal 112 and
			while the value of doValue is 1."
	::= 27248


    doValue0-113	TRAP-TYPE
	ENTERPRISE	network-device
	VARIABLES	{ doValue, adminDateAndTime, adminNDTrapSeqNo,
			  doIndex, doType, doValue1String }
	DESCRIPTION	"This trap is generated when set
			 doValue0TrapID equal 113 and
			while the value of doValue is 1."
	::= 27249


    doValue0-114	TRAP-TYPE
	ENTERPRISE	network-device
	VARIABLES	{ doValue, adminDateAndTime, adminNDTrapSeqNo,
			  doIndex, doType, doValue1String }
	DESCRIPTION	"This trap is generated when set
			 doValue0TrapID equal 114 and
			while the value of doValue is 1."
	::= 27250


    doValue0-115	TRAP-TYPE
	ENTERPRISE	network-device
	VARIABLES	{ doValue, adminDateAndTime, adminNDTrapSeqNo,
			  doIndex, doType, doValue1String }
	DESCRIPTION	"This trap is generated when set
			 doValue0TrapID equal 115 and
			while the value of doValue is 1."
	::= 27251


    doValue0-116	TRAP-TYPE
	ENTERPRISE	network-device
	VARIABLES	{ doValue, adminDateAndTime, adminNDTrapSeqNo,
			  doIndex, doType, doValue1String }
	DESCRIPTION	"This trap is generated when set
			 doValue0TrapID equal 116 and
			while the value of doValue is 1."
	::= 27252


    doValue0-117	TRAP-TYPE
	ENTERPRISE	network-device
	VARIABLES	{ doValue, adminDateAndTime, adminNDTrapSeqNo,
			  doIndex, doType, doValue1String }
	DESCRIPTION	"This trap is generated when set
			 doValue0TrapID equal 117 and
			while the value of doValue is 1."
	::= 27253


    doValue0-118	TRAP-TYPE
	ENTERPRISE	network-device
	VARIABLES	{ doValue, adminDateAndTime, adminNDTrapSeqNo,
			  doIndex, doType, doValue1String }
	DESCRIPTION	"This trap is generated when set
			 doValue0TrapID equal 118 and
			while the value of doValue is 1."
	::= 27254


    doValue0-119	TRAP-TYPE
	ENTERPRISE	network-device
	VARIABLES	{ doValue, adminDateAndTime, adminNDTrapSeqNo,
			  doIndex, doType, doValue1String }
	DESCRIPTION	"This trap is generated when set
			 doValue0TrapID equal 119 and
			while the value of doValue is 1."
	::= 27255


    doValue0-120	TRAP-TYPE
	ENTERPRISE	network-device
	VARIABLES	{ doValue, adminDateAndTime, adminNDTrapSeqNo,
			  doIndex, doType, doValue1String }
	DESCRIPTION	"This trap is generated when set
			 doValue0TrapID equal 120 and
			while the value of doValue is 1."
	::= 27256


    doValue0-121	TRAP-TYPE
	ENTERPRISE	network-device
	VARIABLES	{ doValue, adminDateAndTime, adminNDTrapSeqNo,
			  doIndex, doType, doValue1String }
	DESCRIPTION	"This trap is generated when set
			 doValue0TrapID equal 121 and
			while the value of doValue is 1."
	::= 27257


    doValue0-122	TRAP-TYPE
	ENTERPRISE	network-device
	VARIABLES	{ doValue, adminDateAndTime, adminNDTrapSeqNo,
			  doIndex, doType, doValue1String }
	DESCRIPTION	"This trap is generated when set
			 doValue0TrapID equal 122 and
			while the value of doValue is 1."
	::= 27258


    doValue0-123	TRAP-TYPE
	ENTERPRISE	network-device
	VARIABLES	{ doValue, adminDateAndTime, adminNDTrapSeqNo,
			  doIndex, doType, doValue1String }
	DESCRIPTION	"This trap is generated when set
			 doValue0TrapID equal 123 and
			while the value of doValue is 1."
	::= 27259


    doValue0-124	TRAP-TYPE
	ENTERPRISE	network-device
	VARIABLES	{ doValue, adminDateAndTime, adminNDTrapSeqNo,
			  doIndex, doType, doValue1String }
	DESCRIPTION	"This trap is generated when set
			 doValue0TrapID equal 124 and
			while the value of doValue is 1."
	::= 27260


    doValue0-125	TRAP-TYPE
	ENTERPRISE	network-device
	VARIABLES	{ doValue, adminDateAndTime, adminNDTrapSeqNo,
			  doIndex, doType, doValue1String }
	DESCRIPTION	"This trap is generated when set
			 doValue0TrapID equal 125 and
			while the value of doValue is 1."
	::= 27261


    doValue0-126	TRAP-TYPE
	ENTERPRISE	network-device
	VARIABLES	{ doValue, adminDateAndTime, adminNDTrapSeqNo,
			  doIndex, doType, doValue1String }
	DESCRIPTION	"This trap is generated when set
			 doValue0TrapID equal 126 and
			while the value of doValue is 1."
	::= 27262


    doValue0-127	TRAP-TYPE
	ENTERPRISE	network-device
	VARIABLES	{ doValue, adminDateAndTime, adminNDTrapSeqNo,
			  doIndex, doType, doValue1String }
	DESCRIPTION	"This trap is generated when set
			 doValue0TrapID equal 127 and
			while the value of doValue is 1."
	::= 27263


    doChangeValue1-1	TRAP-TYPE
	ENTERPRISE	network-device
	VARIABLES	{ doValue, adminDateAndTime, adminNDTrapSeqNo,
			  doIndex, doType, doValue1String }
	DESCRIPTION	"This trap is generated when set
			 doChangeValue1TrapID equal 1 and
			the value of doValue change from 0 to 1."
	::= 27649


    doChangeValue1-2	TRAP-TYPE
	ENTERPRISE	network-device
	VARIABLES	{ doValue, adminDateAndTime, adminNDTrapSeqNo,
			  doIndex, doType, doValue1String }
	DESCRIPTION	"This trap is generated when set
			 doChangeValue1TrapID equal 2 and
			the value of doValue change from 0 to 1."
	::= 27650


    doChangeValue1-3	TRAP-TYPE
	ENTERPRISE	network-device
	VARIABLES	{ doValue, adminDateAndTime, adminNDTrapSeqNo,
			  doIndex, doType, doValue1String }
	DESCRIPTION	"This trap is generated when set
			 doChangeValue1TrapID equal 3 and
			the value of doValue change from 0 to 1."
	::= 27651


    doChangeValue1-4	TRAP-TYPE
	ENTERPRISE	network-device
	VARIABLES	{ doValue, adminDateAndTime, adminNDTrapSeqNo,
			  doIndex, doType, doValue1String }
	DESCRIPTION	"This trap is generated when set
			 doChangeValue1TrapID equal 4 and
			the value of doValue change from 0 to 1."
	::= 27652


    doChangeValue1-5	TRAP-TYPE
	ENTERPRISE	network-device
	VARIABLES	{ doValue, adminDateAndTime, adminNDTrapSeqNo,
			  doIndex, doType, doValue1String }
	DESCRIPTION	"This trap is generated when set
			 doChangeValue1TrapID equal 5 and
			the value of doValue change from 0 to 1."
	::= 27653


    doChangeValue1-6	TRAP-TYPE
	ENTERPRISE	network-device
	VARIABLES	{ doValue, adminDateAndTime, adminNDTrapSeqNo,
			  doIndex, doType, doValue1String }
	DESCRIPTION	"This trap is generated when set
			 doChangeValue1TrapID equal 6 and
			the value of doValue change from 0 to 1."
	::= 27654


    doChangeValue1-7	TRAP-TYPE
	ENTERPRISE	network-device
	VARIABLES	{ doValue, adminDateAndTime, adminNDTrapSeqNo,
			  doIndex, doType, doValue1String }
	DESCRIPTION	"This trap is generated when set
			 doChangeValue1TrapID equal 7 and
			the value of doValue change from 0 to 1."
	::= 27655


    doChangeValue1-8	TRAP-TYPE
	ENTERPRISE	network-device
	VARIABLES	{ doValue, adminDateAndTime, adminNDTrapSeqNo,
			  doIndex, doType, doValue1String }
	DESCRIPTION	"This trap is generated when set
			 doChangeValue1TrapID equal 8 and
			the value of doValue change from 0 to 1."
	::= 27656


    doChangeValue1-9	TRAP-TYPE
	ENTERPRISE	network-device
	VARIABLES	{ doValue, adminDateAndTime, adminNDTrapSeqNo,
			  doIndex, doType, doValue1String }
	DESCRIPTION	"This trap is generated when set
			 doChangeValue1TrapID equal 9 and
			the value of doValue change from 0 to 1."
	::= 27657


    doChangeValue1-10	TRAP-TYPE
	ENTERPRISE	network-device
	VARIABLES	{ doValue, adminDateAndTime, adminNDTrapSeqNo,
			  doIndex, doType, doValue1String }
	DESCRIPTION	"This trap is generated when set
			 doChangeValue1TrapID equal 10 and
			the value of doValue change from 0 to 1."
	::= 27658


    doChangeValue1-11	TRAP-TYPE
	ENTERPRISE	network-device
	VARIABLES	{ doValue, adminDateAndTime, adminNDTrapSeqNo,
			  doIndex, doType, doValue1String }
	DESCRIPTION	"This trap is generated when set
			 doChangeValue1TrapID equal 11 and
			the value of doValue change from 0 to 1."
	::= 27659


    doChangeValue1-12	TRAP-TYPE
	ENTERPRISE	network-device
	VARIABLES	{ doValue, adminDateAndTime, adminNDTrapSeqNo,
			  doIndex, doType, doValue1String }
	DESCRIPTION	"This trap is generated when set
			 doChangeValue1TrapID equal 12 and
			the value of doValue change from 0 to 1."
	::= 27660


    doChangeValue1-13	TRAP-TYPE
	ENTERPRISE	network-device
	VARIABLES	{ doValue, adminDateAndTime, adminNDTrapSeqNo,
			  doIndex, doType, doValue1String }
	DESCRIPTION	"This trap is generated when set
			 doChangeValue1TrapID equal 13 and
			the value of doValue change from 0 to 1."
	::= 27661


    doChangeValue1-14	TRAP-TYPE
	ENTERPRISE	network-device
	VARIABLES	{ doValue, adminDateAndTime, adminNDTrapSeqNo,
			  doIndex, doType, doValue1String }
	DESCRIPTION	"This trap is generated when set
			 doChangeValue1TrapID equal 14 and
			the value of doValue change from 0 to 1."
	::= 27662


    doChangeValue1-15	TRAP-TYPE
	ENTERPRISE	network-device
	VARIABLES	{ doValue, adminDateAndTime, adminNDTrapSeqNo,
			  doIndex, doType, doValue1String }
	DESCRIPTION	"This trap is generated when set
			 doChangeValue1TrapID equal 15 and
			the value of doValue change from 0 to 1."
	::= 27663


    doChangeValue1-16	TRAP-TYPE
	ENTERPRISE	network-device
	VARIABLES	{ doValue, adminDateAndTime, adminNDTrapSeqNo,
			  doIndex, doType, doValue1String }
	DESCRIPTION	"This trap is generated when set
			 doChangeValue1TrapID equal 16 and
			the value of doValue change from 0 to 1."
	::= 27664


    doChangeValue1-17	TRAP-TYPE
	ENTERPRISE	network-device
	VARIABLES	{ doValue, adminDateAndTime, adminNDTrapSeqNo,
			  doIndex, doType, doValue1String }
	DESCRIPTION	"This trap is generated when set
			 doChangeValue1TrapID equal 17 and
			the value of doValue change from 0 to 1."
	::= 27665


    doChangeValue1-18	TRAP-TYPE
	ENTERPRISE	network-device
	VARIABLES	{ doValue, adminDateAndTime, adminNDTrapSeqNo,
			  doIndex, doType, doValue1String }
	DESCRIPTION	"This trap is generated when set
			 doChangeValue1TrapID equal 18 and
			the value of doValue change from 0 to 1."
	::= 27666


    doChangeValue1-19	TRAP-TYPE
	ENTERPRISE	network-device
	VARIABLES	{ doValue, adminDateAndTime, adminNDTrapSeqNo,
			  doIndex, doType, doValue1String }
	DESCRIPTION	"This trap is generated when set
			 doChangeValue1TrapID equal 19 and
			the value of doValue change from 0 to 1."
	::= 27667


    doChangeValue1-20	TRAP-TYPE
	ENTERPRISE	network-device
	VARIABLES	{ doValue, adminDateAndTime, adminNDTrapSeqNo,
			  doIndex, doType, doValue1String }
	DESCRIPTION	"This trap is generated when set
			 doChangeValue1TrapID equal 20 and
			the value of doValue change from 0 to 1."
	::= 27668


    doChangeValue1-21	TRAP-TYPE
	ENTERPRISE	network-device
	VARIABLES	{ doValue, adminDateAndTime, adminNDTrapSeqNo,
			  doIndex, doType, doValue1String }
	DESCRIPTION	"This trap is generated when set
			 doChangeValue1TrapID equal 21 and
			the value of doValue change from 0 to 1."
	::= 27669


    doChangeValue1-22	TRAP-TYPE
	ENTERPRISE	network-device
	VARIABLES	{ doValue, adminDateAndTime, adminNDTrapSeqNo,
			  doIndex, doType, doValue1String }
	DESCRIPTION	"This trap is generated when set
			 doChangeValue1TrapID equal 22 and
			the value of doValue change from 0 to 1."
	::= 27670


    doChangeValue1-23	TRAP-TYPE
	ENTERPRISE	network-device
	VARIABLES	{ doValue, adminDateAndTime, adminNDTrapSeqNo,
			  doIndex, doType, doValue1String }
	DESCRIPTION	"This trap is generated when set
			 doChangeValue1TrapID equal 23 and
			the value of doValue change from 0 to 1."
	::= 27671


    doChangeValue1-24	TRAP-TYPE
	ENTERPRISE	network-device
	VARIABLES	{ doValue, adminDateAndTime, adminNDTrapSeqNo,
			  doIndex, doType, doValue1String }
	DESCRIPTION	"This trap is generated when set
			 doChangeValue1TrapID equal 24 and
			the value of doValue change from 0 to 1."
	::= 27672


    doChangeValue1-25	TRAP-TYPE
	ENTERPRISE	network-device
	VARIABLES	{ doValue, adminDateAndTime, adminNDTrapSeqNo,
			  doIndex, doType, doValue1String }
	DESCRIPTION	"This trap is generated when set
			 doChangeValue1TrapID equal 25 and
			the value of doValue change from 0 to 1."
	::= 27673


    doChangeValue1-26	TRAP-TYPE
	ENTERPRISE	network-device
	VARIABLES	{ doValue, adminDateAndTime, adminNDTrapSeqNo,
			  doIndex, doType, doValue1String }
	DESCRIPTION	"This trap is generated when set
			 doChangeValue1TrapID equal 26 and
			the value of doValue change from 0 to 1."
	::= 27674


    doChangeValue1-27	TRAP-TYPE
	ENTERPRISE	network-device
	VARIABLES	{ doValue, adminDateAndTime, adminNDTrapSeqNo,
			  doIndex, doType, doValue1String }
	DESCRIPTION	"This trap is generated when set
			 doChangeValue1TrapID equal 27 and
			the value of doValue change from 0 to 1."
	::= 27675


    doChangeValue1-28	TRAP-TYPE
	ENTERPRISE	network-device
	VARIABLES	{ doValue, adminDateAndTime, adminNDTrapSeqNo,
			  doIndex, doType, doValue1String }
	DESCRIPTION	"This trap is generated when set
			 doChangeValue1TrapID equal 28 and
			the value of doValue change from 0 to 1."
	::= 27676


    doChangeValue1-29	TRAP-TYPE
	ENTERPRISE	network-device
	VARIABLES	{ doValue, adminDateAndTime, adminNDTrapSeqNo,
			  doIndex, doType, doValue1String }
	DESCRIPTION	"This trap is generated when set
			 doChangeValue1TrapID equal 29 and
			the value of doValue change from 0 to 1."
	::= 27677


    doChangeValue1-30	TRAP-TYPE
	ENTERPRISE	network-device
	VARIABLES	{ doValue, adminDateAndTime, adminNDTrapSeqNo,
			  doIndex, doType, doValue1String }
	DESCRIPTION	"This trap is generated when set
			 doChangeValue1TrapID equal 30 and
			the value of doValue change from 0 to 1."
	::= 27678


    doChangeValue1-31	TRAP-TYPE
	ENTERPRISE	network-device
	VARIABLES	{ doValue, adminDateAndTime, adminNDTrapSeqNo,
			  doIndex, doType, doValue1String }
	DESCRIPTION	"This trap is generated when set
			 doChangeValue1TrapID equal 31 and
			the value of doValue change from 0 to 1."
	::= 27679


    doChangeValue1-32	TRAP-TYPE
	ENTERPRISE	network-device
	VARIABLES	{ doValue, adminDateAndTime, adminNDTrapSeqNo,
			  doIndex, doType, doValue1String }
	DESCRIPTION	"This trap is generated when set
			 doChangeValue1TrapID equal 32 and
			the value of doValue change from 0 to 1."
	::= 27680


    doChangeValue1-33	TRAP-TYPE
	ENTERPRISE	network-device
	VARIABLES	{ doValue, adminDateAndTime, adminNDTrapSeqNo,
			  doIndex, doType, doValue1String }
	DESCRIPTION	"This trap is generated when set
			 doChangeValue1TrapID equal 33 and
			the value of doValue change from 0 to 1."
	::= 27681


    doChangeValue1-34	TRAP-TYPE
	ENTERPRISE	network-device
	VARIABLES	{ doValue, adminDateAndTime, adminNDTrapSeqNo,
			  doIndex, doType, doValue1String }
	DESCRIPTION	"This trap is generated when set
			 doChangeValue1TrapID equal 34 and
			the value of doValue change from 0 to 1."
	::= 27682


    doChangeValue1-35	TRAP-TYPE
	ENTERPRISE	network-device
	VARIABLES	{ doValue, adminDateAndTime, adminNDTrapSeqNo,
			  doIndex, doType, doValue1String }
	DESCRIPTION	"This trap is generated when set
			 doChangeValue1TrapID equal 35 and
			the value of doValue change from 0 to 1."
	::= 27683


    doChangeValue1-36	TRAP-TYPE
	ENTERPRISE	network-device
	VARIABLES	{ doValue, adminDateAndTime, adminNDTrapSeqNo,
			  doIndex, doType, doValue1String }
	DESCRIPTION	"This trap is generated when set
			 doChangeValue1TrapID equal 36 and
			the value of doValue change from 0 to 1."
	::= 27684


    doChangeValue1-37	TRAP-TYPE
	ENTERPRISE	network-device
	VARIABLES	{ doValue, adminDateAndTime, adminNDTrapSeqNo,
			  doIndex, doType, doValue1String }
	DESCRIPTION	"This trap is generated when set
			 doChangeValue1TrapID equal 37 and
			the value of doValue change from 0 to 1."
	::= 27685


    doChangeValue1-38	TRAP-TYPE
	ENTERPRISE	network-device
	VARIABLES	{ doValue, adminDateAndTime, adminNDTrapSeqNo,
			  doIndex, doType, doValue1String }
	DESCRIPTION	"This trap is generated when set
			 doChangeValue1TrapID equal 38 and
			the value of doValue change from 0 to 1."
	::= 27686


    doChangeValue1-39	TRAP-TYPE
	ENTERPRISE	network-device
	VARIABLES	{ doValue, adminDateAndTime, adminNDTrapSeqNo,
			  doIndex, doType, doValue1String }
	DESCRIPTION	"This trap is generated when set
			 doChangeValue1TrapID equal 39 and
			the value of doValue change from 0 to 1."
	::= 27687


    doChangeValue1-40	TRAP-TYPE
	ENTERPRISE	network-device
	VARIABLES	{ doValue, adminDateAndTime, adminNDTrapSeqNo,
			  doIndex, doType, doValue1String }
	DESCRIPTION	"This trap is generated when set
			 doChangeValue1TrapID equal 40 and
			the value of doValue change from 0 to 1."
	::= 27688


    doChangeValue1-41	TRAP-TYPE
	ENTERPRISE	network-device
	VARIABLES	{ doValue, adminDateAndTime, adminNDTrapSeqNo,
			  doIndex, doType, doValue1String }
	DESCRIPTION	"This trap is generated when set
			 doChangeValue1TrapID equal 41 and
			the value of doValue change from 0 to 1."
	::= 27689


    doChangeValue1-42	TRAP-TYPE
	ENTERPRISE	network-device
	VARIABLES	{ doValue, adminDateAndTime, adminNDTrapSeqNo,
			  doIndex, doType, doValue1String }
	DESCRIPTION	"This trap is generated when set
			 doChangeValue1TrapID equal 42 and
			the value of doValue change from 0 to 1."
	::= 27690


    doChangeValue1-43	TRAP-TYPE
	ENTERPRISE	network-device
	VARIABLES	{ doValue, adminDateAndTime, adminNDTrapSeqNo,
			  doIndex, doType, doValue1String }
	DESCRIPTION	"This trap is generated when set
			 doChangeValue1TrapID equal 43 and
			the value of doValue change from 0 to 1."
	::= 27691


    doChangeValue1-44	TRAP-TYPE
	ENTERPRISE	network-device
	VARIABLES	{ doValue, adminDateAndTime, adminNDTrapSeqNo,
			  doIndex, doType, doValue1String }
	DESCRIPTION	"This trap is generated when set
			 doChangeValue1TrapID equal 44 and
			the value of doValue change from 0 to 1."
	::= 27692


    doChangeValue1-45	TRAP-TYPE
	ENTERPRISE	network-device
	VARIABLES	{ doValue, adminDateAndTime, adminNDTrapSeqNo,
			  doIndex, doType, doValue1String }
	DESCRIPTION	"This trap is generated when set
			 doChangeValue1TrapID equal 45 and
			the value of doValue change from 0 to 1."
	::= 27693


    doChangeValue1-46	TRAP-TYPE
	ENTERPRISE	network-device
	VARIABLES	{ doValue, adminDateAndTime, adminNDTrapSeqNo,
			  doIndex, doType, doValue1String }
	DESCRIPTION	"This trap is generated when set
			 doChangeValue1TrapID equal 46 and
			the value of doValue change from 0 to 1."
	::= 27694


    doChangeValue1-47	TRAP-TYPE
	ENTERPRISE	network-device
	VARIABLES	{ doValue, adminDateAndTime, adminNDTrapSeqNo,
			  doIndex, doType, doValue1String }
	DESCRIPTION	"This trap is generated when set
			 doChangeValue1TrapID equal 47 and
			the value of doValue change from 0 to 1."
	::= 27695


    doChangeValue1-48	TRAP-TYPE
	ENTERPRISE	network-device
	VARIABLES	{ doValue, adminDateAndTime, adminNDTrapSeqNo,
			  doIndex, doType, doValue1String }
	DESCRIPTION	"This trap is generated when set
			 doChangeValue1TrapID equal 48 and
			the value of doValue change from 0 to 1."
	::= 27696


    doChangeValue1-49	TRAP-TYPE
	ENTERPRISE	network-device
	VARIABLES	{ doValue, adminDateAndTime, adminNDTrapSeqNo,
			  doIndex, doType, doValue1String }
	DESCRIPTION	"This trap is generated when set
			 doChangeValue1TrapID equal 49 and
			the value of doValue change from 0 to 1."
	::= 27697


    doChangeValue1-50	TRAP-TYPE
	ENTERPRISE	network-device
	VARIABLES	{ doValue, adminDateAndTime, adminNDTrapSeqNo,
			  doIndex, doType, doValue1String }
	DESCRIPTION	"This trap is generated when set
			 doChangeValue1TrapID equal 50 and
			the value of doValue change from 0 to 1."
	::= 27698


    doChangeValue1-51	TRAP-TYPE
	ENTERPRISE	network-device
	VARIABLES	{ doValue, adminDateAndTime, adminNDTrapSeqNo,
			  doIndex, doType, doValue1String }
	DESCRIPTION	"This trap is generated when set
			 doChangeValue1TrapID equal 51 and
			the value of doValue change from 0 to 1."
	::= 27699


    doChangeValue1-52	TRAP-TYPE
	ENTERPRISE	network-device
	VARIABLES	{ doValue, adminDateAndTime, adminNDTrapSeqNo,
			  doIndex, doType, doValue1String }
	DESCRIPTION	"This trap is generated when set
			 doChangeValue1TrapID equal 52 and
			the value of doValue change from 0 to 1."
	::= 27700


    doChangeValue1-53	TRAP-TYPE
	ENTERPRISE	network-device
	VARIABLES	{ doValue, adminDateAndTime, adminNDTrapSeqNo,
			  doIndex, doType, doValue1String }
	DESCRIPTION	"This trap is generated when set
			 doChangeValue1TrapID equal 53 and
			the value of doValue change from 0 to 1."
	::= 27701


    doChangeValue1-54	TRAP-TYPE
	ENTERPRISE	network-device
	VARIABLES	{ doValue, adminDateAndTime, adminNDTrapSeqNo,
			  doIndex, doType, doValue1String }
	DESCRIPTION	"This trap is generated when set
			 doChangeValue1TrapID equal 54 and
			the value of doValue change from 0 to 1."
	::= 27702


    doChangeValue1-55	TRAP-TYPE
	ENTERPRISE	network-device
	VARIABLES	{ doValue, adminDateAndTime, adminNDTrapSeqNo,
			  doIndex, doType, doValue1String }
	DESCRIPTION	"This trap is generated when set
			 doChangeValue1TrapID equal 55 and
			the value of doValue change from 0 to 1."
	::= 27703


    doChangeValue1-56	TRAP-TYPE
	ENTERPRISE	network-device
	VARIABLES	{ doValue, adminDateAndTime, adminNDTrapSeqNo,
			  doIndex, doType, doValue1String }
	DESCRIPTION	"This trap is generated when set
			 doChangeValue1TrapID equal 56 and
			the value of doValue change from 0 to 1."
	::= 27704


    doChangeValue1-57	TRAP-TYPE
	ENTERPRISE	network-device
	VARIABLES	{ doValue, adminDateAndTime, adminNDTrapSeqNo,
			  doIndex, doType, doValue1String }
	DESCRIPTION	"This trap is generated when set
			 doChangeValue1TrapID equal 57 and
			the value of doValue change from 0 to 1."
	::= 27705


    doChangeValue1-58	TRAP-TYPE
	ENTERPRISE	network-device
	VARIABLES	{ doValue, adminDateAndTime, adminNDTrapSeqNo,
			  doIndex, doType, doValue1String }
	DESCRIPTION	"This trap is generated when set
			 doChangeValue1TrapID equal 58 and
			the value of doValue change from 0 to 1."
	::= 27706


    doChangeValue1-59	TRAP-TYPE
	ENTERPRISE	network-device
	VARIABLES	{ doValue, adminDateAndTime, adminNDTrapSeqNo,
			  doIndex, doType, doValue1String }
	DESCRIPTION	"This trap is generated when set
			 doChangeValue1TrapID equal 59 and
			the value of doValue change from 0 to 1."
	::= 27707


    doChangeValue1-60	TRAP-TYPE
	ENTERPRISE	network-device
	VARIABLES	{ doValue, adminDateAndTime, adminNDTrapSeqNo,
			  doIndex, doType, doValue1String }
	DESCRIPTION	"This trap is generated when set
			 doChangeValue1TrapID equal 60 and
			the value of doValue change from 0 to 1."
	::= 27708


    doChangeValue1-61	TRAP-TYPE
	ENTERPRISE	network-device
	VARIABLES	{ doValue, adminDateAndTime, adminNDTrapSeqNo,
			  doIndex, doType, doValue1String }
	DESCRIPTION	"This trap is generated when set
			 doChangeValue1TrapID equal 61 and
			the value of doValue change from 0 to 1."
	::= 27709


    doChangeValue1-62	TRAP-TYPE
	ENTERPRISE	network-device
	VARIABLES	{ doValue, adminDateAndTime, adminNDTrapSeqNo,
			  doIndex, doType, doValue1String }
	DESCRIPTION	"This trap is generated when set
			 doChangeValue1TrapID equal 62 and
			the value of doValue change from 0 to 1."
	::= 27710


    doChangeValue1-63	TRAP-TYPE
	ENTERPRISE	network-device
	VARIABLES	{ doValue, adminDateAndTime, adminNDTrapSeqNo,
			  doIndex, doType, doValue1String }
	DESCRIPTION	"This trap is generated when set
			 doChangeValue1TrapID equal 63 and
			the value of doValue change from 0 to 1."
	::= 27711


    doChangeValue1-64	TRAP-TYPE
	ENTERPRISE	network-device
	VARIABLES	{ doValue, adminDateAndTime, adminNDTrapSeqNo,
			  doIndex, doType, doValue1String }
	DESCRIPTION	"This trap is generated when set
			 doChangeValue1TrapID equal 64 and
			the value of doValue change from 0 to 1."
	::= 27712


    doChangeValue1-65	TRAP-TYPE
	ENTERPRISE	network-device
	VARIABLES	{ doValue, adminDateAndTime, adminNDTrapSeqNo,
			  doIndex, doType, doValue1String }
	DESCRIPTION	"This trap is generated when set
			 doChangeValue1TrapID equal 65 and
			the value of doValue change from 0 to 1."
	::= 27713


    doChangeValue1-66	TRAP-TYPE
	ENTERPRISE	network-device
	VARIABLES	{ doValue, adminDateAndTime, adminNDTrapSeqNo,
			  doIndex, doType, doValue1String }
	DESCRIPTION	"This trap is generated when set
			 doChangeValue1TrapID equal 66 and
			the value of doValue change from 0 to 1."
	::= 27714


    doChangeValue1-67	TRAP-TYPE
	ENTERPRISE	network-device
	VARIABLES	{ doValue, adminDateAndTime, adminNDTrapSeqNo,
			  doIndex, doType, doValue1String }
	DESCRIPTION	"This trap is generated when set
			 doChangeValue1TrapID equal 67 and
			the value of doValue change from 0 to 1."
	::= 27715


    doChangeValue1-68	TRAP-TYPE
	ENTERPRISE	network-device
	VARIABLES	{ doValue, adminDateAndTime, adminNDTrapSeqNo,
			  doIndex, doType, doValue1String }
	DESCRIPTION	"This trap is generated when set
			 doChangeValue1TrapID equal 68 and
			the value of doValue change from 0 to 1."
	::= 27716


    doChangeValue1-69	TRAP-TYPE
	ENTERPRISE	network-device
	VARIABLES	{ doValue, adminDateAndTime, adminNDTrapSeqNo,
			  doIndex, doType, doValue1String }
	DESCRIPTION	"This trap is generated when set
			 doChangeValue1TrapID equal 69 and
			the value of doValue change from 0 to 1."
	::= 27717


    doChangeValue1-70	TRAP-TYPE
	ENTERPRISE	network-device
	VARIABLES	{ doValue, adminDateAndTime, adminNDTrapSeqNo,
			  doIndex, doType, doValue1String }
	DESCRIPTION	"This trap is generated when set
			 doChangeValue1TrapID equal 70 and
			the value of doValue change from 0 to 1."
	::= 27718


    doChangeValue1-71	TRAP-TYPE
	ENTERPRISE	network-device
	VARIABLES	{ doValue, adminDateAndTime, adminNDTrapSeqNo,
			  doIndex, doType, doValue1String }
	DESCRIPTION	"This trap is generated when set
			 doChangeValue1TrapID equal 71 and
			the value of doValue change from 0 to 1."
	::= 27719


    doChangeValue1-72	TRAP-TYPE
	ENTERPRISE	network-device
	VARIABLES	{ doValue, adminDateAndTime, adminNDTrapSeqNo,
			  doIndex, doType, doValue1String }
	DESCRIPTION	"This trap is generated when set
			 doChangeValue1TrapID equal 72 and
			the value of doValue change from 0 to 1."
	::= 27720


    doChangeValue1-73	TRAP-TYPE
	ENTERPRISE	network-device
	VARIABLES	{ doValue, adminDateAndTime, adminNDTrapSeqNo,
			  doIndex, doType, doValue1String }
	DESCRIPTION	"This trap is generated when set
			 doChangeValue1TrapID equal 73 and
			the value of doValue change from 0 to 1."
	::= 27721


    doChangeValue1-74	TRAP-TYPE
	ENTERPRISE	network-device
	VARIABLES	{ doValue, adminDateAndTime, adminNDTrapSeqNo,
			  doIndex, doType, doValue1String }
	DESCRIPTION	"This trap is generated when set
			 doChangeValue1TrapID equal 74 and
			the value of doValue change from 0 to 1."
	::= 27722


    doChangeValue1-75	TRAP-TYPE
	ENTERPRISE	network-device
	VARIABLES	{ doValue, adminDateAndTime, adminNDTrapSeqNo,
			  doIndex, doType, doValue1String }
	DESCRIPTION	"This trap is generated when set
			 doChangeValue1TrapID equal 75 and
			the value of doValue change from 0 to 1."
	::= 27723


    doChangeValue1-76	TRAP-TYPE
	ENTERPRISE	network-device
	VARIABLES	{ doValue, adminDateAndTime, adminNDTrapSeqNo,
			  doIndex, doType, doValue1String }
	DESCRIPTION	"This trap is generated when set
			 doChangeValue1TrapID equal 76 and
			the value of doValue change from 0 to 1."
	::= 27724


    doChangeValue1-77	TRAP-TYPE
	ENTERPRISE	network-device
	VARIABLES	{ doValue, adminDateAndTime, adminNDTrapSeqNo,
			  doIndex, doType, doValue1String }
	DESCRIPTION	"This trap is generated when set
			 doChangeValue1TrapID equal 77 and
			the value of doValue change from 0 to 1."
	::= 27725


    doChangeValue1-78	TRAP-TYPE
	ENTERPRISE	network-device
	VARIABLES	{ doValue, adminDateAndTime, adminNDTrapSeqNo,
			  doIndex, doType, doValue1String }
	DESCRIPTION	"This trap is generated when set
			 doChangeValue1TrapID equal 78 and
			the value of doValue change from 0 to 1."
	::= 27726


    doChangeValue1-79	TRAP-TYPE
	ENTERPRISE	network-device
	VARIABLES	{ doValue, adminDateAndTime, adminNDTrapSeqNo,
			  doIndex, doType, doValue1String }
	DESCRIPTION	"This trap is generated when set
			 doChangeValue1TrapID equal 79 and
			the value of doValue change from 0 to 1."
	::= 27727


    doChangeValue1-80	TRAP-TYPE
	ENTERPRISE	network-device
	VARIABLES	{ doValue, adminDateAndTime, adminNDTrapSeqNo,
			  doIndex, doType, doValue1String }
	DESCRIPTION	"This trap is generated when set
			 doChangeValue1TrapID equal 80 and
			the value of doValue change from 0 to 1."
	::= 27728


    doChangeValue1-81	TRAP-TYPE
	ENTERPRISE	network-device
	VARIABLES	{ doValue, adminDateAndTime, adminNDTrapSeqNo,
			  doIndex, doType, doValue1String }
	DESCRIPTION	"This trap is generated when set
			 doChangeValue1TrapID equal 81 and
			the value of doValue change from 0 to 1."
	::= 27729


    doChangeValue1-82	TRAP-TYPE
	ENTERPRISE	network-device
	VARIABLES	{ doValue, adminDateAndTime, adminNDTrapSeqNo,
			  doIndex, doType, doValue1String }
	DESCRIPTION	"This trap is generated when set
			 doChangeValue1TrapID equal 82 and
			the value of doValue change from 0 to 1."
	::= 27730


    doChangeValue1-83	TRAP-TYPE
	ENTERPRISE	network-device
	VARIABLES	{ doValue, adminDateAndTime, adminNDTrapSeqNo,
			  doIndex, doType, doValue1String }
	DESCRIPTION	"This trap is generated when set
			 doChangeValue1TrapID equal 83 and
			the value of doValue change from 0 to 1."
	::= 27731


    doChangeValue1-84	TRAP-TYPE
	ENTERPRISE	network-device
	VARIABLES	{ doValue, adminDateAndTime, adminNDTrapSeqNo,
			  doIndex, doType, doValue1String }
	DESCRIPTION	"This trap is generated when set
			 doChangeValue1TrapID equal 84 and
			the value of doValue change from 0 to 1."
	::= 27732


    doChangeValue1-85	TRAP-TYPE
	ENTERPRISE	network-device
	VARIABLES	{ doValue, adminDateAndTime, adminNDTrapSeqNo,
			  doIndex, doType, doValue1String }
	DESCRIPTION	"This trap is generated when set
			 doChangeValue1TrapID equal 85 and
			the value of doValue change from 0 to 1."
	::= 27733


    doChangeValue1-86	TRAP-TYPE
	ENTERPRISE	network-device
	VARIABLES	{ doValue, adminDateAndTime, adminNDTrapSeqNo,
			  doIndex, doType, doValue1String }
	DESCRIPTION	"This trap is generated when set
			 doChangeValue1TrapID equal 86 and
			the value of doValue change from 0 to 1."
	::= 27734


    doChangeValue1-87	TRAP-TYPE
	ENTERPRISE	network-device
	VARIABLES	{ doValue, adminDateAndTime, adminNDTrapSeqNo,
			  doIndex, doType, doValue1String }
	DESCRIPTION	"This trap is generated when set
			 doChangeValue1TrapID equal 87 and
			the value of doValue change from 0 to 1."
	::= 27735


    doChangeValue1-88	TRAP-TYPE
	ENTERPRISE	network-device
	VARIABLES	{ doValue, adminDateAndTime, adminNDTrapSeqNo,
			  doIndex, doType, doValue1String }
	DESCRIPTION	"This trap is generated when set
			 doChangeValue1TrapID equal 88 and
			the value of doValue change from 0 to 1."
	::= 27736


    doChangeValue1-89	TRAP-TYPE
	ENTERPRISE	network-device
	VARIABLES	{ doValue, adminDateAndTime, adminNDTrapSeqNo,
			  doIndex, doType, doValue1String }
	DESCRIPTION	"This trap is generated when set
			 doChangeValue1TrapID equal 89 and
			the value of doValue change from 0 to 1."
	::= 27737


    doChangeValue1-90	TRAP-TYPE
	ENTERPRISE	network-device
	VARIABLES	{ doValue, adminDateAndTime, adminNDTrapSeqNo,
			  doIndex, doType, doValue1String }
	DESCRIPTION	"This trap is generated when set
			 doChangeValue1TrapID equal 90 and
			the value of doValue change from 0 to 1."
	::= 27738


    doChangeValue1-91	TRAP-TYPE
	ENTERPRISE	network-device
	VARIABLES	{ doValue, adminDateAndTime, adminNDTrapSeqNo,
			  doIndex, doType, doValue1String }
	DESCRIPTION	"This trap is generated when set
			 doChangeValue1TrapID equal 91 and
			the value of doValue change from 0 to 1."
	::= 27739


    doChangeValue1-92	TRAP-TYPE
	ENTERPRISE	network-device
	VARIABLES	{ doValue, adminDateAndTime, adminNDTrapSeqNo,
			  doIndex, doType, doValue1String }
	DESCRIPTION	"This trap is generated when set
			 doChangeValue1TrapID equal 92 and
			the value of doValue change from 0 to 1."
	::= 27740


    doChangeValue1-93	TRAP-TYPE
	ENTERPRISE	network-device
	VARIABLES	{ doValue, adminDateAndTime, adminNDTrapSeqNo,
			  doIndex, doType, doValue1String }
	DESCRIPTION	"This trap is generated when set
			 doChangeValue1TrapID equal 93 and
			the value of doValue change from 0 to 1."
	::= 27741


    doChangeValue1-94	TRAP-TYPE
	ENTERPRISE	network-device
	VARIABLES	{ doValue, adminDateAndTime, adminNDTrapSeqNo,
			  doIndex, doType, doValue1String }
	DESCRIPTION	"This trap is generated when set
			 doChangeValue1TrapID equal 94 and
			the value of doValue change from 0 to 1."
	::= 27742


    doChangeValue1-95	TRAP-TYPE
	ENTERPRISE	network-device
	VARIABLES	{ doValue, adminDateAndTime, adminNDTrapSeqNo,
			  doIndex, doType, doValue1String }
	DESCRIPTION	"This trap is generated when set
			 doChangeValue1TrapID equal 95 and
			the value of doValue change from 0 to 1."
	::= 27743


    doChangeValue1-96	TRAP-TYPE
	ENTERPRISE	network-device
	VARIABLES	{ doValue, adminDateAndTime, adminNDTrapSeqNo,
			  doIndex, doType, doValue1String }
	DESCRIPTION	"This trap is generated when set
			 doChangeValue1TrapID equal 96 and
			the value of doValue change from 0 to 1."
	::= 27744


    doChangeValue1-97	TRAP-TYPE
	ENTERPRISE	network-device
	VARIABLES	{ doValue, adminDateAndTime, adminNDTrapSeqNo,
			  doIndex, doType, doValue1String }
	DESCRIPTION	"This trap is generated when set
			 doChangeValue1TrapID equal 97 and
			the value of doValue change from 0 to 1."
	::= 27745


    doChangeValue1-98	TRAP-TYPE
	ENTERPRISE	network-device
	VARIABLES	{ doValue, adminDateAndTime, adminNDTrapSeqNo,
			  doIndex, doType, doValue1String }
	DESCRIPTION	"This trap is generated when set
			 doChangeValue1TrapID equal 98 and
			the value of doValue change from 0 to 1."
	::= 27746


    doChangeValue1-99	TRAP-TYPE
	ENTERPRISE	network-device
	VARIABLES	{ doValue, adminDateAndTime, adminNDTrapSeqNo,
			  doIndex, doType, doValue1String }
	DESCRIPTION	"This trap is generated when set
			 doChangeValue1TrapID equal 99 and
			the value of doValue change from 0 to 1."
	::= 27747


    doChangeValue1-100	TRAP-TYPE
	ENTERPRISE	network-device
	VARIABLES	{ doValue, adminDateAndTime, adminNDTrapSeqNo,
			  doIndex, doType, doValue1String }
	DESCRIPTION	"This trap is generated when set
			 doChangeValue1TrapID equal 100 and
			the value of doValue change from 0 to 1."
	::= 27748


    doChangeValue1-101	TRAP-TYPE
	ENTERPRISE	network-device
	VARIABLES	{ doValue, adminDateAndTime, adminNDTrapSeqNo,
			  doIndex, doType, doValue1String }
	DESCRIPTION	"This trap is generated when set
			 doChangeValue1TrapID equal 101 and
			the value of doValue change from 0 to 1."
	::= 27749


    doChangeValue1-102	TRAP-TYPE
	ENTERPRISE	network-device
	VARIABLES	{ doValue, adminDateAndTime, adminNDTrapSeqNo,
			  doIndex, doType, doValue1String }
	DESCRIPTION	"This trap is generated when set
			 doChangeValue1TrapID equal 102 and
			the value of doValue change from 0 to 1."
	::= 27750


    doChangeValue1-103	TRAP-TYPE
	ENTERPRISE	network-device
	VARIABLES	{ doValue, adminDateAndTime, adminNDTrapSeqNo,
			  doIndex, doType, doValue1String }
	DESCRIPTION	"This trap is generated when set
			 doChangeValue1TrapID equal 103 and
			the value of doValue change from 0 to 1."
	::= 27751


    doChangeValue1-104	TRAP-TYPE
	ENTERPRISE	network-device
	VARIABLES	{ doValue, adminDateAndTime, adminNDTrapSeqNo,
			  doIndex, doType, doValue1String }
	DESCRIPTION	"This trap is generated when set
			 doChangeValue1TrapID equal 104 and
			the value of doValue change from 0 to 1."
	::= 27752


    doChangeValue1-105	TRAP-TYPE
	ENTERPRISE	network-device
	VARIABLES	{ doValue, adminDateAndTime, adminNDTrapSeqNo,
			  doIndex, doType, doValue1String }
	DESCRIPTION	"This trap is generated when set
			 doChangeValue1TrapID equal 105 and
			the value of doValue change from 0 to 1."
	::= 27753


    doChangeValue1-106	TRAP-TYPE
	ENTERPRISE	network-device
	VARIABLES	{ doValue, adminDateAndTime, adminNDTrapSeqNo,
			  doIndex, doType, doValue1String }
	DESCRIPTION	"This trap is generated when set
			 doChangeValue1TrapID equal 106 and
			the value of doValue change from 0 to 1."
	::= 27754


    doChangeValue1-107	TRAP-TYPE
	ENTERPRISE	network-device
	VARIABLES	{ doValue, adminDateAndTime, adminNDTrapSeqNo,
			  doIndex, doType, doValue1String }
	DESCRIPTION	"This trap is generated when set
			 doChangeValue1TrapID equal 107 and
			the value of doValue change from 0 to 1."
	::= 27755


    doChangeValue1-108	TRAP-TYPE
	ENTERPRISE	network-device
	VARIABLES	{ doValue, adminDateAndTime, adminNDTrapSeqNo,
			  doIndex, doType, doValue1String }
	DESCRIPTION	"This trap is generated when set
			 doChangeValue1TrapID equal 108 and
			the value of doValue change from 0 to 1."
	::= 27756


    doChangeValue1-109	TRAP-TYPE
	ENTERPRISE	network-device
	VARIABLES	{ doValue, adminDateAndTime, adminNDTrapSeqNo,
			  doIndex, doType, doValue1String }
	DESCRIPTION	"This trap is generated when set
			 doChangeValue1TrapID equal 109 and
			the value of doValue change from 0 to 1."
	::= 27757


    doChangeValue1-110	TRAP-TYPE
	ENTERPRISE	network-device
	VARIABLES	{ doValue, adminDateAndTime, adminNDTrapSeqNo,
			  doIndex, doType, doValue1String }
	DESCRIPTION	"This trap is generated when set
			 doChangeValue1TrapID equal 110 and
			the value of doValue change from 0 to 1."
	::= 27758


    doChangeValue1-111	TRAP-TYPE
	ENTERPRISE	network-device
	VARIABLES	{ doValue, adminDateAndTime, adminNDTrapSeqNo,
			  doIndex, doType, doValue1String }
	DESCRIPTION	"This trap is generated when set
			 doChangeValue1TrapID equal 111 and
			the value of doValue change from 0 to 1."
	::= 27759


    doChangeValue1-112	TRAP-TYPE
	ENTERPRISE	network-device
	VARIABLES	{ doValue, adminDateAndTime, adminNDTrapSeqNo,
			  doIndex, doType, doValue1String }
	DESCRIPTION	"This trap is generated when set
			 doChangeValue1TrapID equal 112 and
			the value of doValue change from 0 to 1."
	::= 27760


    doChangeValue1-113	TRAP-TYPE
	ENTERPRISE	network-device
	VARIABLES	{ doValue, adminDateAndTime, adminNDTrapSeqNo,
			  doIndex, doType, doValue1String }
	DESCRIPTION	"This trap is generated when set
			 doChangeValue1TrapID equal 113 and
			the value of doValue change from 0 to 1."
	::= 27761


    doChangeValue1-114	TRAP-TYPE
	ENTERPRISE	network-device
	VARIABLES	{ doValue, adminDateAndTime, adminNDTrapSeqNo,
			  doIndex, doType, doValue1String }
	DESCRIPTION	"This trap is generated when set
			 doChangeValue1TrapID equal 114 and
			the value of doValue change from 0 to 1."
	::= 27762


    doChangeValue1-115	TRAP-TYPE
	ENTERPRISE	network-device
	VARIABLES	{ doValue, adminDateAndTime, adminNDTrapSeqNo,
			  doIndex, doType, doValue1String }
	DESCRIPTION	"This trap is generated when set
			 doChangeValue1TrapID equal 115 and
			the value of doValue change from 0 to 1."
	::= 27763


    doChangeValue1-116	TRAP-TYPE
	ENTERPRISE	network-device
	VARIABLES	{ doValue, adminDateAndTime, adminNDTrapSeqNo,
			  doIndex, doType, doValue1String }
	DESCRIPTION	"This trap is generated when set
			 doChangeValue1TrapID equal 116 and
			the value of doValue change from 0 to 1."
	::= 27764


    doChangeValue1-117	TRAP-TYPE
	ENTERPRISE	network-device
	VARIABLES	{ doValue, adminDateAndTime, adminNDTrapSeqNo,
			  doIndex, doType, doValue1String }
	DESCRIPTION	"This trap is generated when set
			 doChangeValue1TrapID equal 117 and
			the value of doValue change from 0 to 1."
	::= 27765


    doChangeValue1-118	TRAP-TYPE
	ENTERPRISE	network-device
	VARIABLES	{ doValue, adminDateAndTime, adminNDTrapSeqNo,
			  doIndex, doType, doValue1String }
	DESCRIPTION	"This trap is generated when set
			 doChangeValue1TrapID equal 118 and
			the value of doValue change from 0 to 1."
	::= 27766


    doChangeValue1-119	TRAP-TYPE
	ENTERPRISE	network-device
	VARIABLES	{ doValue, adminDateAndTime, adminNDTrapSeqNo,
			  doIndex, doType, doValue1String }
	DESCRIPTION	"This trap is generated when set
			 doChangeValue1TrapID equal 119 and
			the value of doValue change from 0 to 1."
	::= 27767


    doChangeValue1-120	TRAP-TYPE
	ENTERPRISE	network-device
	VARIABLES	{ doValue, adminDateAndTime, adminNDTrapSeqNo,
			  doIndex, doType, doValue1String }
	DESCRIPTION	"This trap is generated when set
			 doChangeValue1TrapID equal 120 and
			the value of doValue change from 0 to 1."
	::= 27768


    doChangeValue1-121	TRAP-TYPE
	ENTERPRISE	network-device
	VARIABLES	{ doValue, adminDateAndTime, adminNDTrapSeqNo,
			  doIndex, doType, doValue1String }
	DESCRIPTION	"This trap is generated when set
			 doChangeValue1TrapID equal 121 and
			the value of doValue change from 0 to 1."
	::= 27769


    doChangeValue1-122	TRAP-TYPE
	ENTERPRISE	network-device
	VARIABLES	{ doValue, adminDateAndTime, adminNDTrapSeqNo,
			  doIndex, doType, doValue1String }
	DESCRIPTION	"This trap is generated when set
			 doChangeValue1TrapID equal 122 and
			the value of doValue change from 0 to 1."
	::= 27770


    doChangeValue1-123	TRAP-TYPE
	ENTERPRISE	network-device
	VARIABLES	{ doValue, adminDateAndTime, adminNDTrapSeqNo,
			  doIndex, doType, doValue1String }
	DESCRIPTION	"This trap is generated when set
			 doChangeValue1TrapID equal 123 and
			the value of doValue change from 0 to 1."
	::= 27771


    doChangeValue1-124	TRAP-TYPE
	ENTERPRISE	network-device
	VARIABLES	{ doValue, adminDateAndTime, adminNDTrapSeqNo,
			  doIndex, doType, doValue1String }
	DESCRIPTION	"This trap is generated when set
			 doChangeValue1TrapID equal 124 and
			the value of doValue change from 0 to 1."
	::= 27772


    doChangeValue1-125	TRAP-TYPE
	ENTERPRISE	network-device
	VARIABLES	{ doValue, adminDateAndTime, adminNDTrapSeqNo,
			  doIndex, doType, doValue1String }
	DESCRIPTION	"This trap is generated when set
			 doChangeValue1TrapID equal 125 and
			the value of doValue change from 0 to 1."
	::= 27773


    doChangeValue1-126	TRAP-TYPE
	ENTERPRISE	network-device
	VARIABLES	{ doValue, adminDateAndTime, adminNDTrapSeqNo,
			  doIndex, doType, doValue1String }
	DESCRIPTION	"This trap is generated when set
			 doChangeValue1TrapID equal 126 and
			the value of doValue change from 0 to 1."
	::= 27774


    doChangeValue1-127	TRAP-TYPE
	ENTERPRISE	network-device
	VARIABLES	{ doValue, adminDateAndTime, adminNDTrapSeqNo,
			  doIndex, doType, doValue1String }
	DESCRIPTION	"This trap is generated when set
			 doChangeValue1TrapID equal 127 and
			the value of doValue change from 0 to 1."
	::= 27775


    doValue1-1	TRAP-TYPE
	ENTERPRISE	network-device
	VARIABLES	{ doValue, adminDateAndTime, adminNDTrapSeqNo,
			  doIndex, doType, doValue1String }
	DESCRIPTION	"This trap is generated when set
			 doValue1TrapID equal 1 and
			while the value of doValue is 1."
	::= 28161


    doValue1-2	TRAP-TYPE
	ENTERPRISE	network-device
	VARIABLES	{ doValue, adminDateAndTime, adminNDTrapSeqNo,
			  doIndex, doType, doValue1String }
	DESCRIPTION	"This trap is generated when set
			 doValue1TrapID equal 2 and
			while the value of doValue is 1."
	::= 28162


    doValue1-3	TRAP-TYPE
	ENTERPRISE	network-device
	VARIABLES	{ doValue, adminDateAndTime, adminNDTrapSeqNo,
			  doIndex, doType, doValue1String }
	DESCRIPTION	"This trap is generated when set
			 doValue1TrapID equal 3 and
			while the value of doValue is 1."
	::= 28163


    doValue1-4	TRAP-TYPE
	ENTERPRISE	network-device
	VARIABLES	{ doValue, adminDateAndTime, adminNDTrapSeqNo,
			  doIndex, doType, doValue1String }
	DESCRIPTION	"This trap is generated when set
			 doValue1TrapID equal 4 and
			while the value of doValue is 1."
	::= 28164


    doValue1-5	TRAP-TYPE
	ENTERPRISE	network-device
	VARIABLES	{ doValue, adminDateAndTime, adminNDTrapSeqNo,
			  doIndex, doType, doValue1String }
	DESCRIPTION	"This trap is generated when set
			 doValue1TrapID equal 5 and
			while the value of doValue is 1."
	::= 28165


    doValue1-6	TRAP-TYPE
	ENTERPRISE	network-device
	VARIABLES	{ doValue, adminDateAndTime, adminNDTrapSeqNo,
			  doIndex, doType, doValue1String }
	DESCRIPTION	"This trap is generated when set
			 doValue1TrapID equal 6 and
			while the value of doValue is 1."
	::= 28166


    doValue1-7	TRAP-TYPE
	ENTERPRISE	network-device
	VARIABLES	{ doValue, adminDateAndTime, adminNDTrapSeqNo,
			  doIndex, doType, doValue1String }
	DESCRIPTION	"This trap is generated when set
			 doValue1TrapID equal 7 and
			while the value of doValue is 1."
	::= 28167


    doValue1-8	TRAP-TYPE
	ENTERPRISE	network-device
	VARIABLES	{ doValue, adminDateAndTime, adminNDTrapSeqNo,
			  doIndex, doType, doValue1String }
	DESCRIPTION	"This trap is generated when set
			 doValue1TrapID equal 8 and
			while the value of doValue is 1."
	::= 28168


    doValue1-9	TRAP-TYPE
	ENTERPRISE	network-device
	VARIABLES	{ doValue, adminDateAndTime, adminNDTrapSeqNo,
			  doIndex, doType, doValue1String }
	DESCRIPTION	"This trap is generated when set
			 doValue1TrapID equal 9 and
			while the value of doValue is 1."
	::= 28169


    doValue1-10	TRAP-TYPE
	ENTERPRISE	network-device
	VARIABLES	{ doValue, adminDateAndTime, adminNDTrapSeqNo,
			  doIndex, doType, doValue1String }
	DESCRIPTION	"This trap is generated when set
			 doValue1TrapID equal 10 and
			while the value of doValue is 1."
	::= 28170


    doValue1-11	TRAP-TYPE
	ENTERPRISE	network-device
	VARIABLES	{ doValue, adminDateAndTime, adminNDTrapSeqNo,
			  doIndex, doType, doValue1String }
	DESCRIPTION	"This trap is generated when set
			 doValue1TrapID equal 11 and
			while the value of doValue is 1."
	::= 28171


    doValue1-12	TRAP-TYPE
	ENTERPRISE	network-device
	VARIABLES	{ doValue, adminDateAndTime, adminNDTrapSeqNo,
			  doIndex, doType, doValue1String }
	DESCRIPTION	"This trap is generated when set
			 doValue1TrapID equal 12 and
			while the value of doValue is 1."
	::= 28172


    doValue1-13	TRAP-TYPE
	ENTERPRISE	network-device
	VARIABLES	{ doValue, adminDateAndTime, adminNDTrapSeqNo,
			  doIndex, doType, doValue1String }
	DESCRIPTION	"This trap is generated when set
			 doValue1TrapID equal 13 and
			while the value of doValue is 1."
	::= 28173


    doValue1-14	TRAP-TYPE
	ENTERPRISE	network-device
	VARIABLES	{ doValue, adminDateAndTime, adminNDTrapSeqNo,
			  doIndex, doType, doValue1String }
	DESCRIPTION	"This trap is generated when set
			 doValue1TrapID equal 14 and
			while the value of doValue is 1."
	::= 28174


    doValue1-15	TRAP-TYPE
	ENTERPRISE	network-device
	VARIABLES	{ doValue, adminDateAndTime, adminNDTrapSeqNo,
			  doIndex, doType, doValue1String }
	DESCRIPTION	"This trap is generated when set
			 doValue1TrapID equal 15 and
			while the value of doValue is 1."
	::= 28175


    doValue1-16	TRAP-TYPE
	ENTERPRISE	network-device
	VARIABLES	{ doValue, adminDateAndTime, adminNDTrapSeqNo,
			  doIndex, doType, doValue1String }
	DESCRIPTION	"This trap is generated when set
			 doValue1TrapID equal 16 and
			while the value of doValue is 1."
	::= 28176


    doValue1-17	TRAP-TYPE
	ENTERPRISE	network-device
	VARIABLES	{ doValue, adminDateAndTime, adminNDTrapSeqNo,
			  doIndex, doType, doValue1String }
	DESCRIPTION	"This trap is generated when set
			 doValue1TrapID equal 17 and
			while the value of doValue is 1."
	::= 28177


    doValue1-18	TRAP-TYPE
	ENTERPRISE	network-device
	VARIABLES	{ doValue, adminDateAndTime, adminNDTrapSeqNo,
			  doIndex, doType, doValue1String }
	DESCRIPTION	"This trap is generated when set
			 doValue1TrapID equal 18 and
			while the value of doValue is 1."
	::= 28178


    doValue1-19	TRAP-TYPE
	ENTERPRISE	network-device
	VARIABLES	{ doValue, adminDateAndTime, adminNDTrapSeqNo,
			  doIndex, doType, doValue1String }
	DESCRIPTION	"This trap is generated when set
			 doValue1TrapID equal 19 and
			while the value of doValue is 1."
	::= 28179


    doValue1-20	TRAP-TYPE
	ENTERPRISE	network-device
	VARIABLES	{ doValue, adminDateAndTime, adminNDTrapSeqNo,
			  doIndex, doType, doValue1String }
	DESCRIPTION	"This trap is generated when set
			 doValue1TrapID equal 20 and
			while the value of doValue is 1."
	::= 28180


    doValue1-21	TRAP-TYPE
	ENTERPRISE	network-device
	VARIABLES	{ doValue, adminDateAndTime, adminNDTrapSeqNo,
			  doIndex, doType, doValue1String }
	DESCRIPTION	"This trap is generated when set
			 doValue1TrapID equal 21 and
			while the value of doValue is 1."
	::= 28181


    doValue1-22	TRAP-TYPE
	ENTERPRISE	network-device
	VARIABLES	{ doValue, adminDateAndTime, adminNDTrapSeqNo,
			  doIndex, doType, doValue1String }
	DESCRIPTION	"This trap is generated when set
			 doValue1TrapID equal 22 and
			while the value of doValue is 1."
	::= 28182


    doValue1-23	TRAP-TYPE
	ENTERPRISE	network-device
	VARIABLES	{ doValue, adminDateAndTime, adminNDTrapSeqNo,
			  doIndex, doType, doValue1String }
	DESCRIPTION	"This trap is generated when set
			 doValue1TrapID equal 23 and
			while the value of doValue is 1."
	::= 28183


    doValue1-24	TRAP-TYPE
	ENTERPRISE	network-device
	VARIABLES	{ doValue, adminDateAndTime, adminNDTrapSeqNo,
			  doIndex, doType, doValue1String }
	DESCRIPTION	"This trap is generated when set
			 doValue1TrapID equal 24 and
			while the value of doValue is 1."
	::= 28184


    doValue1-25	TRAP-TYPE
	ENTERPRISE	network-device
	VARIABLES	{ doValue, adminDateAndTime, adminNDTrapSeqNo,
			  doIndex, doType, doValue1String }
	DESCRIPTION	"This trap is generated when set
			 doValue1TrapID equal 25 and
			while the value of doValue is 1."
	::= 28185


    doValue1-26	TRAP-TYPE
	ENTERPRISE	network-device
	VARIABLES	{ doValue, adminDateAndTime, adminNDTrapSeqNo,
			  doIndex, doType, doValue1String }
	DESCRIPTION	"This trap is generated when set
			 doValue1TrapID equal 26 and
			while the value of doValue is 1."
	::= 28186


    doValue1-27	TRAP-TYPE
	ENTERPRISE	network-device
	VARIABLES	{ doValue, adminDateAndTime, adminNDTrapSeqNo,
			  doIndex, doType, doValue1String }
	DESCRIPTION	"This trap is generated when set
			 doValue1TrapID equal 27 and
			while the value of doValue is 1."
	::= 28187


    doValue1-28	TRAP-TYPE
	ENTERPRISE	network-device
	VARIABLES	{ doValue, adminDateAndTime, adminNDTrapSeqNo,
			  doIndex, doType, doValue1String }
	DESCRIPTION	"This trap is generated when set
			 doValue1TrapID equal 28 and
			while the value of doValue is 1."
	::= 28188


    doValue1-29	TRAP-TYPE
	ENTERPRISE	network-device
	VARIABLES	{ doValue, adminDateAndTime, adminNDTrapSeqNo,
			  doIndex, doType, doValue1String }
	DESCRIPTION	"This trap is generated when set
			 doValue1TrapID equal 29 and
			while the value of doValue is 1."
	::= 28189


    doValue1-30	TRAP-TYPE
	ENTERPRISE	network-device
	VARIABLES	{ doValue, adminDateAndTime, adminNDTrapSeqNo,
			  doIndex, doType, doValue1String }
	DESCRIPTION	"This trap is generated when set
			 doValue1TrapID equal 30 and
			while the value of doValue is 1."
	::= 28190


    doValue1-31	TRAP-TYPE
	ENTERPRISE	network-device
	VARIABLES	{ doValue, adminDateAndTime, adminNDTrapSeqNo,
			  doIndex, doType, doValue1String }
	DESCRIPTION	"This trap is generated when set
			 doValue1TrapID equal 31 and
			while the value of doValue is 1."
	::= 28191


    doValue1-32	TRAP-TYPE
	ENTERPRISE	network-device
	VARIABLES	{ doValue, adminDateAndTime, adminNDTrapSeqNo,
			  doIndex, doType, doValue1String }
	DESCRIPTION	"This trap is generated when set
			 doValue1TrapID equal 32 and
			while the value of doValue is 1."
	::= 28192


    doValue1-33	TRAP-TYPE
	ENTERPRISE	network-device
	VARIABLES	{ doValue, adminDateAndTime, adminNDTrapSeqNo,
			  doIndex, doType, doValue1String }
	DESCRIPTION	"This trap is generated when set
			 doValue1TrapID equal 33 and
			while the value of doValue is 1."
	::= 28193


    doValue1-34	TRAP-TYPE
	ENTERPRISE	network-device
	VARIABLES	{ doValue, adminDateAndTime, adminNDTrapSeqNo,
			  doIndex, doType, doValue1String }
	DESCRIPTION	"This trap is generated when set
			 doValue1TrapID equal 34 and
			while the value of doValue is 1."
	::= 28194


    doValue1-35	TRAP-TYPE
	ENTERPRISE	network-device
	VARIABLES	{ doValue, adminDateAndTime, adminNDTrapSeqNo,
			  doIndex, doType, doValue1String }
	DESCRIPTION	"This trap is generated when set
			 doValue1TrapID equal 35 and
			while the value of doValue is 1."
	::= 28195


    doValue1-36	TRAP-TYPE
	ENTERPRISE	network-device
	VARIABLES	{ doValue, adminDateAndTime, adminNDTrapSeqNo,
			  doIndex, doType, doValue1String }
	DESCRIPTION	"This trap is generated when set
			 doValue1TrapID equal 36 and
			while the value of doValue is 1."
	::= 28196


    doValue1-37	TRAP-TYPE
	ENTERPRISE	network-device
	VARIABLES	{ doValue, adminDateAndTime, adminNDTrapSeqNo,
			  doIndex, doType, doValue1String }
	DESCRIPTION	"This trap is generated when set
			 doValue1TrapID equal 37 and
			while the value of doValue is 1."
	::= 28197


    doValue1-38	TRAP-TYPE
	ENTERPRISE	network-device
	VARIABLES	{ doValue, adminDateAndTime, adminNDTrapSeqNo,
			  doIndex, doType, doValue1String }
	DESCRIPTION	"This trap is generated when set
			 doValue1TrapID equal 38 and
			while the value of doValue is 1."
	::= 28198


    doValue1-39	TRAP-TYPE
	ENTERPRISE	network-device
	VARIABLES	{ doValue, adminDateAndTime, adminNDTrapSeqNo,
			  doIndex, doType, doValue1String }
	DESCRIPTION	"This trap is generated when set
			 doValue1TrapID equal 39 and
			while the value of doValue is 1."
	::= 28199


    doValue1-40	TRAP-TYPE
	ENTERPRISE	network-device
	VARIABLES	{ doValue, adminDateAndTime, adminNDTrapSeqNo,
			  doIndex, doType, doValue1String }
	DESCRIPTION	"This trap is generated when set
			 doValue1TrapID equal 40 and
			while the value of doValue is 1."
	::= 28200


    doValue1-41	TRAP-TYPE
	ENTERPRISE	network-device
	VARIABLES	{ doValue, adminDateAndTime, adminNDTrapSeqNo,
			  doIndex, doType, doValue1String }
	DESCRIPTION	"This trap is generated when set
			 doValue1TrapID equal 41 and
			while the value of doValue is 1."
	::= 28201


    doValue1-42	TRAP-TYPE
	ENTERPRISE	network-device
	VARIABLES	{ doValue, adminDateAndTime, adminNDTrapSeqNo,
			  doIndex, doType, doValue1String }
	DESCRIPTION	"This trap is generated when set
			 doValue1TrapID equal 42 and
			while the value of doValue is 1."
	::= 28202


    doValue1-43	TRAP-TYPE
	ENTERPRISE	network-device
	VARIABLES	{ doValue, adminDateAndTime, adminNDTrapSeqNo,
			  doIndex, doType, doValue1String }
	DESCRIPTION	"This trap is generated when set
			 doValue1TrapID equal 43 and
			while the value of doValue is 1."
	::= 28203


    doValue1-44	TRAP-TYPE
	ENTERPRISE	network-device
	VARIABLES	{ doValue, adminDateAndTime, adminNDTrapSeqNo,
			  doIndex, doType, doValue1String }
	DESCRIPTION	"This trap is generated when set
			 doValue1TrapID equal 44 and
			while the value of doValue is 1."
	::= 28204


    doValue1-45	TRAP-TYPE
	ENTERPRISE	network-device
	VARIABLES	{ doValue, adminDateAndTime, adminNDTrapSeqNo,
			  doIndex, doType, doValue1String }
	DESCRIPTION	"This trap is generated when set
			 doValue1TrapID equal 45 and
			while the value of doValue is 1."
	::= 28205


    doValue1-46	TRAP-TYPE
	ENTERPRISE	network-device
	VARIABLES	{ doValue, adminDateAndTime, adminNDTrapSeqNo,
			  doIndex, doType, doValue1String }
	DESCRIPTION	"This trap is generated when set
			 doValue1TrapID equal 46 and
			while the value of doValue is 1."
	::= 28206


    doValue1-47	TRAP-TYPE
	ENTERPRISE	network-device
	VARIABLES	{ doValue, adminDateAndTime, adminNDTrapSeqNo,
			  doIndex, doType, doValue1String }
	DESCRIPTION	"This trap is generated when set
			 doValue1TrapID equal 47 and
			while the value of doValue is 1."
	::= 28207


    doValue1-48	TRAP-TYPE
	ENTERPRISE	network-device
	VARIABLES	{ doValue, adminDateAndTime, adminNDTrapSeqNo,
			  doIndex, doType, doValue1String }
	DESCRIPTION	"This trap is generated when set
			 doValue1TrapID equal 48 and
			while the value of doValue is 1."
	::= 28208


    doValue1-49	TRAP-TYPE
	ENTERPRISE	network-device
	VARIABLES	{ doValue, adminDateAndTime, adminNDTrapSeqNo,
			  doIndex, doType, doValue1String }
	DESCRIPTION	"This trap is generated when set
			 doValue1TrapID equal 49 and
			while the value of doValue is 1."
	::= 28209


    doValue1-50	TRAP-TYPE
	ENTERPRISE	network-device
	VARIABLES	{ doValue, adminDateAndTime, adminNDTrapSeqNo,
			  doIndex, doType, doValue1String }
	DESCRIPTION	"This trap is generated when set
			 doValue1TrapID equal 50 and
			while the value of doValue is 1."
	::= 28210


    doValue1-51	TRAP-TYPE
	ENTERPRISE	network-device
	VARIABLES	{ doValue, adminDateAndTime, adminNDTrapSeqNo,
			  doIndex, doType, doValue1String }
	DESCRIPTION	"This trap is generated when set
			 doValue1TrapID equal 51 and
			while the value of doValue is 1."
	::= 28211


    doValue1-52	TRAP-TYPE
	ENTERPRISE	network-device
	VARIABLES	{ doValue, adminDateAndTime, adminNDTrapSeqNo,
			  doIndex, doType, doValue1String }
	DESCRIPTION	"This trap is generated when set
			 doValue1TrapID equal 52 and
			while the value of doValue is 1."
	::= 28212


    doValue1-53	TRAP-TYPE
	ENTERPRISE	network-device
	VARIABLES	{ doValue, adminDateAndTime, adminNDTrapSeqNo,
			  doIndex, doType, doValue1String }
	DESCRIPTION	"This trap is generated when set
			 doValue1TrapID equal 53 and
			while the value of doValue is 1."
	::= 28213


    doValue1-54	TRAP-TYPE
	ENTERPRISE	network-device
	VARIABLES	{ doValue, adminDateAndTime, adminNDTrapSeqNo,
			  doIndex, doType, doValue1String }
	DESCRIPTION	"This trap is generated when set
			 doValue1TrapID equal 54 and
			while the value of doValue is 1."
	::= 28214


    doValue1-55	TRAP-TYPE
	ENTERPRISE	network-device
	VARIABLES	{ doValue, adminDateAndTime, adminNDTrapSeqNo,
			  doIndex, doType, doValue1String }
	DESCRIPTION	"This trap is generated when set
			 doValue1TrapID equal 55 and
			while the value of doValue is 1."
	::= 28215


    doValue1-56	TRAP-TYPE
	ENTERPRISE	network-device
	VARIABLES	{ doValue, adminDateAndTime, adminNDTrapSeqNo,
			  doIndex, doType, doValue1String }
	DESCRIPTION	"This trap is generated when set
			 doValue1TrapID equal 56 and
			while the value of doValue is 1."
	::= 28216


    doValue1-57	TRAP-TYPE
	ENTERPRISE	network-device
	VARIABLES	{ doValue, adminDateAndTime, adminNDTrapSeqNo,
			  doIndex, doType, doValue1String }
	DESCRIPTION	"This trap is generated when set
			 doValue1TrapID equal 57 and
			while the value of doValue is 1."
	::= 28217


    doValue1-58	TRAP-TYPE
	ENTERPRISE	network-device
	VARIABLES	{ doValue, adminDateAndTime, adminNDTrapSeqNo,
			  doIndex, doType, doValue1String }
	DESCRIPTION	"This trap is generated when set
			 doValue1TrapID equal 58 and
			while the value of doValue is 1."
	::= 28218


    doValue1-59	TRAP-TYPE
	ENTERPRISE	network-device
	VARIABLES	{ doValue, adminDateAndTime, adminNDTrapSeqNo,
			  doIndex, doType, doValue1String }
	DESCRIPTION	"This trap is generated when set
			 doValue1TrapID equal 59 and
			while the value of doValue is 1."
	::= 28219


    doValue1-60	TRAP-TYPE
	ENTERPRISE	network-device
	VARIABLES	{ doValue, adminDateAndTime, adminNDTrapSeqNo,
			  doIndex, doType, doValue1String }
	DESCRIPTION	"This trap is generated when set
			 doValue1TrapID equal 60 and
			while the value of doValue is 1."
	::= 28220


    doValue1-61	TRAP-TYPE
	ENTERPRISE	network-device
	VARIABLES	{ doValue, adminDateAndTime, adminNDTrapSeqNo,
			  doIndex, doType, doValue1String }
	DESCRIPTION	"This trap is generated when set
			 doValue1TrapID equal 61 and
			while the value of doValue is 1."
	::= 28221


    doValue1-62	TRAP-TYPE
	ENTERPRISE	network-device
	VARIABLES	{ doValue, adminDateAndTime, adminNDTrapSeqNo,
			  doIndex, doType, doValue1String }
	DESCRIPTION	"This trap is generated when set
			 doValue1TrapID equal 62 and
			while the value of doValue is 1."
	::= 28222


    doValue1-63	TRAP-TYPE
	ENTERPRISE	network-device
	VARIABLES	{ doValue, adminDateAndTime, adminNDTrapSeqNo,
			  doIndex, doType, doValue1String }
	DESCRIPTION	"This trap is generated when set
			 doValue1TrapID equal 63 and
			while the value of doValue is 1."
	::= 28223


    doValue1-64	TRAP-TYPE
	ENTERPRISE	network-device
	VARIABLES	{ doValue, adminDateAndTime, adminNDTrapSeqNo,
			  doIndex, doType, doValue1String }
	DESCRIPTION	"This trap is generated when set
			 doValue1TrapID equal 64 and
			while the value of doValue is 1."
	::= 28224


    doValue1-65	TRAP-TYPE
	ENTERPRISE	network-device
	VARIABLES	{ doValue, adminDateAndTime, adminNDTrapSeqNo,
			  doIndex, doType, doValue1String }
	DESCRIPTION	"This trap is generated when set
			 doValue1TrapID equal 65 and
			while the value of doValue is 1."
	::= 28225


    doValue1-66	TRAP-TYPE
	ENTERPRISE	network-device
	VARIABLES	{ doValue, adminDateAndTime, adminNDTrapSeqNo,
			  doIndex, doType, doValue1String }
	DESCRIPTION	"This trap is generated when set
			 doValue1TrapID equal 66 and
			while the value of doValue is 1."
	::= 28226


    doValue1-67	TRAP-TYPE
	ENTERPRISE	network-device
	VARIABLES	{ doValue, adminDateAndTime, adminNDTrapSeqNo,
			  doIndex, doType, doValue1String }
	DESCRIPTION	"This trap is generated when set
			 doValue1TrapID equal 67 and
			while the value of doValue is 1."
	::= 28227


    doValue1-68	TRAP-TYPE
	ENTERPRISE	network-device
	VARIABLES	{ doValue, adminDateAndTime, adminNDTrapSeqNo,
			  doIndex, doType, doValue1String }
	DESCRIPTION	"This trap is generated when set
			 doValue1TrapID equal 68 and
			while the value of doValue is 1."
	::= 28228


    doValue1-69	TRAP-TYPE
	ENTERPRISE	network-device
	VARIABLES	{ doValue, adminDateAndTime, adminNDTrapSeqNo,
			  doIndex, doType, doValue1String }
	DESCRIPTION	"This trap is generated when set
			 doValue1TrapID equal 69 and
			while the value of doValue is 1."
	::= 28229


    doValue1-70	TRAP-TYPE
	ENTERPRISE	network-device
	VARIABLES	{ doValue, adminDateAndTime, adminNDTrapSeqNo,
			  doIndex, doType, doValue1String }
	DESCRIPTION	"This trap is generated when set
			 doValue1TrapID equal 70 and
			while the value of doValue is 1."
	::= 28230


    doValue1-71	TRAP-TYPE
	ENTERPRISE	network-device
	VARIABLES	{ doValue, adminDateAndTime, adminNDTrapSeqNo,
			  doIndex, doType, doValue1String }
	DESCRIPTION	"This trap is generated when set
			 doValue1TrapID equal 71 and
			while the value of doValue is 1."
	::= 28231


    doValue1-72	TRAP-TYPE
	ENTERPRISE	network-device
	VARIABLES	{ doValue, adminDateAndTime, adminNDTrapSeqNo,
			  doIndex, doType, doValue1String }
	DESCRIPTION	"This trap is generated when set
			 doValue1TrapID equal 72 and
			while the value of doValue is 1."
	::= 28232


    doValue1-73	TRAP-TYPE
	ENTERPRISE	network-device
	VARIABLES	{ doValue, adminDateAndTime, adminNDTrapSeqNo,
			  doIndex, doType, doValue1String }
	DESCRIPTION	"This trap is generated when set
			 doValue1TrapID equal 73 and
			while the value of doValue is 1."
	::= 28233


    doValue1-74	TRAP-TYPE
	ENTERPRISE	network-device
	VARIABLES	{ doValue, adminDateAndTime, adminNDTrapSeqNo,
			  doIndex, doType, doValue1String }
	DESCRIPTION	"This trap is generated when set
			 doValue1TrapID equal 74 and
			while the value of doValue is 1."
	::= 28234


    doValue1-75	TRAP-TYPE
	ENTERPRISE	network-device
	VARIABLES	{ doValue, adminDateAndTime, adminNDTrapSeqNo,
			  doIndex, doType, doValue1String }
	DESCRIPTION	"This trap is generated when set
			 doValue1TrapID equal 75 and
			while the value of doValue is 1."
	::= 28235


    doValue1-76	TRAP-TYPE
	ENTERPRISE	network-device
	VARIABLES	{ doValue, adminDateAndTime, adminNDTrapSeqNo,
			  doIndex, doType, doValue1String }
	DESCRIPTION	"This trap is generated when set
			 doValue1TrapID equal 76 and
			while the value of doValue is 1."
	::= 28236


    doValue1-77	TRAP-TYPE
	ENTERPRISE	network-device
	VARIABLES	{ doValue, adminDateAndTime, adminNDTrapSeqNo,
			  doIndex, doType, doValue1String }
	DESCRIPTION	"This trap is generated when set
			 doValue1TrapID equal 77 and
			while the value of doValue is 1."
	::= 28237


    doValue1-78	TRAP-TYPE
	ENTERPRISE	network-device
	VARIABLES	{ doValue, adminDateAndTime, adminNDTrapSeqNo,
			  doIndex, doType, doValue1String }
	DESCRIPTION	"This trap is generated when set
			 doValue1TrapID equal 78 and
			while the value of doValue is 1."
	::= 28238


    doValue1-79	TRAP-TYPE
	ENTERPRISE	network-device
	VARIABLES	{ doValue, adminDateAndTime, adminNDTrapSeqNo,
			  doIndex, doType, doValue1String }
	DESCRIPTION	"This trap is generated when set
			 doValue1TrapID equal 79 and
			while the value of doValue is 1."
	::= 28239


    doValue1-80	TRAP-TYPE
	ENTERPRISE	network-device
	VARIABLES	{ doValue, adminDateAndTime, adminNDTrapSeqNo,
			  doIndex, doType, doValue1String }
	DESCRIPTION	"This trap is generated when set
			 doValue1TrapID equal 80 and
			while the value of doValue is 1."
	::= 28240


    doValue1-81	TRAP-TYPE
	ENTERPRISE	network-device
	VARIABLES	{ doValue, adminDateAndTime, adminNDTrapSeqNo,
			  doIndex, doType, doValue1String }
	DESCRIPTION	"This trap is generated when set
			 doValue1TrapID equal 81 and
			while the value of doValue is 1."
	::= 28241


    doValue1-82	TRAP-TYPE
	ENTERPRISE	network-device
	VARIABLES	{ doValue, adminDateAndTime, adminNDTrapSeqNo,
			  doIndex, doType, doValue1String }
	DESCRIPTION	"This trap is generated when set
			 doValue1TrapID equal 82 and
			while the value of doValue is 1."
	::= 28242


    doValue1-83	TRAP-TYPE
	ENTERPRISE	network-device
	VARIABLES	{ doValue, adminDateAndTime, adminNDTrapSeqNo,
			  doIndex, doType, doValue1String }
	DESCRIPTION	"This trap is generated when set
			 doValue1TrapID equal 83 and
			while the value of doValue is 1."
	::= 28243


    doValue1-84	TRAP-TYPE
	ENTERPRISE	network-device
	VARIABLES	{ doValue, adminDateAndTime, adminNDTrapSeqNo,
			  doIndex, doType, doValue1String }
	DESCRIPTION	"This trap is generated when set
			 doValue1TrapID equal 84 and
			while the value of doValue is 1."
	::= 28244


    doValue1-85	TRAP-TYPE
	ENTERPRISE	network-device
	VARIABLES	{ doValue, adminDateAndTime, adminNDTrapSeqNo,
			  doIndex, doType, doValue1String }
	DESCRIPTION	"This trap is generated when set
			 doValue1TrapID equal 85 and
			while the value of doValue is 1."
	::= 28245


    doValue1-86	TRAP-TYPE
	ENTERPRISE	network-device
	VARIABLES	{ doValue, adminDateAndTime, adminNDTrapSeqNo,
			  doIndex, doType, doValue1String }
	DESCRIPTION	"This trap is generated when set
			 doValue1TrapID equal 86 and
			while the value of doValue is 1."
	::= 28246


    doValue1-87	TRAP-TYPE
	ENTERPRISE	network-device
	VARIABLES	{ doValue, adminDateAndTime, adminNDTrapSeqNo,
			  doIndex, doType, doValue1String }
	DESCRIPTION	"This trap is generated when set
			 doValue1TrapID equal 87 and
			while the value of doValue is 1."
	::= 28247


    doValue1-88	TRAP-TYPE
	ENTERPRISE	network-device
	VARIABLES	{ doValue, adminDateAndTime, adminNDTrapSeqNo,
			  doIndex, doType, doValue1String }
	DESCRIPTION	"This trap is generated when set
			 doValue1TrapID equal 88 and
			while the value of doValue is 1."
	::= 28248


    doValue1-89	TRAP-TYPE
	ENTERPRISE	network-device
	VARIABLES	{ doValue, adminDateAndTime, adminNDTrapSeqNo,
			  doIndex, doType, doValue1String }
	DESCRIPTION	"This trap is generated when set
			 doValue1TrapID equal 89 and
			while the value of doValue is 1."
	::= 28249


    doValue1-90	TRAP-TYPE
	ENTERPRISE	network-device
	VARIABLES	{ doValue, adminDateAndTime, adminNDTrapSeqNo,
			  doIndex, doType, doValue1String }
	DESCRIPTION	"This trap is generated when set
			 doValue1TrapID equal 90 and
			while the value of doValue is 1."
	::= 28250


    doValue1-91	TRAP-TYPE
	ENTERPRISE	network-device
	VARIABLES	{ doValue, adminDateAndTime, adminNDTrapSeqNo,
			  doIndex, doType, doValue1String }
	DESCRIPTION	"This trap is generated when set
			 doValue1TrapID equal 91 and
			while the value of doValue is 1."
	::= 28251


    doValue1-92	TRAP-TYPE
	ENTERPRISE	network-device
	VARIABLES	{ doValue, adminDateAndTime, adminNDTrapSeqNo,
			  doIndex, doType, doValue1String }
	DESCRIPTION	"This trap is generated when set
			 doValue1TrapID equal 92 and
			while the value of doValue is 1."
	::= 28252


    doValue1-93	TRAP-TYPE
	ENTERPRISE	network-device
	VARIABLES	{ doValue, adminDateAndTime, adminNDTrapSeqNo,
			  doIndex, doType, doValue1String }
	DESCRIPTION	"This trap is generated when set
			 doValue1TrapID equal 93 and
			while the value of doValue is 1."
	::= 28253


    doValue1-94	TRAP-TYPE
	ENTERPRISE	network-device
	VARIABLES	{ doValue, adminDateAndTime, adminNDTrapSeqNo,
			  doIndex, doType, doValue1String }
	DESCRIPTION	"This trap is generated when set
			 doValue1TrapID equal 94 and
			while the value of doValue is 1."
	::= 28254


    doValue1-95	TRAP-TYPE
	ENTERPRISE	network-device
	VARIABLES	{ doValue, adminDateAndTime, adminNDTrapSeqNo,
			  doIndex, doType, doValue1String }
	DESCRIPTION	"This trap is generated when set
			 doValue1TrapID equal 95 and
			while the value of doValue is 1."
	::= 28255


    doValue1-96	TRAP-TYPE
	ENTERPRISE	network-device
	VARIABLES	{ doValue, adminDateAndTime, adminNDTrapSeqNo,
			  doIndex, doType, doValue1String }
	DESCRIPTION	"This trap is generated when set
			 doValue1TrapID equal 96 and
			while the value of doValue is 1."
	::= 28256


    doValue1-97	TRAP-TYPE
	ENTERPRISE	network-device
	VARIABLES	{ doValue, adminDateAndTime, adminNDTrapSeqNo,
			  doIndex, doType, doValue1String }
	DESCRIPTION	"This trap is generated when set
			 doValue1TrapID equal 97 and
			while the value of doValue is 1."
	::= 28257


    doValue1-98	TRAP-TYPE
	ENTERPRISE	network-device
	VARIABLES	{ doValue, adminDateAndTime, adminNDTrapSeqNo,
			  doIndex, doType, doValue1String }
	DESCRIPTION	"This trap is generated when set
			 doValue1TrapID equal 98 and
			while the value of doValue is 1."
	::= 28258


    doValue1-99	TRAP-TYPE
	ENTERPRISE	network-device
	VARIABLES	{ doValue, adminDateAndTime, adminNDTrapSeqNo,
			  doIndex, doType, doValue1String }
	DESCRIPTION	"This trap is generated when set
			 doValue1TrapID equal 99 and
			while the value of doValue is 1."
	::= 28259


    doValue1-100	TRAP-TYPE
	ENTERPRISE	network-device
	VARIABLES	{ doValue, adminDateAndTime, adminNDTrapSeqNo,
			  doIndex, doType, doValue1String }
	DESCRIPTION	"This trap is generated when set
			 doValue1TrapID equal 100 and
			while the value of doValue is 1."
	::= 28260


    doValue1-101	TRAP-TYPE
	ENTERPRISE	network-device
	VARIABLES	{ doValue, adminDateAndTime, adminNDTrapSeqNo,
			  doIndex, doType, doValue1String }
	DESCRIPTION	"This trap is generated when set
			 doValue1TrapID equal 101 and
			while the value of doValue is 1."
	::= 28261


    doValue1-102	TRAP-TYPE
	ENTERPRISE	network-device
	VARIABLES	{ doValue, adminDateAndTime, adminNDTrapSeqNo,
			  doIndex, doType, doValue1String }
	DESCRIPTION	"This trap is generated when set
			 doValue1TrapID equal 102 and
			while the value of doValue is 1."
	::= 28262


    doValue1-103	TRAP-TYPE
	ENTERPRISE	network-device
	VARIABLES	{ doValue, adminDateAndTime, adminNDTrapSeqNo,
			  doIndex, doType, doValue1String }
	DESCRIPTION	"This trap is generated when set
			 doValue1TrapID equal 103 and
			while the value of doValue is 1."
	::= 28263


    doValue1-104	TRAP-TYPE
	ENTERPRISE	network-device
	VARIABLES	{ doValue, adminDateAndTime, adminNDTrapSeqNo,
			  doIndex, doType, doValue1String }
	DESCRIPTION	"This trap is generated when set
			 doValue1TrapID equal 104 and
			while the value of doValue is 1."
	::= 28264


    doValue1-105	TRAP-TYPE
	ENTERPRISE	network-device
	VARIABLES	{ doValue, adminDateAndTime, adminNDTrapSeqNo,
			  doIndex, doType, doValue1String }
	DESCRIPTION	"This trap is generated when set
			 doValue1TrapID equal 105 and
			while the value of doValue is 1."
	::= 28265


    doValue1-106	TRAP-TYPE
	ENTERPRISE	network-device
	VARIABLES	{ doValue, adminDateAndTime, adminNDTrapSeqNo,
			  doIndex, doType, doValue1String }
	DESCRIPTION	"This trap is generated when set
			 doValue1TrapID equal 106 and
			while the value of doValue is 1."
	::= 28266


    doValue1-107	TRAP-TYPE
	ENTERPRISE	network-device
	VARIABLES	{ doValue, adminDateAndTime, adminNDTrapSeqNo,
			  doIndex, doType, doValue1String }
	DESCRIPTION	"This trap is generated when set
			 doValue1TrapID equal 107 and
			while the value of doValue is 1."
	::= 28267


    doValue1-108	TRAP-TYPE
	ENTERPRISE	network-device
	VARIABLES	{ doValue, adminDateAndTime, adminNDTrapSeqNo,
			  doIndex, doType, doValue1String }
	DESCRIPTION	"This trap is generated when set
			 doValue1TrapID equal 108 and
			while the value of doValue is 1."
	::= 28268


    doValue1-109	TRAP-TYPE
	ENTERPRISE	network-device
	VARIABLES	{ doValue, adminDateAndTime, adminNDTrapSeqNo,
			  doIndex, doType, doValue1String }
	DESCRIPTION	"This trap is generated when set
			 doValue1TrapID equal 109 and
			while the value of doValue is 1."
	::= 28269


    doValue1-110	TRAP-TYPE
	ENTERPRISE	network-device
	VARIABLES	{ doValue, adminDateAndTime, adminNDTrapSeqNo,
			  doIndex, doType, doValue1String }
	DESCRIPTION	"This trap is generated when set
			 doValue1TrapID equal 110 and
			while the value of doValue is 1."
	::= 28270


    doValue1-111	TRAP-TYPE
	ENTERPRISE	network-device
	VARIABLES	{ doValue, adminDateAndTime, adminNDTrapSeqNo,
			  doIndex, doType, doValue1String }
	DESCRIPTION	"This trap is generated when set
			 doValue1TrapID equal 111 and
			while the value of doValue is 1."
	::= 28271


    doValue1-112	TRAP-TYPE
	ENTERPRISE	network-device
	VARIABLES	{ doValue, adminDateAndTime, adminNDTrapSeqNo,
			  doIndex, doType, doValue1String }
	DESCRIPTION	"This trap is generated when set
			 doValue1TrapID equal 112 and
			while the value of doValue is 1."
	::= 28272


    doValue1-113	TRAP-TYPE
	ENTERPRISE	network-device
	VARIABLES	{ doValue, adminDateAndTime, adminNDTrapSeqNo,
			  doIndex, doType, doValue1String }
	DESCRIPTION	"This trap is generated when set
			 doValue1TrapID equal 113 and
			while the value of doValue is 1."
	::= 28273


    doValue1-114	TRAP-TYPE
	ENTERPRISE	network-device
	VARIABLES	{ doValue, adminDateAndTime, adminNDTrapSeqNo,
			  doIndex, doType, doValue1String }
	DESCRIPTION	"This trap is generated when set
			 doValue1TrapID equal 114 and
			while the value of doValue is 1."
	::= 28274


    doValue1-115	TRAP-TYPE
	ENTERPRISE	network-device
	VARIABLES	{ doValue, adminDateAndTime, adminNDTrapSeqNo,
			  doIndex, doType, doValue1String }
	DESCRIPTION	"This trap is generated when set
			 doValue1TrapID equal 115 and
			while the value of doValue is 1."
	::= 28275


    doValue1-116	TRAP-TYPE
	ENTERPRISE	network-device
	VARIABLES	{ doValue, adminDateAndTime, adminNDTrapSeqNo,
			  doIndex, doType, doValue1String }
	DESCRIPTION	"This trap is generated when set
			 doValue1TrapID equal 116 and
			while the value of doValue is 1."
	::= 28276


    doValue1-117	TRAP-TYPE
	ENTERPRISE	network-device
	VARIABLES	{ doValue, adminDateAndTime, adminNDTrapSeqNo,
			  doIndex, doType, doValue1String }
	DESCRIPTION	"This trap is generated when set
			 doValue1TrapID equal 117 and
			while the value of doValue is 1."
	::= 28277


    doValue1-118	TRAP-TYPE
	ENTERPRISE	network-device
	VARIABLES	{ doValue, adminDateAndTime, adminNDTrapSeqNo,
			  doIndex, doType, doValue1String }
	DESCRIPTION	"This trap is generated when set
			 doValue1TrapID equal 118 and
			while the value of doValue is 1."
	::= 28278


    doValue1-119	TRAP-TYPE
	ENTERPRISE	network-device
	VARIABLES	{ doValue, adminDateAndTime, adminNDTrapSeqNo,
			  doIndex, doType, doValue1String }
	DESCRIPTION	"This trap is generated when set
			 doValue1TrapID equal 119 and
			while the value of doValue is 1."
	::= 28279


    doValue1-120	TRAP-TYPE
	ENTERPRISE	network-device
	VARIABLES	{ doValue, adminDateAndTime, adminNDTrapSeqNo,
			  doIndex, doType, doValue1String }
	DESCRIPTION	"This trap is generated when set
			 doValue1TrapID equal 120 and
			while the value of doValue is 1."
	::= 28280


    doValue1-121	TRAP-TYPE
	ENTERPRISE	network-device
	VARIABLES	{ doValue, adminDateAndTime, adminNDTrapSeqNo,
			  doIndex, doType, doValue1String }
	DESCRIPTION	"This trap is generated when set
			 doValue1TrapID equal 121 and
			while the value of doValue is 1."
	::= 28281


    doValue1-122	TRAP-TYPE
	ENTERPRISE	network-device
	VARIABLES	{ doValue, adminDateAndTime, adminNDTrapSeqNo,
			  doIndex, doType, doValue1String }
	DESCRIPTION	"This trap is generated when set
			 doValue1TrapID equal 122 and
			while the value of doValue is 1."
	::= 28282


    doValue1-123	TRAP-TYPE
	ENTERPRISE	network-device
	VARIABLES	{ doValue, adminDateAndTime, adminNDTrapSeqNo,
			  doIndex, doType, doValue1String }
	DESCRIPTION	"This trap is generated when set
			 doValue1TrapID equal 123 and
			while the value of doValue is 1."
	::= 28283


    doValue1-124	TRAP-TYPE
	ENTERPRISE	network-device
	VARIABLES	{ doValue, adminDateAndTime, adminNDTrapSeqNo,
			  doIndex, doType, doValue1String }
	DESCRIPTION	"This trap is generated when set
			 doValue1TrapID equal 124 and
			while the value of doValue is 1."
	::= 28284


    doValue1-125	TRAP-TYPE
	ENTERPRISE	network-device
	VARIABLES	{ doValue, adminDateAndTime, adminNDTrapSeqNo,
			  doIndex, doType, doValue1String }
	DESCRIPTION	"This trap is generated when set
			 doValue1TrapID equal 125 and
			while the value of doValue is 1."
	::= 28285


    doValue1-126	TRAP-TYPE
	ENTERPRISE	network-device
	VARIABLES	{ doValue, adminDateAndTime, adminNDTrapSeqNo,
			  doIndex, doType, doValue1String }
	DESCRIPTION	"This trap is generated when set
			 doValue1TrapID equal 126 and
			while the value of doValue is 1."
	::= 28286


    doValue1-127	TRAP-TYPE
	ENTERPRISE	network-device
	VARIABLES	{ doValue, adminDateAndTime, adminNDTrapSeqNo,
			  doIndex, doType, doValue1String }
	DESCRIPTION	"This trap is generated when set
			 doValue1TrapID equal 127 and
			while the value of doValue is 1."
	::= 28287

    subUnitNotConnected1	TRAP-TYPE
	ENTERPRISE	network-device
	VARIABLES	{ subUnitStatus,
			  adminDateAndTime, adminNDTrapSeqNo,
			  subUnitIndex }
	DESCRIPTION	"This trap is generated when set
			subUnitNotConnectedTrapID equal 1 and
 			the subunit is disconnected."
	::= 32769

    subUnitNotConnected2	TRAP-TYPE
	ENTERPRISE	network-device
	VARIABLES	{ subUnitStatus,
			  adminDateAndTime, adminNDTrapSeqNo,
			  subUnitIndex }
	DESCRIPTION	"This trap is generated when set
			subUnitNotConnectedTrapID equal 2 and
 			the subunit is disconnected."
	::= 32770

    subUnitNotConnected3	TRAP-TYPE
	ENTERPRISE	network-device
	VARIABLES	{ subUnitStatus,
			  adminDateAndTime, adminNDTrapSeqNo,
			  subUnitIndex }
	DESCRIPTION	"This trap is generated when set
			subUnitNotConnectedTrapID equal 3 and
 			the subunit is disconnected."
	::= 32771

    subUnitNotConnected4	TRAP-TYPE
	ENTERPRISE	network-device
	VARIABLES	{ subUnitStatus,
			  adminDateAndTime, adminNDTrapSeqNo,
			  subUnitIndex }
	DESCRIPTION	"This trap is generated when set
			subUnitNotConnectedTrapID equal 4 and
 			the subunit is disconnected."
	::= 32772

    subUnitNotConnected5	TRAP-TYPE
	ENTERPRISE	network-device
	VARIABLES	{ subUnitStatus,
			  adminDateAndTime, adminNDTrapSeqNo,
			  subUnitIndex }
	DESCRIPTION	"This trap is generated when set
			subUnitNotConnectedTrapID equal 5 and
 			the subunit is disconnected."
	::= 32773

    subUnitNotConnected6	TRAP-TYPE
	ENTERPRISE	network-device
	VARIABLES	{ subUnitStatus,
			  adminDateAndTime, adminNDTrapSeqNo,
			  subUnitIndex }
	DESCRIPTION	"This trap is generated when set
			subUnitNotConnectedTrapID equal 6 and
 			the subunit is disconnected."
	::= 32774

    subUnitNotConnected7	TRAP-TYPE
	ENTERPRISE	network-device
	VARIABLES	{ subUnitStatus,
			  adminDateAndTime, adminNDTrapSeqNo,
			  subUnitIndex }
	DESCRIPTION	"This trap is generated when set
			subUnitNotConnectedTrapID equal 7 and
 			the subunit is disconnected."
	::= 32775

    subUnitNotConnected8	TRAP-TYPE
	ENTERPRISE	network-device
	VARIABLES	{ subUnitStatus,
			  adminDateAndTime, adminNDTrapSeqNo,
			  subUnitIndex }
	DESCRIPTION	"This trap is generated when set
			subUnitNotConnectedTrapID equal 8 and
 			the subunit is disconnected."
	::= 32776

    subUnitNotConnected9	TRAP-TYPE
	ENTERPRISE	network-device
	VARIABLES	{ subUnitStatus,
			  adminDateAndTime, adminNDTrapSeqNo,
			  subUnitIndex }
	DESCRIPTION	"This trap is generated when set
			subUnitNotConnectedTrapID equal 9 and
 			the subunit is disconnected."
	::= 32777

    subUnitNotConnected10	TRAP-TYPE
	ENTERPRISE	network-device
	VARIABLES	{ subUnitStatus,
			  adminDateAndTime, adminNDTrapSeqNo,
			  subUnitIndex }
	DESCRIPTION	"This trap is generated when set
			subUnitNotConnectedTrapID equal 10 and
 			the subunit is disconnected."
	::= 32778

    subUnitNotConnected11	TRAP-TYPE
	ENTERPRISE	network-device
	VARIABLES	{ subUnitStatus,
			  adminDateAndTime, adminNDTrapSeqNo,
			  subUnitIndex }
	DESCRIPTION	"This trap is generated when set
			subUnitNotConnectedTrapID equal 11 and
 			the subunit is disconnected."
	::= 32779

    subUnitNotConnected12	TRAP-TYPE
	ENTERPRISE	network-device
	VARIABLES	{ subUnitStatus,
			  adminDateAndTime, adminNDTrapSeqNo,
			  subUnitIndex }
	DESCRIPTION	"This trap is generated when set
			subUnitNotConnectedTrapID equal 12 and
 			the subunit is disconnected."
	::= 32780

    subUnitNotConnected13	TRAP-TYPE
	ENTERPRISE	network-device
	VARIABLES	{ subUnitStatus,
			  adminDateAndTime, adminNDTrapSeqNo,
			  subUnitIndex }
	DESCRIPTION	"This trap is generated when set
			subUnitNotConnectedTrapID equal 13 and
 			the subunit is disconnected."
	::= 32781

    subUnitNotConnected14	TRAP-TYPE
	ENTERPRISE	network-device
	VARIABLES	{ subUnitStatus,
			  adminDateAndTime, adminNDTrapSeqNo,
			  subUnitIndex }
	DESCRIPTION	"This trap is generated when set
			subUnitNotConnectedTrapID equal 14 and
 			the subunit is disconnected."
	::= 32782

    subUnitNotConnected15	TRAP-TYPE
	ENTERPRISE	network-device
	VARIABLES	{ subUnitStatus,
			  adminDateAndTime, adminNDTrapSeqNo,
			  subUnitIndex }
	DESCRIPTION	"This trap is generated when set
			subUnitNotConnectedTrapID equal 15 and
 			the subunit is disconnected."
	::= 32783

    subUnitNotConnected16	TRAP-TYPE
	ENTERPRISE	network-device
	VARIABLES	{ subUnitStatus,
			  adminDateAndTime, adminNDTrapSeqNo,
			  subUnitIndex }
	DESCRIPTION	"This trap is generated when set
			subUnitNotConnectedTrapID equal 16 and
 			the subunit is disconnected."
	::= 32784

    subUnitNotConnected17	TRAP-TYPE
	ENTERPRISE	network-device
	VARIABLES	{ subUnitStatus,
			  adminDateAndTime, adminNDTrapSeqNo,
			  subUnitIndex }
	DESCRIPTION	"This trap is generated when set
			subUnitNotConnectedTrapID equal 17 and
 			the subunit is disconnected."
	::= 32785

    subUnitNotConnected18	TRAP-TYPE
	ENTERPRISE	network-device
	VARIABLES	{ subUnitStatus,
			  adminDateAndTime, adminNDTrapSeqNo,
			  subUnitIndex }
	DESCRIPTION	"This trap is generated when set
			subUnitNotConnectedTrapID equal 18 and
 			the subunit is disconnected."
	::= 32786

    subUnitNotConnected19	TRAP-TYPE
	ENTERPRISE	network-device
	VARIABLES	{ subUnitStatus,
			  adminDateAndTime, adminNDTrapSeqNo,
			  subUnitIndex }
	DESCRIPTION	"This trap is generated when set
			subUnitNotConnectedTrapID equal 19 and
 			the subunit is disconnected."
	::= 32787

    subUnitNotConnected20	TRAP-TYPE
	ENTERPRISE	network-device
	VARIABLES	{ subUnitStatus,
			  adminDateAndTime, adminNDTrapSeqNo,
			  subUnitIndex }
	DESCRIPTION	"This trap is generated when set
			subUnitNotConnectedTrapID equal 20 and
 			the subunit is disconnected."
	::= 32788

    subUnitNotConnected21	TRAP-TYPE
	ENTERPRISE	network-device
	VARIABLES	{ subUnitStatus,
			  adminDateAndTime, adminNDTrapSeqNo,
			  subUnitIndex }
	DESCRIPTION	"This trap is generated when set
			subUnitNotConnectedTrapID equal 21 and
 			the subunit is disconnected."
	::= 32789

    subUnitNotConnected22	TRAP-TYPE
	ENTERPRISE	network-device
	VARIABLES	{ subUnitStatus,
			  adminDateAndTime, adminNDTrapSeqNo,
			  subUnitIndex }
	DESCRIPTION	"This trap is generated when set
			subUnitNotConnectedTrapID equal 22 and
 			the subunit is disconnected."
	::= 32790

    subUnitNotConnected23	TRAP-TYPE
	ENTERPRISE	network-device
	VARIABLES	{ subUnitStatus,
			  adminDateAndTime, adminNDTrapSeqNo,
			  subUnitIndex }
	DESCRIPTION	"This trap is generated when set
			subUnitNotConnectedTrapID equal 23 and
 			the subunit is disconnected."
	::= 32791

    subUnitNotConnected24	TRAP-TYPE
	ENTERPRISE	network-device
	VARIABLES	{ subUnitStatus,
			  adminDateAndTime, adminNDTrapSeqNo,
			  subUnitIndex }
	DESCRIPTION	"This trap is generated when set
			subUnitNotConnectedTrapID equal 24 and
 			the subunit is disconnected."
	::= 32792

    subUnitNotConnected25	TRAP-TYPE
	ENTERPRISE	network-device
	VARIABLES	{ subUnitStatus,
			  adminDateAndTime, adminNDTrapSeqNo,
			  subUnitIndex }
	DESCRIPTION	"This trap is generated when set
			subUnitNotConnectedTrapID equal 25 and
 			the subunit is disconnected."
	::= 32793

    subUnitNotConnected26	TRAP-TYPE
	ENTERPRISE	network-device
	VARIABLES	{ subUnitStatus,
			  adminDateAndTime, adminNDTrapSeqNo,
			  subUnitIndex }
	DESCRIPTION	"This trap is generated when set
			subUnitNotConnectedTrapID equal 26 and
 			the subunit is disconnected."
	::= 32794

    subUnitNotConnected27	TRAP-TYPE
	ENTERPRISE	network-device
	VARIABLES	{ subUnitStatus,
			  adminDateAndTime, adminNDTrapSeqNo,
			  subUnitIndex }
	DESCRIPTION	"This trap is generated when set
			subUnitNotConnectedTrapID equal 27 and
 			the subunit is disconnected."
	::= 32795

    subUnitNotConnected28	TRAP-TYPE
	ENTERPRISE	network-device
	VARIABLES	{ subUnitStatus,
			  adminDateAndTime, adminNDTrapSeqNo,
			  subUnitIndex }
	DESCRIPTION	"This trap is generated when set
			subUnitNotConnectedTrapID equal 28 and
 			the subunit is disconnected."
	::= 32796

    subUnitNotConnected29	TRAP-TYPE
	ENTERPRISE	network-device
	VARIABLES	{ subUnitStatus,
			  adminDateAndTime, adminNDTrapSeqNo,
			  subUnitIndex }
	DESCRIPTION	"This trap is generated when set
			subUnitNotConnectedTrapID equal 29 and
 			the subunit is disconnected."
	::= 32797

    subUnitNotConnected30	TRAP-TYPE
	ENTERPRISE	network-device
	VARIABLES	{ subUnitStatus,
			  adminDateAndTime, adminNDTrapSeqNo,
			  subUnitIndex }
	DESCRIPTION	"This trap is generated when set
			subUnitNotConnectedTrapID equal 30 and
 			the subunit is disconnected."
	::= 32798

    subUnitNotConnected31	TRAP-TYPE
	ENTERPRISE	network-device
	VARIABLES	{ subUnitStatus,
			  adminDateAndTime, adminNDTrapSeqNo,
			  subUnitIndex }
	DESCRIPTION	"This trap is generated when set
			subUnitNotConnectedTrapID equal 31 and
 			the subunit is disconnected."
	::= 32799

    subUnitNotConnected32	TRAP-TYPE
	ENTERPRISE	network-device
	VARIABLES	{ subUnitStatus,
			  adminDateAndTime, adminNDTrapSeqNo,
			  subUnitIndex }
	DESCRIPTION	"This trap is generated when set
			subUnitNotConnectedTrapID equal 32 and
 			the subunit is disconnected."
	::= 32800

    subUnitNotConnected33	TRAP-TYPE
	ENTERPRISE	network-device
	VARIABLES	{ subUnitStatus,
			  adminDateAndTime, adminNDTrapSeqNo,
			  subUnitIndex }
	DESCRIPTION	"This trap is generated when set
			subUnitNotConnectedTrapID equal 33 and
 			the subunit is disconnected."
	::= 32801

    subUnitNotConnected34	TRAP-TYPE
	ENTERPRISE	network-device
	VARIABLES	{ subUnitStatus,
			  adminDateAndTime, adminNDTrapSeqNo,
			  subUnitIndex }
	DESCRIPTION	"This trap is generated when set
			subUnitNotConnectedTrapID equal 34 and
 			the subunit is disconnected."
	::= 32802

    subUnitNotConnected35	TRAP-TYPE
	ENTERPRISE	network-device
	VARIABLES	{ subUnitStatus,
			  adminDateAndTime, adminNDTrapSeqNo,
			  subUnitIndex }
	DESCRIPTION	"This trap is generated when set
			subUnitNotConnectedTrapID equal 35 and
 			the subunit is disconnected."
	::= 32803

    subUnitNotConnected36	TRAP-TYPE
	ENTERPRISE	network-device
	VARIABLES	{ subUnitStatus,
			  adminDateAndTime, adminNDTrapSeqNo,
			  subUnitIndex }
	DESCRIPTION	"This trap is generated when set
			subUnitNotConnectedTrapID equal 36 and
 			the subunit is disconnected."
	::= 32804

    subUnitNotConnected37	TRAP-TYPE
	ENTERPRISE	network-device
	VARIABLES	{ subUnitStatus,
			  adminDateAndTime, adminNDTrapSeqNo,
			  subUnitIndex }
	DESCRIPTION	"This trap is generated when set
			subUnitNotConnectedTrapID equal 37 and
 			the subunit is disconnected."
	::= 32805

    subUnitNotConnected38	TRAP-TYPE
	ENTERPRISE	network-device
	VARIABLES	{ subUnitStatus,
			  adminDateAndTime, adminNDTrapSeqNo,
			  subUnitIndex }
	DESCRIPTION	"This trap is generated when set
			subUnitNotConnectedTrapID equal 38 and
 			the subunit is disconnected."
	::= 32806

    subUnitNotConnected39	TRAP-TYPE
	ENTERPRISE	network-device
	VARIABLES	{ subUnitStatus,
			  adminDateAndTime, adminNDTrapSeqNo,
			  subUnitIndex }
	DESCRIPTION	"This trap is generated when set
			subUnitNotConnectedTrapID equal 39 and
 			the subunit is disconnected."
	::= 32807

    subUnitNotConnected40	TRAP-TYPE
	ENTERPRISE	network-device
	VARIABLES	{ subUnitStatus,
			  adminDateAndTime, adminNDTrapSeqNo,
			  subUnitIndex }
	DESCRIPTION	"This trap is generated when set
			subUnitNotConnectedTrapID equal 40 and
 			the subunit is disconnected."
	::= 32808

    subUnitNotConnected41	TRAP-TYPE
	ENTERPRISE	network-device
	VARIABLES	{ subUnitStatus,
			  adminDateAndTime, adminNDTrapSeqNo,
			  subUnitIndex }
	DESCRIPTION	"This trap is generated when set
			subUnitNotConnectedTrapID equal 41 and
 			the subunit is disconnected."
	::= 32809

    subUnitNotConnected42	TRAP-TYPE
	ENTERPRISE	network-device
	VARIABLES	{ subUnitStatus,
			  adminDateAndTime, adminNDTrapSeqNo,
			  subUnitIndex }
	DESCRIPTION	"This trap is generated when set
			subUnitNotConnectedTrapID equal 42 and
 			the subunit is disconnected."
	::= 32810

    subUnitNotConnected43	TRAP-TYPE
	ENTERPRISE	network-device
	VARIABLES	{ subUnitStatus,
			  adminDateAndTime, adminNDTrapSeqNo,
			  subUnitIndex }
	DESCRIPTION	"This trap is generated when set
			subUnitNotConnectedTrapID equal 43 and
 			the subunit is disconnected."
	::= 32811

    subUnitNotConnected44	TRAP-TYPE
	ENTERPRISE	network-device
	VARIABLES	{ subUnitStatus,
			  adminDateAndTime, adminNDTrapSeqNo,
			  subUnitIndex }
	DESCRIPTION	"This trap is generated when set
			subUnitNotConnectedTrapID equal 44 and
 			the subunit is disconnected."
	::= 32812

    subUnitNotConnected45	TRAP-TYPE
	ENTERPRISE	network-device
	VARIABLES	{ subUnitStatus,
			  adminDateAndTime, adminNDTrapSeqNo,
			  subUnitIndex }
	DESCRIPTION	"This trap is generated when set
			subUnitNotConnectedTrapID equal 45 and
 			the subunit is disconnected."
	::= 32813

    subUnitNotConnected46	TRAP-TYPE
	ENTERPRISE	network-device
	VARIABLES	{ subUnitStatus,
			  adminDateAndTime, adminNDTrapSeqNo,
			  subUnitIndex }
	DESCRIPTION	"This trap is generated when set
			subUnitNotConnectedTrapID equal 46 and
 			the subunit is disconnected."
	::= 32814

    subUnitNotConnected47	TRAP-TYPE
	ENTERPRISE	network-device
	VARIABLES	{ subUnitStatus,
			  adminDateAndTime, adminNDTrapSeqNo,
			  subUnitIndex }
	DESCRIPTION	"This trap is generated when set
			subUnitNotConnectedTrapID equal 47 and
 			the subunit is disconnected."
	::= 32815

    subUnitNotConnected48	TRAP-TYPE
	ENTERPRISE	network-device
	VARIABLES	{ subUnitStatus,
			  adminDateAndTime, adminNDTrapSeqNo,
			  subUnitIndex }
	DESCRIPTION	"This trap is generated when set
			subUnitNotConnectedTrapID equal 48 and
 			the subunit is disconnected."
	::= 32816

    subUnitNotConnected49	TRAP-TYPE
	ENTERPRISE	network-device
	VARIABLES	{ subUnitStatus,
			  adminDateAndTime, adminNDTrapSeqNo,
			  subUnitIndex }
	DESCRIPTION	"This trap is generated when set
			subUnitNotConnectedTrapID equal 49 and
 			the subunit is disconnected."
	::= 32817

    subUnitNotConnected50	TRAP-TYPE
	ENTERPRISE	network-device
	VARIABLES	{ subUnitStatus,
			  adminDateAndTime, adminNDTrapSeqNo,
			  subUnitIndex }
	DESCRIPTION	"This trap is generated when set
			subUnitNotConnectedTrapID equal 50 and
 			the subunit is disconnected."
	::= 32818

    subUnitNotConnected51	TRAP-TYPE
	ENTERPRISE	network-device
	VARIABLES	{ subUnitStatus,
			  adminDateAndTime, adminNDTrapSeqNo,
			  subUnitIndex }
	DESCRIPTION	"This trap is generated when set
			subUnitNotConnectedTrapID equal 51 and
 			the subunit is disconnected."
	::= 32819

    subUnitNotConnected52	TRAP-TYPE
	ENTERPRISE	network-device
	VARIABLES	{ subUnitStatus,
			  adminDateAndTime, adminNDTrapSeqNo,
			  subUnitIndex }
	DESCRIPTION	"This trap is generated when set
			subUnitNotConnectedTrapID equal 52 and
 			the subunit is disconnected."
	::= 32820

    subUnitNotConnected53	TRAP-TYPE
	ENTERPRISE	network-device
	VARIABLES	{ subUnitStatus,
			  adminDateAndTime, adminNDTrapSeqNo,
			  subUnitIndex }
	DESCRIPTION	"This trap is generated when set
			subUnitNotConnectedTrapID equal 53 and
 			the subunit is disconnected."
	::= 32821

    subUnitNotConnected54	TRAP-TYPE
	ENTERPRISE	network-device
	VARIABLES	{ subUnitStatus,
			  adminDateAndTime, adminNDTrapSeqNo,
			  subUnitIndex }
	DESCRIPTION	"This trap is generated when set
			subUnitNotConnectedTrapID equal 54 and
 			the subunit is disconnected."
	::= 32822

    subUnitNotConnected55	TRAP-TYPE
	ENTERPRISE	network-device
	VARIABLES	{ subUnitStatus,
			  adminDateAndTime, adminNDTrapSeqNo,
			  subUnitIndex }
	DESCRIPTION	"This trap is generated when set
			subUnitNotConnectedTrapID equal 55 and
 			the subunit is disconnected."
	::= 32823

    subUnitNotConnected56	TRAP-TYPE
	ENTERPRISE	network-device
	VARIABLES	{ subUnitStatus,
			  adminDateAndTime, adminNDTrapSeqNo,
			  subUnitIndex }
	DESCRIPTION	"This trap is generated when set
			subUnitNotConnectedTrapID equal 56 and
 			the subunit is disconnected."
	::= 32824

    subUnitNotConnected57	TRAP-TYPE
	ENTERPRISE	network-device
	VARIABLES	{ subUnitStatus,
			  adminDateAndTime, adminNDTrapSeqNo,
			  subUnitIndex }
	DESCRIPTION	"This trap is generated when set
			subUnitNotConnectedTrapID equal 57 and
 			the subunit is disconnected."
	::= 32825

    subUnitNotConnected58	TRAP-TYPE
	ENTERPRISE	network-device
	VARIABLES	{ subUnitStatus,
			  adminDateAndTime, adminNDTrapSeqNo,
			  subUnitIndex }
	DESCRIPTION	"This trap is generated when set
			subUnitNotConnectedTrapID equal 58 and
 			the subunit is disconnected."
	::= 32826

    subUnitNotConnected59	TRAP-TYPE
	ENTERPRISE	network-device
	VARIABLES	{ subUnitStatus,
			  adminDateAndTime, adminNDTrapSeqNo,
			  subUnitIndex }
	DESCRIPTION	"This trap is generated when set
			subUnitNotConnectedTrapID equal 59 and
 			the subunit is disconnected."
	::= 32827

    subUnitNotConnected60	TRAP-TYPE
	ENTERPRISE	network-device
	VARIABLES	{ subUnitStatus,
			  adminDateAndTime, adminNDTrapSeqNo,
			  subUnitIndex }
	DESCRIPTION	"This trap is generated when set
			subUnitNotConnectedTrapID equal 60 and
 			the subunit is disconnected."
	::= 32828

    subUnitNotConnected61	TRAP-TYPE
	ENTERPRISE	network-device
	VARIABLES	{ subUnitStatus,
			  adminDateAndTime, adminNDTrapSeqNo,
			  subUnitIndex }
	DESCRIPTION	"This trap is generated when set
			subUnitNotConnectedTrapID equal 61 and
 			the subunit is disconnected."
	::= 32829

    subUnitNotConnected62	TRAP-TYPE
	ENTERPRISE	network-device
	VARIABLES	{ subUnitStatus,
			  adminDateAndTime, adminNDTrapSeqNo,
			  subUnitIndex }
	DESCRIPTION	"This trap is generated when set
			subUnitNotConnectedTrapID equal 62 and
 			the subunit is disconnected."
	::= 32830

    subUnitNotConnected63	TRAP-TYPE
	ENTERPRISE	network-device
	VARIABLES	{ subUnitStatus,
			  adminDateAndTime, adminNDTrapSeqNo,
			  subUnitIndex }
	DESCRIPTION	"This trap is generated when set
			subUnitNotConnectedTrapID equal 63 and
 			the subunit is disconnected."
	::= 32831

    subUnitNotConnected64	TRAP-TYPE
	ENTERPRISE	network-device
	VARIABLES	{ subUnitStatus,
			  adminDateAndTime, adminNDTrapSeqNo,
			  subUnitIndex }
	DESCRIPTION	"This trap is generated when set
			subUnitNotConnectedTrapID equal 64 and
 			the subunit is disconnected."
	::= 32832

    subUnitNotConnected65	TRAP-TYPE
	ENTERPRISE	network-device
	VARIABLES	{ subUnitStatus,
			  adminDateAndTime, adminNDTrapSeqNo,
			  subUnitIndex }
	DESCRIPTION	"This trap is generated when set
			subUnitNotConnectedTrapID equal 65 and
 			the subunit is disconnected."
	::= 32833

    subUnitNotConnected66	TRAP-TYPE
	ENTERPRISE	network-device
	VARIABLES	{ subUnitStatus,
			  adminDateAndTime, adminNDTrapSeqNo,
			  subUnitIndex }
	DESCRIPTION	"This trap is generated when set
			subUnitNotConnectedTrapID equal 66 and
 			the subunit is disconnected."
	::= 32834

    subUnitNotConnected67	TRAP-TYPE
	ENTERPRISE	network-device
	VARIABLES	{ subUnitStatus,
			  adminDateAndTime, adminNDTrapSeqNo,
			  subUnitIndex }
	DESCRIPTION	"This trap is generated when set
			subUnitNotConnectedTrapID equal 67 and
 			the subunit is disconnected."
	::= 32835

    subUnitNotConnected68	TRAP-TYPE
	ENTERPRISE	network-device
	VARIABLES	{ subUnitStatus,
			  adminDateAndTime, adminNDTrapSeqNo,
			  subUnitIndex }
	DESCRIPTION	"This trap is generated when set
			subUnitNotConnectedTrapID equal 68 and
 			the subunit is disconnected."
	::= 32836

    subUnitNotConnected69	TRAP-TYPE
	ENTERPRISE	network-device
	VARIABLES	{ subUnitStatus,
			  adminDateAndTime, adminNDTrapSeqNo,
			  subUnitIndex }
	DESCRIPTION	"This trap is generated when set
			subUnitNotConnectedTrapID equal 69 and
 			the subunit is disconnected."
	::= 32837

    subUnitNotConnected70	TRAP-TYPE
	ENTERPRISE	network-device
	VARIABLES	{ subUnitStatus,
			  adminDateAndTime, adminNDTrapSeqNo,
			  subUnitIndex }
	DESCRIPTION	"This trap is generated when set
			subUnitNotConnectedTrapID equal 70 and
 			the subunit is disconnected."
	::= 32838

    subUnitNotConnected71	TRAP-TYPE
	ENTERPRISE	network-device
	VARIABLES	{ subUnitStatus,
			  adminDateAndTime, adminNDTrapSeqNo,
			  subUnitIndex }
	DESCRIPTION	"This trap is generated when set
			subUnitNotConnectedTrapID equal 71 and
 			the subunit is disconnected."
	::= 32839

    subUnitNotConnected72	TRAP-TYPE
	ENTERPRISE	network-device
	VARIABLES	{ subUnitStatus,
			  adminDateAndTime, adminNDTrapSeqNo,
			  subUnitIndex }
	DESCRIPTION	"This trap is generated when set
			subUnitNotConnectedTrapID equal 72 and
 			the subunit is disconnected."
	::= 32840

    subUnitNotConnected73	TRAP-TYPE
	ENTERPRISE	network-device
	VARIABLES	{ subUnitStatus,
			  adminDateAndTime, adminNDTrapSeqNo,
			  subUnitIndex }
	DESCRIPTION	"This trap is generated when set
			subUnitNotConnectedTrapID equal 73 and
 			the subunit is disconnected."
	::= 32841

    subUnitNotConnected74	TRAP-TYPE
	ENTERPRISE	network-device
	VARIABLES	{ subUnitStatus,
			  adminDateAndTime, adminNDTrapSeqNo,
			  subUnitIndex }
	DESCRIPTION	"This trap is generated when set
			subUnitNotConnectedTrapID equal 74 and
 			the subunit is disconnected."
	::= 32842

    subUnitNotConnected75	TRAP-TYPE
	ENTERPRISE	network-device
	VARIABLES	{ subUnitStatus,
			  adminDateAndTime, adminNDTrapSeqNo,
			  subUnitIndex }
	DESCRIPTION	"This trap is generated when set
			subUnitNotConnectedTrapID equal 75 and
 			the subunit is disconnected."
	::= 32843

    subUnitNotConnected76	TRAP-TYPE
	ENTERPRISE	network-device
	VARIABLES	{ subUnitStatus,
			  adminDateAndTime, adminNDTrapSeqNo,
			  subUnitIndex }
	DESCRIPTION	"This trap is generated when set
			subUnitNotConnectedTrapID equal 76 and
 			the subunit is disconnected."
	::= 32844

    subUnitNotConnected77	TRAP-TYPE
	ENTERPRISE	network-device
	VARIABLES	{ subUnitStatus,
			  adminDateAndTime, adminNDTrapSeqNo,
			  subUnitIndex }
	DESCRIPTION	"This trap is generated when set
			subUnitNotConnectedTrapID equal 77 and
 			the subunit is disconnected."
	::= 32845

    subUnitNotConnected78	TRAP-TYPE
	ENTERPRISE	network-device
	VARIABLES	{ subUnitStatus,
			  adminDateAndTime, adminNDTrapSeqNo,
			  subUnitIndex }
	DESCRIPTION	"This trap is generated when set
			subUnitNotConnectedTrapID equal 78 and
 			the subunit is disconnected."
	::= 32846

    subUnitNotConnected79	TRAP-TYPE
	ENTERPRISE	network-device
	VARIABLES	{ subUnitStatus,
			  adminDateAndTime, adminNDTrapSeqNo,
			  subUnitIndex }
	DESCRIPTION	"This trap is generated when set
			subUnitNotConnectedTrapID equal 79 and
 			the subunit is disconnected."
	::= 32847

    subUnitNotConnected80	TRAP-TYPE
	ENTERPRISE	network-device
	VARIABLES	{ subUnitStatus,
			  adminDateAndTime, adminNDTrapSeqNo,
			  subUnitIndex }
	DESCRIPTION	"This trap is generated when set
			subUnitNotConnectedTrapID equal 80 and
 			the subunit is disconnected."
	::= 32848

    subUnitNotConnected81	TRAP-TYPE
	ENTERPRISE	network-device
	VARIABLES	{ subUnitStatus,
			  adminDateAndTime, adminNDTrapSeqNo,
			  subUnitIndex }
	DESCRIPTION	"This trap is generated when set
			subUnitNotConnectedTrapID equal 81 and
 			the subunit is disconnected."
	::= 32849

    subUnitNotConnected82	TRAP-TYPE
	ENTERPRISE	network-device
	VARIABLES	{ subUnitStatus,
			  adminDateAndTime, adminNDTrapSeqNo,
			  subUnitIndex }
	DESCRIPTION	"This trap is generated when set
			subUnitNotConnectedTrapID equal 82 and
 			the subunit is disconnected."
	::= 32850

    subUnitNotConnected83	TRAP-TYPE
	ENTERPRISE	network-device
	VARIABLES	{ subUnitStatus,
			  adminDateAndTime, adminNDTrapSeqNo,
			  subUnitIndex }
	DESCRIPTION	"This trap is generated when set
			subUnitNotConnectedTrapID equal 83 and
 			the subunit is disconnected."
	::= 32851

    subUnitNotConnected84	TRAP-TYPE
	ENTERPRISE	network-device
	VARIABLES	{ subUnitStatus,
			  adminDateAndTime, adminNDTrapSeqNo,
			  subUnitIndex }
	DESCRIPTION	"This trap is generated when set
			subUnitNotConnectedTrapID equal 84 and
 			the subunit is disconnected."
	::= 32852

    subUnitNotConnected85	TRAP-TYPE
	ENTERPRISE	network-device
	VARIABLES	{ subUnitStatus,
			  adminDateAndTime, adminNDTrapSeqNo,
			  subUnitIndex }
	DESCRIPTION	"This trap is generated when set
			subUnitNotConnectedTrapID equal 85 and
 			the subunit is disconnected."
	::= 32853

    subUnitNotConnected86	TRAP-TYPE
	ENTERPRISE	network-device
	VARIABLES	{ subUnitStatus,
			  adminDateAndTime, adminNDTrapSeqNo,
			  subUnitIndex }
	DESCRIPTION	"This trap is generated when set
			subUnitNotConnectedTrapID equal 86 and
 			the subunit is disconnected."
	::= 32854

    subUnitNotConnected87	TRAP-TYPE
	ENTERPRISE	network-device
	VARIABLES	{ subUnitStatus,
			  adminDateAndTime, adminNDTrapSeqNo,
			  subUnitIndex }
	DESCRIPTION	"This trap is generated when set
			subUnitNotConnectedTrapID equal 87 and
 			the subunit is disconnected."
	::= 32855

    subUnitNotConnected88	TRAP-TYPE
	ENTERPRISE	network-device
	VARIABLES	{ subUnitStatus,
			  adminDateAndTime, adminNDTrapSeqNo,
			  subUnitIndex }
	DESCRIPTION	"This trap is generated when set
			subUnitNotConnectedTrapID equal 88 and
 			the subunit is disconnected."
	::= 32856

    subUnitNotConnected89	TRAP-TYPE
	ENTERPRISE	network-device
	VARIABLES	{ subUnitStatus,
			  adminDateAndTime, adminNDTrapSeqNo,
			  subUnitIndex }
	DESCRIPTION	"This trap is generated when set
			subUnitNotConnectedTrapID equal 89 and
 			the subunit is disconnected."
	::= 32857

    subUnitNotConnected90	TRAP-TYPE
	ENTERPRISE	network-device
	VARIABLES	{ subUnitStatus,
			  adminDateAndTime, adminNDTrapSeqNo,
			  subUnitIndex }
	DESCRIPTION	"This trap is generated when set
			subUnitNotConnectedTrapID equal 90 and
 			the subunit is disconnected."
	::= 32858

    subUnitNotConnected91	TRAP-TYPE
	ENTERPRISE	network-device
	VARIABLES	{ subUnitStatus,
			  adminDateAndTime, adminNDTrapSeqNo,
			  subUnitIndex }
	DESCRIPTION	"This trap is generated when set
			subUnitNotConnectedTrapID equal 91 and
 			the subunit is disconnected."
	::= 32859

    subUnitNotConnected92	TRAP-TYPE
	ENTERPRISE	network-device
	VARIABLES	{ subUnitStatus,
			  adminDateAndTime, adminNDTrapSeqNo,
			  subUnitIndex }
	DESCRIPTION	"This trap is generated when set
			subUnitNotConnectedTrapID equal 92 and
 			the subunit is disconnected."
	::= 32860

    subUnitNotConnected93	TRAP-TYPE
	ENTERPRISE	network-device
	VARIABLES	{ subUnitStatus,
			  adminDateAndTime, adminNDTrapSeqNo,
			  subUnitIndex }
	DESCRIPTION	"This trap is generated when set
			subUnitNotConnectedTrapID equal 93 and
 			the subunit is disconnected."
	::= 32861

    subUnitNotConnected94	TRAP-TYPE
	ENTERPRISE	network-device
	VARIABLES	{ subUnitStatus,
			  adminDateAndTime, adminNDTrapSeqNo,
			  subUnitIndex }
	DESCRIPTION	"This trap is generated when set
			subUnitNotConnectedTrapID equal 94 and
 			the subunit is disconnected."
	::= 32862

    subUnitNotConnected95	TRAP-TYPE
	ENTERPRISE	network-device
	VARIABLES	{ subUnitStatus,
			  adminDateAndTime, adminNDTrapSeqNo,
			  subUnitIndex }
	DESCRIPTION	"This trap is generated when set
			subUnitNotConnectedTrapID equal 95 and
 			the subunit is disconnected."
	::= 32863

    subUnitNotConnected96	TRAP-TYPE
	ENTERPRISE	network-device
	VARIABLES	{ subUnitStatus,
			  adminDateAndTime, adminNDTrapSeqNo,
			  subUnitIndex }
	DESCRIPTION	"This trap is generated when set
			subUnitNotConnectedTrapID equal 96 and
 			the subunit is disconnected."
	::= 32864

    subUnitNotConnected97	TRAP-TYPE
	ENTERPRISE	network-device
	VARIABLES	{ subUnitStatus,
			  adminDateAndTime, adminNDTrapSeqNo,
			  subUnitIndex }
	DESCRIPTION	"This trap is generated when set
			subUnitNotConnectedTrapID equal 97 and
 			the subunit is disconnected."
	::= 32865

    subUnitNotConnected98	TRAP-TYPE
	ENTERPRISE	network-device
	VARIABLES	{ subUnitStatus,
			  adminDateAndTime, adminNDTrapSeqNo,
			  subUnitIndex }
	DESCRIPTION	"This trap is generated when set
			subUnitNotConnectedTrapID equal 98 and
 			the subunit is disconnected."
	::= 32866

    subUnitNotConnected99	TRAP-TYPE
	ENTERPRISE	network-device
	VARIABLES	{ subUnitStatus,
			  adminDateAndTime, adminNDTrapSeqNo,
			  subUnitIndex }
	DESCRIPTION	"This trap is generated when set
			subUnitNotConnectedTrapID equal 99 and
 			the subunit is disconnected."
	::= 32867

    subUnitNotConnected100	TRAP-TYPE
	ENTERPRISE	network-device
	VARIABLES	{ subUnitStatus,
			  adminDateAndTime, adminNDTrapSeqNo,
			  subUnitIndex }
	DESCRIPTION	"This trap is generated when set
			subUnitNotConnectedTrapID equal 100 and
 			the subunit is disconnected."
	::= 32868

    subUnitNotConnected101	TRAP-TYPE
	ENTERPRISE	network-device
	VARIABLES	{ subUnitStatus,
			  adminDateAndTime, adminNDTrapSeqNo,
			  subUnitIndex }
	DESCRIPTION	"This trap is generated when set
			subUnitNotConnectedTrapID equal 101 and
 			the subunit is disconnected."
	::= 32869

    subUnitNotConnected102	TRAP-TYPE
	ENTERPRISE	network-device
	VARIABLES	{ subUnitStatus,
			  adminDateAndTime, adminNDTrapSeqNo,
			  subUnitIndex }
	DESCRIPTION	"This trap is generated when set
			subUnitNotConnectedTrapID equal 102 and
 			the subunit is disconnected."
	::= 32870

    subUnitNotConnected103	TRAP-TYPE
	ENTERPRISE	network-device
	VARIABLES	{ subUnitStatus,
			  adminDateAndTime, adminNDTrapSeqNo,
			  subUnitIndex }
	DESCRIPTION	"This trap is generated when set
			subUnitNotConnectedTrapID equal 103 and
 			the subunit is disconnected."
	::= 32871

    subUnitNotConnected104	TRAP-TYPE
	ENTERPRISE	network-device
	VARIABLES	{ subUnitStatus,
			  adminDateAndTime, adminNDTrapSeqNo,
			  subUnitIndex }
	DESCRIPTION	"This trap is generated when set
			subUnitNotConnectedTrapID equal 104 and
 			the subunit is disconnected."
	::= 32872

    subUnitNotConnected105	TRAP-TYPE
	ENTERPRISE	network-device
	VARIABLES	{ subUnitStatus,
			  adminDateAndTime, adminNDTrapSeqNo,
			  subUnitIndex }
	DESCRIPTION	"This trap is generated when set
			subUnitNotConnectedTrapID equal 105 and
 			the subunit is disconnected."
	::= 32873

    subUnitNotConnected106	TRAP-TYPE
	ENTERPRISE	network-device
	VARIABLES	{ subUnitStatus,
			  adminDateAndTime, adminNDTrapSeqNo,
			  subUnitIndex }
	DESCRIPTION	"This trap is generated when set
			subUnitNotConnectedTrapID equal 106 and
 			the subunit is disconnected."
	::= 32874

    subUnitNotConnected107	TRAP-TYPE
	ENTERPRISE	network-device
	VARIABLES	{ subUnitStatus,
			  adminDateAndTime, adminNDTrapSeqNo,
			  subUnitIndex }
	DESCRIPTION	"This trap is generated when set
			subUnitNotConnectedTrapID equal 107 and
 			the subunit is disconnected."
	::= 32875

    subUnitNotConnected108	TRAP-TYPE
	ENTERPRISE	network-device
	VARIABLES	{ subUnitStatus,
			  adminDateAndTime, adminNDTrapSeqNo,
			  subUnitIndex }
	DESCRIPTION	"This trap is generated when set
			subUnitNotConnectedTrapID equal 108 and
 			the subunit is disconnected."
	::= 32876

    subUnitNotConnected109	TRAP-TYPE
	ENTERPRISE	network-device
	VARIABLES	{ subUnitStatus,
			  adminDateAndTime, adminNDTrapSeqNo,
			  subUnitIndex }
	DESCRIPTION	"This trap is generated when set
			subUnitNotConnectedTrapID equal 109 and
 			the subunit is disconnected."
	::= 32877

    subUnitNotConnected110	TRAP-TYPE
	ENTERPRISE	network-device
	VARIABLES	{ subUnitStatus,
			  adminDateAndTime, adminNDTrapSeqNo,
			  subUnitIndex }
	DESCRIPTION	"This trap is generated when set
			subUnitNotConnectedTrapID equal 110 and
 			the subunit is disconnected."
	::= 32878

    subUnitNotConnected111	TRAP-TYPE
	ENTERPRISE	network-device
	VARIABLES	{ subUnitStatus,
			  adminDateAndTime, adminNDTrapSeqNo,
			  subUnitIndex }
	DESCRIPTION	"This trap is generated when set
			subUnitNotConnectedTrapID equal 111 and
 			the subunit is disconnected."
	::= 32879

    subUnitNotConnected112	TRAP-TYPE
	ENTERPRISE	network-device
	VARIABLES	{ subUnitStatus,
			  adminDateAndTime, adminNDTrapSeqNo,
			  subUnitIndex }
	DESCRIPTION	"This trap is generated when set
			subUnitNotConnectedTrapID equal 112 and
 			the subunit is disconnected."
	::= 32880

    subUnitNotConnected113	TRAP-TYPE
	ENTERPRISE	network-device
	VARIABLES	{ subUnitStatus,
			  adminDateAndTime, adminNDTrapSeqNo,
			  subUnitIndex }
	DESCRIPTION	"This trap is generated when set
			subUnitNotConnectedTrapID equal 113 and
 			the subunit is disconnected."
	::= 32881

    subUnitNotConnected114	TRAP-TYPE
	ENTERPRISE	network-device
	VARIABLES	{ subUnitStatus,
			  adminDateAndTime, adminNDTrapSeqNo,
			  subUnitIndex }
	DESCRIPTION	"This trap is generated when set
			subUnitNotConnectedTrapID equal 114 and
 			the subunit is disconnected."
	::= 32882

    subUnitNotConnected115	TRAP-TYPE
	ENTERPRISE	network-device
	VARIABLES	{ subUnitStatus,
			  adminDateAndTime, adminNDTrapSeqNo,
			  subUnitIndex }
	DESCRIPTION	"This trap is generated when set
			subUnitNotConnectedTrapID equal 115 and
 			the subunit is disconnected."
	::= 32883

    subUnitNotConnected116	TRAP-TYPE
	ENTERPRISE	network-device
	VARIABLES	{ subUnitStatus,
			  adminDateAndTime, adminNDTrapSeqNo,
			  subUnitIndex }
	DESCRIPTION	"This trap is generated when set
			subUnitNotConnectedTrapID equal 116 and
 			the subunit is disconnected."
	::= 32884

    subUnitNotConnected117	TRAP-TYPE
	ENTERPRISE	network-device
	VARIABLES	{ subUnitStatus,
			  adminDateAndTime, adminNDTrapSeqNo,
			  subUnitIndex }
	DESCRIPTION	"This trap is generated when set
			subUnitNotConnectedTrapID equal 117 and
 			the subunit is disconnected."
	::= 32885

    subUnitNotConnected118	TRAP-TYPE
	ENTERPRISE	network-device
	VARIABLES	{ subUnitStatus,
			  adminDateAndTime, adminNDTrapSeqNo,
			  subUnitIndex }
	DESCRIPTION	"This trap is generated when set
			subUnitNotConnectedTrapID equal 118 and
 			the subunit is disconnected."
	::= 32886

    subUnitNotConnected119	TRAP-TYPE
	ENTERPRISE	network-device
	VARIABLES	{ subUnitStatus,
			  adminDateAndTime, adminNDTrapSeqNo,
			  subUnitIndex }
	DESCRIPTION	"This trap is generated when set
			subUnitNotConnectedTrapID equal 119 and
 			the subunit is disconnected."
	::= 32887

    subUnitNotConnected120	TRAP-TYPE
	ENTERPRISE	network-device
	VARIABLES	{ subUnitStatus,
			  adminDateAndTime, adminNDTrapSeqNo,
			  subUnitIndex }
	DESCRIPTION	"This trap is generated when set
			subUnitNotConnectedTrapID equal 120 and
 			the subunit is disconnected."
	::= 32888

    subUnitNotConnected121	TRAP-TYPE
	ENTERPRISE	network-device
	VARIABLES	{ subUnitStatus,
			  adminDateAndTime, adminNDTrapSeqNo,
			  subUnitIndex }
	DESCRIPTION	"This trap is generated when set
			subUnitNotConnectedTrapID equal 121 and
 			the subunit is disconnected."
	::= 32889

    subUnitNotConnected122	TRAP-TYPE
	ENTERPRISE	network-device
	VARIABLES	{ subUnitStatus,
			  adminDateAndTime, adminNDTrapSeqNo,
			  subUnitIndex }
	DESCRIPTION	"This trap is generated when set
			subUnitNotConnectedTrapID equal 122 and
 			the subunit is disconnected."
	::= 32890

    subUnitNotConnected123	TRAP-TYPE
	ENTERPRISE	network-device
	VARIABLES	{ subUnitStatus,
			  adminDateAndTime, adminNDTrapSeqNo,
			  subUnitIndex }
	DESCRIPTION	"This trap is generated when set
			subUnitNotConnectedTrapID equal 123 and
 			the subunit is disconnected."
	::= 32891

    subUnitNotConnected124	TRAP-TYPE
	ENTERPRISE	network-device
	VARIABLES	{ subUnitStatus,
			  adminDateAndTime, adminNDTrapSeqNo,
			  subUnitIndex }
	DESCRIPTION	"This trap is generated when set
			subUnitNotConnectedTrapID equal 124 and
 			the subunit is disconnected."
	::= 32892

    subUnitNotConnected125	TRAP-TYPE
	ENTERPRISE	network-device
	VARIABLES	{ subUnitStatus,
			  adminDateAndTime, adminNDTrapSeqNo,
			  subUnitIndex }
	DESCRIPTION	"This trap is generated when set
			subUnitNotConnectedTrapID equal 125 and
 			the subunit is disconnected."
	::= 32893

    subUnitNotConnected126	TRAP-TYPE
	ENTERPRISE	network-device
	VARIABLES	{ subUnitStatus,
			  adminDateAndTime, adminNDTrapSeqNo,
			  subUnitIndex }
	DESCRIPTION	"This trap is generated when set
			subUnitNotConnectedTrapID equal 126 and
 			the subunit is disconnected."
	::= 32894

    subUnitNotConnected127	TRAP-TYPE
	ENTERPRISE	network-device
	VARIABLES	{ subUnitStatus,
			  adminDateAndTime, adminNDTrapSeqNo,
			  subUnitIndex }
	DESCRIPTION	"This trap is generated when set
			subUnitNotConnectedTrapID equal 127 and
 			the subunit is disconnected."
	::= 32895

    subUnitConnected1	TRAP-TYPE
	ENTERPRISE	network-device
	VARIABLES	{ subUnitStatus,
			  adminDateAndTime, adminNDTrapSeqNo,
			  subUnitIndex }
	DESCRIPTION	"This trap is generated when set
			subUnitConnectedTrapID equal 1 and
 			the subunit is connected."
	::= 33281

    subUnitConnected2	TRAP-TYPE
	ENTERPRISE	network-device
	VARIABLES	{ subUnitStatus,
			  adminDateAndTime, adminNDTrapSeqNo,
			  subUnitIndex }
	DESCRIPTION	"This trap is generated when set
			subUnitConnectedTrapID equal 2 and
 			the subunit is connected."
	::= 33282

    subUnitConnected3	TRAP-TYPE
	ENTERPRISE	network-device
	VARIABLES	{ subUnitStatus,
			  adminDateAndTime, adminNDTrapSeqNo,
			  subUnitIndex }
	DESCRIPTION	"This trap is generated when set
			subUnitConnectedTrapID equal 3 and
 			the subunit is connected."
	::= 33283

    subUnitConnected4	TRAP-TYPE
	ENTERPRISE	network-device
	VARIABLES	{ subUnitStatus,
			  adminDateAndTime, adminNDTrapSeqNo,
			  subUnitIndex }
	DESCRIPTION	"This trap is generated when set
			subUnitConnectedTrapID equal 4 and
 			the subunit is connected."
	::= 33284

    subUnitConnected5	TRAP-TYPE
	ENTERPRISE	network-device
	VARIABLES	{ subUnitStatus,
			  adminDateAndTime, adminNDTrapSeqNo,
			  subUnitIndex }
	DESCRIPTION	"This trap is generated when set
			subUnitConnectedTrapID equal 5 and
 			the subunit is connected."
	::= 33285

    subUnitConnected6	TRAP-TYPE
	ENTERPRISE	network-device
	VARIABLES	{ subUnitStatus,
			  adminDateAndTime, adminNDTrapSeqNo,
			  subUnitIndex }
	DESCRIPTION	"This trap is generated when set
			subUnitConnectedTrapID equal 6 and
 			the subunit is connected."
	::= 33286

    subUnitConnected7	TRAP-TYPE
	ENTERPRISE	network-device
	VARIABLES	{ subUnitStatus,
			  adminDateAndTime, adminNDTrapSeqNo,
			  subUnitIndex }
	DESCRIPTION	"This trap is generated when set
			subUnitConnectedTrapID equal 7 and
 			the subunit is connected."
	::= 33287

    subUnitConnected8	TRAP-TYPE
	ENTERPRISE	network-device
	VARIABLES	{ subUnitStatus,
			  adminDateAndTime, adminNDTrapSeqNo,
			  subUnitIndex }
	DESCRIPTION	"This trap is generated when set
			subUnitConnectedTrapID equal 8 and
 			the subunit is connected."
	::= 33288

    subUnitConnected9	TRAP-TYPE
	ENTERPRISE	network-device
	VARIABLES	{ subUnitStatus,
			  adminDateAndTime, adminNDTrapSeqNo,
			  subUnitIndex }
	DESCRIPTION	"This trap is generated when set
			subUnitConnectedTrapID equal 9 and
 			the subunit is connected."
	::= 33289

    subUnitConnected10	TRAP-TYPE
	ENTERPRISE	network-device
	VARIABLES	{ subUnitStatus,
			  adminDateAndTime, adminNDTrapSeqNo,
			  subUnitIndex }
	DESCRIPTION	"This trap is generated when set
			subUnitConnectedTrapID equal 10 and
 			the subunit is connected."
	::= 33290

    subUnitConnected11	TRAP-TYPE
	ENTERPRISE	network-device
	VARIABLES	{ subUnitStatus,
			  adminDateAndTime, adminNDTrapSeqNo,
			  subUnitIndex }
	DESCRIPTION	"This trap is generated when set
			subUnitConnectedTrapID equal 11 and
 			the subunit is connected."
	::= 33291

    subUnitConnected12	TRAP-TYPE
	ENTERPRISE	network-device
	VARIABLES	{ subUnitStatus,
			  adminDateAndTime, adminNDTrapSeqNo,
			  subUnitIndex }
	DESCRIPTION	"This trap is generated when set
			subUnitConnectedTrapID equal 12 and
 			the subunit is connected."
	::= 33292

    subUnitConnected13	TRAP-TYPE
	ENTERPRISE	network-device
	VARIABLES	{ subUnitStatus,
			  adminDateAndTime, adminNDTrapSeqNo,
			  subUnitIndex }
	DESCRIPTION	"This trap is generated when set
			subUnitConnectedTrapID equal 13 and
 			the subunit is connected."
	::= 33293

    subUnitConnected14	TRAP-TYPE
	ENTERPRISE	network-device
	VARIABLES	{ subUnitStatus,
			  adminDateAndTime, adminNDTrapSeqNo,
			  subUnitIndex }
	DESCRIPTION	"This trap is generated when set
			subUnitConnectedTrapID equal 14 and
 			the subunit is connected."
	::= 33294

    subUnitConnected15	TRAP-TYPE
	ENTERPRISE	network-device
	VARIABLES	{ subUnitStatus,
			  adminDateAndTime, adminNDTrapSeqNo,
			  subUnitIndex }
	DESCRIPTION	"This trap is generated when set
			subUnitConnectedTrapID equal 15 and
 			the subunit is connected."
	::= 33295

    subUnitConnected16	TRAP-TYPE
	ENTERPRISE	network-device
	VARIABLES	{ subUnitStatus,
			  adminDateAndTime, adminNDTrapSeqNo,
			  subUnitIndex }
	DESCRIPTION	"This trap is generated when set
			subUnitConnectedTrapID equal 16 and
 			the subunit is connected."
	::= 33296

    subUnitConnected17	TRAP-TYPE
	ENTERPRISE	network-device
	VARIABLES	{ subUnitStatus,
			  adminDateAndTime, adminNDTrapSeqNo,
			  subUnitIndex }
	DESCRIPTION	"This trap is generated when set
			subUnitConnectedTrapID equal 17 and
 			the subunit is connected."
	::= 33297

    subUnitConnected18	TRAP-TYPE
	ENTERPRISE	network-device
	VARIABLES	{ subUnitStatus,
			  adminDateAndTime, adminNDTrapSeqNo,
			  subUnitIndex }
	DESCRIPTION	"This trap is generated when set
			subUnitConnectedTrapID equal 18 and
 			the subunit is connected."
	::= 33298

    subUnitConnected19	TRAP-TYPE
	ENTERPRISE	network-device
	VARIABLES	{ subUnitStatus,
			  adminDateAndTime, adminNDTrapSeqNo,
			  subUnitIndex }
	DESCRIPTION	"This trap is generated when set
			subUnitConnectedTrapID equal 19 and
 			the subunit is connected."
	::= 33299

    subUnitConnected20	TRAP-TYPE
	ENTERPRISE	network-device
	VARIABLES	{ subUnitStatus,
			  adminDateAndTime, adminNDTrapSeqNo,
			  subUnitIndex }
	DESCRIPTION	"This trap is generated when set
			subUnitConnectedTrapID equal 20 and
 			the subunit is connected."
	::= 33300

    subUnitConnected21	TRAP-TYPE
	ENTERPRISE	network-device
	VARIABLES	{ subUnitStatus,
			  adminDateAndTime, adminNDTrapSeqNo,
			  subUnitIndex }
	DESCRIPTION	"This trap is generated when set
			subUnitConnectedTrapID equal 21 and
 			the subunit is connected."
	::= 33301

    subUnitConnected22	TRAP-TYPE
	ENTERPRISE	network-device
	VARIABLES	{ subUnitStatus,
			  adminDateAndTime, adminNDTrapSeqNo,
			  subUnitIndex }
	DESCRIPTION	"This trap is generated when set
			subUnitConnectedTrapID equal 22 and
 			the subunit is connected."
	::= 33302

    subUnitConnected23	TRAP-TYPE
	ENTERPRISE	network-device
	VARIABLES	{ subUnitStatus,
			  adminDateAndTime, adminNDTrapSeqNo,
			  subUnitIndex }
	DESCRIPTION	"This trap is generated when set
			subUnitConnectedTrapID equal 23 and
 			the subunit is connected."
	::= 33303

    subUnitConnected24	TRAP-TYPE
	ENTERPRISE	network-device
	VARIABLES	{ subUnitStatus,
			  adminDateAndTime, adminNDTrapSeqNo,
			  subUnitIndex }
	DESCRIPTION	"This trap is generated when set
			subUnitConnectedTrapID equal 24 and
 			the subunit is connected."
	::= 33304

    subUnitConnected25	TRAP-TYPE
	ENTERPRISE	network-device
	VARIABLES	{ subUnitStatus,
			  adminDateAndTime, adminNDTrapSeqNo,
			  subUnitIndex }
	DESCRIPTION	"This trap is generated when set
			subUnitConnectedTrapID equal 25 and
 			the subunit is connected."
	::= 33305

    subUnitConnected26	TRAP-TYPE
	ENTERPRISE	network-device
	VARIABLES	{ subUnitStatus,
			  adminDateAndTime, adminNDTrapSeqNo,
			  subUnitIndex }
	DESCRIPTION	"This trap is generated when set
			subUnitConnectedTrapID equal 26 and
 			the subunit is connected."
	::= 33306

    subUnitConnected27	TRAP-TYPE
	ENTERPRISE	network-device
	VARIABLES	{ subUnitStatus,
			  adminDateAndTime, adminNDTrapSeqNo,
			  subUnitIndex }
	DESCRIPTION	"This trap is generated when set
			subUnitConnectedTrapID equal 27 and
 			the subunit is connected."
	::= 33307

    subUnitConnected28	TRAP-TYPE
	ENTERPRISE	network-device
	VARIABLES	{ subUnitStatus,
			  adminDateAndTime, adminNDTrapSeqNo,
			  subUnitIndex }
	DESCRIPTION	"This trap is generated when set
			subUnitConnectedTrapID equal 28 and
 			the subunit is connected."
	::= 33308

    subUnitConnected29	TRAP-TYPE
	ENTERPRISE	network-device
	VARIABLES	{ subUnitStatus,
			  adminDateAndTime, adminNDTrapSeqNo,
			  subUnitIndex }
	DESCRIPTION	"This trap is generated when set
			subUnitConnectedTrapID equal 29 and
 			the subunit is connected."
	::= 33309

    subUnitConnected30	TRAP-TYPE
	ENTERPRISE	network-device
	VARIABLES	{ subUnitStatus,
			  adminDateAndTime, adminNDTrapSeqNo,
			  subUnitIndex }
	DESCRIPTION	"This trap is generated when set
			subUnitConnectedTrapID equal 30 and
 			the subunit is connected."
	::= 33310

    subUnitConnected31	TRAP-TYPE
	ENTERPRISE	network-device
	VARIABLES	{ subUnitStatus,
			  adminDateAndTime, adminNDTrapSeqNo,
			  subUnitIndex }
	DESCRIPTION	"This trap is generated when set
			subUnitConnectedTrapID equal 31 and
 			the subunit is connected."
	::= 33311

    subUnitConnected32	TRAP-TYPE
	ENTERPRISE	network-device
	VARIABLES	{ subUnitStatus,
			  adminDateAndTime, adminNDTrapSeqNo,
			  subUnitIndex }
	DESCRIPTION	"This trap is generated when set
			subUnitConnectedTrapID equal 32 and
 			the subunit is connected."
	::= 33312

    subUnitConnected33	TRAP-TYPE
	ENTERPRISE	network-device
	VARIABLES	{ subUnitStatus,
			  adminDateAndTime, adminNDTrapSeqNo,
			  subUnitIndex }
	DESCRIPTION	"This trap is generated when set
			subUnitConnectedTrapID equal 33 and
 			the subunit is connected."
	::= 33313

    subUnitConnected34	TRAP-TYPE
	ENTERPRISE	network-device
	VARIABLES	{ subUnitStatus,
			  adminDateAndTime, adminNDTrapSeqNo,
			  subUnitIndex }
	DESCRIPTION	"This trap is generated when set
			subUnitConnectedTrapID equal 34 and
 			the subunit is connected."
	::= 33314

    subUnitConnected35	TRAP-TYPE
	ENTERPRISE	network-device
	VARIABLES	{ subUnitStatus,
			  adminDateAndTime, adminNDTrapSeqNo,
			  subUnitIndex }
	DESCRIPTION	"This trap is generated when set
			subUnitConnectedTrapID equal 35 and
 			the subunit is connected."
	::= 33315

    subUnitConnected36	TRAP-TYPE
	ENTERPRISE	network-device
	VARIABLES	{ subUnitStatus,
			  adminDateAndTime, adminNDTrapSeqNo,
			  subUnitIndex }
	DESCRIPTION	"This trap is generated when set
			subUnitConnectedTrapID equal 36 and
 			the subunit is connected."
	::= 33316

    subUnitConnected37	TRAP-TYPE
	ENTERPRISE	network-device
	VARIABLES	{ subUnitStatus,
			  adminDateAndTime, adminNDTrapSeqNo,
			  subUnitIndex }
	DESCRIPTION	"This trap is generated when set
			subUnitConnectedTrapID equal 37 and
 			the subunit is connected."
	::= 33317

    subUnitConnected38	TRAP-TYPE
	ENTERPRISE	network-device
	VARIABLES	{ subUnitStatus,
			  adminDateAndTime, adminNDTrapSeqNo,
			  subUnitIndex }
	DESCRIPTION	"This trap is generated when set
			subUnitConnectedTrapID equal 38 and
 			the subunit is connected."
	::= 33318

    subUnitConnected39	TRAP-TYPE
	ENTERPRISE	network-device
	VARIABLES	{ subUnitStatus,
			  adminDateAndTime, adminNDTrapSeqNo,
			  subUnitIndex }
	DESCRIPTION	"This trap is generated when set
			subUnitConnectedTrapID equal 39 and
 			the subunit is connected."
	::= 33319

    subUnitConnected40	TRAP-TYPE
	ENTERPRISE	network-device
	VARIABLES	{ subUnitStatus,
			  adminDateAndTime, adminNDTrapSeqNo,
			  subUnitIndex }
	DESCRIPTION	"This trap is generated when set
			subUnitConnectedTrapID equal 40 and
 			the subunit is connected."
	::= 33320

    subUnitConnected41	TRAP-TYPE
	ENTERPRISE	network-device
	VARIABLES	{ subUnitStatus,
			  adminDateAndTime, adminNDTrapSeqNo,
			  subUnitIndex }
	DESCRIPTION	"This trap is generated when set
			subUnitConnectedTrapID equal 41 and
 			the subunit is connected."
	::= 33321

    subUnitConnected42	TRAP-TYPE
	ENTERPRISE	network-device
	VARIABLES	{ subUnitStatus,
			  adminDateAndTime, adminNDTrapSeqNo,
			  subUnitIndex }
	DESCRIPTION	"This trap is generated when set
			subUnitConnectedTrapID equal 42 and
 			the subunit is connected."
	::= 33322

    subUnitConnected43	TRAP-TYPE
	ENTERPRISE	network-device
	VARIABLES	{ subUnitStatus,
			  adminDateAndTime, adminNDTrapSeqNo,
			  subUnitIndex }
	DESCRIPTION	"This trap is generated when set
			subUnitConnectedTrapID equal 43 and
 			the subunit is connected."
	::= 33323

    subUnitConnected44	TRAP-TYPE
	ENTERPRISE	network-device
	VARIABLES	{ subUnitStatus,
			  adminDateAndTime, adminNDTrapSeqNo,
			  subUnitIndex }
	DESCRIPTION	"This trap is generated when set
			subUnitConnectedTrapID equal 44 and
 			the subunit is connected."
	::= 33324

    subUnitConnected45	TRAP-TYPE
	ENTERPRISE	network-device
	VARIABLES	{ subUnitStatus,
			  adminDateAndTime, adminNDTrapSeqNo,
			  subUnitIndex }
	DESCRIPTION	"This trap is generated when set
			subUnitConnectedTrapID equal 45 and
 			the subunit is connected."
	::= 33325

    subUnitConnected46	TRAP-TYPE
	ENTERPRISE	network-device
	VARIABLES	{ subUnitStatus,
			  adminDateAndTime, adminNDTrapSeqNo,
			  subUnitIndex }
	DESCRIPTION	"This trap is generated when set
			subUnitConnectedTrapID equal 46 and
 			the subunit is connected."
	::= 33326

    subUnitConnected47	TRAP-TYPE
	ENTERPRISE	network-device
	VARIABLES	{ subUnitStatus,
			  adminDateAndTime, adminNDTrapSeqNo,
			  subUnitIndex }
	DESCRIPTION	"This trap is generated when set
			subUnitConnectedTrapID equal 47 and
 			the subunit is connected."
	::= 33327

    subUnitConnected48	TRAP-TYPE
	ENTERPRISE	network-device
	VARIABLES	{ subUnitStatus,
			  adminDateAndTime, adminNDTrapSeqNo,
			  subUnitIndex }
	DESCRIPTION	"This trap is generated when set
			subUnitConnectedTrapID equal 48 and
 			the subunit is connected."
	::= 33328

    subUnitConnected49	TRAP-TYPE
	ENTERPRISE	network-device
	VARIABLES	{ subUnitStatus,
			  adminDateAndTime, adminNDTrapSeqNo,
			  subUnitIndex }
	DESCRIPTION	"This trap is generated when set
			subUnitConnectedTrapID equal 49 and
 			the subunit is connected."
	::= 33329

    subUnitConnected50	TRAP-TYPE
	ENTERPRISE	network-device
	VARIABLES	{ subUnitStatus,
			  adminDateAndTime, adminNDTrapSeqNo,
			  subUnitIndex }
	DESCRIPTION	"This trap is generated when set
			subUnitConnectedTrapID equal 50 and
 			the subunit is connected."
	::= 33330

    subUnitConnected51	TRAP-TYPE
	ENTERPRISE	network-device
	VARIABLES	{ subUnitStatus,
			  adminDateAndTime, adminNDTrapSeqNo,
			  subUnitIndex }
	DESCRIPTION	"This trap is generated when set
			subUnitConnectedTrapID equal 51 and
 			the subunit is connected."
	::= 33331

    subUnitConnected52	TRAP-TYPE
	ENTERPRISE	network-device
	VARIABLES	{ subUnitStatus,
			  adminDateAndTime, adminNDTrapSeqNo,
			  subUnitIndex }
	DESCRIPTION	"This trap is generated when set
			subUnitConnectedTrapID equal 52 and
 			the subunit is connected."
	::= 33332

    subUnitConnected53	TRAP-TYPE
	ENTERPRISE	network-device
	VARIABLES	{ subUnitStatus,
			  adminDateAndTime, adminNDTrapSeqNo,
			  subUnitIndex }
	DESCRIPTION	"This trap is generated when set
			subUnitConnectedTrapID equal 53 and
 			the subunit is connected."
	::= 33333

    subUnitConnected54	TRAP-TYPE
	ENTERPRISE	network-device
	VARIABLES	{ subUnitStatus,
			  adminDateAndTime, adminNDTrapSeqNo,
			  subUnitIndex }
	DESCRIPTION	"This trap is generated when set
			subUnitConnectedTrapID equal 54 and
 			the subunit is connected."
	::= 33334

    subUnitConnected55	TRAP-TYPE
	ENTERPRISE	network-device
	VARIABLES	{ subUnitStatus,
			  adminDateAndTime, adminNDTrapSeqNo,
			  subUnitIndex }
	DESCRIPTION	"This trap is generated when set
			subUnitConnectedTrapID equal 55 and
 			the subunit is connected."
	::= 33335

    subUnitConnected56	TRAP-TYPE
	ENTERPRISE	network-device
	VARIABLES	{ subUnitStatus,
			  adminDateAndTime, adminNDTrapSeqNo,
			  subUnitIndex }
	DESCRIPTION	"This trap is generated when set
			subUnitConnectedTrapID equal 56 and
 			the subunit is connected."
	::= 33336

    subUnitConnected57	TRAP-TYPE
	ENTERPRISE	network-device
	VARIABLES	{ subUnitStatus,
			  adminDateAndTime, adminNDTrapSeqNo,
			  subUnitIndex }
	DESCRIPTION	"This trap is generated when set
			subUnitConnectedTrapID equal 57 and
 			the subunit is connected."
	::= 33337

    subUnitConnected58	TRAP-TYPE
	ENTERPRISE	network-device
	VARIABLES	{ subUnitStatus,
			  adminDateAndTime, adminNDTrapSeqNo,
			  subUnitIndex }
	DESCRIPTION	"This trap is generated when set
			subUnitConnectedTrapID equal 58 and
 			the subunit is connected."
	::= 33338

    subUnitConnected59	TRAP-TYPE
	ENTERPRISE	network-device
	VARIABLES	{ subUnitStatus,
			  adminDateAndTime, adminNDTrapSeqNo,
			  subUnitIndex }
	DESCRIPTION	"This trap is generated when set
			subUnitConnectedTrapID equal 59 and
 			the subunit is connected."
	::= 33339

    subUnitConnected60	TRAP-TYPE
	ENTERPRISE	network-device
	VARIABLES	{ subUnitStatus,
			  adminDateAndTime, adminNDTrapSeqNo,
			  subUnitIndex }
	DESCRIPTION	"This trap is generated when set
			subUnitConnectedTrapID equal 60 and
 			the subunit is connected."
	::= 33340

    subUnitConnected61	TRAP-TYPE
	ENTERPRISE	network-device
	VARIABLES	{ subUnitStatus,
			  adminDateAndTime, adminNDTrapSeqNo,
			  subUnitIndex }
	DESCRIPTION	"This trap is generated when set
			subUnitConnectedTrapID equal 61 and
 			the subunit is connected."
	::= 33341

    subUnitConnected62	TRAP-TYPE
	ENTERPRISE	network-device
	VARIABLES	{ subUnitStatus,
			  adminDateAndTime, adminNDTrapSeqNo,
			  subUnitIndex }
	DESCRIPTION	"This trap is generated when set
			subUnitConnectedTrapID equal 62 and
 			the subunit is connected."
	::= 33342

    subUnitConnected63	TRAP-TYPE
	ENTERPRISE	network-device
	VARIABLES	{ subUnitStatus,
			  adminDateAndTime, adminNDTrapSeqNo,
			  subUnitIndex }
	DESCRIPTION	"This trap is generated when set
			subUnitConnectedTrapID equal 63 and
 			the subunit is connected."
	::= 33343

    subUnitConnected64	TRAP-TYPE
	ENTERPRISE	network-device
	VARIABLES	{ subUnitStatus,
			  adminDateAndTime, adminNDTrapSeqNo,
			  subUnitIndex }
	DESCRIPTION	"This trap is generated when set
			subUnitConnectedTrapID equal 64 and
 			the subunit is connected."
	::= 33344

    subUnitConnected65	TRAP-TYPE
	ENTERPRISE	network-device
	VARIABLES	{ subUnitStatus,
			  adminDateAndTime, adminNDTrapSeqNo,
			  subUnitIndex }
	DESCRIPTION	"This trap is generated when set
			subUnitConnectedTrapID equal 65 and
 			the subunit is connected."
	::= 33345

    subUnitConnected66	TRAP-TYPE
	ENTERPRISE	network-device
	VARIABLES	{ subUnitStatus,
			  adminDateAndTime, adminNDTrapSeqNo,
			  subUnitIndex }
	DESCRIPTION	"This trap is generated when set
			subUnitConnectedTrapID equal 66 and
 			the subunit is connected."
	::= 33346

    subUnitConnected67	TRAP-TYPE
	ENTERPRISE	network-device
	VARIABLES	{ subUnitStatus,
			  adminDateAndTime, adminNDTrapSeqNo,
			  subUnitIndex }
	DESCRIPTION	"This trap is generated when set
			subUnitConnectedTrapID equal 67 and
 			the subunit is connected."
	::= 33347

    subUnitConnected68	TRAP-TYPE
	ENTERPRISE	network-device
	VARIABLES	{ subUnitStatus,
			  adminDateAndTime, adminNDTrapSeqNo,
			  subUnitIndex }
	DESCRIPTION	"This trap is generated when set
			subUnitConnectedTrapID equal 68 and
 			the subunit is connected."
	::= 33348

    subUnitConnected69	TRAP-TYPE
	ENTERPRISE	network-device
	VARIABLES	{ subUnitStatus,
			  adminDateAndTime, adminNDTrapSeqNo,
			  subUnitIndex }
	DESCRIPTION	"This trap is generated when set
			subUnitConnectedTrapID equal 69 and
 			the subunit is connected."
	::= 33349

    subUnitConnected70	TRAP-TYPE
	ENTERPRISE	network-device
	VARIABLES	{ subUnitStatus,
			  adminDateAndTime, adminNDTrapSeqNo,
			  subUnitIndex }
	DESCRIPTION	"This trap is generated when set
			subUnitConnectedTrapID equal 70 and
 			the subunit is connected."
	::= 33350

    subUnitConnected71	TRAP-TYPE
	ENTERPRISE	network-device
	VARIABLES	{ subUnitStatus,
			  adminDateAndTime, adminNDTrapSeqNo,
			  subUnitIndex }
	DESCRIPTION	"This trap is generated when set
			subUnitConnectedTrapID equal 71 and
 			the subunit is connected."
	::= 33351

    subUnitConnected72	TRAP-TYPE
	ENTERPRISE	network-device
	VARIABLES	{ subUnitStatus,
			  adminDateAndTime, adminNDTrapSeqNo,
			  subUnitIndex }
	DESCRIPTION	"This trap is generated when set
			subUnitConnectedTrapID equal 72 and
 			the subunit is connected."
	::= 33352

    subUnitConnected73	TRAP-TYPE
	ENTERPRISE	network-device
	VARIABLES	{ subUnitStatus,
			  adminDateAndTime, adminNDTrapSeqNo,
			  subUnitIndex }
	DESCRIPTION	"This trap is generated when set
			subUnitConnectedTrapID equal 73 and
 			the subunit is connected."
	::= 33353

    subUnitConnected74	TRAP-TYPE
	ENTERPRISE	network-device
	VARIABLES	{ subUnitStatus,
			  adminDateAndTime, adminNDTrapSeqNo,
			  subUnitIndex }
	DESCRIPTION	"This trap is generated when set
			subUnitConnectedTrapID equal 74 and
 			the subunit is connected."
	::= 33354

    subUnitConnected75	TRAP-TYPE
	ENTERPRISE	network-device
	VARIABLES	{ subUnitStatus,
			  adminDateAndTime, adminNDTrapSeqNo,
			  subUnitIndex }
	DESCRIPTION	"This trap is generated when set
			subUnitConnectedTrapID equal 75 and
 			the subunit is connected."
	::= 33355

    subUnitConnected76	TRAP-TYPE
	ENTERPRISE	network-device
	VARIABLES	{ subUnitStatus,
			  adminDateAndTime, adminNDTrapSeqNo,
			  subUnitIndex }
	DESCRIPTION	"This trap is generated when set
			subUnitConnectedTrapID equal 76 and
 			the subunit is connected."
	::= 33356

    subUnitConnected77	TRAP-TYPE
	ENTERPRISE	network-device
	VARIABLES	{ subUnitStatus,
			  adminDateAndTime, adminNDTrapSeqNo,
			  subUnitIndex }
	DESCRIPTION	"This trap is generated when set
			subUnitConnectedTrapID equal 77 and
 			the subunit is connected."
	::= 33357

    subUnitConnected78	TRAP-TYPE
	ENTERPRISE	network-device
	VARIABLES	{ subUnitStatus,
			  adminDateAndTime, adminNDTrapSeqNo,
			  subUnitIndex }
	DESCRIPTION	"This trap is generated when set
			subUnitConnectedTrapID equal 78 and
 			the subunit is connected."
	::= 33358

    subUnitConnected79	TRAP-TYPE
	ENTERPRISE	network-device
	VARIABLES	{ subUnitStatus,
			  adminDateAndTime, adminNDTrapSeqNo,
			  subUnitIndex }
	DESCRIPTION	"This trap is generated when set
			subUnitConnectedTrapID equal 79 and
 			the subunit is connected."
	::= 33359

    subUnitConnected80	TRAP-TYPE
	ENTERPRISE	network-device
	VARIABLES	{ subUnitStatus,
			  adminDateAndTime, adminNDTrapSeqNo,
			  subUnitIndex }
	DESCRIPTION	"This trap is generated when set
			subUnitConnectedTrapID equal 80 and
 			the subunit is connected."
	::= 33360

    subUnitConnected81	TRAP-TYPE
	ENTERPRISE	network-device
	VARIABLES	{ subUnitStatus,
			  adminDateAndTime, adminNDTrapSeqNo,
			  subUnitIndex }
	DESCRIPTION	"This trap is generated when set
			subUnitConnectedTrapID equal 81 and
 			the subunit is connected."
	::= 33361

    subUnitConnected82	TRAP-TYPE
	ENTERPRISE	network-device
	VARIABLES	{ subUnitStatus,
			  adminDateAndTime, adminNDTrapSeqNo,
			  subUnitIndex }
	DESCRIPTION	"This trap is generated when set
			subUnitConnectedTrapID equal 82 and
 			the subunit is connected."
	::= 33362

    subUnitConnected83	TRAP-TYPE
	ENTERPRISE	network-device
	VARIABLES	{ subUnitStatus,
			  adminDateAndTime, adminNDTrapSeqNo,
			  subUnitIndex }
	DESCRIPTION	"This trap is generated when set
			subUnitConnectedTrapID equal 83 and
 			the subunit is connected."
	::= 33363

    subUnitConnected84	TRAP-TYPE
	ENTERPRISE	network-device
	VARIABLES	{ subUnitStatus,
			  adminDateAndTime, adminNDTrapSeqNo,
			  subUnitIndex }
	DESCRIPTION	"This trap is generated when set
			subUnitConnectedTrapID equal 84 and
 			the subunit is connected."
	::= 33364

    subUnitConnected85	TRAP-TYPE
	ENTERPRISE	network-device
	VARIABLES	{ subUnitStatus,
			  adminDateAndTime, adminNDTrapSeqNo,
			  subUnitIndex }
	DESCRIPTION	"This trap is generated when set
			subUnitConnectedTrapID equal 85 and
 			the subunit is connected."
	::= 33365

    subUnitConnected86	TRAP-TYPE
	ENTERPRISE	network-device
	VARIABLES	{ subUnitStatus,
			  adminDateAndTime, adminNDTrapSeqNo,
			  subUnitIndex }
	DESCRIPTION	"This trap is generated when set
			subUnitConnectedTrapID equal 86 and
 			the subunit is connected."
	::= 33366

    subUnitConnected87	TRAP-TYPE
	ENTERPRISE	network-device
	VARIABLES	{ subUnitStatus,
			  adminDateAndTime, adminNDTrapSeqNo,
			  subUnitIndex }
	DESCRIPTION	"This trap is generated when set
			subUnitConnectedTrapID equal 87 and
 			the subunit is connected."
	::= 33367

    subUnitConnected88	TRAP-TYPE
	ENTERPRISE	network-device
	VARIABLES	{ subUnitStatus,
			  adminDateAndTime, adminNDTrapSeqNo,
			  subUnitIndex }
	DESCRIPTION	"This trap is generated when set
			subUnitConnectedTrapID equal 88 and
 			the subunit is connected."
	::= 33368

    subUnitConnected89	TRAP-TYPE
	ENTERPRISE	network-device
	VARIABLES	{ subUnitStatus,
			  adminDateAndTime, adminNDTrapSeqNo,
			  subUnitIndex }
	DESCRIPTION	"This trap is generated when set
			subUnitConnectedTrapID equal 89 and
 			the subunit is connected."
	::= 33369

    subUnitConnected90	TRAP-TYPE
	ENTERPRISE	network-device
	VARIABLES	{ subUnitStatus,
			  adminDateAndTime, adminNDTrapSeqNo,
			  subUnitIndex }
	DESCRIPTION	"This trap is generated when set
			subUnitConnectedTrapID equal 90 and
 			the subunit is connected."
	::= 33370

    subUnitConnected91	TRAP-TYPE
	ENTERPRISE	network-device
	VARIABLES	{ subUnitStatus,
			  adminDateAndTime, adminNDTrapSeqNo,
			  subUnitIndex }
	DESCRIPTION	"This trap is generated when set
			subUnitConnectedTrapID equal 91 and
 			the subunit is connected."
	::= 33371

    subUnitConnected92	TRAP-TYPE
	ENTERPRISE	network-device
	VARIABLES	{ subUnitStatus,
			  adminDateAndTime, adminNDTrapSeqNo,
			  subUnitIndex }
	DESCRIPTION	"This trap is generated when set
			subUnitConnectedTrapID equal 92 and
 			the subunit is connected."
	::= 33372

    subUnitConnected93	TRAP-TYPE
	ENTERPRISE	network-device
	VARIABLES	{ subUnitStatus,
			  adminDateAndTime, adminNDTrapSeqNo,
			  subUnitIndex }
	DESCRIPTION	"This trap is generated when set
			subUnitConnectedTrapID equal 93 and
 			the subunit is connected."
	::= 33373

    subUnitConnected94	TRAP-TYPE
	ENTERPRISE	network-device
	VARIABLES	{ subUnitStatus,
			  adminDateAndTime, adminNDTrapSeqNo,
			  subUnitIndex }
	DESCRIPTION	"This trap is generated when set
			subUnitConnectedTrapID equal 94 and
 			the subunit is connected."
	::= 33374

    subUnitConnected95	TRAP-TYPE
	ENTERPRISE	network-device
	VARIABLES	{ subUnitStatus,
			  adminDateAndTime, adminNDTrapSeqNo,
			  subUnitIndex }
	DESCRIPTION	"This trap is generated when set
			subUnitConnectedTrapID equal 95 and
 			the subunit is connected."
	::= 33375

    subUnitConnected96	TRAP-TYPE
	ENTERPRISE	network-device
	VARIABLES	{ subUnitStatus,
			  adminDateAndTime, adminNDTrapSeqNo,
			  subUnitIndex }
	DESCRIPTION	"This trap is generated when set
			subUnitConnectedTrapID equal 96 and
 			the subunit is connected."
	::= 33376

    subUnitConnected97	TRAP-TYPE
	ENTERPRISE	network-device
	VARIABLES	{ subUnitStatus,
			  adminDateAndTime, adminNDTrapSeqNo,
			  subUnitIndex }
	DESCRIPTION	"This trap is generated when set
			subUnitConnectedTrapID equal 97 and
 			the subunit is connected."
	::= 33377

    subUnitConnected98	TRAP-TYPE
	ENTERPRISE	network-device
	VARIABLES	{ subUnitStatus,
			  adminDateAndTime, adminNDTrapSeqNo,
			  subUnitIndex }
	DESCRIPTION	"This trap is generated when set
			subUnitConnectedTrapID equal 98 and
 			the subunit is connected."
	::= 33378

    subUnitConnected99	TRAP-TYPE
	ENTERPRISE	network-device
	VARIABLES	{ subUnitStatus,
			  adminDateAndTime, adminNDTrapSeqNo,
			  subUnitIndex }
	DESCRIPTION	"This trap is generated when set
			subUnitConnectedTrapID equal 99 and
 			the subunit is connected."
	::= 33379

    subUnitConnected100	TRAP-TYPE
	ENTERPRISE	network-device
	VARIABLES	{ subUnitStatus,
			  adminDateAndTime, adminNDTrapSeqNo,
			  subUnitIndex }
	DESCRIPTION	"This trap is generated when set
			subUnitConnectedTrapID equal 100 and
 			the subunit is connected."
	::= 33380

    subUnitConnected101	TRAP-TYPE
	ENTERPRISE	network-device
	VARIABLES	{ subUnitStatus,
			  adminDateAndTime, adminNDTrapSeqNo,
			  subUnitIndex }
	DESCRIPTION	"This trap is generated when set
			subUnitConnectedTrapID equal 101 and
 			the subunit is connected."
	::= 33381

    subUnitConnected102	TRAP-TYPE
	ENTERPRISE	network-device
	VARIABLES	{ subUnitStatus,
			  adminDateAndTime, adminNDTrapSeqNo,
			  subUnitIndex }
	DESCRIPTION	"This trap is generated when set
			subUnitConnectedTrapID equal 102 and
 			the subunit is connected."
	::= 33382

    subUnitConnected103	TRAP-TYPE
	ENTERPRISE	network-device
	VARIABLES	{ subUnitStatus,
			  adminDateAndTime, adminNDTrapSeqNo,
			  subUnitIndex }
	DESCRIPTION	"This trap is generated when set
			subUnitConnectedTrapID equal 103 and
 			the subunit is connected."
	::= 33383

    subUnitConnected104	TRAP-TYPE
	ENTERPRISE	network-device
	VARIABLES	{ subUnitStatus,
			  adminDateAndTime, adminNDTrapSeqNo,
			  subUnitIndex }
	DESCRIPTION	"This trap is generated when set
			subUnitConnectedTrapID equal 104 and
 			the subunit is connected."
	::= 33384

    subUnitConnected105	TRAP-TYPE
	ENTERPRISE	network-device
	VARIABLES	{ subUnitStatus,
			  adminDateAndTime, adminNDTrapSeqNo,
			  subUnitIndex }
	DESCRIPTION	"This trap is generated when set
			subUnitConnectedTrapID equal 105 and
 			the subunit is connected."
	::= 33385

    subUnitConnected106	TRAP-TYPE
	ENTERPRISE	network-device
	VARIABLES	{ subUnitStatus,
			  adminDateAndTime, adminNDTrapSeqNo,
			  subUnitIndex }
	DESCRIPTION	"This trap is generated when set
			subUnitConnectedTrapID equal 106 and
 			the subunit is connected."
	::= 33386

    subUnitConnected107	TRAP-TYPE
	ENTERPRISE	network-device
	VARIABLES	{ subUnitStatus,
			  adminDateAndTime, adminNDTrapSeqNo,
			  subUnitIndex }
	DESCRIPTION	"This trap is generated when set
			subUnitConnectedTrapID equal 107 and
 			the subunit is connected."
	::= 33387

    subUnitConnected108	TRAP-TYPE
	ENTERPRISE	network-device
	VARIABLES	{ subUnitStatus,
			  adminDateAndTime, adminNDTrapSeqNo,
			  subUnitIndex }
	DESCRIPTION	"This trap is generated when set
			subUnitConnectedTrapID equal 108 and
 			the subunit is connected."
	::= 33388

    subUnitConnected109	TRAP-TYPE
	ENTERPRISE	network-device
	VARIABLES	{ subUnitStatus,
			  adminDateAndTime, adminNDTrapSeqNo,
			  subUnitIndex }
	DESCRIPTION	"This trap is generated when set
			subUnitConnectedTrapID equal 109 and
 			the subunit is connected."
	::= 33389

    subUnitConnected110	TRAP-TYPE
	ENTERPRISE	network-device
	VARIABLES	{ subUnitStatus,
			  adminDateAndTime, adminNDTrapSeqNo,
			  subUnitIndex }
	DESCRIPTION	"This trap is generated when set
			subUnitConnectedTrapID equal 110 and
 			the subunit is connected."
	::= 33390

    subUnitConnected111	TRAP-TYPE
	ENTERPRISE	network-device
	VARIABLES	{ subUnitStatus,
			  adminDateAndTime, adminNDTrapSeqNo,
			  subUnitIndex }
	DESCRIPTION	"This trap is generated when set
			subUnitConnectedTrapID equal 111 and
 			the subunit is connected."
	::= 33391

    subUnitConnected112	TRAP-TYPE
	ENTERPRISE	network-device
	VARIABLES	{ subUnitStatus,
			  adminDateAndTime, adminNDTrapSeqNo,
			  subUnitIndex }
	DESCRIPTION	"This trap is generated when set
			subUnitConnectedTrapID equal 112 and
 			the subunit is connected."
	::= 33392

    subUnitConnected113	TRAP-TYPE
	ENTERPRISE	network-device
	VARIABLES	{ subUnitStatus,
			  adminDateAndTime, adminNDTrapSeqNo,
			  subUnitIndex }
	DESCRIPTION	"This trap is generated when set
			subUnitConnectedTrapID equal 113 and
 			the subunit is connected."
	::= 33393

    subUnitConnected114	TRAP-TYPE
	ENTERPRISE	network-device
	VARIABLES	{ subUnitStatus,
			  adminDateAndTime, adminNDTrapSeqNo,
			  subUnitIndex }
	DESCRIPTION	"This trap is generated when set
			subUnitConnectedTrapID equal 114 and
 			the subunit is connected."
	::= 33394

    subUnitConnected115	TRAP-TYPE
	ENTERPRISE	network-device
	VARIABLES	{ subUnitStatus,
			  adminDateAndTime, adminNDTrapSeqNo,
			  subUnitIndex }
	DESCRIPTION	"This trap is generated when set
			subUnitConnectedTrapID equal 115 and
 			the subunit is connected."
	::= 33395

    subUnitConnected116	TRAP-TYPE
	ENTERPRISE	network-device
	VARIABLES	{ subUnitStatus,
			  adminDateAndTime, adminNDTrapSeqNo,
			  subUnitIndex }
	DESCRIPTION	"This trap is generated when set
			subUnitConnectedTrapID equal 116 and
 			the subunit is connected."
	::= 33396

    subUnitConnected117	TRAP-TYPE
	ENTERPRISE	network-device
	VARIABLES	{ subUnitStatus,
			  adminDateAndTime, adminNDTrapSeqNo,
			  subUnitIndex }
	DESCRIPTION	"This trap is generated when set
			subUnitConnectedTrapID equal 117 and
 			the subunit is connected."
	::= 33397

    subUnitConnected118	TRAP-TYPE
	ENTERPRISE	network-device
	VARIABLES	{ subUnitStatus,
			  adminDateAndTime, adminNDTrapSeqNo,
			  subUnitIndex }
	DESCRIPTION	"This trap is generated when set
			subUnitConnectedTrapID equal 118 and
 			the subunit is connected."
	::= 33398

    subUnitConnected119	TRAP-TYPE
	ENTERPRISE	network-device
	VARIABLES	{ subUnitStatus,
			  adminDateAndTime, adminNDTrapSeqNo,
			  subUnitIndex }
	DESCRIPTION	"This trap is generated when set
			subUnitConnectedTrapID equal 119 and
 			the subunit is connected."
	::= 33399

    subUnitConnected120	TRAP-TYPE
	ENTERPRISE	network-device
	VARIABLES	{ subUnitStatus,
			  adminDateAndTime, adminNDTrapSeqNo,
			  subUnitIndex }
	DESCRIPTION	"This trap is generated when set
			subUnitConnectedTrapID equal 120 and
 			the subunit is connected."
	::= 33400

    subUnitConnected121	TRAP-TYPE
	ENTERPRISE	network-device
	VARIABLES	{ subUnitStatus,
			  adminDateAndTime, adminNDTrapSeqNo,
			  subUnitIndex }
	DESCRIPTION	"This trap is generated when set
			subUnitConnectedTrapID equal 121 and
 			the subunit is connected."
	::= 33401

    subUnitConnected122	TRAP-TYPE
	ENTERPRISE	network-device
	VARIABLES	{ subUnitStatus,
			  adminDateAndTime, adminNDTrapSeqNo,
			  subUnitIndex }
	DESCRIPTION	"This trap is generated when set
			subUnitConnectedTrapID equal 122 and
 			the subunit is connected."
	::= 33402

    subUnitConnected123	TRAP-TYPE
	ENTERPRISE	network-device
	VARIABLES	{ subUnitStatus,
			  adminDateAndTime, adminNDTrapSeqNo,
			  subUnitIndex }
	DESCRIPTION	"This trap is generated when set
			subUnitConnectedTrapID equal 123 and
 			the subunit is connected."
	::= 33403

    subUnitConnected124	TRAP-TYPE
	ENTERPRISE	network-device
	VARIABLES	{ subUnitStatus,
			  adminDateAndTime, adminNDTrapSeqNo,
			  subUnitIndex }
	DESCRIPTION	"This trap is generated when set
			subUnitConnectedTrapID equal 124 and
 			the subunit is connected."
	::= 33404

    subUnitConnected125	TRAP-TYPE
	ENTERPRISE	network-device
	VARIABLES	{ subUnitStatus,
			  adminDateAndTime, adminNDTrapSeqNo,
			  subUnitIndex }
	DESCRIPTION	"This trap is generated when set
			subUnitConnectedTrapID equal 125 and
 			the subunit is connected."
	::= 33405

    subUnitConnected126	TRAP-TYPE
	ENTERPRISE	network-device
	VARIABLES	{ subUnitStatus,
			  adminDateAndTime, adminNDTrapSeqNo,
			  subUnitIndex }
	DESCRIPTION	"This trap is generated when set
			subUnitConnectedTrapID equal 126 and
 			the subunit is connected."
	::= 33406

    subUnitConnected127	TRAP-TYPE
	ENTERPRISE	network-device
	VARIABLES	{ subUnitStatus,
			  adminDateAndTime, adminNDTrapSeqNo,
			  subUnitIndex }
	DESCRIPTION	"This trap is generated when set
			subUnitConnectedTrapID equal 127 and
 			the subunit is connected."
	::= 33407

    multiMeterNotConnected1	TRAP-TYPE
	ENTERPRISE	network-device
	VARIABLES	{ multiMeterStatus,
			  adminDateAndTime, adminNDTrapSeqNo,
			  multiMeterIndex }
	DESCRIPTION	"This trap is generated when set
			multiMeterNotConnectedTrapID equal 1 and
 			the multimeter is disconnected."
	::= 38913

    multiMeterNotConnected2	TRAP-TYPE
	ENTERPRISE	network-device
	VARIABLES	{ multiMeterStatus,
			  adminDateAndTime, adminNDTrapSeqNo,
			  multiMeterIndex }
	DESCRIPTION	"This trap is generated when set
			multiMeterNotConnectedTrapID equal 2 and
 			the multimeter is disconnected."
	::= 38914

    multiMeterNotConnected3	TRAP-TYPE
	ENTERPRISE	network-device
	VARIABLES	{ multiMeterStatus,
			  adminDateAndTime, adminNDTrapSeqNo,
			  multiMeterIndex }
	DESCRIPTION	"This trap is generated when set
			multiMeterNotConnectedTrapID equal 3 and
 			the multimeter is disconnected."
	::= 38915

    multiMeterNotConnected4	TRAP-TYPE
	ENTERPRISE	network-device
	VARIABLES	{ multiMeterStatus,
			  adminDateAndTime, adminNDTrapSeqNo,
			  multiMeterIndex }
	DESCRIPTION	"This trap is generated when set
			multiMeterNotConnectedTrapID equal 4 and
 			the multimeter is disconnected."
	::= 38916

    multiMeterNotConnected5	TRAP-TYPE
	ENTERPRISE	network-device
	VARIABLES	{ multiMeterStatus,
			  adminDateAndTime, adminNDTrapSeqNo,
			  multiMeterIndex }
	DESCRIPTION	"This trap is generated when set
			multiMeterNotConnectedTrapID equal 5 and
 			the multimeter is disconnected."
	::= 38917

    multiMeterNotConnected6	TRAP-TYPE
	ENTERPRISE	network-device
	VARIABLES	{ multiMeterStatus,
			  adminDateAndTime, adminNDTrapSeqNo,
			  multiMeterIndex }
	DESCRIPTION	"This trap is generated when set
			multiMeterNotConnectedTrapID equal 6 and
 			the multimeter is disconnected."
	::= 38918

    multiMeterNotConnected7	TRAP-TYPE
	ENTERPRISE	network-device
	VARIABLES	{ multiMeterStatus,
			  adminDateAndTime, adminNDTrapSeqNo,
			  multiMeterIndex }
	DESCRIPTION	"This trap is generated when set
			multiMeterNotConnectedTrapID equal 7 and
 			the multimeter is disconnected."
	::= 38919

    multiMeterNotConnected8	TRAP-TYPE
	ENTERPRISE	network-device
	VARIABLES	{ multiMeterStatus,
			  adminDateAndTime, adminNDTrapSeqNo,
			  multiMeterIndex }
	DESCRIPTION	"This trap is generated when set
			multiMeterNotConnectedTrapID equal 8 and
 			the multimeter is disconnected."
	::= 38920

    multiMeterNotConnected9	TRAP-TYPE
	ENTERPRISE	network-device
	VARIABLES	{ multiMeterStatus,
			  adminDateAndTime, adminNDTrapSeqNo,
			  multiMeterIndex }
	DESCRIPTION	"This trap is generated when set
			multiMeterNotConnectedTrapID equal 9 and
 			the multimeter is disconnected."
	::= 38921

    multiMeterNotConnected10	TRAP-TYPE
	ENTERPRISE	network-device
	VARIABLES	{ multiMeterStatus,
			  adminDateAndTime, adminNDTrapSeqNo,
			  multiMeterIndex }
	DESCRIPTION	"This trap is generated when set
			multiMeterNotConnectedTrapID equal 10 and
 			the multimeter is disconnected."
	::= 38922

    multiMeterNotConnected11	TRAP-TYPE
	ENTERPRISE	network-device
	VARIABLES	{ multiMeterStatus,
			  adminDateAndTime, adminNDTrapSeqNo,
			  multiMeterIndex }
	DESCRIPTION	"This trap is generated when set
			multiMeterNotConnectedTrapID equal 11 and
 			the multimeter is disconnected."
	::= 38923

    multiMeterNotConnected12	TRAP-TYPE
	ENTERPRISE	network-device
	VARIABLES	{ multiMeterStatus,
			  adminDateAndTime, adminNDTrapSeqNo,
			  multiMeterIndex }
	DESCRIPTION	"This trap is generated when set
			multiMeterNotConnectedTrapID equal 12 and
 			the multimeter is disconnected."
	::= 38924

    multiMeterNotConnected13	TRAP-TYPE
	ENTERPRISE	network-device
	VARIABLES	{ multiMeterStatus,
			  adminDateAndTime, adminNDTrapSeqNo,
			  multiMeterIndex }
	DESCRIPTION	"This trap is generated when set
			multiMeterNotConnectedTrapID equal 13 and
 			the multimeter is disconnected."
	::= 38925

    multiMeterNotConnected14	TRAP-TYPE
	ENTERPRISE	network-device
	VARIABLES	{ multiMeterStatus,
			  adminDateAndTime, adminNDTrapSeqNo,
			  multiMeterIndex }
	DESCRIPTION	"This trap is generated when set
			multiMeterNotConnectedTrapID equal 14 and
 			the multimeter is disconnected."
	::= 38926

    multiMeterNotConnected15	TRAP-TYPE
	ENTERPRISE	network-device
	VARIABLES	{ multiMeterStatus,
			  adminDateAndTime, adminNDTrapSeqNo,
			  multiMeterIndex }
	DESCRIPTION	"This trap is generated when set
			multiMeterNotConnectedTrapID equal 15 and
 			the multimeter is disconnected."
	::= 38927

    multiMeterNotConnected16	TRAP-TYPE
	ENTERPRISE	network-device
	VARIABLES	{ multiMeterStatus,
			  adminDateAndTime, adminNDTrapSeqNo,
			  multiMeterIndex }
	DESCRIPTION	"This trap is generated when set
			multiMeterNotConnectedTrapID equal 16 and
 			the multimeter is disconnected."
	::= 38928

    multiMeterNotConnected17	TRAP-TYPE
	ENTERPRISE	network-device
	VARIABLES	{ multiMeterStatus,
			  adminDateAndTime, adminNDTrapSeqNo,
			  multiMeterIndex }
	DESCRIPTION	"This trap is generated when set
			multiMeterNotConnectedTrapID equal 17 and
 			the multimeter is disconnected."
	::= 38929

    multiMeterNotConnected18	TRAP-TYPE
	ENTERPRISE	network-device
	VARIABLES	{ multiMeterStatus,
			  adminDateAndTime, adminNDTrapSeqNo,
			  multiMeterIndex }
	DESCRIPTION	"This trap is generated when set
			multiMeterNotConnectedTrapID equal 18 and
 			the multimeter is disconnected."
	::= 38930

    multiMeterNotConnected19	TRAP-TYPE
	ENTERPRISE	network-device
	VARIABLES	{ multiMeterStatus,
			  adminDateAndTime, adminNDTrapSeqNo,
			  multiMeterIndex }
	DESCRIPTION	"This trap is generated when set
			multiMeterNotConnectedTrapID equal 19 and
 			the multimeter is disconnected."
	::= 38931

    multiMeterNotConnected20	TRAP-TYPE
	ENTERPRISE	network-device
	VARIABLES	{ multiMeterStatus,
			  adminDateAndTime, adminNDTrapSeqNo,
			  multiMeterIndex }
	DESCRIPTION	"This trap is generated when set
			multiMeterNotConnectedTrapID equal 20 and
 			the multimeter is disconnected."
	::= 38932

    multiMeterNotConnected21	TRAP-TYPE
	ENTERPRISE	network-device
	VARIABLES	{ multiMeterStatus,
			  adminDateAndTime, adminNDTrapSeqNo,
			  multiMeterIndex }
	DESCRIPTION	"This trap is generated when set
			multiMeterNotConnectedTrapID equal 21 and
 			the multimeter is disconnected."
	::= 38933

    multiMeterNotConnected22	TRAP-TYPE
	ENTERPRISE	network-device
	VARIABLES	{ multiMeterStatus,
			  adminDateAndTime, adminNDTrapSeqNo,
			  multiMeterIndex }
	DESCRIPTION	"This trap is generated when set
			multiMeterNotConnectedTrapID equal 22 and
 			the multimeter is disconnected."
	::= 38934

    multiMeterNotConnected23	TRAP-TYPE
	ENTERPRISE	network-device
	VARIABLES	{ multiMeterStatus,
			  adminDateAndTime, adminNDTrapSeqNo,
			  multiMeterIndex }
	DESCRIPTION	"This trap is generated when set
			multiMeterNotConnectedTrapID equal 23 and
 			the multimeter is disconnected."
	::= 38935

    multiMeterNotConnected24	TRAP-TYPE
	ENTERPRISE	network-device
	VARIABLES	{ multiMeterStatus,
			  adminDateAndTime, adminNDTrapSeqNo,
			  multiMeterIndex }
	DESCRIPTION	"This trap is generated when set
			multiMeterNotConnectedTrapID equal 24 and
 			the multimeter is disconnected."
	::= 38936

    multiMeterNotConnected25	TRAP-TYPE
	ENTERPRISE	network-device
	VARIABLES	{ multiMeterStatus,
			  adminDateAndTime, adminNDTrapSeqNo,
			  multiMeterIndex }
	DESCRIPTION	"This trap is generated when set
			multiMeterNotConnectedTrapID equal 25 and
 			the multimeter is disconnected."
	::= 38937

    multiMeterNotConnected26	TRAP-TYPE
	ENTERPRISE	network-device
	VARIABLES	{ multiMeterStatus,
			  adminDateAndTime, adminNDTrapSeqNo,
			  multiMeterIndex }
	DESCRIPTION	"This trap is generated when set
			multiMeterNotConnectedTrapID equal 26 and
 			the multimeter is disconnected."
	::= 38938

    multiMeterNotConnected27	TRAP-TYPE
	ENTERPRISE	network-device
	VARIABLES	{ multiMeterStatus,
			  adminDateAndTime, adminNDTrapSeqNo,
			  multiMeterIndex }
	DESCRIPTION	"This trap is generated when set
			multiMeterNotConnectedTrapID equal 27 and
 			the multimeter is disconnected."
	::= 38939

    multiMeterNotConnected28	TRAP-TYPE
	ENTERPRISE	network-device
	VARIABLES	{ multiMeterStatus,
			  adminDateAndTime, adminNDTrapSeqNo,
			  multiMeterIndex }
	DESCRIPTION	"This trap is generated when set
			multiMeterNotConnectedTrapID equal 28 and
 			the multimeter is disconnected."
	::= 38940

    multiMeterNotConnected29	TRAP-TYPE
	ENTERPRISE	network-device
	VARIABLES	{ multiMeterStatus,
			  adminDateAndTime, adminNDTrapSeqNo,
			  multiMeterIndex }
	DESCRIPTION	"This trap is generated when set
			multiMeterNotConnectedTrapID equal 29 and
 			the multimeter is disconnected."
	::= 38941

    multiMeterNotConnected30	TRAP-TYPE
	ENTERPRISE	network-device
	VARIABLES	{ multiMeterStatus,
			  adminDateAndTime, adminNDTrapSeqNo,
			  multiMeterIndex }
	DESCRIPTION	"This trap is generated when set
			multiMeterNotConnectedTrapID equal 30 and
 			the multimeter is disconnected."
	::= 38942

    multiMeterNotConnected31	TRAP-TYPE
	ENTERPRISE	network-device
	VARIABLES	{ multiMeterStatus,
			  adminDateAndTime, adminNDTrapSeqNo,
			  multiMeterIndex }
	DESCRIPTION	"This trap is generated when set
			multiMeterNotConnectedTrapID equal 31 and
 			the multimeter is disconnected."
	::= 38943

    multiMeterNotConnected32	TRAP-TYPE
	ENTERPRISE	network-device
	VARIABLES	{ multiMeterStatus,
			  adminDateAndTime, adminNDTrapSeqNo,
			  multiMeterIndex }
	DESCRIPTION	"This trap is generated when set
			multiMeterNotConnectedTrapID equal 32 and
 			the multimeter is disconnected."
	::= 38944

    multiMeterNotConnected33	TRAP-TYPE
	ENTERPRISE	network-device
	VARIABLES	{ multiMeterStatus,
			  adminDateAndTime, adminNDTrapSeqNo,
			  multiMeterIndex }
	DESCRIPTION	"This trap is generated when set
			multiMeterNotConnectedTrapID equal 33 and
 			the multimeter is disconnected."
	::= 38945

    multiMeterNotConnected34	TRAP-TYPE
	ENTERPRISE	network-device
	VARIABLES	{ multiMeterStatus,
			  adminDateAndTime, adminNDTrapSeqNo,
			  multiMeterIndex }
	DESCRIPTION	"This trap is generated when set
			multiMeterNotConnectedTrapID equal 34 and
 			the multimeter is disconnected."
	::= 38946

    multiMeterNotConnected35	TRAP-TYPE
	ENTERPRISE	network-device
	VARIABLES	{ multiMeterStatus,
			  adminDateAndTime, adminNDTrapSeqNo,
			  multiMeterIndex }
	DESCRIPTION	"This trap is generated when set
			multiMeterNotConnectedTrapID equal 35 and
 			the multimeter is disconnected."
	::= 38947

    multiMeterNotConnected36	TRAP-TYPE
	ENTERPRISE	network-device
	VARIABLES	{ multiMeterStatus,
			  adminDateAndTime, adminNDTrapSeqNo,
			  multiMeterIndex }
	DESCRIPTION	"This trap is generated when set
			multiMeterNotConnectedTrapID equal 36 and
 			the multimeter is disconnected."
	::= 38948

    multiMeterNotConnected37	TRAP-TYPE
	ENTERPRISE	network-device
	VARIABLES	{ multiMeterStatus,
			  adminDateAndTime, adminNDTrapSeqNo,
			  multiMeterIndex }
	DESCRIPTION	"This trap is generated when set
			multiMeterNotConnectedTrapID equal 37 and
 			the multimeter is disconnected."
	::= 38949

    multiMeterNotConnected38	TRAP-TYPE
	ENTERPRISE	network-device
	VARIABLES	{ multiMeterStatus,
			  adminDateAndTime, adminNDTrapSeqNo,
			  multiMeterIndex }
	DESCRIPTION	"This trap is generated when set
			multiMeterNotConnectedTrapID equal 38 and
 			the multimeter is disconnected."
	::= 38950

    multiMeterNotConnected39	TRAP-TYPE
	ENTERPRISE	network-device
	VARIABLES	{ multiMeterStatus,
			  adminDateAndTime, adminNDTrapSeqNo,
			  multiMeterIndex }
	DESCRIPTION	"This trap is generated when set
			multiMeterNotConnectedTrapID equal 39 and
 			the multimeter is disconnected."
	::= 38951

    multiMeterNotConnected40	TRAP-TYPE
	ENTERPRISE	network-device
	VARIABLES	{ multiMeterStatus,
			  adminDateAndTime, adminNDTrapSeqNo,
			  multiMeterIndex }
	DESCRIPTION	"This trap is generated when set
			multiMeterNotConnectedTrapID equal 40 and
 			the multimeter is disconnected."
	::= 38952

    multiMeterNotConnected41	TRAP-TYPE
	ENTERPRISE	network-device
	VARIABLES	{ multiMeterStatus,
			  adminDateAndTime, adminNDTrapSeqNo,
			  multiMeterIndex }
	DESCRIPTION	"This trap is generated when set
			multiMeterNotConnectedTrapID equal 41 and
 			the multimeter is disconnected."
	::= 38953

    multiMeterNotConnected42	TRAP-TYPE
	ENTERPRISE	network-device
	VARIABLES	{ multiMeterStatus,
			  adminDateAndTime, adminNDTrapSeqNo,
			  multiMeterIndex }
	DESCRIPTION	"This trap is generated when set
			multiMeterNotConnectedTrapID equal 42 and
 			the multimeter is disconnected."
	::= 38954

    multiMeterNotConnected43	TRAP-TYPE
	ENTERPRISE	network-device
	VARIABLES	{ multiMeterStatus,
			  adminDateAndTime, adminNDTrapSeqNo,
			  multiMeterIndex }
	DESCRIPTION	"This trap is generated when set
			multiMeterNotConnectedTrapID equal 43 and
 			the multimeter is disconnected."
	::= 38955

    multiMeterNotConnected44	TRAP-TYPE
	ENTERPRISE	network-device
	VARIABLES	{ multiMeterStatus,
			  adminDateAndTime, adminNDTrapSeqNo,
			  multiMeterIndex }
	DESCRIPTION	"This trap is generated when set
			multiMeterNotConnectedTrapID equal 44 and
 			the multimeter is disconnected."
	::= 38956

    multiMeterNotConnected45	TRAP-TYPE
	ENTERPRISE	network-device
	VARIABLES	{ multiMeterStatus,
			  adminDateAndTime, adminNDTrapSeqNo,
			  multiMeterIndex }
	DESCRIPTION	"This trap is generated when set
			multiMeterNotConnectedTrapID equal 45 and
 			the multimeter is disconnected."
	::= 38957

    multiMeterNotConnected46	TRAP-TYPE
	ENTERPRISE	network-device
	VARIABLES	{ multiMeterStatus,
			  adminDateAndTime, adminNDTrapSeqNo,
			  multiMeterIndex }
	DESCRIPTION	"This trap is generated when set
			multiMeterNotConnectedTrapID equal 46 and
 			the multimeter is disconnected."
	::= 38958

    multiMeterNotConnected47	TRAP-TYPE
	ENTERPRISE	network-device
	VARIABLES	{ multiMeterStatus,
			  adminDateAndTime, adminNDTrapSeqNo,
			  multiMeterIndex }
	DESCRIPTION	"This trap is generated when set
			multiMeterNotConnectedTrapID equal 47 and
 			the multimeter is disconnected."
	::= 38959

    multiMeterNotConnected48	TRAP-TYPE
	ENTERPRISE	network-device
	VARIABLES	{ multiMeterStatus,
			  adminDateAndTime, adminNDTrapSeqNo,
			  multiMeterIndex }
	DESCRIPTION	"This trap is generated when set
			multiMeterNotConnectedTrapID equal 48 and
 			the multimeter is disconnected."
	::= 38960

    multiMeterNotConnected49	TRAP-TYPE
	ENTERPRISE	network-device
	VARIABLES	{ multiMeterStatus,
			  adminDateAndTime, adminNDTrapSeqNo,
			  multiMeterIndex }
	DESCRIPTION	"This trap is generated when set
			multiMeterNotConnectedTrapID equal 49 and
 			the multimeter is disconnected."
	::= 38961

    multiMeterNotConnected50	TRAP-TYPE
	ENTERPRISE	network-device
	VARIABLES	{ multiMeterStatus,
			  adminDateAndTime, adminNDTrapSeqNo,
			  multiMeterIndex }
	DESCRIPTION	"This trap is generated when set
			multiMeterNotConnectedTrapID equal 50 and
 			the multimeter is disconnected."
	::= 38962

    multiMeterNotConnected51	TRAP-TYPE
	ENTERPRISE	network-device
	VARIABLES	{ multiMeterStatus,
			  adminDateAndTime, adminNDTrapSeqNo,
			  multiMeterIndex }
	DESCRIPTION	"This trap is generated when set
			multiMeterNotConnectedTrapID equal 51 and
 			the multimeter is disconnected."
	::= 38963

    multiMeterNotConnected52	TRAP-TYPE
	ENTERPRISE	network-device
	VARIABLES	{ multiMeterStatus,
			  adminDateAndTime, adminNDTrapSeqNo,
			  multiMeterIndex }
	DESCRIPTION	"This trap is generated when set
			multiMeterNotConnectedTrapID equal 52 and
 			the multimeter is disconnected."
	::= 38964

    multiMeterNotConnected53	TRAP-TYPE
	ENTERPRISE	network-device
	VARIABLES	{ multiMeterStatus,
			  adminDateAndTime, adminNDTrapSeqNo,
			  multiMeterIndex }
	DESCRIPTION	"This trap is generated when set
			multiMeterNotConnectedTrapID equal 53 and
 			the multimeter is disconnected."
	::= 38965

    multiMeterNotConnected54	TRAP-TYPE
	ENTERPRISE	network-device
	VARIABLES	{ multiMeterStatus,
			  adminDateAndTime, adminNDTrapSeqNo,
			  multiMeterIndex }
	DESCRIPTION	"This trap is generated when set
			multiMeterNotConnectedTrapID equal 54 and
 			the multimeter is disconnected."
	::= 38966

    multiMeterNotConnected55	TRAP-TYPE
	ENTERPRISE	network-device
	VARIABLES	{ multiMeterStatus,
			  adminDateAndTime, adminNDTrapSeqNo,
			  multiMeterIndex }
	DESCRIPTION	"This trap is generated when set
			multiMeterNotConnectedTrapID equal 55 and
 			the multimeter is disconnected."
	::= 38967

    multiMeterNotConnected56	TRAP-TYPE
	ENTERPRISE	network-device
	VARIABLES	{ multiMeterStatus,
			  adminDateAndTime, adminNDTrapSeqNo,
			  multiMeterIndex }
	DESCRIPTION	"This trap is generated when set
			multiMeterNotConnectedTrapID equal 56 and
 			the multimeter is disconnected."
	::= 38968

    multiMeterNotConnected57	TRAP-TYPE
	ENTERPRISE	network-device
	VARIABLES	{ multiMeterStatus,
			  adminDateAndTime, adminNDTrapSeqNo,
			  multiMeterIndex }
	DESCRIPTION	"This trap is generated when set
			multiMeterNotConnectedTrapID equal 57 and
 			the multimeter is disconnected."
	::= 38969

    multiMeterNotConnected58	TRAP-TYPE
	ENTERPRISE	network-device
	VARIABLES	{ multiMeterStatus,
			  adminDateAndTime, adminNDTrapSeqNo,
			  multiMeterIndex }
	DESCRIPTION	"This trap is generated when set
			multiMeterNotConnectedTrapID equal 58 and
 			the multimeter is disconnected."
	::= 38970

    multiMeterNotConnected59	TRAP-TYPE
	ENTERPRISE	network-device
	VARIABLES	{ multiMeterStatus,
			  adminDateAndTime, adminNDTrapSeqNo,
			  multiMeterIndex }
	DESCRIPTION	"This trap is generated when set
			multiMeterNotConnectedTrapID equal 59 and
 			the multimeter is disconnected."
	::= 38971

    multiMeterNotConnected60	TRAP-TYPE
	ENTERPRISE	network-device
	VARIABLES	{ multiMeterStatus,
			  adminDateAndTime, adminNDTrapSeqNo,
			  multiMeterIndex }
	DESCRIPTION	"This trap is generated when set
			multiMeterNotConnectedTrapID equal 60 and
 			the multimeter is disconnected."
	::= 38972

    multiMeterNotConnected61	TRAP-TYPE
	ENTERPRISE	network-device
	VARIABLES	{ multiMeterStatus,
			  adminDateAndTime, adminNDTrapSeqNo,
			  multiMeterIndex }
	DESCRIPTION	"This trap is generated when set
			multiMeterNotConnectedTrapID equal 61 and
 			the multimeter is disconnected."
	::= 38973

    multiMeterNotConnected62	TRAP-TYPE
	ENTERPRISE	network-device
	VARIABLES	{ multiMeterStatus,
			  adminDateAndTime, adminNDTrapSeqNo,
			  multiMeterIndex }
	DESCRIPTION	"This trap is generated when set
			multiMeterNotConnectedTrapID equal 62 and
 			the multimeter is disconnected."
	::= 38974

    multiMeterNotConnected63	TRAP-TYPE
	ENTERPRISE	network-device
	VARIABLES	{ multiMeterStatus,
			  adminDateAndTime, adminNDTrapSeqNo,
			  multiMeterIndex }
	DESCRIPTION	"This trap is generated when set
			multiMeterNotConnectedTrapID equal 63 and
 			the multimeter is disconnected."
	::= 38975

    multiMeterNotConnected64	TRAP-TYPE
	ENTERPRISE	network-device
	VARIABLES	{ multiMeterStatus,
			  adminDateAndTime, adminNDTrapSeqNo,
			  multiMeterIndex }
	DESCRIPTION	"This trap is generated when set
			multiMeterNotConnectedTrapID equal 64 and
 			the multimeter is disconnected."
	::= 38976

    multiMeterNotConnected65	TRAP-TYPE
	ENTERPRISE	network-device
	VARIABLES	{ multiMeterStatus,
			  adminDateAndTime, adminNDTrapSeqNo,
			  multiMeterIndex }
	DESCRIPTION	"This trap is generated when set
			multiMeterNotConnectedTrapID equal 65 and
 			the multimeter is disconnected."
	::= 38977

    multiMeterNotConnected66	TRAP-TYPE
	ENTERPRISE	network-device
	VARIABLES	{ multiMeterStatus,
			  adminDateAndTime, adminNDTrapSeqNo,
			  multiMeterIndex }
	DESCRIPTION	"This trap is generated when set
			multiMeterNotConnectedTrapID equal 66 and
 			the multimeter is disconnected."
	::= 38978

    multiMeterNotConnected67	TRAP-TYPE
	ENTERPRISE	network-device
	VARIABLES	{ multiMeterStatus,
			  adminDateAndTime, adminNDTrapSeqNo,
			  multiMeterIndex }
	DESCRIPTION	"This trap is generated when set
			multiMeterNotConnectedTrapID equal 67 and
 			the multimeter is disconnected."
	::= 38979

    multiMeterNotConnected68	TRAP-TYPE
	ENTERPRISE	network-device
	VARIABLES	{ multiMeterStatus,
			  adminDateAndTime, adminNDTrapSeqNo,
			  multiMeterIndex }
	DESCRIPTION	"This trap is generated when set
			multiMeterNotConnectedTrapID equal 68 and
 			the multimeter is disconnected."
	::= 38980

    multiMeterNotConnected69	TRAP-TYPE
	ENTERPRISE	network-device
	VARIABLES	{ multiMeterStatus,
			  adminDateAndTime, adminNDTrapSeqNo,
			  multiMeterIndex }
	DESCRIPTION	"This trap is generated when set
			multiMeterNotConnectedTrapID equal 69 and
 			the multimeter is disconnected."
	::= 38981

    multiMeterNotConnected70	TRAP-TYPE
	ENTERPRISE	network-device
	VARIABLES	{ multiMeterStatus,
			  adminDateAndTime, adminNDTrapSeqNo,
			  multiMeterIndex }
	DESCRIPTION	"This trap is generated when set
			multiMeterNotConnectedTrapID equal 70 and
 			the multimeter is disconnected."
	::= 38982

    multiMeterNotConnected71	TRAP-TYPE
	ENTERPRISE	network-device
	VARIABLES	{ multiMeterStatus,
			  adminDateAndTime, adminNDTrapSeqNo,
			  multiMeterIndex }
	DESCRIPTION	"This trap is generated when set
			multiMeterNotConnectedTrapID equal 71 and
 			the multimeter is disconnected."
	::= 38983

    multiMeterNotConnected72	TRAP-TYPE
	ENTERPRISE	network-device
	VARIABLES	{ multiMeterStatus,
			  adminDateAndTime, adminNDTrapSeqNo,
			  multiMeterIndex }
	DESCRIPTION	"This trap is generated when set
			multiMeterNotConnectedTrapID equal 72 and
 			the multimeter is disconnected."
	::= 38984

    multiMeterNotConnected73	TRAP-TYPE
	ENTERPRISE	network-device
	VARIABLES	{ multiMeterStatus,
			  adminDateAndTime, adminNDTrapSeqNo,
			  multiMeterIndex }
	DESCRIPTION	"This trap is generated when set
			multiMeterNotConnectedTrapID equal 73 and
 			the multimeter is disconnected."
	::= 38985

    multiMeterNotConnected74	TRAP-TYPE
	ENTERPRISE	network-device
	VARIABLES	{ multiMeterStatus,
			  adminDateAndTime, adminNDTrapSeqNo,
			  multiMeterIndex }
	DESCRIPTION	"This trap is generated when set
			multiMeterNotConnectedTrapID equal 74 and
 			the multimeter is disconnected."
	::= 38986

    multiMeterNotConnected75	TRAP-TYPE
	ENTERPRISE	network-device
	VARIABLES	{ multiMeterStatus,
			  adminDateAndTime, adminNDTrapSeqNo,
			  multiMeterIndex }
	DESCRIPTION	"This trap is generated when set
			multiMeterNotConnectedTrapID equal 75 and
 			the multimeter is disconnected."
	::= 38987

    multiMeterNotConnected76	TRAP-TYPE
	ENTERPRISE	network-device
	VARIABLES	{ multiMeterStatus,
			  adminDateAndTime, adminNDTrapSeqNo,
			  multiMeterIndex }
	DESCRIPTION	"This trap is generated when set
			multiMeterNotConnectedTrapID equal 76 and
 			the multimeter is disconnected."
	::= 38988

    multiMeterNotConnected77	TRAP-TYPE
	ENTERPRISE	network-device
	VARIABLES	{ multiMeterStatus,
			  adminDateAndTime, adminNDTrapSeqNo,
			  multiMeterIndex }
	DESCRIPTION	"This trap is generated when set
			multiMeterNotConnectedTrapID equal 77 and
 			the multimeter is disconnected."
	::= 38989

    multiMeterNotConnected78	TRAP-TYPE
	ENTERPRISE	network-device
	VARIABLES	{ multiMeterStatus,
			  adminDateAndTime, adminNDTrapSeqNo,
			  multiMeterIndex }
	DESCRIPTION	"This trap is generated when set
			multiMeterNotConnectedTrapID equal 78 and
 			the multimeter is disconnected."
	::= 38990

    multiMeterNotConnected79	TRAP-TYPE
	ENTERPRISE	network-device
	VARIABLES	{ multiMeterStatus,
			  adminDateAndTime, adminNDTrapSeqNo,
			  multiMeterIndex }
	DESCRIPTION	"This trap is generated when set
			multiMeterNotConnectedTrapID equal 79 and
 			the multimeter is disconnected."
	::= 38991

    multiMeterNotConnected80	TRAP-TYPE
	ENTERPRISE	network-device
	VARIABLES	{ multiMeterStatus,
			  adminDateAndTime, adminNDTrapSeqNo,
			  multiMeterIndex }
	DESCRIPTION	"This trap is generated when set
			multiMeterNotConnectedTrapID equal 80 and
 			the multimeter is disconnected."
	::= 38992

    multiMeterNotConnected81	TRAP-TYPE
	ENTERPRISE	network-device
	VARIABLES	{ multiMeterStatus,
			  adminDateAndTime, adminNDTrapSeqNo,
			  multiMeterIndex }
	DESCRIPTION	"This trap is generated when set
			multiMeterNotConnectedTrapID equal 81 and
 			the multimeter is disconnected."
	::= 38993

    multiMeterNotConnected82	TRAP-TYPE
	ENTERPRISE	network-device
	VARIABLES	{ multiMeterStatus,
			  adminDateAndTime, adminNDTrapSeqNo,
			  multiMeterIndex }
	DESCRIPTION	"This trap is generated when set
			multiMeterNotConnectedTrapID equal 82 and
 			the multimeter is disconnected."
	::= 38994

    multiMeterNotConnected83	TRAP-TYPE
	ENTERPRISE	network-device
	VARIABLES	{ multiMeterStatus,
			  adminDateAndTime, adminNDTrapSeqNo,
			  multiMeterIndex }
	DESCRIPTION	"This trap is generated when set
			multiMeterNotConnectedTrapID equal 83 and
 			the multimeter is disconnected."
	::= 38995

    multiMeterNotConnected84	TRAP-TYPE
	ENTERPRISE	network-device
	VARIABLES	{ multiMeterStatus,
			  adminDateAndTime, adminNDTrapSeqNo,
			  multiMeterIndex }
	DESCRIPTION	"This trap is generated when set
			multiMeterNotConnectedTrapID equal 84 and
 			the multimeter is disconnected."
	::= 38996

    multiMeterNotConnected85	TRAP-TYPE
	ENTERPRISE	network-device
	VARIABLES	{ multiMeterStatus,
			  adminDateAndTime, adminNDTrapSeqNo,
			  multiMeterIndex }
	DESCRIPTION	"This trap is generated when set
			multiMeterNotConnectedTrapID equal 85 and
 			the multimeter is disconnected."
	::= 38997

    multiMeterNotConnected86	TRAP-TYPE
	ENTERPRISE	network-device
	VARIABLES	{ multiMeterStatus,
			  adminDateAndTime, adminNDTrapSeqNo,
			  multiMeterIndex }
	DESCRIPTION	"This trap is generated when set
			multiMeterNotConnectedTrapID equal 86 and
 			the multimeter is disconnected."
	::= 38998

    multiMeterNotConnected87	TRAP-TYPE
	ENTERPRISE	network-device
	VARIABLES	{ multiMeterStatus,
			  adminDateAndTime, adminNDTrapSeqNo,
			  multiMeterIndex }
	DESCRIPTION	"This trap is generated when set
			multiMeterNotConnectedTrapID equal 87 and
 			the multimeter is disconnected."
	::= 38999

    multiMeterNotConnected88	TRAP-TYPE
	ENTERPRISE	network-device
	VARIABLES	{ multiMeterStatus,
			  adminDateAndTime, adminNDTrapSeqNo,
			  multiMeterIndex }
	DESCRIPTION	"This trap is generated when set
			multiMeterNotConnectedTrapID equal 88 and
 			the multimeter is disconnected."
	::= 39000

    multiMeterNotConnected89	TRAP-TYPE
	ENTERPRISE	network-device
	VARIABLES	{ multiMeterStatus,
			  adminDateAndTime, adminNDTrapSeqNo,
			  multiMeterIndex }
	DESCRIPTION	"This trap is generated when set
			multiMeterNotConnectedTrapID equal 89 and
 			the multimeter is disconnected."
	::= 39001

    multiMeterNotConnected90	TRAP-TYPE
	ENTERPRISE	network-device
	VARIABLES	{ multiMeterStatus,
			  adminDateAndTime, adminNDTrapSeqNo,
			  multiMeterIndex }
	DESCRIPTION	"This trap is generated when set
			multiMeterNotConnectedTrapID equal 90 and
 			the multimeter is disconnected."
	::= 39002

    multiMeterNotConnected91	TRAP-TYPE
	ENTERPRISE	network-device
	VARIABLES	{ multiMeterStatus,
			  adminDateAndTime, adminNDTrapSeqNo,
			  multiMeterIndex }
	DESCRIPTION	"This trap is generated when set
			multiMeterNotConnectedTrapID equal 91 and
 			the multimeter is disconnected."
	::= 39003

    multiMeterNotConnected92	TRAP-TYPE
	ENTERPRISE	network-device
	VARIABLES	{ multiMeterStatus,
			  adminDateAndTime, adminNDTrapSeqNo,
			  multiMeterIndex }
	DESCRIPTION	"This trap is generated when set
			multiMeterNotConnectedTrapID equal 92 and
 			the multimeter is disconnected."
	::= 39004

    multiMeterNotConnected93	TRAP-TYPE
	ENTERPRISE	network-device
	VARIABLES	{ multiMeterStatus,
			  adminDateAndTime, adminNDTrapSeqNo,
			  multiMeterIndex }
	DESCRIPTION	"This trap is generated when set
			multiMeterNotConnectedTrapID equal 93 and
 			the multimeter is disconnected."
	::= 39005

    multiMeterNotConnected94	TRAP-TYPE
	ENTERPRISE	network-device
	VARIABLES	{ multiMeterStatus,
			  adminDateAndTime, adminNDTrapSeqNo,
			  multiMeterIndex }
	DESCRIPTION	"This trap is generated when set
			multiMeterNotConnectedTrapID equal 94 and
 			the multimeter is disconnected."
	::= 39006

    multiMeterNotConnected95	TRAP-TYPE
	ENTERPRISE	network-device
	VARIABLES	{ multiMeterStatus,
			  adminDateAndTime, adminNDTrapSeqNo,
			  multiMeterIndex }
	DESCRIPTION	"This trap is generated when set
			multiMeterNotConnectedTrapID equal 95 and
 			the multimeter is disconnected."
	::= 39007

    multiMeterNotConnected96	TRAP-TYPE
	ENTERPRISE	network-device
	VARIABLES	{ multiMeterStatus,
			  adminDateAndTime, adminNDTrapSeqNo,
			  multiMeterIndex }
	DESCRIPTION	"This trap is generated when set
			multiMeterNotConnectedTrapID equal 96 and
 			the multimeter is disconnected."
	::= 39008

    multiMeterNotConnected97	TRAP-TYPE
	ENTERPRISE	network-device
	VARIABLES	{ multiMeterStatus,
			  adminDateAndTime, adminNDTrapSeqNo,
			  multiMeterIndex }
	DESCRIPTION	"This trap is generated when set
			multiMeterNotConnectedTrapID equal 97 and
 			the multimeter is disconnected."
	::= 39009

    multiMeterNotConnected98	TRAP-TYPE
	ENTERPRISE	network-device
	VARIABLES	{ multiMeterStatus,
			  adminDateAndTime, adminNDTrapSeqNo,
			  multiMeterIndex }
	DESCRIPTION	"This trap is generated when set
			multiMeterNotConnectedTrapID equal 98 and
 			the multimeter is disconnected."
	::= 39010

    multiMeterNotConnected99	TRAP-TYPE
	ENTERPRISE	network-device
	VARIABLES	{ multiMeterStatus,
			  adminDateAndTime, adminNDTrapSeqNo,
			  multiMeterIndex }
	DESCRIPTION	"This trap is generated when set
			multiMeterNotConnectedTrapID equal 99 and
 			the multimeter is disconnected."
	::= 39011

    multiMeterNotConnected100	TRAP-TYPE
	ENTERPRISE	network-device
	VARIABLES	{ multiMeterStatus,
			  adminDateAndTime, adminNDTrapSeqNo,
			  multiMeterIndex }
	DESCRIPTION	"This trap is generated when set
			multiMeterNotConnectedTrapID equal 100 and
 			the multimeter is disconnected."
	::= 39012

    multiMeterNotConnected101	TRAP-TYPE
	ENTERPRISE	network-device
	VARIABLES	{ multiMeterStatus,
			  adminDateAndTime, adminNDTrapSeqNo,
			  multiMeterIndex }
	DESCRIPTION	"This trap is generated when set
			multiMeterNotConnectedTrapID equal 101 and
 			the multimeter is disconnected."
	::= 39013

    multiMeterNotConnected102	TRAP-TYPE
	ENTERPRISE	network-device
	VARIABLES	{ multiMeterStatus,
			  adminDateAndTime, adminNDTrapSeqNo,
			  multiMeterIndex }
	DESCRIPTION	"This trap is generated when set
			multiMeterNotConnectedTrapID equal 102 and
 			the multimeter is disconnected."
	::= 39014

    multiMeterNotConnected103	TRAP-TYPE
	ENTERPRISE	network-device
	VARIABLES	{ multiMeterStatus,
			  adminDateAndTime, adminNDTrapSeqNo,
			  multiMeterIndex }
	DESCRIPTION	"This trap is generated when set
			multiMeterNotConnectedTrapID equal 103 and
 			the multimeter is disconnected."
	::= 39015

    multiMeterNotConnected104	TRAP-TYPE
	ENTERPRISE	network-device
	VARIABLES	{ multiMeterStatus,
			  adminDateAndTime, adminNDTrapSeqNo,
			  multiMeterIndex }
	DESCRIPTION	"This trap is generated when set
			multiMeterNotConnectedTrapID equal 104 and
 			the multimeter is disconnected."
	::= 39016

    multiMeterNotConnected105	TRAP-TYPE
	ENTERPRISE	network-device
	VARIABLES	{ multiMeterStatus,
			  adminDateAndTime, adminNDTrapSeqNo,
			  multiMeterIndex }
	DESCRIPTION	"This trap is generated when set
			multiMeterNotConnectedTrapID equal 105 and
 			the multimeter is disconnected."
	::= 39017

    multiMeterNotConnected106	TRAP-TYPE
	ENTERPRISE	network-device
	VARIABLES	{ multiMeterStatus,
			  adminDateAndTime, adminNDTrapSeqNo,
			  multiMeterIndex }
	DESCRIPTION	"This trap is generated when set
			multiMeterNotConnectedTrapID equal 106 and
 			the multimeter is disconnected."
	::= 39018

    multiMeterNotConnected107	TRAP-TYPE
	ENTERPRISE	network-device
	VARIABLES	{ multiMeterStatus,
			  adminDateAndTime, adminNDTrapSeqNo,
			  multiMeterIndex }
	DESCRIPTION	"This trap is generated when set
			multiMeterNotConnectedTrapID equal 107 and
 			the multimeter is disconnected."
	::= 39019

    multiMeterNotConnected108	TRAP-TYPE
	ENTERPRISE	network-device
	VARIABLES	{ multiMeterStatus,
			  adminDateAndTime, adminNDTrapSeqNo,
			  multiMeterIndex }
	DESCRIPTION	"This trap is generated when set
			multiMeterNotConnectedTrapID equal 108 and
 			the multimeter is disconnected."
	::= 39020

    multiMeterNotConnected109	TRAP-TYPE
	ENTERPRISE	network-device
	VARIABLES	{ multiMeterStatus,
			  adminDateAndTime, adminNDTrapSeqNo,
			  multiMeterIndex }
	DESCRIPTION	"This trap is generated when set
			multiMeterNotConnectedTrapID equal 109 and
 			the multimeter is disconnected."
	::= 39021

    multiMeterNotConnected110	TRAP-TYPE
	ENTERPRISE	network-device
	VARIABLES	{ multiMeterStatus,
			  adminDateAndTime, adminNDTrapSeqNo,
			  multiMeterIndex }
	DESCRIPTION	"This trap is generated when set
			multiMeterNotConnectedTrapID equal 110 and
 			the multimeter is disconnected."
	::= 39022

    multiMeterNotConnected111	TRAP-TYPE
	ENTERPRISE	network-device
	VARIABLES	{ multiMeterStatus,
			  adminDateAndTime, adminNDTrapSeqNo,
			  multiMeterIndex }
	DESCRIPTION	"This trap is generated when set
			multiMeterNotConnectedTrapID equal 111 and
 			the multimeter is disconnected."
	::= 39023

    multiMeterNotConnected112	TRAP-TYPE
	ENTERPRISE	network-device
	VARIABLES	{ multiMeterStatus,
			  adminDateAndTime, adminNDTrapSeqNo,
			  multiMeterIndex }
	DESCRIPTION	"This trap is generated when set
			multiMeterNotConnectedTrapID equal 112 and
 			the multimeter is disconnected."
	::= 39024

    multiMeterNotConnected113	TRAP-TYPE
	ENTERPRISE	network-device
	VARIABLES	{ multiMeterStatus,
			  adminDateAndTime, adminNDTrapSeqNo,
			  multiMeterIndex }
	DESCRIPTION	"This trap is generated when set
			multiMeterNotConnectedTrapID equal 113 and
 			the multimeter is disconnected."
	::= 39025

    multiMeterNotConnected114	TRAP-TYPE
	ENTERPRISE	network-device
	VARIABLES	{ multiMeterStatus,
			  adminDateAndTime, adminNDTrapSeqNo,
			  multiMeterIndex }
	DESCRIPTION	"This trap is generated when set
			multiMeterNotConnectedTrapID equal 114 and
 			the multimeter is disconnected."
	::= 39026

    multiMeterNotConnected115	TRAP-TYPE
	ENTERPRISE	network-device
	VARIABLES	{ multiMeterStatus,
			  adminDateAndTime, adminNDTrapSeqNo,
			  multiMeterIndex }
	DESCRIPTION	"This trap is generated when set
			multiMeterNotConnectedTrapID equal 115 and
 			the multimeter is disconnected."
	::= 39027

    multiMeterNotConnected116	TRAP-TYPE
	ENTERPRISE	network-device
	VARIABLES	{ multiMeterStatus,
			  adminDateAndTime, adminNDTrapSeqNo,
			  multiMeterIndex }
	DESCRIPTION	"This trap is generated when set
			multiMeterNotConnectedTrapID equal 116 and
 			the multimeter is disconnected."
	::= 39028

    multiMeterNotConnected117	TRAP-TYPE
	ENTERPRISE	network-device
	VARIABLES	{ multiMeterStatus,
			  adminDateAndTime, adminNDTrapSeqNo,
			  multiMeterIndex }
	DESCRIPTION	"This trap is generated when set
			multiMeterNotConnectedTrapID equal 117 and
 			the multimeter is disconnected."
	::= 39029

    multiMeterNotConnected118	TRAP-TYPE
	ENTERPRISE	network-device
	VARIABLES	{ multiMeterStatus,
			  adminDateAndTime, adminNDTrapSeqNo,
			  multiMeterIndex }
	DESCRIPTION	"This trap is generated when set
			multiMeterNotConnectedTrapID equal 118 and
 			the multimeter is disconnected."
	::= 39030

    multiMeterNotConnected119	TRAP-TYPE
	ENTERPRISE	network-device
	VARIABLES	{ multiMeterStatus,
			  adminDateAndTime, adminNDTrapSeqNo,
			  multiMeterIndex }
	DESCRIPTION	"This trap is generated when set
			multiMeterNotConnectedTrapID equal 119 and
 			the multimeter is disconnected."
	::= 39031

    multiMeterNotConnected120	TRAP-TYPE
	ENTERPRISE	network-device
	VARIABLES	{ multiMeterStatus,
			  adminDateAndTime, adminNDTrapSeqNo,
			  multiMeterIndex }
	DESCRIPTION	"This trap is generated when set
			multiMeterNotConnectedTrapID equal 120 and
 			the multimeter is disconnected."
	::= 39032

    multiMeterNotConnected121	TRAP-TYPE
	ENTERPRISE	network-device
	VARIABLES	{ multiMeterStatus,
			  adminDateAndTime, adminNDTrapSeqNo,
			  multiMeterIndex }
	DESCRIPTION	"This trap is generated when set
			multiMeterNotConnectedTrapID equal 121 and
 			the multimeter is disconnected."
	::= 39033

    multiMeterNotConnected122	TRAP-TYPE
	ENTERPRISE	network-device
	VARIABLES	{ multiMeterStatus,
			  adminDateAndTime, adminNDTrapSeqNo,
			  multiMeterIndex }
	DESCRIPTION	"This trap is generated when set
			multiMeterNotConnectedTrapID equal 122 and
 			the multimeter is disconnected."
	::= 39034

    multiMeterNotConnected123	TRAP-TYPE
	ENTERPRISE	network-device
	VARIABLES	{ multiMeterStatus,
			  adminDateAndTime, adminNDTrapSeqNo,
			  multiMeterIndex }
	DESCRIPTION	"This trap is generated when set
			multiMeterNotConnectedTrapID equal 123 and
 			the multimeter is disconnected."
	::= 39035

    multiMeterNotConnected124	TRAP-TYPE
	ENTERPRISE	network-device
	VARIABLES	{ multiMeterStatus,
			  adminDateAndTime, adminNDTrapSeqNo,
			  multiMeterIndex }
	DESCRIPTION	"This trap is generated when set
			multiMeterNotConnectedTrapID equal 124 and
 			the multimeter is disconnected."
	::= 39036

    multiMeterNotConnected125	TRAP-TYPE
	ENTERPRISE	network-device
	VARIABLES	{ multiMeterStatus,
			  adminDateAndTime, adminNDTrapSeqNo,
			  multiMeterIndex }
	DESCRIPTION	"This trap is generated when set
			multiMeterNotConnectedTrapID equal 125 and
 			the multimeter is disconnected."
	::= 39037

    multiMeterNotConnected126	TRAP-TYPE
	ENTERPRISE	network-device
	VARIABLES	{ multiMeterStatus,
			  adminDateAndTime, adminNDTrapSeqNo,
			  multiMeterIndex }
	DESCRIPTION	"This trap is generated when set
			multiMeterNotConnectedTrapID equal 126 and
 			the multimeter is disconnected."
	::= 39038

    multiMeterNotConnected127	TRAP-TYPE
	ENTERPRISE	network-device
	VARIABLES	{ multiMeterStatus,
			  adminDateAndTime, adminNDTrapSeqNo,
			  multiMeterIndex }
	DESCRIPTION	"This trap is generated when set
			multiMeterNotConnectedTrapID equal 127 and
 			the multimeter is disconnected."
	::= 39039

    multiMeterConnected1	TRAP-TYPE
	ENTERPRISE	network-device
	VARIABLES	{ multiMeterStatus,
			  adminDateAndTime, adminNDTrapSeqNo,
			  multiMeterIndex }
	DESCRIPTION	"This trap is generated when set
			multiMeterConnectedTrapID equal 1 and
 			the multimeter is connected."
	::= 39425

    multiMeterConnected2	TRAP-TYPE
	ENTERPRISE	network-device
	VARIABLES	{ multiMeterStatus,
			  adminDateAndTime, adminNDTrapSeqNo,
			  multiMeterIndex }
	DESCRIPTION	"This trap is generated when set
			multiMeterConnectedTrapID equal 2 and
 			the multimeter is connected."
	::= 39426

    multiMeterConnected3	TRAP-TYPE
	ENTERPRISE	network-device
	VARIABLES	{ multiMeterStatus,
			  adminDateAndTime, adminNDTrapSeqNo,
			  multiMeterIndex }
	DESCRIPTION	"This trap is generated when set
			multiMeterConnectedTrapID equal 3 and
 			the multimeter is connected."
	::= 39427

    multiMeterConnected4	TRAP-TYPE
	ENTERPRISE	network-device
	VARIABLES	{ multiMeterStatus,
			  adminDateAndTime, adminNDTrapSeqNo,
			  multiMeterIndex }
	DESCRIPTION	"This trap is generated when set
			multiMeterConnectedTrapID equal 4 and
 			the multimeter is connected."
	::= 39428

    multiMeterConnected5	TRAP-TYPE
	ENTERPRISE	network-device
	VARIABLES	{ multiMeterStatus,
			  adminDateAndTime, adminNDTrapSeqNo,
			  multiMeterIndex }
	DESCRIPTION	"This trap is generated when set
			multiMeterConnectedTrapID equal 5 and
 			the multimeter is connected."
	::= 39429

    multiMeterConnected6	TRAP-TYPE
	ENTERPRISE	network-device
	VARIABLES	{ multiMeterStatus,
			  adminDateAndTime, adminNDTrapSeqNo,
			  multiMeterIndex }
	DESCRIPTION	"This trap is generated when set
			multiMeterConnectedTrapID equal 6 and
 			the multimeter is connected."
	::= 39430

    multiMeterConnected7	TRAP-TYPE
	ENTERPRISE	network-device
	VARIABLES	{ multiMeterStatus,
			  adminDateAndTime, adminNDTrapSeqNo,
			  multiMeterIndex }
	DESCRIPTION	"This trap is generated when set
			multiMeterConnectedTrapID equal 7 and
 			the multimeter is connected."
	::= 39431

    multiMeterConnected8	TRAP-TYPE
	ENTERPRISE	network-device
	VARIABLES	{ multiMeterStatus,
			  adminDateAndTime, adminNDTrapSeqNo,
			  multiMeterIndex }
	DESCRIPTION	"This trap is generated when set
			multiMeterConnectedTrapID equal 8 and
 			the multimeter is connected."
	::= 39432

    multiMeterConnected9	TRAP-TYPE
	ENTERPRISE	network-device
	VARIABLES	{ multiMeterStatus,
			  adminDateAndTime, adminNDTrapSeqNo,
			  multiMeterIndex }
	DESCRIPTION	"This trap is generated when set
			multiMeterConnectedTrapID equal 9 and
 			the multimeter is connected."
	::= 39433

    multiMeterConnected10	TRAP-TYPE
	ENTERPRISE	network-device
	VARIABLES	{ multiMeterStatus,
			  adminDateAndTime, adminNDTrapSeqNo,
			  multiMeterIndex }
	DESCRIPTION	"This trap is generated when set
			multiMeterConnectedTrapID equal 10 and
 			the multimeter is connected."
	::= 39434

    multiMeterConnected11	TRAP-TYPE
	ENTERPRISE	network-device
	VARIABLES	{ multiMeterStatus,
			  adminDateAndTime, adminNDTrapSeqNo,
			  multiMeterIndex }
	DESCRIPTION	"This trap is generated when set
			multiMeterConnectedTrapID equal 11 and
 			the multimeter is connected."
	::= 39435

    multiMeterConnected12	TRAP-TYPE
	ENTERPRISE	network-device
	VARIABLES	{ multiMeterStatus,
			  adminDateAndTime, adminNDTrapSeqNo,
			  multiMeterIndex }
	DESCRIPTION	"This trap is generated when set
			multiMeterConnectedTrapID equal 12 and
 			the multimeter is connected."
	::= 39436

    multiMeterConnected13	TRAP-TYPE
	ENTERPRISE	network-device
	VARIABLES	{ multiMeterStatus,
			  adminDateAndTime, adminNDTrapSeqNo,
			  multiMeterIndex }
	DESCRIPTION	"This trap is generated when set
			multiMeterConnectedTrapID equal 13 and
 			the multimeter is connected."
	::= 39437

    multiMeterConnected14	TRAP-TYPE
	ENTERPRISE	network-device
	VARIABLES	{ multiMeterStatus,
			  adminDateAndTime, adminNDTrapSeqNo,
			  multiMeterIndex }
	DESCRIPTION	"This trap is generated when set
			multiMeterConnectedTrapID equal 14 and
 			the multimeter is connected."
	::= 39438

    multiMeterConnected15	TRAP-TYPE
	ENTERPRISE	network-device
	VARIABLES	{ multiMeterStatus,
			  adminDateAndTime, adminNDTrapSeqNo,
			  multiMeterIndex }
	DESCRIPTION	"This trap is generated when set
			multiMeterConnectedTrapID equal 15 and
 			the multimeter is connected."
	::= 39439

    multiMeterConnected16	TRAP-TYPE
	ENTERPRISE	network-device
	VARIABLES	{ multiMeterStatus,
			  adminDateAndTime, adminNDTrapSeqNo,
			  multiMeterIndex }
	DESCRIPTION	"This trap is generated when set
			multiMeterConnectedTrapID equal 16 and
 			the multimeter is connected."
	::= 39440

    multiMeterConnected17	TRAP-TYPE
	ENTERPRISE	network-device
	VARIABLES	{ multiMeterStatus,
			  adminDateAndTime, adminNDTrapSeqNo,
			  multiMeterIndex }
	DESCRIPTION	"This trap is generated when set
			multiMeterConnectedTrapID equal 17 and
 			the multimeter is connected."
	::= 39441

    multiMeterConnected18	TRAP-TYPE
	ENTERPRISE	network-device
	VARIABLES	{ multiMeterStatus,
			  adminDateAndTime, adminNDTrapSeqNo,
			  multiMeterIndex }
	DESCRIPTION	"This trap is generated when set
			multiMeterConnectedTrapID equal 18 and
 			the multimeter is connected."
	::= 39442

    multiMeterConnected19	TRAP-TYPE
	ENTERPRISE	network-device
	VARIABLES	{ multiMeterStatus,
			  adminDateAndTime, adminNDTrapSeqNo,
			  multiMeterIndex }
	DESCRIPTION	"This trap is generated when set
			multiMeterConnectedTrapID equal 19 and
 			the multimeter is connected."
	::= 39443

    multiMeterConnected20	TRAP-TYPE
	ENTERPRISE	network-device
	VARIABLES	{ multiMeterStatus,
			  adminDateAndTime, adminNDTrapSeqNo,
			  multiMeterIndex }
	DESCRIPTION	"This trap is generated when set
			multiMeterConnectedTrapID equal 20 and
 			the multimeter is connected."
	::= 39444

    multiMeterConnected21	TRAP-TYPE
	ENTERPRISE	network-device
	VARIABLES	{ multiMeterStatus,
			  adminDateAndTime, adminNDTrapSeqNo,
			  multiMeterIndex }
	DESCRIPTION	"This trap is generated when set
			multiMeterConnectedTrapID equal 21 and
 			the multimeter is connected."
	::= 39445

    multiMeterConnected22	TRAP-TYPE
	ENTERPRISE	network-device
	VARIABLES	{ multiMeterStatus,
			  adminDateAndTime, adminNDTrapSeqNo,
			  multiMeterIndex }
	DESCRIPTION	"This trap is generated when set
			multiMeterConnectedTrapID equal 22 and
 			the multimeter is connected."
	::= 39446

    multiMeterConnected23	TRAP-TYPE
	ENTERPRISE	network-device
	VARIABLES	{ multiMeterStatus,
			  adminDateAndTime, adminNDTrapSeqNo,
			  multiMeterIndex }
	DESCRIPTION	"This trap is generated when set
			multiMeterConnectedTrapID equal 23 and
 			the multimeter is connected."
	::= 39447

    multiMeterConnected24	TRAP-TYPE
	ENTERPRISE	network-device
	VARIABLES	{ multiMeterStatus,
			  adminDateAndTime, adminNDTrapSeqNo,
			  multiMeterIndex }
	DESCRIPTION	"This trap is generated when set
			multiMeterConnectedTrapID equal 24 and
 			the multimeter is connected."
	::= 39448

    multiMeterConnected25	TRAP-TYPE
	ENTERPRISE	network-device
	VARIABLES	{ multiMeterStatus,
			  adminDateAndTime, adminNDTrapSeqNo,
			  multiMeterIndex }
	DESCRIPTION	"This trap is generated when set
			multiMeterConnectedTrapID equal 25 and
 			the multimeter is connected."
	::= 39449

    multiMeterConnected26	TRAP-TYPE
	ENTERPRISE	network-device
	VARIABLES	{ multiMeterStatus,
			  adminDateAndTime, adminNDTrapSeqNo,
			  multiMeterIndex }
	DESCRIPTION	"This trap is generated when set
			multiMeterConnectedTrapID equal 26 and
 			the multimeter is connected."
	::= 39450

    multiMeterConnected27	TRAP-TYPE
	ENTERPRISE	network-device
	VARIABLES	{ multiMeterStatus,
			  adminDateAndTime, adminNDTrapSeqNo,
			  multiMeterIndex }
	DESCRIPTION	"This trap is generated when set
			multiMeterConnectedTrapID equal 27 and
 			the multimeter is connected."
	::= 39451

    multiMeterConnected28	TRAP-TYPE
	ENTERPRISE	network-device
	VARIABLES	{ multiMeterStatus,
			  adminDateAndTime, adminNDTrapSeqNo,
			  multiMeterIndex }
	DESCRIPTION	"This trap is generated when set
			multiMeterConnectedTrapID equal 28 and
 			the multimeter is connected."
	::= 39452

    multiMeterConnected29	TRAP-TYPE
	ENTERPRISE	network-device
	VARIABLES	{ multiMeterStatus,
			  adminDateAndTime, adminNDTrapSeqNo,
			  multiMeterIndex }
	DESCRIPTION	"This trap is generated when set
			multiMeterConnectedTrapID equal 29 and
 			the multimeter is connected."
	::= 39453

    multiMeterConnected30	TRAP-TYPE
	ENTERPRISE	network-device
	VARIABLES	{ multiMeterStatus,
			  adminDateAndTime, adminNDTrapSeqNo,
			  multiMeterIndex }
	DESCRIPTION	"This trap is generated when set
			multiMeterConnectedTrapID equal 30 and
 			the multimeter is connected."
	::= 39454

    multiMeterConnected31	TRAP-TYPE
	ENTERPRISE	network-device
	VARIABLES	{ multiMeterStatus,
			  adminDateAndTime, adminNDTrapSeqNo,
			  multiMeterIndex }
	DESCRIPTION	"This trap is generated when set
			multiMeterConnectedTrapID equal 31 and
 			the multimeter is connected."
	::= 39455

    multiMeterConnected32	TRAP-TYPE
	ENTERPRISE	network-device
	VARIABLES	{ multiMeterStatus,
			  adminDateAndTime, adminNDTrapSeqNo,
			  multiMeterIndex }
	DESCRIPTION	"This trap is generated when set
			multiMeterConnectedTrapID equal 32 and
 			the multimeter is connected."
	::= 39456

    multiMeterConnected33	TRAP-TYPE
	ENTERPRISE	network-device
	VARIABLES	{ multiMeterStatus,
			  adminDateAndTime, adminNDTrapSeqNo,
			  multiMeterIndex }
	DESCRIPTION	"This trap is generated when set
			multiMeterConnectedTrapID equal 33 and
 			the multimeter is connected."
	::= 39457

    multiMeterConnected34	TRAP-TYPE
	ENTERPRISE	network-device
	VARIABLES	{ multiMeterStatus,
			  adminDateAndTime, adminNDTrapSeqNo,
			  multiMeterIndex }
	DESCRIPTION	"This trap is generated when set
			multiMeterConnectedTrapID equal 34 and
 			the multimeter is connected."
	::= 39458

    multiMeterConnected35	TRAP-TYPE
	ENTERPRISE	network-device
	VARIABLES	{ multiMeterStatus,
			  adminDateAndTime, adminNDTrapSeqNo,
			  multiMeterIndex }
	DESCRIPTION	"This trap is generated when set
			multiMeterConnectedTrapID equal 35 and
 			the multimeter is connected."
	::= 39459

    multiMeterConnected36	TRAP-TYPE
	ENTERPRISE	network-device
	VARIABLES	{ multiMeterStatus,
			  adminDateAndTime, adminNDTrapSeqNo,
			  multiMeterIndex }
	DESCRIPTION	"This trap is generated when set
			multiMeterConnectedTrapID equal 36 and
 			the multimeter is connected."
	::= 39460

    multiMeterConnected37	TRAP-TYPE
	ENTERPRISE	network-device
	VARIABLES	{ multiMeterStatus,
			  adminDateAndTime, adminNDTrapSeqNo,
			  multiMeterIndex }
	DESCRIPTION	"This trap is generated when set
			multiMeterConnectedTrapID equal 37 and
 			the multimeter is connected."
	::= 39461

    multiMeterConnected38	TRAP-TYPE
	ENTERPRISE	network-device
	VARIABLES	{ multiMeterStatus,
			  adminDateAndTime, adminNDTrapSeqNo,
			  multiMeterIndex }
	DESCRIPTION	"This trap is generated when set
			multiMeterConnectedTrapID equal 38 and
 			the multimeter is connected."
	::= 39462

    multiMeterConnected39	TRAP-TYPE
	ENTERPRISE	network-device
	VARIABLES	{ multiMeterStatus,
			  adminDateAndTime, adminNDTrapSeqNo,
			  multiMeterIndex }
	DESCRIPTION	"This trap is generated when set
			multiMeterConnectedTrapID equal 39 and
 			the multimeter is connected."
	::= 39463

    multiMeterConnected40	TRAP-TYPE
	ENTERPRISE	network-device
	VARIABLES	{ multiMeterStatus,
			  adminDateAndTime, adminNDTrapSeqNo,
			  multiMeterIndex }
	DESCRIPTION	"This trap is generated when set
			multiMeterConnectedTrapID equal 40 and
 			the multimeter is connected."
	::= 39464

    multiMeterConnected41	TRAP-TYPE
	ENTERPRISE	network-device
	VARIABLES	{ multiMeterStatus,
			  adminDateAndTime, adminNDTrapSeqNo,
			  multiMeterIndex }
	DESCRIPTION	"This trap is generated when set
			multiMeterConnectedTrapID equal 41 and
 			the multimeter is connected."
	::= 39465

    multiMeterConnected42	TRAP-TYPE
	ENTERPRISE	network-device
	VARIABLES	{ multiMeterStatus,
			  adminDateAndTime, adminNDTrapSeqNo,
			  multiMeterIndex }
	DESCRIPTION	"This trap is generated when set
			multiMeterConnectedTrapID equal 42 and
 			the multimeter is connected."
	::= 39466

    multiMeterConnected43	TRAP-TYPE
	ENTERPRISE	network-device
	VARIABLES	{ multiMeterStatus,
			  adminDateAndTime, adminNDTrapSeqNo,
			  multiMeterIndex }
	DESCRIPTION	"This trap is generated when set
			multiMeterConnectedTrapID equal 43 and
 			the multimeter is connected."
	::= 39467

    multiMeterConnected44	TRAP-TYPE
	ENTERPRISE	network-device
	VARIABLES	{ multiMeterStatus,
			  adminDateAndTime, adminNDTrapSeqNo,
			  multiMeterIndex }
	DESCRIPTION	"This trap is generated when set
			multiMeterConnectedTrapID equal 44 and
 			the multimeter is connected."
	::= 39468

    multiMeterConnected45	TRAP-TYPE
	ENTERPRISE	network-device
	VARIABLES	{ multiMeterStatus,
			  adminDateAndTime, adminNDTrapSeqNo,
			  multiMeterIndex }
	DESCRIPTION	"This trap is generated when set
			multiMeterConnectedTrapID equal 45 and
 			the multimeter is connected."
	::= 39469

    multiMeterConnected46	TRAP-TYPE
	ENTERPRISE	network-device
	VARIABLES	{ multiMeterStatus,
			  adminDateAndTime, adminNDTrapSeqNo,
			  multiMeterIndex }
	DESCRIPTION	"This trap is generated when set
			multiMeterConnectedTrapID equal 46 and
 			the multimeter is connected."
	::= 39470

    multiMeterConnected47	TRAP-TYPE
	ENTERPRISE	network-device
	VARIABLES	{ multiMeterStatus,
			  adminDateAndTime, adminNDTrapSeqNo,
			  multiMeterIndex }
	DESCRIPTION	"This trap is generated when set
			multiMeterConnectedTrapID equal 47 and
 			the multimeter is connected."
	::= 39471

    multiMeterConnected48	TRAP-TYPE
	ENTERPRISE	network-device
	VARIABLES	{ multiMeterStatus,
			  adminDateAndTime, adminNDTrapSeqNo,
			  multiMeterIndex }
	DESCRIPTION	"This trap is generated when set
			multiMeterConnectedTrapID equal 48 and
 			the multimeter is connected."
	::= 39472

    multiMeterConnected49	TRAP-TYPE
	ENTERPRISE	network-device
	VARIABLES	{ multiMeterStatus,
			  adminDateAndTime, adminNDTrapSeqNo,
			  multiMeterIndex }
	DESCRIPTION	"This trap is generated when set
			multiMeterConnectedTrapID equal 49 and
 			the multimeter is connected."
	::= 39473

    multiMeterConnected50	TRAP-TYPE
	ENTERPRISE	network-device
	VARIABLES	{ multiMeterStatus,
			  adminDateAndTime, adminNDTrapSeqNo,
			  multiMeterIndex }
	DESCRIPTION	"This trap is generated when set
			multiMeterConnectedTrapID equal 50 and
 			the multimeter is connected."
	::= 39474

    multiMeterConnected51	TRAP-TYPE
	ENTERPRISE	network-device
	VARIABLES	{ multiMeterStatus,
			  adminDateAndTime, adminNDTrapSeqNo,
			  multiMeterIndex }
	DESCRIPTION	"This trap is generated when set
			multiMeterConnectedTrapID equal 51 and
 			the multimeter is connected."
	::= 39475

    multiMeterConnected52	TRAP-TYPE
	ENTERPRISE	network-device
	VARIABLES	{ multiMeterStatus,
			  adminDateAndTime, adminNDTrapSeqNo,
			  multiMeterIndex }
	DESCRIPTION	"This trap is generated when set
			multiMeterConnectedTrapID equal 52 and
 			the multimeter is connected."
	::= 39476

    multiMeterConnected53	TRAP-TYPE
	ENTERPRISE	network-device
	VARIABLES	{ multiMeterStatus,
			  adminDateAndTime, adminNDTrapSeqNo,
			  multiMeterIndex }
	DESCRIPTION	"This trap is generated when set
			multiMeterConnectedTrapID equal 53 and
 			the multimeter is connected."
	::= 39477

    multiMeterConnected54	TRAP-TYPE
	ENTERPRISE	network-device
	VARIABLES	{ multiMeterStatus,
			  adminDateAndTime, adminNDTrapSeqNo,
			  multiMeterIndex }
	DESCRIPTION	"This trap is generated when set
			multiMeterConnectedTrapID equal 54 and
 			the multimeter is connected."
	::= 39478

    multiMeterConnected55	TRAP-TYPE
	ENTERPRISE	network-device
	VARIABLES	{ multiMeterStatus,
			  adminDateAndTime, adminNDTrapSeqNo,
			  multiMeterIndex }
	DESCRIPTION	"This trap is generated when set
			multiMeterConnectedTrapID equal 55 and
 			the multimeter is connected."
	::= 39479

    multiMeterConnected56	TRAP-TYPE
	ENTERPRISE	network-device
	VARIABLES	{ multiMeterStatus,
			  adminDateAndTime, adminNDTrapSeqNo,
			  multiMeterIndex }
	DESCRIPTION	"This trap is generated when set
			multiMeterConnectedTrapID equal 56 and
 			the multimeter is connected."
	::= 39480

    multiMeterConnected57	TRAP-TYPE
	ENTERPRISE	network-device
	VARIABLES	{ multiMeterStatus,
			  adminDateAndTime, adminNDTrapSeqNo,
			  multiMeterIndex }
	DESCRIPTION	"This trap is generated when set
			multiMeterConnectedTrapID equal 57 and
 			the multimeter is connected."
	::= 39481

    multiMeterConnected58	TRAP-TYPE
	ENTERPRISE	network-device
	VARIABLES	{ multiMeterStatus,
			  adminDateAndTime, adminNDTrapSeqNo,
			  multiMeterIndex }
	DESCRIPTION	"This trap is generated when set
			multiMeterConnectedTrapID equal 58 and
 			the multimeter is connected."
	::= 39482

    multiMeterConnected59	TRAP-TYPE
	ENTERPRISE	network-device
	VARIABLES	{ multiMeterStatus,
			  adminDateAndTime, adminNDTrapSeqNo,
			  multiMeterIndex }
	DESCRIPTION	"This trap is generated when set
			multiMeterConnectedTrapID equal 59 and
 			the multimeter is connected."
	::= 39483

    multiMeterConnected60	TRAP-TYPE
	ENTERPRISE	network-device
	VARIABLES	{ multiMeterStatus,
			  adminDateAndTime, adminNDTrapSeqNo,
			  multiMeterIndex }
	DESCRIPTION	"This trap is generated when set
			multiMeterConnectedTrapID equal 60 and
 			the multimeter is connected."
	::= 39484

    multiMeterConnected61	TRAP-TYPE
	ENTERPRISE	network-device
	VARIABLES	{ multiMeterStatus,
			  adminDateAndTime, adminNDTrapSeqNo,
			  multiMeterIndex }
	DESCRIPTION	"This trap is generated when set
			multiMeterConnectedTrapID equal 61 and
 			the multimeter is connected."
	::= 39485

    multiMeterConnected62	TRAP-TYPE
	ENTERPRISE	network-device
	VARIABLES	{ multiMeterStatus,
			  adminDateAndTime, adminNDTrapSeqNo,
			  multiMeterIndex }
	DESCRIPTION	"This trap is generated when set
			multiMeterConnectedTrapID equal 62 and
 			the multimeter is connected."
	::= 39486

    multiMeterConnected63	TRAP-TYPE
	ENTERPRISE	network-device
	VARIABLES	{ multiMeterStatus,
			  adminDateAndTime, adminNDTrapSeqNo,
			  multiMeterIndex }
	DESCRIPTION	"This trap is generated when set
			multiMeterConnectedTrapID equal 63 and
 			the multimeter is connected."
	::= 39487

    multiMeterConnected64	TRAP-TYPE
	ENTERPRISE	network-device
	VARIABLES	{ multiMeterStatus,
			  adminDateAndTime, adminNDTrapSeqNo,
			  multiMeterIndex }
	DESCRIPTION	"This trap is generated when set
			multiMeterConnectedTrapID equal 64 and
 			the multimeter is connected."
	::= 39488

    multiMeterConnected65	TRAP-TYPE
	ENTERPRISE	network-device
	VARIABLES	{ multiMeterStatus,
			  adminDateAndTime, adminNDTrapSeqNo,
			  multiMeterIndex }
	DESCRIPTION	"This trap is generated when set
			multiMeterConnectedTrapID equal 65 and
 			the multimeter is connected."
	::= 39489

    multiMeterConnected66	TRAP-TYPE
	ENTERPRISE	network-device
	VARIABLES	{ multiMeterStatus,
			  adminDateAndTime, adminNDTrapSeqNo,
			  multiMeterIndex }
	DESCRIPTION	"This trap is generated when set
			multiMeterConnectedTrapID equal 66 and
 			the multimeter is connected."
	::= 39490

    multiMeterConnected67	TRAP-TYPE
	ENTERPRISE	network-device
	VARIABLES	{ multiMeterStatus,
			  adminDateAndTime, adminNDTrapSeqNo,
			  multiMeterIndex }
	DESCRIPTION	"This trap is generated when set
			multiMeterConnectedTrapID equal 67 and
 			the multimeter is connected."
	::= 39491

    multiMeterConnected68	TRAP-TYPE
	ENTERPRISE	network-device
	VARIABLES	{ multiMeterStatus,
			  adminDateAndTime, adminNDTrapSeqNo,
			  multiMeterIndex }
	DESCRIPTION	"This trap is generated when set
			multiMeterConnectedTrapID equal 68 and
 			the multimeter is connected."
	::= 39492

    multiMeterConnected69	TRAP-TYPE
	ENTERPRISE	network-device
	VARIABLES	{ multiMeterStatus,
			  adminDateAndTime, adminNDTrapSeqNo,
			  multiMeterIndex }
	DESCRIPTION	"This trap is generated when set
			multiMeterConnectedTrapID equal 69 and
 			the multimeter is connected."
	::= 39493

    multiMeterConnected70	TRAP-TYPE
	ENTERPRISE	network-device
	VARIABLES	{ multiMeterStatus,
			  adminDateAndTime, adminNDTrapSeqNo,
			  multiMeterIndex }
	DESCRIPTION	"This trap is generated when set
			multiMeterConnectedTrapID equal 70 and
 			the multimeter is connected."
	::= 39494

    multiMeterConnected71	TRAP-TYPE
	ENTERPRISE	network-device
	VARIABLES	{ multiMeterStatus,
			  adminDateAndTime, adminNDTrapSeqNo,
			  multiMeterIndex }
	DESCRIPTION	"This trap is generated when set
			multiMeterConnectedTrapID equal 71 and
 			the multimeter is connected."
	::= 39495

    multiMeterConnected72	TRAP-TYPE
	ENTERPRISE	network-device
	VARIABLES	{ multiMeterStatus,
			  adminDateAndTime, adminNDTrapSeqNo,
			  multiMeterIndex }
	DESCRIPTION	"This trap is generated when set
			multiMeterConnectedTrapID equal 72 and
 			the multimeter is connected."
	::= 39496

    multiMeterConnected73	TRAP-TYPE
	ENTERPRISE	network-device
	VARIABLES	{ multiMeterStatus,
			  adminDateAndTime, adminNDTrapSeqNo,
			  multiMeterIndex }
	DESCRIPTION	"This trap is generated when set
			multiMeterConnectedTrapID equal 73 and
 			the multimeter is connected."
	::= 39497

    multiMeterConnected74	TRAP-TYPE
	ENTERPRISE	network-device
	VARIABLES	{ multiMeterStatus,
			  adminDateAndTime, adminNDTrapSeqNo,
			  multiMeterIndex }
	DESCRIPTION	"This trap is generated when set
			multiMeterConnectedTrapID equal 74 and
 			the multimeter is connected."
	::= 39498

    multiMeterConnected75	TRAP-TYPE
	ENTERPRISE	network-device
	VARIABLES	{ multiMeterStatus,
			  adminDateAndTime, adminNDTrapSeqNo,
			  multiMeterIndex }
	DESCRIPTION	"This trap is generated when set
			multiMeterConnectedTrapID equal 75 and
 			the multimeter is connected."
	::= 39499

    multiMeterConnected76	TRAP-TYPE
	ENTERPRISE	network-device
	VARIABLES	{ multiMeterStatus,
			  adminDateAndTime, adminNDTrapSeqNo,
			  multiMeterIndex }
	DESCRIPTION	"This trap is generated when set
			multiMeterConnectedTrapID equal 76 and
 			the multimeter is connected."
	::= 39500

    multiMeterConnected77	TRAP-TYPE
	ENTERPRISE	network-device
	VARIABLES	{ multiMeterStatus,
			  adminDateAndTime, adminNDTrapSeqNo,
			  multiMeterIndex }
	DESCRIPTION	"This trap is generated when set
			multiMeterConnectedTrapID equal 77 and
 			the multimeter is connected."
	::= 39501

    multiMeterConnected78	TRAP-TYPE
	ENTERPRISE	network-device
	VARIABLES	{ multiMeterStatus,
			  adminDateAndTime, adminNDTrapSeqNo,
			  multiMeterIndex }
	DESCRIPTION	"This trap is generated when set
			multiMeterConnectedTrapID equal 78 and
 			the multimeter is connected."
	::= 39502

    multiMeterConnected79	TRAP-TYPE
	ENTERPRISE	network-device
	VARIABLES	{ multiMeterStatus,
			  adminDateAndTime, adminNDTrapSeqNo,
			  multiMeterIndex }
	DESCRIPTION	"This trap is generated when set
			multiMeterConnectedTrapID equal 79 and
 			the multimeter is connected."
	::= 39503

    multiMeterConnected80	TRAP-TYPE
	ENTERPRISE	network-device
	VARIABLES	{ multiMeterStatus,
			  adminDateAndTime, adminNDTrapSeqNo,
			  multiMeterIndex }
	DESCRIPTION	"This trap is generated when set
			multiMeterConnectedTrapID equal 80 and
 			the multimeter is connected."
	::= 39504

    multiMeterConnected81	TRAP-TYPE
	ENTERPRISE	network-device
	VARIABLES	{ multiMeterStatus,
			  adminDateAndTime, adminNDTrapSeqNo,
			  multiMeterIndex }
	DESCRIPTION	"This trap is generated when set
			multiMeterConnectedTrapID equal 81 and
 			the multimeter is connected."
	::= 39505

    multiMeterConnected82	TRAP-TYPE
	ENTERPRISE	network-device
	VARIABLES	{ multiMeterStatus,
			  adminDateAndTime, adminNDTrapSeqNo,
			  multiMeterIndex }
	DESCRIPTION	"This trap is generated when set
			multiMeterConnectedTrapID equal 82 and
 			the multimeter is connected."
	::= 39506

    multiMeterConnected83	TRAP-TYPE
	ENTERPRISE	network-device
	VARIABLES	{ multiMeterStatus,
			  adminDateAndTime, adminNDTrapSeqNo,
			  multiMeterIndex }
	DESCRIPTION	"This trap is generated when set
			multiMeterConnectedTrapID equal 83 and
 			the multimeter is connected."
	::= 39507

    multiMeterConnected84	TRAP-TYPE
	ENTERPRISE	network-device
	VARIABLES	{ multiMeterStatus,
			  adminDateAndTime, adminNDTrapSeqNo,
			  multiMeterIndex }
	DESCRIPTION	"This trap is generated when set
			multiMeterConnectedTrapID equal 84 and
 			the multimeter is connected."
	::= 39508

    multiMeterConnected85	TRAP-TYPE
	ENTERPRISE	network-device
	VARIABLES	{ multiMeterStatus,
			  adminDateAndTime, adminNDTrapSeqNo,
			  multiMeterIndex }
	DESCRIPTION	"This trap is generated when set
			multiMeterConnectedTrapID equal 85 and
 			the multimeter is connected."
	::= 39509

    multiMeterConnected86	TRAP-TYPE
	ENTERPRISE	network-device
	VARIABLES	{ multiMeterStatus,
			  adminDateAndTime, adminNDTrapSeqNo,
			  multiMeterIndex }
	DESCRIPTION	"This trap is generated when set
			multiMeterConnectedTrapID equal 86 and
 			the multimeter is connected."
	::= 39510

    multiMeterConnected87	TRAP-TYPE
	ENTERPRISE	network-device
	VARIABLES	{ multiMeterStatus,
			  adminDateAndTime, adminNDTrapSeqNo,
			  multiMeterIndex }
	DESCRIPTION	"This trap is generated when set
			multiMeterConnectedTrapID equal 87 and
 			the multimeter is connected."
	::= 39511

    multiMeterConnected88	TRAP-TYPE
	ENTERPRISE	network-device
	VARIABLES	{ multiMeterStatus,
			  adminDateAndTime, adminNDTrapSeqNo,
			  multiMeterIndex }
	DESCRIPTION	"This trap is generated when set
			multiMeterConnectedTrapID equal 88 and
 			the multimeter is connected."
	::= 39512

    multiMeterConnected89	TRAP-TYPE
	ENTERPRISE	network-device
	VARIABLES	{ multiMeterStatus,
			  adminDateAndTime, adminNDTrapSeqNo,
			  multiMeterIndex }
	DESCRIPTION	"This trap is generated when set
			multiMeterConnectedTrapID equal 89 and
 			the multimeter is connected."
	::= 39513

    multiMeterConnected90	TRAP-TYPE
	ENTERPRISE	network-device
	VARIABLES	{ multiMeterStatus,
			  adminDateAndTime, adminNDTrapSeqNo,
			  multiMeterIndex }
	DESCRIPTION	"This trap is generated when set
			multiMeterConnectedTrapID equal 90 and
 			the multimeter is connected."
	::= 39514

    multiMeterConnected91	TRAP-TYPE
	ENTERPRISE	network-device
	VARIABLES	{ multiMeterStatus,
			  adminDateAndTime, adminNDTrapSeqNo,
			  multiMeterIndex }
	DESCRIPTION	"This trap is generated when set
			multiMeterConnectedTrapID equal 91 and
 			the multimeter is connected."
	::= 39515

    multiMeterConnected92	TRAP-TYPE
	ENTERPRISE	network-device
	VARIABLES	{ multiMeterStatus,
			  adminDateAndTime, adminNDTrapSeqNo,
			  multiMeterIndex }
	DESCRIPTION	"This trap is generated when set
			multiMeterConnectedTrapID equal 92 and
 			the multimeter is connected."
	::= 39516

    multiMeterConnected93	TRAP-TYPE
	ENTERPRISE	network-device
	VARIABLES	{ multiMeterStatus,
			  adminDateAndTime, adminNDTrapSeqNo,
			  multiMeterIndex }
	DESCRIPTION	"This trap is generated when set
			multiMeterConnectedTrapID equal 93 and
 			the multimeter is connected."
	::= 39517

    multiMeterConnected94	TRAP-TYPE
	ENTERPRISE	network-device
	VARIABLES	{ multiMeterStatus,
			  adminDateAndTime, adminNDTrapSeqNo,
			  multiMeterIndex }
	DESCRIPTION	"This trap is generated when set
			multiMeterConnectedTrapID equal 94 and
 			the multimeter is connected."
	::= 39518

    multiMeterConnected95	TRAP-TYPE
	ENTERPRISE	network-device
	VARIABLES	{ multiMeterStatus,
			  adminDateAndTime, adminNDTrapSeqNo,
			  multiMeterIndex }
	DESCRIPTION	"This trap is generated when set
			multiMeterConnectedTrapID equal 95 and
 			the multimeter is connected."
	::= 39519

    multiMeterConnected96	TRAP-TYPE
	ENTERPRISE	network-device
	VARIABLES	{ multiMeterStatus,
			  adminDateAndTime, adminNDTrapSeqNo,
			  multiMeterIndex }
	DESCRIPTION	"This trap is generated when set
			multiMeterConnectedTrapID equal 96 and
 			the multimeter is connected."
	::= 39520

    multiMeterConnected97	TRAP-TYPE
	ENTERPRISE	network-device
	VARIABLES	{ multiMeterStatus,
			  adminDateAndTime, adminNDTrapSeqNo,
			  multiMeterIndex }
	DESCRIPTION	"This trap is generated when set
			multiMeterConnectedTrapID equal 97 and
 			the multimeter is connected."
	::= 39521

    multiMeterConnected98	TRAP-TYPE
	ENTERPRISE	network-device
	VARIABLES	{ multiMeterStatus,
			  adminDateAndTime, adminNDTrapSeqNo,
			  multiMeterIndex }
	DESCRIPTION	"This trap is generated when set
			multiMeterConnectedTrapID equal 98 and
 			the multimeter is connected."
	::= 39522

    multiMeterConnected99	TRAP-TYPE
	ENTERPRISE	network-device
	VARIABLES	{ multiMeterStatus,
			  adminDateAndTime, adminNDTrapSeqNo,
			  multiMeterIndex }
	DESCRIPTION	"This trap is generated when set
			multiMeterConnectedTrapID equal 99 and
 			the multimeter is connected."
	::= 39523

    multiMeterConnected100	TRAP-TYPE
	ENTERPRISE	network-device
	VARIABLES	{ multiMeterStatus,
			  adminDateAndTime, adminNDTrapSeqNo,
			  multiMeterIndex }
	DESCRIPTION	"This trap is generated when set
			multiMeterConnectedTrapID equal 100 and
 			the multimeter is connected."
	::= 39524

    multiMeterConnected101	TRAP-TYPE
	ENTERPRISE	network-device
	VARIABLES	{ multiMeterStatus,
			  adminDateAndTime, adminNDTrapSeqNo,
			  multiMeterIndex }
	DESCRIPTION	"This trap is generated when set
			multiMeterConnectedTrapID equal 101 and
 			the multimeter is connected."
	::= 39525

    multiMeterConnected102	TRAP-TYPE
	ENTERPRISE	network-device
	VARIABLES	{ multiMeterStatus,
			  adminDateAndTime, adminNDTrapSeqNo,
			  multiMeterIndex }
	DESCRIPTION	"This trap is generated when set
			multiMeterConnectedTrapID equal 102 and
 			the multimeter is connected."
	::= 39526

    multiMeterConnected103	TRAP-TYPE
	ENTERPRISE	network-device
	VARIABLES	{ multiMeterStatus,
			  adminDateAndTime, adminNDTrapSeqNo,
			  multiMeterIndex }
	DESCRIPTION	"This trap is generated when set
			multiMeterConnectedTrapID equal 103 and
 			the multimeter is connected."
	::= 39527

    multiMeterConnected104	TRAP-TYPE
	ENTERPRISE	network-device
	VARIABLES	{ multiMeterStatus,
			  adminDateAndTime, adminNDTrapSeqNo,
			  multiMeterIndex }
	DESCRIPTION	"This trap is generated when set
			multiMeterConnectedTrapID equal 104 and
 			the multimeter is connected."
	::= 39528

    multiMeterConnected105	TRAP-TYPE
	ENTERPRISE	network-device
	VARIABLES	{ multiMeterStatus,
			  adminDateAndTime, adminNDTrapSeqNo,
			  multiMeterIndex }
	DESCRIPTION	"This trap is generated when set
			multiMeterConnectedTrapID equal 105 and
 			the multimeter is connected."
	::= 39529

    multiMeterConnected106	TRAP-TYPE
	ENTERPRISE	network-device
	VARIABLES	{ multiMeterStatus,
			  adminDateAndTime, adminNDTrapSeqNo,
			  multiMeterIndex }
	DESCRIPTION	"This trap is generated when set
			multiMeterConnectedTrapID equal 106 and
 			the multimeter is connected."
	::= 39530

    multiMeterConnected107	TRAP-TYPE
	ENTERPRISE	network-device
	VARIABLES	{ multiMeterStatus,
			  adminDateAndTime, adminNDTrapSeqNo,
			  multiMeterIndex }
	DESCRIPTION	"This trap is generated when set
			multiMeterConnectedTrapID equal 107 and
 			the multimeter is connected."
	::= 39531

    multiMeterConnected108	TRAP-TYPE
	ENTERPRISE	network-device
	VARIABLES	{ multiMeterStatus,
			  adminDateAndTime, adminNDTrapSeqNo,
			  multiMeterIndex }
	DESCRIPTION	"This trap is generated when set
			multiMeterConnectedTrapID equal 108 and
 			the multimeter is connected."
	::= 39532

    multiMeterConnected109	TRAP-TYPE
	ENTERPRISE	network-device
	VARIABLES	{ multiMeterStatus,
			  adminDateAndTime, adminNDTrapSeqNo,
			  multiMeterIndex }
	DESCRIPTION	"This trap is generated when set
			multiMeterConnectedTrapID equal 109 and
 			the multimeter is connected."
	::= 39533

    multiMeterConnected110	TRAP-TYPE
	ENTERPRISE	network-device
	VARIABLES	{ multiMeterStatus,
			  adminDateAndTime, adminNDTrapSeqNo,
			  multiMeterIndex }
	DESCRIPTION	"This trap is generated when set
			multiMeterConnectedTrapID equal 110 and
 			the multimeter is connected."
	::= 39534

    multiMeterConnected111	TRAP-TYPE
	ENTERPRISE	network-device
	VARIABLES	{ multiMeterStatus,
			  adminDateAndTime, adminNDTrapSeqNo,
			  multiMeterIndex }
	DESCRIPTION	"This trap is generated when set
			multiMeterConnectedTrapID equal 111 and
 			the multimeter is connected."
	::= 39535

    multiMeterConnected112	TRAP-TYPE
	ENTERPRISE	network-device
	VARIABLES	{ multiMeterStatus,
			  adminDateAndTime, adminNDTrapSeqNo,
			  multiMeterIndex }
	DESCRIPTION	"This trap is generated when set
			multiMeterConnectedTrapID equal 112 and
 			the multimeter is connected."
	::= 39536

    multiMeterConnected113	TRAP-TYPE
	ENTERPRISE	network-device
	VARIABLES	{ multiMeterStatus,
			  adminDateAndTime, adminNDTrapSeqNo,
			  multiMeterIndex }
	DESCRIPTION	"This trap is generated when set
			multiMeterConnectedTrapID equal 113 and
 			the multimeter is connected."
	::= 39537

    multiMeterConnected114	TRAP-TYPE
	ENTERPRISE	network-device
	VARIABLES	{ multiMeterStatus,
			  adminDateAndTime, adminNDTrapSeqNo,
			  multiMeterIndex }
	DESCRIPTION	"This trap is generated when set
			multiMeterConnectedTrapID equal 114 and
 			the multimeter is connected."
	::= 39538

    multiMeterConnected115	TRAP-TYPE
	ENTERPRISE	network-device
	VARIABLES	{ multiMeterStatus,
			  adminDateAndTime, adminNDTrapSeqNo,
			  multiMeterIndex }
	DESCRIPTION	"This trap is generated when set
			multiMeterConnectedTrapID equal 115 and
 			the multimeter is connected."
	::= 39539

    multiMeterConnected116	TRAP-TYPE
	ENTERPRISE	network-device
	VARIABLES	{ multiMeterStatus,
			  adminDateAndTime, adminNDTrapSeqNo,
			  multiMeterIndex }
	DESCRIPTION	"This trap is generated when set
			multiMeterConnectedTrapID equal 116 and
 			the multimeter is connected."
	::= 39540

    multiMeterConnected117	TRAP-TYPE
	ENTERPRISE	network-device
	VARIABLES	{ multiMeterStatus,
			  adminDateAndTime, adminNDTrapSeqNo,
			  multiMeterIndex }
	DESCRIPTION	"This trap is generated when set
			multiMeterConnectedTrapID equal 117 and
 			the multimeter is connected."
	::= 39541

    multiMeterConnected118	TRAP-TYPE
	ENTERPRISE	network-device
	VARIABLES	{ multiMeterStatus,
			  adminDateAndTime, adminNDTrapSeqNo,
			  multiMeterIndex }
	DESCRIPTION	"This trap is generated when set
			multiMeterConnectedTrapID equal 118 and
 			the multimeter is connected."
	::= 39542

    multiMeterConnected119	TRAP-TYPE
	ENTERPRISE	network-device
	VARIABLES	{ multiMeterStatus,
			  adminDateAndTime, adminNDTrapSeqNo,
			  multiMeterIndex }
	DESCRIPTION	"This trap is generated when set
			multiMeterConnectedTrapID equal 119 and
 			the multimeter is connected."
	::= 39543

    multiMeterConnected120	TRAP-TYPE
	ENTERPRISE	network-device
	VARIABLES	{ multiMeterStatus,
			  adminDateAndTime, adminNDTrapSeqNo,
			  multiMeterIndex }
	DESCRIPTION	"This trap is generated when set
			multiMeterConnectedTrapID equal 120 and
 			the multimeter is connected."
	::= 39544

    multiMeterConnected121	TRAP-TYPE
	ENTERPRISE	network-device
	VARIABLES	{ multiMeterStatus,
			  adminDateAndTime, adminNDTrapSeqNo,
			  multiMeterIndex }
	DESCRIPTION	"This trap is generated when set
			multiMeterConnectedTrapID equal 121 and
 			the multimeter is connected."
	::= 39545

    multiMeterConnected122	TRAP-TYPE
	ENTERPRISE	network-device
	VARIABLES	{ multiMeterStatus,
			  adminDateAndTime, adminNDTrapSeqNo,
			  multiMeterIndex }
	DESCRIPTION	"This trap is generated when set
			multiMeterConnectedTrapID equal 122 and
 			the multimeter is connected."
	::= 39546

    multiMeterConnected123	TRAP-TYPE
	ENTERPRISE	network-device
	VARIABLES	{ multiMeterStatus,
			  adminDateAndTime, adminNDTrapSeqNo,
			  multiMeterIndex }
	DESCRIPTION	"This trap is generated when set
			multiMeterConnectedTrapID equal 123 and
 			the multimeter is connected."
	::= 39547

    multiMeterConnected124	TRAP-TYPE
	ENTERPRISE	network-device
	VARIABLES	{ multiMeterStatus,
			  adminDateAndTime, adminNDTrapSeqNo,
			  multiMeterIndex }
	DESCRIPTION	"This trap is generated when set
			multiMeterConnectedTrapID equal 124 and
 			the multimeter is connected."
	::= 39548

    multiMeterConnected125	TRAP-TYPE
	ENTERPRISE	network-device
	VARIABLES	{ multiMeterStatus,
			  adminDateAndTime, adminNDTrapSeqNo,
			  multiMeterIndex }
	DESCRIPTION	"This trap is generated when set
			multiMeterConnectedTrapID equal 125 and
 			the multimeter is connected."
	::= 39549

    multiMeterConnected126	TRAP-TYPE
	ENTERPRISE	network-device
	VARIABLES	{ multiMeterStatus,
			  adminDateAndTime, adminNDTrapSeqNo,
			  multiMeterIndex }
	DESCRIPTION	"This trap is generated when set
			multiMeterConnectedTrapID equal 126 and
 			the multimeter is connected."
	::= 39550

    multiMeterConnected127	TRAP-TYPE
	ENTERPRISE	network-device
	VARIABLES	{ multiMeterStatus,
			  adminDateAndTime, adminNDTrapSeqNo,
			  multiMeterIndex }
	DESCRIPTION	"This trap is generated when set
			multiMeterConnectedTrapID equal 127 and
 			the multimeter is connected."
	::= 39551


END
