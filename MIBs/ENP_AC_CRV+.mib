------------------------------------------------------------
-- EMERSON NETWORK POWER
-- RDU-SIC MIB
------------------------------------------------------------

ENP-ENP_AC_CRV+-MIB DEFINITIONS ::= BEGIN

IMPORTS
	MODULE-IDENTITY, OBJECT-TYPE, NOTIFICATION-TYPE,
	Integer32, Counter32, enterprises
		FROM SNMPv2-SMI
	TEXTUAL-CONVENTION, DisplayString, DateAndTime
		FROM SNMPv2-TC;
		
		
------------------------------------------------------------
-- Node definitions
------------------------------------------------------------

enp OBJECT IDENTIFIER ::= { enterprises 13400 }

products OBJECT IDENTIFIER ::= { enp 2 }

ENP_AC_CRV+ MODULE-IDENTITY
	LAST-UPDATED "201512161315Z"
	ORGANIZATION "
		EMERSON NETWORK POWER (ENPC)"
	CONTACT-INFO "
		EMERSON NETWORK POWER"
	DESCRIPTION "
		EMERSON NETWORK POWER (ENP) RDU-SIC MIB.
		Copyright 2008-2012 Emerson Corporation. All rights reserved."
	::= { products 339 }


------------------------------------------------------------
-- Textual conventions
------------------------------------------------------------

Status ::= TEXTUAL-CONVENTION
	STATUS current
	DESCRIPTION "
		The severity of the alarm. One of
		(0) informational
		(1) warning
		(2) critical"
	SYNTAX INTEGER {
		informational(0),
		warning(1),
		critical(2) }
		
StatusChange ::= TEXTUAL-CONVENTION
	STATUS current
	DESCRIPTION "
		Indicates 'activated' (0) or 'deactivated' (1) alarm events."
	SYNTAX INTEGER {
		activated(0),
		deactivated(1) }


------------------------------------------------------------
-- 1. Identification of the plant { ENP_AC_CRV+ 1 }
------------------------------------------------------------

ident OBJECT IDENTIFIER ::= { ENP_AC_CRV+ 1 }
															
identManufacturer OBJECT-TYPE
	SYNTAX DisplayString
	MAX-ACCESS read-only
	STATUS current
	DESCRIPTION "
		The name of the device manufacturer."
	::= { ident 1 }

identModel OBJECT-TYPE
	SYNTAX DisplayString
	MAX-ACCESS read-only
	STATUS current
	DESCRIPTION "
		The manufacturers model designation of the device."
	::= { ident 2 }
	
identIndex OBJECT-TYPE
	SYNTAX Integer32
	MAX-ACCESS read-write
	STATUS current
	DESCRIPTION "
		The sequence number of the device."
	::= { ident 3 }
	

------------------------------------------------------------
-- 2 system values { ENP_AC_CRV+ 2 }
------------------------------------------------------------

system OBJECT IDENTIFIER ::= { ENP_AC_CRV+ 2 }


Group2 OBJECT IDENTIFIER ::= { system 2 }

		Softshutdownstatus OBJECT-TYPE 
				 SYNTAX Integer32
				 MAX-ACCESS read-only
				 STATUS current
				 DESCRIPTION
				"Soft shutdown status, stored as 1."
				 ::= { Group2 1 }

		PanelOff OBJECT-TYPE 
				 SYNTAX Integer32
				 MAX-ACCESS read-only
				 STATUS current
				 DESCRIPTION
				"Panel Off, stored as 1."
				 ::= { Group2 2 }

		Monitorshutdown OBJECT-TYPE 
				 SYNTAX Integer32
				 MAX-ACCESS read-only
				 STATUS current
				 DESCRIPTION
				"Monitor shutdown, stored as 1."
				 ::= { Group2 3 }

		Refrigeration OBJECT-TYPE 
				 SYNTAX Integer32
				 MAX-ACCESS read-only
				 STATUS current
				 DESCRIPTION
				"Refrigeration, stored as 1."
				 ::= { Group2 4 }

		Heatingflag OBJECT-TYPE 
				 SYNTAX Integer32
				 MAX-ACCESS read-only
				 STATUS current
				 DESCRIPTION
				"Heating flag, stored as 1."
				 ::= { Group2 5 }

		Humidification OBJECT-TYPE 
				 SYNTAX Integer32
				 MAX-ACCESS read-only
				 STATUS current
				 DESCRIPTION
				"Humidification, stored as 1."
				 ::= { Group2 6 }

		Dehumidifying OBJECT-TYPE 
				 SYNTAX Integer32
				 MAX-ACCESS read-only
				 STATUS current
				 DESCRIPTION
				"Dehumidifying, stored as 1."
				 ::= { Group2 7 }

		Fan1Status OBJECT-TYPE 
				 SYNTAX Integer32
				 MAX-ACCESS read-only
				 STATUS current
				 DESCRIPTION
				"Fan 1 Status, stored as 1."
				 ::= { Group2 8 }

		Fan2Status OBJECT-TYPE 
				 SYNTAX Integer32
				 MAX-ACCESS read-only
				 STATUS current
				 DESCRIPTION
				"Fan 2 Status, stored as 1."
				 ::= { Group2 9 }

		Fan3status OBJECT-TYPE 
				 SYNTAX Integer32
				 MAX-ACCESS read-only
				 STATUS current
				 DESCRIPTION
				"Fan 3 status, stored as 1."
				 ::= { Group2 10 }

		Fan4Status OBJECT-TYPE 
				 SYNTAX Integer32
				 MAX-ACCESS read-only
				 STATUS current
				 DESCRIPTION
				"Fan 4 Status, stored as 1."
				 ::= { Group2 11 }

		Condensatepumpoutput OBJECT-TYPE 
				 SYNTAX Integer32
				 MAX-ACCESS read-only
				 STATUS current
				 DESCRIPTION
				"Condensate pump output, stored as 1."
				 ::= { Group2 12 }

		CompressorOutput OBJECT-TYPE 
				 SYNTAX Integer32
				 MAX-ACCESS read-only
				 STATUS current
				 DESCRIPTION
				"Compressor Output, stored as 1."
				 ::= { Group2 13 }

		Electricheatingoutput OBJECT-TYPE 
				 SYNTAX Integer32
				 MAX-ACCESS read-only
				 STATUS current
				 DESCRIPTION
				"Electric heating output, stored as 1."
				 ::= { Group2 14 }

		Fanoutput OBJECT-TYPE 
				 SYNTAX Integer32
				 MAX-ACCESS read-only
				 STATUS current
				 DESCRIPTION
				"Fan output, stored as 1."
				 ::= { Group2 15 }

		Humidifieroutput OBJECT-TYPE 
				 SYNTAX Integer32
				 MAX-ACCESS read-only
				 STATUS current
				 DESCRIPTION
				"Humidifier output, stored as 1."
				 ::= { Group2 16 }

		Commonalarmoutput OBJECT-TYPE 
				 SYNTAX Integer32
				 MAX-ACCESS read-only
				 STATUS current
				 DESCRIPTION
				"Common alarm output, stored as 1."
				 ::= { Group2 17 }

		Liquidsolenoidvalveoutput OBJECT-TYPE 
				 SYNTAX Integer32
				 MAX-ACCESS read-only
				 STATUS current
				 DESCRIPTION
				"Liquid solenoid valve output, stored as 1."
				 ::= { Group2 18 }

		Highpressurealarm OBJECT-TYPE 
				 SYNTAX Integer32
				 MAX-ACCESS read-only
				 STATUS current
				 DESCRIPTION
				"High pressure alarm, stored as 1."
				 ::= { Group2 19 }

		Lowpressurealarm OBJECT-TYPE 
				 SYNTAX Integer32
				 MAX-ACCESS read-only
				 STATUS current
				 DESCRIPTION
				"Low pressure alarm, stored as 1."
				 ::= { Group2 20 }

		Abnormalhighpressurealarm OBJECT-TYPE 
				 SYNTAX Integer32
				 MAX-ACCESS read-only
				 STATUS current
				 DESCRIPTION
				"Abnormal high pressure alarm, stored as 1."
				 ::= { Group2 21 }

		Exhausttemperaturealarm OBJECT-TYPE 
				 SYNTAX Integer32
				 MAX-ACCESS read-only
				 STATUS current
				 DESCRIPTION
				"Exhaust temperature alarm, stored as 1."
				 ::= { Group2 22 }

		Exhaustlowsuperheat OBJECT-TYPE 
				 SYNTAX Integer32
				 MAX-ACCESS read-only
				 STATUS current
				 DESCRIPTION
				"Exhaust low superheat, stored as 1."
				 ::= { Group2 23 }

		Returnairhightempalarm OBJECT-TYPE 
				 SYNTAX Integer32
				 MAX-ACCESS read-only
				 STATUS current
				 DESCRIPTION
				"Return air high temp alarm, stored as 1."
				 ::= { Group2 24 }

		supplyairLowtempalarm OBJECT-TYPE 
				 SYNTAX Integer32
				 MAX-ACCESS read-only
				 STATUS current
				 DESCRIPTION
				"supply air Low temp alarm, stored as 1."
				 ::= { Group2 25 }

		supplyairhightempalarm OBJECT-TYPE 
				 SYNTAX Integer32
				 MAX-ACCESS read-only
				 STATUS current
				 DESCRIPTION
				"supply air high temp alarm, stored as 1."
				 ::= { Group2 26 }

		Returnairhighhumalarm OBJECT-TYPE 
				 SYNTAX Integer32
				 MAX-ACCESS read-only
				 STATUS current
				 DESCRIPTION
				"Return air high hum alarm, stored as 1."
				 ::= { Group2 27 }

		Returnairlowhumalarm OBJECT-TYPE 
				 SYNTAX Integer32
				 MAX-ACCESS read-only
				 STATUS current
				 DESCRIPTION
				"Return air low hum alarm, stored as 1."
				 ::= { Group2 28 }

		HighPressureLockalarm OBJECT-TYPE 
				 SYNTAX Integer32
				 MAX-ACCESS read-only
				 STATUS current
				 DESCRIPTION
				"High Pressure Lock alarm, stored as 1."
				 ::= { Group2 29 }

		LowPressureLockalarm OBJECT-TYPE 
				 SYNTAX Integer32
				 MAX-ACCESS read-only
				 STATUS current
				 DESCRIPTION
				"Low Pressure Lock alarm, stored as 1."
				 ::= { Group2 30 }

		Lockexhausttemperaturealarm OBJECT-TYPE 
				 SYNTAX Integer32
				 MAX-ACCESS read-only
				 STATUS current
				 DESCRIPTION
				"Lock exhaust temperature alarm, stored as 1."
				 ::= { Group2 31 }

		Lowexhaustsuperheatlockalarm OBJECT-TYPE 
				 SYNTAX Integer32
				 MAX-ACCESS read-only
				 STATUS current
				 DESCRIPTION
				"Low exhaust superheat lock alarm, stored as 1."
				 ::= { Group2 32 }

		Powerlossalarm OBJECT-TYPE 
				 SYNTAX Integer32
				 MAX-ACCESS read-only
				 STATUS current
				 DESCRIPTION
				"Power loss alarm, stored as 1."
				 ::= { Group2 33 }

		Powerovervoltagealarm OBJECT-TYPE 
				 SYNTAX Integer32
				 MAX-ACCESS read-only
				 STATUS current
				 DESCRIPTION
				"Power overvoltage alarm, stored as 1."
				 ::= { Group2 34 }

		Powerundervoltagealarm OBJECT-TYPE 
				 SYNTAX Integer32
				 MAX-ACCESS read-only
				 STATUS current
				 DESCRIPTION
				"Power undervoltage alarm, stored as 1."
				 ::= { Group2 35 }

		Powerlosephasealarm OBJECT-TYPE 
				 SYNTAX Integer32
				 MAX-ACCESS read-only
				 STATUS current
				 DESCRIPTION
				"Power lose phase alarm, stored as 1."
				 ::= { Group2 36 }

		Flooroverflowalarm OBJECT-TYPE 
				 SYNTAX Integer32
				 MAX-ACCESS read-only
				 STATUS current
				 DESCRIPTION
				"Floor overflow alarm, stored as 1."
				 ::= { Group2 37 }

		Highwaterlevelalarm OBJECT-TYPE 
				 SYNTAX Integer32
				 MAX-ACCESS read-only
				 STATUS current
				 DESCRIPTION
				"High water level alarm, stored as 1."
				 ::= { Group2 38 }

		Filtercloggedalarm OBJECT-TYPE 
				 SYNTAX Integer32
				 MAX-ACCESS read-only
				 STATUS current
				 DESCRIPTION
				"Filter clogged alarm, stored as 1."
				 ::= { Group2 39 }

		Filtermaintenance OBJECT-TYPE 
				 SYNTAX Integer32
				 MAX-ACCESS read-only
				 STATUS current
				 DESCRIPTION
				"Filter maintenance, stored as 1."
				 ::= { Group2 40 }

		Airflowlossalarm OBJECT-TYPE 
				 SYNTAX Integer32
				 MAX-ACCESS read-only
				 STATUS current
				 DESCRIPTION
				"Airflow loss alarm, stored as 1."
				 ::= { Group2 41 }

		Lowpressuresensorlock OBJECT-TYPE 
				 SYNTAX Integer32
				 MAX-ACCESS read-only
				 STATUS current
				 DESCRIPTION
				"Low pressure sensor lock, stored as 1."
				 ::= { Group2 42 }

		RemoteShutdownAlarm OBJECT-TYPE 
				 SYNTAX Integer32
				 MAX-ACCESS read-only
				 STATUS current
				 DESCRIPTION
				"Remote Shutdown Alarm, stored as 1."
				 ::= { Group2 43 }

		Grouphostlossalarm OBJECT-TYPE 
				 SYNTAX Integer32
				 MAX-ACCESS read-only
				 STATUS current
				 DESCRIPTION
				"Group host loss alarm, stored as 1."
				 ::= { Group2 44 }

		GroupSlavelossalarm OBJECT-TYPE 
				 SYNTAX Integer32
				 MAX-ACCESS read-only
				 STATUS current
				 DESCRIPTION
				"Group Slave loss alarm, stored as 1."
				 ::= { Group2 45 }

		Returnairtempsensorfault OBJECT-TYPE 
				 SYNTAX Integer32
				 MAX-ACCESS read-only
				 STATUS current
				 DESCRIPTION
				"Return air temp sensor fault, stored as 1."
				 ::= { Group2 46 }

		Returnairhumsensorfault OBJECT-TYPE 
				 SYNTAX Integer32
				 MAX-ACCESS read-only
				 STATUS current
				 DESCRIPTION
				"Return air hum sensor fault, stored as 1."
				 ::= { Group2 47 }

		Supplyairtempdiffsensorfault OBJECT-TYPE 
				 SYNTAX Integer32
				 MAX-ACCESS read-only
				 STATUS current
				 DESCRIPTION
				"Supply air temp diff sensor fault, stored as 1."
				 ::= { Group2 48 }

		Supplyairtempsensorfault OBJECT-TYPE 
				 SYNTAX Integer32
				 MAX-ACCESS read-only
				 STATUS current
				 DESCRIPTION
				"Supply air temp sensor fault, stored as 1."
				 ::= { Group2 49 }

		Remotetempsensorfault OBJECT-TYPE 
				 SYNTAX Integer32
				 MAX-ACCESS read-only
				 STATUS current
				 DESCRIPTION
				"Remote temp sensor fault, stored as 1."
				 ::= { Group2 50 }

		Highpressuresensorfault OBJECT-TYPE 
				 SYNTAX Integer32
				 MAX-ACCESS read-only
				 STATUS current
				 DESCRIPTION
				"High pressure sensor fault, stored as 1."
				 ::= { Group2 51 }

		Electricheatingfailurealarm OBJECT-TYPE 
				 SYNTAX Integer32
				 MAX-ACCESS read-only
				 STATUS current
				 DESCRIPTION
				"Electric heating failure alarm, stored as 1."
				 ::= { Group2 52 }

		Exhaustgastempsensorfault OBJECT-TYPE 
				 SYNTAX Integer32
				 MAX-ACCESS read-only
				 STATUS current
				 DESCRIPTION
				"Exhaust gas temp sensor fault, stored as 1."
				 ::= { Group2 53 }

		Fanpowerfailure OBJECT-TYPE 
				 SYNTAX Integer32
				 MAX-ACCESS read-only
				 STATUS current
				 DESCRIPTION
				"Fan power failure, stored as 1."
				 ::= { Group2 54 }

		EEVcommunicationfailure OBJECT-TYPE 
				 SYNTAX Integer32
				 MAX-ACCESS read-only
				 STATUS current
				 DESCRIPTION
				"EEV communication failure, stored as 1."
				 ::= { Group2 55 }

		Notselectedrefrigerantalarm OBJECT-TYPE 
				 SYNTAX Integer32
				 MAX-ACCESS read-only
				 STATUS current
				 DESCRIPTION
				"Not selected refrigerant alarm, stored as 1."
				 ::= { Group2 56 }

		Refrigerantshortagealarm OBJECT-TYPE 
				 SYNTAX Integer32
				 MAX-ACCESS read-only
				 STATUS current
				 DESCRIPTION
				"Refrigerant shortage alarm, stored as 1."
				 ::= { Group2 57 }

		Intakeairtemperaturesensorfault OBJECT-TYPE 
				 SYNTAX Integer32
				 MAX-ACCESS read-only
				 STATUS current
				 DESCRIPTION
				"Intake air temperature sensor fault, stored as 1."
				 ::= { Group2 58 }

		Lowpressuresensorfault OBJECT-TYPE 
				 SYNTAX Integer32
				 MAX-ACCESS read-only
				 STATUS current
				 DESCRIPTION
				"Low pressure sensor fault, stored as 1."
				 ::= { Group2 59 }

		Compressordrivecommunicationfault OBJECT-TYPE 
				 SYNTAX Integer32
				 MAX-ACCESS read-only
				 STATUS current
				 DESCRIPTION
				"Compressor drive communication fault, stored as 1."
				 ::= { Group2 60 }

		Compressordrivefault OBJECT-TYPE 
				 SYNTAX Integer32
				 MAX-ACCESS read-only
				 STATUS current
				 DESCRIPTION
				"Compressor drive fault, stored as 1."
				 ::= { Group2 61 }

		Compressorradiatorover-temperature OBJECT-TYPE 
				 SYNTAX Integer32
				 MAX-ACCESS read-only
				 STATUS current
				 DESCRIPTION
				"Compressor radiator over-temperature, stored as 1."
				 ::= { Group2 62 }

		Compressorovercurrentprotection OBJECT-TYPE 
				 SYNTAX Integer32
				 MAX-ACCESS read-only
				 STATUS current
				 DESCRIPTION
				"Compressor overcurrent protection, stored as 1."
				 ::= { Group2 63 }

		Compressorphaselossprotection OBJECT-TYPE 
				 SYNTAX Integer32
				 MAX-ACCESS read-only
				 STATUS current
				 DESCRIPTION
				"Compressor phase loss protection, stored as 1."
				 ::= { Group2 64 }

		Compressorbusvoltagefault OBJECT-TYPE 
				 SYNTAX Integer32
				 MAX-ACCESS read-only
				 STATUS current
				 DESCRIPTION
				"Compressor bus voltage fault, stored as 1."
				 ::= { Group2 65 }

		Humidifierfaultalarm OBJECT-TYPE 
				 SYNTAX Integer32
				 MAX-ACCESS read-only
				 STATUS current
				 DESCRIPTION
				"Humidifier fault alarm, stored as 1."
				 ::= { Group2 66 }

		Groupaddressrepeatedalarm OBJECT-TYPE 
				 SYNTAX Integer32
				 MAX-ACCESS read-only
				 STATUS current
				 DESCRIPTION
				"Group address repeated alarm, stored as 1."
				 ::= { Group2 67 }

		Supplyairtemperature OBJECT-TYPE 
				 SYNTAX Integer32
				 MAX-ACCESS read-only
				 STATUS current
				 DESCRIPTION
				"Supply air temperature, stored as 0.01deg.C."
				 ::= { Group2 68 }

		Returnairtemperature OBJECT-TYPE 
				 SYNTAX Integer32
				 MAX-ACCESS read-only
				 STATUS current
				 DESCRIPTION
				"Return air temperature, stored as 0.01deg.C."
				 ::= { Group2 69 }

		Returnairhumidity OBJECT-TYPE 
				 SYNTAX Integer32
				 MAX-ACCESS read-only
				 STATUS current
				 DESCRIPTION
				"Return air humidity, stored as 0.01%."
				 ::= { Group2 70 }

		Theoreticalairhumidity OBJECT-TYPE 
				 SYNTAX Integer32
				 MAX-ACCESS read-only
				 STATUS current
				 DESCRIPTION
				"Theoretical air humidity, stored as 0.01%."
				 ::= { Group2 71 }

		Aphasevoltage OBJECT-TYPE 
				 SYNTAX Integer32
				 MAX-ACCESS read-only
				 STATUS current
				 DESCRIPTION
				"A phase voltage, stored as 0.01V."
				 ::= { Group2 83 }

		Bphasevoltage OBJECT-TYPE 
				 SYNTAX Integer32
				 MAX-ACCESS read-only
				 STATUS current
				 DESCRIPTION
				"B phase voltage, stored as 0.01V."
				 ::= { Group2 84 }

		Cphasevoltage OBJECT-TYPE 
				 SYNTAX Integer32
				 MAX-ACCESS read-only
				 STATUS current
				 DESCRIPTION
				"C phase voltage, stored as 0.01V."
				 ::= { Group2 85 }

		Powerfrequency OBJECT-TYPE 
				 SYNTAX Integer32
				 MAX-ACCESS read-only
				 STATUS current
				 DESCRIPTION
				"Power frequency, stored as 0.01Hz."
				 ::= { Group2 86 }

		Unitoperationstatus OBJECT-TYPE 
				 SYNTAX Integer32
				 MAX-ACCESS read-only
				 STATUS current
				 DESCRIPTION
				"Unit operation status, stored as 1."
				 ::= { Group2 87 }

		Unitgroupcontrolmode OBJECT-TYPE 
				 SYNTAX Integer32
				 MAX-ACCESS read-only
				 STATUS current
				 DESCRIPTION
				"Unit group control mode, stored as 1."
				 ::= { Group2 88 }

		Compressorcapacity OBJECT-TYPE 
				 SYNTAX Integer32
				 MAX-ACCESS read-only
				 STATUS current
				 DESCRIPTION
				"Compressor capacity, stored as 0.01%."
				 ::= { Group2 89 }

		Fanspeed OBJECT-TYPE 
				 SYNTAX Integer32
				 MAX-ACCESS read-only
				 STATUS current
				 DESCRIPTION
				"Fan speed, stored as 0.01%."
				 ::= { Group2 90 }

		CommunicateStatus OBJECT-TYPE 
				 SYNTAX Integer32
				 MAX-ACCESS read-only
				 STATUS current
				 DESCRIPTION
				"CommunicateStatus, stored as 1."
				 ::= { Group2 91 }

Group3 OBJECT IDENTIFIER ::= { system 3 }

		RemoteOn OBJECT-TYPE 
				 SYNTAX Integer32
				 MAX-ACCESS read-write
				 STATUS current
				 DESCRIPTION
				"Remote On, stored as 1."
				 ::= { Group3 1 }

		RemoteOff OBJECT-TYPE 
				 SYNTAX Integer32
				 MAX-ACCESS read-write
				 STATUS current
				 DESCRIPTION
				"Remote Off, stored as 1."
				 ::= { Group3 2 }

Group4 OBJECT IDENTIFIER ::= { system 4 }

		Supplyairtemperaturesetpoint OBJECT-TYPE 
				 SYNTAX Integer32
				 MAX-ACCESS read-write
				 STATUS current
				 DESCRIPTION
				"Supply air temperature setpoint, stored as 1deg.C."
				 ::= { Group4 1 }

		Remotetemperaturesetpoint OBJECT-TYPE 
				 SYNTAX Integer32
				 MAX-ACCESS read-write
				 STATUS current
				 DESCRIPTION
				"Remote temperature setpoint, stored as 1deg.C."
				 ::= { Group4 2 }

		Returnairtemperaturesetpoint OBJECT-TYPE 
				 SYNTAX Integer32
				 MAX-ACCESS read-write
				 STATUS current
				 DESCRIPTION
				"Return air temperature set point, stored as 1deg.C."
				 ::= { Group4 3 }

		Supplyairhumiditysetpoint OBJECT-TYPE 
				 SYNTAX Integer32
				 MAX-ACCESS read-write
				 STATUS current
				 DESCRIPTION
				"Supply air humidity setpoint, stored as 1%."
				 ::= { Group4 4 }

		LogNumberSet OBJECT-TYPE 
				 SYNTAX Integer32
				 MAX-ACCESS read-write
				 STATUS current
				 DESCRIPTION
				"LogNumberSet, stored as 1."
				 ::= { Group4 5 }
                                   

------------------------------------------------------------
-- 3 Alarm trap table { ENP_AC_CRV+  3 }
-- If you want to know the equipment trap list detail, please find a Excel file named "RDU-SIC trap table";
------------------------------------------------------------

alarmTrapTable OBJECT-TYPE
	SYNTAX SEQUENCE OF AlarmTrapEntry
	MAX-ACCESS not-accessible
	STATUS current
	DESCRIPTION "
		Table holding information about the submitted alarm traps."
	::= { ENP_AC_CRV+  3 }

alarmTrapEntry OBJECT-TYPE
	SYNTAX AlarmTrapEntry
	MAX-ACCESS not-accessible
	STATUS current
	DESCRIPTION "
		An entry (conceptual row) in the alarmTrapTable."
	INDEX { alarmIndex }
	::= { alarmTrapTable 1 }

AlarmTrapEntry ::= SEQUENCE {
	alarmIndex Counter32,
	alarmTime DisplayString,
	alarmStatusChange StatusChange,
	alarmSeverity Status,
	alarmDescription DisplayString,
	alarmId Integer32 }

alarmIndex OBJECT-TYPE
	SYNTAX Counter32
	MAX-ACCESS read-only
	STATUS current
	DESCRIPTION "
		The unique sequence number of this alarm trap."
	::= { alarmTrapEntry 1 }

alarmTime OBJECT-TYPE
	SYNTAX DisplayString
	MAX-ACCESS read-only
	STATUS current
	DESCRIPTION "
		Date and time when event occured."
	::= { alarmTrapEntry 2 }

alarmStatusChange OBJECT-TYPE
	SYNTAX StatusChange
	MAX-ACCESS read-only
	STATUS current
	DESCRIPTION "
		Indicates 'activated' (0) or 'deactivated' (1) alarm events."
	::= { alarmTrapEntry 3 }

alarmSeverity OBJECT-TYPE
	SYNTAX Status
	MAX-ACCESS read-only
	STATUS current
	DESCRIPTION "
		The severity of the alarm. One of
		(0) informational
		(1) warning
		(2) critical"
	::= { alarmTrapEntry 4 }
	
alarmDescription OBJECT-TYPE
	SYNTAX DisplayString
	MAX-ACCESS read-only
	STATUS current
	DESCRIPTION "
		Free-text description of alarm."
	::= { alarmTrapEntry 5 }
	
alarmId OBJECT-TYPE
	SYNTAX Integer32
	MAX-ACCESS read-only
	STATUS current
	DESCRIPTION "
		Alarm id."
	::= { alarmTrapEntry 6 }


------------------------------------------------------------
-- End of MIB definitions
------------------------------------------------------------

END
