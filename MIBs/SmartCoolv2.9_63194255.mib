--
-- MIB generated by Airedale
-- Tuesday, 02 April 2013
-- Current to SmartCool_2_9 Software
--

    CAREL-smartcool-MIB DEFINITIONS ::= BEGIN
 
		IMPORTS
			OBJECT-GROUP
				FROM SNMPv2-CONF			
			sysContact, sysName, sysLocation			
				FROM SNMPv2-MIB
			enterprises, MODULE-IDENTITY, OBJECT-TYPE, Integer32, NOTIFICATION-TYPE			
				FROM SNMPv2-SMI;		
		
        smartcoolMIB MODULE-IDENTITY
      		LAST-UPDATED  "201005041725Z"		-- April 02, 2013 at 15:25 GMT
      		ORGANIZATION  "Airedale International Air Conditioning"
      		CONTACT-INFO
                "
                   
                        Airedale International Air Conditioning
                        Leeds Road,
                       	Rawdon, Leeds. LS19 6JY
                        Tel: +00 (44) 113 239 1000
                "
      		DESCRIPTION
                "This is the MIB module for the SmartCool device, using pcoweb SNMP"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { smartcoolMIB 1 }

	-- 1.3.6.1.4.1.9839.2.1.1.19
        bms-on-off OBJECT-TYPE 
		    SYNTAX Integer32 (0..1)
                    UNITS "N/A"
                    MAX-ACCESS read-write
                    STATUS current
                    DESCRIPTION "On/Off by Supervisor"
                    ::= { digitalObjects 19 }

	-- 1.3.6.1.4.1.9839.2.1.1.20
        reset-al OBJECT-TYPE 
		    SYNTAX Integer32 (0..1)
                    UNITS "N/A"
                    MAX-ACCESS read-write
                    STATUS current
                    DESCRIPTION "Reset Alarms by Supervisor"
                    ::= { digitalObjects 20 }     

	-- 1.3.6.1.4.1.9839.2.1.1.40
        remote-on-off OBJECT-TYPE 
		    SYNTAX Integer32 (0..1)
                    UNITS "N/A"
                    MAX-ACCESS read-write
                    STATUS current
                    DESCRIPTION "Remote on/Off"
                    ::= { digitalObjects 40 }   

	-- 1.3.6.1.4.1.9839.2.1.1.22
       airflow-switch OBJECT-TYPE 
		    SYNTAX Integer32 (0..1)
                    UNITS "N/A"
                    MAX-ACCESS read-write
                    STATUS current
                    DESCRIPTION "Airflow Switch Status"
                    ::= { digitalObjects 22 }  
	
       
        -- 1.3.6.1.4.1.9839.2.1.1.24
        phase-rotation OBJECT-TYPE 
		    SYNTAX Integer32 (0..1)
                    UNITS "N/A"
                    MAX-ACCESS read-only
                    STATUS current
                    DESCRIPTION "Phase Rotation"
                    ::= { digitalObjects 24 } 

	 -- 1.3.6.1.4.1.9839.2.1.1.25
        water-condensate-pump-status OBJECT-TYPE 
		    SYNTAX Integer32 (0..1)
                    UNITS "N/A"
                    MAX-ACCESS read-only
                    STATUS current
                    DESCRIPTION "Water Condensate Pump Status"
                    ::= { digitalObjects 25 } 

	 -- 1.3.6.1.4.1.9839.2.1.1.26
        fire-smoke-status OBJECT-TYPE 
		    SYNTAX Integer32 (0..1)
                    UNITS "N/A"
                    MAX-ACCESS read-only
                    STATUS current
                    DESCRIPTION "Fire Smoke Status"
                    ::= { digitalObjects 26 } 

	-- 1.3.6.1.4.1.9839.2.1.1.27
        leak-detector-status OBJECT-TYPE 
		    SYNTAX Integer32 (0..1)
                    UNITS "N/A"
                    MAX-ACCESS read-only
                    STATUS current
                    DESCRIPTION "Leak Detector Status"
                    ::= { digitalObjects 27 } 

	
	-- 1.3.6.1.4.1.9839.2.1.1.28
        overheat-cutout-status OBJECT-TYPE 
		    SYNTAX Integer32 (0..1)
                    UNITS "N/A"
                    MAX-ACCESS read-only
                    STATUS current
                    DESCRIPTION "Overheat Cutout Status"
                    ::= { digitalObjects 28 } 


        -- 1.3.6.1.4.1.9839.2.1.1.29
        cp1-cct1-status OBJECT-TYPE 
		    SYNTAX Integer32 (0..1)
                    UNITS "N/A"
                    MAX-ACCESS read-only
                    STATUS current
                    DESCRIPTION "Compressor 1 Circuit 1 Status"
                    ::= { digitalObjects 29 } 

        -- 1.3.6.1.4.1.9839.2.1.1.30
        cp2-cct1-status OBJECT-TYPE 
		    SYNTAX Integer32 (0..1)
                    UNITS "N/A"
                    MAX-ACCESS read-only
                    STATUS current
                    DESCRIPTION "Compressor 2 Circuit 1 Status"
                    ::= { digitalObjects 30 }   

        -- 1.3.6.1.4.1.9839.2.1.1.31
        lp-cct1-status OBJECT-TYPE 
		    SYNTAX Integer32 (0..1)
                    UNITS "N/A"
                    MAX-ACCESS read-only
                    STATUS current
                    DESCRIPTION "Low Pressure Switch Circuit 1 Status"
                    ::= { digitalObjects 31 }      

        -- 1.3.6.1.4.1.9839.2.1.1.32
        lp-cct2-status OBJECT-TYPE 
		    SYNTAX Integer32 (0..1)
                    UNITS "N/A"
                    MAX-ACCESS read-only
                    STATUS current
                    DESCRIPTION "Low Pressure Switch Circuit 2 Status"
                    ::= { digitalObjects 32 }      


        -- 1.3.6.1.4.1.9839.2.1.1.33
        cp1-cct2-status OBJECT-TYPE 
		    SYNTAX Integer32 (0..1)
                    UNITS "N/A"
                    MAX-ACCESS read-only
                    STATUS current
                    DESCRIPTION "Compressor 1 Circuit 2 Status"
                    ::= { digitalObjects 33 }    

        -- 1.3.6.1.4.1.9839.2.1.1.34
        cp2-cct2-status OBJECT-TYPE 
		    SYNTAX Integer32 (0..1)
                    UNITS "N/A"
                    MAX-ACCESS read-only
                    STATUS current
                    DESCRIPTION "Compressor 2 Circuit 2 Status"
                    ::= { digitalObjects 34 }                                     
 	
	-- 1.3.6.1.4.1.9839.2.1.1.143
        cooling-on OBJECT-TYPE
                    SYNTAX Integer32 (0..1)
                    UNITS "N/A"
                    MAX-ACCESS read-only
                    STATUS current
                    DESCRIPTION "Cooling On"
                    ::= { digitalObjects 143 }
              
	-- 1.3.6.1.4.1.9839.2.1.1.144
        heating-on OBJECT-TYPE
                    SYNTAX Integer32 (0..1)
                    UNITS "N/A"
                    MAX-ACCESS read-only
                    STATUS current
                    DESCRIPTION "Heating On"
                    ::= { digitalObjects 144 }

	-- 1.3.6.1.4.1.9839.2.1.1.145
        humidification-on OBJECT-TYPE
                    SYNTAX Integer32 (0..1)
                    UNITS "N/A"
                    MAX-ACCESS read-only
                    STATUS current
                    DESCRIPTION "Humidification On"
                    ::= { digitalObjects 145 }
	

	-- 1.3.6.1.4.1.9839.2.1.1.146
        dehumidification-on OBJECT-TYPE
                    SYNTAX Integer32 (0..1)
                    UNITS "N/A"
                    MAX-ACCESS read-only
                    STATUS current
                    DESCRIPTION "Dehumidification On"
                    ::= { digitalObjects 146 }

	-- 1.3.6.1.4.1.9839.2.1.1.147
        heat-1-on OBJECT-TYPE
                    SYNTAX Integer32 (0..1)
                    UNITS "N/A"
                    MAX-ACCESS read-only
                    STATUS current
                    DESCRIPTION "Heating Stage 1 On"
                    ::= { digitalObjects 147 }

	-- 1.3.6.1.4.1.9839.2.1.1.148
        heat-2-on OBJECT-TYPE
                    SYNTAX Integer32 (0..1)
                    UNITS "N/A"
                    MAX-ACCESS read-only
                    STATUS current
                    DESCRIPTION "Heating Stage 2 On"
                    ::= { digitalObjects 148 }
	

	-- 1.3.6.1.4.1.9839.2.1.1.149
        heat-3-on OBJECT-TYPE
                    SYNTAX Integer32 (0..1)
                    UNITS "N/A"
                    MAX-ACCESS read-only
                    STATUS current
                    DESCRIPTION "Heating Stage 3 On"
                    ::= { digitalObjects 149 }


	

        -- 1.3.6.1.4.1.9839.2.1.2
        analogObjects OBJECT IDENTIFIER ::= { smartcoolMIB 2 }


	-- 1.3.6.1.4.1.9839.2.1.2.21
        return-hum-1 OBJECT-TYPE
                    SYNTAX Integer32 (-32767..32767)
                    UNITS "%RH x10"
                    MAX-ACCESS read-only
                    STATUS current
                    DESCRIPTION "Return Humidity"
                    ::= { analogObjects 21 }
	
	-- 1.3.6.1.4.1.9839.2.1.2.22
        liquid-press-1 OBJECT-TYPE
                    SYNTAX Integer32 (-32767..32767)
                    UNITS "BarG x10"
                    MAX-ACCESS read-only
                    STATUS current
                    DESCRIPTION "Liquid Pressure Circuit 1"
                    ::= { analogObjects 22 }

	-- 1.3.6.1.4.1.9839.2.1.2.23
        ret-air-temp OBJECT-TYPE
                    SYNTAX Integer32 (-32767..32767)
                    UNITS "DegC x10"
                    MAX-ACCESS read-only
                    STATUS current
                    DESCRIPTION "Return Air Temperature"
                    ::= { analogObjects 23 }

	
	
	
	-- 1.3.6.1.4.1.9839.2.1.2.25
        dis-temp-cct1 OBJECT-TYPE
                    SYNTAX Integer32 (-32767..32767)
                    UNITS "DegC x10"
                    MAX-ACCESS read-only
                    STATUS current
                    DESCRIPTION "Discharge Temperature Circuit 1"
                    ::= { analogObjects 25 }


	-- 1.3.6.1.4.1.9839.2.1.2.26
        liquid-press-2 OBJECT-TYPE
                    SYNTAX Integer32 (-32767..32767)
                    UNITS "BarG x10"
                    MAX-ACCESS read-only
                    STATUS current
                    DESCRIPTION "Liquid Pressure Circuit 2"
                    ::= { analogObjects 26 }
	
	

        -- 1.3.6.1.4.1.9839.2.1.2.28
        temp-setp OBJECT-TYPE
                    SYNTAX Integer32 (50..250)
                    UNITS "DegC x10"
                    MAX-ACCESS read-write
                    STATUS current
                    DESCRIPTION "Adjustable Temperature Setpoint by SNMP"
                    ::= { analogObjects 28 }

	-- 1.3.6.1.4.1.9839.2.1.2.29
        hum-setp OBJECT-TYPE
                    SYNTAX Integer32 (50..250)
                    UNITS "%RH x10"
                    MAX-ACCESS read-write
                    STATUS current
                    DESCRIPTION "Adjustable Humidity Setpoint by SNMP"
                    ::= { analogObjects 29 }


		
	-- 1.3.6.1.4.1.9839.2.1.2.57
        hpc-cct1 OBJECT-TYPE
                    SYNTAX Integer32 (-32767..32767)
                    UNITS "DegC x10"
                    MAX-ACCESS read-only
                    STATUS current
                    DESCRIPTION "Head Pressure Control Circuit 1"
                    ::= { analogObjects 57 }

	
	-- 1.3.6.1.4.1.9839.2.1.2.58
        hpc-cct2 OBJECT-TYPE
                    SYNTAX Integer32 (-32767..32767)
                    UNITS "DegC x10"
                    MAX-ACCESS read-only
                    STATUS current
                    DESCRIPTION "Head Pressure Control Circuit 2"
                    ::= { analogObjects 58 }


	-- 1.3.6.1.4.1.9839.2.1.2.59
        fan-speed OBJECT-TYPE
                    SYNTAX Integer32 (-32767..32767)
                    UNITS "% x10"
                    MAX-ACCESS read-only
                    STATUS current
                    DESCRIPTION "Fan Speed"
                    ::= { analogObjects 59 }

	-- 1.3.6.1.4.1.9839.2.1.2.63
        dis-temp-cct2 OBJECT-TYPE
                    SYNTAX Integer32 (-32767..32767)
                    UNITS "% x10"
                    MAX-ACCESS read-only
                    STATUS current
                    DESCRIPTION "Discharge Temperature Circuit 2"
                    ::= { analogObjects 63 }


	
	
	
        -- 1.3.6.1.4.1.9839.2.1.3
        integerObjects OBJECT IDENTIFIER ::= { smartcoolMIB 3 }

	-- 1.3.6.1.4.1.9839.2.1.3.21
        unit-status OBJECT-TYPE
                    SYNTAX Integer32 (-32767..32767)
                    UNITS "N/A"
                    MAX-ACCESS read-only
                    STATUS current
                    DESCRIPTION "Unit Status"
                    ::= { integerObjects 21 }

-- 1.3.6.1.4.1.9839.2.1.100
trapObjects OBJECT IDENTIFIER ::= { smartcoolMIB  100 }	



-- 1.3.6.1.4.1.9839.2.1.100.41
ret-hum-probe-al NOTIFICATION-TYPE
STATUS current
DESCRIPTION "Return Humidity Probe Alarm"
::= { trapObjects 41 }


-- 1.3.6.1.4.1.9839.2.1.100.42
ret-hum-probe-al-clear NOTIFICATION-TYPE
STATUS current
DESCRIPTION "Return Humidity Probe Alarm Cleared"
::= { trapObjects 42 }


-- 1.3.6.1.4.1.9839.2.1.100.43
liq-press-trans-cct1-al NOTIFICATION-TYPE
STATUS current
DESCRIPTION "Liquid Pressure Transducer Circuit 1 Alarm"
::= { trapObjects 43 }


-- 1.3.6.1.4.1.9839.2.1.100.44
liq-press-trans-cct1-al-clear NOTIFICATION-TYPE
STATUS current
DESCRIPTION "Liquid Pressure Transducer Circuit 1 Alarm Cleared"
::= { trapObjects 44 }


-- 1.3.6.1.4.1.9839.2.1.100.45
ret-temp-probe-al NOTIFICATION-TYPE
STATUS current
DESCRIPTION "Return Temperature Probe Alarm"
::= { trapObjects 45 }


-- 1.3.6.1.4.1.9839.2.1.100.46
ret-temp-probe-al-clear NOTIFICATION-TYPE
STATUS current
DESCRIPTION "Return Temperature Probe Alarm Cleared"
::= { trapObjects 46 }


-- 1.3.6.1.4.1.9839.2.1.100.49
dis-temp-probe-cct1-al NOTIFICATION-TYPE
STATUS current
DESCRIPTION "Discharge Temperature Probe Circuit 1 Alarm"
::= { trapObjects 49 }


-- 1.3.6.1.4.1.9839.2.1.100.50
dis-temp-probe-cct1-al-clear NOTIFICATION-TYPE
STATUS current
DESCRIPTION "Discharge Temperature Probe Circuit 1 Alarm Cleared"
::= { trapObjects 50 }


-- 1.3.6.1.4.1.9839.2.1.100.51
liq-press-trans-cct2-al NOTIFICATION-TYPE
STATUS current
DESCRIPTION "Liquid Pressure Transducer Circuit 2 Alarm"
::= { trapObjects 51 }


-- 1.3.6.1.4.1.9839.2.1.100.52
liq-press-trans-cct2-al-clear NOTIFICATION-TYPE
STATUS current
DESCRIPTION "Liquid Pressure Transducer Circuit 2 Alarm Cleared"
::= { trapObjects 52 }
			

-- 1.3.6.1.4.1.9839.2.1.100.53
dis-temp-probe-cct2-al NOTIFICATION-TYPE
STATUS current
DESCRIPTION "Discharge Temperature Probe Circuit 2 Alarm"
::= { trapObjects 53 }


-- 1.3.6.1.4.1.9839.2.1.100.54
dis-temp-probe-cct2-al-clear NOTIFICATION-TYPE
STATUS current
DESCRIPTION "Discharge Temperature Probe Circuit 2 Alarm Cleared"
::= { trapObjects 54 }


-- 1.3.6.1.4.1.9839.2.1.100.55
airflow-fail-al NOTIFICATION-TYPE
STATUS current
DESCRIPTION "Airflow Fail Alarm"
::= { trapObjects 55 }


-- 1.3.6.1.4.1.9839.2.1.100.56
airflow-fail-al-clear NOTIFICATION-TYPE
STATUS current
DESCRIPTION "Airflow Fail Alarm Cleared"
::= { trapObjects 56 }


-- 1.3.6.1.4.1.9839.2.1.100.57
comp1-cct1-status-al NOTIFICATION-TYPE
STATUS current
DESCRIPTION "Compressor 1 Circuit 1 Status Alarm"
::= { trapObjects 57 }


-- 1.3.6.1.4.1.9839.2.1.100.58
comp1-cct1-status-al-clear NOTIFICATION-TYPE
STATUS current
DESCRIPTION "Compressor 1 Circuit 1 Status Alarm Cleared"
::= { trapObjects 58 }


-- 1.3.6.1.4.1.9839.2.1.100.59
comp2-cct1-status-al NOTIFICATION-TYPE
STATUS current
DESCRIPTION "Compressor 2 Circuit 1 Status Alarm"
::= { trapObjects 59 }


-- 1.3.6.1.4.1.9839.2.1.100.60
comp2-cct1-status-al-clear NOTIFICATION-TYPE
STATUS current
DESCRIPTION "Compressor 2 Circuit 1 Status Alarm Cleared"
::= { trapObjects 60 }


-- 1.3.6.1.4.1.9839.2.1.100.61
comp1-cct2-status-al NOTIFICATION-TYPE
STATUS current
DESCRIPTION "Compressor 1 Circuit 2 Status Alarm"
::= { trapObjects 61 }


-- 1.3.6.1.4.1.9839.2.1.100.62
comp1-cct2-status-al-clear NOTIFICATION-TYPE
STATUS current
DESCRIPTION "Compressor 1 Circuit 2 Status Alarm Cleared"
::= { trapObjects 62 }


-- 1.3.6.1.4.1.9839.2.1.100.63
comp2-cct2-status-al NOTIFICATION-TYPE
STATUS current
DESCRIPTION "Compressor 2 Circuit 2 Status Alarm"
::= { trapObjects 63 }


-- 1.3.6.1.4.1.9839.2.1.100.64
comp2-cct2-status-al-clear NOTIFICATION-TYPE
STATUS current
DESCRIPTION "Compressor 2 Circuit 2 Status Alarm Cleared"
::= { trapObjects 64 }


-- 1.3.6.1.4.1.9839.2.1.100.65
filter-change-al NOTIFICATION-TYPE
STATUS current
DESCRIPTION "Filter Change Alarm"
::= { trapObjects 65 }


-- 1.3.6.1.4.1.9839.2.1.100.66
filter-change-al-clear NOTIFICATION-TYPE
STATUS current
DESCRIPTION "Filter Change Alarm Cleared"
::= { trapObjects 66 }


-- 1.3.6.1.4.1.9839.2.1.100.69
water-flood-al NOTIFICATION-TYPE
STATUS current
DESCRIPTION "Water Flood Alarm"
::= { trapObjects 69 }


-- 1.3.6.1.4.1.9839.2.1.100.70
water-flood-al-clear NOTIFICATION-TYPE
STATUS current
DESCRIPTION "Water Flood Alarm Cleared"
::= { trapObjects 70 }


-- 1.3.6.1.4.1.9839.2.1.100.71
fire-smoke-al NOTIFICATION-TYPE
STATUS current
DESCRIPTION "Fire Smoke Alarm"
::= { trapObjects 71 }


-- 1.3.6.1.4.1.9839.2.1.100.72
fire-smoke-al-clear NOTIFICATION-TYPE
STATUS current
DESCRIPTION "Fire Smoke Alarm Cleared"
::= { trapObjects 72 }


-- 1.3.6.1.4.1.9839.2.1.100.73
overheat-cutout-al NOTIFICATION-TYPE
STATUS current
DESCRIPTION "Overheat Cutout Alarm"
::= { trapObjects 73 }


-- 1.3.6.1.4.1.9839.2.1.100.74
overheat-cutout-al-clear NOTIFICATION-TYPE
STATUS current
DESCRIPTION "Overheat Cutout Alarm Cleared"
::= { trapObjects 74 }


-- 1.3.6.1.4.1.9839.2.1.100.75
low-press-cct1-al NOTIFICATION-TYPE
STATUS current
DESCRIPTION "Low Pressure Circuit 1 Alarm"
::= { trapObjects 75 }


-- 1.3.6.1.4.1.9839.2.1.100.76
low-press-cct1-al-clear NOTIFICATION-TYPE
STATUS current
DESCRIPTION "Low Pressure Circuit 1 Alarm Cleared"
::= { trapObjects 76 }


-- 1.3.6.1.4.1.9839.2.1.100.77
low-press-cct2-al NOTIFICATION-TYPE
STATUS current
DESCRIPTION "Low Pressure Circuit 2 Alarm"
::= { trapObjects 77 }


-- 1.3.6.1.4.1.9839.2.1.100.78
low-press-cct2-al-clear NOTIFICATION-TYPE
STATUS current
DESCRIPTION "Low Pressure Circuit 2 Alarm Cleared"
::= { trapObjects 78 }


-- 1.3.6.1.4.1.9839.2.1.100.93
high-ret-temp-al NOTIFICATION-TYPE
STATUS current
DESCRIPTION "High Return Temperature Alarm"
::= { trapObjects 93 }


-- 1.3.6.1.4.1.9839.2.1.100.94
high-ret-temp-al-clear NOTIFICATION-TYPE
STATUS current
DESCRIPTION "High Return Temperature Alarm Cleared"
::= { trapObjects 94 }

-- 1.3.6.1.4.1.9839.2.1.100.95
low-ret-temp-al NOTIFICATION-TYPE
STATUS current
DESCRIPTION "Low Return Temperature Alarm"
::= { trapObjects 95 }


-- 1.3.6.1.4.1.9839.2.1.100.96
low-ret-temp-al-clear NOTIFICATION-TYPE
STATUS current
DESCRIPTION "Low Return Temperature Alarm Cleared"
::= { trapObjects 96 }

-- 1.3.6.1.4.1.9839.2.1.100.101
high-press-cct1-al NOTIFICATION-TYPE
STATUS current
DESCRIPTION "High Pressure Circuit 1 Alarm"
::= { trapObjects 101 }


-- 1.3.6.1.4.1.9839.2.1.100.102
high-press-cct1-al-clear NOTIFICATION-TYPE
STATUS current
DESCRIPTION "High Pressure Circuit 1 Alarm Cleared"
::= { trapObjects 102 }


-- 1.3.6.1.4.1.9839.2.1.100.103
high-press-cct2-al NOTIFICATION-TYPE
STATUS current
DESCRIPTION "High Pressure Circuit 2 Alarm"
::= { trapObjects 103 }


-- 1.3.6.1.4.1.9839.2.1.100.104
high-press-cct2-al-clear NOTIFICATION-TYPE
STATUS current
DESCRIPTION "High Pressure Circuit 2 Alarm Cleared"
::= { trapObjects 104 }


-- 1.3.6.1.4.1.9839.2.1.100.105
clock-al NOTIFICATION-TYPE
STATUS current
DESCRIPTION "Controller Clock Alarm"
::= { trapObjects 105 }


-- 1.3.6.1.4.1.9839.2.1.100.106
clock-al-clear NOTIFICATION-TYPE
STATUS current
DESCRIPTION "Controller Clock Alarm Cleared"
::= { trapObjects 106 }


-- 1.3.6.1.4.1.9839.2.1.100.111
plan-dis-al NOTIFICATION-TYPE
STATUS current
DESCRIPTION "pLAN Disconnected Alarm"
::= { trapObjects 111 }


-- 1.3.6.1.4.1.9839.2.1.100.112
plan-dis-al-clear NOTIFICATION-TYPE
STATUS current
DESCRIPTION "pLAN Disconnected Alarm Cleared"
::= { trapObjects 112 }


-- 1.3.6.1.4.1.9839.2.1.100.113
humidity-al NOTIFICATION-TYPE
STATUS current
DESCRIPTION "pLAN Disconnected Alarm"
::= { trapObjects 113 }


-- 1.3.6.1.4.1.9839.2.1.100.114
humidity-al-clear NOTIFICATION-TYPE
STATUS current
DESCRIPTION "Humidity Alarm Cleared"
::= { trapObjects 114 }

-- 1.3.6.1.4.1.9839.2.1.100.117
non-critical-al NOTIFICATION-TYPE
STATUS current
DESCRIPTION "Non Critical Alarm"
::= { trapObjects 117 }


-- 1.3.6.1.4.1.9839.2.1.100.118
non-critical-al-clear NOTIFICATION-TYPE
STATUS current
DESCRIPTION "Non Critical Alarm Cleared"
::= { trapObjects 118 }


-- 1.3.6.1.4.1.9839.2.1.100.119
critical-al NOTIFICATION-TYPE
STATUS current
DESCRIPTION "Critical Alarm"
::= { trapObjects 119 }


-- 1.3.6.1.4.1.9839.2.1.100.120
critical-al-clear NOTIFICATION-TYPE
STATUS current
DESCRIPTION "Critical Alarm Cleared"
::= { trapObjects 120 }


-- 1.3.6.1.4.1.9839.2.1.100.123
high-dis-temp-cct1-al NOTIFICATION-TYPE
STATUS current
DESCRIPTION "High Discharge Temperature Circuit 1 Alarm"
::= { trapObjects 123 }


-- 1.3.6.1.4.1.9839.2.1.100.124
high-dis-temp-cct1-al-clear NOTIFICATION-TYPE
STATUS current
DESCRIPTION "High Discharge Temperature Circuit 1 Alarm Cleared"
::= { trapObjects 124 }


-- 1.3.6.1.4.1.9839.2.1.100.125
high-dis-temp-cct2-al NOTIFICATION-TYPE
STATUS current
DESCRIPTION "High Discharge Temperature Circuit 2 Alarm"
::= { trapObjects 125 }


-- 1.3.6.1.4.1.9839.2.1.100.126
high-dis-temp-cct2-al-clear NOTIFICATION-TYPE
STATUS current
DESCRIPTION "High Discharge Temperature Circuit 2 Alarm Cleared"
::= { trapObjects 126 }


	END

--
-- 63172573-81822241-SmartCool.MIB
--
