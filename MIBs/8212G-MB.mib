--------------------------------------------------------------------------------
-- PDI SNMP MIB FOR 8212G
-- M4G,BCMS 
--
-- Revision 1.00
-- January 17, 2008
--------------------------------------------------------------------------------
D8212G-MB DEFINITIONS ::= BEGIN

IMPORTS
  org, iso, dod, internet, directory, mgmt, experimental, private, enterprises
    FROM RFC-1155-SMI 
  OBJECT-TYPE
    FROM RFC-1212
  DisplayString
    FROM RFC-1213;

--------------------------------------------------------------------------------
-- OID hierarchy
--------------------------------------------------------------------------------

pdi         	OBJECT IDENTIFIER ::= { enterprises 24436 }
 products    	OBJECT IDENTIFIER ::= { pdi 1 }
  remdisplay	OBJECT IDENTIFIER ::= { products 5 }
   d8212g		OBJECT IDENTIFIER ::= { remdisplay 2 }
    display		OBJECT IDENTIFIER ::= { d8212g 1 }
    device1		OBJECT IDENTIFIER ::= { d8212g 2 }
     pdu1		OBJECT IDENTIFIER ::= { device1 4 }
    device2		OBJECT IDENTIFIER ::= { d8212g 3 }
     bcmsplus1	OBJECT IDENTIFIER ::= { device2 2 }
    displaytraps  OBJECT IDENTIFIER ::= { d8212g 14 }

--------------------------------------------------------------------------------
-- Display register values
--------------------------------------------------------------------------------

display-alarm
	OBJECT-TYPE
	SYNTAX  INTEGER
	ACCESS  read-only
	STATUS  mandatory
	DESCRIPTION "alarm register
				bit 0:	Communications Error 1
				bit 1:	Communications Error 2
				bit 2:	Communications Error 3
				bit 3:	Communications Error 4
				bit 4:	Communications Error 5
				bit 5:	Communications Error 6
				bit 6:	Communications Error 7
				bit 7:	Communications Error 8
				bit 8:	Communications Error 9
				bit 9:	Communications Error 10
				bit 10:	Communications Error 11
				bit 11:	Communications Error 12
				bit 12:	Summary Alarm
				bits 13 – 15: Always read as 0"
		::= { display 1 }

display-banner-1
	OBJECT-TYPE
	SYNTAX  INTEGER
	ACCESS  read-write
	STATUS  mandatory
	DESCRIPTION "Banner Character 1"
		::= { display 2 }

display-banner-2
	OBJECT-TYPE
	SYNTAX  INTEGER
	ACCESS  read-write
	STATUS  mandatory
	DESCRIPTION "Banner Character 2"
		::= { display 3 }

display-banner-3
	OBJECT-TYPE
	SYNTAX  INTEGER
	ACCESS  read-write
	STATUS  mandatory
	DESCRIPTION "Banner Character 3"
		::= { display 4 }

display-banner-4
	OBJECT-TYPE
	SYNTAX  INTEGER
	ACCESS  read-write
	STATUS  mandatory
	DESCRIPTION "Banner Character 4"
		::= { display 5 }

display-banner-5
	OBJECT-TYPE
	SYNTAX  INTEGER
	ACCESS  read-write
	STATUS  mandatory
	DESCRIPTION "Banner Character 5"
		::= { display 6 }

display-banner-6
	OBJECT-TYPE
	SYNTAX  INTEGER
	ACCESS  read-write
	STATUS  mandatory
	DESCRIPTION "Banner Character 6"
		::= { display 7 }

display-banner-7
	OBJECT-TYPE
	SYNTAX  INTEGER
	ACCESS  read-write
	STATUS  mandatory
	DESCRIPTION "Banner Character 7"
		::= { display 8 }

display-banner-8
	OBJECT-TYPE
	SYNTAX  INTEGER
	ACCESS  read-write
	STATUS  mandatory
	DESCRIPTION "Banner Character 8"
		::= { display 9 }

display-banner-9
	OBJECT-TYPE
	SYNTAX  INTEGER
	ACCESS  read-write
	STATUS  mandatory
	DESCRIPTION "Banner Character 9"
		::= { display 10 }

display-banner-10
	OBJECT-TYPE
	SYNTAX  INTEGER
	ACCESS  read-write
	STATUS  mandatory
	DESCRIPTION "Banner Character 10"
		::= { display 11 }

display-banner-11
	OBJECT-TYPE
	SYNTAX  INTEGER
	ACCESS  read-write
	STATUS  mandatory
	DESCRIPTION "Banner Character 11"
		::= { display 12 }

display-banner-12
	OBJECT-TYPE
	SYNTAX  INTEGER
	ACCESS  read-write
	STATUS  mandatory
	DESCRIPTION "Banner Character 12"
		::= { display 13 }

display-banner-13
	OBJECT-TYPE
	SYNTAX  INTEGER
	ACCESS  read-write
	STATUS  mandatory
	DESCRIPTION "Banner Character 13"
		::= { display 14 }

display-banner-14
	OBJECT-TYPE
	SYNTAX  INTEGER
	ACCESS  read-write
	STATUS  mandatory
	DESCRIPTION "Banner Character 14"
		::= { display 15 }

display-banner-15
	OBJECT-TYPE
	SYNTAX  INTEGER
	ACCESS  read-write
	STATUS  mandatory
	DESCRIPTION "Banner Character 15"
		::= { display 16 }

display-banner-16
	OBJECT-TYPE
	SYNTAX  INTEGER
	ACCESS  read-write
	STATUS  mandatory
	DESCRIPTION "Banner Character 16"
		::= { display 17 }

display-banner-17
	OBJECT-TYPE
	SYNTAX  INTEGER
	ACCESS  read-write
	STATUS  mandatory
	DESCRIPTION "Banner Character 17"
		::= { display 18 }

display-banner-18
	OBJECT-TYPE
	SYNTAX  INTEGER
	ACCESS  read-write
	STATUS  mandatory
	DESCRIPTION "Banner Character 18"
		::= { display 19 }

display-banner-19
	OBJECT-TYPE
	SYNTAX  INTEGER
	ACCESS  read-write
	STATUS  mandatory
	DESCRIPTION "Banner Character 19"
		::= { display 20 }

display-banner-20
	OBJECT-TYPE
	SYNTAX  INTEGER
	ACCESS  read-write
	STATUS  mandatory
	DESCRIPTION "Banner Character 20"
		::= { display 21 }

display-banner-21
	OBJECT-TYPE
	SYNTAX  INTEGER
	ACCESS  read-write
	STATUS  mandatory
	DESCRIPTION "Banner Character 21"
		::= { display 22 }

display-banner-22
	OBJECT-TYPE
	SYNTAX  INTEGER
	ACCESS  read-write
	STATUS  mandatory
	DESCRIPTION "Banner Character 22"
		::= { display 23 }

display-banner-23
	OBJECT-TYPE
	SYNTAX  INTEGER
	ACCESS  read-write
	STATUS  mandatory
	DESCRIPTION "Banner Character 23"
		::= { display 24 }

display-banner-24
	OBJECT-TYPE
	SYNTAX  INTEGER
	ACCESS  read-write
	STATUS  mandatory
	DESCRIPTION "Banner Character 24"
		::= { display 25 }

display-banner-25
	OBJECT-TYPE
	SYNTAX  INTEGER
	ACCESS  read-write
	STATUS  mandatory
	DESCRIPTION "Banner Character 25"
		::= { display 26 }

display-banner-26
	OBJECT-TYPE
	SYNTAX  INTEGER
	ACCESS  read-write
	STATUS  mandatory
	DESCRIPTION "Banner Character 26"
		::= { display 27 }

display-banner-27
	OBJECT-TYPE
	SYNTAX  INTEGER
	ACCESS  read-write
	STATUS  mandatory
	DESCRIPTION "Banner Character 27"
		::= { display 28 }

display-banner-28
	OBJECT-TYPE
	SYNTAX  INTEGER
	ACCESS  read-write
	STATUS  mandatory
	DESCRIPTION "Banner Character 28"
		::= { display 29 }

display-banner-29
	OBJECT-TYPE
	SYNTAX  INTEGER
	ACCESS  read-write
	STATUS  mandatory
	DESCRIPTION "Banner Character 29"
		::= { display 30 }

display-banner-30
	OBJECT-TYPE
	SYNTAX  INTEGER
	ACCESS  read-write
	STATUS  mandatory
	DESCRIPTION "Banner Character 30"
		::= { display 31 }

display-banner-31
	OBJECT-TYPE
	SYNTAX  INTEGER
	ACCESS  read-write
	STATUS  mandatory
	DESCRIPTION "Banner Character 31"
		::= { display 32 }

display-banner-32
	OBJECT-TYPE
	SYNTAX  INTEGER
	ACCESS  read-write
	STATUS  mandatory
	DESCRIPTION "Banner Character 32"
		::= { display 33 }

display-banner-33
	OBJECT-TYPE
	SYNTAX  INTEGER
	ACCESS  read-write
	STATUS  mandatory
	DESCRIPTION "Banner Character 33"
		::= { display 34 }

display-banner-34
	OBJECT-TYPE
	SYNTAX  INTEGER
	ACCESS  read-write
	STATUS  mandatory
	DESCRIPTION "Banner Character 34"
		::= { display 35 }

display-banner-35
	OBJECT-TYPE
	SYNTAX  INTEGER
	ACCESS  read-write
	STATUS  mandatory
	DESCRIPTION "Banner Character 35"
		::= { display 36 }

display-banner-36
	OBJECT-TYPE
	SYNTAX  INTEGER
	ACCESS  read-write
	STATUS  mandatory
	DESCRIPTION "Banner Character 36"
		::= { display 37 }

display-banner-37
	OBJECT-TYPE
	SYNTAX  INTEGER
	ACCESS  read-write
	STATUS  mandatory
	DESCRIPTION "Banner Character 37"
		::= { display 38 }

display-banner-38
	OBJECT-TYPE
	SYNTAX  INTEGER
	ACCESS  read-write
	STATUS  mandatory
	DESCRIPTION "Banner Character 38"
		::= { display 39 }

display-banner-39
	OBJECT-TYPE
	SYNTAX  INTEGER
	ACCESS  read-write
	STATUS  mandatory
	DESCRIPTION "Banner Character 39"
		::= { display 40 }

display-banner-40
	OBJECT-TYPE
	SYNTAX  INTEGER
	ACCESS  read-write
	STATUS  mandatory
	DESCRIPTION "Banner Character 40"
		::= { display 41 }

display-version
	OBJECT-TYPE
	SYNTAX  INTEGER
	ACCESS  read-only
	STATUS  mandatory
	DESCRIPTION "Software Version"
		::= { display 42 }

display-revision
	OBJECT-TYPE
	SYNTAX  INTEGER
	ACCESS  read-only
	STATUS  mandatory
	DESCRIPTION "Software Revision"
		::= { display 43 }

display-number-devices
	OBJECT-TYPE
	SYNTAX  INTEGER
	ACCESS  read-write
	STATUS  mandatory
	DESCRIPTION "Number of Devices"
		::= { display 44 }

display-device-1-options
	OBJECT-TYPE
	SYNTAX  INTEGER
	ACCESS  read-write
	STATUS  mandatory
	DESCRIPTION "Device 1 options - same for all devices below
			BCMS PLUS:        bit 0:	Panel Size (0=225, 1=400) 
bit 1:	CB Zero Current Alarms(1 = enable)
bit 2:	CB Warnings (1 = enable)
bit 3:	CB Alarms (1 = enable)
bit 4:	Total Currents Alarms(1 = enable)
bit 5:	Voltage Alarms(1 = enable)
bits 6 – 15: Always read as 0

			BCMS CB:		bit 1:	Total Currents Alarms(1 = enable)
bit 2:	Voltage Alarms(1 = enable)
bits 3 – 15: Always read as 0"
		::= { display 45 }

display-device-2-options
	OBJECT-TYPE
	SYNTAX  INTEGER
	ACCESS  read-write
	STATUS  mandatory
	DESCRIPTION "Device 2 options"
		::= { display 46 }

display-device-3-options
	OBJECT-TYPE
	SYNTAX  INTEGER
	ACCESS  read-write
	STATUS  mandatory
	DESCRIPTION "Device 3 options"
		::= { display 47 }

display-device-4-options
	OBJECT-TYPE
	SYNTAX  INTEGER
	ACCESS  read-write
	STATUS  mandatory
	DESCRIPTION "Device 4 options"
		::= { display 48 }

display-device-5-options
	OBJECT-TYPE
	SYNTAX  INTEGER
	ACCESS  read-write
	STATUS  mandatory
	DESCRIPTION "Device 5 options"
		::= { display 49 }

display-device-6-options
	OBJECT-TYPE
	SYNTAX  INTEGER
	ACCESS  read-write
	STATUS  mandatory
	DESCRIPTION "Device 6 options"
		::= { display 50 }

display-device-7-options
	OBJECT-TYPE
	SYNTAX  INTEGER
	ACCESS  read-write
	STATUS  mandatory
	DESCRIPTION "Device 7 options"
		::= { display 51 }

display-device-8-options
	OBJECT-TYPE
	SYNTAX  INTEGER
	ACCESS  read-write
	STATUS  mandatory
	DESCRIPTION "Device 8 options"
		::= { display 52 }

display-device-9-options
	OBJECT-TYPE
	SYNTAX  INTEGER
	ACCESS  read-write
	STATUS  mandatory
	DESCRIPTION "Device 9 options"
		::= { display 53 }

display-device-10-options
	OBJECT-TYPE
	SYNTAX  INTEGER
	ACCESS  read-write
	STATUS  mandatory
	DESCRIPTION "Device 10 options"
		::= { display 54 }

display-device-11-options
	OBJECT-TYPE
	SYNTAX  INTEGER
	ACCESS  read-write
	STATUS  mandatory
	DESCRIPTION "Device 11 options"
		::= { display 55 }

display-device-12-options
	OBJECT-TYPE
	SYNTAX  INTEGER
	ACCESS  read-write
	STATUS  mandatory
	DESCRIPTION "Device 12 options"
		::= { display 56 }

--------------------------------------------------------------------------------
-- PDU register values
--------------------------------------------------------------------------------

pdu1-input-voltage-1-ab
	OBJECT-TYPE
	SYNTAX  INTEGER
	ACCESS  read-only
	STATUS  mandatory
	DESCRIPTION "Input Voltage 1 AB"
		::= { pdu1 1 }

pdu1-input-voltage-1-bc
	OBJECT-TYPE
	SYNTAX  INTEGER
	ACCESS  read-only
	STATUS  mandatory
	DESCRIPTION "Input Voltage 1 BC"
		::= { pdu1 2 }

pdu1-input-voltage-1-ca
	OBJECT-TYPE
	SYNTAX  INTEGER
	ACCESS  read-only
	STATUS  mandatory
	DESCRIPTION "Input Voltage 1 CA"
		::= { pdu1 3 }

pdu1-input-voltage-1-frequency
	OBJECT-TYPE
	SYNTAX  INTEGER
	ACCESS  read-only
	STATUS  mandatory
	DESCRIPTION "Input Voltage 1 Frequency"
		::= { pdu1 4 }

pdu1-input-voltage-1-ab-thd
	OBJECT-TYPE
	SYNTAX  INTEGER
	ACCESS  read-only
	STATUS  mandatory
	DESCRIPTION "Input Voltage 1 AB THD"
		::= { pdu1 5 }

pdu1-input-voltage-1-bc-thd
	OBJECT-TYPE
	SYNTAX  INTEGER
	ACCESS  read-only
	STATUS  mandatory
	DESCRIPTION "Input Voltage 1 BC THD"
		::= { pdu1 6 }

pdu1-input-voltage-1-ca-thd
	OBJECT-TYPE
	SYNTAX  INTEGER
	ACCESS  read-only
	STATUS  mandatory
	DESCRIPTION "Input Voltage 1 CA THD"
		::= { pdu1 7 }

pdu1-input-voltage-2-ab
	OBJECT-TYPE
	SYNTAX  INTEGER
	ACCESS  read-only
	STATUS  mandatory
	DESCRIPTION "Input Voltage 2 AB - optional second input"
		::= { pdu1 8 }

pdu1-input-voltage-2-bc
	OBJECT-TYPE
	SYNTAX  INTEGER
	ACCESS  read-only
	STATUS  mandatory
	DESCRIPTION "Input Voltage 2 BC - optional second input"
		::= { pdu1 9 }

pdu1-input-voltage-2-ca
	OBJECT-TYPE
	SYNTAX  INTEGER
	ACCESS  read-only
	STATUS  mandatory
	DESCRIPTION "Input Voltage 2 CA - optional second input"
		::= { pdu1 10 }

pdu1-input-voltage-2-frequency
	OBJECT-TYPE
	SYNTAX  INTEGER
	ACCESS  read-only
	STATUS  mandatory
	DESCRIPTION "Input Voltage 2 Frequency - optional second input"
		::= { pdu1 11 }

pdu1-phase-difference-v1-to-v2
	OBJECT-TYPE
	SYNTAX  INTEGER
	ACCESS  read-only
	STATUS  mandatory
	DESCRIPTION "Phase difference input V1 to Input V2 - optional second input"
		::= { pdu1 12 }

pdu1-input-voltage-2-ab-thd
	OBJECT-TYPE
	SYNTAX  INTEGER
	ACCESS  read-only
	STATUS  mandatory
	DESCRIPTION "Input Voltage 2 AB THD - optional second input"
		::= { pdu1 13 }

pdu1-input-voltage-2-bc-thd
	OBJECT-TYPE
	SYNTAX  INTEGER
	ACCESS  read-only
	STATUS  mandatory
	DESCRIPTION "Input Voltage 2 BC THD - optional second input"
		::= { pdu1 14 }

pdu1-input-voltage-2-ca-thd
	OBJECT-TYPE
	SYNTAX  INTEGER
	ACCESS  read-only
	STATUS  mandatory
	DESCRIPTION "Input Voltage 2 CA THD - optional second input"
		::= { pdu1 15 }

pdu1-output-voltage-1-ab
	OBJECT-TYPE
	SYNTAX  INTEGER
	ACCESS  read-only
	STATUS  mandatory
	DESCRIPTION "Output Voltage 1 AB"
		::= { pdu1 16 }

pdu1-output-voltage-1-bc
	OBJECT-TYPE
	SYNTAX  INTEGER
	ACCESS  read-only
	STATUS  mandatory
	DESCRIPTION "Output Voltage 1 BC"
		::= { pdu1 17 }

pdu1-output-voltage-1-ca
	OBJECT-TYPE
	SYNTAX  INTEGER
	ACCESS  read-only
	STATUS  mandatory
	DESCRIPTION "Output Voltage 1 CA"
		::= { pdu1 18 }

pdu1-output-voltage-1-an
	OBJECT-TYPE
	SYNTAX  INTEGER
	ACCESS  read-only
	STATUS  mandatory
	DESCRIPTION "Output Voltage 1 AN"
		::= { pdu1 19 }

pdu1-output-voltage-1-bn
	OBJECT-TYPE
	SYNTAX  INTEGER
	ACCESS  read-only
	STATUS  mandatory
	DESCRIPTION "Output Voltage 1 BN"
		::= { pdu1 20 }

pdu1-output-voltage-1-cn
	OBJECT-TYPE
	SYNTAX  INTEGER
	ACCESS  read-only
	STATUS  mandatory
	DESCRIPTION "Output Voltage 1 CN"
		::= { pdu1 21 }

pdu1-output-current-1-a
	OBJECT-TYPE
	SYNTAX  INTEGER
	ACCESS  read-only
	STATUS  mandatory
	DESCRIPTION "Output Current 1 A"
		::= { pdu1 22 }

pdu1-output-current-1-b
	OBJECT-TYPE
	SYNTAX  INTEGER
	ACCESS  read-only
	STATUS  mandatory
	DESCRIPTION "Output Current 1 B"
		::= { pdu1 23 }

pdu1-output-current-1-c
	OBJECT-TYPE
	SYNTAX  INTEGER
	ACCESS  read-only
	STATUS  mandatory
	DESCRIPTION "Output Current 1 C"
		::= { pdu1 24 }

pdu1-output-1-kw-a
	OBJECT-TYPE
	SYNTAX  INTEGER
	ACCESS  read-only
	STATUS  mandatory
	DESCRIPTION "Output 1 KW A"
		::= { pdu1 25 }

pdu1-output-1-kw-b
	OBJECT-TYPE
	SYNTAX  INTEGER
	ACCESS  read-only
	STATUS  mandatory
	DESCRIPTION "Output 1 KW B"
		::= { pdu1 26 }

pdu1-output-1-kw-c
	OBJECT-TYPE
	SYNTAX  INTEGER
	ACCESS  read-only
	STATUS  mandatory
	DESCRIPTION "Output 1 KW C"
		::= { pdu1 27 }

pdu1-output-1-kw-total
	OBJECT-TYPE
	SYNTAX  INTEGER
	ACCESS  read-only
	STATUS  mandatory
	DESCRIPTION "Output 1 KW Total"
		::= { pdu1 28 }

pdu1-output-1-kva-a
	OBJECT-TYPE
	SYNTAX  INTEGER
	ACCESS  read-only
	STATUS  mandatory
	DESCRIPTION "Output 1 KVA A"
		::= { pdu1 29 }

pdu1-output-1-kva-b
	OBJECT-TYPE
	SYNTAX  INTEGER
	ACCESS  read-only
	STATUS  mandatory
	DESCRIPTION "Output 1 KVA B"
		::= { pdu1 30 }

pdu1-output-1-kva-c
	OBJECT-TYPE
	SYNTAX  INTEGER
	ACCESS  read-only
	STATUS  mandatory
	DESCRIPTION "Output 1 KVA C"
		::= { pdu1 31 }

pdu1-output-1-kva-total
	OBJECT-TYPE
	SYNTAX  INTEGER
	ACCESS  read-only
	STATUS  mandatory
	DESCRIPTION "Output 1 KVA Total"
		::= { pdu1 32 }

pdu1-output-1-kvar-a
	OBJECT-TYPE
	SYNTAX  INTEGER
	ACCESS  read-only
	STATUS  mandatory
	DESCRIPTION "Output 1 KVAR A"
		::= { pdu1 33 }

pdu1-output-1-kvar-b
	OBJECT-TYPE
	SYNTAX  INTEGER
	ACCESS  read-only
	STATUS  mandatory
	DESCRIPTION "Output 1 KVAR B"
		::= { pdu1 34 }

pdu1-output-1-kvar-c
	OBJECT-TYPE
	SYNTAX  INTEGER
	ACCESS  read-only
	STATUS  mandatory
	DESCRIPTION "Output 1 KVAR C"
		::= { pdu1 35 }

pdu1-output-1-kvar-total
	OBJECT-TYPE
	SYNTAX  INTEGER
	ACCESS  read-only
	STATUS  mandatory
	DESCRIPTION "Output 1 KVAR Total"
		::= { pdu1 36 }

pdu1-output-1-pf-a
	OBJECT-TYPE
	SYNTAX  INTEGER
	ACCESS  read-only
	STATUS  mandatory
	DESCRIPTION "Output 1 PF A"
		::= { pdu1 37 }

pdu1-output-1-pf-b
	OBJECT-TYPE
	SYNTAX  INTEGER
	ACCESS  read-only
	STATUS  mandatory
	DESCRIPTION "Output 1 PF B"
		::= { pdu1 38 }

pdu1-output-1-pf-c
	OBJECT-TYPE
	SYNTAX  INTEGER
	ACCESS  read-only
	STATUS  mandatory
	DESCRIPTION "Output 1 PF C"
		::= { pdu1 39 }

pdu1-output-1-kwh-low
	OBJECT-TYPE
	SYNTAX  INTEGER
	ACCESS  read-only
	STATUS  mandatory
	DESCRIPTION "Output 1 KWH low"
		::= { pdu1 40 }

pdu1-output-1-kwh-high
	OBJECT-TYPE
	SYNTAX  INTEGER
	ACCESS  read-only
	STATUS  mandatory
	DESCRIPTION "Output 1 KWH high"
		::= { pdu1 41 }

pdu1-neutral-current
	OBJECT-TYPE
	SYNTAX  INTEGER
	ACCESS  read-only
	STATUS  mandatory
	DESCRIPTION "Output Neutral current"
		::= { pdu1 42 }

pdu1-ground-current
	OBJECT-TYPE
	SYNTAX  INTEGER
	ACCESS  read-only
	STATUS  mandatory
	DESCRIPTION "Output Ground Current"
		::= { pdu1 43 }

pdu1-output-voltage-2-ab
	OBJECT-TYPE
	SYNTAX  INTEGER
	ACCESS  read-only
	STATUS  mandatory
	DESCRIPTION "Output Voltage 2 AB - Optional Second Output"
		::= { pdu1 44 }

pdu1-output-voltage-2-bc
	OBJECT-TYPE
	SYNTAX  INTEGER
	ACCESS  read-only
	STATUS  mandatory
	DESCRIPTION "Output Voltage 2 BC - Optional Second Output"
		::= { pdu1 45 }

pdu1-output-voltage-2-ca
	OBJECT-TYPE
	SYNTAX  INTEGER
	ACCESS  read-only
	STATUS  mandatory
	DESCRIPTION "Output Voltage 2 CA - Optional Second Output"
		::= { pdu1 46 }

pdu1-output-voltage-2-an
	OBJECT-TYPE
	SYNTAX  INTEGER
	ACCESS  read-only
	STATUS  mandatory
	DESCRIPTION "Output Voltage 2 AN - Optional Second Output"
		::= { pdu1 47 }

pdu1-output-voltage-2-bn
	OBJECT-TYPE
	SYNTAX  INTEGER
	ACCESS  read-only
	STATUS  mandatory
	DESCRIPTION "Output Voltage 2 BN - Optional Second Output"
		::= { pdu1 48 }

pdu1-output-voltage-2-cn
	OBJECT-TYPE
	SYNTAX  INTEGER
	ACCESS  read-only
	STATUS  mandatory
	DESCRIPTION "Output Voltage 2 CN - Optional Second Output"
		::= { pdu1 49 }

pdu1-output-current-2-a
	OBJECT-TYPE
	SYNTAX  INTEGER
	ACCESS  read-only
	STATUS  mandatory
	DESCRIPTION "Output Current 2 A - Optional Second Output"
		::= { pdu1 50 }

pdu1-output-current-2-b
	OBJECT-TYPE
	SYNTAX  INTEGER
	ACCESS  read-only
	STATUS  mandatory
	DESCRIPTION "Output Current 2 B - Optional Second Output"
		::= { pdu1 51 }

pdu1-output-current-2-c
	OBJECT-TYPE
	SYNTAX  INTEGER
	ACCESS  read-only
	STATUS  mandatory
	DESCRIPTION "Output Current 2 C - Optional Second Output"
		::= { pdu1 52 }

pdu1-output-2-kw-a
	OBJECT-TYPE
	SYNTAX  INTEGER
	ACCESS  read-only
	STATUS  mandatory
	DESCRIPTION "Output KW A - Optional Second Output"
		::= { pdu1 53 }

pdu1-output-2-kw-b
	OBJECT-TYPE
	SYNTAX  INTEGER
	ACCESS  read-only
	STATUS  mandatory
	DESCRIPTION "Output KW B - Optional Second Output"
		::= { pdu1 54 }

pdu1-output-2-kw-c
	OBJECT-TYPE
	SYNTAX  INTEGER
	ACCESS  read-only
	STATUS  mandatory
	DESCRIPTION "Output KW C - Optional Second Output"
		::= { pdu1 55 }

pdu1-output-2-kw-total
	OBJECT-TYPE
	SYNTAX  INTEGER
	ACCESS  read-only
	STATUS  mandatory
	DESCRIPTION "Output KW Total - Optional Second Output"
		::= { pdu1 56 }

pdu1-output-2-kva-a
	OBJECT-TYPE
	SYNTAX  INTEGER
	ACCESS  read-only
	STATUS  mandatory
	DESCRIPTION "Output KVA A - Optional Second Output"
		::= { pdu1 57 }

pdu1-output-2-kva-b
	OBJECT-TYPE
	SYNTAX  INTEGER
	ACCESS  read-only
	STATUS  mandatory
	DESCRIPTION "Output KVA B - Optional Second Output"
		::= { pdu1 58 }

pdu1-output-2-kva-c
	OBJECT-TYPE
	SYNTAX  INTEGER
	ACCESS  read-only
	STATUS  mandatory
	DESCRIPTION "Output KVA C - Optional Second Output"
		::= { pdu1 59 }

pdu1-output-2-kva-total
	OBJECT-TYPE
	SYNTAX  INTEGER
	ACCESS  read-only
	STATUS  mandatory
	DESCRIPTION "Output KVA Total - Optional Second Output"
		::= { pdu1 60 }

pdu1-output-2-kvar-a
	OBJECT-TYPE
	SYNTAX  INTEGER
	ACCESS  read-only
	STATUS  mandatory
	DESCRIPTION "Output KVAR A - Optional Second Output"
		::= { pdu1 61 }

pdu1-output-2-kvar-b
	OBJECT-TYPE
	SYNTAX  INTEGER
	ACCESS  read-only
	STATUS  mandatory
	DESCRIPTION "Output KVAR B - Optional Second Output"
		::= { pdu1 62 }

pdu1-output-2-kvar-c
	OBJECT-TYPE
	SYNTAX  INTEGER
	ACCESS  read-only
	STATUS  mandatory
	DESCRIPTION "Output KVAR C - Optional Second Output"
		::= { pdu1 63 }

pdu1-output-2-kvar-total
	OBJECT-TYPE
	SYNTAX  INTEGER
	ACCESS  read-only
	STATUS  mandatory
	DESCRIPTION "Output KVAR Total - Optional Second Output"
		::= { pdu1 64 }

pdu1-output-2-pf-a
	OBJECT-TYPE
	SYNTAX  INTEGER
	ACCESS  read-only
	STATUS  mandatory
	DESCRIPTION "Output PF A - Optional Second Output"
		::= { pdu1 65 }

pdu1-output-2-pf-b
	OBJECT-TYPE
	SYNTAX  INTEGER
	ACCESS  read-only
	STATUS  mandatory
	DESCRIPTION "Output PF B - Optional Second Output"
		::= { pdu1 66 }

pdu1-output-2-pf-c
	OBJECT-TYPE
	SYNTAX  INTEGER
	ACCESS  read-only
	STATUS  mandatory
	DESCRIPTION "Output PF C - Optional Second Output"
		::= { pdu1 67 }

pdu1-output-2-kwh-low
	OBJECT-TYPE
	SYNTAX  INTEGER
	ACCESS  read-only
	STATUS  mandatory
	DESCRIPTION "Output KWH low - Optional Second Output"
		::= { pdu1 68 }

pdu1-output-2-kwh-high
	OBJECT-TYPE
	SYNTAX  INTEGER
	ACCESS  read-only
	STATUS  mandatory
	DESCRIPTION "Output KWH high - Optional Second Output"
		::= { pdu1 69 }

pdu1-summary-alarms
	OBJECT-TYPE
	SYNTAX  INTEGER
	ACCESS  read-only
	STATUS  mandatory
	DESCRIPTION "Summary Alarm
                   bit 0: Voltage Alarm
                   bit 1: Current Alarm
                   bit 2: Building Alarm
                   bit 3: Digital Alarm
                   bit 4: EPO
                   bit 5: Remote EPO
                   bit 6: Thermal Overtemp
                   bit 7: Thermal Hightemp
                   bit 8: Phase Rotation
                   bits 9-15 not used"
		::= { pdu1 70 }

pdu1-summary-alarms-latched
	OBJECT-TYPE
	SYNTAX  INTEGER
	ACCESS  read-write
	STATUS  mandatory
	DESCRIPTION "Summary Alarm Latched
                    - Same bits as Summary Alarm"
		::= { pdu1 71 }

pdu1-input-voltage-1-alarms
	OBJECT-TYPE
	SYNTAX  INTEGER
	ACCESS  read-only
	STATUS  mandatory
	DESCRIPTION "Input Voltage 1 Alarms
                   bit 0: Volt AB High
                   bit 1: Volt AB Low
                   bit 2: Volt BC High
                   bit 3: Volt BC Low
                   bit 4: Volt CA High
                   bit 5: Volt CA Low
                   bits 6-15 not used"
		::= { pdu1 72 }

pdu1-input-voltage-1-alarms-latched
	OBJECT-TYPE
	SYNTAX  INTEGER
	ACCESS  read-write
	STATUS  mandatory
	DESCRIPTION "Input Voltage 1 Alarms Latched
                    - Same bits as Input Voltage 1 Alarms"
		::= { pdu1 73 }

pdu1-input-voltage-2-alarms
	OBJECT-TYPE
	SYNTAX  INTEGER
	ACCESS  read-only
	STATUS  mandatory
	DESCRIPTION "Input Voltage 2 Alarms
                   bit 0: Volt AB High
                   bit 1: Volt AB Low
                   bit 2: Volt BC High
                   bit 3: Volt BC Low
                   bit 4: Volt CA High
                   bit 5: Volt CA Low
                   bits 6-15 not used"
		::= { pdu1 74 }

pdu1-input-voltage-2-alarms-latched
	OBJECT-TYPE
	SYNTAX  INTEGER
	ACCESS  read-write
	STATUS  mandatory
	DESCRIPTION "Input Voltage 2 Alarms Latched
                    - Same bits as Input Voltage 2 Alarms"
		::= { pdu1 75 }

pdu1-output-voltage-1-alarms
	OBJECT-TYPE
	SYNTAX  INTEGER
	ACCESS  read-only
	STATUS  mandatory
	DESCRIPTION "Output Voltage 1 Alarms
                   bit 0: Volt AB High
                   bit 1: Volt AB Low
                   bit 2: Volt BC High
                   bit 3: Volt BC Low
                   bit 4: Volt CA High
                   bit 5: Volt CA Low
                   bit 6: Volt AN High
                   bit 7: Volt AN Low
                   bit 8: Volt BN High
                   bit 9: Volt BN Low
                   bit 10: Volt CN High
                   bit 11: Volt CN Low
                   bits 12-15 not used"
		::= { pdu1 76 }

pdu1-output-voltage-1-alarms-latched
	OBJECT-TYPE
	SYNTAX  INTEGER
	ACCESS  read-write
	STATUS  mandatory
	DESCRIPTION "Output Voltage 1 Alarms Latched
                    - Same bits as Output Voltage 1 Alarms"
		::= { pdu1 77 }

pdu1-output-voltage-2-alarms
	OBJECT-TYPE
	SYNTAX  INTEGER
	ACCESS  read-only
	STATUS  mandatory
	DESCRIPTION "Output Voltage 1 Alarms
			  - Optional Second Output
                   bit 0: Volt AB High
                   bit 1: Volt AB Low
                   bit 2: Volt BC High
                   bit 3: Volt BC Low
                   bit 4: Volt CA High
                   bit 5: Volt CA Low
                   bit 6: Volt AN High
                   bit 7: Volt AN Low
                   bit 8: Volt BN High
                   bit 9: Volt BN Low
                   bit 10: Volt CN High
                   bit 11: Volt CN Low
                   bits 12-15 not used"
		::= { pdu1 78 }

pdu1-output-voltage-2-alarms-latched
	OBJECT-TYPE
	SYNTAX  INTEGER
	ACCESS  read-write
	STATUS  mandatory
	DESCRIPTION "Output Voltage 2 Alarms Latched
                    - Same bits as Output Current 1 Alarms
                    - Optional Second Output"
		::= { pdu1 79 }

pdu1-output-current-1-alarms
	OBJECT-TYPE
	SYNTAX  INTEGER
	ACCESS  read-only
	STATUS  mandatory
	DESCRIPTION "Output Current 1 Alarms
                   bit 0: Current A High
                   bit 1: Current A Low
                   bit 2: Current B High
                   bit 3: Current B Low
                   bit 4: Current C High
                   bit 5: Current C Low
                   bit 6: Neutral Current High
                   bit 7: Neutral Current Low
                   bit 8: Ground Current High
                   bit 9: Ground Current Low
                   bits 10-15 not used"
		::= { pdu1 80 }

pdu1-output-current-1-alarms-latched
	OBJECT-TYPE
	SYNTAX  INTEGER
	ACCESS  read-write
	STATUS  mandatory
	DESCRIPTION "Output Current 2 Alarms Latched
                    - Same bits as Output Voltage 2 Alarms"
		::= { pdu1 81 }

pdu1-output-current-2-alarms
	OBJECT-TYPE
	SYNTAX  INTEGER
	ACCESS  read-only
	STATUS  mandatory
	DESCRIPTION "Output Current 2 Alarms
			  - Optional Second Output
                   bit 0: Current A High
                   bit 1: Current A Low
                   bit 2: Current B High
                   bit 3: Current B Low
                   bit 4: Current C High
                   bit 5: Current C Low
                   bits 6-15 not used"
		::= { pdu1 82 }

pdu1-output-current-2-alarms-latched
	OBJECT-TYPE
	SYNTAX  INTEGER
	ACCESS  read-write
	STATUS  mandatory
	DESCRIPTION "Output Current 2 Alarms Latched
                    - Same bits as Output Current 2 Alarms
                    - Optional Second Output"
		::= { pdu1 83 }

pdu1-output-power-1-alarms
	OBJECT-TYPE
	SYNTAX  INTEGER
	ACCESS  read-only
	STATUS  mandatory
	DESCRIPTION "Output Power 1 Alarms
                   bit 0: KW A High
                   bit 1: KW B High
                   bit 2: KW C High
                   bit 3: KW Total High
                   bit 4: KVA A High
                   bit 5: KVA B High
                   bit 6: KVA C High
                   bit 7: KVA Total High
                   bits 8-15 not used"
		::= { pdu1 84 }

pdu1-output-power-1-alarms-latched
	OBJECT-TYPE
	SYNTAX  INTEGER
	ACCESS  read-write
	STATUS  mandatory
	DESCRIPTION "Output Power 1 Alarms Latched
                    - Same bits as Output Power 1 Alarms"
		::= { pdu1 85 }

pdu1-output-power-2-alarms
	OBJECT-TYPE
	SYNTAX  INTEGER
	ACCESS  read-only
	STATUS  mandatory
	DESCRIPTION "Output Power 2 Alarms
                   - Optional Second Output
                   bit 0: KW A High
                   bit 1: KW B High
                   bit 2: KW C High
                   bit 3: KW Total High
                   bit 4: KVA A High
                   bit 5: KVA B High
                   bit 6: KVA C High
                   bit 7: KVA Total High
                   bits 8-15 not used"
		::= { pdu1 86 }

pdu1-output-power-2-alarms-latched
	OBJECT-TYPE
	SYNTAX  INTEGER
	ACCESS  read-write
	STATUS  mandatory
	DESCRIPTION "Output Power 2 Alarms Latched
                    - Same bits as Output Power 2 Alarms
                    - Optional Second Output"
		::= { pdu1 87 }

pdu-building-alarms
	OBJECT-TYPE
	SYNTAX  INTEGER
	ACCESS  read-only
	STATUS  mandatory
	DESCRIPTION "Building Alarms
                   bit 0: Building Alarm 1
                   bit 1: Building Alarm 2
                   bit 2: Building Alarm 3
                   bit 3: Building Alarm 4
                   bit 4: Building Alarm 5 - Optional Advanced Contractor
                   bit 5: Building Alarm 6 - Optional Advanced Contractor
                   bit 6: Building Alarm 7 - Optional Advanced Contractor
                   bit 7: Building Alarm 8 - Optional Advanced Contractor
                   bits 8-15 not used"
		::= { pdu1 88 }

pdu-building-alarms-latched
	OBJECT-TYPE
	SYNTAX  INTEGER
	ACCESS  read-write
	STATUS  mandatory
	DESCRIPTION "Building Alarms Latched
                    - Same bits as Building Alarms"
		::= { pdu1 89 }

pdu-digital-alarms
	OBJECT-TYPE
	SYNTAX  INTEGER
	ACCESS  read-only
	STATUS  mandatory
	DESCRIPTION "Digital Alarms
                   bit 0: Digital Alarm 1
                   bit 1: Digital Alarm 2
                   bit 2: Digital Alarm 3
                   bit 3: Digital Alarm 4
                   bits 4-15 not used"
		::= { pdu1 90 }

pdu-digital-alarms-latched
	OBJECT-TYPE
	SYNTAX  INTEGER
	ACCESS  read-write
	STATUS  mandatory
	DESCRIPTION "Digital Alarms Latched
                    - Same bits as Digital Alarms"
		::= { pdu1 91 }

pdu-reserver-1
	OBJECT-TYPE
	SYNTAX  INTEGER
	ACCESS  read-only
	STATUS  mandatory
	DESCRIPTION "Reserved 1"
		::= { pdu1 92 }

pdu-reserver-2
	OBJECT-TYPE
	SYNTAX  INTEGER
	ACCESS  read-only
	STATUS  mandatory
	DESCRIPTION "Reserved 2"
		::= { pdu1 93 }

pdu-reserver-3
	OBJECT-TYPE
	SYNTAX  INTEGER
	ACCESS  read-only
	STATUS  mandatory
	DESCRIPTION "Reserved 3"
		::= { pdu1 94 }

pdu-reserver-4
	OBJECT-TYPE
	SYNTAX  INTEGER
	ACCESS  read-only
	STATUS  mandatory
	DESCRIPTION "Reserved 4"
		::= { pdu1 95 }

pdu-reserver-5
	OBJECT-TYPE
	SYNTAX  INTEGER
	ACCESS  read-only
	STATUS  mandatory
	DESCRIPTION "Reserved 5"
		::= { pdu1 96 }

pdu-reserver-6
	OBJECT-TYPE
	SYNTAX  INTEGER
	ACCESS  read-only
	STATUS  mandatory
	DESCRIPTION "Reserved 6"
		::= { pdu1 97 }

pdu-reserver-7
	OBJECT-TYPE
	SYNTAX  INTEGER
	ACCESS  read-only
	STATUS  mandatory
	DESCRIPTION "Reserved 7"
		::= { pdu1 98 }

pdu-reserver-8
	OBJECT-TYPE
	SYNTAX  INTEGER
	ACCESS  read-only
	STATUS  mandatory
	DESCRIPTION "Reserved 8"
		::= { pdu1 99 }

pdu1-enable
	OBJECT-TYPE
	SYNTAX  INTEGER
	ACCESS  read-write
	STATUS  mandatory
	DESCRIPTION "Enable - Enables write to calibration and limits"
		::= { pdu1 100 }

pdu1-setup
	OBJECT-TYPE
	SYNTAX  INTEGER
	ACCESS  read-write
	STATUS  mandatory
	DESCRIPTION "setup
                   bit 0: Second output enabled
                   bit 1: Second Input enabled
                   bit 2: Advanced Contractor enabled
                   bits 3-15 not used"
		::= { pdu1 101 }

pdu1-nominal-input-voltage-1
	OBJECT-TYPE
	SYNTAX  INTEGER
	ACCESS  read-write
	STATUS  mandatory
	DESCRIPTION "Nominal Input Voltage 1"
		::= { pdu1 102 }

pdu1-nominal-output-voltage-1
	OBJECT-TYPE
	SYNTAX  INTEGER
	ACCESS  read-write
	STATUS  mandatory
	DESCRIPTION "Nominal Output Voltage 1"
		::= { pdu1 103 }

pdu1-nominal-input-output-voltage-2
	OBJECT-TYPE
	SYNTAX  INTEGER
	ACCESS  read-write
	STATUS  mandatory
	DESCRIPTION "Nominal Input/Output Voltage 2"
		::= { pdu1 104 }

pdu1-rated-output-current-1
	OBJECT-TYPE
	SYNTAX  INTEGER
	ACCESS  read-write
	STATUS  mandatory
	DESCRIPTION "Rated Output Current 1"
		::= { pdu1 105 }

pdu1-rated-output-current-2
	OBJECT-TYPE
	SYNTAX  INTEGER
	ACCESS  read-write
	STATUS  mandatory
	DESCRIPTION "Rated Output Current 2"
		::= { pdu1 106 }

pdu1-rated-neutrral-current
	OBJECT-TYPE
	SYNTAX  INTEGER
	ACCESS  read-write
	STATUS  mandatory
	DESCRIPTION "Nominal Input Voltage 1"
		::= { pdu1 107 }

pdu1-ct-ratio-output-1
	OBJECT-TYPE
	SYNTAX  INTEGER
	ACCESS  read-write
	STATUS  mandatory
	DESCRIPTION "CT Ratio Output 1"
		::= { pdu1 108 }

pdu1-ct-ratio-output-2
	OBJECT-TYPE
	SYNTAX  INTEGER
	ACCESS  read-write
	STATUS  mandatory
	DESCRIPTION "CT Ratio Output 2"
		::= { pdu1 109 }

pdu1-ct-ratio-neutral
	OBJECT-TYPE
	SYNTAX  INTEGER
	ACCESS  read-write
	STATUS  mandatory
	DESCRIPTION "CT ratio Neutral"
		::= { pdu1 110 }

pdu1-kva
	OBJECT-TYPE
	SYNTAX  INTEGER
	ACCESS  read-write
	STATUS  mandatory
	DESCRIPTION "KVA"
		::= { pdu1 111 }

pdu1-input-voltage-1-ll-high-limit
	OBJECT-TYPE
	SYNTAX  INTEGER
	ACCESS  read-write
	STATUS  mandatory
	DESCRIPTION "Input Voltage 1 LL High Limit"
		::= { pdu1 112 }

pdu1-input-voltage-1-ll-low-limit
	OBJECT-TYPE
	SYNTAX  INTEGER
	ACCESS  read-write
	STATUS  mandatory
	DESCRIPTION "Input Voltage 1 LL Low Limit"
		::= { pdu1 113 }

pdu1-frequency-v1-high-limit
	OBJECT-TYPE
	SYNTAX  INTEGER
	ACCESS  read-write
	STATUS  mandatory
	DESCRIPTION "Frequency Voltage 1 High Limit"
		::= { pdu1 114 }

pdu1-frequency-v1-low-limit
	OBJECT-TYPE
	SYNTAX  INTEGER
	ACCESS  read-write
	STATUS  mandatory
	DESCRIPTION "Frequency Voltage 1 Low Limit"
		::= { pdu1 115 }

pdu1-input-voltage-2-ll-high-limit
	OBJECT-TYPE
	SYNTAX  INTEGER
	ACCESS  read-write
	STATUS  mandatory
	DESCRIPTION "Input Voltage 2 LL High Limit - Optional Second Input"
		::= { pdu1 116 }

pdu1-input-voltage-2-ll-low-limit
	OBJECT-TYPE
	SYNTAX  INTEGER
	ACCESS  read-write
	STATUS  mandatory
	DESCRIPTION "Input Voltage 2 LL Low Limit - Optional Second Input"
		::= { pdu1 117 }

pdu1-frequency-v2-high-limit
	OBJECT-TYPE
	SYNTAX  INTEGER
	ACCESS  read-write
	STATUS  mandatory
	DESCRIPTION "Frequency Voltage 2 High Limit - Optional Second Input"
		::= { pdu1 118 }

pdu1-frequency-v2-low-limit
	OBJECT-TYPE
	SYNTAX  INTEGER
	ACCESS  read-write
	STATUS  mandatory
	DESCRIPTION "Frequency Voltage 2 Low Limit - Optional Second Input"
		::= { pdu1 119 }

pdu1-phase-input-1-and-input-2
	OBJECT-TYPE
	SYNTAX  INTEGER
	ACCESS  read-write
	STATUS  mandatory
	DESCRIPTION "Phase Input 1 and Input 2 - Optional Second Input"
		::= { pdu1 120 }

pdu1-output-voltage-1-ll-high-limit
	OBJECT-TYPE
	SYNTAX  INTEGER
	ACCESS  read-write
	STATUS  mandatory
	DESCRIPTION "Output Voltage 1 LL High Limit"
		::= { pdu1 121 }

pdu1-output-voltage-1-ll-low-limit
	OBJECT-TYPE
	SYNTAX  INTEGER
	ACCESS  read-write
	STATUS  mandatory
	DESCRIPTION "Output Voltage 1 LL Low Limit"
		::= { pdu1 122 }

pdu1-output-voltage-1-ln-high-limit
	OBJECT-TYPE
	SYNTAX  INTEGER
	ACCESS  read-write
	STATUS  mandatory
	DESCRIPTION "Output Voltage 1 LN High Limit"
		::= { pdu1 123 }

pdu1-output-voltage-1-ln-low-limit
	OBJECT-TYPE
	SYNTAX  INTEGER
	ACCESS  read-write
	STATUS  mandatory
	DESCRIPTION "Output Voltage 1 LN Low Limit"
		::= { pdu1 124 }

pdu1-output-current-1-high-limit
	OBJECT-TYPE
	SYNTAX  INTEGER
	ACCESS  read-write
	STATUS  mandatory
	DESCRIPTION "Output Current 1 High Limit"
		::= { pdu1 125 }

pdu1-output-current-1-low-limit
	OBJECT-TYPE
	SYNTAX  INTEGER
	ACCESS  read-write
	STATUS  mandatory
	DESCRIPTION "Output Current 1 Low Limit"
		::= { pdu1 126 }

pdu1-output-kw-1-high-limit
	OBJECT-TYPE
	SYNTAX  INTEGER
	ACCESS  read-write
	STATUS  mandatory
	DESCRIPTION "Output KW 1 High Limit"
		::= { pdu1 127 }

pdu1-output-kva-1-high-limit
	OBJECT-TYPE
	SYNTAX  INTEGER
	ACCESS  read-write
	STATUS  mandatory
	DESCRIPTION "Output KVA 1 High Limit"
		::= { pdu1 128 }

pdu1-output-neutral-high-limit
	OBJECT-TYPE
	SYNTAX  INTEGER
	ACCESS  read-write
	STATUS  mandatory
	DESCRIPTION "Output Neutral High Limit"
		::= { pdu1 129 }

pdu1-output-neutral-low-limit
	OBJECT-TYPE
	SYNTAX  INTEGER
	ACCESS  read-write
	STATUS  mandatory
	DESCRIPTION "Output Neutral Low Limit"
		::= { pdu1 130 }

pdu1-output-ground-high-limit
	OBJECT-TYPE
	SYNTAX  INTEGER
	ACCESS  read-write
	STATUS  mandatory
	DESCRIPTION "Output Ground High Limit"
		::= { pdu1 131 }

pdu1-output-ground-low-limit
	OBJECT-TYPE
	SYNTAX  INTEGER
	ACCESS  read-write
	STATUS  mandatory
	DESCRIPTION "Output Ground Low Limit"
		::= { pdu1 132 }

pdu1-output-voltage-2-ll-high-limit
	OBJECT-TYPE
	SYNTAX  INTEGER
	ACCESS  read-write
	STATUS  mandatory
	DESCRIPTION "Output Voltage 2 LL High Limit - Optional Second Output"
		::= { pdu1 133 }

pdu1-output-voltage-2-ll-low-limit
	OBJECT-TYPE
	SYNTAX  INTEGER
	ACCESS  read-write
	STATUS  mandatory
	DESCRIPTION "Output Voltage 2 LL Low Limit - Optional Second Output"
		::= { pdu1 134 }

pdu1-output-voltage-2-ln-high-limit
	OBJECT-TYPE
	SYNTAX  INTEGER
	ACCESS  read-write
	STATUS  mandatory
	DESCRIPTION "Output Voltage 2 LN High Limit - Optional Second Output"
		::= { pdu1 135 }

pdu1-output-voltage-2-ln-low-limit
	OBJECT-TYPE
	SYNTAX  INTEGER
	ACCESS  read-write
	STATUS  mandatory
	DESCRIPTION "Output Voltage 2 LN Low Limit - Optional Second Output"
		::= { pdu1 136 }

pdu1-output-current-2-high-limit
	OBJECT-TYPE
	SYNTAX  INTEGER
	ACCESS  read-write
	STATUS  mandatory
	DESCRIPTION "Output Current 2 High Limit"
		::= { pdu1 137 }

pdu1-output-current-2-low-limit
	OBJECT-TYPE
	SYNTAX  INTEGER
	ACCESS  read-write
	STATUS  mandatory
	DESCRIPTION "Output Current 2 Low Limit"
		::= { pdu1 138 }

pdu1-output-kw-2-high-limit
	OBJECT-TYPE
	SYNTAX  INTEGER
	ACCESS  read-write
	STATUS  mandatory
	DESCRIPTION "Output KW 2 High Limit"
		::= { pdu1 139 }

pdu1-output-kvw-2-high-limit
	OBJECT-TYPE
	SYNTAX  INTEGER
	ACCESS  read-write
	STATUS  mandatory
	DESCRIPTION "Output KVA 2 High Limit"
		::= { pdu1 140 }

pdu1-building-alarm-enable
	OBJECT-TYPE
	SYNTAX  INTEGER
	ACCESS  read-write
	STATUS  mandatory
	DESCRIPTION "Building Alarm Enable - Enable is High
			 bit 0: Building Alarm 1
			 bit 1: Building Alarm 2
			 bit 2: Building Alarm 3
			 bit 3: Building Alarm 4
			 bit 4: Building Alarm 5 - Optional Advanced Contractor
			 bit 5: Building Alarm 6 - Optional Advanced Contractor
			 bit 6: Building Alarm 7 - Optional Advanced Contractor
			 bit 7: Building Alarm 8 - Optional Advanced Contractor
			 bits 8-15: not used"
		::= { pdu1 141 }

pdu1-building-alarm-nominal
	OBJECT-TYPE
	SYNTAX  INTEGER
	ACCESS  read-write
	STATUS  mandatory
	DESCRIPTION "Building Alarm Nominal - Nominal Closed is High
			 Bits same as Building Alarm Enable"
		::= { pdu1 142 }

pdu1-digital-alarm-enable
	OBJECT-TYPE
	SYNTAX  INTEGER
	ACCESS  read-write
	STATUS  mandatory
	DESCRIPTION "Digital Alarm Enable - Enable is High
			 bit 0: Digital Alarm 1
			 bit 1: Digital Alarm 2
			 bit 2: Digital Alarm 3
			 bit 3: Digital Alarm 4
                   bits 4-15: not used"
		::= { pdu1 143 }

pdu1-digital-alarm-nominal
	OBJECT-TYPE
	SYNTAX  INTEGER
	ACCESS  read-write
	STATUS  mandatory
	DESCRIPTION "Digital Alarm Nominal - Nominal Closed is High
			 Bits same as Digital Alarm Enable"
		::= { pdu1 144 }

pdu1-building-alarm-1-name-1-2
	OBJECT-TYPE
	SYNTAX  INTEGER
	ACCESS  read-write
	STATUS  mandatory
	DESCRIPTION "Building Alarm 1 Name 1-2 - 2 characters in one integer"
		::= { pdu1 145 }

pdu1-building-alarm-1-name-3-4
	OBJECT-TYPE
	SYNTAX  INTEGER
	ACCESS  read-write
	STATUS  mandatory
	DESCRIPTION "Building Alarm 1 Name 3-4 - 2 characters in one integer"
		::= { pdu1 146 }

pdu1-building-alarm-1-name-5-6
	OBJECT-TYPE
	SYNTAX  INTEGER
	ACCESS  read-write
	STATUS  mandatory
	DESCRIPTION "Building Alarm 1 Name 5-6 - 2 characters in one integer"
		::= { pdu1 147 }

pdu1-building-alarm-1-name-7-8
	OBJECT-TYPE
	SYNTAX  INTEGER
	ACCESS  read-write
	STATUS  mandatory
	DESCRIPTION "Building Alarm 1 Name 7-8 - 2 characters in one integer"
		::= { pdu1 148 }

pdu1-building-alarm-2-name-1-2
	OBJECT-TYPE
	SYNTAX  INTEGER
	ACCESS  read-write
	STATUS  mandatory
	DESCRIPTION "Building Alarm 2 Name 1-2 - 2 characters in one integer"
		::= { pdu1 149 }

pdu1-building-alarm-2-name-3-4
	OBJECT-TYPE
	SYNTAX  INTEGER
	ACCESS  read-write
	STATUS  mandatory
	DESCRIPTION "Building Alarm 2 Name 3-4 - 2 characters in one integer"
		::= { pdu1 150 }

pdu1-building-alarm-2-name-5-6
	OBJECT-TYPE
	SYNTAX  INTEGER
	ACCESS  read-write
	STATUS  mandatory
	DESCRIPTION "Building Alarm 2 Name 5-6 - 2 characters in one integer"
		::= { pdu1 151 }

pdu1-building-alarm-2-name-7-8
	OBJECT-TYPE
	SYNTAX  INTEGER
	ACCESS  read-write
	STATUS  mandatory
	DESCRIPTION "Building Alarm 2 Name 7-8 - 2 characters in one integer"
		::= { pdu1 152 }

pdu1-building-alarm-3-name-1-2
	OBJECT-TYPE
	SYNTAX  INTEGER
	ACCESS  read-write
	STATUS  mandatory
	DESCRIPTION "Building Alarm 3 Name 1-2 - 2 characters in one integer"
		::= { pdu1 153 }

pdu1-building-alarm-3-name-3-4
	OBJECT-TYPE
	SYNTAX  INTEGER
	ACCESS  read-write
	STATUS  mandatory
	DESCRIPTION "Building Alarm 3 Name 3-4 - 2 characters in one integer"
		::= { pdu1 154 }

pdu1-building-alarm-3-name-5-6
	OBJECT-TYPE
	SYNTAX  INTEGER
	ACCESS  read-write
	STATUS  mandatory
	DESCRIPTION "Building Alarm 3 Name 5-6 - 2 characters in one integer"
		::= { pdu1 155 }

pdu1-building-alarm-3-name-7-8
	OBJECT-TYPE
	SYNTAX  INTEGER
	ACCESS  read-write
	STATUS  mandatory
	DESCRIPTION "Building Alarm 3 Name 7-8 - 2 characters in one integer"
		::= { pdu1 156 }

pdu1-building-alarm-4-name-1-2
	OBJECT-TYPE
	SYNTAX  INTEGER
	ACCESS  read-write
	STATUS  mandatory
	DESCRIPTION "Building Alarm 4 Name 1-2 - 2 characters in one integer"
		::= { pdu1 157 }

pdu1-building-alarm-4-name-3-4
	OBJECT-TYPE
	SYNTAX  INTEGER
	ACCESS  read-write
	STATUS  mandatory
	DESCRIPTION "Building Alarm 4 Name 3-4 - 2 characters in one integer"
		::= { pdu1 158 }

pdu1-building-alarm-4-name-5-6
	OBJECT-TYPE
	SYNTAX  INTEGER
	ACCESS  read-write
	STATUS  mandatory
	DESCRIPTION "Building Alarm 4 Name 5-6 - 2 characters in one integer"
		::= { pdu1 159 }

pdu1-building-alarm-4-name-7-8
	OBJECT-TYPE
	SYNTAX  INTEGER
	ACCESS  read-write
	STATUS  mandatory
	DESCRIPTION "Building Alarm 4 Name 7-8 - 2 characters in one integer"
		::= { pdu1 160 }

pdu1-building-alarm-5-name-1-2
	OBJECT-TYPE
	SYNTAX  INTEGER
	ACCESS  read-write
	STATUS  mandatory
	DESCRIPTION "Building Alarm 5 Name 1-2 - 2 characters in one integer
                   - Optional Advanced Contractor"
		::= { pdu1 161 }

pdu1-building-alarm-5-name-3-4
	OBJECT-TYPE
	SYNTAX  INTEGER
	ACCESS  read-write
	STATUS  mandatory
	DESCRIPTION "Building Alarm 5 Name 3-4 - 2 characters in one integer
                   - Optional Advanced Contractor"
		::= { pdu1 162 }

pdu1-building-alarm-5-name-5-6
	OBJECT-TYPE
	SYNTAX  INTEGER
	ACCESS  read-write
	STATUS  mandatory
	DESCRIPTION "Building Alarm 5 Name 5-6 - 2 characters in one integer
                   - Optional Advanced Contractor"
		::= { pdu1 163 }

pdu1-building-alarm-5-name-7-8
	OBJECT-TYPE
	SYNTAX  INTEGER
	ACCESS  read-write
	STATUS  mandatory
	DESCRIPTION "Building Alarm 5 Name 7-8 - 2 characters in one integer
                   - Optional Advanced Contractor"
		::= { pdu1 164 }

pdu1-building-alarm-6-name-1-2
	OBJECT-TYPE
	SYNTAX  INTEGER
	ACCESS  read-write
	STATUS  mandatory
	DESCRIPTION "Building Alarm 5 Name 1-2 - 6 characters in one integer
                   - Optional Advanced Contractor"
		::= { pdu1 165 }

pdu1-building-alarm-6-name-3-4
	OBJECT-TYPE
	SYNTAX  INTEGER
	ACCESS  read-write
	STATUS  mandatory
	DESCRIPTION "Building Alarm 6 Name 3-4 - 2 characters in one integer
                   - Optional Advanced Contractor"
		::= { pdu1 166 }

pdu1-building-alarm-6-name-5-6
	OBJECT-TYPE
	SYNTAX  INTEGER
	ACCESS  read-write
	STATUS  mandatory
	DESCRIPTION "Building Alarm 6 Name 5-6 - 2 characters in one integer
                   - Optional Advanced Contractor"
		::= { pdu1 167 }

pdu1-building-alarm-6-name-7-8
	OBJECT-TYPE
	SYNTAX  INTEGER
	ACCESS  read-write
	STATUS  mandatory
	DESCRIPTION "Building Alarm 6 Name 7-8 - 2 characters in one integer
                   - Optional Advanced Contractor"
		::= { pdu1 168 }

pdu1-building-alarm-7-name-1-2
	OBJECT-TYPE
	SYNTAX  INTEGER
	ACCESS  read-write
	STATUS  mandatory
	DESCRIPTION "Building Alarm 7 Name 1-2 - 2 characters in one integer
                   - Optional Advanced Contractor"
		::= { pdu1 169 }

pdu1-building-alarm-7-name-3-4
	OBJECT-TYPE
	SYNTAX  INTEGER
	ACCESS  read-write
	STATUS  mandatory
	DESCRIPTION "Building Alarm 7 Name 3-4 - 2 characters in one integer
                   - Optional Advanced Contractor"
		::= { pdu1 170 }

pdu1-building-alarm-7-name-5-6
	OBJECT-TYPE
	SYNTAX  INTEGER
	ACCESS  read-write
	STATUS  mandatory
	DESCRIPTION "Building Alarm 7 Name 5-6 - 2 characters in one integer
                   - Optional Advanced Contractor"
		::= { pdu1 171 }

pdu1-building-alarm-7-name-7-8
	OBJECT-TYPE
	SYNTAX  INTEGER
	ACCESS  read-write
	STATUS  mandatory
	DESCRIPTION "Building Alarm 7 Name 7-8 - 2 characters in one integer
                   - Optional Advanced Contractor"
		::= { pdu1 172 }

pdu1-building-alarm-8-name-1-2
	OBJECT-TYPE
	SYNTAX  INTEGER
	ACCESS  read-write
	STATUS  mandatory
	DESCRIPTION "Building Alarm 8 Name 1-2 - 2 characters in one integer
                   - Optional Advanced Contractor"
		::= { pdu1 173 }

pdu1-building-alarm-8-name-3-4
	OBJECT-TYPE
	SYNTAX  INTEGER
	ACCESS  read-write
	STATUS  mandatory
	DESCRIPTION "Building Alarm 8 Name 3-4 - 2 characters in one integer
                   - Optional Advanced Contractor"
		::= { pdu1 174 }

pdu1-building-alarm-8-name-5-6
	OBJECT-TYPE
	SYNTAX  INTEGER
	ACCESS  read-write
	STATUS  mandatory
	DESCRIPTION "Building Alarm 8 Name 5-6 - 2 characters in one integer
                   - Optional Advanced Contractor"
		::= { pdu1 175 }

pdu1-building-alarm-8-name-7-8
	OBJECT-TYPE
	SYNTAX  INTEGER
	ACCESS  read-write
	STATUS  mandatory
	DESCRIPTION "Building Alarm 8 Name 7-8 - 2 characters in one integer
                   - Optional Advanced Contractor"
		::= { pdu1 176 }

pdu1-digital-alarm-1-name-1-2
	OBJECT-TYPE
	SYNTAX  INTEGER
	ACCESS  read-write
	STATUS  mandatory
	DESCRIPTION "Digital Alarm 1 Name 1-2 - 2 characters in one integer"
		::= { pdu1 177 }

pdu1-digital-alarm-1-name-3-4
	OBJECT-TYPE
	SYNTAX  INTEGER
	ACCESS  read-write
	STATUS  mandatory
	DESCRIPTION "Digital Alarm 1 Name 3-4 - 2 characters in one integer"
		::= { pdu1 178 }

pdu1-digital-alarm-1-name-5-6
	OBJECT-TYPE
	SYNTAX  INTEGER
	ACCESS  read-write
	STATUS  mandatory
	DESCRIPTION "Digital Alarm 1 Name 5-6 - 2 characters in one integer"
		::= { pdu1 179 }

pdu1-digital-alarm-1-name-7-8
	OBJECT-TYPE
	SYNTAX  INTEGER
	ACCESS  read-write
	STATUS  mandatory
	DESCRIPTION "Digital Alarm 1 Name 7-8 - 2 characters in one integer"
		::= { pdu1 180 }

pdu1-digital-alarm-2-name-1-2
	OBJECT-TYPE
	SYNTAX  INTEGER
	ACCESS  read-write
	STATUS  mandatory
	DESCRIPTION "Digital Alarm 2 Name 1-2 - 2 characters in one integer"
		::= { pdu1 181 }

pdu1-digital-alarm-2-name-3-4
	OBJECT-TYPE
	SYNTAX  INTEGER
	ACCESS  read-write
	STATUS  mandatory
	DESCRIPTION "Digital Alarm 2 Name 3-4 - 2 characters in one integer"
		::= { pdu1 182 }

pdu1-digital-alarm-2-name-5-6
	OBJECT-TYPE
	SYNTAX  INTEGER
	ACCESS  read-write
	STATUS  mandatory
	DESCRIPTION "Digital Alarm 2 Name 5-6 - 2 characters in one integer"
		::= { pdu1 183 }

pdu1-digital-alarm-2-name-7-8
	OBJECT-TYPE
	SYNTAX  INTEGER
	ACCESS  read-write
	STATUS  mandatory
	DESCRIPTION "Digital Alarm 2 Name 7-8 - 2 characters in one integer"
		::= { pdu1 184 }

pdu1-digital-alarm-3-name-1-2
	OBJECT-TYPE
	SYNTAX  INTEGER
	ACCESS  read-write
	STATUS  mandatory
	DESCRIPTION "Digital Alarm 3 Name 1-2 - 2 characters in one integer"
		::= { pdu1 185 }

pdu1-digital-alarm-3-name-3-4
	OBJECT-TYPE
	SYNTAX  INTEGER
	ACCESS  read-write
	STATUS  mandatory
	DESCRIPTION "Digital Alarm 3 Name 3-4 - 2 characters in one integer"
		::= { pdu1 186 }

pdu1-digital-alarm-3-name-5-6
	OBJECT-TYPE
	SYNTAX  INTEGER
	ACCESS  read-write
	STATUS  mandatory
	DESCRIPTION "Digital Alarm 3 Name 5-6 - 2 characters in one integer"
		::= { pdu1 187 }

pdu1-digital-alarm-3-name-7-8
	OBJECT-TYPE
	SYNTAX  INTEGER
	ACCESS  read-write
	STATUS  mandatory
	DESCRIPTION "Digital Alarm 3 Name 7-8 - 2 characters in one integer"
		::= { pdu1 188 }

pdu1-digital-alarm-4-name-1-2
	OBJECT-TYPE
	SYNTAX  INTEGER
	ACCESS  read-write
	STATUS  mandatory
	DESCRIPTION "Digital Alarm 4 Name 1-2 - 2 characters in one integer"
		::= { pdu1 189 }

pdu1-digital-alarm-4-name-3-4
	OBJECT-TYPE
	SYNTAX  INTEGER
	ACCESS  read-write
	STATUS  mandatory
	DESCRIPTION "Digital Alarm 4 Name 3-4 - 2 characters in one integer"
		::= { pdu1 190 }

pdu1-digital-alarm-4-name-5-6
	OBJECT-TYPE
	SYNTAX  INTEGER
	ACCESS  read-write
	STATUS  mandatory
	DESCRIPTION "Digital Alarm 4 Name 5-6 - 2 characters in one integer"
		::= { pdu1 191 }

pdu1-digital-alarm-4-name-7-8
	OBJECT-TYPE
	SYNTAX  INTEGER
	ACCESS  read-write
	STATUS  mandatory
	DESCRIPTION "Digital Alarm 4 Name 7-8 - 2 characters in one integer"
		::= { pdu1 192 }

pdu1-relay-1-alarm-point
	OBJECT-TYPE
	SYNTAX  INTEGER
	ACCESS  read-write
	STATUS  mandatory
	DESCRIPTION "Relay 1 Alarm Point"
		::= { pdu1 193 }

pdu1-relay-2-alarm-point
	OBJECT-TYPE
	SYNTAX  INTEGER
	ACCESS  read-write
	STATUS  mandatory
	DESCRIPTION "Relay 2 Alarm Point"
		::= { pdu1 194 }

pdu1-relay-3-alarm-point
	OBJECT-TYPE
	SYNTAX  INTEGER
	ACCESS  read-write
	STATUS  mandatory
	DESCRIPTION "Relay 3 Alarm Point"
		::= { pdu1 195 }

pdu1-relay-4-alarm-point
	OBJECT-TYPE
	SYNTAX  INTEGER
	ACCESS  read-write
	STATUS  mandatory
	DESCRIPTION "Relay 4 Alarm Point"
		::= { pdu1 196 }

pdu1-relay-5-alarm-point
	OBJECT-TYPE
	SYNTAX  INTEGER
	ACCESS  read-write
	STATUS  mandatory
	DESCRIPTION "Relay 5 Alarm Point - Optional Advanced Contractor"
		::= { pdu1 197 }

pdu1-relay-6-alarm-point
	OBJECT-TYPE
	SYNTAX  INTEGER
	ACCESS  read-write
	STATUS  mandatory
	DESCRIPTION "Relay 6 Alarm Point - Optional Advanced Contractor"
		::= { pdu1 198 }

pdu1-relay-7-alarm-point
	OBJECT-TYPE
	SYNTAX  INTEGER
	ACCESS  read-write
	STATUS  mandatory
	DESCRIPTION "Relay 7 Alarm Point - Optional Advanced Contractor"
		::= { pdu1 199 }

pdu1-relay-8-alarm-point
	OBJECT-TYPE
	SYNTAX  INTEGER
	ACCESS  read-write
	STATUS  mandatory
	DESCRIPTION "Relay 8 Alarm Point - Optional Advanced Contractor"
		::= { pdu1 200 }

pdu1-relay-1-alarm-bits
	OBJECT-TYPE
	SYNTAX  INTEGER
	ACCESS  read-write
	STATUS  mandatory
	DESCRIPTION "Relay 1 Alarm Bits - Which Bits of the Alarm Points will be Alarmed"
		::= { pdu1 201 }

pdu1-relay-2-alarm-bits
	OBJECT-TYPE
	SYNTAX  INTEGER
	ACCESS  read-write
	STATUS  mandatory
	DESCRIPTION "Relay 2 Alarm Bits"
		::= { pdu1 202 }

pdu1-relay-3-alarm-bits
	OBJECT-TYPE
	SYNTAX  INTEGER
	ACCESS  read-write
	STATUS  mandatory
	DESCRIPTION "Relay 3 Alarm Bits"
		::= { pdu1 203 }

pdu1-relay-4-alarm-bits
	OBJECT-TYPE
	SYNTAX  INTEGER
	ACCESS  read-write
	STATUS  mandatory
	DESCRIPTION "Relay 4 Alarm Bits"
		::= { pdu1 204 }

pdu1-relay-5-alarm-bits
	OBJECT-TYPE
	SYNTAX  INTEGER
	ACCESS  read-write
	STATUS  mandatory
	DESCRIPTION "Relay 5 Alarm Bits - Optional Advanced Contractor"
		::= { pdu1 205 }

pdu1-relay-6-alarm-bits
	OBJECT-TYPE
	SYNTAX  INTEGER
	ACCESS  read-write
	STATUS  mandatory
	DESCRIPTION "Relay 6 Alarm Bits - Optional Advanced Contractor"
		::= { pdu1 206 }

pdu1-relay-7-alarm-bits
	OBJECT-TYPE
	SYNTAX  INTEGER
	ACCESS  read-write
	STATUS  mandatory
	DESCRIPTION "Relay 7 Alarm Bits - Optional Advanced Contractor"
		::= { pdu1 207 }

pdu1-relay-8-alarm-bits
	OBJECT-TYPE
	SYNTAX  INTEGER
	ACCESS  read-write
	STATUS  mandatory
	DESCRIPTION "Relay 8 Alarm Bits - Optional Advanced Contractor"
		::= { pdu1 208 }


--------------------------------------------------------------------------------
-- BCMSPLUS register values
--------------------------------------------------------------------------------

bcms1-cb1-current
	OBJECT-TYPE
	SYNTAX  INTEGER
	ACCESS  read-only
	STATUS  mandatory
	DESCRIPTION "CB1 Current
		     Note for all currents 1-42: 100 = 10.0 amps"
		::= { bcmsplus1 1 }
  
bcms1-cb2-current
	OBJECT-TYPE
	SYNTAX  INTEGER
	ACCESS  read-only
	STATUS  mandatory
	DESCRIPTION "CB2 Current"
		::= { bcmsplus1 2 }

bcms1-cb3-current
	OBJECT-TYPE
	SYNTAX  INTEGER
	ACCESS  read-only
	STATUS  mandatory
	DESCRIPTION "CB3 Current"
		::= { bcmsplus1 3 }

bcms1-cb4-current
	OBJECT-TYPE
	SYNTAX  INTEGER
	ACCESS  read-only
	STATUS  mandatory
	DESCRIPTION "CB4 Current"
		::= { bcmsplus1 4 }

bcms1-cb5-current
	OBJECT-TYPE
	SYNTAX  INTEGER
	ACCESS  read-only
	STATUS  mandatory
	DESCRIPTION "CB5 Current"
		::= { bcmsplus1 5 }

bcms1-cb6-current
	OBJECT-TYPE
	SYNTAX  INTEGER
	ACCESS  read-only
	STATUS  mandatory
	DESCRIPTION "CB6 Current"
		::= { bcmsplus1 6 }

bcms1-cb7-current
	OBJECT-TYPE
	SYNTAX  INTEGER
	ACCESS  read-only
	STATUS  mandatory
	DESCRIPTION "CB7 Current"
		::= { bcmsplus1 7 }

bcms1-cb8-current
	OBJECT-TYPE
	SYNTAX  INTEGER
	ACCESS  read-only
	STATUS  mandatory
	DESCRIPTION "CB8 Current"
		::= { bcmsplus1 8 }

bcms1-cb9-current
	OBJECT-TYPE
	SYNTAX  INTEGER
	ACCESS  read-only
	STATUS  mandatory
	DESCRIPTION "CB9 Current"
		::= { bcmsplus1 9 }

bcms1-cb10-current
	OBJECT-TYPE
	SYNTAX  INTEGER
	ACCESS  read-only
	STATUS  mandatory
	DESCRIPTION "CB10 Current"
		::= { bcmsplus1 10 }

bcms1-cb11-current
	OBJECT-TYPE
	SYNTAX  INTEGER
	ACCESS  read-only
	STATUS  mandatory
	DESCRIPTION "CB11 Current"
		::= { bcmsplus1 11 }
  
bcms1-cb12-current
	OBJECT-TYPE
	SYNTAX  INTEGER
	ACCESS  read-only
	STATUS  mandatory
	DESCRIPTION "CB12 Current"
		::= { bcmsplus1 12 }

bcms1-cb13-current
	OBJECT-TYPE
	SYNTAX  INTEGER
	ACCESS  read-only
	STATUS  mandatory
	DESCRIPTION "CB13 Current"
		::= { bcmsplus1 13 }

bcms1-cb14-current
	OBJECT-TYPE
	SYNTAX  INTEGER
	ACCESS  read-only
	STATUS  mandatory
	DESCRIPTION "CB14 Current"
		::= { bcmsplus1 14 }

bcms1-cb15-current
	OBJECT-TYPE
	SYNTAX  INTEGER
	ACCESS  read-only
	STATUS  mandatory
	DESCRIPTION "CB15 Current"
		::= { bcmsplus1 15 }

bcms1-cb16-current
	OBJECT-TYPE
	SYNTAX  INTEGER
	ACCESS  read-only
	STATUS  mandatory
	DESCRIPTION "CB16 Current"
		::= { bcmsplus1 16 }

bcms1-cb17-current
	OBJECT-TYPE
	SYNTAX  INTEGER
	ACCESS  read-only
	STATUS  mandatory
	DESCRIPTION "CB17 Current"
		::= { bcmsplus1 17 }

bcms1-cb18-current
	OBJECT-TYPE
	SYNTAX  INTEGER
	ACCESS  read-only
	STATUS  mandatory
	DESCRIPTION "CB18 Current"
		::= { bcmsplus1 18 }

bcms1-cb19-current
	OBJECT-TYPE
	SYNTAX  INTEGER
	ACCESS  read-only
	STATUS  mandatory
	DESCRIPTION "CB19 Current"
		::= { bcmsplus1 19 }

bcms1-cb20-current
	OBJECT-TYPE
	SYNTAX  INTEGER
	ACCESS  read-only
	STATUS  mandatory
	DESCRIPTION "CB20 Current"
		::= { bcmsplus1 20 }

bcms1-cb21-current
	OBJECT-TYPE
	SYNTAX  INTEGER
	ACCESS  read-only
	STATUS  mandatory
	DESCRIPTION "CB21 Current"
		::= { bcmsplus1 21 }
  
bcms1-cb22-current
	OBJECT-TYPE
	SYNTAX  INTEGER
	ACCESS  read-only
	STATUS  mandatory
	DESCRIPTION "CB22 Current"
		::= { bcmsplus1 22 }

bcms1-cb23-current
	OBJECT-TYPE
	SYNTAX  INTEGER
	ACCESS  read-only
	STATUS  mandatory
	DESCRIPTION "CB23 Current"
		::= { bcmsplus1 23 }

bcms1-cb24-current
	OBJECT-TYPE
	SYNTAX  INTEGER
	ACCESS  read-only
	STATUS  mandatory
	DESCRIPTION "CB24 Current"
		::= { bcmsplus1 24 }

bcms1-cb25-current
	OBJECT-TYPE
	SYNTAX  INTEGER
	ACCESS  read-only
	STATUS  mandatory
	DESCRIPTION "CB25 Current"
		::= { bcmsplus1 25 }

bcms1-cb26-current
	OBJECT-TYPE
	SYNTAX  INTEGER
	ACCESS  read-only
	STATUS  mandatory
	DESCRIPTION "CB26 Current"
		::= { bcmsplus1 26 }

bcms1-cb27-current
	OBJECT-TYPE
	SYNTAX  INTEGER
	ACCESS  read-only
	STATUS  mandatory
	DESCRIPTION "CB27 Current"
		::= { bcmsplus1 27 }

bcms1-cb28-current
	OBJECT-TYPE
	SYNTAX  INTEGER
	ACCESS  read-only
	STATUS  mandatory
	DESCRIPTION "CB28 Current"
		::= { bcmsplus1 28 }

bcms1-cb29-current
	OBJECT-TYPE
	SYNTAX  INTEGER
	ACCESS  read-only
	STATUS  mandatory
	DESCRIPTION "CB29 Current"
		::= { bcmsplus1 29 }

bcms1-cb30-current
	OBJECT-TYPE
	SYNTAX  INTEGER
	ACCESS  read-only
	STATUS  mandatory
	DESCRIPTION "CB30 Current"
		::= { bcmsplus1 30 }

bcms1-cb31-current
	OBJECT-TYPE
	SYNTAX  INTEGER
	ACCESS  read-only
	STATUS  mandatory
	DESCRIPTION "CB31 Current"
		::= { bcmsplus1 31 }
  
bcms1-cb32-current
	OBJECT-TYPE
	SYNTAX  INTEGER
	ACCESS  read-only
	STATUS  mandatory
	DESCRIPTION "CB32 Current"
		::= { bcmsplus1 32 }

bcms1-cb33-current
	OBJECT-TYPE
	SYNTAX  INTEGER
	ACCESS  read-only
	STATUS  mandatory
	DESCRIPTION "CB33 Current"
		::= { bcmsplus1 33 }

bcms1-cb34-current
	OBJECT-TYPE
	SYNTAX  INTEGER
	ACCESS  read-only
	STATUS  mandatory
	DESCRIPTION "CB34 Current"
		::= { bcmsplus1 34 }

bcms1-cb35-current
	OBJECT-TYPE
	SYNTAX  INTEGER
	ACCESS  read-only
	STATUS  mandatory
	DESCRIPTION "CB35 Current"
		::= { bcmsplus1 35 }

bcms1-cb36-current
	OBJECT-TYPE
	SYNTAX  INTEGER
	ACCESS  read-only
	STATUS  mandatory
	DESCRIPTION "CB36 Current"
		::= { bcmsplus1 36 }

bcms1-cb37-current
	OBJECT-TYPE
	SYNTAX  INTEGER
	ACCESS  read-only
	STATUS  mandatory
	DESCRIPTION "CB37 Current"
		::= { bcmsplus1 37 }

bcms1-cb38-current
	OBJECT-TYPE
	SYNTAX  INTEGER
	ACCESS  read-only
	STATUS  mandatory
	DESCRIPTION "CB38 Current"
		::= { bcmsplus1 38 }

bcms1-cb39-current
	OBJECT-TYPE
	SYNTAX  INTEGER
	ACCESS  read-only
	STATUS  mandatory
	DESCRIPTION "CB39 Current"
		::= { bcmsplus1 39 }

bcms1-cb40-current
	OBJECT-TYPE
	SYNTAX  INTEGER
	ACCESS  read-only
	STATUS  mandatory
	DESCRIPTION "CB40 Current"
		::= { bcmsplus1 40 }

bcms1-cb41-current
	OBJECT-TYPE
	SYNTAX  INTEGER
	ACCESS  read-only
	STATUS  mandatory
	DESCRIPTION "CB41 Current"
		::= { bcmsplus1 41 }
  
bcms1-cb42-current
	OBJECT-TYPE
	SYNTAX  INTEGER
	ACCESS  read-only
	STATUS  mandatory
	DESCRIPTION "CB42 Current"
		::= { bcmsplus1 42 }

bcms1-cb1-min
	OBJECT-TYPE
	SYNTAX  INTEGER
	ACCESS  read-only
	STATUS  mandatory
	DESCRIPTION "CB1 Min
		     Note for all minumum currents 1-42: 100 = 10.0 amps"
		::= { bcmsplus1 43 }

bcms1-cb2-min
	OBJECT-TYPE
	SYNTAX  INTEGER
	ACCESS  read-only
	STATUS  mandatory
	DESCRIPTION "CB2 Min"
		::= { bcmsplus1 44 }

bcms1-cb3-min
	OBJECT-TYPE
	SYNTAX  INTEGER
	ACCESS  read-only
	STATUS  mandatory
	DESCRIPTION "CB3 Min"
		::= { bcmsplus1 45 }

bcms1-cb4-min
	OBJECT-TYPE
	SYNTAX  INTEGER
	ACCESS  read-only
	STATUS  mandatory
	DESCRIPTION "CB4 Min"
		::= { bcmsplus1 46 }

bcms1-cb5-min
	OBJECT-TYPE
	SYNTAX  INTEGER
	ACCESS  read-only
	STATUS  mandatory
	DESCRIPTION "CB5 Min"
		::= { bcmsplus1 47 }

bcms1-cb6-min
	OBJECT-TYPE
	SYNTAX  INTEGER
	ACCESS  read-only
	STATUS  mandatory
	DESCRIPTION "CB6 Min"
		::= { bcmsplus1 48 }

bcms1-cb7-min
	OBJECT-TYPE
	SYNTAX  INTEGER
	ACCESS  read-only
	STATUS  mandatory
	DESCRIPTION "CB7 Min"
		::= { bcmsplus1 49 }

bcms1-cb8-min
	OBJECT-TYPE
	SYNTAX  INTEGER
	ACCESS  read-only
	STATUS  mandatory
	DESCRIPTION "CB8 Min"
		::= { bcmsplus1 50 }

bcms1-cb9-min
	OBJECT-TYPE
	SYNTAX  INTEGER
	ACCESS  read-only
	STATUS  mandatory
	DESCRIPTION "CB9 Min"
		::= { bcmsplus1 51 }
  
bcms1-cb10-min
	OBJECT-TYPE
	SYNTAX  INTEGER
	ACCESS  read-only
	STATUS  mandatory
	DESCRIPTION "CB10 Min"
		::= { bcmsplus1 52 }

bcms1-cb11-min
	OBJECT-TYPE
	SYNTAX  INTEGER
	ACCESS  read-only
	STATUS  mandatory
	DESCRIPTION "CB11 Min"
		::= { bcmsplus1 53 }

bcms1-cb12-min
	OBJECT-TYPE
	SYNTAX  INTEGER
	ACCESS  read-only
	STATUS  mandatory
	DESCRIPTION "CB12 Min"
		::= { bcmsplus1 54 }

bcms1-cb13-min
	OBJECT-TYPE
	SYNTAX  INTEGER
	ACCESS  read-only
	STATUS  mandatory
	DESCRIPTION "CB13 Min"
		::= { bcmsplus1 55 }

bcms1-cb14-min
	OBJECT-TYPE
	SYNTAX  INTEGER
	ACCESS  read-only
	STATUS  mandatory
	DESCRIPTION "CB14 Min"
		::= { bcmsplus1 56 }

bcms1-cb15-min
	OBJECT-TYPE
	SYNTAX  INTEGER
	ACCESS  read-only
	STATUS  mandatory
	DESCRIPTION "CB15 Min"
		::= { bcmsplus1 57 }

bcms1-cb16-min
	OBJECT-TYPE
	SYNTAX  INTEGER
	ACCESS  read-only
	STATUS  mandatory
	DESCRIPTION "CB16 Min"
		::= { bcmsplus1 58 }

bcms1-cb17-min
	OBJECT-TYPE
	SYNTAX  INTEGER
	ACCESS  read-only
	STATUS  mandatory
	DESCRIPTION "CB17 Min"
		::= { bcmsplus1 59 }


bcms1-cb18-min
	OBJECT-TYPE
	SYNTAX  INTEGER
	ACCESS  read-only
	STATUS  mandatory
	DESCRIPTION "CB18 Min"
		::= { bcmsplus1 60 }

bcms1-cb19-min
	OBJECT-TYPE
	SYNTAX  INTEGER
	ACCESS  read-only
	STATUS  mandatory
	DESCRIPTION "CB19 Min"
		::= { bcmsplus1 61 }
  
bcms1-cb20-min
	OBJECT-TYPE
	SYNTAX  INTEGER
	ACCESS  read-only
	STATUS  mandatory
	DESCRIPTION "CB20 Min"
		::= { bcmsplus1 62 }

bcms1-cb21-min
	OBJECT-TYPE
	SYNTAX  INTEGER
	ACCESS  read-only
	STATUS  mandatory
	DESCRIPTION "CB21 Min"
		::= { bcmsplus1 63 }

bcms1-cb22-min
	OBJECT-TYPE
	SYNTAX  INTEGER
	ACCESS  read-only
	STATUS  mandatory
	DESCRIPTION "CB22 Min"
		::= { bcmsplus1 64 }

bcms1-cb23-min
	OBJECT-TYPE
	SYNTAX  INTEGER
	ACCESS  read-only
	STATUS  mandatory
	DESCRIPTION "CB23 Min"
		::= { bcmsplus1 65 }

bcms1-cb24-min
	OBJECT-TYPE
	SYNTAX  INTEGER
	ACCESS  read-only
	STATUS  mandatory
	DESCRIPTION "CB24 Min"
		::= { bcmsplus1 66 }

bcms1-cb25-min
	OBJECT-TYPE
	SYNTAX  INTEGER
	ACCESS  read-only
	STATUS  mandatory
	DESCRIPTION "CB25 Min"
		::= { bcmsplus1 67 }

bcms1-cb26-min
	OBJECT-TYPE
	SYNTAX  INTEGER
	ACCESS  read-only
	STATUS  mandatory
	DESCRIPTION "CB26 Min"
		::= { bcmsplus1 68 }

bcms1-cb27-min
	OBJECT-TYPE
	SYNTAX  INTEGER
	ACCESS  read-only
	STATUS  mandatory
	DESCRIPTION "CB27 Min"
		::= { bcmsplus1 69 }

bcms1-cb28-min
	OBJECT-TYPE
	SYNTAX  INTEGER
	ACCESS  read-only
	STATUS  mandatory
	DESCRIPTION "CB28 Min"
		::= { bcmsplus1 70 }

bcms1-cb29-min
	OBJECT-TYPE
	SYNTAX  INTEGER
	ACCESS  read-only
	STATUS  mandatory
	DESCRIPTION "CB29 Min"
		::= { bcmsplus1 71 }
  
bcms1-cb30-min
	OBJECT-TYPE
	SYNTAX  INTEGER
	ACCESS  read-only
	STATUS  mandatory
	DESCRIPTION "CB30 Min"
		::= { bcmsplus1 72 }

bcms1-cb31-min
	OBJECT-TYPE
	SYNTAX  INTEGER
	ACCESS  read-only
	STATUS  mandatory
	DESCRIPTION "CB31 Min"
		::= { bcmsplus1 73 }

bcms1-cb32-min
	OBJECT-TYPE
	SYNTAX  INTEGER
	ACCESS  read-only
	STATUS  mandatory
	DESCRIPTION "CB32 Min"
		::= { bcmsplus1 74 }

bcms1-cb33-min
	OBJECT-TYPE
	SYNTAX  INTEGER
	ACCESS  read-only
	STATUS  mandatory
	DESCRIPTION "CB33 Min"
		::= { bcmsplus1 75 }

bcms1-cb34-min
	OBJECT-TYPE
	SYNTAX  INTEGER
	ACCESS  read-only
	STATUS  mandatory
	DESCRIPTION "CB34 Min"
		::= { bcmsplus1 76 }

bcms1-cb35-min
	OBJECT-TYPE
	SYNTAX  INTEGER
	ACCESS  read-only
	STATUS  mandatory
	DESCRIPTION "CB35 Min"
		::= { bcmsplus1 77 }

bcms1-cb36-min
	OBJECT-TYPE
	SYNTAX  INTEGER
	ACCESS  read-only
	STATUS  mandatory
	DESCRIPTION "CB36 Min"
		::= { bcmsplus1 78 }

bcms1-cb37-min
	OBJECT-TYPE
	SYNTAX  INTEGER
	ACCESS  read-only
	STATUS  mandatory
	DESCRIPTION "CB37 Min"
		::= { bcmsplus1 79 }

bcms1-cb38-min
	OBJECT-TYPE
	SYNTAX  INTEGER
	ACCESS  read-only
	STATUS  mandatory
	DESCRIPTION "CB38 Min"
		::= { bcmsplus1 80 }

bcms1-cb39-min
	OBJECT-TYPE
	SYNTAX  INTEGER
	ACCESS  read-only
	STATUS  mandatory
	DESCRIPTION "CB39 Min"
		::= { bcmsplus1 81 }
  
bcms1-cb40-min
	OBJECT-TYPE
	SYNTAX  INTEGER
	ACCESS  read-only
	STATUS  mandatory
	DESCRIPTION "CB40 Min"
		::= { bcmsplus1 82 }

bcms1-cb41-min
	OBJECT-TYPE
	SYNTAX  INTEGER
	ACCESS  read-only
	STATUS  mandatory
	DESCRIPTION "CB41 Min"
		::= { bcmsplus1 83 }

bcms1-cb42-min
	OBJECT-TYPE
	SYNTAX  INTEGER
	ACCESS  read-only
	STATUS  mandatory
	DESCRIPTION "CB42 Min"
		::= { bcmsplus1 84 }

bcms1-cb1-max
	OBJECT-TYPE
	SYNTAX  INTEGER
	ACCESS  read-only
	STATUS  mandatory
	DESCRIPTION "CB1 Max
		     Note for all maximum currents 1-42: 100 = 10.0 amps"
		::= { bcmsplus1 85 }

bcms1-cb2-max
	OBJECT-TYPE
	SYNTAX  INTEGER
	ACCESS  read-only
	STATUS  mandatory
	DESCRIPTION "CB2 Max"
		::= { bcmsplus1 86 }

bcms1-cb3-max
	OBJECT-TYPE
	SYNTAX  INTEGER
	ACCESS  read-only
	STATUS  mandatory
	DESCRIPTION "CB3 Max"
		::= { bcmsplus1 87 }

bcms1-cb4-max
	OBJECT-TYPE
	SYNTAX  INTEGER
	ACCESS  read-only
	STATUS  mandatory
	DESCRIPTION "CB4 Max"
		::= { bcmsplus1 88 }

bcms1-cb5-max
	OBJECT-TYPE
	SYNTAX  INTEGER
	ACCESS  read-only
	STATUS  mandatory
	DESCRIPTION "CB5 Max"
		::= { bcmsplus1 89 }

bcms1-cb6-max
	OBJECT-TYPE
	SYNTAX  INTEGER
	ACCESS  read-only
	STATUS  mandatory
	DESCRIPTION "CB6 Max"
		::= { bcmsplus1 90 }

bcms1-cb7-max
	OBJECT-TYPE
	SYNTAX  INTEGER
	ACCESS  read-only
	STATUS  mandatory
	DESCRIPTION "CB7 Max"
		::= { bcmsplus1 91 }
  
bcms1-cb8-max
	OBJECT-TYPE
	SYNTAX  INTEGER
	ACCESS  read-only
	STATUS  mandatory
	DESCRIPTION "CB8 Max"
		::= { bcmsplus1 92 }

bcms1-cb9-max
	OBJECT-TYPE
	SYNTAX  INTEGER
	ACCESS  read-only
	STATUS  mandatory
	DESCRIPTION "CB9 Max"
		::= { bcmsplus1 93 }

bcms1-cb10-max
	OBJECT-TYPE
	SYNTAX  INTEGER
	ACCESS  read-only
	STATUS  mandatory
	DESCRIPTION "CB10 Max"
		::= { bcmsplus1 94 }

bcms1-cb11-max
	OBJECT-TYPE
	SYNTAX  INTEGER
	ACCESS  read-only
	STATUS  mandatory
	DESCRIPTION "CB11 Max"
		::= { bcmsplus1 95 }

bcms1-cb12-max
	OBJECT-TYPE
	SYNTAX  INTEGER
	ACCESS  read-only
	STATUS  mandatory
	DESCRIPTION "CB12 Max"
		::= { bcmsplus1 96 }

bcms1-cb13-max
	OBJECT-TYPE
	SYNTAX  INTEGER
	ACCESS  read-only
	STATUS  mandatory
	DESCRIPTION "CB13 Max"
		::= { bcmsplus1 97 }

bcms1-cb14-max
	OBJECT-TYPE
	SYNTAX  INTEGER
	ACCESS  read-only
	STATUS  mandatory
	DESCRIPTION "CB14 Max"
		::= { bcmsplus1 98 }

bcms1-cb15-max
	OBJECT-TYPE
	SYNTAX  INTEGER
	ACCESS  read-only
	STATUS  mandatory
	DESCRIPTION "CB15 Max"
		::= { bcmsplus1 99 }


bcms1-cb16-max
	OBJECT-TYPE
	SYNTAX  INTEGER
	ACCESS  read-only
	STATUS  mandatory
	DESCRIPTION "CB16 Max"
		::= { bcmsplus1 100 }

bcms1-cb17-max
	OBJECT-TYPE
	SYNTAX  INTEGER
	ACCESS  read-only
	STATUS  mandatory
	DESCRIPTION "CB17 Max"
		::= { bcmsplus1 101 }
  
bcms1-cb18-max
	OBJECT-TYPE
	SYNTAX  INTEGER
	ACCESS  read-only
	STATUS  mandatory
	DESCRIPTION "CB18 Max"
		::= { bcmsplus1 102 }

bcms1-cb19-max
	OBJECT-TYPE
	SYNTAX  INTEGER
	ACCESS  read-only
	STATUS  mandatory
	DESCRIPTION "CB19 Max"
		::= { bcmsplus1 103 }

bcms1-cb20-max
	OBJECT-TYPE
	SYNTAX  INTEGER
	ACCESS  read-only
	STATUS  mandatory
	DESCRIPTION "CB20 Max"
		::= { bcmsplus1 104 }

bcms1-cb21-max
	OBJECT-TYPE
	SYNTAX  INTEGER
	ACCESS  read-only
	STATUS  mandatory
	DESCRIPTION "CB21 Max"
		::= { bcmsplus1 105 }

bcms1-cb22-max
	OBJECT-TYPE
	SYNTAX  INTEGER
	ACCESS  read-only
	STATUS  mandatory
	DESCRIPTION "CB22 Max"
		::= { bcmsplus1 106 }

bcms1-cb23-max
	OBJECT-TYPE
	SYNTAX  INTEGER
	ACCESS  read-only
	STATUS  mandatory
	DESCRIPTION "CB23 Max"
		::= { bcmsplus1 107 }

bcms1-cb24-max
	OBJECT-TYPE
	SYNTAX  INTEGER
	ACCESS  read-only
	STATUS  mandatory
	DESCRIPTION "CB24 Max"
		::= { bcmsplus1 108 }

bcms1-cb25-max
	OBJECT-TYPE
	SYNTAX  INTEGER
	ACCESS  read-only
	STATUS  mandatory
	DESCRIPTION "CB25 Max"
		::= { bcmsplus1 109 }

bcms1-cb26-max
	OBJECT-TYPE
	SYNTAX  INTEGER
	ACCESS  read-only
	STATUS  mandatory
	DESCRIPTION "CB26 Max"
		::= { bcmsplus1 110 }

bcms1-cb27-max
	OBJECT-TYPE
	SYNTAX  INTEGER
	ACCESS  read-only
	STATUS  mandatory
	DESCRIPTION "CB27 Max"
		::= { bcmsplus1 111 }
  
bcms1-cb28-max
	OBJECT-TYPE
	SYNTAX  INTEGER
	ACCESS  read-only
	STATUS  mandatory
	DESCRIPTION "CB28 Max"
		::= { bcmsplus1 112 }

bcms1-cb29-max
	OBJECT-TYPE
	SYNTAX  INTEGER
	ACCESS  read-only
	STATUS  mandatory
	DESCRIPTION "CB29 Max"
		::= { bcmsplus1 113 }

bcms1-cb30-max
	OBJECT-TYPE
	SYNTAX  INTEGER
	ACCESS  read-only
	STATUS  mandatory
	DESCRIPTION "CB30 Max"
		::= { bcmsplus1 114 }

bcms1-cb31-max
	OBJECT-TYPE
	SYNTAX  INTEGER
	ACCESS  read-only
	STATUS  mandatory
	DESCRIPTION "CB31 Max"
		::= { bcmsplus1 115 }

bcms1-cb32-max
	OBJECT-TYPE
	SYNTAX  INTEGER
	ACCESS  read-only
	STATUS  mandatory
	DESCRIPTION "CB32 Max"
		::= { bcmsplus1 116 }

bcms1-cb33-max
	OBJECT-TYPE
	SYNTAX  INTEGER
	ACCESS  read-only
	STATUS  mandatory
	DESCRIPTION "CB33 Max"
		::= { bcmsplus1 117 }

bcms1-cb34-max
	OBJECT-TYPE
	SYNTAX  INTEGER
	ACCESS  read-only
	STATUS  mandatory
	DESCRIPTION "CB34 Max"
		::= { bcmsplus1 118 }

bcms1-cb35-max
	OBJECT-TYPE
	SYNTAX  INTEGER
	ACCESS  read-only
	STATUS  mandatory
	DESCRIPTION "CB35 Max"
		::= { bcmsplus1 119 }

bcms1-cb36-max
	OBJECT-TYPE
	SYNTAX  INTEGER
	ACCESS  read-only
	STATUS  mandatory
	DESCRIPTION "CB36 Max"
		::= { bcmsplus1 120 }

bcms1-cb37-max
	OBJECT-TYPE
	SYNTAX  INTEGER
	ACCESS  read-only
	STATUS  mandatory
	DESCRIPTION "CB37 Max"
		::= { bcmsplus1 121 }
  
bcms1-cb38-max
	OBJECT-TYPE
	SYNTAX  INTEGER
	ACCESS  read-only
	STATUS  mandatory
	DESCRIPTION "CB38 Max"
		::= { bcmsplus1 122 }

bcms1-cb39-max
	OBJECT-TYPE
	SYNTAX  INTEGER
	ACCESS  read-only
	STATUS  mandatory
	DESCRIPTION "CB39 Max"
		::= { bcmsplus1 123 }

bcms1-cb40-max
	OBJECT-TYPE
	SYNTAX  INTEGER
	ACCESS  read-only
	STATUS  mandatory
	DESCRIPTION "CB40 Max"
		::= { bcmsplus1 124 }

bcms1-cb41-max
	OBJECT-TYPE
	SYNTAX  INTEGER
	ACCESS  read-only
	STATUS  mandatory
	DESCRIPTION "CB41 Max"
		::= { bcmsplus1 125 }

bcms1-cb42-max
	OBJECT-TYPE
	SYNTAX  INTEGER
	ACCESS  read-only
	STATUS  mandatory
	DESCRIPTION "CB42 Max"
		::= { bcmsplus1 126 }

bcms1-cb1-16-zero
	OBJECT-TYPE
	SYNTAX  INTEGER
	ACCESS  read-write
	STATUS  mandatory
	DESCRIPTION "CB1-16 Zero
		       Bit 0 = CB1
                   Bit 15 = CB16"
		::= { bcmsplus1 127 }

bcms1-cb17-32-zero
	OBJECT-TYPE
	SYNTAX  INTEGER
	ACCESS  read-write
	STATUS  mandatory
	DESCRIPTION "CB17-32 Zero
		       Bit 0 = CB17
                   Bit 15 = CB32"
		::= { bcmsplus1 128 }

bcms1-cb33-42-zero
	OBJECT-TYPE
	SYNTAX  INTEGER
	ACCESS  read-write
	STATUS  mandatory
	DESCRIPTION "CB33-42 Zero
		       Bit 0 = CB33
                   Bit 9 = CB42
                   Bits 10-25 not used"
		::= { bcmsplus1 129 }

bcms1-cb1-16-warning
	OBJECT-TYPE
	SYNTAX  INTEGER
	ACCESS  read-write
	STATUS  mandatory
	DESCRIPTION "CB1-16 Warning
		       Bit 0 = CB1
                   Bit 15 = CB16"
		::= { bcmsplus1 130 }

bcms1-cb17-32-warning
	OBJECT-TYPE
	SYNTAX  INTEGER
	ACCESS  read-write
	STATUS  mandatory
	DESCRIPTION "CB17-32 Warning
		       Bit 0 = CB17
                   Bit 15 = CB32"
		::= { bcmsplus1 131 }
  
bcms1-cb33-42-warning
	OBJECT-TYPE
	SYNTAX  INTEGER
	ACCESS  read-write
	STATUS  mandatory
	DESCRIPTION "CB33-42 Warning
		       Bit 0 = CB33
                   Bit 9 = CB42
                   Bits 10-25 not used"
		::= { bcmsplus1 132 }

bcms1-cb1-16-alarm
	OBJECT-TYPE
	SYNTAX  INTEGER
	ACCESS  read-write
	STATUS  mandatory
	DESCRIPTION "CB1-16 Alarm
		       Bit 0 = CB1
                   Bit 15 = CB16"
		::= { bcmsplus1 133 }

bcms1-cb17-32-alarm
	OBJECT-TYPE
	SYNTAX  INTEGER
	ACCESS  read-write
	STATUS  mandatory
	DESCRIPTION "CB17-32 Alarm
		       Bit 0 = CB17
                   Bit 15 = CB32"
		::= { bcmsplus1 134 }

bcms1-cb33-42-alarm
	OBJECT-TYPE
	SYNTAX  INTEGER
	ACCESS  read-write
	STATUS  mandatory
	DESCRIPTION "CB33-42 Alarm
		       Bit 0 = CB33
                   Bit 9 = CB42
                   Bits 10-25 not used"
		::= { bcmsplus1 135 }

bcms1-cb1-breaker-size
	OBJECT-TYPE
	SYNTAX  INTEGER
	ACCESS  read-write
	STATUS  mandatory
	DESCRIPTION "CB1 Breaker-Size
		     Note for all breaker sizes 1-42: 10 = 10 amps
                     Range is 10 to 100 amps"
		::= { bcmsplus1 136 }

bcms1-cb2-breaker-size
	OBJECT-TYPE
	SYNTAX  INTEGER
	ACCESS  read-write
	STATUS  mandatory
	DESCRIPTION "CB2 Breaker-Size"
		::= { bcmsplus1 137 }

bcms1-cb3-breaker-size
	OBJECT-TYPE
	SYNTAX  INTEGER
	ACCESS  read-write
	STATUS  mandatory
	DESCRIPTION "CB3 Breaker-Size"
		::= { bcmsplus1 138 }

bcms1-cb4-breaker-size
	OBJECT-TYPE
	SYNTAX  INTEGER
	ACCESS  read-write
	STATUS  mandatory
	DESCRIPTION "CB4 Breaker-Size"
		::= { bcmsplus1 139 }

bcms1-cb5-breaker-size
	OBJECT-TYPE
	SYNTAX  INTEGER
	ACCESS  read-write
	STATUS  mandatory
	DESCRIPTION "CB5 Breaker-Size"
		::= { bcmsplus1 140 }

bcms1-cb6-breaker-size
	OBJECT-TYPE
	SYNTAX  INTEGER
	ACCESS  read-write
	STATUS  mandatory
	DESCRIPTION "CB6 Breaker-Size"
		::= { bcmsplus1 141 }
  
bcms1-cb7-breaker-size
	OBJECT-TYPE
	SYNTAX  INTEGER
	ACCESS  read-write
	STATUS  mandatory
	DESCRIPTION "CB7 Breaker-Size"
		::= { bcmsplus1 142 }

bcms1-cb8-breaker-size
	OBJECT-TYPE
	SYNTAX  INTEGER
	ACCESS  read-write
	STATUS  mandatory
	DESCRIPTION "CB8 Breaker-Size"
		::= { bcmsplus1 143 }

bcms1-cb9-breaker-size
	OBJECT-TYPE
	SYNTAX  INTEGER
	ACCESS  read-write
	STATUS  mandatory
	DESCRIPTION "CB9 Breaker-Size"
		::= { bcmsplus1 144 }

bcms1-cb10-breaker-size
	OBJECT-TYPE
	SYNTAX  INTEGER
	ACCESS  read-write
	STATUS  mandatory
	DESCRIPTION "CB10 Breaker-Size"
		::= { bcmsplus1 145 }

bcms1-cb11-breaker-size
	OBJECT-TYPE
	SYNTAX  INTEGER
	ACCESS  read-write
	STATUS  mandatory
	DESCRIPTION "CB11 Breaker-Size"
		::= { bcmsplus1 146 }

bcms1-cb12-breaker-size
	OBJECT-TYPE
	SYNTAX  INTEGER
	ACCESS  read-write
	STATUS  mandatory
	DESCRIPTION "CB12 Breaker-Size"
		::= { bcmsplus1 147 }

bcms1-cb13-breaker-size
	OBJECT-TYPE
	SYNTAX  INTEGER
	ACCESS  read-write
	STATUS  mandatory
	DESCRIPTION "CB13 Breaker-Size"
		::= { bcmsplus1 148 }

bcms1-cb14-breaker-size
	OBJECT-TYPE
	SYNTAX  INTEGER
	ACCESS  read-write
	STATUS  mandatory
	DESCRIPTION "CB14 Breaker-Size"
		::= { bcmsplus1 149 }

bcms1-cb15-breaker-size
	OBJECT-TYPE
	SYNTAX  INTEGER
	ACCESS  read-write
	STATUS  mandatory
	DESCRIPTION "CB15 Breaker-Size"
		::= { bcmsplus1 150 }

bcms1-cb16-breaker-size
	OBJECT-TYPE
	SYNTAX  INTEGER
	ACCESS  read-write
	STATUS  mandatory
	DESCRIPTION "CB16 Breaker-Size"
		::= { bcmsplus1 151 }
  
bcms1-cb17-breaker-size
	OBJECT-TYPE
	SYNTAX  INTEGER
	ACCESS  read-write
	STATUS  mandatory
	DESCRIPTION "CB17 Breaker-Size"
		::= { bcmsplus1 152 }

bcms1-cb18-breaker-size
	OBJECT-TYPE
	SYNTAX  INTEGER
	ACCESS  read-write
	STATUS  mandatory
	DESCRIPTION "CB18 Breaker-Size"
		::= { bcmsplus1 153 }

bcms1-cb19-breaker-size
	OBJECT-TYPE
	SYNTAX  INTEGER
	ACCESS  read-write
	STATUS  mandatory
	DESCRIPTION "CB19 Breaker-Size"
		::= { bcmsplus1 154 }

bcms1-cb20-breaker-size
	OBJECT-TYPE
	SYNTAX  INTEGER
	ACCESS  read-write
	STATUS  mandatory
	DESCRIPTION "CB20 Breaker-Size"
		::= { bcmsplus1 155 }

bcms1-cb21-breaker-size
	OBJECT-TYPE
	SYNTAX  INTEGER
	ACCESS  read-write
	STATUS  mandatory
	DESCRIPTION "CB21 Breaker-Size"
		::= { bcmsplus1 156 }

bcms1-cb22-breaker-size
	OBJECT-TYPE
	SYNTAX  INTEGER
	ACCESS  read-write
	STATUS  mandatory
	DESCRIPTION "CB22 Breaker-Size"
		::= { bcmsplus1 157 }

bcms1-cb23-breaker-size
	OBJECT-TYPE
	SYNTAX  INTEGER
	ACCESS  read-write
	STATUS  mandatory
	DESCRIPTION "CB23 Breaker-Size"
		::= { bcmsplus1 158 }

bcms1-cb24-breaker-size
	OBJECT-TYPE
	SYNTAX  INTEGER
	ACCESS  read-write
	STATUS  mandatory
	DESCRIPTION "CB24 Breaker-Size"
		::= { bcmsplus1 159 }

bcms1-cb25-breaker-size
	OBJECT-TYPE
	SYNTAX  INTEGER
	ACCESS  read-write
	STATUS  mandatory
	DESCRIPTION "CB25 Breaker-Size"
		::= { bcmsplus1 160 }

bcms1-cb26-breaker-size
	OBJECT-TYPE
	SYNTAX  INTEGER
	ACCESS  read-write
	STATUS  mandatory
	DESCRIPTION "CB26 Breaker-Size"
		::= { bcmsplus1 161 }
  
bcms1-cb27-breaker-size
	OBJECT-TYPE
	SYNTAX  INTEGER
	ACCESS  read-write
	STATUS  mandatory
	DESCRIPTION "CB27 Breaker-Size"
		::= { bcmsplus1 162 }

bcms1-cb28-breaker-size
	OBJECT-TYPE
	SYNTAX  INTEGER
	ACCESS  read-write
	STATUS  mandatory
	DESCRIPTION "CB28 Breaker-Size"
		::= { bcmsplus1 163 }

bcms1-cb29-breaker-size
	OBJECT-TYPE
	SYNTAX  INTEGER
	ACCESS  read-write
	STATUS  mandatory
	DESCRIPTION "CB29 Breaker-Size"
		::= { bcmsplus1 164 }

bcms1-cb30-breaker-size
	OBJECT-TYPE
	SYNTAX  INTEGER
	ACCESS  read-write
	STATUS  mandatory
	DESCRIPTION "CB30 Breaker-Size"
		::= { bcmsplus1 165 }

bcms1-cb31-breaker-size
	OBJECT-TYPE
	SYNTAX  INTEGER
	ACCESS  read-write
	STATUS  mandatory
	DESCRIPTION "CB31 Breaker-Size"
		::= { bcmsplus1 166 }

bcms1-cb32-breaker-size
	OBJECT-TYPE
	SYNTAX  INTEGER
	ACCESS  read-write
	STATUS  mandatory
	DESCRIPTION "CB32 Breaker-Size"
		::= { bcmsplus1 167 }

bcms1-cb33-breaker-size
	OBJECT-TYPE
	SYNTAX  INTEGER
	ACCESS  read-write
	STATUS  mandatory
	DESCRIPTION "CB33 Breaker-Size"
		::= { bcmsplus1 168 }

bcms1-cb34-breaker-size
	OBJECT-TYPE
	SYNTAX  INTEGER
	ACCESS  read-write
	STATUS  mandatory
	DESCRIPTION "CB34 Breaker-Size"
		::= { bcmsplus1 169 }

bcms1-cb35-breaker-size
	OBJECT-TYPE
	SYNTAX  INTEGER
	ACCESS  read-write
	STATUS  mandatory
	DESCRIPTION "CB35 Breaker-Size"
		::= { bcmsplus1 170 }

bcms1-cb36-breaker-size
	OBJECT-TYPE
	SYNTAX  INTEGER
	ACCESS  read-write
	STATUS  mandatory
	DESCRIPTION "CB36 Breaker-Size"
		::= { bcmsplus1 171 }
  
bcms1-cb37-breaker-size
	OBJECT-TYPE
	SYNTAX  INTEGER
	ACCESS  read-write
	STATUS  mandatory
	DESCRIPTION "CB37 Breaker-Size"
		::= { bcmsplus1 172 }

bcms1-cb38-breaker-size
	OBJECT-TYPE
	SYNTAX  INTEGER
	ACCESS  read-write
	STATUS  mandatory
	DESCRIPTION "CB38 Breaker-Size"
		::= { bcmsplus1 173 }

bcms1-cb39-breaker-size
	OBJECT-TYPE
	SYNTAX  INTEGER
	ACCESS  read-write
	STATUS  mandatory
	DESCRIPTION "CB39 Breaker-Size"
		::= { bcmsplus1 174 }

bcms1-cb40-breaker-size
	OBJECT-TYPE
	SYNTAX  INTEGER
	ACCESS  read-write
	STATUS  mandatory
	DESCRIPTION "CB40 Breaker-Size"
		::= { bcmsplus1 175 }

bcms1-cb41-breaker-size
	OBJECT-TYPE
	SYNTAX  INTEGER
	ACCESS  read-write
	STATUS  mandatory
	DESCRIPTION "CB41 Breaker-Size"
		::= { bcmsplus1 176 }

bcms1-cb42-breaker-size
	OBJECT-TYPE
	SYNTAX  INTEGER
	ACCESS  read-write
	STATUS  mandatory
	DESCRIPTION "CB42 Breaker-Size"
		::= { bcmsplus1 177 }

bcms1-cb1-warning-threshold
	OBJECT-TYPE
	SYNTAX  INTEGER
	ACCESS  read-write
	STATUS  mandatory
	DESCRIPTION "CB1 CB1-warning-threshold
		     Note for all warning thresholds 1-42: 70 = 70% of breaker size
                     range is 0-100%"
		::= { bcmsplus1 178 }

bcms1-cb2-warning-threshold
	OBJECT-TYPE
	SYNTAX  INTEGER
	ACCESS  read-write
	STATUS  mandatory
	DESCRIPTION "CB2 Warning-Threshold"
		::= { bcmsplus1 179 }

bcms1-cb3-warning-threshold
	OBJECT-TYPE
	SYNTAX  INTEGER
	ACCESS  read-write
	STATUS  mandatory
	DESCRIPTION "CB3 Warning-Threshold"
		::= { bcmsplus1 180 }

bcms1-cb4-warning-threshold
	OBJECT-TYPE
	SYNTAX  INTEGER
	ACCESS  read-write
	STATUS  mandatory
	DESCRIPTION "CB4 Warning-Threshold"
		::= { bcmsplus1 181 }
  
bcms1-cb5-warning-threshold
	OBJECT-TYPE
	SYNTAX  INTEGER
	ACCESS  read-write
	STATUS  mandatory
	DESCRIPTION "CB5 Warning-Threshold"
		::= { bcmsplus1 182 }

bcms1-cb6-warning-threshold
	OBJECT-TYPE
	SYNTAX  INTEGER
	ACCESS  read-write
	STATUS  mandatory
	DESCRIPTION "CB6 Warning-Threshold"
		::= { bcmsplus1 183 }

bcms1-cb7-warning-threshold
	OBJECT-TYPE
	SYNTAX  INTEGER
	ACCESS  read-write
	STATUS  mandatory
	DESCRIPTION "CB7 Warning-Threshold"
		::= { bcmsplus1 184 }

bcms1-cb8-warning-threshold
	OBJECT-TYPE
	SYNTAX  INTEGER
	ACCESS  read-write
	STATUS  mandatory
	DESCRIPTION "CB8 Warning-Threshold"
		::= { bcmsplus1 185 }

bcms1-cb9-warning-threshold
	OBJECT-TYPE
	SYNTAX  INTEGER
	ACCESS  read-write
	STATUS  mandatory
	DESCRIPTION "CB9 Warning-Threshold"
		::= { bcmsplus1 186 }

bcms1-cb10-warning-threshold
	OBJECT-TYPE
	SYNTAX  INTEGER
	ACCESS  read-write
	STATUS  mandatory
	DESCRIPTION "CB10 Warning-Threshold"
		::= { bcmsplus1 187 }

bcms1-cb11-warning-threshold
	OBJECT-TYPE
	SYNTAX  INTEGER
	ACCESS  read-write
	STATUS  mandatory
	DESCRIPTION "CB11 Warning-Threshold"
		::= { bcmsplus1 188 }

bcms1-cb12-warning-threshold
	OBJECT-TYPE
	SYNTAX  INTEGER
	ACCESS  read-write
	STATUS  mandatory
	DESCRIPTION "CB12 Warning-Threshold"
		::= { bcmsplus1 189 }

bcms1-cb13-warning-threshold
	OBJECT-TYPE
	SYNTAX  INTEGER
	ACCESS  read-write
	STATUS  mandatory
	DESCRIPTION "CB13 Warning-Threshold"
		::= { bcmsplus1 190 }

bcms1-cb14-warning-threshold
	OBJECT-TYPE
	SYNTAX  INTEGER
	ACCESS  read-write
	STATUS  mandatory
	DESCRIPTION "CB14 Warning-Threshold"
		::= { bcmsplus1 191 }
  
bcms1-cb15-warning-threshold
	OBJECT-TYPE
	SYNTAX  INTEGER
	ACCESS  read-write
	STATUS  mandatory
	DESCRIPTION "CB15 Warning-Threshold"
		::= { bcmsplus1 192 }

bcms1-cb16-warning-threshold
	OBJECT-TYPE
	SYNTAX  INTEGER
	ACCESS  read-write
	STATUS  mandatory
	DESCRIPTION "CB16 Warning-Threshold"
		::= { bcmsplus1 193 }

bcms1-cb17-warning-threshold
	OBJECT-TYPE
	SYNTAX  INTEGER
	ACCESS  read-write
	STATUS  mandatory
	DESCRIPTION "CB17 Warning-Threshold"
		::= { bcmsplus1 194 }

bcms1-cb18-warning-threshold
	OBJECT-TYPE
	SYNTAX  INTEGER
	ACCESS  read-write
	STATUS  mandatory
	DESCRIPTION "CB18 Warning-Threshold"
		::= { bcmsplus1 195 }

bcms1-cb19-warning-threshold
	OBJECT-TYPE
	SYNTAX  INTEGER
	ACCESS  read-write
	STATUS  mandatory
	DESCRIPTION "CB19 Warning-Threshold"
		::= { bcmsplus1 196 }

bcms1-cb20-warning-threshold
	OBJECT-TYPE
	SYNTAX  INTEGER
	ACCESS  read-write
	STATUS  mandatory
	DESCRIPTION "CB20 Warning-Threshold"
		::= { bcmsplus1 197 }

bcms1-cb21-warning-threshold
	OBJECT-TYPE
	SYNTAX  INTEGER
	ACCESS  read-write
	STATUS  mandatory
	DESCRIPTION "CB21 Warning-Threshold"
		::= { bcmsplus1 198 }

bcms1-cb22-warning-threshold
	OBJECT-TYPE
	SYNTAX  INTEGER
	ACCESS  read-write
	STATUS  mandatory
	DESCRIPTION "CB22 Warning-Threshold"
		::= { bcmsplus1 199 }

bcms1-cb23-warning-threshold
	OBJECT-TYPE
	SYNTAX  INTEGER
	ACCESS  read-write
	STATUS  mandatory
	DESCRIPTION "CB23 Warning-Threshold"
		::= { bcmsplus1 200 }

bcms1-cb24-warning-threshold
	OBJECT-TYPE
	SYNTAX  INTEGER
	ACCESS  read-write
	STATUS  mandatory
	DESCRIPTION "CB24 Warning-Threshold"
		::= { bcmsplus1 201 }
  
bcms1-cb25-warning-threshold
	OBJECT-TYPE
	SYNTAX  INTEGER
	ACCESS  read-write
	STATUS  mandatory
	DESCRIPTION "CB25 Warning-Threshold"
		::= { bcmsplus1 202 }

bcms1-cb26-warning-threshold
	OBJECT-TYPE
	SYNTAX  INTEGER
	ACCESS  read-write
	STATUS  mandatory
	DESCRIPTION "CB26 Warning-Threshold"
		::= { bcmsplus1 203 }

bcms1-cb27-warning-threshold
	OBJECT-TYPE
	SYNTAX  INTEGER
	ACCESS  read-write
	STATUS  mandatory
	DESCRIPTION "CB27 Warning-Threshold"
		::= { bcmsplus1 204 }

bcms1-cb28-warning-threshold
	OBJECT-TYPE
	SYNTAX  INTEGER
	ACCESS  read-write
	STATUS  mandatory
	DESCRIPTION "CB28 Warning-Threshold"
		::= { bcmsplus1 205 }

bcms1-cb29-warning-threshold
	OBJECT-TYPE
	SYNTAX  INTEGER
	ACCESS  read-write
	STATUS  mandatory
	DESCRIPTION "CB29 Warning-Threshold"
		::= { bcmsplus1 206 }

bcms1-cb30-warning-threshold
	OBJECT-TYPE
	SYNTAX  INTEGER
	ACCESS  read-write
	STATUS  mandatory
	DESCRIPTION "CB30 Warning-Threshold"
		::= { bcmsplus1 207 }

bcms1-cb31-warning-threshold
	OBJECT-TYPE
	SYNTAX  INTEGER
	ACCESS  read-write
	STATUS  mandatory
	DESCRIPTION "CB31 Warning-Threshold"
		::= { bcmsplus1 208 }

bcms1-cb32-warning-threshold
	OBJECT-TYPE
	SYNTAX  INTEGER
	ACCESS  read-write
	STATUS  mandatory
	DESCRIPTION "CB32 Warning-Threshold"
		::= { bcmsplus1 209 }

bcms1-cb33-warning-threshold
	OBJECT-TYPE
	SYNTAX  INTEGER
	ACCESS  read-write
	STATUS  mandatory
	DESCRIPTION "CB33 Warning-Threshold"
		::= { bcmsplus1 210 }

bcms1-cb34-warning-threshold
	OBJECT-TYPE
	SYNTAX  INTEGER
	ACCESS  read-write
	STATUS  mandatory
	DESCRIPTION "CB34 Warning-Threshold"
		::= { bcmsplus1 211 }
  
bcms1-cb35-warning-threshold
	OBJECT-TYPE
	SYNTAX  INTEGER
	ACCESS  read-write
	STATUS  mandatory
	DESCRIPTION "CB35 Warning-Threshold"
		::= { bcmsplus1 212 }

bcms1-cb36-warning-threshold
	OBJECT-TYPE
	SYNTAX  INTEGER
	ACCESS  read-write
	STATUS  mandatory
	DESCRIPTION "CB36 Warning-Threshold"
		::= { bcmsplus1 213 }

bcms1-cb37-warning-threshold
	OBJECT-TYPE
	SYNTAX  INTEGER
	ACCESS  read-write
	STATUS  mandatory
	DESCRIPTION "CB37 Warning-Threshold"
		::= { bcmsplus1 214 }

bcms1-cb38-warning-threshold
	OBJECT-TYPE
	SYNTAX  INTEGER
	ACCESS  read-write
	STATUS  mandatory
	DESCRIPTION "CB38 Warning-Threshold"
		::= { bcmsplus1 215 }

bcms1-cb39-warning-threshold
	OBJECT-TYPE
	SYNTAX  INTEGER
	ACCESS  read-write
	STATUS  mandatory
	DESCRIPTION "CB39 Warning-Threshold"
		::= { bcmsplus1 216 }

bcms1-cb40-warning-threshold
	OBJECT-TYPE
	SYNTAX  INTEGER
	ACCESS  read-write
	STATUS  mandatory
	DESCRIPTION "CB40 Warning-Threshold"
		::= { bcmsplus1 217 }

bcms1-cb41-warning-threshold
	OBJECT-TYPE
	SYNTAX  INTEGER
	ACCESS  read-write
	STATUS  mandatory
	DESCRIPTION "CB41 Warning-Threshold"
		::= { bcmsplus1 218 }

bcms1-cb42-warning-threshold
	OBJECT-TYPE
	SYNTAX  INTEGER
	ACCESS  read-write
	STATUS  mandatory
	DESCRIPTION "CB42 Warning-Threshold"
		::= { bcmsplus1 219 }

bcms1-cb1-alarm-threshold
	OBJECT-TYPE
	SYNTAX  INTEGER
	ACCESS  read-write
	STATUS  mandatory
	DESCRIPTION "CB1 Alarm-Threshold
		     Note for all alarm thresholds 1-42: 80 = 80% of breaker size
                     range is 0-100%"
		::= { bcmsplus1 220 }


bcms1-cb2-alarm-threshold
	OBJECT-TYPE
	SYNTAX  INTEGER
	ACCESS  read-write
	STATUS  mandatory
	DESCRIPTION "CB2 Alarm-Threshold"
		::= { bcmsplus1 221 }
  
bcms1-cb3-alarm-threshold
	OBJECT-TYPE
	SYNTAX  INTEGER
	ACCESS  read-write
	STATUS  mandatory
	DESCRIPTION "CB3 Alarm-Threshold"
		::= { bcmsplus1 222 }

bcms1-cb4-alarm-threshold
	OBJECT-TYPE
	SYNTAX  INTEGER
	ACCESS  read-write
	STATUS  mandatory
	DESCRIPTION "CB4 Alarm-Threshold"
		::= { bcmsplus1 223 }

bcms1-cb5-alarm-threshold
	OBJECT-TYPE
	SYNTAX  INTEGER
	ACCESS  read-write
	STATUS  mandatory
	DESCRIPTION "CB5 Alarm-Threshold"
		::= { bcmsplus1 224 }

bcms1-cb6-alarm-threshold
	OBJECT-TYPE
	SYNTAX  INTEGER
	ACCESS  read-write
	STATUS  mandatory
	DESCRIPTION "CB6 Alarm-Threshold"
		::= { bcmsplus1 225 }

bcms1-cb7-alarm-threshold
	OBJECT-TYPE
	SYNTAX  INTEGER
	ACCESS  read-write
	STATUS  mandatory
	DESCRIPTION "CB7 Alarm-Threshold"
		::= { bcmsplus1 226 }

bcms1-cb8-alarm-threshold
	OBJECT-TYPE
	SYNTAX  INTEGER
	ACCESS  read-write
	STATUS  mandatory
	DESCRIPTION "CB8 Alarm-Threshold"
		::= { bcmsplus1 227 }

bcms1-cb9-alarm-threshold
	OBJECT-TYPE
	SYNTAX  INTEGER
	ACCESS  read-write
	STATUS  mandatory
	DESCRIPTION "CB9 Alarm-Threshold"
		::= { bcmsplus1 228 }

bcms1-cb10-alarm-threshold
	OBJECT-TYPE
	SYNTAX  INTEGER
	ACCESS  read-write
	STATUS  mandatory
	DESCRIPTION "CB10 Alarm-Threshold"
		::= { bcmsplus1 229 }

bcms1-cb11-alarm-threshold
	OBJECT-TYPE
	SYNTAX  INTEGER
	ACCESS  read-write
	STATUS  mandatory
	DESCRIPTION "CB11 Alarm-Threshold"
		::= { bcmsplus1 230 }

bcms1-cb12-alarm-threshold
	OBJECT-TYPE
	SYNTAX  INTEGER
	ACCESS  read-write
	STATUS  mandatory
	DESCRIPTION "CB12 Alarm-Threshold"
		::= { bcmsplus1 231 }
  
bcms1-cb13-alarm-threshold
	OBJECT-TYPE
	SYNTAX  INTEGER
	ACCESS  read-write
	STATUS  mandatory
	DESCRIPTION "CB13 Alarm-Threshold"
		::= { bcmsplus1 232 }

bcms1-cb14-alarm-threshold
	OBJECT-TYPE
	SYNTAX  INTEGER
	ACCESS  read-write
	STATUS  mandatory
	DESCRIPTION "CB14 Alarm-Threshold"
		::= { bcmsplus1 233 }

bcms1-cb15-alarm-threshold
	OBJECT-TYPE
	SYNTAX  INTEGER
	ACCESS  read-write
	STATUS  mandatory
	DESCRIPTION "CB15 Alarm-Threshold"
		::= { bcmsplus1 234 }

bcms1-cb16-alarm-threshold
	OBJECT-TYPE
	SYNTAX  INTEGER
	ACCESS  read-write
	STATUS  mandatory
	DESCRIPTION "CB16 Alarm-Threshold"
		::= { bcmsplus1 235 }

bcms1-cb17-alarm-threshold
	OBJECT-TYPE
	SYNTAX  INTEGER
	ACCESS  read-write
	STATUS  mandatory
	DESCRIPTION "CB17 Alarm-Threshold"
		::= { bcmsplus1 236 }

bcms1-cb18-alarm-threshold
	OBJECT-TYPE
	SYNTAX  INTEGER
	ACCESS  read-write
	STATUS  mandatory
	DESCRIPTION "CB18 Alarm-Threshold"
		::= { bcmsplus1 237 }

bcms1-cb19-alarm-threshold
	OBJECT-TYPE
	SYNTAX  INTEGER
	ACCESS  read-write
	STATUS  mandatory
	DESCRIPTION "CB19 Alarm-Threshold"
		::= { bcmsplus1 238 }

bcms1-cb20-alarm-threshold
	OBJECT-TYPE
	SYNTAX  INTEGER
	ACCESS  read-write
	STATUS  mandatory
	DESCRIPTION "CB20 Alarm-Threshold"
		::= { bcmsplus1 239 }

bcms1-cb21-alarm-threshold
	OBJECT-TYPE
	SYNTAX  INTEGER
	ACCESS  read-write
	STATUS  mandatory
	DESCRIPTION "CB21 Alarm-Threshold"
		::= { bcmsplus1 240 }

bcms1-cb22-alarm-threshold
	OBJECT-TYPE
	SYNTAX  INTEGER
	ACCESS  read-write
	STATUS  mandatory
	DESCRIPTION "CB22 Alarm-Threshold"
		::= { bcmsplus1 241 }
  
bcms1-cb23-alarm-threshold
	OBJECT-TYPE
	SYNTAX  INTEGER
	ACCESS  read-write
	STATUS  mandatory
	DESCRIPTION "CB23 Alarm-Threshold"
		::= { bcmsplus1 242 }

bcms1-cb24-alarm-threshold
	OBJECT-TYPE
	SYNTAX  INTEGER
	ACCESS  read-write
	STATUS  mandatory
	DESCRIPTION "CB24 Alarm-Threshold"
		::= { bcmsplus1 243 }

bcms1-cb25-alarm-threshold
	OBJECT-TYPE
	SYNTAX  INTEGER
	ACCESS  read-write
	STATUS  mandatory
	DESCRIPTION "CB25 Alarm-Threshold"
		::= { bcmsplus1 244 }

bcms1-cb26-alarm-threshold
	OBJECT-TYPE
	SYNTAX  INTEGER
	ACCESS  read-write
	STATUS  mandatory
	DESCRIPTION "CB26 Alarm-Threshold"
		::= { bcmsplus1 245 }

bcms1-cb27-alarm-threshold
	OBJECT-TYPE
	SYNTAX  INTEGER
	ACCESS  read-write
	STATUS  mandatory
	DESCRIPTION "CB27 Alarm-Threshold"
		::= { bcmsplus1 246 }

bcms1-cb28-alarm-threshold
	OBJECT-TYPE
	SYNTAX  INTEGER
	ACCESS  read-write
	STATUS  mandatory
	DESCRIPTION "CB28 Alarm-Threshold"
		::= { bcmsplus1 247 }

bcms1-cb29-alarm-threshold
	OBJECT-TYPE
	SYNTAX  INTEGER
	ACCESS  read-write
	STATUS  mandatory
	DESCRIPTION "CB29 Alarm-Threshold"
		::= { bcmsplus1 248 }

bcms1-cb30-alarm-threshold
	OBJECT-TYPE
	SYNTAX  INTEGER
	ACCESS  read-write
	STATUS  mandatory
	DESCRIPTION "CB30 Alarm-Threshold"
		::= { bcmsplus1 249 }

bcms1-cb31-alarm-threshold
	OBJECT-TYPE
	SYNTAX  INTEGER
	ACCESS  read-write
	STATUS  mandatory
	DESCRIPTION "CB31 Alarm-Threshold"
		::= { bcmsplus1 250 }

bcms1-cb32-alarm-threshold
	OBJECT-TYPE
	SYNTAX  INTEGER
	ACCESS  read-write
	STATUS  mandatory
	DESCRIPTION "CB32 Alarm-Threshold"
		::= { bcmsplus1 251 }
  
bcms1-cb33-alarm-threshold
	OBJECT-TYPE
	SYNTAX  INTEGER
	ACCESS  read-write
	STATUS  mandatory
	DESCRIPTION "CB33 Alarm-Threshold"
		::= { bcmsplus1 252 }

bcms1-cb34-alarm-threshold
	OBJECT-TYPE
	SYNTAX  INTEGER
	ACCESS  read-write
	STATUS  mandatory
	DESCRIPTION "CB34 Alarm-Threshold"
		::= { bcmsplus1 253 }

bcms1-cb35-alarm-threshold
	OBJECT-TYPE
	SYNTAX  INTEGER
	ACCESS  read-write
	STATUS  mandatory
	DESCRIPTION "CB35 Alarm-Threshold"
		::= { bcmsplus1 254 }

bcms1-cb36-alarm-threshold
	OBJECT-TYPE
	SYNTAX  INTEGER
	ACCESS  read-write
	STATUS  mandatory
	DESCRIPTION "CB36 Alarm-Threshold"
		::= { bcmsplus1 255 }

bcms1-cb37-alarm-threshold
	OBJECT-TYPE
	SYNTAX  INTEGER
	ACCESS  read-write
	STATUS  mandatory
	DESCRIPTION "CB37 Alarm-Threshold"
		::= { bcmsplus1 256 }

bcms1-cb38-alarm-threshold
	OBJECT-TYPE
	SYNTAX  INTEGER
	ACCESS  read-write
	STATUS  mandatory
	DESCRIPTION "CB38 Alarm-Threshold"
		::= { bcmsplus1 257 }

bcms1-cb39-alarm-threshold
	OBJECT-TYPE
	SYNTAX  INTEGER
	ACCESS  read-write
	STATUS  mandatory
	DESCRIPTION "CB39 Alarm-Threshold"
		::= { bcmsplus1 258 }

bcms1-cb40-alarm-threshold
	OBJECT-TYPE
	SYNTAX  INTEGER
	ACCESS  read-write
	STATUS  mandatory
	DESCRIPTION "CB40 Alarm-Threshold"
		::= { bcmsplus1 259 }

bcms1-cb41-alarm-threshold
	OBJECT-TYPE
	SYNTAX  INTEGER
	ACCESS  read-write
	STATUS  mandatory
	DESCRIPTION "CB41 Alarm-Threshold"
		::= { bcmsplus1 260 }

bcms1-cb42-alarm-threshold
	OBJECT-TYPE
	SYNTAX  INTEGER
	ACCESS  read-write
	STATUS  mandatory
	DESCRIPTION "CB42 Alarm-Threshold"
		::= { bcmsplus1 261 }

bcms1-cb1-warning-time-delay
	OBJECT-TYPE
	SYNTAX  INTEGER
	ACCESS  read-write
	STATUS  mandatory
	DESCRIPTION "CB1 Warning-Time-Delay
		     Note for all warning time delays 1-42: units are in seconds"                     
		::= { bcmsplus1 262 }

bcms1-cb2-warning-time-delay
	OBJECT-TYPE
	SYNTAX  INTEGER
	ACCESS  read-write
	STATUS  mandatory
	DESCRIPTION "CB2 Warning-Time-Delay"
		::= { bcmsplus1 263 }
  
bcms1-cb3-warning-time-delay
	OBJECT-TYPE
	SYNTAX  INTEGER
	ACCESS  read-write
	STATUS  mandatory
	DESCRIPTION "CB3 Warning-Time-Delay"
		::= { bcmsplus1 264 }

bcms1-cb4-warning-time-delay
	OBJECT-TYPE
	SYNTAX  INTEGER
	ACCESS  read-write
	STATUS  mandatory
	DESCRIPTION "CB4 Warning-Time-Delay"
		::= { bcmsplus1 265 }

bcms1-cb5-warning-time-delay
	OBJECT-TYPE
	SYNTAX  INTEGER
	ACCESS  read-write
	STATUS  mandatory
	DESCRIPTION "CB5 Warning-Time-Delay"
		::= { bcmsplus1 266 }

bcms1-cb6-warning-time-delay
	OBJECT-TYPE
	SYNTAX  INTEGER
	ACCESS  read-write
	STATUS  mandatory
	DESCRIPTION "CB6 Warning-Time-Delay"
		::= { bcmsplus1 267 }

bcms1-cb7-warning-time-delay
	OBJECT-TYPE
	SYNTAX  INTEGER
	ACCESS  read-write
	STATUS  mandatory
	DESCRIPTION "CB7 Warning-Time-Delay"
		::= { bcmsplus1 268 }

bcms1-cb8-warning-time-delay
	OBJECT-TYPE
	SYNTAX  INTEGER
	ACCESS  read-write
	STATUS  mandatory
	DESCRIPTION "CB8 Warning-Time-Delay"
		::= { bcmsplus1 269 }

bcms1-cb9-warning-time-delay
	OBJECT-TYPE
	SYNTAX  INTEGER
	ACCESS  read-write
	STATUS  mandatory
	DESCRIPTION "CB9 Warning-Time-Delay"
		::= { bcmsplus1 270 }

bcms1-cb10-warning-time-delay
	OBJECT-TYPE
	SYNTAX  INTEGER
	ACCESS  read-write
	STATUS  mandatory
	DESCRIPTION "CB10 Warning-Time-Delay"
		::= { bcmsplus1 271 }

bcms1-cb11-warning-time-delay
	OBJECT-TYPE
	SYNTAX  INTEGER
	ACCESS  read-write
	STATUS  mandatory
	DESCRIPTION "CB11 Warning-Time-Delay"
		::= { bcmsplus1 272 }

bcms1-cb12-warning-time-delay
	OBJECT-TYPE
	SYNTAX  INTEGER
	ACCESS  read-write
	STATUS  mandatory
	DESCRIPTION "CB12 Warning-Time-Delay"
		::= { bcmsplus1 273 }
  
bcms1-cb13-warning-time-delay
	OBJECT-TYPE
	SYNTAX  INTEGER
	ACCESS  read-write
	STATUS  mandatory
	DESCRIPTION "CB13 Warning-Time-Delay"
		::= { bcmsplus1 274 }

bcms1-cb14-warning-time-delay
	OBJECT-TYPE
	SYNTAX  INTEGER
	ACCESS  read-write
	STATUS  mandatory
	DESCRIPTION "CB14 Warning-Time-Delay"
		::= { bcmsplus1 275 }

bcms1-cb15-warning-time-delay
	OBJECT-TYPE
	SYNTAX  INTEGER
	ACCESS  read-write
	STATUS  mandatory
	DESCRIPTION "CB15 Warning-Time-Delay"
		::= { bcmsplus1 276 }

bcms1-cb16-warning-time-delay
	OBJECT-TYPE
	SYNTAX  INTEGER
	ACCESS  read-write
	STATUS  mandatory
	DESCRIPTION "CB16 Warning-Time-Delay"
		::= { bcmsplus1 277 }

bcms1-cb17-warning-time-delay
	OBJECT-TYPE
	SYNTAX  INTEGER
	ACCESS  read-write
	STATUS  mandatory
	DESCRIPTION "CB17 Warning-Time-Delay"
		::= { bcmsplus1 278 }

bcms1-cb18-warning-time-delay
	OBJECT-TYPE
	SYNTAX  INTEGER
	ACCESS  read-write
	STATUS  mandatory
	DESCRIPTION "CB18 Warning-Time-Delay"
		::= { bcmsplus1 279 }

bcms1-cb19-warning-time-delay
	OBJECT-TYPE
	SYNTAX  INTEGER
	ACCESS  read-write
	STATUS  mandatory
	DESCRIPTION "CB19 Warning-Time-Delay"
		::= { bcmsplus1 280 }

bcms1-cb20-warning-time-delay
	OBJECT-TYPE
	SYNTAX  INTEGER
	ACCESS  read-write
	STATUS  mandatory
	DESCRIPTION "CB20 Warning-Time-Delay"
		::= { bcmsplus1 281 }

bcms1-cb21-warning-time-delay
	OBJECT-TYPE
	SYNTAX  INTEGER
	ACCESS  read-write
	STATUS  mandatory
	DESCRIPTION "CB21 Warning-Time-Delay"
		::= { bcmsplus1 282 }

bcms1-cb22-warning-time-delay
	OBJECT-TYPE
	SYNTAX  INTEGER
	ACCESS  read-write
	STATUS  mandatory
	DESCRIPTION "CB22 Warning-Time-Delay"
		::= { bcmsplus1 283 }
  
bcms1-cb23-warning-time-delay
	OBJECT-TYPE
	SYNTAX  INTEGER
	ACCESS  read-write
	STATUS  mandatory
	DESCRIPTION "CB23 Warning-Time-Delay"
		::= { bcmsplus1 284 }

bcms1-cb24-warning-time-delay
	OBJECT-TYPE
	SYNTAX  INTEGER
	ACCESS  read-write
	STATUS  mandatory
	DESCRIPTION "CB24 Warning-Time-Delay"
		::= { bcmsplus1 285 }

bcms1-cb25-warning-time-delay
	OBJECT-TYPE
	SYNTAX  INTEGER
	ACCESS  read-write
	STATUS  mandatory
	DESCRIPTION "CB25 Warning-Time-Delay"
		::= { bcmsplus1 286 }

bcms1-cb26-warning-time-delay
	OBJECT-TYPE
	SYNTAX  INTEGER
	ACCESS  read-write
	STATUS  mandatory
	DESCRIPTION "CB26 Warning-Time-Delay"
		::= { bcmsplus1 287 }

bcms1-cb27-warning-time-delay
	OBJECT-TYPE
	SYNTAX  INTEGER
	ACCESS  read-write
	STATUS  mandatory
	DESCRIPTION "CB27 Warning-Time-Delay"
		::= { bcmsplus1 288 }

bcms1-cb28-warning-time-delay
	OBJECT-TYPE
	SYNTAX  INTEGER
	ACCESS  read-write
	STATUS  mandatory
	DESCRIPTION "CB28 Warning-Time-Delay"
		::= { bcmsplus1 289 }

bcms1-cb29-warning-time-delay
	OBJECT-TYPE
	SYNTAX  INTEGER
	ACCESS  read-write
	STATUS  mandatory
	DESCRIPTION "CB29 Warning-Time-Delay"
		::= { bcmsplus1 290}

bcms1-cb30-warning-time-delay
	OBJECT-TYPE
	SYNTAX  INTEGER
	ACCESS  read-write
	STATUS  mandatory
	DESCRIPTION "CB30 Warning-Time-Delay"
		::= { bcmsplus1 291 }

bcms1-cb31-warning-time-delay
	OBJECT-TYPE
	SYNTAX  INTEGER
	ACCESS  read-write
	STATUS  mandatory
	DESCRIPTION "CB31 Warning-Time-Delay"
		::= { bcmsplus1 292 }

bcms1-cb32-warning-time-delay
	OBJECT-TYPE
	SYNTAX  INTEGER
	ACCESS  read-write
	STATUS  mandatory
	DESCRIPTION "CB32 Warning-Time-Delay"
		::= { bcmsplus1 293 }
  
bcms1-cb33-warning-time-delay
	OBJECT-TYPE
	SYNTAX  INTEGER
	ACCESS  read-write
	STATUS  mandatory
	DESCRIPTION "CB33 Warning-Time-Delay"
		::= { bcmsplus1 294 }

bcms1-cb34-warning-time-delay
	OBJECT-TYPE
	SYNTAX  INTEGER
	ACCESS  read-write
	STATUS  mandatory
	DESCRIPTION "CB34 Warning-Time-Delay"
		::= { bcmsplus1 295 }

bcms1-cb35-warning-time-delay
	OBJECT-TYPE
	SYNTAX  INTEGER
	ACCESS  read-write
	STATUS  mandatory
	DESCRIPTION "CB35 Warning-Time-Delay"
		::= { bcmsplus1 296 }

bcms1-cb36-warning-time-delay
	OBJECT-TYPE
	SYNTAX  INTEGER
	ACCESS  read-write
	STATUS  mandatory
	DESCRIPTION "CB36 Warning-Time-Delay"
		::= { bcmsplus1 297 }

bcms1-cb37-warning-time-delay
	OBJECT-TYPE
	SYNTAX  INTEGER
	ACCESS  read-write
	STATUS  mandatory
	DESCRIPTION "CB37 Warning-Time-Delay"
		::= { bcmsplus1 298 }

bcms1-cb38-warning-time-delay
	OBJECT-TYPE
	SYNTAX  INTEGER
	ACCESS  read-write
	STATUS  mandatory
	DESCRIPTION "CB38 Warning-Time-Delay"
		::= { bcmsplus1 299 }

bcms1-cb39-warning-time-delay
	OBJECT-TYPE
	SYNTAX  INTEGER
	ACCESS  read-write
	STATUS  mandatory
	DESCRIPTION "CB39 Warning-Time-Delay"
		::= { bcmsplus1 300 }

bcms1-cb40-warning-time-delay
	OBJECT-TYPE
	SYNTAX  INTEGER
	ACCESS  read-write
	STATUS  mandatory
	DESCRIPTION "CB40 Warning-Time-Delay"
		::= { bcmsplus1 301 }

bcms1-cb41-warning-time-delay
	OBJECT-TYPE
	SYNTAX  INTEGER
	ACCESS  read-write
	STATUS  mandatory
	DESCRIPTION "CB41 Warning-Time-Delay"
		::= { bcmsplus1 302 }

bcms1-cb42-warning-time-delay
	OBJECT-TYPE
	SYNTAX  INTEGER
	ACCESS  read-write
	STATUS  mandatory
	DESCRIPTION "CB42 Warning-Time-Delay"
		::= { bcmsplus1 303 }

bcms1-cb1-alarm-time-delay
	OBJECT-TYPE
	SYNTAX  INTEGER
	ACCESS  read-write
	STATUS  mandatory
	DESCRIPTION "CB1 Alarm-Time-Delay
		       Note for all alarm time delays 1-42: units are in seconds"                     
		::= { bcmsplus1 304 }

bcms1-cb2-alarm-time-delay
	OBJECT-TYPE
	SYNTAX  INTEGER
	ACCESS  read-write
	STATUS  mandatory
	DESCRIPTION "CB2 Alarm-Time-Delay"
		::= { bcmsplus1 305 }
  
bcms1-cb3-alarm-time-delay
	OBJECT-TYPE
	SYNTAX  INTEGER
	ACCESS  read-write
	STATUS  mandatory
	DESCRIPTION "CB3 Alarm-Time-Delay"
		::= { bcmsplus1 306 }

bcms1-cb4-alarm-time-delay
	OBJECT-TYPE
	SYNTAX  INTEGER
	ACCESS  read-write
	STATUS  mandatory
	DESCRIPTION "CB4 Alarm-Time-Delay"
		::= { bcmsplus1 307 }

bcms1-cb5-alarm-time-delay
	OBJECT-TYPE
	SYNTAX  INTEGER
	ACCESS  read-write
	STATUS  mandatory
	DESCRIPTION "CB5 Alarm-Time-Delay"
		::= { bcmsplus1 308 }

bcms1-cb6-alarm-time-delay
	OBJECT-TYPE
	SYNTAX  INTEGER
	ACCESS  read-write
	STATUS  mandatory
	DESCRIPTION "CB6 Alarm-Time-Delay"
		::= { bcmsplus1 309 }

bcms1-cb7-alarm-time-delay
	OBJECT-TYPE
	SYNTAX  INTEGER
	ACCESS  read-write
	STATUS  mandatory
	DESCRIPTION "CB7 Alarm-Time-Delay"
		::= { bcmsplus1 310 }

bcms1-cb8-alarm-time-delay
	OBJECT-TYPE
	SYNTAX  INTEGER
	ACCESS  read-write
	STATUS  mandatory
	DESCRIPTION "CB8 Alarm-Time-Delay"
		::= { bcmsplus1 311 }

bcms1-cb9-alarm-time-delay
	OBJECT-TYPE
	SYNTAX  INTEGER
	ACCESS  read-write
	STATUS  mandatory
	DESCRIPTION "CB9 Alarm-Time-Delay"
		::= { bcmsplus1 312 }

bcms1-cb10-alarm-time-delay
	OBJECT-TYPE
	SYNTAX  INTEGER
	ACCESS  read-write
	STATUS  mandatory
	DESCRIPTION "CB10 Alarm-Time-Delay"
		::= { bcmsplus1 313 }

bcms1-cb11-alarm-time-delay
	OBJECT-TYPE
	SYNTAX  INTEGER
	ACCESS  read-write
	STATUS  mandatory
	DESCRIPTION "CB11 Alarm-Time-Delay"
		::= { bcmsplus1 314 }

bcms1-cb12-alarm-time-delay
	OBJECT-TYPE
	SYNTAX  INTEGER
	ACCESS  read-write
	STATUS  mandatory
	DESCRIPTION "CB12 Alarm-Time-Delay"
		::= { bcmsplus1 315 }
  
bcms1-cb13-alarm-time-delay
	OBJECT-TYPE
	SYNTAX  INTEGER
	ACCESS  read-write
	STATUS  mandatory
	DESCRIPTION "CB13 Alarm-Time-Delay"
		::= { bcmsplus1 316 }

bcms1-cb14-alarm-time-delay
	OBJECT-TYPE
	SYNTAX  INTEGER
	ACCESS  read-write
	STATUS  mandatory
	DESCRIPTION "CB14 Alarm-Time-Delay"
		::= { bcmsplus1 317 }

bcms1-cb15-alarm-time-delay
	OBJECT-TYPE
	SYNTAX  INTEGER
	ACCESS  read-write
	STATUS  mandatory
	DESCRIPTION "CB15 Alarm-Time-Delay"
		::= { bcmsplus1 318 }

bcms1-cb16-alarm-time-delay
	OBJECT-TYPE
	SYNTAX  INTEGER
	ACCESS  read-write
	STATUS  mandatory
	DESCRIPTION "CB16 Alarm-Time-Delay"
		::= { bcmsplus1 319 }

bcms1-cb17-alarm-time-delay
	OBJECT-TYPE
	SYNTAX  INTEGER
	ACCESS  read-write
	STATUS  mandatory
	DESCRIPTION "CB17 Alarm-Time-Delay"
		::= { bcmsplus1 320 }

bcms1-cb18-alarm-time-delay
	OBJECT-TYPE
	SYNTAX  INTEGER
	ACCESS  read-write
	STATUS  mandatory
	DESCRIPTION "CB18 Alarm-Time-Delay"
		::= { bcmsplus1 321 }

bcms1-cb19-alarm-time-delay
	OBJECT-TYPE
	SYNTAX  INTEGER
	ACCESS  read-write
	STATUS  mandatory
	DESCRIPTION "CB19 Alarm-Time-Delay"
		::= { bcmsplus1 322 }

bcms1-cb20-alarm-time-delay
	OBJECT-TYPE
	SYNTAX  INTEGER
	ACCESS  read-write
	STATUS  mandatory
	DESCRIPTION "CB20 Alarm-Time-Delay"
		::= { bcmsplus1 323 }

bcms1-cb21-alarm-time-delay
	OBJECT-TYPE
	SYNTAX  INTEGER
	ACCESS  read-write
	STATUS  mandatory
	DESCRIPTION "CB21 Alarm-Time-Delay"
		::= { bcmsplus1 324 }

bcms1-cb22-alarm-time-delay
	OBJECT-TYPE
	SYNTAX  INTEGER
	ACCESS  read-write
	STATUS  mandatory
	DESCRIPTION "CB22 Alarm-Time-Delay"
		::= { bcmsplus1 325 }
  
bcms1-cb23-alarm-time-delay
	OBJECT-TYPE
	SYNTAX  INTEGER
	ACCESS  read-write
	STATUS  mandatory
	DESCRIPTION "CB23 Alarm-Time-Delay"
		::= { bcmsplus1 326 }

bcms1-cb24-alarm-time-delay
	OBJECT-TYPE
	SYNTAX  INTEGER
	ACCESS  read-write
	STATUS  mandatory
	DESCRIPTION "CB24 Alarm-Time-Delay"
		::= { bcmsplus1 327 }

bcms1-cb25-alarm-time-delay
	OBJECT-TYPE
	SYNTAX  INTEGER
	ACCESS  read-write
	STATUS  mandatory
	DESCRIPTION "CB25 Alarm-Time-Delay"
		::= { bcmsplus1 328 }

bcms1-cb26-alarm-time-delay
	OBJECT-TYPE
	SYNTAX  INTEGER
	ACCESS  read-write
	STATUS  mandatory
	DESCRIPTION "CB26 Alarm-Time-Delay"
		::= { bcmsplus1 329 }

bcms1-cb27-alarm-time-delay
	OBJECT-TYPE
	SYNTAX  INTEGER
	ACCESS  read-write
	STATUS  mandatory
	DESCRIPTION "CB27 Alarm-Time-Delay"
		::= { bcmsplus1 330 }

bcms1-cb28-alarm-time-delay
	OBJECT-TYPE
	SYNTAX  INTEGER
	ACCESS  read-write
	STATUS  mandatory
	DESCRIPTION "CB28 Alarm-Time-Delay"
		::= { bcmsplus1 331 }

bcms1-cb29-alarm-time-delay
	OBJECT-TYPE
	SYNTAX  INTEGER
	ACCESS  read-write
	STATUS  mandatory
	DESCRIPTION "CB29 Alarm-Time-Delay"
		::= { bcmsplus1 332 }

bcms1-cb30-alarm-time-delay
	OBJECT-TYPE
	SYNTAX  INTEGER
	ACCESS  read-write
	STATUS  mandatory
	DESCRIPTION "CB30 Alarm-Time-Delay"
		::= { bcmsplus1 333 }

bcms1-cb31-alarm-time-delay
	OBJECT-TYPE
	SYNTAX  INTEGER
	ACCESS  read-write
	STATUS  mandatory
	DESCRIPTION "CB31 Alarm-Time-Delay"
		::= { bcmsplus1 334 }

bcms1-cb32-alarm-time-delay
	OBJECT-TYPE
	SYNTAX  INTEGER
	ACCESS  read-write
	STATUS  mandatory
	DESCRIPTION "CB32 Alarm-Time-Delay"
		::= { bcmsplus1 335 }
  
bcms1-cb33-alarm-time-delay
	OBJECT-TYPE
	SYNTAX  INTEGER
	ACCESS  read-write
	STATUS  mandatory
	DESCRIPTION "CB33 Alarm-Time-Delay"
		::= { bcmsplus1 336 }

bcms1-cb34-alarm-time-delay
	OBJECT-TYPE
	SYNTAX  INTEGER
	ACCESS  read-write
	STATUS  mandatory
	DESCRIPTION "CB34 Alarm-Time-Delay"
		::= { bcmsplus1 337 }

bcms1-cb35-alarm-time-delay
	OBJECT-TYPE
	SYNTAX  INTEGER
	ACCESS  read-write
	STATUS  mandatory
	DESCRIPTION "CB35 Alarm-Time-Delay"
		::= { bcmsplus1 338 }

bcms1-cb36-alarm-time-delay
	OBJECT-TYPE
	SYNTAX  INTEGER
	ACCESS  read-write
	STATUS  mandatory
	DESCRIPTION "CB36 Alarm-Time-Delay"
		::= { bcmsplus1 339 }

bcms1-cb37-alarm-time-delay
	OBJECT-TYPE
	SYNTAX  INTEGER
	ACCESS  read-write
	STATUS  mandatory
	DESCRIPTION "CB37 Alarm-Time-Delay"
		::= { bcmsplus1 340 }

bcms1-cb38-alarm-time-delay
	OBJECT-TYPE
	SYNTAX  INTEGER
	ACCESS  read-write
	STATUS  mandatory
	DESCRIPTION "CB38 Alarm-Time-Delay"
		::= { bcmsplus1 341 }

bcms1-cb39-alarm-time-delay
	OBJECT-TYPE
	SYNTAX  INTEGER
	ACCESS  read-write
	STATUS  mandatory
	DESCRIPTION "CB39 Alarm-Time-Delay"
		::= { bcmsplus1 342 }

bcms1-cb40-alarm-time-delay
	OBJECT-TYPE
	SYNTAX  INTEGER
	ACCESS  read-write
	STATUS  mandatory
	DESCRIPTION "CB40 Alarm-Time-Delay"
		::= { bcmsplus1 343 }

bcms1-cb41-alarm-time-delay
	OBJECT-TYPE
	SYNTAX  INTEGER
	ACCESS  read-write
	STATUS  mandatory
	DESCRIPTION "CB41 Alarm-Time-Delay"
		::= { bcmsplus1 344 }

bcms1-cb42-alarm-time-delay
	OBJECT-TYPE
	SYNTAX  INTEGER
	ACCESS  read-write
	STATUS  mandatory
	DESCRIPTION "CB42 Alarm-Time-Delay"
		::= { bcmsplus1 345 }

bcms1-global-breaker-size
	OBJECT-TYPE
	SYNTAX  INTEGER
	ACCESS  read-write
	STATUS  mandatory
	DESCRIPTION "Global-breaker-size
		     Note for global breaker size: 10 = 10 amps
                     Range is 10 to 100 amps"
		::= { bcmsplus1 346 }

bcms1-global-warning-threshold
	OBJECT-TYPE
	SYNTAX  INTEGER
	ACCESS  read-write
	STATUS  mandatory
	DESCRIPTION "Global-warning-threshold
		     Note for global warning threshold: 70 = 70% of breaker size
                     range is 0-100%"
		::= { bcmsplus1 347 }

bcms1-global-alarm-threshold
	OBJECT-TYPE
	SYNTAX  INTEGER
	ACCESS  read-write
	STATUS  mandatory
	DESCRIPTION "Global-alarm-threshold
		     Note for global alarm threshold: 80 = 80% of breaker size
                     range is 0-100%"
		::= { bcmsplus1 348 }

bcms1-global-warning-time-delay
	OBJECT-TYPE
	SYNTAX  INTEGER
	ACCESS  read-write
	STATUS  mandatory
	DESCRIPTION "Global-warning-time-delay
		     Note for global warning time delay: units are in seconds"                     
		::= { bcmsplus1 349 }

bcms1-global-alarm-time-delay
	OBJECT-TYPE
	SYNTAX  INTEGER
	ACCESS  read-write
	STATUS  mandatory
	DESCRIPTION "Global-alarm-time-delay
		     Note for global alarm time delay: units are in seconds"                     
		::= { bcmsplus1 350 }

bcms1-min-max-reset
	OBJECT-TYPE
	SYNTAX  INTEGER
	ACCESS  read-write
	STATUS  mandatory
	DESCRIPTION "Min-max-Reset
                     Note for Min-max Reset: writing to this register will clear minimum
		     and maximum current values"
		::= { bcmsplus1 351 }

bcms1-global-warning-alarm-register
	OBJECT-TYPE
	SYNTAX  INTEGER
	ACCESS  read-only
	STATUS  mandatory
	DESCRIPTION "Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { bcmsplus1 352 }

bcms1-meter-alarm-status-latching
	OBJECT-TYPE
	SYNTAX  INTEGER
	ACCESS  read-write
	STATUS  mandatory
	DESCRIPTION "Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus1 353 }

bcms1-meter-alarm-status-nonlatching
	OBJECT-TYPE
	SYNTAX  INTEGER
	ACCESS  read-only
	STATUS  mandatory
	DESCRIPTION "Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus1 354 }

bcms1-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 – 15: Not Used"
		::= { bcmsplus1 355 }

bcms1-current-option-setting
	OBJECT-TYPE
	SYNTAX  INTEGER
	ACCESS  read-only
	STATUS  mandatory
	DESCRIPTION "Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { bcmsplus1 356 }

bcms1-current-phase-a-panelboard
	OBJECT-TYPE
	SYNTAX  INTEGER
	ACCESS  read-only
	STATUS  mandatory
	DESCRIPTION "Current-Phase-A-Panelboard
                     Note for all currents: 100 = 10.0 amps"
		::= { bcmsplus1 357 }

bcms1-current-phase-b-panelboard
	OBJECT-TYPE
	SYNTAX  INTEGER
	ACCESS  read-only
	STATUS  mandatory
	DESCRIPTION "Current-Phase-B-Panelboard"
		::= { bcmsplus1 358 }

bcms1-current-phase-c-panelboard
	OBJECT-TYPE
	SYNTAX  INTEGER
	ACCESS  read-only
	STATUS  mandatory
	DESCRIPTION "Current-Phase-C-Panelboard"
		::= { bcmsplus1 359 }

bcms1-current-neutral-panelboard
	OBJECT-TYPE
	SYNTAX  INTEGER
	ACCESS  read-only
	STATUS  mandatory
	DESCRIPTION "Current-Neutral-Panelboard"
		::= { bcmsplus1 360 }


bcms1-over-current-alarm-threshhold-pnlbd
	OBJECT-TYPE
	SYNTAX  INTEGER
	ACCESS  read-write
	STATUS  mandatory
	DESCRIPTION "Over-Current-Alarm-Threshhold-Pnlbd"
		::= { bcmsplus1 361 }

bcms1-under-current-alarm-threshhold-pnlbd
	OBJECT-TYPE
	SYNTAX  INTEGER
	ACCESS  read-write
	STATUS  mandatory
	DESCRIPTION "Under-Current-Alarm-Threshhold-Pnlbd"
		::= { bcmsplus1 362 }

bcms1-over-current-set-counter-pnlbd
	OBJECT-TYPE
	SYNTAX  INTEGER
	ACCESS  read-only
	STATUS  mandatory
	DESCRIPTION "Over-Current-Set-Counter-Pnlbd
		     Note for all counters:
                     The set counter is incremented when the value goes outside the threshold limit
                     The reset counter is incremented when the value is returns to  the threshold limit"
		::= { bcmsplus1 363 }

bcms1-over-current-reset-counter-pnlbd
	OBJECT-TYPE
	SYNTAX  INTEGER
	ACCESS  read-only
	STATUS  mandatory
	DESCRIPTION "Over-Current-Reset-Counter-Pnlbd"
		::= { bcmsplus1 364 }

bcms1-under-current-set-counter-pnlbd
	OBJECT-TYPE
	SYNTAX  INTEGER
	ACCESS  read-only
	STATUS  mandatory
	DESCRIPTION "Under-Current-Set-Counter-Pnlbd"
		::= { bcmsplus1 365 }

bcms1-under-current-reset-counter-pnlbd
	OBJECT-TYPE
	SYNTAX  INTEGER
	ACCESS  read-only
	STATUS  mandatory
	DESCRIPTION "Under-Current-Reset-Counter-Pnlbd"
		::= { bcmsplus1 366 }

bcms1-current-phase-a-both-pnlbd
	OBJECT-TYPE
	SYNTAX  INTEGER
	ACCESS  read-only
	STATUS  mandatory
	DESCRIPTION "Current-Phase-A-Both-Pnlbd"
		::= { bcmsplus1 367 }

bcms1-current-phase-b-both-pnlbd
	OBJECT-TYPE
	SYNTAX  INTEGER
	ACCESS  read-only
	STATUS  mandatory
	DESCRIPTION "Current-Phase-B-Both-Pnlbd"
		::= { bcmsplus1 368 }

bcms1-current-phase-c-both-pnlbd
	OBJECT-TYPE
	SYNTAX  INTEGER
	ACCESS  read-only
	STATUS  mandatory
	DESCRIPTION "Current-Phase-C-Both-Pnlbd"
		::= { bcmsplus1 369 }

bcms1-current-neutral-both-pnlbd
	OBJECT-TYPE
	SYNTAX  INTEGER
	ACCESS  read-only
	STATUS  mandatory
	DESCRIPTION "Current-Neutral-Both-Pnlbd"
		::= { bcmsplus1 370 }


bcms1-over-current-alarm-threshhold-both-pnlbd
	OBJECT-TYPE
	SYNTAX  INTEGER
	ACCESS  read-write
	STATUS  mandatory
	DESCRIPTION "Over-Current-Alarm-Threshhold-Both-Pnlbd"
		::= { bcmsplus1 371 }

bcms1-under-current-alarm-threshhold-both-pnlbd
	OBJECT-TYPE
	SYNTAX  INTEGER
	ACCESS  read-write
	STATUS  mandatory
	DESCRIPTION "Under-Current-Alarm-Threshhold-Both-Pnlbd"
		::= { bcmsplus1 372 }

bcms1-over-current-set-counter-both-pnlbd
	OBJECT-TYPE
	SYNTAX  INTEGER
	ACCESS  read-only
	STATUS  mandatory
	DESCRIPTION "Over-Current-Set-Counter-Both-Pnlbd"
		::= { bcmsplus1 373 }

bcms1-over-current-reset-counter-both-pnlbd
	OBJECT-TYPE
	SYNTAX  INTEGER
	ACCESS  read-only
	STATUS  mandatory
	DESCRIPTION "Over-Current-Reset-Counter-Both-Pnlbd"
		::= { bcmsplus1 374 }

bcms1-under-current-set-counter-both-pnlbd
	OBJECT-TYPE
	SYNTAX  INTEGER
	ACCESS  read-only
	STATUS  mandatory
	DESCRIPTION "Under-Current-Set-Counter-Both-Pnlbd"
		::= { bcmsplus1 375 }

bcms1-under-current-reset-counter-both-pnlbd
	OBJECT-TYPE
	SYNTAX  INTEGER
	ACCESS  read-only
	STATUS  mandatory
	DESCRIPTION "Under-Current-Reset-Counter-Both-Pnlbd"
		::= { bcmsplus1 376 }

bcms1-voltage-option-setting
	OBJECT-TYPE
	SYNTAX  INTEGER
	ACCESS  read-only
	STATUS  mandatory
	DESCRIPTION "Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { bcmsplus1 377 }

bcms1-voltage-a-b-main
	OBJECT-TYPE
	SYNTAX  INTEGER
	ACCESS  read-only
	STATUS  mandatory
	DESCRIPTION "Voltage-A-B-Main
                     Note for all voltages: 1200 = 120.0 volts"
		::= { bcmsplus1 378 }

bcms1-voltage-b-c-main
	OBJECT-TYPE
	SYNTAX  INTEGER
	ACCESS  read-only
	STATUS  mandatory
	DESCRIPTION "Voltage-B-C-Main"
		::= { bcmsplus1 379 }

bcms1-voltage-c-a-main
	OBJECT-TYPE
	SYNTAX  INTEGER
	ACCESS  read-only
	STATUS  mandatory
	DESCRIPTION "Voltage-C-A-Main"
		::= { bcmsplus1 380 }

bcms1-voltage-a-n-main
	OBJECT-TYPE
	SYNTAX  INTEGER
	ACCESS  read-only
	STATUS  mandatory
	DESCRIPTION "Voltage-A-N-Main"
		::= { bcmsplus1 381 }

bcms1-voltage-b-n-main
	OBJECT-TYPE
	SYNTAX  INTEGER
	ACCESS  read-only
	STATUS  mandatory
	DESCRIPTION "Voltage-B-N-Main"
		::= { bcmsplus1 382 }

bcms1-voltage-c-n-main
	OBJECT-TYPE
	SYNTAX  INTEGER
	ACCESS  read-only
	STATUS  mandatory
	DESCRIPTION "Voltage-C-N-Main"
		::= { bcmsplus1 383 }

bcms1-over-voltage-alarm-threshhold-main
	OBJECT-TYPE
	SYNTAX  INTEGER
	ACCESS  read-write
	STATUS  mandatory
	DESCRIPTION "Over-Voltage-Alarm-Threshhold-Main
                     Note All Over and Under Voltage is for L-L values"
		::= { bcmsplus1 384 }

bcms1-under-voltage-alarm-threshhold-main
	OBJECT-TYPE
	SYNTAX  INTEGER
	ACCESS  read-write
	STATUS  mandatory
	DESCRIPTION "Under-Voltage-Alarm-Threshhold-Main"
		::= { bcmsplus1 385 }

bcms1-over-voltage-set-counter-main
	OBJECT-TYPE
	SYNTAX  INTEGER
	ACCESS  read-only
	STATUS  mandatory
	DESCRIPTION "Over-Voltage-Set-Counter-Main"
		::= { bcmsplus1 386 }

bcms1-over-voltage-reset-counter-main
	OBJECT-TYPE
	SYNTAX  INTEGER
	ACCESS  read-only
	STATUS  mandatory
	DESCRIPTION "Over-Voltage-Reset-Counter-Main"
		::= { bcmsplus1 387 }

bcms1-under-voltage-set-counter-main
	OBJECT-TYPE
	SYNTAX  INTEGER
	ACCESS  read-only
	STATUS  mandatory
	DESCRIPTION "Under-Voltage-Set-Counter-Main"
		::= { bcmsplus1 388 }

bcms1-under-voltage-reset-counter-main
	OBJECT-TYPE
	SYNTAX  INTEGER
	ACCESS  read-only
	STATUS  mandatory
	DESCRIPTION "Under-Voltage-Reset-Counter-Main"
		::= { bcmsplus1 389 }


bcms1-voltage-frequency-main
	OBJECT-TYPE
	SYNTAX  INTEGER
	ACCESS  read-only
	STATUS  mandatory
	DESCRIPTION "Voltage-Frequency-Main
                     note for frequency: 600 = 60.0Hz
                     Range is 40-70Hz
                     Note if insufficient voltage is present frequency will read 0xFFFF"
		::= { bcmsplus1 390 }

bcms1-voltage-a-b-alternate
	OBJECT-TYPE
	SYNTAX  INTEGER
	ACCESS  read-only
	STATUS  mandatory
	DESCRIPTION "Voltage-A-B-Alternate"
		::= { bcmsplus1 391 }

bcms1-voltage-b-c-alternate
	OBJECT-TYPE
	SYNTAX  INTEGER
	ACCESS  read-only
	STATUS  mandatory
	DESCRIPTION "Voltage-B-C-Alternate"
		::= { bcmsplus1 392 }

bcms1-voltage-c-a-alternate
	OBJECT-TYPE
	SYNTAX  INTEGER
	ACCESS  read-only
	STATUS  mandatory
	DESCRIPTION "Voltage-C-A-Alternate"
		::= { bcmsplus1 393 }

bcms1-voltage-a-n-alternate
	OBJECT-TYPE
	SYNTAX  INTEGER
	ACCESS  read-only
	STATUS  mandatory
	DESCRIPTION "Voltage-A-N-Alternate"
		::= { bcmsplus1 394 }

bcms1-voltage-b-N-alternate
	OBJECT-TYPE
	SYNTAX  INTEGER
	ACCESS  read-only
	STATUS  mandatory
	DESCRIPTION "Voltage-B-N-Alternate"
		::= { bcmsplus1 395 }

bcms1-voltage-c-n-alternate
	OBJECT-TYPE
	SYNTAX  INTEGER
	ACCESS  read-only
	STATUS  mandatory
	DESCRIPTION "Voltage-C-N-Alternate"
		::= { bcmsplus1 396 }

bcms1-over-voltage-alarm-threshhold-alternate
	OBJECT-TYPE
	SYNTAX  INTEGER
	ACCESS  read-write
	STATUS  mandatory
	DESCRIPTION "Over-Voltage-Alarm-Threshhold-Alternate"
		::= { bcmsplus1 397 }

bcms1-under-voltage-alarm-threshhold-alternate
	OBJECT-TYPE
	SYNTAX  INTEGER
	ACCESS  read-write
	STATUS  mandatory
	DESCRIPTION "Under-Voltage-Alarm-Threshhold-Alternate"
		::= { bcmsplus1 398 }

bcms1-over-voltage-set-counter-alternate
	OBJECT-TYPE
	SYNTAX  INTEGER
	ACCESS  read-only
	STATUS  mandatory
	DESCRIPTION "Over-Voltage-Set-Counter-Alternate"
		::= { bcmsplus1 399 }

bcms1-over-voltage-reset-counter-alternate
	OBJECT-TYPE
	SYNTAX  INTEGER
	ACCESS  read-only
	STATUS  mandatory
	DESCRIPTION "Over-Voltage-Reset-Counter-Alternate"
		::= { bcmsplus1 400 }

bcms1-under-voltage-set-counter-alternate
	OBJECT-TYPE
	SYNTAX  INTEGER
	ACCESS  read-only
	STATUS  mandatory
	DESCRIPTION "Under-Voltage-Set-Counter-Alternate"
		::= { bcmsplus1 401 }

bcms1-under-voltage-reset-counter-alternate
	OBJECT-TYPE
	SYNTAX  INTEGER
	ACCESS  read-only
	STATUS  mandatory
	DESCRIPTION "Under-Voltage-Reset-Counter-Alternate"
		::= { bcmsplus1 402 }

bcms1-real-power-kw
	OBJECT-TYPE
	SYNTAX  INTEGER
	ACCESS  read-only
	STATUS  mandatory
	DESCRIPTION "Real-Power-KW
                     Note for all KWs: 100 = 10.0 KW"
		::= { bcmsplus1 403 }

bcms1-peal-power-phase-a
	OBJECT-TYPE
	SYNTAX  INTEGER
	ACCESS  read-only
	STATUS  mandatory
	DESCRIPTION "Real-Power-Phase-A"
		::= { bcmsplus1 404 }

bcms1-real-power-phase-b
	OBJECT-TYPE
	SYNTAX  INTEGER
	ACCESS  read-only
	STATUS  mandatory
	DESCRIPTION "Real-Power-Phase-B"
		::= { bcmsplus1 405 }

bcms1-real-power-phase-c
	OBJECT-TYPE
	SYNTAX  INTEGER
	ACCESS  read-only
	STATUS  mandatory
	DESCRIPTION "Real-Power-Phase-C"
		::= { bcmsplus1 406 }

bcms1-reactive-power-kvar
	OBJECT-TYPE
	SYNTAX  INTEGER
	ACCESS  read-only
	STATUS  mandatory
	DESCRIPTION "Reactive-Power-KVAR
                     Note for KVAR: 100 = 10.0 KVAR"
		::= { bcmsplus1 407 }

bcms1-apparent-Power-kva
	OBJECT-TYPE
	SYNTAX  INTEGER
	ACCESS  read-only
	STATUS  mandatory
	DESCRIPTION "Apparent-Power-KVA
                     Note for KVA: 100 = 10.0 KVA"
		::= { bcmsplus1 408 }

bcms1-total-power-factor
	OBJECT-TYPE
	SYNTAX  INTEGER
	ACCESS  read-only
	STATUS  mandatory
	DESCRIPTION "Total-Power-Factor
                     Note for all Power Factor: 1000 = 100.0 PF"
		::= { bcmsplus1 409 }

bcms1-power-factor-phase-a
	OBJECT-TYPE
	SYNTAX  INTEGER
	ACCESS  read-only
	STATUS  mandatory
	DESCRIPTION "Power-Factor-Phase-A"
		::= { bcmsplus1 410 }

bcms1-Power-factor-phase-b
	OBJECT-TYPE
	SYNTAX  INTEGER
	ACCESS  read-only
	STATUS  mandatory
	DESCRIPTION "Power-Factor-Phase-B"
		::= { bcmsplus1 411 }

bcms1-Power-factor-phase-c
	OBJECT-TYPE
	SYNTAX  INTEGER
	ACCESS  read-only
	STATUS  mandatory
	DESCRIPTION "Power-Factor-Phase-C"
		::= { bcmsplus1 412 }

bcms1-energy-consumption-kwh-lower-word-integer
	OBJECT-TYPE
	SYNTAX  INTEGER
	ACCESS  read-write
	STATUS  mandatory
	DESCRIPTION "Energy-Consumption-KWh-Lower-Word-Integer
		     Note for KWh: 100 = 100KWh
                     Combine lower and upper integers into a word for total KWh"
		::= { bcmsplus1 413 }

bcms1-energy-consumption-kwh-upper-word-integer
	OBJECT-TYPE
	SYNTAX  INTEGER
	ACCESS  read-write
	STATUS  mandatory
	DESCRIPTION "Energy-Consumption-KWh-Upper-Word-Integer"
		::= { bcmsplus1 414 }

bcms1-main-voltage-thd-phase-a
	OBJECT-TYPE
	SYNTAX  INTEGER
	ACCESS  read-only
	STATUS  mandatory
	DESCRIPTION "Main-Voltage-THD-Phase-A"
		::= { bcmsplus1 415 }

bcms1-main-voltage-thd-phase-b
	OBJECT-TYPE
	SYNTAX  INTEGER
	ACCESS  read-only
	STATUS  mandatory
	DESCRIPTION "Main-Voltage-THD-Phase-B"
		::= { bcmsplus1 416 }

bcms1-main-voltage-thd-phase-c
	OBJECT-TYPE
	SYNTAX  INTEGER
	ACCESS  read-only
	STATUS  mandatory
	DESCRIPTION "Main-Voltage-THD-Phase-C"
		::= { bcmsplus1 417 }

bcms1-alt-voltage-thd-phase-a
	OBJECT-TYPE
	SYNTAX  INTEGER
	ACCESS  read-only
	STATUS  mandatory
	DESCRIPTION "Alt-Voltage-THD-Phase-A"
		::= { bcmsplus1 418 }

bcms1-alt-voltage-thd-phase-b
	OBJECT-TYPE
	SYNTAX  INTEGER
	ACCESS  read-only
	STATUS  mandatory
	DESCRIPTION "Alt-Voltage-THD-Phase-B"
		::= { bcmsplus1 419 }

bcms1-alt-voltage-thd-phase-c
	OBJECT-TYPE
	SYNTAX  INTEGER
	ACCESS  read-only
	STATUS  mandatory
	DESCRIPTION "Alt-Voltage-THD-Phase-C"
		::= { bcmsplus1 420 }

bcms1-current-ground-panelboard
	OBJECT-TYPE
	SYNTAX  INTEGER
	ACCESS  read-only
	STATUS  mandatory
	DESCRIPTION "Current-Ground-Panelboard"
		::= { bcmsplus1 421 }

bcms1-percent-load-phase-a
	OBJECT-TYPE
	SYNTAX  INTEGER
	ACCESS  read-only
	STATUS  mandatory
	DESCRIPTION "Percent Load Phase A"
		::= { bcmsplus1 422 }

bcms1-percent-load-phase-b
	OBJECT-TYPE
	SYNTAX  INTEGER
	ACCESS  read-only
	STATUS  mandatory
	DESCRIPTION "Percent Load Phase B"
		::= { bcmsplus1 423 }

bcms1-percent-load-phase-c
	OBJECT-TYPE
	SYNTAX  INTEGER
	ACCESS  read-only
	STATUS  mandatory
	DESCRIPTION "Percent Load Phase C"
		::= { bcmsplus1 424 }

bcms1-full-load-current
	OBJECT-TYPE
	SYNTAX  INTEGER
	ACCESS  read-write
	STATUS  mandatory
	DESCRIPTION "Full Load Current"
		::= { bcmsplus1 425 }

--------------------------------------------------------------------------------
-- Trap register values
--------------------------------------------------------------------------------

display-summary-trap
        TRAP-TYPE
	  ENTERPRISE	displaytraps
	  VARIABLES		{ display-alarm }
	  DESCRIPTION	"Dispaly Summary Alarm Trap"
	  ::= 1


END
