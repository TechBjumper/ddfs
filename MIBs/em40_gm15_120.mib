GEISTMFG-EM40GM15-120-MIB DEFINITIONS ::= BEGIN

IMPORTS
	MODULE-IDENTITY, OBJECT-TYPE, enterprises, Unsigned32 FROM SNMPv2-SMI;

geistmfg MODULE-IDENTITY
	LAST-UPDATED "200709170000Z"
	ORGANIZATION "Geist Manufacturing"
	CONTACT-INFO "support@geistmfg.com/800.432.3219"
	DESCRIPTION "The MIB for EM40/GM15-120"
	::= { enterprises 21239 }
	

em40gm15_120 OBJECT IDENTIFIER
	::=  { geistmfg 15 }


productInfo OBJECT IDENTIFIER
	::= { em40gm15_120 1 }

totalDeciAmps OBJECT IDENTIFIER
	::= { em40gm15_120 2 }

circuit4 OBJECT IDENTIFIER
	::= { em40gm15_120 3 }

circuit3 OBJECT IDENTIFIER
	::= { em40gm15_120 4 }

circuit2 OBJECT IDENTIFIER
	::= { em40gm15_120 5 }

circuit1 OBJECT IDENTIFIER
	::= { em40gm15_120 6 }




productTitle    OBJECT-TYPE
   SYNTAX DisplayString
   ACCESS read-only
   STATUS mandatory
   DESCRIPTION
      "Name of product"
   ::= { productInfo 1 }
   
productVersion    OBJECT-TYPE
   SYNTAX DisplayString
   ACCESS read-only
   STATUS mandatory
   DESCRIPTION
      "Firmware version"
   ::= { productInfo 2 }

productName    OBJECT-TYPE
   SYNTAX DisplayString
   ACCESS read-only
   STATUS mandatory
   DESCRIPTION
      "Unit friendly name"
   ::= { productInfo 3 }

productMAC    OBJECT-TYPE
   SYNTAX DisplayString
   ACCESS read-only
   STATUS mandatory
   DESCRIPTION
      "Unit MAC address"
   ::= { productInfo 4 }

productIP    OBJECT-TYPE
   SYNTAX DisplayString
   ACCESS read-only
   STATUS mandatory
   DESCRIPTION
      "IP address of the unit"
   ::= { productInfo 5 }




totalDeciAmpsPhaseA   OBJECT-TYPE
   SYNTAX INTEGER(0..300)
   UNITS "0.1 Amps"
   ACCESS read-only
   STATUS mandatory
   DESCRIPTION
   "Total Amps consumed by PhaseA, in units of 0.1 amps"
   ::= { totalDeciAmps 1 }

totalDeciAmpsPhaseB   OBJECT-TYPE
   SYNTAX INTEGER(0..300)
   UNITS "0.1 Amps"
   ACCESS read-only
   STATUS mandatory
   DESCRIPTION
   "Total Amps consumed by PhaseB, in units of 0.1 amps"
   ::= { totalDeciAmps 2 }

totalDeciAmpsPhaseC   OBJECT-TYPE
   SYNTAX INTEGER(0..300)
   UNITS "0.1 Amps"
   ACCESS read-only
   STATUS mandatory
   DESCRIPTION
   "Total Amps consumed by PhaseC, in units of 0.1 amps"
   ::= { totalDeciAmps 3 }





outlet1AName OBJECT-TYPE
   SYNTAX DisplayString
   ACCESS read-only
   STATUS mandatory
   DESCRIPTION
   "Friendly name for outlet 1"
   ::= { circuit4 1 }

outlet1ADeciAmps OBJECT-TYPE
   SYNTAX INTEGER(0..255)
   UNITS "0.1 Amps"
   ACCESS read-only
   STATUS mandatory
   DESCRIPTION
   "Amps used by outlet 1, in units of 0.1 amps"
   ::= { circuit4 2 }

outlet2BName OBJECT-TYPE
   SYNTAX DisplayString
   ACCESS read-only
   STATUS mandatory
   DESCRIPTION
   "Friendly name for outlet 2"
   ::= { circuit4 3 }

outlet2BDeciAmps OBJECT-TYPE
   SYNTAX INTEGER(0..255)
   UNITS "0.1 Amps"
   ACCESS read-only
   STATUS mandatory
   DESCRIPTION
   "Amps used by outlet 2, in units of 0.1 amps"
   ::= { circuit4 4 }

outlet3CName OBJECT-TYPE
   SYNTAX DisplayString
   ACCESS read-only
   STATUS mandatory
   DESCRIPTION
   "Friendly name for outlet 3"
   ::= { circuit4 5 }

outlet3CDeciAmps OBJECT-TYPE
   SYNTAX INTEGER(0..255)
   UNITS "0.1 Amps"
   ACCESS read-only
   STATUS mandatory
   DESCRIPTION
   "Amps used by outlet 3, in units of 0.1 amps"
   ::= { circuit4 6 }



outlet4AName OBJECT-TYPE
   SYNTAX DisplayString
   ACCESS read-only
   STATUS mandatory
   DESCRIPTION
   "Friendly name for outlet 4"
   ::= { circuit3 1 }

outlet4ADeciAmps OBJECT-TYPE
   SYNTAX INTEGER(0..255)
   UNITS "0.1 Amps"
   ACCESS read-only
   STATUS mandatory
   DESCRIPTION
   "Amps used by outlet 4, in units of 0.1 amps"
   ::= { circuit3 2 }

outlet5BName OBJECT-TYPE
   SYNTAX DisplayString
   ACCESS read-only
   STATUS mandatory
   DESCRIPTION
   "Friendly name for outlet 5"
   ::= { circuit3 3 }

outlet5BDeciAmps OBJECT-TYPE
   SYNTAX INTEGER(0..255)
   UNITS "0.1 Amps"
   ACCESS read-only
   STATUS mandatory
   DESCRIPTION
   "Amps used by outlet 5, in units of 0.1 amps"
   ::= { circuit3 4 }

outlet6CName OBJECT-TYPE
   SYNTAX DisplayString
   ACCESS read-only
   STATUS mandatory
   DESCRIPTION
   "Friendly name for outlet 6"
   ::= { circuit3 5 }

outlet6CDeciAmps OBJECT-TYPE
   SYNTAX INTEGER(0..255)
   UNITS "0.1 Amps"
   ACCESS read-only
   STATUS mandatory
   DESCRIPTION
   "Amps used by outlet 6, in units of 0.1 amps"
   ::= { circuit3 6 }



outlet7AName OBJECT-TYPE
   SYNTAX DisplayString
   ACCESS read-only
   STATUS mandatory
   DESCRIPTION
   "Friendly name for outlet 7"
   ::= { circuit2 1 }

outlet7ADeciAmps OBJECT-TYPE
   SYNTAX INTEGER(0..255)
   UNITS "0.1 Amps"
   ACCESS read-only
   STATUS mandatory
   DESCRIPTION
   "Amps used by outlet 7, in units of 0.1 amps"
   ::= { circuit2 2 }

outlet8BName OBJECT-TYPE
   SYNTAX DisplayString
   ACCESS read-only
   STATUS mandatory
   DESCRIPTION
   "Friendly name for outlet 8"
   ::= { circuit2 3 }

outlet8BDeciAmps OBJECT-TYPE
   SYNTAX INTEGER(0..255)
   UNITS "0.1 Amps"
   ACCESS read-only
   STATUS mandatory
   DESCRIPTION
   "Amps used by outlet 8, in units of 0.1 amps"
   ::= { circuit2 4 }

outlet9CName OBJECT-TYPE
   SYNTAX DisplayString
   ACCESS read-only
   STATUS mandatory
   DESCRIPTION
   "Friendly name for outlet 9"
   ::= { circuit2 5 }

outlet9CDeciAmps OBJECT-TYPE
   SYNTAX INTEGER(0..255)
   UNITS "0.1 Amps"
   ACCESS read-only
   STATUS mandatory
   DESCRIPTION
   "Amps used by outlet 9, in units of 0.1 amps"
   ::= { circuit2 6 }



outlet10AName OBJECT-TYPE
   SYNTAX DisplayString
   ACCESS read-only
   STATUS mandatory
   DESCRIPTION
   "Friendly name for outlet 10"
   ::= { circuit1 1 }

outlet10ADeciAmps OBJECT-TYPE
   SYNTAX INTEGER(0..255)
   UNITS "0.1 Amps"
   ACCESS read-only
   STATUS mandatory
   DESCRIPTION
   "Amps used by outlet 10, in units of 0.1 amps"
   ::= { circuit1 2 }

outlet11BName OBJECT-TYPE
   SYNTAX DisplayString
   ACCESS read-only
   STATUS mandatory
   DESCRIPTION
   "Friendly name for outlet 11"
   ::= { circuit1 3 }

outlet11BDeciAmps OBJECT-TYPE
   SYNTAX INTEGER(0..255)
   UNITS "0.1 Amps"
   ACCESS read-only
   STATUS mandatory
   DESCRIPTION
   "Amps used by outlet 11, in units of 0.1 amps"
   ::= { circuit1 4 }

outlet12CName OBJECT-TYPE
   SYNTAX DisplayString
   ACCESS read-only
   STATUS mandatory
   DESCRIPTION
   "Friendly name for outlet 12"
   ::= { circuit1 5 }

outlet12CDeciAmps OBJECT-TYPE
   SYNTAX INTEGER(0..255)
   UNITS "0.1 Amps"
   ACCESS read-only
   STATUS mandatory
   DESCRIPTION
   "Amps used by outlet 12, in units of 0.1 amps"
   ::= { circuit1 6 }





totalDeciAmpsPhaseATRAP TRAP-TYPE
ENTERPRISE geistmfg
VARIABLES { totalDeciAmpsPhaseA }
DESCRIPTION "Amps PhaseA Trap"
::= 1

totalDeciAmpsPhaseBTRAP TRAP-TYPE
ENTERPRISE geistmfg
VARIABLES { totalDeciAmpsPhaseB }
DESCRIPTION "Amps PhaseB Trap"
::= 2

totalDeciAmpsPhaseCTRAP TRAP-TYPE
ENTERPRISE geistmfg
VARIABLES { totalDeciAmpsPhaseC }
DESCRIPTION "Amps PhaseC Trap"
::= 3





outlet1ADeciAmpsTRAP TRAP-TYPE
ENTERPRISE geistmfg
VARIABLES { outlet1ADeciAmps }
DESCRIPTION "Amps outlet1ADeciAmps Trap"
::= 4

outlet2BDeciAmpsTRAP TRAP-TYPE
ENTERPRISE geistmfg
VARIABLES { outlet2BDeciAmps }
DESCRIPTION "Amps outlet2BDeciAmps Trap"
::= 5

outlet3CDeciAmpsTRAP TRAP-TYPE
ENTERPRISE geistmfg
VARIABLES { outlet3CDeciAmps }
DESCRIPTION "Amps outlet3CDeciAmps Trap"
::= 6



outlet4ADeciAmpsTRAP TRAP-TYPE
ENTERPRISE geistmfg
VARIABLES { outlet4ADeciAmps }
DESCRIPTION "Amps outlet4ADeciAmps Trap"
::= 7

outlet5BDeciAmpsTRAP TRAP-TYPE
ENTERPRISE geistmfg
VARIABLES { outlet5BDeciAmps }
DESCRIPTION "Amps outlet5BDeciAmps Trap"
::= 8

outlet6CDeciAmpsTRAP TRAP-TYPE
ENTERPRISE geistmfg
VARIABLES { outlet6CDeciAmps }
DESCRIPTION "Amps outlet6CDeciAmps Trap"
::= 9



outlet7ADeciAmpsTRAP TRAP-TYPE
ENTERPRISE geistmfg
VARIABLES { outlet7ADeciAmps }
DESCRIPTION "Amps outlet7ADeciAmps Trap"
::= 10

outlet8BDeciAmpsTRAP TRAP-TYPE
ENTERPRISE geistmfg
VARIABLES { outlet8BDeciAmps }
DESCRIPTION "Amps outlet8BDeciAmps Trap"
::= 11

outlet9CDeciAmpsTRAP TRAP-TYPE
ENTERPRISE geistmfg
VARIABLES { outlet9CDeciAmps }
DESCRIPTION "Amps outlet9CDeciAmps Trap"
::= 12



outlet10ADeciAmpsTRAP TRAP-TYPE
ENTERPRISE geistmfg
VARIABLES { outlet10ADeciAmps }
DESCRIPTION "Amps outlet10ADeciAmps Trap"
::= 13

outlet11BDeciAmpsTRAP TRAP-TYPE
ENTERPRISE geistmfg
VARIABLES { outlet11BDeciAmps }
DESCRIPTION "Amps outlet11BDeciAmps Trap"
::= 14

outlet12CDeciAmpsTRAP TRAP-TYPE
ENTERPRISE geistmfg
VARIABLES { outlet12CDeciAmps }
DESCRIPTION "Amps outlet12CDeciAmps Trap"
::= 15



END
