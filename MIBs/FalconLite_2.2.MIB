--  Title:    FALCONLITE.MIB
--  Version:  v2.2
--  Date:     11/04/02 13:00pm
--
--  Copyright @ 2002 RLE Technologies.  All rights reserved worldwide.
--
--  This MIB defines objects for the RLE FalconLite SNMP Agent.
--

RLE-FALCONLITE-MIB DEFINITIONS ::= BEGIN

IMPORTS
        TruthValue
                FROM RFC1253
        DisplayString
                FROM RFC1213-MIB
        OBJECT-TYPE
                FROM RFC-1212
        Counter, enterprises
                FROM RFC1155-SMI;
   PositiveInteger ::= INTEGER (1..'FFFFFFFF'h)

rle OBJECT IDENTIFIER ::= { enterprises  3184 }

products   OBJECT IDENTIFIER ::= { rle  1 }

falconLite   OBJECT IDENTIFIER ::= { products  3 }

falconLiteMIB OBJECT IDENTIFIER ::= { falconLite 1 }

falconLiteIdent OBJECT IDENTIFIER ::= { falconLiteMIB 1 }

falconLiteIdentManufacturer OBJECT-TYPE
    SYNTAX  DisplayString
    ACCESS  read-only
    STATUS  mandatory
    DESCRIPTION
           "The Monitor Control Unit manufacturer."
    ::= { falconLiteIdent  1 }

falconLiteIdentModel OBJECT-TYPE
    SYNTAX  DisplayString
    ACCESS  read-only
    STATUS  mandatory
    DESCRIPTION
           "The Monitor Control Unit Model designation."
    ::= { falconLiteIdent  2 }

falconLiteIdentSoftwareVersion OBJECT-TYPE
    SYNTAX  DisplayString
    ACCESS  read-only
    STATUS  mandatory
    DESCRIPTION
           "The falconLite SNMP Agent software version."
    ::= { falconLiteIdent  3 }

falconLiteIdentSpecific OBJECT-TYPE
    SYNTAX  OBJECT IDENTIFIER
    ACCESS  read-only
    STATUS  mandatory
    DESCRIPTION
           "A reference to MIB definitions specific to the
            particular Monitor Unit being managed. This
            object is used to locate the product-specific MIB
            for this device.

            If this information is not present, its value
            should be the OBJECT IDENTIFIER { 0 0 },
            which is a syntactically valid object identifier,
            and any conformant implementation of ASN.1 and BER
            must be able to generate and recognize this value."
    ::= { falconLiteIdent  4 }

falconLiteSystem OBJECT IDENTIFIER ::= { falconLiteMIB 2 }

falconLiteClock OBJECT-TYPE
    SYNTAX  DisplayString
    ACCESS  read-write
    STATUS  mandatory
    DESCRIPTION
           "The falconLite internal clock settings.
            Displayed as MM/DD/YY HH:MM:SS"
    ::= { falconLiteSystem  1 }

falconLiteInputVoltage OBJECT-TYPE
    SYNTAX  INTEGER (-2147483648..2147483647)
    ACCESS  read-only
    STATUS  mandatory
    DESCRIPTION
           "The falconLite input voltage (DC Power)."
    ::= { falconLiteSystem  4 }

falconLiteAnalogAverage OBJECT-TYPE
    SYNTAX  INTEGER (0..60)
    ACCESS  read-write
    STATUS  mandatory
    DESCRIPTION
           "This is the analog averaging duration in seconds.
            The analog input readings are averaged for this time
            period before updating. This value must be set to
            1,2,3,4,5,6,10,15,20,30 or 60 seconds.
            This variable is stored in non-volatile memory."
    ::= { falconLiteSystem  7 }

falconLiteInputs OBJECT IDENTIFIER ::= { falconLiteMIB  3 }

falconLiteInput1 OBJECT IDENTIFIER ::= { falconLiteInputs 1 }

falconLiteInput1State OBJECT-TYPE
    SYNTAX  INTEGER {
    internalTemperature(8)
}
    ACCESS  read-only
    STATUS  mandatory
    DESCRIPTION
           "The state of use of Input Number 1. This input is
            an internal temperature sensor."
    ::= { falconLiteInput1  1 }

falconLiteInput1Reading OBJECT-TYPE
    SYNTAX  INTEGER (-2147483648..2147483647)
    ACCESS  read-only
    STATUS  mandatory
    DESCRIPTION
           "The reading for sensor 1, the internal temperature sensor."
    ::= { falconLiteInput1  2 }

falconLiteInput1Offset OBJECT-TYPE
    SYNTAX  INTEGER (-2147483648..2147483647)
    ACCESS  read-write
    STATUS  mandatory
    DESCRIPTION
           "A correction Offset associated with the sensor variable.
            The value of Offset is added to the value from
            Input Sensor Number 1 to obtain the value of
            the Input1 variable. The Offset variable is stored in
            non-volatile memory."
    ::= { falconLiteInput1  4 }

falconLiteInput1Label OBJECT-TYPE
    SYNTAX  DisplayString
    ACCESS  read-write
    STATUS  mandatory
    DESCRIPTION
           "A user-defined text string associated with Input Number 1.
            The text string is stored in non-volatile memory."
    ::= { falconLiteInput1  5 }

falconLiteInput1UOM OBJECT-TYPE
    SYNTAX  DisplayString
    ACCESS  read-write
    STATUS  mandatory
    DESCRIPTION
           "A user-defined text string associated with Input Number 1.
            The text string is stored in non-volatile memory."
    ::= { falconLiteInput1  6 }

falconLiteInput1HighLimit2 OBJECT-TYPE
    SYNTAX  INTEGER (-2147483648..2147483647)
    ACCESS  read-write
    STATUS  mandatory
    DESCRIPTION
           "When input 1 reaches or exceeds this value a trap will
            be generated signifying a high alarm condition at
            sensor 1.
            The HighLimit2 variable is stored in non-volatile memory."
    ::= { falconLiteInput1  7 }

falconLiteInput1HighLimit OBJECT-TYPE
    SYNTAX  INTEGER (-2147483648..2147483647)
    ACCESS  read-write
    STATUS  mandatory
    DESCRIPTION
           "When input 1 reaches or exceeds this value a trap will
            be generated signifying a high alarm condition at
            sensor 1.
            The HighLimit variable is stored in non-volatile memory."
    ::= { falconLiteInput1  8 }

falconLiteInput1LowLimit OBJECT-TYPE
    SYNTAX  INTEGER (-2147483648..2147483647)
    ACCESS  read-write
    STATUS  mandatory
    DESCRIPTION
           "When input 1 reaches or goes below this value a trap will
            be generated signifying a low alarm condition at sensor 1.
            The LowLimit variable is stored in non-volatile memory."
    ::= { falconLiteInput1  9 }

falconLiteInput1LowLimit2 OBJECT-TYPE
    SYNTAX  INTEGER (-2147483648..2147483647)
    ACCESS  read-write
    STATUS  mandatory
    DESCRIPTION
           "When input 1 reaches or goes below this value a trap will
            be generated signifying a low alarm condition at sensor 1.
            The LowLimit variable is stored in non-volatile memory."
    ::= { falconLiteInput1  10 }

falconLiteInput1Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput1  12 }

falconLiteInput1Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconLiteInput1  13 }

falconLiteInput1Schedule OBJECT-TYPE
    SYNTAX  INTEGER {
    none(0),
    a(1),
    b(2)
}
    ACCESS  read-write
    STATUS  mandatory
    DESCRIPTION
           "The current alarm disable schedule for input 1."
    ::= { falconLiteInput1  14 }

falconLiteInput1OffLabel OBJECT-TYPE
    SYNTAX  DisplayString
    ACCESS  read-write
    STATUS  mandatory
    DESCRIPTION
           "A user-defined text string associated with Input Number 1.
           This string is used for off text.
           The text string is stored in non-volatile memory."
    ::= { falconLiteInput1  15 }

falconLiteInput2 OBJECT IDENTIFIER ::= { falconLiteInputs 2 }

falconLiteInput2State OBJECT-TYPE
    SYNTAX  INTEGER {
    internalHumidity(9)
}
    ACCESS  read-only
    STATUS  mandatory
    DESCRIPTION
           "The state of use of Input Number 2. This is the
            internal humidity sensor."
    ::= { falconLiteInput2  1 }

falconLiteInput2Reading OBJECT-TYPE
    SYNTAX  INTEGER (-2147483648..2147483647)
    ACCESS  read-only
    STATUS  mandatory
    DESCRIPTION
           "The reading for sensor 2, the internal humidity sensor."
    ::= { falconLiteInput2  2 }

falconLiteInput2Offset OBJECT-TYPE
    SYNTAX  INTEGER (-2147483648..2147483647)
    ACCESS  read-write
    STATUS  mandatory
    DESCRIPTION
           "A correction Offset associated with the sensor variable.
            The value of Offset is added to the value from
            Input Sensor Number 2 to obtain the value of
            the Input2 variable. The Offset variable is stored in
            non-volatile memory."
    ::= { falconLiteInput2  4 }

falconLiteInput2Label OBJECT-TYPE
    SYNTAX  DisplayString
    ACCESS  read-write
    STATUS  mandatory
    DESCRIPTION
           "A user-defined text string associated with Input Number 2.
            The text string is stored in non-volatile memory."
    ::= { falconLiteInput2  5 }

falconLiteInput2UOM OBJECT-TYPE
    SYNTAX  DisplayString
    ACCESS  read-write
    STATUS  mandatory
    DESCRIPTION
           "A user-defined text string associated with Input Number 2.
            The text string is stored in non-volatile memory."
    ::= { falconLiteInput2  6 }

falconLiteInput2HighLimit2 OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { falconLiteInput2  7 }

falconLiteInput2HighLimit OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { falconLiteInput2  8 }

falconLiteInput2LowLimit OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { falconLiteInput2  9 }

falconLiteInput2LowLimit2 OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { falconLiteInput2  10 }

falconLiteInput2RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconLiteInput2  11 }

falconLiteInput2Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput2  12 }

falconLiteInput2Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconLiteInput2  13 }

falconLiteInput2Schedule OBJECT-TYPE
    SYNTAX  INTEGER {
    none(0),
    a(1),
    b(2)
}
    ACCESS  read-write
    STATUS  mandatory
    DESCRIPTION
           "The current alarm disable schedule for input 2."
    ::= { falconLiteInput2  14 }

falconLiteInput2OffLabel OBJECT-TYPE
    SYNTAX  DisplayString
    ACCESS  read-write
    STATUS  mandatory
    DESCRIPTION
           "A user-defined text string associated with Input Number 2.
           This string is used for off text.
           The text string is stored in non-volatile memory."
    ::= { falconLiteInput2  15 }

falconLiteInput3 OBJECT IDENTIFIER ::= { falconLiteInputs 3 }

falconLiteInput3State OBJECT-TYPE
    SYNTAX  INTEGER {
    notInstalled(1),
    analog4to20Installed(2)
}
    ACCESS  read-write
    STATUS  mandatory
    DESCRIPTION
           "The state of use of Input Number 3. When a sensor is
            connected to Input 3 set State to installed(2) to
            indicate that the value of falconLiteReading3 is valid.
            When no sensor is connected to Input 3 set the State 
            to notInstalled(1) to indicate that the value of
            falconLiteReading3 may not be valid.
            This variable is stored in non-volatile memory."
    ::= { falconLiteInput3  1 }

falconLiteInput3Reading OBJECT-TYPE
    SYNTAX  INTEGER (-2147483648..2147483647)
    ACCESS  read-only
    STATUS  mandatory
    DESCRIPTION
           "The reading for sensor 3."
    ::= { falconLiteInput3  2 }

falconLiteInput3Gain OBJECT-TYPE
    SYNTAX  INTEGER (-2147483648..2147483647)
    ACCESS  read-write
    STATUS  mandatory
    DESCRIPTION
           "A correction gain associated with the sensor variable.
            The value of gain is multiplied by the value from
            Input Sensor Number 3 to obtain the value of
            the Input3 variable. The gain variable is stored in
            non-volatile memory."
    ::= { falconLiteInput3  3 }

falconLiteInput3Offset OBJECT-TYPE
    SYNTAX  INTEGER (-2147483648..2147483647)
    ACCESS  read-write
    STATUS  mandatory
    DESCRIPTION
           "A correction Offset associated with the sensor variable.
            The value of Offset is added to the value from
            Input Sensor Number 3 to obtain the value of
            the Input3 variable. The Offset variable is stored in
            non-volatile memory."
    ::= { falconLiteInput3  4 }

falconLiteInput3Label OBJECT-TYPE
    SYNTAX  DisplayString
    ACCESS  read-write
    STATUS  mandatory
    DESCRIPTION
           "A user-defined text string associated with Input Number 3.
            The text string is stored in non-volatile memory."
    ::= { falconLiteInput3  5 }

falconLiteInput3UOM OBJECT-TYPE
    SYNTAX  DisplayString
    ACCESS  read-write
    STATUS  mandatory
    DESCRIPTION
           "A user-defined text string associated with Input Number 3.
            The text string is stored in non-volatile memory."
    ::= { falconLiteInput3  6 }

falconLiteInput3HighLimit2 OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { falconLiteInput3  7 }

falconLiteInput3HighLimit OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { falconLiteInput3  8 }

falconLiteInput3LowLimit OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { falconLiteInput3  9 }

falconLiteInput3LowLimit2 OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { falconLiteInput3  10 }

falconLiteInput3Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput3  12 }

falconLiteInput3Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconLiteInput3  13 }

falconLiteInput3Schedule OBJECT-TYPE
    SYNTAX  INTEGER {
    none(0),
    a(1),
    b(2)
}
    ACCESS  read-write
    STATUS  mandatory
    DESCRIPTION
           "The current alarm disable schedule for input 3."
    ::= { falconLiteInput3  14 }

falconLiteInput3OffLabel OBJECT-TYPE
    SYNTAX  DisplayString
    ACCESS  read-write
    STATUS  mandatory
    DESCRIPTION
           "A user-defined text string associated with Input Number 3.
           This string is used for digital off text.
           The text string is stored in non-volatile memory."
    ::= { falconLiteInput3  15 }

falconLiteInput4 OBJECT IDENTIFIER ::= { falconLiteInputs 4 }

falconLiteInput4State OBJECT-TYPE
    SYNTAX  INTEGER {
    notInstalled(1),
    analog4to20Installed(2)
}
    ACCESS  read-write
    STATUS  mandatory
    DESCRIPTION
           "The state of use of Input Number 4. When a sensor is
            connected to Input 4 set State to installed(2) to
            indicate that the value of falconLiteReading4 is valid.
            When no sensor is connected to Input 4 set
            State to notInstalled(1) to indicate that the value of
            falconLiteReading4 may not be valid.
            This variable is stored in non-volatile memory."
    ::= { falconLiteInput4  1 }

falconLiteInput4Reading OBJECT-TYPE
    SYNTAX  INTEGER (-2147483648..2147483647)
    ACCESS  read-only
    STATUS  mandatory
    DESCRIPTION
           "The reading for sensor 4."
    ::= { falconLiteInput4  2 }

falconLiteInput4Gain OBJECT-TYPE
    SYNTAX  INTEGER (-2147483648..2147483647)
    ACCESS  read-write
    STATUS  mandatory
    DESCRIPTION
           "A correction gain associated with the sensor variable.
            The value of gain is multiplied by the value from
            Input Sensor Number 4 to obtain the value of
            the Input4 variable. The gain variable is stored in
            non-volatile memory."
    ::= { falconLiteInput4  3 }

falconLiteInput4Offset OBJECT-TYPE
    SYNTAX  INTEGER (-2147483648..2147483647)
    ACCESS  read-write
    STATUS  mandatory
    DESCRIPTION
           "A correction Offset associated with the sensor variable.
            The value of Offset is added to the value from
            Input Sensor Number 4 to obtain the value of
            the Input4 variable. The Offset variable is stored in
            non-volatile memory."
    ::= { falconLiteInput4  4 }

falconLiteInput4Label OBJECT-TYPE
    SYNTAX  DisplayString
    ACCESS  read-write
    STATUS  mandatory
    DESCRIPTION
           "A user-defined text string associated with Input Number 4.
            The text string is stored in non-volatile memory."
    ::= { falconLiteInput4  5 }

falconLiteInput4UOM OBJECT-TYPE
    SYNTAX  DisplayString
    ACCESS  read-write
    STATUS  mandatory
    DESCRIPTION
           "A user-defined text string associated with Input Number 4.
            The text string is stored in non-volatile memory."
    ::= { falconLiteInput4  6 }

falconLiteInput4HighLimit2 OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { falconLiteInput4  7 }

falconLiteInput4HighLimit OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { falconLiteInput4  8 }

falconLiteInput4LowLimit OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { falconLiteInput4  9 }

falconLiteInput4LowLimit2 OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { falconLiteInput4  10 }

falconLiteInput4Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput4  12 }

falconLiteInput4Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconLiteInput4  13 }

falconLiteInput4Schedule OBJECT-TYPE
    SYNTAX  INTEGER {
    none(0),
    a(1),
    b(2)
}
    ACCESS  read-write
    STATUS  mandatory
    DESCRIPTION
           "The current alarm disable schedule for input 4."
    ::= { falconLiteInput4  14 }

falconLiteInput4OffLabel OBJECT-TYPE
    SYNTAX  DisplayString
    ACCESS  read-write
    STATUS  mandatory
    DESCRIPTION
           "A user-defined text string associated with Input Number 4.
           This string is used for off text.
           The text string is stored in non-volatile memory."
    ::= { falconLiteInput4  15 }

falconLiteInput5 OBJECT IDENTIFIER ::= { falconLiteInputs 5 }

falconLiteInput5State OBJECT-TYPE
    SYNTAX  INTEGER {
    notInstalled(1),
    digitalNOInstalled(3),
    digitalNCInstalled(4),
	 digitalSTInstalled(5)
}
    ACCESS  read-write
    STATUS  mandatory
    DESCRIPTION
           "The state of use of Input Number 5. When a sensor is
            connected to Input 5 set State to installed(2) to
            indicate that the value of falconLiteReading4 is valid.
            When no sensor is connected to Input 5 set
            State to notInstalled(1) to indicate that the value of
            falconLiteReading5 may not be valid.
            This variable is stored in non-volatile memory."
    ::= { falconLiteInput5  1 }

falconLiteInput5Reading OBJECT-TYPE
    SYNTAX  INTEGER (-2147483648..2147483647)
    ACCESS  read-only
    STATUS  mandatory
    DESCRIPTION
           "The reading for sensor 5.
            If the input is digital, the reading will be 1 (active) or
            0 (inactive)"
    ::= { falconLiteInput5  2 }

falconLiteInput5Label OBJECT-TYPE
    SYNTAX  DisplayString
    ACCESS  read-write
    STATUS  mandatory
    DESCRIPTION
           "A user-defined text string associated with Input Number 5.
            The text string is stored in non-volatile memory."
    ::= { falconLiteInput5  5 }

falconLiteInput5Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput5  12 }

falconLiteInput5Schedule OBJECT-TYPE
    SYNTAX  INTEGER {
    none(0),
    a(1),
    b(2)
}
    ACCESS  read-write
    STATUS  mandatory
    DESCRIPTION
           "The current alarm disable schedule for input 5."
    ::= { falconLiteInput5  14 }

falconLiteInput5OffLabel OBJECT-TYPE
    SYNTAX  DisplayString
    ACCESS  read-write
    STATUS  mandatory
    DESCRIPTION
           "A user-defined text string associated with Input Number 5.
           This string is used for digital off text.
           The text string is stored in non-volatile memory."
    ::= { falconLiteInput5  15 }

falconLiteInput6 OBJECT IDENTIFIER ::= { falconLiteInputs 6 }

falconLiteInput6State OBJECT-TYPE
    SYNTAX  INTEGER {
    notInstalled(1),
    digitalNOInstalled(3),
    digitalNCInstalled(4),
	 digitalSTInstalled(5)
}
    ACCESS  read-write
    STATUS  mandatory
    DESCRIPTION
           "The state of use of Input Number 6. When a sensor is
            connected to Input 6 set State to installed(2) to
            indicate that the value of falconLiteReading6 is valid.
            When no sensor is connected to Input 6 set
            State to notInstalled(1) to indicate that the value of
            falconLiteReading6 may not be valid.
            This variable is stored in non-volatile memory."
    ::= { falconLiteInput6  1 }

falconLiteInput6Reading OBJECT-TYPE
    SYNTAX  INTEGER (-2147483648..2147483647)
    ACCESS  read-only
    STATUS  mandatory
    DESCRIPTION
           "The reading for sensor 6.
            If the input is digital, the reading will be 1 (active) or
            0 (inactive)"
    ::= { falconLiteInput6  2 }

falconLiteInput6Label OBJECT-TYPE
    SYNTAX  DisplayString
    ACCESS  read-write
    STATUS  mandatory
    DESCRIPTION
           "A user-defined text string associated with Input Number 6.
            The text string is stored in non-volatile memory."
    ::= { falconLiteInput6  5 }

falconLiteInput6Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput6  12 }

falconLiteInput6Schedule OBJECT-TYPE
    SYNTAX  INTEGER {
    none(0),
    a(1),
    b(2)
}
    ACCESS  read-write
    STATUS  mandatory
    DESCRIPTION
           "The current alarm disable schedule for input 6."
    ::= { falconLiteInput6  14 }

falconLiteInput6OffLabel OBJECT-TYPE
    SYNTAX  DisplayString
    ACCESS  read-write
    STATUS  mandatory
    DESCRIPTION
           "A user-defined text string associated with Input Number 6.
           This string is used for digital off text.
           The text string is stored in non-volatile memory."
    ::= { falconLiteInput6  15 }

falconLiteInput7 OBJECT IDENTIFIER ::= { falconLiteInputs 7 }

falconLiteInput7State OBJECT-TYPE
    SYNTAX  INTEGER {
    notInstalled(1),
    digitalNOInstalled(3),
    digitalNCInstalled(4),
	 digitalSTInstalled(5)
}
    ACCESS  read-write
    STATUS  mandatory
    DESCRIPTION
           "The state of use of Input Number 7. When a sensor is
            connected to Input 7 set State to installed(2) to
            indicate that the value of falconLiteReading4 is valid.
            When no sensor is connected to Input 7 set
            State to notInstalled(1) to indicate that the value of
            falconLiteReading7 may not be valid.
            This variable is stored in non-volatile memory."
    ::= { falconLiteInput7  1 }

falconLiteInput7Reading OBJECT-TYPE
    SYNTAX  INTEGER (-2147483648..2147483647)
    ACCESS  read-only
    STATUS  mandatory
    DESCRIPTION
           "The reading for sensor 7.
            If the input is digital, the reading will be 1 (active) or
            0 (inactive)"
    ::= { falconLiteInput7  2 }

falconLiteInput7Label OBJECT-TYPE
    SYNTAX  DisplayString
    ACCESS  read-write
    STATUS  mandatory
    DESCRIPTION
           "A user-defined text string associated with Input Number 7.
            The text string is stored in non-volatile memory."
    ::= { falconLiteInput7  5 }

falconLiteInput7Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput7  12 }

falconLiteInput7Schedule OBJECT-TYPE
    SYNTAX  INTEGER {
    none(0),
    a(1),
    b(2)
}
    ACCESS  read-only
    STATUS  mandatory
    DESCRIPTION
           "The current alarm disable schedule for input 7."
    ::= { falconLiteInput7  14 }

falconLiteInput7OffLabel OBJECT-TYPE
    SYNTAX  DisplayString
    ACCESS  read-write
    STATUS  mandatory
    DESCRIPTION
           "A user-defined text string associated with Input Number 7.
           This string is used for digital off text.
           The text string is stored in non-volatile memory."
    ::= { falconLiteInput7  15 }

falconLiteInput8 OBJECT IDENTIFIER ::= { falconLiteInputs 8 }

falconLiteInput8State OBJECT-TYPE
    SYNTAX  INTEGER {
    notInstalled(1),
    digitalNOInstalled(3),
    digitalNCInstalled(4),
	 digitalSTInstalled(5)
}
    ACCESS  read-write
    STATUS  mandatory
    DESCRIPTION
           "The state of use of Input Number 8. When a sensor is
            connected to Input 8 set State to installed(2) to
            indicate that the value of falconLiteReading8 is valid.
            When no sensor is connected to Input 8 set
            State to notInstalled(1) to indicate that the value of
            falconLiteReading8 may not be valid.
            This variable is stored in non-volatile memory."
    ::= { falconLiteInput8  1 }

falconLiteInput8Reading OBJECT-TYPE
    SYNTAX  INTEGER (-2147483648..2147483647)
    ACCESS  read-only
    STATUS  mandatory
    DESCRIPTION
           "The reading for sensor 8.
            If the input is digital, the reading will be 1 (active) or
            0 (inactive)"
    ::= { falconLiteInput8  2 }

falconLiteInput8Label OBJECT-TYPE
    SYNTAX  DisplayString
    ACCESS  read-write
    STATUS  mandatory
    DESCRIPTION
           "A user-defined text string associated with Input Number 8.
            The text string is stored in non-volatile memory."
    ::= { falconLiteInput8  5 }

falconLiteInput8Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconLiteInput8  12 }

falconLiteInput8Schedule OBJECT-TYPE
    SYNTAX  INTEGER {
    none(0),
    a(1),
    b(2)
}
    ACCESS  read-only
    STATUS  mandatory
    DESCRIPTION
           "The current alarm disable schedule for input 8."
    ::= { falconLiteInput8  14 }

falconLiteInput8OffLabel OBJECT-TYPE
    SYNTAX  DisplayString
    ACCESS  read-write
    STATUS  mandatory
    DESCRIPTION
           "A user-defined text string associated with Input Number 8.
           This string is used for off text.
           The text string is stored in non-volatile memory."
    ::= { falconLiteInput8  15 }

falconLiteAlarms OBJECT IDENTIFIER ::= { falconLiteMIB  5 }

falconLiteAlarmsPresent OBJECT-TYPE
    SYNTAX     Gauge32
    ACCESS     read-only
    STATUS     mandatory
    DESCRIPTION
        "The present number of active alarm conditions."
    ::= { falconLiteAlarms 1 }

falconLiteAlarmTable OBJECT-TYPE
    SYNTAX     SEQUENCE OF FalconLiteAlarmEntry
    ACCESS     not-accessible
    STATUS     mandatory
    DESCRIPTION
       "A list of alarm table entries.  The table contains
        zero, one, or many rows at any moment, depending upon
        the number of alarm conditions in effect.  The table
        is initially empty at agent startup.  The agent
        creates a row in the table each time a condition is
        detected and deletes that row when that condition no
        longer pertains.  The agent creates the first row with
        falconLiteAlarmId equal to 1, and increments the value of
        falconLiteAlarmId each time a new row is created, wrapping to
        the first free value greater than or equal to 1 when
        the maximum value of falconLiteAlarmId would otherwise be
        exceeded.  Consequently, after multiple operations,
        the table may become sparse, e.g., containing entries
        for rows 95, 100, 101, and 203 and the entries should
        not be assumed to be in chronological order because
        falconLiteAlarmId might have wrapped.

        Alarms are named by an AutonomousType (OBJECT
        IDENTIFIER), falconLiteAlarmDescr, to allow a single table to
        reflect well known alarms plus alarms defined by a
        particular implementation, i.e., as documented in the
        private enterprise MIB definition for the device.  No
        two rows will have the same value of falconLiteAlarmDescr,
        since alarms define conditions.  In order to meet this
        requirement, care should be taken in the definition of
        alarm conditions to insure that a system cannot enter
        the same condition multiple times simultaneously.

        The number of rows in the table at any given time is
        reflected by the value of falconLiteAlarmsPresent."
    ::= { falconLiteAlarms 2 }

falconLiteAlarmEntry OBJECT-TYPE
    SYNTAX     FalconLiteAlarmEntry
    ACCESS     not-accessible
    STATUS     mandatory
    DESCRIPTION
         "An entry containing information applicable to a
         particular alarm."
   INDEX { falconLiteAlarmId }
   ::= { falconLiteAlarmTable 1 }

FalconLiteAlarmEntry ::= SEQUENCE {
    falconLiteAlarmId          PositiveInteger,
    falconLiteAlarmDescr       OBJECT IDENTIFIER
}

falconLiteAlarmId OBJECT-TYPE
    SYNTAX     PositiveInteger
    ACCESS     not-accessible
    STATUS     mandatory
    DESCRIPTION
         "A unique identifier for an alarm condition.  This
          value must remain constant."
    ::= { falconLiteAlarmEntry 1 }

falconLiteAlarmDescr OBJECT-TYPE
    SYNTAX     OBJECT IDENTIFIER
    ACCESS     read-only
    STATUS     mandatory
    DESCRIPTION
        "A reference to an alarm description object.  The
         object referenced should not be accessible, but rather
         be used to provide a unique description of the alarm
         condition."
    ::= { falconLiteAlarmEntry 2 }

--
-- Well known alarm conditions.
--

falconLiteWellKnownAlarms    OBJECT IDENTIFIER ::= { falconLiteAlarms 3 }

falconLiteInput1HighAlarm OBJECT-TYPE
    SYNTAX     OBJECT IDENTIFIER
    ACCESS     read-only
    STATUS     mandatory
    DESCRIPTION
        "The reading for sensor 1 has reached the high limit
        value."
    ::= { falconLiteWellKnownAlarms  1 }

falconLiteInput1LowAlarm OBJECT-TYPE
    SYNTAX     OBJECT IDENTIFIER
    ACCESS     read-only
    STATUS     mandatory
    DESCRIPTION
        "The reading for sensor 1 has reached the low limit
        value."
    ::= { falconLiteWellKnownAlarms  2 }

falconLiteInput1High2Alarm OBJECT-TYPE
    SYNTAX     OBJECT IDENTIFIER
    ACCESS     read-only
    STATUS     mandatory
    DESCRIPTION
        "The reading for sensor 1 has reached the high limit
        value."
    ::= { falconLiteWellKnownAlarms  3 }

falconLiteInput1Low2Alarm OBJECT-TYPE
    SYNTAX     OBJECT IDENTIFIER
    ACCESS     read-only
    STATUS     mandatory
    DESCRIPTION
        "The reading for sensor 1 has reached the low limit
        value."
    ::= { falconLiteWellKnownAlarms  4 }

falconLiteInput2HighAlarm OBJECT-TYPE
    SYNTAX     OBJECT IDENTIFIER
    ACCESS     read-only
    STATUS     mandatory
    DESCRIPTION
        "The reading for sensor 2 has reached the high limit
        value."
    ::= { falconLiteWellKnownAlarms  5 }

falconLiteInput2LowAlarm OBJECT-TYPE
    SYNTAX     OBJECT IDENTIFIER
    ACCESS     read-only
    STATUS     mandatory
    DESCRIPTION
        "The reading for sensor 2 has reached the low limit
        value."
    ::= { falconLiteWellKnownAlarms  6 }

falconLiteInput2High2Alarm OBJECT-TYPE
    SYNTAX     OBJECT IDENTIFIER
    ACCESS     read-only
    STATUS     mandatory
    DESCRIPTION
        "The reading for sensor 2 has reached the high limit
        value."
    ::= { falconLiteWellKnownAlarms  7 }

falconLiteInput2Low2Alarm OBJECT-TYPE
    SYNTAX     OBJECT IDENTIFIER
    ACCESS     read-only
    STATUS     mandatory
    DESCRIPTION
        "The reading for sensor 2 has reached the low limit
        value."
    ::= { falconLiteWellKnownAlarms  8 }

falconLiteInput3HighAlarm OBJECT-TYPE
    SYNTAX     OBJECT IDENTIFIER
    ACCESS     read-only
    STATUS     mandatory
    DESCRIPTION
        "The reading for sensor 3 has reached the high limit
        value."
    ::= { falconLiteWellKnownAlarms  9 }

falconLiteInput3LowAlarm OBJECT-TYPE
    SYNTAX     OBJECT IDENTIFIER
    ACCESS     read-only
    STATUS     mandatory
    DESCRIPTION
        "The reading for sensor 3 has reached the low limit
        value."
    ::= { falconLiteWellKnownAlarms  10 }

falconLiteInput3High2Alarm OBJECT-TYPE
    SYNTAX     OBJECT IDENTIFIER
    ACCESS     read-only
    STATUS     mandatory
    DESCRIPTION
        "The reading for sensor 3 has reached the high limit
        value."
    ::= { falconLiteWellKnownAlarms  11 }

falconLiteInput3Low2Alarm OBJECT-TYPE
    SYNTAX     OBJECT IDENTIFIER
    ACCESS     read-only
    STATUS     mandatory
    DESCRIPTION
        "The reading for sensor 3 has reached the low limit
        value."
    ::= { falconLiteWellKnownAlarms  12 }

falconLiteInput4HighAlarm OBJECT-TYPE
    SYNTAX     OBJECT IDENTIFIER
    ACCESS     read-only
    STATUS     mandatory
    DESCRIPTION
        "The reading for sensor 4 has reached the high limit
        value."
    ::= { falconLiteWellKnownAlarms  13 }

falconLiteInput4LowAlarm OBJECT-TYPE
    SYNTAX     OBJECT IDENTIFIER
    ACCESS     read-only
    STATUS     mandatory
    DESCRIPTION
        "The reading for sensor 4 has reached the low limit
        value."
    ::= { falconLiteWellKnownAlarms  14 }

falconLiteInput4High2Alarm OBJECT-TYPE
    SYNTAX     OBJECT IDENTIFIER
    ACCESS     read-only
    STATUS     mandatory
    DESCRIPTION
        "The reading for sensor 4 has reached the high limit
        value."
    ::= { falconLiteWellKnownAlarms  15 }

falconLiteInput4Low2Alarm OBJECT-TYPE
    SYNTAX     OBJECT IDENTIFIER
    ACCESS     read-only
    STATUS     mandatory
    DESCRIPTION
        "The reading for sensor 4 has reached the low limit
        value."
    ::= { falconLiteWellKnownAlarms  16 }

falconLiteInput5DigAlarm OBJECT-TYPE
    SYNTAX     OBJECT IDENTIFIER
    ACCESS     read-only
    STATUS     mandatory
    DESCRIPTION
        "The digital input 5 has been activated."
    ::= { falconLiteWellKnownAlarms  85 }

falconLiteInput6DigAlarm OBJECT-TYPE
    SYNTAX     OBJECT IDENTIFIER
    ACCESS     read-only
    STATUS     mandatory 
    DESCRIPTION
        "The digital input 6 has been activated."
    ::= { falconLiteWellKnownAlarms  86 }

falconLiteInput7DigAlarm OBJECT-TYPE
    SYNTAX     OBJECT IDENTIFIER
    ACCESS     read-only
    STATUS     mandatory
    DESCRIPTION
        "The digital input 7 has been activated."
    ::= { falconLiteWellKnownAlarms  87 }

falconLiteInput8DigAlarm OBJECT-TYPE
    SYNTAX     OBJECT IDENTIFIER
    ACCESS     read-only
    STATUS     mandatory
    DESCRIPTION
        "The digital input 8 has been activated."
    ::= { falconLiteWellKnownAlarms  88 }

falconLiteAlarmHistory OBJECT IDENTIFIER ::= { falconLiteMIB  7 }

falconLiteAlarmHistoryEntries OBJECT-TYPE
    SYNTAX     Gauge32
    ACCESS read-only
    STATUS     mandatory
    DESCRIPTION
        "The present number of entries in the alarm history."
    ::= { falconLiteAlarmHistory 1 }

falconLiteAlarmHistoryClear OBJECT-TYPE
    SYNTAX  INTEGER {
    clearBuffer(1)
}
    ACCESS  read-write
    STATUS  mandatory
    DESCRIPTION
           "Setting this value to ClearBuffer(1) will clear the
            alarm history buffer. "
    ::= { falconLiteAlarmHistory 2 }

falconLiteAlarmHistoryTable OBJECT-TYPE
    SYNTAX     SEQUENCE OF FalconLiteAlarmHistoryEntry
    ACCESS not-accessible
    STATUS     mandatory
    DESCRIPTION
       "A list of alarm history table entries stored in the
        in the non-volatile memory.  The table contains zero,
        one, or many rows at any moment, depending upon the
        number of alarm conditions in effect. The falconLite creates
        a row in the table each time a new alarm is detected.
        The falconLite creates the first row with falconLiteAlarmHistoryId
        equal to 1, and increments the value of falconLiteAlarmHistoryId
        each time a new row is created, up to a maximum of 100.
        After 100 entries are created, the falconLite will overwrite
        the earliest entry with the latest alarm.
        The number of rows in the table at any given time is
        reflected by the value of falconLiteAlarmHistoryEntries."
    ::= { falconLiteAlarmHistory 3 }

falconLiteAlarmHistoryEntry OBJECT-TYPE
    SYNTAX     FalconLiteAlarmHistoryEntry
    ACCESS     not-accessible
    STATUS     mandatory
    DESCRIPTION
         "An entry containing information applicable to a
         particular alarm history entry."
   INDEX { falconLiteAlarmHistoryId }
   ::= { falconLiteAlarmHistoryTable 1 }

FalconLiteAlarmHistoryEntry ::= SEQUENCE {
    falconLiteAlarmHistoryId     PositiveInteger,
    falconLiteAlarmHistoryText   DisplayString
}

falconLiteAlarmHistoryId OBJECT-TYPE
    SYNTAX     PositiveInteger
    ACCESS not-accessible
    STATUS     mandatory
    DESCRIPTION
         "A unique identifier for an alarm condition.  This
          value must remain constant."
    ::= { falconLiteAlarmHistoryEntry 1 }

falconLiteAlarmHistoryText OBJECT-TYPE
    SYNTAX     DisplayString
    ACCESS read-only
    STATUS     mandatory
    DESCRIPTION
        "A text desciption of the alarm history entry.
         Each of the strings will have the following format,
         AHxxx-id-type-timestamp label
         xxx  = number entry in the table
         id   = Alarm ID
         type = HIGH, LOW, ALM or RTN
         timestamp = MM/DD/YY HH:MM:SS
         Label = The label associated with the input channel
         These alarms are stored in non-volatile memory."
    ::= { falconLiteAlarmHistoryEntry 2 }

falconLiteTrapSettings OBJECT IDENTIFIER ::= { falconLiteMIB  8 }

falconLitePersistantTraps OBJECT-TYPE
    SYNTAX  INTEGER (0..2147483647)
    ACCESS read-write
    STATUS     mandatory
    DESCRIPTION
        "The number of minutes between persistant traps.
         Set this to 0 to turn off persistant traps.
         This value is stored in non-volatile memory."
    ::= { falconLiteTrapSettings 1 }

falconLiteAlarmAcknowledge OBJECT-TYPE
    SYNTAX  INTEGER {
    acknowledgeAlarms(1)
}
    ACCESS  read-write
    STATUS  mandatory
    DESCRIPTION
           "Setting this value to AcknowledgeAlarms(1) will
            stop the falconLite from sending persistant traps
            and dial out sequences."
    ::= { falconLiteTrapSettings 2 }

falconLiteSchedules OBJECT IDENTIFIER ::= { falconLiteMIB  9 }

falconLiteScheduleABeginDOW OBJECT-TYPE
    SYNTAX  INTEGER {
    sunday(1),
    monday(2),
    tuesday(3),
    wednesday(4),
    thursday(5),
    friday(6),
    saturday(7)
}
    ACCESS  read-write
    STATUS  mandatory
    DESCRIPTION
           "The beginning day of the week for schedule A.
            This variable is stored in non-volatile memory."
    ::= { falconLiteSchedules  1 }

falconLiteScheduleAEndDOW OBJECT-TYPE
    SYNTAX  INTEGER {
    sunday(1),
    monday(2),
    tuesday(3),
    wednesday(4),
    thursday(5),
    friday(6),
    saturday(7)
}
    ACCESS  read-write
    STATUS  mandatory
    DESCRIPTION
           "The ending day of the week for schedule A.
            This variable is stored in non-volatile memory."
    ::= { falconLiteSchedules  2 }

falconLiteScheduleABeginTime OBJECT-TYPE
    SYNTAX  DisplayString
    ACCESS  read-write
    STATUS  mandatory
    DESCRIPTION
           "The schedule A beginning time of day.
            Displayed as HH:MM"
    ::= { falconLiteSchedules  3 }

falconLiteScheduleAEndTime OBJECT-TYPE
    SYNTAX  DisplayString
    ACCESS  read-write
    STATUS  mandatory
    DESCRIPTION
           "The schedule A ending time of day.
            Displayed as HH:MM"
    ::= { falconLiteSchedules  4 }

falconLiteScheduleBBeginDOW OBJECT-TYPE
    SYNTAX  INTEGER {
    sunday(1),
    monday(2),
    tuesday(3),
    wednesday(4),
    thursday(5),
    friday(6),
    saturday(7)
}
    ACCESS  read-write
    STATUS  mandatory
    DESCRIPTION
           "The beginning day of the week for schedule B.
            This variable is stored in non-volatile memory."
    ::= { falconLiteSchedules  5 }

falconLiteScheduleBEndDOW OBJECT-TYPE
    SYNTAX  INTEGER {
    sunday(1),
    monday(2),
    tuesday(3),
    wednesday(4),
    thursday(5),
    friday(6),
    saturday(7)
}
    ACCESS  read-write
    STATUS  mandatory
    DESCRIPTION
           "The ending day of the week for schedule B.
            This variable is stored in non-volatile memory."
    ::= { falconLiteSchedules  6 }

falconLiteScheduleBBeginTime OBJECT-TYPE
    SYNTAX  DisplayString
    ACCESS  read-write
    STATUS  mandatory
    DESCRIPTION
           "The schedule B beginning time of day.
            Displayed as HH:MM"
    ::= { falconLiteSchedules  7 }

falconLiteScheduleBEndTime OBJECT-TYPE
    SYNTAX  DisplayString
    ACCESS  read-write
    STATUS  mandatory
    DESCRIPTION
           "The schedule B ending time of day.
            Displayed as HH:MM"
    ::= { falconLiteSchedules  8 }

falconLitePortTrap OBJECT IDENTIFIER ::= { falconLiteMIB  10 }
falconLitePortTrapClear OBJECT IDENTIFIER ::= { falconLiteMIB  11 }

falconLitePort01Trap TRAP-TYPE
    ENTERPRISE   falconLitePortTrap 
    VARIABLES {
        falconLiteAlarmId,
        falconLiteAlarmDescr,
        falconLiteInput1Reading,
        falconLiteInput1UOM,
        falconLiteInput1Label
    }
    DESCRIPTION
        "The internal temperature sensor has reached an alarm state."
    ::= 1

falconlitePort02Trap TRAP-TYPE
    ENTERPRISE   falconLitePortTrap 
    VARIABLES {
        falconLiteAlarmId,
        falconLiteAlarmDescr,
        falconLiteInput2Reading,
        falconLiteInput2UOM,
        falconLiteInput2Label
    }
    DESCRIPTION
        "The internal humidity sensor has reached an alarm state."
    ::= 2

falconLitePort03Trap TRAP-TYPE
    ENTERPRISE   falconLitePortTrap 
    VARIABLES {
        falconLiteAlarmId,
        falconLiteAlarmDescr,
        falconLiteInput3Reading,
        falconLiteInput3UOM,
        falconLiteInput3Label
    }
    DESCRIPTION
        "The sensor on port #03 has reached an alarm state."
    ::= 3

falconLitePort04Trap TRAP-TYPE
    ENTERPRISE   falconLitePortTrap 
    VARIABLES {
        falconLiteAlarmId,
        falconLiteAlarmDescr,
        falconLiteInput4Reading,
        falconLiteInput4UOM,
        falconLiteInput4Label
    }
    DESCRIPTION
        "The sensor on port #04 has reached an alarm state."
    ::= 4

falconLitePort05Trap TRAP-TYPE
    ENTERPRISE   falconLitePortTrap 
    VARIABLES {
        falconLiteAlarmId,
        falconLiteAlarmDescr,
        falconLiteInput5Label
    }
    DESCRIPTION
        "The sensor on port #05 has reached an alarm state."
    ::= 5

falconLitePort06Trap TRAP-TYPE
    ENTERPRISE   falconLitePortTrap 
    VARIABLES {
        falconLiteAlarmId,
        falconLiteAlarmDescr,
        falconLiteInput6Label
    }
    DESCRIPTION
        "The sensor on port #06 has reached an alarm state."
    ::= 6

falconLitePort07Trap TRAP-TYPE
    ENTERPRISE   falconLitePortTrap 
    VARIABLES {
        falconLiteAlarmId,
        falconLiteAlarmDescr,
        falconLiteInput7Label
    }
    DESCRIPTION
        "The sensor on port #07 has reached an alarm state."
    ::= 7

falconLitePort08Trap TRAP-TYPE
    ENTERPRISE   falconLitePortTrap 
    VARIABLES {
        falconLiteAlarmId,
        falconLiteAlarmDescr,
        falconLiteInput8Label
    }
    DESCRIPTION
        "The sensor on port #08 has reached an alarm state."
    ::= 8

falconLitePort01TrapClear TRAP-TYPE
    ENTERPRISE   falconLitePortTrapClear 
    VARIABLES {
        falconLiteAlarmId,
        falconLiteAlarmDescr,
        falconLiteInput1Reading,
        falconLiteInput1UOM,
        falconLiteInput1OffLabel
    }
    DESCRIPTION
        "The internal temperature sensor alarm has returned to normal."
    ::= 1

falconLitePort02TrapClear TRAP-TYPE
    ENTERPRISE   falconLitePortTrapClear 
    VARIABLES {
        falconLiteAlarmId,
        falconLiteAlarmDescr,
        falconLiteInput2Reading,
        falconLiteInput2UOM,
        falconLiteInput2OffLabel
    }
    DESCRIPTION
        "The internal humidity sensor alarm has returned to normal."
    ::= 2

falconLitePort03TrapClear TRAP-TYPE
    ENTERPRISE   falconLitePortTrapClear 
    VARIABLES {
        falconLiteAlarmId,
        falconLiteAlarmDescr,
        falconLiteInput3Reading,
        falconLiteInput3UOM,
        falconLiteInput3OffLabel
    }
    DESCRIPTION
        "The sensor on port #03 has returned to normal."
    ::= 3

falconLitePort04TrapClear TRAP-TYPE
    ENTERPRISE   falconLitePortTrapClear 
    VARIABLES {
        falconLiteAlarmId,
        falconLiteAlarmDescr,
        falconLiteInput4Reading,
        falconLiteInput4UOM,
        falconLiteInput4OffLabel
    }
    DESCRIPTION
        "The sensor on port #04 has returned to normal."
    ::= 4

falconLitePort05TrapClear TRAP-TYPE
    ENTERPRISE   falconLitePortTrapClear 
    VARIABLES {
        falconLiteAlarmId,
        falconLiteAlarmDescr,
        falconLiteInput5OffLabel
    }
    DESCRIPTION
        "The sensor on port #05 has returned to normal."
    ::= 5

falconLitePort06TrapClear TRAP-TYPE
    ENTERPRISE   falconLitePortTrapClear 
    VARIABLES {
        falconLiteAlarmId,
        falconLiteAlarmDescr,
        falconLiteInput6OffLabel
    }
    DESCRIPTION
        "The sensor on port #06 has returned to normal."
    ::= 6

falconLitePort07TrapClear TRAP-TYPE
    ENTERPRISE   falconLitePortTrapClear 
    VARIABLES {
        falconLiteAlarmId,
        falconLiteAlarmDescr,
        falconLiteInput7OffLabel
    }
    DESCRIPTION
        "The sensor on port #07 has returned to normal."
    ::= 7

falconLitePort08TrapClear TRAP-TYPE
    ENTERPRISE   falconLitePortTrapClear 
    VARIABLES {
        falconLiteAlarmId,
        falconLiteAlarmDescr,
        falconLiteInput8OffLabel
    }
    DESCRIPTION
        "The sensor on port #08 has returned to normal."
    ::= 8

--
-- The falconLite Extension
--
        falconLite8 OBJECT IDENTIFIER ::= { falconLite 2 }

END
