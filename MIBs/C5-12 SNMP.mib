--
-- CAREL-dencoccu.MIB
-- MIB generated by CAREL
-- Thursday, 15 August 2013
--

    CAREL-dencoccu-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI
			DisplayString
				FROM SNMPv2-TC;
		
        dencoccuMIB MODULE-IDENTITY
      		LAST-UPDATED  "201308151024Z"		-- August 15, 2013 at 10:24 GMT
      		ORGANIZATION  "CAREL Industries S.r.l."
      		CONTACT-INFO
                "
                        Carel Industries S.r.l.
                        Via dell'Industria, 11
                        35020 Brugine (PD) Italy
                        Tel: +39 049 9716611
                        E-mail: carel@carel.com
                "
      		DESCRIPTION
                "This is the MIB module for the dencoccu device."
			REVISION "201308151024Z"
			DESCRIPTION
				"version4pCOweb"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { dencoccuMIB 1 }

        -- 1.3.6.1.4.1.9839.2.1.1.1
        bms-on-off OBJECT-TYPE
                    SYNTAX Integer32 (0..1)
                    UNITS "N/A"
                    MAX-ACCESS read-write
                    STATUS current
                    DESCRIPTION "BMS Unit On/Off"
                    DEFVAL { 0 }
                    ::= { digitalObjects 1 }

        -- 1.3.6.1.4.1.9839.2.1.1.2
        reset-alarms-bms OBJECT-TYPE
                    SYNTAX Integer32 (0..1)
                    UNITS "N/A"
                    MAX-ACCESS read-write
                    STATUS current
                    DESCRIPTION "Alarm Reset By BMS"
                    DEFVAL { 0 }
                    ::= { digitalObjects 2 }

        -- 1.3.6.1.4.1.9839.2.1.1.3
        mal-return-air-temp OBJECT-TYPE
                    SYNTAX Integer32 (0..1)
                    UNITS "N/A"
                    MAX-ACCESS read-only
                    STATUS current
                    DESCRIPTION "Return Air Temperature Sensor Fail Alarm"
                    DEFVAL { 0 }
                    ::= { digitalObjects 3 }

        -- 1.3.6.1.4.1.9839.2.1.1.4
        mal-return-air-hum OBJECT-TYPE
                    SYNTAX Integer32 (0..1)
                    UNITS "N/A"
                    MAX-ACCESS read-only
                    STATUS current
                    DESCRIPTION "Return Air Humidity Sensor Fail Alarm"
                    DEFVAL { 0 }
                    ::= { digitalObjects 4 }

        -- 1.3.6.1.4.1.9839.2.1.1.5
        mal-supply-air-temp OBJECT-TYPE
                    SYNTAX Integer32 (0..1)
                    UNITS "N/A"
                    MAX-ACCESS read-only
                    STATUS current
                    DESCRIPTION "Supply Air Temperature Sensor Fail Alarm"
                    DEFVAL { 0 }
                    ::= { digitalObjects 5 }

        -- 1.3.6.1.4.1.9839.2.1.1.6
        mal-supply-air-hum OBJECT-TYPE
                    SYNTAX Integer32 (0..1)
                    UNITS "N/A"
                    MAX-ACCESS read-only
                    STATUS current
                    DESCRIPTION "Supply Air Humidity Sensor Fail Alarm"
                    DEFVAL { 0 }
                    ::= { digitalObjects 6 }

        -- 1.3.6.1.4.1.9839.2.1.1.7
        mal-cw-inlet OBJECT-TYPE
                    SYNTAX Integer32 (0..1)
                    UNITS "N/A"
                    MAX-ACCESS read-only
                    STATUS current
                    DESCRIPTION "Water Temperature Sensor Fail Alarm"
                    DEFVAL { 0 }
                    ::= { digitalObjects 7 }

        -- 1.3.6.1.4.1.9839.2.1.1.8
        mal-cw-outlet OBJECT-TYPE
                    SYNTAX Integer32 (0..1)
                    UNITS "N/A"
                    MAX-ACCESS read-only
                    STATUS current
                    DESCRIPTION "Water Temperature Sensor Fail Alarm"
                    DEFVAL { 0 }
                    ::= { digitalObjects 8 }

        -- 1.3.6.1.4.1.9839.2.1.1.9
        mal-disch-press OBJECT-TYPE
                    SYNTAX Integer32 (0..1)
                    UNITS "N/A"
                    MAX-ACCESS read-only
                    STATUS current
                    DESCRIPTION "Discharge pressure sensor fail alarm"
                    DEFVAL { 0 }
                    ::= { digitalObjects 9 }

        -- 1.3.6.1.4.1.9839.2.1.1.10
        mal-disch-temp OBJECT-TYPE
                    SYNTAX Integer32 (0..1)
                    UNITS "N/A"
                    MAX-ACCESS read-only
                    STATUS current
                    DESCRIPTION "Discharge temperature sensor fail alarm"
                    DEFVAL { 0 }
                    ::= { digitalObjects 10 }

        -- 1.3.6.1.4.1.9839.2.1.1.11
        mal-airflow-press-diff OBJECT-TYPE
                    SYNTAX Integer32 (0..1)
                    UNITS "N/A"
                    MAX-ACCESS read-only
                    STATUS current
                    DESCRIPTION "Airflow Fail Alarm"
                    DEFVAL { 0 }
                    ::= { digitalObjects 11 }

        -- 1.3.6.1.4.1.9839.2.1.1.12
        mal-aps-press-trasducer OBJECT-TYPE
                    SYNTAX Integer32 (0..1)
                    UNITS "N/A"
                    MAX-ACCESS read-only
                    STATUS current
                    DESCRIPTION "N/A"
                    DEFVAL { 0 }
                    ::= { digitalObjects 12 }

        -- 1.3.6.1.4.1.9839.2.1.1.13
        mal-amb-temp OBJECT-TYPE
                    SYNTAX Integer32 (0..1)
                    UNITS "N/A"
                    MAX-ACCESS read-only
                    STATUS current
                    DESCRIPTION "N/A"
                    DEFVAL { 0 }
                    ::= { digitalObjects 13 }

        -- 1.3.6.1.4.1.9839.2.1.1.14
        mal-airflow-fail OBJECT-TYPE
                    SYNTAX Integer32 (0..1)
                    UNITS "N/A"
                    MAX-ACCESS read-only
                    STATUS current
                    DESCRIPTION "Airflow Fail Alarm"
                    DEFVAL { 0 }
                    ::= { digitalObjects 14 }

        -- 1.3.6.1.4.1.9839.2.1.1.15
        mal-filter-blocked OBJECT-TYPE
                    SYNTAX Integer32 (0..1)
                    UNITS "N/A"
                    MAX-ACCESS read-only
                    STATUS current
                    DESCRIPTION "Filter Blocked Alarm"
                    DEFVAL { 0 }
                    ::= { digitalObjects 15 }

        -- 1.3.6.1.4.1.9839.2.1.1.16
        mal-water-detection OBJECT-TYPE
                    SYNTAX Integer32 (0..1)
                    UNITS "N/A"
                    MAX-ACCESS read-only
                    STATUS current
                    DESCRIPTION "Water Detection Alarm"
                    DEFVAL { 0 }
                    ::= { digitalObjects 16 }

        -- 1.3.6.1.4.1.9839.2.1.1.17
        mal-auxiliary-alarm-1 OBJECT-TYPE
                    SYNTAX Integer32 (0..1)
                    UNITS "N/A"
                    MAX-ACCESS read-only
                    STATUS current
                    DESCRIPTION "Auxiliary Alarm 1"
                    DEFVAL { 0 }
                    ::= { digitalObjects 17 }

        -- 1.3.6.1.4.1.9839.2.1.1.18
        mal-auxiliary-alarm-2 OBJECT-TYPE
                    SYNTAX Integer32 (0..1)
                    UNITS "N/A"
                    MAX-ACCESS read-only
                    STATUS current
                    DESCRIPTION "Auxiliary Alarm 2"
                    DEFVAL { 0 }
                    ::= { digitalObjects 18 }

        -- 1.3.6.1.4.1.9839.2.1.1.19
        al-high-control-temp OBJECT-TYPE
                    SYNTAX Integer32 (0..1)
                    UNITS "N/A"
                    MAX-ACCESS read-only
                    STATUS current
                    DESCRIPTION "N/A"
                    DEFVAL { 0 }
                    ::= { digitalObjects 19 }

        -- 1.3.6.1.4.1.9839.2.1.1.20
        al-low-control-temp OBJECT-TYPE
                    SYNTAX Integer32 (0..1)
                    UNITS "N/A"
                    MAX-ACCESS read-write
                    STATUS current
                    DESCRIPTION "N/A"
                    DEFVAL { 0 }
                    ::= { digitalObjects 20 }

        -- 1.3.6.1.4.1.9839.2.1.1.21
        al-high-control-hum OBJECT-TYPE
                    SYNTAX Integer32 (0..1)
                    UNITS "N/A"
                    MAX-ACCESS read-only
                    STATUS current
                    DESCRIPTION "N/A"
                    DEFVAL { 0 }
                    ::= { digitalObjects 21 }

        -- 1.3.6.1.4.1.9839.2.1.1.22
        al-low-control-hum OBJECT-TYPE
                    SYNTAX Integer32 (0..1)
                    UNITS "N/A"
                    MAX-ACCESS read-write
                    STATUS current
                    DESCRIPTION "N/A"
                    DEFVAL { 0 }
                    ::= { digitalObjects 22 }

        -- 1.3.6.1.4.1.9839.2.1.1.23
        mal-low-supply-air-temp OBJECT-TYPE
                    SYNTAX Integer32 (0..1)
                    UNITS "N/A"
                    MAX-ACCESS read-only
                    STATUS current
                    DESCRIPTION "Low Supply Temperature Alarm"
                    DEFVAL { 0 }
                    ::= { digitalObjects 23 }

        -- 1.3.6.1.4.1.9839.2.1.1.24
        mal-high-supply-air-hum OBJECT-TYPE
                    SYNTAX Integer32 (0..1)
                    UNITS "N/A"
                    MAX-ACCESS read-only
                    STATUS current
                    DESCRIPTION "High Supply Humidity Alarm"
                    DEFVAL { 0 }
                    ::= { digitalObjects 24 }

        -- 1.3.6.1.4.1.9839.2.1.1.25
        mal-heater-over-temp OBJECT-TYPE
                    SYNTAX Integer32 (0..1)
                    UNITS "N/A"
                    MAX-ACCESS read-only
                    STATUS current
                    DESCRIPTION "Heater Over Temp Alarm"
                    DEFVAL { 0 }
                    ::= { digitalObjects 25 }

        -- 1.3.6.1.4.1.9839.2.1.1.26
        mal-ref-leak-detection OBJECT-TYPE
                    SYNTAX Integer32 (0..1)
                    UNITS "N/A"
                    MAX-ACCESS read-only
                    STATUS current
                    DESCRIPTION "Refrigerant Leak Detection Alarm"
                    DEFVAL { 0 }
                    ::= { digitalObjects 26 }

        -- 1.3.6.1.4.1.9839.2.1.1.27
        mal-sump-pump-failure OBJECT-TYPE
                    SYNTAX Integer32 (0..1)
                    UNITS "N/A"
                    MAX-ACCESS read-only
                    STATUS current
                    DESCRIPTION "N/A"
                    DEFVAL { 0 }
                    ::= { digitalObjects 27 }

        -- 1.3.6.1.4.1.9839.2.1.1.28
        mal-plan OBJECT-TYPE
                    SYNTAX Integer32 (0..1)
                    UNITS "N/A"
                    MAX-ACCESS read-only
                    STATUS current
                    DESCRIPTION "Denconet Comms Alarm"
                    DEFVAL { 0 }
                    ::= { digitalObjects 28 }

        -- 1.3.6.1.4.1.9839.2.1.1.29
        mal-clock OBJECT-TYPE
                    SYNTAX Integer32 (0..1)
                    UNITS "N/A"
                    MAX-ACCESS read-only
                    STATUS current
                    DESCRIPTION "Clock Alarm"
                    DEFVAL { 0 }
                    ::= { digitalObjects 29 }

        -- 1.3.6.1.4.1.9839.2.1.1.30
        crit-al-active OBJECT-TYPE
                    SYNTAX Integer32 (0..1)
                    UNITS "N/A"
                    MAX-ACCESS read-only
                    STATUS current
                    DESCRIPTION "Critical Alarm Status"
                    DEFVAL { 0 }
                    ::= { digitalObjects 30 }

        -- 1.3.6.1.4.1.9839.2.1.1.31
        maint-al-active OBJECT-TYPE
                    SYNTAX Integer32 (0..1)
                    UNITS "N/A"
                    MAX-ACCESS read-only
                    STATUS current
                    DESCRIPTION "Maintenance Alarm Status"
                    DEFVAL { 0 }
                    ::= { digitalObjects 31 }

        -- 1.3.6.1.4.1.9839.2.1.1.32
        syson OBJECT-TYPE
                    SYNTAX Integer32 (0..1)
                    UNITS "N/A"
                    MAX-ACCESS read-only
                    STATUS current
                    DESCRIPTION "N/A"
                    DEFVAL { 0 }
                    ::= { digitalObjects 32 }

        -- 1.3.6.1.4.1.9839.2.1.1.33
        alarm-comp1 OBJECT-TYPE
                    SYNTAX Integer32 (0..1)
                    UNITS "N/A"
                    MAX-ACCESS read-write
                    STATUS current
                    DESCRIPTION "N/A"
                    DEFVAL { 0 }
                    ::= { digitalObjects 33 }

        -- 1.3.6.1.4.1.9839.2.1.1.34
        alarm-comp2 OBJECT-TYPE
                    SYNTAX Integer32 (0..1)
                    UNITS "N/A"
                    MAX-ACCESS read-write
                    STATUS current
                    DESCRIPTION "N/A"
                    DEFVAL { 0 }
                    ::= { digitalObjects 34 }

        -- 1.3.6.1.4.1.9839.2.1.1.35
        evd-alarms OBJECT-TYPE
                    SYNTAX Integer32 (0..1)
                    UNITS "N/A"
                    MAX-ACCESS read-only
                    STATUS current
                    DESCRIPTION "N/A"
                    DEFVAL { 0 }
                    ::= { digitalObjects 35 }

        -- 1.3.6.1.4.1.9839.2.1.1.36
        cpy-alarms OBJECT-TYPE
                    SYNTAX Integer32 (0..1)
                    UNITS "N/A"
                    MAX-ACCESS read-only
                    STATUS current
                    DESCRIPTION "N/A"
                    DEFVAL { 0 }
                    ::= { digitalObjects 36 }

        -- 1.3.6.1.4.1.9839.2.1.1.37
        energy-meter-alarms OBJECT-TYPE
                    SYNTAX Integer32 (0..1)
                    UNITS "N/A"
                    MAX-ACCESS read-only
                    STATUS current
                    DESCRIPTION "N/A"
                    DEFVAL { 0 }
                    ::= { digitalObjects 37 }

        -- 1.3.6.1.4.1.9839.2.1.1.38
        pco-global-alarm OBJECT-TYPE
                    SYNTAX Integer32 (0..1)
                    UNITS "N/A"
                    MAX-ACCESS read-only
                    STATUS current
                    DESCRIPTION "N/A"
                    DEFVAL { 0 }
                    ::= { digitalObjects 38 }

        -- 1.3.6.1.4.1.9839.2.1.1.39
        al-offline-pcoe OBJECT-TYPE
                    SYNTAX Integer32 (0..1)
                    UNITS "N/A"
                    MAX-ACCESS read-only
                    STATUS current
                    DESCRIPTION "Alarm offline of pCOe"
                    DEFVAL { 0 }
                    ::= { digitalObjects 39 }

        -- 1.3.6.1.4.1.9839.2.1.1.40
        data-written-pwrp-2 OBJECT-TYPE
                    SYNTAX Integer32 (0..1)
                    UNITS "N/A"
                    MAX-ACCESS read-write
                    STATUS current
                    DESCRIPTION "PowerPlus configuration done"
                    DEFVAL { 0 }
                    ::= { digitalObjects 40 }

        -- 1.3.6.1.4.1.9839.2.1.1.41
        model-error-pwrp-2 OBJECT-TYPE
                    SYNTAX Integer32 (0..1)
                    UNITS "N/A"
                    MAX-ACCESS read-only
                    STATUS current
                    DESCRIPTION "Inverter model not compatible with selected compressor"
                    DEFVAL { 0 }
                    ::= { digitalObjects 41 }

        -- 1.3.6.1.4.1.9839.2.1.1.44
        model-error-pwrp-1 OBJECT-TYPE
                    SYNTAX Integer32 (0..1)
                    UNITS "N/A"
                    MAX-ACCESS read-only
                    STATUS current
                    DESCRIPTION "Inverter model not compatible with selected compressor"
                    DEFVAL { 0 }
                    ::= { digitalObjects 44 }

        -- 1.3.6.1.4.1.9839.2.1.1.99
        data-written-pwrp-1 OBJECT-TYPE
                    SYNTAX Integer32 (0..1)
                    UNITS "N/A"
                    MAX-ACCESS read-write
                    STATUS current
                    DESCRIPTION "PowerPlus configuration done"
                    DEFVAL { 0 }
                    ::= { digitalObjects 99 }

        -- 1.3.6.1.4.1.9839.2.1.1.301
        on-off-timezones OBJECT-TYPE
                    SYNTAX Integer32 (0..1)
                    UNITS "N/A"
                    MAX-ACCESS read-write
                    STATUS current
                    DESCRIPTION "Enable Unit On/Off by Time zones"
                    DEFVAL { 0 }
                    ::= { digitalObjects 301 }

        -- 1.3.6.1.4.1.9839.2.1.1.302
        en-time-zones-t OBJECT-TYPE
                    SYNTAX Integer32 (0..1)
                    UNITS "N/A"
                    MAX-ACCESS read-write
                    STATUS current
                    DESCRIPTION "Enable Unit Temperature Set Point Adjustment by Time zones"
                    DEFVAL { 0 }
                    ::= { digitalObjects 302 }

        -- 1.3.6.1.4.1.9839.2.1.1.303
        en-time-zones-h OBJECT-TYPE
                    SYNTAX Integer32 (0..1)
                    UNITS "N/A"
                    MAX-ACCESS read-write
                    STATUS current
                    DESCRIPTION "Enable Unit Humidity Set Point Adjustment by Time zones"
                    DEFVAL { 0 }
                    ::= { digitalObjects 303 }

        -- 1.3.6.1.4.1.9839.2.1.1.304
        al-hp-limit-circ OBJECT-TYPE
                    SYNTAX Integer32 (0..1)
                    UNITS "N/A"
                    MAX-ACCESS read-only
                    STATUS current
                    DESCRIPTION "N/A"
                    DEFVAL { 0 }
                    ::= { digitalObjects 304 }

        -- 1.3.6.1.4.1.9839.2.1.1.305
        al-lp-limit-circ OBJECT-TYPE
                    SYNTAX Integer32 (0..1)
                    UNITS "N/A"
                    MAX-ACCESS read-only
                    STATUS current
                    DESCRIPTION "N/A"
                    DEFVAL { 0 }
                    ::= { digitalObjects 305 }

        -- 1.3.6.1.4.1.9839.2.1.1.306
        mal-bms-offline OBJECT-TYPE
                    SYNTAX Integer32 (0..1)
                    UNITS "N/A"
                    MAX-ACCESS read-only
                    STATUS current
                    DESCRIPTION "Result of the operation"
                    DEFVAL { 0 }
                    ::= { digitalObjects 306 }

        -- 1.3.6.1.4.1.9839.2.1.1.307
        mal-offline-pcoe OBJECT-TYPE
                    SYNTAX Integer32 (0..1)
                    UNITS "N/A"
                    MAX-ACCESS read-only
                    STATUS current
                    DESCRIPTION "Alarm offline of pCOe"
                    DEFVAL { 0 }
                    ::= { digitalObjects 307 }

        -- 1.3.6.1.4.1.9839.2.1.1.308
        mal-control-temp OBJECT-TYPE
                    SYNTAX Integer32 (0..1)
                    UNITS "N/A"
                    MAX-ACCESS read-only
                    STATUS current
                    DESCRIPTION "N/A"
                    DEFVAL { 0 }
                    ::= { digitalObjects 308 }

        -- 1.3.6.1.4.1.9839.2.1.1.309
        mal-control-temp-al-u1 OBJECT-TYPE
                    SYNTAX Integer32 (0..1)
                    UNITS "N/A"
                    MAX-ACCESS read-only
                    STATUS current
                    DESCRIPTION "N/A"
                    DEFVAL { 0 }
                    ::= { digitalObjects 309 }

        -- 1.3.6.1.4.1.9839.2.1.1.310
        mal-control-temp-al-u2 OBJECT-TYPE
                    SYNTAX Integer32 (0..1)
                    UNITS "N/A"
                    MAX-ACCESS read-only
                    STATUS current
                    DESCRIPTION "N/A"
                    DEFVAL { 0 }
                    ::= { digitalObjects 310 }

        -- 1.3.6.1.4.1.9839.2.1.1.311
        mal-control-temp-al-u3 OBJECT-TYPE
                    SYNTAX Integer32 (0..1)
                    UNITS "N/A"
                    MAX-ACCESS read-only
                    STATUS current
                    DESCRIPTION "N/A"
                    DEFVAL { 0 }
                    ::= { digitalObjects 311 }

        -- 1.3.6.1.4.1.9839.2.1.1.312
        mal-control-temp-al-u4 OBJECT-TYPE
                    SYNTAX Integer32 (0..1)
                    UNITS "N/A"
                    MAX-ACCESS read-only
                    STATUS current
                    DESCRIPTION "N/A"
                    DEFVAL { 0 }
                    ::= { digitalObjects 312 }

        -- 1.3.6.1.4.1.9839.2.1.1.313
        mal-control-temp-al-u5 OBJECT-TYPE
                    SYNTAX Integer32 (0..1)
                    UNITS "N/A"
                    MAX-ACCESS read-only
                    STATUS current
                    DESCRIPTION "N/A"
                    DEFVAL { 0 }
                    ::= { digitalObjects 313 }

        -- 1.3.6.1.4.1.9839.2.1.1.314
        mal-control-temp-al-u6 OBJECT-TYPE
                    SYNTAX Integer32 (0..1)
                    UNITS "N/A"
                    MAX-ACCESS read-only
                    STATUS current
                    DESCRIPTION "N/A"
                    DEFVAL { 0 }
                    ::= { digitalObjects 314 }

        -- 1.3.6.1.4.1.9839.2.1.1.315
        mal-control-temp-al-u7 OBJECT-TYPE
                    SYNTAX Integer32 (0..1)
                    UNITS "N/A"
                    MAX-ACCESS read-only
                    STATUS current
                    DESCRIPTION "N/A"
                    DEFVAL { 0 }
                    ::= { digitalObjects 315 }

        -- 1.3.6.1.4.1.9839.2.1.1.316
        mal-control-temp-al-u8 OBJECT-TYPE
                    SYNTAX Integer32 (0..1)
                    UNITS "N/A"
                    MAX-ACCESS read-only
                    STATUS current
                    DESCRIPTION "N/A"
                    DEFVAL { 0 }
                    ::= { digitalObjects 316 }

        -- 1.3.6.1.4.1.9839.2.1.1.317
        mal-control-hum OBJECT-TYPE
                    SYNTAX Integer32 (0..1)
                    UNITS "N/A"
                    MAX-ACCESS read-only
                    STATUS current
                    DESCRIPTION "N/A"
                    DEFVAL { 0 }
                    ::= { digitalObjects 317 }

        -- 1.3.6.1.4.1.9839.2.1.1.318
        mal-control-hum-al-u1 OBJECT-TYPE
                    SYNTAX Integer32 (0..1)
                    UNITS "N/A"
                    MAX-ACCESS read-only
                    STATUS current
                    DESCRIPTION "N/A"
                    DEFVAL { 0 }
                    ::= { digitalObjects 318 }

        -- 1.3.6.1.4.1.9839.2.1.1.319
        mal-control-hum-al-u2 OBJECT-TYPE
                    SYNTAX Integer32 (0..1)
                    UNITS "N/A"
                    MAX-ACCESS read-only
                    STATUS current
                    DESCRIPTION "N/A"
                    DEFVAL { 0 }
                    ::= { digitalObjects 319 }

        -- 1.3.6.1.4.1.9839.2.1.1.320
        mal-control-hum-al-u3 OBJECT-TYPE
                    SYNTAX Integer32 (0..1)
                    UNITS "N/A"
                    MAX-ACCESS read-only
                    STATUS current
                    DESCRIPTION "N/A"
                    DEFVAL { 0 }
                    ::= { digitalObjects 320 }

        -- 1.3.6.1.4.1.9839.2.1.1.321
        mal-control-hum-al-u4 OBJECT-TYPE
                    SYNTAX Integer32 (0..1)
                    UNITS "N/A"
                    MAX-ACCESS read-only
                    STATUS current
                    DESCRIPTION "N/A"
                    DEFVAL { 0 }
                    ::= { digitalObjects 321 }

        -- 1.3.6.1.4.1.9839.2.1.1.322
        mal-control-hum-al-u5 OBJECT-TYPE
                    SYNTAX Integer32 (0..1)
                    UNITS "N/A"
                    MAX-ACCESS read-only
                    STATUS current
                    DESCRIPTION "N/A"
                    DEFVAL { 0 }
                    ::= { digitalObjects 322 }

        -- 1.3.6.1.4.1.9839.2.1.1.323
        ma-control-hum-al-u6 OBJECT-TYPE
                    SYNTAX Integer32 (0..1)
                    UNITS "N/A"
                    MAX-ACCESS read-only
                    STATUS current
                    DESCRIPTION "N/A"
                    DEFVAL { 0 }
                    ::= { digitalObjects 323 }

        -- 1.3.6.1.4.1.9839.2.1.1.324
        ma-control-hum-al-u7 OBJECT-TYPE
                    SYNTAX Integer32 (0..1)
                    UNITS "N/A"
                    MAX-ACCESS read-only
                    STATUS current
                    DESCRIPTION "N/A"
                    DEFVAL { 0 }
                    ::= { digitalObjects 324 }

        -- 1.3.6.1.4.1.9839.2.1.1.325
        mal-control-hum-al-u8 OBJECT-TYPE
                    SYNTAX Integer32 (0..1)
                    UNITS "N/A"
                    MAX-ACCESS read-only
                    STATUS current
                    DESCRIPTION "N/A"
                    DEFVAL { 0 }
                    ::= { digitalObjects 325 }

        -- 1.3.6.1.4.1.9839.2.1.1.326
        vk-end-default OBJECT-TYPE
                    SYNTAX Integer32 (0..1)
                    UNITS "N/A"
                    MAX-ACCESS read-only
                    STATUS current
                    DESCRIPTION "N/A"
                    DEFVAL { 0 }
                    ::= { digitalObjects 326 }

        -- 1.3.6.1.4.1.9839.2.1.1.327
        night-puge OBJECT-TYPE
                    SYNTAX Integer32 (0..1)
                    UNITS "N/A"
                    MAX-ACCESS read-write
                    STATUS current
                    DESCRIPTION "Unit Night Purge (Only Unit Fan Output Energises)"
                    DEFVAL { 0 }
                    ::= { digitalObjects 327 }

        -- 1.3.6.1.4.1.9839.2.1.1.328
        critical-alarm OBJECT-TYPE
                    SYNTAX Integer32 (0..1)
                    UNITS "N/A"
                    MAX-ACCESS read-only
                    STATUS current
                    DESCRIPTION "N/A"
                    DEFVAL { 0 }
                    ::= { digitalObjects 328 }

        -- 1.3.6.1.4.1.9839.2.1.1.329
        maintenance-alarm OBJECT-TYPE
                    SYNTAX Integer32 (0..1)
                    UNITS "N/A"
                    MAX-ACCESS read-only
                    STATUS current
                    DESCRIPTION "N/A"
                    DEFVAL { 0 }
                    ::= { digitalObjects 329 }

        -- 1.3.6.1.4.1.9839.2.1.1.330
        bms-ef-1 OBJECT-TYPE
                    SYNTAX Integer32 (0..1)
                    UNITS "N/A"
                    MAX-ACCESS read-write
                    STATUS current
                    DESCRIPTION "LECU 1 BMS On/Off"
                    DEFVAL { 0 }
                    ::= { digitalObjects 330 }

        -- 1.3.6.1.4.1.9839.2.1.1.331
        damper-ef-1 OBJECT-TYPE
                    SYNTAX Integer32 (0..1)
                    UNITS "N/A"
                    MAX-ACCESS read-only
                    STATUS current
                    DESCRIPTION "LECU 1 Damper (0 =Auto; 1=100%OPEN)"
                    DEFVAL { 0 }
                    ::= { digitalObjects 331 }

        -- 1.3.6.1.4.1.9839.2.1.1.332
        bms-ef-2 OBJECT-TYPE
                    SYNTAX Integer32 (0..1)
                    UNITS "N/A"
                    MAX-ACCESS read-write
                    STATUS current
                    DESCRIPTION "LECU 2 BMS On/Off"
                    DEFVAL { 0 }
                    ::= { digitalObjects 332 }

        -- 1.3.6.1.4.1.9839.2.1.1.333
        damper-ef-2 OBJECT-TYPE
                    SYNTAX Integer32 (0..1)
                    UNITS "N/A"
                    MAX-ACCESS read-only
                    STATUS current
                    DESCRIPTION "LECU 2 Damper (0 =Auto; 1=100%OPEN)"
                    DEFVAL { 0 }
                    ::= { digitalObjects 333 }

        -- 1.3.6.1.4.1.9839.2.1.1.334
        bms-ef-3 OBJECT-TYPE
                    SYNTAX Integer32 (0..1)
                    UNITS "N/A"
                    MAX-ACCESS read-write
                    STATUS current
                    DESCRIPTION "LECU 3 BMS On/Off"
                    DEFVAL { 0 }
                    ::= { digitalObjects 334 }

        -- 1.3.6.1.4.1.9839.2.1.1.335
        damper-ef-3 OBJECT-TYPE
                    SYNTAX Integer32 (0..1)
                    UNITS "N/A"
                    MAX-ACCESS read-only
                    STATUS current
                    DESCRIPTION "LECU 3 Damper (0 =Auto; 1=100%OPEN)"
                    DEFVAL { 0 }
                    ::= { digitalObjects 335 }

        -- 1.3.6.1.4.1.9839.2.1.1.336
        bms-ef-4 OBJECT-TYPE
                    SYNTAX Integer32 (0..1)
                    UNITS "N/A"
                    MAX-ACCESS read-write
                    STATUS current
                    DESCRIPTION "LECU 4 BMS On/Off"
                    DEFVAL { 0 }
                    ::= { digitalObjects 336 }

        -- 1.3.6.1.4.1.9839.2.1.1.337
        damper-ef-4 OBJECT-TYPE
                    SYNTAX Integer32 (0..1)
                    UNITS "N/A"
                    MAX-ACCESS read-only
                    STATUS current
                    DESCRIPTION "LECU 4 Damper (0 =Auto; 1=100%OPEN)"
                    DEFVAL { 0 }
                    ::= { digitalObjects 337 }

        -- 1.3.6.1.4.1.9839.2.1.1.338
        bms-ef-5 OBJECT-TYPE
                    SYNTAX Integer32 (0..1)
                    UNITS "N/A"
                    MAX-ACCESS read-write
                    STATUS current
                    DESCRIPTION "LECU 5 BMS On/Off"
                    DEFVAL { 0 }
                    ::= { digitalObjects 338 }

        -- 1.3.6.1.4.1.9839.2.1.1.339
        damper-ef-5 OBJECT-TYPE
                    SYNTAX Integer32 (0..1)
                    UNITS "N/A"
                    MAX-ACCESS read-only
                    STATUS current
                    DESCRIPTION "LECU 5 Damper (0 =Auto; 1=100%OPEN)"
                    DEFVAL { 0 }
                    ::= { digitalObjects 339 }

        -- 1.3.6.1.4.1.9839.2.1.1.340
        bms-ef-6 OBJECT-TYPE
                    SYNTAX Integer32 (0..1)
                    UNITS "N/A"
                    MAX-ACCESS read-write
                    STATUS current
                    DESCRIPTION "LECU 6 BMS On/Off"
                    DEFVAL { 0 }
                    ::= { digitalObjects 340 }

        -- 1.3.6.1.4.1.9839.2.1.1.341
        damper-ef-6 OBJECT-TYPE
                    SYNTAX Integer32 (0..1)
                    UNITS "N/A"
                    MAX-ACCESS read-only
                    STATUS current
                    DESCRIPTION "LECU 6 Damper (0 =Auto; 1=100%OPEN)"
                    DEFVAL { 0 }
                    ::= { digitalObjects 341 }

        -- 1.3.6.1.4.1.9839.2.1.1.342
        bms-ef-7 OBJECT-TYPE
                    SYNTAX Integer32 (0..1)
                    UNITS "N/A"
                    MAX-ACCESS read-write
                    STATUS current
                    DESCRIPTION "LECU 7 BMS On/Off"
                    DEFVAL { 0 }
                    ::= { digitalObjects 342 }

        -- 1.3.6.1.4.1.9839.2.1.1.343
        damper-ef-7 OBJECT-TYPE
                    SYNTAX Integer32 (0..1)
                    UNITS "N/A"
                    MAX-ACCESS read-only
                    STATUS current
                    DESCRIPTION "LECU 7 Damper (0 =Auto; 1=100%OPEN)"
                    DEFVAL { 0 }
                    ::= { digitalObjects 343 }

        -- 1.3.6.1.4.1.9839.2.1.1.344
        bms-ef-8 OBJECT-TYPE
                    SYNTAX Integer32 (0..1)
                    UNITS "N/A"
                    MAX-ACCESS read-write
                    STATUS current
                    DESCRIPTION "LECU 8 BMS On/Off"
                    DEFVAL { 0 }
                    ::= { digitalObjects 344 }

        -- 1.3.6.1.4.1.9839.2.1.1.345
        damper-ef-8 OBJECT-TYPE
                    SYNTAX Integer32 (0..1)
                    UNITS "N/A"
                    MAX-ACCESS read-only
                    STATUS current
                    DESCRIPTION "LECU 8 Damper (0 =Auto; 1=100%OPEN)"
                    DEFVAL { 0 }
                    ::= { digitalObjects 345 }

        -- 1.3.6.1.4.1.9839.2.1.1.346
        bms-ef-9 OBJECT-TYPE
                    SYNTAX Integer32 (0..1)
                    UNITS "N/A"
                    MAX-ACCESS read-write
                    STATUS current
                    DESCRIPTION "LECU 9 BMS On/Off"
                    DEFVAL { 0 }
                    ::= { digitalObjects 346 }

        -- 1.3.6.1.4.1.9839.2.1.1.347
        damper-ef-9 OBJECT-TYPE
                    SYNTAX Integer32 (0..1)
                    UNITS "N/A"
                    MAX-ACCESS read-only
                    STATUS current
                    DESCRIPTION "LECU 9 Damper (0 =Auto; 1=100%OPEN)"
                    DEFVAL { 0 }
                    ::= { digitalObjects 347 }

        -- 1.3.6.1.4.1.9839.2.1.1.348
        bms-ef-10 OBJECT-TYPE
                    SYNTAX Integer32 (0..1)
                    UNITS "N/A"
                    MAX-ACCESS read-write
                    STATUS current
                    DESCRIPTION "LECU 10 BMS On/Off"
                    DEFVAL { 0 }
                    ::= { digitalObjects 348 }

        -- 1.3.6.1.4.1.9839.2.1.1.349
        damper-ef-10 OBJECT-TYPE
                    SYNTAX Integer32 (0..1)
                    UNITS "N/A"
                    MAX-ACCESS read-only
                    STATUS current
                    DESCRIPTION "LECU 10 Damper (0 =Auto; 1=100%OPEN)"
                    DEFVAL { 0 }
                    ::= { digitalObjects 349 }

        -- 1.3.6.1.4.1.9839.2.1.1.350
        bms-ef-11 OBJECT-TYPE
                    SYNTAX Integer32 (0..1)
                    UNITS "N/A"
                    MAX-ACCESS read-write
                    STATUS current
                    DESCRIPTION "LECU 11 BMS On/Off"
                    DEFVAL { 0 }
                    ::= { digitalObjects 350 }

        -- 1.3.6.1.4.1.9839.2.1.1.351
        damper-ef-11 OBJECT-TYPE
                    SYNTAX Integer32 (0..1)
                    UNITS "N/A"
                    MAX-ACCESS read-only
                    STATUS current
                    DESCRIPTION "LECU 11 Damper (0 =Auto; 1=100%OPEN)"
                    DEFVAL { 0 }
                    ::= { digitalObjects 351 }

        -- 1.3.6.1.4.1.9839.2.1.1.352
        bms-ef-12 OBJECT-TYPE
                    SYNTAX Integer32 (0..1)
                    UNITS "N/A"
                    MAX-ACCESS read-write
                    STATUS current
                    DESCRIPTION "LECU 12 BMS On/Off"
                    DEFVAL { 0 }
                    ::= { digitalObjects 352 }

        -- 1.3.6.1.4.1.9839.2.1.1.353
        damper-ef-12 OBJECT-TYPE
                    SYNTAX Integer32 (0..1)
                    UNITS "N/A"
                    MAX-ACCESS read-only
                    STATUS current
                    DESCRIPTION "LECU 12 Damper (0 =Auto; 1=100%OPEN)"
                    DEFVAL { 0 }
                    ::= { digitalObjects 353 }

        -- 1.3.6.1.4.1.9839.2.1.1.354
        bms-ef-13 OBJECT-TYPE
                    SYNTAX Integer32 (0..1)
                    UNITS "N/A"
                    MAX-ACCESS read-write
                    STATUS current
                    DESCRIPTION "LECU 13 BMS On/Off"
                    DEFVAL { 0 }
                    ::= { digitalObjects 354 }

        -- 1.3.6.1.4.1.9839.2.1.1.355
        damper-ef-13 OBJECT-TYPE
                    SYNTAX Integer32 (0..1)
                    UNITS "N/A"
                    MAX-ACCESS read-only
                    STATUS current
                    DESCRIPTION "LECU 13 Damper (0 =Auto; 1=100%OPEN)"
                    DEFVAL { 0 }
                    ::= { digitalObjects 355 }

        -- 1.3.6.1.4.1.9839.2.1.1.356
        bms-ef-14 OBJECT-TYPE
                    SYNTAX Integer32 (0..1)
                    UNITS "N/A"
                    MAX-ACCESS read-write
                    STATUS current
                    DESCRIPTION "LECU 14 BMS On/Off"
                    DEFVAL { 0 }
                    ::= { digitalObjects 356 }

        -- 1.3.6.1.4.1.9839.2.1.1.357
        damper-ef-14 OBJECT-TYPE
                    SYNTAX Integer32 (0..1)
                    UNITS "N/A"
                    MAX-ACCESS read-only
                    STATUS current
                    DESCRIPTION "LECU 14 Damper (0 =Auto; 1=100%OPEN)"
                    DEFVAL { 0 }
                    ::= { digitalObjects 357 }

        -- 1.3.6.1.4.1.9839.2.1.1.358
        bms-ef-15 OBJECT-TYPE
                    SYNTAX Integer32 (0..1)
                    UNITS "N/A"
                    MAX-ACCESS read-write
                    STATUS current
                    DESCRIPTION "LECU 15 BMS On/Off"
                    DEFVAL { 0 }
                    ::= { digitalObjects 358 }

        -- 1.3.6.1.4.1.9839.2.1.1.359
        damper-ef-15 OBJECT-TYPE
                    SYNTAX Integer32 (0..1)
                    UNITS "N/A"
                    MAX-ACCESS read-only
                    STATUS current
                    DESCRIPTION "LECU 15 Damper (0 =Auto; 1=100%OPEN)"
                    DEFVAL { 0 }
                    ::= { digitalObjects 359 }

        -- 1.3.6.1.4.1.9839.2.1.1.360
        bms-ef-16 OBJECT-TYPE
                    SYNTAX Integer32 (0..1)
                    UNITS "N/A"
                    MAX-ACCESS read-write
                    STATUS current
                    DESCRIPTION "LECU 16 BMS On/Off"
                    DEFVAL { 0 }
                    ::= { digitalObjects 360 }

        -- 1.3.6.1.4.1.9839.2.1.1.361
        damper-ef-16 OBJECT-TYPE
                    SYNTAX Integer32 (0..1)
                    UNITS "N/A"
                    MAX-ACCESS read-only
                    STATUS current
                    DESCRIPTION "LECU 16 Damper (0 =Auto; 1=100%OPEN)"
                    DEFVAL { 0 }
                    ::= { digitalObjects 361 }

        -- 1.3.6.1.4.1.9839.2.1.1.362
        bms-ef-17 OBJECT-TYPE
                    SYNTAX Integer32 (0..1)
                    UNITS "N/A"
                    MAX-ACCESS read-write
                    STATUS current
                    DESCRIPTION "LECU 17 BMS On/Off"
                    DEFVAL { 0 }
                    ::= { digitalObjects 362 }

        -- 1.3.6.1.4.1.9839.2.1.1.363
        damper-ef-17 OBJECT-TYPE
                    SYNTAX Integer32 (0..1)
                    UNITS "N/A"
                    MAX-ACCESS read-only
                    STATUS current
                    DESCRIPTION "LECU 17 Damper (0 =Auto; 1=100%OPEN)"
                    DEFVAL { 0 }
                    ::= { digitalObjects 363 }

        -- 1.3.6.1.4.1.9839.2.1.1.364
        bms-ef-18 OBJECT-TYPE
                    SYNTAX Integer32 (0..1)
                    UNITS "N/A"
                    MAX-ACCESS read-write
                    STATUS current
                    DESCRIPTION "LECU 18 BMS On/Off"
                    DEFVAL { 0 }
                    ::= { digitalObjects 364 }

        -- 1.3.6.1.4.1.9839.2.1.1.365
        damper-ef-18 OBJECT-TYPE
                    SYNTAX Integer32 (0..1)
                    UNITS "N/A"
                    MAX-ACCESS read-only
                    STATUS current
                    DESCRIPTION "LECU 18 Damper (0 =Auto; 1=100%OPEN)"
                    DEFVAL { 0 }
                    ::= { digitalObjects 365 }

        -- 1.3.6.1.4.1.9839.2.1.1.366
        bms-ef-19 OBJECT-TYPE
                    SYNTAX Integer32 (0..1)
                    UNITS "N/A"
                    MAX-ACCESS read-write
                    STATUS current
                    DESCRIPTION "LECU 19 BMS On/Off"
                    DEFVAL { 0 }
                    ::= { digitalObjects 366 }

        -- 1.3.6.1.4.1.9839.2.1.1.367
        damper-ef-19 OBJECT-TYPE
                    SYNTAX Integer32 (0..1)
                    UNITS "N/A"
                    MAX-ACCESS read-only
                    STATUS current
                    DESCRIPTION "LECU 19 Damper (0 =Auto; 1=100%OPEN)"
                    DEFVAL { 0 }
                    ::= { digitalObjects 367 }

        -- 1.3.6.1.4.1.9839.2.1.1.368
        bms-ef-20 OBJECT-TYPE
                    SYNTAX Integer32 (0..1)
                    UNITS "N/A"
                    MAX-ACCESS read-write
                    STATUS current
                    DESCRIPTION "LECU 20 BMS On/Off"
                    DEFVAL { 0 }
                    ::= { digitalObjects 368 }

        -- 1.3.6.1.4.1.9839.2.1.1.369
        damper-ef-20 OBJECT-TYPE
                    SYNTAX Integer32 (0..1)
                    UNITS "N/A"
                    MAX-ACCESS read-only
                    STATUS current
                    DESCRIPTION "LECU 20 Damper (0 =Auto; 1=100%OPEN)"
                    DEFVAL { 0 }
                    ::= { digitalObjects 369 }

        -- 1.3.6.1.4.1.9839.2.1.1.370
        bms-ef-21 OBJECT-TYPE
                    SYNTAX Integer32 (0..1)
                    UNITS "N/A"
                    MAX-ACCESS read-write
                    STATUS current
                    DESCRIPTION "LECU 21 BMS On/Off"
                    DEFVAL { 0 }
                    ::= { digitalObjects 370 }

        -- 1.3.6.1.4.1.9839.2.1.1.371
        damper-ef-21 OBJECT-TYPE
                    SYNTAX Integer32 (0..1)
                    UNITS "N/A"
                    MAX-ACCESS read-only
                    STATUS current
                    DESCRIPTION "LECU 21 Damper (0 =Auto; 1=100%OPEN)"
                    DEFVAL { 0 }
                    ::= { digitalObjects 371 }

        -- 1.3.6.1.4.1.9839.2.1.1.372
        bms-ef-22 OBJECT-TYPE
                    SYNTAX Integer32 (0..1)
                    UNITS "N/A"
                    MAX-ACCESS read-write
                    STATUS current
                    DESCRIPTION "LECU 22 BMS On/Off"
                    DEFVAL { 0 }
                    ::= { digitalObjects 372 }

        -- 1.3.6.1.4.1.9839.2.1.1.373
        damper-ef-22 OBJECT-TYPE
                    SYNTAX Integer32 (0..1)
                    UNITS "N/A"
                    MAX-ACCESS read-only
                    STATUS current
                    DESCRIPTION "LECU 22 Damper (0 =Auto; 1=100%OPEN)"
                    DEFVAL { 0 }
                    ::= { digitalObjects 373 }

        -- 1.3.6.1.4.1.9839.2.1.1.374
        bms-ef-23 OBJECT-TYPE
                    SYNTAX Integer32 (0..1)
                    UNITS "N/A"
                    MAX-ACCESS read-write
                    STATUS current
                    DESCRIPTION "LECU 23 BMS On/Off"
                    DEFVAL { 0 }
                    ::= { digitalObjects 374 }

        -- 1.3.6.1.4.1.9839.2.1.1.375
        damper-ef-23 OBJECT-TYPE
                    SYNTAX Integer32 (0..1)
                    UNITS "N/A"
                    MAX-ACCESS read-only
                    STATUS current
                    DESCRIPTION "LECU 23 Damper (0 =Auto; 1=100%OPEN)"
                    DEFVAL { 0 }
                    ::= { digitalObjects 375 }

        -- 1.3.6.1.4.1.9839.2.1.1.376
        bms-ef-24 OBJECT-TYPE
                    SYNTAX Integer32 (0..1)
                    UNITS "N/A"
                    MAX-ACCESS read-write
                    STATUS current
                    DESCRIPTION "LECU 24 BMS On/Off"
                    DEFVAL { 0 }
                    ::= { digitalObjects 376 }

        -- 1.3.6.1.4.1.9839.2.1.1.377
        damper-ef-24 OBJECT-TYPE
                    SYNTAX Integer32 (0..1)
                    UNITS "N/A"
                    MAX-ACCESS read-only
                    STATUS current
                    DESCRIPTION "LECU 24 Damper (0 =Auto; 1=100%OPEN)"
                    DEFVAL { 0 }
                    ::= { digitalObjects 377 }

        -- 1.3.6.1.4.1.9839.2.1.1.378
        bms-ef-25 OBJECT-TYPE
                    SYNTAX Integer32 (0..1)
                    UNITS "N/A"
                    MAX-ACCESS read-write
                    STATUS current
                    DESCRIPTION "LECU 25 BMS On/Off"
                    DEFVAL { 0 }
                    ::= { digitalObjects 378 }

        -- 1.3.6.1.4.1.9839.2.1.1.379
        damper-ef-25 OBJECT-TYPE
                    SYNTAX Integer32 (0..1)
                    UNITS "N/A"
                    MAX-ACCESS read-only
                    STATUS current
                    DESCRIPTION "LECU 25 Damper (0 =Auto; 1=100%OPEN)"
                    DEFVAL { 0 }
                    ::= { digitalObjects 379 }

        -- 1.3.6.1.4.1.9839.2.1.1.380
        bms-ef-26 OBJECT-TYPE
                    SYNTAX Integer32 (0..1)
                    UNITS "N/A"
                    MAX-ACCESS read-write
                    STATUS current
                    DESCRIPTION "LECU 26 BMS On/Off"
                    DEFVAL { 0 }
                    ::= { digitalObjects 380 }

        -- 1.3.6.1.4.1.9839.2.1.1.381
        damper-ef-26 OBJECT-TYPE
                    SYNTAX Integer32 (0..1)
                    UNITS "N/A"
                    MAX-ACCESS read-only
                    STATUS current
                    DESCRIPTION "LECU 26 Damper (0 =Auto; 1=100%OPEN)"
                    DEFVAL { 0 }
                    ::= { digitalObjects 381 }

        -- 1.3.6.1.4.1.9839.2.1.1.382
        bms-ef-27 OBJECT-TYPE
                    SYNTAX Integer32 (0..1)
                    UNITS "N/A"
                    MAX-ACCESS read-write
                    STATUS current
                    DESCRIPTION "LECU 27 BMS On/Off"
                    DEFVAL { 0 }
                    ::= { digitalObjects 382 }

        -- 1.3.6.1.4.1.9839.2.1.1.383
        damper-ef-27 OBJECT-TYPE
                    SYNTAX Integer32 (0..1)
                    UNITS "N/A"
                    MAX-ACCESS read-only
                    STATUS current
                    DESCRIPTION "LECU 27 Damper (0 =Auto; 1=100%OPEN)"
                    DEFVAL { 0 }
                    ::= { digitalObjects 383 }

        -- 1.3.6.1.4.1.9839.2.1.1.384
        bms-ef-28 OBJECT-TYPE
                    SYNTAX Integer32 (0..1)
                    UNITS "N/A"
                    MAX-ACCESS read-write
                    STATUS current
                    DESCRIPTION "LECU 28 BMS On/Off"
                    DEFVAL { 0 }
                    ::= { digitalObjects 384 }

        -- 1.3.6.1.4.1.9839.2.1.1.385
        damper-ef-28 OBJECT-TYPE
                    SYNTAX Integer32 (0..1)
                    UNITS "N/A"
                    MAX-ACCESS read-only
                    STATUS current
                    DESCRIPTION "LECU 28 Damper (0 =Auto; 1=100%OPEN)"
                    DEFVAL { 0 }
                    ::= { digitalObjects 385 }

        -- 1.3.6.1.4.1.9839.2.1.1.386
        bms-ef-29 OBJECT-TYPE
                    SYNTAX Integer32 (0..1)
                    UNITS "N/A"
                    MAX-ACCESS read-write
                    STATUS current
                    DESCRIPTION "LECU 29 BMS On/Off"
                    DEFVAL { 0 }
                    ::= { digitalObjects 386 }

        -- 1.3.6.1.4.1.9839.2.1.1.387
        damper-ef-29 OBJECT-TYPE
                    SYNTAX Integer32 (0..1)
                    UNITS "N/A"
                    MAX-ACCESS read-only
                    STATUS current
                    DESCRIPTION "LECU 29 Damper (0 =Auto; 1=100%OPEN)"
                    DEFVAL { 0 }
                    ::= { digitalObjects 387 }

        -- 1.3.6.1.4.1.9839.2.1.1.388
        bms-ef-30 OBJECT-TYPE
                    SYNTAX Integer32 (0..1)
                    UNITS "N/A"
                    MAX-ACCESS read-write
                    STATUS current
                    DESCRIPTION "LECU 30 BMS On/Off"
                    DEFVAL { 0 }
                    ::= { digitalObjects 388 }

        -- 1.3.6.1.4.1.9839.2.1.1.389
        damper-ef-30 OBJECT-TYPE
                    SYNTAX Integer32 (0..1)
                    UNITS "N/A"
                    MAX-ACCESS read-only
                    STATUS current
                    DESCRIPTION "LECU 30 Damper (0 =Auto; 1=100%OPEN)"
                    DEFVAL { 0 }
                    ::= { digitalObjects 389 }

        -- 1.3.6.1.4.1.9839.2.1.1.390
        bms-ef-31 OBJECT-TYPE
                    SYNTAX Integer32 (0..1)
                    UNITS "N/A"
                    MAX-ACCESS read-write
                    STATUS current
                    DESCRIPTION "LECU 31 BMS On/Off"
                    DEFVAL { 0 }
                    ::= { digitalObjects 390 }

        -- 1.3.6.1.4.1.9839.2.1.1.391
        damper-ef-31 OBJECT-TYPE
                    SYNTAX Integer32 (0..1)
                    UNITS "N/A"
                    MAX-ACCESS read-only
                    STATUS current
                    DESCRIPTION "LECU 31 Damper (0 =Auto; 1=100%OPEN)"
                    DEFVAL { 0 }
                    ::= { digitalObjects 391 }

        -- 1.3.6.1.4.1.9839.2.1.1.392
        bms-ef-32 OBJECT-TYPE
                    SYNTAX Integer32 (0..1)
                    UNITS "N/A"
                    MAX-ACCESS read-write
                    STATUS current
                    DESCRIPTION "LECU 32 BMS On/Off"
                    DEFVAL { 0 }
                    ::= { digitalObjects 392 }

        -- 1.3.6.1.4.1.9839.2.1.1.393
        damper-ef-32 OBJECT-TYPE
                    SYNTAX Integer32 (0..1)
                    UNITS "N/A"
                    MAX-ACCESS read-only
                    STATUS current
                    DESCRIPTION "LECU 32 Damper (0 =Auto; 1=100%OPEN)"
                    DEFVAL { 0 }
                    ::= { digitalObjects 393 }

        -- 1.3.6.1.4.1.9839.2.1.1.394
        bms-ef-33 OBJECT-TYPE
                    SYNTAX Integer32 (0..1)
                    UNITS "N/A"
                    MAX-ACCESS read-write
                    STATUS current
                    DESCRIPTION "LECU 33 BMS On/Off"
                    DEFVAL { 0 }
                    ::= { digitalObjects 394 }

        -- 1.3.6.1.4.1.9839.2.1.1.395
        damper-ef-33 OBJECT-TYPE
                    SYNTAX Integer32 (0..1)
                    UNITS "N/A"
                    MAX-ACCESS read-only
                    STATUS current
                    DESCRIPTION "LECU 33 Damper (0 =Auto; 1=100%OPEN)"
                    DEFVAL { 0 }
                    ::= { digitalObjects 395 }

        -- 1.3.6.1.4.1.9839.2.1.1.396
        bms-ef-34 OBJECT-TYPE
                    SYNTAX Integer32 (0..1)
                    UNITS "N/A"
                    MAX-ACCESS read-write
                    STATUS current
                    DESCRIPTION "LECU 34 BMS On/Off"
                    DEFVAL { 0 }
                    ::= { digitalObjects 396 }

        -- 1.3.6.1.4.1.9839.2.1.1.397
        damper-ef-34 OBJECT-TYPE
                    SYNTAX Integer32 (0..1)
                    UNITS "N/A"
                    MAX-ACCESS read-only
                    STATUS current
                    DESCRIPTION "LECU 34 Damper (0 =Auto; 1=100%OPEN)"
                    DEFVAL { 0 }
                    ::= { digitalObjects 397 }

        -- 1.3.6.1.4.1.9839.2.1.1.398
        bms-ef-35 OBJECT-TYPE
                    SYNTAX Integer32 (0..1)
                    UNITS "N/A"
                    MAX-ACCESS read-write
                    STATUS current
                    DESCRIPTION "LECU 35 BMS On/Off"
                    DEFVAL { 0 }
                    ::= { digitalObjects 398 }

        -- 1.3.6.1.4.1.9839.2.1.1.399
        damper-ef-35 OBJECT-TYPE
                    SYNTAX Integer32 (0..1)
                    UNITS "N/A"
                    MAX-ACCESS read-only
                    STATUS current
                    DESCRIPTION "LECU 35 Damper (0 =Auto; 1=100%OPEN)"
                    DEFVAL { 0 }
                    ::= { digitalObjects 399 }

        -- 1.3.6.1.4.1.9839.2.1.1.400
        mal-ef-01 OBJECT-TYPE
                    SYNTAX Integer32 (0..1)
                    UNITS "N/A"
                    MAX-ACCESS read-only
                    STATUS current
                    DESCRIPTION "LECU 1 ALARM"
                    DEFVAL { 0 }
                    ::= { digitalObjects 400 }

        -- 1.3.6.1.4.1.9839.2.1.1.401
        mal-ef-02 OBJECT-TYPE
                    SYNTAX Integer32 (0..1)
                    UNITS "N/A"
                    MAX-ACCESS read-only
                    STATUS current
                    DESCRIPTION "LECU 2 ALARM"
                    DEFVAL { 0 }
                    ::= { digitalObjects 401 }

        -- 1.3.6.1.4.1.9839.2.1.1.402
        mal-ef-03 OBJECT-TYPE
                    SYNTAX Integer32 (0..1)
                    UNITS "N/A"
                    MAX-ACCESS read-only
                    STATUS current
                    DESCRIPTION "LECU 3 ALARM"
                    DEFVAL { 0 }
                    ::= { digitalObjects 402 }

        -- 1.3.6.1.4.1.9839.2.1.1.403
        mal-ef-04 OBJECT-TYPE
                    SYNTAX Integer32 (0..1)
                    UNITS "N/A"
                    MAX-ACCESS read-only
                    STATUS current
                    DESCRIPTION "LECU 4 ALARM"
                    DEFVAL { 0 }
                    ::= { digitalObjects 403 }

        -- 1.3.6.1.4.1.9839.2.1.1.404
        mal-ef-05 OBJECT-TYPE
                    SYNTAX Integer32 (0..1)
                    UNITS "N/A"
                    MAX-ACCESS read-only
                    STATUS current
                    DESCRIPTION "LECU 5 ALARM"
                    DEFVAL { 0 }
                    ::= { digitalObjects 404 }

        -- 1.3.6.1.4.1.9839.2.1.1.405
        mal-ef-06 OBJECT-TYPE
                    SYNTAX Integer32 (0..1)
                    UNITS "N/A"
                    MAX-ACCESS read-only
                    STATUS current
                    DESCRIPTION "LECU 6 ALARM"
                    DEFVAL { 0 }
                    ::= { digitalObjects 405 }

        -- 1.3.6.1.4.1.9839.2.1.1.406
        mal-ef-07 OBJECT-TYPE
                    SYNTAX Integer32 (0..1)
                    UNITS "N/A"
                    MAX-ACCESS read-only
                    STATUS current
                    DESCRIPTION "LECU 7 ALARM"
                    DEFVAL { 0 }
                    ::= { digitalObjects 406 }

        -- 1.3.6.1.4.1.9839.2.1.1.407
        mal-ef-08 OBJECT-TYPE
                    SYNTAX Integer32 (0..1)
                    UNITS "N/A"
                    MAX-ACCESS read-only
                    STATUS current
                    DESCRIPTION "LECU 8 ALARM"
                    DEFVAL { 0 }
                    ::= { digitalObjects 407 }

        -- 1.3.6.1.4.1.9839.2.1.1.408
        mal-ef-09 OBJECT-TYPE
                    SYNTAX Integer32 (0..1)
                    UNITS "N/A"
                    MAX-ACCESS read-only
                    STATUS current
                    DESCRIPTION "LECU 9 ALARM"
                    DEFVAL { 0 }
                    ::= { digitalObjects 408 }

        -- 1.3.6.1.4.1.9839.2.1.1.409
        mal-ef-10 OBJECT-TYPE
                    SYNTAX Integer32 (0..1)
                    UNITS "N/A"
                    MAX-ACCESS read-only
                    STATUS current
                    DESCRIPTION "LECU 10 ALARM"
                    DEFVAL { 0 }
                    ::= { digitalObjects 409 }

        -- 1.3.6.1.4.1.9839.2.1.1.410
        mal-ef-11 OBJECT-TYPE
                    SYNTAX Integer32 (0..1)
                    UNITS "N/A"
                    MAX-ACCESS read-only
                    STATUS current
                    DESCRIPTION "LECU 11 ALARM"
                    DEFVAL { 0 }
                    ::= { digitalObjects 410 }

        -- 1.3.6.1.4.1.9839.2.1.1.411
        mal-ef-12 OBJECT-TYPE
                    SYNTAX Integer32 (0..1)
                    UNITS "N/A"
                    MAX-ACCESS read-only
                    STATUS current
                    DESCRIPTION "LECU 12 ALARM"
                    DEFVAL { 0 }
                    ::= { digitalObjects 411 }

        -- 1.3.6.1.4.1.9839.2.1.1.412
        mal-ef-13 OBJECT-TYPE
                    SYNTAX Integer32 (0..1)
                    UNITS "N/A"
                    MAX-ACCESS read-only
                    STATUS current
                    DESCRIPTION "LECU 13 ALARM"
                    DEFVAL { 0 }
                    ::= { digitalObjects 412 }

        -- 1.3.6.1.4.1.9839.2.1.1.413
        mal-ef-14 OBJECT-TYPE
                    SYNTAX Integer32 (0..1)
                    UNITS "N/A"
                    MAX-ACCESS read-only
                    STATUS current
                    DESCRIPTION "LECU 14 ALARM"
                    DEFVAL { 0 }
                    ::= { digitalObjects 413 }

        -- 1.3.6.1.4.1.9839.2.1.1.414
        mal-ef-15 OBJECT-TYPE
                    SYNTAX Integer32 (0..1)
                    UNITS "N/A"
                    MAX-ACCESS read-only
                    STATUS current
                    DESCRIPTION "LECU 15 ALARM"
                    DEFVAL { 0 }
                    ::= { digitalObjects 414 }

        -- 1.3.6.1.4.1.9839.2.1.1.415
        mal-ef-16 OBJECT-TYPE
                    SYNTAX Integer32 (0..1)
                    UNITS "N/A"
                    MAX-ACCESS read-only
                    STATUS current
                    DESCRIPTION "LECU 16 ALARM"
                    DEFVAL { 0 }
                    ::= { digitalObjects 415 }

        -- 1.3.6.1.4.1.9839.2.1.1.416
        mal-ef-17 OBJECT-TYPE
                    SYNTAX Integer32 (0..1)
                    UNITS "N/A"
                    MAX-ACCESS read-only
                    STATUS current
                    DESCRIPTION "LECU 17 ALARM"
                    DEFVAL { 0 }
                    ::= { digitalObjects 416 }

        -- 1.3.6.1.4.1.9839.2.1.1.417
        mal-ef-18 OBJECT-TYPE
                    SYNTAX Integer32 (0..1)
                    UNITS "N/A"
                    MAX-ACCESS read-only
                    STATUS current
                    DESCRIPTION "LECU 18 ALARM"
                    DEFVAL { 0 }
                    ::= { digitalObjects 417 }

        -- 1.3.6.1.4.1.9839.2.1.1.418
        mal-ef-19 OBJECT-TYPE
                    SYNTAX Integer32 (0..1)
                    UNITS "N/A"
                    MAX-ACCESS read-only
                    STATUS current
                    DESCRIPTION "LECU 19 ALARM"
                    DEFVAL { 0 }
                    ::= { digitalObjects 418 }

        -- 1.3.6.1.4.1.9839.2.1.1.419
        mal-ef-20 OBJECT-TYPE
                    SYNTAX Integer32 (0..1)
                    UNITS "N/A"
                    MAX-ACCESS read-only
                    STATUS current
                    DESCRIPTION "LECU 20 ALARM"
                    DEFVAL { 0 }
                    ::= { digitalObjects 419 }

        -- 1.3.6.1.4.1.9839.2.1.1.420
        mal-ef-21 OBJECT-TYPE
                    SYNTAX Integer32 (0..1)
                    UNITS "N/A"
                    MAX-ACCESS read-only
                    STATUS current
                    DESCRIPTION "LECU 21 ALARM"
                    DEFVAL { 0 }
                    ::= { digitalObjects 420 }

        -- 1.3.6.1.4.1.9839.2.1.1.421
        mal-ef-22 OBJECT-TYPE
                    SYNTAX Integer32 (0..1)
                    UNITS "N/A"
                    MAX-ACCESS read-only
                    STATUS current
                    DESCRIPTION "LECU 22 ALARM"
                    DEFVAL { 0 }
                    ::= { digitalObjects 421 }

        -- 1.3.6.1.4.1.9839.2.1.1.422
        mal-ef-23 OBJECT-TYPE
                    SYNTAX Integer32 (0..1)
                    UNITS "N/A"
                    MAX-ACCESS read-only
                    STATUS current
                    DESCRIPTION "LECU 23 ALARM"
                    DEFVAL { 0 }
                    ::= { digitalObjects 422 }

        -- 1.3.6.1.4.1.9839.2.1.1.423
        mal-ef-24 OBJECT-TYPE
                    SYNTAX Integer32 (0..1)
                    UNITS "N/A"
                    MAX-ACCESS read-only
                    STATUS current
                    DESCRIPTION "LECU 24 ALARM"
                    DEFVAL { 0 }
                    ::= { digitalObjects 423 }

        -- 1.3.6.1.4.1.9839.2.1.1.424
        mal-ef-25 OBJECT-TYPE
                    SYNTAX Integer32 (0..1)
                    UNITS "N/A"
                    MAX-ACCESS read-only
                    STATUS current
                    DESCRIPTION "LECU 25 ALARM"
                    DEFVAL { 0 }
                    ::= { digitalObjects 424 }

        -- 1.3.6.1.4.1.9839.2.1.1.425
        mal-ef-26 OBJECT-TYPE
                    SYNTAX Integer32 (0..1)
                    UNITS "N/A"
                    MAX-ACCESS read-only
                    STATUS current
                    DESCRIPTION "LECU 26 ALARM"
                    DEFVAL { 0 }
                    ::= { digitalObjects 425 }

        -- 1.3.6.1.4.1.9839.2.1.1.426
        mal-ef-27 OBJECT-TYPE
                    SYNTAX Integer32 (0..1)
                    UNITS "N/A"
                    MAX-ACCESS read-only
                    STATUS current
                    DESCRIPTION "LECU 27 ALARM"
                    DEFVAL { 0 }
                    ::= { digitalObjects 426 }

        -- 1.3.6.1.4.1.9839.2.1.1.427
        mal-ef-28 OBJECT-TYPE
                    SYNTAX Integer32 (0..1)
                    UNITS "N/A"
                    MAX-ACCESS read-only
                    STATUS current
                    DESCRIPTION "LECU 28 ALARM"
                    DEFVAL { 0 }
                    ::= { digitalObjects 427 }

        -- 1.3.6.1.4.1.9839.2.1.1.428
        mal-ef-29 OBJECT-TYPE
                    SYNTAX Integer32 (0..1)
                    UNITS "N/A"
                    MAX-ACCESS read-only
                    STATUS current
                    DESCRIPTION "LECU 29 ALARM"
                    DEFVAL { 0 }
                    ::= { digitalObjects 428 }

        -- 1.3.6.1.4.1.9839.2.1.1.429
        mal-ef-30 OBJECT-TYPE
                    SYNTAX Integer32 (0..1)
                    UNITS "N/A"
                    MAX-ACCESS read-only
                    STATUS current
                    DESCRIPTION "LECU 30 ALARM"
                    DEFVAL { 0 }
                    ::= { digitalObjects 429 }

        -- 1.3.6.1.4.1.9839.2.1.1.430
        mal-ef-31 OBJECT-TYPE
                    SYNTAX Integer32 (0..1)
                    UNITS "N/A"
                    MAX-ACCESS read-only
                    STATUS current
                    DESCRIPTION "LECU 31 ALARM"
                    DEFVAL { 0 }
                    ::= { digitalObjects 430 }

        -- 1.3.6.1.4.1.9839.2.1.1.431
        mal-ef-32 OBJECT-TYPE
                    SYNTAX Integer32 (0..1)
                    UNITS "N/A"
                    MAX-ACCESS read-only
                    STATUS current
                    DESCRIPTION "LECU 32 ALARM"
                    DEFVAL { 0 }
                    ::= { digitalObjects 431 }

        -- 1.3.6.1.4.1.9839.2.1.1.432
        mal-ef-33 OBJECT-TYPE
                    SYNTAX Integer32 (0..1)
                    UNITS "N/A"
                    MAX-ACCESS read-only
                    STATUS current
                    DESCRIPTION "LECU 33 ALARM"
                    DEFVAL { 0 }
                    ::= { digitalObjects 432 }

        -- 1.3.6.1.4.1.9839.2.1.1.433
        mal-ef-34 OBJECT-TYPE
                    SYNTAX Integer32 (0..1)
                    UNITS "N/A"
                    MAX-ACCESS read-only
                    STATUS current
                    DESCRIPTION "LECU 34 ALARM"
                    DEFVAL { 0 }
                    ::= { digitalObjects 433 }

        -- 1.3.6.1.4.1.9839.2.1.1.434
        mal-ef-35 OBJECT-TYPE
                    SYNTAX Integer32 (0..1)
                    UNITS "N/A"
                    MAX-ACCESS read-only
                    STATUS current
                    DESCRIPTION "LECU 35 ALARM"
                    DEFVAL { 0 }
                    ::= { digitalObjects 434 }

        -- 1.3.6.1.4.1.9839.2.1.1.435
        aux-alarm1-critical-or-maint OBJECT-TYPE
                    SYNTAX Integer32 (0..1)
                    UNITS "N/A"
                    MAX-ACCESS read-write
                    STATUS current
                    DESCRIPTION "N/A"
                    DEFVAL { 0 }
                    ::= { digitalObjects 435 }

        -- 1.3.6.1.4.1.9839.2.1.1.436
        aux-alarm2-critical-or-maint OBJECT-TYPE
                    SYNTAX Integer32 (0..1)
                    UNITS "N/A"
                    MAX-ACCESS read-write
                    STATUS current
                    DESCRIPTION "N/A"
                    DEFVAL { 0 }
                    ::= { digitalObjects 436 }

        -- 1.3.6.1.4.1.9839.2.1.1.437
        control-type OBJECT-TYPE
                    SYNTAX Integer32 (0..1)
                    UNITS "N/A"
                    MAX-ACCESS read-write
                    STATUS current
                    DESCRIPTION "N/A"
                    DEFVAL { 0 }
                    ::= { digitalObjects 437 }

        -- 1.3.6.1.4.1.9839.2.1.1.438
        b01-rah-enable OBJECT-TYPE
                    SYNTAX Integer32 (0..1)
                    UNITS "N/A"
                    MAX-ACCESS read-write
                    STATUS current
                    DESCRIPTION "N/A"
                    DEFVAL { 0 }
                    ::= { digitalObjects 438 }

        -- 1.3.6.1.4.1.9839.2.1.1.439
        b02-rat-enable OBJECT-TYPE
                    SYNTAX Integer32 (0..1)
                    UNITS "N/A"
                    MAX-ACCESS read-write
                    STATUS current
                    DESCRIPTION "N/A"
                    DEFVAL { 0 }
                    ::= { digitalObjects 439 }

        -- 1.3.6.1.4.1.9839.2.1.1.440
        b03-sat-enable OBJECT-TYPE
                    SYNTAX Integer32 (0..1)
                    UNITS "N/A"
                    MAX-ACCESS read-write
                    STATUS current
                    DESCRIPTION "N/A"
                    DEFVAL { 0 }
                    ::= { digitalObjects 440 }

        -- 1.3.6.1.4.1.9839.2.1.1.441
        b04-cw-inlet-enable OBJECT-TYPE
                    SYNTAX Integer32 (0..1)
                    UNITS "N/A"
                    MAX-ACCESS read-write
                    STATUS current
                    DESCRIPTION "N/A"
                    DEFVAL { 0 }
                    ::= { digitalObjects 441 }

        -- 1.3.6.1.4.1.9839.2.1.1.442
        b05-cw-outlet-enable OBJECT-TYPE
                    SYNTAX Integer32 (0..1)
                    UNITS "N/A"
                    MAX-ACCESS read-write
                    STATUS current
                    DESCRIPTION "N/A"
                    DEFVAL { 0 }
                    ::= { digitalObjects 442 }

        -- 1.3.6.1.4.1.9839.2.1.1.443
        b06-disch-press-enable OBJECT-TYPE
                    SYNTAX Integer32 (0..1)
                    UNITS "N/A"
                    MAX-ACCESS read-write
                    STATUS current
                    DESCRIPTION "N/A"
                    DEFVAL { 0 }
                    ::= { digitalObjects 443 }

        -- 1.3.6.1.4.1.9839.2.1.1.444
        b07-disch-temp-enable OBJECT-TYPE
                    SYNTAX Integer32 (0..1)
                    UNITS "N/A"
                    MAX-ACCESS read-write
                    STATUS current
                    DESCRIPTION "N/A"
                    DEFVAL { 0 }
                    ::= { digitalObjects 444 }

        -- 1.3.6.1.4.1.9839.2.1.1.445
        b08-airflow-enable OBJECT-TYPE
                    SYNTAX Integer32 (0..1)
                    UNITS "N/A"
                    MAX-ACCESS read-only
                    STATUS current
                    DESCRIPTION "N/A"
                    DEFVAL { 0 }
                    ::= { digitalObjects 445 }

        -- 1.3.6.1.4.1.9839.2.1.1.446
        b08-sah-enable OBJECT-TYPE
                    SYNTAX Integer32 (0..1)
                    UNITS "N/A"
                    MAX-ACCESS read-only
                    STATUS current
                    DESCRIPTION "N/A"
                    DEFVAL { 0 }
                    ::= { digitalObjects 446 }

        -- 1.3.6.1.4.1.9839.2.1.1.447
        b101-aps-press-enable OBJECT-TYPE
                    SYNTAX Integer32 (0..1)
                    UNITS "N/A"
                    MAX-ACCESS read-write
                    STATUS current
                    DESCRIPTION "N/A"
                    DEFVAL { 0 }
                    ::= { digitalObjects 447 }

        -- 1.3.6.1.4.1.9839.2.1.1.448
        b102-amb-temp-enable OBJECT-TYPE
                    SYNTAX Integer32 (0..1)
                    UNITS "N/A"
                    MAX-ACCESS read-write
                    STATUS current
                    DESCRIPTION "N/A"
                    DEFVAL { 0 }
                    ::= { digitalObjects 448 }

        -- 1.3.6.1.4.1.9839.2.1.1.449
        compressor-off-by-eev-alarms OBJECT-TYPE
                    SYNTAX Integer32 (0..1)
                    UNITS "N/A"
                    MAX-ACCESS read-only
                    STATUS current
                    DESCRIPTION "N/A"
                    DEFVAL { 0 }
                    ::= { digitalObjects 449 }

        -- 1.3.6.1.4.1.9839.2.1.1.450
        b103-cw-feedback-enable OBJECT-TYPE
                    SYNTAX Integer32 (0..1)
                    UNITS "N/A"
                    MAX-ACCESS read-write
                    STATUS current
                    DESCRIPTION "N/A"
                    DEFVAL { 0 }
                    ::= { digitalObjects 450 }

        -- 1.3.6.1.4.1.9839.2.1.1.451
        dcra-night-setback-en OBJECT-TYPE
                    SYNTAX Integer32 (0..1)
                    UNITS "N/A"
                    MAX-ACCESS read-write
                    STATUS current
                    DESCRIPTION "N/A"
                    DEFVAL { 0 }
                    ::= { digitalObjects 451 }

        -- 1.3.6.1.4.1.9839.2.1.1.452
        enable-fan-tickover OBJECT-TYPE
                    SYNTAX Integer32 (0..1)
                    UNITS "N/A"
                    MAX-ACCESS read-write
                    STATUS current
                    DESCRIPTION "N/A"
                    DEFVAL { 0 }
                    ::= { digitalObjects 452 }

        -- 1.3.6.1.4.1.9839.2.1.1.453
        combicool-en OBJECT-TYPE
                    SYNTAX Integer32 (0..1)
                    UNITS "N/A"
                    MAX-ACCESS read-only
                    STATUS current
                    DESCRIPTION "N/A"
                    DEFVAL { 0 }
                    ::= { digitalObjects 453 }

        -- 1.3.6.1.4.1.9839.2.1.1.454
        combicool-display-primary OBJECT-TYPE
                    SYNTAX Integer32 (0..1)
                    UNITS "N/A"
                    MAX-ACCESS read-write
                    STATUS current
                    DESCRIPTION "N/A"
                    DEFVAL { 0 }
                    ::= { digitalObjects 454 }

        -- 1.3.6.1.4.1.9839.2.1.1.455
        combicool-display-secondary OBJECT-TYPE
                    SYNTAX Integer32 (0..1)
                    UNITS "N/A"
                    MAX-ACCESS read-write
                    STATUS current
                    DESCRIPTION "N/A"
                    DEFVAL { 0 }
                    ::= { digitalObjects 455 }

        -- 1.3.6.1.4.1.9839.2.1.1.456
        combicool-display-change OBJECT-TYPE
                    SYNTAX Integer32 (0..1)
                    UNITS "N/A"
                    MAX-ACCESS read-write
                    STATUS current
                    DESCRIPTION "N/A"
                    DEFVAL { 0 }
                    ::= { digitalObjects 456 }

        -- 1.3.6.1.4.1.9839.2.1.1.457
        combicool-display-temp OBJECT-TYPE
                    SYNTAX Integer32 (0..1)
                    UNITS "N/A"
                    MAX-ACCESS read-write
                    STATUS current
                    DESCRIPTION "N/A"
                    DEFVAL { 0 }
                    ::= { digitalObjects 457 }

        -- 1.3.6.1.4.1.9839.2.1.1.458
        ambicool-en OBJECT-TYPE
                    SYNTAX Integer32 (0..1)
                    UNITS "N/A"
                    MAX-ACCESS read-write
                    STATUS current
                    DESCRIPTION "N/A"
                    DEFVAL { 0 }
                    ::= { digitalObjects 458 }

        -- 1.3.6.1.4.1.9839.2.1.1.459
        ambicool-control OBJECT-TYPE
                    SYNTAX Integer32 (0..1)
                    UNITS "N/A"
                    MAX-ACCESS read-write
                    STATUS current
                    DESCRIPTION "Select ambicool control on 0 (Return Temp), 1 (Control Temperature)"
                    DEFVAL { 0 }
                    ::= { digitalObjects 459 }

        -- 1.3.6.1.4.1.9839.2.1.1.460
        reset-hr-ambicool OBJECT-TYPE
                    SYNTAX Integer32 (0..1)
                    UNITS "N/A"
                    MAX-ACCESS read-write
                    STATUS current
                    DESCRIPTION "N/A"
                    DEFVAL { 0 }
                    ::= { digitalObjects 460 }

        -- 1.3.6.1.4.1.9839.2.1.1.461
        ambicool-demand-hand-en OBJECT-TYPE
                    SYNTAX Integer32 (0..1)
                    UNITS "N/A"
                    MAX-ACCESS read-write
                    STATUS current
                    DESCRIPTION "N/A"
                    DEFVAL { 0 }
                    ::= { digitalObjects 461 }

        -- 1.3.6.1.4.1.9839.2.1.1.462
        en-comp1 OBJECT-TYPE
                    SYNTAX Integer32 (0..1)
                    UNITS "N/A"
                    MAX-ACCESS read-write
                    STATUS current
                    DESCRIPTION "N/A"
                    DEFVAL { 0 }
                    ::= { digitalObjects 462 }

        -- 1.3.6.1.4.1.9839.2.1.1.463
        en-comp2 OBJECT-TYPE
                    SYNTAX Integer32 (0..1)
                    UNITS "N/A"
                    MAX-ACCESS read-write
                    STATUS current
                    DESCRIPTION "N/A"
                    DEFVAL { 0 }
                    ::= { digitalObjects 463 }

        -- 1.3.6.1.4.1.9839.2.1.1.464
        digital-cool-en OBJECT-TYPE
                    SYNTAX Integer32 (0..1)
                    UNITS "N/A"
                    MAX-ACCESS read-only
                    STATUS current
                    DESCRIPTION "N/A"
                    DEFVAL { 0 }
                    ::= { digitalObjects 464 }

        -- 1.3.6.1.4.1.9839.2.1.1.465
        digital-heat-en OBJECT-TYPE
                    SYNTAX Integer32 (0..1)
                    UNITS "N/A"
                    MAX-ACCESS read-only
                    STATUS current
                    DESCRIPTION "N/A"
                    DEFVAL { 0 }
                    ::= { digitalObjects 465 }

        -- 1.3.6.1.4.1.9839.2.1.1.466
        model-10-18-type OBJECT-TYPE
                    SYNTAX Integer32 (0..1)
                    UNITS "N/A"
                    MAX-ACCESS read-write
                    STATUS current
                    DESCRIPTION "N/A"
                    DEFVAL { 1 }
                    ::= { digitalObjects 466 }

        -- 1.3.6.1.4.1.9839.2.1.1.467
        unit-92-comp-1 OBJECT-TYPE
                    SYNTAX Integer32 (0..1)
                    UNITS "N/A"
                    MAX-ACCESS read-write
                    STATUS current
                    DESCRIPTION "N/A"
                    DEFVAL { 0 }
                    ::= { digitalObjects 467 }

        -- 1.3.6.1.4.1.9839.2.1.1.468
        unit-92-comp-2 OBJECT-TYPE
                    SYNTAX Integer32 (0..1)
                    UNITS "N/A"
                    MAX-ACCESS read-write
                    STATUS current
                    DESCRIPTION "N/A"
                    DEFVAL { 0 }
                    ::= { digitalObjects 468 }

        -- 1.3.6.1.4.1.9839.2.1.1.469
        unit-10-comp-1-model-onoff OBJECT-TYPE
                    SYNTAX Integer32 (0..1)
                    UNITS "N/A"
                    MAX-ACCESS read-write
                    STATUS current
                    DESCRIPTION "N/A"
                    DEFVAL { 0 }
                    ::= { digitalObjects 469 }

        -- 1.3.6.1.4.1.9839.2.1.1.470
        zone-unit OBJECT-TYPE
                    SYNTAX Integer32 (0..1)
                    UNITS "N/A"
                    MAX-ACCESS read-write
                    STATUS current
                    DESCRIPTION "N/A"
                    DEFVAL { 0 }
                    ::= { digitalObjects 470 }

        -- 1.3.6.1.4.1.9839.2.1.1.471
        airflow-direction OBJECT-TYPE
                    SYNTAX Integer32 (0..1)
                    UNITS "N/A"
                    MAX-ACCESS read-write
                    STATUS current
                    DESCRIPTION "N/A"
                    DEFVAL { 0 }
                    ::= { digitalObjects 471 }

        -- 1.3.6.1.4.1.9839.2.1.1.472
        en-water-alarm-critical OBJECT-TYPE
                    SYNTAX Integer32 (0..1)
                    UNITS "N/A"
                    MAX-ACCESS read-write
                    STATUS current
                    DESCRIPTION "N/A"
                    DEFVAL { 0 }
                    ::= { digitalObjects 472 }

        -- 1.3.6.1.4.1.9839.2.1.1.473
        actuator-hand-mode OBJECT-TYPE
                    SYNTAX Integer32 (0..1)
                    UNITS "N/A"
                    MAX-ACCESS read-write
                    STATUS current
                    DESCRIPTION "Result of the selection"
                    DEFVAL { 0 }
                    ::= { digitalObjects 473 }

        -- 1.3.6.1.4.1.9839.2.1.1.474
        sel-filter-al OBJECT-TYPE
                    SYNTAX Integer32 (0..1)
                    UNITS "N/A"
                    MAX-ACCESS read-write
                    STATUS current
                    DESCRIPTION "N/A"
                    DEFVAL { 0 }
                    ::= { digitalObjects 474 }

        -- 1.3.6.1.4.1.9839.2.1.1.475
        critical-alarm-no-nc OBJECT-TYPE
                    SYNTAX Integer32 (0..1)
                    UNITS "N/A"
                    MAX-ACCESS read-write
                    STATUS current
                    DESCRIPTION "N/A"
                    DEFVAL { 0 }
                    ::= { digitalObjects 475 }

        -- 1.3.6.1.4.1.9839.2.1.1.476
        maint-alarm-no-nc OBJECT-TYPE
                    SYNTAX Integer32 (0..1)
                    UNITS "N/A"
                    MAX-ACCESS read-write
                    STATUS current
                    DESCRIPTION "N/A"
                    DEFVAL { 0 }
                    ::= { digitalObjects 476 }

        -- 1.3.6.1.4.1.9839.2.1.1.477
        en-humidifier OBJECT-TYPE
                    SYNTAX Integer32 (0..1)
                    UNITS "N/A"
                    MAX-ACCESS read-write
                    STATUS current
                    DESCRIPTION "N/A"
                    DEFVAL { 0 }
                    ::= { digitalObjects 477 }

        -- 1.3.6.1.4.1.9839.2.1.1.478
        heat-pump-en OBJECT-TYPE
                    SYNTAX Integer32 (0..1)
                    UNITS "N/A"
                    MAX-ACCESS read-write
                    STATUS current
                    DESCRIPTION "N/A"
                    DEFVAL { 0 }
                    ::= { digitalObjects 478 }

        -- 1.3.6.1.4.1.9839.2.1.1.479
        real-enable-defrost OBJECT-TYPE
                    SYNTAX Integer32 (0..1)
                    UNITS "N/A"
                    MAX-ACCESS read-write
                    STATUS current
                    DESCRIPTION "N/A"
                    DEFVAL { 0 }
                    ::= { digitalObjects 479 }

        -- 1.3.6.1.4.1.9839.2.1.1.480
        enable-defrost OBJECT-TYPE
                    SYNTAX Integer32 (0..1)
                    UNITS "N/A"
                    MAX-ACCESS read-write
                    STATUS current
                    DESCRIPTION "N/A"
                    DEFVAL { 0 }
                    ::= { digitalObjects 480 }

        -- 1.3.6.1.4.1.9839.2.1.1.481
        denconet-enable OBJECT-TYPE
                    SYNTAX Integer32 (0..1)
                    UNITS "N/A"
                    MAX-ACCESS read-write
                    STATUS current
                    DESCRIPTION "N/A"
                    DEFVAL { 0 }
                    ::= { digitalObjects 481 }

        -- 1.3.6.1.4.1.9839.2.1.1.482
        en-bms-on-off OBJECT-TYPE
                    SYNTAX Integer32 (0..1)
                    UNITS "N/A"
                    MAX-ACCESS read-write
                    STATUS current
                    DESCRIPTION "N/A"
                    DEFVAL { 0 }
                    ::= { digitalObjects 482 }

        -- 1.3.6.1.4.1.9839.2.1.1.483
        reset-hr-fan OBJECT-TYPE
                    SYNTAX Integer32 (0..1)
                    UNITS "N/A"
                    MAX-ACCESS read-write
                    STATUS current
                    DESCRIPTION "N/A"
                    DEFVAL { 0 }
                    ::= { digitalObjects 483 }

        -- 1.3.6.1.4.1.9839.2.1.1.484
        re-assigned-temp OBJECT-TYPE
                    SYNTAX Integer32 (0..1)
                    UNITS "N/A"
                    MAX-ACCESS read-write
                    STATUS current
                    DESCRIPTION "N/A"
                    DEFVAL { 0 }
                    ::= { digitalObjects 484 }

        -- 1.3.6.1.4.1.9839.2.1.1.485
        reset-hr-comp1 OBJECT-TYPE
                    SYNTAX Integer32 (0..1)
                    UNITS "N/A"
                    MAX-ACCESS read-write
                    STATUS current
                    DESCRIPTION "N/A"
                    DEFVAL { 0 }
                    ::= { digitalObjects 485 }

        -- 1.3.6.1.4.1.9839.2.1.1.486
        re-assigned-hum OBJECT-TYPE
                    SYNTAX Integer32 (0..1)
                    UNITS "N/A"
                    MAX-ACCESS read-write
                    STATUS current
                    DESCRIPTION "N/A"
                    DEFVAL { 0 }
                    ::= { digitalObjects 486 }

        -- 1.3.6.1.4.1.9839.2.1.1.487
        reset-hr-comp2 OBJECT-TYPE
                    SYNTAX Integer32 (0..1)
                    UNITS "N/A"
                    MAX-ACCESS read-write
                    STATUS current
                    DESCRIPTION "N/A"
                    DEFVAL { 0 }
                    ::= { digitalObjects 487 }

        -- 1.3.6.1.4.1.9839.2.1.1.488
        ctrl-temp-probe OBJECT-TYPE
                    SYNTAX Integer32 (0..1)
                    UNITS "N/A"
                    MAX-ACCESS read-write
                    STATUS current
                    DESCRIPTION "N/A"
                    DEFVAL { 0 }
                    ::= { digitalObjects 488 }

        -- 1.3.6.1.4.1.9839.2.1.1.489
        denconet-temp-sel OBJECT-TYPE
                    SYNTAX Integer32 (0..1)
                    UNITS "N/A"
                    MAX-ACCESS read-write
                    STATUS current
                    DESCRIPTION "N/A"
                    DEFVAL { 0 }
                    ::= { digitalObjects 489 }

        -- 1.3.6.1.4.1.9839.2.1.1.490
        denconet-hum-sel OBJECT-TYPE
                    SYNTAX Integer32 (0..1)
                    UNITS "N/A"
                    MAX-ACCESS read-write
                    STATUS current
                    DESCRIPTION "N/A"
                    DEFVAL { 0 }
                    ::= { digitalObjects 490 }

        -- 1.3.6.1.4.1.9839.2.1.1.491
        reset-hr-0-10-cool OBJECT-TYPE
                    SYNTAX Integer32 (0..1)
                    UNITS "N/A"
                    MAX-ACCESS read-write
                    STATUS current
                    DESCRIPTION "N/A"
                    DEFVAL { 0 }
                    ::= { digitalObjects 491 }

        -- 1.3.6.1.4.1.9839.2.1.1.492
        denconet-network-sa OBJECT-TYPE
                    SYNTAX Integer32 (0..1)
                    UNITS "N/A"
                    MAX-ACCESS read-write
                    STATUS current
                    DESCRIPTION "N/A"
                    DEFVAL { 0 }
                    ::= { digitalObjects 492 }

        -- 1.3.6.1.4.1.9839.2.1.1.493
        reset-hr-dodc-cool OBJECT-TYPE
                    SYNTAX Integer32 (0..1)
                    UNITS "N/A"
                    MAX-ACCESS read-write
                    STATUS current
                    DESCRIPTION "N/A"
                    DEFVAL { 0 }
                    ::= { digitalObjects 493 }

        -- 1.3.6.1.4.1.9839.2.1.1.494
        test-sequence OBJECT-TYPE
                    SYNTAX Integer32 (0..1)
                    UNITS "N/A"
                    MAX-ACCESS read-write
                    STATUS current
                    DESCRIPTION "N/A"
                    DEFVAL { 0 }
                    ::= { digitalObjects 494 }

        -- 1.3.6.1.4.1.9839.2.1.1.495
        b03-sat-alarm-enable OBJECT-TYPE
                    SYNTAX Integer32 (0..1)
                    UNITS "N/A"
                    MAX-ACCESS read-write
                    STATUS current
                    DESCRIPTION "N/A"
                    DEFVAL { 0 }
                    ::= { digitalObjects 495 }

        -- 1.3.6.1.4.1.9839.2.1.1.496
        b03-sat-interlock-enable OBJECT-TYPE
                    SYNTAX Integer32 (0..1)
                    UNITS "N/A"
                    MAX-ACCESS read-write
                    STATUS current
                    DESCRIPTION "N/A"
                    DEFVAL { 0 }
                    ::= { digitalObjects 496 }

        -- 1.3.6.1.4.1.9839.2.1.1.497
        reset-hr-heater1 OBJECT-TYPE
                    SYNTAX Integer32 (0..1)
                    UNITS "N/A"
                    MAX-ACCESS read-write
                    STATUS current
                    DESCRIPTION "N/A"
                    DEFVAL { 0 }
                    ::= { digitalObjects 497 }

        -- 1.3.6.1.4.1.9839.2.1.1.498
        reset-sequence-m OBJECT-TYPE
                    SYNTAX Integer32 (0..1)
                    UNITS "N/A"
                    MAX-ACCESS read-write
                    STATUS current
                    DESCRIPTION "N/A"
                    DEFVAL { 0 }
                    ::= { digitalObjects 498 }

        -- 1.3.6.1.4.1.9839.2.1.1.499
        reset-hr-heater2 OBJECT-TYPE
                    SYNTAX Integer32 (0..1)
                    UNITS "N/A"
                    MAX-ACCESS read-write
                    STATUS current
                    DESCRIPTION "N/A"
                    DEFVAL { 0 }
                    ::= { digitalObjects 499 }

        -- 1.3.6.1.4.1.9839.2.1.1.500
        fail-stop-cont OBJECT-TYPE
                    SYNTAX Integer32 (0..1)
                    UNITS "N/A"
                    MAX-ACCESS read-write
                    STATUS current
                    DESCRIPTION "N/A"
                    DEFVAL { 0 }
                    ::= { digitalObjects 500 }

        -- 1.3.6.1.4.1.9839.2.1.1.501
        reset-hr-0-10-heat OBJECT-TYPE
                    SYNTAX Integer32 (0..1)
                    UNITS "N/A"
                    MAX-ACCESS read-write
                    STATUS current
                    DESCRIPTION "N/A"
                    DEFVAL { 0 }
                    ::= { digitalObjects 501 }

        -- 1.3.6.1.4.1.9839.2.1.1.502
        reset-hr-dodc-heat OBJECT-TYPE
                    SYNTAX Integer32 (0..1)
                    UNITS "N/A"
                    MAX-ACCESS read-write
                    STATUS current
                    DESCRIPTION "N/A"
                    DEFVAL { 0 }
                    ::= { digitalObjects 502 }

        -- 1.3.6.1.4.1.9839.2.1.1.503
        reset-hr-rem-hum OBJECT-TYPE
                    SYNTAX Integer32 (0..1)
                    UNITS "N/A"
                    MAX-ACCESS read-write
                    STATUS current
                    DESCRIPTION "N/A"
                    DEFVAL { 0 }
                    ::= { digitalObjects 503 }

        -- 1.3.6.1.4.1.9839.2.1.1.504
        reset-hr-dehum OBJECT-TYPE
                    SYNTAX Integer32 (0..1)
                    UNITS "N/A"
                    MAX-ACCESS read-write
                    STATUS current
                    DESCRIPTION "N/A"
                    DEFVAL { 0 }
                    ::= { digitalObjects 504 }

        -- 1.3.6.1.4.1.9839.2.1.1.505
        reset-hr-cond OBJECT-TYPE
                    SYNTAX Integer32 (0..1)
                    UNITS "N/A"
                    MAX-ACCESS read-write
                    STATUS current
                    DESCRIPTION "N/A"
                    DEFVAL { 0 }
                    ::= { digitalObjects 505 }

        -- 1.3.6.1.4.1.9839.2.1.1.506
        ctrl-hum-probe OBJECT-TYPE
                    SYNTAX Integer32 (0..1)
                    UNITS "N/A"
                    MAX-ACCESS read-write
                    STATUS current
                    DESCRIPTION "N/A"
                    DEFVAL { 0 }
                    ::= { digitalObjects 506 }

        -- 1.3.6.1.4.1.9839.2.1.1.507
        reset-hr-drycool1 OBJECT-TYPE
                    SYNTAX Integer32 (0..1)
                    UNITS "N/A"
                    MAX-ACCESS read-write
                    STATUS current
                    DESCRIPTION "N/A"
                    DEFVAL { 0 }
                    ::= { digitalObjects 507 }

        -- 1.3.6.1.4.1.9839.2.1.1.508
        reset-hr-drycool2 OBJECT-TYPE
                    SYNTAX Integer32 (0..1)
                    UNITS "N/A"
                    MAX-ACCESS read-write
                    STATUS current
                    DESCRIPTION "N/A"
                    DEFVAL { 0 }
                    ::= { digitalObjects 508 }

        -- 1.3.6.1.4.1.9839.2.1.1.509
        reset-hr-critical OBJECT-TYPE
                    SYNTAX Integer32 (0..1)
                    UNITS "N/A"
                    MAX-ACCESS read-write
                    STATUS current
                    DESCRIPTION "N/A"
                    DEFVAL { 0 }
                    ::= { digitalObjects 509 }

        -- 1.3.6.1.4.1.9839.2.1.1.510
        reset-hr-maint OBJECT-TYPE
                    SYNTAX Integer32 (0..1)
                    UNITS "N/A"
                    MAX-ACCESS read-write
                    STATUS current
                    DESCRIPTION "N/A"
                    DEFVAL { 0 }
                    ::= { digitalObjects 510 }

        -- 1.3.6.1.4.1.9839.2.1.1.511
        b08-sah-interlock-enable OBJECT-TYPE
                    SYNTAX Integer32 (0..1)
                    UNITS "N/A"
                    MAX-ACCESS read-write
                    STATUS current
                    DESCRIPTION "N/A"
                    DEFVAL { 0 }
                    ::= { digitalObjects 511 }

        -- 1.3.6.1.4.1.9839.2.1.1.512
        regulation-type OBJECT-TYPE
                    SYNTAX Integer32 (0..1)
                    UNITS "N/A"
                    MAX-ACCESS read-write
                    STATUS current
                    DESCRIPTION "N/A"
                    DEFVAL { 0 }
                    ::= { digitalObjects 512 }

        -- 1.3.6.1.4.1.9839.2.1.1.513
        dehum-en OBJECT-TYPE
                    SYNTAX Integer32 (0..1)
                    UNITS "N/A"
                    MAX-ACCESS read-write
                    STATUS current
                    DESCRIPTION "N/A"
                    DEFVAL { 0 }
                    ::= { digitalObjects 513 }

        -- 1.3.6.1.4.1.9839.2.1.1.514
        dehum-interlock-en OBJECT-TYPE
                    SYNTAX Integer32 (0..1)
                    UNITS "N/A"
                    MAX-ACCESS read-write
                    STATUS current
                    DESCRIPTION "N/A"
                    DEFVAL { 0 }
                    ::= { digitalObjects 514 }

        -- 1.3.6.1.4.1.9839.2.1.1.515
        comp-sequence OBJECT-TYPE
                    SYNTAX Integer32 (0..1)
                    UNITS "N/A"
                    MAX-ACCESS read-write
                    STATUS current
                    DESCRIPTION "N/A"
                    DEFVAL { 0 }
                    ::= { digitalObjects 515 }

        -- 1.3.6.1.4.1.9839.2.1.1.516
        cool-demand-hand-en OBJECT-TYPE
                    SYNTAX Integer32 (0..1)
                    UNITS "N/A"
                    MAX-ACCESS read-write
                    STATUS current
                    DESCRIPTION "N/A"
                    DEFVAL { 0 }
                    ::= { digitalObjects 516 }

        -- 1.3.6.1.4.1.9839.2.1.1.517
        heat-demand-hand-en OBJECT-TYPE
                    SYNTAX Integer32 (0..1)
                    UNITS "N/A"
                    MAX-ACCESS read-write
                    STATUS current
                    DESCRIPTION "N/A"
                    DEFVAL { 0 }
                    ::= { digitalObjects 517 }

        -- 1.3.6.1.4.1.9839.2.1.1.518
        cwvalve-type OBJECT-TYPE
                    SYNTAX Integer32 (0..1)
                    UNITS "N/A"
                    MAX-ACCESS read-write
                    STATUS current
                    DESCRIPTION "N/A"
                    DEFVAL { 0 }
                    ::= { digitalObjects 518 }

        -- 1.3.6.1.4.1.9839.2.1.1.519
        hum-demand-hand-en OBJECT-TYPE
                    SYNTAX Integer32 (0..1)
                    UNITS "N/A"
                    MAX-ACCESS read-write
                    STATUS current
                    DESCRIPTION "N/A"
                    DEFVAL { 0 }
                    ::= { digitalObjects 519 }

        -- 1.3.6.1.4.1.9839.2.1.1.520
        combicool-config OBJECT-TYPE
                    SYNTAX Integer32 (0..1)
                    UNITS "N/A"
                    MAX-ACCESS read-write
                    STATUS current
                    DESCRIPTION "N/A"
                    DEFVAL { 0 }
                    ::= { digitalObjects 520 }

        -- 1.3.6.1.4.1.9839.2.1.1.521
        dehum-demand-hand-en OBJECT-TYPE
                    SYNTAX Integer32 (0..1)
                    UNITS "N/A"
                    MAX-ACCESS read-write
                    STATUS current
                    DESCRIPTION "N/A"
                    DEFVAL { 0 }
                    ::= { digitalObjects 521 }

        -- 1.3.6.1.4.1.9839.2.1.1.522
        maint-alarm-hand-en OBJECT-TYPE
                    SYNTAX Integer32 (0..1)
                    UNITS "N/A"
                    MAX-ACCESS read-write
                    STATUS current
                    DESCRIPTION "N/A"
                    DEFVAL { 0 }
                    ::= { digitalObjects 522 }

        -- 1.3.6.1.4.1.9839.2.1.1.523
        critical-alarm-hand-en OBJECT-TYPE
                    SYNTAX Integer32 (0..1)
                    UNITS "N/A"
                    MAX-ACCESS read-write
                    STATUS current
                    DESCRIPTION "N/A"
                    DEFVAL { 0 }
                    ::= { digitalObjects 523 }

        -- 1.3.6.1.4.1.9839.2.1.1.524
        din-01 OBJECT-TYPE
                    SYNTAX Integer32 (0..1)
                    UNITS "N/A"
                    MAX-ACCESS read-write
                    STATUS current
                    DESCRIPTION "N/A"
                    DEFVAL { 0 }
                    ::= { digitalObjects 524 }

        -- 1.3.6.1.4.1.9839.2.1.1.525
        din-02 OBJECT-TYPE
                    SYNTAX Integer32 (0..1)
                    UNITS "N/A"
                    MAX-ACCESS read-write
                    STATUS current
                    DESCRIPTION "N/A"
                    DEFVAL { 0 }
                    ::= { digitalObjects 525 }

        -- 1.3.6.1.4.1.9839.2.1.1.526
        din-03 OBJECT-TYPE
                    SYNTAX Integer32 (0..1)
                    UNITS "N/A"
                    MAX-ACCESS read-write
                    STATUS current
                    DESCRIPTION "N/A"
                    DEFVAL { 0 }
                    ::= { digitalObjects 526 }

        -- 1.3.6.1.4.1.9839.2.1.1.527
        din-04 OBJECT-TYPE
                    SYNTAX Integer32 (0..1)
                    UNITS "N/A"
                    MAX-ACCESS read-write
                    STATUS current
                    DESCRIPTION "N/A"
                    DEFVAL { 0 }
                    ::= { digitalObjects 527 }

        -- 1.3.6.1.4.1.9839.2.1.1.528
        din-05 OBJECT-TYPE
                    SYNTAX Integer32 (0..1)
                    UNITS "N/A"
                    MAX-ACCESS read-write
                    STATUS current
                    DESCRIPTION "N/A"
                    DEFVAL { 0 }
                    ::= { digitalObjects 528 }

        -- 1.3.6.1.4.1.9839.2.1.1.529
        din-06 OBJECT-TYPE
                    SYNTAX Integer32 (0..1)
                    UNITS "N/A"
                    MAX-ACCESS read-write
                    STATUS current
                    DESCRIPTION "N/A"
                    DEFVAL { 0 }
                    ::= { digitalObjects 529 }

        -- 1.3.6.1.4.1.9839.2.1.1.530
        din-07 OBJECT-TYPE
                    SYNTAX Integer32 (0..1)
                    UNITS "N/A"
                    MAX-ACCESS read-write
                    STATUS current
                    DESCRIPTION "N/A"
                    DEFVAL { 0 }
                    ::= { digitalObjects 530 }

        -- 1.3.6.1.4.1.9839.2.1.1.531
        din-08 OBJECT-TYPE
                    SYNTAX Integer32 (0..1)
                    UNITS "N/A"
                    MAX-ACCESS read-write
                    STATUS current
                    DESCRIPTION "N/A"
                    DEFVAL { 0 }
                    ::= { digitalObjects 531 }

        -- 1.3.6.1.4.1.9839.2.1.1.532
        din-09 OBJECT-TYPE
                    SYNTAX Integer32 (0..1)
                    UNITS "N/A"
                    MAX-ACCESS read-write
                    STATUS current
                    DESCRIPTION "N/A"
                    DEFVAL { 0 }
                    ::= { digitalObjects 532 }

        -- 1.3.6.1.4.1.9839.2.1.1.533
        din-10 OBJECT-TYPE
                    SYNTAX Integer32 (0..1)
                    UNITS "N/A"
                    MAX-ACCESS read-write
                    STATUS current
                    DESCRIPTION "N/A"
                    DEFVAL { 0 }
                    ::= { digitalObjects 533 }

        -- 1.3.6.1.4.1.9839.2.1.1.534
        din-11 OBJECT-TYPE
                    SYNTAX Integer32 (0..1)
                    UNITS "N/A"
                    MAX-ACCESS read-write
                    STATUS current
                    DESCRIPTION "N/A"
                    DEFVAL { 0 }
                    ::= { digitalObjects 534 }

        -- 1.3.6.1.4.1.9839.2.1.1.535
        din-12 OBJECT-TYPE
                    SYNTAX Integer32 (0..1)
                    UNITS "N/A"
                    MAX-ACCESS read-write
                    STATUS current
                    DESCRIPTION "N/A"
                    DEFVAL { 0 }
                    ::= { digitalObjects 535 }

        -- 1.3.6.1.4.1.9839.2.1.1.536
        din-13 OBJECT-TYPE
                    SYNTAX Integer32 (0..1)
                    UNITS "N/A"
                    MAX-ACCESS read-write
                    STATUS current
                    DESCRIPTION "N/A"
                    DEFVAL { 0 }
                    ::= { digitalObjects 536 }

        -- 1.3.6.1.4.1.9839.2.1.1.537
        din-14 OBJECT-TYPE
                    SYNTAX Integer32 (0..1)
                    UNITS "N/A"
                    MAX-ACCESS read-write
                    STATUS current
                    DESCRIPTION "N/A"
                    DEFVAL { 0 }
                    ::= { digitalObjects 537 }

        -- 1.3.6.1.4.1.9839.2.1.1.538
        din-15 OBJECT-TYPE
                    SYNTAX Integer32 (0..1)
                    UNITS "N/A"
                    MAX-ACCESS read-write
                    STATUS current
                    DESCRIPTION "N/A"
                    DEFVAL { 0 }
                    ::= { digitalObjects 538 }

        -- 1.3.6.1.4.1.9839.2.1.1.539
        din-16 OBJECT-TYPE
                    SYNTAX Integer32 (0..1)
                    UNITS "N/A"
                    MAX-ACCESS read-write
                    STATUS current
                    DESCRIPTION "N/A"
                    DEFVAL { 0 }
                    ::= { digitalObjects 539 }

        -- 1.3.6.1.4.1.9839.2.1.1.540
        din-17 OBJECT-TYPE
                    SYNTAX Integer32 (0..1)
                    UNITS "N/A"
                    MAX-ACCESS read-write
                    STATUS current
                    DESCRIPTION "N/A"
                    DEFVAL { 0 }
                    ::= { digitalObjects 540 }

        -- 1.3.6.1.4.1.9839.2.1.1.541
        din-18 OBJECT-TYPE
                    SYNTAX Integer32 (0..1)
                    UNITS "N/A"
                    MAX-ACCESS read-write
                    STATUS current
                    DESCRIPTION "N/A"
                    DEFVAL { 0 }
                    ::= { digitalObjects 541 }

        -- 1.3.6.1.4.1.9839.2.1.1.542
        do01 OBJECT-TYPE
                    SYNTAX Integer32 (0..1)
                    UNITS "N/A"
                    MAX-ACCESS read-write
                    STATUS current
                    DESCRIPTION "N/A"
                    DEFVAL { 0 }
                    ::= { digitalObjects 542 }

        -- 1.3.6.1.4.1.9839.2.1.1.543
        do02 OBJECT-TYPE
                    SYNTAX Integer32 (0..1)
                    UNITS "N/A"
                    MAX-ACCESS read-write
                    STATUS current
                    DESCRIPTION "N/A"
                    DEFVAL { 0 }
                    ::= { digitalObjects 543 }

        -- 1.3.6.1.4.1.9839.2.1.1.544
        do03 OBJECT-TYPE
                    SYNTAX Integer32 (0..1)
                    UNITS "N/A"
                    MAX-ACCESS read-write
                    STATUS current
                    DESCRIPTION "N/A"
                    DEFVAL { 0 }
                    ::= { digitalObjects 544 }

        -- 1.3.6.1.4.1.9839.2.1.1.545
        do04 OBJECT-TYPE
                    SYNTAX Integer32 (0..1)
                    UNITS "N/A"
                    MAX-ACCESS read-write
                    STATUS current
                    DESCRIPTION "N/A"
                    DEFVAL { 0 }
                    ::= { digitalObjects 545 }

        -- 1.3.6.1.4.1.9839.2.1.1.546
        do05 OBJECT-TYPE
                    SYNTAX Integer32 (0..1)
                    UNITS "N/A"
                    MAX-ACCESS read-write
                    STATUS current
                    DESCRIPTION "N/A"
                    DEFVAL { 0 }
                    ::= { digitalObjects 546 }

        -- 1.3.6.1.4.1.9839.2.1.1.547
        do06 OBJECT-TYPE
                    SYNTAX Integer32 (0..1)
                    UNITS "N/A"
                    MAX-ACCESS read-write
                    STATUS current
                    DESCRIPTION "N/A"
                    DEFVAL { 0 }
                    ::= { digitalObjects 547 }

        -- 1.3.6.1.4.1.9839.2.1.1.548
        do07 OBJECT-TYPE
                    SYNTAX Integer32 (0..1)
                    UNITS "N/A"
                    MAX-ACCESS read-write
                    STATUS current
                    DESCRIPTION "N/A"
                    DEFVAL { 0 }
                    ::= { digitalObjects 548 }

        -- 1.3.6.1.4.1.9839.2.1.1.549
        do08 OBJECT-TYPE
                    SYNTAX Integer32 (0..1)
                    UNITS "N/A"
                    MAX-ACCESS read-write
                    STATUS current
                    DESCRIPTION "N/A"
                    DEFVAL { 0 }
                    ::= { digitalObjects 549 }

        -- 1.3.6.1.4.1.9839.2.1.1.550
        do09 OBJECT-TYPE
                    SYNTAX Integer32 (0..1)
                    UNITS "N/A"
                    MAX-ACCESS read-write
                    STATUS current
                    DESCRIPTION "N/A"
                    DEFVAL { 0 }
                    ::= { digitalObjects 550 }

        -- 1.3.6.1.4.1.9839.2.1.1.551
        do10 OBJECT-TYPE
                    SYNTAX Integer32 (0..1)
                    UNITS "N/A"
                    MAX-ACCESS read-write
                    STATUS current
                    DESCRIPTION "N/A"
                    DEFVAL { 0 }
                    ::= { digitalObjects 551 }

        -- 1.3.6.1.4.1.9839.2.1.1.552
        do11 OBJECT-TYPE
                    SYNTAX Integer32 (0..1)
                    UNITS "N/A"
                    MAX-ACCESS read-write
                    STATUS current
                    DESCRIPTION "N/A"
                    DEFVAL { 0 }
                    ::= { digitalObjects 552 }

        -- 1.3.6.1.4.1.9839.2.1.1.553
        do12 OBJECT-TYPE
                    SYNTAX Integer32 (0..1)
                    UNITS "N/A"
                    MAX-ACCESS read-write
                    STATUS current
                    DESCRIPTION "N/A"
                    DEFVAL { 0 }
                    ::= { digitalObjects 553 }

        -- 1.3.6.1.4.1.9839.2.1.1.554
        do13 OBJECT-TYPE
                    SYNTAX Integer32 (0..1)
                    UNITS "N/A"
                    MAX-ACCESS read-write
                    STATUS current
                    DESCRIPTION "N/A"
                    DEFVAL { 0 }
                    ::= { digitalObjects 554 }

        -- 1.3.6.1.4.1.9839.2.1.1.555
        do14 OBJECT-TYPE
                    SYNTAX Integer32 (0..1)
                    UNITS "N/A"
                    MAX-ACCESS read-write
                    STATUS current
                    DESCRIPTION "N/A"
                    DEFVAL { 0 }
                    ::= { digitalObjects 555 }

        -- 1.3.6.1.4.1.9839.2.1.1.556
        do15 OBJECT-TYPE
                    SYNTAX Integer32 (0..1)
                    UNITS "N/A"
                    MAX-ACCESS read-write
                    STATUS current
                    DESCRIPTION "N/A"
                    DEFVAL { 0 }
                    ::= { digitalObjects 556 }

        -- 1.3.6.1.4.1.9839.2.1.1.557
        do16 OBJECT-TYPE
                    SYNTAX Integer32 (0..1)
                    UNITS "N/A"
                    MAX-ACCESS read-write
                    STATUS current
                    DESCRIPTION "N/A"
                    DEFVAL { 0 }
                    ::= { digitalObjects 557 }

        -- 1.3.6.1.4.1.9839.2.1.1.558
        do17 OBJECT-TYPE
                    SYNTAX Integer32 (0..1)
                    UNITS "N/A"
                    MAX-ACCESS read-write
                    STATUS current
                    DESCRIPTION "N/A"
                    DEFVAL { 0 }
                    ::= { digitalObjects 558 }

        -- 1.3.6.1.4.1.9839.2.1.1.559
        do18 OBJECT-TYPE
                    SYNTAX Integer32 (0..1)
                    UNITS "N/A"
                    MAX-ACCESS read-write
                    STATUS current
                    DESCRIPTION "N/A"
                    DEFVAL { 0 }
                    ::= { digitalObjects 559 }

        -- 1.3.6.1.4.1.9839.2.1.1.560
        reset-run-hours OBJECT-TYPE
                    SYNTAX Integer32 (0..1)
                    UNITS "N/A"
                    MAX-ACCESS read-write
                    STATUS current
                    DESCRIPTION "N/A"
                    DEFVAL { 0 }
                    ::= { digitalObjects 560 }

        -- 1.3.6.1.4.1.9839.2.1.1.561
        sel-on-off OBJECT-TYPE
                    SYNTAX Integer32 (0..1)
                    UNITS "N/A"
                    MAX-ACCESS read-write
                    STATUS current
                    DESCRIPTION "N/A"
                    DEFVAL { 0 }
                    ::= { digitalObjects 561 }

        -- 1.3.6.1.4.1.9839.2.1.1.562
        bms-heart-beat OBJECT-TYPE
                    SYNTAX Integer32 (0..1)
                    UNITS "N/A"
                    MAX-ACCESS read-write
                    STATUS current
                    DESCRIPTION "N/A"
                    DEFVAL { 0 }
                    ::= { digitalObjects 562 }

        -- 1.3.6.1.4.1.9839.2.1.1.563
        en-bms-offline-al OBJECT-TYPE
                    SYNTAX Integer32 (0..1)
                    UNITS "N/A"
                    MAX-ACCESS read-write
                    STATUS current
                    DESCRIPTION "Value"
                    DEFVAL { 0 }
                    ::= { digitalObjects 563 }

        -- 1.3.6.1.4.1.9839.2.1.1.564
        bms-online OBJECT-TYPE
                    SYNTAX Integer32 (0..1)
                    UNITS "N/A"
                    MAX-ACCESS read-only
                    STATUS current
                    DESCRIPTION "N/A"
                    DEFVAL { 0 }
                    ::= { digitalObjects 564 }

        -- 1.3.6.1.4.1.9839.2.1.1.565
        return-air-moisture-sel OBJECT-TYPE
                    SYNTAX Integer32 (0..1)
                    UNITS "N/A"
                    MAX-ACCESS read-write
                    STATUS current
                    DESCRIPTION "Result of the selection"
                    DEFVAL { 0 }
                    ::= { digitalObjects 565 }

        -- 1.3.6.1.4.1.9839.2.1.1.566
        en-unit-fan-speed-ctrl OBJECT-TYPE
                    SYNTAX Integer32 (0..1)
                    UNITS "N/A"
                    MAX-ACCESS read-write
                    STATUS current
                    DESCRIPTION "N/A"
                    DEFVAL { 0 }
                    ::= { digitalObjects 566 }

        -- 1.3.6.1.4.1.9839.2.1.1.567
        restore-defaults OBJECT-TYPE
                    SYNTAX Integer32 (0..1)
                    UNITS "N/A"
                    MAX-ACCESS read-write
                    STATUS current
                    DESCRIPTION "N/A"
                    DEFVAL { 0 }
                    ::= { digitalObjects 567 }

        -- 1.3.6.1.4.1.9839.2.1.1.568
        dummy OBJECT-TYPE
                    SYNTAX Integer32 (0..1)
                    UNITS "N/A"
                    MAX-ACCESS read-write
                    STATUS current
                    DESCRIPTION "N/A"
                    DEFVAL { 0 }
                    ::= { digitalObjects 568 }

        -- 1.3.6.1.4.1.9839.2.1.1.569
        unit1-denconet-enable OBJECT-TYPE
                    SYNTAX Integer32 (0..1)
                    UNITS "N/A"
                    MAX-ACCESS read-only
                    STATUS current
                    DESCRIPTION "N/A"
                    DEFVAL { 0 }
                    ::= { digitalObjects 569 }

        -- 1.3.6.1.4.1.9839.2.1.1.570
        unit2-denconet-enable OBJECT-TYPE
                    SYNTAX Integer32 (0..1)
                    UNITS "N/A"
                    MAX-ACCESS read-only
                    STATUS current
                    DESCRIPTION "N/A"
                    DEFVAL { 0 }
                    ::= { digitalObjects 570 }

        -- 1.3.6.1.4.1.9839.2.1.1.571
        unit3-denconet-enable OBJECT-TYPE
                    SYNTAX Integer32 (0..1)
                    UNITS "N/A"
                    MAX-ACCESS read-only
                    STATUS current
                    DESCRIPTION "N/A"
                    DEFVAL { 0 }
                    ::= { digitalObjects 571 }

        -- 1.3.6.1.4.1.9839.2.1.1.572
        unit4-denconet-enable OBJECT-TYPE
                    SYNTAX Integer32 (0..1)
                    UNITS "N/A"
                    MAX-ACCESS read-only
                    STATUS current
                    DESCRIPTION "N/A"
                    DEFVAL { 0 }
                    ::= { digitalObjects 572 }

        -- 1.3.6.1.4.1.9839.2.1.1.573
        unit5-denconet-enable OBJECT-TYPE
                    SYNTAX Integer32 (0..1)
                    UNITS "N/A"
                    MAX-ACCESS read-only
                    STATUS current
                    DESCRIPTION "N/A"
                    DEFVAL { 0 }
                    ::= { digitalObjects 573 }

        -- 1.3.6.1.4.1.9839.2.1.1.574
        unit6-denconet-enable OBJECT-TYPE
                    SYNTAX Integer32 (0..1)
                    UNITS "N/A"
                    MAX-ACCESS read-only
                    STATUS current
                    DESCRIPTION "N/A"
                    DEFVAL { 0 }
                    ::= { digitalObjects 574 }

        -- 1.3.6.1.4.1.9839.2.1.1.575
        unit7-denconet-enable OBJECT-TYPE
                    SYNTAX Integer32 (0..1)
                    UNITS "N/A"
                    MAX-ACCESS read-only
                    STATUS current
                    DESCRIPTION "N/A"
                    DEFVAL { 0 }
                    ::= { digitalObjects 575 }

        -- 1.3.6.1.4.1.9839.2.1.1.576
        unit8-denconet-enable OBJECT-TYPE
                    SYNTAX Integer32 (0..1)
                    UNITS "N/A"
                    MAX-ACCESS read-only
                    STATUS current
                    DESCRIPTION "N/A"
                    DEFVAL { 0 }
                    ::= { digitalObjects 576 }

        -- 1.3.6.1.4.1.9839.2.1.1.577
        denconet-temp-sel-u1 OBJECT-TYPE
                    SYNTAX Integer32 (0..1)
                    UNITS "N/A"
                    MAX-ACCESS read-only
                    STATUS current
                    DESCRIPTION "N/A"
                    DEFVAL { 0 }
                    ::= { digitalObjects 577 }

        -- 1.3.6.1.4.1.9839.2.1.1.578
        denconet-temp-sel-u2 OBJECT-TYPE
                    SYNTAX Integer32 (0..1)
                    UNITS "N/A"
                    MAX-ACCESS read-only
                    STATUS current
                    DESCRIPTION "N/A"
                    DEFVAL { 0 }
                    ::= { digitalObjects 578 }

        -- 1.3.6.1.4.1.9839.2.1.1.579
        denconet-temp-sel-u3 OBJECT-TYPE
                    SYNTAX Integer32 (0..1)
                    UNITS "N/A"
                    MAX-ACCESS read-only
                    STATUS current
                    DESCRIPTION "N/A"
                    DEFVAL { 0 }
                    ::= { digitalObjects 579 }

        -- 1.3.6.1.4.1.9839.2.1.1.580
        denconet-temp-sel-u4 OBJECT-TYPE
                    SYNTAX Integer32 (0..1)
                    UNITS "N/A"
                    MAX-ACCESS read-only
                    STATUS current
                    DESCRIPTION "N/A"
                    DEFVAL { 0 }
                    ::= { digitalObjects 580 }

        -- 1.3.6.1.4.1.9839.2.1.1.581
        denconet-temp-sel-u5 OBJECT-TYPE
                    SYNTAX Integer32 (0..1)
                    UNITS "N/A"
                    MAX-ACCESS read-only
                    STATUS current
                    DESCRIPTION "N/A"
                    DEFVAL { 0 }
                    ::= { digitalObjects 581 }

        -- 1.3.6.1.4.1.9839.2.1.1.582
        denconet-temp-sel-u6 OBJECT-TYPE
                    SYNTAX Integer32 (0..1)
                    UNITS "N/A"
                    MAX-ACCESS read-only
                    STATUS current
                    DESCRIPTION "N/A"
                    DEFVAL { 0 }
                    ::= { digitalObjects 582 }

        -- 1.3.6.1.4.1.9839.2.1.1.583
        denconet-temp-sel-u7 OBJECT-TYPE
                    SYNTAX Integer32 (0..1)
                    UNITS "N/A"
                    MAX-ACCESS read-only
                    STATUS current
                    DESCRIPTION "N/A"
                    DEFVAL { 0 }
                    ::= { digitalObjects 583 }

        -- 1.3.6.1.4.1.9839.2.1.1.584
        denconet-temp-sel-u8 OBJECT-TYPE
                    SYNTAX Integer32 (0..1)
                    UNITS "N/A"
                    MAX-ACCESS read-only
                    STATUS current
                    DESCRIPTION "N/A"
                    DEFVAL { 0 }
                    ::= { digitalObjects 584 }

        -- 1.3.6.1.4.1.9839.2.1.1.585
        denconet-hum-sel-u1 OBJECT-TYPE
                    SYNTAX Integer32 (0..1)
                    UNITS "N/A"
                    MAX-ACCESS read-only
                    STATUS current
                    DESCRIPTION "N/A"
                    DEFVAL { 0 }
                    ::= { digitalObjects 585 }

        -- 1.3.6.1.4.1.9839.2.1.1.586
        denconet-hum-sel-u2 OBJECT-TYPE
                    SYNTAX Integer32 (0..1)
                    UNITS "N/A"
                    MAX-ACCESS read-only
                    STATUS current
                    DESCRIPTION "N/A"
                    DEFVAL { 0 }
                    ::= { digitalObjects 586 }

        -- 1.3.6.1.4.1.9839.2.1.1.587
        denconet-hum-sel-u3 OBJECT-TYPE
                    SYNTAX Integer32 (0..1)
                    UNITS "N/A"
                    MAX-ACCESS read-only
                    STATUS current
                    DESCRIPTION "N/A"
                    DEFVAL { 0 }
                    ::= { digitalObjects 587 }

        -- 1.3.6.1.4.1.9839.2.1.1.588
        denconet-hum-sel-u4 OBJECT-TYPE
                    SYNTAX Integer32 (0..1)
                    UNITS "N/A"
                    MAX-ACCESS read-only
                    STATUS current
                    DESCRIPTION "N/A"
                    DEFVAL { 0 }
                    ::= { digitalObjects 588 }

        -- 1.3.6.1.4.1.9839.2.1.1.589
        denconet-hum-sel-u5 OBJECT-TYPE
                    SYNTAX Integer32 (0..1)
                    UNITS "N/A"
                    MAX-ACCESS read-only
                    STATUS current
                    DESCRIPTION "N/A"
                    DEFVAL { 0 }
                    ::= { digitalObjects 589 }

        -- 1.3.6.1.4.1.9839.2.1.1.590
        denconet-hum-sel-u6 OBJECT-TYPE
                    SYNTAX Integer32 (0..1)
                    UNITS "N/A"
                    MAX-ACCESS read-only
                    STATUS current
                    DESCRIPTION "N/A"
                    DEFVAL { 0 }
                    ::= { digitalObjects 590 }

        -- 1.3.6.1.4.1.9839.2.1.1.591
        denconet-hum-sel-u7 OBJECT-TYPE
                    SYNTAX Integer32 (0..1)
                    UNITS "N/A"
                    MAX-ACCESS read-only
                    STATUS current
                    DESCRIPTION "N/A"
                    DEFVAL { 0 }
                    ::= { digitalObjects 591 }

        -- 1.3.6.1.4.1.9839.2.1.1.592
        denconet-hum-sel-u8 OBJECT-TYPE
                    SYNTAX Integer32 (0..1)
                    UNITS "N/A"
                    MAX-ACCESS read-only
                    STATUS current
                    DESCRIPTION "N/A"
                    DEFVAL { 0 }
                    ::= { digitalObjects 592 }

        -- 1.3.6.1.4.1.9839.2.1.1.593
        stand-alone-temp OBJECT-TYPE
                    SYNTAX Integer32 (0..1)
                    UNITS "N/A"
                    MAX-ACCESS read-write
                    STATUS current
                    DESCRIPTION "N/A"
                    DEFVAL { 0 }
                    ::= { digitalObjects 593 }

        -- 1.3.6.1.4.1.9839.2.1.1.594
        stand-alone-ru-t OBJECT-TYPE
                    SYNTAX Integer32 (0..1)
                    UNITS "N/A"
                    MAX-ACCESS read-write
                    STATUS current
                    DESCRIPTION "N/A"
                    DEFVAL { 0 }
                    ::= { digitalObjects 594 }

        -- 1.3.6.1.4.1.9839.2.1.1.595
        master-ru-t OBJECT-TYPE
                    SYNTAX Integer32 (0..1)
                    UNITS "N/A"
                    MAX-ACCESS read-write
                    STATUS current
                    DESCRIPTION "N/A"
                    DEFVAL { 0 }
                    ::= { digitalObjects 595 }

        -- 1.3.6.1.4.1.9839.2.1.1.596
        denconet-network-sa-u2 OBJECT-TYPE
                    SYNTAX Integer32 (0..1)
                    UNITS "N/A"
                    MAX-ACCESS read-only
                    STATUS current
                    DESCRIPTION "N/A"
                    DEFVAL { 0 }
                    ::= { digitalObjects 596 }

        -- 1.3.6.1.4.1.9839.2.1.1.597
        denconet-network-sa-u5 OBJECT-TYPE
                    SYNTAX Integer32 (0..1)
                    UNITS "N/A"
                    MAX-ACCESS read-only
                    STATUS current
                    DESCRIPTION "N/A"
                    DEFVAL { 0 }
                    ::= { digitalObjects 597 }

        -- 1.3.6.1.4.1.9839.2.1.1.598
        denconet-network-sa-u8 OBJECT-TYPE
                    SYNTAX Integer32 (0..1)
                    UNITS "N/A"
                    MAX-ACCESS read-only
                    STATUS current
                    DESCRIPTION "N/A"
                    DEFVAL { 0 }
                    ::= { digitalObjects 598 }

        -- 1.3.6.1.4.1.9839.2.1.1.599
        denconet-network-sa-u3 OBJECT-TYPE
                    SYNTAX Integer32 (0..1)
                    UNITS "N/A"
                    MAX-ACCESS read-only
                    STATUS current
                    DESCRIPTION "N/A"
                    DEFVAL { 0 }
                    ::= { digitalObjects 599 }

        -- 1.3.6.1.4.1.9839.2.1.1.600
        denconet-network-sa-u6 OBJECT-TYPE
                    SYNTAX Integer32 (0..1)
                    UNITS "N/A"
                    MAX-ACCESS read-only
                    STATUS current
                    DESCRIPTION "N/A"
                    DEFVAL { 0 }
                    ::= { digitalObjects 600 }

        -- 1.3.6.1.4.1.9839.2.1.1.601
        denconet-network-sa-u4 OBJECT-TYPE
                    SYNTAX Integer32 (0..1)
                    UNITS "N/A"
                    MAX-ACCESS read-only
                    STATUS current
                    DESCRIPTION "N/A"
                    DEFVAL { 0 }
                    ::= { digitalObjects 601 }

        -- 1.3.6.1.4.1.9839.2.1.1.602
        denconet-network-sa-u7 OBJECT-TYPE
                    SYNTAX Integer32 (0..1)
                    UNITS "N/A"
                    MAX-ACCESS read-only
                    STATUS current
                    DESCRIPTION "N/A"
                    DEFVAL { 0 }
                    ::= { digitalObjects 602 }

        -- 1.3.6.1.4.1.9839.2.1.1.603
        stand-alone-or-master-ru-t OBJECT-TYPE
                    SYNTAX Integer32 (0..1)
                    UNITS "N/A"
                    MAX-ACCESS read-write
                    STATUS current
                    DESCRIPTION "N/A"
                    DEFVAL { 0 }
                    ::= { digitalObjects 603 }

        -- 1.3.6.1.4.1.9839.2.1.1.604
        re-assigned-temp-master OBJECT-TYPE
                    SYNTAX Integer32 (0..1)
                    UNITS "N/A"
                    MAX-ACCESS read-write
                    STATUS current
                    DESCRIPTION "N/A"
                    DEFVAL { 0 }
                    ::= { digitalObjects 604 }

        -- 1.3.6.1.4.1.9839.2.1.1.605
        re-assigned-temp-slave OBJECT-TYPE
                    SYNTAX Integer32 (0..1)
                    UNITS "N/A"
                    MAX-ACCESS read-write
                    STATUS current
                    DESCRIPTION "N/A"
                    DEFVAL { 0 }
                    ::= { digitalObjects 605 }

        -- 1.3.6.1.4.1.9839.2.1.1.606
        check-ru-t OBJECT-TYPE
                    SYNTAX Integer32 (0..1)
                    UNITS "N/A"
                    MAX-ACCESS read-write
                    STATUS current
                    DESCRIPTION "N/A"
                    DEFVAL { 0 }
                    ::= { digitalObjects 606 }

        -- 1.3.6.1.4.1.9839.2.1.1.607
        mcs-mode OBJECT-TYPE
                    SYNTAX Integer32 (0..1)
                    UNITS "N/A"
                    MAX-ACCESS read-write
                    STATUS current
                    DESCRIPTION "N/A"
                    DEFVAL { 0 }
                    ::= { digitalObjects 607 }

        -- 1.3.6.1.4.1.9839.2.1.1.608
        dnet-present-u1 OBJECT-TYPE
                    SYNTAX Integer32 (0..1)
                    UNITS "N/A"
                    MAX-ACCESS read-only
                    STATUS current
                    DESCRIPTION "N/A"
                    DEFVAL { 0 }
                    ::= { digitalObjects 608 }

        -- 1.3.6.1.4.1.9839.2.1.1.609
        dnet-present-u2 OBJECT-TYPE
                    SYNTAX Integer32 (0..1)
                    UNITS "N/A"
                    MAX-ACCESS read-only
                    STATUS current
                    DESCRIPTION "N/A"
                    DEFVAL { 0 }
                    ::= { digitalObjects 609 }

        -- 1.3.6.1.4.1.9839.2.1.1.610
        dnet-present-u3 OBJECT-TYPE
                    SYNTAX Integer32 (0..1)
                    UNITS "N/A"
                    MAX-ACCESS read-only
                    STATUS current
                    DESCRIPTION "N/A"
                    DEFVAL { 0 }
                    ::= { digitalObjects 610 }

        -- 1.3.6.1.4.1.9839.2.1.1.611
        dnet-present-u4 OBJECT-TYPE
                    SYNTAX Integer32 (0..1)
                    UNITS "N/A"
                    MAX-ACCESS read-only
                    STATUS current
                    DESCRIPTION "N/A"
                    DEFVAL { 0 }
                    ::= { digitalObjects 611 }

        -- 1.3.6.1.4.1.9839.2.1.1.612
        dnet-present-u5 OBJECT-TYPE
                    SYNTAX Integer32 (0..1)
                    UNITS "N/A"
                    MAX-ACCESS read-only
                    STATUS current
                    DESCRIPTION "N/A"
                    DEFVAL { 0 }
                    ::= { digitalObjects 612 }

        -- 1.3.6.1.4.1.9839.2.1.1.613
        dnet-present-u6 OBJECT-TYPE
                    SYNTAX Integer32 (0..1)
                    UNITS "N/A"
                    MAX-ACCESS read-only
                    STATUS current
                    DESCRIPTION "N/A"
                    DEFVAL { 0 }
                    ::= { digitalObjects 613 }

        -- 1.3.6.1.4.1.9839.2.1.1.614
        dnet-present-u7 OBJECT-TYPE
                    SYNTAX Integer32 (0..1)
                    UNITS "N/A"
                    MAX-ACCESS read-only
                    STATUS current
                    DESCRIPTION "N/A"
                    DEFVAL { 0 }
                    ::= { digitalObjects 614 }

        -- 1.3.6.1.4.1.9839.2.1.1.615
        dnet-present-u8 OBJECT-TYPE
                    SYNTAX Integer32 (0..1)
                    UNITS "N/A"
                    MAX-ACCESS read-only
                    STATUS current
                    DESCRIPTION "N/A"
                    DEFVAL { 0 }
                    ::= { digitalObjects 615 }

        -- 1.3.6.1.4.1.9839.2.1.1.616
        en-special-cooling-demand OBJECT-TYPE
                    SYNTAX Integer32 (0..1)
                    UNITS "N/A"
                    MAX-ACCESS read-write
                    STATUS current
                    DESCRIPTION "N/A"
                    DEFVAL { 0 }
                    ::= { digitalObjects 616 }

        -- 1.3.6.1.4.1.9839.2.1.1.617
        defrost-active OBJECT-TYPE
                    SYNTAX Integer32 (0..1)
                    UNITS "N/A"
                    MAX-ACCESS read-write
                    STATUS current
                    DESCRIPTION "N/A"
                    DEFVAL { 0 }
                    ::= { digitalObjects 617 }

        -- 1.3.6.1.4.1.9839.2.1.1.618
        two-circuits OBJECT-TYPE
                    SYNTAX Integer32 (0..1)
                    UNITS "N/A"
                    MAX-ACCESS read-write
                    STATUS current
                    DESCRIPTION "N/A"
                    DEFVAL { 0 }
                    ::= { digitalObjects 618 }

        -- 1.3.6.1.4.1.9839.2.1.1.619
        force-lecu OBJECT-TYPE
                    SYNTAX Integer32 (0..1)
                    UNITS "N/A"
                    MAX-ACCESS read-write
                    STATUS current
                    DESCRIPTION "N/A"
                    DEFVAL { 0 }
                    ::= { digitalObjects 619 }

        -- 1.3.6.1.4.1.9839.2.1.1.620
        lecu-off OBJECT-TYPE
                    SYNTAX Integer32 (0..1)
                    UNITS "N/A"
                    MAX-ACCESS read-write
                    STATUS current
                    DESCRIPTION "N/A"
                    DEFVAL { 0 }
                    ::= { digitalObjects 620 }

        -- 1.3.6.1.4.1.9839.2.1.1.621
        i-cmd-trigger OBJECT-TYPE
                    SYNTAX Integer32 (0..1)
                    UNITS "N/A"
                    MAX-ACCESS read-write
                    STATUS current
                    DESCRIPTION "N/A"
                    DEFVAL { 0 }
                    ::= { digitalObjects 621 }

        -- 1.3.6.1.4.1.9839.2.1.1.622
        offline-unit1 OBJECT-TYPE
                    SYNTAX Integer32 (0..1)
                    UNITS "N/A"
                    MAX-ACCESS read-only
                    STATUS current
                    DESCRIPTION "N/A"
                    DEFVAL { 0 }
                    ::= { digitalObjects 622 }

        -- 1.3.6.1.4.1.9839.2.1.1.623
        offline-unit2 OBJECT-TYPE
                    SYNTAX Integer32 (0..1)
                    UNITS "N/A"
                    MAX-ACCESS read-only
                    STATUS current
                    DESCRIPTION "N/A"
                    DEFVAL { 0 }
                    ::= { digitalObjects 623 }

        -- 1.3.6.1.4.1.9839.2.1.1.624
        offline-unit3 OBJECT-TYPE
                    SYNTAX Integer32 (0..1)
                    UNITS "N/A"
                    MAX-ACCESS read-only
                    STATUS current
                    DESCRIPTION "N/A"
                    DEFVAL { 0 }
                    ::= { digitalObjects 624 }

        -- 1.3.6.1.4.1.9839.2.1.1.625
        offline-unit4 OBJECT-TYPE
                    SYNTAX Integer32 (0..1)
                    UNITS "N/A"
                    MAX-ACCESS read-only
                    STATUS current
                    DESCRIPTION "N/A"
                    DEFVAL { 0 }
                    ::= { digitalObjects 625 }

        -- 1.3.6.1.4.1.9839.2.1.1.626
        offline-unit5 OBJECT-TYPE
                    SYNTAX Integer32 (0..1)
                    UNITS "N/A"
                    MAX-ACCESS read-only
                    STATUS current
                    DESCRIPTION "N/A"
                    DEFVAL { 0 }
                    ::= { digitalObjects 626 }

        -- 1.3.6.1.4.1.9839.2.1.1.627
        offline-unit6 OBJECT-TYPE
                    SYNTAX Integer32 (0..1)
                    UNITS "N/A"
                    MAX-ACCESS read-only
                    STATUS current
                    DESCRIPTION "N/A"
                    DEFVAL { 0 }
                    ::= { digitalObjects 627 }

        -- 1.3.6.1.4.1.9839.2.1.1.628
        offline-unit7 OBJECT-TYPE
                    SYNTAX Integer32 (0..1)
                    UNITS "N/A"
                    MAX-ACCESS read-only
                    STATUS current
                    DESCRIPTION "N/A"
                    DEFVAL { 0 }
                    ::= { digitalObjects 628 }

        -- 1.3.6.1.4.1.9839.2.1.1.629
        offline-unit8 OBJECT-TYPE
                    SYNTAX Integer32 (0..1)
                    UNITS "N/A"
                    MAX-ACCESS read-only
                    STATUS current
                    DESCRIPTION "N/A"
                    DEFVAL { 0 }
                    ::= { digitalObjects 629 }

        -- 1.3.6.1.4.1.9839.2.1.1.630
        store-pgd OBJECT-TYPE
                    SYNTAX Integer32 (0..1)
                    UNITS "N/A"
                    MAX-ACCESS read-write
                    STATUS current
                    DESCRIPTION "N/A"
                    DEFVAL { 0 }
                    ::= { digitalObjects 630 }

        -- 1.3.6.1.4.1.9839.2.1.1.631
        restore-pgd OBJECT-TYPE
                    SYNTAX Integer32 (0..1)
                    UNITS "N/A"
                    MAX-ACCESS read-write
                    STATUS current
                    DESCRIPTION "N/A"
                    DEFVAL { 0 }
                    ::= { digitalObjects 631 }

        -- 1.3.6.1.4.1.9839.2.1.1.632
        cool-active OBJECT-TYPE
                    SYNTAX Integer32 (0..1)
                    UNITS "N/A"
                    MAX-ACCESS read-write
                    STATUS current
                    DESCRIPTION "N/A"
                    DEFVAL { 0 }
                    ::= { digitalObjects 632 }

        -- 1.3.6.1.4.1.9839.2.1.1.633
        heat-active OBJECT-TYPE
                    SYNTAX Integer32 (0..1)
                    UNITS "N/A"
                    MAX-ACCESS read-write
                    STATUS current
                    DESCRIPTION "N/A"
                    DEFVAL { 0 }
                    ::= { digitalObjects 633 }

        -- 1.3.6.1.4.1.9839.2.1.1.634
        dehum-active OBJECT-TYPE
                    SYNTAX Integer32 (0..1)
                    UNITS "N/A"
                    MAX-ACCESS read-write
                    STATUS current
                    DESCRIPTION "N/A"
                    DEFVAL { 0 }
                    ::= { digitalObjects 634 }

        -- 1.3.6.1.4.1.9839.2.1.1.635
        hum-active OBJECT-TYPE
                    SYNTAX Integer32 (0..1)
                    UNITS "N/A"
                    MAX-ACCESS read-write
                    STATUS current
                    DESCRIPTION "N/A"
                    DEFVAL { 0 }
                    ::= { digitalObjects 635 }

        -- 1.3.6.1.4.1.9839.2.1.1.636
        unit-fan OBJECT-TYPE
                    SYNTAX Integer32 (0..1)
                    UNITS "N/A"
                    MAX-ACCESS read-only
                    STATUS current
                    DESCRIPTION "Fan Status"
                    DEFVAL { 0 }
                    ::= { digitalObjects 636 }

        -- 1.3.6.1.4.1.9839.2.1.1.637
        pump OBJECT-TYPE
                    SYNTAX Integer32 (0..1)
                    UNITS "N/A"
                    MAX-ACCESS read-write
                    STATUS current
                    DESCRIPTION "N/A"
                    DEFVAL { 0 }
                    ::= { digitalObjects 637 }

        -- 1.3.6.1.4.1.9839.2.1.1.638
        min-speed-require OBJECT-TYPE
                    SYNTAX Integer32 (0..1)
                    UNITS "N/A"
                    MAX-ACCESS read-only
                    STATUS current
                    DESCRIPTION "N/A"
                    DEFVAL { 0 }
                    ::= { digitalObjects 638 }

        -- 1.3.6.1.4.1.9839.2.1.1.639
        reset-alarm OBJECT-TYPE
                    SYNTAX Integer32 (0..1)
                    UNITS "N/A"
                    MAX-ACCESS read-only
                    STATUS current
                    DESCRIPTION "Alarms reset by pressing the key ALARM from display"
                    DEFVAL { 0 }
                    ::= { digitalObjects 639 }

        -- 1.3.6.1.4.1.9839.2.1.1.640
        comp-1-req-actual OBJECT-TYPE
                    SYNTAX Integer32 (0..1)
                    UNITS "N/A"
                    MAX-ACCESS read-only
                    STATUS current
                    DESCRIPTION "N/A"
                    DEFVAL { 0 }
                    ::= { digitalObjects 640 }

        -- 1.3.6.1.4.1.9839.2.1.1.641
        en-evd-evo OBJECT-TYPE
                    SYNTAX Integer32 (0..1)
                    UNITS "N/A"
                    MAX-ACCESS read-only
                    STATUS current
                    DESCRIPTION "at leat one valve is configured and so eved evo management enabled"
                    DEFVAL { 0 }
                    ::= { digitalObjects 641 }

        -- 1.3.6.1.4.1.9839.2.1.1.642
        enable-2nd-evap OBJECT-TYPE
                    SYNTAX Integer32 (0..1)
                    UNITS "N/A"
                    MAX-ACCESS read-only
                    STATUS current
                    DESCRIPTION "N/A"
                    DEFVAL { 0 }
                    ::= { digitalObjects 642 }

        -- 1.3.6.1.4.1.9839.2.1.1.643
        fs-aps-control OBJECT-TYPE
                    SYNTAX Integer32 (0..1)
                    UNITS "N/A"
                    MAX-ACCESS read-only
                    STATUS current
                    DESCRIPTION "Fan speed APS (under floor pressure control)"
                    DEFVAL { 0 }
                    ::= { digitalObjects 643 }

        -- 1.3.6.1.4.1.9839.2.1.1.644
        aps-manual-fan-en OBJECT-TYPE
                    SYNTAX Integer32 (0..1)
                    UNITS "N/A"
                    MAX-ACCESS read-write
                    STATUS current
                    DESCRIPTION "N/A"
                    DEFVAL { 0 }
                    ::= { digitalObjects 644 }

        -- 1.3.6.1.4.1.9839.2.1.1.645
        fan-tickover-required OBJECT-TYPE
                    SYNTAX Integer32 (0..1)
                    UNITS "N/A"
                    MAX-ACCESS read-only
                    STATUS current
                    DESCRIPTION "N/A"
                    DEFVAL { 0 }
                    ::= { digitalObjects 645 }

        -- 1.3.6.1.4.1.9839.2.1.1.646
        comp-1-lead OBJECT-TYPE
                    SYNTAX Integer32 (0..1)
                    UNITS "N/A"
                    MAX-ACCESS read-only
                    STATUS current
                    DESCRIPTION "N/A"
                    DEFVAL { 0 }
                    ::= { digitalObjects 646 }

        -- 1.3.6.1.4.1.9839.2.1.1.647
        comp-2-lead OBJECT-TYPE
                    SYNTAX Integer32 (0..1)
                    UNITS "N/A"
                    MAX-ACCESS read-only
                    STATUS current
                    DESCRIPTION "N/A"
                    DEFVAL { 0 }
                    ::= { digitalObjects 647 }

        -- 1.3.6.1.4.1.9839.2.1.1.648
        comp-1-lead-not OBJECT-TYPE
                    SYNTAX Integer32 (0..1)
                    UNITS "N/A"
                    MAX-ACCESS read-only
                    STATUS current
                    DESCRIPTION "N/A"
                    DEFVAL { 0 }
                    ::= { digitalObjects 648 }

        -- 1.3.6.1.4.1.9839.2.1.1.649
        comp-2-lead-not OBJECT-TYPE
                    SYNTAX Integer32 (0..1)
                    UNITS "N/A"
                    MAX-ACCESS read-only
                    STATUS current
                    DESCRIPTION "N/A"
                    DEFVAL { 0 }
                    ::= { digitalObjects 649 }

        -- 1.3.6.1.4.1.9839.2.1.1.650
        vk-default-wait OBJECT-TYPE
                    SYNTAX Integer32 (0..1)
                    UNITS "N/A"
                    MAX-ACCESS read-only
                    STATUS current
                    DESCRIPTION "N/A"
                    DEFVAL { 0 }
                    ::= { digitalObjects 650 }

        -- 1.3.6.1.4.1.9839.2.1.1.1100
        abletooff-bldc-1 OBJECT-TYPE
                    SYNTAX Integer32 (0..1)
                    UNITS "N/A"
                    MAX-ACCESS read-only
                    STATUS current
                    DESCRIPTION "Minimum on time elapsed"
                    DEFVAL { 0 }
                    ::= { digitalObjects 1100 }

        -- 1.3.6.1.4.1.9839.2.1.1.1101
        abletoon-bldc-1 OBJECT-TYPE
                    SYNTAX Integer32 (0..1)
                    UNITS "N/A"
                    MAX-ACCESS read-only
                    STATUS current
                    DESCRIPTION "Minimum off time elapsed"
                    DEFVAL { 0 }
                    ::= { digitalObjects 1101 }

        -- 1.3.6.1.4.1.9839.2.1.1.1102
        al-deltap-bldc-1 OBJECT-TYPE
                    SYNTAX Integer32 (0..1)
                    UNITS "N/A"
                    MAX-ACCESS read-only
                    STATUS current
                    DESCRIPTION "Low pressure difference alarm"
                    DEFVAL { 0 }
                    ::= { digitalObjects 1102 }

        -- 1.3.6.1.4.1.9839.2.1.1.1103
        alrmcompoff-bldc-1 OBJECT-TYPE
                    SYNTAX Integer32 (0..1)
                    UNITS "N/A"
                    MAX-ACCESS read-only
                    STATUS current
                    DESCRIPTION "Alarm state that shut off compressor"
                    DEFVAL { 0 }
                    ::= { digitalObjects 1103 }

        -- 1.3.6.1.4.1.9839.2.1.1.1104
        can-run-bldc-1 OBJECT-TYPE
                    SYNTAX Integer32 (0..1)
                    UNITS "N/A"
                    MAX-ACCESS read-only
                    STATUS current
                    DESCRIPTION "N/A"
                    DEFVAL { 0 }
                    ::= { digitalObjects 1104 }

        -- 1.3.6.1.4.1.9839.2.1.1.1105
        compon-bldc-1 OBJECT-TYPE
                    SYNTAX Integer32 (0..1)
                    UNITS "N/A"
                    MAX-ACCESS read-only
                    STATUS current
                    DESCRIPTION "Compressor power on"
                    DEFVAL { 0 }
                    ::= { digitalObjects 1105 }

        -- 1.3.6.1.4.1.9839.2.1.1.1106
        compreq-bldc-1 OBJECT-TYPE
                    SYNTAX Integer32 (0..1)
                    UNITS "N/A"
                    MAX-ACCESS read-write
                    STATUS current
                    DESCRIPTION "Request to switch on/off compressor (used for shut down procedure)"
                    DEFVAL { 0 }
                    ::= { digitalObjects 1106 }

        -- 1.3.6.1.4.1.9839.2.1.1.1107
        compreq-bldc-1-tmp OBJECT-TYPE
                    SYNTAX Integer32 (0..1)
                    UNITS "N/A"
                    MAX-ACCESS read-write
                    STATUS current
                    DESCRIPTION "Request to switch on/off compressor (used for shut down procedure)"
                    DEFVAL { 0 }
                    ::= { digitalObjects 1107 }

        -- 1.3.6.1.4.1.9839.2.1.1.1108
        compsaft-res-bldc-1 OBJECT-TYPE
                    SYNTAX Integer32 (0..1)
                    UNITS "N/A"
                    MAX-ACCESS read-only
                    STATUS current
                    DESCRIPTION "Request to reset of compressor safety timing (starting failure repair)"
                    DEFVAL { 0 }
                    ::= { digitalObjects 1108 }

        -- 1.3.6.1.4.1.9839.2.1.1.1109
        en-oil-mng-bldc-1 OBJECT-TYPE
                    SYNTAX Integer32 (0..1)
                    UNITS "N/A"
                    MAX-ACCESS read-write
                    STATUS current
                    DESCRIPTION "N/A"
                    DEFVAL { 0 }
                    ::= { digitalObjects 1109 }

        -- 1.3.6.1.4.1.9839.2.1.1.1110
        envalrm-bldc-1 OBJECT-TYPE
                    SYNTAX Integer32 (0..1)
                    UNITS "N/A"
                    MAX-ACCESS read-only
                    STATUS current
                    DESCRIPTION "Out of envelop alarm"
                    DEFVAL { 0 }
                    ::= { digitalObjects 1110 }

        -- 1.3.6.1.4.1.9839.2.1.1.1111
        eqvlvcmd-bldc-1 OBJECT-TYPE
                    SYNTAX Integer32 (0..1)
                    UNITS "N/A"
                    MAX-ACCESS read-only
                    STATUS current
                    DESCRIPTION "Equalization solenoid valve output"
                    DEFVAL { 0 }
                    ::= { digitalObjects 1111 }

        -- 1.3.6.1.4.1.9839.2.1.1.1112
        errflag-bldc-1 OBJECT-TYPE
                    SYNTAX Integer32 (0..1)
                    UNITS "N/A"
                    MAX-ACCESS read-only
                    STATUS current
                    DESCRIPTION "Default values not load"
                    DEFVAL { 0 }
                    ::= { digitalObjects 1112 }

        -- 1.3.6.1.4.1.9839.2.1.1.1113
        frcoff-bldc-1 OBJECT-TYPE
                    SYNTAX Integer32 (0..1)
                    UNITS "N/A"
                    MAX-ACCESS read-only
                    STATUS current
                    DESCRIPTION "Compressor forced off"
                    DEFVAL { 0 }
                    ::= { digitalObjects 1113 }

        -- 1.3.6.1.4.1.9839.2.1.1.1114
        gotominspeed-bldc-1 OBJECT-TYPE
                    SYNTAX Integer32 (0..1)
                    UNITS "N/A"
                    MAX-ACCESS read-write
                    STATUS current
                    DESCRIPTION "Force compressor down to min speed"
                    DEFVAL { 0 }
                    ::= { digitalObjects 1114 }

        -- 1.3.6.1.4.1.9839.2.1.1.1115
        gotominspeed-bldc-1-inv OBJECT-TYPE
                    SYNTAX Integer32 (0..1)
                    UNITS "N/A"
                    MAX-ACCESS read-write
                    STATUS current
                    DESCRIPTION "Force compressor down to min speed"
                    DEFVAL { 0 }
                    ::= { digitalObjects 1115 }

        -- 1.3.6.1.4.1.9839.2.1.1.1116
        oralstartfail-bldc-1 OBJECT-TYPE
                    SYNTAX Integer32 (0..1)
                    UNITS "N/A"
                    MAX-ACCESS read-only
                    STATUS current
                    DESCRIPTION "Compressor fails to start alarm"
                    DEFVAL { 0 }
                    ::= { digitalObjects 1116 }

        -- 1.3.6.1.4.1.9839.2.1.1.1117
        orcompalrm-bldc-1 OBJECT-TYPE
                    SYNTAX Integer32 (0..1)
                    UNITS "N/A"
                    MAX-ACCESS read-only
                    STATUS current
                    DESCRIPTION "Alarm state that shut off compressor"
                    DEFVAL { 0 }
                    ::= { digitalObjects 1117 }

        -- 1.3.6.1.4.1.9839.2.1.1.1118
        specificparam-bldc-1 OBJECT-TYPE
                    SYNTAX Integer32 (0..1)
                    UNITS "N/A"
                    MAX-ACCESS read-write
                    STATUS current
                    DESCRIPTION "Use specific parameters (Max acceleration; enevelope alarm delay)"
                    DEFVAL { 0 }
                    ::= { digitalObjects 1118 }

        -- 1.3.6.1.4.1.9839.2.1.1.1119
        specificparam-bldc-1-inv OBJECT-TYPE
                    SYNTAX Integer32 (0..1)
                    UNITS "N/A"
                    MAX-ACCESS read-write
                    STATUS current
                    DESCRIPTION "Use specific parameters (Max acceleration; enevelope alarm delay)"
                    DEFVAL { 0 }
                    ::= { digitalObjects 1119 }

        -- 1.3.6.1.4.1.9839.2.1.1.1120
        vfd-res-bldc-1 OBJECT-TYPE
                    SYNTAX Integer32 (0..1)
                    UNITS "N/A"
                    MAX-ACCESS read-only
                    STATUS current
                    DESCRIPTION "Inverter alarm reset command"
                    DEFVAL { 0 }
                    ::= { digitalObjects 1120 }

        -- 1.3.6.1.4.1.9839.2.1.1.1121
        oil-return-request-bldc-1 OBJECT-TYPE
                    SYNTAX Integer32 (0..1)
                    UNITS "N/A"
                    MAX-ACCESS read-only
                    STATUS current
                    DESCRIPTION "N/A"
                    DEFVAL { 0 }
                    ::= { digitalObjects 1121 }

        -- 1.3.6.1.4.1.9839.2.1.1.1150
        al-hightempdscg-bldc-1 OBJECT-TYPE
                    SYNTAX Integer32 (0..1)
                    UNITS "N/A"
                    MAX-ACCESS read-write
                    STATUS current
                    DESCRIPTION "Discharge temperature alarm"
                    DEFVAL { 0 }
                    ::= { digitalObjects 1150 }

        -- 1.3.6.1.4.1.9839.2.1.1.1151
        al-offline-pwrp-1 OBJECT-TYPE
                    SYNTAX Integer32 (0..1)
                    UNITS "N/A"
                    MAX-ACCESS read-only
                    STATUS current
                    DESCRIPTION "Alarm Power+ offline "
                    DEFVAL { 0 }
                    ::= { digitalObjects 1151 }

        -- 1.3.6.1.4.1.9839.2.1.1.1152
        alrmres-pwrp-1 OBJECT-TYPE
                    SYNTAX Integer32 (0..1)
                    UNITS "N/A"
                    MAX-ACCESS read-write
                    STATUS current
                    DESCRIPTION "Reset alarms of Powerplus"
                    DEFVAL { 0 }
                    ::= { digitalObjects 1152 }

        -- 1.3.6.1.4.1.9839.2.1.1.1153
        vfd-alrm-pwrp-1 OBJECT-TYPE
                    SYNTAX Integer32 (0..1)
                    UNITS "N/A"
                    MAX-ACCESS read-only
                    STATUS current
                    DESCRIPTION "General Inverter Alarm"
                    DEFVAL { 0 }
                    ::= { digitalObjects 1153 }

        -- 1.3.6.1.4.1.9839.2.1.1.1155
        al-01-overcurrent-pwrp-1 OBJECT-TYPE
                    SYNTAX Integer32 (0..1)
                    UNITS "N/A"
                    MAX-ACCESS read-only
                    STATUS current
                    DESCRIPTION "N/A"
                    DEFVAL { 0 }
                    ::= { digitalObjects 1155 }

        -- 1.3.6.1.4.1.9839.2.1.1.1156
        al-02-motoroverload-pwrp-1 OBJECT-TYPE
                    SYNTAX Integer32 (0..1)
                    UNITS "N/A"
                    MAX-ACCESS read-only
                    STATUS current
                    DESCRIPTION "N/A"
                    DEFVAL { 0 }
                    ::= { digitalObjects 1156 }

        -- 1.3.6.1.4.1.9839.2.1.1.1157
        al-03-overvoltage-pwrp-1 OBJECT-TYPE
                    SYNTAX Integer32 (0..1)
                    UNITS "N/A"
                    MAX-ACCESS read-only
                    STATUS current
                    DESCRIPTION "N/A"
                    DEFVAL { 0 }
                    ::= { digitalObjects 1157 }

        -- 1.3.6.1.4.1.9839.2.1.1.1158
        al-04-undervoltage-pwrp-1 OBJECT-TYPE
                    SYNTAX Integer32 (0..1)
                    UNITS "N/A"
                    MAX-ACCESS read-only
                    STATUS current
                    DESCRIPTION "N/A"
                    DEFVAL { 0 }
                    ::= { digitalObjects 1158 }

        -- 1.3.6.1.4.1.9839.2.1.1.1159
        al-05-driveovert-pwrp-1 OBJECT-TYPE
                    SYNTAX Integer32 (0..1)
                    UNITS "N/A"
                    MAX-ACCESS read-only
                    STATUS current
                    DESCRIPTION "N/A"
                    DEFVAL { 0 }
                    ::= { digitalObjects 1159 }

        -- 1.3.6.1.4.1.9839.2.1.1.1160
        al-06-driveundert-pwrp-1 OBJECT-TYPE
                    SYNTAX Integer32 (0..1)
                    UNITS "N/A"
                    MAX-ACCESS read-only
                    STATUS current
                    DESCRIPTION "N/A"
                    DEFVAL { 0 }
                    ::= { digitalObjects 1160 }

        -- 1.3.6.1.4.1.9839.2.1.1.1161
        al-07-overcurrenthw-pwrp-1 OBJECT-TYPE
                    SYNTAX Integer32 (0..1)
                    UNITS "N/A"
                    MAX-ACCESS read-only
                    STATUS current
                    DESCRIPTION "N/A"
                    DEFVAL { 0 }
                    ::= { digitalObjects 1161 }

        -- 1.3.6.1.4.1.9839.2.1.1.1162
        al-08-motorovertemp-pwrp-1 OBJECT-TYPE
                    SYNTAX Integer32 (0..1)
                    UNITS "N/A"
                    MAX-ACCESS read-only
                    STATUS current
                    DESCRIPTION "N/A"
                    DEFVAL { 0 }
                    ::= { digitalObjects 1162 }

        -- 1.3.6.1.4.1.9839.2.1.1.1163
        al-09-drivefailure-pwrp-1 OBJECT-TYPE
                    SYNTAX Integer32 (0..1)
                    UNITS "N/A"
                    MAX-ACCESS read-only
                    STATUS current
                    DESCRIPTION "N/A"
                    DEFVAL { 0 }
                    ::= { digitalObjects 1163 }

        -- 1.3.6.1.4.1.9839.2.1.1.1164
        al-10-cpu-error-pwrp-1 OBJECT-TYPE
                    SYNTAX Integer32 (0..1)
                    UNITS "N/A"
                    MAX-ACCESS read-only
                    STATUS current
                    DESCRIPTION "N/A"
                    DEFVAL { 0 }
                    ::= { digitalObjects 1164 }

        -- 1.3.6.1.4.1.9839.2.1.1.1165
        al-11-paramdefault-pwrp-1 OBJECT-TYPE
                    SYNTAX Integer32 (0..1)
                    UNITS "N/A"
                    MAX-ACCESS read-only
                    STATUS current
                    DESCRIPTION "N/A"
                    DEFVAL { 0 }
                    ::= { digitalObjects 1165 }

        -- 1.3.6.1.4.1.9839.2.1.1.1166
        al-12-dc-busripple-pwrp-1 OBJECT-TYPE
                    SYNTAX Integer32 (0..1)
                    UNITS "N/A"
                    MAX-ACCESS read-only
                    STATUS current
                    DESCRIPTION "N/A"
                    DEFVAL { 0 }
                    ::= { digitalObjects 1166 }

        -- 1.3.6.1.4.1.9839.2.1.1.1167
        al-13-datacommsfault-pwrp-1 OBJECT-TYPE
                    SYNTAX Integer32 (0..1)
                    UNITS "N/A"
                    MAX-ACCESS read-only
                    STATUS current
                    DESCRIPTION "N/A"
                    DEFVAL { 0 }
                    ::= { digitalObjects 1167 }

        -- 1.3.6.1.4.1.9839.2.1.1.1168
        al-14-drivethermistor-pwrp-1 OBJECT-TYPE
                    SYNTAX Integer32 (0..1)
                    UNITS "N/A"
                    MAX-ACCESS read-only
                    STATUS current
                    DESCRIPTION "N/A"
                    DEFVAL { 0 }
                    ::= { digitalObjects 1168 }

        -- 1.3.6.1.4.1.9839.2.1.1.1169
        al-15-autotunefault-pwrp-1 OBJECT-TYPE
                    SYNTAX Integer32 (0..1)
                    UNITS "N/A"
                    MAX-ACCESS read-only
                    STATUS current
                    DESCRIPTION "N/A"
                    DEFVAL { 0 }
                    ::= { digitalObjects 1169 }

        -- 1.3.6.1.4.1.9839.2.1.1.1170
        al-16-drivedisabled-pwrp-1 OBJECT-TYPE
                    SYNTAX Integer32 (0..1)
                    UNITS "N/A"
                    MAX-ACCESS read-only
                    STATUS current
                    DESCRIPTION "N/A"
                    DEFVAL { 0 }
                    ::= { digitalObjects 1170 }

        -- 1.3.6.1.4.1.9839.2.1.1.1171
        al-17-motorphase-pwrp-1 OBJECT-TYPE
                    SYNTAX Integer32 (0..1)
                    UNITS "N/A"
                    MAX-ACCESS read-only
                    STATUS current
                    DESCRIPTION "N/A"
                    DEFVAL { 0 }
                    ::= { digitalObjects 1171 }

        -- 1.3.6.1.4.1.9839.2.1.1.1172
        al-18-fanfault-pwrp-1 OBJECT-TYPE
                    SYNTAX Integer32 (0..1)
                    UNITS "N/A"
                    MAX-ACCESS read-only
                    STATUS current
                    DESCRIPTION "N/A"
                    DEFVAL { 0 }
                    ::= { digitalObjects 1172 }

        -- 1.3.6.1.4.1.9839.2.1.1.1173
        al-19-speedfault-pwrp-1 OBJECT-TYPE
                    SYNTAX Integer32 (0..1)
                    UNITS "N/A"
                    MAX-ACCESS read-only
                    STATUS current
                    DESCRIPTION "N/A"
                    DEFVAL { 0 }
                    ::= { digitalObjects 1173 }

        -- 1.3.6.1.4.1.9839.2.1.1.1174
        al-20-pfc-failure-pwrp-1 OBJECT-TYPE
                    SYNTAX Integer32 (0..1)
                    UNITS "N/A"
                    MAX-ACCESS read-only
                    STATUS current
                    DESCRIPTION "N/A"
                    DEFVAL { 0 }
                    ::= { digitalObjects 1174 }

        -- 1.3.6.1.4.1.9839.2.1.1.1175
        al-21-errorcode21-pwrp-1 OBJECT-TYPE
                    SYNTAX Integer32 (0..1)
                    UNITS "N/A"
                    MAX-ACCESS read-only
                    STATUS current
                    DESCRIPTION "N/A"
                    DEFVAL { 0 }
                    ::= { digitalObjects 1175 }

        -- 1.3.6.1.4.1.9839.2.1.1.1176
        al-22-pfc-undervoltage-pwrp-1 OBJECT-TYPE
                    SYNTAX Integer32 (0..1)
                    UNITS "N/A"
                    MAX-ACCESS read-only
                    STATUS current
                    DESCRIPTION "N/A"
                    DEFVAL { 0 }
                    ::= { digitalObjects 1176 }

        -- 1.3.6.1.4.1.9839.2.1.1.1177
        al-23-sto-surveyfail-pwrp-1 OBJECT-TYPE
                    SYNTAX Integer32 (0..1)
                    UNITS "N/A"
                    MAX-ACCESS read-only
                    STATUS current
                    DESCRIPTION "N/A"
                    DEFVAL { 0 }
                    ::= { digitalObjects 1177 }

        -- 1.3.6.1.4.1.9839.2.1.1.1178
        al-24-sto-surveyfail-pwrp-1 OBJECT-TYPE
                    SYNTAX Integer32 (0..1)
                    UNITS "N/A"
                    MAX-ACCESS read-only
                    STATUS current
                    DESCRIPTION "N/A"
                    DEFVAL { 0 }
                    ::= { digitalObjects 1178 }

        -- 1.3.6.1.4.1.9839.2.1.1.1179
        al-25-errorcode25-pwrp-1 OBJECT-TYPE
                    SYNTAX Integer32 (0..1)
                    UNITS "N/A"
                    MAX-ACCESS read-only
                    STATUS current
                    DESCRIPTION "N/A"
                    DEFVAL { 0 }
                    ::= { digitalObjects 1179 }

        -- 1.3.6.1.4.1.9839.2.1.1.1180
        al-26-errorcode26-pwrp-1 OBJECT-TYPE
                    SYNTAX Integer32 (0..1)
                    UNITS "N/A"
                    MAX-ACCESS read-only
                    STATUS current
                    DESCRIPTION "N/A"
                    DEFVAL { 0 }
                    ::= { digitalObjects 1180 }

        -- 1.3.6.1.4.1.9839.2.1.1.1181
        al-27-errorcode27-pwrp-1 OBJECT-TYPE
                    SYNTAX Integer32 (0..1)
                    UNITS "N/A"
                    MAX-ACCESS read-only
                    STATUS current
                    DESCRIPTION "N/A"
                    DEFVAL { 0 }
                    ::= { digitalObjects 1181 }

        -- 1.3.6.1.4.1.9839.2.1.1.1182
        al-28-errorcode28-pwrp-1 OBJECT-TYPE
                    SYNTAX Integer32 (0..1)
                    UNITS "N/A"
                    MAX-ACCESS read-only
                    STATUS current
                    DESCRIPTION "N/A"
                    DEFVAL { 0 }
                    ::= { digitalObjects 1182 }

        -- 1.3.6.1.4.1.9839.2.1.1.1183
        al-29-errorcode28-pwrp-1 OBJECT-TYPE
                    SYNTAX Integer32 (0..1)
                    UNITS "N/A"
                    MAX-ACCESS read-only
                    STATUS current
                    DESCRIPTION "N/A"
                    DEFVAL { 0 }
                    ::= { digitalObjects 1183 }

        -- 1.3.6.1.4.1.9839.2.1.1.1184
        al-30-errorcode30-pwrp-1 OBJECT-TYPE
                    SYNTAX Integer32 (0..1)
                    UNITS "N/A"
                    MAX-ACCESS read-only
                    STATUS current
                    DESCRIPTION "N/A"
                    DEFVAL { 0 }
                    ::= { digitalObjects 1184 }

        -- 1.3.6.1.4.1.9839.2.1.1.1200
        abletooff-bldc-2 OBJECT-TYPE
                    SYNTAX Integer32 (0..1)
                    UNITS "N/A"
                    MAX-ACCESS read-only
                    STATUS current
                    DESCRIPTION "Minimum on time elapsed"
                    DEFVAL { 0 }
                    ::= { digitalObjects 1200 }

        -- 1.3.6.1.4.1.9839.2.1.1.1201
        abletoon-bldc-2 OBJECT-TYPE
                    SYNTAX Integer32 (0..1)
                    UNITS "N/A"
                    MAX-ACCESS read-only
                    STATUS current
                    DESCRIPTION "Minimum off time elapsed"
                    DEFVAL { 0 }
                    ::= { digitalObjects 1201 }

        -- 1.3.6.1.4.1.9839.2.1.1.1202
        al-deltap-bldc-2 OBJECT-TYPE
                    SYNTAX Integer32 (0..1)
                    UNITS "N/A"
                    MAX-ACCESS read-only
                    STATUS current
                    DESCRIPTION "Low pressure difference alarm"
                    DEFVAL { 0 }
                    ::= { digitalObjects 1202 }

        -- 1.3.6.1.4.1.9839.2.1.1.1203
        alrmcompoff-bldc-2 OBJECT-TYPE
                    SYNTAX Integer32 (0..1)
                    UNITS "N/A"
                    MAX-ACCESS read-only
                    STATUS current
                    DESCRIPTION "Alarm state that shut off compressor"
                    DEFVAL { 0 }
                    ::= { digitalObjects 1203 }

        -- 1.3.6.1.4.1.9839.2.1.1.1204
        can-run-bldc-2 OBJECT-TYPE
                    SYNTAX Integer32 (0..1)
                    UNITS "N/A"
                    MAX-ACCESS read-only
                    STATUS current
                    DESCRIPTION "N/A"
                    DEFVAL { 0 }
                    ::= { digitalObjects 1204 }

        -- 1.3.6.1.4.1.9839.2.1.1.1205
        compon-bldc-2 OBJECT-TYPE
                    SYNTAX Integer32 (0..1)
                    UNITS "N/A"
                    MAX-ACCESS read-only
                    STATUS current
                    DESCRIPTION "Compressor power on"
                    DEFVAL { 0 }
                    ::= { digitalObjects 1205 }

        -- 1.3.6.1.4.1.9839.2.1.1.1206
        compreq-bldc-2 OBJECT-TYPE
                    SYNTAX Integer32 (0..1)
                    UNITS "N/A"
                    MAX-ACCESS read-write
                    STATUS current
                    DESCRIPTION "Request to switch on/off compressor (used for shut down procedure)"
                    DEFVAL { 0 }
                    ::= { digitalObjects 1206 }

        -- 1.3.6.1.4.1.9839.2.1.1.1207
        compreq-bldc-2-tmp OBJECT-TYPE
                    SYNTAX Integer32 (0..1)
                    UNITS "N/A"
                    MAX-ACCESS read-write
                    STATUS current
                    DESCRIPTION "Request to switch on/off compressor (used for shut down procedure)"
                    DEFVAL { 0 }
                    ::= { digitalObjects 1207 }

        -- 1.3.6.1.4.1.9839.2.1.1.1208
        compsaft-res-bldc-2 OBJECT-TYPE
                    SYNTAX Integer32 (0..1)
                    UNITS "N/A"
                    MAX-ACCESS read-only
                    STATUS current
                    DESCRIPTION "Request to reset of compressor safety timing (starting failure repair)"
                    DEFVAL { 0 }
                    ::= { digitalObjects 1208 }

        -- 1.3.6.1.4.1.9839.2.1.1.1209
        en-oil-mng-bldc-2 OBJECT-TYPE
                    SYNTAX Integer32 (0..1)
                    UNITS "N/A"
                    MAX-ACCESS read-write
                    STATUS current
                    DESCRIPTION "N/A"
                    DEFVAL { 0 }
                    ::= { digitalObjects 1209 }

        -- 1.3.6.1.4.1.9839.2.1.1.1210
        envalrm-bldc-2 OBJECT-TYPE
                    SYNTAX Integer32 (0..1)
                    UNITS "N/A"
                    MAX-ACCESS read-only
                    STATUS current
                    DESCRIPTION "Out of envelop alarm"
                    DEFVAL { 0 }
                    ::= { digitalObjects 1210 }

        -- 1.3.6.1.4.1.9839.2.1.1.1211
        eqvlvcmd-bldc-2 OBJECT-TYPE
                    SYNTAX Integer32 (0..1)
                    UNITS "N/A"
                    MAX-ACCESS read-only
                    STATUS current
                    DESCRIPTION "Equalization solenoid valve output"
                    DEFVAL { 0 }
                    ::= { digitalObjects 1211 }

        -- 1.3.6.1.4.1.9839.2.1.1.1212
        errflag-bldc-2 OBJECT-TYPE
                    SYNTAX Integer32 (0..1)
                    UNITS "N/A"
                    MAX-ACCESS read-only
                    STATUS current
                    DESCRIPTION "Default values not load"
                    DEFVAL { 0 }
                    ::= { digitalObjects 1212 }

        -- 1.3.6.1.4.1.9839.2.1.1.1213
        frcoff-bldc-2 OBJECT-TYPE
                    SYNTAX Integer32 (0..1)
                    UNITS "N/A"
                    MAX-ACCESS read-only
                    STATUS current
                    DESCRIPTION "Compressor forced off"
                    DEFVAL { 0 }
                    ::= { digitalObjects 1213 }

        -- 1.3.6.1.4.1.9839.2.1.1.1214
        gotominspeed-bldc-2-inv OBJECT-TYPE
                    SYNTAX Integer32 (0..1)
                    UNITS "N/A"
                    MAX-ACCESS read-write
                    STATUS current
                    DESCRIPTION "Force compressor down to min speed"
                    DEFVAL { 0 }
                    ::= { digitalObjects 1214 }

        -- 1.3.6.1.4.1.9839.2.1.1.1215
        oralstartfail-bldc-2 OBJECT-TYPE
                    SYNTAX Integer32 (0..1)
                    UNITS "N/A"
                    MAX-ACCESS read-only
                    STATUS current
                    DESCRIPTION "Compressor fails to start alarm"
                    DEFVAL { 0 }
                    ::= { digitalObjects 1215 }

        -- 1.3.6.1.4.1.9839.2.1.1.1216
        orcompalrm-bldc-2 OBJECT-TYPE
                    SYNTAX Integer32 (0..1)
                    UNITS "N/A"
                    MAX-ACCESS read-only
                    STATUS current
                    DESCRIPTION "Alarm state that shut off compressor"
                    DEFVAL { 0 }
                    ::= { digitalObjects 1216 }

        -- 1.3.6.1.4.1.9839.2.1.1.1217
        specificparam-bldc-2-inv OBJECT-TYPE
                    SYNTAX Integer32 (0..1)
                    UNITS "N/A"
                    MAX-ACCESS read-write
                    STATUS current
                    DESCRIPTION "Use specific parameters (Max acceleration; enevelope alarm delay)"
                    DEFVAL { 0 }
                    ::= { digitalObjects 1217 }

        -- 1.3.6.1.4.1.9839.2.1.1.1218
        vfd-res-bldc-2 OBJECT-TYPE
                    SYNTAX Integer32 (0..1)
                    UNITS "N/A"
                    MAX-ACCESS read-only
                    STATUS current
                    DESCRIPTION "Inverter alarm reset command"
                    DEFVAL { 0 }
                    ::= { digitalObjects 1218 }

        -- 1.3.6.1.4.1.9839.2.1.1.1219
        oil-return-request-bldc-2 OBJECT-TYPE
                    SYNTAX Integer32 (0..1)
                    UNITS "N/A"
                    MAX-ACCESS read-only
                    STATUS current
                    DESCRIPTION "N/A"
                    DEFVAL { 0 }
                    ::= { digitalObjects 1219 }

        -- 1.3.6.1.4.1.9839.2.1.1.1250
        al-hightempdscg-bldc-2 OBJECT-TYPE
                    SYNTAX Integer32 (0..1)
                    UNITS "N/A"
                    MAX-ACCESS read-write
                    STATUS current
                    DESCRIPTION "Discharge temperature alarm"
                    DEFVAL { 0 }
                    ::= { digitalObjects 1250 }

        -- 1.3.6.1.4.1.9839.2.1.1.1251
        al-offline-pwrp-2 OBJECT-TYPE
                    SYNTAX Integer32 (0..1)
                    UNITS "N/A"
                    MAX-ACCESS read-only
                    STATUS current
                    DESCRIPTION "Alarm Power+ offline "
                    DEFVAL { 0 }
                    ::= { digitalObjects 1251 }

        -- 1.3.6.1.4.1.9839.2.1.1.1252
        alrmres-pwrp-2 OBJECT-TYPE
                    SYNTAX Integer32 (0..1)
                    UNITS "N/A"
                    MAX-ACCESS read-write
                    STATUS current
                    DESCRIPTION "Reset alarms of Powerplus"
                    DEFVAL { 0 }
                    ::= { digitalObjects 1252 }

        -- 1.3.6.1.4.1.9839.2.1.1.1253
        vfd-alrm-pwrp-2 OBJECT-TYPE
                    SYNTAX Integer32 (0..1)
                    UNITS "N/A"
                    MAX-ACCESS read-only
                    STATUS current
                    DESCRIPTION "General Inverter Alarm"
                    DEFVAL { 0 }
                    ::= { digitalObjects 1253 }

        -- 1.3.6.1.4.1.9839.2.1.1.1255
        al-01-overcurrent-pwrp-2 OBJECT-TYPE
                    SYNTAX Integer32 (0..1)
                    UNITS "N/A"
                    MAX-ACCESS read-only
                    STATUS current
                    DESCRIPTION "N/A"
                    DEFVAL { 0 }
                    ::= { digitalObjects 1255 }

        -- 1.3.6.1.4.1.9839.2.1.1.1256
        al-02-motoroverload-pwrp-2 OBJECT-TYPE
                    SYNTAX Integer32 (0..1)
                    UNITS "N/A"
                    MAX-ACCESS read-only
                    STATUS current
                    DESCRIPTION "N/A"
                    DEFVAL { 0 }
                    ::= { digitalObjects 1256 }

        -- 1.3.6.1.4.1.9839.2.1.1.1257
        al-03-overvoltage-pwrp-2 OBJECT-TYPE
                    SYNTAX Integer32 (0..1)
                    UNITS "N/A"
                    MAX-ACCESS read-only
                    STATUS current
                    DESCRIPTION "N/A"
                    DEFVAL { 0 }
                    ::= { digitalObjects 1257 }

        -- 1.3.6.1.4.1.9839.2.1.1.1258
        al-04-undervoltage-pwrp-2 OBJECT-TYPE
                    SYNTAX Integer32 (0..1)
                    UNITS "N/A"
                    MAX-ACCESS read-only
                    STATUS current
                    DESCRIPTION "N/A"
                    DEFVAL { 0 }
                    ::= { digitalObjects 1258 }

        -- 1.3.6.1.4.1.9839.2.1.1.1259
        al-05-driveovert-pwrp-2 OBJECT-TYPE
                    SYNTAX Integer32 (0..1)
                    UNITS "N/A"
                    MAX-ACCESS read-only
                    STATUS current
                    DESCRIPTION "N/A"
                    DEFVAL { 0 }
                    ::= { digitalObjects 1259 }

        -- 1.3.6.1.4.1.9839.2.1.1.1260
        al-06-driveundert-pwrp-2 OBJECT-TYPE
                    SYNTAX Integer32 (0..1)
                    UNITS "N/A"
                    MAX-ACCESS read-only
                    STATUS current
                    DESCRIPTION "N/A"
                    DEFVAL { 0 }
                    ::= { digitalObjects 1260 }

        -- 1.3.6.1.4.1.9839.2.1.1.1261
        al-07-overcurrenthw-pwrp-2 OBJECT-TYPE
                    SYNTAX Integer32 (0..1)
                    UNITS "N/A"
                    MAX-ACCESS read-only
                    STATUS current
                    DESCRIPTION "N/A"
                    DEFVAL { 0 }
                    ::= { digitalObjects 1261 }

        -- 1.3.6.1.4.1.9839.2.1.1.1262
        al-08-motorovertemp-pwrp-2 OBJECT-TYPE
                    SYNTAX Integer32 (0..1)
                    UNITS "N/A"
                    MAX-ACCESS read-only
                    STATUS current
                    DESCRIPTION "N/A"
                    DEFVAL { 0 }
                    ::= { digitalObjects 1262 }

        -- 1.3.6.1.4.1.9839.2.1.1.1263
        al-09-drivefailure-pwrp-2 OBJECT-TYPE
                    SYNTAX Integer32 (0..1)
                    UNITS "N/A"
                    MAX-ACCESS read-only
                    STATUS current
                    DESCRIPTION "N/A"
                    DEFVAL { 0 }
                    ::= { digitalObjects 1263 }

        -- 1.3.6.1.4.1.9839.2.1.1.1264
        al-10-cpu-error-pwrp-2 OBJECT-TYPE
                    SYNTAX Integer32 (0..1)
                    UNITS "N/A"
                    MAX-ACCESS read-only
                    STATUS current
                    DESCRIPTION "N/A"
                    DEFVAL { 0 }
                    ::= { digitalObjects 1264 }

        -- 1.3.6.1.4.1.9839.2.1.1.1265
        al-11-paramdefault-pwrp-2 OBJECT-TYPE
                    SYNTAX Integer32 (0..1)
                    UNITS "N/A"
                    MAX-ACCESS read-only
                    STATUS current
                    DESCRIPTION "N/A"
                    DEFVAL { 0 }
                    ::= { digitalObjects 1265 }

        -- 1.3.6.1.4.1.9839.2.1.1.1266
        al-12-dc-busripple-pwrp-2 OBJECT-TYPE
                    SYNTAX Integer32 (0..1)
                    UNITS "N/A"
                    MAX-ACCESS read-only
                    STATUS current
                    DESCRIPTION "N/A"
                    DEFVAL { 0 }
                    ::= { digitalObjects 1266 }

        -- 1.3.6.1.4.1.9839.2.1.1.1267
        al-13-datacommsfault-pwrp-2 OBJECT-TYPE
                    SYNTAX Integer32 (0..1)
                    UNITS "N/A"
                    MAX-ACCESS read-only
                    STATUS current
                    DESCRIPTION "N/A"
                    DEFVAL { 0 }
                    ::= { digitalObjects 1267 }

        -- 1.3.6.1.4.1.9839.2.1.1.1268
        al-14-drivethermistor-pwrp-2 OBJECT-TYPE
                    SYNTAX Integer32 (0..1)
                    UNITS "N/A"
                    MAX-ACCESS read-only
                    STATUS current
                    DESCRIPTION "N/A"
                    DEFVAL { 0 }
                    ::= { digitalObjects 1268 }

        -- 1.3.6.1.4.1.9839.2.1.1.1269
        al-15-autotunefault-pwrp-2 OBJECT-TYPE
                    SYNTAX Integer32 (0..1)
                    UNITS "N/A"
                    MAX-ACCESS read-only
                    STATUS current
                    DESCRIPTION "N/A"
                    DEFVAL { 0 }
                    ::= { digitalObjects 1269 }

        -- 1.3.6.1.4.1.9839.2.1.1.1270
        al-16-drivedisabled-pwrp-2 OBJECT-TYPE
                    SYNTAX Integer32 (0..1)
                    UNITS "N/A"
                    MAX-ACCESS read-only
                    STATUS current
                    DESCRIPTION "N/A"
                    DEFVAL { 0 }
                    ::= { digitalObjects 1270 }

        -- 1.3.6.1.4.1.9839.2.1.1.1271
        al-17-motorphase-pwrp-2 OBJECT-TYPE
                    SYNTAX Integer32 (0..1)
                    UNITS "N/A"
                    MAX-ACCESS read-only
                    STATUS current
                    DESCRIPTION "N/A"
                    DEFVAL { 0 }
                    ::= { digitalObjects 1271 }

        -- 1.3.6.1.4.1.9839.2.1.1.1272
        al-18-fanfault-pwrp-2 OBJECT-TYPE
                    SYNTAX Integer32 (0..1)
                    UNITS "N/A"
                    MAX-ACCESS read-only
                    STATUS current
                    DESCRIPTION "N/A"
                    DEFVAL { 0 }
                    ::= { digitalObjects 1272 }

        -- 1.3.6.1.4.1.9839.2.1.1.1273
        al-19-speedfault-pwrp-2 OBJECT-TYPE
                    SYNTAX Integer32 (0..1)
                    UNITS "N/A"
                    MAX-ACCESS read-only
                    STATUS current
                    DESCRIPTION "N/A"
                    DEFVAL { 0 }
                    ::= { digitalObjects 1273 }

        -- 1.3.6.1.4.1.9839.2.1.1.1274
        al-20-pfc-failure-pwrp-2 OBJECT-TYPE
                    SYNTAX Integer32 (0..1)
                    UNITS "N/A"
                    MAX-ACCESS read-only
                    STATUS current
                    DESCRIPTION "N/A"
                    DEFVAL { 0 }
                    ::= { digitalObjects 1274 }

        -- 1.3.6.1.4.1.9839.2.1.1.1275
        al-21-errorcode21-pwrp-2 OBJECT-TYPE
                    SYNTAX Integer32 (0..1)
                    UNITS "N/A"
                    MAX-ACCESS read-only
                    STATUS current
                    DESCRIPTION "N/A"
                    DEFVAL { 0 }
                    ::= { digitalObjects 1275 }

        -- 1.3.6.1.4.1.9839.2.1.1.1276
        al-22-pfc-undervoltage-pwrp-2 OBJECT-TYPE
                    SYNTAX Integer32 (0..1)
                    UNITS "N/A"
                    MAX-ACCESS read-only
                    STATUS current
                    DESCRIPTION "N/A"
                    DEFVAL { 0 }
                    ::= { digitalObjects 1276 }

        -- 1.3.6.1.4.1.9839.2.1.1.1277
        al-23-sto-surveyfail-pwrp-2 OBJECT-TYPE
                    SYNTAX Integer32 (0..1)
                    UNITS "N/A"
                    MAX-ACCESS read-only
                    STATUS current
                    DESCRIPTION "N/A"
                    DEFVAL { 0 }
                    ::= { digitalObjects 1277 }

        -- 1.3.6.1.4.1.9839.2.1.1.1278
        al-24-sto-surveyfail-pwrp-2 OBJECT-TYPE
                    SYNTAX Integer32 (0..1)
                    UNITS "N/A"
                    MAX-ACCESS read-only
                    STATUS current
                    DESCRIPTION "N/A"
                    DEFVAL { 0 }
                    ::= { digitalObjects 1278 }

        -- 1.3.6.1.4.1.9839.2.1.1.1279
        al-25-errorcode25-pwrp-2 OBJECT-TYPE
                    SYNTAX Integer32 (0..1)
                    UNITS "N/A"
                    MAX-ACCESS read-only
                    STATUS current
                    DESCRIPTION "N/A"
                    DEFVAL { 0 }
                    ::= { digitalObjects 1279 }

        -- 1.3.6.1.4.1.9839.2.1.1.1280
        al-26-errorcode26-pwrp-2 OBJECT-TYPE
                    SYNTAX Integer32 (0..1)
                    UNITS "N/A"
                    MAX-ACCESS read-only
                    STATUS current
                    DESCRIPTION "N/A"
                    DEFVAL { 0 }
                    ::= { digitalObjects 1280 }

        -- 1.3.6.1.4.1.9839.2.1.1.1281
        al-27-errorcode27-pwrp-2 OBJECT-TYPE
                    SYNTAX Integer32 (0..1)
                    UNITS "N/A"
                    MAX-ACCESS read-only
                    STATUS current
                    DESCRIPTION "N/A"
                    DEFVAL { 0 }
                    ::= { digitalObjects 1281 }

        -- 1.3.6.1.4.1.9839.2.1.1.1282
        al-28-errorcode28-pwrp-2 OBJECT-TYPE
                    SYNTAX Integer32 (0..1)
                    UNITS "N/A"
                    MAX-ACCESS read-only
                    STATUS current
                    DESCRIPTION "N/A"
                    DEFVAL { 0 }
                    ::= { digitalObjects 1282 }

        -- 1.3.6.1.4.1.9839.2.1.1.1283
        al-29-errorcode28-pwrp-2 OBJECT-TYPE
                    SYNTAX Integer32 (0..1)
                    UNITS "N/A"
                    MAX-ACCESS read-only
                    STATUS current
                    DESCRIPTION "N/A"
                    DEFVAL { 0 }
                    ::= { digitalObjects 1283 }

        -- 1.3.6.1.4.1.9839.2.1.1.1284
        al-30-errorcode30-pwrp-2 OBJECT-TYPE
                    SYNTAX Integer32 (0..1)
                    UNITS "N/A"
                    MAX-ACCESS read-only
                    STATUS current
                    DESCRIPTION "N/A"
                    DEFVAL { 0 }
                    ::= { digitalObjects 1284 }

        -- 1.3.6.1.4.1.9839.2.1.1.1300
        evd-pco-synchro-ok OBJECT-TYPE
                    SYNTAX Integer32 (0..1)
                    UNITS "N/A"
                    MAX-ACCESS read-only
                    STATUS current
                    DESCRIPTION "EVD ready to receive the Cooling capacity and starts to regulate the EEV based on the SH"
                    DEFVAL { 0 }
                    ::= { digitalObjects 1300 }

        -- 1.3.6.1.4.1.9839.2.1.1.1301
        evd-alarm-offline OBJECT-TYPE
                    SYNTAX Integer32 (0..1)
                    UNITS "N/A"
                    MAX-ACCESS read-only
                    STATUS current
                    DESCRIPTION "Driver offline alarm"
                    DEFVAL { 0 }
                    ::= { digitalObjects 1301 }

        -- 1.3.6.1.4.1.9839.2.1.1.1302
        alarm-s1 OBJECT-TYPE
                    SYNTAX Integer32 (0..1)
                    UNITS "N/A"
                    MAX-ACCESS read-only
                    STATUS current
                    DESCRIPTION "Alarm probe S1"
                    DEFVAL { 0 }
                    ::= { digitalObjects 1302 }

        -- 1.3.6.1.4.1.9839.2.1.1.1303
        alarm-s2 OBJECT-TYPE
                    SYNTAX Integer32 (0..1)
                    UNITS "N/A"
                    MAX-ACCESS read-only
                    STATUS current
                    DESCRIPTION "Alarm probe S2"
                    DEFVAL { 0 }
                    ::= { digitalObjects 1303 }

        -- 1.3.6.1.4.1.9839.2.1.1.1304
        alarm-s3 OBJECT-TYPE
                    SYNTAX Integer32 (0..1)
                    UNITS "N/A"
                    MAX-ACCESS read-only
                    STATUS current
                    DESCRIPTION "Alarm probe S3"
                    DEFVAL { 0 }
                    ::= { digitalObjects 1304 }

        -- 1.3.6.1.4.1.9839.2.1.1.1305
        alarm-s4 OBJECT-TYPE
                    SYNTAX Integer32 (0..1)
                    UNITS "N/A"
                    MAX-ACCESS read-only
                    STATUS current
                    DESCRIPTION "Alarm probe S4"
                    DEFVAL { 0 }
                    ::= { digitalObjects 1305 }

        -- 1.3.6.1.4.1.9839.2.1.1.1306
        evd-reg-alarms-a OBJECT-TYPE
                    SYNTAX Integer32 (0..1)
                    UNITS "N/A"
                    MAX-ACCESS read-only
                    STATUS current
                    DESCRIPTION "EVD EVO regulation alarms - Valve A"
                    DEFVAL { 0 }
                    ::= { digitalObjects 1306 }

        -- 1.3.6.1.4.1.9839.2.1.1.1307
        evd-reg-alarms-b OBJECT-TYPE
                    SYNTAX Integer32 (0..1)
                    UNITS "N/A"
                    MAX-ACCESS read-only
                    STATUS current
                    DESCRIPTION "EVD EVO regulation alarms - Valve B"
                    DEFVAL { 0 }
                    ::= { digitalObjects 1307 }

        -- 1.3.6.1.4.1.9839.2.1.1.1308
        evd-system-alarms OBJECT-TYPE
                    SYNTAX Integer32 (0..1)
                    UNITS "N/A"
                    MAX-ACCESS read-only
                    STATUS current
                    DESCRIPTION "EVD EVO system alarms"
                    DEFVAL { 0 }
                    ::= { digitalObjects 1308 }

        -- 1.3.6.1.4.1.9839.2.1.1.1309
        low-sh-alarm-a OBJECT-TYPE
                    SYNTAX Integer32 (0..1)
                    UNITS "N/A"
                    MAX-ACCESS read-only
                    STATUS current
                    DESCRIPTION "LowSH (low super heat) alarm - Valve A"
                    DEFVAL { 0 }
                    ::= { digitalObjects 1309 }

        -- 1.3.6.1.4.1.9839.2.1.1.1310
        low-sh-alarm-b OBJECT-TYPE
                    SYNTAX Integer32 (0..1)
                    UNITS "N/A"
                    MAX-ACCESS read-only
                    STATUS current
                    DESCRIPTION "LowSH (low super heat) alarm - Valve B"
                    DEFVAL { 0 }
                    ::= { digitalObjects 1310 }

        -- 1.3.6.1.4.1.9839.2.1.1.1311
        lop-alarm-a OBJECT-TYPE
                    SYNTAX Integer32 (0..1)
                    UNITS "N/A"
                    MAX-ACCESS read-only
                    STATUS current
                    DESCRIPTION "LOP (low temperature of evaporation) alarm - Valve A"
                    DEFVAL { 0 }
                    ::= { digitalObjects 1311 }

        -- 1.3.6.1.4.1.9839.2.1.1.1312
        lop-alarm-b OBJECT-TYPE
                    SYNTAX Integer32 (0..1)
                    UNITS "N/A"
                    MAX-ACCESS read-only
                    STATUS current
                    DESCRIPTION "LOP (low temperature of evaporation) alarm - Valve B"
                    DEFVAL { 0 }
                    ::= { digitalObjects 1312 }

        -- 1.3.6.1.4.1.9839.2.1.1.1313
        mop-alarm-a OBJECT-TYPE
                    SYNTAX Integer32 (0..1)
                    UNITS "N/A"
                    MAX-ACCESS read-only
                    STATUS current
                    DESCRIPTION "MOP alarm - Valve A"
                    DEFVAL { 0 }
                    ::= { digitalObjects 1313 }

        -- 1.3.6.1.4.1.9839.2.1.1.1314
        mop-alarm-b OBJECT-TYPE
                    SYNTAX Integer32 (0..1)
                    UNITS "N/A"
                    MAX-ACCESS read-only
                    STATUS current
                    DESCRIPTION "MOP alarm - Valve B"
                    DEFVAL { 0 }
                    ::= { digitalObjects 1314 }

        -- 1.3.6.1.4.1.9839.2.1.1.1315
        eev-motor-alarm-a OBJECT-TYPE
                    SYNTAX Integer32 (0..1)
                    UNITS "N/A"
                    MAX-ACCESS read-only
                    STATUS current
                    DESCRIPTION "EEV motor error - Valve A"
                    DEFVAL { 0 }
                    ::= { digitalObjects 1315 }

        -- 1.3.6.1.4.1.9839.2.1.1.1316
        eev-motor-alarm-b OBJECT-TYPE
                    SYNTAX Integer32 (0..1)
                    UNITS "N/A"
                    MAX-ACCESS read-only
                    STATUS current
                    DESCRIPTION "EEV motor error - Valve B"
                    DEFVAL { 0 }
                    ::= { digitalObjects 1316 }

        -- 1.3.6.1.4.1.9839.2.1.1.1317
        low-suct-alarm-a OBJECT-TYPE
                    SYNTAX Integer32 (0..1)
                    UNITS "N/A"
                    MAX-ACCESS read-only
                    STATUS current
                    DESCRIPTION "Low suction temperature alarm - Valve A"
                    DEFVAL { 0 }
                    ::= { digitalObjects 1317 }

        -- 1.3.6.1.4.1.9839.2.1.1.1318
        low-suct-alarm-b OBJECT-TYPE
                    SYNTAX Integer32 (0..1)
                    UNITS "N/A"
                    MAX-ACCESS read-only
                    STATUS current
                    DESCRIPTION "Low suction temperature alarm - Valve B"
                    DEFVAL { 0 }
                    ::= { digitalObjects 1318 }

        -- 1.3.6.1.4.1.9839.2.1.1.1319
        evotunes-alarms-a OBJECT-TYPE
                    SYNTAX Integer32 (0..1)
                    UNITS "N/A"
                    MAX-ACCESS read-only
                    STATUS current
                    DESCRIPTION "Evotunes alarm - Valve A"
                    DEFVAL { 0 }
                    ::= { digitalObjects 1319 }

        -- 1.3.6.1.4.1.9839.2.1.1.1320
        evotunes-alarm-b OBJECT-TYPE
                    SYNTAX Integer32 (0..1)
                    UNITS "N/A"
                    MAX-ACCESS read-only
                    STATUS current
                    DESCRIPTION "Evotunes alarm - Valve B"
                    DEFVAL { 0 }
                    ::= { digitalObjects 1320 }

        -- 1.3.6.1.4.1.9839.2.1.1.1321
        hitcond-alarm OBJECT-TYPE
                    SYNTAX Integer32 (0..1)
                    UNITS "N/A"
                    MAX-ACCESS read-only
                    STATUS current
                    DESCRIPTION "High condensing temperature alarm"
                    DEFVAL { 0 }
                    ::= { digitalObjects 1321 }

        -- 1.3.6.1.4.1.9839.2.1.1.1322
        eeprom-alarm OBJECT-TYPE
                    SYNTAX Integer32 (0..1)
                    UNITS "N/A"
                    MAX-ACCESS read-only
                    STATUS current
                    DESCRIPTION "EEPROM alarm"
                    DEFVAL { 0 }
                    ::= { digitalObjects 1322 }

        -- 1.3.6.1.4.1.9839.2.1.1.1323
        battery-alarm OBJECT-TYPE
                    SYNTAX Integer32 (0..1)
                    UNITS "N/A"
                    MAX-ACCESS read-only
                    STATUS current
                    DESCRIPTION "Discharge battery alarm"
                    DEFVAL { 0 }
                    ::= { digitalObjects 1323 }

        -- 1.3.6.1.4.1.9839.2.1.1.1324
        emergency-closing-alarm OBJECT-TYPE
                    SYNTAX Integer32 (0..1)
                    UNITS "N/A"
                    MAX-ACCESS read-only
                    STATUS current
                    DESCRIPTION "Alarm status for emercency valve closing"
                    DEFVAL { 0 }
                    ::= { digitalObjects 1324 }

        -- 1.3.6.1.4.1.9839.2.1.1.1325
        incomplete-closing-alarm OBJECT-TYPE
                    SYNTAX Integer32 (0..1)
                    UNITS "N/A"
                    MAX-ACCESS read-only
                    STATUS current
                    DESCRIPTION "Incomplete valve closing alarm"
                    DEFVAL { 0 }
                    ::= { digitalObjects 1325 }

        -- 1.3.6.1.4.1.9839.2.1.1.1326
        digital-input-1 OBJECT-TYPE
                    SYNTAX Integer32 (0..1)
                    UNITS "N/A"
                    MAX-ACCESS read-only
                    STATUS current
                    DESCRIPTION "EVD digital input 1 (DI1)"
                    DEFVAL { 0 }
                    ::= { digitalObjects 1326 }

        -- 1.3.6.1.4.1.9839.2.1.1.1327
        digital-input-2 OBJECT-TYPE
                    SYNTAX Integer32 (0..1)
                    UNITS "N/A"
                    MAX-ACCESS read-only
                    STATUS current
                    DESCRIPTION "EVD digital input 2(DI2)"
                    DEFVAL { 0 }
                    ::= { digitalObjects 1327 }

        -- 1.3.6.1.4.1.9839.2.1.1.1328
        default-parameter OBJECT-TYPE
                    SYNTAX Integer32 (0..1)
                    UNITS "N/A"
                    MAX-ACCESS read-only
                    STATUS current
                    DESCRIPTION "Trigger for parameter default value require"
                    DEFVAL { 0 }
                    ::= { digitalObjects 1328 }

        -- 1.3.6.1.4.1.9839.2.1.1.1329
        evd-default-running OBJECT-TYPE
                    SYNTAX Integer32 (0..1)
                    UNITS "N/A"
                    MAX-ACCESS read-only
                    STATUS current
                    DESCRIPTION "Trigger for parameters default execution on running"
                    DEFVAL { 0 }
                    ::= { digitalObjects 1329 }

        -- 1.3.6.1.4.1.9839.2.1.1.1330
        default-superparam OBJECT-TYPE
                    SYNTAX Integer32 (0..1)
                    UNITS "N/A"
                    MAX-ACCESS read-only
                    STATUS current
                    DESCRIPTION "Trigger for superparameter default value require"
                    DEFVAL { 0 }
                    ::= { digitalObjects 1330 }

        -- 1.3.6.1.4.1.9839.2.1.1.1400
        al-offline-cpy OBJECT-TYPE
                    SYNTAX Integer32 (0..1)
                    UNITS "N/A"
                    MAX-ACCESS read-only
                    STATUS current
                    DESCRIPTION "Offline alarm"
                    DEFVAL { 0 }
                    ::= { digitalObjects 1400 }

        -- 1.3.6.1.4.1.9839.2.1.1.1401
        alrmpresent-cpy OBJECT-TYPE
                    SYNTAX Integer32 (0..1)
                    UNITS "N/A"
                    MAX-ACCESS read-only
                    STATUS current
                    DESCRIPTION "Blocking alarm present"
                    DEFVAL { 0 }
                    ::= { digitalObjects 1401 }

        -- 1.3.6.1.4.1.9839.2.1.1.1402
        cpy-can-run OBJECT-TYPE
                    SYNTAX Integer32 (0..1)
                    UNITS "N/A"
                    MAX-ACCESS read-only
                    STATUS current
                    DESCRIPTION "N/A"
                    DEFVAL { 0 }
                    ::= { digitalObjects 1402 }

        -- 1.3.6.1.4.1.9839.2.1.1.1403
        humid-enable OBJECT-TYPE
                    SYNTAX Integer32 (0..1)
                    UNITS "N/A"
                    MAX-ACCESS read-write
                    STATUS current
                    DESCRIPTION "N/A"
                    DEFVAL { 0 }
                    ::= { digitalObjects 1403 }

        -- 1.3.6.1.4.1.9839.2.1.1.1404
        en-cpy-humidifier OBJECT-TYPE
                    SYNTAX Integer32 (0..1)
                    UNITS "N/A"
                    MAX-ACCESS read-only
                    STATUS current
                    DESCRIPTION "N/A"
                    DEFVAL { 0 }
                    ::= { digitalObjects 1404 }

        -- 1.3.6.1.4.1.9839.2.1.1.1405
        cpy-1.i62-bit3-precleaning-w OBJECT-TYPE
                    SYNTAX Integer32 (0..1)
                    UNITS "N/A"
                    MAX-ACCESS read-write
                    STATUS current
                    DESCRIPTION "Precleaning enabled in mask"
                    DEFVAL { 0 }
                    ::= { digitalObjects 1405 }

        -- 1.3.6.1.4.1.9839.2.1.1.1406
        serialreq-cpy OBJECT-TYPE
                    SYNTAX Integer32 (0..1)
                    UNITS "N/A"
                    MAX-ACCESS read-write
                    STATUS current
                    DESCRIPTION "N/A"
                    DEFVAL { 0 }
                    ::= { digitalObjects 1406 }

        -- 1.3.6.1.4.1.9839.2.1.1.1407
        warningpresent-cpy OBJECT-TYPE
                    SYNTAX Integer32 (0..1)
                    UNITS "N/A"
                    MAX-ACCESS read-only
                    STATUS current
                    DESCRIPTION "Warning alarm present"
                    DEFVAL { 0 }
                    ::= { digitalObjects 1407 }

        -- 1.3.6.1.4.1.9839.2.1.1.1408
        cpy-1.d17-drnman-msk OBJECT-TYPE
                    SYNTAX Integer32 (0..1)
                    UNITS "N/A"
                    MAX-ACCESS read-write
                    STATUS current
                    DESCRIPTION "Manual drain"
                    DEFVAL { 0 }
                    ::= { digitalObjects 1408 }

        -- 1.3.6.1.4.1.9839.2.1.1.1409
        cpy-1.i84-al-e1-paramsnotdwnld OBJECT-TYPE
                    SYNTAX Integer32 (0..1)
                    UNITS "N/A"
                    MAX-ACCESS read-only
                    STATUS current
                    DESCRIPTION "Parameters not downloaded alarm"
                    DEFVAL { 0 }
                    ::= { digitalObjects 1409 }

        -- 1.3.6.1.4.1.9839.2.1.1.1410
        cpy-1.i84-al-ec-hiconduct OBJECT-TYPE
                    SYNTAX Integer32 (0..1)
                    UNITS "N/A"
                    MAX-ACCESS read-only
                    STATUS current
                    DESCRIPTION "High conductivity alarm"
                    DEFVAL { 0 }
                    ::= { digitalObjects 1410 }

        -- 1.3.6.1.4.1.9839.2.1.1.1411
        cpy-1.i84-al-eh-currhi OBJECT-TYPE
                    SYNTAX Integer32 (0..1)
                    UNITS "N/A"
                    MAX-ACCESS read-only
                    STATUS current
                    DESCRIPTION "High current alarm"
                    DEFVAL { 0 }
                    ::= { digitalObjects 1411 }

        -- 1.3.6.1.4.1.9839.2.1.1.1412
        cpy-1.i84-al-ep-lowproduction OBJECT-TYPE
                    SYNTAX Integer32 (0..1)
                    UNITS "N/A"
                    MAX-ACCESS read-only
                    STATUS current
                    DESCRIPTION "Low production alarm"
                    DEFVAL { 0 }
                    ::= { digitalObjects 1412 }

        -- 1.3.6.1.4.1.9839.2.1.1.1413
        cpy-1.i84-al-mn-cyllife OBJECT-TYPE
                    SYNTAX Integer32 (0..1)
                    UNITS "N/A"
                    MAX-ACCESS read-only
                    STATUS current
                    DESCRIPTION "Cylinder life alarm"
                    DEFVAL { 0 }
                    ::= { digitalObjects 1413 }

        -- 1.3.6.1.4.1.9839.2.1.1.1414
        cpy-1.i85-al-e3-prbnotconnected OBJECT-TYPE
                    SYNTAX Integer32 (0..1)
                    UNITS "N/A"
                    MAX-ACCESS read-only
                    STATUS current
                    DESCRIPTION "Probe not connected alarm"
                    DEFVAL { 0 }
                    ::= { digitalObjects 1414 }

        -- 1.3.6.1.4.1.9839.2.1.1.1415
        cpy-1.i85-al-ed-alrmdrn OBJECT-TYPE
                    SYNTAX Integer32 (0..1)
                    UNITS "N/A"
                    MAX-ACCESS read-only
                    STATUS current
                    DESCRIPTION "Drain alarm"
                    DEFVAL { 0 }
                    ::= { digitalObjects 1415 }

        -- 1.3.6.1.4.1.9839.2.1.1.1416
        cpy-1.i85-al-ef-missingw OBJECT-TYPE
                    SYNTAX Integer32 (0..1)
                    UNITS "N/A"
                    MAX-ACCESS read-only
                    STATUS current
                    DESCRIPTION "Missing water alarm"
                    DEFVAL { 0 }
                    ::= { digitalObjects 1416 }

        -- 1.3.6.1.4.1.9839.2.1.1.1417
        cpy-1.i85-al-eh1-hihum OBJECT-TYPE
                    SYNTAX Integer32 (0..1)
                    UNITS "N/A"
                    MAX-ACCESS read-only
                    STATUS current
                    DESCRIPTION "High humidity alarm"
                    DEFVAL { 0 }
                    ::= { digitalObjects 1417 }

        -- 1.3.6.1.4.1.9839.2.1.1.1418
        cpy-1.i85-al-eh2-lowhum OBJECT-TYPE
                    SYNTAX Integer32 (0..1)
                    UNITS "N/A"
                    MAX-ACCESS read-only
                    STATUS current
                    DESCRIPTION "Low humidity alarm"
                    DEFVAL { 0 }
                    ::= { digitalObjects 1418 }

        -- 1.3.6.1.4.1.9839.2.1.1.1419
        cpy-1.i85-al-eu-cylfull OBJECT-TYPE
                    SYNTAX Integer32 (0..1)
                    UNITS "N/A"
                    MAX-ACCESS read-only
                    STATUS current
                    DESCRIPTION "Full cylinder alarm"
                    DEFVAL { 0 }
                    ::= { digitalObjects 1419 }

        -- 1.3.6.1.4.1.9839.2.1.1.1420
        cpy-1.i85-al-su-serialdisconnected OBJECT-TYPE
                    SYNTAX Integer32 (0..1)
                    UNITS "N/A"
                    MAX-ACCESS read-only
                    STATUS current
                    DESCRIPTION "Serial disconnected alarm"
                    DEFVAL { 0 }
                    ::= { digitalObjects 1420 }

        -- 1.3.6.1.4.1.9839.2.1.1.1421
        cpy-1.i84-al-e0-calibrationparams OBJECT-TYPE
                    SYNTAX Integer32 (0..1)
                    UNITS "N/A"
                    MAX-ACCESS read-only
                    STATUS current
                    DESCRIPTION "Calibration parameters alarm"
                    DEFVAL { 0 }
                    ::= { digitalObjects 1421 }

        -- 1.3.6.1.4.1.9839.2.1.1.1500
        en-energy-meter OBJECT-TYPE
                    SYNTAX Integer32 (0..1)
                    UNITS "N/A"
                    MAX-ACCESS read-write
                    STATUS current
                    DESCRIPTION "N/A"
                    DEFVAL { 0 }
                    ::= { digitalObjects 1500 }

        -- 1.3.6.1.4.1.9839.2.1.1.1501
        al-offline-energy-meters OBJECT-TYPE
                    SYNTAX Integer32 (0..1)
                    UNITS "N/A"
                    MAX-ACCESS read-only
                    STATUS current
                    DESCRIPTION "N/A"
                    DEFVAL { 0 }
                    ::= { digitalObjects 1501 }

        -- 1.3.6.1.4.1.9839.2.1.1.1600
        en-danfoss OBJECT-TYPE
                    SYNTAX Integer32 (0..1)
                    UNITS "N/A"
                    MAX-ACCESS read-write
                    STATUS current
                    DESCRIPTION "N/A"
                    DEFVAL { 1 }
                    ::= { digitalObjects 1600 }

        -- 1.3.6.1.4.1.9839.2.1.1.1601
        al-offline-danfoss OBJECT-TYPE
                    SYNTAX Integer32 (0..1)
                    UNITS "N/A"
                    MAX-ACCESS read-only
                    STATUS current
                    DESCRIPTION "N/A"
                    DEFVAL { 0 }
                    ::= { digitalObjects 1601 }

        -- 1.3.6.1.4.1.9839.2.1.1.1602
        al-danfoss-inverter-alarm OBJECT-TYPE
                    SYNTAX Integer32 (0..1)
                    UNITS "N/A"
                    MAX-ACCESS read-only
                    STATUS current
                    DESCRIPTION "N/A"
                    DEFVAL { 0 }
                    ::= { digitalObjects 1602 }

        -- 1.3.6.1.4.1.9839.2.1.1.1603
        al-oil-protection-danfoss OBJECT-TYPE
                    SYNTAX Integer32 (0..1)
                    UNITS "N/A"
                    MAX-ACCESS read-only
                    STATUS current
                    DESCRIPTION "N/A"
                    DEFVAL { 0 }
                    ::= { digitalObjects 1603 }

        -- 1.3.6.1.4.1.9839.2.1.1.1604
        can-show-danfoss-option OBJECT-TYPE
                    SYNTAX Integer32 (0..1)
                    UNITS "N/A"
                    MAX-ACCESS read-only
                    STATUS current
                    DESCRIPTION "N/A"
                    DEFVAL { 0 }
                    ::= { digitalObjects 1604 }

        -- 1.3.6.1.4.1.9839.2.1.1.1605
        tandem-danfoss OBJECT-TYPE
                    SYNTAX Integer32 (0..1)
                    UNITS "N/A"
                    MAX-ACCESS read-only
                    STATUS current
                    DESCRIPTION "N/A"
                    DEFVAL { 0 }
                    ::= { digitalObjects 1605 }

        -- 1.3.6.1.4.1.9839.2.1.1.1606
        compon-danfoss-inv OBJECT-TYPE
                    SYNTAX Integer32 (0..1)
                    UNITS "N/A"
                    MAX-ACCESS read-only
                    STATUS current
                    DESCRIPTION "Compressor power on"
                    DEFVAL { 0 }
                    ::= { digitalObjects 1606 }

        -- 1.3.6.1.4.1.9839.2.1.1.1607
        specificparam-danfoss OBJECT-TYPE
                    SYNTAX Integer32 (0..1)
                    UNITS "N/A"
                    MAX-ACCESS read-only
                    STATUS current
                    DESCRIPTION "Use specific parameters (Max acceleration; enevelope alarm delay)"
                    DEFVAL { 0 }
                    ::= { digitalObjects 1607 }

        -- 1.3.6.1.4.1.9839.2.1.1.1608
        abletoon-danf-inv-1 OBJECT-TYPE
                    SYNTAX Integer32 (0..1)
                    UNITS "N/A"
                    MAX-ACCESS read-only
                    STATUS current
                    DESCRIPTION "Minimum off time elapsed"
                    DEFVAL { 0 }
                    ::= { digitalObjects 1608 }

        -- 1.3.6.1.4.1.9839.2.1.1.1609
        abletooff-danf-inv-1 OBJECT-TYPE
                    SYNTAX Integer32 (0..1)
                    UNITS "N/A"
                    MAX-ACCESS read-only
                    STATUS current
                    DESCRIPTION "Minimum on time elapsed"
                    DEFVAL { 0 }
                    ::= { digitalObjects 1609 }

        -- 1.3.6.1.4.1.9839.2.1.1.1610
        danfoss-inverter-compressor-on OBJECT-TYPE
                    SYNTAX Integer32 (0..1)
                    UNITS "N/A"
                    MAX-ACCESS read-only
                    STATUS current
                    DESCRIPTION "N/A"
                    DEFVAL { 0 }
                    ::= { digitalObjects 1610 }

        -- 1.3.6.1.4.1.9839.2.1.1.1611
        running-danfoss OBJECT-TYPE
                    SYNTAX Integer32 (0..1)
                    UNITS "N/A"
                    MAX-ACCESS read-only
                    STATUS current
                    DESCRIPTION "N/A"
                    DEFVAL { 0 }
                    ::= { digitalObjects 1611 }

        -- 1.3.6.1.4.1.9839.2.1.1.1612
        alrmcompoff-danfoss OBJECT-TYPE
                    SYNTAX Integer32 (0..1)
                    UNITS "N/A"
                    MAX-ACCESS read-only
                    STATUS current
                    DESCRIPTION "Alarm state that shut off compressor"
                    DEFVAL { 0 }
                    ::= { digitalObjects 1612 }

        -- 1.3.6.1.4.1.9839.2.1.1.1613
        compsaft-res-danfoss OBJECT-TYPE
                    SYNTAX Integer32 (0..1)
                    UNITS "N/A"
                    MAX-ACCESS read-only
                    STATUS current
                    DESCRIPTION "Request to reset of compressor safety timing (starting failure repair)"
                    DEFVAL { 0 }
                    ::= { digitalObjects 1613 }

        -- 1.3.6.1.4.1.9839.2.1.1.1614
        vfd-res-danfoss OBJECT-TYPE
                    SYNTAX Integer32 (0..1)
                    UNITS "N/A"
                    MAX-ACCESS read-only
                    STATUS current
                    DESCRIPTION "Inverter alarm reset command"
                    DEFVAL { 0 }
                    ::= { digitalObjects 1614 }

        -- 1.3.6.1.4.1.9839.2.1.1.1615
        envalrm-danfoss OBJECT-TYPE
                    SYNTAX Integer32 (0..1)
                    UNITS "N/A"
                    MAX-ACCESS read-only
                    STATUS current
                    DESCRIPTION "Out of envelop alarm"
                    DEFVAL { 0 }
                    ::= { digitalObjects 1615 }

        -- 1.3.6.1.4.1.9839.2.1.1.1616
        oralstartfail-danfoss OBJECT-TYPE
                    SYNTAX Integer32 (0..1)
                    UNITS "N/A"
                    MAX-ACCESS read-only
                    STATUS current
                    DESCRIPTION "Compressor fails to start alarm"
                    DEFVAL { 0 }
                    ::= { digitalObjects 1616 }

        -- 1.3.6.1.4.1.9839.2.1.1.1617
        al-deltap-danfoss OBJECT-TYPE
                    SYNTAX Integer32 (0..1)
                    UNITS "N/A"
                    MAX-ACCESS read-only
                    STATUS current
                    DESCRIPTION "Low pressure difference alarm"
                    DEFVAL { 0 }
                    ::= { digitalObjects 1617 }

        -- 1.3.6.1.4.1.9839.2.1.1.1618
        al-hightempdscg-danfoss OBJECT-TYPE
                    SYNTAX Integer32 (0..1)
                    UNITS "N/A"
                    MAX-ACCESS read-write
                    STATUS current
                    DESCRIPTION "Discharge temperature alarm"
                    DEFVAL { 0 }
                    ::= { digitalObjects 1618 }

        -- 1.3.6.1.4.1.9839.2.1.1.1619
        errflag-danfoss OBJECT-TYPE
                    SYNTAX Integer32 (0..1)
                    UNITS "N/A"
                    MAX-ACCESS read-only
                    STATUS current
                    DESCRIPTION "Default values not load"
                    DEFVAL { 0 }
                    ::= { digitalObjects 1619 }

        -- 1.3.6.1.4.1.9839.2.1.1.2001
        hwsw-chk.sw-beta-ok OBJECT-TYPE
                    SYNTAX Integer32 (0..1)
                    UNITS "N/A"
                    MAX-ACCESS read-only
                    STATUS current
                    DESCRIPTION "$$$EMPTYCELL$$$"
                    DEFVAL { 0 }
                    ::= { digitalObjects 2001 }



        -- 1.3.6.1.4.1.9839.2.1.2
        analogObjects OBJECT IDENTIFIER ::= { dencoccuMIB 2 }

        -- 1.3.6.1.4.1.9839.2.1.2.1
        control-temp OBJECT-TYPE
                    SYNTAX Integer32 (-3277..3277)
                    UNITS "C x10"
                    MAX-ACCESS read-only
                    STATUS current
                    DESCRIPTION "Control Temperature"
                    DEFVAL { 0 }
                    ::= { analogObjects 1 }

        -- 1.3.6.1.4.1.9839.2.1.2.2
        control-hum OBJECT-TYPE
                    SYNTAX Integer32 (-999..3277)
                    UNITS "%Rh x10"
                    MAX-ACCESS read-only
                    STATUS current
                    DESCRIPTION "Control Humidity"
                    DEFVAL { 0 }
                    ::= { analogObjects 2 }

        -- 1.3.6.1.4.1.9839.2.1.2.3
        return-air-temp OBJECT-TYPE
                    SYNTAX Integer32 (-3277..3277)
                    UNITS "C x10"
                    MAX-ACCESS read-only
                    STATUS current
                    DESCRIPTION "Return Air Temperature"
                    DEFVAL { 0 }
                    ::= { analogObjects 3 }

        -- 1.3.6.1.4.1.9839.2.1.2.4
        return-air-hum OBJECT-TYPE
                    SYNTAX Integer32 (-999..3277)
                    UNITS "%Rh x10"
                    MAX-ACCESS read-only
                    STATUS current
                    DESCRIPTION "Return Air Humidity"
                    DEFVAL { 0 }
                    ::= { analogObjects 4 }

        -- 1.3.6.1.4.1.9839.2.1.2.5
        disp-cool-demand OBJECT-TYPE
                    SYNTAX Integer32 (0..3277)
                    UNITS "% x10"
                    MAX-ACCESS read-only
                    STATUS current
                    DESCRIPTION "Cooling Demand"
                    DEFVAL { 0 }
                    ::= { analogObjects 5 }

        -- 1.3.6.1.4.1.9839.2.1.2.6
        disp-heat-demand OBJECT-TYPE
                    SYNTAX Integer32 (0..3277)
                    UNITS "% x10"
                    MAX-ACCESS read-only
                    STATUS current
                    DESCRIPTION "Heating Demand"
                    DEFVAL { 0 }
                    ::= { analogObjects 6 }

        -- 1.3.6.1.4.1.9839.2.1.2.7
        disp-hum-demand OBJECT-TYPE
                    SYNTAX Integer32 (0..3277)
                    UNITS "% x10"
                    MAX-ACCESS read-only
                    STATUS current
                    DESCRIPTION "Humidity Demand"
                    DEFVAL { 0 }
                    ::= { analogObjects 7 }

        -- 1.3.6.1.4.1.9839.2.1.2.8
        disp-dehum-demand OBJECT-TYPE
                    SYNTAX Integer32 (0..3277)
                    UNITS "% x10"
                    MAX-ACCESS read-only
                    STATUS current
                    DESCRIPTION "Dehum Demand"
                    DEFVAL { 0 }
                    ::= { analogObjects 8 }

        -- 1.3.6.1.4.1.9839.2.1.2.9
        ambicool-demand OBJECT-TYPE
                    SYNTAX Integer32 (0..3277)
                    UNITS "% x10"
                    MAX-ACCESS read-only
                    STATUS current
                    DESCRIPTION "Ambicool Demand"
                    DEFVAL { 0 }
                    ::= { analogObjects 9 }

        -- 1.3.6.1.4.1.9839.2.1.2.10
        special-cooling-demand OBJECT-TYPE
                    SYNTAX Integer32 (-3277..3277)
                    UNITS "% x10"
                    MAX-ACCESS read-only
                    STATUS current
                    DESCRIPTION "Special Cooling Demand"
                    DEFVAL { 0 }
                    ::= { analogObjects 10 }

        -- 1.3.6.1.4.1.9839.2.1.2.11
        supply-air-temp OBJECT-TYPE
                    SYNTAX Integer32 (-999..3277)
                    UNITS "C x10"
                    MAX-ACCESS read-only
                    STATUS current
                    DESCRIPTION "Supply Air Temperature"
                    DEFVAL { 0 }
                    ::= { analogObjects 11 }

        -- 1.3.6.1.4.1.9839.2.1.2.12
        supply-air-hum OBJECT-TYPE
                    SYNTAX Integer32 (-999..3277)
                    UNITS "%Rh x10"
                    MAX-ACCESS read-only
                    STATUS current
                    DESCRIPTION "Supply Air Humidity"
                    DEFVAL { 0 }
                    ::= { analogObjects 12 }

        -- 1.3.6.1.4.1.9839.2.1.2.13
        cw-inlet-temp OBJECT-TYPE
                    SYNTAX Integer32 (-999..3277)
                    UNITS "C x10"
                    MAX-ACCESS read-only
                    STATUS current
                    DESCRIPTION "Water temperature inlet"
                    DEFVAL { 0 }
                    ::= { analogObjects 13 }

        -- 1.3.6.1.4.1.9839.2.1.2.14
        cw-outlet-temp OBJECT-TYPE
                    SYNTAX Integer32 (-999..3277)
                    UNITS "C x10"
                    MAX-ACCESS read-only
                    STATUS current
                    DESCRIPTION "Water temperature outlet"
                    DEFVAL { 0 }
                    ::= { analogObjects 14 }

        -- 1.3.6.1.4.1.9839.2.1.2.15
        discharge-press OBJECT-TYPE
                    SYNTAX Integer32 (-999..3277)
                    UNITS "bar x10"
                    MAX-ACCESS read-only
                    STATUS current
                    DESCRIPTION "Discharge Pressure"
                    DEFVAL { 0 }
                    ::= { analogObjects 15 }

        -- 1.3.6.1.4.1.9839.2.1.2.16
        discharge-temp OBJECT-TYPE
                    SYNTAX Integer32 (-760..3920)
                    UNITS "N/A"
                    MAX-ACCESS read-only
                    STATUS current
                    DESCRIPTION "Discharge temperature"
                    DEFVAL { 0 }
                    ::= { analogObjects 16 }

        -- 1.3.6.1.4.1.9839.2.1.2.17
        eev-probe-value-s1 OBJECT-TYPE
                    SYNTAX Integer32 (-32768..32767)
                    UNITS "N/A"
                    MAX-ACCESS read-only
                    STATUS current
                    DESCRIPTION "S1 probe value"
                    DEFVAL { 0 }
                    ::= { analogObjects 17 }

        -- 1.3.6.1.4.1.9839.2.1.2.18
        eev-probe-value-s2 OBJECT-TYPE
                    SYNTAX Integer32 (-32768..32767)
                    UNITS "N/A"
                    MAX-ACCESS read-only
                    STATUS current
                    DESCRIPTION "S2 probe value"
                    DEFVAL { 0 }
                    ::= { analogObjects 18 }

        -- 1.3.6.1.4.1.9839.2.1.2.19
        eev-probe-value-s3 OBJECT-TYPE
                    SYNTAX Integer32 (-32768..32767)
                    UNITS "N/A"
                    MAX-ACCESS read-only
                    STATUS current
                    DESCRIPTION "S3 probe value"
                    DEFVAL { 0 }
                    ::= { analogObjects 19 }

        -- 1.3.6.1.4.1.9839.2.1.2.20
        eev-probe-value-s4 OBJECT-TYPE
                    SYNTAX Integer32 (-32768..32767)
                    UNITS "N/A"
                    MAX-ACCESS read-only
                    STATUS current
                    DESCRIPTION "S4 probe value"
                    DEFVAL { 0 }
                    ::= { analogObjects 20 }

        -- 1.3.6.1.4.1.9839.2.1.2.21
        aps-press-trasducer OBJECT-TYPE
                    SYNTAX Integer32 (-32767..32767)
                    UNITS "N/A"
                    MAX-ACCESS read-only
                    STATUS current
                    DESCRIPTION "APS Pressure Trasducer"
                    DEFVAL { 0 }
                    ::= { analogObjects 21 }

        -- 1.3.6.1.4.1.9839.2.1.2.22
        amb-temp OBJECT-TYPE
                    SYNTAX Integer32 (-999..3277)
                    UNITS "C x10"
                    MAX-ACCESS read-only
                    STATUS current
                    DESCRIPTION "Ambient Temperature"
                    DEFVAL { 0 }
                    ::= { analogObjects 22 }

        -- 1.3.6.1.4.1.9839.2.1.2.23
        sel-set-temp OBJECT-TYPE
                    SYNTAX Integer32 (5..400)
                    UNITS "C x10"
                    MAX-ACCESS read-write
                    STATUS current
                    DESCRIPTION "Temperature Set Point"
                    DEFVAL { 210 }
                    ::= { analogObjects 23 }

        -- 1.3.6.1.4.1.9839.2.1.2.24
        sel-set-hum OBJECT-TYPE
                    SYNTAX Integer32 (0..999)
                    UNITS "%Rh x10"
                    MAX-ACCESS read-write
                    STATUS current
                    DESCRIPTION "Humidity Set Point"
                    DEFVAL { 500 }
                    ::= { analogObjects 24 }

        -- 1.3.6.1.4.1.9839.2.1.2.25
        temp-alarm-band OBJECT-TYPE
                    SYNTAX Integer32 (10..200)
                    UNITS "C x10"
                    MAX-ACCESS read-write
                    STATUS current
                    DESCRIPTION "Temperature Alarm Band"
                    DEFVAL { 40 }
                    ::= { analogObjects 25 }

        -- 1.3.6.1.4.1.9839.2.1.2.26
        hum-alarm-band OBJECT-TYPE
                    SYNTAX Integer32 (20..200)
                    UNITS "%Rh x10"
                    MAX-ACCESS read-write
                    STATUS current
                    DESCRIPTION "Humidity Alarm Band"
                    DEFVAL { 100 }
                    ::= { analogObjects 26 }

        -- 1.3.6.1.4.1.9839.2.1.2.27
        cool-dead-zone OBJECT-TYPE
                    SYNTAX Integer32 (0..50)
                    UNITS "C x10"
                    MAX-ACCESS read-write
                    STATUS current
                    DESCRIPTION "Cooling Dead Zone"
                    DEFVAL { 0 }
                    ::= { analogObjects 27 }

        -- 1.3.6.1.4.1.9839.2.1.2.28
        cool-prop-band OBJECT-TYPE
                    SYNTAX Integer32 (0..150)
                    UNITS "C x10"
                    MAX-ACCESS read-write
                    STATUS current
                    DESCRIPTION "Cooling Proportional Band"
                    DEFVAL { 20 }
                    ::= { analogObjects 28 }

        -- 1.3.6.1.4.1.9839.2.1.2.29
        heat-dead-zone OBJECT-TYPE
                    SYNTAX Integer32 (0..50)
                    UNITS "C x10"
                    MAX-ACCESS read-write
                    STATUS current
                    DESCRIPTION "Heating Dead Zone"
                    DEFVAL { 10 }
                    ::= { analogObjects 29 }

        -- 1.3.6.1.4.1.9839.2.1.2.30
        heat-prop-band OBJECT-TYPE
                    SYNTAX Integer32 (3..150)
                    UNITS "C x10"
                    MAX-ACCESS read-write
                    STATUS current
                    DESCRIPTION "Heating Proportional Band"
                    DEFVAL { 20 }
                    ::= { analogObjects 30 }

        -- 1.3.6.1.4.1.9839.2.1.2.31
        dehum-dead-zone OBJECT-TYPE
                    SYNTAX Integer32 (0..150)
                    UNITS "%Rh x10"
                    MAX-ACCESS read-write
                    STATUS current
                    DESCRIPTION "Dehum Dead Zone"
                    DEFVAL { 20 }
                    ::= { analogObjects 31 }

        -- 1.3.6.1.4.1.9839.2.1.2.32
        dehum-prop-band OBJECT-TYPE
                    SYNTAX Integer32 (20..150)
                    UNITS "%Rh x10"
                    MAX-ACCESS read-write
                    STATUS current
                    DESCRIPTION "Dehum Proportional Band"
                    DEFVAL { 50 }
                    ::= { analogObjects 32 }

        -- 1.3.6.1.4.1.9839.2.1.2.33
        hum-dead-zone OBJECT-TYPE
                    SYNTAX Integer32 (0..150)
                    UNITS "%Rh x10"
                    MAX-ACCESS read-write
                    STATUS current
                    DESCRIPTION "Humidity Dead Zone"
                    DEFVAL { 20 }
                    ::= { analogObjects 33 }

        -- 1.3.6.1.4.1.9839.2.1.2.34
        hum-prop-band OBJECT-TYPE
                    SYNTAX Integer32 (20..150)
                    UNITS "%Rh x10"
                    MAX-ACCESS read-write
                    STATUS current
                    DESCRIPTION "Humidity Proportional Band"
                    DEFVAL { 50 }
                    ::= { analogObjects 34 }

        -- 1.3.6.1.4.1.9839.2.1.2.35
        cw-feedback-valve OBJECT-TYPE
                    SYNTAX Integer32 (0..9999)
                    UNITS "N/A"
                    MAX-ACCESS read-only
                    STATUS current
                    DESCRIPTION "CW Feedback valve"
                    DEFVAL { 0 }
                    ::= { analogObjects 35 }

        -- 1.3.6.1.4.1.9839.2.1.2.36
        eev-superheat-a OBJECT-TYPE
                    SYNTAX Integer32 (-32768..32767)
                    UNITS "N/A"
                    MAX-ACCESS read-only
                    STATUS current
                    DESCRIPTION "N/A"
                    DEFVAL { 0 }
                    ::= { analogObjects 36 }

        -- 1.3.6.1.4.1.9839.2.1.2.37
        eev-superheat-b OBJECT-TYPE
                    SYNTAX Integer32 (-32768..32767)
                    UNITS "N/A"
                    MAX-ACCESS read-only
                    STATUS current
                    DESCRIPTION "N/A"
                    DEFVAL { 0 }
                    ::= { analogObjects 37 }

        -- 1.3.6.1.4.1.9839.2.1.2.38
        comp-1-speed OBJECT-TYPE
                    SYNTAX Integer32 (-32768..32767)
                    UNITS "N/A"
                    MAX-ACCESS read-only
                    STATUS current
                    DESCRIPTION "N/A"
                    DEFVAL { 0 }
                    ::= { analogObjects 38 }

        -- 1.3.6.1.4.1.9839.2.1.2.39
        comp-2-speed OBJECT-TYPE
                    SYNTAX Integer32 (-32768..32767)
                    UNITS "N/A"
                    MAX-ACCESS read-only
                    STATUS current
                    DESCRIPTION "N/A"
                    DEFVAL { 0 }
                    ::= { analogObjects 39 }

        -- 1.3.6.1.4.1.9839.2.1.2.40
        eev-position-a OBJECT-TYPE
                    SYNTAX Integer32 (-32768..32767)
                    UNITS "N/A"
                    MAX-ACCESS read-only
                    STATUS current
                    DESCRIPTION "N/A"
                    DEFVAL { 0 }
                    ::= { analogObjects 40 }

        -- 1.3.6.1.4.1.9839.2.1.2.41
        eev-position-b OBJECT-TYPE
                    SYNTAX Integer32 (-32768..32767)
                    UNITS "N/A"
                    MAX-ACCESS read-only
                    STATUS current
                    DESCRIPTION "N/A"
                    DEFVAL { 0 }
                    ::= { analogObjects 41 }

        -- 1.3.6.1.4.1.9839.2.1.2.42
        voltage-1-l-bms OBJECT-TYPE
                    SYNTAX Integer32 (-32768..32767)
                    UNITS "N/A"
                    MAX-ACCESS read-only
                    STATUS current
                    DESCRIPTION "N/A"
                    DEFVAL { 0 }
                    ::= { analogObjects 42 }

        -- 1.3.6.1.4.1.9839.2.1.2.43
        voltage-2-l-bms OBJECT-TYPE
                    SYNTAX Integer32 (-32768..32767)
                    UNITS "N/A"
                    MAX-ACCESS read-only
                    STATUS current
                    DESCRIPTION "N/A"
                    DEFVAL { 0 }
                    ::= { analogObjects 43 }

        -- 1.3.6.1.4.1.9839.2.1.2.44
        voltage-3-l-bms OBJECT-TYPE
                    SYNTAX Integer32 (-32768..32767)
                    UNITS "N/A"
                    MAX-ACCESS read-only
                    STATUS current
                    DESCRIPTION "N/A"
                    DEFVAL { 0 }
                    ::= { analogObjects 44 }

        -- 1.3.6.1.4.1.9839.2.1.2.45
        current-1-l-bms OBJECT-TYPE
                    SYNTAX Integer32 (-32768..32767)
                    UNITS "N/A"
                    MAX-ACCESS read-only
                    STATUS current
                    DESCRIPTION "N/A"
                    DEFVAL { 0 }
                    ::= { analogObjects 45 }

        -- 1.3.6.1.4.1.9839.2.1.2.46
        current-2-l-bms OBJECT-TYPE
                    SYNTAX Integer32 (-32768..32767)
                    UNITS "N/A"
                    MAX-ACCESS read-only
                    STATUS current
                    DESCRIPTION "N/A"
                    DEFVAL { 0 }
                    ::= { analogObjects 46 }

        -- 1.3.6.1.4.1.9839.2.1.2.47
        current-3-l-bms OBJECT-TYPE
                    SYNTAX Integer32 (-32768..32767)
                    UNITS "N/A"
                    MAX-ACCESS read-only
                    STATUS current
                    DESCRIPTION "N/A"
                    DEFVAL { 0 }
                    ::= { analogObjects 47 }

        -- 1.3.6.1.4.1.9839.2.1.2.48
        power-1-l-bms OBJECT-TYPE
                    SYNTAX Integer32 (-32768..32767)
                    UNITS "N/A"
                    MAX-ACCESS read-only
                    STATUS current
                    DESCRIPTION "N/A"
                    DEFVAL { 0 }
                    ::= { analogObjects 48 }

        -- 1.3.6.1.4.1.9839.2.1.2.49
        power-2-l-bms OBJECT-TYPE
                    SYNTAX Integer32 (-32768..32767)
                    UNITS "N/A"
                    MAX-ACCESS read-only
                    STATUS current
                    DESCRIPTION "N/A"
                    DEFVAL { 0 }
                    ::= { analogObjects 49 }

        -- 1.3.6.1.4.1.9839.2.1.2.50
        power-3-l-bms OBJECT-TYPE
                    SYNTAX Integer32 (-32768..32767)
                    UNITS "N/A"
                    MAX-ACCESS read-only
                    STATUS current
                    DESCRIPTION "N/A"
                    DEFVAL { 0 }
                    ::= { analogObjects 50 }

        -- 1.3.6.1.4.1.9839.2.1.2.51
        reactive-1-l-bms OBJECT-TYPE
                    SYNTAX Integer32 (-32768..32767)
                    UNITS "N/A"
                    MAX-ACCESS read-only
                    STATUS current
                    DESCRIPTION "N/A"
                    DEFVAL { 0 }
                    ::= { analogObjects 51 }

        -- 1.3.6.1.4.1.9839.2.1.2.52
        reactive-2-l-bms OBJECT-TYPE
                    SYNTAX Integer32 (-32768..32767)
                    UNITS "N/A"
                    MAX-ACCESS read-only
                    STATUS current
                    DESCRIPTION "N/A"
                    DEFVAL { 0 }
                    ::= { analogObjects 52 }

        -- 1.3.6.1.4.1.9839.2.1.2.53
        reactive-3-l-bms OBJECT-TYPE
                    SYNTAX Integer32 (-32768..32767)
                    UNITS "N/A"
                    MAX-ACCESS read-only
                    STATUS current
                    DESCRIPTION "N/A"
                    DEFVAL { 0 }
                    ::= { analogObjects 53 }

        -- 1.3.6.1.4.1.9839.2.1.2.54
        power-factor-bms OBJECT-TYPE
                    SYNTAX Integer32 (-32768..32767)
                    UNITS "N/A"
                    MAX-ACCESS read-only
                    STATUS current
                    DESCRIPTION "N/A"
                    DEFVAL { 0 }
                    ::= { analogObjects 54 }

        -- 1.3.6.1.4.1.9839.2.1.2.55
        active-energy-h-bms OBJECT-TYPE
                    SYNTAX Integer32 (-32768..32767)
                    UNITS "N/A"
                    MAX-ACCESS read-only
                    STATUS current
                    DESCRIPTION "N/A"
                    DEFVAL { 0 }
                    ::= { analogObjects 55 }

        -- 1.3.6.1.4.1.9839.2.1.2.56
        active-energy-l-bms OBJECT-TYPE
                    SYNTAX Integer32 (-32768..32767)
                    UNITS "N/A"
                    MAX-ACCESS read-only
                    STATUS current
                    DESCRIPTION "N/A"
                    DEFVAL { 0 }
                    ::= { analogObjects 56 }

        -- 1.3.6.1.4.1.9839.2.1.2.57
        apparent-energy-h-bms OBJECT-TYPE
                    SYNTAX Integer32 (-32768..32767)
                    UNITS "N/A"
                    MAX-ACCESS read-only
                    STATUS current
                    DESCRIPTION "N/A"
                    DEFVAL { 0 }
                    ::= { analogObjects 57 }

        -- 1.3.6.1.4.1.9839.2.1.2.58
        apparent-energy-l-bms OBJECT-TYPE
                    SYNTAX Integer32 (-32768..32767)
                    UNITS "N/A"
                    MAX-ACCESS read-only
                    STATUS current
                    DESCRIPTION "N/A"
                    DEFVAL { 0 }
                    ::= { analogObjects 58 }

        -- 1.3.6.1.4.1.9839.2.1.2.59
        disp-aout1 OBJECT-TYPE
                    SYNTAX Integer32 (0..3277)
                    UNITS "N/A"
                    MAX-ACCESS read-only
                    STATUS current
                    DESCRIPTION "N/A"
                    DEFVAL { 0 }
                    ::= { analogObjects 59 }

        -- 1.3.6.1.4.1.9839.2.1.2.60
        disp-aout2 OBJECT-TYPE
                    SYNTAX Integer32 (0..3277)
                    UNITS "N/A"
                    MAX-ACCESS read-only
                    STATUS current
                    DESCRIPTION "N/A"
                    DEFVAL { 0 }
                    ::= { analogObjects 60 }

        -- 1.3.6.1.4.1.9839.2.1.2.61
        disp-aout3 OBJECT-TYPE
                    SYNTAX Integer32 (0..3277)
                    UNITS "N/A"
                    MAX-ACCESS read-only
                    STATUS current
                    DESCRIPTION "N/A"
                    DEFVAL { 0 }
                    ::= { analogObjects 61 }

        -- 1.3.6.1.4.1.9839.2.1.2.62
        disp-aout4 OBJECT-TYPE
                    SYNTAX Integer32 (0..999)
                    UNITS "N/A"
                    MAX-ACCESS read-only
                    STATUS current
                    DESCRIPTION "N/A"
                    DEFVAL { 0 }
                    ::= { analogObjects 62 }

        -- 1.3.6.1.4.1.9839.2.1.2.63
        dcra-fan-setpoint OBJECT-TYPE
                    SYNTAX Integer32 (0..400)
                    UNITS "N/A"
                    MAX-ACCESS read-write
                    STATUS current
                    DESCRIPTION "N/A"
                    DEFVAL { 280 }
                    ::= { analogObjects 63 }

        -- 1.3.6.1.4.1.9839.2.1.2.64
        dcra-fan-diff OBJECT-TYPE
                    SYNTAX Integer32 (0..999)
                    UNITS "N/A"
                    MAX-ACCESS read-write
                    STATUS current
                    DESCRIPTION "N/A"
                    DEFVAL { 0 }
                    ::= { analogObjects 64 }

        -- 1.3.6.1.4.1.9839.2.1.2.65
        dcra-fan-min-speed OBJECT-TYPE
                    SYNTAX Integer32 (0..500)
                    UNITS "N/A"
                    MAX-ACCESS read-write
                    STATUS current
                    DESCRIPTION "N/A"
                    DEFVAL { 0 }
                    ::= { analogObjects 65 }

        -- 1.3.6.1.4.1.9839.2.1.2.66
        dcra-fan-max-speed OBJECT-TYPE
                    SYNTAX Integer32 (500..1000)
                    UNITS "bar x10"
                    MAX-ACCESS read-write
                    STATUS current
                    DESCRIPTION "N/A"
                    DEFVAL { 1000 }
                    ::= { analogObjects 66 }

        -- 1.3.6.1.4.1.9839.2.1.2.301
        set-temp1 OBJECT-TYPE
                    SYNTAX Integer32 (5..400)
                    UNITS "C x10"
                    MAX-ACCESS read-write
                    STATUS current
                    DESCRIPTION "Time Zone 1 Temperature Set Point"
                    DEFVAL { 210 }
                    ::= { analogObjects 301 }

        -- 1.3.6.1.4.1.9839.2.1.2.302
        set-temp2 OBJECT-TYPE
                    SYNTAX Integer32 (5..400)
                    UNITS "C x10"
                    MAX-ACCESS read-write
                    STATUS current
                    DESCRIPTION "Time Zone 2 Temperature Set Point"
                    DEFVAL { 210 }
                    ::= { analogObjects 302 }

        -- 1.3.6.1.4.1.9839.2.1.2.303
        set-temp3 OBJECT-TYPE
                    SYNTAX Integer32 (5..400)
                    UNITS "C x10"
                    MAX-ACCESS read-write
                    STATUS current
                    DESCRIPTION "Time Zone 3 Temperature Set Point"
                    DEFVAL { 210 }
                    ::= { analogObjects 303 }

        -- 1.3.6.1.4.1.9839.2.1.2.304
        set-temp4 OBJECT-TYPE
                    SYNTAX Integer32 (5..400)
                    UNITS "C x10"
                    MAX-ACCESS read-write
                    STATUS current
                    DESCRIPTION "Time Zone 4 Temperature Set Point"
                    DEFVAL { 210 }
                    ::= { analogObjects 304 }

        -- 1.3.6.1.4.1.9839.2.1.2.305
        set-hum1 OBJECT-TYPE
                    SYNTAX Integer32 (0..999)
                    UNITS "%Rh x10"
                    MAX-ACCESS read-write
                    STATUS current
                    DESCRIPTION "Time Zone 1 Humidity Set Point"
                    DEFVAL { 500 }
                    ::= { analogObjects 305 }

        -- 1.3.6.1.4.1.9839.2.1.2.306
        set-hum2 OBJECT-TYPE
                    SYNTAX Integer32 (0..999)
                    UNITS "%Rh x10"
                    MAX-ACCESS read-write
                    STATUS current
                    DESCRIPTION "Time Zone 2 Humidity Set Point"
                    DEFVAL { 500 }
                    ::= { analogObjects 306 }

        -- 1.3.6.1.4.1.9839.2.1.2.307
        set-hum3 OBJECT-TYPE
                    SYNTAX Integer32 (0..999)
                    UNITS "%Rh x10"
                    MAX-ACCESS read-write
                    STATUS current
                    DESCRIPTION "Time Zone 3 Humidity Set Point"
                    DEFVAL { 500 }
                    ::= { analogObjects 307 }

        -- 1.3.6.1.4.1.9839.2.1.2.308
        set-hum4 OBJECT-TYPE
                    SYNTAX Integer32 (0..999)
                    UNITS "%Rh x10"
                    MAX-ACCESS read-write
                    STATUS current
                    DESCRIPTION "Time Zone 4 Humidity Set Point"
                    DEFVAL { 500 }
                    ::= { analogObjects 308 }

        -- 1.3.6.1.4.1.9839.2.1.2.309
        chilled-water-setpoint OBJECT-TYPE
                    SYNTAX Integer32 (50..250)
                    UNITS "C x10"
                    MAX-ACCESS read-write
                    STATUS current
                    DESCRIPTION "Combicool Chilled Water Temperature Limit"
                    DEFVAL { 100 }
                    ::= { analogObjects 309 }

        -- 1.3.6.1.4.1.9839.2.1.2.310
        tile-unit-average-temp OBJECT-TYPE
                    SYNTAX Integer32 (-32768..32767)
                    UNITS "C x10"
                    MAX-ACCESS read-write
                    STATUS current
                    DESCRIPTION "Tile Unit (LECU) Average Temperature (FROM THE BMS)"
                    DEFVAL { 0 }
                    ::= { analogObjects 310 }

        -- 1.3.6.1.4.1.9839.2.1.2.311
        room-t-ef-1 OBJECT-TYPE
                    SYNTAX Integer32 (0..3277)
                    UNITS "C x10"
                    MAX-ACCESS read-only
                    STATUS current
                    DESCRIPTION "LECU 1 Room Temperature"
                    DEFVAL { 0 }
                    ::= { analogObjects 311 }

        -- 1.3.6.1.4.1.9839.2.1.2.312
        ufloor-ef-1 OBJECT-TYPE
                    SYNTAX Integer32 (-3277..3277)
                    UNITS "C x10"
                    MAX-ACCESS read-only
                    STATUS current
                    DESCRIPTION "LECU 1 Underfloor Temperature"
                    DEFVAL { 0 }
                    ::= { analogObjects 312 }

        -- 1.3.6.1.4.1.9839.2.1.2.313
        temp-sp-ef-1 OBJECT-TYPE
                    SYNTAX Integer32 (0..32767)
                    UNITS "C x10"
                    MAX-ACCESS read-write
                    STATUS current
                    DESCRIPTION "LECU 1 Temperature Setpoint"
                    DEFVAL { 0 }
                    ::= { analogObjects 313 }

        -- 1.3.6.1.4.1.9839.2.1.2.314
        damperd-ef-1 OBJECT-TYPE
                    SYNTAX Integer32 (-3277..3277)
                    UNITS "% x10"
                    MAX-ACCESS read-only
                    STATUS current
                    DESCRIPTION "LECU 1 Damper Demand"
                    DEFVAL { 0 }
                    ::= { analogObjects 314 }

        -- 1.3.6.1.4.1.9839.2.1.2.315
        room-t-ef-2 OBJECT-TYPE
                    SYNTAX Integer32 (-3277..3277)
                    UNITS "C x10"
                    MAX-ACCESS read-only
                    STATUS current
                    DESCRIPTION "LECU 2 Room Temperature"
                    DEFVAL { 0 }
                    ::= { analogObjects 315 }

        -- 1.3.6.1.4.1.9839.2.1.2.316
        ufloor-ef-2 OBJECT-TYPE
                    SYNTAX Integer32 (-3277..3277)
                    UNITS "C x10"
                    MAX-ACCESS read-only
                    STATUS current
                    DESCRIPTION "LECU 2 Underfloor Temperature"
                    DEFVAL { 0 }
                    ::= { analogObjects 316 }

        -- 1.3.6.1.4.1.9839.2.1.2.317
        temp-sp-ef-2 OBJECT-TYPE
                    SYNTAX Integer32 (0..32767)
                    UNITS "C x10"
                    MAX-ACCESS read-write
                    STATUS current
                    DESCRIPTION "LECU 2 Temperature Setpoint"
                    DEFVAL { 0 }
                    ::= { analogObjects 317 }

        -- 1.3.6.1.4.1.9839.2.1.2.318
        damperd-ef-2 OBJECT-TYPE
                    SYNTAX Integer32 (-3277..3277)
                    UNITS "% x10"
                    MAX-ACCESS read-only
                    STATUS current
                    DESCRIPTION "LECU 2 Damper Demand"
                    DEFVAL { 0 }
                    ::= { analogObjects 318 }

        -- 1.3.6.1.4.1.9839.2.1.2.319
        room-t-ef-3 OBJECT-TYPE
                    SYNTAX Integer32 (-3277..3277)
                    UNITS "C x10"
                    MAX-ACCESS read-only
                    STATUS current
                    DESCRIPTION "LECU 3 Room Temperature"
                    DEFVAL { 0 }
                    ::= { analogObjects 319 }

        -- 1.3.6.1.4.1.9839.2.1.2.320
        ufloor-ef-3 OBJECT-TYPE
                    SYNTAX Integer32 (-3277..3277)
                    UNITS "C x10"
                    MAX-ACCESS read-only
                    STATUS current
                    DESCRIPTION "LECU 3 Underfloor Temperature"
                    DEFVAL { 0 }
                    ::= { analogObjects 320 }

        -- 1.3.6.1.4.1.9839.2.1.2.321
        temp-sp-ef-3 OBJECT-TYPE
                    SYNTAX Integer32 (0..32767)
                    UNITS "C x10"
                    MAX-ACCESS read-write
                    STATUS current
                    DESCRIPTION "LECU 3 Temperature Setpoint"
                    DEFVAL { 0 }
                    ::= { analogObjects 321 }

        -- 1.3.6.1.4.1.9839.2.1.2.322
        damperd-ef-3 OBJECT-TYPE
                    SYNTAX Integer32 (-3277..3277)
                    UNITS "% x10"
                    MAX-ACCESS read-only
                    STATUS current
                    DESCRIPTION "LECU 3 Damper Demand"
                    DEFVAL { 0 }
                    ::= { analogObjects 322 }

        -- 1.3.6.1.4.1.9839.2.1.2.323
        room-t-ef-4 OBJECT-TYPE
                    SYNTAX Integer32 (-3277..3277)
                    UNITS "C x10"
                    MAX-ACCESS read-only
                    STATUS current
                    DESCRIPTION "LECU 4 Room Temperature"
                    DEFVAL { 0 }
                    ::= { analogObjects 323 }

        -- 1.3.6.1.4.1.9839.2.1.2.324
        ufloor-ef-4 OBJECT-TYPE
                    SYNTAX Integer32 (-3277..3277)
                    UNITS "C x10"
                    MAX-ACCESS read-only
                    STATUS current
                    DESCRIPTION "LECU 4 Underfloor Temperature"
                    DEFVAL { 0 }
                    ::= { analogObjects 324 }

        -- 1.3.6.1.4.1.9839.2.1.2.325
        temp-sp-ef-4 OBJECT-TYPE
                    SYNTAX Integer32 (0..32767)
                    UNITS "C x10"
                    MAX-ACCESS read-write
                    STATUS current
                    DESCRIPTION "LECU 4 Temperature Setpoint"
                    DEFVAL { 0 }
                    ::= { analogObjects 325 }

        -- 1.3.6.1.4.1.9839.2.1.2.326
        damperd-ef-4 OBJECT-TYPE
                    SYNTAX Integer32 (-3277..3277)
                    UNITS "% x10"
                    MAX-ACCESS read-only
                    STATUS current
                    DESCRIPTION "LECU 4 Damper Demand"
                    DEFVAL { 0 }
                    ::= { analogObjects 326 }

        -- 1.3.6.1.4.1.9839.2.1.2.327
        room-t-ef-5 OBJECT-TYPE
                    SYNTAX Integer32 (-3277..3277)
                    UNITS "C x10"
                    MAX-ACCESS read-only
                    STATUS current
                    DESCRIPTION "LECU 5 Room Temperature"
                    DEFVAL { 0 }
                    ::= { analogObjects 327 }

        -- 1.3.6.1.4.1.9839.2.1.2.328
        ufloor-ef-5 OBJECT-TYPE
                    SYNTAX Integer32 (-3277..3277)
                    UNITS "C x10"
                    MAX-ACCESS read-only
                    STATUS current
                    DESCRIPTION "LECU 5 Underfloor Temperature"
                    DEFVAL { 0 }
                    ::= { analogObjects 328 }

        -- 1.3.6.1.4.1.9839.2.1.2.329
        temp-sp-ef-5 OBJECT-TYPE
                    SYNTAX Integer32 (0..32767)
                    UNITS "C x10"
                    MAX-ACCESS read-write
                    STATUS current
                    DESCRIPTION "LECU 5 Temperature Setpoint"
                    DEFVAL { 0 }
                    ::= { analogObjects 329 }

        -- 1.3.6.1.4.1.9839.2.1.2.330
        damperd-ef-5 OBJECT-TYPE
                    SYNTAX Integer32 (-3277..3277)
                    UNITS "% x10"
                    MAX-ACCESS read-only
                    STATUS current
                    DESCRIPTION "LECU 5 Damper Demand"
                    DEFVAL { 0 }
                    ::= { analogObjects 330 }

        -- 1.3.6.1.4.1.9839.2.1.2.331
        room-t-ef-6 OBJECT-TYPE
                    SYNTAX Integer32 (-3277..3277)
                    UNITS "C x10"
                    MAX-ACCESS read-only
                    STATUS current
                    DESCRIPTION "LECU 6 Room Temperature"
                    DEFVAL { 0 }
                    ::= { analogObjects 331 }

        -- 1.3.6.1.4.1.9839.2.1.2.332
        ufloor-ef-6 OBJECT-TYPE
                    SYNTAX Integer32 (-3277..3277)
                    UNITS "C x10"
                    MAX-ACCESS read-only
                    STATUS current
                    DESCRIPTION "LECU 6 Underfloor Temperature"
                    DEFVAL { 0 }
                    ::= { analogObjects 332 }

        -- 1.3.6.1.4.1.9839.2.1.2.333
        temp-sp-ef-6 OBJECT-TYPE
                    SYNTAX Integer32 (0..32767)
                    UNITS "C x10"
                    MAX-ACCESS read-write
                    STATUS current
                    DESCRIPTION "LECU 6 Temperature Setpoint"
                    DEFVAL { 0 }
                    ::= { analogObjects 333 }

        -- 1.3.6.1.4.1.9839.2.1.2.334
        damperd-ef-6 OBJECT-TYPE
                    SYNTAX Integer32 (-3277..3277)
                    UNITS "% x10"
                    MAX-ACCESS read-only
                    STATUS current
                    DESCRIPTION "LECU 6 Damper Demand"
                    DEFVAL { 0 }
                    ::= { analogObjects 334 }

        -- 1.3.6.1.4.1.9839.2.1.2.335
        room-t-ef-7 OBJECT-TYPE
                    SYNTAX Integer32 (-3277..3277)
                    UNITS "C x10"
                    MAX-ACCESS read-only
                    STATUS current
                    DESCRIPTION "LECU 7 Room Temperature"
                    DEFVAL { 0 }
                    ::= { analogObjects 335 }

        -- 1.3.6.1.4.1.9839.2.1.2.336
        ufloor-ef-7 OBJECT-TYPE
                    SYNTAX Integer32 (-3277..3277)
                    UNITS "C x10"
                    MAX-ACCESS read-only
                    STATUS current
                    DESCRIPTION "LECU 7 Underfloor Temperature"
                    DEFVAL { 0 }
                    ::= { analogObjects 336 }

        -- 1.3.6.1.4.1.9839.2.1.2.337
        temp-sp-ef-7 OBJECT-TYPE
                    SYNTAX Integer32 (0..32767)
                    UNITS "C x10"
                    MAX-ACCESS read-write
                    STATUS current
                    DESCRIPTION "LECU 7 Temperature Setpoint"
                    DEFVAL { 0 }
                    ::= { analogObjects 337 }

        -- 1.3.6.1.4.1.9839.2.1.2.338
        damperd-ef-7 OBJECT-TYPE
                    SYNTAX Integer32 (-3277..3277)
                    UNITS "% x10"
                    MAX-ACCESS read-only
                    STATUS current
                    DESCRIPTION "LECU 7 Damper Demand"
                    DEFVAL { 0 }
                    ::= { analogObjects 338 }

        -- 1.3.6.1.4.1.9839.2.1.2.339
        room-t-ef-8 OBJECT-TYPE
                    SYNTAX Integer32 (-3277..3277)
                    UNITS "C x10"
                    MAX-ACCESS read-only
                    STATUS current
                    DESCRIPTION "LECU 8 Room Temperature"
                    DEFVAL { 0 }
                    ::= { analogObjects 339 }

        -- 1.3.6.1.4.1.9839.2.1.2.340
        ufloor-ef-8 OBJECT-TYPE
                    SYNTAX Integer32 (-3277..3277)
                    UNITS "C x10"
                    MAX-ACCESS read-only
                    STATUS current
                    DESCRIPTION "LECU 8 Underfloor Temperature"
                    DEFVAL { 0 }
                    ::= { analogObjects 340 }

        -- 1.3.6.1.4.1.9839.2.1.2.341
        temp-sp-ef-8 OBJECT-TYPE
                    SYNTAX Integer32 (0..32767)
                    UNITS "C x10"
                    MAX-ACCESS read-write
                    STATUS current
                    DESCRIPTION "LECU 8 Temperature Setpoint"
                    DEFVAL { 0 }
                    ::= { analogObjects 341 }

        -- 1.3.6.1.4.1.9839.2.1.2.342
        damperd-ef-8 OBJECT-TYPE
                    SYNTAX Integer32 (-3277..3277)
                    UNITS "% x10"
                    MAX-ACCESS read-only
                    STATUS current
                    DESCRIPTION "LECU 8 Damper Demand"
                    DEFVAL { 0 }
                    ::= { analogObjects 342 }

        -- 1.3.6.1.4.1.9839.2.1.2.343
        room-t-ef-9 OBJECT-TYPE
                    SYNTAX Integer32 (-3277..3277)
                    UNITS "C x10"
                    MAX-ACCESS read-only
                    STATUS current
                    DESCRIPTION "LECU 9 Room Temperature"
                    DEFVAL { 0 }
                    ::= { analogObjects 343 }

        -- 1.3.6.1.4.1.9839.2.1.2.344
        ufloor-ef-9 OBJECT-TYPE
                    SYNTAX Integer32 (-3277..3277)
                    UNITS "C x10"
                    MAX-ACCESS read-only
                    STATUS current
                    DESCRIPTION "LECU 9 Underfloor Temperature"
                    DEFVAL { 0 }
                    ::= { analogObjects 344 }

        -- 1.3.6.1.4.1.9839.2.1.2.345
        temp-sp-ef-9 OBJECT-TYPE
                    SYNTAX Integer32 (0..32767)
                    UNITS "C x10"
                    MAX-ACCESS read-write
                    STATUS current
                    DESCRIPTION "LECU 9 Temperature Setpoint"
                    DEFVAL { 0 }
                    ::= { analogObjects 345 }

        -- 1.3.6.1.4.1.9839.2.1.2.346
        damperd-ef-9 OBJECT-TYPE
                    SYNTAX Integer32 (-3277..3277)
                    UNITS "% x10"
                    MAX-ACCESS read-only
                    STATUS current
                    DESCRIPTION "LECU 9 Damper Demand"
                    DEFVAL { 0 }
                    ::= { analogObjects 346 }

        -- 1.3.6.1.4.1.9839.2.1.2.347
        room-t-ef-10 OBJECT-TYPE
                    SYNTAX Integer32 (-3277..3277)
                    UNITS "C x10"
                    MAX-ACCESS read-only
                    STATUS current
                    DESCRIPTION "LECU 10 Room Temperature"
                    DEFVAL { 0 }
                    ::= { analogObjects 347 }

        -- 1.3.6.1.4.1.9839.2.1.2.348
        ufloor-ef-10 OBJECT-TYPE
                    SYNTAX Integer32 (-3277..3277)
                    UNITS "C x10"
                    MAX-ACCESS read-only
                    STATUS current
                    DESCRIPTION "LECU 10 Underfloor Temperature"
                    DEFVAL { 0 }
                    ::= { analogObjects 348 }

        -- 1.3.6.1.4.1.9839.2.1.2.349
        temp-sp-ef-10 OBJECT-TYPE
                    SYNTAX Integer32 (0..32767)
                    UNITS "C x10"
                    MAX-ACCESS read-write
                    STATUS current
                    DESCRIPTION "LECU 10 Temperature Setpoint"
                    DEFVAL { 0 }
                    ::= { analogObjects 349 }

        -- 1.3.6.1.4.1.9839.2.1.2.350
        damperd-ef-10 OBJECT-TYPE
                    SYNTAX Integer32 (-3277..3277)
                    UNITS "% x10"
                    MAX-ACCESS read-only
                    STATUS current
                    DESCRIPTION "LECU 10 Damper Demand"
                    DEFVAL { 0 }
                    ::= { analogObjects 350 }

        -- 1.3.6.1.4.1.9839.2.1.2.351
        room-t-ef-11 OBJECT-TYPE
                    SYNTAX Integer32 (-3277..3277)
                    UNITS "C x10"
                    MAX-ACCESS read-only
                    STATUS current
                    DESCRIPTION "LECU 11 Room Temperature"
                    DEFVAL { 0 }
                    ::= { analogObjects 351 }

        -- 1.3.6.1.4.1.9839.2.1.2.352
        ufloor-ef-11 OBJECT-TYPE
                    SYNTAX Integer32 (-3277..3277)
                    UNITS "C x10"
                    MAX-ACCESS read-only
                    STATUS current
                    DESCRIPTION "LECU 11 Underfloor Temperature"
                    DEFVAL { 0 }
                    ::= { analogObjects 352 }

        -- 1.3.6.1.4.1.9839.2.1.2.353
        temp-sp-ef-11 OBJECT-TYPE
                    SYNTAX Integer32 (0..32767)
                    UNITS "C x10"
                    MAX-ACCESS read-write
                    STATUS current
                    DESCRIPTION "LECU 11 Temperature Setpoint"
                    DEFVAL { 0 }
                    ::= { analogObjects 353 }

        -- 1.3.6.1.4.1.9839.2.1.2.354
        damperd-ef-11 OBJECT-TYPE
                    SYNTAX Integer32 (-3277..3277)
                    UNITS "% x10"
                    MAX-ACCESS read-only
                    STATUS current
                    DESCRIPTION "LECU 11 Damper Demand"
                    DEFVAL { 0 }
                    ::= { analogObjects 354 }

        -- 1.3.6.1.4.1.9839.2.1.2.355
        room-t-ef-12 OBJECT-TYPE
                    SYNTAX Integer32 (-3277..3277)
                    UNITS "C x10"
                    MAX-ACCESS read-only
                    STATUS current
                    DESCRIPTION "LECU 12 Room Temperature"
                    DEFVAL { 0 }
                    ::= { analogObjects 355 }

        -- 1.3.6.1.4.1.9839.2.1.2.356
        ufloor-ef-12 OBJECT-TYPE
                    SYNTAX Integer32 (-3277..3277)
                    UNITS "C x10"
                    MAX-ACCESS read-only
                    STATUS current
                    DESCRIPTION "LECU 12 Underfloor Temperature"
                    DEFVAL { 0 }
                    ::= { analogObjects 356 }

        -- 1.3.6.1.4.1.9839.2.1.2.357
        temp-sp-ef-12 OBJECT-TYPE
                    SYNTAX Integer32 (0..32767)
                    UNITS "C x10"
                    MAX-ACCESS read-write
                    STATUS current
                    DESCRIPTION "LECU 12 Temperature Setpoint"
                    DEFVAL { 0 }
                    ::= { analogObjects 357 }

        -- 1.3.6.1.4.1.9839.2.1.2.358
        damperd-ef-12 OBJECT-TYPE
                    SYNTAX Integer32 (-3277..3277)
                    UNITS "% x10"
                    MAX-ACCESS read-only
                    STATUS current
                    DESCRIPTION "LECU 12 Damper Demand"
                    DEFVAL { 0 }
                    ::= { analogObjects 358 }

        -- 1.3.6.1.4.1.9839.2.1.2.359
        room-t-ef-13 OBJECT-TYPE
                    SYNTAX Integer32 (-3277..3277)
                    UNITS "C x10"
                    MAX-ACCESS read-only
                    STATUS current
                    DESCRIPTION "LECU 13 Room Temperature"
                    DEFVAL { 0 }
                    ::= { analogObjects 359 }

        -- 1.3.6.1.4.1.9839.2.1.2.360
        ufloor-ef-13 OBJECT-TYPE
                    SYNTAX Integer32 (-3277..3277)
                    UNITS "C x10"
                    MAX-ACCESS read-only
                    STATUS current
                    DESCRIPTION "LECU 13 Underfloor Temperature"
                    DEFVAL { 0 }
                    ::= { analogObjects 360 }

        -- 1.3.6.1.4.1.9839.2.1.2.361
        temp-sp-ef-13 OBJECT-TYPE
                    SYNTAX Integer32 (0..32767)
                    UNITS "C x10"
                    MAX-ACCESS read-write
                    STATUS current
                    DESCRIPTION "LECU 13 Temperature Setpoint"
                    DEFVAL { 0 }
                    ::= { analogObjects 361 }

        -- 1.3.6.1.4.1.9839.2.1.2.362
        damperd-ef-13 OBJECT-TYPE
                    SYNTAX Integer32 (-3277..3277)
                    UNITS "% x10"
                    MAX-ACCESS read-only
                    STATUS current
                    DESCRIPTION "LECU 13 Damper Demand"
                    DEFVAL { 0 }
                    ::= { analogObjects 362 }

        -- 1.3.6.1.4.1.9839.2.1.2.363
        room-t-ef-14 OBJECT-TYPE
                    SYNTAX Integer32 (-3277..3277)
                    UNITS "C x10"
                    MAX-ACCESS read-only
                    STATUS current
                    DESCRIPTION "LECU 14 Room Temperature"
                    DEFVAL { 0 }
                    ::= { analogObjects 363 }

        -- 1.3.6.1.4.1.9839.2.1.2.364
        ufloor-ef-14 OBJECT-TYPE
                    SYNTAX Integer32 (-3277..3277)
                    UNITS "C x10"
                    MAX-ACCESS read-only
                    STATUS current
                    DESCRIPTION "LECU 14 Underfloor Temperature"
                    DEFVAL { 0 }
                    ::= { analogObjects 364 }

        -- 1.3.6.1.4.1.9839.2.1.2.365
        temp-sp-ef-14 OBJECT-TYPE
                    SYNTAX Integer32 (0..32767)
                    UNITS "C x10"
                    MAX-ACCESS read-write
                    STATUS current
                    DESCRIPTION "LECU 14 Temperature Setpoint"
                    DEFVAL { 0 }
                    ::= { analogObjects 365 }

        -- 1.3.6.1.4.1.9839.2.1.2.366
        damperd-ef-14 OBJECT-TYPE
                    SYNTAX Integer32 (-3277..3277)
                    UNITS "% x10"
                    MAX-ACCESS read-only
                    STATUS current
                    DESCRIPTION "LECU 14 Damper Demand"
                    DEFVAL { 0 }
                    ::= { analogObjects 366 }

        -- 1.3.6.1.4.1.9839.2.1.2.367
        room-t-ef-15 OBJECT-TYPE
                    SYNTAX Integer32 (-3277..3277)
                    UNITS "C x10"
                    MAX-ACCESS read-only
                    STATUS current
                    DESCRIPTION "LECU 15 Room Temperature"
                    DEFVAL { 0 }
                    ::= { analogObjects 367 }

        -- 1.3.6.1.4.1.9839.2.1.2.368
        ufloor-ef-15 OBJECT-TYPE
                    SYNTAX Integer32 (-3277..3277)
                    UNITS "C x10"
                    MAX-ACCESS read-only
                    STATUS current
                    DESCRIPTION "LECU 15 Underfloor Temperature"
                    DEFVAL { 0 }
                    ::= { analogObjects 368 }

        -- 1.3.6.1.4.1.9839.2.1.2.369
        temp-sp-ef-15 OBJECT-TYPE
                    SYNTAX Integer32 (0..32767)
                    UNITS "C x10"
                    MAX-ACCESS read-write
                    STATUS current
                    DESCRIPTION "LECU 15 Temperature Setpoint"
                    DEFVAL { 0 }
                    ::= { analogObjects 369 }

        -- 1.3.6.1.4.1.9839.2.1.2.370
        damperd-ef-15 OBJECT-TYPE
                    SYNTAX Integer32 (-3277..3277)
                    UNITS "% x10"
                    MAX-ACCESS read-only
                    STATUS current
                    DESCRIPTION "LECU 15 Damper Demand"
                    DEFVAL { 0 }
                    ::= { analogObjects 370 }

        -- 1.3.6.1.4.1.9839.2.1.2.371
        room-t-ef-16 OBJECT-TYPE
                    SYNTAX Integer32 (-3277..3277)
                    UNITS "C x10"
                    MAX-ACCESS read-only
                    STATUS current
                    DESCRIPTION "LECU 16 Room Temperature"
                    DEFVAL { 0 }
                    ::= { analogObjects 371 }

        -- 1.3.6.1.4.1.9839.2.1.2.372
        ufloor-ef-16 OBJECT-TYPE
                    SYNTAX Integer32 (-3277..3277)
                    UNITS "C x10"
                    MAX-ACCESS read-only
                    STATUS current
                    DESCRIPTION "LECU 16 Underfloor Temperature"
                    DEFVAL { 0 }
                    ::= { analogObjects 372 }

        -- 1.3.6.1.4.1.9839.2.1.2.373
        temp-sp-ef-16 OBJECT-TYPE
                    SYNTAX Integer32 (0..32767)
                    UNITS "C x10"
                    MAX-ACCESS read-write
                    STATUS current
                    DESCRIPTION "LECU 16 Temperature Setpoint"
                    DEFVAL { 0 }
                    ::= { analogObjects 373 }

        -- 1.3.6.1.4.1.9839.2.1.2.374
        damperd-ef-16 OBJECT-TYPE
                    SYNTAX Integer32 (-3277..3277)
                    UNITS "% x10"
                    MAX-ACCESS read-only
                    STATUS current
                    DESCRIPTION "LECU 16 Damper Demand"
                    DEFVAL { 0 }
                    ::= { analogObjects 374 }

        -- 1.3.6.1.4.1.9839.2.1.2.375
        room-t-ef-17 OBJECT-TYPE
                    SYNTAX Integer32 (-3277..3277)
                    UNITS "C x10"
                    MAX-ACCESS read-only
                    STATUS current
                    DESCRIPTION "LECU 17 Room Temperature"
                    DEFVAL { 0 }
                    ::= { analogObjects 375 }

        -- 1.3.6.1.4.1.9839.2.1.2.376
        ufloor-ef-17 OBJECT-TYPE
                    SYNTAX Integer32 (-3277..3277)
                    UNITS "C x10"
                    MAX-ACCESS read-only
                    STATUS current
                    DESCRIPTION "LECU 17 Underfloor Temperature"
                    DEFVAL { 0 }
                    ::= { analogObjects 376 }

        -- 1.3.6.1.4.1.9839.2.1.2.377
        temp-sp-ef-17 OBJECT-TYPE
                    SYNTAX Integer32 (0..32767)
                    UNITS "C x10"
                    MAX-ACCESS read-write
                    STATUS current
                    DESCRIPTION "LECU 17 Temperature Setpoint"
                    DEFVAL { 0 }
                    ::= { analogObjects 377 }

        -- 1.3.6.1.4.1.9839.2.1.2.378
        damperd-ef-17 OBJECT-TYPE
                    SYNTAX Integer32 (-3277..3277)
                    UNITS "% x10"
                    MAX-ACCESS read-only
                    STATUS current
                    DESCRIPTION "LECU 17 Damper Demand"
                    DEFVAL { 0 }
                    ::= { analogObjects 378 }

        -- 1.3.6.1.4.1.9839.2.1.2.379
        room-t-ef-18 OBJECT-TYPE
                    SYNTAX Integer32 (-3277..3277)
                    UNITS "C x10"
                    MAX-ACCESS read-only
                    STATUS current
                    DESCRIPTION "LECU 18 Room Temperature"
                    DEFVAL { 0 }
                    ::= { analogObjects 379 }

        -- 1.3.6.1.4.1.9839.2.1.2.380
        ufloor-ef-18 OBJECT-TYPE
                    SYNTAX Integer32 (-3277..3277)
                    UNITS "C x10"
                    MAX-ACCESS read-only
                    STATUS current
                    DESCRIPTION "LECU 18 Underfloor Temperature"
                    DEFVAL { 0 }
                    ::= { analogObjects 380 }

        -- 1.3.6.1.4.1.9839.2.1.2.381
        temp-sp-ef-18 OBJECT-TYPE
                    SYNTAX Integer32 (0..32767)
                    UNITS "C x10"
                    MAX-ACCESS read-write
                    STATUS current
                    DESCRIPTION "LECU 18 Temperature Setpoint"
                    DEFVAL { 0 }
                    ::= { analogObjects 381 }

        -- 1.3.6.1.4.1.9839.2.1.2.382
        damperd-ef-18 OBJECT-TYPE
                    SYNTAX Integer32 (-3277..3277)
                    UNITS "% x10"
                    MAX-ACCESS read-only
                    STATUS current
                    DESCRIPTION "LECU 18 Damper Demand"
                    DEFVAL { 0 }
                    ::= { analogObjects 382 }

        -- 1.3.6.1.4.1.9839.2.1.2.383
        room-t-ef-19 OBJECT-TYPE
                    SYNTAX Integer32 (-3277..3277)
                    UNITS "C x10"
                    MAX-ACCESS read-only
                    STATUS current
                    DESCRIPTION "LECU 19 Room Temperature"
                    DEFVAL { 0 }
                    ::= { analogObjects 383 }

        -- 1.3.6.1.4.1.9839.2.1.2.384
        ufloor-ef-19 OBJECT-TYPE
                    SYNTAX Integer32 (-3277..3277)
                    UNITS "C x10"
                    MAX-ACCESS read-only
                    STATUS current
                    DESCRIPTION "LECU 19 Underfloor Temperature"
                    DEFVAL { 0 }
                    ::= { analogObjects 384 }

        -- 1.3.6.1.4.1.9839.2.1.2.385
        temp-sp-ef-19 OBJECT-TYPE
                    SYNTAX Integer32 (0..32767)
                    UNITS "C x10"
                    MAX-ACCESS read-write
                    STATUS current
                    DESCRIPTION "LECU 19 Temperature Setpoint"
                    DEFVAL { 0 }
                    ::= { analogObjects 385 }

        -- 1.3.6.1.4.1.9839.2.1.2.386
        damperd-ef-19 OBJECT-TYPE
                    SYNTAX Integer32 (-3277..3277)
                    UNITS "% x10"
                    MAX-ACCESS read-only
                    STATUS current
                    DESCRIPTION "LECU 19 Damper Demand"
                    DEFVAL { 0 }
                    ::= { analogObjects 386 }

        -- 1.3.6.1.4.1.9839.2.1.2.387
        room-t-ef-20 OBJECT-TYPE
                    SYNTAX Integer32 (-3277..3277)
                    UNITS "C x10"
                    MAX-ACCESS read-only
                    STATUS current
                    DESCRIPTION "LECU 20 Room Temperature"
                    DEFVAL { 0 }
                    ::= { analogObjects 387 }

        -- 1.3.6.1.4.1.9839.2.1.2.388
        ufloor-ef-20 OBJECT-TYPE
                    SYNTAX Integer32 (-3277..3277)
                    UNITS "C x10"
                    MAX-ACCESS read-only
                    STATUS current
                    DESCRIPTION "LECU 20 Underfloor Temperature"
                    DEFVAL { 0 }
                    ::= { analogObjects 388 }

        -- 1.3.6.1.4.1.9839.2.1.2.389
        temp-sp-ef-20 OBJECT-TYPE
                    SYNTAX Integer32 (0..32767)
                    UNITS "C x10"
                    MAX-ACCESS read-write
                    STATUS current
                    DESCRIPTION "LECU 20 Temperature Setpoint"
                    DEFVAL { 0 }
                    ::= { analogObjects 389 }

        -- 1.3.6.1.4.1.9839.2.1.2.390
        damperd-ef-20 OBJECT-TYPE
                    SYNTAX Integer32 (-3277..3277)
                    UNITS "% x10"
                    MAX-ACCESS read-only
                    STATUS current
                    DESCRIPTION "LECU 20 Damper Demand"
                    DEFVAL { 0 }
                    ::= { analogObjects 390 }

        -- 1.3.6.1.4.1.9839.2.1.2.391
        room-t-ef-21 OBJECT-TYPE
                    SYNTAX Integer32 (-3277..3277)
                    UNITS "C x10"
                    MAX-ACCESS read-only
                    STATUS current
                    DESCRIPTION "LECU 21 Room Temperature"
                    DEFVAL { 0 }
                    ::= { analogObjects 391 }

        -- 1.3.6.1.4.1.9839.2.1.2.392
        ufloor-ef-21 OBJECT-TYPE
                    SYNTAX Integer32 (-3277..3277)
                    UNITS "C x10"
                    MAX-ACCESS read-only
                    STATUS current
                    DESCRIPTION "LECU 21 Underfloor Temperature"
                    DEFVAL { 0 }
                    ::= { analogObjects 392 }

        -- 1.3.6.1.4.1.9839.2.1.2.393
        temp-sp-ef-21 OBJECT-TYPE
                    SYNTAX Integer32 (0..32767)
                    UNITS "C x10"
                    MAX-ACCESS read-write
                    STATUS current
                    DESCRIPTION "LECU 21 Temperature Setpoint"
                    DEFVAL { 0 }
                    ::= { analogObjects 393 }

        -- 1.3.6.1.4.1.9839.2.1.2.394
        damperd-ef-21 OBJECT-TYPE
                    SYNTAX Integer32 (-3277..3277)
                    UNITS "% x10"
                    MAX-ACCESS read-only
                    STATUS current
                    DESCRIPTION "LECU 21 Damper Demand"
                    DEFVAL { 0 }
                    ::= { analogObjects 394 }

        -- 1.3.6.1.4.1.9839.2.1.2.395
        room-t-ef-22 OBJECT-TYPE
                    SYNTAX Integer32 (-3277..3277)
                    UNITS "C x10"
                    MAX-ACCESS read-only
                    STATUS current
                    DESCRIPTION "LECU 22 Room Temperature"
                    DEFVAL { 0 }
                    ::= { analogObjects 395 }

        -- 1.3.6.1.4.1.9839.2.1.2.396
        ufloor-ef-22 OBJECT-TYPE
                    SYNTAX Integer32 (-3277..3277)
                    UNITS "C x10"
                    MAX-ACCESS read-only
                    STATUS current
                    DESCRIPTION "LECU 22 Underfloor Temperature"
                    DEFVAL { 0 }
                    ::= { analogObjects 396 }

        -- 1.3.6.1.4.1.9839.2.1.2.397
        temp-sp-ef-22 OBJECT-TYPE
                    SYNTAX Integer32 (0..32767)
                    UNITS "C x10"
                    MAX-ACCESS read-write
                    STATUS current
                    DESCRIPTION "LECU 22 Temperature Setpoint"
                    DEFVAL { 0 }
                    ::= { analogObjects 397 }

        -- 1.3.6.1.4.1.9839.2.1.2.398
        damperd-ef-22 OBJECT-TYPE
                    SYNTAX Integer32 (-3277..3277)
                    UNITS "% x10"
                    MAX-ACCESS read-only
                    STATUS current
                    DESCRIPTION "LECU 22 Damper Demand"
                    DEFVAL { 0 }
                    ::= { analogObjects 398 }

        -- 1.3.6.1.4.1.9839.2.1.2.399
        room-t-ef-23 OBJECT-TYPE
                    SYNTAX Integer32 (-3277..3277)
                    UNITS "C x10"
                    MAX-ACCESS read-only
                    STATUS current
                    DESCRIPTION "LECU 23 Room Temperature"
                    DEFVAL { 0 }
                    ::= { analogObjects 399 }

        -- 1.3.6.1.4.1.9839.2.1.2.400
        ufloor-ef-23 OBJECT-TYPE
                    SYNTAX Integer32 (-3277..3277)
                    UNITS "C x10"
                    MAX-ACCESS read-only
                    STATUS current
                    DESCRIPTION "LECU 23 Underfloor Temperature"
                    DEFVAL { 0 }
                    ::= { analogObjects 400 }

        -- 1.3.6.1.4.1.9839.2.1.2.401
        temp-sp-ef-23 OBJECT-TYPE
                    SYNTAX Integer32 (0..32767)
                    UNITS "C x10"
                    MAX-ACCESS read-write
                    STATUS current
                    DESCRIPTION "LECU 23 Temperature Setpoint"
                    DEFVAL { 0 }
                    ::= { analogObjects 401 }

        -- 1.3.6.1.4.1.9839.2.1.2.402
        damperd-ef-23 OBJECT-TYPE
                    SYNTAX Integer32 (-3277..3277)
                    UNITS "% x10"
                    MAX-ACCESS read-only
                    STATUS current
                    DESCRIPTION "LECU 23 Damper Demand"
                    DEFVAL { 0 }
                    ::= { analogObjects 402 }

        -- 1.3.6.1.4.1.9839.2.1.2.403
        room-t-ef-24 OBJECT-TYPE
                    SYNTAX Integer32 (-3277..3277)
                    UNITS "C x10"
                    MAX-ACCESS read-only
                    STATUS current
                    DESCRIPTION "LECU 24 Room Temperature"
                    DEFVAL { 0 }
                    ::= { analogObjects 403 }

        -- 1.3.6.1.4.1.9839.2.1.2.404
        ufloor-ef-24 OBJECT-TYPE
                    SYNTAX Integer32 (-3277..3277)
                    UNITS "C x10"
                    MAX-ACCESS read-only
                    STATUS current
                    DESCRIPTION "LECU 24 Underfloor Temperature"
                    DEFVAL { 0 }
                    ::= { analogObjects 404 }

        -- 1.3.6.1.4.1.9839.2.1.2.405
        temp-sp-ef-24 OBJECT-TYPE
                    SYNTAX Integer32 (0..32767)
                    UNITS "C x10"
                    MAX-ACCESS read-write
                    STATUS current
                    DESCRIPTION "LECU 24 Temperature Setpoint"
                    DEFVAL { 0 }
                    ::= { analogObjects 405 }

        -- 1.3.6.1.4.1.9839.2.1.2.406
        damperd-ef-24 OBJECT-TYPE
                    SYNTAX Integer32 (-3277..3277)
                    UNITS "% x10"
                    MAX-ACCESS read-only
                    STATUS current
                    DESCRIPTION "LECU 24 Damper Demand"
                    DEFVAL { 0 }
                    ::= { analogObjects 406 }

        -- 1.3.6.1.4.1.9839.2.1.2.407
        room-t-ef-25 OBJECT-TYPE
                    SYNTAX Integer32 (-3277..3277)
                    UNITS "C x10"
                    MAX-ACCESS read-only
                    STATUS current
                    DESCRIPTION "LECU 25 Room Temperature"
                    DEFVAL { 0 }
                    ::= { analogObjects 407 }

        -- 1.3.6.1.4.1.9839.2.1.2.408
        ufloor-ef-25 OBJECT-TYPE
                    SYNTAX Integer32 (-3277..3277)
                    UNITS "C x10"
                    MAX-ACCESS read-only
                    STATUS current
                    DESCRIPTION "LECU 25 Underfloor Temperature"
                    DEFVAL { 0 }
                    ::= { analogObjects 408 }

        -- 1.3.6.1.4.1.9839.2.1.2.409
        temp-sp-ef-25 OBJECT-TYPE
                    SYNTAX Integer32 (0..32767)
                    UNITS "C x10"
                    MAX-ACCESS read-write
                    STATUS current
                    DESCRIPTION "LECU 25 Temperature Setpoint"
                    DEFVAL { 0 }
                    ::= { analogObjects 409 }

        -- 1.3.6.1.4.1.9839.2.1.2.410
        damperd-ef-25 OBJECT-TYPE
                    SYNTAX Integer32 (-3277..3277)
                    UNITS "% x10"
                    MAX-ACCESS read-only
                    STATUS current
                    DESCRIPTION "LECU 25 Damper Demand"
                    DEFVAL { 0 }
                    ::= { analogObjects 410 }

        -- 1.3.6.1.4.1.9839.2.1.2.411
        room-t-ef-26 OBJECT-TYPE
                    SYNTAX Integer32 (-3277..3277)
                    UNITS "C x10"
                    MAX-ACCESS read-only
                    STATUS current
                    DESCRIPTION "LECU 26 Room Temperature"
                    DEFVAL { 0 }
                    ::= { analogObjects 411 }

        -- 1.3.6.1.4.1.9839.2.1.2.412
        ufloor-ef-26 OBJECT-TYPE
                    SYNTAX Integer32 (-3277..3277)
                    UNITS "C x10"
                    MAX-ACCESS read-only
                    STATUS current
                    DESCRIPTION "LECU 26 Underfloor Temperature"
                    DEFVAL { 0 }
                    ::= { analogObjects 412 }

        -- 1.3.6.1.4.1.9839.2.1.2.413
        temp-sp-ef-26 OBJECT-TYPE
                    SYNTAX Integer32 (0..32767)
                    UNITS "C x10"
                    MAX-ACCESS read-write
                    STATUS current
                    DESCRIPTION "LECU 26 Temperature Setpoint"
                    DEFVAL { 0 }
                    ::= { analogObjects 413 }

        -- 1.3.6.1.4.1.9839.2.1.2.414
        damperd-ef-26 OBJECT-TYPE
                    SYNTAX Integer32 (-3277..3277)
                    UNITS "% x10"
                    MAX-ACCESS read-only
                    STATUS current
                    DESCRIPTION "LECU 26 Damper Demand"
                    DEFVAL { 0 }
                    ::= { analogObjects 414 }

        -- 1.3.6.1.4.1.9839.2.1.2.415
        room-t-ef-27 OBJECT-TYPE
                    SYNTAX Integer32 (-3277..3277)
                    UNITS "C x10"
                    MAX-ACCESS read-only
                    STATUS current
                    DESCRIPTION "LECU 27 Room Temperature"
                    DEFVAL { 0 }
                    ::= { analogObjects 415 }

        -- 1.3.6.1.4.1.9839.2.1.2.416
        ufloor-ef-27 OBJECT-TYPE
                    SYNTAX Integer32 (-3277..3277)
                    UNITS "C x10"
                    MAX-ACCESS read-only
                    STATUS current
                    DESCRIPTION "LECU 27 Underfloor Temperature"
                    DEFVAL { 0 }
                    ::= { analogObjects 416 }

        -- 1.3.6.1.4.1.9839.2.1.2.417
        temp-sp-ef-27 OBJECT-TYPE
                    SYNTAX Integer32 (0..32767)
                    UNITS "C x10"
                    MAX-ACCESS read-write
                    STATUS current
                    DESCRIPTION "LECU 27 Temperature Setpoint"
                    DEFVAL { 0 }
                    ::= { analogObjects 417 }

        -- 1.3.6.1.4.1.9839.2.1.2.418
        damperd-ef-27 OBJECT-TYPE
                    SYNTAX Integer32 (-3277..3277)
                    UNITS "% x10"
                    MAX-ACCESS read-only
                    STATUS current
                    DESCRIPTION "LECU 27 Damper Demand"
                    DEFVAL { 0 }
                    ::= { analogObjects 418 }

        -- 1.3.6.1.4.1.9839.2.1.2.419
        room-t-ef-28 OBJECT-TYPE
                    SYNTAX Integer32 (-3277..3277)
                    UNITS "C x10"
                    MAX-ACCESS read-only
                    STATUS current
                    DESCRIPTION "LECU 28 Room Temperature"
                    DEFVAL { 0 }
                    ::= { analogObjects 419 }

        -- 1.3.6.1.4.1.9839.2.1.2.420
        ufloor-ef-28 OBJECT-TYPE
                    SYNTAX Integer32 (-3277..3277)
                    UNITS "C x10"
                    MAX-ACCESS read-only
                    STATUS current
                    DESCRIPTION "LECU 28 Underfloor Temperature"
                    DEFVAL { 0 }
                    ::= { analogObjects 420 }

        -- 1.3.6.1.4.1.9839.2.1.2.421
        temp-sp-ef-28 OBJECT-TYPE
                    SYNTAX Integer32 (0..32767)
                    UNITS "C x10"
                    MAX-ACCESS read-write
                    STATUS current
                    DESCRIPTION "LECU 28 Temperature Setpoint"
                    DEFVAL { 0 }
                    ::= { analogObjects 421 }

        -- 1.3.6.1.4.1.9839.2.1.2.422
        damperd-ef-28 OBJECT-TYPE
                    SYNTAX Integer32 (-3277..3277)
                    UNITS "% x10"
                    MAX-ACCESS read-only
                    STATUS current
                    DESCRIPTION "LECU 28 Damper Demand"
                    DEFVAL { 0 }
                    ::= { analogObjects 422 }

        -- 1.3.6.1.4.1.9839.2.1.2.423
        room-t-ef-29 OBJECT-TYPE
                    SYNTAX Integer32 (-3277..3277)
                    UNITS "C x10"
                    MAX-ACCESS read-only
                    STATUS current
                    DESCRIPTION "LECU 29 Room Temperature"
                    DEFVAL { 0 }
                    ::= { analogObjects 423 }

        -- 1.3.6.1.4.1.9839.2.1.2.424
        ufloor-ef-29 OBJECT-TYPE
                    SYNTAX Integer32 (-3277..3277)
                    UNITS "C x10"
                    MAX-ACCESS read-only
                    STATUS current
                    DESCRIPTION "LECU 29 Underfloor Temperature"
                    DEFVAL { 0 }
                    ::= { analogObjects 424 }

        -- 1.3.6.1.4.1.9839.2.1.2.425
        temp-sp-ef-29 OBJECT-TYPE
                    SYNTAX Integer32 (0..32767)
                    UNITS "C x10"
                    MAX-ACCESS read-write
                    STATUS current
                    DESCRIPTION "LECU 29 Temperature Setpoint"
                    DEFVAL { 0 }
                    ::= { analogObjects 425 }

        -- 1.3.6.1.4.1.9839.2.1.2.426
        damperd-ef-29 OBJECT-TYPE
                    SYNTAX Integer32 (-3277..3277)
                    UNITS "% x10"
                    MAX-ACCESS read-only
                    STATUS current
                    DESCRIPTION "LECU 29 Damper Demand"
                    DEFVAL { 0 }
                    ::= { analogObjects 426 }

        -- 1.3.6.1.4.1.9839.2.1.2.427
        room-t-ef-30 OBJECT-TYPE
                    SYNTAX Integer32 (-3277..3277)
                    UNITS "C x10"
                    MAX-ACCESS read-only
                    STATUS current
                    DESCRIPTION "LECU 30 Room Temperature"
                    DEFVAL { 0 }
                    ::= { analogObjects 427 }

        -- 1.3.6.1.4.1.9839.2.1.2.428
        ufloor-ef-30 OBJECT-TYPE
                    SYNTAX Integer32 (-3277..3277)
                    UNITS "C x10"
                    MAX-ACCESS read-only
                    STATUS current
                    DESCRIPTION "LECU 30 Underfloor Temperature"
                    DEFVAL { 0 }
                    ::= { analogObjects 428 }

        -- 1.3.6.1.4.1.9839.2.1.2.429
        temp-sp-ef-30 OBJECT-TYPE
                    SYNTAX Integer32 (0..32767)
                    UNITS "C x10"
                    MAX-ACCESS read-write
                    STATUS current
                    DESCRIPTION "LECU 30 Temperature Setpoint"
                    DEFVAL { 0 }
                    ::= { analogObjects 429 }

        -- 1.3.6.1.4.1.9839.2.1.2.430
        damperd-ef-30 OBJECT-TYPE
                    SYNTAX Integer32 (-3277..3277)
                    UNITS "% x10"
                    MAX-ACCESS read-only
                    STATUS current
                    DESCRIPTION "LECU 30 Damper Demand"
                    DEFVAL { 0 }
                    ::= { analogObjects 430 }

        -- 1.3.6.1.4.1.9839.2.1.2.431
        room-t-ef-31 OBJECT-TYPE
                    SYNTAX Integer32 (-3277..3277)
                    UNITS "C x10"
                    MAX-ACCESS read-only
                    STATUS current
                    DESCRIPTION "LECU 31 Room Temperature"
                    DEFVAL { 0 }
                    ::= { analogObjects 431 }

        -- 1.3.6.1.4.1.9839.2.1.2.432
        ufloor-ef-31 OBJECT-TYPE
                    SYNTAX Integer32 (-3277..3277)
                    UNITS "C x10"
                    MAX-ACCESS read-only
                    STATUS current
                    DESCRIPTION "LECU 31 Underfloor Temperature"
                    DEFVAL { 0 }
                    ::= { analogObjects 432 }

        -- 1.3.6.1.4.1.9839.2.1.2.433
        temp-sp-ef-31 OBJECT-TYPE
                    SYNTAX Integer32 (0..32767)
                    UNITS "C x10"
                    MAX-ACCESS read-write
                    STATUS current
                    DESCRIPTION "LECU 31 Temperature Setpoint"
                    DEFVAL { 0 }
                    ::= { analogObjects 433 }

        -- 1.3.6.1.4.1.9839.2.1.2.434
        damperd-ef-31 OBJECT-TYPE
                    SYNTAX Integer32 (-3277..3277)
                    UNITS "% x10"
                    MAX-ACCESS read-only
                    STATUS current
                    DESCRIPTION "LECU 31 Damper Demand"
                    DEFVAL { 0 }
                    ::= { analogObjects 434 }

        -- 1.3.6.1.4.1.9839.2.1.2.435
        room-t-ef-32 OBJECT-TYPE
                    SYNTAX Integer32 (-3277..3277)
                    UNITS "C x10"
                    MAX-ACCESS read-only
                    STATUS current
                    DESCRIPTION "LECU 32 Room Temperature"
                    DEFVAL { 0 }
                    ::= { analogObjects 435 }

        -- 1.3.6.1.4.1.9839.2.1.2.436
        ufloor-ef-32 OBJECT-TYPE
                    SYNTAX Integer32 (-3277..3277)
                    UNITS "C x10"
                    MAX-ACCESS read-only
                    STATUS current
                    DESCRIPTION "LECU 32 Underfloor Temperature"
                    DEFVAL { 0 }
                    ::= { analogObjects 436 }

        -- 1.3.6.1.4.1.9839.2.1.2.437
        temp-sp-ef-32 OBJECT-TYPE
                    SYNTAX Integer32 (0..32767)
                    UNITS "C x10"
                    MAX-ACCESS read-write
                    STATUS current
                    DESCRIPTION "LECU 32 Temperature Setpoint"
                    DEFVAL { 0 }
                    ::= { analogObjects 437 }

        -- 1.3.6.1.4.1.9839.2.1.2.438
        damperd-ef-32 OBJECT-TYPE
                    SYNTAX Integer32 (-3277..3277)
                    UNITS "% x10"
                    MAX-ACCESS read-only
                    STATUS current
                    DESCRIPTION "LECU 32 Damper Demand"
                    DEFVAL { 0 }
                    ::= { analogObjects 438 }

        -- 1.3.6.1.4.1.9839.2.1.2.439
        room-t-ef-33 OBJECT-TYPE
                    SYNTAX Integer32 (-3277..3277)
                    UNITS "C x10"
                    MAX-ACCESS read-only
                    STATUS current
                    DESCRIPTION "LECU 33 Room Temperature"
                    DEFVAL { 0 }
                    ::= { analogObjects 439 }

        -- 1.3.6.1.4.1.9839.2.1.2.440
        ufloor-ef-33 OBJECT-TYPE
                    SYNTAX Integer32 (-3277..3277)
                    UNITS "C x10"
                    MAX-ACCESS read-only
                    STATUS current
                    DESCRIPTION "LECU 33 Underfloor Temperature"
                    DEFVAL { 0 }
                    ::= { analogObjects 440 }

        -- 1.3.6.1.4.1.9839.2.1.2.441
        temp-sp-ef-33 OBJECT-TYPE
                    SYNTAX Integer32 (0..32767)
                    UNITS "C x10"
                    MAX-ACCESS read-write
                    STATUS current
                    DESCRIPTION "LECU 33 Temperature Setpoint"
                    DEFVAL { 0 }
                    ::= { analogObjects 441 }

        -- 1.3.6.1.4.1.9839.2.1.2.442
        damperd-ef-33 OBJECT-TYPE
                    SYNTAX Integer32 (-3277..3277)
                    UNITS "% x10"
                    MAX-ACCESS read-only
                    STATUS current
                    DESCRIPTION "LECU 33 Damper Demand"
                    DEFVAL { 0 }
                    ::= { analogObjects 442 }

        -- 1.3.6.1.4.1.9839.2.1.2.443
        room-t-ef-34 OBJECT-TYPE
                    SYNTAX Integer32 (-3277..3277)
                    UNITS "C x10"
                    MAX-ACCESS read-only
                    STATUS current
                    DESCRIPTION "LECU 34 Room Temperature"
                    DEFVAL { 0 }
                    ::= { analogObjects 443 }

        -- 1.3.6.1.4.1.9839.2.1.2.444
        ufloor-ef-34 OBJECT-TYPE
                    SYNTAX Integer32 (-3277..3277)
                    UNITS "C x10"
                    MAX-ACCESS read-only
                    STATUS current
                    DESCRIPTION "LECU 34 Underfloor Temperature"
                    DEFVAL { 0 }
                    ::= { analogObjects 444 }

        -- 1.3.6.1.4.1.9839.2.1.2.445
        temp-sp-ef-34 OBJECT-TYPE
                    SYNTAX Integer32 (0..32767)
                    UNITS "C x10"
                    MAX-ACCESS read-write
                    STATUS current
                    DESCRIPTION "LECU 34 Temperature Setpoint"
                    DEFVAL { 0 }
                    ::= { analogObjects 445 }

        -- 1.3.6.1.4.1.9839.2.1.2.446
        damperd-ef-34 OBJECT-TYPE
                    SYNTAX Integer32 (-3277..3277)
                    UNITS "C x10"
                    MAX-ACCESS read-only
                    STATUS current
                    DESCRIPTION "LECU 34 Damper Demand"
                    DEFVAL { 0 }
                    ::= { analogObjects 446 }

        -- 1.3.6.1.4.1.9839.2.1.2.447
        room-t-ef-35 OBJECT-TYPE
                    SYNTAX Integer32 (-3277..3277)
                    UNITS "C x10"
                    MAX-ACCESS read-only
                    STATUS current
                    DESCRIPTION "LECU 35 Room Temperature"
                    DEFVAL { 0 }
                    ::= { analogObjects 447 }

        -- 1.3.6.1.4.1.9839.2.1.2.448
        ufloor-ef-35 OBJECT-TYPE
                    SYNTAX Integer32 (-3277..3277)
                    UNITS "C x10"
                    MAX-ACCESS read-only
                    STATUS current
                    DESCRIPTION "LECU 35 Underfloor Temperature"
                    DEFVAL { 0 }
                    ::= { analogObjects 448 }

        -- 1.3.6.1.4.1.9839.2.1.2.449
        temp-sp-ef-35 OBJECT-TYPE
                    SYNTAX Integer32 (0..32767)
                    UNITS "C x10"
                    MAX-ACCESS read-write
                    STATUS current
                    DESCRIPTION "LECU 35 Temperature Setpoint"
                    DEFVAL { 0 }
                    ::= { analogObjects 449 }

        -- 1.3.6.1.4.1.9839.2.1.2.450
        damperd-ef-35 OBJECT-TYPE
                    SYNTAX Integer32 (-3277..3277)
                    UNITS "% x10"
                    MAX-ACCESS read-only
                    STATUS current
                    DESCRIPTION "LECU 35 Damper Demand"
                    DEFVAL { 0 }
                    ::= { analogObjects 450 }

        -- 1.3.6.1.4.1.9839.2.1.2.451
        ef-average-temp OBJECT-TYPE
                    SYNTAX Integer32 (-3277..3277)
                    UNITS "C x10"
                    MAX-ACCESS read-only
                    STATUS current
                    DESCRIPTION "Tile Unit (LECU) Average Temperature !FROM THE LECU's!"
                    DEFVAL { 0 }
                    ::= { analogObjects 451 }

        -- 1.3.6.1.4.1.9839.2.1.2.452
        lecu-setpoint OBJECT-TYPE
                    SYNTAX Integer32 (-999..999)
                    UNITS "C x10"
                    MAX-ACCESS read-write
                    STATUS current
                    DESCRIPTION "Default LECU setpoint (After Restart)"
                    DEFVAL { 210 }
                    ::= { analogObjects 452 }

        -- 1.3.6.1.4.1.9839.2.1.2.453
        comp-threshold-hp-low OBJECT-TYPE
                    SYNTAX Integer32 (0..999)
                    UNITS "N/A"
                    MAX-ACCESS read-write
                    STATUS current
                    DESCRIPTION "N/A"
                    DEFVAL { 0 }
                    ::= { analogObjects 453 }

        -- 1.3.6.1.4.1.9839.2.1.2.454
        comp-threshold-lp OBJECT-TYPE
                    SYNTAX Integer32 (0..999)
                    UNITS "N/A"
                    MAX-ACCESS read-write
                    STATUS current
                    DESCRIPTION "N/A"
                    DEFVAL { 0 }
                    ::= { analogObjects 454 }

        -- 1.3.6.1.4.1.9839.2.1.2.455
        b05-min-value-cw-outlet OBJECT-TYPE
                    SYNTAX Integer32 (0..100)
                    UNITS "N/A"
                    MAX-ACCESS read-write
                    STATUS current
                    DESCRIPTION "N/A"
                    DEFVAL { 0 }
                    ::= { analogObjects 455 }

        -- 1.3.6.1.4.1.9839.2.1.2.456
        b05-max-value-cw-outlet OBJECT-TYPE
                    SYNTAX Integer32 (350..500)
                    UNITS "N/A"
                    MAX-ACCESS read-write
                    STATUS current
                    DESCRIPTION "N/A"
                    DEFVAL { 400 }
                    ::= { analogObjects 456 }

        -- 1.3.6.1.4.1.9839.2.1.2.457
        aps-press-filter-thr OBJECT-TYPE
                    SYNTAX Integer32 (-32767..32767)
                    UNITS "N/A"
                    MAX-ACCESS read-write
                    STATUS current
                    DESCRIPTION "APS Pressure filter threshold"
                    DEFVAL { 0 }
                    ::= { analogObjects 457 }

        -- 1.3.6.1.4.1.9839.2.1.2.458
        aps-press-filter-delay OBJECT-TYPE
                    SYNTAX Integer32 (0..999)
                    UNITS "sec x10"
                    MAX-ACCESS read-write
                    STATUS current
                    DESCRIPTION "APS Pressure filter delay"
                    DEFVAL { 0 }
                    ::= { analogObjects 458 }

        -- 1.3.6.1.4.1.9839.2.1.2.459
        b01-offset-rah OBJECT-TYPE
                    SYNTAX Integer32 (-200..200)
                    UNITS "N/A"
                    MAX-ACCESS read-write
                    STATUS current
                    DESCRIPTION "N/A"
                    DEFVAL { 0 }
                    ::= { analogObjects 459 }

        -- 1.3.6.1.4.1.9839.2.1.2.460
        b02-offset-rat OBJECT-TYPE
                    SYNTAX Integer32 (-100..100)
                    UNITS "N/A"
                    MAX-ACCESS read-write
                    STATUS current
                    DESCRIPTION "N/A"
                    DEFVAL { 0 }
                    ::= { analogObjects 460 }

        -- 1.3.6.1.4.1.9839.2.1.2.461
        b03-offset-sat OBJECT-TYPE
                    SYNTAX Integer32 (-100..100)
                    UNITS "N/A"
                    MAX-ACCESS read-write
                    STATUS current
                    DESCRIPTION "N/A"
                    DEFVAL { 0 }
                    ::= { analogObjects 461 }

        -- 1.3.6.1.4.1.9839.2.1.2.462
        b04-offset-cw-inlet OBJECT-TYPE
                    SYNTAX Integer32 (-100..100)
                    UNITS "N/A"
                    MAX-ACCESS read-write
                    STATUS current
                    DESCRIPTION "N/A"
                    DEFVAL { 0 }
                    ::= { analogObjects 462 }

        -- 1.3.6.1.4.1.9839.2.1.2.463
        b05-offset-cw-outlet OBJECT-TYPE
                    SYNTAX Integer32 (-100..100)
                    UNITS "N/A"
                    MAX-ACCESS read-write
                    STATUS current
                    DESCRIPTION "N/A"
                    DEFVAL { 0 }
                    ::= { analogObjects 463 }

        -- 1.3.6.1.4.1.9839.2.1.2.464
        b06-offset-disch-press OBJECT-TYPE
                    SYNTAX Integer32 (-99..99)
                    UNITS "N/A"
                    MAX-ACCESS read-write
                    STATUS current
                    DESCRIPTION "N/A"
                    DEFVAL { 0 }
                    ::= { analogObjects 464 }

        -- 1.3.6.1.4.1.9839.2.1.2.465
        b07-offset-disch-temp OBJECT-TYPE
                    SYNTAX Integer32 (-99..99)
                    UNITS "N/A"
                    MAX-ACCESS read-write
                    STATUS current
                    DESCRIPTION "N/A"
                    DEFVAL { 0 }
                    ::= { analogObjects 465 }

        -- 1.3.6.1.4.1.9839.2.1.2.466
        b08-offset-airflow OBJECT-TYPE
                    SYNTAX Integer32 (-999..999)
                    UNITS "N/A"
                    MAX-ACCESS read-write
                    STATUS current
                    DESCRIPTION "N/A"
                    DEFVAL { 0 }
                    ::= { analogObjects 466 }

        -- 1.3.6.1.4.1.9839.2.1.2.467
        b08-offset-sah OBJECT-TYPE
                    SYNTAX Integer32 (-200..200)
                    UNITS "N/A"
                    MAX-ACCESS read-write
                    STATUS current
                    DESCRIPTION "N/A"
                    DEFVAL { 0 }
                    ::= { analogObjects 467 }

        -- 1.3.6.1.4.1.9839.2.1.2.468
        b101-offset-aps-press OBJECT-TYPE
                    SYNTAX Integer32 (-32768..32767)
                    UNITS "N/A"
                    MAX-ACCESS read-write
                    STATUS current
                    DESCRIPTION "N/A"
                    DEFVAL { 0 }
                    ::= { analogObjects 468 }

        -- 1.3.6.1.4.1.9839.2.1.2.469
        b102-offset-amb-temp OBJECT-TYPE
                    SYNTAX Integer32 (-32768..32767)
                    UNITS "N/A"
                    MAX-ACCESS read-write
                    STATUS current
                    DESCRIPTION "N/A"
                    DEFVAL { 0 }
                    ::= { analogObjects 469 }

        -- 1.3.6.1.4.1.9839.2.1.2.470
        set-temp OBJECT-TYPE
                    SYNTAX Integer32 (-999..3277)
                    UNITS "N/A"
                    MAX-ACCESS read-write
                    STATUS current
                    DESCRIPTION "N/A"
                    DEFVAL { 0 }
                    ::= { analogObjects 470 }

        -- 1.3.6.1.4.1.9839.2.1.2.471
        set-hum OBJECT-TYPE
                    SYNTAX Integer32 (-999..3277)
                    UNITS "N/A"
                    MAX-ACCESS read-write
                    STATUS current
                    DESCRIPTION "N/A"
                    DEFVAL { 0 }
                    ::= { analogObjects 471 }

        -- 1.3.6.1.4.1.9839.2.1.2.472
        return-air-hum-abs OBJECT-TYPE
                    SYNTAX Integer32 (0..32767)
                    UNITS "N/A"
                    MAX-ACCESS read-only
                    STATUS current
                    DESCRIPTION "Humidity absolute expressed as enthalpy in tenths of g/kg of air"
                    DEFVAL { 0 }
                    ::= { analogObjects 472 }

        -- 1.3.6.1.4.1.9839.2.1.2.473
        design-sa-temp OBJECT-TYPE
                    SYNTAX Integer32 (-9999..9999)
                    UNITS "N/A"
                    MAX-ACCESS read-write
                    STATUS current
                    DESCRIPTION "N/A"
                    DEFVAL { 0 }
                    ::= { analogObjects 473 }

        -- 1.3.6.1.4.1.9839.2.1.2.474
        b02-max-value-rat OBJECT-TYPE
                    SYNTAX Integer32 (350..500)
                    UNITS "N/A"
                    MAX-ACCESS read-write
                    STATUS current
                    DESCRIPTION "N/A"
                    DEFVAL { 400 }
                    ::= { analogObjects 474 }

        -- 1.3.6.1.4.1.9839.2.1.2.475
        b01-min-value-rah OBJECT-TYPE
                    SYNTAX Integer32 (0..200)
                    UNITS "N/A"
                    MAX-ACCESS read-write
                    STATUS current
                    DESCRIPTION "N/A"
                    DEFVAL { 0 }
                    ::= { analogObjects 475 }

        -- 1.3.6.1.4.1.9839.2.1.2.476
        b03-min-value-sat OBJECT-TYPE
                    SYNTAX Integer32 (-100..0)
                    UNITS "N/A"
                    MAX-ACCESS read-write
                    STATUS current
                    DESCRIPTION "N/A"
                    DEFVAL { -100 }
                    ::= { analogObjects 476 }

        -- 1.3.6.1.4.1.9839.2.1.2.477
        b03-max-value-sat OBJECT-TYPE
                    SYNTAX Integer32 (350..500)
                    UNITS "N/A"
                    MAX-ACCESS read-write
                    STATUS current
                    DESCRIPTION "N/A"
                    DEFVAL { 350 }
                    ::= { analogObjects 477 }

        -- 1.3.6.1.4.1.9839.2.1.2.478
        sat-low-al-set OBJECT-TYPE
                    SYNTAX Integer32 (-50..300)
                    UNITS "N/A"
                    MAX-ACCESS read-write
                    STATUS current
                    DESCRIPTION "N/A"
                    DEFVAL { 150 }
                    ::= { analogObjects 478 }

        -- 1.3.6.1.4.1.9839.2.1.2.479
        b08-min-value-sah OBJECT-TYPE
                    SYNTAX Integer32 (0..200)
                    UNITS "N/A"
                    MAX-ACCESS read-write
                    STATUS current
                    DESCRIPTION "N/A"
                    DEFVAL { 0 }
                    ::= { analogObjects 479 }

        -- 1.3.6.1.4.1.9839.2.1.2.480
        b08-max-value-sah OBJECT-TYPE
                    SYNTAX Integer32 (500..1000)
                    UNITS "N/A"
                    MAX-ACCESS read-write
                    STATUS current
                    DESCRIPTION "N/A"
                    DEFVAL { 1000 }
                    ::= { analogObjects 480 }

        -- 1.3.6.1.4.1.9839.2.1.2.481
        sah-high-al-set OBJECT-TYPE
                    SYNTAX Integer32 (250..1000)
                    UNITS "N/A"
                    MAX-ACCESS read-write
                    STATUS current
                    DESCRIPTION "N/A"
                    DEFVAL { 900 }
                    ::= { analogObjects 481 }

        -- 1.3.6.1.4.1.9839.2.1.2.482
        b04-min-value-cw-inlet OBJECT-TYPE
                    SYNTAX Integer32 (0..100)
                    UNITS "N/A"
                    MAX-ACCESS read-write
                    STATUS current
                    DESCRIPTION "N/A"
                    DEFVAL { 0 }
                    ::= { analogObjects 482 }

        -- 1.3.6.1.4.1.9839.2.1.2.483
        b04-max-value-cw-inlet OBJECT-TYPE
                    SYNTAX Integer32 (350..500)
                    UNITS "N/A"
                    MAX-ACCESS read-write
                    STATUS current
                    DESCRIPTION "N/A"
                    DEFVAL { 400 }
                    ::= { analogObjects 483 }

        -- 1.3.6.1.4.1.9839.2.1.2.484
        b06-min-value-disch-press OBJECT-TYPE
                    SYNTAX Integer32 (-5..10)
                    UNITS "N/A"
                    MAX-ACCESS read-write
                    STATUS current
                    DESCRIPTION "N/A"
                    DEFVAL { 0 }
                    ::= { analogObjects 484 }

        -- 1.3.6.1.4.1.9839.2.1.2.485
        b06-max-value-disch-press OBJECT-TYPE
                    SYNTAX Integer32 (70..450)
                    UNITS "N/A"
                    MAX-ACCESS read-write
                    STATUS current
                    DESCRIPTION "N/A"
                    DEFVAL { 345 }
                    ::= { analogObjects 485 }

        -- 1.3.6.1.4.1.9839.2.1.2.486
        cooling-req-dehum OBJECT-TYPE
                    SYNTAX Integer32 (0..1000)
                    UNITS "N/A"
                    MAX-ACCESS read-write
                    STATUS current
                    DESCRIPTION "N/A"
                    DEFVAL { 700 }
                    ::= { analogObjects 486 }

        -- 1.3.6.1.4.1.9839.2.1.2.487
        cooling-demand-dehum-off OBJECT-TYPE
                    SYNTAX Integer32 (0..1100)
                    UNITS "N/A"
                    MAX-ACCESS read-write
                    STATUS current
                    DESCRIPTION "N/A"
                    DEFVAL { 500 }
                    ::= { analogObjects 487 }

        -- 1.3.6.1.4.1.9839.2.1.2.488
        b07-min-value-disch-temp OBJECT-TYPE
                    SYNTAX Integer32 (-5..10)
                    UNITS "N/A"
                    MAX-ACCESS read-write
                    STATUS current
                    DESCRIPTION "N/A"
                    DEFVAL { 0 }
                    ::= { analogObjects 488 }

        -- 1.3.6.1.4.1.9839.2.1.2.489
        b07-max-value-disch-temp OBJECT-TYPE
                    SYNTAX Integer32 (70..450)
                    UNITS "N/A"
                    MAX-ACCESS read-write
                    STATUS current
                    DESCRIPTION "N/A"
                    DEFVAL { 345 }
                    ::= { analogObjects 489 }

        -- 1.3.6.1.4.1.9839.2.1.2.490
        dcra-fan-max-speed-night OBJECT-TYPE
                    SYNTAX Integer32 (0..999)
                    UNITS "bar x10"
                    MAX-ACCESS read-only
                    STATUS current
                    DESCRIPTION "N/A"
                    DEFVAL { 0 }
                    ::= { analogObjects 490 }

        -- 1.3.6.1.4.1.9839.2.1.2.491
        dcra-set-day-back OBJECT-TYPE
                    SYNTAX Integer32 (0..999)
                    UNITS "bar x10"
                    MAX-ACCESS read-write
                    STATUS current
                    DESCRIPTION "N/A"
                    DEFVAL { 0 }
                    ::= { analogObjects 491 }

        -- 1.3.6.1.4.1.9839.2.1.2.492
        dcra-hyst-day-back OBJECT-TYPE
                    SYNTAX Integer32 (0..999)
                    UNITS "bar x10"
                    MAX-ACCESS read-only
                    STATUS current
                    DESCRIPTION "N/A"
                    DEFVAL { 0 }
                    ::= { analogObjects 492 }

        -- 1.3.6.1.4.1.9839.2.1.2.493
        cool-demand-hand OBJECT-TYPE
                    SYNTAX Integer32 (0..1000)
                    UNITS "N/A"
                    MAX-ACCESS read-write
                    STATUS current
                    DESCRIPTION "N/A"
                    DEFVAL { 0 }
                    ::= { analogObjects 493 }

        -- 1.3.6.1.4.1.9839.2.1.2.494
        heat-demand-hand OBJECT-TYPE
                    SYNTAX Integer32 (0..1000)
                    UNITS "N/A"
                    MAX-ACCESS read-write
                    STATUS current
                    DESCRIPTION "N/A"
                    DEFVAL { 0 }
                    ::= { analogObjects 494 }

        -- 1.3.6.1.4.1.9839.2.1.2.495
        hum-demand-hand OBJECT-TYPE
                    SYNTAX Integer32 (0..1000)
                    UNITS "N/A"
                    MAX-ACCESS read-write
                    STATUS current
                    DESCRIPTION "N/A"
                    DEFVAL { 0 }
                    ::= { analogObjects 495 }

        -- 1.3.6.1.4.1.9839.2.1.2.496
        dehum-demand-hand OBJECT-TYPE
                    SYNTAX Integer32 (0..1000)
                    UNITS "N/A"
                    MAX-ACCESS read-write
                    STATUS current
                    DESCRIPTION "N/A"
                    DEFVAL { 0 }
                    ::= { analogObjects 496 }

        -- 1.3.6.1.4.1.9839.2.1.2.497
        ambicool-demand-hand OBJECT-TYPE
                    SYNTAX Integer32 (0..1000)
                    UNITS "N/A"
                    MAX-ACCESS read-write
                    STATUS current
                    DESCRIPTION "N/A"
                    DEFVAL { 0 }
                    ::= { analogObjects 497 }

        -- 1.3.6.1.4.1.9839.2.1.2.498
        max-prod OBJECT-TYPE
                    SYNTAX Integer32 (200..1000)
                    UNITS "N/A"
                    MAX-ACCESS read-write
                    STATUS current
                    DESCRIPTION "N/A"
                    DEFVAL { 1000 }
                    ::= { analogObjects 498 }

        -- 1.3.6.1.4.1.9839.2.1.2.499
        airflow-press-diff OBJECT-TYPE
                    SYNTAX Integer32 (-32768..32767)
                    UNITS "N/A"
                    MAX-ACCESS read-only
                    STATUS current
                    DESCRIPTION "N/A"
                    DEFVAL { 0 }
                    ::= { analogObjects 499 }

        -- 1.3.6.1.4.1.9839.2.1.2.500
        design-sa-tol OBJECT-TYPE
                    SYNTAX Integer32 (-9999..9999)
                    UNITS "N/A"
                    MAX-ACCESS read-write
                    STATUS current
                    DESCRIPTION "N/A"
                    DEFVAL { 0 }
                    ::= { analogObjects 500 }

        -- 1.3.6.1.4.1.9839.2.1.2.501
        design-ra-temp OBJECT-TYPE
                    SYNTAX Integer32 (-9999..9999)
                    UNITS "N/A"
                    MAX-ACCESS read-write
                    STATUS current
                    DESCRIPTION "N/A"
                    DEFVAL { 0 }
                    ::= { analogObjects 501 }

        -- 1.3.6.1.4.1.9839.2.1.2.502
        b01-max-value-rah OBJECT-TYPE
                    SYNTAX Integer32 (500..1000)
                    UNITS "N/A"
                    MAX-ACCESS read-write
                    STATUS current
                    DESCRIPTION "N/A"
                    DEFVAL { 1000 }
                    ::= { analogObjects 502 }

        -- 1.3.6.1.4.1.9839.2.1.2.503
        disp-aout5 OBJECT-TYPE
                    SYNTAX Integer32 (0..3277)
                    UNITS "N/A"
                    MAX-ACCESS read-write
                    STATUS current
                    DESCRIPTION "N/A"
                    DEFVAL { 0 }
                    ::= { analogObjects 503 }

        -- 1.3.6.1.4.1.9839.2.1.2.504
        disp-aout6 OBJECT-TYPE
                    SYNTAX Integer32 (0..3277)
                    UNITS "N/A"
                    MAX-ACCESS read-write
                    STATUS current
                    DESCRIPTION "N/A"
                    DEFVAL { 0 }
                    ::= { analogObjects 504 }

        -- 1.3.6.1.4.1.9839.2.1.2.505
        water-in-setpoint-ddra OBJECT-TYPE
                    SYNTAX Integer32 (-32768..32767)
                    UNITS "N/A"
                    MAX-ACCESS read-write
                    STATUS current
                    DESCRIPTION "N/A"
                    DEFVAL { 0 }
                    ::= { analogObjects 505 }

        -- 1.3.6.1.4.1.9839.2.1.2.506
        water-in-diff-ddra OBJECT-TYPE
                    SYNTAX Integer32 (0..32767)
                    UNITS "N/A"
                    MAX-ACCESS read-write
                    STATUS current
                    DESCRIPTION "N/A"
                    DEFVAL { 0 }
                    ::= { analogObjects 506 }

        -- 1.3.6.1.4.1.9839.2.1.2.507
        aps-press-set OBJECT-TYPE
                    SYNTAX Integer32 (0..32767)
                    UNITS "Pa x10"
                    MAX-ACCESS read-write
                    STATUS current
                    DESCRIPTION "N/A"
                    DEFVAL { 0 }
                    ::= { analogObjects 507 }

        -- 1.3.6.1.4.1.9839.2.1.2.508
        aps-press-diff OBJECT-TYPE
                    SYNTAX Integer32 (0..32767)
                    UNITS "Pa x10"
                    MAX-ACCESS read-write
                    STATUS current
                    DESCRIPTION "N/A"
                    DEFVAL { 0 }
                    ::= { analogObjects 508 }

        -- 1.3.6.1.4.1.9839.2.1.2.509
        aps-manual-fan-speed OBJECT-TYPE
                    SYNTAX Integer32 (0..100)
                    UNITS "V x10"
                    MAX-ACCESS read-write
                    STATUS current
                    DESCRIPTION "manual APS fan output voltage"
                    DEFVAL { 0 }
                    ::= { analogObjects 509 }

        -- 1.3.6.1.4.1.9839.2.1.2.510
        aps-demand-fan-mask OBJECT-TYPE
                    SYNTAX Integer32 (-32768..32767)
                    UNITS "N/A"
                    MAX-ACCESS read-only
                    STATUS current
                    DESCRIPTION "N/A"
                    DEFVAL { 0 }
                    ::= { analogObjects 510 }

        -- 1.3.6.1.4.1.9839.2.1.2.511
        tickover-active-thresh OBJECT-TYPE
                    SYNTAX Integer32 (0..1000)
                    UNITS "% x10"
                    MAX-ACCESS read-write
                    STATUS current
                    DESCRIPTION "N/A"
                    DEFVAL { 0 }
                    ::= { analogObjects 511 }

        -- 1.3.6.1.4.1.9839.2.1.2.512
        fan-tickover-demand OBJECT-TYPE
                    SYNTAX Integer32 (0..1000)
                    UNITS "N/A"
                    MAX-ACCESS read-write
                    STATUS current
                    DESCRIPTION "N/A"
                    DEFVAL { 0 }
                    ::= { analogObjects 512 }

        -- 1.3.6.1.4.1.9839.2.1.2.513
        freecooling-perc OBJECT-TYPE
                    SYNTAX Integer32 (0..1000)
                    UNITS "% x10"
                    MAX-ACCESS read-write
                    STATUS current
                    DESCRIPTION "Freecooling band before compressor request"
                    DEFVAL { 330 }
                    ::= { analogObjects 513 }

        -- 1.3.6.1.4.1.9839.2.1.2.514
        comp-threshold-hp OBJECT-TYPE
                    SYNTAX Integer32 (0..999)
                    UNITS "N/A"
                    MAX-ACCESS read-write
                    STATUS current
                    DESCRIPTION "N/A"
                    DEFVAL { 0 }
                    ::= { analogObjects 514 }

        -- 1.3.6.1.4.1.9839.2.1.2.515
        hp-alr-hysteresis-circ1 OBJECT-TYPE
                    SYNTAX Integer32 (0..999)
                    UNITS "N/A"
                    MAX-ACCESS read-write
                    STATUS current
                    DESCRIPTION "N/A"
                    DEFVAL { 0 }
                    ::= { analogObjects 515 }

        -- 1.3.6.1.4.1.9839.2.1.2.516
        hp-alr-threshold-circ1 OBJECT-TYPE
                    SYNTAX Integer32 (-20..9999)
                    UNITS "bar x10"
                    MAX-ACCESS read-write
                    STATUS current
                    DESCRIPTION "N/A"
                    DEFVAL { 0 }
                    ::= { analogObjects 516 }

        -- 1.3.6.1.4.1.9839.2.1.2.517
        fixedonthrsh OBJECT-TYPE
                    SYNTAX Integer32 (0..9999)
                    UNITS "N/A"
                    MAX-ACCESS read-write
                    STATUS current
                    DESCRIPTION "Threshold of BLDC speeed (in rps) to call on fixed speed compressor"
                    DEFVAL { 900 }
                    ::= { analogObjects 517 }

        -- 1.3.6.1.4.1.9839.2.1.2.518
        fixedoffthrsh OBJECT-TYPE
                    SYNTAX Integer32 (0..9999)
                    UNITS "N/A"
                    MAX-ACCESS read-write
                    STATUS current
                    DESCRIPTION "Threshold of BLDC speeed (in rps) to switch off fixed speed compressor"
                    DEFVAL { 300 }
                    ::= { analogObjects 518 }

        -- 1.3.6.1.4.1.9839.2.1.2.519
        oil-return-rps-demand-1 OBJECT-TYPE
                    SYNTAX Integer32 (0..9999)
                    UNITS "N/A"
                    MAX-ACCESS read-write
                    STATUS current
                    DESCRIPTION "N/A"
                    DEFVAL { 0 }
                    ::= { analogObjects 519 }

        -- 1.3.6.1.4.1.9839.2.1.2.520
        oil-return-rps-demand-2 OBJECT-TYPE
                    SYNTAX Integer32 (0..9999)
                    UNITS "N/A"
                    MAX-ACCESS read-write
                    STATUS current
                    DESCRIPTION "N/A"
                    DEFVAL { 0 }
                    ::= { analogObjects 520 }

        -- 1.3.6.1.4.1.9839.2.1.2.521
        discharge-superheat OBJECT-TYPE
                    SYNTAX Integer32 (-760..3240)
                    UNITS "N/A"
                    MAX-ACCESS read-only
                    STATUS current
                    DESCRIPTION "Discharge superheat"
                    DEFVAL { 0 }
                    ::= { analogObjects 521 }

        -- 1.3.6.1.4.1.9839.2.1.2.522
        min-inverter-on-threshold OBJECT-TYPE
                    SYNTAX Integer32 (0..1000)
                    UNITS "N/A"
                    MAX-ACCESS read-write
                    STATUS current
                    DESCRIPTION "N/A"
                    DEFVAL { 0 }
                    ::= { analogObjects 522 }

        -- 1.3.6.1.4.1.9839.2.1.2.523
        unit-fan-min-speed-msk OBJECT-TYPE
                    SYNTAX Integer32 (0..100)
                    UNITS "N/A"
                    MAX-ACCESS read-write
                    STATUS current
                    DESCRIPTION "N/A"
                    DEFVAL { 0 }
                    ::= { analogObjects 523 }

        -- 1.3.6.1.4.1.9839.2.1.2.524
        unit-fan-max-speed-msk OBJECT-TYPE
                    SYNTAX Integer32 (0..100)
                    UNITS "N/A"
                    MAX-ACCESS read-write
                    STATUS current
                    DESCRIPTION "N/A"
                    DEFVAL { 0 }
                    ::= { analogObjects 524 }

        -- 1.3.6.1.4.1.9839.2.1.2.525
        unit-fan-dehum-speed OBJECT-TYPE
                    SYNTAX Integer32 (0..100)
                    UNITS "N/A"
                    MAX-ACCESS read-write
                    STATUS current
                    DESCRIPTION "N/A"
                    DEFVAL { 0 }
                    ::= { analogObjects 525 }

        -- 1.3.6.1.4.1.9839.2.1.2.526
        average-temp OBJECT-TYPE
                    SYNTAX Integer32 (0..3277)
                    UNITS "N/A"
                    MAX-ACCESS read-write
                    STATUS current
                    DESCRIPTION "N/A"
                    DEFVAL { 0 }
                    ::= { analogObjects 526 }

        -- 1.3.6.1.4.1.9839.2.1.2.527
        start-defrost-sp OBJECT-TYPE
                    SYNTAX Integer32 (0..999)
                    UNITS "N/A"
                    MAX-ACCESS read-write
                    STATUS current
                    DESCRIPTION "N/A"
                    DEFVAL { 20 }
                    ::= { analogObjects 527 }

        -- 1.3.6.1.4.1.9839.2.1.2.528
        stop-defrost-sp OBJECT-TYPE
                    SYNTAX Integer32 (0..999)
                    UNITS "N/A"
                    MAX-ACCESS read-write
                    STATUS current
                    DESCRIPTION "N/A"
                    DEFVAL { 160 }
                    ::= { analogObjects 528 }

        -- 1.3.6.1.4.1.9839.2.1.2.529
        b08-min-value-airflow OBJECT-TYPE
                    SYNTAX Integer32 (0..1000)
                    UNITS "N/A"
                    MAX-ACCESS read-write
                    STATUS current
                    DESCRIPTION "N/A"
                    DEFVAL { 0 }
                    ::= { analogObjects 529 }

        -- 1.3.6.1.4.1.9839.2.1.2.530
        b08-max-value-airflow OBJECT-TYPE
                    SYNTAX Integer32 (0..25000)
                    UNITS "N/A"
                    MAX-ACCESS read-write
                    STATUS current
                    DESCRIPTION "N/A"
                    DEFVAL { 25000 }
                    ::= { analogObjects 530 }

        -- 1.3.6.1.4.1.9839.2.1.2.531
        special-cooling-sp OBJECT-TYPE
                    SYNTAX Integer32 (0..1000)
                    UNITS "N/A"
                    MAX-ACCESS read-write
                    STATUS current
                    DESCRIPTION "N/A"
                    DEFVAL { 100 }
                    ::= { analogObjects 531 }

        -- 1.3.6.1.4.1.9839.2.1.2.532
        conv-temp1-c OBJECT-TYPE
                    SYNTAX Integer32 (-32767..32767)
                    UNITS "C x10"
                    MAX-ACCESS read-write
                    STATUS current
                    DESCRIPTION "N/A"
                    DEFVAL { 0 }
                    ::= { analogObjects 532 }

        -- 1.3.6.1.4.1.9839.2.1.2.533
        lp-alr-threshold-circ-1 OBJECT-TYPE
                    SYNTAX Integer32 (0..32767)
                    UNITS "N/A"
                    MAX-ACCESS read-write
                    STATUS current
                    DESCRIPTION "N/A"
                    DEFVAL { 0 }
                    ::= { analogObjects 533 }

        -- 1.3.6.1.4.1.9839.2.1.2.534
        lp-alr-hysteresis-circ-1 OBJECT-TYPE
                    SYNTAX Integer32 (-32768..32767)
                    UNITS "N/A"
                    MAX-ACCESS read-write
                    STATUS current
                    DESCRIPTION "N/A"
                    DEFVAL { 0 }
                    ::= { analogObjects 534 }

        -- 1.3.6.1.4.1.9839.2.1.2.535
        pcoe-1.ainminvalue-ch-1 OBJECT-TYPE
                    SYNTAX Integer32 (-9999..9999)
                    UNITS "N/A"
                    MAX-ACCESS read-write
                    STATUS current
                    DESCRIPTION "Min value AIn channel 1"
                    DEFVAL { 0 }
                    ::= { analogObjects 535 }

        -- 1.3.6.1.4.1.9839.2.1.2.536
        pcoe-1.ainmaxvalue-ch-1 OBJECT-TYPE
                    SYNTAX Integer32 (-9999..9999)
                    UNITS "N/A"
                    MAX-ACCESS read-write
                    STATUS current
                    DESCRIPTION "Max value AIn channel 1"
                    DEFVAL { 100 }
                    ::= { analogObjects 536 }

        -- 1.3.6.1.4.1.9839.2.1.2.1100
        oil-return-thr-bldc-1 OBJECT-TYPE
                    SYNTAX Integer32 (0..9999)
                    UNITS "N/A"
                    MAX-ACCESS read-write
                    STATUS current
                    DESCRIPTION "N/A"
                    DEFVAL { 0 }
                    ::= { analogObjects 1100 }

        -- 1.3.6.1.4.1.9839.2.1.2.1101
        comppwr-perc-bldc-1-tandem OBJECT-TYPE
                    SYNTAX Integer32 (0..1000)
                    UNITS "N/A"
                    MAX-ACCESS read-only
                    STATUS current
                    DESCRIPTION "Power request (percentage)"
                    DEFVAL { 1 }
                    ::= { analogObjects 1101 }

        -- 1.3.6.1.4.1.9839.2.1.2.1102
        condregsetp-bldc-1 OBJECT-TYPE
                    SYNTAX Integer32 (-32768..32767)
                    UNITS "N/A"
                    MAX-ACCESS read-only
                    STATUS current
                    DESCRIPTION "Condensing press. lower limit (Fan regul. in chiller) (bar/psi)"
                    DEFVAL { 0 }
                    ::= { analogObjects 1102 }

        -- 1.3.6.1.4.1.9839.2.1.2.1103
        condregsettemp-bldc-1 OBJECT-TYPE
                    SYNTAX Integer32 (-32768..32767)
                    UNITS "C/F x10"
                    MAX-ACCESS read-only
                    STATUS current
                    DESCRIPTION "Condensing temp. lower limit (Fan regul. in chiller)"
                    DEFVAL { 0 }
                    ::= { analogObjects 1103 }

        -- 1.3.6.1.4.1.9839.2.1.2.1104
        evapregsetp-bldc-1 OBJECT-TYPE
                    SYNTAX Integer32 (-32768..32767)
                    UNITS "N/A"
                    MAX-ACCESS read-only
                    STATUS current
                    DESCRIPTION "Evaporating Press. upper limit (Fan regul. in Pdc) (bar/psi)"
                    DEFVAL { 0 }
                    ::= { analogObjects 1104 }

        -- 1.3.6.1.4.1.9839.2.1.2.1105
        evapregsettemp-bldc-1 OBJECT-TYPE
                    SYNTAX Integer32 (-32768..32767)
                    UNITS "C/F x10"
                    MAX-ACCESS read-only
                    STATUS current
                    DESCRIPTION "Evaporating temp. upper limit (Fan regul. in Pdc)"
                    DEFVAL { 0 }
                    ::= { analogObjects 1105 }

        -- 1.3.6.1.4.1.9839.2.1.2.1106
        maxgoupspeedrate-bldc-1 OBJECT-TYPE
                    SYNTAX Integer32 (0..99)
                    UNITS "N/A"
                    MAX-ACCESS read-write
                    STATUS current
                    DESCRIPTION "Max. increase speed rate (going to target speed in defrost) [rps/s]"
                    DEFVAL { 10 }
                    ::= { analogObjects 1106 }

        -- 1.3.6.1.4.1.9839.2.1.2.1107
        minspeedgoto-rps-bldc-1 OBJECT-TYPE
                    SYNTAX Integer32 (0..999)
                    UNITS "N/A"
                    MAX-ACCESS read-write
                    STATUS current
                    DESCRIPTION "Minimum speed (used by Goto_Min_Speed) [rps]"
                    DEFVAL { 0 }
                    ::= { analogObjects 1107 }

        -- 1.3.6.1.4.1.9839.2.1.2.1108
        vfd-req-0-1000-bldc-1 OBJECT-TYPE
                    SYNTAX Integer32 (0..9999)
                    UNITS "N/A"
                    MAX-ACCESS read-only
                    STATUS current
                    DESCRIPTION "Speed request out to inverter module"
                    DEFVAL { 0 }
                    ::= { analogObjects 1108 }

        -- 1.3.6.1.4.1.9839.2.1.2.1109
        max-speed-x-rps-bldc-1 OBJECT-TYPE
                    SYNTAX Integer32 (-32768..32767)
                    UNITS "N/A"
                    MAX-ACCESS read-write
                    STATUS current
                    DESCRIPTION "N/A"
                    DEFVAL { 0 }
                    ::= { analogObjects 1109 }

        -- 1.3.6.1.4.1.9839.2.1.2.1110
        bldc-1.startup-speed OBJECT-TYPE
                    SYNTAX Integer32 (200..1200)
                    UNITS "N/A"
                    MAX-ACCESS read-write
                    STATUS current
                    DESCRIPTION "Startup speed rps"
                    DEFVAL { 500 }
                    ::= { analogObjects 1110 }

        -- 1.3.6.1.4.1.9839.2.1.2.1111
        delta-p-bldc-1 OBJECT-TYPE
                    SYNTAX Integer32 (-32768..32767)
                    UNITS "N/A"
                    MAX-ACCESS read-only
                    STATUS current
                    DESCRIPTION "N/A"
                    DEFVAL { 0 }
                    ::= { analogObjects 1111 }

        -- 1.3.6.1.4.1.9839.2.1.2.1112
        calc-p-ratio-bldc-1 OBJECT-TYPE
                    SYNTAX Integer32 (-32768..32767)
                    UNITS "N/A"
                    MAX-ACCESS read-only
                    STATUS current
                    DESCRIPTION "N/A"
                    DEFVAL { 0 }
                    ::= { analogObjects 1112 }

        -- 1.3.6.1.4.1.9839.2.1.2.1150
        maxoutfreq-rps-pwrp-1 OBJECT-TYPE
                    SYNTAX Integer32 (0..3600)
                    UNITS "N/A"
                    MAX-ACCESS read-only
                    STATUS current
                    DESCRIPTION "Maximum power+ output frequency set (Rps)"
                    DEFVAL { 0 }
                    ::= { analogObjects 1150 }

        -- 1.3.6.1.4.1.9839.2.1.2.1151
        minoutfreq-rps-pwrp-1 OBJECT-TYPE
                    SYNTAX Integer32 (0..5000)
                    UNITS "N/A"
                    MAX-ACCESS read-only
                    STATUS current
                    DESCRIPTION "Minimum drive output frequency (rps)"
                    DEFVAL { 0 }
                    ::= { analogObjects 1151 }

        -- 1.3.6.1.4.1.9839.2.1.2.1152
        mota-pwrp-1 OBJECT-TYPE
                    SYNTAX Integer32 (-9999..9999)
                    UNITS "% x10"
                    MAX-ACCESS read-only
                    STATUS current
                    DESCRIPTION "Motor current"
                    DEFVAL { 0 }
                    ::= { analogObjects 1152 }

        -- 1.3.6.1.4.1.9839.2.1.2.1153
        motv-pwrp-1 OBJECT-TYPE
                    SYNTAX Integer32 (-9999..9999)
                    UNITS "V x10"
                    MAX-ACCESS read-only
                    STATUS current
                    DESCRIPTION "Motor voltage"
                    DEFVAL { 0 }
                    ::= { analogObjects 1153 }

        -- 1.3.6.1.4.1.9839.2.1.2.1154
        rotorspeed-hz-pwrp-1 OBJECT-TYPE
                    SYNTAX Integer32 (0..9999)
                    UNITS "N/A"
                    MAX-ACCESS read-only
                    STATUS current
                    DESCRIPTION "Rotor speed"
                    DEFVAL { 0 }
                    ::= { analogObjects 1154 }

        -- 1.3.6.1.4.1.9839.2.1.2.1155
        rotorspeed-rps-pwrp-1 OBJECT-TYPE
                    SYNTAX Integer32 (0..9999)
                    UNITS "N/A"
                    MAX-ACCESS read-only
                    STATUS current
                    DESCRIPTION "Rotor speed"
                    DEFVAL { 0 }
                    ::= { analogObjects 1155 }

        -- 1.3.6.1.4.1.9839.2.1.2.1156
        motor-power-pwrp-1 OBJECT-TYPE
                    SYNTAX Integer32 (-32768..32767)
                    UNITS "N/A"
                    MAX-ACCESS read-only
                    STATUS current
                    DESCRIPTION "N/A"
                    DEFVAL { 0 }
                    ::= { analogObjects 1156 }

        -- 1.3.6.1.4.1.9839.2.1.2.1200
        oil-return-thr-bldc-2 OBJECT-TYPE
                    SYNTAX Integer32 (0..9999)
                    UNITS "N/A"
                    MAX-ACCESS read-write
                    STATUS current
                    DESCRIPTION "N/A"
                    DEFVAL { 0 }
                    ::= { analogObjects 1200 }

        -- 1.3.6.1.4.1.9839.2.1.2.1201
        condregsetp-bldc-2 OBJECT-TYPE
                    SYNTAX Integer32 (-32768..32767)
                    UNITS "N/A"
                    MAX-ACCESS read-only
                    STATUS current
                    DESCRIPTION "Condensing press. lower limit (Fan regul. in chiller) (bar/psi)"
                    DEFVAL { 0 }
                    ::= { analogObjects 1201 }

        -- 1.3.6.1.4.1.9839.2.1.2.1202
        condregsettemp-bldc-2 OBJECT-TYPE
                    SYNTAX Integer32 (-32768..32767)
                    UNITS "C/F x10"
                    MAX-ACCESS read-only
                    STATUS current
                    DESCRIPTION "Condensing temp. lower limit (Fan regul. in chiller)"
                    DEFVAL { 0 }
                    ::= { analogObjects 1202 }

        -- 1.3.6.1.4.1.9839.2.1.2.1203
        evapregsetp-bldc-2 OBJECT-TYPE
                    SYNTAX Integer32 (-32768..32767)
                    UNITS "N/A"
                    MAX-ACCESS read-only
                    STATUS current
                    DESCRIPTION "Evaporating Press. upper limit (Fan regul. in Pdc) (bar/psi)"
                    DEFVAL { 0 }
                    ::= { analogObjects 1203 }

        -- 1.3.6.1.4.1.9839.2.1.2.1204
        evapregsettemp-bldc-2 OBJECT-TYPE
                    SYNTAX Integer32 (-32768..32767)
                    UNITS "C/F x10"
                    MAX-ACCESS read-only
                    STATUS current
                    DESCRIPTION "Evaporating temp. upper limit (Fan regul. in Pdc)"
                    DEFVAL { 0 }
                    ::= { analogObjects 1204 }

        -- 1.3.6.1.4.1.9839.2.1.2.1205
        maxgoupspeedrate-bldc-2 OBJECT-TYPE
                    SYNTAX Integer32 (0..99)
                    UNITS "N/A"
                    MAX-ACCESS read-write
                    STATUS current
                    DESCRIPTION "Max. increase speed rate (going to target speed in defrost) [rps/s]"
                    DEFVAL { 10 }
                    ::= { analogObjects 1205 }

        -- 1.3.6.1.4.1.9839.2.1.2.1206
        minspeedgoto-rps-bldc-2 OBJECT-TYPE
                    SYNTAX Integer32 (0..999)
                    UNITS "N/A"
                    MAX-ACCESS read-write
                    STATUS current
                    DESCRIPTION "Minimum speed (used by Goto_Min_Speed) [rps]"
                    DEFVAL { 0 }
                    ::= { analogObjects 1206 }

        -- 1.3.6.1.4.1.9839.2.1.2.1207
        vfd-req-0-1000-bldc-2 OBJECT-TYPE
                    SYNTAX Integer32 (0..9999)
                    UNITS "N/A"
                    MAX-ACCESS read-only
                    STATUS current
                    DESCRIPTION "Speed request out to inverter module"
                    DEFVAL { 0 }
                    ::= { analogObjects 1207 }

        -- 1.3.6.1.4.1.9839.2.1.2.1208
        max-speed-x-rps-bldc-2 OBJECT-TYPE
                    SYNTAX Integer32 (-32768..32767)
                    UNITS "N/A"
                    MAX-ACCESS read-write
                    STATUS current
                    DESCRIPTION "N/A"
                    DEFVAL { 0 }
                    ::= { analogObjects 1208 }

        -- 1.3.6.1.4.1.9839.2.1.2.1209
        delta-p-bldc-2 OBJECT-TYPE
                    SYNTAX Integer32 (-32768..32767)
                    UNITS "N/A"
                    MAX-ACCESS read-only
                    STATUS current
                    DESCRIPTION "N/A"
                    DEFVAL { 0 }
                    ::= { analogObjects 1209 }

        -- 1.3.6.1.4.1.9839.2.1.2.1210
        calc-p-ratio-bldc-2 OBJECT-TYPE
                    SYNTAX Integer32 (-32768..32767)
                    UNITS "N/A"
                    MAX-ACCESS read-only
                    STATUS current
                    DESCRIPTION "N/A"
                    DEFVAL { 0 }
                    ::= { analogObjects 1210 }

        -- 1.3.6.1.4.1.9839.2.1.2.1211
        bldc-2.startup-speed OBJECT-TYPE
                    SYNTAX Integer32 (200..1200)
                    UNITS "N/A"
                    MAX-ACCESS read-write
                    STATUS current
                    DESCRIPTION "Startup speed rps"
                    DEFVAL { 500 }
                    ::= { analogObjects 1211 }

        -- 1.3.6.1.4.1.9839.2.1.2.1250
        maxoutfreq-rps-pwrp-2 OBJECT-TYPE
                    SYNTAX Integer32 (0..3600)
                    UNITS "N/A"
                    MAX-ACCESS read-only
                    STATUS current
                    DESCRIPTION "Maximum power+ output frequency set (Rps)"
                    DEFVAL { 0 }
                    ::= { analogObjects 1250 }

        -- 1.3.6.1.4.1.9839.2.1.2.1251
        minoutfreq-rps-pwrp-2 OBJECT-TYPE
                    SYNTAX Integer32 (0..5000)
                    UNITS "N/A"
                    MAX-ACCESS read-only
                    STATUS current
                    DESCRIPTION "Minimum drive output frequency (rps)"
                    DEFVAL { 0 }
                    ::= { analogObjects 1251 }

        -- 1.3.6.1.4.1.9839.2.1.2.1252
        mota-pwrp-2 OBJECT-TYPE
                    SYNTAX Integer32 (-9999..9999)
                    UNITS "% x10"
                    MAX-ACCESS read-only
                    STATUS current
                    DESCRIPTION "Motor current"
                    DEFVAL { 0 }
                    ::= { analogObjects 1252 }

        -- 1.3.6.1.4.1.9839.2.1.2.1253
        motv-pwrp-2 OBJECT-TYPE
                    SYNTAX Integer32 (-9999..9999)
                    UNITS "V x10"
                    MAX-ACCESS read-only
                    STATUS current
                    DESCRIPTION "Motor voltage"
                    DEFVAL { 0 }
                    ::= { analogObjects 1253 }

        -- 1.3.6.1.4.1.9839.2.1.2.1254
        rotorspeed-hz-pwrp-2 OBJECT-TYPE
                    SYNTAX Integer32 (0..9999)
                    UNITS "N/A"
                    MAX-ACCESS read-only
                    STATUS current
                    DESCRIPTION "Rotor speed"
                    DEFVAL { 0 }
                    ::= { analogObjects 1254 }

        -- 1.3.6.1.4.1.9839.2.1.2.1255
        rotorspeed-rps-pwrp-2 OBJECT-TYPE
                    SYNTAX Integer32 (0..9999)
                    UNITS "N/A"
                    MAX-ACCESS read-only
                    STATUS current
                    DESCRIPTION "Rotor speed"
                    DEFVAL { 0 }
                    ::= { analogObjects 1255 }

        -- 1.3.6.1.4.1.9839.2.1.2.1256
        motor-power-pwrp-2 OBJECT-TYPE
                    SYNTAX Integer32 (-32768..32767)
                    UNITS "N/A"
                    MAX-ACCESS read-only
                    STATUS current
                    DESCRIPTION "N/A"
                    DEFVAL { 0 }
                    ::= { analogObjects 1256 }

        -- 1.3.6.1.4.1.9839.2.1.2.1300
        dscgsh-set-evds-1 OBJECT-TYPE
                    SYNTAX Integer32 (10..8000)
                    UNITS "N/A"
                    MAX-ACCESS read-only
                    STATUS current
                    DESCRIPTION "Setpoint discharge superheat"
                    ::= { analogObjects 1300 }

        -- 1.3.6.1.4.1.9839.2.1.2.1301
        s1-probe-value OBJECT-TYPE
                    SYNTAX Integer32 (-32768..32767)
                    UNITS "N/A"
                    MAX-ACCESS read-only
                    STATUS current
                    DESCRIPTION "S1 probe value"
                    DEFVAL { 0 }
                    ::= { analogObjects 1301 }

        -- 1.3.6.1.4.1.9839.2.1.2.1302
        s2-probe-value OBJECT-TYPE
                    SYNTAX Integer32 (-32768..32767)
                    UNITS "N/A"
                    MAX-ACCESS read-only
                    STATUS current
                    DESCRIPTION "S2 probe value"
                    DEFVAL { 0 }
                    ::= { analogObjects 1302 }

        -- 1.3.6.1.4.1.9839.2.1.2.1303
        s3-probe-value OBJECT-TYPE
                    SYNTAX Integer32 (-32768..32767)
                    UNITS "N/A"
                    MAX-ACCESS read-only
                    STATUS current
                    DESCRIPTION "S3 probe value"
                    DEFVAL { 0 }
                    ::= { analogObjects 1303 }

        -- 1.3.6.1.4.1.9839.2.1.2.1304
        s4-probe-value OBJECT-TYPE
                    SYNTAX Integer32 (-32768..32767)
                    UNITS "N/A"
                    MAX-ACCESS read-only
                    STATUS current
                    DESCRIPTION "S4 probe value"
                    DEFVAL { 0 }
                    ::= { analogObjects 1304 }

        -- 1.3.6.1.4.1.9839.2.1.2.1305
        s4-ntc-thermtc-evds-1 OBJECT-TYPE
                    SYNTAX Integer32 (10..8000)
                    UNITS "sec x10"
                    MAX-ACCESS read-only
                    STATUS current
                    DESCRIPTION "Thermal time constant (T.C.)  for S4 NTC probe"
                    ::= { analogObjects 1305 }

        -- 1.3.6.1.4.1.9839.2.1.2.1306
        dscgtempset-evds-1 OBJECT-TYPE
                    SYNTAX Integer32 (10..8000)
                    UNITS "N/A"
                    MAX-ACCESS read-only
                    STATUS current
                    DESCRIPTION "Setpoint discharge temperature"
                    ::= { analogObjects 1306 }

        -- 1.3.6.1.4.1.9839.2.1.2.1307
        condensing-press OBJECT-TYPE
                    SYNTAX Integer32 (-32768..32767)
                    UNITS "N/A"
                    MAX-ACCESS read-only
                    STATUS current
                    DESCRIPTION "Condensing pressure"
                    DEFVAL { 0 }
                    ::= { analogObjects 1307 }

        -- 1.3.6.1.4.1.9839.2.1.2.1308
        condensing-temp OBJECT-TYPE
                    SYNTAX Integer32 (-32768..32767)
                    UNITS "N/A"
                    MAX-ACCESS read-only
                    STATUS current
                    DESCRIPTION "Condensing temperature"
                    DEFVAL { 0 }
                    ::= { analogObjects 1308 }

        -- 1.3.6.1.4.1.9839.2.1.2.1309
        suction-temp-a OBJECT-TYPE
                    SYNTAX Integer32 (-32768..32767)
                    UNITS "N/A"
                    MAX-ACCESS read-only
                    STATUS current
                    DESCRIPTION "Suction temperature valve A"
                    DEFVAL { 0 }
                    ::= { analogObjects 1309 }

        -- 1.3.6.1.4.1.9839.2.1.2.1310
        suction-temp-b OBJECT-TYPE
                    SYNTAX Integer32 (-32768..32767)
                    UNITS "C/F x10"
                    MAX-ACCESS read-only
                    STATUS current
                    DESCRIPTION "Suction temperature valve B"
                    DEFVAL { 0 }
                    ::= { analogObjects 1310 }

        -- 1.3.6.1.4.1.9839.2.1.2.1311
        evaporation-temp-a OBJECT-TYPE
                    SYNTAX Integer32 (-32768..32767)
                    UNITS "C/F x10"
                    MAX-ACCESS read-only
                    STATUS current
                    DESCRIPTION "Evaporation temperature valve A"
                    DEFVAL { 0 }
                    ::= { analogObjects 1311 }

        -- 1.3.6.1.4.1.9839.2.1.2.1312
        evaporation-temp-b OBJECT-TYPE
                    SYNTAX Integer32 (-32768..32767)
                    UNITS "C/F x10"
                    MAX-ACCESS read-only
                    STATUS current
                    DESCRIPTION "Evaporation temperature valve B"
                    DEFVAL { 0 }
                    ::= { analogObjects 1312 }

        -- 1.3.6.1.4.1.9839.2.1.2.1313
        evaporation-press-a OBJECT-TYPE
                    SYNTAX Integer32 (-32768..32767)
                    UNITS "N/A"
                    MAX-ACCESS read-only
                    STATUS current
                    DESCRIPTION "Evaporation pressure valve A"
                    DEFVAL { 0 }
                    ::= { analogObjects 1313 }

        -- 1.3.6.1.4.1.9839.2.1.2.1314
        evaporation-press-b OBJECT-TYPE
                    SYNTAX Integer32 (-32768..32767)
                    UNITS "N/A"
                    MAX-ACCESS read-only
                    STATUS current
                    DESCRIPTION "Evaporation pressure valve B"
                    DEFVAL { 0 }
                    ::= { analogObjects 1314 }

        -- 1.3.6.1.4.1.9839.2.1.2.1315
        superheat-a OBJECT-TYPE
                    SYNTAX Integer32 (-32768..32767)
                    UNITS "N/A"
                    MAX-ACCESS read-only
                    STATUS current
                    DESCRIPTION "Superheat valve A"
                    DEFVAL { 0 }
                    ::= { analogObjects 1315 }

        -- 1.3.6.1.4.1.9839.2.1.2.1316
        superheat-b OBJECT-TYPE
                    SYNTAX Integer32 (-32768..32767)
                    UNITS "N/A"
                    MAX-ACCESS read-only
                    STATUS current
                    DESCRIPTION "Superheat valve B"
                    DEFVAL { 0 }
                    ::= { analogObjects 1316 }

        -- 1.3.6.1.4.1.9839.2.1.2.1317
        mop-inhibthrsh-evds-1 OBJECT-TYPE
                    SYNTAX Integer32 (0..9999)
                    UNITS "N/A"
                    MAX-ACCESS read-only
                    STATUS current
                    DESCRIPTION "MOP inhibition threshold"
                    DEFVAL { 0 }
                    ::= { analogObjects 1317 }

        -- 1.3.6.1.4.1.9839.2.1.2.1318
        mop-thrshfastchange-evds-1 OBJECT-TYPE
                    SYNTAX Integer32 (-600..2000)
                    UNITS "N/A"
                    MAX-ACCESS read-only
                    STATUS current
                    DESCRIPTION "MOP threshold for frequent change"
                    DEFVAL { 0 }
                    ::= { analogObjects 1318 }

        -- 1.3.6.1.4.1.9839.2.1.2.1319
        dscgsh-evds-1 OBJECT-TYPE
                    SYNTAX Integer32 (-400..1800)
                    UNITS "C/F x10"
                    MAX-ACCESS read-only
                    STATUS current
                    DESCRIPTION "Discharge superheat"
                    DEFVAL { 0 }
                    ::= { analogObjects 1319 }

        -- 1.3.6.1.4.1.9839.2.1.2.1320
        dscgtemp-evds-1 OBJECT-TYPE
                    SYNTAX Integer32 (-600..2000)
                    UNITS "C/F x10"
                    MAX-ACCESS read-only
                    STATUS current
                    DESCRIPTION "Discharge temperature"
                    DEFVAL { 0 }
                    ::= { analogObjects 1320 }

        -- 1.3.6.1.4.1.9839.2.1.2.1321
        evd-1.a17-eev-position-percent-show OBJECT-TYPE
                    SYNTAX Integer32 (0..1000)
                    UNITS "N/A"
                    MAX-ACCESS read-write
                    STATUS current
                    DESCRIPTION "Valve A opening percent"
                    DEFVAL { 0 }
                    ::= { analogObjects 1321 }

        -- 1.3.6.1.4.1.9839.2.1.2.1322
        evd-1.a66-eev-pos-percent-2nd-show OBJECT-TYPE
                    SYNTAX Integer32 (0..1000)
                    UNITS "N/A"
                    MAX-ACCESS read-write
                    STATUS current
                    DESCRIPTION "Opening percent - Valve B"
                    DEFVAL { 0 }
                    ::= { analogObjects 1322 }

        -- 1.3.6.1.4.1.9839.2.1.2.1323
        evd-1.a34-s1-value-offset-msk OBJECT-TYPE
                    SYNTAX Integer32 (-8700..8700)
                    UNITS "N/A"
                    MAX-ACCESS read-write
                    STATUS current
                    DESCRIPTION "S1: calibration offset"
                    DEFVAL { 0 }
                    ::= { analogObjects 1323 }

        -- 1.3.6.1.4.1.9839.2.1.2.1324
        evd-1.a41-s2-value-offset-msk OBJECT-TYPE
                    SYNTAX Integer32 (-360..360)
                    UNITS "N/A"
                    MAX-ACCESS read-write
                    STATUS current
                    DESCRIPTION "S2 calibration offset"
                    DEFVAL { 0 }
                    ::= { analogObjects 1324 }

        -- 1.3.6.1.4.1.9839.2.1.2.1325
        evd-1.a35-s3-value-offset-msk OBJECT-TYPE
                    SYNTAX Integer32 (-8700..8700)
                    UNITS "N/A"
                    MAX-ACCESS read-write
                    STATUS current
                    DESCRIPTION "S3: calibration offset "
                    DEFVAL { 0 }
                    ::= { analogObjects 1325 }

        -- 1.3.6.1.4.1.9839.2.1.2.1326
        evd-1.a42-s4-value-offset-msk OBJECT-TYPE
                    SYNTAX Integer32 (-360..360)
                    UNITS "N/A"
                    MAX-ACCESS read-write
                    STATUS current
                    DESCRIPTION "S4 calibration offset"
                    DEFVAL { 0 }
                    ::= { analogObjects 1326 }

        -- 1.3.6.1.4.1.9839.2.1.2.1400
        cpy-1.a33-c8-serialalrmdelay-msk OBJECT-TYPE
                    SYNTAX Integer32 (0..3000)
                    UNITS "N/A"
                    MAX-ACCESS read-write
                    STATUS current
                    DESCRIPTION "Serial alarm delay at CPY side"
                    DEFVAL { 0 }
                    ::= { analogObjects 1400 }

        -- 1.3.6.1.4.1.9839.2.1.2.1401
        cpy-1.a30-d6-curr OBJECT-TYPE
                    SYNTAX Integer32 (0..999)
                    UNITS "N/A"
                    MAX-ACCESS read-only
                    STATUS current
                    DESCRIPTION "Displayed current"
                    DEFVAL { 0 }
                    ::= { analogObjects 1401 }

        -- 1.3.6.1.4.1.9839.2.1.2.1402
        cpy-1.a15-d3-steaminstantflowrate OBJECT-TYPE
                    SYNTAX Integer32 (0..1990)
                    UNITS "Kg/h x10"
                    MAX-ACCESS read-only
                    STATUS current
                    DESCRIPTION "Display instant steam flow-rate (instant value)"
                    DEFVAL { 0 }
                    ::= { analogObjects 1402 }

        -- 1.3.6.1.4.1.9839.2.1.2.1500
        energy-meters-1.current-1-l-spv OBJECT-TYPE
                    SYNTAX Integer32 (0..9999)
                    UNITS "N/A"
                    MAX-ACCESS read-only
                    STATUS current
                    DESCRIPTION "Current line 1 "
                    DEFVAL { 0 }
                    ::= { analogObjects 1500 }

        -- 1.3.6.1.4.1.9839.2.1.2.1501
        energy-meters-1.current-2-l-spv OBJECT-TYPE
                    SYNTAX Integer32 (0..9999)
                    UNITS "N/A"
                    MAX-ACCESS read-only
                    STATUS current
                    DESCRIPTION "Current line 2"
                    DEFVAL { 0 }
                    ::= { analogObjects 1501 }

        -- 1.3.6.1.4.1.9839.2.1.2.1502
        energy-meters-1.current-3-l-spv OBJECT-TYPE
                    SYNTAX Integer32 (0..9999)
                    UNITS "N/A"
                    MAX-ACCESS read-only
                    STATUS current
                    DESCRIPTION "Current line 3"
                    DEFVAL { 0 }
                    ::= { analogObjects 1502 }

        -- 1.3.6.1.4.1.9839.2.1.2.1503
        energy-meters-1.apparent-power-1-l-spv OBJECT-TYPE
                    SYNTAX Integer32 (0..9999)
                    UNITS "N/A"
                    MAX-ACCESS read-only
                    STATUS current
                    DESCRIPTION "Reactive power 1 "
                    DEFVAL { 0 }
                    ::= { analogObjects 1503 }

        -- 1.3.6.1.4.1.9839.2.1.2.1504
        energy-meters-1.apparent-power-2-l-spv OBJECT-TYPE
                    SYNTAX Integer32 (0..9999)
                    UNITS "N/A"
                    MAX-ACCESS read-only
                    STATUS current
                    DESCRIPTION "Reactive power 2"
                    DEFVAL { 0 }
                    ::= { analogObjects 1504 }

        -- 1.3.6.1.4.1.9839.2.1.2.1505
        energy-meters-1.apparent-power-3-l-spv OBJECT-TYPE
                    SYNTAX Integer32 (0..9999)
                    UNITS "N/A"
                    MAX-ACCESS read-only
                    STATUS current
                    DESCRIPTION "Reactive power 3 "
                    DEFVAL { 0 }
                    ::= { analogObjects 1505 }

        -- 1.3.6.1.4.1.9839.2.1.2.1506
        energy-meters-1.power-1-l-spv OBJECT-TYPE
                    SYNTAX Integer32 (0..9999)
                    UNITS "N/A"
                    MAX-ACCESS read-only
                    STATUS current
                    DESCRIPTION "Power 1 "
                    DEFVAL { 0 }
                    ::= { analogObjects 1506 }

        -- 1.3.6.1.4.1.9839.2.1.2.1507
        energy-meters-1.power-2-l-spv OBJECT-TYPE
                    SYNTAX Integer32 (0..9999)
                    UNITS "N/A"
                    MAX-ACCESS read-only
                    STATUS current
                    DESCRIPTION "Power 2"
                    DEFVAL { 0 }
                    ::= { analogObjects 1507 }

        -- 1.3.6.1.4.1.9839.2.1.2.1508
        energy-meters-1.power-3-l-spv OBJECT-TYPE
                    SYNTAX Integer32 (0..9999)
                    UNITS "N/A"
                    MAX-ACCESS read-only
                    STATUS current
                    DESCRIPTION "Power 3"
                    DEFVAL { 0 }
                    ::= { analogObjects 1508 }

        -- 1.3.6.1.4.1.9839.2.1.2.1600
        danfoss-act-rps OBJECT-TYPE
                    SYNTAX Integer32 (-32768..32767)
                    UNITS "N/A"
                    MAX-ACCESS read-only
                    STATUS current
                    DESCRIPTION "N/A"
                    DEFVAL { 0 }
                    ::= { analogObjects 1600 }

        -- 1.3.6.1.4.1.9839.2.1.2.1601
        comp-pwr-req-danfoss-act OBJECT-TYPE
                    SYNTAX Integer32 (0..1000)
                    UNITS "N/A"
                    MAX-ACCESS read-only
                    STATUS current
                    DESCRIPTION "N/A"
                    DEFVAL { 0 }
                    ::= { analogObjects 1601 }

        -- 1.3.6.1.4.1.9839.2.1.2.1602
        danfoss-min-rps OBJECT-TYPE
                    SYNTAX Integer32 (-32768..32767)
                    UNITS "N/A"
                    MAX-ACCESS read-only
                    STATUS current
                    DESCRIPTION "N/A"
                    DEFVAL { 0 }
                    ::= { analogObjects 1602 }

        -- 1.3.6.1.4.1.9839.2.1.2.1603
        danfoss-max-rps OBJECT-TYPE
                    SYNTAX Integer32 (-32768..32767)
                    UNITS "N/A"
                    MAX-ACCESS read-only
                    STATUS current
                    DESCRIPTION "N/A"
                    DEFVAL { 0 }
                    ::= { analogObjects 1603 }

        -- 1.3.6.1.4.1.9839.2.1.2.1604
        danfoss-fboost-rps OBJECT-TYPE
                    SYNTAX Integer32 (250..1000)
                    UNITS "N/A"
                    MAX-ACCESS read-write
                    STATUS current
                    DESCRIPTION "Danfoss boost speed for oil management"
                    DEFVAL { 700 }
                    ::= { analogObjects 1604 }

        -- 1.3.6.1.4.1.9839.2.1.2.1605
        danfoss-fmin-demand OBJECT-TYPE
                    SYNTAX Integer32 (0..1000)
                    UNITS "N/A"
                    MAX-ACCESS read-write
                    STATUS current
                    DESCRIPTION "N/A"
                    DEFVAL { 0 }
                    ::= { analogObjects 1605 }

        -- 1.3.6.1.4.1.9839.2.1.2.1606
        fixedoffthrsh-danfoss OBJECT-TYPE
                    SYNTAX Integer32 (0..9999)
                    UNITS "N/A"
                    MAX-ACCESS read-write
                    STATUS current
                    DESCRIPTION "Threshold of BLDC speeed (in rps) to call on fixed speed compressor"
                    DEFVAL { 900 }
                    ::= { analogObjects 1606 }

        -- 1.3.6.1.4.1.9839.2.1.2.1607
        fixedonthrsh-danfoss OBJECT-TYPE
                    SYNTAX Integer32 (0..9999)
                    UNITS "N/A"
                    MAX-ACCESS read-write
                    STATUS current
                    DESCRIPTION "Threshold of BLDC speeed (in rps) to call on fixed speed compressor"
                    DEFVAL { 900 }
                    ::= { analogObjects 1607 }

        -- 1.3.6.1.4.1.9839.2.1.2.1608
        condregsettemp-danfoss OBJECT-TYPE
                    SYNTAX Integer32 (-32768..32767)
                    UNITS "C/F x10"
                    MAX-ACCESS read-only
                    STATUS current
                    DESCRIPTION "Condensing temp. lower limit (Fan regul. in chiller)"
                    DEFVAL { 0 }
                    ::= { analogObjects 1608 }

        -- 1.3.6.1.4.1.9839.2.1.2.1609
        evapregsettemp-danfoss OBJECT-TYPE
                    SYNTAX Integer32 (-32768..32767)
                    UNITS "C/F x10"
                    MAX-ACCESS read-only
                    STATUS current
                    DESCRIPTION "Evaporating temp. upper limit (Fan regul. in Pdc)"
                    DEFVAL { 0 }
                    ::= { analogObjects 1609 }

        -- 1.3.6.1.4.1.9839.2.1.2.1610
        evapregsetp-danfoss OBJECT-TYPE
                    SYNTAX Integer32 (-32768..32767)
                    UNITS "N/A"
                    MAX-ACCESS read-only
                    STATUS current
                    DESCRIPTION "Evaporating Press. upper limit (Fan regul. in Pdc) (bar/psi)"
                    DEFVAL { 0 }
                    ::= { analogObjects 1610 }

        -- 1.3.6.1.4.1.9839.2.1.2.1611
        condregsetp-danfoss OBJECT-TYPE
                    SYNTAX Integer32 (-32768..32767)
                    UNITS "N/A"
                    MAX-ACCESS read-only
                    STATUS current
                    DESCRIPTION "Condensing press. lower limit (Fan regul. in chiller) (bar/psi)"
                    DEFVAL { 0 }
                    ::= { analogObjects 1611 }

        -- 1.3.6.1.4.1.9839.2.1.2.1612
        maxgoupspeedrate-danfoss OBJECT-TYPE
                    SYNTAX Integer32 (0..990)
                    UNITS "N/A"
                    MAX-ACCESS read-write
                    STATUS current
                    DESCRIPTION "Max. increase speed rate (going to target speed in defrost) [rps/s]"
                    DEFVAL { 20 }
                    ::= { analogObjects 1612 }

        -- 1.3.6.1.4.1.9839.2.1.2.1613
        danfoss-bldc.delta-p OBJECT-TYPE
                    SYNTAX Integer32 (0..999)
                    UNITS "N/A"
                    MAX-ACCESS read-only
                    STATUS current
                    DESCRIPTION "Pressure difference (bar/psi depending on selection)"
                    DEFVAL { 0 }
                    ::= { analogObjects 1613 }

        -- 1.3.6.1.4.1.9839.2.1.2.1614
        danfoss-bldc.calc-p-ratio OBJECT-TYPE
                    SYNTAX Integer32 (0..9999)
                    UNITS "N/A"
                    MAX-ACCESS read-only
                    STATUS current
                    DESCRIPTION "Calculated pressure ratio "
                    DEFVAL { 0 }
                    ::= { analogObjects 1614 }



        -- 1.3.6.1.4.1.9839.2.1.3
        integerObjects OBJECT IDENTIFIER ::= { dencoccuMIB 3 }

        -- 1.3.6.1.4.1.9839.2.1.3.1
        unit-status OBJECT-TYPE
                    SYNTAX Integer32 (0..10)
                    UNITS "N/A"
                    MAX-ACCESS read-only
                    STATUS current
                    DESCRIPTION "Unit Status (0 = Unit On, 1 = Off by Alarms, 2 = Off by BMS, 3 = Off by Time Zones, 4 = Off by DI, 5 = Off by Keyboard, 6 = On HOA Mode, 7 = Stand-by, 8 = On Generator Mode, 9 = Night Purge Mode; 10 = Defrost Mode)"
                    DEFVAL { 0 }
                    ::= { integerObjects 1 }

        -- 1.3.6.1.4.1.9839.2.1.3.2
        comp-1-status OBJECT-TYPE
                    SYNTAX Integer32 (-32768..32767)
                    UNITS "N/A"
                    MAX-ACCESS read-only
                    STATUS current
                    DESCRIPTION "N/A"
                    DEFVAL { 0 }
                    ::= { integerObjects 2 }

        -- 1.3.6.1.4.1.9839.2.1.3.3
        comp-2-status OBJECT-TYPE
                    SYNTAX Integer32 (-32768..32767)
                    UNITS "N/A"
                    MAX-ACCESS read-only
                    STATUS current
                    DESCRIPTION "N/A"
                    DEFVAL { 0 }
                    ::= { integerObjects 3 }

        -- 1.3.6.1.4.1.9839.2.1.3.4
        airflow-m3h-hh OBJECT-TYPE
                    SYNTAX Integer32 (-32768..32767)
                    UNITS "N/A"
                    MAX-ACCESS read-only
                    STATUS current
                    DESCRIPTION "N/A"
                    DEFVAL { 0 }
                    ::= { integerObjects 4 }

        -- 1.3.6.1.4.1.9839.2.1.3.5
        airflow-m3h-mm OBJECT-TYPE
                    SYNTAX Integer32 (-32768..32767)
                    UNITS "N/A"
                    MAX-ACCESS read-only
                    STATUS current
                    DESCRIPTION "N/A"
                    DEFVAL { 0 }
                    ::= { integerObjects 5 }

        -- 1.3.6.1.4.1.9839.2.1.3.6
        airflow-m3h-ll OBJECT-TYPE
                    SYNTAX Integer32 (-32768..32767)
                    UNITS "N/A"
                    MAX-ACCESS read-only
                    STATUS current
                    DESCRIPTION "N/A"
                    DEFVAL { 0 }
                    ::= { integerObjects 6 }

        -- 1.3.6.1.4.1.9839.2.1.3.7
        airflow-m3s-hh OBJECT-TYPE
                    SYNTAX Integer32 (-32768..32767)
                    UNITS "N/A"
                    MAX-ACCESS read-only
                    STATUS current
                    DESCRIPTION "N/A"
                    DEFVAL { 0 }
                    ::= { integerObjects 7 }

        -- 1.3.6.1.4.1.9839.2.1.3.8
        airflow-m3s-ll OBJECT-TYPE
                    SYNTAX Integer32 (-32768..32767)
                    UNITS "N/A"
                    MAX-ACCESS read-only
                    STATUS current
                    DESCRIPTION "N/A"
                    DEFVAL { 0 }
                    ::= { integerObjects 8 }

        -- 1.3.6.1.4.1.9839.2.1.3.9
        x-h-main-fan OBJECT-TYPE
                    SYNTAX Integer32 (0..999)
                    UNITS "hour"
                    MAX-ACCESS read-only
                    STATUS current
                    DESCRIPTION "Unit Fan Run Hours (high part)"
                    DEFVAL { 0 }
                    ::= { integerObjects 9 }

        -- 1.3.6.1.4.1.9839.2.1.3.10
        x-l-main-fan OBJECT-TYPE
                    SYNTAX Integer32 (0..999)
                    UNITS "hour"
                    MAX-ACCESS read-only
                    STATUS current
                    DESCRIPTION "Unit Fan Run Hours (low part)"
                    DEFVAL { 0 }
                    ::= { integerObjects 10 }

        -- 1.3.6.1.4.1.9839.2.1.3.11
        h-hour-comp1 OBJECT-TYPE
                    SYNTAX Integer32 (0..999)
                    UNITS "hour"
                    MAX-ACCESS read-only
                    STATUS current
                    DESCRIPTION "Compressor 1 Run Hours (high part)"
                    DEFVAL { 0 }
                    ::= { integerObjects 11 }

        -- 1.3.6.1.4.1.9839.2.1.3.12
        l-hour-comp1 OBJECT-TYPE
                    SYNTAX Integer32 (0..999)
                    UNITS "hour"
                    MAX-ACCESS read-only
                    STATUS current
                    DESCRIPTION "Compressor 1 Run Hours (low part)"
                    DEFVAL { 0 }
                    ::= { integerObjects 12 }

        -- 1.3.6.1.4.1.9839.2.1.3.13
        h-hour-comp2 OBJECT-TYPE
                    SYNTAX Integer32 (0..999)
                    UNITS "hour"
                    MAX-ACCESS read-only
                    STATUS current
                    DESCRIPTION "Compressor 2 Run Hours (high part)"
                    DEFVAL { 0 }
                    ::= { integerObjects 13 }

        -- 1.3.6.1.4.1.9839.2.1.3.14
        l-hour-comp2 OBJECT-TYPE
                    SYNTAX Integer32 (0..999)
                    UNITS "hour"
                    MAX-ACCESS read-only
                    STATUS current
                    DESCRIPTION "Compressor 2 Run Hours (low part)"
                    DEFVAL { 0 }
                    ::= { integerObjects 14 }

        -- 1.3.6.1.4.1.9839.2.1.3.15
        h-hour-0-10-cool OBJECT-TYPE
                    SYNTAX Integer32 (0..999)
                    UNITS "hour"
                    MAX-ACCESS read-only
                    STATUS current
                    DESCRIPTION "0 _ 10v Cooling Run Hours (high part)"
                    DEFVAL { 0 }
                    ::= { integerObjects 15 }

        -- 1.3.6.1.4.1.9839.2.1.3.16
        l-hour-0-10-cool OBJECT-TYPE
                    SYNTAX Integer32 (0..999)
                    UNITS "hour"
                    MAX-ACCESS read-only
                    STATUS current
                    DESCRIPTION "0 _ 10v Cooling Run Hours (low part)"
                    DEFVAL { 0 }
                    ::= { integerObjects 16 }

        -- 1.3.6.1.4.1.9839.2.1.3.17
        h-hour-dodc-cool OBJECT-TYPE
                    SYNTAX Integer32 (0..999)
                    UNITS "hour"
                    MAX-ACCESS read-only
                    STATUS current
                    DESCRIPTION "DODC Cooling Run Hours (high part)"
                    DEFVAL { 0 }
                    ::= { integerObjects 17 }

        -- 1.3.6.1.4.1.9839.2.1.3.18
        l-hour-dodc-cool OBJECT-TYPE
                    SYNTAX Integer32 (0..999)
                    UNITS "hour"
                    MAX-ACCESS read-only
                    STATUS current
                    DESCRIPTION "DODC Cooling Run Hours (low part)"
                    DEFVAL { 0 }
                    ::= { integerObjects 18 }

        -- 1.3.6.1.4.1.9839.2.1.3.19
        h-hour-ambicool OBJECT-TYPE
                    SYNTAX Integer32 (0..999)
                    UNITS "hour"
                    MAX-ACCESS read-only
                    STATUS current
                    DESCRIPTION "Ambicool Run Hours (high part)"
                    DEFVAL { 0 }
                    ::= { integerObjects 19 }

        -- 1.3.6.1.4.1.9839.2.1.3.20
        l-hour-ambicool OBJECT-TYPE
                    SYNTAX Integer32 (0..999)
                    UNITS "hour"
                    MAX-ACCESS read-only
                    STATUS current
                    DESCRIPTION "Ambicool Run Hours (low part)"
                    DEFVAL { 0 }
                    ::= { integerObjects 20 }

        -- 1.3.6.1.4.1.9839.2.1.3.21
        h-hour-heater1 OBJECT-TYPE
                    SYNTAX Integer32 (0..999)
                    UNITS "N/A"
                    MAX-ACCESS read-only
                    STATUS current
                    DESCRIPTION "Heater 1 Run Hours (high part)"
                    DEFVAL { 0 }
                    ::= { integerObjects 21 }

        -- 1.3.6.1.4.1.9839.2.1.3.22
        l-hour-heater1 OBJECT-TYPE
                    SYNTAX Integer32 (0..999)
                    UNITS "hour"
                    MAX-ACCESS read-only
                    STATUS current
                    DESCRIPTION "Heater 1 Run Hours (low part)"
                    DEFVAL { 0 }
                    ::= { integerObjects 22 }

        -- 1.3.6.1.4.1.9839.2.1.3.23
        h-hour-heater2 OBJECT-TYPE
                    SYNTAX Integer32 (0..999)
                    UNITS "hour"
                    MAX-ACCESS read-only
                    STATUS current
                    DESCRIPTION "Heater 2 Run Hours (high part)"
                    DEFVAL { 0 }
                    ::= { integerObjects 23 }

        -- 1.3.6.1.4.1.9839.2.1.3.24
        l-hour-heater2 OBJECT-TYPE
                    SYNTAX Integer32 (0..999)
                    UNITS "hour"
                    MAX-ACCESS read-only
                    STATUS current
                    DESCRIPTION "Heater 2 Run Hours (low part)"
                    DEFVAL { 0 }
                    ::= { integerObjects 24 }

        -- 1.3.6.1.4.1.9839.2.1.3.25
        h-hour-0-10-heat OBJECT-TYPE
                    SYNTAX Integer32 (0..999)
                    UNITS "hour"
                    MAX-ACCESS read-only
                    STATUS current
                    DESCRIPTION "0 _ 10v Heating Run Hours (high part)"
                    DEFVAL { 0 }
                    ::= { integerObjects 25 }

        -- 1.3.6.1.4.1.9839.2.1.3.26
        l-hour-0-10-heat OBJECT-TYPE
                    SYNTAX Integer32 (0..999)
                    UNITS "hour"
                    MAX-ACCESS read-only
                    STATUS current
                    DESCRIPTION "0 _ 10v Heating Run Hours (low part)"
                    DEFVAL { 0 }
                    ::= { integerObjects 26 }

        -- 1.3.6.1.4.1.9839.2.1.3.27
        h-hour-dodc-heat OBJECT-TYPE
                    SYNTAX Integer32 (0..999)
                    UNITS "hour"
                    MAX-ACCESS read-only
                    STATUS current
                    DESCRIPTION "DODC Heating Run Hours (high part)"
                    DEFVAL { 0 }
                    ::= { integerObjects 27 }

        -- 1.3.6.1.4.1.9839.2.1.3.28
        l-hour-dodc-heat OBJECT-TYPE
                    SYNTAX Integer32 (0..999)
                    UNITS "hour"
                    MAX-ACCESS read-only
                    STATUS current
                    DESCRIPTION "DODC Heating Run Hours (low part)"
                    DEFVAL { 0 }
                    ::= { integerObjects 28 }

        -- 1.3.6.1.4.1.9839.2.1.3.29
        h-hour-dehum OBJECT-TYPE
                    SYNTAX Integer32 (0..999)
                    UNITS "hour"
                    MAX-ACCESS read-only
                    STATUS current
                    DESCRIPTION "Dehum Run Hours (high part)"
                    DEFVAL { 0 }
                    ::= { integerObjects 29 }

        -- 1.3.6.1.4.1.9839.2.1.3.30
        l-hour-dehum OBJECT-TYPE
                    SYNTAX Integer32 (0..999)
                    UNITS "hour"
                    MAX-ACCESS read-only
                    STATUS current
                    DESCRIPTION "Dehum Run Hours (low part)"
                    DEFVAL { 0 }
                    ::= { integerObjects 30 }

        -- 1.3.6.1.4.1.9839.2.1.3.31
        current-day OBJECT-TYPE
                    SYNTAX Integer32 (1..31)
                    UNITS "N/A"
                    MAX-ACCESS read-only
                    STATUS current
                    DESCRIPTION "Current day"
                    DEFVAL { 1 }
                    ::= { integerObjects 31 }

        -- 1.3.6.1.4.1.9839.2.1.3.32
        current-month OBJECT-TYPE
                    SYNTAX Integer32 (1..12)
                    UNITS "N/A"
                    MAX-ACCESS read-only
                    STATUS current
                    DESCRIPTION "Current month"
                    DEFVAL { 1 }
                    ::= { integerObjects 32 }

        -- 1.3.6.1.4.1.9839.2.1.3.33
        current-year OBJECT-TYPE
                    SYNTAX Integer32 (0..99)
                    UNITS "N/A"
                    MAX-ACCESS read-only
                    STATUS current
                    DESCRIPTION "Current year"
                    DEFVAL { 0 }
                    ::= { integerObjects 33 }

        -- 1.3.6.1.4.1.9839.2.1.3.34
        current-hour OBJECT-TYPE
                    SYNTAX Integer32 (0..23)
                    UNITS "hour"
                    MAX-ACCESS read-only
                    STATUS current
                    DESCRIPTION "Current hour"
                    DEFVAL { 0 }
                    ::= { integerObjects 34 }

        -- 1.3.6.1.4.1.9839.2.1.3.35
        current-minute OBJECT-TYPE
                    SYNTAX Integer32 (0..59)
                    UNITS "N/A"
                    MAX-ACCESS read-only
                    STATUS current
                    DESCRIPTION "Current minute"
                    DEFVAL { 0 }
                    ::= { integerObjects 35 }

        -- 1.3.6.1.4.1.9839.2.1.3.36
        compr-type OBJECT-TYPE
                    SYNTAX Integer32 (1..51)
                    UNITS "N/A"
                    MAX-ACCESS read-write
                    STATUS current
                    DESCRIPTION "Compressor model: 0=nd ; 1= Siam ANB33F-400V; 2=ANB42F-400V; 3=ANB52F-400V; 4=Samsung UG5T360F-400V; 5=UG5T450F-400V; 6=UG5T520F-400V; 7=SIAM AEB33F-400V; 8=AEB60F-400V"
                    DEFVAL { 1 }
                    ::= { integerObjects 36 }

        -- 1.3.6.1.4.1.9839.2.1.3.37
        powerplus-type-required OBJECT-TYPE
                    SYNTAX Integer32 (0..9)
                    UNITS "N/A"
                    MAX-ACCESS read-only
                    STATUS current
                    DESCRIPTION "Inverter model min. requirement: 0=null; 1=14A-400V; 2=22A-400V; 3=22A-400V;4=14A-400V;5=22A-400V;6=22A-400V"
                    DEFVAL { 0 }
                    ::= { integerObjects 37 }

        -- 1.3.6.1.4.1.9839.2.1.3.38
        dc-bus-voltage OBJECT-TYPE
                    SYNTAX Integer32 (0..9999)
                    UNITS "V"
                    MAX-ACCESS read-only
                    STATUS current
                    DESCRIPTION "DC Bus Voltage [V]"
                    DEFVAL { 0 }
                    ::= { integerObjects 38 }

        -- 1.3.6.1.4.1.9839.2.1.3.39
        compon-danfoss-delay OBJECT-TYPE
                    SYNTAX Integer32 (0..9999)
                    UNITS "sec"
                    MAX-ACCESS read-only
                    STATUS current
                    DESCRIPTION "Compressor power on (delay)"
                    DEFVAL { 0 }
                    ::= { integerObjects 39 }

        -- 1.3.6.1.4.1.9839.2.1.3.201
        plan-address OBJECT-TYPE
                    SYNTAX Integer32 (0..31)
                    UNITS "N/A"
                    MAX-ACCESS read-only
                    STATUS current
                    DESCRIPTION "Address of the controller in the pLAN network"
                    DEFVAL { 0 }
                    ::= { integerObjects 201 }

        -- 1.3.6.1.4.1.9839.2.1.3.202
        plan-status-01-16 OBJECT-TYPE
                    SYNTAX Integer32 (-32768..32767)
                    UNITS "N/A"
                    MAX-ACCESS read-only
                    STATUS current
                    DESCRIPTION "Indicates the status (online/offline) of the units from 1 to 16"
                    DEFVAL { 0 }
                    ::= { integerObjects 202 }

        -- 1.3.6.1.4.1.9839.2.1.3.203
        plan-status-17-32 OBJECT-TYPE
                    SYNTAX Integer32 (-32768..32767)
                    UNITS "N/A"
                    MAX-ACCESS read-only
                    STATUS current
                    DESCRIPTION "Indicates the status (online/offline) of the units from 17 to 32"
                    DEFVAL { 0 }
                    ::= { integerObjects 203 }

        -- 1.3.6.1.4.1.9839.2.1.3.204
        plan-info OBJECT-TYPE
                    SYNTAX Integer32 (-32768..32767)
                    UNITS "N/A"
                    MAX-ACCESS read-only
                    STATUS current
                    DESCRIPTION "Contains several information concerning the pLAN"
                    DEFVAL { 0 }
                    ::= { integerObjects 204 }

        -- 1.3.6.1.4.1.9839.2.1.3.205
        perm-mem-writecycle-cnt OBJECT-TYPE
                    SYNTAX Integer32 (0..32767)
                    UNITS "N/A"
                    MAX-ACCESS read-only
                    STATUS current
                    DESCRIPTION "Specifies the number of write cycles in the permanent memory (_T_ memory)"
                    DEFVAL { 0 }
                    ::= { integerObjects 205 }

        -- 1.3.6.1.4.1.9839.2.1.3.206
        bms-address OBJECT-TYPE
                    SYNTAX Integer32 (1..207)
                    UNITS "N/A"
                    MAX-ACCESS read-write
                    STATUS current
                    DESCRIPTION "Address of the controller in a supervisory system network n.1"
                    DEFVAL { 1 }
                    ::= { integerObjects 206 }

        -- 1.3.6.1.4.1.9839.2.1.3.207
        language OBJECT-TYPE
                    SYNTAX Integer32 (0..19)
                    UNITS "N/A"
                    MAX-ACCESS read-write
                    STATUS current
                    DESCRIPTION "Current language index (0=first language)"
                    DEFVAL { 0 }
                    ::= { integerObjects 207 }

        -- 1.3.6.1.4.1.9839.2.1.3.208
        new-hour OBJECT-TYPE
                    SYNTAX Integer32 (0..23)
                    UNITS "hour"
                    MAX-ACCESS read-write
                    STATUS current
                    DESCRIPTION "New hour"
                    DEFVAL { 0 }
                    ::= { integerObjects 208 }

        -- 1.3.6.1.4.1.9839.2.1.3.209
        new-minute OBJECT-TYPE
                    SYNTAX Integer32 (0..59)
                    UNITS "N/A"
                    MAX-ACCESS read-write
                    STATUS current
                    DESCRIPTION "New minute"
                    DEFVAL { 0 }
                    ::= { integerObjects 209 }

        -- 1.3.6.1.4.1.9839.2.1.3.210
        new-day OBJECT-TYPE
                    SYNTAX Integer32 (1..31)
                    UNITS "N/A"
                    MAX-ACCESS read-write
                    STATUS current
                    DESCRIPTION "New day"
                    ::= { integerObjects 210 }

        -- 1.3.6.1.4.1.9839.2.1.3.211
        new-month OBJECT-TYPE
                    SYNTAX Integer32 (1..12)
                    UNITS "N/A"
                    MAX-ACCESS read-write
                    STATUS current
                    DESCRIPTION "New month"
                    ::= { integerObjects 211 }

        -- 1.3.6.1.4.1.9839.2.1.3.212
        new-year OBJECT-TYPE
                    SYNTAX Integer32 (0..99)
                    UNITS "N/A"
                    MAX-ACCESS read-write
                    STATUS current
                    DESCRIPTION "New year"
                    DEFVAL { 0 }
                    ::= { integerObjects 212 }

        -- 1.3.6.1.4.1.9839.2.1.3.213
        bms2-address OBJECT-TYPE
                    SYNTAX Integer32 (1..207)
                    UNITS "N/A"
                    MAX-ACCESS read-write
                    STATUS current
                    DESCRIPTION "Address of the controller in a supervisory system network n.2"
                    DEFVAL { 1 }
                    ::= { integerObjects 213 }

        -- 1.3.6.1.4.1.9839.2.1.3.301
        serial-number-1 OBJECT-TYPE
                    SYNTAX Integer32 (0..9)
                    UNITS "N/A"
                    MAX-ACCESS read-write
                    STATUS current
                    DESCRIPTION "Unit Serial Number Digit 1"
                    DEFVAL { 0 }
                    ::= { integerObjects 301 }

        -- 1.3.6.1.4.1.9839.2.1.3.302
        serial-number-2 OBJECT-TYPE
                    SYNTAX Integer32 (0..9)
                    UNITS "N/A"
                    MAX-ACCESS read-write
                    STATUS current
                    DESCRIPTION "Unit Serial Number Digit 2"
                    DEFVAL { 0 }
                    ::= { integerObjects 302 }

        -- 1.3.6.1.4.1.9839.2.1.3.303
        serial-number-3 OBJECT-TYPE
                    SYNTAX Integer32 (0..9)
                    UNITS "N/A"
                    MAX-ACCESS read-write
                    STATUS current
                    DESCRIPTION "Unit Serial Number Digit 3"
                    DEFVAL { 0 }
                    ::= { integerObjects 303 }

        -- 1.3.6.1.4.1.9839.2.1.3.304
        serial-number-4 OBJECT-TYPE
                    SYNTAX Integer32 (0..9)
                    UNITS "N/A"
                    MAX-ACCESS read-write
                    STATUS current
                    DESCRIPTION "Unit Serial Number Digit 4"
                    DEFVAL { 0 }
                    ::= { integerObjects 304 }

        -- 1.3.6.1.4.1.9839.2.1.3.305
        serial-number-5 OBJECT-TYPE
                    SYNTAX Integer32 (0..9)
                    UNITS "N/A"
                    MAX-ACCESS read-write
                    STATUS current
                    DESCRIPTION "Unit Serial Number Digit 5"
                    DEFVAL { 0 }
                    ::= { integerObjects 305 }

        -- 1.3.6.1.4.1.9839.2.1.3.306
        serial-number-6 OBJECT-TYPE
                    SYNTAX Integer32 (0..9)
                    UNITS "N/A"
                    MAX-ACCESS read-write
                    STATUS current
                    DESCRIPTION "Unit Serial Number Digit 6"
                    DEFVAL { 0 }
                    ::= { integerObjects 306 }

        -- 1.3.6.1.4.1.9839.2.1.3.307
        serial-number-7 OBJECT-TYPE
                    SYNTAX Integer32 (0..9)
                    UNITS "N/A"
                    MAX-ACCESS read-write
                    STATUS current
                    DESCRIPTION "Unit Serial Number Digit 7"
                    DEFVAL { 0 }
                    ::= { integerObjects 307 }

        -- 1.3.6.1.4.1.9839.2.1.3.308
        commission-date-day OBJECT-TYPE
                    SYNTAX Integer32 (1..31)
                    UNITS "day"
                    MAX-ACCESS read-write
                    STATUS current
                    DESCRIPTION "Unit Commission Date Day"
                    DEFVAL { 1 }
                    ::= { integerObjects 308 }

        -- 1.3.6.1.4.1.9839.2.1.3.309
        commission-date-month OBJECT-TYPE
                    SYNTAX Integer32 (1..12)
                    UNITS "N/A"
                    MAX-ACCESS read-write
                    STATUS current
                    DESCRIPTION "Unit Commission Date Month"
                    DEFVAL { 1 }
                    ::= { integerObjects 309 }

        -- 1.3.6.1.4.1.9839.2.1.3.310
        commission-date-year OBJECT-TYPE
                    SYNTAX Integer32 (5..99)
                    UNITS "N/A"
                    MAX-ACCESS read-write
                    STATUS current
                    DESCRIPTION "Unit Commission Date Year"
                    DEFVAL { 5 }
                    ::= { integerObjects 310 }

        -- 1.3.6.1.4.1.9839.2.1.3.311
        f1-hour-on1 OBJECT-TYPE
                    SYNTAX Integer32 (0..23)
                    UNITS "hour"
                    MAX-ACCESS read-write
                    STATUS current
                    DESCRIPTION "Unit On/Off Time zone F1-1 On Hour"
                    DEFVAL { 0 }
                    ::= { integerObjects 311 }

        -- 1.3.6.1.4.1.9839.2.1.3.312
        f1-min-on1 OBJECT-TYPE
                    SYNTAX Integer32 (0..59)
                    UNITS "min"
                    MAX-ACCESS read-write
                    STATUS current
                    DESCRIPTION "Unit On/Off Time zone F1-1 On Minute"
                    DEFVAL { 0 }
                    ::= { integerObjects 312 }

        -- 1.3.6.1.4.1.9839.2.1.3.313
        f1-hour-off1 OBJECT-TYPE
                    SYNTAX Integer32 (0..23)
                    UNITS "hour"
                    MAX-ACCESS read-write
                    STATUS current
                    DESCRIPTION "Unit On/Off Time zone F1-1 Off Hour"
                    DEFVAL { 0 }
                    ::= { integerObjects 313 }

        -- 1.3.6.1.4.1.9839.2.1.3.314
        f1-min-off1 OBJECT-TYPE
                    SYNTAX Integer32 (0..59)
                    UNITS "min"
                    MAX-ACCESS read-write
                    STATUS current
                    DESCRIPTION "Unit On/Off Time zone F1-1 Off Minute"
                    DEFVAL { 0 }
                    ::= { integerObjects 314 }

        -- 1.3.6.1.4.1.9839.2.1.3.315
        f1-hour-on2 OBJECT-TYPE
                    SYNTAX Integer32 (0..23)
                    UNITS "hour"
                    MAX-ACCESS read-write
                    STATUS current
                    DESCRIPTION "Unit On/Off Time zone F1-2 On Hour"
                    DEFVAL { 0 }
                    ::= { integerObjects 315 }

        -- 1.3.6.1.4.1.9839.2.1.3.316
        f1-min-on2 OBJECT-TYPE
                    SYNTAX Integer32 (0..59)
                    UNITS "min"
                    MAX-ACCESS read-write
                    STATUS current
                    DESCRIPTION "Unit On/Off Time zone F1-2 On Minute"
                    DEFVAL { 0 }
                    ::= { integerObjects 316 }

        -- 1.3.6.1.4.1.9839.2.1.3.317
        f1-hour-off2 OBJECT-TYPE
                    SYNTAX Integer32 (0..23)
                    UNITS "hour"
                    MAX-ACCESS read-write
                    STATUS current
                    DESCRIPTION "Unit On/Off Time zone F1-2 Off Hour"
                    DEFVAL { 0 }
                    ::= { integerObjects 317 }

        -- 1.3.6.1.4.1.9839.2.1.3.318
        f1-min-off2 OBJECT-TYPE
                    SYNTAX Integer32 (0..59)
                    UNITS "min"
                    MAX-ACCESS read-write
                    STATUS current
                    DESCRIPTION "Unit On/Off Time zone F1-2 Off Minute"
                    DEFVAL { 0 }
                    ::= { integerObjects 318 }

        -- 1.3.6.1.4.1.9839.2.1.3.319
        f2-hour-on OBJECT-TYPE
                    SYNTAX Integer32 (0..23)
                    UNITS "hour"
                    MAX-ACCESS read-write
                    STATUS current
                    DESCRIPTION "Unit On/Off Time zone F2 On Hour"
                    DEFVAL { 0 }
                    ::= { integerObjects 319 }

        -- 1.3.6.1.4.1.9839.2.1.3.320
        f2-min-on OBJECT-TYPE
                    SYNTAX Integer32 (0..59)
                    UNITS "min"
                    MAX-ACCESS read-write
                    STATUS current
                    DESCRIPTION "Unit On/Off Time zone F2 On Minute"
                    DEFVAL { 0 }
                    ::= { integerObjects 320 }

        -- 1.3.6.1.4.1.9839.2.1.3.321
        f2-hour-off OBJECT-TYPE
                    SYNTAX Integer32 (0..23)
                    UNITS "hour"
                    MAX-ACCESS read-write
                    STATUS current
                    DESCRIPTION "Unit On/Off Time zone F2 Off Hour"
                    DEFVAL { 0 }
                    ::= { integerObjects 321 }

        -- 1.3.6.1.4.1.9839.2.1.3.322
        f2-min-off OBJECT-TYPE
                    SYNTAX Integer32 (0..59)
                    UNITS "min"
                    MAX-ACCESS read-write
                    STATUS current
                    DESCRIPTION "Unit On/Off Time zone F2 Off Minute"
                    DEFVAL { 0 }
                    ::= { integerObjects 322 }

        -- 1.3.6.1.4.1.9839.2.1.3.323
        monday-type OBJECT-TYPE
                    SYNTAX Integer32 (0..3)
                    UNITS "N/A"
                    MAX-ACCESS read-write
                    STATUS current
                    DESCRIPTION "Monday Time Zone Selection (0=F1, 1=F2, 2=F3 &3=F4)"
                    DEFVAL { 0 }
                    ::= { integerObjects 323 }

        -- 1.3.6.1.4.1.9839.2.1.3.324
        tuesday-type OBJECT-TYPE
                    SYNTAX Integer32 (0..3)
                    UNITS "N/A"
                    MAX-ACCESS read-write
                    STATUS current
                    DESCRIPTION "Tuesday Time Zone Selection (0=F1, 1=F2, 2=F3 &3=F4)"
                    DEFVAL { 0 }
                    ::= { integerObjects 324 }

        -- 1.3.6.1.4.1.9839.2.1.3.325
        wednesday-type OBJECT-TYPE
                    SYNTAX Integer32 (0..3)
                    UNITS "N/A"
                    MAX-ACCESS read-write
                    STATUS current
                    DESCRIPTION "Wednesday Time Zone Selection (0=F1, 1=F2, 2=F3 &3=F4)"
                    DEFVAL { 0 }
                    ::= { integerObjects 325 }

        -- 1.3.6.1.4.1.9839.2.1.3.326
        thursday-type OBJECT-TYPE
                    SYNTAX Integer32 (0..3)
                    UNITS "N/A"
                    MAX-ACCESS read-write
                    STATUS current
                    DESCRIPTION "Thursday Time Zone Selection (0=F1, 1=F2, 2=F3 &3=F4)"
                    DEFVAL { 0 }
                    ::= { integerObjects 326 }

        -- 1.3.6.1.4.1.9839.2.1.3.327
        friday-type OBJECT-TYPE
                    SYNTAX Integer32 (0..3)
                    UNITS "N/A"
                    MAX-ACCESS read-write
                    STATUS current
                    DESCRIPTION "Friday Time Zone Selection (0=F1, 1=F2, 2=F3 &3=F4)"
                    DEFVAL { 0 }
                    ::= { integerObjects 327 }

        -- 1.3.6.1.4.1.9839.2.1.3.328
        saturday-type OBJECT-TYPE
                    SYNTAX Integer32 (0..3)
                    UNITS "N/A"
                    MAX-ACCESS read-write
                    STATUS current
                    DESCRIPTION "Saturday Time Zone Selection (0=F1, 1=F2, 2=F3 &3=F4)"
                    DEFVAL { 0 }
                    ::= { integerObjects 328 }

        -- 1.3.6.1.4.1.9839.2.1.3.329
        sunday-type OBJECT-TYPE
                    SYNTAX Integer32 (0..3)
                    UNITS "N/A"
                    MAX-ACCESS read-write
                    STATUS current
                    DESCRIPTION "Sunday Time Zone Selection (0=F1, 1=F2, 2=F3 &3=F4)"
                    DEFVAL { 0 }
                    ::= { integerObjects 329 }

        -- 1.3.6.1.4.1.9839.2.1.3.330
        temp-hour1 OBJECT-TYPE
                    SYNTAX Integer32 (0..23)
                    UNITS "hour"
                    MAX-ACCESS read-write
                    STATUS current
                    DESCRIPTION "Temperature set point Time zone 1 Hour"
                    DEFVAL { 0 }
                    ::= { integerObjects 330 }

        -- 1.3.6.1.4.1.9839.2.1.3.331
        temp-minute1 OBJECT-TYPE
                    SYNTAX Integer32 (0..59)
                    UNITS "min"
                    MAX-ACCESS read-write
                    STATUS current
                    DESCRIPTION "Temperature set point Time zone 1 Minute"
                    DEFVAL { 0 }
                    ::= { integerObjects 331 }

        -- 1.3.6.1.4.1.9839.2.1.3.332
        temp-hour2 OBJECT-TYPE
                    SYNTAX Integer32 (0..23)
                    UNITS "hour"
                    MAX-ACCESS read-write
                    STATUS current
                    DESCRIPTION "Temperature set point Time zone 2 Hour"
                    DEFVAL { 0 }
                    ::= { integerObjects 332 }

        -- 1.3.6.1.4.1.9839.2.1.3.333
        temp-minute2 OBJECT-TYPE
                    SYNTAX Integer32 (0..59)
                    UNITS "min"
                    MAX-ACCESS read-write
                    STATUS current
                    DESCRIPTION "Temperature set point Time zone 2 Minute"
                    DEFVAL { 0 }
                    ::= { integerObjects 333 }

        -- 1.3.6.1.4.1.9839.2.1.3.334
        temp-hour3 OBJECT-TYPE
                    SYNTAX Integer32 (0..23)
                    UNITS "hour"
                    MAX-ACCESS read-write
                    STATUS current
                    DESCRIPTION "Temperature set point Time zone 3 Hour"
                    DEFVAL { 0 }
                    ::= { integerObjects 334 }

        -- 1.3.6.1.4.1.9839.2.1.3.335
        temp-minute3 OBJECT-TYPE
                    SYNTAX Integer32 (0..59)
                    UNITS "min"
                    MAX-ACCESS read-write
                    STATUS current
                    DESCRIPTION "Temperature set point Time zone 3 Minute"
                    DEFVAL { 0 }
                    ::= { integerObjects 335 }

        -- 1.3.6.1.4.1.9839.2.1.3.336
        temp-hour4 OBJECT-TYPE
                    SYNTAX Integer32 (0..23)
                    UNITS "hour"
                    MAX-ACCESS read-write
                    STATUS current
                    DESCRIPTION "Temperature set point Time zone 4 Hour"
                    DEFVAL { 0 }
                    ::= { integerObjects 336 }

        -- 1.3.6.1.4.1.9839.2.1.3.337
        temp-minute4 OBJECT-TYPE
                    SYNTAX Integer32 (0..59)
                    UNITS "min"
                    MAX-ACCESS read-write
                    STATUS current
                    DESCRIPTION "Temperature set point Time zone 4 Minute"
                    DEFVAL { 0 }
                    ::= { integerObjects 337 }

        -- 1.3.6.1.4.1.9839.2.1.3.338
        hum-hour1 OBJECT-TYPE
                    SYNTAX Integer32 (0..23)
                    UNITS "hour"
                    MAX-ACCESS read-write
                    STATUS current
                    DESCRIPTION "Humidity set point Time zone 1 Hour"
                    DEFVAL { 0 }
                    ::= { integerObjects 338 }

        -- 1.3.6.1.4.1.9839.2.1.3.339
        hum-minute1 OBJECT-TYPE
                    SYNTAX Integer32 (0..59)
                    UNITS "min"
                    MAX-ACCESS read-write
                    STATUS current
                    DESCRIPTION "Humidity set point Time zone 1 Minute"
                    DEFVAL { 0 }
                    ::= { integerObjects 339 }

        -- 1.3.6.1.4.1.9839.2.1.3.340
        hum-hour2 OBJECT-TYPE
                    SYNTAX Integer32 (0..23)
                    UNITS "hour"
                    MAX-ACCESS read-write
                    STATUS current
                    DESCRIPTION "Humidity set point Time zone 2 Hour"
                    DEFVAL { 0 }
                    ::= { integerObjects 340 }

        -- 1.3.6.1.4.1.9839.2.1.3.341
        hum-minute2 OBJECT-TYPE
                    SYNTAX Integer32 (0..59)
                    UNITS "min"
                    MAX-ACCESS read-write
                    STATUS current
                    DESCRIPTION "Humidity set point Time zone 2 Minute"
                    DEFVAL { 0 }
                    ::= { integerObjects 341 }

        -- 1.3.6.1.4.1.9839.2.1.3.342
        hum-hour3 OBJECT-TYPE
                    SYNTAX Integer32 (0..23)
                    UNITS "hour"
                    MAX-ACCESS read-write
                    STATUS current
                    DESCRIPTION "Humidity set point Time zone 3 Hour"
                    DEFVAL { 0 }
                    ::= { integerObjects 342 }

        -- 1.3.6.1.4.1.9839.2.1.3.343
        hum-minute3 OBJECT-TYPE
                    SYNTAX Integer32 (0..59)
                    UNITS "min"
                    MAX-ACCESS read-write
                    STATUS current
                    DESCRIPTION "Humidity set point Time zone 3 Minute"
                    DEFVAL { 0 }
                    ::= { integerObjects 343 }

        -- 1.3.6.1.4.1.9839.2.1.3.344
        hum-hour4 OBJECT-TYPE
                    SYNTAX Integer32 (0..23)
                    UNITS "hour"
                    MAX-ACCESS read-write
                    STATUS current
                    DESCRIPTION "Humidity set point Time zone 4 Hour"
                    DEFVAL { 0 }
                    ::= { integerObjects 344 }

        -- 1.3.6.1.4.1.9839.2.1.3.345
        hum-minute4 OBJECT-TYPE
                    SYNTAX Integer32 (0..59)
                    UNITS "min"
                    MAX-ACCESS read-write
                    STATUS current
                    DESCRIPTION "Humidity set point Time zone 4 Minute"
                    DEFVAL { 0 }
                    ::= { integerObjects 345 }

        -- 1.3.6.1.4.1.9839.2.1.3.346
        dcra-day-start OBJECT-TYPE
                    SYNTAX Integer32 (0..23)
                    UNITS "N/A"
                    MAX-ACCESS read-write
                    STATUS current
                    DESCRIPTION "N/A"
                    DEFVAL { 0 }
                    ::= { integerObjects 346 }

        -- 1.3.6.1.4.1.9839.2.1.3.347
        dcra-night-start OBJECT-TYPE
                    SYNTAX Integer32 (0..23)
                    UNITS "N/A"
                    MAX-ACCESS read-write
                    STATUS current
                    DESCRIPTION "N/A"
                    DEFVAL { 0 }
                    ::= { integerObjects 347 }

        -- 1.3.6.1.4.1.9839.2.1.3.348
        b101-102-type-ain-mask OBJECT-TYPE
                    SYNTAX Integer32 (0..7)
                    UNITS "N/A"
                    MAX-ACCESS read-write
                    STATUS current
                    DESCRIPTION "N/A"
                    DEFVAL { 0 }
                    ::= { integerObjects 348 }

        -- 1.3.6.1.4.1.9839.2.1.3.349
        aps-press-inttime OBJECT-TYPE
                    SYNTAX Integer32 (1..32767)
                    UNITS "sec"
                    MAX-ACCESS read-write
                    STATUS current
                    DESCRIPTION "N/A"
                    ::= { integerObjects 349 }

        -- 1.3.6.1.4.1.9839.2.1.3.350
        fan-s-ef-1 OBJECT-TYPE
                    SYNTAX Integer32 (0..3)
                    UNITS "N/A"
                    MAX-ACCESS read-write
                    STATUS current
                    DESCRIPTION "LECU 1 Fan Speed (0 = AUTO, 1 = Speed 1, 2 = Speed 2, 3 = Speed 3)"
                    DEFVAL { 0 }
                    ::= { integerObjects 350 }

        -- 1.3.6.1.4.1.9839.2.1.3.351
        fan-s-ef-2 OBJECT-TYPE
                    SYNTAX Integer32 (0..3)
                    UNITS "N/A"
                    MAX-ACCESS read-write
                    STATUS current
                    DESCRIPTION "LECU 2 Fan Speed (0 = AUTO, 1 = Speed 1, 2 = Speed 2, 3 = Speed 3)"
                    DEFVAL { 0 }
                    ::= { integerObjects 351 }

        -- 1.3.6.1.4.1.9839.2.1.3.352
        fan-s-ef-3 OBJECT-TYPE
                    SYNTAX Integer32 (0..3)
                    UNITS "N/A"
                    MAX-ACCESS read-write
                    STATUS current
                    DESCRIPTION "LECU 3 Fan Speed (0 = AUTO, 1 = Speed 1, 2 = Speed 2, 3 = Speed 3)"
                    DEFVAL { 0 }
                    ::= { integerObjects 352 }

        -- 1.3.6.1.4.1.9839.2.1.3.353
        fan-s-ef-4 OBJECT-TYPE
                    SYNTAX Integer32 (0..3)
                    UNITS "N/A"
                    MAX-ACCESS read-write
                    STATUS current
                    DESCRIPTION "LECU 4 Fan Speed (0 = AUTO, 1 = Speed 1, 2 = Speed 2, 3 = Speed 3)"
                    DEFVAL { 0 }
                    ::= { integerObjects 353 }

        -- 1.3.6.1.4.1.9839.2.1.3.354
        fan-s-ef-5 OBJECT-TYPE
                    SYNTAX Integer32 (0..3)
                    UNITS "N/A"
                    MAX-ACCESS read-write
                    STATUS current
                    DESCRIPTION "LECU 5 Fan Speed (0 = AUTO, 1 = Speed 1, 2 = Speed 2, 3 = Speed 3)"
                    DEFVAL { 0 }
                    ::= { integerObjects 354 }

        -- 1.3.6.1.4.1.9839.2.1.3.355
        fan-s-ef-6 OBJECT-TYPE
                    SYNTAX Integer32 (0..3)
                    UNITS "N/A"
                    MAX-ACCESS read-write
                    STATUS current
                    DESCRIPTION "LECU 6 Fan Speed (0 = AUTO, 1 = Speed 1, 2 = Speed 2, 3 = Speed 3)"
                    DEFVAL { 0 }
                    ::= { integerObjects 355 }

        -- 1.3.6.1.4.1.9839.2.1.3.356
        fan-s-ef-7 OBJECT-TYPE
                    SYNTAX Integer32 (0..3)
                    UNITS "N/A"
                    MAX-ACCESS read-write
                    STATUS current
                    DESCRIPTION "LECU 7 Fan Speed (0 = AUTO, 1 = Speed 1, 2 = Speed 2, 3 = Speed 3)"
                    DEFVAL { 0 }
                    ::= { integerObjects 356 }

        -- 1.3.6.1.4.1.9839.2.1.3.357
        fan-s-ef-8 OBJECT-TYPE
                    SYNTAX Integer32 (0..3)
                    UNITS "N/A"
                    MAX-ACCESS read-write
                    STATUS current
                    DESCRIPTION "LECU 8 Fan Speed (0 = AUTO, 1 = Speed 1, 2 = Speed 2, 3 = Speed 3)"
                    DEFVAL { 0 }
                    ::= { integerObjects 357 }

        -- 1.3.6.1.4.1.9839.2.1.3.358
        fan-s-ef-9 OBJECT-TYPE
                    SYNTAX Integer32 (0..3)
                    UNITS "N/A"
                    MAX-ACCESS read-write
                    STATUS current
                    DESCRIPTION "LECU 9 Fan Speed (0 = AUTO, 1 = Speed 1, 2 = Speed 2, 3 = Speed 3)"
                    DEFVAL { 0 }
                    ::= { integerObjects 358 }

        -- 1.3.6.1.4.1.9839.2.1.3.359
        fan-s-ef-10 OBJECT-TYPE
                    SYNTAX Integer32 (0..3)
                    UNITS "N/A"
                    MAX-ACCESS read-write
                    STATUS current
                    DESCRIPTION "LECU 10 Fan Speed (0 = AUTO, 1 = Speed 1, 2 = Speed 2, 3 = Speed 3)"
                    DEFVAL { 0 }
                    ::= { integerObjects 359 }

        -- 1.3.6.1.4.1.9839.2.1.3.360
        fan-s-ef-11 OBJECT-TYPE
                    SYNTAX Integer32 (0..3)
                    UNITS "N/A"
                    MAX-ACCESS read-write
                    STATUS current
                    DESCRIPTION "LECU 11 Fan Speed (0 = AUTO, 1 = Speed 1, 2 = Speed 2, 3 = Speed 3)"
                    DEFVAL { 0 }
                    ::= { integerObjects 360 }

        -- 1.3.6.1.4.1.9839.2.1.3.361
        fan-s-ef-12 OBJECT-TYPE
                    SYNTAX Integer32 (0..3)
                    UNITS "N/A"
                    MAX-ACCESS read-write
                    STATUS current
                    DESCRIPTION "LECU 12 Fan Speed (0 = AUTO, 1 = Speed 1, 2 = Speed 2, 3 = Speed 3)"
                    DEFVAL { 0 }
                    ::= { integerObjects 361 }

        -- 1.3.6.1.4.1.9839.2.1.3.362
        fan-s-ef-13 OBJECT-TYPE
                    SYNTAX Integer32 (0..3)
                    UNITS "N/A"
                    MAX-ACCESS read-write
                    STATUS current
                    DESCRIPTION "LECU 13 Fan Speed (0 = AUTO, 1 = Speed 1, 2 = Speed 2, 3 = Speed 3)"
                    DEFVAL { 0 }
                    ::= { integerObjects 362 }

        -- 1.3.6.1.4.1.9839.2.1.3.363
        fan-s-ef-14 OBJECT-TYPE
                    SYNTAX Integer32 (0..3)
                    UNITS "N/A"
                    MAX-ACCESS read-write
                    STATUS current
                    DESCRIPTION "LECU 14 Fan Speed (0 = AUTO, 1 = Speed 1, 2 = Speed 2, 3 = Speed 3)"
                    DEFVAL { 0 }
                    ::= { integerObjects 363 }

        -- 1.3.6.1.4.1.9839.2.1.3.364
        fan-s-ef-15 OBJECT-TYPE
                    SYNTAX Integer32 (0..3)
                    UNITS "N/A"
                    MAX-ACCESS read-write
                    STATUS current
                    DESCRIPTION "LECU 15 Fan Speed (0 = AUTO, 1 = Speed 1, 2 = Speed 2, 3 = Speed 3)"
                    DEFVAL { 0 }
                    ::= { integerObjects 364 }

        -- 1.3.6.1.4.1.9839.2.1.3.365
        fan-s-ef-16 OBJECT-TYPE
                    SYNTAX Integer32 (0..3)
                    UNITS "N/A"
                    MAX-ACCESS read-write
                    STATUS current
                    DESCRIPTION "LECU 16 Fan Speed (0 = AUTO, 1 = Speed 1, 2 = Speed 2, 3 = Speed 3)"
                    DEFVAL { 0 }
                    ::= { integerObjects 365 }

        -- 1.3.6.1.4.1.9839.2.1.3.366
        fan-s-ef-17 OBJECT-TYPE
                    SYNTAX Integer32 (0..3)
                    UNITS "N/A"
                    MAX-ACCESS read-write
                    STATUS current
                    DESCRIPTION "LECU 17 Fan Speed (0 = AUTO, 1 = Speed 1, 2 = Speed 2, 3 = Speed 3)"
                    DEFVAL { 0 }
                    ::= { integerObjects 366 }

        -- 1.3.6.1.4.1.9839.2.1.3.367
        fan-s-ef-18 OBJECT-TYPE
                    SYNTAX Integer32 (0..3)
                    UNITS "N/A"
                    MAX-ACCESS read-write
                    STATUS current
                    DESCRIPTION "LECU 18 Fan Speed (0 = AUTO, 1 = Speed 1, 2 = Speed 2, 3 = Speed 3)"
                    DEFVAL { 0 }
                    ::= { integerObjects 367 }

        -- 1.3.6.1.4.1.9839.2.1.3.368
        fan-s-ef-19 OBJECT-TYPE
                    SYNTAX Integer32 (0..3)
                    UNITS "N/A"
                    MAX-ACCESS read-write
                    STATUS current
                    DESCRIPTION "LECU 19 Fan Speed (0 = AUTO, 1 = Speed 1, 2 = Speed 2, 3 = Speed 3)"
                    DEFVAL { 0 }
                    ::= { integerObjects 368 }

        -- 1.3.6.1.4.1.9839.2.1.3.369
        fan-s-ef-20 OBJECT-TYPE
                    SYNTAX Integer32 (0..3)
                    UNITS "N/A"
                    MAX-ACCESS read-write
                    STATUS current
                    DESCRIPTION "LECU 20 Fan Speed (0 = AUTO, 1 = Speed 1, 2 = Speed 2, 3 = Speed 3)"
                    DEFVAL { 0 }
                    ::= { integerObjects 369 }

        -- 1.3.6.1.4.1.9839.2.1.3.370
        fan-s-ef-21 OBJECT-TYPE
                    SYNTAX Integer32 (0..3)
                    UNITS "N/A"
                    MAX-ACCESS read-write
                    STATUS current
                    DESCRIPTION "LECU 21 Fan Speed (0 = AUTO, 1 = Speed 1, 2 = Speed 2, 3 = Speed 3)"
                    DEFVAL { 0 }
                    ::= { integerObjects 370 }

        -- 1.3.6.1.4.1.9839.2.1.3.371
        fan-s-ef-22 OBJECT-TYPE
                    SYNTAX Integer32 (0..3)
                    UNITS "N/A"
                    MAX-ACCESS read-write
                    STATUS current
                    DESCRIPTION "LECU 22 Fan Speed (0 = AUTO, 1 = Speed 1, 2 = Speed 2, 3 = Speed 3)"
                    DEFVAL { 0 }
                    ::= { integerObjects 371 }

        -- 1.3.6.1.4.1.9839.2.1.3.372
        fan-s-ef-23 OBJECT-TYPE
                    SYNTAX Integer32 (0..3)
                    UNITS "N/A"
                    MAX-ACCESS read-write
                    STATUS current
                    DESCRIPTION "LECU 23 Fan Speed (0 = AUTO, 1 = Speed 1, 2 = Speed 2, 3 = Speed 3)"
                    DEFVAL { 0 }
                    ::= { integerObjects 372 }

        -- 1.3.6.1.4.1.9839.2.1.3.373
        fan-s-ef-24 OBJECT-TYPE
                    SYNTAX Integer32 (0..3)
                    UNITS "N/A"
                    MAX-ACCESS read-write
                    STATUS current
                    DESCRIPTION "LECU 24 Fan Speed (0 = AUTO, 1 = Speed 1, 2 = Speed 2, 3 = Speed 3)"
                    DEFVAL { 0 }
                    ::= { integerObjects 373 }

        -- 1.3.6.1.4.1.9839.2.1.3.374
        fan-s-ef-25 OBJECT-TYPE
                    SYNTAX Integer32 (0..3)
                    UNITS "N/A"
                    MAX-ACCESS read-write
                    STATUS current
                    DESCRIPTION "LECU 25 Fan Speed (0 = AUTO, 1 = Speed 1, 2 = Speed 2, 3 = Speed 3)"
                    DEFVAL { 0 }
                    ::= { integerObjects 374 }

        -- 1.3.6.1.4.1.9839.2.1.3.375
        fan-s-ef-26 OBJECT-TYPE
                    SYNTAX Integer32 (0..3)
                    UNITS "N/A"
                    MAX-ACCESS read-write
                    STATUS current
                    DESCRIPTION "LECU 26 Fan Speed (0 = AUTO, 1 = Speed 1, 2 = Speed 2, 3 = Speed 3)"
                    DEFVAL { 0 }
                    ::= { integerObjects 375 }

        -- 1.3.6.1.4.1.9839.2.1.3.376
        fan-s-ef-27 OBJECT-TYPE
                    SYNTAX Integer32 (0..3)
                    UNITS "N/A"
                    MAX-ACCESS read-write
                    STATUS current
                    DESCRIPTION "LECU 27 Fan Speed (0 = AUTO, 1 = Speed 1, 2 = Speed 2, 3 = Speed 3)"
                    DEFVAL { 0 }
                    ::= { integerObjects 376 }

        -- 1.3.6.1.4.1.9839.2.1.3.377
        fan-s-ef-28 OBJECT-TYPE
                    SYNTAX Integer32 (0..3)
                    UNITS "N/A"
                    MAX-ACCESS read-write
                    STATUS current
                    DESCRIPTION "LECU 28 Fan Speed (0 = AUTO, 1 = Speed 1, 2 = Speed 2, 3 = Speed 3)"
                    DEFVAL { 0 }
                    ::= { integerObjects 377 }

        -- 1.3.6.1.4.1.9839.2.1.3.378
        fan-s-ef-29 OBJECT-TYPE
                    SYNTAX Integer32 (0..3)
                    UNITS "N/A"
                    MAX-ACCESS read-write
                    STATUS current
                    DESCRIPTION "LECU 29 Fan Speed (0 = AUTO, 1 = Speed 1, 2 = Speed 2, 3 = Speed 3)"
                    DEFVAL { 0 }
                    ::= { integerObjects 378 }

        -- 1.3.6.1.4.1.9839.2.1.3.379
        fan-s-ef-30 OBJECT-TYPE
                    SYNTAX Integer32 (0..3)
                    UNITS "N/A"
                    MAX-ACCESS read-write
                    STATUS current
                    DESCRIPTION "LECU 30 Fan Speed (0 = AUTO, 1 = Speed 1, 2 = Speed 2, 3 = Speed 3)"
                    DEFVAL { 0 }
                    ::= { integerObjects 379 }

        -- 1.3.6.1.4.1.9839.2.1.3.380
        fan-s-ef-31 OBJECT-TYPE
                    SYNTAX Integer32 (0..3)
                    UNITS "N/A"
                    MAX-ACCESS read-write
                    STATUS current
                    DESCRIPTION "LECU 31 Fan Speed (0 = AUTO, 1 = Speed 1, 2 = Speed 2, 3 = Speed 3)"
                    DEFVAL { 0 }
                    ::= { integerObjects 380 }

        -- 1.3.6.1.4.1.9839.2.1.3.381
        fan-s-ef-32 OBJECT-TYPE
                    SYNTAX Integer32 (0..3)
                    UNITS "N/A"
                    MAX-ACCESS read-write
                    STATUS current
                    DESCRIPTION "LECU 32 Fan Speed (0 = AUTO, 1 = Speed 1, 2 = Speed 2, 3 = Speed 3)"
                    DEFVAL { 0 }
                    ::= { integerObjects 381 }

        -- 1.3.6.1.4.1.9839.2.1.3.382
        fan-s-ef-33 OBJECT-TYPE
                    SYNTAX Integer32 (0..3)
                    UNITS "N/A"
                    MAX-ACCESS read-write
                    STATUS current
                    DESCRIPTION "LECU 33 Fan Speed (0 = AUTO, 1 = Speed 1, 2 = Speed 2, 3 = Speed 3)"
                    DEFVAL { 0 }
                    ::= { integerObjects 382 }

        -- 1.3.6.1.4.1.9839.2.1.3.383
        fan-s-ef-34 OBJECT-TYPE
                    SYNTAX Integer32 (0..3)
                    UNITS "N/A"
                    MAX-ACCESS read-write
                    STATUS current
                    DESCRIPTION "LECU 34 Fan Speed (0 = AUTO, 1 = Speed 1, 2 = Speed 2, 3 = Speed 3)"
                    DEFVAL { 0 }
                    ::= { integerObjects 383 }

        -- 1.3.6.1.4.1.9839.2.1.3.384
        fan-s-ef-35 OBJECT-TYPE
                    SYNTAX Integer32 (0..3)
                    UNITS "N/A"
                    MAX-ACCESS read-write
                    STATUS current
                    DESCRIPTION "LECU 35 Fan Speed (0 = AUTO, 1 = Speed 1, 2 = Speed 2, 3 = Speed 3)"
                    DEFVAL { 0 }
                    ::= { integerObjects 384 }

        -- 1.3.6.1.4.1.9839.2.1.3.385
        lecu-number OBJECT-TYPE
                    SYNTAX Integer32 (0..35)
                    UNITS "N/A"
                    MAX-ACCESS read-write
                    STATUS current
                    DESCRIPTION "Number of LECU's"
                    DEFVAL { 0 }
                    ::= { integerObjects 385 }

        -- 1.3.6.1.4.1.9839.2.1.3.386
        lecu-fan-speed OBJECT-TYPE
                    SYNTAX Integer32 (0..3)
                    UNITS "N/A"
                    MAX-ACCESS read-write
                    STATUS current
                    DESCRIPTION "LECU Default Fan Speed (After Restart)"
                    DEFVAL { 2 }
                    ::= { integerObjects 386 }

        -- 1.3.6.1.4.1.9839.2.1.3.387
        compressor-1-power OBJECT-TYPE
                    SYNTAX Integer32 (0..100)
                    UNITS "%"
                    MAX-ACCESS read-write
                    STATUS current
                    DESCRIPTION "N/A"
                    DEFVAL { 0 }
                    ::= { integerObjects 387 }

        -- 1.3.6.1.4.1.9839.2.1.3.388
        compressor-2-power OBJECT-TYPE
                    SYNTAX Integer32 (0..100)
                    UNITS "%"
                    MAX-ACCESS read-write
                    STATUS current
                    DESCRIPTION "N/A"
                    DEFVAL { 0 }
                    ::= { integerObjects 388 }

        -- 1.3.6.1.4.1.9839.2.1.3.390
        b08-sah-or-airflow-enable OBJECT-TYPE
                    SYNTAX Integer32 (0..2)
                    UNITS "N/A"
                    MAX-ACCESS read-write
                    STATUS current
                    DESCRIPTION "N/A"
                    DEFVAL { 0 }
                    ::= { integerObjects 390 }

        -- 1.3.6.1.4.1.9839.2.1.3.391
        discharge-temp-p2t OBJECT-TYPE
                    SYNTAX Integer32 (-32768..32767)
                    UNITS "bar"
                    MAX-ACCESS read-only
                    STATUS current
                    DESCRIPTION "N/A"
                    DEFVAL { 0 }
                    ::= { integerObjects 391 }

        -- 1.3.6.1.4.1.9839.2.1.3.392
        dev-1-avail OBJECT-TYPE
                    SYNTAX Integer32 (-32768..32767)
                    UNITS "N/A"
                    MAX-ACCESS read-only
                    STATUS current
                    DESCRIPTION "N/A"
                    DEFVAL { 0 }
                    ::= { integerObjects 392 }

        -- 1.3.6.1.4.1.9839.2.1.3.393
        dev-2-avail OBJECT-TYPE
                    SYNTAX Integer32 (-32768..32767)
                    UNITS "N/A"
                    MAX-ACCESS read-only
                    STATUS current
                    DESCRIPTION "N/A"
                    DEFVAL { 0 }
                    ::= { integerObjects 393 }

        -- 1.3.6.1.4.1.9839.2.1.3.394
        act-heat-demand OBJECT-TYPE
                    SYNTAX Integer32 (0..32767)
                    UNITS "N/A"
                    MAX-ACCESS read-write
                    STATUS current
                    DESCRIPTION "N/A"
                    DEFVAL { 0 }
                    ::= { integerObjects 394 }

        -- 1.3.6.1.4.1.9839.2.1.3.395
        hum-demand OBJECT-TYPE
                    SYNTAX Integer32 (0..32767)
                    UNITS "N/A"
                    MAX-ACCESS read-write
                    STATUS current
                    DESCRIPTION "N/A"
                    DEFVAL { 0 }
                    ::= { integerObjects 395 }

        -- 1.3.6.1.4.1.9839.2.1.3.396
        dehum-demand OBJECT-TYPE
                    SYNTAX Integer32 (0..32767)
                    UNITS "N/A"
                    MAX-ACCESS read-write
                    STATUS current
                    DESCRIPTION "N/A"
                    DEFVAL { 0 }
                    ::= { integerObjects 396 }

        -- 1.3.6.1.4.1.9839.2.1.3.397
        cool-demand OBJECT-TYPE
                    SYNTAX Integer32 (0..32767)
                    UNITS "N/A"
                    MAX-ACCESS read-write
                    STATUS current
                    DESCRIPTION "N/A"
                    DEFVAL { 0 }
                    ::= { integerObjects 397 }

        -- 1.3.6.1.4.1.9839.2.1.3.398
        serial-number-8 OBJECT-TYPE
                    SYNTAX Integer32 (0..9)
                    UNITS "N/A"
                    MAX-ACCESS read-write
                    STATUS current
                    DESCRIPTION "Unit Serial Number Digit 8"
                    DEFVAL { 0 }
                    ::= { integerObjects 398 }

        -- 1.3.6.1.4.1.9839.2.1.3.399
        i-status-cmd-result OBJECT-TYPE
                    SYNTAX Integer32 (0..32767)
                    UNITS "N/A"
                    MAX-ACCESS read-write
                    STATUS current
                    DESCRIPTION "N/A"
                    DEFVAL { 0 }
                    ::= { integerObjects 399 }

        -- 1.3.6.1.4.1.9839.2.1.3.400
        cooling-type OBJECT-TYPE
                    SYNTAX Integer32 (0..10)
                    UNITS "N/A"
                    MAX-ACCESS read-write
                    STATUS current
                    DESCRIPTION "0="A"; 1="W"; 2="X"; 3="F (Ambicool)"; 4="D (Combicool)"; 5="C"; 6="XR"; 7="DA"; 8="DX"; 9="DC"; 10="DW""
                    DEFVAL { 0 }
                    ::= { integerObjects 400 }

        -- 1.3.6.1.4.1.9839.2.1.3.401
        serial-number-9 OBJECT-TYPE
                    SYNTAX Integer32 (0..9)
                    UNITS "N/A"
                    MAX-ACCESS read-write
                    STATUS current
                    DESCRIPTION "Unit Serial Number Digit 9"
                    DEFVAL { 0 }
                    ::= { integerObjects 401 }

        -- 1.3.6.1.4.1.9839.2.1.3.402
        model-number OBJECT-TYPE
                    SYNTAX Integer32 (0..39)
                    UNITS "N/A"
                    MAX-ACCESS read-write
                    STATUS current
                    DESCRIPTION "N/A"
                    DEFVAL { 0 }
                    ::= { integerObjects 402 }

        -- 1.3.6.1.4.1.9839.2.1.3.403
        serial-number-10 OBJECT-TYPE
                    SYNTAX Integer32 (0..9)
                    UNITS "N/A"
                    MAX-ACCESS read-write
                    STATUS current
                    DESCRIPTION "Unit Serial Number Digit 10"
                    DEFVAL { 0 }
                    ::= { integerObjects 403 }

        -- 1.3.6.1.4.1.9839.2.1.3.404
        airflow-fail-alarm-delay OBJECT-TYPE
                    SYNTAX Integer32 (0..600)
                    UNITS "sec"
                    MAX-ACCESS read-write
                    STATUS current
                    DESCRIPTION "N/A"
                    DEFVAL { 0 }
                    ::= { integerObjects 404 }

        -- 1.3.6.1.4.1.9839.2.1.3.405
        min-time-on-off-h1 OBJECT-TYPE
                    SYNTAX Integer32 (0..32000)
                    UNITS "sec"
                    MAX-ACCESS read-write
                    STATUS current
                    DESCRIPTION "N/A"
                    DEFVAL { 0 }
                    ::= { integerObjects 405 }

        -- 1.3.6.1.4.1.9839.2.1.3.406
        min-time-on-on-same-h1 OBJECT-TYPE
                    SYNTAX Integer32 (0..32000)
                    UNITS "sec"
                    MAX-ACCESS read-write
                    STATUS current
                    DESCRIPTION "N/A"
                    DEFVAL { 0 }
                    ::= { integerObjects 406 }

        -- 1.3.6.1.4.1.9839.2.1.3.407
        min-time-off-on-h1 OBJECT-TYPE
                    SYNTAX Integer32 (0..32767)
                    UNITS "sec"
                    MAX-ACCESS read-write
                    STATUS current
                    DESCRIPTION "N/A"
                    DEFVAL { 0 }
                    ::= { integerObjects 407 }

        -- 1.3.6.1.4.1.9839.2.1.3.408
        min-time-on-on-diff-h1 OBJECT-TYPE
                    SYNTAX Integer32 (0..32000)
                    UNITS "sec"
                    MAX-ACCESS read-write
                    STATUS current
                    DESCRIPTION "N/A"
                    DEFVAL { 0 }
                    ::= { integerObjects 408 }

        -- 1.3.6.1.4.1.9839.2.1.3.409
        min-time-on-off-h2 OBJECT-TYPE
                    SYNTAX Integer32 (0..32000)
                    UNITS "sec"
                    MAX-ACCESS read-write
                    STATUS current
                    DESCRIPTION "N/A"
                    DEFVAL { 0 }
                    ::= { integerObjects 409 }

        -- 1.3.6.1.4.1.9839.2.1.3.410
        min-time-on-on-same-h2 OBJECT-TYPE
                    SYNTAX Integer32 (0..32000)
                    UNITS "sec"
                    MAX-ACCESS read-write
                    STATUS current
                    DESCRIPTION "N/A"
                    DEFVAL { 0 }
                    ::= { integerObjects 410 }

        -- 1.3.6.1.4.1.9839.2.1.3.411
        min-time-off-on-h2 OBJECT-TYPE
                    SYNTAX Integer32 (0..32767)
                    UNITS "sec"
                    MAX-ACCESS read-write
                    STATUS current
                    DESCRIPTION "N/A"
                    DEFVAL { 0 }
                    ::= { integerObjects 411 }

        -- 1.3.6.1.4.1.9839.2.1.3.412
        min-time-on-on-diff-h2 OBJECT-TYPE
                    SYNTAX Integer32 (0..32000)
                    UNITS "sec"
                    MAX-ACCESS read-write
                    STATUS current
                    DESCRIPTION "N/A"
                    DEFVAL { 0 }
                    ::= { integerObjects 412 }

        -- 1.3.6.1.4.1.9839.2.1.3.413
        min-time-on-off-rem-hum OBJECT-TYPE
                    SYNTAX Integer32 (0..32000)
                    UNITS "sec"
                    MAX-ACCESS read-write
                    STATUS current
                    DESCRIPTION "N/A"
                    DEFVAL { 0 }
                    ::= { integerObjects 413 }

        -- 1.3.6.1.4.1.9839.2.1.3.414
        min-time-on-on-same-rem-hum OBJECT-TYPE
                    SYNTAX Integer32 (0..32000)
                    UNITS "sec"
                    MAX-ACCESS read-write
                    STATUS current
                    DESCRIPTION "N/A"
                    DEFVAL { 0 }
                    ::= { integerObjects 414 }

        -- 1.3.6.1.4.1.9839.2.1.3.415
        min-time-off-on-rem-hum OBJECT-TYPE
                    SYNTAX Integer32 (0..32767)
                    UNITS "sec"
                    MAX-ACCESS read-write
                    STATUS current
                    DESCRIPTION "N/A"
                    DEFVAL { 0 }
                    ::= { integerObjects 415 }

        -- 1.3.6.1.4.1.9839.2.1.3.416
        min-time-on-on-diff-rem-hum OBJECT-TYPE
                    SYNTAX Integer32 (0..32000)
                    UNITS "sec"
                    MAX-ACCESS read-write
                    STATUS current
                    DESCRIPTION "N/A"
                    DEFVAL { 0 }
                    ::= { integerObjects 416 }

        -- 1.3.6.1.4.1.9839.2.1.3.417
        hand-mode-output-voltage OBJECT-TYPE
                    SYNTAX Integer32 (0..1000)
                    UNITS "N/A"
                    MAX-ACCESS read-write
                    STATUS current
                    DESCRIPTION "Value of hand mode voltage"
                    DEFVAL { 0 }
                    ::= { integerObjects 417 }

        -- 1.3.6.1.4.1.9839.2.1.3.418
        fb1-baudrate OBJECT-TYPE
                    SYNTAX Integer32 (0..5)
                    UNITS "N/A"
                    MAX-ACCESS read-write
                    STATUS current
                    DESCRIPTION "0 = 1200, 1 = 2400, 2 = 4800, 3 = 9600, 4 = 19200, 5 = 38400"
                    DEFVAL { 0 }
                    ::= { integerObjects 418 }

        -- 1.3.6.1.4.1.9839.2.1.3.419
        fb1-address OBJECT-TYPE
                    SYNTAX Integer32 (0..207)
                    UNITS "N/A"
                    MAX-ACCESS read-write
                    STATUS current
                    DESCRIPTION "N/A"
                    DEFVAL { 0 }
                    ::= { integerObjects 419 }

        -- 1.3.6.1.4.1.9839.2.1.3.420
        bms-fan-speed OBJECT-TYPE
                    SYNTAX Integer32 (0..1000)
                    UNITS "N/A"
                    MAX-ACCESS read-write
                    STATUS current
                    DESCRIPTION "N/A"
                    DEFVAL { 0 }
                    ::= { integerObjects 420 }

        -- 1.3.6.1.4.1.9839.2.1.3.421
        ddra-fan-output OBJECT-TYPE
                    SYNTAX Integer32 (0..1000)
                    UNITS "N/A"
                    MAX-ACCESS read-write
                    STATUS current
                    DESCRIPTION "Value to return if Sel=1"
                    DEFVAL { 0 }
                    ::= { integerObjects 421 }

        -- 1.3.6.1.4.1.9839.2.1.3.422
        bms-offline-al-delay OBJECT-TYPE
                    SYNTAX Integer32 (1..32000)
                    UNITS "sec"
                    MAX-ACCESS read-write
                    STATUS current
                    DESCRIPTION "N/A"
                    DEFVAL { 1 }
                    ::= { integerObjects 422 }

        -- 1.3.6.1.4.1.9839.2.1.3.423
        fan-speed-ctrl-type OBJECT-TYPE
                    SYNTAX Integer32 (0..3)
                    UNITS "N/A"
                    MAX-ACCESS read-write
                    STATUS current
                    DESCRIPTION "N/A"
                    DEFVAL { 0 }
                    ::= { integerObjects 423 }

        -- 1.3.6.1.4.1.9839.2.1.3.424
        std-cool-demand OBJECT-TYPE
                    SYNTAX Integer32 (0..32767)
                    UNITS "N/A"
                    MAX-ACCESS read-write
                    STATUS current
                    DESCRIPTION "N/A"
                    DEFVAL { 0 }
                    ::= { integerObjects 424 }

        -- 1.3.6.1.4.1.9839.2.1.3.425
        bms-baudrate OBJECT-TYPE
                    SYNTAX Integer32 (0..4)
                    UNITS "N/A"
                    MAX-ACCESS read-write
                    STATUS current
                    DESCRIPTION "N/A"
                    DEFVAL { 0 }
                    ::= { integerObjects 425 }

        -- 1.3.6.1.4.1.9839.2.1.3.426
        bms-protocol-type OBJECT-TYPE
                    SYNTAX Integer32 (0..4)
                    UNITS "N/A"
                    MAX-ACCESS read-write
                    STATUS current
                    DESCRIPTION "N/A"
                    DEFVAL { 0 }
                    ::= { integerObjects 426 }

        -- 1.3.6.1.4.1.9839.2.1.3.427
        high-part-bios OBJECT-TYPE
                    SYNTAX Integer32 (0..32767)
                    UNITS "N/A"
                    MAX-ACCESS read-write
                    STATUS current
                    DESCRIPTION "N/A"
                    DEFVAL { 0 }
                    ::= { integerObjects 427 }

        -- 1.3.6.1.4.1.9839.2.1.3.428
        low-part-bios OBJECT-TYPE
                    SYNTAX Integer32 (0..32767)
                    UNITS "N/A"
                    MAX-ACCESS read-write
                    STATUS current
                    DESCRIPTION "N/A"
                    DEFVAL { 0 }
                    ::= { integerObjects 428 }

        -- 1.3.6.1.4.1.9839.2.1.3.429
        bios-day OBJECT-TYPE
                    SYNTAX Integer32 (0..32767)
                    UNITS "N/A"
                    MAX-ACCESS read-write
                    STATUS current
                    DESCRIPTION "N/A"
                    DEFVAL { 0 }
                    ::= { integerObjects 429 }

        -- 1.3.6.1.4.1.9839.2.1.3.430
        bios-month OBJECT-TYPE
                    SYNTAX Integer32 (0..32767)
                    UNITS "N/A"
                    MAX-ACCESS read-write
                    STATUS current
                    DESCRIPTION "N/A"
                    DEFVAL { 0 }
                    ::= { integerObjects 430 }

        -- 1.3.6.1.4.1.9839.2.1.3.431
        bios-year OBJECT-TYPE
                    SYNTAX Integer32 (0..32767)
                    UNITS "N/A"
                    MAX-ACCESS read-write
                    STATUS current
                    DESCRIPTION "N/A"
                    DEFVAL { 0 }
                    ::= { integerObjects 431 }

        -- 1.3.6.1.4.1.9839.2.1.3.432
        high-part-boot OBJECT-TYPE
                    SYNTAX Integer32 (0..32767)
                    UNITS "N/A"
                    MAX-ACCESS read-write
                    STATUS current
                    DESCRIPTION "N/A"
                    DEFVAL { 0 }
                    ::= { integerObjects 432 }

        -- 1.3.6.1.4.1.9839.2.1.3.433
        low-part-boot OBJECT-TYPE
                    SYNTAX Integer32 (0..32767)
                    UNITS "N/A"
                    MAX-ACCESS read-write
                    STATUS current
                    DESCRIPTION "N/A"
                    DEFVAL { 0 }
                    ::= { integerObjects 433 }

        -- 1.3.6.1.4.1.9839.2.1.3.434
        boot-day OBJECT-TYPE
                    SYNTAX Integer32 (0..32767)
                    UNITS "N/A"
                    MAX-ACCESS read-write
                    STATUS current
                    DESCRIPTION "N/A"
                    DEFVAL { 0 }
                    ::= { integerObjects 434 }

        -- 1.3.6.1.4.1.9839.2.1.3.435
        boot-month OBJECT-TYPE
                    SYNTAX Integer32 (0..32767)
                    UNITS "N/A"
                    MAX-ACCESS read-write
                    STATUS current
                    DESCRIPTION "N/A"
                    DEFVAL { 0 }
                    ::= { integerObjects 435 }

        -- 1.3.6.1.4.1.9839.2.1.3.436
        boot-year OBJECT-TYPE
                    SYNTAX Integer32 (0..32767)
                    UNITS "N/A"
                    MAX-ACCESS read-write
                    STATUS current
                    DESCRIPTION "N/A"
                    DEFVAL { 0 }
                    ::= { integerObjects 436 }

        -- 1.3.6.1.4.1.9839.2.1.3.437
        b02-min-value-rat OBJECT-TYPE
                    SYNTAX Integer32 (0..10)
                    UNITS "N/A"
                    MAX-ACCESS read-write
                    STATUS current
                    DESCRIPTION "N/A"
                    DEFVAL { 0 }
                    ::= { integerObjects 437 }

        -- 1.3.6.1.4.1.9839.2.1.3.438
        bms2-protocol-type OBJECT-TYPE
                    SYNTAX Integer32 (0..2)
                    UNITS "N/A"
                    MAX-ACCESS read-write
                    STATUS current
                    DESCRIPTION "N/A"
                    DEFVAL { 0 }
                    ::= { integerObjects 438 }

        -- 1.3.6.1.4.1.9839.2.1.3.439
        bms2-baudrate OBJECT-TYPE
                    SYNTAX Integer32 (0..4)
                    UNITS "N/A"
                    MAX-ACCESS read-write
                    STATUS current
                    DESCRIPTION "N/A"
                    DEFVAL { 0 }
                    ::= { integerObjects 439 }

        -- 1.3.6.1.4.1.9839.2.1.3.440
        denconet-type OBJECT-TYPE
                    SYNTAX Integer32 (0..2)
                    UNITS "N/A"
                    MAX-ACCESS read-write
                    STATUS current
                    DESCRIPTION "0 = SENSOR AVERAGING; 1 = AUTO CHANGE OVER"
                    DEFVAL { 0 }
                    ::= { integerObjects 440 }

        -- 1.3.6.1.4.1.9839.2.1.3.441
        denconet-unit-number OBJECT-TYPE
                    SYNTAX Integer32 (0..8)
                    UNITS "N/A"
                    MAX-ACCESS read-write
                    STATUS current
                    DESCRIPTION "N/A"
                    DEFVAL { 0 }
                    ::= { integerObjects 441 }

        -- 1.3.6.1.4.1.9839.2.1.3.442
        denconet-t OBJECT-TYPE
                    SYNTAX Integer32 (0..3)
                    UNITS "N/A"
                    MAX-ACCESS read-write
                    STATUS current
                    DESCRIPTION "N/A"
                    DEFVAL { 0 }
                    ::= { integerObjects 442 }

        -- 1.3.6.1.4.1.9839.2.1.3.443
        real-dnet-t OBJECT-TYPE
                    SYNTAX Integer32 (0..32767)
                    UNITS "N/A"
                    MAX-ACCESS read-write
                    STATUS current
                    DESCRIPTION "N/A"
                    DEFVAL { 0 }
                    ::= { integerObjects 443 }

        -- 1.3.6.1.4.1.9839.2.1.3.444
        denconet-h OBJECT-TYPE
                    SYNTAX Integer32 (0..3)
                    UNITS "N/A"
                    MAX-ACCESS read-write
                    STATUS current
                    DESCRIPTION "N/A"
                    DEFVAL { 0 }
                    ::= { integerObjects 444 }

        -- 1.3.6.1.4.1.9839.2.1.3.445
        real-dnet-h OBJECT-TYPE
                    SYNTAX Integer32 (0..32767)
                    UNITS "N/A"
                    MAX-ACCESS read-write
                    STATUS current
                    DESCRIPTION "N/A"
                    DEFVAL { 0 }
                    ::= { integerObjects 445 }

        -- 1.3.6.1.4.1.9839.2.1.3.446
        sat-low-al-delay OBJECT-TYPE
                    SYNTAX Integer32 (1..30)
                    UNITS "N/A"
                    MAX-ACCESS read-write
                    STATUS current
                    DESCRIPTION "N/A"
                    DEFVAL { 15 }
                    ::= { integerObjects 446 }

        -- 1.3.6.1.4.1.9839.2.1.3.447
        rotation-time OBJECT-TYPE
                    SYNTAX Integer32 (1..999)
                    UNITS "N/A"
                    MAX-ACCESS read-write
                    STATUS current
                    DESCRIPTION "N/A"
                    DEFVAL { 1 }
                    ::= { integerObjects 447 }

        -- 1.3.6.1.4.1.9839.2.1.3.448
        h-hour-rem-hum OBJECT-TYPE
                    SYNTAX Integer32 (0..32767)
                    UNITS "N/A"
                    MAX-ACCESS read-write
                    STATUS current
                    DESCRIPTION "N/A"
                    DEFVAL { 0 }
                    ::= { integerObjects 448 }

        -- 1.3.6.1.4.1.9839.2.1.3.449
        h-hour-cond OBJECT-TYPE
                    SYNTAX Integer32 (0..32767)
                    UNITS "N/A"
                    MAX-ACCESS read-write
                    STATUS current
                    DESCRIPTION "N/A"
                    DEFVAL { 0 }
                    ::= { integerObjects 449 }

        -- 1.3.6.1.4.1.9839.2.1.3.450
        l-hour-cond OBJECT-TYPE
                    SYNTAX Integer32 (0..32767)
                    UNITS "N/A"
                    MAX-ACCESS read-write
                    STATUS current
                    DESCRIPTION "N/A"
                    DEFVAL { 0 }
                    ::= { integerObjects 450 }

        -- 1.3.6.1.4.1.9839.2.1.3.451
        h-hour-drycool1 OBJECT-TYPE
                    SYNTAX Integer32 (0..32767)
                    UNITS "N/A"
                    MAX-ACCESS read-write
                    STATUS current
                    DESCRIPTION "N/A"
                    DEFVAL { 0 }
                    ::= { integerObjects 451 }

        -- 1.3.6.1.4.1.9839.2.1.3.452
        l-hour-drycool1 OBJECT-TYPE
                    SYNTAX Integer32 (0..32767)
                    UNITS "N/A"
                    MAX-ACCESS read-write
                    STATUS current
                    DESCRIPTION "N/A"
                    DEFVAL { 0 }
                    ::= { integerObjects 452 }

        -- 1.3.6.1.4.1.9839.2.1.3.453
        h-hour-critical OBJECT-TYPE
                    SYNTAX Integer32 (0..32767)
                    UNITS "N/A"
                    MAX-ACCESS read-write
                    STATUS current
                    DESCRIPTION "N/A"
                    DEFVAL { 0 }
                    ::= { integerObjects 453 }

        -- 1.3.6.1.4.1.9839.2.1.3.454
        l-hour-critical OBJECT-TYPE
                    SYNTAX Integer32 (0..32767)
                    UNITS "N/A"
                    MAX-ACCESS read-write
                    STATUS current
                    DESCRIPTION "N/A"
                    DEFVAL { 0 }
                    ::= { integerObjects 454 }

        -- 1.3.6.1.4.1.9839.2.1.3.455
        sah-high-al-delay OBJECT-TYPE
                    SYNTAX Integer32 (1..30)
                    UNITS "N/A"
                    MAX-ACCESS read-write
                    STATUS current
                    DESCRIPTION "N/A"
                    DEFVAL { 15 }
                    ::= { integerObjects 455 }

        -- 1.3.6.1.4.1.9839.2.1.3.456
        h-hour-maint OBJECT-TYPE
                    SYNTAX Integer32 (0..32767)
                    UNITS "N/A"
                    MAX-ACCESS read-write
                    STATUS current
                    DESCRIPTION "N/A"
                    DEFVAL { 0 }
                    ::= { integerObjects 456 }

        -- 1.3.6.1.4.1.9839.2.1.3.457
        l-hour-maint OBJECT-TYPE
                    SYNTAX Integer32 (0..32767)
                    UNITS "N/A"
                    MAX-ACCESS read-write
                    STATUS current
                    DESCRIPTION "N/A"
                    DEFVAL { 0 }
                    ::= { integerObjects 457 }

        -- 1.3.6.1.4.1.9839.2.1.3.458
        time-integr OBJECT-TYPE
                    SYNTAX Integer32 (0..15)
                    UNITS "N/A"
                    MAX-ACCESS read-write
                    STATUS current
                    DESCRIPTION "N/A"
                    DEFVAL { 10 }
                    ::= { integerObjects 458 }

        -- 1.3.6.1.4.1.9839.2.1.3.459
        stage-delay-time OBJECT-TYPE
                    SYNTAX Integer32 (10..90)
                    UNITS "N/A"
                    MAX-ACCESS read-write
                    STATUS current
                    DESCRIPTION "N/A"
                    DEFVAL { 20 }
                    ::= { integerObjects 459 }

        -- 1.3.6.1.4.1.9839.2.1.3.460
        start-delay-time OBJECT-TYPE
                    SYNTAX Integer32 (0..300)
                    UNITS "N/A"
                    MAX-ACCESS read-write
                    STATUS current
                    DESCRIPTION "N/A"
                    DEFVAL { 0 }
                    ::= { integerObjects 460 }

        -- 1.3.6.1.4.1.9839.2.1.3.461
        function-delay-time OBJECT-TYPE
                    SYNTAX Integer32 (10..120)
                    UNITS "N/A"
                    MAX-ACCESS read-write
                    STATUS current
                    DESCRIPTION "N/A"
                    DEFVAL { 10 }
                    ::= { integerObjects 461 }

        -- 1.3.6.1.4.1.9839.2.1.3.462
        average-type OBJECT-TYPE
                    SYNTAX Integer32 (0..2)
                    UNITS "N/A"
                    MAX-ACCESS read-write
                    STATUS current
                    DESCRIPTION "N/A"
                    DEFVAL { 0 }
                    ::= { integerObjects 462 }

        -- 1.3.6.1.4.1.9839.2.1.3.463
        n-comp OBJECT-TYPE
                    SYNTAX Integer32 (1..4)
                    UNITS "N/A"
                    MAX-ACCESS read-write
                    STATUS current
                    DESCRIPTION "N/A"
                    DEFVAL { 2 }
                    ::= { integerObjects 463 }

        -- 1.3.6.1.4.1.9839.2.1.3.464
        dcra-fan-type OBJECT-TYPE
                    SYNTAX Integer32 (0..2)
                    UNITS "N/A"
                    MAX-ACCESS read-write
                    STATUS current
                    DESCRIPTION "N/A"
                    DEFVAL { 0 }
                    ::= { integerObjects 464 }

        -- 1.3.6.1.4.1.9839.2.1.3.465
        cool-dodc-valve-run-t OBJECT-TYPE
                    SYNTAX Integer32 (30..250)
                    UNITS "N/A"
                    MAX-ACCESS read-write
                    STATUS current
                    DESCRIPTION "N/A"
                    DEFVAL { 180 }
                    ::= { integerObjects 465 }

        -- 1.3.6.1.4.1.9839.2.1.3.466
        dry-cool-fan-number OBJECT-TYPE
                    SYNTAX Integer32 (0..2)
                    UNITS "N/A"
                    MAX-ACCESS read-write
                    STATUS current
                    DESCRIPTION "N/A"
                    DEFVAL { 2 }
                    ::= { integerObjects 466 }

        -- 1.3.6.1.4.1.9839.2.1.3.467
        heat-type OBJECT-TYPE
                    SYNTAX Integer32 (0..4)
                    UNITS "N/A"
                    MAX-ACCESS read-write
                    STATUS current
                    DESCRIPTION "N/A"
                    DEFVAL { 0 }
                    ::= { integerObjects 467 }

        -- 1.3.6.1.4.1.9839.2.1.3.468
        n-heaters OBJECT-TYPE
                    SYNTAX Integer32 (1..3)
                    UNITS "N/A"
                    MAX-ACCESS read-write
                    STATUS current
                    DESCRIPTION "N/A"
                    DEFVAL { 2 }
                    ::= { integerObjects 468 }

        -- 1.3.6.1.4.1.9839.2.1.3.469
        heat-dodc-valve-run-t OBJECT-TYPE
                    SYNTAX Integer32 (30..250)
                    UNITS "N/A"
                    MAX-ACCESS read-write
                    STATUS current
                    DESCRIPTION "N/A"
                    DEFVAL { 180 }
                    ::= { integerObjects 469 }

        -- 1.3.6.1.4.1.9839.2.1.3.470
        hum-type OBJECT-TYPE
                    SYNTAX Integer32 (0..3)
                    UNITS "N/A"
                    MAX-ACCESS read-write
                    STATUS current
                    DESCRIPTION "N/A"
                    DEFVAL { 0 }
                    ::= { integerObjects 470 }

        -- 1.3.6.1.4.1.9839.2.1.3.471
        cw-ctrl-type OBJECT-TYPE
                    SYNTAX Integer32 (0..2)
                    UNITS "N/A"
                    MAX-ACCESS read-write
                    STATUS current
                    DESCRIPTION "N/A"
                    DEFVAL { 0 }
                    ::= { integerObjects 471 }

        -- 1.3.6.1.4.1.9839.2.1.3.472
        new-mins-touch OBJECT-TYPE
                    SYNTAX Integer32 (0..59)
                    UNITS "N/A"
                    MAX-ACCESS read-write
                    STATUS current
                    DESCRIPTION "N/A"
                    DEFVAL { 0 }
                    ::= { integerObjects 472 }

        -- 1.3.6.1.4.1.9839.2.1.3.473
        airflow-fail-cw-force OBJECT-TYPE
                    SYNTAX Integer32 (0..2)
                    UNITS "N/A"
                    MAX-ACCESS read-write
                    STATUS current
                    DESCRIPTION "(Force valve on alarm config, 0 = none, 1 = open, 2 = closed"
                    DEFVAL { 0 }
                    ::= { integerObjects 473 }

        -- 1.3.6.1.4.1.9839.2.1.3.474
        new-hour-touch OBJECT-TYPE
                    SYNTAX Integer32 (0..23)
                    UNITS "N/A"
                    MAX-ACCESS read-write
                    STATUS current
                    DESCRIPTION "N/A"
                    DEFVAL { 0 }
                    ::= { integerObjects 474 }

        -- 1.3.6.1.4.1.9839.2.1.3.475
        new-day-touch OBJECT-TYPE
                    SYNTAX Integer32 (1..31)
                    UNITS "N/A"
                    MAX-ACCESS read-write
                    STATUS current
                    DESCRIPTION "N/A"
                    ::= { integerObjects 475 }

        -- 1.3.6.1.4.1.9839.2.1.3.476
        hum-heat-interlock OBJECT-TYPE
                    SYNTAX Integer32 (0..2)
                    UNITS "N/A"
                    MAX-ACCESS read-write
                    STATUS current
                    DESCRIPTION "N/A"
                    DEFVAL { 0 }
                    ::= { integerObjects 476 }

        -- 1.3.6.1.4.1.9839.2.1.3.477
        new-month-touch OBJECT-TYPE
                    SYNTAX Integer32 (1..12)
                    UNITS "N/A"
                    MAX-ACCESS read-write
                    STATUS current
                    DESCRIPTION "N/A"
                    ::= { integerObjects 477 }

        -- 1.3.6.1.4.1.9839.2.1.3.478
        new-year-touch OBJECT-TYPE
                    SYNTAX Integer32 (0..99)
                    UNITS "N/A"
                    MAX-ACCESS read-write
                    STATUS current
                    DESCRIPTION "N/A"
                    DEFVAL { 0 }
                    ::= { integerObjects 478 }

        -- 1.3.6.1.4.1.9839.2.1.3.479
        airflow-k-factor-adj OBJECT-TYPE
                    SYNTAX Integer32 (0..400)
                    UNITS "N/A"
                    MAX-ACCESS read-write
                    STATUS current
                    DESCRIPTION "N/A"
                    DEFVAL { 0 }
                    ::= { integerObjects 479 }

        -- 1.3.6.1.4.1.9839.2.1.3.480
        airflow-fans-number OBJECT-TYPE
                    SYNTAX Integer32 (1..3)
                    UNITS "N/A"
                    MAX-ACCESS read-write
                    STATUS current
                    DESCRIPTION "N/A"
                    DEFVAL { 1 }
                    ::= { integerObjects 480 }

        -- 1.3.6.1.4.1.9839.2.1.3.481
        refrigerant-type OBJECT-TYPE
                    SYNTAX Integer32 (0..19)
                    UNITS "N/A"
                    MAX-ACCESS read-write
                    STATUS current
                    DESCRIPTION "Gas type - 0=R22; 1=R134a; 2=R404A; 3=R407C; 4=R410A; 5=R507A; 6=R290; 7=R600; 8=R600a; 9=R717; 10=R744; 11=R728; 12=R1270; 13=R417A; 14=R422D; 15=R413A; 16=R422A; 17=R423A; 18=R407A; 19=R427A."
                    DEFVAL { 2 }
                    ::= { integerObjects 481 }

        -- 1.3.6.1.4.1.9839.2.1.3.482
        fan-run-on-time OBJECT-TYPE
                    SYNTAX Integer32 (0..999)
                    UNITS "N/A"
                    MAX-ACCESS read-write
                    STATUS current
                    DESCRIPTION "N/A"
                    DEFVAL { 0 }
                    ::= { integerObjects 482 }

        -- 1.3.6.1.4.1.9839.2.1.3.483
        unit1-denconet-type OBJECT-TYPE
                    SYNTAX Integer32 (0..99)
                    UNITS "N/A"
                    MAX-ACCESS read-only
                    STATUS current
                    DESCRIPTION "N/A"
                    DEFVAL { 0 }
                    ::= { integerObjects 483 }

        -- 1.3.6.1.4.1.9839.2.1.3.484
        unit2-denconet-type OBJECT-TYPE
                    SYNTAX Integer32 (0..99)
                    UNITS "N/A"
                    MAX-ACCESS read-only
                    STATUS current
                    DESCRIPTION "N/A"
                    DEFVAL { 0 }
                    ::= { integerObjects 484 }

        -- 1.3.6.1.4.1.9839.2.1.3.485
        unit3-denconet-type OBJECT-TYPE
                    SYNTAX Integer32 (0..99)
                    UNITS "N/A"
                    MAX-ACCESS read-only
                    STATUS current
                    DESCRIPTION "N/A"
                    DEFVAL { 0 }
                    ::= { integerObjects 485 }

        -- 1.3.6.1.4.1.9839.2.1.3.486
        unit4-denconet-type OBJECT-TYPE
                    SYNTAX Integer32 (0..99)
                    UNITS "N/A"
                    MAX-ACCESS read-only
                    STATUS current
                    DESCRIPTION "N/A"
                    DEFVAL { 0 }
                    ::= { integerObjects 486 }

        -- 1.3.6.1.4.1.9839.2.1.3.487
        unit5-denconet-type OBJECT-TYPE
                    SYNTAX Integer32 (0..99)
                    UNITS "N/A"
                    MAX-ACCESS read-only
                    STATUS current
                    DESCRIPTION "N/A"
                    DEFVAL { 0 }
                    ::= { integerObjects 487 }

        -- 1.3.6.1.4.1.9839.2.1.3.488
        unit6-denconet-type OBJECT-TYPE
                    SYNTAX Integer32 (0..99)
                    UNITS "N/A"
                    MAX-ACCESS read-only
                    STATUS current
                    DESCRIPTION "N/A"
                    DEFVAL { 0 }
                    ::= { integerObjects 488 }

        -- 1.3.6.1.4.1.9839.2.1.3.489
        unit7-denconet-type OBJECT-TYPE
                    SYNTAX Integer32 (0..99)
                    UNITS "N/A"
                    MAX-ACCESS read-only
                    STATUS current
                    DESCRIPTION "N/A"
                    DEFVAL { 0 }
                    ::= { integerObjects 489 }

        -- 1.3.6.1.4.1.9839.2.1.3.490
        unit8-denconet-type OBJECT-TYPE
                    SYNTAX Integer32 (0..99)
                    UNITS "N/A"
                    MAX-ACCESS read-only
                    STATUS current
                    DESCRIPTION "N/A"
                    DEFVAL { 0 }
                    ::= { integerObjects 490 }

        -- 1.3.6.1.4.1.9839.2.1.3.491
        denconet-temp OBJECT-TYPE
                    SYNTAX Integer32 (0..3)
                    UNITS "N/A"
                    MAX-ACCESS read-write
                    STATUS current
                    DESCRIPTION "N/A"
                    DEFVAL { 0 }
                    ::= { integerObjects 491 }

        -- 1.3.6.1.4.1.9839.2.1.3.492
        denconet-temp-u1 OBJECT-TYPE
                    SYNTAX Integer32 (0..99)
                    UNITS "N/A"
                    MAX-ACCESS read-only
                    STATUS current
                    DESCRIPTION "N/A"
                    DEFVAL { 0 }
                    ::= { integerObjects 492 }

        -- 1.3.6.1.4.1.9839.2.1.3.493
        denconet-temp-u2 OBJECT-TYPE
                    SYNTAX Integer32 (0..99)
                    UNITS "N/A"
                    MAX-ACCESS read-only
                    STATUS current
                    DESCRIPTION "N/A"
                    DEFVAL { 0 }
                    ::= { integerObjects 493 }

        -- 1.3.6.1.4.1.9839.2.1.3.494
        denconet-temp-u3 OBJECT-TYPE
                    SYNTAX Integer32 (0..99)
                    UNITS "N/A"
                    MAX-ACCESS read-only
                    STATUS current
                    DESCRIPTION "N/A"
                    DEFVAL { 0 }
                    ::= { integerObjects 494 }

        -- 1.3.6.1.4.1.9839.2.1.3.495
        denconet-temp-u4 OBJECT-TYPE
                    SYNTAX Integer32 (0..99)
                    UNITS "N/A"
                    MAX-ACCESS read-only
                    STATUS current
                    DESCRIPTION "N/A"
                    DEFVAL { 0 }
                    ::= { integerObjects 495 }

        -- 1.3.6.1.4.1.9839.2.1.3.496
        denconet-temp-u5 OBJECT-TYPE
                    SYNTAX Integer32 (0..99)
                    UNITS "N/A"
                    MAX-ACCESS read-only
                    STATUS current
                    DESCRIPTION "N/A"
                    DEFVAL { 0 }
                    ::= { integerObjects 496 }

        -- 1.3.6.1.4.1.9839.2.1.3.497
        denconet-temp-u6 OBJECT-TYPE
                    SYNTAX Integer32 (0..99)
                    UNITS "N/A"
                    MAX-ACCESS read-only
                    STATUS current
                    DESCRIPTION "N/A"
                    DEFVAL { 0 }
                    ::= { integerObjects 497 }

        -- 1.3.6.1.4.1.9839.2.1.3.498
        denconet-temp-u7 OBJECT-TYPE
                    SYNTAX Integer32 (0..99)
                    UNITS "N/A"
                    MAX-ACCESS read-only
                    STATUS current
                    DESCRIPTION "N/A"
                    DEFVAL { 0 }
                    ::= { integerObjects 498 }

        -- 1.3.6.1.4.1.9839.2.1.3.499
        denconet-temp-u8 OBJECT-TYPE
                    SYNTAX Integer32 (0..99)
                    UNITS "N/A"
                    MAX-ACCESS read-only
                    STATUS current
                    DESCRIPTION "N/A"
                    DEFVAL { 0 }
                    ::= { integerObjects 499 }

        -- 1.3.6.1.4.1.9839.2.1.3.500
        unit1-hum OBJECT-TYPE
                    SYNTAX Integer32 (0..32767)
                    UNITS "N/A"
                    MAX-ACCESS read-only
                    STATUS current
                    DESCRIPTION "N/A"
                    DEFVAL { 0 }
                    ::= { integerObjects 500 }

        -- 1.3.6.1.4.1.9839.2.1.3.501
        unit2-hum OBJECT-TYPE
                    SYNTAX Integer32 (0..32767)
                    UNITS "N/A"
                    MAX-ACCESS read-only
                    STATUS current
                    DESCRIPTION "N/A"
                    DEFVAL { 0 }
                    ::= { integerObjects 501 }

        -- 1.3.6.1.4.1.9839.2.1.3.502
        unit3-hum OBJECT-TYPE
                    SYNTAX Integer32 (0..32767)
                    UNITS "N/A"
                    MAX-ACCESS read-only
                    STATUS current
                    DESCRIPTION "N/A"
                    DEFVAL { 0 }
                    ::= { integerObjects 502 }

        -- 1.3.6.1.4.1.9839.2.1.3.503
        unit4-hum OBJECT-TYPE
                    SYNTAX Integer32 (0..32767)
                    UNITS "N/A"
                    MAX-ACCESS read-only
                    STATUS current
                    DESCRIPTION "N/A"
                    DEFVAL { 0 }
                    ::= { integerObjects 503 }

        -- 1.3.6.1.4.1.9839.2.1.3.504
        unit5-hum OBJECT-TYPE
                    SYNTAX Integer32 (0..32767)
                    UNITS "N/A"
                    MAX-ACCESS read-only
                    STATUS current
                    DESCRIPTION "N/A"
                    DEFVAL { 0 }
                    ::= { integerObjects 504 }

        -- 1.3.6.1.4.1.9839.2.1.3.505
        unit6-hum OBJECT-TYPE
                    SYNTAX Integer32 (0..32767)
                    UNITS "N/A"
                    MAX-ACCESS read-only
                    STATUS current
                    DESCRIPTION "N/A"
                    DEFVAL { 0 }
                    ::= { integerObjects 505 }

        -- 1.3.6.1.4.1.9839.2.1.3.506
        unit7-hum OBJECT-TYPE
                    SYNTAX Integer32 (0..32767)
                    UNITS "N/A"
                    MAX-ACCESS read-only
                    STATUS current
                    DESCRIPTION "N/A"
                    DEFVAL { 0 }
                    ::= { integerObjects 506 }

        -- 1.3.6.1.4.1.9839.2.1.3.507
        unit8-hum OBJECT-TYPE
                    SYNTAX Integer32 (0..32767)
                    UNITS "N/A"
                    MAX-ACCESS read-only
                    STATUS current
                    DESCRIPTION "N/A"
                    DEFVAL { 0 }
                    ::= { integerObjects 507 }

        -- 1.3.6.1.4.1.9839.2.1.3.508
        unit1-temp OBJECT-TYPE
                    SYNTAX Integer32 (0..9999)
                    UNITS "N/A"
                    MAX-ACCESS read-only
                    STATUS current
                    DESCRIPTION "N/A"
                    DEFVAL { 0 }
                    ::= { integerObjects 508 }

        -- 1.3.6.1.4.1.9839.2.1.3.509
        unit2-temp OBJECT-TYPE
                    SYNTAX Integer32 (0..9999)
                    UNITS "N/A"
                    MAX-ACCESS read-only
                    STATUS current
                    DESCRIPTION "N/A"
                    DEFVAL { 0 }
                    ::= { integerObjects 509 }

        -- 1.3.6.1.4.1.9839.2.1.3.510
        unit3-temp OBJECT-TYPE
                    SYNTAX Integer32 (0..9999)
                    UNITS "N/A"
                    MAX-ACCESS read-only
                    STATUS current
                    DESCRIPTION "N/A"
                    DEFVAL { 0 }
                    ::= { integerObjects 510 }

        -- 1.3.6.1.4.1.9839.2.1.3.511
        unit4-temp OBJECT-TYPE
                    SYNTAX Integer32 (0..9999)
                    UNITS "N/A"
                    MAX-ACCESS read-only
                    STATUS current
                    DESCRIPTION "N/A"
                    DEFVAL { 0 }
                    ::= { integerObjects 511 }

        -- 1.3.6.1.4.1.9839.2.1.3.512
        unit5-temp OBJECT-TYPE
                    SYNTAX Integer32 (0..9999)
                    UNITS "N/A"
                    MAX-ACCESS read-only
                    STATUS current
                    DESCRIPTION "N/A"
                    DEFVAL { 0 }
                    ::= { integerObjects 512 }

        -- 1.3.6.1.4.1.9839.2.1.3.513
        unit6-temp OBJECT-TYPE
                    SYNTAX Integer32 (0..9999)
                    UNITS "N/A"
                    MAX-ACCESS read-only
                    STATUS current
                    DESCRIPTION "N/A"
                    DEFVAL { 0 }
                    ::= { integerObjects 513 }

        -- 1.3.6.1.4.1.9839.2.1.3.514
        unit7-temp OBJECT-TYPE
                    SYNTAX Integer32 (0..9999)
                    UNITS "N/A"
                    MAX-ACCESS read-only
                    STATUS current
                    DESCRIPTION "N/A"
                    DEFVAL { 0 }
                    ::= { integerObjects 514 }

        -- 1.3.6.1.4.1.9839.2.1.3.515
        unit8-temp OBJECT-TYPE
                    SYNTAX Integer32 (0..9999)
                    UNITS "N/A"
                    MAX-ACCESS read-only
                    STATUS current
                    DESCRIPTION "N/A"
                    DEFVAL { 0 }
                    ::= { integerObjects 515 }

        -- 1.3.6.1.4.1.9839.2.1.3.516
        denconet-hum OBJECT-TYPE
                    SYNTAX Integer32 (0..3)
                    UNITS "N/A"
                    MAX-ACCESS read-write
                    STATUS current
                    DESCRIPTION "N/A"
                    DEFVAL { 0 }
                    ::= { integerObjects 516 }

        -- 1.3.6.1.4.1.9839.2.1.3.517
        denconet-hum-u1 OBJECT-TYPE
                    SYNTAX Integer32 (0..99)
                    UNITS "N/A"
                    MAX-ACCESS read-only
                    STATUS current
                    DESCRIPTION "N/A"
                    DEFVAL { 0 }
                    ::= { integerObjects 517 }

        -- 1.3.6.1.4.1.9839.2.1.3.518
        denconet-hum-u2 OBJECT-TYPE
                    SYNTAX Integer32 (0..99)
                    UNITS "N/A"
                    MAX-ACCESS read-only
                    STATUS current
                    DESCRIPTION "N/A"
                    DEFVAL { 0 }
                    ::= { integerObjects 518 }

        -- 1.3.6.1.4.1.9839.2.1.3.519
        denconet-hum-u3 OBJECT-TYPE
                    SYNTAX Integer32 (0..99)
                    UNITS "N/A"
                    MAX-ACCESS read-only
                    STATUS current
                    DESCRIPTION "N/A"
                    DEFVAL { 0 }
                    ::= { integerObjects 519 }

        -- 1.3.6.1.4.1.9839.2.1.3.520
        denconet-hum-u4 OBJECT-TYPE
                    SYNTAX Integer32 (0..99)
                    UNITS "N/A"
                    MAX-ACCESS read-only
                    STATUS current
                    DESCRIPTION "N/A"
                    DEFVAL { 0 }
                    ::= { integerObjects 520 }

        -- 1.3.6.1.4.1.9839.2.1.3.521
        denconet-hum-u5 OBJECT-TYPE
                    SYNTAX Integer32 (0..99)
                    UNITS "N/A"
                    MAX-ACCESS read-only
                    STATUS current
                    DESCRIPTION "N/A"
                    DEFVAL { 0 }
                    ::= { integerObjects 521 }

        -- 1.3.6.1.4.1.9839.2.1.3.522
        denconet-hum-u6 OBJECT-TYPE
                    SYNTAX Integer32 (0..99)
                    UNITS "N/A"
                    MAX-ACCESS read-only
                    STATUS current
                    DESCRIPTION "N/A"
                    DEFVAL { 0 }
                    ::= { integerObjects 522 }

        -- 1.3.6.1.4.1.9839.2.1.3.523
        denconet-hum-u7 OBJECT-TYPE
                    SYNTAX Integer32 (0..99)
                    UNITS "N/A"
                    MAX-ACCESS read-only
                    STATUS current
                    DESCRIPTION "N/A"
                    DEFVAL { 0 }
                    ::= { integerObjects 523 }

        -- 1.3.6.1.4.1.9839.2.1.3.524
        denconet-hum-u8 OBJECT-TYPE
                    SYNTAX Integer32 (0..99)
                    UNITS "N/A"
                    MAX-ACCESS read-only
                    STATUS current
                    DESCRIPTION "N/A"
                    DEFVAL { 0 }
                    ::= { integerObjects 524 }

        -- 1.3.6.1.4.1.9839.2.1.3.525
        unit1-run-hr-low OBJECT-TYPE
                    SYNTAX Integer32 (0..9999)
                    UNITS "N/A"
                    MAX-ACCESS read-only
                    STATUS current
                    DESCRIPTION "N/A"
                    DEFVAL { 0 }
                    ::= { integerObjects 525 }

        -- 1.3.6.1.4.1.9839.2.1.3.526
        unit2-run-hr-low OBJECT-TYPE
                    SYNTAX Integer32 (0..9999)
                    UNITS "N/A"
                    MAX-ACCESS read-only
                    STATUS current
                    DESCRIPTION "N/A"
                    DEFVAL { 0 }
                    ::= { integerObjects 526 }

        -- 1.3.6.1.4.1.9839.2.1.3.527
        unit3-run-hr-low OBJECT-TYPE
                    SYNTAX Integer32 (0..9999)
                    UNITS "N/A"
                    MAX-ACCESS read-only
                    STATUS current
                    DESCRIPTION "N/A"
                    DEFVAL { 0 }
                    ::= { integerObjects 527 }

        -- 1.3.6.1.4.1.9839.2.1.3.528
        unit4-run-hr-low OBJECT-TYPE
                    SYNTAX Integer32 (0..9999)
                    UNITS "N/A"
                    MAX-ACCESS read-only
                    STATUS current
                    DESCRIPTION "N/A"
                    DEFVAL { 0 }
                    ::= { integerObjects 528 }

        -- 1.3.6.1.4.1.9839.2.1.3.529
        unit5-run-hr-low OBJECT-TYPE
                    SYNTAX Integer32 (0..9999)
                    UNITS "N/A"
                    MAX-ACCESS read-only
                    STATUS current
                    DESCRIPTION "N/A"
                    DEFVAL { 0 }
                    ::= { integerObjects 529 }

        -- 1.3.6.1.4.1.9839.2.1.3.530
        unit6-run-hr-low OBJECT-TYPE
                    SYNTAX Integer32 (0..9999)
                    UNITS "N/A"
                    MAX-ACCESS read-only
                    STATUS current
                    DESCRIPTION "N/A"
                    DEFVAL { 0 }
                    ::= { integerObjects 530 }

        -- 1.3.6.1.4.1.9839.2.1.3.531
        unit7-run-hr-low OBJECT-TYPE
                    SYNTAX Integer32 (0..9999)
                    UNITS "N/A"
                    MAX-ACCESS read-only
                    STATUS current
                    DESCRIPTION "N/A"
                    DEFVAL { 0 }
                    ::= { integerObjects 531 }

        -- 1.3.6.1.4.1.9839.2.1.3.532
        unit8-run-hr-low OBJECT-TYPE
                    SYNTAX Integer32 (0..9999)
                    UNITS "N/A"
                    MAX-ACCESS read-only
                    STATUS current
                    DESCRIPTION "N/A"
                    DEFVAL { 0 }
                    ::= { integerObjects 532 }

        -- 1.3.6.1.4.1.9839.2.1.3.533
        unit1-run-hr-high OBJECT-TYPE
                    SYNTAX Integer32 (0..9999)
                    UNITS "N/A"
                    MAX-ACCESS read-only
                    STATUS current
                    DESCRIPTION "N/A"
                    DEFVAL { 0 }
                    ::= { integerObjects 533 }

        -- 1.3.6.1.4.1.9839.2.1.3.534
        unit2-run-hr-high OBJECT-TYPE
                    SYNTAX Integer32 (0..9999)
                    UNITS "N/A"
                    MAX-ACCESS read-only
                    STATUS current
                    DESCRIPTION "N/A"
                    DEFVAL { 0 }
                    ::= { integerObjects 534 }

        -- 1.3.6.1.4.1.9839.2.1.3.535
        unit3-run-hr-high OBJECT-TYPE
                    SYNTAX Integer32 (0..9999)
                    UNITS "N/A"
                    MAX-ACCESS read-only
                    STATUS current
                    DESCRIPTION "N/A"
                    DEFVAL { 0 }
                    ::= { integerObjects 535 }

        -- 1.3.6.1.4.1.9839.2.1.3.536
        unit4-run-hr-high OBJECT-TYPE
                    SYNTAX Integer32 (0..9999)
                    UNITS "N/A"
                    MAX-ACCESS read-only
                    STATUS current
                    DESCRIPTION "N/A"
                    DEFVAL { 0 }
                    ::= { integerObjects 536 }

        -- 1.3.6.1.4.1.9839.2.1.3.537
        unit5-run-hr-high OBJECT-TYPE
                    SYNTAX Integer32 (0..9999)
                    UNITS "N/A"
                    MAX-ACCESS read-only
                    STATUS current
                    DESCRIPTION "N/A"
                    DEFVAL { 0 }
                    ::= { integerObjects 537 }

        -- 1.3.6.1.4.1.9839.2.1.3.538
        unit6-run-hr-high OBJECT-TYPE
                    SYNTAX Integer32 (0..9999)
                    UNITS "N/A"
                    MAX-ACCESS read-only
                    STATUS current
                    DESCRIPTION "N/A"
                    DEFVAL { 0 }
                    ::= { integerObjects 538 }

        -- 1.3.6.1.4.1.9839.2.1.3.539
        unit7-run-hr-high OBJECT-TYPE
                    SYNTAX Integer32 (0..9999)
                    UNITS "N/A"
                    MAX-ACCESS read-only
                    STATUS current
                    DESCRIPTION "N/A"
                    DEFVAL { 0 }
                    ::= { integerObjects 539 }

        -- 1.3.6.1.4.1.9839.2.1.3.540
        unit8-run-hr-high OBJECT-TYPE
                    SYNTAX Integer32 (0..9999)
                    UNITS "N/A"
                    MAX-ACCESS read-only
                    STATUS current
                    DESCRIPTION "N/A"
                    DEFVAL { 0 }
                    ::= { integerObjects 540 }

        -- 1.3.6.1.4.1.9839.2.1.3.541
        average-hum OBJECT-TYPE
                    SYNTAX Integer32 (0..32767)
                    UNITS "N/A"
                    MAX-ACCESS read-write
                    STATUS current
                    DESCRIPTION "N/A"
                    DEFVAL { 0 }
                    ::= { integerObjects 541 }

        -- 1.3.6.1.4.1.9839.2.1.3.542
        average-unit-number-temp OBJECT-TYPE
                    SYNTAX Integer32 (0..32767)
                    UNITS "N/A"
                    MAX-ACCESS read-write
                    STATUS current
                    DESCRIPTION "N/A"
                    DEFVAL { 0 }
                    ::= { integerObjects 542 }

        -- 1.3.6.1.4.1.9839.2.1.3.543
        average-unit-number-hum OBJECT-TYPE
                    SYNTAX Integer32 (0..32767)
                    UNITS "N/A"
                    MAX-ACCESS read-write
                    STATUS current
                    DESCRIPTION "N/A"
                    DEFVAL { 0 }
                    ::= { integerObjects 543 }

        -- 1.3.6.1.4.1.9839.2.1.3.544
        real-mst-t OBJECT-TYPE
                    SYNTAX Integer32 (0..32767)
                    UNITS "N/A"
                    MAX-ACCESS read-write
                    STATUS current
                    DESCRIPTION "N/A"
                    DEFVAL { 0 }
                    ::= { integerObjects 544 }

        -- 1.3.6.1.4.1.9839.2.1.3.545
        real-chk-t OBJECT-TYPE
                    SYNTAX Integer32 (0..32767)
                    UNITS "N/A"
                    MAX-ACCESS read-write
                    STATUS current
                    DESCRIPTION "N/A"
                    DEFVAL { 0 }
                    ::= { integerObjects 545 }

        -- 1.3.6.1.4.1.9839.2.1.3.546
        real-mst-h OBJECT-TYPE
                    SYNTAX Integer32 (0..32767)
                    UNITS "N/A"
                    MAX-ACCESS read-write
                    STATUS current
                    DESCRIPTION "N/A"
                    DEFVAL { 0 }
                    ::= { integerObjects 546 }

        -- 1.3.6.1.4.1.9839.2.1.3.547
        real-chk-h OBJECT-TYPE
                    SYNTAX Integer32 (0..32767)
                    UNITS "N/A"
                    MAX-ACCESS read-write
                    STATUS current
                    DESCRIPTION "N/A"
                    DEFVAL { 0 }
                    ::= { integerObjects 547 }

        -- 1.3.6.1.4.1.9839.2.1.3.548
        defrost-delay OBJECT-TYPE
                    SYNTAX Integer32 (0..99)
                    UNITS "N/A"
                    MAX-ACCESS read-write
                    STATUS current
                    DESCRIPTION "N/A"
                    DEFVAL { 2 }
                    ::= { integerObjects 548 }

        -- 1.3.6.1.4.1.9839.2.1.3.549
        defrost-max-time OBJECT-TYPE
                    SYNTAX Integer32 (0..99)
                    UNITS "N/A"
                    MAX-ACCESS read-write
                    STATUS current
                    DESCRIPTION "N/A"
                    DEFVAL { 5 }
                    ::= { integerObjects 549 }

        -- 1.3.6.1.4.1.9839.2.1.3.550
        defr-on-type OBJECT-TYPE
                    SYNTAX Integer32 (0..2)
                    UNITS "N/A"
                    MAX-ACCESS read-write
                    STATUS current
                    DESCRIPTION "N/A"
                    DEFVAL { 2 }
                    ::= { integerObjects 550 }

        -- 1.3.6.1.4.1.9839.2.1.3.551
        defr-off-type OBJECT-TYPE
                    SYNTAX Integer32 (0..2)
                    UNITS "N/A"
                    MAX-ACCESS read-write
                    STATUS current
                    DESCRIPTION "N/A"
                    DEFVAL { 2 }
                    ::= { integerObjects 551 }

        -- 1.3.6.1.4.1.9839.2.1.3.552
        lp-startup-delay OBJECT-TYPE
                    SYNTAX Integer32 (0..32000)
                    UNITS "N/A"
                    MAX-ACCESS read-write
                    STATUS current
                    DESCRIPTION "N/A"
                    DEFVAL { 0 }
                    ::= { integerObjects 552 }

        -- 1.3.6.1.4.1.9839.2.1.3.553
        lp-running-delay OBJECT-TYPE
                    SYNTAX Integer32 (0..32767)
                    UNITS "N/A"
                    MAX-ACCESS read-write
                    STATUS current
                    DESCRIPTION "N/A"
                    DEFVAL { 0 }
                    ::= { integerObjects 553 }

        -- 1.3.6.1.4.1.9839.2.1.3.554
        aps-demand-fan OBJECT-TYPE
                    SYNTAX Integer32 (0..1000)
                    UNITS "N/A"
                    MAX-ACCESS read-write
                    STATUS current
                    DESCRIPTION "Under Floor Pressure Control Fan Demand Output"
                    DEFVAL { 0 }
                    ::= { integerObjects 554 }

        -- 1.3.6.1.4.1.9839.2.1.3.555
        hp-delay OBJECT-TYPE
                    SYNTAX Integer32 (0..999)
                    UNITS "N/A"
                    MAX-ACCESS read-write
                    STATUS current
                    DESCRIPTION "High pressure prevent warning delay"
                    DEFVAL { 5 }
                    ::= { integerObjects 555 }

        -- 1.3.6.1.4.1.9839.2.1.3.556
        stage-load-up-time OBJECT-TYPE
                    SYNTAX Integer32 (0..999)
                    UNITS "N/A"
                    MAX-ACCESS read-write
                    STATUS current
                    DESCRIPTION "Time between steps on load-up"
                    DEFVAL { 10 }
                    ::= { integerObjects 556 }

        -- 1.3.6.1.4.1.9839.2.1.3.557
        delaytooff OBJECT-TYPE
                    SYNTAX Integer32 (0..999)
                    UNITS "sec"
                    MAX-ACCESS read-write
                    STATUS current
                    DESCRIPTION "Delay time to validate request to switch off fixed speed compressor"
                    DEFVAL { 0 }
                    ::= { integerObjects 557 }

        -- 1.3.6.1.4.1.9839.2.1.3.558
        stage-unload-delay-time OBJECT-TYPE
                    SYNTAX Integer32 (0..999)
                    UNITS "N/A"
                    MAX-ACCESS read-write
                    STATUS current
                    DESCRIPTION "Delay between two unload"
                    DEFVAL { 10 }
                    ::= { integerObjects 558 }

        -- 1.3.6.1.4.1.9839.2.1.3.559
        delaytoon OBJECT-TYPE
                    SYNTAX Integer32 (0..999)
                    UNITS "sec"
                    MAX-ACCESS read-write
                    STATUS current
                    DESCRIPTION "Delay time to validate request to switch on fixed speed compressor"
                    DEFVAL { 0 }
                    ::= { integerObjects 559 }

        -- 1.3.6.1.4.1.9839.2.1.3.560
        discharge-press-kpa OBJECT-TYPE
                    SYNTAX Integer32 (-32768..32767)
                    UNITS "N/A"
                    MAX-ACCESS read-only
                    STATUS current
                    DESCRIPTION "N/A"
                    DEFVAL { 0 }
                    ::= { integerObjects 560 }

        -- 1.3.6.1.4.1.9839.2.1.3.561
        lp-autoreset-max-time OBJECT-TYPE
                    SYNTAX Integer32 (-32768..32767)
                    UNITS "N/A"
                    MAX-ACCESS read-write
                    STATUS current
                    DESCRIPTION "N/A"
                    DEFVAL { 0 }
                    ::= { integerObjects 561 }

        -- 1.3.6.1.4.1.9839.2.1.3.562
        lp-autoreset-max-num OBJECT-TYPE
                    SYNTAX Integer32 (-32768..32767)
                    UNITS "N/A"
                    MAX-ACCESS read-write
                    STATUS current
                    DESCRIPTION "N/A"
                    DEFVAL { 0 }
                    ::= { integerObjects 562 }

        -- 1.3.6.1.4.1.9839.2.1.3.563
        reset-auto-max-time-pwrp OBJECT-TYPE
                    SYNTAX Integer32 (0..32767)
                    UNITS "N/A"
                    MAX-ACCESS read-write
                    STATUS current
                    DESCRIPTION "N/A"
                    DEFVAL { 0 }
                    ::= { integerObjects 563 }

        -- 1.3.6.1.4.1.9839.2.1.3.564
        reset-auto-max-num-pwrp OBJECT-TYPE
                    SYNTAX Integer32 (0..32767)
                    UNITS "N/A"
                    MAX-ACCESS read-write
                    STATUS current
                    DESCRIPTION "N/A"
                    DEFVAL { 0 }
                    ::= { integerObjects 564 }

        -- 1.3.6.1.4.1.9839.2.1.3.1100
        oil-return-req-min-thr-bldc-1 OBJECT-TYPE
                    SYNTAX Integer32 (0..1000)
                    UNITS "%"
                    MAX-ACCESS read-write
                    STATUS current
                    DESCRIPTION "N/A"
                    DEFVAL { 300 }
                    ::= { integerObjects 1100 }

        -- 1.3.6.1.4.1.9839.2.1.3.1101
        devavbl-bldc-1 OBJECT-TYPE
                    SYNTAX Integer32 (0..99)
                    UNITS "N/A"
                    MAX-ACCESS read-only
                    STATUS current
                    DESCRIPTION "Compressor status information for DeviceAvaliable List"
                    DEFVAL { 0 }
                    ::= { integerObjects 1101 }

        -- 1.3.6.1.4.1.9839.2.1.3.1102
        envcntdwn-bldc-1 OBJECT-TYPE
                    SYNTAX Integer32 (0..32000)
                    UNITS "N/A"
                    MAX-ACCESS read-only
                    STATUS current
                    DESCRIPTION "Out of envelop timing countdown"
                    DEFVAL { 0 }
                    ::= { integerObjects 1102 }

        -- 1.3.6.1.4.1.9839.2.1.3.1103
        envoutmaxt-spec-bldc-1 OBJECT-TYPE
                    SYNTAX Integer32 (0..32000)
                    UNITS "sec"
                    MAX-ACCESS read-write
                    STATUS current
                    DESCRIPTION "Out of envelop alarm delay time to be used when specified by pin"
                    DEFVAL { 0 }
                    ::= { integerObjects 1103 }

        -- 1.3.6.1.4.1.9839.2.1.3.1104
        hightemp-zone-bldc-1 OBJECT-TYPE
                    SYNTAX Integer32 (0..32767)
                    UNITS "N/A"
                    MAX-ACCESS read-only
                    STATUS current
                    DESCRIPTION "N/A"
                    DEFVAL { 0 }
                    ::= { integerObjects 1104 }

        -- 1.3.6.1.4.1.9839.2.1.3.1105
        minofft-comp OBJECT-TYPE
                    SYNTAX Integer32 (0..999)
                    UNITS "sec"
                    MAX-ACCESS read-write
                    STATUS current
                    DESCRIPTION "Compressor minimum off time"
                    DEFVAL { 120 }
                    ::= { integerObjects 1105 }

        -- 1.3.6.1.4.1.9839.2.1.3.1106
        minonondifft-comp OBJECT-TYPE
                    SYNTAX Integer32 (0..32000)
                    UNITS "N/A"
                    MAX-ACCESS read-write
                    STATUS current
                    DESCRIPTION "Minimum time between startings of different devices"
                    DEFVAL { 0 }
                    ::= { integerObjects 1106 }

        -- 1.3.6.1.4.1.9839.2.1.3.1107
        minononsamet-comp OBJECT-TYPE
                    SYNTAX Integer32 (0..999)
                    UNITS "sec"
                    MAX-ACCESS read-write
                    STATUS current
                    DESCRIPTION "Minimum time between compressor starts"
                    DEFVAL { 600 }
                    ::= { integerObjects 1107 }

        -- 1.3.6.1.4.1.9839.2.1.3.1108
        minont-comp OBJECT-TYPE
                    SYNTAX Integer32 (0..600)
                    UNITS "sec"
                    MAX-ACCESS read-write
                    STATUS current
                    DESCRIPTION "Compressor minimum on time (startup period)"
                    DEFVAL { 60 }
                    ::= { integerObjects 1108 }

        -- 1.3.6.1.4.1.9839.2.1.3.1109
        minont-cntdwn-bldc-1 OBJECT-TYPE
                    SYNTAX Integer32 (0..32767)
                    UNITS "sec"
                    MAX-ACCESS read-only
                    STATUS current
                    DESCRIPTION "Countdown of minimum On time (to switch OFF)"
                    DEFVAL { 0 }
                    ::= { integerObjects 1109 }

        -- 1.3.6.1.4.1.9839.2.1.3.1110
        rfrg-bldc-1 OBJECT-TYPE
                    SYNTAX Integer32 (0..14)
                    UNITS "N/A"
                    MAX-ACCESS read-write
                    STATUS current
                    DESCRIPTION "Gas type (1=R134a;3= R407C;4=R410A)"
                    DEFVAL { 4 }
                    ::= { integerObjects 1110 }

        -- 1.3.6.1.4.1.9839.2.1.3.1111
        saft-cntdwn-bldc-1 OBJECT-TYPE
                    SYNTAX Integer32 (0..32767)
                    UNITS "sec"
                    MAX-ACCESS read-only
                    STATUS current
                    DESCRIPTION "Countdown of safety OFF  time ( to switch ON)"
                    DEFVAL { 0 }
                    ::= { integerObjects 1111 }

        -- 1.3.6.1.4.1.9839.2.1.3.1112
        xdspalrmzone-bldc-1 OBJECT-TYPE
                    SYNTAX Integer32 (0..32767)
                    UNITS "N/A"
                    MAX-ACCESS read-only
                    STATUS current
                    DESCRIPTION "0=Null;1=OK;2=Max.comp.R.;3=Max.disch.P.;4=HCurr.;5=Max.suct.P.;6=Min.comp.R.;7=LowDP;8=Min.disch.P.;9=Min.suct.P."
                    DEFVAL { 0 }
                    ::= { integerObjects 1112 }

        -- 1.3.6.1.4.1.9839.2.1.3.1113
        time-oil-non-return-thr-bldc-1 OBJECT-TYPE
                    SYNTAX Integer32 (0..32000)
                    UNITS "sec"
                    MAX-ACCESS read-write
                    STATUS current
                    DESCRIPTION "N/A"
                    DEFVAL { 0 }
                    ::= { integerObjects 1113 }

        -- 1.3.6.1.4.1.9839.2.1.3.1114
        time-oil-return-thr-bldc-1 OBJECT-TYPE
                    SYNTAX Integer32 (0..32000)
                    UNITS "sec"
                    MAX-ACCESS read-write
                    STATUS current
                    DESCRIPTION "N/A"
                    DEFVAL { 0 }
                    ::= { integerObjects 1114 }

        -- 1.3.6.1.4.1.9839.2.1.3.1115
        countdown-al-dp-bldc-1 OBJECT-TYPE
                    SYNTAX Integer32 (-32768..32767)
                    UNITS "N/A"
                    MAX-ACCESS read-only
                    STATUS current
                    DESCRIPTION "N/A"
                    DEFVAL { 0 }
                    ::= { integerObjects 1115 }

        -- 1.3.6.1.4.1.9839.2.1.3.1150
        comptyp-pwrp-1 OBJECT-TYPE
                    SYNTAX Integer32 (1..35)
                    UNITS "N/A"
                    MAX-ACCESS read-write
                    STATUS current
                    DESCRIPTION "Value coming from inverter module (0=Undefined;1,2,3=Siam R410A;4,5,6=Samsung;7,8=Siam R407C;9,10=MHI R407C;11,12=Siam SNB;13=Siam TNB R410A))"
                    DEFVAL { 1 }
                    ::= { integerObjects 1150 }

        -- 1.3.6.1.4.1.9839.2.1.3.1151
        currerrcode-pwrp-1 OBJECT-TYPE
                    SYNTAX Integer32 (0..99)
                    UNITS "N/A"
                    MAX-ACCESS read-only
                    STATUS current
                    DESCRIPTION "Show the present drive error"
                    DEFVAL { 0 }
                    ::= { integerObjects 1151 }

        -- 1.3.6.1.4.1.9839.2.1.3.1152
        dc-busv-pwrp-1 OBJECT-TYPE
                    SYNTAX Integer32 (0..9999)
                    UNITS "V"
                    MAX-ACCESS read-only
                    STATUS current
                    DESCRIPTION "DC Bus voltage"
                    DEFVAL { 0 }
                    ::= { integerObjects 1152 }

        -- 1.3.6.1.4.1.9839.2.1.3.1153
        drivestatus-pwrp-1 OBJECT-TYPE
                    SYNTAX Integer32 (0..9)
                    UNITS "N/A"
                    MAX-ACCESS read-only
                    STATUS current
                    DESCRIPTION "Show the driver status: 0=Stop; 1=Run; 2=Alarm"
                    DEFVAL { 0 }
                    ::= { integerObjects 1153 }

        -- 1.3.6.1.4.1.9839.2.1.3.1154
        drivetemp-pwrp-1 OBJECT-TYPE
                    SYNTAX Integer32 (-999..999)
                    UNITS "C"
                    MAX-ACCESS read-only
                    STATUS current
                    DESCRIPTION "Power+ temperature"
                    DEFVAL { 0 }
                    ::= { integerObjects 1154 }

        -- 1.3.6.1.4.1.9839.2.1.3.1155
        rotorspeed-0-1000-pwrp-1 OBJECT-TYPE
                    SYNTAX Integer32 (0..9999)
                    UNITS "%"
                    MAX-ACCESS read-only
                    STATUS current
                    DESCRIPTION "Rotor Speed scaled [0.0% - 100.0%]"
                    DEFVAL { 0 }
                    ::= { integerObjects 1155 }

        -- 1.3.6.1.4.1.9839.2.1.3.1156
        rotorspeed-rpm-pwrp-1 OBJECT-TYPE
                    SYNTAX Integer32 (0..9999)
                    UNITS "N/A"
                    MAX-ACCESS read-only
                    STATUS current
                    DESCRIPTION "Rotor speed [rpm]"
                    DEFVAL { 0 }
                    ::= { integerObjects 1156 }

        -- 1.3.6.1.4.1.9839.2.1.3.1157
        minont-cntdwn-onoff-c1 OBJECT-TYPE
                    SYNTAX Integer32 (0..32000)
                    UNITS "sec"
                    MAX-ACCESS read-only
                    STATUS current
                    DESCRIPTION "Countdown minimum off time"
                    DEFVAL { 0 }
                    ::= { integerObjects 1157 }

        -- 1.3.6.1.4.1.9839.2.1.3.1158
        saft-cntdwn-onoff-c1 OBJECT-TYPE
                    SYNTAX Integer32 (0..32000)
                    UNITS "sec"
                    MAX-ACCESS read-only
                    STATUS current
                    DESCRIPTION "Countdown safety time"
                    DEFVAL { 0 }
                    ::= { integerObjects 1158 }

        -- 1.3.6.1.4.1.9839.2.1.3.1200
        oil-return-req-min-thr-bldc-2 OBJECT-TYPE
                    SYNTAX Integer32 (0..1000)
                    UNITS "N/A"
                    MAX-ACCESS read-write
                    STATUS current
                    DESCRIPTION "N/A"
                    DEFVAL { 300 }
                    ::= { integerObjects 1200 }

        -- 1.3.6.1.4.1.9839.2.1.3.1201
        devavbl-bldc-2 OBJECT-TYPE
                    SYNTAX Integer32 (0..99)
                    UNITS "N/A"
                    MAX-ACCESS read-only
                    STATUS current
                    DESCRIPTION "Compressor status information for DeviceAvaliable List"
                    DEFVAL { 0 }
                    ::= { integerObjects 1201 }

        -- 1.3.6.1.4.1.9839.2.1.3.1202
        envcntdwn-bldc-2 OBJECT-TYPE
                    SYNTAX Integer32 (0..32000)
                    UNITS "N/A"
                    MAX-ACCESS read-only
                    STATUS current
                    DESCRIPTION "Out of envelop timing countdown"
                    DEFVAL { 0 }
                    ::= { integerObjects 1202 }

        -- 1.3.6.1.4.1.9839.2.1.3.1203
        envoutmaxt-spec-bldc-2 OBJECT-TYPE
                    SYNTAX Integer32 (0..32000)
                    UNITS "sec"
                    MAX-ACCESS read-write
                    STATUS current
                    DESCRIPTION "Out of envelop alarm delay time to be used when specified by pin"
                    DEFVAL { 0 }
                    ::= { integerObjects 1203 }

        -- 1.3.6.1.4.1.9839.2.1.3.1204
        hightemp-zone-bldc-2 OBJECT-TYPE
                    SYNTAX Integer32 (0..32767)
                    UNITS "N/A"
                    MAX-ACCESS read-only
                    STATUS current
                    DESCRIPTION "N/A"
                    DEFVAL { 0 }
                    ::= { integerObjects 1204 }

        -- 1.3.6.1.4.1.9839.2.1.3.1205
        minont-cntdwn-bldc-2 OBJECT-TYPE
                    SYNTAX Integer32 (0..32767)
                    UNITS "sec"
                    MAX-ACCESS read-only
                    STATUS current
                    DESCRIPTION "Countdown of minimum On time (to switch OFF)"
                    DEFVAL { 0 }
                    ::= { integerObjects 1205 }

        -- 1.3.6.1.4.1.9839.2.1.3.1206
        rfrg-bldc-2 OBJECT-TYPE
                    SYNTAX Integer32 (0..14)
                    UNITS "N/A"
                    MAX-ACCESS read-write
                    STATUS current
                    DESCRIPTION "Gas type (1=R134a;3= R407C;4=R410A)"
                    DEFVAL { 4 }
                    ::= { integerObjects 1206 }

        -- 1.3.6.1.4.1.9839.2.1.3.1207
        saft-cntdwn-bldc-2 OBJECT-TYPE
                    SYNTAX Integer32 (0..32767)
                    UNITS "sec"
                    MAX-ACCESS read-only
                    STATUS current
                    DESCRIPTION "Countdown of safety OFF  time ( to switch ON)"
                    DEFVAL { 0 }
                    ::= { integerObjects 1207 }

        -- 1.3.6.1.4.1.9839.2.1.3.1208
        xdspalrmzone-bldc-2 OBJECT-TYPE
                    SYNTAX Integer32 (0..32767)
                    UNITS "N/A"
                    MAX-ACCESS read-only
                    STATUS current
                    DESCRIPTION "0=Null;1=OK;2=Max.comp.R.;3=Max.disch.P.;4=HCurr.;5=Max.suct.P.;6=Min.comp.R.;7=LowDP;8=Min.disch.P.;9=Min.suct.P."
                    DEFVAL { 0 }
                    ::= { integerObjects 1208 }

        -- 1.3.6.1.4.1.9839.2.1.3.1209
        time-oil-non-return-thr-bldc-2 OBJECT-TYPE
                    SYNTAX Integer32 (0..32000)
                    UNITS "sec"
                    MAX-ACCESS read-write
                    STATUS current
                    DESCRIPTION "N/A"
                    DEFVAL { 0 }
                    ::= { integerObjects 1209 }

        -- 1.3.6.1.4.1.9839.2.1.3.1210
        time-oil-return-thr-bldc-2 OBJECT-TYPE
                    SYNTAX Integer32 (0..32000)
                    UNITS "sec"
                    MAX-ACCESS read-write
                    STATUS current
                    DESCRIPTION "N/A"
                    DEFVAL { 0 }
                    ::= { integerObjects 1210 }

        -- 1.3.6.1.4.1.9839.2.1.3.1211
        countdown-al-dp-bldc-2 OBJECT-TYPE
                    SYNTAX Integer32 (-32768..32767)
                    UNITS "N/A"
                    MAX-ACCESS read-write
                    STATUS current
                    DESCRIPTION "N/A"
                    DEFVAL { 0 }
                    ::= { integerObjects 1211 }

        -- 1.3.6.1.4.1.9839.2.1.3.1250
        comptyp-pwrp-2 OBJECT-TYPE
                    SYNTAX Integer32 (1..35)
                    UNITS "N/A"
                    MAX-ACCESS read-write
                    STATUS current
                    DESCRIPTION "Value coming from inverter module (0=Undefined;1,2,3=Siam R410A;4,5,6=Samsung;7,8=Siam R407C;9,10=MHI R407C;11,12=Siam SNB;13=Siam TNB R410A))"
                    DEFVAL { 1 }
                    ::= { integerObjects 1250 }

        -- 1.3.6.1.4.1.9839.2.1.3.1251
        currerrcode-pwrp-2 OBJECT-TYPE
                    SYNTAX Integer32 (0..99)
                    UNITS "N/A"
                    MAX-ACCESS read-only
                    STATUS current
                    DESCRIPTION "Show the present drive error"
                    DEFVAL { 0 }
                    ::= { integerObjects 1251 }

        -- 1.3.6.1.4.1.9839.2.1.3.1252
        dc-busv-pwrp-2 OBJECT-TYPE
                    SYNTAX Integer32 (0..9999)
                    UNITS "V"
                    MAX-ACCESS read-only
                    STATUS current
                    DESCRIPTION "DC Bus voltage"
                    DEFVAL { 0 }
                    ::= { integerObjects 1252 }

        -- 1.3.6.1.4.1.9839.2.1.3.1253
        drivestatus-pwrp-2 OBJECT-TYPE
                    SYNTAX Integer32 (0..9)
                    UNITS "N/A"
                    MAX-ACCESS read-only
                    STATUS current
                    DESCRIPTION "Show the driver status: 0=Stop; 1=Run; 2=Alarm"
                    DEFVAL { 0 }
                    ::= { integerObjects 1253 }

        -- 1.3.6.1.4.1.9839.2.1.3.1254
        drivetemp-pwrp-2 OBJECT-TYPE
                    SYNTAX Integer32 (-999..999)
                    UNITS "C"
                    MAX-ACCESS read-only
                    STATUS current
                    DESCRIPTION "Power+ temperature"
                    DEFVAL { 0 }
                    ::= { integerObjects 1254 }

        -- 1.3.6.1.4.1.9839.2.1.3.1255
        rotorspeed-0-1000-pwrp-2 OBJECT-TYPE
                    SYNTAX Integer32 (0..9999)
                    UNITS "%"
                    MAX-ACCESS read-only
                    STATUS current
                    DESCRIPTION "Rotor Speed scaled [0.0% - 100.0%]"
                    DEFVAL { 0 }
                    ::= { integerObjects 1255 }

        -- 1.3.6.1.4.1.9839.2.1.3.1256
        rotorspeed-rpm-pwrp-2 OBJECT-TYPE
                    SYNTAX Integer32 (0..9999)
                    UNITS "N/A"
                    MAX-ACCESS read-only
                    STATUS current
                    DESCRIPTION "Rotor speed [rpm]"
                    DEFVAL { 0 }
                    ::= { integerObjects 1256 }

        -- 1.3.6.1.4.1.9839.2.1.3.1257
        minont-cntdwn-onoff-c2 OBJECT-TYPE
                    SYNTAX Integer32 (0..32000)
                    UNITS "sec"
                    MAX-ACCESS read-only
                    STATUS current
                    DESCRIPTION "Countdown minimum off time"
                    DEFVAL { 0 }
                    ::= { integerObjects 1257 }

        -- 1.3.6.1.4.1.9839.2.1.3.1258
        saft-cntdwn-onoff-c2 OBJECT-TYPE
                    SYNTAX Integer32 (0..32000)
                    UNITS "sec"
                    MAX-ACCESS read-only
                    STATUS current
                    DESCRIPTION "Countdown safety time"
                    DEFVAL { 0 }
                    ::= { integerObjects 1258 }

        -- 1.3.6.1.4.1.9839.2.1.3.1259
        saft-cntdwn-comp-2-tandem OBJECT-TYPE
                    SYNTAX Integer32 (0..32000)
                    UNITS "sec"
                    MAX-ACCESS read-only
                    STATUS current
                    DESCRIPTION "Countdown of safety OFF  time ( to switch ON)"
                    DEFVAL { 0 }
                    ::= { integerObjects 1259 }

        -- 1.3.6.1.4.1.9839.2.1.3.1260
        minont-cntdwn-comp-2-tandem OBJECT-TYPE
                    SYNTAX Integer32 (0..32000)
                    UNITS "sec"
                    MAX-ACCESS read-only
                    STATUS current
                    DESCRIPTION "Countdown of minimum On time (to switch OFF)"
                    DEFVAL { 0 }
                    ::= { integerObjects 1260 }

        -- 1.3.6.1.4.1.9839.2.1.3.1300
        valve-number OBJECT-TYPE
                    SYNTAX Integer32 (0..2)
                    UNITS "N/A"
                    MAX-ACCESS read-write
                    STATUS current
                    DESCRIPTION "Number of valve used ---> 1 = Single,   2 = Twin"
                    DEFVAL { 1 }
                    ::= { integerObjects 1300 }

        -- 1.3.6.1.4.1.9839.2.1.3.1301
        refrigerant-valve-a OBJECT-TYPE
                    SYNTAX Integer32 (-32768..32767)
                    UNITS "N/A"
                    MAX-ACCESS read-only
                    STATUS current
                    DESCRIPTION "N/A"
                    DEFVAL { 0 }
                    ::= { integerObjects 1301 }

        -- 1.3.6.1.4.1.9839.2.1.3.1302
        refrigerant-valve-b OBJECT-TYPE
                    SYNTAX Integer32 (-32768..32767)
                    UNITS "N/A"
                    MAX-ACCESS read-only
                    STATUS current
                    DESCRIPTION "N/A"
                    DEFVAL { 0 }
                    ::= { integerObjects 1302 }

        -- 1.3.6.1.4.1.9839.2.1.3.1303
        valve-a-capacity OBJECT-TYPE
                    SYNTAX Integer32 (-32768..32767)
                    UNITS "N/A"
                    MAX-ACCESS read-only
                    STATUS current
                    DESCRIPTION "N/A"
                    DEFVAL { 0 }
                    ::= { integerObjects 1303 }

        -- 1.3.6.1.4.1.9839.2.1.3.1304
        valve-b-capacity OBJECT-TYPE
                    SYNTAX Integer32 (-32768..32767)
                    UNITS "N/A"
                    MAX-ACCESS read-only
                    STATUS current
                    DESCRIPTION "N/A"
                    DEFVAL { 0 }
                    ::= { integerObjects 1304 }

        -- 1.3.6.1.4.1.9839.2.1.3.1305
        regsubtyp-evds-1 OBJECT-TYPE
                    SYNTAX Integer32 (1..3)
                    UNITS "N/A"
                    MAX-ACCESS read-only
                    STATUS current
                    DESCRIPTION "Type of sub-regulation"
                    ::= { integerObjects 1305 }

        -- 1.3.6.1.4.1.9839.2.1.3.1306
        s1-valueextended-evds-1 OBJECT-TYPE
                    SYNTAX Integer32 (0..9999)
                    UNITS "N/A"
                    MAX-ACCESS read-only
                    STATUS current
                    DESCRIPTION "S1 probe: pressure value with high precision (kPa/psi)"
                    DEFVAL { 0 }
                    ::= { integerObjects 1306 }

        -- 1.3.6.1.4.1.9839.2.1.3.1307
        s3-valueextended-evds-1 OBJECT-TYPE
                    SYNTAX Integer32 (0..32000)
                    UNITS "bar"
                    MAX-ACCESS read-only
                    STATUS current
                    DESCRIPTION "S3 probe: pressure value with high precision (kPa/psi)"
                    DEFVAL { 0 }
                    ::= { integerObjects 1307 }

        -- 1.3.6.1.4.1.9839.2.1.3.1308
        evd-1.i4-eev-position-steps OBJECT-TYPE
                    SYNTAX Integer32 (0..9999)
                    UNITS "N/A"
                    MAX-ACCESS read-only
                    STATUS current
                    DESCRIPTION "EEV position - Valve A"
                    DEFVAL { 0 }
                    ::= { integerObjects 1308 }

        -- 1.3.6.1.4.1.9839.2.1.3.1309
        evd-1.i49-eev-position-steps-2nd OBJECT-TYPE
                    SYNTAX Integer32 (0..9999)
                    UNITS "N/A"
                    MAX-ACCESS read-only
                    STATUS current
                    DESCRIPTION "EEV position - Valve B"
                    DEFVAL { 0 }
                    ::= { integerObjects 1309 }

        -- 1.3.6.1.4.1.9839.2.1.3.1310
        evd-1.i37-start-eev-opening-ratio-msk OBJECT-TYPE
                    SYNTAX Integer32 (0..100)
                    UNITS "N/A"
                    MAX-ACCESS read-write
                    STATUS current
                    DESCRIPTION "Open valve startup  (capacity ratio EVAP / EEV) - Valve A"
                    DEFVAL { 50 }
                    ::= { integerObjects 1310 }

        -- 1.3.6.1.4.1.9839.2.1.3.1311
        evd-1.i60-start-eev-open-ratio-2nd-msk OBJECT-TYPE
                    SYNTAX Integer32 (0..100)
                    UNITS "N/A"
                    MAX-ACCESS read-write
                    STATUS current
                    DESCRIPTION "Open valve startup  (capacity ratio EVAP / EEV) - Valve B"
                    DEFVAL { 0 }
                    ::= { integerObjects 1311 }

        -- 1.3.6.1.4.1.9839.2.1.3.1312
        eev-status-a OBJECT-TYPE
                    SYNTAX Integer32 (0..99)
                    UNITS "N/A"
                    MAX-ACCESS read-only
                    STATUS current
                    DESCRIPTION "N/A"
                    DEFVAL { 0 }
                    ::= { integerObjects 1312 }

        -- 1.3.6.1.4.1.9839.2.1.3.1313
        eev-status-b OBJECT-TYPE
                    SYNTAX Integer32 (0..99)
                    UNITS "N/A"
                    MAX-ACCESS read-only
                    STATUS current
                    DESCRIPTION "N/A"
                    DEFVAL { 0 }
                    ::= { integerObjects 1313 }

        -- 1.3.6.1.4.1.9839.2.1.3.1400
        alrmcode-cpy OBJECT-TYPE
                    SYNTAX Integer32 (0..15)
                    UNITS "N/A"
                    MAX-ACCESS read-only
                    STATUS current
                    DESCRIPTION "Alarm code to be used in alarm mask"
                    DEFVAL { 0 }
                    ::= { integerObjects 1400 }

        -- 1.3.6.1.4.1.9839.2.1.3.1401
        deviceaddr-cpy OBJECT-TYPE
                    SYNTAX Integer32 (0..9999)
                    UNITS "N/A"
                    MAX-ACCESS read-write
                    STATUS current
                    DESCRIPTION "N/A"
                    DEFVAL { 0 }
                    ::= { integerObjects 1401 }

        -- 1.3.6.1.4.1.9839.2.1.3.1402
        prod-request-cpy OBJECT-TYPE
                    SYNTAX Integer32 (0..32767)
                    UNITS "N/A"
                    MAX-ACCESS read-write
                    STATUS current
                    DESCRIPTION "N/A"
                    DEFVAL { 0 }
                    ::= { integerObjects 1402 }

        -- 1.3.6.1.4.1.9839.2.1.3.1403
        warningcode-cpy OBJECT-TYPE
                    SYNTAX Integer32 (0..5)
                    UNITS "N/A"
                    MAX-ACCESS read-only
                    STATUS current
                    DESCRIPTION "N/A"
                    DEFVAL { 0 }
                    ::= { integerObjects 1403 }

        -- 1.3.6.1.4.1.9839.2.1.3.1404
        cpy-1.i05-b1-optionalfunctions-msk OBJECT-TYPE
                    SYNTAX Integer32 (0..255)
                    UNITS "N/A"
                    MAX-ACCESS read-write
                    STATUS current
                    DESCRIPTION "Optional functions in mask"
                    DEFVAL { 0 }
                    ::= { integerObjects 1404 }

        -- 1.3.6.1.4.1.9839.2.1.3.1405
        cpy-1.i06-b2-delayofftime-msk OBJECT-TYPE
                    SYNTAX Integer32 (0..120)
                    UNITS "N/A"
                    MAX-ACCESS read-write
                    STATUS current
                    DESCRIPTION "Delay off time"
                    DEFVAL { 0 }
                    ::= { integerObjects 1405 }

        -- 1.3.6.1.4.1.9839.2.1.3.1406
        cpy-1.i07-b4-conductw-msk OBJECT-TYPE
                    SYNTAX Integer32 (0..1250)
                    UNITS "N/A"
                    MAX-ACCESS read-write
                    STATUS current
                    DESCRIPTION "Water conductivity (0 = automatic measurement)"
                    DEFVAL { 0 }
                    ::= { integerObjects 1406 }

        -- 1.3.6.1.4.1.9839.2.1.3.1407
        cpy-1.i08-b5-conductw-warningthrsh-msk OBJECT-TYPE
                    SYNTAX Integer32 (0..2000)
                    UNITS "N/A"
                    MAX-ACCESS read-write
                    STATUS current
                    DESCRIPTION "Water conductivity warning threshold"
                    DEFVAL { 0 }
                    ::= { integerObjects 1407 }

        -- 1.3.6.1.4.1.9839.2.1.3.1408
        cpy-1.i09-b6-conductw-alrmthrsh-msk OBJECT-TYPE
                    SYNTAX Integer32 (0..2000)
                    UNITS "N/A"
                    MAX-ACCESS read-write
                    STATUS current
                    DESCRIPTION "Water conductivity alarm threshold"
                    DEFVAL { 0 }
                    ::= { integerObjects 1408 }

        -- 1.3.6.1.4.1.9839.2.1.3.1409
        cpy-1.i10-b7-foamdetectionthrsh-msk OBJECT-TYPE
                    SYNTAX Integer32 (0..100)
                    UNITS "N/A"
                    MAX-ACCESS read-write
                    STATUS current
                    DESCRIPTION "Foam detection threshold (0 = no foam detection)"
                    DEFVAL { 0 }
                    ::= { integerObjects 1409 }

        -- 1.3.6.1.4.1.9839.2.1.3.1410
        cpy-1.i11-b8-drndilutionfreqadj-msk OBJECT-TYPE
                    SYNTAX Integer32 (50..200)
                    UNITS "%"
                    MAX-ACCESS read-write
                    STATUS current
                    DESCRIPTION "Adjust dilution drain frequency in mask"
                    DEFVAL { 50 }
                    ::= { integerObjects 1410 }

        -- 1.3.6.1.4.1.9839.2.1.3.1411
        cpy-1.i14-c4-baudrate-msk OBJECT-TYPE
                    SYNTAX Integer32 (0..1)
                    UNITS "N/A"
                    MAX-ACCESS read-write
                    STATUS current
                    DESCRIPTION "Baudrate of the CPY for both ModBus and Carel"
                    DEFVAL { 0 }
                    ::= { integerObjects 1411 }

        -- 1.3.6.1.4.1.9839.2.1.3.1412
        cpy-1.i15-c5-frameconfig-msk OBJECT-TYPE
                    SYNTAX Integer32 (0..11)
                    UNITS "N/A"
                    MAX-ACCESS read-write
                    STATUS current
                    DESCRIPTION "Frame configuration of the CPY for ModBus. See documentation for details."
                    DEFVAL { 0 }
                    ::= { integerObjects 1412 }

        -- 1.3.6.1.4.1.9839.2.1.3.1413
        cpy-1.i17-b9-drndurationadj-msk OBJECT-TYPE
                    SYNTAX Integer32 (50..200)
                    UNITS "%"
                    MAX-ACCESS read-write
                    STATUS current
                    DESCRIPTION "Adjust duration drain in mask"
                    DEFVAL { 50 }
                    ::= { integerObjects 1413 }

        -- 1.3.6.1.4.1.9839.2.1.3.1414
        cpy-1.i18-bb-cylindermaintlimt-msk OBJECT-TYPE
                    SYNTAX Integer32 (0..4000)
                    UNITS "N/A"
                    MAX-ACCESS read-write
                    STATUS current
                    DESCRIPTION "Maintenance time limit (0 = no life warning and maintenance alarm)"
                    DEFVAL { 0 }
                    ::= { integerObjects 1414 }

        -- 1.3.6.1.4.1.9839.2.1.3.1415
        cpy-1.i19-be-periodicdrnhourswait-msk OBJECT-TYPE
                    SYNTAX Integer32 (0..240)
                    UNITS "N/A"
                    MAX-ACCESS read-write
                    STATUS current
                    DESCRIPTION "Hours to wait for periodic drain"
                    DEFVAL { 0 }
                    ::= { integerObjects 1415 }

        -- 1.3.6.1.4.1.9839.2.1.3.1416
        cpy-1.i20-bf-inactivitydrndayswait-msk OBJECT-TYPE
                    SYNTAX Integer32 (1..199)
                    UNITS "N/A"
                    MAX-ACCESS read-write
                    STATUS current
                    DESCRIPTION "Days to wait for inactivity drain"
                    DEFVAL { 1 }
                    ::= { integerObjects 1416 }

        -- 1.3.6.1.4.1.9839.2.1.3.1417
        cpy-1.i79-cpy-uey-model-msk OBJECT-TYPE
                    SYNTAX Integer32 (0..999)
                    UNITS "N/A"
                    MAX-ACCESS read-write
                    STATUS current
                    DESCRIPTION "CPY/UEY model in mask"
                    DEFVAL { 0 }
                    ::= { integerObjects 1417 }

        -- 1.3.6.1.4.1.9839.2.1.3.1418
        cpy-1.i46-humstate OBJECT-TYPE
                    SYNTAX Integer32 (0..11)
                    UNITS "N/A"
                    MAX-ACCESS read-only
                    STATUS current
                    DESCRIPTION "Humidifier status (0 = not active (no request, shutdown or disabled); 1 = start evaporation cycle; 2 = water fi ll in progress; 3 = evaporation in progress ; 4 = AFS drain ; 5 = water drain (to dilute or manual); 6 = end of water drain; 7 = complete drain for long inactivity; 8 = complete drain from manual or network control; 9 = no water management; 10 = pre-wash; 11 = periodical drain)"
                    DEFVAL { 0 }
                    ::= { integerObjects 1418 }

        -- 1.3.6.1.4.1.9839.2.1.3.1419
        cpy-1.i49-conductivity OBJECT-TYPE
                    SYNTAX Integer32 (0..2000)
                    UNITS "N/A"
                    MAX-ACCESS read-only
                    STATUS current
                    DESCRIPTION "Actual value of conductivity"
                    DEFVAL { 0 }
                    ::= { integerObjects 1419 }

        -- 1.3.6.1.4.1.9839.2.1.3.1420
        cpy-model OBJECT-TYPE
                    SYNTAX Integer32 (0..99)
                    UNITS "N/A"
                    MAX-ACCESS read-write
                    STATUS current
                    DESCRIPTION "N/A"
                    DEFVAL { 0 }
                    ::= { integerObjects 1420 }

        -- 1.3.6.1.4.1.9839.2.1.3.1500
        energy-meters-1.system-type OBJECT-TYPE
                    SYNTAX Integer32 (0..4)
                    UNITS "N/A"
                    MAX-ACCESS read-write
                    STATUS current
                    DESCRIPTION "$$$EMPTYCELL$$$"
                    DEFVAL { 0 }
                    ::= { integerObjects 1500 }

        -- 1.3.6.1.4.1.9839.2.1.3.1501
        energy-meters-1.reset-tmp OBJECT-TYPE
                    SYNTAX Integer32 (0..1)
                    UNITS "N/A"
                    MAX-ACCESS read-write
                    STATUS current
                    DESCRIPTION "Reset the counter"
                    DEFVAL { 0 }
                    ::= { integerObjects 1501 }

        -- 1.3.6.1.4.1.9839.2.1.3.1502
        energy-meters-1.ct-l-msk OBJECT-TYPE
                    SYNTAX Integer32 (0..9999)
                    UNITS "N/A"
                    MAX-ACCESS read-only
                    STATUS current
                    DESCRIPTION "$$$EMPTYCELL$$$"
                    DEFVAL { 0 }
                    ::= { integerObjects 1502 }

        -- 1.3.6.1.4.1.9839.2.1.3.1503
        energy-meters-1.ct-h-msk OBJECT-TYPE
                    SYNTAX Integer32 (0..9999)
                    UNITS "N/A"
                    MAX-ACCESS read-only
                    STATUS current
                    DESCRIPTION "$$$EMPTYCELL$$$"
                    DEFVAL { 0 }
                    ::= { integerObjects 1503 }

        -- 1.3.6.1.4.1.9839.2.1.3.1504
        energy-meters-1.vt-l-msk OBJECT-TYPE
                    SYNTAX Integer32 (0..9999)
                    UNITS "N/A"
                    MAX-ACCESS read-only
                    STATUS current
                    DESCRIPTION "$$$EMPTYCELL$$$"
                    DEFVAL { 0 }
                    ::= { integerObjects 1504 }

        -- 1.3.6.1.4.1.9839.2.1.3.1505
        energy-meters-1.vt-h-msk OBJECT-TYPE
                    SYNTAX Integer32 (0..9999)
                    UNITS "N/A"
                    MAX-ACCESS read-only
                    STATUS current
                    DESCRIPTION "$$$EMPTYCELL$$$"
                    DEFVAL { 0 }
                    ::= { integerObjects 1505 }

        -- 1.3.6.1.4.1.9839.2.1.3.1506
        energy-meters-1.power-factor-ll-msk OBJECT-TYPE
                    SYNTAX Integer32 (0..9999)
                    UNITS "N/A"
                    MAX-ACCESS read-only
                    STATUS current
                    DESCRIPTION "Integer value for mask"
                    DEFVAL { 0 }
                    ::= { integerObjects 1506 }

        -- 1.3.6.1.4.1.9839.2.1.3.1507
        energy-meters-1.power-factor-l-msk OBJECT-TYPE
                    SYNTAX Integer32 (0..9999)
                    UNITS "N/A"
                    MAX-ACCESS read-only
                    STATUS current
                    DESCRIPTION "Integer value for mask"
                    DEFVAL { 0 }
                    ::= { integerObjects 1507 }

        -- 1.3.6.1.4.1.9839.2.1.3.1508
        energy-meters-1.power-l-msk OBJECT-TYPE
                    SYNTAX Integer32 (0..9999)
                    UNITS "N/A"
                    MAX-ACCESS read-only
                    STATUS current
                    DESCRIPTION "Integer value for mask"
                    DEFVAL { 0 }
                    ::= { integerObjects 1508 }

        -- 1.3.6.1.4.1.9839.2.1.3.1509
        energy-meters-1.power-m-msk OBJECT-TYPE
                    SYNTAX Integer32 (0..9999)
                    UNITS "N/A"
                    MAX-ACCESS read-only
                    STATUS current
                    DESCRIPTION "Integer value for mask"
                    DEFVAL { 0 }
                    ::= { integerObjects 1509 }

        -- 1.3.6.1.4.1.9839.2.1.3.1510
        energy-meters-1.power-h-msk OBJECT-TYPE
                    SYNTAX Integer32 (0..9999)
                    UNITS "N/A"
                    MAX-ACCESS read-only
                    STATUS current
                    DESCRIPTION "Integer value for mask"
                    DEFVAL { 0 }
                    ::= { integerObjects 1510 }

        -- 1.3.6.1.4.1.9839.2.1.3.1511
        energy-meters-1.energy-l-msk OBJECT-TYPE
                    SYNTAX Integer32 (0..999)
                    UNITS "N/A"
                    MAX-ACCESS read-only
                    STATUS current
                    DESCRIPTION "Integer value for mask"
                    DEFVAL { 0 }
                    ::= { integerObjects 1511 }

        -- 1.3.6.1.4.1.9839.2.1.3.1512
        energy-meters-1.energy-m-msk OBJECT-TYPE
                    SYNTAX Integer32 (0..9999)
                    UNITS "N/A"
                    MAX-ACCESS read-only
                    STATUS current
                    DESCRIPTION "Integer value for mask"
                    DEFVAL { 0 }
                    ::= { integerObjects 1512 }

        -- 1.3.6.1.4.1.9839.2.1.3.1513
        energy-meters-1.energy-h-msk OBJECT-TYPE
                    SYNTAX Integer32 (0..9999)
                    UNITS "N/A"
                    MAX-ACCESS read-only
                    STATUS current
                    DESCRIPTION "Integer value for mask"
                    DEFVAL { 0 }
                    ::= { integerObjects 1513 }

        -- 1.3.6.1.4.1.9839.2.1.3.1514
        energy-meters-1.apparent-energy-l-msk OBJECT-TYPE
                    SYNTAX Integer32 (0..999)
                    UNITS "N/A"
                    MAX-ACCESS read-only
                    STATUS current
                    DESCRIPTION "Integer value for mask"
                    DEFVAL { 0 }
                    ::= { integerObjects 1514 }

        -- 1.3.6.1.4.1.9839.2.1.3.1515
        energy-meters-1.apparent-energy-h-msk OBJECT-TYPE
                    SYNTAX Integer32 (0..9999)
                    UNITS "N/A"
                    MAX-ACCESS read-only
                    STATUS current
                    DESCRIPTION "Integer value for mask"
                    DEFVAL { 0 }
                    ::= { integerObjects 1515 }

        -- 1.3.6.1.4.1.9839.2.1.3.1516
        energy-meters-1.apparent-energy-m-msk OBJECT-TYPE
                    SYNTAX Integer32 (0..9999)
                    UNITS "N/A"
                    MAX-ACCESS read-only
                    STATUS current
                    DESCRIPTION "Integer value for mask"
                    DEFVAL { 0 }
                    ::= { integerObjects 1516 }

        -- 1.3.6.1.4.1.9839.2.1.3.1517
        energy-meters-1.voltage-1-l-spv OBJECT-TYPE
                    SYNTAX Integer32 (0..9999)
                    UNITS "V"
                    MAX-ACCESS read-only
                    STATUS current
                    DESCRIPTION "Voltage 1"
                    DEFVAL { 0 }
                    ::= { integerObjects 1517 }

        -- 1.3.6.1.4.1.9839.2.1.3.1518
        energy-meters-1.voltage-2-l-spv OBJECT-TYPE
                    SYNTAX Integer32 (0..9999)
                    UNITS "V"
                    MAX-ACCESS read-only
                    STATUS current
                    DESCRIPTION "Voltage 2"
                    DEFVAL { 0 }
                    ::= { integerObjects 1518 }

        -- 1.3.6.1.4.1.9839.2.1.3.1519
        energy-meters-1.voltage-3-l-spv OBJECT-TYPE
                    SYNTAX Integer32 (0..9999)
                    UNITS "V"
                    MAX-ACCESS read-only
                    STATUS current
                    DESCRIPTION "Voltage 3"
                    DEFVAL { 0 }
                    ::= { integerObjects 1519 }

        -- 1.3.6.1.4.1.9839.2.1.3.1520
        energy-meters-1.voltage-l3-l1-l-spv OBJECT-TYPE
                    SYNTAX Integer32 (0..9999)
                    UNITS "V"
                    MAX-ACCESS read-only
                    STATUS current
                    DESCRIPTION "Voltage L3-L1"
                    DEFVAL { 0 }
                    ::= { integerObjects 1520 }

        -- 1.3.6.1.4.1.9839.2.1.3.1521
        energy-meters-1.voltage-l2-l3-l-spv OBJECT-TYPE
                    SYNTAX Integer32 (0..9999)
                    UNITS "V"
                    MAX-ACCESS read-only
                    STATUS current
                    DESCRIPTION "Voltage L2-L3"
                    DEFVAL { 0 }
                    ::= { integerObjects 1521 }

        -- 1.3.6.1.4.1.9839.2.1.3.1522
        energy-meters-1.voltage-l1-l2-l-spv OBJECT-TYPE
                    SYNTAX Integer32 (0..9999)
                    UNITS "V"
                    MAX-ACCESS read-only
                    STATUS current
                    DESCRIPTION "Voltage L1-L2"
                    DEFVAL { 0 }
                    ::= { integerObjects 1522 }

        -- 1.3.6.1.4.1.9839.2.1.3.1600
        danfoss-act-rpm OBJECT-TYPE
                    SYNTAX Integer32 (0..32767)
                    UNITS "N/A"
                    MAX-ACCESS read-write
                    STATUS current
                    DESCRIPTION "N/A"
                    DEFVAL { 0 }
                    ::= { integerObjects 1600 }

        -- 1.3.6.1.4.1.9839.2.1.3.1601
        danfoss-req-rpm OBJECT-TYPE
                    SYNTAX Integer32 (0..32767)
                    UNITS "N/A"
                    MAX-ACCESS read-only
                    STATUS current
                    DESCRIPTION "N/A"
                    DEFVAL { 0 }
                    ::= { integerObjects 1601 }

        -- 1.3.6.1.4.1.9839.2.1.3.1602
        danfoss-min-rpm OBJECT-TYPE
                    SYNTAX Integer32 (0..32767)
                    UNITS "N/A"
                    MAX-ACCESS read-write
                    STATUS current
                    DESCRIPTION "N/A"
                    DEFVAL { 0 }
                    ::= { integerObjects 1602 }

        -- 1.3.6.1.4.1.9839.2.1.3.1603
        danfoss-max-rpm OBJECT-TYPE
                    SYNTAX Integer32 (0..32767)
                    UNITS "N/A"
                    MAX-ACCESS read-write
                    STATUS current
                    DESCRIPTION "N/A"
                    DEFVAL { 0 }
                    ::= { integerObjects 1603 }

        -- 1.3.6.1.4.1.9839.2.1.3.1604
        saft-cntdwn-danf-inv-1 OBJECT-TYPE
                    SYNTAX Integer32 (0..32767)
                    UNITS "sec"
                    MAX-ACCESS read-only
                    STATUS current
                    DESCRIPTION "Countdown of safety OFF  time ( to switch ON)"
                    DEFVAL { 0 }
                    ::= { integerObjects 1604 }

        -- 1.3.6.1.4.1.9839.2.1.3.1605
        minont-cntdwn-danf-inv-1 OBJECT-TYPE
                    SYNTAX Integer32 (0..32767)
                    UNITS "sec"
                    MAX-ACCESS read-only
                    STATUS current
                    DESCRIPTION "Countdown of minimum On time (to switch OFF)"
                    DEFVAL { 0 }
                    ::= { integerObjects 1605 }

        -- 1.3.6.1.4.1.9839.2.1.3.1606
        devavbl-danf-inv-1 OBJECT-TYPE
                    SYNTAX Integer32 (0..99)
                    UNITS "N/A"
                    MAX-ACCESS read-only
                    STATUS current
                    DESCRIPTION "Compressor status information for DeviceAvaliable List"
                    DEFVAL { 0 }
                    ::= { integerObjects 1606 }

        -- 1.3.6.1.4.1.9839.2.1.3.1607
        danfoss-inv-1.control-card-temp OBJECT-TYPE
                    SYNTAX Integer32 (0..32767)
                    UNITS "N/A"
                    MAX-ACCESS read-only
                    STATUS current
                    DESCRIPTION "N/A"
                    DEFVAL { 0 }
                    ::= { integerObjects 1607 }

        -- 1.3.6.1.4.1.9839.2.1.3.1608
        danfoss-disch-temp OBJECT-TYPE
                    SYNTAX Integer32 (-999..999)
                    UNITS "C"
                    MAX-ACCESS read-only
                    STATUS current
                    DESCRIPTION "Danfoss compressor discharge temperature [_C]"
                    DEFVAL { 0 }
                    ::= { integerObjects 1608 }

        -- 1.3.6.1.4.1.9839.2.1.3.1609
        danfoss-inverter-request OBJECT-TYPE
                    SYNTAX Integer32 (-32768..32767)
                    UNITS "N/A"
                    MAX-ACCESS read-only
                    STATUS current
                    DESCRIPTION "N/A"
                    DEFVAL { 0 }
                    ::= { integerObjects 1609 }

        -- 1.3.6.1.4.1.9839.2.1.3.1610
        danfoss-act-cool-capacity-invert OBJECT-TYPE
                    SYNTAX Integer32 (0..999)
                    UNITS "N/A"
                    MAX-ACCESS read-only
                    STATUS current
                    DESCRIPTION "N/A"
                    DEFVAL { 0 }
                    ::= { integerObjects 1610 }

        -- 1.3.6.1.4.1.9839.2.1.3.1611
        xdspalrmzone-danfoss OBJECT-TYPE
                    SYNTAX Integer32 (0..32767)
                    UNITS "N/A"
                    MAX-ACCESS read-only
                    STATUS current
                    DESCRIPTION "0=Null;1=OK;2=Max.comp.R.;3=Max.disch.P.;4=HCurr.;5=Max.suct.P.;6=Min.comp.R.;7=LowDP;8=Min.disch.P.;9=Min.suct.P."
                    DEFVAL { 0 }
                    ::= { integerObjects 1611 }

        -- 1.3.6.1.4.1.9839.2.1.3.1612
        showstate-tandem-danfoss OBJECT-TYPE
                    SYNTAX Integer32 (0..99)
                    UNITS "N/A"
                    MAX-ACCESS read-only
                    STATUS current
                    DESCRIPTION "State machine condition"
                    DEFVAL { 0 }
                    ::= { integerObjects 1612 }

        -- 1.3.6.1.4.1.9839.2.1.3.1613
        circcoolcap-a-evd-tandem-danfoss OBJECT-TYPE
                    SYNTAX Integer32 (0..100)
                    UNITS "N/A"
                    MAX-ACCESS read-write
                    STATUS current
                    DESCRIPTION "Circuit cooling capacity requirement for valve A"
                    DEFVAL { 0 }
                    ::= { integerObjects 1613 }

        -- 1.3.6.1.4.1.9839.2.1.3.1614
        danfoss-low-speed-thr OBJECT-TYPE
                    SYNTAX Integer32 (0..32767)
                    UNITS "N/A"
                    MAX-ACCESS read-write
                    STATUS current
                    DESCRIPTION "N/A"
                    DEFVAL { 0 }
                    ::= { integerObjects 1614 }

        -- 1.3.6.1.4.1.9839.2.1.3.1615
        rfrg-danfoss OBJECT-TYPE
                    SYNTAX Integer32 (0..14)
                    UNITS "N/A"
                    MAX-ACCESS read-write
                    STATUS current
                    DESCRIPTION "Gas type (1=R134a;3= R407C;4=R410A)"
                    DEFVAL { 4 }
                    ::= { integerObjects 1615 }

        -- 1.3.6.1.4.1.9839.2.1.3.1616
        hightemp-zone-danfoss OBJECT-TYPE
                    SYNTAX Integer32 (0..32767)
                    UNITS "N/A"
                    MAX-ACCESS read-only
                    STATUS current
                    DESCRIPTION "N/A"
                    DEFVAL { 0 }
                    ::= { integerObjects 1616 }

        -- 1.3.6.1.4.1.9839.2.1.3.1617
        envcntdwn-danfoss OBJECT-TYPE
                    SYNTAX Integer32 (0..32000)
                    UNITS "N/A"
                    MAX-ACCESS read-only
                    STATUS current
                    DESCRIPTION "Out of envelop timing countdown"
                    DEFVAL { 0 }
                    ::= { integerObjects 1617 }

        -- 1.3.6.1.4.1.9839.2.1.3.1618
        envoutmaxt-spec-danfoss OBJECT-TYPE
                    SYNTAX Integer32 (0..32000)
                    UNITS "sec"
                    MAX-ACCESS read-write
                    STATUS current
                    DESCRIPTION "Out of envelop alarm delay time to be used when specified by pin"
                    DEFVAL { 0 }
                    ::= { integerObjects 1618 }

        -- 1.3.6.1.4.1.9839.2.1.3.1619
        danfoss-bldc.countdown-al-dp OBJECT-TYPE
                    SYNTAX Integer32 (0..32000)
                    UNITS "sec"
                    MAX-ACCESS read-only
                    STATUS current
                    DESCRIPTION "Low delta pressure alarm countdown"
                    DEFVAL { 0 }
                    ::= { integerObjects 1619 }

        -- 1.3.6.1.4.1.9839.2.1.3.1620
        danfoss-inv-1.motor-current-int-part OBJECT-TYPE
                    SYNTAX Integer32 (0..32767)
                    UNITS "N/A"
                    MAX-ACCESS read-only
                    STATUS current
                    DESCRIPTION "N/A"
                    DEFVAL { 0 }
                    ::= { integerObjects 1620 }

        -- 1.3.6.1.4.1.9839.2.1.3.1621
        danfoss-inv-1.motor-power-int-part OBJECT-TYPE
                    SYNTAX Integer32 (0..32767)
                    UNITS "N/A"
                    MAX-ACCESS read-only
                    STATUS current
                    DESCRIPTION "N/A"
                    DEFVAL { 0 }
                    ::= { integerObjects 1621 }

        -- 1.3.6.1.4.1.9839.2.1.3.2001
        hwsw-chk.h-sw-version OBJECT-TYPE
                    SYNTAX Integer32 (0..99)
                    UNITS "N/A"
                    MAX-ACCESS read-only
                    STATUS current
                    DESCRIPTION "$$$EMPTYCELL$$$"
                    DEFVAL { 9 }
                    ::= { integerObjects 2001 }

        -- 1.3.6.1.4.1.9839.2.1.3.2002
        hwsw-chk.l-sw-version OBJECT-TYPE
                    SYNTAX Integer32 (0..9)
                    UNITS "N/A"
                    MAX-ACCESS read-only
                    STATUS current
                    DESCRIPTION "$$$EMPTYCELL$$$"
                    DEFVAL { 9 }
                    ::= { integerObjects 2002 }

        -- 1.3.6.1.4.1.9839.2.1.3.2003
        hwsw-chk.sw-beta OBJECT-TYPE
                    SYNTAX Integer32 (0..99)
                    UNITS "N/A"
                    MAX-ACCESS read-only
                    STATUS current
                    DESCRIPTION "$$$EMPTYCELL$$$"
                    DEFVAL { 9 }
                    ::= { integerObjects 2003 }

        -- 1.3.6.1.4.1.9839.2.1.3.2004
        hwsw-chk.sw-day OBJECT-TYPE
                    SYNTAX Integer32 (0..99)
                    UNITS "N/A"
                    MAX-ACCESS read-only
                    STATUS current
                    DESCRIPTION "$$$EMPTYCELL$$$"
                    DEFVAL { 0 }
                    ::= { integerObjects 2004 }

        -- 1.3.6.1.4.1.9839.2.1.3.2005
        hwsw-chk.sw-month OBJECT-TYPE
                    SYNTAX Integer32 (0..99)
                    UNITS "N/A"
                    MAX-ACCESS read-only
                    STATUS current
                    DESCRIPTION "$$$EMPTYCELL$$$"
                    DEFVAL { 0 }
                    ::= { integerObjects 2005 }

        -- 1.3.6.1.4.1.9839.2.1.3.2006
        hwsw-chk.sw-year OBJECT-TYPE
                    SYNTAX Integer32 (0..99)
                    UNITS "N/A"
                    MAX-ACCESS read-only
                    STATUS current
                    DESCRIPTION "$$$EMPTYCELL$$$"
                    DEFVAL { 0 }
                    ::= { integerObjects 2006 }


	
	END

--
-- CAREL-dencoccu.MIB
--
