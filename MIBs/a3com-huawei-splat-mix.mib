-- ------------------------------------------------------------------

-- Description：  HuaWei Lan Switch Dual Main Control MIB
--
-- Version: V1.1
-- History:
-- Revise History：1) 2003-03-27 Fuzhenyu created
-- V1.1 2004-10-12 updated by gaolong
--      Import NOTIFICATION-TYPE.
--      MAX-ACCESS clause value from write-only to read-write.
--      Substitute hwsMixTrapMib MODULE-IDENTITY with hwsMixTrapMib OBJECT IDENTIFIER.
-- ------------------------------------------------------------------

-- ------------------------------------------------------------------
--
-- Variable imported
--
-- ------------------------------------------------------------------

A3COM-HUAWEI-LswMix-MIB DEFINITIONS ::= BEGIN

IMPORTS
	
	MODULE-IDENTITY, OBJECT-TYPE, NOTIFICATION-TYPE
        FROM SNMPv2-SMI
    hwLswFrameIndex,hwLswSlotIndex
        FROM A3COM-HUAWEI-DEVICE-MIB
    lswCommon
        FROM A3COM-HUAWEI-OID-MIB;		

--  the document include the private data about device
-- ******************************beginning  ******************************
--
-- ------------------------------------------------------------------    
	hwLswMix MODULE-IDENTITY
	        LAST-UPDATED "200106290000Z"
	        ORGANIZATION ""
	        CONTACT-INFO
	        ""
	        DESCRIPTION
	        ""
	        REVISION "200106290000Z"
	        DESCRIPTION
	        ""
	        ::= { lswCommon  17 }


--  the document include the private data about device mix

hwLswLastSwitchDate OBJECT-TYPE
	SYNTAX INTEGER
	MAX-ACCESS  read-only
	STATUS  current
	DESCRIPTION "Date of last change mpu"
	::= { hwLswMix 1 }

hwLswLastSwitchTime OBJECT-TYPE
	SYNTAX INTEGER
	MAX-ACCESS  read-only
	STATUS  current
	DESCRIPTION "Date of last change mpu"
	::= { hwLswMix 2 }

hwLswMpuSwitchsNum OBJECT-TYPE
	SYNTAX INTEGER
	MAX-ACCESS  read-only
	STATUS  current
	DESCRIPTION "the number of switched mpu"
	::= { hwLswMix 3 }
	
hwLswMpuSwitch OBJECT-TYPE
	SYNTAX INTEGER{
    	switch(1)
    }
	MAX-ACCESS  read-write
	STATUS  current
	DESCRIPTION "the variable used to switch mpu, read operation not supported."
	::= { hwLswMix 4 }

--  the document include the private data about main card
hwLswXSlotTable OBJECT-TYPE
    SYNTAX  SEQUENCE OF HwLswXSlotEntry
    MAX-ACCESS  not-accessible
    STATUS  current
    DESCRIPTION
       "The source main table."
     ::= { hwLswMix 5 }

hwLswXSlotEntry OBJECT-TYPE
    SYNTAX  HwLswXSlotEntry
    MAX-ACCESS  not-accessible
    STATUS  current
    DESCRIPTION
       "An entry in the source main table."
    INDEX   { hwLswFrameIndex, hwLswSlotIndex }
     ::= { hwLswXSlotTable 1 }

HwLswXSlotEntry ::=
    SEQUENCE {
        hwLswMainCardBoardStatus        INTEGER
    }

hwLswMainCardBoardStatus OBJECT-TYPE
    SYNTAX  INTEGER{
    	master(1),
    	standby(2)
    }
    MAX-ACCESS  read-only
    STATUS  current
    DESCRIPTION
       "the value describing whether the card is master or standby"
     ::= { hwLswXSlotEntry 1 }

   hwsMixTrapMib OBJECT IDENTIFIER        ::= { hwLswMix  10 }

   hwSlaveSwitchOver NOTIFICATION-TYPE
      STATUS  current
      DESCRIPTION
              "Back board mode set OK"
      ::= { hwsMixTrapMib 1 }    
      
END
