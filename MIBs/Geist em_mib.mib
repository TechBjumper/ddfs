GEISTMFG-EM-SERIES-MIB DEFINITIONS ::= BEGIN

IMPORTS
	MODULE-IDENTITY, OBJECT-TYPE, enterprises, Unsigned32 FROM SNMPv2-SMI;

geistmfg MODULE-IDENTITY
	 LAST-UPDATED "200906170000Z"
	 ORGANIZATION "Geist Manufacturing"
	 CONTACT-INFO "support@geistmfg.com/800.432.3219"
	 DESCRIPTION "The MIB for EM Series PDU"
	 ::= { enterprises 21239 }
	

emMeter OBJECT IDENTIFIER
	::= { geistmfg 3 }


unitInfo OBJECT IDENTIFIER
	::= { emMeter 1 }


unitInfoTitle    OBJECT-TYPE
   SYNTAX DisplayString
   ACCESS read-only
   STATUS mandatory
   DESCRIPTION
      "Type of unit"
   ::= { unitInfo 1 }
 
unitInfoVersion    OBJECT-TYPE
   SYNTAX DisplayString
   ACCESS read-only
   STATUS mandatory
   DESCRIPTION
      "Unit version number"
   ::= { unitInfo 2 }
 
unitInfoName    OBJECT-TYPE
   SYNTAX DisplayString
   ACCESS read-only
   STATUS mandatory
   DESCRIPTION
      "Unit's friendly name"
   ::= { unitInfo 3 }
 
unitInfoMAC    OBJECT-TYPE
   SYNTAX DisplayString
   ACCESS read-only
   STATUS mandatory
   DESCRIPTION
      "MAC address of the unit"
   ::= { unitInfo 4 }
 
unitInfoIP    OBJECT-TYPE
   SYNTAX DisplayString
   ACCESS read-only
   STATUS mandatory
   DESCRIPTION
      "Unit's current IP address"
   ::= { unitInfo 5 }
 
unitInfoMainCount    OBJECT-TYPE
   SYNTAX INTEGER(0..8)
   ACCESS read-only
   STATUS mandatory
   DESCRIPTION
      "Number of Main (Total Amps) channels on the unit"
   ::= { unitInfo 6 }
 
unitInfoAuxCount    OBJECT-TYPE
   SYNTAX INTEGER(0..32)
   ACCESS read-only
   STATUS mandatory
   DESCRIPTION
      "Number of Auxillary (Outlet) channels on the unit"
   ::= { unitInfo 7 }
 

mainChannelTable 	OBJECT-TYPE
	DESCRIPTION
		"Contains entries for each Main (Total Amps) channel"
	::= { emMeter 2 }

mainChannelEntry	OBJECT-TYPE
	SYNTAX MainChannelEntry
	ACCESS not-accessible
	STATUS mandatory
	DESCRIPTION
		"Contains info for a specific Main (Total Amps) channel"		
	INDEX { mainChannelIndex }
	::= { mainChannelTable 1 }

MainChannelEntry ::= SEQUENCE {
	mainChannelIndex			INTEGER,
	mainChannelName				DisplayString,
	mainChannelFriendly		DisplayString,
	mainChannelDeciAmps		INTEGER,
	mainChannelGroup			DisplayString
}

mainChannelIndex 	OBJECT-TYPE
	SYNTAX INTEGER
	ACCESS read-only
	STATUS mandatory
	DESCRIPTION
		"Channel number"
	::= { mainChannelEntry 1 }

mainChannelName		OBJECT-TYPE
	SYNTAX DisplayString
	ACCESS read-only
	STATUS mandatory
	DESCRIPTION
		"Fixed identity for this channel"
	::= { mainChannelEntry 2 }

mainChannelFriendly		OBJECT-TYPE
	SYNTAX DisplayString
	ACCESS read-only
	STATUS mandatory
	DESCRIPTION
		"User selected channel name (if supported)"
	::= { mainChannelEntry 3 }

mainChannelDeciAmps		OBJECT-TYPE
	SYNTAX INTEGER
	UNITS "0.1 Amps"
	ACCESS read-only
	STATUS mandatory
	DESCRIPTION
		"Current reading for this channel in deci-amps (0.1 amps)"
	::= { mainChannelEntry 4 }

mainChannelGroup		OBJECT-TYPE
	SYNTAX DisplayString
	ACCESS read-only
	STATUS mandatory
	DESCRIPTION
		"Group name this channel belongs to"
	::= { mainChannelEntry 5 }



auxChannelTable 	OBJECT-TYPE
	DESCRIPTION
		"Contains entries for each Auxillary (Outlet) channel"
	::= { emMeter 3 }

auxChannelEntry		OBJECT-TYPE
	SYNTAX AuxChannelEntry
	ACCESS not-accessible
	STATUS mandatory
	DESCRIPTION
		"Contains info for a specific Auxillary (Outlet) channel"		
	INDEX { auxChannelIndex }
	::= { auxChannelTable 1 }

AuxChannelEntry ::= SEQUENCE {
	auxChannelIndex			INTEGER,
	auxChannelName				DisplayString,
	auxChannelFriendly		DisplayString,
	auxChannelDeciAmps		INTEGER,
	auxChannelGroup			DisplayString
}

auxChannelIndex 	OBJECT-TYPE
	SYNTAX INTEGER
	ACCESS read-only
	STATUS mandatory
	DESCRIPTION
		"Channel number"
	::= { auxChannelEntry 1 }

auxChannelName		OBJECT-TYPE
	SYNTAX DisplayString
	ACCESS read-only
	STATUS mandatory
	DESCRIPTION
		"Fixed identity for this channel"
	::= { auxChannelEntry 2 }

auxChannelFriendly		OBJECT-TYPE
	SYNTAX DisplayString
	ACCESS read-only
	STATUS mandatory
	DESCRIPTION
		"User selected channel name (if supported)"
	::= { auxChannelEntry 3 }

auxChannelDeciAmps		OBJECT-TYPE
	SYNTAX INTEGER
	UNITS "0.1 Amps"
	ACCESS read-only
	STATUS mandatory
	DESCRIPTION
		"Current reading for this channel in deci-amps (0.1 amps)"
	::= { auxChannelEntry 4 }

auxChannelGroup		OBJECT-TYPE
	SYNTAX DisplayString
	ACCESS read-only
	STATUS mandatory
	DESCRIPTION
		"Group name this channel belongs to"
	::= { auxChannelEntry 5 }


mainChannelDeciAmps01ALARM TRAP-TYPE
	ENTERPRISE emMeter
	VARIABLES { mainChannelDeciAmps }
	DESCRIPTION "Alarm Trap - Main Channel 1"
	::= 1
	
mainChannelDeciAmps02ALARM TRAP-TYPE
	ENTERPRISE emMeter
	VARIABLES { mainChannelDeciAmps }
	DESCRIPTION "Alarm Trap - Main Channel 2"
	::= 2
	
mainChannelDeciAmps03ALARM TRAP-TYPE
	ENTERPRISE emMeter
	VARIABLES { mainChannelDeciAmps }
	DESCRIPTION "Alarm Trap - Main Channel 3"
	::= 3
	
mainChannelDeciAmps04ALARM TRAP-TYPE
	ENTERPRISE emMeter
	VARIABLES { mainChannelDeciAmps }
	DESCRIPTION "Alarm Trap - Main Channel 4"
	::= 4
	
mainChannelDeciAmps05ALARM TRAP-TYPE
	ENTERPRISE emMeter
	VARIABLES { mainChannelDeciAmps }
	DESCRIPTION "Alarm Trap - Main Channel 5"
	::= 5
	
mainChannelDeciAmps06ALARM TRAP-TYPE
	ENTERPRISE emMeter
	VARIABLES { mainChannelDeciAmps }
	DESCRIPTION "Alarm Trap - Main Channel 6"
	::= 6
	
mainChannelDeciAmps07ALARM TRAP-TYPE
	ENTERPRISE emMeter
	VARIABLES { mainChannelDeciAmps }
	DESCRIPTION "Alarm Trap - Main Channel 7"
	::= 7
	
mainChannelDeciAmps08ALARM TRAP-TYPE
	ENTERPRISE emMeter
	VARIABLES { mainChannelDeciAmps }
	DESCRIPTION "Alarm Trap - Main Channel 8"
	::= 8
	

auxChannelDeciAmps01ALARM TRAP-TYPE
	ENTERPRISE emMeter
	VARIABLES { auxChannelDeciAmps }
	DESCRIPTION "Alarm Trap - Aux Channel 1"
	::= 9
	
auxChannelDeciAmps02ALARM TRAP-TYPE
	ENTERPRISE emMeter
	VARIABLES { auxChannelDeciAmps }
	DESCRIPTION "Alarm Trap - Aux Channel 2"
	::= 10
	
auxChannelDeciAmps03ALARM TRAP-TYPE
	ENTERPRISE emMeter
	VARIABLES { auxChannelDeciAmps }
	DESCRIPTION "Alarm Trap - Aux Channel 3"
	::= 11
	
auxChannelDeciAmps04ALARM TRAP-TYPE
	ENTERPRISE emMeter
	VARIABLES { auxChannelDeciAmps }
	DESCRIPTION "Alarm Trap - Aux Channel 4"
	::= 12

auxChannelDeciAmps05ALARM TRAP-TYPE
	ENTERPRISE emMeter
	VARIABLES { auxChannelDeciAmps }
	DESCRIPTION "Alarm Trap - Aux Channel 5"
	::= 13
	
auxChannelDeciAmps06ALARM TRAP-TYPE
	ENTERPRISE emMeter
	VARIABLES { auxChannelDeciAmps }
	DESCRIPTION "Alarm Trap - Aux Channel 6"
	::= 14
	
auxChannelDeciAmps07ALARM TRAP-TYPE
	ENTERPRISE emMeter
	VARIABLES { auxChannelDeciAmps }
	DESCRIPTION "Alarm Trap - Aux Channel 7"
	::= 15
	
auxChannelDeciAmps08ALARM TRAP-TYPE
	ENTERPRISE emMeter
	VARIABLES { auxChannelDeciAmps }
	DESCRIPTION "Alarm Trap - Aux Channel 8"
	::= 16

auxChannelDeciAmps09ALARM TRAP-TYPE
	ENTERPRISE emMeter
	VARIABLES { auxChannelDeciAmps }
	DESCRIPTION "Alarm Trap - Aux Channel 9"
	::= 17
	
auxChannelDeciAmps10ALARM TRAP-TYPE
	ENTERPRISE emMeter
	VARIABLES { auxChannelDeciAmps }
	DESCRIPTION "Alarm Trap - Aux Channel 10"
	::= 18
	
auxChannelDeciAmps11ALARM TRAP-TYPE
	ENTERPRISE emMeter
	VARIABLES { auxChannelDeciAmps }
	DESCRIPTION "Alarm Trap - Aux Channel 11"
	::= 19
	
auxChannelDeciAmps12ALARM TRAP-TYPE
	ENTERPRISE emMeter
	VARIABLES { auxChannelDeciAmps }
	DESCRIPTION "Alarm Trap - Aux Channel 12"
	::= 20

auxChannelDeciAmps13ALARM TRAP-TYPE
	ENTERPRISE emMeter
	VARIABLES { auxChannelDeciAmps }
	DESCRIPTION "Alarm Trap - Aux Channel 13"
	::= 21
	
auxChannelDeciAmps14ALARM TRAP-TYPE
	ENTERPRISE emMeter
	VARIABLES { auxChannelDeciAmps }
	DESCRIPTION "Alarm Trap - Aux Channel 14"
	::= 22
	
auxChannelDeciAmps15ALARM TRAP-TYPE
	ENTERPRISE emMeter
	VARIABLES { auxChannelDeciAmps }
	DESCRIPTION "Alarm Trap - Aux Channel 15"
	::= 23
	
auxChannelDeciAmps16ALARM TRAP-TYPE
	ENTERPRISE emMeter
	VARIABLES { auxChannelDeciAmps }
	DESCRIPTION "Alarm Trap - Aux Channel 16"
	::= 24
	
auxChannelDeciAmps17ALARM TRAP-TYPE
	ENTERPRISE emMeter
	VARIABLES { auxChannelDeciAmps }
	DESCRIPTION "Alarm Trap - Aux Channel 17"
	::= 25
	
auxChannelDeciAmps18ALARM TRAP-TYPE
	ENTERPRISE emMeter
	VARIABLES { auxChannelDeciAmps }
	DESCRIPTION "Alarm Trap - Aux Channel 18"
	::= 26
	
auxChannelDeciAmps19ALARM TRAP-TYPE
	ENTERPRISE emMeter
	VARIABLES { auxChannelDeciAmps }
	DESCRIPTION "Alarm Trap - Aux Channel 19"
	::= 27
	
auxChannelDeciAmps20ALARM TRAP-TYPE
	ENTERPRISE emMeter
	VARIABLES { auxChannelDeciAmps }
	DESCRIPTION "Alarm Trap - Aux Channel 20"
	::= 28

auxChannelDeciAmps21ALARM TRAP-TYPE
	ENTERPRISE emMeter
	VARIABLES { auxChannelDeciAmps }
	DESCRIPTION "Alarm Trap - Aux Channel 21"
	::= 29
	
auxChannelDeciAmps22ALARM TRAP-TYPE
	ENTERPRISE emMeter
	VARIABLES { auxChannelDeciAmps }
	DESCRIPTION "Alarm Trap - Aux Channel 22"
	::= 30
	
auxChannelDeciAmps23ALARM TRAP-TYPE
	ENTERPRISE emMeter
	VARIABLES { auxChannelDeciAmps }
	DESCRIPTION "Alarm Trap - Aux Channel 23"
	::= 31
	
auxChannelDeciAmps24ALARM TRAP-TYPE
	ENTERPRISE emMeter
	VARIABLES { auxChannelDeciAmps }
	DESCRIPTION "Alarm Trap - Aux Channel 24"
	::= 32

auxChannelDeciAmps25ALARM TRAP-TYPE
	ENTERPRISE emMeter
	VARIABLES { auxChannelDeciAmps }
	DESCRIPTION "Alarm Trap - Aux Channel 25"
	::= 33
	
auxChannelDeciAmps26ALARM TRAP-TYPE
	ENTERPRISE emMeter
	VARIABLES { auxChannelDeciAmps }
	DESCRIPTION "Alarm Trap - Aux Channel 26"
	::= 34
	
auxChannelDeciAmps27ALARM TRAP-TYPE
	ENTERPRISE emMeter
	VARIABLES { auxChannelDeciAmps }
	DESCRIPTION "Alarm Trap - Aux Channel 27"
	::= 35
	
auxChannelDeciAmps28ALARM TRAP-TYPE
	ENTERPRISE emMeter
	VARIABLES { auxChannelDeciAmps }
	DESCRIPTION "Alarm Trap - Aux Channel 28"
	::= 36

auxChannelDeciAmps29ALARM TRAP-TYPE
	ENTERPRISE emMeter
	VARIABLES { auxChannelDeciAmps }
	DESCRIPTION "Alarm Trap - Aux Channel 29"
	::= 37
	
auxChannelDeciAmps30ALARM TRAP-TYPE
	ENTERPRISE emMeter
	VARIABLES { auxChannelDeciAmps }
	DESCRIPTION "Alarm Trap - Aux Channel 30"
	::= 38
	
auxChannelDeciAmps31ALARM TRAP-TYPE
	ENTERPRISE emMeter
	VARIABLES { auxChannelDeciAmps }
	DESCRIPTION "Alarm Trap - Aux Channel 31"
	::= 39
	
auxChannelDeciAmps32ALARM TRAP-TYPE
	ENTERPRISE emMeter
	VARIABLES { auxChannelDeciAmps }
	DESCRIPTION "Alarm Trap - Aux Channel 32"
	::= 40

	

mainChannelDeciAmps01WARN TRAP-TYPE
	ENTERPRISE emMeter
	VARIABLES { mainChannelDeciAmps }
	DESCRIPTION "Warning Trap - Main Channel 1"
	::= 41
	
mainChannelDeciAmps02WARN TRAP-TYPE
	ENTERPRISE emMeter
	VARIABLES { mainChannelDeciAmps }
	DESCRIPTION "Warning Trap - Main Channel 2"
	::= 42
	
mainChannelDeciAmps03WARN TRAP-TYPE
	ENTERPRISE emMeter
	VARIABLES { mainChannelDeciAmps }
	DESCRIPTION "Warning Trap - Main Channel 3"
	::= 43
	
mainChannelDeciAmps04WARN TRAP-TYPE
	ENTERPRISE emMeter
	VARIABLES { mainChannelDeciAmps }
	DESCRIPTION "Warning Trap - Main Channel 4"
	::= 44
	
mainChannelDeciAmps05WARN TRAP-TYPE
	ENTERPRISE emMeter
	VARIABLES { mainChannelDeciAmps }
	DESCRIPTION "Warning Trap - Main Channel 5"
	::= 45
	
mainChannelDeciAmps06WARN TRAP-TYPE
	ENTERPRISE emMeter
	VARIABLES { mainChannelDeciAmps }
	DESCRIPTION "Warning Trap - Main Channel 6"
	::= 46
	
mainChannelDeciAmps07WARN TRAP-TYPE
	ENTERPRISE emMeter
	VARIABLES { mainChannelDeciAmps }
	DESCRIPTION "Warning Trap - Main Channel 7"
	::= 47
	
mainChannelDeciAmps08WARN TRAP-TYPE
	ENTERPRISE emMeter
	VARIABLES { mainChannelDeciAmps }
	DESCRIPTION "Warning Trap - Main Channel 8"
	::= 48
	

auxChannelDeciAmps01WARN TRAP-TYPE
	ENTERPRISE emMeter
	VARIABLES { auxChannelDeciAmps }
	DESCRIPTION "Warning Trap - Aux Channel 1"
	::= 49
	
auxChannelDeciAmps02WARN TRAP-TYPE
	ENTERPRISE emMeter
	VARIABLES { auxChannelDeciAmps }
	DESCRIPTION "Warning Trap - Aux Channel 2"
	::= 50
	
auxChannelDeciAmps03WARN TRAP-TYPE
	ENTERPRISE emMeter
	VARIABLES { auxChannelDeciAmps }
	DESCRIPTION "Warning Trap - Aux Channel 3"
	::= 51
	
auxChannelDeciAmps04WARN TRAP-TYPE
	ENTERPRISE emMeter
	VARIABLES { auxChannelDeciAmps }
	DESCRIPTION "Warning Trap - Aux Channel 4"
	::= 52

auxChannelDeciAmps05WARN TRAP-TYPE
	ENTERPRISE emMeter
	VARIABLES { auxChannelDeciAmps }
	DESCRIPTION "Warning Trap - Aux Channel 5"
	::= 53
	
auxChannelDeciAmps06WARN TRAP-TYPE
	ENTERPRISE emMeter
	VARIABLES { auxChannelDeciAmps }
	DESCRIPTION "Warning Trap - Aux Channel 6"
	::= 54
	
auxChannelDeciAmps07WARN TRAP-TYPE
	ENTERPRISE emMeter
	VARIABLES { auxChannelDeciAmps }
	DESCRIPTION "Warning Trap - Aux Channel 7"
	::= 55
	
auxChannelDeciAmps08WARN TRAP-TYPE
	ENTERPRISE emMeter
	VARIABLES { auxChannelDeciAmps }
	DESCRIPTION "Warning Trap - Aux Channel 8"
	::= 56

auxChannelDeciAmps09WARN TRAP-TYPE
	ENTERPRISE emMeter
	VARIABLES { auxChannelDeciAmps }
	DESCRIPTION "Warning Trap - Aux Channel 9"
	::= 57
	
auxChannelDeciAmps10WARN TRAP-TYPE
	ENTERPRISE emMeter
	VARIABLES { auxChannelDeciAmps }
	DESCRIPTION "Warning Trap - Aux Channel 10"
	::= 58
	
auxChannelDeciAmps11WARN TRAP-TYPE
	ENTERPRISE emMeter
	VARIABLES { auxChannelDeciAmps }
	DESCRIPTION "Warning Trap - Aux Channel 11"
	::= 59
	
auxChannelDeciAmps12WARN TRAP-TYPE
	ENTERPRISE emMeter
	VARIABLES { auxChannelDeciAmps }
	DESCRIPTION "Warning Trap - Aux Channel 12"
	::= 60

auxChannelDeciAmps13WARN TRAP-TYPE
	ENTERPRISE emMeter
	VARIABLES { auxChannelDeciAmps }
	DESCRIPTION "Warning Trap - Aux Channel 13"
	::= 61
	
auxChannelDeciAmps14WARN TRAP-TYPE
	ENTERPRISE emMeter
	VARIABLES { auxChannelDeciAmps }
	DESCRIPTION "Warning Trap - Aux Channel 14"
	::= 62
	
auxChannelDeciAmps15WARN TRAP-TYPE
	ENTERPRISE emMeter
	VARIABLES { auxChannelDeciAmps }
	DESCRIPTION "Warning Trap - Aux Channel 15"
	::= 63
	
auxChannelDeciAmps16WARN TRAP-TYPE
	ENTERPRISE emMeter
	VARIABLES { auxChannelDeciAmps }
	DESCRIPTION "Warning Trap - Aux Channel 16"
	::= 64
	
auxChannelDeciAmps17WARN TRAP-TYPE
	ENTERPRISE emMeter
	VARIABLES { auxChannelDeciAmps }
	DESCRIPTION "Warning Trap - Aux Channel 17"
	::= 65
	
auxChannelDeciAmps18WARN TRAP-TYPE
	ENTERPRISE emMeter
	VARIABLES { auxChannelDeciAmps }
	DESCRIPTION "Warning Trap - Aux Channel 18"
	::= 66
	
auxChannelDeciAmps19WARN TRAP-TYPE
	ENTERPRISE emMeter
	VARIABLES { auxChannelDeciAmps }
	DESCRIPTION "Warning Trap - Aux Channel 19"
	::= 67

auxChannelDeciAmps20WARN TRAP-TYPE
	ENTERPRISE emMeter
	VARIABLES { auxChannelDeciAmps }
	DESCRIPTION "Warning Trap - Aux Channel 20"
	::= 68

auxChannelDeciAmps21WARN TRAP-TYPE
	ENTERPRISE emMeter
	VARIABLES { auxChannelDeciAmps }
	DESCRIPTION "Warning Trap - Aux Channel 21"
	::= 69
	
auxChannelDeciAmps22WARN TRAP-TYPE
	ENTERPRISE emMeter
	VARIABLES { auxChannelDeciAmps }
	DESCRIPTION "Warning Trap - Aux Channel 22"
	::= 70
	
auxChannelDeciAmps23WARN TRAP-TYPE
	ENTERPRISE emMeter
	VARIABLES { auxChannelDeciAmps }
	DESCRIPTION "Warning Trap - Aux Channel 23"
	::= 71
	
auxChannelDeciAmps24WARN TRAP-TYPE
	ENTERPRISE emMeter
	VARIABLES { auxChannelDeciAmps }
	DESCRIPTION "Warning Trap - Aux Channel 24"
	::= 72

auxChannelDeciAmps25WARN TRAP-TYPE
	ENTERPRISE emMeter
	VARIABLES { auxChannelDeciAmps }
	DESCRIPTION "Warning Trap - Aux Channel 25"
	::= 73
	
auxChannelDeciAmps26WARN TRAP-TYPE
	ENTERPRISE emMeter
	VARIABLES { auxChannelDeciAmps }
	DESCRIPTION "Warning Trap - Aux Channel 26"
	::= 74
	
auxChannelDeciAmps27WARN TRAP-TYPE
	ENTERPRISE emMeter
	VARIABLES { auxChannelDeciAmps }
	DESCRIPTION "Warning Trap - Aux Channel 27"
	::= 75
	
auxChannelDeciAmps28WARN TRAP-TYPE
	ENTERPRISE emMeter
	VARIABLES { auxChannelDeciAmps }
	DESCRIPTION "Warning Trap - Aux Channel 28"
	::= 76

auxChannelDeciAmps29WARN TRAP-TYPE
	ENTERPRISE emMeter
	VARIABLES { auxChannelDeciAmps }
	DESCRIPTION "Warning Trap - Aux Channel 29"
	::= 77
	
auxChannelDeciAmps30WARN TRAP-TYPE
	ENTERPRISE emMeter
	VARIABLES { auxChannelDeciAmps }
	DESCRIPTION "Warning Trap - Aux Channel 30"
	::= 78
	
auxChannelDeciAmps31WARN TRAP-TYPE
	ENTERPRISE emMeter
	VARIABLES { auxChannelDeciAmps }
	DESCRIPTION "Warning Trap - Aux Channel 31"
	::= 79
	
auxChannelDeciAmps32WARN TRAP-TYPE
	ENTERPRISE emMeter
	VARIABLES { auxChannelDeciAmps }
	DESCRIPTION "Warning Trap - Aux Channel 32"
	::= 80


END
