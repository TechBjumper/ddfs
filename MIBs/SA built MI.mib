Pulizzi-Eatonb-2483C DEFINITIONS ::= BEGIN

IMPORTS
	NOTIFICATION-TYPE, OBJECT-TYPE, MODULE-IDENTITY, 
	enterprises, IpAddress, Integer32
		FROM SNMPv2-SMI
	DisplayString, MacAddress
		FROM SNMPv2-TC;

pulizzi MODULE-IDENTITY
	LAST-UPDATED "200711281703Z"
	ORGANIZATION 
		"Pulizzi Engineering, a Subsidiary of Eaton Electrical/PowerWare
		4300 W. 61st North, Sioux Falls, SD 57107"
	CONTACT-INFO 
		"Pulizzi Engineering, a Subsidiary of Eaton Electrical/PowerWare
		 4300 W. 61st North, Sioux Falls, SD 57107
	     Electrical Design Engineer: Curt Nesbitt"
	DESCRIPTION 
		"The Pulizzi-Eaton-2483C mib is loaded for the ICM2483C Intelligent Current Meter "
::= { enterprises 20677 }

icm2483c             OBJECT IDENTIFIER ::= { pulizzi 3 1 1 }
unitConfig           OBJECT IDENTIFIER ::= { icm2483c 1 }
networkSettings      OBJECT IDENTIFIER ::= { icm2483c 2 }
measurements         OBJECT IDENTIFIER ::= { icm2483c 3 }
                 
uptime  OBJECT-TYPE
SYNTAX 	TimeTicks
	MAX-ACCESS  	read-write
	STATUS 	current
	DESCRIPTION 
		""
	::= { unitConfig 1  }                 
                 
unitName  OBJECT-TYPE
	SYNTAX     OCTET STRING
	MAX-ACCESS read-write
	STATUS     current
	DESCRIPTION 
		"Unit Name"
	::= { unitConfig 2  }

lowThresholdChan1  OBJECT-TYPE
	SYNTAX     Integer32
	UNITS 	"Amps"
	MAX-ACCESS read-write
	STATUS     current
	DESCRIPTION 
		"Lo current threshold channel-1"
	::= { unitConfig 3  }

lowThresholdChan2  OBJECT-TYPE
	SYNTAX     Integer32
	UNITS 	"Amps"
	MAX-ACCESS read-write
	STATUS     current
	DESCRIPTION 
		""
	::= { unitConfig 4  }

lowThresholdChan3  OBJECT-TYPE
	SYNTAX     Integer32
	UNITS 	"Amps"
	MAX-ACCESS read-write
	STATUS     current
	DESCRIPTION 
		""
	::= { unitConfig 5  }

lowThresholdChan4 OBJECT-TYPE
	SYNTAX     Integer32
	UNITS 	"Amps"
	MAX-ACCESS read-write
	STATUS     current
	DESCRIPTION 
		""
	::= { unitConfig 6   }

lowThresholdChan5 OBJECT-TYPE
	SYNTAX     Integer32
	UNITS 	"Amps"
	MAX-ACCESS read-write
	STATUS     current
	DESCRIPTION 
		""
	::= { unitConfig 7  }

lowThresholdChan6 OBJECT-TYPE
	SYNTAX     Integer32
	UNITS 	"Amps"
	MAX-ACCESS read-write
	STATUS     current
	DESCRIPTION 
		""
	::= { unitConfig 8  }

lowThresholdChan7 OBJECT-TYPE
	SYNTAX     Integer32
	UNITS 	"Amps or Degrees Farenheit"
	MAX-ACCESS read-write
	STATUS     current
	DESCRIPTION 
		""
	::= { unitConfig 9  }

lowThresholdChan8 OBJECT-TYPE
	SYNTAX     Integer32
	UNITS 	"Amps or Degrees Farenheit"
	MAX-ACCESS read-write
	STATUS     current
	DESCRIPTION 
		""
	::= { unitConfig 10  }

highThresholdChan1  OBJECT-TYPE
	SYNTAX     Integer32
	UNITS 	"Amps"
	MAX-ACCESS read-write
	STATUS     current
	DESCRIPTION 
		""
	::= { unitConfig 11  }

highThresholdChan2  OBJECT-TYPE
	SYNTAX     Integer32
	UNITS 	"Amps"
	MAX-ACCESS read-write
	STATUS     current
	DESCRIPTION 
		""
	::= { unitConfig 12  }

highThresholdChan3  OBJECT-TYPE
	SYNTAX     Integer32
	UNITS 	"Amps"
	MAX-ACCESS read-write
	STATUS     current
	DESCRIPTION 
		""
	::= { unitConfig 13  }    
	
highThresholdChan4  OBJECT-TYPE
	SYNTAX     Integer32
	UNITS 	"Amps"
	MAX-ACCESS read-write
	STATUS     current
	DESCRIPTION 
		""
	::= { unitConfig 14  }

highThresholdChan5  OBJECT-TYPE
	SYNTAX     Integer32
	UNITS 	"Amps"
	MAX-ACCESS read-write
	STATUS     current
	DESCRIPTION 
		""
	::= { unitConfig 15   }

highThresholdChan6  OBJECT-TYPE
	SYNTAX     Integer32
	UNITS 	"Amps"
	MAX-ACCESS read-write
	STATUS     current
	DESCRIPTION 
		""
	::= { unitConfig 16  }

highThresholdChan7  OBJECT-TYPE
	SYNTAX     Integer32
	UNITS 	"Amps or Degrees Farenheit"
	MAX-ACCESS read-write
	STATUS     current
	DESCRIPTION 
		""
	::= { unitConfig 17  }

highThresholdChan8  OBJECT-TYPE
	SYNTAX     Integer32
	UNITS 	"Amps or Degrees Farenheit"
	MAX-ACCESS read-write
	STATUS     current
	DESCRIPTION 
		""
	::= { unitConfig 18  }

temperatureEnableChan7  OBJECT-TYPE
	SYNTAX     OCTET STRING
	MAX-ACCESS read-write
	STATUS     current
	DESCRIPTION 
		""
	::= { unitConfig 19 }

temperatureEnableChan8  OBJECT-TYPE
	SYNTAX     OCTET STRING
	MAX-ACCESS read-write
	STATUS     current
	DESCRIPTION 
		""
	::= { unitConfig 20 }

firmwareRevision  OBJECT-TYPE
	SYNTAX     OCTET STRING
	MAX-ACCESS read-only
	STATUS     current
	DESCRIPTION 
		""
	::= { unitConfig 21 }


unitIPAddress  OBJECT-TYPE
	SYNTAX     IpAddress
	MAX-ACCESS read-write
	STATUS     current
	DESCRIPTION 
		""
	::= { networkSettings 1   }

unitSubnetMask  OBJECT-TYPE
	SYNTAX     IpAddress
	MAX-ACCESS read-write
	STATUS     current
	DESCRIPTION 
		""
	::= { networkSettings 2  }

unitGateway  OBJECT-TYPE
	SYNTAX     IpAddress
	MAX-ACCESS read-write
	STATUS     current
	DESCRIPTION 
		""
	::= { networkSettings 3  }

unitMACAddress  OBJECT-TYPE
	SYNTAX     OCTET STRING
	MAX-ACCESS read-only
	STATUS     current
	DESCRIPTION 
		""
	::= { networkSettings 4  }


trapDestIP  OBJECT-TYPE
	SYNTAX     IpAddress
	MAX-ACCESS read-write
	STATUS     current
	DESCRIPTION 
		""
	::= { networkSettings 5  }


mailServerIP  OBJECT-TYPE
	SYNTAX     IpAddress
	MAX-ACCESS read-write
	STATUS     current
	DESCRIPTION 
		""
	::= { networkSettings 6  }

alertEmailAddress  OBJECT-TYPE
--	SYNTAX     IpAddress
	SYNTAX     OCTET STRING
	MAX-ACCESS read-write
	STATUS     current
	DESCRIPTION 
		""
	::= { networkSettings 7  }


chan1  OBJECT-TYPE
	SYNTAX     Integer32
	UNITS 	"Amps"
	MAX-ACCESS read-only
	STATUS     current
	DESCRIPTION 
		"current reading channel-1 Amps"
	::= { measurements 1  }

chan2  OBJECT-TYPE
	SYNTAX     Integer32
	UNITS 	"Amps"
	MAX-ACCESS read-only
	STATUS     current
	DESCRIPTION 
		""
	::= { measurements 2  }

chan3  OBJECT-TYPE
	SYNTAX     Integer32
	UNITS 	"Amps"
	MAX-ACCESS read-only
	STATUS     current
	DESCRIPTION 
		""
	::= { measurements 3  }

chan4  OBJECT-TYPE
	SYNTAX     Integer32
	UNITS 	"Amps"
	MAX-ACCESS read-only
	STATUS     current
	DESCRIPTION 
		""
	::= { measurements 4  }

chan5  OBJECT-TYPE
	SYNTAX     Integer32
	UNITS 	"Amps"
	MAX-ACCESS read-only
	STATUS     current
	DESCRIPTION 
		""
	::= { measurements 5  }

chan6  OBJECT-TYPE
	SYNTAX     Integer32
	UNITS 	"Amps"
	MAX-ACCESS read-only
	STATUS     current
	DESCRIPTION 
		""
	::= { measurements 6  }

chan7  OBJECT-TYPE
	SYNTAX     Integer32
	UNITS 	"Amps or Degrees Farenheit"
	MAX-ACCESS read-only
	STATUS     current
	DESCRIPTION 
		""
	::= { measurements 7  }

chan8  OBJECT-TYPE
	SYNTAX     Integer32
	UNITS 	"Amps or Degrees Farenheit"
	MAX-ACCESS read-only
	STATUS     current
	DESCRIPTION 
		""
	::= { measurements 8  }    


END
