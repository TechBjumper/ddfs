--
-- CAREL-uchiller_cmp.MIB
-- MIB generated by CAREL
-- Friday, 14 March 2003
--

    CAREL-uchiller_cmp-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        uchiller_cmpMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the uchiller_cmp device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- uchiller_cmpMIB OBJECT IDENTIFIER ::= { instruments 1 }
		
        -- 1.3.6.1.4.1.9839.2.1.1
        digitalObjects OBJECT IDENTIFIER ::= { uchiller_cmpMIB 1 }

        -- 1.3.6.1.4.1.9839.2.1.1.1
        est_inv OBJECT-TYPE
                    SYNTAX Integer32 (0..1)
                    UNITS "N/A"
                    MAX-ACCESS read-write
                    STATUS current
                    DESCRIPTION "Cooling - Heating"
                    ::= { digitalObjects 1 }

        -- 1.3.6.1.4.1.9839.2.1.1.2
        on_off_unita OBJECT-TYPE
                    SYNTAX Integer32 (0..1)
                    UNITS "N/A"
                    MAX-ACCESS read-write
                    STATUS current
                    DESCRIPTION "On-Off if remote On/Off is disabled"
                    ::= { digitalObjects 2 }

        -- 1.3.6.1.4.1.9839.2.1.1.5
        allarme_hp OBJECT-TYPE
                    SYNTAX Integer32 (0..1)
                    UNITS "N/A"
                    MAX-ACCESS read-only
                    STATUS current
                    DESCRIPTION "High pressure alarm"
                    ::= { digitalObjects 5 }

        -- 1.3.6.1.4.1.9839.2.1.1.6
        allarme_lp OBJECT-TYPE
                    SYNTAX Integer32 (0..1)
                    UNITS "N/A"
                    MAX-ACCESS read-only
                    STATUS current
                    DESCRIPTION "Low pressure alarm"
                    ::= { digitalObjects 6 }

        -- 1.3.6.1.4.1.9839.2.1.1.8
        all_flusso OBJECT-TYPE
                    SYNTAX Integer32 (0..1)
                    UNITS "N/A"
                    MAX-ACCESS read-only
                    STATUS current
                    DESCRIPTION "Flowmeter alarm"
                    ::= { digitalObjects 8 }

        -- 1.3.6.1.4.1.9839.2.1.1.9
        err_sonda_b3 OBJECT-TYPE
                    SYNTAX Integer32 (0..1)
                    UNITS "N/A"
                    MAX-ACCESS read-only
                    STATUS current
                    DESCRIPTION "Probe b3 faulty or not connected"
                    ::= { digitalObjects 9 }

        -- 1.3.6.1.4.1.9839.2.1.1.10
        err_sonda_b2 OBJECT-TYPE
                    SYNTAX Integer32 (0..1)
                    UNITS "N/A"
                    MAX-ACCESS read-only
                    STATUS current
                    DESCRIPTION "Probe b2 faulty or not connected"
                    ::= { digitalObjects 10 }

        -- 1.3.6.1.4.1.9839.2.1.1.11
        err_sonda_b1 OBJECT-TYPE
                    SYNTAX Integer32 (0..1)
                    UNITS "N/A"
                    MAX-ACCESS read-only
                    STATUS current
                    DESCRIPTION "Probe b1 faulty or not connected"
                    ::= { digitalObjects 11 }

        -- 1.3.6.1.4.1.9839.2.1.1.13
        err_eeprom_s OBJECT-TYPE
                    SYNTAX Integer32 (0..1)
                    UNITS "N/A"
                    MAX-ACCESS read-only
                    STATUS current
                    DESCRIPTION "Faulty eeprom alarm"
                    ::= { digitalObjects 13 }

        -- 1.3.6.1.4.1.9839.2.1.1.16
        all_termin_off OBJECT-TYPE
                    SYNTAX Integer32 (0..1)
                    UNITS "N/A"
                    MAX-ACCESS read-only
                    STATUS current
                    DESCRIPTION "Alarm in the communic. with the remote terminal"
                    ::= { digitalObjects 16 }

        -- 1.3.6.1.4.1.9839.2.1.1.17
        sbrinamento_on OBJECT-TYPE
                    SYNTAX Integer32 (0..1)
                    UNITS "N/A"
                    MAX-ACCESS read-only
                    STATUS current
                    DESCRIPTION "Defrost in progress"
                    ::= { digitalObjects 17 }

        -- 1.3.6.1.4.1.9839.2.1.1.18
        all_sbrinamento OBJECT-TYPE
                    SYNTAX Integer32 (0..1)
                    UNITS "N/A"
                    MAX-ACCESS read-only
                    STATUS current
                    DESCRIPTION "Defrost timeout"
                    ::= { digitalObjects 18 }

        -- 1.3.6.1.4.1.9839.2.1.1.19
        all_antigelo OBJECT-TYPE
                    SYNTAX Integer32 (0..1)
                    UNITS "N/A"
                    MAX-ACCESS read-only
                    STATUS current
                    DESCRIPTION "Freezing alarm"
                    ::= { digitalObjects 19 }

        -- 1.3.6.1.4.1.9839.2.1.1.20
        all_agelo_sonda OBJECT-TYPE
                    SYNTAX Integer32 (0..1)
                    UNITS "N/A"
                    MAX-ACCESS read-only
                    STATUS current
                    DESCRIPTION "Low temperature alarm"
                    ::= { digitalObjects 20 }

        -- 1.3.6.1.4.1.9839.2.1.1.21
        all_sovratens OBJECT-TYPE
                    SYNTAX Integer32 (0..1)
                    UNITS "N/A"
                    MAX-ACCESS read-only
                    STATUS current
                    DESCRIPTION "Overvoltage alarm"
                    ::= { digitalObjects 21 }

        -- 1.3.6.1.4.1.9839.2.1.1.22
        all_sottotens OBJECT-TYPE
                    SYNTAX Integer32 (0..1)
                    UNITS "N/A"
                    MAX-ACCESS read-only
                    STATUS current
                    DESCRIPTION "Undervoltage alarm"
                    ::= { digitalObjects 22 }

        -- 1.3.6.1.4.1.9839.2.1.1.25
        stato_pompa OBJECT-TYPE
                    SYNTAX Integer32 (0..1)
                    UNITS "N/A"
                    MAX-ACCESS read-only
                    STATUS current
                    DESCRIPTION "Pump status"
                    ::= { digitalObjects 25 }

        -- 1.3.6.1.4.1.9839.2.1.1.26
        stato_compress OBJECT-TYPE
                    SYNTAX Integer32 (0..1)
                    UNITS "N/A"
                    MAX-ACCESS read-only
                    STATUS current
                    DESCRIPTION "Comp. 1 status"
                    ::= { digitalObjects 26 }

        -- 1.3.6.1.4.1.9839.2.1.1.27
        stato_resists OBJECT-TYPE
                    SYNTAX Integer32 (0..1)
                    UNITS "N/A"
                    MAX-ACCESS read-only
                    STATUS current
                    DESCRIPTION "Resist. status"
                    ::= { digitalObjects 27 }

        -- 1.3.6.1.4.1.9839.2.1.1.28
        stato_valvola OBJECT-TYPE
                    SYNTAX Integer32 (0..1)
                    UNITS "N/A"
                    MAX-ACCESS read-only
                    STATUS current
                    DESCRIPTION "Valve status"
                    ::= { digitalObjects 28 }

        -- 1.3.6.1.4.1.9839.2.1.1.30
        stato_ventils OBJECT-TYPE
                    SYNTAX Integer32 (0..1)
                    UNITS "N/A"
                    MAX-ACCESS read-only
                    STATUS current
                    DESCRIPTION "Fan status"
                    ::= { digitalObjects 30 }

        -- 1.3.6.1.4.1.9839.2.1.1.40
        unita_misura OBJECT-TYPE
                    SYNTAX Integer32 (0..1)
                    UNITS "flag"
                    MAX-ACCESS read-write
                    STATUS current
                    DESCRIPTION "Measurement Unit"
                    DEFVAL { 0 }
                    ::= { digitalObjects 40 }

        -- 1.3.6.1.4.1.9839.2.1.1.41
        out_per_fan_f1 OBJECT-TYPE
                    SYNTAX Integer32 (0..1)
                    UNITS "flags"
                    MAX-ACCESS read-write
                    STATUS current
                    DESCRIPTION "Fans Output"
                    DEFVAL { 0 }
                    ::= { digitalObjects 41 }

        -- 1.3.6.1.4.1.9839.2.1.1.42
        esecuz_sbrin_d1 OBJECT-TYPE
                    SYNTAX Integer32 (0..1)
                    UNITS "flag"
                    MAX-ACCESS read-write
                    STATUS current
                    DESCRIPTION "Defrosting cycle / condensation antifreeze"
                    DEFVAL { 1 }
                    ::= { digitalObjects 42 }

        -- 1.3.6.1.4.1.9839.2.1.1.43
        def_time_tmp_d2 OBJECT-TYPE
                    SYNTAX Integer32 (0..1)
                    UNITS "flag"
                    MAX-ACCESS read-write
                    STATUS current
                    DESCRIPTION "Timed or temperature-based defrosting"
                    DEFVAL { 0 }
                    ::= { digitalObjects 43 }

        -- 1.3.6.1.4.1.9839.2.1.1.44
        res_gelo_sbr_db OBJECT-TYPE
                    SYNTAX Integer32 (0..1)
                    UNITS "flag"
                    MAX-ACCESS read-write
                    STATUS current
                    DESCRIPTION "Antifreeze heaters activated while defrosting"
                    DEFVAL { 0 }
                    ::= { digitalObjects 44 }

        -- 1.3.6.1.4.1.9839.2.1.1.45
        en_sonda_res_a6 OBJECT-TYPE
                    SYNTAX Integer32 (0..1)
                    UNITS "flag"
                    MAX-ACCESS read-write
                    STATUS current
                    DESCRIPTION "Support heaters probe"
                    DEFVAL { 0 }
                    ::= { digitalObjects 45 }

        -- 1.3.6.1.4.1.9839.2.1.1.46
        all_lp_sonda_p7 OBJECT-TYPE
                    SYNTAX Integer32 (0..1)
                    UNITS "flag"
                    MAX-ACCESS read-write
                    STATUS current
                    DESCRIPTION "Low pressure alarm with pressure probes"
                    DEFVAL { 0 }
                    ::= { digitalObjects 46 }

        -- 1.3.6.1.4.1.9839.2.1.1.47
        en_id_on_off_h7 OBJECT-TYPE
                    SYNTAX Integer32 (0..1)
                    UNITS "flag"
                    MAX-ACCESS read-write
                    STATUS current
                    DESCRIPTION "ON/OFF digital input"
                    DEFVAL { 0 }
                    ::= { digitalObjects 47 }

        -- 1.3.6.1.4.1.9839.2.1.1.48
        all_lp_comp_pa OBJECT-TYPE
                    SYNTAX Integer32 (0..1)
                    UNITS "flag"
                    MAX-ACCESS read-write
                    STATUS current
                    DESCRIPTION "Low pressure alarm selection"
                    DEFVAL { 0 }
                    ::= { digitalObjects 48 }

        -- 1.3.6.1.4.1.9839.2.1.1.49
        en_set2_hc OBJECT-TYPE
                    SYNTAX Integer32 (0..1)
                    UNITS "flag"
                    MAX-ACCESS read-write
                    STATUS current
                    DESCRIPTION "Second set of param."
                    DEFVAL { 0 }
                    ::= { digitalObjects 49 }

        -- 1.3.6.1.4.1.9839.2.1.1.50
        inv_est_inv_hd OBJECT-TYPE
                    SYNTAX Integer32 (0..1)
                    UNITS "flag"
                    MAX-ACCESS read-write
                    STATUS current
                    DESCRIPTION "Logic inversion cooling/heating"
                    DEFVAL { 0 }
                    ::= { digitalObjects 50 }

        -- 1.3.6.1.4.1.9839.2.1.1.51
        sel_rele_all_hf OBJECT-TYPE
                    SYNTAX Integer32 (0..1)
                    UNITS "flag"
                    MAX-ACCESS read-write
                    STATUS current
                    DESCRIPTION "Alarm relay status without alarm condition"
                    DEFVAL { 1 }
                    ::= { digitalObjects 51 }

        -- 1.3.6.1.4.1.9839.2.1.1.55
        ab_estate_inv_h6 OBJECT-TYPE
                    SYNTAX Integer32 (0..1)
                    UNITS "flag"
                    MAX-ACCESS read-write
                    STATUS current
                    DESCRIPTION "Cooling/heating digital input with P8/P9 = 8, 9"
                    DEFVAL { 0 }
                    ::= { digitalObjects 55 }

        -- 1.3.6.1.4.1.9839.2.1.1.56
        rotaz_compr_r5 OBJECT-TYPE
                    SYNTAX Integer32 (0..1)
                    UNITS "N/A"
                    MAX-ACCESS read-only
                    STATUS current
                    DESCRIPTION "Compressor rotation"
                    DEFVAL { 3 }
                    ::= { digitalObjects 56 }



        -- 1.3.6.1.4.1.9839.2.1.2
        analogObjects OBJECT IDENTIFIER ::= { uchiller_cmpMIB 2 }

        -- 1.3.6.1.4.1.9839.2.1.2.1
        sonda_b1 OBJECT-TYPE
                    SYNTAX Integer32 (-32767..32767)
                    UNITS "N/A"
                    MAX-ACCESS read-only
                    STATUS current
                    DESCRIPTION "Inlet probe"
                    ::= { analogObjects 1 }

        -- 1.3.6.1.4.1.9839.2.1.2.2
        sonda_b2 OBJECT-TYPE
                    SYNTAX Integer32 (-32767..32767)
                    UNITS "N/A"
                    MAX-ACCESS read-only
                    STATUS current
                    DESCRIPTION "Water temperaturte at evaporator output B2"
                    ::= { analogObjects 2 }

        -- 1.3.6.1.4.1.9839.2.1.2.3
        sonda_b3 OBJECT-TYPE
                    SYNTAX Integer32 (-32767..32767)
                    UNITS "N/A"
                    MAX-ACCESS read-only
                    STATUS current
                    DESCRIPTION "Temperature/pressure defrosting B3"
                    ::= { analogObjects 3 }

        -- 1.3.6.1.4.1.9839.2.1.2.5
        i_scala_press OBJECT-TYPE
                    SYNTAX Integer32 (0..32767)
                    UNITS "bar x10"
                    MAX-ACCESS read-write
                    STATUS current
                    DESCRIPTION "Min. value current input"
                    DEFVAL { 0 }
                    ::= { analogObjects 5 }

        -- 1.3.6.1.4.1.9839.2.1.2.6
        f_scala_press OBJECT-TYPE
                    SYNTAX Integer32 (-32767..400)
                    UNITS "bar x10"
                    MAX-ACCESS read-write
                    STATUS current
                    DESCRIPTION "Max value current input"
                    DEFVAL { 300 }
                    ::= { analogObjects 6 }

        -- 1.3.6.1.4.1.9839.2.1.2.7
        calibra_b1 OBJECT-TYPE
                    SYNTAX Integer32 (-120..120)
                    UNITS "°C/°F x10"
                    MAX-ACCESS read-only
                    STATUS current
                    DESCRIPTION "Probe B1 calibration"
                    DEFVAL { 0 }
                    ::= { analogObjects 7 }

        -- 1.3.6.1.4.1.9839.2.1.2.8
        calibra_b2 OBJECT-TYPE
                    SYNTAX Integer32 (-120..120)
                    UNITS "°C/°F x10"
                    MAX-ACCESS read-only
                    STATUS current
                    DESCRIPTION "Probe outlet B2 calibration"
                    DEFVAL { 0 }
                    ::= { analogObjects 8 }

        -- 1.3.6.1.4.1.9839.2.1.2.9
        calibra_b3 OBJECT-TYPE
                    SYNTAX Integer32 (-120..120)
                    UNITS "°C/°F x10"
                    MAX-ACCESS read-only
                    STATUS current
                    DESCRIPTION "Defrosting probe B3 calibration"
                    DEFVAL { 0 }
                    ::= { analogObjects 9 }

        -- 1.3.6.1.4.1.9839.2.1.2.10
        setp_estate OBJECT-TYPE
                    SYNTAX Integer32 (-32767..32767)
                    UNITS "°C/°F x10"
                    MAX-ACCESS read-write
                    STATUS current
                    DESCRIPTION "Cooling Set-Point"
                    DEFVAL { 120 }
                    ::= { analogObjects 10 }

        -- 1.3.6.1.4.1.9839.2.1.2.11
        diff_estate OBJECT-TYPE
                    SYNTAX Integer32 (3..199)
                    UNITS "°C/°F x10"
                    MAX-ACCESS read-write
                    STATUS current
                    DESCRIPTION "Cooling differential"
                    DEFVAL { 30 }
                    ::= { analogObjects 11 }

        -- 1.3.6.1.4.1.9839.2.1.2.12
        setp_inverno OBJECT-TYPE
                    SYNTAX Integer32 (-32767..32767)
                    UNITS "°C/°F x10"
                    MAX-ACCESS read-write
                    STATUS current
                    DESCRIPTION "Heating set-point"
                    DEFVAL { 400 }
                    ::= { analogObjects 12 }

        -- 1.3.6.1.4.1.9839.2.1.2.13
        diff_inverno OBJECT-TYPE
                    SYNTAX Integer32 (3..199)
                    UNITS "°C/°F x10"
                    MAX-ACCESS read-write
                    STATUS current
                    DESCRIPTION "Heating differential"
                    DEFVAL { 30 }
                    ::= { analogObjects 13 }

        -- 1.3.6.1.4.1.9839.2.1.2.14
        min_set_est OBJECT-TYPE
                    SYNTAX Integer32 (-400..32767)
                    UNITS "°C/°F x10"
                    MAX-ACCESS read-write
                    STATUS current
                    DESCRIPTION "Min. Cooling set-point"
                    DEFVAL { -400 }
                    ::= { analogObjects 14 }

        -- 1.3.6.1.4.1.9839.2.1.2.15
        max_set_est OBJECT-TYPE
                    SYNTAX Integer32 (-32767..1990)
                    UNITS "°C/°F x10"
                    MAX-ACCESS read-write
                    STATUS current
                    DESCRIPTION "Max. Cooling set-point"
                    DEFVAL { 900 }
                    ::= { analogObjects 15 }

        -- 1.3.6.1.4.1.9839.2.1.2.16
        min_set_inv OBJECT-TYPE
                    SYNTAX Integer32 (-400..32767)
                    UNITS "°C/°F x10"
                    MAX-ACCESS read-write
                    STATUS current
                    DESCRIPTION "Min. Heating set-point"
                    DEFVAL { -400 }
                    ::= { analogObjects 16 }

        -- 1.3.6.1.4.1.9839.2.1.2.17
        max_set_inv OBJECT-TYPE
                    SYNTAX Integer32 (-32767..1990)
                    UNITS "°C/°F x10"
                    MAX-ACCESS read-write
                    STATUS current
                    DESCRIPTION "Max. Heating set-point"
                    DEFVAL { 900 }
                    ::= { analogObjects 17 }

        -- 1.3.6.1.4.1.9839.2.1.2.18
        tmin_vel_est_f5 OBJECT-TYPE
                    SYNTAX Integer32 (-32767..32767)
                    UNITS "°C/°F bar x10"
                    MAX-ACCESS read-write
                    STATUS current
                    DESCRIPTION "Temperature value for min Cooling speed .Pressure"
                    DEFVAL { 130 }
                    ::= { analogObjects 18 }

        -- 1.3.6.1.4.1.9839.2.1.2.19
        tmax_vel_est_f6 OBJECT-TYPE
                    SYNTAX Integer32 (-32767..32767)
                    UNITS "°C/°F bar x10"
                    MAX-ACCESS read-write
                    STATUS current
                    DESCRIPTION "Temperature value for max Cooling speed. Pressure"
                    DEFVAL { 160 }
                    ::= { analogObjects 19 }

        -- 1.3.6.1.4.1.9839.2.1.2.20
        tmin_vel_inv_f7 OBJECT-TYPE
                    SYNTAX Integer32 (-32767..32767)
                    UNITS "°C/°F bar x10"
                    MAX-ACCESS read-write
                    STATUS current
                    DESCRIPTION "Temperature value for min Heating speed. Pressure"
                    DEFVAL { 130 }
                    ::= { analogObjects 20 }

        -- 1.3.6.1.4.1.9839.2.1.2.21
        tmax_vel_inv_f8 OBJECT-TYPE
                    SYNTAX Integer32 (-32767..32767)
                    UNITS "°C/°F bar x10"
                    MAX-ACCESS read-write
                    STATUS current
                    DESCRIPTION "Temperature value for max Heating speed.Pressure"
                    DEFVAL { 90 }
                    ::= { analogObjects 21 }

        -- 1.3.6.1.4.1.9839.2.1.2.22
        toff_fan_est_f9 OBJECT-TYPE
                    SYNTAX Integer32 (-32767..32767)
                    UNITS "°C/°F bar x10"
                    MAX-ACCESS read-write
                    STATUS current
                    DESCRIPTION "Temperature to turn OFF the fan in Cooling .Pressure"
                    DEFVAL { 80 }
                    ::= { analogObjects 22 }

        -- 1.3.6.1.4.1.9839.2.1.2.23
        toff_fan_inv_fa OBJECT-TYPE
                    SYNTAX Integer32 (-32767..32767)
                    UNITS "°C/°F bar x10"
                    MAX-ACCESS read-write
                    STATUS current
                    DESCRIPTION "Temperature to turn OFF the fan in Winter. Pressure"
                    DEFVAL { 160 }
                    ::= { analogObjects 23 }

        -- 1.3.6.1.4.1.9839.2.1.2.24
        parametro_d3 OBJECT-TYPE
                    SYNTAX Integer32 (-32767..32767)
                    UNITS "°C/°F bar x10"
                    MAX-ACCESS read-write
                    STATUS current
                    DESCRIPTION "Temperat./pressure starting the defrost.cycle"
                    DEFVAL { 35 }
                    ::= { analogObjects 24 }

        -- 1.3.6.1.4.1.9839.2.1.2.25
        parametro_d4 OBJECT-TYPE
                    SYNTAX Integer32 (-32767..32767)
                    UNITS "°C/°F bar x10"
                    MAX-ACCESS read-write
                    STATUS current
                    DESCRIPTION "End-defrosting temperature/pressure"
                    DEFVAL { 140 }
                    ::= { analogObjects 25 }

        -- 1.3.6.1.4.1.9839.2.1.2.26
        set_al_agelo_a1 OBJECT-TYPE
                    SYNTAX Integer32 (-32767..32767)
                    UNITS "°C/°F x10"
                    MAX-ACCESS read-write
                    STATUS current
                    DESCRIPTION "Antifreeze"
                    DEFVAL { 30 }
                    ::= { analogObjects 26 }

        -- 1.3.6.1.4.1.9839.2.1.2.27
        dif_al_agelo_a2 OBJECT-TYPE
                    SYNTAX Integer32 (3..199)
                    UNITS "°C/°F x10"
                    MAX-ACCESS read-write
                    STATUS current
                    DESCRIPTION "Differential for antifreeze/low ambient temperatur"
                    DEFVAL { 50 }
                    ::= { analogObjects 27 }

        -- 1.3.6.1.4.1.9839.2.1.2.28
        set_res_gelo_a4 OBJECT-TYPE
                    SYNTAX Integer32 (-32767..32767)
                    UNITS "°C/°F x10"
                    MAX-ACCESS read-write
                    STATUS current
                    DESCRIPTION "Setpoint for the activation of antifreeze supp."
                    DEFVAL { 50 }
                    ::= { analogObjects 28 }

        -- 1.3.6.1.4.1.9839.2.1.2.29
        dif_res_gelo_a5 OBJECT-TYPE
                    SYNTAX Integer32 (3..199)
                    UNITS "°C/°F x10"
                    MAX-ACCESS read-write
                    STATUS current
                    DESCRIPTION "Antifreeze/Support heaters differential"
                    DEFVAL { 10 }
                    ::= { analogObjects 29 }

        -- 1.3.6.1.4.1.9839.2.1.2.30
        lim_set_gelo_a7 OBJECT-TYPE
                    SYNTAX Integer32 (-400..1220)
                    UNITS "°C/°F x10"
                    MAX-ACCESS read-write
                    STATUS current
                    DESCRIPTION "Antifreeze-alarm set"
                    DEFVAL { -400 }
                    ::= { analogObjects 30 }

        -- 1.3.6.1.4.1.9839.2.1.2.31
        set_res_risc_a8 OBJECT-TYPE
                    SYNTAX Integer32 (-32767..32767)
                    UNITS "°C/°F x10"
                    MAX-ACCESS read-write
                    STATUS current
                    DESCRIPTION "Heating support-resistance set"
                    DEFVAL { 250 }
                    ::= { analogObjects 31 }

        -- 1.3.6.1.4.1.9839.2.1.2.32
        dif_res_risc_a9 OBJECT-TYPE
                    SYNTAX Integer32 (3..199)
                    UNITS "°C/°F x10"
                    MAX-ACCESS read-write
                    STATUS current
                    DESCRIPTION "Heating support-resistance differential"
                    DEFVAL { 30 }
                    ::= { analogObjects 32 }

        -- 1.3.6.1.4.1.9839.2.1.2.33
        set_all_at_pb OBJECT-TYPE
                    SYNTAX Integer32 (-400..1990)
                    UNITS "/d x10"
                    MAX-ACCESS read-write
                    STATUS current
                    DESCRIPTION "High temperature alarm set"
                    DEFVAL { 900 }
                    ::= { analogObjects 33 }

        -- 1.3.6.1.4.1.9839.2.1.2.34
        sonda_b4 OBJECT-TYPE
                    SYNTAX Integer32 (-32767..32767)
                    UNITS "N/A"
                    MAX-ACCESS read-only
                    STATUS current
                    DESCRIPTION "Probe B4"
                    ::= { analogObjects 34 }



        -- 1.3.6.1.4.1.9839.2.1.3
        integerObjects OBJECT IDENTIFIER ::= { uchiller_cmpMIB 3 }

        -- 1.3.6.1.4.1.9839.2.1.3.1
        velocita_vent OBJECT-TYPE
                    SYNTAX Integer32 (-32767..32767)
                    UNITS "N/A"
                    MAX-ACCESS read-only
                    STATUS current
                    DESCRIPTION "Fan speed 0-100%"
                    ::= { integerObjects 1 }

        -- 1.3.6.1.4.1.9839.2.1.3.6
        filtro_digitale OBJECT-TYPE
                    SYNTAX Integer32 (1..15)
                    UNITS "N/A"
                    MAX-ACCESS read-write
                    STATUS current
                    DESCRIPTION "Digital filter"
                    DEFVAL { 4 }
                    ::= { integerObjects 6 }

        -- 1.3.6.1.4.1.9839.2.1.3.8
        tmin_on_comp_c1 OBJECT-TYPE
                    SYNTAX Integer32 (0..150)
                    UNITS "sec"
                    MAX-ACCESS read-write
                    STATUS current
                    DESCRIPTION "Min. running time"
                    DEFVAL { 60 }
                    ::= { integerObjects 8 }

        -- 1.3.6.1.4.1.9839.2.1.3.9
        tmin_sp_comp_c2 OBJECT-TYPE
                    SYNTAX Integer32 (0..90)
                    UNITS "10 sec"
                    MAX-ACCESS read-write
                    STATUS current
                    DESCRIPTION "Min. stopping time"
                    DEFVAL { 6 }
                    ::= { integerObjects 9 }

        -- 1.3.6.1.4.1.9839.2.1.3.10
        time_2_acc_c3 OBJECT-TYPE
                    SYNTAX Integer32 (0..90)
                    UNITS "10 sec"
                    MAX-ACCESS read-write
                    STATUS current
                    DESCRIPTION "Time interval between 2 starts"
                    DEFVAL { 36 }
                    ::= { integerObjects 10 }

        -- 1.3.6.1.4.1.9839.2.1.3.11
        rit_on_comp_c6 OBJECT-TYPE
                    SYNTAX Integer32 (0..150)
                    UNITS "sec"
                    MAX-ACCESS read-write
                    STATUS current
                    DESCRIPTION "Delay at start-up"
                    DEFVAL { 0 }
                    ::= { integerObjects 11 }

        -- 1.3.6.1.4.1.9839.2.1.3.12
        rit_c_on_pmp_c7 OBJECT-TYPE
                    SYNTAX Integer32 (0..150)
                    UNITS "sec"
                    MAX-ACCESS read-write
                    STATUS current
                    DESCRIPTION "Delay in switching on compressor after switch. On"
                    DEFVAL { 20 }
                    ::= { integerObjects 12 }

        -- 1.3.6.1.4.1.9839.2.1.3.13
        off_p_off_v_c8 OBJECT-TYPE
                    SYNTAX Integer32 (0..150)
                    UNITS "min"
                    MAX-ACCESS read-write
                    STATUS current
                    DESCRIPTION "Delay in switching off compress. After switc.off"
                    DEFVAL { 20 }
                    ::= { integerObjects 13 }

        -- 1.3.6.1.4.1.9839.2.1.3.14
        contaore_c1_c9 OBJECT-TYPE
                    SYNTAX Integer32 (0..19900)
                    UNITS "hours"
                    MAX-ACCESS read-only
                    STATUS current
                    DESCRIPTION "Hour counter comp. 1"
                    DEFVAL { 0 }
                    ::= { integerObjects 14 }

        -- 1.3.6.1.4.1.9839.2.1.3.15
        max_ore_comp_cb OBJECT-TYPE
                    SYNTAX Integer32 (0..100)
                    UNITS "100 hours"
                    MAX-ACCESS read-write
                    STATUS current
                    DESCRIPTION "Timer threshold during normal operation"
                    DEFVAL { 0 }
                    ::= { integerObjects 15 }

        -- 1.3.6.1.4.1.9839.2.1.3.16
        ore_pmp_vent_cc OBJECT-TYPE
                    SYNTAX Integer32 (0..19900)
                    UNITS "hours"
                    MAX-ACCESS read-only
                    STATUS current
                    DESCRIPTION "Pump/inlet fan timer"
                    DEFVAL { 0 }
                    ::= { integerObjects 16 }

        -- 1.3.6.1.4.1.9839.2.1.3.17
        modo_vent_f2 OBJECT-TYPE
                    SYNTAX Integer32 (0..3)
                    UNITS "flags"
                    MAX-ACCESS read-write
                    STATUS current
                    DESCRIPTION "Operating logic of the fans"
                    DEFVAL { 0 }
                    ::= { integerObjects 17 }

        -- 1.3.6.1.4.1.9839.2.1.3.18
        min_volt_f3 OBJECT-TYPE
                    SYNTAX Integer32 (0..32767)
                    UNITS "step"
                    MAX-ACCESS read-write
                    STATUS current
                    DESCRIPTION "Minimum tension threshold for Triac"
                    DEFVAL { 35 }
                    ::= { integerObjects 18 }

        -- 1.3.6.1.4.1.9839.2.1.3.19
        max_volt_f4 OBJECT-TYPE
                    SYNTAX Integer32 (-32767..100)
                    UNITS "step"
                    MAX-ACCESS read-write
                    STATUS current
                    DESCRIPTION "Max.tension threshold for Triac"
                    DEFVAL { 75 }
                    ::= { integerObjects 19 }

        -- 1.3.6.1.4.1.9839.2.1.3.20
        t_spunto_v_fb OBJECT-TYPE
                    SYNTAX Integer32 (0..99)
                    UNITS "sec"
                    MAX-ACCESS read-write
                    STATUS current
                    DESCRIPTION "Starting time of fans"
                    DEFVAL { 4 }
                    ::= { integerObjects 20 }

        -- 1.3.6.1.4.1.9839.2.1.3.21
        t_imp_triac_fc OBJECT-TYPE
                    SYNTAX Integer32 (0..15)
                    UNITS "msec"
                    MAX-ACCESS read-write
                    STATUS current
                    DESCRIPTION "Triac impulse duration"
                    DEFVAL { 2 }
                    ::= { integerObjects 21 }

        -- 1.3.6.1.4.1.9839.2.1.3.22
        t_min_on_def_d5 OBJECT-TYPE
                    SYNTAX Integer32 (10..150)
                    UNITS "sec"
                    MAX-ACCESS read-write
                    STATUS current
                    DESCRIPTION "Minimum time interval before starting a defr. Cycl"
                    DEFVAL { 10 }
                    ::= { integerObjects 22 }

        -- 1.3.6.1.4.1.9839.2.1.3.23
        t_min_def_d6 OBJECT-TYPE
                    SYNTAX Integer32 (0..150)
                    UNITS "sec"
                    MAX-ACCESS read-write
                    STATUS current
                    DESCRIPTION "Min. duration of a defrosting cycle"
                    DEFVAL { 0 }
                    ::= { integerObjects 23 }

        -- 1.3.6.1.4.1.9839.2.1.3.24
        t_max_def_d7 OBJECT-TYPE
                    SYNTAX Integer32 (1..15)
                    UNITS "min"
                    MAX-ACCESS read-write
                    STATUS current
                    DESCRIPTION "Max. duration of a defrosting cycle"
                    DEFVAL { 5 }
                    ::= { integerObjects 24 }

        -- 1.3.6.1.4.1.9839.2.1.3.25
        rit_tra_2def_d8 OBJECT-TYPE
                    SYNTAX Integer32 (10..150)
                    UNITS "min"
                    MAX-ACCESS read-write
                    STATUS current
                    DESCRIPTION "Time-delay between 2 defrosting"
                    DEFVAL { 30 }
                    ::= { integerObjects 25 }

        -- 1.3.6.1.4.1.9839.2.1.3.26
        wait_on_def_dc OBJECT-TYPE
                    SYNTAX Integer32 (0..3)
                    UNITS "min"
                    MAX-ACCESS read-write
                    STATUS current
                    DESCRIPTION "Delay before defrosting"
                    DEFVAL { 0 }
                    ::= { integerObjects 26 }

        -- 1.3.6.1.4.1.9839.2.1.3.27
        wait_end_def_dd OBJECT-TYPE
                    SYNTAX Integer32 (0..3)
                    UNITS "min"
                    MAX-ACCESS read-write
                    STATUS current
                    DESCRIPTION "Delay after defrosting"
                    DEFVAL { 0 }
                    ::= { integerObjects 27 }

        -- 1.3.6.1.4.1.9839.2.1.3.28
        rit_all_ag_a3 OBJECT-TYPE
                    SYNTAX Integer32 (0..150)
                    UNITS "sec"
                    MAX-ACCESS read-write
                    STATUS current
                    DESCRIPTION "Time to bypass the antfreeze/low amb. Temp. allarm"
                    DEFVAL { 0 }
                    ::= { integerObjects 28 }

        -- 1.3.6.1.4.1.9839.2.1.3.29
        r_al_on_flux_p1 OBJECT-TYPE
                    SYNTAX Integer32 (0..150)
                    UNITS "sec"
                    MAX-ACCESS read-write
                    STATUS current
                    DESCRIPTION "Flowmeter down delayed when starting the pump"
                    DEFVAL { 20 }
                    ::= { integerObjects 29 }

        -- 1.3.6.1.4.1.9839.2.1.3.30
        r_al_rg_flux_p2 OBJECT-TYPE
                    SYNTAX Integer32 (0..90)
                    UNITS "sec"
                    MAX-ACCESS read-write
                    STATUS current
                    DESCRIPTION "Flowswitch alarm delayed during normal operating"
                    DEFVAL { 5 }
                    ::= { integerObjects 30 }

        -- 1.3.6.1.4.1.9839.2.1.3.31
        rit_all_lp_p3 OBJECT-TYPE
                    SYNTAX Integer32 (0..199)
                    UNITS "sec"
                    MAX-ACCESS read-write
                    STATUS current
                    DESCRIPTION "Low pressure alarm delayed at compr. start-up"
                    DEFVAL { 40 }
                    ::= { integerObjects 31 }

        -- 1.3.6.1.4.1.9839.2.1.3.32
        t_buzzer_p4 OBJECT-TYPE
                    SYNTAX Integer32 (0..15)
                    UNITS "min"
                    MAX-ACCESS read-write
                    STATUS current
                    DESCRIPTION "Buzzer ON"
                    DEFVAL { 0 }
                    ::= { integerObjects 32 }

        -- 1.3.6.1.4.1.9839.2.1.3.33
        riprist_all_p5 OBJECT-TYPE
                    SYNTAX Integer32 (0..4)
                    UNITS "flag"
                    MAX-ACCESS read-write
                    STATUS current
                    DESCRIPTION "Reset of alarms"
                    DEFVAL { 0 }
                    ::= { integerObjects 33 }

        -- 1.3.6.1.4.1.9839.2.1.3.34
        selez_id1_p8 OBJECT-TYPE
                    SYNTAX Integer32 (0..7)
                    UNITS "flag"
                    MAX-ACCESS read-write
                    STATUS current
                    DESCRIPTION "Sel. of the digital input"
                    DEFVAL { 0 }
                    ::= { integerObjects 34 }

        -- 1.3.6.1.4.1.9839.2.1.3.35
        selez_id2_p9 OBJECT-TYPE
                    SYNTAX Integer32 (-32767..32767)
                    UNITS "N/A"
                    MAX-ACCESS read-write
                    STATUS current
                    DESCRIPTION "Sel. of the digital input n.2"
                    ::= { integerObjects 35 }

        -- 1.3.6.1.4.1.9839.2.1.3.36
        modello_mac_h1 OBJECT-TYPE
                    SYNTAX Integer32 (0..8)
                    UNITS "flag"
                    MAX-ACCESS read-only
                    STATUS current
                    DESCRIPTION "Unit model"
                    DEFVAL { 2 }
                    ::= { integerObjects 36 }

        -- 1.3.6.1.4.1.9839.2.1.3.37
        modo_pmp_vnt_h5 OBJECT-TYPE
                    SYNTAX Integer32 (0..2)
                    UNITS "flag"
                    MAX-ACCESS read-write
                    STATUS current
                    DESCRIPTION "Operating logic of the Pump/Inlet fan"
                    DEFVAL { 1 }
                    ::= { integerObjects 37 }

        -- 1.3.6.1.4.1.9839.2.1.3.38
        blocca_tasti_h9 OBJECT-TYPE
                    SYNTAX Integer32 (0..3)
                    UNITS "flag"
                    MAX-ACCESS read-write
                    STATUS current
                    DESCRIPTION "Keyboard lock-up"
                    DEFVAL { 1 }
                    ::= { integerObjects 38 }

        -- 1.3.6.1.4.1.9839.2.1.3.39
        seradd OBJECT-TYPE
                    SYNTAX Integer32 (1..199)
                    UNITS "N/A"
                    MAX-ACCESS read-write
                    STATUS current
                    DESCRIPTION "Serial address"
                    DEFVAL { 1 }
                    ::= { integerObjects 39 }

        -- 1.3.6.1.4.1.9839.2.1.3.40
        passw_telec_hb OBJECT-TYPE
                    SYNTAX Integer32 (0..15)
                    UNITS "N/A"
                    MAX-ACCESS read-write
                    STATUS current
                    DESCRIPTION "Infrared remote unit password"
                    DEFVAL { 0 }
                    ::= { integerObjects 40 }

        -- 1.3.6.1.4.1.9839.2.1.3.41
        valv_inv_ch_he OBJECT-TYPE
                    SYNTAX Integer32 (0..2)
                    UNITS "flag"
                    MAX-ACCESS read-write
                    STATUS current
                    DESCRIPTION "Valve status cooling"
                    DEFVAL { 0 }
                    ::= { integerObjects 41 }

        -- 1.3.6.1.4.1.9839.2.1.3.42
        numero_term_h8 OBJECT-TYPE
                    SYNTAX Integer32 (0..1)
                    UNITS "flag"
                    MAX-ACCESS read-write
                    STATUS current
                    DESCRIPTION "Number of terminals"
                    DEFVAL { 0 }
                    ::= { integerObjects 42 }

        -- 1.3.6.1.4.1.9839.2.1.3.43
        high_temp_all_pc OBJECT-TYPE
                    SYNTAX Integer32 (0..150)
                    UNITS "min"
                    MAX-ACCESS read-write
                    STATUS current
                    DESCRIPTION "High temperature alarm delayed at start-up"
                    DEFVAL { 30 }
                    ::= { integerObjects 43 }

        -- 1.3.6.1.4.1.9839.2.1.3.51
        versione_sw_hg OBJECT-TYPE
                    SYNTAX Integer32 (-32767..32767)
                    UNITS "N/A"
                    MAX-ACCESS read-only
                    STATUS current
                    DESCRIPTION "SW Release"
                    DEFVAL { 13 }
                    ::= { integerObjects 51 }

        -- 1.3.6.1.4.1.9839.2.1.3.52
        rit_acc_comp OBJECT-TYPE
                    SYNTAX Integer32 (-32767..32767)
                    UNITS "sec"
                    MAX-ACCESS read-only
                    STATUS current
                    DESCRIPTION "Start delay between the two compressors"
                    ::= { integerObjects 52 }

        -- 1.3.6.1.4.1.9839.2.1.3.53
        rit_spegn_comp OBJECT-TYPE
                    SYNTAX Integer32 (0..15)
                    UNITS "sec"
                    MAX-ACCESS read-only
                    STATUS current
                    DESCRIPTION "Stop delay between the two compressors"
                    DEFVAL { 0 }
                    ::= { integerObjects 53 }

        -- 1.3.6.1.4.1.9839.2.1.3.56
        tempo_acc_pompa OBJECT-TYPE
                    SYNTAX Integer32 (1..150)
                    UNITS "min"
                    MAX-ACCESS read-only
                    STATUS current
                    DESCRIPTION "Minimum time between two pump starts"
                    DEFVAL { 30 }
                    ::= { integerObjects 56 }


	
	END

--
-- CAREL-uchiller_cmp.MIB
--
