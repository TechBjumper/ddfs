GEISTMFG-EM8GM6-MIB DEFINITIONS ::= BEGIN

IMPORTS
	MODULE-IDENTITY, OBJECT-TYPE, enterprises, Unsigned32 FROM SNMPv2-SMI;

geistmfg MODULE-IDENTITY
	LAST-UPDATED "200612150000Z"
	ORGANIZATION "Geist Manufacturing"
	CONTACT-INFO "support@geistmfg.com/800.432.3219"
	DESCRIPTION "The MIB for EM8/GM6"
	::= { enterprises 21239 }
	

em8gm6 OBJECT IDENTIFIER
::=  { geistmfg 8 }


	
productInfo OBJECT IDENTIFIER
	::= { em8gm6 1 }

totalDeciAmps OBJECT IDENTIFIER
	::= { em8gm6 2 }




productTitle    OBJECT-TYPE
   SYNTAX DisplayString
   ACCESS read-only
   STATUS mandatory
   DESCRIPTION
      "Name of product"
   ::= { productInfo 1 }
   
productVersion    OBJECT-TYPE
   SYNTAX DisplayString
   ACCESS read-only
   STATUS mandatory
   DESCRIPTION
      "Firmware version"
   ::= { productInfo 2 }

productName    OBJECT-TYPE
   SYNTAX DisplayString
   ACCESS read-only
   STATUS mandatory
   DESCRIPTION
      "Unit friendly name"
   ::= { productInfo 3 }

productMAC    OBJECT-TYPE
   SYNTAX DisplayString
   ACCESS read-only
   STATUS mandatory
   DESCRIPTION
      "Unit MAC address"
   ::= { productInfo 4 }

productIP    OBJECT-TYPE
   SYNTAX DisplayString
   ACCESS read-only
   STATUS mandatory
   DESCRIPTION
      "IP address of the unit"
   ::= { productInfo 5 }




totalDeciAmpsCircuit1   OBJECT-TYPE
   SYNTAX INTEGER(0..300)
   UNITS "0.1 Amps"
   ACCESS read-only
   STATUS mandatory
   DESCRIPTION
   "Total Amps consumed by Circuit1, in units of 0.1 amps"
   ::= { totalDeciAmps 1 }

totalDeciAmpsCircuit2   OBJECT-TYPE
   SYNTAX INTEGER(0..300)
   UNITS "0.1 Amps"
   ACCESS read-only
   STATUS mandatory
   DESCRIPTION
   "Total Amps consumed by Circuit2, in units of 0.1 amps"
   ::= { totalDeciAmps 2 }

totalDeciAmpsCircuit3   OBJECT-TYPE
   SYNTAX INTEGER(0..300)
   UNITS "0.1 Amps"
   ACCESS read-only
   STATUS mandatory
   DESCRIPTION
   "Total Amps consumed by Circuit3, in units of 0.1 amps"
   ::= { totalDeciAmps 3 }

totalDeciAmpsCircuit4   OBJECT-TYPE
   SYNTAX INTEGER(0..300)
   UNITS "0.1 Amps"
   ACCESS read-only
   STATUS mandatory
   DESCRIPTION
   "Total Amps consumed by Circuit4, in units of 0.1 amps"
   ::= { totalDeciAmps 4 }

totalDeciAmpsCircuit5   OBJECT-TYPE
   SYNTAX INTEGER(0..300)
   UNITS "0.1 Amps"
   ACCESS read-only
   STATUS mandatory
   DESCRIPTION
   "Total Amps consumed by Circuit5, in units of 0.1 amps"
   ::= { totalDeciAmps 5 }

totalDeciAmpsCircuit6   OBJECT-TYPE
   SYNTAX INTEGER(0..300)
   UNITS "0.1 Amps"
   ACCESS read-only
   STATUS mandatory
   DESCRIPTION
   "Total Amps consumed by Circuit6, in units of 0.1 amps"
   ::= { totalDeciAmps 6 }



totalDeciAmpsCircuit1TRAP TRAP-TYPE
ENTERPRISE geistmfg
VARIABLES { totalDeciAmpsCircuit1 }
DESCRIPTION "Amps Circuit1 Trap"
::= 1

totalDeciAmpsCircuit2TRAP TRAP-TYPE
ENTERPRISE geistmfg
VARIABLES { totalDeciAmpsCircuit2 }
DESCRIPTION "Amps Circuit2 Trap"
::= 2

totalDeciAmpsCircuit3TRAP TRAP-TYPE
ENTERPRISE geistmfg
VARIABLES { totalDeciAmpsCircuit3 }
DESCRIPTION "Amps Circuit3 Trap"
::= 3

totalDeciAmpsCircuit4TRAP TRAP-TYPE
ENTERPRISE geistmfg
VARIABLES { totalDeciAmpsCircuit4 }
DESCRIPTION "Amps Circuit4 Trap"
::= 4

totalDeciAmpsCircuit5TRAP TRAP-TYPE
ENTERPRISE geistmfg
VARIABLES { totalDeciAmpsCircuit5 }
DESCRIPTION "Amps Circuit5 Trap"
::= 5

totalDeciAmpsCircuit6TRAP TRAP-TYPE
ENTERPRISE geistmfg
VARIABLES { totalDeciAmpsCircuit6 }
DESCRIPTION "Amps Circuit6 Trap"
::= 6

END
