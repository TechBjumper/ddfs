--
-- CAREL-cdz.MIB
-- MIB generated by CAREL
-- Friday, 28 november 2016
--

    CAREL-cdz-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI
			DisplayString
				FROM SNMPv2-TC;
		
        cdzMIB MODULE-IDENTITY
      		LAST-UPDATED  "201503271023Z"		-- March 27, 2015 at 10:23 GMT
      		ORGANIZATION  "CAREL Industries S.r.l."
      		CONTACT-INFO
                "
                        Carel Industries S.r.l.
                        Via dell'Industria, 11
                        35020 Brugine (PD) Italy
                        Tel: +39 049 9716611
                        E-mail: carel@carel.com
                "
      		DESCRIPTION
                "This is the MIB module for the cdz device."
			REVISION "201503271023Z"
			DESCRIPTION
				"version4pCOweb"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { cdzMIB 1 }

       -- 1.3.6.1.4.1.9839.2.1.1.50
        on-off-by-pLAN OBJECT-TYPE
                    SYNTAX Integer32 (0..1)
                    UNITS "N/A"
                    MAX-ACCESS read-write
                    STATUS current
                    DESCRIPTION "On/Off all unit by pLAN (only from unit 1)"
                    DEFVAL { 0 }
                    ::= { digitalObjects 50 }

        -- 1.3.6.1.4.1.9839.2.1.1.51
        sms-unit-info-req OBJECT-TYPE
                    SYNTAX Integer32 (0..1)
                    UNITS "N/A"
                    MAX-ACCESS read-write
                    STATUS current
                    DESCRIPTION "Request SMS unit info"
                    DEFVAL { 0 }
                    ::= { digitalObjects 51 }

        -- 1.3.6.1.4.1.9839.2.1.1.52
        on-off-by-bms OBJECT-TYPE
                    SYNTAX Integer32 (0..1)
                    UNITS "N/A"
                    MAX-ACCESS read-write
                    STATUS current
                    DESCRIPTION "On/Off unit by BMS (0= Off, 1= On)"
                    DEFVAL { 0 }
                    ::= { digitalObjects 52 }

        -- 1.3.6.1.4.1.9839.2.1.1.53
        en-valve-1-by-bms OBJECT-TYPE
                    SYNTAX Integer32 (0..1)
                    UNITS "N/A"
                    MAX-ACCESS read-write
                    STATUS current
                    DESCRIPTION "Enable valve 1 by BMS (0= Off, 1= On)"
                    DEFVAL { 0 }
                    ::= { digitalObjects 53 }

        -- 1.3.6.1.4.1.9839.2.1.1.54
        en-valve-2-by-bms OBJECT-TYPE
                    SYNTAX Integer32 (0..1)
                    UNITS "N/A"
                    MAX-ACCESS read-write
                    STATUS current
                    DESCRIPTION "Enable valve 2 by BMS (0= Off, 1= On)"
                    DEFVAL { 0 }
                    ::= { digitalObjects 54 }

        -- 1.3.6.1.4.1.9839.2.1.1.55
        valve-1-logic-by-bms OBJECT-TYPE
                    SYNTAX Integer32 (0..1)
                    UNITS "N/A"
                    MAX-ACCESS read-write
                    STATUS current
                    DESCRIPTION "Valve 1 logic cooling/heating valve by BMS (0= Cooling, 1= Heating)"
                    DEFVAL { 0 }
                    ::= { digitalObjects 55 }

        -- 1.3.6.1.4.1.9839.2.1.1.56
        valve-2-logic-by-bms OBJECT-TYPE
                    SYNTAX Integer32 (0..1)
                    UNITS "N/A"
                    MAX-ACCESS read-write
                    STATUS current
                    DESCRIPTION "Valve 2 logic cooling/heating valve by BMS (0= Cooling, 1= Heating)"
                    DEFVAL { 0 }
                    ::= { digitalObjects 56 }

        -- 1.3.6.1.4.1.9839.2.1.1.57
        freecooling-deactivation-by-bms OBJECT-TYPE
                    SYNTAX Integer32 (0..1)
                    UNITS "N/A"
                    MAX-ACCESS read-write
                    STATUS current
                    DESCRIPTION "Freecooling deactivation (0= FC enable, 1= FC Disable)"
                    DEFVAL { 0 }
                    ::= { digitalObjects 57 }

        -- 1.3.6.1.4.1.9839.2.1.1.58
        en-cooling-req-by-bms OBJECT-TYPE
                    SYNTAX Integer32 (0..1)
                    UNITS "N/A"
                    MAX-ACCESS read-write
                    STATUS current
                    DESCRIPTION "Enable cooling request by BMS (0= Disable, 1= Enabled)"
                    DEFVAL { 0 }
                    ::= { digitalObjects 58 }

        -- 1.3.6.1.4.1.9839.2.1.1.59
        en-heating-req-by-bms OBJECT-TYPE
                    SYNTAX Integer32 (0..1)
                    UNITS "N/A"
                    MAX-ACCESS read-write
                    STATUS current
                    DESCRIPTION "Enable Heating request by BMS (0= Disable, 1= Enabled)"
                    DEFVAL { 0 }
                    ::= { digitalObjects 59 }

        -- 1.3.6.1.4.1.9839.2.1.1.60
        en-humid-req-by-bms OBJECT-TYPE
                    SYNTAX Integer32 (0..1)
                    UNITS "N/A"
                    MAX-ACCESS read-write
                    STATUS current
                    DESCRIPTION "Enable humidifier request by BMS (0= Disable, 1= Enabled)"
                    DEFVAL { 0 }
                    ::= { digitalObjects 60 }

        -- 1.3.6.1.4.1.9839.2.1.1.61
        en-dehumid-req-by-bms OBJECT-TYPE
                    SYNTAX Integer32 (0..1)
                    UNITS "N/A"
                    MAX-ACCESS read-write
                    STATUS current
                    DESCRIPTION "Enable dehumidifier request by BMS (0= Disable, 1= Enabled)"
                    DEFVAL { 0 }
                    ::= { digitalObjects 61 }

        -- 1.3.6.1.4.1.9839.2.1.1.62
        dual-cooling-priority-by-bms OBJECT-TYPE
                    SYNTAX Integer32 (0..1)
                    UNITS "N/A"
                    MAX-ACCESS read-write
                    STATUS current
                    DESCRIPTION "Dual cooling priority (0= CW, 1= DX)"
                    DEFVAL { 0 }
                    ::= { digitalObjects 62 }

        -- 1.3.6.1.4.1.9839.2.1.1.63
        bms-forced-speed OBJECT-TYPE
                    SYNTAX Integer32 (0..1)
                    UNITS "N/A"
                    MAX-ACCESS read-write
                    STATUS current
                    DESCRIPTION "Fans speed forced by BMS (0= Not forced, 1= Forced)"
                    DEFVAL { 0 }
                    ::= { digitalObjects 63 }

        -- 1.3.6.1.4.1.9839.2.1.1.64
        limit-max-comp-speed-by-bms OBJECT-TYPE
                    SYNTAX Integer32 (0..1)
                    UNITS "N/A"
                    MAX-ACCESS read-write
                    STATUS current
                    DESCRIPTION "Limit max compressor speed by BMS (0= Limit disable, 1= Limit enable)"
                    DEFVAL { 0 }
                    ::= { digitalObjects 64 }

        -- 1.3.6.1.4.1.9839.2.1.1.65
        configurable-alarm-1-by-bms OBJECT-TYPE
                    SYNTAX Integer32 (0..1)
                    UNITS "N/A"
                    MAX-ACCESS read-write
                    STATUS current
                    DESCRIPTION "Configurable alarm 1 by BMS (0= Alarm not active, 1= Alarm active)"
                    DEFVAL { 0 }
                    ::= { digitalObjects 65 }

        -- 1.3.6.1.4.1.9839.2.1.1.66
        configurable-alarm-2-by-bms OBJECT-TYPE
                    SYNTAX Integer32 (0..1)
                    UNITS "N/A"
                    MAX-ACCESS read-write
                    STATUS current
                    DESCRIPTION "Configurable alarm 2 by BMS (0= Alarm not active, 1= Alarm active)"
                    DEFVAL { 0 }
                    ::= { digitalObjects 66 }

        -- 1.3.6.1.4.1.9839.2.1.1.67
        configurable-alarm-3-by-bms OBJECT-TYPE
                    SYNTAX Integer32 (0..1)
                    UNITS "N/A"
                    MAX-ACCESS read-write
                    STATUS current
                    DESCRIPTION "Configurable alarm 3 by BMS (0= Alarm not active, 1= Alarm active)"
                    DEFVAL { 0 }
                    ::= { digitalObjects 67 }

        -- 1.3.6.1.4.1.9839.2.1.1.68
        global-al-reset-by-spv-auto OBJECT-TYPE
                    SYNTAX Integer32 (0..1)
                    UNITS "N/A"
                    MAX-ACCESS read-write
                    STATUS current
                    DESCRIPTION "Reset alarm (0= No request, 1= Request, with automatic reset)"
                    DEFVAL { 0 }
                    ::= { digitalObjects 68 }

        -- 1.3.6.1.4.1.9839.2.1.1.69
        reset-alarm-all-unit-by-bms-auto OBJECT-TYPE
                    SYNTAX Integer32 (0..1)
                    UNITS "N/A"
                    MAX-ACCESS read-write
                    STATUS current
                    DESCRIPTION "Reset alarm all unit in pLAN (0= No request, 1= Request, with automatic reset)"
                    DEFVAL { 0 }
                    ::= { digitalObjects 69 }

        -- 1.3.6.1.4.1.9839.2.1.1.70
        global-al-reset-by-spv-man OBJECT-TYPE
                    SYNTAX Integer32 (0..1)
                    UNITS "N/A"
                    MAX-ACCESS read-write
                    STATUS current
                    DESCRIPTION "Reset alarm (0= No request, 1= Request, with manual reset)"
                    DEFVAL { 0 }
                    ::= { digitalObjects 70 }

        -- 1.3.6.1.4.1.9839.2.1.1.71
        reset-alarm-all-unit-by-bms-man OBJECT-TYPE
                    SYNTAX Integer32 (0..1)
                    UNITS "N/A"
                    MAX-ACCESS read-write
                    STATUS current
                    DESCRIPTION "Reset alarm all unit in pLAN (0= No request, 1= Request, with manual reset)"
                    DEFVAL { 0 }
                    ::= { digitalObjects 71 }

        -- 1.3.6.1.4.1.9839.2.1.1.72
        bms-1-watchdog-digital-var OBJECT-TYPE
                    SYNTAX Integer32 (0..1)
                    UNITS "N/A"
                    MAX-ACCESS read-write
                    STATUS current
                    DESCRIPTION "BMS 1 Watchdog Digital Variables"
                    DEFVAL { 0 }
                    ::= { digitalObjects 72 }

        -- 1.3.6.1.4.1.9839.2.1.1.74
        reg-by-local-or-bms OBJECT-TYPE
                    SYNTAX Integer32 (0..1)
                    UNITS "N/A"
                    MAX-ACCESS read-write
                    STATUS current
                    DESCRIPTION "Regulation by local or BMS (0= Local, 1= BMS)"
                    DEFVAL { 0 }
                    ::= { digitalObjects 74 }

        -- 1.3.6.1.4.1.9839.2.1.1.75
        reset-modbus-fan-totalizer OBJECT-TYPE
                    SYNTAX Integer32 (0..1)
                    UNITS "N/A"
                    MAX-ACCESS read-write
                    STATUS current
                    DESCRIPTION "Reset energy modbus fan totalizer"
                    DEFVAL { 0 }
                    ::= { digitalObjects 75 }

        -- 1.3.6.1.4.1.9839.2.1.1.76
        reset-water-circuit-1-totalizer OBJECT-TYPE
                    SYNTAX Integer32 (0..1)
                    UNITS "N/A"
                    MAX-ACCESS read-write
                    STATUS current
                    DESCRIPTION "Reset energy water circuit 1 totalizer"
                    DEFVAL { 0 }
                    ::= { digitalObjects 76 }

        -- 1.3.6.1.4.1.9839.2.1.1.77
        reset-water-circuit-2-totalizer OBJECT-TYPE
                    SYNTAX Integer32 (0..1)
                    UNITS "N/A"
                    MAX-ACCESS read-write
                    STATUS current
                    DESCRIPTION "Reset energy water circuit 2 totalizer"
                    DEFVAL { 0 }
                    ::= { digitalObjects 77 }
                    
        -- 1.3.6.1.4.1.9839.2.1.1.78
        reset-electrical-energy OBJECT-TYPE
                    SYNTAX Integer32 (0..1)
                    UNITS "N/A"
                    MAX-ACCESS read-write
                    STATUS current
                    DESCRIPTION "Reset electrical energy totalizer"
                    DEFVAL { 0 }
                    ::= { digitalObjects 78 }

        -- 1.3.6.1.4.1.9839.2.1.1.79
        on-off-fc-by-bms OBJECT-TYPE
                    SYNTAX Integer32 (0..1)
                    UNITS "N/A"
                    MAX-ACCESS read-write
                    STATUS current
                    DESCRIPTION "Enable or disable FC By BMS"
                    DEFVAL { 0 }
                    ::= { digitalObjects 79 }

        -- 1.3.6.1.4.1.9839.2.1.1.81
        din-1-pco1 OBJECT-TYPE
                    SYNTAX Integer32 (0..1)
                    UNITS "N/A"
                    MAX-ACCESS read-only
                    STATUS current
                    DESCRIPTION "Digital input 1 pco1 (0= Open,1= Close)"
                    DEFVAL { 0 }
                    ::= { digitalObjects 81 }

        -- 1.3.6.1.4.1.9839.2.1.1.82
        din-2-pco1 OBJECT-TYPE
                    SYNTAX Integer32 (0..1)
                    UNITS "N/A"
                    MAX-ACCESS read-only
                    STATUS current
                    DESCRIPTION "Digital input 2 pco1 (0= Open,1= Close)"
                    DEFVAL { 0 }
                    ::= { digitalObjects 82 }

        -- 1.3.6.1.4.1.9839.2.1.1.83
        din-3-pco1 OBJECT-TYPE
                    SYNTAX Integer32 (0..1)
                    UNITS "N/A"
                    MAX-ACCESS read-only
                    STATUS current
                    DESCRIPTION "Digital input 3 pco1 (0= Open,1= Close)"
                    DEFVAL { 0 }
                    ::= { digitalObjects 83 }

        -- 1.3.6.1.4.1.9839.2.1.1.84
        din-4-pco1 OBJECT-TYPE
                    SYNTAX Integer32 (0..1)
                    UNITS "N/A"
                    MAX-ACCESS read-only
                    STATUS current
                    DESCRIPTION "Digital input 4 pco1 (0= Open,1= Close)"
                    DEFVAL { 0 }
                    ::= { digitalObjects 84 }

        -- 1.3.6.1.4.1.9839.2.1.1.85
        din-5-pco1 OBJECT-TYPE
                    SYNTAX Integer32 (0..1)
                    UNITS "N/A"
                    MAX-ACCESS read-only
                    STATUS current
                    DESCRIPTION "Digital input 5 pco1 (0= Open,1= Close)"
                    DEFVAL { 0 }
                    ::= { digitalObjects 85 }

        -- 1.3.6.1.4.1.9839.2.1.1.86
        din-6-pco1 OBJECT-TYPE
                    SYNTAX Integer32 (0..1)
                    UNITS "N/A"
                    MAX-ACCESS read-only
                    STATUS current
                    DESCRIPTION "Digital input 6 pco1 (0= Open,1= Close)"
                    DEFVAL { 0 }
                    ::= { digitalObjects 86 }

        -- 1.3.6.1.4.1.9839.2.1.1.87
        din-7-pco1 OBJECT-TYPE
                    SYNTAX Integer32 (0..1)
                    UNITS "N/A"
                    MAX-ACCESS read-only
                    STATUS current
                    DESCRIPTION "Digital input 7 pco1 (0= Open,1= Close)"
                    DEFVAL { 0 }
                    ::= { digitalObjects 87 }

        -- 1.3.6.1.4.1.9839.2.1.1.88
        din-8-pco1 OBJECT-TYPE
                    SYNTAX Integer32 (0..1)
                    UNITS "N/A"
                    MAX-ACCESS read-only
                    STATUS current
                    DESCRIPTION "Digital input 8 pco1 (0= Open,1= Close)"
                    DEFVAL { 0 }
                    ::= { digitalObjects 88 }

        -- 1.3.6.1.4.1.9839.2.1.1.89
        din-9-pco1 OBJECT-TYPE
                    SYNTAX Integer32 (0..1)
                    UNITS "N/A"
                    MAX-ACCESS read-only
                    STATUS current
                    DESCRIPTION "Digital input 9 pco1 (0= Open,1= Close)"
                    DEFVAL { 0 }
                    ::= { digitalObjects 89 }

        -- 1.3.6.1.4.1.9839.2.1.1.90
        din-10-pco1 OBJECT-TYPE
                    SYNTAX Integer32 (0..1)
                    UNITS "N/A"
                    MAX-ACCESS read-only
                    STATUS current
                    DESCRIPTION "Digital input 10 pco1 (0= Open,1= Close)"
                    DEFVAL { 0 }
                    ::= { digitalObjects 90 }

        -- 1.3.6.1.4.1.9839.2.1.1.91
        din-11-pco1 OBJECT-TYPE
                    SYNTAX Integer32 (0..1)
                    UNITS "N/A"
                    MAX-ACCESS read-only
                    STATUS current
                    DESCRIPTION "Digital input 11 pco1 (0= Open,1= Close)"
                    DEFVAL { 0 }
                    ::= { digitalObjects 91 }

        -- 1.3.6.1.4.1.9839.2.1.1.92
        din-12-pco1 OBJECT-TYPE
                    SYNTAX Integer32 (0..1)
                    UNITS "N/A"
                    MAX-ACCESS read-only
                    STATUS current
                    DESCRIPTION "Digital input 12 pco1 (0= Open,1= Close)"
                    DEFVAL { 0 }
                    ::= { digitalObjects 92 }

        -- 1.3.6.1.4.1.9839.2.1.1.93
        din-13-pco1 OBJECT-TYPE
                    SYNTAX Integer32 (0..1)
                    UNITS "N/A"
                    MAX-ACCESS read-only
                    STATUS current
                    DESCRIPTION "Digital input 13 pco1 (0= Open,1= Close)"
                    DEFVAL { 0 }
                    ::= { digitalObjects 93 }

        -- 1.3.6.1.4.1.9839.2.1.1.94
        din-14-pco1 OBJECT-TYPE
                    SYNTAX Integer32 (0..1)
                    UNITS "N/A"
                    MAX-ACCESS read-only
                    STATUS current
                    DESCRIPTION "Digital input 14 pco1 (0= Open,1= Close)"
                    DEFVAL { 0 }
                    ::= { digitalObjects 94 }

        -- 1.3.6.1.4.1.9839.2.1.1.95
        din-15-pco1 OBJECT-TYPE
                    SYNTAX Integer32 (0..1)
                    UNITS "N/A"
                    MAX-ACCESS read-only
                    STATUS current
                    DESCRIPTION "Digital input 15 pco1 (0= Open,1= Close)"
                    DEFVAL { 0 }
                    ::= { digitalObjects 95 }

        -- 1.3.6.1.4.1.9839.2.1.1.96
        din-16-pco1 OBJECT-TYPE
                    SYNTAX Integer32 (0..1)
                    UNITS "N/A"
                    MAX-ACCESS read-only
                    STATUS current
                    DESCRIPTION "Digital input 16 pco1 (0= Open,1= Close)"
                    DEFVAL { 0 }
                    ::= { digitalObjects 96 }

        -- 1.3.6.1.4.1.9839.2.1.1.97
        din-17-pco1 OBJECT-TYPE
                    SYNTAX Integer32 (0..1)
                    UNITS "N/A"
                    MAX-ACCESS read-only
                    STATUS current
                    DESCRIPTION "Digital input 17 pco1 (0= Open,1= Close)"
                    DEFVAL { 0 }
                    ::= { digitalObjects 97 }

        -- 1.3.6.1.4.1.9839.2.1.1.98
        din-18-pco1 OBJECT-TYPE
                    SYNTAX Integer32 (0..1)
                    UNITS "N/A"
                    MAX-ACCESS read-only
                    STATUS current
                    DESCRIPTION "Digital input 18 pco1 (0= Open,1= Close)"
                    DEFVAL { 0 }
                    ::= { digitalObjects 98 }

        -- 1.3.6.1.4.1.9839.2.1.1.99
        din-1-pcoe1 OBJECT-TYPE
                    SYNTAX Integer32 (0..1)
                    UNITS "N/A"
                    MAX-ACCESS read-only
                    STATUS current
                    DESCRIPTION "Digital input 1 pcoe1 (0= Open,1= Close)"
                    DEFVAL { 0 }
                    ::= { digitalObjects 99 }

        -- 1.3.6.1.4.1.9839.2.1.1.100
        din-2-pcoe1 OBJECT-TYPE
                    SYNTAX Integer32 (0..1)
                    UNITS "N/A"
                    MAX-ACCESS read-only
                    STATUS current
                    DESCRIPTION "Digital input 2 pcoe1 (0= Open,1= Close)"
                    DEFVAL { 0 }
                    ::= { digitalObjects 100 }

        -- 1.3.6.1.4.1.9839.2.1.1.101
        din-3-pcoe1 OBJECT-TYPE
                    SYNTAX Integer32 (0..1)
                    UNITS "N/A"
                    MAX-ACCESS read-only
                    STATUS current
                    DESCRIPTION "Digital input 3 pcoe1 (0= Open,1= Close)"
                    DEFVAL { 0 }
                    ::= { digitalObjects 101 }

        -- 1.3.6.1.4.1.9839.2.1.1.102
        din-4-pcoe1 OBJECT-TYPE
                    SYNTAX Integer32 (0..1)
                    UNITS "N/A"
                    MAX-ACCESS read-only
                    STATUS current
                    DESCRIPTION "Digital input 4 pcoe1 (0= Open,1= Close)"
                    DEFVAL { 0 }
                    ::= { digitalObjects 102 }

        -- 1.3.6.1.4.1.9839.2.1.1.103
        din-1-pcoe2 OBJECT-TYPE
                    SYNTAX Integer32 (0..1)
                    UNITS "N/A"
                    MAX-ACCESS read-only
                    STATUS current
                    DESCRIPTION "Digital input 1 pcoe2 (0= Open,1= Close)"
                    DEFVAL { 0 }
                    ::= { digitalObjects 103 }

        -- 1.3.6.1.4.1.9839.2.1.1.104
        din-2-pcoe2 OBJECT-TYPE
                    SYNTAX Integer32 (0..1)
                    UNITS "N/A"
                    MAX-ACCESS read-only
                    STATUS current
                    DESCRIPTION "Digital input 2 pcoe2 (0= Open,1= Close)"
                    DEFVAL { 0 }
                    ::= { digitalObjects 104 }

        -- 1.3.6.1.4.1.9839.2.1.1.105
        din-3-pcoe2 OBJECT-TYPE
                    SYNTAX Integer32 (0..1)
                    UNITS "N/A"
                    MAX-ACCESS read-only
                    STATUS current
                    DESCRIPTION "Digital input 3 pcoe2 (0= Open,1= Close)"
                    DEFVAL { 0 }
                    ::= { digitalObjects 105 }

        -- 1.3.6.1.4.1.9839.2.1.1.106
        din-4-pcoe2 OBJECT-TYPE
                    SYNTAX Integer32 (0..1)
                    UNITS "N/A"
                    MAX-ACCESS read-only
                    STATUS current
                    DESCRIPTION "Digital input 4 pcoe2 (0= Open,1= Close)"
                    DEFVAL { 0 }
                    ::= { digitalObjects 106 }

        -- 1.3.6.1.4.1.9839.2.1.1.107
        din-1-pcoe3 OBJECT-TYPE
                    SYNTAX Integer32 (0..1)
                    UNITS "N/A"
                    MAX-ACCESS read-only
                    STATUS current
                    DESCRIPTION "Digital input 1 pcoe3 (0= Open,1= Close)"
                    DEFVAL { 0 }
                    ::= { digitalObjects 107 }

        -- 1.3.6.1.4.1.9839.2.1.1.108
        din-2-pcoe3 OBJECT-TYPE
                    SYNTAX Integer32 (0..1)
                    UNITS "N/A"
                    MAX-ACCESS read-only
                    STATUS current
                    DESCRIPTION "Digital input 2 pcoe3 (0= Open,1= Close)"
                    DEFVAL { 0 }
                    ::= { digitalObjects 108 }

        -- 1.3.6.1.4.1.9839.2.1.1.109
        din-3-pcoe3 OBJECT-TYPE
                    SYNTAX Integer32 (0..1)
                    UNITS "N/A"
                    MAX-ACCESS read-only
                    STATUS current
                    DESCRIPTION "Digital input 3 pcoe3 (0= Open,1= Close)"
                    DEFVAL { 0 }
                    ::= { digitalObjects 109 }

        -- 1.3.6.1.4.1.9839.2.1.1.110
        din-4-pcoe3 OBJECT-TYPE
                    SYNTAX Integer32 (0..1)
                    UNITS "N/A"
                    MAX-ACCESS read-only
                    STATUS current
                    DESCRIPTION "Digital input 4 pcoe3 (0= Open,1= Close)"
                    DEFVAL { 0 }
                    ::= { digitalObjects 110 }

        -- 1.3.6.1.4.1.9839.2.1.1.111
        din-1-pcoe4 OBJECT-TYPE
                    SYNTAX Integer32 (0..1)
                    UNITS "N/A"
                    MAX-ACCESS read-only
                    STATUS current
                    DESCRIPTION "Digital input 1 pcoe4 (0= Open,1= Close)"
                    DEFVAL { 0 }
                    ::= { digitalObjects 111 }

        -- 1.3.6.1.4.1.9839.2.1.1.112
        din-2-pcoe4 OBJECT-TYPE
                    SYNTAX Integer32 (0..1)
                    UNITS "N/A"
                    MAX-ACCESS read-only
                    STATUS current
                    DESCRIPTION "Digital input 2 pcoe4 (0= Open,1= Close)"
                    DEFVAL { 0 }
                    ::= { digitalObjects 112 }

        -- 1.3.6.1.4.1.9839.2.1.1.113
        din-3-pcoe4 OBJECT-TYPE
                    SYNTAX Integer32 (0..1)
                    UNITS "N/A"
                    MAX-ACCESS read-only
                    STATUS current
                    DESCRIPTION "Digital input 3 pcoe4 (0= Open,1= Close)"
                    DEFVAL { 0 }
                    ::= { digitalObjects 113 }

        -- 1.3.6.1.4.1.9839.2.1.1.114
        din-4-pcoe4 OBJECT-TYPE
                    SYNTAX Integer32 (0..1)
                    UNITS "N/A"
                    MAX-ACCESS read-only
                    STATUS current
                    DESCRIPTION "Digital input 4 pcoe4 (0= Open,1= Close)"
                    DEFVAL { 0 }
                    ::= { digitalObjects 114 }

        -- 1.3.6.1.4.1.9839.2.1.1.115
        din-1-pcoe5 OBJECT-TYPE
                    SYNTAX Integer32 (0..1)
                    UNITS "N/A"
                    MAX-ACCESS read-only
                    STATUS current
                    DESCRIPTION "Digital input 1 pcoe5 (0= Open,1= Close)"
                    DEFVAL { 0 }
                    ::= { digitalObjects 115 }

        -- 1.3.6.1.4.1.9839.2.1.1.116
        din-2-pcoe5 OBJECT-TYPE
                    SYNTAX Integer32 (0..1)
                    UNITS "N/A"
                    MAX-ACCESS read-only
                    STATUS current
                    DESCRIPTION "Digital input 2 pcoe5 (0= Open,1= Close)"
                    DEFVAL { 0 }
                    ::= { digitalObjects 116 }

        -- 1.3.6.1.4.1.9839.2.1.1.117
        din-3-pcoe5 OBJECT-TYPE
                    SYNTAX Integer32 (0..1)
                    UNITS "N/A"
                    MAX-ACCESS read-only
                    STATUS current
                    DESCRIPTION "Digital input 3 pcoe5 (0= Open,1= Close)"
                    DEFVAL { 0 }
                    ::= { digitalObjects 117 }

        -- 1.3.6.1.4.1.9839.2.1.1.118
        din-4-pcoe5 OBJECT-TYPE
                    SYNTAX Integer32 (0..1)
                    UNITS "N/A"
                    MAX-ACCESS read-only
                    STATUS current
                    DESCRIPTION "Digital input 4 pcoe5 (0= Open,1= Close)"
                    DEFVAL { 0 }
                    ::= { digitalObjects 118 }

        -- 1.3.6.1.4.1.9839.2.1.1.119
        din-1-eev1 OBJECT-TYPE
                    SYNTAX Integer32 (0..1)
                    UNITS "N/A"
                    MAX-ACCESS read-only
                    STATUS current
                    DESCRIPTION "Digital input 1 EEV1 (0= Open,1= Close)"
                    DEFVAL { 0 }
                    ::= { digitalObjects 119 }

        -- 1.3.6.1.4.1.9839.2.1.1.120
        din-2-eev1 OBJECT-TYPE
                    SYNTAX Integer32 (0..1)
                    UNITS "N/A"
                    MAX-ACCESS read-only
                    STATUS current
                    DESCRIPTION "Digital input 2 EEV1 (0= Open,1= Close)"
                    DEFVAL { 0 }
                    ::= { digitalObjects 120 }

        -- 1.3.6.1.4.1.9839.2.1.1.121
        din-1-eev2 OBJECT-TYPE
                    SYNTAX Integer32 (0..1)
                    UNITS "N/A"
                    MAX-ACCESS read-only
                    STATUS current
                    DESCRIPTION "Digital input 1 EEV2 (0= Open,1= Close)"
                    DEFVAL { 0 }
                    ::= { digitalObjects 121 }

        -- 1.3.6.1.4.1.9839.2.1.1.122
        din-2-eev2 OBJECT-TYPE
                    SYNTAX Integer32 (0..1)
                    UNITS "N/A"
                    MAX-ACCESS read-only
                    STATUS current
                    DESCRIPTION "Digital input 2 EEV2 (0= Open,1= Close)"
                    DEFVAL { 0 }
                    ::= { digitalObjects 122 }

        -- 1.3.6.1.4.1.9839.2.1.1.123
        din-1-inv1 OBJECT-TYPE
                    SYNTAX Integer32 (0..1)
                    UNITS "N/A"
                    MAX-ACCESS read-only
                    STATUS current
                    DESCRIPTION "Digital input 1 INV1 (0= Open,1= Close)"
                    DEFVAL { 0 }
                    ::= { digitalObjects 123 }

        -- 1.3.6.1.4.1.9839.2.1.1.124
        din-2-inv1 OBJECT-TYPE
                    SYNTAX Integer32 (0..1)
                    UNITS "N/A"
                    MAX-ACCESS read-only
                    STATUS current
                    DESCRIPTION "Digital input 2 INV1 (0= Open,1= Close)"
                    DEFVAL { 0 }
                    ::= { digitalObjects 124 }

        -- 1.3.6.1.4.1.9839.2.1.1.125
        din-3-inv1 OBJECT-TYPE
                    SYNTAX Integer32 (0..1)
                    UNITS "N/A"
                    MAX-ACCESS read-only
                    STATUS current
                    DESCRIPTION "Digital input 3 INV1 (0= Open,1= Close)"
                    DEFVAL { 0 }
                    ::= { digitalObjects 125 }

        -- 1.3.6.1.4.1.9839.2.1.1.126
        din-4-inv1 OBJECT-TYPE
                    SYNTAX Integer32 (0..1)
                    UNITS "N/A"
                    MAX-ACCESS read-only
                    STATUS current
                    DESCRIPTION "Digital input 4 INV1 (0= Open,1= Close)"
                    DEFVAL { 0 }
                    ::= { digitalObjects 126 }

        -- 1.3.6.1.4.1.9839.2.1.1.127
        din-5-inv1 OBJECT-TYPE
                    SYNTAX Integer32 (0..1)
                    UNITS "N/A"
                    MAX-ACCESS read-only
                    STATUS current
                    DESCRIPTION "Digital input 5 INV1 (0= Open,1= Close)"
                    DEFVAL { 0 }
                    ::= { digitalObjects 127 }

        -- 1.3.6.1.4.1.9839.2.1.1.128
        din-6-inv1 OBJECT-TYPE
                    SYNTAX Integer32 (0..1)
                    UNITS "N/A"
                    MAX-ACCESS read-only
                    STATUS current
                    DESCRIPTION "Digital input 6 INV1 (0= Open,1= Close)"
                    DEFVAL { 0 }
                    ::= { digitalObjects 128 }

        -- 1.3.6.1.4.1.9839.2.1.1.129
        din-1-inv2 OBJECT-TYPE
                    SYNTAX Integer32 (0..1)
                    UNITS "N/A"
                    MAX-ACCESS read-only
                    STATUS current
                    DESCRIPTION "Digital input 1 INV2 (0= Open,1= Close)"
                    DEFVAL { 0 }
                    ::= { digitalObjects 129 }

        -- 1.3.6.1.4.1.9839.2.1.1.130
        din-2-inv2 OBJECT-TYPE
                    SYNTAX Integer32 (0..1)
                    UNITS "N/A"
                    MAX-ACCESS read-only
                    STATUS current
                    DESCRIPTION "Digital input 2 INV2 (0= Open,1= Close)"
                    DEFVAL { 0 }
                    ::= { digitalObjects 130 }

        -- 1.3.6.1.4.1.9839.2.1.1.131
        din-3-inv2 OBJECT-TYPE
                    SYNTAX Integer32 (0..1)
                    UNITS "N/A"
                    MAX-ACCESS read-only
                    STATUS current
                    DESCRIPTION "Digital input 3 INV2 (0= Open,1= Close)"
                    DEFVAL { 0 }
                    ::= { digitalObjects 131 }

        -- 1.3.6.1.4.1.9839.2.1.1.132
        din-4-inv2 OBJECT-TYPE
                    SYNTAX Integer32 (0..1)
                    UNITS "N/A"
                    MAX-ACCESS read-only
                    STATUS current
                    DESCRIPTION "Digital input 4 INV2 (0= Open,1= Close)"
                    DEFVAL { 0 }
                    ::= { digitalObjects 132 }

        -- 1.3.6.1.4.1.9839.2.1.1.133
        din-5-inv2 OBJECT-TYPE
                    SYNTAX Integer32 (0..1)
                    UNITS "N/A"
                    MAX-ACCESS read-only
                    STATUS current
                    DESCRIPTION "Digital input 5 INV2 (0= Open,1= Close)"
                    DEFVAL { 0 }
                    ::= { digitalObjects 133 }

        -- 1.3.6.1.4.1.9839.2.1.1.134
        din-6-inv2 OBJECT-TYPE
                    SYNTAX Integer32 (0..1)
                    UNITS "N/A"
                    MAX-ACCESS read-only
                    STATUS current
                    DESCRIPTION "Digital input 6 INV2 (0= Open,1= Close)"
                    DEFVAL { 0 }
                    ::= { digitalObjects 134 }

        -- 1.3.6.1.4.1.9839.2.1.1.160
        dout-1-pco1 OBJECT-TYPE
                    SYNTAX Integer32 (0..1)
                    UNITS "N/A"
                    MAX-ACCESS read-only
                    STATUS current
                    DESCRIPTION "Digital output 1 pco1 (0= Open,1= Close)"
                    DEFVAL { 0 }
                    ::= { digitalObjects 160 }

        -- 1.3.6.1.4.1.9839.2.1.1.161
        dout-2-pco1 OBJECT-TYPE
                    SYNTAX Integer32 (0..1)
                    UNITS "N/A"
                    MAX-ACCESS read-only
                    STATUS current
                    DESCRIPTION "Digital output 2 pco1 (0= Open,1= Close)"
                    DEFVAL { 0 }
                    ::= { digitalObjects 161 }

        -- 1.3.6.1.4.1.9839.2.1.1.162
        dout-3-pco1 OBJECT-TYPE
                    SYNTAX Integer32 (0..1)
                    UNITS "N/A"
                    MAX-ACCESS read-only
                    STATUS current
                    DESCRIPTION "Digital output 3 pco1 (0= Open,1= Close)"
                    DEFVAL { 0 }
                    ::= { digitalObjects 162 }

        -- 1.3.6.1.4.1.9839.2.1.1.163
        dout-4-pco1 OBJECT-TYPE
                    SYNTAX Integer32 (0..1)
                    UNITS "N/A"
                    MAX-ACCESS read-only
                    STATUS current
                    DESCRIPTION "Digital output 4 pco1 (0= Open,1= Close)"
                    DEFVAL { 0 }
                    ::= { digitalObjects 163 }

        -- 1.3.6.1.4.1.9839.2.1.1.164
        dout-5-pco1 OBJECT-TYPE
                    SYNTAX Integer32 (0..1)
                    UNITS "N/A"
                    MAX-ACCESS read-only
                    STATUS current
                    DESCRIPTION "Digital output 5 pco1 (0= Open,1= Close)"
                    DEFVAL { 0 }
                    ::= { digitalObjects 164 }

        -- 1.3.6.1.4.1.9839.2.1.1.165
        dout-6-pco1 OBJECT-TYPE
                    SYNTAX Integer32 (0..1)
                    UNITS "N/A"
                    MAX-ACCESS read-only
                    STATUS current
                    DESCRIPTION "Digital output 6 pco1 (0= Open,1= Close)"
                    DEFVAL { 0 }
                    ::= { digitalObjects 165 }

        -- 1.3.6.1.4.1.9839.2.1.1.166
        dout-7-pco1 OBJECT-TYPE
                    SYNTAX Integer32 (0..1)
                    UNITS "N/A"
                    MAX-ACCESS read-only
                    STATUS current
                    DESCRIPTION "Digital output 7 pco1 (0= Open,1= Close)"
                    DEFVAL { 0 }
                    ::= { digitalObjects 166 }

        -- 1.3.6.1.4.1.9839.2.1.1.167
        dout-8-pco1 OBJECT-TYPE
                    SYNTAX Integer32 (0..1)
                    UNITS "N/A"
                    MAX-ACCESS read-only
                    STATUS current
                    DESCRIPTION "Digital output 8 pco1 (0= Open,1= Close)"
                    DEFVAL { 0 }
                    ::= { digitalObjects 167 }

        -- 1.3.6.1.4.1.9839.2.1.1.168
        dout-9-pco1 OBJECT-TYPE
                    SYNTAX Integer32 (0..1)
                    UNITS "N/A"
                    MAX-ACCESS read-only
                    STATUS current
                    DESCRIPTION "Digital output 9 pco1 (0= Open,1= Close)"
                    DEFVAL { 0 }
                    ::= { digitalObjects 168 }

        -- 1.3.6.1.4.1.9839.2.1.1.169
        dout-10-pco1 OBJECT-TYPE
                    SYNTAX Integer32 (0..1)
                    UNITS "N/A"
                    MAX-ACCESS read-only
                    STATUS current
                    DESCRIPTION "Digital output 10 pco1 (0= Open,1= Close)"
                    DEFVAL { 0 }
                    ::= { digitalObjects 169 }

        -- 1.3.6.1.4.1.9839.2.1.1.170
        dout-11-pco1 OBJECT-TYPE
                    SYNTAX Integer32 (0..1)
                    UNITS "N/A"
                    MAX-ACCESS read-only
                    STATUS current
                    DESCRIPTION "Digital output 11 pco1 (0= Open,1= Close)"
                    DEFVAL { 0 }
                    ::= { digitalObjects 170 }

        -- 1.3.6.1.4.1.9839.2.1.1.171
        dout-12-pco1 OBJECT-TYPE
                    SYNTAX Integer32 (0..1)
                    UNITS "N/A"
                    MAX-ACCESS read-only
                    STATUS current
                    DESCRIPTION "Digital output 12 pco1 (0= Open,1= Close)"
                    DEFVAL { 0 }
                    ::= { digitalObjects 171 }

        -- 1.3.6.1.4.1.9839.2.1.1.172
        dout-13-pco1 OBJECT-TYPE
                    SYNTAX Integer32 (0..1)
                    UNITS "N/A"
                    MAX-ACCESS read-only
                    STATUS current
                    DESCRIPTION "Digital output 13 pco1 (0= Open,1= Close)"
                    DEFVAL { 0 }
                    ::= { digitalObjects 172 }

        -- 1.3.6.1.4.1.9839.2.1.1.173
        dout-14-pco1 OBJECT-TYPE
                    SYNTAX Integer32 (0..1)
                    UNITS "N/A"
                    MAX-ACCESS read-only
                    STATUS current
                    DESCRIPTION "Digital output 14 pco1 (0= Open,1= Close)"
                    DEFVAL { 0 }
                    ::= { digitalObjects 173 }

        -- 1.3.6.1.4.1.9839.2.1.1.174
        dout-15-pco1 OBJECT-TYPE
                    SYNTAX Integer32 (0..1)
                    UNITS "N/A"
                    MAX-ACCESS read-only
                    STATUS current
                    DESCRIPTION "Digital output 15 pco1 (0= Open,1= Close)"
                    DEFVAL { 0 }
                    ::= { digitalObjects 174 }

        -- 1.3.6.1.4.1.9839.2.1.1.175
        dout-16-pco1 OBJECT-TYPE
                    SYNTAX Integer32 (0..1)
                    UNITS "N/A"
                    MAX-ACCESS read-only
                    STATUS current
                    DESCRIPTION "Digital output 16 pco1 (0= Open,1= Close)"
                    DEFVAL { 0 }
                    ::= { digitalObjects 175 }

        -- 1.3.6.1.4.1.9839.2.1.1.176
        dout-17-pco1 OBJECT-TYPE
                    SYNTAX Integer32 (0..1)
                    UNITS "N/A"
                    MAX-ACCESS read-only
                    STATUS current
                    DESCRIPTION "Digital output 17 pco1 (0= Open,1= Close)"
                    DEFVAL { 0 }
                    ::= { digitalObjects 176 }

        -- 1.3.6.1.4.1.9839.2.1.1.177
        dout-18-pco1 OBJECT-TYPE
                    SYNTAX Integer32 (0..1)
                    UNITS "N/A"
                    MAX-ACCESS read-only
                    STATUS current
                    DESCRIPTION "Digital output 18 pco1 (0= Open,1= Close)"
                    DEFVAL { 0 }
                    ::= { digitalObjects 177 }

        -- 1.3.6.1.4.1.9839.2.1.1.178
        dout-1-pcoe1 OBJECT-TYPE
                    SYNTAX Integer32 (0..1)
                    UNITS "N/A"
                    MAX-ACCESS read-only
                    STATUS current
                    DESCRIPTION "Digital output 1 pcoe1 (0= Open,1= Close)"
                    DEFVAL { 0 }
                    ::= { digitalObjects 178 }

        -- 1.3.6.1.4.1.9839.2.1.1.179
        dout-2-pcoe1 OBJECT-TYPE
                    SYNTAX Integer32 (0..1)
                    UNITS "N/A"
                    MAX-ACCESS read-only
                    STATUS current
                    DESCRIPTION "Digital output 2 pcoe1 (0= Open,1= Close)"
                    DEFVAL { 0 }
                    ::= { digitalObjects 179 }

        -- 1.3.6.1.4.1.9839.2.1.1.180
        dout-3-pcoe1 OBJECT-TYPE
                    SYNTAX Integer32 (0..1)
                    UNITS "N/A"
                    MAX-ACCESS read-only
                    STATUS current
                    DESCRIPTION "Digital output 3 pcoe1 (0= Open,1= Close)"
                    DEFVAL { 0 }
                    ::= { digitalObjects 180 }

        -- 1.3.6.1.4.1.9839.2.1.1.181
        dout-4-pcoe1 OBJECT-TYPE
                    SYNTAX Integer32 (0..1)
                    UNITS "N/A"
                    MAX-ACCESS read-only
                    STATUS current
                    DESCRIPTION "Digital output 4 pcoe1 (0= Open,1= Close)"
                    DEFVAL { 0 }
                    ::= { digitalObjects 181 }

        -- 1.3.6.1.4.1.9839.2.1.1.182
        dout-1-pcoe2 OBJECT-TYPE
                    SYNTAX Integer32 (0..1)
                    UNITS "N/A"
                    MAX-ACCESS read-only
                    STATUS current
                    DESCRIPTION "Digital output 1 pcoe2 (0= Open,1= Close)"
                    DEFVAL { 0 }
                    ::= { digitalObjects 182 }

        -- 1.3.6.1.4.1.9839.2.1.1.183
        dout-2-pcoe2 OBJECT-TYPE
                    SYNTAX Integer32 (0..1)
                    UNITS "N/A"
                    MAX-ACCESS read-only
                    STATUS current
                    DESCRIPTION "Digital output 2 pcoe2 (0= Open,1= Close)"
                    DEFVAL { 0 }
                    ::= { digitalObjects 183 }

        -- 1.3.6.1.4.1.9839.2.1.1.184
        dout-3-pcoe2 OBJECT-TYPE
                    SYNTAX Integer32 (0..1)
                    UNITS "N/A"
                    MAX-ACCESS read-only
                    STATUS current
                    DESCRIPTION "Digital output 3 pcoe2 (0= Open,1= Close)"
                    DEFVAL { 0 }
                    ::= { digitalObjects 184 }

        -- 1.3.6.1.4.1.9839.2.1.1.185
        dout-4-pcoe2 OBJECT-TYPE
                    SYNTAX Integer32 (0..1)
                    UNITS "N/A"
                    MAX-ACCESS read-only
                    STATUS current
                    DESCRIPTION "Digital output 4 pcoe2 (0= Open,1= Close)"
                    DEFVAL { 0 }
                    ::= { digitalObjects 185 }

        -- 1.3.6.1.4.1.9839.2.1.1.186
        dout-1-pcoe3 OBJECT-TYPE
                    SYNTAX Integer32 (0..1)
                    UNITS "N/A"
                    MAX-ACCESS read-only
                    STATUS current
                    DESCRIPTION "Digital output 1 pcoe3 (0= Open,1= Close)"
                    DEFVAL { 0 }
                    ::= { digitalObjects 186 }

        -- 1.3.6.1.4.1.9839.2.1.1.187
        dout-2-pcoe3 OBJECT-TYPE
                    SYNTAX Integer32 (0..1)
                    UNITS "N/A"
                    MAX-ACCESS read-only
                    STATUS current
                    DESCRIPTION "Digital output 2 pcoe3 (0= Open,1= Close)"
                    DEFVAL { 0 }
                    ::= { digitalObjects 187 }

        -- 1.3.6.1.4.1.9839.2.1.1.188
        dout-3-pcoe3 OBJECT-TYPE
                    SYNTAX Integer32 (0..1)
                    UNITS "N/A"
                    MAX-ACCESS read-only
                    STATUS current
                    DESCRIPTION "Digital output 3 pcoe3 (0= Open,1= Close)"
                    DEFVAL { 0 }
                    ::= { digitalObjects 188 }

        -- 1.3.6.1.4.1.9839.2.1.1.189
        dout-4-pcoe3 OBJECT-TYPE
                    SYNTAX Integer32 (0..1)
                    UNITS "N/A"
                    MAX-ACCESS read-only
                    STATUS current
                    DESCRIPTION "Digital output 4 pcoe3 (0= Open,1= Close)"
                    DEFVAL { 0 }
                    ::= { digitalObjects 189 }

        -- 1.3.6.1.4.1.9839.2.1.1.190
        dout-1-pcoe4 OBJECT-TYPE
                    SYNTAX Integer32 (0..1)
                    UNITS "N/A"
                    MAX-ACCESS read-only
                    STATUS current
                    DESCRIPTION "Digital output 1 pcoe4 (0= Open,1= Close)"
                    DEFVAL { 0 }
                    ::= { digitalObjects 190 }

        -- 1.3.6.1.4.1.9839.2.1.1.191
        dout-2-pcoe4 OBJECT-TYPE
                    SYNTAX Integer32 (0..1)
                    UNITS "N/A"
                    MAX-ACCESS read-only
                    STATUS current
                    DESCRIPTION "Digital output 2 pcoe4 (0= Open,1= Close)"
                    DEFVAL { 0 }
                    ::= { digitalObjects 191 }

        -- 1.3.6.1.4.1.9839.2.1.1.192
        dout-3-pcoe4 OBJECT-TYPE
                    SYNTAX Integer32 (0..1)
                    UNITS "N/A"
                    MAX-ACCESS read-only
                    STATUS current
                    DESCRIPTION "Digital output 3 pcoe4 (0= Open,1= Close)"
                    DEFVAL { 0 }
                    ::= { digitalObjects 192 }

        -- 1.3.6.1.4.1.9839.2.1.1.193
        dout-4-pcoe4 OBJECT-TYPE
                    SYNTAX Integer32 (0..1)
                    UNITS "N/A"
                    MAX-ACCESS read-only
                    STATUS current
                    DESCRIPTION "Digital output 4 pcoe4 (0= Open,1= Close)"
                    DEFVAL { 0 }
                    ::= { digitalObjects 193 }

        -- 1.3.6.1.4.1.9839.2.1.1.194
        dout-1-pcoe5 OBJECT-TYPE
                    SYNTAX Integer32 (0..1)
                    UNITS "N/A"
                    MAX-ACCESS read-only
                    STATUS current
                    DESCRIPTION "Digital output 1 pcoe5 (0= Open,1= Close)"
                    DEFVAL { 0 }
                    ::= { digitalObjects 194 }

        -- 1.3.6.1.4.1.9839.2.1.1.195
        dout-2-pcoe5 OBJECT-TYPE
                    SYNTAX Integer32 (0..1)
                    UNITS "N/A"
                    MAX-ACCESS read-only
                    STATUS current
                    DESCRIPTION "Digital output 2 pcoe5 (0= Open,1= Close)"
                    DEFVAL { 0 }
                    ::= { digitalObjects 195 }

        -- 1.3.6.1.4.1.9839.2.1.1.196
        dout-3-pcoe5 OBJECT-TYPE
                    SYNTAX Integer32 (0..1)
                    UNITS "N/A"
                    MAX-ACCESS read-only
                    STATUS current
                    DESCRIPTION "Digital output 3 pcoe5 (0= Open,1= Close)"
                    DEFVAL { 0 }
                    ::= { digitalObjects 196 }

        -- 1.3.6.1.4.1.9839.2.1.1.197
        dout-4-pcoe5 OBJECT-TYPE
                    SYNTAX Integer32 (0..1)
                    UNITS "N/A"
                    MAX-ACCESS read-only
                    STATUS current
                    DESCRIPTION "Digital output 4 pcoe5 (0= Open,1= Close)"
                    DEFVAL { 0 }
                    ::= { digitalObjects 197 }

        -- 1.3.6.1.4.1.9839.2.1.1.198
        dout-1-eev1 OBJECT-TYPE
                    SYNTAX Integer32 (0..1)
                    UNITS "N/A"
                    MAX-ACCESS read-only
                    STATUS current
                    DESCRIPTION "Digital output 1 EEV1 (0= Open,1= Close)"
                    DEFVAL { 0 }
                    ::= { digitalObjects 198 }

        -- 1.3.6.1.4.1.9839.2.1.1.199
        dout-2-eev1 OBJECT-TYPE
                    SYNTAX Integer32 (0..1)
                    UNITS "N/A"
                    MAX-ACCESS read-only
                    STATUS current
                    DESCRIPTION "Digital output 2 EEV1 (0= Open,1= Close)"
                    DEFVAL { 0 }
                    ::= { digitalObjects 199 }

        -- 1.3.6.1.4.1.9839.2.1.1.220
        mal-warning OBJECT-TYPE
                    SYNTAX Integer32 (0..1)
                    UNITS "N/A"
                    MAX-ACCESS read-only
                    STATUS current
                    DESCRIPTION "AL001 - Warning alarm"
                    DEFVAL { 0 }
                    ::= { digitalObjects 220 }

        -- 1.3.6.1.4.1.9839.2.1.1.221
        mal-not-serious OBJECT-TYPE
                    SYNTAX Integer32 (0..1)
                    UNITS "N/A"
                    MAX-ACCESS read-only
                    STATUS current
                    DESCRIPTION "AL002 - Not serious alarm"
                    DEFVAL { 0 }
                    ::= { digitalObjects 221 }

        -- 1.3.6.1.4.1.9839.2.1.1.222
        mal-serious OBJECT-TYPE
                    SYNTAX Integer32 (0..1)
                    UNITS "N/A"
                    MAX-ACCESS read-only
                    STATUS current
                    DESCRIPTION "AL003 - Serious alarm"
                    DEFVAL { 0 }
                    ::= { digitalObjects 222 }

        -- 1.3.6.1.4.1.9839.2.1.1.224
        mal-circuit-1 OBJECT-TYPE
                    SYNTAX Integer32 (0..1)
                    UNITS "N/A"
                    MAX-ACCESS read-only
                    STATUS current
                    DESCRIPTION "AL004 - Circuit 1 alarm"
                    DEFVAL { 0 }
                    ::= { digitalObjects 224 }

        -- 1.3.6.1.4.1.9839.2.1.1.225
        mal-circuit-2 OBJECT-TYPE
                    SYNTAX Integer32 (0..1)
                    UNITS "N/A"
                    MAX-ACCESS read-only
                    STATUS current
                    DESCRIPTION "AL005 - Circuit 2 alarm"
                    DEFVAL { 0 }
                    ::= { digitalObjects 225 }

        -- 1.3.6.1.4.1.9839.2.1.1.230
        mal-clock OBJECT-TYPE
                    SYNTAX Integer32 (0..1)
                    UNITS "N/A"
                    MAX-ACCESS read-only
                    STATUS current
                    DESCRIPTION "AL010 - Clock alarm"
                    DEFVAL { 0 }
                    ::= { digitalObjects 230 }

        -- 1.3.6.1.4.1.9839.2.1.1.231
        mal-plan OBJECT-TYPE
                    SYNTAX Integer32 (0..1)
                    UNITS "N/A"
                    MAX-ACCESS read-only
                    STATUS current
                    DESCRIPTION "AL011 - pLAN Disconnect"
                    DEFVAL { 0 }
                    ::= { digitalObjects 231 }

        -- 1.3.6.1.4.1.9839.2.1.1.232
        mal-bms-1-offline OBJECT-TYPE
                    SYNTAX Integer32 (0..1)
                    UNITS "N/A"
                    MAX-ACCESS read-only
                    STATUS current
                    DESCRIPTION "AL012 - BMS 1 Offline alarm"
                    DEFVAL { 0 }
                    ::= { digitalObjects 232 }

        -- 1.3.6.1.4.1.9839.2.1.1.233
        mal-bms-2-offline OBJECT-TYPE
                    SYNTAX Integer32 (0..1)
                    UNITS "N/A"
                    MAX-ACCESS read-only
                    STATUS current
                    DESCRIPTION "AL013 - BMS 2 Offline alarm"
                    DEFVAL { 0 }
                    ::= { digitalObjects 233 }

        -- 1.3.6.1.4.1.9839.2.1.1.234
        mal-inlet-temp-1 OBJECT-TYPE
                    SYNTAX Integer32 (0..1)
                    UNITS "N/A"
                    MAX-ACCESS read-only
                    STATUS current
                    DESCRIPTION "AL014 - Inlet temp. probe 1 alarm"
                    DEFVAL { 0 }
                    ::= { digitalObjects 234 }

        -- 1.3.6.1.4.1.9839.2.1.1.235
        mal-inlet-temp-2 OBJECT-TYPE
                    SYNTAX Integer32 (0..1)
                    UNITS "N/A"
                    MAX-ACCESS read-only
                    STATUS current
                    DESCRIPTION "AL015 - Inlet temp. probe 2 alarm"
                    DEFVAL { 0 }
                    ::= { digitalObjects 235 }

        -- 1.3.6.1.4.1.9839.2.1.1.236
        mal-inlet-temp-3 OBJECT-TYPE
                    SYNTAX Integer32 (0..1)
                    UNITS "N/A"
                    MAX-ACCESS read-only
                    STATUS current
                    DESCRIPTION "AL016 - Inlet temp. probe 3 alarm"
                    DEFVAL { 0 }
                    ::= { digitalObjects 236 }

        -- 1.3.6.1.4.1.9839.2.1.1.237
        mal-outlet-temp-1 OBJECT-TYPE
                    SYNTAX Integer32 (0..1)
                    UNITS "N/A"
                    MAX-ACCESS read-only
                    STATUS current
                    DESCRIPTION "AL017 - Outlet temp. probe 1 alarm"
                    DEFVAL { 0 }
                    ::= { digitalObjects 237 }

        -- 1.3.6.1.4.1.9839.2.1.1.238
        mal-outlet-temp-2 OBJECT-TYPE
                    SYNTAX Integer32 (0..1)
                    UNITS "N/A"
                    MAX-ACCESS read-only
                    STATUS current
                    DESCRIPTION "AL018 - Outlet temp. probe 2 alarm"
                    DEFVAL { 0 }
                    ::= { digitalObjects 238 }

        -- 1.3.6.1.4.1.9839.2.1.1.239
        mal-outlet-temp-3 OBJECT-TYPE
                    SYNTAX Integer32 (0..1)
                    UNITS "N/A"
                    MAX-ACCESS read-only
                    STATUS current
                    DESCRIPTION "AL019 - Outlet temp. probe 3 alarm"
                    DEFVAL { 0 }
                    ::= { digitalObjects 239 }

        -- 1.3.6.1.4.1.9839.2.1.1.240
        mal-twin-valve-1 OBJECT-TYPE
                    SYNTAX Integer32 (0..1)
                    UNITS "N/A"
                    MAX-ACCESS read-only
                    STATUS current
                    DESCRIPTION "AL020 - Valve 1 inlet water temp. probe alarm"
                    DEFVAL { 0 }
                    ::= { digitalObjects 240 }

        -- 1.3.6.1.4.1.9839.2.1.1.241
        mal-twout-valve-1 OBJECT-TYPE
                    SYNTAX Integer32 (0..1)
                    UNITS "N/A"
                    MAX-ACCESS read-only
                    STATUS current
                    DESCRIPTION "AL021 - Valve 1 outlet water temp. probe alarm"
                    DEFVAL { 0 }
                    ::= { digitalObjects 241 }

        -- 1.3.6.1.4.1.9839.2.1.1.242
        mal-twby-valve-1 OBJECT-TYPE
                    SYNTAX Integer32 (0..1)
                    UNITS "N/A"
                    MAX-ACCESS read-only
                    STATUS current
                    DESCRIPTION "AL022 - Valve 1 bypass water temp. probe alarm"
                    DEFVAL { 0 }
                    ::= { digitalObjects 242 }

        -- 1.3.6.1.4.1.9839.2.1.1.243
        mal-twin-valve-2 OBJECT-TYPE
                    SYNTAX Integer32 (0..1)
                    UNITS "N/A"
                    MAX-ACCESS read-only
                    STATUS current
                    DESCRIPTION "AL023 - Valve 2 inlet water temp. probe alarm"
                    DEFVAL { 0 }
                    ::= { digitalObjects 243 }

        -- 1.3.6.1.4.1.9839.2.1.1.244
        mal-twout-valve-2 OBJECT-TYPE
                    SYNTAX Integer32 (0..1)
                    UNITS "N/A"
                    MAX-ACCESS read-only
                    STATUS current
                    DESCRIPTION "AL024 - Valve 2 outlet water temp. probe alarm"
                    DEFVAL { 0 }
                    ::= { digitalObjects 244 }

        -- 1.3.6.1.4.1.9839.2.1.1.245
        mal-twby-valve-2 OBJECT-TYPE
                    SYNTAX Integer32 (0..1)
                    UNITS "N/A"
                    MAX-ACCESS read-only
                    STATUS current
                    DESCRIPTION "AL025 - Valve 2 bypass water temp. probe alarm"
                    DEFVAL { 0 }
                    ::= { digitalObjects 245 }

        -- 1.3.6.1.4.1.9839.2.1.1.246
        mal-coil-temp OBJECT-TYPE
                    SYNTAX Integer32 (0..1)
                    UNITS "N/A"
                    MAX-ACCESS read-only
                    STATUS current
                    DESCRIPTION "AL026 - Coil temp. probe alarm"
                    DEFVAL { 0 }
                    ::= { digitalObjects 246 }

        -- 1.3.6.1.4.1.9839.2.1.1.247
        mal-external-air-temp-read OBJECT-TYPE
                    SYNTAX Integer32 (0..1)
                    UNITS "N/A"
                    MAX-ACCESS read-only
                    STATUS current
                    DESCRIPTION "AL027 - Coil temp. probe alarm"
                    DEFVAL { 0 }
                    ::= { digitalObjects 247 }

        -- 1.3.6.1.4.1.9839.2.1.1.248
        mal-inlet-humidity OBJECT-TYPE
                    SYNTAX Integer32 (0..1)
                    UNITS "N/A"
                    MAX-ACCESS read-only
                    STATUS current
                    DESCRIPTION "AL028 - Inlet humidity probe alarm"
                    DEFVAL { 0 }
                    ::= { digitalObjects 248 }

        -- 1.3.6.1.4.1.9839.2.1.1.249
        mal-outlet-humidity OBJECT-TYPE
                    SYNTAX Integer32 (0..1)
                    UNITS "N/A"
                    MAX-ACCESS read-only
                    STATUS current
                    DESCRIPTION "AL029 - Outlet humidity probe alarm"
                    DEFVAL { 0 }
                    ::= { digitalObjects 249 }

        -- 1.3.6.1.4.1.9839.2.1.1.250
        mal-ext-humidity OBJECT-TYPE
                    SYNTAX Integer32 (0..1)
                    UNITS "N/A"
                    MAX-ACCESS read-only
                    STATUS current
                    DESCRIPTION "AL030 - External air probe alarm"
                    DEFVAL { 0 }
                    ::= { digitalObjects 250 }

        -- 1.3.6.1.4.1.9839.2.1.1.251
        mal-lp-c1-probe OBJECT-TYPE
                    SYNTAX Integer32 (0..1)
                    UNITS "N/A"
                    MAX-ACCESS read-only
                    STATUS current
                    DESCRIPTION "AL031 - Low press. C1 probe alarm"
                    DEFVAL { 0 }
                    ::= { digitalObjects 251 }

        -- 1.3.6.1.4.1.9839.2.1.1.252
        mal-lp-c2-probe OBJECT-TYPE
                    SYNTAX Integer32 (0..1)
                    UNITS "N/A"
                    MAX-ACCESS read-only
                    STATUS current
                    DESCRIPTION "AL032 - Low press. C2 probe alarm"
                    DEFVAL { 0 }
                    ::= { digitalObjects 252 }

        -- 1.3.6.1.4.1.9839.2.1.1.253
        mal-hp-c1-probe OBJECT-TYPE
                    SYNTAX Integer32 (0..1)
                    UNITS "N/A"
                    MAX-ACCESS read-only
                    STATUS current
                    DESCRIPTION "AL033 - High press. C1 probe alarm"
                    DEFVAL { 0 }
                    ::= { digitalObjects 253 }

        -- 1.3.6.1.4.1.9839.2.1.1.254
        mal-hp-c2-probe OBJECT-TYPE
                    SYNTAX Integer32 (0..1)
                    UNITS "N/A"
                    MAX-ACCESS read-only
                    STATUS current
                    DESCRIPTION "AL034 - High press. C1 probe alarm"
                    DEFVAL { 0 }
                    ::= { digitalObjects 254 }

        -- 1.3.6.1.4.1.9839.2.1.1.255
        mal-t-suction-c1 OBJECT-TYPE
                    SYNTAX Integer32 (0..1)
                    UNITS "N/A"
                    MAX-ACCESS read-only
                    STATUS current
                    DESCRIPTION "AL035 - Suction temp. C1 probe alarm"
                    DEFVAL { 0 }
                    ::= { digitalObjects 255 }

        -- 1.3.6.1.4.1.9839.2.1.1.256
        mal-t-suction-c2 OBJECT-TYPE
                    SYNTAX Integer32 (0..1)
                    UNITS "N/A"
                    MAX-ACCESS read-only
                    STATUS current
                    DESCRIPTION "AL036 - Suction temp. C2 probe alarm"
                    DEFVAL { 0 }
                    ::= { digitalObjects 256 }

        -- 1.3.6.1.4.1.9839.2.1.1.257
        mal-t-discharge-c1 OBJECT-TYPE
                    SYNTAX Integer32 (0..1)
                    UNITS "N/A"
                    MAX-ACCESS read-only
                    STATUS current
                    DESCRIPTION "AL037 - Discharge temp. C1 probe alarm"
                    DEFVAL { 0 }
                    ::= { digitalObjects 257 }

        -- 1.3.6.1.4.1.9839.2.1.1.258
        mal-t-discharge-c2 OBJECT-TYPE
                    SYNTAX Integer32 (0..1)
                    UNITS "N/A"
                    MAX-ACCESS read-only
                    STATUS current
                    DESCRIPTION "AL038 - Discharge temp. C2 probe alarm"
                    DEFVAL { 0 }
                    ::= { digitalObjects 258 }

        -- 1.3.6.1.4.1.9839.2.1.1.259
        mal-tinw-condenser OBJECT-TYPE
                    SYNTAX Integer32 (0..1)
                    UNITS "N/A"
                    MAX-ACCESS read-only
                    STATUS current
                    DESCRIPTION "AL039 - Inlet condenser temp. probe alarm"
                    DEFVAL { 0 }
                    ::= { digitalObjects 259 }

        -- 1.3.6.1.4.1.9839.2.1.1.260
        mal-hot-water-in OBJECT-TYPE
                    SYNTAX Integer32 (0..1)
                    UNITS "N/A"
                    MAX-ACCESS read-only
                    STATUS current
                    DESCRIPTION "AL040 - Inlet hot water temp. probe alarm"
                    DEFVAL { 0 }
                    ::= { digitalObjects 260 }

        -- 1.3.6.1.4.1.9839.2.1.1.261
        mal-dp-sensor OBJECT-TYPE
                    SYNTAX Integer32 (0..1)
                    UNITS "N/A"
                    MAX-ACCESS read-only
                    STATUS current
                    DESCRIPTION "AL041 - DP probe alarm"
                    DEFVAL { 0 }
                    ::= { digitalObjects 261 }

        -- 1.3.6.1.4.1.9839.2.1.1.262
        mal-water-flow-valve-1 OBJECT-TYPE
                    SYNTAX Integer32 (0..1)
                    UNITS "N/A"
                    MAX-ACCESS read-only
                    STATUS current
                    DESCRIPTION "AL042 - Water flow valve 1 probe alarm"
                    DEFVAL { 0 }
                    ::= { digitalObjects 262 }

        -- 1.3.6.1.4.1.9839.2.1.1.263
        mal-water-flow-valve-2 OBJECT-TYPE
                    SYNTAX Integer32 (0..1)
                    UNITS "N/A"
                    MAX-ACCESS read-only
                    STATUS current
                    DESCRIPTION "AL043 - Water flow valve 2 probe alarm"
                    DEFVAL { 0 }
                    ::= { digitalObjects 263 }

        -- 1.3.6.1.4.1.9839.2.1.1.264
        mal-electrical-panel-temp OBJECT-TYPE
                    SYNTAX Integer32 (0..1)
                    UNITS "N/A"
                    MAX-ACCESS read-only
                    STATUS current
                    DESCRIPTION "AL044 - Electrical panel temp. probe alarm"
                    DEFVAL { 0 }
                    ::= { digitalObjects 264 }

        -- 1.3.6.1.4.1.9839.2.1.1.265
        mal-fans-speed-analog-request OBJECT-TYPE
                    SYNTAX Integer32 (0..1)
                    UNITS "N/A"
                    MAX-ACCESS read-only
                    STATUS current
                    DESCRIPTION "AL045 - Analog request alarm"
                    DEFVAL { 0 }
                    ::= { digitalObjects 265 }

        -- 1.3.6.1.4.1.9839.2.1.1.266
        mal-airflow-by-switch OBJECT-TYPE
                    SYNTAX Integer32 (0..1)
                    UNITS "N/A"
                    MAX-ACCESS read-only
                    STATUS current
                    DESCRIPTION "AL046 - Airflow alarm"
                    DEFVAL { 0 }
                    ::= { digitalObjects 266 }

        -- 1.3.6.1.4.1.9839.2.1.1.267
        mal-airflow-by-probe OBJECT-TYPE
                    SYNTAX Integer32 (0..1)
                    UNITS "N/A"
                    MAX-ACCESS read-only
                    STATUS current
                    DESCRIPTION "AL047 - Airflow alarm by automatic control"
                    DEFVAL { 0 }
                    ::= { digitalObjects 267 }

        -- 1.3.6.1.4.1.9839.2.1.1.268
        mal-dirty-filter OBJECT-TYPE
                    SYNTAX Integer32 (0..1)
                    UNITS "N/A"
                    MAX-ACCESS read-only
                    STATUS current
                    DESCRIPTION "AL048 - Dirty filter alarm"
                    DEFVAL { 0 }
                    ::= { digitalObjects 268 }

        -- 1.3.6.1.4.1.9839.2.1.1.269
        mal-thermal-fan-alarm OBJECT-TYPE
                    SYNTAX Integer32 (0..1)
                    UNITS "N/A"
                    MAX-ACCESS read-only
                    STATUS current
                    DESCRIPTION "AL049 - Thermal fan alarm"
                    DEFVAL { 0 }
                    ::= { digitalObjects 269 }

        -- 1.3.6.1.4.1.9839.2.1.1.270
        mal-power-supply OBJECT-TYPE
                    SYNTAX Integer32 (0..1)
                    UNITS "N/A"
                    MAX-ACCESS read-only
                    STATUS current
                    DESCRIPTION "AL050 - Power supply alarm"
                    DEFVAL { 0 }
                    ::= { digitalObjects 270 }

        -- 1.3.6.1.4.1.9839.2.1.1.271
        mal-heater-step-1 OBJECT-TYPE
                    SYNTAX Integer32 (0..1)
                    UNITS "N/A"
                    MAX-ACCESS read-only
                    STATUS current
                    DESCRIPTION "AL051 - Heater step 1 alarm"
                    DEFVAL { 0 }
                    ::= { digitalObjects 271 }

        -- 1.3.6.1.4.1.9839.2.1.1.272
        mal-heater-step-2 OBJECT-TYPE
                    SYNTAX Integer32 (0..1)
                    UNITS "N/A"
                    MAX-ACCESS read-only
                    STATUS current
                    DESCRIPTION "AL052 - Heater step 2 alarm"
                    DEFVAL { 0 }
                    ::= { digitalObjects 272 }

        -- 1.3.6.1.4.1.9839.2.1.1.273
        mal-lp-c1-by-switch OBJECT-TYPE
                    SYNTAX Integer32 (0..1)
                    UNITS "N/A"
                    MAX-ACCESS read-only
                    STATUS current
                    DESCRIPTION "AL053 - Low pressure C1 alarm by pressostat"
                    DEFVAL { 0 }
                    ::= { digitalObjects 273 }

        -- 1.3.6.1.4.1.9839.2.1.1.274
        mal-lp-c2-by-switch OBJECT-TYPE
                    SYNTAX Integer32 (0..1)
                    UNITS "N/A"
                    MAX-ACCESS read-only
                    STATUS current
                    DESCRIPTION "AL054 - Low pressure C2 alarm by pressostat"
                    DEFVAL { 0 }
                    ::= { digitalObjects 274 }

        -- 1.3.6.1.4.1.9839.2.1.1.275
        mal-hp-c1-by-switch OBJECT-TYPE
                    SYNTAX Integer32 (0..1)
                    UNITS "N/A"
                    MAX-ACCESS read-only
                    STATUS current
                    DESCRIPTION "AL055 - High pressure C1 alarm by pressostat"
                    DEFVAL { 0 }
                    ::= { digitalObjects 275 }

        -- 1.3.6.1.4.1.9839.2.1.1.276
        mal-hp-c2-by-switch OBJECT-TYPE
                    SYNTAX Integer32 (0..1)
                    UNITS "N/A"
                    MAX-ACCESS read-only
                    STATUS current
                    DESCRIPTION "AL056 - High pressure C2 alarm by pressostat"
                    DEFVAL { 0 }
                    ::= { digitalObjects 276 }

        -- 1.3.6.1.4.1.9839.2.1.1.277
        mal-lp-c1-by-probe OBJECT-TYPE
                    SYNTAX Integer32 (0..1)
                    UNITS "N/A"
                    MAX-ACCESS read-only
                    STATUS current
                    DESCRIPTION "AL057 - Low pressure C1 alarm by probe"
                    DEFVAL { 0 }
                    ::= { digitalObjects 277 }

        -- 1.3.6.1.4.1.9839.2.1.1.278
        mal-lp-c2-by-probe OBJECT-TYPE
                    SYNTAX Integer32 (0..1)
                    UNITS "N/A"
                    MAX-ACCESS read-only
                    STATUS current
                    DESCRIPTION "AL058 - Low pressure C2 alarm by probe"
                    DEFVAL { 0 }
                    ::= { digitalObjects 278 }

        -- 1.3.6.1.4.1.9839.2.1.1.279
        mal-hp-c1-by-probe OBJECT-TYPE
                    SYNTAX Integer32 (0..1)
                    UNITS "N/A"
                    MAX-ACCESS read-only
                    STATUS current
                    DESCRIPTION "AL059 - High pressure C1 alarm by probe"
                    DEFVAL { 0 }
                    ::= { digitalObjects 279 }

        -- 1.3.6.1.4.1.9839.2.1.1.280
        mal-hp-c2-by-probe OBJECT-TYPE
                    SYNTAX Integer32 (0..1)
                    UNITS "N/A"
                    MAX-ACCESS read-only
                    STATUS current
                    DESCRIPTION "AL060 - High pressure C2 alarm by probe"
                    DEFVAL { 0 }
                    ::= { digitalObjects 280 }

        -- 1.3.6.1.4.1.9839.2.1.1.281
        mal-thermal-head-comp-inv-1 OBJECT-TYPE
                    SYNTAX Integer32 (0..1)
                    UNITS "N/A"
                    MAX-ACCESS read-only
                    STATUS current
                    DESCRIPTION "AL061 - Thermal head comp. inverter 1"
                    DEFVAL { 0 }
                    ::= { digitalObjects 281 }

        -- 1.3.6.1.4.1.9839.2.1.1.282
        mal-thermal-head-comp-inv-2 OBJECT-TYPE
                    SYNTAX Integer32 (0..1)
                    UNITS "N/A"
                    MAX-ACCESS read-only
                    STATUS current
                    DESCRIPTION "AL062 - Thermal head comp. inverter 2"
                    DEFVAL { 0 }
                    ::= { digitalObjects 282 }

        -- 1.3.6.1.4.1.9839.2.1.1.283
        mal-flow-switch-valve-1 OBJECT-TYPE
                    SYNTAX Integer32 (0..1)
                    UNITS "N/A"
                    MAX-ACCESS read-only
                    STATUS current
                    DESCRIPTION "AL063 - Flow switch valve 1 alarm"
                    DEFVAL { 0 }
                    ::= { digitalObjects 283 }

        -- 1.3.6.1.4.1.9839.2.1.1.284
        mal-flow-switch-valve-2 OBJECT-TYPE
                    SYNTAX Integer32 (0..1)
                    UNITS "N/A"
                    MAX-ACCESS read-only
                    STATUS current
                    DESCRIPTION "AL064 - Flow switch valve 1 alarm"
                    DEFVAL { 0 }
                    ::= { digitalObjects 284 }

        -- 1.3.6.1.4.1.9839.2.1.1.285
        mal-ext-humidifier-alarm OBJECT-TYPE
                    SYNTAX Integer32 (0..1)
                    UNITS "N/A"
                    MAX-ACCESS read-only
                    STATUS current
                    DESCRIPTION "AL065 - External humidifier alarm"
                    DEFVAL { 0 }
                    ::= { digitalObjects 285 }

        -- 1.3.6.1.4.1.9839.2.1.1.286
        mal-flooding OBJECT-TYPE
                    SYNTAX Integer32 (0..1)
                    UNITS "N/A"
                    MAX-ACCESS read-only
                    STATUS current
                    DESCRIPTION "AL066 - Flooding alarm"
                    DEFVAL { 0 }
                    ::= { digitalObjects 286 }

        -- 1.3.6.1.4.1.9839.2.1.1.287
        mal-fire-smoke OBJECT-TYPE
                    SYNTAX Integer32 (0..1)
                    UNITS "N/A"
                    MAX-ACCESS read-only
                    STATUS current
                    DESCRIPTION "AL067 - Fire/smoke alarm"
                    DEFVAL { 0 }
                    ::= { digitalObjects 287 }

        -- 1.3.6.1.4.1.9839.2.1.1.288
        mal-settable-1 OBJECT-TYPE
                    SYNTAX Integer32 (0..1)
                    UNITS "N/A"
                    MAX-ACCESS read-only
                    STATUS current
                    DESCRIPTION "AL068 - Settable alarm 1"
                    DEFVAL { 0 }
                    ::= { digitalObjects 288 }

        -- 1.3.6.1.4.1.9839.2.1.1.289
        mal-settable-2 OBJECT-TYPE
                    SYNTAX Integer32 (0..1)
                    UNITS "N/A"
                    MAX-ACCESS read-only
                    STATUS current
                    DESCRIPTION "AL069 - Settable alarm 2"
                    DEFVAL { 0 }
                    ::= { digitalObjects 289 }

        -- 1.3.6.1.4.1.9839.2.1.1.290
        mal-settable-3 OBJECT-TYPE
                    SYNTAX Integer32 (0..1)
                    UNITS "N/A"
                    MAX-ACCESS read-only
                    STATUS current
                    DESCRIPTION "AL070 - Settable alarm 3"
                    DEFVAL { 0 }
                    ::= { digitalObjects 290 }

        -- 1.3.6.1.4.1.9839.2.1.1.291
        mal-high-room-temp-1 OBJECT-TYPE
                    SYNTAX Integer32 (0..1)
                    UNITS "N/A"
                    MAX-ACCESS read-only
                    STATUS current
                    DESCRIPTION "AL071 - High room temp. alarm 1"
                    DEFVAL { 0 }
                    ::= { digitalObjects 291 }

        -- 1.3.6.1.4.1.9839.2.1.1.292
        mal-low-room-temp OBJECT-TYPE
                    SYNTAX Integer32 (0..1)
                    UNITS "N/A"
                    MAX-ACCESS read-only
                    STATUS current
                    DESCRIPTION "AL072 - Low room temp. alarm"
                    DEFVAL { 0 }
                    ::= { digitalObjects 292 }

        -- 1.3.6.1.4.1.9839.2.1.1.293
        mal-high-room-humidity OBJECT-TYPE
                    SYNTAX Integer32 (0..1)
                    UNITS "N/A"
                    MAX-ACCESS read-only
                    STATUS current
                    DESCRIPTION "AL073 - High room humidity alarm"
                    DEFVAL { 0 }
                    ::= { digitalObjects 293 }

        -- 1.3.6.1.4.1.9839.2.1.1.294
        mal-low-room-humidity OBJECT-TYPE
                    SYNTAX Integer32 (0..1)
                    UNITS "N/A"
                    MAX-ACCESS read-only
                    STATUS current
                    DESCRIPTION "AL074 - Low room humidity alarm"
                    DEFVAL { 0 }
                    ::= { digitalObjects 294 }

        -- 1.3.6.1.4.1.9839.2.1.1.295
        fc-alarm OBJECT-TYPE
                    SYNTAX Integer32 (0..1)
                    UNITS "N/A"
                    MAX-ACCESS read-only
                    STATUS current
                    DESCRIPTION "AL075 - Freecooling low temperature alarm"
                    DEFVAL { 0 }
                    ::= { digitalObjects 295 }

        -- 1.3.6.1.4.1.9839.2.1.1.296
        mal-start-failure-env-1 OBJECT-TYPE
                    SYNTAX Integer32 (0..1)
                    UNITS "N/A"
                    MAX-ACCESS read-only
                    STATUS current
                    DESCRIPTION "AL076 - Start failure envelope 1 alarm"
                    DEFVAL { 0 }
                    ::= { digitalObjects 296 }

        -- 1.3.6.1.4.1.9839.2.1.1.297
        mal-max-discharge-temp-env-1 OBJECT-TYPE
                    SYNTAX Integer32 (0..1)
                    UNITS "N/A"
                    MAX-ACCESS read-only
                    STATUS current
                    DESCRIPTION "AL077 - Max discharge temp. envelope 1 alarm"
                    DEFVAL { 0 }
                    ::= { digitalObjects 297 }

        -- 1.3.6.1.4.1.9839.2.1.1.298
        mal-max-hp-env-1 OBJECT-TYPE
                    SYNTAX Integer32 (0..1)
                    UNITS "N/A"
                    MAX-ACCESS read-only
                    STATUS current
                    DESCRIPTION "AL078 - Max condensing pressure envelope 1 alarm"
                    DEFVAL { 0 }
                    ::= { digitalObjects 298 }

        -- 1.3.6.1.4.1.9839.2.1.1.299
        mal-min-lp-env-1 OBJECT-TYPE
                    SYNTAX Integer32 (0..1)
                    UNITS "N/A"
                    MAX-ACCESS read-only
                    STATUS current
                    DESCRIPTION "AL079 - Min evaporating pressure envelope 1 alarm"
                    DEFVAL { 0 }
                    ::= { digitalObjects 299 }

        -- 1.3.6.1.4.1.9839.2.1.1.300
        mal-max-lp-env-1 OBJECT-TYPE
                    SYNTAX Integer32 (0..1)
                    UNITS "N/A"
                    MAX-ACCESS read-only
                    STATUS current
                    DESCRIPTION "AL080 - Max evaporating pressure envelope 1 alarm"
                    DEFVAL { 0 }
                    ::= { digitalObjects 300 }

        -- 1.3.6.1.4.1.9839.2.1.1.301
        mal-min-dp-env-1 OBJECT-TYPE
                    SYNTAX Integer32 (0..1)
                    UNITS "N/A"
                    MAX-ACCESS read-only
                    STATUS current
                    DESCRIPTION "AL081 - Min differential pressure envelope 1 alarm"
                    DEFVAL { 0 }
                    ::= { digitalObjects 301 }

        -- 1.3.6.1.4.1.9839.2.1.1.302
        mal-min-rp-env-1 OBJECT-TYPE
                    SYNTAX Integer32 (0..1)
                    UNITS "N/A"
                    MAX-ACCESS read-only
                    STATUS current
                    DESCRIPTION "AL082 - Min pressure ratio envelope 1 alarm"
                    DEFVAL { 0 }
                    ::= { digitalObjects 302 }

        -- 1.3.6.1.4.1.9839.2.1.1.303
        mal-start-failure-env-2 OBJECT-TYPE
                    SYNTAX Integer32 (0..1)
                    UNITS "N/A"
                    MAX-ACCESS read-only
                    STATUS current
                    DESCRIPTION "AL083 - Start failure envelope 2 alarm"
                    DEFVAL { 0 }
                    ::= { digitalObjects 303 }

        -- 1.3.6.1.4.1.9839.2.1.1.304
        mal-max-discharge-temp-env-2 OBJECT-TYPE
                    SYNTAX Integer32 (0..1)
                    UNITS "N/A"
                    MAX-ACCESS read-only
                    STATUS current
                    DESCRIPTION "AL084 - Max discharge temp. envelope 1 alarm"
                    DEFVAL { 0 }
                    ::= { digitalObjects 304 }

        -- 1.3.6.1.4.1.9839.2.1.1.305
        mal-max-hp-env-2 OBJECT-TYPE
                    SYNTAX Integer32 (0..1)
                    UNITS "N/A"
                    MAX-ACCESS read-only
                    STATUS current
                    DESCRIPTION "AL085 - Max condensing pressure envelope 2 alarm"
                    DEFVAL { 0 }
                    ::= { digitalObjects 305 }

        -- 1.3.6.1.4.1.9839.2.1.1.306
        mal-min-lp-env-2 OBJECT-TYPE
                    SYNTAX Integer32 (0..1)
                    UNITS "N/A"
                    MAX-ACCESS read-only
                    STATUS current
                    DESCRIPTION "AL086 - Min evaporating pressure envelope 2 alarm"
                    DEFVAL { 0 }
                    ::= { digitalObjects 306 }

        -- 1.3.6.1.4.1.9839.2.1.1.307
        mal-max-lp-env-2 OBJECT-TYPE
                    SYNTAX Integer32 (0..1)
                    UNITS "N/A"
                    MAX-ACCESS read-only
                    STATUS current
                    DESCRIPTION "AL087 - Max evaporating pressure envelope 2 alarm"
                    DEFVAL { 0 }
                    ::= { digitalObjects 307 }

        -- 1.3.6.1.4.1.9839.2.1.1.308
        mal-min-dp-env-2 OBJECT-TYPE
                    SYNTAX Integer32 (0..1)
                    UNITS "N/A"
                    MAX-ACCESS read-only
                    STATUS current
                    DESCRIPTION "AL088 - Min differential pressure envelope 2 alarm"
                    DEFVAL { 0 }
                    ::= { digitalObjects 308 }

        -- 1.3.6.1.4.1.9839.2.1.1.309
        mal-min-rp-env-2 OBJECT-TYPE
                    SYNTAX Integer32 (0..1)
                    UNITS "N/A"
                    MAX-ACCESS read-only
                    STATUS current
                    DESCRIPTION "AL089 - Min pressure ratio envelope 2 alarm"
                    DEFVAL { 0 }
                    ::= { digitalObjects 309 }

        -- 1.3.6.1.4.1.9839.2.1.1.310
        al-working-hours-comp-1 OBJECT-TYPE
                    SYNTAX Integer32 (0..1)
                    UNITS "N/A"
                    MAX-ACCESS read-only
                    STATUS current
                    DESCRIPTION "AL090 - Working hours compressor 1 alarm"
                    DEFVAL { 0 }
                    ::= { digitalObjects 310 }

        -- 1.3.6.1.4.1.9839.2.1.1.311
        al-working-hours-comp-2 OBJECT-TYPE
                    SYNTAX Integer32 (0..1)
                    UNITS "N/A"
                    MAX-ACCESS read-only
                    STATUS current
                    DESCRIPTION "AL091 - Working hours compressor 2 alarm"
                    DEFVAL { 0 }
                    ::= { digitalObjects 311 }

        -- 1.3.6.1.4.1.9839.2.1.1.312
        al-working-hours-comp-3 OBJECT-TYPE
                    SYNTAX Integer32 (0..1)
                    UNITS "N/A"
                    MAX-ACCESS read-only
                    STATUS current
                    DESCRIPTION "AL092 - Working hours compressor 3 alarm"
                    DEFVAL { 0 }
                    ::= { digitalObjects 312 }

        -- 1.3.6.1.4.1.9839.2.1.1.313
        al-working-hours-comp-4 OBJECT-TYPE
                    SYNTAX Integer32 (0..1)
                    UNITS "N/A"
                    MAX-ACCESS read-only
                    STATUS current
                    DESCRIPTION "AL093 - Working hours compressor 3 alarm"
                    DEFVAL { 0 }
                    ::= { digitalObjects 313 }

        -- 1.3.6.1.4.1.9839.2.1.1.314
        al-working-hours-comp-5 OBJECT-TYPE
                    SYNTAX Integer32 (0..1)
                    UNITS "N/A"
                    MAX-ACCESS read-only
                    STATUS current
                    DESCRIPTION "AL094 - Working hours compressor 5 alarm"
                    DEFVAL { 0 }
                    ::= { digitalObjects 314 }

        -- 1.3.6.1.4.1.9839.2.1.1.315
        al-working-hours-comp-6 OBJECT-TYPE
                    SYNTAX Integer32 (0..1)
                    UNITS "N/A"
                    MAX-ACCESS read-only
                    STATUS current
                    DESCRIPTION "AL095 - Working hours compressor 6 alarm"
                    DEFVAL { 0 }
                    ::= { digitalObjects 315 }

        -- 1.3.6.1.4.1.9839.2.1.1.316
        al-working-hours-fans OBJECT-TYPE
                    SYNTAX Integer32 (0..1)
                    UNITS "N/A"
                    MAX-ACCESS read-only
                    STATUS current
                    DESCRIPTION "AL096 - Working hours fans alarm"
                    DEFVAL { 0 }
                    ::= { digitalObjects 316 }

        -- 1.3.6.1.4.1.9839.2.1.1.317
        al-working-hours-filter OBJECT-TYPE
                    SYNTAX Integer32 (0..1)
                    UNITS "N/A"
                    MAX-ACCESS read-only
                    STATUS current
                    DESCRIPTION "AL097 - Working hours filter alarm"
                    DEFVAL { 0 }
                    ::= { digitalObjects 317 }

        -- 1.3.6.1.4.1.9839.2.1.1.318
        al-working-hours-humidifier OBJECT-TYPE
                    SYNTAX Integer32 (0..1)
                    UNITS "N/A"
                    MAX-ACCESS read-only
                    STATUS current
                    DESCRIPTION "AL098 - Working hours humidifier alarm"
                    DEFVAL { 0 }
                    ::= { digitalObjects 318 }

        -- 1.3.6.1.4.1.9839.2.1.1.319
        al-working-hours-heater OBJECT-TYPE
                    SYNTAX Integer32 (0..1)
                    UNITS "N/A"
                    MAX-ACCESS read-only
                    STATUS current
                    DESCRIPTION "AL097 - Working hours heater alarm"
                    DEFVAL { 0 }
                    ::= { digitalObjects 319 }

        -- 1.3.6.1.4.1.9839.2.1.1.320
        al-working-hours-fc OBJECT-TYPE
                    SYNTAX Integer32 (0..1)
                    UNITS "N/A"
                    MAX-ACCESS read-only
                    STATUS current
                    DESCRIPTION "AL100 - Working hours FC alarm"
                    DEFVAL { 0 }
                    ::= { digitalObjects 320 }

        -- 1.3.6.1.4.1.9839.2.1.1.321
        mal-pcoe-1-offline OBJECT-TYPE
                    SYNTAX Integer32 (0..1)
                    UNITS "N/A"
                    MAX-ACCESS read-only
                    STATUS current
                    DESCRIPTION "AL101 - pCOE 1 offline alarm"
                    DEFVAL { 0 }
                    ::= { digitalObjects 321 }

        -- 1.3.6.1.4.1.9839.2.1.1.322
        mal-pcoe-2-offline OBJECT-TYPE
                    SYNTAX Integer32 (0..1)
                    UNITS "N/A"
                    MAX-ACCESS read-only
                    STATUS current
                    DESCRIPTION "AL102 - pCOE 2 offline alarm"
                    DEFVAL { 0 }
                    ::= { digitalObjects 322 }

        -- 1.3.6.1.4.1.9839.2.1.1.323
        mal-pcoe-3-offline OBJECT-TYPE
                    SYNTAX Integer32 (0..1)
                    UNITS "N/A"
                    MAX-ACCESS read-only
                    STATUS current
                    DESCRIPTION "AL103 - pCOE 3 offline alarm"
                    DEFVAL { 0 }
                    ::= { digitalObjects 323 }

        -- 1.3.6.1.4.1.9839.2.1.1.324
        mal-pcoe-4-offline OBJECT-TYPE
                    SYNTAX Integer32 (0..1)
                    UNITS "N/A"
                    MAX-ACCESS read-only
                    STATUS current
                    DESCRIPTION "AL104 - pCOE 4 offline alarm"
                    DEFVAL { 0 }
                    ::= { digitalObjects 324 }

        -- 1.3.6.1.4.1.9839.2.1.1.325
        mal-pcoe-5-offline OBJECT-TYPE
                    SYNTAX Integer32 (0..1)
                    UNITS "N/A"
                    MAX-ACCESS read-only
                    STATUS current
                    DESCRIPTION "AL105 - pCOE 5 offline alarm"
                    DEFVAL { 0 }
                    ::= { digitalObjects 325 }

        -- 1.3.6.1.4.1.9839.2.1.1.326
        mal-offline-eev-1 OBJECT-TYPE
                    SYNTAX Integer32 (0..1)
                    UNITS "N/A"
                    MAX-ACCESS read-only
                    STATUS current
                    DESCRIPTION "AL106 - EEV 1 offline alarm"
                    DEFVAL { 0 }
                    ::= { digitalObjects 326 }

        -- 1.3.6.1.4.1.9839.2.1.1.327
        mal-lan-error-eev-1 OBJECT-TYPE
                    SYNTAX Integer32 (0..1)
                    UNITS "N/A"
                    MAX-ACCESS read-only
                    STATUS current
                    DESCRIPTION "AL107 - EEV 1 Lan error"
                    DEFVAL { 0 }
                    ::= { digitalObjects 327 }

        -- 1.3.6.1.4.1.9839.2.1.1.328
        mal-eprom-error-eev-1 OBJECT-TYPE
                    SYNTAX Integer32 (0..1)
                    UNITS "N/A"
                    MAX-ACCESS read-only
                    STATUS current
                    DESCRIPTION "AL108 - EEV 1 Eprom error"
                    DEFVAL { 0 }
                    ::= { digitalObjects 328 }

        -- 1.3.6.1.4.1.9839.2.1.1.329
        mal-step-motor-eev-1 OBJECT-TYPE
                    SYNTAX Integer32 (0..1)
                    UNITS "N/A"
                    MAX-ACCESS read-only
                    STATUS current
                    DESCRIPTION "AL109 - EEV 1 Step motor error"
                    DEFVAL { 0 }
                    ::= { digitalObjects 329 }

        -- 1.3.6.1.4.1.9839.2.1.1.330
        mal-fw-not-compatible-eev-1 OBJECT-TYPE
                    SYNTAX Integer32 (0..1)
                    UNITS "N/A"
                    MAX-ACCESS read-only
                    STATUS current
                    DESCRIPTION "AL110 - EEV 1 Firmware not compatible"
                    DEFVAL { 0 }
                    ::= { digitalObjects 330 }

        -- 1.3.6.1.4.1.9839.2.1.1.331
        mal-offline-eev-2 OBJECT-TYPE
                    SYNTAX Integer32 (0..1)
                    UNITS "N/A"
                    MAX-ACCESS read-only
                    STATUS current
                    DESCRIPTION "AL111 - EEV 2 offline alarm"
                    DEFVAL { 0 }
                    ::= { digitalObjects 331 }

        -- 1.3.6.1.4.1.9839.2.1.1.332
        mal-lan-error-eev-2 OBJECT-TYPE
                    SYNTAX Integer32 (0..1)
                    UNITS "N/A"
                    MAX-ACCESS read-only
                    STATUS current
                    DESCRIPTION "AL112 - EEV 2 Lan error"
                    DEFVAL { 0 }
                    ::= { digitalObjects 332 }

        -- 1.3.6.1.4.1.9839.2.1.1.333
        mal-eprom-error-eev-2 OBJECT-TYPE
                    SYNTAX Integer32 (0..1)
                    UNITS "N/A"
                    MAX-ACCESS read-only
                    STATUS current
                    DESCRIPTION "AL113 - EEV 2 Eprom error"
                    DEFVAL { 0 }
                    ::= { digitalObjects 333 }

        -- 1.3.6.1.4.1.9839.2.1.1.334
        mal-step-motor-eev-2 OBJECT-TYPE
                    SYNTAX Integer32 (0..1)
                    UNITS "N/A"
                    MAX-ACCESS read-only
                    STATUS current
                    DESCRIPTION "AL114 - EEV 2 Step motor error"
                    DEFVAL { 0 }
                    ::= { digitalObjects 334 }

        -- 1.3.6.1.4.1.9839.2.1.1.335
        mal-fw-not-compatible-eev-2 OBJECT-TYPE
                    SYNTAX Integer32 (0..1)
                    UNITS "N/A"
                    MAX-ACCESS read-only
                    STATUS current
                    DESCRIPTION "AL115 - EEV 2 Firmware not compatible"
                    DEFVAL { 0 }
                    ::= { digitalObjects 335 }

        -- 1.3.6.1.4.1.9839.2.1.1.336
        mal-general-alarm-inv-1 OBJECT-TYPE
                    SYNTAX Integer32 (0..1)
                    UNITS "N/A"
                    MAX-ACCESS read-only
                    STATUS current
                    DESCRIPTION "AL116 - General alarm inverter 1"
                    DEFVAL { 0 }
                    ::= { digitalObjects 336 }

        -- 1.3.6.1.4.1.9839.2.1.1.337
        mal-display-loss-inv-1 OBJECT-TYPE
                    SYNTAX Integer32 (0..1)
                    UNITS "N/A"
                    MAX-ACCESS read-only
                    STATUS current
                    DESCRIPTION "AL117 - Display loss alarm inverter 1"
                    DEFVAL { 0 }
                    ::= { digitalObjects 337 }

        -- 1.3.6.1.4.1.9839.2.1.1.338
        mal-safe-torque-off-inv-1 OBJECT-TYPE
                    SYNTAX Integer32 (0..1)
                    UNITS "N/A"
                    MAX-ACCESS read-only
                    STATUS current
                    DESCRIPTION "AL118 - Safe torque Off alarm inverter 1"
                    DEFVAL { 0 }
                    ::= { digitalObjects 338 }

        -- 1.3.6.1.4.1.9839.2.1.1.339
        mal-sto-1-loss-inv-1 OBJECT-TYPE
                    SYNTAX Integer32 (0..1)
                    UNITS "N/A"
                    MAX-ACCESS read-only
                    STATUS current
                    DESCRIPTION "AL119 - STO 1 loss alarm inverter 1"
                    DEFVAL { 0 }
                    ::= { digitalObjects 339 }

        -- 1.3.6.1.4.1.9839.2.1.1.340
        mal-sto-2-loss-inv-1 OBJECT-TYPE
                    SYNTAX Integer32 (0..1)
                    UNITS "N/A"
                    MAX-ACCESS read-only
                    STATUS current
                    DESCRIPTION "AL120 - STO 2 loss alarm inverter 1"
                    DEFVAL { 0 }
                    ::= { digitalObjects 340 }

        -- 1.3.6.1.4.1.9839.2.1.1.341
        mal-underload-inv-1 OBJECT-TYPE
                    SYNTAX Integer32 (0..1)
                    UNITS "N/A"
                    MAX-ACCESS read-only
                    STATUS current
                    DESCRIPTION "AL121 - Underload alarm inverter 1"
                    DEFVAL { 0 }
                    ::= { digitalObjects 341 }

        -- 1.3.6.1.4.1.9839.2.1.1.342
        mal-stall-motor-inv-1 OBJECT-TYPE
                    SYNTAX Integer32 (0..1)
                    UNITS "N/A"
                    MAX-ACCESS read-only
                    STATUS current
                    DESCRIPTION "AL122 - Stall motor alarm inverter 1"
                    DEFVAL { 0 }
                    ::= { digitalObjects 342 }

        -- 1.3.6.1.4.1.9839.2.1.1.343
        mal-encoder-error-inv-1 OBJECT-TYPE
                    SYNTAX Integer32 (0..1)
                    UNITS "N/A"
                    MAX-ACCESS read-only
                    STATUS current
                    DESCRIPTION "AL123 - Encoder error inverter 1"
                    DEFVAL { 0 }
                    ::= { digitalObjects 343 }

        -- 1.3.6.1.4.1.9839.2.1.1.344
        mal-parameter-setting-error-inv-1 OBJECT-TYPE
                    SYNTAX Integer32 (0..1)
                    UNITS "N/A"
                    MAX-ACCESS read-only
                    STATUS current
                    DESCRIPTION "AL124 - Parameter setting error inverter 1"
                    DEFVAL { 0 }
                    ::= { digitalObjects 344 }

        -- 1.3.6.1.4.1.9839.2.1.1.345
        mal-sw-incompatible-inv-1 OBJECT-TYPE
                    SYNTAX Integer32 (0..1)
                    UNITS "N/A"
                    MAX-ACCESS read-only
                    STATUS current
                    DESCRIPTION "AL125 - SW Incompatible alarm inverter 1"
                    DEFVAL { 0 }
                    ::= { digitalObjects 345 }

        -- 1.3.6.1.4.1.9839.2.1.1.346
        mal-config-file-error-inv-1 OBJECT-TYPE
                    SYNTAX Integer32 (0..1)
                    UNITS "N/A"
                    MAX-ACCESS read-only
                    STATUS current
                    DESCRIPTION "AL126 - Configuration file error inverter 1"
                    DEFVAL { 0 }
                    ::= { digitalObjects 346 }

        -- 1.3.6.1.4.1.9839.2.1.1.347
        mal-config-file-reading-error-inv-1 OBJECT-TYPE
                    SYNTAX Integer32 (0..1)
                    UNITS "N/A"
                    MAX-ACCESS read-only
                    STATUS current
                    DESCRIPTION "AL127 - Configuration file reading error inverter 1"
                    DEFVAL { 0 }
                    ::= { digitalObjects 347 }

        -- 1.3.6.1.4.1.9839.2.1.1.348
        mal-overcurrent-motor-inv-1 OBJECT-TYPE
                    SYNTAX Integer32 (0..1)
                    UNITS "N/A"
                    MAX-ACCESS read-only
                    STATUS current
                    DESCRIPTION "AL128 - Overcurrent motor inverter 1"
                    DEFVAL { 0 }
                    ::= { digitalObjects 348 }

        -- 1.3.6.1.4.1.9839.2.1.1.349
        mal-read-current-error-inv-1 OBJECT-TYPE
                    SYNTAX Integer32 (0..1)
                    UNITS "N/A"
                    MAX-ACCESS read-only
                    STATUS current
                    DESCRIPTION "AL129 - Read current error inverter 1"
                    DEFVAL { 0 }
                    ::= { digitalObjects 349 }

        -- 1.3.6.1.4.1.9839.2.1.1.350
        mal-high-voltage-dc-bus-inv-1 OBJECT-TYPE
                    SYNTAX Integer32 (0..1)
                    UNITS "N/A"
                    MAX-ACCESS read-only
                    STATUS current
                    DESCRIPTION "AL130 - High voltage DC BUS alarm inverter 1"
                    DEFVAL { 0 }
                    ::= { digitalObjects 350 }

        -- 1.3.6.1.4.1.9839.2.1.1.351
        mal-low-voltage-dc-bus-inv-1 OBJECT-TYPE
                    SYNTAX Integer32 (0..1)
                    UNITS "N/A"
                    MAX-ACCESS read-only
                    STATUS current
                    DESCRIPTION "AL131 - Low voltage DC BUS alarm inverter 1"
                    DEFVAL { 0 }
                    ::= { digitalObjects 351 }

        -- 1.3.6.1.4.1.9839.2.1.1.352
        mal-high-temp-igbt-inv-1 OBJECT-TYPE
                    SYNTAX Integer32 (0..1)
                    UNITS "N/A"
                    MAX-ACCESS read-only
                    STATUS current
                    DESCRIPTION "AL132 - High temperature IGBT alarm inverter 1"
                    DEFVAL { 0 }
                    ::= { digitalObjects 352 }

        -- 1.3.6.1.4.1.9839.2.1.1.353
        mal-high-temp-cb-inv-1 OBJECT-TYPE
                    SYNTAX Integer32 (0..1)
                    UNITS "N/A"
                    MAX-ACCESS read-only
                    STATUS current
                    DESCRIPTION "AL133 - High temperature CB alarm inverter 1"
                    DEFVAL { 0 }
                    ::= { digitalObjects 353 }

        -- 1.3.6.1.4.1.9839.2.1.1.354
        mal-thermal-switch-error-inv-1 OBJECT-TYPE
                    SYNTAX Integer32 (0..1)
                    UNITS "N/A"
                    MAX-ACCESS read-only
                    STATUS current
                    DESCRIPTION "AL134 - Thermal switch error inverter 1"
                    DEFVAL { 0 }
                    ::= { digitalObjects 354 }

        -- 1.3.6.1.4.1.9839.2.1.1.355
        mal-force-trip-inv-1 OBJECT-TYPE
                    SYNTAX Integer32 (0..1)
                    UNITS "N/A"
                    MAX-ACCESS read-only
                    STATUS current
                    DESCRIPTION "AL135 - Force trip inverter 1"
                    DEFVAL { 0 }
                    ::= { digitalObjects 355 }

        -- 1.3.6.1.4.1.9839.2.1.1.356
        mal-error-identification-motor-inv-1 OBJECT-TYPE
                    SYNTAX Integer32 (0..1)
                    UNITS "N/A"
                    MAX-ACCESS read-only
                    STATUS current
                    DESCRIPTION "AL136 - Error identification motor inverter 1"
                    DEFVAL { 0 }
                    ::= { digitalObjects 356 }

        -- 1.3.6.1.4.1.9839.2.1.1.357
        mal-error-high-speed-motor-inv-1 OBJECT-TYPE
                    SYNTAX Integer32 (0..1)
                    UNITS "N/A"
                    MAX-ACCESS read-only
                    STATUS current
                    DESCRIPTION "AL137 - Error high speed motor inverter 1"
                    DEFVAL { 0 }
                    ::= { digitalObjects 357 }

        -- 1.3.6.1.4.1.9839.2.1.1.358
        mal-earth-fault-inv-1 OBJECT-TYPE
                    SYNTAX Integer32 (0..1)
                    UNITS "N/A"
                    MAX-ACCESS read-only
                    STATUS current
                    DESCRIPTION "AL138 - Earth fault inverter 1"
                    DEFVAL { 0 }
                    ::= { digitalObjects 358 }

        -- 1.3.6.1.4.1.9839.2.1.1.359
        mal-short-circuit-inv-1 OBJECT-TYPE
                    SYNTAX Integer32 (0..1)
                    UNITS "N/A"
                    MAX-ACCESS read-only
                    STATUS current
                    DESCRIPTION "AL139 - Short circuit alarm inverter 1"
                    DEFVAL { 0 }
                    ::= { digitalObjects 359 }

        -- 1.3.6.1.4.1.9839.2.1.1.360
        mal-wiring-error-inv-1 OBJECT-TYPE
                    SYNTAX Integer32 (0..1)
                    UNITS "N/A"
                    MAX-ACCESS read-only
                    STATUS current
                    DESCRIPTION "AL140 - Wiring error inverter 1"
                    DEFVAL { 0 }
                    ::= { digitalObjects 360 }

        -- 1.3.6.1.4.1.9839.2.1.1.361
        mal-power-phase-loss-inv-1 OBJECT-TYPE
                    SYNTAX Integer32 (0..1)
                    UNITS "N/A"
                    MAX-ACCESS read-only
                    STATUS current
                    DESCRIPTION "AL141 - Power phase loss alarm inverter 1"
                    DEFVAL { 0 }
                    ::= { digitalObjects 361 }

        -- 1.3.6.1.4.1.9839.2.1.1.362
        mal-motor-phase-loss-inv-1 OBJECT-TYPE
                    SYNTAX Integer32 (0..1)
                    UNITS "N/A"
                    MAX-ACCESS read-only
                    STATUS current
                    DESCRIPTION "AL142 - Motor Phase Loss alarm inverter 1"
                    DEFVAL { 0 }
                    ::= { digitalObjects 362 }

        -- 1.3.6.1.4.1.9839.2.1.1.363
        mal-drive-internal-error-inv-1 OBJECT-TYPE
                    SYNTAX Integer32 (0..1)
                    UNITS "N/A"
                    MAX-ACCESS read-only
                    STATUS current
                    DESCRIPTION "AL143 - Drive internal error inverter 1"
                    DEFVAL { 0 }
                    ::= { digitalObjects 363 }

        -- 1.3.6.1.4.1.9839.2.1.1.364
        mal-comunication-error-inv-1 OBJECT-TYPE
                    SYNTAX Integer32 (0..1)
                    UNITS "N/A"
                    MAX-ACCESS read-only
                    STATUS current
                    DESCRIPTION "AL144 - Comunication error inverter 1"
                    DEFVAL { 0 }
                    ::= { digitalObjects 364 }

        -- 1.3.6.1.4.1.9839.2.1.1.365
        mal-motor-overload-inv-1 OBJECT-TYPE
                    SYNTAX Integer32 (0..1)
                    UNITS "N/A"
                    MAX-ACCESS read-only
                    STATUS current
                    DESCRIPTION "AL145 - Motor overload alarm inverter 1"
                    DEFVAL { 0 }
                    ::= { digitalObjects 365 }

        -- 1.3.6.1.4.1.9839.2.1.1.366
        mal-inverter-overload-inv-1 OBJECT-TYPE
                    SYNTAX Integer32 (0..1)
                    UNITS "N/A"
                    MAX-ACCESS read-only
                    STATUS current
                    DESCRIPTION "AL146 - Inverter overload alarm inverter 1"
                    DEFVAL { 0 }
                    ::= { digitalObjects 366 }

        -- 1.3.6.1.4.1.9839.2.1.1.367
        mal-overtorque-inv-1 OBJECT-TYPE
                    SYNTAX Integer32 (0..1)
                    UNITS "N/A"
                    MAX-ACCESS read-only
                    STATUS current
                    DESCRIPTION "AL147 - Overtorque alarm inverter 1"
                    DEFVAL { 0 }
                    ::= { digitalObjects 367 }

        -- 1.3.6.1.4.1.9839.2.1.1.368
        mal-excessive-speed-deviation-inv-1 OBJECT-TYPE
                    SYNTAX Integer32 (0..1)
                    UNITS "N/A"
                    MAX-ACCESS read-only
                    STATUS current
                    DESCRIPTION "AL148 - Excessive speed deviation alarm inverter 1"
                    DEFVAL { 0 }
                    ::= { digitalObjects 368 }

        -- 1.3.6.1.4.1.9839.2.1.1.369
        mal-no-pulses-received-inv-1 OBJECT-TYPE
                    SYNTAX Integer32 (0..1)
                    UNITS "N/A"
                    MAX-ACCESS read-only
                    STATUS current
                    DESCRIPTION "AL149 - No pulses received alarm inverter 1"
                    DEFVAL { 0 }
                    ::= { digitalObjects 369 }

        -- 1.3.6.1.4.1.9839.2.1.1.370
        mal-memory-error-inv-1 OBJECT-TYPE
                    SYNTAX Integer32 (0..1)
                    UNITS "N/A"
                    MAX-ACCESS read-only
                    STATUS current
                    DESCRIPTION "AL150 - Memory error inverter 1"
                    DEFVAL { 0 }
                    ::= { digitalObjects 370 }

        -- 1.3.6.1.4.1.9839.2.1.1.371
        mal-control-board-error-inv-1 OBJECT-TYPE
                    SYNTAX Integer32 (0..1)
                    UNITS "N/A"
                    MAX-ACCESS read-only
                    STATUS current
                    DESCRIPTION "AL151 - Control board error inverter 1"
                    DEFVAL { 0 }
                    ::= { digitalObjects 371 }

        -- 1.3.6.1.4.1.9839.2.1.1.372
        mal-output-current-imbalance-inv-1 OBJECT-TYPE
                    SYNTAX Integer32 (0..1)
                    UNITS "N/A"
                    MAX-ACCESS read-only
                    STATUS current
                    DESCRIPTION "AL152 - Output current imbalance inverter 1"
                    DEFVAL { 0 }
                    ::= { digitalObjects 372 }

        -- 1.3.6.1.4.1.9839.2.1.1.373
        mal-high-speed-to-restart-inv-1 OBJECT-TYPE
                    SYNTAX Integer32 (0..1)
                    UNITS "N/A"
                    MAX-ACCESS read-only
                    STATUS current
                    DESCRIPTION "AL153 - High speed to restart alarm inverter 1"
                    DEFVAL { 0 }
                    ::= { digitalObjects 373 }

        -- 1.3.6.1.4.1.9839.2.1.1.374
        mal-current-offset-fault-inv-1 OBJECT-TYPE
                    SYNTAX Integer32 (0..1)
                    UNITS "N/A"
                    MAX-ACCESS read-only
                    STATUS current
                    DESCRIPTION "AL154 - Current offset fault alarm inverter 1"
                    DEFVAL { 0 }
                    ::= { digitalObjects 374 }

        -- 1.3.6.1.4.1.9839.2.1.1.375
        mal-run-command-error-inv-1 OBJECT-TYPE
                    SYNTAX Integer32 (0..1)
                    UNITS "N/A"
                    MAX-ACCESS read-only
                    STATUS current
                    DESCRIPTION "AL155 - Run command error inverter 1"
                    DEFVAL { 0 }
                    ::= { digitalObjects 375 }

        -- 1.3.6.1.4.1.9839.2.1.1.376
        mal-fan-error-inv-1 OBJECT-TYPE
                    SYNTAX Integer32 (0..1)
                    UNITS "N/A"
                    MAX-ACCESS read-only
                    STATUS current
                    DESCRIPTION "AL156 - Fan error inverter 1"
                    DEFVAL { 0 }
                    ::= { digitalObjects 376 }

        -- 1.3.6.1.4.1.9839.2.1.1.377
        mal-driver-disable-inv-1 OBJECT-TYPE
                    SYNTAX Integer32 (0..1)
                    UNITS "N/A"
                    MAX-ACCESS read-only
                    STATUS current
                    DESCRIPTION "AL157 - Driver disable alarm inverter 1"
                    DEFVAL { 0 }
                    ::= { digitalObjects 377 }

        -- 1.3.6.1.4.1.9839.2.1.1.378
        mal-analog-reading-error-inv-1 OBJECT-TYPE
                    SYNTAX Integer32 (0..1)
                    UNITS "N/A"
                    MAX-ACCESS read-only
                    STATUS current
                    DESCRIPTION "AL158 - Analog reading error inverter 1"
                    DEFVAL { 0 }
                    ::= { digitalObjects 378 }

        -- 1.3.6.1.4.1.9839.2.1.1.379
        mal-pfc-error-inv-1 OBJECT-TYPE
                    SYNTAX Integer32 (0..1)
                    UNITS "N/A"
                    MAX-ACCESS read-only
                    STATUS current
                    DESCRIPTION "AL159 - PFC error inverter 1"
                    DEFVAL { 0 }
                    ::= { digitalObjects 379 }

        -- 1.3.6.1.4.1.9839.2.1.1.380
        mal-speed-control-error-inv-1 OBJECT-TYPE
                    SYNTAX Integer32 (0..1)
                    UNITS "N/A"
                    MAX-ACCESS read-only
                    STATUS current
                    DESCRIPTION "AL160 - Speed control error inverter 1"
                    DEFVAL { 0 }
                    ::= { digitalObjects 380 }

        -- 1.3.6.1.4.1.9839.2.1.1.381
        mal-overcurrent-accelleration-inv-1 OBJECT-TYPE
                    SYNTAX Integer32 (0..1)
                    UNITS "N/A"
                    MAX-ACCESS read-only
                    STATUS current
                    DESCRIPTION "AL161 - Overcurrent accelleration alarm inverter 1"
                    DEFVAL { 0 }
                    ::= { digitalObjects 381 }

        -- 1.3.6.1.4.1.9839.2.1.1.382
        mal-overcurrent-constant-speeed-inv-1 OBJECT-TYPE
                    SYNTAX Integer32 (0..1)
                    UNITS "N/A"
                    MAX-ACCESS read-only
                    STATUS current
                    DESCRIPTION "AL162 - Overcurrent constant speeed alarm inverter 1"
                    DEFVAL { 0 }
                    ::= { digitalObjects 382 }

        -- 1.3.6.1.4.1.9839.2.1.1.383
        mal-overcurrent-decelleration-inv-1 OBJECT-TYPE
                    SYNTAX Integer32 (0..1)
                    UNITS "N/A"
                    MAX-ACCESS read-only
                    STATUS current
                    DESCRIPTION "AL163 - Overcurrent decelleration alarm inverter 1"
                    DEFVAL { 0 }
                    ::= { digitalObjects 383 }

        -- 1.3.6.1.4.1.9839.2.1.1.384
        mal-current-greater-than-150-inv-1 OBJECT-TYPE
                    SYNTAX Integer32 (0..1)
                    UNITS "N/A"
                    MAX-ACCESS read-only
                    STATUS current
                    DESCRIPTION "AL164 - Current greater than 150 alarm inverter 1"
                    DEFVAL { 0 }
                    ::= { digitalObjects 384 }

        -- 1.3.6.1.4.1.9839.2.1.1.385
        mal-abnormal-condition-inv-1 OBJECT-TYPE
                    SYNTAX Integer32 (0..1)
                    UNITS "N/A"
                    MAX-ACCESS read-only
                    STATUS current
                    DESCRIPTION "AL165 - Abnormal condition alarm inverter 1"
                    DEFVAL { 0 }
                    ::= { digitalObjects 385 }

        -- 1.3.6.1.4.1.9839.2.1.1.386
        mal-driver-high-temperature-inv-1 OBJECT-TYPE
                    SYNTAX Integer32 (0..1)
                    UNITS "N/A"
                    MAX-ACCESS read-only
                    STATUS current
                    DESCRIPTION "AL166 - Driver high temperature alarm inverter 1"
                    DEFVAL { 0 }
                    ::= { digitalObjects 386 }

        -- 1.3.6.1.4.1.9839.2.1.1.387
        mal-driver-low-temperature-inv-1 OBJECT-TYPE
                    SYNTAX Integer32 (0..1)
                    UNITS "N/A"
                    MAX-ACCESS read-only
                    STATUS current
                    DESCRIPTION "AL167 - Driver low temperature alarm inverter 1"
                    DEFVAL { 0 }
                    ::= { digitalObjects 387 }

        -- 1.3.6.1.4.1.9839.2.1.1.388
        mal-high-current-hw-inv-1 OBJECT-TYPE
                    SYNTAX Integer32 (0..1)
                    UNITS "N/A"
                    MAX-ACCESS read-only
                    STATUS current
                    DESCRIPTION "AL168 - High current HW alarm inverter 1"
                    DEFVAL { 0 }
                    ::= { digitalObjects 388 }

        -- 1.3.6.1.4.1.9839.2.1.1.389
        mal-default-parameter-error-inv-1 OBJECT-TYPE
                    SYNTAX Integer32 (0..1)
                    UNITS "N/A"
                    MAX-ACCESS read-only
                    STATUS current
                    DESCRIPTION "AL169 - Default parameter error inverter 1"
                    DEFVAL { 0 }
                    ::= { digitalObjects 389 }

        -- 1.3.6.1.4.1.9839.2.1.1.390
        mal-ripple-dc-bus-error-inv-1 OBJECT-TYPE
                    SYNTAX Integer32 (0..1)
                    UNITS "N/A"
                    MAX-ACCESS read-only
                    STATUS current
                    DESCRIPTION "AL170 - Ripple DC BUS error inverter 1"
                    DEFVAL { 0 }
                    ::= { digitalObjects 390 }

        -- 1.3.6.1.4.1.9839.2.1.1.391
        mal-autotoning-error-inv-1 OBJECT-TYPE
                    SYNTAX Integer32 (0..1)
                    UNITS "N/A"
                    MAX-ACCESS read-only
                    STATUS current
                    DESCRIPTION "AL171 - Autotoning error inverter 1"
                    DEFVAL { 0 }
                    ::= { digitalObjects 391 }

        -- 1.3.6.1.4.1.9839.2.1.1.392
        mal-offline-inv-1 OBJECT-TYPE
                    SYNTAX Integer32 (0..1)
                    UNITS "N/A"
                    MAX-ACCESS read-only
                    STATUS current
                    DESCRIPTION "AL172 - Offline inverter 1"
                    DEFVAL { 0 }
                    ::= { digitalObjects 392 }

        -- 1.3.6.1.4.1.9839.2.1.1.393
        mal-write-parameter-error-inv-1 OBJECT-TYPE
                    SYNTAX Integer32 (0..1)
                    UNITS "N/A"
                    MAX-ACCESS read-only
                    STATUS current
                    DESCRIPTION "AL173 - Write parameter error inverter 1"
                    DEFVAL { 0 }
                    ::= { digitalObjects 393 }

        -- 1.3.6.1.4.1.9839.2.1.1.396
        mal-general-alarm-inv-2 OBJECT-TYPE
                    SYNTAX Integer32 (0..1)
                    UNITS "N/A"
                    MAX-ACCESS read-only
                    STATUS current
                    DESCRIPTION "AL176 - General alarm  inverter 2"
                    DEFVAL { 0 }
                    ::= { digitalObjects 396 }

        -- 1.3.6.1.4.1.9839.2.1.1.397
        mal-display-loss-inv-2 OBJECT-TYPE
                    SYNTAX Integer32 (0..1)
                    UNITS "N/A"
                    MAX-ACCESS read-only
                    STATUS current
                    DESCRIPTION "AL177 - Display loss alarm  inverter 2"
                    DEFVAL { 0 }
                    ::= { digitalObjects 397 }

        -- 1.3.6.1.4.1.9839.2.1.1.398
        mal-safe-torque-off-inv-2 OBJECT-TYPE
                    SYNTAX Integer32 (0..1)
                    UNITS "N/A"
                    MAX-ACCESS read-only
                    STATUS current
                    DESCRIPTION "AL178 - Safe torque Off alarm  inverter 2"
                    DEFVAL { 0 }
                    ::= { digitalObjects 398 }

        -- 1.3.6.1.4.1.9839.2.1.1.399
        mal-sto-1-loss-inv-2 OBJECT-TYPE
                    SYNTAX Integer32 (0..1)
                    UNITS "N/A"
                    MAX-ACCESS read-only
                    STATUS current
                    DESCRIPTION "AL179 - STO 1 loss alarm  inverter 2"
                    DEFVAL { 0 }
                    ::= { digitalObjects 399 }

        -- 1.3.6.1.4.1.9839.2.1.1.400
        mal-sto-2-loss-inv-2 OBJECT-TYPE
                    SYNTAX Integer32 (0..1)
                    UNITS "N/A"
                    MAX-ACCESS read-only
                    STATUS current
                    DESCRIPTION "AL180 - STO 2 loss alarm  inverter 2"
                    DEFVAL { 0 }
                    ::= { digitalObjects 400 }

        -- 1.3.6.1.4.1.9839.2.1.1.401
        mal-underload-inv-2 OBJECT-TYPE
                    SYNTAX Integer32 (0..1)
                    UNITS "N/A"
                    MAX-ACCESS read-only
                    STATUS current
                    DESCRIPTION "AL181 - Underload alarm  inverter 2"
                    DEFVAL { 0 }
                    ::= { digitalObjects 401 }

        -- 1.3.6.1.4.1.9839.2.1.1.402
        mal-stall-motor-inv-2 OBJECT-TYPE
                    SYNTAX Integer32 (0..1)
                    UNITS "N/A"
                    MAX-ACCESS read-only
                    STATUS current
                    DESCRIPTION "AL182 - Stall motor alarm  inverter 2"
                    DEFVAL { 0 }
                    ::= { digitalObjects 402 }

        -- 1.3.6.1.4.1.9839.2.1.1.403
        mal-encoder-error-inv-2 OBJECT-TYPE
                    SYNTAX Integer32 (0..1)
                    UNITS "N/A"
                    MAX-ACCESS read-only
                    STATUS current
                    DESCRIPTION "AL183 - Encoder error  inverter 2"
                    DEFVAL { 0 }
                    ::= { digitalObjects 403 }

        -- 1.3.6.1.4.1.9839.2.1.1.404
        mal-parameter-setting-error-inv-2 OBJECT-TYPE
                    SYNTAX Integer32 (0..1)
                    UNITS "N/A"
                    MAX-ACCESS read-only
                    STATUS current
                    DESCRIPTION "AL184 - Parameter setting error  inverter 2"
                    DEFVAL { 0 }
                    ::= { digitalObjects 404 }

        -- 1.3.6.1.4.1.9839.2.1.1.405
        mal-sw-incompatible-inv-2 OBJECT-TYPE
                    SYNTAX Integer32 (0..1)
                    UNITS "N/A"
                    MAX-ACCESS read-only
                    STATUS current
                    DESCRIPTION "AL185 - SW Incompatible alarm  inverter 2"
                    DEFVAL { 0 }
                    ::= { digitalObjects 405 }

        -- 1.3.6.1.4.1.9839.2.1.1.406
        mal-config-file-error-inv-2 OBJECT-TYPE
                    SYNTAX Integer32 (0..1)
                    UNITS "N/A"
                    MAX-ACCESS read-only
                    STATUS current
                    DESCRIPTION "AL186 - Configuration file error  inverter 2"
                    DEFVAL { 0 }
                    ::= { digitalObjects 406 }

        -- 1.3.6.1.4.1.9839.2.1.1.407
        mal-config-file-reading-error-inv-2 OBJECT-TYPE
                    SYNTAX Integer32 (0..1)
                    UNITS "N/A"
                    MAX-ACCESS read-only
                    STATUS current
                    DESCRIPTION "AL187 - Configuration file reading error  inverter 2"
                    DEFVAL { 0 }
                    ::= { digitalObjects 407 }

        -- 1.3.6.1.4.1.9839.2.1.1.408
        mal-overcurrent-motor-inv-2 OBJECT-TYPE
                    SYNTAX Integer32 (0..1)
                    UNITS "N/A"
                    MAX-ACCESS read-only
                    STATUS current
                    DESCRIPTION "AL188 - Overcurrent motor  inverter 2"
                    DEFVAL { 0 }
                    ::= { digitalObjects 408 }

        -- 1.3.6.1.4.1.9839.2.1.1.409
        mal-read-current-error-inv-2 OBJECT-TYPE
                    SYNTAX Integer32 (0..1)
                    UNITS "N/A"
                    MAX-ACCESS read-only
                    STATUS current
                    DESCRIPTION "AL189 - Read current error  inverter 2"
                    DEFVAL { 0 }
                    ::= { digitalObjects 409 }

        -- 1.3.6.1.4.1.9839.2.1.1.410
        mal-high-voltage-dc-bus-inv-2 OBJECT-TYPE
                    SYNTAX Integer32 (0..1)
                    UNITS "N/A"
                    MAX-ACCESS read-only
                    STATUS current
                    DESCRIPTION "AL190 - High voltage DC BUS alarm  inverter 2"
                    DEFVAL { 0 }
                    ::= { digitalObjects 410 }

        -- 1.3.6.1.4.1.9839.2.1.1.411
        mal-low-voltage-dc-bus-inv-2 OBJECT-TYPE
                    SYNTAX Integer32 (0..1)
                    UNITS "N/A"
                    MAX-ACCESS read-only
                    STATUS current
                    DESCRIPTION "AL191 - Low voltage DC BUS alarm  inverter 2"
                    DEFVAL { 0 }
                    ::= { digitalObjects 411 }

        -- 1.3.6.1.4.1.9839.2.1.1.412
        mal-high-temp-igbt-inv-2 OBJECT-TYPE
                    SYNTAX Integer32 (0..1)
                    UNITS "N/A"
                    MAX-ACCESS read-only
                    STATUS current
                    DESCRIPTION "AL192 - High temperature IGBT alarm  inverter 2"
                    DEFVAL { 0 }
                    ::= { digitalObjects 412 }

        -- 1.3.6.1.4.1.9839.2.1.1.413
        mal-high-temp-cb-inv-2 OBJECT-TYPE
                    SYNTAX Integer32 (0..1)
                    UNITS "N/A"
                    MAX-ACCESS read-only
                    STATUS current
                    DESCRIPTION "AL193 - High temperature CB alarm  inverter 2"
                    DEFVAL { 0 }
                    ::= { digitalObjects 413 }

        -- 1.3.6.1.4.1.9839.2.1.1.414
        mal-thermal-switch-error-inv-2 OBJECT-TYPE
                    SYNTAX Integer32 (0..1)
                    UNITS "N/A"
                    MAX-ACCESS read-only
                    STATUS current
                    DESCRIPTION "AL194 - Thermal switch error  inverter 2"
                    DEFVAL { 0 }
                    ::= { digitalObjects 414 }

        -- 1.3.6.1.4.1.9839.2.1.1.415
        mal-force-trip-inv-2 OBJECT-TYPE
                    SYNTAX Integer32 (0..1)
                    UNITS "N/A"
                    MAX-ACCESS read-only
                    STATUS current
                    DESCRIPTION "AL195 - Force trip  inverter 2"
                    DEFVAL { 0 }
                    ::= { digitalObjects 415 }

        -- 1.3.6.1.4.1.9839.2.1.1.416
        mal-error-identification-motor-inv-2 OBJECT-TYPE
                    SYNTAX Integer32 (0..1)
                    UNITS "N/A"
                    MAX-ACCESS read-only
                    STATUS current
                    DESCRIPTION "AL196 - Error identification motor  inverter 2"
                    DEFVAL { 0 }
                    ::= { digitalObjects 416 }

        -- 1.3.6.1.4.1.9839.2.1.1.417
        mal-error-high-speed-motor-inv-2 OBJECT-TYPE
                    SYNTAX Integer32 (0..1)
                    UNITS "N/A"
                    MAX-ACCESS read-only
                    STATUS current
                    DESCRIPTION "AL197 - Error high speed motor  inverter 2"
                    DEFVAL { 0 }
                    ::= { digitalObjects 417 }

        -- 1.3.6.1.4.1.9839.2.1.1.418
        mal-earth-fault-inv-2 OBJECT-TYPE
                    SYNTAX Integer32 (0..1)
                    UNITS "N/A"
                    MAX-ACCESS read-only
                    STATUS current
                    DESCRIPTION "AL198 - Earth fault  inverter 2"
                    DEFVAL { 0 }
                    ::= { digitalObjects 418 }

        -- 1.3.6.1.4.1.9839.2.1.1.419
        mal-short-circuit-inv-2 OBJECT-TYPE
                    SYNTAX Integer32 (0..1)
                    UNITS "N/A"
                    MAX-ACCESS read-only
                    STATUS current
                    DESCRIPTION "AL199 - Short circuit alarm  inverter 2"
                    DEFVAL { 0 }
                    ::= { digitalObjects 419 }

        -- 1.3.6.1.4.1.9839.2.1.1.420
        mal-wiring-error-inv-2 OBJECT-TYPE
                    SYNTAX Integer32 (0..1)
                    UNITS "N/A"
                    MAX-ACCESS read-only
                    STATUS current
                    DESCRIPTION "AL200 - Wiring error  inverter 2"
                    DEFVAL { 0 }
                    ::= { digitalObjects 420 }

        -- 1.3.6.1.4.1.9839.2.1.1.421
        mal-power-phase-loss-inv-2 OBJECT-TYPE
                    SYNTAX Integer32 (0..1)
                    UNITS "N/A"
                    MAX-ACCESS read-only
                    STATUS current
                    DESCRIPTION "AL201 - Power phase loss alarm  inverter 2"
                    DEFVAL { 0 }
                    ::= { digitalObjects 421 }

        -- 1.3.6.1.4.1.9839.2.1.1.422
        mal-motor-phase-loss-inv-2 OBJECT-TYPE
                    SYNTAX Integer32 (0..1)
                    UNITS "N/A"
                    MAX-ACCESS read-only
                    STATUS current
                    DESCRIPTION "AL202 - Motor Phase Loss alarm  inverter 2"
                    DEFVAL { 0 }
                    ::= { digitalObjects 422 }

        -- 1.3.6.1.4.1.9839.2.1.1.423
        mal-drive-internal-error-inv-2 OBJECT-TYPE
                    SYNTAX Integer32 (0..1)
                    UNITS "N/A"
                    MAX-ACCESS read-only
                    STATUS current
                    DESCRIPTION "AL203 - Drive internal error  inverter 2"
                    DEFVAL { 0 }
                    ::= { digitalObjects 423 }

        -- 1.3.6.1.4.1.9839.2.1.1.424
        mal-comunication-error-inv-2 OBJECT-TYPE
                    SYNTAX Integer32 (0..1)
                    UNITS "N/A"
                    MAX-ACCESS read-only
                    STATUS current
                    DESCRIPTION "AL204 - Comunication error  inverter 2"
                    DEFVAL { 0 }
                    ::= { digitalObjects 424 }

        -- 1.3.6.1.4.1.9839.2.1.1.425
        mal-motor-overload-inv-2 OBJECT-TYPE
                    SYNTAX Integer32 (0..1)
                    UNITS "N/A"
                    MAX-ACCESS read-only
                    STATUS current
                    DESCRIPTION "AL205 - Motor overload alarm  inverter 2"
                    DEFVAL { 0 }
                    ::= { digitalObjects 425 }

        -- 1.3.6.1.4.1.9839.2.1.1.426
        mal-inverter-overload-inv-2 OBJECT-TYPE
                    SYNTAX Integer32 (0..1)
                    UNITS "N/A"
                    MAX-ACCESS read-only
                    STATUS current
                    DESCRIPTION "AL206 - Inverter overload alarm  inverter 2"
                    DEFVAL { 0 }
                    ::= { digitalObjects 426 }

        -- 1.3.6.1.4.1.9839.2.1.1.427
        mal-overtorque-inv-2 OBJECT-TYPE
                    SYNTAX Integer32 (0..1)
                    UNITS "N/A"
                    MAX-ACCESS read-only
                    STATUS current
                    DESCRIPTION "AL207 - Overtorque alarm  inverter 2"
                    DEFVAL { 0 }
                    ::= { digitalObjects 427 }

        -- 1.3.6.1.4.1.9839.2.1.1.428
        mal-excessive-speed-deviation-inv-2 OBJECT-TYPE
                    SYNTAX Integer32 (0..1)
                    UNITS "N/A"
                    MAX-ACCESS read-only
                    STATUS current
                    DESCRIPTION "AL208 - Excessive speed deviation alarm  inverter 2"
                    DEFVAL { 0 }
                    ::= { digitalObjects 428 }

        -- 1.3.6.1.4.1.9839.2.1.1.429
        mal-no-pulses-received-inv-2 OBJECT-TYPE
                    SYNTAX Integer32 (0..1)
                    UNITS "N/A"
                    MAX-ACCESS read-only
                    STATUS current
                    DESCRIPTION "AL209 - No pulses received alarm  inverter 2"
                    DEFVAL { 0 }
                    ::= { digitalObjects 429 }

        -- 1.3.6.1.4.1.9839.2.1.1.430
        mal-memory-error-inv-2 OBJECT-TYPE
                    SYNTAX Integer32 (0..1)
                    UNITS "N/A"
                    MAX-ACCESS read-only
                    STATUS current
                    DESCRIPTION "AL210 - Memory error  inverter 2"
                    DEFVAL { 0 }
                    ::= { digitalObjects 430 }

        -- 1.3.6.1.4.1.9839.2.1.1.431
        mal-control-board-error-inv-2 OBJECT-TYPE
                    SYNTAX Integer32 (0..1)
                    UNITS "N/A"
                    MAX-ACCESS read-only
                    STATUS current
                    DESCRIPTION "AL211 - Control board error  inverter 2"
                    DEFVAL { 0 }
                    ::= { digitalObjects 431 }

        -- 1.3.6.1.4.1.9839.2.1.1.432
        mal-output-current-imbalance-inv-2 OBJECT-TYPE
                    SYNTAX Integer32 (0..1)
                    UNITS "N/A"
                    MAX-ACCESS read-only
                    STATUS current
                    DESCRIPTION "AL212 - Output current imbalance  inverter 2"
                    DEFVAL { 0 }
                    ::= { digitalObjects 432 }

        -- 1.3.6.1.4.1.9839.2.1.1.433
        mal-high-speed-to-restart-inv-2 OBJECT-TYPE
                    SYNTAX Integer32 (0..1)
                    UNITS "N/A"
                    MAX-ACCESS read-only
                    STATUS current
                    DESCRIPTION "AL213 - High speed to restart alarm  inverter 2"
                    DEFVAL { 0 }
                    ::= { digitalObjects 433 }

        -- 1.3.6.1.4.1.9839.2.1.1.434
        mal-current-offset-fault-inv-2 OBJECT-TYPE
                    SYNTAX Integer32 (0..1)
                    UNITS "N/A"
                    MAX-ACCESS read-only
                    STATUS current
                    DESCRIPTION "AL214 - Current offset fault alarm  inverter 2"
                    DEFVAL { 0 }
                    ::= { digitalObjects 434 }

        -- 1.3.6.1.4.1.9839.2.1.1.435
        mal-run-command-error-inv-2 OBJECT-TYPE
                    SYNTAX Integer32 (0..1)
                    UNITS "N/A"
                    MAX-ACCESS read-only
                    STATUS current
                    DESCRIPTION "AL215 - Run command error  inverter 2"
                    DEFVAL { 0 }
                    ::= { digitalObjects 435 }

        -- 1.3.6.1.4.1.9839.2.1.1.436
        mal-fan-error-inv-2 OBJECT-TYPE
                    SYNTAX Integer32 (0..1)
                    UNITS "N/A"
                    MAX-ACCESS read-only
                    STATUS current
                    DESCRIPTION "AL216 - Fan error  inverter 2"
                    DEFVAL { 0 }
                    ::= { digitalObjects 436 }

        -- 1.3.6.1.4.1.9839.2.1.1.437
        mal-driver-disable-inv-2 OBJECT-TYPE
                    SYNTAX Integer32 (0..1)
                    UNITS "N/A"
                    MAX-ACCESS read-only
                    STATUS current
                    DESCRIPTION "AL217 - Driver disable alarm  inverter 2"
                    DEFVAL { 0 }
                    ::= { digitalObjects 437 }

        -- 1.3.6.1.4.1.9839.2.1.1.438
        mal-analog-reading-error-inv-2 OBJECT-TYPE
                    SYNTAX Integer32 (0..1)
                    UNITS "N/A"
                    MAX-ACCESS read-only
                    STATUS current
                    DESCRIPTION "AL218 - Analog reading error  inverter 2"
                    DEFVAL { 0 }
                    ::= { digitalObjects 438 }

        -- 1.3.6.1.4.1.9839.2.1.1.439
        mal-pfc-error-inv-2 OBJECT-TYPE
                    SYNTAX Integer32 (0..1)
                    UNITS "N/A"
                    MAX-ACCESS read-only
                    STATUS current
                    DESCRIPTION "AL219 - PFC error  inverter 2"
                    DEFVAL { 0 }
                    ::= { digitalObjects 439 }

        -- 1.3.6.1.4.1.9839.2.1.1.440
        mal-speed-control-error-inv-2 OBJECT-TYPE
                    SYNTAX Integer32 (0..1)
                    UNITS "N/A"
                    MAX-ACCESS read-only
                    STATUS current
                    DESCRIPTION "AL220 - Speed control error  inverter 2"
                    DEFVAL { 0 }
                    ::= { digitalObjects 440 }

        -- 1.3.6.1.4.1.9839.2.1.1.441
        mal-overcurrent-accelleration-inv-2 OBJECT-TYPE
                    SYNTAX Integer32 (0..1)
                    UNITS "N/A"
                    MAX-ACCESS read-only
                    STATUS current
                    DESCRIPTION "AL221 - Overcurrent accelleration alarm  inverter 2"
                    DEFVAL { 0 }
                    ::= { digitalObjects 441 }

        -- 1.3.6.1.4.1.9839.2.1.1.442
        mal-overcurrent-constant-speeed-inv-2 OBJECT-TYPE
                    SYNTAX Integer32 (0..1)
                    UNITS "N/A"
                    MAX-ACCESS read-only
                    STATUS current
                    DESCRIPTION "AL222 - Overcurrent constant speeed alarm  inverter 2"
                    DEFVAL { 0 }
                    ::= { digitalObjects 442 }

        -- 1.3.6.1.4.1.9839.2.1.1.443
        mal-overcurrent-decelleration-inv-2 OBJECT-TYPE
                    SYNTAX Integer32 (0..1)
                    UNITS "N/A"
                    MAX-ACCESS read-only
                    STATUS current
                    DESCRIPTION "AL223 - Overcurrent decelleration alarm  inverter 2"
                    DEFVAL { 0 }
                    ::= { digitalObjects 443 }

        -- 1.3.6.1.4.1.9839.2.1.1.444
        mal-current-greater-than-150-inv-2 OBJECT-TYPE
                    SYNTAX Integer32 (0..1)
                    UNITS "N/A"
                    MAX-ACCESS read-only
                    STATUS current
                    DESCRIPTION "AL224 - Current greater than 150 alarm  inverter 2"
                    DEFVAL { 0 }
                    ::= { digitalObjects 444 }

        -- 1.3.6.1.4.1.9839.2.1.1.445
        mal-abnormal-condition-inv-2 OBJECT-TYPE
                    SYNTAX Integer32 (0..1)
                    UNITS "N/A"
                    MAX-ACCESS read-only
                    STATUS current
                    DESCRIPTION "AL225 - Abnormal condition alarm  inverter 2"
                    DEFVAL { 0 }
                    ::= { digitalObjects 445 }

        -- 1.3.6.1.4.1.9839.2.1.1.446
        mal-driver-high-temperature-inv-2 OBJECT-TYPE
                    SYNTAX Integer32 (0..1)
                    UNITS "N/A"
                    MAX-ACCESS read-only
                    STATUS current
                    DESCRIPTION "AL226 - Driver high temperature alarm  inverter 2"
                    DEFVAL { 0 }
                    ::= { digitalObjects 446 }

        -- 1.3.6.1.4.1.9839.2.1.1.447
        mal-driver-low-temperature-inv-2 OBJECT-TYPE
                    SYNTAX Integer32 (0..1)
                    UNITS "N/A"
                    MAX-ACCESS read-only
                    STATUS current
                    DESCRIPTION "AL227 - Driver low temperature alarm  inverter 2"
                    DEFVAL { 0 }
                    ::= { digitalObjects 447 }

        -- 1.3.6.1.4.1.9839.2.1.1.448
        mal-high-current-hw-inv-2 OBJECT-TYPE
                    SYNTAX Integer32 (0..1)
                    UNITS "N/A"
                    MAX-ACCESS read-only
                    STATUS current
                    DESCRIPTION "AL228 - High current HW alarm  inverter 2"
                    DEFVAL { 0 }
                    ::= { digitalObjects 448 }

        -- 1.3.6.1.4.1.9839.2.1.1.449
        mal-default-parameter-error-inv-2 OBJECT-TYPE
                    SYNTAX Integer32 (0..1)
                    UNITS "N/A"
                    MAX-ACCESS read-only
                    STATUS current
                    DESCRIPTION "AL229 - Default parameter error  inverter 2"
                    DEFVAL { 0 }
                    ::= { digitalObjects 449 }

        -- 1.3.6.1.4.1.9839.2.1.1.450
        mal-ripple-dc-bus-error-inv-2 OBJECT-TYPE
                    SYNTAX Integer32 (0..1)
                    UNITS "N/A"
                    MAX-ACCESS read-only
                    STATUS current
                    DESCRIPTION "AL230 - Ripple DC BUS error  inverter 2"
                    DEFVAL { 0 }
                    ::= { digitalObjects 450 }

        -- 1.3.6.1.4.1.9839.2.1.1.451
        mal-autotoning-error-inv-2 OBJECT-TYPE
                    SYNTAX Integer32 (0..1)
                    UNITS "N/A"
                    MAX-ACCESS read-only
                    STATUS current
                    DESCRIPTION "AL231 - Autotoning error  inverter 2"
                    DEFVAL { 0 }
                    ::= { digitalObjects 451 }

        -- 1.3.6.1.4.1.9839.2.1.1.452
        mal-offline-inv-2 OBJECT-TYPE
                    SYNTAX Integer32 (0..1)
                    UNITS "N/A"
                    MAX-ACCESS read-only
                    STATUS current
                    DESCRIPTION "AL232 - Offline  inverter 2"
                    DEFVAL { 0 }
                    ::= { digitalObjects 452 }

        -- 1.3.6.1.4.1.9839.2.1.1.453
        mal-write-parameter-error-inv-2 OBJECT-TYPE
                    SYNTAX Integer32 (0..1)
                    UNITS "N/A"
                    MAX-ACCESS read-only
                    STATUS current
                    DESCRIPTION "AL233 - Write parameter error  inverter 2"
                    DEFVAL { 0 }
                    ::= { digitalObjects 453 }

        -- 1.3.6.1.4.1.9839.2.1.1.456
        mal-cpy-internal-memory OBJECT-TYPE
                    SYNTAX Integer32 (0..1)
                    UNITS "N/A"
                    MAX-ACCESS read-only
                    STATUS current
                    DESCRIPTION "AL233 - CPY internal memory error"
                    DEFVAL { 0 }
                    ::= { digitalObjects 456 }

        -- 1.3.6.1.4.1.9839.2.1.1.457
        mal-cpy-config-parameter OBJECT-TYPE
                    SYNTAX Integer32 (0..1)
                    UNITS "N/A"
                    MAX-ACCESS read-only
                    STATUS current
                    DESCRIPTION "AL237 - CPY configuration parameter error"
                    DEFVAL { 0 }
                    ::= { digitalObjects 457 }

        -- 1.3.6.1.4.1.9839.2.1.1.458
        mal-cpy-memory-backup OBJECT-TYPE
                    SYNTAX Integer32 (0..1)
                    UNITS "N/A"
                    MAX-ACCESS read-only
                    STATUS current
                    DESCRIPTION "AL238 - CPY memory backup error"
                    DEFVAL { 0 }
                    ::= { digitalObjects 458 }

        -- 1.3.6.1.4.1.9839.2.1.1.459
        mal-cpy-comunication OBJECT-TYPE
                    SYNTAX Integer32 (0..1)
                    UNITS "N/A"
                    MAX-ACCESS read-only
                    STATUS current
                    DESCRIPTION "AL239 - CPY comunication error"
                    DEFVAL { 0 }
                    ::= { digitalObjects 459 }

        -- 1.3.6.1.4.1.9839.2.1.1.460
        mal-cpy-high-current OBJECT-TYPE
                    SYNTAX Integer32 (0..1)
                    UNITS "N/A"
                    MAX-ACCESS read-only
                    STATUS current
                    DESCRIPTION "AL240 - CPY high current alarm"
                    DEFVAL { 0 }
                    ::= { digitalObjects 460 }

        -- 1.3.6.1.4.1.9839.2.1.1.461
        mal-cpy-low-production OBJECT-TYPE
                    SYNTAX Integer32 (0..1)
                    UNITS "N/A"
                    MAX-ACCESS read-only
                    STATUS current
                    DESCRIPTION "AL241 - CPY low production alarm"
                    DEFVAL { 0 }
                    ::= { digitalObjects 461 }

        -- 1.3.6.1.4.1.9839.2.1.1.462
        mal-cpy-high-conductivity OBJECT-TYPE
                    SYNTAX Integer32 (0..1)
                    UNITS "N/A"
                    MAX-ACCESS read-only
                    STATUS current
                    DESCRIPTION "AL242 - CPY high conductivity alarm"
                    DEFVAL { 0 }
                    ::= { digitalObjects 462 }

        -- 1.3.6.1.4.1.9839.2.1.1.463
        mal-cpy-high-water-level OBJECT-TYPE
                    SYNTAX Integer32 (0..1)
                    UNITS "N/A"
                    MAX-ACCESS read-only
                    STATUS current
                    DESCRIPTION "AL243 - CPY high water level alarm"
                    DEFVAL { 0 }
                    ::= { digitalObjects 463 }

        -- 1.3.6.1.4.1.9839.2.1.1.464
        mal-cpy-lack-of-water OBJECT-TYPE
                    SYNTAX Integer32 (0..1)
                    UNITS "N/A"
                    MAX-ACCESS read-only
                    STATUS current
                    DESCRIPTION "AL244 - CPY lack of water alarm"
                    DEFVAL { 0 }
                    ::= { digitalObjects 464 }

        -- 1.3.6.1.4.1.9839.2.1.1.465
        mal-cpy-drain-valve-problem OBJECT-TYPE
                    SYNTAX Integer32 (0..1)
                    UNITS "N/A"
                    MAX-ACCESS read-only
                    STATUS current
                    DESCRIPTION "AL245 - CPY drain valve problem alarm"
                    DEFVAL { 0 }
                    ::= { digitalObjects 465 }

        -- 1.3.6.1.4.1.9839.2.1.1.466
        mal-cpy-cylinder-depleted OBJECT-TYPE
                    SYNTAX Integer32 (0..1)
                    UNITS "N/A"
                    MAX-ACCESS read-only
                    STATUS current
                    DESCRIPTION "AL246 - CPY cylinder depleted alarm"
                    DEFVAL { 0 }
                    ::= { digitalObjects 466 }

        -- 1.3.6.1.4.1.9839.2.1.1.467
        mal-cpy-cylinder-dirty OBJECT-TYPE
                    SYNTAX Integer32 (0..1)
                    UNITS "N/A"
                    MAX-ACCESS read-only
                    STATUS current
                    DESCRIPTION "AL247 - CPY cylinder dirty alarm"
                    DEFVAL { 0 }
                    ::= { digitalObjects 467 }

        -- 1.3.6.1.4.1.9839.2.1.1.468
        mal-cpy-cylinder-foam OBJECT-TYPE
                    SYNTAX Integer32 (0..1)
                    UNITS "N/A"
                    MAX-ACCESS read-only
                    STATUS current
                    DESCRIPTION "AL248 - CPY cylinder foam alarm"
                    DEFVAL { 0 }
                    ::= { digitalObjects 468 }

        -- 1.3.6.1.4.1.9839.2.1.1.469
        mal-cpy-offline OBJECT-TYPE
                    SYNTAX Integer32 (0..1)
                    UNITS "N/A"
                    MAX-ACCESS read-only
                    STATUS current
                    DESCRIPTION "AL249 - CPY offline alarm"
                    DEFVAL { 0 }
                    ::= { digitalObjects 469 }

        -- 1.3.6.1.4.1.9839.2.1.1.470
        mal-hgp-c1-probe OBJECT-TYPE
                    SYNTAX Integer32 (0..1)
                    UNITS "N/A"
                    MAX-ACCESS read-only
                    STATUS current
                    DESCRIPTION "AL250 - Hot gas pressure circuit 1 probe alarm"
                    DEFVAL { 0 }
                    ::= { digitalObjects 470 }

        -- 1.3.6.1.4.1.9839.2.1.1.471
        mal-hgp-c2-probe OBJECT-TYPE
                    SYNTAX Integer32 (0..1)
                    UNITS "N/A"
                    MAX-ACCESS read-only
                    STATUS current
                    DESCRIPTION "AL251 - Hot gas pressure circuit 2 probe alarm"
                    DEFVAL { 0 }
                    ::= { digitalObjects 471 }

        -- 1.3.6.1.4.1.9839.2.1.1.472
        mal-variation-t-setpoint-1 OBJECT-TYPE
                    SYNTAX Integer32 (0..1)
                    UNITS "N/A"
                    MAX-ACCESS read-only
                    STATUS current
                    DESCRIPTION "AL252 - Alarm variation general/cooling setpoint by analog input"
                    DEFVAL { 0 }
                    ::= { digitalObjects 472 }

        -- 1.3.6.1.4.1.9839.2.1.1.473
        mal-variation-t-setpoint-2 OBJECT-TYPE
                    SYNTAX Integer32 (0..1)
                    UNITS "N/A"
                    MAX-ACCESS read-only
                    STATUS current
                    DESCRIPTION "AL253 - Alarm variation heating setpoint by analog input"
                    DEFVAL { 0 }
                    ::= { digitalObjects 473 }

        -- 1.3.6.1.4.1.9839.2.1.1.474
        mal-variation-h-setpoint OBJECT-TYPE
                    SYNTAX Integer32 (0..1)
                    UNITS "N/A"
                    MAX-ACCESS read-only
                    STATUS current
                    DESCRIPTION "AL254 - Alarm variation humidity setpoint by analog input"
                    DEFVAL { 0 }
                    ::= { digitalObjects 474 }

        -- 1.3.6.1.4.1.9839.2.1.1.475
        mal-low-cooling-dt OBJECT-TYPE
                    SYNTAX Integer32 (0..1)
                    UNITS "N/A"
                    MAX-ACCESS read-only
                    STATUS current
                    DESCRIPTION "AL255 - Low cooling dT alarm"
                    DEFVAL { 0 }
                    ::= { digitalObjects 475 }

        -- 1.3.6.1.4.1.9839.2.1.1.476
        mal-low-heating-dt OBJECT-TYPE
                    SYNTAX Integer32 (0..1)
                    UNITS "N/A"
                    MAX-ACCESS read-only
                    STATUS current
                    DESCRIPTION "AL256 - Low Heating dT alarm"
                    DEFVAL { 0 }
                    ::= { digitalObjects 476 }

        -- 1.3.6.1.4.1.9839.2.1.1.477
        al-bios-not-compatible OBJECT-TYPE
                    SYNTAX Integer32 (0..1)
                    UNITS "N/A"
                    MAX-ACCESS read-only
                    STATUS current
                    DESCRIPTION "BIOS not compatible"
                    DEFVAL { 0 }
                    ::= { digitalObjects 477 }

        -- 1.3.6.1.4.1.9839.2.1.1.478
        mal-offline-eev-3 OBJECT-TYPE
                    SYNTAX Integer32 (0..1)
                    UNITS "N/A"
                    MAX-ACCESS read-only
                    STATUS current
                    DESCRIPTION "AL258 - EEV 3 offline alarm"
                    DEFVAL { 0 }
                    ::= { digitalObjects 478 }

        -- 1.3.6.1.4.1.9839.2.1.1.479
        mal-lan-error-eev-3 OBJECT-TYPE
                    SYNTAX Integer32 (0..1)
                    UNITS "N/A"
                    MAX-ACCESS read-only
                    STATUS current
                    DESCRIPTION "AL259 - EEV 3 Lan error"
                    DEFVAL { 0 }
                    ::= { digitalObjects 479 }

        -- 1.3.6.1.4.1.9839.2.1.1.480
        mal-eprom-error-eev-3 OBJECT-TYPE
                    SYNTAX Integer32 (0..1)
                    UNITS "N/A"
                    MAX-ACCESS read-only
                    STATUS current
                    DESCRIPTION "AL260 - EEV 3 Eprom error"
                    DEFVAL { 0 }
                    ::= { digitalObjects 480 }

        -- 1.3.6.1.4.1.9839.2.1.1.481
        mal-step-motor-eev-3 OBJECT-TYPE
                    SYNTAX Integer32 (0..1)
                    UNITS "N/A"
                    MAX-ACCESS read-only
                    STATUS current
                    DESCRIPTION "AL261 - EEV 3 Step motor error"
                    DEFVAL { 0 }
                    ::= { digitalObjects 481 }

        -- 1.3.6.1.4.1.9839.2.1.1.482
        mal-fw-not-compatible-eev-3 OBJECT-TYPE
                    SYNTAX Integer32 (0..1)
                    UNITS "N/A"
                    MAX-ACCESS read-only
                    STATUS current
                    DESCRIPTION "AL262 - EEV 3 Firmware not compatible"
                    DEFVAL { 0 }
                    ::= { digitalObjects 482 }

        -- 1.3.6.1.4.1.9839.2.1.1.483
        mal-offline-eev-4 OBJECT-TYPE
                    SYNTAX Integer32 (0..1)
                    UNITS "N/A"
                    MAX-ACCESS read-only
                    STATUS current
                    DESCRIPTION "AL263 - EEV 4 offline alarm"
                    DEFVAL { 0 }
                    ::= { digitalObjects 483 }

        -- 1.3.6.1.4.1.9839.2.1.1.484
        mal-lan-error-eev-4 OBJECT-TYPE
                    SYNTAX Integer32 (0..1)
                    UNITS "N/A"
                    MAX-ACCESS read-only
                    STATUS current
                    DESCRIPTION "AL264 - EEV 4 Lan error"
                    DEFVAL { 0 }
                    ::= { digitalObjects 484 }

        -- 1.3.6.1.4.1.9839.2.1.1.485
        mal-eprom-error-eev-4 OBJECT-TYPE
                    SYNTAX Integer32 (0..1)
                    UNITS "N/A"
                    MAX-ACCESS read-only
                    STATUS current
                    DESCRIPTION "AL265 - EEV 4 Eprom error"
                    DEFVAL { 0 }
                    ::= { digitalObjects 485 }

        -- 1.3.6.1.4.1.9839.2.1.1.486
        mal-step-motor-eev-4 OBJECT-TYPE
                    SYNTAX Integer32 (0..1)
                    UNITS "N/A"
                    MAX-ACCESS read-only
                    STATUS current
                    DESCRIPTION "AL266 - EEV 4 Step motor error"
                    DEFVAL { 0 }
                    ::= { digitalObjects 486 }

        -- 1.3.6.1.4.1.9839.2.1.1.487
        mal-fw-not-compatible-eev-4 OBJECT-TYPE
                    SYNTAX Integer32 (0..1)
                    UNITS "N/A"
                    MAX-ACCESS read-only
                    STATUS current
                    DESCRIPTION "AL267 - EEV 4 Firmware not compatible"
                    DEFVAL { 0 }
                    ::= { digitalObjects 487 }

        -- 1.3.6.1.4.1.9839.2.1.1.488
        mal-high-room-temp-2 OBJECT-TYPE
                    SYNTAX Integer32 (0..1)
                    UNITS "N/A"
                    MAX-ACCESS read-only
                    STATUS current
                    DESCRIPTION "AL268 - High room temp. alarm 2"
                    DEFVAL { 0 }
                    ::= { digitalObjects 488 }

        -- 1.3.6.1.4.1.9839.2.1.1.489
        mAl-Dirty-Filter-Press-Sensor OBJECT-TYPE
                    SYNTAX Integer32 (0..1)
                    UNITS "N/A"
                    MAX-ACCESS read-only
                    STATUS current
                    DESCRIPTION "AL269 - Dirty filter pressure sensor alarm"
                    DEFVAL { 0 }
                    ::= { digitalObjects 489 }

        -- 1.3.6.1.4.1.9839.2.1.1.490
        mAl-User-Fan-Speed-1-Error OBJECT-TYPE
                    SYNTAX Integer32 (0..1)
                    UNITS "N/A"
                    MAX-ACCESS read-only
                    STATUS current
                    DESCRIPTION "AL270 - User fan 1 speed error"
                    DEFVAL { 0 }
                    ::= { digitalObjects 490 }

        -- 1.3.6.1.4.1.9839.2.1.1.491
        mAl-User-Fan-Speed-2-Error OBJECT-TYPE
                    SYNTAX Integer32 (0..1)
                    UNITS "N/A"
                    MAX-ACCESS read-only
                    STATUS current
                    DESCRIPTION "AL271 - User fan 2 speed error"
                    DEFVAL { 0 }
                    ::= { digitalObjects 491 }

        -- 1.3.6.1.4.1.9839.2.1.1.492
        mAl-Ext-FC-Fan-Speed-Error OBJECT-TYPE
                    SYNTAX Integer32 (0..1)
                    UNITS "N/A"
                    MAX-ACCESS read-only
                    STATUS current
                    DESCRIPTION "AL272 - Freecooling fan speed error"
                    DEFVAL { 0 }
                    ::= { digitalObjects 492 }

        -- 1.3.6.1.4.1.9839.2.1.1.493
        mAl-Cooling-Req-By-AIN OBJECT-TYPE
                    SYNTAX Integer32 (0..1)
                    UNITS "N/A"
                    MAX-ACCESS read-only
                    STATUS current
                    DESCRIPTION "AL273 - Alarm cooling request by AIN"
                    DEFVAL { 0 }
                    ::= { digitalObjects 493 }

        -- 1.3.6.1.4.1.9839.2.1.1.494
        mAl-heating-Req-By-AIN OBJECT-TYPE
                    SYNTAX Integer32 (0..1)
                    UNITS "N/A"
                    MAX-ACCESS read-only
                    STATUS current
                    DESCRIPTION "AL274 - Alarm heating request by AIN"
                    DEFVAL { 0 }
                    ::= { digitalObjects 494 }

        -- 1.3.6.1.4.1.9839.2.1.1.495
        mAl-Humid-Req-By-AIN OBJECT-TYPE
                    SYNTAX Integer32 (0..1)
                    UNITS "N/A"
                    MAX-ACCESS read-only
                    STATUS current
                    DESCRIPTION "AL275 - Alarm humidifierrequest by AIN"
                    DEFVAL { 0 }
                    ::= { digitalObjects 495 }

        -- 1.3.6.1.4.1.9839.2.1.1.496
        mAl-Dehumid-Req-By-AIN OBJECT-TYPE
                    SYNTAX Integer32 (0..1)
                    UNITS "N/A"
                    MAX-ACCESS read-only
                    STATUS current
                    DESCRIPTION "AL276 - Alarm dehumidifierrequest by AIN"
                    DEFVAL { 0 }
                    ::= { digitalObjects 496 }


        -- 1.3.6.1.4.1.9839.2.1.1.497
        mAl-Feedback-Valve-1 OBJECT-TYPE
                    SYNTAX Integer32 (0..1)
                    UNITS "N/A"
                    MAX-ACCESS read-only
                    STATUS current
                    DESCRIPTION "AL277 - Alarm feedback valve 1 position"
                    DEFVAL { 0 }
                    ::= { digitalObjects 497 }

        -- 1.3.6.1.4.1.9839.2.1.1.498
        mAl-Feedback-Valve-2 OBJECT-TYPE
                    SYNTAX Integer32 (0..1)
                    UNITS "N/A"
                    MAX-ACCESS read-only
                    STATUS current
                    DESCRIPTION "AL278 - Alarm feedback valve 2 position"
                    DEFVAL { 0 }
                    ::= { digitalObjects 498 }

        -- 1.3.6.1.4.1.9839.2.1.1.499
        mAl-Fan-1 OBJECT-TYPE
                    SYNTAX Integer32 (0..1)
                    UNITS "N/A"
                    MAX-ACCESS read-only
                    STATUS current
                    DESCRIPTION "AL279 - Alarm user fan 1"
                    DEFVAL { 0 }
                    ::= { digitalObjects 499 }

        -- 1.3.6.1.4.1.9839.2.1.1.500
        mAl-Fan-2 OBJECT-TYPE
                    SYNTAX Integer32 (0..1)
                    UNITS "N/A"
                    MAX-ACCESS read-only
                    STATUS current
                    DESCRIPTION "AL280 - Alarm user fan 2"
                    DEFVAL { 0 }
                    ::= { digitalObjects 500 }

        -- 1.3.6.1.4.1.9839.2.1.1.501
        mAl-Fan-3 OBJECT-TYPE
                    SYNTAX Integer32 (0..1)
                    UNITS "N/A"
                    MAX-ACCESS read-only
                    STATUS current
                    DESCRIPTION "AL281 - Alarm user fan 3"
                    DEFVAL { 0 }
                    ::= { digitalObjects 501 }

        -- 1.3.6.1.4.1.9839.2.1.1.502
        mAl-Fan-4 OBJECT-TYPE
                    SYNTAX Integer32 (0..1)
                    UNITS "N/A"
                    MAX-ACCESS read-only
                    STATUS current
                    DESCRIPTION "AL282 - Alarm user fan 4"
                    DEFVAL { 0 }
                    ::= { digitalObjects 502 }

        -- 1.3.6.1.4.1.9839.2.1.1.503
        mAl-Fan-5 OBJECT-TYPE
                    SYNTAX Integer32 (0..1)
                    UNITS "N/A"
                    MAX-ACCESS read-only
                    STATUS current
                    DESCRIPTION "AL283 - Alarm user fan 5"
                    DEFVAL { 0 }
                    ::= { digitalObjects 503 }

        -- 1.3.6.1.4.1.9839.2.1.1.504
        mAl-Fan-6 OBJECT-TYPE
                    SYNTAX Integer32 (0..1)
                    UNITS "N/A"
                    MAX-ACCESS read-only
                    STATUS current
                    DESCRIPTION "AL284 - Alarm user fan 6"
                    DEFVAL { 0 }
                    ::= { digitalObjects 504 }

        -- 1.3.6.1.4.1.9839.2.1.1.505
        mAl-Fan-7 OBJECT-TYPE
                    SYNTAX Integer32 (0..1)
                    UNITS "N/A"
                    MAX-ACCESS read-only
                    STATUS current
                    DESCRIPTION "AL285 - Alarm user fan 7"
                    DEFVAL { 0 }
                    ::= { digitalObjects 505 }

        -- 1.3.6.1.4.1.9839.2.1.1.506
        mAl-Fan-8 OBJECT-TYPE
                    SYNTAX Integer32 (0..1)
                    UNITS "N/A"
                    MAX-ACCESS read-only
                    STATUS current
                    DESCRIPTION "AL286 - Alarm user fan 8"
                    DEFVAL { 0 }
                    ::= { digitalObjects 506 }

        -- 1.3.6.1.4.1.9839.2.1.1.507
        mAl-Fan-9 OBJECT-TYPE
                    SYNTAX Integer32 (0..1)
                    UNITS "N/A"
                    MAX-ACCESS read-only
                    STATUS current
                    DESCRIPTION "AL287 - Alarm user fan 9"
                    DEFVAL { 0 }
                    ::= { digitalObjects 507 }

        -- 1.3.6.1.4.1.9839.2.1.1.508
        mAl-Fan-10 OBJECT-TYPE
                    SYNTAX Integer32 (0..1)
                    UNITS "N/A"
                    MAX-ACCESS read-only
                    STATUS current
                    DESCRIPTION "AL288 - Alarm user fan 10"
                    DEFVAL { 0 }
                    ::= { digitalObjects 508 }

        -- 1.3.6.1.4.1.9839.2.1.1.509
        mAl-Thermostat-Probe OBJECT-TYPE
                    SYNTAX Integer32 (0..1)
                    UNITS "N/A"
                    MAX-ACCESS read-only
                    STATUS current
                    DESCRIPTION "AL289 - Alarm thermostat probe"
                    DEFVAL { 0 }
                    ::= { digitalObjects 509 }

        -- 1.3.6.1.4.1.9839.2.1.1.510
        mAl-in-water-pressure-valve-1 OBJECT-TYPE
                    SYNTAX Integer32 (0..1)
                    UNITS "N/A"
                    MAX-ACCESS read-only
                    STATUS current
                    DESCRIPTION "AL290 - Inlet water pressure valve 1 probe fault"
                    DEFVAL { 0 }
                    ::= { digitalObjects 510 }

        -- 1.3.6.1.4.1.9839.2.1.1.511
        mAl-out-water-pressure-valve-1 OBJECT-TYPE
                    SYNTAX Integer32 (0..1)
                    UNITS "N/A"
                    MAX-ACCESS read-only
                    STATUS current
                    DESCRIPTION "AL291 - Outlet water pressure valve 1 probe fault"
                    DEFVAL { 0 }
                    ::= { digitalObjects 511 }

        -- 1.3.6.1.4.1.9839.2.1.1.512
        mAl-in-water-pressure-valve-2 OBJECT-TYPE
                    SYNTAX Integer32 (0..1)
                    UNITS "N/A"
                    MAX-ACCESS read-only
                    STATUS current
                    DESCRIPTION "AL292 - Inlet water pressure valve 2 probe fault"
                    DEFVAL { 0 }
                    ::= { digitalObjects 512 }

        -- 1.3.6.1.4.1.9839.2.1.1.513
        mAl-out-water-pressure-valve-2 OBJECT-TYPE
                    SYNTAX Integer32 (0..1)
                    UNITS "N/A"
                    MAX-ACCESS read-only
                    STATUS current
                    DESCRIPTION "AL293 - Outlet water pressure valve 2 probe fault"
                    DEFVAL { 0 }
                    ::= { digitalObjects 513 }
                    
        -- 1.3.6.1.4.1.9839.2.1.1.514
        mAl-seneca-s203ta OBJECT-TYPE
                    SYNTAX Integer32 (0..1)
                    UNITS "N/A"
                    MAX-ACCESS read-only
                    STATUS current
                    DESCRIPTION "AL294 - Seneca S203TA general alarm"
                    DEFVAL { 0 }
                    ::= { digitalObjects 514 }
                    
        -- 1.3.6.1.4.1.9839.2.1.1.515
        mAl-qeed-qi-50 OBJECT-TYPE
                    SYNTAX Integer32 (0..1)
                    UNITS "N/A"
                    MAX-ACCESS read-only
                    STATUS current
                    DESCRIPTION "AL295 - QEED QI 50 general alarm"
                    DEFVAL { 0 }
                    ::= { digitalObjects 515 }

        -- 1.3.6.1.4.1.9839.2.1.1.541
        alarm-cfg-1 OBJECT-TYPE
                    SYNTAX Integer32 (0..1)
                    UNITS "N/A"
                    MAX-ACCESS read-only
                    STATUS current
                    DESCRIPTION "Configurable alarm 1 status"
                    DEFVAL { 0 }
                    ::= { digitalObjects 541 }

        -- 1.3.6.1.4.1.9839.2.1.1.542
        alarm-cfg-2 OBJECT-TYPE
                    SYNTAX Integer32 (0..1)
                    UNITS "N/A"
                    MAX-ACCESS read-only
                    STATUS current
                    DESCRIPTION "Configurable alarm 2 status"
                    DEFVAL { 0 }
                    ::= { digitalObjects 542 }

        -- 1.3.6.1.4.1.9839.2.1.1.543
        alarm-cfg-3 OBJECT-TYPE
                    SYNTAX Integer32 (0..1)
                    UNITS "N/A"
                    MAX-ACCESS read-only
                    STATUS current
                    DESCRIPTION "Configurable alarm 3 status"
                    DEFVAL { 0 }
                    ::= { digitalObjects 543 }

        -- 1.3.6.1.4.1.9839.2.1.1.544
        alarm-cfg-4 OBJECT-TYPE
                    SYNTAX Integer32 (0..1)
                    UNITS "N/A"
                    MAX-ACCESS read-only
                    STATUS current
                    DESCRIPTION "Configurable alarm 4 status"
                    DEFVAL { 0 }
                    ::= { digitalObjects 544 }

        -- 1.3.6.1.4.1.9839.2.1.1.545
        alarm-cfg-5 OBJECT-TYPE
                    SYNTAX Integer32 (0..1)
                    UNITS "N/A"
                    MAX-ACCESS read-only
                    STATUS current
                    DESCRIPTION "Configurable alarm 5 status"
                    DEFVAL { 0 }
                    ::= { digitalObjects 545 }

        -- 1.3.6.1.4.1.9839.2.1.1.546
        alarm-cfg-6 OBJECT-TYPE
                    SYNTAX Integer32 (0..1)
                    UNITS "N/A"
                    MAX-ACCESS read-only
                    STATUS current
                    DESCRIPTION "Configurable alarm 6 status"
                    DEFVAL { 0 }
                    ::= { digitalObjects 546 }

        -- 1.3.6.1.4.1.9839.2.1.1.550
        general-alarm OBJECT-TYPE
                    SYNTAX Integer32 (0..1)
                    UNITS "N/A"
                    MAX-ACCESS read-only
                    STATUS current
                    DESCRIPTION "General alarm (0= Ok, 1= Alarm)"
                    DEFVAL { 0 }
                    ::= { digitalObjects 550 }

        -- 1.3.6.1.4.1.9839.2.1.1.551
        unit-ready OBJECT-TYPE
                    SYNTAX Integer32 (0..1)
                    UNITS "N/A"
                    MAX-ACCESS read-only
                    STATUS current
                    DESCRIPTION "Unit ready (0= Not ready, 1= Ready)"
                    DEFVAL { 0 }
                    ::= { digitalObjects 551 }

        -- 1.3.6.1.4.1.9839.2.1.1.552
        unit-on-off OBJECT-TYPE
                    SYNTAX Integer32 (0..1)
                    UNITS "N/A"
                    MAX-ACCESS read-only
                    STATUS current
                    DESCRIPTION "Unit On/Off status (0= Off, 1= On)"
                    DEFVAL { 0 }
                    ::= { digitalObjects 552 }

        -- 1.3.6.1.4.1.9839.2.1.1.553
        shutdown-alarm OBJECT-TYPE
                    SYNTAX Integer32 (0..1)
                    UNITS "N/A"
                    MAX-ACCESS read-only
                    STATUS current
                    DESCRIPTION "Unit off by alarm (0= Ok, 1= Alarm)"
                    DEFVAL { 0 }
                    ::= { digitalObjects 553 }

        -- 1.3.6.1.4.1.9839.2.1.1.554
        compressor-1-on-off OBJECT-TYPE
                    SYNTAX Integer32 (0..1)
                    UNITS "N/A"
                    MAX-ACCESS read-only
                    STATUS current
                    DESCRIPTION "Compressor 1 status (0= Off, 1= On)"
                    DEFVAL { 0 }
                    ::= { digitalObjects 554 }

        -- 1.3.6.1.4.1.9839.2.1.1.555
        compressor-2-on-off OBJECT-TYPE
                    SYNTAX Integer32 (0..1)
                    UNITS "N/A"
                    MAX-ACCESS read-only
                    STATUS current
                    DESCRIPTION "Compressor 2 status (0= Off, 1= On)"
                    DEFVAL { 0 }
                    ::= { digitalObjects 555 }

        -- 1.3.6.1.4.1.9839.2.1.1.556
        compressor-3-on-off OBJECT-TYPE
                    SYNTAX Integer32 (0..1)
                    UNITS "N/A"
                    MAX-ACCESS read-only
                    STATUS current
                    DESCRIPTION "Compressor 3 status (0= Off, 1= On)"
                    DEFVAL { 0 }
                    ::= { digitalObjects 556 }

        -- 1.3.6.1.4.1.9839.2.1.1.557
        compressor-4-on-off OBJECT-TYPE
                    SYNTAX Integer32 (0..1)
                    UNITS "N/A"
                    MAX-ACCESS read-only
                    STATUS current
                    DESCRIPTION "Compressor 4 status (0= Off, 1= On)"
                    DEFVAL { 0 }
                    ::= { digitalObjects 557 }

        -- 1.3.6.1.4.1.9839.2.1.1.558
        compressor-5-on-off OBJECT-TYPE
                    SYNTAX Integer32 (0..1)
                    UNITS "N/A"
                    MAX-ACCESS read-only
                    STATUS current
                    DESCRIPTION "Compressor 5 status (0= Off, 1= On)"
                    DEFVAL { 0 }
                    ::= { digitalObjects 558 }

        -- 1.3.6.1.4.1.9839.2.1.1.559
        compressor-6-on-off OBJECT-TYPE
                    SYNTAX Integer32 (0..1)
                    UNITS "N/A"
                    MAX-ACCESS read-only
                    STATUS current
                    DESCRIPTION "Compressor 6 status (0= Off, 1= On)"
                    DEFVAL { 0 }
                    ::= { digitalObjects 559 }

        -- 1.3.6.1.4.1.9839.2.1.1.560
        or-compressors OBJECT-TYPE
                    SYNTAX Integer32 (0..1)
                    UNITS "N/A"
                    MAX-ACCESS read-only
                    STATUS current
                    DESCRIPTION "Compressors status (0= Off, 1= On)"
                    DEFVAL { 0 }
                    ::= { digitalObjects 560 }

        -- 1.3.6.1.4.1.9839.2.1.1.561
        power-line-active OBJECT-TYPE
                    SYNTAX Integer32 (0..1)
                    UNITS "N/A"
                    MAX-ACCESS read-only
                    STATUS current
                    DESCRIPTION "Power line active (0= Line A, 1= Line B)"
                    DEFVAL { 0 }
                    ::= { digitalObjects 561 }

        -- 1.3.6.1.4.1.9839.2.1.1.562
        heater-run OBJECT-TYPE
                    SYNTAX Integer32 (0..1)
                    UNITS "N/A"
                    MAX-ACCESS read-only
                    STATUS current
                    DESCRIPTION "Heater status (0= Off, 1= On)"
                    DEFVAL { 0 }
                    ::= { digitalObjects 562 }

        -- 1.3.6.1.4.1.9839.2.1.1.563
        fc-run OBJECT-TYPE
                    SYNTAX Integer32 (0..1)
                    UNITS "N/A"
                    MAX-ACCESS read-only
                    STATUS current
                    DESCRIPTION "Freecooling running (0= Off, 1=On)"
                    DEFVAL { 0 }
                    ::= { digitalObjects 563 }

        -- 1.3.6.1.4.1.9839.2.1.1.564
        comp-c1-run OBJECT-TYPE
                    SYNTAX Integer32 (0..1)
                    UNITS "N/A"
                    MAX-ACCESS read-only
                    STATUS current
                    DESCRIPTION "Circuit 1 running"
                    DEFVAL { 0 }
                    ::= { digitalObjects 564 }

        -- 1.3.6.1.4.1.9839.2.1.1.565
        comp-c2-run OBJECT-TYPE
                    SYNTAX Integer32 (0..1)
                    UNITS "N/A"
                    MAX-ACCESS read-only
                    STATUS current
                    DESCRIPTION "Circuit 2 running"
                    DEFVAL { 0 }
                    ::= { digitalObjects 565 }

        -- 1.3.6.1.4.1.9839.2.1.1.566
        emergency-mode-active OBJECT-TYPE
                    SYNTAX Integer32 (0..1)
                    UNITS "N/A"
                    MAX-ACCESS read-only
                    STATUS current
                    DESCRIPTION "Emergency mode active (0= Off, 1= On)"
                    DEFVAL { 1 }
                    ::= { digitalObjects 566 }



        -- 1.3.6.1.4.1.9839.2.1.2
        analogObjects OBJECT IDENTIFIER ::= { cdzMIB 2 }

        -- 1.3.6.1.4.1.9839.2.1.2.51
        bms-cooling-setpoint OBJECT-TYPE
                    SYNTAX Integer32 (-999..999)
                    UNITS "C/F x10"
                    MAX-ACCESS read-write
                    STATUS current
                    DESCRIPTION "Cooling setpoint"
                    DEFVAL { 0 }
                    ::= { analogObjects 51 }

        -- 1.3.6.1.4.1.9839.2.1.2.52
        bms-heating-setpoint OBJECT-TYPE
                    SYNTAX Integer32 (-999..999)
                    UNITS "C/F x10"
                    MAX-ACCESS read-write
                    STATUS current
                    DESCRIPTION "Heating setpoint"
                    DEFVAL { 0 }
                    ::= { analogObjects 52 }

        -- 1.3.6.1.4.1.9839.2.1.2.53
        bms-emergency-setpoint OBJECT-TYPE
                    SYNTAX Integer32 (-999..999)
                    UNITS "C/F x10"
                    MAX-ACCESS read-write
                    STATUS current
                    DESCRIPTION "Emergency setpoint"
                    DEFVAL { 0 }
                    ::= { analogObjects 53 }

        -- 1.3.6.1.4.1.9839.2.1.2.54
        bms-humidity-setpoint OBJECT-TYPE
                    SYNTAX Integer32 (-999..999)
                    UNITS "%Rh x10"
                    MAX-ACCESS read-write
                    STATUS current
                    DESCRIPTION "Humidity setpoint"
                    DEFVAL { 0 }
                    ::= { analogObjects 54 }

        -- 1.3.6.1.4.1.9839.2.1.2.60
        bms-external-temp OBJECT-TYPE
                    SYNTAX Integer32 (-999..999)
                    UNITS "C/F x10"
                    MAX-ACCESS read-write
                    STATUS current
                    DESCRIPTION "External air temperature by BMS"
                    DEFVAL { 0 }
                    ::= { analogObjects 60 }

        -- 1.3.6.1.4.1.9839.2.1.2.71
        inlet-temp-1 OBJECT-TYPE
                    SYNTAX Integer32 (-999..999)
                    UNITS "C/F x10"
                    MAX-ACCESS read-only
                    STATUS current
                    DESCRIPTION "Inlet temperature 1"
                    DEFVAL { 0 }
                    ::= { analogObjects 71 }

        -- 1.3.6.1.4.1.9839.2.1.2.72
        inlet-temp-2 OBJECT-TYPE
                    SYNTAX Integer32 (-999..999)
                    UNITS "C/F x10"
                    MAX-ACCESS read-only
                    STATUS current
                    DESCRIPTION "Inlet temperature 2"
                    DEFVAL { 0 }
                    ::= { analogObjects 72 }

        -- 1.3.6.1.4.1.9839.2.1.2.73
        inlet-temp-3 OBJECT-TYPE
                    SYNTAX Integer32 (-999..999)
                    UNITS "C/F x10"
                    MAX-ACCESS read-only
                    STATUS current
                    DESCRIPTION "Inlet temperature 3"
                    DEFVAL { 0 }
                    ::= { analogObjects 73 }

        -- 1.3.6.1.4.1.9839.2.1.2.74
        outlet-temp-1 OBJECT-TYPE
                    SYNTAX Integer32 (-999..999)
                    UNITS "C/F x10"
                    MAX-ACCESS read-only
                    STATUS current
                    DESCRIPTION "Outlet temperature 1"
                    DEFVAL { 0 }
                    ::= { analogObjects 74 }

        -- 1.3.6.1.4.1.9839.2.1.2.75
        outlet-temp-2 OBJECT-TYPE
                    SYNTAX Integer32 (-999..999)
                    UNITS "C/F x10"
                    MAX-ACCESS read-only
                    STATUS current
                    DESCRIPTION "Outlet temperature 2"
                    DEFVAL { 0 }
                    ::= { analogObjects 75 }

        -- 1.3.6.1.4.1.9839.2.1.2.76
        outlet-temp-3 OBJECT-TYPE
                    SYNTAX Integer32 (-999..999)
                    UNITS "C/F x10"
                    MAX-ACCESS read-only
                    STATUS current
                    DESCRIPTION "Outlet temperature 3"
                    DEFVAL { 0 }
                    ::= { analogObjects 76 }

        -- 1.3.6.1.4.1.9839.2.1.2.77
        twin-valve-1 OBJECT-TYPE
                    SYNTAX Integer32 (-999..999)
                    UNITS "C/F x10"
                    MAX-ACCESS read-only
                    STATUS current
                    DESCRIPTION "Valve 1 inlet water temperature"
                    DEFVAL { 0 }
                    ::= { analogObjects 77 }

        -- 1.3.6.1.4.1.9839.2.1.2.78
        twout-valve-1 OBJECT-TYPE
                    SYNTAX Integer32 (-999..999)
                    UNITS "C/F x10"
                    MAX-ACCESS read-only
                    STATUS current
                    DESCRIPTION "Valve 1 outlet water temperature"
                    DEFVAL { 0 }
                    ::= { analogObjects 78 }

        -- 1.3.6.1.4.1.9839.2.1.2.79
        twby-valve-1 OBJECT-TYPE
                    SYNTAX Integer32 (-999..999)
                    UNITS "C/F x10"
                    MAX-ACCESS read-only
                    STATUS current
                    DESCRIPTION "Valve 1 water bypass temperature"
                    DEFVAL { 0 }
                    ::= { analogObjects 79 }

        -- 1.3.6.1.4.1.9839.2.1.2.80
        twin-valve-2 OBJECT-TYPE
                    SYNTAX Integer32 (-999..999)
                    UNITS "C/F x10"
                    MAX-ACCESS read-only
                    STATUS current
                    DESCRIPTION "Valve 2 inlet water temperature"
                    DEFVAL { 0 }
                    ::= { analogObjects 80 }

        -- 1.3.6.1.4.1.9839.2.1.2.81
        twout-valve-2 OBJECT-TYPE
                    SYNTAX Integer32 (-999..999)
                    UNITS "C/F x10"
                    MAX-ACCESS read-only
                    STATUS current
                    DESCRIPTION "Valve 2 outlet water temperature"
                    DEFVAL { 0 }
                    ::= { analogObjects 81 }

        -- 1.3.6.1.4.1.9839.2.1.2.82
        twby-valve-2 OBJECT-TYPE
                    SYNTAX Integer32 (-999..999)
                    UNITS "C/F x10"
                    MAX-ACCESS read-only
                    STATUS current
                    DESCRIPTION "Valve 2 water bypass temperature"
                    DEFVAL { 0 }
                    ::= { analogObjects 82 }

        -- 1.3.6.1.4.1.9839.2.1.2.83
        coil-temp OBJECT-TYPE
                    SYNTAX Integer32 (-999..999)
                    UNITS "C/F x10"
                    MAX-ACCESS read-only
                    STATUS current
                    DESCRIPTION "Coil temperature"
                    DEFVAL { 0 }
                    ::= { analogObjects 83 }

        -- 1.3.6.1.4.1.9839.2.1.2.84
        tinw-condenser OBJECT-TYPE
                    SYNTAX Integer32 (-999..999)
                    UNITS "C/F x10"
                    MAX-ACCESS read-only
                    STATUS current
                    DESCRIPTION "Condenser inlet temperature water"
                    DEFVAL { 0 }
                    ::= { analogObjects 84 }

        -- 1.3.6.1.4.1.9839.2.1.2.85
        hot-water-in OBJECT-TYPE
                    SYNTAX Integer32 (-999..999)
                    UNITS "C/F x10"
                    MAX-ACCESS read-only
                    STATUS current
                    DESCRIPTION "Hot water inlet temperature"
                    DEFVAL { 0 }
                    ::= { analogObjects 85 }

        -- 1.3.6.1.4.1.9839.2.1.2.86
        external-air-temp-read OBJECT-TYPE
                    SYNTAX Integer32 (-999..999)
                    UNITS "C/F x10"
                    MAX-ACCESS read-only
                    STATUS current
                    DESCRIPTION "External air temperature by probe"
                    DEFVAL { 0 }
                    ::= { analogObjects 86 }

        -- 1.3.6.1.4.1.9839.2.1.2.87
        plan-external-temp OBJECT-TYPE
                    SYNTAX Integer32 (-999..999)
                    UNITS "C/F x10"
                    MAX-ACCESS read-only
                    STATUS current
                    DESCRIPTION "External air temperature by pLAN"
                    DEFVAL { 0 }
                    ::= { analogObjects 87 }

        -- 1.3.6.1.4.1.9839.2.1.2.88
        t-suction-c1 OBJECT-TYPE
                    SYNTAX Integer32 (-999..999)
                    UNITS "C/F x10"
                    MAX-ACCESS read-only
                    STATUS current
                    DESCRIPTION "Suction temperature C1"
                    DEFVAL { 0 }
                    ::= { analogObjects 88 }

        -- 1.3.6.1.4.1.9839.2.1.2.89
        t-discharge-c1 OBJECT-TYPE
                    SYNTAX Integer32 (-999..999)
                    UNITS "C/F x10"
                    MAX-ACCESS read-only
                    STATUS current
                    DESCRIPTION "Discharge temperature C1"
                    DEFVAL { 0 }
                    ::= { analogObjects 89 }

        -- 1.3.6.1.4.1.9839.2.1.2.90
        t-evap-dew-c1 OBJECT-TYPE
                    SYNTAX Integer32 (-999..999)
                    UNITS "C/F x10"
                    MAX-ACCESS read-only
                    STATUS current
                    DESCRIPTION "Evaporation temperature Dew-point circuit 1"
                    DEFVAL { 0 }
                    ::= { analogObjects 90 }

        -- 1.3.6.1.4.1.9839.2.1.2.91
        t-evap-bub-c1 OBJECT-TYPE
                    SYNTAX Integer32 (-999..999)
                    UNITS "C/F x10"
                    MAX-ACCESS read-only
                    STATUS current
                    DESCRIPTION "Evaporation temperature Bubble-point circuit 1"
                    DEFVAL { 0 }
                    ::= { analogObjects 91 }

        -- 1.3.6.1.4.1.9839.2.1.2.92
        t-cond-dew-c1 OBJECT-TYPE
                    SYNTAX Integer32 (-999..999)
                    UNITS "C/F x10"
                    MAX-ACCESS read-only
                    STATUS current
                    DESCRIPTION "Condensation temperature Dew-point circuit 1"
                    DEFVAL { 0 }
                    ::= { analogObjects 92 }

        -- 1.3.6.1.4.1.9839.2.1.2.93
        t-cond-bub-c1 OBJECT-TYPE
                    SYNTAX Integer32 (-999..999)
                    UNITS "C/F x10"
                    MAX-ACCESS read-only
                    STATUS current
                    DESCRIPTION "Condensation temperature Bubble-point circuit 1"
                    DEFVAL { 0 }
                    ::= { analogObjects 93 }

        -- 1.3.6.1.4.1.9839.2.1.2.94
        sh-c1-value OBJECT-TYPE
                    SYNTAX Integer32 (-999..999)
                    UNITS "K x10"
                    MAX-ACCESS read-only
                    STATUS current
                    DESCRIPTION "Superheating circuit 1 value"
                    DEFVAL { 0 }
                    ::= { analogObjects 94 }

        -- 1.3.6.1.4.1.9839.2.1.2.95
        t-suction-c2 OBJECT-TYPE
                    SYNTAX Integer32 (-999..999)
                    UNITS "C/F x10"
                    MAX-ACCESS read-only
                    STATUS current
                    DESCRIPTION "Suction temperature C2"
                    DEFVAL { 0 }
                    ::= { analogObjects 95 }

        -- 1.3.6.1.4.1.9839.2.1.2.96
        t-discharge-c2 OBJECT-TYPE
                    SYNTAX Integer32 (-999..999)
                    UNITS "C/F x10"
                    MAX-ACCESS read-only
                    STATUS current
                    DESCRIPTION "Discharge temperature C2"
                    DEFVAL { 0 }
                    ::= { analogObjects 96 }

        -- 1.3.6.1.4.1.9839.2.1.2.97
        t-evap-dew-c2 OBJECT-TYPE
                    SYNTAX Integer32 (-999..999)
                    UNITS "C/F x10"
                    MAX-ACCESS read-only
                    STATUS current
                    DESCRIPTION "Evaporation temperature Dew-point circuit 2"
                    DEFVAL { 0 }
                    ::= { analogObjects 97 }

        -- 1.3.6.1.4.1.9839.2.1.2.98
        t-evap-bub-c2 OBJECT-TYPE
                    SYNTAX Integer32 (-999..999)
                    UNITS "C/F x10"
                    MAX-ACCESS read-only
                    STATUS current
                    DESCRIPTION "Evaporation temperature Bubble-point circuit 2"
                    DEFVAL { 0 }
                    ::= { analogObjects 98 }

        -- 1.3.6.1.4.1.9839.2.1.2.99
        t-cond-dew-c2 OBJECT-TYPE
                    SYNTAX Integer32 (-999..999)
                    UNITS "C/F x10"
                    MAX-ACCESS read-only
                    STATUS current
                    DESCRIPTION "Condensation temperature Dew-point circuit 2"
                    DEFVAL { 0 }
                    ::= { analogObjects 99 }

        -- 1.3.6.1.4.1.9839.2.1.2.100
        t-cond-bub-c2 OBJECT-TYPE
                    SYNTAX Integer32 (-999..999)
                    UNITS "C/F x10"
                    MAX-ACCESS read-only
                    STATUS current
                    DESCRIPTION "Condensation temperature Bubble-point circuit 2"
                    DEFVAL { 0 }
                    ::= { analogObjects 100 }

        -- 1.3.6.1.4.1.9839.2.1.2.101
        sh-c2-value OBJECT-TYPE
                    SYNTAX Integer32 (-999..999)
                    UNITS "K x10"
                    MAX-ACCESS read-only
                    STATUS current
                    DESCRIPTION "Superheating circuit 2 value"
                    DEFVAL { 0 }
                    ::= { analogObjects 101 }

        -- 1.3.6.1.4.1.9839.2.1.2.102
        inlet-temperature-avg OBJECT-TYPE
                    SYNTAX Integer32 (-999..999)
                    UNITS "C/F x10"
                    MAX-ACCESS read-only
                    STATUS current
                    DESCRIPTION "Inlet temperature average"
                    DEFVAL { 0 }
                    ::= { analogObjects 102 }

        -- 1.3.6.1.4.1.9839.2.1.2.103
        inlet-temperature-avg-2 OBJECT-TYPE
                    SYNTAX Integer32 (-999..999)
                    UNITS "C/F x10"
                    MAX-ACCESS read-only
                    STATUS current
                    DESCRIPTION "Inlet temperature average"
                    DEFVAL { 0 }
                    ::= { analogObjects 103 }

        -- 1.3.6.1.4.1.9839.2.1.2.104
        inlet-temperature-avg-3 OBJECT-TYPE
                    SYNTAX Integer32 (-999..999)
                    UNITS "C/F x10"
                    MAX-ACCESS read-only
                    STATUS current
                    DESCRIPTION "Inlet temperature average"
                    DEFVAL { 0 }
                    ::= { analogObjects 104 }

        -- 1.3.6.1.4.1.9839.2.1.2.105
        outlet-temperature-avg OBJECT-TYPE
                    SYNTAX Integer32 (-999..999)
                    UNITS "C/F x10"
                    MAX-ACCESS read-only
                    STATUS current
                    DESCRIPTION "Outlet temperature average"
                    DEFVAL { 0 }
                    ::= { analogObjects 105 }

        -- 1.3.6.1.4.1.9839.2.1.2.106
        outlet-temperature-avg-2 OBJECT-TYPE
                    SYNTAX Integer32 (-999..999)
                    UNITS "C/F x10"
                    MAX-ACCESS read-only
                    STATUS current
                    DESCRIPTION "Outlet temperature average"
                    DEFVAL { 0 }
                    ::= { analogObjects 106 }

        -- 1.3.6.1.4.1.9839.2.1.2.107
        outlet-temperature-avg-3 OBJECT-TYPE
                    SYNTAX Integer32 (-999..999)
                    UNITS "C/F x10"
                    MAX-ACCESS read-only
                    STATUS current
                    DESCRIPTION "Outlet temperature average"
                    DEFVAL { 0 }
                    ::= { analogObjects 107 }

        -- 1.3.6.1.4.1.9839.2.1.2.108
        regulation-temp OBJECT-TYPE
                    SYNTAX Integer32 (-999..999)
                    UNITS "C/F x10"
                    MAX-ACCESS read-only
                    STATUS current
                    DESCRIPTION "Regulation temperature"
                    DEFVAL { 0 }
                    ::= { analogObjects 108 }

        -- 1.3.6.1.4.1.9839.2.1.2.109
        regulation-temp-2 OBJECT-TYPE
                    SYNTAX Integer32 (-999..999)
                    UNITS "C/F x10"
                    MAX-ACCESS read-only
                    STATUS current
                    DESCRIPTION "Regulation temperature"
                    DEFVAL { 0 }
                    ::= { analogObjects 109 }

        -- 1.3.6.1.4.1.9839.2.1.2.110
        regulation-temp-3 OBJECT-TYPE
                    SYNTAX Integer32 (-999..999)
                    UNITS "C/F x10"
                    MAX-ACCESS read-only
                    STATUS current
                    DESCRIPTION "Regulation temperature"
                    DEFVAL { 0 }
                    ::= { analogObjects 110 }

        -- 1.3.6.1.4.1.9839.2.1.2.111
        inlet-humidity OBJECT-TYPE
                    SYNTAX Integer32 (0..999)
                    UNITS "%Rh x10"
                    MAX-ACCESS read-only
                    STATUS current
                    DESCRIPTION "Inlet air humidity"
                    DEFVAL { 0 }
                    ::= { analogObjects 111 }

        -- 1.3.6.1.4.1.9839.2.1.2.112
        outlet-humidity OBJECT-TYPE
                    SYNTAX Integer32 (0..999)
                    UNITS "%Rh x10"
                    MAX-ACCESS read-only
                    STATUS current
                    DESCRIPTION "Outlet air humidity"
                    DEFVAL { 0 }
                    ::= { analogObjects 112 }

        -- 1.3.6.1.4.1.9839.2.1.2.113
        ext-humidity OBJECT-TYPE
                    SYNTAX Integer32 (0..999)
                    UNITS "%Rh x10"
                    MAX-ACCESS read-only
                    STATUS current
                    DESCRIPTION "External air humidity"
                    DEFVAL { 0 }
                    ::= { analogObjects 113 }

        -- 1.3.6.1.4.1.9839.2.1.2.114
        lp-c1 OBJECT-TYPE
                    SYNTAX Integer32 (-999..999)
                    UNITS "bar x10"
                    MAX-ACCESS read-only
                    STATUS current
                    DESCRIPTION "Low pressure circuit 1 value"
                    DEFVAL { 0 }
                    ::= { analogObjects 114 }

        -- 1.3.6.1.4.1.9839.2.1.2.115
        hp-c1 OBJECT-TYPE
                    SYNTAX Integer32 (-999..999)
                    UNITS "bar x10"
                    MAX-ACCESS read-only
                    STATUS current
                    DESCRIPTION "High pressure circuit 1 value"
                    DEFVAL { 0 }
                    ::= { analogObjects 115 }

        -- 1.3.6.1.4.1.9839.2.1.2.116
        hgp-c1 OBJECT-TYPE
                    SYNTAX Integer32 (-999..999)
                    UNITS "bar x10"
                    MAX-ACCESS read-only
                    STATUS current
                    DESCRIPTION "Hot gas pressure circuit 1 value"
                    DEFVAL { 0 }
                    ::= { analogObjects 116 }

        -- 1.3.6.1.4.1.9839.2.1.2.117
        lp-c2 OBJECT-TYPE
                    SYNTAX Integer32 (-999..999)
                    UNITS "bar x10"
                    MAX-ACCESS read-only
                    STATUS current
                    DESCRIPTION "Low pressure circuit 2 value"
                    DEFVAL { 0 }
                    ::= { analogObjects 117 }

        -- 1.3.6.1.4.1.9839.2.1.2.118
        hp-c2 OBJECT-TYPE
                    SYNTAX Integer32 (-999..999)
                    UNITS "bar x10"
                    MAX-ACCESS read-only
                    STATUS current
                    DESCRIPTION "High pressure circuit 2 value"
                    DEFVAL { 0 }
                    ::= { analogObjects 118 }

        -- 1.3.6.1.4.1.9839.2.1.2.119
        hgp-c2 OBJECT-TYPE
                    SYNTAX Integer32 (-999..999)
                    UNITS "bar x10"
                    MAX-ACCESS read-only
                    STATUS current
                    DESCRIPTION "Hot gas pressure circuit 2 value"
                    DEFVAL { 0 }
                    ::= { analogObjects 119 }

        -- 1.3.6.1.4.1.9839.2.1.2.120
        dp-value OBJECT-TYPE
                    SYNTAX Integer32 (0..30000)
                    UNITS "Pa x10"
                    MAX-ACCESS read-only
                    STATUS current
                    DESCRIPTION "DP value"
                    DEFVAL { 0 }
                    ::= { analogObjects 120 }

        -- 1.3.6.1.4.1.9839.2.1.2.121
        steam-production OBJECT-TYPE
                    SYNTAX Integer32 (0..999)
                    UNITS "Kg/h x10"
                    MAX-ACCESS read-only
                    STATUS current
                    DESCRIPTION "Steam production (Kg/h)"
                    DEFVAL { 0 }
                    ::= { analogObjects 121 }

        -- 1.3.6.1.4.1.9839.2.1.2.122
        feedback-rps-inverter-1 OBJECT-TYPE
                    SYNTAX Integer32 (-9999..9999)
                    UNITS "N/A"
                    MAX-ACCESS read-only
                    STATUS current
                    DESCRIPTION "Inverter compressor 1 speed (RPS)"
                    DEFVAL { 0 }
                    ::= { analogObjects 122 }

        -- 1.3.6.1.4.1.9839.2.1.2.123
        feedback-rps-inverter-2 OBJECT-TYPE
                    SYNTAX Integer32 (-9999..9999)
                    UNITS "N/A"
                    MAX-ACCESS read-only
                    STATUS current
                    DESCRIPTION "Inverter compressor 2 speed (RPS)"
                    DEFVAL { 0 }
                    ::= { analogObjects 123 }

        -- 1.3.6.1.4.1.9839.2.1.2.131
        cooling-setpoint-active OBJECT-TYPE
                    SYNTAX Integer32 (0..999)
                    UNITS "C/F x10"
                    MAX-ACCESS read-only
                    STATUS current
                    DESCRIPTION "Cooling temperature setpoint active"
                    DEFVAL { 0 }
                    ::= { analogObjects 131 }

        -- 1.3.6.1.4.1.9839.2.1.2.132
        heating-setpoint-active OBJECT-TYPE
                    SYNTAX Integer32 (0..999)
                    UNITS "C/F x10"
                    MAX-ACCESS read-only
                    STATUS current
                    DESCRIPTION "Heating temperature setpoint active"
                    DEFVAL { 0 }
                    ::= { analogObjects 132 }

        -- 1.3.6.1.4.1.9839.2.1.2.133
        emergency-setpoint-active OBJECT-TYPE
                    SYNTAX Integer32 (0..999)
                    UNITS "C/F x10"
                    MAX-ACCESS read-only
                    STATUS current
                    DESCRIPTION "Emergency temperature setpoint active"
                    DEFVAL { 0 }
                    ::= { analogObjects 133 }

        -- 1.3.6.1.4.1.9839.2.1.2.134
        humidity-setpoint-active OBJECT-TYPE
                    SYNTAX Integer32 (0..999)
                    UNITS "%Rh x10"
                    MAX-ACCESS read-only
                    STATUS current
                    DESCRIPTION "Humidity setpoint active"
                    DEFVAL { 0 }
                    ::= { analogObjects 134 }

        -- 1.3.6.1.4.1.9839.2.1.2.136
        cooling-capacity-circuit-1 OBJECT-TYPE
                    SYNTAX Integer32 (-9999..9999)
                    UNITS "N/A"
                    MAX-ACCESS read-only
                    STATUS current
                    DESCRIPTION "Cooling capacity water circuit 1 (Kw)"
                    DEFVAL { 0 }
                    ::= { analogObjects 136 }

        -- 1.3.6.1.4.1.9839.2.1.2.137
        cooling-capacity-circuit-2 OBJECT-TYPE
                    SYNTAX Integer32 (-9999..9999)
                    UNITS "N/A"
                    MAX-ACCESS read-only
                    STATUS current
                    DESCRIPTION "Cooling capacity water circuit 2 (Kw)"
                    DEFVAL { 0 }
                    ::= { analogObjects 137 }

        -- 1.3.6.1.4.1.9839.2.1.2.138
        in-water-pressure-valve-1 OBJECT-TYPE
                    SYNTAX Integer32 (-9999..9999)
                    UNITS "N/A"
                    MAX-ACCESS read-only
                    STATUS current
                    DESCRIPTION "Valve 1 inlet water pressure"
                    DEFVAL { 0 }
                    ::= { analogObjects 138 }

        -- 1.3.6.1.4.1.9839.2.1.2.139
        out-water-pressure-valve-1 OBJECT-TYPE
                    SYNTAX Integer32 (-9999..9999)
                    UNITS "N/A"
                    MAX-ACCESS read-only
                    STATUS current
                    DESCRIPTION "Valve 1 outlet water pressure"
                    DEFVAL { 0 }
                    ::= { analogObjects 139 }

        -- 1.3.6.1.4.1.9839.2.1.2.140
        in-water-pressure-valve-2 OBJECT-TYPE
                    SYNTAX Integer32 (-9999..9999)
                    UNITS "N/A"
                    MAX-ACCESS read-only
                    STATUS current
                    DESCRIPTION "Valve 2 inlet water pressure"
                    DEFVAL { 0 }
                    ::= { analogObjects 140 }

        -- 1.3.6.1.4.1.9839.2.1.2.141
        out-water-pressure-valve-2 OBJECT-TYPE
                    SYNTAX Integer32 (-9999..9999)
                    UNITS "N/A"
                    MAX-ACCESS read-only
                    STATUS current
                    DESCRIPTION "Valve 2 outlet water pressure"
                    DEFVAL { 0 }
                    ::= { analogObjects 141 }
                    
        -- 1.3.6.1.4.1.9839.2.1.2.142
        kwatt-3ph-seneca-s203ta OBJECT-TYPE
                    SYNTAX Integer32 (-9999..9999)
                    UNITS "N/A"
                    MAX-ACCESS read-only
                    STATUS current
                    DESCRIPTION "Active power absorbed"
                    DEFVAL { 0 }
                    ::= { analogObjects 142 }
                    
        -- 1.3.6.1.4.1.9839.2.1.2.143
        electrical-Current OBJECT-TYPE
                    SYNTAX Integer32 (-9999..9999)
                    UNITS "N/A"
                    MAX-ACCESS read-only
                    STATUS current
                    DESCRIPTION "Electrical current absorbed"
                    DEFVAL { 0 }
                    ::= { analogObjects 143 }



        -- 1.3.6.1.4.1.9839.2.1.3
        integerObjects OBJECT IDENTIFIER ::= { cdzMIB 3 }


        -- 1.3.6.1.4.1.9839.2.1.3.31
        comp-power-output OBJECT-TYPE
                    SYNTAX Integer32 (0..9999)
                    UNITS "N/A"
                    MAX-ACCESS read-only
                    STATUS current
                    DESCRIPTION "Compressor power output (0 - 1000)"
                    DEFVAL { 0 }
                    ::= { integerObjects 31 }

        -- 1.3.6.1.4.1.9839.2.1.3.51
        ext-fan-request OBJECT-TYPE
                    SYNTAX Integer32 (0..1000)
                    UNITS "N/A"
                    MAX-ACCESS read-write
                    STATUS current
                    DESCRIPTION "External fan request (0-1000)"
                    DEFVAL { 0 }
                    ::= { integerObjects 51 }

        -- 1.3.6.1.4.1.9839.2.1.3.52
        cooling-req-by-bms OBJECT-TYPE
                    SYNTAX Integer32 (0..1000)
                    UNITS "N/A"
                    MAX-ACCESS read-write
                    STATUS current
                    DESCRIPTION "Cooling request by BMS (0 - 1000)"
                    DEFVAL { 0 }
                    ::= { integerObjects 52 }

        -- 1.3.6.1.4.1.9839.2.1.3.53
        heating-req-by-bms OBJECT-TYPE
                    SYNTAX Integer32 (0..1000)
                    UNITS "N/A"
                    MAX-ACCESS read-write
                    STATUS current
                    DESCRIPTION "Heating request by BMS (0 - 1000)"
                    DEFVAL { 0 }
                    ::= { integerObjects 53 }

        -- 1.3.6.1.4.1.9839.2.1.3.54
        humid-req-by-bms OBJECT-TYPE
                    SYNTAX Integer32 (0..1000)
                    UNITS "N/A"
                    MAX-ACCESS read-write
                    STATUS current
                    DESCRIPTION "Humidifier request by BMS (0 - 1000)"
                    DEFVAL { 0 }
                    ::= { integerObjects 54 }

        -- 1.3.6.1.4.1.9839.2.1.3.55
        dehumid-req-by-bms OBJECT-TYPE
                    SYNTAX Integer32 (0..1000)
                    UNITS "N/A"
                    MAX-ACCESS read-write
                    STATUS current
                    DESCRIPTION "Dehumidifier request by BMS (0 - 1000)"
                    DEFVAL { 0 }
                    ::= { integerObjects 55 }

        -- 1.3.6.1.4.1.9839.2.1.3.56
        bms-air-flow-set-point OBJECT-TYPE
                    SYNTAX Integer32 (0..999)
                    UNITS "N/A"
                    MAX-ACCESS read-write
                    STATUS current
                    DESCRIPTION "BMS air flow set point (m3/h * 100)"
                    DEFVAL { 0 }
                    ::= { integerObjects 56 }

        -- 1.3.6.1.4.1.9839.2.1.3.57
        bms-dp-set-point OBJECT-TYPE
                    SYNTAX Integer32 (0..999)
                    UNITS "Pa"
                    MAX-ACCESS read-write
                    STATUS current
                    DESCRIPTION "DP set point"
                    DEFVAL { 0 }
                    ::= { integerObjects 57 }

        -- 1.3.6.1.4.1.9839.2.1.3.58
        bms-1-watchdog-integer-var OBJECT-TYPE
                    SYNTAX Integer32 (0..32767)
                    UNITS "N/A"
                    MAX-ACCESS read-write
                    STATUS current
                    DESCRIPTION "BMS 1 Watchdog integer variables"
                    DEFVAL { 0 }
                    ::= { integerObjects 58 }

	-- 1.3.6.1.4.1.9839.2.1.3.69
        sw-version-L OBJECT-TYPE
                    SYNTAX Integer32 (0..99)
                    UNITS "N/A"
                    MAX-ACCESS read-only
                    STATUS current
                    DESCRIPTION "Software version 02.XX"
                    DEFVAL { 0 }
                    ::= { integerObjects 69 }

	-- 1.3.6.1.4.1.9839.2.1.3.70
        sw-version-H OBJECT-TYPE
                    SYNTAX Integer32 (0..99)
                    UNITS "N/A"
                    MAX-ACCESS read-only
                    STATUS current
                    DESCRIPTION "Software version XX.00"
                    DEFVAL { 0 }
                    ::= { integerObjects 70 }

        -- 1.3.6.1.4.1.9839.2.1.3.71
        sw-code-sup OBJECT-TYPE
                    SYNTAX Integer32 (0..9999)
                    UNITS "N/A"
                    MAX-ACCESS read-only
                    STATUS current
                    DESCRIPTION "Software code (HF1200XXXX)"
                    DEFVAL { 0 }
                    ::= { integerObjects 71 }

        -- 1.3.6.1.4.1.9839.2.1.3.72
        c-hours OBJECT-TYPE
                    SYNTAX Integer32 (0..99)
                    UNITS "N/A"
                    MAX-ACCESS read-only
                    STATUS current
                    DESCRIPTION "Hours"
                    DEFVAL { 0 }
                    ::= { integerObjects 72 }

        -- 1.3.6.1.4.1.9839.2.1.3.73
        c-minute OBJECT-TYPE
                    SYNTAX Integer32 (-32768..32767)
                    UNITS "N/A"
                    MAX-ACCESS read-only
                    STATUS current
                    DESCRIPTION "Minute"
                    DEFVAL { 0 }
                    ::= { integerObjects 73 }

        -- 1.3.6.1.4.1.9839.2.1.3.74
        c-day OBJECT-TYPE
                    SYNTAX Integer32 (0..99)
                    UNITS "N/A"
                    MAX-ACCESS read-only
                    STATUS current
                    DESCRIPTION "Day"
                    DEFVAL { 0 }
                    ::= { integerObjects 74 }

        -- 1.3.6.1.4.1.9839.2.1.3.75
        c-month OBJECT-TYPE
                    SYNTAX Integer32 (0..99)
                    UNITS "N/A"
                    MAX-ACCESS read-only
                    STATUS current
                    DESCRIPTION "Month"
                    DEFVAL { 0 }
                    ::= { integerObjects 75 }

        -- 1.3.6.1.4.1.9839.2.1.3.76
        c-year OBJECT-TYPE
                    SYNTAX Integer32 (0..99)
                    UNITS "N/A"
                    MAX-ACCESS read-only
                    STATUS current
                    DESCRIPTION "Year"
                    DEFVAL { 0 }
                    ::= { integerObjects 76 }

        -- 1.3.6.1.4.1.9839.2.1.3.77
        c-weekday OBJECT-TYPE
                    SYNTAX Integer32 (0..9)
                    UNITS "N/A"
                    MAX-ACCESS read-only
                    STATUS current
                    DESCRIPTION "Weekday (1= Monday, 2= Tuesday, 3= Wednesday, 4= Thursday, 5= Friday, 6= Saturday, 7= Sunday)"
                    DEFVAL { 0 }
                    ::= { integerObjects 77 }

        -- 1.3.6.1.4.1.9839.2.1.3.78
        dp-value-int OBJECT-TYPE
                    SYNTAX Integer32 (0..30000)
                    UNITS "Pa"
                    MAX-ACCESS read-only
                    STATUS current
                    DESCRIPTION "DP value"
                    DEFVAL { 0 }
                    ::= { integerObjects 78 }

        -- 1.3.6.1.4.1.9839.2.1.3.79
        dp-setpoint-active OBJECT-TYPE
                    SYNTAX Integer32 (0..32767)
                    UNITS "Pa"
                    MAX-ACCESS read-only
                    STATUS current
                    DESCRIPTION "DP setpoint active (Pa)"
                    DEFVAL { 0 }
                    ::= { integerObjects 79 }

        -- 1.3.6.1.4.1.9839.2.1.3.80
        unit-status OBJECT-TYPE
                    SYNTAX Integer32 (0..6)
                    UNITS "N/A"
                    MAX-ACCESS read-only
                    STATUS current
                    DESCRIPTION "Unit status (0= Unit On, 1= Standby, 2= Off by scheduler, 3= Off by BMS, 4= Off by DIN, 5= Off by Keyboard, 6= Off by alarm)"
                    DEFVAL { 0 }
                    ::= { integerObjects 80 }

        -- 1.3.6.1.4.1.9839.2.1.3.81
        ain-1-pco1 OBJECT-TYPE
                    SYNTAX Integer32 (0..1)
                    UNITS "N/A"
                    MAX-ACCESS read-only
                    STATUS current
                    DESCRIPTION "Analog input 1 pco1"
                    DEFVAL { 0 }
                    ::= { integerObjects 81 }

        -- 1.3.6.1.4.1.9839.2.1.3.82
        ain-2-pco1 OBJECT-TYPE
                    SYNTAX Integer32 (0..1)
                    UNITS "N/A"
                    MAX-ACCESS read-only
                    STATUS current
                    DESCRIPTION "Analog input 2 pco1"
                    DEFVAL { 0 }
                    ::= { integerObjects 82 }

        -- 1.3.6.1.4.1.9839.2.1.3.83
        ain-3-pco1 OBJECT-TYPE
                    SYNTAX Integer32 (0..1)
                    UNITS "N/A"
                    MAX-ACCESS read-only
                    STATUS current
                    DESCRIPTION "Analog input 3 pco1"
                    DEFVAL { 0 }
                    ::= { integerObjects 83 }

        -- 1.3.6.1.4.1.9839.2.1.3.84
        ain-4-pco1 OBJECT-TYPE
                    SYNTAX Integer32 (0..1)
                    UNITS "N/A"
                    MAX-ACCESS read-only
                    STATUS current
                    DESCRIPTION "Analog input 4 pco1"
                    DEFVAL { 0 }
                    ::= { integerObjects 84 }

        -- 1.3.6.1.4.1.9839.2.1.3.85
        ain-5-pco1 OBJECT-TYPE
                    SYNTAX Integer32 (0..1)
                    UNITS "N/A"
                    MAX-ACCESS read-only
                    STATUS current
                    DESCRIPTION "Analog input 5 pco1"
                    DEFVAL { 0 }
                    ::= { integerObjects 85 }

        -- 1.3.6.1.4.1.9839.2.1.3.86
        ain-6-pco1 OBJECT-TYPE
                    SYNTAX Integer32 (0..1)
                    UNITS "N/A"
                    MAX-ACCESS read-only
                    STATUS current
                    DESCRIPTION "Analog input 6 pco1"
                    DEFVAL { 0 }
                    ::= { integerObjects 86 }

        -- 1.3.6.1.4.1.9839.2.1.3.87
        ain-7-pco1 OBJECT-TYPE
                    SYNTAX Integer32 (0..1)
                    UNITS "N/A"
                    MAX-ACCESS read-only
                    STATUS current
                    DESCRIPTION "Analog input 7 pco1"
                    DEFVAL { 0 }
                    ::= { integerObjects 87 }

        -- 1.3.6.1.4.1.9839.2.1.3.88
        ain-8-pco1 OBJECT-TYPE
                    SYNTAX Integer32 (0..1)
                    UNITS "N/A"
                    MAX-ACCESS read-only
                    STATUS current
                    DESCRIPTION "Analog input 8 pco1"
                    DEFVAL { 0 }
                    ::= { integerObjects 88 }

        -- 1.3.6.1.4.1.9839.2.1.3.89
        ain-9-pco1 OBJECT-TYPE
                    SYNTAX Integer32 (0..1)
                    UNITS "N/A"
                    MAX-ACCESS read-only
                    STATUS current
                    DESCRIPTION "Analog input 9 pco1"
                    DEFVAL { 0 }
                    ::= { integerObjects 89 }

        -- 1.3.6.1.4.1.9839.2.1.3.90
        ain-10-pco1 OBJECT-TYPE
                    SYNTAX Integer32 (0..1)
                    UNITS "N/A"
                    MAX-ACCESS read-only
                    STATUS current
                    DESCRIPTION "Analog input 10 pco1"
                    DEFVAL { 0 }
                    ::= { integerObjects 90 }

        -- 1.3.6.1.4.1.9839.2.1.3.91
        ain-11-pco1 OBJECT-TYPE
                    SYNTAX Integer32 (0..1)
                    UNITS "N/A"
                    MAX-ACCESS read-only
                    STATUS current
                    DESCRIPTION "Analog input 11 pco1"
                    DEFVAL { 0 }
                    ::= { integerObjects 91 }

        -- 1.3.6.1.4.1.9839.2.1.3.92
        ain-12-pco1 OBJECT-TYPE
                    SYNTAX Integer32 (0..1)
                    UNITS "N/A"
                    MAX-ACCESS read-only
                    STATUS current
                    DESCRIPTION "Analog input 12 pco1"
                    DEFVAL { 0 }
                    ::= { integerObjects 92 }

        -- 1.3.6.1.4.1.9839.2.1.3.93
        ain-1-pcoe1 OBJECT-TYPE
                    SYNTAX Integer32 (0..1)
                    UNITS "N/A"
                    MAX-ACCESS read-only
                    STATUS current
                    DESCRIPTION "Analog input 1 pcoe1"
                    DEFVAL { 0 }
                    ::= { integerObjects 93 }

        -- 1.3.6.1.4.1.9839.2.1.3.94
        ain-2-pcoe1 OBJECT-TYPE
                    SYNTAX Integer32 (0..1)
                    UNITS "N/A"
                    MAX-ACCESS read-only
                    STATUS current
                    DESCRIPTION "Analog input 2 pcoe1"
                    DEFVAL { 0 }
                    ::= { integerObjects 94 }

        -- 1.3.6.1.4.1.9839.2.1.3.95
        ain-3-pcoe1 OBJECT-TYPE
                    SYNTAX Integer32 (0..1)
                    UNITS "N/A"
                    MAX-ACCESS read-only
                    STATUS current
                    DESCRIPTION "Analog input 3 pcoe1"
                    DEFVAL { 0 }
                    ::= { integerObjects 95 }

        -- 1.3.6.1.4.1.9839.2.1.3.96
        ain-4-pcoe1 OBJECT-TYPE
                    SYNTAX Integer32 (0..1)
                    UNITS "N/A"
                    MAX-ACCESS read-only
                    STATUS current
                    DESCRIPTION "Analog input 4 pcoe1"
                    DEFVAL { 0 }
                    ::= { integerObjects 96 }

        -- 1.3.6.1.4.1.9839.2.1.3.97
        ain-1-pcoe2 OBJECT-TYPE
                    SYNTAX Integer32 (0..1)
                    UNITS "N/A"
                    MAX-ACCESS read-only
                    STATUS current
                    DESCRIPTION "Analog input 1 pcoe2"
                    DEFVAL { 0 }
                    ::= { integerObjects 97 }

        -- 1.3.6.1.4.1.9839.2.1.3.98
        ain-2-pcoe2 OBJECT-TYPE
                    SYNTAX Integer32 (0..1)
                    UNITS "N/A"
                    MAX-ACCESS read-only
                    STATUS current
                    DESCRIPTION "Analog input 2 pcoe2"
                    DEFVAL { 0 }
                    ::= { integerObjects 98 }

        -- 1.3.6.1.4.1.9839.2.1.3.99
        ain-3-pcoe2 OBJECT-TYPE
                    SYNTAX Integer32 (0..1)
                    UNITS "N/A"
                    MAX-ACCESS read-only
                    STATUS current
                    DESCRIPTION "Analog input 3 pcoe2"
                    DEFVAL { 0 }
                    ::= { integerObjects 99 }

        -- 1.3.6.1.4.1.9839.2.1.3.100
        ain-4-pcoe2 OBJECT-TYPE
                    SYNTAX Integer32 (0..1)
                    UNITS "N/A"
                    MAX-ACCESS read-only
                    STATUS current
                    DESCRIPTION "Analog input 4 pcoe2"
                    DEFVAL { 0 }
                    ::= { integerObjects 100 }

        -- 1.3.6.1.4.1.9839.2.1.3.101
        ain-1-pcoe3 OBJECT-TYPE
                    SYNTAX Integer32 (0..1)
                    UNITS "N/A"
                    MAX-ACCESS read-only
                    STATUS current
                    DESCRIPTION "Analog input 1 pcoe3"
                    DEFVAL { 0 }
                    ::= { integerObjects 101 }

        -- 1.3.6.1.4.1.9839.2.1.3.102
        ain-2-pcoe3 OBJECT-TYPE
                    SYNTAX Integer32 (0..1)
                    UNITS "N/A"
                    MAX-ACCESS read-only
                    STATUS current
                    DESCRIPTION "Analog input 2 pcoe3"
                    DEFVAL { 0 }
                    ::= { integerObjects 102 }

        -- 1.3.6.1.4.1.9839.2.1.3.103
        ain-3-pcoe3 OBJECT-TYPE
                    SYNTAX Integer32 (0..1)
                    UNITS "N/A"
                    MAX-ACCESS read-only
                    STATUS current
                    DESCRIPTION "Analog input 3 pcoe3"
                    DEFVAL { 0 }
                    ::= { integerObjects 103 }

        -- 1.3.6.1.4.1.9839.2.1.3.104
        ain-4-pcoe3 OBJECT-TYPE
                    SYNTAX Integer32 (0..1)
                    UNITS "N/A"
                    MAX-ACCESS read-only
                    STATUS current
                    DESCRIPTION "Analog input 4 pcoe3"
                    DEFVAL { 0 }
                    ::= { integerObjects 104 }

        -- 1.3.6.1.4.1.9839.2.1.3.105
        ain-1-pcoe4 OBJECT-TYPE
                    SYNTAX Integer32 (0..1)
                    UNITS "N/A"
                    MAX-ACCESS read-only
                    STATUS current
                    DESCRIPTION "Analog input 1 pcoe4"
                    DEFVAL { 0 }
                    ::= { integerObjects 105 }

        -- 1.3.6.1.4.1.9839.2.1.3.106
        ain-2-pcoe4 OBJECT-TYPE
                    SYNTAX Integer32 (0..1)
                    UNITS "N/A"
                    MAX-ACCESS read-only
                    STATUS current
                    DESCRIPTION "Analog input 2 pcoe4"
                    DEFVAL { 0 }
                    ::= { integerObjects 106 }

        -- 1.3.6.1.4.1.9839.2.1.3.107
        ain-3-pcoe4 OBJECT-TYPE
                    SYNTAX Integer32 (0..1)
                    UNITS "N/A"
                    MAX-ACCESS read-only
                    STATUS current
                    DESCRIPTION "Analog input 3 pcoe4"
                    DEFVAL { 0 }
                    ::= { integerObjects 107 }

        -- 1.3.6.1.4.1.9839.2.1.3.108
        ain-4-pcoe4 OBJECT-TYPE
                    SYNTAX Integer32 (0..1)
                    UNITS "N/A"
                    MAX-ACCESS read-only
                    STATUS current
                    DESCRIPTION "Analog input 4 pcoe4"
                    DEFVAL { 0 }
                    ::= { integerObjects 108 }

        -- 1.3.6.1.4.1.9839.2.1.3.109
        ain-1-pcoe5 OBJECT-TYPE
                    SYNTAX Integer32 (0..1)
                    UNITS "N/A"
                    MAX-ACCESS read-only
                    STATUS current
                    DESCRIPTION "Analog input 1 pcoe5"
                    DEFVAL { 0 }
                    ::= { integerObjects 109 }

        -- 1.3.6.1.4.1.9839.2.1.3.110
        ain-2-pcoe5 OBJECT-TYPE
                    SYNTAX Integer32 (0..1)
                    UNITS "N/A"
                    MAX-ACCESS read-only
                    STATUS current
                    DESCRIPTION "Analog input 2 pcoe5"
                    DEFVAL { 0 }
                    ::= { integerObjects 110 }

        -- 1.3.6.1.4.1.9839.2.1.3.111
        ain-3-pcoe5 OBJECT-TYPE
                    SYNTAX Integer32 (0..1)
                    UNITS "N/A"
                    MAX-ACCESS read-only
                    STATUS current
                    DESCRIPTION "Analog input 3 pcoe5"
                    DEFVAL { 0 }
                    ::= { integerObjects 111 }

        -- 1.3.6.1.4.1.9839.2.1.3.112
        ain-4-pcoe5 OBJECT-TYPE
                    SYNTAX Integer32 (0..1)
                    UNITS "N/A"
                    MAX-ACCESS read-only
                    STATUS current
                    DESCRIPTION "Analog input 4 pcoe5"
                    DEFVAL { 0 }
                    ::= { integerObjects 112 }

        -- 1.3.6.1.4.1.9839.2.1.3.113
        ain-1-eev1 OBJECT-TYPE
                    SYNTAX Integer32 (-32768..32767)
                    UNITS "N/A"
                    MAX-ACCESS read-only
                    STATUS current
                    DESCRIPTION "Analog input 1 EEV1"
                    DEFVAL { 0 }
                    ::= { integerObjects 113 }

        -- 1.3.6.1.4.1.9839.2.1.3.114
        ain-2-eev1 OBJECT-TYPE
                    SYNTAX Integer32 (-32768..32767)
                    UNITS "N/A"
                    MAX-ACCESS read-only
                    STATUS current
                    DESCRIPTION "Analog input 2 EEV1"
                    DEFVAL { 0 }
                    ::= { integerObjects 114 }

        -- 1.3.6.1.4.1.9839.2.1.3.115
        ain-3-eev1 OBJECT-TYPE
                    SYNTAX Integer32 (-32768..32767)
                    UNITS "N/A"
                    MAX-ACCESS read-only
                    STATUS current
                    DESCRIPTION "Analog input 3 EEV1"
                    DEFVAL { 0 }
                    ::= { integerObjects 115 }

        -- 1.3.6.1.4.1.9839.2.1.3.116
        ain-4-eev1 OBJECT-TYPE
                    SYNTAX Integer32 (-32768..32767)
                    UNITS "N/A"
                    MAX-ACCESS read-only
                    STATUS current
                    DESCRIPTION "Analog input 4 EEV1"
                    DEFVAL { 0 }
                    ::= { integerObjects 116 }

        -- 1.3.6.1.4.1.9839.2.1.3.117
        ain-1-eev2 OBJECT-TYPE
                    SYNTAX Integer32 (-32768..32767)
                    UNITS "N/A"
                    MAX-ACCESS read-only
                    STATUS current
                    DESCRIPTION "Analog input 1 EEV2"
                    DEFVAL { 0 }
                    ::= { integerObjects 117 }

        -- 1.3.6.1.4.1.9839.2.1.3.118
        ain-2-eev2 OBJECT-TYPE
                    SYNTAX Integer32 (-32768..32767)
                    UNITS "N/A"
                    MAX-ACCESS read-only
                    STATUS current
                    DESCRIPTION "Analog input 2 EEV2"
                    DEFVAL { 0 }
                    ::= { integerObjects 118 }

        -- 1.3.6.1.4.1.9839.2.1.3.119
        ain-3-eev2 OBJECT-TYPE
                    SYNTAX Integer32 (-32768..32767)
                    UNITS "N/A"
                    MAX-ACCESS read-only
                    STATUS current
                    DESCRIPTION "Analog input 3 EEV2"
                    DEFVAL { 0 }
                    ::= { integerObjects 119 }

        -- 1.3.6.1.4.1.9839.2.1.3.120
        ain-4-eev2 OBJECT-TYPE
                    SYNTAX Integer32 (-32768..32767)
                    UNITS "N/A"
                    MAX-ACCESS read-only
                    STATUS current
                    DESCRIPTION "Analog input 4 EEV2"
                    DEFVAL { 0 }
                    ::= { integerObjects 120 }

        -- 1.3.6.1.4.1.9839.2.1.3.141
        aout-1-pco1 OBJECT-TYPE
                    SYNTAX Integer32 (0..1000)
                    UNITS "N/A"
                    MAX-ACCESS read-only
                    STATUS current
                    DESCRIPTION "Analog output 1 pco1 (0 = 0V,1000= 10V)"
                    DEFVAL { 0 }
                    ::= { integerObjects 141 }

        -- 1.3.6.1.4.1.9839.2.1.3.142
        aout-2-pco1 OBJECT-TYPE
                    SYNTAX Integer32 (0..1000)
                    UNITS "N/A"
                    MAX-ACCESS read-only
                    STATUS current
                    DESCRIPTION "Analog output 2 pco1 (0 = 0V,1000= 10V)"
                    DEFVAL { 0 }
                    ::= { integerObjects 142 }

        -- 1.3.6.1.4.1.9839.2.1.3.143
        aout-3-pco1 OBJECT-TYPE
                    SYNTAX Integer32 (0..1000)
                    UNITS "N/A"
                    MAX-ACCESS read-only
                    STATUS current
                    DESCRIPTION "Analog output 3 pco1 (0 = 0V,1000= 10V)"
                    DEFVAL { 0 }
                    ::= { integerObjects 143 }

        -- 1.3.6.1.4.1.9839.2.1.3.144
        aout-4-pco1 OBJECT-TYPE
                    SYNTAX Integer32 (0..1000)
                    UNITS "N/A"
                    MAX-ACCESS read-only
                    STATUS current
                    DESCRIPTION "Analog output 4 pco1 (0 = 0V,1000= 10V)"
                    DEFVAL { 0 }
                    ::= { integerObjects 144 }

        -- 1.3.6.1.4.1.9839.2.1.3.145
        aout-5-pco1 OBJECT-TYPE
                    SYNTAX Integer32 (0..1000)
                    UNITS "N/A"
                    MAX-ACCESS read-only
                    STATUS current
                    DESCRIPTION "Analog output 5 pco1 (0 = 0V,1000= 10V)"
                    DEFVAL { 0 }
                    ::= { integerObjects 145 }

        -- 1.3.6.1.4.1.9839.2.1.3.146
        aout-6-pco1 OBJECT-TYPE
                    SYNTAX Integer32 (0..1000)
                    UNITS "N/A"
                    MAX-ACCESS read-only
                    STATUS current
                    DESCRIPTION "Analog output 6 pco1 (0 = 0V,1000= 10V)"
                    DEFVAL { 0 }
                    ::= { integerObjects 146 }

        -- 1.3.6.1.4.1.9839.2.1.3.147
        aout-1-pcoe1 OBJECT-TYPE
                    SYNTAX Integer32 (0..1000)
                    UNITS "N/A"
                    MAX-ACCESS read-only
                    STATUS current
                    DESCRIPTION "Analog output 1 pcoe1 (0 = 0V,1000= 10V)"
                    DEFVAL { 0 }
                    ::= { integerObjects 147 }

        -- 1.3.6.1.4.1.9839.2.1.3.148
        aout-1-pcoe2 OBJECT-TYPE
                    SYNTAX Integer32 (0..1000)
                    UNITS "N/A"
                    MAX-ACCESS read-only
                    STATUS current
                    DESCRIPTION "Analog output 1 pcoe2 (0 = 0V,1000= 10V)"
                    DEFVAL { 0 }
                    ::= { integerObjects 148 }

        -- 1.3.6.1.4.1.9839.2.1.3.149
        aout-1-pcoe3 OBJECT-TYPE
                    SYNTAX Integer32 (0..1000)
                    UNITS "N/A"
                    MAX-ACCESS read-only
                    STATUS current
                    DESCRIPTION "Analog output 1 pcoe3 (0 = 0V,1000= 10V)"
                    DEFVAL { 0 }
                    ::= { integerObjects 149 }

        -- 1.3.6.1.4.1.9839.2.1.3.150
        aout-1-pcoe4 OBJECT-TYPE
                    SYNTAX Integer32 (0..1000)
                    UNITS "N/A"
                    MAX-ACCESS read-only
                    STATUS current
                    DESCRIPTION "Analog output 1 pcoe4 (0 = 0V,1000= 10V)"
                    DEFVAL { 0 }
                    ::= { integerObjects 150 }

        -- 1.3.6.1.4.1.9839.2.1.3.151
        aout-1-pcoe5 OBJECT-TYPE
                    SYNTAX Integer32 (0..1000)
                    UNITS "N/A"
                    MAX-ACCESS read-only
                    STATUS current
                    DESCRIPTION "Analog output 1 pcoe5 (0 = 0V,1000= 10V)"
                    DEFVAL { 0 }
                    ::= { integerObjects 151 }

        -- 1.3.6.1.4.1.9839.2.1.3.171
        mem-alarm-data-from-1-to-15 OBJECT-TYPE
                    SYNTAX Integer32 (-32768..32767)
                    UNITS "N/A"
                    MAX-ACCESS read-only
                    STATUS current
                    DESCRIPTION "Alarm data from 1 to 15 (Bit1 = AL1, Bit15 = AL15)"
                    DEFVAL { 0 }
                    ::= { integerObjects 171 }

        -- 1.3.6.1.4.1.9839.2.1.3.172
        mem-alarm-data-from-16-to-31 OBJECT-TYPE
                    SYNTAX Integer32 (-32768..32767)
                    UNITS "N/A"
                    MAX-ACCESS read-only
                    STATUS current
                    DESCRIPTION "Alarm data from 16 to 31 (Bit0 = AL16, Bit15 = AL31)"
                    DEFVAL { 0 }
                    ::= { integerObjects 172 }

        -- 1.3.6.1.4.1.9839.2.1.3.173
        mem-alarm-data-from-32-to-47 OBJECT-TYPE
                    SYNTAX Integer32 (-32768..32767)
                    UNITS "N/A"
                    MAX-ACCESS read-only
                    STATUS current
                    DESCRIPTION "Alarm data from 32 to 47 (Bit0 = AL32, Bit15 = AL47)"
                    DEFVAL { 0 }
                    ::= { integerObjects 173 }

        -- 1.3.6.1.4.1.9839.2.1.3.174
        mem-alarm-data-from-48-to-63 OBJECT-TYPE
                    SYNTAX Integer32 (-32768..32767)
                    UNITS "N/A"
                    MAX-ACCESS read-only
                    STATUS current
                    DESCRIPTION "Alarm data from 48 to 63 (Bit0 = AL48, Bit15 = AL63)"
                    DEFVAL { 0 }
                    ::= { integerObjects 174 }

        -- 1.3.6.1.4.1.9839.2.1.3.175
        mem-alarm-data-from-64-to-79 OBJECT-TYPE
                    SYNTAX Integer32 (-32768..32767)
                    UNITS "N/A"
                    MAX-ACCESS read-only
                    STATUS current
                    DESCRIPTION "Alarm data from 64 to 79 (Bit0 = AL64, Bit15 = AL79)"
                    DEFVAL { 0 }
                    ::= { integerObjects 175 }

        -- 1.3.6.1.4.1.9839.2.1.3.176
        mem-alarm-data-from-80-to-95 OBJECT-TYPE
                    SYNTAX Integer32 (-32768..32767)
                    UNITS "N/A"
                    MAX-ACCESS read-only
                    STATUS current
                    DESCRIPTION "Alarm data from 80 to 95 (Bit0 = AL80, Bit15 = AL95)"
                    DEFVAL { 0 }
                    ::= { integerObjects 176 }

        -- 1.3.6.1.4.1.9839.2.1.3.177
        mem-alarm-data-from-96-to-111 OBJECT-TYPE
                    SYNTAX Integer32 (-32768..32767)
                    UNITS "N/A"
                    MAX-ACCESS read-only
                    STATUS current
                    DESCRIPTION "Alarm data from 96 to 111 (Bit0 = AL96, Bit15 = AL111)"
                    DEFVAL { 0 }
                    ::= { integerObjects 177 }

        -- 1.3.6.1.4.1.9839.2.1.3.178
        mem-alarm-data-from-112-to-127 OBJECT-TYPE
                    SYNTAX Integer32 (-32768..32767)
                    UNITS "N/A"
                    MAX-ACCESS read-only
                    STATUS current
                    DESCRIPTION "Alarm data from 112 to 127 (Bit0 = AL112, Bit15 = AL127)"
                    DEFVAL { 0 }
                    ::= { integerObjects 178 }

        -- 1.3.6.1.4.1.9839.2.1.3.179
        mem-alarm-data-from-128-to-143 OBJECT-TYPE
                    SYNTAX Integer32 (-32768..32767)
                    UNITS "N/A"
                    MAX-ACCESS read-only
                    STATUS current
                    DESCRIPTION "Alarm data from 128 to 143 (Bit0 = AL128, Bit15 = AL143)"
                    DEFVAL { 0 }
                    ::= { integerObjects 179 }

        -- 1.3.6.1.4.1.9839.2.1.3.180
        mem-alarm-data-from-144-to-159 OBJECT-TYPE
                    SYNTAX Integer32 (-32768..32767)
                    UNITS "N/A"
                    MAX-ACCESS read-only
                    STATUS current
                    DESCRIPTION "Alarm data from 144 to 159 (Bit0 = AL144, Bit15 = AL159)"
                    DEFVAL { 0 }
                    ::= { integerObjects 180 }

        -- 1.3.6.1.4.1.9839.2.1.3.181
        mem-alarm-data-from-160-to-175 OBJECT-TYPE
                    SYNTAX Integer32 (-32768..32767)
                    UNITS "N/A"
                    MAX-ACCESS read-only
                    STATUS current
                    DESCRIPTION "Alarm data from 160 to 175 (Bit0 = AL160, Bit15 = AL175)"
                    DEFVAL { 0 }
                    ::= { integerObjects 181 }

        -- 1.3.6.1.4.1.9839.2.1.3.182
        mem-alarm-data-from-176-to-191 OBJECT-TYPE
                    SYNTAX Integer32 (-32768..32767)
                    UNITS "N/A"
                    MAX-ACCESS read-only
                    STATUS current
                    DESCRIPTION "Alarm data from 176 to 191 (Bit0 = AL176, Bit15 = AL191)"
                    DEFVAL { 0 }
                    ::= { integerObjects 182 }

        -- 1.3.6.1.4.1.9839.2.1.3.183
        mem-alarm-data-from-192-to-207 OBJECT-TYPE
                    SYNTAX Integer32 (-32768..32767)
                    UNITS "N/A"
                    MAX-ACCESS read-only
                    STATUS current
                    DESCRIPTION "Alarm data from 192 to 207 (Bit0 = AL192, Bit15 = AL207)"
                    DEFVAL { 0 }
                    ::= { integerObjects 183 }

        -- 1.3.6.1.4.1.9839.2.1.3.184
        mem-alarm-data-from-208-to-223 OBJECT-TYPE
                    SYNTAX Integer32 (-32768..32767)
                    UNITS "N/A"
                    MAX-ACCESS read-only
                    STATUS current
                    DESCRIPTION "Alarm data from 208 to 223 (Bit0 = AL208, Bit15 = AL223)"
                    DEFVAL { 0 }
                    ::= { integerObjects 184 }

        -- 1.3.6.1.4.1.9839.2.1.3.185
        mem-alarm-data-from-224-to-239 OBJECT-TYPE
                    SYNTAX Integer32 (-32768..32767)
                    UNITS "N/A"
                    MAX-ACCESS read-only
                    STATUS current
                    DESCRIPTION "Alarm data from 224 to 239 (Bit0 = AL224, Bit15 = AL239)"
                    DEFVAL { 0 }
                    ::= { integerObjects 185 }

        -- 1.3.6.1.4.1.9839.2.1.3.186
        mem-alarm-data-from-240-to-255 OBJECT-TYPE
                    SYNTAX Integer32 (-32768..32767)
                    UNITS "N/A"
                    MAX-ACCESS read-only
                    STATUS current
                    DESCRIPTION "Alarm data from 240 to 255 (Bit0 = AL240, Bit15 = AL255)"
                    DEFVAL { 0 }
                    ::= { integerObjects 186 }

        -- 1.3.6.1.4.1.9839.2.1.3.187
        mem-alarm-data-from-256-to-271 OBJECT-TYPE
                    SYNTAX Integer32 (-32768..32767)
                    UNITS "N/A"
                    MAX-ACCESS read-only
                    STATUS current
                    DESCRIPTION "Alarm data from 256 to 271 (Bit0 = AL256, Bit15 = AL271)"
                    DEFVAL { 0 }
                    ::= { integerObjects 187 }

        -- 1.3.6.1.4.1.9839.2.1.3.188
        mem-alarm-data-from-272-to-287 OBJECT-TYPE
                    SYNTAX Integer32 (-32768..32767)
                    UNITS "N/A"
                    MAX-ACCESS read-only
                    STATUS current
                    DESCRIPTION "Alarm data from 272 to 287 (Bit0 = AL272, Bit15 = AL287)"
                    DEFVAL { 0 }
                    ::= { integerObjects 188 }

        -- 1.3.6.1.4.1.9839.2.1.3.189
        mem-alarm-data-from-288-to-303 OBJECT-TYPE
                    SYNTAX Integer32 (-32768..32767)
                    UNITS "N/A"
                    MAX-ACCESS read-only
                    STATUS current
                    DESCRIPTION "Alarm data from 288 to 303 (Bit0 = AL288, Bit15 = AL303)"
                    DEFVAL { 0 }
                    ::= { integerObjects 189 }

        -- 1.3.6.1.4.1.9839.2.1.3.190
        mem-alarm-data-from-304-to-319 OBJECT-TYPE
                    SYNTAX Integer32 (-32768..32767)
                    UNITS "N/A"
                    MAX-ACCESS read-only
                    STATUS current
                    DESCRIPTION "Alarm data from 304 to 319 (Bit0 = AL304, Bit15 = AL319)"
                    DEFVAL { 0 }
                    ::= { integerObjects 190 }

        -- 1.3.6.1.4.1.9839.2.1.3.191
        cooling-req-0-1000 OBJECT-TYPE
                    SYNTAX Integer32 (0..1000)
                    UNITS "N/A"
                    MAX-ACCESS read-only
                    STATUS current
                    DESCRIPTION "Cooling request 0-1000"
                    DEFVAL { 0 }
                    ::= { integerObjects 191 }

        -- 1.3.6.1.4.1.9839.2.1.3.192
        heating-req-0-1000 OBJECT-TYPE
                    SYNTAX Integer32 (0..1000)
                    UNITS "N/A"
                    MAX-ACCESS read-only
                    STATUS current
                    DESCRIPTION "Heating request 0-1000"
                    DEFVAL { 0 }
                    ::= { integerObjects 192 }

        -- 1.3.6.1.4.1.9839.2.1.3.193
        emergency-request OBJECT-TYPE
                    SYNTAX Integer32 (0..1000)
                    UNITS "N/A"
                    MAX-ACCESS read-only
                    STATUS current
                    DESCRIPTION "Emergency request 0-1000"
                    DEFVAL { 0 }
                    ::= { integerObjects 193 }

        -- 1.3.6.1.4.1.9839.2.1.3.194
        humidity-req-0-1000 OBJECT-TYPE
                    SYNTAX Integer32 (0..1000)
                    UNITS "N/A"
                    MAX-ACCESS read-only
                    STATUS current
                    DESCRIPTION "Humidity request 0-1000"
                    DEFVAL { 0 }
                    ::= { integerObjects 194 }

        -- 1.3.6.1.4.1.9839.2.1.3.195
        dehumidity-req-0-1000 OBJECT-TYPE
                    SYNTAX Integer32 (0..1000)
                    UNITS "N/A"
                    MAX-ACCESS read-only
                    STATUS current
                    DESCRIPTION "Dehumidity request 0-1000"
                    DEFVAL { 0 }
                    ::= { integerObjects 195 }

        -- 1.3.6.1.4.1.9839.2.1.3.196
        fans-request-1 OBJECT-TYPE
                    SYNTAX Integer32 (0..1000)
                    UNITS "N/A"
                    MAX-ACCESS read-only
                    STATUS current
                    DESCRIPTION "Fans request 1"
                    DEFVAL { 0 }
                    ::= { integerObjects 196 }

        -- 1.3.6.1.4.1.9839.2.1.3.197
        fans-request-2 OBJECT-TYPE
                    SYNTAX Integer32 (0..1000)
                    UNITS "N/A"
                    MAX-ACCESS read-only
                    STATUS current
                    DESCRIPTION "Fans request 2"
                    DEFVAL { 0 }
                    ::= { integerObjects 197 }

        -- 1.3.6.1.4.1.9839.2.1.3.198
        fans-request-3 OBJECT-TYPE
                    SYNTAX Integer32 (0..1000)
                    UNITS "N/A"
                    MAX-ACCESS read-only
                    STATUS current
                    DESCRIPTION "Fans request 3"
                    DEFVAL { 0 }
                    ::= { integerObjects 198 }

        -- 1.3.6.1.4.1.9839.2.1.3.199
        fans-speed-1 OBJECT-TYPE
                    SYNTAX Integer32 (0..1000)
                    UNITS "N/A"
                    MAX-ACCESS read-only
                    STATUS current
                    DESCRIPTION "Fans speed 1 (0-1000)"
                    DEFVAL { 0 }
                    ::= { integerObjects 199 }

        -- 1.3.6.1.4.1.9839.2.1.3.200
        fans-speed-2 OBJECT-TYPE
                    SYNTAX Integer32 (0..1000)
                    UNITS "N/A"
                    MAX-ACCESS read-only
                    STATUS current
                    DESCRIPTION "Fans speed 2 (0-1000)"
                    DEFVAL { 0 }
                    ::= { integerObjects 200 }

        -- 1.3.6.1.4.1.9839.2.1.3.201
        fans-speed-3 OBJECT-TYPE
                    SYNTAX Integer32 (0..1000)
                    UNITS "N/A"
                    MAX-ACCESS read-only
                    STATUS current
                    DESCRIPTION "Fans speed 3 (0-1000)"
                    DEFVAL { 0 }
                    ::= { integerObjects 201 }

        -- 1.3.6.1.4.1.9839.2.1.3.202
        airflow-setpoint-active OBJECT-TYPE
                    SYNTAX Integer32 (-32768..32767)
                    UNITS "N/A"
                    MAX-ACCESS read-only
                    STATUS current
                    DESCRIPTION "Airflow setpoint active ((m3/h)*10)"
                    DEFVAL { 0 }
                    ::= { integerObjects 202 }

        -- 1.3.6.1.4.1.9839.2.1.3.203
        current-air-flow OBJECT-TYPE
                    SYNTAX Integer32 (0..32767)
                    UNITS "N/A"
                    MAX-ACCESS read-only
                    STATUS current
                    DESCRIPTION "Current air flow ((m3/h)*10)"
                    DEFVAL { 0 }
                    ::= { integerObjects 203 }

        -- 1.3.6.1.4.1.9839.2.1.3.204
        valve-1-position-0-1000 OBJECT-TYPE
                    SYNTAX Integer32 (0..1000)
                    UNITS "N/A"
                    MAX-ACCESS read-only
                    STATUS current
                    DESCRIPTION "Valve 1 Position (0 - 1000)"
                    DEFVAL { 0 }
                    ::= { integerObjects 204 }

        -- 1.3.6.1.4.1.9839.2.1.3.205
        valve-2-position-0-1000 OBJECT-TYPE
                    SYNTAX Integer32 (0..1000)
                    UNITS "N/A"
                    MAX-ACCESS read-only
                    STATUS current
                    DESCRIPTION "Valve 2 Position (0 - 1000)"
                    DEFVAL { 0 }
                    ::= { integerObjects 205 }

        -- 1.3.6.1.4.1.9839.2.1.3.206
        water-flow-valve-1 OBJECT-TYPE
                    SYNTAX Integer32 (-32768..32767)
                    UNITS "N/A"
                    MAX-ACCESS read-only
                    STATUS current
                    DESCRIPTION "Water flow valve 1( l/h ) or (m3/h /10)"
                    DEFVAL { 0 }
                    ::= { integerObjects 206 }

        -- 1.3.6.1.4.1.9839.2.1.3.207
        water-flow-valve-2 OBJECT-TYPE
                    SYNTAX Integer32 (-32768..32767)
                    UNITS "N/A"
                    MAX-ACCESS read-only
                    STATUS current
                    DESCRIPTION "Water flow valve 2( l/h ) or (m3/h /10)"
                    DEFVAL { 0 }
                    ::= { integerObjects 207 }

        -- 1.3.6.1.4.1.9839.2.1.3.208
        hot-water-valve-signal OBJECT-TYPE
                    SYNTAX Integer32 (0..1000)
                    UNITS "N/A"
                    MAX-ACCESS read-only
                    STATUS current
                    DESCRIPTION "Hot water valve request (0-1000)"
                    DEFVAL { 0 }
                    ::= { integerObjects 208 }

        -- 1.3.6.1.4.1.9839.2.1.3.209
        feedback-0-1000-inverter-1 OBJECT-TYPE
                    SYNTAX Integer32 (0..1000)
                    UNITS "N/A"
                    MAX-ACCESS read-only
                    STATUS current
                    DESCRIPTION "Feedback 0-1000 inverter 1"
                    DEFVAL { 0 }
                    ::= { integerObjects 209 }

        -- 1.3.6.1.4.1.9839.2.1.3.210
        feedback-0-1000-inverter-2 OBJECT-TYPE
                    SYNTAX Integer32 (0..1000)
                    UNITS "N/A"
                    MAX-ACCESS read-only
                    STATUS current
                    DESCRIPTION "Feedback 0-1000 inverter 2"
                    DEFVAL { 0 }
                    ::= { integerObjects 210 }

        -- 1.3.6.1.4.1.9839.2.1.3.211
        envelope-1-action OBJECT-TYPE
                    SYNTAX Integer32 (0..9)
                    UNITS "N/A"
                    MAX-ACCESS read-only
                    STATUS current
                    DESCRIPTION "Envelope action circuit 1 ( 0= None, 1= Low pressure ratio, 2= Low DP, 3= Max LP, 4= Min LP, 5= Max HP, 6= High discharge temp.)"
                    DEFVAL { 0 }
                    ::= { integerObjects 211 }

        -- 1.3.6.1.4.1.9839.2.1.3.212
        envelope-2-action OBJECT-TYPE
                    SYNTAX Integer32 (0..9)
                    UNITS "N/A"
                    MAX-ACCESS read-only
                    STATUS current
                    DESCRIPTION "Envelope action circuit 2 ( 0= None, 1= Low pressure ratio, 2= Low DP, 3= Max LP, 4= Min LP, 5= Max HP, 6= High discharge temp.)"
                    DEFVAL { 0 }
                    ::= { integerObjects 212 }

        -- 1.3.6.1.4.1.9839.2.1.3.213
        eev-1-position OBJECT-TYPE
                    SYNTAX Integer32 (0..100)
                    UNITS "N/A"
                    MAX-ACCESS read-only
                    STATUS current
                    DESCRIPTION "Electronic expansion valve 1 position (0-100%)"
                    DEFVAL { 0 }
                    ::= { integerObjects 213 }

        -- 1.3.6.1.4.1.9839.2.1.3.214
        eev-2-position OBJECT-TYPE
                    SYNTAX Integer32 (0..100)
                    UNITS "N/A"
                    MAX-ACCESS read-only
                    STATUS current
                    DESCRIPTION "Electronic expansion valve 2 position (0-100%)"
                    DEFVAL { 0 }
                    ::= { integerObjects 214 }

        -- 1.3.6.1.4.1.9839.2.1.3.215
        cond-evap-fan-speed-1 OBJECT-TYPE
                    SYNTAX Integer32 (0..1000)
                    UNITS "N/A"
                    MAX-ACCESS read-only
                    STATUS current
                    DESCRIPTION "Condenser/Evaporator or drycooler fans speed"
                    DEFVAL { 0 }
                    ::= { integerObjects 215 }

        -- 1.3.6.1.4.1.9839.2.1.3.216
        cond-evap-fan-speed-2 OBJECT-TYPE
                    SYNTAX Integer32 (0..1000)
                    UNITS "N/A"
                    MAX-ACCESS read-only
                    STATUS current
                    DESCRIPTION "Condenser/Evaporator fans speed 2"
                    DEFVAL { 0 }
                    ::= { integerObjects 216 }

        -- 1.3.6.1.4.1.9839.2.1.3.217
        hot-gas-precise-c1-signal OBJECT-TYPE
                    SYNTAX Integer32 (0..1000)
                    UNITS "N/A"
                    MAX-ACCESS read-only
                    STATUS current
                    DESCRIPTION "Hot gas precise request circuit 1"
                    DEFVAL { 0 }
                    ::= { integerObjects 217 }

        -- 1.3.6.1.4.1.9839.2.1.3.218
        hot-gas-precise-c2-signal OBJECT-TYPE
                    SYNTAX Integer32 (0..1000)
                    UNITS "N/A"
                    MAX-ACCESS read-only
                    STATUS current
                    DESCRIPTION "Hot gas precise request circuit 2"
                    DEFVAL { 0 }
                    ::= { integerObjects 218 }

        -- 1.3.6.1.4.1.9839.2.1.3.219
        hot-gas-bypass-c1-signal OBJECT-TYPE
                    SYNTAX Integer32 (0..1000)
                    UNITS "N/A"
                    MAX-ACCESS read-only
                    STATUS current
                    DESCRIPTION "Hot gas bypass request circuit 1"
                    DEFVAL { 0 }
                    ::= { integerObjects 219 }

        -- 1.3.6.1.4.1.9839.2.1.3.220
        hot-gas-bypass-c2-signal OBJECT-TYPE
                    SYNTAX Integer32 (0..1000)
                    UNITS "N/A"
                    MAX-ACCESS read-only
                    STATUS current
                    DESCRIPTION "Hot gas bypass request circuit 2"
                    DEFVAL { 0 }
                    ::= { integerObjects 220 }

        -- 1.3.6.1.4.1.9839.2.1.3.221
        heater-icon-request OBJECT-TYPE
                    SYNTAX Integer32 (0..1000)
                    UNITS "N/A"
                    MAX-ACCESS read-only
                    STATUS current
                    DESCRIPTION "Heater production (0-1000)"
                    DEFVAL { 0 }
                    ::= { integerObjects 221 }

        -- 1.3.6.1.4.1.9839.2.1.3.222
        feedback-humidifier-0-1000 OBJECT-TYPE
                    SYNTAX Integer32 (0..1000)
                    UNITS "N/A"
                    MAX-ACCESS read-only
                    STATUS current
                    DESCRIPTION "Humidifier production (0-1000)"
                    DEFVAL { 0 }
                    ::= { integerObjects 222 }

        -- 1.3.6.1.4.1.9839.2.1.3.223
        fan-working-hrs-l OBJECT-TYPE
                    SYNTAX Integer32 (0..9999)
                    UNITS "N/A"
                    MAX-ACCESS read-only
                    STATUS current
                    DESCRIPTION "Fan working hours (h)"
                    DEFVAL { 0 }
                    ::= { integerObjects 223 }

        -- 1.3.6.1.4.1.9839.2.1.3.224
        fan-working-hrs-h OBJECT-TYPE
                    SYNTAX Integer32 (0..9999)
                    UNITS "N/A"
                    MAX-ACCESS read-only
                    STATUS current
                    DESCRIPTION "Fan working hours (h*10000)"
                    DEFVAL { 0 }
                    ::= { integerObjects 224 }

        -- 1.3.6.1.4.1.9839.2.1.3.225
        filter-working-hrs-l OBJECT-TYPE
                    SYNTAX Integer32 (0..9999)
                    UNITS "N/A"
                    MAX-ACCESS read-only
                    STATUS current
                    DESCRIPTION "Filter working hours (h)"
                    DEFVAL { 0 }
                    ::= { integerObjects 225 }

        -- 1.3.6.1.4.1.9839.2.1.3.226
        filter-working-hrs-h OBJECT-TYPE
                    SYNTAX Integer32 (0..9999)
                    UNITS "N/A"
                    MAX-ACCESS read-only
                    STATUS current
                    DESCRIPTION "Filter working hours (h*10000)"
                    DEFVAL { 0 }
                    ::= { integerObjects 226 }

        -- 1.3.6.1.4.1.9839.2.1.3.227
        humidifier-working-hrs-l OBJECT-TYPE
                    SYNTAX Integer32 (0..9999)
                    UNITS "N/A"
                    MAX-ACCESS read-only
                    STATUS current
                    DESCRIPTION "Humidifier working hours (h)"
                    DEFVAL { 0 }
                    ::= { integerObjects 227 }

        -- 1.3.6.1.4.1.9839.2.1.3.228
        humidifier-working-hrs-h OBJECT-TYPE
                    SYNTAX Integer32 (0..9999)
                    UNITS "N/A"
                    MAX-ACCESS read-only
                    STATUS current
                    DESCRIPTION "Humidifier working hours (h*10000)"
                    DEFVAL { 0 }
                    ::= { integerObjects 228 }

        -- 1.3.6.1.4.1.9839.2.1.3.229
        heater-working-hrs-l OBJECT-TYPE
                    SYNTAX Integer32 (0..9999)
                    UNITS "N/A"
                    MAX-ACCESS read-only
                    STATUS current
                    DESCRIPTION "Heater working hours (h)"
                    DEFVAL { 0 }
                    ::= { integerObjects 229 }

        -- 1.3.6.1.4.1.9839.2.1.3.230
        heater-working-hrs-h OBJECT-TYPE
                    SYNTAX Integer32 (0..9999)
                    UNITS "N/A"
                    MAX-ACCESS read-only
                    STATUS current
                    DESCRIPTION "Heater working hours (h*10000)"
                    DEFVAL { 0 }
                    ::= { integerObjects 230 }

        -- 1.3.6.1.4.1.9839.2.1.3.231
        fc-working-hrs-l OBJECT-TYPE
                    SYNTAX Integer32 (0..9999)
                    UNITS "N/A"
                    MAX-ACCESS read-only
                    STATUS current
                    DESCRIPTION "FC working hours (h)"
                    DEFVAL { 0 }
                    ::= { integerObjects 231 }

        -- 1.3.6.1.4.1.9839.2.1.3.232
        fc-working-hrs-h OBJECT-TYPE
                    SYNTAX Integer32 (0..9999)
                    UNITS "N/A"
                    MAX-ACCESS read-only
                    STATUS current
                    DESCRIPTION "FC working hours (h*10000)"
                    DEFVAL { 0 }
                    ::= { integerObjects 232 }

        -- 1.3.6.1.4.1.9839.2.1.3.233
        comp-1-working-hrs-l OBJECT-TYPE
                    SYNTAX Integer32 (0..9999)
                    UNITS "N/A"
                    MAX-ACCESS read-only
                    STATUS current
                    DESCRIPTION "Compressor 1 working hours (h)"
                    DEFVAL { 0 }
                    ::= { integerObjects 233 }

        -- 1.3.6.1.4.1.9839.2.1.3.234
        comp-1-working-hrs-h OBJECT-TYPE
                    SYNTAX Integer32 (0..9999)
                    UNITS "N/A"
                    MAX-ACCESS read-only
                    STATUS current
                    DESCRIPTION "Compressor 1 working hours (h*10000)"
                    DEFVAL { 0 }
                    ::= { integerObjects 234 }

        -- 1.3.6.1.4.1.9839.2.1.3.235
        comp-2-working-hrs-l OBJECT-TYPE
                    SYNTAX Integer32 (0..9999)
                    UNITS "N/A"
                    MAX-ACCESS read-only
                    STATUS current
                    DESCRIPTION "Compressor 2 working hours (h)"
                    DEFVAL { 0 }
                    ::= { integerObjects 235 }

        -- 1.3.6.1.4.1.9839.2.1.3.236
        comp-2-working-hrs-h OBJECT-TYPE
                    SYNTAX Integer32 (0..9999)
                    UNITS "N/A"
                    MAX-ACCESS read-only
                    STATUS current
                    DESCRIPTION "Compressor 2 working hours (h*10000)"
                    DEFVAL { 0 }
                    ::= { integerObjects 236 }

        -- 1.3.6.1.4.1.9839.2.1.3.237
        comp-3-working-hrs-l OBJECT-TYPE
                    SYNTAX Integer32 (0..9999)
                    UNITS "N/A"
                    MAX-ACCESS read-only
                    STATUS current
                    DESCRIPTION "Compressor 3 working hours (h)"
                    DEFVAL { 0 }
                    ::= { integerObjects 237 }

        -- 1.3.6.1.4.1.9839.2.1.3.238
        comp-3-working-hrs-h OBJECT-TYPE
                    SYNTAX Integer32 (0..9999)
                    UNITS "N/A"
                    MAX-ACCESS read-only
                    STATUS current
                    DESCRIPTION "Compressor 3 working hours (h*10000)"
                    DEFVAL { 0 }
                    ::= { integerObjects 238 }

        -- 1.3.6.1.4.1.9839.2.1.3.239
        comp-4-working-hrs-l OBJECT-TYPE
                    SYNTAX Integer32 (0..9999)
                    UNITS "N/A"
                    MAX-ACCESS read-only
                    STATUS current
                    DESCRIPTION "Compressor 4 working hours (h)"
                    DEFVAL { 0 }
                    ::= { integerObjects 239 }

        -- 1.3.6.1.4.1.9839.2.1.3.240
        comp-4-working-hrs-h OBJECT-TYPE
                    SYNTAX Integer32 (0..9999)
                    UNITS "N/A"
                    MAX-ACCESS read-only
                    STATUS current
                    DESCRIPTION "Compressor 4 working hours (h*10000)"
                    DEFVAL { 0 }
                    ::= { integerObjects 240 }

        -- 1.3.6.1.4.1.9839.2.1.3.241
        comp-5-working-hrs-l OBJECT-TYPE
                    SYNTAX Integer32 (0..9999)
                    UNITS "N/A"
                    MAX-ACCESS read-only
                    STATUS current
                    DESCRIPTION "Compressor 5 working hours (h)"
                    DEFVAL { 0 }
                    ::= { integerObjects 241 }

        -- 1.3.6.1.4.1.9839.2.1.3.242
        comp-5-working-hrs-h OBJECT-TYPE
                    SYNTAX Integer32 (0..9999)
                    UNITS "N/A"
                    MAX-ACCESS read-only
                    STATUS current
                    DESCRIPTION "Compressor 5 working hours (h*10000)"
                    DEFVAL { 0 }
                    ::= { integerObjects 242 }

        -- 1.3.6.1.4.1.9839.2.1.3.243
        comp-6-working-hrs-l OBJECT-TYPE
                    SYNTAX Integer32 (0..9999)
                    UNITS "N/A"
                    MAX-ACCESS read-only
                    STATUS current
                    DESCRIPTION "Compressor 6 working hours (h)"
                    DEFVAL { 0 }
                    ::= { integerObjects 243 }

        -- 1.3.6.1.4.1.9839.2.1.3.244
        comp-6-working-hrs-h OBJECT-TYPE
                    SYNTAX Integer32 (0..9999)
                    UNITS "N/A"
                    MAX-ACCESS read-only
                    STATUS current
                    DESCRIPTION "Compressor 6 working hours (h*10000)"
                    DEFVAL { 0 }
                    ::= { integerObjects 244 }

        -- 1.3.6.1.4.1.9839.2.1.3.245
        eev-3-position OBJECT-TYPE
                    SYNTAX Integer32 (0..100)
                    UNITS "N/A"
                    MAX-ACCESS read-only
                    STATUS current
                    DESCRIPTION "Electronic expansion valve 3 position (0-100%)"
                    DEFVAL { 0 }
                    ::= { integerObjects 245 }

        -- 1.3.6.1.4.1.9839.2.1.3.246
        eev-4-position OBJECT-TYPE
                    SYNTAX Integer32 (0..100)
                    UNITS "N/A"
                    MAX-ACCESS read-only
                    STATUS current
                    DESCRIPTION "Electronic expansion valve 4 position (0-100%)"
                    DEFVAL { 0 }
                    ::= { integerObjects 246 }

        -- 1.3.6.1.4.1.9839.2.1.3.250
        force-fan-request OBJECT-TYPE
                    SYNTAX Integer32 (0..9)
                    UNITS "N/A"
                    MAX-ACCESS read-only
                    STATUS current
                    DESCRIPTION "Fan control (0= Local, 1= BMS, 2= pLAN, 3=Disable)"
                    DEFVAL { 0 }
                    ::= { integerObjects 250 }

        -- 1.3.6.1.4.1.9839.2.1.3.251
        force-cooling-request OBJECT-TYPE
                    SYNTAX Integer32 (0..9)
                    UNITS "N/A"
                    MAX-ACCESS read-only
                    STATUS current
                    DESCRIPTION "Cooling request control(0= Local, 1= BMS, 2= pLAN, 3=Disable)"
                    DEFVAL { 0 }
                    ::= { integerObjects 251 }

        -- 1.3.6.1.4.1.9839.2.1.3.252
        force-heating-request OBJECT-TYPE
                    SYNTAX Integer32 (0..9)
                    UNITS "N/A"
                    MAX-ACCESS read-only
                    STATUS current
                    DESCRIPTION "Heating request control (0= Local, 1= BMS, 2= pLAN, 3=Disable)"
                    DEFVAL { 0 }
                    ::= { integerObjects 252 }

        -- 1.3.6.1.4.1.9839.2.1.3.253
        force-humidity-request OBJECT-TYPE
                    SYNTAX Integer32 (0..9)
                    UNITS "N/A"
                    MAX-ACCESS read-only
                    STATUS current
                    DESCRIPTION "Humidifier request control (0= Local, 1= BMS, 2= pLAN, 3=Disable)"
                    DEFVAL { 0 }
                    ::= { integerObjects 253 }

        -- 1.3.6.1.4.1.9839.2.1.3.254
        force-dehumidity-request OBJECT-TYPE
                    SYNTAX Integer32 (0..9)
                    UNITS "N/A"
                    MAX-ACCESS read-only
                    STATUS current
                    DESCRIPTION "Dehumidification request control (0= Local, 1= BMS, 2= pLAN, 3=Disable)"
                    DEFVAL { 0 }
                    ::= { integerObjects 254 }

        -- 1.3.6.1.4.1.9839.2.1.3.260
        output-al-configurable-status OBJECT-TYPE
                    SYNTAX Integer32 (-32768..32767)
                    UNITS "N/A"
                    MAX-ACCESS read-only
                    STATUS current
                    DESCRIPTION "Output alarms configurable status"
                    DEFVAL { 0 }
                    ::= { integerObjects 260 }

        -- 1.3.6.1.4.1.9839.2.1.3.261
        compressor-status OBJECT-TYPE
                    SYNTAX Integer32 (-32768..32767)
                    UNITS "N/A"
                    MAX-ACCESS read-only
                    STATUS current
                    DESCRIPTION "Compressor status"
                    DEFVAL { 0 }
                    ::= { integerObjects 261 }

        -- 1.3.6.1.4.1.9839.2.1.3.270
        fan-total-power OBJECT-TYPE
                    SYNTAX Integer32 (-32768..32767)
                    UNITS "N/A"
                    MAX-ACCESS read-only
                    STATUS current
                    DESCRIPTION "Total power user fans"
                    DEFVAL { 0 }
                    ::= { integerObjects 270 }


        -- 1.3.6.1.4.1.9839.2.1.3.300
        history-alarm-present OBJECT-TYPE
                    SYNTAX Integer32 (-32768..32767)
                    UNITS "N/A"
                    MAX-ACCESS read-only
                    STATUS current
                    DESCRIPTION "History alarm present (Bit0= History alarm 1 present.......Bit9= History alarm 10 present)"
                    DEFVAL { 0 }
                    ::= { integerObjects 300 }

        -- 1.3.6.1.4.1.9839.2.1.3.301
        history-al-1-hh-mm OBJECT-TYPE
                    SYNTAX Integer32 (0..32767)
                    UNITS "N/A"
                    MAX-ACCESS read-only
                    STATUS current
                    DESCRIPTION "History alarm 1 ( HH : MM )"
                    DEFVAL { 0 }
                    ::= { integerObjects 301 }

        -- 1.3.6.1.4.1.9839.2.1.3.302
        history-al-2-hh-mm OBJECT-TYPE
                    SYNTAX Integer32 (0..32767)
                    UNITS "N/A"
                    MAX-ACCESS read-only
                    STATUS current
                    DESCRIPTION "History alarm 2 ( HH : MM )"
                    DEFVAL { 0 }
                    ::= { integerObjects 302 }

        -- 1.3.6.1.4.1.9839.2.1.3.303
        history-al-3-hh-mm OBJECT-TYPE
                    SYNTAX Integer32 (0..32767)
                    UNITS "N/A"
                    MAX-ACCESS read-only
                    STATUS current
                    DESCRIPTION "History alarm 3 ( HH : MM )"
                    DEFVAL { 0 }
                    ::= { integerObjects 303 }

        -- 1.3.6.1.4.1.9839.2.1.3.304
        history-al-4-hh-mm OBJECT-TYPE
                    SYNTAX Integer32 (0..32767)
                    UNITS "N/A"
                    MAX-ACCESS read-only
                    STATUS current
                    DESCRIPTION "History alarm 4 ( HH : MM )"
                    DEFVAL { 0 }
                    ::= { integerObjects 304 }

        -- 1.3.6.1.4.1.9839.2.1.3.305
        history-al-5-hh-mm OBJECT-TYPE
                    SYNTAX Integer32 (0..32767)
                    UNITS "N/A"
                    MAX-ACCESS read-only
                    STATUS current
                    DESCRIPTION "History alarm 5 ( HH : MM )"
                    DEFVAL { 0 }
                    ::= { integerObjects 305 }

        -- 1.3.6.1.4.1.9839.2.1.3.306
        history-al-6-hh-mm OBJECT-TYPE
                    SYNTAX Integer32 (0..32767)
                    UNITS "N/A"
                    MAX-ACCESS read-only
                    STATUS current
                    DESCRIPTION "History alarm 6 ( HH : MM )"
                    DEFVAL { 0 }
                    ::= { integerObjects 306 }

        -- 1.3.6.1.4.1.9839.2.1.3.307
        history-al-7-hh-mm OBJECT-TYPE
                    SYNTAX Integer32 (0..32767)
                    UNITS "N/A"
                    MAX-ACCESS read-only
                    STATUS current
                    DESCRIPTION "History alarm 7 ( HH : MM )"
                    DEFVAL { 0 }
                    ::= { integerObjects 307 }

        -- 1.3.6.1.4.1.9839.2.1.3.308
        history-al-8-hh-mm OBJECT-TYPE
                    SYNTAX Integer32 (0..32767)
                    UNITS "N/A"
                    MAX-ACCESS read-only
                    STATUS current
                    DESCRIPTION "History alarm 8 ( HH : MM )"
                    DEFVAL { 0 }
                    ::= { integerObjects 308 }

        -- 1.3.6.1.4.1.9839.2.1.3.309
        history-al-9-hh-mm OBJECT-TYPE
                    SYNTAX Integer32 (0..32767)
                    UNITS "N/A"
                    MAX-ACCESS read-only
                    STATUS current
                    DESCRIPTION "History alarm 9 ( HH : MM )"
                    DEFVAL { 0 }
                    ::= { integerObjects 309 }

        -- 1.3.6.1.4.1.9839.2.1.3.310
        history-al-10-hh-mm OBJECT-TYPE
                    SYNTAX Integer32 (0..32767)
                    UNITS "N/A"
                    MAX-ACCESS read-only
                    STATUS current
                    DESCRIPTION "History alarm 10 ( HH : MM )"
                    DEFVAL { 0 }
                    ::= { integerObjects 310 }

        -- 1.3.6.1.4.1.9839.2.1.3.311
        history-al-1-dd-mm OBJECT-TYPE
                    SYNTAX Integer32 (0..32767)
                    UNITS "N/A"
                    MAX-ACCESS read-only
                    STATUS current
                    DESCRIPTION "History alarm 1 ( DD / MM )"
                    DEFVAL { 0 }
                    ::= { integerObjects 311 }

        -- 1.3.6.1.4.1.9839.2.1.3.312
        history-al-2-dd-mm OBJECT-TYPE
                    SYNTAX Integer32 (0..32767)
                    UNITS "N/A"
                    MAX-ACCESS read-only
                    STATUS current
                    DESCRIPTION "History alarm 7 ( DD / MM )"
                    DEFVAL { 0 }
                    ::= { integerObjects 312 }

        -- 1.3.6.1.4.1.9839.2.1.3.313
        history-al-3-dd-mm OBJECT-TYPE
                    SYNTAX Integer32 (0..32767)
                    UNITS "N/A"
                    MAX-ACCESS read-only
                    STATUS current
                    DESCRIPTION "History alarm 3 ( DD / MM )"
                    DEFVAL { 0 }
                    ::= { integerObjects 313 }

        -- 1.3.6.1.4.1.9839.2.1.3.314
        history-al-4-dd-mm OBJECT-TYPE
                    SYNTAX Integer32 (0..32767)
                    UNITS "N/A"
                    MAX-ACCESS read-only
                    STATUS current
                    DESCRIPTION "History alarm 4 ( DD / MM )"
                    DEFVAL { 0 }
                    ::= { integerObjects 314 }

        -- 1.3.6.1.4.1.9839.2.1.3.315
        history-al-5-dd-mm OBJECT-TYPE
                    SYNTAX Integer32 (0..32767)
                    UNITS "N/A"
                    MAX-ACCESS read-only
                    STATUS current
                    DESCRIPTION "History alarm 5 ( DD / MM )"
                    DEFVAL { 0 }
                    ::= { integerObjects 315 }

        -- 1.3.6.1.4.1.9839.2.1.3.316
        history-al-6-dd-mm OBJECT-TYPE
                    SYNTAX Integer32 (0..32767)
                    UNITS "N/A"
                    MAX-ACCESS read-only
                    STATUS current
                    DESCRIPTION "History alarm 6 ( DD / MM )"
                    DEFVAL { 0 }
                    ::= { integerObjects 316 }

        -- 1.3.6.1.4.1.9839.2.1.3.317
        history-al-7-dd-mm OBJECT-TYPE
                    SYNTAX Integer32 (0..32767)
                    UNITS "N/A"
                    MAX-ACCESS read-only
                    STATUS current
                    DESCRIPTION "History alarm 7 ( DD / MM )"
                    DEFVAL { 0 }
                    ::= { integerObjects 317 }

        -- 1.3.6.1.4.1.9839.2.1.3.318
        history-al-8-dd-mm OBJECT-TYPE
                    SYNTAX Integer32 (0..32767)
                    UNITS "N/A"
                    MAX-ACCESS read-only
                    STATUS current
                    DESCRIPTION "History alarm 8 ( DD / MM )"
                    DEFVAL { 0 }
                    ::= { integerObjects 318 }

        -- 1.3.6.1.4.1.9839.2.1.3.319
        history-al-9-dd-mm OBJECT-TYPE
                    SYNTAX Integer32 (0..32767)
                    UNITS "N/A"
                    MAX-ACCESS read-only
                    STATUS current
                    DESCRIPTION "History alarm 9 ( DD / MM )"
                    DEFVAL { 0 }
                    ::= { integerObjects 319 }

        -- 1.3.6.1.4.1.9839.2.1.3.320
        history-al-10-dd-mm OBJECT-TYPE
                    SYNTAX Integer32 (0..32767)
                    UNITS "N/A"
                    MAX-ACCESS read-only
                    STATUS current
                    DESCRIPTION "History alarm 10 ( DD / MM )"
                    DEFVAL { 0 }
                    ::= { integerObjects 320 }

        -- 1.3.6.1.4.1.9839.2.1.3.321
        history-al-1-yy-code OBJECT-TYPE
                    SYNTAX Integer32 (0..32767)
                    UNITS "N/A"
                    MAX-ACCESS read-only
                    STATUS current
                    DESCRIPTION "History alarm 1 ( YY - CODE )"
                    DEFVAL { 0 }
                    ::= { integerObjects 321 }

        -- 1.3.6.1.4.1.9839.2.1.3.322
        history-al-2-yy-code OBJECT-TYPE
                    SYNTAX Integer32 (0..32767)
                    UNITS "N/A"
                    MAX-ACCESS read-only
                    STATUS current
                    DESCRIPTION "History alarm 2 ( YY - CODE )"
                    DEFVAL { 0 }
                    ::= { integerObjects 322 }

        -- 1.3.6.1.4.1.9839.2.1.3.323
        history-al-3-yy-code OBJECT-TYPE
                    SYNTAX Integer32 (0..32767)
                    UNITS "N/A"
                    MAX-ACCESS read-only
                    STATUS current
                    DESCRIPTION "History alarm 3 ( YY - CODE )"
                    DEFVAL { 0 }
                    ::= { integerObjects 323 }

        -- 1.3.6.1.4.1.9839.2.1.3.324
        history-al-4-yy-code OBJECT-TYPE
                    SYNTAX Integer32 (0..32767)
                    UNITS "N/A"
                    MAX-ACCESS read-only
                    STATUS current
                    DESCRIPTION "History alarm 4 ( YY - CODE )"
                    DEFVAL { 0 }
                    ::= { integerObjects 324 }

        -- 1.3.6.1.4.1.9839.2.1.3.325
        history-al-5-yy-code OBJECT-TYPE
                    SYNTAX Integer32 (0..32767)
                    UNITS "N/A"
                    MAX-ACCESS read-only
                    STATUS current
                    DESCRIPTION "History alarm 5 ( YY - CODE )"
                    DEFVAL { 0 }
                    ::= { integerObjects 325 }

        -- 1.3.6.1.4.1.9839.2.1.3.326
        history-al-6-yy-code OBJECT-TYPE
                    SYNTAX Integer32 (0..32767)
                    UNITS "N/A"
                    MAX-ACCESS read-only
                    STATUS current
                    DESCRIPTION "History alarm 6 ( YY - CODE )"
                    DEFVAL { 0 }
                    ::= { integerObjects 326 }

        -- 1.3.6.1.4.1.9839.2.1.3.327
        history-al-7-yy-code OBJECT-TYPE
                    SYNTAX Integer32 (0..32767)
                    UNITS "N/A"
                    MAX-ACCESS read-only
                    STATUS current
                    DESCRIPTION "History alarm 7 ( YY - CODE )"
                    DEFVAL { 0 }
                    ::= { integerObjects 327 }

        -- 1.3.6.1.4.1.9839.2.1.3.328
        history-al-8-yy-code OBJECT-TYPE
                    SYNTAX Integer32 (0..32767)
                    UNITS "N/A"
                    MAX-ACCESS read-only
                    STATUS current
                    DESCRIPTION "History alarm 8 ( YY - CODE )"
                    DEFVAL { 0 }
                    ::= { integerObjects 328 }

        -- 1.3.6.1.4.1.9839.2.1.3.329
        history-al-9-yy-code OBJECT-TYPE
                    SYNTAX Integer32 (0..32767)
                    UNITS "N/A"
                    MAX-ACCESS read-only
                    STATUS current
                    DESCRIPTION "History alarm 9 ( YY - CODE )"
                    DEFVAL { 0 }
                    ::= { integerObjects 329 }

        -- 1.3.6.1.4.1.9839.2.1.3.330
        history-al-10-yy-code OBJECT-TYPE
                    SYNTAX Integer32 (0..32767)
                    UNITS "N/A"
                    MAX-ACCESS read-only
                    STATUS current
                    DESCRIPTION "History alarm 10 ( YY - CODE )"
                    DEFVAL { 0 }
                    ::= { integerObjects 330 }

        -- 1.3.6.1.4.1.9839.2.1.3.350
        modbus-fan-totalizer-l OBJECT-TYPE
                    SYNTAX Integer32 (0..32767)
                    UNITS "N/A"
                    MAX-ACCESS read-only
                    STATUS current
                    DESCRIPTION "Electric energy modbus fan (bit 0-15)"
                    DEFVAL { 0 }
                    ::= { integerObjects 350 }

        -- 1.3.6.1.4.1.9839.2.1.3.351
        modbus-fan-totalizer-h OBJECT-TYPE
                    SYNTAX Integer32 (0..32767)
                    UNITS "N/A"
                    MAX-ACCESS read-only
                    STATUS current
                    DESCRIPTION "Electric energy modbus fan (bit 16-31)"
                    DEFVAL { 0 }
                    ::= { integerObjects 351 }

        -- 1.3.6.1.4.1.9839.2.1.3.352
        water-circuit-1-totalizer-l OBJECT-TYPE
                    SYNTAX Integer32 (0..32767)
                    UNITS "N/A"
                    MAX-ACCESS read-only
                    STATUS current
                    DESCRIPTION "Thermal energy water circuit 1 (bit 0-15)"
                    DEFVAL { 0 }
                    ::= { integerObjects 352 }

        -- 1.3.6.1.4.1.9839.2.1.3.353
        water-circuit-1-totalizer-h OBJECT-TYPE
                    SYNTAX Integer32 (0..32767)
                    UNITS "N/A"
                    MAX-ACCESS read-only
                    STATUS current
                    DESCRIPTION "Thermal energy water circuit 1 (bit 16-31)"
                    DEFVAL { 0 }
                    ::= { integerObjects 353 }

        -- 1.3.6.1.4.1.9839.2.1.3.354
        water-circuit-2-totalizer-l OBJECT-TYPE
                    SYNTAX Integer32 (0..32767)
                    UNITS "N/A"
                    MAX-ACCESS read-only
                    STATUS current
                    DESCRIPTION "Thermal energy water circuit 2 (bit 0-15)"
                    DEFVAL { 0 }
                    ::= { integerObjects 354 }

        -- 1.3.6.1.4.1.9839.2.1.3.355
        water-circuit-2-totalizer-h OBJECT-TYPE
                    SYNTAX Integer32 (0..32767)
                    UNITS "N/A"
                    MAX-ACCESS read-only
                    STATUS current
                    DESCRIPTION "Thermal energy water circuit 2 (bit 16-31)"
                    DEFVAL { 0 }
                    ::= { integerObjects 355 }
                    
        -- 1.3.6.1.4.1.9839.2.1.3.356
        ener-3ph-l-seneca-s203ta OBJECT-TYPE
                    SYNTAX Integer32 (0..32767)
                    UNITS "N/A"
                    MAX-ACCESS read-only
                    STATUS current
                    DESCRIPTION "Electrical energy  (bit 0-15)"
                    DEFVAL { 0 }
                    ::= { integerObjects 356 }
                    
        -- 1.3.6.1.4.1.9839.2.1.3.357
        ener-3ph-h-seneca-s203ta OBJECT-TYPE
                    SYNTAX Integer32 (0..32767)
                    UNITS "N/A"
                    MAX-ACCESS read-only
                    STATUS current
                    DESCRIPTION "Electrical energy  (bit 16-31)"
                    DEFVAL { 0 }
                    ::= { integerObjects 357 }
	
	END

--
-- CAREL-cdz.MIB
--
