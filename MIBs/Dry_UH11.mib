-- ----------------------------------------------------------------------------
--          UPS Ambient Signal Adaptor and UH11 UPS MIB
--                  DRY-UH11-MIB
--
--
--      Copyright (c) 1999-2000 HUAWEI ELECTRIC TECH. CO., LTD, SHENZHEN.
--      Copyright (c) 2000-2001 AVANSYS POWER CO., LTD., SHENZHEN.
--      Copyright (c) 2001-2006 EMERSON NETWORK POWER CO., LTD.
--      All rights reserved.
--
--      Created    by: Su Chunlei
--      Created  date: 2006-05-17
--      Modified Date: 
-- ----------------------------------------------------------------------------

DRY-UH11-MIB DEFINITIONS ::= BEGIN

IMPORTS
    OBJECT-TYPE
        FROM RFC-1212

    TRAP-TYPE 
        FROM RFC-1215

    enterprises, IpAddress
        FROM RFC1155-SMI;

    DisplayString ::= OCTET STRING                  


    -- ------------------------------------------------------------------------
    -- the location of UPS group in ENP enterprise.
    -- ------------------------------------------------------------------------ 
    emersonNetworkPower     OBJECT IDENTIFIER ::= { enterprises 13400 }
    products                OBJECT IDENTIFIER ::= { emersonNetworkPower 2 }
    iTrustUps               OBJECT IDENTIFIER ::= { products 1 }
    
    -- ------------------------------------------------------------------------
    -- the main objects about UPS
    -- ------------------------------------------------------------------------ 
    upsAgent        OBJECT IDENTIFIER ::= { iTrustUps 1 }
    upsCommon       OBJECT IDENTIFIER ::= { iTrustUps 2 }
    upsSpecial      OBJECT IDENTIFIER ::= { iTrustUps 3 }
    upsAlarm        OBJECT IDENTIFIER ::= { iTrustUps 4 }

    upsIdent        OBJECT IDENTIFIER ::= { upsCommon 1 }
    
    iTrustUH11      OBJECT IDENTIFIER ::= { upsSpecial 1 }
    iTrustUH31      OBJECT IDENTIFIER ::= { upsSpecial 2 }
    iTrustUL33      OBJECT IDENTIFIER ::= { upsSpecial 3 }

    -- ------------------------------------------------------------------------
    -- the common objects about a  UPS
    -- ------------------------------------------------------------------------ 
    upsBaseIdent    OBJECT IDENTIFIER ::=  { upsIdent 1 }
    upsSmartIdent   OBJECT IDENTIFIER ::=  { upsIdent 2 }

    upsBaseAlaram   OBJECT IDENTIFIER ::=  { upsAlarm 1 }
    upsSmartAlarm   OBJECT IDENTIFIER ::=  { upsAlarm 2 }

    -- ------------------------------------------------------------------------
    -- the detail objects about a special UPS
    -- ------------------------------------------------------------------------ 
    upsBattery      OBJECT IDENTIFIER ::=  { iTrustUH11 2 }
    upsInput        OBJECT IDENTIFIER ::=  { iTrustUH11 3 }
    upsOutput       OBJECT IDENTIFIER ::=  { iTrustUH11 4 }
    upsStatus       OBJECT IDENTIFIER ::=  { iTrustUH11 5 }
    upsTest         OBJECT IDENTIFIER ::=  { iTrustUH11 6 }
    upsControl      OBJECT IDENTIFIER ::=  { iTrustUH11 7 }
    upsConfig       OBJECT IDENTIFIER ::=  { iTrustUH11 8 }
    dryContactor    OBJECT IDENTIFIER ::=  { iTrustUH11 9 }

    upsBaseBattery  OBJECT IDENTIFIER ::=  { upsBattery 1 }
    upsSmartBattery OBJECT IDENTIFIER ::=  { upsBattery 2 }
    
    upsBaseInput    OBJECT IDENTIFIER ::=  { upsInput 1 }
    upsSmartInput   OBJECT IDENTIFIER ::=  { upsInput 2 }
    
    upsBaseOutput   OBJECT IDENTIFIER ::=  { upsOutput 1 }
    upsSmartOutput  OBJECT IDENTIFIER ::=  { upsOutput 2 }

    upsBaseStatus   OBJECT IDENTIFIER ::=  { upsStatus 1 }
    upsSmartStatus  OBJECT IDENTIFIER ::=  { upsStatus 2 }
    
    upsBaseControl  OBJECT IDENTIFIER ::=  { upsControl 1 }
    upsSmartControl OBJECT IDENTIFIER ::=  { upsControl 2 }
    
    upsBaseTest     OBJECT IDENTIFIER ::=  { upsTest 1 }
    upsSmartTest    OBJECT IDENTIFIER ::=  { upsTest 2 }
    
    upsBaseConfig   OBJECT IDENTIFIER ::=  { upsConfig 1 }
    upsSmartConfig  OBJECT IDENTIFIER ::=  { upsConfig 2 }
    upsPlanConfig   OBJECT IDENTIFIER ::=  { upsConfig 3 }
    
    dryBaseStatus   OBJECT IDENTIFIER ::=  { dryContactor 1 }
    dryBaseInput    OBJECT IDENTIFIER ::=  { dryContactor 2 }
    drySmartInput   OBJECT IDENTIFIER ::=  { dryContactor 3 }
    dryBaseOutput   OBJECT IDENTIFIER ::=  { dryContactor 4 }


    -- ------------------------------------------------------------------------
    -- 1. upsAgent group
    -- ------------------------------------------------------------------------ 
   
    agentRevision OBJECT-TYPE
        SYNTAX INTEGER
        ACCESS read-only
        STATUS mandatory
        DESCRIPTION
            "The software version of the agent."
        ::= { upsAgent 1 }

    agentManagersNum OBJECT-TYPE
        SYNTAX INTEGER
        ACCESS read-only
        STATUS mandatory
        DESCRIPTION
           "The number of managers that can manage the agent. "
        ::= { upsAgent 2 }
 
    agentManagersTable OBJECT-TYPE
        SYNTAX SEQUENCE OF AgentManagersEntry
        ACCESS not-accessible
        STATUS mandatory
        DESCRIPTION
            "A list of managers of the agent.  The number of
            entries is given by the value of agentManagersNum."
        ::= { upsAgent 3 }
 
    agentManagersEntry OBJECT-TYPE
        SYNTAX AgentManagersEntry
        ACCESS not-accessible
        STATUS mandatory
        DESCRIPTION
            "The managers of the agent."
        INDEX  { managerIndex}
        ::= { agentManagersTable 1 }
 
    AgentManagersEntry ::=
        SEQUENCE {
            managerIndex
                INTEGER,
            managerAddr
                IpAddress,
            publicCommunityString
                 DisplayString,
            privateCommunityString
                 DisplayString,
            managerPrivilege
                INTEGER,
            acceptTrapLevel
                INTEGER,
            managerAccept
                INTEGER
        }
 
    managerIndex OBJECT-TYPE
        SYNTAX INTEGER
        ACCESS read-only
        STATUS mandatory
        DESCRIPTION
            "The index of the managers entry."
        ::= { agentManagersEntry 1 }
    
    managerAddr OBJECT-TYPE
        SYNTAX IpAddress
        ACCESS read-write
        STATUS mandatory
        DESCRIPTION
            "The IP address of the manager."
        ::= { agentManagersEntry 2 }

    publicCommunityString OBJECT-TYPE
        SYNTAX DisplayString
        ACCESS read-write
        STATUS mandatory
        DESCRIPTION
           "The public community name to use in the query request."
        ::= { agentManagersEntry 3 }
 
    privateCommunityString OBJECT-TYPE
        SYNTAX DisplayString
        ACCESS read-write
        STATUS mandatory
        DESCRIPTION
           "The private community name to use int the control request."
        ::= { agentManagersEntry 4 }
 
    managerPrivilege OBJECT-TYPE
        SYNTAX INTEGER {
            forbidden(0),
            query(1),
            control(2),
            administrator(3)
       }
        ACCESS read-write
        STATUS mandatory
        DESCRIPTION
            "The privilege of the manager to access the agent.
            setting forbidden(0) indicates the manager have no any privilege to access the agent,
            setting query(1) indicates the manager can GET information from agent only,
            setting control(2) indicates the manager can GET information from agent and 
            send control command to the agent.
            setting administrator(3) indicates the manager has all management privilege
            including set or modify this managers table."
       ::= { agentManagersEntry 5 }

    acceptTrapLevel OBJECT-TYPE
         SYNTAX INTEGER {
            information(1),
            warning(2),
            severe(3),
            noTraps(4)
        }
        ACCESS read-write
        STATUS mandatory
        DESCRIPTION
            "The severity threshold of traps to send to the manager.
            traps are labeled in severity as informational(1), warning(2),
            severe(3).  Only traps of equal or greater severity than
            this value are sent to the manager. setting noTraps(4) indicates
            agent do not send any traps to the manager."
       ::= { agentManagersEntry 6 }

    managerAccept OBJECT-TYPE
        SYNTAX INTEGER   {
            view(0),
            new(1),
            modify(2),
            delete(3)
        }
        ACCESS read-write
        STATUS mandatory
        DESCRIPTION
           "An entry will be added if new(1), will be modified if modify(2), 
           and will be removed if delete(3)."
        ::= { agentManagersEntry 7 }

    -- ------------------------------------------------------------------------
    -- 2. iTrustUH11 group
    -- ------------------------------------------------------------------------ 

    -- ------------------------------------------------------------------------
    -- 2.1 upsIdent group
    -- ------------------------------------------------------------------------ 

    -- ------------------------------------------------------------------------ 
    -- 2.1.1 the upsBaseIdent group
    -- ------------------------------------------------------------------------ 

    upsBaseIdentModel OBJECT-TYPE
        SYNTAX DisplayString
        ACCESS read-only
        STATUS mandatory
        DESCRIPTION
            "The UPS model name (e.g. 'iTrust UPS 6KVA')."
        ::= { upsBaseIdent 1 }

    upsBaseIdentUpsName OBJECT-TYPE
        SYNTAX DisplayString
        ACCESS read-write
        STATUS mandatory
        DESCRIPTION
            "An 8 byte ID string identifying the UPS.  This object
             can be set by the administrator."
        ::= { upsBaseIdent 2 }
                
    
    -- ------------------------------------------------------------------------ 
    -- 2.1.2 the upsSmartIdent group
    -- ------------------------------------------------------------------------ 
            
    upsSmartIdentFirmwareRevision OBJECT-TYPE
        SYNTAX DisplayString
        ACCESS read-only
        STATUS mandatory
        DESCRIPTION
            "The firmware revision of the UPS system."
        ::= { upsSmartIdent 1 }
        
    -- !!!!!!!!!!!!!!!!!!!!!!!!!!!!!!!!!!!!!!!!!!!!!!!!
    -- IMPORTANT: iTrust UPS does NOT support manu-date and product-serial
    --            to read these variables will get 'reserved'
    upsSmartIdentDateOfManufacture OBJECT-TYPE
        SYNTAX DisplayString
       ACCESS read-only
        STATUS mandatory
        DESCRIPTION
           "The date when the UPS was manufactured in yyyy/mm/dd format."
        ::= { upsSmartIdent 2 }

    upsSmartIdentUpsSerialNumber OBJECT-TYPE
         SYNTAX DisplayString
        ACCESS read-only
         STATUS mandatory
         DESCRIPTION
            "An 8-character string identifying the serial number of
              the UPS internal microprocessor.  This number is set at
              the factory.  NOTE: This number does NOT correspond to
             the serial number on the rear of the UPS."
        ::= { upsSmartIdent 3 }
    
    upsSmartIdentUpsFactory OBJECT-TYPE
        SYNTAX DisplayString
        ACCESS read-only
        STATUS mandatory
        DESCRIPTION
            "The name of the factory that manufactured this UPS."
        ::= { upsSmartIdent 4 }
    
    
    -- ------------------------------------------------------------------------ 
    -- 3.1.2. the upsBattery group
    -- ------------------------------------------------------------------------ 

    -- ------------------------------------------------------------------------ 
    -- 3.1.2.1 the upsBaseBattery group
    -- ------------------------------------------------------------------------ 
    upsBaseBatteryStatus OBJECT-TYPE
       SYNTAX INTEGER  {
            unknown(1),
            batteryNormal(2),
            batteryLow(3),
            batteryHigh(4), 
            batteryFault(5), 
            batteryForewarning(6)
        }
        ACCESS read-only
        STATUS mandatory
        DESCRIPTION
            "The status of the batteries. A batteryLow(3)
             value indicates the UPS will be unable to sustain the
             current load, and its services will be lost if power is
             not restored.  The amount of run time in reserve at the
             time of low battery can be configured by the
             upsSmartConfigLowBatteryRunTime. A batteryFault(5) indicates
             the battery has some faults, batteryForewarning(6) indicates
             the battery is forewarning."
        ::= { upsBaseBattery 1 }

    -- ------------------------------------------------------------------------ 
    -- 3.1.2.2 the upsSmartBattery group
    ------------------------------------------------------------------------ 
    upsSmartBatteryCapacity OBJECT-TYPE
        SYNTAX INTEGER
        ACCESS read-only
        STATUS mandatory
        DESCRIPTION
            "The remaining battery capacity expressed in
             percent of full capacity."
    ::= { upsSmartBattery 1 }

    upsSmartBatteryVoltage OBJECT-TYPE
        SYNTAX INTEGER
        ACCESS read-only
        STATUS mandatory
        DESCRIPTION
            "The current voltage of battery expressed in 1/10 VDC."
        ::= { upsSmartBattery 2 }
    
    upsSmartBatteryTemperature OBJECT-TYPE
        SYNTAX INTEGER
        ACCESS read-only
        STATUS mandatory
        DESCRIPTION
            "The current internal UPS temperature expressed in tenths of
             a Celsius degree."
        ::= { upsSmartBattery 4 }
    
    upsSmartBatteryDiagnosticStatus OBJECT-TYPE
        SYNTAX INTEGER  {
            unknown(1),
            notTesting(2),
            testing(3),
            testFail(4)
        }
        ACCESS read-only
        STATUS mandatory
        DESCRIPTION
            "The status of battery diagnostics, testing(2) indicates that the
            battery diagnostics is in progress."
        ::= { upsSmartBattery 5 }

    upsSmartBatteryChargingMode OBJECT-TYPE
        SYNTAX INTEGER  {
            unknown(1),
            uncharging(2),
            floatingCharging(3),
            equalCharging(4)
        }
        ACCESS read-only
        STATUS mandatory
        DESCRIPTION
            "The status of battery charge, uncharging(2), floatingCharging(3),
            equalCharging(4)."
        ::= { upsSmartBattery 6 }
  
    -- ------------------------------------------------------------------------ 
    -- 3.1.3. the upsInout group
    -- ------------------------------------------------------------------------ 

    -- ------------------------------------------------------------------------ 
    -- 3.1.3.1 the upsBaseInput group
    -- ------------------------------------------------------------------------ 
    
    -- ------------------------------------------------------------------------ 
    -- 3.1.3.2 the upsSmartInput group
    -- ------------------------------------------------------------------------ 

    upsSmartInputLineVoltage OBJECT-TYPE
        SYNTAX INTEGER
        ACCESS read-only
        STATUS mandatory
        DESCRIPTION
            "The current utility line voltage in 1/10 VAC."
        ::= { upsSmartInput 1 }

    upsSmartInputFrequency OBJECT-TYPE
        SYNTAX INTEGER
        ACCESS read-only
        STATUS mandatory
        DESCRIPTION
            "The current input frequency to the UPS system in 1/10 Hz."
        ::= { upsSmartInput 6 }

    -- ------------------------------------------------------------------------ 
    -- 3.1.4. the upsOutput group
    -- ------------------------------------------------------------------------ 

    -- ------------------------------------------------------------------------ 
    -- 3.1.4.1 the upsBaseOutput group
    -- ------------------------------------------------------------------------ 
    upsBaseOutputStatus OBJECT-TYPE
        SYNTAX INTEGER  {
            unknown(1),
            off(2),
            onLine(3),
            onBattery(4),
            onBypass(5)
        }
        ACCESS read-only
        STATUS mandatory
        DESCRIPTION
            "The current state of the UPS.  If the UPS is unable
             to determine the state of the UPS this variable is set
             to unknown(1)."
        ::= { upsBaseOutput 1 }
    

    -- ------------------------------------------------------------------------ 
    -- 3.1.4.2 the upsSmartOutput group
    ------------------------------------------------------------------------ 
    upsSmartOutputVoltage OBJECT-TYPE
        SYNTAX INTEGER
        ACCESS read-only
        STATUS mandatory
        DESCRIPTION
            "The output voltage of the UPS system in 1/10 VAC."
        ::= { upsSmartOutput 1 }

    upsSmartOutputFrequency OBJECT-TYPE
        SYNTAX INTEGER
        ACCESS read-only
        STATUS mandatory
        DESCRIPTION
            "The current output frequency of the UPS system in 1/10 Hz."
    ::= { upsSmartOutput 2 }
    
    upsSmartOutputLoad OBJECT-TYPE
        SYNTAX INTEGER
        ACCESS read-only
        STATUS mandatory
        DESCRIPTION
            "The current UPS load expressed in percent of rated capacity."
        ::= { upsSmartOutput 3 }

    upsSmartOutputCurrent OBJECT-TYPE
        SYNTAX INTEGER
        ACCESS read-only
        STATUS mandatory
        DESCRIPTION
            "The current ouput current of the UPS system in 1/10 AAC."
        ::= { upsSmartOutput 4 }

    -- --------------------------------------------------------------------- 
    -- 3.1.5. the upsStatus group
    ------------------------------------------------------------------------ 
    -- ---------------------------------------------------------------------
    -- 3.1.5.1 the upsBaseStatus group
    ------------------------------------------------------------------------ 
    upsBaseStatusCommunication OBJECT-TYPE
        SYNTAX INTEGER {
            unknown(1),
            ok(2),
            lostCommunication(3),
            notEstablished(4)
        }
        ACCESS read-only
        STATUS mandatory
        DESCRIPTION
            "The status of communication to UPS. lostCommunication(3) indicates
            some errors occurred between UPS and the UPS Ambient Signal Adaptor. 
            notEstablished(4) indicates the UPS Ambient Signal Adaptor can not connect 
            to UPS, maybe error on communication port or port settings error."
        ::= { upsBaseStatus 1 }
    
    
    upsBaseStatusUpsStatus OBJECT-TYPE
        SYNTAX INTEGER {
            unknown(1),
            on(2),
            off(3),
            shutdowning(4)
        }
        ACCESS read-only
        STATUS mandatory
        DESCRIPTION
            "The ON/OFF status of UPS. shutdowning(4) indicates the UPS 
             is in shutdowning progress."
        ::= { upsBaseStatus 2 }


    -- ---------------------------------------------------------------------
    -- 3.1.5.2 the upsSmartStatus group
    ------------------------------------------------------------------------ 

    upsSmartStatusInputVoltage OBJECT-TYPE
        SYNTAX INTEGER  {
            unknown(1),
            normal(2),
            blackout(3),
            overMaximumLimit(4),
            brownout(5)
        }
        ACCESS read-only
        STATUS mandatory
        DESCRIPTION
            "The status of input voltage. blackout(3) indicates the input utility is
            fail, overMaximumLimit(4) indicates the input voltage is exceed the allowed 
            maximum value, brownout(5) indicates the voltage of input is between 120 and
            160 volt."
        ::= { upsSmartStatus 1 }

    upsSmartStatusFrequenceSynchronization OBJECT-TYPE
        SYNTAX INTEGER  {
            unknown(1),
            synchronous(2),
            asynchronous(3)
        }
        ACCESS read-only
        STATUS mandatory
        DESCRIPTION
            "The synchronization status between the frequence of input voltage 
            and the output."
        ::= { upsSmartStatus 5 }
    
    upsSmartStatusRectifier OBJECT-TYPE
        SYNTAX INTEGER  {
            unknown(1),
            ok(2),
            fail(3)
        }
        ACCESS read-only
        STATUS mandatory
        DESCRIPTION
            "The state of rectifier."
        ::= { upsSmartStatus 6 }

    upsSmartStatusInverter OBJECT-TYPE
        SYNTAX INTEGER  {
            unknown(1),
            ok(2),
            fail(3)
        }
        ACCESS read-only
        STATUS mandatory
        DESCRIPTION
            "The state of inverter."
        ::= { upsSmartStatus 7 }

    upsSmartStatusBypassVoltage OBJECT-TYPE
        SYNTAX INTEGER  {
            unknown(1),
            normal(2),
            overMinimumLimit(3),
            overMaximumLimit(4)
        }
        ACCESS read-only
        STATUS mandatory
        DESCRIPTION
            "The state of bypass voltage."
        ::= { upsSmartStatus 8 }

    upsSmartStatusCharger OBJECT-TYPE
        SYNTAX INTEGER  {
            unknown(1),
            ok(2),
            fail(3)
        }
        ACCESS read-only
        STATUS mandatory
        DESCRIPTION
            "The state of charger."
        ::= { upsSmartStatus 9 }

    upsSmartStatusUtilityFrequence OBJECT-TYPE
        SYNTAX INTEGER  {
            unknown(1),
            normal(2),
            overLimit(3)
        }
        ACCESS read-only
        STATUS mandatory
        DESCRIPTION
            "The state of the frequence of utility. overLimit(3) indicates the
            frequence is over maximum limit or minimum limit."
        ::= { upsSmartStatus 10 }

    upsSmartStatusOutputLine OBJECT-TYPE
        SYNTAX INTEGER  {
            unknown(1),
            normal(2),
            shortcut(3)
        }
        ACCESS read-only
        STATUS mandatory
        DESCRIPTION
            "The state of output line."
        ::= { upsSmartStatus 11 }

    upsSmartStatusLoad OBJECT-TYPE
        SYNTAX INTEGER  {
            unknown(1),
            normal(2),
            overLoad(3)
        }
        ACCESS read-only
        STATUS mandatory
        DESCRIPTION
            "The state of the current load of UPS."
        ::= { upsSmartStatus 12 }

    upsSmartStatusInternalTemperature OBJECT-TYPE
        SYNTAX INTEGER  {
            unknown(1),
            normal(2),
            overLimit(3)
        }
        ACCESS read-only
        STATUS mandatory
        DESCRIPTION
            "The state of the internal temperature of UPS."
        ::= { upsSmartStatus 13 }

    -- ------------------------------------------------------------------------ 
    -- 3.1.6. the upsTest group
    -- ------------------------------------------------------------------------ 

    -- ------------------------------------------------------------------------ 
    -- 3.1.6.1 the upsBaseTest group
    -- ------------------------------------------------------------------------ 
    
    -- no upsBaseTest variables

    -- ------------------------------------------------------------------------ 
    -- 3.1.6.2 the upsSmartTest group
    -- ------------------------------------------------------------------------ 
    upsSmartTestBatteryDiagnostics OBJECT-TYPE
        SYNTAX INTEGER  {
            noTestDiagnostics(1),
            testDiagnostics(2),
            cancelTestDiagnostics(3)
        }
        ACCESS read-write
        STATUS mandatory
        DESCRIPTION
            "Setting this variable to testDiagnostics(2) causes
             the UPS to perform a diagnostic self test."
        ::= { upsSmartTest 1 }
    
    upsSmartTestIndicators OBJECT-TYPE
         SYNTAX INTEGER {
             noTestIndicators(1),
             testIndicators(2)
        }
        ACCESS read-write
        STATUS mandatory
        DESCRIPTION
            "Setting this variable to testIndicators(2) causes
             the UPS to perform a warning beep test.
                 Setting this value to noTestIndicators(1) has no effect."
        ::= { upsSmartTest 2 }
    
    
--    upsSmartTestSwitchBypass OBJECT-TYPE
--        SYNTAX INTEGER {
--            noPerformBypassTest(1),
--            switchToBypass(2),
--            switchOutOfBypass(3)
--        }
--        ACCESS read-write
--        STATUS mandatory
--        DESCRIPTION 
--            "setting switchToBypass(2) to this variable to 
--             indicate the UPS to switch to bypasss.
--             WARNING: before doing this, please save you document 
--             at fist, and make sure the utility is in ok status."
--        ::= { upsSmartTest 3 }

    -- ------------------------------------------------------------------------ 
    -- 3.1.7. the upsControl group
    -- ------------------------------------------------------------------------ 
    -- 
    -- ------------------------------------------------------------------------ 
    -- 3.1.7.1 the upsBaseControl group
    -- ------------------------------------------------------------------------ 
    
    -- no variables

    -- ------------------------------------------------------------------------ 
    -- 3.1.7.2 the upsSmartControl group
    -- ------------------------------------------------------------------------ 
        
    upsSmartControlTurnOnUps OBJECT-TYPE
        SYNTAX INTEGER  {
            noTurnOnUps(1),
            turnOnUps(2)
        }
        ACCESS read-write
        STATUS mandatory
        DESCRIPTION
            "Setting this variable to turnOnUps(2) to turn on UPS.
             Setting this value to noTurnOnUps(1) has no effect.

             The value noTurnOnUps(1) will always be returned 
             when the variable is read."
        ::= { upsSmartControl 1 }
         
    upsSmartControlUpsOff OBJECT-TYPE
        SYNTAX INTEGER  {
            noTurnUpsOff(1),
            turnUpsOff(2),
            turnUpsDelayOff(3),
            cancelUpsDelayOff(4)
        }
        ACCESS read-write
        STATUS mandatory
        DESCRIPTION
            "Setting this variable to turnUpsOff(2) causes
             the UPS to shut off.  When in this state, the UPS
             will not provide output power regardless of the input
             line state.  The on/off switch on the UPS
             must be toggled for the UPS to return to operation.
             
             setting this variable to turnUpsDelayOff(3) causes
             the UPS to enter to delay-shutdown progresss, the value of 
             delay time is given by the variable upsSmartConfigShutoffDelay.
             
             setting this variable to cancelUpsDelayOff(4) to cancel the
             delay-shutdown progress.
    
             Setting this value to noTurnUpsOff(1) has no
             effect.
    
             The value noTurnUpsOff(1) will always be returned
             when the variable is read."
        ::= { upsSmartControl 2 }
    
    upsSmartControlCancelAlarmBeep OBJECT-TYPE
        SYNTAX INTEGER  {
            noCancelBeep(1),
            cancelAlarmBeep(2)
        }
        ACCESS read-write
        STATUS mandatory
        DESCRIPTION
            "Cancel the current alarm beep while a warning occurred.
    
             Setting this value to noCancelBeep(1) has no
             effect.

             Setting this value to cancelAlarmBeep(2) cause the
             current alarm beep off. 
    
             The value noCancelBeep(1) will always be returned
             when the variable is read."
        ::= { upsSmartControl 3 }

    -- ------------------------------------------------------------------------ 
    -- 3.1.8. the upsConfig group
    -- ------------------------------------------------------------------------ 
    
    -- ------------------------------------------------------------------------ 
    -- 3.1.8.1 the upsBaseConfig group
    -- ------------------------------------------------------------------------ 
    
 
    -- ------------------------------------------------------------------------ 
    -- 3.1.8.2 the upsSmartConfig group
    -- ------------------------------------------------------------------------ 
    upsSmartConfigReturnDelay OBJECT-TYPE
        SYNTAX INTEGER
        ACCESS read-write
        STATUS mandatory
        DESCRIPTION
            "The delay in seconds after utility line power returns
             before the UPS will turn on.  This value is also used
             when the UPS comes out of a reboot and before the UPS
             wakes up from 'sleep' mode.  Allowed values are from 
             0 to 43200 seconds(12 hours).
    
             If a value other than a supported value is provided in a
             set request, the UPS interprets it as a the next higher
             acceptable value.  If the provided value is higher than
             the highest acceptable value, the highest acceptable
             value is used."
        ::= { upsSmartConfig 1 }
    
    upsSmartConfigShutoffDelay OBJECT-TYPE
        SYNTAX INTEGER
        ACCESS read-write
        STATUS mandatory
        DESCRIPTION
            "The delay in seconds the UPS remains on after being told
             to turn off.  Allowed values are from 120 to 600 seconds.
    
             If a value other than a supported value is provided in a
             set request, the UPS interprets it as next higher acceptable
             value.  If the provided value is higher than the highest
             acceptable value, the highest acceptable value is used."
        ::= { upsSmartConfig 2 }
    
    
    upsSmartConfigAutoReturn OBJECT-TYPE
        SYNTAX INTEGER  {
            unknown(1),
            no(2),
            yes(3)
        }
        ACCESS read-write
        STATUS mandatory
        DESCRIPTION
            "If yes(3) the UPS will auto return after utility line 
             power returns, no(2) to keep off.
             a unknown(1) return indicates an error occurred on 
             getting this config variable."
        ::= { upsSmartConfig 3 }

    upsSmartConfigTimeOfBatteryDiagnostic OBJECT-TYPE
        SYNTAX INTEGER
        ACCESS read-write
        STATUS mandatory
        DESCRIPTION
            "The time of battery self diagnostic in seconds,
            the valid value is 1 to 600 seconds." 
        ::= { upsSmartConfig 4 }

    upsSmartConfigCombiningMode OBJECT-TYPE
        SYNTAX INTEGER {
            unknown(1),
            single(2),
            master(3),
            slave(4)
        }
        ACCESS read-write
        STATUS mandatory
        DESCRIPTION
            "Setting this variable to indicate the combining work mode of the UPS."
        ::= { upsSmartConfig 5 }
 
    upsSmartConfigCombiningWorkTime OBJECT-TYPE
        SYNTAX INTEGER {
            unknown(1),
            by-7-days(2),          -- oneWeek
            by-30-days(3),         -- oneMonth
            by-90-days(4),         -- oneSeason
            by-180-days(5)         -- halfYear
        }
        ACCESS read-write
        STATUS mandatory
        DESCRIPTION
            "The work time of alternating from master UPS and slave or
             from slave to master."
        ::= { upsSmartConfig 6 }
    
    upsSmartConfigEnablePowerSupplyTimeOnBattery OBJECT-TYPE
        SYNTAX INTEGER
        ACCESS read-write
        STATUS mandatory
        DESCRIPTION
            "The time of enable power supply on battery in seconds,
            the valid value is -1 to 86400 seconds. 
            the UPS will be delayed shutdown if the time out.
            if -1 set to this variable, UPS will supply power till
            the battery low or utility power restore. " 
        ::= { upsSmartConfig 9 }


    -- ------------------------------------------------------------------------ 
    -- 3.1.8.3 the upsPlanConfig group
    ------------------------------------------------------------------------ 
    upsPlanConfigNum OBJECT-TYPE
        SYNTAX INTEGER
        ACCESS read-only
        STATUS mandatory
        DESCRIPTION
           "The number of schedulable tasks current set. "
        ::= { upsPlanConfig 1 }
 
    upsPlanConfigTable OBJECT-TYPE
        SYNTAX SEQUENCE OF UpsPlanConfigEntry
        ACCESS not-accessible
        STATUS mandatory
        DESCRIPTION
            "A list of schedule tasks that will be scheduled at given time. 
             The number of entries is given by the value of upsPlanConfigNum."
        ::= { upsPlanConfig 2 }
 
    upsPlanConfigEntry OBJECT-TYPE
        SYNTAX UpsPlanConfigEntry
        ACCESS not-accessible
        STATUS mandatory
        DESCRIPTION
            "The plan of schedulable tasks."
        INDEX  { planIndex}
        ::= { upsPlanConfigTable 1 }
 
    UpsPlanConfigEntry ::=
        SEQUENCE {
            planIndex
                INTEGER,
            planName
                INTEGER,
            scheduleCycle
                INTEGER,
            scheduleTime
                 DisplayString,
            lastScheduledTime
                 DisplayString,
            runMissing
                INTEGER,
            planAccept
                INTEGER
        }
 
    planIndex OBJECT-TYPE
        SYNTAX INTEGER
        ACCESS read-only
        STATUS mandatory
        DESCRIPTION
            "The index of the plans entry. it will be ignored 
            when add a new plan to list."
        ::= { upsPlanConfigEntry 1 }
    
    planName OBJECT-TYPE
        SYNTAX INTEGER {
            turnDelayOffUps(1),
            turnUpsOn(3),
            turnUpsOff(4),
            batteryDiagnostic(5)
        }
        ACCESS read-write
        STATUS mandatory
        DESCRIPTION
            "The name of schedulable task."
        ::= { upsPlanConfigEntry 2 }

    scheduleCycle OBJECT-TYPE
        SYNTAX INTEGER  {
            once(1),
            daily(2),
            weekly(3),
            biweekly(4),
            monthly(5)
        }
        ACCESS read-write
        STATUS mandatory
        DESCRIPTION
           "The cycle to schedule the plan."
        ::= { upsPlanConfigEntry 3 }
 
    scheduleTime OBJECT-TYPE
        SYNTAX DisplayString
        ACCESS read-write
        STATUS mandatory
        DESCRIPTION
           "The time to schedule this task, format as yyyy/mm/dd hh:mm:ss"
        ::= { upsPlanConfigEntry 4 }
 
    lastScheduledTime OBJECT-TYPE
        SYNTAX DisplayString
        ACCESS read-only
        STATUS mandatory
        DESCRIPTION
           "The last time of the task was scheduled, format as yyyy/mm/dd hh:mm:ss"
        ::= { upsPlanConfigEntry 5 }

    runMissing OBJECT-TYPE
        SYNTAX INTEGER {
            ignoreMissedPlan(0),
            runMissedPlan(1)
       }
        ACCESS read-write
        STATUS mandatory
        DESCRIPTION
            "Continue to run this plan if is not scheduled at given time."
       ::= { upsPlanConfigEntry 6 }

    planAccept OBJECT-TYPE
        SYNTAX INTEGER   {
            view(0),
            new(1),
            delete(2)
        }
        ACCESS read-write
        STATUS mandatory
        DESCRIPTION
           "An entry will be added if new(1), and will be removed if delete(2)."
        ::= { upsPlanConfigEntry 7 }

                                                                                
    -- ------------------------------------------------------------------------ 
    -- 3.1.9. the dryContactor group
    -- ------------------------------------------------------------------------ 
    
    -- ------------------------------------------------------------------------ 
    -- 3.1.9.1 the dryBaseStatus group
    -- ------------------------------------------------------------------------ 
    dryBaseStatusCommunication OBJECT-TYPE
        SYNTAX INTEGER {
            unknown(1),
            ok(2),
            lostCommunication(3),
            notEstablished(4)
        }
        ACCESS read-only
        STATUS mandatory
        DESCRIPTION
            "The status of communication to the UPS Ambient Signal Adaptor. 
            lostCommunication(3) indicates some errors occurred between the dry 
            contactor card and agent. notEstablished(4) indicates agent can not
            connect to UPS, maybe error on communication port or port settings
            error."
        ::= { dryBaseStatus 1 }
    
    -- ------------------------------------------------------------------------ 
    -- 3.1.9.2 the dryBaseInput group
    -- ------------------------------------------------------------------------ 
    dryBaseInputStatus1 OBJECT-TYPE
        SYNTAX INTEGER  {
            unknown(1),
            open(2),
            closed(3)
        }
        ACCESS read-only
        STATUS mandatory
        DESCRIPTION
            "The current state of the input dry contactor 1. If the UPS is unable
             to determine the state of the UPS this variable is set to unknown(1)."
        ::= { dryBaseInput 1 }

    dryBaseInputStatus2 OBJECT-TYPE
        SYNTAX INTEGER  {
            unknown(1),
            open(2),
            closed(3)
        }
        ACCESS read-only
        STATUS mandatory
        DESCRIPTION
            "The current state of the input dry contactor 2. If the UPS is unable
             to determine the state of the UPS this variable is set to unknown(1)."
        ::= { dryBaseInput 2 }

    dryBaseInputStatus3 OBJECT-TYPE
        SYNTAX INTEGER  {
            unknown(1),
            open(2),
            closed(3)
        }
        ACCESS read-only
        STATUS mandatory
        DESCRIPTION
            "The current state of the input dry contactor 3. If the UPS is unable
             to determine the state of the UPS this variable is set to unknown(1)."
        ::= { dryBaseInput 3 }

    dryBaseInputStatus4 OBJECT-TYPE
        SYNTAX INTEGER  {
            unknown(1),
            open(2),
            closed(3)
        }
        ACCESS read-only
        STATUS mandatory
        DESCRIPTION
            "The current state of the input dry contactor 4. If the UPS is unable
             to determine the state of the UPS this variable is set to unknown(1)."
        ::= { dryBaseInput 4 }

    dryBaseInputStatus5 OBJECT-TYPE
        SYNTAX INTEGER  {
            unknown(1),
            open(2),
            closed(3)
        }
        ACCESS read-only
        STATUS mandatory
        DESCRIPTION
            "The current state of the input dry contactor 5. If the UPS is unable
             to determine the state of the UPS this variable is set to unknown(1)."
        ::= { dryBaseInput 5 }

    dryBaseInputStatus6 OBJECT-TYPE
        SYNTAX INTEGER  {
            unknown(1),
            open(2),
            closed(3)
        }
        ACCESS read-only
        STATUS mandatory
        DESCRIPTION
            "The current state of the input dry contactor 6. If the UPS is unable
             to determine the state of the UPS this variable is set to unknown(1)."
        ::= { dryBaseInput 6 }

    dryBaseInputStatus7 OBJECT-TYPE
        SYNTAX INTEGER  {
            unknown(1),
            open(2),
            closed(3)
        }
        ACCESS read-only
        STATUS mandatory
        DESCRIPTION
            "The current state of the input dry contactor 7. If the UPS is unable
             to determine the state of the UPS this variable is set to unknown(1)."
        ::= { dryBaseInput 7 }

    dryBaseInputStatus8 OBJECT-TYPE
        SYNTAX INTEGER  {
            unknown(1),
            open(2),
            closed(3)
        }
        ACCESS read-only
        STATUS mandatory
        DESCRIPTION
            "The current state of the input dry contactor 8. If the UPS is unable
             to determine the state of the UPS this variable is set to unknown(1)."
        ::= { dryBaseInput 8 }
    
    -- ------------------------------------------------------------------------ 
    -- 3.1.9.3 the drySmartInput group
    -- ------------------------------------------------------------------------ 
    drySmartInput1 OBJECT-TYPE
        SYNTAX INTEGER
        ACCESS read-only
        STATUS mandatory
        DESCRIPTION
            "The current input ambient parameter 1."
        ::= { drySmartInput 1 }

    drySmartInput2 OBJECT-TYPE
        SYNTAX INTEGER
        ACCESS read-only
        STATUS mandatory
        DESCRIPTION
            "The current input ambient parameter 2."
        ::= { drySmartInput 2 }

    drySmartInput3 OBJECT-TYPE
        SYNTAX INTEGER
        ACCESS read-only
        STATUS mandatory
        DESCRIPTION
            "The current input ambient parameter 3."
        ::= { drySmartInput 3 }

    drySmartInput4 OBJECT-TYPE
        SYNTAX INTEGER
        ACCESS read-only
        STATUS mandatory
        DESCRIPTION
            "The current input ambient parameter 4."
        ::= { drySmartInput 4 }

    drySmartInput5 OBJECT-TYPE
        SYNTAX INTEGER
        ACCESS read-only
        STATUS mandatory
        DESCRIPTION
            "The current input ambient parameter 5."
        ::= { drySmartInput 5 }

    drySmartInput6 OBJECT-TYPE
        SYNTAX INTEGER
        ACCESS read-only
        STATUS mandatory
        DESCRIPTION
            "The current input ambient parameter 6."
        ::= { drySmartInput 6 }

    drySmartInput7 OBJECT-TYPE
        SYNTAX INTEGER
        ACCESS read-only
        STATUS mandatory
        DESCRIPTION
            "The current input ambient parameter 7."
        ::= { drySmartInput 7 }

    drySmartInput8 OBJECT-TYPE
        SYNTAX INTEGER
        ACCESS read-only
        STATUS mandatory
        DESCRIPTION
            "The current input ambient parameter 8."
        ::= { drySmartInput 8 }
    
    -- ------------------------------------------------------------------------ 
    -- 3.1.9.4 the dryBaseOutput group
    -- ------------------------------------------------------------------------ 
    dryBaseOutputStatus1 OBJECT-TYPE
        SYNTAX INTEGER  {
            unknown(1),
            normal(2),
            onbattery(3)
        }
        ACCESS read-only
        STATUS mandatory
        DESCRIPTION
            "The current state of the output dry contactor 1. It represents the
             UPS input status. If the UPS is on battery, this variable is 
             set to onbattery(3). Otherwise, it is set to normal(0)."
        ::= { dryBaseOutput 1 }

    dryBaseOutputStatus2 OBJECT-TYPE
        SYNTAX INTEGER  {
            unknown(1),
            normal(2),
            batterylow(3)
        }
        ACCESS read-only
        STATUS mandatory
        DESCRIPTION
            "The current state of the output dry contactor 2. It represents the
             UPS battery status. If the battery low prewarning appears, this 
             variable is set to batterylow(3). Otherwise, it is set to normal(0)."
        ::= { dryBaseOutput 2 }

    dryBaseOutputStatus3 OBJECT-TYPE
        SYNTAX INTEGER  {
            unknown(1),
            normal(2),
            onBypassOrNoOutput(3)
        }
        ACCESS read-only
        STATUS mandatory
        DESCRIPTION
            "The current state of the output dry contactor 3. It represents the
             UPS output status. If the UPS is on bypass or no output, this 
             variable is set to onBypassOrNoOutput(3). Otherwise, it is set 
             to normal(0)."
        ::= { dryBaseOutput 3 }

    dryBaseOutputStatus4 OBJECT-TYPE
        SYNTAX INTEGER  {
            unknown(1),
            normal(2),
            fault(3)
        }
        ACCESS read-only
        STATUS mandatory
        DESCRIPTION
            "The current state of the input dry contactor 4. If there is some 
            fault with the UPS, this variable is set to fault(3). Otherwise, 
            it is set to normal(0)."
        ::= { dryBaseOutput 4 }

    dryBaseOutputStatus5 OBJECT-TYPE
        SYNTAX INTEGER  {
            unknown(1),
            normal(2),
            abnormal(3)
        }
        ACCESS read-only
        STATUS mandatory
        DESCRIPTION
            "The current state of the input dry contactor 5. It is reserverd."
        ::= { dryBaseOutput 5 }


    -- ------------------------------------------------------------------------ 
    -- 2.2. the upsAlarm group
    -- ------------------------------------------------------------------------ 

    -- ------------------------------------------------------------------------ 
    -- 2.2.1 the upsBaseAlaram group
    -- ------------------------------------------------------------------------ 
    
    -- no upsBaseAlaram variables


    -- ------------------------------------------------------------------------ 
    -- 2.2.2 the upsSmartAlarm group
    -- ------------------------------------------------------------------------ 
    upsSmartAlarmPresentNum OBJECT-TYPE
        SYNTAX INTEGER
        ACCESS read-only
        STATUS mandatory
        DESCRIPTION
           "The present number of active alarams. "
        ::= { upsSmartAlarm 1 }
 
    upsSmartAlarmPresentTable OBJECT-TYPE
        SYNTAX SEQUENCE OF UpsSmartAlarmPresentEntry
        ACCESS not-accessible
        STATUS mandatory
        DESCRIPTION
            "A list of current UPS alarms, The number of entries is given 
            by the value of upsSmartAlarmPresentNum."
        ::= { upsSmartAlarm 2 }
 
    upsSmartAlarmPresentEntry OBJECT-TYPE
        SYNTAX UpsSmartAlarmPresentEntry
        ACCESS not-accessible
        STATUS mandatory
        DESCRIPTION
            "The present alarms list. "
        INDEX  { presentAlarmIndex}
        ::= { upsSmartAlarmPresentTable 1 }
 
    UpsSmartAlarmPresentEntry ::=
        SEQUENCE {
            presentAlarmIndex
                INTEGER,
            presentAlarmTime
                DisplayString,
            presentAlarmId
                INTEGER,
            presentAlarmName
                DisplayString,
            presentAlaramLevel
                INTEGER
        }
 
    presentAlarmIndex OBJECT-TYPE
        SYNTAX INTEGER
        ACCESS read-only
        STATUS mandatory
        DESCRIPTION
            "The index of the present alaram entry."
        ::= { upsSmartAlarmPresentEntry 1 }
    
    presentAlarmTime OBJECT-TYPE
        SYNTAX DisplayString
        ACCESS read-only
        STATUS mandatory
        DESCRIPTION
           "The time of the alarm generated, format as yyyy/mm/dd hh:mm:ss"
        ::= { upsSmartAlarmPresentEntry 2 }
 
    presentAlarmId OBJECT-TYPE
        SYNTAX INTEGER
        ACCESS read-only
        STATUS mandatory
        DESCRIPTION
            "The alarm ID."
       ::= { upsSmartAlarmPresentEntry 3 }

    presentAlarmName OBJECT-TYPE
        SYNTAX DisplayString
        ACCESS read-only
        STATUS mandatory
        DESCRIPTION
           "The name of the alarm."
        ::= { upsSmartAlarmPresentEntry 4 }

    presentAlaramLevel OBJECT-TYPE
        SYNTAX INTEGER {
            information(1),
            warning(2),
            severe(3)
        }
        ACCESS read-only
        STATUS mandatory
        DESCRIPTION
            "The alarm level."
       ::= { upsSmartAlarmPresentEntry 5 }

    -- historical alarms
    upsSmartAlarmHistoryNum OBJECT-TYPE
        SYNTAX INTEGER
        ACCESS read-only
        STATUS mandatory
        DESCRIPTION
           "The number of historical alarms."
        ::= { upsSmartAlarm 3 }
 
    upsSmartAlarmHistoryTable OBJECT-TYPE
        SYNTAX SEQUENCE OF UpsSmartAlarmHistoryEntry
        ACCESS not-accessible
        STATUS mandatory
        DESCRIPTION
            "A list of historical UPS alarms, The number of entries is given 
            by the value of upsSmartAlarmHistoryNum."
        ::= { upsSmartAlarm 4 }
 
    upsSmartAlarmHistoryEntry OBJECT-TYPE
        SYNTAX UpsSmartAlarmHistoryEntry
        ACCESS not-accessible
        STATUS mandatory
        DESCRIPTION
            "The historical alarms list."
        INDEX  { historyAlarmIndex}
        ::= { upsSmartAlarmHistoryTable 1 }
 
    UpsSmartAlarmHistoryEntry ::=
        SEQUENCE {
            historyAlarmIndex
                INTEGER,
            historyAlarmTime
                DisplayString,
            historyAlarmId
                INTEGER,
            historyAlarmName
                DisplayString,
            historyAlaramLevel
                INTEGER
        }
 
    historyAlarmIndex OBJECT-TYPE
        SYNTAX INTEGER
        ACCESS read-only
        STATUS mandatory
        DESCRIPTION
            "The index of the historical alaram entry."
        ::= { upsSmartAlarmHistoryEntry 1 }
    
    historyAlarmTime OBJECT-TYPE
        SYNTAX DisplayString
        ACCESS read-only
        STATUS mandatory
        DESCRIPTION
           "The time of the alarm generated, format as yyyy/mm/dd hh:mm:ss."
        ::= { upsSmartAlarmHistoryEntry 2 }
 
    historyAlarmId OBJECT-TYPE
        SYNTAX INTEGER
        ACCESS read-only
        STATUS mandatory
        DESCRIPTION
            "The alarm ID."
       ::= { upsSmartAlarmHistoryEntry 3 }

    historyAlarmName OBJECT-TYPE
        SYNTAX DisplayString
        ACCESS read-only
        STATUS mandatory
        DESCRIPTION
           "The name of the alarm."
        ::= { upsSmartAlarmHistoryEntry 4 }

    historyAlaramLevel OBJECT-TYPE
        SYNTAX INTEGER {
            information(1),
            warning(2),
            severe(3)
        }
        ACCESS read-only
        STATUS mandatory
        DESCRIPTION
            "The alarm level."
       ::= { upsSmartAlarmHistoryEntry 5 }


    -- ------------------------------------------------------------------------ 
    -- Traps
    -- ------------------------------------------------------------------------ 

    --
    -- trap args
    --
    trapArgsString OBJECT-TYPE
        SYNTAX  DisplayString 
        ACCESS read-only
        STATUS mandatory
        DESCRIPTION
            "This OID allows iTrust UPS traps to be sent with an octet string argument
             that may not be defined in the iTrust UPS MIB.
      
             A get of this OID will return a NULL string."
        ::= { upsAlarm 2002 }
   
   
    communication1Lost TRAP-TYPE
        ENTERPRISE iTrustUps
        VARIABLES { trapArgsString }
        DESCRIPTION
             "SEVERE: Communication to the UPS Ambient Signal Adaptor has been lost.
             Steps to reestablish communication are in progress."
       --#TYPE "Communication to the UPS Ambient Signal Adaptor failure"
       --#SUMMARY "Communication to the UPS Ambient Signal Adaptor has been lost."
       --#ARGUMENTS { }
       --#SEVERITY CRITICAL
       --#TIMEINDEX 1
       --#HELP ""
       --#HELPTAG 0
       --#STATE DEGRADED
        ::= 1
   
    communication1Established TRAP-TYPE
        ENTERPRISE iTrustUps
        VARIABLES { trapArgsString }
        DESCRIPTION
            "INFORMATION: Communication to the UPS Ambient Signal Adaptor 
            has been established."
       --#TYPE "Communication to the UPS Ambient Signal Adaptor established"
       --#SUMMARY "Communication to the UPS Ambient Signal Adaptor has been established."
       --#ARGUMENTS { }
       --#SEVERITY INFORMATIONAL
       --#TIMEINDEX 1
       --#HELP ""
       --#HELPTAG 0
       --#STATE OPERATIONAL
        ::= 2

    upsOverLoad TRAP-TYPE
        ENTERPRISE iTrustUps
        VARIABLES { upsSmartOutputLoad }
        DESCRIPTION
            "SEVERE: The UPS has sensed a load greater than 100 percent
             of its rated capacity, the variable is current load(percent)."
       --#TYPE "iTrust UPS: UPS overload"
       --#SUMMARY "The UPS has sensed a load greater than 100 percent of its rated capacity."
       --#ARGUMENTS { }
       --#SEVERITY CRITICAL
       --#TIMEINDEX 1
       --#HELP ""
       --#HELPTAG 0
       --#STATE DEGRADED
        ::= 3
   
    outputOverloadDispel TRAP-TYPE
        ENTERPRISE iTrustUps
        VARIABLES { trapArgsString }
        DESCRIPTION
            "INFORMATION: The overload status of output is now dispeled. "
       --#TYPE "iTrust UPS: The overload status of output overload is now dispeled."
       --#SUMMARY "The overload status of output is now dispeled."
       --#ARGUMENTS { }
       --#SEVERITY INFORMATIONAL
       --#TIMEINDEX 1
       --#HELP ""
       --#HELPTAG 0
       --#STATE OPERATIONAL
        ::= 4

    upsOnNormal TRAP-TYPE
        ENTERPRISE iTrustUps
        VARIABLES { trapArgsString }
        DESCRIPTION
            "INFORMATION: UPS is on normal status."
       --#TYPE "iTrust UPS: UPS is on normal status."
       --#SUMMARY "UPS is on normal status."
       --#ARGUMENTS { }
       --#SEVERITY INFORMATIONAL
       --#TIMEINDEX 1
       --#HELP ""
       --#HELPTAG 0
       --#STATE OPERATIONAL
        ::= 5

    upsOnBattery TRAP-TYPE
        ENTERPRISE iTrustUps
        VARIABLES { trapArgsString }
        DESCRIPTION
            "WARNING: The UPS has switched to battery backup power."
       --#TYPE "iTrust UPS: On battery"
       --#SUMMARY "The UPS has switched to battery backup power."
       --#ARGUMENTS { }
       --#SEVERITY MAJOR
       --#TIMEINDEX 1
       --#HELP ""
       --#HELPTAG 0
       --#STATE OPERATIONAL
        ::= 6

    upsOnBypass TRAP-TYPE
        ENTERPRISE iTrustUps
        VARIABLES { trapArgsString }
        DESCRIPTION
            "WARNING: The UPS has been switched to bypass."
       --#TYPE "iTrust UPS: UPS on bypass"
       --#SUMMARY "The UPS is being switched to bypass."
       --#ARGUMENTS { }
       --#SEVERITY MAJOR
       --#TIMEINDEX 1
       --#HELP ""
       --#HELPTAG 0
       --#STATE NONOPERATIONAL
        ::= 7

    upsOutputStopped TRAP-TYPE
        ENTERPRISE iTrustUps
        VARIABLES { trapArgsString }
        DESCRIPTION
            "SEVERE: The UPS has stopped power supply, maybe the utility is fault
            and low battery, or UPS have some critical faults."
       --#TYPE "iTrust UPS: The UPS has stopped power supply."
       --#SUMMARY "The UPS has stopped power supply."
       --#ARGUMENTS { }
       --#SEVERITY CRITICAL
       --#TIMEINDEX 1
       --#HELP ""
       --#HELPTAG 0
       --#STATE DEGRADED
        ::= 8
    
    upsTurnedOff TRAP-TYPE
        ENTERPRISE iTrustUps
        VARIABLES { trapArgsString }
        DESCRIPTION
            "WARNING: The UPS has been turned 'off' by the
             management station."
       --#TYPE "iTrust UPS: Switched off"
       --#SUMMARY "The UPS is switched off by a management station."
       --#ARGUMENTS { }
       --#SEVERITY MAJOR
       --#TIMEINDEX 1
       --#HELP ""
       --#HELPTAG 0
       --#STATE NONOPERATIONAL
        ::= 9

    upsTurningOff TRAP-TYPE
        ENTERPRISE iTrustUps
        VARIABLES { trapArgsString }
        DESCRIPTION
            "SEVERE: The UPS is in shutdown progress(delay off), it will be turned off
            after 'upsSmartConfigShutoffDelay' seconds."
       --#TYPE "iTrust UPS: Delay turn off"
       --#SUMMARY "The UPS is being switched off by a management station."
       --#ARGUMENTS { }
       --#SEVERITY CRITICAL
       --#TIMEINDEX 1
       --#HELP ""
       --#HELPTAG 0
       --#STATE DEGRADED
        ::= 10

    upsTurnedOn TRAP-TYPE
        ENTERPRISE iTrustUps
        VARIABLES { trapArgsString }
        DESCRIPTION
            "INFORMATION: The UPS is turned on."
       --#TYPE "iTrust UPS: UPS turned on"
       --#SUMMARY "The UPS is turned on."
       --#ARGUMENTS { }
       --#SEVERITY INFORMATIONAL
       --#TIMEINDEX 1
       --#HELP ""
       --#HELPTAG 0
       --#STATE OPERATIONAL
        ::= 11

    utilityFault TRAP-TYPE
        ENTERPRISE iTrustUps
        VARIABLES { trapArgsString }
        DESCRIPTION
            "WARNING: The utility is fault, now UPS is on battery."
       --#TYPE "iTrust UPS: The utility is fault, now UPS is on battery."
       --#SUMMARY "The utility is fault, now UPS is on battery."
       --#ARGUMENTS { }
       --#SEVERITY MAJOR
       --#TIMEINDEX 1
       --#HELP ""
       --#HELPTAG 0
       --#STATE NONOPERATIONAL
        ::= 12

    utilityHighVoltage TRAP-TYPE
        ENTERPRISE iTrustUps
        VARIABLES { trapArgsString }
        DESCRIPTION
            "WARNING: The voltage of utility is too high and now UPS is switched to battery."
       --#TYPE "iTrust UPS: The voltage of utility is too high."
       --#SUMMARY "The utility voltage is too high and now UPS is switched to battery."
       --#ARGUMENTS { }
       --#SEVERITY MAJOR
       --#TIMEINDEX 1
       --#HELP ""
       --#HELPTAG 0
       --#STATE NONOPERATIONAL
        ::= 13

    utilityLowVoltage TRAP-TYPE
        ENTERPRISE iTrustUps
        VARIABLES { trapArgsString }
        DESCRIPTION
            "WARNING: The utility is in low voltage."
       --#TYPE "iTrust UPS: The utility is in low voltage."
       --#SUMMARY "The utility is in low voltage."
       --#ARGUMENTS { }
       --#SEVERITY MAJOR
       --#TIMEINDEX 1
       --#HELP ""
       --#HELPTAG 0
       --#STATE NONOPERATIONAL
        ::= 14

    powerRestored TRAP-TYPE
        ENTERPRISE iTrustUps
        VARIABLES { trapArgsString }
        DESCRIPTION
            "INFORMATION: Utility power has been restored."
       --#TYPE "iTrust UPS: Utility restored"
       --#SUMMARY "Normal power has been restored to the UPS."
       --#ARGUMENTS { }
       --#SEVERITY INFORMATIONAL
       --#TIMEINDEX 1
       --#HELP ""
       --#HELPTAG 0
       --#STATE OPERATIONAL
        ::= 15

    utilityFrequenceExceedLimit TRAP-TYPE
        ENTERPRISE iTrustUps
        VARIABLES { trapArgsString }
        DESCRIPTION
            "SEVERE: The frequence of utility exceeds limit."
       --#TYPE "iTrust UPS: The frequence of utility exceeds limit."
       --#SUMMARY "Utility frequence exceeds limit."
       --#ARGUMENTS { }
       --#SEVERITY CRITICAL
       --#TIMEINDEX 1
       --#HELP ""
       --#HELPTAG 0
       --#STATE DEGRADED
        ::= 16

    utilityFrequenceNormal TRAP-TYPE
        ENTERPRISE iTrustUps
        VARIABLES { trapArgsString }
        DESCRIPTION
            "INFORMATION:  The frequence of utility is returned to normal from 
             the status of exceeding limit."
       --#TYPE "iTrust UPS: The frequence of utility is returned to normal."
       --#SUMMARY "The frequence of utility is returned to normal."
       --#ARGUMENTS { }
       --#SEVERITY INFORMATIONAL
       --#TIMEINDEX 1
       --#HELP ""
       --#HELPTAG 0
       --#STATE OPERATIONAL
        ::= 17

    inputAndOutputNotSynchronized TRAP-TYPE
        ENTERPRISE iTrustUps
        VARIABLES { trapArgsString }
        DESCRIPTION
            "WARNING: The input and ouput of UPS are not in phase."
       --#TYPE "iTrust UPS: The Input and output are not synchronized."
       --#SUMMARY "Input and output are not synchronized."
       --#ARGUMENTS { }
       --#SEVERITY MAJOR
       --#TIMEINDEX 1
       --#HELP ""
       --#HELPTAG 0
       --#STATE NONOPERATIONAL
        ::= 18

    inputAndOutputSynchronized TRAP-TYPE
        ENTERPRISE iTrustUps
        VARIABLES { trapArgsString }
        DESCRIPTION
            "INFORMATION: The phase of input and ouput of UPS are returned to in phase."
       --#TYPE "iTrust UPS: The input and ouput of UPS are returned to in phase."
       --#SUMMARY "The input and ouput of UPS are returned to in phase."
       --#ARGUMENTS { }
       --#SEVERITY INFORMATIONAL
       --#TIMEINDEX 1
       --#HELP ""
       --#HELPTAG 0
       --#STATE OPERATIONAL
        ::= 19

    bypassVoltageTooLow TRAP-TYPE
        ENTERPRISE iTrustUps
        VARIABLES { trapArgsString }
        DESCRIPTION
            "SEVERE: The voltage of bypass is too low,
             CAUTION: it is improper if switch UPS to bypass."
       --#TYPE "iTrust UPS: Low bypass voltage."
       --#SUMMARY "The bypass voltage is too low."
       --#ARGUMENTS { }
       --#SEVERITY CRITICAL
       --#TIMEINDEX 1
       --#HELP ""
       --#HELPTAG 0
       --#STATE DEGRADED
        ::= 20

    bypassVoltageTooHigh TRAP-TYPE
        ENTERPRISE iTrustUps
        VARIABLES { trapArgsString }
        DESCRIPTION
            "SEVERE: Voltage of bypass exceeds upper limit."
       --#TYPE "iTrust UPS: Voltage of bypass exceeds upper limit."
       --#SUMMARY "Voltage of bypass exceeds upper limit."
       --#ARGUMENTS { }
       --#SEVERITY CRITICAL
       --#TIMEINDEX 1
       --#HELP ""
       --#HELPTAG 0
       --#STATE DEGRADED
        ::= 21

    bypassVoltageRestored TRAP-TYPE
        ENTERPRISE iTrustUps
        VARIABLES { trapArgsString }
        DESCRIPTION
            "INFORMATION: The voltage of bypass is restored."
       --#TYPE "iTrust UPS: Bypass voltage restored."
       --#SUMMARY "The voltage of Bypass is restored."
       --#ARGUMENTS { }
       --#SEVERITY INFORMATIONAL
       --#TIMEINDEX 1
       --#HELP ""
       --#HELPTAG 0
       --#STATE OPERATIONAL
        ::= 22

    upsDischarged TRAP-TYPE
        ENTERPRISE iTrustUps
        VARIABLES { trapArgsString }
        DESCRIPTION
            "SEVERE: The UPS just started a runtime calibration
             discharge.  The UPS batteries are being discharged."
       --#TYPE "iTrust UPS: Deep discharge"
       --#SUMMARY "The UPS has just started a runtime calibration discharge."
       --#ARGUMENTS { }
       --#SEVERITY CRITICAL
       --#TIMEINDEX 1
       --#HELP ""
       --#HELPTAG 0
       --#STATE DEGRADED
        ::= 23

    upsDiagnosticsPassed TRAP-TYPE
        ENTERPRISE iTrustUps
        VARIABLES { trapArgsString }
        DESCRIPTION
            "INFORMATION: The UPS passed its internal battery self-test."
       --#TYPE "iTrust UPS: Passed battery self-test"
       --#SUMMARY "The UPS has passed its internal battery self-test."
       --#ARGUMENTS { }
       --#SEVERITY INFORMATIONAL
       --#TIMEINDEX 1
       --#HELP ""
       --#HELPTAG 0
       --#STATE OPERATIONAL
        ::= 24

    lowBattery TRAP-TYPE
        ENTERPRISE iTrustUps
        VARIABLES { trapArgsString }
        DESCRIPTION
            "SEVERE: The UPS batteries are low and will soon be exhausted.
             If utility power is not restored the UPS will put itself
             to 'sleep' and immediately cut power to the load."
       --#TYPE "iTrust UPS: Low battery"
       --#SUMMARY "The UPS batteries are low and will soon be exhausted."
       --#ARGUMENTS { }
       --#SEVERITY CRITICAL
       --#TIMEINDEX 1
       --#HELP ""
       --#HELPTAG 0
       --#STATE DEGRADED
        ::= 25

    batteryHighVoltage TRAP-TYPE
        ENTERPRISE iTrustUps
        VARIABLES { trapArgsString }
        DESCRIPTION
            "WARNING: The voltage of battery is too high, the charger maybe failure."
       --#TYPE "iTrust UPS: The voltage of battery is too high."
       --#SUMMARY "The voltage of battery is too high."
       --#ARGUMENTS { }
       --#SEVERITY MAJOR
       --#TIMEINDEX 1
       --#HELP ""
       --#HELPTAG 0
       --#STATE NONOPERATIONAL
        ::= 26

    batteryFailed TRAP-TYPE
        ENTERPRISE iTrustUps
        VARIABLES { trapArgsString }
        DESCRIPTION
            "SEVERE: The battery is failure."
       --#TYPE "iTrust UPS: Battery failed."
       --#SUMMARY "The battery is failure."
       --#ARGUMENTS { }
       --#SEVERITY CRITICAL
       --#TIMEINDEX 1
       --#HELP ""
       --#HELPTAG 0
       --#STATE DEGRADED
        ::= 27

    lowBatteryForewarning TRAP-TYPE
        ENTERPRISE iTrustUps
        VARIABLES { trapArgsString }
        DESCRIPTION
            "SEVERE: Low battery is forewarning, the UPS battery will be 
            exhausted in 2 miniutes (if the UPS is in full load condition)."
       --#TYPE "iTrust UPS: Low battery is forewarning."
       --#SUMMARY "Low battery is forewarning."
       --#ARGUMENTS { }
       --#SEVERITY CRITICAL
       --#TIMEINDEX 1
       --#HELP ""
       --#HELPTAG 0
       --#STATE DEGRADED
        ::= 28

    batteryVoltageRestored TRAP-TYPE
        ENTERPRISE iTrustUps
        VARIABLES { trapArgsString }
        DESCRIPTION
            "INFORMATION: The voltage of battery has restored to normal."
       --#TYPE "iTrust UPS: Battery voltage restored."
       --#SUMMARY "The voltage of battery has restored."
       --#ARGUMENTS { }
       --#SEVERITY INFORMATIONAL
       --#TIMEINDEX 1
       --#HELP ""
       --#HELPTAG 0
       --#STATE OPERATIONAL
        ::= 29
    
    batteryEqualCharging TRAP-TYPE
        ENTERPRISE iTrustUps
        VARIABLES { trapArgsString }
        DESCRIPTION
            "INFORMATION: The battery is now on equal charging."
       --#TYPE "iTrust UPS: Battery on equal charging."
       --#SUMMARY "Battery on equal charging."
       --#ARGUMENTS { }
       --#SEVERITY INFORMATIONAL
       --#TIMEINDEX 1
       --#HELP ""
       --#HELPTAG 0
       --#STATE OPERATIONAL
        ::= 30

    batteryFloatCharging TRAP-TYPE
        ENTERPRISE iTrustUps
        VARIABLES { trapArgsString }
        DESCRIPTION
            "INFORMATION: The battery is now on floating charging."
       --#TYPE "iTrust UPS: Battery on floating charging."
       --#SUMMARY "Battery on floating charging."
       --#ARGUMENTS { }
       --#SEVERITY INFORMATIONAL
       --#TIMEINDEX 1
       --#HELP ""
       --#HELPTAG 0
       --#STATE OPERATIONAL
        ::= 31

    inverterFailed TRAP-TYPE
        ENTERPRISE iTrustUps
        VARIABLES { trapArgsString }
        DESCRIPTION
            "SEVERE: The inverter of UPS is now failed."
       --#TYPE "iTrust UPS: Inverter failed."
       --#SUMMARY "The inverter is failure."
       --#ARGUMENTS { }
       --#SEVERITY CRITICAL
       --#TIMEINDEX 1
       --#HELP ""
       --#HELPTAG 0
       --#STATE DEGRADED
        ::= 32

    inverterRecovered TRAP-TYPE
        ENTERPRISE iTrustUps
        VARIABLES { trapArgsString }
        DESCRIPTION
            "INFORMATION: The fault of inverter is resumed."
       --#TYPE "iTrust UPS: the fault of INV is resumed."
       --#SUMMARY "The fault of INV is resumed, and now UPS is ok."
       --#ARGUMENTS { }
       --#SEVERITY INFORMATIONAL
       --#TIMEINDEX 1
       --#HELP ""
       --#HELPTAG 0
       --#STATE OPERATIONAL
        ::= 33

    rectifierFailed TRAP-TYPE
        ENTERPRISE iTrustUps
        VARIABLES { trapArgsString }
        DESCRIPTION
            "SEVERE: The rectifier is in failure."
       --#TYPE "iTrust UPS: The rectifier failed."
       --#SUMMARY "The rectifier failed."
       --#ARGUMENTS { }
       --#SEVERITY CRITICAL
       --#TIMEINDEX 1
       --#HELP ""
       --#HELPTAG 0
       --#STATE DEGRADED
        ::= 34

    rectifierRecovered TRAP-TYPE
        ENTERPRISE iTrustUps
        VARIABLES { trapArgsString }
        DESCRIPTION
            "INFORMATION: The fault of rectifier is resumed."
       --#TYPE "iTrust UPS: Rectifier recovered."
       --#SUMMARY "The rectifier recovered."
       --#ARGUMENTS { }
       --#SEVERITY INFORMATIONAL
       --#TIMEINDEX 1
       --#HELP ""
       --#HELPTAG 0
       --#STATE OPERATIONAL
        ::= 35

    chargerFailed TRAP-TYPE
        ENTERPRISE iTrustUps
        VARIABLES { trapArgsString }
        DESCRIPTION
            "SEVERE: The charger is failure."
       --#TYPE "iTrust UPS: The charger failed."
       --#SUMMARY "The charger is failure."
       --#ARGUMENTS { }
       --#SEVERITY CRITICAL
       --#TIMEINDEX 1
       --#HELP ""
       --#HELPTAG 0
       --#STATE DEGRADED
        ::= 36

    chargerRecovered TRAP-TYPE
        ENTERPRISE iTrustUps
        VARIABLES { trapArgsString }
        DESCRIPTION
            "INFORMATION: The fault of charger is resumed, and now UPS is ok."
       --#TYPE "iTrust UPS: Charger recovered."
       --#SUMMARY "The fault of charger is resumed."
       --#ARGUMENTS { }
       --#SEVERITY INFORMATIONAL
       --#TIMEINDEX 1
       --#HELP ""
       --#HELPTAG 0
       --#STATE OPERATIONAL
        ::= 37

    outputShorted TRAP-TYPE
        ENTERPRISE iTrustUps
        VARIABLES { trapArgsString }
        DESCRIPTION
            "SEVERE: The UPS output line is shorted."
       --#TYPE "iTrust UPS: Output line shorted."
       --#SUMMARY "The UPS output line is shorted."
       --#ARGUMENTS { }
       --#SEVERITY CRITICAL
       --#TIMEINDEX 1
       --#HELP ""
       --#HELPTAG 0
       --#STATE DEGRADED
        ::= 38

    outputShortedSolved TRAP-TYPE
        ENTERPRISE iTrustUps
        VARIABLES { trapArgsString }
        DESCRIPTION
            "INFORMATION: The fault of output line shorted is solved."
       --#TYPE "iTrust UPS: Shorted circuit fault is solved."
       --#SUMMARY "The fault of output line shorted is solved."
       --#ARGUMENTS { }
       --#SEVERITY INFORMATIONAL
       --#TIMEINDEX 1
       --#HELP ""
       --#HELPTAG 0
       --#STATE OPERATIONAL
        ::= 39

    internalTemperatureTooHigh TRAP-TYPE
        ENTERPRISE iTrustUps
        VARIABLES { upsSmartBatteryTemperature }
        DESCRIPTION
            "SEVERE: The internal temperature of UPS is too high."
       --#TYPE "iTrust UPS: UPS internal temperature too high."
       --#SUMMARY "The internal temperature of UPS is too high."
       --#ARGUMENTS { }
       --#SEVERITY CRITICAL
       --#TIMEINDEX 1
       --#HELP ""
       --#HELPTAG 0
       --#STATE DEGRADED
        ::= 40

    highInternalTemperatureDispeled TRAP-TYPE
        ENTERPRISE iTrustUps
        VARIABLES { trapArgsString }
        DESCRIPTION
            "INFORMATION: The high internal temperature is dispeled and 
             now return to normal status. "
       --#TYPE "iTrust UPS: The high internal temperature is dispeled ."
       --#SUMMARY "The high internal temperature is dispeled."
       --#ARGUMENTS { }
       --#SEVERITY INFORMATIONAL
       --#TIMEINDEX 1
       --#HELP ""
       --#HELPTAG 0
       --#STATE OPERATIONAL
        ::= 41

    inputDryContactor1Closed TRAP-TYPE
        ENTERPRISE iTrustUps
        VARIABLES { trapArgsString }
        DESCRIPTION
            "INFORMATION: Input Dry Contactor 1 Closed. "
       --#TYPE "Input Dry Contactor 1 Closed."
       --#SUMMARY "Input Dry Contactor 1 Closed."
       --#ARGUMENTS { }
       --#SEVERITY INFORMATIONAL
       --#TIMEINDEX 1
       --#HELP ""
       --#HELPTAG 0
       --#STATE OPERATIONAL
        ::= 42

    inputDryContactor1Open TRAP-TYPE
        ENTERPRISE iTrustUps
        VARIABLES { trapArgsString }
        DESCRIPTION
            "INFORMATION: Input Dry Contactor 1 Open. "
       --#TYPE "Input Dry Contactor 1 Open."
       --#SUMMARY "Input Dry Contactor 1 Open."
       --#ARGUMENTS { }
       --#SEVERITY INFORMATIONAL
       --#TIMEINDEX 1
       --#HELP ""
       --#HELPTAG 0
       --#STATE OPERATIONAL
        ::= 43

    inputDryContactor2Closed TRAP-TYPE
        ENTERPRISE iTrustUps
        VARIABLES { trapArgsString }
        DESCRIPTION
            "INFORMATION: Input Dry Contactor 2 Closed. "
       --#TYPE "Input Dry Contactor 2 Closed."
       --#SUMMARY "Input Dry Contactor 2 Closed."
       --#ARGUMENTS { }
       --#SEVERITY INFORMATIONAL
       --#TIMEINDEX 1
       --#HELP ""
       --#HELPTAG 0
       --#STATE OPERATIONAL
        ::= 44

    inputDryContactor2Open TRAP-TYPE
        ENTERPRISE iTrustUps
        VARIABLES { trapArgsString }
        DESCRIPTION
            "INFORMATION: Input Dry Contactor 2 Open. "
       --#TYPE "Input Dry Contactor 2 Open."
       --#SUMMARY "Input Dry Contactor 2 Open."
       --#ARGUMENTS { }
       --#SEVERITY INFORMATIONAL
       --#TIMEINDEX 1
       --#HELP ""
       --#HELPTAG 0
       --#STATE OPERATIONAL
        ::= 45

    inputDryContactor3Closed TRAP-TYPE
        ENTERPRISE iTrustUps
        VARIABLES { trapArgsString }
        DESCRIPTION
            "INFORMATION: Input Dry Contactor 3 Closed. "
       --#TYPE "Input Dry Contactor 3 Closed."
       --#SUMMARY "Input Dry Contactor 3 Closed."
       --#ARGUMENTS { }
       --#SEVERITY INFORMATIONAL
       --#TIMEINDEX 1
       --#HELP ""
       --#HELPTAG 0
       --#STATE OPERATIONAL
        ::= 46

    inputDryContactor3Open TRAP-TYPE
        ENTERPRISE iTrustUps
        VARIABLES { trapArgsString }
        DESCRIPTION
            "INFORMATION: Input Dry Contactor 3 Open. "
       --#TYPE "Input Dry Contactor 3 Open."
       --#SUMMARY "Input Dry Contactor 3 Open."
       --#ARGUMENTS { }
       --#SEVERITY INFORMATIONAL
       --#TIMEINDEX 1
       --#HELP ""
       --#HELPTAG 0
       --#STATE OPERATIONAL
        ::= 47

    inputDryContactor4Closed TRAP-TYPE
        ENTERPRISE iTrustUps
        VARIABLES { trapArgsString }
        DESCRIPTION
            "INFORMATION: Input Dry Contactor 4 Closed. "
       --#TYPE "Input Dry Contactor 4 Closed."
       --#SUMMARY "Input Dry Contactor 4 Closed."
       --#ARGUMENTS { }
       --#SEVERITY INFORMATIONAL
       --#TIMEINDEX 1
       --#HELP ""
       --#HELPTAG 0
       --#STATE OPERATIONAL
        ::= 48

    inputDryContactor4Open TRAP-TYPE
        ENTERPRISE iTrustUps
        VARIABLES { trapArgsString }
        DESCRIPTION
            "INFORMATION: Input Dry Contactor 4 Open. "
       --#TYPE "Input Dry Contactor 4 Open."
       --#SUMMARY "Input Dry Contactor 4 Open."
       --#ARGUMENTS { }
       --#SEVERITY INFORMATIONAL
       --#TIMEINDEX 1
       --#HELP ""
       --#HELPTAG 0
       --#STATE OPERATIONAL
        ::= 49

    inputDryContactor5Closed TRAP-TYPE
        ENTERPRISE iTrustUps
        VARIABLES { trapArgsString }
        DESCRIPTION
            "INFORMATION: Input Dry Contactor 5 Closed. "
       --#TYPE "Input Dry Contactor 5 Closed."
       --#SUMMARY "Input Dry Contactor 5 Closed."
       --#ARGUMENTS { }
       --#SEVERITY INFORMATIONAL
       --#TIMEINDEX 1
       --#HELP ""
       --#HELPTAG 0
       --#STATE OPERATIONAL
        ::= 50

    inputDryContactor5Open TRAP-TYPE
        ENTERPRISE iTrustUps
        VARIABLES { trapArgsString }
        DESCRIPTION
            "INFORMATION: Input Dry Contactor 5 Open. "
       --#TYPE "Input Dry Contactor 5 Open."
       --#SUMMARY "Input Dry Contactor 5 Open."
       --#ARGUMENTS { }
       --#SEVERITY INFORMATIONAL
       --#TIMEINDEX 1
       --#HELP ""
       --#HELPTAG 0
       --#STATE OPERATIONAL
        ::= 51

    inputDryContactor6Closed TRAP-TYPE
        ENTERPRISE iTrustUps
        VARIABLES { trapArgsString }
        DESCRIPTION
            "INFORMATION: Input Dry Contactor 6 Closed. "
       --#TYPE "Input Dry Contactor 6 Closed."
       --#SUMMARY "Input Dry Contactor 6 Closed."
       --#ARGUMENTS { }
       --#SEVERITY INFORMATIONAL
       --#TIMEINDEX 1
       --#HELP ""
       --#HELPTAG 0
       --#STATE OPERATIONAL
        ::= 52

    inputDryContactor6Open TRAP-TYPE
        ENTERPRISE iTrustUps
        VARIABLES { trapArgsString }
        DESCRIPTION
            "INFORMATION: Input Dry Contactor 6 Open. "
       --#TYPE "Input Dry Contactor 6 Open."
       --#SUMMARY "Input Dry Contactor 6 Open."
       --#ARGUMENTS { }
       --#SEVERITY INFORMATIONAL
       --#TIMEINDEX 1
       --#HELP ""
       --#HELPTAG 0
       --#STATE OPERATIONAL
        ::= 53

    inputDryContactor7Closed TRAP-TYPE
        ENTERPRISE iTrustUps
        VARIABLES { trapArgsString }
        DESCRIPTION
            "INFORMATION: Input Dry Contactor 7 Closed. "
       --#TYPE "Input Dry Contactor 7 Closed."
       --#SUMMARY "Input Dry Contactor 7 Closed."
       --#ARGUMENTS { }
       --#SEVERITY INFORMATIONAL
       --#TIMEINDEX 1
       --#HELP ""
       --#HELPTAG 0
       --#STATE OPERATIONAL
        ::= 54

    inputDryContactor7Open TRAP-TYPE
        ENTERPRISE iTrustUps
        VARIABLES { trapArgsString }
        DESCRIPTION
            "INFORMATION: Input Dry Contactor 7 Open. "
       --#TYPE "Input Dry Contactor 7 Open."
       --#SUMMARY "Input Dry Contactor 7 Open."
       --#ARGUMENTS { }
       --#SEVERITY INFORMATIONAL
       --#TIMEINDEX 1
       --#HELP ""
       --#HELPTAG 0
       --#STATE OPERATIONAL
        ::= 55

    inputDryContactor8Closed TRAP-TYPE
        ENTERPRISE iTrustUps
        VARIABLES { trapArgsString }
        DESCRIPTION
            "INFORMATION: Input Dry Contactor 8 Closed. "
       --#TYPE "Input Dry Contactor 8 Closed."
       --#SUMMARY "Input Dry Contactor 8 Closed."
       --#ARGUMENTS { }
       --#SEVERITY INFORMATIONAL
       --#TIMEINDEX 1
       --#HELP ""
       --#HELPTAG 0
       --#STATE OPERATIONAL
        ::= 56

    inputDryContactor8Open TRAP-TYPE
        ENTERPRISE iTrustUps
        VARIABLES { trapArgsString }
        DESCRIPTION
            "INFORMATION: Input Dry Contactor 8 Open. "
       --#TYPE "Input Dry Contactor 8 Open."
       --#SUMMARY "Input Dry Contactor 8 Open."
       --#ARGUMENTS { }
       --#SEVERITY INFORMATIONAL
       --#TIMEINDEX 1
       --#HELP ""
       --#HELPTAG 0
       --#STATE OPERATIONAL
        ::= 57

    outputDryContactor1Closed TRAP-TYPE
        ENTERPRISE iTrustUps
        VARIABLES { trapArgsString }
        DESCRIPTION
            "INFORMATION: Output Dry Contactor 1
            (Input Status): On Battery"
       --#TYPE "Output Dry Contactor 1 Closed."
       --#SUMMARY "Output Dry Contactor 1 Closed."
       --#ARGUMENTS { }
       --#SEVERITY INFORMATIONAL
       --#TIMEINDEX 1
       --#HELP ""
       --#HELPTAG 0
       --#STATE OPERATIONAL
        ::= 58

    outputDryContactor1Open TRAP-TYPE
        ENTERPRISE iTrustUps
        VARIABLES { trapArgsString }
        DESCRIPTION
            "INFORMATION: Output Dry Contactor 1
            (Input Status): Normal"
       --#TYPE "Output Dry Contactor 1 Open."
       --#SUMMARY "Output Dry Contactor 1 Open."
       --#ARGUMENTS { }
       --#SEVERITY INFORMATIONAL
       --#TIMEINDEX 1
       --#HELP ""
       --#HELPTAG 0
       --#STATE OPERATIONAL
        ::= 59

    outputDryContactor2Closed TRAP-TYPE
        ENTERPRISE iTrustUps
        VARIABLES { trapArgsString }
        DESCRIPTION
            "INFORMATION: Output Dry Contactor 2
            (Battery Status): Battery Low"
       --#TYPE "Output Dry Contactor 2 Closed."
       --#SUMMARY "Output Dry Contactor 2 Closed."
       --#ARGUMENTS { }
       --#SEVERITY INFORMATIONAL
       --#TIMEINDEX 1
       --#HELP ""
       --#HELPTAG 0
       --#STATE OPERATIONAL
        ::= 60

    outputDryContactor2Open TRAP-TYPE
        ENTERPRISE iTrustUps
        VARIABLES { trapArgsString }
        DESCRIPTION
            "INFORMATION: Output Dry Contactor 2
            (Battery Status):Normal"
       --#TYPE "Output Dry Contactor 2 Open."
       --#SUMMARY "Output Dry Contactor 2 Open."
       --#ARGUMENTS { }
       --#SEVERITY INFORMATIONAL
       --#TIMEINDEX 1
       --#HELP ""
       --#HELPTAG 0
       --#STATE OPERATIONAL
        ::= 61

    outputDryContactor3Closed TRAP-TYPE
        ENTERPRISE iTrustUps
        VARIABLES { trapArgsString }
        DESCRIPTION
            "INFORMATION: Output Dry Contactor 3
            (Output Status):On Bypass or No Output"
       --#TYPE "Output Dry Contactor 3 Closed."
       --#SUMMARY "Output Dry Contactor 3 Closed."
       --#ARGUMENTS { }
       --#SEVERITY INFORMATIONAL
       --#TIMEINDEX 1
       --#HELP ""
       --#HELPTAG 0
       --#STATE OPERATIONAL
        ::= 62

    outputDryContactor3Open TRAP-TYPE
        ENTERPRISE iTrustUps
        VARIABLES { trapArgsString }
        DESCRIPTION
            "INFORMATION: Output Dry Contactor 3
            (Output Status): Normal"
       --#TYPE "Output Dry Contactor 3 Open."
       --#SUMMARY "Output Dry Contactor 3 Open."
       --#ARGUMENTS { }
       --#SEVERITY INFORMATIONAL
       --#TIMEINDEX 1
       --#HELP ""
       --#HELPTAG 0
       --#STATE OPERATIONAL
        ::= 63

    outputDryContactor4Closed TRAP-TYPE
        ENTERPRISE iTrustUps
        VARIABLES { trapArgsString }
        DESCRIPTION
            "INFORMATION: Output Dry Contactor 4
            (UPS Status): Fault"
       --#TYPE "Output Dry Contactor 4 Closed."
       --#SUMMARY "Output Dry Contactor 4 Closed."
       --#ARGUMENTS { }
       --#SEVERITY INFORMATIONAL
       --#TIMEINDEX 1
       --#HELP ""
       --#HELPTAG 0
       --#STATE OPERATIONAL
        ::= 64

    outputDryContactor4Open TRAP-TYPE
        ENTERPRISE iTrustUps
        VARIABLES { trapArgsString }
        DESCRIPTION
            "INFORMATION: Output Dry Contactor 4
            (UPS Status): Normal"
       --#TYPE "Output Dry Contactor 4 Open."
       --#SUMMARY "Output Dry Contactor 4 Open."
       --#ARGUMENTS { }
       --#SEVERITY INFORMATIONAL
       --#TIMEINDEX 1
       --#HELP ""
       --#HELPTAG 0
       --#STATE OPERATIONAL
        ::= 65

    outputDryContactor5Closed TRAP-TYPE
        ENTERPRISE iTrustUps
        VARIABLES { trapArgsString }
        DESCRIPTION
            "INFORMATION: Output Dry Contactor 5
            (Reserved): Abnormal"
       --#TYPE "Output Dry Contactor 5 Closed."
       --#SUMMARY "Output Dry Contactor 5 Closed."
       --#ARGUMENTS { }
       --#SEVERITY INFORMATIONAL
       --#TIMEINDEX 1
       --#HELP ""
       --#HELPTAG 0
       --#STATE OPERATIONAL
        ::= 66

    outputDryContactor5Open TRAP-TYPE
        ENTERPRISE iTrustUps
        VARIABLES { trapArgsString }
        DESCRIPTION
            "INFORMATION: Output Dry Contactor 5
            (Reserved): Normal"
       --#TYPE "Output Dry Contactor 5 Open."
       --#SUMMARY "Output Dry Contactor 5 Open."
       --#ARGUMENTS { }
       --#SEVERITY INFORMATIONAL
       --#TIMEINDEX 1
       --#HELP ""
       --#HELPTAG 0
       --#STATE OPERATIONAL
        ::= 67
   
    communication2Lost TRAP-TYPE
        ENTERPRISE iTrustUps
        VARIABLES { trapArgsString }
        DESCRIPTION
             "SEVERE: Communication between the dry contactor
             card and the UPS has been lost. Steps to reestablish 
             communication are in progress."
       --#TYPE "Communication to the UPS failure"
       --#SUMMARY "Communication to the UPS has been lost."
       --#ARGUMENTS { }
       --#SEVERITY CRITICAL
       --#TIMEINDEX 1
       --#HELP ""
       --#HELPTAG 0
       --#STATE DEGRADED
        ::= 68
   
    communication2Established TRAP-TYPE
        ENTERPRISE iTrustUps
        VARIABLES { trapArgsString }
        DESCRIPTION
            "INFORMATION: Communication between the dry contactor
             card and the UPS has been established."
       --#TYPE "Communication to the UPS established"
       --#SUMMARY "Communication to the UPS has been established."
       --#ARGUMENTS { }
       --#SEVERITY INFORMATIONAL
       --#TIMEINDEX 1
       --#HELP ""
       --#HELPTAG 0
       --#STATE OPERATIONAL
        ::= 69

END -- end of DRY-UH11-MIB
