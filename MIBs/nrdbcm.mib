NIOBRARA-BCM-MIB DEFINITIONS ::= BEGIN

--  Title:    NRDBCM.MIB
--  Version:  v1.4
--  Date:     01/13/09
--
--  Copyright @ 2001-2009 Niobrara R&D Corporation.  All rights reserved worldwide.
--
--  This MIB defines objects for the PWRM BCM Poller QUCM SNMP Agent.
--

          IMPORTS
	      enterprises, Counter,
	      TimeTicks, Gauge, IpAddress     FROM RFC1155-SMI
          OBJECT-TYPE                     FROM RFC-1212
          sysUpTime, DisplayString        FROM RFC1213-MIB
	      TRAP-TYPE                       FROM RFC-1215;

	  niobrara OBJECT IDENTIFIER ::= { enterprises 6532 }




--
-- Niobrara Automation
--

    niobraraAutomation OBJECT IDENTIFIER ::= { niobrara 1 }

--
-- NRD Automation
--
	nrdExtensions OBJECT IDENTIFIER ::= { niobraraAutomation 1 }

	nrdExperimental OBJECT IDENTIFIER ::= { niobraraAutomation 2 }

	nrdPrivate OBJECT IDENTIFIER ::= { niobraraAutomation 3 }


--
-- NRD Extensions
--


	  ntrapargs                      OBJECT IDENTIFIER ::=  { nrdExtensions 10 }

-- the ntrapargs group
ntrapargsInteger OBJECT-TYPE
   SYNTAX INTEGER    
   ACCESS read-only
   STATUS mandatory
   DESCRIPTION
      "This OID allows Niobrara traps to be sent with an integer argument
       that my not be defined in the POWERLOGIC MIB.
      
       A get of this OID will return 0."
   ::= { ntrapargs 1 }
  
ntrapargsIpAddress OBJECT-TYPE
   SYNTAX IpAddress   
   ACCESS read-only
   STATUS mandatory
   DESCRIPTION
      "This OID allows Niobrara traps to be sent with an IP address argument
       that my not be defined in the BCM MIB.
      
       A get of this OID will return 0.0.0.0."
   ::= { ntrapargs 2 }
   
ntrapargsString OBJECT-TYPE
   SYNTAX  DisplayString 
   ACCESS read-only
   STATUS mandatory
   DESCRIPTION
      "This OID allows Niobrara traps to be sent with an octet string argument
       that my not be defined in the BCM MIB.
      
       A get of this OID will return a NULL string."
   ::= { ntrapargs 3 }

ntrapargsGauge OBJECT-TYPE
   SYNTAX  Gauge 
   ACCESS read-only
   STATUS mandatory
   DESCRIPTION
      "This OID allows Niobrara traps to be sent with a Gauge argument
       that my not be defined in the BCM MIB.
      
       A get of this OID will return 0."
   ::= { ntrapargs 4 }

ntrapargsTimeTicks OBJECT-TYPE
   SYNTAX TimeTicks  
   ACCESS read-only
   STATUS mandatory
   DESCRIPTION
      "This OID allows Niobrara traps to be sent with a TimeTicks argument
       that my not be defined in the BCM MIB.
      
       A get of this OID will return 0."
   ::= { ntrapargs 5 }



--
-- NRD Private
--

	nrdPWRM OBJECT IDENTIFIER ::= { nrdPrivate 2 }

          --
          --      The Device Identification group.
          --      All objects in this group are determined at device
          --      initialization and remain static.
          --


          nrdbcmIden        OBJECT IDENTIFIER ::= { nrdPWRM 1 }

          nrdbcmSoftwareVersion OBJECT-TYPE
              SYNTAX DisplayString (SIZE (255))
              ACCESS read-only
              STATUS mandatory
              DESCRIPTION
                      "The QUCM SNMP Agent software version."
              ::= { nrdbcmIden 1 }

          nrdbcmFirmwareVersion OBJECT-TYPE
              SYNTAX DisplayString (SIZE (255))
              ACCESS read-only
              STATUS mandatory
              DESCRIPTION
                      "The QUCM firmware version."
              ::= { nrdbcmIden 2 }

          nrdbcmtitle OBJECT-TYPE
              SYNTAX DisplayString (SIZE (255))
              ACCESS read-only
              STATUS mandatory
              DESCRIPTION
                      "The QUCM Title Name."
              ::= { nrdbcmIden 3 }

          nrdbcmVendor OBJECT-TYPE
              SYNTAX DisplayString (SIZE (255))
              ACCESS read-only
              STATUS mandatory
              DESCRIPTION
                      "Niobrara."
              ::= { nrdbcmIden 4 }

          nrdbcmModel OBJECT-TYPE
              SYNTAX INTEGER  {
                 qucmOE(0)
              }
              ACCESS read-only
              STATUS mandatory
              DESCRIPTION
                      "The QUCM model type."
              ::= { nrdbcmIden 5 }

--
-- Branch Circuit Monitor Data
--

          nrdbcmData     OBJECT IDENTIFIER ::= { nrdPWRM 2 }
          
          nrdbcmNumMeters OBJECT-TYPE
              SYNTAX INTEGER (1..64)
              ACCESS read-only
              STATUS mandatory
              DESCRIPTION
                      "The number of Veris Branch Circuit Monitors configured 
                      in this device. This entry indicates the number of rows in
                      the Data table."
              ::= { nrdbcmData 1 }

          nrdbcmDataTable OBJECT-TYPE
              SYNTAX SEQUENCE OF NrdbcmDataEntry
              ACCESS not-accessible
              STATUS mandatory
              ::= { nrdbcmData 2 }

          nrdbcmDataEntry OBJECT-TYPE
              SYNTAX NrdbcmDataEntry
              ACCESS not-accessible
              STATUS mandatory
              INDEX { nrdbcmMeter }
              ::= { nrdbcmDataTable 1 }

          NrdbcmDataEntry ::= SEQUENCE {
              nrdbcmMeter                       INTEGER,
              nrdbcmMeterName                   DisplayString,
              nrdbcmNetworkIP                   IpAddress,
              nrdbcmMeterSlaveAddress           INTEGER,
              nrdbcmBreaker1A01Current          INTEGER,
              nrdbcmBreaker1B02Current          INTEGER,
              nrdbcmBreaker1A03Current          INTEGER,
              nrdbcmBreaker1B04Current          INTEGER,
              nrdbcmBreaker1A05Current          INTEGER,
              nrdbcmBreaker1B06Current          INTEGER,
              nrdbcmBreaker1A07Current          INTEGER,
              nrdbcmBreaker1B08Current          INTEGER,
              nrdbcmBreaker1A09Current          INTEGER,
              nrdbcmBreaker1B10Current          INTEGER,
              nrdbcmBreaker1A11Current          INTEGER,
              nrdbcmBreaker1B12Current          INTEGER,
              nrdbcmBreaker1A13Current          INTEGER,
              nrdbcmBreaker1B14Current          INTEGER,
              nrdbcmBreaker1A15Current          INTEGER,
              nrdbcmBreaker1B16Current          INTEGER,
              nrdbcmBreaker1A17Current          INTEGER,
              nrdbcmBreaker1B18Current          INTEGER,
              nrdbcmBreaker1A19Current          INTEGER,
              nrdbcmBreaker1B20Current          INTEGER,
              nrdbcmBreaker1A21Current          INTEGER,
              nrdbcmBreaker1B22Current          INTEGER,
              nrdbcmBreaker1A23Current          INTEGER,
              nrdbcmBreaker1B24Current          INTEGER,
              nrdbcmBreaker1A25Current          INTEGER,
              nrdbcmBreaker1B26Current          INTEGER,
              nrdbcmBreaker1A27Current          INTEGER,
              nrdbcmBreaker1B28Current          INTEGER,
              nrdbcmBreaker1A29Current          INTEGER,
              nrdbcmBreaker1B30Current          INTEGER,
              nrdbcmBreaker1A31Current          INTEGER,
              nrdbcmBreaker1B32Current          INTEGER,
              nrdbcmBreaker1A33Current          INTEGER,
              nrdbcmBreaker1B34Current          INTEGER,
              nrdbcmBreaker1A35Current          INTEGER,
              nrdbcmBreaker1B36Current          INTEGER,
              nrdbcmBreaker1A37Current          INTEGER,
              nrdbcmBreaker1B38Current          INTEGER,
              nrdbcmBreaker1A39Current          INTEGER,
              nrdbcmBreaker1B40Current          INTEGER,
              nrdbcmBreaker1A41Current          INTEGER,
              nrdbcmBreaker1B42Current          INTEGER,
              nrdbcmBreaker1A01Status           INTEGER,
              nrdbcmBreaker1B02Status           INTEGER,
              nrdbcmBreaker1A03Status           INTEGER,
              nrdbcmBreaker1B04Status           INTEGER,
              nrdbcmBreaker1A05Status           INTEGER,
              nrdbcmBreaker1B06Status           INTEGER,
              nrdbcmBreaker1A07Status           INTEGER,
              nrdbcmBreaker1B08Status           INTEGER,
              nrdbcmBreaker1A09Status           INTEGER,
              nrdbcmBreaker1B10Status           INTEGER,
              nrdbcmBreaker1A11Status           INTEGER,
              nrdbcmBreaker1B12Status           INTEGER,
              nrdbcmBreaker1A13Status           INTEGER,
              nrdbcmBreaker1B14Status           INTEGER,
              nrdbcmBreaker1A15Status           INTEGER,
              nrdbcmBreaker1B16Status           INTEGER,
              nrdbcmBreaker1A17Status           INTEGER,
              nrdbcmBreaker1B18Status           INTEGER,
              nrdbcmBreaker1A19Status           INTEGER,
              nrdbcmBreaker1B20Status           INTEGER,
              nrdbcmBreaker1A21Status           INTEGER,
              nrdbcmBreaker1B22Status           INTEGER,
              nrdbcmBreaker1A23Status           INTEGER,
              nrdbcmBreaker1B24Status           INTEGER,
              nrdbcmBreaker1A25Status           INTEGER,
              nrdbcmBreaker1B26Status           INTEGER,
              nrdbcmBreaker1A27Status           INTEGER,
              nrdbcmBreaker1B28Status           INTEGER,
              nrdbcmBreaker1A29Status           INTEGER,
              nrdbcmBreaker1B30Status           INTEGER,
              nrdbcmBreaker1A31Status           INTEGER,
              nrdbcmBreaker1B32Status           INTEGER,
              nrdbcmBreaker1A33Status           INTEGER,
              nrdbcmBreaker1B34Status           INTEGER,
              nrdbcmBreaker1A35Status           INTEGER,
              nrdbcmBreaker1B36Status           INTEGER,
              nrdbcmBreaker1A37Status           INTEGER,
              nrdbcmBreaker1B38Status           INTEGER,
              nrdbcmBreaker1A39Status           INTEGER,
              nrdbcmBreaker1B40Status           INTEGER,
              nrdbcmBreaker1A41Status           INTEGER,
              nrdbcmBreaker1B42Status           INTEGER,
			nrdbcmBreaker1A01Name		    DisplayString,
			nrdbcmBreaker1B02Name		    DisplayString,
			nrdbcmBreaker1A03Name		    DisplayString,
			nrdbcmBreaker1B04Name		    DisplayString,
			nrdbcmBreaker1A05Name		    DisplayString,
			nrdbcmBreaker1B06Name		    DisplayString,
			nrdbcmBreaker1A07Name		    DisplayString,
			nrdbcmBreaker1B08Name		    DisplayString,
			nrdbcmBreaker1A09Name		    DisplayString,
			nrdbcmBreaker1B10Name		    DisplayString,
			nrdbcmBreaker1A11Name		    DisplayString,
			nrdbcmBreaker1B12Name		    DisplayString,
			nrdbcmBreaker1A13Name		    DisplayString,
			nrdbcmBreaker1B14Name		    DisplayString,
			nrdbcmBreaker1A15Name		    DisplayString,
			nrdbcmBreaker1B16Name		    DisplayString,
			nrdbcmBreaker1A17Name		    DisplayString,
			nrdbcmBreaker1B18Name		    DisplayString,
			nrdbcmBreaker1A19Name		    DisplayString,
			nrdbcmBreaker1B20Name		    DisplayString,
			nrdbcmBreaker1A21Name		    DisplayString,
			nrdbcmBreaker1B22Name		    DisplayString,
			nrdbcmBreaker1A23Name		    DisplayString,
			nrdbcmBreaker1B24Name		    DisplayString,
			nrdbcmBreaker1A25Name		    DisplayString,
			nrdbcmBreaker1B26Name		    DisplayString,
			nrdbcmBreaker1A27Name		    DisplayString,
			nrdbcmBreaker1B28Name		    DisplayString,
			nrdbcmBreaker1A29Name		    DisplayString,
			nrdbcmBreaker1B30Name		    DisplayString,
			nrdbcmBreaker1A31Name		    DisplayString,
			nrdbcmBreaker1B32Name		    DisplayString,
			nrdbcmBreaker1A33Name		    DisplayString,
			nrdbcmBreaker1B34Name		    DisplayString,
			nrdbcmBreaker1A35Name		    DisplayString,
			nrdbcmBreaker1B36Name		    DisplayString,
			nrdbcmBreaker1A37Name		    DisplayString,
			nrdbcmBreaker1B38Name		    DisplayString,
			nrdbcmBreaker1A39Name		    DisplayString,
			nrdbcmBreaker1B40Name		    DisplayString,
			nrdbcmBreaker1A41Name		    DisplayString,
			nrdbcmBreaker1B42Name		    DisplayString
          }

          nrdbcmMeter OBJECT-TYPE
              SYNTAX INTEGER (1..60)
              ACCESS read-only
              STATUS mandatory
              DESCRIPTION
                      "The meter number."
              ::= { nrdbcmDataEntry 1 }
          
         nrdbcmMeterName OBJECT-TYPE
              SYNTAX DisplayString (SIZE (255))
              ACCESS read-only
              STATUS mandatory
              DESCRIPTION
                      "The BCM's Meter Name."
              ::= { nrdbcmDataEntry 2 }

         nrdbcmNetworkIP	OBJECT-TYPE
              SYNTAX	IpAddress
              ACCESS	read-only
	          STATUS	mandatory
	          DESCRIPTION
		            "The IP address of the meter's server"
		      ::= { nrdbcmDataEntry 3 }

         nrdbcmMeterSlaveAddress OBJECT-TYPE
              SYNTAX INTEGER (1..255)
              ACCESS read-only
              STATUS mandatory
              DESCRIPTION
                      "The meter's drop number."
              ::= { nrdbcmDataEntry 4 }
          
          nrdbcmBreaker1A01Current OBJECT-TYPE
              SYNTAX INTEGER (0..65535)
              ACCESS read-only
              STATUS mandatory
              DESCRIPTION
                      "The Current for Breaker 1A01.
                      (Unit of measure: .1 Amp)"
              ::= { nrdbcmDataEntry 5 }

          nrdbcmBreaker1B02Current OBJECT-TYPE
              SYNTAX INTEGER (0..65535)
              ACCESS read-only
              STATUS mandatory
              DESCRIPTION
                      "The Current for Breaker 1B02.
                      (Unit of measure: .1 Amp)"
              ::= { nrdbcmDataEntry 6 }

          nrdbcmBreaker1A03Current OBJECT-TYPE
              SYNTAX INTEGER (0..65535)
              ACCESS read-only
              STATUS mandatory
              DESCRIPTION
                      "The Current for Breaker 1A03.
                      (Unit of measure: .1 Amp)"
              ::= { nrdbcmDataEntry 7 }

          nrdbcmBreaker1B04Current OBJECT-TYPE
              SYNTAX INTEGER (0..65535)
              ACCESS read-only
              STATUS mandatory
              DESCRIPTION
                      "The Current for Breaker 1B04.
                      (Unit of measure: .1 Amp)"
              ::= { nrdbcmDataEntry 8 }

          nrdbcmBreaker1A05Current OBJECT-TYPE
              SYNTAX INTEGER (0..65535)
              ACCESS read-only
              STATUS mandatory
              DESCRIPTION
                      "The Current for Breaker 1A05.
                      (Unit of measure: .1 Amp)"
              ::= { nrdbcmDataEntry 9 }

          nrdbcmBreaker1B06Current OBJECT-TYPE
              SYNTAX INTEGER (0..65535)
              ACCESS read-only
              STATUS mandatory
              DESCRIPTION
                      "The Current for Breaker 1B06.
                      (Unit of measure: .1 Amp)"
              ::= { nrdbcmDataEntry 10 }

          nrdbcmBreaker1A07Current OBJECT-TYPE
              SYNTAX INTEGER (0..65535)
              ACCESS read-only
              STATUS mandatory
              DESCRIPTION
                      "The Current for Breaker 1A07.
                      (Unit of measure: .1 Amp)"
              ::= { nrdbcmDataEntry 11 }

          nrdbcmBreaker1B08Current OBJECT-TYPE
              SYNTAX INTEGER (0..65535)
              ACCESS read-only
              STATUS mandatory
              DESCRIPTION
                      "The Current for Breaker 1B08.
                      (Unit of measure: .1 Amp)"
              ::= { nrdbcmDataEntry 12 }

          nrdbcmBreaker1A09Current OBJECT-TYPE
              SYNTAX INTEGER (0..65535)
              ACCESS read-only
              STATUS mandatory
              DESCRIPTION
                      "The Current for Breaker 1A09.
                      (Unit of measure: .1 Amp)"
              ::= { nrdbcmDataEntry 13 }

          nrdbcmBreaker1B10Current OBJECT-TYPE
              SYNTAX INTEGER (0..65535)
              ACCESS read-only
              STATUS mandatory
              DESCRIPTION
                      "The Current for Breaker 1B10.
                      (Unit of measure: .1 Amp)"
              ::= { nrdbcmDataEntry 14 }

          nrdbcmBreaker1A11Current OBJECT-TYPE
              SYNTAX INTEGER (0..65535)
              ACCESS read-only
              STATUS mandatory
              DESCRIPTION
                      "The Current for Breaker 1A11.
                      (Unit of measure: .1 Amp)"
              ::= { nrdbcmDataEntry 15 }

          nrdbcmBreaker1B12Current OBJECT-TYPE
              SYNTAX INTEGER (0..65535)
              ACCESS read-only
              STATUS mandatory
              DESCRIPTION
                      "The Current for Breaker 1B12.
                      (Unit of measure: .1 Amp)"
              ::= { nrdbcmDataEntry 16 }

          nrdbcmBreaker1A13Current OBJECT-TYPE
              SYNTAX INTEGER (0..65535)
              ACCESS read-only
              STATUS mandatory
              DESCRIPTION
                      "The Current for Breaker 1A13.
                      (Unit of measure: .1 Amp)"
              ::= { nrdbcmDataEntry 17 }

          nrdbcmBreaker1B14Current OBJECT-TYPE
              SYNTAX INTEGER (0..65535)
              ACCESS read-only
              STATUS mandatory
              DESCRIPTION
                      "The Current for Breaker 1B14.
                      (Unit of measure: .1 Amp)"
              ::= { nrdbcmDataEntry 18 }

          nrdbcmBreaker1A15Current OBJECT-TYPE
              SYNTAX INTEGER (0..65535)
              ACCESS read-only
              STATUS mandatory
              DESCRIPTION
                      "The Current for Breaker 1A15.
                      (Unit of measure: .1 Amp)"
              ::= { nrdbcmDataEntry 19 }

          nrdbcmBreaker1B16Current OBJECT-TYPE
              SYNTAX INTEGER (0..65535)
              ACCESS read-only
              STATUS mandatory
              DESCRIPTION
                      "The Current for Breaker 1B16.
                      (Unit of measure: .1 Amp)"
              ::= { nrdbcmDataEntry 20 }

          nrdbcmBreaker1A17Current OBJECT-TYPE
              SYNTAX INTEGER (0..65535)
              ACCESS read-only
              STATUS mandatory
              DESCRIPTION
                      "The Current for Breaker 1A17.
                      (Unit of measure: .1 Amp)"
              ::= { nrdbcmDataEntry 21 }

          nrdbcmBreaker1B18Current OBJECT-TYPE
              SYNTAX INTEGER (0..65535)
              ACCESS read-only
              STATUS mandatory
              DESCRIPTION
                      "The Current for Breaker 1B18.
                      (Unit of measure: .1 Amp)"
              ::= { nrdbcmDataEntry 22 }

          nrdbcmBreaker1A19Current OBJECT-TYPE
              SYNTAX INTEGER (0..65535)
              ACCESS read-only
              STATUS mandatory
              DESCRIPTION
                      "The Current for Breaker 1A19.
                      (Unit of measure: .1 Amp)"
              ::= { nrdbcmDataEntry 23 }

          nrdbcmBreaker1B20Current OBJECT-TYPE
              SYNTAX INTEGER (0..65535)
              ACCESS read-only
              STATUS mandatory
              DESCRIPTION
                      "The Current for Breaker 1B20.
                      (Unit of measure: .1 Amp)"
              ::= { nrdbcmDataEntry 24 }

          nrdbcmBreaker1A21Current OBJECT-TYPE
              SYNTAX INTEGER (0..65535)
              ACCESS read-only
              STATUS mandatory
              DESCRIPTION
                      "The Current for Breaker 1A21.
                      (Unit of measure: .1 Amp)"
              ::= { nrdbcmDataEntry 25 }

          nrdbcmBreaker1B22Current OBJECT-TYPE
              SYNTAX INTEGER (0..65535)
              ACCESS read-only
              STATUS mandatory
              DESCRIPTION
                      "The Current for Breaker 1B22.
                      (Unit of measure: .1 Amp)"
              ::= { nrdbcmDataEntry 26 }

          nrdbcmBreaker1A23Current OBJECT-TYPE
              SYNTAX INTEGER (0..65535)
              ACCESS read-only
              STATUS mandatory
              DESCRIPTION
                      "The Current for Breaker 1A23.
                      (Unit of measure: .1 Amp)"
              ::= { nrdbcmDataEntry 27 }

          nrdbcmBreaker1B24Current OBJECT-TYPE
              SYNTAX INTEGER (0..65535)
              ACCESS read-only
              STATUS mandatory
              DESCRIPTION
                      "The Current for Breaker 1B24.
                      (Unit of measure: .1 Amp)"
              ::= { nrdbcmDataEntry 28 }

          nrdbcmBreaker1A25Current OBJECT-TYPE
              SYNTAX INTEGER (0..65535)
              ACCESS read-only
              STATUS mandatory
              DESCRIPTION
                      "The Current for Breaker 1A25.
                      (Unit of measure: .1 Amp)"
              ::= { nrdbcmDataEntry 29 }

          nrdbcmBreaker1B26Current OBJECT-TYPE
              SYNTAX INTEGER (0..65535)
              ACCESS read-only
              STATUS mandatory
              DESCRIPTION
                      "The Current for Breaker 1B26.
                      (Unit of measure: .1 Amp)"
              ::= { nrdbcmDataEntry 30 }

          nrdbcmBreaker1A27Current OBJECT-TYPE
              SYNTAX INTEGER (0..65535)
              ACCESS read-only
              STATUS mandatory
              DESCRIPTION
                      "The Current for Breaker 1A27.
                      (Unit of measure: .1 Amp)"
              ::= { nrdbcmDataEntry 31 }

          nrdbcmBreaker1B28Current OBJECT-TYPE
              SYNTAX INTEGER (0..65535)
              ACCESS read-only
              STATUS mandatory
              DESCRIPTION
                      "The Current for Breaker 1B28.
                      (Unit of measure: .1 Amp)"
              ::= { nrdbcmDataEntry 32 }

          nrdbcmBreaker1A29Current OBJECT-TYPE
              SYNTAX INTEGER (0..65535)
              ACCESS read-only
              STATUS mandatory
              DESCRIPTION
                      "The Current for Breaker 1A29.
                      (Unit of measure: .1 Amp)"
              ::= { nrdbcmDataEntry 33 }

          nrdbcmBreaker1B30Current OBJECT-TYPE
              SYNTAX INTEGER (0..65535)
              ACCESS read-only
              STATUS mandatory
              DESCRIPTION
                      "The Current for Breaker 1B30.
                      (Unit of measure: .1 Amp)"
              ::= { nrdbcmDataEntry 34 }

          nrdbcmBreaker1A31Current OBJECT-TYPE
              SYNTAX INTEGER (0..65535)
              ACCESS read-only
              STATUS mandatory
              DESCRIPTION
                      "The Current for Breaker 1A31.
                      (Unit of measure: .1 Amp)"
              ::= { nrdbcmDataEntry 35 }

          nrdbcmBreaker1B32Current OBJECT-TYPE
              SYNTAX INTEGER (0..65535)
              ACCESS read-only
              STATUS mandatory
              DESCRIPTION
                      "The Current for Breaker 1B32.
                      (Unit of measure: .1 Amp)"
              ::= { nrdbcmDataEntry 36 }

          nrdbcmBreaker1A33Current OBJECT-TYPE
              SYNTAX INTEGER (0..65535)
              ACCESS read-only
              STATUS mandatory
              DESCRIPTION
                      "The Current for Breaker 1A33.
                      (Unit of measure: .1 Amp)"
              ::= { nrdbcmDataEntry 37 }
	
          nrdbcmBreaker1B34Current OBJECT-TYPE
              SYNTAX INTEGER (0..65535)
              ACCESS read-only
              STATUS mandatory
              DESCRIPTION
                      "The Current for Breaker 1B34.
                      (Unit of measure: .1 Amp)"
              ::= { nrdbcmDataEntry 38 }
	
          nrdbcmBreaker1A35Current OBJECT-TYPE
              SYNTAX INTEGER (0..65535)
              ACCESS read-only
              STATUS mandatory
              DESCRIPTION
                      "The Current for Breaker 1A35.
                      (Unit of measure: .1 Amp)"
              ::= { nrdbcmDataEntry 39 }
	
          nrdbcmBreaker1B36Current OBJECT-TYPE
              SYNTAX INTEGER (0..65535)
              ACCESS read-only
              STATUS mandatory
              DESCRIPTION
                      "The Current for Breaker 1B36.
                      (Unit of measure: .1 Amp)"
              ::= { nrdbcmDataEntry 40 }
	
          nrdbcmBreaker1A37Current OBJECT-TYPE
              SYNTAX INTEGER (0..65535)
              ACCESS read-only
              STATUS mandatory
              DESCRIPTION
                      "The Current for Breaker 1A37.
                      (Unit of measure: .1 Amp)"
              ::= { nrdbcmDataEntry 41 }
	
          nrdbcmBreaker1B38Current OBJECT-TYPE
              SYNTAX INTEGER (0..65535)
              ACCESS read-only
              STATUS mandatory
              DESCRIPTION
                      "The Current for Breaker 1B38.
                      (Unit of measure: .1 Amp)"
              ::= { nrdbcmDataEntry 42 }
	
          nrdbcmBreaker1A39Current OBJECT-TYPE
              SYNTAX INTEGER (0..65535)
              ACCESS read-only
              STATUS mandatory
              DESCRIPTION
                      "The Current for Breaker 1A39.
                      (Unit of measure: .1 Amp)"
              ::= { nrdbcmDataEntry 43 }
	
          nrdbcmBreaker1B40Current OBJECT-TYPE
              SYNTAX INTEGER (0..65535)
              ACCESS read-only
              STATUS mandatory
              DESCRIPTION
                      "The Current for Breaker 1B40.
                      (Unit of measure: .1 Amp)"
              ::= { nrdbcmDataEntry 44 }
	
          nrdbcmBreaker1A41Current OBJECT-TYPE
              SYNTAX INTEGER (0..65535)
              ACCESS read-only
              STATUS mandatory
              DESCRIPTION
                      "The Current for Breaker 1A41.
                      (Unit of measure: .1 Amp)"
              ::= { nrdbcmDataEntry 45 }
	
          nrdbcmBreaker1B42Current OBJECT-TYPE
              SYNTAX INTEGER (0..65535)
              ACCESS read-only
              STATUS mandatory
              DESCRIPTION
                      "The Current for Breaker 1B42.
                      (Unit of measure: .1 Amp)"
              ::= { nrdbcmDataEntry 46 }

          nrdbcmBreaker1A01Status OBJECT-TYPE
              SYNTAX INTEGER  {
                 currentOFF(0),
                 currentON(1),
                 highAlarm(2),
                 veryhighAlarm(3),
                 tripped(4)
              }
              ACCESS read-only
              STATUS mandatory
              DESCRIPTION
                      "The state for Breaker 1A01."
              ::= { nrdbcmDataEntry 47 }

          nrdbcmBreaker1B02Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B02."
              ::= { nrdbcmDataEntry 48 }

          nrdbcmBreaker1A03Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A03."
              ::= { nrdbcmDataEntry 49 }

          nrdbcmBreaker1B04Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B04."
              ::= { nrdbcmDataEntry 50 }

          nrdbcmBreaker1A05Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A05."
              ::= { nrdbcmDataEntry 51 }

          nrdbcmBreaker1B06Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B06."
              ::= { nrdbcmDataEntry 52 }

          nrdbcmBreaker1A07Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A07."
              ::= { nrdbcmDataEntry 53 }

          nrdbcmBreaker1B08Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B08."
              ::= { nrdbcmDataEntry 54 }

          nrdbcmBreaker1A09Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A09."
              ::= { nrdbcmDataEntry 55 }

          nrdbcmBreaker1B10Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B10."
              ::= { nrdbcmDataEntry 56 }

          nrdbcmBreaker1A11Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A11."
              ::= { nrdbcmDataEntry 57 }

          nrdbcmBreaker1B12Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B12."
              ::= { nrdbcmDataEntry 58 }

          nrdbcmBreaker1A13Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A13."
              ::= { nrdbcmDataEntry 59 }

          nrdbcmBreaker1B14Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B14."
              ::= { nrdbcmDataEntry 60 }

          nrdbcmBreaker1A15Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A15."
              ::= { nrdbcmDataEntry 61 }

          nrdbcmBreaker1B16Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B16."
              ::= { nrdbcmDataEntry 62 }

          nrdbcmBreaker1A17Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A17."
              ::= { nrdbcmDataEntry 63 }

          nrdbcmBreaker1B18Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B18."
              ::= { nrdbcmDataEntry 64 }

          nrdbcmBreaker1A19Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A19."
              ::= { nrdbcmDataEntry 65 }

          nrdbcmBreaker1B20Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B20."
              ::= { nrdbcmDataEntry 66 }

          nrdbcmBreaker1A21Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A21."
              ::= { nrdbcmDataEntry 67 }

          nrdbcmBreaker1B22Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B22."
              ::= { nrdbcmDataEntry 68 }

          nrdbcmBreaker1A23Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A23."
              ::= { nrdbcmDataEntry 69 }

          nrdbcmBreaker1B24Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B24."
              ::= { nrdbcmDataEntry 70 }

          nrdbcmBreaker1A25Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A25."
              ::= { nrdbcmDataEntry 71 }

          nrdbcmBreaker1B26Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B26."
              ::= { nrdbcmDataEntry 72 }

          nrdbcmBreaker1A27Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A27."
              ::= { nrdbcmDataEntry 73 }

          nrdbcmBreaker1B28Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B28."
              ::= { nrdbcmDataEntry 74 }

          nrdbcmBreaker1A29Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A29."
              ::= { nrdbcmDataEntry 75 }

          nrdbcmBreaker1B30Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B30."
              ::= { nrdbcmDataEntry 76 }

          nrdbcmBreaker1A31Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A31."
              ::= { nrdbcmDataEntry 77 }

          nrdbcmBreaker1B32Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B32."
              ::= { nrdbcmDataEntry 78 }

          nrdbcmBreaker1A33Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A33."
              ::= { nrdbcmDataEntry 79 }
	
          nrdbcmBreaker1B34Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B34."
              ::= { nrdbcmDataEntry 80 }
	
          nrdbcmBreaker1A35Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A35."
              ::= { nrdbcmDataEntry 81 }
	
          nrdbcmBreaker1B36Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B36."
              ::= { nrdbcmDataEntry 82 }
	
          nrdbcmBreaker1A37Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A37."
              ::= { nrdbcmDataEntry 83 }
	
          nrdbcmBreaker1B38Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B38."
              ::= { nrdbcmDataEntry 84 }
	
          nrdbcmBreaker1A39Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A39."
              ::= { nrdbcmDataEntry 85 }
	
          nrdbcmBreaker1B40Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B40."
              ::= { nrdbcmDataEntry 86 }
	
          nrdbcmBreaker1A41Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1A41."
              ::= { nrdbcmDataEntry 87 }
	
          nrdbcmBreaker1B42Status OBJECT-TYPE
              SYNTAX INTEGER  {
                 currentOFF(0),
                 currentON(1),
                 highAlarm(2),
                 veryhighAlarm(3),
                 tripped(4)
              }
              ACCESS read-only
              STATUS mandatory
              DESCRIPTION
                      "The Status for Breaker 1B42."
              ::= { nrdbcmDataEntry 88 }

         nrdbcmBreaker1A01Name OBJECT-TYPE
              SYNTAX DisplayString (SIZE (255))
              ACCESS read-only
              STATUS mandatory
              DESCRIPTION
                      "The Name for Breaker 1A01."
              ::= { nrdbcmDataEntry 89 }

         nrdbcmBreaker1B02Name OBJECT-TYPE
              SYNTAX DisplayString (SIZE (255))
              ACCESS read-only
              STATUS mandatory
              DESCRIPTION
                      "The Name for Breaker 1B02."
              ::= { nrdbcmDataEntry 90 }

         nrdbcmBreaker1A03Name OBJECT-TYPE
              SYNTAX DisplayString (SIZE (255))
              ACCESS read-only
              STATUS mandatory
              DESCRIPTION
                      "The Name for Breaker 1A03."
              ::= { nrdbcmDataEntry 91 }

         nrdbcmBreaker1B04Name OBJECT-TYPE
              SYNTAX DisplayString (SIZE (255))
              ACCESS read-only
              STATUS mandatory
              DESCRIPTION
                      "The Name for Breaker 1B04."
              ::= { nrdbcmDataEntry 92 }

         nrdbcmBreaker1A05Name OBJECT-TYPE
              SYNTAX DisplayString (SIZE (255))
              ACCESS read-only
              STATUS mandatory
              DESCRIPTION
                      "The Name for Breaker 1A05."
              ::= { nrdbcmDataEntry 93 }

         nrdbcmBreaker1B06Name OBJECT-TYPE
              SYNTAX DisplayString (SIZE (255))
              ACCESS read-only
              STATUS mandatory
              DESCRIPTION
                      "The Name for Breaker 1B06."
              ::= { nrdbcmDataEntry 94 }

         nrdbcmBreaker1A07Name OBJECT-TYPE
              SYNTAX DisplayString (SIZE (255))
              ACCESS read-only
              STATUS mandatory
              DESCRIPTION
                      "The Name for Breaker 1A07."
              ::= { nrdbcmDataEntry 95 }

         nrdbcmBreaker1B08Name OBJECT-TYPE
              SYNTAX DisplayString (SIZE (255))
              ACCESS read-only
              STATUS mandatory
              DESCRIPTION
                      "The Name for Breaker 1B08."
              ::= { nrdbcmDataEntry 96 }

         nrdbcmBreaker1A09Name OBJECT-TYPE
              SYNTAX DisplayString (SIZE (255))
              ACCESS read-only
              STATUS mandatory
              DESCRIPTION
                      "The Name for Breaker 1A09."
              ::= { nrdbcmDataEntry 97 }

         nrdbcmBreaker1B10Name OBJECT-TYPE
              SYNTAX DisplayString (SIZE (255))
              ACCESS read-only
              STATUS mandatory
              DESCRIPTION
                      "The Name for Breaker 1B10."
              ::= { nrdbcmDataEntry 98 }

         nrdbcmBreaker1A11Name OBJECT-TYPE
              SYNTAX DisplayString (SIZE (255))
              ACCESS read-only
              STATUS mandatory
              DESCRIPTION
                      "The Name for Breaker 1A11."
              ::= { nrdbcmDataEntry 99 }

         nrdbcmBreaker1B12Name OBJECT-TYPE
              SYNTAX DisplayString (SIZE (255))
              ACCESS read-only
              STATUS mandatory
              DESCRIPTION
                      "The Name for Breaker 1B12."
              ::= { nrdbcmDataEntry 100 }

         nrdbcmBreaker1A13Name OBJECT-TYPE
              SYNTAX DisplayString (SIZE (255))
              ACCESS read-only
              STATUS mandatory
              DESCRIPTION
                      "The Name for Breaker 1A13."
              ::= { nrdbcmDataEntry 101 }

         nrdbcmBreaker1B14Name OBJECT-TYPE
              SYNTAX DisplayString (SIZE (255))
              ACCESS read-only
              STATUS mandatory
              DESCRIPTION
                      "The Name for Breaker 1B14."
              ::= { nrdbcmDataEntry 102 }

         nrdbcmBreaker1A15Name OBJECT-TYPE
              SYNTAX DisplayString (SIZE (255))
              ACCESS read-only
              STATUS mandatory
              DESCRIPTION
                      "The Name for Breaker 1A15."
              ::= { nrdbcmDataEntry 103 }

         nrdbcmBreaker1B16Name OBJECT-TYPE
              SYNTAX DisplayString (SIZE (255))
              ACCESS read-only
              STATUS mandatory
              DESCRIPTION
                      "The Name for Breaker 1B16."
              ::= { nrdbcmDataEntry 104 }

         nrdbcmBreaker1A17Name OBJECT-TYPE
              SYNTAX DisplayString (SIZE (255))
              ACCESS read-only
              STATUS mandatory
              DESCRIPTION
                      "The Name for Breaker 1A17."
              ::= { nrdbcmDataEntry 105 }

         nrdbcmBreaker1B18Name OBJECT-TYPE
              SYNTAX DisplayString (SIZE (255))
              ACCESS read-only
              STATUS mandatory
              DESCRIPTION
                      "The Name for Breaker 1B18."
              ::= { nrdbcmDataEntry 106 }

         nrdbcmBreaker1A19Name OBJECT-TYPE
              SYNTAX DisplayString (SIZE (255))
              ACCESS read-only
              STATUS mandatory
              DESCRIPTION
                      "The Name for Breaker 1A19."
              ::= { nrdbcmDataEntry 107 }

         nrdbcmBreaker1B20Name OBJECT-TYPE
              SYNTAX DisplayString (SIZE (255))
              ACCESS read-only
              STATUS mandatory
              DESCRIPTION
                      "The Name for Breaker 1B20."
              ::= { nrdbcmDataEntry 108 }

         nrdbcmBreaker1A21Name OBJECT-TYPE
              SYNTAX DisplayString (SIZE (255))
              ACCESS read-only
              STATUS mandatory
              DESCRIPTION
                      "The Name for Breaker 1A21."
              ::= { nrdbcmDataEntry 109 }

         nrdbcmBreaker1B22Name OBJECT-TYPE
              SYNTAX DisplayString (SIZE (255))
              ACCESS read-only
              STATUS mandatory
              DESCRIPTION
                      "The Name for Breaker 1B22."
              ::= { nrdbcmDataEntry 110 }

         nrdbcmBreaker1A23Name OBJECT-TYPE
              SYNTAX DisplayString (SIZE (255))
              ACCESS read-only
              STATUS mandatory
              DESCRIPTION
                      "The Name for Breaker 1A23."
              ::= { nrdbcmDataEntry 111 }

         nrdbcmBreaker1B24Name OBJECT-TYPE
              SYNTAX DisplayString (SIZE (255))
              ACCESS read-only
              STATUS mandatory
              DESCRIPTION
                      "The Name for Breaker 1B24."
              ::= { nrdbcmDataEntry 112 }

         nrdbcmBreaker1A25Name OBJECT-TYPE
              SYNTAX DisplayString (SIZE (255))
              ACCESS read-only
              STATUS mandatory
              DESCRIPTION
                      "The Name for Breaker 1A25."
              ::= { nrdbcmDataEntry 113 }

         nrdbcmBreaker1B26Name OBJECT-TYPE
              SYNTAX DisplayString (SIZE (255))
              ACCESS read-only
              STATUS mandatory
              DESCRIPTION
                      "The Name for Breaker 1B26."
              ::= { nrdbcmDataEntry 114 }

         nrdbcmBreaker1A27Name OBJECT-TYPE
              SYNTAX DisplayString (SIZE (255))
              ACCESS read-only
              STATUS mandatory
              DESCRIPTION
                      "The Name for Breaker 1A27."
              ::= { nrdbcmDataEntry 115 }

         nrdbcmBreaker1B28Name OBJECT-TYPE
              SYNTAX DisplayString (SIZE (255))
              ACCESS read-only
              STATUS mandatory
              DESCRIPTION
                      "The Name for Breaker 1B28."
              ::= { nrdbcmDataEntry 116 }

         nrdbcmBreaker1A29Name OBJECT-TYPE
              SYNTAX DisplayString (SIZE (255))
              ACCESS read-only
              STATUS mandatory
              DESCRIPTION
                      "The Name for Breaker 1A29."
              ::= { nrdbcmDataEntry 117 }

         nrdbcmBreaker1B30Name OBJECT-TYPE
              SYNTAX DisplayString (SIZE (255))
              ACCESS read-only
              STATUS mandatory
              DESCRIPTION
                      "The Name for Breaker 1B30."
              ::= { nrdbcmDataEntry 118 }

         nrdbcmBreaker1A31Name OBJECT-TYPE
              SYNTAX DisplayString (SIZE (255))
              ACCESS read-only
              STATUS mandatory
              DESCRIPTION
                      "The Name for Breaker 1A31."
              ::= { nrdbcmDataEntry 119 }

         nrdbcmBreaker1B32Name OBJECT-TYPE
              SYNTAX DisplayString (SIZE (255))
              ACCESS read-only
              STATUS mandatory
              DESCRIPTION
                      "The Name for Breaker 1B32."
              ::= { nrdbcmDataEntry 120 }

         nrdbcmBreaker1A33Name OBJECT-TYPE
              SYNTAX DisplayString (SIZE (255))
              ACCESS read-only
              STATUS mandatory
              DESCRIPTION
                      "The Name for Breaker 1A33."
              ::= { nrdbcmDataEntry 121 }

         nrdbcmBreaker1B34Name OBJECT-TYPE
              SYNTAX DisplayString (SIZE (255))
              ACCESS read-only
              STATUS mandatory
              DESCRIPTION
                      "The Name for Breaker 1B34."
              ::= { nrdbcmDataEntry 122 }

         nrdbcmBreaker1A35Name OBJECT-TYPE
              SYNTAX DisplayString (SIZE (255))
              ACCESS read-only
              STATUS mandatory
              DESCRIPTION
                      "The Name for Breaker 1A35."
              ::= { nrdbcmDataEntry 123 }

         nrdbcmBreaker1B36Name OBJECT-TYPE
              SYNTAX DisplayString (SIZE (255))
              ACCESS read-only
              STATUS mandatory
              DESCRIPTION
                      "The Name for Breaker 1B36."
              ::= { nrdbcmDataEntry 124 }

         nrdbcmBreaker1A37Name OBJECT-TYPE
              SYNTAX DisplayString (SIZE (255))
              ACCESS read-only
              STATUS mandatory
              DESCRIPTION
                      "The Name for Breaker 1A37."
              ::= { nrdbcmDataEntry 125 }

         nrdbcmBreaker1B38Name OBJECT-TYPE
              SYNTAX DisplayString (SIZE (255))
              ACCESS read-only
              STATUS mandatory
              DESCRIPTION
                      "The Name for Breaker 1B38."
              ::= { nrdbcmDataEntry 126 }

         nrdbcmBreaker1A39Name OBJECT-TYPE
              SYNTAX DisplayString (SIZE (255))
              ACCESS read-only
              STATUS mandatory
              DESCRIPTION
                      "The Name for Breaker 1A39."
              ::= { nrdbcmDataEntry 127 }

         nrdbcmBreaker1B40Name OBJECT-TYPE
              SYNTAX DisplayString (SIZE (255))
              ACCESS read-only
              STATUS mandatory
              DESCRIPTION
                      "The Name for Breaker 1B40."
              ::= { nrdbcmDataEntry 128 }

         nrdbcmBreaker1A41Name OBJECT-TYPE
              SYNTAX DisplayString (SIZE (255))
              ACCESS read-only
              STATUS mandatory
              DESCRIPTION
                      "The Name for Breaker 1A41."
              ::= { nrdbcmDataEntry 129 }

         nrdbcmBreaker1B42Name OBJECT-TYPE
              SYNTAX DisplayString (SIZE (255))
              ACCESS read-only
              STATUS mandatory
              DESCRIPTION
                      "The Name for Breaker 1B42."
              ::= { nrdbcmDataEntry 130 }




--
--  The PWRM BCM traps
--
          nrdbcmtraps        OBJECT IDENTIFIER ::= { nrdPWRM 3 }

nrdbcmDeviceOnline TRAP-TYPE
			ENTERPRISE	niobrara
			VARIABLES  	{ ntrapargsString }
			DESCRIPTION
			"The QUCM has established communication with the meter."

			::= 1
	
nrdbcmDeviceOffline TRAP-TYPE
			ENTERPRISE	niobrara
			VARIABLES  	{ ntrapargsString }
			DESCRIPTION
			"The QUCM has lost communication with the meter."

			::= 2


nrdbcmTrip TRAP-TYPE
   			ENTERPRISE niobrara
   			VARIABLES { ntrapargsInteger, ntrapargsString }
   			DESCRIPTION
      			"INFORMATION: An alarm condition has been detected.
       			The first variable is the fault condition."
   			::= 3

nrdbcmAlarmConditionCleared TRAP-TYPE
   			ENTERPRISE niobrara
   			VARIABLES { ntrapargsInteger, ntrapargsString }
   			DESCRIPTION
      			"INFORMATION: An alarm condition has been cleared.
      			The first variable is the fault condition."
   			::= 4




	END
