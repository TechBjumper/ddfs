RPDU DEFINITIONS ::= BEGIN

IMPORTS

DisplayString                                                   FROM SNMPv2-TC
MODULE-IDENTITY, OBJECT-TYPE,enterprises,Integer32,NOTIFICATION-TYPE FROM SNMPv2-SMI;

RPDU MODULE-IDENTITY
	LAST-UPDATED "xxx"
	ORGANIZATION "xxx"
	CONTACT-INFO "xxx"
	DESCRIPTION "xxx"
	::= {enterprises 30966 }


PDUSys OBJECT IDENTIFIER ::= { enterprises 30966 }
rpdu OBJECT IDENTIFIER ::= { PDUSys 6}  

-------------------------------master---------------------------------------------
rpduDeviceOne OBJECT IDENTIFIER ::= { rpdu 1}
rpdumaster OBJECT IDENTIFIER ::= { rpduDeviceOne 1}

masterName OBJECT-TYPE
    SYNTAX      DisplayString
    MAX-ACCESS  read-write
    STATUS      current
    DESCRIPTION
	"This is the first device."
    ::= { rpdumaster 1}
    
masterType OBJECT-TYPE
    SYNTAX      DisplayString
    MAX-ACCESS  read-only
    STATUS      current
    DESCRIPTION
	"This is device type "
    ::= { rpdumaster 2}
    
masterOutputNumber OBJECT-TYPE 
    SYNTAX      Integer32
    MAX-ACCESS  read-only
    STATUS      current
    DESCRIPTION
	"This is the output quantity"
::= { rpdumaster 7}
    
masterLineOne OBJECT IDENTIFIER ::= { rpdumaster 3}
masterLineOnePower OBJECT-TYPE
    SYNTAX      DisplayString
    MAX-ACCESS  read-only
    STATUS      current
    DESCRIPTION
	"The power of phase one"
    ::= { masterLineOne 1}
masterLineOnePF OBJECT-TYPE
    SYNTAX      DisplayString
    MAX-ACCESS  read-only
    STATUS      current
    DESCRIPTION
	"The power factor of phase one"
    ::= { masterLineOne 2}
    
masterLineOneEnergy OBJECT-TYPE
    SYNTAX      DisplayString
    MAX-ACCESS  read-only
    STATUS      current
    DESCRIPTION
	"The energy of phase one"
    ::= { masterLineOne 3}
masterLineOneCurrent OBJECT-TYPE
    SYNTAX      DisplayString
    MAX-ACCESS  read-only
    STATUS      current
    DESCRIPTION
	"The current of phase one"
    ::= { masterLineOne 4}
masterLineOneVoltage OBJECT-TYPE
    SYNTAX      Integer32
    MAX-ACCESS  read-only
    STATUS      current
    DESCRIPTION
	"The voltage of phase one"
    ::= { masterLineOne 5}
masterLineOneCurrentMin OBJECT-TYPE
    SYNTAX      DisplayString
    MAX-ACCESS  read-only
    STATUS      current
    DESCRIPTION
	"The Min. current value of phase one"
	::= { masterLineOne 6}
masterLineOneCurrentMax OBJECT-TYPE
    SYNTAX      DisplayString
    MAX-ACCESS  read-only
    STATUS      current
    DESCRIPTION
	"The Max. current value of phase one"
    ::= { masterLineOne 7}
    
masterLineOneVoltageMin OBJECT-TYPE
    SYNTAX      Integer32
    MAX-ACCESS  read-only
    STATUS      current
    DESCRIPTION
	"The Min. voltage value of phase one"
    ::= { masterLineOne 8}
    
masterLineOneVoltageMax OBJECT-TYPE
    SYNTAX      Integer32
    MAX-ACCESS  read-only
    STATUS      current
    DESCRIPTION
	"The Max. voltage value of phase one"
    ::= { masterLineOne 9}


masterLineTwo OBJECT IDENTIFIER ::= { rpdumaster 4}
masterLineTwoPower OBJECT-TYPE
    SYNTAX      DisplayString
    MAX-ACCESS  read-only
    STATUS      current
    DESCRIPTION
	"The power of phase two"
    ::= { masterLineTwo 1}

masterLineTwoPF OBJECT-TYPE
    SYNTAX      DisplayString
    MAX-ACCESS  read-only
    STATUS      current
    DESCRIPTION
	"The power factor of phase two"   
    ::= { masterLineTwo 2}
    
masterLineTwoEnergy OBJECT-TYPE
    SYNTAX      DisplayString
    MAX-ACCESS  read-only
    STATUS      current
    DESCRIPTION
	"The energy of phase two"
    ::= { masterLineTwo 3}
masterLineTwoCurrent OBJECT-TYPE           
    SYNTAX      DisplayString
    MAX-ACCESS  read-only
    STATUS      current
    DESCRIPTION
	"The current of phase two"
    ::= { masterLineTwo 4}
masterLineTwoVoltage OBJECT-TYPE
    SYNTAX      Integer32
    MAX-ACCESS  read-only
    STATUS      current
    DESCRIPTION
	"The voltage of phase two"
    ::= { masterLineTwo 5}
masterLineTwoCurrentMin OBJECT-TYPE
    SYNTAX      DisplayString
    MAX-ACCESS  read-only
    STATUS      current
    DESCRIPTION
	"The Min. current value of phase two"
    ::= { masterLineTwo 6}
masterLineTwoCurrentMax OBJECT-TYPE
    SYNTAX      DisplayString
    MAX-ACCESS  read-only
    STATUS      current
    DESCRIPTION
	"The Max. current value of phase two"
    ::= { masterLineTwo 7}
    
masterLineTwoVoltageMin OBJECT-TYPE
    SYNTAX      Integer32
    MAX-ACCESS  read-only
    STATUS      current
    DESCRIPTION
	"The Min. voltage value of phase two"
    ::= { masterLineTwo 8}
    
masterLineTwoVoltageMax OBJECT-TYPE
    SYNTAX      Integer32
    MAX-ACCESS  read-only
    STATUS      current
    DESCRIPTION
	"The Max. voltage value of phase two"
    ::= { masterLineTwo 9}



masterLineThree OBJECT IDENTIFIER ::= { rpdumaster 5}
masterLineThreePower OBJECT-TYPE
    SYNTAX      DisplayString
    MAX-ACCESS  read-only
    STATUS      current
    DESCRIPTION
	"The power of phase three"
    ::= { masterLineThree 1}

masterLineThreePF OBJECT-TYPE
    SYNTAX      DisplayString
    MAX-ACCESS  read-only
    STATUS      current
    DESCRIPTION
	"The power factor of phase three"     
    ::= { masterLineThree 2}
    
masterLineThreeEnergy OBJECT-TYPE
    SYNTAX      DisplayString
    MAX-ACCESS  read-only
    STATUS      current
    DESCRIPTION
	"The energy of phase three"
    ::= { masterLineThree 3}
masterLineThreeCurrent OBJECT-TYPE
    SYNTAX      DisplayString
    MAX-ACCESS  read-only
    STATUS      current
    DESCRIPTION
	"The current of phase three"
    ::= { masterLineThree 4}
masterLineThreeVoltage OBJECT-TYPE
    SYNTAX      Integer32
    MAX-ACCESS  read-only
    STATUS      current
    DESCRIPTION
	"The voltage of phase three"
    ::= { masterLineThree 5}
masterLineThreeCurrentMin OBJECT-TYPE
    SYNTAX      DisplayString
    MAX-ACCESS  read-only
    STATUS      current
    DESCRIPTION
	"The Min. current value of phase three"
    ::= { masterLineThree 6}
masterLineThreeCurrentMax OBJECT-TYPE
    SYNTAX      DisplayString
    MAX-ACCESS  read-only
    STATUS      current
    DESCRIPTION
	"The Max. current value of phase three"
    ::= { masterLineThree 7}
    
masterLineThreeVoltageMin OBJECT-TYPE
    SYNTAX      Integer32
    MAX-ACCESS  read-only
    STATUS      current
    DESCRIPTION
	"The Min. voltage value of phase three"
    ::= { masterLineThree 8}
    
masterLineThreeVoltageMax OBJECT-TYPE
    SYNTAX      Integer32
    MAX-ACCESS  read-only
    STATUS      current
    DESCRIPTION
	"The Max. voltage value of phase three"
    ::= { masterLineThree 9}


masterSensor OBJECT IDENTIFIER ::= { rpdumaster 6}
masterTempOne OBJECT-TYPE
    SYNTAX      Integer32
    MAX-ACCESS  read-only
    STATUS      current
    DESCRIPTION
	"The first temperature sensor of master"
    ::= { masterSensor 1}
masterTempTwo OBJECT-TYPE
    SYNTAX      Integer32
    MAX-ACCESS  read-only
    STATUS      current
    DESCRIPTION
	"The second temperature sensor of master"
    ::= { masterSensor 2}
masterTempThree OBJECT-TYPE
    SYNTAX      Integer32
    MAX-ACCESS  read-only
    STATUS      current
    DESCRIPTION
	"The third temperature sensor of master"
    ::= { masterSensor 3}
masterTempFour OBJECT-TYPE
    SYNTAX      Integer32
    MAX-ACCESS  read-only
    STATUS      current
    DESCRIPTION
	"The fourth temperature sensor of master"
    ::= { masterSensor 4}
masterHumOne OBJECT-TYPE
    SYNTAX      Integer32
    MAX-ACCESS  read-only
    STATUS      current
    DESCRIPTION
	"The first humidity sensor of master"
    ::= { masterSensor 5}
masterHumTwo OBJECT-TYPE
    SYNTAX      Integer32
    MAX-ACCESS  read-only
    STATUS      current
    DESCRIPTION
	"The second humidity sensor of master"
    ::= { masterSensor 6}
masterHumThree OBJECT-TYPE
    SYNTAX      Integer32
    MAX-ACCESS  read-only
    STATUS      current
    DESCRIPTION
	"The third humidity sensor of master"
    ::= { masterSensor 7}
masterHumFour OBJECT-TYPE
    SYNTAX      Integer32
    MAX-ACCESS  read-only
    STATUS      current
    DESCRIPTION
	"The fourth humidity sensor of master"
    ::= { masterSensor 8}
masterDoorOne OBJECT-TYPE
    SYNTAX      DisplayString
    MAX-ACCESS  read-only
    STATUS      current
    DESCRIPTION
	"The first door sensor of master"    
    ::= { masterSensor 9}
masterDoorTwo OBJECT-TYPE
    SYNTAX      DisplayString
    MAX-ACCESS  read-only
    STATUS      current
    DESCRIPTION
	"The second door sensor of master"  
    ::= { masterSensor 10}
masterSmoke OBJECT-TYPE
    SYNTAX      DisplayString
    MAX-ACCESS  read-only
    STATUS      current
    DESCRIPTION
	"The smoke sensor of master"
    ::= { masterSensor 11}
masterWater OBJECT-TYPE
    SYNTAX      DisplayString
    MAX-ACCESS  read-only
    STATUS      current
    DESCRIPTION
	"The water sensor of master"
    ::= { masterSensor 12}


	
        
masterOutputName OBJECT IDENTIFIER ::= { rpdumaster 8}
masterOutputNameOne OBJECT-TYPE
    SYNTAX      DisplayString
    MAX-ACCESS  read-write
    STATUS      current
    DESCRIPTION
	"The first output name of master"
    ::= { masterOutputName 1}

masterOutputNameTwo OBJECT-TYPE
    SYNTAX      DisplayString
    MAX-ACCESS  read-write
    STATUS      current
    DESCRIPTION
	"The second output name of master"
    ::= { masterOutputName 2}
masterOutputNameThree OBJECT-TYPE
    SYNTAX      DisplayString
    MAX-ACCESS  read-write
    STATUS      current
    DESCRIPTION
	"The third output name of master"
    ::= { masterOutputName 3}
masterOutputNameFour OBJECT-TYPE
    SYNTAX      DisplayString
    MAX-ACCESS  read-write
    STATUS      current
    DESCRIPTION
	"The fourth output name of master"
    ::= { masterOutputName 4}
masterOutputNameFive OBJECT-TYPE
    SYNTAX      DisplayString
    MAX-ACCESS  read-write
    STATUS      current
    DESCRIPTION
	"The fifth output name of master"
    ::= { masterOutputName 5}
masterOutputNameSix OBJECT-TYPE
    SYNTAX      DisplayString
    MAX-ACCESS  read-write
    STATUS      current
    DESCRIPTION
	"The sixth output name of master"
    ::= { masterOutputName 6}
masterOutputNameSeven OBJECT-TYPE
    SYNTAX      DisplayString
    MAX-ACCESS  read-write
    STATUS      current
    DESCRIPTION
	"The seventh output name of master"
    ::= { masterOutputName 7}
masterOutputNameEight OBJECT-TYPE
    SYNTAX      DisplayString
    MAX-ACCESS  read-write
    STATUS      current
    DESCRIPTION
	"The eighth output name of master"
    ::= { masterOutputName 8}
masterOutputNameNine OBJECT-TYPE
    SYNTAX      DisplayString
    MAX-ACCESS  read-write
    STATUS      current
    DESCRIPTION
	"The nineth output name of master"
    ::= { masterOutputName 9}
masterOutputNameTen OBJECT-TYPE
    SYNTAX      DisplayString
    MAX-ACCESS  read-write
    STATUS      current
    DESCRIPTION
	"The tenth output name of master"
    ::= { masterOutputName 10}
masterOutputNameEleven OBJECT-TYPE
    SYNTAX      DisplayString
    MAX-ACCESS  read-write
    STATUS      current
    DESCRIPTION
	"The eleventh output name of master"
    ::= { masterOutputName 11}
masterOutputNameTwelve OBJECT-TYPE
    SYNTAX      DisplayString
    MAX-ACCESS  read-write
    STATUS      current
    DESCRIPTION
	"The twelfth output name of master"
    ::= { masterOutputName 12}
masterOutputNameThirteen OBJECT-TYPE
    SYNTAX      DisplayString
    MAX-ACCESS  read-write
    STATUS      current
    DESCRIPTION
	"The thirteenth output name of master"
    ::= { masterOutputName 13}
masterOutputNameFourteen OBJECT-TYPE
    SYNTAX      DisplayString
    MAX-ACCESS  read-write
    STATUS      current
    DESCRIPTION
	"The fourteenth output name of master"
    ::= { masterOutputName 14}
masterOutputNameFifteen OBJECT-TYPE
    SYNTAX      DisplayString
    MAX-ACCESS  read-write
    STATUS      current
    DESCRIPTION
	"The fifteenth output name of master"
    ::= { masterOutputName 15}
masterOutputNameSixteen OBJECT-TYPE
    SYNTAX      DisplayString
    MAX-ACCESS  read-write
    STATUS      current
    DESCRIPTION
	"The sixteenth output name of master"
    ::= { masterOutputName 16}
masterOutputNameSeventeen OBJECT-TYPE
    SYNTAX      DisplayString
    MAX-ACCESS  read-write
    STATUS      current
    DESCRIPTION
	"The seventeenth output name of master"
    ::= { masterOutputName 17}
masterOutputNameEighteen OBJECT-TYPE
    SYNTAX      DisplayString
    MAX-ACCESS  read-write
    STATUS      current
    DESCRIPTION
	"The eighteenh output name of master"
    ::= { masterOutputName 18}
masterOutputNameNineteen OBJECT-TYPE
    SYNTAX      DisplayString
    MAX-ACCESS  read-write
    STATUS      current
    DESCRIPTION
	"The nineteenth output name of master"
    ::= { masterOutputName 19}
masterOutputNameTwenty OBJECT-TYPE
    SYNTAX      DisplayString
    MAX-ACCESS  read-write
    STATUS      current
    DESCRIPTION
	"The twentieth output name of master"
    ::= { masterOutputName 20}
masterOutputNameTwentyOne OBJECT-TYPE
    SYNTAX      DisplayString
    MAX-ACCESS  read-write
    STATUS      current
    DESCRIPTION
	"The twenty-first output name of master"
    ::= { masterOutputName 21}
masterOutputNameTwentyTwo OBJECT-TYPE
    SYNTAX      DisplayString
    MAX-ACCESS  read-write
    STATUS      current
    DESCRIPTION
	"The twenty-second output name of master"
    ::= { masterOutputName 22}
masterOutputNameTwentyThree OBJECT-TYPE
    SYNTAX      DisplayString
    MAX-ACCESS  read-write
    STATUS      current
    DESCRIPTION
	"The twenty-third output name of master"
    ::= { masterOutputName 23}
masterOutputNameTwentyFour OBJECT-TYPE
    SYNTAX      DisplayString
    MAX-ACCESS  read-write
    STATUS      current
    DESCRIPTION
	"The twenty-fourth output name of master"
    ::= { masterOutputName 24}


    
masterOutputStatus OBJECT IDENTIFIER ::= { rpdumaster 9}

masterOutputStatusOne OBJECT-TYPE
    SYNTAX      DisplayString
    MAX-ACCESS  read-write
    STATUS      current
    DESCRIPTION
	"The first output status of master"
    ::= { masterOutputStatus 1}
masterOutputStatusTwo OBJECT-TYPE
    SYNTAX      DisplayString
    MAX-ACCESS  read-write
    STATUS      current
    DESCRIPTION
	"The second output status of master"
    ::= { masterOutputStatus 2}

masterOutputStatusThree OBJECT-TYPE
    SYNTAX      DisplayString
    MAX-ACCESS  read-write
    STATUS      current
    DESCRIPTION
	"The third output status of master"
    ::= { masterOutputStatus 3}
masterOutputStatusFour OBJECT-TYPE
    SYNTAX      DisplayString
    MAX-ACCESS  read-write
    STATUS      current
    DESCRIPTION
	"The fourth output status of master"
    ::= { masterOutputStatus 4}
masterOutputStatusFive OBJECT-TYPE
    SYNTAX      DisplayString
    MAX-ACCESS  read-write
    STATUS      current
    DESCRIPTION
	"The fifth output status of master"
    ::= { masterOutputStatus 5}
masterOutputStatusSix OBJECT-TYPE
    SYNTAX      DisplayString
    MAX-ACCESS  read-write
    STATUS      current
    DESCRIPTION
	"The sixth output status of master"
    ::= { masterOutputStatus 6}
masterOutputStatusSeven OBJECT-TYPE
    SYNTAX      DisplayString
    MAX-ACCESS  read-write
    STATUS      current
    DESCRIPTION
	"The seventh output status of master"
    ::= { masterOutputStatus 7}
masterOutputStatusEight OBJECT-TYPE
    SYNTAX      DisplayString
    MAX-ACCESS  read-write
    STATUS      current
    DESCRIPTION
	"The eighth output status of master"
    ::= { masterOutputStatus 8}
masterOutputStatusNine OBJECT-TYPE
    SYNTAX      DisplayString
    MAX-ACCESS  read-write
    STATUS      current
    DESCRIPTION
	"The nineth output status of master"
    ::= { masterOutputStatus 9}
masterOutputStatusTen OBJECT-TYPE
    SYNTAX      DisplayString
    MAX-ACCESS  read-write
    STATUS      current
    DESCRIPTION
	"The tenth output status of master"
    ::= { masterOutputStatus 10}
masterOutputStatusEleven OBJECT-TYPE
    SYNTAX      DisplayString
    MAX-ACCESS  read-write
    STATUS      current
    DESCRIPTION
	"The eleventh output status of master"
    ::= { masterOutputStatus 11}
masterOutputStatusTwelve OBJECT-TYPE
    SYNTAX      DisplayString
    MAX-ACCESS  read-write
    STATUS      current
    DESCRIPTION
	"The twelfth output status of master"
    ::= { masterOutputStatus 12}
masterOutputStatusThirteen OBJECT-TYPE
    SYNTAX      DisplayString
    MAX-ACCESS  read-write
    STATUS      current
    DESCRIPTION
	"The thirteenth output status of master"
    ::= { masterOutputStatus 13}
masterOutputStatusFourteen OBJECT-TYPE
    SYNTAX      DisplayString
    MAX-ACCESS  read-write
    STATUS      current
    DESCRIPTION
	"The fourteenth output status of master"
    ::= { masterOutputStatus 14}
masterOutputStatusFifteen OBJECT-TYPE
    SYNTAX      DisplayString
    MAX-ACCESS  read-write
    STATUS      current
    DESCRIPTION
	"The fifteenth output status of master"
    ::= { masterOutputStatus 15}
masterOutputStatusSixteen OBJECT-TYPE
    SYNTAX      DisplayString
    MAX-ACCESS  read-write
    STATUS      current
    DESCRIPTION
	"The sixteenth output status of master"
    ::= { masterOutputStatus 16}
masterOutputStatusSeventeen OBJECT-TYPE
    SYNTAX      DisplayString
    MAX-ACCESS  read-write
    STATUS      current
    DESCRIPTION
	"The seventeenth output status of master"
    ::= { masterOutputStatus 17}
masterOutputStatusEighteen OBJECT-TYPE
    SYNTAX      DisplayString
    MAX-ACCESS  read-write
    STATUS      current
    DESCRIPTION
	"The eighteenth output status of master"
    ::= { masterOutputStatus 18}
masterOutputStatusNineteen OBJECT-TYPE
    SYNTAX      DisplayString
    MAX-ACCESS  read-write
    STATUS      current
    DESCRIPTION
	"The nineteenth output status of master"
    ::= { masterOutputStatus 19}
masterOutputStatusTwenty OBJECT-TYPE
    SYNTAX      DisplayString
    MAX-ACCESS  read-write
    STATUS      current
    DESCRIPTION
	"The twentieth output status of master"
    ::= { masterOutputStatus 20}
masterOutputStatusTwentyOne OBJECT-TYPE
    SYNTAX      DisplayString
    MAX-ACCESS  read-write
    STATUS      current
    DESCRIPTION
	"The twenty-first output status of master"
    ::= { masterOutputStatus 21}
masterOutputStatusTwentyTwo OBJECT-TYPE
    SYNTAX      DisplayString
    MAX-ACCESS  read-write
    STATUS      current
    DESCRIPTION
	"The twenty-second output status of master"
    ::= { masterOutputStatus 22}
masterOutputStatusTwentyThree OBJECT-TYPE
    SYNTAX      DisplayString
    MAX-ACCESS  read-write
    STATUS      current
    DESCRIPTION
	"The twenty-third output status of master"
    ::= { masterOutputStatus 23}
masterOutputStatusTwentyFour OBJECT-TYPE
    SYNTAX      DisplayString
    MAX-ACCESS  read-write
    STATUS      current
    DESCRIPTION
	"The twenty-fourth output status of master"
    ::= { masterOutputStatus 24}

masterOutputCurrent   OBJECT IDENTIFIER ::= { rpdumaster 10}
masterOutputCurrentOne OBJECT-TYPE
    SYNTAX      DisplayString
    MAX-ACCESS  read-only
    STATUS      current
    DESCRIPTION
	"The current value of the master's first output"
    ::= { masterOutputCurrent 1}
masterOutputCurrentTwo OBJECT-TYPE
    SYNTAX      DisplayString
    MAX-ACCESS  read-only
    STATUS      current
    DESCRIPTION
	"The current value of the master's second output"
    ::= { masterOutputCurrent 2}
masterOutputCurrentThree OBJECT-TYPE
    SYNTAX      DisplayString
    MAX-ACCESS  read-only
    STATUS      current
    DESCRIPTION
	"The current value of the master's third output"
    ::= { masterOutputCurrent 3}
masterOutputCurrentFour OBJECT-TYPE
    SYNTAX      DisplayString
    MAX-ACCESS  read-only
    STATUS      current
    DESCRIPTION
	"The current value of the master's fourth output"
    ::= { masterOutputCurrent 4}
masterOutputCurrentFive OBJECT-TYPE
    SYNTAX      DisplayString
    MAX-ACCESS  read-only
    STATUS      current
    DESCRIPTION
	"The current value of the master's fifth output"
    ::= { masterOutputCurrent 5}
masterOutputCurrentSix OBJECT-TYPE
    SYNTAX      DisplayString
    MAX-ACCESS  read-only
    STATUS      current
    DESCRIPTION
	"The current value of the master's sixth output"
    ::= { masterOutputCurrent 6}
masterOutputCurrentSeven OBJECT-TYPE
    SYNTAX      DisplayString
    MAX-ACCESS  read-only
    STATUS      current
    DESCRIPTION
	"The current value of the master's seventh output"
    ::= { masterOutputCurrent 7}
masterOutputCurrentEight OBJECT-TYPE
    SYNTAX      DisplayString
    MAX-ACCESS  read-only
    STATUS      current
    DESCRIPTION
	"The current value of the master's eighth output"
    ::= { masterOutputCurrent 8}
masterOutputCurrentNine OBJECT-TYPE
    SYNTAX      DisplayString
    MAX-ACCESS  read-only
    STATUS      current
    DESCRIPTION
	"The current value of the master's nineth output"
    ::= { masterOutputCurrent 9}
masterOutputCurrentTen OBJECT-TYPE
    SYNTAX      DisplayString
    MAX-ACCESS  read-only
    STATUS      current
    DESCRIPTION
	"The current value of the master's tenth output"
    ::= { masterOutputCurrent 10}
masterOutputCurrentEleven OBJECT-TYPE
    SYNTAX      DisplayString
    MAX-ACCESS  read-only
    STATUS      current
    DESCRIPTION
	"The current value of the master's eleventh output"
    ::= { masterOutputCurrent 11}
masterOutputCurrentTwelve OBJECT-TYPE
    SYNTAX      DisplayString
    MAX-ACCESS  read-only
    STATUS      current
    DESCRIPTION
	"The current value of the master's twelfth output"
    ::= { masterOutputCurrent 12}
masterOutputCurrentThirteen OBJECT-TYPE
    SYNTAX      DisplayString
    MAX-ACCESS  read-only
    STATUS      current
    DESCRIPTION
	"The current value of the master's thirteenth output"
    ::= { masterOutputCurrent 13}
masterOutputCurrentFourteen OBJECT-TYPE
    SYNTAX      DisplayString
    MAX-ACCESS  read-only
    STATUS      current
    DESCRIPTION
	"The current value of the master's fourteenth output"
    ::= { masterOutputCurrent 14}
masterOutputCurrentFifteen OBJECT-TYPE
    SYNTAX      DisplayString
    MAX-ACCESS  read-only
    STATUS      current
    DESCRIPTION
	"The current value of the master's fifteenth output"
    ::= { masterOutputCurrent 15}
masterOutputCurrentSixteen OBJECT-TYPE
    SYNTAX      DisplayString
    MAX-ACCESS  read-only
    STATUS      current
    DESCRIPTION
	"The current value of the master's sixteenth output"
    ::= { masterOutputCurrent 16}
masterOutputCurrentSeventeen OBJECT-TYPE
    SYNTAX      DisplayString
    MAX-ACCESS  read-only
    STATUS      current
    DESCRIPTION
	"The current value of the master's seventeenth output"
    ::= { masterOutputCurrent 17}
masterOutputCurrentEighteen OBJECT-TYPE
    SYNTAX      DisplayString
    MAX-ACCESS  read-only
    STATUS      current
    DESCRIPTION
	"The current value of the master's eighteenth output"
    ::= { masterOutputCurrent 18}
masterOutputCurrentNineteen OBJECT-TYPE
    SYNTAX      DisplayString
    MAX-ACCESS  read-only
    STATUS      current
    DESCRIPTION
	"The current value of the master's nineteenth output"
    ::= { masterOutputCurrent 19}
masterOutputCurrentTwenty OBJECT-TYPE
    SYNTAX      DisplayString
    MAX-ACCESS  read-only
    STATUS      current
    DESCRIPTION
	"The current value of the master's twentieth output"
    ::= { masterOutputCurrent 20}
masterOutputCurrentTwentyOne OBJECT-TYPE
    SYNTAX      DisplayString
    MAX-ACCESS  read-only
    STATUS      current
    DESCRIPTION
	"The current value of the master's twenty-first output"
    ::= { masterOutputCurrent 21}
masterOutputCurrentTwentyTwo OBJECT-TYPE
    SYNTAX      DisplayString
    MAX-ACCESS  read-only
    STATUS      current
    DESCRIPTION
	"The current value of the master's twenty-second output"
    ::= { masterOutputCurrent 22}
masterOutputCurrentTwentyThree OBJECT-TYPE
    SYNTAX      DisplayString
    MAX-ACCESS  read-only
    STATUS      current
    DESCRIPTION
	"The current value of the master's twenty-third output"
    ::= { masterOutputCurrent 23}
masterOutputCurrentTwentyFour OBJECT-TYPE
    SYNTAX      DisplayString
    MAX-ACCESS  read-only
    STATUS      current
    DESCRIPTION
	"The current value of the master's twenty-fourth output"
    ::= { masterOutputCurrent 24}

masterOutputCurrentMin   OBJECT IDENTIFIER ::= { rpdumaster 11}
masterOutputCurrentMinOne OBJECT-TYPE
    SYNTAX      DisplayString
    MAX-ACCESS  read-only
    STATUS      current
    DESCRIPTION
	"The Min. current value of the master's first output"
    ::= { masterOutputCurrentMin 1}
masterOutputCurrentMinTwo OBJECT-TYPE
    SYNTAX      DisplayString
    MAX-ACCESS  read-only
    STATUS      current
    DESCRIPTION
	"The Min. current value of the master's second output"
    ::= { masterOutputCurrentMin 2}
masterOutputCurrentMinThree OBJECT-TYPE
    SYNTAX      DisplayString
    MAX-ACCESS  read-only
    STATUS      current
    DESCRIPTION
	"The Min. current value of the master's third output"
    ::= { masterOutputCurrentMin 3}
masterOutputCurrentMinFour OBJECT-TYPE
    SYNTAX      DisplayString
    MAX-ACCESS  read-only
    STATUS      current
    DESCRIPTION
	"The Min. current value of the master's fourth output"
    ::= { masterOutputCurrentMin 4}
masterOutputCurrentMinFive OBJECT-TYPE
    SYNTAX      DisplayString
    MAX-ACCESS  read-only
    STATUS      current
    DESCRIPTION
	"The Min. current value of the master's fifth output"
    ::= { masterOutputCurrentMin 5}
masterOutputCurrentMinSix OBJECT-TYPE
    SYNTAX      DisplayString
    MAX-ACCESS  read-only
    STATUS      current
    DESCRIPTION
	"The Min. current value of the master's sixth output"
    ::= { masterOutputCurrentMin 6}
masterOutputCurrentMinSeven OBJECT-TYPE
    SYNTAX      DisplayString
    MAX-ACCESS  read-only
    STATUS      current
    DESCRIPTION
	"The Min. current value of the master's seventh output"
    ::= { masterOutputCurrentMin 7}
masterOutputCurrentMinEight OBJECT-TYPE
    SYNTAX      DisplayString
    MAX-ACCESS  read-only
    STATUS      current
    DESCRIPTION
	"The Min. current value of the master's eighth output"
    ::= { masterOutputCurrentMin 8}
masterOutputCurrentMinNine OBJECT-TYPE
    SYNTAX      DisplayString
    MAX-ACCESS  read-only
    STATUS      current
    DESCRIPTION
	"The Min. current value of the master's nineth output"
    ::= { masterOutputCurrentMin 9}
masterOutputCurrentMinTen OBJECT-TYPE
    SYNTAX      DisplayString
    MAX-ACCESS  read-only
    STATUS      current
    DESCRIPTION
	"The Min. current value of the master's tenth output"
    ::= { masterOutputCurrentMin 10}
masterOutputCurrentMinEleven OBJECT-TYPE
    SYNTAX      DisplayString
    MAX-ACCESS  read-only
    STATUS      current
    DESCRIPTION
	"The Min. current value of the master's eleventh output"
    ::= { masterOutputCurrentMin 11}
masterOutputCurrentMinTwleve OBJECT-TYPE
    SYNTAX      DisplayString
    MAX-ACCESS  read-only
    STATUS      current
    DESCRIPTION
	"The Min. current value of the master's twelfth output"
    ::= { masterOutputCurrentMin 12}
masterOutputCurrentMinThirteen OBJECT-TYPE
    SYNTAX      DisplayString
    MAX-ACCESS  read-only
    STATUS      current
    DESCRIPTION
	"The Min. current value of the master's thirteenth output"
    ::= { masterOutputCurrentMin 13}
masterOutputCurrentMinFourteen OBJECT-TYPE
    SYNTAX      DisplayString
    MAX-ACCESS  read-only
    STATUS      current
    DESCRIPTION
	"The Min. current value of the master's fourteenth output"
    ::= { masterOutputCurrentMin 14}
masterOutputCurrentMinFifteen OBJECT-TYPE
    SYNTAX      DisplayString
    MAX-ACCESS  read-only
    STATUS      current
    DESCRIPTION
	"The Min. current value of the master's fifteenth output"
    ::= { masterOutputCurrentMin 15}
masterOutputCurrentMinSixteen OBJECT-TYPE
    SYNTAX      DisplayString
    MAX-ACCESS  read-only
    STATUS      current
    DESCRIPTION
	"The Min. current value of the master's sixteenth output"
    ::= { masterOutputCurrentMin 16}
masterOutputCurrentMinSeventeen OBJECT-TYPE
    SYNTAX      DisplayString
    MAX-ACCESS  read-only
    STATUS      current
    DESCRIPTION
	"The Min. current value of the master's seventeenth output"
    ::= { masterOutputCurrentMin 17}
masterOutputCurrentMinEighteen OBJECT-TYPE
    SYNTAX      DisplayString
    MAX-ACCESS  read-only
    STATUS      current
    DESCRIPTION
	"The Min. current value of the master's eighteenth output"
    ::= { masterOutputCurrentMin 18}
masterOutputCurrentMinNineteen OBJECT-TYPE
    SYNTAX      DisplayString
    MAX-ACCESS  read-only
    STATUS      current
    DESCRIPTION
	"The Min. current value of the master's nineteenth output"
    ::= { masterOutputCurrentMin 19}
masterOutputCurrentMinTwenty OBJECT-TYPE
    SYNTAX      DisplayString
    MAX-ACCESS  read-only
    STATUS      current
    DESCRIPTION
	"The Min. current value of the master's twentieth output"
    ::= { masterOutputCurrentMin 20}
masterOutputCurrentMinTwentyOne OBJECT-TYPE
    SYNTAX      DisplayString
    MAX-ACCESS  read-only
    STATUS      current
    DESCRIPTION
	"The Min. current value of the master's twentyth-first output"
    ::= { masterOutputCurrentMin 21}
masterOutputCurrentMinTwentyTwo OBJECT-TYPE
    SYNTAX      DisplayString
    MAX-ACCESS  read-only
    STATUS      current
    DESCRIPTION
	"The Min. current value of the master's twentyth-second output"
    ::= { masterOutputCurrentMin 22}
masterOutputCurrentMinTwentyThree OBJECT-TYPE
    SYNTAX      DisplayString
    MAX-ACCESS  read-only
    STATUS      current
    DESCRIPTION
	"The Min. current value of the master's twentyth-third output"
    ::= { masterOutputCurrentMin 23}
masterOutputCurrentMinTwentyFour OBJECT-TYPE
    SYNTAX      DisplayString
    MAX-ACCESS  read-only
    STATUS      current
    DESCRIPTION
	"The Min. current value of the master's twentyth-fourth output"
    ::= { masterOutputCurrentMin 24}




masterOutputCurrentMax   OBJECT IDENTIFIER ::= { rpdumaster 12}
masterOutputCurrentMaxOne OBJECT-TYPE
    SYNTAX      DisplayString
    MAX-ACCESS  read-only
    STATUS      current
    DESCRIPTION
	"The Max. current value of the master's first output"
    ::= { masterOutputCurrentMax 1}
masterOutputCurrentMaxTwo OBJECT-TYPE
    SYNTAX      DisplayString
    MAX-ACCESS  read-only
    STATUS      current
    DESCRIPTION
	"The Max. current value of the master's second output"
    ::= { masterOutputCurrentMax 2}
masterOutputCurrentMaxThree OBJECT-TYPE
    SYNTAX      DisplayString
    MAX-ACCESS  read-only
    STATUS      current
    DESCRIPTION
	"The Max. current value of the master's third output"
    ::= { masterOutputCurrentMax 3}
masterOutputCurrentMaxFour OBJECT-TYPE
    SYNTAX      DisplayString
    MAX-ACCESS  read-only
    STATUS      current
    DESCRIPTION
	"The Max. current value of the master's fourth output"
    ::= { masterOutputCurrentMax 4}
masterOutputCurrentMaxFive OBJECT-TYPE
    SYNTAX      DisplayString
    MAX-ACCESS  read-only
    STATUS      current
    DESCRIPTION
	"The Max. current value of the master's fifth output"
    ::= { masterOutputCurrentMax 5}
masterOutputCurrentMaxSix OBJECT-TYPE
    SYNTAX      DisplayString
    MAX-ACCESS  read-only
    STATUS      current
    DESCRIPTION
	"The Max. current value of the master's sixth output"
    ::= { masterOutputCurrentMax 6}
masterOutputCurrentMaxSeven OBJECT-TYPE
    SYNTAX      DisplayString
    MAX-ACCESS  read-only
    STATUS      current
    DESCRIPTION
	"The Max. current value of the master's seventh output"
    ::= { masterOutputCurrentMax 7}
masterOutputCurrentMaxEight OBJECT-TYPE
    SYNTAX      DisplayString
    MAX-ACCESS  read-only
    STATUS      current
    DESCRIPTION
	"The Max. current value of the master's eighth output"
    ::= { masterOutputCurrentMax 8}
masterOutputCurrentMaxNine OBJECT-TYPE
    SYNTAX      DisplayString
    MAX-ACCESS  read-only
    STATUS      current
    DESCRIPTION
	"The Max. current value of the master's nineth output"
    ::= { masterOutputCurrentMax 9}
masterOutputCurrentMaxTen OBJECT-TYPE
    SYNTAX      DisplayString
    MAX-ACCESS  read-only
    STATUS      current
    DESCRIPTION
	"The Max. current value of the master's tenth output"
    ::= { masterOutputCurrentMax 10}
masterOutputCurrentMaxEleven OBJECT-TYPE
    SYNTAX      DisplayString
    MAX-ACCESS  read-only
    STATUS      current
    DESCRIPTION
	"The Max. current value of the master's eleventh output"
    ::= { masterOutputCurrentMax 11}
masterOutputCurrentMaxTwleve OBJECT-TYPE
    SYNTAX      DisplayString
    MAX-ACCESS  read-only
    STATUS      current
    DESCRIPTION
	"The Max. current value of the master's twelfth output"
    ::= { masterOutputCurrentMax 12}
masterOutputCurrentMaxThirteen OBJECT-TYPE
    SYNTAX      DisplayString
    MAX-ACCESS  read-only
    STATUS      current
    DESCRIPTION
	"The Max. current value of the master's thirteenth output"
    ::= { masterOutputCurrentMax 13}
masterOutputCurrentMaxFourteen OBJECT-TYPE
    SYNTAX      DisplayString
    MAX-ACCESS  read-only
    STATUS      current
    DESCRIPTION
	"The Max. current value of the master's fourteenth output"
    ::= { masterOutputCurrentMax 14}
masterOutputCurrentMaxFifteen OBJECT-TYPE
    SYNTAX      DisplayString
    MAX-ACCESS  read-only
    STATUS      current
    DESCRIPTION
	"The Max. current value of the master's fifteenth output"
    ::= { masterOutputCurrentMax 15}
masterOutputCurrentMaxSixteen OBJECT-TYPE
    SYNTAX      DisplayString
    MAX-ACCESS  read-only
    STATUS      current
    DESCRIPTION
	"The Max. current value of the master's sixteenth output"
    ::= { masterOutputCurrentMax 16}
masterOutputCurrentMaxSeventeen OBJECT-TYPE
    SYNTAX      DisplayString
    MAX-ACCESS  read-only
    STATUS      current
    DESCRIPTION
	"The Max. current value of the master's seventeenth output"
    ::= { masterOutputCurrentMax 17}
masterOutputCurrentMaxEighteen OBJECT-TYPE
    SYNTAX      DisplayString
    MAX-ACCESS  read-only
    STATUS      current
    DESCRIPTION
	"The Max. current value of the master's eighteenth output"
    ::= { masterOutputCurrentMax 18}
masterOutputCurrentMaxNineteen OBJECT-TYPE
    SYNTAX      DisplayString
    MAX-ACCESS  read-only
    STATUS      current
    DESCRIPTION
	"The Max. current value of the master's nineteenth output"
    ::= { masterOutputCurrentMax 19}
masterOutputCurrentMaxTwenty OBJECT-TYPE
    SYNTAX      DisplayString
    MAX-ACCESS  read-only
    STATUS      current
    DESCRIPTION
	"The Max. current value of the master's twentieth output"
    ::= { masterOutputCurrentMax 20}
masterOutputCurrentMaxTwentyOne OBJECT-TYPE
    SYNTAX      DisplayString
    MAX-ACCESS  read-only
    STATUS      current
    DESCRIPTION
	"The Max. current value of the master's twenty-first output"
    ::= { masterOutputCurrentMax 21}
masterOutputCurrentMaxTwentyTwo OBJECT-TYPE
    SYNTAX      DisplayString
    MAX-ACCESS  read-only
    STATUS      current
    DESCRIPTION
	"The Max. current value of the master's twenty-second output"
    ::= { masterOutputCurrentMax 22}
masterOutputCurrentMaxTwentyThree OBJECT-TYPE
    SYNTAX      DisplayString
    MAX-ACCESS  read-only
    STATUS      current
    DESCRIPTION
	"The Max. current value of the master's twenty-third output"
    ::= { masterOutputCurrentMax 23}
masterOutputCurrentMaxTwentyFour OBJECT-TYPE
    SYNTAX      DisplayString
    MAX-ACCESS  read-only
    STATUS      current
    DESCRIPTION
	"The Max. current value of the master's twenty-fourth output"
    ::= { masterOutputCurrentMax 24}


masterOutputCurrentEnergy  OBJECT IDENTIFIER ::= { rpdumaster 13}
masterOutputCurrentEnergyOne OBJECT-TYPE
    SYNTAX	DisplayString
    MAX-ACCESS	read-only
    STATUS	current
    DESCRIPTION
	"The energy value of the master's first output"
    ::={masterOutputCurrentEnergy 1}
masterOutputCurrentEnergyTwo OBJECT-TYPE
    SYNTAX	DisplayString
    MAX-ACCESS	read-only
    STATUS	current
    DESCRIPTION
	"The energy value of the master's second output"
    ::={masterOutputCurrentEnergy 2}
masterOutputCurrentEnergyThree OBJECT-TYPE
    SYNTAX	DisplayString
    MAX-ACCESS	read-only
    STATUS	current
    DESCRIPTION
	"The energy value of the master's third output"
    ::={masterOutputCurrentEnergy 3}
masterOutputCurrentEnergyFour OBJECT-TYPE
    SYNTAX	DisplayString
    MAX-ACCESS	read-only
    STATUS	current
    DESCRIPTION
	"The energy value of the master's fourth output"
    ::={masterOutputCurrentEnergy 4}
masterOutputCurrentEnergyFive OBJECT-TYPE
    SYNTAX	DisplayString
    MAX-ACCESS	read-only
    STATUS	current
    DESCRIPTION
	"The energy value of the master's fifth output"
    ::={masterOutputCurrentEnergy 5}
masterOutputCurrentEnergySix OBJECT-TYPE
    SYNTAX	DisplayString
    MAX-ACCESS	read-only
    STATUS	current
    DESCRIPTION
	"The energy value of the master's sixth output"
    ::={masterOutputCurrentEnergy 6}
masterOutputCurrentEnergySeven OBJECT-TYPE
    SYNTAX	DisplayString
    MAX-ACCESS	read-only
    STATUS	current
    DESCRIPTION
	"The energy value of the master's seventh output"
    ::={masterOutputCurrentEnergy 7}
masterOutputCurrentEnergyEight OBJECT-TYPE
    SYNTAX	DisplayString
    MAX-ACCESS	read-only
    STATUS	current
    DESCRIPTION
	"The energy value of the master's eighth output"
    ::={masterOutputCurrentEnergy 8}
masterOutputCurrentEnergyNine OBJECT-TYPE
    SYNTAX	DisplayString
    MAX-ACCESS	read-only
    STATUS	current
    DESCRIPTION
	"The energy value of the master's nineth output"
    ::={masterOutputCurrentEnergy 9}
masterOutputCurrentEnergyTen OBJECT-TYPE
    SYNTAX	DisplayString
    MAX-ACCESS	read-only
    STATUS	current
    DESCRIPTION
	"The energy value of the master's tenth output"
    ::={masterOutputCurrentEnergy 10}
masterOutputCurrentEnergyEleven OBJECT-TYPE
    SYNTAX	DisplayString
    MAX-ACCESS	read-only
    STATUS	current
    DESCRIPTION
	"The energy value of the master's eleventh output"
    ::={masterOutputCurrentEnergy 11}
masterOutputCurrentEnergyTwelve OBJECT-TYPE
    SYNTAX	DisplayString
    MAX-ACCESS	read-only
    STATUS	current
    DESCRIPTION
	"The energy value of the master's twelfth output"
    ::={masterOutputCurrentEnergy 12}
masterOutputCurrentEnergyThirteen OBJECT-TYPE
    SYNTAX	DisplayString
    MAX-ACCESS	read-only
    STATUS	current
    DESCRIPTION
	"The energy value of the master's thirteenth output"
    ::={masterOutputCurrentEnergy 13}
masterOutputCurrentEnergyFourteen OBJECT-TYPE
    SYNTAX	DisplayString
    MAX-ACCESS	read-only
    STATUS	current
    DESCRIPTION
	"The energy value of the master's fourteenth output"
    ::={masterOutputCurrentEnergy 14}
masterOutputCurrentEnergyFifteen OBJECT-TYPE
    SYNTAX	DisplayString
    MAX-ACCESS	read-only
    STATUS	current
    DESCRIPTION
	"The energy value of the master's fifteenth output"
    ::={masterOutputCurrentEnergy 15}
masterOutputCurrentEnergySixteen OBJECT-TYPE
    SYNTAX	DisplayString
    MAX-ACCESS	read-only
    STATUS	current
    DESCRIPTION
	"The energy value of the master's sixteenth output"
    ::={masterOutputCurrentEnergy 16}
masterOutputCurrentEnergySeventeen OBJECT-TYPE
    SYNTAX	DisplayString
    MAX-ACCESS	read-only
    STATUS	current
    DESCRIPTION
	"The energy value of the master's seventeenth output"
    ::={masterOutputCurrentEnergy 17}
masterOutputCurrentEnergyEighteen OBJECT-TYPE
    SYNTAX	DisplayString
    MAX-ACCESS	read-only
    STATUS	current
    DESCRIPTION
	"The energy value of the master's eighteenth output"
    ::={masterOutputCurrentEnergy 18}
masterOutputCurrentEnergyNineteen OBJECT-TYPE
    SYNTAX	DisplayString
    MAX-ACCESS	read-only
    STATUS	current
    DESCRIPTION
	"The energy value of the master's nineteenth output"
    ::={masterOutputCurrentEnergy 19}
masterOutputCurrentEnergyTwenty OBJECT-TYPE
    SYNTAX	DisplayString
    MAX-ACCESS	read-only
    STATUS	current
    DESCRIPTION
	"The energy value of the master's twentieth output"
    ::={masterOutputCurrentEnergy 20}
masterOutputCurrentEnergyTwentyOne OBJECT-TYPE
    SYNTAX	DisplayString
    MAX-ACCESS	read-only
    STATUS	current
    DESCRIPTION
	"The energy value of the master's twenty-first output"
    ::={masterOutputCurrentEnergy 21}
masterOutputCurrentEnergyTwentyTwo OBJECT-TYPE
    SYNTAX	DisplayString
    MAX-ACCESS	read-only
    STATUS	current
    DESCRIPTION
	"The energy value of the master's twenty-second output"
    ::={masterOutputCurrentEnergy 22}
masterOutputCurrentEnergyTwentyThree OBJECT-TYPE
    SYNTAX	DisplayString
    MAX-ACCESS	read-only
    STATUS	current
    DESCRIPTION
	"The energy value of the master's twenty-third output"
    ::={masterOutputCurrentEnergy 23}
masterOutputCurrentEnergyTwentyFour OBJECT-TYPE
    SYNTAX	DisplayString
    MAX-ACCESS	read-only
    STATUS	current
    DESCRIPTION
	"The energy value of the master's twenty-fourth output"
    ::={masterOutputCurrentEnergy 24}
    
-------------------------------Slave1---------------------------------------------  
rpduDeviceTwo OBJECT IDENTIFIER ::= { rpdu 2}
rpduSlaveOne OBJECT IDENTIFIER ::= { rpduDeviceTwo 1}

slaveOneName OBJECT-TYPE
    SYNTAX      DisplayString
    MAX-ACCESS  read-write
    STATUS      current
    DESCRIPTION
	"This is the second device."
    ::= { rpduSlaveOne 1}
    
slaveOneType OBJECT-TYPE
    SYNTAX      DisplayString
    MAX-ACCESS  read-only
    STATUS      current
    DESCRIPTION
	"This is device type "
    ::= { rpduSlaveOne 2}
    
slaveOneOutputNumber OBJECT-TYPE 
    SYNTAX      Integer32
    MAX-ACCESS  read-only
    STATUS      current
    DESCRIPTION
	"This is the output quantity"
::= { rpduSlaveOne 7}
    
slaveOneLineOne OBJECT IDENTIFIER ::= { rpduSlaveOne 3}
slaveOneLineOnePower OBJECT-TYPE
    SYNTAX      DisplayString
    MAX-ACCESS  read-only
    STATUS      current
    DESCRIPTION
	"The power of phase one"
    ::= { slaveOneLineOne 1}
slaveOneLineOnePF OBJECT-TYPE
    SYNTAX      DisplayString
    MAX-ACCESS  read-only
    STATUS      current
    DESCRIPTION
	"The power factor of phase one"
    ::= { slaveOneLineOne 2}
    
slaveOneLineOneEnergy OBJECT-TYPE
    SYNTAX      DisplayString
    MAX-ACCESS  read-only
    STATUS      current
    DESCRIPTION
	"The energy of phase one"
    ::= { slaveOneLineOne 3}
slaveOneLineOneCurrent OBJECT-TYPE
    SYNTAX      DisplayString
    MAX-ACCESS  read-only
    STATUS      current
    DESCRIPTION
	"The current of phase one"
    ::= { slaveOneLineOne 4}
slaveOneLineOneVoltage OBJECT-TYPE
    SYNTAX      Integer32
    MAX-ACCESS  read-only
    STATUS      current
    DESCRIPTION
	"The voltage of phase one"
    ::= { slaveOneLineOne 5}
slaveOneLineOneCurrentMin OBJECT-TYPE
    SYNTAX      DisplayString
    MAX-ACCESS  read-only
    STATUS      current
    DESCRIPTION
	"The Min. current value of phase one"
	::= { slaveOneLineOne 6}
slaveOneLineOneCurrentMax OBJECT-TYPE
    SYNTAX      DisplayString
    MAX-ACCESS  read-only
    STATUS      current
    DESCRIPTION
	"The Max. current value of phase one"
    ::= { slaveOneLineOne 7}
    
slaveOneLineOneVoltageMin OBJECT-TYPE
    SYNTAX      Integer32
    MAX-ACCESS  read-only
    STATUS      current
    DESCRIPTION
	"The Min. voltage value of phase one"
    ::= { slaveOneLineOne 8}
    
slaveOneLineOneVoltageMax OBJECT-TYPE
    SYNTAX      Integer32
    MAX-ACCESS  read-only
    STATUS      current
    DESCRIPTION
	"The Max. voltage value of phase one"
    ::= { slaveOneLineOne 9}


slaveOneLineTwo OBJECT IDENTIFIER ::= { rpduSlaveOne 4}
slaveOneLineTwoPower OBJECT-TYPE
    SYNTAX      DisplayString
    MAX-ACCESS  read-only
    STATUS      current
    DESCRIPTION
	"The power of phase two"
    ::= { slaveOneLineTwo 1}

slaveOneLineTwoPF OBJECT-TYPE
    SYNTAX      DisplayString
    MAX-ACCESS  read-only
    STATUS      current
    DESCRIPTION
	"The power factor of phase two"   
    ::= { slaveOneLineTwo 2}
    
slaveOneLineTwoEnergy OBJECT-TYPE
    SYNTAX      DisplayString
    MAX-ACCESS  read-only
    STATUS      current
    DESCRIPTION
	"The energy of phase two"
    ::= { slaveOneLineTwo 3}
slaveOneLineTwoCurrent OBJECT-TYPE           
    SYNTAX      DisplayString
    MAX-ACCESS  read-only
    STATUS      current
    DESCRIPTION
	"The current of phase two"
    ::= { slaveOneLineTwo 4}
slaveOneLineTwoVoltage OBJECT-TYPE
    SYNTAX      Integer32
    MAX-ACCESS  read-only
    STATUS      current
    DESCRIPTION
	"The voltage of phase two"
    ::= { slaveOneLineTwo 5}
slaveOneLineTwoCurrentMin OBJECT-TYPE
    SYNTAX      DisplayString
    MAX-ACCESS  read-only
    STATUS      current
    DESCRIPTION
	"The Min. current value of phase two"
    ::= { slaveOneLineTwo 6}
slaveOneLineTwoCurrentMax OBJECT-TYPE
    SYNTAX      DisplayString
    MAX-ACCESS  read-only
    STATUS      current
    DESCRIPTION
	"The Max. current value of phase two"
    ::= { slaveOneLineTwo 7}
    
slaveOneLineTwoVoltageMin OBJECT-TYPE
    SYNTAX      Integer32
    MAX-ACCESS  read-only
    STATUS      current
    DESCRIPTION
	"The Min. voltage value of phase two"
    ::= { slaveOneLineTwo 8}
    
slaveOneLineTwoVoltageMax OBJECT-TYPE
    SYNTAX      Integer32
    MAX-ACCESS  read-only
    STATUS      current
    DESCRIPTION
	"The Max. voltage value of phase two"
    ::= { slaveOneLineTwo 9}



slaveOneLineThree OBJECT IDENTIFIER ::= { rpduSlaveOne 5}
slaveOneLineThreePower OBJECT-TYPE
    SYNTAX      DisplayString
    MAX-ACCESS  read-only
    STATUS      current
    DESCRIPTION
	"The power of phase three"
    ::= { slaveOneLineThree 1}

slaveOneLineThreePF OBJECT-TYPE
    SYNTAX      DisplayString
    MAX-ACCESS  read-only
    STATUS      current
    DESCRIPTION
	"The power factor of phase three"     
    ::= { slaveOneLineThree 2}
    
slaveOneLineThreeEnergy OBJECT-TYPE
    SYNTAX      DisplayString
    MAX-ACCESS  read-only
    STATUS      current
    DESCRIPTION
	"The energy of phase three"
    ::= { slaveOneLineThree 3}
slaveOneLineThreeCurrent OBJECT-TYPE
    SYNTAX      DisplayString
    MAX-ACCESS  read-only
    STATUS      current
    DESCRIPTION
	"The current of phase three"
    ::= { slaveOneLineThree 4}
slaveOneLineThreeVoltage OBJECT-TYPE
    SYNTAX      Integer32
    MAX-ACCESS  read-only
    STATUS      current
    DESCRIPTION
	"The voltage of phase three"
    ::= { slaveOneLineThree 5}
slaveOneLineThreeCurrentMin OBJECT-TYPE
    SYNTAX      DisplayString
    MAX-ACCESS  read-only
    STATUS      current
    DESCRIPTION
	"The Min. current value of phase three"
    ::= { slaveOneLineThree 6}
slaveOneLineThreeCurrentMax OBJECT-TYPE
    SYNTAX      DisplayString
    MAX-ACCESS  read-only
    STATUS      current
    DESCRIPTION
	"The Max. current value of phase three"
    ::= { slaveOneLineThree 7}
    
slaveOneLineThreeVoltageMin OBJECT-TYPE
    SYNTAX      Integer32
    MAX-ACCESS  read-only
    STATUS      current
    DESCRIPTION
	"The Min. voltage value of phase three"
    ::= { slaveOneLineThree 8}
    
slaveOneLineThreeVoltageMax OBJECT-TYPE
    SYNTAX      Integer32
    MAX-ACCESS  read-only
    STATUS      current
    DESCRIPTION
	"The Max. voltage value of phase three"
    ::= { slaveOneLineThree 9}


slaveOneSensor OBJECT IDENTIFIER ::= { rpduSlaveOne 6}
slaveOneTempOne OBJECT-TYPE
    SYNTAX      Integer32
    MAX-ACCESS  read-only
    STATUS      current
    DESCRIPTION
	"The first temperature sensor of slave 1"
    ::= { slaveOneSensor 1}
slaveOneTempTwo OBJECT-TYPE
    SYNTAX      Integer32
    MAX-ACCESS  read-only
    STATUS      current
    DESCRIPTION
	"The second temperature sensor of slave 1"
    ::= { slaveOneSensor 2}
slaveOneTempThree OBJECT-TYPE
    SYNTAX      Integer32
    MAX-ACCESS  read-only
    STATUS      current
    DESCRIPTION
	"The third temperature sensor of slave 1"
    ::= { slaveOneSensor 3}
slaveOneTempFour OBJECT-TYPE
    SYNTAX      Integer32
    MAX-ACCESS  read-only
    STATUS      current
    DESCRIPTION
	"The fourth temperature sensor of slave 1"
    ::= { slaveOneSensor 4}
slaveOneHumOne OBJECT-TYPE
    SYNTAX      Integer32
    MAX-ACCESS  read-only
    STATUS      current
    DESCRIPTION
	"The first humidity sensor of slave 1"
    ::= { slaveOneSensor 5}
slaveOneHumTwo OBJECT-TYPE
    SYNTAX      Integer32
    MAX-ACCESS  read-only
    STATUS      current
    DESCRIPTION
	"The second humidity sensor of slave 1"
    ::= { slaveOneSensor 6}
slaveOneHumThree OBJECT-TYPE
    SYNTAX      Integer32
    MAX-ACCESS  read-only
    STATUS      current
    DESCRIPTION
	"The third humidity sensor of slave 1"
    ::= { slaveOneSensor 7}
slaveOneHumFour OBJECT-TYPE
    SYNTAX      Integer32
    MAX-ACCESS  read-only
    STATUS      current
    DESCRIPTION
	"The fourth humidity sensor of slave 1"
    ::= { slaveOneSensor 8}
slaveOneDoorOne OBJECT-TYPE
    SYNTAX      DisplayString
    MAX-ACCESS  read-only
    STATUS      current
    DESCRIPTION
	"The first door sensor of slave 1"    
    ::= { slaveOneSensor 9}
slaveOneDoorTwo OBJECT-TYPE
    SYNTAX      DisplayString
    MAX-ACCESS  read-only
    STATUS      current
    DESCRIPTION
	"The second door sensor of slave 1"  
    ::= { slaveOneSensor 10}
slaveOneSmoke OBJECT-TYPE
    SYNTAX      DisplayString
    MAX-ACCESS  read-only
    STATUS      current
    DESCRIPTION
	"The smoke sensor of slave 1"
    ::= { slaveOneSensor 11}
slaveOneWater OBJECT-TYPE
    SYNTAX      DisplayString
    MAX-ACCESS  read-only
    STATUS      current
    DESCRIPTION
	"The water sensor of slave 1"
    ::= { slaveOneSensor 12}


	
        
slaveOneOutputName OBJECT IDENTIFIER ::= { rpduSlaveOne 8}
slaveOneOutputNameOne OBJECT-TYPE
    SYNTAX      DisplayString
    MAX-ACCESS  read-write
    STATUS      current
    DESCRIPTION
	"The first output name of slave 1"
    ::= { slaveOneOutputName 1}

slaveOneOutputNameTwo OBJECT-TYPE
    SYNTAX      DisplayString
    MAX-ACCESS  read-write
    STATUS      current
    DESCRIPTION
	"The second output name of slave 1"
    ::= { slaveOneOutputName 2}
slaveOneOutputNameThree OBJECT-TYPE
    SYNTAX      DisplayString
    MAX-ACCESS  read-write
    STATUS      current
    DESCRIPTION
	"The third output name of slave 1"
    ::= { slaveOneOutputName 3}
slaveOneOutputNameFour OBJECT-TYPE
    SYNTAX      DisplayString
    MAX-ACCESS  read-write
    STATUS      current
    DESCRIPTION
	"The fourth output name of slave 1"
    ::= { slaveOneOutputName 4}
slaveOneOutputNameFive OBJECT-TYPE
    SYNTAX      DisplayString
    MAX-ACCESS  read-write
    STATUS      current
    DESCRIPTION
	"The fifth output name of slave 1"
    ::= { slaveOneOutputName 5}
slaveOneOutputNameSix OBJECT-TYPE
    SYNTAX      DisplayString
    MAX-ACCESS  read-write
    STATUS      current
    DESCRIPTION
	"The sixth output name of slave 1"
    ::= { slaveOneOutputName 6}
slaveOneOutputNameSeven OBJECT-TYPE
    SYNTAX      DisplayString
    MAX-ACCESS  read-write
    STATUS      current
    DESCRIPTION
	"The seventh output name of slave 1"
    ::= { slaveOneOutputName 7}
slaveOneOutputNameEight OBJECT-TYPE
    SYNTAX      DisplayString
    MAX-ACCESS  read-write
    STATUS      current
    DESCRIPTION
	"The eighth output name of slave 1"
    ::= { slaveOneOutputName 8}
slaveOneOutputNameNine OBJECT-TYPE
    SYNTAX      DisplayString
    MAX-ACCESS  read-write
    STATUS      current
    DESCRIPTION
	"The nineth output name of slave 1"
    ::= { slaveOneOutputName 9}
slaveOneOutputNameTen OBJECT-TYPE
    SYNTAX      DisplayString
    MAX-ACCESS  read-write
    STATUS      current
    DESCRIPTION
	"The tenth output name of slave 1"
    ::= { slaveOneOutputName 10}
slaveOneOutputNameEleven OBJECT-TYPE
    SYNTAX      DisplayString
    MAX-ACCESS  read-write
    STATUS      current
    DESCRIPTION
	"The eleventh output name of slave 1"
    ::= { slaveOneOutputName 11}
slaveOneOutputNameTwelve OBJECT-TYPE
    SYNTAX      DisplayString
    MAX-ACCESS  read-write
    STATUS      current
    DESCRIPTION
	"The twelfth output name of slave 1"
    ::= { slaveOneOutputName 12}
slaveOneOutputNameThirteen OBJECT-TYPE
    SYNTAX      DisplayString
    MAX-ACCESS  read-write
    STATUS      current
    DESCRIPTION
	"The thirteenth output name of slave 1"
    ::= { slaveOneOutputName 13}
slaveOneOutputNameFourteen OBJECT-TYPE
    SYNTAX      DisplayString
    MAX-ACCESS  read-write
    STATUS      current
    DESCRIPTION
	"The fourteenth output name of slave 1"
    ::= { slaveOneOutputName 14}
slaveOneOutputNameFifteen OBJECT-TYPE
    SYNTAX      DisplayString
    MAX-ACCESS  read-write
    STATUS      current
    DESCRIPTION
	"The fifteenth output name of slave 1"
    ::= { slaveOneOutputName 15}
slaveOneOutputNameSixteen OBJECT-TYPE
    SYNTAX      DisplayString
    MAX-ACCESS  read-write
    STATUS      current
    DESCRIPTION
	"The sixteenth output name of slave 1"
    ::= { slaveOneOutputName 16}
slaveOneOutputNameSeventeen OBJECT-TYPE
    SYNTAX      DisplayString
    MAX-ACCESS  read-write
    STATUS      current
    DESCRIPTION
	"The seventeenth output name of slave 1"
    ::= { slaveOneOutputName 17}
slaveOneOutputNameEighteen OBJECT-TYPE
    SYNTAX      DisplayString
    MAX-ACCESS  read-write
    STATUS      current
    DESCRIPTION
	"The eighteenh output name of slave 1"
    ::= { slaveOneOutputName 18}
slaveOneOutputNameNineteen OBJECT-TYPE
    SYNTAX      DisplayString
    MAX-ACCESS  read-write
    STATUS      current
    DESCRIPTION
	"The nineteenth output name of slave 1"
    ::= { slaveOneOutputName 19}
slaveOneOutputNameTwenty OBJECT-TYPE
    SYNTAX      DisplayString
    MAX-ACCESS  read-write
    STATUS      current
    DESCRIPTION
	"The twentieth output name of slave 1"
    ::= { slaveOneOutputName 20}
slaveOneOutputNameTwentyOne OBJECT-TYPE
    SYNTAX      DisplayString
    MAX-ACCESS  read-write
    STATUS      current
    DESCRIPTION
	"The twenty-first output name of slave 1"
    ::= { slaveOneOutputName 21}
slaveOneOutputNameTwentyTwo OBJECT-TYPE
    SYNTAX      DisplayString
    MAX-ACCESS  read-write
    STATUS      current
    DESCRIPTION
	"The twenty-second output name of slave 1"
    ::= { slaveOneOutputName 22}
slaveOneOutputNameTwentyThree OBJECT-TYPE
    SYNTAX      DisplayString
    MAX-ACCESS  read-write
    STATUS      current
    DESCRIPTION
	"The twenty-third output name of slave 1"
    ::= { slaveOneOutputName 23}
slaveOneOutputNameTwentyFour OBJECT-TYPE
    SYNTAX      DisplayString
    MAX-ACCESS  read-write
    STATUS      current
    DESCRIPTION
	"The twenty-fourth output name of slave 1"
    ::= { slaveOneOutputName 24}


    
slaveOneOutputStatus OBJECT IDENTIFIER ::= { rpduSlaveOne 9}

slaveOneOutputStatusOne OBJECT-TYPE
    SYNTAX      DisplayString
    MAX-ACCESS  read-write
    STATUS      current
    DESCRIPTION
	"The first output status of slave 1"
    ::= { slaveOneOutputStatus 1}
slaveOneOutputStatusTwo OBJECT-TYPE
    SYNTAX      DisplayString
    MAX-ACCESS  read-write
    STATUS      current
    DESCRIPTION
	"The second output status of slave 1"
    ::= { slaveOneOutputStatus 2}

slaveOneOutputStatusThree OBJECT-TYPE
    SYNTAX      DisplayString
    MAX-ACCESS  read-write
    STATUS      current
    DESCRIPTION
	"The third output status of slave 1"
    ::= { slaveOneOutputStatus 3}
slaveOneOutputStatusFour OBJECT-TYPE
    SYNTAX      DisplayString
    MAX-ACCESS  read-write
    STATUS      current
    DESCRIPTION
	"The fourth output status of slave 1"
    ::= { slaveOneOutputStatus 4}
slaveOneOutputStatusFive OBJECT-TYPE
    SYNTAX      DisplayString
    MAX-ACCESS  read-write
    STATUS      current
    DESCRIPTION
	"The fifth output status of slave 1"
    ::= { slaveOneOutputStatus 5}
slaveOneOutputStatusSix OBJECT-TYPE
    SYNTAX      DisplayString
    MAX-ACCESS  read-write
    STATUS      current
    DESCRIPTION
	"The sixth output status of slave 1"
    ::= { slaveOneOutputStatus 6}
slaveOneOutputStatusSeven OBJECT-TYPE
    SYNTAX      DisplayString
    MAX-ACCESS  read-write
    STATUS      current
    DESCRIPTION
	"The seventh output status of slave 1"
    ::= { slaveOneOutputStatus 7}
slaveOneOutputStatusEight OBJECT-TYPE
    SYNTAX      DisplayString
    MAX-ACCESS  read-write
    STATUS      current
    DESCRIPTION
	"The eighth output status of slave 1"
    ::= { slaveOneOutputStatus 8}
slaveOneOutputStatusNine OBJECT-TYPE
    SYNTAX      DisplayString
    MAX-ACCESS  read-write
    STATUS      current
    DESCRIPTION
	"The nineth output status of slave 1"
    ::= { slaveOneOutputStatus 9}
slaveOneOutputStatusTen OBJECT-TYPE
    SYNTAX      DisplayString
    MAX-ACCESS  read-write
    STATUS      current
    DESCRIPTION
	"The tenth output status of slave 1"
    ::= { slaveOneOutputStatus 10}
slaveOneOutputStatusEleven OBJECT-TYPE
    SYNTAX      DisplayString
    MAX-ACCESS  read-write
    STATUS      current
    DESCRIPTION
	"The eleventh output status of slave 1"
    ::= { slaveOneOutputStatus 11}
slaveOneOutputStatusTwelve OBJECT-TYPE
    SYNTAX      DisplayString
    MAX-ACCESS  read-write
    STATUS      current
    DESCRIPTION
	"The twelfth output status of slave 1"
    ::= { slaveOneOutputStatus 12}
slaveOneOutputStatusThirteen OBJECT-TYPE
    SYNTAX      DisplayString
    MAX-ACCESS  read-write
    STATUS      current
    DESCRIPTION
	"The thirteenth output status of slave 1"
    ::= { slaveOneOutputStatus 13}
slaveOneOutputStatusFourteen OBJECT-TYPE
    SYNTAX      DisplayString
    MAX-ACCESS  read-write
    STATUS      current
    DESCRIPTION
	"The fourteenth output status of slave 1"
    ::= { slaveOneOutputStatus 14}
slaveOneOutputStatusFifteen OBJECT-TYPE
    SYNTAX      DisplayString
    MAX-ACCESS  read-write
    STATUS      current
    DESCRIPTION
	"The fifteenth output status of slave 1"
    ::= { slaveOneOutputStatus 15}
slaveOneOutputStatusSixteen OBJECT-TYPE
    SYNTAX      DisplayString
    MAX-ACCESS  read-write
    STATUS      current
    DESCRIPTION
	"The sixteenth output status of slave 1"
    ::= { slaveOneOutputStatus 16}
slaveOneOutputStatusSeventeen OBJECT-TYPE
    SYNTAX      DisplayString
    MAX-ACCESS  read-write
    STATUS      current
    DESCRIPTION
	"The seventeenth output status of slave 1"
    ::= { slaveOneOutputStatus 17}
slaveOneOutputStatusEighteen OBJECT-TYPE
    SYNTAX      DisplayString
    MAX-ACCESS  read-write
    STATUS      current
    DESCRIPTION
	"The eighteenth output status of slave 1"
    ::= { slaveOneOutputStatus 18}
slaveOneOutputStatusNineteen OBJECT-TYPE
    SYNTAX      DisplayString
    MAX-ACCESS  read-write
    STATUS      current
    DESCRIPTION
	"The nineteenth output status of slave 1"
    ::= { slaveOneOutputStatus 19}
slaveOneOutputStatusTwenty OBJECT-TYPE
    SYNTAX      DisplayString
    MAX-ACCESS  read-write
    STATUS      current
    DESCRIPTION
	"The twentieth output status of slave 1"
    ::= { slaveOneOutputStatus 20}
slaveOneOutputStatusTwentyOne OBJECT-TYPE
    SYNTAX      DisplayString
    MAX-ACCESS  read-write
    STATUS      current
    DESCRIPTION
	"The twenty-first output status of slave 1"
    ::= { slaveOneOutputStatus 21}
slaveOneOutputStatusTwentyTwo OBJECT-TYPE
    SYNTAX      DisplayString
    MAX-ACCESS  read-write
    STATUS      current
    DESCRIPTION
	"The twenty-second output status of slave 1"
    ::= { slaveOneOutputStatus 22}
slaveOneOutputStatusTwentyThree OBJECT-TYPE
    SYNTAX      DisplayString
    MAX-ACCESS  read-write
    STATUS      current
    DESCRIPTION
	"The twenty-third output status of slave 1"
    ::= { slaveOneOutputStatus 23}
slaveOneOutputStatusTwentyFour OBJECT-TYPE
    SYNTAX      DisplayString
    MAX-ACCESS  read-write
    STATUS      current
    DESCRIPTION
	"The twenty-fourth output status of slave 1"
    ::= { slaveOneOutputStatus 24}

slaveOneOutputCurrent   OBJECT IDENTIFIER ::= { rpduSlaveOne 10}
slaveOneOutputCurrentOne OBJECT-TYPE
    SYNTAX      DisplayString
    MAX-ACCESS  read-only
    STATUS      current
    DESCRIPTION
	"The current value of the first output of the slave 1"
    ::= { slaveOneOutputCurrent 1}
slaveOneOutputCurrentTwo OBJECT-TYPE
    SYNTAX      DisplayString
    MAX-ACCESS  read-only
    STATUS      current
    DESCRIPTION
	"The current value of the second output of the slave 1"
    ::= { slaveOneOutputCurrent 2}
slaveOneOutputCurrentThree OBJECT-TYPE
    SYNTAX      DisplayString
    MAX-ACCESS  read-only
    STATUS      current
    DESCRIPTION
	"The current value of the third output of the slave 1"
    ::= { slaveOneOutputCurrent 3}
slaveOneOutputCurrentFour OBJECT-TYPE
    SYNTAX      DisplayString
    MAX-ACCESS  read-only
    STATUS      current
    DESCRIPTION
	"The current value of the fourth output of the slave 1"
    ::= { slaveOneOutputCurrent 4}
slaveOneOutputCurrentFive OBJECT-TYPE
    SYNTAX      DisplayString
    MAX-ACCESS  read-only
    STATUS      current
    DESCRIPTION
	"The current value of the fifth output of the slave 1"
    ::= { slaveOneOutputCurrent 5}
slaveOneOutputCurrentSix OBJECT-TYPE
    SYNTAX      DisplayString
    MAX-ACCESS  read-only
    STATUS      current
    DESCRIPTION
	"The current value of the sixth output of the slave 1"
    ::= { slaveOneOutputCurrent 6}
slaveOneOutputCurrentSeven OBJECT-TYPE
    SYNTAX      DisplayString
    MAX-ACCESS  read-only
    STATUS      current
    DESCRIPTION
	"The current value of the seventh output of the slave 1"
    ::= { slaveOneOutputCurrent 7}
slaveOneOutputCurrentEight OBJECT-TYPE
    SYNTAX      DisplayString
    MAX-ACCESS  read-only
    STATUS      current
    DESCRIPTION
	"The current value of the eighth output of the slave 1"
    ::= { slaveOneOutputCurrent 8}
slaveOneOutputCurrentNine OBJECT-TYPE
    SYNTAX      DisplayString
    MAX-ACCESS  read-only
    STATUS      current
    DESCRIPTION
	"The current value of the nineth output of the slave 1"
    ::= { slaveOneOutputCurrent 9}
slaveOneOutputCurrentTen OBJECT-TYPE
    SYNTAX      DisplayString
    MAX-ACCESS  read-only
    STATUS      current
    DESCRIPTION
	"The current value of the tenth output of the slave 1"
    ::= { slaveOneOutputCurrent 10}
slaveOneOutputCurrentEleven OBJECT-TYPE
    SYNTAX      DisplayString
    MAX-ACCESS  read-only
    STATUS      current
    DESCRIPTION
	"The current value of the eleventh output of the slave 1"
    ::= { slaveOneOutputCurrent 11}
slaveOneOutputCurrentTwelve OBJECT-TYPE
    SYNTAX      DisplayString
    MAX-ACCESS  read-only
    STATUS      current
    DESCRIPTION
	"The current value of the twelfth output of the slave 1"
    ::= { slaveOneOutputCurrent 12}
slaveOneOutputCurrentThirteen OBJECT-TYPE
    SYNTAX      DisplayString
    MAX-ACCESS  read-only
    STATUS      current
    DESCRIPTION
	"The current value of the thirteenth output of the slave 1"
    ::= { slaveOneOutputCurrent 13}
slaveOneOutputCurrentFourteen OBJECT-TYPE
    SYNTAX      DisplayString
    MAX-ACCESS  read-only
    STATUS      current
    DESCRIPTION
	"The current value of the fourteenth output of the slave 1"
    ::= { slaveOneOutputCurrent 14}
slaveOneOutputCurrentFifteen OBJECT-TYPE
    SYNTAX      DisplayString
    MAX-ACCESS  read-only
    STATUS      current
    DESCRIPTION
	"The current value of the fifteenth output of the slave 1"
    ::= { slaveOneOutputCurrent 15}
slaveOneOutputCurrentSixteen OBJECT-TYPE
    SYNTAX      DisplayString
    MAX-ACCESS  read-only
    STATUS      current
    DESCRIPTION
	"The current value of the sixteenth output of the slave 1"
    ::= { slaveOneOutputCurrent 16}
slaveOneOutputCurrentSeventeen OBJECT-TYPE
    SYNTAX      DisplayString
    MAX-ACCESS  read-only
    STATUS      current
    DESCRIPTION
	"The current value of the seventeenth output of the slave 1"
    ::= { slaveOneOutputCurrent 17}
slaveOneOutputCurrentEighteen OBJECT-TYPE
    SYNTAX      DisplayString
    MAX-ACCESS  read-only
    STATUS      current
    DESCRIPTION
	"The current value of the eighteenth output of the slave 1"
    ::= { slaveOneOutputCurrent 18}
slaveOneOutputCurrentNineteen OBJECT-TYPE
    SYNTAX      DisplayString
    MAX-ACCESS  read-only
    STATUS      current
    DESCRIPTION
	"The current value of the nineteenth output of the slave 1"
    ::= { slaveOneOutputCurrent 19}
slaveOneOutputCurrentTwenty OBJECT-TYPE
    SYNTAX      DisplayString
    MAX-ACCESS  read-only
    STATUS      current
    DESCRIPTION
	"The current value of the twentieth output of the slave 1"
    ::= { slaveOneOutputCurrent 20}
slaveOneOutputCurrentTwentyOne OBJECT-TYPE
    SYNTAX      DisplayString
    MAX-ACCESS  read-only
    STATUS      current
    DESCRIPTION
	"The current value of the twenty-first output of the slave 1"
    ::= { slaveOneOutputCurrent 21}
slaveOneOutputCurrentTwentyTwo OBJECT-TYPE
    SYNTAX      DisplayString
    MAX-ACCESS  read-only
    STATUS      current
    DESCRIPTION
	"The current value of the twenty-second output of the slave 1"
    ::= { slaveOneOutputCurrent 22}
slaveOneOutputCurrentTwentyThree OBJECT-TYPE
    SYNTAX      DisplayString
    MAX-ACCESS  read-only
    STATUS      current
    DESCRIPTION
	"The current value of the twenty-third output of the slave 1"
    ::= { slaveOneOutputCurrent 23}
slaveOneOutputCurrentTwentyFour OBJECT-TYPE
    SYNTAX      DisplayString
    MAX-ACCESS  read-only
    STATUS      current
    DESCRIPTION
	"The current value of the twenty-fourth output of the slave 1"
    ::= { slaveOneOutputCurrent 24}

slaveOneOutputCurrentMin   OBJECT IDENTIFIER ::= { rpduSlaveOne 11}
slaveOneOutputCurrentMinOne OBJECT-TYPE
    SYNTAX      DisplayString
    MAX-ACCESS  read-only
    STATUS      current
    DESCRIPTION
	"The Min. current value of the first output of slave 1"
    ::= { slaveOneOutputCurrentMin 1}
slaveOneOutputCurrentMinTwo OBJECT-TYPE
    SYNTAX      DisplayString
    MAX-ACCESS  read-only
    STATUS      current
    DESCRIPTION
	"The Min. current value of the second output of the slave 1"
    ::= { slaveOneOutputCurrentMin 2}
slaveOneOutputCurrentMinThree OBJECT-TYPE
    SYNTAX      DisplayString
    MAX-ACCESS  read-only
    STATUS      current
    DESCRIPTION
	"The Min. current value of the third output of the slave 1"
    ::= { slaveOneOutputCurrentMin 3}
slaveOneOutputCurrentMinFour OBJECT-TYPE
    SYNTAX      DisplayString
    MAX-ACCESS  read-only
    STATUS      current
    DESCRIPTION
	"The Min. current value of the fourth output of the slave 1"
    ::= { slaveOneOutputCurrentMin 4}
slaveOneOutputCurrentMinFive OBJECT-TYPE
    SYNTAX      DisplayString
    MAX-ACCESS  read-only
    STATUS      current
    DESCRIPTION
	"The Min. current value of the fifth output of the slave 1"
    ::= { slaveOneOutputCurrentMin 5}
slaveOneOutputCurrentMinSix OBJECT-TYPE
    SYNTAX      DisplayString
    MAX-ACCESS  read-only
    STATUS      current
    DESCRIPTION
	"The Min. current value of the sixth output of the slave 1"
    ::= { slaveOneOutputCurrentMin 6}
slaveOneOutputCurrentMinSeven OBJECT-TYPE
    SYNTAX      DisplayString
    MAX-ACCESS  read-only
    STATUS      current
    DESCRIPTION
	"The Min. current value of the seventh output of the slave 1"
    ::= { slaveOneOutputCurrentMin 7}
slaveOneOutputCurrentMinEight OBJECT-TYPE
    SYNTAX      DisplayString
    MAX-ACCESS  read-only
    STATUS      current
    DESCRIPTION
	"The Min. current value of the eighth output of the slave 1"
    ::= { slaveOneOutputCurrentMin 8}
slaveOneOutputCurrentMinNine OBJECT-TYPE
    SYNTAX      DisplayString
    MAX-ACCESS  read-only
    STATUS      current
    DESCRIPTION
	"The Min. current value of the nineth output of the slave 1"
    ::= { slaveOneOutputCurrentMin 9}
slaveOneOutputCurrentMinTen OBJECT-TYPE
    SYNTAX      DisplayString
    MAX-ACCESS  read-only
    STATUS      current
    DESCRIPTION
	"The Min. current value of the tenth output of the slave 1"
    ::= { slaveOneOutputCurrentMin 10}
slaveOneOutputCurrentMinEleven OBJECT-TYPE
    SYNTAX      DisplayString
    MAX-ACCESS  read-only
    STATUS      current
    DESCRIPTION
	"The Min. current value of the eleventh output of the slave 1"
    ::= { slaveOneOutputCurrentMin 11}
slaveOneOutputCurrentMinTwleve OBJECT-TYPE
    SYNTAX      DisplayString
    MAX-ACCESS  read-only
    STATUS      current
    DESCRIPTION
	"The Min. current value of the twelfth output of the slave 1"
    ::= { slaveOneOutputCurrentMin 12}
slaveOneOutputCurrentMinThirteen OBJECT-TYPE
    SYNTAX      DisplayString
    MAX-ACCESS  read-only
    STATUS      current
    DESCRIPTION
	"The Min. current value of the thirteenth output of the slave 1"
    ::= { slaveOneOutputCurrentMin 13}
slaveOneOutputCurrentMinFourteen OBJECT-TYPE
    SYNTAX      DisplayString
    MAX-ACCESS  read-only
    STATUS      current
    DESCRIPTION
	"The Min. current value of the fourteenth output of the slave 1"
    ::= { slaveOneOutputCurrentMin 14}
slaveOneOutputCurrentMinFifteen OBJECT-TYPE
    SYNTAX      DisplayString
    MAX-ACCESS  read-only
    STATUS      current
    DESCRIPTION
	"The Min. current value of the fifteenth output of the slave 1"
    ::= { slaveOneOutputCurrentMin 15}
slaveOneOutputCurrentMinSixteen OBJECT-TYPE
    SYNTAX      DisplayString
    MAX-ACCESS  read-only
    STATUS      current
    DESCRIPTION
	"The Min. current value of the sixteenth output of the slave 1"
    ::= { slaveOneOutputCurrentMin 16}
slaveOneOutputCurrentMinSeventeen OBJECT-TYPE
    SYNTAX      DisplayString
    MAX-ACCESS  read-only
    STATUS      current
    DESCRIPTION
	"The Min. current value of the seventeenth output of the slave 1"
    ::= { slaveOneOutputCurrentMin 17}
slaveOneOutputCurrentMinEighteen OBJECT-TYPE
    SYNTAX      DisplayString
    MAX-ACCESS  read-only
    STATUS      current
    DESCRIPTION
	"The Min. current value of the eighteenth output of the slave 1"
    ::= { slaveOneOutputCurrentMin 18}
slaveOneOutputCurrentMinNineteen OBJECT-TYPE
    SYNTAX      DisplayString
    MAX-ACCESS  read-only
    STATUS      current
    DESCRIPTION
	"The Min. current value of the nineteenth output of the slave 1"
    ::= { slaveOneOutputCurrentMin 19}
slaveOneOutputCurrentMinTwenty OBJECT-TYPE
    SYNTAX      DisplayString
    MAX-ACCESS  read-only
    STATUS      current
    DESCRIPTION
	"The Min. current value of the twentieth output of the slave 1"
    ::= { slaveOneOutputCurrentMin 20}
slaveOneOutputCurrentMinTwentyOne OBJECT-TYPE
    SYNTAX      DisplayString
    MAX-ACCESS  read-only
    STATUS      current
    DESCRIPTION
	"The Min. current value of the twentyth-first output of the slave 1"
    ::= { slaveOneOutputCurrentMin 21}
slaveOneOutputCurrentMinTwentyTwo OBJECT-TYPE
    SYNTAX      DisplayString
    MAX-ACCESS  read-only
    STATUS      current
    DESCRIPTION
	"The Min. current value of the twentyth-second output of the slave 1"
    ::= { slaveOneOutputCurrentMin 22}
slaveOneOutputCurrentMinTwentyThree OBJECT-TYPE
    SYNTAX      DisplayString
    MAX-ACCESS  read-only
    STATUS      current
    DESCRIPTION
	"The Min. current value of the twentyth-third output of the slave 1"
    ::= { slaveOneOutputCurrentMin 23}
slaveOneOutputCurrentMinTwentyFour OBJECT-TYPE
    SYNTAX      DisplayString
    MAX-ACCESS  read-only
    STATUS      current
    DESCRIPTION
	"The Min. current value of the twentyth-fourth output of the slave 1"
    ::= { slaveOneOutputCurrentMin 24}




slaveOneOutputCurrentMax   OBJECT IDENTIFIER ::= { rpduSlaveOne 12}
slaveOneOutputCurrentMaxOne OBJECT-TYPE
    SYNTAX      DisplayString
    MAX-ACCESS  read-only
    STATUS      current
    DESCRIPTION
	"The Max. current value of the first output of slave 1"
    ::= { slaveOneOutputCurrentMax 1}
slaveOneOutputCurrentMaxTwo OBJECT-TYPE
    SYNTAX      DisplayString
    MAX-ACCESS  read-only
    STATUS      current
    DESCRIPTION
	"The Max. current value of the second output of the slave 1"
    ::= { slaveOneOutputCurrentMax 2}
slaveOneOutputCurrentMaxThree OBJECT-TYPE
    SYNTAX      DisplayString
    MAX-ACCESS  read-only
    STATUS      current
    DESCRIPTION
	"The Max. current value of the third output of the slave 1"
    ::= { slaveOneOutputCurrentMax 3}
slaveOneOutputCurrentMaxFour OBJECT-TYPE
    SYNTAX      DisplayString
    MAX-ACCESS  read-only
    STATUS      current
    DESCRIPTION
	"The Max. current value of the fourth output of the slave 1"
    ::= { slaveOneOutputCurrentMax 4}
slaveOneOutputCurrentMaxFive OBJECT-TYPE
    SYNTAX      DisplayString
    MAX-ACCESS  read-only
    STATUS      current
    DESCRIPTION
	"The Max. current value of the fifth output of the slave 1"
    ::= { slaveOneOutputCurrentMax 5}
slaveOneOutputCurrentMaxSix OBJECT-TYPE
    SYNTAX      DisplayString
    MAX-ACCESS  read-only
    STATUS      current
    DESCRIPTION
	"The Max. current value of the sixth output of the slave 1"
    ::= { slaveOneOutputCurrentMax 6}
slaveOneOutputCurrentMaxSeven OBJECT-TYPE
    SYNTAX      DisplayString
    MAX-ACCESS  read-only
    STATUS      current
    DESCRIPTION
	"The Max. current value of the seventh output of the slave 1"
    ::= { slaveOneOutputCurrentMax 7}
slaveOneOutputCurrentMaxEight OBJECT-TYPE
    SYNTAX      DisplayString
    MAX-ACCESS  read-only
    STATUS      current
    DESCRIPTION
	"The Max. current value of the eighth output of the slave 1"
    ::= { slaveOneOutputCurrentMax 8}
slaveOneOutputCurrentMaxNine OBJECT-TYPE
    SYNTAX      DisplayString
    MAX-ACCESS  read-only
    STATUS      current
    DESCRIPTION
	"The Max. current value of the nineth output of the slave 1"
    ::= { slaveOneOutputCurrentMax 9}
slaveOneOutputCurrentMaxTen OBJECT-TYPE
    SYNTAX      DisplayString
    MAX-ACCESS  read-only
    STATUS      current
    DESCRIPTION
	"The Max. current value of the tenth output of the slave 1"
    ::= { slaveOneOutputCurrentMax 10}
slaveOneOutputCurrentMaxEleven OBJECT-TYPE
    SYNTAX      DisplayString
    MAX-ACCESS  read-only
    STATUS      current
    DESCRIPTION
	"The Max. current value of the eleventh output of the slave 1"
    ::= { slaveOneOutputCurrentMax 11}
slaveOneOutputCurrentMaxTwleve OBJECT-TYPE
    SYNTAX      DisplayString
    MAX-ACCESS  read-only
    STATUS      current
    DESCRIPTION
	"The Max. current value of the twelfth output of the slave 1"
    ::= { slaveOneOutputCurrentMax 12}
slaveOneOutputCurrentMaxThirteen OBJECT-TYPE
    SYNTAX      DisplayString
    MAX-ACCESS  read-only
    STATUS      current
    DESCRIPTION
	"The Max. current value of the thirteenth output of the slave 1"
    ::= { slaveOneOutputCurrentMax 13}
slaveOneOutputCurrentMaxFourteen OBJECT-TYPE
    SYNTAX      DisplayString
    MAX-ACCESS  read-only
    STATUS      current
    DESCRIPTION
	"The Max. current value of the fourteenth output of the slave 1"
    ::= { slaveOneOutputCurrentMax 14}
slaveOneOutputCurrentMaxFifteen OBJECT-TYPE
    SYNTAX      DisplayString
    MAX-ACCESS  read-only
    STATUS      current
    DESCRIPTION
	"The Max. current value of the fifteenth output of the slave 1"
    ::= { slaveOneOutputCurrentMax 15}
slaveOneOutputCurrentMaxSixteen OBJECT-TYPE
    SYNTAX      DisplayString
    MAX-ACCESS  read-only
    STATUS      current
    DESCRIPTION
	"The Max. current value of the sixteenth output of the slave 1"
    ::= { slaveOneOutputCurrentMax 16}
slaveOneOutputCurrentMaxSeventeen OBJECT-TYPE
    SYNTAX      DisplayString
    MAX-ACCESS  read-only
    STATUS      current
    DESCRIPTION
	"The Max. current value of the seventeenth output of the slave 1"
    ::= { slaveOneOutputCurrentMax 17}
slaveOneOutputCurrentMaxEighteen OBJECT-TYPE
    SYNTAX      DisplayString
    MAX-ACCESS  read-only
    STATUS      current
    DESCRIPTION
	"The Max. current value of the eighteenth output of the slave 1"
    ::= { slaveOneOutputCurrentMax 18}
slaveOneOutputCurrentMaxNineteen OBJECT-TYPE
    SYNTAX      DisplayString
    MAX-ACCESS  read-only
    STATUS      current
    DESCRIPTION
	"The Max. current value of the nineteenth output of the slave 1"
    ::= { slaveOneOutputCurrentMax 19}
slaveOneOutputCurrentMaxTwenty OBJECT-TYPE
    SYNTAX      DisplayString
    MAX-ACCESS  read-only
    STATUS      current
    DESCRIPTION
	"The Max. current value of the twentieth output of the slave 1"
    ::= { slaveOneOutputCurrentMax 20}
slaveOneOutputCurrentMaxTwentyOne OBJECT-TYPE
    SYNTAX      DisplayString
    MAX-ACCESS  read-only
    STATUS      current
    DESCRIPTION
	"The Max. current value of the twenty-first output of the slave 1"
    ::= { slaveOneOutputCurrentMax 21}
slaveOneOutputCurrentMaxTwentyTwo OBJECT-TYPE
    SYNTAX      DisplayString
    MAX-ACCESS  read-only
    STATUS      current
    DESCRIPTION
	"The Max. current value of the twenty-second output of the slave 1"
    ::= { slaveOneOutputCurrentMax 22}
slaveOneOutputCurrentMaxTwentyThree OBJECT-TYPE
    SYNTAX      DisplayString
    MAX-ACCESS  read-only
    STATUS      current
    DESCRIPTION
	"The Max. current value of the twenty-third output of the slave 1"
    ::= { slaveOneOutputCurrentMax 23}
slaveOneOutputCurrentMaxTwentyFour OBJECT-TYPE
    SYNTAX      DisplayString
    MAX-ACCESS  read-only
    STATUS      current
    DESCRIPTION
	"The Max. current value of the twenty-fourth output of the slave 1"
    ::= { slaveOneOutputCurrentMax 24}


slaveOneOutputCurrentEnergy  OBJECT IDENTIFIER ::= { rpduSlaveOne 13}
slaveOneOutputCurrentEnergyOne OBJECT-TYPE
    SYNTAX	DisplayString
    MAX-ACCESS	read-only
    STATUS	current
    DESCRIPTION
	"The energy value of the first output of slave 1"
    ::={slaveOneOutputCurrentEnergy 1}
slaveOneOutputCurrentEnergyTwo OBJECT-TYPE
    SYNTAX	DisplayString
    MAX-ACCESS	read-only
    STATUS	current
    DESCRIPTION
	"The energy value of the second output of the slave 1"
    ::={slaveOneOutputCurrentEnergy 2}
slaveOneOutputCurrentEnergyThree OBJECT-TYPE
    SYNTAX	DisplayString
    MAX-ACCESS	read-only
    STATUS	current
    DESCRIPTION
	"The energy value of the third output of the slave 1"
    ::={slaveOneOutputCurrentEnergy 3}
slaveOneOutputCurrentEnergyFour OBJECT-TYPE
    SYNTAX	DisplayString
    MAX-ACCESS	read-only
    STATUS	current
    DESCRIPTION
	"The energy value of the fourth output of the slave 1"
    ::={slaveOneOutputCurrentEnergy 4}
slaveOneOutputCurrentEnergyFive OBJECT-TYPE
    SYNTAX	DisplayString
    MAX-ACCESS	read-only
    STATUS	current
    DESCRIPTION
	"The energy value of the fifth output of the slave 1"
    ::={slaveOneOutputCurrentEnergy 5}
slaveOneOutputCurrentEnergySix OBJECT-TYPE
    SYNTAX	DisplayString
    MAX-ACCESS	read-only
    STATUS	current
    DESCRIPTION
	"The energy value of the sixth output of the slave 1"
    ::={slaveOneOutputCurrentEnergy 6}
slaveOneOutputCurrentEnergySeven OBJECT-TYPE
    SYNTAX	DisplayString
    MAX-ACCESS	read-only
    STATUS	current
    DESCRIPTION
	"The energy value of the seventh output of the slave 1"
    ::={slaveOneOutputCurrentEnergy 7}
slaveOneOutputCurrentEnergyEight OBJECT-TYPE
    SYNTAX	DisplayString
    MAX-ACCESS	read-only
    STATUS	current
    DESCRIPTION
	"The energy value of the eighth output of the slave 1"
    ::={slaveOneOutputCurrentEnergy 8}
slaveOneOutputCurrentEnergyNine OBJECT-TYPE
    SYNTAX	DisplayString
    MAX-ACCESS	read-only
    STATUS	current
    DESCRIPTION
	"The energy value of the nineth output of the slave 1"
    ::={slaveOneOutputCurrentEnergy 9}
slaveOneOutputCurrentEnergyTen OBJECT-TYPE
    SYNTAX	DisplayString
    MAX-ACCESS	read-only
    STATUS	current
    DESCRIPTION
	"The energy value of the tenth output of the slave 1"
    ::={slaveOneOutputCurrentEnergy 10}
slaveOneOutputCurrentEnergyEleven OBJECT-TYPE
    SYNTAX	DisplayString
    MAX-ACCESS	read-only
    STATUS	current
    DESCRIPTION
	"The energy value of the eleventh output of the slave 1"
    ::={slaveOneOutputCurrentEnergy 11}
slaveOneOutputCurrentEnergyTwelve OBJECT-TYPE
    SYNTAX	DisplayString
    MAX-ACCESS	read-only
    STATUS	current
    DESCRIPTION
	"The energy value of the twelfth output of the slave 1"
    ::={slaveOneOutputCurrentEnergy 12}
slaveOneOutputCurrentEnergyThirteen OBJECT-TYPE
    SYNTAX	DisplayString
    MAX-ACCESS	read-only
    STATUS	current
    DESCRIPTION
	"The energy value of the thirteenth output of the slave 1"
    ::={slaveOneOutputCurrentEnergy 13}
slaveOneOutputCurrentEnergyFourteen OBJECT-TYPE
    SYNTAX	DisplayString
    MAX-ACCESS	read-only
    STATUS	current
    DESCRIPTION
	"The energy value of the fourteenth output of the slave 1"
    ::={slaveOneOutputCurrentEnergy 14}
slaveOneOutputCurrentEnergyFifteen OBJECT-TYPE
    SYNTAX	DisplayString
    MAX-ACCESS	read-only
    STATUS	current
    DESCRIPTION
	"The energy value of the fifteenth output of the slave 1"
    ::={slaveOneOutputCurrentEnergy 15}
slaveOneOutputCurrentEnergySixteen OBJECT-TYPE
    SYNTAX	DisplayString
    MAX-ACCESS	read-only
    STATUS	current
    DESCRIPTION
	"The energy value of the sixteenth output of the slave 1"
    ::={slaveOneOutputCurrentEnergy 16}
slaveOneOutputCurrentEnergySeventeen OBJECT-TYPE
    SYNTAX	DisplayString
    MAX-ACCESS	read-only
    STATUS	current
    DESCRIPTION
	"The energy value of the seventeenth output of the slave 1"
    ::={slaveOneOutputCurrentEnergy 17}
slaveOneOutputCurrentEnergyEighteen OBJECT-TYPE
    SYNTAX	DisplayString
    MAX-ACCESS	read-only
    STATUS	current
    DESCRIPTION
	"The energy value of the eighteenth output of the slave 1"
    ::={slaveOneOutputCurrentEnergy 18}
slaveOneOutputCurrentEnergyNineteen OBJECT-TYPE
    SYNTAX	DisplayString
    MAX-ACCESS	read-only
    STATUS	current
    DESCRIPTION
	"The energy value of the nineteenth output of the slave 1"
    ::={slaveOneOutputCurrentEnergy 19}
slaveOneOutputCurrentEnergyTwenty OBJECT-TYPE
    SYNTAX	DisplayString
    MAX-ACCESS	read-only
    STATUS	current
    DESCRIPTION
	"The energy value of the twentieth output of the slave 1"
    ::={slaveOneOutputCurrentEnergy 20}
slaveOneOutputCurrentEnergyTwentyOne OBJECT-TYPE
    SYNTAX	DisplayString
    MAX-ACCESS	read-only
    STATUS	current
    DESCRIPTION
	"The energy value of the twenty-first output of the slave 1"
    ::={slaveOneOutputCurrentEnergy 21}
slaveOneOutputCurrentEnergyTwentyTwo OBJECT-TYPE
    SYNTAX	DisplayString
    MAX-ACCESS	read-only
    STATUS	current
    DESCRIPTION
	"The energy value of the twenty-second output of the slave 1"
    ::={slaveOneOutputCurrentEnergy 22}
slaveOneOutputCurrentEnergyTwentyThree OBJECT-TYPE
    SYNTAX	DisplayString
    MAX-ACCESS	read-only
    STATUS	current
    DESCRIPTION
	"The energy value of the twenty-third output of the slave 1"
    ::={slaveOneOutputCurrentEnergy 23}
slaveOneOutputCurrentEnergyTwentyFour OBJECT-TYPE
    SYNTAX	DisplayString
    MAX-ACCESS	read-only
    STATUS	current
    DESCRIPTION
	"The energy value of the twenty-fourth output of the slave 1"
    ::={slaveOneOutputCurrentEnergy 24}

-------------------------------Slave2---------------------------------------------  
rpduDeviceThree OBJECT IDENTIFIER ::= { rpdu 3}
rpduSlaveTwo OBJECT IDENTIFIER ::= { rpduDeviceThree 1}

slaveTwoName OBJECT-TYPE
    SYNTAX      DisplayString
    MAX-ACCESS  read-write
    STATUS      current
    DESCRIPTION
	"This is the third device."
    ::= { rpduSlaveTwo 1}
    
slaveTwoType OBJECT-TYPE
    SYNTAX      DisplayString
    MAX-ACCESS  read-only
    STATUS      current
    DESCRIPTION
	"This is device type "
    ::= { rpduSlaveTwo 2}
    
slaveTwoOutputNumber OBJECT-TYPE 
    SYNTAX      Integer32
    MAX-ACCESS  read-only
    STATUS      current
    DESCRIPTION
	"This is the output quantity"
::= { rpduSlaveTwo 7}
    
slaveTwoLineOne OBJECT IDENTIFIER ::= { rpduSlaveTwo 3}
slaveTwoLineOnePower OBJECT-TYPE
    SYNTAX      DisplayString
    MAX-ACCESS  read-only
    STATUS      current
    DESCRIPTION
	"The power of phase one"
    ::= { slaveTwoLineOne 1}
slaveTwoLineOnePF OBJECT-TYPE
    SYNTAX      DisplayString
    MAX-ACCESS  read-only
    STATUS      current
    DESCRIPTION
	"The power factor of phase one"
    ::= { slaveTwoLineOne 2}
    
slaveTwoLineOneEnergy OBJECT-TYPE
    SYNTAX      DisplayString
    MAX-ACCESS  read-only
    STATUS      current
    DESCRIPTION
	"The energy of phase one"
    ::= { slaveTwoLineOne 3}
slaveTwoLineOneCurrent OBJECT-TYPE
    SYNTAX      DisplayString
    MAX-ACCESS  read-only
    STATUS      current
    DESCRIPTION
	"The current of phase one"
    ::= { slaveTwoLineOne 4}
slaveTwoLineOneVoltage OBJECT-TYPE
    SYNTAX      Integer32
    MAX-ACCESS  read-only
    STATUS      current
    DESCRIPTION
	"The voltage of phase one"
    ::= { slaveTwoLineOne 5}
slaveTwoLineOneCurrentMin OBJECT-TYPE
    SYNTAX      DisplayString
    MAX-ACCESS  read-only
    STATUS      current
    DESCRIPTION
	"The Min. current value of phase one"
	::= { slaveTwoLineOne 6}
slaveTwoLineOneCurrentMax OBJECT-TYPE
    SYNTAX      DisplayString
    MAX-ACCESS  read-only
    STATUS      current
    DESCRIPTION
	"The Max. current value of phase one"
    ::= { slaveTwoLineOne 7}
    
slaveTwoLineOneVoltageMin OBJECT-TYPE
    SYNTAX      Integer32
    MAX-ACCESS  read-only
    STATUS      current
    DESCRIPTION
	"The Min. voltage value of phase one"
    ::= { slaveTwoLineOne 8}
    
slaveTwoLineOneVoltageMax OBJECT-TYPE
    SYNTAX      Integer32
    MAX-ACCESS  read-only
    STATUS      current
    DESCRIPTION
	"The Max. voltage value of phase one"
    ::= { slaveTwoLineOne 9}


slaveTwoLineTwo OBJECT IDENTIFIER ::= { rpduSlaveTwo 4}
slaveTwoLineTwoPower OBJECT-TYPE
    SYNTAX      DisplayString
    MAX-ACCESS  read-only
    STATUS      current
    DESCRIPTION
	"The power of phase two"
    ::= { slaveTwoLineTwo 1}

slaveTwoLineTwoPF OBJECT-TYPE
    SYNTAX      DisplayString
    MAX-ACCESS  read-only
    STATUS      current
    DESCRIPTION
	"The power factor of phase two"   
    ::= { slaveTwoLineTwo 2}
    
slaveTwoLineTwoEnergy OBJECT-TYPE
    SYNTAX      DisplayString
    MAX-ACCESS  read-only
    STATUS      current
    DESCRIPTION
	"The energy of phase two"
    ::= { slaveTwoLineTwo 3}
slaveTwoLineTwoCurrent OBJECT-TYPE           
    SYNTAX      DisplayString 
    MAX-ACCESS  read-only
    STATUS      current
    DESCRIPTION
	"The current of phase two"
    ::= { slaveTwoLineTwo 4}
slaveTwoLineTwoVoltage OBJECT-TYPE
    SYNTAX      Integer32
    MAX-ACCESS  read-only
    STATUS      current
    DESCRIPTION
	"The voltage of phase two"
    ::= { slaveTwoLineTwo 5}
slaveTwoLineTwoCurrentMin OBJECT-TYPE
    SYNTAX      DisplayString
    MAX-ACCESS  read-only
    STATUS      current
    DESCRIPTION
	"The Min. current value of phase two"
    ::= { slaveTwoLineTwo 6}
slaveTwoLineTwoCurrentMax OBJECT-TYPE
    SYNTAX      DisplayString
    MAX-ACCESS  read-only
    STATUS      current
    DESCRIPTION
	"The Max. current value of phase two"
    ::= { slaveTwoLineTwo 7}
    
slaveTwoLineTwoVoltageMin OBJECT-TYPE
    SYNTAX      Integer32
    MAX-ACCESS  read-only
    STATUS      current
    DESCRIPTION
	"The Min. voltage value of phase two"
    ::= { slaveTwoLineTwo 8}
    
slaveTwoLineTwoVoltageMax OBJECT-TYPE
    SYNTAX      Integer32
    MAX-ACCESS  read-only
    STATUS      current
    DESCRIPTION
	"The Max. voltage value of phase two"
    ::= { slaveTwoLineTwo 9}



slaveTwoLineThree OBJECT IDENTIFIER ::= { rpduSlaveTwo 5}
slaveTwoLineThreePower OBJECT-TYPE
    SYNTAX      DisplayString
    MAX-ACCESS  read-only
    STATUS      current
    DESCRIPTION
	"The power of phase three"
    ::= { slaveTwoLineThree 1}

slaveTwoLineThreePF OBJECT-TYPE
    SYNTAX      DisplayString
    MAX-ACCESS  read-only
    STATUS      current
    DESCRIPTION
	"The power factor of phase three"     
    ::= { slaveTwoLineThree 2}
    
slaveTwoLineThreeEnergy OBJECT-TYPE
    SYNTAX      DisplayString
    MAX-ACCESS  read-only
    STATUS      current
    DESCRIPTION
	"The energy of phase three"
    ::= { slaveTwoLineThree 3}
slaveTwoLineThreeCurrent OBJECT-TYPE
    SYNTAX      DisplayString
    MAX-ACCESS  read-only
    STATUS      current
    DESCRIPTION
	"The current of phase three"
    ::= { slaveTwoLineThree 4}
slaveTwoLineThreeVoltage OBJECT-TYPE
    SYNTAX      Integer32
    MAX-ACCESS  read-only
    STATUS      current
    DESCRIPTION
	"The voltage of phase three"
    ::= { slaveTwoLineThree 5}
slaveTwoLineThreeCurrentMin OBJECT-TYPE
    SYNTAX      DisplayString
    MAX-ACCESS  read-only
    STATUS      current
    DESCRIPTION
	"The Min. current value of phase three"
    ::= { slaveTwoLineThree 6}
slaveTwoLineThreeCurrentMax OBJECT-TYPE
    SYNTAX      DisplayString
    MAX-ACCESS  read-only
    STATUS      current
    DESCRIPTION
	"The Max. current value of phase three"
    ::= { slaveTwoLineThree 7}
    
slaveTwoLineThreeVoltageMin OBJECT-TYPE
    SYNTAX      Integer32
    MAX-ACCESS  read-only
    STATUS      current
    DESCRIPTION
	"The Min. voltage value of phase three"
    ::= { slaveTwoLineThree 8}
    
slaveTwoLineThreeVoltageMax OBJECT-TYPE
    SYNTAX      Integer32
    MAX-ACCESS  read-only
    STATUS      current
    DESCRIPTION
	"The Max. voltage value of phase three"
    ::= { slaveTwoLineThree 9}


slaveTwoSensor OBJECT IDENTIFIER ::= { rpduSlaveTwo 6}
slaveTwoTempOne OBJECT-TYPE
    SYNTAX      Integer32
    MAX-ACCESS  read-only
    STATUS      current
    DESCRIPTION
	"The first temperature sensor of slave 2"
    ::= { slaveTwoSensor 1}
slaveTwoTempTwo OBJECT-TYPE
    SYNTAX      Integer32
    MAX-ACCESS  read-only
    STATUS      current
    DESCRIPTION
	"The second temperature sensor of slave 2"
    ::= { slaveTwoSensor 2}
slaveTwoTempThree OBJECT-TYPE
    SYNTAX      Integer32
    MAX-ACCESS  read-only
    STATUS      current
    DESCRIPTION
	"The third temperature sensor of slave 2"
    ::= { slaveTwoSensor 3}
slaveTwoTempFour OBJECT-TYPE
    SYNTAX      Integer32
    MAX-ACCESS  read-only
    STATUS      current
    DESCRIPTION
	"The fourth temperature sensor of slave 2"
    ::= { slaveTwoSensor 4}
slaveTwoHumOne OBJECT-TYPE
    SYNTAX      Integer32
    MAX-ACCESS  read-only
    STATUS      current
    DESCRIPTION
	"The first humidity sensor of slave 2"
    ::= { slaveTwoSensor 5}
slaveTwoHumTwo OBJECT-TYPE
    SYNTAX      Integer32
    MAX-ACCESS  read-only
    STATUS      current
    DESCRIPTION
	"The second humidity sensor of slave 2"
    ::= { slaveTwoSensor 6}
slaveTwoHumThree OBJECT-TYPE
    SYNTAX      Integer32
    MAX-ACCESS  read-only
    STATUS      current
    DESCRIPTION
	"The third humidity sensor of slave 2"
    ::= { slaveTwoSensor 7}
slaveTwoHumFour OBJECT-TYPE
    SYNTAX      Integer32
    MAX-ACCESS  read-only
    STATUS      current
    DESCRIPTION
	"The fourth humidity sensor of slave 2"
    ::= { slaveTwoSensor 8}
slaveTwoDoorOne OBJECT-TYPE
    SYNTAX      DisplayString
    MAX-ACCESS  read-only
    STATUS      current
    DESCRIPTION
	"The first door sensor of slave 2"    
    ::= { slaveTwoSensor 9}
slaveTwoDoorTwo OBJECT-TYPE
    SYNTAX      DisplayString
    MAX-ACCESS  read-only
    STATUS      current
    DESCRIPTION
	"The second door sensor of slave 2"  
    ::= { slaveTwoSensor 10}
slaveTwoSmoke OBJECT-TYPE
    SYNTAX      DisplayString
    MAX-ACCESS  read-only
    STATUS      current
    DESCRIPTION
	"The smoke sensor of slave 2"
    ::= { slaveTwoSensor 11}
slaveTwoWater OBJECT-TYPE
    SYNTAX      DisplayString
    MAX-ACCESS  read-only
    STATUS      current
    DESCRIPTION
	"The water sensor of slave 2"
    ::= { slaveTwoSensor 12}


	
        
slaveTwoOutputName OBJECT IDENTIFIER ::= { rpduSlaveTwo 8}
slaveTwoOutputNameOne OBJECT-TYPE
    SYNTAX      DisplayString
    MAX-ACCESS  read-write
    STATUS      current
    DESCRIPTION
	"The first output name of slave 2"
    ::= { slaveTwoOutputName 1}

slaveTwoOutputNameTwo OBJECT-TYPE
    SYNTAX      DisplayString
    MAX-ACCESS  read-write
    STATUS      current
    DESCRIPTION
	"The second output name of slave 2"
    ::= { slaveTwoOutputName 2}
slaveTwoOutputNameThree OBJECT-TYPE
    SYNTAX      DisplayString
    MAX-ACCESS  read-write
    STATUS      current
    DESCRIPTION
	"The third output name of slave 2"
    ::= { slaveTwoOutputName 3}
slaveTwoOutputNameFour OBJECT-TYPE
    SYNTAX      DisplayString
    MAX-ACCESS  read-write
    STATUS      current
    DESCRIPTION
	"The fourth output name of slave 2"
    ::= { slaveTwoOutputName 4}
slaveTwoOutputNameFive OBJECT-TYPE
    SYNTAX      DisplayString
    MAX-ACCESS  read-write
    STATUS      current
    DESCRIPTION
	"The fifth output name of slave 2"
    ::= { slaveTwoOutputName 5}
slaveTwoOutputNameSix OBJECT-TYPE
    SYNTAX      DisplayString
    MAX-ACCESS  read-write
    STATUS      current
    DESCRIPTION
	"The sixth output name of slave 2"
    ::= { slaveTwoOutputName 6}
slaveTwoOutputNameSeven OBJECT-TYPE
    SYNTAX      DisplayString
    MAX-ACCESS  read-write
    STATUS      current
    DESCRIPTION
	"The seventh output name of slave 2"
    ::= { slaveTwoOutputName 7}
slaveTwoOutputNameEight OBJECT-TYPE
    SYNTAX      DisplayString
    MAX-ACCESS  read-write
    STATUS      current
    DESCRIPTION
	"The eighth output name of slave 2"
    ::= { slaveTwoOutputName 8}
slaveTwoOutputNameNine OBJECT-TYPE
    SYNTAX      DisplayString
    MAX-ACCESS  read-write
    STATUS      current
    DESCRIPTION
	"The nineth output name of slave 2"
    ::= { slaveTwoOutputName 9}
slaveTwoOutputNameTen OBJECT-TYPE
    SYNTAX      DisplayString
    MAX-ACCESS  read-write
    STATUS      current
    DESCRIPTION
	"The tenth output name of slave 2"
    ::= { slaveTwoOutputName 10}
slaveTwoOutputNameEleven OBJECT-TYPE
    SYNTAX      DisplayString
    MAX-ACCESS  read-write
    STATUS      current
    DESCRIPTION
	"The eleventh output name of slave 2"
    ::= { slaveTwoOutputName 11}
slaveTwoOutputNameTwelve OBJECT-TYPE
    SYNTAX      DisplayString
    MAX-ACCESS  read-write
    STATUS      current
    DESCRIPTION
	"The twelfth output name of slave 2"
    ::= { slaveTwoOutputName 12}
slaveTwoOutputNameThirteen OBJECT-TYPE
    SYNTAX      DisplayString
    MAX-ACCESS  read-write
    STATUS      current
    DESCRIPTION
	"The thirteenth output name of slave 2"
    ::= { slaveTwoOutputName 13}
slaveTwoOutputNameFourteen OBJECT-TYPE
    SYNTAX      DisplayString
    MAX-ACCESS  read-write
    STATUS      current
    DESCRIPTION
	"The fourteenth output name of slave 2"
    ::= { slaveTwoOutputName 14}
slaveTwoOutputNameFifteen OBJECT-TYPE
    SYNTAX      DisplayString
    MAX-ACCESS  read-write
    STATUS      current
    DESCRIPTION
	"The fifteenth output name of slave 2"
    ::= { slaveTwoOutputName 15}
slaveTwoOutputNameSixteen OBJECT-TYPE
    SYNTAX      DisplayString
    MAX-ACCESS  read-write
    STATUS      current
    DESCRIPTION
	"The sixteenth output name of slave 2"
    ::= { slaveTwoOutputName 16}
slaveTwoOutputNameSeventeen OBJECT-TYPE
    SYNTAX      DisplayString
    MAX-ACCESS  read-write
    STATUS      current
    DESCRIPTION
	"The seventeenth output name of slave 2"
    ::= { slaveTwoOutputName 17}
slaveTwoOutputNameEighteen OBJECT-TYPE
    SYNTAX      DisplayString
    MAX-ACCESS  read-write
    STATUS      current
    DESCRIPTION
	"The eighteenh output name of slave 2"
    ::= { slaveTwoOutputName 18}
slaveTwoOutputNameNineteen OBJECT-TYPE
    SYNTAX      DisplayString
    MAX-ACCESS  read-write
    STATUS      current
    DESCRIPTION
	"The nineteenth output name of slave 2"
    ::= { slaveTwoOutputName 19}
slaveTwoOutputNameTwenty OBJECT-TYPE
    SYNTAX      DisplayString
    MAX-ACCESS  read-write
    STATUS      current
    DESCRIPTION
	"The twentieth output name of slave 2"
    ::= { slaveTwoOutputName 20}
slaveTwoOutputNameTwentyOne OBJECT-TYPE
    SYNTAX      DisplayString
    MAX-ACCESS  read-write
    STATUS      current
    DESCRIPTION
	"The twenty-first output name of slave 2"
    ::= { slaveTwoOutputName 21}
slaveTwoOutputNameTwentyTwo OBJECT-TYPE
    SYNTAX      DisplayString
    MAX-ACCESS  read-write
    STATUS      current
    DESCRIPTION
	"The twenty-second output name of slave 2"
    ::= { slaveTwoOutputName 22}
slaveTwoOutputNameTwentyThree OBJECT-TYPE
    SYNTAX      DisplayString
    MAX-ACCESS  read-write
    STATUS      current
    DESCRIPTION
	"The twenty-third output name of slave 2"
    ::= { slaveTwoOutputName 23}
slaveTwoOutputNameTwentyFour OBJECT-TYPE
    SYNTAX      DisplayString
    MAX-ACCESS  read-write
    STATUS      current
    DESCRIPTION
	"The twenty-fourth output name of slave 2"
    ::= { slaveTwoOutputName 24}


    
slaveTwoOutputStatus OBJECT IDENTIFIER ::= { rpduSlaveTwo 9}

slaveTwoOutputStatusOne OBJECT-TYPE
    SYNTAX      DisplayString
    MAX-ACCESS  read-write
    STATUS      current
    DESCRIPTION
	"The first output status of slave 2"
    ::= { slaveTwoOutputStatus 1}
slaveTwoOutputStatusTwo OBJECT-TYPE
    SYNTAX      DisplayString
    MAX-ACCESS  read-write
    STATUS      current
    DESCRIPTION
	"The second output status of slave 2"
    ::= { slaveTwoOutputStatus 2}

slaveTwoOutputStatusThree OBJECT-TYPE
    SYNTAX      DisplayString
    MAX-ACCESS  read-write
    STATUS      current
    DESCRIPTION
	"The third output status of slave 2"
    ::= { slaveTwoOutputStatus 3}
slaveTwoOutputStatusFour OBJECT-TYPE
    SYNTAX      DisplayString
    MAX-ACCESS  read-write
    STATUS      current
    DESCRIPTION
	"The fourth output status of slave 2"
    ::= { slaveTwoOutputStatus 4}
slaveTwoOutputStatusFive OBJECT-TYPE
    SYNTAX      DisplayString
    MAX-ACCESS  read-write
    STATUS      current
    DESCRIPTION
	"The fifth output status of slave 2"
    ::= { slaveTwoOutputStatus 5}
slaveTwoOutputStatusSix OBJECT-TYPE
    SYNTAX      DisplayString
    MAX-ACCESS  read-write
    STATUS      current
    DESCRIPTION
	"The sixth output status of slave 2"
    ::= { slaveTwoOutputStatus 6}
slaveTwoOutputStatusSeven OBJECT-TYPE
    SYNTAX      DisplayString
    MAX-ACCESS  read-write
    STATUS      current
    DESCRIPTION
	"The seventh output status of slave 2"
    ::= { slaveTwoOutputStatus 7}
slaveTwoOutputStatusEight OBJECT-TYPE
    SYNTAX      DisplayString
    MAX-ACCESS  read-write
    STATUS      current
    DESCRIPTION
	"The eighth output status of slave 2"
    ::= { slaveTwoOutputStatus 8}
slaveTwoOutputStatusNine OBJECT-TYPE
    SYNTAX      DisplayString
    MAX-ACCESS  read-write
    STATUS      current
    DESCRIPTION
	"The nineth output status of slave 2"
    ::= { slaveTwoOutputStatus 9}
slaveTwoOutputStatusTen OBJECT-TYPE
    SYNTAX      DisplayString
    MAX-ACCESS  read-write
    STATUS      current
    DESCRIPTION
	"The tenth output status of slave 2"
    ::= { slaveTwoOutputStatus 10}
slaveTwoOutputStatusEleven OBJECT-TYPE
    SYNTAX      DisplayString
    MAX-ACCESS  read-write
    STATUS      current
    DESCRIPTION
	"The eleventh output status of slave 2"
    ::= { slaveTwoOutputStatus 11}
slaveTwoOutputStatusTwelve OBJECT-TYPE
    SYNTAX      DisplayString
    MAX-ACCESS  read-write
    STATUS      current
    DESCRIPTION
	"The twelfth output status of slave 2"
    ::= { slaveTwoOutputStatus 12}
slaveTwoOutputStatusThirteen OBJECT-TYPE
    SYNTAX      DisplayString
    MAX-ACCESS  read-write
    STATUS      current
    DESCRIPTION
	"The thirteenth output status of slave 2"
    ::= { slaveTwoOutputStatus 13}
slaveTwoOutputStatusFourteen OBJECT-TYPE
    SYNTAX      DisplayString
    MAX-ACCESS  read-write
    STATUS      current
    DESCRIPTION
	"The fourteenth output status of slave 2"
    ::= { slaveTwoOutputStatus 14}
slaveTwoOutputStatusFifteen OBJECT-TYPE
    SYNTAX      DisplayString
    MAX-ACCESS  read-write
    STATUS      current
    DESCRIPTION
	"The fifteenth output status of slave 2"
    ::= { slaveTwoOutputStatus 15}
slaveTwoOutputStatusSixteen OBJECT-TYPE
    SYNTAX      DisplayString
    MAX-ACCESS  read-write
    STATUS      current
    DESCRIPTION
	"The sixteenth output status of slave 2"
    ::= { slaveTwoOutputStatus 16}
slaveTwoOutputStatusSeventeen OBJECT-TYPE
    SYNTAX      DisplayString
    MAX-ACCESS  read-write
    STATUS      current
    DESCRIPTION
	"The seventeenth output status of slave 2"
    ::= { slaveTwoOutputStatus 17}
slaveTwoOutputStatusEighteen OBJECT-TYPE
    SYNTAX      DisplayString
    MAX-ACCESS  read-write
    STATUS      current
    DESCRIPTION
	"The eighteenth output status of slave 2"
    ::= { slaveTwoOutputStatus 18}
slaveTwoOutputStatusNineteen OBJECT-TYPE
    SYNTAX      DisplayString
    MAX-ACCESS  read-write
    STATUS      current
    DESCRIPTION
	"The nineteenth output status of slave 2"
    ::= { slaveTwoOutputStatus 19}
slaveTwoOutputStatusTwenty OBJECT-TYPE
    SYNTAX      DisplayString
    MAX-ACCESS  read-write
    STATUS      current
    DESCRIPTION
	"The twentieth output status of slave 2"
    ::= { slaveTwoOutputStatus 20}
slaveTwoOutputStatusTwentyOne OBJECT-TYPE
    SYNTAX      DisplayString
    MAX-ACCESS  read-write
    STATUS      current
    DESCRIPTION
	"The twenty-first output status of slave 2"
    ::= { slaveTwoOutputStatus 21}
slaveTwoOutputStatusTwentyTwo OBJECT-TYPE
    SYNTAX      DisplayString
    MAX-ACCESS  read-write
    STATUS      current
    DESCRIPTION
	"The twenty-second output status of slave 2"
    ::= { slaveTwoOutputStatus 22}
slaveTwoOutputStatusTwentyThree OBJECT-TYPE
    SYNTAX      DisplayString
    MAX-ACCESS  read-write
    STATUS      current
    DESCRIPTION
	"The twenty-third output status of slave 2"
    ::= { slaveTwoOutputStatus 23}
slaveTwoOutputStatusTwentyFour OBJECT-TYPE
    SYNTAX      DisplayString
    MAX-ACCESS  read-write
    STATUS      current
    DESCRIPTION
	"The twenty-fourth output status of slave 2"
    ::= { slaveTwoOutputStatus 24}

slaveTwoOutputCurrent   OBJECT IDENTIFIER ::= { rpduSlaveTwo 10}
slaveTwoOutputCurrentOne OBJECT-TYPE
    SYNTAX      DisplayString
    MAX-ACCESS  read-only
    STATUS      current
    DESCRIPTION
	"The current value of the first output of the slave 2"
    ::= { slaveTwoOutputCurrent 1}
slaveTwoOutputCurrentTwo OBJECT-TYPE
    SYNTAX      DisplayString
    MAX-ACCESS  read-only
    STATUS      current
    DESCRIPTION
	"The current value of the second output of the slave 2"
    ::= { slaveTwoOutputCurrent 2}
slaveTwoOutputCurrentThree OBJECT-TYPE
    SYNTAX      DisplayString
    MAX-ACCESS  read-only
    STATUS      current
    DESCRIPTION
	"The current value of the third output of the slave 2"
    ::= { slaveTwoOutputCurrent 3}
slaveTwoOutputCurrentFour OBJECT-TYPE
    SYNTAX      DisplayString
    MAX-ACCESS  read-only
    STATUS      current
    DESCRIPTION
	"The current value of the fourth output of the slave 2"
    ::= { slaveTwoOutputCurrent 4}
slaveTwoOutputCurrentFive OBJECT-TYPE
    SYNTAX      DisplayString
    MAX-ACCESS  read-only
    STATUS      current
    DESCRIPTION
	"The current value of the fifth output of the slave 2"
    ::= { slaveTwoOutputCurrent 5}
slaveTwoOutputCurrentSix OBJECT-TYPE
    SYNTAX      DisplayString
    MAX-ACCESS  read-only
    STATUS      current
    DESCRIPTION
	"The current value of the sixth output of the slave 2"
    ::= { slaveTwoOutputCurrent 6}
slaveTwoOutputCurrentSeven OBJECT-TYPE
    SYNTAX      DisplayString
    MAX-ACCESS  read-only
    STATUS      current
    DESCRIPTION
	"The current value of the seventh output of the slave 2"
    ::= { slaveTwoOutputCurrent 7}
slaveTwoOutputCurrentEight OBJECT-TYPE
    SYNTAX      DisplayString
    MAX-ACCESS  read-only
    STATUS      current
    DESCRIPTION
	"The current value of the eighth output of the slave 2"
    ::= { slaveTwoOutputCurrent 8}
slaveTwoOutputCurrentNine OBJECT-TYPE
    SYNTAX      DisplayString
    MAX-ACCESS  read-only
    STATUS      current
    DESCRIPTION
	"The current value of the nineth output of the slave 2"
    ::= { slaveTwoOutputCurrent 9}
slaveTwoOutputCurrentTen OBJECT-TYPE
    SYNTAX      DisplayString
    MAX-ACCESS  read-only
    STATUS      current
    DESCRIPTION
	"The current value of the tenth output of the slave 2"
    ::= { slaveTwoOutputCurrent 10}
slaveTwoOutputCurrentEleven OBJECT-TYPE
    SYNTAX      DisplayString
    MAX-ACCESS  read-only
    STATUS      current
    DESCRIPTION
	"The current value of the eleventh output of the slave 2"
    ::= { slaveTwoOutputCurrent 11}
slaveTwoOutputCurrentTwelve OBJECT-TYPE
    SYNTAX      DisplayString
    MAX-ACCESS  read-only
    STATUS      current
    DESCRIPTION
	"The current value of the twelfth output of the slave 2"
    ::= { slaveTwoOutputCurrent 12}
slaveTwoOutputCurrentThirteen OBJECT-TYPE
    SYNTAX      DisplayString
    MAX-ACCESS  read-only
    STATUS      current
    DESCRIPTION
	"The current value of the thirteenth output of the slave 2"
    ::= { slaveTwoOutputCurrent 13}
slaveTwoOutputCurrentFourteen OBJECT-TYPE
    SYNTAX      DisplayString
    MAX-ACCESS  read-only
    STATUS      current
    DESCRIPTION
	"The current value of the fourteenth output of the slave 2"
    ::= { slaveTwoOutputCurrent 14}
slaveTwoOutputCurrentFifteen OBJECT-TYPE
    SYNTAX      DisplayString
    MAX-ACCESS  read-only
    STATUS      current
    DESCRIPTION
	"The current value of the fifteenth output of the slave 2"
    ::= { slaveTwoOutputCurrent 15}
slaveTwoOutputCurrentSixteen OBJECT-TYPE
    SYNTAX      DisplayString
    MAX-ACCESS  read-only
    STATUS      current
    DESCRIPTION
	"The current value of the sixteenth output of the slave 2"
    ::= { slaveTwoOutputCurrent 16}
slaveTwoOutputCurrentSeventeen OBJECT-TYPE
    SYNTAX      DisplayString
    MAX-ACCESS  read-only
    STATUS      current
    DESCRIPTION
	"The current value of the seventeenth output of the slave 2"
    ::= { slaveTwoOutputCurrent 17}
slaveTwoOutputCurrentEighteen OBJECT-TYPE
    SYNTAX      DisplayString
    MAX-ACCESS  read-only
    STATUS      current
    DESCRIPTION
	"The current value of the eighteenth output of the slave 2"
    ::= { slaveTwoOutputCurrent 18}
slaveTwoOutputCurrentNineteen OBJECT-TYPE
    SYNTAX      DisplayString
    MAX-ACCESS  read-only
    STATUS      current
    DESCRIPTION
	"The current value of the nineteenth output of the slave 2"
    ::= { slaveTwoOutputCurrent 19}
slaveTwoOutputCurrentTwenty OBJECT-TYPE
    SYNTAX      DisplayString
    MAX-ACCESS  read-only
    STATUS      current
    DESCRIPTION
	"The current value of the twentieth output of the slave 2"
    ::= { slaveTwoOutputCurrent 20}
slaveTwoOutputCurrentTwentyOne OBJECT-TYPE
    SYNTAX      DisplayString
    MAX-ACCESS  read-only
    STATUS      current
    DESCRIPTION
	"The current value of the twenty-first output of the slave 2"
    ::= { slaveTwoOutputCurrent 21}
slaveTwoOutputCurrentTwentyTwo OBJECT-TYPE
    SYNTAX      DisplayString
    MAX-ACCESS  read-only
    STATUS      current
    DESCRIPTION
	"The current value of the twenty-second output of the slave 2"
    ::= { slaveTwoOutputCurrent 22}
slaveTwoOutputCurrentTwentyThree OBJECT-TYPE
    SYNTAX      DisplayString
    MAX-ACCESS  read-only
    STATUS      current
    DESCRIPTION
	"The current value of the twenty-third output of the slave 2"
    ::= { slaveTwoOutputCurrent 23}
slaveTwoOutputCurrentTwentyFour OBJECT-TYPE
    SYNTAX      DisplayString
    MAX-ACCESS  read-only
    STATUS      current
    DESCRIPTION
	"The current value of the twenty-fourth output of the slave 2"
    ::= { slaveTwoOutputCurrent 24}

slaveTwoOutputCurrentMin   OBJECT IDENTIFIER ::= { rpduSlaveTwo 11}
slaveTwoOutputCurrentMinOne OBJECT-TYPE
    SYNTAX      DisplayString
    MAX-ACCESS  read-only
    STATUS      current
    DESCRIPTION
	"The Min. current value of the first output of the slave 2"
    ::= { slaveTwoOutputCurrentMin 1}
slaveTwoOutputCurrentMinTwo OBJECT-TYPE
    SYNTAX      DisplayString
    MAX-ACCESS  read-only
    STATUS      current
    DESCRIPTION
	"The Min. current value of the second output of the slave 2"
    ::= { slaveTwoOutputCurrentMin 2}
slaveTwoOutputCurrentMinThree OBJECT-TYPE
    SYNTAX      DisplayString
    MAX-ACCESS  read-only
    STATUS      current
    DESCRIPTION
	"The Min. current value of the third output of the slave 2"
    ::= { slaveTwoOutputCurrentMin 3}
slaveTwoOutputCurrentMinFour OBJECT-TYPE
    SYNTAX      DisplayString
    MAX-ACCESS  read-only
    STATUS      current
    DESCRIPTION
	"The Min. current value of the fourth output of the slave 2"
    ::= { slaveTwoOutputCurrentMin 4}
slaveTwoOutputCurrentMinFive OBJECT-TYPE
    SYNTAX      DisplayString
    MAX-ACCESS  read-only
    STATUS      current
    DESCRIPTION
	"The Min. current value of the fifth output of the slave 2"
    ::= { slaveTwoOutputCurrentMin 5}
slaveTwoOutputCurrentMinSix OBJECT-TYPE
    SYNTAX      DisplayString
    MAX-ACCESS  read-only
    STATUS      current
    DESCRIPTION
	"The Min. current value of the sixth output of the slave 2"
    ::= { slaveTwoOutputCurrentMin 6}
slaveTwoOutputCurrentMinSeven OBJECT-TYPE
    SYNTAX      DisplayString
    MAX-ACCESS  read-only
    STATUS      current
    DESCRIPTION
	"The Min. current value of the seventh output of the slave 2"
    ::= { slaveTwoOutputCurrentMin 7}
slaveTwoOutputCurrentMinEight OBJECT-TYPE
    SYNTAX      DisplayString
    MAX-ACCESS  read-only
    STATUS      current
    DESCRIPTION
	"The Min. current value of the eighth output of the slave 2"
    ::= { slaveTwoOutputCurrentMin 8}
slaveTwoOutputCurrentMinNine OBJECT-TYPE
    SYNTAX      DisplayString
    MAX-ACCESS  read-only
    STATUS      current
    DESCRIPTION
	"The Min. current value of the nineth output of the slave 2"
    ::= { slaveTwoOutputCurrentMin 9}
slaveTwoOutputCurrentMinTen OBJECT-TYPE
    SYNTAX      DisplayString
    MAX-ACCESS  read-only
    STATUS      current
    DESCRIPTION
	"The Min. current value of the tenth output of the slave 2"
    ::= { slaveTwoOutputCurrentMin 10}
slaveTwoOutputCurrentMinEleven OBJECT-TYPE
    SYNTAX      DisplayString
    MAX-ACCESS  read-only
    STATUS      current
    DESCRIPTION
	"The Min. current value of the eleventh output of the slave 2"
    ::= { slaveTwoOutputCurrentMin 11}
slaveTwoOutputCurrentMinTwleve OBJECT-TYPE
    SYNTAX      DisplayString
    MAX-ACCESS  read-only
    STATUS      current
    DESCRIPTION
	"The Min. current value of the twelfth output of the slave 2"
    ::= { slaveTwoOutputCurrentMin 12}
slaveTwoOutputCurrentMinThirteen OBJECT-TYPE
    SYNTAX      DisplayString
    MAX-ACCESS  read-only
    STATUS      current
    DESCRIPTION
	"The Min. current value of the thirteenth output of the slave 2"
    ::= { slaveTwoOutputCurrentMin 13}
slaveTwoOutputCurrentMinFourteen OBJECT-TYPE
    SYNTAX      DisplayString
    MAX-ACCESS  read-only
    STATUS      current
    DESCRIPTION
	"The Min. current value of the fourteenth output of the slave 2"
    ::= { slaveTwoOutputCurrentMin 14}
slaveTwoOutputCurrentMinFifteen OBJECT-TYPE
    SYNTAX      DisplayString
    MAX-ACCESS  read-only
    STATUS      current
    DESCRIPTION
	"The Min. current value of the fifteenth output of the slave 2"
    ::= { slaveTwoOutputCurrentMin 15}
slaveTwoOutputCurrentMinSixteen OBJECT-TYPE
    SYNTAX      DisplayString
    MAX-ACCESS  read-only
    STATUS      current
    DESCRIPTION
	"The Min. current value of the sixteenth output of the slave 2"
    ::= { slaveTwoOutputCurrentMin 16}
slaveTwoOutputCurrentMinSeventeen OBJECT-TYPE
    SYNTAX      DisplayString
    MAX-ACCESS  read-only
    STATUS      current
    DESCRIPTION
	"The Min. current value of the seventeenth output of the slave 2"
    ::= { slaveTwoOutputCurrentMin 17}
slaveTwoOutputCurrentMinEighteen OBJECT-TYPE
    SYNTAX      DisplayString
    MAX-ACCESS  read-only
    STATUS      current
    DESCRIPTION
	"The Min. current value of the eighteenth output of the slave 2"
    ::= { slaveTwoOutputCurrentMin 18}
slaveTwoOutputCurrentMinNineteen OBJECT-TYPE
    SYNTAX      DisplayString
    MAX-ACCESS  read-only
    STATUS      current
    DESCRIPTION
	"The Min. current value of the nineteenth output of the slave 2"
    ::= { slaveTwoOutputCurrentMin 19}
slaveTwoOutputCurrentMinTwenty OBJECT-TYPE
    SYNTAX      DisplayString
    MAX-ACCESS  read-only
    STATUS      current
    DESCRIPTION
	"The Min. current value of the twentieth output of the slave 2"
    ::= { slaveTwoOutputCurrentMin 20}
slaveTwoOutputCurrentMinTwentyOne OBJECT-TYPE
    SYNTAX      DisplayString
    MAX-ACCESS  read-only
    STATUS      current
    DESCRIPTION
	"The Min. current value of the twentyth-first output of the slave 2"
    ::= { slaveTwoOutputCurrentMin 21}
slaveTwoOutputCurrentMinTwentyTwo OBJECT-TYPE
    SYNTAX      DisplayString
    MAX-ACCESS  read-only
    STATUS      current
    DESCRIPTION
	"The Min. current value of the twentyth-second output of the slave 2"
    ::= { slaveTwoOutputCurrentMin 22}
slaveTwoOutputCurrentMinTwentyThree OBJECT-TYPE
    SYNTAX      DisplayString
    MAX-ACCESS  read-only
    STATUS      current
    DESCRIPTION
	"The Min. current value of the twentyth-third output of the slave 2"
    ::= { slaveTwoOutputCurrentMin 23}
slaveTwoOutputCurrentMinTwentyFour OBJECT-TYPE
    SYNTAX      DisplayString
    MAX-ACCESS  read-only
    STATUS      current
    DESCRIPTION
	"The Min. current value of the twentyth-fourth output of the slave 2"
    ::= { slaveTwoOutputCurrentMin 24}




slaveTwoOutputCurrentMax   OBJECT IDENTIFIER ::= { rpduSlaveTwo 12}
slaveTwoOutputCurrentMaxOne OBJECT-TYPE
    SYNTAX      DisplayString
    MAX-ACCESS  read-only
    STATUS      current
    DESCRIPTION
	"The Max. current value of the first output of the slave 2"
    ::= { slaveTwoOutputCurrentMax 1}
slaveTwoOutputCurrentMaxTwo OBJECT-TYPE
    SYNTAX      DisplayString
    MAX-ACCESS  read-only
    STATUS      current
    DESCRIPTION
	"The Max. current value of the second output of the slave 2"
    ::= { slaveTwoOutputCurrentMax 2}
slaveTwoOutputCurrentMaxThree OBJECT-TYPE
    SYNTAX      DisplayString
    MAX-ACCESS  read-only
    STATUS      current
    DESCRIPTION
	"The Max. current value of the third output of the slave 2"
    ::= { slaveTwoOutputCurrentMax 3}
slaveTwoOutputCurrentMaxFour OBJECT-TYPE
    SYNTAX      DisplayString
    MAX-ACCESS  read-only
    STATUS      current
    DESCRIPTION
	"The Max. current value of the fourth output of the slave 2"
    ::= { slaveTwoOutputCurrentMax 4}
slaveTwoOutputCurrentMaxFive OBJECT-TYPE
    SYNTAX      DisplayString
    MAX-ACCESS  read-only
    STATUS      current
    DESCRIPTION
	"The Max. current value of the fifth output of the slave 2"
    ::= { slaveTwoOutputCurrentMax 5}
slaveTwoOutputCurrentMaxSix OBJECT-TYPE
    SYNTAX      DisplayString
    MAX-ACCESS  read-only
    STATUS      current
    DESCRIPTION
	"The Max. current value of the sixth output of the slave 2"
    ::= { slaveTwoOutputCurrentMax 6}
slaveTwoOutputCurrentMaxSeven OBJECT-TYPE
    SYNTAX      DisplayString
    MAX-ACCESS  read-only
    STATUS      current
    DESCRIPTION
	"The Max. current value of the seventh output of the slave 2"
    ::= { slaveTwoOutputCurrentMax 7}
slaveTwoOutputCurrentMaxEight OBJECT-TYPE
    SYNTAX      DisplayString
    MAX-ACCESS  read-only
    STATUS      current
    DESCRIPTION
	"The Max. current value of the eighth output of the slave 2"
    ::= { slaveTwoOutputCurrentMax 8}
slaveTwoOutputCurrentMaxNine OBJECT-TYPE
    SYNTAX      DisplayString
    MAX-ACCESS  read-only
    STATUS      current
    DESCRIPTION
	"The Max. current value of the nineth output of the slave 2"
    ::= { slaveTwoOutputCurrentMax 9}
slaveTwoOutputCurrentMaxTen OBJECT-TYPE
    SYNTAX      DisplayString
    MAX-ACCESS  read-only
    STATUS      current
    DESCRIPTION
	"The Max. current value of the tenth output of the slave 2"
    ::= { slaveTwoOutputCurrentMax 10}
slaveTwoOutputCurrentMaxEleven OBJECT-TYPE
    SYNTAX      DisplayString
    MAX-ACCESS  read-only
    STATUS      current
    DESCRIPTION
	"The Max. current value of the eleventh output of the slave 2"
    ::= { slaveTwoOutputCurrentMax 11}
slaveTwoOutputCurrentMaxTwleve OBJECT-TYPE
    SYNTAX      DisplayString
    MAX-ACCESS  read-only
    STATUS      current
    DESCRIPTION
	"The Max. current value of the twelfth output of the slave 2"
    ::= { slaveTwoOutputCurrentMax 12}
slaveTwoOutputCurrentMaxThirteen OBJECT-TYPE
    SYNTAX      DisplayString
    MAX-ACCESS  read-only
    STATUS      current
    DESCRIPTION
	"The Max. current value of the thirteenth output of the slave 2"
    ::= { slaveTwoOutputCurrentMax 13}
slaveTwoOutputCurrentMaxFourteen OBJECT-TYPE
    SYNTAX      DisplayString
    MAX-ACCESS  read-only
    STATUS      current
    DESCRIPTION
	"The Max. current value of the fourteenth output of the slave 2"
    ::= { slaveTwoOutputCurrentMax 14}
slaveTwoOutputCurrentMaxFifteen OBJECT-TYPE
    SYNTAX      DisplayString
    MAX-ACCESS  read-only
    STATUS      current
    DESCRIPTION
	"The Max. current value of the fifteenth output of the slave 2"
    ::= { slaveTwoOutputCurrentMax 15}
slaveTwoOutputCurrentMaxSixteen OBJECT-TYPE
    SYNTAX      DisplayString
    MAX-ACCESS  read-only
    STATUS      current
    DESCRIPTION
	"The Max. current value of the sixteenth output of the slave 2"
    ::= { slaveTwoOutputCurrentMax 16}
slaveTwoOutputCurrentMaxSeventeen OBJECT-TYPE
    SYNTAX      DisplayString
    MAX-ACCESS  read-only
    STATUS      current
    DESCRIPTION
	"The Max. current value of the seventeenth output of the slave 2"
    ::= { slaveTwoOutputCurrentMax 17}
slaveTwoOutputCurrentMaxEighteen OBJECT-TYPE
    SYNTAX      DisplayString
    MAX-ACCESS  read-only
    STATUS      current
    DESCRIPTION
	"The Max. current value of the eighteenth output of the slave 2"
    ::= { slaveTwoOutputCurrentMax 18}
slaveTwoOutputCurrentMaxNineteen OBJECT-TYPE
    SYNTAX      DisplayString
    MAX-ACCESS  read-only
    STATUS      current
    DESCRIPTION
	"The Max. current value of the nineteenth output of the slave 2"
    ::= { slaveTwoOutputCurrentMax 19}
slaveTwoOutputCurrentMaxTwenty OBJECT-TYPE
    SYNTAX      DisplayString
    MAX-ACCESS  read-only
    STATUS      current
    DESCRIPTION
	"The Max. current value of the twentieth output of the slave 2"
    ::= { slaveTwoOutputCurrentMax 20}
slaveTwoOutputCurrentMaxTwentyOne OBJECT-TYPE
    SYNTAX      DisplayString
    MAX-ACCESS  read-only
    STATUS      current
    DESCRIPTION
	"The Max. current value of the twenty-first output of the slave 2"
    ::= { slaveTwoOutputCurrentMax 21}
slaveTwoOutputCurrentMaxTwentyTwo OBJECT-TYPE
    SYNTAX      DisplayString
    MAX-ACCESS  read-only
    STATUS      current
    DESCRIPTION
	"The Max. current value of the twenty-second output of the slave 2"
    ::= { slaveTwoOutputCurrentMax 22}
slaveTwoOutputCurrentMaxTwentyThree OBJECT-TYPE
    SYNTAX      DisplayString
    MAX-ACCESS  read-only
    STATUS      current
    DESCRIPTION
	"The Max. current value of the twenty-third output of the slave 2"
    ::= { slaveTwoOutputCurrentMax 23}
slaveTwoOutputCurrentMaxTwentyFour OBJECT-TYPE
    SYNTAX      DisplayString
    MAX-ACCESS  read-only
    STATUS      current
    DESCRIPTION
	"The Max. current value of the twenty-fourth output of the slave 2"
    ::= { slaveTwoOutputCurrentMax 24}


slaveTwoOutputCurrentEnergy  OBJECT IDENTIFIER ::= { rpduSlaveTwo 13}
slaveTwoOutputCurrentEnergyOne OBJECT-TYPE
    SYNTAX	DisplayString
    MAX-ACCESS	read-only
    STATUS	current
    DESCRIPTION
	"The energy value of the first output of the slave 2"
    ::={slaveTwoOutputCurrentEnergy 1}
slaveTwoOutputCurrentEnergyTwo OBJECT-TYPE
    SYNTAX	DisplayString
    MAX-ACCESS	read-only
    STATUS	current
    DESCRIPTION
	"The energy value of the second output of the slave 2"
    ::={slaveTwoOutputCurrentEnergy 2}
slaveTwoOutputCurrentEnergyThree OBJECT-TYPE
    SYNTAX	DisplayString
    MAX-ACCESS	read-only
    STATUS	current
    DESCRIPTION
	"The energy value of the third output of the slave 2"
    ::={slaveTwoOutputCurrentEnergy 3}
slaveTwoOutputCurrentEnergyFour OBJECT-TYPE
    SYNTAX	DisplayString
    MAX-ACCESS	read-only
    STATUS	current
    DESCRIPTION
	"The energy value of the fourth output of the slave 2"
    ::={slaveTwoOutputCurrentEnergy 4}
slaveTwoOutputCurrentEnergyFive OBJECT-TYPE
    SYNTAX	DisplayString
    MAX-ACCESS	read-only
    STATUS	current
    DESCRIPTION
	"The energy value of the fifth output of the slave 2"
    ::={slaveTwoOutputCurrentEnergy 5}
slaveTwoOutputCurrentEnergySix OBJECT-TYPE
    SYNTAX	DisplayString
    MAX-ACCESS	read-only
    STATUS	current
    DESCRIPTION
	"The energy value of the sixth output of the slave 2"
    ::={slaveTwoOutputCurrentEnergy 6}
slaveTwoOutputCurrentEnergySeven OBJECT-TYPE
    SYNTAX	DisplayString
    MAX-ACCESS	read-only
    STATUS	current
    DESCRIPTION
	"The energy value of the seventh output of the slave 2"
    ::={slaveTwoOutputCurrentEnergy 7}
slaveTwoOutputCurrentEnergyEight OBJECT-TYPE
    SYNTAX	DisplayString
    MAX-ACCESS	read-only
    STATUS	current
    DESCRIPTION
	"The energy value of the eighth output of the slave 2"
    ::={slaveTwoOutputCurrentEnergy 8}
slaveTwoOutputCurrentEnergyNine OBJECT-TYPE
    SYNTAX	DisplayString
    MAX-ACCESS	read-only
    STATUS	current
    DESCRIPTION
	"The energy value of the nineth output of the slave 2"
    ::={slaveTwoOutputCurrentEnergy 9}
slaveTwoOutputCurrentEnergyTen OBJECT-TYPE
    SYNTAX	DisplayString
    MAX-ACCESS	read-only
    STATUS	current
    DESCRIPTION
	"The energy value of the tenth output of the slave 2"
    ::={slaveTwoOutputCurrentEnergy 10}
slaveTwoOutputCurrentEnergyEleven OBJECT-TYPE
    SYNTAX	DisplayString
    MAX-ACCESS	read-only
    STATUS	current
    DESCRIPTION
	"The energy value of the eleventh output of the slave 2"
    ::={slaveTwoOutputCurrentEnergy 11}
slaveTwoOutputCurrentEnergyTwelve OBJECT-TYPE
    SYNTAX	DisplayString
    MAX-ACCESS	read-only
    STATUS	current
    DESCRIPTION
	"The energy value of the twelfth output of the slave 2"
    ::={slaveTwoOutputCurrentEnergy 12}
slaveTwoOutputCurrentEnergyThirteen OBJECT-TYPE
    SYNTAX	DisplayString
    MAX-ACCESS	read-only
    STATUS	current
    DESCRIPTION
	"The energy value of the thirteenth output of the slave 2"
    ::={slaveTwoOutputCurrentEnergy 13}
slaveTwoOutputCurrentEnergyFourteen OBJECT-TYPE
    SYNTAX	DisplayString
    MAX-ACCESS	read-only
    STATUS	current
    DESCRIPTION
	"The energy value of the fourteenth output of the slave 2"
    ::={slaveTwoOutputCurrentEnergy 14}
slaveTwoOutputCurrentEnergyFifteen OBJECT-TYPE
    SYNTAX	DisplayString
    MAX-ACCESS	read-only
    STATUS	current
    DESCRIPTION
	"The energy value of the fifteenth output of the slave 2"
    ::={slaveTwoOutputCurrentEnergy 15}
slaveTwoOutputCurrentEnergySixteen OBJECT-TYPE
    SYNTAX	DisplayString
    MAX-ACCESS	read-only
    STATUS	current
    DESCRIPTION
	"The energy value of the sixteenth output of the slave 2"
    ::={slaveTwoOutputCurrentEnergy 16}
slaveTwoOutputCurrentEnergySeventeen OBJECT-TYPE
    SYNTAX	DisplayString
    MAX-ACCESS	read-only
    STATUS	current
    DESCRIPTION
	"The energy value of the seventeenth output of the slave 2"
    ::={slaveTwoOutputCurrentEnergy 17}
slaveTwoOutputCurrentEnergyEighteen OBJECT-TYPE
    SYNTAX	DisplayString
    MAX-ACCESS	read-only
    STATUS	current
    DESCRIPTION
	"The energy value of the eighteenth output of the slave 2"
    ::={slaveTwoOutputCurrentEnergy 18}
slaveTwoOutputCurrentEnergyNineteen OBJECT-TYPE
    SYNTAX	DisplayString
    MAX-ACCESS	read-only
    STATUS	current
    DESCRIPTION
	"The energy value of the nineteenth output of the slave 2"
    ::={slaveTwoOutputCurrentEnergy 19}
slaveTwoOutputCurrentEnergyTwenty OBJECT-TYPE
    SYNTAX	DisplayString
    MAX-ACCESS	read-only
    STATUS	current
    DESCRIPTION
	"The energy value of the twentieth output of the slave 2"
    ::={slaveTwoOutputCurrentEnergy 20}
slaveTwoOutputCurrentEnergyTwentyOne OBJECT-TYPE
    SYNTAX	DisplayString
    MAX-ACCESS	read-only
    STATUS	current
    DESCRIPTION
	"The energy value of the twenty-first output of the slave 2"
    ::={slaveTwoOutputCurrentEnergy 21}
slaveTwoOutputCurrentEnergyTwentyTwo OBJECT-TYPE
    SYNTAX	DisplayString
    MAX-ACCESS	read-only
    STATUS	current
    DESCRIPTION
	"The energy value of the twenty-second output of the slave 2"
    ::={slaveTwoOutputCurrentEnergy 22}
slaveTwoOutputCurrentEnergyTwentyThree OBJECT-TYPE
    SYNTAX	DisplayString
    MAX-ACCESS	read-only
    STATUS	current
    DESCRIPTION
	"The energy value of the twenty-third output of the slave 2"
    ::={slaveTwoOutputCurrentEnergy 23}
slaveTwoOutputCurrentEnergyTwentyFour OBJECT-TYPE
    SYNTAX	DisplayString
    MAX-ACCESS	read-only
    STATUS	current
    DESCRIPTION
	"The energy value of the twenty-fourth output of the slave 2"
    ::={slaveTwoOutputCurrentEnergy 24}

-------------------------------Slave3---------------------------------------------  
rpduDeviceFour OBJECT IDENTIFIER ::= { rpdu 4}
rpduSlaveThree OBJECT IDENTIFIER ::= { rpduDeviceFour 1}

slaveThreeName OBJECT-TYPE
    SYNTAX      DisplayString
    MAX-ACCESS  read-write
    STATUS      current
    DESCRIPTION
	"This is the fourth device."
    ::= { rpduSlaveThree 1}
    
slaveThreeType OBJECT-TYPE
    SYNTAX      DisplayString
    MAX-ACCESS  read-only
    STATUS      current
    DESCRIPTION
	"This is device type "
    ::= { rpduSlaveThree 2}
    
slaveThreeOutputNumber OBJECT-TYPE 
    SYNTAX      Integer32
    MAX-ACCESS  read-only
    STATUS      current
    DESCRIPTION
	"This is the output quantity"
::= { rpduSlaveThree 7}
    
slaveThreeLineOne OBJECT IDENTIFIER ::= { rpduSlaveThree 3}
slaveThreeLineOnePower OBJECT-TYPE
    SYNTAX      DisplayString
    MAX-ACCESS  read-only
    STATUS      current
    DESCRIPTION
	"The power of phase one"
    ::= { slaveThreeLineOne 1}
slaveThreeLineOnePF OBJECT-TYPE
    SYNTAX      DisplayString
    MAX-ACCESS  read-only
    STATUS      current
    DESCRIPTION
	"The power factor of phase one"
    ::= { slaveThreeLineOne 2}
    
slaveThreeLineOneEnergy OBJECT-TYPE
    SYNTAX      DisplayString
    MAX-ACCESS  read-only
    STATUS      current
    DESCRIPTION
	"The energy of phase one"
    ::= { slaveThreeLineOne 3}
slaveThreeLineOneCurrent OBJECT-TYPE
    SYNTAX      DisplayString
    MAX-ACCESS  read-only
    STATUS      current
    DESCRIPTION
	"The current of phase one"
    ::= { slaveThreeLineOne 4}
slaveThreeLineOneVoltage OBJECT-TYPE
    SYNTAX      Integer32
    MAX-ACCESS  read-only
    STATUS      current
    DESCRIPTION
	"The voltage of phase one"
    ::= { slaveThreeLineOne 5}
slaveThreeLineOneCurrentMin OBJECT-TYPE
    SYNTAX      DisplayString
    MAX-ACCESS  read-only
    STATUS      current
    DESCRIPTION
	"The Min. current value of phase one"
	::= { slaveThreeLineOne 6}
slaveThreeLineOneCurrentMax OBJECT-TYPE
    SYNTAX      DisplayString
    MAX-ACCESS  read-only
    STATUS      current
    DESCRIPTION
	"The Max. current value of phase one"
    ::= { slaveThreeLineOne 7}
    
slaveThreeLineOneVoltageMin OBJECT-TYPE
    SYNTAX      Integer32
    MAX-ACCESS  read-only
    STATUS      current
    DESCRIPTION
	"The Min. voltage value of phase one"
    ::= { slaveThreeLineOne 8}
    
slaveThreeLineOneVoltageMax OBJECT-TYPE
    SYNTAX      Integer32
    MAX-ACCESS  read-only
    STATUS      current
    DESCRIPTION
	"The Max. voltage value of phase one"
    ::= { slaveThreeLineOne 9}


slaveThreeLineTwo OBJECT IDENTIFIER ::= { rpduSlaveThree 4}
slaveThreeLineTwoPower OBJECT-TYPE
    SYNTAX      DisplayString
    MAX-ACCESS  read-only
    STATUS      current
    DESCRIPTION
	"The power of phase two"
    ::= { slaveThreeLineTwo 1}

slaveThreeLineTwoPF OBJECT-TYPE
    SYNTAX      DisplayString
    MAX-ACCESS  read-only
    STATUS      current
    DESCRIPTION
	"The power factor of phase two"   
    ::= { slaveThreeLineTwo 2}
    
slaveThreeLineTwoEnergy OBJECT-TYPE
    SYNTAX      DisplayString
    MAX-ACCESS  read-only
    STATUS      current
    DESCRIPTION
	"The energy of phase two"
    ::= { slaveThreeLineTwo 3}
slaveThreeLineTwoCurrent OBJECT-TYPE           
    SYNTAX      DisplayString 
    MAX-ACCESS  read-only
    STATUS      current
    DESCRIPTION
	"The current of phase two"
    ::= { slaveThreeLineTwo 4}
slaveThreeLineTwoVoltage OBJECT-TYPE
    SYNTAX      Integer32
    MAX-ACCESS  read-only
    STATUS      current
    DESCRIPTION
	"The voltage of phase two"
    ::= { slaveThreeLineTwo 5}
slaveThreeLineTwoCurrentMin OBJECT-TYPE
    SYNTAX      DisplayString
    MAX-ACCESS  read-only
    STATUS      current
    DESCRIPTION
	"The Min. current value of phase two"
    ::= { slaveThreeLineTwo 6}
slaveThreeLineTwoCurrentMax OBJECT-TYPE
    SYNTAX      DisplayString
    MAX-ACCESS  read-only
    STATUS      current
    DESCRIPTION
	"The Max. current value of phase two"
    ::= { slaveThreeLineTwo 7}
    
slaveThreeLineTwoVoltageMin OBJECT-TYPE
    SYNTAX      Integer32
    MAX-ACCESS  read-only
    STATUS      current
    DESCRIPTION
	"The Min. voltage value of phase two"
    ::= { slaveThreeLineTwo 8}
    
slaveThreeLineTwoVoltageMax OBJECT-TYPE
    SYNTAX      Integer32
    MAX-ACCESS  read-only
    STATUS      current
    DESCRIPTION
	"The Max. voltage value of phase two"
    ::= { slaveThreeLineTwo 9}



slaveThreeLineThree OBJECT IDENTIFIER ::= { rpduSlaveThree 5}
slaveThreeLineThreePower OBJECT-TYPE
    SYNTAX      DisplayString
    MAX-ACCESS  read-only
    STATUS      current
    DESCRIPTION
	"The power of phase three"
    ::= { slaveThreeLineThree 1}

slaveThreeLineThreePF OBJECT-TYPE
    SYNTAX      DisplayString
    MAX-ACCESS  read-only
    STATUS      current
    DESCRIPTION
	"The power factor of phase three"     
    ::= { slaveThreeLineThree 2}
    
slaveThreeLineThreeEnergy OBJECT-TYPE
    SYNTAX      DisplayString
    MAX-ACCESS  read-only
    STATUS      current
    DESCRIPTION
	"The energy of phase three"
    ::= { slaveThreeLineThree 3}
slaveThreeLineThreeCurrent OBJECT-TYPE
    SYNTAX      DisplayString
    MAX-ACCESS  read-only
    STATUS      current
    DESCRIPTION
	"The current of phase three"
    ::= { slaveThreeLineThree 4}
slaveThreeLineThreeVoltage OBJECT-TYPE
    SYNTAX      Integer32
    MAX-ACCESS  read-only
    STATUS      current
    DESCRIPTION
	"The voltage of phase three"
    ::= { slaveThreeLineThree 5}
slaveThreeLineThreeCurrentMin OBJECT-TYPE
    SYNTAX      DisplayString
    MAX-ACCESS  read-only
    STATUS      current
    DESCRIPTION
	"The Min. current value of phase three"
    ::= { slaveThreeLineThree 6}
slaveThreeLineThreeCurrentMax OBJECT-TYPE
    SYNTAX      DisplayString
    MAX-ACCESS  read-only
    STATUS      current
    DESCRIPTION
	"The Max. current value of phase three"
    ::= { slaveThreeLineThree 7}
    
slaveThreeLineThreeVoltageMin OBJECT-TYPE
    SYNTAX      Integer32
    MAX-ACCESS  read-only
    STATUS      current
    DESCRIPTION
	"The Min. voltage value of phase three"
    ::= { slaveThreeLineThree 8}
    
slaveThreeLineThreeVoltageMax OBJECT-TYPE
    SYNTAX      Integer32
    MAX-ACCESS  read-only
    STATUS      current
    DESCRIPTION
	"The Max. voltage value of phase three"
    ::= { slaveThreeLineThree 9}


slaveThreeSensor OBJECT IDENTIFIER ::= { rpduSlaveThree 6}
slaveThreeTempOne OBJECT-TYPE
    SYNTAX      Integer32
    MAX-ACCESS  read-only
    STATUS      current
    DESCRIPTION
	"The first temperature sensor of slave 3"
    ::= { slaveThreeSensor 1}
slaveThreeTempTwo OBJECT-TYPE
    SYNTAX      Integer32
    MAX-ACCESS  read-only
    STATUS      current
    DESCRIPTION
	"The second temperature sensor of slave 3"
    ::= { slaveThreeSensor 2}
slaveThreeTempThree OBJECT-TYPE
    SYNTAX      Integer32
    MAX-ACCESS  read-only
    STATUS      current
    DESCRIPTION
	"The third temperature sensor of slave 3"
    ::= { slaveThreeSensor 3}
slaveThreeTempFour OBJECT-TYPE
    SYNTAX      Integer32
    MAX-ACCESS  read-only
    STATUS      current
    DESCRIPTION
	"The fourth temperature sensor of slave 3"
    ::= { slaveThreeSensor 4}
slaveThreeHumOne OBJECT-TYPE
    SYNTAX      Integer32
    MAX-ACCESS  read-only
    STATUS      current
    DESCRIPTION
	"The first humidity sensor of slave 3"
    ::= { slaveThreeSensor 5}
slaveThreeHumTwo OBJECT-TYPE
    SYNTAX      Integer32
    MAX-ACCESS  read-only
    STATUS      current
    DESCRIPTION
	"The second humidity sensor of slave 3"
    ::= { slaveThreeSensor 6}
slaveThreeHumThree OBJECT-TYPE
    SYNTAX      Integer32
    MAX-ACCESS  read-only
    STATUS      current
    DESCRIPTION
	"The third humidity sensor of slave 3"
    ::= { slaveThreeSensor 7}
slaveThreeHumFour OBJECT-TYPE
    SYNTAX      Integer32
    MAX-ACCESS  read-only
    STATUS      current
    DESCRIPTION
	"The fourth humidity sensor of slave 3"
    ::= { slaveThreeSensor 8}
slaveThreeDoorOne OBJECT-TYPE
    SYNTAX      DisplayString
    MAX-ACCESS  read-only
    STATUS      current
    DESCRIPTION
	"The first door sensor of slave 3"    
    ::= { slaveThreeSensor 9}
slaveThreeDoorTwo OBJECT-TYPE
    SYNTAX      DisplayString
    MAX-ACCESS  read-only
    STATUS      current
    DESCRIPTION
	"The second door sensor of slave 3"  
    ::= { slaveThreeSensor 10}
slaveThreeSmoke OBJECT-TYPE
    SYNTAX      DisplayString
    MAX-ACCESS  read-only
    STATUS      current
    DESCRIPTION
	"The smoke sensor of slave 3"
    ::= { slaveThreeSensor 11}
slaveThreeWater OBJECT-TYPE
    SYNTAX      DisplayString
    MAX-ACCESS  read-only
    STATUS      current
    DESCRIPTION
	"The water sensor of slave 3"
    ::= { slaveThreeSensor 12}


	
        
slaveThreeOutputName OBJECT IDENTIFIER ::= { rpduSlaveThree 8}
slaveThreeOutputNameOne OBJECT-TYPE
    SYNTAX      DisplayString
    MAX-ACCESS  read-write
    STATUS      current
    DESCRIPTION
	"The first output name of slave 3"
    ::= { slaveThreeOutputName 1}

slaveThreeOutputNameTwo OBJECT-TYPE
    SYNTAX      DisplayString
    MAX-ACCESS  read-write
    STATUS      current
    DESCRIPTION
	"The second output name of slave 3"
    ::= { slaveThreeOutputName 2}
slaveThreeOutputNameThree OBJECT-TYPE
    SYNTAX      DisplayString
    MAX-ACCESS  read-write
    STATUS      current
    DESCRIPTION
	"The third output name of slave 3"
    ::= { slaveThreeOutputName 3}
slaveThreeOutputNameFour OBJECT-TYPE
    SYNTAX      DisplayString
    MAX-ACCESS  read-write
    STATUS      current
    DESCRIPTION
	"The fourth output name of slave 3"
    ::= { slaveThreeOutputName 4}
slaveThreeOutputNameFive OBJECT-TYPE
    SYNTAX      DisplayString
    MAX-ACCESS  read-write
    STATUS      current
    DESCRIPTION
	"The fifth output name of slave 3"
    ::= { slaveThreeOutputName 5}
slaveThreeOutputNameSix OBJECT-TYPE
    SYNTAX      DisplayString
    MAX-ACCESS  read-write
    STATUS      current
    DESCRIPTION
	"The sixth output name of slave 3"
    ::= { slaveThreeOutputName 6}
slaveThreeOutputNameSeven OBJECT-TYPE
    SYNTAX      DisplayString
    MAX-ACCESS  read-write
    STATUS      current
    DESCRIPTION
	"The seventh output name of slave 3"
    ::= { slaveThreeOutputName 7}
slaveThreeOutputNameEight OBJECT-TYPE
    SYNTAX      DisplayString
    MAX-ACCESS  read-write
    STATUS      current
    DESCRIPTION
	"The eighth output name of slave 3"
    ::= { slaveThreeOutputName 8}
slaveThreeOutputNameNine OBJECT-TYPE
    SYNTAX      DisplayString
    MAX-ACCESS  read-write
    STATUS      current
    DESCRIPTION
	"The nineth output name of slave 3"
    ::= { slaveThreeOutputName 9}
slaveThreeOutputNameTen OBJECT-TYPE
    SYNTAX      DisplayString
    MAX-ACCESS  read-write
    STATUS      current
    DESCRIPTION
	"The tenth output name of slave 3"
    ::= { slaveThreeOutputName 10}
slaveThreeOutputNameEleven OBJECT-TYPE
    SYNTAX      DisplayString
    MAX-ACCESS  read-write
    STATUS      current
    DESCRIPTION
	"The eleventh output name of slave 3"
    ::= { slaveThreeOutputName 11}
slaveThreeOutputNameTwelve OBJECT-TYPE
    SYNTAX      DisplayString
    MAX-ACCESS  read-write
    STATUS      current
    DESCRIPTION
	"The twelfth output name of slave 3"
    ::= { slaveThreeOutputName 12}
slaveThreeOutputNameThirteen OBJECT-TYPE
    SYNTAX      DisplayString
    MAX-ACCESS  read-write
    STATUS      current
    DESCRIPTION
	"The thirteenth output name of slave 3"
    ::= { slaveThreeOutputName 13}
slaveThreeOutputNameFourteen OBJECT-TYPE
    SYNTAX      DisplayString
    MAX-ACCESS  read-write
    STATUS      current
    DESCRIPTION
	"The fourteenth output name of slave 3"
    ::= { slaveThreeOutputName 14}
slaveThreeOutputNameFifteen OBJECT-TYPE
    SYNTAX      DisplayString
    MAX-ACCESS  read-write
    STATUS      current
    DESCRIPTION
	"The fifteenth output name of slave 3"
    ::= { slaveThreeOutputName 15}
slaveThreeOutputNameSixteen OBJECT-TYPE
    SYNTAX      DisplayString
    MAX-ACCESS  read-write
    STATUS      current
    DESCRIPTION
	"The sixteenth output name of slave 3"
    ::= { slaveThreeOutputName 16}
slaveThreeOutputNameSeventeen OBJECT-TYPE
    SYNTAX      DisplayString
    MAX-ACCESS  read-write
    STATUS      current
    DESCRIPTION
	"The seventeenth output name of slave 3"
    ::= { slaveThreeOutputName 17}
slaveThreeOutputNameEighteen OBJECT-TYPE
    SYNTAX      DisplayString
    MAX-ACCESS  read-write
    STATUS      current
    DESCRIPTION
	"The eighteenh output name of slave 3"
    ::= { slaveThreeOutputName 18}
slaveThreeOutputNameNineteen OBJECT-TYPE
    SYNTAX      DisplayString
    MAX-ACCESS  read-write
    STATUS      current
    DESCRIPTION
	"The nineteenth output name of slave 3"
    ::= { slaveThreeOutputName 19}
slaveThreeOutputNameTwenty OBJECT-TYPE
    SYNTAX      DisplayString
    MAX-ACCESS  read-write
    STATUS      current
    DESCRIPTION
	"The twentieth output name of slave 3"
    ::= { slaveThreeOutputName 20}
slaveThreeOutputNameTwentyOne OBJECT-TYPE
    SYNTAX      DisplayString
    MAX-ACCESS  read-write
    STATUS      current
    DESCRIPTION
	"The twenty-first output name of slave 3"
    ::= { slaveThreeOutputName 21}
slaveThreeOutputNameTwentyTwo OBJECT-TYPE
    SYNTAX      DisplayString
    MAX-ACCESS  read-write
    STATUS      current
    DESCRIPTION
	"The twenty-second output name of slave 3"
    ::= { slaveThreeOutputName 22}
slaveThreeOutputNameTwentyThree OBJECT-TYPE
    SYNTAX      DisplayString
    MAX-ACCESS  read-write
    STATUS      current
    DESCRIPTION
	"The twenty-third output name of slave 3"
    ::= { slaveThreeOutputName 23}
slaveThreeOutputNameTwentyFour OBJECT-TYPE
    SYNTAX      DisplayString
    MAX-ACCESS  read-write
    STATUS      current
    DESCRIPTION
	"The twenty-fourth output name of slave 3"
    ::= { slaveThreeOutputName 24}


    
slaveThreeOutputStatus OBJECT IDENTIFIER ::= { rpduSlaveThree 9}

slaveThreeOutputStatusOne OBJECT-TYPE
    SYNTAX      DisplayString
    MAX-ACCESS  read-write
    STATUS      current
    DESCRIPTION
	"The first output status of slave 3"
    ::= { slaveThreeOutputStatus 1}
slaveThreeOutputStatusTwo OBJECT-TYPE
    SYNTAX      DisplayString
    MAX-ACCESS  read-write
    STATUS      current
    DESCRIPTION
	"The second output status of slave 3"
    ::= { slaveThreeOutputStatus 2}

slaveThreeOutputStatusThree OBJECT-TYPE
    SYNTAX      DisplayString
    MAX-ACCESS  read-write
    STATUS      current
    DESCRIPTION
	"The third output status of slave 3"
    ::= { slaveThreeOutputStatus 3}
slaveThreeOutputStatusFour OBJECT-TYPE
    SYNTAX      DisplayString
    MAX-ACCESS  read-write
    STATUS      current
    DESCRIPTION
	"The fourth output status of slave 3"
    ::= { slaveThreeOutputStatus 4}
slaveThreeOutputStatusFive OBJECT-TYPE
    SYNTAX      DisplayString
    MAX-ACCESS  read-write
    STATUS      current
    DESCRIPTION
	"The fifth output status of slave 3"
    ::= { slaveThreeOutputStatus 5}
slaveThreeOutputStatusSix OBJECT-TYPE
    SYNTAX      DisplayString
    MAX-ACCESS  read-write
    STATUS      current
    DESCRIPTION
	"The sixth output status of slave 3"
    ::= { slaveThreeOutputStatus 6}
slaveThreeOutputStatusSeven OBJECT-TYPE
    SYNTAX      DisplayString
    MAX-ACCESS  read-write
    STATUS      current
    DESCRIPTION
	"The seventh output status of slave 3"
    ::= { slaveThreeOutputStatus 7}
slaveThreeOutputStatusEight OBJECT-TYPE
    SYNTAX      DisplayString
    MAX-ACCESS  read-write
    STATUS      current
    DESCRIPTION
	"The eighth output status of slave 3"
    ::= { slaveThreeOutputStatus 8}
slaveThreeOutputStatusNine OBJECT-TYPE
    SYNTAX      DisplayString
    MAX-ACCESS  read-write
    STATUS      current
    DESCRIPTION
	"The nineth output status of slave 3"
    ::= { slaveThreeOutputStatus 9}
slaveThreeOutputStatusTen OBJECT-TYPE
    SYNTAX      DisplayString
    MAX-ACCESS  read-write
    STATUS      current
    DESCRIPTION
	"The tenth output status of slave 3"
    ::= { slaveThreeOutputStatus 10}
slaveThreeOutputStatusEleven OBJECT-TYPE
    SYNTAX      DisplayString
    MAX-ACCESS  read-write
    STATUS      current
    DESCRIPTION
	"The eleventh output status of slave 3"
    ::= { slaveThreeOutputStatus 11}
slaveThreeOutputStatusTwelve OBJECT-TYPE
    SYNTAX      DisplayString
    MAX-ACCESS  read-write
    STATUS      current
    DESCRIPTION
	"The twelfth output status of slave 3"
    ::= { slaveThreeOutputStatus 12}
slaveThreeOutputStatusThirteen OBJECT-TYPE
    SYNTAX      DisplayString
    MAX-ACCESS  read-write
    STATUS      current
    DESCRIPTION
	"The thirteenth output status of slave 3"
    ::= { slaveThreeOutputStatus 13}
slaveThreeOutputStatusFourteen OBJECT-TYPE
    SYNTAX      DisplayString
    MAX-ACCESS  read-write
    STATUS      current
    DESCRIPTION
	"The fourteenth output status of slave 3"
    ::= { slaveThreeOutputStatus 14}
slaveThreeOutputStatusFifteen OBJECT-TYPE
    SYNTAX      DisplayString
    MAX-ACCESS  read-write
    STATUS      current
    DESCRIPTION
	"The fifteenth output status of slave 3"
    ::= { slaveThreeOutputStatus 15}
slaveThreeOutputStatusSixteen OBJECT-TYPE
    SYNTAX      DisplayString
    MAX-ACCESS  read-write
    STATUS      current
    DESCRIPTION
	"The sixteenth output status of slave 3"
    ::= { slaveThreeOutputStatus 16}
slaveThreeOutputStatusSeventeen OBJECT-TYPE
    SYNTAX      DisplayString
    MAX-ACCESS  read-write
    STATUS      current
    DESCRIPTION
	"The seventeenth output status of slave 3"
    ::= { slaveThreeOutputStatus 17}
slaveThreeOutputStatusEighteen OBJECT-TYPE
    SYNTAX      DisplayString
    MAX-ACCESS  read-write
    STATUS      current
    DESCRIPTION
	"The eighteenth output status of slave 3"
    ::= { slaveThreeOutputStatus 18}
slaveThreeOutputStatusNineteen OBJECT-TYPE
    SYNTAX      DisplayString
    MAX-ACCESS  read-write
    STATUS      current
    DESCRIPTION
	"The nineteenth output status of slave 3"
    ::= { slaveThreeOutputStatus 19}
slaveThreeOutputStatusTwenty OBJECT-TYPE
    SYNTAX      DisplayString
    MAX-ACCESS  read-write
    STATUS      current
    DESCRIPTION
	"The twentieth output status of slave 3"
    ::= { slaveThreeOutputStatus 20}
slaveThreeOutputStatusTwentyOne OBJECT-TYPE
    SYNTAX      DisplayString
    MAX-ACCESS  read-write
    STATUS      current
    DESCRIPTION
	"The twenty-first output status of slave 3"
    ::= { slaveThreeOutputStatus 21}
slaveThreeOutputStatusTwentyTwo OBJECT-TYPE
    SYNTAX      DisplayString
    MAX-ACCESS  read-write
    STATUS      current
    DESCRIPTION
	"The twenty-second output status of slave 3"
    ::= { slaveThreeOutputStatus 22}
slaveThreeOutputStatusTwentyThree OBJECT-TYPE
    SYNTAX      DisplayString
    MAX-ACCESS  read-write
    STATUS      current
    DESCRIPTION
	"The twenty-third output status of slave 3"
    ::= { slaveThreeOutputStatus 23}
slaveThreeOutputStatusTwentyFour OBJECT-TYPE
    SYNTAX      DisplayString
    MAX-ACCESS  read-write
    STATUS      current
    DESCRIPTION
	"The twenty-fourth output status of slave 3"
    ::= { slaveThreeOutputStatus 24}

slaveThreeOutputCurrent   OBJECT IDENTIFIER ::= { rpduSlaveThree 10}
slaveThreeOutputCurrentOne OBJECT-TYPE
    SYNTAX      DisplayString
    MAX-ACCESS  read-only
    STATUS      current
    DESCRIPTION
	"The current value of the first output of the slave 3"
    ::= { slaveThreeOutputCurrent 1}
slaveThreeOutputCurrentTwo OBJECT-TYPE
    SYNTAX      DisplayString
    MAX-ACCESS  read-only
    STATUS      current
    DESCRIPTION
	"The current value of the second output of the slave 3"
    ::= { slaveThreeOutputCurrent 2}
slaveThreeOutputCurrentThree OBJECT-TYPE
    SYNTAX      DisplayString
    MAX-ACCESS  read-only
    STATUS      current
    DESCRIPTION
	"The current value of the third output of the slave 3"
    ::= { slaveThreeOutputCurrent 3}
slaveThreeOutputCurrentFour OBJECT-TYPE
    SYNTAX      DisplayString
    MAX-ACCESS  read-only
    STATUS      current
    DESCRIPTION
	"The current value of the fourth output of the slave 3"
    ::= { slaveThreeOutputCurrent 4}
slaveThreeOutputCurrentFive OBJECT-TYPE
    SYNTAX      DisplayString
    MAX-ACCESS  read-only
    STATUS      current
    DESCRIPTION
	"The current value of the fifth output of the slave 3"
    ::= { slaveThreeOutputCurrent 5}
slaveThreeOutputCurrentSix OBJECT-TYPE
    SYNTAX      DisplayString
    MAX-ACCESS  read-only
    STATUS      current
    DESCRIPTION
	"The current value of the sixth output of the slave 3"
    ::= { slaveThreeOutputCurrent 6}
slaveThreeOutputCurrentSeven OBJECT-TYPE
    SYNTAX      DisplayString
    MAX-ACCESS  read-only
    STATUS      current
    DESCRIPTION
	"The current value of the seventh output of the slave 3"
    ::= { slaveThreeOutputCurrent 7}
slaveThreeOutputCurrentEight OBJECT-TYPE
    SYNTAX      DisplayString
    MAX-ACCESS  read-only
    STATUS      current
    DESCRIPTION
	"The current value of the eighth output of the slave 3"
    ::= { slaveThreeOutputCurrent 8}
slaveThreeOutputCurrentNine OBJECT-TYPE
    SYNTAX      DisplayString
    MAX-ACCESS  read-only
    STATUS      current
    DESCRIPTION
	"The current value of the nineth output of the slave 3"
    ::= { slaveThreeOutputCurrent 9}
slaveThreeOutputCurrentTen OBJECT-TYPE
    SYNTAX      DisplayString
    MAX-ACCESS  read-only
    STATUS      current
    DESCRIPTION
	"The current value of the tenth output of the slave 3"
    ::= { slaveThreeOutputCurrent 10}
slaveThreeOutputCurrentEleven OBJECT-TYPE
    SYNTAX      DisplayString
    MAX-ACCESS  read-only
    STATUS      current
    DESCRIPTION
	"The current value of the eleventh output of the slave 3"
    ::= { slaveThreeOutputCurrent 11}
slaveThreeOutputCurrentTwelve OBJECT-TYPE
    SYNTAX      DisplayString
    MAX-ACCESS  read-only
    STATUS      current
    DESCRIPTION
	"The current value of the twelfth output of the slave 3"
    ::= { slaveThreeOutputCurrent 12}
slaveThreeOutputCurrentThirteen OBJECT-TYPE
    SYNTAX      DisplayString
    MAX-ACCESS  read-only
    STATUS      current
    DESCRIPTION
	"The current value of the thirteenth output of the slave 3"
    ::= { slaveThreeOutputCurrent 13}
slaveThreeOutputCurrentFourteen OBJECT-TYPE
    SYNTAX      DisplayString
    MAX-ACCESS  read-only
    STATUS      current
    DESCRIPTION
	"The current value of the fourteenth output of the slave 3"
    ::= { slaveThreeOutputCurrent 14}
slaveThreeOutputCurrentFifteen OBJECT-TYPE
    SYNTAX      DisplayString
    MAX-ACCESS  read-only
    STATUS      current
    DESCRIPTION
	"The current value of the fifteenth output of the slave 3"
    ::= { slaveThreeOutputCurrent 15}
slaveThreeOutputCurrentSixteen OBJECT-TYPE
    SYNTAX      DisplayString
    MAX-ACCESS  read-only
    STATUS      current
    DESCRIPTION
	"The current value of the sixteenth output of the slave 3"
    ::= { slaveThreeOutputCurrent 16}
slaveThreeOutputCurrentSeventeen OBJECT-TYPE
    SYNTAX      DisplayString
    MAX-ACCESS  read-only
    STATUS      current
    DESCRIPTION
	"The current value of the seventeenth output of the slave 3"
    ::= { slaveThreeOutputCurrent 17}
slaveThreeOutputCurrentEighteen OBJECT-TYPE
    SYNTAX      DisplayString
    MAX-ACCESS  read-only
    STATUS      current
    DESCRIPTION
	"The current value of the eighteenth output of the slave 3"
    ::= { slaveThreeOutputCurrent 18}
slaveThreeOutputCurrentNineteen OBJECT-TYPE
    SYNTAX      DisplayString
    MAX-ACCESS  read-only
    STATUS      current
    DESCRIPTION
	"The current value of the nineteenth output of the slave 3"
    ::= { slaveThreeOutputCurrent 19}
slaveThreeOutputCurrentTwenty OBJECT-TYPE
    SYNTAX      DisplayString
    MAX-ACCESS  read-only
    STATUS      current
    DESCRIPTION
	"The current value of the twentieth output of the slave 3"
    ::= { slaveThreeOutputCurrent 20}
slaveThreeOutputCurrentTwentyOne OBJECT-TYPE
    SYNTAX      DisplayString
    MAX-ACCESS  read-only
    STATUS      current
    DESCRIPTION
	"The current value of the twenty-first output of the slave 3"
    ::= { slaveThreeOutputCurrent 21}
slaveThreeOutputCurrentTwentyTwo OBJECT-TYPE
    SYNTAX      DisplayString
    MAX-ACCESS  read-only
    STATUS      current
    DESCRIPTION
	"The current value of the twenty-second output of the slave 3"
    ::= { slaveThreeOutputCurrent 22}
slaveThreeOutputCurrentTwentyThree OBJECT-TYPE
    SYNTAX      DisplayString
    MAX-ACCESS  read-only
    STATUS      current
    DESCRIPTION
	"The current value of the twenty-third output of the slave 3"
    ::= { slaveThreeOutputCurrent 23}
slaveThreeOutputCurrentTwentyFour OBJECT-TYPE
    SYNTAX      DisplayString
    MAX-ACCESS  read-only
    STATUS      current
    DESCRIPTION
	"The current value of the twenty-fourth output of the slave 3"
    ::= { slaveThreeOutputCurrent 24}

slaveThreeOutputCurrentMin   OBJECT IDENTIFIER ::= { rpduSlaveThree 11}
slaveThreeOutputCurrentMinOne OBJECT-TYPE
    SYNTAX      DisplayString
    MAX-ACCESS  read-only
    STATUS      current
    DESCRIPTION
	"The Min. current value of the first output of the slave 3"
    ::= { slaveThreeOutputCurrentMin 1}
slaveThreeOutputCurrentMinTwo OBJECT-TYPE
    SYNTAX      DisplayString
    MAX-ACCESS  read-only
    STATUS      current
    DESCRIPTION
	"The Min. current value of the second output of the slave 3"
    ::= { slaveThreeOutputCurrentMin 2}
slaveThreeOutputCurrentMinThree OBJECT-TYPE
    SYNTAX      DisplayString
    MAX-ACCESS  read-only
    STATUS      current
    DESCRIPTION
	"The Min. current value of the third output of the slave 3"
    ::= { slaveThreeOutputCurrentMin 3}
slaveThreeOutputCurrentMinFour OBJECT-TYPE
    SYNTAX      DisplayString
    MAX-ACCESS  read-only
    STATUS      current
    DESCRIPTION
	"The Min. current value of the fourth output of the slave 3"
    ::= { slaveThreeOutputCurrentMin 4}
slaveThreeOutputCurrentMinFive OBJECT-TYPE
    SYNTAX      DisplayString
    MAX-ACCESS  read-only
    STATUS      current
    DESCRIPTION
	"The Min. current value of the fifth output of the slave 3"
    ::= { slaveThreeOutputCurrentMin 5}
slaveThreeOutputCurrentMinSix OBJECT-TYPE
    SYNTAX      DisplayString
    MAX-ACCESS  read-only
    STATUS      current
    DESCRIPTION
	"The Min. current value of the sixth output of the slave 3"
    ::= { slaveThreeOutputCurrentMin 6}
slaveThreeOutputCurrentMinSeven OBJECT-TYPE
    SYNTAX      DisplayString
    MAX-ACCESS  read-only
    STATUS      current
    DESCRIPTION
	"The Min. current value of the seventh output of the slave 3"
    ::= { slaveThreeOutputCurrentMin 7}
slaveThreeOutputCurrentMinEight OBJECT-TYPE
    SYNTAX      DisplayString
    MAX-ACCESS  read-only
    STATUS      current
    DESCRIPTION
	"The Min. current value of the eighth output of the slave 3"
    ::= { slaveThreeOutputCurrentMin 8}
slaveThreeOutputCurrentMinNine OBJECT-TYPE
    SYNTAX      DisplayString
    MAX-ACCESS  read-only
    STATUS      current
    DESCRIPTION
	"The Min. current value of the nineth output of the slave 3"
    ::= { slaveThreeOutputCurrentMin 9}
slaveThreeOutputCurrentMinTen OBJECT-TYPE
    SYNTAX      DisplayString
    MAX-ACCESS  read-only
    STATUS      current
    DESCRIPTION
	"The Min. current value of the tenth output of the slave 3"
    ::= { slaveThreeOutputCurrentMin 10}
slaveThreeOutputCurrentMinEleven OBJECT-TYPE
    SYNTAX      DisplayString
    MAX-ACCESS  read-only
    STATUS      current
    DESCRIPTION
	"The Min. current value of the eleventh output of the slave 3"
    ::= { slaveThreeOutputCurrentMin 11}
slaveThreeOutputCurrentMinTwleve OBJECT-TYPE
    SYNTAX      DisplayString
    MAX-ACCESS  read-only
    STATUS      current
    DESCRIPTION
	"The Min. current value of the twelfth output of the slave 3"
    ::= { slaveThreeOutputCurrentMin 12}
slaveThreeOutputCurrentMinThirteen OBJECT-TYPE
    SYNTAX      DisplayString
    MAX-ACCESS  read-only
    STATUS      current
    DESCRIPTION
	"The Min. current value of the thirteenth output of the slave 3"
    ::= { slaveThreeOutputCurrentMin 13}
slaveThreeOutputCurrentMinFourteen OBJECT-TYPE
    SYNTAX      DisplayString
    MAX-ACCESS  read-only
    STATUS      current
    DESCRIPTION
	"The Min. current value of the fourteenth output of the slave 3"
    ::= { slaveThreeOutputCurrentMin 14}
slaveThreeOutputCurrentMinFifteen OBJECT-TYPE
    SYNTAX      DisplayString
    MAX-ACCESS  read-only
    STATUS      current
    DESCRIPTION
	"The Min. current value of the fifteenth output of the slave 3"
    ::= { slaveThreeOutputCurrentMin 15}
slaveThreeOutputCurrentMinSixteen OBJECT-TYPE
    SYNTAX      DisplayString
    MAX-ACCESS  read-only
    STATUS      current
    DESCRIPTION
	"The Min. current value of the sixteenth output of the slave 3"
    ::= { slaveThreeOutputCurrentMin 16}
slaveThreeOutputCurrentMinSeventeen OBJECT-TYPE
    SYNTAX      DisplayString
    MAX-ACCESS  read-only
    STATUS      current
    DESCRIPTION
	"The Min. current value of the seventeenth output of the slave 3"
    ::= { slaveThreeOutputCurrentMin 17}
slaveThreeOutputCurrentMinEighteen OBJECT-TYPE
    SYNTAX      DisplayString
    MAX-ACCESS  read-only
    STATUS      current
    DESCRIPTION
	"The Min. current value of the eighteenth output of the slave 3"
    ::= { slaveThreeOutputCurrentMin 18}
slaveThreeOutputCurrentMinNineteen OBJECT-TYPE
    SYNTAX      DisplayString
    MAX-ACCESS  read-only
    STATUS      current
    DESCRIPTION
	"The Min. current value of the nineteenth output of the slave 3"
    ::= { slaveThreeOutputCurrentMin 19}
slaveThreeOutputCurrentMinTwenty OBJECT-TYPE
    SYNTAX      DisplayString
    MAX-ACCESS  read-only
    STATUS      current
    DESCRIPTION
	"The Min. current value of the twentieth output of the slave 3"
    ::= { slaveThreeOutputCurrentMin 20}
slaveThreeOutputCurrentMinTwentyOne OBJECT-TYPE
    SYNTAX      DisplayString
    MAX-ACCESS  read-only
    STATUS      current
    DESCRIPTION
	"The Min. current value of the twentyth-first output of the slave 3"
    ::= { slaveThreeOutputCurrentMin 21}
slaveThreeOutputCurrentMinTwentyTwo OBJECT-TYPE
    SYNTAX      DisplayString
    MAX-ACCESS  read-only
    STATUS      current
    DESCRIPTION
	"The Min. current value of the twentyth-second output of the slave 3"
    ::= { slaveThreeOutputCurrentMin 22}
slaveThreeOutputCurrentMinTwentyThree OBJECT-TYPE
    SYNTAX      DisplayString
    MAX-ACCESS  read-only
    STATUS      current
    DESCRIPTION
	"The Min. current value of the twentyth-third output of the slave 3"
    ::= { slaveThreeOutputCurrentMin 23}
slaveThreeOutputCurrentMinTwentyFour OBJECT-TYPE
    SYNTAX      DisplayString
    MAX-ACCESS  read-only
    STATUS      current
    DESCRIPTION
	"The Min. current value of the twentyth-fourth output of the slave 3"
    ::= { slaveThreeOutputCurrentMin 24}




slaveThreeOutputCurrentMax   OBJECT IDENTIFIER ::= { rpduSlaveThree 12}
slaveThreeOutputCurrentMaxOne OBJECT-TYPE
    SYNTAX      DisplayString
    MAX-ACCESS  read-only
    STATUS      current
    DESCRIPTION
	"The Max. current value of the first output of the slave 3"
    ::= { slaveThreeOutputCurrentMax 1}
slaveThreeOutputCurrentMaxTwo OBJECT-TYPE
    SYNTAX      DisplayString
    MAX-ACCESS  read-only
    STATUS      current
    DESCRIPTION
	"The Max. current value of the second output of the slave 3"
    ::= { slaveThreeOutputCurrentMax 2}
slaveThreeOutputCurrentMaxThree OBJECT-TYPE
    SYNTAX      DisplayString
    MAX-ACCESS  read-only
    STATUS      current
    DESCRIPTION
	"The Max. current value of the third output of the slave 3"
    ::= { slaveThreeOutputCurrentMax 3}
slaveThreeOutputCurrentMaxFour OBJECT-TYPE
    SYNTAX      DisplayString
    MAX-ACCESS  read-only
    STATUS      current
    DESCRIPTION
	"The Max. current value of the fourth output of the slave 3"
    ::= { slaveThreeOutputCurrentMax 4}
slaveThreeOutputCurrentMaxFive OBJECT-TYPE
    SYNTAX      DisplayString
    MAX-ACCESS  read-only
    STATUS      current
    DESCRIPTION
	"The Max. current value of the fifth output of the slave 3"
    ::= { slaveThreeOutputCurrentMax 5}
slaveThreeOutputCurrentMaxSix OBJECT-TYPE
    SYNTAX      DisplayString
    MAX-ACCESS  read-only
    STATUS      current
    DESCRIPTION
	"The Max. current value of the sixth output of the slave 3"
    ::= { slaveThreeOutputCurrentMax 6}
slaveThreeOutputCurrentMaxSeven OBJECT-TYPE
    SYNTAX      DisplayString
    MAX-ACCESS  read-only
    STATUS      current
    DESCRIPTION
	"The Max. current value of the seventh output of the slave 3"
    ::= { slaveThreeOutputCurrentMax 7}
slaveThreeOutputCurrentMaxEight OBJECT-TYPE
    SYNTAX      DisplayString
    MAX-ACCESS  read-only
    STATUS      current
    DESCRIPTION
	"The Max. current value of the eighth output of the slave 3"
    ::= { slaveThreeOutputCurrentMax 8}
slaveThreeOutputCurrentMaxNine OBJECT-TYPE
    SYNTAX      DisplayString
    MAX-ACCESS  read-only
    STATUS      current
    DESCRIPTION
	"The Max. current value of the nineth output of the slave 3"
    ::= { slaveThreeOutputCurrentMax 9}
slaveThreeOutputCurrentMaxTen OBJECT-TYPE
    SYNTAX      DisplayString
    MAX-ACCESS  read-only
    STATUS      current
    DESCRIPTION
	"The Max. current value of the tenth output of the slave 3"
    ::= { slaveThreeOutputCurrentMax 10}
slaveThreeOutputCurrentMaxEleven OBJECT-TYPE
    SYNTAX      DisplayString
    MAX-ACCESS  read-only
    STATUS      current
    DESCRIPTION
	"The Max. current value of the eleventh output of the slave 3"
    ::= { slaveThreeOutputCurrentMax 11}
slaveThreeOutputCurrentMaxTwleve OBJECT-TYPE
    SYNTAX      DisplayString
    MAX-ACCESS  read-only
    STATUS      current
    DESCRIPTION
	"The Max. current value of the twelfth output of the slave 3"
    ::= { slaveThreeOutputCurrentMax 12}
slaveThreeOutputCurrentMaxThirteen OBJECT-TYPE
    SYNTAX      DisplayString
    MAX-ACCESS  read-only
    STATUS      current
    DESCRIPTION
	"The Max. current value of the thirteenth output of the slave 3"
    ::= { slaveThreeOutputCurrentMax 13}
slaveThreeOutputCurrentMaxFourteen OBJECT-TYPE
    SYNTAX      DisplayString
    MAX-ACCESS  read-only
    STATUS      current
    DESCRIPTION
	"The Max. current value of the fourteenth output of the slave 3"
    ::= { slaveThreeOutputCurrentMax 14}
slaveThreeOutputCurrentMaxFifteen OBJECT-TYPE
    SYNTAX      DisplayString
    MAX-ACCESS  read-only
    STATUS      current
    DESCRIPTION
	"The Max. current value of the fifteenth output of the slave 3"
    ::= { slaveThreeOutputCurrentMax 15}
slaveThreeOutputCurrentMaxSixteen OBJECT-TYPE
    SYNTAX      DisplayString
    MAX-ACCESS  read-only
    STATUS      current
    DESCRIPTION
	"The Max. current value of the sixteenth output of the slave 3"
    ::= { slaveThreeOutputCurrentMax 16}
slaveThreeOutputCurrentMaxSeventeen OBJECT-TYPE
    SYNTAX      DisplayString
    MAX-ACCESS  read-only
    STATUS      current
    DESCRIPTION
	"The Max. current value of the seventeenth output of the slave 3"
    ::= { slaveThreeOutputCurrentMax 17}
slaveThreeOutputCurrentMaxEighteen OBJECT-TYPE
    SYNTAX      DisplayString
    MAX-ACCESS  read-only
    STATUS      current
    DESCRIPTION
	"The Max. current value of the eighteenth output of the slave 3"
    ::= { slaveThreeOutputCurrentMax 18}
slaveThreeOutputCurrentMaxNineteen OBJECT-TYPE
    SYNTAX      DisplayString
    MAX-ACCESS  read-only
    STATUS      current
    DESCRIPTION
	"The Max. current value of the nineteenth output of the slave 3"
    ::= { slaveThreeOutputCurrentMax 19}
slaveThreeOutputCurrentMaxTwenty OBJECT-TYPE
    SYNTAX      DisplayString
    MAX-ACCESS  read-only
    STATUS      current
    DESCRIPTION
	"The Max. current value of the twentieth output of the slave 3"
    ::= { slaveThreeOutputCurrentMax 20}
slaveThreeOutputCurrentMaxTwentyOne OBJECT-TYPE
    SYNTAX      DisplayString
    MAX-ACCESS  read-only
    STATUS      current
    DESCRIPTION
	"The Max. current value of the twenty-first output of the slave 3"
    ::= { slaveThreeOutputCurrentMax 21}
slaveThreeOutputCurrentMaxTwentyTwo OBJECT-TYPE
    SYNTAX      DisplayString
    MAX-ACCESS  read-only
    STATUS      current
    DESCRIPTION
	"The Max. current value of the twenty-second output of the slave 3"
    ::= { slaveThreeOutputCurrentMax 22}
slaveThreeOutputCurrentMaxTwentyThree OBJECT-TYPE
    SYNTAX      DisplayString
    MAX-ACCESS  read-only
    STATUS      current
    DESCRIPTION
	"The Max. current value of the twenty-third output of the slave 3"
    ::= { slaveThreeOutputCurrentMax 23}
slaveThreeOutputCurrentMaxTwentyFour OBJECT-TYPE
    SYNTAX      DisplayString
    MAX-ACCESS  read-only
    STATUS      current
    DESCRIPTION
	"The Max. current value of the twenty-fourth output of the slave 3"
    ::= { slaveThreeOutputCurrentMax 24}


slaveThreeOutputCurrentEnergy  OBJECT IDENTIFIER ::= { rpduSlaveThree 13}
slaveThreeOutputCurrentEnergyOne OBJECT-TYPE
    SYNTAX	DisplayString
    MAX-ACCESS	read-only
    STATUS	current
    DESCRIPTION
	"The energy value of the first output of the slave 3"
    ::={slaveThreeOutputCurrentEnergy 1}
slaveThreeOutputCurrentEnergyTwo OBJECT-TYPE
    SYNTAX	DisplayString
    MAX-ACCESS	read-only
    STATUS	current
    DESCRIPTION
	"The energy value of the second output of the slave 3"
    ::={slaveThreeOutputCurrentEnergy 2}
slaveThreeOutputCurrentEnergyThree OBJECT-TYPE
    SYNTAX	DisplayString
    MAX-ACCESS	read-only
    STATUS	current
    DESCRIPTION
	"The energy value of the third output of the slave 3"
    ::={slaveThreeOutputCurrentEnergy 3}
slaveThreeOutputCurrentEnergyFour OBJECT-TYPE
    SYNTAX	DisplayString
    MAX-ACCESS	read-only
    STATUS	current
    DESCRIPTION
	"The energy value of the fourth output of the slave 3"
    ::={slaveThreeOutputCurrentEnergy 4}
slaveThreeOutputCurrentEnergyFive OBJECT-TYPE
    SYNTAX	DisplayString
    MAX-ACCESS	read-only
    STATUS	current
    DESCRIPTION
	"The energy value of the fifth output of the slave 3"
    ::={slaveThreeOutputCurrentEnergy 5}
slaveThreeOutputCurrentEnergySix OBJECT-TYPE
    SYNTAX	DisplayString
    MAX-ACCESS	read-only
    STATUS	current
    DESCRIPTION
	"The energy value of the sixth output of the slave 3"
    ::={slaveThreeOutputCurrentEnergy 6}
slaveThreeOutputCurrentEnergySeven OBJECT-TYPE
    SYNTAX	DisplayString
    MAX-ACCESS	read-only
    STATUS	current
    DESCRIPTION
	"The energy value of the seventh output of the slave 3"
    ::={slaveThreeOutputCurrentEnergy 7}
slaveThreeOutputCurrentEnergyEight OBJECT-TYPE
    SYNTAX	DisplayString
    MAX-ACCESS	read-only
    STATUS	current
    DESCRIPTION
	"The energy value of the eighth output of the slave 3"
    ::={slaveThreeOutputCurrentEnergy 8}
slaveThreeOutputCurrentEnergyNine OBJECT-TYPE
    SYNTAX	DisplayString
    MAX-ACCESS	read-only
    STATUS	current
    DESCRIPTION
	"The energy value of the nineth output of the slave 3"
    ::={slaveThreeOutputCurrentEnergy 9}
slaveThreeOutputCurrentEnergyTen OBJECT-TYPE
    SYNTAX	DisplayString
    MAX-ACCESS	read-only
    STATUS	current
    DESCRIPTION
	"The energy value of the tenth output of the slave 3"
    ::={slaveThreeOutputCurrentEnergy 10}
slaveThreeOutputCurrentEnergyEleven OBJECT-TYPE
    SYNTAX	DisplayString
    MAX-ACCESS	read-only
    STATUS	current
    DESCRIPTION
	"The energy value of the eleventh output of the slave 3"
    ::={slaveThreeOutputCurrentEnergy 11}
slaveThreeOutputCurrentEnergyTwelve OBJECT-TYPE
    SYNTAX	DisplayString
    MAX-ACCESS	read-only
    STATUS	current
    DESCRIPTION
	"The energy value of the twelfth output of the slave 3"
    ::={slaveThreeOutputCurrentEnergy 12}
slaveThreeOutputCurrentEnergyThirteen OBJECT-TYPE
    SYNTAX	DisplayString
    MAX-ACCESS	read-only
    STATUS	current
    DESCRIPTION
	"The energy value of the thirteenth output of the slave 3"
    ::={slaveThreeOutputCurrentEnergy 13}
slaveThreeOutputCurrentEnergyFourteen OBJECT-TYPE
    SYNTAX	DisplayString
    MAX-ACCESS	read-only
    STATUS	current
    DESCRIPTION
	"The energy value of the fourteenth output of the slave 3"
    ::={slaveThreeOutputCurrentEnergy 14}
slaveThreeOutputCurrentEnergyFifteen OBJECT-TYPE
    SYNTAX	DisplayString
    MAX-ACCESS	read-only
    STATUS	current
    DESCRIPTION
	"The energy value of the fifteenth output of the slave 3"
    ::={slaveThreeOutputCurrentEnergy 15}
slaveThreeOutputCurrentEnergySixteen OBJECT-TYPE
    SYNTAX	DisplayString
    MAX-ACCESS	read-only
    STATUS	current
    DESCRIPTION
	"The energy value of the sixteenth output of the slave 3"
    ::={slaveThreeOutputCurrentEnergy 16}
slaveThreeOutputCurrentEnergySeventeen OBJECT-TYPE
    SYNTAX	DisplayString
    MAX-ACCESS	read-only
    STATUS	current
    DESCRIPTION
	"The energy value of the seventeenth output of the slave 3"
    ::={slaveThreeOutputCurrentEnergy 17}
slaveThreeOutputCurrentEnergyEighteen OBJECT-TYPE
    SYNTAX	DisplayString
    MAX-ACCESS	read-only
    STATUS	current
    DESCRIPTION
	"The energy value of the eighteenth output of the slave 3"
    ::={slaveThreeOutputCurrentEnergy 18}
slaveThreeOutputCurrentEnergyNineteen OBJECT-TYPE
    SYNTAX	DisplayString
    MAX-ACCESS	read-only
    STATUS	current
    DESCRIPTION
	"The energy value of the nineteenth output of the slave 3"
    ::={slaveThreeOutputCurrentEnergy 19}
slaveThreeOutputCurrentEnergyTwenty OBJECT-TYPE
    SYNTAX	DisplayString
    MAX-ACCESS	read-only
    STATUS	current
    DESCRIPTION
	"The energy value of the twentieth output of the slave 3"
    ::={slaveThreeOutputCurrentEnergy 20}
slaveThreeOutputCurrentEnergyTwentyOne OBJECT-TYPE
    SYNTAX	DisplayString
    MAX-ACCESS	read-only
    STATUS	current
    DESCRIPTION
	"The energy value of the twenty-first output of the slave 3"
    ::={slaveThreeOutputCurrentEnergy 21}
slaveThreeOutputCurrentEnergyTwentyTwo OBJECT-TYPE
    SYNTAX	DisplayString
    MAX-ACCESS	read-only
    STATUS	current
    DESCRIPTION
	"The energy value of the twenty-second output of the slave 3"
    ::={slaveThreeOutputCurrentEnergy 22}
slaveThreeOutputCurrentEnergyTwentyThree OBJECT-TYPE
    SYNTAX	DisplayString
    MAX-ACCESS	read-only
    STATUS	current
    DESCRIPTION
	"The energy value of the twenty-third output of the slave 3"
    ::={slaveThreeOutputCurrentEnergy 23}
slaveThreeOutputCurrentEnergyTwentyFour OBJECT-TYPE
    SYNTAX	DisplayString
    MAX-ACCESS	read-only
    STATUS	current
    DESCRIPTION
	"The energy value of the twenty-fourth output of the slave 3"
    ::={slaveThreeOutputCurrentEnergy 24}

-------------------------------Slave4---------------------------------------------  
rpduDeviceFive OBJECT IDENTIFIER ::= { rpdu 5}
rpduSlaveFour OBJECT IDENTIFIER ::= { rpduDeviceFive 1}

slaveFourName OBJECT-TYPE
    SYNTAX      DisplayString
    MAX-ACCESS  read-write
    STATUS      current
    DESCRIPTION
	"This is the fifth device."
    ::= { rpduSlaveFour 1}
    
slaveFourType OBJECT-TYPE
    SYNTAX      DisplayString
    MAX-ACCESS  read-only
    STATUS      current
    DESCRIPTION
	"This is device type "
    ::= { rpduSlaveFour 2}
    
slaveFourOutputNumber OBJECT-TYPE 
    SYNTAX      Integer32
    MAX-ACCESS  read-only
    STATUS      current
    DESCRIPTION
	"This is the output quantity"
::= { rpduSlaveFour 7}
    
slaveFourLineOne OBJECT IDENTIFIER ::= { rpduSlaveFour 3}
slaveFourLineOnePower OBJECT-TYPE
    SYNTAX      DisplayString
    MAX-ACCESS  read-only
    STATUS      current
    DESCRIPTION
	"The power of phase one"
    ::= { slaveFourLineOne 1}
slaveFourLineOnePF OBJECT-TYPE
    SYNTAX      DisplayString
    MAX-ACCESS  read-only
    STATUS      current
    DESCRIPTION
	"The power factor of phase one"
    ::= { slaveFourLineOne 2}
    
slaveFourLineOneEnergy OBJECT-TYPE
    SYNTAX      DisplayString
    MAX-ACCESS  read-only
    STATUS      current
    DESCRIPTION
	"The energy of phase one"
    ::= { slaveFourLineOne 3}
slaveFourLineOneCurrent OBJECT-TYPE
    SYNTAX      DisplayString
    MAX-ACCESS  read-only
    STATUS      current
    DESCRIPTION
	"The current of phase one"
    ::= { slaveFourLineOne 4}
slaveFourLineOneVoltage OBJECT-TYPE
    SYNTAX      Integer32
    MAX-ACCESS  read-only
    STATUS      current
    DESCRIPTION
	"The voltage of phase one"
    ::= { slaveFourLineOne 5}
slaveFourLineOneCurrentMin OBJECT-TYPE
    SYNTAX      DisplayString
    MAX-ACCESS  read-only
    STATUS      current
    DESCRIPTION
	"The Min. current value of phase one"
	::= { slaveFourLineOne 6}
slaveFourLineOneCurrentMax OBJECT-TYPE
    SYNTAX      DisplayString
    MAX-ACCESS  read-only
    STATUS      current
    DESCRIPTION
	"The Max. current value of phase one"
    ::= { slaveFourLineOne 7}
    
slaveFourLineOneVoltageMin OBJECT-TYPE
    SYNTAX      Integer32
    MAX-ACCESS  read-only
    STATUS      current
    DESCRIPTION
	"The Min. voltage value of phase one"
    ::= { slaveFourLineOne 8}
    
slaveFourLineOneVoltageMax OBJECT-TYPE
    SYNTAX      Integer32
    MAX-ACCESS  read-only
    STATUS      current
    DESCRIPTION
	"The Max. voltage value of phase one"
    ::= { slaveFourLineOne 9}


slaveFourLineTwo OBJECT IDENTIFIER ::= { rpduSlaveFour 4}
slaveFourLineTwoPower OBJECT-TYPE
    SYNTAX      DisplayString
    MAX-ACCESS  read-only
    STATUS      current
    DESCRIPTION
	"The power of phase two"
    ::= { slaveFourLineTwo 1}

slaveFourLineTwoPF OBJECT-TYPE
    SYNTAX      DisplayString
    MAX-ACCESS  read-only
    STATUS      current
    DESCRIPTION
	"The power factor of phase two"   
    ::= { slaveFourLineTwo 2}
    
slaveFourLineTwoEnergy OBJECT-TYPE
    SYNTAX      DisplayString
    MAX-ACCESS  read-only
    STATUS      current
    DESCRIPTION
	"The energy of phase two"
    ::= { slaveFourLineTwo 3}
slaveFourLineTwoCurrent OBJECT-TYPE           
    SYNTAX      DisplayString 
    MAX-ACCESS  read-only
    STATUS      current
    DESCRIPTION
	"The current of phase two"
    ::= { slaveFourLineTwo 4}
slaveFourLineTwoVoltage OBJECT-TYPE
    SYNTAX      Integer32
    MAX-ACCESS  read-only
    STATUS      current
    DESCRIPTION
	"The voltage of phase two"
    ::= { slaveFourLineTwo 5}
slaveFourLineTwoCurrentMin OBJECT-TYPE
    SYNTAX      DisplayString
    MAX-ACCESS  read-only
    STATUS      current
    DESCRIPTION
	"The Min. current value of phase two"
    ::= { slaveFourLineTwo 6}
slaveFourLineTwoCurrentMax OBJECT-TYPE
    SYNTAX      DisplayString
    MAX-ACCESS  read-only
    STATUS      current
    DESCRIPTION
	"The Max. current value of phase two"
    ::= { slaveFourLineTwo 7}
    
slaveFourLineTwoVoltageMin OBJECT-TYPE
    SYNTAX      Integer32
    MAX-ACCESS  read-only
    STATUS      current
    DESCRIPTION
	"The Min. voltage value of phase two"
    ::= { slaveFourLineTwo 8}
    
slaveFourLineTwoVoltageMax OBJECT-TYPE
    SYNTAX      Integer32
    MAX-ACCESS  read-only
    STATUS      current
    DESCRIPTION
	"The Max. voltage value of phase two"
    ::= { slaveFourLineTwo 9}



slaveFourLineThree OBJECT IDENTIFIER ::= { rpduSlaveFour 5}
slaveFourLineThreePower OBJECT-TYPE
    SYNTAX      DisplayString
    MAX-ACCESS  read-only
    STATUS      current
    DESCRIPTION
	"The power of phase three"
    ::= { slaveFourLineThree 1}

slaveFourLineThreePF OBJECT-TYPE
    SYNTAX      DisplayString
    MAX-ACCESS  read-only
    STATUS      current
    DESCRIPTION
	"The power factor of phase three"     
    ::= { slaveFourLineThree 2}
    
slaveFourLineThreeEnergy OBJECT-TYPE
    SYNTAX      DisplayString
    MAX-ACCESS  read-only
    STATUS      current
    DESCRIPTION
	"The energy of phase three"
    ::= { slaveFourLineThree 3}
slaveFourLineThreeCurrent OBJECT-TYPE
    SYNTAX      DisplayString
    MAX-ACCESS  read-only
    STATUS      current
    DESCRIPTION
	"The current of phase three"
    ::= { slaveFourLineThree 4}
slaveFourLineThreeVoltage OBJECT-TYPE
    SYNTAX      Integer32
    MAX-ACCESS  read-only
    STATUS      current
    DESCRIPTION
	"The voltage of phase three"
    ::= { slaveFourLineThree 5}
slaveFourLineThreeCurrentMin OBJECT-TYPE
    SYNTAX      DisplayString
    MAX-ACCESS  read-only
    STATUS      current
    DESCRIPTION
	"The Min. current value of phase three"
    ::= { slaveFourLineThree 6}
slaveFourLineThreeCurrentMax OBJECT-TYPE
    SYNTAX      DisplayString
    MAX-ACCESS  read-only
    STATUS      current
    DESCRIPTION
	"The Max. current value of phase three"
    ::= { slaveFourLineThree 7}
    
slaveFourLineThreeVoltageMin OBJECT-TYPE
    SYNTAX      Integer32
    MAX-ACCESS  read-only
    STATUS      current
    DESCRIPTION
	"The Min. voltage value of phase three"
    ::= { slaveFourLineThree 8}
    
slaveFourLineThreeVoltageMax OBJECT-TYPE
    SYNTAX      Integer32
    MAX-ACCESS  read-only
    STATUS      current
    DESCRIPTION
	"The Max. voltage value of phase three"
    ::= { slaveFourLineThree 9}


slaveFourSensor OBJECT IDENTIFIER ::= { rpduSlaveFour 6}
slaveFourTempOne OBJECT-TYPE
    SYNTAX      Integer32
    MAX-ACCESS  read-only
    STATUS      current
    DESCRIPTION
	"The first temperature sensor of slave 4"
    ::= { slaveFourSensor 1}
slaveFourTempTwo OBJECT-TYPE
    SYNTAX      Integer32
    MAX-ACCESS  read-only
    STATUS      current
    DESCRIPTION
	"The second temperature sensor of slave 4"
    ::= { slaveFourSensor 2}
slaveFourTempThree OBJECT-TYPE
    SYNTAX      Integer32
    MAX-ACCESS  read-only
    STATUS      current
    DESCRIPTION
	"The third temperature sensor of slave 4"
    ::= { slaveFourSensor 3}
slaveFourTempFour OBJECT-TYPE
    SYNTAX      Integer32
    MAX-ACCESS  read-only
    STATUS      current
    DESCRIPTION
	"The fourth temperature sensor of slave 4"
    ::= { slaveFourSensor 4}
slaveFourHumOne OBJECT-TYPE
    SYNTAX      Integer32
    MAX-ACCESS  read-only
    STATUS      current
    DESCRIPTION
	"The first humidity sensor of slave 4"
    ::= { slaveFourSensor 5}
slaveFourHumTwo OBJECT-TYPE
    SYNTAX      Integer32
    MAX-ACCESS  read-only
    STATUS      current
    DESCRIPTION
	"The second humidity sensor of slave 4"
    ::= { slaveFourSensor 6}
slaveFourHumThree OBJECT-TYPE
    SYNTAX      Integer32
    MAX-ACCESS  read-only
    STATUS      current
    DESCRIPTION
	"The third humidity sensor of slave 4"
    ::= { slaveFourSensor 7}
slaveFourHumFour OBJECT-TYPE
    SYNTAX      Integer32
    MAX-ACCESS  read-only
    STATUS      current
    DESCRIPTION
	"The fourth humidity sensor of slave 4"
    ::= { slaveFourSensor 8}

slaveFourDoorOne OBJECT-TYPE
    SYNTAX      DisplayString
    MAX-ACCESS  read-only
    STATUS      current
    DESCRIPTION
	"The first door sensor of slave 4"    
    ::= { slaveFourSensor 9}
slaveFourDoorTwo OBJECT-TYPE
    SYNTAX      DisplayString
    MAX-ACCESS  read-only
    STATUS      current
    DESCRIPTION
	"The second door sensor of slave 4"  
    ::= { slaveFourSensor 10}
slaveFourSmoke OBJECT-TYPE
    SYNTAX      DisplayString
    MAX-ACCESS  read-only
    STATUS      current
    DESCRIPTION
	"The smoke sensor of slave 4"
    ::= { slaveFourSensor 11}
slaveFourWater OBJECT-TYPE
    SYNTAX      DisplayString
    MAX-ACCESS  read-only
    STATUS      current
    DESCRIPTION
	"The water sensor of slave 4"
    ::= { slaveFourSensor 12}


	
        
slaveFourOutputName OBJECT IDENTIFIER ::= { rpduSlaveFour 8}
slaveFourOutputNameOne OBJECT-TYPE
    SYNTAX      DisplayString
    MAX-ACCESS  read-write
    STATUS      current
    DESCRIPTION
	"The first output name of slave 4"
    ::= { slaveFourOutputName 1}

slaveFourOutputNameTwo OBJECT-TYPE
    SYNTAX      DisplayString
    MAX-ACCESS  read-write
    STATUS      current
    DESCRIPTION
	"The second output name of slave 4"
    ::= { slaveFourOutputName 2}
slaveFourOutputNameThree OBJECT-TYPE
    SYNTAX      DisplayString
    MAX-ACCESS  read-write
    STATUS      current
    DESCRIPTION
	"The third output name of slave 4"
    ::= { slaveFourOutputName 3}
slaveFourOutputNameFour OBJECT-TYPE
    SYNTAX      DisplayString
    MAX-ACCESS  read-write
    STATUS      current
    DESCRIPTION
	"The fourth output name of slave 4"
    ::= { slaveFourOutputName 4}
slaveFourOutputNameFive OBJECT-TYPE
    SYNTAX      DisplayString
    MAX-ACCESS  read-write
    STATUS      current
    DESCRIPTION
	"The fifth output name of slave 4"
    ::= { slaveFourOutputName 5}
slaveFourOutputNameSix OBJECT-TYPE
    SYNTAX      DisplayString
    MAX-ACCESS  read-write
    STATUS      current
    DESCRIPTION
	"The sixth output name of slave 4"
    ::= { slaveFourOutputName 6}
slaveFourOutputNameSeven OBJECT-TYPE
    SYNTAX      DisplayString
    MAX-ACCESS  read-write
    STATUS      current
    DESCRIPTION
	"The seventh output name of slave 4"
    ::= { slaveFourOutputName 7}
slaveFourOutputNameEight OBJECT-TYPE
    SYNTAX      DisplayString
    MAX-ACCESS  read-write
    STATUS      current
    DESCRIPTION
	"The eighth output name of slave 4"
    ::= { slaveFourOutputName 8}
slaveFourOutputNameNine OBJECT-TYPE
    SYNTAX      DisplayString
    MAX-ACCESS  read-write
    STATUS      current
    DESCRIPTION
	"The nineth output name of slave 4"
    ::= { slaveFourOutputName 9}
slaveFourOutputNameTen OBJECT-TYPE
    SYNTAX      DisplayString
    MAX-ACCESS  read-write
    STATUS      current
    DESCRIPTION
	"The tenth output name of slave 4"
    ::= { slaveFourOutputName 10}
slaveFourOutputNameEleven OBJECT-TYPE
    SYNTAX      DisplayString
    MAX-ACCESS  read-write
    STATUS      current
    DESCRIPTION
	"The eleventh output name of slave 4"
    ::= { slaveFourOutputName 11}
slaveFourOutputNameTwelve OBJECT-TYPE
    SYNTAX      DisplayString
    MAX-ACCESS  read-write
    STATUS      current
    DESCRIPTION
	"The twelfth output name of slave 4"
    ::= { slaveFourOutputName 12}
slaveFourOutputNameThirteen OBJECT-TYPE
    SYNTAX      DisplayString
    MAX-ACCESS  read-write
    STATUS      current
    DESCRIPTION
	"The thirteenth output name of slave 4"
    ::= { slaveFourOutputName 13}
slaveFourOutputNameFourteen OBJECT-TYPE
    SYNTAX      DisplayString
    MAX-ACCESS  read-write
    STATUS      current
    DESCRIPTION
	"The fourteenth output name of slave 4"
    ::= { slaveFourOutputName 14}
slaveFourOutputNameFifteen OBJECT-TYPE
    SYNTAX      DisplayString
    MAX-ACCESS  read-write
    STATUS      current
    DESCRIPTION
	"The fifteenth output name of slave 4"
    ::= { slaveFourOutputName 15}
slaveFourOutputNameSixteen OBJECT-TYPE
    SYNTAX      DisplayString
    MAX-ACCESS  read-write
    STATUS      current
    DESCRIPTION
	"The sixteenth output name of slave 4"
    ::= { slaveFourOutputName 16}
slaveFourOutputNameSeventeen OBJECT-TYPE
    SYNTAX      DisplayString
    MAX-ACCESS  read-write
    STATUS      current
    DESCRIPTION
	"The seventeenth output name of slave 4"
    ::= { slaveFourOutputName 17}
slaveFourOutputNameEighteen OBJECT-TYPE
    SYNTAX      DisplayString
    MAX-ACCESS  read-write
    STATUS      current
    DESCRIPTION
	"The eighteenh output name of slave 4"
    ::= { slaveFourOutputName 18}
slaveFourOutputNameNineteen OBJECT-TYPE
    SYNTAX      DisplayString
    MAX-ACCESS  read-write
    STATUS      current
    DESCRIPTION
	"The nineteenth output name of slave 4"
    ::= { slaveFourOutputName 19}
slaveFourOutputNameTwenty OBJECT-TYPE
    SYNTAX      DisplayString
    MAX-ACCESS  read-write
    STATUS      current
    DESCRIPTION
	"The twentieth output name of slave 4"
    ::= { slaveFourOutputName 20}
slaveFourOutputNameTwentyOne OBJECT-TYPE
    SYNTAX      DisplayString
    MAX-ACCESS  read-write
    STATUS      current
    DESCRIPTION
	"The twenty-first output name of slave 4"
    ::= { slaveFourOutputName 21}
slaveFourOutputNameTwentyTwo OBJECT-TYPE
    SYNTAX      DisplayString
    MAX-ACCESS  read-write
    STATUS      current
    DESCRIPTION
	"The twenty-second output name of slave 4"
    ::= { slaveFourOutputName 22}
slaveFourOutputNameTwentyThree OBJECT-TYPE
    SYNTAX      DisplayString
    MAX-ACCESS  read-write
    STATUS      current
    DESCRIPTION
	"The twenty-third output name of slave 4"
    ::= { slaveFourOutputName 23}
slaveFourOutputNameTwentyFour OBJECT-TYPE
    SYNTAX      DisplayString
    MAX-ACCESS  read-write
    STATUS      current
    DESCRIPTION
	"The twenty-fourth output name of slave 4"
    ::= { slaveFourOutputName 24}


    
slaveFourOutputStatus OBJECT IDENTIFIER ::= { rpduSlaveFour 9}

slaveFourOutputStatusOne OBJECT-TYPE
    SYNTAX      DisplayString
    MAX-ACCESS  read-write
    STATUS      current
    DESCRIPTION
	"The first output status of slave 4"
    ::= { slaveFourOutputStatus 1}
slaveFourOutputStatusTwo OBJECT-TYPE
    SYNTAX      DisplayString
    MAX-ACCESS  read-write
    STATUS      current
    DESCRIPTION
	"The second output status of slave 4"
    ::= { slaveFourOutputStatus 2}

slaveFourOutputStatusThree OBJECT-TYPE
    SYNTAX      DisplayString
    MAX-ACCESS  read-write
    STATUS      current
    DESCRIPTION
	"The third output status of slave 4"
    ::= { slaveFourOutputStatus 3}
slaveFourOutputStatusFour OBJECT-TYPE
    SYNTAX      DisplayString
    MAX-ACCESS  read-write
    STATUS      current
    DESCRIPTION
	"The fourth output status of slave 4"
    ::= { slaveFourOutputStatus 4}
slaveFourOutputStatusFive OBJECT-TYPE
    SYNTAX      DisplayString
    MAX-ACCESS  read-write
    STATUS      current
    DESCRIPTION
	"The fifth output status of slave 4"
    ::= { slaveFourOutputStatus 5}
slaveFourOutputStatusSix OBJECT-TYPE
    SYNTAX      DisplayString
    MAX-ACCESS  read-write
    STATUS      current
    DESCRIPTION
	"The sixth output status of slave 4"
    ::= { slaveFourOutputStatus 6}
slaveFourOutputStatusSeven OBJECT-TYPE
    SYNTAX      DisplayString
    MAX-ACCESS  read-write
    STATUS      current
    DESCRIPTION
	"The seventh output status of slave 4"
    ::= { slaveFourOutputStatus 7}
slaveFourOutputStatusEight OBJECT-TYPE
    SYNTAX      DisplayString
    MAX-ACCESS  read-write
    STATUS      current
    DESCRIPTION
	"The eighth output status of slave 4"
    ::= { slaveFourOutputStatus 8}
slaveFourOutputStatusNine OBJECT-TYPE
    SYNTAX      DisplayString
    MAX-ACCESS  read-write
    STATUS      current
    DESCRIPTION
	"The nineth output status of slave 4"
    ::= { slaveFourOutputStatus 9}
slaveFourOutputStatusTen OBJECT-TYPE
    SYNTAX      DisplayString
    MAX-ACCESS  read-write
    STATUS      current
    DESCRIPTION
	"The tenth output status of slave 4"
    ::= { slaveFourOutputStatus 10}
slaveFourOutputStatusEleven OBJECT-TYPE
    SYNTAX      DisplayString
    MAX-ACCESS  read-write
    STATUS      current
    DESCRIPTION
	"The eleventh output status of slave 4"
    ::= { slaveFourOutputStatus 11}
slaveFourOutputStatusTwelve OBJECT-TYPE
    SYNTAX      DisplayString
    MAX-ACCESS  read-write
    STATUS      current
    DESCRIPTION
	"The twelfth output status of slave 4"
    ::= { slaveFourOutputStatus 12}
slaveFourOutputStatusThirteen OBJECT-TYPE
    SYNTAX      DisplayString
    MAX-ACCESS  read-write
    STATUS      current
    DESCRIPTION
	"The thirteenth output status of slave 4"
    ::= { slaveFourOutputStatus 13}
slaveFourOutputStatusFourteen OBJECT-TYPE
    SYNTAX      DisplayString
    MAX-ACCESS  read-write
    STATUS      current
    DESCRIPTION
	"The fourteenth output status of slave 4"
    ::= { slaveFourOutputStatus 14}
slaveFourOutputStatusFifteen OBJECT-TYPE
    SYNTAX      DisplayString
    MAX-ACCESS  read-write
    STATUS      current
    DESCRIPTION
	"The fifteenth output status of slave 4"
    ::= { slaveFourOutputStatus 15}
slaveFourOutputStatusSixteen OBJECT-TYPE
    SYNTAX      DisplayString
    MAX-ACCESS  read-write
    STATUS      current
    DESCRIPTION
	"The sixteenth output status of slave 4"
    ::= { slaveFourOutputStatus 16}
slaveFourOutputStatusSeventeen OBJECT-TYPE
    SYNTAX      DisplayString
    MAX-ACCESS  read-write
    STATUS      current
    DESCRIPTION
	"The seventeenth output status of slave 4"
    ::= { slaveFourOutputStatus 17}
slaveFourOutputStatusEighteen OBJECT-TYPE
    SYNTAX      DisplayString
    MAX-ACCESS  read-write
    STATUS      current
    DESCRIPTION
	"The eighteenth output status of slave 4"
    ::= { slaveFourOutputStatus 18}
slaveFourOutputStatusNineteen OBJECT-TYPE
    SYNTAX      DisplayString
    MAX-ACCESS  read-write
    STATUS      current
    DESCRIPTION
	"The nineteenth output status of slave 4"
    ::= { slaveFourOutputStatus 19}
slaveFourOutputStatusTwenty OBJECT-TYPE
    SYNTAX      DisplayString
    MAX-ACCESS  read-write
    STATUS      current
    DESCRIPTION
	"The twentieth output status of slave 4"
    ::= { slaveFourOutputStatus 20}
slaveFourOutputStatusTwentyOne OBJECT-TYPE
    SYNTAX      DisplayString
    MAX-ACCESS  read-write
    STATUS      current
    DESCRIPTION
	"The twenty-first output status of slave 4"
    ::= { slaveFourOutputStatus 21}
slaveFourOutputStatusTwentyTwo OBJECT-TYPE
    SYNTAX      DisplayString
    MAX-ACCESS  read-write
    STATUS      current
    DESCRIPTION
	"The twenty-second output status of slave 4"
    ::= { slaveFourOutputStatus 22}
slaveFourOutputStatusTwentyThree OBJECT-TYPE
    SYNTAX      DisplayString
    MAX-ACCESS  read-write
    STATUS      current
    DESCRIPTION
	"The twenty-third output status of slave 4"
    ::= { slaveFourOutputStatus 23}
slaveFourOutputStatusTwentyFour OBJECT-TYPE
    SYNTAX      DisplayString
    MAX-ACCESS  read-write
    STATUS      current
    DESCRIPTION
	"The twenty-fourth output status of slave 4"
    ::= { slaveFourOutputStatus 24}

slaveFourOutputCurrent   OBJECT IDENTIFIER ::= { rpduSlaveFour 10}
slaveFourOutputCurrentOne OBJECT-TYPE
    SYNTAX      DisplayString
    MAX-ACCESS  read-only
    STATUS      current
    DESCRIPTION
	"The current value of the first output of the slave 4"
    ::= { slaveFourOutputCurrent 1}
slaveFourOutputCurrentTwo OBJECT-TYPE
    SYNTAX      DisplayString
    MAX-ACCESS  read-only
    STATUS      current
    DESCRIPTION
	"The current value of the second output of the slave 4"
    ::= { slaveFourOutputCurrent 2}
slaveFourOutputCurrentThree OBJECT-TYPE
    SYNTAX      DisplayString
    MAX-ACCESS  read-only
    STATUS      current
    DESCRIPTION
	"The current value of the third output of the slave 4"
    ::= { slaveFourOutputCurrent 3}
slaveFourOutputCurrentFour OBJECT-TYPE
    SYNTAX      DisplayString
    MAX-ACCESS  read-only
    STATUS      current
    DESCRIPTION
	"The current value of the fourth output of the slave 4"
    ::= { slaveFourOutputCurrent 4}
slaveFourOutputCurrentFive OBJECT-TYPE
    SYNTAX      DisplayString
    MAX-ACCESS  read-only
    STATUS      current
    DESCRIPTION
	"The current value of the fifth output of the slave 4"
    ::= { slaveFourOutputCurrent 5}
slaveFourOutputCurrentSix OBJECT-TYPE
    SYNTAX      DisplayString
    MAX-ACCESS  read-only
    STATUS      current
    DESCRIPTION
	"The current value of the sixth output of the slave 4"
    ::= { slaveFourOutputCurrent 6}
slaveFourOutputCurrentSeven OBJECT-TYPE
    SYNTAX      DisplayString
    MAX-ACCESS  read-only
    STATUS      current
    DESCRIPTION
	"The current value of the seventh output of the slave 4"
    ::= { slaveFourOutputCurrent 7}
slaveFourOutputCurrentEight OBJECT-TYPE
    SYNTAX      DisplayString
    MAX-ACCESS  read-only
    STATUS      current
    DESCRIPTION
	"The current value of the eighth output of the slave 4"
    ::= { slaveFourOutputCurrent 8}
slaveFourOutputCurrentNine OBJECT-TYPE
    SYNTAX      DisplayString
    MAX-ACCESS  read-only
    STATUS      current
    DESCRIPTION
	"The current value of the nineth output of the slave 4"
    ::= { slaveFourOutputCurrent 9}
slaveFourOutputCurrentTen OBJECT-TYPE
    SYNTAX      DisplayString
    MAX-ACCESS  read-only
    STATUS      current
    DESCRIPTION
	"The current value of the tenth output of the slave 4"
    ::= { slaveFourOutputCurrent 10}
slaveFourOutputCurrentEleven OBJECT-TYPE
    SYNTAX      DisplayString
    MAX-ACCESS  read-only
    STATUS      current
    DESCRIPTION
	"The current value of the eleventh output of the slave 4"
    ::= { slaveFourOutputCurrent 11}
slaveFourOutputCurrentTwelve OBJECT-TYPE
    SYNTAX      DisplayString
    MAX-ACCESS  read-only
    STATUS      current
    DESCRIPTION
	"The current value of the twelfth output of the slave 4"
    ::= { slaveFourOutputCurrent 12}
slaveFourOutputCurrentThirteen OBJECT-TYPE
    SYNTAX      DisplayString
    MAX-ACCESS  read-only
    STATUS      current
    DESCRIPTION
	"The current value of the thirteenth output of the slave 4"
    ::= { slaveFourOutputCurrent 13}
slaveFourOutputCurrentFourteen OBJECT-TYPE
    SYNTAX      DisplayString
    MAX-ACCESS  read-only
    STATUS      current
    DESCRIPTION
	"The current value of the fourteenth output of the slave 4"
    ::= { slaveFourOutputCurrent 14}
slaveFourOutputCurrentFifteen OBJECT-TYPE
    SYNTAX      DisplayString
    MAX-ACCESS  read-only
    STATUS      current
    DESCRIPTION
	"The current value of the fifteenth output of the slave 4"
    ::= { slaveFourOutputCurrent 15}
slaveFourOutputCurrentSixteen OBJECT-TYPE
    SYNTAX      DisplayString
    MAX-ACCESS  read-only
    STATUS      current
    DESCRIPTION
	"The current value of the sixteenth output of the slave 4"
    ::= { slaveFourOutputCurrent 16}
slaveFourOutputCurrentSeventeen OBJECT-TYPE
    SYNTAX      DisplayString
    MAX-ACCESS  read-only
    STATUS      current
    DESCRIPTION
	"The current value of the seventeenth output of the slave 4"
    ::= { slaveFourOutputCurrent 17}
slaveFourOutputCurrentEighteen OBJECT-TYPE
    SYNTAX      DisplayString
    MAX-ACCESS  read-only
    STATUS      current
    DESCRIPTION
	"The current value of the eighteenth output of the slave 4"
    ::= { slaveFourOutputCurrent 18}
slaveFourOutputCurrentNineteen OBJECT-TYPE
    SYNTAX      DisplayString
    MAX-ACCESS  read-only
    STATUS      current
    DESCRIPTION
	"The current value of the nineteenth output of the slave 4"
    ::= { slaveFourOutputCurrent 19}
slaveFourOutputCurrentTwenty OBJECT-TYPE
    SYNTAX      DisplayString
    MAX-ACCESS  read-only
    STATUS      current
    DESCRIPTION
	"The current value of the twentieth output of the slave 4"
    ::= { slaveFourOutputCurrent 20}
slaveFourOutputCurrentTwentyOne OBJECT-TYPE
    SYNTAX      DisplayString
    MAX-ACCESS  read-only
    STATUS      current
    DESCRIPTION
	"The current value of the twenty-first output of the slave 4"
    ::= { slaveFourOutputCurrent 21}
slaveFourOutputCurrentTwentyTwo OBJECT-TYPE
    SYNTAX      DisplayString
    MAX-ACCESS  read-only
    STATUS      current
    DESCRIPTION
	"The current value of the twenty-second output of the slave 4"
    ::= { slaveFourOutputCurrent 22}
slaveFourOutputCurrentTwentyThree OBJECT-TYPE
    SYNTAX      DisplayString
    MAX-ACCESS  read-only
    STATUS      current
    DESCRIPTION
	"The current value of the twenty-third output of the slave 4"
    ::= { slaveFourOutputCurrent 23}
slaveFourOutputCurrentTwentyFour OBJECT-TYPE
    SYNTAX      DisplayString
    MAX-ACCESS  read-only
    STATUS      current
    DESCRIPTION
	"The current value of the twenty-fourth output of the slave 4"
    ::= { slaveFourOutputCurrent 24}

slaveFourOutputCurrentMin   OBJECT IDENTIFIER ::= { rpduSlaveFour 11}
slaveFourOutputCurrentMinOne OBJECT-TYPE
    SYNTAX      DisplayString
    MAX-ACCESS  read-only
    STATUS      current
    DESCRIPTION
	"The Min. current value of the first output of the slave 4"
    ::= { slaveFourOutputCurrentMin 1}
slaveFourOutputCurrentMinTwo OBJECT-TYPE
    SYNTAX      DisplayString
    MAX-ACCESS  read-only
    STATUS      current
    DESCRIPTION
	"The Min. current value of the second output of the slave 4"
    ::= { slaveFourOutputCurrentMin 2}
slaveFourOutputCurrentMinThree OBJECT-TYPE
    SYNTAX      DisplayString
    MAX-ACCESS  read-only
    STATUS      current
    DESCRIPTION
	"The Min. current value of the third output of the slave 4"
    ::= { slaveFourOutputCurrentMin 3}
slaveFourOutputCurrentMinFour OBJECT-TYPE
    SYNTAX      DisplayString
    MAX-ACCESS  read-only
    STATUS      current
    DESCRIPTION
	"The Min. current value of the fourth output of the slave 4"
    ::= { slaveFourOutputCurrentMin 4}
slaveFourOutputCurrentMinFive OBJECT-TYPE
    SYNTAX      DisplayString
    MAX-ACCESS  read-only
    STATUS      current
    DESCRIPTION
	"The Min. current value of the fifth output of the slave 4"
    ::= { slaveFourOutputCurrentMin 5}
slaveFourOutputCurrentMinSix OBJECT-TYPE
    SYNTAX      DisplayString
    MAX-ACCESS  read-only
    STATUS      current
    DESCRIPTION
	"The Min. current value of the sixth output of the slave 4"
    ::= { slaveFourOutputCurrentMin 6}
slaveFourOutputCurrentMinSeven OBJECT-TYPE
    SYNTAX      DisplayString
    MAX-ACCESS  read-only
    STATUS      current
    DESCRIPTION
	"The Min. current value of the seventh output of the slave 4"
    ::= { slaveFourOutputCurrentMin 7}
slaveFourOutputCurrentMinEight OBJECT-TYPE
    SYNTAX      DisplayString
    MAX-ACCESS  read-only
    STATUS      current
    DESCRIPTION
	"The Min. current value of the eighth output of the slave 4"
    ::= { slaveFourOutputCurrentMin 8}
slaveFourOutputCurrentMinNine OBJECT-TYPE
    SYNTAX      DisplayString
    MAX-ACCESS  read-only
    STATUS      current
    DESCRIPTION
	"The Min. current value of the nineth output of the slave 4"
    ::= { slaveFourOutputCurrentMin 9}
slaveFourOutputCurrentMinTen OBJECT-TYPE
    SYNTAX      DisplayString
    MAX-ACCESS  read-only
    STATUS      current
    DESCRIPTION
	"The Min. current value of the tenth output of the slave 4"
    ::= { slaveFourOutputCurrentMin 10}
slaveFourOutputCurrentMinEleven OBJECT-TYPE
    SYNTAX      DisplayString
    MAX-ACCESS  read-only
    STATUS      current
    DESCRIPTION
	"The Min. current value of the eleventh output of the slave 4"
    ::= { slaveFourOutputCurrentMin 11}
slaveFourOutputCurrentMinTwleve OBJECT-TYPE
    SYNTAX      DisplayString
    MAX-ACCESS  read-only
    STATUS      current
    DESCRIPTION
	"The Min. current value of the twelfth output of the slave 4"
    ::= { slaveFourOutputCurrentMin 12}
slaveFourOutputCurrentMinThirteen OBJECT-TYPE
    SYNTAX      DisplayString
    MAX-ACCESS  read-only
    STATUS      current
    DESCRIPTION
	"The Min. current value of the thirteenth output of the slave 4"
    ::= { slaveFourOutputCurrentMin 13}
slaveFourOutputCurrentMinFourteen OBJECT-TYPE
    SYNTAX      DisplayString
    MAX-ACCESS  read-only
    STATUS      current
    DESCRIPTION
	"The Min. current value of the fourteenth output of the slave 4"
    ::= { slaveFourOutputCurrentMin 14}
slaveFourOutputCurrentMinFifteen OBJECT-TYPE
    SYNTAX      DisplayString
    MAX-ACCESS  read-only
    STATUS      current
    DESCRIPTION
	"The Min. current value of the fifteenth output of the slave 4"
    ::= { slaveFourOutputCurrentMin 15}
slaveFourOutputCurrentMinSixteen OBJECT-TYPE
    SYNTAX      DisplayString
    MAX-ACCESS  read-only
    STATUS      current
    DESCRIPTION
	"The Min. current value of the sixteenth output of the slave 4"
    ::= { slaveFourOutputCurrentMin 16}
slaveFourOutputCurrentMinSeventeen OBJECT-TYPE
    SYNTAX      DisplayString
    MAX-ACCESS  read-only
    STATUS      current
    DESCRIPTION
	"The Min. current value of the seventeenth output of the slave 4"
    ::= { slaveFourOutputCurrentMin 17}
slaveFourOutputCurrentMinEighteen OBJECT-TYPE
    SYNTAX      DisplayString
    MAX-ACCESS  read-only
    STATUS      current
    DESCRIPTION
	"The Min. current value of the eighteenth output of the slave 4"
    ::= { slaveFourOutputCurrentMin 18}
slaveFourOutputCurrentMinNineteen OBJECT-TYPE
    SYNTAX      DisplayString
    MAX-ACCESS  read-only
    STATUS      current
    DESCRIPTION
	"The Min. current value of the nineteenth output of the slave 4"
    ::= { slaveFourOutputCurrentMin 19}
slaveFourOutputCurrentMinTwenty OBJECT-TYPE
    SYNTAX      DisplayString
    MAX-ACCESS  read-only
    STATUS      current
    DESCRIPTION
	"The Min. current value of the twentieth output of the slave 4"
    ::= { slaveFourOutputCurrentMin 20}
slaveFourOutputCurrentMinTwentyOne OBJECT-TYPE
    SYNTAX      DisplayString
    MAX-ACCESS  read-only
    STATUS      current
    DESCRIPTION
	"The Min. current value of the twentyth-first output of the slave 4"
    ::= { slaveFourOutputCurrentMin 21}
slaveFourOutputCurrentMinTwentyTwo OBJECT-TYPE
    SYNTAX      DisplayString
    MAX-ACCESS  read-only
    STATUS      current
    DESCRIPTION
	"The Min. current value of the twentyth-second output of the slave 4"
    ::= { slaveFourOutputCurrentMin 22}
slaveFourOutputCurrentMinTwentyThree OBJECT-TYPE
    SYNTAX      DisplayString
    MAX-ACCESS  read-only
    STATUS      current
    DESCRIPTION
	"The Min. current value of the twentyth-third output of the slave 4"
    ::= { slaveFourOutputCurrentMin 23}
slaveFourOutputCurrentMinTwentyFour OBJECT-TYPE
    SYNTAX      DisplayString
    MAX-ACCESS  read-only
    STATUS      current
    DESCRIPTION
	"The Min. current value of the twentyth-fourth output of the slave 4"
    ::= { slaveFourOutputCurrentMin 24}




slaveFourOutputCurrentMax   OBJECT IDENTIFIER ::= { rpduSlaveFour 12}
slaveFourOutputCurrentMaxOne OBJECT-TYPE
    SYNTAX      DisplayString
    MAX-ACCESS  read-only
    STATUS      current
    DESCRIPTION
	"The Max. current value of the first output of the slave 4"
    ::= { slaveFourOutputCurrentMax 1}
slaveFourOutputCurrentMaxTwo OBJECT-TYPE
    SYNTAX      DisplayString
    MAX-ACCESS  read-only
    STATUS      current
    DESCRIPTION
	"The Max. current value of the second output of the slave 4"
    ::= { slaveFourOutputCurrentMax 2}
slaveFourOutputCurrentMaxThree OBJECT-TYPE
    SYNTAX      DisplayString
    MAX-ACCESS  read-only
    STATUS      current
    DESCRIPTION
	"The Max. current value of the third output of the slave 4"
    ::= { slaveFourOutputCurrentMax 3}
slaveFourOutputCurrentMaxFour OBJECT-TYPE
    SYNTAX      DisplayString
    MAX-ACCESS  read-only
    STATUS      current
    DESCRIPTION
	"The Max. current value of the fourth output of the slave 4"
    ::= { slaveFourOutputCurrentMax 4}
slaveFourOutputCurrentMaxFive OBJECT-TYPE
    SYNTAX      DisplayString
    MAX-ACCESS  read-only
    STATUS      current
    DESCRIPTION
	"The Max. current value of the fifth output of the slave 4"
    ::= { slaveFourOutputCurrentMax 5}
slaveFourOutputCurrentMaxSix OBJECT-TYPE
    SYNTAX      DisplayString
    MAX-ACCESS  read-only
    STATUS      current
    DESCRIPTION
	"The Max. current value of the sixth output of the slave 4"
    ::= { slaveFourOutputCurrentMax 6}
slaveFourOutputCurrentMaxSeven OBJECT-TYPE
    SYNTAX      DisplayString
    MAX-ACCESS  read-only
    STATUS      current
    DESCRIPTION
	"The Max. current value of the seventh output of the slave 4"
    ::= { slaveFourOutputCurrentMax 7}
slaveFourOutputCurrentMaxEight OBJECT-TYPE
    SYNTAX      DisplayString
    MAX-ACCESS  read-only
    STATUS      current
    DESCRIPTION
	"The Max. current value of the eighth output of the slave 4"
    ::= { slaveFourOutputCurrentMax 8}
slaveFourOutputCurrentMaxNine OBJECT-TYPE
    SYNTAX      DisplayString
    MAX-ACCESS  read-only
    STATUS      current
    DESCRIPTION
	"The Max. current value of the nineth output of the slave 4"
    ::= { slaveFourOutputCurrentMax 9}
slaveFourOutputCurrentMaxTen OBJECT-TYPE
    SYNTAX      DisplayString
    MAX-ACCESS  read-only
    STATUS      current
    DESCRIPTION
	"The Max. current value of the tenth output of the slave 4"
    ::= { slaveFourOutputCurrentMax 10}
slaveFourOutputCurrentMaxEleven OBJECT-TYPE
    SYNTAX      DisplayString
    MAX-ACCESS  read-only
    STATUS      current
    DESCRIPTION
	"The Max. current value of the eleventh output of the slave 4"
    ::= { slaveFourOutputCurrentMax 11}
slaveFourOutputCurrentMaxTwleve OBJECT-TYPE
    SYNTAX      DisplayString
    MAX-ACCESS  read-only
    STATUS      current
    DESCRIPTION
	"The Max. current value of the twelfth output of the slave 4"
    ::= { slaveFourOutputCurrentMax 12}
slaveFourOutputCurrentMaxThirteen OBJECT-TYPE
    SYNTAX      DisplayString
    MAX-ACCESS  read-only
    STATUS      current
    DESCRIPTION
	"The Max. current value of the thirteenth output of the slave 4"
    ::= { slaveFourOutputCurrentMax 13}
slaveFourOutputCurrentMaxFourteen OBJECT-TYPE
    SYNTAX      DisplayString
    MAX-ACCESS  read-only
    STATUS      current
    DESCRIPTION
	"The Max. current value of the fourteenth output of the slave 4"
    ::= { slaveFourOutputCurrentMax 14}
slaveFourOutputCurrentMaxFifteen OBJECT-TYPE
    SYNTAX      DisplayString
    MAX-ACCESS  read-only
    STATUS      current
    DESCRIPTION
	"The Max. current value of the fifteenth output of the slave 4"
    ::= { slaveFourOutputCurrentMax 15}
slaveFourOutputCurrentMaxSixteen OBJECT-TYPE
    SYNTAX      DisplayString
    MAX-ACCESS  read-only
    STATUS      current
    DESCRIPTION
	"The Max. current value of the sixteenth output of the slave 4"
    ::= { slaveFourOutputCurrentMax 16}
slaveFourOutputCurrentMaxSeventeen OBJECT-TYPE
    SYNTAX      DisplayString
    MAX-ACCESS  read-only
    STATUS      current
    DESCRIPTION
	"The Max. current value of the seventeenth output of the slave 4"
    ::= { slaveFourOutputCurrentMax 17}
slaveFourOutputCurrentMaxEighteen OBJECT-TYPE
    SYNTAX      DisplayString
    MAX-ACCESS  read-only
    STATUS      current
    DESCRIPTION
	"The Max. current value of the eighteenth output of the slave 4"
    ::= { slaveFourOutputCurrentMax 18}
slaveFourOutputCurrentMaxNineteen OBJECT-TYPE
    SYNTAX      DisplayString
    MAX-ACCESS  read-only
    STATUS      current
    DESCRIPTION
	"The Max. current value of the nineteenth output of the slave 4"
    ::= { slaveFourOutputCurrentMax 19}
slaveFourOutputCurrentMaxTwenty OBJECT-TYPE
    SYNTAX      DisplayString
    MAX-ACCESS  read-only
    STATUS      current
    DESCRIPTION
	"The Max. current value of the twentieth output of the slave 4"
    ::= { slaveFourOutputCurrentMax 20}
slaveFourOutputCurrentMaxTwentyOne OBJECT-TYPE
    SYNTAX      DisplayString
    MAX-ACCESS  read-only
    STATUS      current
    DESCRIPTION
	"The Max. current value of the twenty-first output of the slave 4"
    ::= { slaveFourOutputCurrentMax 21}
slaveFourOutputCurrentMaxTwentyTwo OBJECT-TYPE
    SYNTAX      DisplayString
    MAX-ACCESS  read-only
    STATUS      current
    DESCRIPTION
	"The Max. current value of the twenty-second output of the slave 4"
    ::= { slaveFourOutputCurrentMax 22}
slaveFourOutputCurrentMaxTwentyThree OBJECT-TYPE
    SYNTAX      DisplayString
    MAX-ACCESS  read-only
    STATUS      current
    DESCRIPTION
	"The Max. current value of the twenty-third output of the slave 4"
    ::= { slaveFourOutputCurrentMax 23}
slaveFourOutputCurrentMaxTwentyFour OBJECT-TYPE
    SYNTAX      DisplayString
    MAX-ACCESS  read-only
    STATUS      current
    DESCRIPTION
	"The Max. current value of the twenty-fourth output of the slave 4"
    ::= { slaveFourOutputCurrentMax 24}


slaveFourOutputCurrentEnergy  OBJECT IDENTIFIER ::= { rpduSlaveFour 13}
slaveFourOutputCurrentEnergyOne OBJECT-TYPE
    SYNTAX	DisplayString
    MAX-ACCESS	read-only
    STATUS	current
    DESCRIPTION
	"The energy value of the first output of the slave 4"
    ::={slaveFourOutputCurrentEnergy 1}
slaveFourOutputCurrentEnergyTwo OBJECT-TYPE
    SYNTAX	DisplayString
    MAX-ACCESS	read-only
    STATUS	current
    DESCRIPTION
	"The energy value of the second output of the slave 4"
    ::={slaveFourOutputCurrentEnergy 2}
slaveFourOutputCurrentEnergyThree OBJECT-TYPE
    SYNTAX	DisplayString
    MAX-ACCESS	read-only
    STATUS	current
    DESCRIPTION
	"The energy value of the third output of the slave 4"
    ::={slaveFourOutputCurrentEnergy 3}
slaveFourOutputCurrentEnergyFour OBJECT-TYPE
    SYNTAX	DisplayString
    MAX-ACCESS	read-only
    STATUS	current
    DESCRIPTION
	"The energy value of the fourth output of the slave 4"
    ::={slaveFourOutputCurrentEnergy 4}
slaveFourOutputCurrentEnergyFive OBJECT-TYPE
    SYNTAX	DisplayString
    MAX-ACCESS	read-only
    STATUS	current
    DESCRIPTION
	"The energy value of the fifth output of the slave 4"
    ::={slaveFourOutputCurrentEnergy 5}
slaveFourOutputCurrentEnergySix OBJECT-TYPE
    SYNTAX	DisplayString
    MAX-ACCESS	read-only
    STATUS	current
    DESCRIPTION
	"The energy value of the sixth output of the slave 4"
    ::={slaveFourOutputCurrentEnergy 6}
slaveFourOutputCurrentEnergySeven OBJECT-TYPE
    SYNTAX	DisplayString
    MAX-ACCESS	read-only
    STATUS	current
    DESCRIPTION
	"The energy value of the seventh output of the slave 4"
    ::={slaveFourOutputCurrentEnergy 7}
slaveFourOutputCurrentEnergyEight OBJECT-TYPE
    SYNTAX	DisplayString
    MAX-ACCESS	read-only
    STATUS	current
    DESCRIPTION
	"The energy value of the eighth output of the slave 4"
    ::={slaveFourOutputCurrentEnergy 8}
slaveFourOutputCurrentEnergyNine OBJECT-TYPE
    SYNTAX	DisplayString
    MAX-ACCESS	read-only
    STATUS	current
    DESCRIPTION
	"The energy value of the nineth output of the slave 4"
    ::={slaveFourOutputCurrentEnergy 9}
slaveFourOutputCurrentEnergyTen OBJECT-TYPE
    SYNTAX	DisplayString
    MAX-ACCESS	read-only
    STATUS	current
    DESCRIPTION
	"The energy value of the tenth output of the slave 4"
    ::={slaveFourOutputCurrentEnergy 10}
slaveFourOutputCurrentEnergyEleven OBJECT-TYPE
    SYNTAX	DisplayString
    MAX-ACCESS	read-only
    STATUS	current
    DESCRIPTION
	"The energy value of the eleventh output of the slave 4"
    ::={slaveFourOutputCurrentEnergy 11}
slaveFourOutputCurrentEnergyTwelve OBJECT-TYPE
    SYNTAX	DisplayString
    MAX-ACCESS	read-only
    STATUS	current
    DESCRIPTION
	"The energy value of the twelfth output of the slave 4"
    ::={slaveFourOutputCurrentEnergy 12}
slaveFourOutputCurrentEnergyThirteen OBJECT-TYPE
    SYNTAX	DisplayString
    MAX-ACCESS	read-only
    STATUS	current
    DESCRIPTION
	"The energy value of the thirteenth output of the slave 4"
    ::={slaveFourOutputCurrentEnergy 13}
slaveFourOutputCurrentEnergyFourteen OBJECT-TYPE
    SYNTAX	DisplayString
    MAX-ACCESS	read-only
    STATUS	current
    DESCRIPTION
	"The energy value of the fourteenth output of the slave 4"
    ::={slaveFourOutputCurrentEnergy 14}
slaveFourOutputCurrentEnergyFifteen OBJECT-TYPE
    SYNTAX	DisplayString
    MAX-ACCESS	read-only
    STATUS	current
    DESCRIPTION
	"The energy value of the fifteenth output of the slave 4"
    ::={slaveFourOutputCurrentEnergy 15}
slaveFourOutputCurrentEnergySixteen OBJECT-TYPE
    SYNTAX	DisplayString
    MAX-ACCESS	read-only
    STATUS	current
    DESCRIPTION
	"The energy value of the sixteenth output of the slave 4"
    ::={slaveFourOutputCurrentEnergy 16}
slaveFourOutputCurrentEnergySeventeen OBJECT-TYPE
    SYNTAX	DisplayString
    MAX-ACCESS	read-only
    STATUS	current
    DESCRIPTION
	"The energy value of the seventeenth output of the slave 4"
    ::={slaveFourOutputCurrentEnergy 17}
slaveFourOutputCurrentEnergyEighteen OBJECT-TYPE
    SYNTAX	DisplayString
    MAX-ACCESS	read-only
    STATUS	current
    DESCRIPTION
	"The energy value of the eighteenth output of the slave 4"
    ::={slaveFourOutputCurrentEnergy 18}
slaveFourOutputCurrentEnergyNineteen OBJECT-TYPE
    SYNTAX	DisplayString
    MAX-ACCESS	read-only
    STATUS	current
    DESCRIPTION
	"The energy value of the nineteenth output of the slave 4"
    ::={slaveFourOutputCurrentEnergy 19}
slaveFourOutputCurrentEnergyTwenty OBJECT-TYPE
    SYNTAX	DisplayString
    MAX-ACCESS	read-only
    STATUS	current
    DESCRIPTION
	"The energy value of the twentieth output of the slave 4"
    ::={slaveFourOutputCurrentEnergy 20}
slaveFourOutputCurrentEnergyTwentyOne OBJECT-TYPE
    SYNTAX	DisplayString
    MAX-ACCESS	read-only
    STATUS	current
    DESCRIPTION
	"The energy value of the twenty-first output of the slave 4"
    ::={slaveFourOutputCurrentEnergy 21}
slaveFourOutputCurrentEnergyTwentyTwo OBJECT-TYPE
    SYNTAX	DisplayString
    MAX-ACCESS	read-only
    STATUS	current
    DESCRIPTION
	"The energy value of the twenty-second output of the slave 4"
    ::={slaveFourOutputCurrentEnergy 22}
slaveFourOutputCurrentEnergyTwentyThree OBJECT-TYPE
    SYNTAX	DisplayString
    MAX-ACCESS	read-only
    STATUS	current
    DESCRIPTION
	"The energy value of the twenty-third output of the slave 4"
    ::={slaveFourOutputCurrentEnergy 23}
slaveFourOutputCurrentEnergyTwentyFour OBJECT-TYPE
    SYNTAX	DisplayString
    MAX-ACCESS	read-only
    STATUS	current
    DESCRIPTION
	"The energy value of the twenty-fourth output of the slave 4"
    ::={slaveFourOutputCurrentEnergy 24}

-------------------------------Slave5--------------------------------------------- 
rpduDeviceSix OBJECT IDENTIFIER ::= { rpdu 6}
rpduSlaveFive OBJECT IDENTIFIER ::= { rpduDeviceSix 1}

slaveFiveName OBJECT-TYPE
    SYNTAX      DisplayString
    MAX-ACCESS  read-write
    STATUS      current
    DESCRIPTION
	"This is the sixth device."
    ::= { rpduSlaveFive 1}
    
slaveFiveType OBJECT-TYPE
    SYNTAX      DisplayString
    MAX-ACCESS  read-only
    STATUS      current
    DESCRIPTION
	"This is device type "
    ::= { rpduSlaveFive 2}
    
slaveFiveOutputNumber OBJECT-TYPE 
    SYNTAX      Integer32
    MAX-ACCESS  read-only
    STATUS      current
    DESCRIPTION
	"This is the output quantity"
::= { rpduSlaveFive 7}
    
slaveFiveLineOne OBJECT IDENTIFIER ::= { rpduSlaveFive 3}
slaveFiveLineOnePower OBJECT-TYPE
    SYNTAX      DisplayString
    MAX-ACCESS  read-only
    STATUS      current
    DESCRIPTION
	"The power of phase one"
    ::= { slaveFiveLineOne 1}
slaveFiveLineOnePF OBJECT-TYPE
    SYNTAX      DisplayString
    MAX-ACCESS  read-only
    STATUS      current
    DESCRIPTION
	"The power factor of phase one"
    ::= { slaveFiveLineOne 2}
    
slaveFiveLineOneEnergy OBJECT-TYPE
    SYNTAX      DisplayString
    MAX-ACCESS  read-only
    STATUS      current
    DESCRIPTION
	"The energy of phase one"
    ::= { slaveFiveLineOne 3}
slaveFiveLineOneCurrent OBJECT-TYPE
    SYNTAX      DisplayString
    MAX-ACCESS  read-only
    STATUS      current
    DESCRIPTION
	"The current of phase one"
    ::= { slaveFiveLineOne 4}
slaveFiveLineOneVoltage OBJECT-TYPE
    SYNTAX      Integer32
    MAX-ACCESS  read-only
    STATUS      current
    DESCRIPTION
	"The voltage of phase one"
    ::= { slaveFiveLineOne 5}
slaveFiveLineOneCurrentMin OBJECT-TYPE
    SYNTAX      DisplayString
    MAX-ACCESS  read-only
    STATUS      current
    DESCRIPTION
	"The Min. current value of phase one"
	::= { slaveFiveLineOne 6}
slaveFiveLineOneCurrentMax OBJECT-TYPE
    SYNTAX      DisplayString
    MAX-ACCESS  read-only
    STATUS      current
    DESCRIPTION
	"The Max. current value of phase one"
    ::= { slaveFiveLineOne 7}
    
slaveFiveLineOneVoltageMin OBJECT-TYPE
    SYNTAX      Integer32
    MAX-ACCESS  read-only
    STATUS      current
    DESCRIPTION
	"The Min. voltage value of phase one"
    ::= { slaveFiveLineOne 8}
    
slaveFiveLineOneVoltageMax OBJECT-TYPE
    SYNTAX      Integer32
    MAX-ACCESS  read-only
    STATUS      current
    DESCRIPTION
	"The Max. voltage value of phase one"
    ::= { slaveFiveLineOne 9}


slaveFiveLineTwo OBJECT IDENTIFIER ::= { rpduSlaveFive 4}
slaveFiveLineTwoPower OBJECT-TYPE
    SYNTAX      DisplayString
    MAX-ACCESS  read-only
    STATUS      current
    DESCRIPTION
	"The power of phase two"
    ::= { slaveFiveLineTwo 1}

slaveFiveLineTwoPF OBJECT-TYPE
    SYNTAX      DisplayString
    MAX-ACCESS  read-only
    STATUS      current
    DESCRIPTION
	"The power factor of phase two"   
    ::= { slaveFiveLineTwo 2}
    
slaveFiveLineTwoEnergy OBJECT-TYPE
    SYNTAX      DisplayString
    MAX-ACCESS  read-only
    STATUS      current
    DESCRIPTION
	"The energy of phase two"
    ::= { slaveFiveLineTwo 3}
slaveFiveLineTwoCurrent OBJECT-TYPE           
    SYNTAX      DisplayString 
    MAX-ACCESS  read-only
    STATUS      current
    DESCRIPTION
	"The current of phase two"
    ::= { slaveFiveLineTwo 4}
slaveFiveLineTwoVoltage OBJECT-TYPE
    SYNTAX      Integer32
    MAX-ACCESS  read-only
    STATUS      current
    DESCRIPTION
	"The voltage of phase two"
    ::= { slaveFiveLineTwo 5}
slaveFiveLineTwoCurrentMin OBJECT-TYPE
    SYNTAX      DisplayString
    MAX-ACCESS  read-only
    STATUS      current
    DESCRIPTION
	"The Min. current value of phase two"
    ::= { slaveFiveLineTwo 6}
slaveFiveLineTwoCurrentMax OBJECT-TYPE
    SYNTAX      DisplayString
    MAX-ACCESS  read-only
    STATUS      current
    DESCRIPTION
	"The Max. current value of phase two"
    ::= { slaveFiveLineTwo 7}
    
slaveFiveLineTwoVoltageMin OBJECT-TYPE
    SYNTAX      Integer32
    MAX-ACCESS  read-only
    STATUS      current
    DESCRIPTION
	"The Min. voltage value of phase two"
    ::= { slaveFiveLineTwo 8}
    
slaveFiveLineTwoVoltageMax OBJECT-TYPE
    SYNTAX      Integer32
    MAX-ACCESS  read-only
    STATUS      current
    DESCRIPTION
	"The Max. voltage value of phase two"
    ::= { slaveFiveLineTwo 9}



slaveFiveLineThree OBJECT IDENTIFIER ::= { rpduSlaveFive 5}
slaveFiveLineThreePower OBJECT-TYPE
    SYNTAX      DisplayString
    MAX-ACCESS  read-only
    STATUS      current
    DESCRIPTION
	"The power of phase three"
    ::= { slaveFiveLineThree 1}

slaveFiveLineThreePF OBJECT-TYPE
    SYNTAX      DisplayString
    MAX-ACCESS  read-only
    STATUS      current
    DESCRIPTION
	"The power factor of phase three"     
    ::= { slaveFiveLineThree 2}
    
slaveFiveLineThreeEnergy OBJECT-TYPE
    SYNTAX      DisplayString
    MAX-ACCESS  read-only
    STATUS      current
    DESCRIPTION
	"The energy of phase three"
    ::= { slaveFiveLineThree 3}
slaveFiveLineThreeCurrent OBJECT-TYPE
    SYNTAX      DisplayString
    MAX-ACCESS  read-only
    STATUS      current
    DESCRIPTION
	"The current of phase three"
    ::= { slaveFiveLineThree 4}
slaveFiveLineThreeVoltage OBJECT-TYPE
    SYNTAX      Integer32
    MAX-ACCESS  read-only
    STATUS      current
    DESCRIPTION
	"The voltage of phase three"
    ::= { slaveFiveLineThree 5}
slaveFiveLineThreeCurrentMin OBJECT-TYPE
    SYNTAX      DisplayString
    MAX-ACCESS  read-only
    STATUS      current
    DESCRIPTION
	"The Min. current value of phase three"
    ::= { slaveFiveLineThree 6}
slaveFiveLineThreeCurrentMax OBJECT-TYPE
    SYNTAX      DisplayString
    MAX-ACCESS  read-only
    STATUS      current
    DESCRIPTION
	"The Max. current value of phase three"
    ::= { slaveFiveLineThree 7}
    
slaveFiveLineThreeVoltageMin OBJECT-TYPE
    SYNTAX      Integer32
    MAX-ACCESS  read-only
    STATUS      current
    DESCRIPTION
	"The Min. voltage value of phase three"
    ::= { slaveFiveLineThree 8}
    
slaveFiveLineThreeVoltageMax OBJECT-TYPE
    SYNTAX      Integer32
    MAX-ACCESS  read-only
    STATUS      current
    DESCRIPTION
	"The Max. voltage value of phase three"
    ::= { slaveFiveLineThree 9}


slaveFiveSensor OBJECT IDENTIFIER ::= { rpduSlaveFive 6}
slaveFiveTempOne OBJECT-TYPE
    SYNTAX      Integer32
    MAX-ACCESS  read-only
    STATUS      current
    DESCRIPTION
	"The first temperature sensor of slave 5"
    ::= { slaveFiveSensor 1}
slaveFiveTempTwo OBJECT-TYPE
    SYNTAX      Integer32
    MAX-ACCESS  read-only
    STATUS      current
    DESCRIPTION
	"The second temperature sensor of slave 5"
    ::= { slaveFiveSensor 2}
slaveFiveTempThree OBJECT-TYPE
    SYNTAX      Integer32
    MAX-ACCESS  read-only
    STATUS      current
    DESCRIPTION
	"The third temperature sensor of slave 5"
    ::= { slaveFiveSensor 3}
slaveFiveTempFour OBJECT-TYPE
    SYNTAX      Integer32
    MAX-ACCESS  read-only
    STATUS      current
    DESCRIPTION
	"The fourth temperature sensor of slave 5"
    ::= { slaveFiveSensor 4}
slaveFiveHumOne OBJECT-TYPE
    SYNTAX      Integer32
    MAX-ACCESS  read-only
    STATUS      current
    DESCRIPTION
	"The first humidity sensor of slave 5"
    ::= { slaveFiveSensor 5}
slaveFiveHumTwo OBJECT-TYPE
    SYNTAX      Integer32
    MAX-ACCESS  read-only
    STATUS      current
    DESCRIPTION
	"The second humidity sensor of slave 5"
    ::= { slaveFiveSensor 6}
slaveFiveHumThree OBJECT-TYPE
    SYNTAX      Integer32
    MAX-ACCESS  read-only
    STATUS      current
    DESCRIPTION
	"The third humidity sensor of slave 5"
    ::= { slaveFiveSensor 7}
slaveFiveHumFour OBJECT-TYPE
    SYNTAX      Integer32
    MAX-ACCESS  read-only
    STATUS      current
    DESCRIPTION
	"The fourth humidity sensor of slave 5"
    ::= { slaveFiveSensor 8}
slaveFiveDoorOne OBJECT-TYPE
    SYNTAX      DisplayString
    MAX-ACCESS  read-only
    STATUS      current
    DESCRIPTION
	"The first door sensor of slave 5"    
    ::= { slaveFiveSensor 9}
slaveFiveDoorTwo OBJECT-TYPE
    SYNTAX      DisplayString
    MAX-ACCESS  read-only
    STATUS      current
    DESCRIPTION
	"The second door sensor of slave 5"  
    ::= { slaveFiveSensor 10}
slaveFiveSmoke OBJECT-TYPE
    SYNTAX      DisplayString
    MAX-ACCESS  read-only
    STATUS      current
    DESCRIPTION
	"The smoke sensor of slave 5"
    ::= { slaveFiveSensor 11}
slaveFiveWater OBJECT-TYPE
    SYNTAX      DisplayString
    MAX-ACCESS  read-only
    STATUS      current
    DESCRIPTION
	"The water sensor of slave 5"
    ::= { slaveFiveSensor 12}


	
        
slaveFiveOutputName OBJECT IDENTIFIER ::= { rpduSlaveFive 8}
slaveFiveOutputNameOne OBJECT-TYPE
    SYNTAX      DisplayString
    MAX-ACCESS  read-write
    STATUS      current
    DESCRIPTION
	"The first output name of slave 5"
    ::= { slaveFiveOutputName 1}

slaveFiveOutputNameTwo OBJECT-TYPE
    SYNTAX      DisplayString
    MAX-ACCESS  read-write
    STATUS      current
    DESCRIPTION
	"The second output name of slave 5"
    ::= { slaveFiveOutputName 2}
slaveFiveOutputNameThree OBJECT-TYPE
    SYNTAX      DisplayString
    MAX-ACCESS  read-write
    STATUS      current
    DESCRIPTION
	"The third output name of slave 5"
    ::= { slaveFiveOutputName 3}
slaveFiveOutputNameFour OBJECT-TYPE
    SYNTAX      DisplayString
    MAX-ACCESS  read-write
    STATUS      current
    DESCRIPTION
	"The fourth output name of slave 5"
    ::= { slaveFiveOutputName 4}
slaveFiveOutputNameFive OBJECT-TYPE
    SYNTAX      DisplayString
    MAX-ACCESS  read-write
    STATUS      current
    DESCRIPTION
	"The fifth output name of slave 5"
    ::= { slaveFiveOutputName 5}
slaveFiveOutputNameSix OBJECT-TYPE
    SYNTAX      DisplayString
    MAX-ACCESS  read-write
    STATUS      current
    DESCRIPTION
	"The sixth output name of slave 5"
    ::= { slaveFiveOutputName 6}
slaveFiveOutputNameSeven OBJECT-TYPE
    SYNTAX      DisplayString
    MAX-ACCESS  read-write
    STATUS      current
    DESCRIPTION
	"The seventh output name of slave 5"
    ::= { slaveFiveOutputName 7}
slaveFiveOutputNameEight OBJECT-TYPE
    SYNTAX      DisplayString
    MAX-ACCESS  read-write
    STATUS      current
    DESCRIPTION
	"The eighth output name of slave 5"
    ::= { slaveFiveOutputName 8}
slaveFiveOutputNameNine OBJECT-TYPE
    SYNTAX      DisplayString
    MAX-ACCESS  read-write
    STATUS      current
    DESCRIPTION
	"The nineth output name of slave 5"
    ::= { slaveFiveOutputName 9}
slaveFiveOutputNameTen OBJECT-TYPE
    SYNTAX      DisplayString
    MAX-ACCESS  read-write
    STATUS      current
    DESCRIPTION
	"The tenth output name of slave 5"
    ::= { slaveFiveOutputName 10}
slaveFiveOutputNameEleven OBJECT-TYPE
    SYNTAX      DisplayString
    MAX-ACCESS  read-write
    STATUS      current
    DESCRIPTION
	"The eleventh output name of slave 5"
    ::= { slaveFiveOutputName 11}
slaveFiveOutputNameTwelve OBJECT-TYPE
    SYNTAX      DisplayString
    MAX-ACCESS  read-write
    STATUS      current
    DESCRIPTION
	"The twelfth output name of slave 5"
    ::= { slaveFiveOutputName 12}
slaveFiveOutputNameThirteen OBJECT-TYPE
    SYNTAX      DisplayString
    MAX-ACCESS  read-write
    STATUS      current
    DESCRIPTION
	"The thirteenth output name of slave 5"
    ::= { slaveFiveOutputName 13}
slaveFiveOutputNameFourteen OBJECT-TYPE
    SYNTAX      DisplayString
    MAX-ACCESS  read-write
    STATUS      current
    DESCRIPTION
	"The fourteenth output name of slave 5"
    ::= { slaveFiveOutputName 14}
slaveFiveOutputNameFifteen OBJECT-TYPE
    SYNTAX      DisplayString
    MAX-ACCESS  read-write
    STATUS      current
    DESCRIPTION
	"The fifteenth output name of slave 5"
    ::= { slaveFiveOutputName 15}
slaveFiveOutputNameSixteen OBJECT-TYPE
    SYNTAX      DisplayString
    MAX-ACCESS  read-write
    STATUS      current
    DESCRIPTION
	"The sixteenth output name of slave 5"
    ::= { slaveFiveOutputName 16}
slaveFiveOutputNameSeventeen OBJECT-TYPE
    SYNTAX      DisplayString
    MAX-ACCESS  read-write
    STATUS      current
    DESCRIPTION
	"The seventeenth output name of slave 5"
    ::= { slaveFiveOutputName 17}
slaveFiveOutputNameEighteen OBJECT-TYPE
    SYNTAX      DisplayString
    MAX-ACCESS  read-write
    STATUS      current
    DESCRIPTION
	"The eighteenh output name of slave 5"
    ::= { slaveFiveOutputName 18}
slaveFiveOutputNameNineteen OBJECT-TYPE
    SYNTAX      DisplayString
    MAX-ACCESS  read-write
    STATUS      current
    DESCRIPTION
	"The nineteenth output name of slave 5"
    ::= { slaveFiveOutputName 19}
slaveFiveOutputNameTwenty OBJECT-TYPE
    SYNTAX      DisplayString
    MAX-ACCESS  read-write
    STATUS      current
    DESCRIPTION
	"The twentieth output name of slave 5"
    ::= { slaveFiveOutputName 20}
slaveFiveOutputNameTwentyOne OBJECT-TYPE
    SYNTAX      DisplayString
    MAX-ACCESS  read-write
    STATUS      current
    DESCRIPTION
	"The twenty-first output name of slave 5"
    ::= { slaveFiveOutputName 21}
slaveFiveOutputNameTwentyTwo OBJECT-TYPE
    SYNTAX      DisplayString
    MAX-ACCESS  read-write
    STATUS      current
    DESCRIPTION
	"The twenty-second output name of slave 5"
    ::= { slaveFiveOutputName 22}
slaveFiveOutputNameTwentyThree OBJECT-TYPE
    SYNTAX      DisplayString
    MAX-ACCESS  read-write
    STATUS      current
    DESCRIPTION
	"The twenty-third output name of slave 5"
    ::= { slaveFiveOutputName 23}
slaveFiveOutputNameTwentyFour OBJECT-TYPE
    SYNTAX      DisplayString
    MAX-ACCESS  read-write
    STATUS      current
    DESCRIPTION
	"The twenty-fourth output name of slave 5"
    ::= { slaveFiveOutputName 24}


    
slaveFiveOutputStatus OBJECT IDENTIFIER ::= { rpduSlaveFive 9}

slaveFiveOutputStatusOne OBJECT-TYPE
    SYNTAX      DisplayString
    MAX-ACCESS  read-write
    STATUS      current
    DESCRIPTION
	"The first output status of slave 5"
    ::= { slaveFiveOutputStatus 1}
slaveFiveOutputStatusTwo OBJECT-TYPE
    SYNTAX      DisplayString
    MAX-ACCESS  read-write
    STATUS      current
    DESCRIPTION
	"The second output status of slave 5"
    ::= { slaveFiveOutputStatus 2}

slaveFiveOutputStatusThree OBJECT-TYPE
    SYNTAX      DisplayString
    MAX-ACCESS  read-write
    STATUS      current
    DESCRIPTION
	"The third output status of slave 5"
    ::= { slaveFiveOutputStatus 3}
slaveFiveOutputStatusFour OBJECT-TYPE
    SYNTAX      DisplayString
    MAX-ACCESS  read-write
    STATUS      current
    DESCRIPTION
	"The fourth output status of slave 5"
    ::= { slaveFiveOutputStatus 4}
slaveFiveOutputStatusFive OBJECT-TYPE
    SYNTAX      DisplayString
    MAX-ACCESS  read-write
    STATUS      current
    DESCRIPTION
	"The fifth output status of slave 5"
    ::= { slaveFiveOutputStatus 5}
slaveFiveOutputStatusSix OBJECT-TYPE
    SYNTAX      DisplayString
    MAX-ACCESS  read-write
    STATUS      current
    DESCRIPTION
	"The sixth output status of slave 5"
    ::= { slaveFiveOutputStatus 6}
slaveFiveOutputStatusSeven OBJECT-TYPE
    SYNTAX      DisplayString
    MAX-ACCESS  read-write
    STATUS      current
    DESCRIPTION
	"The seventh output status of slave 5"
    ::= { slaveFiveOutputStatus 7}
slaveFiveOutputStatusEight OBJECT-TYPE
    SYNTAX      DisplayString
    MAX-ACCESS  read-write
    STATUS      current
    DESCRIPTION
	"The eighth output status of slave 5"
    ::= { slaveFiveOutputStatus 8}
slaveFiveOutputStatusNine OBJECT-TYPE
    SYNTAX      DisplayString
    MAX-ACCESS  read-write
    STATUS      current
    DESCRIPTION
	"The nineth output status of slave 5"
    ::= { slaveFiveOutputStatus 9}
slaveFiveOutputStatusTen OBJECT-TYPE
    SYNTAX      DisplayString
    MAX-ACCESS  read-write
    STATUS      current
    DESCRIPTION
	"The tenth output status of slave 5"
    ::= { slaveFiveOutputStatus 10}
slaveFiveOutputStatusEleven OBJECT-TYPE
    SYNTAX      DisplayString
    MAX-ACCESS  read-write
    STATUS      current
    DESCRIPTION
	"The eleventh output status of slave 5"
    ::= { slaveFiveOutputStatus 11}
slaveFiveOutputStatusTwelve OBJECT-TYPE
    SYNTAX      DisplayString
    MAX-ACCESS  read-write
    STATUS      current
    DESCRIPTION
	"The twelfth output status of slave 5"
    ::= { slaveFiveOutputStatus 12}
slaveFiveOutputStatusThirteen OBJECT-TYPE
    SYNTAX      DisplayString
    MAX-ACCESS  read-write
    STATUS      current
    DESCRIPTION
	"The thirteenth output status of slave 5"
    ::= { slaveFiveOutputStatus 13}
slaveFiveOutputStatusFourteen OBJECT-TYPE
    SYNTAX      DisplayString
    MAX-ACCESS  read-write
    STATUS      current
    DESCRIPTION
	"The fourteenth output status of slave 5"
    ::= { slaveFiveOutputStatus 14}
slaveFiveOutputStatusFifteen OBJECT-TYPE
    SYNTAX      DisplayString
    MAX-ACCESS  read-write
    STATUS      current
    DESCRIPTION
	"The fifteenth output status of slave 5"
    ::= { slaveFiveOutputStatus 15}
slaveFiveOutputStatusSixteen OBJECT-TYPE
    SYNTAX      DisplayString
    MAX-ACCESS  read-write
    STATUS      current
    DESCRIPTION
	"The sixteenth output status of slave 5"
    ::= { slaveFiveOutputStatus 16}
slaveFiveOutputStatusSeventeen OBJECT-TYPE
    SYNTAX      DisplayString
    MAX-ACCESS  read-write
    STATUS      current
    DESCRIPTION
	"The seventeenth output status of slave 5"
    ::= { slaveFiveOutputStatus 17}
slaveFiveOutputStatusEighteen OBJECT-TYPE
    SYNTAX      DisplayString
    MAX-ACCESS  read-write
    STATUS      current
    DESCRIPTION
	"The eighteenth output status of slave 5"
    ::= { slaveFiveOutputStatus 18}
slaveFiveOutputStatusNineteen OBJECT-TYPE
    SYNTAX      DisplayString
    MAX-ACCESS  read-write
    STATUS      current
    DESCRIPTION
	"The nineteenth output status of slave 5"
    ::= { slaveFiveOutputStatus 19}
slaveFiveOutputStatusTwenty OBJECT-TYPE
    SYNTAX      DisplayString
    MAX-ACCESS  read-write
    STATUS      current
    DESCRIPTION
	"The twentieth output status of slave 5"
    ::= { slaveFiveOutputStatus 20}
slaveFiveOutputStatusTwentyOne OBJECT-TYPE
    SYNTAX      DisplayString
    MAX-ACCESS  read-write
    STATUS      current
    DESCRIPTION
	"The twenty-first output status of slave 5"
    ::= { slaveFiveOutputStatus 21}
slaveFiveOutputStatusTwentyTwo OBJECT-TYPE
    SYNTAX      DisplayString
    MAX-ACCESS  read-write
    STATUS      current
    DESCRIPTION
	"The twenty-second output status of slave 5"
    ::= { slaveFiveOutputStatus 22}
slaveFiveOutputStatusTwentyThree OBJECT-TYPE
    SYNTAX      DisplayString
    MAX-ACCESS  read-write
    STATUS      current
    DESCRIPTION
	"The twenty-third output status of slave 5"
    ::= { slaveFiveOutputStatus 23}
slaveFiveOutputStatusTwentyFour OBJECT-TYPE
    SYNTAX      DisplayString
    MAX-ACCESS  read-write
    STATUS      current
    DESCRIPTION
	"The twenty-fourth output status of slave 5"
    ::= { slaveFiveOutputStatus 24}

slaveFiveOutputCurrent   OBJECT IDENTIFIER ::= { rpduSlaveFive 10}
slaveFiveOutputCurrentOne OBJECT-TYPE
    SYNTAX      DisplayString
    MAX-ACCESS  read-only
    STATUS      current
    DESCRIPTION
	"The current value of the first output of the slave 5"
    ::= { slaveFiveOutputCurrent 1}
slaveFiveOutputCurrentTwo OBJECT-TYPE
    SYNTAX      DisplayString
    MAX-ACCESS  read-only
    STATUS      current
    DESCRIPTION
	"The current value of the second output of the slave 5"
    ::= { slaveFiveOutputCurrent 2}
slaveFiveOutputCurrentThree OBJECT-TYPE
    SYNTAX      DisplayString
    MAX-ACCESS  read-only
    STATUS      current
    DESCRIPTION
	"The current value of the third output of the slave 5"
    ::= { slaveFiveOutputCurrent 3}
slaveFiveOutputCurrentFour OBJECT-TYPE
    SYNTAX      DisplayString
    MAX-ACCESS  read-only
    STATUS      current
    DESCRIPTION
	"The current value of the fourth output of the slave 5"
    ::= { slaveFiveOutputCurrent 4}
slaveFiveOutputCurrentFive OBJECT-TYPE
    SYNTAX      DisplayString
    MAX-ACCESS  read-only
    STATUS      current
    DESCRIPTION
	"The current value of the fifth output of the slave 5"
    ::= { slaveFiveOutputCurrent 5}
slaveFiveOutputCurrentSix OBJECT-TYPE
    SYNTAX      DisplayString
    MAX-ACCESS  read-only
    STATUS      current
    DESCRIPTION
	"The current value of the sixth output of the slave 5"
    ::= { slaveFiveOutputCurrent 6}
slaveFiveOutputCurrentSeven OBJECT-TYPE
    SYNTAX      DisplayString
    MAX-ACCESS  read-only
    STATUS      current
    DESCRIPTION
	"The current value of the seventh output of the slave 5"
    ::= { slaveFiveOutputCurrent 7}
slaveFiveOutputCurrentEight OBJECT-TYPE
    SYNTAX      DisplayString
    MAX-ACCESS  read-only
    STATUS      current
    DESCRIPTION
	"The current value of the eighth output of the slave 5"
    ::= { slaveFiveOutputCurrent 8}
slaveFiveOutputCurrentNine OBJECT-TYPE
    SYNTAX      DisplayString
    MAX-ACCESS  read-only
    STATUS      current
    DESCRIPTION
	"The current value of the nineth output of the slave 5"
    ::= { slaveFiveOutputCurrent 9}
slaveFiveOutputCurrentTen OBJECT-TYPE
    SYNTAX      DisplayString
    MAX-ACCESS  read-only
    STATUS      current
    DESCRIPTION
	"The current value of the tenth output of the slave 5"
    ::= { slaveFiveOutputCurrent 10}
slaveFiveOutputCurrentEleven OBJECT-TYPE
    SYNTAX      DisplayString
    MAX-ACCESS  read-only
    STATUS      current
    DESCRIPTION
	"The current value of the eleventh output of the slave 5"
    ::= { slaveFiveOutputCurrent 11}
slaveFiveOutputCurrentTwelve OBJECT-TYPE
    SYNTAX      DisplayString
    MAX-ACCESS  read-only
    STATUS      current
    DESCRIPTION
	"The current value of the twelfth output of the slave 5"
    ::= { slaveFiveOutputCurrent 12}
slaveFiveOutputCurrentThirteen OBJECT-TYPE
    SYNTAX      DisplayString
    MAX-ACCESS  read-only
    STATUS      current
    DESCRIPTION
	"The current value of the thirteenth output of the slave 5"
    ::= { slaveFiveOutputCurrent 13}
slaveFiveOutputCurrentFourteen OBJECT-TYPE
    SYNTAX      DisplayString
    MAX-ACCESS  read-only
    STATUS      current
    DESCRIPTION
	"The current value of the fourteenth output of the slave 5"
    ::= { slaveFiveOutputCurrent 14}
slaveFiveOutputCurrentFifteen OBJECT-TYPE
    SYNTAX      DisplayString
    MAX-ACCESS  read-only
    STATUS      current
    DESCRIPTION
	"The current value of the fifteenth output of the slave 5"
    ::= { slaveFiveOutputCurrent 15}
slaveFiveOutputCurrentSixteen OBJECT-TYPE
    SYNTAX      DisplayString
    MAX-ACCESS  read-only
    STATUS      current
    DESCRIPTION
	"The current value of the sixteenth output of the slave 5"
    ::= { slaveFiveOutputCurrent 16}
slaveFiveOutputCurrentSeventeen OBJECT-TYPE
    SYNTAX      DisplayString
    MAX-ACCESS  read-only
    STATUS      current
    DESCRIPTION
	"The current value of the seventeenth output of the slave 5"
    ::= { slaveFiveOutputCurrent 17}
slaveFiveOutputCurrentEighteen OBJECT-TYPE
    SYNTAX      DisplayString
    MAX-ACCESS  read-only
    STATUS      current
    DESCRIPTION
	"The current value of the eighteenth output of the slave 5"
    ::= { slaveFiveOutputCurrent 18}
slaveFiveOutputCurrentNineteen OBJECT-TYPE
    SYNTAX      DisplayString
    MAX-ACCESS  read-only
    STATUS      current
    DESCRIPTION
	"The current value of the nineteenth output of the slave 5"
    ::= { slaveFiveOutputCurrent 19}
slaveFiveOutputCurrentTwenty OBJECT-TYPE
    SYNTAX      DisplayString
    MAX-ACCESS  read-only
    STATUS      current
    DESCRIPTION
	"The current value of the twentieth output of the slave 5"
    ::= { slaveFiveOutputCurrent 20}
slaveFiveOutputCurrentTwentyOne OBJECT-TYPE
    SYNTAX      DisplayString
    MAX-ACCESS  read-only
    STATUS      current
    DESCRIPTION
	"The current value of the twenty-first output of the slave 5"
    ::= { slaveFiveOutputCurrent 21}
slaveFiveOutputCurrentTwentyTwo OBJECT-TYPE
    SYNTAX      DisplayString
    MAX-ACCESS  read-only
    STATUS      current
    DESCRIPTION
	"The current value of the twenty-second output of the slave 5"
    ::= { slaveFiveOutputCurrent 22}
slaveFiveOutputCurrentTwentyThree OBJECT-TYPE
    SYNTAX      DisplayString
    MAX-ACCESS  read-only
    STATUS      current
    DESCRIPTION
	"The current value of the twenty-third output of the slave 5"
    ::= { slaveFiveOutputCurrent 23}
slaveFiveOutputCurrentTwentyFour OBJECT-TYPE
    SYNTAX      DisplayString
    MAX-ACCESS  read-only
    STATUS      current
    DESCRIPTION
	"The current value of the twenty-fourth output of the slave 5"
    ::= { slaveFiveOutputCurrent 24}

slaveFiveOutputCurrentMin   OBJECT IDENTIFIER ::= { rpduSlaveFive 11}
slaveFiveOutputCurrentMinOne OBJECT-TYPE
    SYNTAX      DisplayString
    MAX-ACCESS  read-only
    STATUS      current
    DESCRIPTION
	"The Min. current value of the first output of the slave 5"
    ::= { slaveFiveOutputCurrentMin 1}
slaveFiveOutputCurrentMinTwo OBJECT-TYPE
    SYNTAX      DisplayString
    MAX-ACCESS  read-only
    STATUS      current
    DESCRIPTION
	"The Min. current value of the second output of the slave 5"
    ::= { slaveFiveOutputCurrentMin 2}
slaveFiveOutputCurrentMinThree OBJECT-TYPE
    SYNTAX      DisplayString
    MAX-ACCESS  read-only
    STATUS      current
    DESCRIPTION
	"The Min. current value of the third output of the slave 5"
    ::= { slaveFiveOutputCurrentMin 3}
slaveFiveOutputCurrentMinFour OBJECT-TYPE
    SYNTAX      DisplayString
    MAX-ACCESS  read-only
    STATUS      current
    DESCRIPTION
	"The Min. current value of the fourth output of the slave 5"
    ::= { slaveFiveOutputCurrentMin 4}
slaveFiveOutputCurrentMinFive OBJECT-TYPE
    SYNTAX      DisplayString
    MAX-ACCESS  read-only
    STATUS      current
    DESCRIPTION
	"The Min. current value of the fifth output of the slave 5"
    ::= { slaveFiveOutputCurrentMin 5}
slaveFiveOutputCurrentMinSix OBJECT-TYPE
    SYNTAX      DisplayString
    MAX-ACCESS  read-only
    STATUS      current
    DESCRIPTION
	"The Min. current value of the sixth output of the slave 5"
    ::= { slaveFiveOutputCurrentMin 6}
slaveFiveOutputCurrentMinSeven OBJECT-TYPE
    SYNTAX      DisplayString
    MAX-ACCESS  read-only
    STATUS      current
    DESCRIPTION
	"The Min. current value of the seventh output of the slave 5"
    ::= { slaveFiveOutputCurrentMin 7}
slaveFiveOutputCurrentMinEight OBJECT-TYPE
    SYNTAX      DisplayString
    MAX-ACCESS  read-only
    STATUS      current
    DESCRIPTION
	"The Min. current value of the eighth output of the slave 5"
    ::= { slaveFiveOutputCurrentMin 8}
slaveFiveOutputCurrentMinNine OBJECT-TYPE
    SYNTAX      DisplayString
    MAX-ACCESS  read-only
    STATUS      current
    DESCRIPTION
	"The Min. current value of the nineth output of the slave 5"
    ::= { slaveFiveOutputCurrentMin 9}
slaveFiveOutputCurrentMinTen OBJECT-TYPE
    SYNTAX      DisplayString
    MAX-ACCESS  read-only
    STATUS      current
    DESCRIPTION
	"The Min. current value of the tenth output of the slave 5"
    ::= { slaveFiveOutputCurrentMin 10}
slaveFiveOutputCurrentMinEleven OBJECT-TYPE
    SYNTAX      DisplayString
    MAX-ACCESS  read-only
    STATUS      current
    DESCRIPTION
	"The Min. current value of the eleventh output of the slave 5"
    ::= { slaveFiveOutputCurrentMin 11}
slaveFiveOutputCurrentMinTwleve OBJECT-TYPE
    SYNTAX      DisplayString
    MAX-ACCESS  read-only
    STATUS      current
    DESCRIPTION
	"The Min. current value of the twelfth output of the slave 5"
    ::= { slaveFiveOutputCurrentMin 12}
slaveFiveOutputCurrentMinThirteen OBJECT-TYPE
    SYNTAX      DisplayString
    MAX-ACCESS  read-only
    STATUS      current
    DESCRIPTION
	"The Min. current value of the thirteenth output of the slave 5"
    ::= { slaveFiveOutputCurrentMin 13}
slaveFiveOutputCurrentMinFourteen OBJECT-TYPE
    SYNTAX      DisplayString
    MAX-ACCESS  read-only
    STATUS      current
    DESCRIPTION
	"The Min. current value of the fourteenth output of the slave 5"
    ::= { slaveFiveOutputCurrentMin 14}
slaveFiveOutputCurrentMinFifteen OBJECT-TYPE
    SYNTAX      DisplayString
    MAX-ACCESS  read-only
    STATUS      current
    DESCRIPTION
	"The Min. current value of the fifteenth output of the slave 5"
    ::= { slaveFiveOutputCurrentMin 15}
slaveFiveOutputCurrentMinSixteen OBJECT-TYPE
    SYNTAX      DisplayString
    MAX-ACCESS  read-only
    STATUS      current
    DESCRIPTION
	"The Min. current value of the sixteenth output of the slave 5"
    ::= { slaveFiveOutputCurrentMin 16}
slaveFiveOutputCurrentMinSeventeen OBJECT-TYPE
    SYNTAX      DisplayString
    MAX-ACCESS  read-only
    STATUS      current
    DESCRIPTION
	"The Min. current value of the seventeenth output of the slave 5"
    ::= { slaveFiveOutputCurrentMin 17}
slaveFiveOutputCurrentMinEighteen OBJECT-TYPE
    SYNTAX      DisplayString
    MAX-ACCESS  read-only
    STATUS      current
    DESCRIPTION
	"The Min. current value of the eighteenth output of the slave 5"
    ::= { slaveFiveOutputCurrentMin 18}
slaveFiveOutputCurrentMinNineteen OBJECT-TYPE
    SYNTAX      DisplayString
    MAX-ACCESS  read-only
    STATUS      current
    DESCRIPTION
	"The Min. current value of the nineteenth output of the slave 5"
    ::= { slaveFiveOutputCurrentMin 19}
slaveFiveOutputCurrentMinTwenty OBJECT-TYPE
    SYNTAX      DisplayString
    MAX-ACCESS  read-only
    STATUS      current
    DESCRIPTION
	"The Min. current value of the twentieth output of the slave 5"
    ::= { slaveFiveOutputCurrentMin 20}
slaveFiveOutputCurrentMinTwentyOne OBJECT-TYPE
    SYNTAX      DisplayString
    MAX-ACCESS  read-only
    STATUS      current
    DESCRIPTION
	"The Min. current value of the twentyth-first output of the slave 5"
    ::= { slaveFiveOutputCurrentMin 21}
slaveFiveOutputCurrentMinTwentyTwo OBJECT-TYPE
    SYNTAX      DisplayString
    MAX-ACCESS  read-only
    STATUS      current
    DESCRIPTION
	"The Min. current value of the twentyth-second output of the slave 5"
    ::= { slaveFiveOutputCurrentMin 22}
slaveFiveOutputCurrentMinTwentyThree OBJECT-TYPE
    SYNTAX      DisplayString
    MAX-ACCESS  read-only
    STATUS      current
    DESCRIPTION
	"The Min. current value of the twentyth-third output of the slave 5"
    ::= { slaveFiveOutputCurrentMin 23}
slaveFiveOutputCurrentMinTwentyFour OBJECT-TYPE
    SYNTAX      DisplayString
    MAX-ACCESS  read-only
    STATUS      current
    DESCRIPTION
	"The Min. current value of the twentyth-fourth output of the slave 5"
    ::= { slaveFiveOutputCurrentMin 24}




slaveFiveOutputCurrentMax   OBJECT IDENTIFIER ::= { rpduSlaveFive 12}
slaveFiveOutputCurrentMaxOne OBJECT-TYPE
    SYNTAX      DisplayString
    MAX-ACCESS  read-only
    STATUS      current
    DESCRIPTION
	"The Max. current value of the first output of the slave 5"
    ::= { slaveFiveOutputCurrentMax 1}
slaveFiveOutputCurrentMaxTwo OBJECT-TYPE
    SYNTAX      DisplayString
    MAX-ACCESS  read-only
    STATUS      current
    DESCRIPTION
	"The Max. current value of the second output of the slave 5"
    ::= { slaveFiveOutputCurrentMax 2}
slaveFiveOutputCurrentMaxThree OBJECT-TYPE
    SYNTAX      DisplayString
    MAX-ACCESS  read-only
    STATUS      current
    DESCRIPTION
	"The Max. current value of the third output of the slave 5"
    ::= { slaveFiveOutputCurrentMax 3}
slaveFiveOutputCurrentMaxFour OBJECT-TYPE
    SYNTAX      DisplayString
    MAX-ACCESS  read-only
    STATUS      current
    DESCRIPTION
	"The Max. current value of the fourth output of the slave 5"
    ::= { slaveFiveOutputCurrentMax 4}
slaveFiveOutputCurrentMaxFive OBJECT-TYPE
    SYNTAX      DisplayString
    MAX-ACCESS  read-only
    STATUS      current
    DESCRIPTION
	"The Max. current value of the fifth output of the slave 5"
    ::= { slaveFiveOutputCurrentMax 5}
slaveFiveOutputCurrentMaxSix OBJECT-TYPE
    SYNTAX      DisplayString
    MAX-ACCESS  read-only
    STATUS      current
    DESCRIPTION
	"The Max. current value of the sixth output of the slave 5"
    ::= { slaveFiveOutputCurrentMax 6}
slaveFiveOutputCurrentMaxSeven OBJECT-TYPE
    SYNTAX      DisplayString
    MAX-ACCESS  read-only
    STATUS      current
    DESCRIPTION
	"The Max. current value of the seventh output of the slave 5"
    ::= { slaveFiveOutputCurrentMax 7}
slaveFiveOutputCurrentMaxEight OBJECT-TYPE
    SYNTAX      DisplayString
    MAX-ACCESS  read-only
    STATUS      current
    DESCRIPTION
	"The Max. current value of the eighth output of the slave 5"
    ::= { slaveFiveOutputCurrentMax 8}
slaveFiveOutputCurrentMaxNine OBJECT-TYPE
    SYNTAX      DisplayString
    MAX-ACCESS  read-only
    STATUS      current
    DESCRIPTION
	"The Max. current value of the nineth output of the slave 5"
    ::= { slaveFiveOutputCurrentMax 9}
slaveFiveOutputCurrentMaxTen OBJECT-TYPE
    SYNTAX      DisplayString
    MAX-ACCESS  read-only
    STATUS      current
    DESCRIPTION
	"The Max. current value of the tenth output of the slave 5"
    ::= { slaveFiveOutputCurrentMax 10}
slaveFiveOutputCurrentMaxEleven OBJECT-TYPE
    SYNTAX      DisplayString
    MAX-ACCESS  read-only
    STATUS      current
    DESCRIPTION
	"The Max. current value of the eleventh output of the slave 5"
    ::= { slaveFiveOutputCurrentMax 11}
slaveFiveOutputCurrentMaxTwleve OBJECT-TYPE
    SYNTAX      DisplayString
    MAX-ACCESS  read-only
    STATUS      current
    DESCRIPTION
	"The Max. current value of the twelfth output of the slave 5"
    ::= { slaveFiveOutputCurrentMax 12}
slaveFiveOutputCurrentMaxThirteen OBJECT-TYPE
    SYNTAX      DisplayString
    MAX-ACCESS  read-only
    STATUS      current
    DESCRIPTION
	"The Max. current value of the thirteenth output of the slave 5"
    ::= { slaveFiveOutputCurrentMax 13}
slaveFiveOutputCurrentMaxFourteen OBJECT-TYPE
    SYNTAX      DisplayString
    MAX-ACCESS  read-only
    STATUS      current
    DESCRIPTION
	"The Max. current value of the fourteenth output of the slave 5"
    ::= { slaveFiveOutputCurrentMax 14}
slaveFiveOutputCurrentMaxFifteen OBJECT-TYPE
    SYNTAX      DisplayString
    MAX-ACCESS  read-only
    STATUS      current
    DESCRIPTION
	"The Max. current value of the fifteenth output of the slave 5"
    ::= { slaveFiveOutputCurrentMax 15}
slaveFiveOutputCurrentMaxSixteen OBJECT-TYPE
    SYNTAX      DisplayString
    MAX-ACCESS  read-only
    STATUS      current
    DESCRIPTION
	"The Max. current value of the sixteenth output of the slave 5"
    ::= { slaveFiveOutputCurrentMax 16}
slaveFiveOutputCurrentMaxSeventeen OBJECT-TYPE
    SYNTAX      DisplayString
    MAX-ACCESS  read-only
    STATUS      current
    DESCRIPTION
	"The Max. current value of the seventeenth output of the slave 5"
    ::= { slaveFiveOutputCurrentMax 17}
slaveFiveOutputCurrentMaxEighteen OBJECT-TYPE
    SYNTAX      DisplayString
    MAX-ACCESS  read-only
    STATUS      current
    DESCRIPTION
	"The Max. current value of the eighteenth output of the slave 5"
    ::= { slaveFiveOutputCurrentMax 18}
slaveFiveOutputCurrentMaxNineteen OBJECT-TYPE
    SYNTAX      DisplayString
    MAX-ACCESS  read-only
    STATUS      current
    DESCRIPTION
	"The Max. current value of the nineteenth output of the slave 5"
    ::= { slaveFiveOutputCurrentMax 19}
slaveFiveOutputCurrentMaxTwenty OBJECT-TYPE
    SYNTAX      DisplayString
    MAX-ACCESS  read-only
    STATUS      current
    DESCRIPTION
	"The Max. current value of the twentieth output of the slave 5"
    ::= { slaveFiveOutputCurrentMax 20}
slaveFiveOutputCurrentMaxTwentyOne OBJECT-TYPE
    SYNTAX      DisplayString
    MAX-ACCESS  read-only
    STATUS      current
    DESCRIPTION
	"The Max. current value of the twenty-first output of the slave 5"
    ::= { slaveFiveOutputCurrentMax 21}
slaveFiveOutputCurrentMaxTwentyTwo OBJECT-TYPE
    SYNTAX      DisplayString
    MAX-ACCESS  read-only
    STATUS      current
    DESCRIPTION
	"The Max. current value of the twenty-second output of the slave 5"
    ::= { slaveFiveOutputCurrentMax 22}
slaveFiveOutputCurrentMaxTwentyThree OBJECT-TYPE
    SYNTAX      DisplayString
    MAX-ACCESS  read-only
    STATUS      current
    DESCRIPTION
	"The Max. current value of the twenty-third output of the slave 5"
    ::= { slaveFiveOutputCurrentMax 23}
slaveFiveOutputCurrentMaxTwentyFour OBJECT-TYPE
    SYNTAX      DisplayString
    MAX-ACCESS  read-only
    STATUS      current
    DESCRIPTION
	"The Max. current value of the twenty-fourth output of the slave 5"
    ::= { slaveFiveOutputCurrentMax 24}


slaveFiveOutputCurrentEnergy  OBJECT IDENTIFIER ::= { rpduSlaveFive 13}
slaveFiveOutputCurrentEnergyOne OBJECT-TYPE
    SYNTAX	DisplayString
    MAX-ACCESS	read-only
    STATUS	current
    DESCRIPTION
	"The energy value of the first output of the slave 5"
    ::={slaveFiveOutputCurrentEnergy 1}
slaveFiveOutputCurrentEnergyTwo OBJECT-TYPE
    SYNTAX	DisplayString
    MAX-ACCESS	read-only
    STATUS	current
    DESCRIPTION
	"The energy value of the second output of the slave 5"
    ::={slaveFiveOutputCurrentEnergy 2}
slaveFiveOutputCurrentEnergyThree OBJECT-TYPE
    SYNTAX	DisplayString
    MAX-ACCESS	read-only
    STATUS	current
    DESCRIPTION
	"The energy value of the third output of the slave 5"
    ::={slaveFiveOutputCurrentEnergy 3}
slaveFiveOutputCurrentEnergyFour OBJECT-TYPE
    SYNTAX	DisplayString
    MAX-ACCESS	read-only
    STATUS	current
    DESCRIPTION
	"The energy value of the fourth output of the slave 5"
    ::={slaveFiveOutputCurrentEnergy 4}
slaveFiveOutputCurrentEnergyFive OBJECT-TYPE
    SYNTAX	DisplayString
    MAX-ACCESS	read-only
    STATUS	current
    DESCRIPTION
	"The energy value of the fifth output of the slave 5"
    ::={slaveFiveOutputCurrentEnergy 5}
slaveFiveOutputCurrentEnergySix OBJECT-TYPE
    SYNTAX	DisplayString
    MAX-ACCESS	read-only
    STATUS	current
    DESCRIPTION
	"The energy value of the sixth output of the slave 5"
    ::={slaveFiveOutputCurrentEnergy 6}
slaveFiveOutputCurrentEnergySeven OBJECT-TYPE
    SYNTAX	DisplayString
    MAX-ACCESS	read-only
    STATUS	current
    DESCRIPTION
	"The energy value of the seventh output of the slave 5"
    ::={slaveFiveOutputCurrentEnergy 7}
slaveFiveOutputCurrentEnergyEight OBJECT-TYPE
    SYNTAX	DisplayString
    MAX-ACCESS	read-only
    STATUS	current
    DESCRIPTION
	"The energy value of the eighth output of the slave 5"
    ::={slaveFiveOutputCurrentEnergy 8}
slaveFiveOutputCurrentEnergyNine OBJECT-TYPE
    SYNTAX	DisplayString
    MAX-ACCESS	read-only
    STATUS	current
    DESCRIPTION
	"The energy value of the nineth output of the slave 5"
    ::={slaveFiveOutputCurrentEnergy 9}
slaveFiveOutputCurrentEnergyTen OBJECT-TYPE
    SYNTAX	DisplayString
    MAX-ACCESS	read-only
    STATUS	current
    DESCRIPTION
	"The energy value of the tenth output of the slave 5"
    ::={slaveFiveOutputCurrentEnergy 10}
slaveFiveOutputCurrentEnergyEleven OBJECT-TYPE
    SYNTAX	DisplayString
    MAX-ACCESS	read-only
    STATUS	current
    DESCRIPTION
	"The energy value of the eleventh output of the slave 5"
    ::={slaveFiveOutputCurrentEnergy 11}
slaveFiveOutputCurrentEnergyTwelve OBJECT-TYPE
    SYNTAX	DisplayString
    MAX-ACCESS	read-only
    STATUS	current
    DESCRIPTION
	"The energy value of the twelfth output of the slave 5"
    ::={slaveFiveOutputCurrentEnergy 12}
slaveFiveOutputCurrentEnergyThirteen OBJECT-TYPE
    SYNTAX	DisplayString
    MAX-ACCESS	read-only
    STATUS	current
    DESCRIPTION
	"The energy value of the thirteenth output of the slave 5"
    ::={slaveFiveOutputCurrentEnergy 13}
slaveFiveOutputCurrentEnergyFourteen OBJECT-TYPE
    SYNTAX	DisplayString
    MAX-ACCESS	read-only
    STATUS	current
    DESCRIPTION
	"The energy value of the fourteenth output of the slave 5"
    ::={slaveFiveOutputCurrentEnergy 14}
slaveFiveOutputCurrentEnergyFifteen OBJECT-TYPE
    SYNTAX	DisplayString
    MAX-ACCESS	read-only
    STATUS	current
    DESCRIPTION
	"The energy value of the fifteenth output of the slave 5"
    ::={slaveFiveOutputCurrentEnergy 15}
slaveFiveOutputCurrentEnergySixteen OBJECT-TYPE
    SYNTAX	DisplayString
    MAX-ACCESS	read-only
    STATUS	current
    DESCRIPTION
	"The energy value of the sixteenth output of the slave 5"
    ::={slaveFiveOutputCurrentEnergy 16}
slaveFiveOutputCurrentEnergySeventeen OBJECT-TYPE
    SYNTAX	DisplayString
    MAX-ACCESS	read-only
    STATUS	current
    DESCRIPTION
	"The energy value of the seventeenth output of the slave 5"
    ::={slaveFiveOutputCurrentEnergy 17}
slaveFiveOutputCurrentEnergyEighteen OBJECT-TYPE
    SYNTAX	DisplayString
    MAX-ACCESS	read-only
    STATUS	current
    DESCRIPTION
	"The energy value of the eighteenth output of the slave 5"
    ::={slaveFiveOutputCurrentEnergy 18}
slaveFiveOutputCurrentEnergyNineteen OBJECT-TYPE
    SYNTAX	DisplayString
    MAX-ACCESS	read-only
    STATUS	current
    DESCRIPTION
	"The energy value of the nineteenth output of the slave 5"
    ::={slaveFiveOutputCurrentEnergy 19}
slaveFiveOutputCurrentEnergyTwenty OBJECT-TYPE
    SYNTAX	DisplayString
    MAX-ACCESS	read-only
    STATUS	current
    DESCRIPTION
	"The energy value of the twentieth output of the slave 5"
    ::={slaveFiveOutputCurrentEnergy 20}
slaveFiveOutputCurrentEnergyTwentyOne OBJECT-TYPE
    SYNTAX	DisplayString
    MAX-ACCESS	read-only
    STATUS	current
    DESCRIPTION
	"The energy value of the twenty-first output of the slave 5"
    ::={slaveFiveOutputCurrentEnergy 21}
slaveFiveOutputCurrentEnergyTwentyTwo OBJECT-TYPE
    SYNTAX	DisplayString
    MAX-ACCESS	read-only
    STATUS	current
    DESCRIPTION
	"The energy value of the twenty-second output of the slave 5"
    ::={slaveFiveOutputCurrentEnergy 22}
slaveFiveOutputCurrentEnergyTwentyThree OBJECT-TYPE
    SYNTAX	DisplayString
    MAX-ACCESS	read-only
    STATUS	current
    DESCRIPTION
	"The energy value of the twenty-third output of the slave 5"
    ::={slaveFiveOutputCurrentEnergy 23}
slaveFiveOutputCurrentEnergyTwentyFour OBJECT-TYPE
    SYNTAX	DisplayString
    MAX-ACCESS	read-only
    STATUS	current
    DESCRIPTION
	"The energy value of the twenty-fourth output of the slave 5"
    ::={slaveFiveOutputCurrentEnergy 24}

-------------------------------Slave6 ---------------------------------------------  
rpduDeviceSeven OBJECT IDENTIFIER ::= { rpdu 7}
rpduSlaveSix OBJECT IDENTIFIER ::= { rpduDeviceSeven 1}

slaveSixName OBJECT-TYPE
    SYNTAX      DisplayString
    MAX-ACCESS  read-write
    STATUS      current
    DESCRIPTION
	"This is the seventh device."
    ::= { rpduSlaveSix 1}
    
slaveSixType OBJECT-TYPE
    SYNTAX      DisplayString
    MAX-ACCESS  read-only
    STATUS      current
    DESCRIPTION
	"This is device type "
    ::= { rpduSlaveSix 2}
    
slaveSixOutputNumber OBJECT-TYPE 
    SYNTAX      Integer32
    MAX-ACCESS  read-only
    STATUS      current
    DESCRIPTION
	"This is the output quantity"
::= { rpduSlaveSix 7}
    
slaveSixLineOne OBJECT IDENTIFIER ::= { rpduSlaveSix 3}
slaveSixLineOnePower OBJECT-TYPE
    SYNTAX      DisplayString
    MAX-ACCESS  read-only
    STATUS      current
    DESCRIPTION
	"The power of phase one"
    ::= { slaveSixLineOne 1}
slaveSixLineOnePF OBJECT-TYPE
    SYNTAX      DisplayString
    MAX-ACCESS  read-only
    STATUS      current
    DESCRIPTION
	"The power factor of phase one"
    ::= { slaveSixLineOne 2}
    
slaveSixLineOneEnergy OBJECT-TYPE
    SYNTAX      DisplayString
    MAX-ACCESS  read-only
    STATUS      current
    DESCRIPTION
	"The energy of phase one"
    ::= { slaveSixLineOne 3}
slaveSixLineOneCurrent OBJECT-TYPE
    SYNTAX      DisplayString
    MAX-ACCESS  read-only
    STATUS      current
    DESCRIPTION
	"The current of phase one"
    ::= { slaveSixLineOne 4}
slaveSixLineOneVoltage OBJECT-TYPE
    SYNTAX      Integer32
    MAX-ACCESS  read-only
    STATUS      current
    DESCRIPTION
	"The voltage of phase one"
    ::= { slaveSixLineOne 5}
slaveSixLineOneCurrentMin OBJECT-TYPE
    SYNTAX      DisplayString
    MAX-ACCESS  read-only
    STATUS      current
    DESCRIPTION
	"The Min. current value of phase one"
	::= { slaveSixLineOne 6}
slaveSixLineOneCurrentMax OBJECT-TYPE
    SYNTAX      DisplayString
    MAX-ACCESS  read-only
    STATUS      current
    DESCRIPTION
	"The Max. current value of phase one"
    ::= { slaveSixLineOne 7}
    
slaveSixLineOneVoltageMin OBJECT-TYPE
    SYNTAX      Integer32
    MAX-ACCESS  read-only
    STATUS      current
    DESCRIPTION
	"The Min. voltage value of phase one"
    ::= { slaveSixLineOne 8}
    
slaveSixLineOneVoltageMax OBJECT-TYPE
    SYNTAX      Integer32
    MAX-ACCESS  read-only
    STATUS      current
    DESCRIPTION
	"The Max. voltage value of phase one"
    ::= { slaveSixLineOne 9}


slaveSixLineTwo OBJECT IDENTIFIER ::= { rpduSlaveSix 4}
slaveSixLineTwoPower OBJECT-TYPE
    SYNTAX      DisplayString
    MAX-ACCESS  read-only
    STATUS      current
    DESCRIPTION
	"The power of phase two"
    ::= { slaveSixLineTwo 1}

slaveSixLineTwoPF OBJECT-TYPE
    SYNTAX      DisplayString
    MAX-ACCESS  read-only
    STATUS      current
    DESCRIPTION
	"The power factor of phase two"   
    ::= { slaveSixLineTwo 2}
    
slaveSixLineTwoEnergy OBJECT-TYPE
    SYNTAX      DisplayString
    MAX-ACCESS  read-only
    STATUS      current
    DESCRIPTION

	"The energy of phase two"
    ::= { slaveSixLineTwo 3}
slaveSixLineTwoCurrent OBJECT-TYPE           
    SYNTAX      DisplayString 
    MAX-ACCESS  read-only
    STATUS      current
    DESCRIPTION
	"The current of phase two"
    ::= { slaveSixLineTwo 4}
slaveSixLineTwoVoltage OBJECT-TYPE
    SYNTAX      Integer32
    MAX-ACCESS  read-only
    STATUS      current
    DESCRIPTION
	"The voltage of phase two"
    ::= { slaveSixLineTwo 5}
slaveSixLineTwoCurrentMin OBJECT-TYPE
    SYNTAX      DisplayString
    MAX-ACCESS  read-only
    STATUS      current
    DESCRIPTION
	"The Min. current value of phase two"
    ::= { slaveSixLineTwo 6}
slaveSixLineTwoCurrentMax OBJECT-TYPE
    SYNTAX      DisplayString
    MAX-ACCESS  read-only
    STATUS      current
    DESCRIPTION
	"The Max. current value of phase two"
    ::= { slaveSixLineTwo 7}
    
slaveSixLineTwoVoltageMin OBJECT-TYPE
    SYNTAX      Integer32
    MAX-ACCESS  read-only
    STATUS      current
    DESCRIPTION
	"The Min. voltage value of phase two"
    ::= { slaveSixLineTwo 8}
    
slaveSixLineTwoVoltageMax OBJECT-TYPE
    SYNTAX      Integer32
    MAX-ACCESS  read-only
    STATUS      current
    DESCRIPTION
	"The Max. voltage value of phase two"
    ::= { slaveSixLineTwo 9}



slaveSixLineThree OBJECT IDENTIFIER ::= { rpduSlaveSix 5}
slaveSixLineThreePower OBJECT-TYPE
    SYNTAX      DisplayString
    MAX-ACCESS  read-only
    STATUS      current
    DESCRIPTION
	"The power of phase three"
    ::= { slaveSixLineThree 1}

slaveSixLineThreePF OBJECT-TYPE
    SYNTAX      DisplayString
    MAX-ACCESS  read-only
    STATUS      current
    DESCRIPTION
	"The power factor of phase three"     
    ::= { slaveSixLineThree 2}
    
slaveSixLineThreeEnergy OBJECT-TYPE
    SYNTAX      DisplayString
    MAX-ACCESS  read-only
    STATUS      current
    DESCRIPTION
	"The energy of phase three"
    ::= { slaveSixLineThree 3}
slaveSixLineThreeCurrent OBJECT-TYPE
    SYNTAX      DisplayString
    MAX-ACCESS  read-only
    STATUS      current
    DESCRIPTION
	"The current of phase three"
    ::= { slaveSixLineThree 4}
slaveSixLineThreeVoltage OBJECT-TYPE
    SYNTAX      Integer32
    MAX-ACCESS  read-only
    STATUS      current
    DESCRIPTION
	"The voltage of phase three"
    ::= { slaveSixLineThree 5}
slaveSixLineThreeCurrentMin OBJECT-TYPE
    SYNTAX      DisplayString
    MAX-ACCESS  read-only
    STATUS      current
    DESCRIPTION
	"The Min. current value of phase three"
    ::= { slaveSixLineThree 6}
slaveSixLineThreeCurrentMax OBJECT-TYPE
    SYNTAX      DisplayString
    MAX-ACCESS  read-only
    STATUS      current
    DESCRIPTION
	"The Max. current value of phase three"
    ::= { slaveSixLineThree 7}
    
slaveSixLineThreeVoltageMin OBJECT-TYPE
    SYNTAX      Integer32
    MAX-ACCESS  read-only
    STATUS      current
    DESCRIPTION
	"The Min. voltage value of phase three"
    ::= { slaveSixLineThree 8}
    
slaveSixLineThreeVoltageMax OBJECT-TYPE
    SYNTAX      Integer32
    MAX-ACCESS  read-only
    STATUS      current
    DESCRIPTION
	"The Max. voltage value of phase three"
    ::= { slaveSixLineThree 9}


slaveSixSensor OBJECT IDENTIFIER ::= { rpduSlaveSix 6}
slaveSixTempOne OBJECT-TYPE
    SYNTAX      Integer32
    MAX-ACCESS  read-only
    STATUS      current
    DESCRIPTION
	"The first temperature sensor of slave 6"
    ::= { slaveSixSensor 1}
slaveSixTempTwo OBJECT-TYPE
    SYNTAX      Integer32
    MAX-ACCESS  read-only
    STATUS      current
    DESCRIPTION
	"The second temperature sensor of slave 6"
    ::= { slaveSixSensor 2}
slaveSixTempThree OBJECT-TYPE
    SYNTAX      Integer32
    MAX-ACCESS  read-only
    STATUS      current
    DESCRIPTION
	"The third temperature sensor of slave 6"
    ::= { slaveSixSensor 3}
slaveSixTempFour OBJECT-TYPE
    SYNTAX      Integer32
    MAX-ACCESS  read-only
    STATUS      current
    DESCRIPTION
	"The fourth temperature sensor of slave 6"
    ::= { slaveSixSensor 4}
slaveSixHumOne OBJECT-TYPE
    SYNTAX      Integer32
    MAX-ACCESS  read-only
    STATUS      current
    DESCRIPTION
	"The first humidity sensor of slave 6"
    ::= { slaveSixSensor 5}
slaveSixHumTwo OBJECT-TYPE
    SYNTAX      Integer32
    MAX-ACCESS  read-only
    STATUS      current
    DESCRIPTION
	"The second humidity sensor of slave 6"
    ::= { slaveSixSensor 6}
slaveSixHumThree OBJECT-TYPE
    SYNTAX      Integer32
    MAX-ACCESS  read-only
    STATUS      current
    DESCRIPTION
	"The third humidity sensor of slave 6"
    ::= { slaveSixSensor 7}
slaveSixHumFour OBJECT-TYPE
    SYNTAX      Integer32
    MAX-ACCESS  read-only
    STATUS      current
    DESCRIPTION
	"The fourth humidity sensor of slave 6"
    ::= { slaveSixSensor 8}
slaveSixDoorOne OBJECT-TYPE
    SYNTAX      DisplayString
    MAX-ACCESS  read-only
    STATUS      current
    DESCRIPTION
	"The first door sensor of slave 6"    
    ::= { slaveSixSensor 9}
slaveSixDoorTwo OBJECT-TYPE
    SYNTAX      DisplayString
    MAX-ACCESS  read-only
    STATUS      current
    DESCRIPTION
	"The second door sensor of slave 6"  
    ::= { slaveSixSensor 10}
slaveSixSmoke OBJECT-TYPE
    SYNTAX      DisplayString
    MAX-ACCESS  read-only
    STATUS      current
    DESCRIPTION
	"The smoke sensor of slave 6"
    ::= { slaveSixSensor 11}
slaveSixWater OBJECT-TYPE
    SYNTAX      DisplayString
    MAX-ACCESS  read-only
    STATUS      current
    DESCRIPTION
	"The water sensor of slave 6"
    ::= { slaveSixSensor 12}


	
        
slaveSixOutputName OBJECT IDENTIFIER ::= { rpduSlaveSix 8}
slaveSixOutputNameOne OBJECT-TYPE
    SYNTAX      DisplayString
    MAX-ACCESS  read-write
    STATUS      current
    DESCRIPTION
	"The first output name of slave 6"
    ::= { slaveSixOutputName 1}

slaveSixOutputNameTwo OBJECT-TYPE
    SYNTAX      DisplayString
    MAX-ACCESS  read-write
    STATUS      current
    DESCRIPTION
	"The second output name of slave 6"
    ::= { slaveSixOutputName 2}
slaveSixOutputNameThree OBJECT-TYPE
    SYNTAX      DisplayString
    MAX-ACCESS  read-write
    STATUS      current
    DESCRIPTION
	"The third output name of slave 6"
    ::= { slaveSixOutputName 3}
slaveSixOutputNameFour OBJECT-TYPE
    SYNTAX      DisplayString
    MAX-ACCESS  read-write
    STATUS      current
    DESCRIPTION
	"The fourth output name of slave 6"
    ::= { slaveSixOutputName 4}
slaveSixOutputNameFive OBJECT-TYPE
    SYNTAX      DisplayString
    MAX-ACCESS  read-write
    STATUS      current
    DESCRIPTION
	"The fifth output name of slave 6"
    ::= { slaveSixOutputName 5}
slaveSixOutputNameSix OBJECT-TYPE
    SYNTAX      DisplayString
    MAX-ACCESS  read-write
    STATUS      current
    DESCRIPTION
	"The sixth output name of slave 6"
    ::= { slaveSixOutputName 6}
slaveSixOutputNameSeven OBJECT-TYPE
    SYNTAX      DisplayString
    MAX-ACCESS  read-write
    STATUS      current
    DESCRIPTION
	"The seventh output name of slave 6"
    ::= { slaveSixOutputName 7}
slaveSixOutputNameEight OBJECT-TYPE
    SYNTAX      DisplayString
    MAX-ACCESS  read-write
    STATUS      current
    DESCRIPTION
	"The eighth output name of slave 6"
    ::= { slaveSixOutputName 8}
slaveSixOutputNameNine OBJECT-TYPE
    SYNTAX      DisplayString
    MAX-ACCESS  read-write
    STATUS      current
    DESCRIPTION
	"The nineth output name of slave 6"
    ::= { slaveSixOutputName 9}
slaveSixOutputNameTen OBJECT-TYPE
    SYNTAX      DisplayString
    MAX-ACCESS  read-write
    STATUS      current
    DESCRIPTION
	"The tenth output name of slave 6"
    ::= { slaveSixOutputName 10}
slaveSixOutputNameEleven OBJECT-TYPE
    SYNTAX      DisplayString
    MAX-ACCESS  read-write
    STATUS      current
    DESCRIPTION
	"The eleventh output name of slave 6"
    ::= { slaveSixOutputName 11}
slaveSixOutputNameTwelve OBJECT-TYPE
    SYNTAX      DisplayString
    MAX-ACCESS  read-write
    STATUS      current
    DESCRIPTION
	"The twelfth output name of slave 6"
    ::= { slaveSixOutputName 12}
slaveSixOutputNameThirteen OBJECT-TYPE
    SYNTAX      DisplayString
    MAX-ACCESS  read-write
    STATUS      current
    DESCRIPTION
	"The thirteenth output name of slave 6"
    ::= { slaveSixOutputName 13}
slaveSixOutputNameFourteen OBJECT-TYPE
    SYNTAX      DisplayString
    MAX-ACCESS  read-write
    STATUS      current
    DESCRIPTION
	"The fourteenth output name of slave 6"
    ::= { slaveSixOutputName 14}
slaveSixOutputNameFifteen OBJECT-TYPE
    SYNTAX      DisplayString
    MAX-ACCESS  read-write
    STATUS      current
    DESCRIPTION
	"The fifteenth output name of slave 6"
    ::= { slaveSixOutputName 15}
slaveSixOutputNameSixteen OBJECT-TYPE
    SYNTAX      DisplayString
    MAX-ACCESS  read-write
    STATUS      current
    DESCRIPTION
	"The sixteenth output name of slave 6"
    ::= { slaveSixOutputName 16}
slaveSixOutputNameSeventeen OBJECT-TYPE
    SYNTAX      DisplayString
    MAX-ACCESS  read-write
    STATUS      current
    DESCRIPTION
	"The seventeenth output name of slave 6"
    ::= { slaveSixOutputName 17}
slaveSixOutputNameEighteen OBJECT-TYPE
    SYNTAX      DisplayString
    MAX-ACCESS  read-write
    STATUS      current
    DESCRIPTION
	"The eighteenh output name of slave 6"
    ::= { slaveSixOutputName 18}
slaveSixOutputNameNineteen OBJECT-TYPE
    SYNTAX      DisplayString
    MAX-ACCESS  read-write
    STATUS      current
    DESCRIPTION
	"The nineteenth output name of slave 6"
    ::= { slaveSixOutputName 19}
slaveSixOutputNameTwenty OBJECT-TYPE
    SYNTAX      DisplayString
    MAX-ACCESS  read-write
    STATUS      current
    DESCRIPTION
	"The twentieth output name of slave 6"
    ::= { slaveSixOutputName 20}
slaveSixOutputNameTwentyOne OBJECT-TYPE
    SYNTAX      DisplayString
    MAX-ACCESS  read-write
    STATUS      current
    DESCRIPTION
	"The twenty-first output name of slave 6"
    ::= { slaveSixOutputName 21}
slaveSixOutputNameTwentyTwo OBJECT-TYPE
    SYNTAX      DisplayString
    MAX-ACCESS  read-write
    STATUS      current
    DESCRIPTION
	"The twenty-second output name of slave 6"
    ::= { slaveSixOutputName 22}
slaveSixOutputNameTwentyThree OBJECT-TYPE
    SYNTAX      DisplayString
    MAX-ACCESS  read-write
    STATUS      current
    DESCRIPTION
	"The twenty-third output name of slave 6"
    ::= { slaveSixOutputName 23}
slaveSixOutputNameTwentyFour OBJECT-TYPE
    SYNTAX      DisplayString
    MAX-ACCESS  read-write
    STATUS      current
    DESCRIPTION
	"The twenty-fourth output name of slave 6"
    ::= { slaveSixOutputName 24}


    
slaveSixOutputStatus OBJECT IDENTIFIER ::= { rpduSlaveSix 9}

slaveSixOutputStatusOne OBJECT-TYPE
    SYNTAX      DisplayString
    MAX-ACCESS  read-write
    STATUS      current
    DESCRIPTION
	"The first output status of slave 6"
    ::= { slaveSixOutputStatus 1}
slaveSixOutputStatusTwo OBJECT-TYPE
    SYNTAX      DisplayString
    MAX-ACCESS  read-write
    STATUS      current
    DESCRIPTION
	"The second output status of slave 6"
    ::= { slaveSixOutputStatus 2}

slaveSixOutputStatusThree OBJECT-TYPE
    SYNTAX      DisplayString
    MAX-ACCESS  read-write
    STATUS      current
    DESCRIPTION
	"The third output status of slave 6"
    ::= { slaveSixOutputStatus 3}
slaveSixOutputStatusFour OBJECT-TYPE
    SYNTAX      DisplayString
    MAX-ACCESS  read-write
    STATUS      current
    DESCRIPTION
	"The fourth output status of slave 6"
    ::= { slaveSixOutputStatus 4}
slaveSixOutputStatusFive OBJECT-TYPE
    SYNTAX      DisplayString
    MAX-ACCESS  read-write
    STATUS      current
    DESCRIPTION
	"The fifth output status of slave 6"
    ::= { slaveSixOutputStatus 5}
slaveSixOutputStatusSix OBJECT-TYPE
    SYNTAX      DisplayString
    MAX-ACCESS  read-write
    STATUS      current
    DESCRIPTION
	"The sixth output status of slave 6"
    ::= { slaveSixOutputStatus 6}
slaveSixOutputStatusSeven OBJECT-TYPE
    SYNTAX      DisplayString
    MAX-ACCESS  read-write
    STATUS      current
    DESCRIPTION
	"The seventh output status of slave 6"
    ::= { slaveSixOutputStatus 7}
slaveSixOutputStatusEight OBJECT-TYPE
    SYNTAX      DisplayString
    MAX-ACCESS  read-write
    STATUS      current
    DESCRIPTION
	"The eighth output status of slave 6"
    ::= { slaveSixOutputStatus 8}
slaveSixOutputStatusNine OBJECT-TYPE
    SYNTAX      DisplayString
    MAX-ACCESS  read-write
    STATUS      current
    DESCRIPTION
	"The nineth output status of slave 6"
    ::= { slaveSixOutputStatus 9}
slaveSixOutputStatusTen OBJECT-TYPE
    SYNTAX      DisplayString
    MAX-ACCESS  read-write
    STATUS      current
    DESCRIPTION
	"The tenth output status of slave 6"
    ::= { slaveSixOutputStatus 10}
slaveSixOutputStatusEleven OBJECT-TYPE
    SYNTAX      DisplayString
    MAX-ACCESS  read-write
    STATUS      current
    DESCRIPTION
	"The eleventh output status of slave 6"
    ::= { slaveSixOutputStatus 11}
slaveSixOutputStatusTwelve OBJECT-TYPE
    SYNTAX      DisplayString
    MAX-ACCESS  read-write
    STATUS      current
    DESCRIPTION
	"The twelfth output status of slave 6"
    ::= { slaveSixOutputStatus 12}
slaveSixOutputStatusThirteen OBJECT-TYPE
    SYNTAX      DisplayString
    MAX-ACCESS  read-write
    STATUS      current
    DESCRIPTION
	"The thirteenth output status of slave 6"
    ::= { slaveSixOutputStatus 13}
slaveSixOutputStatusFourteen OBJECT-TYPE
    SYNTAX      DisplayString
    MAX-ACCESS  read-write
    STATUS      current
    DESCRIPTION
	"The fourteenth output status of slave 6"
    ::= { slaveSixOutputStatus 14}
slaveSixOutputStatusFifteen OBJECT-TYPE
    SYNTAX      DisplayString
    MAX-ACCESS  read-write
    STATUS      current
    DESCRIPTION
	"The fifteenth output status of slave 6"
    ::= { slaveSixOutputStatus 15}
slaveSixOutputStatusSixteen OBJECT-TYPE
    SYNTAX      DisplayString
    MAX-ACCESS  read-write
    STATUS      current
    DESCRIPTION
	"The sixteenth output status of slave 6"
    ::= { slaveSixOutputStatus 16}
slaveSixOutputStatusSeventeen OBJECT-TYPE
    SYNTAX      DisplayString
    MAX-ACCESS  read-write
    STATUS      current
    DESCRIPTION
	"The seventeenth output status of slave 6"
    ::= { slaveSixOutputStatus 17}
slaveSixOutputStatusEighteen OBJECT-TYPE
    SYNTAX      DisplayString
    MAX-ACCESS  read-write
    STATUS      current
    DESCRIPTION
	"The eighteenth output status of slave 6"
    ::= { slaveSixOutputStatus 18}
slaveSixOutputStatusNineteen OBJECT-TYPE
    SYNTAX      DisplayString
    MAX-ACCESS  read-write
    STATUS      current
    DESCRIPTION
	"The nineteenth output status of slave 6"
    ::= { slaveSixOutputStatus 19}
slaveSixOutputStatusTwenty OBJECT-TYPE
    SYNTAX      DisplayString
    MAX-ACCESS  read-write
    STATUS      current
    DESCRIPTION
	"The twentieth output status of slave 6"
    ::= { slaveSixOutputStatus 20}
slaveSixOutputStatusTwentyOne OBJECT-TYPE
    SYNTAX      DisplayString
    MAX-ACCESS  read-write
    STATUS      current
    DESCRIPTION
	"The twenty-first output status of slave 6"
    ::= { slaveSixOutputStatus 21}
slaveSixOutputStatusTwentyTwo OBJECT-TYPE
    SYNTAX      DisplayString
    MAX-ACCESS  read-write
    STATUS      current
    DESCRIPTION
	"The twenty-second output status of slave 6"
    ::= { slaveSixOutputStatus 22}
slaveSixOutputStatusTwentyThree OBJECT-TYPE
    SYNTAX      DisplayString
    MAX-ACCESS  read-write
    STATUS      current
    DESCRIPTION
	"The twenty-third output status of slave 6"
    ::= { slaveSixOutputStatus 23}
slaveSixOutputStatusTwentyFour OBJECT-TYPE
    SYNTAX      DisplayString
    MAX-ACCESS  read-write
    STATUS      current
    DESCRIPTION
	"The twenty-fourth output status of slave 6"
    ::= { slaveSixOutputStatus 24}

slaveSixOutputCurrent   OBJECT IDENTIFIER ::= { rpduSlaveSix 10}
slaveSixOutputCurrentOne OBJECT-TYPE
    SYNTAX      DisplayString
    MAX-ACCESS  read-only
    STATUS      current
    DESCRIPTION
	"The current value of the first output of the slave 6"
    ::= { slaveSixOutputCurrent 1}
slaveSixOutputCurrentTwo OBJECT-TYPE
    SYNTAX      DisplayString
    MAX-ACCESS  read-only
    STATUS      current
    DESCRIPTION
	"The current value of the second output of the slave 6"
    ::= { slaveSixOutputCurrent 2}
slaveSixOutputCurrentThree OBJECT-TYPE
    SYNTAX      DisplayString
    MAX-ACCESS  read-only
    STATUS      current
    DESCRIPTION
	"The current value of the third output of the slave 6"
    ::= { slaveSixOutputCurrent 3}
slaveSixOutputCurrentFour OBJECT-TYPE
    SYNTAX      DisplayString
    MAX-ACCESS  read-only
    STATUS      current
    DESCRIPTION
	"The current value of the fourth output of the slave 6"
    ::= { slaveSixOutputCurrent 4}
slaveSixOutputCurrentFive OBJECT-TYPE
    SYNTAX      DisplayString
    MAX-ACCESS  read-only
    STATUS      current
    DESCRIPTION
	"The current value of the fifth output of the slave 6"
    ::= { slaveSixOutputCurrent 5}
slaveSixOutputCurrentSix OBJECT-TYPE
    SYNTAX      DisplayString
    MAX-ACCESS  read-only
    STATUS      current
    DESCRIPTION
	"The current value of the sixth output of the slave 6"
    ::= { slaveSixOutputCurrent 6}
slaveSixOutputCurrentSeven OBJECT-TYPE
    SYNTAX      DisplayString
    MAX-ACCESS  read-only
    STATUS      current
    DESCRIPTION
	"The current value of the seventh output of the slave 6"
    ::= { slaveSixOutputCurrent 7}
slaveSixOutputCurrentEight OBJECT-TYPE
    SYNTAX      DisplayString
    MAX-ACCESS  read-only
    STATUS      current
    DESCRIPTION
	"The current value of the eighth output of the slave 6"
    ::= { slaveSixOutputCurrent 8}
slaveSixOutputCurrentNine OBJECT-TYPE
    SYNTAX      DisplayString
    MAX-ACCESS  read-only
    STATUS      current
    DESCRIPTION
	"The current value of the nineth output of the slave 6"
    ::= { slaveSixOutputCurrent 9}
slaveSixOutputCurrentTen OBJECT-TYPE
    SYNTAX      DisplayString
    MAX-ACCESS  read-only
    STATUS      current
    DESCRIPTION
	"The current value of the tenth output of the slave 6"
    ::= { slaveSixOutputCurrent 10}
slaveSixOutputCurrentEleven OBJECT-TYPE
    SYNTAX      DisplayString
    MAX-ACCESS  read-only
    STATUS      current
    DESCRIPTION
	"The current value of the eleventh output of the slave 6"
    ::= { slaveSixOutputCurrent 11}
slaveSixOutputCurrentTwelve OBJECT-TYPE
    SYNTAX      DisplayString
    MAX-ACCESS  read-only
    STATUS      current
    DESCRIPTION
	"The current value of the twelfth output of the slave 6"
    ::= { slaveSixOutputCurrent 12}
slaveSixOutputCurrentThirteen OBJECT-TYPE
    SYNTAX      DisplayString
    MAX-ACCESS  read-only
    STATUS      current
    DESCRIPTION
	"The current value of the thirteenth output of the slave 6"
    ::= { slaveSixOutputCurrent 13}
slaveSixOutputCurrentFourteen OBJECT-TYPE
    SYNTAX      DisplayString
    MAX-ACCESS  read-only
    STATUS      current
    DESCRIPTION
	"The current value of the fourteenth output of the slave 6"
    ::= { slaveSixOutputCurrent 14}
slaveSixOutputCurrentFifteen OBJECT-TYPE
    SYNTAX      DisplayString
    MAX-ACCESS  read-only
    STATUS      current
    DESCRIPTION
	"The current value of the fifteenth output of the slave 6"
    ::= { slaveSixOutputCurrent 15}
slaveSixOutputCurrentSixteen OBJECT-TYPE
    SYNTAX      DisplayString
    MAX-ACCESS  read-only
    STATUS      current
    DESCRIPTION
	"The current value of the sixteenth output of the slave 6"
    ::= { slaveSixOutputCurrent 16}
slaveSixOutputCurrentSeventeen OBJECT-TYPE
    SYNTAX      DisplayString
    MAX-ACCESS  read-only
    STATUS      current
    DESCRIPTION
	"The current value of the seventeenth output of the slave 6"
    ::= { slaveSixOutputCurrent 17}
slaveSixOutputCurrentEighteen OBJECT-TYPE
    SYNTAX      DisplayString
    MAX-ACCESS  read-only
    STATUS      current
    DESCRIPTION
	"The current value of the eighteenth output of the slave 6"
    ::= { slaveSixOutputCurrent 18}
slaveSixOutputCurrentNineteen OBJECT-TYPE
    SYNTAX      DisplayString
    MAX-ACCESS  read-only
    STATUS      current
    DESCRIPTION
	"The current value of the nineteenth output of the slave 6"
    ::= { slaveSixOutputCurrent 19}
slaveSixOutputCurrentTwenty OBJECT-TYPE
    SYNTAX      DisplayString
    MAX-ACCESS  read-only
    STATUS      current
    DESCRIPTION
	"The current value of the twentieth output of the slave 6"
    ::= { slaveSixOutputCurrent 20}
slaveSixOutputCurrentTwentyOne OBJECT-TYPE
    SYNTAX      DisplayString
    MAX-ACCESS  read-only
    STATUS      current
    DESCRIPTION
	"The current value of the twenty-first output of the slave 6"
    ::= { slaveSixOutputCurrent 21}
slaveSixOutputCurrentTwentyTwo OBJECT-TYPE
    SYNTAX      DisplayString
    MAX-ACCESS  read-only
    STATUS      current
    DESCRIPTION
	"The current value of the twenty-second output of the slave 6"
    ::= { slaveSixOutputCurrent 22}
slaveSixOutputCurrentTwentyThree OBJECT-TYPE
    SYNTAX      DisplayString
    MAX-ACCESS  read-only
    STATUS      current
    DESCRIPTION
	"The current value of the twenty-third output of the slave 6"
    ::= { slaveSixOutputCurrent 23}
slaveSixOutputCurrentTwentyFour OBJECT-TYPE
    SYNTAX      DisplayString
    MAX-ACCESS  read-only
    STATUS      current
    DESCRIPTION
	"The current value of the twenty-fourth output of the slave 6"
    ::= { slaveSixOutputCurrent 24}

slaveSixOutputCurrentMin   OBJECT IDENTIFIER ::= { rpduSlaveSix 11}
slaveSixOutputCurrentMinOne OBJECT-TYPE
    SYNTAX      DisplayString
    MAX-ACCESS  read-only
    STATUS      current
    DESCRIPTION
	"The Min. current value of the first output of the slave 6"
    ::= { slaveSixOutputCurrentMin 1}
slaveSixOutputCurrentMinTwo OBJECT-TYPE
    SYNTAX      DisplayString
    MAX-ACCESS  read-only
    STATUS      current
    DESCRIPTION
	"The Min. current value of the second output of the slave 6"
    ::= { slaveSixOutputCurrentMin 2}
slaveSixOutputCurrentMinThree OBJECT-TYPE
    SYNTAX      DisplayString
    MAX-ACCESS  read-only
    STATUS      current
    DESCRIPTION
	"The Min. current value of the third output of the slave 6"
    ::= { slaveSixOutputCurrentMin 3}
slaveSixOutputCurrentMinFour OBJECT-TYPE
    SYNTAX      DisplayString
    MAX-ACCESS  read-only
    STATUS      current
    DESCRIPTION
	"The Min. current value of the fourth output of the slave 6"
    ::= { slaveSixOutputCurrentMin 4}
slaveSixOutputCurrentMinFive OBJECT-TYPE
    SYNTAX      DisplayString
    MAX-ACCESS  read-only
    STATUS      current
    DESCRIPTION
	"The Min. current value of the fifth output of the slave 6"
    ::= { slaveSixOutputCurrentMin 5}
slaveSixOutputCurrentMinSix OBJECT-TYPE
    SYNTAX      DisplayString
    MAX-ACCESS  read-only
    STATUS      current
    DESCRIPTION
	"The Min. current value of the sixth output of the slave 6"
    ::= { slaveSixOutputCurrentMin 6}
slaveSixOutputCurrentMinSeven OBJECT-TYPE
    SYNTAX      DisplayString
    MAX-ACCESS  read-only
    STATUS      current
    DESCRIPTION
	"The Min. current value of the seventh output of the slave 6"
    ::= { slaveSixOutputCurrentMin 7}
slaveSixOutputCurrentMinEight OBJECT-TYPE
    SYNTAX      DisplayString
    MAX-ACCESS  read-only
    STATUS      current
    DESCRIPTION
	"The Min. current value of the eighth output of the slave 6"
    ::= { slaveSixOutputCurrentMin 8}
slaveSixOutputCurrentMinNine OBJECT-TYPE
    SYNTAX      DisplayString
    MAX-ACCESS  read-only
    STATUS      current
    DESCRIPTION
	"The Min. current value of the nineth output of the slave 6"
    ::= { slaveSixOutputCurrentMin 9}
slaveSixOutputCurrentMinTen OBJECT-TYPE
    SYNTAX      DisplayString
    MAX-ACCESS  read-only
    STATUS      current
    DESCRIPTION
	"The Min. current value of the tenth output of the slave 6"
    ::= { slaveSixOutputCurrentMin 10}
slaveSixOutputCurrentMinEleven OBJECT-TYPE
    SYNTAX      DisplayString
    MAX-ACCESS  read-only
    STATUS      current
    DESCRIPTION
	"The Min. current value of the eleventh output of the slave 6"
    ::= { slaveSixOutputCurrentMin 11}
slaveSixOutputCurrentMinTwleve OBJECT-TYPE
    SYNTAX      DisplayString
    MAX-ACCESS  read-only
    STATUS      current
    DESCRIPTION
	"The Min. current value of the twelfth output of the slave 6"
    ::= { slaveSixOutputCurrentMin 12}
slaveSixOutputCurrentMinThirteen OBJECT-TYPE
    SYNTAX      DisplayString
    MAX-ACCESS  read-only
    STATUS      current
    DESCRIPTION
	"The Min. current value of the thirteenth output of the slave 6"
    ::= { slaveSixOutputCurrentMin 13}
slaveSixOutputCurrentMinFourteen OBJECT-TYPE
    SYNTAX      DisplayString
    MAX-ACCESS  read-only
    STATUS      current
    DESCRIPTION
	"The Min. current value of the fourteenth output of the slave 6"
    ::= { slaveSixOutputCurrentMin 14}
slaveSixOutputCurrentMinFifteen OBJECT-TYPE
    SYNTAX      DisplayString
    MAX-ACCESS  read-only
    STATUS      current
    DESCRIPTION
	"The Min. current value of the fifteenth output of the slave 6"
    ::= { slaveSixOutputCurrentMin 15}
slaveSixOutputCurrentMinSixteen OBJECT-TYPE
    SYNTAX      DisplayString
    MAX-ACCESS  read-only
    STATUS      current
    DESCRIPTION
	"The Min. current value of the sixteenth output of the slave 6"
    ::= { slaveSixOutputCurrentMin 16}
slaveSixOutputCurrentMinSeventeen OBJECT-TYPE
    SYNTAX      DisplayString
    MAX-ACCESS  read-only
    STATUS      current
    DESCRIPTION
	"The Min. current value of the seventeenth output of the slave 6"
    ::= { slaveSixOutputCurrentMin 17}
slaveSixOutputCurrentMinEighteen OBJECT-TYPE
    SYNTAX      DisplayString
    MAX-ACCESS  read-only
    STATUS      current
    DESCRIPTION
	"The Min. current value of the eighteenth output of the slave 6"
    ::= { slaveSixOutputCurrentMin 18}
slaveSixOutputCurrentMinNineteen OBJECT-TYPE
    SYNTAX      DisplayString
    MAX-ACCESS  read-only
    STATUS      current
    DESCRIPTION
	"The Min. current value of the nineteenth output of the slave 6"
    ::= { slaveSixOutputCurrentMin 19}
slaveSixOutputCurrentMinTwenty OBJECT-TYPE
    SYNTAX      DisplayString
    MAX-ACCESS  read-only
    STATUS      current
    DESCRIPTION
	"The Min. current value of the twentieth output of the slave 6"
    ::= { slaveSixOutputCurrentMin 20}
slaveSixOutputCurrentMinTwentyOne OBJECT-TYPE
    SYNTAX      DisplayString
    MAX-ACCESS  read-only
    STATUS      current
    DESCRIPTION
	"The Min. current value of the twentyth-first output of the slave 6"
    ::= { slaveSixOutputCurrentMin 21}
slaveSixOutputCurrentMinTwentyTwo OBJECT-TYPE
    SYNTAX      DisplayString
    MAX-ACCESS  read-only
    STATUS      current
    DESCRIPTION
	"The Min. current value of the twentyth-second output of the slave 6"
    ::= { slaveSixOutputCurrentMin 22}
slaveSixOutputCurrentMinTwentyThree OBJECT-TYPE
    SYNTAX      DisplayString
    MAX-ACCESS  read-only
    STATUS      current
    DESCRIPTION
	"The Min. current value of the twentyth-third output of the slave 6"
    ::= { slaveSixOutputCurrentMin 23}
slaveSixOutputCurrentMinTwentyFour OBJECT-TYPE
    SYNTAX      DisplayString
    MAX-ACCESS  read-only
    STATUS      current
    DESCRIPTION
	"The Min. current value of the twentyth-fourth output of the slave 6"
    ::= { slaveSixOutputCurrentMin 24}




slaveSixOutputCurrentMax   OBJECT IDENTIFIER ::= { rpduSlaveSix 12}
slaveSixOutputCurrentMaxOne OBJECT-TYPE
    SYNTAX      DisplayString
    MAX-ACCESS  read-only
    STATUS      current
    DESCRIPTION
	"The Max. current value of the first output of the slave 6"
    ::= { slaveSixOutputCurrentMax 1}
slaveSixOutputCurrentMaxTwo OBJECT-TYPE
    SYNTAX      DisplayString
    MAX-ACCESS  read-only
    STATUS      current
    DESCRIPTION
	"The Max. current value of the second output of the slave 6"
    ::= { slaveSixOutputCurrentMax 2}
slaveSixOutputCurrentMaxThree OBJECT-TYPE
    SYNTAX      DisplayString
    MAX-ACCESS  read-only
    STATUS      current
    DESCRIPTION
	"The Max. current value of the third output of the slave 6"
    ::= { slaveSixOutputCurrentMax 3}
slaveSixOutputCurrentMaxFour OBJECT-TYPE
    SYNTAX      DisplayString
    MAX-ACCESS  read-only
    STATUS      current
    DESCRIPTION
	"The Max. current value of the fourth output of the slave 6"
    ::= { slaveSixOutputCurrentMax 4}
slaveSixOutputCurrentMaxFive OBJECT-TYPE
    SYNTAX      DisplayString
    MAX-ACCESS  read-only
    STATUS      current
    DESCRIPTION
	"The Max. current value of the fifth output of the slave 6"
    ::= { slaveSixOutputCurrentMax 5}
slaveSixOutputCurrentMaxSix OBJECT-TYPE
    SYNTAX      DisplayString
    MAX-ACCESS  read-only
    STATUS      current
    DESCRIPTION
	"The Max. current value of the sixth output of the slave 6"
    ::= { slaveSixOutputCurrentMax 6}
slaveSixOutputCurrentMaxSeven OBJECT-TYPE
    SYNTAX      DisplayString
    MAX-ACCESS  read-only
    STATUS      current
    DESCRIPTION
	"The Max. current value of the seventh output of the slave 6"
    ::= { slaveSixOutputCurrentMax 7}
slaveSixOutputCurrentMaxEight OBJECT-TYPE
    SYNTAX      DisplayString
    MAX-ACCESS  read-only
    STATUS      current
    DESCRIPTION
	"The Max. current value of the eighth output of the slave 6"
    ::= { slaveSixOutputCurrentMax 8}
slaveSixOutputCurrentMaxNine OBJECT-TYPE
    SYNTAX      DisplayString
    MAX-ACCESS  read-only
    STATUS      current
    DESCRIPTION
	"The Max. current value of the nineth output of the slave 6"
    ::= { slaveSixOutputCurrentMax 9}
slaveSixOutputCurrentMaxTen OBJECT-TYPE
    SYNTAX      DisplayString
    MAX-ACCESS  read-only
    STATUS      current
    DESCRIPTION
	"The Max. current value of the tenth output of the slave 6"
    ::= { slaveSixOutputCurrentMax 10}
slaveSixOutputCurrentMaxEleven OBJECT-TYPE
    SYNTAX      DisplayString
    MAX-ACCESS  read-only
    STATUS      current
    DESCRIPTION
	"The Max. current value of the eleventh output of the slave 6"
    ::= { slaveSixOutputCurrentMax 11}
slaveSixOutputCurrentMaxTwleve OBJECT-TYPE
    SYNTAX      DisplayString
    MAX-ACCESS  read-only
    STATUS      current
    DESCRIPTION
	"The Max. current value of the twelfth output of the slave 6"
    ::= { slaveSixOutputCurrentMax 12}
slaveSixOutputCurrentMaxThirteen OBJECT-TYPE
    SYNTAX      DisplayString
    MAX-ACCESS  read-only
    STATUS      current
    DESCRIPTION
	"The Max. current value of the thirteenth output of the slave 6"
    ::= { slaveSixOutputCurrentMax 13}
slaveSixOutputCurrentMaxFourteen OBJECT-TYPE
    SYNTAX      DisplayString
    MAX-ACCESS  read-only
    STATUS      current
    DESCRIPTION
	"The Max. current value of the fourteenth output of the slave 6"
    ::= { slaveSixOutputCurrentMax 14}
slaveSixOutputCurrentMaxFifteen OBJECT-TYPE
    SYNTAX      DisplayString
    MAX-ACCESS  read-only
    STATUS      current
    DESCRIPTION
	"The Max. current value of the fifteenth output of the slave 6"
    ::= { slaveSixOutputCurrentMax 15}
slaveSixOutputCurrentMaxSixteen OBJECT-TYPE
    SYNTAX      DisplayString
    MAX-ACCESS  read-only
    STATUS      current
    DESCRIPTION
	"The Max. current value of the sixteenth output of the slave 6"
    ::= { slaveSixOutputCurrentMax 16}
slaveSixOutputCurrentMaxSeventeen OBJECT-TYPE
    SYNTAX      DisplayString
    MAX-ACCESS  read-only
    STATUS      current
    DESCRIPTION
	"The Max. current value of the seventeenth output of the slave 6"
    ::= { slaveSixOutputCurrentMax 17}
slaveSixOutputCurrentMaxEighteen OBJECT-TYPE
    SYNTAX      DisplayString
    MAX-ACCESS  read-only
    STATUS      current
    DESCRIPTION
	"The Max. current value of the eighteenth output of the slave 6"
    ::= { slaveSixOutputCurrentMax 18}
slaveSixOutputCurrentMaxNineteen OBJECT-TYPE
    SYNTAX      DisplayString
    MAX-ACCESS  read-only
    STATUS      current
    DESCRIPTION
	"The Max. current value of the nineteenth output of the slave 6"
    ::= { slaveSixOutputCurrentMax 19}
slaveSixOutputCurrentMaxTwenty OBJECT-TYPE
    SYNTAX      DisplayString
    MAX-ACCESS  read-only
    STATUS      current
    DESCRIPTION
	"The Max. current value of the twentieth output of the slave 6"
    ::= { slaveSixOutputCurrentMax 20}
slaveSixOutputCurrentMaxTwentyOne OBJECT-TYPE
    SYNTAX      DisplayString
    MAX-ACCESS  read-only
    STATUS      current
    DESCRIPTION
	"The Max. current value of the twenty-first output of the slave 6"
    ::= { slaveSixOutputCurrentMax 21}
slaveSixOutputCurrentMaxTwentyTwo OBJECT-TYPE
    SYNTAX      DisplayString
    MAX-ACCESS  read-only
    STATUS      current
    DESCRIPTION
	"The Max. current value of the twenty-second output of the slave 6"
    ::= { slaveSixOutputCurrentMax 22}
slaveSixOutputCurrentMaxTwentyThree OBJECT-TYPE
    SYNTAX      DisplayString
    MAX-ACCESS  read-only
    STATUS      current
    DESCRIPTION
	"The Max. current value of the twenty-third output of the slave 6"
    ::= { slaveSixOutputCurrentMax 23}
slaveSixOutputCurrentMaxTwentyFour OBJECT-TYPE
    SYNTAX      DisplayString
    MAX-ACCESS  read-only
    STATUS      current
    DESCRIPTION
	"The Max. current value of the twenty-fourth output of the slave 6"
    ::= { slaveSixOutputCurrentMax 24}


slaveSixOutputCurrentEnergy  OBJECT IDENTIFIER ::= { rpduSlaveSix 13}
slaveSixOutputCurrentEnergyOne OBJECT-TYPE
    SYNTAX	DisplayString
    MAX-ACCESS	read-only
    STATUS	current
    DESCRIPTION
	"The energy value of the first output of the slave 6"
    ::={slaveSixOutputCurrentEnergy 1}
slaveSixOutputCurrentEnergyTwo OBJECT-TYPE
    SYNTAX	DisplayString
    MAX-ACCESS	read-only
    STATUS	current
    DESCRIPTION
	"The energy value of the second output of the slave 6"
    ::={slaveSixOutputCurrentEnergy 2}
slaveSixOutputCurrentEnergyThree OBJECT-TYPE
    SYNTAX	DisplayString
    MAX-ACCESS	read-only
    STATUS	current
    DESCRIPTION
	"The energy value of the third output of the slave 6"
    ::={slaveSixOutputCurrentEnergy 3}
slaveSixOutputCurrentEnergyFour OBJECT-TYPE
    SYNTAX	DisplayString
    MAX-ACCESS	read-only
    STATUS	current
    DESCRIPTION
	"The energy value of the fourth output of the slave 6"
    ::={slaveSixOutputCurrentEnergy 4}
slaveSixOutputCurrentEnergyFive OBJECT-TYPE
    SYNTAX	DisplayString
    MAX-ACCESS	read-only
    STATUS	current
    DESCRIPTION
	"The energy value of the fifth output of the slave 6"
    ::={slaveSixOutputCurrentEnergy 5}
slaveSixOutputCurrentEnergySix OBJECT-TYPE
    SYNTAX	DisplayString
    MAX-ACCESS	read-only
    STATUS	current
    DESCRIPTION
	"The energy value of the sixth output of the slave 6"
    ::={slaveSixOutputCurrentEnergy 6}
slaveSixOutputCurrentEnergySeven OBJECT-TYPE
    SYNTAX	DisplayString
    MAX-ACCESS	read-only
    STATUS	current
    DESCRIPTION
	"The energy value of the seventh output of the slave 6"
    ::={slaveSixOutputCurrentEnergy 7}
slaveSixOutputCurrentEnergyEight OBJECT-TYPE
    SYNTAX	DisplayString
    MAX-ACCESS	read-only
    STATUS	current
    DESCRIPTION
	"The energy value of the eighth output of the slave 6"
    ::={slaveSixOutputCurrentEnergy 8}
slaveSixOutputCurrentEnergyNine OBJECT-TYPE
    SYNTAX	DisplayString
    MAX-ACCESS	read-only
    STATUS	current
    DESCRIPTION
	"The energy value of the nineth output of the slave 6"
    ::={slaveSixOutputCurrentEnergy 9}
slaveSixOutputCurrentEnergyTen OBJECT-TYPE
    SYNTAX	DisplayString
    MAX-ACCESS	read-only
    STATUS	current
    DESCRIPTION
	"The energy value of the tenth output of the slave 6"
    ::={slaveSixOutputCurrentEnergy 10}
slaveSixOutputCurrentEnergyEleven OBJECT-TYPE
    SYNTAX	DisplayString
    MAX-ACCESS	read-only
    STATUS	current
    DESCRIPTION
	"The energy value of the eleventh output of the slave 6"
    ::={slaveSixOutputCurrentEnergy 11}
slaveSixOutputCurrentEnergyTwelve OBJECT-TYPE
    SYNTAX	DisplayString
    MAX-ACCESS	read-only
    STATUS	current
    DESCRIPTION
	"The energy value of the twelfth output of the slave 6"
    ::={slaveSixOutputCurrentEnergy 12}
slaveSixOutputCurrentEnergyThirteen OBJECT-TYPE
    SYNTAX	DisplayString
    MAX-ACCESS	read-only
    STATUS	current
    DESCRIPTION
	"The energy value of the thirteenth output of the slave 6"
    ::={slaveSixOutputCurrentEnergy 13}
slaveSixOutputCurrentEnergyFourteen OBJECT-TYPE
    SYNTAX	DisplayString
    MAX-ACCESS	read-only
    STATUS	current
    DESCRIPTION
	"The energy value of the fourteenth output of the slave 6"
    ::={slaveSixOutputCurrentEnergy 14}
slaveSixOutputCurrentEnergyFifteen OBJECT-TYPE
    SYNTAX	DisplayString
    MAX-ACCESS	read-only
    STATUS	current
    DESCRIPTION
	"The energy value of the fifteenth output of the slave 6"
    ::={slaveSixOutputCurrentEnergy 15}
slaveSixOutputCurrentEnergySixteen OBJECT-TYPE
    SYNTAX	DisplayString
    MAX-ACCESS	read-only
    STATUS	current
    DESCRIPTION
	"The energy value of the sixteenth output of the slave 6"
    ::={slaveSixOutputCurrentEnergy 16}
slaveSixOutputCurrentEnergySeventeen OBJECT-TYPE
    SYNTAX	DisplayString
    MAX-ACCESS	read-only
    STATUS	current
    DESCRIPTION
	"The energy value of the seventeenth output of the slave 6"
    ::={slaveSixOutputCurrentEnergy 17}
slaveSixOutputCurrentEnergyEighteen OBJECT-TYPE
    SYNTAX	DisplayString
    MAX-ACCESS	read-only
    STATUS	current
    DESCRIPTION
	"The energy value of the eighteenth output of the slave 6"
    ::={slaveSixOutputCurrentEnergy 18}
slaveSixOutputCurrentEnergyNineteen OBJECT-TYPE
    SYNTAX	DisplayString
    MAX-ACCESS	read-only
    STATUS	current
    DESCRIPTION
	"The energy value of the nineteenth output of the slave 6"
    ::={slaveSixOutputCurrentEnergy 19}
slaveSixOutputCurrentEnergyTwenty OBJECT-TYPE
    SYNTAX	DisplayString
    MAX-ACCESS	read-only
    STATUS	current
    DESCRIPTION
	"The energy value of the twentieth output of the slave 6"
    ::={slaveSixOutputCurrentEnergy 20}
slaveSixOutputCurrentEnergyTwentyOne OBJECT-TYPE
    SYNTAX	DisplayString
    MAX-ACCESS	read-only
    STATUS	current
    DESCRIPTION
	"The energy value of the twenty-first output of the slave 6"
    ::={slaveSixOutputCurrentEnergy 21}
slaveSixOutputCurrentEnergyTwentyTwo OBJECT-TYPE
    SYNTAX	DisplayString
    MAX-ACCESS	read-only
    STATUS	current
    DESCRIPTION
	"The energy value of the twenty-second output of the slave 6"
    ::={slaveSixOutputCurrentEnergy 22}
slaveSixOutputCurrentEnergyTwentyThree OBJECT-TYPE
    SYNTAX	DisplayString
    MAX-ACCESS	read-only
    STATUS	current
    DESCRIPTION
	"The energy value of the twenty-third output of the slave 6"
    ::={slaveSixOutputCurrentEnergy 23}
slaveSixOutputCurrentEnergyTwentyFour OBJECT-TYPE
    SYNTAX	DisplayString
    MAX-ACCESS	read-only
    STATUS	current
    DESCRIPTION
	"The energy value of the twenty-fourth output of the slave 6"
    ::={slaveSixOutputCurrentEnergy 24}

-------------------------------Slave7 --------------------------------------------- 
rpduDeviceEight OBJECT IDENTIFIER ::= { rpdu 8}
rpduSlaveSeven OBJECT IDENTIFIER ::= { rpduDeviceEight 1}

slaveSevenName OBJECT-TYPE
    SYNTAX      DisplayString
    MAX-ACCESS  read-write
    STATUS      current
    DESCRIPTION
	"This is the eighth device."
    ::= { rpduSlaveSeven 1}
    
slaveSevenType OBJECT-TYPE
    SYNTAX      DisplayString
    MAX-ACCESS  read-only
    STATUS      current
    DESCRIPTION
	"This is device type "
    ::= { rpduSlaveSeven 2}
    
slaveSevenOutputNumber OBJECT-TYPE 
    SYNTAX      Integer32
    MAX-ACCESS  read-only
    STATUS      current
    DESCRIPTION
	"This is the output quantity"
::= { rpduSlaveSeven 7}
    
slaveSevenLineOne OBJECT IDENTIFIER ::= { rpduSlaveSeven 3}
slaveSevenLineOnePower OBJECT-TYPE
    SYNTAX      DisplayString
    MAX-ACCESS  read-only
    STATUS      current
    DESCRIPTION
	"The power of phase one"
    ::= { slaveSevenLineOne 1}
slaveSevenLineOnePF OBJECT-TYPE
    SYNTAX      DisplayString
    MAX-ACCESS  read-only
    STATUS      current
    DESCRIPTION
	"The power factor of phase one"
    ::= { slaveSevenLineOne 2}
    
slaveSevenLineOneEnergy OBJECT-TYPE
    SYNTAX      DisplayString
    MAX-ACCESS  read-only
    STATUS      current
    DESCRIPTION
	"The energy of phase one"
    ::= { slaveSevenLineOne 3}
slaveSevenLineOneCurrent OBJECT-TYPE
    SYNTAX      DisplayString
    MAX-ACCESS  read-only
    STATUS      current
    DESCRIPTION
	"The current of phase one"
    ::= { slaveSevenLineOne 4}
slaveSevenLineOneVoltage OBJECT-TYPE
    SYNTAX      Integer32
    MAX-ACCESS  read-only
    STATUS      current
    DESCRIPTION
	"The voltage of phase one"
    ::= { slaveSevenLineOne 5}
slaveSevenLineOneCurrentMin OBJECT-TYPE
    SYNTAX      DisplayString
    MAX-ACCESS  read-only
    STATUS      current
    DESCRIPTION
	"The Min. current value of phase one"
	::= { slaveSevenLineOne 6}
slaveSevenLineOneCurrentMax OBJECT-TYPE
    SYNTAX      DisplayString
    MAX-ACCESS  read-only
    STATUS      current
    DESCRIPTION
	"The Max. current value of phase one"
    ::= { slaveSevenLineOne 7}
    
slaveSevenLineOneVoltageMin OBJECT-TYPE
    SYNTAX      Integer32
    MAX-ACCESS  read-only
    STATUS      current
    DESCRIPTION
	"The Min. voltage value of phase one"
    ::= { slaveSevenLineOne 8}
    
slaveSevenLineOneVoltageMax OBJECT-TYPE
    SYNTAX      Integer32
    MAX-ACCESS  read-only
    STATUS      current
    DESCRIPTION
	"The Max. voltage value of phase one"
    ::= { slaveSevenLineOne 9}


slaveSevenLineTwo OBJECT IDENTIFIER ::= { rpduSlaveSeven 4}
slaveSevenLineTwoPower OBJECT-TYPE
    SYNTAX      DisplayString
    MAX-ACCESS  read-only
    STATUS      current
    DESCRIPTION
	"The power of phase two"
    ::= { slaveSevenLineTwo 1}

slaveSevenLineTwoPF OBJECT-TYPE
    SYNTAX      DisplayString
    MAX-ACCESS  read-only
    STATUS      current
    DESCRIPTION
	"The power factor of phase two"   
    ::= { slaveSevenLineTwo 2}
    
slaveSevenLineTwoEnergy OBJECT-TYPE
    SYNTAX      DisplayString
    MAX-ACCESS  read-only
    STATUS      current
    DESCRIPTION
	"The energy of phase two"
    ::= { slaveSevenLineTwo 3}
slaveSevenLineTwoCurrent OBJECT-TYPE           
    SYNTAX      DisplayString 
    MAX-ACCESS  read-only
    STATUS      current
    DESCRIPTION
	"The current of phase two"
    ::= { slaveSevenLineTwo 4}
slaveSevenLineTwoVoltage OBJECT-TYPE
    SYNTAX      Integer32
    MAX-ACCESS  read-only
    STATUS      current
    DESCRIPTION
	"The voltage of phase two"
    ::= { slaveSevenLineTwo 5}
slaveSevenLineTwoCurrentMin OBJECT-TYPE
    SYNTAX      DisplayString
    MAX-ACCESS  read-only
    STATUS      current
    DESCRIPTION
	"The Min. current value of phase two"
    ::= { slaveSevenLineTwo 6}
slaveSevenLineTwoCurrentMax OBJECT-TYPE
    SYNTAX      DisplayString
    MAX-ACCESS  read-only
    STATUS      current
    DESCRIPTION
	"The Max. current value of phase two"
    ::= { slaveSevenLineTwo 7}
    
slaveSevenLineTwoVoltageMin OBJECT-TYPE
    SYNTAX      Integer32
    MAX-ACCESS  read-only
    STATUS      current
    DESCRIPTION
	"The Min. voltage value of phase two"
    ::= { slaveSevenLineTwo 8}
    
slaveSevenLineTwoVoltageMax OBJECT-TYPE
    SYNTAX      Integer32
    MAX-ACCESS  read-only
    STATUS      current
    DESCRIPTION
	"The Max. voltage value of phase two"
    ::= { slaveSevenLineTwo 9}



slaveSevenLineThree OBJECT IDENTIFIER ::= { rpduSlaveSeven 5}
slaveSevenLineThreePower OBJECT-TYPE
    SYNTAX      DisplayString
    MAX-ACCESS  read-only
    STATUS      current
    DESCRIPTION
	"The power of phase three"
    ::= { slaveSevenLineThree 1}

slaveSevenLineThreePF OBJECT-TYPE
    SYNTAX      DisplayString
    MAX-ACCESS  read-only
    STATUS      current
    DESCRIPTION
	"The power factor of phase three"     
    ::= { slaveSevenLineThree 2}
    
slaveSevenLineThreeEnergy OBJECT-TYPE
    SYNTAX      DisplayString
    MAX-ACCESS  read-only
    STATUS      current
    DESCRIPTION
	"The energy of phase three"
    ::= { slaveSevenLineThree 3}
slaveSevenLineThreeCurrent OBJECT-TYPE
    SYNTAX      DisplayString
    MAX-ACCESS  read-only
    STATUS      current
    DESCRIPTION
	"The current of phase three"
    ::= { slaveSevenLineThree 4}
slaveSevenLineThreeVoltage OBJECT-TYPE
    SYNTAX      Integer32
    MAX-ACCESS  read-only
    STATUS      current
    DESCRIPTION
	"The voltage of phase three"
    ::= { slaveSevenLineThree 5}
slaveSevenLineThreeCurrentMin OBJECT-TYPE
    SYNTAX      DisplayString
    MAX-ACCESS  read-only
    STATUS      current
    DESCRIPTION
	"The Min. current value of phase three"
    ::= { slaveSevenLineThree 6}
slaveSevenLineThreeCurrentMax OBJECT-TYPE
    SYNTAX      DisplayString
    MAX-ACCESS  read-only
    STATUS      current
    DESCRIPTION
	"The Max. current value of phase three"
    ::= { slaveSevenLineThree 7}
    
slaveSevenLineThreeVoltageMin OBJECT-TYPE
    SYNTAX      Integer32
    MAX-ACCESS  read-only
    STATUS      current
    DESCRIPTION
	"The Min. voltage value of phase three"
    ::= { slaveSevenLineThree 8}
    
slaveSevenLineThreeVoltageMax OBJECT-TYPE
    SYNTAX      Integer32
    MAX-ACCESS  read-only
    STATUS      current
    DESCRIPTION
	"The Max. voltage value of phase three"
    ::= { slaveSevenLineThree 9}


slaveSevenSensor OBJECT IDENTIFIER ::= { rpduSlaveSeven 6}
slaveSevenTempOne OBJECT-TYPE
    SYNTAX      Integer32
    MAX-ACCESS  read-only
    STATUS      current
    DESCRIPTION
	"The first temperature sensor of slave 7"
    ::= { slaveSevenSensor 1}
slaveSevenTempTwo OBJECT-TYPE
    SYNTAX      Integer32
    MAX-ACCESS  read-only
    STATUS      current
    DESCRIPTION
	"The second temperature sensor of slave 7"
    ::= { slaveSevenSensor 2}
slaveSevenTempThree OBJECT-TYPE
    SYNTAX      Integer32
    MAX-ACCESS  read-only
    STATUS      current
    DESCRIPTION
	"The third temperature sensor of slave 7"
    ::= { slaveSevenSensor 3}
slaveSevenTempFour OBJECT-TYPE
    SYNTAX      Integer32
    MAX-ACCESS  read-only
    STATUS      current
    DESCRIPTION
	"The fourth temperature sensor of slave 7"
    ::= { slaveSevenSensor 4}
slaveSevenHumOne OBJECT-TYPE
    SYNTAX      Integer32
    MAX-ACCESS  read-only
    STATUS      current
    DESCRIPTION
	"The first humidity sensor of slave 7"
    ::= { slaveSevenSensor 5}
slaveSevenHumTwo OBJECT-TYPE
    SYNTAX      Integer32
    MAX-ACCESS  read-only
    STATUS      current
    DESCRIPTION
	"The second humidity sensor of slave 7"
    ::= { slaveSevenSensor 6}
slaveSevenHumThree OBJECT-TYPE
    SYNTAX      Integer32
    MAX-ACCESS  read-only
    STATUS      current
    DESCRIPTION
	"The third humidity sensor of slave 7"
    ::= { slaveSevenSensor 7}
slaveSevenHumFour OBJECT-TYPE
    SYNTAX      Integer32
    MAX-ACCESS  read-only
    STATUS      current
    DESCRIPTION
	"The fourth humidity sensor of slave 7"
    ::= { slaveSevenSensor 8}
slaveSevenDoorOne OBJECT-TYPE
    SYNTAX      DisplayString
    MAX-ACCESS  read-only
    STATUS      current
    DESCRIPTION
	"The first door sensor of slave 7"    
    ::= { slaveSevenSensor 9}
slaveSevenDoorTwo OBJECT-TYPE
    SYNTAX      DisplayString
    MAX-ACCESS  read-only
    STATUS      current
    DESCRIPTION
	"The second door sensor of slave 7"  
    ::= { slaveSevenSensor 10}
slaveSevenSmoke OBJECT-TYPE
    SYNTAX      DisplayString
    MAX-ACCESS  read-only
    STATUS      current
    DESCRIPTION
	"The smoke sensor of slave 7"
    ::= { slaveSevenSensor 11}
slaveSevenWater OBJECT-TYPE
    SYNTAX      DisplayString
    MAX-ACCESS  read-only
    STATUS      current
    DESCRIPTION
	"The water sensor of slave 7"
    ::= { slaveSevenSensor 12}


	
        
slaveSevenOutputName OBJECT IDENTIFIER ::= { rpduSlaveSeven 8}
slaveSevenOutputNameOne OBJECT-TYPE
    SYNTAX      DisplayString
    MAX-ACCESS  read-write
    STATUS      current
    DESCRIPTION
	"The first output name of slave 7"
    ::= { slaveSevenOutputName 1}

slaveSevenOutputNameTwo OBJECT-TYPE
    SYNTAX      DisplayString
    MAX-ACCESS  read-write
    STATUS      current
    DESCRIPTION
	"The second output name of slave 7"
    ::= { slaveSevenOutputName 2}
slaveSevenOutputNameThree OBJECT-TYPE
    SYNTAX      DisplayString
    MAX-ACCESS  read-write
    STATUS      current
    DESCRIPTION
	"The third output name of slave 7"
    ::= { slaveSevenOutputName 3}
slaveSevenOutputNameFour OBJECT-TYPE
    SYNTAX      DisplayString
    MAX-ACCESS  read-write
    STATUS      current
    DESCRIPTION
	"The fourth output name of slave 7"
    ::= { slaveSevenOutputName 4}
slaveSevenOutputNameFive OBJECT-TYPE
    SYNTAX      DisplayString
    MAX-ACCESS  read-write
    STATUS      current
    DESCRIPTION
	"The fifth output name of slave 7"
    ::= { slaveSevenOutputName 5}
slaveSevenOutputNameSix OBJECT-TYPE
    SYNTAX      DisplayString
    MAX-ACCESS  read-write
    STATUS      current
    DESCRIPTION
	"The sixth output name of slave 7"
    ::= { slaveSevenOutputName 6}
slaveSevenOutputNameSeven OBJECT-TYPE
    SYNTAX      DisplayString
    MAX-ACCESS  read-write
    STATUS      current
    DESCRIPTION
	"The seventh output name of slave 7"
    ::= { slaveSevenOutputName 7}
slaveSevenOutputNameEight OBJECT-TYPE
    SYNTAX      DisplayString
    MAX-ACCESS  read-write
    STATUS      current
    DESCRIPTION
	"The eighth output name of slave 7"
    ::= { slaveSevenOutputName 8}
slaveSevenOutputNameNine OBJECT-TYPE
    SYNTAX      DisplayString
    MAX-ACCESS  read-write
    STATUS      current
    DESCRIPTION
	"The nineth output name of slave 7"
    ::= { slaveSevenOutputName 9}
slaveSevenOutputNameTen OBJECT-TYPE
    SYNTAX      DisplayString
    MAX-ACCESS  read-write
    STATUS      current
    DESCRIPTION
	"The tenth output name of slave 7"
    ::= { slaveSevenOutputName 10}
slaveSevenOutputNameEleven OBJECT-TYPE
    SYNTAX      DisplayString
    MAX-ACCESS  read-write
    STATUS      current
    DESCRIPTION
	"The eleventh output name of slave 7"
    ::= { slaveSevenOutputName 11}
slaveSevenOutputNameTwelve OBJECT-TYPE
    SYNTAX      DisplayString
    MAX-ACCESS  read-write
    STATUS      current
    DESCRIPTION
	"The twelfth output name of slave 7"
    ::= { slaveSevenOutputName 12}
slaveSevenOutputNameThirteen OBJECT-TYPE
    SYNTAX      DisplayString
    MAX-ACCESS  read-write
    STATUS      current
    DESCRIPTION
	"The thirteenth output name of slave 7"
    ::= { slaveSevenOutputName 13}
slaveSevenOutputNameFourteen OBJECT-TYPE
    SYNTAX      DisplayString
    MAX-ACCESS  read-write
    STATUS      current
    DESCRIPTION
	"The fourteenth output name of slave 7"
    ::= { slaveSevenOutputName 14}
slaveSevenOutputNameFifteen OBJECT-TYPE
    SYNTAX      DisplayString
    MAX-ACCESS  read-write
    STATUS      current
    DESCRIPTION
	"The fifteenth output name of slave 7"
    ::= { slaveSevenOutputName 15}
slaveSevenOutputNameSixteen OBJECT-TYPE
    SYNTAX      DisplayString
    MAX-ACCESS  read-write
    STATUS      current
    DESCRIPTION
	"The sixteenth output name of slave 7"
    ::= { slaveSevenOutputName 16}
slaveSevenOutputNameSeventeen OBJECT-TYPE
    SYNTAX      DisplayString
    MAX-ACCESS  read-write
    STATUS      current
    DESCRIPTION
	"The seventeenth output name of slave 7"
    ::= { slaveSevenOutputName 17}
slaveSevenOutputNameEighteen OBJECT-TYPE
    SYNTAX      DisplayString
    MAX-ACCESS  read-write
    STATUS      current
    DESCRIPTION
	"The eighteenh output name of slave 7"
    ::= { slaveSevenOutputName 18}
slaveSevenOutputNameNineteen OBJECT-TYPE
    SYNTAX      DisplayString
    MAX-ACCESS  read-write
    STATUS      current
    DESCRIPTION
	"The nineteenth output name of slave 7"
    ::= { slaveSevenOutputName 19}
slaveSevenOutputNameTwenty OBJECT-TYPE
    SYNTAX      DisplayString
    MAX-ACCESS  read-write
    STATUS      current
    DESCRIPTION
	"The twentieth output name of slave 7"
    ::= { slaveSevenOutputName 20}
slaveSevenOutputNameTwentyOne OBJECT-TYPE
    SYNTAX      DisplayString
    MAX-ACCESS  read-write
    STATUS      current
    DESCRIPTION
	"The twenty-first output name of slave 7"
    ::= { slaveSevenOutputName 21}
slaveSevenOutputNameTwentyTwo OBJECT-TYPE
    SYNTAX      DisplayString
    MAX-ACCESS  read-write
    STATUS      current
    DESCRIPTION
	"The twenty-second output name of slave 7"
    ::= { slaveSevenOutputName 22}
slaveSevenOutputNameTwentyThree OBJECT-TYPE
    SYNTAX      DisplayString
    MAX-ACCESS  read-write
    STATUS      current
    DESCRIPTION
	"The twenty-third output name of slave 7"
    ::= { slaveSevenOutputName 23}
slaveSevenOutputNameTwentyFour OBJECT-TYPE
    SYNTAX      DisplayString
    MAX-ACCESS  read-write
    STATUS      current
    DESCRIPTION
	"The twenty-fourth output name of slave 7"
    ::= { slaveSevenOutputName 24}


    
slaveSevenOutputStatus OBJECT IDENTIFIER ::= { rpduSlaveSeven 9}

slaveSevenOutputStatusOne OBJECT-TYPE
    SYNTAX      DisplayString
    MAX-ACCESS  read-write
    STATUS      current
    DESCRIPTION
	"The first output status of slave 7"
    ::= { slaveSevenOutputStatus 1}
slaveSevenOutputStatusTwo OBJECT-TYPE
    SYNTAX      DisplayString
    MAX-ACCESS  read-write
    STATUS      current
    DESCRIPTION
	"The second output status of slave 7"
    ::= { slaveSevenOutputStatus 2}

slaveSevenOutputStatusThree OBJECT-TYPE
    SYNTAX      DisplayString
    MAX-ACCESS  read-write
    STATUS      current
    DESCRIPTION
	"The third output status of slave 7"
    ::= { slaveSevenOutputStatus 3}
slaveSevenOutputStatusFour OBJECT-TYPE
    SYNTAX      DisplayString
    MAX-ACCESS  read-write
    STATUS      current
    DESCRIPTION
	"The fourth output status of slave 7"
    ::= { slaveSevenOutputStatus 4}
slaveSevenOutputStatusFive OBJECT-TYPE
    SYNTAX      DisplayString
    MAX-ACCESS  read-write
    STATUS      current
    DESCRIPTION
	"The fifth output status of slave 7"
    ::= { slaveSevenOutputStatus 5}
slaveSevenOutputStatusSix OBJECT-TYPE
    SYNTAX      DisplayString
    MAX-ACCESS  read-write
    STATUS      current
    DESCRIPTION
	"The sixth output status of slave 7"
    ::= { slaveSevenOutputStatus 6}
slaveSevenOutputStatusSeven OBJECT-TYPE
    SYNTAX      DisplayString
    MAX-ACCESS  read-write
    STATUS      current
    DESCRIPTION
	"The seventh output status of slave 7"
    ::= { slaveSevenOutputStatus 7}
slaveSevenOutputStatusEight OBJECT-TYPE
    SYNTAX      DisplayString
    MAX-ACCESS  read-write
    STATUS      current
    DESCRIPTION
	"The eighth output status of slave 7"
    ::= { slaveSevenOutputStatus 8}
slaveSevenOutputStatusNine OBJECT-TYPE
    SYNTAX      DisplayString
    MAX-ACCESS  read-write
    STATUS      current
    DESCRIPTION
	"The nineth output status of slave 7"
    ::= { slaveSevenOutputStatus 9}
slaveSevenOutputStatusTen OBJECT-TYPE
    SYNTAX      DisplayString
    MAX-ACCESS  read-write
    STATUS      current
    DESCRIPTION
	"The tenth output status of slave 7"
    ::= { slaveSevenOutputStatus 10}
slaveSevenOutputStatusEleven OBJECT-TYPE
    SYNTAX      DisplayString
    MAX-ACCESS  read-write
    STATUS      current
    DESCRIPTION
	"The eleventh output status of slave 7"
    ::= { slaveSevenOutputStatus 11}
slaveSevenOutputStatusTwelve OBJECT-TYPE
    SYNTAX      DisplayString
    MAX-ACCESS  read-write
    STATUS      current
    DESCRIPTION
	"The twelfth output status of slave 7"
    ::= { slaveSevenOutputStatus 12}
slaveSevenOutputStatusThirteen OBJECT-TYPE
    SYNTAX      DisplayString
    MAX-ACCESS  read-write
    STATUS      current
    DESCRIPTION
	"The thirteenth output status of slave 7"
    ::= { slaveSevenOutputStatus 13}
slaveSevenOutputStatusFourteen OBJECT-TYPE
    SYNTAX      DisplayString
    MAX-ACCESS  read-write
    STATUS      current
    DESCRIPTION
	"The fourteenth output status of slave 7"
    ::= { slaveSevenOutputStatus 14}
slaveSevenOutputStatusFifteen OBJECT-TYPE
    SYNTAX      DisplayString
    MAX-ACCESS  read-write
    STATUS      current
    DESCRIPTION
	"The fifteenth output status of slave 7"
    ::= { slaveSevenOutputStatus 15}
slaveSevenOutputStatusSixteen OBJECT-TYPE
    SYNTAX      DisplayString
    MAX-ACCESS  read-write
    STATUS      current
    DESCRIPTION
	"The sixteenth output status of slave 7"
    ::= { slaveSevenOutputStatus 16}
slaveSevenOutputStatusSeventeen OBJECT-TYPE
    SYNTAX      DisplayString
    MAX-ACCESS  read-write
    STATUS      current
    DESCRIPTION
	"The seventeenth output status of slave 7"
    ::= { slaveSevenOutputStatus 17}
slaveSevenOutputStatusEighteen OBJECT-TYPE
    SYNTAX      DisplayString
    MAX-ACCESS  read-write
    STATUS      current
    DESCRIPTION
	"The eighteenth output status of slave 7"
    ::= { slaveSevenOutputStatus 18}
slaveSevenOutputStatusNineteen OBJECT-TYPE
    SYNTAX      DisplayString
    MAX-ACCESS  read-write
    STATUS      current
    DESCRIPTION
	"The nineteenth output status of slave 7"
    ::= { slaveSevenOutputStatus 19}
slaveSevenOutputStatusTwenty OBJECT-TYPE
    SYNTAX      DisplayString
    MAX-ACCESS  read-write
    STATUS      current
    DESCRIPTION
	"The twentieth output status of slave 7"
    ::= { slaveSevenOutputStatus 20}
slaveSevenOutputStatusTwentyOne OBJECT-TYPE
    SYNTAX      DisplayString
    MAX-ACCESS  read-write
    STATUS      current
    DESCRIPTION
	"The twenty-first output status of slave 7"
    ::= { slaveSevenOutputStatus 21}
slaveSevenOutputStatusTwentyTwo OBJECT-TYPE
    SYNTAX      DisplayString
    MAX-ACCESS  read-write
    STATUS      current
    DESCRIPTION
	"The twenty-second output status of slave 7"
    ::= { slaveSevenOutputStatus 22}
slaveSevenOutputStatusTwentyThree OBJECT-TYPE
    SYNTAX      DisplayString
    MAX-ACCESS  read-write
    STATUS      current
    DESCRIPTION
	"The twenty-third output status of slave 7"
    ::= { slaveSevenOutputStatus 23}
slaveSevenOutputStatusTwentyFour OBJECT-TYPE
    SYNTAX      DisplayString
    MAX-ACCESS  read-write
    STATUS      current
    DESCRIPTION
	"The twenty-fourth output status of slave 7"
    ::= { slaveSevenOutputStatus 24}

slaveSevenOutputCurrent   OBJECT IDENTIFIER ::= { rpduSlaveSeven 10}
slaveSevenOutputCurrentOne OBJECT-TYPE
    SYNTAX      DisplayString
    MAX-ACCESS  read-only
    STATUS      current
    DESCRIPTION
	"The current value of the first output of the slave 7"
    ::= { slaveSevenOutputCurrent 1}
slaveSevenOutputCurrentTwo OBJECT-TYPE
    SYNTAX      DisplayString
    MAX-ACCESS  read-only
    STATUS      current
    DESCRIPTION
	"The current value of the second output of the slave 7"
    ::= { slaveSevenOutputCurrent 2}
slaveSevenOutputCurrentThree OBJECT-TYPE
    SYNTAX      DisplayString
    MAX-ACCESS  read-only
    STATUS      current
    DESCRIPTION
	"The current value of the third output of the slave 7"
    ::= { slaveSevenOutputCurrent 3}
slaveSevenOutputCurrentFour OBJECT-TYPE
    SYNTAX      DisplayString
    MAX-ACCESS  read-only
    STATUS      current
    DESCRIPTION
	"The current value of the fourth output of the slave 7"
    ::= { slaveSevenOutputCurrent 4}
slaveSevenOutputCurrentFive OBJECT-TYPE
    SYNTAX      DisplayString
    MAX-ACCESS  read-only
    STATUS      current
    DESCRIPTION
	"The current value of the fifth output of the slave 7"
    ::= { slaveSevenOutputCurrent 5}
slaveSevenOutputCurrentSix OBJECT-TYPE
    SYNTAX      DisplayString
    MAX-ACCESS  read-only
    STATUS      current
    DESCRIPTION
	"The current value of the sixth output of the slave 7"
    ::= { slaveSevenOutputCurrent 6}
slaveSevenOutputCurrentSeven OBJECT-TYPE
    SYNTAX      DisplayString
    MAX-ACCESS  read-only
    STATUS      current
    DESCRIPTION
	"The current value of the seventh output of the slave 7"
    ::= { slaveSevenOutputCurrent 7}
slaveSevenOutputCurrentEight OBJECT-TYPE
    SYNTAX      DisplayString
    MAX-ACCESS  read-only
    STATUS      current
    DESCRIPTION
	"The current value of the eighth output of the slave 7"
    ::= { slaveSevenOutputCurrent 8}
slaveSevenOutputCurrentNine OBJECT-TYPE
    SYNTAX      DisplayString
    MAX-ACCESS  read-only
    STATUS      current
    DESCRIPTION
	"The current value of the nineth output of the slave 7"
    ::= { slaveSevenOutputCurrent 9}
slaveSevenOutputCurrentTen OBJECT-TYPE
    SYNTAX      DisplayString
    MAX-ACCESS  read-only
    STATUS      current
    DESCRIPTION
	"The current value of the tenth output of the slave 7"
    ::= { slaveSevenOutputCurrent 10}
slaveSevenOutputCurrentEleven OBJECT-TYPE
    SYNTAX      DisplayString
    MAX-ACCESS  read-only
    STATUS      current
    DESCRIPTION
	"The current value of the eleventh output of the slave 7"
    ::= { slaveSevenOutputCurrent 11}
slaveSevenOutputCurrentTwelve OBJECT-TYPE
    SYNTAX      DisplayString
    MAX-ACCESS  read-only
    STATUS      current
    DESCRIPTION
	"The current value of the twelfth output of the slave 7"
    ::= { slaveSevenOutputCurrent 12}
slaveSevenOutputCurrentThirteen OBJECT-TYPE
    SYNTAX      DisplayString
    MAX-ACCESS  read-only
    STATUS      current
    DESCRIPTION
	"The current value of the thirteenth output of the slave 7"
    ::= { slaveSevenOutputCurrent 13}
slaveSevenOutputCurrentFourteen OBJECT-TYPE
    SYNTAX      DisplayString
    MAX-ACCESS  read-only
    STATUS      current
    DESCRIPTION
	"The current value of the fourteenth output of the slave 7"
    ::= { slaveSevenOutputCurrent 14}
slaveSevenOutputCurrentFifteen OBJECT-TYPE
    SYNTAX      DisplayString
    MAX-ACCESS  read-only
    STATUS      current
    DESCRIPTION
	"The current value of the fifteenth output of the slave 7"
    ::= { slaveSevenOutputCurrent 15}
slaveSevenOutputCurrentSixteen OBJECT-TYPE
    SYNTAX      DisplayString
    MAX-ACCESS  read-only
    STATUS      current
    DESCRIPTION
	"The current value of the sixteenth output of the slave 7"
    ::= { slaveSevenOutputCurrent 16}
slaveSevenOutputCurrentSeventeen OBJECT-TYPE
    SYNTAX      DisplayString
    MAX-ACCESS  read-only
    STATUS      current
    DESCRIPTION
	"The current value of the seventeenth output of the slave 7"
    ::= { slaveSevenOutputCurrent 17}
slaveSevenOutputCurrentEighteen OBJECT-TYPE
    SYNTAX      DisplayString
    MAX-ACCESS  read-only
    STATUS      current
    DESCRIPTION
	"The current value of the eighteenth output of the slave 7"
    ::= { slaveSevenOutputCurrent 18}
slaveSevenOutputCurrentNineteen OBJECT-TYPE
    SYNTAX      DisplayString
    MAX-ACCESS  read-only
    STATUS      current
    DESCRIPTION
	"The current value of the nineteenth output of the slave 7"
    ::= { slaveSevenOutputCurrent 19}
slaveSevenOutputCurrentTwenty OBJECT-TYPE
    SYNTAX      DisplayString
    MAX-ACCESS  read-only
    STATUS      current
    DESCRIPTION
	"The current value of the twentieth output of the slave 7"
    ::= { slaveSevenOutputCurrent 20}
slaveSevenOutputCurrentTwentyOne OBJECT-TYPE
    SYNTAX      DisplayString
    MAX-ACCESS  read-only
    STATUS      current
    DESCRIPTION
	"The current value of the twenty-first output of the slave 7"
    ::= { slaveSevenOutputCurrent 21}
slaveSevenOutputCurrentTwentyTwo OBJECT-TYPE
    SYNTAX      DisplayString
    MAX-ACCESS  read-only
    STATUS      current
    DESCRIPTION
	"The current value of the twenty-second output of the slave 7"
    ::= { slaveSevenOutputCurrent 22}
slaveSevenOutputCurrentTwentyThree OBJECT-TYPE
    SYNTAX      DisplayString
    MAX-ACCESS  read-only
    STATUS      current
    DESCRIPTION
	"The current value of the twenty-third output of the slave 7"
    ::= { slaveSevenOutputCurrent 23}
slaveSevenOutputCurrentTwentyFour OBJECT-TYPE
    SYNTAX      DisplayString
    MAX-ACCESS  read-only
    STATUS      current
    DESCRIPTION
	"The current value of the twenty-fourth output of the slave 7"
    ::= { slaveSevenOutputCurrent 24}

slaveSevenOutputCurrentMin   OBJECT IDENTIFIER ::= { rpduSlaveSeven 11}
slaveSevenOutputCurrentMinOne OBJECT-TYPE
    SYNTAX      DisplayString
    MAX-ACCESS  read-only
    STATUS      current
    DESCRIPTION
	"The Min. current value of the first output of the slave 7"
    ::= { slaveSevenOutputCurrentMin 1}
slaveSevenOutputCurrentMinTwo OBJECT-TYPE
    SYNTAX      DisplayString
    MAX-ACCESS  read-only
    STATUS      current
    DESCRIPTION
	"The Min. current value of the second output of the slave 7"
    ::= { slaveSevenOutputCurrentMin 2}
slaveSevenOutputCurrentMinThree OBJECT-TYPE
    SYNTAX      DisplayString
    MAX-ACCESS  read-only
    STATUS      current
    DESCRIPTION
	"The Min. current value of the third output of the slave 7"
    ::= { slaveSevenOutputCurrentMin 3}
slaveSevenOutputCurrentMinFour OBJECT-TYPE
    SYNTAX      DisplayString
    MAX-ACCESS  read-only
    STATUS      current
    DESCRIPTION
	"The Min. current value of the fourth output of the slave 7"
    ::= { slaveSevenOutputCurrentMin 4}
slaveSevenOutputCurrentMinFive OBJECT-TYPE
    SYNTAX      DisplayString
    MAX-ACCESS  read-only
    STATUS      current
    DESCRIPTION
	"The Min. current value of the fifth output of the slave 7"
    ::= { slaveSevenOutputCurrentMin 5}
slaveSevenOutputCurrentMinSix OBJECT-TYPE
    SYNTAX      DisplayString
    MAX-ACCESS  read-only
    STATUS      current
    DESCRIPTION
	"The Min. current value of the sixth output of the slave 7"
    ::= { slaveSevenOutputCurrentMin 6}
slaveSevenOutputCurrentMinSeven OBJECT-TYPE
    SYNTAX      DisplayString
    MAX-ACCESS  read-only
    STATUS      current
    DESCRIPTION
	"The Min. current value of the seventh output of the slave 7"
    ::= { slaveSevenOutputCurrentMin 7}
slaveSevenOutputCurrentMinEight OBJECT-TYPE
    SYNTAX      DisplayString
    MAX-ACCESS  read-only
    STATUS      current
    DESCRIPTION
	"The Min. current value of the eighth output of the slave 7"
    ::= { slaveSevenOutputCurrentMin 8}
slaveSevenOutputCurrentMinNine OBJECT-TYPE
    SYNTAX      DisplayString
    MAX-ACCESS  read-only
    STATUS      current
    DESCRIPTION
	"The Min. current value of the nineth output of the slave 7"
    ::= { slaveSevenOutputCurrentMin 9}
slaveSevenOutputCurrentMinTen OBJECT-TYPE
    SYNTAX      DisplayString
    MAX-ACCESS  read-only
    STATUS      current
    DESCRIPTION
	"The Min. current value of the tenth output of the slave 7"
    ::= { slaveSevenOutputCurrentMin 10}
slaveSevenOutputCurrentMinEleven OBJECT-TYPE
    SYNTAX      DisplayString
    MAX-ACCESS  read-only
    STATUS      current
    DESCRIPTION
	"The Min. current value of the eleventh output of the slave 7"
    ::= { slaveSevenOutputCurrentMin 11}
slaveSevenOutputCurrentMinTwleve OBJECT-TYPE
    SYNTAX      DisplayString
    MAX-ACCESS  read-only
    STATUS      current
    DESCRIPTION
	"The Min. current value of the twelfth output of the slave 7"
    ::= { slaveSevenOutputCurrentMin 12}
slaveSevenOutputCurrentMinThirteen OBJECT-TYPE
    SYNTAX      DisplayString
    MAX-ACCESS  read-only
    STATUS      current
    DESCRIPTION
	"The Min. current value of the thirteenth output of the slave 7"
    ::= { slaveSevenOutputCurrentMin 13}
slaveSevenOutputCurrentMinFourteen OBJECT-TYPE
    SYNTAX      DisplayString
    MAX-ACCESS  read-only
    STATUS      current
    DESCRIPTION
	"The Min. current value of the fourteenth output of the slave 7"
    ::= { slaveSevenOutputCurrentMin 14}
slaveSevenOutputCurrentMinFifteen OBJECT-TYPE
    SYNTAX      DisplayString
    MAX-ACCESS  read-only
    STATUS      current
    DESCRIPTION
	"The Min. current value of the fifteenth output of the slave 7"
    ::= { slaveSevenOutputCurrentMin 15}
slaveSevenOutputCurrentMinSixteen OBJECT-TYPE
    SYNTAX      DisplayString
    MAX-ACCESS  read-only
    STATUS      current
    DESCRIPTION
	"The Min. current value of the sixteenth output of the slave 7"
    ::= { slaveSevenOutputCurrentMin 16}
slaveSevenOutputCurrentMinSeventeen OBJECT-TYPE
    SYNTAX      DisplayString
    MAX-ACCESS  read-only
    STATUS      current
    DESCRIPTION
	"The Min. current value of the seventeenth output of the slave 7"
    ::= { slaveSevenOutputCurrentMin 17}
slaveSevenOutputCurrentMinEighteen OBJECT-TYPE
    SYNTAX      DisplayString
    MAX-ACCESS  read-only
    STATUS      current
    DESCRIPTION
	"The Min. current value of the eighteenth output of the slave 7"
    ::= { slaveSevenOutputCurrentMin 18}
slaveSevenOutputCurrentMinNineteen OBJECT-TYPE
    SYNTAX      DisplayString
    MAX-ACCESS  read-only
    STATUS      current
    DESCRIPTION
	"The Min. current value of the nineteenth output of the slave 7"
    ::= { slaveSevenOutputCurrentMin 19}
slaveSevenOutputCurrentMinTwenty OBJECT-TYPE
    SYNTAX      DisplayString
    MAX-ACCESS  read-only
    STATUS      current
    DESCRIPTION
	"The Min. current value of the twentieth output of the slave 7"
    ::= { slaveSevenOutputCurrentMin 20}
slaveSevenOutputCurrentMinTwentyOne OBJECT-TYPE
    SYNTAX      DisplayString
    MAX-ACCESS  read-only
    STATUS      current
    DESCRIPTION
	"The Min. current value of the twentyth-first output of the slave 7"
    ::= { slaveSevenOutputCurrentMin 21}
slaveSevenOutputCurrentMinTwentyTwo OBJECT-TYPE
    SYNTAX      DisplayString
    MAX-ACCESS  read-only
    STATUS      current
    DESCRIPTION
	"The Min. current value of the twentyth-second output of the slave 7"
    ::= { slaveSevenOutputCurrentMin 22}
slaveSevenOutputCurrentMinTwentyThree OBJECT-TYPE
    SYNTAX      DisplayString
    MAX-ACCESS  read-only
    STATUS      current
    DESCRIPTION
	"The Min. current value of the twentyth-third output of the slave 7"
    ::= { slaveSevenOutputCurrentMin 23}
slaveSevenOutputCurrentMinTwentyFour OBJECT-TYPE
    SYNTAX      DisplayString
    MAX-ACCESS  read-only
    STATUS      current
    DESCRIPTION
	"The Min. current value of the twentyth-fourth output of the slave 7"
    ::= { slaveSevenOutputCurrentMin 24}




slaveSevenOutputCurrentMax   OBJECT IDENTIFIER ::= { rpduSlaveSeven 12}
slaveSevenOutputCurrentMaxOne OBJECT-TYPE
    SYNTAX      DisplayString
    MAX-ACCESS  read-only
    STATUS      current
    DESCRIPTION
	"The Max. current value of the first output of the slave 7"
    ::= { slaveSevenOutputCurrentMax 1}
slaveSevenOutputCurrentMaxTwo OBJECT-TYPE
    SYNTAX      DisplayString
    MAX-ACCESS  read-only
    STATUS      current
    DESCRIPTION
	"The Max. current value of the second output of the slave 7"
    ::= { slaveSevenOutputCurrentMax 2}
slaveSevenOutputCurrentMaxThree OBJECT-TYPE
    SYNTAX      DisplayString
    MAX-ACCESS  read-only
    STATUS      current
    DESCRIPTION
	"The Max. current value of the third output of the slave 7"
    ::= { slaveSevenOutputCurrentMax 3}
slaveSevenOutputCurrentMaxFour OBJECT-TYPE
    SYNTAX      DisplayString
    MAX-ACCESS  read-only
    STATUS      current
    DESCRIPTION
	"The Max. current value of the fourth output of the slave 7"
    ::= { slaveSevenOutputCurrentMax 4}
slaveSevenOutputCurrentMaxFive OBJECT-TYPE
    SYNTAX      DisplayString
    MAX-ACCESS  read-only
    STATUS      current
    DESCRIPTION
	"The Max. current value of the fifth output of the slave 7"
    ::= { slaveSevenOutputCurrentMax 5}
slaveSevenOutputCurrentMaxSix OBJECT-TYPE
    SYNTAX      DisplayString
    MAX-ACCESS  read-only
    STATUS      current
    DESCRIPTION
	"The Max. current value of the sixth output of the slave 7"
    ::= { slaveSevenOutputCurrentMax 6}
slaveSevenOutputCurrentMaxSeven OBJECT-TYPE
    SYNTAX      DisplayString
    MAX-ACCESS  read-only
    STATUS      current
    DESCRIPTION
	"The Max. current value of the seventh output of the slave 7"
    ::= { slaveSevenOutputCurrentMax 7}
slaveSevenOutputCurrentMaxEight OBJECT-TYPE
    SYNTAX      DisplayString
    MAX-ACCESS  read-only
    STATUS      current
    DESCRIPTION
	"The Max. current value of the eighth output of the slave 7"
    ::= { slaveSevenOutputCurrentMax 8}
slaveSevenOutputCurrentMaxNine OBJECT-TYPE
    SYNTAX      DisplayString
    MAX-ACCESS  read-only
    STATUS      current
    DESCRIPTION
	"The Max. current value of the nineth output of the slave 7"
    ::= { slaveSevenOutputCurrentMax 9}
slaveSevenOutputCurrentMaxTen OBJECT-TYPE
    SYNTAX      DisplayString
    MAX-ACCESS  read-only
    STATUS      current
    DESCRIPTION
	"The Max. current value of the tenth output of the slave 7"
    ::= { slaveSevenOutputCurrentMax 10}
slaveSevenOutputCurrentMaxEleven OBJECT-TYPE
    SYNTAX      DisplayString
    MAX-ACCESS  read-only
    STATUS      current
    DESCRIPTION
	"The Max. current value of the eleventh output of the slave 7"
    ::= { slaveSevenOutputCurrentMax 11}
slaveSevenOutputCurrentMaxTwleve OBJECT-TYPE
    SYNTAX      DisplayString
    MAX-ACCESS  read-only
    STATUS      current
    DESCRIPTION
	"The Max. current value of the twelfth output of the slave 7"
    ::= { slaveSevenOutputCurrentMax 12}
slaveSevenOutputCurrentMaxThirteen OBJECT-TYPE
    SYNTAX      DisplayString
    MAX-ACCESS  read-only
    STATUS      current
    DESCRIPTION
	"The Max. current value of the thirteenth output of the slave 7"
    ::= { slaveSevenOutputCurrentMax 13}
slaveSevenOutputCurrentMaxFourteen OBJECT-TYPE
    SYNTAX      DisplayString
    MAX-ACCESS  read-only
    STATUS      current
    DESCRIPTION
	"The Max. current value of the fourteenth output of the slave 7"
    ::= { slaveSevenOutputCurrentMax 14}
slaveSevenOutputCurrentMaxFifteen OBJECT-TYPE
    SYNTAX      DisplayString
    MAX-ACCESS  read-only
    STATUS      current
    DESCRIPTION
	"The Max. current value of the fifteenth output of the slave 7"
    ::= { slaveSevenOutputCurrentMax 15}
slaveSevenOutputCurrentMaxSixteen OBJECT-TYPE
    SYNTAX      DisplayString
    MAX-ACCESS  read-only
    STATUS      current
    DESCRIPTION
	"The Max. current value of the sixteenth output of the slave 7"
    ::= { slaveSevenOutputCurrentMax 16}
slaveSevenOutputCurrentMaxSeventeen OBJECT-TYPE
    SYNTAX      DisplayString
    MAX-ACCESS  read-only
    STATUS      current
    DESCRIPTION
	"The Max. current value of the seventeenth output of the slave 7"
    ::= { slaveSevenOutputCurrentMax 17}
slaveSevenOutputCurrentMaxEighteen OBJECT-TYPE
    SYNTAX      DisplayString
    MAX-ACCESS  read-only
    STATUS      current
    DESCRIPTION
	"The Max. current value of the eighteenth output of the slave 7"
    ::= { slaveSevenOutputCurrentMax 18}
slaveSevenOutputCurrentMaxNineteen OBJECT-TYPE
    SYNTAX      DisplayString
    MAX-ACCESS  read-only
    STATUS      current
    DESCRIPTION
	"The Max. current value of the nineteenth output of the slave 7"
    ::= { slaveSevenOutputCurrentMax 19}
slaveSevenOutputCurrentMaxTwenty OBJECT-TYPE
    SYNTAX      DisplayString
    MAX-ACCESS  read-only
    STATUS      current
    DESCRIPTION
	"The Max. current value of the twentieth output of the slave 7"
    ::= { slaveSevenOutputCurrentMax 20}
slaveSevenOutputCurrentMaxTwentyOne OBJECT-TYPE
    SYNTAX      DisplayString
    MAX-ACCESS  read-only
    STATUS      current
    DESCRIPTION
	"The Max. current value of the twenty-first output of the slave 7"
    ::= { slaveSevenOutputCurrentMax 21}
slaveSevenOutputCurrentMaxTwentyTwo OBJECT-TYPE
    SYNTAX      DisplayString
    MAX-ACCESS  read-only
    STATUS      current
    DESCRIPTION
	"The Max. current value of the twenty-second output of the slave 7"
    ::= { slaveSevenOutputCurrentMax 22}
slaveSevenOutputCurrentMaxTwentyThree OBJECT-TYPE
    SYNTAX      DisplayString
    MAX-ACCESS  read-only
    STATUS      current
    DESCRIPTION
	"The Max. current value of the twenty-third output of the slave 7"
    ::= { slaveSevenOutputCurrentMax 23}
slaveSevenOutputCurrentMaxTwentyFour OBJECT-TYPE
    SYNTAX      DisplayString
    MAX-ACCESS  read-only
    STATUS      current
    DESCRIPTION
	"The Max. current value of the twenty-fourth output of the slave 7"
    ::= { slaveSevenOutputCurrentMax 24}


slaveSevenOutputCurrentEnergy  OBJECT IDENTIFIER ::= { rpduSlaveSeven 13}
slaveSevenOutputCurrentEnergyOne OBJECT-TYPE
    SYNTAX	DisplayString
    MAX-ACCESS	read-only
    STATUS	current
    DESCRIPTION
	"The energy value of the first output of the slave 7"
    ::={slaveSevenOutputCurrentEnergy 1}
slaveSevenOutputCurrentEnergyTwo OBJECT-TYPE
    SYNTAX	DisplayString
    MAX-ACCESS	read-only
    STATUS	current
    DESCRIPTION
	"The energy value of the second output of the slave 7"
    ::={slaveSevenOutputCurrentEnergy 2}
slaveSevenOutputCurrentEnergyThree OBJECT-TYPE
    SYNTAX	DisplayString
    MAX-ACCESS	read-only
    STATUS	current
    DESCRIPTION
	"The energy value of the third output of the slave 7"
    ::={slaveSevenOutputCurrentEnergy 3}
slaveSevenOutputCurrentEnergyFour OBJECT-TYPE
    SYNTAX	DisplayString
    MAX-ACCESS	read-only
    STATUS	current
    DESCRIPTION
	"The energy value of the fourth output of the slave 7"
    ::={slaveSevenOutputCurrentEnergy 4}
slaveSevenOutputCurrentEnergyFive OBJECT-TYPE
    SYNTAX	DisplayString
    MAX-ACCESS	read-only
    STATUS	current
    DESCRIPTION
	"The energy value of the fifth output of the slave 7"
    ::={slaveSevenOutputCurrentEnergy 5}
slaveSevenOutputCurrentEnergySix OBJECT-TYPE
    SYNTAX	DisplayString
    MAX-ACCESS	read-only
    STATUS	current
    DESCRIPTION
	"The energy value of the sixth output of the slave 7"
    ::={slaveSevenOutputCurrentEnergy 6}
slaveSevenOutputCurrentEnergySeven OBJECT-TYPE
    SYNTAX	DisplayString
    MAX-ACCESS	read-only
    STATUS	current
    DESCRIPTION
	"The energy value of the seventh output of the slave 7"
    ::={slaveSevenOutputCurrentEnergy 7}
slaveSevenOutputCurrentEnergyEight OBJECT-TYPE
    SYNTAX	DisplayString
    MAX-ACCESS	read-only
    STATUS	current
    DESCRIPTION
	"The energy value of the eighth output of the slave 7"
    ::={slaveSevenOutputCurrentEnergy 8}
slaveSevenOutputCurrentEnergyNine OBJECT-TYPE
    SYNTAX	DisplayString
    MAX-ACCESS	read-only
    STATUS	current
    DESCRIPTION
	"The energy value of the nineth output of the slave 7"
    ::={slaveSevenOutputCurrentEnergy 9}
slaveSevenOutputCurrentEnergyTen OBJECT-TYPE
    SYNTAX	DisplayString
    MAX-ACCESS	read-only
    STATUS	current
    DESCRIPTION
	"The energy value of the tenth output of the slave 7"
    ::={slaveSevenOutputCurrentEnergy 10}
slaveSevenOutputCurrentEnergyEleven OBJECT-TYPE
    SYNTAX	DisplayString
    MAX-ACCESS	read-only
    STATUS	current
    DESCRIPTION
	"The energy value of the eleventh output of the slave 7"
    ::={slaveSevenOutputCurrentEnergy 11}
slaveSevenOutputCurrentEnergyTwelve OBJECT-TYPE
    SYNTAX	DisplayString
    MAX-ACCESS	read-only
    STATUS	current
    DESCRIPTION
	"The energy value of the twelfth output of the slave 7"
    ::={slaveSevenOutputCurrentEnergy 12}
slaveSevenOutputCurrentEnergyThirteen OBJECT-TYPE
    SYNTAX	DisplayString
    MAX-ACCESS	read-only
    STATUS	current
    DESCRIPTION
	"The energy value of the thirteenth output of the slave 7"
    ::={slaveSevenOutputCurrentEnergy 13}
slaveSevenOutputCurrentEnergyFourteen OBJECT-TYPE
    SYNTAX	DisplayString
    MAX-ACCESS	read-only
    STATUS	current
    DESCRIPTION
	"The energy value of the fourteenth output of the slave 7"
    ::={slaveSevenOutputCurrentEnergy 14}
slaveSevenOutputCurrentEnergyFifteen OBJECT-TYPE
    SYNTAX	DisplayString
    MAX-ACCESS	read-only
    STATUS	current
    DESCRIPTION
	"The energy value of the fifteenth output of the slave 7"
    ::={slaveSevenOutputCurrentEnergy 15}
slaveSevenOutputCurrentEnergySixteen OBJECT-TYPE
    SYNTAX	DisplayString
    MAX-ACCESS	read-only
    STATUS	current
    DESCRIPTION
	"The energy value of the sixteenth output of the slave 7"
    ::={slaveSevenOutputCurrentEnergy 16}
slaveSevenOutputCurrentEnergySeventeen OBJECT-TYPE
    SYNTAX	DisplayString
    MAX-ACCESS	read-only
    STATUS	current
    DESCRIPTION
	"The energy value of the seventeenth output of the slave 7"
    ::={slaveSevenOutputCurrentEnergy 17}
slaveSevenOutputCurrentEnergyEighteen OBJECT-TYPE
    SYNTAX	DisplayString
    MAX-ACCESS	read-only
    STATUS	current
    DESCRIPTION
	"The energy value of the eighteenth output of the slave 7"
    ::={slaveSevenOutputCurrentEnergy 18}
slaveSevenOutputCurrentEnergyNineteen OBJECT-TYPE
    SYNTAX	DisplayString
    MAX-ACCESS	read-only
    STATUS	current
    DESCRIPTION
	"The energy value of the nineteenth output of the slave 7"
    ::={slaveSevenOutputCurrentEnergy 19}
slaveSevenOutputCurrentEnergyTwenty OBJECT-TYPE
    SYNTAX	DisplayString
    MAX-ACCESS	read-only
    STATUS	current
    DESCRIPTION
	"The energy value of the twentieth output of the slave 7"
    ::={slaveSevenOutputCurrentEnergy 20}
slaveSevenOutputCurrentEnergyTwentyOne OBJECT-TYPE
    SYNTAX	DisplayString
    MAX-ACCESS	read-only
    STATUS	current
    DESCRIPTION
	"The energy value of the twenty-first output of the slave 7"
    ::={slaveSevenOutputCurrentEnergy 21}
slaveSevenOutputCurrentEnergyTwentyTwo OBJECT-TYPE
    SYNTAX	DisplayString
    MAX-ACCESS	read-only
    STATUS	current
    DESCRIPTION
	"The energy value of the twenty-second output of the slave 7"
    ::={slaveSevenOutputCurrentEnergy 22}
slaveSevenOutputCurrentEnergyTwentyThree OBJECT-TYPE
    SYNTAX	DisplayString
    MAX-ACCESS	read-only
    STATUS	current
    DESCRIPTION
	"The energy value of the twenty-third output of the slave 7"
    ::={slaveSevenOutputCurrentEnergy 23}
slaveSevenOutputCurrentEnergyTwentyFour OBJECT-TYPE
    SYNTAX	DisplayString
    MAX-ACCESS	read-only
    STATUS	current
    DESCRIPTION
	"The energy value of the twenty-fourth output of the slave 7"
    ::={slaveSevenOutputCurrentEnergy 24}

-------------------------------Slave8 ---------------------------------------------
rpduDeviceNine OBJECT IDENTIFIER ::= { rpdu 9}
rpduSlaveEight OBJECT IDENTIFIER ::= { rpduDeviceNine 1}

slaveEightName OBJECT-TYPE
    SYNTAX      DisplayString
    MAX-ACCESS  read-write
    STATUS      current
    DESCRIPTION
	"This is the ninth device."
    ::= { rpduSlaveEight 1}
    
slaveEightType OBJECT-TYPE
    SYNTAX      DisplayString
    MAX-ACCESS  read-only
    STATUS      current
    DESCRIPTION
	"This is device type "
    ::= { rpduSlaveEight 2}
    
slaveEightOutputNumber OBJECT-TYPE 
    SYNTAX      Integer32
    MAX-ACCESS  read-only
    STATUS      current
    DESCRIPTION
	"This is the output quantity"
::= { rpduSlaveEight 7}
    
slaveEightLineOne OBJECT IDENTIFIER ::= { rpduSlaveEight 3}
slaveEightLineOnePower OBJECT-TYPE
    SYNTAX      DisplayString
    MAX-ACCESS  read-only
    STATUS      current
    DESCRIPTION
	"The power of phase one"
    ::= { slaveEightLineOne 1}
slaveEightLineOnePF OBJECT-TYPE
    SYNTAX      DisplayString
    MAX-ACCESS  read-only
    STATUS      current
    DESCRIPTION
	"The power factor of phase one"
    ::= { slaveEightLineOne 2}
    
slaveEightLineOneEnergy OBJECT-TYPE
    SYNTAX      DisplayString
    MAX-ACCESS  read-only
    STATUS      current
    DESCRIPTION
	"The energy of phase one"
    ::= { slaveEightLineOne 3}
slaveEightLineOneCurrent OBJECT-TYPE
    SYNTAX      DisplayString
    MAX-ACCESS  read-only
    STATUS      current
    DESCRIPTION
	"The current of phase one"
    ::= { slaveEightLineOne 4}
slaveEightLineOneVoltage OBJECT-TYPE
    SYNTAX      Integer32
    MAX-ACCESS  read-only
    STATUS      current
    DESCRIPTION
	"The voltage of phase one"
    ::= { slaveEightLineOne 5}
slaveEightLineOneCurrentMin OBJECT-TYPE
    SYNTAX      DisplayString
    MAX-ACCESS  read-only
    STATUS      current
    DESCRIPTION
	"The Min. current value of phase one"
	::= { slaveEightLineOne 6}
slaveEightLineOneCurrentMax OBJECT-TYPE
    SYNTAX      DisplayString
    MAX-ACCESS  read-only
    STATUS      current
    DESCRIPTION
	"The Max. current value of phase one"
    ::= { slaveEightLineOne 7}
    
slaveEightLineOneVoltageMin OBJECT-TYPE
    SYNTAX      Integer32
    MAX-ACCESS  read-only
    STATUS      current
    DESCRIPTION
	"The Min. voltage value of phase one"
    ::= { slaveEightLineOne 8}
    
slaveEightLineOneVoltageMax OBJECT-TYPE
    SYNTAX      Integer32
    MAX-ACCESS  read-only
    STATUS      current
    DESCRIPTION
	"The Max. voltage value of phase one"
    ::= { slaveEightLineOne 9}


slaveEightLineTwo OBJECT IDENTIFIER ::= { rpduSlaveEight 4}
slaveEightLineTwoPower OBJECT-TYPE
    SYNTAX      DisplayString
    MAX-ACCESS  read-only
    STATUS      current
    DESCRIPTION
	"The power of phase two"
    ::= { slaveEightLineTwo 1}

slaveEightLineTwoPF OBJECT-TYPE
    SYNTAX      DisplayString
    MAX-ACCESS  read-only
    STATUS      current
    DESCRIPTION
	"The power factor of phase two"   
    ::= { slaveEightLineTwo 2}
    
slaveEightLineTwoEnergy OBJECT-TYPE
    SYNTAX      DisplayString
    MAX-ACCESS  read-only
    STATUS      current
    DESCRIPTION
	"The energy of phase two"
    ::= { slaveEightLineTwo 3}
slaveEightLineTwoCurrent OBJECT-TYPE           
    SYNTAX      DisplayString 
    MAX-ACCESS  read-only
    STATUS      current
    DESCRIPTION
	"The current of phase two"
    ::= { slaveEightLineTwo 4}
slaveEightLineTwoVoltage OBJECT-TYPE
    SYNTAX      Integer32
    MAX-ACCESS  read-only
    STATUS      current
    DESCRIPTION
	"The voltage of phase two"
    ::= { slaveEightLineTwo 5}
slaveEightLineTwoCurrentMin OBJECT-TYPE
    SYNTAX      DisplayString
    MAX-ACCESS  read-only
    STATUS      current
    DESCRIPTION
	"The Min. current value of phase two"
    ::= { slaveEightLineTwo 6}
slaveEightLineTwoCurrentMax OBJECT-TYPE
    SYNTAX      DisplayString
    MAX-ACCESS  read-only
    STATUS      current
    DESCRIPTION
	"The Max. current value of phase two"
    ::= { slaveEightLineTwo 7}
    
slaveEightLineTwoVoltageMin OBJECT-TYPE
    SYNTAX      Integer32
    MAX-ACCESS  read-only
    STATUS      current
    DESCRIPTION
	"The Min. voltage value of phase two"
    ::= { slaveEightLineTwo 8}
    
slaveEightLineTwoVoltageMax OBJECT-TYPE
    SYNTAX      Integer32
    MAX-ACCESS  read-only
    STATUS      current
    DESCRIPTION
	"The Max. voltage value of phase two"
    ::= { slaveEightLineTwo 9}



slaveEightLineThree OBJECT IDENTIFIER ::= { rpduSlaveEight 5}
slaveEightLineThreePower OBJECT-TYPE
    SYNTAX      DisplayString
    MAX-ACCESS  read-only
    STATUS      current
    DESCRIPTION
	"The power of phase three"
    ::= { slaveEightLineThree 1}

slaveEightLineThreePF OBJECT-TYPE
    SYNTAX      DisplayString
    MAX-ACCESS  read-only
    STATUS      current
    DESCRIPTION
	"The power factor of phase three"     
    ::= { slaveEightLineThree 2}
    
slaveEightLineThreeEnergy OBJECT-TYPE
    SYNTAX      DisplayString
    MAX-ACCESS  read-only
    STATUS      current
    DESCRIPTION
	"The energy of phase three"
    ::= { slaveEightLineThree 3}
slaveEightLineThreeCurrent OBJECT-TYPE
    SYNTAX      DisplayString
    MAX-ACCESS  read-only
    STATUS      current
    DESCRIPTION
	"The current of phase three"
    ::= { slaveEightLineThree 4}
slaveEightLineThreeVoltage OBJECT-TYPE
    SYNTAX      Integer32
    MAX-ACCESS  read-only
    STATUS      current
    DESCRIPTION
	"The voltage of phase three"
    ::= { slaveEightLineThree 5}
slaveEightLineThreeCurrentMin OBJECT-TYPE
    SYNTAX      DisplayString
    MAX-ACCESS  read-only
    STATUS      current
    DESCRIPTION
	"The Min. current value of phase three"
    ::= { slaveEightLineThree 6}
slaveEightLineThreeCurrentMax OBJECT-TYPE
    SYNTAX      DisplayString
    MAX-ACCESS  read-only
    STATUS      current
    DESCRIPTION
	"The Max. current value of phase three"
    ::= { slaveEightLineThree 7}
    
slaveEightLineThreeVoltageMin OBJECT-TYPE
    SYNTAX      Integer32
    MAX-ACCESS  read-only
    STATUS      current
    DESCRIPTION
	"The Min. voltage value of phase three"
    ::= { slaveEightLineThree 8}
    
slaveEightLineThreeVoltageMax OBJECT-TYPE
    SYNTAX      Integer32
    MAX-ACCESS  read-only
    STATUS      current
    DESCRIPTION
	"The Max. voltage value of phase three"
    ::= { slaveEightLineThree 9}


slaveEightSensor OBJECT IDENTIFIER ::= { rpduSlaveEight 6}
slaveEightTempOne OBJECT-TYPE
    SYNTAX      Integer32
    MAX-ACCESS  read-only
    STATUS      current
    DESCRIPTION
	"The first temperature sensor of slave 8"
    ::= { slaveEightSensor 1}
slaveEightTempTwo OBJECT-TYPE
    SYNTAX      Integer32
    MAX-ACCESS  read-only
    STATUS      current
    DESCRIPTION
	"The second temperature sensor of slave 8"
    ::= { slaveEightSensor 2}
slaveEightTempThree OBJECT-TYPE
    SYNTAX      Integer32
    MAX-ACCESS  read-only
    STATUS      current
    DESCRIPTION
	"The third temperature sensor of slave 8"
    ::= { slaveEightSensor 3}
slaveEightTempFour OBJECT-TYPE
    SYNTAX      Integer32
    MAX-ACCESS  read-only
    STATUS      current
    DESCRIPTION
	"The fourth temperature sensor of slave 8"
    ::= { slaveEightSensor 4}
slaveEightHumOne OBJECT-TYPE
    SYNTAX      Integer32
    MAX-ACCESS  read-only
    STATUS      current
    DESCRIPTION
	"The first humidity sensor of slave 8"
    ::= { slaveEightSensor 5}
slaveEightHumTwo OBJECT-TYPE
    SYNTAX      Integer32
    MAX-ACCESS  read-only
    STATUS      current
    DESCRIPTION
	"The second humidity sensor of slave 8"
    ::= { slaveEightSensor 6}
slaveEightHumThree OBJECT-TYPE
    SYNTAX      Integer32
    MAX-ACCESS  read-only
    STATUS      current
    DESCRIPTION
	"The third humidity sensor of slave 8"
    ::= { slaveEightSensor 7}
slaveEightHumFour OBJECT-TYPE
    SYNTAX      Integer32
    MAX-ACCESS  read-only
    STATUS      current
    DESCRIPTION
	"The fourth humidity sensor of slave 8"
    ::= { slaveEightSensor 8}
slaveEightDoorOne OBJECT-TYPE
    SYNTAX      DisplayString
    MAX-ACCESS  read-only
    STATUS      current
    DESCRIPTION
	"The first door sensor of slave 8"    
    ::= { slaveEightSensor 9}
slaveEightDoorTwo OBJECT-TYPE
    SYNTAX      DisplayString
    MAX-ACCESS  read-only
    STATUS      current
    DESCRIPTION
	"The second door sensor of slave 8"  
    ::= { slaveEightSensor 10}
slaveEightSmoke OBJECT-TYPE
    SYNTAX      DisplayString
    MAX-ACCESS  read-only
    STATUS      current
    DESCRIPTION
	"The smoke sensor of slave 8"
    ::= { slaveEightSensor 11}
slaveEightWater OBJECT-TYPE
    SYNTAX      DisplayString
    MAX-ACCESS  read-only
    STATUS      current
    DESCRIPTION
	"The water sensor of slave 8"
    ::= { slaveEightSensor 12}


	
        
slaveEightOutputName OBJECT IDENTIFIER ::= { rpduSlaveEight 8}
slaveEightOutputNameOne OBJECT-TYPE
    SYNTAX      DisplayString
    MAX-ACCESS  read-write
    STATUS      current
    DESCRIPTION
	"The first output name of slave 8"
    ::= { slaveEightOutputName 1}

slaveEightOutputNameTwo OBJECT-TYPE
    SYNTAX      DisplayString
    MAX-ACCESS  read-write
    STATUS      current
    DESCRIPTION
	"The second output name of slave 8"
    ::= { slaveEightOutputName 2}
slaveEightOutputNameThree OBJECT-TYPE
    SYNTAX      DisplayString
    MAX-ACCESS  read-write
    STATUS      current
    DESCRIPTION
	"The third output name of slave 8"
    ::= { slaveEightOutputName 3}
slaveEightOutputNameFour OBJECT-TYPE
    SYNTAX      DisplayString
    MAX-ACCESS  read-write
    STATUS      current
    DESCRIPTION
	"The fourth output name of slave 8"
    ::= { slaveEightOutputName 4}
slaveEightOutputNameFive OBJECT-TYPE
    SYNTAX      DisplayString
    MAX-ACCESS  read-write
    STATUS      current
    DESCRIPTION
	"The fifth output name of slave 8"
    ::= { slaveEightOutputName 5}
slaveEightOutputNameSix OBJECT-TYPE
    SYNTAX      DisplayString
    MAX-ACCESS  read-write
    STATUS      current
    DESCRIPTION
	"The sixth output name of slave 8"
    ::= { slaveEightOutputName 6}
slaveEightOutputNameSeven OBJECT-TYPE
    SYNTAX      DisplayString
    MAX-ACCESS  read-write
    STATUS      current
    DESCRIPTION
	"The seventh output name of slave 8"
    ::= { slaveEightOutputName 7}
slaveEightOutputNameEight OBJECT-TYPE
    SYNTAX      DisplayString
    MAX-ACCESS  read-write
    STATUS      current
    DESCRIPTION
	"The eighth output name of slave 8"
    ::= { slaveEightOutputName 8}
slaveEightOutputNameNine OBJECT-TYPE
    SYNTAX      DisplayString
    MAX-ACCESS  read-write
    STATUS      current
    DESCRIPTION
	"The nineth output name of slave 8"
    ::= { slaveEightOutputName 9}
slaveEightOutputNameTen OBJECT-TYPE
    SYNTAX      DisplayString
    MAX-ACCESS  read-write
    STATUS      current
    DESCRIPTION
	"The tenth output name of slave 8"
    ::= { slaveEightOutputName 10}
slaveEightOutputNameEleven OBJECT-TYPE
    SYNTAX      DisplayString
    MAX-ACCESS  read-write
    STATUS      current
    DESCRIPTION
	"The eleventh output name of slave 8"
    ::= { slaveEightOutputName 11}
slaveEightOutputNameTwelve OBJECT-TYPE
    SYNTAX      DisplayString
    MAX-ACCESS  read-write
    STATUS      current
    DESCRIPTION
	"The twelfth output name of slave 8"
    ::= { slaveEightOutputName 12}
slaveEightOutputNameThirteen OBJECT-TYPE
    SYNTAX      DisplayString
    MAX-ACCESS  read-write
    STATUS      current
    DESCRIPTION
	"The thirteenth output name of slave 8"
    ::= { slaveEightOutputName 13}
slaveEightOutputNameFourteen OBJECT-TYPE
    SYNTAX      DisplayString
    MAX-ACCESS  read-write
    STATUS      current
    DESCRIPTION
	"The fourteenth output name of slave 8"
    ::= { slaveEightOutputName 14}
slaveEightOutputNameFifteen OBJECT-TYPE
    SYNTAX      DisplayString
    MAX-ACCESS  read-write
    STATUS      current
    DESCRIPTION
	"The fifteenth output name of slave 8"
    ::= { slaveEightOutputName 15}
slaveEightOutputNameSixteen OBJECT-TYPE
    SYNTAX      DisplayString
    MAX-ACCESS  read-write
    STATUS      current
    DESCRIPTION
	"The sixteenth output name of slave 8"
    ::= { slaveEightOutputName 16}
slaveEightOutputNameSeventeen OBJECT-TYPE
    SYNTAX      DisplayString
    MAX-ACCESS  read-write
    STATUS      current
    DESCRIPTION
	"The seventeenth output name of slave 8"
    ::= { slaveEightOutputName 17}
slaveEightOutputNameEighteen OBJECT-TYPE
    SYNTAX      DisplayString
    MAX-ACCESS  read-write
    STATUS      current
    DESCRIPTION
	"The eighteenh output name of slave 8"
    ::= { slaveEightOutputName 18}
slaveEightOutputNameNineteen OBJECT-TYPE
    SYNTAX      DisplayString
    MAX-ACCESS  read-write
    STATUS      current
    DESCRIPTION
	"The nineteenth output name of slave 8"
    ::= { slaveEightOutputName 19}
slaveEightOutputNameTwenty OBJECT-TYPE
    SYNTAX      DisplayString
    MAX-ACCESS  read-write
    STATUS      current
    DESCRIPTION
	"The twentieth output name of slave 8"
    ::= { slaveEightOutputName 20}
slaveEightOutputNameTwentyOne OBJECT-TYPE
    SYNTAX      DisplayString
    MAX-ACCESS  read-write
    STATUS      current
    DESCRIPTION
	"The twenty-first output name of slave 8"
    ::= { slaveEightOutputName 21}
slaveEightOutputNameTwentyTwo OBJECT-TYPE
    SYNTAX      DisplayString
    MAX-ACCESS  read-write
    STATUS      current
    DESCRIPTION
	"The twenty-second output name of slave 8"
    ::= { slaveEightOutputName 22}
slaveEightOutputNameTwentyThree OBJECT-TYPE
    SYNTAX      DisplayString
    MAX-ACCESS  read-write
    STATUS      current
    DESCRIPTION
	"The twenty-third output name of slave 8"
    ::= { slaveEightOutputName 23}
slaveEightOutputNameTwentyFour OBJECT-TYPE
    SYNTAX      DisplayString
    MAX-ACCESS  read-write
    STATUS      current
    DESCRIPTION
	"The twenty-fourth output name of slave 8"
    ::= { slaveEightOutputName 24}


    
slaveEightOutputStatus OBJECT IDENTIFIER ::= { rpduSlaveEight 9}

slaveEightOutputStatusOne OBJECT-TYPE
    SYNTAX      DisplayString
    MAX-ACCESS  read-write
    STATUS      current
    DESCRIPTION
	"The first output status of slave 8"
    ::= { slaveEightOutputStatus 1}
slaveEightOutputStatusTwo OBJECT-TYPE
    SYNTAX      DisplayString
    MAX-ACCESS  read-write
    STATUS      current
    DESCRIPTION
	"The second output status of slave 8"
    ::= { slaveEightOutputStatus 2}

slaveEightOutputStatusThree OBJECT-TYPE
    SYNTAX      DisplayString
    MAX-ACCESS  read-write
    STATUS      current
    DESCRIPTION
	"The third output status of slave 8"
    ::= { slaveEightOutputStatus 3}
slaveEightOutputStatusFour OBJECT-TYPE
    SYNTAX      DisplayString
    MAX-ACCESS  read-write
    STATUS      current
    DESCRIPTION
	"The fourth output status of slave 8"
    ::= { slaveEightOutputStatus 4}
slaveEightOutputStatusFive OBJECT-TYPE
    SYNTAX      DisplayString
    MAX-ACCESS  read-write
    STATUS      current
    DESCRIPTION
	"The fifth output status of slave 8"
    ::= { slaveEightOutputStatus 5}
slaveEightOutputStatusSix OBJECT-TYPE
    SYNTAX      DisplayString
    MAX-ACCESS  read-write
    STATUS      current
    DESCRIPTION
	"The sixth output status of slave 8"
    ::= { slaveEightOutputStatus 6}
slaveEightOutputStatusSeven OBJECT-TYPE
    SYNTAX      DisplayString
    MAX-ACCESS  read-write
    STATUS      current
    DESCRIPTION
	"The seventh output status of slave 8"
    ::= { slaveEightOutputStatus 7}
slaveEightOutputStatusEight OBJECT-TYPE
    SYNTAX      DisplayString
    MAX-ACCESS  read-write
    STATUS      current
    DESCRIPTION
	"The eighth output status of slave 8"
    ::= { slaveEightOutputStatus 8}
slaveEightOutputStatusNine OBJECT-TYPE
    SYNTAX      DisplayString
    MAX-ACCESS  read-write
    STATUS      current
    DESCRIPTION
	"The nineth output status of slave 8"
    ::= { slaveEightOutputStatus 9}
slaveEightOutputStatusTen OBJECT-TYPE
    SYNTAX      DisplayString
    MAX-ACCESS  read-write
    STATUS      current
    DESCRIPTION
	"The tenth output status of slave 8"
    ::= { slaveEightOutputStatus 10}
slaveEightOutputStatusEleven OBJECT-TYPE
    SYNTAX      DisplayString
    MAX-ACCESS  read-write
    STATUS      current
    DESCRIPTION
	"The eleventh output status of slave 8"
    ::= { slaveEightOutputStatus 11}
slaveEightOutputStatusTwelve OBJECT-TYPE
    SYNTAX      DisplayString
    MAX-ACCESS  read-write
    STATUS      current
    DESCRIPTION
	"The twelfth output status of slave 8"
    ::= { slaveEightOutputStatus 12}
slaveEightOutputStatusThirteen OBJECT-TYPE
    SYNTAX      DisplayString
    MAX-ACCESS  read-write
    STATUS      current
    DESCRIPTION
	"The thirteenth output status of slave 8"
    ::= { slaveEightOutputStatus 13}
slaveEightOutputStatusFourteen OBJECT-TYPE
    SYNTAX      DisplayString
    MAX-ACCESS  read-write
    STATUS      current
    DESCRIPTION
	"The fourteenth output status of slave 8"
    ::= { slaveEightOutputStatus 14}
slaveEightOutputStatusFifteen OBJECT-TYPE
    SYNTAX      DisplayString
    MAX-ACCESS  read-write
    STATUS      current
    DESCRIPTION
	"The fifteenth output status of slave 8"
    ::= { slaveEightOutputStatus 15}
slaveEightOutputStatusSixteen OBJECT-TYPE
    SYNTAX      DisplayString
    MAX-ACCESS  read-write
    STATUS      current
    DESCRIPTION
	"The sixteenth output status of slave 8"
    ::= { slaveEightOutputStatus 16}
slaveEightOutputStatusSeventeen OBJECT-TYPE
    SYNTAX      DisplayString
    MAX-ACCESS  read-write
    STATUS      current
    DESCRIPTION
	"The seventeenth output status of slave 8"
    ::= { slaveEightOutputStatus 17}
slaveEightOutputStatusEighteen OBJECT-TYPE
    SYNTAX      DisplayString
    MAX-ACCESS  read-write
    STATUS      current
    DESCRIPTION
	"The eighteenth output status of slave 8"
    ::= { slaveEightOutputStatus 18}
slaveEightOutputStatusNineteen OBJECT-TYPE
    SYNTAX      DisplayString
    MAX-ACCESS  read-write
    STATUS      current
    DESCRIPTION
	"The nineteenth output status of slave 8"
    ::= { slaveEightOutputStatus 19}
slaveEightOutputStatusTwenty OBJECT-TYPE
    SYNTAX      DisplayString
    MAX-ACCESS  read-write
    STATUS      current
    DESCRIPTION
	"The twentieth output status of slave 8"
    ::= { slaveEightOutputStatus 20}
slaveEightOutputStatusTwentyOne OBJECT-TYPE
    SYNTAX      DisplayString
    MAX-ACCESS  read-write
    STATUS      current
    DESCRIPTION
	"The twenty-first output status of slave 8"
    ::= { slaveEightOutputStatus 21}
slaveEightOutputStatusTwentyTwo OBJECT-TYPE
    SYNTAX      DisplayString
    MAX-ACCESS  read-write
    STATUS      current
    DESCRIPTION
	"The twenty-second output status of slave 8"
    ::= { slaveEightOutputStatus 22}
slaveEightOutputStatusTwentyThree OBJECT-TYPE
    SYNTAX      DisplayString
    MAX-ACCESS  read-write
    STATUS      current
    DESCRIPTION
	"The twenty-third output status of slave 8"
    ::= { slaveEightOutputStatus 23}
slaveEightOutputStatusTwentyFour OBJECT-TYPE
    SYNTAX      DisplayString
    MAX-ACCESS  read-write
    STATUS      current
    DESCRIPTION
	"The twenty-fourth output status of slave 8"
    ::= { slaveEightOutputStatus 24}

slaveEightOutputCurrent   OBJECT IDENTIFIER ::= { rpduSlaveEight 10}
slaveEightOutputCurrentOne OBJECT-TYPE
    SYNTAX      DisplayString
    MAX-ACCESS  read-only
    STATUS      current
    DESCRIPTION
	"The current value of the first output of the slave 8"
    ::= { slaveEightOutputCurrent 1}
slaveEightOutputCurrentTwo OBJECT-TYPE
    SYNTAX      DisplayString
    MAX-ACCESS  read-only
    STATUS      current
    DESCRIPTION
	"The current value of the second output of the slave 8"
    ::= { slaveEightOutputCurrent 2}
slaveEightOutputCurrentThree OBJECT-TYPE
    SYNTAX      DisplayString
    MAX-ACCESS  read-only
    STATUS      current
    DESCRIPTION
	"The current value of the third output of the slave 8"
    ::= { slaveEightOutputCurrent 3}
slaveEightOutputCurrentFour OBJECT-TYPE
    SYNTAX      DisplayString
    MAX-ACCESS  read-only
    STATUS      current
    DESCRIPTION
	"The current value of the fourth output of the slave 8"
    ::= { slaveEightOutputCurrent 4}
slaveEightOutputCurrentFive OBJECT-TYPE
    SYNTAX      DisplayString
    MAX-ACCESS  read-only
    STATUS      current
    DESCRIPTION
	"The current value of the fifth output of the slave 8"
    ::= { slaveEightOutputCurrent 5}
slaveEightOutputCurrentSix OBJECT-TYPE
    SYNTAX      DisplayString
    MAX-ACCESS  read-only
    STATUS      current
    DESCRIPTION
	"The current value of the sixth output of the slave 8"
    ::= { slaveEightOutputCurrent 6}
slaveEightOutputCurrentSeven OBJECT-TYPE
    SYNTAX      DisplayString
    MAX-ACCESS  read-only
    STATUS      current
    DESCRIPTION
	"The current value of the seventh output of the slave 8"
    ::= { slaveEightOutputCurrent 7}
slaveEightOutputCurrentEight OBJECT-TYPE
    SYNTAX      DisplayString
    MAX-ACCESS  read-only
    STATUS      current
    DESCRIPTION
	"The current value of the eighth output of the slave 8"
    ::= { slaveEightOutputCurrent 8}
slaveEightOutputCurrentNine OBJECT-TYPE
    SYNTAX      DisplayString
    MAX-ACCESS  read-only
    STATUS      current
    DESCRIPTION
	"The current value of the nineth output of the slave 8"
    ::= { slaveEightOutputCurrent 9}
slaveEightOutputCurrentTen OBJECT-TYPE
    SYNTAX      DisplayString
    MAX-ACCESS  read-only
    STATUS      current
    DESCRIPTION
	"The current value of the tenth output of the slave 8"
    ::= { slaveEightOutputCurrent 10}
slaveEightOutputCurrentEleven OBJECT-TYPE
    SYNTAX      DisplayString
    MAX-ACCESS  read-only
    STATUS      current
    DESCRIPTION
	"The current value of the eleventh output of the slave 8"
    ::= { slaveEightOutputCurrent 11}
slaveEightOutputCurrentTwelve OBJECT-TYPE
    SYNTAX      DisplayString
    MAX-ACCESS  read-only
    STATUS      current
    DESCRIPTION
	"The current value of the twelfth output of the slave 8"
    ::= { slaveEightOutputCurrent 12}
slaveEightOutputCurrentThirteen OBJECT-TYPE
    SYNTAX      DisplayString
    MAX-ACCESS  read-only
    STATUS      current
    DESCRIPTION
	"The current value of the thirteenth output of the slave 8"
    ::= { slaveEightOutputCurrent 13}
slaveEightOutputCurrentFourteen OBJECT-TYPE
    SYNTAX      DisplayString
    MAX-ACCESS  read-only
    STATUS      current
    DESCRIPTION
	"The current value of the fourteenth output of the slave 8"
    ::= { slaveEightOutputCurrent 14}
slaveEightOutputCurrentFifteen OBJECT-TYPE
    SYNTAX      DisplayString
    MAX-ACCESS  read-only
    STATUS      current
    DESCRIPTION
	"The current value of the fifteenth output of the slave 8"
    ::= { slaveEightOutputCurrent 15}
slaveEightOutputCurrentSixteen OBJECT-TYPE
    SYNTAX      DisplayString
    MAX-ACCESS  read-only
    STATUS      current
    DESCRIPTION
	"The current value of the sixteenth output of the slave 8"
    ::= { slaveEightOutputCurrent 16}
slaveEightOutputCurrentSeventeen OBJECT-TYPE
    SYNTAX      DisplayString
    MAX-ACCESS  read-only
    STATUS      current
    DESCRIPTION
	"The current value of the seventeenth output of the slave 8"
    ::= { slaveEightOutputCurrent 17}
slaveEightOutputCurrentEighteen OBJECT-TYPE
    SYNTAX      DisplayString
    MAX-ACCESS  read-only
    STATUS      current
    DESCRIPTION
	"The current value of the eighteenth output of the slave 8"
    ::= { slaveEightOutputCurrent 18}
slaveEightOutputCurrentNineteen OBJECT-TYPE
    SYNTAX      DisplayString
    MAX-ACCESS  read-only
    STATUS      current
    DESCRIPTION
	"The current value of the nineteenth output of the slave 8"
    ::= { slaveEightOutputCurrent 19}
slaveEightOutputCurrentTwenty OBJECT-TYPE
    SYNTAX      DisplayString
    MAX-ACCESS  read-only
    STATUS      current
    DESCRIPTION
	"The current value of the twentieth output of the slave 8"
    ::= { slaveEightOutputCurrent 20}
slaveEightOutputCurrentTwentyOne OBJECT-TYPE
    SYNTAX      DisplayString
    MAX-ACCESS  read-only
    STATUS      current
    DESCRIPTION
	"The current value of the twenty-first output of the slave 8"
    ::= { slaveEightOutputCurrent 21}
slaveEightOutputCurrentTwentyTwo OBJECT-TYPE
    SYNTAX      DisplayString
    MAX-ACCESS  read-only
    STATUS      current
    DESCRIPTION
	"The current value of the twenty-second output of the slave 8"
    ::= { slaveEightOutputCurrent 22}
slaveEightOutputCurrentTwentyThree OBJECT-TYPE
    SYNTAX      DisplayString
    MAX-ACCESS  read-only
    STATUS      current
    DESCRIPTION
	"The current value of the twenty-third output of the slave 8"
    ::= { slaveEightOutputCurrent 23}
slaveEightOutputCurrentTwentyFour OBJECT-TYPE
    SYNTAX      DisplayString
    MAX-ACCESS  read-only
    STATUS      current
    DESCRIPTION
	"The current value of the twenty-fourth output of the slave 8"
    ::= { slaveEightOutputCurrent 24}

slaveEightOutputCurrentMin   OBJECT IDENTIFIER ::= { rpduSlaveEight 11}
slaveEightOutputCurrentMinOne OBJECT-TYPE
    SYNTAX      DisplayString
    MAX-ACCESS  read-only
    STATUS      current
    DESCRIPTION
	"The Min. current value of the first output of the slave 8"
    ::= { slaveEightOutputCurrentMin 1}
slaveEightOutputCurrentMinTwo OBJECT-TYPE
    SYNTAX      DisplayString
    MAX-ACCESS  read-only
    STATUS      current
    DESCRIPTION
	"The Min. current value of the second output of the slave 8"
    ::= { slaveEightOutputCurrentMin 2}
slaveEightOutputCurrentMinThree OBJECT-TYPE
    SYNTAX      DisplayString
    MAX-ACCESS  read-only
    STATUS      current
    DESCRIPTION
	"The Min. current value of the third output of the slave 8"
    ::= { slaveEightOutputCurrentMin 3}
slaveEightOutputCurrentMinFour OBJECT-TYPE
    SYNTAX      DisplayString
    MAX-ACCESS  read-only
    STATUS      current
    DESCRIPTION
	"The Min. current value of the fourth output of the slave 8"
    ::= { slaveEightOutputCurrentMin 4}
slaveEightOutputCurrentMinFive OBJECT-TYPE
    SYNTAX      DisplayString
    MAX-ACCESS  read-only
    STATUS      current
    DESCRIPTION
	"The Min. current value of the fifth output of the slave 8"
    ::= { slaveEightOutputCurrentMin 5}
slaveEightOutputCurrentMinSix OBJECT-TYPE
    SYNTAX      DisplayString
    MAX-ACCESS  read-only
    STATUS      current
    DESCRIPTION
	"The Min. current value of the sixth output of the slave 8"
    ::= { slaveEightOutputCurrentMin 6}
slaveEightOutputCurrentMinSeven OBJECT-TYPE
    SYNTAX      DisplayString
    MAX-ACCESS  read-only
    STATUS      current
    DESCRIPTION
	"The Min. current value of the seventh output of the slave 8"
    ::= { slaveEightOutputCurrentMin 7}
slaveEightOutputCurrentMinEight OBJECT-TYPE
    SYNTAX      DisplayString
    MAX-ACCESS  read-only
    STATUS      current
    DESCRIPTION
	"The Min. current value of the eighth output of the slave 8"
    ::= { slaveEightOutputCurrentMin 8}
slaveEightOutputCurrentMinNine OBJECT-TYPE
    SYNTAX      DisplayString
    MAX-ACCESS  read-only
    STATUS      current
    DESCRIPTION
	"The Min. current value of the nineth output of the slave 8"
    ::= { slaveEightOutputCurrentMin 9}
slaveEightOutputCurrentMinTen OBJECT-TYPE
    SYNTAX      DisplayString
    MAX-ACCESS  read-only
    STATUS      current
    DESCRIPTION
	"The Min. current value of the tenth output of the slave 8"
    ::= { slaveEightOutputCurrentMin 10}
slaveEightOutputCurrentMinEleven OBJECT-TYPE
    SYNTAX      DisplayString
    MAX-ACCESS  read-only
    STATUS      current
    DESCRIPTION
	"The Min. current value of the eleventh output of the slave 8"
    ::= { slaveEightOutputCurrentMin 11}
slaveEightOutputCurrentMinTwleve OBJECT-TYPE
    SYNTAX      DisplayString
    MAX-ACCESS  read-only
    STATUS      current
    DESCRIPTION
	"The Min. current value of the twelfth output of the slave 8"
    ::= { slaveEightOutputCurrentMin 12}
slaveEightOutputCurrentMinThirteen OBJECT-TYPE
    SYNTAX      DisplayString
    MAX-ACCESS  read-only
    STATUS      current
    DESCRIPTION
	"The Min. current value of the thirteenth output of the slave 8"
    ::= { slaveEightOutputCurrentMin 13}
slaveEightOutputCurrentMinFourteen OBJECT-TYPE
    SYNTAX      DisplayString
    MAX-ACCESS  read-only
    STATUS      current
    DESCRIPTION
	"The Min. current value of the fourteenth output of the slave 8"
    ::= { slaveEightOutputCurrentMin 14}
slaveEightOutputCurrentMinFifteen OBJECT-TYPE
    SYNTAX      DisplayString
    MAX-ACCESS  read-only
    STATUS      current
    DESCRIPTION
	"The Min. current value of the fifteenth output of the slave 8"
    ::= { slaveEightOutputCurrentMin 15}
slaveEightOutputCurrentMinSixteen OBJECT-TYPE
    SYNTAX      DisplayString
    MAX-ACCESS  read-only
    STATUS      current
    DESCRIPTION
	"The Min. current value of the sixteenth output of the slave 8"
    ::= { slaveEightOutputCurrentMin 16}
slaveEightOutputCurrentMinSeventeen OBJECT-TYPE
    SYNTAX      DisplayString
    MAX-ACCESS  read-only
    STATUS      current
    DESCRIPTION
	"The Min. current value of the seventeenth output of the slave 8"
    ::= { slaveEightOutputCurrentMin 17}
slaveEightOutputCurrentMinEighteen OBJECT-TYPE
    SYNTAX      DisplayString
    MAX-ACCESS  read-only
    STATUS      current
    DESCRIPTION
	"The Min. current value of the eighteenth output of the slave 8"
    ::= { slaveEightOutputCurrentMin 18}
slaveEightOutputCurrentMinNineteen OBJECT-TYPE
    SYNTAX      DisplayString
    MAX-ACCESS  read-only
    STATUS      current
    DESCRIPTION
	"The Min. current value of the nineteenth output of the slave 8"
    ::= { slaveEightOutputCurrentMin 19}
slaveEightOutputCurrentMinTwenty OBJECT-TYPE
    SYNTAX      DisplayString
    MAX-ACCESS  read-only
    STATUS      current
    DESCRIPTION
	"The Min. current value of the twentieth output of the slave 8"
    ::= { slaveEightOutputCurrentMin 20}
slaveEightOutputCurrentMinTwentyOne OBJECT-TYPE
    SYNTAX      DisplayString
    MAX-ACCESS  read-only
    STATUS      current
    DESCRIPTION
	"The Min. current value of the twentyth-first output of the slave 8"
    ::= { slaveEightOutputCurrentMin 21}
slaveEightOutputCurrentMinTwentyTwo OBJECT-TYPE
    SYNTAX      DisplayString
    MAX-ACCESS  read-only
    STATUS      current
    DESCRIPTION
	"The Min. current value of the twentyth-second output of the slave 8"
    ::= { slaveEightOutputCurrentMin 22}
slaveEightOutputCurrentMinTwentyThree OBJECT-TYPE
    SYNTAX      DisplayString
    MAX-ACCESS  read-only
    STATUS      current
    DESCRIPTION
	"The Min. current value of the twentyth-third output of the slave 8"
    ::= { slaveEightOutputCurrentMin 23}
slaveEightOutputCurrentMinTwentyFour OBJECT-TYPE
    SYNTAX      DisplayString
    MAX-ACCESS  read-only
    STATUS      current
    DESCRIPTION
	"The Min. current value of the twentyth-fourth output of the slave 8"
    ::= { slaveEightOutputCurrentMin 24}




slaveEightOutputCurrentMax   OBJECT IDENTIFIER ::= { rpduSlaveEight 12}
slaveEightOutputCurrentMaxOne OBJECT-TYPE
    SYNTAX      DisplayString
    MAX-ACCESS  read-only
    STATUS      current
    DESCRIPTION
	"The Max. current value of the first output of the slave 8"
    ::= { slaveEightOutputCurrentMax 1}
slaveEightOutputCurrentMaxTwo OBJECT-TYPE
    SYNTAX      DisplayString
    MAX-ACCESS  read-only
    STATUS      current
    DESCRIPTION
	"The Max. current value of the second output of the slave 8"
    ::= { slaveEightOutputCurrentMax 2}
slaveEightOutputCurrentMaxThree OBJECT-TYPE
    SYNTAX      DisplayString
    MAX-ACCESS  read-only
    STATUS      current
    DESCRIPTION
	"The Max. current value of the third output of the slave 8"
    ::= { slaveEightOutputCurrentMax 3}
slaveEightOutputCurrentMaxFour OBJECT-TYPE
    SYNTAX      DisplayString
    MAX-ACCESS  read-only
    STATUS      current
    DESCRIPTION
	"The Max. current value of the fourth output of the slave 8"
    ::= { slaveEightOutputCurrentMax 4}
slaveEightOutputCurrentMaxFive OBJECT-TYPE
    SYNTAX      DisplayString
    MAX-ACCESS  read-only
    STATUS      current
    DESCRIPTION
	"The Max. current value of the fifth output of the slave 8"
    ::= { slaveEightOutputCurrentMax 5}
slaveEightOutputCurrentMaxSix OBJECT-TYPE
    SYNTAX      DisplayString
    MAX-ACCESS  read-only
    STATUS      current
    DESCRIPTION
	"The Max. current value of the sixth output of the slave 8"
    ::= { slaveEightOutputCurrentMax 6}
slaveEightOutputCurrentMaxSeven OBJECT-TYPE
    SYNTAX      DisplayString
    MAX-ACCESS  read-only
    STATUS      current
    DESCRIPTION
	"The Max. current value of the seventh output of the slave 8"
    ::= { slaveEightOutputCurrentMax 7}
slaveEightOutputCurrentMaxEight OBJECT-TYPE
    SYNTAX      DisplayString
    MAX-ACCESS  read-only
    STATUS      current
    DESCRIPTION
	"The Max. current value of the eighth output of the slave 8"
    ::= { slaveEightOutputCurrentMax 8}
slaveEightOutputCurrentMaxNine OBJECT-TYPE
    SYNTAX      DisplayString
    MAX-ACCESS  read-only
    STATUS      current
    DESCRIPTION
	"The Max. current value of the nineth output of the slave 8"
    ::= { slaveEightOutputCurrentMax 9}
slaveEightOutputCurrentMaxTen OBJECT-TYPE
    SYNTAX      DisplayString
    MAX-ACCESS  read-only
    STATUS      current
    DESCRIPTION
	"The Max. current value of the tenth output of the slave 8"
    ::= { slaveEightOutputCurrentMax 10}
slaveEightOutputCurrentMaxEleven OBJECT-TYPE
    SYNTAX      DisplayString
    MAX-ACCESS  read-only
    STATUS      current
    DESCRIPTION
	"The Max. current value of the eleventh output of the slave 8"
    ::= { slaveEightOutputCurrentMax 11}
slaveEightOutputCurrentMaxTwleve OBJECT-TYPE
    SYNTAX      DisplayString
    MAX-ACCESS  read-only
    STATUS      current
    DESCRIPTION
	"The Max. current value of the twelfth output of the slave 8"
    ::= { slaveEightOutputCurrentMax 12}
slaveEightOutputCurrentMaxThirteen OBJECT-TYPE
    SYNTAX      DisplayString
    MAX-ACCESS  read-only
    STATUS      current
    DESCRIPTION
	"The Max. current value of the thirteenth output of the slave 8"
    ::= { slaveEightOutputCurrentMax 13}
slaveEightOutputCurrentMaxFourteen OBJECT-TYPE
    SYNTAX      DisplayString
    MAX-ACCESS  read-only
    STATUS      current
    DESCRIPTION
	"The Max. current value of the fourteenth output of the slave 8"
    ::= { slaveEightOutputCurrentMax 14}
slaveEightOutputCurrentMaxFifteen OBJECT-TYPE
    SYNTAX      DisplayString
    MAX-ACCESS  read-only
    STATUS      current
    DESCRIPTION
	"The Max. current value of the fifteenth output of the slave 8"
    ::= { slaveEightOutputCurrentMax 15}
slaveEightOutputCurrentMaxSixteen OBJECT-TYPE
    SYNTAX      DisplayString
    MAX-ACCESS  read-only
    STATUS      current
    DESCRIPTION
	"The Max. current value of the sixteenth output of the slave 8"
    ::= { slaveEightOutputCurrentMax 16}
slaveEightOutputCurrentMaxSeventeen OBJECT-TYPE
    SYNTAX      DisplayString
    MAX-ACCESS  read-only
    STATUS      current
    DESCRIPTION
	"The Max. current value of the seventeenth output of the slave 8"
    ::= { slaveEightOutputCurrentMax 17}
slaveEightOutputCurrentMaxEighteen OBJECT-TYPE
    SYNTAX      DisplayString
    MAX-ACCESS  read-only
    STATUS      current
    DESCRIPTION
	"The Max. current value of the eighteenth output of the slave 8"
    ::= { slaveEightOutputCurrentMax 18}
slaveEightOutputCurrentMaxNineteen OBJECT-TYPE
    SYNTAX      DisplayString
    MAX-ACCESS  read-only
    STATUS      current
    DESCRIPTION
	"The Max. current value of the nineteenth output of the slave 8"
    ::= { slaveEightOutputCurrentMax 19}
slaveEightOutputCurrentMaxTwenty OBJECT-TYPE
    SYNTAX      DisplayString
    MAX-ACCESS  read-only
    STATUS      current
    DESCRIPTION
	"The Max. current value of the twentieth output of the slave 8"
    ::= { slaveEightOutputCurrentMax 20}
slaveEightOutputCurrentMaxTwentyOne OBJECT-TYPE
    SYNTAX      DisplayString
    MAX-ACCESS  read-only
    STATUS      current
    DESCRIPTION
	"The Max. current value of the twenty-first output of the slave 8"
    ::= { slaveEightOutputCurrentMax 21}
slaveEightOutputCurrentMaxTwentyTwo OBJECT-TYPE
    SYNTAX      DisplayString
    MAX-ACCESS  read-only
    STATUS      current
    DESCRIPTION
	"The Max. current value of the twenty-second output of the slave 8"
    ::= { slaveEightOutputCurrentMax 22}
slaveEightOutputCurrentMaxTwentyThree OBJECT-TYPE
    SYNTAX      DisplayString
    MAX-ACCESS  read-only
    STATUS      current
    DESCRIPTION
	"The Max. current value of the twenty-third output of the slave 8"
    ::= { slaveEightOutputCurrentMax 23}
slaveEightOutputCurrentMaxTwentyFour OBJECT-TYPE
    SYNTAX      DisplayString
    MAX-ACCESS  read-only
    STATUS      current
    DESCRIPTION
	"The Max. current value of the twenty-fourth output of the slave 8"
    ::= { slaveEightOutputCurrentMax 24}


slaveEightOutputCurrentEnergy  OBJECT IDENTIFIER ::= { rpduSlaveEight 13}
slaveEightOutputCurrentEnergyOne OBJECT-TYPE
    SYNTAX	DisplayString
    MAX-ACCESS	read-only
    STATUS	current
    DESCRIPTION
	"The energy value of the first output of the slave 8"
    ::={slaveEightOutputCurrentEnergy 1}
slaveEightOutputCurrentEnergyTwo OBJECT-TYPE
    SYNTAX	DisplayString
    MAX-ACCESS	read-only
    STATUS	current
    DESCRIPTION
	"The energy value of the second output of the slave 8"
    ::={slaveEightOutputCurrentEnergy 2}
slaveEightOutputCurrentEnergyThree OBJECT-TYPE
    SYNTAX	DisplayString
    MAX-ACCESS	read-only
    STATUS	current
    DESCRIPTION
	"The energy value of the third output of the slave 8"
    ::={slaveEightOutputCurrentEnergy 3}
slaveEightOutputCurrentEnergyFour OBJECT-TYPE
    SYNTAX	DisplayString
    MAX-ACCESS	read-only
    STATUS	current
    DESCRIPTION
	"The energy value of the fourth output of the slave 8"
    ::={slaveEightOutputCurrentEnergy 4}
slaveEightOutputCurrentEnergyFive OBJECT-TYPE
    SYNTAX	DisplayString
    MAX-ACCESS	read-only
    STATUS	current
    DESCRIPTION
	"The energy value of the fifth output of the slave 8"
    ::={slaveEightOutputCurrentEnergy 5}
slaveEightOutputCurrentEnergySix OBJECT-TYPE
    SYNTAX	DisplayString
    MAX-ACCESS	read-only
    STATUS	current
    DESCRIPTION
	"The energy value of the sixth output of the slave 8"
    ::={slaveEightOutputCurrentEnergy 6}
slaveEightOutputCurrentEnergySeven OBJECT-TYPE
    SYNTAX	DisplayString
    MAX-ACCESS	read-only
    STATUS	current
    DESCRIPTION
	"The energy value of the seventh output of the slave 8"
    ::={slaveEightOutputCurrentEnergy 7}
slaveEightOutputCurrentEnergyEight OBJECT-TYPE
    SYNTAX	DisplayString
    MAX-ACCESS	read-only
    STATUS	current
    DESCRIPTION
	"The energy value of the eighth output of the slave 8"
    ::={slaveEightOutputCurrentEnergy 8}
slaveEightOutputCurrentEnergyNine OBJECT-TYPE
    SYNTAX	DisplayString
    MAX-ACCESS	read-only
    STATUS	current
    DESCRIPTION
	"The energy value of the nineth output of the slave 8"
    ::={slaveEightOutputCurrentEnergy 9}
slaveEightOutputCurrentEnergyTen OBJECT-TYPE
    SYNTAX	DisplayString
    MAX-ACCESS	read-only
    STATUS	current
    DESCRIPTION
	"The energy value of the tenth output of the slave 8"
    ::={slaveEightOutputCurrentEnergy 10}
slaveEightOutputCurrentEnergyEleven OBJECT-TYPE
    SYNTAX	DisplayString
    MAX-ACCESS	read-only
    STATUS	current
    DESCRIPTION
	"The energy value of the eleventh output of the slave 8"
    ::={slaveEightOutputCurrentEnergy 11}
slaveEightOutputCurrentEnergyTwelve OBJECT-TYPE
    SYNTAX	DisplayString
    MAX-ACCESS	read-only
    STATUS	current
    DESCRIPTION
	"The energy value of the twelfth output of the slave 8"
    ::={slaveEightOutputCurrentEnergy 12}
slaveEightOutputCurrentEnergyThirteen OBJECT-TYPE
    SYNTAX	DisplayString
    MAX-ACCESS	read-only
    STATUS	current
    DESCRIPTION
	"The energy value of the thirteenth output of the slave 8"
    ::={slaveEightOutputCurrentEnergy 13}
slaveEightOutputCurrentEnergyFourteen OBJECT-TYPE
    SYNTAX	DisplayString
    MAX-ACCESS	read-only
    STATUS	current
    DESCRIPTION
	"The energy value of the fourteenth output of the slave 8"
    ::={slaveEightOutputCurrentEnergy 14}
slaveEightOutputCurrentEnergyFifteen OBJECT-TYPE
    SYNTAX	DisplayString
    MAX-ACCESS	read-only
    STATUS	current
    DESCRIPTION
	"The energy value of the fifteenth output of the slave 8"
    ::={slaveEightOutputCurrentEnergy 15}
slaveEightOutputCurrentEnergySixteen OBJECT-TYPE
    SYNTAX	DisplayString
    MAX-ACCESS	read-only
    STATUS	current
    DESCRIPTION
	"The energy value of the sixteenth output of the slave 8"
    ::={slaveEightOutputCurrentEnergy 16}
slaveEightOutputCurrentEnergySeventeen OBJECT-TYPE
    SYNTAX	DisplayString
    MAX-ACCESS	read-only
    STATUS	current
    DESCRIPTION
	"The energy value of the seventeenth output of the slave 8"
    ::={slaveEightOutputCurrentEnergy 17}
slaveEightOutputCurrentEnergyEighteen OBJECT-TYPE
    SYNTAX	DisplayString
    MAX-ACCESS	read-only
    STATUS	current
    DESCRIPTION
	"The energy value of the eighteenth output of the slave 8"
    ::={slaveEightOutputCurrentEnergy 18}
slaveEightOutputCurrentEnergyNineteen OBJECT-TYPE
    SYNTAX	DisplayString
    MAX-ACCESS	read-only
    STATUS	current
    DESCRIPTION
	"The energy value of the nineteenth output of the slave 8"
    ::={slaveEightOutputCurrentEnergy 19}
slaveEightOutputCurrentEnergyTwenty OBJECT-TYPE
    SYNTAX	DisplayString
    MAX-ACCESS	read-only
    STATUS	current
    DESCRIPTION
	"The energy value of the twentieth output of the slave 8"
    ::={slaveEightOutputCurrentEnergy 20}
slaveEightOutputCurrentEnergyTwentyOne OBJECT-TYPE
    SYNTAX	DisplayString
    MAX-ACCESS	read-only
    STATUS	current
    DESCRIPTION
	"The energy value of the twenty-first output of the slave 8"
    ::={slaveEightOutputCurrentEnergy 21}
slaveEightOutputCurrentEnergyTwentyTwo OBJECT-TYPE
    SYNTAX	DisplayString
    MAX-ACCESS	read-only
    STATUS	current
    DESCRIPTION
	"The energy value of the twenty-second output of the slave 8"
    ::={slaveEightOutputCurrentEnergy 22}
slaveEightOutputCurrentEnergyTwentyThree OBJECT-TYPE
    SYNTAX	DisplayString
    MAX-ACCESS	read-only
    STATUS	current
    DESCRIPTION
	"The energy value of the twenty-third output of the slave 8"
    ::={slaveEightOutputCurrentEnergy 23}
slaveEightOutputCurrentEnergyTwentyFour OBJECT-TYPE
    SYNTAX	DisplayString
    MAX-ACCESS	read-only
    STATUS	current
    DESCRIPTION
	"The energy value of the twenty-fourth output of the slave 8"
    ::={slaveEightOutputCurrentEnergy 24}

-------------------------------Slave9 ------------------------------------------
rpduDeviceTen OBJECT IDENTIFIER ::= { rpdu 10}
rpduSlaveNine OBJECT IDENTIFIER ::= { rpduDeviceTen 1}

slaveNineName OBJECT-TYPE
    SYNTAX      DisplayString
    MAX-ACCESS  read-write
    STATUS      current
    DESCRIPTION
	"This is the tenth device."
    ::= { rpduSlaveNine 1}
    
slaveNineType OBJECT-TYPE
    SYNTAX      DisplayString
    MAX-ACCESS  read-only
    STATUS      current
    DESCRIPTION
	"This is device type "
    ::= { rpduSlaveNine  2}
    
slaveNineOutputNumber OBJECT-TYPE 
    SYNTAX      Integer32
    MAX-ACCESS  read-only
    STATUS      current
    DESCRIPTION
	"This is the output quantity"
::= { rpduSlaveNine  7}
    
slaveNineLineOne OBJECT IDENTIFIER ::= { rpduSlaveNine  3}
slaveNineLineOnePower OBJECT-TYPE
    SYNTAX      DisplayString
    MAX-ACCESS  read-only
    STATUS      current
    DESCRIPTION
	"The power of phase one"
    ::= { slaveNineLineOne 1}
slaveNineLineOnePF OBJECT-TYPE
    SYNTAX      DisplayString
    MAX-ACCESS  read-only
    STATUS      current
    DESCRIPTION
	"The power factor of phase one"
    ::= { slaveNineLineOne 2}
    
slaveNineLineOneEnergy OBJECT-TYPE
    SYNTAX      DisplayString
    MAX-ACCESS  read-only
    STATUS      current
    DESCRIPTION
	"The energy of phase one"
    ::= { slaveNineLineOne 3}
slaveNineLineOneCurrent OBJECT-TYPE
    SYNTAX      DisplayString
    MAX-ACCESS  read-only
    STATUS      current
    DESCRIPTION
	"The current of phase one"
    ::= { slaveNineLineOne 4}
slaveNineLineOneVoltage OBJECT-TYPE
    SYNTAX      Integer32
    MAX-ACCESS  read-only
    STATUS      current
    DESCRIPTION
	"The voltage of phase one"
    ::= { slaveNineLineOne 5}
slaveNineLineOneCurrentMin OBJECT-TYPE
    SYNTAX      DisplayString
    MAX-ACCESS  read-only
    STATUS      current
    DESCRIPTION
	"The Min. current value of phase one"
	::= { slaveNineLineOne 6}
slaveNineLineOneCurrentMax OBJECT-TYPE
    SYNTAX      DisplayString
    MAX-ACCESS  read-only
    STATUS      current
    DESCRIPTION
	"The Max. current value of phase one"
    ::= { slaveNineLineOne 7}
    
slaveNineLineOneVoltageMin OBJECT-TYPE
    SYNTAX      Integer32
    MAX-ACCESS  read-only
    STATUS      current
    DESCRIPTION
	"The Min. voltage value of phase one"
    ::= { slaveNineLineOne 8}
    
slaveNineLineOneVoltageMax OBJECT-TYPE
    SYNTAX      Integer32
    MAX-ACCESS  read-only
    STATUS      current
    DESCRIPTION
	"The Max. voltage value of phase one"
    ::= { slaveNineLineOne 9}


slaveNineLineTwo OBJECT IDENTIFIER ::= { rpduSlaveNine  4}
slaveNineLineTwoPower OBJECT-TYPE
    SYNTAX      DisplayString
    MAX-ACCESS  read-only
    STATUS      current
    DESCRIPTION
	"The power of phase two"
    ::= { slaveNineLineTwo 1}

slaveNineLineTwoPF OBJECT-TYPE
    SYNTAX      DisplayString
    MAX-ACCESS  read-only
    STATUS      current
    DESCRIPTION
	"The power factor of phase two"   
    ::= { slaveNineLineTwo 2}
    
slaveNineLineTwoEnergy OBJECT-TYPE
    SYNTAX      DisplayString
    MAX-ACCESS  read-only
    STATUS      current
    DESCRIPTION
	"The energy of phase two"
    ::= { slaveNineLineTwo 3}
slaveNineLineTwoCurrent OBJECT-TYPE           
    SYNTAX      DisplayString 
    MAX-ACCESS  read-only
    STATUS      current
    DESCRIPTION
	"The current of phase two"
    ::= { slaveNineLineTwo 4}
slaveNineLineTwoVoltage OBJECT-TYPE
    SYNTAX      Integer32
    MAX-ACCESS  read-only
    STATUS      current
    DESCRIPTION
	"The voltage of phase two"
    ::= { slaveNineLineTwo 5}
slaveNineLineTwoCurrentMin OBJECT-TYPE
    SYNTAX      DisplayString
    MAX-ACCESS  read-only
    STATUS      current
    DESCRIPTION
	"The Min. current value of phase two"
    ::= { slaveNineLineTwo 6}
slaveNineLineTwoCurrentMax OBJECT-TYPE
    SYNTAX      DisplayString
    MAX-ACCESS  read-only
    STATUS      current
    DESCRIPTION
	"The Max. current value of phase two"
    ::= { slaveNineLineTwo 7}
    
slaveNineLineTwoVoltageMin OBJECT-TYPE
    SYNTAX      Integer32
    MAX-ACCESS  read-only
    STATUS      current
    DESCRIPTION
	"The Min. voltage value of phase two"
    ::= { slaveNineLineTwo 8}
    
slaveNineLineTwoVoltageMax OBJECT-TYPE
    SYNTAX      Integer32
    MAX-ACCESS  read-only
    STATUS      current
    DESCRIPTION
	"The Max. voltage value of phase two"
    ::= { slaveNineLineTwo 9}



slaveNineLineThree OBJECT IDENTIFIER ::= { rpduSlaveNine  5}
slaveNineLineThreePower OBJECT-TYPE
    SYNTAX      DisplayString
    MAX-ACCESS  read-only
    STATUS      current
    DESCRIPTION
	"The power of phase three"
    ::= { slaveNineLineThree 1}

slaveNineLineThreePF OBJECT-TYPE
    SYNTAX      DisplayString
    MAX-ACCESS  read-only
    STATUS      current
    DESCRIPTION
	"The power factor of phase three"     
    ::= { slaveNineLineThree 2}
    
slaveNineLineThreeEnergy OBJECT-TYPE
    SYNTAX      DisplayString
    MAX-ACCESS  read-only
    STATUS      current
    DESCRIPTION
	"The energy of phase three"
    ::= { slaveNineLineThree 3}
slaveNineLineThreeCurrent OBJECT-TYPE
    SYNTAX      DisplayString
    MAX-ACCESS  read-only
    STATUS      current
    DESCRIPTION
	"The current of phase three"
    ::= { slaveNineLineThree 4}
slaveNineLineThreeVoltage OBJECT-TYPE
    SYNTAX      Integer32
    MAX-ACCESS  read-only
    STATUS      current
    DESCRIPTION
	"The voltage of phase three"
    ::= { slaveNineLineThree 5}
slaveNineLineThreeCurrentMin OBJECT-TYPE
    SYNTAX      DisplayString
    MAX-ACCESS  read-only
    STATUS      current
    DESCRIPTION
	"The Min. current value of phase three"
    ::= { slaveNineLineThree 6}
slaveNineLineThreeCurrentMax OBJECT-TYPE
    SYNTAX      DisplayString
    MAX-ACCESS  read-only
    STATUS      current
    DESCRIPTION
	"The Max. current value of phase three"
    ::= { slaveNineLineThree 7}
    
slaveNineLineThreeVoltageMin OBJECT-TYPE
    SYNTAX      Integer32
    MAX-ACCESS  read-only
    STATUS      current
    DESCRIPTION
	"The Min. voltage value of phase three"
    ::= { slaveNineLineThree 8}
    
slaveNineLineThreeVoltageMax OBJECT-TYPE
    SYNTAX      Integer32
    MAX-ACCESS  read-only
    STATUS      current
    DESCRIPTION
	"The Max. voltage value of phase three"
    ::= { slaveNineLineThree 9}


slaveNineSensor OBJECT IDENTIFIER ::= { rpduSlaveNine  6}
slaveNineTempOne OBJECT-TYPE
    SYNTAX      Integer32
    MAX-ACCESS  read-only
    STATUS      current
    DESCRIPTION
	"The first temperature sensor of slave 9"
    ::= { slaveNineSensor 1}
slaveNineTempTwo OBJECT-TYPE
    SYNTAX      Integer32
    MAX-ACCESS  read-only
    STATUS      current
    DESCRIPTION
	"The second temperature sensor of slave 9"
    ::= { slaveNineSensor 2}
slaveNineTempThree OBJECT-TYPE
    SYNTAX      Integer32
    MAX-ACCESS  read-only
    STATUS      current
    DESCRIPTION
	"The third temperature sensor of slave 9"
    ::= { slaveNineSensor 3}
slaveNineTempFour OBJECT-TYPE
    SYNTAX      Integer32
    MAX-ACCESS  read-only
    STATUS      current
    DESCRIPTION
	"The fourth temperature sensor of slave 9"
    ::= { slaveNineSensor 4}
slaveNineHumOne OBJECT-TYPE
    SYNTAX      Integer32
    MAX-ACCESS  read-only
    STATUS      current
    DESCRIPTION
	"The first humidity sensor of slave 9"
    ::= { slaveNineSensor 5}
slaveNineHumTwo OBJECT-TYPE
    SYNTAX      Integer32
    MAX-ACCESS  read-only
    STATUS      current
    DESCRIPTION
	"The second humidity sensor of slave 9"
    ::= { slaveNineSensor 6}
slaveNineHumThree OBJECT-TYPE
    SYNTAX      Integer32
    MAX-ACCESS  read-only
    STATUS      current
    DESCRIPTION
	"The third humidity sensor of slave 9"
    ::= { slaveNineSensor 7}
slaveNineHumFour OBJECT-TYPE
    SYNTAX      Integer32
    MAX-ACCESS  read-only
    STATUS      current
    DESCRIPTION
	"The fourth humidity sensor of slave 9"
    ::= { slaveNineSensor 8}
slaveNineDoorOne OBJECT-TYPE
    SYNTAX      DisplayString
    MAX-ACCESS  read-only
    STATUS      current
    DESCRIPTION
	"The first door sensor of slave 9"    
    ::= { slaveNineSensor 9}
slaveNineDoorTwo OBJECT-TYPE
    SYNTAX      DisplayString
    MAX-ACCESS  read-only
    STATUS      current
    DESCRIPTION
	"The second door sensor of slave 9"  
    ::= { slaveNineSensor 10}
slaveNineSmoke OBJECT-TYPE
    SYNTAX      DisplayString
    MAX-ACCESS  read-only
    STATUS      current
    DESCRIPTION
	"The smoke sensor of slave 9"
    ::= { slaveNineSensor 11}
slaveNineWater OBJECT-TYPE
    SYNTAX      DisplayString
    MAX-ACCESS  read-only
    STATUS      current
    DESCRIPTION
	"The water sensor of slave 9"
    ::= { slaveNineSensor 12}


	
        
slaveNineOutputName OBJECT IDENTIFIER ::= { rpduSlaveNine  8}
slaveNineOutputNameOne OBJECT-TYPE
    SYNTAX      DisplayString
    MAX-ACCESS  read-write
    STATUS      current
    DESCRIPTION
	"The first output name of slave 9"
    ::= { slaveNineOutputName 1}

slaveNineOutputNameTwo OBJECT-TYPE
    SYNTAX      DisplayString
    MAX-ACCESS  read-write
    STATUS      current
    DESCRIPTION
	"The second output name of slave 9"
    ::= { slaveNineOutputName 2}
slaveNineOutputNameThree OBJECT-TYPE
    SYNTAX      DisplayString
    MAX-ACCESS  read-write
    STATUS      current
    DESCRIPTION
	"The third output name of slave 9"
    ::= { slaveNineOutputName 3}
slaveNineOutputNameFour OBJECT-TYPE
    SYNTAX      DisplayString
    MAX-ACCESS  read-write
    STATUS      current
    DESCRIPTION
	"The fourth output name of slave 9"
    ::= { slaveNineOutputName 4}
slaveNineOutputNameFive OBJECT-TYPE
    SYNTAX      DisplayString
    MAX-ACCESS  read-write
    STATUS      current
    DESCRIPTION
	"The fifth output name of slave 9"
    ::= { slaveNineOutputName 5}
slaveNineOutputNameSix OBJECT-TYPE
    SYNTAX      DisplayString
    MAX-ACCESS  read-write
    STATUS      current
    DESCRIPTION
	"The sixth output name of slave 9"
    ::= { slaveNineOutputName 6}
slaveNineOutputNameSeven OBJECT-TYPE
    SYNTAX      DisplayString
    MAX-ACCESS  read-write
    STATUS      current
    DESCRIPTION
	"The seventh output name of slave 9"
    ::= { slaveNineOutputName 7}
slaveNineOutputNameEight OBJECT-TYPE
    SYNTAX      DisplayString
    MAX-ACCESS  read-write
    STATUS      current
    DESCRIPTION
	"The eighth output name of slave 9"
    ::= { slaveNineOutputName 8}
slaveNineOutputNameNine OBJECT-TYPE
    SYNTAX      DisplayString
    MAX-ACCESS  read-write
    STATUS      current
    DESCRIPTION
	"The nineth output name of slave 9"
    ::= { slaveNineOutputName 9}
slaveNineOutputNameTen OBJECT-TYPE
    SYNTAX      DisplayString
    MAX-ACCESS  read-write
    STATUS      current
    DESCRIPTION
	"The tenth output name of slave 9"
    ::= { slaveNineOutputName 10}
slaveNineOutputNameEleven OBJECT-TYPE
    SYNTAX      DisplayString
    MAX-ACCESS  read-write
    STATUS      current
    DESCRIPTION
	"The eleventh output name of slave 9"
    ::= { slaveNineOutputName 11}
slaveNineOutputNameTwelve OBJECT-TYPE
    SYNTAX      DisplayString
    MAX-ACCESS  read-write
    STATUS      current
    DESCRIPTION
	"The twelfth output name of slave 9"
    ::= { slaveNineOutputName 12}
slaveNineOutputNameThirteen OBJECT-TYPE
    SYNTAX      DisplayString
    MAX-ACCESS  read-write
    STATUS      current
    DESCRIPTION
	"The thirteenth output name of slave 9"
    ::= { slaveNineOutputName 13}
slaveNineOutputNameFourteen OBJECT-TYPE
    SYNTAX      DisplayString
    MAX-ACCESS  read-write
    STATUS      current
    DESCRIPTION
	"The fourteenth output name of slave 9"
    ::= { slaveNineOutputName 14}
slaveNineOutputNameFifteen OBJECT-TYPE
    SYNTAX      DisplayString
    MAX-ACCESS  read-write
    STATUS      current
    DESCRIPTION
	"The fifteenth output name of slave 9"
    ::= { slaveNineOutputName 15}
slaveNineOutputNameSixteen OBJECT-TYPE
    SYNTAX      DisplayString
    MAX-ACCESS  read-write
    STATUS      current
    DESCRIPTION
	"The sixteenth output name of slave 9"
    ::= { slaveNineOutputName 16}
slaveNineOutputNameSeventeen OBJECT-TYPE
    SYNTAX      DisplayString
    MAX-ACCESS  read-write
    STATUS      current
    DESCRIPTION
	"The seventeenth output name of slave 9"
    ::= { slaveNineOutputName 17}
slaveNineOutputNameEighteen OBJECT-TYPE
    SYNTAX      DisplayString
    MAX-ACCESS  read-write
    STATUS      current
    DESCRIPTION
	"The eighteenh output name of slave 9"
    ::= { slaveNineOutputName 18}
slaveNineOutputNameNineteen OBJECT-TYPE
    SYNTAX      DisplayString
    MAX-ACCESS  read-write
    STATUS      current
    DESCRIPTION
	"The nineteenth output name of slave 9"
    ::= { slaveNineOutputName 19}
slaveNineOutputNameTwenty OBJECT-TYPE
    SYNTAX      DisplayString
    MAX-ACCESS  read-write
    STATUS      current
    DESCRIPTION
	"The twentieth output name of slave 9"
    ::= { slaveNineOutputName 20}
slaveNineOutputNameTwentyOne OBJECT-TYPE
    SYNTAX      DisplayString
    MAX-ACCESS  read-write
    STATUS      current
    DESCRIPTION
	"The twenty-first output name of slave 9"
    ::= { slaveNineOutputName 21}
slaveNineOutputNameTwentyTwo OBJECT-TYPE
    SYNTAX      DisplayString
    MAX-ACCESS  read-write
    STATUS      current
    DESCRIPTION
	"The twenty-second output name of slave 9"
    ::= { slaveNineOutputName 22}
slaveNineOutputNameTwentyThree OBJECT-TYPE
    SYNTAX      DisplayString
    MAX-ACCESS  read-write
    STATUS      current
    DESCRIPTION
	"The twenty-third output name of slave 9"
    ::= { slaveNineOutputName 23}
slaveNineOutputNameTwentyFour OBJECT-TYPE
    SYNTAX      DisplayString
    MAX-ACCESS  read-write
    STATUS      current
    DESCRIPTION
	"The twenty-fourth output name of slave 9"
    ::= { slaveNineOutputName 24}


    
slaveNineOutputStatus OBJECT IDENTIFIER ::= { rpduSlaveNine  9}

slaveNineOutputStatusOne OBJECT-TYPE
    SYNTAX      DisplayString
    MAX-ACCESS  read-write
    STATUS      current
    DESCRIPTION
	"The first output status of slave 9"
    ::= { slaveNineOutputStatus 1}
slaveNineOutputStatusTwo OBJECT-TYPE
    SYNTAX      DisplayString
    MAX-ACCESS  read-write
    STATUS      current
    DESCRIPTION
	"The second output status of slave 9"
    ::= { slaveNineOutputStatus 2}

slaveNineOutputStatusThree OBJECT-TYPE
    SYNTAX      DisplayString
    MAX-ACCESS  read-write
    STATUS      current
    DESCRIPTION
	"The third output status of slave 9"
    ::= { slaveNineOutputStatus 3}
slaveNineOutputStatusFour OBJECT-TYPE
    SYNTAX      DisplayString
    MAX-ACCESS  read-write
    STATUS      current
    DESCRIPTION
	"The fourth output status of slave 9"
    ::= { slaveNineOutputStatus 4}
slaveNineOutputStatusFive OBJECT-TYPE
    SYNTAX      DisplayString
    MAX-ACCESS  read-write
    STATUS      current
    DESCRIPTION
	"The fifth output status of slave 9"
    ::= { slaveNineOutputStatus 5}
slaveNineOutputStatusSix OBJECT-TYPE
    SYNTAX      DisplayString
    MAX-ACCESS  read-write
    STATUS      current
    DESCRIPTION
	"The sixth output status of slave 9"
    ::= { slaveNineOutputStatus 6}
slaveNineOutputStatusSeven OBJECT-TYPE
    SYNTAX      DisplayString
    MAX-ACCESS  read-write
    STATUS      current
    DESCRIPTION
	"The seventh output status of slave 9"
    ::= { slaveNineOutputStatus 7}
slaveNineOutputStatusEight OBJECT-TYPE
    SYNTAX      DisplayString
    MAX-ACCESS  read-write
    STATUS      current
    DESCRIPTION
	"The eighth output status of slave 9"
    ::= { slaveNineOutputStatus 8}
slaveNineOutputStatusNine OBJECT-TYPE
    SYNTAX      DisplayString
    MAX-ACCESS  read-write
    STATUS      current
    DESCRIPTION
	"The nineth output status of slave 9"
    ::= { slaveNineOutputStatus 9}
slaveNineOutputStatusTen OBJECT-TYPE
    SYNTAX      DisplayString
    MAX-ACCESS  read-write
    STATUS      current
    DESCRIPTION
	"The tenth output status of slave 9"
    ::= { slaveNineOutputStatus 10}
slaveNineOutputStatusEleven OBJECT-TYPE
    SYNTAX      DisplayString
    MAX-ACCESS  read-write
    STATUS      current
    DESCRIPTION
	"The eleventh output status of slave 9"
    ::= { slaveNineOutputStatus 11}
slaveNineOutputStatusTwelve OBJECT-TYPE
    SYNTAX      DisplayString
    MAX-ACCESS  read-write
    STATUS      current
    DESCRIPTION
	"The twelfth output status of slave 9"
    ::= { slaveNineOutputStatus 12}
slaveNineOutputStatusThirteen OBJECT-TYPE
    SYNTAX      DisplayString
    MAX-ACCESS  read-write
    STATUS      current
    DESCRIPTION
	"The thirteenth output status of slave 9"
    ::= { slaveNineOutputStatus 13}
slaveNineOutputStatusFourteen OBJECT-TYPE
    SYNTAX      DisplayString
    MAX-ACCESS  read-write
    STATUS      current
    DESCRIPTION
	"The fourteenth output status of slave 9"
    ::= { slaveNineOutputStatus 14}
slaveNineOutputStatusFifteen OBJECT-TYPE
    SYNTAX      DisplayString
    MAX-ACCESS  read-write
    STATUS      current
    DESCRIPTION
	"The fifteenth output status of slave 9"
    ::= { slaveNineOutputStatus 15}
slaveNineOutputStatusSixteen OBJECT-TYPE
    SYNTAX      DisplayString
    MAX-ACCESS  read-write
    STATUS      current
    DESCRIPTION
	"The sixteenth output status of slave 9"
    ::= { slaveNineOutputStatus 16}
slaveNineOutputStatusSeventeen OBJECT-TYPE
    SYNTAX      DisplayString
    MAX-ACCESS  read-write
    STATUS      current
    DESCRIPTION
	"The seventeenth output status of slave 9"
    ::= { slaveNineOutputStatus 17}
slaveNineOutputStatusEighteen OBJECT-TYPE
    SYNTAX      DisplayString
    MAX-ACCESS  read-write
    STATUS      current
    DESCRIPTION
	"The eighteenth output status of slave 9"
    ::= { slaveNineOutputStatus 18}
slaveNineOutputStatusNineteen OBJECT-TYPE
    SYNTAX      DisplayString
    MAX-ACCESS  read-write
    STATUS      current
    DESCRIPTION
	"The nineteenth output status of slave 9"
    ::= { slaveNineOutputStatus 19}
slaveNineOutputStatusTwenty OBJECT-TYPE
    SYNTAX      DisplayString
    MAX-ACCESS  read-write
    STATUS      current
    DESCRIPTION
	"The twentieth output status of slave 9"
    ::= { slaveNineOutputStatus 20}
slaveNineOutputStatusTwentyOne OBJECT-TYPE
    SYNTAX      DisplayString
    MAX-ACCESS  read-write
    STATUS      current
    DESCRIPTION
	"The twenty-first output status of slave 9"
    ::= { slaveNineOutputStatus 21}
slaveNineOutputStatusTwentyTwo OBJECT-TYPE
    SYNTAX      DisplayString
    MAX-ACCESS  read-write
    STATUS      current
    DESCRIPTION
	"The twenty-second output status of slave 9"
    ::= { slaveNineOutputStatus 22}
slaveNineOutputStatusTwentyThree OBJECT-TYPE
    SYNTAX      DisplayString
    MAX-ACCESS  read-write
    STATUS      current
    DESCRIPTION
	"The twenty-third output status of slave 9"
    ::= { slaveNineOutputStatus 23}
slaveNineOutputStatusTwentyFour OBJECT-TYPE
    SYNTAX      DisplayString
    MAX-ACCESS  read-write
    STATUS      current
    DESCRIPTION
	"The twenty-fourth output status of slave 9"
    ::= { slaveNineOutputStatus 24}

slaveNineOutputCurrent   OBJECT IDENTIFIER ::= { rpduSlaveNine  10}
slaveNineOutputCurrentOne OBJECT-TYPE
    SYNTAX      DisplayString
    MAX-ACCESS  read-only
    STATUS      current
    DESCRIPTION
	"The current value of the first output of the slave 9"
    ::= { slaveNineOutputCurrent 1}
slaveNineOutputCurrentTwo OBJECT-TYPE
    SYNTAX      DisplayString
    MAX-ACCESS  read-only
    STATUS      current
    DESCRIPTION
	"The current value of the second output of the slave 9"
    ::= { slaveNineOutputCurrent 2}
slaveNineOutputCurrentThree OBJECT-TYPE
    SYNTAX      DisplayString
    MAX-ACCESS  read-only
    STATUS      current
    DESCRIPTION
	"The current value of the third output of the slave 9"
    ::= { slaveNineOutputCurrent 3}
slaveNineOutputCurrentFour OBJECT-TYPE
    SYNTAX      DisplayString
    MAX-ACCESS  read-only
    STATUS      current
    DESCRIPTION
	"The current value of the fourth output of the slave 9"
    ::= { slaveNineOutputCurrent 4}
slaveNineOutputCurrentFive OBJECT-TYPE
    SYNTAX      DisplayString
    MAX-ACCESS  read-only
    STATUS      current
    DESCRIPTION
	"The current value of the fifth output of the slave 9"
    ::= { slaveNineOutputCurrent 5}
slaveNineOutputCurrentSix OBJECT-TYPE
    SYNTAX      DisplayString
    MAX-ACCESS  read-only
    STATUS      current
    DESCRIPTION
	"The current value of the sixth output of the slave 9"
    ::= { slaveNineOutputCurrent 6}
slaveNineOutputCurrentSeven OBJECT-TYPE
    SYNTAX      DisplayString
    MAX-ACCESS  read-only
    STATUS      current
    DESCRIPTION
	"The current value of the seventh output of the slave 9"
    ::= { slaveNineOutputCurrent 7}
slaveNineOutputCurrentEight OBJECT-TYPE
    SYNTAX      DisplayString
    MAX-ACCESS  read-only
    STATUS      current
    DESCRIPTION
	"The current value of the eighth output of the slave 9"
    ::= { slaveNineOutputCurrent 8}
slaveNineOutputCurrentNine OBJECT-TYPE
    SYNTAX      DisplayString
    MAX-ACCESS  read-only
    STATUS      current
    DESCRIPTION
	"The current value of the nineth output of the slave 9"
    ::= { slaveNineOutputCurrent 9}
slaveNineOutputCurrentTen OBJECT-TYPE
    SYNTAX      DisplayString
    MAX-ACCESS  read-only
    STATUS      current
    DESCRIPTION
	"The current value of the tenth output of the slave 9"
    ::= { slaveNineOutputCurrent 10}
slaveNineOutputCurrentEleven OBJECT-TYPE
    SYNTAX      DisplayString
    MAX-ACCESS  read-only
    STATUS      current
    DESCRIPTION
	"The current value of the eleventh output of the slave 9"
    ::= { slaveNineOutputCurrent 11}
slaveNineOutputCurrentTwelve OBJECT-TYPE
    SYNTAX      DisplayString
    MAX-ACCESS  read-only
    STATUS      current
    DESCRIPTION
	"The current value of the twelfth output of the slave 9"
    ::= { slaveNineOutputCurrent 12}
slaveNineOutputCurrentThirteen OBJECT-TYPE
    SYNTAX      DisplayString
    MAX-ACCESS  read-only
    STATUS      current
    DESCRIPTION
	"The current value of the thirteenth output of the slave 9"
    ::= { slaveNineOutputCurrent 13}
slaveNineOutputCurrentFourteen OBJECT-TYPE
    SYNTAX      DisplayString
    MAX-ACCESS  read-only
    STATUS      current
    DESCRIPTION
	"The current value of the fourteenth output of the slave 9"
    ::= { slaveNineOutputCurrent 14}
slaveNineOutputCurrentFifteen OBJECT-TYPE
    SYNTAX      DisplayString
    MAX-ACCESS  read-only
    STATUS      current
    DESCRIPTION
	"The current value of the fifteenth output of the slave 9"
    ::= { slaveNineOutputCurrent 15}
slaveNineOutputCurrentSixteen OBJECT-TYPE
    SYNTAX      DisplayString
    MAX-ACCESS  read-only
    STATUS      current
    DESCRIPTION
	"The current value of the sixteenth output of the slave 9"
    ::= { slaveNineOutputCurrent 16}
slaveNineOutputCurrentSeventeen OBJECT-TYPE
    SYNTAX      DisplayString
    MAX-ACCESS  read-only
    STATUS      current
    DESCRIPTION
	"The current value of the seventeenth output of the slave 9"
    ::= { slaveNineOutputCurrent 17}
slaveNineOutputCurrentEighteen OBJECT-TYPE
    SYNTAX      DisplayString
    MAX-ACCESS  read-only
    STATUS      current
    DESCRIPTION
	"The current value of the eighteenth output of the slave 9"
    ::= { slaveNineOutputCurrent 18}
slaveNineOutputCurrentNineteen OBJECT-TYPE
    SYNTAX      DisplayString
    MAX-ACCESS  read-only
    STATUS      current
    DESCRIPTION
	"The current value of the nineteenth output of the slave 9"
    ::= { slaveNineOutputCurrent 19}
slaveNineOutputCurrentTwenty OBJECT-TYPE
    SYNTAX      DisplayString
    MAX-ACCESS  read-only
    STATUS      current
    DESCRIPTION
	"The current value of the twentieth output of the slave 9"
    ::= { slaveNineOutputCurrent 20}
slaveNineOutputCurrentTwentyOne OBJECT-TYPE
    SYNTAX      DisplayString
    MAX-ACCESS  read-only
    STATUS      current
    DESCRIPTION
	"The current value of the twenty-first output of the slave 9"
    ::= { slaveNineOutputCurrent 21}
slaveNineOutputCurrentTwentyTwo OBJECT-TYPE
    SYNTAX      DisplayString
    MAX-ACCESS  read-only
    STATUS      current
    DESCRIPTION
	"The current value of the twenty-second output of the slave 9"
    ::= { slaveNineOutputCurrent 22}
slaveNineOutputCurrentTwentyThree OBJECT-TYPE
    SYNTAX      DisplayString
    MAX-ACCESS  read-only
    STATUS      current
    DESCRIPTION
	"The current value of the twenty-third output of the slave 9"
    ::= { slaveNineOutputCurrent 23}
slaveNineOutputCurrentTwentyFour OBJECT-TYPE
    SYNTAX      DisplayString
    MAX-ACCESS  read-only
    STATUS      current
    DESCRIPTION
	"The current value of the twenty-fourth output of the slave 9"
    ::= { slaveNineOutputCurrent 24}

slaveNineOutputCurrentMin   OBJECT IDENTIFIER ::= { rpduSlaveNine  11}
slaveNineOutputCurrentMinOne OBJECT-TYPE
    SYNTAX      DisplayString
    MAX-ACCESS  read-only
    STATUS      current
    DESCRIPTION
	"The Min. current value of the first output of the slave 9"
    ::= { slaveNineOutputCurrentMin 1}
slaveNineOutputCurrentMinTwo OBJECT-TYPE
    SYNTAX      DisplayString
    MAX-ACCESS  read-only
    STATUS      current
    DESCRIPTION
	"The Min. current value of the second output of the slave 9"
    ::= { slaveNineOutputCurrentMin 2}
slaveNineOutputCurrentMinThree OBJECT-TYPE
    SYNTAX      DisplayString
    MAX-ACCESS  read-only
    STATUS      current
    DESCRIPTION
	"The Min. current value of the third output of the slave 9"
    ::= { slaveNineOutputCurrentMin 3}
slaveNineOutputCurrentMinFour OBJECT-TYPE
    SYNTAX      DisplayString
    MAX-ACCESS  read-only
    STATUS      current
    DESCRIPTION
	"The Min. current value of the fourth output of the slave 9"
    ::= { slaveNineOutputCurrentMin 4}
slaveNineOutputCurrentMinFive OBJECT-TYPE
    SYNTAX      DisplayString
    MAX-ACCESS  read-only
    STATUS      current
    DESCRIPTION
	"The Min. current value of the fifth output of the slave 9"
    ::= { slaveNineOutputCurrentMin 5}
slaveNineOutputCurrentMinSix OBJECT-TYPE
    SYNTAX      DisplayString
    MAX-ACCESS  read-only
    STATUS      current
    DESCRIPTION
	"The Min. current value of the sixth output of the slave 9"
    ::= { slaveNineOutputCurrentMin 6}
slaveNineOutputCurrentMinSeven OBJECT-TYPE
    SYNTAX      DisplayString
    MAX-ACCESS  read-only
    STATUS      current
    DESCRIPTION
	"The Min. current value of the seventh output of the slave 9"
    ::= { slaveNineOutputCurrentMin 7}
slaveNineOutputCurrentMinEight OBJECT-TYPE
    SYNTAX      DisplayString
    MAX-ACCESS  read-only
    STATUS      current
    DESCRIPTION
	"The Min. current value of the eighth output of the slave 9"
    ::= { slaveNineOutputCurrentMin 8}
slaveNineOutputCurrentMinNine OBJECT-TYPE
    SYNTAX      DisplayString
    MAX-ACCESS  read-only
    STATUS      current
    DESCRIPTION
	"The Min. current value of the nineth output of the slave 9"
    ::= { slaveNineOutputCurrentMin 9}
slaveNineOutputCurrentMinTen OBJECT-TYPE
    SYNTAX      DisplayString
    MAX-ACCESS  read-only
    STATUS      current
    DESCRIPTION
	"The Min. current value of the tenth output of the slave 9"
    ::= { slaveNineOutputCurrentMin 10}
slaveNineOutputCurrentMinEleven OBJECT-TYPE
    SYNTAX      DisplayString
    MAX-ACCESS  read-only
    STATUS      current
    DESCRIPTION
	"The Min. current value of the eleventh output of the slave 9"
    ::= { slaveNineOutputCurrentMin 11}
slaveNineOutputCurrentMinTwleve OBJECT-TYPE
    SYNTAX      DisplayString
    MAX-ACCESS  read-only
    STATUS      current
    DESCRIPTION
	"The Min. current value of the twelfth output of the slave 9"
    ::= { slaveNineOutputCurrentMin 12}
slaveNineOutputCurrentMinThirteen OBJECT-TYPE
    SYNTAX      DisplayString
    MAX-ACCESS  read-only
    STATUS      current
    DESCRIPTION
	"The Min. current value of the thirteenth output of the slave 9"
    ::= { slaveNineOutputCurrentMin 13}
slaveNineOutputCurrentMinFourteen OBJECT-TYPE
    SYNTAX      DisplayString
    MAX-ACCESS  read-only
    STATUS      current
    DESCRIPTION
	"The Min. current value of the fourteenth output of the slave 9"
    ::= { slaveNineOutputCurrentMin 14}
slaveNineOutputCurrentMinFifteen OBJECT-TYPE
    SYNTAX      DisplayString
    MAX-ACCESS  read-only
    STATUS      current
    DESCRIPTION
	"The Min. current value of the fifteenth output of the slave 9"
    ::= { slaveNineOutputCurrentMin 15}
slaveNineOutputCurrentMinSixteen OBJECT-TYPE
    SYNTAX      DisplayString
    MAX-ACCESS  read-only
    STATUS      current
    DESCRIPTION
	"The Min. current value of the sixteenth output of the slave 9"
    ::= { slaveNineOutputCurrentMin 16}
slaveNineOutputCurrentMinSeventeen OBJECT-TYPE
    SYNTAX      DisplayString
    MAX-ACCESS  read-only
    STATUS      current
    DESCRIPTION
	"The Min. current value of the seventeenth output of the slave 9"
    ::= { slaveNineOutputCurrentMin 17}
slaveNineOutputCurrentMinEighteen OBJECT-TYPE
    SYNTAX      DisplayString
    MAX-ACCESS  read-only
    STATUS      current
    DESCRIPTION
	"The Min. current value of the eighteenth output of the slave 9"
    ::= { slaveNineOutputCurrentMin 18}
slaveNineOutputCurrentMinNineteen OBJECT-TYPE
    SYNTAX      DisplayString
    MAX-ACCESS  read-only
    STATUS      current
    DESCRIPTION
	"The Min. current value of the nineteenth output of the slave 9"
    ::= { slaveNineOutputCurrentMin 19}
slaveNineOutputCurrentMinTwenty OBJECT-TYPE
    SYNTAX      DisplayString
    MAX-ACCESS  read-only
    STATUS      current
    DESCRIPTION
	"The Min. current value of the twentieth output of the slave 9"
    ::= { slaveNineOutputCurrentMin 20}
slaveNineOutputCurrentMinTwentyOne OBJECT-TYPE
    SYNTAX      DisplayString
    MAX-ACCESS  read-only
    STATUS      current
    DESCRIPTION
	"The Min. current value of the twentyth-first output of the slave 9"
    ::= { slaveNineOutputCurrentMin 21}
slaveNineOutputCurrentMinTwentyTwo OBJECT-TYPE
    SYNTAX      DisplayString
    MAX-ACCESS  read-only
    STATUS      current
    DESCRIPTION
	"The Min. current value of the twentyth-second output of the slave 9"
    ::= { slaveNineOutputCurrentMin 22}
slaveNineOutputCurrentMinTwentyThree OBJECT-TYPE
    SYNTAX      DisplayString
    MAX-ACCESS  read-only
    STATUS      current
    DESCRIPTION
	"The Min. current value of the twentyth-third output of the slave 9"
    ::= { slaveNineOutputCurrentMin 23}
slaveNineOutputCurrentMinTwentyFour OBJECT-TYPE
    SYNTAX      DisplayString
    MAX-ACCESS  read-only
    STATUS      current
    DESCRIPTION
	"The Min. current value of the twentyth-fourth output of the slave 9"
    ::= { slaveNineOutputCurrentMin 24}




slaveNineOutputCurrentMax   OBJECT IDENTIFIER ::= { rpduSlaveNine  12}
slaveNineOutputCurrentMaxOne OBJECT-TYPE
    SYNTAX      DisplayString
    MAX-ACCESS  read-only
    STATUS      current
    DESCRIPTION
	"The Max. current value of the first output of the slave 9"
    ::= { slaveNineOutputCurrentMax 1}
slaveNineOutputCurrentMaxTwo OBJECT-TYPE
    SYNTAX      DisplayString
    MAX-ACCESS  read-only
    STATUS      current
    DESCRIPTION
	"The Max. current value of the second output of the slave 9"
    ::= { slaveNineOutputCurrentMax 2}
slaveNineOutputCurrentMaxThree OBJECT-TYPE
    SYNTAX      DisplayString
    MAX-ACCESS  read-only
    STATUS      current
    DESCRIPTION
	"The Max. current value of the third output of the slave 9"
    ::= { slaveNineOutputCurrentMax 3}
slaveNineOutputCurrentMaxFour OBJECT-TYPE
    SYNTAX      DisplayString
    MAX-ACCESS  read-only
    STATUS      current
    DESCRIPTION
	"The Max. current value of the fourth output of the slave 9"
    ::= { slaveNineOutputCurrentMax 4}
slaveNineOutputCurrentMaxFive OBJECT-TYPE
    SYNTAX      DisplayString
    MAX-ACCESS  read-only
    STATUS      current
    DESCRIPTION
	"The Max. current value of the fifth output of the slave 9"
    ::= { slaveNineOutputCurrentMax 5}
slaveNineOutputCurrentMaxSix OBJECT-TYPE
    SYNTAX      DisplayString
    MAX-ACCESS  read-only
    STATUS      current
    DESCRIPTION
	"The Max. current value of the sixth output of the slave 9"
    ::= { slaveNineOutputCurrentMax 6}
slaveNineOutputCurrentMaxSeven OBJECT-TYPE
    SYNTAX      DisplayString
    MAX-ACCESS  read-only
    STATUS      current
    DESCRIPTION
	"The Max. current value of the seventh output of the slave 9"
    ::= { slaveNineOutputCurrentMax 7}
slaveNineOutputCurrentMaxEight OBJECT-TYPE
    SYNTAX      DisplayString
    MAX-ACCESS  read-only
    STATUS      current
    DESCRIPTION
	"The Max. current value of the eighth output of the slave 9"
    ::= { slaveNineOutputCurrentMax 8}
slaveNineOutputCurrentMaxNine OBJECT-TYPE
    SYNTAX      DisplayString
    MAX-ACCESS  read-only
    STATUS      current
    DESCRIPTION
	"The Max. current value of the nineth output of the slave 9"
    ::= { slaveNineOutputCurrentMax 9}
slaveNineOutputCurrentMaxTen OBJECT-TYPE
    SYNTAX      DisplayString
    MAX-ACCESS  read-only
    STATUS      current
    DESCRIPTION
	"The Max. current value of the tenth output of the slave 9"
    ::= { slaveNineOutputCurrentMax 10}
slaveNineOutputCurrentMaxEleven OBJECT-TYPE
    SYNTAX      DisplayString
    MAX-ACCESS  read-only
    STATUS      current
    DESCRIPTION
	"The Max. current value of the eleventh output of the slave 9"
    ::= { slaveNineOutputCurrentMax 11}
slaveNineOutputCurrentMaxTwleve OBJECT-TYPE
    SYNTAX      DisplayString
    MAX-ACCESS  read-only
    STATUS      current
    DESCRIPTION
	"The Max. current value of the twelfth output of the slave 9"
    ::= { slaveNineOutputCurrentMax 12}
slaveNineOutputCurrentMaxThirteen OBJECT-TYPE
    SYNTAX      DisplayString
    MAX-ACCESS  read-only
    STATUS      current
    DESCRIPTION
	"The Max. current value of the thirteenth output of the slave 9"
    ::= { slaveNineOutputCurrentMax 13}
slaveNineOutputCurrentMaxFourteen OBJECT-TYPE
    SYNTAX      DisplayString
    MAX-ACCESS  read-only
    STATUS      current
    DESCRIPTION
	"The Max. current value of the fourteenth output of the slave 9"
    ::= { slaveNineOutputCurrentMax 14}
slaveNineOutputCurrentMaxFifteen OBJECT-TYPE
    SYNTAX      DisplayString
    MAX-ACCESS  read-only
    STATUS      current
    DESCRIPTION
	"The Max. current value of the fifteenth output of the slave 9"
    ::= { slaveNineOutputCurrentMax 15}
slaveNineOutputCurrentMaxSixteen OBJECT-TYPE
    SYNTAX      DisplayString
    MAX-ACCESS  read-only
    STATUS      current
    DESCRIPTION
	"The Max. current value of the sixteenth output of the slave 9"
    ::= { slaveNineOutputCurrentMax 16}
slaveNineOutputCurrentMaxSeventeen OBJECT-TYPE
    SYNTAX      DisplayString
    MAX-ACCESS  read-only
    STATUS      current
    DESCRIPTION
	"The Max. current value of the seventeenth output of the slave 9"
    ::= { slaveNineOutputCurrentMax 17}
slaveNineOutputCurrentMaxEighteen OBJECT-TYPE
    SYNTAX      DisplayString
    MAX-ACCESS  read-only
    STATUS      current
    DESCRIPTION
	"The Max. current value of the eighteenth output of the slave 9"
    ::= { slaveNineOutputCurrentMax 18}
slaveNineOutputCurrentMaxNineteen OBJECT-TYPE
    SYNTAX      DisplayString
    MAX-ACCESS  read-only
    STATUS      current
    DESCRIPTION
	"The Max. current value of the nineteenth output of the slave 9"
    ::= { slaveNineOutputCurrentMax 19}
slaveNineOutputCurrentMaxTwenty OBJECT-TYPE
    SYNTAX      DisplayString
    MAX-ACCESS  read-only
    STATUS      current
    DESCRIPTION
	"The Max. current value of the twentieth output of the slave 9"
    ::= { slaveNineOutputCurrentMax 20}
slaveNineOutputCurrentMaxTwentyOne OBJECT-TYPE
    SYNTAX      DisplayString
    MAX-ACCESS  read-only
    STATUS      current
    DESCRIPTION
	"The Max. current value of the twenty-first output of the slave 9"
    ::= { slaveNineOutputCurrentMax 21}
slaveNineOutputCurrentMaxTwentyTwo OBJECT-TYPE
    SYNTAX      DisplayString
    MAX-ACCESS  read-only
    STATUS      current
    DESCRIPTION
	"The Max. current value of the twenty-second output of the slave 9"
    ::= { slaveNineOutputCurrentMax 22}
slaveNineOutputCurrentMaxTwentyThree OBJECT-TYPE
    SYNTAX      DisplayString
    MAX-ACCESS  read-only
    STATUS      current
    DESCRIPTION
	"The Max. current value of the twenty-third output of the slave 9"
    ::= { slaveNineOutputCurrentMax 23}
slaveNineOutputCurrentMaxTwentyFour OBJECT-TYPE
    SYNTAX      DisplayString
    MAX-ACCESS  read-only
    STATUS      current
    DESCRIPTION
	"The Max. current value of the twenty-fourth output of the slave 9"
    ::= { slaveNineOutputCurrentMax 24}


slaveNineOutputCurrentEnergy  OBJECT IDENTIFIER ::= { rpduSlaveNine  13}
slaveNineOutputCurrentEnergyOne OBJECT-TYPE
    SYNTAX	DisplayString
    MAX-ACCESS	read-only
    STATUS	current
    DESCRIPTION
	"The energy value of the first output of the slave 9"
    ::={slaveNineOutputCurrentEnergy 1}
slaveNineOutputCurrentEnergyTwo OBJECT-TYPE
    SYNTAX	DisplayString
    MAX-ACCESS	read-only
    STATUS	current
    DESCRIPTION
	"The energy value of the second output of the slave 9"
    ::={slaveNineOutputCurrentEnergy 2}
slaveNineOutputCurrentEnergyThree OBJECT-TYPE
    SYNTAX	DisplayString
    MAX-ACCESS	read-only
    STATUS	current
    DESCRIPTION
	"The energy value of the third output of the slave 9"
    ::={slaveNineOutputCurrentEnergy 3}
slaveNineOutputCurrentEnergyFour OBJECT-TYPE
    SYNTAX	DisplayString
    MAX-ACCESS	read-only
    STATUS	current
    DESCRIPTION
	"The energy value of the fourth output of the slave 9"
    ::={slaveNineOutputCurrentEnergy 4}
slaveNineOutputCurrentEnergyFive OBJECT-TYPE
    SYNTAX	DisplayString
    MAX-ACCESS	read-only
    STATUS	current
    DESCRIPTION
	"The energy value of the fifth output of the slave 9"
    ::={slaveNineOutputCurrentEnergy 5}
slaveNineOutputCurrentEnergySix OBJECT-TYPE
    SYNTAX	DisplayString
    MAX-ACCESS	read-only
    STATUS	current
    DESCRIPTION
	"The energy value of the sixth output of the slave 9"
    ::={slaveNineOutputCurrentEnergy 6}
slaveNineOutputCurrentEnergySeven OBJECT-TYPE
    SYNTAX	DisplayString
    MAX-ACCESS	read-only
    STATUS	current
    DESCRIPTION
	"The energy value of the seventh output of the slave 9"
    ::={slaveNineOutputCurrentEnergy 7}
slaveNineOutputCurrentEnergyEight OBJECT-TYPE
    SYNTAX	DisplayString
    MAX-ACCESS	read-only
    STATUS	current
    DESCRIPTION
	"The energy value of the eighth output of the slave 9"
    ::={slaveNineOutputCurrentEnergy 8}
slaveNineOutputCurrentEnergyNine OBJECT-TYPE
    SYNTAX	DisplayString
    MAX-ACCESS	read-only
    STATUS	current
    DESCRIPTION
	"The energy value of the nineth output of the slave 9"
    ::={slaveNineOutputCurrentEnergy 9}
slaveNineOutputCurrentEnergyTen OBJECT-TYPE
    SYNTAX	DisplayString
    MAX-ACCESS	read-only
    STATUS	current
    DESCRIPTION
	"The energy value of the tenth output of the slave 9"
    ::={slaveNineOutputCurrentEnergy 10}
slaveNineOutputCurrentEnergyEleven OBJECT-TYPE
    SYNTAX	DisplayString
    MAX-ACCESS	read-only
    STATUS	current
    DESCRIPTION
	"The energy value of the eleventh output of the slave 9"
    ::={slaveNineOutputCurrentEnergy 11}
slaveNineOutputCurrentEnergyTwelve OBJECT-TYPE
    SYNTAX	DisplayString
    MAX-ACCESS	read-only
    STATUS	current
    DESCRIPTION
	"The energy value of the twelfth output of the slave 9"
    ::={slaveNineOutputCurrentEnergy 12}
slaveNineOutputCurrentEnergyThirteen OBJECT-TYPE
    SYNTAX	DisplayString
    MAX-ACCESS	read-only
    STATUS	current
    DESCRIPTION
	"The energy value of the thirteenth output of the slave 9"
    ::={slaveNineOutputCurrentEnergy 13}
slaveNineOutputCurrentEnergyFourteen OBJECT-TYPE
    SYNTAX	DisplayString
    MAX-ACCESS	read-only
    STATUS	current
    DESCRIPTION
	"The energy value of the fourteenth output of the slave 9"
    ::={slaveNineOutputCurrentEnergy 14}
slaveNineOutputCurrentEnergyFifteen OBJECT-TYPE
    SYNTAX	DisplayString
    MAX-ACCESS	read-only
    STATUS	current
    DESCRIPTION
	"The energy value of the fifteenth output of the slave 9"
    ::={slaveNineOutputCurrentEnergy 15}
slaveNineOutputCurrentEnergySixteen OBJECT-TYPE
    SYNTAX	DisplayString
    MAX-ACCESS	read-only
    STATUS	current
    DESCRIPTION
	"The energy value of the sixteenth output of the slave 9"
    ::={slaveNineOutputCurrentEnergy 16}
slaveNineOutputCurrentEnergySeventeen OBJECT-TYPE
    SYNTAX	DisplayString
    MAX-ACCESS	read-only
    STATUS	current
    DESCRIPTION
	"The energy value of the seventeenth output of the slave 9"
    ::={slaveNineOutputCurrentEnergy 17}
slaveNineOutputCurrentEnergyEighteen OBJECT-TYPE
    SYNTAX	DisplayString
    MAX-ACCESS	read-only
    STATUS	current
    DESCRIPTION
	"The energy value of the eighteenth output of the slave 9"
    ::={slaveNineOutputCurrentEnergy 18}
slaveNineOutputCurrentEnergyNineteen OBJECT-TYPE
    SYNTAX	DisplayString
    MAX-ACCESS	read-only
    STATUS	current
    DESCRIPTION
	"The energy value of the nineteenth output of the slave 9"
    ::={slaveNineOutputCurrentEnergy 19}
slaveNineOutputCurrentEnergyTwenty OBJECT-TYPE
    SYNTAX	DisplayString
    MAX-ACCESS	read-only
    STATUS	current
    DESCRIPTION
	"The energy value of the twentieth output of the slave 9"
    ::={slaveNineOutputCurrentEnergy 20}
slaveNineOutputCurrentEnergyTwentyOne OBJECT-TYPE
    SYNTAX	DisplayString
    MAX-ACCESS	read-only
    STATUS	current
    DESCRIPTION
	"The energy value of the twenty-first output of the slave 9"
    ::={slaveNineOutputCurrentEnergy 21}
slaveNineOutputCurrentEnergyTwentyTwo OBJECT-TYPE
    SYNTAX	DisplayString
    MAX-ACCESS	read-only
    STATUS	current
    DESCRIPTION
	"The energy value of the twenty-second output of the slave 9"
    ::={slaveNineOutputCurrentEnergy 22}
slaveNineOutputCurrentEnergyTwentyThree OBJECT-TYPE
    SYNTAX	DisplayString
    MAX-ACCESS	read-only
    STATUS	current
    DESCRIPTION
	"The energy value of the twenty-third output of the slave 9"
    ::={slaveNineOutputCurrentEnergy 23}
slaveNineOutputCurrentEnergyTwentyFour OBJECT-TYPE
    SYNTAX	DisplayString
    MAX-ACCESS	read-only
    STATUS	current
    DESCRIPTION
	"The energy value of the twenty-fourth output of the slave 9"
    ::={slaveNineOutputCurrentEnergy 24}

-------------------------------End ---------------------------------------------     
                                                                                     
                                                                                     
END
