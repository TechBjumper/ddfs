--------------------------------------------------------------------------------
-- PDI SNMP MIB FOR BCMSplus
--
-- Revision 1.01
-- Feb 29, 2008
--------------------------------------------------------------------------------
BCMSplus DEFINITIONS ::= BEGIN

IMPORTS
  org, iso, dod, internet, directory, mgmt, experimental, private, enterprises
    FROM RFC-1155-SMI 
  OBJECT-TYPE
    FROM RFC-1212
  DisplayString
    FROM RFC-1213;

--------------------------------------------------------------------------------
-- OID hierarchy
--------------------------------------------------------------------------------

pdi         OBJECT IDENTIFIER ::= { enterprises 24436 }
products    OBJECT IDENTIFIER ::= { pdi 1 }
bcms		OBJECT IDENTIFIER ::= { products 3 }
bcmsII	OBJECT IDENTIFIER ::= { bcms 2 }
bcmsplus	OBJECT IDENTIFIER ::= { bcmsII 3 }
panelboard1 OBJECT IDENTIFIER ::= { bcmsplus 1 }
panelboard2 OBJECT IDENTIFIER ::= { bcmsplus 2 }
bcmstraps   OBJECT IDENTIFIER ::= { bcmsplus 9 }

--------------------------------------------------------------------------------
-- BCMS register values
--------------------------------------------------------------------------------

pb1-CB1-Current
	OBJECT-TYPE
	SYNTAX  INTEGER
	ACCESS  read-only
	STATUS  mandatory
	DESCRIPTION "PB1 CB1 Current
		     Note for all currents 1-42: 100 = 10.0 amps"
		::= { panelboard1 1 }
  
pb1-CB2-Current
	OBJECT-TYPE
	SYNTAX  INTEGER
	ACCESS  read-only
	STATUS  mandatory
	DESCRIPTION "PB1 CB2 Current"
		::= { panelboard1 2 }

pb1-CB3-Current
	OBJECT-TYPE
	SYNTAX  INTEGER
	ACCESS  read-only
	STATUS  mandatory
	DESCRIPTION "PB1 CB3 Current"
		::= { panelboard1 3 }

pb1-CB4-Current
	OBJECT-TYPE
	SYNTAX  INTEGER
	ACCESS  read-only
	STATUS  mandatory
	DESCRIPTION "PB1 CB4 Current"
		::= { panelboard1 4 }

pb1-CB5-Current
	OBJECT-TYPE
	SYNTAX  INTEGER
	ACCESS  read-only
	STATUS  mandatory
	DESCRIPTION "PB1 CB5 Current"
		::= { panelboard1 5 }

pb1-CB6-Current
	OBJECT-TYPE
	SYNTAX  INTEGER
	ACCESS  read-only
	STATUS  mandatory
	DESCRIPTION "PB1 CB6 Current"
		::= { panelboard1 6 }

pb1-CB7-Current
	OBJECT-TYPE
	SYNTAX  INTEGER
	ACCESS  read-only
	STATUS  mandatory
	DESCRIPTION "PB1 CB7 Current"
		::= { panelboard1 7 }

pb1-CB8-Current
	OBJECT-TYPE
	SYNTAX  INTEGER
	ACCESS  read-only
	STATUS  mandatory
	DESCRIPTION "PB1 CB8 Current"
		::= { panelboard1 8 }

pb1-CB9-Current
	OBJECT-TYPE
	SYNTAX  INTEGER
	ACCESS  read-only
	STATUS  mandatory
	DESCRIPTION "PB1 CB9 Current"
		::= { panelboard1 9 }

pb1-CB10-Current
	OBJECT-TYPE
	SYNTAX  INTEGER
	ACCESS  read-only
	STATUS  mandatory
	DESCRIPTION "PB1 CB10 Current"
		::= { panelboard1 10 }

pb1-CB11-Current
	OBJECT-TYPE
	SYNTAX  INTEGER
	ACCESS  read-only
	STATUS  mandatory
	DESCRIPTION "PB1 CB11 Current"
		::= { panelboard1 11 }
  
pb1-CB12-Current
	OBJECT-TYPE
	SYNTAX  INTEGER
	ACCESS  read-only
	STATUS  mandatory
	DESCRIPTION "PB1 CB12 Current"
		::= { panelboard1 12 }

pb1-CB13-Current
	OBJECT-TYPE
	SYNTAX  INTEGER
	ACCESS  read-only
	STATUS  mandatory
	DESCRIPTION "PB1 CB13 Current"
		::= { panelboard1 13 }

pb1-CB14-Current
	OBJECT-TYPE
	SYNTAX  INTEGER
	ACCESS  read-only
	STATUS  mandatory
	DESCRIPTION "PB1 CB14 Current"
		::= { panelboard1 14 }

pb1-CB15-Current
	OBJECT-TYPE
	SYNTAX  INTEGER
	ACCESS  read-only
	STATUS  mandatory
	DESCRIPTION "PB1 CB15 Current"
		::= { panelboard1 15 }

pb1-CB16-Current
	OBJECT-TYPE
	SYNTAX  INTEGER
	ACCESS  read-only
	STATUS  mandatory
	DESCRIPTION "PB1 CB16 Current"
		::= { panelboard1 16 }

pb1-CB17-Current
	OBJECT-TYPE
	SYNTAX  INTEGER
	ACCESS  read-only
	STATUS  mandatory
	DESCRIPTION "PB1 CB17 Current"
		::= { panelboard1 17 }

pb1-CB18-Current
	OBJECT-TYPE
	SYNTAX  INTEGER
	ACCESS  read-only
	STATUS  mandatory
	DESCRIPTION "PB1 CB18 Current"
		::= { panelboard1 18 }

pb1-CB19-Current
	OBJECT-TYPE
	SYNTAX  INTEGER
	ACCESS  read-only
	STATUS  mandatory
	DESCRIPTION "PB1 CB19 Current"
		::= { panelboard1 19 }

pb1-CB20-Current
	OBJECT-TYPE
	SYNTAX  INTEGER
	ACCESS  read-only
	STATUS  mandatory
	DESCRIPTION "PB1 CB20 Current"
		::= { panelboard1 20 }

pb1-CB21-Current
	OBJECT-TYPE
	SYNTAX  INTEGER
	ACCESS  read-only
	STATUS  mandatory
	DESCRIPTION "PB1 CB21 Current"
		::= { panelboard1 21 }
  
pb1-CB22-Current
	OBJECT-TYPE
	SYNTAX  INTEGER
	ACCESS  read-only
	STATUS  mandatory
	DESCRIPTION "PB1 CB22 Current"
		::= { panelboard1 22 }

pb1-CB23-Current
	OBJECT-TYPE
	SYNTAX  INTEGER
	ACCESS  read-only
	STATUS  mandatory
	DESCRIPTION "PB1 CB23 Current"
		::= { panelboard1 23 }

pb1-CB24-Current
	OBJECT-TYPE
	SYNTAX  INTEGER
	ACCESS  read-only
	STATUS  mandatory
	DESCRIPTION "PB1 CB24 Current"
		::= { panelboard1 24 }

pb1-CB25-Current
	OBJECT-TYPE
	SYNTAX  INTEGER
	ACCESS  read-only
	STATUS  mandatory
	DESCRIPTION "PB1 CB25 Current"
		::= { panelboard1 25 }

pb1-CB26-Current
	OBJECT-TYPE
	SYNTAX  INTEGER
	ACCESS  read-only
	STATUS  mandatory
	DESCRIPTION "PB1 CB26 Current"
		::= { panelboard1 26 }

pb1-CB27-Current
	OBJECT-TYPE
	SYNTAX  INTEGER
	ACCESS  read-only
	STATUS  mandatory
	DESCRIPTION "PB1 CB27 Current"
		::= { panelboard1 27 }

pb1-CB28-Current
	OBJECT-TYPE
	SYNTAX  INTEGER
	ACCESS  read-only
	STATUS  mandatory
	DESCRIPTION "PB1 CB28 Current"
		::= { panelboard1 28 }

pb1-CB29-Current
	OBJECT-TYPE
	SYNTAX  INTEGER
	ACCESS  read-only
	STATUS  mandatory
	DESCRIPTION "PB1 CB29 Current"
		::= { panelboard1 29 }

pb1-CB30-Current
	OBJECT-TYPE
	SYNTAX  INTEGER
	ACCESS  read-only
	STATUS  mandatory
	DESCRIPTION "PB1 CB30 Current"
		::= { panelboard1 30 }

pb1-CB31-Current
	OBJECT-TYPE
	SYNTAX  INTEGER
	ACCESS  read-only
	STATUS  mandatory
	DESCRIPTION "PB1 CB31 Current"
		::= { panelboard1 31 }
  
pb1-CB32-Current
	OBJECT-TYPE
	SYNTAX  INTEGER
	ACCESS  read-only
	STATUS  mandatory
	DESCRIPTION "PB1 CB32 Current"
		::= { panelboard1 32 }

pb1-CB33-Current
	OBJECT-TYPE
	SYNTAX  INTEGER
	ACCESS  read-only
	STATUS  mandatory
	DESCRIPTION "PB1 CB33 Current"
		::= { panelboard1 33 }

pb1-CB34-Current
	OBJECT-TYPE
	SYNTAX  INTEGER
	ACCESS  read-only
	STATUS  mandatory
	DESCRIPTION "PB1 CB34 Current"
		::= { panelboard1 34 }

pb1-CB35-Current
	OBJECT-TYPE
	SYNTAX  INTEGER
	ACCESS  read-only
	STATUS  mandatory
	DESCRIPTION "PB1 CB35 Current"
		::= { panelboard1 35 }

pb1-CB36-Current
	OBJECT-TYPE
	SYNTAX  INTEGER
	ACCESS  read-only
	STATUS  mandatory
	DESCRIPTION "PB1 CB36 Current"
		::= { panelboard1 36 }

pb1-CB37-Current
	OBJECT-TYPE
	SYNTAX  INTEGER
	ACCESS  read-only
	STATUS  mandatory
	DESCRIPTION "PB1 CB37 Current"
		::= { panelboard1 37 }

pb1-CB38-Current
	OBJECT-TYPE
	SYNTAX  INTEGER
	ACCESS  read-only
	STATUS  mandatory
	DESCRIPTION "PB1 CB38 Current"
		::= { panelboard1 38 }

pb1-CB39-Current
	OBJECT-TYPE
	SYNTAX  INTEGER
	ACCESS  read-only
	STATUS  mandatory
	DESCRIPTION "PB1 CB39 Current"
		::= { panelboard1 39 }

pb1-CB40-Current
	OBJECT-TYPE
	SYNTAX  INTEGER
	ACCESS  read-only
	STATUS  mandatory
	DESCRIPTION "PB1 CB40 Current"
		::= { panelboard1 40 }

pb1-CB41-Current
	OBJECT-TYPE
	SYNTAX  INTEGER
	ACCESS  read-only
	STATUS  mandatory
	DESCRIPTION "PB1 CB41 Current"
		::= { panelboard1 41 }
  
pb1-CB42-Current
	OBJECT-TYPE
	SYNTAX  INTEGER
	ACCESS  read-only
	STATUS  mandatory
	DESCRIPTION "PB1 CB42 Current"
		::= { panelboard1 42 }

pb1-CB1-Min
	OBJECT-TYPE
	SYNTAX  INTEGER
	ACCESS  read-only
	STATUS  mandatory
	DESCRIPTION "PB1 CB1 Min
		     Note for all minumum currents 1-42: 100 = 10.0 amps"
		::= { panelboard1 43 }

pb1-CB2-Min
	OBJECT-TYPE
	SYNTAX  INTEGER
	ACCESS  read-only
	STATUS  mandatory
	DESCRIPTION "PB1 CB2 Min"
		::= { panelboard1 44 }

pb1-CB3-Min
	OBJECT-TYPE
	SYNTAX  INTEGER
	ACCESS  read-only
	STATUS  mandatory
	DESCRIPTION "PB1 CB3 Min"
		::= { panelboard1 45 }

pb1-CB4-Min
	OBJECT-TYPE
	SYNTAX  INTEGER
	ACCESS  read-only
	STATUS  mandatory
	DESCRIPTION "PB1 CB4 Min"
		::= { panelboard1 46 }

pb1-CB5-Min
	OBJECT-TYPE
	SYNTAX  INTEGER
	ACCESS  read-only
	STATUS  mandatory
	DESCRIPTION "PB1 CB5 Min"
		::= { panelboard1 47 }

pb1-CB6-Min
	OBJECT-TYPE
	SYNTAX  INTEGER
	ACCESS  read-only
	STATUS  mandatory
	DESCRIPTION "PB1 CB6 Min"
		::= { panelboard1 48 }

pb1-CB7-Min
	OBJECT-TYPE
	SYNTAX  INTEGER
	ACCESS  read-only
	STATUS  mandatory
	DESCRIPTION "PB1 CB7 Min"
		::= { panelboard1 49 }

pb1-CB8-Min
	OBJECT-TYPE
	SYNTAX  INTEGER
	ACCESS  read-only
	STATUS  mandatory
	DESCRIPTION "PB1 CB8 Min"
		::= { panelboard1 50 }

pb1-CB9-Min
	OBJECT-TYPE
	SYNTAX  INTEGER
	ACCESS  read-only
	STATUS  mandatory
	DESCRIPTION "PB1 CB9 Min"
		::= { panelboard1 51 }
  
pb1-CB10-Min
	OBJECT-TYPE
	SYNTAX  INTEGER
	ACCESS  read-only
	STATUS  mandatory
	DESCRIPTION "PB1 CB10 Min"
		::= { panelboard1 52 }

pb1-CB11-Min
	OBJECT-TYPE
	SYNTAX  INTEGER
	ACCESS  read-only
	STATUS  mandatory
	DESCRIPTION "PB1 CB11 Min"
		::= { panelboard1 53 }

pb1-CB12-Min
	OBJECT-TYPE
	SYNTAX  INTEGER
	ACCESS  read-only
	STATUS  mandatory
	DESCRIPTION "PB1 CB12 Min"
		::= { panelboard1 54 }

pb1-CB13-Min
	OBJECT-TYPE
	SYNTAX  INTEGER
	ACCESS  read-only
	STATUS  mandatory
	DESCRIPTION "PB1 CB13 Min"
		::= { panelboard1 55 }

pb1-CB14-Min
	OBJECT-TYPE
	SYNTAX  INTEGER
	ACCESS  read-only
	STATUS  mandatory
	DESCRIPTION "PB1 CB14 Min"
		::= { panelboard1 56 }

pb1-CB15-Min
	OBJECT-TYPE
	SYNTAX  INTEGER
	ACCESS  read-only
	STATUS  mandatory
	DESCRIPTION "PB1 CB15 Min"
		::= { panelboard1 57 }

pb1-CB16-Min
	OBJECT-TYPE
	SYNTAX  INTEGER
	ACCESS  read-only
	STATUS  mandatory
	DESCRIPTION "PB1 CB16 Min"
		::= { panelboard1 58 }

pb1-CB17-Min
	OBJECT-TYPE
	SYNTAX  INTEGER
	ACCESS  read-only
	STATUS  mandatory
	DESCRIPTION "PB1 CB17 Min"
		::= { panelboard1 59 }


pb1-CB18-Min
	OBJECT-TYPE
	SYNTAX  INTEGER
	ACCESS  read-only
	STATUS  mandatory
	DESCRIPTION "PB1 CB18 Min"
		::= { panelboard1 60 }

pb1-CB19-Min
	OBJECT-TYPE
	SYNTAX  INTEGER
	ACCESS  read-only
	STATUS  mandatory
	DESCRIPTION "PB1 CB19 Min"
		::= { panelboard1 61 }
  
pb1-CB20-Min
	OBJECT-TYPE
	SYNTAX  INTEGER
	ACCESS  read-only
	STATUS  mandatory
	DESCRIPTION "PB1 CB20 Min"
		::= { panelboard1 62 }

pb1-CB21-Min
	OBJECT-TYPE
	SYNTAX  INTEGER
	ACCESS  read-only
	STATUS  mandatory
	DESCRIPTION "PB1 CB21 Min"
		::= { panelboard1 63 }

pb1-CB22-Min
	OBJECT-TYPE
	SYNTAX  INTEGER
	ACCESS  read-only
	STATUS  mandatory
	DESCRIPTION "PB1 CB22 Min"
		::= { panelboard1 64 }

pb1-CB23-Min
	OBJECT-TYPE
	SYNTAX  INTEGER
	ACCESS  read-only
	STATUS  mandatory
	DESCRIPTION "PB1 CB23 Min"
		::= { panelboard1 65 }

pb1-CB24-Min
	OBJECT-TYPE
	SYNTAX  INTEGER
	ACCESS  read-only
	STATUS  mandatory
	DESCRIPTION "PB1 CB24 Min"
		::= { panelboard1 66 }

pb1-CB25-Min
	OBJECT-TYPE
	SYNTAX  INTEGER
	ACCESS  read-only
	STATUS  mandatory
	DESCRIPTION "PB1 CB25 Min"
		::= { panelboard1 67 }

pb1-CB26-Min
	OBJECT-TYPE
	SYNTAX  INTEGER
	ACCESS  read-only
	STATUS  mandatory
	DESCRIPTION "PB1 CB26 Min"
		::= { panelboard1 68 }

pb1-CB27-Min
	OBJECT-TYPE
	SYNTAX  INTEGER
	ACCESS  read-only
	STATUS  mandatory
	DESCRIPTION "PB1 CB27 Min"
		::= { panelboard1 69 }

pb1-CB28-Min
	OBJECT-TYPE
	SYNTAX  INTEGER
	ACCESS  read-only
	STATUS  mandatory
	DESCRIPTION "PB1 CB28 Min"
		::= { panelboard1 70 }

pb1-CB29-Min
	OBJECT-TYPE
	SYNTAX  INTEGER
	ACCESS  read-only
	STATUS  mandatory
	DESCRIPTION "PB1 CB29 Min"
		::= { panelboard1 71 }
  
pb1-CB30-Min
	OBJECT-TYPE
	SYNTAX  INTEGER
	ACCESS  read-only
	STATUS  mandatory
	DESCRIPTION "PB1 CB30 Min"
		::= { panelboard1 72 }

pb1-CB31-Min
	OBJECT-TYPE
	SYNTAX  INTEGER
	ACCESS  read-only
	STATUS  mandatory
	DESCRIPTION "PB1 CB31 Min"
		::= { panelboard1 73 }

pb1-CB32-Min
	OBJECT-TYPE
	SYNTAX  INTEGER
	ACCESS  read-only
	STATUS  mandatory
	DESCRIPTION "PB1 CB32 Min"
		::= { panelboard1 74 }

pb1-CB33-Min
	OBJECT-TYPE
	SYNTAX  INTEGER
	ACCESS  read-only
	STATUS  mandatory
	DESCRIPTION "PB1 CB33 Min"
		::= { panelboard1 75 }

pb1-CB34-Min
	OBJECT-TYPE
	SYNTAX  INTEGER
	ACCESS  read-only
	STATUS  mandatory
	DESCRIPTION "PB1 CB34 Min"
		::= { panelboard1 76 }

pb1-CB35-Min
	OBJECT-TYPE
	SYNTAX  INTEGER
	ACCESS  read-only
	STATUS  mandatory
	DESCRIPTION "PB1 CB35 Min"
		::= { panelboard1 77 }

pb1-CB36-Min
	OBJECT-TYPE
	SYNTAX  INTEGER
	ACCESS  read-only
	STATUS  mandatory
	DESCRIPTION "PB1 CB36 Min"
		::= { panelboard1 78 }

pb1-CB37-Min
	OBJECT-TYPE
	SYNTAX  INTEGER
	ACCESS  read-only
	STATUS  mandatory
	DESCRIPTION "PB1 CB37 Min"
		::= { panelboard1 79 }

pb1-CB38-Min
	OBJECT-TYPE
	SYNTAX  INTEGER
	ACCESS  read-only
	STATUS  mandatory
	DESCRIPTION "PB1 CB38 Min"
		::= { panelboard1 80 }

pb1-CB39-Min
	OBJECT-TYPE
	SYNTAX  INTEGER
	ACCESS  read-only
	STATUS  mandatory
	DESCRIPTION "PB1 CB39 Min"
		::= { panelboard1 81 }
  
pb1-CB40-Min
	OBJECT-TYPE
	SYNTAX  INTEGER
	ACCESS  read-only
	STATUS  mandatory
	DESCRIPTION "PB1 CB40 Min"
		::= { panelboard1 82 }

pb1-CB41-Min
	OBJECT-TYPE
	SYNTAX  INTEGER
	ACCESS  read-only
	STATUS  mandatory
	DESCRIPTION "PB1 CB41 Min"
		::= { panelboard1 83 }

pb1-CB42-Min
	OBJECT-TYPE
	SYNTAX  INTEGER
	ACCESS  read-only
	STATUS  mandatory
	DESCRIPTION "PB1 CB42 Min"
		::= { panelboard1 84 }

pb1-CB1-Max
	OBJECT-TYPE
	SYNTAX  INTEGER
	ACCESS  read-only
	STATUS  mandatory
	DESCRIPTION "PB1 CB1 Max
		     Note for all maximum currents 1-42: 100 = 10.0 amps"
		::= { panelboard1 85 }

pb1-CB2-Max
	OBJECT-TYPE
	SYNTAX  INTEGER
	ACCESS  read-only
	STATUS  mandatory
	DESCRIPTION "PB1 CB2 Max"
		::= { panelboard1 86 }

pb1-CB3-Max
	OBJECT-TYPE
	SYNTAX  INTEGER
	ACCESS  read-only
	STATUS  mandatory
	DESCRIPTION "PB1 CB3 Max"
		::= { panelboard1 87 }

pb1-CB4-Max
	OBJECT-TYPE
	SYNTAX  INTEGER
	ACCESS  read-only
	STATUS  mandatory
	DESCRIPTION "PB1 CB4 Max"
		::= { panelboard1 88 }

pb1-CB5-Max
	OBJECT-TYPE
	SYNTAX  INTEGER
	ACCESS  read-only
	STATUS  mandatory
	DESCRIPTION "PB1 CB5 Max"
		::= { panelboard1 89 }

pb1-CB6-Max
	OBJECT-TYPE
	SYNTAX  INTEGER
	ACCESS  read-only
	STATUS  mandatory
	DESCRIPTION "PB1 CB6 Max"
		::= { panelboard1 90 }

pb1-CB7-Max
	OBJECT-TYPE
	SYNTAX  INTEGER
	ACCESS  read-only
	STATUS  mandatory
	DESCRIPTION "PB1 CB7 Max"
		::= { panelboard1 91 }
  
pb1-CB8-Max
	OBJECT-TYPE
	SYNTAX  INTEGER
	ACCESS  read-only
	STATUS  mandatory
	DESCRIPTION "PB1 CB8 Max"
		::= { panelboard1 92 }

pb1-CB9-Max
	OBJECT-TYPE
	SYNTAX  INTEGER
	ACCESS  read-only
	STATUS  mandatory
	DESCRIPTION "PB1 CB9 Max"
		::= { panelboard1 93 }

pb1-CB10-Max
	OBJECT-TYPE
	SYNTAX  INTEGER
	ACCESS  read-only
	STATUS  mandatory
	DESCRIPTION "PB1 CB10 Max"
		::= { panelboard1 94 }

pb1-CB11-Max
	OBJECT-TYPE
	SYNTAX  INTEGER
	ACCESS  read-only
	STATUS  mandatory
	DESCRIPTION "PB1 CB11 Max"
		::= { panelboard1 95 }

pb1-CB12-Max
	OBJECT-TYPE
	SYNTAX  INTEGER
	ACCESS  read-only
	STATUS  mandatory
	DESCRIPTION "PB1 CB12 Max"
		::= { panelboard1 96 }

pb1-CB13-Max
	OBJECT-TYPE
	SYNTAX  INTEGER
	ACCESS  read-only
	STATUS  mandatory
	DESCRIPTION "PB1 CB13 Max"
		::= { panelboard1 97 }

pb1-CB14-Max
	OBJECT-TYPE
	SYNTAX  INTEGER
	ACCESS  read-only
	STATUS  mandatory
	DESCRIPTION "PB1 CB14 Max"
		::= { panelboard1 98 }

pb1-CB15-Max
	OBJECT-TYPE
	SYNTAX  INTEGER
	ACCESS  read-only
	STATUS  mandatory
	DESCRIPTION "PB1 CB15 Max"
		::= { panelboard1 99 }


pb1-CB16-Max
	OBJECT-TYPE
	SYNTAX  INTEGER
	ACCESS  read-only
	STATUS  mandatory
	DESCRIPTION "PB1 CB16 Max"
		::= { panelboard1 100 }

pb1-CB17-Max
	OBJECT-TYPE
	SYNTAX  INTEGER
	ACCESS  read-only
	STATUS  mandatory
	DESCRIPTION "PB1 CB17 Max"
		::= { panelboard1 101 }
  
pb1-CB18-Max
	OBJECT-TYPE
	SYNTAX  INTEGER
	ACCESS  read-only
	STATUS  mandatory
	DESCRIPTION "PB1 CB18 Max"
		::= { panelboard1 102 }

pb1-CB19-Max
	OBJECT-TYPE
	SYNTAX  INTEGER
	ACCESS  read-only
	STATUS  mandatory
	DESCRIPTION "PB1 CB19 Max"
		::= { panelboard1 103 }

pb1-CB20-Max
	OBJECT-TYPE
	SYNTAX  INTEGER
	ACCESS  read-only
	STATUS  mandatory
	DESCRIPTION "PB1 CB20 Max"
		::= { panelboard1 104 }

pb1-CB21-Max
	OBJECT-TYPE
	SYNTAX  INTEGER
	ACCESS  read-only
	STATUS  mandatory
	DESCRIPTION "PB1 CB21 Max"
		::= { panelboard1 105 }

pb1-CB22-Max
	OBJECT-TYPE
	SYNTAX  INTEGER
	ACCESS  read-only
	STATUS  mandatory
	DESCRIPTION "PB1 CB22 Max"
		::= { panelboard1 106 }

pb1-CB23-Max
	OBJECT-TYPE
	SYNTAX  INTEGER
	ACCESS  read-only
	STATUS  mandatory
	DESCRIPTION "PB1 CB23 Max"
		::= { panelboard1 107 }

pb1-CB24-Max
	OBJECT-TYPE
	SYNTAX  INTEGER
	ACCESS  read-only
	STATUS  mandatory
	DESCRIPTION "PB1 CB24 Max"
		::= { panelboard1 108 }

pb1-CB25-Max
	OBJECT-TYPE
	SYNTAX  INTEGER
	ACCESS  read-only
	STATUS  mandatory
	DESCRIPTION "PB1 CB25 Max"
		::= { panelboard1 109 }

pb1-CB26-Max
	OBJECT-TYPE
	SYNTAX  INTEGER
	ACCESS  read-only
	STATUS  mandatory
	DESCRIPTION "PB1 CB26 Max"
		::= { panelboard1 110 }

pb1-CB27-Max
	OBJECT-TYPE
	SYNTAX  INTEGER
	ACCESS  read-only
	STATUS  mandatory
	DESCRIPTION "PB1 CB27 Max"
		::= { panelboard1 111 }
  
pb1-CB28-Max
	OBJECT-TYPE
	SYNTAX  INTEGER
	ACCESS  read-only
	STATUS  mandatory
	DESCRIPTION "PB1 CB28 Max"
		::= { panelboard1 112 }

pb1-CB29-Max
	OBJECT-TYPE
	SYNTAX  INTEGER
	ACCESS  read-only
	STATUS  mandatory
	DESCRIPTION "PB1 CB29 Max"
		::= { panelboard1 113 }

pb1-CB30-Max
	OBJECT-TYPE
	SYNTAX  INTEGER
	ACCESS  read-only
	STATUS  mandatory
	DESCRIPTION "PB1 CB30 Max"
		::= { panelboard1 114 }

pb1-CB31-Max
	OBJECT-TYPE
	SYNTAX  INTEGER
	ACCESS  read-only
	STATUS  mandatory
	DESCRIPTION "PB1 CB31 Max"
		::= { panelboard1 115 }

pb1-CB32-Max
	OBJECT-TYPE
	SYNTAX  INTEGER
	ACCESS  read-only
	STATUS  mandatory
	DESCRIPTION "PB1 CB32 Max"
		::= { panelboard1 116 }

pb1-CB33-Max
	OBJECT-TYPE
	SYNTAX  INTEGER
	ACCESS  read-only
	STATUS  mandatory
	DESCRIPTION "PB1 CB33 Max"
		::= { panelboard1 117 }

pb1-CB34-Max
	OBJECT-TYPE
	SYNTAX  INTEGER
	ACCESS  read-only
	STATUS  mandatory
	DESCRIPTION "PB1 CB34 Max"
		::= { panelboard1 118 }

pb1-CB35-Max
	OBJECT-TYPE
	SYNTAX  INTEGER
	ACCESS  read-only
	STATUS  mandatory
	DESCRIPTION "PB1 CB35 Max"
		::= { panelboard1 119 }

pb1-CB36-Max
	OBJECT-TYPE
	SYNTAX  INTEGER
	ACCESS  read-only
	STATUS  mandatory
	DESCRIPTION "PB1 CB36 Max"
		::= { panelboard1 120 }

pb1-CB37-Max
	OBJECT-TYPE
	SYNTAX  INTEGER
	ACCESS  read-only
	STATUS  mandatory
	DESCRIPTION "PB1 CB37 Max"
		::= { panelboard1 121 }
  
pb1-CB38-Max
	OBJECT-TYPE
	SYNTAX  INTEGER
	ACCESS  read-only
	STATUS  mandatory
	DESCRIPTION "PB1 CB38 Max"
		::= { panelboard1 122 }

pb1-CB39-Max
	OBJECT-TYPE
	SYNTAX  INTEGER
	ACCESS  read-only
	STATUS  mandatory
	DESCRIPTION "PB1 CB39 Max"
		::= { panelboard1 123 }

pb1-CB40-Max
	OBJECT-TYPE
	SYNTAX  INTEGER
	ACCESS  read-only
	STATUS  mandatory
	DESCRIPTION "PB1 CB40 Max"
		::= { panelboard1 124 }

pb1-CB41-Max
	OBJECT-TYPE
	SYNTAX  INTEGER
	ACCESS  read-only
	STATUS  mandatory
	DESCRIPTION "PB1 CB41 Max"
		::= { panelboard1 125 }

pb1-CB42-Max
	OBJECT-TYPE
	SYNTAX  INTEGER
	ACCESS  read-only
	STATUS  mandatory
	DESCRIPTION "PB1 CB42 Max"
		::= { panelboard1 126 }

pb1-CB1-16-Zero
	OBJECT-TYPE
	SYNTAX  INTEGER
	ACCESS  read-write
	STATUS  mandatory
	DESCRIPTION "PB1 CB1-16 Zero
		     Bit 0 = CB1
                     Bit 15 = CB16"
		::= { panelboard1 127 }

pb1-CB17-32-Zero
	OBJECT-TYPE
	SYNTAX  INTEGER
	ACCESS  read-write
	STATUS  mandatory
	DESCRIPTION "PB1 CB17-32 Zero
		     Bit 0 = CB17
                     Bit 15 = CB32"
		     
		::= { panelboard1 128 }

pb1-CB33-42-Zero
	OBJECT-TYPE
	SYNTAX  INTEGER
	ACCESS  read-write
	STATUS  mandatory
	DESCRIPTION "PB1 CB33-42 Zero
		     Bit 0 = CB33
                     Bit 9 = CB42
                     Bits 10-25 not used"
		::= { panelboard1 129 }

pb1-CB1-16-Warning
	OBJECT-TYPE
	SYNTAX  INTEGER
	ACCESS  read-write
	STATUS  mandatory
	DESCRIPTION "PB1 CB1-16 Warning
		     Bit 0 = CB1
                     Bit 15 = CB16"
		::= { panelboard1 130 }

pb1-CB17-32-Warning
	OBJECT-TYPE
	SYNTAX  INTEGER
	ACCESS  read-write
	STATUS  mandatory
	DESCRIPTION "PB1 CB17-32 Warning
		     Bit 0 = CB17
                     Bit 15 = CB32"
		::= { panelboard1 131 }
  
pb1-CB33-42-Warning
	OBJECT-TYPE
	SYNTAX  INTEGER
	ACCESS  read-write
	STATUS  mandatory
	DESCRIPTION "PB1 CB33-42 Warning
		     Bit 0 = CB33
                     Bit 9 = CB42
                     Bits 10-25 not used"
		::= { panelboard1 132 }

pb1-CB1-16-Alarm
	OBJECT-TYPE
	SYNTAX  INTEGER
	ACCESS  read-write
	STATUS  mandatory
	DESCRIPTION "PB1 CB1-16 Alarm
		     Bit 0 = CB1
                     Bit 15 = CB16"
		::= { panelboard1 133 }

pb1-CB17-32-Alarm
	OBJECT-TYPE
	SYNTAX  INTEGER
	ACCESS  read-write
	STATUS  mandatory
	DESCRIPTION "PB1 CB17-32 Alarm
		     Bit 0 = CB17
                     Bit 15 = CB32"
		::= { panelboard1 134 }

pb1-CB33-42-Alarm
	OBJECT-TYPE
	SYNTAX  INTEGER
	ACCESS  read-write
	STATUS  mandatory
	DESCRIPTION "PB1 CB33-42 Alarm
		     Bit 0 = CB33
                     Bit 9 = CB42
                     Bits 10-25 not used"
		::= { panelboard1 135 }

pb1-CB1-Breaker-Size
	OBJECT-TYPE
	SYNTAX  INTEGER
	ACCESS  read-write
	STATUS  mandatory
	DESCRIPTION "PB1 CB1 Breaker-Size
		     Note for all breaker sizes 1-42: 10 = 10 amps
                     Range is 10 to 100 amps"
		::= { panelboard1 136 }

pb1-CB2-Breaker-Size
	OBJECT-TYPE
	SYNTAX  INTEGER
	ACCESS  read-write
	STATUS  mandatory
	DESCRIPTION "PB1 CB2 Breaker-Size"
		::= { panelboard1 137 }

pb1-CB3-Breaker-Size
	OBJECT-TYPE
	SYNTAX  INTEGER
	ACCESS  read-write
	STATUS  mandatory
	DESCRIPTION "PB1 CB3 Breaker-Size"
		::= { panelboard1 138 }

pb1-CB4-Breaker-Size
	OBJECT-TYPE
	SYNTAX  INTEGER
	ACCESS  read-write
	STATUS  mandatory
	DESCRIPTION "PB1 CB4 Breaker-Size"
		::= { panelboard1 139 }

pb1-CB5-Breaker-Size
	OBJECT-TYPE
	SYNTAX  INTEGER
	ACCESS  read-write
	STATUS  mandatory
	DESCRIPTION "PB1 CB5 Breaker-Size"
		::= { panelboard1 140 }

pb1-CB6-Breaker-Size
	OBJECT-TYPE
	SYNTAX  INTEGER
	ACCESS  read-write
	STATUS  mandatory
	DESCRIPTION "PB1 CB6 Breaker-Size"
		::= { panelboard1 141 }
  
pb1-CB7-Breaker-Size
	OBJECT-TYPE
	SYNTAX  INTEGER
	ACCESS  read-write
	STATUS  mandatory
	DESCRIPTION "PB1 CB7 Breaker-Size"
		::= { panelboard1 142 }

pb1-CB8-Breaker-Size
	OBJECT-TYPE
	SYNTAX  INTEGER
	ACCESS  read-write
	STATUS  mandatory
	DESCRIPTION "PB1 CB8 Breaker-Size"
		::= { panelboard1 143 }

pb1-CB9-Breaker-Size
	OBJECT-TYPE
	SYNTAX  INTEGER
	ACCESS  read-write
	STATUS  mandatory
	DESCRIPTION "PB1 CB9 Breaker-Size"
		::= { panelboard1 144 }

pb1-CB10-Breaker-Size
	OBJECT-TYPE
	SYNTAX  INTEGER
	ACCESS  read-write
	STATUS  mandatory
	DESCRIPTION "PB1 CB10 Breaker-Size"
		::= { panelboard1 145 }

pb1-CB11-Breaker-Size
	OBJECT-TYPE
	SYNTAX  INTEGER
	ACCESS  read-write
	STATUS  mandatory
	DESCRIPTION "PB1 CB11 Breaker-Size"
		::= { panelboard1 146 }

pb1-CB12-Breaker-Size
	OBJECT-TYPE
	SYNTAX  INTEGER
	ACCESS  read-write
	STATUS  mandatory
	DESCRIPTION "PB1 CB12 Breaker-Size"
		::= { panelboard1 147 }

pb1-CB13-Breaker-Size
	OBJECT-TYPE
	SYNTAX  INTEGER
	ACCESS  read-write
	STATUS  mandatory
	DESCRIPTION "PB1 CB13 Breaker-Size"
		::= { panelboard1 148 }

pb1-CB14-Breaker-Size
	OBJECT-TYPE
	SYNTAX  INTEGER
	ACCESS  read-write
	STATUS  mandatory
	DESCRIPTION "PB1 CB14 Breaker-Size"
		::= { panelboard1 149 }

pb1-CB15-Breaker-Size
	OBJECT-TYPE
	SYNTAX  INTEGER
	ACCESS  read-write
	STATUS  mandatory
	DESCRIPTION "PB1 CB15 Breaker-Size"
		::= { panelboard1 150 }

pb1-CB16-Breaker-Size
	OBJECT-TYPE
	SYNTAX  INTEGER
	ACCESS  read-write
	STATUS  mandatory
	DESCRIPTION "PB1 CB16 Breaker-Size"
		::= { panelboard1 151 }
  
pb1-CB17-Breaker-Size
	OBJECT-TYPE
	SYNTAX  INTEGER
	ACCESS  read-write
	STATUS  mandatory
	DESCRIPTION "PB1 CB17 Breaker-Size"
		::= { panelboard1 152 }

pb1-CB18-Breaker-Size
	OBJECT-TYPE
	SYNTAX  INTEGER
	ACCESS  read-write
	STATUS  mandatory
	DESCRIPTION "PB1 CB18 Breaker-Size"
		::= { panelboard1 153 }

pb1-CB19-Breaker-Size
	OBJECT-TYPE
	SYNTAX  INTEGER
	ACCESS  read-write
	STATUS  mandatory
	DESCRIPTION "PB1 CB19 Breaker-Size"
		::= { panelboard1 154 }

pb1-CB20-Breaker-Size
	OBJECT-TYPE
	SYNTAX  INTEGER
	ACCESS  read-write
	STATUS  mandatory
	DESCRIPTION "PB1 CB20 Breaker-Size"
		::= { panelboard1 155 }

pb1-CB21-Breaker-Size
	OBJECT-TYPE
	SYNTAX  INTEGER
	ACCESS  read-write
	STATUS  mandatory
	DESCRIPTION "PB1 CB21 Breaker-Size"
		::= { panelboard1 156 }

pb1-CB22-Breaker-Size
	OBJECT-TYPE
	SYNTAX  INTEGER
	ACCESS  read-write
	STATUS  mandatory
	DESCRIPTION "PB1 CB22 Breaker-Size"
		::= { panelboard1 157 }

pb1-CB23-Breaker-Size
	OBJECT-TYPE
	SYNTAX  INTEGER
	ACCESS  read-write
	STATUS  mandatory
	DESCRIPTION "PB1 CB23 Breaker-Size"
		::= { panelboard1 158 }

pb1-CB24-Breaker-Size
	OBJECT-TYPE
	SYNTAX  INTEGER
	ACCESS  read-write
	STATUS  mandatory
	DESCRIPTION "PB1 CB24 Breaker-Size"
		::= { panelboard1 159 }

pb1-CB25-Breaker-Size
	OBJECT-TYPE
	SYNTAX  INTEGER
	ACCESS  read-write
	STATUS  mandatory
	DESCRIPTION "PB1 CB25 Breaker-Size"
		::= { panelboard1 160 }

pb1-CB26-Breaker-Size
	OBJECT-TYPE
	SYNTAX  INTEGER
	ACCESS  read-write
	STATUS  mandatory
	DESCRIPTION "PB1 CB26 Breaker-Size"
		::= { panelboard1 161 }
  
pb1-CB27-Breaker-Size
	OBJECT-TYPE
	SYNTAX  INTEGER
	ACCESS  read-write
	STATUS  mandatory
	DESCRIPTION "PB1 CB27 Breaker-Size"
		::= { panelboard1 162 }

pb1-CB28-Breaker-Size
	OBJECT-TYPE
	SYNTAX  INTEGER
	ACCESS  read-write
	STATUS  mandatory
	DESCRIPTION "PB1 CB28 Breaker-Size"
		::= { panelboard1 163 }

pb1-CB29-Breaker-Size
	OBJECT-TYPE
	SYNTAX  INTEGER
	ACCESS  read-write
	STATUS  mandatory
	DESCRIPTION "PB1 CB29 Breaker-Size"
		::= { panelboard1 164 }

pb1-CB30-Breaker-Size
	OBJECT-TYPE
	SYNTAX  INTEGER
	ACCESS  read-write
	STATUS  mandatory
	DESCRIPTION "PB1 CB30 Breaker-Size"
		::= { panelboard1 165 }

pb1-CB31-Breaker-Size
	OBJECT-TYPE
	SYNTAX  INTEGER
	ACCESS  read-write
	STATUS  mandatory
	DESCRIPTION "PB1 CB31 Breaker-Size"
		::= { panelboard1 166 }

pb1-CB32-Breaker-Size
	OBJECT-TYPE
	SYNTAX  INTEGER
	ACCESS  read-write
	STATUS  mandatory
	DESCRIPTION "PB1 CB32 Breaker-Size"
		::= { panelboard1 167 }

pb1-CB33-Breaker-Size
	OBJECT-TYPE
	SYNTAX  INTEGER
	ACCESS  read-write
	STATUS  mandatory
	DESCRIPTION "PB1 CB33 Breaker-Size"
		::= { panelboard1 168 }

pb1-CB34-Breaker-Size
	OBJECT-TYPE
	SYNTAX  INTEGER
	ACCESS  read-write
	STATUS  mandatory
	DESCRIPTION "PB1 CB34 Breaker-Size"
		::= { panelboard1 169 }

pb1-CB35-Breaker-Size
	OBJECT-TYPE
	SYNTAX  INTEGER
	ACCESS  read-write
	STATUS  mandatory
	DESCRIPTION "PB1 CB35 Breaker-Size"
		::= { panelboard1 170 }

pb1-CB36-Breaker-Size
	OBJECT-TYPE
	SYNTAX  INTEGER
	ACCESS  read-write
	STATUS  mandatory
	DESCRIPTION "PB1 CB36 Breaker-Size"
		::= { panelboard1 171 }
  
pb1-CB37-Breaker-Size
	OBJECT-TYPE
	SYNTAX  INTEGER
	ACCESS  read-write
	STATUS  mandatory
	DESCRIPTION "PB1 CB37 Breaker-Size"
		::= { panelboard1 172 }

pb1-CB38-Breaker-Size
	OBJECT-TYPE
	SYNTAX  INTEGER
	ACCESS  read-write
	STATUS  mandatory
	DESCRIPTION "PB1 CB38 Breaker-Size"
		::= { panelboard1 173 }

pb1-CB39-Breaker-Size
	OBJECT-TYPE
	SYNTAX  INTEGER
	ACCESS  read-write
	STATUS  mandatory
	DESCRIPTION "PB1 CB39 Breaker-Size"
		::= { panelboard1 174 }

pb1-CB40-Breaker-Size
	OBJECT-TYPE
	SYNTAX  INTEGER
	ACCESS  read-write
	STATUS  mandatory
	DESCRIPTION "PB1 CB40 Breaker-Size"
		::= { panelboard1 175 }

pb1-CB41-Breaker-Size
	OBJECT-TYPE
	SYNTAX  INTEGER
	ACCESS  read-write
	STATUS  mandatory
	DESCRIPTION "PB1 CB41 Breaker-Size"
		::= { panelboard1 176 }

pb1-CB42-Breaker-Size
	OBJECT-TYPE
	SYNTAX  INTEGER
	ACCESS  read-write
	STATUS  mandatory
	DESCRIPTION "PB1 CB42 Breaker-Size"
		::= { panelboard1 177 }

pb1-CB1-Warning-Threshold
	OBJECT-TYPE
	SYNTAX  INTEGER
	ACCESS  read-write
	STATUS  mandatory
	DESCRIPTION "PB1 CB1 CB1-Warning-Threshold
		     Note for all warning thresholds 1-42: 70 = 70% of breaker size
                     range is 0-100%"
		::= { panelboard1 178 }

pb1-CB2-Warning-Threshold
	OBJECT-TYPE
	SYNTAX  INTEGER
	ACCESS  read-write
	STATUS  mandatory
	DESCRIPTION "PB1 CB2 Warning-Threshold"
		::= { panelboard1 179 }

pb1-CB3-Warning-Threshold
	OBJECT-TYPE
	SYNTAX  INTEGER
	ACCESS  read-write
	STATUS  mandatory
	DESCRIPTION "PB1 CB3 Warning-Threshold"
		::= { panelboard1 180 }

pb1-CB4-Warning-Threshold
	OBJECT-TYPE
	SYNTAX  INTEGER
	ACCESS  read-write
	STATUS  mandatory
	DESCRIPTION "PB1 CB4 Warning-Threshold"
		::= { panelboard1 181 }
  
pb1-CB5-Warning-Threshold
	OBJECT-TYPE
	SYNTAX  INTEGER
	ACCESS  read-write
	STATUS  mandatory
	DESCRIPTION "PB1 CB5 Warning-Threshold"
		::= { panelboard1 182 }

pb1-CB6-Warning-Threshold
	OBJECT-TYPE
	SYNTAX  INTEGER
	ACCESS  read-write
	STATUS  mandatory
	DESCRIPTION "PB1 CB6 Warning-Threshold"
		::= { panelboard1 183 }

pb1-CB7-Warning-Threshold
	OBJECT-TYPE
	SYNTAX  INTEGER
	ACCESS  read-write
	STATUS  mandatory
	DESCRIPTION "PB1 CB7 Warning-Threshold"
		::= { panelboard1 184 }

pb1-CB8-Warning-Threshold
	OBJECT-TYPE
	SYNTAX  INTEGER
	ACCESS  read-write
	STATUS  mandatory
	DESCRIPTION "PB1 CB8 Warning-Threshold"
		::= { panelboard1 185 }

pb1-CB9-Warning-Threshold
	OBJECT-TYPE
	SYNTAX  INTEGER
	ACCESS  read-write
	STATUS  mandatory
	DESCRIPTION "PB1 CB9 Warning-Threshold"
		::= { panelboard1 186 }

pb1-CB10-Warning-Threshold
	OBJECT-TYPE
	SYNTAX  INTEGER
	ACCESS  read-write
	STATUS  mandatory
	DESCRIPTION "PB1 CB10 Warning-Threshold"
		::= { panelboard1 187 }

pb1-CB11-Warning-Threshold
	OBJECT-TYPE
	SYNTAX  INTEGER
	ACCESS  read-write
	STATUS  mandatory
	DESCRIPTION "PB1 CB11 Warning-Threshold"
		::= { panelboard1 188 }

pb1-CB12-Warning-Threshold
	OBJECT-TYPE
	SYNTAX  INTEGER
	ACCESS  read-write
	STATUS  mandatory
	DESCRIPTION "PB1 CB12 Warning-Threshold"
		::= { panelboard1 189 }

pb1-CB13-Warning-Threshold
	OBJECT-TYPE
	SYNTAX  INTEGER
	ACCESS  read-write
	STATUS  mandatory
	DESCRIPTION "PB1 CB13 Warning-Threshold"
		::= { panelboard1 190 }

pb1-CB14-Warning-Threshold
	OBJECT-TYPE
	SYNTAX  INTEGER
	ACCESS  read-write
	STATUS  mandatory
	DESCRIPTION "PB1 CB14 Warning-Threshold"
		::= { panelboard1 191 }
  
pb1-CB15-Warning-Threshold
	OBJECT-TYPE
	SYNTAX  INTEGER
	ACCESS  read-write
	STATUS  mandatory
	DESCRIPTION "PB1 CB15 Warning-Threshold"
		::= { panelboard1 192 }

pb1-CB16-Warning-Threshold
	OBJECT-TYPE
	SYNTAX  INTEGER
	ACCESS  read-write
	STATUS  mandatory
	DESCRIPTION "PB1 CB16 Warning-Threshold"
		::= { panelboard1 193 }

pb1-CB17-Warning-Threshold
	OBJECT-TYPE
	SYNTAX  INTEGER
	ACCESS  read-write
	STATUS  mandatory
	DESCRIPTION "PB1 CB17 Warning-Threshold"
		::= { panelboard1 194 }

pb1-CB18-Warning-Threshold
	OBJECT-TYPE
	SYNTAX  INTEGER
	ACCESS  read-write
	STATUS  mandatory
	DESCRIPTION "PB1 CB18 Warning-Threshold"
		::= { panelboard1 195 }

pb1-CB19-Warning-Threshold
	OBJECT-TYPE
	SYNTAX  INTEGER
	ACCESS  read-write
	STATUS  mandatory
	DESCRIPTION "PB1 CB19 Warning-Threshold"
		::= { panelboard1 196 }

pb1-CB20-Warning-Threshold
	OBJECT-TYPE
	SYNTAX  INTEGER
	ACCESS  read-write
	STATUS  mandatory
	DESCRIPTION "PB1 CB20 Warning-Threshold"
		::= { panelboard1 197 }

pb1-CB21-Warning-Threshold
	OBJECT-TYPE
	SYNTAX  INTEGER
	ACCESS  read-write
	STATUS  mandatory
	DESCRIPTION "PB1 CB21 Warning-Threshold"
		::= { panelboard1 198 }

pb1-CB22-Warning-Threshold
	OBJECT-TYPE
	SYNTAX  INTEGER
	ACCESS  read-write
	STATUS  mandatory
	DESCRIPTION "PB1 CB22 Warning-Threshold"
		::= { panelboard1 199 }

pb1-CB23-Warning-Threshold
	OBJECT-TYPE
	SYNTAX  INTEGER
	ACCESS  read-write
	STATUS  mandatory
	DESCRIPTION "PB1 CB23 Warning-Threshold"
		::= { panelboard1 200 }

pb1-CB24-Warning-Threshold
	OBJECT-TYPE
	SYNTAX  INTEGER
	ACCESS  read-write
	STATUS  mandatory
	DESCRIPTION "PB1 CB24 Warning-Threshold"
		::= { panelboard1 201 }
  
pb1-CB25-Warning-Threshold
	OBJECT-TYPE
	SYNTAX  INTEGER
	ACCESS  read-write
	STATUS  mandatory
	DESCRIPTION "PB1 CB25 Warning-Threshold"
		::= { panelboard1 202 }

pb1-CB26-Warning-Threshold
	OBJECT-TYPE
	SYNTAX  INTEGER
	ACCESS  read-write
	STATUS  mandatory
	DESCRIPTION "PB1 CB26 Warning-Threshold"
		::= { panelboard1 203 }

pb1-CB27-Warning-Threshold
	OBJECT-TYPE
	SYNTAX  INTEGER
	ACCESS  read-write
	STATUS  mandatory
	DESCRIPTION "PB1 CB27 Warning-Threshold"
		::= { panelboard1 204 }

pb1-CB28-Warning-Threshold
	OBJECT-TYPE
	SYNTAX  INTEGER
	ACCESS  read-write
	STATUS  mandatory
	DESCRIPTION "PB1 CB28 Warning-Threshold"
		::= { panelboard1 205 }

pb1-CB29-Warning-Threshold
	OBJECT-TYPE
	SYNTAX  INTEGER
	ACCESS  read-write
	STATUS  mandatory
	DESCRIPTION "PB1 CB29 Warning-Threshold"
		::= { panelboard1 206 }

pb1-CB30-Warning-Threshold
	OBJECT-TYPE
	SYNTAX  INTEGER
	ACCESS  read-write
	STATUS  mandatory
	DESCRIPTION "PB1 CB30 Warning-Threshold"
		::= { panelboard1 207 }

pb1-CB31-Warning-Threshold
	OBJECT-TYPE
	SYNTAX  INTEGER
	ACCESS  read-write
	STATUS  mandatory
	DESCRIPTION "PB1 CB31 Warning-Threshold"
		::= { panelboard1 208 }

pb1-CB32-Warning-Threshold
	OBJECT-TYPE
	SYNTAX  INTEGER
	ACCESS  read-write
	STATUS  mandatory
	DESCRIPTION "PB1 CB32 Warning-Threshold"
		::= { panelboard1 209 }

pb1-CB33-Warning-Threshold
	OBJECT-TYPE
	SYNTAX  INTEGER
	ACCESS  read-write
	STATUS  mandatory
	DESCRIPTION "PB1 CB33 Warning-Threshold"
		::= { panelboard1 210 }

pb1-CB34-Warning-Threshold
	OBJECT-TYPE
	SYNTAX  INTEGER
	ACCESS  read-write
	STATUS  mandatory
	DESCRIPTION "PB1 CB34 Warning-Threshold"
		::= { panelboard1 211 }
  
pb1-CB35-Warning-Threshold
	OBJECT-TYPE
	SYNTAX  INTEGER
	ACCESS  read-write
	STATUS  mandatory
	DESCRIPTION "PB1 CB35 Warning-Threshold"
		::= { panelboard1 212 }

pb1-CB36-Warning-Threshold
	OBJECT-TYPE
	SYNTAX  INTEGER
	ACCESS  read-write
	STATUS  mandatory
	DESCRIPTION "PB1 CB36 Warning-Threshold"
		::= { panelboard1 213 }

pb1-CB37-Warning-Threshold
	OBJECT-TYPE
	SYNTAX  INTEGER
	ACCESS  read-write
	STATUS  mandatory
	DESCRIPTION "PB1 CB37 Warning-Threshold"
		::= { panelboard1 214 }

pb1-CB38-Warning-Threshold
	OBJECT-TYPE
	SYNTAX  INTEGER
	ACCESS  read-write
	STATUS  mandatory
	DESCRIPTION "PB1 CB38 Warning-Threshold"
		::= { panelboard1 215 }

pb1-CB39-Warning-Threshold
	OBJECT-TYPE
	SYNTAX  INTEGER
	ACCESS  read-write
	STATUS  mandatory
	DESCRIPTION "PB1 CB39 Warning-Threshold"
		::= { panelboard1 216 }

pb1-CB40-Warning-Threshold
	OBJECT-TYPE
	SYNTAX  INTEGER
	ACCESS  read-write
	STATUS  mandatory
	DESCRIPTION "PB1 CB40 Warning-Threshold"
		::= { panelboard1 217 }

pb1-CB41-Warning-Threshold
	OBJECT-TYPE
	SYNTAX  INTEGER
	ACCESS  read-write
	STATUS  mandatory
	DESCRIPTION "PB1 CB41 Warning-Threshold"
		::= { panelboard1 218 }

pb1-CB42-Warning-Threshold
	OBJECT-TYPE
	SYNTAX  INTEGER
	ACCESS  read-write
	STATUS  mandatory
	DESCRIPTION "PB1 CB42 Warning-Threshold"
		::= { panelboard1 219 }

pb1-CB1-Alarm-Threshold
	OBJECT-TYPE
	SYNTAX  INTEGER
	ACCESS  read-write
	STATUS  mandatory
	DESCRIPTION "PB1 CB1 Alarm-Threshold
		     Note for all alarm thresholds 1-42: 80 = 80% of breaker size
                     range is 0-100%"
		::= { panelboard1 220 }


pb1-CB2-Alarm-Threshold
	OBJECT-TYPE
	SYNTAX  INTEGER
	ACCESS  read-write
	STATUS  mandatory
	DESCRIPTION "PB1 CB2 Alarm-Threshold"
		::= { panelboard1 221 }
  
pb1-CB3-Alarm-Threshold
	OBJECT-TYPE
	SYNTAX  INTEGER
	ACCESS  read-write
	STATUS  mandatory
	DESCRIPTION "PB1 CB3 Alarm-Threshold"
		::= { panelboard1 222 }

pb1-CB4-Alarm-Threshold
	OBJECT-TYPE
	SYNTAX  INTEGER
	ACCESS  read-write
	STATUS  mandatory
	DESCRIPTION "PB1 CB4 Alarm-Threshold"
		::= { panelboard1 223 }

pb1-CB5-Alarm-Threshold
	OBJECT-TYPE
	SYNTAX  INTEGER
	ACCESS  read-write
	STATUS  mandatory
	DESCRIPTION "PB1 CB5 Alarm-Threshold"
		::= { panelboard1 224 }

pb1-CB6-Alarm-Threshold
	OBJECT-TYPE
	SYNTAX  INTEGER
	ACCESS  read-write
	STATUS  mandatory
	DESCRIPTION "PB1 CB6 Alarm-Threshold"
		::= { panelboard1 225 }

pb1-CB7-Alarm-Threshold
	OBJECT-TYPE
	SYNTAX  INTEGER
	ACCESS  read-write
	STATUS  mandatory
	DESCRIPTION "PB1 CB7 Alarm-Threshold"
		::= { panelboard1 226 }

pb1-CB8-Alarm-Threshold
	OBJECT-TYPE
	SYNTAX  INTEGER
	ACCESS  read-write
	STATUS  mandatory
	DESCRIPTION "PB1 CB8 Alarm-Threshold"
		::= { panelboard1 227 }

pb1-CB9-Alarm-Threshold
	OBJECT-TYPE
	SYNTAX  INTEGER
	ACCESS  read-write
	STATUS  mandatory
	DESCRIPTION "PB1 CB9 Alarm-Threshold"
		::= { panelboard1 228 }

pb1-CB10-Alarm-Threshold
	OBJECT-TYPE
	SYNTAX  INTEGER
	ACCESS  read-write
	STATUS  mandatory
	DESCRIPTION "PB1 CB10 Alarm-Threshold"
		::= { panelboard1 229 }

pb1-CB11-Alarm-Threshold
	OBJECT-TYPE
	SYNTAX  INTEGER
	ACCESS  read-write
	STATUS  mandatory
	DESCRIPTION "PB1 CB11 Alarm-Threshold"
		::= { panelboard1 230 }

pb1-CB12-Alarm-Threshold
	OBJECT-TYPE
	SYNTAX  INTEGER
	ACCESS  read-write
	STATUS  mandatory
	DESCRIPTION "PB1 CB12 Alarm-Threshold"
		::= { panelboard1 231 }
  
pb1-CB13-Alarm-Threshold
	OBJECT-TYPE
	SYNTAX  INTEGER
	ACCESS  read-write
	STATUS  mandatory
	DESCRIPTION "PB1 CB13 Alarm-Threshold"
		::= { panelboard1 232 }

pb1-CB14-Alarm-Threshold
	OBJECT-TYPE
	SYNTAX  INTEGER
	ACCESS  read-write
	STATUS  mandatory
	DESCRIPTION "PB1 CB14 Alarm-Threshold"
		::= { panelboard1 233 }

pb1-CB15-Alarm-Threshold
	OBJECT-TYPE
	SYNTAX  INTEGER
	ACCESS  read-write
	STATUS  mandatory
	DESCRIPTION "PB1 CB15 Alarm-Threshold"
		::= { panelboard1 234 }

pb1-CB16-Alarm-Threshold
	OBJECT-TYPE
	SYNTAX  INTEGER
	ACCESS  read-write
	STATUS  mandatory
	DESCRIPTION "PB1 CB16 Alarm-Threshold"
		::= { panelboard1 235 }

pb1-CB17-Alarm-Threshold
	OBJECT-TYPE
	SYNTAX  INTEGER
	ACCESS  read-write
	STATUS  mandatory
	DESCRIPTION "PB1 CB17 Alarm-Threshold"
		::= { panelboard1 236 }

pb1-CB18-Alarm-Threshold
	OBJECT-TYPE
	SYNTAX  INTEGER
	ACCESS  read-write
	STATUS  mandatory
	DESCRIPTION "PB1 CB18 Alarm-Threshold"
		::= { panelboard1 237 }

pb1-CB19-Alarm-Threshold
	OBJECT-TYPE
	SYNTAX  INTEGER
	ACCESS  read-write
	STATUS  mandatory
	DESCRIPTION "PB1 CB19 Alarm-Threshold"
		::= { panelboard1 238 }

pb1-CB20-Alarm-Threshold
	OBJECT-TYPE
	SYNTAX  INTEGER
	ACCESS  read-write
	STATUS  mandatory
	DESCRIPTION "PB1 CB20 Alarm-Threshold"
		::= { panelboard1 239 }

pb1-CB21-Alarm-Threshold
	OBJECT-TYPE
	SYNTAX  INTEGER
	ACCESS  read-write
	STATUS  mandatory
	DESCRIPTION "PB1 CB21 Alarm-Threshold"
		::= { panelboard1 240 }

pb1-CB22-Alarm-Threshold
	OBJECT-TYPE
	SYNTAX  INTEGER
	ACCESS  read-write
	STATUS  mandatory
	DESCRIPTION "PB1 CB22 Alarm-Threshold"
		::= { panelboard1 241 }
  
pb1-CB23-Alarm-Threshold
	OBJECT-TYPE
	SYNTAX  INTEGER
	ACCESS  read-write
	STATUS  mandatory
	DESCRIPTION "PB1 CB23 Alarm-Threshold"
		::= { panelboard1 242 }

pb1-CB24-Alarm-Threshold
	OBJECT-TYPE
	SYNTAX  INTEGER
	ACCESS  read-write
	STATUS  mandatory
	DESCRIPTION "PB1 CB24 Alarm-Threshold"
		::= { panelboard1 243 }

pb1-CB25-Alarm-Threshold
	OBJECT-TYPE
	SYNTAX  INTEGER
	ACCESS  read-write
	STATUS  mandatory
	DESCRIPTION "PB1 CB25 Alarm-Threshold"
		::= { panelboard1 244 }

pb1-CB26-Alarm-Threshold
	OBJECT-TYPE
	SYNTAX  INTEGER
	ACCESS  read-write
	STATUS  mandatory
	DESCRIPTION "PB1 CB26 Alarm-Threshold"
		::= { panelboard1 245 }

pb1-CB27-Alarm-Threshold
	OBJECT-TYPE
	SYNTAX  INTEGER
	ACCESS  read-write
	STATUS  mandatory
	DESCRIPTION "PB1 CB27 Alarm-Threshold"
		::= { panelboard1 246 }

pb1-CB28-Alarm-Threshold
	OBJECT-TYPE
	SYNTAX  INTEGER
	ACCESS  read-write
	STATUS  mandatory
	DESCRIPTION "PB1 CB28 Alarm-Threshold"
		::= { panelboard1 247 }

pb1-CB29-Alarm-Threshold
	OBJECT-TYPE
	SYNTAX  INTEGER
	ACCESS  read-write
	STATUS  mandatory
	DESCRIPTION "PB1 CB29 Alarm-Threshold"
		::= { panelboard1 248 }

pb1-CB30-Alarm-Threshold
	OBJECT-TYPE
	SYNTAX  INTEGER
	ACCESS  read-write
	STATUS  mandatory
	DESCRIPTION "PB1 CB30 Alarm-Threshold"
		::= { panelboard1 249 }

pb1-CB31-Alarm-Threshold
	OBJECT-TYPE
	SYNTAX  INTEGER
	ACCESS  read-write
	STATUS  mandatory
	DESCRIPTION "PB1 CB31 Alarm-Threshold"
		::= { panelboard1 250 }

pb1-CB32-Alarm-Threshold
	OBJECT-TYPE
	SYNTAX  INTEGER
	ACCESS  read-write
	STATUS  mandatory
	DESCRIPTION "PB1 CB32 Alarm-Threshold"
		::= { panelboard1 251 }
  
pb1-CB33-Alarm-Threshold
	OBJECT-TYPE
	SYNTAX  INTEGER
	ACCESS  read-write
	STATUS  mandatory
	DESCRIPTION "PB1 CB33 Alarm-Threshold"
		::= { panelboard1 252 }

pb1-CB34-Alarm-Threshold
	OBJECT-TYPE
	SYNTAX  INTEGER
	ACCESS  read-write
	STATUS  mandatory
	DESCRIPTION "PB1 CB34 Alarm-Threshold"
		::= { panelboard1 253 }

pb1-CB35-Alarm-Threshold
	OBJECT-TYPE
	SYNTAX  INTEGER
	ACCESS  read-write
	STATUS  mandatory
	DESCRIPTION "PB1 CB35 Alarm-Threshold"
		::= { panelboard1 254 }

pb1-CB36-Alarm-Threshold
	OBJECT-TYPE
	SYNTAX  INTEGER
	ACCESS  read-write
	STATUS  mandatory
	DESCRIPTION "PB1 CB36 Alarm-Threshold"
		::= { panelboard1 255 }

pb1-CB37-Alarm-Threshold
	OBJECT-TYPE
	SYNTAX  INTEGER
	ACCESS  read-write
	STATUS  mandatory
	DESCRIPTION "PB1 CB37 Alarm-Threshold"
		::= { panelboard1 256 }

pb1-CB38-Alarm-Threshold
	OBJECT-TYPE
	SYNTAX  INTEGER
	ACCESS  read-write
	STATUS  mandatory
	DESCRIPTION "PB1 CB38 Alarm-Threshold"
		::= { panelboard1 257 }

pb1-CB39-Alarm-Threshold
	OBJECT-TYPE
	SYNTAX  INTEGER
	ACCESS  read-write
	STATUS  mandatory
	DESCRIPTION "PB1 CB39 Alarm-Threshold"
		::= { panelboard1 258 }

pb1-CB40-Alarm-Threshold
	OBJECT-TYPE
	SYNTAX  INTEGER
	ACCESS  read-write
	STATUS  mandatory
	DESCRIPTION "PB1 CB40 Alarm-Threshold"
		::= { panelboard1 259 }

pb1-CB41-Alarm-Threshold
	OBJECT-TYPE
	SYNTAX  INTEGER
	ACCESS  read-write
	STATUS  mandatory
	DESCRIPTION "PB1 CB41 Alarm-Threshold"
		::= { panelboard1 260 }

pb1-CB42-Alarm-Threshold
	OBJECT-TYPE
	SYNTAX  INTEGER
	ACCESS  read-write
	STATUS  mandatory
	DESCRIPTION "PB1 CB42 Alarm-Threshold"
		::= { panelboard1 261 }

pb1-CB1-Warning-Time-Delay
	OBJECT-TYPE
	SYNTAX  INTEGER
	ACCESS  read-write
	STATUS  mandatory
	DESCRIPTION "PB1 CB1 Warning-Time-Delay
		     Note for all warning time delays 1-42: units are in seconds"                     
		::= { panelboard1 262 }

pb1-CB2-Warning-Time-Delay
	OBJECT-TYPE
	SYNTAX  INTEGER
	ACCESS  read-write
	STATUS  mandatory
	DESCRIPTION "PB1 CB2 Warning-Time-Delay"
		::= { panelboard1 263 }
  
pb1-CB3-Warning-Time-Delay
	OBJECT-TYPE
	SYNTAX  INTEGER
	ACCESS  read-write
	STATUS  mandatory
	DESCRIPTION "PB1 CB3 Warning-Time-Delay"
		::= { panelboard1 264 }

pb1-CB4-Warning-Time-Delay
	OBJECT-TYPE
	SYNTAX  INTEGER
	ACCESS  read-write
	STATUS  mandatory
	DESCRIPTION "PB1 CB4 Warning-Time-Delay"
		::= { panelboard1 265 }

pb1-CB5-Warning-Time-Delay
	OBJECT-TYPE
	SYNTAX  INTEGER
	ACCESS  read-write
	STATUS  mandatory
	DESCRIPTION "PB1 CB5 Warning-Time-Delay"
		::= { panelboard1 266 }

pb1-CB6-Warning-Time-Delay
	OBJECT-TYPE
	SYNTAX  INTEGER
	ACCESS  read-write
	STATUS  mandatory
	DESCRIPTION "PB1 CB6 Warning-Time-Delay"
		::= { panelboard1 267 }

pb1-CB7-Warning-Time-Delay
	OBJECT-TYPE
	SYNTAX  INTEGER
	ACCESS  read-write
	STATUS  mandatory
	DESCRIPTION "PB1 CB7 Warning-Time-Delay"
		::= { panelboard1 268 }

pb1-CB8-Warning-Time-Delay
	OBJECT-TYPE
	SYNTAX  INTEGER
	ACCESS  read-write
	STATUS  mandatory
	DESCRIPTION "PB1 CB8 Warning-Time-Delay"
		::= { panelboard1 269 }

pb1-CB9-Warning-Time-Delay
	OBJECT-TYPE
	SYNTAX  INTEGER
	ACCESS  read-write
	STATUS  mandatory
	DESCRIPTION "PB1 CB9 Warning-Time-Delay"
		::= { panelboard1 270 }

pb1-CB10-Warning-Time-Delay
	OBJECT-TYPE
	SYNTAX  INTEGER
	ACCESS  read-write
	STATUS  mandatory
	DESCRIPTION "PB1 CB10 Warning-Time-Delay"
		::= { panelboard1 271 }

pb1-CB11-Warning-Time-Delay
	OBJECT-TYPE
	SYNTAX  INTEGER
	ACCESS  read-write
	STATUS  mandatory
	DESCRIPTION "PB1 CB11 Warning-Time-Delay"
		::= { panelboard1 272 }

pb1-CB12-Warning-Time-Delay
	OBJECT-TYPE
	SYNTAX  INTEGER
	ACCESS  read-write
	STATUS  mandatory
	DESCRIPTION "PB1 CB12 Warning-Time-Delay"
		::= { panelboard1 273 }
  
pb1-CB13-Warning-Time-Delay
	OBJECT-TYPE
	SYNTAX  INTEGER
	ACCESS  read-write
	STATUS  mandatory
	DESCRIPTION "PB1 CB13 Warning-Time-Delay"
		::= { panelboard1 274 }

pb1-CB14-Warning-Time-Delay
	OBJECT-TYPE
	SYNTAX  INTEGER
	ACCESS  read-write
	STATUS  mandatory
	DESCRIPTION "PB1 CB14 Warning-Time-Delay"
		::= { panelboard1 275 }

pb1-CB15-Warning-Time-Delay
	OBJECT-TYPE
	SYNTAX  INTEGER
	ACCESS  read-write
	STATUS  mandatory
	DESCRIPTION "PB1 CB15 Warning-Time-Delay"
		::= { panelboard1 276 }

pb1-CB16-Warning-Time-Delay
	OBJECT-TYPE
	SYNTAX  INTEGER
	ACCESS  read-write
	STATUS  mandatory
	DESCRIPTION "PB1 CB16 Warning-Time-Delay"
		::= { panelboard1 277 }

pb1-CB17-Warning-Time-Delay
	OBJECT-TYPE
	SYNTAX  INTEGER
	ACCESS  read-write
	STATUS  mandatory
	DESCRIPTION "PB1 CB17 Warning-Time-Delay"
		::= { panelboard1 278 }

pb1-CB18-Warning-Time-Delay
	OBJECT-TYPE
	SYNTAX  INTEGER
	ACCESS  read-write
	STATUS  mandatory
	DESCRIPTION "PB1 CB18 Warning-Time-Delay"
		::= { panelboard1 279 }

pb1-CB19-Warning-Time-Delay
	OBJECT-TYPE
	SYNTAX  INTEGER
	ACCESS  read-write
	STATUS  mandatory
	DESCRIPTION "PB1 CB19 Warning-Time-Delay"
		::= { panelboard1 280 }

pb1-CB20-Warning-Time-Delay
	OBJECT-TYPE
	SYNTAX  INTEGER
	ACCESS  read-write
	STATUS  mandatory
	DESCRIPTION "PB1 CB20 Warning-Time-Delay"
		::= { panelboard1 281 }

pb1-CB21-Warning-Time-Delay
	OBJECT-TYPE
	SYNTAX  INTEGER
	ACCESS  read-write
	STATUS  mandatory
	DESCRIPTION "PB1 CB21 Warning-Time-Delay"
		::= { panelboard1 282 }

pb1-CB22-Warning-Time-Delay
	OBJECT-TYPE
	SYNTAX  INTEGER
	ACCESS  read-write
	STATUS  mandatory
	DESCRIPTION "PB1 CB22 Warning-Time-Delay"
		::= { panelboard1 283 }
  
pb1-CB23-Warning-Time-Delay
	OBJECT-TYPE
	SYNTAX  INTEGER
	ACCESS  read-write
	STATUS  mandatory
	DESCRIPTION "PB1 CB23 Warning-Time-Delay"
		::= { panelboard1 284 }

pb1-CB24-Warning-Time-Delay
	OBJECT-TYPE
	SYNTAX  INTEGER
	ACCESS  read-write
	STATUS  mandatory
	DESCRIPTION "PB1 CB24 Warning-Time-Delay"
		::= { panelboard1 285 }

pb1-CB25-Warning-Time-Delay
	OBJECT-TYPE
	SYNTAX  INTEGER
	ACCESS  read-write
	STATUS  mandatory
	DESCRIPTION "PB1 CB25 Warning-Time-Delay"
		::= { panelboard1 286 }

pb1-CB26-Warning-Time-Delay
	OBJECT-TYPE
	SYNTAX  INTEGER
	ACCESS  read-write
	STATUS  mandatory
	DESCRIPTION "PB1 CB26 Warning-Time-Delay"
		::= { panelboard1 287 }

pb1-CB27-Warning-Time-Delay
	OBJECT-TYPE
	SYNTAX  INTEGER
	ACCESS  read-write
	STATUS  mandatory
	DESCRIPTION "PB1 CB27 Warning-Time-Delay"
		::= { panelboard1 288 }

pb1-CB28-Warning-Time-Delay
	OBJECT-TYPE
	SYNTAX  INTEGER
	ACCESS  read-write
	STATUS  mandatory
	DESCRIPTION "PB1 CB28 Warning-Time-Delay"
		::= { panelboard1 289 }

pb1-CB29-Warning-Time-Delay
	OBJECT-TYPE
	SYNTAX  INTEGER
	ACCESS  read-write
	STATUS  mandatory
	DESCRIPTION "PB1 CB29 Warning-Time-Delay"
		::= { panelboard1 290}

pb1-CB30-Warning-Time-Delay
	OBJECT-TYPE
	SYNTAX  INTEGER
	ACCESS  read-write
	STATUS  mandatory
	DESCRIPTION "PB1 CB30 Warning-Time-Delay"
		::= { panelboard1 291 }

pb1-CB31-Warning-Time-Delay
	OBJECT-TYPE
	SYNTAX  INTEGER
	ACCESS  read-write
	STATUS  mandatory
	DESCRIPTION "PB1 CB31 Warning-Time-Delay"
		::= { panelboard1 292 }

pb1-CB32-Warning-Time-Delay
	OBJECT-TYPE
	SYNTAX  INTEGER
	ACCESS  read-write
	STATUS  mandatory
	DESCRIPTION "PB1 CB32 Warning-Time-Delay"
		::= { panelboard1 293 }
  
pb1-CB33-Warning-Time-Delay
	OBJECT-TYPE
	SYNTAX  INTEGER
	ACCESS  read-write
	STATUS  mandatory
	DESCRIPTION "PB1 CB33 Warning-Time-Delay"
		::= { panelboard1 294 }

pb1-CB34-Warning-Time-Delay
	OBJECT-TYPE
	SYNTAX  INTEGER
	ACCESS  read-write
	STATUS  mandatory
	DESCRIPTION "PB1 CB34 Warning-Time-Delay"
		::= { panelboard1 295 }

pb1-CB35-Warning-Time-Delay
	OBJECT-TYPE
	SYNTAX  INTEGER
	ACCESS  read-write
	STATUS  mandatory
	DESCRIPTION "PB1 CB35 Warning-Time-Delay"
		::= { panelboard1 296 }

pb1-CB36-Warning-Time-Delay
	OBJECT-TYPE
	SYNTAX  INTEGER
	ACCESS  read-write
	STATUS  mandatory
	DESCRIPTION "PB1 CB36 Warning-Time-Delay"
		::= { panelboard1 297 }

pb1-CB37-Warning-Time-Delay
	OBJECT-TYPE
	SYNTAX  INTEGER
	ACCESS  read-write
	STATUS  mandatory
	DESCRIPTION "PB1 CB37 Warning-Time-Delay"
		::= { panelboard1 298 }

pb1-CB38-Warning-Time-Delay
	OBJECT-TYPE
	SYNTAX  INTEGER
	ACCESS  read-write
	STATUS  mandatory
	DESCRIPTION "PB1 CB38 Warning-Time-Delay"
		::= { panelboard1 299 }

pb1-CB39-Warning-Time-Delay
	OBJECT-TYPE
	SYNTAX  INTEGER
	ACCESS  read-write
	STATUS  mandatory
	DESCRIPTION "PB1 CB39 Warning-Time-Delay"
		::= { panelboard1 300 }

pb1-CB40-Warning-Time-Delay
	OBJECT-TYPE
	SYNTAX  INTEGER
	ACCESS  read-write
	STATUS  mandatory
	DESCRIPTION "PB1 CB40 Warning-Time-Delay"
		::= { panelboard1 301 }

pb1-CB41-Warning-Time-Delay
	OBJECT-TYPE
	SYNTAX  INTEGER
	ACCESS  read-write
	STATUS  mandatory
	DESCRIPTION "PB1 CB41 Warning-Time-Delay"
		::= { panelboard1 302 }

pb1-CB42-Warning-Time-Delay
	OBJECT-TYPE
	SYNTAX  INTEGER
	ACCESS  read-write
	STATUS  mandatory
	DESCRIPTION "PB1 CB42 Warning-Time-Delay"
		::= { panelboard1 303 }

pb1-CB1-Alarm-Time-Delay
	OBJECT-TYPE
	SYNTAX  INTEGER
	ACCESS  read-write
	STATUS  mandatory
	DESCRIPTION "PB1 CB1 Alarm-Time-Delay
		     Note for all alarm time delays 1-42: units are in seconds"                     
		::= { panelboard1 304 }

pb1-CB2-Alarm-Time-Delay
	OBJECT-TYPE
	SYNTAX  INTEGER
	ACCESS  read-write
	STATUS  mandatory
	DESCRIPTION "PB1 CB2 Alarm-Time-Delay"
		::= { panelboard1 305 }
  
pb1-CB3-Alarm-Time-Delay
	OBJECT-TYPE
	SYNTAX  INTEGER
	ACCESS  read-write
	STATUS  mandatory
	DESCRIPTION "PB1 CB3 Alarm-Time-Delay"
		::= { panelboard1 306 }

pb1-CB4-Alarm-Time-Delay
	OBJECT-TYPE
	SYNTAX  INTEGER
	ACCESS  read-write
	STATUS  mandatory
	DESCRIPTION "PB1 CB4 Alarm-Time-Delay"
		::= { panelboard1 307 }

pb1-CB5-Alarm-Time-Delay
	OBJECT-TYPE
	SYNTAX  INTEGER
	ACCESS  read-write
	STATUS  mandatory
	DESCRIPTION "PB1 CB5 Alarm-Time-Delay"
		::= { panelboard1 308 }

pb1-CB6-Alarm-Time-Delay
	OBJECT-TYPE
	SYNTAX  INTEGER
	ACCESS  read-write
	STATUS  mandatory
	DESCRIPTION "PB1 CB6 Alarm-Time-Delay"
		::= { panelboard1 309 }

pb1-CB7-Alarm-Time-Delay
	OBJECT-TYPE
	SYNTAX  INTEGER
	ACCESS  read-write
	STATUS  mandatory
	DESCRIPTION "PB1 CB7 Alarm-Time-Delay"
		::= { panelboard1 310 }

pb1-CB8-Alarm-Time-Delay
	OBJECT-TYPE
	SYNTAX  INTEGER
	ACCESS  read-write
	STATUS  mandatory
	DESCRIPTION "PB1 CB8 Alarm-Time-Delay"
		::= { panelboard1 311 }

pb1-CB9-Alarm-Time-Delay
	OBJECT-TYPE
	SYNTAX  INTEGER
	ACCESS  read-write
	STATUS  mandatory
	DESCRIPTION "PB1 CB9 Alarm-Time-Delay"
		::= { panelboard1 312 }

pb1-CB10-Alarm-Time-Delay
	OBJECT-TYPE
	SYNTAX  INTEGER
	ACCESS  read-write
	STATUS  mandatory
	DESCRIPTION "PB1 CB10 Alarm-Time-Delay"
		::= { panelboard1 313 }

pb1-CB11-Alarm-Time-Delay
	OBJECT-TYPE
	SYNTAX  INTEGER
	ACCESS  read-write
	STATUS  mandatory
	DESCRIPTION "PB1 CB11 Alarm-Time-Delay"
		::= { panelboard1 314 }

pb1-CB12-Alarm-Time-Delay
	OBJECT-TYPE
	SYNTAX  INTEGER
	ACCESS  read-write
	STATUS  mandatory
	DESCRIPTION "PB1 CB12 Alarm-Time-Delay"
		::= { panelboard1 315 }
  
pb1-CB13-Alarm-Time-Delay
	OBJECT-TYPE
	SYNTAX  INTEGER
	ACCESS  read-write
	STATUS  mandatory
	DESCRIPTION "PB1 CB13 Alarm-Time-Delay"
		::= { panelboard1 316 }

pb1-CB14-Alarm-Time-Delay
	OBJECT-TYPE
	SYNTAX  INTEGER
	ACCESS  read-write
	STATUS  mandatory
	DESCRIPTION "PB1 CB14 Alarm-Time-Delay"
		::= { panelboard1 317 }

pb1-CB15-Alarm-Time-Delay
	OBJECT-TYPE
	SYNTAX  INTEGER
	ACCESS  read-write
	STATUS  mandatory
	DESCRIPTION "PB1 CB15 Alarm-Time-Delay"
		::= { panelboard1 318 }

pb1-CB16-Alarm-Time-Delay
	OBJECT-TYPE
	SYNTAX  INTEGER
	ACCESS  read-write
	STATUS  mandatory
	DESCRIPTION "PB1 CB16 Alarm-Time-Delay"
		::= { panelboard1 319 }

pb1-CB17-Alarm-Time-Delay
	OBJECT-TYPE
	SYNTAX  INTEGER
	ACCESS  read-write
	STATUS  mandatory
	DESCRIPTION "PB1 CB17 Alarm-Time-Delay"
		::= { panelboard1 320 }

pb1-CB18-Alarm-Time-Delay
	OBJECT-TYPE
	SYNTAX  INTEGER
	ACCESS  read-write
	STATUS  mandatory
	DESCRIPTION "PB1 CB18 Alarm-Time-Delay"
		::= { panelboard1 321 }

pb1-CB19-Alarm-Time-Delay
	OBJECT-TYPE
	SYNTAX  INTEGER
	ACCESS  read-write
	STATUS  mandatory
	DESCRIPTION "PB1 CB19 Alarm-Time-Delay"
		::= { panelboard1 322 }

pb1-CB20-Alarm-Time-Delay
	OBJECT-TYPE
	SYNTAX  INTEGER
	ACCESS  read-write
	STATUS  mandatory
	DESCRIPTION "PB1 CB20 Alarm-Time-Delay"
		::= { panelboard1 323 }

pb1-CB21-Alarm-Time-Delay
	OBJECT-TYPE
	SYNTAX  INTEGER
	ACCESS  read-write
	STATUS  mandatory
	DESCRIPTION "PB1 CB21 Alarm-Time-Delay"
		::= { panelboard1 324 }

pb1-CB22-Alarm-Time-Delay
	OBJECT-TYPE
	SYNTAX  INTEGER
	ACCESS  read-write
	STATUS  mandatory
	DESCRIPTION "PB1 CB22 Alarm-Time-Delay"
		::= { panelboard1 325 }
  
pb1-CB23-Alarm-Time-Delay
	OBJECT-TYPE
	SYNTAX  INTEGER
	ACCESS  read-write
	STATUS  mandatory
	DESCRIPTION "PB1 CB23 Alarm-Time-Delay"
		::= { panelboard1 326 }

pb1-CB24-Alarm-Time-Delay
	OBJECT-TYPE
	SYNTAX  INTEGER
	ACCESS  read-write
	STATUS  mandatory
	DESCRIPTION "PB1 CB24 Alarm-Time-Delay"
		::= { panelboard1 327 }

pb1-CB25-Alarm-Time-Delay
	OBJECT-TYPE
	SYNTAX  INTEGER
	ACCESS  read-write
	STATUS  mandatory
	DESCRIPTION "PB1 CB25 Alarm-Time-Delay"
		::= { panelboard1 328 }

pb1-CB26-Alarm-Time-Delay
	OBJECT-TYPE
	SYNTAX  INTEGER
	ACCESS  read-write
	STATUS  mandatory
	DESCRIPTION "PB1 CB26 Alarm-Time-Delay"
		::= { panelboard1 329 }

pb1-CB27-Alarm-Time-Delay
	OBJECT-TYPE
	SYNTAX  INTEGER
	ACCESS  read-write
	STATUS  mandatory
	DESCRIPTION "PB1 CB27 Alarm-Time-Delay"
		::= { panelboard1 330 }

pb1-CB28-Alarm-Time-Delay
	OBJECT-TYPE
	SYNTAX  INTEGER
	ACCESS  read-write
	STATUS  mandatory
	DESCRIPTION "PB1 CB28 Alarm-Time-Delay"
		::= { panelboard1 331 }

pb1-CB29-Alarm-Time-Delay
	OBJECT-TYPE
	SYNTAX  INTEGER
	ACCESS  read-write
	STATUS  mandatory
	DESCRIPTION "PB1 CB29 Alarm-Time-Delay"
		::= { panelboard1 332 }

pb1-CB30-Alarm-Time-Delay
	OBJECT-TYPE
	SYNTAX  INTEGER
	ACCESS  read-write
	STATUS  mandatory
	DESCRIPTION "PB1 CB30 Alarm-Time-Delay"
		::= { panelboard1 333 }

pb1-CB31-Alarm-Time-Delay
	OBJECT-TYPE
	SYNTAX  INTEGER
	ACCESS  read-write
	STATUS  mandatory
	DESCRIPTION "PB1 CB31 Alarm-Time-Delay"
		::= { panelboard1 334 }

pb1-CB32-Alarm-Time-Delay
	OBJECT-TYPE
	SYNTAX  INTEGER
	ACCESS  read-write
	STATUS  mandatory
	DESCRIPTION "PB1 CB32 Alarm-Time-Delay"
		::= { panelboard1 335 }
  
pb1-CB33-Alarm-Time-Delay
	OBJECT-TYPE
	SYNTAX  INTEGER
	ACCESS  read-write
	STATUS  mandatory
	DESCRIPTION "PB1 CB33 Alarm-Time-Delay"
		::= { panelboard1 336 }

pb1-CB34-Alarm-Time-Delay
	OBJECT-TYPE
	SYNTAX  INTEGER
	ACCESS  read-write
	STATUS  mandatory
	DESCRIPTION "PB1 CB34 Alarm-Time-Delay"
		::= { panelboard1 337 }

pb1-CB35-Alarm-Time-Delay
	OBJECT-TYPE
	SYNTAX  INTEGER
	ACCESS  read-write
	STATUS  mandatory
	DESCRIPTION "PB1 CB35 Alarm-Time-Delay"
		::= { panelboard1 338 }

pb1-CB36-Alarm-Time-Delay
	OBJECT-TYPE
	SYNTAX  INTEGER
	ACCESS  read-write
	STATUS  mandatory
	DESCRIPTION "PB1 CB36 Alarm-Time-Delay"
		::= { panelboard1 339 }

pb1-CB37-Alarm-Time-Delay
	OBJECT-TYPE
	SYNTAX  INTEGER
	ACCESS  read-write
	STATUS  mandatory
	DESCRIPTION "PB1 CB37 Alarm-Time-Delay"
		::= { panelboard1 340 }

pb1-CB38-Alarm-Time-Delay
	OBJECT-TYPE
	SYNTAX  INTEGER
	ACCESS  read-write
	STATUS  mandatory
	DESCRIPTION "PB1 CB38 Alarm-Time-Delay"
		::= { panelboard1 341 }

pb1-CB39-Alarm-Time-Delay
	OBJECT-TYPE
	SYNTAX  INTEGER
	ACCESS  read-write
	STATUS  mandatory
	DESCRIPTION "PB1 CB39 Alarm-Time-Delay"
		::= { panelboard1 342 }

pb1-CB40-Alarm-Time-Delay
	OBJECT-TYPE
	SYNTAX  INTEGER
	ACCESS  read-write
	STATUS  mandatory
	DESCRIPTION "PB1 CB40 Alarm-Time-Delay"
		::= { panelboard1 343 }

pb1-CB41-Alarm-Time-Delay
	OBJECT-TYPE
	SYNTAX  INTEGER
	ACCESS  read-write
	STATUS  mandatory
	DESCRIPTION "PB1 CB41 Alarm-Time-Delay"
		::= { panelboard1 344 }

pb1-CB42-Alarm-Time-Delay
	OBJECT-TYPE
	SYNTAX  INTEGER
	ACCESS  read-write
	STATUS  mandatory
	DESCRIPTION "PB1 CB42 Alarm-Time-Delay"
		::= { panelboard1 345 }

pb1-Global-Breaker-Size
	OBJECT-TYPE
	SYNTAX  INTEGER
	ACCESS  read-write
	STATUS  mandatory
	DESCRIPTION "PB1 Global-Breaker-Size
		     Note for global breaker size: 10 = 10 amps
                     Range is 10 to 100 amps"
		::= { panelboard1 346 }

pb1-Global-Warning-Threshold
	OBJECT-TYPE
	SYNTAX  INTEGER
	ACCESS  read-write
	STATUS  mandatory
	DESCRIPTION "PB1 Global-Warning-Threshold
		     Note for global warning threshold: 70 = 70% of breaker size
                     range is 0-100%"
		::= { panelboard1 347 }

pb1-Global-Alarm-Threshold
	OBJECT-TYPE
	SYNTAX  INTEGER
	ACCESS  read-write
	STATUS  mandatory
	DESCRIPTION "PB1 Global-Alarm-Threshold
		     Note for global alarm threshold: 80 = 80% of breaker size
                     range is 0-100%"
		::= { panelboard1 348 }

pb1-Global-Warning-Time-Delay
	OBJECT-TYPE
	SYNTAX  INTEGER
	ACCESS  read-write
	STATUS  mandatory
	DESCRIPTION "PB1 Global-Warning-Time-Delay
		     Note for global warning time delay: units are in seconds"                     
		::= { panelboard1 349 }

pb1-Global-Alarm-Time-Delay
	OBJECT-TYPE
	SYNTAX  INTEGER
	ACCESS  read-write
	STATUS  mandatory
	DESCRIPTION "PB1 Global-Alarm-Time-Delay
		     Note for global alarm time delay: units are in seconds"                     
		::= { panelboard1 350 }

pb1-Min-Max-Reset
	OBJECT-TYPE
	SYNTAX  INTEGER
	ACCESS  read-write
	STATUS  mandatory
	DESCRIPTION "PB1 Min-Max-Reset
                     Note for Min-Max Reset: writing to this register will clear minimum
		     and maximum current values"
		::= { panelboard1 351 }

pb1-Global-Warning-Alarm-Register
	OBJECT-TYPE
	SYNTAX  INTEGER
	ACCESS  read-only
	STATUS  mandatory
	DESCRIPTION "PB1 Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { panelboard1 352 }

pb1-Meter-Alarm-Status-Latching
	OBJECT-TYPE
	SYNTAX  INTEGER
	ACCESS  read-write
	STATUS  mandatory
	DESCRIPTION "PB1 Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { panelboard1 353 }

pb1-Meter-Alarm-Status-Nonlatching
	OBJECT-TYPE
	SYNTAX  INTEGER
	ACCESS  read-only
	STATUS  mandatory
	DESCRIPTION "PB1 Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { panelboard1 354 }

pb1-Digital-Alarm-Status
	OBJECT-TYPE
	SYNTAX  INTEGER
	ACCESS  read-only
	STATUS  mandatory
	DESCRIPTION "PB1 Digital-Alarm-Status
			bit 0:	Digital alarm 1
			bit 1:	Digital alarm 2
			bit 2: 	Digital alarm 3
			bit 3: 	Digital alarm 4
			bits 4 – 15: Not Used"
		::= { panelboard1 355 }

pb1-Current-Option-Setting
	OBJECT-TYPE
	SYNTAX  INTEGER
	ACCESS  read-only
	STATUS  mandatory
	DESCRIPTION "PB1 Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { panelboard1 356 }

pb1-Current-Phase-A-Panelboard
	OBJECT-TYPE
	SYNTAX  INTEGER
	ACCESS  read-only
	STATUS  mandatory
	DESCRIPTION "PB1 Current-Phase-A-Panelboard
                     Note for all currents: 100 = 10.0 amps"
		::= { panelboard1 357 }

pb1-Current-Phase-B-Panelboard
	OBJECT-TYPE
	SYNTAX  INTEGER
	ACCESS  read-only
	STATUS  mandatory
	DESCRIPTION "PB1 Current-Phase-B-Panelboard"
		::= { panelboard1 358 }

pb1-Current-Phase-C-Panelboard
	OBJECT-TYPE
	SYNTAX  INTEGER
	ACCESS  read-only
	STATUS  mandatory
	DESCRIPTION "PB1 Current-Phase-C-Panelboard"
		::= { panelboard1 359 }

pb1-Current-Neutral-Panelboard
	OBJECT-TYPE
	SYNTAX  INTEGER
	ACCESS  read-only
	STATUS  mandatory
	DESCRIPTION "PB1 Current-Neutral-Panelboard"
		::= { panelboard1 360 }


pb1-Over-Current-Alarm-Threshhold-Pnlbd
	OBJECT-TYPE
	SYNTAX  INTEGER
	ACCESS  read-write
	STATUS  mandatory
	DESCRIPTION "PB1 Over-Current-Alarm-Threshhold-Pnlbd"
		::= { panelboard1 361 }

pb1-Under-Current-Alarm-Threshhold-Pnlbd
	OBJECT-TYPE
	SYNTAX  INTEGER
	ACCESS  read-write
	STATUS  mandatory
	DESCRIPTION "PB1 Under-Current-Alarm-Threshhold-Pnlbd"
		::= { panelboard1 362 }

pb1-Over-Current-Set-Counter-Pnlbd
	OBJECT-TYPE
	SYNTAX  INTEGER
	ACCESS  read-only
	STATUS  mandatory
	DESCRIPTION "PB1 Over-Current-Set-Counter-Pnlbd
		     Note for all counters:
                     The set counter is incremented when the value goes outside the threshold limit
                     The reset counter is incremented when the value is returns to  the threshold limit"
		::= { panelboard1 363 }

pb1-Over-Current-Reset-Counter-Pnlbd
	OBJECT-TYPE
	SYNTAX  INTEGER
	ACCESS  read-only
	STATUS  mandatory
	DESCRIPTION "PB1 Over-Current-Reset-Counter-Pnlbd"
		::= { panelboard1 364 }

pb1-Under-Current-Set-Counter-Pnlbd
	OBJECT-TYPE
	SYNTAX  INTEGER
	ACCESS  read-only
	STATUS  mandatory
	DESCRIPTION "PB1 Under-Current-Set-Counter-Pnlbd"
		::= { panelboard1 365 }

pb1-Under-Current-Reset-Counter-Pnlbd
	OBJECT-TYPE
	SYNTAX  INTEGER
	ACCESS  read-only
	STATUS  mandatory
	DESCRIPTION "PB1 Under-Current-Reset-Counter-Pnlbd"
		::= { panelboard1 366 }

pb1-Current-Phase-A-Both-Pnlbd
	OBJECT-TYPE
	SYNTAX  INTEGER
	ACCESS  read-only
	STATUS  mandatory
	DESCRIPTION "PB1 Current-Phase-A-Both-Pnlbd"
		::= { panelboard1 367 }

pb1-Current-Phase-B-Both-Pnlbd
	OBJECT-TYPE
	SYNTAX  INTEGER
	ACCESS  read-only
	STATUS  mandatory
	DESCRIPTION "PB1 Current-Phase-B-Both-Pnlbd"
		::= { panelboard1 368 }

pb1-Current-Phase-C-Both-Pnlbd
	OBJECT-TYPE
	SYNTAX  INTEGER
	ACCESS  read-only
	STATUS  mandatory
	DESCRIPTION "PB1 Current-Phase-C-Both-Pnlbd"
		::= { panelboard1 369 }

pb1-Current-Neutral-Both-Pnlbd
	OBJECT-TYPE
	SYNTAX  INTEGER
	ACCESS  read-only
	STATUS  mandatory
	DESCRIPTION "PB1 Current-Neutral-Both-Pnlbd"
		::= { panelboard1 370 }


pb1-Over-Current-Alarm-Threshhold-Both-Pnlbd
	OBJECT-TYPE
	SYNTAX  INTEGER
	ACCESS  read-write
	STATUS  mandatory
	DESCRIPTION "PB1 Over-Current-Alarm-Threshhold-Both-Pnlbd"
		::= { panelboard1 371 }

pb1-Under-Current-Alarm-Threshhold-Both-Pnlbd
	OBJECT-TYPE
	SYNTAX  INTEGER
	ACCESS  read-write
	STATUS  mandatory
	DESCRIPTION "PB1 Under-Current-Alarm-Threshhold-Both-Pnlbd"
		::= { panelboard1 372 }

pb1-Over-Current-Set-Counter-Both-Pnlbd
	OBJECT-TYPE
	SYNTAX  INTEGER
	ACCESS  read-only
	STATUS  mandatory
	DESCRIPTION "PB1 Over-Current-Set-Counter-Both-Pnlbd"
		::= { panelboard1 373 }

pb1-Over-Current-Reset-Counter-Both-Pnlbd
	OBJECT-TYPE
	SYNTAX  INTEGER
	ACCESS  read-only
	STATUS  mandatory
	DESCRIPTION "PB1 Over-Current-Reset-Counter-Both-Pnlbd"
		::= { panelboard1 374 }

pb1-Under-Current-Set-Counter-Both-Pnlbd
	OBJECT-TYPE
	SYNTAX  INTEGER
	ACCESS  read-only
	STATUS  mandatory
	DESCRIPTION "PB1 Under-Current-Set-Counter-Both-Pnlbd"
		::= { panelboard1 375 }

pb1-Under-Current-Reset-Counter-Both-Pnlbd
	OBJECT-TYPE
	SYNTAX  INTEGER
	ACCESS  read-only
	STATUS  mandatory
	DESCRIPTION "PB1 Under-Current-Reset-Counter-Both-Pnlbd"
		::= { panelboard1 376 }

pb1-Voltage-Option-Setting
	OBJECT-TYPE
	SYNTAX  INTEGER
	ACCESS  read-only
	STATUS  mandatory
	DESCRIPTION "PB1 Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { panelboard1 377 }

pb1-Voltage-A-B-Main
	OBJECT-TYPE
	SYNTAX  INTEGER
	ACCESS  read-only
	STATUS  mandatory
	DESCRIPTION "PB1 Voltage-A-B-Main
                     Note for all voltages: 1200 = 120.0 volts"
		::= { panelboard1 378 }

pb1-Voltage-B-C-Main
	OBJECT-TYPE
	SYNTAX  INTEGER
	ACCESS  read-only
	STATUS  mandatory
	DESCRIPTION "PB1 Voltage-B-C-Main"
		::= { panelboard1 379 }

pb1-Voltage-C-A-Main
	OBJECT-TYPE
	SYNTAX  INTEGER
	ACCESS  read-only
	STATUS  mandatory
	DESCRIPTION "PB1 Voltage-C-A-Main"
		::= { panelboard1 380 }

pb1-Voltage-A-N-Main
	OBJECT-TYPE
	SYNTAX  INTEGER
	ACCESS  read-only
	STATUS  mandatory
	DESCRIPTION "PB1 Voltage-A-N-Main"
		::= { panelboard1 381 }

pb1-Voltage-B-N-Main
	OBJECT-TYPE
	SYNTAX  INTEGER
	ACCESS  read-only
	STATUS  mandatory
	DESCRIPTION "PB1 Voltage-B-N-Main"
		::= { panelboard1 382 }

pb1-Voltage-C-N-Main
	OBJECT-TYPE
	SYNTAX  INTEGER
	ACCESS  read-only
	STATUS  mandatory
	DESCRIPTION "PB1 Voltage-C-N-Main"
		::= { panelboard1 383 }

pb1-Over-Voltage-Alarm-Threshhold-Main
	OBJECT-TYPE
	SYNTAX  INTEGER
	ACCESS  read-write
	STATUS  mandatory
	DESCRIPTION "PB1 Over-Voltage-Alarm-Threshhold-Main
                     Note All Over and Under Voltage is for L-L values"
		::= { panelboard1 384 }

pb1-Under-Voltage-Alarm-Threshhold-Main
	OBJECT-TYPE
	SYNTAX  INTEGER
	ACCESS  read-write
	STATUS  mandatory
	DESCRIPTION "PB1 Under-Voltage-Alarm-Threshhold-Main"
		::= { panelboard1 385 }

pb1-Over-Voltage-Set-Counter-Main
	OBJECT-TYPE
	SYNTAX  INTEGER
	ACCESS  read-only
	STATUS  mandatory
	DESCRIPTION "PB1 Over-Voltage-Set-Counter-Main"
		::= { panelboard1 386 }

pb1-Over-Voltage-Reset-Counter-Main
	OBJECT-TYPE
	SYNTAX  INTEGER
	ACCESS  read-only
	STATUS  mandatory
	DESCRIPTION "PB1 Over-Voltage-Reset-Counter-Main"
		::= { panelboard1 387 }

pb1-Under-Voltage-Set-Counter-Main
	OBJECT-TYPE
	SYNTAX  INTEGER
	ACCESS  read-only
	STATUS  mandatory
	DESCRIPTION "PB1 Under-Voltage-Set-Counter-Main"
		::= { panelboard1 388 }

pb1-Under-Voltage-Reset-Counter-Main
	OBJECT-TYPE
	SYNTAX  INTEGER
	ACCESS  read-only
	STATUS  mandatory
	DESCRIPTION "PB1 Under-Voltage-Reset-Counter-Main"
		::= { panelboard1 389 }


pb1-Voltage-Frequency-Main
	OBJECT-TYPE
	SYNTAX  INTEGER
	ACCESS  read-only
	STATUS  mandatory
	DESCRIPTION "PB1 Voltage-Frequency-Main
                     note for frequency: 600 = 60.0Hz
                     Range is 40-70Hz
                     Note if insufficient voltage is present frequency will read 0xFFFF"
		::= { panelboard1 390 }

pb1-Voltage-A-B-Alternate
	OBJECT-TYPE
	SYNTAX  INTEGER
	ACCESS  read-only
	STATUS  mandatory
	DESCRIPTION "PB1 Voltage-A-B-Alternate"
		::= { panelboard1 391 }

pb1-Voltage-B-C-Alternate
	OBJECT-TYPE
	SYNTAX  INTEGER
	ACCESS  read-only
	STATUS  mandatory
	DESCRIPTION "PB1 Voltage-B-C-Alternate"
		::= { panelboard1 392 }

pb1-Voltage-C-A-Alternate
	OBJECT-TYPE
	SYNTAX  INTEGER
	ACCESS  read-only
	STATUS  mandatory
	DESCRIPTION "PB1 Voltage-C-A-Alternate"
		::= { panelboard1 393 }

pb1-Voltage-A-N-Alternate
	OBJECT-TYPE
	SYNTAX  INTEGER
	ACCESS  read-only
	STATUS  mandatory
	DESCRIPTION "PB1 Voltage-A-N-Alternate"
		::= { panelboard1 394 }

pb1-Voltage-B-N-Alternate
	OBJECT-TYPE
	SYNTAX  INTEGER
	ACCESS  read-only
	STATUS  mandatory
	DESCRIPTION "PB1 Voltage-B-N-Alternate"
		::= { panelboard1 395 }

pb1-Voltage-C-N-Alternate
	OBJECT-TYPE
	SYNTAX  INTEGER
	ACCESS  read-only
	STATUS  mandatory
	DESCRIPTION "PB1 Voltage-C-N-Alternate"
		::= { panelboard1 396 }

pb1-Over-Voltage-Alarm-Threshhold-Alternate
	OBJECT-TYPE
	SYNTAX  INTEGER
	ACCESS  read-write
	STATUS  mandatory
	DESCRIPTION "PB1 Over-Voltage-Alarm-Threshhold-Alternate"
		::= { panelboard1 397 }

pb1-Under-Voltage-Alarm-Threshhold-Alternate
	OBJECT-TYPE
	SYNTAX  INTEGER
	ACCESS  read-write
	STATUS  mandatory
	DESCRIPTION "PB1 Under-Voltage-Alarm-Threshhold-Alternate"
		::= { panelboard1 398 }

pb1-Over-Voltage-Set-Counter-Alternate
	OBJECT-TYPE
	SYNTAX  INTEGER
	ACCESS  read-only
	STATUS  mandatory
	DESCRIPTION "PB1 Over-Voltage-Set-Counter-Alternate"
		::= { panelboard1 399 }

pb1-Over-Voltage-Reset-Counter-Alternate
	OBJECT-TYPE
	SYNTAX  INTEGER
	ACCESS  read-only
	STATUS  mandatory
	DESCRIPTION "PB1 Over-Voltage-Reset-Counter-Alternate"
		::= { panelboard1 400 }

pb1-Under-Voltage-Set-Counter-Alternate
	OBJECT-TYPE
	SYNTAX  INTEGER
	ACCESS  read-only
	STATUS  mandatory
	DESCRIPTION "PB1 Under-Voltage-Set-Counter-Alternate"
		::= { panelboard1 401 }

pb1-Under-Voltage-Reset-Counter-Alternate
	OBJECT-TYPE
	SYNTAX  INTEGER
	ACCESS  read-only
	STATUS  mandatory
	DESCRIPTION "PB1 Under-Voltage-Reset-Counter-Alternate"
		::= { panelboard1 402 }

pb1-Real-Power-KW
	OBJECT-TYPE
	SYNTAX  INTEGER
	ACCESS  read-only
	STATUS  mandatory
	DESCRIPTION "PB1 Real-Power-KW
                     Note for all KWs: 100 = 10.0 KW"
		::= { panelboard1 403 }

pb1-Real-Power-Phase-A
	OBJECT-TYPE
	SYNTAX  INTEGER
	ACCESS  read-only
	STATUS  mandatory
	DESCRIPTION "PB1 Real-Power-Phase-A"
		::= { panelboard1 404 }

pb1-Real-Power-Phase-B
	OBJECT-TYPE
	SYNTAX  INTEGER
	ACCESS  read-only
	STATUS  mandatory
	DESCRIPTION "PB1 Real-Power-Phase-B"
		::= { panelboard1 405 }

pb1-Real-Power-Phase-C
	OBJECT-TYPE
	SYNTAX  INTEGER
	ACCESS  read-only
	STATUS  mandatory
	DESCRIPTION "PB1 Real-Power-Phase-C"
		::= { panelboard1 406 }

pb1-Reactive-Power-KVAR
	OBJECT-TYPE
	SYNTAX  INTEGER
	ACCESS  read-only
	STATUS  mandatory
	DESCRIPTION "PB1 Reactive-Power-KVAR
                     Note for KVAR: 100 = 10.0 KVAR"
		::= { panelboard1 407 }

pb1-Apparent-Power-KVA
	OBJECT-TYPE
	SYNTAX  INTEGER
	ACCESS  read-only
	STATUS  mandatory
	DESCRIPTION "PB1 Apparent-Power-KVA
                     Note for KVA: 100 = 10.0 KVA"
		::= { panelboard1 408 }

pb1-Total-Power-Factor
	OBJECT-TYPE
	SYNTAX  INTEGER
	ACCESS  read-only
	STATUS  mandatory
	DESCRIPTION "PB1 Total-Power-Factor
                     Note for all Power Factor: 1000 = 100.0 PF"
		::= { panelboard1 409 }

pb1-Power-Factor-Phase-A
	OBJECT-TYPE
	SYNTAX  INTEGER
	ACCESS  read-only
	STATUS  mandatory
	DESCRIPTION "PB1 Power-Factor-Phase-A"
		::= { panelboard1 410 }

pb1-Power-Factor-Phase-B
	OBJECT-TYPE
	SYNTAX  INTEGER
	ACCESS  read-only
	STATUS  mandatory
	DESCRIPTION "PB1 Power-Factor-Phase-B"
		::= { panelboard1 411 }

pb1-Power-Factor-Phase-C
	OBJECT-TYPE
	SYNTAX  INTEGER
	ACCESS  read-only
	STATUS  mandatory
	DESCRIPTION "PB1 Power-Factor-Phase-C"
		::= { panelboard1 412 }

pb1-Energy-Consumption-KWh-Lower-Word-Integer
	OBJECT-TYPE
	SYNTAX  INTEGER
	ACCESS  read-write
	STATUS  mandatory
	DESCRIPTION "PB1 Energy-Consumption-KWh-Lower-Word-Integer
		     Note for KWh: 100 = 100KWh
                     Combine lower and upper integers into a word for total KWh"
		::= { panelboard1 413 }

pb1-Energy-Consumption-KWh-Upper-Word-Integer
	OBJECT-TYPE
	SYNTAX  INTEGER
	ACCESS  read-write
	STATUS  mandatory
	DESCRIPTION "PB1 Energy-Consumption-KWh-Upper-Word-Integer"
		::= { panelboard1 414 }

pb1-Main-Voltage-THD-Phase-A
	OBJECT-TYPE
	SYNTAX  INTEGER
	ACCESS  read-only
	STATUS  mandatory
	DESCRIPTION "PB1 Main-Voltage-THD-Phase-A"
		::= { panelboard1 415 }

pb1-Main-Voltage-THD-Phase-B
	OBJECT-TYPE
	SYNTAX  INTEGER
	ACCESS  read-only
	STATUS  mandatory
	DESCRIPTION "PB1 Main-Voltage-THD-Phase-B"
		::= { panelboard1 416 }

pb1-Main-Voltage-THD-Phase-C
	OBJECT-TYPE
	SYNTAX  INTEGER
	ACCESS  read-only
	STATUS  mandatory
	DESCRIPTION "PB1 Main-Voltage-THD-Phase-C"
		::= { panelboard1 417 }

pb1-Alt-Voltage-THD-Phase-A
	OBJECT-TYPE
	SYNTAX  INTEGER
	ACCESS  read-only
	STATUS  mandatory
	DESCRIPTION "PB1 Alt-Voltage-THD-Phase-A"
		::= { panelboard1 418 }

pb1-Alt-Voltage-THD-Phase-B
	OBJECT-TYPE
	SYNTAX  INTEGER
	ACCESS  read-only
	STATUS  mandatory
	DESCRIPTION "PB1 Alt-Voltage-THD-Phase-B"
		::= { panelboard1 419 }

pb1-Alt-Voltage-THD-Phase-C
	OBJECT-TYPE
	SYNTAX  INTEGER
	ACCESS  read-only
	STATUS  mandatory
	DESCRIPTION "PB1 Alt-Voltage-THD-Phase-C"
		::= { panelboard1 420 }

pb1-Current-Ground-Panelboard
	OBJECT-TYPE
	SYNTAX  INTEGER
	ACCESS  read-only
	STATUS  mandatory
	DESCRIPTION "PB1 Current-Ground-Panelboard"
		::= { panelboard1 421 }



--------------------------------------------------------------------------------

pb2-CB1-Current
	OBJECT-TYPE
	SYNTAX  INTEGER
	ACCESS  read-only
	STATUS  mandatory
	DESCRIPTION "PB2 CB1 Current
		     Note for all currents 1-42: 100 = 10.0 amps"
		::= { panelboard2 1 }
  
pb2-CB2-Current
	OBJECT-TYPE
	SYNTAX  INTEGER
	ACCESS  read-only
	STATUS  mandatory
	DESCRIPTION "PB2 CB2 Current"
		::= { panelboard2 2 }

pb2-CB3-Current
	OBJECT-TYPE
	SYNTAX  INTEGER
	ACCESS  read-only
	STATUS  mandatory
	DESCRIPTION "PB2 CB3 Current"
		::= { panelboard2 3 }

pb2-CB4-Current
	OBJECT-TYPE
	SYNTAX  INTEGER
	ACCESS  read-only
	STATUS  mandatory
	DESCRIPTION "PB2 CB4 Current"
		::= { panelboard2 4 }

pb2-CB5-Current
	OBJECT-TYPE
	SYNTAX  INTEGER
	ACCESS  read-only
	STATUS  mandatory
	DESCRIPTION "PB2 CB5 Current"
		::= { panelboard2 5 }

pb2-CB6-Current
	OBJECT-TYPE
	SYNTAX  INTEGER
	ACCESS  read-only
	STATUS  mandatory
	DESCRIPTION "PB2 CB6 Current"
		::= { panelboard2 6 }

pb2-CB7-Current
	OBJECT-TYPE
	SYNTAX  INTEGER
	ACCESS  read-only
	STATUS  mandatory
	DESCRIPTION "PB2 CB7 Current"
		::= { panelboard2 7 }

pb2-CB8-Current
	OBJECT-TYPE
	SYNTAX  INTEGER
	ACCESS  read-only
	STATUS  mandatory
	DESCRIPTION "PB2 CB8 Current"
		::= { panelboard2 8 }

pb2-CB9-Current
	OBJECT-TYPE
	SYNTAX  INTEGER
	ACCESS  read-only
	STATUS  mandatory
	DESCRIPTION "PB2 CB9 Current"
		::= { panelboard2 9 }

pb2-CB10-Current
	OBJECT-TYPE
	SYNTAX  INTEGER
	ACCESS  read-only
	STATUS  mandatory
	DESCRIPTION "PB2 CB10 Current"
		::= { panelboard2 10 }

pb2-CB11-Current
	OBJECT-TYPE
	SYNTAX  INTEGER
	ACCESS  read-only
	STATUS  mandatory
	DESCRIPTION "PB2 CB11 Current"
		::= { panelboard2 11 }
  
pb2-CB12-Current
	OBJECT-TYPE
	SYNTAX  INTEGER
	ACCESS  read-only
	STATUS  mandatory
	DESCRIPTION "PB2 CB12 Current"
		::= { panelboard2 12 }

pb2-CB13-Current
	OBJECT-TYPE
	SYNTAX  INTEGER
	ACCESS  read-only
	STATUS  mandatory
	DESCRIPTION "PB2 CB13 Current"
		::= { panelboard2 13 }

pb2-CB14-Current
	OBJECT-TYPE
	SYNTAX  INTEGER
	ACCESS  read-only
	STATUS  mandatory
	DESCRIPTION "PB2 CB14 Current"
		::= { panelboard2 14 }

pb2-CB15-Current
	OBJECT-TYPE
	SYNTAX  INTEGER
	ACCESS  read-only
	STATUS  mandatory
	DESCRIPTION "PB2 CB15 Current"
		::= { panelboard2 15 }

pb2-CB16-Current
	OBJECT-TYPE
	SYNTAX  INTEGER
	ACCESS  read-only
	STATUS  mandatory
	DESCRIPTION "PB2 CB16 Current"
		::= { panelboard2 16 }

pb2-CB17-Current
	OBJECT-TYPE
	SYNTAX  INTEGER
	ACCESS  read-only
	STATUS  mandatory
	DESCRIPTION "PB2 CB17 Current"
		::= { panelboard2 17 }

pb2-CB18-Current
	OBJECT-TYPE
	SYNTAX  INTEGER
	ACCESS  read-only
	STATUS  mandatory
	DESCRIPTION "PB2 CB18 Current"
		::= { panelboard2 18 }

pb2-CB19-Current
	OBJECT-TYPE
	SYNTAX  INTEGER
	ACCESS  read-only
	STATUS  mandatory
	DESCRIPTION "PB2 CB19 Current"
		::= { panelboard2 19 }

pb2-CB20-Current
	OBJECT-TYPE
	SYNTAX  INTEGER
	ACCESS  read-only
	STATUS  mandatory
	DESCRIPTION "PB2 CB20 Current"
		::= { panelboard2 20 }

pb2-CB21-Current
	OBJECT-TYPE
	SYNTAX  INTEGER
	ACCESS  read-only
	STATUS  mandatory
	DESCRIPTION "PB2 CB21 Current"
		::= { panelboard2 21 }
  
pb2-CB22-Current
	OBJECT-TYPE
	SYNTAX  INTEGER
	ACCESS  read-only
	STATUS  mandatory
	DESCRIPTION "PB2 CB22 Current"
		::= { panelboard2 22 }

pb2-CB23-Current
	OBJECT-TYPE
	SYNTAX  INTEGER
	ACCESS  read-only
	STATUS  mandatory
	DESCRIPTION "PB2 CB23 Current"
		::= { panelboard2 23 }

pb2-CB24-Current
	OBJECT-TYPE
	SYNTAX  INTEGER
	ACCESS  read-only
	STATUS  mandatory
	DESCRIPTION "PB2 CB24 Current"
		::= { panelboard2 24 }

pb2-CB25-Current
	OBJECT-TYPE
	SYNTAX  INTEGER
	ACCESS  read-only
	STATUS  mandatory
	DESCRIPTION "PB2 CB25 Current"
		::= { panelboard2 25 }

pb2-CB26-Current
	OBJECT-TYPE
	SYNTAX  INTEGER
	ACCESS  read-only
	STATUS  mandatory
	DESCRIPTION "PB2 CB26 Current"
		::= { panelboard2 26 }

pb2-CB27-Current
	OBJECT-TYPE
	SYNTAX  INTEGER
	ACCESS  read-only
	STATUS  mandatory
	DESCRIPTION "PB2 CB27 Current"
		::= { panelboard2 27 }

pb2-CB28-Current
	OBJECT-TYPE
	SYNTAX  INTEGER
	ACCESS  read-only
	STATUS  mandatory
	DESCRIPTION "PB2 CB28 Current"
		::= { panelboard2 28 }

pb2-CB29-Current
	OBJECT-TYPE
	SYNTAX  INTEGER
	ACCESS  read-only
	STATUS  mandatory
	DESCRIPTION "PB2 CB29 Current"
		::= { panelboard2 29 }

pb2-CB30-Current
	OBJECT-TYPE
	SYNTAX  INTEGER
	ACCESS  read-only
	STATUS  mandatory
	DESCRIPTION "PB2 CB30 Current"
		::= { panelboard2 30 }

pb2-CB31-Current
	OBJECT-TYPE
	SYNTAX  INTEGER
	ACCESS  read-only
	STATUS  mandatory
	DESCRIPTION "PB2 CB31 Current"
		::= { panelboard2 31 }
  
pb2-CB32-Current
	OBJECT-TYPE
	SYNTAX  INTEGER
	ACCESS  read-only
	STATUS  mandatory
	DESCRIPTION "PB2 CB32 Current"
		::= { panelboard2 32 }

pb2-CB33-Current
	OBJECT-TYPE
	SYNTAX  INTEGER
	ACCESS  read-only
	STATUS  mandatory
	DESCRIPTION "PB2 CB33 Current"
		::= { panelboard2 33 }

pb2-CB34-Current
	OBJECT-TYPE
	SYNTAX  INTEGER
	ACCESS  read-only
	STATUS  mandatory
	DESCRIPTION "PB2 CB34 Current"
		::= { panelboard2 34 }

pb2-CB35-Current
	OBJECT-TYPE
	SYNTAX  INTEGER
	ACCESS  read-only
	STATUS  mandatory
	DESCRIPTION "PB2 CB35 Current"
		::= { panelboard2 35 }

pb2-CB36-Current
	OBJECT-TYPE
	SYNTAX  INTEGER
	ACCESS  read-only
	STATUS  mandatory
	DESCRIPTION "PB2 CB36 Current"
		::= { panelboard2 36 }

pb2-CB37-Current
	OBJECT-TYPE
	SYNTAX  INTEGER
	ACCESS  read-only
	STATUS  mandatory
	DESCRIPTION "PB2 CB37 Current"
		::= { panelboard2 37 }

pb2-CB38-Current
	OBJECT-TYPE
	SYNTAX  INTEGER
	ACCESS  read-only
	STATUS  mandatory
	DESCRIPTION "PB2 CB38 Current"
		::= { panelboard2 38 }

pb2-CB39-Current
	OBJECT-TYPE
	SYNTAX  INTEGER
	ACCESS  read-only
	STATUS  mandatory
	DESCRIPTION "PB2 CB39 Current"
		::= { panelboard2 39 }

pb2-CB40-Current
	OBJECT-TYPE
	SYNTAX  INTEGER
	ACCESS  read-only
	STATUS  mandatory
	DESCRIPTION "PB2 CB40 Current"
		::= { panelboard2 40 }

pb2-CB41-Current
	OBJECT-TYPE
	SYNTAX  INTEGER
	ACCESS  read-only
	STATUS  mandatory
	DESCRIPTION "PB2 CB41 Current"
		::= { panelboard2 41 }
  
pb2-CB42-Current
	OBJECT-TYPE
	SYNTAX  INTEGER
	ACCESS  read-only
	STATUS  mandatory
	DESCRIPTION "PB2 CB42 Current"
		::= { panelboard2 42 }

pb2-CB1-Min
	OBJECT-TYPE
	SYNTAX  INTEGER
	ACCESS  read-only
	STATUS  mandatory
	DESCRIPTION "PB2 CB1 Min
		     Note for all minumum currents 1-42: 100 = 10.0 amps"
		::= { panelboard2 43 }

pb2-CB2-Min
	OBJECT-TYPE
	SYNTAX  INTEGER
	ACCESS  read-only
	STATUS  mandatory
	DESCRIPTION "PB2 CB2 Min"
		::= { panelboard2 44 }

pb2-CB3-Min
	OBJECT-TYPE
	SYNTAX  INTEGER
	ACCESS  read-only
	STATUS  mandatory
	DESCRIPTION "PB2 CB3 Min"
		::= { panelboard2 45 }

pb2-CB4-Min
	OBJECT-TYPE
	SYNTAX  INTEGER
	ACCESS  read-only
	STATUS  mandatory
	DESCRIPTION "PB2 CB4 Min"
		::= { panelboard2 46 }

pb2-CB5-Min
	OBJECT-TYPE
	SYNTAX  INTEGER
	ACCESS  read-only
	STATUS  mandatory
	DESCRIPTION "PB2 CB5 Min"
		::= { panelboard2 47 }

pb2-CB6-Min
	OBJECT-TYPE
	SYNTAX  INTEGER
	ACCESS  read-only
	STATUS  mandatory
	DESCRIPTION "PB2 CB6 Min"
		::= { panelboard2 48 }

pb2-CB7-Min
	OBJECT-TYPE
	SYNTAX  INTEGER
	ACCESS  read-only
	STATUS  mandatory
	DESCRIPTION "PB2 CB7 Min"
		::= { panelboard2 49 }

pb2-CB8-Min
	OBJECT-TYPE
	SYNTAX  INTEGER
	ACCESS  read-only
	STATUS  mandatory
	DESCRIPTION "PB2 CB8 Min"
		::= { panelboard2 50 }

pb2-CB9-Min
	OBJECT-TYPE
	SYNTAX  INTEGER
	ACCESS  read-only
	STATUS  mandatory
	DESCRIPTION "PB2 CB9 Min"
		::= { panelboard2 51 }
  
pb2-CB10-Min
	OBJECT-TYPE
	SYNTAX  INTEGER
	ACCESS  read-only
	STATUS  mandatory
	DESCRIPTION "PB2 CB10 Min"
		::= { panelboard2 52 }

pb2-CB11-Min
	OBJECT-TYPE
	SYNTAX  INTEGER
	ACCESS  read-only
	STATUS  mandatory
	DESCRIPTION "PB2 CB11 Min"
		::= { panelboard2 53 }

pb2-CB12-Min
	OBJECT-TYPE
	SYNTAX  INTEGER
	ACCESS  read-only
	STATUS  mandatory
	DESCRIPTION "PB2 CB12 Min"
		::= { panelboard2 54 }

pb2-CB13-Min
	OBJECT-TYPE
	SYNTAX  INTEGER
	ACCESS  read-only
	STATUS  mandatory
	DESCRIPTION "PB2 CB13 Min"
		::= { panelboard2 55 }

pb2-CB14-Min
	OBJECT-TYPE
	SYNTAX  INTEGER
	ACCESS  read-only
	STATUS  mandatory
	DESCRIPTION "PB2 CB14 Min"
		::= { panelboard2 56 }

pb2-CB15-Min
	OBJECT-TYPE
	SYNTAX  INTEGER
	ACCESS  read-only
	STATUS  mandatory
	DESCRIPTION "PB2 CB15 Min"
		::= { panelboard2 57 }

pb2-CB16-Min
	OBJECT-TYPE
	SYNTAX  INTEGER
	ACCESS  read-only
	STATUS  mandatory
	DESCRIPTION "PB2 CB16 Min"
		::= { panelboard2 58 }

pb2-CB17-Min
	OBJECT-TYPE
	SYNTAX  INTEGER
	ACCESS  read-only
	STATUS  mandatory
	DESCRIPTION "PB2 CB17 Min"
		::= { panelboard2 59 }


pb2-CB18-Min
	OBJECT-TYPE
	SYNTAX  INTEGER
	ACCESS  read-only
	STATUS  mandatory
	DESCRIPTION "PB2 CB18 Min"
		::= { panelboard2 60 }

pb2-CB19-Min
	OBJECT-TYPE
	SYNTAX  INTEGER
	ACCESS  read-only
	STATUS  mandatory
	DESCRIPTION "PB2 CB19 Min"
		::= { panelboard2 61 }
  
pb2-CB20-Min
	OBJECT-TYPE
	SYNTAX  INTEGER
	ACCESS  read-only
	STATUS  mandatory
	DESCRIPTION "PB2 CB20 Min"
		::= { panelboard2 62 }

pb2-CB21-Min
	OBJECT-TYPE
	SYNTAX  INTEGER
	ACCESS  read-only
	STATUS  mandatory
	DESCRIPTION "PB2 CB21 Min"
		::= { panelboard2 63 }

pb2-CB22-Min
	OBJECT-TYPE
	SYNTAX  INTEGER
	ACCESS  read-only
	STATUS  mandatory
	DESCRIPTION "PB2 CB22 Min"
		::= { panelboard2 64 }

pb2-CB23-Min
	OBJECT-TYPE
	SYNTAX  INTEGER
	ACCESS  read-only
	STATUS  mandatory
	DESCRIPTION "PB2 CB23 Min"
		::= { panelboard2 65 }

pb2-CB24-Min
	OBJECT-TYPE
	SYNTAX  INTEGER
	ACCESS  read-only
	STATUS  mandatory
	DESCRIPTION "PB2 CB24 Min"
		::= { panelboard2 66 }

pb2-CB25-Min
	OBJECT-TYPE
	SYNTAX  INTEGER
	ACCESS  read-only
	STATUS  mandatory
	DESCRIPTION "PB2 CB25 Min"
		::= { panelboard2 67 }

pb2-CB26-Min
	OBJECT-TYPE
	SYNTAX  INTEGER
	ACCESS  read-only
	STATUS  mandatory
	DESCRIPTION "PB2 CB26 Min"
		::= { panelboard2 68 }

pb2-CB27-Min
	OBJECT-TYPE
	SYNTAX  INTEGER
	ACCESS  read-only
	STATUS  mandatory
	DESCRIPTION "PB2 CB27 Min"
		::= { panelboard2 69 }

pb2-CB28-Min
	OBJECT-TYPE
	SYNTAX  INTEGER
	ACCESS  read-only
	STATUS  mandatory
	DESCRIPTION "PB2 CB28 Min"
		::= { panelboard2 70 }

pb2-CB29-Min
	OBJECT-TYPE
	SYNTAX  INTEGER
	ACCESS  read-only
	STATUS  mandatory
	DESCRIPTION "PB2 CB29 Min"
		::= { panelboard2 71 }
  
pb2-CB30-Min
	OBJECT-TYPE
	SYNTAX  INTEGER
	ACCESS  read-only
	STATUS  mandatory
	DESCRIPTION "PB2 CB30 Min"
		::= { panelboard2 72 }

pb2-CB31-Min
	OBJECT-TYPE
	SYNTAX  INTEGER
	ACCESS  read-only
	STATUS  mandatory
	DESCRIPTION "PB2 CB31 Min"
		::= { panelboard2 73 }

pb2-CB32-Min
	OBJECT-TYPE
	SYNTAX  INTEGER
	ACCESS  read-only
	STATUS  mandatory
	DESCRIPTION "PB2 CB32 Min"
		::= { panelboard2 74 }

pb2-CB33-Min
	OBJECT-TYPE
	SYNTAX  INTEGER
	ACCESS  read-only
	STATUS  mandatory
	DESCRIPTION "PB2 CB33 Min"
		::= { panelboard2 75 }

pb2-CB34-Min
	OBJECT-TYPE
	SYNTAX  INTEGER
	ACCESS  read-only
	STATUS  mandatory
	DESCRIPTION "PB2 CB34 Min"
		::= { panelboard2 76 }

pb2-CB35-Min
	OBJECT-TYPE
	SYNTAX  INTEGER
	ACCESS  read-only
	STATUS  mandatory
	DESCRIPTION "PB2 CB35 Min"
		::= { panelboard2 77 }

pb2-CB36-Min
	OBJECT-TYPE
	SYNTAX  INTEGER
	ACCESS  read-only
	STATUS  mandatory
	DESCRIPTION "PB2 CB36 Min"
		::= { panelboard2 78 }

pb2-CB37-Min
	OBJECT-TYPE
	SYNTAX  INTEGER
	ACCESS  read-only
	STATUS  mandatory
	DESCRIPTION "PB2 CB37 Min"
		::= { panelboard2 79 }

pb2-CB38-Min
	OBJECT-TYPE
	SYNTAX  INTEGER
	ACCESS  read-only
	STATUS  mandatory
	DESCRIPTION "PB2 CB38 Min"
		::= { panelboard2 80 }

pb2-CB39-Min
	OBJECT-TYPE
	SYNTAX  INTEGER
	ACCESS  read-only
	STATUS  mandatory
	DESCRIPTION "PB2 CB39 Min"
		::= { panelboard2 81 }
  
pb2-CB40-Min
	OBJECT-TYPE
	SYNTAX  INTEGER
	ACCESS  read-only
	STATUS  mandatory
	DESCRIPTION "PB2 CB40 Min"
		::= { panelboard2 82 }

pb2-CB41-Min
	OBJECT-TYPE
	SYNTAX  INTEGER
	ACCESS  read-only
	STATUS  mandatory
	DESCRIPTION "PB2 CB41 Min"
		::= { panelboard2 83 }

pb2-CB42-Min
	OBJECT-TYPE
	SYNTAX  INTEGER
	ACCESS  read-only
	STATUS  mandatory
	DESCRIPTION "PB2 CB42 Min"
		::= { panelboard2 84 }

pb2-CB1-Max
	OBJECT-TYPE
	SYNTAX  INTEGER
	ACCESS  read-only
	STATUS  mandatory
	DESCRIPTION "PB2 CB1 Max
		     Note for all maximum currents 1-42: 100 = 10.0 amps"
		::= { panelboard2 85 }

pb2-CB2-Max
	OBJECT-TYPE
	SYNTAX  INTEGER
	ACCESS  read-only
	STATUS  mandatory
	DESCRIPTION "PB2 CB2 Max"
		::= { panelboard2 86 }

pb2-CB3-Max
	OBJECT-TYPE
	SYNTAX  INTEGER
	ACCESS  read-only
	STATUS  mandatory
	DESCRIPTION "PB2 CB3 Max"
		::= { panelboard2 87 }

pb2-CB4-Max
	OBJECT-TYPE
	SYNTAX  INTEGER
	ACCESS  read-only
	STATUS  mandatory
	DESCRIPTION "PB2 CB4 Max"
		::= { panelboard2 88 }

pb2-CB5-Max
	OBJECT-TYPE
	SYNTAX  INTEGER
	ACCESS  read-only
	STATUS  mandatory
	DESCRIPTION "PB2 CB5 Max"
		::= { panelboard2 89 }

pb2-CB6-Max
	OBJECT-TYPE
	SYNTAX  INTEGER
	ACCESS  read-only
	STATUS  mandatory
	DESCRIPTION "PB2 CB6 Max"
		::= { panelboard2 90 }

pb2-CB7-Max
	OBJECT-TYPE
	SYNTAX  INTEGER
	ACCESS  read-only
	STATUS  mandatory
	DESCRIPTION "PB2 CB7 Max"
		::= { panelboard2 91 }
  
pb2-CB8-Max
	OBJECT-TYPE
	SYNTAX  INTEGER
	ACCESS  read-only
	STATUS  mandatory
	DESCRIPTION "PB2 CB8 Max"
		::= { panelboard2 92 }

pb2-CB9-Max
	OBJECT-TYPE
	SYNTAX  INTEGER
	ACCESS  read-only
	STATUS  mandatory
	DESCRIPTION "PB2 CB9 Max"
		::= { panelboard2 93 }

pb2-CB10-Max
	OBJECT-TYPE
	SYNTAX  INTEGER
	ACCESS  read-only
	STATUS  mandatory
	DESCRIPTION "PB2 CB10 Max"
		::= { panelboard2 94 }

pb2-CB11-Max
	OBJECT-TYPE
	SYNTAX  INTEGER
	ACCESS  read-only
	STATUS  mandatory
	DESCRIPTION "PB2 CB11 Max"
		::= { panelboard2 95 }

pb2-CB12-Max
	OBJECT-TYPE
	SYNTAX  INTEGER
	ACCESS  read-only
	STATUS  mandatory
	DESCRIPTION "PB2 CB12 Max"
		::= { panelboard2 96 }

pb2-CB13-Max
	OBJECT-TYPE
	SYNTAX  INTEGER
	ACCESS  read-only
	STATUS  mandatory
	DESCRIPTION "PB2 CB13 Max"
		::= { panelboard2 97 }

pb2-CB14-Max
	OBJECT-TYPE
	SYNTAX  INTEGER
	ACCESS  read-only
	STATUS  mandatory
	DESCRIPTION "PB2 CB14 Max"
		::= { panelboard2 98 }

pb2-CB15-Max
	OBJECT-TYPE
	SYNTAX  INTEGER
	ACCESS  read-only
	STATUS  mandatory
	DESCRIPTION "PB2 CB15 Max"
		::= { panelboard2 99 }


pb2-CB16-Max
	OBJECT-TYPE
	SYNTAX  INTEGER
	ACCESS  read-only
	STATUS  mandatory
	DESCRIPTION "PB2 CB16 Max"
		::= { panelboard2 100 }

pb2-CB17-Max
	OBJECT-TYPE
	SYNTAX  INTEGER
	ACCESS  read-only
	STATUS  mandatory
	DESCRIPTION "PB2 CB17 Max"
		::= { panelboard2 101 }
  
pb2-CB18-Max
	OBJECT-TYPE
	SYNTAX  INTEGER
	ACCESS  read-only
	STATUS  mandatory
	DESCRIPTION "PB2 CB18 Max"
		::= { panelboard2 102 }

pb2-CB19-Max
	OBJECT-TYPE
	SYNTAX  INTEGER
	ACCESS  read-only
	STATUS  mandatory
	DESCRIPTION "PB2 CB19 Max"
		::= { panelboard2 103 }

pb2-CB20-Max
	OBJECT-TYPE
	SYNTAX  INTEGER
	ACCESS  read-only
	STATUS  mandatory
	DESCRIPTION "PB2 CB20 Max"
		::= { panelboard2 104 }

pb2-CB21-Max
	OBJECT-TYPE
	SYNTAX  INTEGER
	ACCESS  read-only
	STATUS  mandatory
	DESCRIPTION "PB2 CB21 Max"
		::= { panelboard2 105 }

pb2-CB22-Max
	OBJECT-TYPE
	SYNTAX  INTEGER
	ACCESS  read-only
	STATUS  mandatory
	DESCRIPTION "PB2 CB22 Max"
		::= { panelboard2 106 }

pb2-CB23-Max
	OBJECT-TYPE
	SYNTAX  INTEGER
	ACCESS  read-only
	STATUS  mandatory
	DESCRIPTION "PB2 CB23 Max"
		::= { panelboard2 107 }

pb2-CB24-Max
	OBJECT-TYPE
	SYNTAX  INTEGER
	ACCESS  read-only
	STATUS  mandatory
	DESCRIPTION "PB2 CB24 Max"
		::= { panelboard2 108 }

pb2-CB25-Max
	OBJECT-TYPE
	SYNTAX  INTEGER
	ACCESS  read-only
	STATUS  mandatory
	DESCRIPTION "PB2 CB25 Max"
		::= { panelboard2 109 }

pb2-CB26-Max
	OBJECT-TYPE
	SYNTAX  INTEGER
	ACCESS  read-only
	STATUS  mandatory
	DESCRIPTION "PB2 CB26 Max"
		::= { panelboard2 110 }

pb2-CB27-Max
	OBJECT-TYPE
	SYNTAX  INTEGER
	ACCESS  read-only
	STATUS  mandatory
	DESCRIPTION "PB2 CB27 Max"
		::= { panelboard2 111 }
  
pb2-CB28-Max
	OBJECT-TYPE
	SYNTAX  INTEGER
	ACCESS  read-only
	STATUS  mandatory
	DESCRIPTION "PB2 CB28 Max"
		::= { panelboard2 112 }

pb2-CB29-Max
	OBJECT-TYPE
	SYNTAX  INTEGER
	ACCESS  read-only
	STATUS  mandatory
	DESCRIPTION "PB2 CB29 Max"
		::= { panelboard2 113 }

pb2-CB30-Max
	OBJECT-TYPE
	SYNTAX  INTEGER
	ACCESS  read-only
	STATUS  mandatory
	DESCRIPTION "PB2 CB30 Max"
		::= { panelboard2 114 }

pb2-CB31-Max
	OBJECT-TYPE
	SYNTAX  INTEGER
	ACCESS  read-only
	STATUS  mandatory
	DESCRIPTION "PB2 CB31 Max"
		::= { panelboard2 115 }

pb2-CB32-Max
	OBJECT-TYPE
	SYNTAX  INTEGER
	ACCESS  read-only
	STATUS  mandatory
	DESCRIPTION "PB2 CB32 Max"
		::= { panelboard2 116 }

pb2-CB33-Max
	OBJECT-TYPE
	SYNTAX  INTEGER
	ACCESS  read-only
	STATUS  mandatory
	DESCRIPTION "PB2 CB33 Max"
		::= { panelboard2 117 }

pb2-CB34-Max
	OBJECT-TYPE
	SYNTAX  INTEGER
	ACCESS  read-only
	STATUS  mandatory
	DESCRIPTION "PB2 CB34 Max"
		::= { panelboard2 118 }

pb2-CB35-Max
	OBJECT-TYPE
	SYNTAX  INTEGER
	ACCESS  read-only
	STATUS  mandatory
	DESCRIPTION "PB2 CB35 Max"
		::= { panelboard2 119 }

pb2-CB36-Max
	OBJECT-TYPE
	SYNTAX  INTEGER
	ACCESS  read-only
	STATUS  mandatory
	DESCRIPTION "PB2 CB36 Max"
		::= { panelboard2 120 }

pb2-CB37-Max
	OBJECT-TYPE
	SYNTAX  INTEGER
	ACCESS  read-only
	STATUS  mandatory
	DESCRIPTION "PB2 CB37 Max"
		::= { panelboard2 121 }
  
pb2-CB38-Max
	OBJECT-TYPE
	SYNTAX  INTEGER
	ACCESS  read-only
	STATUS  mandatory
	DESCRIPTION "PB2 CB38 Max"
		::= { panelboard2 122 }

pb2-CB39-Max
	OBJECT-TYPE
	SYNTAX  INTEGER
	ACCESS  read-only
	STATUS  mandatory
	DESCRIPTION "PB2 CB39 Max"
		::= { panelboard2 123 }

pb2-CB40-Max
	OBJECT-TYPE
	SYNTAX  INTEGER
	ACCESS  read-only
	STATUS  mandatory
	DESCRIPTION "PB2 CB40 Max"
		::= { panelboard2 124 }

pb2-CB41-Max
	OBJECT-TYPE
	SYNTAX  INTEGER
	ACCESS  read-only
	STATUS  mandatory
	DESCRIPTION "PB2 CB41 Max"
		::= { panelboard2 125 }

pb2-CB42-Max
	OBJECT-TYPE
	SYNTAX  INTEGER
	ACCESS  read-only
	STATUS  mandatory
	DESCRIPTION "PB2 CB42 Max"
		::= { panelboard2 126 }

pb2-CB1-16-Zero
	OBJECT-TYPE
	SYNTAX  INTEGER
	ACCESS  read-write
	STATUS  mandatory
	DESCRIPTION "PB2 CB1-16 Zero
		     Bit 0 = CB1
                     Bit 15 = CB16"
		::= { panelboard2 127 }

pb2-CB17-32-Zero
	OBJECT-TYPE
	SYNTAX  INTEGER
	ACCESS  read-write
	STATUS  mandatory
	DESCRIPTION "PB2 CB17-32 Zero
		     Bit 0 = CB17
                     Bit 15 = CB32"
		     
		::= { panelboard2 128 }

pb2-CB33-42-Zero
	OBJECT-TYPE
	SYNTAX  INTEGER
	ACCESS  read-write
	STATUS  mandatory
	DESCRIPTION "PB2 CB33-42 Zero
		     Bit 0 = CB33
                     Bit 9 = CB42
                     Bits 10-25 not used"
		::= { panelboard2 129 }

pb2-CB1-16-Warning
	OBJECT-TYPE
	SYNTAX  INTEGER
	ACCESS  read-write
	STATUS  mandatory
	DESCRIPTION "PB2 CB1-16 Warning
		     Bit 0 = CB1
                     Bit 15 = CB16"
		::= { panelboard2 130 }

pb2-CB17-32-Warning
	OBJECT-TYPE
	SYNTAX  INTEGER
	ACCESS  read-write
	STATUS  mandatory
	DESCRIPTION "PB2 CB17-32 Warning
		     Bit 0 = CB17
                     Bit 15 = CB32"
		::= { panelboard2 131 }
  
pb2-CB33-42-Warning
	OBJECT-TYPE
	SYNTAX  INTEGER
	ACCESS  read-write
	STATUS  mandatory
	DESCRIPTION "PB2 CB33-42 Warning
		     Bit 0 = CB33
                     Bit 9 = CB42
                     Bits 10-25 not used"
		::= { panelboard2 132 }

pb2-CB1-16-Alarm
	OBJECT-TYPE
	SYNTAX  INTEGER
	ACCESS  read-write
	STATUS  mandatory
	DESCRIPTION "PB2 CB1-16 Alarm
		     Bit 0 = CB1
                     Bit 15 = CB16"
		::= { panelboard2 133 }

pb2-CB17-32-Alarm
	OBJECT-TYPE
	SYNTAX  INTEGER
	ACCESS  read-write
	STATUS  mandatory
	DESCRIPTION "PB2 CB17-32 Alarm
		     Bit 0 = CB17
                     Bit 15 = CB32"
		::= { panelboard2 134 }

pb2-CB33-42-Alarm
	OBJECT-TYPE
	SYNTAX  INTEGER
	ACCESS  read-write
	STATUS  mandatory
	DESCRIPTION "PB2 CB33-42 Alarm
		     Bit 0 = CB33
                     Bit 9 = CB42
                     Bits 10-25 not used"
		::= { panelboard2 135 }

pb2-CB1-Breaker-Size
	OBJECT-TYPE
	SYNTAX  INTEGER
	ACCESS  read-write
	STATUS  mandatory
	DESCRIPTION "PB2 CB1 Breaker-Size
		     Note for all breaker sizes 1-42: 10 = 10 amps
                     Range is 10 to 100 amps"
		::= { panelboard2 136 }

pb2-CB2-Breaker-Size
	OBJECT-TYPE
	SYNTAX  INTEGER
	ACCESS  read-write
	STATUS  mandatory
	DESCRIPTION "PB2 CB2 Breaker-Size"
		::= { panelboard2 137 }

pb2-CB3-Breaker-Size
	OBJECT-TYPE
	SYNTAX  INTEGER
	ACCESS  read-write
	STATUS  mandatory
	DESCRIPTION "PB2 CB3 Breaker-Size"
		::= { panelboard2 138 }

pb2-CB4-Breaker-Size
	OBJECT-TYPE
	SYNTAX  INTEGER
	ACCESS  read-write
	STATUS  mandatory
	DESCRIPTION "PB2 CB4 Breaker-Size"
		::= { panelboard2 139 }

pb2-CB5-Breaker-Size
	OBJECT-TYPE
	SYNTAX  INTEGER
	ACCESS  read-write
	STATUS  mandatory
	DESCRIPTION "PB2 CB5 Breaker-Size"
		::= { panelboard2 140 }

pb2-CB6-Breaker-Size
	OBJECT-TYPE
	SYNTAX  INTEGER
	ACCESS  read-write
	STATUS  mandatory
	DESCRIPTION "PB2 CB6 Breaker-Size"
		::= { panelboard2 141 }
  
pb2-CB7-Breaker-Size
	OBJECT-TYPE
	SYNTAX  INTEGER
	ACCESS  read-write
	STATUS  mandatory
	DESCRIPTION "PB2 CB7 Breaker-Size"
		::= { panelboard2 142 }

pb2-CB8-Breaker-Size
	OBJECT-TYPE
	SYNTAX  INTEGER
	ACCESS  read-write
	STATUS  mandatory
	DESCRIPTION "PB2 CB8 Breaker-Size"
		::= { panelboard2 143 }

pb2-CB9-Breaker-Size
	OBJECT-TYPE
	SYNTAX  INTEGER
	ACCESS  read-write
	STATUS  mandatory
	DESCRIPTION "PB2 CB9 Breaker-Size"
		::= { panelboard2 144 }

pb2-CB10-Breaker-Size
	OBJECT-TYPE
	SYNTAX  INTEGER
	ACCESS  read-write
	STATUS  mandatory
	DESCRIPTION "PB2 CB10 Breaker-Size"
		::= { panelboard2 145 }

pb2-CB11-Breaker-Size
	OBJECT-TYPE
	SYNTAX  INTEGER
	ACCESS  read-write
	STATUS  mandatory
	DESCRIPTION "PB2 CB11 Breaker-Size"
		::= { panelboard2 146 }

pb2-CB12-Breaker-Size
	OBJECT-TYPE
	SYNTAX  INTEGER
	ACCESS  read-write
	STATUS  mandatory
	DESCRIPTION "PB2 CB12 Breaker-Size"
		::= { panelboard2 147 }

pb2-CB13-Breaker-Size
	OBJECT-TYPE
	SYNTAX  INTEGER
	ACCESS  read-write
	STATUS  mandatory
	DESCRIPTION "PB2 CB13 Breaker-Size"
		::= { panelboard2 148 }

pb2-CB14-Breaker-Size
	OBJECT-TYPE
	SYNTAX  INTEGER
	ACCESS  read-write
	STATUS  mandatory
	DESCRIPTION "PB2 CB14 Breaker-Size"
		::= { panelboard2 149 }

pb2-CB15-Breaker-Size
	OBJECT-TYPE
	SYNTAX  INTEGER
	ACCESS  read-write
	STATUS  mandatory
	DESCRIPTION "PB2 CB15 Breaker-Size"
		::= { panelboard2 150 }

pb2-CB16-Breaker-Size
	OBJECT-TYPE
	SYNTAX  INTEGER
	ACCESS  read-write
	STATUS  mandatory
	DESCRIPTION "PB2 CB16 Breaker-Size"
		::= { panelboard2 151 }
  
pb2-CB17-Breaker-Size
	OBJECT-TYPE
	SYNTAX  INTEGER
	ACCESS  read-write
	STATUS  mandatory
	DESCRIPTION "PB2 CB17 Breaker-Size"
		::= { panelboard2 152 }

pb2-CB18-Breaker-Size
	OBJECT-TYPE
	SYNTAX  INTEGER
	ACCESS  read-write
	STATUS  mandatory
	DESCRIPTION "PB2 CB18 Breaker-Size"
		::= { panelboard2 153 }

pb2-CB19-Breaker-Size
	OBJECT-TYPE
	SYNTAX  INTEGER
	ACCESS  read-write
	STATUS  mandatory
	DESCRIPTION "PB2 CB19 Breaker-Size"
		::= { panelboard2 154 }

pb2-CB20-Breaker-Size
	OBJECT-TYPE
	SYNTAX  INTEGER
	ACCESS  read-write
	STATUS  mandatory
	DESCRIPTION "PB2 CB20 Breaker-Size"
		::= { panelboard2 155 }

pb2-CB21-Breaker-Size
	OBJECT-TYPE
	SYNTAX  INTEGER
	ACCESS  read-write
	STATUS  mandatory
	DESCRIPTION "PB2 CB21 Breaker-Size"
		::= { panelboard2 156 }

pb2-CB22-Breaker-Size
	OBJECT-TYPE
	SYNTAX  INTEGER
	ACCESS  read-write
	STATUS  mandatory
	DESCRIPTION "PB2 CB22 Breaker-Size"
		::= { panelboard2 157 }

pb2-CB23-Breaker-Size
	OBJECT-TYPE
	SYNTAX  INTEGER
	ACCESS  read-write
	STATUS  mandatory
	DESCRIPTION "PB2 CB23 Breaker-Size"
		::= { panelboard2 158 }

pb2-CB24-Breaker-Size
	OBJECT-TYPE
	SYNTAX  INTEGER
	ACCESS  read-write
	STATUS  mandatory
	DESCRIPTION "PB2 CB24 Breaker-Size"
		::= { panelboard2 159 }

pb2-CB25-Breaker-Size
	OBJECT-TYPE
	SYNTAX  INTEGER
	ACCESS  read-write
	STATUS  mandatory
	DESCRIPTION "PB2 CB25 Breaker-Size"
		::= { panelboard2 160 }

pb2-CB26-Breaker-Size
	OBJECT-TYPE
	SYNTAX  INTEGER
	ACCESS  read-write
	STATUS  mandatory
	DESCRIPTION "PB2 CB26 Breaker-Size"
		::= { panelboard2 161 }
  
pb2-CB27-Breaker-Size
	OBJECT-TYPE
	SYNTAX  INTEGER
	ACCESS  read-write
	STATUS  mandatory
	DESCRIPTION "PB2 CB27 Breaker-Size"
		::= { panelboard2 162 }

pb2-CB28-Breaker-Size
	OBJECT-TYPE
	SYNTAX  INTEGER
	ACCESS  read-write
	STATUS  mandatory
	DESCRIPTION "PB2 CB28 Breaker-Size"
		::= { panelboard2 163 }

pb2-CB29-Breaker-Size
	OBJECT-TYPE
	SYNTAX  INTEGER
	ACCESS  read-write
	STATUS  mandatory
	DESCRIPTION "PB2 CB29 Breaker-Size"
		::= { panelboard2 164 }

pb2-CB30-Breaker-Size
	OBJECT-TYPE
	SYNTAX  INTEGER
	ACCESS  read-write
	STATUS  mandatory
	DESCRIPTION "PB2 CB30 Breaker-Size"
		::= { panelboard2 165 }

pb2-CB31-Breaker-Size
	OBJECT-TYPE
	SYNTAX  INTEGER
	ACCESS  read-write
	STATUS  mandatory
	DESCRIPTION "PB2 CB31 Breaker-Size"
		::= { panelboard2 166 }

pb2-CB32-Breaker-Size
	OBJECT-TYPE
	SYNTAX  INTEGER
	ACCESS  read-write
	STATUS  mandatory
	DESCRIPTION "PB2 CB32 Breaker-Size"
		::= { panelboard2 167 }

pb2-CB33-Breaker-Size
	OBJECT-TYPE
	SYNTAX  INTEGER
	ACCESS  read-write
	STATUS  mandatory
	DESCRIPTION "PB2 CB33 Breaker-Size"
		::= { panelboard2 168 }

pb2-CB34-Breaker-Size
	OBJECT-TYPE
	SYNTAX  INTEGER
	ACCESS  read-write
	STATUS  mandatory
	DESCRIPTION "PB2 CB34 Breaker-Size"
		::= { panelboard2 169 }

pb2-CB35-Breaker-Size
	OBJECT-TYPE
	SYNTAX  INTEGER
	ACCESS  read-write
	STATUS  mandatory
	DESCRIPTION "PB2 CB35 Breaker-Size"
		::= { panelboard2 170 }

pb2-CB36-Breaker-Size
	OBJECT-TYPE
	SYNTAX  INTEGER
	ACCESS  read-write
	STATUS  mandatory
	DESCRIPTION "PB2 CB36 Breaker-Size"
		::= { panelboard2 171 }
  
pb2-CB37-Breaker-Size
	OBJECT-TYPE
	SYNTAX  INTEGER
	ACCESS  read-write
	STATUS  mandatory
	DESCRIPTION "PB2 CB37 Breaker-Size"
		::= { panelboard2 172 }

pb2-CB38-Breaker-Size
	OBJECT-TYPE
	SYNTAX  INTEGER
	ACCESS  read-write
	STATUS  mandatory
	DESCRIPTION "PB2 CB38 Breaker-Size"
		::= { panelboard2 173 }

pb2-CB39-Breaker-Size
	OBJECT-TYPE
	SYNTAX  INTEGER
	ACCESS  read-write
	STATUS  mandatory
	DESCRIPTION "PB2 CB39 Breaker-Size"
		::= { panelboard2 174 }

pb2-CB40-Breaker-Size
	OBJECT-TYPE
	SYNTAX  INTEGER
	ACCESS  read-write
	STATUS  mandatory
	DESCRIPTION "PB2 CB40 Breaker-Size"
		::= { panelboard2 175 }

pb2-CB41-Breaker-Size
	OBJECT-TYPE
	SYNTAX  INTEGER
	ACCESS  read-write
	STATUS  mandatory
	DESCRIPTION "PB2 CB41 Breaker-Size"
		::= { panelboard2 176 }

pb2-CB42-Breaker-Size
	OBJECT-TYPE
	SYNTAX  INTEGER
	ACCESS  read-write
	STATUS  mandatory
	DESCRIPTION "PB2 CB42 Breaker-Size"
		::= { panelboard2 177 }

pb2-CB1-Warning-Threshold
	OBJECT-TYPE
	SYNTAX  INTEGER
	ACCESS  read-write
	STATUS  mandatory
	DESCRIPTION "PB2 CB1 CB1-Warning-Threshold
		     Note for all warning thresholds 1-42: 70 = 70% of breaker size
                     range is 0-100%"
		::= { panelboard2 178 }

pb2-CB2-Warning-Threshold
	OBJECT-TYPE
	SYNTAX  INTEGER
	ACCESS  read-write
	STATUS  mandatory
	DESCRIPTION "PB2 CB2 Warning-Threshold"
		::= { panelboard2 179 }

pb2-CB3-Warning-Threshold
	OBJECT-TYPE
	SYNTAX  INTEGER
	ACCESS  read-write
	STATUS  mandatory
	DESCRIPTION "PB2 CB3 Warning-Threshold"
		::= { panelboard2 180 }

pb2-CB4-Warning-Threshold
	OBJECT-TYPE
	SYNTAX  INTEGER
	ACCESS  read-write
	STATUS  mandatory
	DESCRIPTION "PB2 CB4 Warning-Threshold"
		::= { panelboard2 181 }
  
pb2-CB5-Warning-Threshold
	OBJECT-TYPE
	SYNTAX  INTEGER
	ACCESS  read-write
	STATUS  mandatory
	DESCRIPTION "PB2 CB5 Warning-Threshold"
		::= { panelboard2 182 }

pb2-CB6-Warning-Threshold
	OBJECT-TYPE
	SYNTAX  INTEGER
	ACCESS  read-write
	STATUS  mandatory
	DESCRIPTION "PB2 CB6 Warning-Threshold"
		::= { panelboard2 183 }

pb2-CB7-Warning-Threshold
	OBJECT-TYPE
	SYNTAX  INTEGER
	ACCESS  read-write
	STATUS  mandatory
	DESCRIPTION "PB2 CB7 Warning-Threshold"
		::= { panelboard2 184 }

pb2-CB8-Warning-Threshold
	OBJECT-TYPE
	SYNTAX  INTEGER
	ACCESS  read-write
	STATUS  mandatory
	DESCRIPTION "PB2 CB8 Warning-Threshold"
		::= { panelboard2 185 }

pb2-CB9-Warning-Threshold
	OBJECT-TYPE
	SYNTAX  INTEGER
	ACCESS  read-write
	STATUS  mandatory
	DESCRIPTION "PB2 CB9 Warning-Threshold"
		::= { panelboard2 186 }

pb2-CB10-Warning-Threshold
	OBJECT-TYPE
	SYNTAX  INTEGER
	ACCESS  read-write
	STATUS  mandatory
	DESCRIPTION "PB2 CB10 Warning-Threshold"
		::= { panelboard2 187 }

pb2-CB11-Warning-Threshold
	OBJECT-TYPE
	SYNTAX  INTEGER
	ACCESS  read-write
	STATUS  mandatory
	DESCRIPTION "PB2 CB11 Warning-Threshold"
		::= { panelboard2 188 }

pb2-CB12-Warning-Threshold
	OBJECT-TYPE
	SYNTAX  INTEGER
	ACCESS  read-write
	STATUS  mandatory
	DESCRIPTION "PB2 CB12 Warning-Threshold"
		::= { panelboard2 189 }

pb2-CB13-Warning-Threshold
	OBJECT-TYPE
	SYNTAX  INTEGER
	ACCESS  read-write
	STATUS  mandatory
	DESCRIPTION "PB2 CB13 Warning-Threshold"
		::= { panelboard2 190 }

pb2-CB14-Warning-Threshold
	OBJECT-TYPE
	SYNTAX  INTEGER
	ACCESS  read-write
	STATUS  mandatory
	DESCRIPTION "PB2 CB14 Warning-Threshold"
		::= { panelboard2 191 }
  
pb2-CB15-Warning-Threshold
	OBJECT-TYPE
	SYNTAX  INTEGER
	ACCESS  read-write
	STATUS  mandatory
	DESCRIPTION "PB2 CB15 Warning-Threshold"
		::= { panelboard2 192 }

pb2-CB16-Warning-Threshold
	OBJECT-TYPE
	SYNTAX  INTEGER
	ACCESS  read-write
	STATUS  mandatory
	DESCRIPTION "PB2 CB16 Warning-Threshold"
		::= { panelboard2 193 }

pb2-CB17-Warning-Threshold
	OBJECT-TYPE
	SYNTAX  INTEGER
	ACCESS  read-write
	STATUS  mandatory
	DESCRIPTION "PB2 CB17 Warning-Threshold"
		::= { panelboard2 194 }

pb2-CB18-Warning-Threshold
	OBJECT-TYPE
	SYNTAX  INTEGER
	ACCESS  read-write
	STATUS  mandatory
	DESCRIPTION "PB2 CB18 Warning-Threshold"
		::= { panelboard2 195 }

pb2-CB19-Warning-Threshold
	OBJECT-TYPE
	SYNTAX  INTEGER
	ACCESS  read-write
	STATUS  mandatory
	DESCRIPTION "PB2 CB19 Warning-Threshold"
		::= { panelboard2 196 }

pb2-CB20-Warning-Threshold
	OBJECT-TYPE
	SYNTAX  INTEGER
	ACCESS  read-write
	STATUS  mandatory
	DESCRIPTION "PB2 CB20 Warning-Threshold"
		::= { panelboard2 197 }

pb2-CB21-Warning-Threshold
	OBJECT-TYPE
	SYNTAX  INTEGER
	ACCESS  read-write
	STATUS  mandatory
	DESCRIPTION "PB2 CB21 Warning-Threshold"
		::= { panelboard2 198 }

pb2-CB22-Warning-Threshold
	OBJECT-TYPE
	SYNTAX  INTEGER
	ACCESS  read-write
	STATUS  mandatory
	DESCRIPTION "PB2 CB22 Warning-Threshold"
		::= { panelboard2 199 }

pb2-CB23-Warning-Threshold
	OBJECT-TYPE
	SYNTAX  INTEGER
	ACCESS  read-write
	STATUS  mandatory
	DESCRIPTION "PB2 CB23 Warning-Threshold"
		::= { panelboard2 200 }

pb2-CB24-Warning-Threshold
	OBJECT-TYPE
	SYNTAX  INTEGER
	ACCESS  read-write
	STATUS  mandatory
	DESCRIPTION "PB2 CB24 Warning-Threshold"
		::= { panelboard2 201 }
  
pb2-CB25-Warning-Threshold
	OBJECT-TYPE
	SYNTAX  INTEGER
	ACCESS  read-write
	STATUS  mandatory
	DESCRIPTION "PB2 CB25 Warning-Threshold"
		::= { panelboard2 202 }

pb2-CB26-Warning-Threshold
	OBJECT-TYPE
	SYNTAX  INTEGER
	ACCESS  read-write
	STATUS  mandatory
	DESCRIPTION "PB2 CB26 Warning-Threshold"
		::= { panelboard2 203 }

pb2-CB27-Warning-Threshold
	OBJECT-TYPE
	SYNTAX  INTEGER
	ACCESS  read-write
	STATUS  mandatory
	DESCRIPTION "PB2 CB27 Warning-Threshold"
		::= { panelboard2 204 }

pb2-CB28-Warning-Threshold
	OBJECT-TYPE
	SYNTAX  INTEGER
	ACCESS  read-write
	STATUS  mandatory
	DESCRIPTION "PB2 CB28 Warning-Threshold"
		::= { panelboard2 205 }

pb2-CB29-Warning-Threshold
	OBJECT-TYPE
	SYNTAX  INTEGER
	ACCESS  read-write
	STATUS  mandatory
	DESCRIPTION "PB2 CB29 Warning-Threshold"
		::= { panelboard2 206 }

pb2-CB30-Warning-Threshold
	OBJECT-TYPE
	SYNTAX  INTEGER
	ACCESS  read-write
	STATUS  mandatory
	DESCRIPTION "PB2 CB30 Warning-Threshold"
		::= { panelboard2 207 }

pb2-CB31-Warning-Threshold
	OBJECT-TYPE
	SYNTAX  INTEGER
	ACCESS  read-write
	STATUS  mandatory
	DESCRIPTION "PB2 CB31 Warning-Threshold"
		::= { panelboard2 208 }

pb2-CB32-Warning-Threshold
	OBJECT-TYPE
	SYNTAX  INTEGER
	ACCESS  read-write
	STATUS  mandatory
	DESCRIPTION "PB2 CB32 Warning-Threshold"
		::= { panelboard2 209 }

pb2-CB33-Warning-Threshold
	OBJECT-TYPE
	SYNTAX  INTEGER
	ACCESS  read-write
	STATUS  mandatory
	DESCRIPTION "PB2 CB33 Warning-Threshold"
		::= { panelboard2 210 }

pb2-CB34-Warning-Threshold
	OBJECT-TYPE
	SYNTAX  INTEGER
	ACCESS  read-write
	STATUS  mandatory
	DESCRIPTION "PB2 CB34 Warning-Threshold"
		::= { panelboard2 211 }
  
pb2-CB35-Warning-Threshold
	OBJECT-TYPE
	SYNTAX  INTEGER
	ACCESS  read-write
	STATUS  mandatory
	DESCRIPTION "PB2 CB35 Warning-Threshold"
		::= { panelboard2 212 }

pb2-CB36-Warning-Threshold
	OBJECT-TYPE
	SYNTAX  INTEGER
	ACCESS  read-write
	STATUS  mandatory
	DESCRIPTION "PB2 CB36 Warning-Threshold"
		::= { panelboard2 213 }

pb2-CB37-Warning-Threshold
	OBJECT-TYPE
	SYNTAX  INTEGER
	ACCESS  read-write
	STATUS  mandatory
	DESCRIPTION "PB2 CB37 Warning-Threshold"
		::= { panelboard2 214 }

pb2-CB38-Warning-Threshold
	OBJECT-TYPE
	SYNTAX  INTEGER
	ACCESS  read-write
	STATUS  mandatory
	DESCRIPTION "PB2 CB38 Warning-Threshold"
		::= { panelboard2 215 }

pb2-CB39-Warning-Threshold
	OBJECT-TYPE
	SYNTAX  INTEGER
	ACCESS  read-write
	STATUS  mandatory
	DESCRIPTION "PB2 CB39 Warning-Threshold"
		::= { panelboard2 216 }

pb2-CB40-Warning-Threshold
	OBJECT-TYPE
	SYNTAX  INTEGER
	ACCESS  read-write
	STATUS  mandatory
	DESCRIPTION "PB2 CB40 Warning-Threshold"
		::= { panelboard2 217 }

pb2-CB41-Warning-Threshold
	OBJECT-TYPE
	SYNTAX  INTEGER
	ACCESS  read-write
	STATUS  mandatory
	DESCRIPTION "PB2 CB41 Warning-Threshold"
		::= { panelboard2 218 }

pb2-CB42-Warning-Threshold
	OBJECT-TYPE
	SYNTAX  INTEGER
	ACCESS  read-write
	STATUS  mandatory
	DESCRIPTION "PB2 CB42 Warning-Threshold"
		::= { panelboard2 219 }

pb2-CB1-Alarm-Threshold
	OBJECT-TYPE
	SYNTAX  INTEGER
	ACCESS  read-write
	STATUS  mandatory
	DESCRIPTION "PB2 CB1 Alarm-Threshold
		     Note for all alarm thresholds 1-42: 80 = 80% of breaker size
                     range is 0-100%"
		::= { panelboard2 220 }


pb2-CB2-Alarm-Threshold
	OBJECT-TYPE
	SYNTAX  INTEGER
	ACCESS  read-write
	STATUS  mandatory
	DESCRIPTION "PB2 CB2 Alarm-Threshold"
		::= { panelboard2 221 }
  
pb2-CB3-Alarm-Threshold
	OBJECT-TYPE
	SYNTAX  INTEGER
	ACCESS  read-write
	STATUS  mandatory
	DESCRIPTION "PB2 CB3 Alarm-Threshold"
		::= { panelboard2 222 }

pb2-CB4-Alarm-Threshold
	OBJECT-TYPE
	SYNTAX  INTEGER
	ACCESS  read-write
	STATUS  mandatory
	DESCRIPTION "PB2 CB4 Alarm-Threshold"
		::= { panelboard2 223 }

pb2-CB5-Alarm-Threshold
	OBJECT-TYPE
	SYNTAX  INTEGER
	ACCESS  read-write
	STATUS  mandatory
	DESCRIPTION "PB2 CB5 Alarm-Threshold"
		::= { panelboard2 224 }

pb2-CB6-Alarm-Threshold
	OBJECT-TYPE
	SYNTAX  INTEGER
	ACCESS  read-write
	STATUS  mandatory
	DESCRIPTION "PB2 CB6 Alarm-Threshold"
		::= { panelboard2 225 }

pb2-CB7-Alarm-Threshold
	OBJECT-TYPE
	SYNTAX  INTEGER
	ACCESS  read-write
	STATUS  mandatory
	DESCRIPTION "PB2 CB7 Alarm-Threshold"
		::= { panelboard2 226 }

pb2-CB8-Alarm-Threshold
	OBJECT-TYPE
	SYNTAX  INTEGER
	ACCESS  read-write
	STATUS  mandatory
	DESCRIPTION "PB2 CB8 Alarm-Threshold"
		::= { panelboard2 227 }

pb2-CB9-Alarm-Threshold
	OBJECT-TYPE
	SYNTAX  INTEGER
	ACCESS  read-write
	STATUS  mandatory
	DESCRIPTION "PB2 CB9 Alarm-Threshold"
		::= { panelboard2 228 }

pb2-CB10-Alarm-Threshold
	OBJECT-TYPE
	SYNTAX  INTEGER
	ACCESS  read-write
	STATUS  mandatory
	DESCRIPTION "PB2 CB10 Alarm-Threshold"
		::= { panelboard2 229 }

pb2-CB11-Alarm-Threshold
	OBJECT-TYPE
	SYNTAX  INTEGER
	ACCESS  read-write
	STATUS  mandatory
	DESCRIPTION "PB2 CB11 Alarm-Threshold"
		::= { panelboard2 230 }

pb2-CB12-Alarm-Threshold
	OBJECT-TYPE
	SYNTAX  INTEGER
	ACCESS  read-write
	STATUS  mandatory
	DESCRIPTION "PB2 CB12 Alarm-Threshold"
		::= { panelboard2 231 }
  
pb2-CB13-Alarm-Threshold
	OBJECT-TYPE
	SYNTAX  INTEGER
	ACCESS  read-write
	STATUS  mandatory
	DESCRIPTION "PB2 CB13 Alarm-Threshold"
		::= { panelboard2 232 }

pb2-CB14-Alarm-Threshold
	OBJECT-TYPE
	SYNTAX  INTEGER
	ACCESS  read-write
	STATUS  mandatory
	DESCRIPTION "PB2 CB14 Alarm-Threshold"
		::= { panelboard2 233 }

pb2-CB15-Alarm-Threshold
	OBJECT-TYPE
	SYNTAX  INTEGER
	ACCESS  read-write
	STATUS  mandatory
	DESCRIPTION "PB2 CB15 Alarm-Threshold"
		::= { panelboard2 234 }

pb2-CB16-Alarm-Threshold
	OBJECT-TYPE
	SYNTAX  INTEGER
	ACCESS  read-write
	STATUS  mandatory
	DESCRIPTION "PB2 CB16 Alarm-Threshold"
		::= { panelboard2 235 }

pb2-CB17-Alarm-Threshold
	OBJECT-TYPE
	SYNTAX  INTEGER
	ACCESS  read-write
	STATUS  mandatory
	DESCRIPTION "PB2 CB17 Alarm-Threshold"
		::= { panelboard2 236 }

pb2-CB18-Alarm-Threshold
	OBJECT-TYPE
	SYNTAX  INTEGER
	ACCESS  read-write
	STATUS  mandatory
	DESCRIPTION "PB2 CB18 Alarm-Threshold"
		::= { panelboard2 237 }

pb2-CB19-Alarm-Threshold
	OBJECT-TYPE
	SYNTAX  INTEGER
	ACCESS  read-write
	STATUS  mandatory
	DESCRIPTION "PB2 CB19 Alarm-Threshold"
		::= { panelboard2 238 }

pb2-CB20-Alarm-Threshold
	OBJECT-TYPE
	SYNTAX  INTEGER
	ACCESS  read-write
	STATUS  mandatory
	DESCRIPTION "PB2 CB20 Alarm-Threshold"
		::= { panelboard2 239 }

pb2-CB21-Alarm-Threshold
	OBJECT-TYPE
	SYNTAX  INTEGER
	ACCESS  read-write
	STATUS  mandatory
	DESCRIPTION "PB2 CB21 Alarm-Threshold"
		::= { panelboard2 240 }

pb2-CB22-Alarm-Threshold
	OBJECT-TYPE
	SYNTAX  INTEGER
	ACCESS  read-write
	STATUS  mandatory
	DESCRIPTION "PB2 CB22 Alarm-Threshold"
		::= { panelboard2 241 }
  
pb2-CB23-Alarm-Threshold
	OBJECT-TYPE
	SYNTAX  INTEGER
	ACCESS  read-write
	STATUS  mandatory
	DESCRIPTION "PB2 CB23 Alarm-Threshold"
		::= { panelboard2 242 }

pb2-CB24-Alarm-Threshold
	OBJECT-TYPE
	SYNTAX  INTEGER
	ACCESS  read-write
	STATUS  mandatory
	DESCRIPTION "PB2 CB24 Alarm-Threshold"
		::= { panelboard2 243 }

pb2-CB25-Alarm-Threshold
	OBJECT-TYPE
	SYNTAX  INTEGER
	ACCESS  read-write
	STATUS  mandatory
	DESCRIPTION "PB2 CB25 Alarm-Threshold"
		::= { panelboard2 244 }

pb2-CB26-Alarm-Threshold
	OBJECT-TYPE
	SYNTAX  INTEGER
	ACCESS  read-write
	STATUS  mandatory
	DESCRIPTION "PB2 CB26 Alarm-Threshold"
		::= { panelboard2 245 }

pb2-CB27-Alarm-Threshold
	OBJECT-TYPE
	SYNTAX  INTEGER
	ACCESS  read-write
	STATUS  mandatory
	DESCRIPTION "PB2 CB27 Alarm-Threshold"
		::= { panelboard2 246 }

pb2-CB28-Alarm-Threshold
	OBJECT-TYPE
	SYNTAX  INTEGER
	ACCESS  read-write
	STATUS  mandatory
	DESCRIPTION "PB2 CB28 Alarm-Threshold"
		::= { panelboard2 247 }

pb2-CB29-Alarm-Threshold
	OBJECT-TYPE
	SYNTAX  INTEGER
	ACCESS  read-write
	STATUS  mandatory
	DESCRIPTION "PB2 CB29 Alarm-Threshold"
		::= { panelboard2 248 }

pb2-CB30-Alarm-Threshold
	OBJECT-TYPE
	SYNTAX  INTEGER
	ACCESS  read-write
	STATUS  mandatory
	DESCRIPTION "PB2 CB30 Alarm-Threshold"
		::= { panelboard2 249 }

pb2-CB31-Alarm-Threshold
	OBJECT-TYPE
	SYNTAX  INTEGER
	ACCESS  read-write
	STATUS  mandatory
	DESCRIPTION "PB2 CB31 Alarm-Threshold"
		::= { panelboard2 250 }

pb2-CB32-Alarm-Threshold
	OBJECT-TYPE
	SYNTAX  INTEGER
	ACCESS  read-write
	STATUS  mandatory
	DESCRIPTION "PB2 CB32 Alarm-Threshold"
		::= { panelboard2 251 }
  
pb2-CB33-Alarm-Threshold
	OBJECT-TYPE
	SYNTAX  INTEGER
	ACCESS  read-write
	STATUS  mandatory
	DESCRIPTION "PB2 CB33 Alarm-Threshold"
		::= { panelboard2 252 }

pb2-CB34-Alarm-Threshold
	OBJECT-TYPE
	SYNTAX  INTEGER
	ACCESS  read-write
	STATUS  mandatory
	DESCRIPTION "PB2 CB34 Alarm-Threshold"
		::= { panelboard2 253 }

pb2-CB35-Alarm-Threshold
	OBJECT-TYPE
	SYNTAX  INTEGER
	ACCESS  read-write
	STATUS  mandatory
	DESCRIPTION "PB2 CB35 Alarm-Threshold"
		::= { panelboard2 254 }

pb2-CB36-Alarm-Threshold
	OBJECT-TYPE
	SYNTAX  INTEGER
	ACCESS  read-write
	STATUS  mandatory
	DESCRIPTION "PB2 CB36 Alarm-Threshold"
		::= { panelboard2 255 }

pb2-CB37-Alarm-Threshold
	OBJECT-TYPE
	SYNTAX  INTEGER
	ACCESS  read-write
	STATUS  mandatory
	DESCRIPTION "PB2 CB37 Alarm-Threshold"
		::= { panelboard2 256 }

pb2-CB38-Alarm-Threshold
	OBJECT-TYPE
	SYNTAX  INTEGER
	ACCESS  read-write
	STATUS  mandatory
	DESCRIPTION "PB2 CB38 Alarm-Threshold"
		::= { panelboard2 257 }

pb2-CB39-Alarm-Threshold
	OBJECT-TYPE
	SYNTAX  INTEGER
	ACCESS  read-write
	STATUS  mandatory
	DESCRIPTION "PB2 CB39 Alarm-Threshold"
		::= { panelboard2 258 }

pb2-CB40-Alarm-Threshold
	OBJECT-TYPE
	SYNTAX  INTEGER
	ACCESS  read-write
	STATUS  mandatory
	DESCRIPTION "PB2 CB40 Alarm-Threshold"
		::= { panelboard2 259 }

pb2-CB41-Alarm-Threshold
	OBJECT-TYPE
	SYNTAX  INTEGER
	ACCESS  read-write
	STATUS  mandatory
	DESCRIPTION "PB2 CB41 Alarm-Threshold"
		::= { panelboard2 260 }

pb2-CB42-Alarm-Threshold
	OBJECT-TYPE
	SYNTAX  INTEGER
	ACCESS  read-write
	STATUS  mandatory
	DESCRIPTION "PB2 CB42 Alarm-Threshold"
		::= { panelboard2 261 }

pb2-CB1-Warning-Time-Delay
	OBJECT-TYPE
	SYNTAX  INTEGER
	ACCESS  read-write
	STATUS  mandatory
	DESCRIPTION "PB2 CB1 Warning-Time-Delay
		     Note for all warning time delays 1-42: units are in seconds"                     
		::= { panelboard2 262 }

pb2-CB2-Warning-Time-Delay
	OBJECT-TYPE
	SYNTAX  INTEGER
	ACCESS  read-write
	STATUS  mandatory
	DESCRIPTION "PB2 CB2 Warning-Time-Delay"
		::= { panelboard2 263 }
  
pb2-CB3-Warning-Time-Delay
	OBJECT-TYPE
	SYNTAX  INTEGER
	ACCESS  read-write
	STATUS  mandatory
	DESCRIPTION "PB2 CB3 Warning-Time-Delay"
		::= { panelboard2 264 }

pb2-CB4-Warning-Time-Delay
	OBJECT-TYPE
	SYNTAX  INTEGER
	ACCESS  read-write
	STATUS  mandatory
	DESCRIPTION "PB2 CB4 Warning-Time-Delay"
		::= { panelboard2 265 }

pb2-CB5-Warning-Time-Delay
	OBJECT-TYPE
	SYNTAX  INTEGER
	ACCESS  read-write
	STATUS  mandatory
	DESCRIPTION "PB2 CB5 Warning-Time-Delay"
		::= { panelboard2 266 }

pb2-CB6-Warning-Time-Delay
	OBJECT-TYPE
	SYNTAX  INTEGER
	ACCESS  read-write
	STATUS  mandatory
	DESCRIPTION "PB2 CB6 Warning-Time-Delay"
		::= { panelboard2 267 }

pb2-CB7-Warning-Time-Delay
	OBJECT-TYPE
	SYNTAX  INTEGER
	ACCESS  read-write
	STATUS  mandatory
	DESCRIPTION "PB2 CB7 Warning-Time-Delay"
		::= { panelboard2 268 }

pb2-CB8-Warning-Time-Delay
	OBJECT-TYPE
	SYNTAX  INTEGER
	ACCESS  read-write
	STATUS  mandatory
	DESCRIPTION "PB2 CB8 Warning-Time-Delay"
		::= { panelboard2 269 }

pb2-CB9-Warning-Time-Delay
	OBJECT-TYPE
	SYNTAX  INTEGER
	ACCESS  read-write
	STATUS  mandatory
	DESCRIPTION "PB2 CB9 Warning-Time-Delay"
		::= { panelboard2 270 }

pb2-CB10-Warning-Time-Delay
	OBJECT-TYPE
	SYNTAX  INTEGER
	ACCESS  read-write
	STATUS  mandatory
	DESCRIPTION "PB2 CB10 Warning-Time-Delay"
		::= { panelboard2 271 }

pb2-CB11-Warning-Time-Delay
	OBJECT-TYPE
	SYNTAX  INTEGER
	ACCESS  read-write
	STATUS  mandatory
	DESCRIPTION "PB2 CB11 Warning-Time-Delay"
		::= { panelboard2 272 }

pb2-CB12-Warning-Time-Delay
	OBJECT-TYPE
	SYNTAX  INTEGER
	ACCESS  read-write
	STATUS  mandatory
	DESCRIPTION "PB2 CB12 Warning-Time-Delay"
		::= { panelboard2 273 }
  
pb2-CB13-Warning-Time-Delay
	OBJECT-TYPE
	SYNTAX  INTEGER
	ACCESS  read-write
	STATUS  mandatory
	DESCRIPTION "PB2 CB13 Warning-Time-Delay"
		::= { panelboard2 274 }

pb2-CB14-Warning-Time-Delay
	OBJECT-TYPE
	SYNTAX  INTEGER
	ACCESS  read-write
	STATUS  mandatory
	DESCRIPTION "PB2 CB14 Warning-Time-Delay"
		::= { panelboard2 275 }

pb2-CB15-Warning-Time-Delay
	OBJECT-TYPE
	SYNTAX  INTEGER
	ACCESS  read-write
	STATUS  mandatory
	DESCRIPTION "PB2 CB15 Warning-Time-Delay"
		::= { panelboard2 276 }

pb2-CB16-Warning-Time-Delay
	OBJECT-TYPE
	SYNTAX  INTEGER
	ACCESS  read-write
	STATUS  mandatory
	DESCRIPTION "PB2 CB16 Warning-Time-Delay"
		::= { panelboard2 277 }

pb2-CB17-Warning-Time-Delay
	OBJECT-TYPE
	SYNTAX  INTEGER
	ACCESS  read-write
	STATUS  mandatory
	DESCRIPTION "PB2 CB17 Warning-Time-Delay"
		::= { panelboard2 278 }

pb2-CB18-Warning-Time-Delay
	OBJECT-TYPE
	SYNTAX  INTEGER
	ACCESS  read-write
	STATUS  mandatory
	DESCRIPTION "PB2 CB18 Warning-Time-Delay"
		::= { panelboard2 279 }

pb2-CB19-Warning-Time-Delay
	OBJECT-TYPE
	SYNTAX  INTEGER
	ACCESS  read-write
	STATUS  mandatory
	DESCRIPTION "PB2 CB19 Warning-Time-Delay"
		::= { panelboard2 280 }

pb2-CB20-Warning-Time-Delay
	OBJECT-TYPE
	SYNTAX  INTEGER
	ACCESS  read-write
	STATUS  mandatory
	DESCRIPTION "PB2 CB20 Warning-Time-Delay"
		::= { panelboard2 281 }

pb2-CB21-Warning-Time-Delay
	OBJECT-TYPE
	SYNTAX  INTEGER
	ACCESS  read-write
	STATUS  mandatory
	DESCRIPTION "PB2 CB21 Warning-Time-Delay"
		::= { panelboard2 282 }

pb2-CB22-Warning-Time-Delay
	OBJECT-TYPE
	SYNTAX  INTEGER
	ACCESS  read-write
	STATUS  mandatory
	DESCRIPTION "PB2 CB22 Warning-Time-Delay"
		::= { panelboard2 283 }
  
pb2-CB23-Warning-Time-Delay
	OBJECT-TYPE
	SYNTAX  INTEGER
	ACCESS  read-write
	STATUS  mandatory
	DESCRIPTION "PB2 CB23 Warning-Time-Delay"
		::= { panelboard2 284 }

pb2-CB24-Warning-Time-Delay
	OBJECT-TYPE
	SYNTAX  INTEGER
	ACCESS  read-write
	STATUS  mandatory
	DESCRIPTION "PB2 CB24 Warning-Time-Delay"
		::= { panelboard2 285 }

pb2-CB25-Warning-Time-Delay
	OBJECT-TYPE
	SYNTAX  INTEGER
	ACCESS  read-write
	STATUS  mandatory
	DESCRIPTION "PB2 CB25 Warning-Time-Delay"
		::= { panelboard2 286 }

pb2-CB26-Warning-Time-Delay
	OBJECT-TYPE
	SYNTAX  INTEGER
	ACCESS  read-write
	STATUS  mandatory
	DESCRIPTION "PB2 CB26 Warning-Time-Delay"
		::= { panelboard2 287 }

pb2-CB27-Warning-Time-Delay
	OBJECT-TYPE
	SYNTAX  INTEGER
	ACCESS  read-write
	STATUS  mandatory
	DESCRIPTION "PB2 CB27 Warning-Time-Delay"
		::= { panelboard2 288 }

pb2-CB28-Warning-Time-Delay
	OBJECT-TYPE
	SYNTAX  INTEGER
	ACCESS  read-write
	STATUS  mandatory
	DESCRIPTION "PB2 CB28 Warning-Time-Delay"
		::= { panelboard2 289 }

pb2-CB29-Warning-Time-Delay
	OBJECT-TYPE
	SYNTAX  INTEGER
	ACCESS  read-write
	STATUS  mandatory
	DESCRIPTION "PB2 CB29 Warning-Time-Delay"
		::= { panelboard2 290}

pb2-CB30-Warning-Time-Delay
	OBJECT-TYPE
	SYNTAX  INTEGER
	ACCESS  read-write
	STATUS  mandatory
	DESCRIPTION "PB2 CB30 Warning-Time-Delay"
		::= { panelboard2 291 }

pb2-CB31-Warning-Time-Delay
	OBJECT-TYPE
	SYNTAX  INTEGER
	ACCESS  read-write
	STATUS  mandatory
	DESCRIPTION "PB2 CB31 Warning-Time-Delay"
		::= { panelboard2 292 }

pb2-CB32-Warning-Time-Delay
	OBJECT-TYPE
	SYNTAX  INTEGER
	ACCESS  read-write
	STATUS  mandatory
	DESCRIPTION "PB2 CB32 Warning-Time-Delay"
		::= { panelboard2 293 }
  
pb2-CB33-Warning-Time-Delay
	OBJECT-TYPE
	SYNTAX  INTEGER
	ACCESS  read-write
	STATUS  mandatory
	DESCRIPTION "PB2 CB33 Warning-Time-Delay"
		::= { panelboard2 294 }

pb2-CB34-Warning-Time-Delay
	OBJECT-TYPE
	SYNTAX  INTEGER
	ACCESS  read-write
	STATUS  mandatory
	DESCRIPTION "PB2 CB34 Warning-Time-Delay"
		::= { panelboard2 295 }

pb2-CB35-Warning-Time-Delay
	OBJECT-TYPE
	SYNTAX  INTEGER
	ACCESS  read-write
	STATUS  mandatory
	DESCRIPTION "PB2 CB35 Warning-Time-Delay"
		::= { panelboard2 296 }

pb2-CB36-Warning-Time-Delay
	OBJECT-TYPE
	SYNTAX  INTEGER
	ACCESS  read-write
	STATUS  mandatory
	DESCRIPTION "PB2 CB36 Warning-Time-Delay"
		::= { panelboard2 297 }

pb2-CB37-Warning-Time-Delay
	OBJECT-TYPE
	SYNTAX  INTEGER
	ACCESS  read-write
	STATUS  mandatory
	DESCRIPTION "PB2 CB37 Warning-Time-Delay"
		::= { panelboard2 298 }

pb2-CB38-Warning-Time-Delay
	OBJECT-TYPE
	SYNTAX  INTEGER
	ACCESS  read-write
	STATUS  mandatory
	DESCRIPTION "PB2 CB38 Warning-Time-Delay"
		::= { panelboard2 299 }

pb2-CB39-Warning-Time-Delay
	OBJECT-TYPE
	SYNTAX  INTEGER
	ACCESS  read-write
	STATUS  mandatory
	DESCRIPTION "PB2 CB39 Warning-Time-Delay"
		::= { panelboard2 300 }

pb2-CB40-Warning-Time-Delay
	OBJECT-TYPE
	SYNTAX  INTEGER
	ACCESS  read-write
	STATUS  mandatory
	DESCRIPTION "PB2 CB40 Warning-Time-Delay"
		::= { panelboard2 301 }

pb2-CB41-Warning-Time-Delay
	OBJECT-TYPE
	SYNTAX  INTEGER
	ACCESS  read-write
	STATUS  mandatory
	DESCRIPTION "PB2 CB41 Warning-Time-Delay"
		::= { panelboard2 302 }

pb2-CB42-Warning-Time-Delay
	OBJECT-TYPE
	SYNTAX  INTEGER
	ACCESS  read-write
	STATUS  mandatory
	DESCRIPTION "PB2 CB42 Warning-Time-Delay"
		::= { panelboard2 303 }

pb2-CB1-Alarm-Time-Delay
	OBJECT-TYPE
	SYNTAX  INTEGER
	ACCESS  read-write
	STATUS  mandatory
	DESCRIPTION "PB2 CB1 Alarm-Time-Delay
		     Note for all alarm time delays 1-42: units are in seconds"                     
		::= { panelboard2 304 }

pb2-CB2-Alarm-Time-Delay
	OBJECT-TYPE
	SYNTAX  INTEGER
	ACCESS  read-write
	STATUS  mandatory
	DESCRIPTION "PB2 CB2 Alarm-Time-Delay"
		::= { panelboard2 305 }
  
pb2-CB3-Alarm-Time-Delay
	OBJECT-TYPE
	SYNTAX  INTEGER
	ACCESS  read-write
	STATUS  mandatory
	DESCRIPTION "PB2 CB3 Alarm-Time-Delay"
		::= { panelboard2 306 }

pb2-CB4-Alarm-Time-Delay
	OBJECT-TYPE
	SYNTAX  INTEGER
	ACCESS  read-write
	STATUS  mandatory
	DESCRIPTION "PB2 CB4 Alarm-Time-Delay"
		::= { panelboard2 307 }

pb2-CB5-Alarm-Time-Delay
	OBJECT-TYPE
	SYNTAX  INTEGER
	ACCESS  read-write
	STATUS  mandatory
	DESCRIPTION "PB2 CB5 Alarm-Time-Delay"
		::= { panelboard2 308 }

pb2-CB6-Alarm-Time-Delay
	OBJECT-TYPE
	SYNTAX  INTEGER
	ACCESS  read-write
	STATUS  mandatory
	DESCRIPTION "PB2 CB6 Alarm-Time-Delay"
		::= { panelboard2 309 }

pb2-CB7-Alarm-Time-Delay
	OBJECT-TYPE
	SYNTAX  INTEGER
	ACCESS  read-write
	STATUS  mandatory
	DESCRIPTION "PB2 CB7 Alarm-Time-Delay"
		::= { panelboard2 310 }

pb2-CB8-Alarm-Time-Delay
	OBJECT-TYPE
	SYNTAX  INTEGER
	ACCESS  read-write
	STATUS  mandatory
	DESCRIPTION "PB2 CB8 Alarm-Time-Delay"
		::= { panelboard2 311 }

pb2-CB9-Alarm-Time-Delay
	OBJECT-TYPE
	SYNTAX  INTEGER
	ACCESS  read-write
	STATUS  mandatory
	DESCRIPTION "PB2 CB9 Alarm-Time-Delay"
		::= { panelboard2 312 }

pb2-CB10-Alarm-Time-Delay
	OBJECT-TYPE
	SYNTAX  INTEGER
	ACCESS  read-write
	STATUS  mandatory
	DESCRIPTION "PB2 CB10 Alarm-Time-Delay"
		::= { panelboard2 313 }

pb2-CB11-Alarm-Time-Delay
	OBJECT-TYPE
	SYNTAX  INTEGER
	ACCESS  read-write
	STATUS  mandatory
	DESCRIPTION "PB2 CB11 Alarm-Time-Delay"
		::= { panelboard2 314 }

pb2-CB12-Alarm-Time-Delay
	OBJECT-TYPE
	SYNTAX  INTEGER
	ACCESS  read-write
	STATUS  mandatory
	DESCRIPTION "PB2 CB12 Alarm-Time-Delay"
		::= { panelboard2 315 }
  
pb2-CB13-Alarm-Time-Delay
	OBJECT-TYPE
	SYNTAX  INTEGER
	ACCESS  read-write
	STATUS  mandatory
	DESCRIPTION "PB2 CB13 Alarm-Time-Delay"
		::= { panelboard2 316 }

pb2-CB14-Alarm-Time-Delay
	OBJECT-TYPE
	SYNTAX  INTEGER
	ACCESS  read-write
	STATUS  mandatory
	DESCRIPTION "PB2 CB14 Alarm-Time-Delay"
		::= { panelboard2 317 }

pb2-CB15-Alarm-Time-Delay
	OBJECT-TYPE
	SYNTAX  INTEGER
	ACCESS  read-write
	STATUS  mandatory
	DESCRIPTION "PB2 CB15 Alarm-Time-Delay"
		::= { panelboard2 318 }

pb2-CB16-Alarm-Time-Delay
	OBJECT-TYPE
	SYNTAX  INTEGER
	ACCESS  read-write
	STATUS  mandatory
	DESCRIPTION "PB2 CB16 Alarm-Time-Delay"
		::= { panelboard2 319 }

pb2-CB17-Alarm-Time-Delay
	OBJECT-TYPE
	SYNTAX  INTEGER
	ACCESS  read-write
	STATUS  mandatory
	DESCRIPTION "PB2 CB17 Alarm-Time-Delay"
		::= { panelboard2 320 }

pb2-CB18-Alarm-Time-Delay
	OBJECT-TYPE
	SYNTAX  INTEGER
	ACCESS  read-write
	STATUS  mandatory
	DESCRIPTION "PB2 CB18 Alarm-Time-Delay"
		::= { panelboard2 321 }

pb2-CB19-Alarm-Time-Delay
	OBJECT-TYPE
	SYNTAX  INTEGER
	ACCESS  read-write
	STATUS  mandatory
	DESCRIPTION "PB2 CB19 Alarm-Time-Delay"
		::= { panelboard2 322 }

pb2-CB20-Alarm-Time-Delay
	OBJECT-TYPE
	SYNTAX  INTEGER
	ACCESS  read-write
	STATUS  mandatory
	DESCRIPTION "PB2 CB20 Alarm-Time-Delay"
		::= { panelboard2 323 }

pb2-CB21-Alarm-Time-Delay
	OBJECT-TYPE
	SYNTAX  INTEGER
	ACCESS  read-write
	STATUS  mandatory
	DESCRIPTION "PB2 CB21 Alarm-Time-Delay"
		::= { panelboard2 324 }

pb2-CB22-Alarm-Time-Delay
	OBJECT-TYPE
	SYNTAX  INTEGER
	ACCESS  read-write
	STATUS  mandatory
	DESCRIPTION "PB2 CB22 Alarm-Time-Delay"
		::= { panelboard2 325 }
  
pb2-CB23-Alarm-Time-Delay
	OBJECT-TYPE
	SYNTAX  INTEGER
	ACCESS  read-write
	STATUS  mandatory
	DESCRIPTION "PB2 CB23 Alarm-Time-Delay"
		::= { panelboard2 326 }

pb2-CB24-Alarm-Time-Delay
	OBJECT-TYPE
	SYNTAX  INTEGER
	ACCESS  read-write
	STATUS  mandatory
	DESCRIPTION "PB2 CB24 Alarm-Time-Delay"
		::= { panelboard2 327 }

pb2-CB25-Alarm-Time-Delay
	OBJECT-TYPE
	SYNTAX  INTEGER
	ACCESS  read-write
	STATUS  mandatory
	DESCRIPTION "PB2 CB25 Alarm-Time-Delay"
		::= { panelboard2 328 }

pb2-CB26-Alarm-Time-Delay
	OBJECT-TYPE
	SYNTAX  INTEGER
	ACCESS  read-write
	STATUS  mandatory
	DESCRIPTION "PB2 CB26 Alarm-Time-Delay"
		::= { panelboard2 329 }

pb2-CB27-Alarm-Time-Delay
	OBJECT-TYPE
	SYNTAX  INTEGER
	ACCESS  read-write
	STATUS  mandatory
	DESCRIPTION "PB2 CB27 Alarm-Time-Delay"
		::= { panelboard2 330 }

pb2-CB28-Alarm-Time-Delay
	OBJECT-TYPE
	SYNTAX  INTEGER
	ACCESS  read-write
	STATUS  mandatory
	DESCRIPTION "PB2 CB28 Alarm-Time-Delay"
		::= { panelboard2 331 }

pb2-CB29-Alarm-Time-Delay
	OBJECT-TYPE
	SYNTAX  INTEGER
	ACCESS  read-write
	STATUS  mandatory
	DESCRIPTION "PB2 CB29 Alarm-Time-Delay"
		::= { panelboard2 332 }

pb2-CB30-Alarm-Time-Delay
	OBJECT-TYPE
	SYNTAX  INTEGER
	ACCESS  read-write
	STATUS  mandatory
	DESCRIPTION "PB2 CB30 Alarm-Time-Delay"
		::= { panelboard2 333 }

pb2-CB31-Alarm-Time-Delay
	OBJECT-TYPE
	SYNTAX  INTEGER
	ACCESS  read-write
	STATUS  mandatory
	DESCRIPTION "PB2 CB31 Alarm-Time-Delay"
		::= { panelboard2 334 }

pb2-CB32-Alarm-Time-Delay
	OBJECT-TYPE
	SYNTAX  INTEGER
	ACCESS  read-write
	STATUS  mandatory
	DESCRIPTION "PB2 CB32 Alarm-Time-Delay"
		::= { panelboard2 335 }
  
pb2-CB33-Alarm-Time-Delay
	OBJECT-TYPE
	SYNTAX  INTEGER
	ACCESS  read-write
	STATUS  mandatory
	DESCRIPTION "PB2 CB33 Alarm-Time-Delay"
		::= { panelboard2 336 }

pb2-CB34-Alarm-Time-Delay
	OBJECT-TYPE
	SYNTAX  INTEGER
	ACCESS  read-write
	STATUS  mandatory
	DESCRIPTION "PB2 CB34 Alarm-Time-Delay"
		::= { panelboard2 337 }

pb2-CB35-Alarm-Time-Delay
	OBJECT-TYPE
	SYNTAX  INTEGER
	ACCESS  read-write
	STATUS  mandatory
	DESCRIPTION "PB2 CB35 Alarm-Time-Delay"
		::= { panelboard2 338 }

pb2-CB36-Alarm-Time-Delay
	OBJECT-TYPE
	SYNTAX  INTEGER
	ACCESS  read-write
	STATUS  mandatory
	DESCRIPTION "PB2 CB36 Alarm-Time-Delay"
		::= { panelboard2 339 }

pb2-CB37-Alarm-Time-Delay
	OBJECT-TYPE
	SYNTAX  INTEGER
	ACCESS  read-write
	STATUS  mandatory
	DESCRIPTION "PB2 CB37 Alarm-Time-Delay"
		::= { panelboard2 340 }

pb2-CB38-Alarm-Time-Delay
	OBJECT-TYPE
	SYNTAX  INTEGER
	ACCESS  read-write
	STATUS  mandatory
	DESCRIPTION "PB2 CB38 Alarm-Time-Delay"
		::= { panelboard2 341 }

pb2-CB39-Alarm-Time-Delay
	OBJECT-TYPE
	SYNTAX  INTEGER
	ACCESS  read-write
	STATUS  mandatory
	DESCRIPTION "PB2 CB39 Alarm-Time-Delay"
		::= { panelboard2 342 }

pb2-CB40-Alarm-Time-Delay
	OBJECT-TYPE
	SYNTAX  INTEGER
	ACCESS  read-write
	STATUS  mandatory
	DESCRIPTION "PB2 CB40 Alarm-Time-Delay"
		::= { panelboard2 343 }

pb2-CB41-Alarm-Time-Delay
	OBJECT-TYPE
	SYNTAX  INTEGER
	ACCESS  read-write
	STATUS  mandatory
	DESCRIPTION "PB2 CB41 Alarm-Time-Delay"
		::= { panelboard2 344 }

pb2-CB42-Alarm-Time-Delay
	OBJECT-TYPE
	SYNTAX  INTEGER
	ACCESS  read-write
	STATUS  mandatory
	DESCRIPTION "PB2 CB42 Alarm-Time-Delay"
		::= { panelboard2 345 }

pb2-Global-Breaker-Size
	OBJECT-TYPE
	SYNTAX  INTEGER
	ACCESS  read-write
	STATUS  mandatory
	DESCRIPTION "PB2 Global-Breaker-Size
		     Note for global breaker size: 10 = 10 amps
                     Range is 10 to 100 amps"
		::= { panelboard2 346 }

pb2-Global-Warning-Threshold
	OBJECT-TYPE
	SYNTAX  INTEGER
	ACCESS  read-write
	STATUS  mandatory
	DESCRIPTION "PB2 Global-Warning-Threshold
		     Note for global warning threshold: 70 = 70% of breaker size
                     range is 0-100%"
		::= { panelboard2 347 }

pb2-Global-Alarm-Threshold
	OBJECT-TYPE
	SYNTAX  INTEGER
	ACCESS  read-write
	STATUS  mandatory
	DESCRIPTION "PB2 Global-Alarm-Threshold
		     Note for global alarm threshold: 80 = 80% of breaker size
                     range is 0-100%"
		::= { panelboard2 348 }

pb2-Global-Warning-Time-Delay
	OBJECT-TYPE
	SYNTAX  INTEGER
	ACCESS  read-write
	STATUS  mandatory
	DESCRIPTION "PB2 Global-Warning-Time-Delay
		     Note for global warning time delay: units are in seconds"                     
		::= { panelboard2 349 }

pb2-Global-Alarm-Time-Delay
	OBJECT-TYPE
	SYNTAX  INTEGER
	ACCESS  read-write
	STATUS  mandatory
	DESCRIPTION "PB2 Global-Alarm-Time-Delay
		     Note for global alarm time delay: units are in seconds"                     
		::= { panelboard2 350 }

pb2-Min-Max-Reset
	OBJECT-TYPE
	SYNTAX  INTEGER
	ACCESS  read-write
	STATUS  mandatory
	DESCRIPTION "PB2 Min-Max-Reset
                     Note for Min-Max Reset: writing to this register will clear minimum
		     and maximum current values"
		::= { panelboard2 351 }

pb2-Global-Warning-Alarm-Register
	OBJECT-TYPE
	SYNTAX  INTEGER
	ACCESS  read-only
	STATUS  mandatory
	DESCRIPTION "PB2 Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { panelboard2 352 }

pb2-Meter-Alarm-Status-Latching
	OBJECT-TYPE
	SYNTAX  INTEGER
	ACCESS  read-write
	STATUS  mandatory
	DESCRIPTION "PB2 Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { panelboard2 353 }

pb2-Meter-Alarm-Status-Nonlatching
	OBJECT-TYPE
	SYNTAX  INTEGER
	ACCESS  read-only
	STATUS  mandatory
	DESCRIPTION "PB2 Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { panelboard2 354 }

pb2-Digital-Alarm-Status
	OBJECT-TYPE
	SYNTAX  INTEGER
	ACCESS  read-only
	STATUS  mandatory
	DESCRIPTION "PB2 Digital-Alarm-Status
			bit 0:	Digital alarm 1
			bit 1:	Digital alarm 2
			bit 2: 	Digital alarm 3
			bit 3: 	Digital alarm 4
			bits 4 – 15: Not Used"
		::= { panelboard2 355 }

pb2-Current-Option-Setting
	OBJECT-TYPE
	SYNTAX  INTEGER
	ACCESS  read-only
	STATUS  mandatory
	DESCRIPTION "PB2 Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { panelboard2 356 }

pb2-Current-Phase-A-Panelboard
	OBJECT-TYPE
	SYNTAX  INTEGER
	ACCESS  read-only
	STATUS  mandatory
	DESCRIPTION "PB2 Current-Phase-A-Panelboard
                     Note for all currents: 100 = 10.0 amps"
		::= { panelboard2 357 }

pb2-Current-Phase-B-Panelboard
	OBJECT-TYPE
	SYNTAX  INTEGER
	ACCESS  read-only
	STATUS  mandatory
	DESCRIPTION "PB2 Current-Phase-B-Panelboard"
		::= { panelboard2 358 }

pb2-Current-Phase-C-Panelboard
	OBJECT-TYPE
	SYNTAX  INTEGER
	ACCESS  read-only
	STATUS  mandatory
	DESCRIPTION "PB2 Current-Phase-C-Panelboard"
		::= { panelboard2 359 }

pb2-Current-Neutral-Panelboard
	OBJECT-TYPE
	SYNTAX  INTEGER
	ACCESS  read-only
	STATUS  mandatory
	DESCRIPTION "PB2 Current-Neutral-Panelboard"
		::= { panelboard2 360 }


pb2-Over-Current-Alarm-Threshhold-Pnlbd
	OBJECT-TYPE
	SYNTAX  INTEGER
	ACCESS  read-write
	STATUS  mandatory
	DESCRIPTION "PB2 Over-Current-Alarm-Threshhold-Pnlbd"
		::= { panelboard2 361 }

pb2-Under-Current-Alarm-Threshhold-Pnlbd
	OBJECT-TYPE
	SYNTAX  INTEGER
	ACCESS  read-write
	STATUS  mandatory
	DESCRIPTION "PB2 Under-Current-Alarm-Threshhold-Pnlbd"
		::= { panelboard2 362 }

pb2-Over-Current-Set-Counter-Pnlbd
	OBJECT-TYPE
	SYNTAX  INTEGER
	ACCESS  read-only
	STATUS  mandatory
	DESCRIPTION "PB2 Over-Current-Set-Counter-Pnlbd
		     Note for all counters:
                     The set counter is incremented when the value goes outside the threshold limit
                     The reset counter is incremented when the value is returns to  the threshold limit"
		::= { panelboard2 363 }

pb2-Over-Current-Reset-Counter-Pnlbd
	OBJECT-TYPE
	SYNTAX  INTEGER
	ACCESS  read-only
	STATUS  mandatory
	DESCRIPTION "PB2 Over-Current-Reset-Counter-Pnlbd"
		::= { panelboard2 364 }

pb2-Under-Current-Set-Counter-Pnlbd
	OBJECT-TYPE
	SYNTAX  INTEGER
	ACCESS  read-only
	STATUS  mandatory
	DESCRIPTION "PB2 Under-Current-Set-Counter-Pnlbd"
		::= { panelboard2 365 }

pb2-Under-Current-Reset-Counter-Pnlbd
	OBJECT-TYPE
	SYNTAX  INTEGER
	ACCESS  read-only
	STATUS  mandatory
	DESCRIPTION "PB2 Under-Current-Reset-Counter-Pnlbd"
		::= { panelboard2 366 }

pb2-Current-Phase-A-Both-Pnlbd
	OBJECT-TYPE
	SYNTAX  INTEGER
	ACCESS  read-only
	STATUS  mandatory
	DESCRIPTION "PB2 Current-Phase-A-Both-Pnlbd"
		::= { panelboard2 367 }

pb2-Current-Phase-B-Both-Pnlbd
	OBJECT-TYPE
	SYNTAX  INTEGER
	ACCESS  read-only
	STATUS  mandatory
	DESCRIPTION "PB2 Current-Phase-B-Both-Pnlbd"
		::= { panelboard2 368 }

pb2-Current-Phase-C-Both-Pnlbd
	OBJECT-TYPE
	SYNTAX  INTEGER
	ACCESS  read-only
	STATUS  mandatory
	DESCRIPTION "PB2 Current-Phase-C-Both-Pnlbd"
		::= { panelboard2 369 }

pb2-Current-Neutral-Both-Pnlbd
	OBJECT-TYPE
	SYNTAX  INTEGER
	ACCESS  read-only
	STATUS  mandatory
	DESCRIPTION "PB2 Current-Neutral-Both-Pnlbd"
		::= { panelboard2 370 }


pb2-Over-Current-Alarm-Threshhold-Both-Pnlbd
	OBJECT-TYPE
	SYNTAX  INTEGER
	ACCESS  read-write
	STATUS  mandatory
	DESCRIPTION "PB2 Over-Current-Alarm-Threshhold-Both-Pnlbd"
		::= { panelboard2 371 }

pb2-Under-Current-Alarm-Threshhold-Both-Pnlbd
	OBJECT-TYPE
	SYNTAX  INTEGER
	ACCESS  read-write
	STATUS  mandatory
	DESCRIPTION "PB2 Under-Current-Alarm-Threshhold-Both-Pnlbd"
		::= { panelboard2 372 }

pb2-Over-Current-Set-Counter-Both-Pnlbd
	OBJECT-TYPE
	SYNTAX  INTEGER
	ACCESS  read-only
	STATUS  mandatory
	DESCRIPTION "PB2 Over-Current-Set-Counter-Both-Pnlbd"
		::= { panelboard2 373 }

pb2-Over-Current-Reset-Counter-Both-Pnlbd
	OBJECT-TYPE
	SYNTAX  INTEGER
	ACCESS  read-only
	STATUS  mandatory
	DESCRIPTION "PB2 Over-Current-Reset-Counter-Both-Pnlbd"
		::= { panelboard2 374 }

pb2-Under-Current-Set-Counter-Both-Pnlbd
	OBJECT-TYPE
	SYNTAX  INTEGER
	ACCESS  read-only
	STATUS  mandatory
	DESCRIPTION "PB2 Under-Current-Set-Counter-Both-Pnlbd"
		::= { panelboard2 375 }

pb2-Under-Current-Reset-Counter-Both-Pnlbd
	OBJECT-TYPE
	SYNTAX  INTEGER
	ACCESS  read-only
	STATUS  mandatory
	DESCRIPTION "PB2 Under-Current-Reset-Counter-Both-Pnlbd"
		::= { panelboard2 376 }

pb2-Voltage-Option-Setting
	OBJECT-TYPE
	SYNTAX  INTEGER
	ACCESS  read-only
	STATUS  mandatory
	DESCRIPTION "PB2 Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { panelboard2 377 }

pb2-Voltage-A-B-Main
	OBJECT-TYPE
	SYNTAX  INTEGER
	ACCESS  read-only
	STATUS  mandatory
	DESCRIPTION "PB2 Voltage-A-B-Main
                     Note for all voltages: 1200 = 120.0 volts"
		::= { panelboard2 378 }

pb2-Voltage-B-C-Main
	OBJECT-TYPE
	SYNTAX  INTEGER
	ACCESS  read-only
	STATUS  mandatory
	DESCRIPTION "PB2 Voltage-B-C-Main"
		::= { panelboard2 379 }

pb2-Voltage-C-A-Main
	OBJECT-TYPE
	SYNTAX  INTEGER
	ACCESS  read-only
	STATUS  mandatory
	DESCRIPTION "PB2 Voltage-C-A-Main"
		::= { panelboard2 380 }

pb2-Voltage-A-N-Main
	OBJECT-TYPE
	SYNTAX  INTEGER
	ACCESS  read-only
	STATUS  mandatory
	DESCRIPTION "PB2 Voltage-A-N-Main"
		::= { panelboard2 381 }

pb2-Voltage-B-N-Main
	OBJECT-TYPE
	SYNTAX  INTEGER
	ACCESS  read-only
	STATUS  mandatory
	DESCRIPTION "PB2 Voltage-B-N-Main"
		::= { panelboard2 382 }

pb2-Voltage-C-N-Main
	OBJECT-TYPE
	SYNTAX  INTEGER
	ACCESS  read-only
	STATUS  mandatory
	DESCRIPTION "PB2 Voltage-C-N-Main"
		::= { panelboard2 383 }

pb2-Over-Voltage-Alarm-Threshhold-MAin
	OBJECT-TYPE
	SYNTAX  INTEGER
	ACCESS  read-write
	STATUS  mandatory
	DESCRIPTION "PB2 Over-Voltage-Alarm-Threshhold-Main
                     Note All Over and Under Voltage is for L-L values"
		::= { panelboard2 384 }

pb2-Under-Voltage-Alarm-Threshhold-Main
	OBJECT-TYPE
	SYNTAX  INTEGER
	ACCESS  read-write
	STATUS  mandatory
	DESCRIPTION "PB2 Under-Voltage-Alarm-Threshhold-Main"
		::= { panelboard2 385 }

pb2-Over-Voltage-Set-Counter-Main
	OBJECT-TYPE
	SYNTAX  INTEGER
	ACCESS  read-only
	STATUS  mandatory
	DESCRIPTION "PB2 Over-Voltage-Set-Counter-Main"
		::= { panelboard2 386 }

pb2-Over-Voltage-Reset-Counter-Main
	OBJECT-TYPE
	SYNTAX  INTEGER
	ACCESS  read-only
	STATUS  mandatory
	DESCRIPTION "PB2 Over-Voltage-Reset-Counter-Main"
		::= { panelboard2 387 }

pb2-Under-Voltage-Set-Counter-Main
	OBJECT-TYPE
	SYNTAX  INTEGER
	ACCESS  read-only
	STATUS  mandatory
	DESCRIPTION "PB2 Under-Voltage-Set-Counter-Main"
		::= { panelboard2 388 }

pb2-Under-Voltage-Reset-Counter-Main
	OBJECT-TYPE
	SYNTAX  INTEGER
	ACCESS  read-only
	STATUS  mandatory
	DESCRIPTION "PB2 Under-Voltage-Reset-Counter-Main"
		::= { panelboard2 389 }


pb2-Voltage-Frequency-Main
	OBJECT-TYPE
	SYNTAX  INTEGER
	ACCESS  read-only
	STATUS  mandatory
	DESCRIPTION "PB2 Voltage-Frequency-Main
                     note for frequency: 600 = 60.0Hz
                     Range is 40-70Hz
                     Note if insufficient voltage is present frequency will read 0xFFFF"
		::= { panelboard2 390 }

pb2-Voltage-A-B-Alternate
	OBJECT-TYPE
	SYNTAX  INTEGER
	ACCESS  read-only
	STATUS  mandatory
	DESCRIPTION "PB2 Voltage-A-B-Alternate"
		::= { panelboard2 391 }

pb2-Voltage-B-C-Alternate
	OBJECT-TYPE
	SYNTAX  INTEGER
	ACCESS  read-only
	STATUS  mandatory
	DESCRIPTION "PB2 Voltage-B-C-Alternate"
		::= { panelboard2 392 }

pb2-Voltage-C-A-Alternate
	OBJECT-TYPE
	SYNTAX  INTEGER
	ACCESS  read-only
	STATUS  mandatory
	DESCRIPTION "PB2 Voltage-C-A-Alternate"
		::= { panelboard2 393 }

pb2-Voltage-A-N-Alternate
	OBJECT-TYPE
	SYNTAX  INTEGER
	ACCESS  read-only
	STATUS  mandatory
	DESCRIPTION "PB2 Voltage-A-N-Alternate"
		::= { panelboard2 394 }

pb2-Voltage-B-N-Alternate
	OBJECT-TYPE
	SYNTAX  INTEGER
	ACCESS  read-only
	STATUS  mandatory
	DESCRIPTION "PB2 Voltage-B-N-Alternate"
		::= { panelboard2 395 }

pb2-Voltage-C-N-Alternate
	OBJECT-TYPE
	SYNTAX  INTEGER
	ACCESS  read-only
	STATUS  mandatory
	DESCRIPTION "PB2 Voltage-C-N-Alternate"
		::= { panelboard2 396 }

pb2-Over-Voltage-Alarm-Threshhold-Alternate
	OBJECT-TYPE
	SYNTAX  INTEGER
	ACCESS  read-write
	STATUS  mandatory
	DESCRIPTION "PB2 Over-Voltage-Alarm-Threshhold-Alternate"
		::= { panelboard2 397 }

pb2-Under-Voltage-Alarm-Threshhold-Alternate
	OBJECT-TYPE
	SYNTAX  INTEGER
	ACCESS  read-write
	STATUS  mandatory
	DESCRIPTION "PB2 Under-Voltage-Alarm-Threshhold-Alternate"
		::= { panelboard2 398 }

pb2-Over-Voltage-Set-Counter-Alternate
	OBJECT-TYPE
	SYNTAX  INTEGER
	ACCESS  read-only
	STATUS  mandatory
	DESCRIPTION "PB2 Over-Voltage-Set-Counter-Alternate"
		::= { panelboard2 399 }

pb2-Over-Voltage-Reset-Counter-Alternate
	OBJECT-TYPE
	SYNTAX  INTEGER
	ACCESS  read-only
	STATUS  mandatory
	DESCRIPTION "PB2 Over-Voltage-Reset-Counter-Alternate"
		::= { panelboard2 400 }

pb2-Under-Voltage-Set-Counter-Alternate
	OBJECT-TYPE
	SYNTAX  INTEGER
	ACCESS  read-only
	STATUS  mandatory
	DESCRIPTION "PB2 Under-Voltage-Set-Counter-Alternate"
		::= { panelboard2 401 }

pb2-Under-Voltage-Reset-Counter-Alternate
	OBJECT-TYPE
	SYNTAX  INTEGER
	ACCESS  read-only
	STATUS  mandatory
	DESCRIPTION "PB2 Under-Voltage-Reset-Counter-Alternate"
		::= { panelboard2 402 }

pb2-Real-Power-KW
	OBJECT-TYPE
	SYNTAX  INTEGER
	ACCESS  read-only
	STATUS  mandatory
	DESCRIPTION "PB2 Real-Power-KW
                     Note for all KWs: 100 = 10.0 KW"
		::= { panelboard2 403 }

pb2-Real-Power-Phase-A
	OBJECT-TYPE
	SYNTAX  INTEGER
	ACCESS  read-only
	STATUS  mandatory
	DESCRIPTION "PB2 Real-Power-Phase-A"
		::= { panelboard2 404 }

pb2-Real-Power-Phase-B
	OBJECT-TYPE
	SYNTAX  INTEGER
	ACCESS  read-only
	STATUS  mandatory
	DESCRIPTION "PB2 Real-Power-Phase-B"
		::= { panelboard2 405 }

pb2-Real-Power-Phase-C
	OBJECT-TYPE
	SYNTAX  INTEGER
	ACCESS  read-only
	STATUS  mandatory
	DESCRIPTION "PB2 Real-Power-Phase-C"
		::= { panelboard2 406 }

pb2-Reactive-Power-KVAR
	OBJECT-TYPE
	SYNTAX  INTEGER
	ACCESS  read-only
	STATUS  mandatory
	DESCRIPTION "PB2 Reactive-Power-KVAR
                     Note for KVAR: 100 = 10.0 KVAR"
		::= { panelboard2 407 }

pb2-Apparent-Power-KVA
	OBJECT-TYPE
	SYNTAX  INTEGER
	ACCESS  read-only
	STATUS  mandatory
	DESCRIPTION "PB2 Apparent-Power-KVA
                     Note for KVA: 100 = 10.0 KVA"
		::= { panelboard2 408 }

pb2-Total-Power-Factor
	OBJECT-TYPE
	SYNTAX  INTEGER
	ACCESS  read-only
	STATUS  mandatory
	DESCRIPTION "PB2 Total-Power-Factor
                     Note for all Power Factor: 1000 = 100.0 PF"
		::= { panelboard2 409 }

pb2-Power-Factor-Phase-A
	OBJECT-TYPE
	SYNTAX  INTEGER
	ACCESS  read-only
	STATUS  mandatory
	DESCRIPTION "PB2 Power-Factor-Phase-A"
		::= { panelboard2 410 }

pb2-Power-Factor-Phase-B
	OBJECT-TYPE
	SYNTAX  INTEGER
	ACCESS  read-only
	STATUS  mandatory
	DESCRIPTION "PB2 Power-Factor-Phase-B"
		::= { panelboard2 411 }

pb2-Power-Factor-Phase-C
	OBJECT-TYPE
	SYNTAX  INTEGER
	ACCESS  read-only
	STATUS  mandatory
	DESCRIPTION "PB2 Power-Factor-Phase-C"
		::= { panelboard2 412 }

pb2-Energy-Consumption-KWh-Lower-Word-Integer
	OBJECT-TYPE
	SYNTAX  INTEGER
	ACCESS  read-write
	STATUS  mandatory
	DESCRIPTION "PB2 Energy-Consumption-KWh-Lower-Word-Integer
		     Note for KWh: 100 = 100KWh
                     Combine lower and upper integers into a word for total KWh"
		::= { panelboard2 413 }

pb2-Energy-Consumption-KWh-Upper-Word-Integer
	OBJECT-TYPE
	SYNTAX  INTEGER
	ACCESS  read-write
	STATUS  mandatory
	DESCRIPTION "PB2 Energy-Consumption-KWh-Upper-Word-Integer"
		::= { panelboard2 414 }

pb2-Main-Voltage-THD-Phase-A
	OBJECT-TYPE
	SYNTAX  INTEGER
	ACCESS  read-only
	STATUS  mandatory
	DESCRIPTION "PB2 Main-Voltage-THD-Phase-A"
		::= { panelboard2 415 }

pb2-Main-Voltage-THD-Phase-B
	OBJECT-TYPE
	SYNTAX  INTEGER
	ACCESS  read-only
	STATUS  mandatory
	DESCRIPTION "PB2 Main-Voltage-THD-Phase-B"
		::= { panelboard2 416 }

pb2-Main-Voltage-THD-Phase-C
	OBJECT-TYPE
	SYNTAX  INTEGER
	ACCESS  read-only
	STATUS  mandatory
	DESCRIPTION "PB2 Main-Voltage-THD-Phase-C"
		::= { panelboard2 417 }

pb2-Alt-Voltage-THD-Phase-A
	OBJECT-TYPE
	SYNTAX  INTEGER
	ACCESS  read-only
	STATUS  mandatory
	DESCRIPTION "PB2 Alt-Voltage-THD-Phase-A"
		::= { panelboard2 418 }

pb2-Alt-Voltage-THD-Phase-B
	OBJECT-TYPE
	SYNTAX  INTEGER
	ACCESS  read-only
	STATUS  mandatory
	DESCRIPTION "PB2 Alt-Voltage-THD-Phase-B"
		::= { panelboard2 419 }

pb2-Alt-Voltage-THD-Phase-C
	OBJECT-TYPE
	SYNTAX  INTEGER
	ACCESS  read-only
	STATUS  mandatory
	DESCRIPTION "PB2 Alt-Voltage-THD-Phase-C"
		::= { panelboard2 420 }

pb2-Current-Ground-Panelboard
	OBJECT-TYPE
	SYNTAX  INTEGER
	ACCESS  read-only
	STATUS  mandatory
	DESCRIPTION "PB2 Current-Ground-Panelboard"
		::= { panelboard2 421 }

--------------------------------------------------------------------------------
-- BCMS traps
--------------------------------------------------------------------------------

pb1AlarmBranch
        TRAP-TYPE
	  ENTERPRISE	bcmstraps
	  VARIABLES		{ pb1-Global-Warning-Alarm-Register }
	  DESCRIPTION	"PB1 Alarm Branch Currnets(warning,alarm,zero)"
	  ::= 1

pb1AlarmV-I
        TRAP-TYPE
	  ENTERPRISE	bcmstraps
	  VARIABLES		{ pb1-Meter-Alarm-Status-Nonlatching }
	  DESCRIPTION	"PB1 Alarm Main Voltage and Current"
	  ::= 2

pb2AlarmBranch
        TRAP-TYPE
	  ENTERPRISE	bcmstraps
	  VARIABLES		{ pb2-Global-Warning-Alarm-Register }
	  DESCRIPTION	"PB2 Alarm Branch Currnets(warning,alarm,zero)"
	  ::= 3

pb2AlarmV-I
        TRAP-TYPE
	  ENTERPRISE	bcmstraps
	  VARIABLES		{ pb2-Meter-Alarm-Status-Nonlatching }
	  DESCRIPTION	"PB2 Alarm Main Voltage and Current"
	  ::= 4
END
